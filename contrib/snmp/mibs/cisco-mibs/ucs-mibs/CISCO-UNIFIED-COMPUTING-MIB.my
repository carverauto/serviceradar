-- ********************************************************************
-- CISCO-UNIFIED-COMPUTING-MIB.my
-- 
-- Cisco Unified Computing System MIB Module
-- 
-- Copyright (c) 2005-2018 Cisco Systems, Inc. All rights reserved.
-- ********************************************************************

CISCO-UNIFIED-COMPUTING-MIB DEFINITIONS ::= BEGIN

IMPORTS
        Unsigned32,
        Counter32,
        OBJECT-TYPE,
        MODULE-IDENTITY,
        NOTIFICATION-TYPE
                FROM SNMPv2-SMI
        MODULE-COMPLIANCE,
        OBJECT-GROUP,
        NOTIFICATION-GROUP
                FROM SNMPv2-CONF
        SnmpAdminString
                FROM SNMP-FRAMEWORK-MIB
        RowPointer,                
        DateAndTime,
        TEXTUAL-CONVENTION
                FROM SNMPv2-TC
        ciscoMgmt
                FROM CISCO-SMI;

ciscoUnifiedComputingMIB MODULE-IDENTITY
        LAST-UPDATED  "201001290000Z" 
        ORGANIZATION  "Cisco"
        CONTACT-INFO
            "Cisco Systems
            Customer Service

            Postal: 170 West Tasman Drive
            San Jose, CA  95134
            USA

            Tel: +1 800 553-NETS

            E-mail: savbu-snmp-dev@cisco.com"
      DESCRIPTION
         "This MIB module defines the managed objects for
         Unified Computing System (UCS) Manager.
                
         Cisco UCS Manager provides centralized management
         capabilities, creates a unified management domain, and
         serves as the central nervous system of the Cisco Unified
         Computing System.
         
         UCS configuration is comprised of operational and
         administrative settings. The data is organized hierarchically
         in a tree structure, starts from the top (root) and contains
         children and parent nodes. Each node in the tree is a managed
         object and each object in the UCS has a unique Distinguished
         Name (DN) that describes the object and its place in the tree.
         Every managed object is also identified through a
         CucsManagedObjectId of type integer.
         
         Managed objects are abstractions of real world resources,
         they represent the physical and logical components of the UCS,
         for example, switch, chassis, blades, and so on. Properties on
         the Managed Objects (MO) are characterized as configurations
         and operations.
         Configuration Policies are the majority of the policies in the
         system and are used to describe configurations of different
         components of the UCS. Policies determine how the system
         behaves under specific circumstances. Certain MOs are not
         created by users, but are automatically created by the UCS,
         power supply objects and fan objects are examples of
         automatically created MOs.
         "
      REVISION "201001290000Z" 
      DESCRIPTION
         "Initial version of this MIB module."
  ::= { ciscoMgmt 719 }

-- *********************************************************************
-- Textual Conventions
-- *********************************************************************

CucsManagedObjectId ::= TEXTUAL-CONVENTION
        DISPLAY-HINT "d"
        STATUS current
        DESCRIPTION
            "A unique identifier for this managed object.
            Objects in UCS Manager are stored in a Management
            Information Tree (MIT). The MIT is a repository of all
            Managed Object (MO) instances, indexed by their
            Distinguished Name (DN).
            The MIT somewhat resembles a file structure - going from
            main folder to the next lowest folder, and so on, until
            the full path to a MO is established.
            
            Every object in UCS Manager has two unique identifiers:
            1) A distinguished name (DN). A DN provides a
            fully-qualified path from the top of the object tree.
            It is built as an ordered sequence of relative names
            separated by the '/' character.
            The DN is used to identify objects in the XML API.
            
            2) A CucsManagedObjectId, which is an integer uniquely
            identifying an object. 
            The CucsManagedObjectId is used to identify objects and
            traverse tables when using the SNMP protocol. 
            
            For example, an object representing a network adaptor
            on a blade might be identified with its DN set
            to 'sys/chassis-5/blade-2/adaptor-1' and its
            CucsManagedObjectId set to '13203'."
        SYNTAX         Unsigned32

CucsManagedObjectDn ::= TEXTUAL-CONVENTION
        STATUS current
        DESCRIPTION
            "An immutable property of all Managed Objects (MO) that
            provides a fully qualified and unambiguous name for the MO.
            A DN provides a fully-qualified path from the top of the
            object tree.
            It is built as an ordered sequence of relative names
            separated by the '/' character.
            
            For example, an object representing a network adaptor
            on a blade might be identified with its DN set
            to 'sys/chassis-5/blade-2/adaptor-1'.
            "
        SYNTAX         OCTET STRING

-- Faults per Managed Object:
-- The information below is organized as follows:
-- MO Name
    -- List of DNs under which the MO can be instantiated in the MIT
        -- List of faults that can be instantiated for this MO

-- compute:Physical
        -- fltComputePhysicalInsufficientlyEquipped
        -- fltComputePhysicalIdentityUnestablishable
        -- fltComputePhysicalPowerProblem
        -- fltComputePhysicalThermalProblem
        -- fltComputePhysicalBiosPostTimeout
        -- fltComputePhysicalDiscoveryFailed
        -- fltComputePhysicalAssociationFailed
        -- fltComputePhysicalInoperable
        -- fltComputePhysicalUnassignedMissing
        -- fltComputePhysicalAssignedMissing
        -- fltComputePhysicalUnidentified
        -- fltComputePhysicalUnassignedInaccessible
        -- fltComputePhysicalAssignedInaccessible
        -- fltComputePhysicalPost-failure
        -- fltComputePhysicalDisassociationFailed
        -- fltComputePhysicalNetworkMisconfigured
        -- fltComputePhysicalAdapterMismatch
        -- fltComputePhysicalConnectivityDown
        -- fltComputePhysicalDeprecated
        -- fltComputePhysicalAdapterFirmwareNeedsUpdate
        -- fltComputePhysicalIdentityUnestablishableOrDeprecated
        -- fltComputePhysicalKmipFault
        -- fltComputePhysicalHardwareInventoryMismatch
        -- fltComputePhysicalPciConfigMismatch
        -- fsmStFailComputePhysicalAssociate:ActivateBios
        -- fsmStFailComputePhysicalAssociate:AssertBypassWait
        -- fsmStFailComputePhysicalAssociate:BiosImgUpdate
        -- fsmStFailComputePhysicalAssociate:BiosPostCompletion
        -- fsmStFailComputePhysicalAssociate:BladePowerOff
        -- fsmStFailComputePhysicalAssociate:BmcConfigPnuOS
        -- fsmStFailComputePhysicalAssociate:BmcPreconfigPnuOSLocal
        -- fsmStFailComputePhysicalAssociate:BmcPreconfigPnuOSPeer
        -- fsmStFailComputePhysicalAssociate:BmcUnconfigPnuOS
        -- fsmStFailComputePhysicalAssociate:BootHost
        -- fsmStFailComputePhysicalAssociate:BootPnuos
        -- fsmStFailComputePhysicalAssociate:BootWait
        -- fsmStFailComputePhysicalAssociate:CalculateVlanGroupForHostOSLocal
        -- fsmStFailComputePhysicalAssociate:CalculateVlanGroupForHostOSPeer
        -- fsmStFailComputePhysicalAssociate:CheckPowerAvailability
        -- fsmStFailComputePhysicalAssociate:CiscoOSOpenGate
        -- fsmStFailComputePhysicalAssociate:ClearBiosUpdate
        -- fsmStFailComputePhysicalAssociate:ConfigCimcVMedia
        -- fsmStFailComputePhysicalAssociate:ConfigExtMgmtGw
        -- fsmStFailComputePhysicalAssociate:ConfigExtMgmtRules
        -- fsmStFailComputePhysicalAssociate:ConfigFanSpeed
        -- fsmStFailComputePhysicalAssociate:ConfigFlexFlash
        -- fsmStFailComputePhysicalAssociate:ConfigHostOsAnnotations
        -- fsmStFailComputePhysicalAssociate:ConfigMgmtIpRules
        -- fsmStFailComputePhysicalAssociate:ConfigServerIdentity
        -- fsmStFailComputePhysicalAssociate:ConfigSoL
        -- fsmStFailComputePhysicalAssociate:ConfigUserAccess
        -- fsmStFailComputePhysicalAssociate:ConfigUuid
        -- fsmStFailComputePhysicalAssociate:DeassertResetBypass
        -- fsmStFailComputePhysicalAssociate:DeleteCurlDownloadedImages
        -- fsmStFailComputePhysicalAssociate:DeleteImagesRemote
        -- fsmStFailComputePhysicalAssociate:GraphicsImageUpdate
        -- fsmStFailComputePhysicalAssociate:HbaImgUpdate
        -- fsmStFailComputePhysicalAssociate:HostOSConfig
        -- fsmStFailComputePhysicalAssociate:HostOSConnect
        -- fsmStFailComputePhysicalAssociate:HostOSIdent
        -- fsmStFailComputePhysicalAssociate:HostOSPolicy
        -- fsmStFailComputePhysicalAssociate:HostOSValidate
        -- fsmStFailComputePhysicalAssociate:LocalDiskFwUpdate
        -- fsmStFailComputePhysicalAssociate:MarkAdapterForReboot
        -- fsmStFailComputePhysicalAssociate:MswitchImgUpdate
        -- fsmStFailComputePhysicalAssociate:NicConfigHostOSLocal
        -- fsmStFailComputePhysicalAssociate:NicConfigHostOSPeer
        -- fsmStFailComputePhysicalAssociate:NicConfigParamsHostOSLocal
        -- fsmStFailComputePhysicalAssociate:NicConfigParamsHostOSPeer
        -- fsmStFailComputePhysicalAssociate:NicConfigPnuOSLocal
        -- fsmStFailComputePhysicalAssociate:NicConfigPnuOSPeer
        -- fsmStFailComputePhysicalAssociate:NicConfigServiceInfraLocal
        -- fsmStFailComputePhysicalAssociate:NicConfigServiceInfraPeer
        -- fsmStFailComputePhysicalAssociate:NicImgUpdate
        -- fsmStFailComputePhysicalAssociate:NicUnconfigPnuOSLocal
        -- fsmStFailComputePhysicalAssociate:NicUnconfigPnuOSPeer
        -- fsmStFailComputePhysicalAssociate:OobPollSasExpanderActivateStatus
        -- fsmStFailComputePhysicalAssociate:OobPollSasExpanderBootImgActivateStatus
        -- fsmStFailComputePhysicalAssociate:OobPollSasExpanderUpdateStatus
        -- fsmStFailComputePhysicalAssociate:OobSasExpanderBootImgActivate
        -- fsmStFailComputePhysicalAssociate:OobSasExpanderImgActivate
        -- fsmStFailComputePhysicalAssociate:OobSasExpanderImgUpdate
        -- fsmStFailComputePhysicalAssociate:OobStorageConfig
        -- fsmStFailComputePhysicalAssociate:OobStorageInventory
        -- fsmStFailComputePhysicalAssociate:PnuOSCatalog
        -- fsmStFailComputePhysicalAssociate:PnuOSConfig
        -- fsmStFailComputePhysicalAssociate:PnuOSIdent
        -- fsmStFailComputePhysicalAssociate:PnuOSInventory
        -- fsmStFailComputePhysicalAssociate:PnuOSLocalDiskConfig
        -- fsmStFailComputePhysicalAssociate:PnuOSPeripheralComponentConfig
        -- fsmStFailComputePhysicalAssociate:PnuOSPolicy
        -- fsmStFailComputePhysicalAssociate:PnuOSSelfTest
        -- fsmStFailComputePhysicalAssociate:PnuOSUnloadDrivers
        -- fsmStFailComputePhysicalAssociate:PnuOSValidate
        -- fsmStFailComputePhysicalAssociate:PollBiosActivateStatus
        -- fsmStFailComputePhysicalAssociate:PollBiosUpdateStatus
        -- fsmStFailComputePhysicalAssociate:PollBoardCtrlPowerCycle
        -- fsmStFailComputePhysicalAssociate:PollBoardCtrlUpdateStatus
        -- fsmStFailComputePhysicalAssociate:PollClearBiosUpdateStatus
        -- fsmStFailComputePhysicalAssociate:PowerCycleBoard
        -- fsmStFailComputePhysicalAssociate:PowerDeployWait
        -- fsmStFailComputePhysicalAssociate:PowerOn
        -- fsmStFailComputePhysicalAssociate:PowerOnPreConfig
        -- fsmStFailComputePhysicalAssociate:PreSanitize
        -- fsmStFailComputePhysicalAssociate:PrepareForBoot
        -- fsmStFailComputePhysicalAssociate:RestoreVdStatus
        -- fsmStFailComputePhysicalAssociate:Sanitize
        -- fsmStFailComputePhysicalAssociate:SasExpanderImgUpdate
        -- fsmStFailComputePhysicalAssociate:SolRedirectDisable
        -- fsmStFailComputePhysicalAssociate:SolRedirectEnable
        -- fsmStFailComputePhysicalAssociate:StorageCtlrImgUpdate
        -- fsmStFailComputePhysicalAssociate:SwConfigHostOSLocal
        -- fsmStFailComputePhysicalAssociate:SwConfigHostOSPeer
        -- fsmStFailComputePhysicalAssociate:SwConfigPnuOSLocal
        -- fsmStFailComputePhysicalAssociate:SwConfigPnuOSPeer
        -- fsmStFailComputePhysicalAssociate:SwConfigPortNivLocal
        -- fsmStFailComputePhysicalAssociate:SwConfigPortNivPeer
        -- fsmStFailComputePhysicalAssociate:SwConfigServiceInfraLocal
        -- fsmStFailComputePhysicalAssociate:SwConfigServiceInfraPeer
        -- fsmStFailComputePhysicalAssociate:SwUnconfigPnuOSLocal
        -- fsmStFailComputePhysicalAssociate:SwUnconfigPnuOSPeer
        -- fsmStFailComputePhysicalAssociate:SyncPowerState
        -- fsmStFailComputePhysicalAssociate:UnconfigCimcVMedia
        -- fsmStFailComputePhysicalAssociate:UnconfigExtMgmtGw
        -- fsmStFailComputePhysicalAssociate:UnconfigExtMgmtRules
        -- fsmStFailComputePhysicalAssociate:UnlockFirmwareImage
        -- fsmStFailComputePhysicalAssociate:UpdateBiosRequest
        -- fsmStFailComputePhysicalAssociate:UpdateBoardCtrlRequest
        -- fsmStFailComputePhysicalAssociate:VerifyFcZoneConfig
        -- fsmStFailComputePhysicalAssociate:activateAdaptorNwFwLocal
        -- fsmStFailComputePhysicalAssociate:activateAdaptorNwFwPeer
        -- fsmStFailComputePhysicalAssociate:activateIBMCFw
        -- fsmStFailComputePhysicalAssociate:copyRemote
        -- fsmStFailComputePhysicalAssociate:downloadImages
        -- fsmStFailComputePhysicalAssociate:hagHostOSConnect
        -- fsmStFailComputePhysicalAssociate:hagPnuOSConnect
        -- fsmStFailComputePhysicalAssociate:hagPnuOSDisconnect
        -- fsmStFailComputePhysicalAssociate:resetIBMC
        -- fsmStFailComputePhysicalAssociate:serialDebugPnuOSConnect
        -- fsmStFailComputePhysicalAssociate:serialDebugPnuOSDisconnect
        -- fsmStFailComputePhysicalAssociate:updateAdaptorNwFwLocal
        -- fsmStFailComputePhysicalAssociate:updateAdaptorNwFwPeer
        -- fsmStFailComputePhysicalAssociate:updateIBMCFw
        -- fsmStFailComputePhysicalAssociate:waitForAdaptorNwFwUpdateLocal
        -- fsmStFailComputePhysicalAssociate:waitForAdaptorNwFwUpdatePeer
        -- fsmStFailComputePhysicalAssociate:waitForIBMCFwUpdate
        -- fsmStFailComputePhysicalDisassociate:BiosPostCompletion
        -- fsmStFailComputePhysicalDisassociate:BmcConfigPnuOS
        -- fsmStFailComputePhysicalDisassociate:BmcPreconfigPnuOSLocal
        -- fsmStFailComputePhysicalDisassociate:BmcPreconfigPnuOSPeer
        -- fsmStFailComputePhysicalDisassociate:BmcUnconfigPnuOS
        -- fsmStFailComputePhysicalDisassociate:BootPnuos
        -- fsmStFailComputePhysicalDisassociate:BootWait
        -- fsmStFailComputePhysicalDisassociate:CheckPowerAvailability
        -- fsmStFailComputePhysicalDisassociate:ConfigBios
        -- fsmStFailComputePhysicalDisassociate:ConfigFlexFlashScrub
        -- fsmStFailComputePhysicalDisassociate:ConfigKvmMgmtDefaultSetting
        -- fsmStFailComputePhysicalDisassociate:ConfigUserAccess
        -- fsmStFailComputePhysicalDisassociate:DeassertResetBypass
        -- fsmStFailComputePhysicalDisassociate:HandlePooling
        -- fsmStFailComputePhysicalDisassociate:NicConfigPnuOSLocal
        -- fsmStFailComputePhysicalDisassociate:NicConfigPnuOSPeer
        -- fsmStFailComputePhysicalDisassociate:NicUnconfigHostOSLocal
        -- fsmStFailComputePhysicalDisassociate:NicUnconfigHostOSPeer
        -- fsmStFailComputePhysicalDisassociate:NicUnconfigPnuOSLocal
        -- fsmStFailComputePhysicalDisassociate:NicUnconfigPnuOSPeer
        -- fsmStFailComputePhysicalDisassociate:NicUnconfigServiceInfraLocal
        -- fsmStFailComputePhysicalDisassociate:NicUnconfigServiceInfraPeer
        -- fsmStFailComputePhysicalDisassociate:OobDiskScrub
        -- fsmStFailComputePhysicalDisassociate:PnuOSCatalog
        -- fsmStFailComputePhysicalDisassociate:PnuOSIdent
        -- fsmStFailComputePhysicalDisassociate:PnuOSPolicy
        -- fsmStFailComputePhysicalDisassociate:PnuOSScrub
        -- fsmStFailComputePhysicalDisassociate:PnuOSSelfTest
        -- fsmStFailComputePhysicalDisassociate:PnuOSUnconfig
        -- fsmStFailComputePhysicalDisassociate:PnuOSValidate
        -- fsmStFailComputePhysicalDisassociate:PowerDeployWait
        -- fsmStFailComputePhysicalDisassociate:PowerOn
        -- fsmStFailComputePhysicalDisassociate:PreSanitize
        -- fsmStFailComputePhysicalDisassociate:ResetSecureBootConfig
        -- fsmStFailComputePhysicalDisassociate:Sanitize
        -- fsmStFailComputePhysicalDisassociate:Shutdown
        -- fsmStFailComputePhysicalDisassociate:SolRedirectDisable
        -- fsmStFailComputePhysicalDisassociate:SolRedirectEnable
        -- fsmStFailComputePhysicalDisassociate:SwConfigPnuOSLocal
        -- fsmStFailComputePhysicalDisassociate:SwConfigPnuOSPeer
        -- fsmStFailComputePhysicalDisassociate:SwConfigPortNivLocal
        -- fsmStFailComputePhysicalDisassociate:SwConfigPortNivPeer
        -- fsmStFailComputePhysicalDisassociate:SwUnconfigHostOSLocal
        -- fsmStFailComputePhysicalDisassociate:SwUnconfigHostOSPeer
        -- fsmStFailComputePhysicalDisassociate:SwUnconfigPnuOSLocal
        -- fsmStFailComputePhysicalDisassociate:SwUnconfigPnuOSPeer
        -- fsmStFailComputePhysicalDisassociate:UnconfigBios
        -- fsmStFailComputePhysicalDisassociate:UnconfigCimcVMedia
        -- fsmStFailComputePhysicalDisassociate:UnconfigExtMgmtGw
        -- fsmStFailComputePhysicalDisassociate:UnconfigExtMgmtRules
        -- fsmStFailComputePhysicalDisassociate:UnconfigFlexFlash
        -- fsmStFailComputePhysicalDisassociate:UnconfigServerIdentity
        -- fsmStFailComputePhysicalDisassociate:UnconfigSoL
        -- fsmStFailComputePhysicalDisassociate:UnconfigUuid
        -- fsmStFailComputePhysicalDisassociate:VerifyFcZoneConfig
        -- fsmStFailComputePhysicalDisassociate:hagPnuOSConnect
        -- fsmStFailComputePhysicalDisassociate:hagPnuOSDisconnect
        -- fsmStFailComputePhysicalDisassociate:serialDebugPnuOSConnect
        -- fsmStFailComputePhysicalDisassociate:serialDebugPnuOSDisconnect
        -- fsmStFailComputePhysicalPowerCap:Config
        -- fsmStFailComputePhysicalDecommission:CleanupCIMC
        -- fsmStFailComputePhysicalDecommission:CleanupPortConfigLocal
        -- fsmStFailComputePhysicalDecommission:CleanupPortConfigPeer
        -- fsmStFailComputePhysicalDecommission:Execute
        -- fsmStFailComputePhysicalDecommission:PrecleanupPortConfig
        -- fsmStFailComputePhysicalDecommission:StopVMediaLocal
        -- fsmStFailComputePhysicalDecommission:StopVMediaPeer
        -- fsmStFailComputePhysicalDecommission:UnconfigExtMgmtGw
        -- fsmStFailComputePhysicalDecommission:UnconfigExtMgmtRules
        -- fsmStFailComputePhysicalSoftShutdown:Execute
        -- fsmStFailComputePhysicalHardShutdown:Execute
        -- fsmStFailComputePhysicalTurnup:CheckPowerAvailability
        -- fsmStFailComputePhysicalTurnup:Execute
        -- fsmStFailComputePhysicalTurnup:PowerDeployWait
        -- fsmStFailComputePhysicalPowercycle:CheckPowerAvailability
        -- fsmStFailComputePhysicalPowercycle:Execute
        -- fsmStFailComputePhysicalPowercycle:PowerDeployWait
        -- fsmStFailComputePhysicalPowercycle:PreSanitize
        -- fsmStFailComputePhysicalPowercycle:Sanitize
        -- fsmStFailComputePhysicalHardreset:CheckPowerAvailability
        -- fsmStFailComputePhysicalHardreset:Execute
        -- fsmStFailComputePhysicalHardreset:PowerDeployWait
        -- fsmStFailComputePhysicalHardreset:PreSanitize
        -- fsmStFailComputePhysicalHardreset:Sanitize
        -- fsmStFailComputePhysicalSoftreset:CheckPowerAvailability
        -- fsmStFailComputePhysicalSoftreset:Execute
        -- fsmStFailComputePhysicalSoftreset:PowerDeployWait
        -- fsmStFailComputePhysicalSoftreset:PreSanitize
        -- fsmStFailComputePhysicalSoftreset:Sanitize
        -- fsmStFailComputePhysicalSwConnUpd:A
        -- fsmStFailComputePhysicalSwConnUpd:B
        -- fsmStFailComputePhysicalBiosRecovery:CheckPowerAvailability
        -- fsmStFailComputePhysicalBiosRecovery:Cleanup
        -- fsmStFailComputePhysicalBiosRecovery:PowerDeployWait
        -- fsmStFailComputePhysicalBiosRecovery:PreSanitize
        -- fsmStFailComputePhysicalBiosRecovery:Reset
        -- fsmStFailComputePhysicalBiosRecovery:Sanitize
        -- fsmStFailComputePhysicalBiosRecovery:SetupVmediaLocal
        -- fsmStFailComputePhysicalBiosRecovery:SetupVmediaPeer
        -- fsmStFailComputePhysicalBiosRecovery:Shutdown
        -- fsmStFailComputePhysicalBiosRecovery:Start
        -- fsmStFailComputePhysicalBiosRecovery:StopVMediaLocal
        -- fsmStFailComputePhysicalBiosRecovery:StopVMediaPeer
        -- fsmStFailComputePhysicalBiosRecovery:TeardownVmediaLocal
        -- fsmStFailComputePhysicalBiosRecovery:TeardownVmediaPeer
        -- fsmStFailComputePhysicalBiosRecovery:Wait
        -- fsmStFailComputePhysicalCmosReset:BladePowerOn
        -- fsmStFailComputePhysicalCmosReset:CheckPowerAvailability
        -- fsmStFailComputePhysicalCmosReset:Execute
        -- fsmStFailComputePhysicalCmosReset:PowerDeployWait
        -- fsmStFailComputePhysicalCmosReset:PreSanitize
        -- fsmStFailComputePhysicalCmosReset:ReconfigBios
        -- fsmStFailComputePhysicalCmosReset:ReconfigUuid
        -- fsmStFailComputePhysicalCmosReset:Sanitize
        -- fsmStFailComputePhysicalResetBmc:Execute
        -- fsmStFailComputePhysicalUpdateExtUsers:Deploy
        -- fsmStFailComputePhysicalUpdateAdaptor:CheckPowerAvailability
        -- fsmStFailComputePhysicalUpdateAdaptor:PollUpdateStatusLocal
        -- fsmStFailComputePhysicalUpdateAdaptor:PollUpdateStatusPeer
        -- fsmStFailComputePhysicalUpdateAdaptor:PowerDeployWait
        -- fsmStFailComputePhysicalUpdateAdaptor:PowerOff
        -- fsmStFailComputePhysicalUpdateAdaptor:PowerOn
        -- fsmStFailComputePhysicalUpdateAdaptor:UpdateRequestLocal
        -- fsmStFailComputePhysicalUpdateAdaptor:UpdateRequestPeer
        -- fsmStFailComputePhysicalActivateAdaptor:ActivateLocal
        -- fsmStFailComputePhysicalActivateAdaptor:ActivatePeer
        -- fsmStFailComputePhysicalActivateAdaptor:AssertBypassWait
        -- fsmStFailComputePhysicalActivateAdaptor:CheckPowerAvailability
        -- fsmStFailComputePhysicalActivateAdaptor:DeassertResetBypass
        -- fsmStFailComputePhysicalActivateAdaptor:PowerDeployWait
        -- fsmStFailComputePhysicalActivateAdaptor:PowerOn
        -- fsmStFailComputePhysicalActivateAdaptor:Reset
        -- fsmStFailComputePhysicalConfigSoL:Execute
        -- fsmStFailComputePhysicalUnconfigSoL:Execute
        -- fsmStFailComputePhysicalDiagnosticInterrupt:Execute
        -- fsmStFailComputePhysicalResetKvm:Execute
        -- fsmStFailComputePhysicalUpdateBIOS:Clear
        -- fsmStFailComputePhysicalUpdateBIOS:PollClearStatus
        -- fsmStFailComputePhysicalUpdateBIOS:PollUpdateStatus
        -- fsmStFailComputePhysicalUpdateBIOS:UpdateRequest
        -- fsmStFailComputePhysicalActivateBIOS:Activate
        -- fsmStFailComputePhysicalActivateBIOS:CheckPowerAvailability
        -- fsmStFailComputePhysicalActivateBIOS:Clear
        -- fsmStFailComputePhysicalActivateBIOS:PollActivateStatus
        -- fsmStFailComputePhysicalActivateBIOS:PollClearStatus
        -- fsmStFailComputePhysicalActivateBIOS:PowerDeployWait
        -- fsmStFailComputePhysicalActivateBIOS:PowerOff
        -- fsmStFailComputePhysicalActivateBIOS:PowerOn
        -- fsmStFailComputePhysicalActivateBIOS:UpdateTokens
        -- fsmStFailComputePhysicalResetIpmi:Execute
        -- fsmStFailComputePhysicalFwUpgrade:ActivateBios
        -- fsmStFailComputePhysicalFwUpgrade:AssertBypassWait
        -- fsmStFailComputePhysicalFwUpgrade:BiosImgUpdate
        -- fsmStFailComputePhysicalFwUpgrade:BiosPostCompletion
        -- fsmStFailComputePhysicalFwUpgrade:BladePowerOff
        -- fsmStFailComputePhysicalFwUpgrade:BmcConfigPnuOS
        -- fsmStFailComputePhysicalFwUpgrade:BmcPreconfigPnuOSLocal
        -- fsmStFailComputePhysicalFwUpgrade:BmcPreconfigPnuOSPeer
        -- fsmStFailComputePhysicalFwUpgrade:BmcUnconfigPnuOS
        -- fsmStFailComputePhysicalFwUpgrade:BootPnuos
        -- fsmStFailComputePhysicalFwUpgrade:BootWait
        -- fsmStFailComputePhysicalFwUpgrade:CheckPowerAvailability
        -- fsmStFailComputePhysicalFwUpgrade:CiscoOSOpenGate
        -- fsmStFailComputePhysicalFwUpgrade:ClearBiosUpdate
        -- fsmStFailComputePhysicalFwUpgrade:DeassertResetBypass
        -- fsmStFailComputePhysicalFwUpgrade:DeleteCurlDownloadedImages
        -- fsmStFailComputePhysicalFwUpgrade:DeleteImagesRemote
        -- fsmStFailComputePhysicalFwUpgrade:GraphicsImageUpdate
        -- fsmStFailComputePhysicalFwUpgrade:HbaImgUpdate
        -- fsmStFailComputePhysicalFwUpgrade:LocalDiskFwUpdate
        -- fsmStFailComputePhysicalFwUpgrade:MswitchImgUpdate
        -- fsmStFailComputePhysicalFwUpgrade:NicConfigPnuOSLocal
        -- fsmStFailComputePhysicalFwUpgrade:NicConfigPnuOSPeer
        -- fsmStFailComputePhysicalFwUpgrade:NicImgUpdate
        -- fsmStFailComputePhysicalFwUpgrade:NicUnconfigPnuOSLocal
        -- fsmStFailComputePhysicalFwUpgrade:NicUnconfigPnuOSPeer
        -- fsmStFailComputePhysicalFwUpgrade:OobPollSasExpanderActivateStatus
        -- fsmStFailComputePhysicalFwUpgrade:OobPollSasExpanderBootImgActivateStatus
        -- fsmStFailComputePhysicalFwUpgrade:OobPollSasExpanderUpdateStatus
        -- fsmStFailComputePhysicalFwUpgrade:OobSasExpanderBootImgActivate
        -- fsmStFailComputePhysicalFwUpgrade:OobSasExpanderImgActivate
        -- fsmStFailComputePhysicalFwUpgrade:OobSasExpanderImgUpdate
        -- fsmStFailComputePhysicalFwUpgrade:OobStorageInventory
        -- fsmStFailComputePhysicalFwUpgrade:PnuOSCatalog
        -- fsmStFailComputePhysicalFwUpgrade:PnuOSConfig
        -- fsmStFailComputePhysicalFwUpgrade:PnuOSIdent
        -- fsmStFailComputePhysicalFwUpgrade:PnuOSInventory
        -- fsmStFailComputePhysicalFwUpgrade:PnuOSPolicy
        -- fsmStFailComputePhysicalFwUpgrade:PnuOSSelfTest
        -- fsmStFailComputePhysicalFwUpgrade:PnuOSUnloadDrivers
        -- fsmStFailComputePhysicalFwUpgrade:PnuOSValidate
        -- fsmStFailComputePhysicalFwUpgrade:PollBiosActivateStatus
        -- fsmStFailComputePhysicalFwUpgrade:PollBiosUpdateStatus
        -- fsmStFailComputePhysicalFwUpgrade:PollBoardCtrlPowerCycle
        -- fsmStFailComputePhysicalFwUpgrade:PollBoardCtrlUpdateStatus
        -- fsmStFailComputePhysicalFwUpgrade:PollClearBiosUpdateStatus
        -- fsmStFailComputePhysicalFwUpgrade:PowerCycleBoard
        -- fsmStFailComputePhysicalFwUpgrade:PowerDeployWait
        -- fsmStFailComputePhysicalFwUpgrade:PowerOn
        -- fsmStFailComputePhysicalFwUpgrade:PreSanitize
        -- fsmStFailComputePhysicalFwUpgrade:Sanitize
        -- fsmStFailComputePhysicalFwUpgrade:SasExpanderImgUpdate
        -- fsmStFailComputePhysicalFwUpgrade:Shutdown
        -- fsmStFailComputePhysicalFwUpgrade:SolRedirectDisable
        -- fsmStFailComputePhysicalFwUpgrade:SolRedirectEnable
        -- fsmStFailComputePhysicalFwUpgrade:StorageCtlrImgUpdate
        -- fsmStFailComputePhysicalFwUpgrade:SwConfigPnuOSLocal
        -- fsmStFailComputePhysicalFwUpgrade:SwConfigPnuOSPeer
        -- fsmStFailComputePhysicalFwUpgrade:SwConfigPortNivLocal
        -- fsmStFailComputePhysicalFwUpgrade:SwConfigPortNivPeer
        -- fsmStFailComputePhysicalFwUpgrade:SwUnconfigPnuOSLocal
        -- fsmStFailComputePhysicalFwUpgrade:SwUnconfigPnuOSPeer
        -- fsmStFailComputePhysicalFwUpgrade:UnconfigCimcVMedia
        -- fsmStFailComputePhysicalFwUpgrade:UnconfigExtMgmtGw
        -- fsmStFailComputePhysicalFwUpgrade:UnconfigExtMgmtRules
        -- fsmStFailComputePhysicalFwUpgrade:UnlockFirmwareImage
        -- fsmStFailComputePhysicalFwUpgrade:UpdateBiosRequest
        -- fsmStFailComputePhysicalFwUpgrade:UpdateBoardCtrlRequest
        -- fsmStFailComputePhysicalFwUpgrade:activateAdaptorNwFwLocal
        -- fsmStFailComputePhysicalFwUpgrade:activateAdaptorNwFwPeer
        -- fsmStFailComputePhysicalFwUpgrade:activateIBMCFw
        -- fsmStFailComputePhysicalFwUpgrade:copyRemote
        -- fsmStFailComputePhysicalFwUpgrade:downloadImages
        -- fsmStFailComputePhysicalFwUpgrade:hagPnuOSConnect
        -- fsmStFailComputePhysicalFwUpgrade:hagPnuOSDisconnect
        -- fsmStFailComputePhysicalFwUpgrade:resetIBMC
        -- fsmStFailComputePhysicalFwUpgrade:serialDebugPnuOSConnect
        -- fsmStFailComputePhysicalFwUpgrade:serialDebugPnuOSDisconnect
        -- fsmStFailComputePhysicalFwUpgrade:updateAdaptorNwFwLocal
        -- fsmStFailComputePhysicalFwUpgrade:updateAdaptorNwFwPeer
        -- fsmStFailComputePhysicalFwUpgrade:updateIBMCFw
        -- fsmStFailComputePhysicalFwUpgrade:waitForAdaptorNwFwUpdateLocal
        -- fsmStFailComputePhysicalFwUpgrade:waitForAdaptorNwFwUpdatePeer
        -- fsmStFailComputePhysicalFwUpgrade:waitForIBMCFwUpdate
        -- fsmStFailComputePhysicalCimcSessionDelete:Execute
        -- fsmStFailComputePhysicalUpdateBoardController:CheckPowerAvailability
        -- fsmStFailComputePhysicalUpdateBoardController:PollBoardCtrlPowerCycle
        -- fsmStFailComputePhysicalUpdateBoardController:PollUpdateStatus
        -- fsmStFailComputePhysicalUpdateBoardController:PowerCycleBoard
        -- fsmStFailComputePhysicalUpdateBoardController:PowerDeployWait
        -- fsmStFailComputePhysicalUpdateBoardController:PrepareForUpdate
        -- fsmStFailComputePhysicalUpdateBoardController:ServerPowerOff
        -- fsmStFailComputePhysicalUpdateBoardController:ServerPowerOn
        -- fsmStFailComputePhysicalUpdateBoardController:UpdateRequest
        -- fsmStFailComputePhysicalConfigBoard:ConfigMemoryPolicy
        -- fsmStFailComputePhysicalResetMemoryErrors:Execute
        -- fsmStFailComputePhysicalServiceInfraDeploy:NicConfigLocal
        -- fsmStFailComputePhysicalServiceInfraDeploy:NicConfigPeer
        -- fsmStFailComputePhysicalServiceInfraDeploy:SwConfigLocal
        -- fsmStFailComputePhysicalServiceInfraDeploy:SwConfigPeer
        -- fsmStFailComputePhysicalServiceInfraWithdraw:NicUnConfigLocal
        -- fsmStFailComputePhysicalServiceInfraWithdraw:NicUnConfigPeer
        -- fsmStFailComputePhysicalServiceInfraWithdraw:SwUnConfigLocal
        -- fsmStFailComputePhysicalServiceInfraWithdraw:SwUnConfigPeer
        -- fsmStFailComputePhysicalFlashController:UpdateFlashLife
        -- fsmStFailComputePhysicalEnableCimcSecureBoot:Activate
        -- fsmStFailComputePhysicalEnableCimcSecureBoot:PollUpdateStatus
        -- fsmStFailComputePhysicalEnableCimcSecureBoot:Reset
        -- fsmStFailComputePhysicalEnableCimcSecureBoot:UpdateRequest
        -- fsmStFailComputePhysicalOobStorageAdminConfig:BootHost
        -- fsmStFailComputePhysicalOobStorageAdminConfig:BootWait
        -- fsmStFailComputePhysicalOobStorageAdminConfig:CheckPowerAvailability
        -- fsmStFailComputePhysicalOobStorageAdminConfig:OobStorageConfig
        -- fsmStFailComputePhysicalOobStorageAdminConfig:OobStorageInventory
        -- fsmStFailComputePhysicalOobStorageAdminConfig:PowerDeployWait
        -- fsmStFailComputePhysicalOobStorageAdminConfig:PreSanitize
        -- fsmStFailComputePhysicalOobStorageAdminConfig:Sanitize
        -- fsmStFailComputePhysicalOobStorageAdminConfig:Shutdown
        -- fsmStFailComputePhysicalOobStorageAdminConfig:TearDownVMediaLocal
        -- fsmStFailComputePhysicalOobStorageAdminConfig:TearDownVMediaPeer
        -- fsmStFailComputePhysicalClearTPM:BiosPostCompletion
        -- fsmStFailComputePhysicalClearTPM:BladePowerOff
        -- fsmStFailComputePhysicalClearTPM:BladePowerOn
        -- fsmStFailComputePhysicalClearTPM:BootHost
        -- fsmStFailComputePhysicalClearTPM:Clear
        -- fsmStFailComputePhysicalClearTPM:PreSanitize
        -- fsmStFailComputePhysicalClearTPM:ReadSmBios
        -- fsmStFailComputePhysicalClearTPM:ReconfigBios
        -- fsmStFailComputePhysicalClearTPM:Sanitize
        -- fsmStFailComputePhysicalClearTPM:SetupVmedia
        -- fsmStFailComputePhysicalClearTPM:StopVMediaLocal
        -- fsmStFailComputePhysicalClearTPM:StopVMediaPeer
        -- fsmStFailComputePhysicalClearTPM:UnconfigVmedia
        -- fsmStFailComputePhysicalDiskZoningInventory:BootHost
        -- fsmStFailComputePhysicalDiskZoningInventory:BootWait
        -- fsmStFailComputePhysicalDiskZoningInventory:PreSanitize
        -- fsmStFailComputePhysicalDiskZoningInventory:Sanitize
        -- fsmStFailComputePhysicalDiskZoningInventory:Shutdown
        -- fsmStFailComputePhysicalDiskZoningInventory:StorageInventory
        -- fsmStFailComputePhysicalDiag:BiosPostCompletion
        -- fsmStFailComputePhysicalDiag:CheckPowerAvailability
        -- fsmStFailComputePhysicalDiag:DisableScriptableVMedia
        -- fsmStFailComputePhysicalDiag:HagConnect
        -- fsmStFailComputePhysicalDiag:HagDisconnect
        -- fsmStFailComputePhysicalDiag:LogTransfer
        -- fsmStFailComputePhysicalDiag:PnuOSIdent
        -- fsmStFailComputePhysicalDiag:PowerOn
        -- fsmStFailComputePhysicalDiag:PowerOnWait
        -- fsmStFailComputePhysicalDiag:PreSanitize
        -- fsmStFailComputePhysicalDiag:PreconfigVmediaLocal
        -- fsmStFailComputePhysicalDiag:PreconfigVmediaPeer
        -- fsmStFailComputePhysicalDiag:RunTests
        -- fsmStFailComputePhysicalDiag:Sanitize
        -- fsmStFailComputePhysicalDiag:SerialDebugConnect
        -- fsmStFailComputePhysicalDiag:SerialDebugDisconnect
        -- fsmStFailComputePhysicalDiag:SetupBootEnvironment
        -- fsmStFailComputePhysicalDiag:SetupVmediaLocal
        -- fsmStFailComputePhysicalDiag:SetupVmediaPeer
        -- fsmStFailComputePhysicalDiag:Shutdown
        -- fsmStFailComputePhysicalDiag:TearDownBootEnvironment
        -- fsmStFailComputePhysicalDiag:TeardownVmediaLocal
        -- fsmStFailComputePhysicalDiag:TeardownVmediaPeer
        -- fsmStFailComputePhysicalDiag:WaitForDebug
        -- fsmStFailComputePhysicalCimcSecurityConfig:KmipCertConfig
        -- fsmStFailComputePhysicalCimcSecurityConfig:KmipSaveCert
        -- fsmRmtErrComputePhysicalAssociate:ActivateBios
        -- fsmRmtErrComputePhysicalAssociate:AssertBypassWait
        -- fsmRmtErrComputePhysicalAssociate:BiosImgUpdate
        -- fsmRmtErrComputePhysicalAssociate:BiosPostCompletion
        -- fsmRmtErrComputePhysicalAssociate:BladePowerOff
        -- fsmRmtErrComputePhysicalAssociate:BmcConfigPnuOS
        -- fsmRmtErrComputePhysicalAssociate:BmcPreconfigPnuOSLocal
        -- fsmRmtErrComputePhysicalAssociate:BmcPreconfigPnuOSPeer
        -- fsmRmtErrComputePhysicalAssociate:BmcUnconfigPnuOS
        -- fsmRmtErrComputePhysicalAssociate:BootHost
        -- fsmRmtErrComputePhysicalAssociate:BootPnuos
        -- fsmRmtErrComputePhysicalAssociate:BootWait
        -- fsmRmtErrComputePhysicalAssociate:CalculateVlanGroupForHostOSLocal
        -- fsmRmtErrComputePhysicalAssociate:CalculateVlanGroupForHostOSPeer
        -- fsmRmtErrComputePhysicalAssociate:CheckPowerAvailability
        -- fsmRmtErrComputePhysicalAssociate:CiscoOSOpenGate
        -- fsmRmtErrComputePhysicalAssociate:ClearBiosUpdate
        -- fsmRmtErrComputePhysicalAssociate:ConfigCimcVMedia
        -- fsmRmtErrComputePhysicalAssociate:ConfigExtMgmtGw
        -- fsmRmtErrComputePhysicalAssociate:ConfigExtMgmtRules
        -- fsmRmtErrComputePhysicalAssociate:ConfigFanSpeed
        -- fsmRmtErrComputePhysicalAssociate:ConfigFlexFlash
        -- fsmRmtErrComputePhysicalAssociate:ConfigHostOsAnnotations
        -- fsmRmtErrComputePhysicalAssociate:ConfigMgmtIpRules
        -- fsmRmtErrComputePhysicalAssociate:ConfigServerIdentity
        -- fsmRmtErrComputePhysicalAssociate:ConfigSoL
        -- fsmRmtErrComputePhysicalAssociate:ConfigUserAccess
        -- fsmRmtErrComputePhysicalAssociate:ConfigUuid
        -- fsmRmtErrComputePhysicalAssociate:DeassertResetBypass
        -- fsmRmtErrComputePhysicalAssociate:DeleteCurlDownloadedImages
        -- fsmRmtErrComputePhysicalAssociate:DeleteImagesRemote
        -- fsmRmtErrComputePhysicalAssociate:GraphicsImageUpdate
        -- fsmRmtErrComputePhysicalAssociate:HbaImgUpdate
        -- fsmRmtErrComputePhysicalAssociate:HostOSConfig
        -- fsmRmtErrComputePhysicalAssociate:HostOSConnect
        -- fsmRmtErrComputePhysicalAssociate:HostOSIdent
        -- fsmRmtErrComputePhysicalAssociate:HostOSPolicy
        -- fsmRmtErrComputePhysicalAssociate:HostOSValidate
        -- fsmRmtErrComputePhysicalAssociate:LocalDiskFwUpdate
        -- fsmRmtErrComputePhysicalAssociate:MarkAdapterForReboot
        -- fsmRmtErrComputePhysicalAssociate:MswitchImgUpdate
        -- fsmRmtErrComputePhysicalAssociate:NicConfigHostOSLocal
        -- fsmRmtErrComputePhysicalAssociate:NicConfigHostOSPeer
        -- fsmRmtErrComputePhysicalAssociate:NicConfigParamsHostOSLocal
        -- fsmRmtErrComputePhysicalAssociate:NicConfigParamsHostOSPeer
        -- fsmRmtErrComputePhysicalAssociate:NicConfigPnuOSLocal
        -- fsmRmtErrComputePhysicalAssociate:NicConfigPnuOSPeer
        -- fsmRmtErrComputePhysicalAssociate:NicConfigServiceInfraLocal
        -- fsmRmtErrComputePhysicalAssociate:NicConfigServiceInfraPeer
        -- fsmRmtErrComputePhysicalAssociate:NicImgUpdate
        -- fsmRmtErrComputePhysicalAssociate:NicUnconfigPnuOSLocal
        -- fsmRmtErrComputePhysicalAssociate:NicUnconfigPnuOSPeer
        -- fsmRmtErrComputePhysicalAssociate:OobPollSasExpanderActivateStatus
        -- fsmRmtErrComputePhysicalAssociate:OobPollSasExpanderBootImgActivateStatus
        -- fsmRmtErrComputePhysicalAssociate:OobPollSasExpanderUpdateStatus
        -- fsmRmtErrComputePhysicalAssociate:OobSasExpanderBootImgActivate
        -- fsmRmtErrComputePhysicalAssociate:OobSasExpanderImgActivate
        -- fsmRmtErrComputePhysicalAssociate:OobSasExpanderImgUpdate
        -- fsmRmtErrComputePhysicalAssociate:OobStorageConfig
        -- fsmRmtErrComputePhysicalAssociate:OobStorageInventory
        -- fsmRmtErrComputePhysicalAssociate:PnuOSCatalog
        -- fsmRmtErrComputePhysicalAssociate:PnuOSConfig
        -- fsmRmtErrComputePhysicalAssociate:PnuOSIdent
        -- fsmRmtErrComputePhysicalAssociate:PnuOSInventory
        -- fsmRmtErrComputePhysicalAssociate:PnuOSLocalDiskConfig
        -- fsmRmtErrComputePhysicalAssociate:PnuOSPeripheralComponentConfig
        -- fsmRmtErrComputePhysicalAssociate:PnuOSPolicy
        -- fsmRmtErrComputePhysicalAssociate:PnuOSSelfTest
        -- fsmRmtErrComputePhysicalAssociate:PnuOSUnloadDrivers
        -- fsmRmtErrComputePhysicalAssociate:PnuOSValidate
        -- fsmRmtErrComputePhysicalAssociate:PollBiosActivateStatus
        -- fsmRmtErrComputePhysicalAssociate:PollBiosUpdateStatus
        -- fsmRmtErrComputePhysicalAssociate:PollBoardCtrlPowerCycle
        -- fsmRmtErrComputePhysicalAssociate:PollBoardCtrlUpdateStatus
        -- fsmRmtErrComputePhysicalAssociate:PollClearBiosUpdateStatus
        -- fsmRmtErrComputePhysicalAssociate:PowerCycleBoard
        -- fsmRmtErrComputePhysicalAssociate:PowerDeployWait
        -- fsmRmtErrComputePhysicalAssociate:PowerOn
        -- fsmRmtErrComputePhysicalAssociate:PowerOnPreConfig
        -- fsmRmtErrComputePhysicalAssociate:PreSanitize
        -- fsmRmtErrComputePhysicalAssociate:PrepareForBoot
        -- fsmRmtErrComputePhysicalAssociate:RestoreVdStatus
        -- fsmRmtErrComputePhysicalAssociate:Sanitize
        -- fsmRmtErrComputePhysicalAssociate:SasExpanderImgUpdate
        -- fsmRmtErrComputePhysicalAssociate:SolRedirectDisable
        -- fsmRmtErrComputePhysicalAssociate:SolRedirectEnable
        -- fsmRmtErrComputePhysicalAssociate:StorageCtlrImgUpdate
        -- fsmRmtErrComputePhysicalAssociate:SwConfigHostOSLocal
        -- fsmRmtErrComputePhysicalAssociate:SwConfigHostOSPeer
        -- fsmRmtErrComputePhysicalAssociate:SwConfigPnuOSLocal
        -- fsmRmtErrComputePhysicalAssociate:SwConfigPnuOSPeer
        -- fsmRmtErrComputePhysicalAssociate:SwConfigPortNivLocal
        -- fsmRmtErrComputePhysicalAssociate:SwConfigPortNivPeer
        -- fsmRmtErrComputePhysicalAssociate:SwConfigServiceInfraLocal
        -- fsmRmtErrComputePhysicalAssociate:SwConfigServiceInfraPeer
        -- fsmRmtErrComputePhysicalAssociate:SwUnconfigPnuOSLocal
        -- fsmRmtErrComputePhysicalAssociate:SwUnconfigPnuOSPeer
        -- fsmRmtErrComputePhysicalAssociate:SyncPowerState
        -- fsmRmtErrComputePhysicalAssociate:UnconfigCimcVMedia
        -- fsmRmtErrComputePhysicalAssociate:UnconfigExtMgmtGw
        -- fsmRmtErrComputePhysicalAssociate:UnconfigExtMgmtRules
        -- fsmRmtErrComputePhysicalAssociate:UnlockFirmwareImage
        -- fsmRmtErrComputePhysicalAssociate:UpdateBiosRequest
        -- fsmRmtErrComputePhysicalAssociate:UpdateBoardCtrlRequest
        -- fsmRmtErrComputePhysicalAssociate:VerifyFcZoneConfig
        -- fsmRmtErrComputePhysicalAssociate:activateAdaptorNwFwLocal
        -- fsmRmtErrComputePhysicalAssociate:activateAdaptorNwFwPeer
        -- fsmRmtErrComputePhysicalAssociate:activateIBMCFw
        -- fsmRmtErrComputePhysicalAssociate:copyRemote
        -- fsmRmtErrComputePhysicalAssociate:downloadImages
        -- fsmRmtErrComputePhysicalAssociate:hagHostOSConnect
        -- fsmRmtErrComputePhysicalAssociate:hagPnuOSConnect
        -- fsmRmtErrComputePhysicalAssociate:hagPnuOSDisconnect
        -- fsmRmtErrComputePhysicalAssociate:resetIBMC
        -- fsmRmtErrComputePhysicalAssociate:serialDebugPnuOSConnect
        -- fsmRmtErrComputePhysicalAssociate:serialDebugPnuOSDisconnect
        -- fsmRmtErrComputePhysicalAssociate:updateAdaptorNwFwLocal
        -- fsmRmtErrComputePhysicalAssociate:updateAdaptorNwFwPeer
        -- fsmRmtErrComputePhysicalAssociate:updateIBMCFw
        -- fsmRmtErrComputePhysicalAssociate:waitForAdaptorNwFwUpdateLocal
        -- fsmRmtErrComputePhysicalAssociate:waitForAdaptorNwFwUpdatePeer
        -- fsmRmtErrComputePhysicalAssociate:waitForIBMCFwUpdate
        -- fsmRmtErrComputePhysicalDisassociate:BiosPostCompletion
        -- fsmRmtErrComputePhysicalDisassociate:BmcConfigPnuOS
        -- fsmRmtErrComputePhysicalDisassociate:BmcPreconfigPnuOSLocal
        -- fsmRmtErrComputePhysicalDisassociate:BmcPreconfigPnuOSPeer
        -- fsmRmtErrComputePhysicalDisassociate:BmcUnconfigPnuOS
        -- fsmRmtErrComputePhysicalDisassociate:BootPnuos
        -- fsmRmtErrComputePhysicalDisassociate:BootWait
        -- fsmRmtErrComputePhysicalDisassociate:CheckPowerAvailability
        -- fsmRmtErrComputePhysicalDisassociate:ConfigBios
        -- fsmRmtErrComputePhysicalDisassociate:ConfigFlexFlashScrub
        -- fsmRmtErrComputePhysicalDisassociate:ConfigKvmMgmtDefaultSetting
        -- fsmRmtErrComputePhysicalDisassociate:ConfigUserAccess
        -- fsmRmtErrComputePhysicalDisassociate:DeassertResetBypass
        -- fsmRmtErrComputePhysicalDisassociate:HandlePooling
        -- fsmRmtErrComputePhysicalDisassociate:NicConfigPnuOSLocal
        -- fsmRmtErrComputePhysicalDisassociate:NicConfigPnuOSPeer
        -- fsmRmtErrComputePhysicalDisassociate:NicUnconfigHostOSLocal
        -- fsmRmtErrComputePhysicalDisassociate:NicUnconfigHostOSPeer
        -- fsmRmtErrComputePhysicalDisassociate:NicUnconfigPnuOSLocal
        -- fsmRmtErrComputePhysicalDisassociate:NicUnconfigPnuOSPeer
        -- fsmRmtErrComputePhysicalDisassociate:NicUnconfigServiceInfraLocal
        -- fsmRmtErrComputePhysicalDisassociate:NicUnconfigServiceInfraPeer
        -- fsmRmtErrComputePhysicalDisassociate:OobDiskScrub
        -- fsmRmtErrComputePhysicalDisassociate:PnuOSCatalog
        -- fsmRmtErrComputePhysicalDisassociate:PnuOSIdent
        -- fsmRmtErrComputePhysicalDisassociate:PnuOSPolicy
        -- fsmRmtErrComputePhysicalDisassociate:PnuOSScrub
        -- fsmRmtErrComputePhysicalDisassociate:PnuOSSelfTest
        -- fsmRmtErrComputePhysicalDisassociate:PnuOSUnconfig
        -- fsmRmtErrComputePhysicalDisassociate:PnuOSValidate
        -- fsmRmtErrComputePhysicalDisassociate:PowerDeployWait
        -- fsmRmtErrComputePhysicalDisassociate:PowerOn
        -- fsmRmtErrComputePhysicalDisassociate:PreSanitize
        -- fsmRmtErrComputePhysicalDisassociate:ResetSecureBootConfig
        -- fsmRmtErrComputePhysicalDisassociate:Sanitize
        -- fsmRmtErrComputePhysicalDisassociate:Shutdown
        -- fsmRmtErrComputePhysicalDisassociate:SolRedirectDisable
        -- fsmRmtErrComputePhysicalDisassociate:SolRedirectEnable
        -- fsmRmtErrComputePhysicalDisassociate:SwConfigPnuOSLocal
        -- fsmRmtErrComputePhysicalDisassociate:SwConfigPnuOSPeer
        -- fsmRmtErrComputePhysicalDisassociate:SwConfigPortNivLocal
        -- fsmRmtErrComputePhysicalDisassociate:SwConfigPortNivPeer
        -- fsmRmtErrComputePhysicalDisassociate:SwUnconfigHostOSLocal
        -- fsmRmtErrComputePhysicalDisassociate:SwUnconfigHostOSPeer
        -- fsmRmtErrComputePhysicalDisassociate:SwUnconfigPnuOSLocal
        -- fsmRmtErrComputePhysicalDisassociate:SwUnconfigPnuOSPeer
        -- fsmRmtErrComputePhysicalDisassociate:UnconfigBios
        -- fsmRmtErrComputePhysicalDisassociate:UnconfigCimcVMedia
        -- fsmRmtErrComputePhysicalDisassociate:UnconfigExtMgmtGw
        -- fsmRmtErrComputePhysicalDisassociate:UnconfigExtMgmtRules
        -- fsmRmtErrComputePhysicalDisassociate:UnconfigFlexFlash
        -- fsmRmtErrComputePhysicalDisassociate:UnconfigServerIdentity
        -- fsmRmtErrComputePhysicalDisassociate:UnconfigSoL
        -- fsmRmtErrComputePhysicalDisassociate:UnconfigUuid
        -- fsmRmtErrComputePhysicalDisassociate:VerifyFcZoneConfig
        -- fsmRmtErrComputePhysicalDisassociate:hagPnuOSConnect
        -- fsmRmtErrComputePhysicalDisassociate:hagPnuOSDisconnect
        -- fsmRmtErrComputePhysicalDisassociate:serialDebugPnuOSConnect
        -- fsmRmtErrComputePhysicalDisassociate:serialDebugPnuOSDisconnect
        -- fsmRmtErrComputePhysicalPowerCap:Config
        -- fsmRmtErrComputePhysicalDecommission:CleanupCIMC
        -- fsmRmtErrComputePhysicalDecommission:CleanupPortConfigLocal
        -- fsmRmtErrComputePhysicalDecommission:CleanupPortConfigPeer
        -- fsmRmtErrComputePhysicalDecommission:Execute
        -- fsmRmtErrComputePhysicalDecommission:PrecleanupPortConfig
        -- fsmRmtErrComputePhysicalDecommission:StopVMediaLocal
        -- fsmRmtErrComputePhysicalDecommission:StopVMediaPeer
        -- fsmRmtErrComputePhysicalDecommission:UnconfigExtMgmtGw
        -- fsmRmtErrComputePhysicalDecommission:UnconfigExtMgmtRules
        -- fsmRmtErrComputePhysicalSoftShutdown:Execute
        -- fsmRmtErrComputePhysicalHardShutdown:Execute
        -- fsmRmtErrComputePhysicalTurnup:CheckPowerAvailability
        -- fsmRmtErrComputePhysicalTurnup:Execute
        -- fsmRmtErrComputePhysicalTurnup:PowerDeployWait
        -- fsmRmtErrComputePhysicalPowercycle:CheckPowerAvailability
        -- fsmRmtErrComputePhysicalPowercycle:Execute
        -- fsmRmtErrComputePhysicalPowercycle:PowerDeployWait
        -- fsmRmtErrComputePhysicalPowercycle:PreSanitize
        -- fsmRmtErrComputePhysicalPowercycle:Sanitize
        -- fsmRmtErrComputePhysicalHardreset:CheckPowerAvailability
        -- fsmRmtErrComputePhysicalHardreset:Execute
        -- fsmRmtErrComputePhysicalHardreset:PowerDeployWait
        -- fsmRmtErrComputePhysicalHardreset:PreSanitize
        -- fsmRmtErrComputePhysicalHardreset:Sanitize
        -- fsmRmtErrComputePhysicalSoftreset:CheckPowerAvailability
        -- fsmRmtErrComputePhysicalSoftreset:Execute
        -- fsmRmtErrComputePhysicalSoftreset:PowerDeployWait
        -- fsmRmtErrComputePhysicalSoftreset:PreSanitize
        -- fsmRmtErrComputePhysicalSoftreset:Sanitize
        -- fsmRmtErrComputePhysicalSwConnUpd:A
        -- fsmRmtErrComputePhysicalSwConnUpd:B
        -- fsmRmtErrComputePhysicalBiosRecovery:CheckPowerAvailability
        -- fsmRmtErrComputePhysicalBiosRecovery:Cleanup
        -- fsmRmtErrComputePhysicalBiosRecovery:PowerDeployWait
        -- fsmRmtErrComputePhysicalBiosRecovery:PreSanitize
        -- fsmRmtErrComputePhysicalBiosRecovery:Reset
        -- fsmRmtErrComputePhysicalBiosRecovery:Sanitize
        -- fsmRmtErrComputePhysicalBiosRecovery:SetupVmediaLocal
        -- fsmRmtErrComputePhysicalBiosRecovery:SetupVmediaPeer
        -- fsmRmtErrComputePhysicalBiosRecovery:Shutdown
        -- fsmRmtErrComputePhysicalBiosRecovery:Start
        -- fsmRmtErrComputePhysicalBiosRecovery:StopVMediaLocal
        -- fsmRmtErrComputePhysicalBiosRecovery:StopVMediaPeer
        -- fsmRmtErrComputePhysicalBiosRecovery:TeardownVmediaLocal
        -- fsmRmtErrComputePhysicalBiosRecovery:TeardownVmediaPeer
        -- fsmRmtErrComputePhysicalBiosRecovery:Wait
        -- fsmRmtErrComputePhysicalCmosReset:BladePowerOn
        -- fsmRmtErrComputePhysicalCmosReset:CheckPowerAvailability
        -- fsmRmtErrComputePhysicalCmosReset:Execute
        -- fsmRmtErrComputePhysicalCmosReset:PowerDeployWait
        -- fsmRmtErrComputePhysicalCmosReset:PreSanitize
        -- fsmRmtErrComputePhysicalCmosReset:ReconfigBios
        -- fsmRmtErrComputePhysicalCmosReset:ReconfigUuid
        -- fsmRmtErrComputePhysicalCmosReset:Sanitize
        -- fsmRmtErrComputePhysicalResetBmc:Execute
        -- fsmRmtErrComputePhysicalUpdateExtUsers:Deploy
        -- fsmRmtErrComputePhysicalUpdateAdaptor:CheckPowerAvailability
        -- fsmRmtErrComputePhysicalUpdateAdaptor:PollUpdateStatusLocal
        -- fsmRmtErrComputePhysicalUpdateAdaptor:PollUpdateStatusPeer
        -- fsmRmtErrComputePhysicalUpdateAdaptor:PowerDeployWait
        -- fsmRmtErrComputePhysicalUpdateAdaptor:PowerOff
        -- fsmRmtErrComputePhysicalUpdateAdaptor:PowerOn
        -- fsmRmtErrComputePhysicalUpdateAdaptor:UpdateRequestLocal
        -- fsmRmtErrComputePhysicalUpdateAdaptor:UpdateRequestPeer
        -- fsmRmtErrComputePhysicalActivateAdaptor:ActivateLocal
        -- fsmRmtErrComputePhysicalActivateAdaptor:ActivatePeer
        -- fsmRmtErrComputePhysicalActivateAdaptor:AssertBypassWait
        -- fsmRmtErrComputePhysicalActivateAdaptor:CheckPowerAvailability
        -- fsmRmtErrComputePhysicalActivateAdaptor:DeassertResetBypass
        -- fsmRmtErrComputePhysicalActivateAdaptor:PowerDeployWait
        -- fsmRmtErrComputePhysicalActivateAdaptor:PowerOn
        -- fsmRmtErrComputePhysicalActivateAdaptor:Reset
        -- fsmRmtErrComputePhysicalConfigSoL:Execute
        -- fsmRmtErrComputePhysicalUnconfigSoL:Execute
        -- fsmRmtErrComputePhysicalDiagnosticInterrupt:Execute
        -- fsmRmtErrComputePhysicalResetKvm:Execute
        -- fsmRmtErrComputePhysicalUpdateBIOS:Clear
        -- fsmRmtErrComputePhysicalUpdateBIOS:PollClearStatus
        -- fsmRmtErrComputePhysicalUpdateBIOS:PollUpdateStatus
        -- fsmRmtErrComputePhysicalUpdateBIOS:UpdateRequest
        -- fsmRmtErrComputePhysicalActivateBIOS:Activate
        -- fsmRmtErrComputePhysicalActivateBIOS:CheckPowerAvailability
        -- fsmRmtErrComputePhysicalActivateBIOS:Clear
        -- fsmRmtErrComputePhysicalActivateBIOS:PollActivateStatus
        -- fsmRmtErrComputePhysicalActivateBIOS:PollClearStatus
        -- fsmRmtErrComputePhysicalActivateBIOS:PowerDeployWait
        -- fsmRmtErrComputePhysicalActivateBIOS:PowerOff
        -- fsmRmtErrComputePhysicalActivateBIOS:PowerOn
        -- fsmRmtErrComputePhysicalActivateBIOS:UpdateTokens
        -- fsmRmtErrComputePhysicalResetIpmi:Execute
        -- fsmRmtErrComputePhysicalFwUpgrade:ActivateBios
        -- fsmRmtErrComputePhysicalFwUpgrade:AssertBypassWait
        -- fsmRmtErrComputePhysicalFwUpgrade:BiosImgUpdate
        -- fsmRmtErrComputePhysicalFwUpgrade:BiosPostCompletion
        -- fsmRmtErrComputePhysicalFwUpgrade:BladePowerOff
        -- fsmRmtErrComputePhysicalFwUpgrade:BmcConfigPnuOS
        -- fsmRmtErrComputePhysicalFwUpgrade:BmcPreconfigPnuOSLocal
        -- fsmRmtErrComputePhysicalFwUpgrade:BmcPreconfigPnuOSPeer
        -- fsmRmtErrComputePhysicalFwUpgrade:BmcUnconfigPnuOS
        -- fsmRmtErrComputePhysicalFwUpgrade:BootPnuos
        -- fsmRmtErrComputePhysicalFwUpgrade:BootWait
        -- fsmRmtErrComputePhysicalFwUpgrade:CheckPowerAvailability
        -- fsmRmtErrComputePhysicalFwUpgrade:CiscoOSOpenGate
        -- fsmRmtErrComputePhysicalFwUpgrade:ClearBiosUpdate
        -- fsmRmtErrComputePhysicalFwUpgrade:DeassertResetBypass
        -- fsmRmtErrComputePhysicalFwUpgrade:DeleteCurlDownloadedImages
        -- fsmRmtErrComputePhysicalFwUpgrade:DeleteImagesRemote
        -- fsmRmtErrComputePhysicalFwUpgrade:GraphicsImageUpdate
        -- fsmRmtErrComputePhysicalFwUpgrade:HbaImgUpdate
        -- fsmRmtErrComputePhysicalFwUpgrade:LocalDiskFwUpdate
        -- fsmRmtErrComputePhysicalFwUpgrade:MswitchImgUpdate
        -- fsmRmtErrComputePhysicalFwUpgrade:NicConfigPnuOSLocal
        -- fsmRmtErrComputePhysicalFwUpgrade:NicConfigPnuOSPeer
        -- fsmRmtErrComputePhysicalFwUpgrade:NicImgUpdate
        -- fsmRmtErrComputePhysicalFwUpgrade:NicUnconfigPnuOSLocal
        -- fsmRmtErrComputePhysicalFwUpgrade:NicUnconfigPnuOSPeer
        -- fsmRmtErrComputePhysicalFwUpgrade:OobPollSasExpanderActivateStatus
        -- fsmRmtErrComputePhysicalFwUpgrade:OobPollSasExpanderBootImgActivateStatus
        -- fsmRmtErrComputePhysicalFwUpgrade:OobPollSasExpanderUpdateStatus
        -- fsmRmtErrComputePhysicalFwUpgrade:OobSasExpanderBootImgActivate
        -- fsmRmtErrComputePhysicalFwUpgrade:OobSasExpanderImgActivate
        -- fsmRmtErrComputePhysicalFwUpgrade:OobSasExpanderImgUpdate
        -- fsmRmtErrComputePhysicalFwUpgrade:OobStorageInventory
        -- fsmRmtErrComputePhysicalFwUpgrade:PnuOSCatalog
        -- fsmRmtErrComputePhysicalFwUpgrade:PnuOSConfig
        -- fsmRmtErrComputePhysicalFwUpgrade:PnuOSIdent
        -- fsmRmtErrComputePhysicalFwUpgrade:PnuOSInventory
        -- fsmRmtErrComputePhysicalFwUpgrade:PnuOSPolicy
        -- fsmRmtErrComputePhysicalFwUpgrade:PnuOSSelfTest
        -- fsmRmtErrComputePhysicalFwUpgrade:PnuOSUnloadDrivers
        -- fsmRmtErrComputePhysicalFwUpgrade:PnuOSValidate
        -- fsmRmtErrComputePhysicalFwUpgrade:PollBiosActivateStatus
        -- fsmRmtErrComputePhysicalFwUpgrade:PollBiosUpdateStatus
        -- fsmRmtErrComputePhysicalFwUpgrade:PollBoardCtrlPowerCycle
        -- fsmRmtErrComputePhysicalFwUpgrade:PollBoardCtrlUpdateStatus
        -- fsmRmtErrComputePhysicalFwUpgrade:PollClearBiosUpdateStatus
        -- fsmRmtErrComputePhysicalFwUpgrade:PowerCycleBoard
        -- fsmRmtErrComputePhysicalFwUpgrade:PowerDeployWait
        -- fsmRmtErrComputePhysicalFwUpgrade:PowerOn
        -- fsmRmtErrComputePhysicalFwUpgrade:PreSanitize
        -- fsmRmtErrComputePhysicalFwUpgrade:Sanitize
        -- fsmRmtErrComputePhysicalFwUpgrade:SasExpanderImgUpdate
        -- fsmRmtErrComputePhysicalFwUpgrade:Shutdown
        -- fsmRmtErrComputePhysicalFwUpgrade:SolRedirectDisable
        -- fsmRmtErrComputePhysicalFwUpgrade:SolRedirectEnable
        -- fsmRmtErrComputePhysicalFwUpgrade:StorageCtlrImgUpdate
        -- fsmRmtErrComputePhysicalFwUpgrade:SwConfigPnuOSLocal
        -- fsmRmtErrComputePhysicalFwUpgrade:SwConfigPnuOSPeer
        -- fsmRmtErrComputePhysicalFwUpgrade:SwConfigPortNivLocal
        -- fsmRmtErrComputePhysicalFwUpgrade:SwConfigPortNivPeer
        -- fsmRmtErrComputePhysicalFwUpgrade:SwUnconfigPnuOSLocal
        -- fsmRmtErrComputePhysicalFwUpgrade:SwUnconfigPnuOSPeer
        -- fsmRmtErrComputePhysicalFwUpgrade:UnconfigCimcVMedia
        -- fsmRmtErrComputePhysicalFwUpgrade:UnconfigExtMgmtGw
        -- fsmRmtErrComputePhysicalFwUpgrade:UnconfigExtMgmtRules
        -- fsmRmtErrComputePhysicalFwUpgrade:UnlockFirmwareImage
        -- fsmRmtErrComputePhysicalFwUpgrade:UpdateBiosRequest
        -- fsmRmtErrComputePhysicalFwUpgrade:UpdateBoardCtrlRequest
        -- fsmRmtErrComputePhysicalFwUpgrade:activateAdaptorNwFwLocal
        -- fsmRmtErrComputePhysicalFwUpgrade:activateAdaptorNwFwPeer
        -- fsmRmtErrComputePhysicalFwUpgrade:activateIBMCFw
        -- fsmRmtErrComputePhysicalFwUpgrade:copyRemote
        -- fsmRmtErrComputePhysicalFwUpgrade:downloadImages
        -- fsmRmtErrComputePhysicalFwUpgrade:hagPnuOSConnect
        -- fsmRmtErrComputePhysicalFwUpgrade:hagPnuOSDisconnect
        -- fsmRmtErrComputePhysicalFwUpgrade:resetIBMC
        -- fsmRmtErrComputePhysicalFwUpgrade:serialDebugPnuOSConnect
        -- fsmRmtErrComputePhysicalFwUpgrade:serialDebugPnuOSDisconnect
        -- fsmRmtErrComputePhysicalFwUpgrade:updateAdaptorNwFwLocal
        -- fsmRmtErrComputePhysicalFwUpgrade:updateAdaptorNwFwPeer
        -- fsmRmtErrComputePhysicalFwUpgrade:updateIBMCFw
        -- fsmRmtErrComputePhysicalFwUpgrade:waitForAdaptorNwFwUpdateLocal
        -- fsmRmtErrComputePhysicalFwUpgrade:waitForAdaptorNwFwUpdatePeer
        -- fsmRmtErrComputePhysicalFwUpgrade:waitForIBMCFwUpdate
        -- fsmRmtErrComputePhysicalCimcSessionDelete:Execute
        -- fsmRmtErrComputePhysicalUpdateBoardController:CheckPowerAvailability
        -- fsmRmtErrComputePhysicalUpdateBoardController:PollBoardCtrlPowerCycle
        -- fsmRmtErrComputePhysicalUpdateBoardController:PollUpdateStatus
        -- fsmRmtErrComputePhysicalUpdateBoardController:PowerCycleBoard
        -- fsmRmtErrComputePhysicalUpdateBoardController:PowerDeployWait
        -- fsmRmtErrComputePhysicalUpdateBoardController:PrepareForUpdate
        -- fsmRmtErrComputePhysicalUpdateBoardController:ServerPowerOff
        -- fsmRmtErrComputePhysicalUpdateBoardController:ServerPowerOn
        -- fsmRmtErrComputePhysicalUpdateBoardController:UpdateRequest
        -- fsmRmtErrComputePhysicalConfigBoard:ConfigMemoryPolicy
        -- fsmRmtErrComputePhysicalResetMemoryErrors:Execute
        -- fsmRmtErrComputePhysicalServiceInfraDeploy:NicConfigLocal
        -- fsmRmtErrComputePhysicalServiceInfraDeploy:NicConfigPeer
        -- fsmRmtErrComputePhysicalServiceInfraDeploy:SwConfigLocal
        -- fsmRmtErrComputePhysicalServiceInfraDeploy:SwConfigPeer
        -- fsmRmtErrComputePhysicalServiceInfraWithdraw:NicUnConfigLocal
        -- fsmRmtErrComputePhysicalServiceInfraWithdraw:NicUnConfigPeer
        -- fsmRmtErrComputePhysicalServiceInfraWithdraw:SwUnConfigLocal
        -- fsmRmtErrComputePhysicalServiceInfraWithdraw:SwUnConfigPeer
        -- fsmRmtErrComputePhysicalFlashController:UpdateFlashLife
        -- fsmRmtErrComputePhysicalEnableCimcSecureBoot:Activate
        -- fsmRmtErrComputePhysicalEnableCimcSecureBoot:PollUpdateStatus
        -- fsmRmtErrComputePhysicalEnableCimcSecureBoot:Reset
        -- fsmRmtErrComputePhysicalEnableCimcSecureBoot:UpdateRequest
        -- fsmRmtErrComputePhysicalOobStorageAdminConfig:BootHost
        -- fsmRmtErrComputePhysicalOobStorageAdminConfig:BootWait
        -- fsmRmtErrComputePhysicalOobStorageAdminConfig:CheckPowerAvailability
        -- fsmRmtErrComputePhysicalOobStorageAdminConfig:OobStorageConfig
        -- fsmRmtErrComputePhysicalOobStorageAdminConfig:OobStorageInventory
        -- fsmRmtErrComputePhysicalOobStorageAdminConfig:PowerDeployWait
        -- fsmRmtErrComputePhysicalOobStorageAdminConfig:PreSanitize
        -- fsmRmtErrComputePhysicalOobStorageAdminConfig:Sanitize
        -- fsmRmtErrComputePhysicalOobStorageAdminConfig:Shutdown
        -- fsmRmtErrComputePhysicalOobStorageAdminConfig:TearDownVMediaLocal
        -- fsmRmtErrComputePhysicalOobStorageAdminConfig:TearDownVMediaPeer
        -- fsmRmtErrComputePhysicalClearTPM:BiosPostCompletion
        -- fsmRmtErrComputePhysicalClearTPM:BladePowerOff
        -- fsmRmtErrComputePhysicalClearTPM:BladePowerOn
        -- fsmRmtErrComputePhysicalClearTPM:BootHost
        -- fsmRmtErrComputePhysicalClearTPM:Clear
        -- fsmRmtErrComputePhysicalClearTPM:PreSanitize
        -- fsmRmtErrComputePhysicalClearTPM:ReadSmBios
        -- fsmRmtErrComputePhysicalClearTPM:ReconfigBios
        -- fsmRmtErrComputePhysicalClearTPM:Sanitize
        -- fsmRmtErrComputePhysicalClearTPM:SetupVmedia
        -- fsmRmtErrComputePhysicalClearTPM:StopVMediaLocal
        -- fsmRmtErrComputePhysicalClearTPM:StopVMediaPeer
        -- fsmRmtErrComputePhysicalClearTPM:UnconfigVmedia
        -- fsmRmtErrComputePhysicalDiskZoningInventory:BootHost
        -- fsmRmtErrComputePhysicalDiskZoningInventory:BootWait
        -- fsmRmtErrComputePhysicalDiskZoningInventory:PreSanitize
        -- fsmRmtErrComputePhysicalDiskZoningInventory:Sanitize
        -- fsmRmtErrComputePhysicalDiskZoningInventory:Shutdown
        -- fsmRmtErrComputePhysicalDiskZoningInventory:StorageInventory
        -- fsmRmtErrComputePhysicalDiag:BiosPostCompletion
        -- fsmRmtErrComputePhysicalDiag:CheckPowerAvailability
        -- fsmRmtErrComputePhysicalDiag:DisableScriptableVMedia
        -- fsmRmtErrComputePhysicalDiag:HagConnect
        -- fsmRmtErrComputePhysicalDiag:HagDisconnect
        -- fsmRmtErrComputePhysicalDiag:LogTransfer
        -- fsmRmtErrComputePhysicalDiag:PnuOSIdent
        -- fsmRmtErrComputePhysicalDiag:PowerOn
        -- fsmRmtErrComputePhysicalDiag:PowerOnWait
        -- fsmRmtErrComputePhysicalDiag:PreSanitize
        -- fsmRmtErrComputePhysicalDiag:PreconfigVmediaLocal
        -- fsmRmtErrComputePhysicalDiag:PreconfigVmediaPeer
        -- fsmRmtErrComputePhysicalDiag:RunTests
        -- fsmRmtErrComputePhysicalDiag:Sanitize
        -- fsmRmtErrComputePhysicalDiag:SerialDebugConnect
        -- fsmRmtErrComputePhysicalDiag:SerialDebugDisconnect
        -- fsmRmtErrComputePhysicalDiag:SetupBootEnvironment
        -- fsmRmtErrComputePhysicalDiag:SetupVmediaLocal
        -- fsmRmtErrComputePhysicalDiag:SetupVmediaPeer
        -- fsmRmtErrComputePhysicalDiag:Shutdown
        -- fsmRmtErrComputePhysicalDiag:TearDownBootEnvironment
        -- fsmRmtErrComputePhysicalDiag:TeardownVmediaLocal
        -- fsmRmtErrComputePhysicalDiag:TeardownVmediaPeer
        -- fsmRmtErrComputePhysicalDiag:WaitForDebug
        -- fsmRmtErrComputePhysicalCimcSecurityConfig:KmipCertConfig
        -- fsmRmtErrComputePhysicalCimcSecurityConfig:KmipSaveCert
        -- fsmFailComputePhysicalAssociate
        -- fsmFailComputePhysicalDisassociate
        -- fsmFailComputePhysicalPowerCap
        -- fsmFailComputePhysicalDecommission
        -- fsmFailComputePhysicalSoftShutdown
        -- fsmFailComputePhysicalHardShutdown
        -- fsmFailComputePhysicalTurnup
        -- fsmFailComputePhysicalPowercycle
        -- fsmFailComputePhysicalHardreset
        -- fsmFailComputePhysicalSoftreset
        -- fsmFailComputePhysicalSwConnUpd
        -- fsmFailComputePhysicalBiosRecovery
        -- fsmFailComputePhysicalCmosReset
        -- fsmFailComputePhysicalResetBmc
        -- fsmFailComputePhysicalUpdateExtUsers
        -- fsmFailComputePhysicalUpdateAdaptor
        -- fsmFailComputePhysicalActivateAdaptor
        -- fsmFailComputePhysicalConfigSoL
        -- fsmFailComputePhysicalUnconfigSoL
        -- fsmFailComputePhysicalDiagnosticInterrupt
        -- fsmFailComputePhysicalResetKvm
        -- fsmFailComputePhysicalUpdateBIOS
        -- fsmFailComputePhysicalActivateBIOS
        -- fsmFailComputePhysicalResetIpmi
        -- fsmFailComputePhysicalFwUpgrade
        -- fsmFailComputePhysicalCimcSessionDelete
        -- fsmFailComputePhysicalUpdateBoardController
        -- fsmFailComputePhysicalConfigBoard
        -- fsmFailComputePhysicalResetMemoryErrors
        -- fsmFailComputePhysicalServiceInfraDeploy
        -- fsmFailComputePhysicalServiceInfraWithdraw
        -- fsmFailComputePhysicalFlashController
        -- fsmFailComputePhysicalEnableCimcSecureBoot
        -- fsmFailComputePhysicalOobStorageAdminConfig
        -- fsmFailComputePhysicalClearTPM
        -- fsmFailComputePhysicalDiskZoningInventory
        -- fsmFailComputePhysicalDiag
        -- fsmFailComputePhysicalCimcSecurityConfig

-- flowctrl:Item
    -- fabric/lan/flowctrl/policy-[name]
        -- fltFlowctrlItemFlowctrlconfig

-- fabric:LanPinGroup
    -- fabric/lan/lan-pin-group-[name]
        -- fltFabricLanPinGroupEmpty

-- fabric:PIoEp
        -- fltFabricPIoEpErrorMisconfigured

-- ident:IdentRequest
    -- metaverse/metasys/IdentQ-[id]
        -- fsmStFailIdentIdentRequestUpdateIdent:Execute
        -- fsmRmtErrIdentIdentRequestUpdateIdent:Execute
        -- fsmFailIdentIdentRequestUpdateIdent

-- ippool:Pool
    -- fabric/lan/network-sets/ip-pool-[name]
    -- org-[name]/ip-pool-[name]
        -- fltIppoolPoolEmpty

-- mgmt:BackupPolicyConfig
    -- sys/bkup-policy-cfg
        -- fltMgmtBackupPolicyConfigConfiguration backup outdated

-- ether:SwitchIntFIo
    -- sys/chassis-[id]/slot-[id]/[type]/port-[portId]
    -- sys/fex-[id]/slot-[id]/[type]/port-[portId]
    -- sys/chassis-[id]/shared-io-module/[type]/port-[portId]
    -- sys/chassis-[id]/slot-[id]/shared-io-module/[type]/port-[portId]
    -- sys/switch-[id]/slot-[id]/[type]/port-[portId]
    -- sys/chassis-[id]/sw-slot-[id]/[type]/port-[portId]
        -- fltEtherSwitchIntFIoSatellite-connection-absent
        -- fltEtherSwitchIntFIoSatellite-wiring-problem
        -- fltEtherSwitchIntFIoSatellite-wiring-numbers-unexpected

-- gmeta:Holder
    -- gmeta/category-[category]-provider-[provider]
        -- fsmStFailGmetaHolderInventory:BeginInventory
        -- fsmStFailGmetaHolderInventory:CheckInventoryStatus
        -- fsmStFailGmetaHolderInventory:EndInventory
        -- fsmStFailGmetaHolderInventory:FullInventory
        -- fsmStFailGmetaHolderInventory:ReportFaultInventory
        -- fsmStFailGmetaHolderInventory:ReportOrgInventory
        -- fsmStFailGmetaHolderInventory:ReportPhysicalInventory
        -- fsmStFailGmetaHolderInventory:ReportStorageInventory
        -- fsmRmtErrGmetaHolderInventory:BeginInventory
        -- fsmRmtErrGmetaHolderInventory:CheckInventoryStatus
        -- fsmRmtErrGmetaHolderInventory:EndInventory
        -- fsmRmtErrGmetaHolderInventory:FullInventory
        -- fsmRmtErrGmetaHolderInventory:ReportFaultInventory
        -- fsmRmtErrGmetaHolderInventory:ReportOrgInventory
        -- fsmRmtErrGmetaHolderInventory:ReportPhysicalInventory
        -- fsmRmtErrGmetaHolderInventory:ReportStorageInventory
        -- fsmFailGmetaHolderInventory

-- pki:Ep
    -- sys/pki-ext
        -- fsmStFailPkiEpUpdateEp:PostSetKeyRingLocal
        -- fsmStFailPkiEpUpdateEp:PostSetKeyRingPeer
        -- fsmStFailPkiEpUpdateEp:SetKeyRingLocal
        -- fsmStFailPkiEpUpdateEp:SetKeyRingPeer
        -- fsmRmtErrPkiEpUpdateEp:PostSetKeyRingLocal
        -- fsmRmtErrPkiEpUpdateEp:PostSetKeyRingPeer
        -- fsmRmtErrPkiEpUpdateEp:SetKeyRingLocal
        -- fsmRmtErrPkiEpUpdateEp:SetKeyRingPeer
        -- fsmFailPkiEpUpdateEp

-- sysdebug:Core
    -- sys/corefiles/file-[name]|[switchId]
        -- fsmStFailSysdebugCoreDownload:CopyPrimary
        -- fsmStFailSysdebugCoreDownload:CopySub
        -- fsmStFailSysdebugCoreDownload:DeletePrimary
        -- fsmStFailSysdebugCoreDownload:DeleteSub
        -- fsmRmtErrSysdebugCoreDownload:CopyPrimary
        -- fsmRmtErrSysdebugCoreDownload:CopySub
        -- fsmRmtErrSysdebugCoreDownload:DeletePrimary
        -- fsmRmtErrSysdebugCoreDownload:DeleteSub
        -- fsmFailSysdebugCoreDownload

-- mgmt:Importer
    -- sys/import-config-[hostname]
        -- fsmStFailMgmtImporterImport:config
        -- fsmStFailMgmtImporterImport:downloadLocal
        -- fsmStFailMgmtImporterImport:reportResults
        -- fsmRmtErrMgmtImporterImport:config
        -- fsmRmtErrMgmtImporterImport:downloadLocal
        -- fsmRmtErrMgmtImporterImport:reportResults
        -- fsmFailMgmtImporterImport

-- fabric:VnetEpSyncEp
    -- extpol/reg/providers/prov-[type]/syncEp
        -- fsmStFailFabricVnetEpSyncEpPushVnetEpDeletion:Sync
        -- fsmRmtErrFabricVnetEpSyncEpPushVnetEpDeletion:Sync
        -- fsmFailFabricVnetEpSyncEpPushVnetEpDeletion

-- sw:Vlan
    -- sys/chassis-[id]/blade-[slotId]/fabric-[switchId]/vc-[id]/vlan-[id]
    -- sys/chassis-[id]/blade-[slotId]/fabric-[switchId]/vc-[id]/vlan-[id]
    -- sys/rack-unit-[id]/fabric-[switchId]/vc-[id]/vlan-[id]
    -- sys/chassis-[id]/cartridge-[slotId]/server-[serverInstanceId]/fabric-[switchId]/vc-[id]/vlan-[id]
    -- sys/chassis-[id]/cartridge-[slotId]/server-[serverInstanceId]/fabric-[switchId]/vc-[id]/vlan-[id]
    -- sys/chassis-[id]/fabric-[switchId]/vc-[id]/vlan-[id]
    -- sys/fex-[id]/fabric-[switchId]/vc-[id]/vlan-[id]
    -- sys/chassis-[id]/blade-[slotId]/adaptor-[id]/mgmt/fabric-[switchId]/vc-[id]/vlan-[id]
    -- sys/rack-unit-[id]/adaptor-[id]/mgmt/fabric-[switchId]/vc-[id]/vlan-[id]
    -- sys/chassis-[id]/cartridge-[slotId]/server-[serverInstanceId]/adaptor-[id]/mgmt/fabric-[switchId]/vc-[id]/vlan-[id]
    -- sys/chassis-[id]/cartridge-[slotId]/server-[serverInstanceId]/adaptor-[id]/mgmt/fabric-[switchId]/vc-[id]/vlan-[id]
    -- sys/chassis-[id]/blade-[slotId]/ext-board-[id]/boardController/mgmt/fabric-[switchId]/vc-[id]/vlan-[id]
    -- sys/rack-unit-[id]/ext-board-[id]/boardController/mgmt/fabric-[switchId]/vc-[id]/vlan-[id]
    -- sys/chassis-[id]/cartridge-[slotId]/server-[serverInstanceId]/ext-board-[id]/boardController/mgmt/fabric-[switchId]/vc-[id]/vlan-[id]
    -- sys/chassis-[id]/blade-[slotId]/boardController/mgmt/fabric-[switchId]/vc-[id]/vlan-[id]
    -- sys/rack-unit-[id]/boardController/mgmt/fabric-[switchId]/vc-[id]/vlan-[id]
    -- sys/chassis-[id]/cartridge-[slotId]/server-[serverInstanceId]/boardController/mgmt/fabric-[switchId]/vc-[id]/vlan-[id]
    -- sys/chassis-[id]/boardController/mgmt/fabric-[switchId]/vc-[id]/vlan-[id]
    -- sys/chassis-[id]/slot-[id]/boardController/mgmt/fabric-[switchId]/vc-[id]/vlan-[id]
    -- sys/chassis-[id]/blade-[slotId]/ext-board-[id]/mgmt/fabric-[switchId]/vc-[id]/vlan-[id]
    -- sys/rack-unit-[id]/ext-board-[id]/mgmt/fabric-[switchId]/vc-[id]/vlan-[id]
    -- sys/chassis-[id]/cartridge-[slotId]/server-[serverInstanceId]/ext-board-[id]/mgmt/fabric-[switchId]/vc-[id]/vlan-[id]
    -- sys/chassis-[id]/blade-[slotId]/mgmt/fabric-[switchId]/vc-[id]/vlan-[id]
    -- sys/rack-unit-[id]/mgmt/fabric-[switchId]/vc-[id]/vlan-[id]
    -- sys/chassis-[id]/cartridge-[slotId]/server-[serverInstanceId]/mgmt/fabric-[switchId]/vc-[id]/vlan-[id]
    -- sys/chassis-[id]/cartridge-[slotId]/server-[serverInstanceId]/mgmt/fabric-[switchId]/vc-[id]/vlan-[id]
    -- sys/chassis-[id]/mgmt/fabric-[switchId]/vc-[id]/vlan-[id]
    -- sys/fex-[id]/mgmt/fabric-[switchId]/vc-[id]/vlan-[id]
    -- sys/chassis-[id]/slot-[id]/mgmt/fabric-[switchId]/vc-[id]/vlan-[id]
    -- sys/fex-[id]/slot-[id]/mgmt/fabric-[switchId]/vc-[id]/vlan-[id]
    -- sys/chassis-[id]/shared-io-module/mgmt/fabric-[switchId]/vc-[id]/vlan-[id]
    -- sys/chassis-[id]/slot-[id]/shared-io-module/mgmt/fabric-[switchId]/vc-[id]/vlan-[id]
    -- sys/chassis-[id]/sw-slot-[id]/mgmt/fabric-[switchId]/vc-[id]/vlan-[id]
    -- sys/chassis-[id]/slot-[id]/mgmt/fabric-[switchId]/vc-[id]/vlan-[id]
    -- sys/switch-[id]/mgmt/fabric-[switchId]/vc-[id]/vlan-[id]
    -- sys/chassis-[id]/blade-[slotId]/board/storage-[type]-[id]/mgmt/fabric-[switchId]/vc-[id]/vlan-[id]
    -- sys/rack-unit-[id]/board/storage-[type]-[id]/mgmt/fabric-[switchId]/vc-[id]/vlan-[id]
    -- sys/chassis-[id]/cartridge-[slotId]/server-[serverInstanceId]/board/storage-[type]-[id]/mgmt/fabric-[switchId]/vc-[id]/vlan-[id]
    -- sys/chassis-[id]/storage-[type]-[id]/mgmt/fabric-[switchId]/vc-[id]/vlan-[id]
    -- sys/chassis-[id]/blade-[slotId]/board/storage-[type]-[id]/disk-[id]/mgmt/fabric-[switchId]/vc-[id]/vlan-[id]
    -- sys/rack-unit-[id]/board/storage-[type]-[id]/disk-[id]/mgmt/fabric-[switchId]/vc-[id]/vlan-[id]
    -- sys/chassis-[id]/cartridge-[slotId]/server-[serverInstanceId]/board/storage-[type]-[id]/disk-[id]/mgmt/fabric-[switchId]/vc-[id]/vlan-[id]
    -- sys/chassis-[id]/storage-[type]-[id]/disk-[id]/mgmt/fabric-[switchId]/vc-[id]/vlan-[id]
    -- sys/chassis-[id]/blade-[slotId]/enc-[id]/disk-[id]/mgmt/fabric-[switchId]/vc-[id]/vlan-[id]
    -- sys/rack-unit-[id]/enc-[id]/disk-[id]/mgmt/fabric-[switchId]/vc-[id]/vlan-[id]
    -- sys/chassis-[id]/cartridge-[slotId]/server-[serverInstanceId]/enc-[id]/disk-[id]/mgmt/fabric-[switchId]/vc-[id]/vlan-[id]
    -- sys/chassis-[id]/enc-[id]/disk-[id]/mgmt/fabric-[switchId]/vc-[id]/vlan-[id]
    -- sys/chassis-[id]/blade-[slotId]/board/storage-[type]-[id]/enc-[id]/disk-[id]/mgmt/fabric-[switchId]/vc-[id]/vlan-[id]
    -- sys/rack-unit-[id]/board/storage-[type]-[id]/enc-[id]/disk-[id]/mgmt/fabric-[switchId]/vc-[id]/vlan-[id]
    -- sys/chassis-[id]/cartridge-[slotId]/server-[serverInstanceId]/board/storage-[type]-[id]/enc-[id]/disk-[id]/mgmt/fabric-[switchId]/vc-[id]/vlan-[id]
    -- sys/chassis-[id]/storage-[type]-[id]/enc-[id]/disk-[id]/mgmt/fabric-[switchId]/vc-[id]/vlan-[id]
    -- sys/chassis-[id]/blade-[slotId]/board/sas-expander-[id]/mgmt/fabric-[switchId]/vc-[id]/vlan-[id]
    -- sys/rack-unit-[id]/board/sas-expander-[id]/mgmt/fabric-[switchId]/vc-[id]/vlan-[id]
    -- sys/chassis-[id]/cartridge-[slotId]/server-[serverInstanceId]/board/sas-expander-[id]/mgmt/fabric-[switchId]/vc-[id]/vlan-[id]
    -- sys/chassis-[id]/sas-expander-[id]/mgmt/fabric-[switchId]/vc-[id]/vlan-[id]
    -- sys/mgmt/fabric-[switchId]/vc-[id]/vlan-[id]
    -- sys/chassis-[id]/blade-[slotId]/fabric-[switchId]/path-[id]/vc-[id]/vlan-[id]
    -- sys/chassis-[id]/blade-[slotId]/fabric-[switchId]/path-[id]/vc-[id]/vlan-[id]
    -- sys/rack-unit-[id]/fabric-[switchId]/path-[id]/vc-[id]/vlan-[id]
    -- sys/chassis-[id]/cartridge-[slotId]/server-[serverInstanceId]/fabric-[switchId]/path-[id]/vc-[id]/vlan-[id]
    -- sys/chassis-[id]/cartridge-[slotId]/server-[serverInstanceId]/fabric-[switchId]/path-[id]/vc-[id]/vlan-[id]
    -- sys/chassis-[id]/fabric-[switchId]/path-[id]/vc-[id]/vlan-[id]
    -- sys/fex-[id]/fabric-[switchId]/path-[id]/vc-[id]/vlan-[id]
    -- sys/chassis-[id]/blade-[slotId]/adaptor-[id]/mgmt/fabric-[switchId]/path-[id]/vc-[id]/vlan-[id]
    -- sys/rack-unit-[id]/adaptor-[id]/mgmt/fabric-[switchId]/path-[id]/vc-[id]/vlan-[id]
    -- sys/chassis-[id]/cartridge-[slotId]/server-[serverInstanceId]/adaptor-[id]/mgmt/fabric-[switchId]/path-[id]/vc-[id]/vlan-[id]
    -- sys/chassis-[id]/cartridge-[slotId]/server-[serverInstanceId]/adaptor-[id]/mgmt/fabric-[switchId]/path-[id]/vc-[id]/vlan-[id]
    -- sys/chassis-[id]/blade-[slotId]/ext-board-[id]/boardController/mgmt/fabric-[switchId]/path-[id]/vc-[id]/vlan-[id]
    -- sys/rack-unit-[id]/ext-board-[id]/boardController/mgmt/fabric-[switchId]/path-[id]/vc-[id]/vlan-[id]
    -- sys/chassis-[id]/cartridge-[slotId]/server-[serverInstanceId]/ext-board-[id]/boardController/mgmt/fabric-[switchId]/path-[id]/vc-[id]/vlan-[id]
    -- sys/chassis-[id]/blade-[slotId]/boardController/mgmt/fabric-[switchId]/path-[id]/vc-[id]/vlan-[id]
    -- sys/rack-unit-[id]/boardController/mgmt/fabric-[switchId]/path-[id]/vc-[id]/vlan-[id]
    -- sys/chassis-[id]/cartridge-[slotId]/server-[serverInstanceId]/boardController/mgmt/fabric-[switchId]/path-[id]/vc-[id]/vlan-[id]
    -- sys/chassis-[id]/boardController/mgmt/fabric-[switchId]/path-[id]/vc-[id]/vlan-[id]
    -- sys/chassis-[id]/slot-[id]/boardController/mgmt/fabric-[switchId]/path-[id]/vc-[id]/vlan-[id]
    -- sys/chassis-[id]/blade-[slotId]/ext-board-[id]/mgmt/fabric-[switchId]/path-[id]/vc-[id]/vlan-[id]
    -- sys/rack-unit-[id]/ext-board-[id]/mgmt/fabric-[switchId]/path-[id]/vc-[id]/vlan-[id]
    -- sys/chassis-[id]/cartridge-[slotId]/server-[serverInstanceId]/ext-board-[id]/mgmt/fabric-[switchId]/path-[id]/vc-[id]/vlan-[id]
    -- sys/chassis-[id]/blade-[slotId]/mgmt/fabric-[switchId]/path-[id]/vc-[id]/vlan-[id]
    -- sys/rack-unit-[id]/mgmt/fabric-[switchId]/path-[id]/vc-[id]/vlan-[id]
    -- sys/chassis-[id]/cartridge-[slotId]/server-[serverInstanceId]/mgmt/fabric-[switchId]/path-[id]/vc-[id]/vlan-[id]
    -- sys/chassis-[id]/cartridge-[slotId]/server-[serverInstanceId]/mgmt/fabric-[switchId]/path-[id]/vc-[id]/vlan-[id]
    -- sys/chassis-[id]/mgmt/fabric-[switchId]/path-[id]/vc-[id]/vlan-[id]
    -- sys/fex-[id]/mgmt/fabric-[switchId]/path-[id]/vc-[id]/vlan-[id]
    -- sys/chassis-[id]/slot-[id]/mgmt/fabric-[switchId]/path-[id]/vc-[id]/vlan-[id]
    -- sys/fex-[id]/slot-[id]/mgmt/fabric-[switchId]/path-[id]/vc-[id]/vlan-[id]
    -- sys/chassis-[id]/shared-io-module/mgmt/fabric-[switchId]/path-[id]/vc-[id]/vlan-[id]
    -- sys/chassis-[id]/slot-[id]/shared-io-module/mgmt/fabric-[switchId]/path-[id]/vc-[id]/vlan-[id]
    -- sys/chassis-[id]/sw-slot-[id]/mgmt/fabric-[switchId]/path-[id]/vc-[id]/vlan-[id]
    -- sys/chassis-[id]/slot-[id]/mgmt/fabric-[switchId]/path-[id]/vc-[id]/vlan-[id]
    -- sys/switch-[id]/mgmt/fabric-[switchId]/path-[id]/vc-[id]/vlan-[id]
    -- sys/chassis-[id]/blade-[slotId]/board/storage-[type]-[id]/mgmt/fabric-[switchId]/path-[id]/vc-[id]/vlan-[id]
    -- sys/rack-unit-[id]/board/storage-[type]-[id]/mgmt/fabric-[switchId]/path-[id]/vc-[id]/vlan-[id]
    -- sys/chassis-[id]/cartridge-[slotId]/server-[serverInstanceId]/board/storage-[type]-[id]/mgmt/fabric-[switchId]/path-[id]/vc-[id]/vlan-[id]
    -- sys/chassis-[id]/storage-[type]-[id]/mgmt/fabric-[switchId]/path-[id]/vc-[id]/vlan-[id]
    -- sys/chassis-[id]/blade-[slotId]/board/storage-[type]-[id]/disk-[id]/mgmt/fabric-[switchId]/path-[id]/vc-[id]/vlan-[id]
    -- sys/rack-unit-[id]/board/storage-[type]-[id]/disk-[id]/mgmt/fabric-[switchId]/path-[id]/vc-[id]/vlan-[id]
    -- sys/chassis-[id]/cartridge-[slotId]/server-[serverInstanceId]/board/storage-[type]-[id]/disk-[id]/mgmt/fabric-[switchId]/path-[id]/vc-[id]/vlan-[id]
    -- sys/chassis-[id]/storage-[type]-[id]/disk-[id]/mgmt/fabric-[switchId]/path-[id]/vc-[id]/vlan-[id]
    -- sys/chassis-[id]/blade-[slotId]/enc-[id]/disk-[id]/mgmt/fabric-[switchId]/path-[id]/vc-[id]/vlan-[id]
    -- sys/rack-unit-[id]/enc-[id]/disk-[id]/mgmt/fabric-[switchId]/path-[id]/vc-[id]/vlan-[id]
    -- sys/chassis-[id]/cartridge-[slotId]/server-[serverInstanceId]/enc-[id]/disk-[id]/mgmt/fabric-[switchId]/path-[id]/vc-[id]/vlan-[id]
    -- sys/chassis-[id]/enc-[id]/disk-[id]/mgmt/fabric-[switchId]/path-[id]/vc-[id]/vlan-[id]
    -- sys/chassis-[id]/blade-[slotId]/board/storage-[type]-[id]/enc-[id]/disk-[id]/mgmt/fabric-[switchId]/path-[id]/vc-[id]/vlan-[id]
    -- sys/rack-unit-[id]/board/storage-[type]-[id]/enc-[id]/disk-[id]/mgmt/fabric-[switchId]/path-[id]/vc-[id]/vlan-[id]
    -- sys/chassis-[id]/cartridge-[slotId]/server-[serverInstanceId]/board/storage-[type]-[id]/enc-[id]/disk-[id]/mgmt/fabric-[switchId]/path-[id]/vc-[id]/vlan-[id]
    -- sys/chassis-[id]/storage-[type]-[id]/enc-[id]/disk-[id]/mgmt/fabric-[switchId]/path-[id]/vc-[id]/vlan-[id]
    -- sys/chassis-[id]/blade-[slotId]/board/sas-expander-[id]/mgmt/fabric-[switchId]/path-[id]/vc-[id]/vlan-[id]
    -- sys/rack-unit-[id]/board/sas-expander-[id]/mgmt/fabric-[switchId]/path-[id]/vc-[id]/vlan-[id]
    -- sys/chassis-[id]/cartridge-[slotId]/server-[serverInstanceId]/board/sas-expander-[id]/mgmt/fabric-[switchId]/path-[id]/vc-[id]/vlan-[id]
    -- sys/chassis-[id]/sas-expander-[id]/mgmt/fabric-[switchId]/path-[id]/vc-[id]/vlan-[id]
    -- sys/mgmt/fabric-[switchId]/path-[id]/vc-[id]/vlan-[id]
    -- sys/switch-[id]/ethlanflowmon/vc-[id]/vlan-[id]
    -- sys/switch-[id]/lanmon-eth/mon-[name]/vc-[id]/vlan-[id]
    -- sys/switch-[id]/sanmon-fc/mon-[name]/vc-[id]/vlan-[id]
    -- sys/switch-[id]/border-eth/ethestc-ep-slot-[slotId]port-[portId]/vlan-[id]
    -- sys/switch-[id]/access-eth/slot-[slotId]-aggr-port-[aggrPortId]/ethestc-ep-slot-[slotId]port-[portId]/vlan-[id]
    -- sys/switch-[id]/border-eth/slot-[slotId]-aggr-port-[aggrPortId]/ethestc-ep-slot-[slotId]port-[portId]/vlan-[id]
    -- sys/switch-[id]/lanmon-eth/mon-[name]/slot-[slotId]-aggr-port-[aggrPortId]/ethestc-ep-slot-[slotId]port-[portId]/vlan-[id]
    -- sys/switch-[id]/sanmon-fc/mon-[name]/slot-[slotId]-aggr-port-[aggrPortId]/ethestc-ep-slot-[slotId]port-[portId]/vlan-[id]
    -- sys/switch-[id]/border-fc/slot-[slotId]-aggr-port-[aggrPortId]/ethestc-ep-slot-[slotId]port-[portId]/vlan-[id]
    -- sys/switch-[id]/phys/slot-[slotId]-aggr-port-[aggrPortId]/ethestc-ep-slot-[slotId]port-[portId]/vlan-[id]
    -- sys/switch-[id]/border-eth/pc-[portId]/vlan-[id]
    -- sys/switch-[id]/lanmon-eth/mon-[name]/pc-[portId]/vlan-[id]
    -- sys/switch-[id]/border-eth/vlan-[id]
    -- sys/switch-[id]/border-eth/ep-slot-[slotId]port-[portId]/vlan-[id]
    -- sys/switch-[id]/access-eth/slot-[slotId]-aggr-port-[aggrPortId]/ep-slot-[slotId]port-[portId]/vlan-[id]
    -- sys/switch-[id]/border-eth/slot-[slotId]-aggr-port-[aggrPortId]/ep-slot-[slotId]port-[portId]/vlan-[id]
    -- sys/switch-[id]/lanmon-eth/mon-[name]/slot-[slotId]-aggr-port-[aggrPortId]/ep-slot-[slotId]port-[portId]/vlan-[id]
    -- sys/switch-[id]/sanmon-fc/mon-[name]/slot-[slotId]-aggr-port-[aggrPortId]/ep-slot-[slotId]port-[portId]/vlan-[id]
    -- sys/switch-[id]/border-fc/slot-[slotId]-aggr-port-[aggrPortId]/ep-slot-[slotId]port-[portId]/vlan-[id]
    -- sys/switch-[id]/phys/slot-[slotId]-aggr-port-[aggrPortId]/ep-slot-[slotId]port-[portId]/vlan-[id]
    -- sys/switch-[id]/border-eth/pc-[portId]/vlan-[id]
    -- sys/switch-[id]/lanmon-eth/mon-[name]/pc-[portId]/vlan-[id]
    -- sys/switch-[id]/lanmon-eth/mon-[name]/vlan-[id]
    -- sys/switch-[id]/sanmon-fc/mon-[name]/vlan-[id]
    -- sys/switch-[id]/border-fc/vlan-[id]
    -- sys/switch-[id]/border-fc/fcoeestc-ep-slot-[slotId]port-[portId]/vlan-[id]
    -- sys/switch-[id]/access-eth/slot-[slotId]-aggr-port-[aggrPortId]/fcoeestc-ep-slot-[slotId]port-[portId]/vlan-[id]
    -- sys/switch-[id]/border-eth/slot-[slotId]-aggr-port-[aggrPortId]/fcoeestc-ep-slot-[slotId]port-[portId]/vlan-[id]
    -- sys/switch-[id]/lanmon-eth/mon-[name]/slot-[slotId]-aggr-port-[aggrPortId]/fcoeestc-ep-slot-[slotId]port-[portId]/vlan-[id]
    -- sys/switch-[id]/sanmon-fc/mon-[name]/slot-[slotId]-aggr-port-[aggrPortId]/fcoeestc-ep-slot-[slotId]port-[portId]/vlan-[id]
    -- sys/switch-[id]/border-fc/slot-[slotId]-aggr-port-[aggrPortId]/fcoeestc-ep-slot-[slotId]port-[portId]/vlan-[id]
    -- sys/switch-[id]/phys/slot-[slotId]-aggr-port-[aggrPortId]/fcoeestc-ep-slot-[slotId]port-[portId]/vlan-[id]
    -- sys/switch-[id]/border-fc/fcoesan-ep-slot-[slotId]port-[portId]/vlan-[id]
    -- sys/switch-[id]/access-eth/slot-[slotId]-aggr-port-[aggrPortId]/fcoesan-ep-slot-[slotId]port-[portId]/vlan-[id]
    -- sys/switch-[id]/border-eth/slot-[slotId]-aggr-port-[aggrPortId]/fcoesan-ep-slot-[slotId]port-[portId]/vlan-[id]
    -- sys/switch-[id]/lanmon-eth/mon-[name]/slot-[slotId]-aggr-port-[aggrPortId]/fcoesan-ep-slot-[slotId]port-[portId]/vlan-[id]
    -- sys/switch-[id]/sanmon-fc/mon-[name]/slot-[slotId]-aggr-port-[aggrPortId]/fcoesan-ep-slot-[slotId]port-[portId]/vlan-[id]
    -- sys/switch-[id]/border-fc/slot-[slotId]-aggr-port-[aggrPortId]/fcoesan-ep-slot-[slotId]port-[portId]/vlan-[id]
    -- sys/switch-[id]/phys/slot-[slotId]-aggr-port-[aggrPortId]/fcoesan-ep-slot-[slotId]port-[portId]/vlan-[id]
    -- sys/switch-[id]/sanmon-fc/mon-[name]/fcoesan-pc-[portId]/vlan-[id]
    -- sys/switch-[id]/border-fc/fcoesan-pc-[portId]/vlan-[id]
    -- sys/switch-[id]/ethlanflowmon/flowexporter-netflow-[name]/vlan-[id]
    -- fabric/lan/profiles/vnic-[name]/vlan-[id]
    -- sys/chassis-[id]/vnic-[name]/vlan-[id]
    -- fabric/lan/profiles/vnic-[name]/vlan-[id]
        -- fltSwVlanExtrasecondaryvlansperprimary

-- aaa:Realm
    -- sys/
        -- fsmStFailAaaRealmUpdateRealm:SetRealmLocal
        -- fsmStFailAaaRealmUpdateRealm:SetRealmPeer
        -- fsmRmtErrAaaRealmUpdateRealm:SetRealmLocal
        -- fsmRmtErrAaaRealmUpdateRealm:SetRealmPeer
        -- fsmFailAaaRealmUpdateRealm

-- dcx:VIf
    -- sys/chassis-[id]/blade-[slotId]/adaptor-[id]/ext-eth-[id]/vif-[id]
    -- sys/rack-unit-[id]/adaptor-[id]/ext-eth-[id]/vif-[id]
    -- sys/chassis-[id]/cartridge-[slotId]/server-[serverInstanceId]/adaptor-[id]/ext-eth-[id]/vif-[id]
    -- sys/chassis-[id]/cartridge-[slotId]/server-[serverInstanceId]/adaptor-[id]/ext-eth-[id]/vif-[id]
    -- sys/chassis-[id]/blade-[slotId]/adaptor-[id]/pc-[portId]/vif-[id]
    -- sys/rack-unit-[id]/adaptor-[id]/pc-[portId]/vif-[id]
    -- sys/chassis-[id]/cartridge-[slotId]/server-[serverInstanceId]/adaptor-[id]/pc-[portId]/vif-[id]
    -- sys/chassis-[id]/cartridge-[slotId]/server-[serverInstanceId]/adaptor-[id]/pc-[portId]/vif-[id]
    -- sys/chassis-[id]/blade-[slotId]/fabric-[switchId]/pc-[portId]/vif-[id]
    -- sys/chassis-[id]/blade-[slotId]/fabric-[switchId]/pc-[portId]/vif-[id]
    -- sys/rack-unit-[id]/fabric-[switchId]/pc-[portId]/vif-[id]
    -- sys/chassis-[id]/cartridge-[slotId]/server-[serverInstanceId]/fabric-[switchId]/pc-[portId]/vif-[id]
    -- sys/chassis-[id]/cartridge-[slotId]/server-[serverInstanceId]/fabric-[switchId]/pc-[portId]/vif-[id]
    -- sys/chassis-[id]/fabric-[switchId]/pc-[portId]/vif-[id]
    -- sys/fex-[id]/fabric-[switchId]/pc-[portId]/vif-[id]
    -- sys/chassis-[id]/blade-[slotId]/adaptor-[id]/mgmt/fabric-[switchId]/pc-[portId]/vif-[id]
    -- sys/rack-unit-[id]/adaptor-[id]/mgmt/fabric-[switchId]/pc-[portId]/vif-[id]
    -- sys/chassis-[id]/cartridge-[slotId]/server-[serverInstanceId]/adaptor-[id]/mgmt/fabric-[switchId]/pc-[portId]/vif-[id]
    -- sys/chassis-[id]/cartridge-[slotId]/server-[serverInstanceId]/adaptor-[id]/mgmt/fabric-[switchId]/pc-[portId]/vif-[id]
    -- sys/chassis-[id]/blade-[slotId]/ext-board-[id]/boardController/mgmt/fabric-[switchId]/pc-[portId]/vif-[id]
    -- sys/rack-unit-[id]/ext-board-[id]/boardController/mgmt/fabric-[switchId]/pc-[portId]/vif-[id]
    -- sys/chassis-[id]/cartridge-[slotId]/server-[serverInstanceId]/ext-board-[id]/boardController/mgmt/fabric-[switchId]/pc-[portId]/vif-[id]
    -- sys/chassis-[id]/blade-[slotId]/boardController/mgmt/fabric-[switchId]/pc-[portId]/vif-[id]
    -- sys/rack-unit-[id]/boardController/mgmt/fabric-[switchId]/pc-[portId]/vif-[id]
    -- sys/chassis-[id]/cartridge-[slotId]/server-[serverInstanceId]/boardController/mgmt/fabric-[switchId]/pc-[portId]/vif-[id]
    -- sys/chassis-[id]/boardController/mgmt/fabric-[switchId]/pc-[portId]/vif-[id]
    -- sys/chassis-[id]/slot-[id]/boardController/mgmt/fabric-[switchId]/pc-[portId]/vif-[id]
    -- sys/chassis-[id]/blade-[slotId]/ext-board-[id]/mgmt/fabric-[switchId]/pc-[portId]/vif-[id]
    -- sys/rack-unit-[id]/ext-board-[id]/mgmt/fabric-[switchId]/pc-[portId]/vif-[id]
    -- sys/chassis-[id]/cartridge-[slotId]/server-[serverInstanceId]/ext-board-[id]/mgmt/fabric-[switchId]/pc-[portId]/vif-[id]
    -- sys/chassis-[id]/blade-[slotId]/mgmt/fabric-[switchId]/pc-[portId]/vif-[id]
    -- sys/rack-unit-[id]/mgmt/fabric-[switchId]/pc-[portId]/vif-[id]
    -- sys/chassis-[id]/cartridge-[slotId]/server-[serverInstanceId]/mgmt/fabric-[switchId]/pc-[portId]/vif-[id]
    -- sys/chassis-[id]/cartridge-[slotId]/server-[serverInstanceId]/mgmt/fabric-[switchId]/pc-[portId]/vif-[id]
    -- sys/chassis-[id]/mgmt/fabric-[switchId]/pc-[portId]/vif-[id]
    -- sys/fex-[id]/mgmt/fabric-[switchId]/pc-[portId]/vif-[id]
    -- sys/chassis-[id]/slot-[id]/mgmt/fabric-[switchId]/pc-[portId]/vif-[id]
    -- sys/fex-[id]/slot-[id]/mgmt/fabric-[switchId]/pc-[portId]/vif-[id]
    -- sys/chassis-[id]/shared-io-module/mgmt/fabric-[switchId]/pc-[portId]/vif-[id]
    -- sys/chassis-[id]/slot-[id]/shared-io-module/mgmt/fabric-[switchId]/pc-[portId]/vif-[id]
    -- sys/chassis-[id]/sw-slot-[id]/mgmt/fabric-[switchId]/pc-[portId]/vif-[id]
    -- sys/chassis-[id]/slot-[id]/mgmt/fabric-[switchId]/pc-[portId]/vif-[id]
    -- sys/switch-[id]/mgmt/fabric-[switchId]/pc-[portId]/vif-[id]
    -- sys/chassis-[id]/blade-[slotId]/board/storage-[type]-[id]/mgmt/fabric-[switchId]/pc-[portId]/vif-[id]
    -- sys/rack-unit-[id]/board/storage-[type]-[id]/mgmt/fabric-[switchId]/pc-[portId]/vif-[id]
    -- sys/chassis-[id]/cartridge-[slotId]/server-[serverInstanceId]/board/storage-[type]-[id]/mgmt/fabric-[switchId]/pc-[portId]/vif-[id]
    -- sys/chassis-[id]/storage-[type]-[id]/mgmt/fabric-[switchId]/pc-[portId]/vif-[id]
    -- sys/chassis-[id]/blade-[slotId]/board/storage-[type]-[id]/disk-[id]/mgmt/fabric-[switchId]/pc-[portId]/vif-[id]
    -- sys/rack-unit-[id]/board/storage-[type]-[id]/disk-[id]/mgmt/fabric-[switchId]/pc-[portId]/vif-[id]
    -- sys/chassis-[id]/cartridge-[slotId]/server-[serverInstanceId]/board/storage-[type]-[id]/disk-[id]/mgmt/fabric-[switchId]/pc-[portId]/vif-[id]
    -- sys/chassis-[id]/storage-[type]-[id]/disk-[id]/mgmt/fabric-[switchId]/pc-[portId]/vif-[id]
    -- sys/chassis-[id]/blade-[slotId]/enc-[id]/disk-[id]/mgmt/fabric-[switchId]/pc-[portId]/vif-[id]
    -- sys/rack-unit-[id]/enc-[id]/disk-[id]/mgmt/fabric-[switchId]/pc-[portId]/vif-[id]
    -- sys/chassis-[id]/cartridge-[slotId]/server-[serverInstanceId]/enc-[id]/disk-[id]/mgmt/fabric-[switchId]/pc-[portId]/vif-[id]
    -- sys/chassis-[id]/enc-[id]/disk-[id]/mgmt/fabric-[switchId]/pc-[portId]/vif-[id]
    -- sys/chassis-[id]/blade-[slotId]/board/storage-[type]-[id]/enc-[id]/disk-[id]/mgmt/fabric-[switchId]/pc-[portId]/vif-[id]
    -- sys/rack-unit-[id]/board/storage-[type]-[id]/enc-[id]/disk-[id]/mgmt/fabric-[switchId]/pc-[portId]/vif-[id]
    -- sys/chassis-[id]/cartridge-[slotId]/server-[serverInstanceId]/board/storage-[type]-[id]/enc-[id]/disk-[id]/mgmt/fabric-[switchId]/pc-[portId]/vif-[id]
    -- sys/chassis-[id]/storage-[type]-[id]/enc-[id]/disk-[id]/mgmt/fabric-[switchId]/pc-[portId]/vif-[id]
    -- sys/chassis-[id]/blade-[slotId]/board/sas-expander-[id]/mgmt/fabric-[switchId]/pc-[portId]/vif-[id]
    -- sys/rack-unit-[id]/board/sas-expander-[id]/mgmt/fabric-[switchId]/pc-[portId]/vif-[id]
    -- sys/chassis-[id]/cartridge-[slotId]/server-[serverInstanceId]/board/sas-expander-[id]/mgmt/fabric-[switchId]/pc-[portId]/vif-[id]
    -- sys/chassis-[id]/sas-expander-[id]/mgmt/fabric-[switchId]/pc-[portId]/vif-[id]
    -- sys/mgmt/fabric-[switchId]/pc-[portId]/vif-[id]
    -- sys/chassis-[id]/blade-[slotId]/adaptor-[id]/host-eth-[id]/fcoe/vif-[id]
    -- sys/rack-unit-[id]/adaptor-[id]/host-eth-[id]/fcoe/vif-[id]
    -- sys/chassis-[id]/cartridge-[slotId]/server-[serverInstanceId]/adaptor-[id]/host-eth-[id]/fcoe/vif-[id]
    -- sys/chassis-[id]/cartridge-[slotId]/server-[serverInstanceId]/adaptor-[id]/host-eth-[id]/fcoe/vif-[id]
    -- sys/chassis-[id]/blade-[slotId]/adaptor-[id]/host-fc-[id]/fcoe/vif-[id]
    -- sys/rack-unit-[id]/adaptor-[id]/host-fc-[id]/fcoe/vif-[id]
    -- sys/chassis-[id]/cartridge-[slotId]/server-[serverInstanceId]/adaptor-[id]/host-fc-[id]/fcoe/vif-[id]
    -- sys/chassis-[id]/cartridge-[slotId]/server-[serverInstanceId]/adaptor-[id]/host-fc-[id]/fcoe/vif-[id]
    -- sys/chassis-[id]/blade-[slotId]/adaptor-[id]/host-eth-[id]/vif-[id]
    -- sys/rack-unit-[id]/adaptor-[id]/host-eth-[id]/vif-[id]
    -- sys/chassis-[id]/cartridge-[slotId]/server-[serverInstanceId]/adaptor-[id]/host-eth-[id]/vif-[id]
    -- sys/chassis-[id]/cartridge-[slotId]/server-[serverInstanceId]/adaptor-[id]/host-eth-[id]/vif-[id]
    -- sys/chassis-[id]/blade-[slotId]/adaptor-[id]/host-fc-[id]/vif-[id]
    -- sys/rack-unit-[id]/adaptor-[id]/host-fc-[id]/vif-[id]
    -- sys/chassis-[id]/cartridge-[slotId]/server-[serverInstanceId]/adaptor-[id]/host-fc-[id]/vif-[id]
    -- sys/chassis-[id]/cartridge-[slotId]/server-[serverInstanceId]/adaptor-[id]/host-fc-[id]/vif-[id]
    -- sys/chassis-[id]/blade-[slotId]/adaptor-[id]/host-service-eth-[id]/vif-[id]
    -- sys/rack-unit-[id]/adaptor-[id]/host-service-eth-[id]/vif-[id]
    -- sys/chassis-[id]/cartridge-[slotId]/server-[serverInstanceId]/adaptor-[id]/host-service-eth-[id]/vif-[id]
    -- sys/chassis-[id]/cartridge-[slotId]/server-[serverInstanceId]/adaptor-[id]/host-service-eth-[id]/vif-[id]
        -- fltDcxVIfLinkState

-- comm:DateTime
    -- sys/svc-ext/datetime-svc
    -- org-[name]/comm-pol-[name]/datetime-svc
        -- fltCommDateTimeCommTimeZoneInvalid

-- aaa:Ep
    -- sys/
        -- fsmStFailAaaEpUpdateEp:SetEpLocal
        -- fsmStFailAaaEpUpdateEp:SetEpPeer
        -- fsmRmtErrAaaEpUpdateEp:SetEpLocal
        -- fsmRmtErrAaaEpUpdateEp:SetEpPeer
        -- fsmFailAaaEpUpdateEp

-- fabric:SanPinGroup
    -- fabric/san/san-pin-group-[name]
        -- fltFabricSanPinGroupEmpty

-- license:File
    -- sys/license/file-[scope]:[id]
        -- fltLicenseFileBadLicenseFile
        -- fltLicenseFileFileNotDeleted
        -- fsmStFailLicenseFileInstall:Local
        -- fsmStFailLicenseFileInstall:Remote
        -- fsmStFailLicenseFileClear:Local
        -- fsmStFailLicenseFileClear:Remote
        -- fsmRmtErrLicenseFileInstall:Local
        -- fsmRmtErrLicenseFileInstall:Remote
        -- fsmRmtErrLicenseFileClear:Local
        -- fsmRmtErrLicenseFileClear:Remote
        -- fsmFailLicenseFileInstall
        -- fsmFailLicenseFileClear

-- equipment:SwitchIOCard
    -- sys/chassis-[id]/sw-slot-[id]
        -- fltEquipmentSwitchIOCardRemoved
        -- fltEquipmentSwitchIOCardThermalProblem
        -- fltEquipmentSwitchIOCardThermalThresholdNonCritical
        -- fltEquipmentSwitchIOCardThermalThresholdCritical
        -- fltEquipmentSwitchIOCardThermalThresholdNonRecoverable
        -- fltEquipmentSwitchIOCardPeerDisconnected
        -- fltEquipmentSwitchIOCardIdentity
        -- fltEquipmentSwitchIOCardCpuThermalThresholdCritical
        -- fltEquipmentSwitchIOCardBackPlanePortProblem
        -- fsmStFailEquipmentSwitchIOCardEvacuate:Execute
        -- fsmStFailEquipmentSwitchIOCardResetEvacuate:Execute
        -- fsmRmtErrEquipmentSwitchIOCardEvacuate:Execute
        -- fsmRmtErrEquipmentSwitchIOCardResetEvacuate:Execute
        -- fsmFailEquipmentSwitchIOCardEvacuate
        -- fsmFailEquipmentSwitchIOCardResetEvacuate

-- fabric:MulticastPolicy
    -- org-[name]/mc-policy-[name]
        -- fltFabricMulticastPolicySameOrEmptyPeerQuerierIp

-- fabric:EthEstcPcEp
    -- fabric/eth-estc/[id]/pc-[portId]/ep-slot-[slotId]-port-[portId]
    -- fabric/server/sw-[id]/slot-[slotId]-aggr-port-[aggrPortId]/ep-slot-[slotId]-port-[portId]
    -- fabric/server/sw-[id]/pc-[portId]/slot-[slotId]-aggr-port-[aggrPortId]/ep-slot-[slotId]-port-[portId]
    -- fabric/eth-estc/[id]/slot-[slotId]-aggr-port-[aggrPortId]/ep-slot-[slotId]-port-[portId]
    -- fabric/eth-estc/[id]/pc-[portId]/slot-[slotId]-aggr-port-[aggrPortId]/ep-slot-[slotId]-port-[portId]
    -- fabric/lan/[id]/slot-[slotId]-aggr-port-[aggrPortId]/ep-slot-[slotId]-port-[portId]
    -- fabric/lan/[id]/pc-[portId]/slot-[slotId]-aggr-port-[aggrPortId]/ep-slot-[slotId]-port-[portId]
    -- fabric/lanmon/[id]/eth-mon-[name]/slot-[slotId]-aggr-port-[aggrPortId]/ep-slot-[slotId]-port-[portId]
    -- fabric/fc-estc/[id]/slot-[slotId]-aggr-port-[aggrPortId]/ep-slot-[slotId]-port-[portId]
    -- fabric/sanmon/[id]/fc-mon-[name]/slot-[slotId]-aggr-port-[aggrPortId]/ep-slot-[slotId]-port-[portId]
    -- fabric/san/[id]/slot-[slotId]-aggr-port-[aggrPortId]/ep-slot-[slotId]-port-[portId]
    -- fabric/san/[id]/fcoesanpc-[portId]/slot-[slotId]-aggr-port-[aggrPortId]/ep-slot-[slotId]-port-[portId]
        -- fltFabricEthEstcPcEpDown

-- sw:EthLanBorder
    -- sys/switch-[id]/border-eth
        -- fltSwEthLanBorderVlan-limit-exceeded
        -- fsmStFailSwEthLanBorderDeploy:UpdateConnectivity
        -- fsmStFailSwEthLanBorderDeploy:UpdateVlanGroups
        -- fsmRmtErrSwEthLanBorderDeploy:UpdateConnectivity
        -- fsmRmtErrSwEthLanBorderDeploy:UpdateVlanGroups
        -- fsmFailSwEthLanBorderDeploy

-- mgmt:KvmCertificate
    -- sys/chassis-[id]/blade-[slotId]/kvm-mgmt-policy-[name]/cert
    -- sys/rack-unit-[id]/kvm-mgmt-policy-[name]/cert
    -- sys/chassis-[id]/cartridge-[slotId]/server-[serverInstanceId]/kvm-mgmt-policy-[name]/cert
    -- org-[name]/kvm-mgmt-policy-[name]/cert
    -- sys/chassis-[id]/blade-[slotId]/adaptor-[id]/mgmt/cert
    -- sys/rack-unit-[id]/adaptor-[id]/mgmt/cert
    -- sys/chassis-[id]/cartridge-[slotId]/server-[serverInstanceId]/adaptor-[id]/mgmt/cert
    -- sys/chassis-[id]/cartridge-[slotId]/server-[serverInstanceId]/adaptor-[id]/mgmt/cert
    -- sys/chassis-[id]/blade-[slotId]/ext-board-[id]/boardController/mgmt/cert
    -- sys/rack-unit-[id]/ext-board-[id]/boardController/mgmt/cert
    -- sys/chassis-[id]/cartridge-[slotId]/server-[serverInstanceId]/ext-board-[id]/boardController/mgmt/cert
    -- sys/chassis-[id]/blade-[slotId]/boardController/mgmt/cert
    -- sys/rack-unit-[id]/boardController/mgmt/cert
    -- sys/chassis-[id]/cartridge-[slotId]/server-[serverInstanceId]/boardController/mgmt/cert
    -- sys/chassis-[id]/boardController/mgmt/cert
    -- sys/chassis-[id]/slot-[id]/boardController/mgmt/cert
    -- sys/chassis-[id]/blade-[slotId]/ext-board-[id]/mgmt/cert
    -- sys/rack-unit-[id]/ext-board-[id]/mgmt/cert
    -- sys/chassis-[id]/cartridge-[slotId]/server-[serverInstanceId]/ext-board-[id]/mgmt/cert
    -- sys/chassis-[id]/blade-[slotId]/mgmt/cert
    -- sys/rack-unit-[id]/mgmt/cert
    -- sys/chassis-[id]/cartridge-[slotId]/server-[serverInstanceId]/mgmt/cert
    -- sys/chassis-[id]/cartridge-[slotId]/server-[serverInstanceId]/mgmt/cert
    -- sys/chassis-[id]/mgmt/cert
    -- sys/fex-[id]/mgmt/cert
    -- sys/chassis-[id]/slot-[id]/mgmt/cert
    -- sys/fex-[id]/slot-[id]/mgmt/cert
    -- sys/chassis-[id]/shared-io-module/mgmt/cert
    -- sys/chassis-[id]/slot-[id]/shared-io-module/mgmt/cert
    -- sys/chassis-[id]/sw-slot-[id]/mgmt/cert
    -- sys/chassis-[id]/slot-[id]/mgmt/cert
    -- sys/switch-[id]/mgmt/cert
    -- sys/chassis-[id]/blade-[slotId]/board/storage-[type]-[id]/mgmt/cert
    -- sys/rack-unit-[id]/board/storage-[type]-[id]/mgmt/cert
    -- sys/chassis-[id]/cartridge-[slotId]/server-[serverInstanceId]/board/storage-[type]-[id]/mgmt/cert
    -- sys/chassis-[id]/storage-[type]-[id]/mgmt/cert
    -- sys/chassis-[id]/blade-[slotId]/board/storage-[type]-[id]/disk-[id]/mgmt/cert
    -- sys/rack-unit-[id]/board/storage-[type]-[id]/disk-[id]/mgmt/cert
    -- sys/chassis-[id]/cartridge-[slotId]/server-[serverInstanceId]/board/storage-[type]-[id]/disk-[id]/mgmt/cert
    -- sys/chassis-[id]/storage-[type]-[id]/disk-[id]/mgmt/cert
    -- sys/chassis-[id]/blade-[slotId]/enc-[id]/disk-[id]/mgmt/cert
    -- sys/rack-unit-[id]/enc-[id]/disk-[id]/mgmt/cert
    -- sys/chassis-[id]/cartridge-[slotId]/server-[serverInstanceId]/enc-[id]/disk-[id]/mgmt/cert
    -- sys/chassis-[id]/enc-[id]/disk-[id]/mgmt/cert
    -- sys/chassis-[id]/blade-[slotId]/board/storage-[type]-[id]/enc-[id]/disk-[id]/mgmt/cert
    -- sys/rack-unit-[id]/board/storage-[type]-[id]/enc-[id]/disk-[id]/mgmt/cert
    -- sys/chassis-[id]/cartridge-[slotId]/server-[serverInstanceId]/board/storage-[type]-[id]/enc-[id]/disk-[id]/mgmt/cert
    -- sys/chassis-[id]/storage-[type]-[id]/enc-[id]/disk-[id]/mgmt/cert
    -- sys/chassis-[id]/blade-[slotId]/board/sas-expander-[id]/mgmt/cert
    -- sys/rack-unit-[id]/board/sas-expander-[id]/mgmt/cert
    -- sys/chassis-[id]/cartridge-[slotId]/server-[serverInstanceId]/board/sas-expander-[id]/mgmt/cert
    -- sys/chassis-[id]/sas-expander-[id]/mgmt/cert
    -- sys/mgmt/cert
        -- fltMgmtKvmCertificateCertificate-unsupported
        -- fltMgmtKvmCertificateCertificate-empty-params

-- extmgmt:If
    -- sys/switch-[id]/extmgmt-intf
        -- fltExtmgmtIfMgmtifdown

-- epqos:Definition
    -- org-[name]/ep-qos-[name]
        -- fsmStFailEpqosDefinitionDeploy:Local
        -- fsmStFailEpqosDefinitionDeploy:Peer
        -- fsmRmtErrEpqosDefinitionDeploy:Local
        -- fsmRmtErrEpqosDefinitionDeploy:Peer
        -- fsmFailEpqosDefinitionDeploy

-- equipment:Chassis
    -- sys/chassis-[id]
        -- fltEquipmentChassisUnsupportedConnectivity
        -- fltEquipmentChassisUnacknowledged
        -- fltEquipmentChassisIdentity
        -- fltEquipmentChassisPowerProblem
        -- fltEquipmentChassisThermalThresholdCritical
        -- fltEquipmentChassisThermalThresholdNonCritical
        -- fltEquipmentChassisThermalThresholdNonRecoverable
        -- fltEquipmentChassisInoperable
        -- fltEquipmentChassisIdentity-unestablishable
        -- fltEquipmentChassisSeeprom-inoperable
        -- fltEquipmentChassisInvalid-fru
        -- fltEquipmentChassisChassislimit-exceeded
        -- fltEquipmentChassisInaccessible-b
        -- fltEquipmentChassisInaccessible-a
        -- fltEquipmentChassisPhysical-security
        -- fsmStFailEquipmentChassisRemoveChassis:CleanupVnicsLocal
        -- fsmStFailEquipmentChassisRemoveChassis:CleanupVnicsPeer
        -- fsmStFailEquipmentChassisRemoveChassis:DisableEndPoint
        -- fsmStFailEquipmentChassisRemoveChassis:UnIdentifyLocal
        -- fsmStFailEquipmentChassisRemoveChassis:UnIdentifyPeer
        -- fsmStFailEquipmentChassisRemoveChassis:Wait
        -- fsmStFailEquipmentChassisRemoveChassis:decomission
        -- fsmStFailEquipmentChassisPsuPolicyConfig:Execute
        -- fsmStFailEquipmentChassisPowerCap:Config
        -- fsmStFailEquipmentChassisPowerCap:Wait
        -- fsmStFailEquipmentChassisDynamicReallocation:Config
        -- fsmStFailEquipmentChassisOobStorageAdminCfg:OobStorageConfig
        -- fsmStFailEquipmentChassisOobStorageAdminCfg:OobStorageInventory
        -- fsmStFailEquipmentChassisAssociate:ActivateAdaptor
        -- fsmStFailEquipmentChassisAssociate:ActivateBrdCtlr
        -- fsmStFailEquipmentChassisAssociate:ActivateCmc
        -- fsmStFailEquipmentChassisAssociate:ActivateLocalDisk
        -- fsmStFailEquipmentChassisAssociate:ActivateSasExpander
        -- fsmStFailEquipmentChassisAssociate:ActivateStorageCtlr
        -- fsmStFailEquipmentChassisAssociate:ConfigChassisAdapterConnectivity
        -- fsmStFailEquipmentChassisAssociate:DeleteCurlDownloadedImages
        -- fsmStFailEquipmentChassisAssociate:DeleteImagesRemote
        -- fsmStFailEquipmentChassisAssociate:DiskZoningConfig
        -- fsmStFailEquipmentChassisAssociate:PollAdaptorActivation
        -- fsmStFailEquipmentChassisAssociate:PollBrdCtlrActivation
        -- fsmStFailEquipmentChassisAssociate:PollCmcActivation
        -- fsmStFailEquipmentChassisAssociate:PollPostDiskZoneStorageInvCIMC
        -- fsmStFailEquipmentChassisAssociate:PollSasExpanderActivate
        -- fsmStFailEquipmentChassisAssociate:PollSasExpanderConfig
        -- fsmStFailEquipmentChassisAssociate:PollStorageCtlrActivation
        -- fsmStFailEquipmentChassisAssociate:PollUpdateAdaptor
        -- fsmStFailEquipmentChassisAssociate:PollUpdateCmc
        -- fsmStFailEquipmentChassisAssociate:PollUpdateSasExpander
        -- fsmStFailEquipmentChassisAssociate:PostDiskZoneStorageInvCIMC
        -- fsmStFailEquipmentChassisAssociate:PostDiskZoneStorageInvCMC
        -- fsmStFailEquipmentChassisAssociate:PowerOffServers
        -- fsmStFailEquipmentChassisAssociate:PowerOnServers
        -- fsmStFailEquipmentChassisAssociate:SasExpanderConfig
        -- fsmStFailEquipmentChassisAssociate:UnlockFirmwareImage
        -- fsmStFailEquipmentChassisAssociate:UpdateAdaptor
        -- fsmStFailEquipmentChassisAssociate:UpdateCmc
        -- fsmStFailEquipmentChassisAssociate:UpdateSasExpander
        -- fsmStFailEquipmentChassisAssociate:WaitBeforeInstallation
        -- fsmStFailEquipmentChassisAssociate:WaitForPowerOff
        -- fsmStFailEquipmentChassisAssociate:copyRemote
        -- fsmStFailEquipmentChassisAssociate:downloadImages
        -- fsmStFailEquipmentChassisDisassociate:complete
        -- fsmStFailEquipmentChassisChassisUpgrade:ActivateAdaptor
        -- fsmStFailEquipmentChassisChassisUpgrade:ActivateBrdCtlr
        -- fsmStFailEquipmentChassisChassisUpgrade:ActivateCmc
        -- fsmStFailEquipmentChassisChassisUpgrade:ActivateLocalDisk
        -- fsmStFailEquipmentChassisChassisUpgrade:ActivateSasExpander
        -- fsmStFailEquipmentChassisChassisUpgrade:ActivateStorageCtlr
        -- fsmStFailEquipmentChassisChassisUpgrade:PollAdaptorActivation
        -- fsmStFailEquipmentChassisChassisUpgrade:PollBrdCtlrActivation
        -- fsmStFailEquipmentChassisChassisUpgrade:PollCmcActivation
        -- fsmStFailEquipmentChassisChassisUpgrade:PollLocalDiskActivate
        -- fsmStFailEquipmentChassisChassisUpgrade:PollSasExpanderActivate
        -- fsmStFailEquipmentChassisChassisUpgrade:PollStorageCtlrActivation
        -- fsmStFailEquipmentChassisChassisUpgrade:PollUpdateStatus
        -- fsmStFailEquipmentChassisChassisUpgrade:PowerOffServers
        -- fsmStFailEquipmentChassisChassisUpgrade:PowerOnServers
        -- fsmStFailEquipmentChassisChassisUpgrade:ResetSasExpander
        -- fsmStFailEquipmentChassisChassisUpgrade:UpdateRequest
        -- fsmStFailEquipmentChassisChassisUpgrade:WaitForPowerOff
        -- fsmStFailEquipmentChassisFwUpgrade:DeleteCurlDownloadedImages
        -- fsmStFailEquipmentChassisFwUpgrade:DeleteImagesRemote
        -- fsmStFailEquipmentChassisFwUpgrade:PollUpdateAdaptor
        -- fsmStFailEquipmentChassisFwUpgrade:PollUpdateCmc
        -- fsmStFailEquipmentChassisFwUpgrade:PollUpdateSasExpander
        -- fsmStFailEquipmentChassisFwUpgrade:UnlockFirmwareImage
        -- fsmStFailEquipmentChassisFwUpgrade:UpdateAdaptor
        -- fsmStFailEquipmentChassisFwUpgrade:UpdateCmc
        -- fsmStFailEquipmentChassisFwUpgrade:UpdateSasExpander
        -- fsmStFailEquipmentChassisFwUpgrade:WaitBeforeInstallation
        -- fsmStFailEquipmentChassisFwUpgrade:copyRemote
        -- fsmStFailEquipmentChassisFwUpgrade:downloadImages
        -- fsmRmtErrEquipmentChassisRemoveChassis:CleanupVnicsLocal
        -- fsmRmtErrEquipmentChassisRemoveChassis:CleanupVnicsPeer
        -- fsmRmtErrEquipmentChassisRemoveChassis:DisableEndPoint
        -- fsmRmtErrEquipmentChassisRemoveChassis:UnIdentifyLocal
        -- fsmRmtErrEquipmentChassisRemoveChassis:UnIdentifyPeer
        -- fsmRmtErrEquipmentChassisRemoveChassis:Wait
        -- fsmRmtErrEquipmentChassisRemoveChassis:decomission
        -- fsmRmtErrEquipmentChassisPsuPolicyConfig:Execute
        -- fsmRmtErrEquipmentChassisPowerCap:Config
        -- fsmRmtErrEquipmentChassisPowerCap:Wait
        -- fsmRmtErrEquipmentChassisDynamicReallocation:Config
        -- fsmRmtErrEquipmentChassisOobStorageAdminCfg:OobStorageConfig
        -- fsmRmtErrEquipmentChassisOobStorageAdminCfg:OobStorageInventory
        -- fsmRmtErrEquipmentChassisAssociate:ActivateAdaptor
        -- fsmRmtErrEquipmentChassisAssociate:ActivateBrdCtlr
        -- fsmRmtErrEquipmentChassisAssociate:ActivateCmc
        -- fsmRmtErrEquipmentChassisAssociate:ActivateLocalDisk
        -- fsmRmtErrEquipmentChassisAssociate:ActivateSasExpander
        -- fsmRmtErrEquipmentChassisAssociate:ActivateStorageCtlr
        -- fsmRmtErrEquipmentChassisAssociate:ConfigChassisAdapterConnectivity
        -- fsmRmtErrEquipmentChassisAssociate:DeleteCurlDownloadedImages
        -- fsmRmtErrEquipmentChassisAssociate:DeleteImagesRemote
        -- fsmRmtErrEquipmentChassisAssociate:DiskZoningConfig
        -- fsmRmtErrEquipmentChassisAssociate:PollAdaptorActivation
        -- fsmRmtErrEquipmentChassisAssociate:PollBrdCtlrActivation
        -- fsmRmtErrEquipmentChassisAssociate:PollCmcActivation
        -- fsmRmtErrEquipmentChassisAssociate:PollPostDiskZoneStorageInvCIMC
        -- fsmRmtErrEquipmentChassisAssociate:PollSasExpanderActivate
        -- fsmRmtErrEquipmentChassisAssociate:PollSasExpanderConfig
        -- fsmRmtErrEquipmentChassisAssociate:PollStorageCtlrActivation
        -- fsmRmtErrEquipmentChassisAssociate:PollUpdateAdaptor
        -- fsmRmtErrEquipmentChassisAssociate:PollUpdateCmc
        -- fsmRmtErrEquipmentChassisAssociate:PollUpdateSasExpander
        -- fsmRmtErrEquipmentChassisAssociate:PostDiskZoneStorageInvCIMC
        -- fsmRmtErrEquipmentChassisAssociate:PostDiskZoneStorageInvCMC
        -- fsmRmtErrEquipmentChassisAssociate:PowerOffServers
        -- fsmRmtErrEquipmentChassisAssociate:PowerOnServers
        -- fsmRmtErrEquipmentChassisAssociate:SasExpanderConfig
        -- fsmRmtErrEquipmentChassisAssociate:UnlockFirmwareImage
        -- fsmRmtErrEquipmentChassisAssociate:UpdateAdaptor
        -- fsmRmtErrEquipmentChassisAssociate:UpdateCmc
        -- fsmRmtErrEquipmentChassisAssociate:UpdateSasExpander
        -- fsmRmtErrEquipmentChassisAssociate:WaitBeforeInstallation
        -- fsmRmtErrEquipmentChassisAssociate:WaitForPowerOff
        -- fsmRmtErrEquipmentChassisAssociate:copyRemote
        -- fsmRmtErrEquipmentChassisAssociate:downloadImages
        -- fsmRmtErrEquipmentChassisDisassociate:complete
        -- fsmRmtErrEquipmentChassisChassisUpgrade:ActivateAdaptor
        -- fsmRmtErrEquipmentChassisChassisUpgrade:ActivateBrdCtlr
        -- fsmRmtErrEquipmentChassisChassisUpgrade:ActivateCmc
        -- fsmRmtErrEquipmentChassisChassisUpgrade:ActivateLocalDisk
        -- fsmRmtErrEquipmentChassisChassisUpgrade:ActivateSasExpander
        -- fsmRmtErrEquipmentChassisChassisUpgrade:ActivateStorageCtlr
        -- fsmRmtErrEquipmentChassisChassisUpgrade:PollAdaptorActivation
        -- fsmRmtErrEquipmentChassisChassisUpgrade:PollBrdCtlrActivation
        -- fsmRmtErrEquipmentChassisChassisUpgrade:PollCmcActivation
        -- fsmRmtErrEquipmentChassisChassisUpgrade:PollLocalDiskActivate
        -- fsmRmtErrEquipmentChassisChassisUpgrade:PollSasExpanderActivate
        -- fsmRmtErrEquipmentChassisChassisUpgrade:PollStorageCtlrActivation
        -- fsmRmtErrEquipmentChassisChassisUpgrade:PollUpdateStatus
        -- fsmRmtErrEquipmentChassisChassisUpgrade:PowerOffServers
        -- fsmRmtErrEquipmentChassisChassisUpgrade:PowerOnServers
        -- fsmRmtErrEquipmentChassisChassisUpgrade:ResetSasExpander
        -- fsmRmtErrEquipmentChassisChassisUpgrade:UpdateRequest
        -- fsmRmtErrEquipmentChassisChassisUpgrade:WaitForPowerOff
        -- fsmRmtErrEquipmentChassisFwUpgrade:DeleteCurlDownloadedImages
        -- fsmRmtErrEquipmentChassisFwUpgrade:DeleteImagesRemote
        -- fsmRmtErrEquipmentChassisFwUpgrade:PollUpdateAdaptor
        -- fsmRmtErrEquipmentChassisFwUpgrade:PollUpdateCmc
        -- fsmRmtErrEquipmentChassisFwUpgrade:PollUpdateSasExpander
        -- fsmRmtErrEquipmentChassisFwUpgrade:UnlockFirmwareImage
        -- fsmRmtErrEquipmentChassisFwUpgrade:UpdateAdaptor
        -- fsmRmtErrEquipmentChassisFwUpgrade:UpdateCmc
        -- fsmRmtErrEquipmentChassisFwUpgrade:UpdateSasExpander
        -- fsmRmtErrEquipmentChassisFwUpgrade:WaitBeforeInstallation
        -- fsmRmtErrEquipmentChassisFwUpgrade:copyRemote
        -- fsmRmtErrEquipmentChassisFwUpgrade:downloadImages
        -- fsmFailEquipmentChassisRemoveChassis
        -- fsmFailEquipmentChassisPsuPolicyConfig
        -- fsmFailEquipmentChassisPowerCap
        -- fsmFailEquipmentChassisDynamicReallocation
        -- fsmFailEquipmentChassisOobStorageAdminCfg
        -- fsmFailEquipmentChassisAssociate
        -- fsmFailEquipmentChassisDisassociate
        -- fsmFailEquipmentChassisChassisUpgrade
        -- fsmFailEquipmentChassisFwUpgrade

-- comm:SvcEp
    -- sys/svc-ext
        -- fltCommSvcEpCommSvcNotDeployed
        -- fsmStFailCommSvcEpUpdateSvcEp:InitIptablesLocal
        -- fsmStFailCommSvcEpUpdateSvcEp:InitIptablesPeer
        -- fsmStFailCommSvcEpUpdateSvcEp:PropogateEpSettings
        -- fsmStFailCommSvcEpUpdateSvcEp:PropogateEpTimeZoneSettingsLocal
        -- fsmStFailCommSvcEpUpdateSvcEp:PropogateEpTimeZoneSettingsPeer
        -- fsmStFailCommSvcEpUpdateSvcEp:PropogateEpTimeZoneSettingsToAdaptorsLocal
        -- fsmStFailCommSvcEpUpdateSvcEp:PropogateEpTimeZoneSettingsToAdaptorsPeer
        -- fsmStFailCommSvcEpUpdateSvcEp:PropogateEpTimeZoneSettingsToFexIomLocal
        -- fsmStFailCommSvcEpUpdateSvcEp:PropogateEpTimeZoneSettingsToFexIomPeer
        -- fsmStFailCommSvcEpUpdateSvcEp:SetEpLocal
        -- fsmStFailCommSvcEpUpdateSvcEp:SetEpPeer
        -- fsmStFailCommSvcEpRestartWebSvc:local
        -- fsmStFailCommSvcEpRestartWebSvc:peer
        -- fsmRmtErrCommSvcEpUpdateSvcEp:InitIptablesLocal
        -- fsmRmtErrCommSvcEpUpdateSvcEp:InitIptablesPeer
        -- fsmRmtErrCommSvcEpUpdateSvcEp:PropogateEpSettings
        -- fsmRmtErrCommSvcEpUpdateSvcEp:PropogateEpTimeZoneSettingsLocal
        -- fsmRmtErrCommSvcEpUpdateSvcEp:PropogateEpTimeZoneSettingsPeer
        -- fsmRmtErrCommSvcEpUpdateSvcEp:PropogateEpTimeZoneSettingsToAdaptorsLocal
        -- fsmRmtErrCommSvcEpUpdateSvcEp:PropogateEpTimeZoneSettingsToAdaptorsPeer
        -- fsmRmtErrCommSvcEpUpdateSvcEp:PropogateEpTimeZoneSettingsToFexIomLocal
        -- fsmRmtErrCommSvcEpUpdateSvcEp:PropogateEpTimeZoneSettingsToFexIomPeer
        -- fsmRmtErrCommSvcEpUpdateSvcEp:SetEpLocal
        -- fsmRmtErrCommSvcEpUpdateSvcEp:SetEpPeer
        -- fsmRmtErrCommSvcEpRestartWebSvc:local
        -- fsmRmtErrCommSvcEpRestartWebSvc:peer
        -- fsmFailCommSvcEpUpdateSvcEp
        -- fsmFailCommSvcEpRestartWebSvc

-- storage:LocalDisk
    -- sys/chassis-[id]/blade-[slotId]/board/storage-[type]-[id]/disk-[id]
    -- sys/rack-unit-[id]/board/storage-[type]-[id]/disk-[id]
    -- sys/chassis-[id]/cartridge-[slotId]/server-[serverInstanceId]/board/storage-[type]-[id]/disk-[id]
    -- sys/chassis-[id]/storage-[type]-[id]/disk-[id]
    -- sys/chassis-[id]/blade-[slotId]/enc-[id]/disk-[id]
    -- sys/rack-unit-[id]/enc-[id]/disk-[id]
    -- sys/chassis-[id]/cartridge-[slotId]/server-[serverInstanceId]/enc-[id]/disk-[id]
    -- sys/chassis-[id]/enc-[id]/disk-[id]
    -- sys/chassis-[id]/blade-[slotId]/board/storage-[type]-[id]/enc-[id]/disk-[id]
    -- sys/rack-unit-[id]/board/storage-[type]-[id]/enc-[id]/disk-[id]
    -- sys/chassis-[id]/cartridge-[slotId]/server-[serverInstanceId]/board/storage-[type]-[id]/enc-[id]/disk-[id]
    -- sys/chassis-[id]/storage-[type]-[id]/enc-[id]/disk-[id]
        -- fltStorageLocalDiskInoperable
        -- fltStorageLocalDiskDegraded
        -- fltStorageLocalDiskRebuildFailed
        -- fltStorageLocalDiskCopybackFailed
        -- fltStorageLocalDiskMissing
        -- fltStorageLocalDiskInaccessible
        -- fltStorageLocalDiskThermalIssueCritical
        -- fltStorageLocalDiskThermalIssueNonRecoverable
        -- fltStorageLocalDiskNot-supported
        -- fltStorageLocalDiskLink-degraded
        -- fltStorageLocalDiskThermalIssueNonCritical
        -- fltStorageLocalDiskFailed
        -- fltStorageLocalDiskUnhealthy
        -- fsmStFailStorageLocalDiskUpdateLocalDisk:PollUpdateStatus
        -- fsmStFailStorageLocalDiskUpdateLocalDisk:PowerOffServers
        -- fsmStFailStorageLocalDiskUpdateLocalDisk:ServersPowerOffCompletion
        -- fsmStFailStorageLocalDiskUpdateLocalDisk:Update
        -- fsmRmtErrStorageLocalDiskUpdateLocalDisk:PollUpdateStatus
        -- fsmRmtErrStorageLocalDiskUpdateLocalDisk:PowerOffServers
        -- fsmRmtErrStorageLocalDiskUpdateLocalDisk:ServersPowerOffCompletion
        -- fsmRmtErrStorageLocalDiskUpdateLocalDisk:Update
        -- fsmFailStorageLocalDiskUpdateLocalDisk

-- fabric:FcoeSanPc
    -- fabric/san/[id]/fcoesanpc-[portId]
        -- fltFabricFcoeSanPcDown
        -- fltFabricFcoeSanPcUnsupported

-- extvmm:VMNDRef
    -- fabric/lan/vm-network-sets/vm-network-[name]/vm-network-def-ref[name]
        -- fltExtvmmVMNDRefVmNetworkReferenceIncorrect

-- fabric:EthLanEp
    -- fabric/lan/[id]/phys-slot-[slotId]-port-[portId]
    -- fabric/server/sw-[id]/slot-[slotId]-aggr-port-[aggrPortId]/phys-slot-[slotId]-port-[portId]
    -- fabric/server/sw-[id]/pc-[portId]/slot-[slotId]-aggr-port-[aggrPortId]/phys-slot-[slotId]-port-[portId]
    -- fabric/eth-estc/[id]/slot-[slotId]-aggr-port-[aggrPortId]/phys-slot-[slotId]-port-[portId]
    -- fabric/eth-estc/[id]/pc-[portId]/slot-[slotId]-aggr-port-[aggrPortId]/phys-slot-[slotId]-port-[portId]
    -- fabric/lan/[id]/slot-[slotId]-aggr-port-[aggrPortId]/phys-slot-[slotId]-port-[portId]
    -- fabric/lan/[id]/pc-[portId]/slot-[slotId]-aggr-port-[aggrPortId]/phys-slot-[slotId]-port-[portId]
    -- fabric/lanmon/[id]/eth-mon-[name]/slot-[slotId]-aggr-port-[aggrPortId]/phys-slot-[slotId]-port-[portId]
    -- fabric/fc-estc/[id]/slot-[slotId]-aggr-port-[aggrPortId]/phys-slot-[slotId]-port-[portId]
    -- fabric/sanmon/[id]/fc-mon-[name]/slot-[slotId]-aggr-port-[aggrPortId]/phys-slot-[slotId]-port-[portId]
    -- fabric/san/[id]/slot-[slotId]-aggr-port-[aggrPortId]/phys-slot-[slotId]-port-[portId]
    -- fabric/san/[id]/fcoesanpc-[portId]/slot-[slotId]-aggr-port-[aggrPortId]/phys-slot-[slotId]-port-[portId]
        -- fltFabricEthLanEpMissingPrimaryVlan
        -- fltFabricEthLanEpOverlapping-vlan
        -- fltFabricEthLanEpUdldLinkDown

-- storage:FlexFlashVirtualDrive
    -- sys/chassis-[id]/blade-[slotId]/board/storage-flexflash-[id]/vd-[id]
    -- sys/rack-unit-[id]/board/storage-flexflash-[id]/vd-[id]
    -- sys/chassis-[id]/cartridge-[slotId]/server-[serverInstanceId]/board/storage-flexflash-[id]/vd-[id]
        -- fltStorageFlexFlashVirtualDriveDegraded
        -- fltStorageFlexFlashVirtualDriveInoperable

-- sw:FcMon
    -- sys/switch-[id]/sanmon-fc/mon-[name]
        -- fsmStFailSwFcMonDeploy:UpdateFcMon
        -- fsmRmtErrSwFcMonDeploy:UpdateFcMon
        -- fsmFailSwFcMonDeploy

-- power:Policy
    -- org-[name]/power-policy-[name]
    -- policy-ep/system-policies/power-policy-[name]
        -- fltPowerPolicyPowerPolicyApplicationFail

-- extvmm:MasterExtKey
    -- sys/extvm-mgmt/ext-key
        -- fsmStFailExtvmmMasterExtKeyConfig:SetLocal
        -- fsmStFailExtvmmMasterExtKeyConfig:SetPeer
        -- fsmRmtErrExtvmmMasterExtKeyConfig:SetLocal
        -- fsmRmtErrExtvmmMasterExtKeyConfig:SetPeer
        -- fsmFailExtvmmMasterExtKeyConfig

-- storage:System
    -- storage-ep/system
        -- fsmStFailStorageSystemSync:Execute
        -- fsmRmtErrStorageSystemSync:Execute
        -- fsmFailStorageSystemSync

-- equipment:Psu
    -- sys/rack-unit-[id]/psu-[id]
    -- sys/chassis-[id]/psu-[id]
    -- sys/fex-[id]/psu-[id]
    -- sys/rack-enclosure-[id]/psu-[id]
    -- sys/switch-[id]/psu-[id]
        -- fltEquipmentPsuPowerSupplyProblem
        -- fltEquipmentPsuInoperable
        -- fltEquipmentPsuMissing
        -- fltEquipmentPsuThermalThresholdNonCritical
        -- fltEquipmentPsuThermalThresholdCritical
        -- fltEquipmentPsuThermalThresholdNonRecoverable
        -- fltEquipmentPsuVoltageThresholdNonCritical
        -- fltEquipmentPsuVoltageThresholdCritical
        -- fltEquipmentPsuVoltageThresholdNonRecoverable
        -- fltEquipmentPsuPerfThresholdNonCritical
        -- fltEquipmentPsuPerfThresholdCritical
        -- fltEquipmentPsuPerfThresholdNonRecoverable
        -- fltEquipmentPsuIdentity
        -- fltEquipmentPsuOffline
        -- fltEquipmentPsuPowerSupplyShutdown
        -- fltEquipmentPsuPowerThreshold
        -- fltEquipmentPsuInputError
        -- fsmStFailEquipmentPsuUpdatePSU:ActivatePsu
        -- fsmStFailEquipmentPsuUpdatePSU:PollActivateStatus
        -- fsmStFailEquipmentPsuUpdatePSU:PollUpdateStatus
        -- fsmStFailEquipmentPsuUpdatePSU:UpdateRequest
        -- fsmRmtErrEquipmentPsuUpdatePSU:ActivatePsu
        -- fsmRmtErrEquipmentPsuUpdatePSU:PollActivateStatus
        -- fsmRmtErrEquipmentPsuUpdatePSU:PollUpdateStatus
        -- fsmRmtErrEquipmentPsuUpdatePSU:UpdateRequest
        -- fsmFailEquipmentPsuUpdatePSU

-- aaa:Locale
    -- sys/user-ext/locale-[name]
        -- fltAaaLocaleLocaleNotDeployed

-- aaa:UserRole
    -- sys/ldap-ext/ldapgroup-[name]/role-[name]
    -- sys/user-ext/remoteuser-[name]/role-[name]
    -- sys/user-ext/user-[name]/role-[name]
        -- fltAaaUserRoleUserRoleNotDeployed

-- ident:MetaSystem
    -- metaverse/metasys
        -- fsmStFailIdentMetaSystemSync:Execute
        -- fsmStFailIdentMetaSystemSync:Ping
        -- fsmStFailIdentMetaSystemUcscUnivSync:Execute
        -- fsmRmtErrIdentMetaSystemSync:Execute
        -- fsmRmtErrIdentMetaSystemSync:Ping
        -- fsmRmtErrIdentMetaSystemUcscUnivSync:Execute
        -- fsmFailIdentMetaSystemSync
        -- fsmFailIdentMetaSystemUcscUnivSync

-- compute:IOHub
    -- sys/chassis-[id]/blade-[slotId]/board/iohub
    -- sys/rack-unit-[id]/board/iohub
    -- sys/chassis-[id]/cartridge-[slotId]/server-[serverInstanceId]/board/iohub
        -- fltComputeIOHubThermalNonCritical
        -- fltComputeIOHubThermalThresholdCritical
        -- fltComputeIOHubThermalThresholdNonRecoverable

-- equipment:SharedIOModule
    -- sys/chassis-[id]/shared-io-module
    -- sys/chassis-[id]/slot-[id]/shared-io-module
        -- fltEquipmentSharedIOModuleInaccessible

-- storage:LocalDiskSlotEp
    -- sys/chassis-[id]/blade-[slotId]/board/disk-[id]
    -- sys/rack-unit-[id]/board/disk-[id]
    -- sys/chassis-[id]/cartridge-[slotId]/server-[serverInstanceId]/board/disk-[id]
        -- fltStorageLocalDiskSlotEpUnusable

-- fabric:FcoeEstcEp
    -- fabric/fc-estc/[id]/phys-fcoe-slot-[slotId]-port-[portId]
    -- fabric/server/sw-[id]/slot-[slotId]-aggr-port-[aggrPortId]/phys-fcoe-slot-[slotId]-port-[portId]
    -- fabric/server/sw-[id]/pc-[portId]/slot-[slotId]-aggr-port-[aggrPortId]/phys-fcoe-slot-[slotId]-port-[portId]
    -- fabric/eth-estc/[id]/slot-[slotId]-aggr-port-[aggrPortId]/phys-fcoe-slot-[slotId]-port-[portId]
    -- fabric/eth-estc/[id]/pc-[portId]/slot-[slotId]-aggr-port-[aggrPortId]/phys-fcoe-slot-[slotId]-port-[portId]
    -- fabric/lan/[id]/slot-[slotId]-aggr-port-[aggrPortId]/phys-fcoe-slot-[slotId]-port-[portId]
    -- fabric/lan/[id]/pc-[portId]/slot-[slotId]-aggr-port-[aggrPortId]/phys-fcoe-slot-[slotId]-port-[portId]
    -- fabric/lanmon/[id]/eth-mon-[name]/slot-[slotId]-aggr-port-[aggrPortId]/phys-fcoe-slot-[slotId]-port-[portId]
    -- fabric/fc-estc/[id]/slot-[slotId]-aggr-port-[aggrPortId]/phys-fcoe-slot-[slotId]-port-[portId]
    -- fabric/sanmon/[id]/fc-mon-[name]/slot-[slotId]-aggr-port-[aggrPortId]/phys-fcoe-slot-[slotId]-port-[portId]
    -- fabric/san/[id]/slot-[slotId]-aggr-port-[aggrPortId]/phys-fcoe-slot-[slotId]-port-[portId]
    -- fabric/san/[id]/fcoesanpc-[portId]/slot-[slotId]-aggr-port-[aggrPortId]/phys-fcoe-slot-[slotId]-port-[portId]
        -- fltFabricFcoeEstcEpDown
        -- fltFabricFcoeEstcEpFcoe-storage-port-invalid

-- mgmt:IPv6IfAddr
    -- sys/chassis-[id]/blade-[slotId]/adaptor-[id]/host-eth-[id]/if-[id]/ifConfig-ipv6/if-ipv6
    -- sys/rack-unit-[id]/adaptor-[id]/host-eth-[id]/if-[id]/ifConfig-ipv6/if-ipv6
    -- sys/chassis-[id]/cartridge-[slotId]/server-[serverInstanceId]/adaptor-[id]/host-eth-[id]/if-[id]/ifConfig-ipv6/if-ipv6
    -- sys/chassis-[id]/cartridge-[slotId]/server-[serverInstanceId]/adaptor-[id]/host-eth-[id]/if-[id]/ifConfig-ipv6/if-ipv6
    -- sys/chassis-[id]/blade-[slotId]/adaptor-[id]/mgmt/if-[id]/ifConfig-ipv6/if-ipv6
    -- sys/rack-unit-[id]/adaptor-[id]/mgmt/if-[id]/ifConfig-ipv6/if-ipv6
    -- sys/chassis-[id]/cartridge-[slotId]/server-[serverInstanceId]/adaptor-[id]/mgmt/if-[id]/ifConfig-ipv6/if-ipv6
    -- sys/chassis-[id]/cartridge-[slotId]/server-[serverInstanceId]/adaptor-[id]/mgmt/if-[id]/ifConfig-ipv6/if-ipv6
    -- sys/chassis-[id]/blade-[slotId]/ext-board-[id]/boardController/mgmt/if-[id]/ifConfig-ipv6/if-ipv6
    -- sys/rack-unit-[id]/ext-board-[id]/boardController/mgmt/if-[id]/ifConfig-ipv6/if-ipv6
    -- sys/chassis-[id]/cartridge-[slotId]/server-[serverInstanceId]/ext-board-[id]/boardController/mgmt/if-[id]/ifConfig-ipv6/if-ipv6
    -- sys/chassis-[id]/blade-[slotId]/boardController/mgmt/if-[id]/ifConfig-ipv6/if-ipv6
    -- sys/rack-unit-[id]/boardController/mgmt/if-[id]/ifConfig-ipv6/if-ipv6
    -- sys/chassis-[id]/cartridge-[slotId]/server-[serverInstanceId]/boardController/mgmt/if-[id]/ifConfig-ipv6/if-ipv6
    -- sys/chassis-[id]/boardController/mgmt/if-[id]/ifConfig-ipv6/if-ipv6
    -- sys/chassis-[id]/slot-[id]/boardController/mgmt/if-[id]/ifConfig-ipv6/if-ipv6
    -- sys/chassis-[id]/blade-[slotId]/ext-board-[id]/mgmt/if-[id]/ifConfig-ipv6/if-ipv6
    -- sys/rack-unit-[id]/ext-board-[id]/mgmt/if-[id]/ifConfig-ipv6/if-ipv6
    -- sys/chassis-[id]/cartridge-[slotId]/server-[serverInstanceId]/ext-board-[id]/mgmt/if-[id]/ifConfig-ipv6/if-ipv6
    -- sys/chassis-[id]/blade-[slotId]/mgmt/if-[id]/ifConfig-ipv6/if-ipv6
    -- sys/rack-unit-[id]/mgmt/if-[id]/ifConfig-ipv6/if-ipv6
    -- sys/chassis-[id]/cartridge-[slotId]/server-[serverInstanceId]/mgmt/if-[id]/ifConfig-ipv6/if-ipv6
    -- sys/chassis-[id]/cartridge-[slotId]/server-[serverInstanceId]/mgmt/if-[id]/ifConfig-ipv6/if-ipv6
    -- sys/chassis-[id]/mgmt/if-[id]/ifConfig-ipv6/if-ipv6
    -- sys/fex-[id]/mgmt/if-[id]/ifConfig-ipv6/if-ipv6
    -- sys/chassis-[id]/slot-[id]/mgmt/if-[id]/ifConfig-ipv6/if-ipv6
    -- sys/fex-[id]/slot-[id]/mgmt/if-[id]/ifConfig-ipv6/if-ipv6
    -- sys/chassis-[id]/shared-io-module/mgmt/if-[id]/ifConfig-ipv6/if-ipv6
    -- sys/chassis-[id]/slot-[id]/shared-io-module/mgmt/if-[id]/ifConfig-ipv6/if-ipv6
    -- sys/chassis-[id]/sw-slot-[id]/mgmt/if-[id]/ifConfig-ipv6/if-ipv6
    -- sys/chassis-[id]/slot-[id]/mgmt/if-[id]/ifConfig-ipv6/if-ipv6
    -- sys/switch-[id]/mgmt/if-[id]/ifConfig-ipv6/if-ipv6
    -- sys/chassis-[id]/blade-[slotId]/board/storage-[type]-[id]/mgmt/if-[id]/ifConfig-ipv6/if-ipv6
    -- sys/rack-unit-[id]/board/storage-[type]-[id]/mgmt/if-[id]/ifConfig-ipv6/if-ipv6
    -- sys/chassis-[id]/cartridge-[slotId]/server-[serverInstanceId]/board/storage-[type]-[id]/mgmt/if-[id]/ifConfig-ipv6/if-ipv6
    -- sys/chassis-[id]/storage-[type]-[id]/mgmt/if-[id]/ifConfig-ipv6/if-ipv6
    -- sys/chassis-[id]/blade-[slotId]/board/storage-[type]-[id]/disk-[id]/mgmt/if-[id]/ifConfig-ipv6/if-ipv6
    -- sys/rack-unit-[id]/board/storage-[type]-[id]/disk-[id]/mgmt/if-[id]/ifConfig-ipv6/if-ipv6
    -- sys/chassis-[id]/cartridge-[slotId]/server-[serverInstanceId]/board/storage-[type]-[id]/disk-[id]/mgmt/if-[id]/ifConfig-ipv6/if-ipv6
    -- sys/chassis-[id]/storage-[type]-[id]/disk-[id]/mgmt/if-[id]/ifConfig-ipv6/if-ipv6
    -- sys/chassis-[id]/blade-[slotId]/enc-[id]/disk-[id]/mgmt/if-[id]/ifConfig-ipv6/if-ipv6
    -- sys/rack-unit-[id]/enc-[id]/disk-[id]/mgmt/if-[id]/ifConfig-ipv6/if-ipv6
    -- sys/chassis-[id]/cartridge-[slotId]/server-[serverInstanceId]/enc-[id]/disk-[id]/mgmt/if-[id]/ifConfig-ipv6/if-ipv6
    -- sys/chassis-[id]/enc-[id]/disk-[id]/mgmt/if-[id]/ifConfig-ipv6/if-ipv6
    -- sys/chassis-[id]/blade-[slotId]/board/storage-[type]-[id]/enc-[id]/disk-[id]/mgmt/if-[id]/ifConfig-ipv6/if-ipv6
    -- sys/rack-unit-[id]/board/storage-[type]-[id]/enc-[id]/disk-[id]/mgmt/if-[id]/ifConfig-ipv6/if-ipv6
    -- sys/chassis-[id]/cartridge-[slotId]/server-[serverInstanceId]/board/storage-[type]-[id]/enc-[id]/disk-[id]/mgmt/if-[id]/ifConfig-ipv6/if-ipv6
    -- sys/chassis-[id]/storage-[type]-[id]/enc-[id]/disk-[id]/mgmt/if-[id]/ifConfig-ipv6/if-ipv6
    -- sys/chassis-[id]/blade-[slotId]/board/sas-expander-[id]/mgmt/if-[id]/ifConfig-ipv6/if-ipv6
    -- sys/rack-unit-[id]/board/sas-expander-[id]/mgmt/if-[id]/ifConfig-ipv6/if-ipv6
    -- sys/chassis-[id]/cartridge-[slotId]/server-[serverInstanceId]/board/sas-expander-[id]/mgmt/if-[id]/ifConfig-ipv6/if-ipv6
    -- sys/chassis-[id]/sas-expander-[id]/mgmt/if-[id]/ifConfig-ipv6/if-ipv6
    -- sys/mgmt/if-[id]/ifConfig-ipv6/if-ipv6
    -- sys/switch-[id]/ifConfig-ipv6/if-ipv6
        -- fsmStFailMgmtIPv6IfAddrSwMgmtOobIpv6IfConfig:Switch
        -- fsmRmtErrMgmtIPv6IfAddrSwMgmtOobIpv6IfConfig:Switch
        -- fsmFailMgmtIPv6IfAddrSwMgmtOobIpv6IfConfig

-- capability:MgmtExtension
    -- capabilities/ep/mgmt-ext
        -- fsmStFailCapabilityMgmtExtensionActivateMgmtExt:ApplyCatalog
        -- fsmStFailCapabilityMgmtExtensionActivateMgmtExt:CopyRemote
        -- fsmStFailCapabilityMgmtExtensionActivateMgmtExt:EvaluateStatus
        -- fsmStFailCapabilityMgmtExtensionActivateMgmtExt:RescanImages
        -- fsmStFailCapabilityMgmtExtensionActivateMgmtExt:UnpackLocal
        -- fsmRmtErrCapabilityMgmtExtensionActivateMgmtExt:ApplyCatalog
        -- fsmRmtErrCapabilityMgmtExtensionActivateMgmtExt:CopyRemote
        -- fsmRmtErrCapabilityMgmtExtensionActivateMgmtExt:EvaluateStatus
        -- fsmRmtErrCapabilityMgmtExtensionActivateMgmtExt:RescanImages
        -- fsmRmtErrCapabilityMgmtExtensionActivateMgmtExt:UnpackLocal
        -- fsmFailCapabilityMgmtExtensionActivateMgmtExt

-- storage:VsanRef
    -- fabric/fc-estc/zone-profile-[name]/zone-[name]/vsan-ref
    -- org-[name]/tier-[name]/ls-[name]/grp-[name]/fc-group/storage-conndef/fc-target-ep-[targetwwpn]/vsan-ref
    -- org-[name]/ls-[name]/grp-[name]/fc-group/storage-conndef/fc-target-ep-[targetwwpn]/vsan-ref
    -- org-[name]/san-conn-pol-[name]/grp-[name]/fc-group/storage-conndef/fc-target-ep-[targetwwpn]/vsan-ref
    -- org-[name]/storage-connpolicy-[name]/fc-target-ep-[targetwwpn]/vsan-ref
        -- fltStorageVsanRefVsanUnresolvable

-- extpol:Provider
    -- extpol/reg/providers/prov-[type]
        -- fsmStFailExtpolProviderReportConfigImport:Report
        -- fsmRmtErrExtpolProviderReportConfigImport:Report
        -- fsmFailExtpolProviderReportConfigImport

-- power:Group
    -- sys/power-ep/group-[name]
        -- fltPowerGroupPowerGroupInsufficientBudget
        -- fltPowerGroupPowerGroupBudgetIncorrect

-- firmware:PackItem
    -- org-[name]/update-backup-version-holder-[bundleType]/pack-image-[hwVendor]|[hwModel]|[type]
    -- org-[name]/fw-catalog-pack-[name]/update-backup-version-holder-[bundleType]/pack-image-[hwVendor]|[hwModel]|[type]
    -- org-[name]/fw-chassis-pack-[name]/update-backup-version-holder-[bundleType]/pack-image-[hwVendor]|[hwModel]|[type]
    -- org-[name]/update-backup-version-holder-[bundleType]/pack-image-[hwVendor]|[hwModel]|[type]
    -- org-[name]/fw-infra-pack-[name]/update-backup-version-holder-[bundleType]/pack-image-[hwVendor]|[hwModel]|[type]
    -- org-[name]/fw-host-pack-[name]/update-backup-version-holder-[bundleType]/pack-image-[hwVendor]|[hwModel]|[type]
    -- org-[name]/fw-mgmt-pack-[name]/update-backup-version-holder-[bundleType]/pack-image-[hwVendor]|[hwModel]|[type]
    -- org-[name]/pack-image-[hwVendor]|[hwModel]|[type]
    -- org-[name]/fw-catalog-pack-[name]/pack-image-[hwVendor]|[hwModel]|[type]
    -- org-[name]/fw-chassis-pack-[name]/pack-image-[hwVendor]|[hwModel]|[type]
    -- org-[name]/pack-image-[hwVendor]|[hwModel]|[type]
    -- org-[name]/fw-infra-pack-[name]/pack-image-[hwVendor]|[hwModel]|[type]
    -- org-[name]/fw-host-pack-[name]/pack-image-[hwVendor]|[hwModel]|[type]
    -- org-[name]/fw-mgmt-pack-[name]/pack-image-[hwVendor]|[hwModel]|[type]
        -- fltFirmwarePackItemImageMissing

-- capability:Catalogue
    -- capabilities
        -- fltCapabilityCatalogueLoadErrors
        -- fsmStFailCapabilityCatalogueDeployCatalogue:SyncBladeAGLocal
        -- fsmStFailCapabilityCatalogueDeployCatalogue:SyncBladeAGRemote
        -- fsmStFailCapabilityCatalogueDeployCatalogue:SyncHostagentAGLocal
        -- fsmStFailCapabilityCatalogueDeployCatalogue:SyncHostagentAGRemote
        -- fsmStFailCapabilityCatalogueDeployCatalogue:SyncNicAGLocal
        -- fsmStFailCapabilityCatalogueDeployCatalogue:SyncNicAGRemote
        -- fsmStFailCapabilityCatalogueDeployCatalogue:SyncPortAGLocal
        -- fsmStFailCapabilityCatalogueDeployCatalogue:SyncPortAGRemote
        -- fsmStFailCapabilityCatalogueDeployCatalogue:finalize
        -- fsmStFailCapabilityCatalogueActivateCatalog:ApplyCatalog
        -- fsmStFailCapabilityCatalogueActivateCatalog:CopyCatFromRep
        -- fsmStFailCapabilityCatalogueActivateCatalog:CopyExternalRepToRemote
        -- fsmStFailCapabilityCatalogueActivateCatalog:CopyRemote
        -- fsmStFailCapabilityCatalogueActivateCatalog:EvaluateStatus
        -- fsmStFailCapabilityCatalogueActivateCatalog:RescanImages
        -- fsmStFailCapabilityCatalogueActivateCatalog:UnpackLocal
        -- fsmRmtErrCapabilityCatalogueDeployCatalogue:SyncBladeAGLocal
        -- fsmRmtErrCapabilityCatalogueDeployCatalogue:SyncBladeAGRemote
        -- fsmRmtErrCapabilityCatalogueDeployCatalogue:SyncHostagentAGLocal
        -- fsmRmtErrCapabilityCatalogueDeployCatalogue:SyncHostagentAGRemote
        -- fsmRmtErrCapabilityCatalogueDeployCatalogue:SyncNicAGLocal
        -- fsmRmtErrCapabilityCatalogueDeployCatalogue:SyncNicAGRemote
        -- fsmRmtErrCapabilityCatalogueDeployCatalogue:SyncPortAGLocal
        -- fsmRmtErrCapabilityCatalogueDeployCatalogue:SyncPortAGRemote
        -- fsmRmtErrCapabilityCatalogueDeployCatalogue:finalize
        -- fsmRmtErrCapabilityCatalogueActivateCatalog:ApplyCatalog
        -- fsmRmtErrCapabilityCatalogueActivateCatalog:CopyCatFromRep
        -- fsmRmtErrCapabilityCatalogueActivateCatalog:CopyExternalRepToRemote
        -- fsmRmtErrCapabilityCatalogueActivateCatalog:CopyRemote
        -- fsmRmtErrCapabilityCatalogueActivateCatalog:EvaluateStatus
        -- fsmRmtErrCapabilityCatalogueActivateCatalog:RescanImages
        -- fsmRmtErrCapabilityCatalogueActivateCatalog:UnpackLocal
        -- fsmFailCapabilityCatalogueDeployCatalogue
        -- fsmFailCapabilityCatalogueActivateCatalog

-- mgmt:Backup
    -- sys/backup-[hostname]
        -- fltMgmtBackupLocal Internal backup failed
        -- fsmStFailMgmtBackupBackup:backupLocal
        -- fsmStFailMgmtBackupBackup:upload
        -- fsmRmtErrMgmtBackupBackup:backupLocal
        -- fsmRmtErrMgmtBackupBackup:upload
        -- fsmFailMgmtBackupBackup

-- mgmt:If
    -- sys/chassis-[id]/blade-[slotId]/adaptor-[id]/host-eth-[id]/if-[id]
    -- sys/rack-unit-[id]/adaptor-[id]/host-eth-[id]/if-[id]
    -- sys/chassis-[id]/cartridge-[slotId]/server-[serverInstanceId]/adaptor-[id]/host-eth-[id]/if-[id]
    -- sys/chassis-[id]/cartridge-[slotId]/server-[serverInstanceId]/adaptor-[id]/host-eth-[id]/if-[id]
    -- sys/chassis-[id]/blade-[slotId]/adaptor-[id]/mgmt/if-[id]
    -- sys/rack-unit-[id]/adaptor-[id]/mgmt/if-[id]
    -- sys/chassis-[id]/cartridge-[slotId]/server-[serverInstanceId]/adaptor-[id]/mgmt/if-[id]
    -- sys/chassis-[id]/cartridge-[slotId]/server-[serverInstanceId]/adaptor-[id]/mgmt/if-[id]
    -- sys/chassis-[id]/blade-[slotId]/ext-board-[id]/boardController/mgmt/if-[id]
    -- sys/rack-unit-[id]/ext-board-[id]/boardController/mgmt/if-[id]
    -- sys/chassis-[id]/cartridge-[slotId]/server-[serverInstanceId]/ext-board-[id]/boardController/mgmt/if-[id]
    -- sys/chassis-[id]/blade-[slotId]/boardController/mgmt/if-[id]
    -- sys/rack-unit-[id]/boardController/mgmt/if-[id]
    -- sys/chassis-[id]/cartridge-[slotId]/server-[serverInstanceId]/boardController/mgmt/if-[id]
    -- sys/chassis-[id]/boardController/mgmt/if-[id]
    -- sys/chassis-[id]/slot-[id]/boardController/mgmt/if-[id]
    -- sys/chassis-[id]/blade-[slotId]/ext-board-[id]/mgmt/if-[id]
    -- sys/rack-unit-[id]/ext-board-[id]/mgmt/if-[id]
    -- sys/chassis-[id]/cartridge-[slotId]/server-[serverInstanceId]/ext-board-[id]/mgmt/if-[id]
    -- sys/chassis-[id]/blade-[slotId]/mgmt/if-[id]
    -- sys/rack-unit-[id]/mgmt/if-[id]
    -- sys/chassis-[id]/cartridge-[slotId]/server-[serverInstanceId]/mgmt/if-[id]
    -- sys/chassis-[id]/cartridge-[slotId]/server-[serverInstanceId]/mgmt/if-[id]
    -- sys/chassis-[id]/mgmt/if-[id]
    -- sys/fex-[id]/mgmt/if-[id]
    -- sys/chassis-[id]/slot-[id]/mgmt/if-[id]
    -- sys/fex-[id]/slot-[id]/mgmt/if-[id]
    -- sys/chassis-[id]/shared-io-module/mgmt/if-[id]
    -- sys/chassis-[id]/slot-[id]/shared-io-module/mgmt/if-[id]
    -- sys/chassis-[id]/sw-slot-[id]/mgmt/if-[id]
    -- sys/chassis-[id]/slot-[id]/mgmt/if-[id]
    -- sys/switch-[id]/mgmt/if-[id]
    -- sys/chassis-[id]/blade-[slotId]/board/storage-[type]-[id]/mgmt/if-[id]
    -- sys/rack-unit-[id]/board/storage-[type]-[id]/mgmt/if-[id]
    -- sys/chassis-[id]/cartridge-[slotId]/server-[serverInstanceId]/board/storage-[type]-[id]/mgmt/if-[id]
    -- sys/chassis-[id]/storage-[type]-[id]/mgmt/if-[id]
    -- sys/chassis-[id]/blade-[slotId]/board/storage-[type]-[id]/disk-[id]/mgmt/if-[id]
    -- sys/rack-unit-[id]/board/storage-[type]-[id]/disk-[id]/mgmt/if-[id]
    -- sys/chassis-[id]/cartridge-[slotId]/server-[serverInstanceId]/board/storage-[type]-[id]/disk-[id]/mgmt/if-[id]
    -- sys/chassis-[id]/storage-[type]-[id]/disk-[id]/mgmt/if-[id]
    -- sys/chassis-[id]/blade-[slotId]/enc-[id]/disk-[id]/mgmt/if-[id]
    -- sys/rack-unit-[id]/enc-[id]/disk-[id]/mgmt/if-[id]
    -- sys/chassis-[id]/cartridge-[slotId]/server-[serverInstanceId]/enc-[id]/disk-[id]/mgmt/if-[id]
    -- sys/chassis-[id]/enc-[id]/disk-[id]/mgmt/if-[id]
    -- sys/chassis-[id]/blade-[slotId]/board/storage-[type]-[id]/enc-[id]/disk-[id]/mgmt/if-[id]
    -- sys/rack-unit-[id]/board/storage-[type]-[id]/enc-[id]/disk-[id]/mgmt/if-[id]
    -- sys/chassis-[id]/cartridge-[slotId]/server-[serverInstanceId]/board/storage-[type]-[id]/enc-[id]/disk-[id]/mgmt/if-[id]
    -- sys/chassis-[id]/storage-[type]-[id]/enc-[id]/disk-[id]/mgmt/if-[id]
    -- sys/chassis-[id]/blade-[slotId]/board/sas-expander-[id]/mgmt/if-[id]
    -- sys/rack-unit-[id]/board/sas-expander-[id]/mgmt/if-[id]
    -- sys/chassis-[id]/cartridge-[slotId]/server-[serverInstanceId]/board/sas-expander-[id]/mgmt/if-[id]
    -- sys/chassis-[id]/sas-expander-[id]/mgmt/if-[id]
    -- sys/mgmt/if-[id]
        -- fltMgmtIfMisConnect
        -- fltMgmtIfMissing
        -- fltMgmtIfNew
        -- fsmStFailMgmtIfSwMgmtOobIfConfig:Switch
        -- fsmStFailMgmtIfSwMgmtInbandIfConfig:Switch
        -- fsmStFailMgmtIfVirtualIfConfig:Local
        -- fsmStFailMgmtIfVirtualIfConfig:Remote
        -- fsmStFailMgmtIfEnableVip:Local
        -- fsmStFailMgmtIfDisableVip:Peer
        -- fsmStFailMgmtIfEnableHA:Local
        -- fsmStFailMgmtIfFaPresence:CheckLicense
        -- fsmStFailMgmtIfFaPresence:Identify
        -- fsmStFailMgmtIfFaConn:ConfigureVifNs
        -- fsmStFailMgmtIfFaConn:DiscoverChassis
        -- fsmStFailMgmtIfFaConn:DiscoverSasExpander
        -- fsmStFailMgmtIfFaConn:OobStorageInventory
        -- fsmStFailMgmtIfFaConn:SharedIOModuleInventory
        -- fsmRmtErrMgmtIfSwMgmtOobIfConfig:Switch
        -- fsmRmtErrMgmtIfSwMgmtInbandIfConfig:Switch
        -- fsmRmtErrMgmtIfVirtualIfConfig:Local
        -- fsmRmtErrMgmtIfVirtualIfConfig:Remote
        -- fsmRmtErrMgmtIfEnableVip:Local
        -- fsmRmtErrMgmtIfDisableVip:Peer
        -- fsmRmtErrMgmtIfEnableHA:Local
        -- fsmRmtErrMgmtIfFaPresence:CheckLicense
        -- fsmRmtErrMgmtIfFaPresence:Identify
        -- fsmRmtErrMgmtIfFaConn:ConfigureVifNs
        -- fsmRmtErrMgmtIfFaConn:DiscoverChassis
        -- fsmRmtErrMgmtIfFaConn:DiscoverSasExpander
        -- fsmRmtErrMgmtIfFaConn:OobStorageInventory
        -- fsmRmtErrMgmtIfFaConn:SharedIOModuleInventory
        -- fsmFailMgmtIfSwMgmtOobIfConfig
        -- fsmFailMgmtIfSwMgmtInbandIfConfig
        -- fsmFailMgmtIfVirtualIfConfig
        -- fsmFailMgmtIfEnableVip
        -- fsmFailMgmtIfDisableVip
        -- fsmFailMgmtIfEnableHA
        -- fsmFailMgmtIfFaPresence
        -- fsmFailMgmtIfFaConn

-- epqos:DefinitionDelTask
    -- org-[name]/ep-qos-deletion-[defIntId]
        -- fsmStFailEpqosDefinitionDelTaskRemove:Local
        -- fsmStFailEpqosDefinitionDelTaskRemove:Peer
        -- fsmRmtErrEpqosDefinitionDelTaskRemove:Local
        -- fsmRmtErrEpqosDefinitionDelTaskRemove:Peer
        -- fsmFailEpqosDefinitionDelTaskRemove

-- vm:Vif
    -- vmm/computeEp-[uuid]/nic-[name]/sw-[phSwitchId]vif-[vifId]
    -- vmm/hv-[uuid]/nic-[name]/sw-[phSwitchId]vif-[vifId]
    -- vmm/vm-[uuid]/nic-[name]/sw-[phSwitchId]vif-[vifId]
        -- fltVmVifLinkState

-- dcx:Vc
    -- sys/chassis-[id]/blade-[slotId]/fabric-[switchId]/vc-[id]
    -- sys/chassis-[id]/blade-[slotId]/fabric-[switchId]/vc-[id]
    -- sys/rack-unit-[id]/fabric-[switchId]/vc-[id]
    -- sys/chassis-[id]/cartridge-[slotId]/server-[serverInstanceId]/fabric-[switchId]/vc-[id]
    -- sys/chassis-[id]/cartridge-[slotId]/server-[serverInstanceId]/fabric-[switchId]/vc-[id]
    -- sys/chassis-[id]/fabric-[switchId]/vc-[id]
    -- sys/fex-[id]/fabric-[switchId]/vc-[id]
    -- sys/chassis-[id]/blade-[slotId]/adaptor-[id]/mgmt/fabric-[switchId]/vc-[id]
    -- sys/rack-unit-[id]/adaptor-[id]/mgmt/fabric-[switchId]/vc-[id]
    -- sys/chassis-[id]/cartridge-[slotId]/server-[serverInstanceId]/adaptor-[id]/mgmt/fabric-[switchId]/vc-[id]
    -- sys/chassis-[id]/cartridge-[slotId]/server-[serverInstanceId]/adaptor-[id]/mgmt/fabric-[switchId]/vc-[id]
    -- sys/chassis-[id]/blade-[slotId]/ext-board-[id]/boardController/mgmt/fabric-[switchId]/vc-[id]
    -- sys/rack-unit-[id]/ext-board-[id]/boardController/mgmt/fabric-[switchId]/vc-[id]
    -- sys/chassis-[id]/cartridge-[slotId]/server-[serverInstanceId]/ext-board-[id]/boardController/mgmt/fabric-[switchId]/vc-[id]
    -- sys/chassis-[id]/blade-[slotId]/boardController/mgmt/fabric-[switchId]/vc-[id]
    -- sys/rack-unit-[id]/boardController/mgmt/fabric-[switchId]/vc-[id]
    -- sys/chassis-[id]/cartridge-[slotId]/server-[serverInstanceId]/boardController/mgmt/fabric-[switchId]/vc-[id]
    -- sys/chassis-[id]/boardController/mgmt/fabric-[switchId]/vc-[id]
    -- sys/chassis-[id]/slot-[id]/boardController/mgmt/fabric-[switchId]/vc-[id]
    -- sys/chassis-[id]/blade-[slotId]/ext-board-[id]/mgmt/fabric-[switchId]/vc-[id]
    -- sys/rack-unit-[id]/ext-board-[id]/mgmt/fabric-[switchId]/vc-[id]
    -- sys/chassis-[id]/cartridge-[slotId]/server-[serverInstanceId]/ext-board-[id]/mgmt/fabric-[switchId]/vc-[id]
    -- sys/chassis-[id]/blade-[slotId]/mgmt/fabric-[switchId]/vc-[id]
    -- sys/rack-unit-[id]/mgmt/fabric-[switchId]/vc-[id]
    -- sys/chassis-[id]/cartridge-[slotId]/server-[serverInstanceId]/mgmt/fabric-[switchId]/vc-[id]
    -- sys/chassis-[id]/cartridge-[slotId]/server-[serverInstanceId]/mgmt/fabric-[switchId]/vc-[id]
    -- sys/chassis-[id]/mgmt/fabric-[switchId]/vc-[id]
    -- sys/fex-[id]/mgmt/fabric-[switchId]/vc-[id]
    -- sys/chassis-[id]/slot-[id]/mgmt/fabric-[switchId]/vc-[id]
    -- sys/fex-[id]/slot-[id]/mgmt/fabric-[switchId]/vc-[id]
    -- sys/chassis-[id]/shared-io-module/mgmt/fabric-[switchId]/vc-[id]
    -- sys/chassis-[id]/slot-[id]/shared-io-module/mgmt/fabric-[switchId]/vc-[id]
    -- sys/chassis-[id]/sw-slot-[id]/mgmt/fabric-[switchId]/vc-[id]
    -- sys/chassis-[id]/slot-[id]/mgmt/fabric-[switchId]/vc-[id]
    -- sys/switch-[id]/mgmt/fabric-[switchId]/vc-[id]
    -- sys/chassis-[id]/blade-[slotId]/board/storage-[type]-[id]/mgmt/fabric-[switchId]/vc-[id]
    -- sys/rack-unit-[id]/board/storage-[type]-[id]/mgmt/fabric-[switchId]/vc-[id]
    -- sys/chassis-[id]/cartridge-[slotId]/server-[serverInstanceId]/board/storage-[type]-[id]/mgmt/fabric-[switchId]/vc-[id]
    -- sys/chassis-[id]/storage-[type]-[id]/mgmt/fabric-[switchId]/vc-[id]
    -- sys/chassis-[id]/blade-[slotId]/board/storage-[type]-[id]/disk-[id]/mgmt/fabric-[switchId]/vc-[id]
    -- sys/rack-unit-[id]/board/storage-[type]-[id]/disk-[id]/mgmt/fabric-[switchId]/vc-[id]
    -- sys/chassis-[id]/cartridge-[slotId]/server-[serverInstanceId]/board/storage-[type]-[id]/disk-[id]/mgmt/fabric-[switchId]/vc-[id]
    -- sys/chassis-[id]/storage-[type]-[id]/disk-[id]/mgmt/fabric-[switchId]/vc-[id]
    -- sys/chassis-[id]/blade-[slotId]/enc-[id]/disk-[id]/mgmt/fabric-[switchId]/vc-[id]
    -- sys/rack-unit-[id]/enc-[id]/disk-[id]/mgmt/fabric-[switchId]/vc-[id]
    -- sys/chassis-[id]/cartridge-[slotId]/server-[serverInstanceId]/enc-[id]/disk-[id]/mgmt/fabric-[switchId]/vc-[id]
    -- sys/chassis-[id]/enc-[id]/disk-[id]/mgmt/fabric-[switchId]/vc-[id]
    -- sys/chassis-[id]/blade-[slotId]/board/storage-[type]-[id]/enc-[id]/disk-[id]/mgmt/fabric-[switchId]/vc-[id]
    -- sys/rack-unit-[id]/board/storage-[type]-[id]/enc-[id]/disk-[id]/mgmt/fabric-[switchId]/vc-[id]
    -- sys/chassis-[id]/cartridge-[slotId]/server-[serverInstanceId]/board/storage-[type]-[id]/enc-[id]/disk-[id]/mgmt/fabric-[switchId]/vc-[id]
    -- sys/chassis-[id]/storage-[type]-[id]/enc-[id]/disk-[id]/mgmt/fabric-[switchId]/vc-[id]
    -- sys/chassis-[id]/blade-[slotId]/board/sas-expander-[id]/mgmt/fabric-[switchId]/vc-[id]
    -- sys/rack-unit-[id]/board/sas-expander-[id]/mgmt/fabric-[switchId]/vc-[id]
    -- sys/chassis-[id]/cartridge-[slotId]/server-[serverInstanceId]/board/sas-expander-[id]/mgmt/fabric-[switchId]/vc-[id]
    -- sys/chassis-[id]/sas-expander-[id]/mgmt/fabric-[switchId]/vc-[id]
    -- sys/mgmt/fabric-[switchId]/vc-[id]
    -- sys/chassis-[id]/blade-[slotId]/fabric-[switchId]/path-[id]/vc-[id]
    -- sys/chassis-[id]/blade-[slotId]/fabric-[switchId]/path-[id]/vc-[id]
    -- sys/rack-unit-[id]/fabric-[switchId]/path-[id]/vc-[id]
    -- sys/chassis-[id]/cartridge-[slotId]/server-[serverInstanceId]/fabric-[switchId]/path-[id]/vc-[id]
    -- sys/chassis-[id]/cartridge-[slotId]/server-[serverInstanceId]/fabric-[switchId]/path-[id]/vc-[id]
    -- sys/chassis-[id]/fabric-[switchId]/path-[id]/vc-[id]
    -- sys/fex-[id]/fabric-[switchId]/path-[id]/vc-[id]
    -- sys/chassis-[id]/blade-[slotId]/adaptor-[id]/mgmt/fabric-[switchId]/path-[id]/vc-[id]
    -- sys/rack-unit-[id]/adaptor-[id]/mgmt/fabric-[switchId]/path-[id]/vc-[id]
    -- sys/chassis-[id]/cartridge-[slotId]/server-[serverInstanceId]/adaptor-[id]/mgmt/fabric-[switchId]/path-[id]/vc-[id]
    -- sys/chassis-[id]/cartridge-[slotId]/server-[serverInstanceId]/adaptor-[id]/mgmt/fabric-[switchId]/path-[id]/vc-[id]
    -- sys/chassis-[id]/blade-[slotId]/ext-board-[id]/boardController/mgmt/fabric-[switchId]/path-[id]/vc-[id]
    -- sys/rack-unit-[id]/ext-board-[id]/boardController/mgmt/fabric-[switchId]/path-[id]/vc-[id]
    -- sys/chassis-[id]/cartridge-[slotId]/server-[serverInstanceId]/ext-board-[id]/boardController/mgmt/fabric-[switchId]/path-[id]/vc-[id]
    -- sys/chassis-[id]/blade-[slotId]/boardController/mgmt/fabric-[switchId]/path-[id]/vc-[id]
    -- sys/rack-unit-[id]/boardController/mgmt/fabric-[switchId]/path-[id]/vc-[id]
    -- sys/chassis-[id]/cartridge-[slotId]/server-[serverInstanceId]/boardController/mgmt/fabric-[switchId]/path-[id]/vc-[id]
    -- sys/chassis-[id]/boardController/mgmt/fabric-[switchId]/path-[id]/vc-[id]
    -- sys/chassis-[id]/slot-[id]/boardController/mgmt/fabric-[switchId]/path-[id]/vc-[id]
    -- sys/chassis-[id]/blade-[slotId]/ext-board-[id]/mgmt/fabric-[switchId]/path-[id]/vc-[id]
    -- sys/rack-unit-[id]/ext-board-[id]/mgmt/fabric-[switchId]/path-[id]/vc-[id]
    -- sys/chassis-[id]/cartridge-[slotId]/server-[serverInstanceId]/ext-board-[id]/mgmt/fabric-[switchId]/path-[id]/vc-[id]
    -- sys/chassis-[id]/blade-[slotId]/mgmt/fabric-[switchId]/path-[id]/vc-[id]
    -- sys/rack-unit-[id]/mgmt/fabric-[switchId]/path-[id]/vc-[id]
    -- sys/chassis-[id]/cartridge-[slotId]/server-[serverInstanceId]/mgmt/fabric-[switchId]/path-[id]/vc-[id]
    -- sys/chassis-[id]/cartridge-[slotId]/server-[serverInstanceId]/mgmt/fabric-[switchId]/path-[id]/vc-[id]
    -- sys/chassis-[id]/mgmt/fabric-[switchId]/path-[id]/vc-[id]
    -- sys/fex-[id]/mgmt/fabric-[switchId]/path-[id]/vc-[id]
    -- sys/chassis-[id]/slot-[id]/mgmt/fabric-[switchId]/path-[id]/vc-[id]
    -- sys/fex-[id]/slot-[id]/mgmt/fabric-[switchId]/path-[id]/vc-[id]
    -- sys/chassis-[id]/shared-io-module/mgmt/fabric-[switchId]/path-[id]/vc-[id]
    -- sys/chassis-[id]/slot-[id]/shared-io-module/mgmt/fabric-[switchId]/path-[id]/vc-[id]
    -- sys/chassis-[id]/sw-slot-[id]/mgmt/fabric-[switchId]/path-[id]/vc-[id]
    -- sys/chassis-[id]/slot-[id]/mgmt/fabric-[switchId]/path-[id]/vc-[id]
    -- sys/switch-[id]/mgmt/fabric-[switchId]/path-[id]/vc-[id]
    -- sys/chassis-[id]/blade-[slotId]/board/storage-[type]-[id]/mgmt/fabric-[switchId]/path-[id]/vc-[id]
    -- sys/rack-unit-[id]/board/storage-[type]-[id]/mgmt/fabric-[switchId]/path-[id]/vc-[id]
    -- sys/chassis-[id]/cartridge-[slotId]/server-[serverInstanceId]/board/storage-[type]-[id]/mgmt/fabric-[switchId]/path-[id]/vc-[id]
    -- sys/chassis-[id]/storage-[type]-[id]/mgmt/fabric-[switchId]/path-[id]/vc-[id]
    -- sys/chassis-[id]/blade-[slotId]/board/storage-[type]-[id]/disk-[id]/mgmt/fabric-[switchId]/path-[id]/vc-[id]
    -- sys/rack-unit-[id]/board/storage-[type]-[id]/disk-[id]/mgmt/fabric-[switchId]/path-[id]/vc-[id]
    -- sys/chassis-[id]/cartridge-[slotId]/server-[serverInstanceId]/board/storage-[type]-[id]/disk-[id]/mgmt/fabric-[switchId]/path-[id]/vc-[id]
    -- sys/chassis-[id]/storage-[type]-[id]/disk-[id]/mgmt/fabric-[switchId]/path-[id]/vc-[id]
    -- sys/chassis-[id]/blade-[slotId]/enc-[id]/disk-[id]/mgmt/fabric-[switchId]/path-[id]/vc-[id]
    -- sys/rack-unit-[id]/enc-[id]/disk-[id]/mgmt/fabric-[switchId]/path-[id]/vc-[id]
    -- sys/chassis-[id]/cartridge-[slotId]/server-[serverInstanceId]/enc-[id]/disk-[id]/mgmt/fabric-[switchId]/path-[id]/vc-[id]
    -- sys/chassis-[id]/enc-[id]/disk-[id]/mgmt/fabric-[switchId]/path-[id]/vc-[id]
    -- sys/chassis-[id]/blade-[slotId]/board/storage-[type]-[id]/enc-[id]/disk-[id]/mgmt/fabric-[switchId]/path-[id]/vc-[id]
    -- sys/rack-unit-[id]/board/storage-[type]-[id]/enc-[id]/disk-[id]/mgmt/fabric-[switchId]/path-[id]/vc-[id]
    -- sys/chassis-[id]/cartridge-[slotId]/server-[serverInstanceId]/board/storage-[type]-[id]/enc-[id]/disk-[id]/mgmt/fabric-[switchId]/path-[id]/vc-[id]
    -- sys/chassis-[id]/storage-[type]-[id]/enc-[id]/disk-[id]/mgmt/fabric-[switchId]/path-[id]/vc-[id]
    -- sys/chassis-[id]/blade-[slotId]/board/sas-expander-[id]/mgmt/fabric-[switchId]/path-[id]/vc-[id]
    -- sys/rack-unit-[id]/board/sas-expander-[id]/mgmt/fabric-[switchId]/path-[id]/vc-[id]
    -- sys/chassis-[id]/cartridge-[slotId]/server-[serverInstanceId]/board/sas-expander-[id]/mgmt/fabric-[switchId]/path-[id]/vc-[id]
    -- sys/chassis-[id]/sas-expander-[id]/mgmt/fabric-[switchId]/path-[id]/vc-[id]
    -- sys/mgmt/fabric-[switchId]/path-[id]/vc-[id]
    -- sys/switch-[id]/ethlanflowmon/vc-[id]
    -- sys/switch-[id]/lanmon-eth/mon-[name]/vc-[id]
    -- sys/switch-[id]/sanmon-fc/mon-[name]/vc-[id]
        -- fltDcxVcDown
        -- fltDcxVcMgmt-vif-down

-- storage:Controller
    -- sys/chassis-[id]/blade-[slotId]/board/storage-[type]-[id]
    -- sys/rack-unit-[id]/board/storage-[type]-[id]
    -- sys/chassis-[id]/cartridge-[slotId]/server-[serverInstanceId]/board/storage-[type]-[id]
    -- sys/chassis-[id]/storage-[type]-[id]
        -- fltStorageControllerPatrolReadFailed
        -- fltStorageControllerInoperable
        -- fltStorageControllerNot-supported
        -- fltStorageControllerDegraded
        -- fltStorageControllerNon-optimal

-- fabric:EthLan
    -- fabric/lan/[id]
        -- fltFabricEthLanNumOfVLANCompGrpExceedLimit

-- storage:Item
    -- sys/switch-[id]/stor-part-[name]
        -- fltStorageItemCapacityExceeded
        -- fltStorageItemCapacityWarning
        -- fltStorageItemFilesystemIssues

-- bios:Unit
    -- sys/chassis-[id]/blade-[slotId]/ext-board-[id]/bios
    -- sys/rack-unit-[id]/ext-board-[id]/bios
    -- sys/chassis-[id]/cartridge-[slotId]/server-[serverInstanceId]/ext-board-[id]/bios
    -- sys/chassis-[id]/blade-[slotId]/bios
    -- sys/rack-unit-[id]/bios
    -- sys/chassis-[id]/cartridge-[slotId]/server-[serverInstanceId]/bios
    -- sys/chassis-[id]/cartridge-[slotId]/server-[serverInstanceId]/bios
        -- fltBiosUnitFD0FailedSecurityVerification

-- vnic:ProfileSet
    -- fabric/lan/profiles
        -- fsmStFailVnicProfileSetDeploy:Local
        -- fsmStFailVnicProfileSetDeploy:Peer
        -- fsmStFailVnicProfileSetDeployAlias:Local
        -- fsmStFailVnicProfileSetDeployAlias:Peer
        -- fsmRmtErrVnicProfileSetDeploy:Local
        -- fsmRmtErrVnicProfileSetDeploy:Peer
        -- fsmRmtErrVnicProfileSetDeployAlias:Local
        -- fsmRmtErrVnicProfileSetDeployAlias:Peer
        -- fsmFailVnicProfileSetDeploy
        -- fsmFailVnicProfileSetDeployAlias

-- lsmaint:MaintPolicy
    -- org-[name]/maint-[name]
        -- fltLsmaintMaintPolicyUnresolvableScheduler

-- ether:PIo
    -- sys/chassis-[id]/slot-[id]/[type]/port-[portId]
    -- sys/fex-[id]/slot-[id]/[type]/port-[portId]
    -- sys/chassis-[id]/shared-io-module/[type]/port-[portId]
    -- sys/chassis-[id]/slot-[id]/shared-io-module/[type]/port-[portId]
    -- sys/switch-[id]/slot-[id]/[type]/port-[portId]
    -- sys/chassis-[id]/sw-slot-[id]/[type]/port-[portId]
    -- sys/chassis-[id]/slot-[id]/[type]/aggr-port-[aggrPortId]/port-[portId]
    -- sys/fex-[id]/slot-[id]/[type]/aggr-port-[aggrPortId]/port-[portId]
    -- sys/chassis-[id]/shared-io-module/[type]/aggr-port-[aggrPortId]/port-[portId]
    -- sys/chassis-[id]/slot-[id]/shared-io-module/[type]/aggr-port-[aggrPortId]/port-[portId]
    -- sys/switch-[id]/slot-[id]/[type]/aggr-port-[aggrPortId]/port-[portId]
    -- sys/chassis-[id]/sw-slot-[id]/[type]/aggr-port-[aggrPortId]/port-[portId]
        -- fltEtherPIoInvalid-sfp
        -- fltEtherPIoUnknownServerDevice
        -- fltEtherPIoInterfaceMismatch

-- processor:Unit
    -- sys/chassis-[id]/blade-[slotId]/board/cpu-[id]
    -- sys/rack-unit-[id]/board/cpu-[id]
    -- sys/chassis-[id]/cartridge-[slotId]/server-[serverInstanceId]/board/cpu-[id]
        -- fltProcessorUnitInoperable
        -- fltProcessorUnitThermalNonCritical
        -- fltProcessorUnitThermalThresholdCritical
        -- fltProcessorUnitThermalThresholdNonRecoverable
        -- fltProcessorUnitVoltageThresholdNonCritical
        -- fltProcessorUnitVoltageThresholdCritical
        -- fltProcessorUnitVoltageThresholdNonRecoverable
        -- fltProcessorUnitIdentity-unestablishable
        -- fltProcessorUnitDisabled

-- fabric:EthLanPcEp
    -- fabric/lan/[id]/pc-[portId]/ep-slot-[slotId]-port-[portId]
    -- fabric/server/sw-[id]/slot-[slotId]-aggr-port-[aggrPortId]/ep-slot-[slotId]-port-[portId]
    -- fabric/server/sw-[id]/pc-[portId]/slot-[slotId]-aggr-port-[aggrPortId]/ep-slot-[slotId]-port-[portId]
    -- fabric/eth-estc/[id]/slot-[slotId]-aggr-port-[aggrPortId]/ep-slot-[slotId]-port-[portId]
    -- fabric/eth-estc/[id]/pc-[portId]/slot-[slotId]-aggr-port-[aggrPortId]/ep-slot-[slotId]-port-[portId]
    -- fabric/lan/[id]/slot-[slotId]-aggr-port-[aggrPortId]/ep-slot-[slotId]-port-[portId]
    -- fabric/lan/[id]/pc-[portId]/slot-[slotId]-aggr-port-[aggrPortId]/ep-slot-[slotId]-port-[portId]
    -- fabric/lanmon/[id]/eth-mon-[name]/slot-[slotId]-aggr-port-[aggrPortId]/ep-slot-[slotId]-port-[portId]
    -- fabric/fc-estc/[id]/slot-[slotId]-aggr-port-[aggrPortId]/ep-slot-[slotId]-port-[portId]
    -- fabric/sanmon/[id]/fc-mon-[name]/slot-[slotId]-aggr-port-[aggrPortId]/ep-slot-[slotId]-port-[portId]
    -- fabric/san/[id]/slot-[slotId]-aggr-port-[aggrPortId]/ep-slot-[slotId]-port-[portId]
    -- fabric/san/[id]/fcoesanpc-[portId]/slot-[slotId]-aggr-port-[aggrPortId]/ep-slot-[slotId]-port-[portId]
        -- fltFabricEthLanPcEpDown
        -- fltFabricEthLanPcEpUdldLinkDown

-- policy:ControlledType
    -- sys/control-ep-[type]/ctrlled-type-[type]
    -- sys/control-ep-[type]/comm-ctrl/ctrlled-type-[type]
    -- sys/control-ep-[type]/cfg-backup-ctrl/ctrlled-type-[type]
    -- sys/control-ep-[type]/datetime-ctrl/ctrlled-type-[type]
    -- sys/control-ep-[type]/discovery-ctrl/ctrlled-type-[type]
    -- sys/control-ep-[type]/dns-ctrl/ctrlled-type-[type]
    -- sys/control-ep-[type]/equipment-ctrl/ctrlled-type-[type]
    -- sys/control-ep-[type]/fault-ctrl/ctrlled-type-[type]
    -- sys/control-ep-[type]/fabric-fw-ctrl/ctrlled-type-[type]
    -- sys/control-ep-[type]/mep-ctrl/ctrlled-type-[type]
    -- sys/control-ep-[type]/monitoring-ctrl/ctrlled-type-[type]
    -- sys/control-ep-[type]/portconfig-ctrl/ctrlled-type-[type]
    -- sys/control-ep-[type]/powermgmt-ctrl/ctrlled-type-[type]
    -- sys/control-ep-[type]/psu-ctrl/ctrlled-type-[type]
    -- sys/control-ep-[type]/security-ctrl/ctrlled-type-[type]
    -- sys/control-ep-[type]/storage-autoconfig-ctrl/ctrlled-type-[type]
        -- fsmStFailPolicyControlledTypeOperate:ResolveAll
        -- fsmRmtErrPolicyControlledTypeOperate:ResolveAll
        -- fsmFailPolicyControlledTypeOperate

-- observe:Observed
    -- extpol/reg/clients/client-[id]/observed-[dataSrcSysId]-[id]
    -- extpol/reg/controllers/contro-[id]/observed-[dataSrcSysId]-[id]
    -- extpol/reg/providers/prov-[type]/observed-[dataSrcSysId]-[id]
    -- extpol/reg/observed-[dataSrcSysId]-[id]
    -- observe/observed-[dataSrcSysId]-[id]
        -- fsmStFailObserveObservedResolvePolicyFsm:Execute
        -- fsmStFailObserveObservedResolveResourceFsm:Execute
        -- fsmStFailObserveObservedResolveVMFsm:Execute
        -- fsmStFailObserveObservedResolveControllerFsm:Execute
        -- fsmRmtErrObserveObservedResolvePolicyFsm:Execute
        -- fsmRmtErrObserveObservedResolveResourceFsm:Execute
        -- fsmRmtErrObserveObservedResolveVMFsm:Execute
        -- fsmRmtErrObserveObservedResolveControllerFsm:Execute
        -- fsmFailObserveObservedResolvePolicyFsm
        -- fsmFailObserveObservedResolveResourceFsm
        -- fsmFailObserveObservedResolveVMFsm
        -- fsmFailObserveObservedResolveControllerFsm

-- sysfile:Mutation
    -- sys/corefiles/file-[name]|[switchId]/mutation
    -- sys/corefiles/mutation
        -- fsmStFailSysfileMutationSingle:Execute
        -- fsmStFailSysfileMutationGlobal:Local
        -- fsmStFailSysfileMutationGlobal:Peer
        -- fsmRmtErrSysfileMutationSingle:Execute
        -- fsmRmtErrSysfileMutationGlobal:Local
        -- fsmRmtErrSysfileMutationGlobal:Peer
        -- fsmFailSysfileMutationSingle
        -- fsmFailSysfileMutationGlobal

-- mgmt:Connection
    -- sys/chassis-[id]/blade-[slotId]/adaptor-[id]/mgmt/mgmt-connection-[type]
    -- sys/rack-unit-[id]/adaptor-[id]/mgmt/mgmt-connection-[type]
    -- sys/chassis-[id]/cartridge-[slotId]/server-[serverInstanceId]/adaptor-[id]/mgmt/mgmt-connection-[type]
    -- sys/chassis-[id]/cartridge-[slotId]/server-[serverInstanceId]/adaptor-[id]/mgmt/mgmt-connection-[type]
    -- sys/chassis-[id]/blade-[slotId]/ext-board-[id]/boardController/mgmt/mgmt-connection-[type]
    -- sys/rack-unit-[id]/ext-board-[id]/boardController/mgmt/mgmt-connection-[type]
    -- sys/chassis-[id]/cartridge-[slotId]/server-[serverInstanceId]/ext-board-[id]/boardController/mgmt/mgmt-connection-[type]
    -- sys/chassis-[id]/blade-[slotId]/boardController/mgmt/mgmt-connection-[type]
    -- sys/rack-unit-[id]/boardController/mgmt/mgmt-connection-[type]
    -- sys/chassis-[id]/cartridge-[slotId]/server-[serverInstanceId]/boardController/mgmt/mgmt-connection-[type]
    -- sys/chassis-[id]/boardController/mgmt/mgmt-connection-[type]
    -- sys/chassis-[id]/slot-[id]/boardController/mgmt/mgmt-connection-[type]
    -- sys/chassis-[id]/blade-[slotId]/ext-board-[id]/mgmt/mgmt-connection-[type]
    -- sys/rack-unit-[id]/ext-board-[id]/mgmt/mgmt-connection-[type]
    -- sys/chassis-[id]/cartridge-[slotId]/server-[serverInstanceId]/ext-board-[id]/mgmt/mgmt-connection-[type]
    -- sys/chassis-[id]/blade-[slotId]/mgmt/mgmt-connection-[type]
    -- sys/rack-unit-[id]/mgmt/mgmt-connection-[type]
    -- sys/chassis-[id]/cartridge-[slotId]/server-[serverInstanceId]/mgmt/mgmt-connection-[type]
    -- sys/chassis-[id]/cartridge-[slotId]/server-[serverInstanceId]/mgmt/mgmt-connection-[type]
    -- sys/chassis-[id]/mgmt/mgmt-connection-[type]
    -- sys/fex-[id]/mgmt/mgmt-connection-[type]
    -- sys/chassis-[id]/slot-[id]/mgmt/mgmt-connection-[type]
    -- sys/fex-[id]/slot-[id]/mgmt/mgmt-connection-[type]
    -- sys/chassis-[id]/shared-io-module/mgmt/mgmt-connection-[type]
    -- sys/chassis-[id]/slot-[id]/shared-io-module/mgmt/mgmt-connection-[type]
    -- sys/chassis-[id]/sw-slot-[id]/mgmt/mgmt-connection-[type]
    -- sys/chassis-[id]/slot-[id]/mgmt/mgmt-connection-[type]
    -- sys/switch-[id]/mgmt/mgmt-connection-[type]
    -- sys/chassis-[id]/blade-[slotId]/board/storage-[type]-[id]/mgmt/mgmt-connection-[type]
    -- sys/rack-unit-[id]/board/storage-[type]-[id]/mgmt/mgmt-connection-[type]
    -- sys/chassis-[id]/cartridge-[slotId]/server-[serverInstanceId]/board/storage-[type]-[id]/mgmt/mgmt-connection-[type]
    -- sys/chassis-[id]/storage-[type]-[id]/mgmt/mgmt-connection-[type]
    -- sys/chassis-[id]/blade-[slotId]/board/storage-[type]-[id]/disk-[id]/mgmt/mgmt-connection-[type]
    -- sys/rack-unit-[id]/board/storage-[type]-[id]/disk-[id]/mgmt/mgmt-connection-[type]
    -- sys/chassis-[id]/cartridge-[slotId]/server-[serverInstanceId]/board/storage-[type]-[id]/disk-[id]/mgmt/mgmt-connection-[type]
    -- sys/chassis-[id]/storage-[type]-[id]/disk-[id]/mgmt/mgmt-connection-[type]
    -- sys/chassis-[id]/blade-[slotId]/enc-[id]/disk-[id]/mgmt/mgmt-connection-[type]
    -- sys/rack-unit-[id]/enc-[id]/disk-[id]/mgmt/mgmt-connection-[type]
    -- sys/chassis-[id]/cartridge-[slotId]/server-[serverInstanceId]/enc-[id]/disk-[id]/mgmt/mgmt-connection-[type]
    -- sys/chassis-[id]/enc-[id]/disk-[id]/mgmt/mgmt-connection-[type]
    -- sys/chassis-[id]/blade-[slotId]/board/storage-[type]-[id]/enc-[id]/disk-[id]/mgmt/mgmt-connection-[type]
    -- sys/rack-unit-[id]/board/storage-[type]-[id]/enc-[id]/disk-[id]/mgmt/mgmt-connection-[type]
    -- sys/chassis-[id]/cartridge-[slotId]/server-[serverInstanceId]/board/storage-[type]-[id]/enc-[id]/disk-[id]/mgmt/mgmt-connection-[type]
    -- sys/chassis-[id]/storage-[type]-[id]/enc-[id]/disk-[id]/mgmt/mgmt-connection-[type]
    -- sys/chassis-[id]/blade-[slotId]/board/sas-expander-[id]/mgmt/mgmt-connection-[type]
    -- sys/rack-unit-[id]/board/sas-expander-[id]/mgmt/mgmt-connection-[type]
    -- sys/chassis-[id]/cartridge-[slotId]/server-[serverInstanceId]/board/sas-expander-[id]/mgmt/mgmt-connection-[type]
    -- sys/chassis-[id]/sas-expander-[id]/mgmt/mgmt-connection-[type]
    -- sys/mgmt/mgmt-connection-[type]
        -- fltMgmtConnectionDisabled
        -- fltMgmtConnectionUnused
        -- fltMgmtConnectionUnsupportedConnectivity

-- policy:PolicyScopeCont
    -- extpol/reg/clients/client-[id]/scope-cont-[appType]
    -- extpol/reg/controllers/contro-[id]/scope-cont-[appType]
    -- extpol/reg/providers/prov-[type]/scope-cont-[appType]
    -- extpol/reg/scope-cont-[appType]
    -- policy-ep/scope-cont-[appType]
        -- fsmStFailPolicyPolicyScopeContReportPolicyFailFsm:ReportError
        -- fsmRmtErrPolicyPolicyScopeContReportPolicyFailFsm:ReportError
        -- fsmFailPolicyPolicyScopeContReportPolicyFailFsm

-- equipment:SystemIOController
    -- sys/chassis-[id]/slot-[id]
        -- fltEquipmentSystemIOControllerRemoved
        -- fltEquipmentSystemIOControllerThermalProblem
        -- fltEquipmentSystemIOControllerUnacknowledged
        -- fltEquipmentSystemIOControllerInoperable
        -- fsmStFailEquipmentSystemIOControllerResetCmc:Execute
        -- fsmRmtErrEquipmentSystemIOControllerResetCmc:Execute
        -- fsmFailEquipmentSystemIOControllerResetCmc

-- extvmm:Provider
    -- sys/extvm-mgmt/vm-[name]
        -- fsmStFailExtvmmProviderConfig:GetVersion
        -- fsmStFailExtvmmProviderConfig:SetLocal
        -- fsmStFailExtvmmProviderConfig:SetPeer
        -- fsmRmtErrExtvmmProviderConfig:GetVersion
        -- fsmRmtErrExtvmmProviderConfig:SetLocal
        -- fsmRmtErrExtvmmProviderConfig:SetPeer
        -- fsmFailExtvmmProviderConfig

-- sysdebug:ManualCoreFileExportTarget
    -- sys/corefiles/file-[name]|[switchId]/export-to-[hostname]
        -- fsmStFailSysdebugManualCoreFileExportTargetExport:Execute
        -- fsmRmtErrSysdebugManualCoreFileExportTargetExport:Execute
        -- fsmFailSysdebugManualCoreFileExportTargetExport

-- fabric:InternalPc
        -- fltFabricInternalPcDown

-- network:OperLevel
    -- sys/switch-[id]/oper-level
        -- fltNetworkOperLevelExtraprimaryvlans
        -- fltNetworkOperLevelExtrasecondaryvlans
        -- fltNetworkOperLevelExtravif

-- synthetic:FsObj
    -- sys/file-[name]
        -- fsmStFailSyntheticFsObjCreate:createLocal
        -- fsmStFailSyntheticFsObjCreate:createRemote
        -- fsmRmtErrSyntheticFsObjCreate:createLocal
        -- fsmRmtErrSyntheticFsObjCreate:createRemote
        -- fsmFailSyntheticFsObjCreate

-- sw:Phys
    -- sys/switch-[id]/phys
        -- fsmStFailSwPhysConfPhysical:ConfigSwA
        -- fsmStFailSwPhysConfPhysical:ConfigSwB
        -- fsmStFailSwPhysConfPhysical:PortInventorySwA
        -- fsmStFailSwPhysConfPhysical:PortInventorySwB
        -- fsmStFailSwPhysConfPhysical:VerifyPhysConfig
        -- fsmRmtErrSwPhysConfPhysical:ConfigSwA
        -- fsmRmtErrSwPhysConfPhysical:ConfigSwB
        -- fsmRmtErrSwPhysConfPhysical:PortInventorySwA
        -- fsmRmtErrSwPhysConfPhysical:PortInventorySwB
        -- fsmRmtErrSwPhysConfPhysical:VerifyPhysConfig
        -- fsmFailSwPhysConfPhysical

-- capability:Updater
    -- capabilities/ep/updater-[fileName]
        -- fsmStFailCapabilityUpdaterUpdater:Apply
        -- fsmStFailCapabilityUpdaterUpdater:CopyRemote
        -- fsmStFailCapabilityUpdaterUpdater:DeleteLocal
        -- fsmStFailCapabilityUpdaterUpdater:EvaluateStatus
        -- fsmStFailCapabilityUpdaterUpdater:Local
        -- fsmStFailCapabilityUpdaterUpdater:RescanImages
        -- fsmStFailCapabilityUpdaterUpdater:UnpackLocal
        -- fsmRmtErrCapabilityUpdaterUpdater:Apply
        -- fsmRmtErrCapabilityUpdaterUpdater:CopyRemote
        -- fsmRmtErrCapabilityUpdaterUpdater:DeleteLocal
        -- fsmRmtErrCapabilityUpdaterUpdater:EvaluateStatus
        -- fsmRmtErrCapabilityUpdaterUpdater:Local
        -- fsmRmtErrCapabilityUpdaterUpdater:RescanImages
        -- fsmRmtErrCapabilityUpdaterUpdater:UnpackLocal
        -- fsmFailCapabilityUpdaterUpdater

-- fabric:PooledVlan
    -- fabric/lan/[id]/net-group-[name]/net-[name]
    -- fabric/lan/net-group-[name]/net-[name]
        -- fltFabricPooledVlanNamedVlanUnresolved

-- ether:ServerIntFIo
    -- sys/chassis-[id]/blade-[slotId]/diag/port-[portId]
    -- sys/rack-unit-[id]/diag/port-[portId]
    -- sys/chassis-[id]/cartridge-[slotId]/server-[serverInstanceId]/diag/port-[portId]
    -- sys/chassis-[id]/cartridge-[slotId]/server-[serverInstanceId]/diag/port-[portId]
    -- sys/chassis-[id]/slot-[id]/[type]/port-[portId]
    -- sys/fex-[id]/slot-[id]/[type]/port-[portId]
    -- sys/chassis-[id]/shared-io-module/[type]/port-[portId]
    -- sys/chassis-[id]/slot-[id]/shared-io-module/[type]/port-[portId]
    -- sys/switch-[id]/slot-[id]/[type]/port-[portId]
    -- sys/chassis-[id]/sw-slot-[id]/[type]/port-[portId]
        -- fltEtherServerIntFIoHardware-failure
        -- fsmStFailEtherServerIntFIoConfigSpeed:Configure
        -- fsmStFailEtherServerIntFIoConfig:Configure
        -- fsmRmtErrEtherServerIntFIoConfigSpeed:Configure
        -- fsmRmtErrEtherServerIntFIoConfig:Configure
        -- fsmFailEtherServerIntFIoConfigSpeed
        -- fsmFailEtherServerIntFIoConfig

-- storage:EnclosureDiskSlotEp
    -- sys/chassis-[id]/blade-[slotId]/enc-[id]/disk-slot-[id]
    -- sys/rack-unit-[id]/enc-[id]/disk-slot-[id]
    -- sys/chassis-[id]/cartridge-[slotId]/server-[serverInstanceId]/enc-[id]/disk-slot-[id]
    -- sys/chassis-[id]/enc-[id]/disk-slot-[id]
    -- sys/chassis-[id]/blade-[slotId]/board/storage-[type]-[id]/enc-[id]/disk-slot-[id]
    -- sys/rack-unit-[id]/board/storage-[type]-[id]/enc-[id]/disk-slot-[id]
    -- sys/chassis-[id]/cartridge-[slotId]/server-[serverInstanceId]/board/storage-[type]-[id]/enc-[id]/disk-slot-[id]
    -- sys/chassis-[id]/storage-[type]-[id]/enc-[id]/disk-slot-[id]
        -- fltStorageEnclosureDiskSlotEpMissing
        -- fltStorageEnclosureDiskSlotEpEquipment-inoperable
        -- fltStorageEnclosureDiskSlotEpChassis-spare
        -- fltStorageEnclosureDiskSlotEpHotspare-unsupported
        -- fltStorageEnclosureDiskSlotEpSharing-unsupported
        -- fltStorageEnclosureDiskSlotEpIoe-ownership-unassigned
        -- fltStorageEnclosureDiskSlotEpHddslot-server2-ownership-unassigned
        -- fltStorageEnclosureDiskSlotEpSecond-controller-absent

-- firmware:Updatable
    -- sys/chassis-[id]/blade-[slotId]/ext-board-[id]/bios/fw-updatable
    -- sys/rack-unit-[id]/ext-board-[id]/bios/fw-updatable
    -- sys/chassis-[id]/cartridge-[slotId]/server-[serverInstanceId]/ext-board-[id]/bios/fw-updatable
    -- sys/chassis-[id]/blade-[slotId]/bios/fw-updatable
    -- sys/rack-unit-[id]/bios/fw-updatable
    -- sys/chassis-[id]/cartridge-[slotId]/server-[serverInstanceId]/bios/fw-updatable
    -- sys/chassis-[id]/cartridge-[slotId]/server-[serverInstanceId]/bios/fw-updatable
    -- sys/rack-unit-[id]/psu-[id]/fw-updatable
    -- sys/chassis-[id]/psu-[id]/fw-updatable
    -- sys/fex-[id]/psu-[id]/fw-updatable
    -- sys/rack-enclosure-[id]/psu-[id]/fw-updatable
    -- sys/switch-[id]/psu-[id]/fw-updatable
    -- sys/chassis-[id]/blade-[slotId]/adaptor-[id]/mgmt/fw-updatable
    -- sys/rack-unit-[id]/adaptor-[id]/mgmt/fw-updatable
    -- sys/chassis-[id]/cartridge-[slotId]/server-[serverInstanceId]/adaptor-[id]/mgmt/fw-updatable
    -- sys/chassis-[id]/cartridge-[slotId]/server-[serverInstanceId]/adaptor-[id]/mgmt/fw-updatable
    -- sys/chassis-[id]/blade-[slotId]/ext-board-[id]/boardController/mgmt/fw-updatable
    -- sys/rack-unit-[id]/ext-board-[id]/boardController/mgmt/fw-updatable
    -- sys/chassis-[id]/cartridge-[slotId]/server-[serverInstanceId]/ext-board-[id]/boardController/mgmt/fw-updatable
    -- sys/chassis-[id]/blade-[slotId]/boardController/mgmt/fw-updatable
    -- sys/rack-unit-[id]/boardController/mgmt/fw-updatable
    -- sys/chassis-[id]/cartridge-[slotId]/server-[serverInstanceId]/boardController/mgmt/fw-updatable
    -- sys/chassis-[id]/boardController/mgmt/fw-updatable
    -- sys/chassis-[id]/slot-[id]/boardController/mgmt/fw-updatable
    -- sys/chassis-[id]/blade-[slotId]/ext-board-[id]/mgmt/fw-updatable
    -- sys/rack-unit-[id]/ext-board-[id]/mgmt/fw-updatable
    -- sys/chassis-[id]/cartridge-[slotId]/server-[serverInstanceId]/ext-board-[id]/mgmt/fw-updatable
    -- sys/chassis-[id]/blade-[slotId]/mgmt/fw-updatable
    -- sys/rack-unit-[id]/mgmt/fw-updatable
    -- sys/chassis-[id]/cartridge-[slotId]/server-[serverInstanceId]/mgmt/fw-updatable
    -- sys/chassis-[id]/cartridge-[slotId]/server-[serverInstanceId]/mgmt/fw-updatable
    -- sys/chassis-[id]/mgmt/fw-updatable
    -- sys/fex-[id]/mgmt/fw-updatable
    -- sys/chassis-[id]/slot-[id]/mgmt/fw-updatable
    -- sys/fex-[id]/slot-[id]/mgmt/fw-updatable
    -- sys/chassis-[id]/shared-io-module/mgmt/fw-updatable
    -- sys/chassis-[id]/slot-[id]/shared-io-module/mgmt/fw-updatable
    -- sys/chassis-[id]/sw-slot-[id]/mgmt/fw-updatable
    -- sys/chassis-[id]/slot-[id]/mgmt/fw-updatable
    -- sys/switch-[id]/mgmt/fw-updatable
    -- sys/chassis-[id]/blade-[slotId]/board/storage-[type]-[id]/mgmt/fw-updatable
    -- sys/rack-unit-[id]/board/storage-[type]-[id]/mgmt/fw-updatable
    -- sys/chassis-[id]/cartridge-[slotId]/server-[serverInstanceId]/board/storage-[type]-[id]/mgmt/fw-updatable
    -- sys/chassis-[id]/storage-[type]-[id]/mgmt/fw-updatable
    -- sys/chassis-[id]/blade-[slotId]/board/storage-[type]-[id]/disk-[id]/mgmt/fw-updatable
    -- sys/rack-unit-[id]/board/storage-[type]-[id]/disk-[id]/mgmt/fw-updatable
    -- sys/chassis-[id]/cartridge-[slotId]/server-[serverInstanceId]/board/storage-[type]-[id]/disk-[id]/mgmt/fw-updatable
    -- sys/chassis-[id]/storage-[type]-[id]/disk-[id]/mgmt/fw-updatable
    -- sys/chassis-[id]/blade-[slotId]/enc-[id]/disk-[id]/mgmt/fw-updatable
    -- sys/rack-unit-[id]/enc-[id]/disk-[id]/mgmt/fw-updatable
    -- sys/chassis-[id]/cartridge-[slotId]/server-[serverInstanceId]/enc-[id]/disk-[id]/mgmt/fw-updatable
    -- sys/chassis-[id]/enc-[id]/disk-[id]/mgmt/fw-updatable
    -- sys/chassis-[id]/blade-[slotId]/board/storage-[type]-[id]/enc-[id]/disk-[id]/mgmt/fw-updatable
    -- sys/rack-unit-[id]/board/storage-[type]-[id]/enc-[id]/disk-[id]/mgmt/fw-updatable
    -- sys/chassis-[id]/cartridge-[slotId]/server-[serverInstanceId]/board/storage-[type]-[id]/enc-[id]/disk-[id]/mgmt/fw-updatable
    -- sys/chassis-[id]/storage-[type]-[id]/enc-[id]/disk-[id]/mgmt/fw-updatable
    -- sys/chassis-[id]/blade-[slotId]/board/sas-expander-[id]/mgmt/fw-updatable
    -- sys/rack-unit-[id]/board/sas-expander-[id]/mgmt/fw-updatable
    -- sys/chassis-[id]/cartridge-[slotId]/server-[serverInstanceId]/board/sas-expander-[id]/mgmt/fw-updatable
    -- sys/chassis-[id]/sas-expander-[id]/mgmt/fw-updatable
    -- sys/mgmt/fw-updatable
    -- sys/chassis-[id]/blade-[slotId]/board/storage-[type]-[id]/onboard-device-[deviceType]-[id]/fw-updatable
    -- sys/rack-unit-[id]/board/storage-[type]-[id]/onboard-device-[deviceType]-[id]/fw-updatable
    -- sys/chassis-[id]/cartridge-[slotId]/server-[serverInstanceId]/board/storage-[type]-[id]/onboard-device-[deviceType]-[id]/fw-updatable
    -- sys/chassis-[id]/storage-[type]-[id]/onboard-device-[deviceType]-[id]/fw-updatable
    -- sys/chassis-[id]/blade-[slotId]/board/sas-expander-[id]/onboard-device-[deviceType]-[id]/fw-updatable
    -- sys/rack-unit-[id]/board/sas-expander-[id]/onboard-device-[deviceType]-[id]/fw-updatable
    -- sys/chassis-[id]/cartridge-[slotId]/server-[serverInstanceId]/board/sas-expander-[id]/onboard-device-[deviceType]-[id]/fw-updatable
    -- sys/chassis-[id]/sas-expander-[id]/onboard-device-[deviceType]-[id]/fw-updatable
        -- fltFirmwareUpdatableImageUnusable

-- mgmt:Controller
    -- sys/chassis-[id]/blade-[slotId]/adaptor-[id]/mgmt
    -- sys/rack-unit-[id]/adaptor-[id]/mgmt
    -- sys/chassis-[id]/cartridge-[slotId]/server-[serverInstanceId]/adaptor-[id]/mgmt
    -- sys/chassis-[id]/cartridge-[slotId]/server-[serverInstanceId]/adaptor-[id]/mgmt
    -- sys/chassis-[id]/blade-[slotId]/ext-board-[id]/boardController/mgmt
    -- sys/rack-unit-[id]/ext-board-[id]/boardController/mgmt
    -- sys/chassis-[id]/cartridge-[slotId]/server-[serverInstanceId]/ext-board-[id]/boardController/mgmt
    -- sys/chassis-[id]/blade-[slotId]/boardController/mgmt
    -- sys/rack-unit-[id]/boardController/mgmt
    -- sys/chassis-[id]/cartridge-[slotId]/server-[serverInstanceId]/boardController/mgmt
    -- sys/chassis-[id]/boardController/mgmt
    -- sys/chassis-[id]/slot-[id]/boardController/mgmt
    -- sys/chassis-[id]/blade-[slotId]/ext-board-[id]/mgmt
    -- sys/rack-unit-[id]/ext-board-[id]/mgmt
    -- sys/chassis-[id]/cartridge-[slotId]/server-[serverInstanceId]/ext-board-[id]/mgmt
    -- sys/chassis-[id]/blade-[slotId]/mgmt
    -- sys/rack-unit-[id]/mgmt
    -- sys/chassis-[id]/cartridge-[slotId]/server-[serverInstanceId]/mgmt
    -- sys/chassis-[id]/cartridge-[slotId]/server-[serverInstanceId]/mgmt
    -- sys/chassis-[id]/mgmt
    -- sys/fex-[id]/mgmt
    -- sys/chassis-[id]/slot-[id]/mgmt
    -- sys/fex-[id]/slot-[id]/mgmt
    -- sys/chassis-[id]/shared-io-module/mgmt
    -- sys/chassis-[id]/slot-[id]/shared-io-module/mgmt
    -- sys/chassis-[id]/sw-slot-[id]/mgmt
    -- sys/chassis-[id]/slot-[id]/mgmt
    -- sys/switch-[id]/mgmt
    -- sys/chassis-[id]/blade-[slotId]/board/storage-[type]-[id]/mgmt
    -- sys/rack-unit-[id]/board/storage-[type]-[id]/mgmt
    -- sys/chassis-[id]/cartridge-[slotId]/server-[serverInstanceId]/board/storage-[type]-[id]/mgmt
    -- sys/chassis-[id]/storage-[type]-[id]/mgmt
    -- sys/chassis-[id]/blade-[slotId]/board/storage-[type]-[id]/disk-[id]/mgmt
    -- sys/rack-unit-[id]/board/storage-[type]-[id]/disk-[id]/mgmt
    -- sys/chassis-[id]/cartridge-[slotId]/server-[serverInstanceId]/board/storage-[type]-[id]/disk-[id]/mgmt
    -- sys/chassis-[id]/storage-[type]-[id]/disk-[id]/mgmt
    -- sys/chassis-[id]/blade-[slotId]/enc-[id]/disk-[id]/mgmt
    -- sys/rack-unit-[id]/enc-[id]/disk-[id]/mgmt
    -- sys/chassis-[id]/cartridge-[slotId]/server-[serverInstanceId]/enc-[id]/disk-[id]/mgmt
    -- sys/chassis-[id]/enc-[id]/disk-[id]/mgmt
    -- sys/chassis-[id]/blade-[slotId]/board/storage-[type]-[id]/enc-[id]/disk-[id]/mgmt
    -- sys/rack-unit-[id]/board/storage-[type]-[id]/enc-[id]/disk-[id]/mgmt
    -- sys/chassis-[id]/cartridge-[slotId]/server-[serverInstanceId]/board/storage-[type]-[id]/enc-[id]/disk-[id]/mgmt
    -- sys/chassis-[id]/storage-[type]-[id]/enc-[id]/disk-[id]/mgmt
    -- sys/chassis-[id]/blade-[slotId]/board/sas-expander-[id]/mgmt
    -- sys/rack-unit-[id]/board/sas-expander-[id]/mgmt
    -- sys/chassis-[id]/cartridge-[slotId]/server-[serverInstanceId]/board/sas-expander-[id]/mgmt
    -- sys/chassis-[id]/sas-expander-[id]/mgmt
    -- sys/mgmt
        -- fltMgmtControllerUnsupportedDimmBlacklisting
        -- fsmStFailMgmtControllerExtMgmtIfConfig:Primary
        -- fsmStFailMgmtControllerExtMgmtIfConfig:Secondary
        -- fsmStFailMgmtControllerUpdateSwitch:resetLocal
        -- fsmStFailMgmtControllerUpdateSwitch:resetRemote
        -- fsmStFailMgmtControllerUpdateSwitch:updateLocal
        -- fsmStFailMgmtControllerUpdateSwitch:updateRemote
        -- fsmStFailMgmtControllerUpdateSwitch:updateSpLocal
        -- fsmStFailMgmtControllerUpdateSwitch:updateSpRemote
        -- fsmStFailMgmtControllerUpdateSwitch:verifyLocal
        -- fsmStFailMgmtControllerUpdateSwitch:verifyRemote
        -- fsmStFailMgmtControllerUpdateIOM:CopyIOMImgToSub
        -- fsmStFailMgmtControllerUpdateIOM:CopyImgFromRep
        -- fsmStFailMgmtControllerUpdateIOM:PollUpdateStatus
        -- fsmStFailMgmtControllerUpdateIOM:UpdateRequest
        -- fsmStFailMgmtControllerActivateIOM:Activate
        -- fsmStFailMgmtControllerActivateIOM:Reset
        -- fsmStFailMgmtControllerUpdateBMC:PollUpdateStatus
        -- fsmStFailMgmtControllerUpdateBMC:UpdateRequest
        -- fsmStFailMgmtControllerActivateBMC:Activate
        -- fsmStFailMgmtControllerActivateBMC:Reset
        -- fsmStFailMgmtControllerUpdateUCSManager:execute
        -- fsmStFailMgmtControllerUpdateUCSManager:start
        -- fsmStFailMgmtControllerSysConfig:Primary
        -- fsmStFailMgmtControllerSysConfig:Secondary
        -- fsmStFailMgmtControllerOnline:BmcConfigureConnLocal
        -- fsmStFailMgmtControllerOnline:BmcConfigureConnPeer
        -- fsmStFailMgmtControllerOnline:SwConfigureConnLocal
        -- fsmStFailMgmtControllerOnline:SwConfigureConnPeer
        -- fsmStFailMgmtControllerRegistryConfig:Remove
        -- fsmStFailMgmtControllerRegistryConfig:RemovePeer
        -- fsmStFailMgmtControllerExtMgmtInterfaceConfig:Active
        -- fsmStFailMgmtControllerExtMgmtInterfaceConfig:CIMCVlanCfgLocal
        -- fsmStFailMgmtControllerExtMgmtInterfaceConfig:CIMCVlanCfgPeer
        -- fsmStFailMgmtControllerExtMgmtInterfaceConfig:CMCVlanCfg
        -- fsmStFailMgmtControllerExtMgmtInterfaceConfig:CMCVlanCfgPeer
        -- fsmStFailMgmtControllerExtMgmtInterfaceConfig:StandbyCMCVlanCfg
        -- fsmStFailMgmtControllerLockConfig:PowerButtonLockConfig
        -- fsmStFailMgmtControllerPowerBudgetReclaimConfig:PowerOffReclaim
        -- fsmStFailMgmtControllerPowerBudgetReclaimConfig:PowerOffWait
        -- fsmStFailMgmtControllerUpdateCMC:PollUpdateStatus
        -- fsmStFailMgmtControllerUpdateCMC:UpdateRequest
        -- fsmStFailMgmtControllerActivateCMC:Activate
        -- fsmStFailMgmtControllerActivateCMC:PollActivation
        -- fsmStFailMgmtControllerActivateCMC:Reset
        -- fsmStFailMgmtControllerUpdateAdaptor:PollUpdateStatus
        -- fsmStFailMgmtControllerUpdateAdaptor:UpdateRequest
        -- fsmStFailMgmtControllerUpdateAdaptor:UpdateRequestPeer
        -- fsmStFailMgmtControllerActivateAdaptor:Activate
        -- fsmStFailMgmtControllerActivateAdaptor:ActivatePeer
        -- fsmStFailMgmtControllerActivateAdaptor:PollActivateStatus
        -- fsmStFailMgmtControllerActivateAdaptor:PowerOffServers
        -- fsmStFailMgmtControllerActivateAdaptor:PowerOnServers
        -- fsmStFailMgmtControllerActivateAdaptor:Reset
        -- fsmStFailMgmtControllerActivateAdaptor:ServersPowerOffCompletion
        -- fsmStFailMgmtControllerUpdateRaidController:Activate
        -- fsmStFailMgmtControllerUpdateRaidController:PollActivation
        -- fsmStFailMgmtControllerUpdateRaidController:PollUpdateStatus
        -- fsmStFailMgmtControllerUpdateRaidController:PowerOffServers
        -- fsmStFailMgmtControllerUpdateRaidController:PowerOnServers
        -- fsmStFailMgmtControllerUpdateRaidController:ServersPowerOffCompletion
        -- fsmStFailMgmtControllerUpdateRaidController:UpdateRequest
        -- fsmStFailMgmtControllerUpdateBoardController:PollUpdateStatus
        -- fsmStFailMgmtControllerUpdateBoardController:PowerOffServers
        -- fsmStFailMgmtControllerUpdateBoardController:PowerOnServers
        -- fsmStFailMgmtControllerUpdateBoardController:PrepareForUpdate
        -- fsmStFailMgmtControllerUpdateBoardController:ServersPowerOffCompletion
        -- fsmStFailMgmtControllerUpdateBoardController:UpdateRequest
        -- fsmStFailMgmtControllerPowerCap:Config
        -- fsmStFailMgmtControllerEnableSecureBoot:PollSecureBootStatus
        -- fsmStFailMgmtControllerEnableSecureBoot:PollUpdateStatus
        -- fsmStFailMgmtControllerEnableSecureBoot:Reset
        -- fsmStFailMgmtControllerEnableSecureBoot:UpdateRequest
        -- fsmStFailMgmtControllerUpdateColusaCMC:PollUpdateStatus
        -- fsmStFailMgmtControllerUpdateColusaCMC:UpdateRequest
        -- fsmStFailMgmtControllerActivateColusaCMC:Activate
        -- fsmStFailMgmtControllerActivateColusaCMC:PollActivation
        -- fsmStFailMgmtControllerActivateColusaCMC:Reset
        -- fsmStFailMgmtControllerUpdateColusaBoardController:PollUpdateStatus
        -- fsmStFailMgmtControllerUpdateColusaBoardController:PowerOffServers
        -- fsmStFailMgmtControllerUpdateColusaBoardController:PowerOnServers
        -- fsmStFailMgmtControllerUpdateColusaBoardController:PrepareForUpdate
        -- fsmStFailMgmtControllerUpdateColusaBoardController:ServersPowerOffCompletion
        -- fsmStFailMgmtControllerUpdateColusaBoardController:UpdateRequest
        -- fsmStFailMgmtControllerUpdateSasExpander:PollUpdateStatus
        -- fsmStFailMgmtControllerUpdateSasExpander:UpdateRequest
        -- fsmStFailMgmtControllerActivateSasExpander:Activate
        -- fsmStFailMgmtControllerActivateSasExpander:PollActivateStatus
        -- fsmStFailMgmtControllerActivateSasExpander:WaitForActivation
        -- fsmStFailMgmtControllerActivateLocalDisk:Activate
        -- fsmStFailMgmtControllerActivateLocalDisk:PollActivateStatus
        -- fsmStFailMgmtControllerUpdateUCSManagerSP:execute
        -- fsmStFailMgmtControllerUpdateUCSManagerSP:start
        -- fsmStFailMgmtControllerKvmCert:Config
        -- fsmStFailMgmtControllerKvmCert:ResetCimc
        -- fsmRmtErrMgmtControllerExtMgmtIfConfig:Primary
        -- fsmRmtErrMgmtControllerExtMgmtIfConfig:Secondary
        -- fsmRmtErrMgmtControllerUpdateSwitch:resetLocal
        -- fsmRmtErrMgmtControllerUpdateSwitch:resetRemote
        -- fsmRmtErrMgmtControllerUpdateSwitch:updateLocal
        -- fsmRmtErrMgmtControllerUpdateSwitch:updateRemote
        -- fsmRmtErrMgmtControllerUpdateSwitch:updateSpLocal
        -- fsmRmtErrMgmtControllerUpdateSwitch:updateSpRemote
        -- fsmRmtErrMgmtControllerUpdateSwitch:verifyLocal
        -- fsmRmtErrMgmtControllerUpdateSwitch:verifyRemote
        -- fsmRmtErrMgmtControllerUpdateIOM:CopyIOMImgToSub
        -- fsmRmtErrMgmtControllerUpdateIOM:CopyImgFromRep
        -- fsmRmtErrMgmtControllerUpdateIOM:PollUpdateStatus
        -- fsmRmtErrMgmtControllerUpdateIOM:UpdateRequest
        -- fsmRmtErrMgmtControllerActivateIOM:Activate
        -- fsmRmtErrMgmtControllerActivateIOM:Reset
        -- fsmRmtErrMgmtControllerUpdateBMC:PollUpdateStatus
        -- fsmRmtErrMgmtControllerUpdateBMC:UpdateRequest
        -- fsmRmtErrMgmtControllerActivateBMC:Activate
        -- fsmRmtErrMgmtControllerActivateBMC:Reset
        -- fsmRmtErrMgmtControllerUpdateUCSManager:execute
        -- fsmRmtErrMgmtControllerUpdateUCSManager:start
        -- fsmRmtErrMgmtControllerSysConfig:Primary
        -- fsmRmtErrMgmtControllerSysConfig:Secondary
        -- fsmRmtErrMgmtControllerOnline:BmcConfigureConnLocal
        -- fsmRmtErrMgmtControllerOnline:BmcConfigureConnPeer
        -- fsmRmtErrMgmtControllerOnline:SwConfigureConnLocal
        -- fsmRmtErrMgmtControllerOnline:SwConfigureConnPeer
        -- fsmRmtErrMgmtControllerRegistryConfig:Remove
        -- fsmRmtErrMgmtControllerRegistryConfig:RemovePeer
        -- fsmRmtErrMgmtControllerExtMgmtInterfaceConfig:Active
        -- fsmRmtErrMgmtControllerExtMgmtInterfaceConfig:CIMCVlanCfgLocal
        -- fsmRmtErrMgmtControllerExtMgmtInterfaceConfig:CIMCVlanCfgPeer
        -- fsmRmtErrMgmtControllerExtMgmtInterfaceConfig:CMCVlanCfg
        -- fsmRmtErrMgmtControllerExtMgmtInterfaceConfig:CMCVlanCfgPeer
        -- fsmRmtErrMgmtControllerExtMgmtInterfaceConfig:StandbyCMCVlanCfg
        -- fsmRmtErrMgmtControllerLockConfig:PowerButtonLockConfig
        -- fsmRmtErrMgmtControllerPowerBudgetReclaimConfig:PowerOffReclaim
        -- fsmRmtErrMgmtControllerPowerBudgetReclaimConfig:PowerOffWait
        -- fsmRmtErrMgmtControllerUpdateCMC:PollUpdateStatus
        -- fsmRmtErrMgmtControllerUpdateCMC:UpdateRequest
        -- fsmRmtErrMgmtControllerActivateCMC:Activate
        -- fsmRmtErrMgmtControllerActivateCMC:PollActivation
        -- fsmRmtErrMgmtControllerActivateCMC:Reset
        -- fsmRmtErrMgmtControllerUpdateAdaptor:PollUpdateStatus
        -- fsmRmtErrMgmtControllerUpdateAdaptor:UpdateRequest
        -- fsmRmtErrMgmtControllerUpdateAdaptor:UpdateRequestPeer
        -- fsmRmtErrMgmtControllerActivateAdaptor:Activate
        -- fsmRmtErrMgmtControllerActivateAdaptor:ActivatePeer
        -- fsmRmtErrMgmtControllerActivateAdaptor:PollActivateStatus
        -- fsmRmtErrMgmtControllerActivateAdaptor:PowerOffServers
        -- fsmRmtErrMgmtControllerActivateAdaptor:PowerOnServers
        -- fsmRmtErrMgmtControllerActivateAdaptor:Reset
        -- fsmRmtErrMgmtControllerActivateAdaptor:ServersPowerOffCompletion
        -- fsmRmtErrMgmtControllerUpdateRaidController:Activate
        -- fsmRmtErrMgmtControllerUpdateRaidController:PollActivation
        -- fsmRmtErrMgmtControllerUpdateRaidController:PollUpdateStatus
        -- fsmRmtErrMgmtControllerUpdateRaidController:PowerOffServers
        -- fsmRmtErrMgmtControllerUpdateRaidController:PowerOnServers
        -- fsmRmtErrMgmtControllerUpdateRaidController:ServersPowerOffCompletion
        -- fsmRmtErrMgmtControllerUpdateRaidController:UpdateRequest
        -- fsmRmtErrMgmtControllerUpdateBoardController:PollUpdateStatus
        -- fsmRmtErrMgmtControllerUpdateBoardController:PowerOffServers
        -- fsmRmtErrMgmtControllerUpdateBoardController:PowerOnServers
        -- fsmRmtErrMgmtControllerUpdateBoardController:PrepareForUpdate
        -- fsmRmtErrMgmtControllerUpdateBoardController:ServersPowerOffCompletion
        -- fsmRmtErrMgmtControllerUpdateBoardController:UpdateRequest
        -- fsmRmtErrMgmtControllerPowerCap:Config
        -- fsmRmtErrMgmtControllerEnableSecureBoot:PollSecureBootStatus
        -- fsmRmtErrMgmtControllerEnableSecureBoot:PollUpdateStatus
        -- fsmRmtErrMgmtControllerEnableSecureBoot:Reset
        -- fsmRmtErrMgmtControllerEnableSecureBoot:UpdateRequest
        -- fsmRmtErrMgmtControllerUpdateColusaCMC:PollUpdateStatus
        -- fsmRmtErrMgmtControllerUpdateColusaCMC:UpdateRequest
        -- fsmRmtErrMgmtControllerActivateColusaCMC:Activate
        -- fsmRmtErrMgmtControllerActivateColusaCMC:PollActivation
        -- fsmRmtErrMgmtControllerActivateColusaCMC:Reset
        -- fsmRmtErrMgmtControllerUpdateColusaBoardController:PollUpdateStatus
        -- fsmRmtErrMgmtControllerUpdateColusaBoardController:PowerOffServers
        -- fsmRmtErrMgmtControllerUpdateColusaBoardController:PowerOnServers
        -- fsmRmtErrMgmtControllerUpdateColusaBoardController:PrepareForUpdate
        -- fsmRmtErrMgmtControllerUpdateColusaBoardController:ServersPowerOffCompletion
        -- fsmRmtErrMgmtControllerUpdateColusaBoardController:UpdateRequest
        -- fsmRmtErrMgmtControllerUpdateSasExpander:PollUpdateStatus
        -- fsmRmtErrMgmtControllerUpdateSasExpander:UpdateRequest
        -- fsmRmtErrMgmtControllerActivateSasExpander:Activate
        -- fsmRmtErrMgmtControllerActivateSasExpander:PollActivateStatus
        -- fsmRmtErrMgmtControllerActivateSasExpander:WaitForActivation
        -- fsmRmtErrMgmtControllerActivateLocalDisk:Activate
        -- fsmRmtErrMgmtControllerActivateLocalDisk:PollActivateStatus
        -- fsmRmtErrMgmtControllerUpdateUCSManagerSP:execute
        -- fsmRmtErrMgmtControllerUpdateUCSManagerSP:start
        -- fsmRmtErrMgmtControllerKvmCert:Config
        -- fsmRmtErrMgmtControllerKvmCert:ResetCimc
        -- fsmFailMgmtControllerExtMgmtIfConfig
        -- fsmFailMgmtControllerUpdateSwitch
        -- fsmFailMgmtControllerUpdateIOM
        -- fsmFailMgmtControllerActivateIOM
        -- fsmFailMgmtControllerUpdateBMC
        -- fsmFailMgmtControllerActivateBMC
        -- fsmFailMgmtControllerUpdateUCSManager
        -- fsmFailMgmtControllerSysConfig
        -- fsmFailMgmtControllerOnline
        -- fsmFailMgmtControllerRegistryConfig
        -- fsmFailMgmtControllerExtMgmtInterfaceConfig
        -- fsmFailMgmtControllerLockConfig
        -- fsmFailMgmtControllerPowerBudgetReclaimConfig
        -- fsmFailMgmtControllerUpdateCMC
        -- fsmFailMgmtControllerActivateCMC
        -- fsmFailMgmtControllerUpdateAdaptor
        -- fsmFailMgmtControllerActivateAdaptor
        -- fsmFailMgmtControllerUpdateRaidController
        -- fsmFailMgmtControllerUpdateBoardController
        -- fsmFailMgmtControllerPowerCap
        -- fsmFailMgmtControllerEnableSecureBoot
        -- fsmFailMgmtControllerUpdateColusaCMC
        -- fsmFailMgmtControllerActivateColusaCMC
        -- fsmFailMgmtControllerUpdateColusaBoardController
        -- fsmFailMgmtControllerUpdateSasExpander
        -- fsmFailMgmtControllerActivateSasExpander
        -- fsmFailMgmtControllerActivateLocalDisk
        -- fsmFailMgmtControllerUpdateUCSManagerSP
        -- fsmFailMgmtControllerKvmCert

-- policy:PolicyScope
    -- extpol/reg/clients/client-[id]/scope-cont-[appType]/context-[name]/scope-[policyType]-[resolveType]-[policyName]
    -- extpol/reg/controllers/contro-[id]/scope-cont-[appType]/context-[name]/scope-[policyType]-[resolveType]-[policyName]
    -- extpol/reg/providers/prov-[type]/scope-cont-[appType]/context-[name]/scope-[policyType]-[resolveType]-[policyName]
    -- extpol/reg/scope-cont-[appType]/context-[name]/scope-[policyType]-[resolveType]-[policyName]
    -- policy-ep/scope-cont-[appType]/context-[name]/scope-[policyType]-[resolveType]-[policyName]
        -- fsmStFailPolicyPolicyScopeReleasePolicyFsm:Release
        -- fsmStFailPolicyPolicyScopeReleaseOperationFsm:Release
        -- fsmStFailPolicyPolicyScopeReleaseStorageFsm:Release
        -- fsmStFailPolicyPolicyScopeResolveManyPolicyFsm:ResolveMany
        -- fsmStFailPolicyPolicyScopeResolveManyOperationFsm:ResolveMany
        -- fsmStFailPolicyPolicyScopeResolveManyStorageFsm:ResolveMany
        -- fsmStFailPolicyPolicyScopeReleaseManyPolicyFsm:ReleaseMany
        -- fsmStFailPolicyPolicyScopeReleaseManyOperationFsm:ReleaseMany
        -- fsmStFailPolicyPolicyScopeReleaseManyStorageFsm:ReleaseMany
        -- fsmStFailPolicyPolicyScopeResolveAllPolicyFsm:ResolveAll
        -- fsmStFailPolicyPolicyScopeResolveAllOperationFsm:ResolveAll
        -- fsmStFailPolicyPolicyScopeResolveAllStorageFsm:ResolveAll
        -- fsmStFailPolicyPolicyScopeReleaseAllPolicyFsm:ReleaseAll
        -- fsmStFailPolicyPolicyScopeReleaseAllOperationFsm:ReleaseAll
        -- fsmStFailPolicyPolicyScopeReleaseAllStorageFsm:ReleaseAll
        -- fsmRmtErrPolicyPolicyScopeReleasePolicyFsm:Release
        -- fsmRmtErrPolicyPolicyScopeReleaseOperationFsm:Release
        -- fsmRmtErrPolicyPolicyScopeReleaseStorageFsm:Release
        -- fsmRmtErrPolicyPolicyScopeResolveManyPolicyFsm:ResolveMany
        -- fsmRmtErrPolicyPolicyScopeResolveManyOperationFsm:ResolveMany
        -- fsmRmtErrPolicyPolicyScopeResolveManyStorageFsm:ResolveMany
        -- fsmRmtErrPolicyPolicyScopeReleaseManyPolicyFsm:ReleaseMany
        -- fsmRmtErrPolicyPolicyScopeReleaseManyOperationFsm:ReleaseMany
        -- fsmRmtErrPolicyPolicyScopeReleaseManyStorageFsm:ReleaseMany
        -- fsmRmtErrPolicyPolicyScopeResolveAllPolicyFsm:ResolveAll
        -- fsmRmtErrPolicyPolicyScopeResolveAllOperationFsm:ResolveAll
        -- fsmRmtErrPolicyPolicyScopeResolveAllStorageFsm:ResolveAll
        -- fsmRmtErrPolicyPolicyScopeReleaseAllPolicyFsm:ReleaseAll
        -- fsmRmtErrPolicyPolicyScopeReleaseAllOperationFsm:ReleaseAll
        -- fsmRmtErrPolicyPolicyScopeReleaseAllStorageFsm:ReleaseAll
        -- fsmFailPolicyPolicyScopeReleasePolicyFsm
        -- fsmFailPolicyPolicyScopeReleaseOperationFsm
        -- fsmFailPolicyPolicyScopeReleaseStorageFsm
        -- fsmFailPolicyPolicyScopeResolveManyPolicyFsm
        -- fsmFailPolicyPolicyScopeResolveManyOperationFsm
        -- fsmFailPolicyPolicyScopeResolveManyStorageFsm
        -- fsmFailPolicyPolicyScopeReleaseManyPolicyFsm
        -- fsmFailPolicyPolicyScopeReleaseManyOperationFsm
        -- fsmFailPolicyPolicyScopeReleaseManyStorageFsm
        -- fsmFailPolicyPolicyScopeResolveAllPolicyFsm
        -- fsmFailPolicyPolicyScopeResolveAllOperationFsm
        -- fsmFailPolicyPolicyScopeResolveAllStorageFsm
        -- fsmFailPolicyPolicyScopeReleaseAllPolicyFsm
        -- fsmFailPolicyPolicyScopeReleaseAllOperationFsm
        -- fsmFailPolicyPolicyScopeReleaseAllStorageFsm

-- sw:ExtUtility
    -- sys/switch-[id]/ext
        -- fsmStFailSwExtUtilityConfPortBreakout:ConfigSwA
        -- fsmStFailSwExtUtilityConfPortBreakout:ConfigSwB
        -- fsmStFailSwExtUtilityConfPortBreakout:PortInventorySwA
        -- fsmStFailSwExtUtilityConfPortBreakout:PortInventorySwB
        -- fsmStFailSwExtUtilityConfPortBreakout:VerifyBreakoutConfig
        -- fsmRmtErrSwExtUtilityConfPortBreakout:ConfigSwA
        -- fsmRmtErrSwExtUtilityConfPortBreakout:ConfigSwB
        -- fsmRmtErrSwExtUtilityConfPortBreakout:PortInventorySwA
        -- fsmRmtErrSwExtUtilityConfPortBreakout:PortInventorySwB
        -- fsmRmtErrSwExtUtilityConfPortBreakout:VerifyBreakoutConfig
        -- fsmFailSwExtUtilityConfPortBreakout

-- fabric:FcEstcEp
    -- fabric/fc-estc/[id]/phys-fc-slot-[slotId]-port-[portId]
        -- fltFabricFcEstcEpFc-storage-port-invalid

-- ls:Server
    -- org-[name]/tier-[name]/ls-[name]
    -- org-[name]/ls-[name]
        -- fltLsServerFailed
        -- fltLsServerDiscoveryFailed
        -- fltLsServerConfigFailure
        -- fltLsServerMaintenanceFailed
        -- fltLsServerRemoved
        -- fltLsServerInaccessible
        -- fltLsServerAssociationFailed
        -- fltLsServerUnassociated
        -- fltLsServerServer-unfulfilled
        -- fltLsServerSvnicNotPresent
        -- fltLsServerFAULT
        -- fsmStFailLsServerConfigure:AnalyzeImpact
        -- fsmStFailLsServerConfigure:ApplyConfig
        -- fsmStFailLsServerConfigure:ApplyDefaultIdentifiers
        -- fsmStFailLsServerConfigure:ApplyIdentifiers
        -- fsmStFailLsServerConfigure:ApplyMaintConfig
        -- fsmStFailLsServerConfigure:ApplyPolicies
        -- fsmStFailLsServerConfigure:ApplyTemplate
        -- fsmStFailLsServerConfigure:CommitStorage
        -- fsmStFailLsServerConfigure:EstimateApplyConfig
        -- fsmStFailLsServerConfigure:EvaluateAssociation
        -- fsmStFailLsServerConfigure:ProvisionStorage
        -- fsmStFailLsServerConfigure:ResolveBootConfig
        -- fsmStFailLsServerConfigure:ResolveDefaultIdentifiers
        -- fsmStFailLsServerConfigure:ResolveDistributable
        -- fsmStFailLsServerConfigure:ResolveDistributableNames
        -- fsmStFailLsServerConfigure:ResolveIdentifiers
        -- fsmStFailLsServerConfigure:ResolveImages
        -- fsmStFailLsServerConfigure:ResolveNetworkPolicies
        -- fsmStFailLsServerConfigure:ResolveNetworkTemplates
        -- fsmStFailLsServerConfigure:ResolvePolicies
        -- fsmStFailLsServerConfigure:ResolveSchedule
        -- fsmStFailLsServerConfigure:ResolveStorageSchedule
        -- fsmStFailLsServerConfigure:ValidatePolicyOwnership
        -- fsmStFailLsServerConfigure:WaitForAssocCompletion
        -- fsmStFailLsServerConfigure:WaitForCommitStorage
        -- fsmStFailLsServerConfigure:WaitForMaintPermission
        -- fsmStFailLsServerConfigure:WaitForMaintWindow
        -- fsmStFailLsServerConfigure:WaitForStorageProvision
        -- fsmStFailLsServerConfigure:checkAssignedDefaultIdentifiersForDup
        -- fsmStFailLsServerConfigure:checkAssignedIdentifiersForDup
        -- fsmRmtErrLsServerConfigure:AnalyzeImpact
        -- fsmRmtErrLsServerConfigure:ApplyConfig
        -- fsmRmtErrLsServerConfigure:ApplyDefaultIdentifiers
        -- fsmRmtErrLsServerConfigure:ApplyIdentifiers
        -- fsmRmtErrLsServerConfigure:ApplyMaintConfig
        -- fsmRmtErrLsServerConfigure:ApplyPolicies
        -- fsmRmtErrLsServerConfigure:ApplyTemplate
        -- fsmRmtErrLsServerConfigure:CommitStorage
        -- fsmRmtErrLsServerConfigure:EstimateApplyConfig
        -- fsmRmtErrLsServerConfigure:EvaluateAssociation
        -- fsmRmtErrLsServerConfigure:ProvisionStorage
        -- fsmRmtErrLsServerConfigure:ResolveBootConfig
        -- fsmRmtErrLsServerConfigure:ResolveDefaultIdentifiers
        -- fsmRmtErrLsServerConfigure:ResolveDistributable
        -- fsmRmtErrLsServerConfigure:ResolveDistributableNames
        -- fsmRmtErrLsServerConfigure:ResolveIdentifiers
        -- fsmRmtErrLsServerConfigure:ResolveImages
        -- fsmRmtErrLsServerConfigure:ResolveNetworkPolicies
        -- fsmRmtErrLsServerConfigure:ResolveNetworkTemplates
        -- fsmRmtErrLsServerConfigure:ResolvePolicies
        -- fsmRmtErrLsServerConfigure:ResolveSchedule
        -- fsmRmtErrLsServerConfigure:ResolveStorageSchedule
        -- fsmRmtErrLsServerConfigure:ValidatePolicyOwnership
        -- fsmRmtErrLsServerConfigure:WaitForAssocCompletion
        -- fsmRmtErrLsServerConfigure:WaitForCommitStorage
        -- fsmRmtErrLsServerConfigure:WaitForMaintPermission
        -- fsmRmtErrLsServerConfigure:WaitForMaintWindow
        -- fsmRmtErrLsServerConfigure:WaitForStorageProvision
        -- fsmRmtErrLsServerConfigure:checkAssignedDefaultIdentifiersForDup
        -- fsmRmtErrLsServerConfigure:checkAssignedIdentifiersForDup
        -- fsmFailLsServerConfigure

-- fabric:FcSanPc
    -- fabric/san/[id]/pc-[portId]
        -- fltFabricFcSanPcIncompatibleSpeed
        -- fltFabricFcSanPcFc-portchannel-members-invalid

-- mgmt:HealthStatus
    -- sys/chassis-[id]/blade-[slotId]/adaptor-[id]/mgmt/health
    -- sys/rack-unit-[id]/adaptor-[id]/mgmt/health
    -- sys/chassis-[id]/cartridge-[slotId]/server-[serverInstanceId]/adaptor-[id]/mgmt/health
    -- sys/chassis-[id]/cartridge-[slotId]/server-[serverInstanceId]/adaptor-[id]/mgmt/health
    -- sys/chassis-[id]/blade-[slotId]/ext-board-[id]/boardController/mgmt/health
    -- sys/rack-unit-[id]/ext-board-[id]/boardController/mgmt/health
    -- sys/chassis-[id]/cartridge-[slotId]/server-[serverInstanceId]/ext-board-[id]/boardController/mgmt/health
    -- sys/chassis-[id]/blade-[slotId]/boardController/mgmt/health
    -- sys/rack-unit-[id]/boardController/mgmt/health
    -- sys/chassis-[id]/cartridge-[slotId]/server-[serverInstanceId]/boardController/mgmt/health
    -- sys/chassis-[id]/boardController/mgmt/health
    -- sys/chassis-[id]/slot-[id]/boardController/mgmt/health
    -- sys/chassis-[id]/blade-[slotId]/ext-board-[id]/mgmt/health
    -- sys/rack-unit-[id]/ext-board-[id]/mgmt/health
    -- sys/chassis-[id]/cartridge-[slotId]/server-[serverInstanceId]/ext-board-[id]/mgmt/health
    -- sys/chassis-[id]/blade-[slotId]/mgmt/health
    -- sys/rack-unit-[id]/mgmt/health
    -- sys/chassis-[id]/cartridge-[slotId]/server-[serverInstanceId]/mgmt/health
    -- sys/chassis-[id]/cartridge-[slotId]/server-[serverInstanceId]/mgmt/health
    -- sys/chassis-[id]/mgmt/health
    -- sys/fex-[id]/mgmt/health
    -- sys/chassis-[id]/slot-[id]/mgmt/health
    -- sys/fex-[id]/slot-[id]/mgmt/health
    -- sys/chassis-[id]/shared-io-module/mgmt/health
    -- sys/chassis-[id]/slot-[id]/shared-io-module/mgmt/health
    -- sys/chassis-[id]/sw-slot-[id]/mgmt/health
    -- sys/chassis-[id]/slot-[id]/mgmt/health
    -- sys/switch-[id]/mgmt/health
    -- sys/chassis-[id]/blade-[slotId]/board/storage-[type]-[id]/mgmt/health
    -- sys/rack-unit-[id]/board/storage-[type]-[id]/mgmt/health
    -- sys/chassis-[id]/cartridge-[slotId]/server-[serverInstanceId]/board/storage-[type]-[id]/mgmt/health
    -- sys/chassis-[id]/storage-[type]-[id]/mgmt/health
    -- sys/chassis-[id]/blade-[slotId]/board/storage-[type]-[id]/disk-[id]/mgmt/health
    -- sys/rack-unit-[id]/board/storage-[type]-[id]/disk-[id]/mgmt/health
    -- sys/chassis-[id]/cartridge-[slotId]/server-[serverInstanceId]/board/storage-[type]-[id]/disk-[id]/mgmt/health
    -- sys/chassis-[id]/storage-[type]-[id]/disk-[id]/mgmt/health
    -- sys/chassis-[id]/blade-[slotId]/enc-[id]/disk-[id]/mgmt/health
    -- sys/rack-unit-[id]/enc-[id]/disk-[id]/mgmt/health
    -- sys/chassis-[id]/cartridge-[slotId]/server-[serverInstanceId]/enc-[id]/disk-[id]/mgmt/health
    -- sys/chassis-[id]/enc-[id]/disk-[id]/mgmt/health
    -- sys/chassis-[id]/blade-[slotId]/board/storage-[type]-[id]/enc-[id]/disk-[id]/mgmt/health
    -- sys/rack-unit-[id]/board/storage-[type]-[id]/enc-[id]/disk-[id]/mgmt/health
    -- sys/chassis-[id]/cartridge-[slotId]/server-[serverInstanceId]/board/storage-[type]-[id]/enc-[id]/disk-[id]/mgmt/health
    -- sys/chassis-[id]/storage-[type]-[id]/enc-[id]/disk-[id]/mgmt/health
    -- sys/chassis-[id]/blade-[slotId]/board/sas-expander-[id]/mgmt/health
    -- sys/rack-unit-[id]/board/sas-expander-[id]/mgmt/health
    -- sys/chassis-[id]/cartridge-[slotId]/server-[serverInstanceId]/board/sas-expander-[id]/mgmt/health
    -- sys/chassis-[id]/sas-expander-[id]/mgmt/health
    -- sys/mgmt/health
    -- sys/switch-[id]/health
        -- fltMgmtHealthStatusHealthWarningIssue
        -- fltMgmtHealthStatusHealthMinorIssue
        -- fltMgmtHealthStatusHealthMajorIssue
        -- fltMgmtHealthStatusHealthCriticalIssue
        -- fltMgmtHealthStatusHealthInfoIssue

-- vnic:EtherIf
    -- fabric/lan/network-sets/fabric-network-[name]/fabric-network-def-[name]/vm-network-def-[name]/if-[name]
    -- fabric/lanmon/eth-flow-monitoring/flow-exporter-profile-[name]/if-[name]
    -- org-[name]/tier-[name]/ls-[name]/if-[name]
    -- org-[name]/ls-[name]/if-[name]
    -- org-[name]/tier-[name]/ls-[name]/ether-[name]/if-[name]
    -- org-[name]/ls-[name]/ether-[name]/if-[name]
    -- org-[name]/lan-conn-pol-[name]/ether-[name]/if-[name]
    -- org-[name]/tier-[name]/ls-[name]/ipc-[name]/if-[name]
    -- org-[name]/ls-[name]/ipc-[name]/if-[name]
    -- org-[name]/lan-conn-templ-[name]/if-[name]
    -- fabric/lan/profiles/vnic-[name]/if-[name]
        -- fltVnicEtherIfVlanAccessFault
        -- fltVnicEtherIfVlanUnresolvable
        -- fltVnicEtherIfInvalidVlan
        -- fltVnicEtherIfRemoteVlanUnresolvable

-- storage:IniGroup
    -- org-[name]/tier-[name]/ls-[name]/grp-[name]
    -- org-[name]/ls-[name]/grp-[name]
    -- org-[name]/san-conn-pol-[name]/grp-[name]
        -- fltStorageIniGroupSwitch-mode-disabled

-- vm:LifeCyclePolicy
    -- org-[name]/vm-lc-policy
        -- fsmStFailVmLifeCyclePolicyConfig:Local
        -- fsmStFailVmLifeCyclePolicyConfig:Peer
        -- fsmRmtErrVmLifeCyclePolicyConfig:Local
        -- fsmRmtErrVmLifeCyclePolicyConfig:Peer
        -- fsmFailVmLifeCyclePolicyConfig

-- equipment:Fan
    -- sys/rack-unit-[id]/fan-module-[tray]-[id]/fan-[id]
    -- sys/chassis-[id]/fan-module-[tray]-[id]/fan-[id]
    -- sys/rack-enclosure-[id]/fan-module-[tray]-[id]/fan-[id]
    -- sys/switch-[id]/fan-module-[tray]-[id]/fan-[id]
    -- sys/fex-[id]/fan-[id]
    -- sys/switch-[id]/fan-[id]
        -- fltEquipmentFanDegraded
        -- fltEquipmentFanInoperable
        -- fltEquipmentFanPerfThresholdNonCritical
        -- fltEquipmentFanPerfThresholdCritical
        -- fltEquipmentFanPerfThresholdNonRecoverable
        -- fltEquipmentFanMissing
        -- fltEquipmentFanPerfThresholdLowerNonRecoverable

-- fabric:PinTarget
        -- fltFabricPinTargetDown

-- firmware:System
    -- sys/fw-system
        -- fsmStFailFirmwareSystemDeploy:ActivateIOM
        -- fsmStFailFirmwareSystemDeploy:ActivateLocalFI
        -- fsmStFailFirmwareSystemDeploy:ActivateRemoteFI
        -- fsmStFailFirmwareSystemDeploy:ActivateUCSM
        -- fsmStFailFirmwareSystemDeploy:ActivateUCSMServicePack
        -- fsmStFailFirmwareSystemDeploy:CopyAllImagesToPeer
        -- fsmStFailFirmwareSystemDeploy:FabEvacOffRemoteFI
        -- fsmStFailFirmwareSystemDeploy:FabEvacOnRemoteFI
        -- fsmStFailFirmwareSystemDeploy:FailOverToRemoteFI
        -- fsmStFailFirmwareSystemDeploy:InternalBackup
        -- fsmStFailFirmwareSystemDeploy:PollActivateOfIOM
        -- fsmStFailFirmwareSystemDeploy:PollActivateOfLocalFI
        -- fsmStFailFirmwareSystemDeploy:PollActivateOfRemoteFI
        -- fsmStFailFirmwareSystemDeploy:PollActivateOfUCSM
        -- fsmStFailFirmwareSystemDeploy:PollActivateOfUCSMServicePack
        -- fsmStFailFirmwareSystemDeploy:PollFabEvacOffRemoteFI
        -- fsmStFailFirmwareSystemDeploy:PollFabEvacOnRemoteFI
        -- fsmStFailFirmwareSystemDeploy:PollFailOverToRemoteFI
        -- fsmStFailFirmwareSystemDeploy:PollInternalBackup
        -- fsmStFailFirmwareSystemDeploy:PollUpdateOfIOM
        -- fsmStFailFirmwareSystemDeploy:PollWaitForUserAck
        -- fsmStFailFirmwareSystemDeploy:ResolveDistributable
        -- fsmStFailFirmwareSystemDeploy:ResolveDistributableNames
        -- fsmStFailFirmwareSystemDeploy:ResolveImages
        -- fsmStFailFirmwareSystemDeploy:UpdateIOM
        -- fsmStFailFirmwareSystemDeploy:WaitForDeploy
        -- fsmStFailFirmwareSystemDeploy:WaitForUserAck
        -- fsmStFailFirmwareSystemDeploy:downloadImages
        -- fsmStFailFirmwareSystemApplyCatalogPack:ActivateCatalog
        -- fsmStFailFirmwareSystemApplyCatalogPack:ResolveDistributable
        -- fsmStFailFirmwareSystemApplyCatalogPack:ResolveDistributableNames
        -- fsmStFailFirmwareSystemApplyCatalogPack:ResolveImages
        -- fsmRmtErrFirmwareSystemDeploy:ActivateIOM
        -- fsmRmtErrFirmwareSystemDeploy:ActivateLocalFI
        -- fsmRmtErrFirmwareSystemDeploy:ActivateRemoteFI
        -- fsmRmtErrFirmwareSystemDeploy:ActivateUCSM
        -- fsmRmtErrFirmwareSystemDeploy:ActivateUCSMServicePack
        -- fsmRmtErrFirmwareSystemDeploy:CopyAllImagesToPeer
        -- fsmRmtErrFirmwareSystemDeploy:FabEvacOffRemoteFI
        -- fsmRmtErrFirmwareSystemDeploy:FabEvacOnRemoteFI
        -- fsmRmtErrFirmwareSystemDeploy:FailOverToRemoteFI
        -- fsmRmtErrFirmwareSystemDeploy:InternalBackup
        -- fsmRmtErrFirmwareSystemDeploy:PollActivateOfIOM
        -- fsmRmtErrFirmwareSystemDeploy:PollActivateOfLocalFI
        -- fsmRmtErrFirmwareSystemDeploy:PollActivateOfRemoteFI
        -- fsmRmtErrFirmwareSystemDeploy:PollActivateOfUCSM
        -- fsmRmtErrFirmwareSystemDeploy:PollActivateOfUCSMServicePack
        -- fsmRmtErrFirmwareSystemDeploy:PollFabEvacOffRemoteFI
        -- fsmRmtErrFirmwareSystemDeploy:PollFabEvacOnRemoteFI
        -- fsmRmtErrFirmwareSystemDeploy:PollFailOverToRemoteFI
        -- fsmRmtErrFirmwareSystemDeploy:PollInternalBackup
        -- fsmRmtErrFirmwareSystemDeploy:PollUpdateOfIOM
        -- fsmRmtErrFirmwareSystemDeploy:PollWaitForUserAck
        -- fsmRmtErrFirmwareSystemDeploy:ResolveDistributable
        -- fsmRmtErrFirmwareSystemDeploy:ResolveDistributableNames
        -- fsmRmtErrFirmwareSystemDeploy:ResolveImages
        -- fsmRmtErrFirmwareSystemDeploy:UpdateIOM
        -- fsmRmtErrFirmwareSystemDeploy:WaitForDeploy
        -- fsmRmtErrFirmwareSystemDeploy:WaitForUserAck
        -- fsmRmtErrFirmwareSystemDeploy:downloadImages
        -- fsmRmtErrFirmwareSystemApplyCatalogPack:ActivateCatalog
        -- fsmRmtErrFirmwareSystemApplyCatalogPack:ResolveDistributable
        -- fsmRmtErrFirmwareSystemApplyCatalogPack:ResolveDistributableNames
        -- fsmRmtErrFirmwareSystemApplyCatalogPack:ResolveImages
        -- fsmFailFirmwareSystemDeploy
        -- fsmFailFirmwareSystemApplyCatalogPack

-- vnic:FcIf
    -- org-[name]/tier-[name]/ls-[name]/fc-[name]/if-default
    -- org-[name]/ls-[name]/fc-[name]/if-default
    -- org-[name]/san-conn-pol-[name]/fc-[name]/if-default
    -- org-[name]/san-conn-templ-[name]/if-default
        -- fltVnicFcIfRemoteVsanUnresolvable

-- sysdebug:TechSupport
    -- sys/tech-support-files/tech-support-[creationTS]
        -- fsmStFailSysdebugTechSupportInitiate:Local
        -- fsmStFailSysdebugTechSupportDeleteTechSupFile:Local
        -- fsmStFailSysdebugTechSupportDeleteTechSupFile:peer
        -- fsmStFailSysdebugTechSupportDownload:CopyPrimary
        -- fsmStFailSysdebugTechSupportDownload:CopySub
        -- fsmStFailSysdebugTechSupportDownload:DeletePrimary
        -- fsmStFailSysdebugTechSupportDownload:DeleteSub
        -- fsmRmtErrSysdebugTechSupportInitiate:Local
        -- fsmRmtErrSysdebugTechSupportDeleteTechSupFile:Local
        -- fsmRmtErrSysdebugTechSupportDeleteTechSupFile:peer
        -- fsmRmtErrSysdebugTechSupportDownload:CopyPrimary
        -- fsmRmtErrSysdebugTechSupportDownload:CopySub
        -- fsmRmtErrSysdebugTechSupportDownload:DeletePrimary
        -- fsmRmtErrSysdebugTechSupportDownload:DeleteSub
        -- fsmFailSysdebugTechSupportInitiate
        -- fsmFailSysdebugTechSupportDeleteTechSupFile
        -- fsmFailSysdebugTechSupportDownload

-- extmgmt:ArpTargets
    -- sys/extmgmt-intf-monitor-policy/arp-target-policy
        -- fltExtmgmtArpTargetsArpTargetsNotValid

-- macpool:Pool
    -- org-[name]/mac-pool-[name]
        -- fltMacpoolPoolEmpty

-- mgmt:PmonEntry
    -- sys/mgmt-entity-[id]/[name]
        -- fltMgmtPmonEntryUCSM process failure

-- storage:MezzFlashLife
    -- sys/chassis-[id]/blade-[slotId]/board/storage-[type]-[id]/flash-life-
    -- sys/rack-unit-[id]/board/storage-[type]-[id]/flash-life-
    -- sys/chassis-[id]/cartridge-[slotId]/server-[serverInstanceId]/board/storage-[type]-[id]/flash-life-
    -- sys/chassis-[id]/storage-[type]-[id]/flash-life-
        -- fltStorageMezzFlashLifeConfiguration-error
        -- fltStorageMezzFlashLifeDegraded

-- fabric:FcoeSanEp
    -- fabric/san/[id]/phys-fcoesanep-slot-[slotId]-port-[portId]
    -- fabric/server/sw-[id]/slot-[slotId]-aggr-port-[aggrPortId]/phys-fcoesanep-slot-[slotId]-port-[portId]
    -- fabric/server/sw-[id]/pc-[portId]/slot-[slotId]-aggr-port-[aggrPortId]/phys-fcoesanep-slot-[slotId]-port-[portId]
    -- fabric/eth-estc/[id]/slot-[slotId]-aggr-port-[aggrPortId]/phys-fcoesanep-slot-[slotId]-port-[portId]
    -- fabric/eth-estc/[id]/pc-[portId]/slot-[slotId]-aggr-port-[aggrPortId]/phys-fcoesanep-slot-[slotId]-port-[portId]
    -- fabric/lan/[id]/slot-[slotId]-aggr-port-[aggrPortId]/phys-fcoesanep-slot-[slotId]-port-[portId]
    -- fabric/lan/[id]/pc-[portId]/slot-[slotId]-aggr-port-[aggrPortId]/phys-fcoesanep-slot-[slotId]-port-[portId]
    -- fabric/lanmon/[id]/eth-mon-[name]/slot-[slotId]-aggr-port-[aggrPortId]/phys-fcoesanep-slot-[slotId]-port-[portId]
    -- fabric/fc-estc/[id]/slot-[slotId]-aggr-port-[aggrPortId]/phys-fcoesanep-slot-[slotId]-port-[portId]
    -- fabric/sanmon/[id]/fc-mon-[name]/slot-[slotId]-aggr-port-[aggrPortId]/phys-fcoesanep-slot-[slotId]-port-[portId]
    -- fabric/san/[id]/slot-[slotId]-aggr-port-[aggrPortId]/phys-fcoesanep-slot-[slotId]-port-[portId]
    -- fabric/san/[id]/fcoesanpc-[portId]/slot-[slotId]-aggr-port-[aggrPortId]/phys-fcoesanep-slot-[slotId]-port-[portId]
        -- fltFabricFcoeSanEpDown
        -- fltFabricFcoeSanEpUnsupported
        -- fltFabricFcoeSanEpUdldLinkDown

-- firmware:Status
    -- sys/chassis-[id]/blade-[slotId]/fw-status
    -- sys/rack-unit-[id]/fw-status
    -- sys/chassis-[id]/cartridge-[slotId]/server-[serverInstanceId]/fw-status
    -- sys/chassis-[id]/fw-status
    -- sys/chassis-[id]/slot-[id]/fw-status
    -- sys/fex-[id]/slot-[id]/fw-status
    -- sys/rack-unit-[id]/psu-[id]/fw-status
    -- sys/chassis-[id]/psu-[id]/fw-status
    -- sys/fex-[id]/psu-[id]/fw-status
    -- sys/rack-enclosure-[id]/psu-[id]/fw-status
    -- sys/switch-[id]/psu-[id]/fw-status
    -- sys/switch-[id]/fw-status
    -- sys/fw-status
        -- fltFirmwareStatusCimcFirmwareMismatch
        -- fltFirmwareStatusPldFirmwareMismatch

-- extmgmt:NdiscTargets
    -- sys/extmgmt-intf-monitor-policy/ndisc-target-policy
        -- fltExtmgmtNdiscTargetsNdiscTargetsNotValid

-- adaptor:ExtEthIf
    -- sys/chassis-[id]/blade-[slotId]/adaptor-[id]/ext-eth-[id]
    -- sys/rack-unit-[id]/adaptor-[id]/ext-eth-[id]
    -- sys/chassis-[id]/cartridge-[slotId]/server-[serverInstanceId]/adaptor-[id]/ext-eth-[id]
    -- sys/chassis-[id]/cartridge-[slotId]/server-[serverInstanceId]/adaptor-[id]/ext-eth-[id]
        -- fltAdaptorExtEthIfMisConnect
        -- fltAdaptorExtEthIfMissing
        -- fltAdaptorExtEthIfUnsupportedConection
        -- fsmStFailAdaptorExtEthIfPathReset:Disable
        -- fsmStFailAdaptorExtEthIfPathReset:Enable
        -- fsmRmtErrAdaptorExtEthIfPathReset:Disable
        -- fsmRmtErrAdaptorExtEthIfPathReset:Enable
        -- fsmFailAdaptorExtEthIfPathReset

-- equipment:ChassisProfile
    -- org-[name]/cp-tier-[name]/cp-[name]
    -- org-[name]/cp-[name]
        -- fltEquipmentChassisProfileFailed
        -- fltEquipmentChassisProfileDiscoveryFailed
        -- fltEquipmentChassisProfileConfigFailure
        -- fltEquipmentChassisProfileRemoved
        -- fltEquipmentChassisProfileInaccessible
        -- fltEquipmentChassisProfileAssociationFailed
        -- fltEquipmentChassisProfileUnassociated
        -- fsmStFailEquipmentChassisProfileConfigure:AnalyzeImpact
        -- fsmStFailEquipmentChassisProfileConfigure:ApplyConfig
        -- fsmStFailEquipmentChassisProfileConfigure:ApplyPolicies
        -- fsmStFailEquipmentChassisProfileConfigure:ApplyTemplate
        -- fsmStFailEquipmentChassisProfileConfigure:EvaluateAssociation
        -- fsmStFailEquipmentChassisProfileConfigure:ResolveDistributable
        -- fsmStFailEquipmentChassisProfileConfigure:ResolveDistributableNames
        -- fsmStFailEquipmentChassisProfileConfigure:ResolveImages
        -- fsmStFailEquipmentChassisProfileConfigure:ResolvePolicies
        -- fsmStFailEquipmentChassisProfileConfigure:ResolveSchedule
        -- fsmStFailEquipmentChassisProfileConfigure:ValidatePolicyOwnership
        -- fsmStFailEquipmentChassisProfileConfigure:WaitForAssocCompletion
        -- fsmStFailEquipmentChassisProfileConfigure:WaitForMaintPermission
        -- fsmRmtErrEquipmentChassisProfileConfigure:AnalyzeImpact
        -- fsmRmtErrEquipmentChassisProfileConfigure:ApplyConfig
        -- fsmRmtErrEquipmentChassisProfileConfigure:ApplyPolicies
        -- fsmRmtErrEquipmentChassisProfileConfigure:ApplyTemplate
        -- fsmRmtErrEquipmentChassisProfileConfigure:EvaluateAssociation
        -- fsmRmtErrEquipmentChassisProfileConfigure:ResolveDistributable
        -- fsmRmtErrEquipmentChassisProfileConfigure:ResolveDistributableNames
        -- fsmRmtErrEquipmentChassisProfileConfigure:ResolveImages
        -- fsmRmtErrEquipmentChassisProfileConfigure:ResolvePolicies
        -- fsmRmtErrEquipmentChassisProfileConfigure:ResolveSchedule
        -- fsmRmtErrEquipmentChassisProfileConfigure:ValidatePolicyOwnership
        -- fsmRmtErrEquipmentChassisProfileConfigure:WaitForAssocCompletion
        -- fsmRmtErrEquipmentChassisProfileConfigure:WaitForMaintPermission
        -- fsmFailEquipmentChassisProfileConfigure

-- compute:RtcBattery
    -- sys/chassis-[id]/blade-[slotId]/board/rtc-battery
    -- sys/rack-unit-[id]/board/rtc-battery
    -- sys/chassis-[id]/cartridge-[slotId]/server-[serverInstanceId]/board/rtc-battery
        -- fltComputeRtcBatteryInoperable

-- compute:Board
    -- sys/chassis-[id]/blade-[slotId]/board
    -- sys/rack-unit-[id]/board
    -- sys/chassis-[id]/cartridge-[slotId]/server-[serverInstanceId]/board
        -- fltComputeBoardPowerError
        -- fltComputeBoardCmosVoltageThresholdCritical
        -- fltComputeBoardCmosVoltageThresholdNonRecoverable
        -- fltComputeBoardPowerFail
        -- fltComputeBoardFailedSecureFuseValidation

-- adaptor:ExtIf
        -- fltAdaptorExtIfLink-down

-- fabric:VlanGroupReq
    -- org-[name]/vlan-group-req-[name]
        -- fltFabricVlanGroupReqVlanGroupPermitUnresolved

-- adaptor:HostIf
        -- fltAdaptorHostIfLink-down

-- fabric:FcSanPcEp
    -- fabric/san/[id]/pc-[portId]/ep-slot-[slotId]-port-[portId]
        -- fltFabricFcSanPcEpDown
        -- fltFabricFcSanPcEpIncompatibleSpeed

-- fabric:EpMgr
    -- fabric/[id]
        -- fltFabricEpMgrEpTransModeFail
        -- fsmStFailFabricEpMgrConfigure:ApplyConfig
        -- fsmStFailFabricEpMgrConfigure:ApplyPhysical
        -- fsmStFailFabricEpMgrConfigure:ValidateConfiguration
        -- fsmStFailFabricEpMgrConfigure:WaitOnPhys
        -- fsmRmtErrFabricEpMgrConfigure:ApplyConfig
        -- fsmRmtErrFabricEpMgrConfigure:ApplyPhysical
        -- fsmRmtErrFabricEpMgrConfigure:ValidateConfiguration
        -- fsmRmtErrFabricEpMgrConfigure:WaitOnPhys
        -- fsmFailFabricEpMgrConfigure

-- fabric:ComputeMSlotEp
    -- fabric/server/chassis-[chassisId]/cart-slot-[slotId]/ins-[serverInstanceId]
        -- fltFabricComputeMSlotEpMisplacedInChassisSlot
        -- fltFabricComputeMSlotEpServerIdentificationProblem
        -- fsmStFailFabricComputeMSlotEpIdentify:ExecuteLocal
        -- fsmStFailFabricComputeMSlotEpIdentify:ExecutePeer
        -- fsmRmtErrFabricComputeMSlotEpIdentify:ExecuteLocal
        -- fsmRmtErrFabricComputeMSlotEpIdentify:ExecutePeer
        -- fsmFailFabricComputeMSlotEpIdentify

-- firmware:AutoSyncPolicy
    -- org-[name]/fw-auto-sync
        -- fltFirmwareAutoSyncPolicyDefaultHostPackageMissing
        -- fltFirmwareAutoSyncPolicyDefaultHostPackageMissingVersions

-- fabric:FcoeSanPcEp
    -- fabric/san/[id]/fcoesanpc-[portId]/fcoesanpcep-slot-[slotId]-port-[portId]
    -- fabric/server/sw-[id]/slot-[slotId]-aggr-port-[aggrPortId]/fcoesanpcep-slot-[slotId]-port-[portId]
    -- fabric/server/sw-[id]/pc-[portId]/slot-[slotId]-aggr-port-[aggrPortId]/fcoesanpcep-slot-[slotId]-port-[portId]
    -- fabric/eth-estc/[id]/slot-[slotId]-aggr-port-[aggrPortId]/fcoesanpcep-slot-[slotId]-port-[portId]
    -- fabric/eth-estc/[id]/pc-[portId]/slot-[slotId]-aggr-port-[aggrPortId]/fcoesanpcep-slot-[slotId]-port-[portId]
    -- fabric/lan/[id]/slot-[slotId]-aggr-port-[aggrPortId]/fcoesanpcep-slot-[slotId]-port-[portId]
    -- fabric/lan/[id]/pc-[portId]/slot-[slotId]-aggr-port-[aggrPortId]/fcoesanpcep-slot-[slotId]-port-[portId]
    -- fabric/lanmon/[id]/eth-mon-[name]/slot-[slotId]-aggr-port-[aggrPortId]/fcoesanpcep-slot-[slotId]-port-[portId]
    -- fabric/fc-estc/[id]/slot-[slotId]-aggr-port-[aggrPortId]/fcoesanpcep-slot-[slotId]-port-[portId]
    -- fabric/sanmon/[id]/fc-mon-[name]/slot-[slotId]-aggr-port-[aggrPortId]/fcoesanpcep-slot-[slotId]-port-[portId]
    -- fabric/san/[id]/slot-[slotId]-aggr-port-[aggrPortId]/fcoesanpcep-slot-[slotId]-port-[portId]
    -- fabric/san/[id]/fcoesanpc-[portId]/slot-[slotId]-aggr-port-[aggrPortId]/fcoesanpcep-slot-[slotId]-port-[portId]
        -- fltFabricFcoeSanPcEpDown
        -- fltFabricFcoeSanPcEpUdldLinkDown

-- aaa:Config
        -- fltAaaConfigServergroup

-- equipment:IOCardBase
        -- fsmStFailEquipmentIOCardBaseFePresence:CheckLicense
        -- fsmStFailEquipmentIOCardBaseFePresence:ConfigChassisId
        -- fsmStFailEquipmentIOCardBaseFePresence:Identify
        -- fsmStFailEquipmentIOCardBaseFeConn:ConfigureEndPoint
        -- fsmStFailEquipmentIOCardBaseFeConn:ConfigureSwMgmtEndPoint
        -- fsmStFailEquipmentIOCardBaseFeConn:ConfigureVifNs
        -- fsmStFailEquipmentIOCardBaseFeConn:DiscoverChassis
        -- fsmStFailEquipmentIOCardBaseFeConn:EnableChassis
        -- fsmRmtErrEquipmentIOCardBaseFePresence:CheckLicense
        -- fsmRmtErrEquipmentIOCardBaseFePresence:ConfigChassisId
        -- fsmRmtErrEquipmentIOCardBaseFePresence:Identify
        -- fsmRmtErrEquipmentIOCardBaseFeConn:ConfigureEndPoint
        -- fsmRmtErrEquipmentIOCardBaseFeConn:ConfigureSwMgmtEndPoint
        -- fsmRmtErrEquipmentIOCardBaseFeConn:ConfigureVifNs
        -- fsmRmtErrEquipmentIOCardBaseFeConn:DiscoverChassis
        -- fsmRmtErrEquipmentIOCardBaseFeConn:EnableChassis
        -- fsmFailEquipmentIOCardBaseFePresence
        -- fsmFailEquipmentIOCardBaseFeConn

-- sw:FcSanBorder
    -- sys/switch-[id]/border-fc
        -- fsmStFailSwFcSanBorderDeploy:UpdateConnectivity
        -- fsmStFailSwFcSanBorderActivateZoneSet:UpdateZones
        -- fsmStFailSwFcSanBorderActivateZoneSet:VerifyUserZoneConfig
        -- fsmRmtErrSwFcSanBorderDeploy:UpdateConnectivity
        -- fsmRmtErrSwFcSanBorderActivateZoneSet:UpdateZones
        -- fsmRmtErrSwFcSanBorderActivateZoneSet:VerifyUserZoneConfig
        -- fsmFailSwFcSanBorderDeploy
        -- fsmFailSwFcSanBorderActivateZoneSet

-- pki:KeyRing
    -- sys/pki-ext/keyring-[name]
        -- fltPkiKeyRingStatus
        -- fltPkiKeyRingKeyRingNotDeployed
        -- fltPkiKeyRingModulus

-- comm:Snmp
    -- sys/svc-ext/snmp-svc
        -- fltCommSnmpSyscontactEmpty

-- sw:EthMon
    -- sys/switch-[id]/lanmon-eth/mon-[name]
        -- fsmStFailSwEthMonDeploy:UpdateEthMon
        -- fsmRmtErrSwEthMonDeploy:UpdateEthMon
        -- fsmFailSwEthMonDeploy

-- power:Budget
    -- sys/chassis-[id]/blade-[slotId]/ext-board-[id]/budget
    -- sys/rack-unit-[id]/ext-board-[id]/budget
    -- sys/chassis-[id]/cartridge-[slotId]/server-[serverInstanceId]/ext-board-[id]/budget
    -- sys/chassis-[id]/blade-[slotId]/budget
    -- sys/rack-unit-[id]/budget
    -- sys/chassis-[id]/cartridge-[slotId]/server-[serverInstanceId]/budget
    -- sys/chassis-[id]/budget
    -- sys/fex-[id]/budget
    -- sys/switch-[id]/budget
        -- fltPowerBudgetPowerBudgetCmcProblem
        -- fltPowerBudgetPowerBudgetBmcProblem
        -- fltPowerBudgetPowerBudgetDiscFail
        -- fltPowerBudgetPowerCapReachedCommit
        -- fltPowerBudgetChassisPsuInsufficient
        -- fltPowerBudgetTStateTransition
        -- fltPowerBudgetFirmwareMismatch
        -- fltPowerBudgetChassisPsuMixedMode
        -- fltPowerBudgetPowerBudgetUnavailable

-- nfs:MountInst
    -- sys/switch-[id]/nfs-mount-inst-[name]
        -- fsmStFailNfsMountInstMount:MountLocal
        -- fsmStFailNfsMountInstMount:MountPeer
        -- fsmStFailNfsMountInstMount:RegisterClient
        -- fsmStFailNfsMountInstMount:VerifyRegistration
        -- fsmStFailNfsMountInstUnmount:UnmountLocal
        -- fsmStFailNfsMountInstUnmount:UnmountPeer
        -- fsmRmtErrNfsMountInstMount:MountLocal
        -- fsmRmtErrNfsMountInstMount:MountPeer
        -- fsmRmtErrNfsMountInstMount:RegisterClient
        -- fsmRmtErrNfsMountInstMount:VerifyRegistration
        -- fsmRmtErrNfsMountInstUnmount:UnmountLocal
        -- fsmRmtErrNfsMountInstUnmount:UnmountPeer
        -- fsmFailNfsMountInstMount
        -- fsmFailNfsMountInstUnmount

-- mgmt:ExportPolicy
    -- org-[name]/
        -- fsmStFailMgmtExportPolicyReportConfigCopy:Report
        -- fsmRmtErrMgmtExportPolicyReportConfigCopy:Report
        -- fsmFailMgmtExportPolicyReportConfigCopy

-- adaptor:HostEthIf
    -- sys/chassis-[id]/blade-[slotId]/adaptor-[id]/host-eth-[id]
    -- sys/rack-unit-[id]/adaptor-[id]/host-eth-[id]
    -- sys/chassis-[id]/cartridge-[slotId]/server-[serverInstanceId]/adaptor-[id]/host-eth-[id]
    -- sys/chassis-[id]/cartridge-[slotId]/server-[serverInstanceId]/adaptor-[id]/host-eth-[id]
        -- fltAdaptorHostEthIfMisConnect
        -- fltAdaptorHostEthIfMissing
        -- fsmStFailAdaptorHostEthIfCircuitReset:DisableA
        -- fsmStFailAdaptorHostEthIfCircuitReset:DisableB
        -- fsmStFailAdaptorHostEthIfCircuitReset:EnableA
        -- fsmStFailAdaptorHostEthIfCircuitReset:EnableB
        -- fsmRmtErrAdaptorHostEthIfCircuitReset:DisableA
        -- fsmRmtErrAdaptorHostEthIfCircuitReset:DisableB
        -- fsmRmtErrAdaptorHostEthIfCircuitReset:EnableA
        -- fsmRmtErrAdaptorHostEthIfCircuitReset:EnableB
        -- fsmFailAdaptorHostEthIfCircuitReset

-- vnic:Profile
    -- fabric/lan/profiles/vnic-[name]
        -- fltVnicProfileProfileConfigIncorrect

-- license:Downloader
    -- sys/license/dnld-[fileName]
        -- fsmStFailLicenseDownloaderDownload:CopyRemote
        -- fsmStFailLicenseDownloaderDownload:DeleteLocal
        -- fsmStFailLicenseDownloaderDownload:DeleteRemote
        -- fsmStFailLicenseDownloaderDownload:Local
        -- fsmStFailLicenseDownloaderDownload:ValidateLocal
        -- fsmStFailLicenseDownloaderDownload:ValidateRemote
        -- fsmRmtErrLicenseDownloaderDownload:CopyRemote
        -- fsmRmtErrLicenseDownloaderDownload:DeleteLocal
        -- fsmRmtErrLicenseDownloaderDownload:DeleteRemote
        -- fsmRmtErrLicenseDownloaderDownload:Local
        -- fsmRmtErrLicenseDownloaderDownload:ValidateLocal
        -- fsmRmtErrLicenseDownloaderDownload:ValidateRemote
        -- fsmFailLicenseDownloaderDownload

-- storage:FlexFlashDrive
    -- sys/chassis-[id]/blade-[slotId]/board/storage-flexflash-[id]/card-[slotNumber]/drive-[name]
    -- sys/rack-unit-[id]/board/storage-flexflash-[id]/card-[slotNumber]/drive-[name]
    -- sys/chassis-[id]/cartridge-[slotId]/server-[serverInstanceId]/board/storage-flexflash-[id]/card-[slotNumber]/drive-[name]
        -- fltStorageFlexFlashDriveUnhealthy

-- firmware:Image
    -- sys/fw-catalogue/image-[name]
        -- fsmStFailFirmwareImageDelete:Local
        -- fsmStFailFirmwareImageDelete:Remote
        -- fsmRmtErrFirmwareImageDelete:Local
        -- fsmRmtErrFirmwareImageDelete:Remote
        -- fsmFailFirmwareImageDelete

-- sw:PortDiscover
    -- sys/switch-[id]/discover
        -- fsmStFailSwPortDiscoverDeploy:EnablePort
        -- fsmRmtErrSwPortDiscoverDeploy:EnablePort
        -- fsmFailSwPortDiscoverDeploy

-- sw:AccessDomain
    -- sys/switch-[id]/access-eth
        -- fsmStFailSwAccessDomainDeploy:UpdateConnectivity
        -- fsmRmtErrSwAccessDomainDeploy:UpdateConnectivity
        -- fsmFailSwAccessDomainDeploy

-- cimcvmedia:ActualMountEntry
    -- sys/chassis-[id]/blade-[slotId]/adaptor-[id]/mgmt/actual-mount-list/actual-mount-entry-[virtualDiskId]
    -- sys/rack-unit-[id]/adaptor-[id]/mgmt/actual-mount-list/actual-mount-entry-[virtualDiskId]
    -- sys/chassis-[id]/cartridge-[slotId]/server-[serverInstanceId]/adaptor-[id]/mgmt/actual-mount-list/actual-mount-entry-[virtualDiskId]
    -- sys/chassis-[id]/cartridge-[slotId]/server-[serverInstanceId]/adaptor-[id]/mgmt/actual-mount-list/actual-mount-entry-[virtualDiskId]
    -- sys/chassis-[id]/blade-[slotId]/ext-board-[id]/boardController/mgmt/actual-mount-list/actual-mount-entry-[virtualDiskId]
    -- sys/rack-unit-[id]/ext-board-[id]/boardController/mgmt/actual-mount-list/actual-mount-entry-[virtualDiskId]
    -- sys/chassis-[id]/cartridge-[slotId]/server-[serverInstanceId]/ext-board-[id]/boardController/mgmt/actual-mount-list/actual-mount-entry-[virtualDiskId]
    -- sys/chassis-[id]/blade-[slotId]/boardController/mgmt/actual-mount-list/actual-mount-entry-[virtualDiskId]
    -- sys/rack-unit-[id]/boardController/mgmt/actual-mount-list/actual-mount-entry-[virtualDiskId]
    -- sys/chassis-[id]/cartridge-[slotId]/server-[serverInstanceId]/boardController/mgmt/actual-mount-list/actual-mount-entry-[virtualDiskId]
    -- sys/chassis-[id]/boardController/mgmt/actual-mount-list/actual-mount-entry-[virtualDiskId]
    -- sys/chassis-[id]/slot-[id]/boardController/mgmt/actual-mount-list/actual-mount-entry-[virtualDiskId]
    -- sys/chassis-[id]/blade-[slotId]/ext-board-[id]/mgmt/actual-mount-list/actual-mount-entry-[virtualDiskId]
    -- sys/rack-unit-[id]/ext-board-[id]/mgmt/actual-mount-list/actual-mount-entry-[virtualDiskId]
    -- sys/chassis-[id]/cartridge-[slotId]/server-[serverInstanceId]/ext-board-[id]/mgmt/actual-mount-list/actual-mount-entry-[virtualDiskId]
    -- sys/chassis-[id]/blade-[slotId]/mgmt/actual-mount-list/actual-mount-entry-[virtualDiskId]
    -- sys/rack-unit-[id]/mgmt/actual-mount-list/actual-mount-entry-[virtualDiskId]
    -- sys/chassis-[id]/cartridge-[slotId]/server-[serverInstanceId]/mgmt/actual-mount-list/actual-mount-entry-[virtualDiskId]
    -- sys/chassis-[id]/cartridge-[slotId]/server-[serverInstanceId]/mgmt/actual-mount-list/actual-mount-entry-[virtualDiskId]
    -- sys/chassis-[id]/mgmt/actual-mount-list/actual-mount-entry-[virtualDiskId]
    -- sys/fex-[id]/mgmt/actual-mount-list/actual-mount-entry-[virtualDiskId]
    -- sys/chassis-[id]/slot-[id]/mgmt/actual-mount-list/actual-mount-entry-[virtualDiskId]
    -- sys/fex-[id]/slot-[id]/mgmt/actual-mount-list/actual-mount-entry-[virtualDiskId]
    -- sys/chassis-[id]/shared-io-module/mgmt/actual-mount-list/actual-mount-entry-[virtualDiskId]
    -- sys/chassis-[id]/slot-[id]/shared-io-module/mgmt/actual-mount-list/actual-mount-entry-[virtualDiskId]
    -- sys/chassis-[id]/sw-slot-[id]/mgmt/actual-mount-list/actual-mount-entry-[virtualDiskId]
    -- sys/chassis-[id]/slot-[id]/mgmt/actual-mount-list/actual-mount-entry-[virtualDiskId]
    -- sys/switch-[id]/mgmt/actual-mount-list/actual-mount-entry-[virtualDiskId]
    -- sys/chassis-[id]/blade-[slotId]/board/storage-[type]-[id]/mgmt/actual-mount-list/actual-mount-entry-[virtualDiskId]
    -- sys/rack-unit-[id]/board/storage-[type]-[id]/mgmt/actual-mount-list/actual-mount-entry-[virtualDiskId]
    -- sys/chassis-[id]/cartridge-[slotId]/server-[serverInstanceId]/board/storage-[type]-[id]/mgmt/actual-mount-list/actual-mount-entry-[virtualDiskId]
    -- sys/chassis-[id]/storage-[type]-[id]/mgmt/actual-mount-list/actual-mount-entry-[virtualDiskId]
    -- sys/chassis-[id]/blade-[slotId]/board/storage-[type]-[id]/disk-[id]/mgmt/actual-mount-list/actual-mount-entry-[virtualDiskId]
    -- sys/rack-unit-[id]/board/storage-[type]-[id]/disk-[id]/mgmt/actual-mount-list/actual-mount-entry-[virtualDiskId]
    -- sys/chassis-[id]/cartridge-[slotId]/server-[serverInstanceId]/board/storage-[type]-[id]/disk-[id]/mgmt/actual-mount-list/actual-mount-entry-[virtualDiskId]
    -- sys/chassis-[id]/storage-[type]-[id]/disk-[id]/mgmt/actual-mount-list/actual-mount-entry-[virtualDiskId]
    -- sys/chassis-[id]/blade-[slotId]/enc-[id]/disk-[id]/mgmt/actual-mount-list/actual-mount-entry-[virtualDiskId]
    -- sys/rack-unit-[id]/enc-[id]/disk-[id]/mgmt/actual-mount-list/actual-mount-entry-[virtualDiskId]
    -- sys/chassis-[id]/cartridge-[slotId]/server-[serverInstanceId]/enc-[id]/disk-[id]/mgmt/actual-mount-list/actual-mount-entry-[virtualDiskId]
    -- sys/chassis-[id]/enc-[id]/disk-[id]/mgmt/actual-mount-list/actual-mount-entry-[virtualDiskId]
    -- sys/chassis-[id]/blade-[slotId]/board/storage-[type]-[id]/enc-[id]/disk-[id]/mgmt/actual-mount-list/actual-mount-entry-[virtualDiskId]
    -- sys/rack-unit-[id]/board/storage-[type]-[id]/enc-[id]/disk-[id]/mgmt/actual-mount-list/actual-mount-entry-[virtualDiskId]
    -- sys/chassis-[id]/cartridge-[slotId]/server-[serverInstanceId]/board/storage-[type]-[id]/enc-[id]/disk-[id]/mgmt/actual-mount-list/actual-mount-entry-[virtualDiskId]
    -- sys/chassis-[id]/storage-[type]-[id]/enc-[id]/disk-[id]/mgmt/actual-mount-list/actual-mount-entry-[virtualDiskId]
    -- sys/chassis-[id]/blade-[slotId]/board/sas-expander-[id]/mgmt/actual-mount-list/actual-mount-entry-[virtualDiskId]
    -- sys/rack-unit-[id]/board/sas-expander-[id]/mgmt/actual-mount-list/actual-mount-entry-[virtualDiskId]
    -- sys/chassis-[id]/cartridge-[slotId]/server-[serverInstanceId]/board/sas-expander-[id]/mgmt/actual-mount-list/actual-mount-entry-[virtualDiskId]
    -- sys/chassis-[id]/sas-expander-[id]/mgmt/actual-mount-list/actual-mount-entry-[virtualDiskId]
    -- sys/mgmt/actual-mount-list/actual-mount-entry-[virtualDiskId]
        -- fltCimcvmediaActualMountEntryVmediaMountFailed

-- fabric:ExternalPc
        -- fltFabricExternalPcDown

-- fabric:VsanEp
    -- fabric/fc-estc/[id]/phys-fc-slot-[slotId]-port-[portId]/vsan-[id]
    -- fabric/san/[id]/phys-slot-[slotId]-port-[portId]/vsan-[id]
    -- fabric/san/[id]/pc-[portId]/vsan-[id]
    -- fabric/fc-estc/[id]/phys-fcoe-slot-[slotId]-port-[portId]/vsan-[id]
    -- fabric/server/sw-[id]/slot-[slotId]-aggr-port-[aggrPortId]/phys-fcoe-slot-[slotId]-port-[portId]/vsan-[id]
    -- fabric/server/sw-[id]/pc-[portId]/slot-[slotId]-aggr-port-[aggrPortId]/phys-fcoe-slot-[slotId]-port-[portId]/vsan-[id]
    -- fabric/eth-estc/[id]/slot-[slotId]-aggr-port-[aggrPortId]/phys-fcoe-slot-[slotId]-port-[portId]/vsan-[id]
    -- fabric/eth-estc/[id]/pc-[portId]/slot-[slotId]-aggr-port-[aggrPortId]/phys-fcoe-slot-[slotId]-port-[portId]/vsan-[id]
    -- fabric/lan/[id]/slot-[slotId]-aggr-port-[aggrPortId]/phys-fcoe-slot-[slotId]-port-[portId]/vsan-[id]
    -- fabric/lan/[id]/pc-[portId]/slot-[slotId]-aggr-port-[aggrPortId]/phys-fcoe-slot-[slotId]-port-[portId]/vsan-[id]
    -- fabric/lanmon/[id]/eth-mon-[name]/slot-[slotId]-aggr-port-[aggrPortId]/phys-fcoe-slot-[slotId]-port-[portId]/vsan-[id]
    -- fabric/fc-estc/[id]/slot-[slotId]-aggr-port-[aggrPortId]/phys-fcoe-slot-[slotId]-port-[portId]/vsan-[id]
    -- fabric/sanmon/[id]/fc-mon-[name]/slot-[slotId]-aggr-port-[aggrPortId]/phys-fcoe-slot-[slotId]-port-[portId]/vsan-[id]
    -- fabric/san/[id]/slot-[slotId]-aggr-port-[aggrPortId]/phys-fcoe-slot-[slotId]-port-[portId]/vsan-[id]
    -- fabric/san/[id]/fcoesanpc-[portId]/slot-[slotId]-aggr-port-[aggrPortId]/phys-fcoe-slot-[slotId]-port-[portId]/vsan-[id]
    -- fabric/san/[id]/phys-fcoesanep-slot-[slotId]-port-[portId]/vsan-[id]
    -- fabric/server/sw-[id]/slot-[slotId]-aggr-port-[aggrPortId]/phys-fcoesanep-slot-[slotId]-port-[portId]/vsan-[id]
    -- fabric/server/sw-[id]/pc-[portId]/slot-[slotId]-aggr-port-[aggrPortId]/phys-fcoesanep-slot-[slotId]-port-[portId]/vsan-[id]
    -- fabric/eth-estc/[id]/slot-[slotId]-aggr-port-[aggrPortId]/phys-fcoesanep-slot-[slotId]-port-[portId]/vsan-[id]
    -- fabric/eth-estc/[id]/pc-[portId]/slot-[slotId]-aggr-port-[aggrPortId]/phys-fcoesanep-slot-[slotId]-port-[portId]/vsan-[id]
    -- fabric/lan/[id]/slot-[slotId]-aggr-port-[aggrPortId]/phys-fcoesanep-slot-[slotId]-port-[portId]/vsan-[id]
    -- fabric/lan/[id]/pc-[portId]/slot-[slotId]-aggr-port-[aggrPortId]/phys-fcoesanep-slot-[slotId]-port-[portId]/vsan-[id]
    -- fabric/lanmon/[id]/eth-mon-[name]/slot-[slotId]-aggr-port-[aggrPortId]/phys-fcoesanep-slot-[slotId]-port-[portId]/vsan-[id]
    -- fabric/fc-estc/[id]/slot-[slotId]-aggr-port-[aggrPortId]/phys-fcoesanep-slot-[slotId]-port-[portId]/vsan-[id]
    -- fabric/sanmon/[id]/fc-mon-[name]/slot-[slotId]-aggr-port-[aggrPortId]/phys-fcoesanep-slot-[slotId]-port-[portId]/vsan-[id]
    -- fabric/san/[id]/slot-[slotId]-aggr-port-[aggrPortId]/phys-fcoesanep-slot-[slotId]-port-[portId]/vsan-[id]
    -- fabric/san/[id]/fcoesanpc-[portId]/slot-[slotId]-aggr-port-[aggrPortId]/phys-fcoesanep-slot-[slotId]-port-[portId]/vsan-[id]
    -- fabric/san/[id]/fcoesanpc-[portId]/vsan-[id]
        -- fltFabricVsanEpErrorDisabled

-- comm:SnmpUser
    -- sys/svc-ext/snmp-svc/snmpv3-user-[name]
        -- fltCommSnmpUserSnmpUserNotDeployed

-- aaa:DefaultAuth
    -- sys/auth-realm/default-auth
        -- fltAaaDefaultAuthDefaultAuthNotDeployed

-- mgmt:DbState
    -- sys/switch-[id]/mgmt-db-state
        -- fltMgmtDbStateDb-corruption-detected
        -- fltMgmtDbStateHigh-db-corruption-detected

-- equipment:HealthLed
    -- sys/chassis-[id]/blade-[slotId]/health-led
    -- sys/chassis-[id]/blade-[slotId]/ext-board-[id]/health-led
    -- sys/rack-unit-[id]/ext-board-[id]/health-led
    -- sys/chassis-[id]/cartridge-[slotId]/server-[serverInstanceId]/ext-board-[id]/health-led
    -- sys/chassis-[id]/blade-[slotId]/health-led
    -- sys/rack-unit-[id]/health-led
    -- sys/chassis-[id]/cartridge-[slotId]/server-[serverInstanceId]/health-led
    -- sys/rack-unit-[id]/health-led
    -- sys/chassis-[id]/health-led
    -- sys/rack-unit-[id]/fan-module-[tray]-[id]/health-led
    -- sys/chassis-[id]/fan-module-[tray]-[id]/health-led
    -- sys/rack-enclosure-[id]/fan-module-[tray]-[id]/health-led
    -- sys/switch-[id]/fan-module-[tray]-[id]/health-led
    -- sys/fex-[id]/health-led
    -- sys/chassis-[id]/slot-[id]/health-led
    -- sys/fex-[id]/slot-[id]/health-led
    -- sys/rack-unit-[id]/psu-[id]/health-led
    -- sys/chassis-[id]/psu-[id]/health-led
    -- sys/fex-[id]/psu-[id]/health-led
    -- sys/rack-enclosure-[id]/psu-[id]/health-led
    -- sys/switch-[id]/psu-[id]/health-led
        -- fltEquipmentHealthLedCriticalError
        -- fltEquipmentHealthLedMinorError

-- fabric:SwChPhEp
    -- fabric/server/chassis-ep-ven-[vendor]-mod[model]-ser-[serial]
        -- fltFabricSwChPhEpUncleanConfiguration

-- firmware:Distributable
    -- sys/fw-catalogue/distrib-[name]
        -- fsmStFailFirmwareDistributableDelete:Local
        -- fsmStFailFirmwareDistributableDelete:Remote
        -- fsmRmtErrFirmwareDistributableDelete:Local
        -- fsmRmtErrFirmwareDistributableDelete:Remote
        -- fsmFailFirmwareDistributableDelete

-- storage:FlexFlashCard
    -- sys/chassis-[id]/blade-[slotId]/board/storage-flexflash-[id]/card-[slotNumber]
    -- sys/rack-unit-[id]/board/storage-flexflash-[id]/card-[slotNumber]
    -- sys/chassis-[id]/cartridge-[slotId]/server-[serverInstanceId]/board/storage-flexflash-[id]/card-[slotNumber]
        -- fltStorageFlexFlashCardInoperable
        -- fltStorageFlexFlashCardMissing
        -- fltStorageFlexFlashCardUnhealthy
        -- fltStorageFlexFlashCardIoerrors

-- adaptor:HostFcIf
    -- sys/chassis-[id]/blade-[slotId]/adaptor-[id]/host-fc-[id]
    -- sys/rack-unit-[id]/adaptor-[id]/host-fc-[id]
    -- sys/chassis-[id]/cartridge-[slotId]/server-[serverInstanceId]/adaptor-[id]/host-fc-[id]
    -- sys/chassis-[id]/cartridge-[slotId]/server-[serverInstanceId]/adaptor-[id]/host-fc-[id]
        -- fsmStFailAdaptorHostFcIfResetFcPersBinding:ExecuteLocal
        -- fsmStFailAdaptorHostFcIfResetFcPersBinding:ExecutePeer
        -- fsmStFailAdaptorHostFcIfCircuitReset:DisableA
        -- fsmStFailAdaptorHostFcIfCircuitReset:DisableB
        -- fsmStFailAdaptorHostFcIfCircuitReset:EnableA
        -- fsmStFailAdaptorHostFcIfCircuitReset:EnableB
        -- fsmRmtErrAdaptorHostFcIfResetFcPersBinding:ExecuteLocal
        -- fsmRmtErrAdaptorHostFcIfResetFcPersBinding:ExecutePeer
        -- fsmRmtErrAdaptorHostFcIfCircuitReset:DisableA
        -- fsmRmtErrAdaptorHostFcIfCircuitReset:DisableB
        -- fsmRmtErrAdaptorHostFcIfCircuitReset:EnableA
        -- fsmRmtErrAdaptorHostFcIfCircuitReset:EnableB
        -- fsmFailAdaptorHostFcIfResetFcPersBinding
        -- fsmFailAdaptorHostFcIfCircuitReset

-- firmware:BootUnit
    -- sys/chassis-[id]/blade-[slotId]/adaptor-[id]/host-eth-[id]/fw-boot-def/bootunit-[type]
    -- sys/rack-unit-[id]/adaptor-[id]/host-eth-[id]/fw-boot-def/bootunit-[type]
    -- sys/chassis-[id]/cartridge-[slotId]/server-[serverInstanceId]/adaptor-[id]/host-eth-[id]/fw-boot-def/bootunit-[type]
    -- sys/chassis-[id]/cartridge-[slotId]/server-[serverInstanceId]/adaptor-[id]/host-eth-[id]/fw-boot-def/bootunit-[type]
    -- sys/chassis-[id]/blade-[slotId]/adaptor-[id]/host-fc-[id]/fw-boot-def/bootunit-[type]
    -- sys/rack-unit-[id]/adaptor-[id]/host-fc-[id]/fw-boot-def/bootunit-[type]
    -- sys/chassis-[id]/cartridge-[slotId]/server-[serverInstanceId]/adaptor-[id]/host-fc-[id]/fw-boot-def/bootunit-[type]
    -- sys/chassis-[id]/cartridge-[slotId]/server-[serverInstanceId]/adaptor-[id]/host-fc-[id]/fw-boot-def/bootunit-[type]
    -- sys/chassis-[id]/blade-[slotId]/ext-board-[id]/bios/fw-boot-def/bootunit-[type]
    -- sys/rack-unit-[id]/ext-board-[id]/bios/fw-boot-def/bootunit-[type]
    -- sys/chassis-[id]/cartridge-[slotId]/server-[serverInstanceId]/ext-board-[id]/bios/fw-boot-def/bootunit-[type]
    -- sys/chassis-[id]/blade-[slotId]/bios/fw-boot-def/bootunit-[type]
    -- sys/rack-unit-[id]/bios/fw-boot-def/bootunit-[type]
    -- sys/chassis-[id]/cartridge-[slotId]/server-[serverInstanceId]/bios/fw-boot-def/bootunit-[type]
    -- sys/chassis-[id]/cartridge-[slotId]/server-[serverInstanceId]/bios/fw-boot-def/bootunit-[type]
    -- capabilities/fw-boot-def/bootunit-[type]
    -- capabilities/ep/mgmt-ext/fw-boot-def/bootunit-[type]
    -- sys/rack-unit-[id]/psu-[id]/fw-boot-def/bootunit-[type]
    -- sys/chassis-[id]/psu-[id]/fw-boot-def/bootunit-[type]
    -- sys/fex-[id]/psu-[id]/fw-boot-def/bootunit-[type]
    -- sys/rack-enclosure-[id]/psu-[id]/fw-boot-def/bootunit-[type]
    -- sys/switch-[id]/psu-[id]/fw-boot-def/bootunit-[type]
    -- sys/chassis-[id]/blade-[slotId]/board/graphics-card-[id]/fw-boot-def/bootunit-[type]
    -- sys/rack-unit-[id]/board/graphics-card-[id]/fw-boot-def/bootunit-[type]
    -- sys/chassis-[id]/cartridge-[slotId]/server-[serverInstanceId]/board/graphics-card-[id]/fw-boot-def/bootunit-[type]
    -- sys/chassis-[id]/blade-[slotId]/adaptor-[id]/mgmt/fw-boot-def/bootunit-[type]
    -- sys/rack-unit-[id]/adaptor-[id]/mgmt/fw-boot-def/bootunit-[type]
    -- sys/chassis-[id]/cartridge-[slotId]/server-[serverInstanceId]/adaptor-[id]/mgmt/fw-boot-def/bootunit-[type]
    -- sys/chassis-[id]/cartridge-[slotId]/server-[serverInstanceId]/adaptor-[id]/mgmt/fw-boot-def/bootunit-[type]
    -- sys/chassis-[id]/blade-[slotId]/ext-board-[id]/boardController/mgmt/fw-boot-def/bootunit-[type]
    -- sys/rack-unit-[id]/ext-board-[id]/boardController/mgmt/fw-boot-def/bootunit-[type]
    -- sys/chassis-[id]/cartridge-[slotId]/server-[serverInstanceId]/ext-board-[id]/boardController/mgmt/fw-boot-def/bootunit-[type]
    -- sys/chassis-[id]/blade-[slotId]/boardController/mgmt/fw-boot-def/bootunit-[type]
    -- sys/rack-unit-[id]/boardController/mgmt/fw-boot-def/bootunit-[type]
    -- sys/chassis-[id]/cartridge-[slotId]/server-[serverInstanceId]/boardController/mgmt/fw-boot-def/bootunit-[type]
    -- sys/chassis-[id]/boardController/mgmt/fw-boot-def/bootunit-[type]
    -- sys/chassis-[id]/slot-[id]/boardController/mgmt/fw-boot-def/bootunit-[type]
    -- sys/chassis-[id]/blade-[slotId]/ext-board-[id]/mgmt/fw-boot-def/bootunit-[type]
    -- sys/rack-unit-[id]/ext-board-[id]/mgmt/fw-boot-def/bootunit-[type]
    -- sys/chassis-[id]/cartridge-[slotId]/server-[serverInstanceId]/ext-board-[id]/mgmt/fw-boot-def/bootunit-[type]
    -- sys/chassis-[id]/blade-[slotId]/mgmt/fw-boot-def/bootunit-[type]
    -- sys/rack-unit-[id]/mgmt/fw-boot-def/bootunit-[type]
    -- sys/chassis-[id]/cartridge-[slotId]/server-[serverInstanceId]/mgmt/fw-boot-def/bootunit-[type]
    -- sys/chassis-[id]/cartridge-[slotId]/server-[serverInstanceId]/mgmt/fw-boot-def/bootunit-[type]
    -- sys/chassis-[id]/mgmt/fw-boot-def/bootunit-[type]
    -- sys/fex-[id]/mgmt/fw-boot-def/bootunit-[type]
    -- sys/chassis-[id]/slot-[id]/mgmt/fw-boot-def/bootunit-[type]
    -- sys/fex-[id]/slot-[id]/mgmt/fw-boot-def/bootunit-[type]
    -- sys/chassis-[id]/shared-io-module/mgmt/fw-boot-def/bootunit-[type]
    -- sys/chassis-[id]/slot-[id]/shared-io-module/mgmt/fw-boot-def/bootunit-[type]
    -- sys/chassis-[id]/sw-slot-[id]/mgmt/fw-boot-def/bootunit-[type]
    -- sys/chassis-[id]/slot-[id]/mgmt/fw-boot-def/bootunit-[type]
    -- sys/switch-[id]/mgmt/fw-boot-def/bootunit-[type]
    -- sys/chassis-[id]/blade-[slotId]/board/storage-[type]-[id]/mgmt/fw-boot-def/bootunit-[type]
    -- sys/rack-unit-[id]/board/storage-[type]-[id]/mgmt/fw-boot-def/bootunit-[type]
    -- sys/chassis-[id]/cartridge-[slotId]/server-[serverInstanceId]/board/storage-[type]-[id]/mgmt/fw-boot-def/bootunit-[type]
    -- sys/chassis-[id]/storage-[type]-[id]/mgmt/fw-boot-def/bootunit-[type]
    -- sys/chassis-[id]/blade-[slotId]/board/storage-[type]-[id]/disk-[id]/mgmt/fw-boot-def/bootunit-[type]
    -- sys/rack-unit-[id]/board/storage-[type]-[id]/disk-[id]/mgmt/fw-boot-def/bootunit-[type]
    -- sys/chassis-[id]/cartridge-[slotId]/server-[serverInstanceId]/board/storage-[type]-[id]/disk-[id]/mgmt/fw-boot-def/bootunit-[type]
    -- sys/chassis-[id]/storage-[type]-[id]/disk-[id]/mgmt/fw-boot-def/bootunit-[type]
    -- sys/chassis-[id]/blade-[slotId]/enc-[id]/disk-[id]/mgmt/fw-boot-def/bootunit-[type]
    -- sys/rack-unit-[id]/enc-[id]/disk-[id]/mgmt/fw-boot-def/bootunit-[type]
    -- sys/chassis-[id]/cartridge-[slotId]/server-[serverInstanceId]/enc-[id]/disk-[id]/mgmt/fw-boot-def/bootunit-[type]
    -- sys/chassis-[id]/enc-[id]/disk-[id]/mgmt/fw-boot-def/bootunit-[type]
    -- sys/chassis-[id]/blade-[slotId]/board/storage-[type]-[id]/enc-[id]/disk-[id]/mgmt/fw-boot-def/bootunit-[type]
    -- sys/rack-unit-[id]/board/storage-[type]-[id]/enc-[id]/disk-[id]/mgmt/fw-boot-def/bootunit-[type]
    -- sys/chassis-[id]/cartridge-[slotId]/server-[serverInstanceId]/board/storage-[type]-[id]/enc-[id]/disk-[id]/mgmt/fw-boot-def/bootunit-[type]
    -- sys/chassis-[id]/storage-[type]-[id]/enc-[id]/disk-[id]/mgmt/fw-boot-def/bootunit-[type]
    -- sys/chassis-[id]/blade-[slotId]/board/sas-expander-[id]/mgmt/fw-boot-def/bootunit-[type]
    -- sys/rack-unit-[id]/board/sas-expander-[id]/mgmt/fw-boot-def/bootunit-[type]
    -- sys/chassis-[id]/cartridge-[slotId]/server-[serverInstanceId]/board/sas-expander-[id]/mgmt/fw-boot-def/bootunit-[type]
    -- sys/chassis-[id]/sas-expander-[id]/mgmt/fw-boot-def/bootunit-[type]
    -- sys/mgmt/fw-boot-def/bootunit-[type]
    -- sys/chassis-[id]/blade-[slotId]/board/storage-[type]-[id]/fw-boot-def/bootunit-[type]
    -- sys/rack-unit-[id]/board/storage-[type]-[id]/fw-boot-def/bootunit-[type]
    -- sys/chassis-[id]/cartridge-[slotId]/server-[serverInstanceId]/board/storage-[type]-[id]/fw-boot-def/bootunit-[type]
    -- sys/chassis-[id]/storage-[type]-[id]/fw-boot-def/bootunit-[type]
    -- sys/chassis-[id]/blade-[slotId]/board/storage-[type]-[id]/disk-[id]/fw-boot-def/bootunit-[type]
    -- sys/rack-unit-[id]/board/storage-[type]-[id]/disk-[id]/fw-boot-def/bootunit-[type]
    -- sys/chassis-[id]/cartridge-[slotId]/server-[serverInstanceId]/board/storage-[type]-[id]/disk-[id]/fw-boot-def/bootunit-[type]
    -- sys/chassis-[id]/storage-[type]-[id]/disk-[id]/fw-boot-def/bootunit-[type]
    -- sys/chassis-[id]/blade-[slotId]/enc-[id]/disk-[id]/fw-boot-def/bootunit-[type]
    -- sys/rack-unit-[id]/enc-[id]/disk-[id]/fw-boot-def/bootunit-[type]
    -- sys/chassis-[id]/cartridge-[slotId]/server-[serverInstanceId]/enc-[id]/disk-[id]/fw-boot-def/bootunit-[type]
    -- sys/chassis-[id]/enc-[id]/disk-[id]/fw-boot-def/bootunit-[type]
    -- sys/chassis-[id]/blade-[slotId]/board/storage-[type]-[id]/enc-[id]/disk-[id]/fw-boot-def/bootunit-[type]
    -- sys/rack-unit-[id]/board/storage-[type]-[id]/enc-[id]/disk-[id]/fw-boot-def/bootunit-[type]
    -- sys/chassis-[id]/cartridge-[slotId]/server-[serverInstanceId]/board/storage-[type]-[id]/enc-[id]/disk-[id]/fw-boot-def/bootunit-[type]
    -- sys/chassis-[id]/storage-[type]-[id]/enc-[id]/disk-[id]/fw-boot-def/bootunit-[type]
    -- sys/chassis-[id]/blade-[slotId]/board/nvme-switch-[id]/fw-boot-def/bootunit-[type]
    -- sys/rack-unit-[id]/board/nvme-switch-[id]/fw-boot-def/bootunit-[type]
    -- sys/chassis-[id]/cartridge-[slotId]/server-[serverInstanceId]/board/nvme-switch-[id]/fw-boot-def/bootunit-[type]
    -- sys/chassis-[id]/blade-[slotId]/board/storage-[type]-[id]/onboard-device-[deviceType]-[id]/fw-boot-def/bootunit-[type]
    -- sys/rack-unit-[id]/board/storage-[type]-[id]/onboard-device-[deviceType]-[id]/fw-boot-def/bootunit-[type]
    -- sys/chassis-[id]/cartridge-[slotId]/server-[serverInstanceId]/board/storage-[type]-[id]/onboard-device-[deviceType]-[id]/fw-boot-def/bootunit-[type]
    -- sys/chassis-[id]/storage-[type]-[id]/onboard-device-[deviceType]-[id]/fw-boot-def/bootunit-[type]
    -- sys/chassis-[id]/blade-[slotId]/board/sas-expander-[id]/onboard-device-[deviceType]-[id]/fw-boot-def/bootunit-[type]
    -- sys/rack-unit-[id]/board/sas-expander-[id]/onboard-device-[deviceType]-[id]/fw-boot-def/bootunit-[type]
    -- sys/chassis-[id]/cartridge-[slotId]/server-[serverInstanceId]/board/sas-expander-[id]/onboard-device-[deviceType]-[id]/fw-boot-def/bootunit-[type]
    -- sys/chassis-[id]/sas-expander-[id]/onboard-device-[deviceType]-[id]/fw-boot-def/bootunit-[type]
    -- sys/chassis-[id]/blade-[slotId]/board/sas-expander-[id]/fw-boot-def/bootunit-[type]
    -- sys/rack-unit-[id]/board/sas-expander-[id]/fw-boot-def/bootunit-[type]
    -- sys/chassis-[id]/cartridge-[slotId]/server-[serverInstanceId]/board/sas-expander-[id]/fw-boot-def/bootunit-[type]
    -- sys/chassis-[id]/sas-expander-[id]/fw-boot-def/bootunit-[type]
        -- fltFirmwareBootUnitCantBoot
        -- fltFirmwareBootUnitActivateStatusFailed
        -- fltFirmwareBootUnitPowerCycleRequired
        -- fltFirmwareBootUnitFirmwareBootFailed

-- storage:SasExpander
    -- sys/chassis-[id]/blade-[slotId]/board/sas-expander-[id]
    -- sys/rack-unit-[id]/board/sas-expander-[id]
    -- sys/chassis-[id]/cartridge-[slotId]/server-[serverInstanceId]/board/sas-expander-[id]
    -- sys/chassis-[id]/sas-expander-[id]
        -- fltStorageSasExpanderInoperable
        -- fltStorageSasExpanderAccessibility-problem
        -- fltStorageSasExpanderDegraded
        -- fltStorageSasExpanderLink-misconnect
        -- fltStorageSasExpanderLink-degraded

-- vnic:Fc
    -- org-[name]/tier-[name]/ls-[name]/fc-[name]
    -- org-[name]/ls-[name]/fc-[name]
    -- org-[name]/san-conn-pol-[name]/fc-[name]
        -- fltVnicFcConfig-failed
        -- fltVnicFcPinningMisconfig
        -- fltVnicFcUnsupported

-- network:Element
    -- sys/switch-[id]
        -- fltNetworkElementInoperable
        -- fltNetworkElementInventoryFailed
        -- fltNetworkElementThermalThresholdCritical
        -- fltNetworkElementMemoryerror
        -- fltNetworkElementRemoved
        -- fltNetworkElementKernelMemCricitalThreshold
        -- fltNetworkElementSystemshutdown
        -- fltNetworkElementDeprecated
        -- fltNetworkElementEvacuationon

-- sw:VlanPortNs
    -- sys/switch-[id]/vlan-port-ns
        -- fltSwVlanPortNsResourceStatus
        -- fltSwVlanPortNsVLANCompNotSupport
        -- fltSwVlanPortNsResourceStatusWarning
        -- fltSwVlanPortNsCompressedSetsExhaustedWarning

-- memory:BufferUnit
    -- sys/chassis-[id]/blade-[slotId]/board/sensor-unit-[id]
    -- sys/rack-unit-[id]/board/sensor-unit-[id]
    -- sys/chassis-[id]/cartridge-[slotId]/server-[serverInstanceId]/board/sensor-unit-[id]
        -- fltMemoryBufferUnitThermalThresholdNonCritical
        -- fltMemoryBufferUnitThermalThresholdCritical
        -- fltMemoryBufferUnitThermalThresholdNonRecoverable

-- equipment:FanModule
    -- sys/rack-unit-[id]/fan-module-[tray]-[id]
    -- sys/chassis-[id]/fan-module-[tray]-[id]
    -- sys/rack-enclosure-[id]/fan-module-[tray]-[id]
    -- sys/switch-[id]/fan-module-[tray]-[id]
        -- fltEquipmentFanModuleMissing
        -- fltEquipmentFanModuleThermalThresholdNonCritical
        -- fltEquipmentFanModuleThermalThresholdCritical
        -- fltEquipmentFanModuleThermalThresholdNonRecoverable
        -- fltEquipmentFanModuleIdentity
        -- fltEquipmentFanModuleDegraded
        -- fltEquipmentFanModuleInoperable

-- aaa:User
    -- sys/user-ext/user-[name]
        -- fltAaaUserLocalUserNotDeployed

-- memory:Array
    -- sys/chassis-[id]/blade-[slotId]/board/memarray-[id]
    -- sys/rack-unit-[id]/board/memarray-[id]
    -- sys/chassis-[id]/cartridge-[slotId]/server-[serverInstanceId]/board/memarray-[id]
        -- fltMemoryArrayVoltageThresholdNonCritical
        -- fltMemoryArrayVoltageThresholdCritical
        -- fltMemoryArrayVoltageThresholdNonRecoverable

-- pki:TP
    -- sys/pki-ext/tp-[name]
        -- fltPkiTPStatus

-- compute:ServerDiscPolicy
    -- org-[name]/server-discovery
        -- fsmStFailComputeServerDiscPolicyResolveScrubPolicy:Resolve
        -- fsmRmtErrComputeServerDiscPolicyResolveScrubPolicy:Resolve
        -- fsmFailComputeServerDiscPolicyResolveScrubPolicy

-- aaa:Domain
    -- sys/auth-realm/domain-[name]
        -- fltAaaDomainDomainNotDeployed

-- aaa:UserLocale
    -- sys/ldap-ext/ldapgroup-[name]/locale-[name]
    -- sys/user-ext/remoteuser-[name]/locale-[name]
    -- sys/user-ext/user-[name]/locale-[name]
        -- fltAaaUserLocaleUserLocaleNotDeployed

-- fcpool:Initiators
    -- org-[name]/wwn-pool-[name]
        -- fltFcpoolInitiatorsEmpty

-- compute:Blade
    -- sys/chassis-[id]/blade-[slotId]
        -- fsmStFailComputeBladeDiscover:BiosPostCompletion
        -- fsmStFailComputeBladeDiscover:BladeBootPnuos
        -- fsmStFailComputeBladeDiscover:BladeBootWait
        -- fsmStFailComputeBladeDiscover:BladePowerOn
        -- fsmStFailComputeBladeDiscover:BladeReadSmbios
        -- fsmStFailComputeBladeDiscover:BmcConfigPnuOS
        -- fsmStFailComputeBladeDiscover:BmcFactoryReset
        -- fsmStFailComputeBladeDiscover:BmcInventory
        -- fsmStFailComputeBladeDiscover:BmcPreConfigPnuOSLocal
        -- fsmStFailComputeBladeDiscover:BmcPreConfigPnuOSPeer
        -- fsmStFailComputeBladeDiscover:BmcPresence
        -- fsmStFailComputeBladeDiscover:BmcShutdownDiscovered
        -- fsmStFailComputeBladeDiscover:CheckAdaptorFw40GCap
        -- fsmStFailComputeBladeDiscover:CheckPowerAvailability
        -- fsmStFailComputeBladeDiscover:ConfigBMCPowerParams
        -- fsmStFailComputeBladeDiscover:ConfigFeLocal
        -- fsmStFailComputeBladeDiscover:ConfigFePeer
        -- fsmStFailComputeBladeDiscover:ConfigFlexFlashScrub
        -- fsmStFailComputeBladeDiscover:ConfigUserAccess
        -- fsmStFailComputeBladeDiscover:HandlePooling
        -- fsmStFailComputeBladeDiscover:NicConfigPnuOSLocal
        -- fsmStFailComputeBladeDiscover:NicConfigPnuOSPeer
        -- fsmStFailComputeBladeDiscover:NicPresenceLocal
        -- fsmStFailComputeBladeDiscover:NicPresencePeer
        -- fsmStFailComputeBladeDiscover:NicUnconfigPnuOSLocal
        -- fsmStFailComputeBladeDiscover:NicUnconfigPnuOSPeer
        -- fsmStFailComputeBladeDiscover:OobStorageInventory
        -- fsmStFailComputeBladeDiscover:PnuOSCatalog
        -- fsmStFailComputeBladeDiscover:PnuOSIdent
        -- fsmStFailComputeBladeDiscover:PnuOSInventory
        -- fsmStFailComputeBladeDiscover:PnuOSPolicy
        -- fsmStFailComputeBladeDiscover:PnuOSPowerProfiling
        -- fsmStFailComputeBladeDiscover:PnuOSScrub
        -- fsmStFailComputeBladeDiscover:PnuOSSelfTest
        -- fsmStFailComputeBladeDiscover:PostScrubOobStorageInventory
        -- fsmStFailComputeBladeDiscover:PowerDeployWait
        -- fsmStFailComputeBladeDiscover:PreSanitize
        -- fsmStFailComputeBladeDiscover:Sanitize
        -- fsmStFailComputeBladeDiscover:SendBmcProfilingDone
        -- fsmStFailComputeBladeDiscover:SendBmcProfilingInit
        -- fsmStFailComputeBladeDiscover:SetupVmediaLocal
        -- fsmStFailComputeBladeDiscover:SetupVmediaPeer
        -- fsmStFailComputeBladeDiscover:SolRedirectDisable
        -- fsmStFailComputeBladeDiscover:SolRedirectEnable
        -- fsmStFailComputeBladeDiscover:SwConfigPnuOSLocal
        -- fsmStFailComputeBladeDiscover:SwConfigPnuOSPeer
        -- fsmStFailComputeBladeDiscover:SwUnconfigPnuOSLocal
        -- fsmStFailComputeBladeDiscover:SwUnconfigPnuOSPeer
        -- fsmStFailComputeBladeDiscover:TeardownVmediaLocal
        -- fsmStFailComputeBladeDiscover:TeardownVmediaPeer
        -- fsmStFailComputeBladeDiscover:UnconfigCimcVMedia
        -- fsmStFailComputeBladeDiscover:UnconfigExtMgmtGw
        -- fsmStFailComputeBladeDiscover:UnconfigExtMgmtRules
        -- fsmStFailComputeBladeDiscover:hagConnect
        -- fsmStFailComputeBladeDiscover:hagDisconnect
        -- fsmStFailComputeBladeDiscover:serialDebugConnect
        -- fsmStFailComputeBladeDiscover:serialDebugDisconnect
        -- fsmRmtErrComputeBladeDiscover:BiosPostCompletion
        -- fsmRmtErrComputeBladeDiscover:BladeBootPnuos
        -- fsmRmtErrComputeBladeDiscover:BladeBootWait
        -- fsmRmtErrComputeBladeDiscover:BladePowerOn
        -- fsmRmtErrComputeBladeDiscover:BladeReadSmbios
        -- fsmRmtErrComputeBladeDiscover:BmcConfigPnuOS
        -- fsmRmtErrComputeBladeDiscover:BmcFactoryReset
        -- fsmRmtErrComputeBladeDiscover:BmcInventory
        -- fsmRmtErrComputeBladeDiscover:BmcPreConfigPnuOSLocal
        -- fsmRmtErrComputeBladeDiscover:BmcPreConfigPnuOSPeer
        -- fsmRmtErrComputeBladeDiscover:BmcPresence
        -- fsmRmtErrComputeBladeDiscover:BmcShutdownDiscovered
        -- fsmRmtErrComputeBladeDiscover:CheckAdaptorFw40GCap
        -- fsmRmtErrComputeBladeDiscover:CheckPowerAvailability
        -- fsmRmtErrComputeBladeDiscover:ConfigBMCPowerParams
        -- fsmRmtErrComputeBladeDiscover:ConfigFeLocal
        -- fsmRmtErrComputeBladeDiscover:ConfigFePeer
        -- fsmRmtErrComputeBladeDiscover:ConfigFlexFlashScrub
        -- fsmRmtErrComputeBladeDiscover:ConfigUserAccess
        -- fsmRmtErrComputeBladeDiscover:HandlePooling
        -- fsmRmtErrComputeBladeDiscover:NicConfigPnuOSLocal
        -- fsmRmtErrComputeBladeDiscover:NicConfigPnuOSPeer
        -- fsmRmtErrComputeBladeDiscover:NicPresenceLocal
        -- fsmRmtErrComputeBladeDiscover:NicPresencePeer
        -- fsmRmtErrComputeBladeDiscover:NicUnconfigPnuOSLocal
        -- fsmRmtErrComputeBladeDiscover:NicUnconfigPnuOSPeer
        -- fsmRmtErrComputeBladeDiscover:OobStorageInventory
        -- fsmRmtErrComputeBladeDiscover:PnuOSCatalog
        -- fsmRmtErrComputeBladeDiscover:PnuOSIdent
        -- fsmRmtErrComputeBladeDiscover:PnuOSInventory
        -- fsmRmtErrComputeBladeDiscover:PnuOSPolicy
        -- fsmRmtErrComputeBladeDiscover:PnuOSPowerProfiling
        -- fsmRmtErrComputeBladeDiscover:PnuOSScrub
        -- fsmRmtErrComputeBladeDiscover:PnuOSSelfTest
        -- fsmRmtErrComputeBladeDiscover:PostScrubOobStorageInventory
        -- fsmRmtErrComputeBladeDiscover:PowerDeployWait
        -- fsmRmtErrComputeBladeDiscover:PreSanitize
        -- fsmRmtErrComputeBladeDiscover:Sanitize
        -- fsmRmtErrComputeBladeDiscover:SendBmcProfilingDone
        -- fsmRmtErrComputeBladeDiscover:SendBmcProfilingInit
        -- fsmRmtErrComputeBladeDiscover:SetupVmediaLocal
        -- fsmRmtErrComputeBladeDiscover:SetupVmediaPeer
        -- fsmRmtErrComputeBladeDiscover:SolRedirectDisable
        -- fsmRmtErrComputeBladeDiscover:SolRedirectEnable
        -- fsmRmtErrComputeBladeDiscover:SwConfigPnuOSLocal
        -- fsmRmtErrComputeBladeDiscover:SwConfigPnuOSPeer
        -- fsmRmtErrComputeBladeDiscover:SwUnconfigPnuOSLocal
        -- fsmRmtErrComputeBladeDiscover:SwUnconfigPnuOSPeer
        -- fsmRmtErrComputeBladeDiscover:TeardownVmediaLocal
        -- fsmRmtErrComputeBladeDiscover:TeardownVmediaPeer
        -- fsmRmtErrComputeBladeDiscover:UnconfigCimcVMedia
        -- fsmRmtErrComputeBladeDiscover:UnconfigExtMgmtGw
        -- fsmRmtErrComputeBladeDiscover:UnconfigExtMgmtRules
        -- fsmRmtErrComputeBladeDiscover:hagConnect
        -- fsmRmtErrComputeBladeDiscover:hagDisconnect
        -- fsmRmtErrComputeBladeDiscover:serialDebugConnect
        -- fsmRmtErrComputeBladeDiscover:serialDebugDisconnect
        -- fsmFailComputeBladeDiscover

-- extvmm:NetworkSets
    -- fabric/lan/network-sets
        -- fsmStFailExtvmmNetworkSetsDeploy:Local
        -- fsmStFailExtvmmNetworkSetsDeploy:Peer
        -- fsmRmtErrExtvmmNetworkSetsDeploy:Local
        -- fsmRmtErrExtvmmNetworkSetsDeploy:Peer
        -- fsmFailExtvmmNetworkSetsDeploy

-- storage:VirtualDrive
    -- sys/chassis-[id]/blade-[slotId]/board/storage-[type]-[id]/vd-[id]
    -- sys/rack-unit-[id]/board/storage-[type]-[id]/vd-[id]
    -- sys/chassis-[id]/cartridge-[slotId]/server-[serverInstanceId]/board/storage-[type]-[id]/vd-[id]
    -- sys/chassis-[id]/storage-[type]-[id]/vd-[id]
    -- sys/chassis-[id]/blade-[slotId]/vd-container-[id]/vd-[id]
    -- sys/rack-unit-[id]/vd-container-[id]/vd-[id]
    -- sys/chassis-[id]/cartridge-[slotId]/server-[serverInstanceId]/vd-container-[id]/vd-[id]
    -- sys/chassis-[id]/vd-container-[id]/vd-[id]
        -- fltStorageVirtualDriveInoperable
        -- fltStorageVirtualDriveDegraded
        -- fltStorageVirtualDriveReconstructionFailed
        -- fltStorageVirtualDriveConsistencyCheckFailed
        -- fltStorageVirtualDriveDeployment-failure
        -- fltStorageVirtualDriveMissing
        -- fltStorageVirtualDriveMismatch

-- policy:Requestor
    -- sys/control-ep-[type]/source-[sourceDme]/context-[name]/scope-[policyType]-[resolveType]-[policyName]/requestor-[name]
        -- fsmStFailPolicyRequestorResolveFromCentral:ResolveFromOpsMgr
        -- fsmStFailPolicyRequestorResolveFromCentral:ResolveFromPolicyMgr
        -- fsmRmtErrPolicyRequestorResolveFromCentral:ResolveFromOpsMgr
        -- fsmRmtErrPolicyRequestorResolveFromCentral:ResolveFromPolicyMgr
        -- fsmFailPolicyRequestorResolveFromCentral

-- network:Limit
    -- sys/switch-[id]/limit-type-[type]-asic-[asicNumber]
        -- fltNetworkLimitUnicast-mac
        -- fltNetworkLimitMulticast-mac
        -- fltNetworkLimitPvlifvlanmbr
        -- fltNetworkLimitPvsystem
        -- fltNetworkLimitIgmpgroup
        -- fltNetworkLimitIftmcpv
        -- fltNetworkLimitDvif

-- equipment:Fex
    -- sys/fex-[id]
        -- fltEquipmentFexPost-failure
        -- fltEquipmentFexIdentity
        -- fltEquipmentFexIdentity-unestablishable
        -- fltEquipmentFexFex-unsupported
        -- fltEquipmentFexBackPlanePortProblem
        -- fsmStFailEquipmentFexRemoveFex:CleanUpVIfs
        -- fsmStFailEquipmentFexRemoveFex:CleanupEntries
        -- fsmStFailEquipmentFexRemoveFex:UnIdentifyLocal
        -- fsmStFailEquipmentFexRemoveFex:Wait
        -- fsmStFailEquipmentFexRemoveFex:decomission
        -- fsmRmtErrEquipmentFexRemoveFex:CleanUpVIfs
        -- fsmRmtErrEquipmentFexRemoveFex:CleanupEntries
        -- fsmRmtErrEquipmentFexRemoveFex:UnIdentifyLocal
        -- fsmRmtErrEquipmentFexRemoveFex:Wait
        -- fsmRmtErrEquipmentFexRemoveFex:decomission
        -- fsmFailEquipmentFexRemoveFex

-- fabric:LanCloud
    -- fabric/lan
        -- fsmStFailFabricLanCloudSwitchMode:SwConfigLocal
        -- fsmStFailFabricLanCloudSwitchMode:SwConfigPeer
        -- fsmStFailFabricLanCloudSwitchMode:WaitForUserAck
        -- fsmRmtErrFabricLanCloudSwitchMode:SwConfigLocal
        -- fsmRmtErrFabricLanCloudSwitchMode:SwConfigPeer
        -- fsmRmtErrFabricLanCloudSwitchMode:WaitForUserAck
        -- fsmFailFabricLanCloudSwitchMode

-- iqnpool:Pool
    -- org-[name]/iqn-pool-[name]
        -- fltIqnpoolPoolEmpty

-- fabric:VlanReq
    -- org-[name]/vlan-req-[name]
        -- fltFabricVlanReqVlanPermitUnresolved

-- equipment:BeaconLed
    -- sys/chassis-[id]/blade-[slotId]/beacon
    -- sys/rack-unit-[id]/beacon
    -- sys/chassis-[id]/cartridge-[slotId]/server-[serverInstanceId]/beacon
    -- sys/chassis-[id]/beacon
    -- sys/rack-unit-[id]/fan-module-[tray]-[id]/beacon
    -- sys/chassis-[id]/fan-module-[tray]-[id]/beacon
    -- sys/rack-enclosure-[id]/fan-module-[tray]-[id]/beacon
    -- sys/switch-[id]/fan-module-[tray]-[id]/beacon
    -- sys/fex-[id]/beacon
    -- sys/chassis-[id]/slot-[id]/beacon
    -- sys/fex-[id]/slot-[id]/beacon
    -- sys/rack-unit-[id]/psu-[id]/beacon
    -- sys/chassis-[id]/psu-[id]/beacon
    -- sys/fex-[id]/psu-[id]/beacon
    -- sys/rack-enclosure-[id]/psu-[id]/beacon
    -- sys/switch-[id]/psu-[id]/beacon
    -- sys/switch-[id]/slot-[id]/beacon
        -- fsmStFailEquipmentBeaconLedIlluminate:ExecuteA
        -- fsmStFailEquipmentBeaconLedIlluminate:ExecuteB
        -- fsmRmtErrEquipmentBeaconLedIlluminate:ExecuteA
        -- fsmRmtErrEquipmentBeaconLedIlluminate:ExecuteB
        -- fsmFailEquipmentBeaconLedIlluminate

-- fabric:NetflowMonSession
    -- fabric/lanmon/eth-flow-monitoring/netflow-mon-[name]
        -- fltFabricNetflowMonSessionFlowMonConfigFail
        -- fltFabricNetflowMonSessionNetflowSessionConfigFail

-- port:PIo
    -- sys/chassis-[id]/slot-[id]/[type]/port-[portId]
    -- sys/fex-[id]/slot-[id]/[type]/port-[portId]
    -- sys/chassis-[id]/shared-io-module/[type]/port-[portId]
    -- sys/chassis-[id]/slot-[id]/shared-io-module/[type]/port-[portId]
    -- sys/switch-[id]/slot-[id]/[type]/port-[portId]
    -- sys/chassis-[id]/sw-slot-[id]/[type]/port-[portId]
    -- sys/chassis-[id]/slot-[id]/[type]/aggr-port-[aggrPortId]/port-[portId]
    -- sys/fex-[id]/slot-[id]/[type]/aggr-port-[aggrPortId]/port-[portId]
    -- sys/chassis-[id]/shared-io-module/[type]/aggr-port-[aggrPortId]/port-[portId]
    -- sys/chassis-[id]/slot-[id]/shared-io-module/[type]/aggr-port-[aggrPortId]/port-[portId]
    -- sys/switch-[id]/slot-[id]/[type]/aggr-port-[aggrPortId]/port-[portId]
    -- sys/chassis-[id]/sw-slot-[id]/[type]/aggr-port-[aggrPortId]/port-[portId]
        -- fltPortPIoLink-down
        -- fltPortPIoFailed
        -- fltPortPIoHardware-failure
        -- fltPortPIoSfp-not-present
        -- fltPortPIoInvalid-sfp
        -- fsmStFailPortPIoInCompatSfpPresence:Shutdown
        -- fsmStFailPortPIoInCompatSfpReplaced:EnablePort
        -- fsmRmtErrPortPIoInCompatSfpPresence:Shutdown
        -- fsmRmtErrPortPIoInCompatSfpReplaced:EnablePort
        -- fsmFailPortPIoInCompatSfpPresence
        -- fsmFailPortPIoInCompatSfpReplaced

-- extvmm:KeyStore
    -- sys/extvm-mgmt/key-store
        -- fsmStFailExtvmmKeyStoreCertInstall:SetLocal
        -- fsmStFailExtvmmKeyStoreCertInstall:SetPeer
        -- fsmRmtErrExtvmmKeyStoreCertInstall:SetLocal
        -- fsmRmtErrExtvmmKeyStoreCertInstall:SetPeer
        -- fsmFailExtvmmKeyStoreCertInstall

-- fabric:DceSwSrvEp
    -- fabric/server/sw-[id]/slot-[slotId]-port-[portId]
    -- fabric/server/sw-[id]/slot-[slotId]-aggr-port-[aggrPortId]/slot-[slotId]-port-[portId]
    -- fabric/server/sw-[id]/pc-[portId]/slot-[slotId]-aggr-port-[aggrPortId]/slot-[slotId]-port-[portId]
    -- fabric/eth-estc/[id]/slot-[slotId]-aggr-port-[aggrPortId]/slot-[slotId]-port-[portId]
    -- fabric/eth-estc/[id]/pc-[portId]/slot-[slotId]-aggr-port-[aggrPortId]/slot-[slotId]-port-[portId]
    -- fabric/lan/[id]/slot-[slotId]-aggr-port-[aggrPortId]/slot-[slotId]-port-[portId]
    -- fabric/lan/[id]/pc-[portId]/slot-[slotId]-aggr-port-[aggrPortId]/slot-[slotId]-port-[portId]
    -- fabric/lanmon/[id]/eth-mon-[name]/slot-[slotId]-aggr-port-[aggrPortId]/slot-[slotId]-port-[portId]
    -- fabric/fc-estc/[id]/slot-[slotId]-aggr-port-[aggrPortId]/slot-[slotId]-port-[portId]
    -- fabric/sanmon/[id]/fc-mon-[name]/slot-[slotId]-aggr-port-[aggrPortId]/slot-[slotId]-port-[portId]
    -- fabric/san/[id]/slot-[slotId]-aggr-port-[aggrPortId]/slot-[slotId]-port-[portId]
    -- fabric/san/[id]/fcoesanpc-[portId]/slot-[slotId]-aggr-port-[aggrPortId]/slot-[slotId]-port-[portId]
        -- fltFabricDceSwSrvEpDown

-- storage:NvmeSwitch
    -- sys/chassis-[id]/blade-[slotId]/board/nvme-switch-[id]
    -- sys/rack-unit-[id]/board/nvme-switch-[id]
    -- sys/chassis-[id]/cartridge-[slotId]/server-[serverInstanceId]/board/nvme-switch-[id]
        -- fltStorageNvmeSwitchDegraded

-- fabric:ExternalEp
        -- fltFabricExternalEpFcZoningEnable

-- sysdebug:LogControlEp
    -- sys/sysdebug/logcontrol
        -- fsmStFailSysdebugLogControlEpLogControlPersist:Local
        -- fsmStFailSysdebugLogControlEpLogControlPersist:Peer
        -- fsmRmtErrSysdebugLogControlEpLogControlPersist:Local
        -- fsmRmtErrSysdebugLogControlEpLogControlPersist:Peer
        -- fsmFailSysdebugLogControlEpLogControlPersist

-- ls:Issues
    -- org-[name]/tier-[name]/ls-[name]/config-issue
    -- org-[name]/ls-[name]/config-issue
        -- fltLsIssuesIscsi-config-failed
        -- fltLsIssuesKvmPolicyUnsupported

-- compute:ABoard
        -- fltComputeABoardThermalProblem
        -- fltComputeABoardMotherBoardVoltageThresholdUpperNonRecoverable
        -- fltComputeABoardMotherBoardVoltageThresholdLowerNonRecoverable
        -- fltComputeABoardMotherBoardVoltageUpperThresholdCritical
        -- fltComputeABoardMotherBoardVoltageLowerThresholdCritical
        -- fltComputeABoardPowerUsageProblem

-- equipment:LocatorLed
    -- sys/chassis-[id]/blade-[slotId]/ext-board-[id]/locator-led
    -- sys/rack-unit-[id]/ext-board-[id]/locator-led
    -- sys/chassis-[id]/cartridge-[slotId]/server-[serverInstanceId]/ext-board-[id]/locator-led
    -- sys/chassis-[id]/blade-[slotId]/locator-led
    -- sys/rack-unit-[id]/locator-led
    -- sys/chassis-[id]/cartridge-[slotId]/server-[serverInstanceId]/locator-led
    -- sys/chassis-[id]/locator-led
    -- sys/rack-unit-[id]/fan-module-[tray]-[id]/locator-led
    -- sys/chassis-[id]/fan-module-[tray]-[id]/locator-led
    -- sys/rack-enclosure-[id]/fan-module-[tray]-[id]/locator-led
    -- sys/switch-[id]/fan-module-[tray]-[id]/locator-led
    -- sys/fex-[id]/locator-led
    -- sys/chassis-[id]/slot-[id]/locator-led
    -- sys/fex-[id]/slot-[id]/locator-led
    -- sys/rack-unit-[id]/psu-[id]/locator-led
    -- sys/chassis-[id]/psu-[id]/locator-led
    -- sys/fex-[id]/psu-[id]/locator-led
    -- sys/rack-enclosure-[id]/psu-[id]/locator-led
    -- sys/switch-[id]/psu-[id]/locator-led
    -- sys/switch-[id]/locator-led
    -- sys/chassis-[id]/blade-[slotId]/board/storage-[type]-[id]/disk-[id]/locator-led
    -- sys/rack-unit-[id]/board/storage-[type]-[id]/disk-[id]/locator-led
    -- sys/chassis-[id]/cartridge-[slotId]/server-[serverInstanceId]/board/storage-[type]-[id]/disk-[id]/locator-led
    -- sys/chassis-[id]/storage-[type]-[id]/disk-[id]/locator-led
    -- sys/chassis-[id]/blade-[slotId]/enc-[id]/disk-[id]/locator-led
    -- sys/rack-unit-[id]/enc-[id]/disk-[id]/locator-led
    -- sys/chassis-[id]/cartridge-[slotId]/server-[serverInstanceId]/enc-[id]/disk-[id]/locator-led
    -- sys/chassis-[id]/enc-[id]/disk-[id]/locator-led
    -- sys/chassis-[id]/blade-[slotId]/board/storage-[type]-[id]/enc-[id]/disk-[id]/locator-led
    -- sys/rack-unit-[id]/board/storage-[type]-[id]/enc-[id]/disk-[id]/locator-led
    -- sys/chassis-[id]/cartridge-[slotId]/server-[serverInstanceId]/board/storage-[type]-[id]/enc-[id]/disk-[id]/locator-led
    -- sys/chassis-[id]/storage-[type]-[id]/enc-[id]/disk-[id]/locator-led
        -- fsmStFailEquipmentLocatorLedSetLocatorLed:Execute
        -- fsmStFailEquipmentLocatorLedSetFeLocatorLed:Execute
        -- fsmStFailEquipmentLocatorLedSetFiLocatorLed:Execute
        -- fsmRmtErrEquipmentLocatorLedSetLocatorLed:Execute
        -- fsmRmtErrEquipmentLocatorLedSetFeLocatorLed:Execute
        -- fsmRmtErrEquipmentLocatorLedSetFiLocatorLed:Execute
        -- fsmFailEquipmentLocatorLedSetLocatorLed
        -- fsmFailEquipmentLocatorLedSetFeLocatorLed
        -- fsmFailEquipmentLocatorLedSetFiLocatorLed

-- storage:FlexFlashController
    -- sys/chassis-[id]/blade-[slotId]/board/storage-flexflash-[id]
    -- sys/rack-unit-[id]/board/storage-flexflash-[id]
    -- sys/chassis-[id]/cartridge-[slotId]/server-[serverInstanceId]/board/storage-flexflash-[id]
        -- fltStorageFlexFlashControllerInoperable
        -- fltStorageFlexFlashControllerUnhealthy
        -- fltStorageFlexFlashControllerMismatch
        -- fsmStFailStorageFlexFlashControllerMOpsReset:Reset
        -- fsmStFailStorageFlexFlashControllerMOpsFormat:Format
        -- fsmStFailStorageFlexFlashControllerMOpsPair:Pair
        -- fsmRmtErrStorageFlexFlashControllerMOpsReset:Reset
        -- fsmRmtErrStorageFlexFlashControllerMOpsFormat:Format
        -- fsmRmtErrStorageFlexFlashControllerMOpsPair:Pair
        -- fsmFailStorageFlexFlashControllerMOpsReset
        -- fsmFailStorageFlexFlashControllerMOpsFormat
        -- fsmFailStorageFlexFlashControllerMOpsPair

-- callhome:Ep
    -- call-home
        -- fltCallhomeEpNoSnmpPolicyForCallhome
        -- fsmStFailCallhomeEpConfigCallhome:SetLocal
        -- fsmStFailCallhomeEpConfigCallhome:SetPeer
        -- fsmRmtErrCallhomeEpConfigCallhome:SetLocal
        -- fsmRmtErrCallhomeEpConfigCallhome:SetPeer
        -- fsmFailCallhomeEpConfigCallhome

-- fabric:ComputeSlotEp
    -- fabric/server/chassis-[chassisId]/slot-[slotId]
        -- fltFabricComputeSlotEpMisplacedInChassisSlot
        -- fltFabricComputeSlotEpServerIdentificationProblem
        -- fltFabricComputeSlotEpNotSupportedInChassisSlot
        -- fsmStFailFabricComputeSlotEpIdentify:ExecuteLocal
        -- fsmStFailFabricComputeSlotEpIdentify:ExecutePeer
        -- fsmRmtErrFabricComputeSlotEpIdentify:ExecuteLocal
        -- fsmRmtErrFabricComputeSlotEpIdentify:ExecutePeer
        -- fsmFailFabricComputeSlotEpIdentify

-- fabric:Mon
        -- fltFabricMonSpanConfigFail

-- moref:ImportRoot
    -- import-ref-root
        -- fsmStFailMorefImportRootApplyMoRefs:ApplyMoProps
        -- fsmStFailMorefImportRootApplyMoRefs:DeleteAllMoRefs
        -- fsmRmtErrMorefImportRootApplyMoRefs:ApplyMoProps
        -- fsmRmtErrMorefImportRootApplyMoRefs:DeleteAllMoRefs
        -- fsmFailMorefImportRootApplyMoRefs

-- compute:Pool
    -- org-[name]/compute-pool-[name]
        -- fltComputePoolEmpty

-- extpol:Registry
    -- extpol/reg
        -- fsmStFailExtpolRegistryCrossDomainConfig:SetLocal
        -- fsmStFailExtpolRegistryCrossDomainConfig:SetPeer
        -- fsmStFailExtpolRegistryCrossDomainDelete:SetLocal
        -- fsmStFailExtpolRegistryCrossDomainDelete:SetPeer
        -- fsmRmtErrExtpolRegistryCrossDomainConfig:SetLocal
        -- fsmRmtErrExtpolRegistryCrossDomainConfig:SetPeer
        -- fsmRmtErrExtpolRegistryCrossDomainDelete:SetLocal
        -- fsmRmtErrExtpolRegistryCrossDomainDelete:SetPeer
        -- fsmFailExtpolRegistryCrossDomainConfig
        -- fsmFailExtpolRegistryCrossDomainDelete

-- firmware:Downloader
    -- sys/fw-catalogue/dnld-[fileName]
        -- fsmStFailFirmwareDownloaderDownload:CopyRemote
        -- fsmStFailFirmwareDownloaderDownload:DeleteLocal
        -- fsmStFailFirmwareDownloaderDownload:Local
        -- fsmStFailFirmwareDownloaderDownload:UnpackLocal
        -- fsmRmtErrFirmwareDownloaderDownload:CopyRemote
        -- fsmRmtErrFirmwareDownloaderDownload:DeleteLocal
        -- fsmRmtErrFirmwareDownloaderDownload:Local
        -- fsmRmtErrFirmwareDownloaderDownload:UnpackLocal
        -- fsmFailFirmwareDownloaderDownload

-- qosclass:Definition
    -- fabric/lan/classes
        -- fsmStFailQosclassDefinitionConfigGlobalQoS:SetLocal
        -- fsmStFailQosclassDefinitionConfigGlobalQoS:SetPeer
        -- fsmStFailQosclassDefinitionConfigGlobalQoS:WaitForUserAck
        -- fsmRmtErrQosclassDefinitionConfigGlobalQoS:SetLocal
        -- fsmRmtErrQosclassDefinitionConfigGlobalQoS:SetPeer
        -- fsmRmtErrQosclassDefinitionConfigGlobalQoS:WaitForUserAck
        -- fsmFailQosclassDefinitionConfigGlobalQoS

-- mgmt:Entity
    -- sys/mgmt-entity-[id]
        -- fltMgmtEntityDegraded
        -- fltMgmtEntityDown
        -- fltMgmtEntityElection-failure
        -- fltMgmtEntityHa-not-ready
        -- fltMgmtEntityVersion-incompatible
        -- fltMgmtEntityManagement-services-failure
        -- fltMgmtEntityManagement-services-unresponsive
        -- fltMgmtEntityDevice-1-shared-storage-error
        -- fltMgmtEntityDevice-2-shared-storage error
        -- fltMgmtEntityDevice-3-shared-storage error
        -- fltMgmtEntityHa-ssh-keys-mismatched
        -- fltMgmtEntityDevice-1-shared-storage-connect error
        -- fltMgmtEntityDevice-2-shared-storage-connect error
        -- fltMgmtEntityDevice-3-shared-storage-connect error
        -- fltMgmtEntityMgmt-db-version-mismatch

-- sw:EthLanFlowMon
    -- sys/switch-[id]/ethlanflowmon
        -- fsmStFailSwEthLanFlowMonDeploy:UpdateEthFlowMon
        -- fsmRmtErrSwEthLanFlowMonDeploy:UpdateEthFlowMon
        -- fsmFailSwEthLanFlowMonDeploy

-- vnic:IScsi
    -- org-[name]/tier-[name]/ls-[name]/iscsi-[name]
    -- org-[name]/ls-[name]/iscsi-[name]
        -- fltVnicIScsiConfig-failed

-- aaa:Org
    -- sys/user-ext/locale-[name]/org-[name]
        -- fltAaaOrgLocaleOrgNotPresent

-- compute:ServerUnit
    -- sys/chassis-[id]/cartridge-[slotId]/server-[serverInstanceId]
        -- fsmStFailComputeServerUnitDiscover:BiosPostCompletion
        -- fsmStFailComputeServerUnitDiscover:BladeBootWait
        -- fsmStFailComputeServerUnitDiscover:BmcConfigPnuOS
        -- fsmStFailComputeServerUnitDiscover:BmcFactoryReset
        -- fsmStFailComputeServerUnitDiscover:BmcInventory
        -- fsmStFailComputeServerUnitDiscover:BmcShutdownDiscovered
        -- fsmStFailComputeServerUnitDiscover:BootPnuos
        -- fsmStFailComputeServerUnitDiscover:CimcPresence
        -- fsmStFailComputeServerUnitDiscover:CleanupNicConfigLocal
        -- fsmStFailComputeServerUnitDiscover:CleanupNicConfigPeer
        -- fsmStFailComputeServerUnitDiscover:ConfigUserAccess
        -- fsmStFailComputeServerUnitDiscover:HandlePooling
        -- fsmStFailComputeServerUnitDiscover:PreSanitize
        -- fsmStFailComputeServerUnitDiscover:ReadSmbios
        -- fsmStFailComputeServerUnitDiscover:Sanitize
        -- fsmStFailComputeServerUnitDiscover:UnconfigCimcVMedia
        -- fsmStFailComputeServerUnitDiscover:UnconfigExtMgmtGw
        -- fsmStFailComputeServerUnitDiscover:UnconfigExtMgmtRules
        -- fsmRmtErrComputeServerUnitDiscover:BiosPostCompletion
        -- fsmRmtErrComputeServerUnitDiscover:BladeBootWait
        -- fsmRmtErrComputeServerUnitDiscover:BmcConfigPnuOS
        -- fsmRmtErrComputeServerUnitDiscover:BmcFactoryReset
        -- fsmRmtErrComputeServerUnitDiscover:BmcInventory
        -- fsmRmtErrComputeServerUnitDiscover:BmcShutdownDiscovered
        -- fsmRmtErrComputeServerUnitDiscover:BootPnuos
        -- fsmRmtErrComputeServerUnitDiscover:CimcPresence
        -- fsmRmtErrComputeServerUnitDiscover:CleanupNicConfigLocal
        -- fsmRmtErrComputeServerUnitDiscover:CleanupNicConfigPeer
        -- fsmRmtErrComputeServerUnitDiscover:ConfigUserAccess
        -- fsmRmtErrComputeServerUnitDiscover:HandlePooling
        -- fsmRmtErrComputeServerUnitDiscover:PreSanitize
        -- fsmRmtErrComputeServerUnitDiscover:ReadSmbios
        -- fsmRmtErrComputeServerUnitDiscover:Sanitize
        -- fsmRmtErrComputeServerUnitDiscover:UnconfigCimcVMedia
        -- fsmRmtErrComputeServerUnitDiscover:UnconfigExtMgmtGw
        -- fsmRmtErrComputeServerUnitDiscover:UnconfigExtMgmtRules
        -- fsmFailComputeServerUnitDiscover

-- fabric:DceSwSrvPcEp
    -- fabric/server/sw-[id]/pc-[portId]/ep-slot-[slotId]-port-[portId]
    -- fabric/server/sw-[id]/slot-[slotId]-aggr-port-[aggrPortId]/ep-slot-[slotId]-port-[portId]
    -- fabric/server/sw-[id]/pc-[portId]/slot-[slotId]-aggr-port-[aggrPortId]/ep-slot-[slotId]-port-[portId]
    -- fabric/eth-estc/[id]/slot-[slotId]-aggr-port-[aggrPortId]/ep-slot-[slotId]-port-[portId]
    -- fabric/eth-estc/[id]/pc-[portId]/slot-[slotId]-aggr-port-[aggrPortId]/ep-slot-[slotId]-port-[portId]
    -- fabric/lan/[id]/slot-[slotId]-aggr-port-[aggrPortId]/ep-slot-[slotId]-port-[portId]
    -- fabric/lan/[id]/pc-[portId]/slot-[slotId]-aggr-port-[aggrPortId]/ep-slot-[slotId]-port-[portId]
    -- fabric/lanmon/[id]/eth-mon-[name]/slot-[slotId]-aggr-port-[aggrPortId]/ep-slot-[slotId]-port-[portId]
    -- fabric/fc-estc/[id]/slot-[slotId]-aggr-port-[aggrPortId]/ep-slot-[slotId]-port-[portId]
    -- fabric/sanmon/[id]/fc-mon-[name]/slot-[slotId]-aggr-port-[aggrPortId]/ep-slot-[slotId]-port-[portId]
    -- fabric/san/[id]/slot-[slotId]-aggr-port-[aggrPortId]/ep-slot-[slotId]-port-[portId]
    -- fabric/san/[id]/fcoesanpc-[portId]/slot-[slotId]-aggr-port-[aggrPortId]/ep-slot-[slotId]-port-[portId]
        -- fltFabricDceSwSrvPcEpDown

-- sysdebug:AutoCoreFileExportTarget
    -- sys/sysdebug/file-export
        -- fltSysdebugAutoCoreFileExportTargetAutoCoreTransferFailure
        -- fsmStFailSysdebugAutoCoreFileExportTargetConfigure:Local
        -- fsmStFailSysdebugAutoCoreFileExportTargetConfigure:Peer
        -- fsmRmtErrSysdebugAutoCoreFileExportTargetConfigure:Local
        -- fsmRmtErrSysdebugAutoCoreFileExportTargetConfigure:Peer
        -- fsmFailSysdebugAutoCoreFileExportTargetConfigure

-- vnic:Ether
    -- org-[name]/tier-[name]/ls-[name]/ether-[name]
    -- org-[name]/ls-[name]/ether-[name]
    -- org-[name]/lan-conn-pol-[name]/ether-[name]
        -- fltVnicEtherConfig-failed
        -- fltVnicEtherPinningMismatch
        -- fltVnicEtherPinningMisconfig
        -- fltVnicEtherVirtualization-conflict
        -- fltVnicEtherVirtualization-netflow-conflict
        -- fltVnicEtherCdn-config-not-applied
        -- fltVnicEtherPrimaryVlanMissing
        -- fltVnicEtherNetSanGroupMisconfigured

-- pool:Element
        -- fltPoolElementDuplicatedAssigned

-- ls:ComputeBinding
    -- org-[name]/tier-[name]/ls-[name]/
    -- org-[name]/ls-[name]/
        -- fltLsComputeBindingAssignmentRequirementsNotMet

-- sysdebug:LogExportPolicy
    -- sys/sysdebug/log-export-policy
        -- fsmStFailSysdebugLogExportPolicyConfigure:Local
        -- fsmStFailSysdebugLogExportPolicyConfigure:Peer
        -- fsmRmtErrSysdebugLogExportPolicyConfigure:Local
        -- fsmRmtErrSysdebugLogExportPolicyConfigure:Peer
        -- fsmFailSysdebugLogExportPolicyConfigure

-- compute:RackUnit
    -- sys/rack-unit-[id]
        -- fltComputeRackUnitFanSpeedConfigurationFailed
        -- fltComputeRackUnitPhysical-security
        -- fltComputeRackUnitUnsupportedConfig
        -- fltComputeRackUnitConfigMismatch
        -- fsmStFailComputeRackUnitDiscover:BiosPostCompletion
        -- fsmStFailComputeRackUnitDiscover:BladePowerOff
        -- fsmStFailComputeRackUnitDiscover:BmcConfigPnuOS
        -- fsmStFailComputeRackUnitDiscover:BmcConfigureConnLocal
        -- fsmStFailComputeRackUnitDiscover:BmcConfigureConnPeer
        -- fsmStFailComputeRackUnitDiscover:BmcFactoryReset
        -- fsmStFailComputeRackUnitDiscover:BmcInventory
        -- fsmStFailComputeRackUnitDiscover:BmcPreconfigPnuOSLocal
        -- fsmStFailComputeRackUnitDiscover:BmcPreconfigPnuOSPeer
        -- fsmStFailComputeRackUnitDiscover:BmcPresence
        -- fsmStFailComputeRackUnitDiscover:BmcShutdownDiscovered
        -- fsmStFailComputeRackUnitDiscover:BmcUnconfigPnuOS
        -- fsmStFailComputeRackUnitDiscover:BootPnuos
        -- fsmStFailComputeRackUnitDiscover:BootWait
        -- fsmStFailComputeRackUnitDiscover:CheckPowerAvailability
        -- fsmStFailComputeRackUnitDiscover:ConfigDiscoveryMode
        -- fsmStFailComputeRackUnitDiscover:ConfigFlexFlashScrub
        -- fsmStFailComputeRackUnitDiscover:ConfigNivMode
        -- fsmStFailComputeRackUnitDiscover:ConfigUserAccess
        -- fsmStFailComputeRackUnitDiscover:HandlePooling
        -- fsmStFailComputeRackUnitDiscover:NicConfigPnuOSLocal
        -- fsmStFailComputeRackUnitDiscover:NicConfigPnuOSPeer
        -- fsmStFailComputeRackUnitDiscover:NicInventoryLocal
        -- fsmStFailComputeRackUnitDiscover:NicInventoryPeer
        -- fsmStFailComputeRackUnitDiscover:OobStorageConfig
        -- fsmStFailComputeRackUnitDiscover:OobStorageInventory
        -- fsmStFailComputeRackUnitDiscover:PnuOSCatalog
        -- fsmStFailComputeRackUnitDiscover:PnuOSConnStatus
        -- fsmStFailComputeRackUnitDiscover:PnuOSConnectivity
        -- fsmStFailComputeRackUnitDiscover:PnuOSIdent
        -- fsmStFailComputeRackUnitDiscover:PnuOSInventory
        -- fsmStFailComputeRackUnitDiscover:PnuOSPolicy
        -- fsmStFailComputeRackUnitDiscover:PnuOSScrub
        -- fsmStFailComputeRackUnitDiscover:PnuOSSelfTest
        -- fsmStFailComputeRackUnitDiscover:PnuosBootWait
        -- fsmStFailComputeRackUnitDiscover:PowerDeployWait
        -- fsmStFailComputeRackUnitDiscover:PreSanitize
        -- fsmStFailComputeRackUnitDiscover:ReadSmbios
        -- fsmStFailComputeRackUnitDiscover:Sanitize
        -- fsmStFailComputeRackUnitDiscover:SolRedirectDisable
        -- fsmStFailComputeRackUnitDiscover:SolRedirectEnable
        -- fsmStFailComputeRackUnitDiscover:SwConfigPnuOSLocal
        -- fsmStFailComputeRackUnitDiscover:SwConfigPnuOSPeer
        -- fsmStFailComputeRackUnitDiscover:SwConfigPortNivLocal
        -- fsmStFailComputeRackUnitDiscover:SwConfigPortNivPeer
        -- fsmStFailComputeRackUnitDiscover:SwConfigureConnLocal
        -- fsmStFailComputeRackUnitDiscover:SwConfigureConnPeer
        -- fsmStFailComputeRackUnitDiscover:SwConfigurePortChannelLocal
        -- fsmStFailComputeRackUnitDiscover:SwConfigurePortChannelPeer
        -- fsmStFailComputeRackUnitDiscover:SwHostOSConfigurePortChannelLocal
        -- fsmStFailComputeRackUnitDiscover:SwHostOSConfigurePortChannelPeer
        -- fsmStFailComputeRackUnitDiscover:SwHostOSMultiPortConnectivityLocal
        -- fsmStFailComputeRackUnitDiscover:SwHostOSMultiPortConnectivityPeer
        -- fsmStFailComputeRackUnitDiscover:SwPnuOSConnectivityLocal
        -- fsmStFailComputeRackUnitDiscover:SwPnuOSConnectivityPeer
        -- fsmStFailComputeRackUnitDiscover:SwPortDetailsLocal
        -- fsmStFailComputeRackUnitDiscover:SwPortDetailsPeer
        -- fsmStFailComputeRackUnitDiscover:SwUnconfigPortNivLocal
        -- fsmStFailComputeRackUnitDiscover:SwUnconfigPortNivPeer
        -- fsmStFailComputeRackUnitDiscover:UnconfigCimcVMedia
        -- fsmStFailComputeRackUnitDiscover:UnconfigExtMgmtGw
        -- fsmStFailComputeRackUnitDiscover:UnconfigExtMgmtRules
        -- fsmStFailComputeRackUnitDiscover:hagConnect
        -- fsmStFailComputeRackUnitDiscover:hagDisconnect
        -- fsmStFailComputeRackUnitDiscover:serialDebugConnect
        -- fsmStFailComputeRackUnitDiscover:serialDebugDisconnect
        -- fsmStFailComputeRackUnitDiscover:waitForConnReady
        -- fsmStFailComputeRackUnitOffline:CleanupLocal
        -- fsmStFailComputeRackUnitOffline:CleanupPeer
        -- fsmStFailComputeRackUnitOffline:SwUnconfigureLocal
        -- fsmStFailComputeRackUnitOffline:SwUnconfigurePeer
        -- fsmStFailComputeRackUnitAdapterReset:DeassertResetBypass
        -- fsmStFailComputeRackUnitAdapterReset:PowerCycle
        -- fsmStFailComputeRackUnitAdapterReset:PreSanitize
        -- fsmStFailComputeRackUnitAdapterReset:Sanitize
        -- fsmStFailComputeRackUnitCreateDhcpEntry:ExecuteLocal
        -- fsmStFailComputeRackUnitCreateDhcpEntry:ExecutePeer
        -- fsmRmtErrComputeRackUnitDiscover:BiosPostCompletion
        -- fsmRmtErrComputeRackUnitDiscover:BladePowerOff
        -- fsmRmtErrComputeRackUnitDiscover:BmcConfigPnuOS
        -- fsmRmtErrComputeRackUnitDiscover:BmcConfigureConnLocal
        -- fsmRmtErrComputeRackUnitDiscover:BmcConfigureConnPeer
        -- fsmRmtErrComputeRackUnitDiscover:BmcFactoryReset
        -- fsmRmtErrComputeRackUnitDiscover:BmcInventory
        -- fsmRmtErrComputeRackUnitDiscover:BmcPreconfigPnuOSLocal
        -- fsmRmtErrComputeRackUnitDiscover:BmcPreconfigPnuOSPeer
        -- fsmRmtErrComputeRackUnitDiscover:BmcPresence
        -- fsmRmtErrComputeRackUnitDiscover:BmcShutdownDiscovered
        -- fsmRmtErrComputeRackUnitDiscover:BmcUnconfigPnuOS
        -- fsmRmtErrComputeRackUnitDiscover:BootPnuos
        -- fsmRmtErrComputeRackUnitDiscover:BootWait
        -- fsmRmtErrComputeRackUnitDiscover:CheckPowerAvailability
        -- fsmRmtErrComputeRackUnitDiscover:ConfigDiscoveryMode
        -- fsmRmtErrComputeRackUnitDiscover:ConfigFlexFlashScrub
        -- fsmRmtErrComputeRackUnitDiscover:ConfigNivMode
        -- fsmRmtErrComputeRackUnitDiscover:ConfigUserAccess
        -- fsmRmtErrComputeRackUnitDiscover:HandlePooling
        -- fsmRmtErrComputeRackUnitDiscover:NicConfigPnuOSLocal
        -- fsmRmtErrComputeRackUnitDiscover:NicConfigPnuOSPeer
        -- fsmRmtErrComputeRackUnitDiscover:NicInventoryLocal
        -- fsmRmtErrComputeRackUnitDiscover:NicInventoryPeer
        -- fsmRmtErrComputeRackUnitDiscover:OobStorageConfig
        -- fsmRmtErrComputeRackUnitDiscover:OobStorageInventory
        -- fsmRmtErrComputeRackUnitDiscover:PnuOSCatalog
        -- fsmRmtErrComputeRackUnitDiscover:PnuOSConnStatus
        -- fsmRmtErrComputeRackUnitDiscover:PnuOSConnectivity
        -- fsmRmtErrComputeRackUnitDiscover:PnuOSIdent
        -- fsmRmtErrComputeRackUnitDiscover:PnuOSInventory
        -- fsmRmtErrComputeRackUnitDiscover:PnuOSPolicy
        -- fsmRmtErrComputeRackUnitDiscover:PnuOSScrub
        -- fsmRmtErrComputeRackUnitDiscover:PnuOSSelfTest
        -- fsmRmtErrComputeRackUnitDiscover:PnuosBootWait
        -- fsmRmtErrComputeRackUnitDiscover:PowerDeployWait
        -- fsmRmtErrComputeRackUnitDiscover:PreSanitize
        -- fsmRmtErrComputeRackUnitDiscover:ReadSmbios
        -- fsmRmtErrComputeRackUnitDiscover:Sanitize
        -- fsmRmtErrComputeRackUnitDiscover:SolRedirectDisable
        -- fsmRmtErrComputeRackUnitDiscover:SolRedirectEnable
        -- fsmRmtErrComputeRackUnitDiscover:SwConfigPnuOSLocal
        -- fsmRmtErrComputeRackUnitDiscover:SwConfigPnuOSPeer
        -- fsmRmtErrComputeRackUnitDiscover:SwConfigPortNivLocal
        -- fsmRmtErrComputeRackUnitDiscover:SwConfigPortNivPeer
        -- fsmRmtErrComputeRackUnitDiscover:SwConfigureConnLocal
        -- fsmRmtErrComputeRackUnitDiscover:SwConfigureConnPeer
        -- fsmRmtErrComputeRackUnitDiscover:SwConfigurePortChannelLocal
        -- fsmRmtErrComputeRackUnitDiscover:SwConfigurePortChannelPeer
        -- fsmRmtErrComputeRackUnitDiscover:SwHostOSConfigurePortChannelLocal
        -- fsmRmtErrComputeRackUnitDiscover:SwHostOSConfigurePortChannelPeer
        -- fsmRmtErrComputeRackUnitDiscover:SwHostOSMultiPortConnectivityLocal
        -- fsmRmtErrComputeRackUnitDiscover:SwHostOSMultiPortConnectivityPeer
        -- fsmRmtErrComputeRackUnitDiscover:SwPnuOSConnectivityLocal
        -- fsmRmtErrComputeRackUnitDiscover:SwPnuOSConnectivityPeer
        -- fsmRmtErrComputeRackUnitDiscover:SwPortDetailsLocal
        -- fsmRmtErrComputeRackUnitDiscover:SwPortDetailsPeer
        -- fsmRmtErrComputeRackUnitDiscover:SwUnconfigPortNivLocal
        -- fsmRmtErrComputeRackUnitDiscover:SwUnconfigPortNivPeer
        -- fsmRmtErrComputeRackUnitDiscover:UnconfigCimcVMedia
        -- fsmRmtErrComputeRackUnitDiscover:UnconfigExtMgmtGw
        -- fsmRmtErrComputeRackUnitDiscover:UnconfigExtMgmtRules
        -- fsmRmtErrComputeRackUnitDiscover:hagConnect
        -- fsmRmtErrComputeRackUnitDiscover:hagDisconnect
        -- fsmRmtErrComputeRackUnitDiscover:serialDebugConnect
        -- fsmRmtErrComputeRackUnitDiscover:serialDebugDisconnect
        -- fsmRmtErrComputeRackUnitDiscover:waitForConnReady
        -- fsmRmtErrComputeRackUnitOffline:CleanupLocal
        -- fsmRmtErrComputeRackUnitOffline:CleanupPeer
        -- fsmRmtErrComputeRackUnitOffline:SwUnconfigureLocal
        -- fsmRmtErrComputeRackUnitOffline:SwUnconfigurePeer
        -- fsmRmtErrComputeRackUnitAdapterReset:DeassertResetBypass
        -- fsmRmtErrComputeRackUnitAdapterReset:PowerCycle
        -- fsmRmtErrComputeRackUnitAdapterReset:PreSanitize
        -- fsmRmtErrComputeRackUnitAdapterReset:Sanitize
        -- fsmRmtErrComputeRackUnitCreateDhcpEntry:ExecuteLocal
        -- fsmRmtErrComputeRackUnitCreateDhcpEntry:ExecutePeer
        -- fsmFailComputeRackUnitDiscover
        -- fsmFailComputeRackUnitOffline
        -- fsmFailComputeRackUnitAdapterReset
        -- fsmFailComputeRackUnitCreateDhcpEntry

-- fabric:Vlan
    -- fabric/eth-estc/[id]/net-[name]
    -- fabric/eth-estc/net-[name]
    -- fabric/lan/[id]/net-[name]
    -- fabric/lan/net-[name]
        -- fltFabricVlanMisconfigured
        -- fltFabricVlanVlanConflictPermit
        -- fltFabricVlanMisconfigured-mcast-policy
        -- fltFabricVlanPrimaryVlanMissingForIsolated
        -- fltFabricVlanPrimaryVlanMissingForCommunity
        -- fltFabricVlanMismatch-a
        -- fltFabricVlanMismatch-b
        -- fltFabricVlanErrorAssocPrimary
        -- fltFabricVlanReserved

-- extvmm:Ep
    -- sys/extvm-mgmt
        -- fsmStFailExtvmmEpClusterRole:SetLocal
        -- fsmStFailExtvmmEpClusterRole:SetPeer
        -- fsmRmtErrExtvmmEpClusterRole:SetLocal
        -- fsmRmtErrExtvmmEpClusterRole:SetPeer
        -- fsmFailExtvmmEpClusterRole

-- policy:ControlEp
    -- sys/control-ep-[type]
        -- fltPolicyControlEpSuspendModeActive
        -- fsmStFailPolicyControlEpOperate:Resolve
        -- fsmRmtErrPolicyControlEpOperate:Resolve
        -- fsmFailPolicyControlEpOperate

-- fabric:FcUserZone
    -- fabric/fc-estc/zone-profile-[name]/zone-[name]
        -- fltFabricFcUserZoneConfigFailure

-- storage:VDMemberEp
    -- sys/chassis-[id]/blade-[slotId]/board/storage-[type]-[id]/vd-[id]/member-[id]
    -- sys/rack-unit-[id]/board/storage-[type]-[id]/vd-[id]/member-[id]
    -- sys/chassis-[id]/cartridge-[slotId]/server-[serverInstanceId]/board/storage-[type]-[id]/vd-[id]/member-[id]
    -- sys/chassis-[id]/storage-[type]-[id]/vd-[id]/member-[id]
    -- sys/chassis-[id]/blade-[slotId]/vd-container-[id]/vd-[id]/member-[id]
    -- sys/rack-unit-[id]/vd-container-[id]/vd-[id]/member-[id]
    -- sys/chassis-[id]/cartridge-[slotId]/server-[serverInstanceId]/vd-container-[id]/vd-[id]/member-[id]
    -- sys/chassis-[id]/vd-container-[id]/vd-[id]/member-[id]
        -- fltStorageVDMemberEpMismatch

-- fabric:FcZoneProfile
    -- fabric/fc-estc/zone-profile-[name]
        -- fltFabricFcZoneProfileSwitch-mode-disabled

-- adaptor:UnitExtn
    -- sys/chassis-[id]/blade-[slotId]/adaptor-[id]/adaptor-extn-[id]
    -- sys/rack-unit-[id]/adaptor-[id]/adaptor-extn-[id]
    -- sys/chassis-[id]/cartridge-[slotId]/server-[serverInstanceId]/adaptor-[id]/adaptor-extn-[id]
    -- sys/chassis-[id]/cartridge-[slotId]/server-[serverInstanceId]/adaptor-[id]/adaptor-extn-[id]
        -- fltAdaptorUnitExtnUnidentifiable-fru
        -- fltAdaptorUnitExtnMissing

-- nfs:MountDef
    -- nfs-ep/nfs-mount-def-[name]
        -- fsmStFailNfsMountDefReportNfsMountSuspend:Report
        -- fsmRmtErrNfsMountDefReportNfsMountSuspend:Report
        -- fsmFailNfsMountDefReportNfsMountSuspend

-- fabric:NetGroup
    -- fabric/lan/[id]/net-group-[name]
    -- fabric/lan/net-group-[name]
        -- fltFabricNetGroupNativeVlanNotFound

-- equipment:SwitchCard
    -- sys/switch-[id]/slot-[id]
        -- fltEquipmentSwitchCardPowerOff

-- storage:Initiator
    -- org-[name]/tier-[name]/ls-[name]/grp-[name]/ini-[name]
    -- org-[name]/ls-[name]/grp-[name]/ini-[name]
    -- org-[name]/san-conn-pol-[name]/grp-[name]/ini-[name]
        -- fltStorageInitiatorConfiguration-error
        -- fltStorageInitiatorDuplicate-fc-zone

-- storage:ADef
        -- fltStorageADefConfiguration-error

-- equipment:IOCard
    -- sys/chassis-[id]/slot-[id]
    -- sys/fex-[id]/slot-[id]
        -- fltEquipmentIOCardRemoved
        -- fltEquipmentIOCardThermalProblem
        -- fltEquipmentIOCardFirmwareUpgrade
        -- fltEquipmentIOCardUnsupportedConnectivity
        -- fltEquipmentIOCardUnacknowledged
        -- fltEquipmentIOCardPeerDisconnected
        -- fltEquipmentIOCardIdentity
        -- fltEquipmentIOCardAutoUpgradingFirmware
        -- fltEquipmentIOCardInaccessible
        -- fltEquipmentIOCardPost-failure
        -- fltEquipmentIOCardThermalThresholdNonCritical
        -- fltEquipmentIOCardThermalThresholdCritical
        -- fltEquipmentIOCardThermalThresholdNonRecoverable
        -- fltEquipmentIOCardDeprecated
        -- fltEquipmentIOCardBackPlanePortProblem
        -- fsmStFailEquipmentIOCardResetCmc:Execute
        -- fsmStFailEquipmentIOCardMuxOffline:CleanupEntries
        -- fsmStFailEquipmentIOCardResetIom:Execute
        -- fsmStFailEquipmentIOCardEvacuate:Execute
        -- fsmStFailEquipmentIOCardResetEvacuate:Execute
        -- fsmStFailEquipmentIOCardResetPeerCmc:Execute
        -- fsmRmtErrEquipmentIOCardResetCmc:Execute
        -- fsmRmtErrEquipmentIOCardMuxOffline:CleanupEntries
        -- fsmRmtErrEquipmentIOCardResetIom:Execute
        -- fsmRmtErrEquipmentIOCardEvacuate:Execute
        -- fsmRmtErrEquipmentIOCardResetEvacuate:Execute
        -- fsmRmtErrEquipmentIOCardResetPeerCmc:Execute
        -- fsmFailEquipmentIOCardResetCmc
        -- fsmFailEquipmentIOCardMuxOffline
        -- fsmFailEquipmentIOCardResetIom
        -- fsmFailEquipmentIOCardEvacuate
        -- fsmFailEquipmentIOCardResetEvacuate
        -- fsmFailEquipmentIOCardResetPeerCmc

-- extpol:Client
    -- extpol/reg/clients/client-[id]
        -- fltExtpolClientClientLostConnectivity
        -- fltExtpolClientGracePeriodWarning
        -- fltExtpolClientGracePeriodWarning2
        -- fltExtpolClientGracePeriodWarning3
        -- fltExtpolClientGracePeriodWarning4
        -- fltExtpolClientGracePeriodWarning5
        -- fltExtpolClientGracePeriodWarning6
        -- fltExtpolClientGracePeriodWarning7
        -- fltExtpolClientGracePeriodWarning1

-- sw:UtilityDomain
    -- sys/switch-[id]/utility-eth
        -- fsmStFailSwUtilityDomainDeploy:UpdateConnectivity
        -- fsmRmtErrSwUtilityDomainDeploy:UpdateConnectivity
        -- fsmFailSwUtilityDomainDeploy

-- aaa:Role
    -- sys/user-ext/role-[name]
        -- fltAaaRoleRoleNotDeployed

-- adaptor:Unit
    -- sys/chassis-[id]/blade-[slotId]/adaptor-[id]
    -- sys/rack-unit-[id]/adaptor-[id]
    -- sys/chassis-[id]/cartridge-[slotId]/server-[serverInstanceId]/adaptor-[id]
    -- sys/chassis-[id]/cartridge-[slotId]/server-[serverInstanceId]/adaptor-[id]
        -- fltAdaptorUnitUnidentifiable-fru
        -- fltAdaptorUnitMissing
        -- fltAdaptorUnitAdaptorReachability
        -- fltAdaptorUnitDeprecated
        -- fltAdaptorUnitPci-config-issue
        -- fltAdaptorUnitUnConnectedAdaptorReachability

-- aaa:UserEp
    -- sys/user-ext
        -- fsmStFailAaaUserEpUpdateUserEp:SetUserLocal
        -- fsmStFailAaaUserEpUpdateUserEp:SetUserPeer
        -- fsmRmtErrAaaUserEpUpdateUserEp:SetUserLocal
        -- fsmRmtErrAaaUserEpUpdateUserEp:SetUserPeer
        -- fsmFailAaaUserEpUpdateUserEp

-- uuidpool:Pool
    -- org-[name]/uuid-pool-[name]
        -- fltUuidpoolPoolEmpty

-- sysdebug:MEpLog
    -- sys/chassis-[id]/blade-[slotId]/adaptor-[id]/mgmt/log-[type]-[id]
    -- sys/rack-unit-[id]/adaptor-[id]/mgmt/log-[type]-[id]
    -- sys/chassis-[id]/cartridge-[slotId]/server-[serverInstanceId]/adaptor-[id]/mgmt/log-[type]-[id]
    -- sys/chassis-[id]/cartridge-[slotId]/server-[serverInstanceId]/adaptor-[id]/mgmt/log-[type]-[id]
    -- sys/chassis-[id]/blade-[slotId]/ext-board-[id]/boardController/mgmt/log-[type]-[id]
    -- sys/rack-unit-[id]/ext-board-[id]/boardController/mgmt/log-[type]-[id]
    -- sys/chassis-[id]/cartridge-[slotId]/server-[serverInstanceId]/ext-board-[id]/boardController/mgmt/log-[type]-[id]
    -- sys/chassis-[id]/blade-[slotId]/boardController/mgmt/log-[type]-[id]
    -- sys/rack-unit-[id]/boardController/mgmt/log-[type]-[id]
    -- sys/chassis-[id]/cartridge-[slotId]/server-[serverInstanceId]/boardController/mgmt/log-[type]-[id]
    -- sys/chassis-[id]/boardController/mgmt/log-[type]-[id]
    -- sys/chassis-[id]/slot-[id]/boardController/mgmt/log-[type]-[id]
    -- sys/chassis-[id]/blade-[slotId]/ext-board-[id]/mgmt/log-[type]-[id]
    -- sys/rack-unit-[id]/ext-board-[id]/mgmt/log-[type]-[id]
    -- sys/chassis-[id]/cartridge-[slotId]/server-[serverInstanceId]/ext-board-[id]/mgmt/log-[type]-[id]
    -- sys/chassis-[id]/blade-[slotId]/mgmt/log-[type]-[id]
    -- sys/rack-unit-[id]/mgmt/log-[type]-[id]
    -- sys/chassis-[id]/cartridge-[slotId]/server-[serverInstanceId]/mgmt/log-[type]-[id]
    -- sys/chassis-[id]/cartridge-[slotId]/server-[serverInstanceId]/mgmt/log-[type]-[id]
    -- sys/chassis-[id]/mgmt/log-[type]-[id]
    -- sys/fex-[id]/mgmt/log-[type]-[id]
    -- sys/chassis-[id]/slot-[id]/mgmt/log-[type]-[id]
    -- sys/fex-[id]/slot-[id]/mgmt/log-[type]-[id]
    -- sys/chassis-[id]/shared-io-module/mgmt/log-[type]-[id]
    -- sys/chassis-[id]/slot-[id]/shared-io-module/mgmt/log-[type]-[id]
    -- sys/chassis-[id]/sw-slot-[id]/mgmt/log-[type]-[id]
    -- sys/chassis-[id]/slot-[id]/mgmt/log-[type]-[id]
    -- sys/switch-[id]/mgmt/log-[type]-[id]
    -- sys/chassis-[id]/blade-[slotId]/board/storage-[type]-[id]/mgmt/log-[type]-[id]
    -- sys/rack-unit-[id]/board/storage-[type]-[id]/mgmt/log-[type]-[id]
    -- sys/chassis-[id]/cartridge-[slotId]/server-[serverInstanceId]/board/storage-[type]-[id]/mgmt/log-[type]-[id]
    -- sys/chassis-[id]/storage-[type]-[id]/mgmt/log-[type]-[id]
    -- sys/chassis-[id]/blade-[slotId]/board/storage-[type]-[id]/disk-[id]/mgmt/log-[type]-[id]
    -- sys/rack-unit-[id]/board/storage-[type]-[id]/disk-[id]/mgmt/log-[type]-[id]
    -- sys/chassis-[id]/cartridge-[slotId]/server-[serverInstanceId]/board/storage-[type]-[id]/disk-[id]/mgmt/log-[type]-[id]
    -- sys/chassis-[id]/storage-[type]-[id]/disk-[id]/mgmt/log-[type]-[id]
    -- sys/chassis-[id]/blade-[slotId]/enc-[id]/disk-[id]/mgmt/log-[type]-[id]
    -- sys/rack-unit-[id]/enc-[id]/disk-[id]/mgmt/log-[type]-[id]
    -- sys/chassis-[id]/cartridge-[slotId]/server-[serverInstanceId]/enc-[id]/disk-[id]/mgmt/log-[type]-[id]
    -- sys/chassis-[id]/enc-[id]/disk-[id]/mgmt/log-[type]-[id]
    -- sys/chassis-[id]/blade-[slotId]/board/storage-[type]-[id]/enc-[id]/disk-[id]/mgmt/log-[type]-[id]
    -- sys/rack-unit-[id]/board/storage-[type]-[id]/enc-[id]/disk-[id]/mgmt/log-[type]-[id]
    -- sys/chassis-[id]/cartridge-[slotId]/server-[serverInstanceId]/board/storage-[type]-[id]/enc-[id]/disk-[id]/mgmt/log-[type]-[id]
    -- sys/chassis-[id]/storage-[type]-[id]/enc-[id]/disk-[id]/mgmt/log-[type]-[id]
    -- sys/chassis-[id]/blade-[slotId]/board/sas-expander-[id]/mgmt/log-[type]-[id]
    -- sys/rack-unit-[id]/board/sas-expander-[id]/mgmt/log-[type]-[id]
    -- sys/chassis-[id]/cartridge-[slotId]/server-[serverInstanceId]/board/sas-expander-[id]/mgmt/log-[type]-[id]
    -- sys/chassis-[id]/sas-expander-[id]/mgmt/log-[type]-[id]
    -- sys/mgmt/log-[type]-[id]
        -- fltSysdebugMEpLogMEpLogLog
        -- fltSysdebugMEpLogMEpLogVeryLow
        -- fltSysdebugMEpLogMEpLogFull
        -- fltSysdebugMEpLogTransferError

-- power:ChassisMember
    -- sys/power-ep/group-[name]/ch-member-[id]
        -- fltPowerChassisMemberPowerGroupCapInsufficient
        -- fltPowerChassisMemberChassisFirmwareProblem
        -- fltPowerChassisMemberChassisPsuInsufficient
        -- fltPowerChassisMemberChassisPsuRedundanceFailure

-- sysdebug:LogExportStatus
    -- sys/sysdebug/log-export-policy/log-export-status-[switchId]
        -- fltSysdebugLogExportStatusLogExportFailure

-- equipment:Tpm
    -- sys/chassis-[id]/blade-[slotId]/board/Tpm-[id]
    -- sys/rack-unit-[id]/board/Tpm-[id]
    -- sys/chassis-[id]/cartridge-[slotId]/server-[serverInstanceId]/board/Tpm-[id]
        -- fltEquipmentTpmSlaveTpm
        -- fltEquipmentTpmTpmMismatch

-- fabric:SanCloud
    -- fabric/san
        -- fsmStFailFabricSanCloudSwitchMode:SwConfigLocal
        -- fsmStFailFabricSanCloudSwitchMode:SwConfigPeer
        -- fsmStFailFabricSanCloudSwitchMode:WaitForUserAck
        -- fsmRmtErrFabricSanCloudSwitchMode:SwConfigLocal
        -- fsmRmtErrFabricSanCloudSwitchMode:SwConfigPeer
        -- fsmRmtErrFabricSanCloudSwitchMode:WaitForUserAck
        -- fsmFailFabricSanCloudSwitchMode

-- dcx:Ns
    -- sys/chassis-[id]/blade-[slotId]/adaptor-[id]/dcxns-[switchId]
    -- sys/rack-unit-[id]/adaptor-[id]/dcxns-[switchId]
    -- sys/chassis-[id]/cartridge-[slotId]/server-[serverInstanceId]/adaptor-[id]/dcxns-[switchId]
    -- sys/chassis-[id]/cartridge-[slotId]/server-[serverInstanceId]/adaptor-[id]/dcxns-[switchId]
        -- fltDcxNsFailed

-- fabric:FcSan
    -- fabric/san/[id]
        -- fltFabricFcSanNumOfVsanExceedLimit

-- extvmm:SwitchDelTask
    -- sys/extvm-mgmt/vsw-deltask-[swIntId]
        -- fsmStFailExtvmmSwitchDelTaskRemoveProvider:RemoveLocal
        -- fsmRmtErrExtvmmSwitchDelTaskRemoveProvider:RemoveLocal
        -- fsmFailExtvmmSwitchDelTaskRemoveProvider

-- license:Instance
    -- sys/license/feature-[name]-[vendor]-[version]/inst-[scope]
        -- fltLicenseInstanceGracePeriodWarning1
        -- fltLicenseInstanceGracePeriodWarning2
        -- fltLicenseInstanceGracePeriodWarning3
        -- fltLicenseInstanceGracePeriodWarning4
        -- fltLicenseInstanceGracePeriodWarning5
        -- fltLicenseInstanceGracePeriodWarning6
        -- fltLicenseInstanceGracePeriodWarning7
        -- fsmStFailLicenseInstanceUpdateFlexlm:Local
        -- fsmStFailLicenseInstanceUpdateFlexlm:Remote
        -- fsmRmtErrLicenseInstanceUpdateFlexlm:Local
        -- fsmRmtErrLicenseInstanceUpdateFlexlm:Remote
        -- fsmFailLicenseInstanceUpdateFlexlm

-- fabric:ReservedVlan
    -- fabric/lan/fab-reserved-vlans
        -- fsmStFailFabricReservedVlanDeploy:ConfigSwitchLocal
        -- fsmStFailFabricReservedVlanDeploy:ConfigSwitchPeer
        -- fsmStFailFabricReservedVlanDeploy:WaitForUserAck
        -- fsmRmtErrFabricReservedVlanDeploy:ConfigSwitchLocal
        -- fsmRmtErrFabricReservedVlanDeploy:ConfigSwitchPeer
        -- fsmRmtErrFabricReservedVlanDeploy:WaitForUserAck
        -- fsmFailFabricReservedVlanDeploy

-- fabric:Vsan
    -- fabric/fc-estc/[id]/net-[name]
    -- fabric/fc-estc/net-[name]
    -- fabric/san/[id]/net-[name]
    -- fabric/san/net-[name]
        -- fltFabricVsanErrorDisabled
        -- fltFabricVsanReserved

-- memory:Unit
    -- sys/chassis-[id]/blade-[slotId]/board/memarray-[id]/mem-[id]
    -- sys/rack-unit-[id]/board/memarray-[id]/mem-[id]
    -- sys/chassis-[id]/cartridge-[slotId]/server-[serverInstanceId]/board/memarray-[id]/mem-[id]
        -- fltMemoryUnitDegraded
        -- fltMemoryUnitInoperable
        -- fltMemoryUnitThermalThresholdNonCritical
        -- fltMemoryUnitThermalThresholdCritical
        -- fltMemoryUnitThermalThresholdNonRecoverable
        -- fltMemoryUnitIdentity-unestablishable
        -- fltMemoryUnitDisabled

-- fabric:CartridgeSlotEp
    -- fabric/server/chassis-[chassisId]/cart-slot-[slotId]
        -- fltFabricCartridgeSlotEpMisplacedInChassisSlot
        -- fsmStFailFabricCartridgeSlotEpIdentify:ExecuteLocal
        -- fsmStFailFabricCartridgeSlotEpIdentify:ExecutePeer
        -- fsmRmtErrFabricCartridgeSlotEpIdentify:ExecuteLocal
        -- fsmRmtErrFabricCartridgeSlotEpIdentify:ExecutePeer
        -- fsmFailFabricCartridgeSlotEpIdentify

-- equipment:InventoryStatus
    -- sys/chassis-[id]/blade-[slotId]/adaptor-[id]/inv-status
    -- sys/rack-unit-[id]/adaptor-[id]/inv-status
    -- sys/chassis-[id]/cartridge-[slotId]/server-[serverInstanceId]/adaptor-[id]/inv-status
    -- sys/chassis-[id]/cartridge-[slotId]/server-[serverInstanceId]/adaptor-[id]/inv-status
    -- sys/chassis-[id]/blade-[slotId]/adaptor-[id]/adaptor-extn-[id]/inv-status
    -- sys/rack-unit-[id]/adaptor-[id]/adaptor-extn-[id]/inv-status
    -- sys/chassis-[id]/cartridge-[slotId]/server-[serverInstanceId]/adaptor-[id]/adaptor-extn-[id]/inv-status
    -- sys/chassis-[id]/cartridge-[slotId]/server-[serverInstanceId]/adaptor-[id]/adaptor-extn-[id]/inv-status
    -- sys/chassis-[id]/blade-[slotId]/inv-status
    -- sys/rack-unit-[id]/inv-status
    -- sys/chassis-[id]/cartridge-[slotId]/server-[serverInstanceId]/inv-status
    -- sys/chassis-[id]/blade-[slotId]/board/graphics-card-[id]/inv-status
    -- sys/rack-unit-[id]/board/graphics-card-[id]/inv-status
    -- sys/chassis-[id]/cartridge-[slotId]/server-[serverInstanceId]/board/graphics-card-[id]/inv-status
    -- sys/chassis-[id]/blade-[slotId]/board/memarray-[id]/mem-[id]/inv-status
    -- sys/rack-unit-[id]/board/memarray-[id]/mem-[id]/inv-status
    -- sys/chassis-[id]/cartridge-[slotId]/server-[serverInstanceId]/board/memarray-[id]/mem-[id]/inv-status
    -- sys/chassis-[id]/blade-[slotId]/board/cpu-[id]/inv-status
    -- sys/rack-unit-[id]/board/cpu-[id]/inv-status
    -- sys/chassis-[id]/cartridge-[slotId]/server-[serverInstanceId]/board/cpu-[id]/inv-status
    -- sys/chassis-[id]/blade-[slotId]/board/security-unit-[id]/inv-status
    -- sys/rack-unit-[id]/board/security-unit-[id]/inv-status
    -- sys/chassis-[id]/cartridge-[slotId]/server-[serverInstanceId]/board/security-unit-[id]/inv-status
    -- sys/chassis-[id]/blade-[slotId]/board/storage-[type]-[id]/inv-status
    -- sys/rack-unit-[id]/board/storage-[type]-[id]/inv-status
    -- sys/chassis-[id]/cartridge-[slotId]/server-[serverInstanceId]/board/storage-[type]-[id]/inv-status
    -- sys/chassis-[id]/storage-[type]-[id]/inv-status
    -- sys/chassis-[id]/blade-[slotId]/board/mini-storage-[type]-[id]/inv-status
    -- sys/rack-unit-[id]/board/mini-storage-[type]-[id]/inv-status
    -- sys/chassis-[id]/cartridge-[slotId]/server-[serverInstanceId]/board/mini-storage-[type]-[id]/inv-status
        -- fltEquipmentInventoryStatusHardwareMismatch

-- mgmt:Interface
    -- org-[name]/tier-[name]/ls-[name]/iface-[mode]
    -- org-[name]/ls-[name]/iface-[mode]
    -- sys/chassis-[id]/blade-[slotId]/adaptor-[id]/mgmt/iface-[mode]
    -- sys/rack-unit-[id]/adaptor-[id]/mgmt/iface-[mode]
    -- sys/chassis-[id]/cartridge-[slotId]/server-[serverInstanceId]/adaptor-[id]/mgmt/iface-[mode]
    -- sys/chassis-[id]/cartridge-[slotId]/server-[serverInstanceId]/adaptor-[id]/mgmt/iface-[mode]
    -- sys/chassis-[id]/blade-[slotId]/ext-board-[id]/boardController/mgmt/iface-[mode]
    -- sys/rack-unit-[id]/ext-board-[id]/boardController/mgmt/iface-[mode]
    -- sys/chassis-[id]/cartridge-[slotId]/server-[serverInstanceId]/ext-board-[id]/boardController/mgmt/iface-[mode]
    -- sys/chassis-[id]/blade-[slotId]/boardController/mgmt/iface-[mode]
    -- sys/rack-unit-[id]/boardController/mgmt/iface-[mode]
    -- sys/chassis-[id]/cartridge-[slotId]/server-[serverInstanceId]/boardController/mgmt/iface-[mode]
    -- sys/chassis-[id]/boardController/mgmt/iface-[mode]
    -- sys/chassis-[id]/slot-[id]/boardController/mgmt/iface-[mode]
    -- sys/chassis-[id]/blade-[slotId]/ext-board-[id]/mgmt/iface-[mode]
    -- sys/rack-unit-[id]/ext-board-[id]/mgmt/iface-[mode]
    -- sys/chassis-[id]/cartridge-[slotId]/server-[serverInstanceId]/ext-board-[id]/mgmt/iface-[mode]
    -- sys/chassis-[id]/blade-[slotId]/mgmt/iface-[mode]
    -- sys/rack-unit-[id]/mgmt/iface-[mode]
    -- sys/chassis-[id]/cartridge-[slotId]/server-[serverInstanceId]/mgmt/iface-[mode]
    -- sys/chassis-[id]/cartridge-[slotId]/server-[serverInstanceId]/mgmt/iface-[mode]
    -- sys/chassis-[id]/mgmt/iface-[mode]
    -- sys/fex-[id]/mgmt/iface-[mode]
    -- sys/chassis-[id]/slot-[id]/mgmt/iface-[mode]
    -- sys/fex-[id]/slot-[id]/mgmt/iface-[mode]
    -- sys/chassis-[id]/shared-io-module/mgmt/iface-[mode]
    -- sys/chassis-[id]/slot-[id]/shared-io-module/mgmt/iface-[mode]
    -- sys/chassis-[id]/sw-slot-[id]/mgmt/iface-[mode]
    -- sys/chassis-[id]/slot-[id]/mgmt/iface-[mode]
    -- sys/switch-[id]/mgmt/iface-[mode]
    -- sys/chassis-[id]/blade-[slotId]/board/storage-[type]-[id]/mgmt/iface-[mode]
    -- sys/rack-unit-[id]/board/storage-[type]-[id]/mgmt/iface-[mode]
    -- sys/chassis-[id]/cartridge-[slotId]/server-[serverInstanceId]/board/storage-[type]-[id]/mgmt/iface-[mode]
    -- sys/chassis-[id]/storage-[type]-[id]/mgmt/iface-[mode]
    -- sys/chassis-[id]/blade-[slotId]/board/storage-[type]-[id]/disk-[id]/mgmt/iface-[mode]
    -- sys/rack-unit-[id]/board/storage-[type]-[id]/disk-[id]/mgmt/iface-[mode]
    -- sys/chassis-[id]/cartridge-[slotId]/server-[serverInstanceId]/board/storage-[type]-[id]/disk-[id]/mgmt/iface-[mode]
    -- sys/chassis-[id]/storage-[type]-[id]/disk-[id]/mgmt/iface-[mode]
    -- sys/chassis-[id]/blade-[slotId]/enc-[id]/disk-[id]/mgmt/iface-[mode]
    -- sys/rack-unit-[id]/enc-[id]/disk-[id]/mgmt/iface-[mode]
    -- sys/chassis-[id]/cartridge-[slotId]/server-[serverInstanceId]/enc-[id]/disk-[id]/mgmt/iface-[mode]
    -- sys/chassis-[id]/enc-[id]/disk-[id]/mgmt/iface-[mode]
    -- sys/chassis-[id]/blade-[slotId]/board/storage-[type]-[id]/enc-[id]/disk-[id]/mgmt/iface-[mode]
    -- sys/rack-unit-[id]/board/storage-[type]-[id]/enc-[id]/disk-[id]/mgmt/iface-[mode]
    -- sys/chassis-[id]/cartridge-[slotId]/server-[serverInstanceId]/board/storage-[type]-[id]/enc-[id]/disk-[id]/mgmt/iface-[mode]
    -- sys/chassis-[id]/storage-[type]-[id]/enc-[id]/disk-[id]/mgmt/iface-[mode]
    -- sys/chassis-[id]/blade-[slotId]/board/sas-expander-[id]/mgmt/iface-[mode]
    -- sys/rack-unit-[id]/board/sas-expander-[id]/mgmt/iface-[mode]
    -- sys/chassis-[id]/cartridge-[slotId]/server-[serverInstanceId]/board/sas-expander-[id]/mgmt/iface-[mode]
    -- sys/chassis-[id]/sas-expander-[id]/mgmt/iface-[mode]
    -- sys/mgmt/iface-[mode]
        -- fltMgmtInterfaceNamedInbandVlanUnresolved
        -- fltMgmtInterfaceInbandUnsupportedServer
        -- fltMgmtInterfaceInbandUnsupportedFirmware
        -- fltMgmtInterfaceInbandPinningInvalid

-- extpol:Ep
    -- extpol
        -- fsmStFailExtpolEpRegisterFsm:Execute
        -- fsmStFailExtpolEpRepairCert:cleanOldData
        -- fsmStFailExtpolEpRepairCert:request
        -- fsmStFailExtpolEpRepairCert:unregister
        -- fsmStFailExtpolEpRepairCert:verify
        -- fsmStFailExtpolEpRepairCert:verifyGuid
        -- fsmRmtErrExtpolEpRegisterFsm:Execute
        -- fsmRmtErrExtpolEpRepairCert:cleanOldData
        -- fsmRmtErrExtpolEpRepairCert:request
        -- fsmRmtErrExtpolEpRepairCert:unregister
        -- fsmRmtErrExtpolEpRepairCert:verify
        -- fsmRmtErrExtpolEpRepairCert:verifyGuid
        -- fsmFailExtpolEpRegisterFsm
        -- fsmFailExtpolEpRepairCert

-- storage:Enclosure
    -- sys/chassis-[id]/blade-[slotId]/enc-[id]
    -- sys/rack-unit-[id]/enc-[id]
    -- sys/chassis-[id]/cartridge-[slotId]/server-[serverInstanceId]/enc-[id]
    -- sys/chassis-[id]/enc-[id]
    -- sys/chassis-[id]/blade-[slotId]/board/storage-[type]-[id]/enc-[id]
    -- sys/rack-unit-[id]/board/storage-[type]-[id]/enc-[id]
    -- sys/chassis-[id]/cartridge-[slotId]/server-[serverInstanceId]/board/storage-[type]-[id]/enc-[id]
    -- sys/chassis-[id]/storage-[type]-[id]/enc-[id]
        -- fltStorageEnclosureThermalIssueNonCritical
        -- fltStorageEnclosureThermalIssueCritical
        -- fltStorageEnclosureThermalIssueNonRecoverable
        -- fltStorageEnclosureMissing
        -- fltStorageEnclosureFru-empty
        -- fsmStFailStorageEnclosureRemoveEnclosure:PollUpdateStorageInvCIMC
        -- fsmStFailStorageEnclosureRemoveEnclosure:UpdateStorageInvCIMC
        -- fsmStFailStorageEnclosureRemoveEnclosure:UpdateStorageInvCMC
        -- fsmStFailStorageEnclosureRemoveEnclosure:ValidateRemoval
        -- fsmRmtErrStorageEnclosureRemoveEnclosure:PollUpdateStorageInvCIMC
        -- fsmRmtErrStorageEnclosureRemoveEnclosure:UpdateStorageInvCIMC
        -- fsmRmtErrStorageEnclosureRemoveEnclosure:UpdateStorageInvCMC
        -- fsmRmtErrStorageEnclosureRemoveEnclosure:ValidateRemoval
        -- fsmFailStorageEnclosureRemoveEnclosure

-- storage:RaidBattery
    -- sys/chassis-[id]/blade-[slotId]/board/storage-[type]-[id]/raid-battery
    -- sys/rack-unit-[id]/board/storage-[type]-[id]/raid-battery
    -- sys/chassis-[id]/cartridge-[slotId]/server-[serverInstanceId]/board/storage-[type]-[id]/raid-battery
    -- sys/chassis-[id]/storage-[type]-[id]/raid-battery
        -- fltStorageRaidBatteryInoperable
        -- fltStorageRaidBatteryDegraded
        -- fltStorageRaidBatteryRelearnAborted
        -- fltStorageRaidBatteryRelearnFailed

-- fabric:VsanMembership
    -- fabric/san/[id]/phys-slot-[slotId]-port-[portId]/vsanmember-[vsanId]
    -- fabric/san/[id]/pc-[portId]/vsanmember-[vsanId]
    -- fabric/fc-estc/[id]/phys-fcoe-slot-[slotId]-port-[portId]/vsanmember-[vsanId]
    -- fabric/server/sw-[id]/slot-[slotId]-aggr-port-[aggrPortId]/phys-fcoe-slot-[slotId]-port-[portId]/vsanmember-[vsanId]
    -- fabric/server/sw-[id]/pc-[portId]/slot-[slotId]-aggr-port-[aggrPortId]/phys-fcoe-slot-[slotId]-port-[portId]/vsanmember-[vsanId]
    -- fabric/eth-estc/[id]/slot-[slotId]-aggr-port-[aggrPortId]/phys-fcoe-slot-[slotId]-port-[portId]/vsanmember-[vsanId]
    -- fabric/eth-estc/[id]/pc-[portId]/slot-[slotId]-aggr-port-[aggrPortId]/phys-fcoe-slot-[slotId]-port-[portId]/vsanmember-[vsanId]
    -- fabric/lan/[id]/slot-[slotId]-aggr-port-[aggrPortId]/phys-fcoe-slot-[slotId]-port-[portId]/vsanmember-[vsanId]
    -- fabric/lan/[id]/pc-[portId]/slot-[slotId]-aggr-port-[aggrPortId]/phys-fcoe-slot-[slotId]-port-[portId]/vsanmember-[vsanId]
    -- fabric/lanmon/[id]/eth-mon-[name]/slot-[slotId]-aggr-port-[aggrPortId]/phys-fcoe-slot-[slotId]-port-[portId]/vsanmember-[vsanId]
    -- fabric/fc-estc/[id]/slot-[slotId]-aggr-port-[aggrPortId]/phys-fcoe-slot-[slotId]-port-[portId]/vsanmember-[vsanId]
    -- fabric/sanmon/[id]/fc-mon-[name]/slot-[slotId]-aggr-port-[aggrPortId]/phys-fcoe-slot-[slotId]-port-[portId]/vsanmember-[vsanId]
    -- fabric/san/[id]/slot-[slotId]-aggr-port-[aggrPortId]/phys-fcoe-slot-[slotId]-port-[portId]/vsanmember-[vsanId]
    -- fabric/san/[id]/fcoesanpc-[portId]/slot-[slotId]-aggr-port-[aggrPortId]/phys-fcoe-slot-[slotId]-port-[portId]/vsanmember-[vsanId]
    -- fabric/san/[id]/phys-fcoesanep-slot-[slotId]-port-[portId]/vsanmember-[vsanId]
    -- fabric/server/sw-[id]/slot-[slotId]-aggr-port-[aggrPortId]/phys-fcoesanep-slot-[slotId]-port-[portId]/vsanmember-[vsanId]
    -- fabric/server/sw-[id]/pc-[portId]/slot-[slotId]-aggr-port-[aggrPortId]/phys-fcoesanep-slot-[slotId]-port-[portId]/vsanmember-[vsanId]
    -- fabric/eth-estc/[id]/slot-[slotId]-aggr-port-[aggrPortId]/phys-fcoesanep-slot-[slotId]-port-[portId]/vsanmember-[vsanId]
    -- fabric/eth-estc/[id]/pc-[portId]/slot-[slotId]-aggr-port-[aggrPortId]/phys-fcoesanep-slot-[slotId]-port-[portId]/vsanmember-[vsanId]
    -- fabric/lan/[id]/slot-[slotId]-aggr-port-[aggrPortId]/phys-fcoesanep-slot-[slotId]-port-[portId]/vsanmember-[vsanId]
    -- fabric/lan/[id]/pc-[portId]/slot-[slotId]-aggr-port-[aggrPortId]/phys-fcoesanep-slot-[slotId]-port-[portId]/vsanmember-[vsanId]
    -- fabric/lanmon/[id]/eth-mon-[name]/slot-[slotId]-aggr-port-[aggrPortId]/phys-fcoesanep-slot-[slotId]-port-[portId]/vsanmember-[vsanId]
    -- fabric/fc-estc/[id]/slot-[slotId]-aggr-port-[aggrPortId]/phys-fcoesanep-slot-[slotId]-port-[portId]/vsanmember-[vsanId]
    -- fabric/sanmon/[id]/fc-mon-[name]/slot-[slotId]-aggr-port-[aggrPortId]/phys-fcoesanep-slot-[slotId]-port-[portId]/vsanmember-[vsanId]
    -- fabric/san/[id]/slot-[slotId]-aggr-port-[aggrPortId]/phys-fcoesanep-slot-[slotId]-port-[portId]/vsanmember-[vsanId]
    -- fabric/san/[id]/fcoesanpc-[portId]/slot-[slotId]-aggr-port-[aggrPortId]/phys-fcoesanep-slot-[slotId]-port-[portId]/vsanmember-[vsanId]
    -- fabric/san/[id]/fcoesanpc-[portId]/vsanmember-[vsanId]
        -- fltFabricVsanMembershipDown

-- aaa:ProviderGroup
    -- sys/ldap-ext/providergroup-[name]
    -- sys/radius-ext/providergroup-[name]
    -- sys/tacacs-ext/providergroup-[name]
        -- fltAaaProviderGroupProvidergroup
        -- fltAaaProviderGroupProvidergroupsize

-- equipment:ComputeConn
    -- sys/chassis-[id]/compute-conn
        -- fltEquipmentComputeConnConfig-problem

-- stats:CollectionPolicy
    -- stats/coll-policy-[name]
        -- fsmStFailStatsCollectionPolicyUpdateEp:SetEpA
        -- fsmStFailStatsCollectionPolicyUpdateEp:SetEpB
        -- fsmRmtErrStatsCollectionPolicyUpdateEp:SetEpA
        -- fsmRmtErrStatsCollectionPolicyUpdateEp:SetEpB
        -- fsmFailStatsCollectionPolicyUpdateEp

-- fabric:EthLanPc
    -- fabric/lan/[id]/pc-[portId]
        -- fltFabricEthLanPcMissingPrimaryVlan
        -- fltFabricEthLanPcOverlapping-vlan

-- fabric:NetGroupRef
    -- sys/chassis-[id]/blade-[slotId]/fabric-[switchId]/vc-[id]/net-group-ref-[name]
    -- sys/chassis-[id]/blade-[slotId]/fabric-[switchId]/vc-[id]/net-group-ref-[name]
    -- sys/rack-unit-[id]/fabric-[switchId]/vc-[id]/net-group-ref-[name]
    -- sys/chassis-[id]/cartridge-[slotId]/server-[serverInstanceId]/fabric-[switchId]/vc-[id]/net-group-ref-[name]
    -- sys/chassis-[id]/cartridge-[slotId]/server-[serverInstanceId]/fabric-[switchId]/vc-[id]/net-group-ref-[name]
    -- sys/chassis-[id]/fabric-[switchId]/vc-[id]/net-group-ref-[name]
    -- sys/fex-[id]/fabric-[switchId]/vc-[id]/net-group-ref-[name]
    -- sys/chassis-[id]/blade-[slotId]/adaptor-[id]/mgmt/fabric-[switchId]/vc-[id]/net-group-ref-[name]
    -- sys/rack-unit-[id]/adaptor-[id]/mgmt/fabric-[switchId]/vc-[id]/net-group-ref-[name]
    -- sys/chassis-[id]/cartridge-[slotId]/server-[serverInstanceId]/adaptor-[id]/mgmt/fabric-[switchId]/vc-[id]/net-group-ref-[name]
    -- sys/chassis-[id]/cartridge-[slotId]/server-[serverInstanceId]/adaptor-[id]/mgmt/fabric-[switchId]/vc-[id]/net-group-ref-[name]
    -- sys/chassis-[id]/blade-[slotId]/ext-board-[id]/boardController/mgmt/fabric-[switchId]/vc-[id]/net-group-ref-[name]
    -- sys/rack-unit-[id]/ext-board-[id]/boardController/mgmt/fabric-[switchId]/vc-[id]/net-group-ref-[name]
    -- sys/chassis-[id]/cartridge-[slotId]/server-[serverInstanceId]/ext-board-[id]/boardController/mgmt/fabric-[switchId]/vc-[id]/net-group-ref-[name]
    -- sys/chassis-[id]/blade-[slotId]/boardController/mgmt/fabric-[switchId]/vc-[id]/net-group-ref-[name]
    -- sys/rack-unit-[id]/boardController/mgmt/fabric-[switchId]/vc-[id]/net-group-ref-[name]
    -- sys/chassis-[id]/cartridge-[slotId]/server-[serverInstanceId]/boardController/mgmt/fabric-[switchId]/vc-[id]/net-group-ref-[name]
    -- sys/chassis-[id]/boardController/mgmt/fabric-[switchId]/vc-[id]/net-group-ref-[name]
    -- sys/chassis-[id]/slot-[id]/boardController/mgmt/fabric-[switchId]/vc-[id]/net-group-ref-[name]
    -- sys/chassis-[id]/blade-[slotId]/ext-board-[id]/mgmt/fabric-[switchId]/vc-[id]/net-group-ref-[name]
    -- sys/rack-unit-[id]/ext-board-[id]/mgmt/fabric-[switchId]/vc-[id]/net-group-ref-[name]
    -- sys/chassis-[id]/cartridge-[slotId]/server-[serverInstanceId]/ext-board-[id]/mgmt/fabric-[switchId]/vc-[id]/net-group-ref-[name]
    -- sys/chassis-[id]/blade-[slotId]/mgmt/fabric-[switchId]/vc-[id]/net-group-ref-[name]
    -- sys/rack-unit-[id]/mgmt/fabric-[switchId]/vc-[id]/net-group-ref-[name]
    -- sys/chassis-[id]/cartridge-[slotId]/server-[serverInstanceId]/mgmt/fabric-[switchId]/vc-[id]/net-group-ref-[name]
    -- sys/chassis-[id]/cartridge-[slotId]/server-[serverInstanceId]/mgmt/fabric-[switchId]/vc-[id]/net-group-ref-[name]
    -- sys/chassis-[id]/mgmt/fabric-[switchId]/vc-[id]/net-group-ref-[name]
    -- sys/fex-[id]/mgmt/fabric-[switchId]/vc-[id]/net-group-ref-[name]
    -- sys/chassis-[id]/slot-[id]/mgmt/fabric-[switchId]/vc-[id]/net-group-ref-[name]
    -- sys/fex-[id]/slot-[id]/mgmt/fabric-[switchId]/vc-[id]/net-group-ref-[name]
    -- sys/chassis-[id]/shared-io-module/mgmt/fabric-[switchId]/vc-[id]/net-group-ref-[name]
    -- sys/chassis-[id]/slot-[id]/shared-io-module/mgmt/fabric-[switchId]/vc-[id]/net-group-ref-[name]
    -- sys/chassis-[id]/sw-slot-[id]/mgmt/fabric-[switchId]/vc-[id]/net-group-ref-[name]
    -- sys/chassis-[id]/slot-[id]/mgmt/fabric-[switchId]/vc-[id]/net-group-ref-[name]
    -- sys/switch-[id]/mgmt/fabric-[switchId]/vc-[id]/net-group-ref-[name]
    -- sys/chassis-[id]/blade-[slotId]/board/storage-[type]-[id]/mgmt/fabric-[switchId]/vc-[id]/net-group-ref-[name]
    -- sys/rack-unit-[id]/board/storage-[type]-[id]/mgmt/fabric-[switchId]/vc-[id]/net-group-ref-[name]
    -- sys/chassis-[id]/cartridge-[slotId]/server-[serverInstanceId]/board/storage-[type]-[id]/mgmt/fabric-[switchId]/vc-[id]/net-group-ref-[name]
    -- sys/chassis-[id]/storage-[type]-[id]/mgmt/fabric-[switchId]/vc-[id]/net-group-ref-[name]
    -- sys/chassis-[id]/blade-[slotId]/board/storage-[type]-[id]/disk-[id]/mgmt/fabric-[switchId]/vc-[id]/net-group-ref-[name]
    -- sys/rack-unit-[id]/board/storage-[type]-[id]/disk-[id]/mgmt/fabric-[switchId]/vc-[id]/net-group-ref-[name]
    -- sys/chassis-[id]/cartridge-[slotId]/server-[serverInstanceId]/board/storage-[type]-[id]/disk-[id]/mgmt/fabric-[switchId]/vc-[id]/net-group-ref-[name]
    -- sys/chassis-[id]/storage-[type]-[id]/disk-[id]/mgmt/fabric-[switchId]/vc-[id]/net-group-ref-[name]
    -- sys/chassis-[id]/blade-[slotId]/enc-[id]/disk-[id]/mgmt/fabric-[switchId]/vc-[id]/net-group-ref-[name]
    -- sys/rack-unit-[id]/enc-[id]/disk-[id]/mgmt/fabric-[switchId]/vc-[id]/net-group-ref-[name]
    -- sys/chassis-[id]/cartridge-[slotId]/server-[serverInstanceId]/enc-[id]/disk-[id]/mgmt/fabric-[switchId]/vc-[id]/net-group-ref-[name]
    -- sys/chassis-[id]/enc-[id]/disk-[id]/mgmt/fabric-[switchId]/vc-[id]/net-group-ref-[name]
    -- sys/chassis-[id]/blade-[slotId]/board/storage-[type]-[id]/enc-[id]/disk-[id]/mgmt/fabric-[switchId]/vc-[id]/net-group-ref-[name]
    -- sys/rack-unit-[id]/board/storage-[type]-[id]/enc-[id]/disk-[id]/mgmt/fabric-[switchId]/vc-[id]/net-group-ref-[name]
    -- sys/chassis-[id]/cartridge-[slotId]/server-[serverInstanceId]/board/storage-[type]-[id]/enc-[id]/disk-[id]/mgmt/fabric-[switchId]/vc-[id]/net-group-ref-[name]
    -- sys/chassis-[id]/storage-[type]-[id]/enc-[id]/disk-[id]/mgmt/fabric-[switchId]/vc-[id]/net-group-ref-[name]
    -- sys/chassis-[id]/blade-[slotId]/board/sas-expander-[id]/mgmt/fabric-[switchId]/vc-[id]/net-group-ref-[name]
    -- sys/rack-unit-[id]/board/sas-expander-[id]/mgmt/fabric-[switchId]/vc-[id]/net-group-ref-[name]
    -- sys/chassis-[id]/cartridge-[slotId]/server-[serverInstanceId]/board/sas-expander-[id]/mgmt/fabric-[switchId]/vc-[id]/net-group-ref-[name]
    -- sys/chassis-[id]/sas-expander-[id]/mgmt/fabric-[switchId]/vc-[id]/net-group-ref-[name]
    -- sys/mgmt/fabric-[switchId]/vc-[id]/net-group-ref-[name]
    -- sys/chassis-[id]/blade-[slotId]/fabric-[switchId]/path-[id]/vc-[id]/net-group-ref-[name]
    -- sys/chassis-[id]/blade-[slotId]/fabric-[switchId]/path-[id]/vc-[id]/net-group-ref-[name]
    -- sys/rack-unit-[id]/fabric-[switchId]/path-[id]/vc-[id]/net-group-ref-[name]
    -- sys/chassis-[id]/cartridge-[slotId]/server-[serverInstanceId]/fabric-[switchId]/path-[id]/vc-[id]/net-group-ref-[name]
    -- sys/chassis-[id]/cartridge-[slotId]/server-[serverInstanceId]/fabric-[switchId]/path-[id]/vc-[id]/net-group-ref-[name]
    -- sys/chassis-[id]/fabric-[switchId]/path-[id]/vc-[id]/net-group-ref-[name]
    -- sys/fex-[id]/fabric-[switchId]/path-[id]/vc-[id]/net-group-ref-[name]
    -- sys/chassis-[id]/blade-[slotId]/adaptor-[id]/mgmt/fabric-[switchId]/path-[id]/vc-[id]/net-group-ref-[name]
    -- sys/rack-unit-[id]/adaptor-[id]/mgmt/fabric-[switchId]/path-[id]/vc-[id]/net-group-ref-[name]
    -- sys/chassis-[id]/cartridge-[slotId]/server-[serverInstanceId]/adaptor-[id]/mgmt/fabric-[switchId]/path-[id]/vc-[id]/net-group-ref-[name]
    -- sys/chassis-[id]/cartridge-[slotId]/server-[serverInstanceId]/adaptor-[id]/mgmt/fabric-[switchId]/path-[id]/vc-[id]/net-group-ref-[name]
    -- sys/chassis-[id]/blade-[slotId]/ext-board-[id]/boardController/mgmt/fabric-[switchId]/path-[id]/vc-[id]/net-group-ref-[name]
    -- sys/rack-unit-[id]/ext-board-[id]/boardController/mgmt/fabric-[switchId]/path-[id]/vc-[id]/net-group-ref-[name]
    -- sys/chassis-[id]/cartridge-[slotId]/server-[serverInstanceId]/ext-board-[id]/boardController/mgmt/fabric-[switchId]/path-[id]/vc-[id]/net-group-ref-[name]
    -- sys/chassis-[id]/blade-[slotId]/boardController/mgmt/fabric-[switchId]/path-[id]/vc-[id]/net-group-ref-[name]
    -- sys/rack-unit-[id]/boardController/mgmt/fabric-[switchId]/path-[id]/vc-[id]/net-group-ref-[name]
    -- sys/chassis-[id]/cartridge-[slotId]/server-[serverInstanceId]/boardController/mgmt/fabric-[switchId]/path-[id]/vc-[id]/net-group-ref-[name]
    -- sys/chassis-[id]/boardController/mgmt/fabric-[switchId]/path-[id]/vc-[id]/net-group-ref-[name]
    -- sys/chassis-[id]/slot-[id]/boardController/mgmt/fabric-[switchId]/path-[id]/vc-[id]/net-group-ref-[name]
    -- sys/chassis-[id]/blade-[slotId]/ext-board-[id]/mgmt/fabric-[switchId]/path-[id]/vc-[id]/net-group-ref-[name]
    -- sys/rack-unit-[id]/ext-board-[id]/mgmt/fabric-[switchId]/path-[id]/vc-[id]/net-group-ref-[name]
    -- sys/chassis-[id]/cartridge-[slotId]/server-[serverInstanceId]/ext-board-[id]/mgmt/fabric-[switchId]/path-[id]/vc-[id]/net-group-ref-[name]
    -- sys/chassis-[id]/blade-[slotId]/mgmt/fabric-[switchId]/path-[id]/vc-[id]/net-group-ref-[name]
    -- sys/rack-unit-[id]/mgmt/fabric-[switchId]/path-[id]/vc-[id]/net-group-ref-[name]
    -- sys/chassis-[id]/cartridge-[slotId]/server-[serverInstanceId]/mgmt/fabric-[switchId]/path-[id]/vc-[id]/net-group-ref-[name]
    -- sys/chassis-[id]/cartridge-[slotId]/server-[serverInstanceId]/mgmt/fabric-[switchId]/path-[id]/vc-[id]/net-group-ref-[name]
    -- sys/chassis-[id]/mgmt/fabric-[switchId]/path-[id]/vc-[id]/net-group-ref-[name]
    -- sys/fex-[id]/mgmt/fabric-[switchId]/path-[id]/vc-[id]/net-group-ref-[name]
    -- sys/chassis-[id]/slot-[id]/mgmt/fabric-[switchId]/path-[id]/vc-[id]/net-group-ref-[name]
    -- sys/fex-[id]/slot-[id]/mgmt/fabric-[switchId]/path-[id]/vc-[id]/net-group-ref-[name]
    -- sys/chassis-[id]/shared-io-module/mgmt/fabric-[switchId]/path-[id]/vc-[id]/net-group-ref-[name]
    -- sys/chassis-[id]/slot-[id]/shared-io-module/mgmt/fabric-[switchId]/path-[id]/vc-[id]/net-group-ref-[name]
    -- sys/chassis-[id]/sw-slot-[id]/mgmt/fabric-[switchId]/path-[id]/vc-[id]/net-group-ref-[name]
    -- sys/chassis-[id]/slot-[id]/mgmt/fabric-[switchId]/path-[id]/vc-[id]/net-group-ref-[name]
    -- sys/switch-[id]/mgmt/fabric-[switchId]/path-[id]/vc-[id]/net-group-ref-[name]
    -- sys/chassis-[id]/blade-[slotId]/board/storage-[type]-[id]/mgmt/fabric-[switchId]/path-[id]/vc-[id]/net-group-ref-[name]
    -- sys/rack-unit-[id]/board/storage-[type]-[id]/mgmt/fabric-[switchId]/path-[id]/vc-[id]/net-group-ref-[name]
    -- sys/chassis-[id]/cartridge-[slotId]/server-[serverInstanceId]/board/storage-[type]-[id]/mgmt/fabric-[switchId]/path-[id]/vc-[id]/net-group-ref-[name]
    -- sys/chassis-[id]/storage-[type]-[id]/mgmt/fabric-[switchId]/path-[id]/vc-[id]/net-group-ref-[name]
    -- sys/chassis-[id]/blade-[slotId]/board/storage-[type]-[id]/disk-[id]/mgmt/fabric-[switchId]/path-[id]/vc-[id]/net-group-ref-[name]
    -- sys/rack-unit-[id]/board/storage-[type]-[id]/disk-[id]/mgmt/fabric-[switchId]/path-[id]/vc-[id]/net-group-ref-[name]
    -- sys/chassis-[id]/cartridge-[slotId]/server-[serverInstanceId]/board/storage-[type]-[id]/disk-[id]/mgmt/fabric-[switchId]/path-[id]/vc-[id]/net-group-ref-[name]
    -- sys/chassis-[id]/storage-[type]-[id]/disk-[id]/mgmt/fabric-[switchId]/path-[id]/vc-[id]/net-group-ref-[name]
    -- sys/chassis-[id]/blade-[slotId]/enc-[id]/disk-[id]/mgmt/fabric-[switchId]/path-[id]/vc-[id]/net-group-ref-[name]
    -- sys/rack-unit-[id]/enc-[id]/disk-[id]/mgmt/fabric-[switchId]/path-[id]/vc-[id]/net-group-ref-[name]
    -- sys/chassis-[id]/cartridge-[slotId]/server-[serverInstanceId]/enc-[id]/disk-[id]/mgmt/fabric-[switchId]/path-[id]/vc-[id]/net-group-ref-[name]
    -- sys/chassis-[id]/enc-[id]/disk-[id]/mgmt/fabric-[switchId]/path-[id]/vc-[id]/net-group-ref-[name]
    -- sys/chassis-[id]/blade-[slotId]/board/storage-[type]-[id]/enc-[id]/disk-[id]/mgmt/fabric-[switchId]/path-[id]/vc-[id]/net-group-ref-[name]
    -- sys/rack-unit-[id]/board/storage-[type]-[id]/enc-[id]/disk-[id]/mgmt/fabric-[switchId]/path-[id]/vc-[id]/net-group-ref-[name]
    -- sys/chassis-[id]/cartridge-[slotId]/server-[serverInstanceId]/board/storage-[type]-[id]/enc-[id]/disk-[id]/mgmt/fabric-[switchId]/path-[id]/vc-[id]/net-group-ref-[name]
    -- sys/chassis-[id]/storage-[type]-[id]/enc-[id]/disk-[id]/mgmt/fabric-[switchId]/path-[id]/vc-[id]/net-group-ref-[name]
    -- sys/chassis-[id]/blade-[slotId]/board/sas-expander-[id]/mgmt/fabric-[switchId]/path-[id]/vc-[id]/net-group-ref-[name]
    -- sys/rack-unit-[id]/board/sas-expander-[id]/mgmt/fabric-[switchId]/path-[id]/vc-[id]/net-group-ref-[name]
    -- sys/chassis-[id]/cartridge-[slotId]/server-[serverInstanceId]/board/sas-expander-[id]/mgmt/fabric-[switchId]/path-[id]/vc-[id]/net-group-ref-[name]
    -- sys/chassis-[id]/sas-expander-[id]/mgmt/fabric-[switchId]/path-[id]/vc-[id]/net-group-ref-[name]
    -- sys/mgmt/fabric-[switchId]/path-[id]/vc-[id]/net-group-ref-[name]
    -- sys/switch-[id]/ethlanflowmon/vc-[id]/net-group-ref-[name]
    -- sys/switch-[id]/lanmon-eth/mon-[name]/vc-[id]/net-group-ref-[name]
    -- sys/switch-[id]/sanmon-fc/mon-[name]/vc-[id]/net-group-ref-[name]
    -- sys/chassis-[id]/blade-[slotId]/fabric-[switchId]/vc-[id]/vlan-cmc[id]/net-group-ref-[name]
    -- sys/chassis-[id]/blade-[slotId]/fabric-[switchId]/vc-[id]/vlan-cmc[id]/net-group-ref-[name]
    -- sys/rack-unit-[id]/fabric-[switchId]/vc-[id]/vlan-cmc[id]/net-group-ref-[name]
    -- sys/chassis-[id]/cartridge-[slotId]/server-[serverInstanceId]/fabric-[switchId]/vc-[id]/vlan-cmc[id]/net-group-ref-[name]
    -- sys/chassis-[id]/cartridge-[slotId]/server-[serverInstanceId]/fabric-[switchId]/vc-[id]/vlan-cmc[id]/net-group-ref-[name]
    -- sys/chassis-[id]/fabric-[switchId]/vc-[id]/vlan-cmc[id]/net-group-ref-[name]
    -- sys/fex-[id]/fabric-[switchId]/vc-[id]/vlan-cmc[id]/net-group-ref-[name]
    -- sys/chassis-[id]/blade-[slotId]/adaptor-[id]/mgmt/fabric-[switchId]/vc-[id]/vlan-cmc[id]/net-group-ref-[name]
    -- sys/rack-unit-[id]/adaptor-[id]/mgmt/fabric-[switchId]/vc-[id]/vlan-cmc[id]/net-group-ref-[name]
    -- sys/chassis-[id]/cartridge-[slotId]/server-[serverInstanceId]/adaptor-[id]/mgmt/fabric-[switchId]/vc-[id]/vlan-cmc[id]/net-group-ref-[name]
    -- sys/chassis-[id]/cartridge-[slotId]/server-[serverInstanceId]/adaptor-[id]/mgmt/fabric-[switchId]/vc-[id]/vlan-cmc[id]/net-group-ref-[name]
    -- sys/chassis-[id]/blade-[slotId]/ext-board-[id]/boardController/mgmt/fabric-[switchId]/vc-[id]/vlan-cmc[id]/net-group-ref-[name]
    -- sys/rack-unit-[id]/ext-board-[id]/boardController/mgmt/fabric-[switchId]/vc-[id]/vlan-cmc[id]/net-group-ref-[name]
    -- sys/chassis-[id]/cartridge-[slotId]/server-[serverInstanceId]/ext-board-[id]/boardController/mgmt/fabric-[switchId]/vc-[id]/vlan-cmc[id]/net-group-ref-[name]
    -- sys/chassis-[id]/blade-[slotId]/boardController/mgmt/fabric-[switchId]/vc-[id]/vlan-cmc[id]/net-group-ref-[name]
    -- sys/rack-unit-[id]/boardController/mgmt/fabric-[switchId]/vc-[id]/vlan-cmc[id]/net-group-ref-[name]
    -- sys/chassis-[id]/cartridge-[slotId]/server-[serverInstanceId]/boardController/mgmt/fabric-[switchId]/vc-[id]/vlan-cmc[id]/net-group-ref-[name]
    -- sys/chassis-[id]/boardController/mgmt/fabric-[switchId]/vc-[id]/vlan-cmc[id]/net-group-ref-[name]
    -- sys/chassis-[id]/slot-[id]/boardController/mgmt/fabric-[switchId]/vc-[id]/vlan-cmc[id]/net-group-ref-[name]
    -- sys/chassis-[id]/blade-[slotId]/ext-board-[id]/mgmt/fabric-[switchId]/vc-[id]/vlan-cmc[id]/net-group-ref-[name]
    -- sys/rack-unit-[id]/ext-board-[id]/mgmt/fabric-[switchId]/vc-[id]/vlan-cmc[id]/net-group-ref-[name]
    -- sys/chassis-[id]/cartridge-[slotId]/server-[serverInstanceId]/ext-board-[id]/mgmt/fabric-[switchId]/vc-[id]/vlan-cmc[id]/net-group-ref-[name]
    -- sys/chassis-[id]/blade-[slotId]/mgmt/fabric-[switchId]/vc-[id]/vlan-cmc[id]/net-group-ref-[name]
    -- sys/rack-unit-[id]/mgmt/fabric-[switchId]/vc-[id]/vlan-cmc[id]/net-group-ref-[name]
    -- sys/chassis-[id]/cartridge-[slotId]/server-[serverInstanceId]/mgmt/fabric-[switchId]/vc-[id]/vlan-cmc[id]/net-group-ref-[name]
    -- sys/chassis-[id]/cartridge-[slotId]/server-[serverInstanceId]/mgmt/fabric-[switchId]/vc-[id]/vlan-cmc[id]/net-group-ref-[name]
    -- sys/chassis-[id]/mgmt/fabric-[switchId]/vc-[id]/vlan-cmc[id]/net-group-ref-[name]
    -- sys/fex-[id]/mgmt/fabric-[switchId]/vc-[id]/vlan-cmc[id]/net-group-ref-[name]
    -- sys/chassis-[id]/slot-[id]/mgmt/fabric-[switchId]/vc-[id]/vlan-cmc[id]/net-group-ref-[name]
    -- sys/fex-[id]/slot-[id]/mgmt/fabric-[switchId]/vc-[id]/vlan-cmc[id]/net-group-ref-[name]
    -- sys/chassis-[id]/shared-io-module/mgmt/fabric-[switchId]/vc-[id]/vlan-cmc[id]/net-group-ref-[name]
    -- sys/chassis-[id]/slot-[id]/shared-io-module/mgmt/fabric-[switchId]/vc-[id]/vlan-cmc[id]/net-group-ref-[name]
    -- sys/chassis-[id]/sw-slot-[id]/mgmt/fabric-[switchId]/vc-[id]/vlan-cmc[id]/net-group-ref-[name]
    -- sys/chassis-[id]/slot-[id]/mgmt/fabric-[switchId]/vc-[id]/vlan-cmc[id]/net-group-ref-[name]
    -- sys/switch-[id]/mgmt/fabric-[switchId]/vc-[id]/vlan-cmc[id]/net-group-ref-[name]
    -- sys/chassis-[id]/blade-[slotId]/board/storage-[type]-[id]/mgmt/fabric-[switchId]/vc-[id]/vlan-cmc[id]/net-group-ref-[name]
    -- sys/rack-unit-[id]/board/storage-[type]-[id]/mgmt/fabric-[switchId]/vc-[id]/vlan-cmc[id]/net-group-ref-[name]
    -- sys/chassis-[id]/cartridge-[slotId]/server-[serverInstanceId]/board/storage-[type]-[id]/mgmt/fabric-[switchId]/vc-[id]/vlan-cmc[id]/net-group-ref-[name]
    -- sys/chassis-[id]/storage-[type]-[id]/mgmt/fabric-[switchId]/vc-[id]/vlan-cmc[id]/net-group-ref-[name]
    -- sys/chassis-[id]/blade-[slotId]/board/storage-[type]-[id]/disk-[id]/mgmt/fabric-[switchId]/vc-[id]/vlan-cmc[id]/net-group-ref-[name]
    -- sys/rack-unit-[id]/board/storage-[type]-[id]/disk-[id]/mgmt/fabric-[switchId]/vc-[id]/vlan-cmc[id]/net-group-ref-[name]
    -- sys/chassis-[id]/cartridge-[slotId]/server-[serverInstanceId]/board/storage-[type]-[id]/disk-[id]/mgmt/fabric-[switchId]/vc-[id]/vlan-cmc[id]/net-group-ref-[name]
    -- sys/chassis-[id]/storage-[type]-[id]/disk-[id]/mgmt/fabric-[switchId]/vc-[id]/vlan-cmc[id]/net-group-ref-[name]
    -- sys/chassis-[id]/blade-[slotId]/enc-[id]/disk-[id]/mgmt/fabric-[switchId]/vc-[id]/vlan-cmc[id]/net-group-ref-[name]
    -- sys/rack-unit-[id]/enc-[id]/disk-[id]/mgmt/fabric-[switchId]/vc-[id]/vlan-cmc[id]/net-group-ref-[name]
    -- sys/chassis-[id]/cartridge-[slotId]/server-[serverInstanceId]/enc-[id]/disk-[id]/mgmt/fabric-[switchId]/vc-[id]/vlan-cmc[id]/net-group-ref-[name]
    -- sys/chassis-[id]/enc-[id]/disk-[id]/mgmt/fabric-[switchId]/vc-[id]/vlan-cmc[id]/net-group-ref-[name]
    -- sys/chassis-[id]/blade-[slotId]/board/storage-[type]-[id]/enc-[id]/disk-[id]/mgmt/fabric-[switchId]/vc-[id]/vlan-cmc[id]/net-group-ref-[name]
    -- sys/rack-unit-[id]/board/storage-[type]-[id]/enc-[id]/disk-[id]/mgmt/fabric-[switchId]/vc-[id]/vlan-cmc[id]/net-group-ref-[name]
    -- sys/chassis-[id]/cartridge-[slotId]/server-[serverInstanceId]/board/storage-[type]-[id]/enc-[id]/disk-[id]/mgmt/fabric-[switchId]/vc-[id]/vlan-cmc[id]/net-group-ref-[name]
    -- sys/chassis-[id]/storage-[type]-[id]/enc-[id]/disk-[id]/mgmt/fabric-[switchId]/vc-[id]/vlan-cmc[id]/net-group-ref-[name]
    -- sys/chassis-[id]/blade-[slotId]/board/sas-expander-[id]/mgmt/fabric-[switchId]/vc-[id]/vlan-cmc[id]/net-group-ref-[name]
    -- sys/rack-unit-[id]/board/sas-expander-[id]/mgmt/fabric-[switchId]/vc-[id]/vlan-cmc[id]/net-group-ref-[name]
    -- sys/chassis-[id]/cartridge-[slotId]/server-[serverInstanceId]/board/sas-expander-[id]/mgmt/fabric-[switchId]/vc-[id]/vlan-cmc[id]/net-group-ref-[name]
    -- sys/chassis-[id]/sas-expander-[id]/mgmt/fabric-[switchId]/vc-[id]/vlan-cmc[id]/net-group-ref-[name]
    -- sys/mgmt/fabric-[switchId]/vc-[id]/vlan-cmc[id]/net-group-ref-[name]
    -- sys/chassis-[id]/blade-[slotId]/fabric-[switchId]/path-[id]/vc-[id]/vlan-cmc[id]/net-group-ref-[name]
    -- sys/chassis-[id]/blade-[slotId]/fabric-[switchId]/path-[id]/vc-[id]/vlan-cmc[id]/net-group-ref-[name]
    -- sys/rack-unit-[id]/fabric-[switchId]/path-[id]/vc-[id]/vlan-cmc[id]/net-group-ref-[name]
    -- sys/chassis-[id]/cartridge-[slotId]/server-[serverInstanceId]/fabric-[switchId]/path-[id]/vc-[id]/vlan-cmc[id]/net-group-ref-[name]
    -- sys/chassis-[id]/cartridge-[slotId]/server-[serverInstanceId]/fabric-[switchId]/path-[id]/vc-[id]/vlan-cmc[id]/net-group-ref-[name]
    -- sys/chassis-[id]/fabric-[switchId]/path-[id]/vc-[id]/vlan-cmc[id]/net-group-ref-[name]
    -- sys/fex-[id]/fabric-[switchId]/path-[id]/vc-[id]/vlan-cmc[id]/net-group-ref-[name]
    -- sys/chassis-[id]/blade-[slotId]/adaptor-[id]/mgmt/fabric-[switchId]/path-[id]/vc-[id]/vlan-cmc[id]/net-group-ref-[name]
    -- sys/rack-unit-[id]/adaptor-[id]/mgmt/fabric-[switchId]/path-[id]/vc-[id]/vlan-cmc[id]/net-group-ref-[name]
    -- sys/chassis-[id]/cartridge-[slotId]/server-[serverInstanceId]/adaptor-[id]/mgmt/fabric-[switchId]/path-[id]/vc-[id]/vlan-cmc[id]/net-group-ref-[name]
    -- sys/chassis-[id]/cartridge-[slotId]/server-[serverInstanceId]/adaptor-[id]/mgmt/fabric-[switchId]/path-[id]/vc-[id]/vlan-cmc[id]/net-group-ref-[name]
    -- sys/chassis-[id]/blade-[slotId]/ext-board-[id]/boardController/mgmt/fabric-[switchId]/path-[id]/vc-[id]/vlan-cmc[id]/net-group-ref-[name]
    -- sys/rack-unit-[id]/ext-board-[id]/boardController/mgmt/fabric-[switchId]/path-[id]/vc-[id]/vlan-cmc[id]/net-group-ref-[name]
    -- sys/chassis-[id]/cartridge-[slotId]/server-[serverInstanceId]/ext-board-[id]/boardController/mgmt/fabric-[switchId]/path-[id]/vc-[id]/vlan-cmc[id]/net-group-ref-[name]
    -- sys/chassis-[id]/blade-[slotId]/boardController/mgmt/fabric-[switchId]/path-[id]/vc-[id]/vlan-cmc[id]/net-group-ref-[name]
    -- sys/rack-unit-[id]/boardController/mgmt/fabric-[switchId]/path-[id]/vc-[id]/vlan-cmc[id]/net-group-ref-[name]
    -- sys/chassis-[id]/cartridge-[slotId]/server-[serverInstanceId]/boardController/mgmt/fabric-[switchId]/path-[id]/vc-[id]/vlan-cmc[id]/net-group-ref-[name]
    -- sys/chassis-[id]/boardController/mgmt/fabric-[switchId]/path-[id]/vc-[id]/vlan-cmc[id]/net-group-ref-[name]
    -- sys/chassis-[id]/slot-[id]/boardController/mgmt/fabric-[switchId]/path-[id]/vc-[id]/vlan-cmc[id]/net-group-ref-[name]
    -- sys/chassis-[id]/blade-[slotId]/ext-board-[id]/mgmt/fabric-[switchId]/path-[id]/vc-[id]/vlan-cmc[id]/net-group-ref-[name]
    -- sys/rack-unit-[id]/ext-board-[id]/mgmt/fabric-[switchId]/path-[id]/vc-[id]/vlan-cmc[id]/net-group-ref-[name]
    -- sys/chassis-[id]/cartridge-[slotId]/server-[serverInstanceId]/ext-board-[id]/mgmt/fabric-[switchId]/path-[id]/vc-[id]/vlan-cmc[id]/net-group-ref-[name]
    -- sys/chassis-[id]/blade-[slotId]/mgmt/fabric-[switchId]/path-[id]/vc-[id]/vlan-cmc[id]/net-group-ref-[name]
    -- sys/rack-unit-[id]/mgmt/fabric-[switchId]/path-[id]/vc-[id]/vlan-cmc[id]/net-group-ref-[name]
    -- sys/chassis-[id]/cartridge-[slotId]/server-[serverInstanceId]/mgmt/fabric-[switchId]/path-[id]/vc-[id]/vlan-cmc[id]/net-group-ref-[name]
    -- sys/chassis-[id]/cartridge-[slotId]/server-[serverInstanceId]/mgmt/fabric-[switchId]/path-[id]/vc-[id]/vlan-cmc[id]/net-group-ref-[name]
    -- sys/chassis-[id]/mgmt/fabric-[switchId]/path-[id]/vc-[id]/vlan-cmc[id]/net-group-ref-[name]
    -- sys/fex-[id]/mgmt/fabric-[switchId]/path-[id]/vc-[id]/vlan-cmc[id]/net-group-ref-[name]
    -- sys/chassis-[id]/slot-[id]/mgmt/fabric-[switchId]/path-[id]/vc-[id]/vlan-cmc[id]/net-group-ref-[name]
    -- sys/fex-[id]/slot-[id]/mgmt/fabric-[switchId]/path-[id]/vc-[id]/vlan-cmc[id]/net-group-ref-[name]
    -- sys/chassis-[id]/shared-io-module/mgmt/fabric-[switchId]/path-[id]/vc-[id]/vlan-cmc[id]/net-group-ref-[name]
    -- sys/chassis-[id]/slot-[id]/shared-io-module/mgmt/fabric-[switchId]/path-[id]/vc-[id]/vlan-cmc[id]/net-group-ref-[name]
    -- sys/chassis-[id]/sw-slot-[id]/mgmt/fabric-[switchId]/path-[id]/vc-[id]/vlan-cmc[id]/net-group-ref-[name]
    -- sys/chassis-[id]/slot-[id]/mgmt/fabric-[switchId]/path-[id]/vc-[id]/vlan-cmc[id]/net-group-ref-[name]
    -- sys/switch-[id]/mgmt/fabric-[switchId]/path-[id]/vc-[id]/vlan-cmc[id]/net-group-ref-[name]
    -- sys/chassis-[id]/blade-[slotId]/board/storage-[type]-[id]/mgmt/fabric-[switchId]/path-[id]/vc-[id]/vlan-cmc[id]/net-group-ref-[name]
    -- sys/rack-unit-[id]/board/storage-[type]-[id]/mgmt/fabric-[switchId]/path-[id]/vc-[id]/vlan-cmc[id]/net-group-ref-[name]
    -- sys/chassis-[id]/cartridge-[slotId]/server-[serverInstanceId]/board/storage-[type]-[id]/mgmt/fabric-[switchId]/path-[id]/vc-[id]/vlan-cmc[id]/net-group-ref-[name]
    -- sys/chassis-[id]/storage-[type]-[id]/mgmt/fabric-[switchId]/path-[id]/vc-[id]/vlan-cmc[id]/net-group-ref-[name]
    -- sys/chassis-[id]/blade-[slotId]/board/storage-[type]-[id]/disk-[id]/mgmt/fabric-[switchId]/path-[id]/vc-[id]/vlan-cmc[id]/net-group-ref-[name]
    -- sys/rack-unit-[id]/board/storage-[type]-[id]/disk-[id]/mgmt/fabric-[switchId]/path-[id]/vc-[id]/vlan-cmc[id]/net-group-ref-[name]
    -- sys/chassis-[id]/cartridge-[slotId]/server-[serverInstanceId]/board/storage-[type]-[id]/disk-[id]/mgmt/fabric-[switchId]/path-[id]/vc-[id]/vlan-cmc[id]/net-group-ref-[name]
    -- sys/chassis-[id]/storage-[type]-[id]/disk-[id]/mgmt/fabric-[switchId]/path-[id]/vc-[id]/vlan-cmc[id]/net-group-ref-[name]
    -- sys/chassis-[id]/blade-[slotId]/enc-[id]/disk-[id]/mgmt/fabric-[switchId]/path-[id]/vc-[id]/vlan-cmc[id]/net-group-ref-[name]
    -- sys/rack-unit-[id]/enc-[id]/disk-[id]/mgmt/fabric-[switchId]/path-[id]/vc-[id]/vlan-cmc[id]/net-group-ref-[name]
    -- sys/chassis-[id]/cartridge-[slotId]/server-[serverInstanceId]/enc-[id]/disk-[id]/mgmt/fabric-[switchId]/path-[id]/vc-[id]/vlan-cmc[id]/net-group-ref-[name]
    -- sys/chassis-[id]/enc-[id]/disk-[id]/mgmt/fabric-[switchId]/path-[id]/vc-[id]/vlan-cmc[id]/net-group-ref-[name]
    -- sys/chassis-[id]/blade-[slotId]/board/storage-[type]-[id]/enc-[id]/disk-[id]/mgmt/fabric-[switchId]/path-[id]/vc-[id]/vlan-cmc[id]/net-group-ref-[name]
    -- sys/rack-unit-[id]/board/storage-[type]-[id]/enc-[id]/disk-[id]/mgmt/fabric-[switchId]/path-[id]/vc-[id]/vlan-cmc[id]/net-group-ref-[name]
    -- sys/chassis-[id]/cartridge-[slotId]/server-[serverInstanceId]/board/storage-[type]-[id]/enc-[id]/disk-[id]/mgmt/fabric-[switchId]/path-[id]/vc-[id]/vlan-cmc[id]/net-group-ref-[name]
    -- sys/chassis-[id]/storage-[type]-[id]/enc-[id]/disk-[id]/mgmt/fabric-[switchId]/path-[id]/vc-[id]/vlan-cmc[id]/net-group-ref-[name]
    -- sys/chassis-[id]/blade-[slotId]/board/sas-expander-[id]/mgmt/fabric-[switchId]/path-[id]/vc-[id]/vlan-cmc[id]/net-group-ref-[name]
    -- sys/rack-unit-[id]/board/sas-expander-[id]/mgmt/fabric-[switchId]/path-[id]/vc-[id]/vlan-cmc[id]/net-group-ref-[name]
    -- sys/chassis-[id]/cartridge-[slotId]/server-[serverInstanceId]/board/sas-expander-[id]/mgmt/fabric-[switchId]/path-[id]/vc-[id]/vlan-cmc[id]/net-group-ref-[name]
    -- sys/chassis-[id]/sas-expander-[id]/mgmt/fabric-[switchId]/path-[id]/vc-[id]/vlan-cmc[id]/net-group-ref-[name]
    -- sys/mgmt/fabric-[switchId]/path-[id]/vc-[id]/vlan-cmc[id]/net-group-ref-[name]
    -- sys/switch-[id]/ethlanflowmon/vc-[id]/vlan-cmc[id]/net-group-ref-[name]
    -- sys/switch-[id]/lanmon-eth/mon-[name]/vc-[id]/vlan-cmc[id]/net-group-ref-[name]
    -- sys/switch-[id]/sanmon-fc/mon-[name]/vc-[id]/vlan-cmc[id]/net-group-ref-[name]
    -- org-[name]/tier-[name]/ls-[name]/ether-[name]/net-group-ref-[name]
    -- org-[name]/ls-[name]/ether-[name]/net-group-ref-[name]
    -- org-[name]/lan-conn-pol-[name]/ether-[name]/net-group-ref-[name]
    -- fabric/lan/profiles/vnic-[name]/net-group-ref-[name]
    -- org-[name]/lan-conn-templ-[name]/net-group-ref-[name]
    -- org-[name]/san-conn-templ-[name]/net-group-ref-[name]
        -- fltFabricNetGroupRefNetSanGroupUnresolvable

CucsFaultCode ::= TEXTUAL-CONVENTION
        STATUS       current
        DESCRIPTION
       "A code identifying a class of fault."
        SYNTAX INTEGER {
    fltFabricComputeSlotEpMisplacedInChassisSlot(156),
    fltFabricComputeSlotEpServerIdentificationProblem(157),
    fltVnicEtherConfigFailed(169),
    fltVnicFcConfigFailed(170),
    fltProcessorUnitInoperable(174),
    fltProcessorUnitThermalNonCritical(175),
    fltProcessorUnitThermalThresholdCritical(176),
    fltProcessorUnitThermalThresholdNonRecoverable(177),
    fltProcessorUnitVoltageThresholdNonCritical(178),
    fltProcessorUnitVoltageThresholdCritical(179),
    fltProcessorUnitVoltageThresholdNonRecoverable(180),
    fltStorageLocalDiskInoperable(181),
    fltStorageItemCapacityExceeded(182),
    fltStorageItemCapacityWarning(183),
    fltMemoryUnitDegraded(184),
    fltMemoryUnitInoperable(185),
    fltMemoryUnitThermalThresholdNonCritical(186),
    fltMemoryUnitThermalThresholdCritical(187),
    fltMemoryUnitThermalThresholdNonRecoverable(188),
    fltMemoryArrayVoltageThresholdNonCritical(189),
    fltMemoryArrayVoltageThresholdCritical(190),
    fltMemoryArrayVoltageThresholdNonRecoverable(191),
    fltAdaptorUnitUnidentifiableFru(200),
    fltAdaptorUnitMissing(203),
    fltAdaptorUnitAdaptorReachability(206),
    fltAdaptorHostIfLinkDown(207),
    fltAdaptorExtIfLinkDown(209),
    fltPortPIoLinkDown(276),
    fltPortPIoFailed(277),
    fltPortPIoHardwareFailure(278),
    fltPortPIoSfpNotPresent(279),
    fltFabricExternalPcDown(282),
    fltDcxVcDown(283),
    fltNetworkElementInoperable(291),
    fltMgmtEntityDegraded(293),
    fltMgmtEntityDown(294),
    fltDcxNsFailed(304),
    fltComputePhysicalInsufficientlyEquipped(305),
    fltComputePhysicalIdentityUnestablishable(306),
    fltComputeBoardPowerError(310),
    fltComputePhysicalPowerProblem(311),
    fltComputePhysicalThermalProblem(312),
    fltComputePhysicalBiosPostTimeout(313),
    fltComputePhysicalDiscoveryFailed(314),
    fltComputePhysicalAssociationFailed(315),
    fltComputePhysicalInoperable(317),
    fltComputePhysicalUnassignedMissing(318),
    fltComputePhysicalAssignedMissing(319),
    fltComputePhysicalUnidentified(320),
    fltComputePhysicalUnassignedInaccessible(321),
    fltComputePhysicalAssignedInaccessible(322),
    fltLsServerFailed(324),
    fltLsServerDiscoveryFailed(326),
    fltLsServerConfigFailure(327),
    fltLsServerMaintenanceFailed(329),
    fltLsServerRemoved(330),
    fltLsServerInaccessible(331),
    fltLsServerAssociationFailed(332),
    fltLsServerUnassociated(334),
    fltLsServerServerUnfulfilled(337),
    fltEtherSwitchIntFIoSatelliteConnectionAbsent(367),
    fltEtherSwitchIntFIoSatelliteWiringProblem(368),
    fltEquipmentPsuPowerSupplyProblem(369),
    fltEquipmentFanDegraded(371),
    fltEquipmentFanInoperable(373),
    fltEquipmentPsuInoperable(374),
    fltEquipmentIOCardRemoved(376),
    fltEquipmentFanModuleMissing(377),
    fltEquipmentPsuMissing(378),
    fltEquipmentIOCardThermalProblem(379),
    fltEquipmentFanModuleThermalThresholdNonCritical(380),
    fltEquipmentPsuThermalThresholdNonCritical(381),
    fltEquipmentFanModuleThermalThresholdCritical(382),
    fltEquipmentPsuThermalThresholdCritical(383),
    fltEquipmentFanModuleThermalThresholdNonRecoverable(384),
    fltEquipmentPsuThermalThresholdNonRecoverable(385),
    fltEquipmentPsuVoltageThresholdNonCritical(387),
    fltEquipmentPsuVoltageThresholdCritical(389),
    fltEquipmentPsuVoltageThresholdNonRecoverable(391),
    fltEquipmentPsuPerfThresholdNonCritical(392),
    fltEquipmentPsuPerfThresholdCritical(393),
    fltEquipmentPsuPerfThresholdNonRecoverable(394),
    fltEquipmentFanPerfThresholdNonCritical(395),
    fltEquipmentFanPerfThresholdCritical(396),
    fltEquipmentFanPerfThresholdNonRecoverable(397),
    fltEquipmentIOCardFirmwareUpgrade(398),
    fltEquipmentChassisUnsupportedConnectivity(399),
    fltEquipmentChassisUnacknowledged(400),
    fltEquipmentIOCardUnsupportedConnectivity(401),
    fltEquipmentIOCardUnacknowledged(402),
    fltEquipmentIOCardPeerDisconnected(403),
    fltEquipmentChassisIdentity(404),
    fltEquipmentIOCardIdentity(405),
    fltEquipmentFanModuleIdentity(406),
    fltEquipmentPsuIdentity(407),
    fltEquipmentChassisPowerProblem(408),
    fltEquipmentChassisThermalThresholdCritical(409),
    fltEquipmentChassisThermalThresholdNonCritical(410),
    fltEquipmentChassisThermalThresholdNonRecoverable(411),
    fltComputeBoardCmosVoltageThresholdCritical(424),
    fltComputeBoardCmosVoltageThresholdNonRecoverable(425),
    fltMgmtEntityElectionFailure(428),
    fltMgmtEntityHaNotReady(429),
    fltMgmtEntityVersionIncompatible(430),
    fltEquipmentFanMissing(434),
    fltEquipmentIOCardAutoUpgradingFirmware(435),
    fltFirmwarePackItemImageMissing(436),
    fltEtherSwitchIntFIoSatelliteWiringNumbersUnexpected(440),
    fltMgmtEntityManagementServicesFailure(451),
    fltMgmtEntityManagementServicesUnresponsive(452),
    fltEquipmentChassisInoperable(456),
    fltEtherServerIntFIoHardwareFailure(458),
    fltDcxVcMgmtVifDown(459),
    fltSysdebugMEpLogMEpLogLog(460),
    fltSysdebugMEpLogMEpLogVeryLow(461),
    fltSysdebugMEpLogMEpLogFull(462),
    fltComputePoolEmpty(463),
    fltUuidpoolPoolEmpty(464),
    fltIppoolPoolEmpty(465),
    fltMacpoolPoolEmpty(466),
    fltFirmwareUpdatableImageUnusable(470),
    fltFirmwareBootUnitCantBoot(471),
    fltFcpoolInitiatorsEmpty(476),
    fltEquipmentIOCardInaccessible(478),
    fltDcxVIfLinkState(479),
    fltEquipmentFanModuleDegraded(480),
    fltEquipmentIOCardPostFailure(481),
    fltEquipmentFanPerfThresholdLowerNonRecoverable(484),
    fltMemoryUnitIdentityUnestablishable(502),
    fltComputePhysicalPostFailure(517),
    fltEquipmentPsuOffline(528),
    fltStorageRaidBatteryInoperable(531),
    fltSysdebugMEpLogTransferError(532),
    fltComputeRtcBatteryInoperable(533),
    fltMemoryBufferUnitThermalThresholdNonCritical(535),
    fltMemoryBufferUnitThermalThresholdCritical(536),
    fltMemoryBufferUnitThermalThresholdNonRecoverable(537),
    fltComputeIOHubThermalNonCritical(538),
    fltComputeIOHubThermalThresholdCritical(539),
    fltComputeIOHubThermalThresholdNonRecoverable(540),
    fltEquipmentChassisIdentityUnestablishable(543),
    fltSwVlanPortNsResourceStatus(549),
    fltFabricLanPinGroupEmpty(621),
    fltFabricSanPinGroupEmpty(622),
    fltAdaptorExtEthIfMisConnect(625),
    fltAdaptorHostEthIfMisConnect(626),
    fltPowerBudgetPowerBudgetCmcProblem(635),
    fltPowerBudgetPowerBudgetBmcProblem(637),
    fltPowerBudgetPowerBudgetDiscFail(640),
    fltPowerGroupPowerGroupInsufficientBudget(642),
    fltPowerGroupPowerGroupBudgetIncorrect(643),
    fltLicenseInstanceGracePeriodWarning1(670),
    fltLicenseInstanceGracePeriodWarning2(671),
    fltLicenseInstanceGracePeriodWarning3(672),
    fltLicenseInstanceGracePeriodWarning4(673),
    fltLicenseInstanceGracePeriodWarning5(674),
    fltLicenseInstanceGracePeriodWarning6(675),
    fltLicenseInstanceGracePeriodWarning7(676),
    fltLicenseFileBadLicenseFile(677),
    fltLicenseFileFileNotDeleted(678),
    fltMgmtIfMisConnect(688),
    fltLsComputeBindingAssignmentRequirementsNotMet(689),
    fltEquipmentFexPostFailure(702),
    fltEquipmentFexIdentity(703),
    fltAdaptorHostEthIfMissing(708),
    fltPortPIoInvalidSfp(713),
    fltMgmtIfMissing(717),
    fltFabricEthLanPcEpDown(727),
    fltFabricFcSanPcEpDown(728),
    fltEquipmentIOCardThermalThresholdNonCritical(729),
    fltEquipmentIOCardThermalThresholdCritical(730),
    fltEquipmentIOCardThermalThresholdNonRecoverable(731),
    fltEquipmentChassisSeepromInoperable(733),
    fltFabricFcSanPcEpIncompatibleSpeed(734),
    fltFabricFcSanPcIncompatibleSpeed(735),
    fltExtmgmtIfMgmtifdown(736),
    fltPowerChassisMemberPowerGroupCapInsufficient(740),
    fltPowerChassisMemberChassisFirmwareProblem(741),
    fltPowerChassisMemberChassisPsuInsufficient(742),
    fltPowerChassisMemberChassisPsuRedundanceFailure(743),
    fltPowerBudgetPowerCapReachedCommit(744),
    fltSysdebugAutoCoreFileExportTargetAutoCoreTransferFailure(747),
    fltFabricMonSpanConfigFail(757),
    fltPowerBudgetChassisPsuInsufficient(764),
    fltPowerBudgetTStateTransition(765),
    fltPowerPolicyPowerPolicyApplicationFail(766),
    fltMgmtIfNew(772),
    fltAdaptorExtEthIfMissing(775),
    fltStorageLocalDiskSlotEpUnusable(776),
    fltFabricEthEstcPcEpDown(777),
    fltEquipmentFexIdentityUnestablishable(778),
    fltEquipmentFanModuleInoperable(794),
    fltLsmaintMaintPolicyUnresolvableScheduler(795),
    fltFabricVsanErrorDisabled(796),
    fltFabricVsanEpErrorDisabled(797),
    fltPowerBudgetFirmwareMismatch(798),
    fltProcessorUnitIdentityUnestablishable(801),
    fltIqnpoolPoolEmpty(821),
    fltFabricDceSwSrvPcEpDown(831),
    fltFabricEpMgrEpTransModeFail(832),
    fltFabricVlanMisconfigured(833),
    fltFabricPIoEpErrorMisconfigured(834),
    fltFabricEthLanEpMissingPrimaryVlan(835),
    fltFabricEthLanPcMissingPrimaryVlan(836),
    fltVnicEtherPinningMismatch(840),
    fltVnicEtherPinningMisconfig(841),
    fltProcessorUnitDisabled(842),
    fltMemoryUnitDisabled(844),
    fltFirmwareBootUnitActivateStatusFailed(856),
    fltFabricInternalPcDown(858),
    fltMgmtEntityDevice1SharedStorageError(863),
    fltMgmtEntityDevice2SharedStorageError(864),
    fltMgmtEntityDevice3SharedStorageError(865),
    fltMgmtEntityHaSshKeysMismatched(866),
    fltMgmtPmonEntryUCSMProcessFailure(867),
    fltComputeBoardPowerFail(868),
    fltComputeABoardThermalProblem(869),
    fltVmVifLinkState(876),
    fltEquipmentPsuPowerSupplyShutdown(881),
    fltEquipmentPsuPowerThreshold(882),
    fltEquipmentPsuInputError(883),
    fltEquipmentSwitchCardPowerOff(884),
    fltNetworkElementInventoryFailed(885),
    fltAdaptorUnitExtnUnidentifiableFru(900),
    fltAdaptorUnitExtnMissing(901),
    fltEquipmentFexFexUnsupported(902),
    fltVnicIScsiConfigFailed(903),
    fltPkiKeyRingStatus(909),
    fltPkiTPStatus(910),
    fltComputePhysicalDisassociationFailed(915),
    fltComputePhysicalNetworkMisconfigured(916),
    fltVnicProfileProfileConfigIncorrect(917),
    fltComputeABoardMotherBoardVoltageThresholdUpperNonRecoverable(918),
    fltComputeABoardMotherBoardVoltageThresholdLowerNonRecoverable(919),
    fltComputeABoardMotherBoardVoltageUpperThresholdCritical(920),
    fltComputeABoardMotherBoardVoltageLowerThresholdCritical(921),
    fltVnicEtherIfVlanAccessFault(932),
    fltVnicEtherIfVlanUnresolvable(933),
    fltVnicEtherIfInvalidVlan(934),
    fltFabricVlanVlanConflictPermit(935),
    fltFabricVlanReqVlanPermitUnresolved(936),
    fltFabricVlanGroupReqVlanGroupPermitUnresolved(937),
    fltExtpolClientClientLostConnectivity(988),
    fltStorageLocalDiskDegraded(996),
    fltStorageRaidBatteryDegraded(997),
    fltStorageRaidBatteryRelearnAborted(998),
    fltStorageRaidBatteryRelearnFailed(999),
    fltStorageADefConfigurationError(1000),
    fltStorageInitiatorConfigurationError(1001),
    fltStorageVsanRefVsanUnresolvable(1002),
    fltStorageControllerPatrolReadFailed(1003),
    fltStorageControllerInoperable(1004),
    fltStorageLocalDiskRebuildFailed(1005),
    fltStorageLocalDiskCopybackFailed(1006),
    fltStorageVirtualDriveInoperable(1007),
    fltStorageVirtualDriveDegraded(1008),
    fltStorageVirtualDriveReconstructionFailed(1009),
    fltStorageVirtualDriveConsistencyCheckFailed(1010),
    fltAaaProviderGroupProvidergroup(1026),
    fltAaaConfigServergroup(1027),
    fltAaaRoleRoleNotDeployed(1028),
    fltAaaLocaleLocaleNotDeployed(1029),
    fltAaaUserRoleUserRoleNotDeployed(1030),
    fltAaaUserLocaleUserLocaleNotDeployed(1031),
    fltPkiKeyRingKeyRingNotDeployed(1032),
    fltCommSnmpSyscontactEmpty(1033),
    fltCommDateTimeCommTimeZoneInvalid(1034),
    fltAaaUserLocalUserNotDeployed(1035),
    fltCommSnmpUserSnmpUserNotDeployed(1036),
    fltCommSvcEpCommSvcNotDeployed(1037),
    fltComputeABoardPowerUsageProblem(1040),
    fltSwVlanPortNsVLANCompNotSupport(1056),
    fltPolicyControlEpSuspendModeActive(1057),
    fltNetworkElementThermalThresholdCritical(1080),
    fltFabricFcoeSanPcEpDown(1081),
    fltFabricFcoeSanEpDown(1082),
    fltFabricVsanMembershipDown(1083),
    fltFabricFcoeSanEpUnsupported(1084),
    fltFabricFcoeSanPcDown(1085),
    fltFabricFcoeSanPcUnsupported(1086),
    fltFabricFcoeEstcEpDown(1087),
    fltFabricPinTargetDown(1088),
    fltFabricExternalEpFcZoningEnable(1089),
    fltFabricEthLanEpOverlappingVlan(1090),
    fltFabricEthLanPcOverlappingVlan(1091),
    fltFabricFcEstcEpFcStoragePortInvalid(1092),
    fltFabricFcoeEstcEpFcoeStoragePortInvalid(1093),
    fltFabricFcSanPcFcPortchannelMembersInvalid(1094),
    fltFabricVlanMisconfiguredMcastPolicy(1095),
    fltMgmtConnectionDisabled(1097),
    fltMgmtConnectionUnused(1098),
    fltMgmtConnectionUnsupportedConnectivity(1099),
    fltCallhomeEpNoSnmpPolicyForCallhome(1102),
    fltCapabilityCatalogueLoadErrors(1103),
    fltExtmgmtArpTargetsArpTargetsNotValid(1114),
    fltVnicFcPinningMisconfig(1209),
    fltExtpolClientGracePeriodWarning(1211),
    fltExtpolClientGracePeriodWarning2(1212),
    fltExtpolClientGracePeriodWarning3(1213),
    fltExtpolClientGracePeriodWarning4(1214),
    fltExtpolClientGracePeriodWarning5(1215),
    fltExtpolClientGracePeriodWarning6(1216),
    fltExtpolClientGracePeriodWarning7(1217),
    fltExtpolClientGracePeriodWarning1(1218),
    fltStorageItemFilesystemIssues(1219),
    fltStorageInitiatorDuplicateFcZone(1220),
    fltStorageIniGroupSwitchModeDisabled(1221),
    fltPkiKeyRingModulus(1222),
    fltAaaOrgLocaleOrgNotPresent(1223),
    fltNetworkOperLevelExtraprimaryvlans(1229),
    fltEquipmentHealthLedCriticalError(1236),
    fltEquipmentHealthLedMinorError(1237),
    fltVnicEtherIfRemoteVlanUnresolvable(1249),
    fltVnicFcIfRemoteVsanUnresolvable(1250),
    fltVnicEtherVirtualizationConflict(1251),
    fltLsIssuesIscsiConfigFailed(1252),
    fltStorageLocalDiskMissing(1256),
    fltStorageFlexFlashControllerInoperable(1257),
    fltStorageFlexFlashCardInoperable(1258),
    fltStorageFlexFlashCardMissing(1259),
    fltStorageFlexFlashVirtualDriveDegraded(1260),
    fltStorageFlexFlashVirtualDriveInoperable(1261),
    fltStorageFlexFlashControllerUnhealthy(1262),
    fltAaaProviderGroupProvidergroupsize(1279),
    fltFirmwareAutoSyncPolicyDefaultHostPackageMissing(1284),
    fltFirmwareAutoSyncPolicyDefaultHostPackageMissingVersions(1285),
    fltFabricNetflowMonSessionFlowMonConfigFail(1304),
    fltFabricNetflowMonSessionNetflowSessionConfigFail(1305),
    fltFabricPooledVlanNamedVlanUnresolved(1306),
    fltExtvmmVMNDRefVmNetworkReferenceIncorrect(1320),
    fltExtmgmtNdiscTargetsNdiscTargetsNotValid(1321),
    fltFirmwareBootUnitPowerCycleRequired(1325),
    fltMgmtControllerUnsupportedDimmBlacklisting(1328),
    fltFabricEthLanEpUdldLinkDown(1358),
    fltFabricEthLanPcEpUdldLinkDown(1359),
    fltFabricFcoeSanEpUdldLinkDown(1360),
    fltFabricFcoeSanPcEpUdldLinkDown(1361),
    fltFirmwareStatusCimcFirmwareMismatch(1365),
    fltFirmwareStatusPldFirmwareMismatch(1366),
    fltSysdebugLogExportStatusLogExportFailure(1369),
    fltVnicEtherVirtualizationNetflowConflict(1380),
    fltFabricVlanPrimaryVlanMissingForIsolated(1382),
    fltFabricVlanPrimaryVlanMissingForCommunity(1383),
    fltFabricVlanMismatchA(1384),
    fltFabricVlanMismatchB(1385),
    fltFabricVlanErrorAssocPrimary(1386),
    fltLsServerSvnicNotPresent(1388),
    fltLsIssuesKvmPolicyUnsupported(1389),
    fltMgmtBackupPolicyConfigConfigurationBackupOutdated(1392),
    fltNetworkOperLevelExtrasecondaryvlans(1396),
    fltSwVlanExtrasecondaryvlansperprimary(1397),
    fltCimcvmediaActualMountEntryVmediaMountFailed(1404),
    fltEquipmentTpmSlaveTpm(1439),
    fltStorageMezzFlashLifeConfigurationError(1448),
    fltStorageMezzFlashLifeDegraded(1449),
    fltStorageFlexFlashControllerMismatch(1450),
    fltStorageFlexFlashDriveUnhealthy(1451),
    fltStorageFlexFlashCardUnhealthy(1452),
    fltPoolElementDuplicatedAssigned(1453),
    fltMgmtInterfaceNamedInbandVlanUnresolved(1454),
    fltMgmtInterfaceInbandUnsupportedServer(1455),
    fltMgmtInterfaceInbandUnsupportedFirmware(1456),
    fltSwVlanPortNsResourceStatusWarning(1464),
    fltNetworkElementMemoryerror(1465),
    fltComputePhysicalAdapterMismatch(1467),
    fltNetworkElementRemoved(1493),
    fltPowerBudgetChassisPsuMixedMode(1498),
    fltPowerBudgetPowerBudgetUnavailable(1499),
    fltStorageLocalDiskInaccessible(1519),
    fltEquipmentChassisInvalidFru(1558),
    fltEquipmentSwitchIOCardRemoved(1559),
    fltEquipmentSwitchIOCardThermalProblem(1560),
    fltEquipmentSwitchIOCardThermalThresholdNonCritical(1561),
    fltEquipmentSwitchIOCardThermalThresholdCritical(1562),
    fltEquipmentSwitchIOCardThermalThresholdNonRecoverable(1563),
    fltEquipmentSwitchIOCardPeerDisconnected(1564),
    fltEquipmentSwitchIOCardIdentity(1565),
    fltEquipmentSwitchIOCardCpuThermalThresholdCritical(1566),
    fltStorageLocalDiskThermalIssueCritical(1604),
    fltStorageLocalDiskThermalIssueNonRecoverable(1605),
    fltStorageLocalDiskNotSupported(1606),
    fltFabricComputeMSlotEpMisplacedInChassisSlot(1616),
    fltFabricComputeMSlotEpServerIdentificationProblem(1617),
    fltFabricCartridgeSlotEpMisplacedInChassisSlot(1618),
    fltStorageControllerNotSupported(1620),
    fltStorageVirtualDriveDeploymentFailure(1621),
    fltStorageVirtualDriveMissing(1622),
    fltStorageVirtualDriveMismatch(1623),
    fltStorageVDMemberEpMismatch(1624),
    fltFirmwareBootUnitFirmwareBootFailed(1627),
    fltAaaDefaultAuthDefaultAuthNotDeployed(1668),
    fltAaaDomainDomainNotDeployed(1669),
    fltLsServerFAULT(1671),
    fltMgmtBackupLocalInternalBackupFailed(1672),
    fltVnicEtherCdnConfigNotApplied(1680),
    fltComputePhysicalConnectivityDown(1681),
    fltStorageSasExpanderInoperable(1685),
    fltStorageSasExpanderAccessibilityProblem(1686),
    fltStorageSasExpanderDegraded(1687),
    fltStorageLocalDiskLinkDegraded(1688),
    fltFabricFcSanNumOfVsanExceedLimit(1694),
    fltSwVlanPortNsCompressedSetsExhaustedWarning(1700),
    fltNetworkElementKernelMemCricitalThreshold(1701),
    fltFlowctrlItemFlowctrlconfig(1702),
    fltNetworkElementSystemshutdown(1703),
    fltMgmtHealthStatusHealthWarningIssue(1704),
    fltMgmtHealthStatusHealthMinorIssue(1705),
    fltMgmtHealthStatusHealthMajorIssue(1706),
    fltMgmtHealthStatusHealthCriticalIssue(1707),
    fltComputePhysicalDeprecated(1708),
    fltComputePhysicalAdapterFirmwareNeedsUpdate(1709),
    fltComputePhysicalIdentityUnestablishableOrDeprecated(1710),
    fltEquipmentIOCardDeprecated(1713),
    fltFabricSwChPhEpUncleanConfiguration(1719),
    fltFabricComputeSlotEpNotSupportedInChassisSlot(1720),
    fltFabricDceSwSrvEpDown(1721),
    fltStorageLocalDiskThermalIssueNonCritical(1731),
    fltStorageLocalDiskFailed(1732),
    fltEquipmentSystemIOControllerRemoved(1744),
    fltComputeRackUnitFanSpeedConfigurationFailed(1745),
    fltFabricEthLanNumOfVLANCompGrpExceedLimit(1748),
    fltFabricMulticastPolicySameOrEmptyPeerQuerierIp(1749),
    fltAdaptorUnitDeprecated(1753),
    fltMgmtInterfaceInbandPinningInvalid(1754),
    fltEtherPIoInvalidSfp(1755),
    fltNetworkOperLevelExtravif(1756),
    fltNetworkElementDeprecated(1757),
    fltFabricNetGroupNativeVlanNotFound(1758),
    fltEquipmentChassisChassislimitExceeded(1761),
    fltMgmtEntityDevice1SharedStorageConnectError(1766),
    fltMgmtEntityDevice2SharedStorageConnectError(1767),
    fltMgmtEntityDevice3SharedStorageConnectError(1768),
    fltSwEthLanBorderVlanLimitExceeded(1778),
    fltMgmtEntityMgmtDbVersionMismatch(1781),
    fltEquipmentTpmTpmMismatch(1784),
    fltEquipmentSharedIOModuleInaccessible(1792),
    fltEquipmentChassisInaccessibleB(1793),
    fltEquipmentChassisInaccessibleA(1794),
    fltEquipmentSystemIOControllerThermalProblem(1795),
    fltEquipmentSystemIOControllerUnacknowledged(1796),
    fltEquipmentIOCardBackPlanePortProblem(1797),
    fltEquipmentSwitchIOCardBackPlanePortProblem(1798),
    fltEquipmentFexBackPlanePortProblem(1799),
    fltFabricFcZoneProfileSwitchModeDisabled(1825),
    fltFabricFcUserZoneConfigFailure(1826),
    fltStorageEnclosureThermalIssueNonCritical(1831),
    fltStorageEnclosureThermalIssueCritical(1832),
    fltStorageEnclosureThermalIssueNonRecoverable(1833),
    fltStorageControllerDegraded(1834),
    fltStorageSasExpanderLinkMisconnect(1835),
    fltStorageSasExpanderLinkDegraded(1836),
    fltStorageEnclosureMissing(1837),
    fltStorageEnclosureFruEmpty(1838),
    fltStorageEnclosureDiskSlotEpMissing(1839),
    fltStorageEnclosureDiskSlotEpEquipmentInoperable(1840),
    fltStorageEnclosureDiskSlotEpChassisSpare(1841),
    fltStorageEnclosureDiskSlotEpHotspareUnsupported(1842),
    fltStorageEnclosureDiskSlotEpSharingUnsupported(1843),
    fltStorageEnclosureDiskSlotEpIoeOwnershipUnassigned(1844),
    fltStorageEnclosureDiskSlotEpHddslotServer2OwnershipUnassigned(1845),
    fltEquipmentChassisProfileFailed(1846),
    fltEquipmentChassisProfileDiscoveryFailed(1847),
    fltEquipmentChassisProfileConfigFailure(1848),
    fltEquipmentChassisProfileRemoved(1849),
    fltEquipmentChassisProfileInaccessible(1850),
    fltEquipmentChassisProfileAssociationFailed(1851),
    fltEquipmentChassisProfileUnassociated(1852),
    fltFabricNetGroupRefNetSanGroupUnresolvable(1873),
    fltEtherPIoUnknownServerDevice(1889),
    fltEtherPIoInterfaceMismatch(1891),
    fltAdaptorUnitPciConfigIssue(1892),
    fltNetworkElementEvacuationon(1893),
    fltNetworkLimitUnicastMac(1894),
    fltNetworkLimitMulticastMac(1895),
    fltNetworkLimitPvlifvlanmbr(1896),
    fltNetworkLimitPvsystem(1897),
    fltNetworkLimitIgmpgroup(1898),
    fltMgmtDbStateDbCorruptionDetected(1899),
    fltMgmtDbStateHighDbCorruptionDetected(1900),
    fltEquipmentInventoryStatusHardwareMismatch(1901),
    fltEquipmentChassisPhysicalSecurity(1902),
    fltEquipmentComputeConnConfigProblem(1903),
    fltVnicEtherPrimaryVlanMissing(1907),
    fltVnicEtherNetSanGroupMisconfigured(1908),
    fltComputePhysicalKmipFault(1912),
    fltComputePhysicalHardwareInventoryMismatch(1913),
    fltComputePhysicalPciConfigMismatch(1914),
    fltStorageEnclosureDiskSlotEpSecondControllerAbsent(1915),
    fltAdaptorUnitUnConnectedAdaptorReachability(1926),
    fltMgmtHealthStatusHealthInfoIssue(1927),
    fltComputeRackUnitPhysicalSecurity(1932),
    fltBiosUnitFD0FailedSecurityVerification(1933),
    fltComputeBoardFailedSecureFuseValidation(1934),
    fltVnicFcUnsupported(1944),
    fltStorageControllerNonOptimal(1945),
    fltStorageFlexFlashCardIoerrors(1946),
    fltStorageNvmeSwitchDegraded(1947),
    fltStorageLocalDiskUnhealthy(1948),
    fltNetworkLimitIftmcpv(1949),
    fltNetworkLimitDvif(1950),
    fltAdaptorExtEthIfUnsupportedConection(1951),
    fltFabricVsanReserved(1956),
    fltFabricVlanReserved(1957),
    fltEquipmentSystemIOControllerInoperable(1959),
    fltComputeRackUnitUnsupportedConfig(1962),
    fltComputeRackUnitConfigMismatch(1963),
    fltMgmtKvmCertificateCertificateUnsupported(1966),
    fltMgmtKvmCertificateCertificateEmptyParams(1967),
    fltStorageControllerPciEquipSlotUnsecure(1968),
    fsmStFailEquipmentChassisRemoveChassisDecomission(16407),
    fsmStFailEquipmentLocatorLedSetLocatorLedExecute(16408),
    fsmStFailMgmtControllerExtMgmtIfConfigSecondary(16518),
    fsmStFailFabricComputeSlotEpIdentifyExecutePeer(16519),
    fsmStFailComputeBladeDiscoverSerialDebugDisconnect(16520),
    fsmStFailEquipmentChassisPsuPolicyConfigExecute(16533),
    fsmStFailAdaptorHostFcIfResetFcPersBindingExecutePeer(16534),
    fsmStFailFabricLanCloudSwitchModeWaitForUserAck(16539),
    fsmStFailVnicProfileSetDeployPeer(16550),
    fsmStFailCommSvcEpUpdateSvcEpSetEpPeer(16576),
    fsmStFailCommSvcEpRestartWebSvcPeer(16577),
    fsmStFailAaaEpUpdateEpSetEpPeer(16579),
    fsmStFailAaaRealmUpdateRealmSetRealmPeer(16580),
    fsmStFailAaaUserEpUpdateUserEpSetUserPeer(16581),
    fsmStFailPkiEpUpdateEpSetKeyRingPeer(16582),
    fsmStFailSysfileMutationSingleExecute(16600),
    fsmStFailSysfileMutationGlobalPeer(16601),
    fsmStFailSysdebugManualCoreFileExportTargetExportExecute(16604),
    fsmStFailSysdebugAutoCoreFileExportTargetConfigurePeer(16605),
    fsmStFailSysdebugLogControlEpLogControlPersistPeer(16606),
    fsmStFailSwAccessDomainDeployUpdateConnectivity(16634),
    fsmStFailSwEthLanBorderDeployUpdateVlanGroups(16635),
    fsmStFailSwFcSanBorderDeployUpdateConnectivity(16636),
    fsmStFailSwUtilityDomainDeployUpdateConnectivity(16637),
    fsmStFailSyntheticFsObjCreateCreateRemote(16641),
    fsmStFailFirmwareDownloaderDownloadUnpackLocal(16650),
    fsmStFailFirmwareImageDeleteRemote(16651),
    fsmStFailMgmtControllerUpdateSwitchVerifyRemote(16653),
    fsmStFailMgmtControllerUpdateIOMUpdateRequest(16654),
    fsmStFailMgmtControllerActivateIOMReset(16655),
    fsmStFailMgmtControllerUpdateBMCUpdateRequest(16656),
    fsmStFailMgmtControllerActivateBMCReset(16657),
    fsmStFailCallhomeEpConfigCallhomeSetPeer(16670),
    fsmStFailMgmtIfSwMgmtOobIfConfigSwitch(16673),
    fsmStFailMgmtIfSwMgmtInbandIfConfigSwitch(16674),
    fsmStFailMgmtIfVirtualIfConfigRemote(16679),
    fsmStFailMgmtIfEnableVipLocal(16680),
    fsmStFailMgmtIfDisableVipPeer(16681),
    fsmStFailMgmtIfEnableHALocal(16682),
    fsmStFailMgmtBackupBackupUpload(16683),
    fsmStFailMgmtImporterImportReportResults(16684),
    fsmStFailStatsCollectionPolicyUpdateEpSetEpB(16742),
    fsmStFailQosclassDefinitionConfigGlobalQoSWaitForUserAck(16745),
    fsmStFailEpqosDefinitionDeployPeer(16749),
    fsmStFailEpqosDefinitionDelTaskRemovePeer(16750),
    fsmStFailEquipmentIOCardResetCmcExecute(16803),
    fsmStFailMgmtControllerUpdateUCSManagerStart(16815),
    fsmStFailMgmtControllerSysConfigSecondary(16823),
    fsmStFailAdaptorExtEthIfPathResetEnable(16852),
    fsmStFailAdaptorHostEthIfCircuitResetEnableB(16857),
    fsmStFailAdaptorHostFcIfCircuitResetEnableB(16858),
    fsmStFailExtvmmProviderConfigSetPeer(16879),
    fsmStFailExtvmmKeyStoreCertInstallSetPeer(16880),
    fsmStFailExtvmmSwitchDelTaskRemoveProviderRemoveLocal(16881),
    fsmStFailExtvmmMasterExtKeyConfigSetPeer(16898),
    fsmStFailCapabilityUpdaterUpdaterUnpackLocal(16904),
    fsmStFailFirmwareDistributableDeleteRemote(16906),
    fsmStFailCapabilityCatalogueDeployCatalogueFinalize(16931),
    fsmStFailEquipmentFexRemoveFexDecomission(16942),
    fsmStFailEquipmentLocatorLedSetFeLocatorLedExecute(16943),
    fsmStFailEquipmentChassisPowerCapWait(16944),
    fsmStFailEquipmentIOCardMuxOfflineCleanupEntries(16945),
    fsmStFailComputePhysicalAssociateWaitForIBMCFwUpdate(16973),
    fsmStFailComputePhysicalDisassociateSerialDebugPnuOSDisconnect(16974),
    fsmStFailComputePhysicalPowerCapConfig(16975),
    fsmStFailComputePhysicalDecommissionUnconfigExtMgmtRules(16976),
    fsmStFailComputePhysicalSoftShutdownExecute(16977),
    fsmStFailComputePhysicalHardShutdownExecute(16978),
    fsmStFailComputePhysicalTurnupPowerDeployWait(16979),
    fsmStFailComputePhysicalPowercycleSanitize(16980),
    fsmStFailComputePhysicalHardresetSanitize(16981),
    fsmStFailComputePhysicalSoftresetSanitize(16982),
    fsmStFailComputePhysicalSwConnUpdB(16983),
    fsmStFailComputePhysicalBiosRecoveryWait(16984),
    fsmStFailComputePhysicalCmosResetSanitize(16986),
    fsmStFailComputePhysicalResetBmcExecute(16987),
    fsmStFailEquipmentIOCardResetIomExecute(16988),
    fsmStFailComputeRackUnitDiscoverWaitForConnReady(16994),
    fsmStFailLsServerConfigureCheckAssignedIdentifiersForDup(16995),
    fsmStFailSwEthMonDeployUpdateEthMon(17000),
    fsmStFailSwFcMonDeployUpdateFcMon(17001),
    fsmStFailFabricSanCloudSwitchModeWaitForUserAck(17002),
    fsmStFailComputePhysicalUpdateExtUsersDeploy(17008),
    fsmStFailSysdebugTechSupportInitiateLocal(17012),
    fsmStFailSysdebugTechSupportDeleteTechSupFilePeer(17013),
    fsmStFailSysdebugTechSupportDownloadDeleteSub(17014),
    fsmStFailComputePhysicalUpdateAdaptorUpdateRequestPeer(17043),
    fsmStFailComputePhysicalActivateAdaptorReset(17044),
    fsmStFailCapabilityCatalogueActivateCatalogUnpackLocal(17045),
    fsmStFailCapabilityMgmtExtensionActivateMgmtExtUnpackLocal(17046),
    fsmStFailLicenseDownloaderDownloadValidateRemote(17050),
    fsmStFailLicenseFileInstallRemote(17051),
    fsmStFailLicenseFileClearRemote(17052),
    fsmStFailLicenseInstanceUpdateFlexlmRemote(17053),
    fsmStFailComputePhysicalConfigSoLExecute(17083),
    fsmStFailComputePhysicalUnconfigSoLExecute(17084),
    fsmStFailPortPIoInCompatSfpPresenceShutdown(17089),
    fsmStFailComputePhysicalDiagnosticInterruptExecute(17116),
    fsmStFailSysdebugCoreDownloadDeleteSub(17133),
    fsmStFailEquipmentChassisDynamicReallocationConfig(17134),
    fsmStFailComputePhysicalResetKvmExecute(17163),
    fsmStFailMgmtControllerOnlineSwConfigureConnPeer(17169),
    fsmStFailComputeRackUnitOfflineSwUnconfigurePeer(17170),
    fsmStFailEquipmentLocatorLedSetFiLocatorLedExecute(17187),
    fsmStFailFabricEpMgrConfigureWaitOnPhys(17214),
    fsmStFailVnicProfileSetDeployAliasPeer(17223),
    fsmStFailSwPhysConfPhysicalVerifyPhysConfig(17239),
    fsmStFailExtvmmEpClusterRoleSetPeer(17254),
    fsmStFailVmLifeCyclePolicyConfigPeer(17259),
    fsmStFailEquipmentBeaconLedIlluminateExecuteB(17262),
    fsmStFailEtherServerIntFIoConfigSpeedConfigure(17271),
    fsmStFailComputePhysicalUpdateBIOSUpdateRequest(17281),
    fsmStFailComputePhysicalActivateBIOSUpdateTokens(17282),
    fsmStFailIdentIdentRequestUpdateIdentExecute(17312),
    fsmStFailIdentMetaSystemSyncPing(17313),
    fsmStFailComputePhysicalResetIpmiExecute(17326),
    fsmStFailComputePhysicalFwUpgradeWaitForIBMCFwUpdate(17327),
    fsmStFailComputeRackUnitAdapterResetSanitize(17328),
    fsmStFailPortPIoInCompatSfpReplacedEnablePort(17358),
    fsmStFailExtpolEpRegisterFsmExecute(17359),
    fsmStFailExtpolRegistryCrossDomainConfigSetPeer(17360),
    fsmStFailExtpolRegistryCrossDomainDeleteSetPeer(17361),
    fsmStFailNfsMountInstMountVerifyRegistration(17377),
    fsmStFailNfsMountInstUnmountUnmountPeer(17378),
    fsmStFailNfsMountDefReportNfsMountSuspendReport(17379),
    fsmStFailStorageSystemSyncExecute(17395),
    fsmStFailFirmwareSystemDeployDownloadImages(17408),
    fsmStFailFirmwareSystemApplyCatalogPackResolveImages(17409),
    fsmStFailComputeServerDiscPolicyResolveScrubPolicyResolve(17426),
    fsmStFailSwFcSanBorderActivateZoneSetVerifyUserZoneConfig(17439),
    fsmStFailExtpolEpRepairCertVerifyGuid(17446),
    fsmStFailPolicyControlEpOperateResolve(17447),
    fsmStFailPolicyPolicyScopeReleasePolicyFsmRelease(17448),
    fsmStFailPolicyPolicyScopeReleaseOperationFsmRelease(17449),
    fsmStFailPolicyPolicyScopeReleaseStorageFsmRelease(17450),
    fsmStFailPolicyPolicyScopeResolveManyPolicyFsmResolveMany(17451),
    fsmStFailPolicyPolicyScopeResolveManyOperationFsmResolveMany(17452),
    fsmStFailPolicyPolicyScopeResolveManyStorageFsmResolveMany(17453),
    fsmStFailPolicyPolicyScopeReleaseManyPolicyFsmReleaseMany(17454),
    fsmStFailPolicyPolicyScopeReleaseManyOperationFsmReleaseMany(17455),
    fsmStFailPolicyPolicyScopeReleaseManyStorageFsmReleaseMany(17456),
    fsmStFailPolicyPolicyScopeResolveAllPolicyFsmResolveAll(17457),
    fsmStFailPolicyPolicyScopeResolveAllOperationFsmResolveAll(17458),
    fsmStFailPolicyPolicyScopeResolveAllStorageFsmResolveAll(17459),
    fsmStFailPolicyPolicyScopeReleaseAllPolicyFsmReleaseAll(17460),
    fsmStFailPolicyPolicyScopeReleaseAllOperationFsmReleaseAll(17461),
    fsmStFailPolicyPolicyScopeReleaseAllStorageFsmReleaseAll(17462),
    fsmStFailMgmtExportPolicyReportConfigCopyReport(17484),
    fsmStFailExtpolProviderReportConfigImportReport(17485),
    fsmStFailObserveObservedResolvePolicyFsmExecute(17491),
    fsmStFailObserveObservedResolveResourceFsmExecute(17492),
    fsmStFailObserveObservedResolveVMFsmExecute(17493),
    fsmStFailObserveObservedResolveControllerFsmExecute(17494),
    fsmStFailMgmtControllerRegistryConfigRemovePeer(17499),
    fsmStFailGmetaHolderInventoryReportStorageInventory(17608),
    fsmStFailComputePhysicalCimcSessionDeleteExecute(17609),
    fsmStFailPolicyControlledTypeOperateResolveAll(17612),
    fsmStFailFabricVnetEpSyncEpPushVnetEpDeletionSync(17619),
    fsmStFailSwEthLanFlowMonDeployUpdateEthFlowMon(17639),
    fsmStFailMgmtIPv6IfAddrSwMgmtOobIpv6IfConfigSwitch(17665),
    fsmStFailComputePhysicalUpdateBoardControllerUpdateRequest(17667),
    fsmStFailExtvmmNetworkSetsDeployPeer(17703),
    fsmStFailComputePhysicalConfigBoardConfigMemoryPolicy(17707),
    fsmStFailComputePhysicalResetMemoryErrorsExecute(17708),
    fsmStFailMgmtControllerExtMgmtInterfaceConfigStandbyCMCVlanCfg(17714),
    fsmStFailComputeRackUnitCreateDhcpEntryExecutePeer(17715),
    fsmStFailComputePhysicalServiceInfraDeploySwConfigPeer(17716),
    fsmStFailComputePhysicalServiceInfraWithdrawSwUnConfigPeer(17717),
    fsmStFailSysdebugLogExportPolicyConfigurePeer(17755),
    fsmStFailComputePhysicalFlashControllerUpdateFlashLife(17757),
    fsmStFailStorageFlexFlashControllerMOpsResetReset(17818),
    fsmStFailStorageFlexFlashControllerMOpsFormatFormat(17819),
    fsmStFailStorageFlexFlashControllerMOpsPairPair(17820),
    fsmStFailComputePhysicalEnableCimcSecureBootUpdateRequest(17826),
    fsmStFailIdentMetaSystemUcscUnivSyncExecute(17850),
    fsmStFailMgmtControllerLockConfigPowerButtonLockConfig(17933),
    fsmStFailMgmtControllerPowerBudgetReclaimConfigPowerOffWait(17934),
    fsmStFailComputePhysicalOobStorageAdminConfigTearDownVMediaPeer(17935),
    fsmStFailEquipmentIOCardBaseFePresenceIdentify(17940),
    fsmStFailEquipmentIOCardBaseFeConnEnableChassis(17941),
    fsmStFailEquipmentPsuUpdatePSUUpdateRequest(17987),
    fsmStFailMgmtControllerUpdateCMCUpdateRequest(18012),
    fsmStFailMgmtControllerActivateCMCReset(18013),
    fsmStFailMgmtControllerUpdateAdaptorUpdateRequestPeer(18014),
    fsmStFailMgmtControllerActivateAdaptorServersPowerOffCompletion(18015),
    fsmStFailMgmtControllerUpdateRaidControllerUpdateRequest(18016),
    fsmStFailMgmtControllerUpdateBoardControllerUpdateRequest(18017),
    fsmStFailFabricCartridgeSlotEpIdentifyExecutePeer(18024),
    fsmStFailFabricComputeMSlotEpIdentifyExecutePeer(18025),
    fsmStFailEquipmentChassisOobStorageAdminCfgOobStorageInventory(18026),
    fsmStFailComputeServerUnitDiscoverUnconfigExtMgmtRules(18032),
    fsmStFailMgmtIfFaPresenceIdentify(18033),
    fsmStFailMgmtIfFaConnSharedIOModuleInventory(18034),
    fsmStFailEquipmentIOCardEvacuateExecute(18045),
    fsmStFailEquipmentIOCardResetEvacuateExecute(18046),
    fsmStFailComputePhysicalClearTPMUnconfigVmedia(18051),
    fsmStFailEquipmentIOCardResetPeerCmcExecute(18102),
    fsmStFailSwExtUtilityConfPortBreakoutVerifyBreakoutConfig(18124),
    fsmStFailEquipmentSwitchIOCardEvacuateExecute(18146),
    fsmStFailEquipmentSwitchIOCardResetEvacuateExecute(18147),
    fsmStFailMorefImportRootApplyMoRefsDeleteAllMoRefs(18161),
    fsmStFailStorageEnclosureRemoveEnclosureValidateRemoval(18169),
    fsmStFailMgmtControllerPowerCapConfig(18184),
    fsmStFailEquipmentSystemIOControllerResetCmcExecute(18185),
    fsmStFailComputePhysicalDiskZoningInventoryStorageInventory(18186),
    fsmStFailEquipmentChassisProfileConfigureWaitForMaintPermission(18206),
    fsmStFailEquipmentChassisAssociateDownloadImages(18207),
    fsmStFailEquipmentChassisDisassociateComplete(18208),
    fsmStFailEtherServerIntFIoConfigConfigure(18237),
    fsmStFailMgmtControllerEnableSecureBootUpdateRequest(18239),
    fsmStFailMgmtControllerUpdateColusaCMCUpdateRequest(18240),
    fsmStFailMgmtControllerActivateColusaCMCReset(18241),
    fsmStFailEquipmentChassisChassisUpgradeWaitForPowerOff(18242),
    fsmStFailMgmtControllerUpdateColusaBoardControllerUpdateRequest(18243),
    fsmStFailMgmtControllerUpdateSasExpanderUpdateRequest(18244),
    fsmStFailMgmtControllerActivateSasExpanderWaitForActivation(18245),
    fsmStFailMgmtControllerActivateLocalDiskPollActivateStatus(18246),
    fsmStFailStorageLocalDiskUpdateLocalDiskUpdate(18247),
    fsmStFailMgmtControllerUpdateUCSManagerSPStart(18259),
    fsmStFailComputePhysicalDiagWaitForDebug(18260),
    fsmStFailComputePhysicalCimcSecurityConfigKmipSaveCert(18261),
    fsmStFailSwPortDiscoverDeployEnablePort(18290),
    fsmStFailPolicyPolicyScopeContReportPolicyFailFsmReportError(18293),
    fsmStFailPolicyRequestorResolveFromCentralResolveFromPolicyMgr(18294),
    fsmStFailFabricReservedVlanDeployWaitForUserAck(18342),
    fsmStFailMgmtControllerKvmCertResetCimc(18352),
    fsmStFailEquipmentChassisFwUpgradeDownloadImages(18353),
    fsmRmtErrEquipmentChassisRemoveChassisDecomission(77847),
    fsmRmtErrEquipmentLocatorLedSetLocatorLedExecute(77848),
    fsmRmtErrMgmtControllerExtMgmtIfConfigSecondary(77958),
    fsmRmtErrFabricComputeSlotEpIdentifyExecutePeer(77959),
    fsmRmtErrComputeBladeDiscoverSerialDebugDisconnect(77960),
    fsmRmtErrEquipmentChassisPsuPolicyConfigExecute(77973),
    fsmRmtErrAdaptorHostFcIfResetFcPersBindingExecutePeer(77974),
    fsmRmtErrFabricLanCloudSwitchModeWaitForUserAck(77979),
    fsmRmtErrVnicProfileSetDeployPeer(77990),
    fsmRmtErrCommSvcEpUpdateSvcEpSetEpPeer(78016),
    fsmRmtErrCommSvcEpRestartWebSvcPeer(78017),
    fsmRmtErrAaaEpUpdateEpSetEpPeer(78019),
    fsmRmtErrAaaRealmUpdateRealmSetRealmPeer(78020),
    fsmRmtErrAaaUserEpUpdateUserEpSetUserPeer(78021),
    fsmRmtErrPkiEpUpdateEpSetKeyRingPeer(78022),
    fsmRmtErrSysfileMutationSingleExecute(78040),
    fsmRmtErrSysfileMutationGlobalPeer(78041),
    fsmRmtErrSysdebugManualCoreFileExportTargetExportExecute(78044),
    fsmRmtErrSysdebugAutoCoreFileExportTargetConfigurePeer(78045),
    fsmRmtErrSysdebugLogControlEpLogControlPersistPeer(78046),
    fsmRmtErrSwAccessDomainDeployUpdateConnectivity(78074),
    fsmRmtErrSwEthLanBorderDeployUpdateVlanGroups(78075),
    fsmRmtErrSwFcSanBorderDeployUpdateConnectivity(78076),
    fsmRmtErrSwUtilityDomainDeployUpdateConnectivity(78077),
    fsmRmtErrSyntheticFsObjCreateCreateRemote(78081),
    fsmRmtErrFirmwareDownloaderDownloadUnpackLocal(78090),
    fsmRmtErrFirmwareImageDeleteRemote(78091),
    fsmRmtErrMgmtControllerUpdateSwitchVerifyRemote(78093),
    fsmRmtErrMgmtControllerUpdateIOMUpdateRequest(78094),
    fsmRmtErrMgmtControllerActivateIOMReset(78095),
    fsmRmtErrMgmtControllerUpdateBMCUpdateRequest(78096),
    fsmRmtErrMgmtControllerActivateBMCReset(78097),
    fsmRmtErrCallhomeEpConfigCallhomeSetPeer(78110),
    fsmRmtErrMgmtIfSwMgmtOobIfConfigSwitch(78113),
    fsmRmtErrMgmtIfSwMgmtInbandIfConfigSwitch(78114),
    fsmRmtErrMgmtIfVirtualIfConfigRemote(78119),
    fsmRmtErrMgmtIfEnableVipLocal(78120),
    fsmRmtErrMgmtIfDisableVipPeer(78121),
    fsmRmtErrMgmtIfEnableHALocal(78122),
    fsmRmtErrMgmtBackupBackupUpload(78123),
    fsmRmtErrMgmtImporterImportReportResults(78124),
    fsmRmtErrStatsCollectionPolicyUpdateEpSetEpB(78182),
    fsmRmtErrQosclassDefinitionConfigGlobalQoSWaitForUserAck(78185),
    fsmRmtErrEpqosDefinitionDeployPeer(78189),
    fsmRmtErrEpqosDefinitionDelTaskRemovePeer(78190),
    fsmRmtErrEquipmentIOCardResetCmcExecute(78243),
    fsmRmtErrMgmtControllerUpdateUCSManagerStart(78255),
    fsmRmtErrMgmtControllerSysConfigSecondary(78263),
    fsmRmtErrAdaptorExtEthIfPathResetEnable(78292),
    fsmRmtErrAdaptorHostEthIfCircuitResetEnableB(78297),
    fsmRmtErrAdaptorHostFcIfCircuitResetEnableB(78298),
    fsmRmtErrExtvmmProviderConfigSetPeer(78319),
    fsmRmtErrExtvmmKeyStoreCertInstallSetPeer(78320),
    fsmRmtErrExtvmmSwitchDelTaskRemoveProviderRemoveLocal(78321),
    fsmRmtErrExtvmmMasterExtKeyConfigSetPeer(78338),
    fsmRmtErrCapabilityUpdaterUpdaterUnpackLocal(78344),
    fsmRmtErrFirmwareDistributableDeleteRemote(78346),
    fsmRmtErrCapabilityCatalogueDeployCatalogueFinalize(78371),
    fsmRmtErrEquipmentFexRemoveFexDecomission(78382),
    fsmRmtErrEquipmentLocatorLedSetFeLocatorLedExecute(78383),
    fsmRmtErrEquipmentChassisPowerCapWait(78384),
    fsmRmtErrEquipmentIOCardMuxOfflineCleanupEntries(78385),
    fsmRmtErrComputePhysicalAssociateWaitForIBMCFwUpdate(78413),
    fsmRmtErrComputePhysicalDisassociateSerialDebugPnuOSDisconnect(78414),
    fsmRmtErrComputePhysicalPowerCapConfig(78415),
    fsmRmtErrComputePhysicalDecommissionUnconfigExtMgmtRules(78416),
    fsmRmtErrComputePhysicalSoftShutdownExecute(78417),
    fsmRmtErrComputePhysicalHardShutdownExecute(78418),
    fsmRmtErrComputePhysicalTurnupPowerDeployWait(78419),
    fsmRmtErrComputePhysicalPowercycleSanitize(78420),
    fsmRmtErrComputePhysicalHardresetSanitize(78421),
    fsmRmtErrComputePhysicalSoftresetSanitize(78422),
    fsmRmtErrComputePhysicalSwConnUpdB(78423),
    fsmRmtErrComputePhysicalBiosRecoveryWait(78424),
    fsmRmtErrComputePhysicalCmosResetSanitize(78426),
    fsmRmtErrComputePhysicalResetBmcExecute(78427),
    fsmRmtErrEquipmentIOCardResetIomExecute(78428),
    fsmRmtErrComputeRackUnitDiscoverWaitForConnReady(78434),
    fsmRmtErrLsServerConfigureCheckAssignedIdentifiersForDup(78435),
    fsmRmtErrSwEthMonDeployUpdateEthMon(78440),
    fsmRmtErrSwFcMonDeployUpdateFcMon(78441),
    fsmRmtErrFabricSanCloudSwitchModeWaitForUserAck(78442),
    fsmRmtErrComputePhysicalUpdateExtUsersDeploy(78448),
    fsmRmtErrSysdebugTechSupportInitiateLocal(78452),
    fsmRmtErrSysdebugTechSupportDeleteTechSupFilePeer(78453),
    fsmRmtErrSysdebugTechSupportDownloadDeleteSub(78454),
    fsmRmtErrComputePhysicalUpdateAdaptorUpdateRequestPeer(78483),
    fsmRmtErrComputePhysicalActivateAdaptorReset(78484),
    fsmRmtErrCapabilityCatalogueActivateCatalogUnpackLocal(78485),
    fsmRmtErrCapabilityMgmtExtensionActivateMgmtExtUnpackLocal(78486),
    fsmRmtErrLicenseDownloaderDownloadValidateRemote(78490),
    fsmRmtErrLicenseFileInstallRemote(78491),
    fsmRmtErrLicenseFileClearRemote(78492),
    fsmRmtErrLicenseInstanceUpdateFlexlmRemote(78493),
    fsmRmtErrComputePhysicalConfigSoLExecute(78523),
    fsmRmtErrComputePhysicalUnconfigSoLExecute(78524),
    fsmRmtErrPortPIoInCompatSfpPresenceShutdown(78529),
    fsmRmtErrComputePhysicalDiagnosticInterruptExecute(78556),
    fsmRmtErrSysdebugCoreDownloadDeleteSub(78573),
    fsmRmtErrEquipmentChassisDynamicReallocationConfig(78574),
    fsmRmtErrComputePhysicalResetKvmExecute(78603),
    fsmRmtErrMgmtControllerOnlineSwConfigureConnPeer(78609),
    fsmRmtErrComputeRackUnitOfflineSwUnconfigurePeer(78610),
    fsmRmtErrEquipmentLocatorLedSetFiLocatorLedExecute(78627),
    fsmRmtErrFabricEpMgrConfigureWaitOnPhys(78654),
    fsmRmtErrVnicProfileSetDeployAliasPeer(78663),
    fsmRmtErrSwPhysConfPhysicalVerifyPhysConfig(78679),
    fsmRmtErrExtvmmEpClusterRoleSetPeer(78694),
    fsmRmtErrVmLifeCyclePolicyConfigPeer(78699),
    fsmRmtErrEquipmentBeaconLedIlluminateExecuteB(78702),
    fsmRmtErrEtherServerIntFIoConfigSpeedConfigure(78711),
    fsmRmtErrComputePhysicalUpdateBIOSUpdateRequest(78721),
    fsmRmtErrComputePhysicalActivateBIOSUpdateTokens(78722),
    fsmRmtErrIdentIdentRequestUpdateIdentExecute(78752),
    fsmRmtErrIdentMetaSystemSyncPing(78753),
    fsmRmtErrComputePhysicalResetIpmiExecute(78766),
    fsmRmtErrComputePhysicalFwUpgradeWaitForIBMCFwUpdate(78767),
    fsmRmtErrComputeRackUnitAdapterResetSanitize(78768),
    fsmRmtErrPortPIoInCompatSfpReplacedEnablePort(78798),
    fsmRmtErrExtpolEpRegisterFsmExecute(78799),
    fsmRmtErrExtpolRegistryCrossDomainConfigSetPeer(78800),
    fsmRmtErrExtpolRegistryCrossDomainDeleteSetPeer(78801),
    fsmRmtErrNfsMountInstMountVerifyRegistration(78817),
    fsmRmtErrNfsMountInstUnmountUnmountPeer(78818),
    fsmRmtErrNfsMountDefReportNfsMountSuspendReport(78819),
    fsmRmtErrStorageSystemSyncExecute(78835),
    fsmRmtErrFirmwareSystemDeployDownloadImages(78848),
    fsmRmtErrFirmwareSystemApplyCatalogPackResolveImages(78849),
    fsmRmtErrComputeServerDiscPolicyResolveScrubPolicyResolve(78866),
    fsmRmtErrSwFcSanBorderActivateZoneSetVerifyUserZoneConfig(78879),
    fsmRmtErrExtpolEpRepairCertVerifyGuid(78886),
    fsmRmtErrPolicyControlEpOperateResolve(78887),
    fsmRmtErrPolicyPolicyScopeReleasePolicyFsmRelease(78888),
    fsmRmtErrPolicyPolicyScopeReleaseOperationFsmRelease(78889),
    fsmRmtErrPolicyPolicyScopeReleaseStorageFsmRelease(78890),
    fsmRmtErrPolicyPolicyScopeResolveManyPolicyFsmResolveMany(78891),
    fsmRmtErrPolicyPolicyScopeResolveManyOperationFsmResolveMany(78892),
    fsmRmtErrPolicyPolicyScopeResolveManyStorageFsmResolveMany(78893),
    fsmRmtErrPolicyPolicyScopeReleaseManyPolicyFsmReleaseMany(78894),
    fsmRmtErrPolicyPolicyScopeReleaseManyOperationFsmReleaseMany(78895),
    fsmRmtErrPolicyPolicyScopeReleaseManyStorageFsmReleaseMany(78896),
    fsmRmtErrPolicyPolicyScopeResolveAllPolicyFsmResolveAll(78897),
    fsmRmtErrPolicyPolicyScopeResolveAllOperationFsmResolveAll(78898),
    fsmRmtErrPolicyPolicyScopeResolveAllStorageFsmResolveAll(78899),
    fsmRmtErrPolicyPolicyScopeReleaseAllPolicyFsmReleaseAll(78900),
    fsmRmtErrPolicyPolicyScopeReleaseAllOperationFsmReleaseAll(78901),
    fsmRmtErrPolicyPolicyScopeReleaseAllStorageFsmReleaseAll(78902),
    fsmRmtErrMgmtExportPolicyReportConfigCopyReport(78924),
    fsmRmtErrExtpolProviderReportConfigImportReport(78925),
    fsmRmtErrObserveObservedResolvePolicyFsmExecute(78931),
    fsmRmtErrObserveObservedResolveResourceFsmExecute(78932),
    fsmRmtErrObserveObservedResolveVMFsmExecute(78933),
    fsmRmtErrObserveObservedResolveControllerFsmExecute(78934),
    fsmRmtErrMgmtControllerRegistryConfigRemovePeer(78939),
    fsmRmtErrGmetaHolderInventoryReportStorageInventory(79048),
    fsmRmtErrComputePhysicalCimcSessionDeleteExecute(79049),
    fsmRmtErrPolicyControlledTypeOperateResolveAll(79052),
    fsmRmtErrFabricVnetEpSyncEpPushVnetEpDeletionSync(79059),
    fsmRmtErrSwEthLanFlowMonDeployUpdateEthFlowMon(79079),
    fsmRmtErrMgmtIPv6IfAddrSwMgmtOobIpv6IfConfigSwitch(79105),
    fsmRmtErrComputePhysicalUpdateBoardControllerUpdateRequest(79107),
    fsmRmtErrExtvmmNetworkSetsDeployPeer(79143),
    fsmRmtErrComputePhysicalConfigBoardConfigMemoryPolicy(79147),
    fsmRmtErrComputePhysicalResetMemoryErrorsExecute(79148),
    fsmRmtErrMgmtControllerExtMgmtInterfaceConfigStandbyCMCVlanCfg(79154),
    fsmRmtErrComputeRackUnitCreateDhcpEntryExecutePeer(79155),
    fsmRmtErrComputePhysicalServiceInfraDeploySwConfigPeer(79156),
    fsmRmtErrComputePhysicalServiceInfraWithdrawSwUnConfigPeer(79157),
    fsmRmtErrSysdebugLogExportPolicyConfigurePeer(79195),
    fsmRmtErrComputePhysicalFlashControllerUpdateFlashLife(79197),
    fsmRmtErrStorageFlexFlashControllerMOpsResetReset(79258),
    fsmRmtErrStorageFlexFlashControllerMOpsFormatFormat(79259),
    fsmRmtErrStorageFlexFlashControllerMOpsPairPair(79260),
    fsmRmtErrComputePhysicalEnableCimcSecureBootUpdateRequest(79266),
    fsmRmtErrIdentMetaSystemUcscUnivSyncExecute(79290),
    fsmRmtErrMgmtControllerLockConfigPowerButtonLockConfig(79373),
    fsmRmtErrMgmtControllerPowerBudgetReclaimConfigPowerOffWait(79374),
    fsmRmtErrComputePhysicalOobStorageAdminConfigTearDownVMediaPeer(79375),
    fsmRmtErrEquipmentIOCardBaseFePresenceIdentify(79380),
    fsmRmtErrEquipmentIOCardBaseFeConnEnableChassis(79381),
    fsmRmtErrEquipmentPsuUpdatePSUUpdateRequest(79427),
    fsmRmtErrMgmtControllerUpdateCMCUpdateRequest(79452),
    fsmRmtErrMgmtControllerActivateCMCReset(79453),
    fsmRmtErrMgmtControllerUpdateAdaptorUpdateRequestPeer(79454),
    fsmRmtErrMgmtControllerActivateAdaptorServersPowerOffCompletion(79455),
    fsmRmtErrMgmtControllerUpdateRaidControllerUpdateRequest(79456),
    fsmRmtErrMgmtControllerUpdateBoardControllerUpdateRequest(79457),
    fsmRmtErrFabricCartridgeSlotEpIdentifyExecutePeer(79464),
    fsmRmtErrFabricComputeMSlotEpIdentifyExecutePeer(79465),
    fsmRmtErrEquipmentChassisOobStorageAdminCfgOobStorageInventory(79466),
    fsmRmtErrComputeServerUnitDiscoverUnconfigExtMgmtRules(79472),
    fsmRmtErrMgmtIfFaPresenceIdentify(79473),
    fsmRmtErrMgmtIfFaConnSharedIOModuleInventory(79474),
    fsmRmtErrEquipmentIOCardEvacuateExecute(79485),
    fsmRmtErrEquipmentIOCardResetEvacuateExecute(79486),
    fsmRmtErrComputePhysicalClearTPMUnconfigVmedia(79491),
    fsmRmtErrEquipmentIOCardResetPeerCmcExecute(79542),
    fsmRmtErrSwExtUtilityConfPortBreakoutVerifyBreakoutConfig(79564),
    fsmRmtErrEquipmentSwitchIOCardEvacuateExecute(79586),
    fsmRmtErrEquipmentSwitchIOCardResetEvacuateExecute(79587),
    fsmRmtErrMorefImportRootApplyMoRefsDeleteAllMoRefs(79601),
    fsmRmtErrStorageEnclosureRemoveEnclosureValidateRemoval(79609),
    fsmRmtErrMgmtControllerPowerCapConfig(79624),
    fsmRmtErrEquipmentSystemIOControllerResetCmcExecute(79625),
    fsmRmtErrComputePhysicalDiskZoningInventoryStorageInventory(79626),
    fsmRmtErrEquipmentChassisProfileConfigureWaitForMaintPermission(79646),
    fsmRmtErrEquipmentChassisAssociateDownloadImages(79647),
    fsmRmtErrEquipmentChassisDisassociateComplete(79648),
    fsmRmtErrEtherServerIntFIoConfigConfigure(79677),
    fsmRmtErrMgmtControllerEnableSecureBootUpdateRequest(79679),
    fsmRmtErrMgmtControllerUpdateColusaCMCUpdateRequest(79680),
    fsmRmtErrMgmtControllerActivateColusaCMCReset(79681),
    fsmRmtErrEquipmentChassisChassisUpgradeWaitForPowerOff(79682),
    fsmRmtErrMgmtControllerUpdateColusaBoardControllerUpdateRequest(79683),
    fsmRmtErrMgmtControllerUpdateSasExpanderUpdateRequest(79684),
    fsmRmtErrMgmtControllerActivateSasExpanderWaitForActivation(79685),
    fsmRmtErrMgmtControllerActivateLocalDiskPollActivateStatus(79686),
    fsmRmtErrStorageLocalDiskUpdateLocalDiskUpdate(79687),
    fsmRmtErrMgmtControllerUpdateUCSManagerSPStart(79699),
    fsmRmtErrComputePhysicalDiagWaitForDebug(79700),
    fsmRmtErrComputePhysicalCimcSecurityConfigKmipSaveCert(79701),
    fsmRmtErrSwPortDiscoverDeployEnablePort(79730),
    fsmRmtErrPolicyPolicyScopeContReportPolicyFailFsmReportError(79733),
    fsmRmtErrPolicyRequestorResolveFromCentralResolveFromPolicyMgr(79734),
    fsmRmtErrFabricReservedVlanDeployWaitForUserAck(79782),
    fsmRmtErrMgmtControllerKvmCertResetCimc(79792),
    fsmRmtErrEquipmentChassisFwUpgradeDownloadImages(79793),
    fsmFailEquipmentChassisRemoveChassis(999447),
    fsmFailEquipmentLocatorLedSetLocatorLed(999448),
    fsmFailMgmtControllerExtMgmtIfConfig(999558),
    fsmFailFabricComputeSlotEpIdentify(999559),
    fsmFailComputeBladeDiscover(999560),
    fsmFailEquipmentChassisPsuPolicyConfig(999573),
    fsmFailAdaptorHostFcIfResetFcPersBinding(999574),
    fsmFailFabricLanCloudSwitchMode(999579),
    fsmFailVnicProfileSetDeploy(999590),
    fsmFailCommSvcEpUpdateSvcEp(999616),
    fsmFailCommSvcEpRestartWebSvc(999617),
    fsmFailAaaEpUpdateEp(999619),
    fsmFailAaaRealmUpdateRealm(999620),
    fsmFailAaaUserEpUpdateUserEp(999621),
    fsmFailPkiEpUpdateEp(999622),
    fsmFailSysfileMutationSingle(999640),
    fsmFailSysfileMutationGlobal(999641),
    fsmFailSysdebugManualCoreFileExportTargetExport(999644),
    fsmFailSysdebugAutoCoreFileExportTargetConfigure(999645),
    fsmFailSysdebugLogControlEpLogControlPersist(999646),
    fsmFailSwAccessDomainDeploy(999674),
    fsmFailSwEthLanBorderDeploy(999675),
    fsmFailSwFcSanBorderDeploy(999676),
    fsmFailSwUtilityDomainDeploy(999677),
    fsmFailSyntheticFsObjCreate(999681),
    fsmFailFirmwareDownloaderDownload(999690),
    fsmFailFirmwareImageDelete(999691),
    fsmFailMgmtControllerUpdateSwitch(999693),
    fsmFailMgmtControllerUpdateIOM(999694),
    fsmFailMgmtControllerActivateIOM(999695),
    fsmFailMgmtControllerUpdateBMC(999696),
    fsmFailMgmtControllerActivateBMC(999697),
    fsmFailCallhomeEpConfigCallhome(999710),
    fsmFailMgmtIfSwMgmtOobIfConfig(999713),
    fsmFailMgmtIfSwMgmtInbandIfConfig(999714),
    fsmFailMgmtIfVirtualIfConfig(999719),
    fsmFailMgmtIfEnableVip(999720),
    fsmFailMgmtIfDisableVip(999721),
    fsmFailMgmtIfEnableHA(999722),
    fsmFailMgmtBackupBackup(999723),
    fsmFailMgmtImporterImport(999724),
    fsmFailStatsCollectionPolicyUpdateEp(999782),
    fsmFailQosclassDefinitionConfigGlobalQoS(999785),
    fsmFailEpqosDefinitionDeploy(999789),
    fsmFailEpqosDefinitionDelTaskRemove(999790),
    fsmFailEquipmentIOCardResetCmc(999843),
    fsmFailMgmtControllerUpdateUCSManager(999855),
    fsmFailMgmtControllerSysConfig(999863),
    fsmFailAdaptorExtEthIfPathReset(999892),
    fsmFailAdaptorHostEthIfCircuitReset(999897),
    fsmFailAdaptorHostFcIfCircuitReset(999898),
    fsmFailExtvmmProviderConfig(999919),
    fsmFailExtvmmKeyStoreCertInstall(999920),
    fsmFailExtvmmSwitchDelTaskRemoveProvider(999921),
    fsmFailExtvmmMasterExtKeyConfig(999938),
    fsmFailCapabilityUpdaterUpdater(999944),
    fsmFailFirmwareDistributableDelete(999946),
    fsmFailCapabilityCatalogueDeployCatalogue(999971),
    fsmFailEquipmentFexRemoveFex(999982),
    fsmFailEquipmentLocatorLedSetFeLocatorLed(999983),
    fsmFailEquipmentChassisPowerCap(999984),
    fsmFailEquipmentIOCardMuxOffline(999985),
    fsmFailComputePhysicalAssociate(1000013),
    fsmFailComputePhysicalDisassociate(1000014),
    fsmFailComputePhysicalPowerCap(1000015),
    fsmFailComputePhysicalDecommission(1000016),
    fsmFailComputePhysicalSoftShutdown(1000017),
    fsmFailComputePhysicalHardShutdown(1000018),
    fsmFailComputePhysicalTurnup(1000019),
    fsmFailComputePhysicalPowercycle(1000020),
    fsmFailComputePhysicalHardreset(1000021),
    fsmFailComputePhysicalSoftreset(1000022),
    fsmFailComputePhysicalSwConnUpd(1000023),
    fsmFailComputePhysicalBiosRecovery(1000024),
    fsmFailComputePhysicalCmosReset(1000026),
    fsmFailComputePhysicalResetBmc(1000027),
    fsmFailEquipmentIOCardResetIom(1000028),
    fsmFailComputeRackUnitDiscover(1000034),
    fsmFailLsServerConfigure(1000035),
    fsmFailSwEthMonDeploy(1000040),
    fsmFailSwFcMonDeploy(1000041),
    fsmFailFabricSanCloudSwitchMode(1000042),
    fsmFailComputePhysicalUpdateExtUsers(1000048),
    fsmFailSysdebugTechSupportInitiate(1000052),
    fsmFailSysdebugTechSupportDeleteTechSupFile(1000053),
    fsmFailSysdebugTechSupportDownload(1000054),
    fsmFailComputePhysicalUpdateAdaptor(1000083),
    fsmFailComputePhysicalActivateAdaptor(1000084),
    fsmFailCapabilityCatalogueActivateCatalog(1000085),
    fsmFailCapabilityMgmtExtensionActivateMgmtExt(1000086),
    fsmFailLicenseDownloaderDownload(1000090),
    fsmFailLicenseFileInstall(1000091),
    fsmFailLicenseFileClear(1000092),
    fsmFailLicenseInstanceUpdateFlexlm(1000093),
    fsmFailComputePhysicalConfigSoL(1000123),
    fsmFailComputePhysicalUnconfigSoL(1000124),
    fsmFailPortPIoInCompatSfpPresence(1000129),
    fsmFailComputePhysicalDiagnosticInterrupt(1000156),
    fsmFailSysdebugCoreDownload(1000173),
    fsmFailEquipmentChassisDynamicReallocation(1000174),
    fsmFailComputePhysicalResetKvm(1000203),
    fsmFailMgmtControllerOnline(1000209),
    fsmFailComputeRackUnitOffline(1000210),
    fsmFailEquipmentLocatorLedSetFiLocatorLed(1000227),
    fsmFailFabricEpMgrConfigure(1000254),
    fsmFailVnicProfileSetDeployAlias(1000263),
    fsmFailSwPhysConfPhysical(1000279),
    fsmFailExtvmmEpClusterRole(1000294),
    fsmFailVmLifeCyclePolicyConfig(1000299),
    fsmFailEquipmentBeaconLedIlluminate(1000302),
    fsmFailEtherServerIntFIoConfigSpeed(1000311),
    fsmFailComputePhysicalUpdateBIOS(1000321),
    fsmFailComputePhysicalActivateBIOS(1000322),
    fsmFailIdentIdentRequestUpdateIdent(1000352),
    fsmFailIdentMetaSystemSync(1000353),
    fsmFailComputePhysicalResetIpmi(1000366),
    fsmFailComputePhysicalFwUpgrade(1000367),
    fsmFailComputeRackUnitAdapterReset(1000368),
    fsmFailPortPIoInCompatSfpReplaced(1000398),
    fsmFailExtpolEpRegisterFsm(1000399),
    fsmFailExtpolRegistryCrossDomainConfig(1000400),
    fsmFailExtpolRegistryCrossDomainDelete(1000401),
    fsmFailNfsMountInstMount(1000417),
    fsmFailNfsMountInstUnmount(1000418),
    fsmFailNfsMountDefReportNfsMountSuspend(1000419),
    fsmFailStorageSystemSync(1000435),
    fsmFailFirmwareSystemDeploy(1000448),
    fsmFailFirmwareSystemApplyCatalogPack(1000449),
    fsmFailComputeServerDiscPolicyResolveScrubPolicy(1000466),
    fsmFailSwFcSanBorderActivateZoneSet(1000479),
    fsmFailExtpolEpRepairCert(1000486),
    fsmFailPolicyControlEpOperate(1000487),
    fsmFailPolicyPolicyScopeReleasePolicyFsm(1000488),
    fsmFailPolicyPolicyScopeReleaseOperationFsm(1000489),
    fsmFailPolicyPolicyScopeReleaseStorageFsm(1000490),
    fsmFailPolicyPolicyScopeResolveManyPolicyFsm(1000491),
    fsmFailPolicyPolicyScopeResolveManyOperationFsm(1000492),
    fsmFailPolicyPolicyScopeResolveManyStorageFsm(1000493),
    fsmFailPolicyPolicyScopeReleaseManyPolicyFsm(1000494),
    fsmFailPolicyPolicyScopeReleaseManyOperationFsm(1000495),
    fsmFailPolicyPolicyScopeReleaseManyStorageFsm(1000496),
    fsmFailPolicyPolicyScopeResolveAllPolicyFsm(1000497),
    fsmFailPolicyPolicyScopeResolveAllOperationFsm(1000498),
    fsmFailPolicyPolicyScopeResolveAllStorageFsm(1000499),
    fsmFailPolicyPolicyScopeReleaseAllPolicyFsm(1000500),
    fsmFailPolicyPolicyScopeReleaseAllOperationFsm(1000501),
    fsmFailPolicyPolicyScopeReleaseAllStorageFsm(1000502),
    fsmFailMgmtExportPolicyReportConfigCopy(1000524),
    fsmFailExtpolProviderReportConfigImport(1000525),
    fsmFailObserveObservedResolvePolicyFsm(1000531),
    fsmFailObserveObservedResolveResourceFsm(1000532),
    fsmFailObserveObservedResolveVMFsm(1000533),
    fsmFailObserveObservedResolveControllerFsm(1000534),
    fsmFailMgmtControllerRegistryConfig(1000539),
    fsmFailGmetaHolderInventory(1000648),
    fsmFailComputePhysicalCimcSessionDelete(1000649),
    fsmFailPolicyControlledTypeOperate(1000652),
    fsmFailFabricVnetEpSyncEpPushVnetEpDeletion(1000659),
    fsmFailSwEthLanFlowMonDeploy(1000679),
    fsmFailMgmtIPv6IfAddrSwMgmtOobIpv6IfConfig(1000705),
    fsmFailComputePhysicalUpdateBoardController(1000707),
    fsmFailExtvmmNetworkSetsDeploy(1000743),
    fsmFailComputePhysicalConfigBoard(1000747),
    fsmFailComputePhysicalResetMemoryErrors(1000748),
    fsmFailMgmtControllerExtMgmtInterfaceConfig(1000754),
    fsmFailComputeRackUnitCreateDhcpEntry(1000755),
    fsmFailComputePhysicalServiceInfraDeploy(1000756),
    fsmFailComputePhysicalServiceInfraWithdraw(1000757),
    fsmFailSysdebugLogExportPolicyConfigure(1000795),
    fsmFailComputePhysicalFlashController(1000797),
    fsmFailStorageFlexFlashControllerMOpsReset(1000858),
    fsmFailStorageFlexFlashControllerMOpsFormat(1000859),
    fsmFailStorageFlexFlashControllerMOpsPair(1000860),
    fsmFailComputePhysicalEnableCimcSecureBoot(1000866),
    fsmFailIdentMetaSystemUcscUnivSync(1000890),
    fsmFailMgmtControllerLockConfig(1000973),
    fsmFailMgmtControllerPowerBudgetReclaimConfig(1000974),
    fsmFailComputePhysicalOobStorageAdminConfig(1000975),
    fsmFailEquipmentIOCardBaseFePresence(1000980),
    fsmFailEquipmentIOCardBaseFeConn(1000981),
    fsmFailEquipmentPsuUpdatePSU(1001027),
    fsmFailMgmtControllerUpdateCMC(1001052),
    fsmFailMgmtControllerActivateCMC(1001053),
    fsmFailMgmtControllerUpdateAdaptor(1001054),
    fsmFailMgmtControllerActivateAdaptor(1001055),
    fsmFailMgmtControllerUpdateRaidController(1001056),
    fsmFailMgmtControllerUpdateBoardController(1001057),
    fsmFailFabricCartridgeSlotEpIdentify(1001064),
    fsmFailFabricComputeMSlotEpIdentify(1001065),
    fsmFailEquipmentChassisOobStorageAdminCfg(1001066),
    fsmFailComputeServerUnitDiscover(1001072),
    fsmFailMgmtIfFaPresence(1001073),
    fsmFailMgmtIfFaConn(1001074),
    fsmFailEquipmentIOCardEvacuate(1001085),
    fsmFailEquipmentIOCardResetEvacuate(1001086),
    fsmFailComputePhysicalClearTPM(1001091),
    fsmFailEquipmentIOCardResetPeerCmc(1001142),
    fsmFailSwExtUtilityConfPortBreakout(1001164),
    fsmFailEquipmentSwitchIOCardEvacuate(1001186),
    fsmFailEquipmentSwitchIOCardResetEvacuate(1001187),
    fsmFailMorefImportRootApplyMoRefs(1001201),
    fsmFailStorageEnclosureRemoveEnclosure(1001209),
    fsmFailMgmtControllerPowerCap(1001224),
    fsmFailEquipmentSystemIOControllerResetCmc(1001225),
    fsmFailComputePhysicalDiskZoningInventory(1001226),
    fsmFailEquipmentChassisProfileConfigure(1001246),
    fsmFailEquipmentChassisAssociate(1001247),
    fsmFailEquipmentChassisDisassociate(1001248),
    fsmFailEtherServerIntFIoConfig(1001277),
    fsmFailMgmtControllerEnableSecureBoot(1001279),
    fsmFailMgmtControllerUpdateColusaCMC(1001280),
    fsmFailMgmtControllerActivateColusaCMC(1001281),
    fsmFailEquipmentChassisChassisUpgrade(1001282),
    fsmFailMgmtControllerUpdateColusaBoardController(1001283),
    fsmFailMgmtControllerUpdateSasExpander(1001284),
    fsmFailMgmtControllerActivateSasExpander(1001285),
    fsmFailMgmtControllerActivateLocalDisk(1001286),
    fsmFailStorageLocalDiskUpdateLocalDisk(1001287),
    fsmFailMgmtControllerUpdateUCSManagerSP(1001299),
    fsmFailComputePhysicalDiag(1001300),
    fsmFailComputePhysicalCimcSecurityConfig(1001301),
    fsmFailSwPortDiscoverDeploy(1001330),
    fsmFailPolicyPolicyScopeContReportPolicyFailFsm(1001333),
    fsmFailPolicyRequestorResolveFromCentral(1001334),
    fsmFailFabricReservedVlanDeploy(1001382),
    fsmFailMgmtControllerKvmCert(1001392),
    fsmFailEquipmentChassisFwUpgrade(1001393)
  }

CucsFaultType  ::= TEXTUAL-CONVENTION
        STATUS       current
        DESCRIPTION
       "A code used to categorize UCS faults"
        SYNTAX INTEGER {
    generic(0),
    configuration(1),
    fsm(2),
    server(3),
    sysdebug(4),
    network(5),
    equipment(6),
    environmental(7),
    security(8),
    management(9),
    chassisProfile(10),
    connectivity(11),
    operational(12)
  }

CucsFaultProbableCause  ::= TEXTUAL-CONVENTION
        STATUS       current
        DESCRIPTION
       "A code used to identify the probable cause of a fault"
        SYNTAX INTEGER {
    fsmFailed(3),
    shutdownFailed(4),
    checkLicenseFailed(5),
    identifyFailed(6),
    configureSwMgmtEndPointFailed(7),
    configureVifNsFailed(8),
    configureEndPointFailed(9),
    discoverChassisFailed(10),
    enableChassisFailed(11),
    decomissionFailed(12),
    unIdentifyLocalFailed(13),
    cleanupEntriesFailed(14),
    waitFailed(15),
    disableEndPointFailed(16),
    unIdentifyPeerFailed(17),
    executeFailed(18),
    configFailed(19),
    bmcConfigureConnLocalFailed(20),
    swConfigureConnLocalFailed(21),
    bmcConfigureConnPeerFailed(22),
    swConfigureConnPeerFailed(23),
    bmcPresenceFailed(24),
    bmcInventoryFailed(25),
    preSanitizeFailed(26),
    sanitizeFailed(27),
    configUserAccessFailed(28),
    configDiscoveryModeFailed(29),
    swUnconfigPortNivLocalFailed(30),
    swUnconfigPortNivPeerFailed(31),
    swConfigPnuoslocalFailed(32),
    swConfigPnuospeerFailed(33),
    bmcPreconfigPnuoslocalFailed(34),
    bmcPreconfigPnuospeerFailed(35),
    bmcConfigPnuosFailed(36),
    bootPnuosFailed(37),
    bootWaitFailed(38),
    biosPostCompletionFailed(39),
    readSmbiosFailed(40),
    hagConnectFailed(41),
    pnuosidentFailed(42),
    pnuospolicyFailed(43),
    pnuosinventoryFailed(44),
    pnuosscrubFailed(45),
    pnuosconnectivityFailed(46),
    waitForConnReadyFailed(47),
    pnuosconnStatusFailed(48),
    swPnuosconnectivityLocalFailed(49),
    swPnuosconnectivityPeerFailed(50),
    pnuosselfTestFailed(51),
    bmcUnconfigPnuosFailed(52),
    hagDisconnectFailed(53),
    nicInventoryLocalFailed(56),
    nicInventoryPeerFailed(57),
    configNivModeFailed(58),
    bmcShutdownDiscoveredFailed(59),
    handlePoolingFailed(60),
    cleanupLocalFailed(63),
    cleanupPeerFailed(64),
    swUnconfigureLocalFailed(65),
    swUnconfigurePeerFailed(66),
    configFeLocalFailed(67),
    configFePeerFailed(68),
    bladePowerOnFailed(69),
    nicPresenceLocalFailed(70),
    nicPresencePeerFailed(71),
    swConfigLocalFailed(74),
    swConfigPeerFailed(75),
    nicConfigLocalFailed(76),
    nicConfigPeerFailed(77),
    stopvmediaLocalFailed(78),
    stopvmediaPeerFailed(79),
    bladeBootWaitFailed(83),
    bladeReadSmbiosFailed(84),
    evaluateStatusFailed(120),
    primaryFailed(121),
    secondaryFailed(122),
    executeLocalFailed(123),
    executePeerFailed(124),
    nicConfigPnuoslocalFailed(125),
    nicConfigPnuospeerFailed(126),
    setupVmediaLocalFailed(127),
    setupVmediaPeerFailed(128),
    bladeBootPnuosFailed(129),
    nicUnconfigPnuoslocalFailed(130),
    nicUnconfigPnuospeerFailed(131),
    swUnconfigPnuoslocalFailed(132),
    swUnconfigPnuospeerFailed(133),
    teardownVmediaLocalFailed(134),
    teardownVmediaPeerFailed(135),
    updateibmcfwFailed(136),
    waitForibmcfwUpdateFailed(137),
    activateibmcfwFailed(138),
    resetibmcFailed(139),
    bladePowerOffFailed(140),
    updateBoardCtrlRequestFailed(141),
    pollBoardCtrlUpdateStatusFailed(142),
    powerOnFailed(143),
    updateAdaptorNwFwLocalFailed(144),
    updateAdaptorNwFwPeerFailed(145),
    waitForAdaptorNwFwUpdateLocalFailed(146),
    waitForAdaptorNwFwUpdatePeerFailed(147),
    activateAdaptorNwFwLocalFailed(148),
    activateAdaptorNwFwPeerFailed(149),
    hagPnuosconnectFailed(150),
    pnuosvalidateFailed(151),
    biosImgUpdateFailed(152),
    storageCtlrImgUpdateFailed(153),
    hbaImgUpdateFailed(154),
    nicImgUpdateFailed(155),
    localDiskFwUpdateFailed(156),
    pnuosconfigFailed(157),
    pnuoslocalDiskConfigFailed(158),
    pnuosunloadDriversFailed(159),
    swConfigHostoslocalFailed(160),
    swConfigHostospeerFailed(161),
    nicConfigHostoslocalFailed(162),
    nicConfigHostospeerFailed(163),
    hagPnuosdisconnectFailed(164),
    configSoLfailed(165),
    prepareForBootFailed(166),
    configUuidFailed(167),
    bootHostFailed(168),
    hagHostosconnectFailed(169),
    hostosidentFailed(170),
    hostospolicyFailed(171),
    hostosvalidateFailed(172),
    hostosconfigFailed(173),
    nicUnconfigHostoslocalFailed(174),
    nicUnconfigHostospeerFailed(175),
    swUnconfigHostoslocalFailed(176),
    swUnconfigHostospeerFailed(177),
    configBiosFailed(178),
    pnuosunconfigFailed(179),
    unconfigUuidFailed(180),
    unconfigBiosFailed(181),
    unconfigSoLfailed(182),
    aFailed(183),
    bFailed(184),
    startFailed(185),
    cleanupFailed(186),
    resetFailed(187),
    reconfigBiosFailed(188),
    applyTemplateFailed(190),
    applyIdentifiersFailed(191),
    applyPoliciesFailed(192),
    resolveBootConfigFailed(193),
    evaluateAssociationFailed(194),
    analyzeImpactFailed(195),
    waitForMaintPermissionFailed(196),
    waitForMaintWindowFailed(197),
    applyConfigFailed(198),
    mgmtifDown(199),
    updateEthMonFailed(200),
    updateFcMonFailed(201),
    serverMoved(202),
    serverIdentificationProblem(203),
    emptyPinGroup(205),
    membershipDown(206),
    vsanMisconfigured(207),
    incompatibleSpeed(208),
    configError(209),
    localFailed(211),
    peerFailed(212),
    configurationFailed(213),
    equipmentInoperable(214),
    thermalProblem(215),
    voltageProblem(216),
    capacityExceeded(217),
    equipmentDegraded(218),
    identityUnestablishable(219),
    setEpLocalFailed(220),
    setEpPeerFailed(221),
    propogateEpSettingsFailed(222),
    propogateEpTimeZoneSettingsLocalFailed(223),
    propogateEpTimeZoneSettingsPeerFailed(224),
    propogateEpTimeZoneSettingsToAdaptorsLocalFailed(225),
    propogateEpTimeZoneSettingsToAdaptorsPeerFailed(226),
    propogateEpTimeZoneSettingsToFexIomLocalFailed(227),
    propogateEpTimeZoneSettingsToFexIomPeerFailed(228),
    deployFailed(230),
    setRealmLocalFailed(231),
    setRealmPeerFailed(232),
    setUserLocalFailed(233),
    setUserPeerFailed(234),
    setKeyRingLocalFailed(235),
    setKeyRingPeerFailed(236),
    unidentifiableFru(237),
    equipmentMissing(238),
    connectivityProblem(239),
    linkDown(240),
    linkMisconnected(241),
    linkMissing(242),
    disableFailed(243),
    enableFailed(244),
    disableAfailed(245),
    enableAfailed(246),
    disableBfailed(247),
    enableBfailed(248),
    vifDown(249),
    tftpServerError(250),
    copySubFailed(251),
    copyPrimaryFailed(252),
    deleteSubFailed(253),
    deletePrimaryFailed(254),
    groupCapInsufficient(255),
    oldChassisComponentFirmware(256),
    oldFirmware(257),
    psuInsufficient(258),
    psuRedundancyFail(260),
    powerCapFail(261),
    powerConsumptionHitLimit(262),
    noAckFromBios(263),
    noCapFail(264),
    updateConnectivityFailed(265),
    createLocalFailed(266),
    createRemoteFailed(267),
    unpackLocalFailed(268),
    deleteLocalFailed(269),
    copyRemoteFailed(270),
    remoteFailed(271),
    updateLocalFailed(272),
    verifyLocalFailed(273),
    resetLocalFailed(274),
    updateRemoteFailed(275),
    verifyRemoteFailed(276),
    resetRemoteFailed(277),
    updateRequestFailed(278),
    pollUpdateStatusFailed(279),
    activateFailed(280),
    updateRequestLocalFailed(281),
    updateRequestPeerFailed(282),
    pollUpdateStatusPeerFailed(284),
    powerOffFailed(285),
    activateLocalFailed(286),
    activatePeerFailed(287),
    prepareForUpdateFailed(288),
    imageDeleted(289),
    imageUnusable(290),
    imageCannotBoot(291),
    applyFailed(292),
    rescanImagesFailed(293),
    applyCatalogFailed(294),
    syncBladeaglocalFailed(295),
    syncBladeagremoteFailed(296),
    syncNicaglocalFailed(297),
    syncNicagremoteFailed(298),
    syncPortaglocalFailed(299),
    syncPortagremoteFailed(300),
    syncHostagentaglocalFailed(301),
    syncHostagentagremoteFailed(302),
    deleteRemoteFailed(306),
    licenseGraceperiod10days(308),
    licenseGraceperiod30days(309),
    licenseGraceperiod60days(310),
    licenseGraceperiod90days(311),
    licenseGraceperiod119days(312),
    licenseGraceperiodExpired(313),
    licenseFileUninstallable(314),
    unsupportedTransceiver(317),
    interfaceFailed(318),
    operationalStateDown(319),
    cmcVifDown(320),
    setLocalFailed(321),
    setPeerFailed(322),
    switchFailed(323),
    limitReached(324),
    emptyPool(325),
    backupLocalFailed(328),
    downloadLocalFailed(330),
    reportResultsFailed(331),
    electionFailure(332),
    managementServicesFailure(333),
    managementServicesUnresponsive(334),
    haNotReady(335),
    versionIncompatible(336),
    logCapacity(338),
    fileTransferFailed(339),
    newLink(340),
    insufficientResources(342),
    insufficientlyEquipped(343),
    powerProblem(344),
    associationFailed(346),
    equipmentInaccessible(347),
    equipmentProblem(348),
    serverFailed(364),
    configurationFailure(365),
    maintenanceFailed(366),
    equipmentRemoved(367),
    serverInaccessible(368),
    assignmentFailed(369),
    unassociated(370),
    nonExistentScheduler(371),
    getVersionFailed(372),
    removeLocalFailed(373),
    setEpAfailed(374),
    setEpBfailed(375),
    bmcPreConfigPnuoslocalFailed(376),
    bmcPreConfigPnuospeerFailed(377),
    satelliteMisConnected(378),
    unexpectedNumberOfLinks(379),
    equipmentOffline(380),
    performanceProblem(381),
    firmwareUpgradeProblem(382),
    serialDebugPnuosdisconnectFailed(383),
    equipmentUnacknowledged(384),
    autoFirmwareUpgrade(385),
    equipmentDisconnected(386),
    cleanupcimcFailed(387),
    validateConfigurationFailed(393),
    applyPhysicalFailed(394),
    waitOnPhysFailed(395),
    vlanMisconfigured(401),
    interfaceMisconfigured(402),
    missingPrimaryVlan(403),
    pinningMismatch(404),
    pinningMisconfig(405),
    equipmentDisabled(406),
    portInventorySwAfailed(419),
    portInventorySwBfailed(420),
    configSwAfailed(421),
    configSwBfailed(422),
    verifyPhysConfigFailed(423),
    activationFailed(427),
    deviceSharedStorageError(438),
    haSshKeysMismatched(439),
    ucsmProcessFailure(440),
    executeAfailed(443),
    executeBfailed(444),
    powerDown(445),
    inventoryFailed(454),
    configureFailed(455),
    clearFailed(456),
    pollClearStatusFailed(457),
    pollActivateStatusFailed(458),
    updateTokensFailed(459),
    pnuoscatalogFailed(461),
    clearBiosUpdateFailed(462),
    pollClearBiosUpdateStatusFailed(463),
    updateBiosRequestFailed(464),
    pollBiosUpdateStatusFailed(465),
    activateBiosFailed(466),
    pollBiosActivateStatusFailed(467),
    fexUnsupported(468),
    invalidKeyringCertificate(469),
    invalidTrustpointCertChain(470),
    disassociationFailed(471),
    vifIdsMismatch(472),
    profileConfigIncorrect(473),
    pingFailed(474),
    inaccessibleVlanReferenced(476),
    referencedVlanUnresolvable(477),
    invalidVlanInTheAllowedVlanList(478),
    vlanConflictPermit(479),
    vlanPermitUnresolved(480),
    groupPermitUnresolved(481),
    checkPowerAvailabilityFailed(482),
    markAdapterForRebootFailed(483),
    deassertResetBypassFailed(484),
    verifyFcZoneConfigFailed(485),
    cleanupPortConfigLocalFailed(486),
    cleanupPortConfigPeerFailed(487),
    powerCycleFailed(488),
    enablePortFailed(489),
    resolveIdentifiersFailed(490),
    applyDefaultIdentifiersFailed(491),
    resolveDefaultIdentifiersFailed(492),
    resolvePoliciesFailed(493),
    resolveDistributableNamesFailed(494),
    resolveDistributableFailed(495),
    resolveImagesFailed(496),
    resolveScheduleFailed(497),
    provisionStorageFailed(498),
    waitForStorageProvisionFailed(499),
    commitStorageFailed(500),
    waitForCommitStorageFailed(501),
    waitForAssocCompletionFailed(502),
    clientLostConnectivity(503),
    registerClientFailed(504),
    verifyRegistrationFailed(505),
    mountLocalFailed(506),
    mountPeerFailed(507),
    unmountLocalFailed(508),
    unmountPeerFailed(509),
    reportFailed(510),
    configurationError(511),
    referencedVsanUnresolvable(512),
    operationFailed(513),
    waitForDeployFailed(518),
    activateucsmFailed(519),
    pollActivateOfucsmFailed(520),
    updateiomFailed(521),
    pollUpdateOfiomFailed(522),
    activateiomFailed(523),
    pollActivateOfiomFailed(524),
    activateRemotefiFailed(525),
    pollActivateOfRemotefiFailed(526),
    waitForUserAckFailed(527),
    activateLocalfiFailed(528),
    pollActivateOfLocalfiFailed(529),
    activateCatalogFailed(530),
    providerGroupAlreadyExists(531),
    invalidServerGroup(532),
    roleConfigError(533),
    localeConfigError(534),
    userRoleConfigError(535),
    userLocaleConfigError(536),
    keyringConfigError(537),
    snmpConfigError(538),
    timezoneFileNotExists(539),
    userConfigError(540),
    snmpUserConfigError(541),
    commSvcConfigError(542),
    resolveFailed(543),
    updateVlanGroupsFailed(544),
    updateZonesFailed(545),
    noVlanOptimization(546),
    suspendModeEntered(547),
    verifyGuidFailed(548),
    unregisterFailed(549),
    cleanOldDataFailed(550),
    requestFailed(551),
    verifyFailed(552),
    releaseFailed(553),
    resolveManyFailed(554),
    releaseManyFailed(555),
    resolveAllFailed(556),
    releaseAllFailed(557),
    fcoeUplinkUnsupportedFiSettings(558),
    fcoeUplinkPortChannelUnsupportedFiSettings(559),
    invalidTarget(560),
    fcZoningEnabled(561),
    fcStorageportNpvMode(562),
    fcoeStorageportNpvMode(563),
    fcPortchannelMembersInconsistentSpeed(564),
    vlanMcastPolicyMisconfigured(565),
    anotherConnectionAlreadyEnabled(566),
    connectionUnused(567),
    unsupportedConnectivity(568),
    callhomeConfigError(569),
    loadCatalogFailed(570),
    arpTargetsConfigError(572),
    removeFailed(573),
    configFlexFlashFailed(574),
    syncPowerStateFailed(575),
    unconfigFlexFlashFailed(576),
    resolveNetworkPoliciesFailed(577),
    resolveNetworkTemplatesFailed(578),
    validatePolicyOwnershipFailed(579),
    licenseInsufficient(580),
    invalidKeyringModulus(581),
    localeOrgConfigError(582),
    checkInventoryStatusFailed(583),
    extraPrimaryVlans(585),
    syncFailed(586),
    healthLedAmberBlinking(587),
    healthLedAmber(588),
    referencedRemoteVlanUnresolvable(589),
    referencedRemoteVsanUnresolvable(590),
    multipleConnectionPolicies(591),
    updateEthFlowMonFailed(592),
    equipmentUnhealthy(593),
    postSetKeyRingLocalFailed(594),
    postSetKeyRingPeerFailed(595),
    providerGroupSizeEmpty(596),
    serverPowerOffFailed(597),
    serverPowerOnFailed(598),
    defaultHostpackMissing(599),
    defaultHostpackMissingVersions(600),
    namedVlanUnresolved(601),
    vmNetworkReferenceIncorrect(602),
    ndiscTargetsConfigError(603),
    configMemoryPolicyFailed(604),
    boardCtrlUpgraded(605),
    incompatibleServerFirmware(606),
    oobStorageInventoryFailed(608),
    configFlexFlashScrubFailed(609),
    cimcvlanCfgLocalFailed(610),
    cimcvlanCfgPeerFailed(611),
    cmcvlanCfgFailed(612),
    cmcvlanCfgPeerFailed(613),
    activeFailed(614),
    swConfigServiceInfraLocalFailed(615),
    swConfigServiceInfraPeerFailed(616),
    nicConfigServiceInfraLocalFailed(617),
    nicConfigServiceInfraPeerFailed(618),
    nicUnconfigServiceInfraLocalFailed(619),
    nicUnconfigServiceInfraPeerFailed(620),
    swUnConfigLocalFailed(621),
    swUnConfigPeerFailed(622),
    nicUnConfigLocalFailed(623),
    nicUnConfigPeerFailed(624),
    powerOnPreConfigFailed(625),
    resetSecureBootConfigFailed(626),
    udldLinkDown(627),
    cimcFirmwareMismatch(630),
    pldFirmwareMismatch(631),
    copyImgFromRepFailed(632),
    copyiomimgToSubFailed(633),
    copyCatFromRepFailed(634),
    copyExternalRepToRemoteFailed(635),
    serverError(636),
    unconfigExtMgmtRulesFailed(637),
    unconfigExtMgmtGwFailed(638),
    unconfigCimcvmediaFailed(639),
    downloadImagesFailed(640),
    graphicsImageUpdateFailed(641),
    configExtMgmtRulesFailed(642),
    configExtMgmtGwFailed(643),
    configCimcvmediaFailed(644),
    deleteCurlDownloadedImagesFailed(645),
    configKvmMgmtDefaultSettingFailed(646),
    updateFlashLifeFailed(647),
    primaryVlanMissingForIsolated(648),
    primaryVlanMissingForCommunity(649),
    vlanMismatch(650),
    vlanErrorAssocPrimary(651),
    svnicNotPresent(652),
    unsupportedCimcFirmware(653),
    configBackupOutdated(654),
    extraSecondaryVlans(655),
    extraSecondaryVlansPerPrimary(656),
    vmediaMountInaccessible(657),
    formatFailed(658),
    pairFailed(659),
    tpmOnSlaveBoard(660),
    checkAssignedIdentifiersForDupFailed(661),
    checkAssignedDefaultIdentifiersForDupFailed(662),
    duplicatedAssigned(663),
    namedInbandVlanUnresolved(664),
    inbandUnsupportedServer(665),
    nearMaxLimit(666),
    memoryError(667),
    adaptorMismatch(668),
    uploadFailed(672),
    psuMixedMode(673),
    powerBudgetUnavailable(674),
    validateLocalFailed(719),
    validateRemoteFailed(720),
    licenseGraceperiodEntered(721),
    licenseFileNotDeleted(722),
    discoveryFailed(723),
    fullInventoryFailed(727),
    beginInventoryFailed(728),
    reportPhysicalInventoryFailed(729),
    reportOrgInventoryFailed(730),
    reportStorageInventoryFailed(731),
    endInventoryFailed(732),
    powerButtonLockConfigFailed(733),
    powerOffWaitFailed(734),
    powerOffReclaimFailed(735),
    solRedirectEnableFailed(736),
    serialDebugConnectFailed(737),
    serialDebugDisconnectFailed(738),
    solRedirectDisableFailed(739),
    swConfigPortNivLocalFailed(740),
    swConfigPortNivPeerFailed(741),
    configbmcpowerParamsFailed(743),
    powerDeployWaitFailed(744),
    pnuospowerProfilingFailed(745),
    sendBmcProfilingInitFailed(746),
    sendBmcProfilingDoneFailed(747),
    serialDebugPnuosconnectFailed(748),
    oobStorageConfigFailed(749),
    nicConfigParamsHostoslocalFailed(751),
    nicConfigParamsHostospeerFailed(752),
    reconfigUuidFailed(755),
    tearDownvmediaLocalFailed(756),
    tearDownvmediaPeerFailed(757),
    configChassisIdFailed(758),
    resolveStorageScheduleFailed(759),
    satelliteConnectionAbsent(761),
    unsupportedConnectivityConfiguration(762),
    fruProblem(763),
    finalizeFailed(766),
    portFailed(767),
    pollUpdateStatusLocalFailed(793),
    activatePsuFailed(794),
    notSupported(795),
    cartridgeMoved(798),
    configurationMismatch(799),
    pollActivationFailed(800),
    powerOffServersFailed(801),
    serversPowerOffCompletionFailed(802),
    deleteImagesRemoteFailed(804),
    oobDiskScrubFailed(805),
    cimcPresenceFailed(806),
    cleanupNicConfigLocalFailed(807),
    cleanupNicConfigPeerFailed(808),
    cleanupVnicsLocalFailed(809),
    cleanupVnicsPeerFailed(810),
    sharediomoduleInventoryFailed(811),
    internalBackupFailed(812),
    pollInternalBackupFailed(813),
    unlockFirmwareImageFailed(814),
    precleanupPortConfigFailed(815),
    readSmBiosFailed(816),
    defaultauthConfigError(817),
    domainConfigError(818),
    fault(819),
    localInternalBackupFailed(820),
    reportFaultInventoryFailed(821),
    configMissing(825),
    pollWaitForUserAckFailed(826),
    setupVmediaFailed(827),
    unconfigVmediaFailed(828),
    equipmentAccessibilityProblem(829),
    equipmentLinkDegraded(830),
    powerCycleBoardFailed(831),
    pollBoardCtrlPowerCycleFailed(832),
    discoverSasExpanderFailed(833),
    vsanExceedLimit(834),
    comprSetsExhausted(836),
    kernelMemCriticalThreshold(837),
    unsupportedPolicyConfig(838),
    fanRemoval(839),
    healthWarning(840),
    healthMinor(841),
    healthMajor(842),
    healthCritical(843),
    checkAdaptorFw40gcapFailed(845),
    calculateVlanGroupForHostoslocalFailed(846),
    calculateVlanGroupForHostospeerFailed(847),
    applyMaintConfigFailed(848),
    unsupportedConfig(849),
    equipmentFailed(855),
    verifyBreakoutConfigFailed(857),
    copyAllImagesToPeerFailed(860),
    cleanUpvifsFailed(861),
    vlanCompGrpCountExceedsLimit(862),
    fiBQuerierIpEmptyOrSameAsPrimary(863),
    deprecated(864),
    invalidPinning(865),
    extraVif(866),
    equipmentDeprecated(867),
    nativeVlanNotFound(868),
    configFanSpeedFailed(870),
    sasExpanderImgUpdateFailed(871),
    chassisLimitExceeded(872),
    mgmtDbCorruption(874),
    bmcFactoryResetFailed(875),
    applyMoPropsFailed(876),
    deleteAllMoRefsFailed(877),
    maxVlanLimitExceeded(878),
    initIptablesLocalFailed(879),
    initIptablesPeerFailed(880),
    replicationFailure(881),
    tpmMismatch(882),
    validateRemovalFailed(883),
    updateStorageInvcmcFailed(884),
    updateStorageInvcimcFailed(885),
    pollUpdateStorageInvcimcFailed(886),
    backplanePortProblem(887),
    standbycmcvlanCfgFailed(888),
    postScrubOobStorageInventoryFailed(889),
    oobSasExpanderImgUpdateFailed(890),
    oobPollSasExpanderUpdateStatusFailed(891),
    oobSasExpanderImgActivateFailed(892),
    oobPollSasExpanderActivateStatusFailed(893),
    ciscoosopenGateFailed(894),
    storageInventoryFailed(895),
    waitBeforeInstallationFailed(896),
    updateCmcFailed(897),
    pollUpdateCmcFailed(898),
    updateAdaptorFailed(899),
    pollUpdateAdaptorFailed(900),
    updateSasExpanderFailed(901),
    pollUpdateSasExpanderFailed(902),
    activateSasExpanderFailed(903),
    pollSasExpanderActivateFailed(904),
    activateCmcFailed(905),
    pollCmcActivationFailed(906),
    waitForPowerOffFailed(907),
    activateAdaptorFailed(908),
    pollAdaptorActivationFailed(909),
    activateStorageCtlrFailed(910),
    pollStorageCtlrActivationFailed(911),
    activateBrdCtlrFailed(912),
    pollBrdCtlrActivationFailed(913),
    activateLocalDiskFailed(914),
    powerOnServersFailed(915),
    diskZoningConfigFailed(916),
    postDiskZoneStorageInvcmcFailed(917),
    postDiskZoneStorageInvcimcFailed(918),
    pollPostDiskZoneStorageInvcimcFailed(919),
    completeFailed(920),
    equipmentLinkMisconnect(921),
    equipmentFruMissing(922),
    equipmentUnavailable(923),
    equipmentHotspareUnsupported(924),
    equipmentOwnershipUnsupported(925),
    equipmentIoeOwnershipUnassigned(926),
    equipmentHddslotServer2OwnershipUnassigned(927),
    verifyUserZoneConfigFailed(934),
    pollSecureBootStatusFailed(935),
    resetSasExpanderFailed(936),
    pollLocalDiskActivateFailed(937),
    waitForActivationFailed(938),
    updateFailed(939),
    networkSanGroupDoesNotExist(941),
    updateSpLocalFailed(942),
    updateSpRemoteFailed(943),
    assertBypassWaitFailed(944),
    fabEvacOnRemotefiFailed(945),
    pollFabEvacOnRemotefiFailed(946),
    fabEvacOffRemotefiFailed(947),
    pollFabEvacOffRemotefiFailed(948),
    failOverToRemotefiFailed(949),
    pollFailOverToRemotefiFailed(950),
    activateucsmservicePackFailed(951),
    pollActivateOfucsmservicePackFailed(952),
    disableScriptablevmediaFailed(953),
    preconfigVmediaLocalFailed(954),
    preconfigVmediaPeerFailed(955),
    setupBootEnvironmentFailed(956),
    powerOnWaitFailed(957),
    runTestsFailed(958),
    logTransferFailed(959),
    waitForDebugFailed(960),
    tearDownBootEnvironmentFailed(961),
    pnuosperipheralComponentConfigFailed(962),
    configMgmtIpRulesFailed(963),
    hostosconnectFailed(964),
    configHostOsAnnotationsFailed(965),
    configServerIdentityFailed(966),
    unconfigServerIdentityFailed(967),
    kmipCertConfigFailed(968),
    kmipSaveCertFailed(969),
    estimateApplyConfigFailed(970),
    configChassisAdapterConnectivityFailed(971),
    portMisconfigure(972),
    transceiverMismatch(973),
    pciConfigIssue(974),
    fabricEvacuated(975),
    unicastMacExhausted(976),
    multicastMacExhausted(977),
    pvlifVlanMbrExhausted(978),
    pvsystemExhausted(979),
    igmpGroupExhausted(980),
    hardwareMismatch(981),
    chassisIntrusion(982),
    configProblem(983),
    networkSanGroupMisconfigured(984),
    reportErrorFailed(985),
    resolveFromPolicyMgrFailed(986),
    resolveFromOpsMgrFailed(987),
    kmipFault(988),
    hardwareInventoryMismatch(989),
    pciConfigMismatch(990),
    equipmentSecondControllerAbsent(991),
    healthInfo(994),
    removePeerFailed(995),
    imageCorrupted(996),
    restoreVdStatusFailed(997),
    vhbaNotSupported(998),
    equipmentNonOptimal(999),
    iftmcPvExhausted(1000),
    dvifExhausted(1001),
    configSwitchPeerFailed(1002),
    configSwitchLocalFailed(1003),
    inoperable(1004),
    configMismatch(1005),
    certificateUnsupported(1006),
    certificateEmptyParams(1007),
    swPortDetailsLocalFailed(1008),
    swPortDetailsPeerFailed(1009),
    swConfigurePortChannelLocalFailed(1010),
    swConfigurePortChannelPeerFailed(1011),
    pnuosBootWaitFailed(1012),
    swHostosmultiPortConnectivityLocalFailed(1013),
    swHostosmultiPortConnectivityPeerFailed(1014),
    swHostosconfigurePortChannelLocalFailed(1015),
    swHostosconfigurePortChannelPeerFailed(1016),
    oobSasExpanderBootImgActivateFailed(1017),
    oobPollSasExpanderBootImgActivateStatusFailed(1018),
    mswitchImgUpdateFailed(1019),
    resetCimcFailed(1020),
    sasExpanderConfigFailed(1021),
    pollSasExpanderConfigFailed(1022),
    equipmentUnsecure(1023)
  }

CucsFaultSeverity  ::= TEXTUAL-CONVENTION
        STATUS       current
        DESCRIPTION
       "A code used to identify the severity of a fault"
        SYNTAX INTEGER {
    cleared(0),
    info(1),
    warning(3),
    minor(4),
    major(5),
    critical(6)
  }

-- *********************************************************************
-- Basic UCS MIB Objects
-- *********************************************************************

ciscoUnifiedComputingMIBObjects OBJECT IDENTIFIER
    ::= { ciscoUnifiedComputingMIB 1 }

END
