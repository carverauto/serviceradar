-- *********************************************************************
-- CISCO-UNIFIED-COMPUTING-MGMT-MIB.my
-- 
-- MIB representation of the Cisco Unified Computing System
-- MGMT management information model package
-- 
-- Created July 2018 by Charles Bullis
-- 
-- Copyright (c) 2005-2018 Cisco Systems, Inc. All rights reserved.
-- 
-- *********************************************************************

CISCO-UNIFIED-COMPUTING-MGMT-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsCommClientAdminState,
    CucsConditionRemoteInvRslt,
    CucsConditionSeverity,
    CucsEtherSatelliteConnectionDisc,
    CucsFsmCompletion,
    CucsFsmFlags,
    CucsFsmFsmStageStatus,
    CucsIpProtocol,
    CucsMgmtASecureBootAdminState,
    CucsMgmtAccess,
    CucsMgmtAdminState,
    CucsMgmtBackupFsmCurrentFsm,
    CucsMgmtBackupFsmStageName,
    CucsMgmtBackupFsmTaskItem,
    CucsMgmtBackupInterval,
    CucsMgmtBackupIssue,
    CucsMgmtBackupJob,
    CucsMgmtBackupJobStatus,
    CucsMgmtBackupPolicyFsmCurrentFsm,
    CucsMgmtBackupPolicyFsmStageName,
    CucsMgmtBackupPostAction,
    CucsMgmtBackupProto,
    CucsMgmtBackupType,
    CucsMgmtCapability,
    CucsMgmtCfgExportPolicyFsmCurrentFsm,
    CucsMgmtCfgExportPolicyFsmStageName,
    CucsMgmtConfigState,
    CucsMgmtConnectionState,
    CucsMgmtControllerFsmCurrentFsm,
    CucsMgmtControllerFsmStageName,
    CucsMgmtControllerFsmTaskFlags,
    CucsMgmtControllerFsmTaskItem,
    CucsMgmtControllerHostagCommMethod,
    CucsMgmtDimmBlacklistingOperState,
    CucsMgmtDiskZoningState,
    CucsMgmtEntityChassisDeviceIoState1,
    CucsMgmtEntityChassisDeviceIoState2,
    CucsMgmtEntityChassisDeviceIoState3,
    CucsMgmtEntityHaFailureReason,
    CucsMgmtEntityHaReadiness,
    CucsMgmtEntityLeadIdForAutoInstall,
    CucsMgmtEntityLeadership,
    CucsMgmtEntityMgmtServicesState,
    CucsMgmtEntityProblems,
    CucsMgmtEntityState,
    CucsMgmtEntityUmbilicalState,
    CucsMgmtExportPolicyAdminState,
    CucsMgmtExportPolicyFsmCurrentFsm,
    CucsMgmtExportPolicyFsmStageName,
    CucsMgmtExportPolicyFsmTaskItem,
    CucsMgmtExportPolicyProto,
    CucsMgmtIPv6IfAddrFsmCurrentFsm,
    CucsMgmtIPv6IfAddrFsmStageName,
    CucsMgmtIPv6IfAddrFsmTaskItem,
    CucsMgmtIfFsmCurrentFsm,
    CucsMgmtIfFsmStageName,
    CucsMgmtIfFsmTaskItem,
    CucsMgmtImportAction,
    CucsMgmtImportStatus,
    CucsMgmtImporterFsmCurrentFsm,
    CucsMgmtImporterFsmStageName,
    CucsMgmtImporterFsmTaskItem,
    CucsMgmtImporterPostAction,
    CucsMgmtImporterProto,
    CucsMgmtIntAuthPolicyMethod,
    CucsMgmtMaintMode,
    CucsMgmtMode,
    CucsMgmtOperState,
    CucsMgmtPmonEntryState,
    CucsMgmtSecureBootOperState,
    CucsMgmtSource,
    CucsMgmtStateQual,
    CucsMgmtStorageSubsystemState,
    CucsMgmtSubject,
    CucsNetworkConnectionType,
    CucsNetworkLocale,
    CucsNetworkPhysEpIfType,
    CucsNetworkPortRole,
    CucsNetworkSwitchId,
    CucsNetworkTransport,
    CucsPkiCertStatus,
    CucsPolicyPolicyOwner,
    CucsTrigAdminState,
    CucsTrigTrigOperState,
    CucsVnicExternalMgmtIPMode
        FROM CISCO-UNIFIED-COMPUTING-TC-MIB;

cucsMgmtObjects MODULE-IDENTITY
    LAST-UPDATED    "201807260000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        MGMT management information model package"
    ::= { ciscoUnifiedComputingMIBObjects 31 }

cucsMgmtAccessPolicyTable OBJECT-TYPE
    SYNTAX           SEQUENCE OF CucsMgmtAccessPolicyEntry
    MAX-ACCESS       not-accessible
    STATUS           current
    DESCRIPTION
        "Cisco UCS mgmt:AccessPolicy managed object table"
    ::= { cucsMgmtObjects 1 }

cucsMgmtAccessPolicyEntry OBJECT-TYPE
    SYNTAX           CucsMgmtAccessPolicyEntry
    MAX-ACCESS       not-accessible
    STATUS           current
    DESCRIPTION
        "Entry for the cucsMgmtAccessPolicyTable table."
    INDEX { cucsMgmtAccessPolicyInstanceId }
    ::= { cucsMgmtAccessPolicyTable 1 }

CucsMgmtAccessPolicyEntry ::= SEQUENCE {
    cucsMgmtAccessPolicyInstanceId                                   CucsManagedObjectId,
    cucsMgmtAccessPolicyDn                                           CucsManagedObjectDn,
    cucsMgmtAccessPolicyRn                                           SnmpAdminString
}

cucsMgmtAccessPolicyInstanceId OBJECT-TYPE
    SYNTAX       CucsManagedObjectId
    MAX-ACCESS   not-accessible
    STATUS       current
    DESCRIPTION
        "Instance identifier of the managed object."
    ::= { cucsMgmtAccessPolicyEntry 1 }

cucsMgmtAccessPolicyDn OBJECT-TYPE
    SYNTAX       CucsManagedObjectDn
    MAX-ACCESS   read-only
    STATUS       current
    DESCRIPTION
        "Cisco UCS mgmt:AccessPolicy:dn managed object property"
    ::= { cucsMgmtAccessPolicyEntry 2 }

cucsMgmtAccessPolicyRn OBJECT-TYPE
    SYNTAX       SnmpAdminString
    MAX-ACCESS   read-only
    STATUS       current
    DESCRIPTION
        "Cisco UCS mgmt:AccessPolicy:rn managed object property"
    ::= { cucsMgmtAccessPolicyEntry 3 }

cucsMgmtAccessPolicyItemTable OBJECT-TYPE
    SYNTAX           SEQUENCE OF CucsMgmtAccessPolicyItemEntry
    MAX-ACCESS       not-accessible
    STATUS           current
    DESCRIPTION
        "Cisco UCS mgmt:AccessPolicyItem managed object table"
    ::= { cucsMgmtObjects 2 }

cucsMgmtAccessPolicyItemEntry OBJECT-TYPE
    SYNTAX           CucsMgmtAccessPolicyItemEntry
    MAX-ACCESS       not-accessible
    STATUS           current
    DESCRIPTION
        "Entry for the cucsMgmtAccessPolicyItemTable table."
    INDEX { cucsMgmtAccessPolicyItemInstanceId }
    ::= { cucsMgmtAccessPolicyItemTable 1 }

CucsMgmtAccessPolicyItemEntry ::= SEQUENCE {
    cucsMgmtAccessPolicyItemInstanceId                               CucsManagedObjectId,
    cucsMgmtAccessPolicyItemDn                                       CucsManagedObjectDn,
    cucsMgmtAccessPolicyItemRn                                       SnmpAdminString,
    cucsMgmtAccessPolicyItemDescr                                    SnmpAdminString,
    cucsMgmtAccessPolicyItemIntId                                    SnmpAdminString,
    cucsMgmtAccessPolicyItemIpPoolName                               SnmpAdminString,
    cucsMgmtAccessPolicyItemName                                     SnmpAdminString,
    cucsMgmtAccessPolicyItemSubject                                  CucsMgmtSubject,
    cucsMgmtAccessPolicyItemPolicyLevel                              Gauge32,
    cucsMgmtAccessPolicyItemPolicyOwner                              CucsPolicyPolicyOwner
}

cucsMgmtAccessPolicyItemInstanceId OBJECT-TYPE
    SYNTAX       CucsManagedObjectId
    MAX-ACCESS   not-accessible
    STATUS       current
    DESCRIPTION
        "Instance identifier of the managed object."
    ::= { cucsMgmtAccessPolicyItemEntry 1 }

cucsMgmtAccessPolicyItemDn OBJECT-TYPE
    SYNTAX       CucsManagedObjectDn
    MAX-ACCESS   read-only
    STATUS       current
    DESCRIPTION
        "Cisco UCS mgmt:AccessPolicyItem:dn managed object property"
    ::= { cucsMgmtAccessPolicyItemEntry 2 }

cucsMgmtAccessPolicyItemRn OBJECT-TYPE
    SYNTAX       SnmpAdminString
    MAX-ACCESS   read-only
    STATUS       current
    DESCRIPTION
        "Cisco UCS mgmt:AccessPolicyItem:rn managed object property"
    ::= { cucsMgmtAccessPolicyItemEntry 3 }

cucsMgmtAccessPolicyItemDescr OBJECT-TYPE
    SYNTAX       SnmpAdminString
    MAX-ACCESS   read-only
    STATUS       current
    DESCRIPTION
        "Cisco UCS mgmt:AccessPolicyItem:descr managed object property"
    ::= { cucsMgmtAccessPolicyItemEntry 4 }

cucsMgmtAccessPolicyItemIntId OBJECT-TYPE
    SYNTAX       SnmpAdminString
    MAX-ACCESS   read-only
    STATUS       current
    DESCRIPTION
        "Cisco UCS mgmt:AccessPolicyItem:intId managed object property"
    ::= { cucsMgmtAccessPolicyItemEntry 5 }

cucsMgmtAccessPolicyItemIpPoolName OBJECT-TYPE
    SYNTAX       SnmpAdminString
    MAX-ACCESS   read-only
    STATUS       current
    DESCRIPTION
        "Cisco UCS mgmt:AccessPolicyItem:ipPoolName managed
        object property"
    ::= { cucsMgmtAccessPolicyItemEntry 6 }

cucsMgmtAccessPolicyItemName OBJECT-TYPE
    SYNTAX       SnmpAdminString
    MAX-ACCESS   read-only
    STATUS       current
    DESCRIPTION
        "Cisco UCS mgmt:AccessPolicyItem:name managed object property"
    ::= { cucsMgmtAccessPolicyItemEntry 7 }

cucsMgmtAccessPolicyItemSubject OBJECT-TYPE
    SYNTAX       CucsMgmtSubject
    MAX-ACCESS   read-only
    STATUS       current
    DESCRIPTION
        "Cisco UCS mgmt:AccessPolicyItem:subject managed object property"
    ::= { cucsMgmtAccessPolicyItemEntry 8 }

cucsMgmtAccessPolicyItemPolicyLevel OBJECT-TYPE
    SYNTAX       Gauge32
    MAX-ACCESS   read-only
    STATUS       current
    DESCRIPTION
        "Cisco UCS mgmt:AccessPolicyItem:policyLevel managed
        object property"
    ::= { cucsMgmtAccessPolicyItemEntry 9 }

cucsMgmtAccessPolicyItemPolicyOwner OBJECT-TYPE
    SYNTAX       CucsPolicyPolicyOwner
    MAX-ACCESS   read-only
    STATUS       current
    DESCRIPTION
        "Cisco UCS mgmt:AccessPolicyItem:policyOwner managed
        object property"
    ::= { cucsMgmtAccessPolicyItemEntry 10 }

cucsMgmtAccessPortTable OBJECT-TYPE
    SYNTAX           SEQUENCE OF CucsMgmtAccessPortEntry
    MAX-ACCESS       not-accessible
    STATUS           current
    DESCRIPTION
        "Cisco UCS mgmt:AccessPort managed object table"
    ::= { cucsMgmtObjects 3 }

cucsMgmtAccessPortEntry OBJECT-TYPE
    SYNTAX           CucsMgmtAccessPortEntry
    MAX-ACCESS       not-accessible
    STATUS           current
    DESCRIPTION
        "Entry for the cucsMgmtAccessPortTable table."
    INDEX { cucsMgmtAccessPortInstanceId }
    ::= { cucsMgmtAccessPortTable 1 }

CucsMgmtAccessPortEntry ::= SEQUENCE {
    cucsMgmtAccessPortInstanceId                                     CucsManagedObjectId,
    cucsMgmtAccessPortDn                                             CucsManagedObjectDn,
    cucsMgmtAccessPortRn                                             SnmpAdminString,
    cucsMgmtAccessPortPort                                           Gauge32,
    cucsMgmtAccessPortProtocol                                       CucsIpProtocol
}

cucsMgmtAccessPortInstanceId OBJECT-TYPE
    SYNTAX       CucsManagedObjectId
    MAX-ACCESS   not-accessible
    STATUS       current
    DESCRIPTION
        "Instance identifier of the managed object."
    ::= { cucsMgmtAccessPortEntry 1 }

cucsMgmtAccessPortDn OBJECT-TYPE
    SYNTAX       CucsManagedObjectDn
    MAX-ACCESS   read-only
    STATUS       current
    DESCRIPTION
        "Cisco UCS mgmt:AccessPort:dn managed object property"
    ::= { cucsMgmtAccessPortEntry 2 }

cucsMgmtAccessPortRn OBJECT-TYPE
    SYNTAX       SnmpAdminString
    MAX-ACCESS   read-only
    STATUS       current
    DESCRIPTION
        "Cisco UCS mgmt:AccessPort:rn managed object property"
    ::= { cucsMgmtAccessPortEntry 3 }

cucsMgmtAccessPortPort OBJECT-TYPE
    SYNTAX       Gauge32
    MAX-ACCESS   read-only
    STATUS       current
    DESCRIPTION
        "Cisco UCS mgmt:AccessPort:port managed object property"
    ::= { cucsMgmtAccessPortEntry 4 }

cucsMgmtAccessPortProtocol OBJECT-TYPE
    SYNTAX       CucsIpProtocol
    MAX-ACCESS   read-only
    STATUS       current
    DESCRIPTION
        "Cisco UCS mgmt:AccessPort:protocol managed object property"
    ::= { cucsMgmtAccessPortEntry 5 }

cucsMgmtBackupTable OBJECT-TYPE
    SYNTAX           SEQUENCE OF CucsMgmtBackupEntry
    MAX-ACCESS       not-accessible
    STATUS           current
    DESCRIPTION
        "Cisco UCS mgmt:Backup managed object table"
    ::= { cucsMgmtObjects 4 }

cucsMgmtBackupEntry OBJECT-TYPE
    SYNTAX           CucsMgmtBackupEntry
    MAX-ACCESS       not-accessible
    STATUS           current
    DESCRIPTION
        "Entry for the cucsMgmtBackupTable table."
    INDEX { cucsMgmtBackupInstanceId }
    ::= { cucsMgmtBackupTable 1 }

CucsMgmtBackupEntry ::= SEQUENCE {
    cucsMgmtBackupInstanceId                                         CucsManagedObjectId,
    cucsMgmtBackupDn                                                 CucsManagedObjectDn,
    cucsMgmtBackupRn                                                 SnmpAdminString,
    cucsMgmtBackupAdminState                                         CucsCommClientAdminState,
    cucsMgmtBackupDescr                                              SnmpAdminString,
    cucsMgmtBackupFsmDescr                                           SnmpAdminString,
    cucsMgmtBackupFsmPrev                                            SnmpAdminString,
    cucsMgmtBackupFsmProgr                                           Gauge32,
    cucsMgmtBackupFsmRmtInvErrCode                                   Gauge32,
    cucsMgmtBackupFsmRmtInvErrDescr                                  SnmpAdminString,
    cucsMgmtBackupFsmRmtInvRslt                                      CucsConditionRemoteInvRslt,
    cucsMgmtBackupFsmStageDescr                                      SnmpAdminString,
    cucsMgmtBackupFsmStamp                                           DateAndTime,
    cucsMgmtBackupFsmStatus                                          SnmpAdminString,
    cucsMgmtBackupFsmTry                                             Gauge32,
    cucsMgmtBackupHostname                                           SnmpAdminString,
    cucsMgmtBackupIntId                                              SnmpAdminString,
    cucsMgmtBackupJob                                                CucsMgmtBackupJob,
    cucsMgmtBackupName                                               SnmpAdminString,
    cucsMgmtBackupPostAction                                         CucsMgmtAbsBackupPostAction,
    cucsMgmtBackupPreservePooledValues                               TruthValue,
    cucsMgmtBackupProto                                              CucsMgmtAbsBackupProto,
    cucsMgmtBackupPwd                                                SnmpAdminString,
    cucsMgmtBackupRemoteFile                                         SnmpAdminString,
    cucsMgmtBackupType                                               CucsMgmtBackupType,
    cucsMgmtBackupUser                                               SnmpAdminString,
    cucsMgmtBackupMaxFiles                                           Gauge32,
    cucsMgmtBackupOwnerPolicy                                        SnmpAdminString,
    cucsMgmtBackupPolicyLevel                                        Gauge32,
    cucsMgmtBackupPolicyOwner                                        CucsPolicyPolicyOwner,
    cucsMgmtBackupBackupstatus                                       CucsMgmtBackupJobStatus
}

cucsMgmtBackupInstanceId OBJECT-TYPE
    SYNTAX       CucsManagedObjectId
    MAX-ACCESS   not-accessible
    STATUS       current
    DESCRIPTION
        "Instance identifier of the managed object."
    ::= { cucsMgmtBackupEntry 1 }

cucsMgmtBackupDn OBJECT-TYPE
    SYNTAX       CucsManagedObjectDn
    MAX-ACCESS   read-only
    STATUS       current
    DESCRIPTION
        "Cisco UCS mgmt:Backup:dn managed object property"
    ::= { cucsMgmtBackupEntry 2 }

cucsMgmtBackupRn OBJECT-TYPE
    SYNTAX       SnmpAdminString
    MAX-ACCESS   read-only
    STATUS       current
    DESCRIPTION
        "Cisco UCS mgmt:Backup:rn managed object property"
    ::= { cucsMgmtBackupEntry 3 }

cucsMgmtBackupAdminState OBJECT-TYPE
    SYNTAX       CucsCommClientAdminState
    MAX-ACCESS   read-only
    STATUS       current
    DESCRIPTION
        "Cisco UCS mgmt:Backup:adminState managed object property"
    ::= { cucsMgmtBackupEntry 4 }

cucsMgmtBackupDescr OBJECT-TYPE
    SYNTAX       SnmpAdminString
    MAX-ACCESS   read-only
    STATUS       current
    DESCRIPTION
        "Cisco UCS mgmt:Backup:descr managed object property"
    ::= { cucsMgmtBackupEntry 5 }

cucsMgmtBackupFsmDescr OBJECT-TYPE
    SYNTAX       SnmpAdminString
    MAX-ACCESS   read-only
    STATUS       current
    DESCRIPTION
        "Cisco UCS mgmt:Backup:fsmDescr managed object property"
    ::= { cucsMgmtBackupEntry 6 }

cucsMgmtBackupFsmPrev OBJECT-TYPE
    SYNTAX       SnmpAdminString
    MAX-ACCESS   read-only
    STATUS       current
    DESCRIPTION
        "Cisco UCS mgmt:Backup:fsmPrev managed object property"
    ::= { cucsMgmtBackupEntry 7 }

cucsMgmtBackupFsmProgr OBJECT-TYPE
    SYNTAX       Gauge32
    MAX-ACCESS   read-only
    STATUS       current
    DESCRIPTION
        "Cisco UCS mgmt:Backup:fsmProgr managed object property"
    ::= { cucsMgmtBackupEntry 8 }

cucsMgmtBackupFsmRmtInvErrCode OBJECT-TYPE
    SYNTAX       Gauge32
    MAX-ACCESS   read-only
    STATUS       current
    DESCRIPTION
        "Cisco UCS mgmt:Backup:fsmRmtInvErrCode managed object property"
    ::= { cucsMgmtBackupEntry 9 }

cucsMgmtBackupFsmRmtInvErrDescr OBJECT-TYPE
    SYNTAX       SnmpAdminString
    MAX-ACCESS   read-only
    STATUS       current
    DESCRIPTION
        "Cisco UCS mgmt:Backup:fsmRmtInvErrDescr managed object property"
    ::= { cucsMgmtBackupEntry 10 }

cucsMgmtBackupFsmRmtInvRslt OBJECT-TYPE
    SYNTAX       CucsConditionRemoteInvRslt
    MAX-ACCESS   read-only
    STATUS       current
    DESCRIPTION
        "Cisco UCS mgmt:Backup:fsmRmtInvRslt managed object property"
    ::= { cucsMgmtBackupEntry 11 }

cucsMgmtBackupFsmStageDescr OBJECT-TYPE
    SYNTAX       SnmpAdminString
    MAX-ACCESS   read-only
    STATUS       current
    DESCRIPTION
        "Cisco UCS mgmt:Backup:fsmStageDescr managed object property"
    ::= { cucsMgmtBackupEntry 12 }

cucsMgmtBackupFsmStamp OBJECT-TYPE
    SYNTAX       DateAndTime
    MAX-ACCESS   read-only
    STATUS       current
    DESCRIPTION
        "Cisco UCS mgmt:Backup:fsmStamp managed object property"
    ::= { cucsMgmtBackupEntry 13 }

cucsMgmtBackupFsmStatus OBJECT-TYPE
    SYNTAX       SnmpAdminString
    MAX-ACCESS   read-only
    STATUS       current
    DESCRIPTION
        "Cisco UCS mgmt:Backup:fsmStatus managed object property"
    ::= { cucsMgmtBackupEntry 14 }

cucsMgmtBackupFsmTry OBJECT-TYPE
    SYNTAX       Gauge32
    MAX-ACCESS   read-only
    STATUS       current
    DESCRIPTION
        "Cisco UCS mgmt:Backup:fsmTry managed object property"
    ::= { cucsMgmtBackupEntry 15 }

cucsMgmtBackupHostname OBJECT-TYPE
    SYNTAX       SnmpAdminString
    MAX-ACCESS   read-only
    STATUS       current
    DESCRIPTION
        "Cisco UCS mgmt:Backup:hostname managed object property"
    ::= { cucsMgmtBackupEntry 16 }

cucsMgmtBackupIntId OBJECT-TYPE
    SYNTAX       SnmpAdminString
    MAX-ACCESS   read-only
    STATUS       current
    DESCRIPTION
        "Cisco UCS mgmt:Backup:intId managed object property"
    ::= { cucsMgmtBackupEntry 17 }

cucsMgmtBackupJob OBJECT-TYPE
    SYNTAX       CucsMgmtBackupJob
    MAX-ACCESS   read-only
    STATUS       current
    DESCRIPTION
        "Cisco UCS mgmt:Backup:job managed object property"
    ::= { cucsMgmtBackupEntry 18 }

cucsMgmtBackupName OBJECT-TYPE
    SYNTAX       SnmpAdminString
    MAX-ACCESS   read-only
    STATUS       current
    DESCRIPTION
        "Cisco UCS mgmt:Backup:name managed object property"
    ::= { cucsMgmtBackupEntry 19 }

cucsMgmtBackupPostAction OBJECT-TYPE
    SYNTAX       CucsMgmtAbsBackupPostAction
    MAX-ACCESS   read-only
    STATUS       current
    DESCRIPTION
        "Cisco UCS mgmt:Backup:postAction managed object property"
    ::= { cucsMgmtBackupEntry 20 }

cucsMgmtBackupPreservePooledValues OBJECT-TYPE
    SYNTAX       TruthValue
    MAX-ACCESS   read-only
    STATUS       current
    DESCRIPTION
        "Cisco UCS mgmt:Backup:preservePooledValues managed
        object property"
    ::= { cucsMgmtBackupEntry 21 }

cucsMgmtBackupProto OBJECT-TYPE
    SYNTAX       CucsMgmtAbsBackupProto
    MAX-ACCESS   read-only
    STATUS       current
    DESCRIPTION
        "Cisco UCS mgmt:Backup:proto managed object property"
    ::= { cucsMgmtBackupEntry 22 }

cucsMgmtBackupPwd OBJECT-TYPE
    SYNTAX       SnmpAdminString
    MAX-ACCESS   read-only
    STATUS       current
    DESCRIPTION
        "Cisco UCS mgmt:Backup:pwd managed object property"
    ::= { cucsMgmtBackupEntry 23 }

cucsMgmtBackupRemoteFile OBJECT-TYPE
    SYNTAX       SnmpAdminString
    MAX-ACCESS   read-only
    STATUS       current
    DESCRIPTION
        "Cisco UCS mgmt:Backup:remoteFile managed object property"
    ::= { cucsMgmtBackupEntry 24 }

cucsMgmtBackupType OBJECT-TYPE
    SYNTAX       CucsMgmtBackupType
    MAX-ACCESS   read-only
    STATUS       current
    DESCRIPTION
        "Cisco UCS mgmt:Backup:type managed object property"
    ::= { cucsMgmtBackupEntry 25 }

cucsMgmtBackupUser OBJECT-TYPE
    SYNTAX       SnmpAdminString
    MAX-ACCESS   read-only
    STATUS       current
    DESCRIPTION
        "Cisco UCS mgmt:Backup:user managed object property"
    ::= { cucsMgmtBackupEntry 26 }

cucsMgmtBackupMaxFiles OBJECT-TYPE
    SYNTAX       Gauge32
    MAX-ACCESS   read-only
    STATUS       current
    DESCRIPTION
        "Cisco UCS mgmt:Backup:maxFiles managed object property"
    ::= { cucsMgmtBackupEntry 27 }

cucsMgmtBackupOwnerPolicy OBJECT-TYPE
    SYNTAX       SnmpAdminString
    MAX-ACCESS   read-only
    STATUS       current
    DESCRIPTION
        "Cisco UCS mgmt:Backup:ownerPolicy managed object property"
    ::= { cucsMgmtBackupEntry 28 }

cucsMgmtBackupPolicyLevel OBJECT-TYPE
    SYNTAX       Gauge32
    MAX-ACCESS   read-only
    STATUS       current
    DESCRIPTION
        "Cisco UCS mgmt:Backup:policyLevel managed object property"
    ::= { cucsMgmtBackupEntry 29 }

cucsMgmtBackupPolicyOwner OBJECT-TYPE
    SYNTAX       CucsPolicyPolicyOwner
    MAX-ACCESS   read-only
    STATUS       current
    DESCRIPTION
        "Cisco UCS mgmt:Backup:policyOwner managed object property"
    ::= { cucsMgmtBackupEntry 30 }

cucsMgmtBackupBackupstatus OBJECT-TYPE
    SYNTAX       CucsMgmtBackupJobStatus
    MAX-ACCESS   read-only
    STATUS       current
    DESCRIPTION
        "Cisco UCS mgmt:Backup:backupstatus managed object property"
    ::= { cucsMgmtBackupEntry 31 }

cucsMgmtBackupExportExtPolicyTable OBJECT-TYPE
    SYNTAX           SEQUENCE OF CucsMgmtBackupExportExtPolicyEntry
    MAX-ACCESS       not-accessible
    STATUS           current
    DESCRIPTION
        "Cisco UCS mgmt:BackupExportExtPolicy managed object table"
    ::= { cucsMgmtObjects 42 }

cucsMgmtBackupExportExtPolicyEntry OBJECT-TYPE
    SYNTAX           CucsMgmtBackupExportExtPolicyEntry
    MAX-ACCESS       not-accessible
    STATUS           current
    DESCRIPTION
        "Entry for the cucsMgmtBackupExportExtPolicyTable table."
    INDEX { cucsMgmtBackupExportExtPolicyInstanceId }
    ::= { cucsMgmtBackupExportExtPolicyTable 1 }

CucsMgmtBackupExportExtPolicyEntry ::= SEQUENCE {
    cucsMgmtBackupExportExtPolicyInstanceId                          CucsManagedObjectId,
    cucsMgmtBackupExportExtPolicyDn                                  CucsManagedObjectDn,
    cucsMgmtBackupExportExtPolicyRn                                  SnmpAdminString,
    cucsMgmtBackupExportExtPolicyAdminState                          CucsMgmtAdminState,
    cucsMgmtBackupExportExtPolicyDescr                               SnmpAdminString,
    cucsMgmtBackupExportExtPolicyFrequency                           Gauge32,
    cucsMgmtBackupExportExtPolicyIntId                               SnmpAdminString,
    cucsMgmtBackupExportExtPolicyName                                SnmpAdminString,
    cucsMgmtBackupExportExtPolicyPolicyLevel                         Gauge32,
    cucsMgmtBackupExportExtPolicyPolicyOwner                         CucsPolicyPolicyOwner
}

cucsMgmtBackupExportExtPolicyInstanceId OBJECT-TYPE
    SYNTAX       CucsManagedObjectId
    MAX-ACCESS   not-accessible
    STATUS       current
    DESCRIPTION
        "Instance identifier of the managed object."
    ::= { cucsMgmtBackupExportExtPolicyEntry 1 }

cucsMgmtBackupExportExtPolicyDn OBJECT-TYPE
    SYNTAX       CucsManagedObjectDn
    MAX-ACCESS   read-only
    STATUS       current
    DESCRIPTION
        "Cisco UCS mgmt:BackupExportExtPolicy:dn managed object property"
    ::= { cucsMgmtBackupExportExtPolicyEntry 2 }

cucsMgmtBackupExportExtPolicyRn OBJECT-TYPE
    SYNTAX       SnmpAdminString
    MAX-ACCESS   read-only
    STATUS       current
    DESCRIPTION
        "Cisco UCS mgmt:BackupExportExtPolicy:rn managed object property"
    ::= { cucsMgmtBackupExportExtPolicyEntry 3 }

cucsMgmtBackupExportExtPolicyAdminState OBJECT-TYPE
    SYNTAX       CucsMgmtAdminState
    MAX-ACCESS   read-only
    STATUS       current
    DESCRIPTION
        "Cisco UCS mgmt:BackupExportExtPolicy:adminState
        managed object property"
    ::= { cucsMgmtBackupExportExtPolicyEntry 4 }

cucsMgmtBackupExportExtPolicyDescr OBJECT-TYPE
    SYNTAX       SnmpAdminString
    MAX-ACCESS   read-only
    STATUS       current
    DESCRIPTION
        "Cisco UCS mgmt:BackupExportExtPolicy:descr managed
        object property"
    ::= { cucsMgmtBackupExportExtPolicyEntry 5 }

cucsMgmtBackupExportExtPolicyFrequency OBJECT-TYPE
    SYNTAX       Gauge32
    MAX-ACCESS   read-only
    STATUS       current
    DESCRIPTION
        "Cisco UCS mgmt:BackupExportExtPolicy:frequency
        managed object property"
    ::= { cucsMgmtBackupExportExtPolicyEntry 6 }

cucsMgmtBackupExportExtPolicyIntId OBJECT-TYPE
    SYNTAX       SnmpAdminString
    MAX-ACCESS   read-only
    STATUS       current
    DESCRIPTION
        "Cisco UCS mgmt:BackupExportExtPolicy:intId managed
        object property"
    ::= { cucsMgmtBackupExportExtPolicyEntry 7 }

cucsMgmtBackupExportExtPolicyName OBJECT-TYPE
    SYNTAX       SnmpAdminString
    MAX-ACCESS   read-only
    STATUS       current
    DESCRIPTION
        "Cisco UCS mgmt:BackupExportExtPolicy:name managed
        object property"
    ::= { cucsMgmtBackupExportExtPolicyEntry 8 }

cucsMgmtBackupExportExtPolicyPolicyLevel OBJECT-TYPE
    SYNTAX       Gauge32
    MAX-ACCESS   read-only
    STATUS       current
    DESCRIPTION
        "Cisco UCS mgmt:BackupExportExtPolicy:policyLevel
        managed object property"
    ::= { cucsMgmtBackupExportExtPolicyEntry 9 }

cucsMgmtBackupExportExtPolicyPolicyOwner OBJECT-TYPE
    SYNTAX       CucsPolicyPolicyOwner
    MAX-ACCESS   read-only
    STATUS       current
    DESCRIPTION
        "Cisco UCS mgmt:BackupExportExtPolicy:policyOwner
        managed object property"
    ::= { cucsMgmtBackupExportExtPolicyEntry 10 }

cucsMgmtBackupFsmTable OBJECT-TYPE
    SYNTAX           SEQUENCE OF CucsMgmtBackupFsmEntry
    MAX-ACCESS       not-accessible
    STATUS           current
    DESCRIPTION
        "Cisco UCS mgmt:BackupFsm managed object table"
    ::= { cucsMgmtObjects 15 }

cucsMgmtBackupFsmEntry OBJECT-TYPE
    SYNTAX           CucsMgmtBackupFsmEntry
    MAX-ACCESS       not-accessible
    STATUS           current
    DESCRIPTION
        "Entry for the cucsMgmtBackupFsmTable table."
    INDEX { cucsMgmtBackupFsmInstanceId }
    ::= { cucsMgmtBackupFsmTable 1 }

CucsMgmtBackupFsmEntry ::= SEQUENCE {
    cucsMgmtBackupFsmInstanceId                                      CucsManagedObjectId,
    cucsMgmtBackupFsmDn                                              CucsManagedObjectDn,
    cucsMgmtBackupFsmRn                                              SnmpAdminString,
    cucsMgmtBackupFsmCompletionTime                                  DateAndTime,
    cucsMgmtBackupFsmCurrentFsm                                      CucsMgmtBackupFsmCurrentFsm,
    cucsMgmtBackupFsmDescrData                                       SnmpAdminString,
    cucsMgmtBackupFsmFsmStatus                                       CucsFsmFsmStageStatus,
    cucsMgmtBackupFsmProgress                                        Gauge32,
    cucsMgmtBackupFsmRmtErrCode                                      Gauge32,
    cucsMgmtBackupFsmRmtErrDescr                                     SnmpAdminString,
    cucsMgmtBackupFsmRmtRslt                                         CucsConditionRemoteInvRslt
}

cucsMgmtBackupFsmInstanceId OBJECT-TYPE
    SYNTAX       CucsManagedObjectId
    MAX-ACCESS   not-accessible
    STATUS       current
    DESCRIPTION
        "Instance identifier of the managed object."
    ::= { cucsMgmtBackupFsmEntry 1 }

cucsMgmtBackupFsmDn OBJECT-TYPE
    SYNTAX       CucsManagedObjectDn
    MAX-ACCESS   read-only
    STATUS       current
    DESCRIPTION
        "Cisco UCS mgmt:BackupFsm:dn managed object property"
    ::= { cucsMgmtBackupFsmEntry 2 }

cucsMgmtBackupFsmRn OBJECT-TYPE
    SYNTAX       SnmpAdminString
    MAX-ACCESS   read-only
    STATUS       current
    DESCRIPTION
        "Cisco UCS mgmt:BackupFsm:rn managed object property"
    ::= { cucsMgmtBackupFsmEntry 3 }

cucsMgmtBackupFsmCompletionTime OBJECT-TYPE
    SYNTAX       DateAndTime
    MAX-ACCESS   read-only
    STATUS       current
    DESCRIPTION
        "Cisco UCS mgmt:BackupFsm:completionTime managed object property"
    ::= { cucsMgmtBackupFsmEntry 4 }

cucsMgmtBackupFsmCurrentFsm OBJECT-TYPE
    SYNTAX       CucsMgmtBackupFsmCurrentFsm
    MAX-ACCESS   read-only
    STATUS       current
    DESCRIPTION
        "Cisco UCS mgmt:BackupFsm:currentFsm managed object property"
    ::= { cucsMgmtBackupFsmEntry 5 }

cucsMgmtBackupFsmDescrData OBJECT-TYPE
    SYNTAX       SnmpAdminString
    MAX-ACCESS   read-only
    STATUS       current
    DESCRIPTION
        "Cisco UCS mgmt:BackupFsm:descr managed object property"
    ::= { cucsMgmtBackupFsmEntry 6 }

cucsMgmtBackupFsmFsmStatus OBJECT-TYPE
    SYNTAX       CucsFsmFsmStageStatus
    MAX-ACCESS   read-only
    STATUS       current
    DESCRIPTION
        "Cisco UCS mgmt:BackupFsm:fsmStatus managed object property"
    ::= { cucsMgmtBackupFsmEntry 7 }

cucsMgmtBackupFsmProgress OBJECT-TYPE
    SYNTAX       Gauge32
    MAX-ACCESS   read-only
    STATUS       current
    DESCRIPTION
        "Cisco UCS mgmt:BackupFsm:progress managed object property"
    ::= { cucsMgmtBackupFsmEntry 8 }

cucsMgmtBackupFsmRmtErrCode OBJECT-TYPE
    SYNTAX       Gauge32
    MAX-ACCESS   read-only
    STATUS       current
    DESCRIPTION
        "Cisco UCS mgmt:BackupFsm:rmtErrCode managed object property"
    ::= { cucsMgmtBackupFsmEntry 9 }

cucsMgmtBackupFsmRmtErrDescr OBJECT-TYPE
    SYNTAX       SnmpAdminString
    MAX-ACCESS   read-only
    STATUS       current
    DESCRIPTION
        "Cisco UCS mgmt:BackupFsm:rmtErrDescr managed object property"
    ::= { cucsMgmtBackupFsmEntry 10 }

cucsMgmtBackupFsmRmtRslt OBJECT-TYPE
    SYNTAX       CucsConditionRemoteInvRslt
    MAX-ACCESS   read-only
    STATUS       current
    DESCRIPTION
        "Cisco UCS mgmt:BackupFsm:rmtRslt managed object property"
    ::= { cucsMgmtBackupFsmEntry 11 }

cucsMgmtBackupFsmStageTable OBJECT-TYPE
    SYNTAX           SEQUENCE OF CucsMgmtBackupFsmStageEntry
    MAX-ACCESS       not-accessible
    STATUS           current
    DESCRIPTION
        "Cisco UCS mgmt:BackupFsmStage managed object table"
    ::= { cucsMgmtObjects 16 }

cucsMgmtBackupFsmStageEntry OBJECT-TYPE
    SYNTAX           CucsMgmtBackupFsmStageEntry
    MAX-ACCESS       not-accessible
    STATUS           current
    DESCRIPTION
        "Entry for the cucsMgmtBackupFsmStageTable table."
    INDEX { cucsMgmtBackupFsmStageInstanceId }
    ::= { cucsMgmtBackupFsmStageTable 1 }

CucsMgmtBackupFsmStageEntry ::= SEQUENCE {
    cucsMgmtBackupFsmStageInstanceId                                 CucsManagedObjectId,
    cucsMgmtBackupFsmStageDn                                         CucsManagedObjectDn,
    cucsMgmtBackupFsmStageRn                                         SnmpAdminString,
    cucsMgmtBackupFsmStageDescrData                                  SnmpAdminString,
    cucsMgmtBackupFsmStageLastUpdateTime                             DateAndTime,
    cucsMgmtBackupFsmStageName                                       CucsMgmtBackupFsmStageName,
    cucsMgmtBackupFsmStageOrder                                      Gauge32,
    cucsMgmtBackupFsmStageRetry                                      Gauge32,
    cucsMgmtBackupFsmStageStageStatus                                CucsFsmFsmStageStatus
}

cucsMgmtBackupFsmStageInstanceId OBJECT-TYPE
    SYNTAX       CucsManagedObjectId
    MAX-ACCESS   not-accessible
    STATUS       current
    DESCRIPTION
        "Instance identifier of the managed object."
    ::= { cucsMgmtBackupFsmStageEntry 1 }

cucsMgmtBackupFsmStageDn OBJECT-TYPE
    SYNTAX       CucsManagedObjectDn
    MAX-ACCESS   read-only
    STATUS       current
    DESCRIPTION
        "Cisco UCS mgmt:BackupFsmStage:dn managed object property"
    ::= { cucsMgmtBackupFsmStageEntry 2 }

cucsMgmtBackupFsmStageRn OBJECT-TYPE
    SYNTAX       SnmpAdminString
    MAX-ACCESS   read-only
    STATUS       current
    DESCRIPTION
        "Cisco UCS mgmt:BackupFsmStage:rn managed object property"
    ::= { cucsMgmtBackupFsmStageEntry 3 }

cucsMgmtBackupFsmStageDescrData OBJECT-TYPE
    SYNTAX       SnmpAdminString
    MAX-ACCESS   read-only
    STATUS       current
    DESCRIPTION
        "Cisco UCS mgmt:BackupFsmStage:descr managed object property"
    ::= { cucsMgmtBackupFsmStageEntry 4 }

cucsMgmtBackupFsmStageLastUpdateTime OBJECT-TYPE
    SYNTAX       DateAndTime
    MAX-ACCESS   read-only
    STATUS       current
    DESCRIPTION
        "Cisco UCS mgmt:BackupFsmStage:lastUpdateTime managed
        object property"
    ::= { cucsMgmtBackupFsmStageEntry 5 }

cucsMgmtBackupFsmStageName OBJECT-TYPE
    SYNTAX       CucsMgmtBackupFsmStageName
    MAX-ACCESS   read-only
    STATUS       current
    DESCRIPTION
        "Cisco UCS mgmt:BackupFsmStage:name managed object property"
    ::= { cucsMgmtBackupFsmStageEntry 6 }

cucsMgmtBackupFsmStageOrder OBJECT-TYPE
    SYNTAX       Gauge32
    MAX-ACCESS   read-only
    STATUS       current
    DESCRIPTION
        "Cisco UCS mgmt:BackupFsmStage:order managed object property"
    ::= { cucsMgmtBackupFsmStageEntry 7 }

cucsMgmtBackupFsmStageRetry OBJECT-TYPE
    SYNTAX       Gauge32
    MAX-ACCESS   read-only
    STATUS       current
    DESCRIPTION
        "Cisco UCS mgmt:BackupFsmStage:retry managed object property"
    ::= { cucsMgmtBackupFsmStageEntry 8 }

cucsMgmtBackupFsmStageStageStatus OBJECT-TYPE
    SYNTAX       CucsFsmFsmStageStatus
    MAX-ACCESS   read-only
    STATUS       current
    DESCRIPTION
        "Cisco UCS mgmt:BackupFsmStage:stageStatus managed
        object property"
    ::= { cucsMgmtBackupFsmStageEntry 9 }

cucsMgmtBackupFsmTaskTable OBJECT-TYPE
    SYNTAX           SEQUENCE OF CucsMgmtBackupFsmTaskEntry
    MAX-ACCESS       not-accessible
    STATUS           current
    DESCRIPTION
        "Cisco UCS mgmt:BackupFsmTask managed object table"
    ::= { cucsMgmtObjects 5 }

cucsMgmtBackupFsmTaskEntry OBJECT-TYPE
    SYNTAX           CucsMgmtBackupFsmTaskEntry
    MAX-ACCESS       not-accessible
    STATUS           current
    DESCRIPTION
        "Entry for the cucsMgmtBackupFsmTaskTable table."
    INDEX { cucsMgmtBackupFsmTaskInstanceId }
    ::= { cucsMgmtBackupFsmTaskTable 1 }

CucsMgmtBackupFsmTaskEntry ::= SEQUENCE {
    cucsMgmtBackupFsmTaskInstanceId                                  CucsManagedObjectId,
    cucsMgmtBackupFsmTaskDn                                          CucsManagedObjectDn,
    cucsMgmtBackupFsmTaskRn                                          SnmpAdminString,
    cucsMgmtBackupFsmTaskCompletion                                  CucsFsmCompletion,
    cucsMgmtBackupFsmTaskFlags                                       CucsFsmFlags,
    cucsMgmtBackupFsmTaskItem                                        CucsMgmtBackupFsmTaskItem,
    cucsMgmtBackupFsmTaskSeqId                                       Gauge32
}

cucsMgmtBackupFsmTaskInstanceId OBJECT-TYPE
    SYNTAX       CucsManagedObjectId
    MAX-ACCESS   not-accessible
    STATUS       current
    DESCRIPTION
        "Instance identifier of the managed object."
    ::= { cucsMgmtBackupFsmTaskEntry 1 }

cucsMgmtBackupFsmTaskDn OBJECT-TYPE
    SYNTAX       CucsManagedObjectDn
    MAX-ACCESS   read-only
    STATUS       current
    DESCRIPTION
        "Cisco UCS mgmt:BackupFsmTask:dn managed object property"
    ::= { cucsMgmtBackupFsmTaskEntry 2 }

cucsMgmtBackupFsmTaskRn OBJECT-TYPE
    SYNTAX       SnmpAdminString
    MAX-ACCESS   read-only
    STATUS       current
    DESCRIPTION
        "Cisco UCS mgmt:BackupFsmTask:rn managed object property"
    ::= { cucsMgmtBackupFsmTaskEntry 3 }

cucsMgmtBackupFsmTaskCompletion OBJECT-TYPE
    SYNTAX       CucsFsmCompletion
    MAX-ACCESS   read-only
    STATUS       current
    DESCRIPTION
        "Cisco UCS mgmt:BackupFsmTask:completion managed object property"
    ::= { cucsMgmtBackupFsmTaskEntry 4 }

cucsMgmtBackupFsmTaskFlags OBJECT-TYPE
    SYNTAX       CucsFsmFlags
    MAX-ACCESS   read-only
    STATUS       current
    DESCRIPTION
        "Cisco UCS mgmt:BackupFsmTask:flags managed object property"
    ::= { cucsMgmtBackupFsmTaskEntry 5 }

cucsMgmtBackupFsmTaskItem OBJECT-TYPE
    SYNTAX       CucsMgmtBackupFsmTaskItem
    MAX-ACCESS   read-only
    STATUS       current
    DESCRIPTION
        "Cisco UCS mgmt:BackupFsmTask:item managed object property"
    ::= { cucsMgmtBackupFsmTaskEntry 6 }

cucsMgmtBackupFsmTaskSeqId OBJECT-TYPE
    SYNTAX       Gauge32
    MAX-ACCESS   read-only
    STATUS       current
    DESCRIPTION
        "Cisco UCS mgmt:BackupFsmTask:seqId managed object property"
    ::= { cucsMgmtBackupFsmTaskEntry 7 }

cucsMgmtBackupPolicyTable OBJECT-TYPE
    SYNTAX           SEQUENCE OF CucsMgmtBackupPolicyEntry
    MAX-ACCESS       not-accessible
    STATUS           current
    DESCRIPTION
        "Cisco UCS mgmt:BackupPolicy managed object table"
    ::= { cucsMgmtObjects 17 }

cucsMgmtBackupPolicyEntry OBJECT-TYPE
    SYNTAX           CucsMgmtBackupPolicyEntry
    MAX-ACCESS       not-accessible
    STATUS           current
    DESCRIPTION
        "Entry for the cucsMgmtBackupPolicyTable table."
    INDEX { cucsMgmtBackupPolicyInstanceId }
    ::= { cucsMgmtBackupPolicyTable 1 }

CucsMgmtBackupPolicyEntry ::= SEQUENCE {
    cucsMgmtBackupPolicyInstanceId                                   CucsManagedObjectId,
    cucsMgmtBackupPolicyDn                                           CucsManagedObjectDn,
    cucsMgmtBackupPolicyRn                                           SnmpAdminString,
    cucsMgmtBackupPolicyAdminState                                   CucsMgmtExportPolicyAdminState,
    cucsMgmtBackupPolicyDescr                                        SnmpAdminString,
    cucsMgmtBackupPolicyFsmDescr                                     SnmpAdminString,
    cucsMgmtBackupPolicyFsmPrev                                      SnmpAdminString,
    cucsMgmtBackupPolicyFsmProgr                                     Gauge32,
    cucsMgmtBackupPolicyFsmRmtInvErrCode                             Gauge32,
    cucsMgmtBackupPolicyFsmRmtInvErrDescr                            SnmpAdminString,
    cucsMgmtBackupPolicyFsmRmtInvRslt                                CucsConditionRemoteInvRslt,
    cucsMgmtBackupPolicyFsmStageDescr                                SnmpAdminString,
    cucsMgmtBackupPolicyFsmStamp                                     DateAndTime,
    cucsMgmtBackupPolicyFsmStatus                                    SnmpAdminString,
    cucsMgmtBackupPolicyFsmTry                                       Gauge32,
    cucsMgmtBackupPolicyHost                                         SnmpAdminString,
    cucsMgmtBackupPolicyIntId                                        SnmpAdminString,
    cucsMgmtBackupPolicyLastBackup                                   DateAndTime,
    cucsMgmtBackupPolicyMaxFiles                                     Gauge32,
    cucsMgmtBackupPolicyName                                         SnmpAdminString,
    cucsMgmtBackupPolicyPolicyLevel                                  Gauge32,
    cucsMgmtBackupPolicyPolicyOwner                                  CucsPolicyPolicyOwner,
    cucsMgmtBackupPolicyProto                                        CucsMgmtExportPolicyProto,
    cucsMgmtBackupPolicyPwd                                          SnmpAdminString,
    cucsMgmtBackupPolicyRemoteFile                                   SnmpAdminString,
    cucsMgmtBackupPolicySchedule                                     CucsMgmtBackupInterval,
    cucsMgmtBackupPolicyUser                                         SnmpAdminString
}

cucsMgmtBackupPolicyInstanceId OBJECT-TYPE
    SYNTAX       CucsManagedObjectId
    MAX-ACCESS   not-accessible
    STATUS       current
    DESCRIPTION
        "Instance identifier of the managed object."
    ::= { cucsMgmtBackupPolicyEntry 1 }

cucsMgmtBackupPolicyDn OBJECT-TYPE
    SYNTAX       CucsManagedObjectDn
    MAX-ACCESS   read-only
    STATUS       current
    DESCRIPTION
        "Cisco UCS mgmt:BackupPolicy:dn managed object property"
    ::= { cucsMgmtBackupPolicyEntry 2 }

cucsMgmtBackupPolicyRn OBJECT-TYPE
    SYNTAX       SnmpAdminString
    MAX-ACCESS   read-only
    STATUS       current
    DESCRIPTION
        "Cisco UCS mgmt:BackupPolicy:rn managed object property"
    ::= { cucsMgmtBackupPolicyEntry 3 }

cucsMgmtBackupPolicyAdminState OBJECT-TYPE
    SYNTAX       CucsMgmtExportPolicyAdminState
    MAX-ACCESS   read-only
    STATUS       current
    DESCRIPTION
        "Cisco UCS mgmt:BackupPolicy:adminState managed object property"
    ::= { cucsMgmtBackupPolicyEntry 4 }

cucsMgmtBackupPolicyDescr OBJECT-TYPE
    SYNTAX       SnmpAdminString
    MAX-ACCESS   read-only
    STATUS       current
    DESCRIPTION
        "Cisco UCS mgmt:BackupPolicy:descr managed object property"
    ::= { cucsMgmtBackupPolicyEntry 5 }

cucsMgmtBackupPolicyFsmDescr OBJECT-TYPE
    SYNTAX       SnmpAdminString
    MAX-ACCESS   read-only
    STATUS       current
    DESCRIPTION
        "Cisco UCS mgmt:BackupPolicy:fsmDescr managed object property"
    ::= { cucsMgmtBackupPolicyEntry 6 }

cucsMgmtBackupPolicyFsmPrev OBJECT-TYPE
    SYNTAX       SnmpAdminString
    MAX-ACCESS   read-only
    STATUS       current
    DESCRIPTION
        "Cisco UCS mgmt:BackupPolicy:fsmPrev managed object property"
    ::= { cucsMgmtBackupPolicyEntry 7 }

cucsMgmtBackupPolicyFsmProgr OBJECT-TYPE
    SYNTAX       Gauge32
    MAX-ACCESS   read-only
    STATUS       current
    DESCRIPTION
        "Cisco UCS mgmt:BackupPolicy:fsmProgr managed object property"
    ::= { cucsMgmtBackupPolicyEntry 8 }

cucsMgmtBackupPolicyFsmRmtInvErrCode OBJECT-TYPE
    SYNTAX       Gauge32
    MAX-ACCESS   read-only
    STATUS       current
    DESCRIPTION
        "Cisco UCS mgmt:BackupPolicy:fsmRmtInvErrCode managed
        object property"
    ::= { cucsMgmtBackupPolicyEntry 9 }

cucsMgmtBackupPolicyFsmRmtInvErrDescr OBJECT-TYPE
    SYNTAX       SnmpAdminString
    MAX-ACCESS   read-only
    STATUS       current
    DESCRIPTION
        "Cisco UCS mgmt:BackupPolicy:fsmRmtInvErrDescr
        managed object property"
    ::= { cucsMgmtBackupPolicyEntry 10 }

cucsMgmtBackupPolicyFsmRmtInvRslt OBJECT-TYPE
    SYNTAX       CucsConditionRemoteInvRslt
    MAX-ACCESS   read-only
    STATUS       current
    DESCRIPTION
        "Cisco UCS mgmt:BackupPolicy:fsmRmtInvRslt managed
        object property"
    ::= { cucsMgmtBackupPolicyEntry 11 }

cucsMgmtBackupPolicyFsmStageDescr OBJECT-TYPE
    SYNTAX       SnmpAdminString
    MAX-ACCESS   read-only
    STATUS       current
    DESCRIPTION
        "Cisco UCS mgmt:BackupPolicy:fsmStageDescr managed
        object property"
    ::= { cucsMgmtBackupPolicyEntry 12 }

cucsMgmtBackupPolicyFsmStamp OBJECT-TYPE
    SYNTAX       DateAndTime
    MAX-ACCESS   read-only
    STATUS       current
    DESCRIPTION
        "Cisco UCS mgmt:BackupPolicy:fsmStamp managed object property"
    ::= { cucsMgmtBackupPolicyEntry 13 }

cucsMgmtBackupPolicyFsmStatus OBJECT-TYPE
    SYNTAX       SnmpAdminString
    MAX-ACCESS   read-only
    STATUS       current
    DESCRIPTION
        "Cisco UCS mgmt:BackupPolicy:fsmStatus managed object property"
    ::= { cucsMgmtBackupPolicyEntry 14 }

cucsMgmtBackupPolicyFsmTry OBJECT-TYPE
    SYNTAX       Gauge32
    MAX-ACCESS   read-only
    STATUS       current
    DESCRIPTION
        "Cisco UCS mgmt:BackupPolicy:fsmTry managed object property"
    ::= { cucsMgmtBackupPolicyEntry 15 }

cucsMgmtBackupPolicyHost OBJECT-TYPE
    SYNTAX       SnmpAdminString
    MAX-ACCESS   read-only
    STATUS       current
    DESCRIPTION
        "Cisco UCS mgmt:BackupPolicy:host managed object property"
    ::= { cucsMgmtBackupPolicyEntry 16 }

cucsMgmtBackupPolicyIntId OBJECT-TYPE
    SYNTAX       SnmpAdminString
    MAX-ACCESS   read-only
    STATUS       current
    DESCRIPTION
        "Cisco UCS mgmt:BackupPolicy:intId managed object property"
    ::= { cucsMgmtBackupPolicyEntry 17 }

cucsMgmtBackupPolicyLastBackup OBJECT-TYPE
    SYNTAX       DateAndTime
    MAX-ACCESS   read-only
    STATUS       current
    DESCRIPTION
        "Cisco UCS mgmt:BackupPolicy:lastBackup managed object property"
    ::= { cucsMgmtBackupPolicyEntry 18 }

cucsMgmtBackupPolicyMaxFiles OBJECT-TYPE
    SYNTAX       Gauge32
    MAX-ACCESS   read-only
    STATUS       current
    DESCRIPTION
        "Cisco UCS mgmt:BackupPolicy:maxFiles managed object property"
    ::= { cucsMgmtBackupPolicyEntry 19 }

cucsMgmtBackupPolicyName OBJECT-TYPE
    SYNTAX       SnmpAdminString
    MAX-ACCESS   read-only
    STATUS       current
    DESCRIPTION
        "Cisco UCS mgmt:BackupPolicy:name managed object property"
    ::= { cucsMgmtBackupPolicyEntry 20 }

cucsMgmtBackupPolicyPolicyLevel OBJECT-TYPE
    SYNTAX       Gauge32
    MAX-ACCESS   read-only
    STATUS       current
    DESCRIPTION
        "Cisco UCS mgmt:BackupPolicy:policyLevel managed object property"
    ::= { cucsMgmtBackupPolicyEntry 21 }

cucsMgmtBackupPolicyPolicyOwner OBJECT-TYPE
    SYNTAX       CucsPolicyPolicyOwner
    MAX-ACCESS   read-only
    STATUS       current
    DESCRIPTION
        "Cisco UCS mgmt:BackupPolicy:policyOwner managed object property"
    ::= { cucsMgmtBackupPolicyEntry 22 }

cucsMgmtBackupPolicyProto OBJECT-TYPE
    SYNTAX       CucsMgmtExportPolicyProto
    MAX-ACCESS   read-only
    STATUS       current
    DESCRIPTION
        "Cisco UCS mgmt:BackupPolicy:proto managed object property"
    ::= { cucsMgmtBackupPolicyEntry 23 }

cucsMgmtBackupPolicyPwd OBJECT-TYPE
    SYNTAX       SnmpAdminString
    MAX-ACCESS   read-only
    STATUS       current
    DESCRIPTION
        "Cisco UCS mgmt:BackupPolicy:pwd managed object property"
    ::= { cucsMgmtBackupPolicyEntry 24 }

cucsMgmtBackupPolicyRemoteFile OBJECT-TYPE
    SYNTAX       SnmpAdminString
    MAX-ACCESS   read-only
    STATUS       current
    DESCRIPTION
        "Cisco UCS mgmt:BackupPolicy:remoteFile managed object property"
    ::= { cucsMgmtBackupPolicyEntry 25 }

cucsMgmtBackupPolicySchedule OBJECT-TYPE
    SYNTAX       CucsMgmtBackupInterval
    MAX-ACCESS   read-only
    STATUS       current
    DESCRIPTION
        "Cisco UCS mgmt:BackupPolicy:schedule managed object property"
    ::= { cucsMgmtBackupPolicyEntry 26 }

cucsMgmtBackupPolicyUser OBJECT-TYPE
    SYNTAX       SnmpAdminString
    MAX-ACCESS   read-only
    STATUS       current
    DESCRIPTION
        "Cisco UCS mgmt:BackupPolicy:user managed object property"
    ::= { cucsMgmtBackupPolicyEntry 27 }

cucsMgmtBackupPolicyConfigTable OBJECT-TYPE
    SYNTAX           SEQUENCE OF CucsMgmtBackupPolicyConfigEntry
    MAX-ACCESS       not-accessible
    STATUS           current
    DESCRIPTION
        "Cisco UCS mgmt:BackupPolicyConfig managed object table"
    ::= { cucsMgmtObjects 43 }

cucsMgmtBackupPolicyConfigEntry OBJECT-TYPE
    SYNTAX           CucsMgmtBackupPolicyConfigEntry
    MAX-ACCESS       not-accessible
    STATUS           current
    DESCRIPTION
        "Entry for the cucsMgmtBackupPolicyConfigTable table."
    INDEX { cucsMgmtBackupPolicyConfigInstanceId }
    ::= { cucsMgmtBackupPolicyConfigTable 1 }

CucsMgmtBackupPolicyConfigEntry ::= SEQUENCE {
    cucsMgmtBackupPolicyConfigInstanceId                             CucsManagedObjectId,
    cucsMgmtBackupPolicyConfigDn                                     CucsManagedObjectDn,
    cucsMgmtBackupPolicyConfigRn                                     SnmpAdminString,
    cucsMgmtBackupPolicyConfigAdminState                             CucsTrigAdminState,
    cucsMgmtBackupPolicyConfigAutoDelete                             TruthValue,
    cucsMgmtBackupPolicyConfigBackupDate                             DateAndTime,
    cucsMgmtBackupPolicyConfigBackupIssue                            CucsMgmtBackupIssue,
    cucsMgmtBackupPolicyConfigDescr                                  SnmpAdminString,
    cucsMgmtBackupPolicyConfigIgnoreCap                              TruthValue,
    cucsMgmtBackupPolicyConfigIntId                                  SnmpAdminString,
    cucsMgmtBackupPolicyConfigName                                   SnmpAdminString,
    cucsMgmtBackupPolicyConfigOperScheduler                          SnmpAdminString,
    cucsMgmtBackupPolicyConfigOperState                              CucsTrigTrigOperState,
    cucsMgmtBackupPolicyConfigPolicyLevel                            Gauge32,
    cucsMgmtBackupPolicyConfigPolicyOwner                            CucsPolicyPolicyOwner,
    cucsMgmtBackupPolicyConfigScheduler                              SnmpAdminString
}

cucsMgmtBackupPolicyConfigInstanceId OBJECT-TYPE
    SYNTAX       CucsManagedObjectId
    MAX-ACCESS   not-accessible
    STATUS       current
    DESCRIPTION
        "Instance identifier of the managed object."
    ::= { cucsMgmtBackupPolicyConfigEntry 1 }

cucsMgmtBackupPolicyConfigDn OBJECT-TYPE
    SYNTAX       CucsManagedObjectDn
    MAX-ACCESS   read-only
    STATUS       current
    DESCRIPTION
        "Cisco UCS mgmt:BackupPolicyConfig:dn managed object property"
    ::= { cucsMgmtBackupPolicyConfigEntry 2 }

cucsMgmtBackupPolicyConfigRn OBJECT-TYPE
    SYNTAX       SnmpAdminString
    MAX-ACCESS   read-only
    STATUS       current
    DESCRIPTION
        "Cisco UCS mgmt:BackupPolicyConfig:rn managed object property"
    ::= { cucsMgmtBackupPolicyConfigEntry 3 }

cucsMgmtBackupPolicyConfigAdminState OBJECT-TYPE
    SYNTAX       CucsTrigAdminState
    MAX-ACCESS   read-only
    STATUS       current
    DESCRIPTION
        "Cisco UCS mgmt:BackupPolicyConfig:adminState managed
        object property"
    ::= { cucsMgmtBackupPolicyConfigEntry 4 }

cucsMgmtBackupPolicyConfigAutoDelete OBJECT-TYPE
    SYNTAX       TruthValue
    MAX-ACCESS   read-only
    STATUS       current
    DESCRIPTION
        "Cisco UCS mgmt:BackupPolicyConfig:autoDelete managed
        object property"
    ::= { cucsMgmtBackupPolicyConfigEntry 5 }

cucsMgmtBackupPolicyConfigBackupDate OBJECT-TYPE
    SYNTAX       DateAndTime
    MAX-ACCESS   read-only
    STATUS       current
    DESCRIPTION
        "Cisco UCS mgmt:BackupPolicyConfig:backupDate managed
        object property"
    ::= { cucsMgmtBackupPolicyConfigEntry 6 }

cucsMgmtBackupPolicyConfigBackupIssue OBJECT-TYPE
    SYNTAX       CucsMgmtBackupIssue
    MAX-ACCESS   read-only
    STATUS       current
    DESCRIPTION
        "Cisco UCS mgmt:BackupPolicyConfig:backupIssue
        managed object property"
    ::= { cucsMgmtBackupPolicyConfigEntry 7 }

cucsMgmtBackupPolicyConfigDescr OBJECT-TYPE
    SYNTAX       SnmpAdminString
    MAX-ACCESS   read-only
    STATUS       current
    DESCRIPTION
        "Cisco UCS mgmt:BackupPolicyConfig:descr managed object property"
    ::= { cucsMgmtBackupPolicyConfigEntry 8 }

cucsMgmtBackupPolicyConfigIgnoreCap OBJECT-TYPE
    SYNTAX       TruthValue
    MAX-ACCESS   read-only
    STATUS       current
    DESCRIPTION
        "Cisco UCS mgmt:BackupPolicyConfig:ignoreCap managed
        object property"
    ::= { cucsMgmtBackupPolicyConfigEntry 9 }

cucsMgmtBackupPolicyConfigIntId OBJECT-TYPE
    SYNTAX       SnmpAdminString
    MAX-ACCESS   read-only
    STATUS       current
    DESCRIPTION
        "Cisco UCS mgmt:BackupPolicyConfig:intId managed object property"
    ::= { cucsMgmtBackupPolicyConfigEntry 10 }

cucsMgmtBackupPolicyConfigName OBJECT-TYPE
    SYNTAX       SnmpAdminString
    MAX-ACCESS   read-only
    STATUS       current
    DESCRIPTION
        "Cisco UCS mgmt:BackupPolicyConfig:name managed object property"
    ::= { cucsMgmtBackupPolicyConfigEntry 11 }

cucsMgmtBackupPolicyConfigOperScheduler OBJECT-TYPE
    SYNTAX       SnmpAdminString
    MAX-ACCESS   read-only
    STATUS       current
    DESCRIPTION
        "Cisco UCS mgmt:BackupPolicyConfig:operScheduler
        managed object property"
    ::= { cucsMgmtBackupPolicyConfigEntry 12 }

cucsMgmtBackupPolicyConfigOperState OBJECT-TYPE
    SYNTAX       CucsTrigTrigOperState
    MAX-ACCESS   read-only
    STATUS       current
    DESCRIPTION
        "Cisco UCS mgmt:BackupPolicyConfig:operState managed
        object property"
    ::= { cucsMgmtBackupPolicyConfigEntry 13 }

cucsMgmtBackupPolicyConfigPolicyLevel OBJECT-TYPE
    SYNTAX       Gauge32
    MAX-ACCESS   read-only
    STATUS       current
    DESCRIPTION
        "Cisco UCS mgmt:BackupPolicyConfig:policyLevel
        managed object property"
    ::= { cucsMgmtBackupPolicyConfigEntry 14 }

cucsMgmtBackupPolicyConfigPolicyOwner OBJECT-TYPE
    SYNTAX       CucsPolicyPolicyOwner
    MAX-ACCESS   read-only
    STATUS       current
    DESCRIPTION
        "Cisco UCS mgmt:BackupPolicyConfig:policyOwner
        managed object property"
    ::= { cucsMgmtBackupPolicyConfigEntry 15 }

cucsMgmtBackupPolicyConfigScheduler OBJECT-TYPE
    SYNTAX       SnmpAdminString
    MAX-ACCESS   read-only
    STATUS       current
    DESCRIPTION
        "Cisco UCS mgmt:BackupPolicyConfig:scheduler managed
        object property"
    ::= { cucsMgmtBackupPolicyConfigEntry 16 }

cucsMgmtBackupPolicyFsmTable OBJECT-TYPE
    SYNTAX           SEQUENCE OF CucsMgmtBackupPolicyFsmEntry
    MAX-ACCESS       not-accessible
    STATUS           current
    DESCRIPTION
        "Cisco UCS mgmt:BackupPolicyFsm managed object table"
    ::= { cucsMgmtObjects 18 }

cucsMgmtBackupPolicyFsmEntry OBJECT-TYPE
    SYNTAX           CucsMgmtBackupPolicyFsmEntry
    MAX-ACCESS       not-accessible
    STATUS           current
    DESCRIPTION
        "Entry for the cucsMgmtBackupPolicyFsmTable table."
    INDEX { cucsMgmtBackupPolicyFsmInstanceId }
    ::= { cucsMgmtBackupPolicyFsmTable 1 }

CucsMgmtBackupPolicyFsmEntry ::= SEQUENCE {
    cucsMgmtBackupPolicyFsmInstanceId                                CucsManagedObjectId,
    cucsMgmtBackupPolicyFsmDn                                        CucsManagedObjectDn,
    cucsMgmtBackupPolicyFsmRn                                        SnmpAdminString,
    cucsMgmtBackupPolicyFsmCompletionTime                            DateAndTime,
    cucsMgmtBackupPolicyFsmCurrentFsm                                CucsMgmtBackupPolicyFsmCurrentFsm,
    cucsMgmtBackupPolicyFsmDescrData                                 SnmpAdminString,
    cucsMgmtBackupPolicyFsmFsmStatus                                 CucsFsmFsmStageStatus,
    cucsMgmtBackupPolicyFsmProgress                                  Gauge32,
    cucsMgmtBackupPolicyFsmRmtErrCode                                Gauge32,
    cucsMgmtBackupPolicyFsmRmtErrDescr                               SnmpAdminString,
    cucsMgmtBackupPolicyFsmRmtRslt                                   CucsConditionRemoteInvRslt
}

cucsMgmtBackupPolicyFsmInstanceId OBJECT-TYPE
    SYNTAX       CucsManagedObjectId
    MAX-ACCESS   not-accessible
    STATUS       current
    DESCRIPTION
        "Instance identifier of the managed object."
    ::= { cucsMgmtBackupPolicyFsmEntry 1 }

cucsMgmtBackupPolicyFsmDn OBJECT-TYPE
    SYNTAX       CucsManagedObjectDn
    MAX-ACCESS   read-only
    STATUS       current
    DESCRIPTION
        "Cisco UCS mgmt:BackupPolicyFsm:dn managed object property"
    ::= { cucsMgmtBackupPolicyFsmEntry 2 }

cucsMgmtBackupPolicyFsmRn OBJECT-TYPE
    SYNTAX       SnmpAdminString
    MAX-ACCESS   read-only
    STATUS       current
    DESCRIPTION
        "Cisco UCS mgmt:BackupPolicyFsm:rn managed object property"
    ::= { cucsMgmtBackupPolicyFsmEntry 3 }

cucsMgmtBackupPolicyFsmCompletionTime OBJECT-TYPE
    SYNTAX       DateAndTime
    MAX-ACCESS   read-only
    STATUS       current
    DESCRIPTION
        "Cisco UCS mgmt:BackupPolicyFsm:completionTime
        managed object property"
    ::= { cucsMgmtBackupPolicyFsmEntry 4 }

cucsMgmtBackupPolicyFsmCurrentFsm OBJECT-TYPE
    SYNTAX       CucsMgmtBackupPolicyFsmCurrentFsm
    MAX-ACCESS   read-only
    STATUS       current
    DESCRIPTION
        "Cisco UCS mgmt:BackupPolicyFsm:currentFsm managed
        object property"
    ::= { cucsMgmtBackupPolicyFsmEntry 5 }

cucsMgmtBackupPolicyFsmDescrData OBJECT-TYPE
    SYNTAX       SnmpAdminString
    MAX-ACCESS   read-only
    STATUS       current
    DESCRIPTION
        "Cisco UCS mgmt:BackupPolicyFsm:descr managed object property"
    ::= { cucsMgmtBackupPolicyFsmEntry 6 }

cucsMgmtBackupPolicyFsmFsmStatus OBJECT-TYPE
    SYNTAX       CucsFsmFsmStageStatus
    MAX-ACCESS   read-only
    STATUS       current
    DESCRIPTION
        "Cisco UCS mgmt:BackupPolicyFsm:fsmStatus managed object property"
    ::= { cucsMgmtBackupPolicyFsmEntry 7 }

cucsMgmtBackupPolicyFsmProgress OBJECT-TYPE
    SYNTAX       Gauge32
    MAX-ACCESS   read-only
    STATUS       current
    DESCRIPTION
        "Cisco UCS mgmt:BackupPolicyFsm:progress managed object property"
    ::= { cucsMgmtBackupPolicyFsmEntry 8 }

cucsMgmtBackupPolicyFsmRmtErrCode OBJECT-TYPE
    SYNTAX       Gauge32
    MAX-ACCESS   read-only
    STATUS       current
    DESCRIPTION
        "Cisco UCS mgmt:BackupPolicyFsm:rmtErrCode managed
        object property"
    ::= { cucsMgmtBackupPolicyFsmEntry 9 }

cucsMgmtBackupPolicyFsmRmtErrDescr OBJECT-TYPE
    SYNTAX       SnmpAdminString
    MAX-ACCESS   read-only
    STATUS       current
    DESCRIPTION
        "Cisco UCS mgmt:BackupPolicyFsm:rmtErrDescr managed
        object property"
    ::= { cucsMgmtBackupPolicyFsmEntry 10 }

cucsMgmtBackupPolicyFsmRmtRslt OBJECT-TYPE
    SYNTAX       CucsConditionRemoteInvRslt
    MAX-ACCESS   read-only
    STATUS       current
    DESCRIPTION
        "Cisco UCS mgmt:BackupPolicyFsm:rmtRslt managed object property"
    ::= { cucsMgmtBackupPolicyFsmEntry 11 }

cucsMgmtBackupPolicyFsmStageTable OBJECT-TYPE
    SYNTAX           SEQUENCE OF CucsMgmtBackupPolicyFsmStageEntry
    MAX-ACCESS       not-accessible
    STATUS           current
    DESCRIPTION
        "Cisco UCS mgmt:BackupPolicyFsmStage managed object table"
    ::= { cucsMgmtObjects 19 }

cucsMgmtBackupPolicyFsmStageEntry OBJECT-TYPE
    SYNTAX           CucsMgmtBackupPolicyFsmStageEntry
    MAX-ACCESS       not-accessible
    STATUS           current
    DESCRIPTION
        "Entry for the cucsMgmtBackupPolicyFsmStageTable table."
    INDEX { cucsMgmtBackupPolicyFsmStageInstanceId }
    ::= { cucsMgmtBackupPolicyFsmStageTable 1 }

CucsMgmtBackupPolicyFsmStageEntry ::= SEQUENCE {
    cucsMgmtBackupPolicyFsmStageInstanceId                           CucsManagedObjectId,
    cucsMgmtBackupPolicyFsmStageDn                                   CucsManagedObjectDn,
    cucsMgmtBackupPolicyFsmStageRn                                   SnmpAdminString,
    cucsMgmtBackupPolicyFsmStageDescrData                            SnmpAdminString,
    cucsMgmtBackupPolicyFsmStageLastUpdateTime                       DateAndTime,
    cucsMgmtBackupPolicyFsmStageName                                 CucsMgmtBackupPolicyFsmStageName,
    cucsMgmtBackupPolicyFsmStageOrder                                Gauge32,
    cucsMgmtBackupPolicyFsmStageRetry                                Gauge32,
    cucsMgmtBackupPolicyFsmStageStageStatus                          CucsFsmFsmStageStatus
}

cucsMgmtBackupPolicyFsmStageInstanceId OBJECT-TYPE
    SYNTAX       CucsManagedObjectId
    MAX-ACCESS   not-accessible
    STATUS       current
    DESCRIPTION
        "Instance identifier of the managed object."
    ::= { cucsMgmtBackupPolicyFsmStageEntry 1 }

cucsMgmtBackupPolicyFsmStageDn OBJECT-TYPE
    SYNTAX       CucsManagedObjectDn
    MAX-ACCESS   read-only
    STATUS       current
    DESCRIPTION
        "Cisco UCS mgmt:BackupPolicyFsmStage:dn managed object property"
    ::= { cucsMgmtBackupPolicyFsmStageEntry 2 }

cucsMgmtBackupPolicyFsmStageRn OBJECT-TYPE
    SYNTAX       SnmpAdminString
    MAX-ACCESS   read-only
    STATUS       current
    DESCRIPTION
        "Cisco UCS mgmt:BackupPolicyFsmStage:rn managed object property"
    ::= { cucsMgmtBackupPolicyFsmStageEntry 3 }

cucsMgmtBackupPolicyFsmStageDescrData OBJECT-TYPE
    SYNTAX       SnmpAdminString
    MAX-ACCESS   read-only
    STATUS       current
    DESCRIPTION
        "Cisco UCS mgmt:BackupPolicyFsmStage:descr managed
        object property"
    ::= { cucsMgmtBackupPolicyFsmStageEntry 4 }

cucsMgmtBackupPolicyFsmStageLastUpdateTime OBJECT-TYPE
    SYNTAX       DateAndTime
    MAX-ACCESS   read-only
    STATUS       current
    DESCRIPTION
        "Cisco UCS mgmt:BackupPolicyFsmStage:lastUpdateTime
        managed object property"
    ::= { cucsMgmtBackupPolicyFsmStageEntry 5 }

cucsMgmtBackupPolicyFsmStageName OBJECT-TYPE
    SYNTAX       CucsMgmtBackupPolicyFsmStageName
    MAX-ACCESS   read-only
    STATUS       current
    DESCRIPTION
        "Cisco UCS mgmt:BackupPolicyFsmStage:name managed object property"
    ::= { cucsMgmtBackupPolicyFsmStageEntry 6 }

cucsMgmtBackupPolicyFsmStageOrder OBJECT-TYPE
    SYNTAX       Gauge32
    MAX-ACCESS   read-only
    STATUS       current
    DESCRIPTION
        "Cisco UCS mgmt:BackupPolicyFsmStage:order managed
        object property"
    ::= { cucsMgmtBackupPolicyFsmStageEntry 7 }

cucsMgmtBackupPolicyFsmStageRetry OBJECT-TYPE
    SYNTAX       Gauge32
    MAX-ACCESS   read-only
    STATUS       current
    DESCRIPTION
        "Cisco UCS mgmt:BackupPolicyFsmStage:retry managed
        object property"
    ::= { cucsMgmtBackupPolicyFsmStageEntry 8 }

cucsMgmtBackupPolicyFsmStageStageStatus OBJECT-TYPE
    SYNTAX       CucsFsmFsmStageStatus
    MAX-ACCESS   read-only
    STATUS       current
    DESCRIPTION
        "Cisco UCS mgmt:BackupPolicyFsmStage:stageStatus
        managed object property"
    ::= { cucsMgmtBackupPolicyFsmStageEntry 9 }

cucsMgmtCfgExportPolicyTable OBJECT-TYPE
    SYNTAX           SEQUENCE OF CucsMgmtCfgExportPolicyEntry
    MAX-ACCESS       not-accessible
    STATUS           current
    DESCRIPTION
        "Cisco UCS mgmt:CfgExportPolicy managed object table"
    ::= { cucsMgmtObjects 20 }

cucsMgmtCfgExportPolicyEntry OBJECT-TYPE
    SYNTAX           CucsMgmtCfgExportPolicyEntry
    MAX-ACCESS       not-accessible
    STATUS           current
    DESCRIPTION
        "Entry for the cucsMgmtCfgExportPolicyTable table."
    INDEX { cucsMgmtCfgExportPolicyInstanceId }
    ::= { cucsMgmtCfgExportPolicyTable 1 }

CucsMgmtCfgExportPolicyEntry ::= SEQUENCE {
    cucsMgmtCfgExportPolicyInstanceId                                CucsManagedObjectId,
    cucsMgmtCfgExportPolicyDn                                        CucsManagedObjectDn,
    cucsMgmtCfgExportPolicyRn                                        SnmpAdminString,
    cucsMgmtCfgExportPolicyAdminState                                CucsMgmtExportPolicyAdminState,
    cucsMgmtCfgExportPolicyDescr                                     SnmpAdminString,
    cucsMgmtCfgExportPolicyFsmDescr                                  SnmpAdminString,
    cucsMgmtCfgExportPolicyFsmPrev                                   SnmpAdminString,
    cucsMgmtCfgExportPolicyFsmProgr                                  Gauge32,
    cucsMgmtCfgExportPolicyFsmRmtInvErrCode                          Gauge32,
    cucsMgmtCfgExportPolicyFsmRmtInvErrDescr                         SnmpAdminString,
    cucsMgmtCfgExportPolicyFsmRmtInvRslt                             CucsConditionRemoteInvRslt,
    cucsMgmtCfgExportPolicyFsmStageDescr                             SnmpAdminString,
    cucsMgmtCfgExportPolicyFsmStamp                                  DateAndTime,
    cucsMgmtCfgExportPolicyFsmStatus                                 SnmpAdminString,
    cucsMgmtCfgExportPolicyFsmTry                                    Gauge32,
    cucsMgmtCfgExportPolicyHost                                      SnmpAdminString,
    cucsMgmtCfgExportPolicyIntId                                     SnmpAdminString,
    cucsMgmtCfgExportPolicyLastBackup                                DateAndTime,
    cucsMgmtCfgExportPolicyMaxFiles                                  Gauge32,
    cucsMgmtCfgExportPolicyName                                      SnmpAdminString,
    cucsMgmtCfgExportPolicyPolicyLevel                               Gauge32,
    cucsMgmtCfgExportPolicyPolicyOwner                               CucsPolicyPolicyOwner,
    cucsMgmtCfgExportPolicyProto                                     CucsMgmtExportPolicyProto,
    cucsMgmtCfgExportPolicyPwd                                       SnmpAdminString,
    cucsMgmtCfgExportPolicyRemoteFile                                SnmpAdminString,
    cucsMgmtCfgExportPolicySchedule                                  CucsMgmtBackupInterval,
    cucsMgmtCfgExportPolicyUser                                      SnmpAdminString
}

cucsMgmtCfgExportPolicyInstanceId OBJECT-TYPE
    SYNTAX       CucsManagedObjectId
    MAX-ACCESS   not-accessible
    STATUS       current
    DESCRIPTION
        "Instance identifier of the managed object."
    ::= { cucsMgmtCfgExportPolicyEntry 1 }

cucsMgmtCfgExportPolicyDn OBJECT-TYPE
    SYNTAX       CucsManagedObjectDn
    MAX-ACCESS   read-only
    STATUS       current
    DESCRIPTION
        "Cisco UCS mgmt:CfgExportPolicy:dn managed object property"
    ::= { cucsMgmtCfgExportPolicyEntry 2 }

cucsMgmtCfgExportPolicyRn OBJECT-TYPE
    SYNTAX       SnmpAdminString
    MAX-ACCESS   read-only
    STATUS       current
    DESCRIPTION
        "Cisco UCS mgmt:CfgExportPolicy:rn managed object property"
    ::= { cucsMgmtCfgExportPolicyEntry 3 }

cucsMgmtCfgExportPolicyAdminState OBJECT-TYPE
    SYNTAX       CucsMgmtExportPolicyAdminState
    MAX-ACCESS   read-only
    STATUS       current
    DESCRIPTION
        "Cisco UCS mgmt:CfgExportPolicy:adminState managed
        object property"
    ::= { cucsMgmtCfgExportPolicyEntry 4 }

cucsMgmtCfgExportPolicyDescr OBJECT-TYPE
    SYNTAX       SnmpAdminString
    MAX-ACCESS   read-only
    STATUS       current
    DESCRIPTION
        "Cisco UCS mgmt:CfgExportPolicy:descr managed object property"
    ::= { cucsMgmtCfgExportPolicyEntry 5 }

cucsMgmtCfgExportPolicyFsmDescr OBJECT-TYPE
    SYNTAX       SnmpAdminString
    MAX-ACCESS   read-only
    STATUS       current
    DESCRIPTION
        "Cisco UCS mgmt:CfgExportPolicy:fsmDescr managed object property"
    ::= { cucsMgmtCfgExportPolicyEntry 6 }

cucsMgmtCfgExportPolicyFsmPrev OBJECT-TYPE
    SYNTAX       SnmpAdminString
    MAX-ACCESS   read-only
    STATUS       current
    DESCRIPTION
        "Cisco UCS mgmt:CfgExportPolicy:fsmPrev managed object property"
    ::= { cucsMgmtCfgExportPolicyEntry 7 }

cucsMgmtCfgExportPolicyFsmProgr OBJECT-TYPE
    SYNTAX       Gauge32
    MAX-ACCESS   read-only
    STATUS       current
    DESCRIPTION
        "Cisco UCS mgmt:CfgExportPolicy:fsmProgr managed object property"
    ::= { cucsMgmtCfgExportPolicyEntry 8 }

cucsMgmtCfgExportPolicyFsmRmtInvErrCode OBJECT-TYPE
    SYNTAX       Gauge32
    MAX-ACCESS   read-only
    STATUS       current
    DESCRIPTION
        "Cisco UCS mgmt:CfgExportPolicy:fsmRmtInvErrCode
        managed object property"
    ::= { cucsMgmtCfgExportPolicyEntry 9 }

cucsMgmtCfgExportPolicyFsmRmtInvErrDescr OBJECT-TYPE
    SYNTAX       SnmpAdminString
    MAX-ACCESS   read-only
    STATUS       current
    DESCRIPTION
        "Cisco UCS mgmt:CfgExportPolicy:fsmRmtInvErrDescr
        managed object property"
    ::= { cucsMgmtCfgExportPolicyEntry 10 }

cucsMgmtCfgExportPolicyFsmRmtInvRslt OBJECT-TYPE
    SYNTAX       CucsConditionRemoteInvRslt
    MAX-ACCESS   read-only
    STATUS       current
    DESCRIPTION
        "Cisco UCS mgmt:CfgExportPolicy:fsmRmtInvRslt managed
        object property"
    ::= { cucsMgmtCfgExportPolicyEntry 11 }

cucsMgmtCfgExportPolicyFsmStageDescr OBJECT-TYPE
    SYNTAX       SnmpAdminString
    MAX-ACCESS   read-only
    STATUS       current
    DESCRIPTION
        "Cisco UCS mgmt:CfgExportPolicy:fsmStageDescr managed
        object property"
    ::= { cucsMgmtCfgExportPolicyEntry 12 }

cucsMgmtCfgExportPolicyFsmStamp OBJECT-TYPE
    SYNTAX       DateAndTime
    MAX-ACCESS   read-only
    STATUS       current
    DESCRIPTION
        "Cisco UCS mgmt:CfgExportPolicy:fsmStamp managed object property"
    ::= { cucsMgmtCfgExportPolicyEntry 13 }

cucsMgmtCfgExportPolicyFsmStatus OBJECT-TYPE
    SYNTAX       SnmpAdminString
    MAX-ACCESS   read-only
    STATUS       current
    DESCRIPTION
        "Cisco UCS mgmt:CfgExportPolicy:fsmStatus managed object property"
    ::= { cucsMgmtCfgExportPolicyEntry 14 }

cucsMgmtCfgExportPolicyFsmTry OBJECT-TYPE
    SYNTAX       Gauge32
    MAX-ACCESS   read-only
    STATUS       current
    DESCRIPTION
        "Cisco UCS mgmt:CfgExportPolicy:fsmTry managed object property"
    ::= { cucsMgmtCfgExportPolicyEntry 15 }

cucsMgmtCfgExportPolicyHost OBJECT-TYPE
    SYNTAX       SnmpAdminString
    MAX-ACCESS   read-only
    STATUS       current
    DESCRIPTION
        "Cisco UCS mgmt:CfgExportPolicy:host managed object property"
    ::= { cucsMgmtCfgExportPolicyEntry 16 }

cucsMgmtCfgExportPolicyIntId OBJECT-TYPE
    SYNTAX       SnmpAdminString
    MAX-ACCESS   read-only
    STATUS       current
    DESCRIPTION
        "Cisco UCS mgmt:CfgExportPolicy:intId managed object property"
    ::= { cucsMgmtCfgExportPolicyEntry 17 }

cucsMgmtCfgExportPolicyLastBackup OBJECT-TYPE
    SYNTAX       DateAndTime
    MAX-ACCESS   read-only
    STATUS       current
    DESCRIPTION
        "Cisco UCS mgmt:CfgExportPolicy:lastBackup managed
        object property"
    ::= { cucsMgmtCfgExportPolicyEntry 18 }

cucsMgmtCfgExportPolicyMaxFiles OBJECT-TYPE
    SYNTAX       Gauge32
    MAX-ACCESS   read-only
    STATUS       current
    DESCRIPTION
        "Cisco UCS mgmt:CfgExportPolicy:maxFiles managed object property"
    ::= { cucsMgmtCfgExportPolicyEntry 19 }

cucsMgmtCfgExportPolicyName OBJECT-TYPE
    SYNTAX       SnmpAdminString
    MAX-ACCESS   read-only
    STATUS       current
    DESCRIPTION
        "Cisco UCS mgmt:CfgExportPolicy:name managed object property"
    ::= { cucsMgmtCfgExportPolicyEntry 20 }

cucsMgmtCfgExportPolicyPolicyLevel OBJECT-TYPE
    SYNTAX       Gauge32
    MAX-ACCESS   read-only
    STATUS       current
    DESCRIPTION
        "Cisco UCS mgmt:CfgExportPolicy:policyLevel managed
        object property"
    ::= { cucsMgmtCfgExportPolicyEntry 21 }

cucsMgmtCfgExportPolicyPolicyOwner OBJECT-TYPE
    SYNTAX       CucsPolicyPolicyOwner
    MAX-ACCESS   read-only
    STATUS       current
    DESCRIPTION
        "Cisco UCS mgmt:CfgExportPolicy:policyOwner managed
        object property"
    ::= { cucsMgmtCfgExportPolicyEntry 22 }

cucsMgmtCfgExportPolicyProto OBJECT-TYPE
    SYNTAX       CucsMgmtExportPolicyProto
    MAX-ACCESS   read-only
    STATUS       current
    DESCRIPTION
        "Cisco UCS mgmt:CfgExportPolicy:proto managed object property"
    ::= { cucsMgmtCfgExportPolicyEntry 23 }

cucsMgmtCfgExportPolicyPwd OBJECT-TYPE
    SYNTAX       SnmpAdminString
    MAX-ACCESS   read-only
    STATUS       current
    DESCRIPTION
        "Cisco UCS mgmt:CfgExportPolicy:pwd managed object property"
    ::= { cucsMgmtCfgExportPolicyEntry 24 }

cucsMgmtCfgExportPolicyRemoteFile OBJECT-TYPE
    SYNTAX       SnmpAdminString
    MAX-ACCESS   read-only
    STATUS       current
    DESCRIPTION
        "Cisco UCS mgmt:CfgExportPolicy:remoteFile managed
        object property"
    ::= { cucsMgmtCfgExportPolicyEntry 25 }

cucsMgmtCfgExportPolicySchedule OBJECT-TYPE
    SYNTAX       CucsMgmtBackupInterval
    MAX-ACCESS   read-only
    STATUS       current
    DESCRIPTION
        "Cisco UCS mgmt:CfgExportPolicy:schedule managed object property"
    ::= { cucsMgmtCfgExportPolicyEntry 26 }

cucsMgmtCfgExportPolicyUser OBJECT-TYPE
    SYNTAX       SnmpAdminString
    MAX-ACCESS   read-only
    STATUS       current
    DESCRIPTION
        "Cisco UCS mgmt:CfgExportPolicy:user managed object property"
    ::= { cucsMgmtCfgExportPolicyEntry 27 }

cucsMgmtCfgExportPolicyFsmTable OBJECT-TYPE
    SYNTAX           SEQUENCE OF CucsMgmtCfgExportPolicyFsmEntry
    MAX-ACCESS       not-accessible
    STATUS           current
    DESCRIPTION
        "Cisco UCS mgmt:CfgExportPolicyFsm managed object table"
    ::= { cucsMgmtObjects 21 }

cucsMgmtCfgExportPolicyFsmEntry OBJECT-TYPE
    SYNTAX           CucsMgmtCfgExportPolicyFsmEntry
    MAX-ACCESS       not-accessible
    STATUS           current
    DESCRIPTION
        "Entry for the cucsMgmtCfgExportPolicyFsmTable table."
    INDEX { cucsMgmtCfgExportPolicyFsmInstanceId }
    ::= { cucsMgmtCfgExportPolicyFsmTable 1 }

CucsMgmtCfgExportPolicyFsmEntry ::= SEQUENCE {
    cucsMgmtCfgExportPolicyFsmInstanceId                             CucsManagedObjectId,
    cucsMgmtCfgExportPolicyFsmDn                                     CucsManagedObjectDn,
    cucsMgmtCfgExportPolicyFsmRn                                     SnmpAdminString,
    cucsMgmtCfgExportPolicyFsmCompletionTime                         DateAndTime,
    cucsMgmtCfgExportPolicyFsmCurrentFsm                             CucsMgmtCfgExportPolicyFsmCurrentFsm,
    cucsMgmtCfgExportPolicyFsmDescrData                              SnmpAdminString,
    cucsMgmtCfgExportPolicyFsmFsmStatus                              CucsFsmFsmStageStatus,
    cucsMgmtCfgExportPolicyFsmProgress                               Gauge32,
    cucsMgmtCfgExportPolicyFsmRmtErrCode                             Gauge32,
    cucsMgmtCfgExportPolicyFsmRmtErrDescr                            SnmpAdminString,
    cucsMgmtCfgExportPolicyFsmRmtRslt                                CucsConditionRemoteInvRslt
}

cucsMgmtCfgExportPolicyFsmInstanceId OBJECT-TYPE
    SYNTAX       CucsManagedObjectId
    MAX-ACCESS   not-accessible
    STATUS       current
    DESCRIPTION
        "Instance identifier of the managed object."
    ::= { cucsMgmtCfgExportPolicyFsmEntry 1 }

cucsMgmtCfgExportPolicyFsmDn OBJECT-TYPE
    SYNTAX       CucsManagedObjectDn
    MAX-ACCESS   read-only
    STATUS       current
    DESCRIPTION
        "Cisco UCS mgmt:CfgExportPolicyFsm:dn managed object property"
    ::= { cucsMgmtCfgExportPolicyFsmEntry 2 }

cucsMgmtCfgExportPolicyFsmRn OBJECT-TYPE
    SYNTAX       SnmpAdminString
    MAX-ACCESS   read-only
    STATUS       current
    DESCRIPTION
        "Cisco UCS mgmt:CfgExportPolicyFsm:rn managed object property"
    ::= { cucsMgmtCfgExportPolicyFsmEntry 3 }

cucsMgmtCfgExportPolicyFsmCompletionTime OBJECT-TYPE
    SYNTAX       DateAndTime
    MAX-ACCESS   read-only
    STATUS       current
    DESCRIPTION
        "Cisco UCS mgmt:CfgExportPolicyFsm:completionTime
        managed object property"
    ::= { cucsMgmtCfgExportPolicyFsmEntry 4 }

cucsMgmtCfgExportPolicyFsmCurrentFsm OBJECT-TYPE
    SYNTAX       CucsMgmtCfgExportPolicyFsmCurrentFsm
    MAX-ACCESS   read-only
    STATUS       current
    DESCRIPTION
        "Cisco UCS mgmt:CfgExportPolicyFsm:currentFsm managed
        object property"
    ::= { cucsMgmtCfgExportPolicyFsmEntry 5 }

cucsMgmtCfgExportPolicyFsmDescrData OBJECT-TYPE
    SYNTAX       SnmpAdminString
    MAX-ACCESS   read-only
    STATUS       current
    DESCRIPTION
        "Cisco UCS mgmt:CfgExportPolicyFsm:descr managed object property"
    ::= { cucsMgmtCfgExportPolicyFsmEntry 6 }

cucsMgmtCfgExportPolicyFsmFsmStatus OBJECT-TYPE
    SYNTAX       CucsFsmFsmStageStatus
    MAX-ACCESS   read-only
    STATUS       current
    DESCRIPTION
        "Cisco UCS mgmt:CfgExportPolicyFsm:fsmStatus managed
        object property"
    ::= { cucsMgmtCfgExportPolicyFsmEntry 7 }

cucsMgmtCfgExportPolicyFsmProgress OBJECT-TYPE
    SYNTAX       Gauge32
    MAX-ACCESS   read-only
    STATUS       current
    DESCRIPTION
        "Cisco UCS mgmt:CfgExportPolicyFsm:progress managed
        object property"
    ::= { cucsMgmtCfgExportPolicyFsmEntry 8 }

cucsMgmtCfgExportPolicyFsmRmtErrCode OBJECT-TYPE
    SYNTAX       Gauge32
    MAX-ACCESS   read-only
    STATUS       current
    DESCRIPTION
        "Cisco UCS mgmt:CfgExportPolicyFsm:rmtErrCode managed
        object property"
    ::= { cucsMgmtCfgExportPolicyFsmEntry 9 }

cucsMgmtCfgExportPolicyFsmRmtErrDescr OBJECT-TYPE
    SYNTAX       SnmpAdminString
    MAX-ACCESS   read-only
    STATUS       current
    DESCRIPTION
        "Cisco UCS mgmt:CfgExportPolicyFsm:rmtErrDescr
        managed object property"
    ::= { cucsMgmtCfgExportPolicyFsmEntry 10 }

cucsMgmtCfgExportPolicyFsmRmtRslt OBJECT-TYPE
    SYNTAX       CucsConditionRemoteInvRslt
    MAX-ACCESS   read-only
    STATUS       current
    DESCRIPTION
        "Cisco UCS mgmt:CfgExportPolicyFsm:rmtRslt managed
        object property"
    ::= { cucsMgmtCfgExportPolicyFsmEntry 11 }

cucsMgmtCfgExportPolicyFsmStageTable OBJECT-TYPE
    SYNTAX           SEQUENCE OF CucsMgmtCfgExportPolicyFsmStageEntry
    MAX-ACCESS       not-accessible
    STATUS           current
    DESCRIPTION
        "Cisco UCS mgmt:CfgExportPolicyFsmStage managed object table"
    ::= { cucsMgmtObjects 22 }

cucsMgmtCfgExportPolicyFsmStageEntry OBJECT-TYPE
    SYNTAX           CucsMgmtCfgExportPolicyFsmStageEntry
    MAX-ACCESS       not-accessible
    STATUS           current
    DESCRIPTION
        "Entry for the cucsMgmtCfgExportPolicyFsmStageTable table."
    INDEX { cucsMgmtCfgExportPolicyFsmStageInstanceId }
    ::= { cucsMgmtCfgExportPolicyFsmStageTable 1 }

CucsMgmtCfgExportPolicyFsmStageEntry ::= SEQUENCE {
    cucsMgmtCfgExportPolicyFsmStageInstanceId                        CucsManagedObjectId,
    cucsMgmtCfgExportPolicyFsmStageDn                                CucsManagedObjectDn,
    cucsMgmtCfgExportPolicyFsmStageRn                                SnmpAdminString,
    cucsMgmtCfgExportPolicyFsmStageDescrData                         SnmpAdminString,
    cucsMgmtCfgExportPolicyFsmStageLastUpdateTime                    DateAndTime,
    cucsMgmtCfgExportPolicyFsmStageName                              CucsMgmtCfgExportPolicyFsmStageName,
    cucsMgmtCfgExportPolicyFsmStageOrder                             Gauge32,
    cucsMgmtCfgExportPolicyFsmStageRetry                             Gauge32,
    cucsMgmtCfgExportPolicyFsmStageStageStatus                       CucsFsmFsmStageStatus
}

cucsMgmtCfgExportPolicyFsmStageInstanceId OBJECT-TYPE
    SYNTAX       CucsManagedObjectId
    MAX-ACCESS   not-accessible
    STATUS       current
    DESCRIPTION
        "Instance identifier of the managed object."
    ::= { cucsMgmtCfgExportPolicyFsmStageEntry 1 }

cucsMgmtCfgExportPolicyFsmStageDn OBJECT-TYPE
    SYNTAX       CucsManagedObjectDn
    MAX-ACCESS   read-only
    STATUS       current
    DESCRIPTION
        "Cisco UCS mgmt:CfgExportPolicyFsmStage:dn managed
        object property"
    ::= { cucsMgmtCfgExportPolicyFsmStageEntry 2 }

cucsMgmtCfgExportPolicyFsmStageRn OBJECT-TYPE
    SYNTAX       SnmpAdminString
    MAX-ACCESS   read-only
    STATUS       current
    DESCRIPTION
        "Cisco UCS mgmt:CfgExportPolicyFsmStage:rn managed
        object property"
    ::= { cucsMgmtCfgExportPolicyFsmStageEntry 3 }

cucsMgmtCfgExportPolicyFsmStageDescrData OBJECT-TYPE
    SYNTAX       SnmpAdminString
    MAX-ACCESS   read-only
    STATUS       current
    DESCRIPTION
        "Cisco UCS mgmt:CfgExportPolicyFsmStage:descr managed
        object property"
    ::= { cucsMgmtCfgExportPolicyFsmStageEntry 4 }

cucsMgmtCfgExportPolicyFsmStageLastUpdateTime OBJECT-TYPE
    SYNTAX       DateAndTime
    MAX-ACCESS   read-only
    STATUS       current
    DESCRIPTION
        "Cisco UCS mgmt:CfgExportPolicyFsmStage:lastUpdateTime
        managed object property"
    ::= { cucsMgmtCfgExportPolicyFsmStageEntry 5 }

cucsMgmtCfgExportPolicyFsmStageName OBJECT-TYPE
    SYNTAX       CucsMgmtCfgExportPolicyFsmStageName
    MAX-ACCESS   read-only
    STATUS       current
    DESCRIPTION
        "Cisco UCS mgmt:CfgExportPolicyFsmStage:name managed
        object property"
    ::= { cucsMgmtCfgExportPolicyFsmStageEntry 6 }

cucsMgmtCfgExportPolicyFsmStageOrder OBJECT-TYPE
    SYNTAX       Gauge32
    MAX-ACCESS   read-only
    STATUS       current
    DESCRIPTION
        "Cisco UCS mgmt:CfgExportPolicyFsmStage:order managed
        object property"
    ::= { cucsMgmtCfgExportPolicyFsmStageEntry 7 }

cucsMgmtCfgExportPolicyFsmStageRetry OBJECT-TYPE
    SYNTAX       Gauge32
    MAX-ACCESS   read-only
    STATUS       current
    DESCRIPTION
        "Cisco UCS mgmt:CfgExportPolicyFsmStage:retry managed
        object property"
    ::= { cucsMgmtCfgExportPolicyFsmStageEntry 8 }

cucsMgmtCfgExportPolicyFsmStageStageStatus OBJECT-TYPE
    SYNTAX       CucsFsmFsmStageStatus
    MAX-ACCESS   read-only
    STATUS       current
    DESCRIPTION
        "Cisco UCS mgmt:CfgExportPolicyFsmStage:stageStatus
        managed object property"
    ::= { cucsMgmtCfgExportPolicyFsmStageEntry 9 }

cucsMgmtCimcSecureBootTable OBJECT-TYPE
    SYNTAX           SEQUENCE OF CucsMgmtCimcSecureBootEntry
    MAX-ACCESS       not-accessible
    STATUS           current
    DESCRIPTION
        "Cisco UCS mgmt:CimcSecureBoot managed object table"
    ::= { cucsMgmtObjects 44 }

cucsMgmtCimcSecureBootEntry OBJECT-TYPE
    SYNTAX           CucsMgmtCimcSecureBootEntry
    MAX-ACCESS       not-accessible
    STATUS           current
    DESCRIPTION
        "Entry for the cucsMgmtCimcSecureBootTable table."
    INDEX { cucsMgmtCimcSecureBootInstanceId }
    ::= { cucsMgmtCimcSecureBootTable 1 }

CucsMgmtCimcSecureBootEntry ::= SEQUENCE {
    cucsMgmtCimcSecureBootInstanceId                                 CucsManagedObjectId,
    cucsMgmtCimcSecureBootDn                                         CucsManagedObjectDn,
    cucsMgmtCimcSecureBootRn                                         SnmpAdminString,
    cucsMgmtCimcSecureBootAdminState                                 CucsMgmtASecureBootAdminState,
    cucsMgmtCimcSecureBootOperState                                  CucsMgmtSecureBootOperState
}

cucsMgmtCimcSecureBootInstanceId OBJECT-TYPE
    SYNTAX       CucsManagedObjectId
    MAX-ACCESS   not-accessible
    STATUS       current
    DESCRIPTION
        "Instance identifier of the managed object."
    ::= { cucsMgmtCimcSecureBootEntry 1 }

cucsMgmtCimcSecureBootDn OBJECT-TYPE
    SYNTAX       CucsManagedObjectDn
    MAX-ACCESS   read-only
    STATUS       current
    DESCRIPTION
        "Cisco UCS mgmt:CimcSecureBoot:dn managed object property"
    ::= { cucsMgmtCimcSecureBootEntry 2 }

cucsMgmtCimcSecureBootRn OBJECT-TYPE
    SYNTAX       SnmpAdminString
    MAX-ACCESS   read-only
    STATUS       current
    DESCRIPTION
        "Cisco UCS mgmt:CimcSecureBoot:rn managed object property"
    ::= { cucsMgmtCimcSecureBootEntry 3 }

cucsMgmtCimcSecureBootAdminState OBJECT-TYPE
    SYNTAX       CucsMgmtASecureBootAdminState
    MAX-ACCESS   read-only
    STATUS       current
    DESCRIPTION
        "Cisco UCS mgmt:CimcSecureBoot:adminState managed object property"
    ::= { cucsMgmtCimcSecureBootEntry 4 }

cucsMgmtCimcSecureBootOperState OBJECT-TYPE
    SYNTAX       CucsMgmtSecureBootOperState
    MAX-ACCESS   read-only
    STATUS       current
    DESCRIPTION
        "Cisco UCS mgmt:CimcSecureBoot:operState managed object property"
    ::= { cucsMgmtCimcSecureBootEntry 5 }

cucsMgmtCmcSecureBootTable OBJECT-TYPE
    SYNTAX           SEQUENCE OF CucsMgmtCmcSecureBootEntry
    MAX-ACCESS       not-accessible
    STATUS           current
    DESCRIPTION
        "Cisco UCS mgmt:CmcSecureBoot managed object table"
    ::= { cucsMgmtObjects 69 }

cucsMgmtCmcSecureBootEntry OBJECT-TYPE
    SYNTAX           CucsMgmtCmcSecureBootEntry
    MAX-ACCESS       not-accessible
    STATUS           current
    DESCRIPTION
        "Entry for the cucsMgmtCmcSecureBootTable table."
    INDEX { cucsMgmtCmcSecureBootInstanceId }
    ::= { cucsMgmtCmcSecureBootTable 1 }

CucsMgmtCmcSecureBootEntry ::= SEQUENCE {
    cucsMgmtCmcSecureBootInstanceId                                  CucsManagedObjectId,
    cucsMgmtCmcSecureBootDn                                          CucsManagedObjectDn,
    cucsMgmtCmcSecureBootRn                                          SnmpAdminString,
    cucsMgmtCmcSecureBootAdminState                                  CucsMgmtASecureBootAdminState,
    cucsMgmtCmcSecureBootOperState                                   CucsMgmtSecureBootOperState
}

cucsMgmtCmcSecureBootInstanceId OBJECT-TYPE
    SYNTAX       CucsManagedObjectId
    MAX-ACCESS   not-accessible
    STATUS       current
    DESCRIPTION
        "Instance identifier of the managed object."
    ::= { cucsMgmtCmcSecureBootEntry 1 }

cucsMgmtCmcSecureBootDn OBJECT-TYPE
    SYNTAX       CucsManagedObjectDn
    MAX-ACCESS   read-only
    STATUS       current
    DESCRIPTION
        "Cisco UCS mgmt:CmcSecureBoot:dn managed object property"
    ::= { cucsMgmtCmcSecureBootEntry 2 }

cucsMgmtCmcSecureBootRn OBJECT-TYPE
    SYNTAX       SnmpAdminString
    MAX-ACCESS   read-only
    STATUS       current
    DESCRIPTION
        "Cisco UCS mgmt:CmcSecureBoot:rn managed object property"
    ::= { cucsMgmtCmcSecureBootEntry 3 }

cucsMgmtCmcSecureBootAdminState OBJECT-TYPE
    SYNTAX       CucsMgmtASecureBootAdminState
    MAX-ACCESS   read-only
    STATUS       current
    DESCRIPTION
        "Cisco UCS mgmt:CmcSecureBoot:adminState managed object property"
    ::= { cucsMgmtCmcSecureBootEntry 4 }

cucsMgmtCmcSecureBootOperState OBJECT-TYPE
    SYNTAX       CucsMgmtSecureBootOperState
    MAX-ACCESS   read-only
    STATUS       current
    DESCRIPTION
        "Cisco UCS mgmt:CmcSecureBoot:operState managed object property"
    ::= { cucsMgmtCmcSecureBootEntry 5 }

cucsMgmtConnectionTable OBJECT-TYPE
    SYNTAX           SEQUENCE OF CucsMgmtConnectionEntry
    MAX-ACCESS       not-accessible
    STATUS           current
    DESCRIPTION
        "Cisco UCS mgmt:Connection managed object table"
    ::= { cucsMgmtObjects 23 }

cucsMgmtConnectionEntry OBJECT-TYPE
    SYNTAX           CucsMgmtConnectionEntry
    MAX-ACCESS       not-accessible
    STATUS           current
    DESCRIPTION
        "Entry for the cucsMgmtConnectionTable table."
    INDEX { cucsMgmtConnectionInstanceId }
    ::= { cucsMgmtConnectionTable 1 }

CucsMgmtConnectionEntry ::= SEQUENCE {
    cucsMgmtConnectionInstanceId                                     CucsManagedObjectId,
    cucsMgmtConnectionDn                                             CucsManagedObjectDn,
    cucsMgmtConnectionRn                                             SnmpAdminString,
    cucsMgmtConnectionAck                                            CucsMgmtConnectionState,
    cucsMgmtConnectionOperState                                      CucsMgmtConnectionState,
    cucsMgmtConnectionType                                           CucsMgmtSource
}

cucsMgmtConnectionInstanceId OBJECT-TYPE
    SYNTAX       CucsManagedObjectId
    MAX-ACCESS   not-accessible
    STATUS       current
    DESCRIPTION
        "Instance identifier of the managed object."
    ::= { cucsMgmtConnectionEntry 1 }

cucsMgmtConnectionDn OBJECT-TYPE
    SYNTAX       CucsManagedObjectDn
    MAX-ACCESS   read-only
    STATUS       current
    DESCRIPTION
        "Cisco UCS mgmt:Connection:dn managed object property"
    ::= { cucsMgmtConnectionEntry 2 }

cucsMgmtConnectionRn OBJECT-TYPE
    SYNTAX       SnmpAdminString
    MAX-ACCESS   read-only
    STATUS       current
    DESCRIPTION
        "Cisco UCS mgmt:Connection:rn managed object property"
    ::= { cucsMgmtConnectionEntry 3 }

cucsMgmtConnectionAck OBJECT-TYPE
    SYNTAX       CucsMgmtConnectionState
    MAX-ACCESS   read-only
    STATUS       current
    DESCRIPTION
        "Cisco UCS mgmt:Connection:ack managed object property"
    ::= { cucsMgmtConnectionEntry 4 }

cucsMgmtConnectionOperState OBJECT-TYPE
    SYNTAX       CucsMgmtConnectionState
    MAX-ACCESS   read-only
    STATUS       current
    DESCRIPTION
        "Cisco UCS mgmt:Connection:operState managed object property"
    ::= { cucsMgmtConnectionEntry 5 }

cucsMgmtConnectionType OBJECT-TYPE
    SYNTAX       CucsMgmtSource
    MAX-ACCESS   read-only
    STATUS       current
    DESCRIPTION
        "Cisco UCS mgmt:Connection:type managed object property"
    ::= { cucsMgmtConnectionEntry 6 }

cucsMgmtControllerTable OBJECT-TYPE
    SYNTAX           SEQUENCE OF CucsMgmtControllerEntry
    MAX-ACCESS       not-accessible
    STATUS           current
    DESCRIPTION
        "Cisco UCS mgmt:Controller managed object table"
    ::= { cucsMgmtObjects 6 }

cucsMgmtControllerEntry OBJECT-TYPE
    SYNTAX           CucsMgmtControllerEntry
    MAX-ACCESS       not-accessible
    STATUS           current
    DESCRIPTION
        "Entry for the cucsMgmtControllerTable table."
    INDEX { cucsMgmtControllerInstanceId }
    ::= { cucsMgmtControllerTable 1 }

CucsMgmtControllerEntry ::= SEQUENCE {
    cucsMgmtControllerInstanceId                                     CucsManagedObjectId,
    cucsMgmtControllerDn                                             CucsManagedObjectDn,
    cucsMgmtControllerRn                                             SnmpAdminString,
    cucsMgmtControllerFsmDescr                                       SnmpAdminString,
    cucsMgmtControllerFsmFlags                                       SnmpAdminString,
    cucsMgmtControllerFsmPrev                                        SnmpAdminString,
    cucsMgmtControllerFsmProgr                                       Gauge32,
    cucsMgmtControllerFsmRmtInvErrCode                               Gauge32,
    cucsMgmtControllerFsmRmtInvErrDescr                              SnmpAdminString,
    cucsMgmtControllerFsmRmtInvRslt                                  CucsConditionRemoteInvRslt,
    cucsMgmtControllerFsmStageDescr                                  SnmpAdminString,
    cucsMgmtControllerFsmStamp                                       DateAndTime,
    cucsMgmtControllerFsmStatus                                      SnmpAdminString,
    cucsMgmtControllerFsmTry                                         Gauge32,
    cucsMgmtControllerGuid                                           SnmpAdminString,
    cucsMgmtControllerModel                                          SnmpAdminString,
    cucsMgmtControllerRevision                                       SnmpAdminString,
    cucsMgmtControllerSerial                                         SnmpAdminString,
    cucsMgmtControllerSubject                                        CucsMgmtSubject,
    cucsMgmtControllerVendor                                         SnmpAdminString,
    cucsMgmtControllerOperConn                                       SnmpAdminString,
    cucsMgmtControllerDimmBlacklistingOperState                      CucsMgmtDimmBlacklistingOperState,
    cucsMgmtControllerStorageOobInterfaceSupported                   TruthValue,
    cucsMgmtControllerStorageSubsystemState                          CucsMgmtStorageSubsystemState,
    cucsMgmtControllerStorageOobConfigSupported                      TruthValue,
    cucsMgmtControllerId                                             CucsNetworkSwitchId,
    cucsMgmtControllerDesiredMaintenanceMode                         CucsMgmtMaintMode,
    cucsMgmtControllerLastRebootReason                               SnmpAdminString,
    cucsMgmtControllerPowerFanSpeedPolicySupported                   TruthValue,
    cucsMgmtControllerSupportedCapability                            CucsMgmtCapability,
    cucsMgmtControllerDiskZoningState                                CucsMgmtDiskZoningState,
    cucsMgmtControllerHostagCommMethod                               CucsMgmtControllerHostagCommMethod,
    cucsMgmtControllerWebUIKvmConsoleSupported                       TruthValue
}

cucsMgmtControllerInstanceId OBJECT-TYPE
    SYNTAX       CucsManagedObjectId
    MAX-ACCESS   not-accessible
    STATUS       current
    DESCRIPTION
        "Instance identifier of the managed object."
    ::= { cucsMgmtControllerEntry 1 }

cucsMgmtControllerDn OBJECT-TYPE
    SYNTAX       CucsManagedObjectDn
    MAX-ACCESS   read-only
    STATUS       current
    DESCRIPTION
        "Cisco UCS mgmt:Controller:dn managed object property"
    ::= { cucsMgmtControllerEntry 2 }

cucsMgmtControllerRn OBJECT-TYPE
    SYNTAX       SnmpAdminString
    MAX-ACCESS   read-only
    STATUS       current
    DESCRIPTION
        "Cisco UCS mgmt:Controller:rn managed object property"
    ::= { cucsMgmtControllerEntry 3 }

cucsMgmtControllerFsmDescr OBJECT-TYPE
    SYNTAX       SnmpAdminString
    MAX-ACCESS   read-only
    STATUS       current
    DESCRIPTION
        "Cisco UCS mgmt:Controller:fsmDescr managed object property"
    ::= { cucsMgmtControllerEntry 4 }

cucsMgmtControllerFsmFlags OBJECT-TYPE
    SYNTAX       SnmpAdminString
    MAX-ACCESS   read-only
    STATUS       current
    DESCRIPTION
        "Cisco UCS mgmt:Controller:fsmFlags managed object property"
    ::= { cucsMgmtControllerEntry 5 }

cucsMgmtControllerFsmPrev OBJECT-TYPE
    SYNTAX       SnmpAdminString
    MAX-ACCESS   read-only
    STATUS       current
    DESCRIPTION
        "Cisco UCS mgmt:Controller:fsmPrev managed object property"
    ::= { cucsMgmtControllerEntry 6 }

cucsMgmtControllerFsmProgr OBJECT-TYPE
    SYNTAX       Gauge32
    MAX-ACCESS   read-only
    STATUS       current
    DESCRIPTION
        "Cisco UCS mgmt:Controller:fsmProgr managed object property"
    ::= { cucsMgmtControllerEntry 7 }

cucsMgmtControllerFsmRmtInvErrCode OBJECT-TYPE
    SYNTAX       Gauge32
    MAX-ACCESS   read-only
    STATUS       current
    DESCRIPTION
        "Cisco UCS mgmt:Controller:fsmRmtInvErrCode managed
        object property"
    ::= { cucsMgmtControllerEntry 8 }

cucsMgmtControllerFsmRmtInvErrDescr OBJECT-TYPE
    SYNTAX       SnmpAdminString
    MAX-ACCESS   read-only
    STATUS       current
    DESCRIPTION
        "Cisco UCS mgmt:Controller:fsmRmtInvErrDescr managed
        object property"
    ::= { cucsMgmtControllerEntry 9 }

cucsMgmtControllerFsmRmtInvRslt OBJECT-TYPE
    SYNTAX       CucsConditionRemoteInvRslt
    MAX-ACCESS   read-only
    STATUS       current
    DESCRIPTION
        "Cisco UCS mgmt:Controller:fsmRmtInvRslt managed object property"
    ::= { cucsMgmtControllerEntry 10 }

cucsMgmtControllerFsmStageDescr OBJECT-TYPE
    SYNTAX       SnmpAdminString
    MAX-ACCESS   read-only
    STATUS       current
    DESCRIPTION
        "Cisco UCS mgmt:Controller:fsmStageDescr managed object property"
    ::= { cucsMgmtControllerEntry 11 }

cucsMgmtControllerFsmStamp OBJECT-TYPE
    SYNTAX       DateAndTime
    MAX-ACCESS   read-only
    STATUS       current
    DESCRIPTION
        "Cisco UCS mgmt:Controller:fsmStamp managed object property"
    ::= { cucsMgmtControllerEntry 12 }

cucsMgmtControllerFsmStatus OBJECT-TYPE
    SYNTAX       SnmpAdminString
    MAX-ACCESS   read-only
    STATUS       current
    DESCRIPTION
        "Cisco UCS mgmt:Controller:fsmStatus managed object property"
    ::= { cucsMgmtControllerEntry 13 }

cucsMgmtControllerFsmTry OBJECT-TYPE
    SYNTAX       Gauge32
    MAX-ACCESS   read-only
    STATUS       current
    DESCRIPTION
        "Cisco UCS mgmt:Controller:fsmTry managed object property"
    ::= { cucsMgmtControllerEntry 14 }

cucsMgmtControllerGuid OBJECT-TYPE
    SYNTAX       SnmpAdminString
    MAX-ACCESS   read-only
    STATUS       current
    DESCRIPTION
        "Cisco UCS mgmt:Controller:guid managed object property"
    ::= { cucsMgmtControllerEntry 15 }

cucsMgmtControllerModel OBJECT-TYPE
    SYNTAX       SnmpAdminString
    MAX-ACCESS   read-only
    STATUS       current
    DESCRIPTION
        "Cisco UCS mgmt:Controller:model managed object property"
    ::= { cucsMgmtControllerEntry 16 }

cucsMgmtControllerRevision OBJECT-TYPE
    SYNTAX       SnmpAdminString
    MAX-ACCESS   read-only
    STATUS       current
    DESCRIPTION
        "Cisco UCS mgmt:Controller:revision managed object property"
    ::= { cucsMgmtControllerEntry 17 }

cucsMgmtControllerSerial OBJECT-TYPE
    SYNTAX       SnmpAdminString
    MAX-ACCESS   read-only
    STATUS       current
    DESCRIPTION
        "Cisco UCS mgmt:Controller:serial managed object property"
    ::= { cucsMgmtControllerEntry 18 }

cucsMgmtControllerSubject OBJECT-TYPE
    SYNTAX       CucsMgmtSubject
    MAX-ACCESS   read-only
    STATUS       current
    DESCRIPTION
        "Cisco UCS mgmt:Controller:subject managed object property"
    ::= { cucsMgmtControllerEntry 19 }

cucsMgmtControllerVendor OBJECT-TYPE
    SYNTAX       SnmpAdminString
    MAX-ACCESS   read-only
    STATUS       current
    DESCRIPTION
        "Cisco UCS mgmt:Controller:vendor managed object property"
    ::= { cucsMgmtControllerEntry 20 }

cucsMgmtControllerOperConn OBJECT-TYPE
    SYNTAX       SnmpAdminString
    MAX-ACCESS   read-only
    STATUS       current
    DESCRIPTION
        "Cisco UCS mgmt:Controller:operConn managed object property"
    ::= { cucsMgmtControllerEntry 21 }

cucsMgmtControllerDimmBlacklistingOperState OBJECT-TYPE
    SYNTAX       CucsMgmtDimmBlacklistingOperState
    MAX-ACCESS   read-only
    STATUS       current
    DESCRIPTION
        "Cisco UCS mgmt:Controller:dimmBlacklistingOperState
        managed object property"
    ::= { cucsMgmtControllerEntry 22 }

cucsMgmtControllerStorageOobInterfaceSupported OBJECT-TYPE
    SYNTAX       TruthValue
    MAX-ACCESS   read-only
    STATUS       current
    DESCRIPTION
        "Cisco UCS mgmt:Controller:storageOobInterfaceSupported
        managed object property"
    ::= { cucsMgmtControllerEntry 23 }

cucsMgmtControllerStorageSubsystemState OBJECT-TYPE
    SYNTAX       CucsMgmtStorageSubsystemState
    MAX-ACCESS   read-only
    STATUS       current
    DESCRIPTION
        "Cisco UCS mgmt:Controller:storageSubsystemState
        managed object property"
    ::= { cucsMgmtControllerEntry 24 }

cucsMgmtControllerStorageOobConfigSupported OBJECT-TYPE
    SYNTAX       TruthValue
    MAX-ACCESS   read-only
    STATUS       current
    DESCRIPTION
        "Cisco UCS mgmt:Controller:storageOobConfigSupported
        managed object property"
    ::= { cucsMgmtControllerEntry 25 }

cucsMgmtControllerId OBJECT-TYPE
    SYNTAX       CucsNetworkSwitchId
    MAX-ACCESS   read-only
    STATUS       current
    DESCRIPTION
        "Cisco UCS mgmt:Controller:id managed object property"
    ::= { cucsMgmtControllerEntry 26 }

cucsMgmtControllerDesiredMaintenanceMode OBJECT-TYPE
    SYNTAX       CucsMgmtMaintMode
    MAX-ACCESS   read-only
    STATUS       current
    DESCRIPTION
        "Cisco UCS mgmt:Controller:desiredMaintenanceMode
        managed object property"
    ::= { cucsMgmtControllerEntry 27 }

cucsMgmtControllerLastRebootReason OBJECT-TYPE
    SYNTAX       SnmpAdminString
    MAX-ACCESS   read-only
    STATUS       current
    DESCRIPTION
        "Cisco UCS mgmt:Controller:lastRebootReason managed
        object property"
    ::= { cucsMgmtControllerEntry 28 }

cucsMgmtControllerPowerFanSpeedPolicySupported OBJECT-TYPE
    SYNTAX       TruthValue
    MAX-ACCESS   read-only
    STATUS       current
    DESCRIPTION
        "Cisco UCS mgmt:Controller:powerFanSpeedPolicySupported
        managed object property"
    ::= { cucsMgmtControllerEntry 29 }

cucsMgmtControllerSupportedCapability OBJECT-TYPE
    SYNTAX       CucsMgmtCapability
    MAX-ACCESS   read-only
    STATUS       current
    DESCRIPTION
        "Cisco UCS mgmt:Controller:supportedCapability
        managed object property"
    ::= { cucsMgmtControllerEntry 30 }

cucsMgmtControllerDiskZoningState OBJECT-TYPE
    SYNTAX       CucsMgmtDiskZoningState
    MAX-ACCESS   read-only
    STATUS       current
    DESCRIPTION
        "Cisco UCS mgmt:Controller:diskZoningState managed
        object property"
    ::= { cucsMgmtControllerEntry 31 }

cucsMgmtControllerHostagCommMethod OBJECT-TYPE
    SYNTAX       CucsMgmtControllerHostagCommMethod
    MAX-ACCESS   read-only
    STATUS       current
    DESCRIPTION
        "Cisco UCS mgmt:Controller:hostagCommMethod managed
        object property"
    ::= { cucsMgmtControllerEntry 32 }

cucsMgmtControllerWebUIKvmConsoleSupported OBJECT-TYPE
    SYNTAX       TruthValue
    MAX-ACCESS   read-only
    STATUS       current
    DESCRIPTION
        "Cisco UCS mgmt:Controller:webUIKvmConsoleSupported
        managed object property"
    ::= { cucsMgmtControllerEntry 33 }

cucsMgmtControllerFsmTable OBJECT-TYPE
    SYNTAX           SEQUENCE OF CucsMgmtControllerFsmEntry
    MAX-ACCESS       not-accessible
    STATUS           current
    DESCRIPTION
        "Cisco UCS mgmt:ControllerFsm managed object table"
    ::= { cucsMgmtObjects 24 }

cucsMgmtControllerFsmEntry OBJECT-TYPE
    SYNTAX           CucsMgmtControllerFsmEntry
    MAX-ACCESS       not-accessible
    STATUS           current
    DESCRIPTION
        "Entry for the cucsMgmtControllerFsmTable table."
    INDEX { cucsMgmtControllerFsmInstanceId }
    ::= { cucsMgmtControllerFsmTable 1 }

CucsMgmtControllerFsmEntry ::= SEQUENCE {
    cucsMgmtControllerFsmInstanceId                                  CucsManagedObjectId,
    cucsMgmtControllerFsmDn                                          CucsManagedObjectDn,
    cucsMgmtControllerFsmRn                                          SnmpAdminString,
    cucsMgmtControllerFsmCompletionTime                              DateAndTime,
    cucsMgmtControllerFsmCurrentFsm                                  CucsMgmtControllerFsmCurrentFsm,
    cucsMgmtControllerFsmDescrData                                   SnmpAdminString,
    cucsMgmtControllerFsmFsmStatus                                   CucsFsmFsmStageStatus,
    cucsMgmtControllerFsmProgress                                    Gauge32,
    cucsMgmtControllerFsmRmtErrCode                                  Gauge32,
    cucsMgmtControllerFsmRmtErrDescr                                 SnmpAdminString,
    cucsMgmtControllerFsmRmtRslt                                     CucsConditionRemoteInvRslt
}

cucsMgmtControllerFsmInstanceId OBJECT-TYPE
    SYNTAX       CucsManagedObjectId
    MAX-ACCESS   not-accessible
    STATUS       current
    DESCRIPTION
        "Instance identifier of the managed object."
    ::= { cucsMgmtControllerFsmEntry 1 }

cucsMgmtControllerFsmDn OBJECT-TYPE
    SYNTAX       CucsManagedObjectDn
    MAX-ACCESS   read-only
    STATUS       current
    DESCRIPTION
        "Cisco UCS mgmt:ControllerFsm:dn managed object property"
    ::= { cucsMgmtControllerFsmEntry 2 }

cucsMgmtControllerFsmRn OBJECT-TYPE
    SYNTAX       SnmpAdminString
    MAX-ACCESS   read-only
    STATUS       current
    DESCRIPTION
        "Cisco UCS mgmt:ControllerFsm:rn managed object property"
    ::= { cucsMgmtControllerFsmEntry 3 }

cucsMgmtControllerFsmCompletionTime OBJECT-TYPE
    SYNTAX       DateAndTime
    MAX-ACCESS   read-only
    STATUS       current
    DESCRIPTION
        "Cisco UCS mgmt:ControllerFsm:completionTime managed
        object property"
    ::= { cucsMgmtControllerFsmEntry 4 }

cucsMgmtControllerFsmCurrentFsm OBJECT-TYPE
    SYNTAX       CucsMgmtControllerFsmCurrentFsm
    MAX-ACCESS   read-only
    STATUS       current
    DESCRIPTION
        "Cisco UCS mgmt:ControllerFsm:currentFsm managed object property"
    ::= { cucsMgmtControllerFsmEntry 5 }

cucsMgmtControllerFsmDescrData OBJECT-TYPE
    SYNTAX       SnmpAdminString
    MAX-ACCESS   read-only
    STATUS       current
    DESCRIPTION
        "Cisco UCS mgmt:ControllerFsm:descr managed object property"
    ::= { cucsMgmtControllerFsmEntry 6 }

cucsMgmtControllerFsmFsmStatus OBJECT-TYPE
    SYNTAX       CucsFsmFsmStageStatus
    MAX-ACCESS   read-only
    STATUS       current
    DESCRIPTION
        "Cisco UCS mgmt:ControllerFsm:fsmStatus managed object property"
    ::= { cucsMgmtControllerFsmEntry 7 }

cucsMgmtControllerFsmProgress OBJECT-TYPE
    SYNTAX       Gauge32
    MAX-ACCESS   read-only
    STATUS       current
    DESCRIPTION
        "Cisco UCS mgmt:ControllerFsm:progress managed object property"
    ::= { cucsMgmtControllerFsmEntry 8 }

cucsMgmtControllerFsmRmtErrCode OBJECT-TYPE
    SYNTAX       Gauge32
    MAX-ACCESS   read-only
    STATUS       current
    DESCRIPTION
        "Cisco UCS mgmt:ControllerFsm:rmtErrCode managed object property"
    ::= { cucsMgmtControllerFsmEntry 9 }

cucsMgmtControllerFsmRmtErrDescr OBJECT-TYPE
    SYNTAX       SnmpAdminString
    MAX-ACCESS   read-only
    STATUS       current
    DESCRIPTION
        "Cisco UCS mgmt:ControllerFsm:rmtErrDescr managed object property"
    ::= { cucsMgmtControllerFsmEntry 10 }

cucsMgmtControllerFsmRmtRslt OBJECT-TYPE
    SYNTAX       CucsConditionRemoteInvRslt
    MAX-ACCESS   read-only
    STATUS       current
    DESCRIPTION
        "Cisco UCS mgmt:ControllerFsm:rmtRslt managed object property"
    ::= { cucsMgmtControllerFsmEntry 11 }

cucsMgmtControllerFsmStageTable OBJECT-TYPE
    SYNTAX           SEQUENCE OF CucsMgmtControllerFsmStageEntry
    MAX-ACCESS       not-accessible
    STATUS           current
    DESCRIPTION
        "Cisco UCS mgmt:ControllerFsmStage managed object table"
    ::= { cucsMgmtObjects 25 }

cucsMgmtControllerFsmStageEntry OBJECT-TYPE
    SYNTAX           CucsMgmtControllerFsmStageEntry
    MAX-ACCESS       not-accessible
    STATUS           current
    DESCRIPTION
        "Entry for the cucsMgmtControllerFsmStageTable table."
    INDEX { cucsMgmtControllerFsmStageInstanceId }
    ::= { cucsMgmtControllerFsmStageTable 1 }

CucsMgmtControllerFsmStageEntry ::= SEQUENCE {
    cucsMgmtControllerFsmStageInstanceId                             CucsManagedObjectId,
    cucsMgmtControllerFsmStageDn                                     CucsManagedObjectDn,
    cucsMgmtControllerFsmStageRn                                     SnmpAdminString,
    cucsMgmtControllerFsmStageDescrData                              SnmpAdminString,
    cucsMgmtControllerFsmStageLastUpdateTime                         DateAndTime,
    cucsMgmtControllerFsmStageName                                   CucsMgmtControllerFsmStageName,
    cucsMgmtControllerFsmStageOrder                                  Gauge32,
    cucsMgmtControllerFsmStageRetry                                  Gauge32,
    cucsMgmtControllerFsmStageStageStatus                            CucsFsmFsmStageStatus
}

cucsMgmtControllerFsmStageInstanceId OBJECT-TYPE
    SYNTAX       CucsManagedObjectId
    MAX-ACCESS   not-accessible
    STATUS       current
    DESCRIPTION
        "Instance identifier of the managed object."
    ::= { cucsMgmtControllerFsmStageEntry 1 }

cucsMgmtControllerFsmStageDn OBJECT-TYPE
    SYNTAX       CucsManagedObjectDn
    MAX-ACCESS   read-only
    STATUS       current
    DESCRIPTION
        "Cisco UCS mgmt:ControllerFsmStage:dn managed object property"
    ::= { cucsMgmtControllerFsmStageEntry 2 }

cucsMgmtControllerFsmStageRn OBJECT-TYPE
    SYNTAX       SnmpAdminString
    MAX-ACCESS   read-only
    STATUS       current
    DESCRIPTION
        "Cisco UCS mgmt:ControllerFsmStage:rn managed object property"
    ::= { cucsMgmtControllerFsmStageEntry 3 }

cucsMgmtControllerFsmStageDescrData OBJECT-TYPE
    SYNTAX       SnmpAdminString
    MAX-ACCESS   read-only
    STATUS       current
    DESCRIPTION
        "Cisco UCS mgmt:ControllerFsmStage:descr managed object property"
    ::= { cucsMgmtControllerFsmStageEntry 4 }

cucsMgmtControllerFsmStageLastUpdateTime OBJECT-TYPE
    SYNTAX       DateAndTime
    MAX-ACCESS   read-only
    STATUS       current
    DESCRIPTION
        "Cisco UCS mgmt:ControllerFsmStage:lastUpdateTime
        managed object property"
    ::= { cucsMgmtControllerFsmStageEntry 5 }

cucsMgmtControllerFsmStageName OBJECT-TYPE
    SYNTAX       CucsMgmtControllerFsmStageName
    MAX-ACCESS   read-only
    STATUS       current
    DESCRIPTION
        "Cisco UCS mgmt:ControllerFsmStage:name managed object property"
    ::= { cucsMgmtControllerFsmStageEntry 6 }

cucsMgmtControllerFsmStageOrder OBJECT-TYPE
    SYNTAX       Gauge32
    MAX-ACCESS   read-only
    STATUS       current
    DESCRIPTION
        "Cisco UCS mgmt:ControllerFsmStage:order managed object property"
    ::= { cucsMgmtControllerFsmStageEntry 7 }

cucsMgmtControllerFsmStageRetry OBJECT-TYPE
    SYNTAX       Gauge32
    MAX-ACCESS   read-only
    STATUS       current
    DESCRIPTION
        "Cisco UCS mgmt:ControllerFsmStage:retry managed object property"
    ::= { cucsMgmtControllerFsmStageEntry 8 }

cucsMgmtControllerFsmStageStageStatus OBJECT-TYPE
    SYNTAX       CucsFsmFsmStageStatus
    MAX-ACCESS   read-only
    STATUS       current
    DESCRIPTION
        "Cisco UCS mgmt:ControllerFsmStage:stageStatus
        managed object property"
    ::= { cucsMgmtControllerFsmStageEntry 9 }

cucsMgmtControllerFsmTaskTable OBJECT-TYPE
    SYNTAX           SEQUENCE OF CucsMgmtControllerFsmTaskEntry
    MAX-ACCESS       not-accessible
    STATUS           current
    DESCRIPTION
        "Cisco UCS mgmt:ControllerFsmTask managed object table"
    ::= { cucsMgmtObjects 7 }

cucsMgmtControllerFsmTaskEntry OBJECT-TYPE
    SYNTAX           CucsMgmtControllerFsmTaskEntry
    MAX-ACCESS       not-accessible
    STATUS           current
    DESCRIPTION
        "Entry for the cucsMgmtControllerFsmTaskTable table."
    INDEX { cucsMgmtControllerFsmTaskInstanceId }
    ::= { cucsMgmtControllerFsmTaskTable 1 }

CucsMgmtControllerFsmTaskEntry ::= SEQUENCE {
    cucsMgmtControllerFsmTaskInstanceId                              CucsManagedObjectId,
    cucsMgmtControllerFsmTaskDn                                      CucsManagedObjectDn,
    cucsMgmtControllerFsmTaskRn                                      SnmpAdminString,
    cucsMgmtControllerFsmTaskCompletion                              CucsFsmCompletion,
    cucsMgmtControllerFsmTaskFlags                                   CucsMgmtControllerFsmTaskFlags,
    cucsMgmtControllerFsmTaskItem                                    CucsMgmtControllerFsmTaskItem,
    cucsMgmtControllerFsmTaskSeqId                                   Gauge32
}

cucsMgmtControllerFsmTaskInstanceId OBJECT-TYPE
    SYNTAX       CucsManagedObjectId
    MAX-ACCESS   not-accessible
    STATUS       current
    DESCRIPTION
        "Instance identifier of the managed object."
    ::= { cucsMgmtControllerFsmTaskEntry 1 }

cucsMgmtControllerFsmTaskDn OBJECT-TYPE
    SYNTAX       CucsManagedObjectDn
    MAX-ACCESS   read-only
    STATUS       current
    DESCRIPTION
        "Cisco UCS mgmt:ControllerFsmTask:dn managed object property"
    ::= { cucsMgmtControllerFsmTaskEntry 2 }

cucsMgmtControllerFsmTaskRn OBJECT-TYPE
    SYNTAX       SnmpAdminString
    MAX-ACCESS   read-only
    STATUS       current
    DESCRIPTION
        "Cisco UCS mgmt:ControllerFsmTask:rn managed object property"
    ::= { cucsMgmtControllerFsmTaskEntry 3 }

cucsMgmtControllerFsmTaskCompletion OBJECT-TYPE
    SYNTAX       CucsFsmCompletion
    MAX-ACCESS   read-only
    STATUS       current
    DESCRIPTION
        "Cisco UCS mgmt:ControllerFsmTask:completion managed
        object property"
    ::= { cucsMgmtControllerFsmTaskEntry 4 }

cucsMgmtControllerFsmTaskFlags OBJECT-TYPE
    SYNTAX       CucsMgmtControllerFsmTaskFlags
    MAX-ACCESS   read-only
    STATUS       current
    DESCRIPTION
        "Cisco UCS mgmt:ControllerFsmTask:flags managed object property"
    ::= { cucsMgmtControllerFsmTaskEntry 5 }

cucsMgmtControllerFsmTaskItem OBJECT-TYPE
    SYNTAX       CucsMgmtControllerFsmTaskItem
    MAX-ACCESS   read-only
    STATUS       current
    DESCRIPTION
        "Cisco UCS mgmt:ControllerFsmTask:item managed object property"
    ::= { cucsMgmtControllerFsmTaskEntry 6 }

cucsMgmtControllerFsmTaskSeqId OBJECT-TYPE
    SYNTAX       Gauge32
    MAX-ACCESS   read-only
    STATUS       current
    DESCRIPTION
        "Cisco UCS mgmt:ControllerFsmTask:seqId managed object property"
    ::= { cucsMgmtControllerFsmTaskEntry 7 }

cucsMgmtDbStateTable OBJECT-TYPE
    SYNTAX           SEQUENCE OF CucsMgmtDbStateEntry
    MAX-ACCESS       not-accessible
    STATUS           current
    DESCRIPTION
        "Cisco UCS mgmt:DbState managed object table"
    ::= { cucsMgmtObjects 71 }

cucsMgmtDbStateEntry OBJECT-TYPE
    SYNTAX           CucsMgmtDbStateEntry
    MAX-ACCESS       not-accessible
    STATUS           current
    DESCRIPTION
        "Entry for the cucsMgmtDbStateTable table."
    INDEX { cucsMgmtDbStateInstanceId }
    ::= { cucsMgmtDbStateTable 1 }

CucsMgmtDbStateEntry ::= SEQUENCE {
    cucsMgmtDbStateInstanceId                                        CucsManagedObjectId,
    cucsMgmtDbStateDn                                                CucsManagedObjectDn,
    cucsMgmtDbStateRn                                                SnmpAdminString,
    cucsMgmtDbStateCorruptedCount                                    Unsigned64,
    cucsMgmtDbStateLastOccurrenceTime                                DateAndTime
}

cucsMgmtDbStateInstanceId OBJECT-TYPE
    SYNTAX       CucsManagedObjectId
    MAX-ACCESS   not-accessible
    STATUS       current
    DESCRIPTION
        "Instance identifier of the managed object."
    ::= { cucsMgmtDbStateEntry 1 }

cucsMgmtDbStateDn OBJECT-TYPE
    SYNTAX       CucsManagedObjectDn
    MAX-ACCESS   read-only
    STATUS       current
    DESCRIPTION
        "Cisco UCS mgmt:DbState:dn managed object property"
    ::= { cucsMgmtDbStateEntry 2 }

cucsMgmtDbStateRn OBJECT-TYPE
    SYNTAX       SnmpAdminString
    MAX-ACCESS   read-only
    STATUS       current
    DESCRIPTION
        "Cisco UCS mgmt:DbState:rn managed object property"
    ::= { cucsMgmtDbStateEntry 3 }

cucsMgmtDbStateCorruptedCount OBJECT-TYPE
    SYNTAX       Unsigned64
    MAX-ACCESS   read-only
    STATUS       current
    DESCRIPTION
        "Cisco UCS mgmt:DbState:corruptedCount managed object property"
    ::= { cucsMgmtDbStateEntry 4 }

cucsMgmtDbStateLastOccurrenceTime OBJECT-TYPE
    SYNTAX       DateAndTime
    MAX-ACCESS   read-only
    STATUS       current
    DESCRIPTION
        "Cisco UCS mgmt:DbState:lastOccurrenceTime managed
        object property"
    ::= { cucsMgmtDbStateEntry 5 }

cucsMgmtEntityTable OBJECT-TYPE
    SYNTAX           SEQUENCE OF CucsMgmtEntityEntry
    MAX-ACCESS       not-accessible
    STATUS           current
    DESCRIPTION
        "Cisco UCS mgmt:Entity managed object table"
    ::= { cucsMgmtObjects 8 }

cucsMgmtEntityEntry OBJECT-TYPE
    SYNTAX           CucsMgmtEntityEntry
    MAX-ACCESS       not-accessible
    STATUS           current
    DESCRIPTION
        "Entry for the cucsMgmtEntityTable table."
    INDEX { cucsMgmtEntityInstanceId }
    ::= { cucsMgmtEntityTable 1 }

CucsMgmtEntityEntry ::= SEQUENCE {
    cucsMgmtEntityInstanceId                                         CucsManagedObjectId,
    cucsMgmtEntityDn                                                 CucsManagedObjectDn,
    cucsMgmtEntityRn                                                 SnmpAdminString,
    cucsMgmtEntityChassis1                                           SnmpAdminString,
    cucsMgmtEntityChassis2                                           SnmpAdminString,
    cucsMgmtEntityChassis3                                           SnmpAdminString,
    cucsMgmtEntityChassisDeviceIoState1                              CucsMgmtEntityChassisDeviceIoState1,
    cucsMgmtEntityChassisDeviceIoState2                              CucsMgmtEntityChassisDeviceIoState2,
    cucsMgmtEntityChassisDeviceIoState3                              CucsMgmtEntityChassisDeviceIoState3,
    cucsMgmtEntityHaFailureReason                                    CucsMgmtEntityHaFailureReason,
    cucsMgmtEntityHaReadiness                                        CucsMgmtEntityHaReadiness,
    cucsMgmtEntityHaReady                                            TruthValue,
    cucsMgmtEntityId                                                 CucsNetworkSwitchId,
    cucsMgmtEntityLeadership                                         CucsMgmtEntityLeadership,
    cucsMgmtEntityMgmtServicesState                                  CucsMgmtEntityMgmtServicesState,
    cucsMgmtEntityProblems                                           CucsMgmtEntityProblems,
    cucsMgmtEntityState                                              CucsMgmtEntityState,
    cucsMgmtEntityUmbilicalState                                     CucsMgmtEntityUmbilicalState,
    cucsMgmtEntityVersionMismatch                                    TruthValue,
    cucsMgmtEntitySshAuthKeysCsum                                    SnmpAdminString,
    cucsMgmtEntitySshAuthKeysSize                                    Unsigned64,
    cucsMgmtEntitySshKeyStatus                                       Unsigned64,
    cucsMgmtEntitySshRootPubKeyCsum                                  SnmpAdminString,
    cucsMgmtEntitySshRootPubKeySize                                  Unsigned64,
    cucsMgmtEntityLeadIdForAutoInstall                               CucsMgmtEntityLeadIdForAutoInstall
}

cucsMgmtEntityInstanceId OBJECT-TYPE
    SYNTAX       CucsManagedObjectId
    MAX-ACCESS   not-accessible
    STATUS       current
    DESCRIPTION
        "Instance identifier of the managed object."
    ::= { cucsMgmtEntityEntry 1 }

cucsMgmtEntityDn OBJECT-TYPE
    SYNTAX       CucsManagedObjectDn
    MAX-ACCESS   read-only
    STATUS       current
    DESCRIPTION
        "Cisco UCS mgmt:Entity:dn managed object property"
    ::= { cucsMgmtEntityEntry 2 }

cucsMgmtEntityRn OBJECT-TYPE
    SYNTAX       SnmpAdminString
    MAX-ACCESS   read-only
    STATUS       current
    DESCRIPTION
        "Cisco UCS mgmt:Entity:rn managed object property"
    ::= { cucsMgmtEntityEntry 3 }

cucsMgmtEntityChassis1 OBJECT-TYPE
    SYNTAX       SnmpAdminString
    MAX-ACCESS   read-only
    STATUS       current
    DESCRIPTION
        "Cisco UCS mgmt:Entity:chassis1 managed object property"
    ::= { cucsMgmtEntityEntry 4 }

cucsMgmtEntityChassis2 OBJECT-TYPE
    SYNTAX       SnmpAdminString
    MAX-ACCESS   read-only
    STATUS       current
    DESCRIPTION
        "Cisco UCS mgmt:Entity:chassis2 managed object property"
    ::= { cucsMgmtEntityEntry 5 }

cucsMgmtEntityChassis3 OBJECT-TYPE
    SYNTAX       SnmpAdminString
    MAX-ACCESS   read-only
    STATUS       current
    DESCRIPTION
        "Cisco UCS mgmt:Entity:chassis3 managed object property"
    ::= { cucsMgmtEntityEntry 6 }

cucsMgmtEntityChassisDeviceIoState1 OBJECT-TYPE
    SYNTAX       CucsMgmtEntityChassisDeviceIoState1
    MAX-ACCESS   read-only
    STATUS       current
    DESCRIPTION
        "Cisco UCS mgmt:Entity:chassisDeviceIoState1 managed
        object property"
    ::= { cucsMgmtEntityEntry 7 }

cucsMgmtEntityChassisDeviceIoState2 OBJECT-TYPE
    SYNTAX       CucsMgmtEntityChassisDeviceIoState2
    MAX-ACCESS   read-only
    STATUS       current
    DESCRIPTION
        "Cisco UCS mgmt:Entity:chassisDeviceIoState2 managed
        object property"
    ::= { cucsMgmtEntityEntry 8 }

cucsMgmtEntityChassisDeviceIoState3 OBJECT-TYPE
    SYNTAX       CucsMgmtEntityChassisDeviceIoState3
    MAX-ACCESS   read-only
    STATUS       current
    DESCRIPTION
        "Cisco UCS mgmt:Entity:chassisDeviceIoState3 managed
        object property"
    ::= { cucsMgmtEntityEntry 9 }

cucsMgmtEntityHaFailureReason OBJECT-TYPE
    SYNTAX       CucsMgmtEntityHaFailureReason
    MAX-ACCESS   read-only
    STATUS       current
    DESCRIPTION
        "Cisco UCS mgmt:Entity:haFailureReason managed object property"
    ::= { cucsMgmtEntityEntry 10 }

cucsMgmtEntityHaReadiness OBJECT-TYPE
    SYNTAX       CucsMgmtEntityHaReadiness
    MAX-ACCESS   read-only
    STATUS       current
    DESCRIPTION
        "Cisco UCS mgmt:Entity:haReadiness managed object property"
    ::= { cucsMgmtEntityEntry 11 }

cucsMgmtEntityHaReady OBJECT-TYPE
    SYNTAX       TruthValue
    MAX-ACCESS   read-only
    STATUS       current
    DESCRIPTION
        "Cisco UCS mgmt:Entity:haReady managed object property"
    ::= { cucsMgmtEntityEntry 12 }

cucsMgmtEntityId OBJECT-TYPE
    SYNTAX       CucsNetworkSwitchId
    MAX-ACCESS   read-only
    STATUS       current
    DESCRIPTION
        "Cisco UCS mgmt:Entity:id managed object property"
    ::= { cucsMgmtEntityEntry 13 }

cucsMgmtEntityLeadership OBJECT-TYPE
    SYNTAX       CucsMgmtEntityLeadership
    MAX-ACCESS   read-only
    STATUS       current
    DESCRIPTION
        "Cisco UCS mgmt:Entity:leadership managed object property"
    ::= { cucsMgmtEntityEntry 14 }

cucsMgmtEntityMgmtServicesState OBJECT-TYPE
    SYNTAX       CucsMgmtEntityMgmtServicesState
    MAX-ACCESS   read-only
    STATUS       current
    DESCRIPTION
        "Cisco UCS mgmt:Entity:mgmtServicesState managed object property"
    ::= { cucsMgmtEntityEntry 15 }

cucsMgmtEntityProblems OBJECT-TYPE
    SYNTAX       CucsMgmtEntityProblems
    MAX-ACCESS   read-only
    STATUS       current
    DESCRIPTION
        "Cisco UCS mgmt:Entity:problems managed object property"
    ::= { cucsMgmtEntityEntry 16 }

cucsMgmtEntityState OBJECT-TYPE
    SYNTAX       CucsMgmtEntityState
    MAX-ACCESS   read-only
    STATUS       current
    DESCRIPTION
        "Cisco UCS mgmt:Entity:state managed object property"
    ::= { cucsMgmtEntityEntry 17 }

cucsMgmtEntityUmbilicalState OBJECT-TYPE
    SYNTAX       CucsMgmtEntityUmbilicalState
    MAX-ACCESS   read-only
    STATUS       current
    DESCRIPTION
        "Cisco UCS mgmt:Entity:umbilicalState managed object property"
    ::= { cucsMgmtEntityEntry 18 }

cucsMgmtEntityVersionMismatch OBJECT-TYPE
    SYNTAX       TruthValue
    MAX-ACCESS   read-only
    STATUS       current
    DESCRIPTION
        "Cisco UCS mgmt:Entity:versionMismatch managed object property"
    ::= { cucsMgmtEntityEntry 19 }

cucsMgmtEntitySshAuthKeysCsum OBJECT-TYPE
    SYNTAX       SnmpAdminString
    MAX-ACCESS   read-only
    STATUS       current
    DESCRIPTION
        "Cisco UCS mgmt:Entity:sshAuthKeysCsum managed object property"
    ::= { cucsMgmtEntityEntry 20 }

cucsMgmtEntitySshAuthKeysSize OBJECT-TYPE
    SYNTAX       Unsigned64
    MAX-ACCESS   read-only
    STATUS       current
    DESCRIPTION
        "Cisco UCS mgmt:Entity:sshAuthKeysSize managed object property"
    ::= { cucsMgmtEntityEntry 21 }

cucsMgmtEntitySshKeyStatus OBJECT-TYPE
    SYNTAX       Unsigned64
    MAX-ACCESS   read-only
    STATUS       current
    DESCRIPTION
        "Cisco UCS mgmt:Entity:sshKeyStatus managed object property"
    ::= { cucsMgmtEntityEntry 22 }

cucsMgmtEntitySshRootPubKeyCsum OBJECT-TYPE
    SYNTAX       SnmpAdminString
    MAX-ACCESS   read-only
    STATUS       current
    DESCRIPTION
        "Cisco UCS mgmt:Entity:sshRootPubKeyCsum managed object property"
    ::= { cucsMgmtEntityEntry 23 }

cucsMgmtEntitySshRootPubKeySize OBJECT-TYPE
    SYNTAX       Unsigned64
    MAX-ACCESS   read-only
    STATUS       current
    DESCRIPTION
        "Cisco UCS mgmt:Entity:sshRootPubKeySize managed object property"
    ::= { cucsMgmtEntityEntry 24 }

cucsMgmtEntityLeadIdForAutoInstall OBJECT-TYPE
    SYNTAX       CucsMgmtEntityLeadIdForAutoInstall
    MAX-ACCESS   read-only
    STATUS       current
    DESCRIPTION
        "Cisco UCS mgmt:Entity:leadIdForAutoInstall managed
        object property"
    ::= { cucsMgmtEntityEntry 25 }

cucsMgmtExportPolicyFsmTable OBJECT-TYPE
    SYNTAX           SEQUENCE OF CucsMgmtExportPolicyFsmEntry
    MAX-ACCESS       not-accessible
    STATUS           current
    DESCRIPTION
        "Cisco UCS mgmt:ExportPolicyFsm managed object table"
    ::= { cucsMgmtObjects 26 }

cucsMgmtExportPolicyFsmEntry OBJECT-TYPE
    SYNTAX           CucsMgmtExportPolicyFsmEntry
    MAX-ACCESS       not-accessible
    STATUS           current
    DESCRIPTION
        "Entry for the cucsMgmtExportPolicyFsmTable table."
    INDEX { cucsMgmtExportPolicyFsmInstanceId }
    ::= { cucsMgmtExportPolicyFsmTable 1 }

CucsMgmtExportPolicyFsmEntry ::= SEQUENCE {
    cucsMgmtExportPolicyFsmInstanceId                                CucsManagedObjectId,
    cucsMgmtExportPolicyFsmDn                                        CucsManagedObjectDn,
    cucsMgmtExportPolicyFsmRn                                        SnmpAdminString,
    cucsMgmtExportPolicyFsmCompletionTime                            DateAndTime,
    cucsMgmtExportPolicyFsmCurrentFsm                                CucsMgmtExportPolicyFsmCurrentFsm,
    cucsMgmtExportPolicyFsmDescr                                     SnmpAdminString,
    cucsMgmtExportPolicyFsmFsmStatus                                 CucsFsmFsmStageStatus,
    cucsMgmtExportPolicyFsmProgress                                  Gauge32,
    cucsMgmtExportPolicyFsmRmtErrCode                                Gauge32,
    cucsMgmtExportPolicyFsmRmtErrDescr                               SnmpAdminString,
    cucsMgmtExportPolicyFsmRmtRslt                                   CucsConditionRemoteInvRslt
}

cucsMgmtExportPolicyFsmInstanceId OBJECT-TYPE
    SYNTAX       CucsManagedObjectId
    MAX-ACCESS   not-accessible
    STATUS       current
    DESCRIPTION
        "Instance identifier of the managed object."
    ::= { cucsMgmtExportPolicyFsmEntry 1 }

cucsMgmtExportPolicyFsmDn OBJECT-TYPE
    SYNTAX       CucsManagedObjectDn
    MAX-ACCESS   read-only
    STATUS       current
    DESCRIPTION
        "Cisco UCS mgmt:ExportPolicyFsm:dn managed object property"
    ::= { cucsMgmtExportPolicyFsmEntry 2 }

cucsMgmtExportPolicyFsmRn OBJECT-TYPE
    SYNTAX       SnmpAdminString
    MAX-ACCESS   read-only
    STATUS       current
    DESCRIPTION
        "Cisco UCS mgmt:ExportPolicyFsm:rn managed object property"
    ::= { cucsMgmtExportPolicyFsmEntry 3 }

cucsMgmtExportPolicyFsmCompletionTime OBJECT-TYPE
    SYNTAX       DateAndTime
    MAX-ACCESS   read-only
    STATUS       current
    DESCRIPTION
        "Cisco UCS mgmt:ExportPolicyFsm:completionTime
        managed object property"
    ::= { cucsMgmtExportPolicyFsmEntry 4 }

cucsMgmtExportPolicyFsmCurrentFsm OBJECT-TYPE
    SYNTAX       CucsMgmtExportPolicyFsmCurrentFsm
    MAX-ACCESS   read-only
    STATUS       current
    DESCRIPTION
        "Cisco UCS mgmt:ExportPolicyFsm:currentFsm managed
        object property"
    ::= { cucsMgmtExportPolicyFsmEntry 5 }

cucsMgmtExportPolicyFsmDescr OBJECT-TYPE
    SYNTAX       SnmpAdminString
    MAX-ACCESS   read-only
    STATUS       current
    DESCRIPTION
        "Cisco UCS mgmt:ExportPolicyFsm:descr managed object property"
    ::= { cucsMgmtExportPolicyFsmEntry 6 }

cucsMgmtExportPolicyFsmFsmStatus OBJECT-TYPE
    SYNTAX       CucsFsmFsmStageStatus
    MAX-ACCESS   read-only
    STATUS       current
    DESCRIPTION
        "Cisco UCS mgmt:ExportPolicyFsm:fsmStatus managed object property"
    ::= { cucsMgmtExportPolicyFsmEntry 7 }

cucsMgmtExportPolicyFsmProgress OBJECT-TYPE
    SYNTAX       Gauge32
    MAX-ACCESS   read-only
    STATUS       current
    DESCRIPTION
        "Cisco UCS mgmt:ExportPolicyFsm:progress managed object property"
    ::= { cucsMgmtExportPolicyFsmEntry 8 }

cucsMgmtExportPolicyFsmRmtErrCode OBJECT-TYPE
    SYNTAX       Gauge32
    MAX-ACCESS   read-only
    STATUS       current
    DESCRIPTION
        "Cisco UCS mgmt:ExportPolicyFsm:rmtErrCode managed
        object property"
    ::= { cucsMgmtExportPolicyFsmEntry 9 }

cucsMgmtExportPolicyFsmRmtErrDescr OBJECT-TYPE
    SYNTAX       SnmpAdminString
    MAX-ACCESS   read-only
    STATUS       current
    DESCRIPTION
        "Cisco UCS mgmt:ExportPolicyFsm:rmtErrDescr managed
        object property"
    ::= { cucsMgmtExportPolicyFsmEntry 10 }

cucsMgmtExportPolicyFsmRmtRslt OBJECT-TYPE
    SYNTAX       CucsConditionRemoteInvRslt
    MAX-ACCESS   read-only
    STATUS       current
    DESCRIPTION
        "Cisco UCS mgmt:ExportPolicyFsm:rmtRslt managed object property"
    ::= { cucsMgmtExportPolicyFsmEntry 11 }

cucsMgmtExportPolicyFsmStageTable OBJECT-TYPE
    SYNTAX           SEQUENCE OF CucsMgmtExportPolicyFsmStageEntry
    MAX-ACCESS       not-accessible
    STATUS           current
    DESCRIPTION
        "Cisco UCS mgmt:ExportPolicyFsmStage managed object table"
    ::= { cucsMgmtObjects 27 }

cucsMgmtExportPolicyFsmStageEntry OBJECT-TYPE
    SYNTAX           CucsMgmtExportPolicyFsmStageEntry
    MAX-ACCESS       not-accessible
    STATUS           current
    DESCRIPTION
        "Entry for the cucsMgmtExportPolicyFsmStageTable table."
    INDEX { cucsMgmtExportPolicyFsmStageInstanceId }
    ::= { cucsMgmtExportPolicyFsmStageTable 1 }

CucsMgmtExportPolicyFsmStageEntry ::= SEQUENCE {
    cucsMgmtExportPolicyFsmStageInstanceId                           CucsManagedObjectId,
    cucsMgmtExportPolicyFsmStageDn                                   CucsManagedObjectDn,
    cucsMgmtExportPolicyFsmStageRn                                   SnmpAdminString,
    cucsMgmtExportPolicyFsmStageDescr                                SnmpAdminString,
    cucsMgmtExportPolicyFsmStageLastUpdateTime                       DateAndTime,
    cucsMgmtExportPolicyFsmStageName                                 CucsMgmtExportPolicyFsmStageName,
    cucsMgmtExportPolicyFsmStageOrder                                Gauge32,
    cucsMgmtExportPolicyFsmStageRetry                                Gauge32,
    cucsMgmtExportPolicyFsmStageStageStatus                          CucsFsmFsmStageStatus
}

cucsMgmtExportPolicyFsmStageInstanceId OBJECT-TYPE
    SYNTAX       CucsManagedObjectId
    MAX-ACCESS   not-accessible
    STATUS       current
    DESCRIPTION
        "Instance identifier of the managed object."
    ::= { cucsMgmtExportPolicyFsmStageEntry 1 }

cucsMgmtExportPolicyFsmStageDn OBJECT-TYPE
    SYNTAX       CucsManagedObjectDn
    MAX-ACCESS   read-only
    STATUS       current
    DESCRIPTION
        "Cisco UCS mgmt:ExportPolicyFsmStage:dn managed object property"
    ::= { cucsMgmtExportPolicyFsmStageEntry 2 }

cucsMgmtExportPolicyFsmStageRn OBJECT-TYPE
    SYNTAX       SnmpAdminString
    MAX-ACCESS   read-only
    STATUS       current
    DESCRIPTION
        "Cisco UCS mgmt:ExportPolicyFsmStage:rn managed object property"
    ::= { cucsMgmtExportPolicyFsmStageEntry 3 }

cucsMgmtExportPolicyFsmStageDescr OBJECT-TYPE
    SYNTAX       SnmpAdminString
    MAX-ACCESS   read-only
    STATUS       current
    DESCRIPTION
        "Cisco UCS mgmt:ExportPolicyFsmStage:descr managed
        object property"
    ::= { cucsMgmtExportPolicyFsmStageEntry 4 }

cucsMgmtExportPolicyFsmStageLastUpdateTime OBJECT-TYPE
    SYNTAX       DateAndTime
    MAX-ACCESS   read-only
    STATUS       current
    DESCRIPTION
        "Cisco UCS mgmt:ExportPolicyFsmStage:lastUpdateTime
        managed object property"
    ::= { cucsMgmtExportPolicyFsmStageEntry 5 }

cucsMgmtExportPolicyFsmStageName OBJECT-TYPE
    SYNTAX       CucsMgmtExportPolicyFsmStageName
    MAX-ACCESS   read-only
    STATUS       current
    DESCRIPTION
        "Cisco UCS mgmt:ExportPolicyFsmStage:name managed object property"
    ::= { cucsMgmtExportPolicyFsmStageEntry 6 }

cucsMgmtExportPolicyFsmStageOrder OBJECT-TYPE
    SYNTAX       Gauge32
    MAX-ACCESS   read-only
    STATUS       current
    DESCRIPTION
        "Cisco UCS mgmt:ExportPolicyFsmStage:order managed
        object property"
    ::= { cucsMgmtExportPolicyFsmStageEntry 7 }

cucsMgmtExportPolicyFsmStageRetry OBJECT-TYPE
    SYNTAX       Gauge32
    MAX-ACCESS   read-only
    STATUS       current
    DESCRIPTION
        "Cisco UCS mgmt:ExportPolicyFsmStage:retry managed
        object property"
    ::= { cucsMgmtExportPolicyFsmStageEntry 8 }

cucsMgmtExportPolicyFsmStageStageStatus OBJECT-TYPE
    SYNTAX       CucsFsmFsmStageStatus
    MAX-ACCESS   read-only
    STATUS       current
    DESCRIPTION
        "Cisco UCS mgmt:ExportPolicyFsmStage:stageStatus
        managed object property"
    ::= { cucsMgmtExportPolicyFsmStageEntry 9 }

cucsMgmtExportPolicyFsmTaskTable OBJECT-TYPE
    SYNTAX           SEQUENCE OF CucsMgmtExportPolicyFsmTaskEntry
    MAX-ACCESS       not-accessible
    STATUS           current
    DESCRIPTION
        "Cisco UCS mgmt:ExportPolicyFsmTask managed object table"
    ::= { cucsMgmtObjects 28 }

cucsMgmtExportPolicyFsmTaskEntry OBJECT-TYPE
    SYNTAX           CucsMgmtExportPolicyFsmTaskEntry
    MAX-ACCESS       not-accessible
    STATUS           current
    DESCRIPTION
        "Entry for the cucsMgmtExportPolicyFsmTaskTable table."
    INDEX { cucsMgmtExportPolicyFsmTaskInstanceId }
    ::= { cucsMgmtExportPolicyFsmTaskTable 1 }

CucsMgmtExportPolicyFsmTaskEntry ::= SEQUENCE {
    cucsMgmtExportPolicyFsmTaskInstanceId                            CucsManagedObjectId,
    cucsMgmtExportPolicyFsmTaskDn                                    CucsManagedObjectDn,
    cucsMgmtExportPolicyFsmTaskRn                                    SnmpAdminString,
    cucsMgmtExportPolicyFsmTaskCompletion                            CucsFsmCompletion,
    cucsMgmtExportPolicyFsmTaskFlags                                 CucsFsmFlags,
    cucsMgmtExportPolicyFsmTaskItem                                  CucsMgmtExportPolicyFsmTaskItem,
    cucsMgmtExportPolicyFsmTaskSeqId                                 Gauge32
}

cucsMgmtExportPolicyFsmTaskInstanceId OBJECT-TYPE
    SYNTAX       CucsManagedObjectId
    MAX-ACCESS   not-accessible
    STATUS       current
    DESCRIPTION
        "Instance identifier of the managed object."
    ::= { cucsMgmtExportPolicyFsmTaskEntry 1 }

cucsMgmtExportPolicyFsmTaskDn OBJECT-TYPE
    SYNTAX       CucsManagedObjectDn
    MAX-ACCESS   read-only
    STATUS       current
    DESCRIPTION
        "Cisco UCS mgmt:ExportPolicyFsmTask:dn managed object property"
    ::= { cucsMgmtExportPolicyFsmTaskEntry 2 }

cucsMgmtExportPolicyFsmTaskRn OBJECT-TYPE
    SYNTAX       SnmpAdminString
    MAX-ACCESS   read-only
    STATUS       current
    DESCRIPTION
        "Cisco UCS mgmt:ExportPolicyFsmTask:rn managed object property"
    ::= { cucsMgmtExportPolicyFsmTaskEntry 3 }

cucsMgmtExportPolicyFsmTaskCompletion OBJECT-TYPE
    SYNTAX       CucsFsmCompletion
    MAX-ACCESS   read-only
    STATUS       current
    DESCRIPTION
        "Cisco UCS mgmt:ExportPolicyFsmTask:completion
        managed object property"
    ::= { cucsMgmtExportPolicyFsmTaskEntry 4 }

cucsMgmtExportPolicyFsmTaskFlags OBJECT-TYPE
    SYNTAX       CucsFsmFlags
    MAX-ACCESS   read-only
    STATUS       current
    DESCRIPTION
        "Cisco UCS mgmt:ExportPolicyFsmTask:flags managed object property"
    ::= { cucsMgmtExportPolicyFsmTaskEntry 5 }

cucsMgmtExportPolicyFsmTaskItem OBJECT-TYPE
    SYNTAX       CucsMgmtExportPolicyFsmTaskItem
    MAX-ACCESS   read-only
    STATUS       current
    DESCRIPTION
        "Cisco UCS mgmt:ExportPolicyFsmTask:item managed object property"
    ::= { cucsMgmtExportPolicyFsmTaskEntry 6 }

cucsMgmtExportPolicyFsmTaskSeqId OBJECT-TYPE
    SYNTAX       Gauge32
    MAX-ACCESS   read-only
    STATUS       current
    DESCRIPTION
        "Cisco UCS mgmt:ExportPolicyFsmTask:seqId managed object property"
    ::= { cucsMgmtExportPolicyFsmTaskEntry 7 }

cucsMgmtHealthAttrTable OBJECT-TYPE
    SYNTAX           SEQUENCE OF CucsMgmtHealthAttrEntry
    MAX-ACCESS       not-accessible
    STATUS           current
    DESCRIPTION
        "Cisco UCS mgmt:HealthAttr managed object table"
    ::= { cucsMgmtObjects 66 }

cucsMgmtHealthAttrEntry OBJECT-TYPE
    SYNTAX           CucsMgmtHealthAttrEntry
    MAX-ACCESS       not-accessible
    STATUS           current
    DESCRIPTION
        "Entry for the cucsMgmtHealthAttrTable table."
    INDEX { cucsMgmtHealthAttrInstanceId }
    ::= { cucsMgmtHealthAttrTable 1 }

CucsMgmtHealthAttrEntry ::= SEQUENCE {
    cucsMgmtHealthAttrInstanceId                                     CucsManagedObjectId,
    cucsMgmtHealthAttrDn                                             CucsManagedObjectDn,
    cucsMgmtHealthAttrRn                                             SnmpAdminString,
    cucsMgmtHealthAttrDescription                                    SnmpAdminString,
    cucsMgmtHealthAttrName                                           SnmpAdminString,
    cucsMgmtHealthAttrSeverity                                       CucsConditionSeverity,
    cucsMgmtHealthAttrValue                                          SnmpAdminString
}

cucsMgmtHealthAttrInstanceId OBJECT-TYPE
    SYNTAX       CucsManagedObjectId
    MAX-ACCESS   not-accessible
    STATUS       current
    DESCRIPTION
        "Instance identifier of the managed object."
    ::= { cucsMgmtHealthAttrEntry 1 }

cucsMgmtHealthAttrDn OBJECT-TYPE
    SYNTAX       CucsManagedObjectDn
    MAX-ACCESS   read-only
    STATUS       current
    DESCRIPTION
        "Cisco UCS mgmt:HealthAttr:dn managed object property"
    ::= { cucsMgmtHealthAttrEntry 2 }

cucsMgmtHealthAttrRn OBJECT-TYPE
    SYNTAX       SnmpAdminString
    MAX-ACCESS   read-only
    STATUS       current
    DESCRIPTION
        "Cisco UCS mgmt:HealthAttr:rn managed object property"
    ::= { cucsMgmtHealthAttrEntry 3 }

cucsMgmtHealthAttrDescription OBJECT-TYPE
    SYNTAX       SnmpAdminString
    MAX-ACCESS   read-only
    STATUS       current
    DESCRIPTION
        "Cisco UCS mgmt:HealthAttr:description managed object property"
    ::= { cucsMgmtHealthAttrEntry 4 }

cucsMgmtHealthAttrName OBJECT-TYPE
    SYNTAX       SnmpAdminString
    MAX-ACCESS   read-only
    STATUS       current
    DESCRIPTION
        "Cisco UCS mgmt:HealthAttr:name managed object property"
    ::= { cucsMgmtHealthAttrEntry 5 }

cucsMgmtHealthAttrSeverity OBJECT-TYPE
    SYNTAX       CucsConditionSeverity
    MAX-ACCESS   read-only
    STATUS       current
    DESCRIPTION
        "Cisco UCS mgmt:HealthAttr:severity managed object property"
    ::= { cucsMgmtHealthAttrEntry 6 }

cucsMgmtHealthAttrValue OBJECT-TYPE
    SYNTAX       SnmpAdminString
    MAX-ACCESS   read-only
    STATUS       current
    DESCRIPTION
        "Cisco UCS mgmt:HealthAttr:value managed object property"
    ::= { cucsMgmtHealthAttrEntry 7 }

cucsMgmtHealthStatusTable OBJECT-TYPE
    SYNTAX           SEQUENCE OF CucsMgmtHealthStatusEntry
    MAX-ACCESS       not-accessible
    STATUS           current
    DESCRIPTION
        "Cisco UCS mgmt:HealthStatus managed object table"
    ::= { cucsMgmtObjects 67 }

cucsMgmtHealthStatusEntry OBJECT-TYPE
    SYNTAX           CucsMgmtHealthStatusEntry
    MAX-ACCESS       not-accessible
    STATUS           current
    DESCRIPTION
        "Entry for the cucsMgmtHealthStatusTable table."
    INDEX { cucsMgmtHealthStatusInstanceId }
    ::= { cucsMgmtHealthStatusTable 1 }

CucsMgmtHealthStatusEntry ::= SEQUENCE {
    cucsMgmtHealthStatusInstanceId                                   CucsManagedObjectId,
    cucsMgmtHealthStatusDn                                           CucsManagedObjectDn,
    cucsMgmtHealthStatusRn                                           SnmpAdminString,
    cucsMgmtHealthStatusHealthQualifier                              SnmpAdminString,
    cucsMgmtHealthStatusHealthSeverity                               CucsConditionSeverity
}

cucsMgmtHealthStatusInstanceId OBJECT-TYPE
    SYNTAX       CucsManagedObjectId
    MAX-ACCESS   not-accessible
    STATUS       current
    DESCRIPTION
        "Instance identifier of the managed object."
    ::= { cucsMgmtHealthStatusEntry 1 }

cucsMgmtHealthStatusDn OBJECT-TYPE
    SYNTAX       CucsManagedObjectDn
    MAX-ACCESS   read-only
    STATUS       current
    DESCRIPTION
        "Cisco UCS mgmt:HealthStatus:dn managed object property"
    ::= { cucsMgmtHealthStatusEntry 2 }

cucsMgmtHealthStatusRn OBJECT-TYPE
    SYNTAX       SnmpAdminString
    MAX-ACCESS   read-only
    STATUS       current
    DESCRIPTION
        "Cisco UCS mgmt:HealthStatus:rn managed object property"
    ::= { cucsMgmtHealthStatusEntry 3 }

cucsMgmtHealthStatusHealthQualifier OBJECT-TYPE
    SYNTAX       SnmpAdminString
    MAX-ACCESS   read-only
    STATUS       current
    DESCRIPTION
        "Cisco UCS mgmt:HealthStatus:healthQualifier managed
        object property"
    ::= { cucsMgmtHealthStatusEntry 4 }

cucsMgmtHealthStatusHealthSeverity OBJECT-TYPE
    SYNTAX       CucsConditionSeverity
    MAX-ACCESS   read-only
    STATUS       current
    DESCRIPTION
        "Cisco UCS mgmt:HealthStatus:healthSeverity managed
        object property"
    ::= { cucsMgmtHealthStatusEntry 5 }

cucsMgmtIPv6IfAddrTable OBJECT-TYPE
    SYNTAX           SEQUENCE OF CucsMgmtIPv6IfAddrEntry
    MAX-ACCESS       not-accessible
    STATUS           current
    DESCRIPTION
        "Cisco UCS mgmt:IPv6IfAddr managed object table"
    ::= { cucsMgmtObjects 33 }

cucsMgmtIPv6IfAddrEntry OBJECT-TYPE
    SYNTAX           CucsMgmtIPv6IfAddrEntry
    MAX-ACCESS       not-accessible
    STATUS           current
    DESCRIPTION
        "Entry for the cucsMgmtIPv6IfAddrTable table."
    INDEX { cucsMgmtIPv6IfAddrInstanceId }
    ::= { cucsMgmtIPv6IfAddrTable 1 }

CucsMgmtIPv6IfAddrEntry ::= SEQUENCE {
    cucsMgmtIPv6IfAddrInstanceId                                     CucsManagedObjectId,
    cucsMgmtIPv6IfAddrDn                                             CucsManagedObjectDn,
    cucsMgmtIPv6IfAddrRn                                             SnmpAdminString,
    cucsMgmtIPv6IfAddrAddr                                           InetAddressIPv6,
    cucsMgmtIPv6IfAddrDefGw                                          InetAddressIPv6,
    cucsMgmtIPv6IfAddrFsmDescr                                       SnmpAdminString,
    cucsMgmtIPv6IfAddrFsmPrev                                        SnmpAdminString,
    cucsMgmtIPv6IfAddrFsmProgr                                       Gauge32,
    cucsMgmtIPv6IfAddrFsmRmtInvErrCode                               Gauge32,
    cucsMgmtIPv6IfAddrFsmRmtInvErrDescr                              SnmpAdminString,
    cucsMgmtIPv6IfAddrFsmRmtInvRslt                                  CucsConditionRemoteInvRslt,
    cucsMgmtIPv6IfAddrFsmStageDescr                                  SnmpAdminString,
    cucsMgmtIPv6IfAddrFsmStamp                                       DateAndTime,
    cucsMgmtIPv6IfAddrFsmStatus                                      SnmpAdminString,
    cucsMgmtIPv6IfAddrFsmTry                                         Gauge32,
    cucsMgmtIPv6IfAddrPrefix                                         Gauge32
}

cucsMgmtIPv6IfAddrInstanceId OBJECT-TYPE
    SYNTAX       CucsManagedObjectId
    MAX-ACCESS   not-accessible
    STATUS       current
    DESCRIPTION
        "Instance identifier of the managed object."
    ::= { cucsMgmtIPv6IfAddrEntry 1 }

cucsMgmtIPv6IfAddrDn OBJECT-TYPE
    SYNTAX       CucsManagedObjectDn
    MAX-ACCESS   read-only
    STATUS       current
    DESCRIPTION
        "Cisco UCS mgmt:IPv6IfAddr:dn managed object property"
    ::= { cucsMgmtIPv6IfAddrEntry 2 }

cucsMgmtIPv6IfAddrRn OBJECT-TYPE
    SYNTAX       SnmpAdminString
    MAX-ACCESS   read-only
    STATUS       current
    DESCRIPTION
        "Cisco UCS mgmt:IPv6IfAddr:rn managed object property"
    ::= { cucsMgmtIPv6IfAddrEntry 3 }

cucsMgmtIPv6IfAddrAddr OBJECT-TYPE
    SYNTAX       InetAddressIPv6
    MAX-ACCESS   read-only
    STATUS       current
    DESCRIPTION
        "Cisco UCS mgmt:IPv6IfAddr:addr managed object property"
    ::= { cucsMgmtIPv6IfAddrEntry 4 }

cucsMgmtIPv6IfAddrDefGw OBJECT-TYPE
    SYNTAX       InetAddressIPv6
    MAX-ACCESS   read-only
    STATUS       current
    DESCRIPTION
        "Cisco UCS mgmt:IPv6IfAddr:defGw managed object property"
    ::= { cucsMgmtIPv6IfAddrEntry 5 }

cucsMgmtIPv6IfAddrFsmDescr OBJECT-TYPE
    SYNTAX       SnmpAdminString
    MAX-ACCESS   read-only
    STATUS       current
    DESCRIPTION
        "Cisco UCS mgmt:IPv6IfAddr:fsmDescr managed object property"
    ::= { cucsMgmtIPv6IfAddrEntry 6 }

cucsMgmtIPv6IfAddrFsmPrev OBJECT-TYPE
    SYNTAX       SnmpAdminString
    MAX-ACCESS   read-only
    STATUS       current
    DESCRIPTION
        "Cisco UCS mgmt:IPv6IfAddr:fsmPrev managed object property"
    ::= { cucsMgmtIPv6IfAddrEntry 7 }

cucsMgmtIPv6IfAddrFsmProgr OBJECT-TYPE
    SYNTAX       Gauge32
    MAX-ACCESS   read-only
    STATUS       current
    DESCRIPTION
        "Cisco UCS mgmt:IPv6IfAddr:fsmProgr managed object property"
    ::= { cucsMgmtIPv6IfAddrEntry 8 }

cucsMgmtIPv6IfAddrFsmRmtInvErrCode OBJECT-TYPE
    SYNTAX       Gauge32
    MAX-ACCESS   read-only
    STATUS       current
    DESCRIPTION
        "Cisco UCS mgmt:IPv6IfAddr:fsmRmtInvErrCode managed
        object property"
    ::= { cucsMgmtIPv6IfAddrEntry 9 }

cucsMgmtIPv6IfAddrFsmRmtInvErrDescr OBJECT-TYPE
    SYNTAX       SnmpAdminString
    MAX-ACCESS   read-only
    STATUS       current
    DESCRIPTION
        "Cisco UCS mgmt:IPv6IfAddr:fsmRmtInvErrDescr managed
        object property"
    ::= { cucsMgmtIPv6IfAddrEntry 10 }

cucsMgmtIPv6IfAddrFsmRmtInvRslt OBJECT-TYPE
    SYNTAX       CucsConditionRemoteInvRslt
    MAX-ACCESS   read-only
    STATUS       current
    DESCRIPTION
        "Cisco UCS mgmt:IPv6IfAddr:fsmRmtInvRslt managed object property"
    ::= { cucsMgmtIPv6IfAddrEntry 11 }

cucsMgmtIPv6IfAddrFsmStageDescr OBJECT-TYPE
    SYNTAX       SnmpAdminString
    MAX-ACCESS   read-only
    STATUS       current
    DESCRIPTION
        "Cisco UCS mgmt:IPv6IfAddr:fsmStageDescr managed object property"
    ::= { cucsMgmtIPv6IfAddrEntry 12 }

cucsMgmtIPv6IfAddrFsmStamp OBJECT-TYPE
    SYNTAX       DateAndTime
    MAX-ACCESS   read-only
    STATUS       current
    DESCRIPTION
        "Cisco UCS mgmt:IPv6IfAddr:fsmStamp managed object property"
    ::= { cucsMgmtIPv6IfAddrEntry 13 }

cucsMgmtIPv6IfAddrFsmStatus OBJECT-TYPE
    SYNTAX       SnmpAdminString
    MAX-ACCESS   read-only
    STATUS       current
    DESCRIPTION
        "Cisco UCS mgmt:IPv6IfAddr:fsmStatus managed object property"
    ::= { cucsMgmtIPv6IfAddrEntry 14 }

cucsMgmtIPv6IfAddrFsmTry OBJECT-TYPE
    SYNTAX       Gauge32
    MAX-ACCESS   read-only
    STATUS       current
    DESCRIPTION
        "Cisco UCS mgmt:IPv6IfAddr:fsmTry managed object property"
    ::= { cucsMgmtIPv6IfAddrEntry 15 }

cucsMgmtIPv6IfAddrPrefix OBJECT-TYPE
    SYNTAX       Gauge32
    MAX-ACCESS   read-only
    STATUS       current
    DESCRIPTION
        "Cisco UCS mgmt:IPv6IfAddr:prefix managed object property"
    ::= { cucsMgmtIPv6IfAddrEntry 16 }

cucsMgmtIPv6IfAddrFsmTable OBJECT-TYPE
    SYNTAX           SEQUENCE OF CucsMgmtIPv6IfAddrFsmEntry
    MAX-ACCESS       not-accessible
    STATUS           current
    DESCRIPTION
        "Cisco UCS mgmt:IPv6IfAddrFsm managed object table"
    ::= { cucsMgmtObjects 34 }

cucsMgmtIPv6IfAddrFsmEntry OBJECT-TYPE
    SYNTAX           CucsMgmtIPv6IfAddrFsmEntry
    MAX-ACCESS       not-accessible
    STATUS           current
    DESCRIPTION
        "Entry for the cucsMgmtIPv6IfAddrFsmTable table."
    INDEX { cucsMgmtIPv6IfAddrFsmInstanceId }
    ::= { cucsMgmtIPv6IfAddrFsmTable 1 }

CucsMgmtIPv6IfAddrFsmEntry ::= SEQUENCE {
    cucsMgmtIPv6IfAddrFsmInstanceId                                  CucsManagedObjectId,
    cucsMgmtIPv6IfAddrFsmDn                                          CucsManagedObjectDn,
    cucsMgmtIPv6IfAddrFsmRn                                          SnmpAdminString,
    cucsMgmtIPv6IfAddrFsmCompletionTime                              DateAndTime,
    cucsMgmtIPv6IfAddrFsmCurrentFsm                                  CucsMgmtIPv6IfAddrFsmCurrentFsm,
    cucsMgmtIPv6IfAddrFsmDescrData                                   SnmpAdminString,
    cucsMgmtIPv6IfAddrFsmFsmStatus                                   CucsFsmFsmStageStatus,
    cucsMgmtIPv6IfAddrFsmProgress                                    Gauge32,
    cucsMgmtIPv6IfAddrFsmRmtErrCode                                  Gauge32,
    cucsMgmtIPv6IfAddrFsmRmtErrDescr                                 SnmpAdminString,
    cucsMgmtIPv6IfAddrFsmRmtRslt                                     CucsConditionRemoteInvRslt
}

cucsMgmtIPv6IfAddrFsmInstanceId OBJECT-TYPE
    SYNTAX       CucsManagedObjectId
    MAX-ACCESS   not-accessible
    STATUS       current
    DESCRIPTION
        "Instance identifier of the managed object."
    ::= { cucsMgmtIPv6IfAddrFsmEntry 1 }

cucsMgmtIPv6IfAddrFsmDn OBJECT-TYPE
    SYNTAX       CucsManagedObjectDn
    MAX-ACCESS   read-only
    STATUS       current
    DESCRIPTION
        "Cisco UCS mgmt:IPv6IfAddrFsm:dn managed object property"
    ::= { cucsMgmtIPv6IfAddrFsmEntry 2 }

cucsMgmtIPv6IfAddrFsmRn OBJECT-TYPE
    SYNTAX       SnmpAdminString
    MAX-ACCESS   read-only
    STATUS       current
    DESCRIPTION
        "Cisco UCS mgmt:IPv6IfAddrFsm:rn managed object property"
    ::= { cucsMgmtIPv6IfAddrFsmEntry 3 }

cucsMgmtIPv6IfAddrFsmCompletionTime OBJECT-TYPE
    SYNTAX       DateAndTime
    MAX-ACCESS   read-only
    STATUS       current
    DESCRIPTION
        "Cisco UCS mgmt:IPv6IfAddrFsm:completionTime managed
        object property"
    ::= { cucsMgmtIPv6IfAddrFsmEntry 4 }

cucsMgmtIPv6IfAddrFsmCurrentFsm OBJECT-TYPE
    SYNTAX       CucsMgmtIPv6IfAddrFsmCurrentFsm
    MAX-ACCESS   read-only
    STATUS       current
    DESCRIPTION
        "Cisco UCS mgmt:IPv6IfAddrFsm:currentFsm managed object property"
    ::= { cucsMgmtIPv6IfAddrFsmEntry 5 }

cucsMgmtIPv6IfAddrFsmDescrData OBJECT-TYPE
    SYNTAX       SnmpAdminString
    MAX-ACCESS   read-only
    STATUS       current
    DESCRIPTION
        "Cisco UCS mgmt:IPv6IfAddrFsm:descr managed object property"
    ::= { cucsMgmtIPv6IfAddrFsmEntry 6 }

cucsMgmtIPv6IfAddrFsmFsmStatus OBJECT-TYPE
    SYNTAX       CucsFsmFsmStageStatus
    MAX-ACCESS   read-only
    STATUS       current
    DESCRIPTION
        "Cisco UCS mgmt:IPv6IfAddrFsm:fsmStatus managed object property"
    ::= { cucsMgmtIPv6IfAddrFsmEntry 7 }

cucsMgmtIPv6IfAddrFsmProgress OBJECT-TYPE
    SYNTAX       Gauge32
    MAX-ACCESS   read-only
    STATUS       current
    DESCRIPTION
        "Cisco UCS mgmt:IPv6IfAddrFsm:progress managed object property"
    ::= { cucsMgmtIPv6IfAddrFsmEntry 8 }

cucsMgmtIPv6IfAddrFsmRmtErrCode OBJECT-TYPE
    SYNTAX       Gauge32
    MAX-ACCESS   read-only
    STATUS       current
    DESCRIPTION
        "Cisco UCS mgmt:IPv6IfAddrFsm:rmtErrCode managed object property"
    ::= { cucsMgmtIPv6IfAddrFsmEntry 9 }

cucsMgmtIPv6IfAddrFsmRmtErrDescr OBJECT-TYPE
    SYNTAX       SnmpAdminString
    MAX-ACCESS   read-only
    STATUS       current
    DESCRIPTION
        "Cisco UCS mgmt:IPv6IfAddrFsm:rmtErrDescr managed object property"
    ::= { cucsMgmtIPv6IfAddrFsmEntry 10 }

cucsMgmtIPv6IfAddrFsmRmtRslt OBJECT-TYPE
    SYNTAX       CucsConditionRemoteInvRslt
    MAX-ACCESS   read-only
    STATUS       current
    DESCRIPTION
        "Cisco UCS mgmt:IPv6IfAddrFsm:rmtRslt managed object property"
    ::= { cucsMgmtIPv6IfAddrFsmEntry 11 }

cucsMgmtIPv6IfAddrFsmStageTable OBJECT-TYPE
    SYNTAX           SEQUENCE OF CucsMgmtIPv6IfAddrFsmStageEntry
    MAX-ACCESS       not-accessible
    STATUS           current
    DESCRIPTION
        "Cisco UCS mgmt:IPv6IfAddrFsmStage managed object table"
    ::= { cucsMgmtObjects 35 }

cucsMgmtIPv6IfAddrFsmStageEntry OBJECT-TYPE
    SYNTAX           CucsMgmtIPv6IfAddrFsmStageEntry
    MAX-ACCESS       not-accessible
    STATUS           current
    DESCRIPTION
        "Entry for the cucsMgmtIPv6IfAddrFsmStageTable table."
    INDEX { cucsMgmtIPv6IfAddrFsmStageInstanceId }
    ::= { cucsMgmtIPv6IfAddrFsmStageTable 1 }

CucsMgmtIPv6IfAddrFsmStageEntry ::= SEQUENCE {
    cucsMgmtIPv6IfAddrFsmStageInstanceId                             CucsManagedObjectId,
    cucsMgmtIPv6IfAddrFsmStageDn                                     CucsManagedObjectDn,
    cucsMgmtIPv6IfAddrFsmStageRn                                     SnmpAdminString,
    cucsMgmtIPv6IfAddrFsmStageDescrData                              SnmpAdminString,
    cucsMgmtIPv6IfAddrFsmStageLastUpdateTime                         DateAndTime,
    cucsMgmtIPv6IfAddrFsmStageName                                   CucsMgmtIPv6IfAddrFsmStageName,
    cucsMgmtIPv6IfAddrFsmStageOrder                                  Gauge32,
    cucsMgmtIPv6IfAddrFsmStageRetry                                  Gauge32,
    cucsMgmtIPv6IfAddrFsmStageStageStatus                            CucsFsmFsmStageStatus
}

cucsMgmtIPv6IfAddrFsmStageInstanceId OBJECT-TYPE
    SYNTAX       CucsManagedObjectId
    MAX-ACCESS   not-accessible
    STATUS       current
    DESCRIPTION
        "Instance identifier of the managed object."
    ::= { cucsMgmtIPv6IfAddrFsmStageEntry 1 }

cucsMgmtIPv6IfAddrFsmStageDn OBJECT-TYPE
    SYNTAX       CucsManagedObjectDn
    MAX-ACCESS   read-only
    STATUS       current
    DESCRIPTION
        "Cisco UCS mgmt:IPv6IfAddrFsmStage:dn managed object property"
    ::= { cucsMgmtIPv6IfAddrFsmStageEntry 2 }

cucsMgmtIPv6IfAddrFsmStageRn OBJECT-TYPE
    SYNTAX       SnmpAdminString
    MAX-ACCESS   read-only
    STATUS       current
    DESCRIPTION
        "Cisco UCS mgmt:IPv6IfAddrFsmStage:rn managed object property"
    ::= { cucsMgmtIPv6IfAddrFsmStageEntry 3 }

cucsMgmtIPv6IfAddrFsmStageDescrData OBJECT-TYPE
    SYNTAX       SnmpAdminString
    MAX-ACCESS   read-only
    STATUS       current
    DESCRIPTION
        "Cisco UCS mgmt:IPv6IfAddrFsmStage:descr managed object property"
    ::= { cucsMgmtIPv6IfAddrFsmStageEntry 4 }

cucsMgmtIPv6IfAddrFsmStageLastUpdateTime OBJECT-TYPE
    SYNTAX       DateAndTime
    MAX-ACCESS   read-only
    STATUS       current
    DESCRIPTION
        "Cisco UCS mgmt:IPv6IfAddrFsmStage:lastUpdateTime
        managed object property"
    ::= { cucsMgmtIPv6IfAddrFsmStageEntry 5 }

cucsMgmtIPv6IfAddrFsmStageName OBJECT-TYPE
    SYNTAX       CucsMgmtIPv6IfAddrFsmStageName
    MAX-ACCESS   read-only
    STATUS       current
    DESCRIPTION
        "Cisco UCS mgmt:IPv6IfAddrFsmStage:name managed object property"
    ::= { cucsMgmtIPv6IfAddrFsmStageEntry 6 }

cucsMgmtIPv6IfAddrFsmStageOrder OBJECT-TYPE
    SYNTAX       Gauge32
    MAX-ACCESS   read-only
    STATUS       current
    DESCRIPTION
        "Cisco UCS mgmt:IPv6IfAddrFsmStage:order managed object property"
    ::= { cucsMgmtIPv6IfAddrFsmStageEntry 7 }

cucsMgmtIPv6IfAddrFsmStageRetry OBJECT-TYPE
    SYNTAX       Gauge32
    MAX-ACCESS   read-only
    STATUS       current
    DESCRIPTION
        "Cisco UCS mgmt:IPv6IfAddrFsmStage:retry managed object property"
    ::= { cucsMgmtIPv6IfAddrFsmStageEntry 8 }

cucsMgmtIPv6IfAddrFsmStageStageStatus OBJECT-TYPE
    SYNTAX       CucsFsmFsmStageStatus
    MAX-ACCESS   read-only
    STATUS       current
    DESCRIPTION
        "Cisco UCS mgmt:IPv6IfAddrFsmStage:stageStatus
        managed object property"
    ::= { cucsMgmtIPv6IfAddrFsmStageEntry 9 }

cucsMgmtIPv6IfAddrFsmTaskTable OBJECT-TYPE
    SYNTAX           SEQUENCE OF CucsMgmtIPv6IfAddrFsmTaskEntry
    MAX-ACCESS       not-accessible
    STATUS           current
    DESCRIPTION
        "Cisco UCS mgmt:IPv6IfAddrFsmTask managed object table"
    ::= { cucsMgmtObjects 36 }

cucsMgmtIPv6IfAddrFsmTaskEntry OBJECT-TYPE
    SYNTAX           CucsMgmtIPv6IfAddrFsmTaskEntry
    MAX-ACCESS       not-accessible
    STATUS           current
    DESCRIPTION
        "Entry for the cucsMgmtIPv6IfAddrFsmTaskTable table."
    INDEX { cucsMgmtIPv6IfAddrFsmTaskInstanceId }
    ::= { cucsMgmtIPv6IfAddrFsmTaskTable 1 }

CucsMgmtIPv6IfAddrFsmTaskEntry ::= SEQUENCE {
    cucsMgmtIPv6IfAddrFsmTaskInstanceId                              CucsManagedObjectId,
    cucsMgmtIPv6IfAddrFsmTaskDn                                      CucsManagedObjectDn,
    cucsMgmtIPv6IfAddrFsmTaskRn                                      SnmpAdminString,
    cucsMgmtIPv6IfAddrFsmTaskCompletion                              CucsFsmCompletion,
    cucsMgmtIPv6IfAddrFsmTaskFlags                                   CucsFsmFlags,
    cucsMgmtIPv6IfAddrFsmTaskItem                                    CucsMgmtIPv6IfAddrFsmTaskItem,
    cucsMgmtIPv6IfAddrFsmTaskSeqId                                   Gauge32
}

cucsMgmtIPv6IfAddrFsmTaskInstanceId OBJECT-TYPE
    SYNTAX       CucsManagedObjectId
    MAX-ACCESS   not-accessible
    STATUS       current
    DESCRIPTION
        "Instance identifier of the managed object."
    ::= { cucsMgmtIPv6IfAddrFsmTaskEntry 1 }

cucsMgmtIPv6IfAddrFsmTaskDn OBJECT-TYPE
    SYNTAX       CucsManagedObjectDn
    MAX-ACCESS   read-only
    STATUS       current
    DESCRIPTION
        "Cisco UCS mgmt:IPv6IfAddrFsmTask:dn managed object property"
    ::= { cucsMgmtIPv6IfAddrFsmTaskEntry 2 }

cucsMgmtIPv6IfAddrFsmTaskRn OBJECT-TYPE
    SYNTAX       SnmpAdminString
    MAX-ACCESS   read-only
    STATUS       current
    DESCRIPTION
        "Cisco UCS mgmt:IPv6IfAddrFsmTask:rn managed object property"
    ::= { cucsMgmtIPv6IfAddrFsmTaskEntry 3 }

cucsMgmtIPv6IfAddrFsmTaskCompletion OBJECT-TYPE
    SYNTAX       CucsFsmCompletion
    MAX-ACCESS   read-only
    STATUS       current
    DESCRIPTION
        "Cisco UCS mgmt:IPv6IfAddrFsmTask:completion managed
        object property"
    ::= { cucsMgmtIPv6IfAddrFsmTaskEntry 4 }

cucsMgmtIPv6IfAddrFsmTaskFlags OBJECT-TYPE
    SYNTAX       CucsFsmFlags
    MAX-ACCESS   read-only
    STATUS       current
    DESCRIPTION
        "Cisco UCS mgmt:IPv6IfAddrFsmTask:flags managed object property"
    ::= { cucsMgmtIPv6IfAddrFsmTaskEntry 5 }

cucsMgmtIPv6IfAddrFsmTaskItem OBJECT-TYPE
    SYNTAX       CucsMgmtIPv6IfAddrFsmTaskItem
    MAX-ACCESS   read-only
    STATUS       current
    DESCRIPTION
        "Cisco UCS mgmt:IPv6IfAddrFsmTask:item managed object property"
    ::= { cucsMgmtIPv6IfAddrFsmTaskEntry 6 }

cucsMgmtIPv6IfAddrFsmTaskSeqId OBJECT-TYPE
    SYNTAX       Gauge32
    MAX-ACCESS   read-only
    STATUS       current
    DESCRIPTION
        "Cisco UCS mgmt:IPv6IfAddrFsmTask:seqId managed object property"
    ::= { cucsMgmtIPv6IfAddrFsmTaskEntry 7 }

cucsMgmtIPv6IfConfigTable OBJECT-TYPE
    SYNTAX           SEQUENCE OF CucsMgmtIPv6IfConfigEntry
    MAX-ACCESS       not-accessible
    STATUS           current
    DESCRIPTION
        "Cisco UCS mgmt:IPv6IfConfig managed object table"
    ::= { cucsMgmtObjects 37 }

cucsMgmtIPv6IfConfigEntry OBJECT-TYPE
    SYNTAX           CucsMgmtIPv6IfConfigEntry
    MAX-ACCESS       not-accessible
    STATUS           current
    DESCRIPTION
        "Entry for the cucsMgmtIPv6IfConfigTable table."
    INDEX { cucsMgmtIPv6IfConfigInstanceId }
    ::= { cucsMgmtIPv6IfConfigTable 1 }

CucsMgmtIPv6IfConfigEntry ::= SEQUENCE {
    cucsMgmtIPv6IfConfigInstanceId                                   CucsManagedObjectId,
    cucsMgmtIPv6IfConfigDn                                           CucsManagedObjectDn,
    cucsMgmtIPv6IfConfigRn                                           SnmpAdminString
}

cucsMgmtIPv6IfConfigInstanceId OBJECT-TYPE
    SYNTAX       CucsManagedObjectId
    MAX-ACCESS   not-accessible
    STATUS       current
    DESCRIPTION
        "Instance identifier of the managed object."
    ::= { cucsMgmtIPv6IfConfigEntry 1 }

cucsMgmtIPv6IfConfigDn OBJECT-TYPE
    SYNTAX       CucsManagedObjectDn
    MAX-ACCESS   read-only
    STATUS       current
    DESCRIPTION
        "Cisco UCS mgmt:IPv6IfConfig:dn managed object property"
    ::= { cucsMgmtIPv6IfConfigEntry 2 }

cucsMgmtIPv6IfConfigRn OBJECT-TYPE
    SYNTAX       SnmpAdminString
    MAX-ACCESS   read-only
    STATUS       current
    DESCRIPTION
        "Cisco UCS mgmt:IPv6IfConfig:rn managed object property"
    ::= { cucsMgmtIPv6IfConfigEntry 3 }

cucsMgmtIfTable OBJECT-TYPE
    SYNTAX           SEQUENCE OF CucsMgmtIfEntry
    MAX-ACCESS       not-accessible
    STATUS           current
    DESCRIPTION
        "Cisco UCS mgmt:If managed object table"
    ::= { cucsMgmtObjects 9 }

cucsMgmtIfEntry OBJECT-TYPE
    SYNTAX           CucsMgmtIfEntry
    MAX-ACCESS       not-accessible
    STATUS           current
    DESCRIPTION
        "Entry for the cucsMgmtIfTable table."
    INDEX { cucsMgmtIfInstanceId }
    ::= { cucsMgmtIfTable 1 }

CucsMgmtIfEntry ::= SEQUENCE {
    cucsMgmtIfInstanceId                                             CucsManagedObjectId,
    cucsMgmtIfDn                                                     CucsManagedObjectDn,
    cucsMgmtIfRn                                                     SnmpAdminString,
    cucsMgmtIfAccess                                                 CucsMgmtAccess,
    cucsMgmtIfAdminState                                             CucsMgmtMgmtAdminState,
    cucsMgmtIfChassisId                                              Gauge32,
    cucsMgmtIfDiscovery                                              CucsEtherSatelliteConnectionDisc,
    cucsMgmtIfEpDn                                                   SnmpAdminString,
    cucsMgmtIfExtBroadcast                                           InetAddressIPv4,
    cucsMgmtIfExtGw                                                  InetAddressIPv4,
    cucsMgmtIfExtIp                                                  InetAddressIPv4,
    cucsMgmtIfExtMask                                                InetAddressIPv4,
    cucsMgmtIfFsmDescr                                               SnmpAdminString,
    cucsMgmtIfFsmPrev                                                SnmpAdminString,
    cucsMgmtIfFsmProgr                                               Gauge32,
    cucsMgmtIfFsmRmtInvErrCode                                       Gauge32,
    cucsMgmtIfFsmRmtInvErrDescr                                      SnmpAdminString,
    cucsMgmtIfFsmRmtInvRslt                                          CucsConditionRemoteInvRslt,
    cucsMgmtIfFsmStageDescr                                          SnmpAdminString,
    cucsMgmtIfFsmStamp                                               DateAndTime,
    cucsMgmtIfFsmStatus                                              SnmpAdminString,
    cucsMgmtIfFsmTry                                                 Gauge32,
    cucsMgmtIfId                                                     Gauge32,
    cucsMgmtIfIfRole                                                 CucsNetworkPortRole,
    cucsMgmtIfIfType                                                 CucsNetworkPhysEpIfType,
    cucsMgmtIfIp                                                     InetAddressIPv4,
    cucsMgmtIfLocale                                                 CucsNetworkLocale,
    cucsMgmtIfMac                                                    MacAddress,
    cucsMgmtIfMask                                                   InetAddressIPv4,
    cucsMgmtIfName                                                   SnmpAdminString,
    cucsMgmtIfPeerDn                                                 SnmpAdminString,
    cucsMgmtIfPeerPortId                                             Gauge32,
    cucsMgmtIfPeerSlotId                                             Gauge32,
    cucsMgmtIfPortId                                                 Gauge32,
    cucsMgmtIfSlotId                                                 Gauge32,
    cucsMgmtIfStateQual                                              CucsMgmtStateQual,
    cucsMgmtIfSubject                                                CucsMgmtSubject,
    cucsMgmtIfSwitchId                                               CucsNetworkSwitchId,
    cucsMgmtIfTransport                                              CucsNetworkTransport,
    cucsMgmtIfType                                                   CucsNetworkConnectionType,
    cucsMgmtIfVnet                                                   Gauge32,
    cucsMgmtIfPeerChassisId                                          Gauge32,
    cucsMgmtIfAggrPortId                                             Gauge32,
    cucsMgmtIfPeerAggrPortId                                         Gauge32
}

cucsMgmtIfInstanceId OBJECT-TYPE
    SYNTAX       CucsManagedObjectId
    MAX-ACCESS   not-accessible
    STATUS       current
    DESCRIPTION
        "Instance identifier of the managed object."
    ::= { cucsMgmtIfEntry 1 }

cucsMgmtIfDn OBJECT-TYPE
    SYNTAX       CucsManagedObjectDn
    MAX-ACCESS   read-only
    STATUS       current
    DESCRIPTION
        "Cisco UCS mgmt:If:dn managed object property"
    ::= { cucsMgmtIfEntry 2 }

cucsMgmtIfRn OBJECT-TYPE
    SYNTAX       SnmpAdminString
    MAX-ACCESS   read-only
    STATUS       current
    DESCRIPTION
        "Cisco UCS mgmt:If:rn managed object property"
    ::= { cucsMgmtIfEntry 3 }

cucsMgmtIfAccess OBJECT-TYPE
    SYNTAX       CucsMgmtAccess
    MAX-ACCESS   read-only
    STATUS       current
    DESCRIPTION
        "Cisco UCS mgmt:If:access managed object property"
    ::= { cucsMgmtIfEntry 4 }

cucsMgmtIfAdminState OBJECT-TYPE
    SYNTAX       CucsMgmtMgmtAdminState
    MAX-ACCESS   read-only
    STATUS       current
    DESCRIPTION
        "Cisco UCS mgmt:If:adminState managed object property"
    ::= { cucsMgmtIfEntry 5 }

cucsMgmtIfChassisId OBJECT-TYPE
    SYNTAX       Gauge32
    MAX-ACCESS   read-only
    STATUS       current
    DESCRIPTION
        "Cisco UCS mgmt:If:chassisId managed object property"
    ::= { cucsMgmtIfEntry 6 }

cucsMgmtIfDiscovery OBJECT-TYPE
    SYNTAX       CucsEtherSatelliteConnectionDisc
    MAX-ACCESS   read-only
    STATUS       current
    DESCRIPTION
        "Cisco UCS mgmt:If:discovery managed object property"
    ::= { cucsMgmtIfEntry 7 }

cucsMgmtIfEpDn OBJECT-TYPE
    SYNTAX       SnmpAdminString
    MAX-ACCESS   read-only
    STATUS       current
    DESCRIPTION
        "Cisco UCS mgmt:If:epDn managed object property"
    ::= { cucsMgmtIfEntry 8 }

cucsMgmtIfExtBroadcast OBJECT-TYPE
    SYNTAX       InetAddressIPv4
    MAX-ACCESS   read-only
    STATUS       current
    DESCRIPTION
        "Cisco UCS mgmt:If:extBroadcast managed object property"
    ::= { cucsMgmtIfEntry 9 }

cucsMgmtIfExtGw OBJECT-TYPE
    SYNTAX       InetAddressIPv4
    MAX-ACCESS   read-only
    STATUS       current
    DESCRIPTION
        "Cisco UCS mgmt:If:extGw managed object property"
    ::= { cucsMgmtIfEntry 10 }

cucsMgmtIfExtIp OBJECT-TYPE
    SYNTAX       InetAddressIPv4
    MAX-ACCESS   read-only
    STATUS       current
    DESCRIPTION
        "Cisco UCS mgmt:If:extIp managed object property"
    ::= { cucsMgmtIfEntry 11 }

cucsMgmtIfExtMask OBJECT-TYPE
    SYNTAX       InetAddressIPv4
    MAX-ACCESS   read-only
    STATUS       current
    DESCRIPTION
        "Cisco UCS mgmt:If:extMask managed object property"
    ::= { cucsMgmtIfEntry 12 }

cucsMgmtIfFsmDescr OBJECT-TYPE
    SYNTAX       SnmpAdminString
    MAX-ACCESS   read-only
    STATUS       current
    DESCRIPTION
        "Cisco UCS mgmt:If:fsmDescr managed object property"
    ::= { cucsMgmtIfEntry 13 }

cucsMgmtIfFsmPrev OBJECT-TYPE
    SYNTAX       SnmpAdminString
    MAX-ACCESS   read-only
    STATUS       current
    DESCRIPTION
        "Cisco UCS mgmt:If:fsmPrev managed object property"
    ::= { cucsMgmtIfEntry 14 }

cucsMgmtIfFsmProgr OBJECT-TYPE
    SYNTAX       Gauge32
    MAX-ACCESS   read-only
    STATUS       current
    DESCRIPTION
        "Cisco UCS mgmt:If:fsmProgr managed object property"
    ::= { cucsMgmtIfEntry 15 }

cucsMgmtIfFsmRmtInvErrCode OBJECT-TYPE
    SYNTAX       Gauge32
    MAX-ACCESS   read-only
    STATUS       current
    DESCRIPTION
        "Cisco UCS mgmt:If:fsmRmtInvErrCode managed object property"
    ::= { cucsMgmtIfEntry 16 }

cucsMgmtIfFsmRmtInvErrDescr OBJECT-TYPE
    SYNTAX       SnmpAdminString
    MAX-ACCESS   read-only
    STATUS       current
    DESCRIPTION
        "Cisco UCS mgmt:If:fsmRmtInvErrDescr managed object property"
    ::= { cucsMgmtIfEntry 17 }

cucsMgmtIfFsmRmtInvRslt OBJECT-TYPE
    SYNTAX       CucsConditionRemoteInvRslt
    MAX-ACCESS   read-only
    STATUS       current
    DESCRIPTION
        "Cisco UCS mgmt:If:fsmRmtInvRslt managed object property"
    ::= { cucsMgmtIfEntry 18 }

cucsMgmtIfFsmStageDescr OBJECT-TYPE
    SYNTAX       SnmpAdminString
    MAX-ACCESS   read-only
    STATUS       current
    DESCRIPTION
        "Cisco UCS mgmt:If:fsmStageDescr managed object property"
    ::= { cucsMgmtIfEntry 19 }

cucsMgmtIfFsmStamp OBJECT-TYPE
    SYNTAX       DateAndTime
    MAX-ACCESS   read-only
    STATUS       current
    DESCRIPTION
        "Cisco UCS mgmt:If:fsmStamp managed object property"
    ::= { cucsMgmtIfEntry 20 }

cucsMgmtIfFsmStatus OBJECT-TYPE
    SYNTAX       SnmpAdminString
    MAX-ACCESS   read-only
    STATUS       current
    DESCRIPTION
        "Cisco UCS mgmt:If:fsmStatus managed object property"
    ::= { cucsMgmtIfEntry 21 }

cucsMgmtIfFsmTry OBJECT-TYPE
    SYNTAX       Gauge32
    MAX-ACCESS   read-only
    STATUS       current
    DESCRIPTION
        "Cisco UCS mgmt:If:fsmTry managed object property"
    ::= { cucsMgmtIfEntry 22 }

cucsMgmtIfId OBJECT-TYPE
    SYNTAX       Gauge32
    MAX-ACCESS   read-only
    STATUS       current
    DESCRIPTION
        "Cisco UCS mgmt:If:id managed object property"
    ::= { cucsMgmtIfEntry 23 }

cucsMgmtIfIfRole OBJECT-TYPE
    SYNTAX       CucsNetworkPortRole
    MAX-ACCESS   read-only
    STATUS       current
    DESCRIPTION
        "Cisco UCS mgmt:If:ifRole managed object property"
    ::= { cucsMgmtIfEntry 24 }

cucsMgmtIfIfType OBJECT-TYPE
    SYNTAX       CucsNetworkPhysEpIfType
    MAX-ACCESS   read-only
    STATUS       current
    DESCRIPTION
        "Cisco UCS mgmt:If:ifType managed object property"
    ::= { cucsMgmtIfEntry 25 }

cucsMgmtIfIp OBJECT-TYPE
    SYNTAX       InetAddressIPv4
    MAX-ACCESS   read-only
    STATUS       current
    DESCRIPTION
        "Cisco UCS mgmt:If:ip managed object property"
    ::= { cucsMgmtIfEntry 26 }

cucsMgmtIfLocale OBJECT-TYPE
    SYNTAX       CucsNetworkLocale
    MAX-ACCESS   read-only
    STATUS       current
    DESCRIPTION
        "Cisco UCS mgmt:If:locale managed object property"
    ::= { cucsMgmtIfEntry 27 }

cucsMgmtIfMac OBJECT-TYPE
    SYNTAX       MacAddress
    MAX-ACCESS   read-only
    STATUS       current
    DESCRIPTION
        "Cisco UCS mgmt:If:mac managed object property"
    ::= { cucsMgmtIfEntry 28 }

cucsMgmtIfMask OBJECT-TYPE
    SYNTAX       InetAddressIPv4
    MAX-ACCESS   read-only
    STATUS       current
    DESCRIPTION
        "Cisco UCS mgmt:If:mask managed object property"
    ::= { cucsMgmtIfEntry 29 }

cucsMgmtIfName OBJECT-TYPE
    SYNTAX       SnmpAdminString
    MAX-ACCESS   read-only
    STATUS       current
    DESCRIPTION
        "Cisco UCS mgmt:If:name managed object property"
    ::= { cucsMgmtIfEntry 30 }

cucsMgmtIfPeerDn OBJECT-TYPE
    SYNTAX       SnmpAdminString
    MAX-ACCESS   read-only
    STATUS       current
    DESCRIPTION
        "Cisco UCS mgmt:If:peerDn managed object property"
    ::= { cucsMgmtIfEntry 31 }

cucsMgmtIfPeerPortId OBJECT-TYPE
    SYNTAX       Gauge32
    MAX-ACCESS   read-only
    STATUS       current
    DESCRIPTION
        "Cisco UCS mgmt:If:peerPortId managed object property"
    ::= { cucsMgmtIfEntry 32 }

cucsMgmtIfPeerSlotId OBJECT-TYPE
    SYNTAX       Gauge32
    MAX-ACCESS   read-only
    STATUS       current
    DESCRIPTION
        "Cisco UCS mgmt:If:peerSlotId managed object property"
    ::= { cucsMgmtIfEntry 33 }

cucsMgmtIfPortId OBJECT-TYPE
    SYNTAX       Gauge32
    MAX-ACCESS   read-only
    STATUS       current
    DESCRIPTION
        "Cisco UCS mgmt:If:portId managed object property"
    ::= { cucsMgmtIfEntry 34 }

cucsMgmtIfSlotId OBJECT-TYPE
    SYNTAX       Gauge32
    MAX-ACCESS   read-only
    STATUS       current
    DESCRIPTION
        "Cisco UCS mgmt:If:slotId managed object property"
    ::= { cucsMgmtIfEntry 35 }

cucsMgmtIfStateQual OBJECT-TYPE
    SYNTAX       CucsMgmtStateQual
    MAX-ACCESS   read-only
    STATUS       current
    DESCRIPTION
        "Cisco UCS mgmt:If:stateQual managed object property"
    ::= { cucsMgmtIfEntry 36 }

cucsMgmtIfSubject OBJECT-TYPE
    SYNTAX       CucsMgmtSubject
    MAX-ACCESS   read-only
    STATUS       current
    DESCRIPTION
        "Cisco UCS mgmt:If:subject managed object property"
    ::= { cucsMgmtIfEntry 37 }

cucsMgmtIfSwitchId OBJECT-TYPE
    SYNTAX       CucsNetworkSwitchId
    MAX-ACCESS   read-only
    STATUS       current
    DESCRIPTION
        "Cisco UCS mgmt:If:switchId managed object property"
    ::= { cucsMgmtIfEntry 38 }

cucsMgmtIfTransport OBJECT-TYPE
    SYNTAX       CucsNetworkTransport
    MAX-ACCESS   read-only
    STATUS       current
    DESCRIPTION
        "Cisco UCS mgmt:If:transport managed object property"
    ::= { cucsMgmtIfEntry 39 }

cucsMgmtIfType OBJECT-TYPE
    SYNTAX       CucsNetworkConnectionType
    MAX-ACCESS   read-only
    STATUS       current
    DESCRIPTION
        "Cisco UCS mgmt:If:type managed object property"
    ::= { cucsMgmtIfEntry 40 }

cucsMgmtIfVnet OBJECT-TYPE
    SYNTAX       Gauge32
    MAX-ACCESS   read-only
    STATUS       current
    DESCRIPTION
        "Cisco UCS mgmt:If:vnet managed object property"
    ::= { cucsMgmtIfEntry 41 }

cucsMgmtIfPeerChassisId OBJECT-TYPE
    SYNTAX       Gauge32
    MAX-ACCESS   read-only
    STATUS       current
    DESCRIPTION
        "Cisco UCS mgmt:If:peerChassisId managed object property"
    ::= { cucsMgmtIfEntry 42 }

cucsMgmtIfAggrPortId OBJECT-TYPE
    SYNTAX       Gauge32
    MAX-ACCESS   read-only
    STATUS       current
    DESCRIPTION
        "Cisco UCS mgmt:If:aggrPortId managed object property"
    ::= { cucsMgmtIfEntry 43 }

cucsMgmtIfPeerAggrPortId OBJECT-TYPE
    SYNTAX       Gauge32
    MAX-ACCESS   read-only
    STATUS       current
    DESCRIPTION
        "Cisco UCS mgmt:If:peerAggrPortId managed object property"
    ::= { cucsMgmtIfEntry 44 }

cucsMgmtIfFsmTable OBJECT-TYPE
    SYNTAX           SEQUENCE OF CucsMgmtIfFsmEntry
    MAX-ACCESS       not-accessible
    STATUS           current
    DESCRIPTION
        "Cisco UCS mgmt:IfFsm managed object table"
    ::= { cucsMgmtObjects 29 }

cucsMgmtIfFsmEntry OBJECT-TYPE
    SYNTAX           CucsMgmtIfFsmEntry
    MAX-ACCESS       not-accessible
    STATUS           current
    DESCRIPTION
        "Entry for the cucsMgmtIfFsmTable table."
    INDEX { cucsMgmtIfFsmInstanceId }
    ::= { cucsMgmtIfFsmTable 1 }

CucsMgmtIfFsmEntry ::= SEQUENCE {
    cucsMgmtIfFsmInstanceId                                          CucsManagedObjectId,
    cucsMgmtIfFsmDn                                                  CucsManagedObjectDn,
    cucsMgmtIfFsmRn                                                  SnmpAdminString,
    cucsMgmtIfFsmCompletionTime                                      DateAndTime,
    cucsMgmtIfFsmCurrentFsm                                          CucsMgmtIfFsmCurrentFsm,
    cucsMgmtIfFsmDescrData                                           SnmpAdminString,
    cucsMgmtIfFsmFsmStatus                                           CucsFsmFsmStageStatus,
    cucsMgmtIfFsmProgress                                            Gauge32,
    cucsMgmtIfFsmRmtErrCode                                          Gauge32,
    cucsMgmtIfFsmRmtErrDescr                                         SnmpAdminString,
    cucsMgmtIfFsmRmtRslt                                             CucsConditionRemoteInvRslt
}

cucsMgmtIfFsmInstanceId OBJECT-TYPE
    SYNTAX       CucsManagedObjectId
    MAX-ACCESS   not-accessible
    STATUS       current
    DESCRIPTION
        "Instance identifier of the managed object."
    ::= { cucsMgmtIfFsmEntry 1 }

cucsMgmtIfFsmDn OBJECT-TYPE
    SYNTAX       CucsManagedObjectDn
    MAX-ACCESS   read-only
    STATUS       current
    DESCRIPTION
        "Cisco UCS mgmt:IfFsm:dn managed object property"
    ::= { cucsMgmtIfFsmEntry 2 }

cucsMgmtIfFsmRn OBJECT-TYPE
    SYNTAX       SnmpAdminString
    MAX-ACCESS   read-only
    STATUS       current
    DESCRIPTION
        "Cisco UCS mgmt:IfFsm:rn managed object property"
    ::= { cucsMgmtIfFsmEntry 3 }

cucsMgmtIfFsmCompletionTime OBJECT-TYPE
    SYNTAX       DateAndTime
    MAX-ACCESS   read-only
    STATUS       current
    DESCRIPTION
        "Cisco UCS mgmt:IfFsm:completionTime managed object property"
    ::= { cucsMgmtIfFsmEntry 4 }

cucsMgmtIfFsmCurrentFsm OBJECT-TYPE
    SYNTAX       CucsMgmtIfFsmCurrentFsm
    MAX-ACCESS   read-only
    STATUS       current
    DESCRIPTION
        "Cisco UCS mgmt:IfFsm:currentFsm managed object property"
    ::= { cucsMgmtIfFsmEntry 5 }

cucsMgmtIfFsmDescrData OBJECT-TYPE
    SYNTAX       SnmpAdminString
    MAX-ACCESS   read-only
    STATUS       current
    DESCRIPTION
        "Cisco UCS mgmt:IfFsm:descr managed object property"
    ::= { cucsMgmtIfFsmEntry 6 }

cucsMgmtIfFsmFsmStatus OBJECT-TYPE
    SYNTAX       CucsFsmFsmStageStatus
    MAX-ACCESS   read-only
    STATUS       current
    DESCRIPTION
        "Cisco UCS mgmt:IfFsm:fsmStatus managed object property"
    ::= { cucsMgmtIfFsmEntry 7 }

cucsMgmtIfFsmProgress OBJECT-TYPE
    SYNTAX       Gauge32
    MAX-ACCESS   read-only
    STATUS       current
    DESCRIPTION
        "Cisco UCS mgmt:IfFsm:progress managed object property"
    ::= { cucsMgmtIfFsmEntry 8 }

cucsMgmtIfFsmRmtErrCode OBJECT-TYPE
    SYNTAX       Gauge32
    MAX-ACCESS   read-only
    STATUS       current
    DESCRIPTION
        "Cisco UCS mgmt:IfFsm:rmtErrCode managed object property"
    ::= { cucsMgmtIfFsmEntry 9 }

cucsMgmtIfFsmRmtErrDescr OBJECT-TYPE
    SYNTAX       SnmpAdminString
    MAX-ACCESS   read-only
    STATUS       current
    DESCRIPTION
        "Cisco UCS mgmt:IfFsm:rmtErrDescr managed object property"
    ::= { cucsMgmtIfFsmEntry 10 }

cucsMgmtIfFsmRmtRslt OBJECT-TYPE
    SYNTAX       CucsConditionRemoteInvRslt
    MAX-ACCESS   read-only
    STATUS       current
    DESCRIPTION
        "Cisco UCS mgmt:IfFsm:rmtRslt managed object property"
    ::= { cucsMgmtIfFsmEntry 11 }

cucsMgmtIfFsmStageTable OBJECT-TYPE
    SYNTAX           SEQUENCE OF CucsMgmtIfFsmStageEntry
    MAX-ACCESS       not-accessible
    STATUS           current
    DESCRIPTION
        "Cisco UCS mgmt:IfFsmStage managed object table"
    ::= { cucsMgmtObjects 30 }

cucsMgmtIfFsmStageEntry OBJECT-TYPE
    SYNTAX           CucsMgmtIfFsmStageEntry
    MAX-ACCESS       not-accessible
    STATUS           current
    DESCRIPTION
        "Entry for the cucsMgmtIfFsmStageTable table."
    INDEX { cucsMgmtIfFsmStageInstanceId }
    ::= { cucsMgmtIfFsmStageTable 1 }

CucsMgmtIfFsmStageEntry ::= SEQUENCE {
    cucsMgmtIfFsmStageInstanceId                                     CucsManagedObjectId,
    cucsMgmtIfFsmStageDn                                             CucsManagedObjectDn,
    cucsMgmtIfFsmStageRn                                             SnmpAdminString,
    cucsMgmtIfFsmStageDescrData                                      SnmpAdminString,
    cucsMgmtIfFsmStageLastUpdateTime                                 DateAndTime,
    cucsMgmtIfFsmStageName                                           CucsMgmtIfFsmStageName,
    cucsMgmtIfFsmStageOrder                                          Gauge32,
    cucsMgmtIfFsmStageRetry                                          Gauge32,
    cucsMgmtIfFsmStageStageStatus                                    CucsFsmFsmStageStatus
}

cucsMgmtIfFsmStageInstanceId OBJECT-TYPE
    SYNTAX       CucsManagedObjectId
    MAX-ACCESS   not-accessible
    STATUS       current
    DESCRIPTION
        "Instance identifier of the managed object."
    ::= { cucsMgmtIfFsmStageEntry 1 }

cucsMgmtIfFsmStageDn OBJECT-TYPE
    SYNTAX       CucsManagedObjectDn
    MAX-ACCESS   read-only
    STATUS       current
    DESCRIPTION
        "Cisco UCS mgmt:IfFsmStage:dn managed object property"
    ::= { cucsMgmtIfFsmStageEntry 2 }

cucsMgmtIfFsmStageRn OBJECT-TYPE
    SYNTAX       SnmpAdminString
    MAX-ACCESS   read-only
    STATUS       current
    DESCRIPTION
        "Cisco UCS mgmt:IfFsmStage:rn managed object property"
    ::= { cucsMgmtIfFsmStageEntry 3 }

cucsMgmtIfFsmStageDescrData OBJECT-TYPE
    SYNTAX       SnmpAdminString
    MAX-ACCESS   read-only
    STATUS       current
    DESCRIPTION
        "Cisco UCS mgmt:IfFsmStage:descr managed object property"
    ::= { cucsMgmtIfFsmStageEntry 4 }

cucsMgmtIfFsmStageLastUpdateTime OBJECT-TYPE
    SYNTAX       DateAndTime
    MAX-ACCESS   read-only
    STATUS       current
    DESCRIPTION
        "Cisco UCS mgmt:IfFsmStage:lastUpdateTime managed object property"
    ::= { cucsMgmtIfFsmStageEntry 5 }

cucsMgmtIfFsmStageName OBJECT-TYPE
    SYNTAX       CucsMgmtIfFsmStageName
    MAX-ACCESS   read-only
    STATUS       current
    DESCRIPTION
        "Cisco UCS mgmt:IfFsmStage:name managed object property"
    ::= { cucsMgmtIfFsmStageEntry 6 }

cucsMgmtIfFsmStageOrder OBJECT-TYPE
    SYNTAX       Gauge32
    MAX-ACCESS   read-only
    STATUS       current
    DESCRIPTION
        "Cisco UCS mgmt:IfFsmStage:order managed object property"
    ::= { cucsMgmtIfFsmStageEntry 7 }

cucsMgmtIfFsmStageRetry OBJECT-TYPE
    SYNTAX       Gauge32
    MAX-ACCESS   read-only
    STATUS       current
    DESCRIPTION
        "Cisco UCS mgmt:IfFsmStage:retry managed object property"
    ::= { cucsMgmtIfFsmStageEntry 8 }

cucsMgmtIfFsmStageStageStatus OBJECT-TYPE
    SYNTAX       CucsFsmFsmStageStatus
    MAX-ACCESS   read-only
    STATUS       current
    DESCRIPTION
        "Cisco UCS mgmt:IfFsmStage:stageStatus managed object property"
    ::= { cucsMgmtIfFsmStageEntry 9 }

cucsMgmtIfFsmTaskTable OBJECT-TYPE
    SYNTAX           SEQUENCE OF CucsMgmtIfFsmTaskEntry
    MAX-ACCESS       not-accessible
    STATUS           current
    DESCRIPTION
        "Cisco UCS mgmt:IfFsmTask managed object table"
    ::= { cucsMgmtObjects 10 }

cucsMgmtIfFsmTaskEntry OBJECT-TYPE
    SYNTAX           CucsMgmtIfFsmTaskEntry
    MAX-ACCESS       not-accessible
    STATUS           current
    DESCRIPTION
        "Entry for the cucsMgmtIfFsmTaskTable table."
    INDEX { cucsMgmtIfFsmTaskInstanceId }
    ::= { cucsMgmtIfFsmTaskTable 1 }

CucsMgmtIfFsmTaskEntry ::= SEQUENCE {
    cucsMgmtIfFsmTaskInstanceId                                      CucsManagedObjectId,
    cucsMgmtIfFsmTaskDn                                              CucsManagedObjectDn,
    cucsMgmtIfFsmTaskRn                                              SnmpAdminString,
    cucsMgmtIfFsmTaskCompletion                                      CucsFsmCompletion,
    cucsMgmtIfFsmTaskFlags                                           CucsFsmFlags,
    cucsMgmtIfFsmTaskItem                                            CucsMgmtIfFsmTaskItem,
    cucsMgmtIfFsmTaskSeqId                                           Gauge32
}

cucsMgmtIfFsmTaskInstanceId OBJECT-TYPE
    SYNTAX       CucsManagedObjectId
    MAX-ACCESS   not-accessible
    STATUS       current
    DESCRIPTION
        "Instance identifier of the managed object."
    ::= { cucsMgmtIfFsmTaskEntry 1 }

cucsMgmtIfFsmTaskDn OBJECT-TYPE
    SYNTAX       CucsManagedObjectDn
    MAX-ACCESS   read-only
    STATUS       current
    DESCRIPTION
        "Cisco UCS mgmt:IfFsmTask:dn managed object property"
    ::= { cucsMgmtIfFsmTaskEntry 2 }

cucsMgmtIfFsmTaskRn OBJECT-TYPE
    SYNTAX       SnmpAdminString
    MAX-ACCESS   read-only
    STATUS       current
    DESCRIPTION
        "Cisco UCS mgmt:IfFsmTask:rn managed object property"
    ::= { cucsMgmtIfFsmTaskEntry 3 }

cucsMgmtIfFsmTaskCompletion OBJECT-TYPE
    SYNTAX       CucsFsmCompletion
    MAX-ACCESS   read-only
    STATUS       current
    DESCRIPTION
        "Cisco UCS mgmt:IfFsmTask:completion managed object property"
    ::= { cucsMgmtIfFsmTaskEntry 4 }

cucsMgmtIfFsmTaskFlags OBJECT-TYPE
    SYNTAX       CucsFsmFlags
    MAX-ACCESS   read-only
    STATUS       current
    DESCRIPTION
        "Cisco UCS mgmt:IfFsmTask:flags managed object property"
    ::= { cucsMgmtIfFsmTaskEntry 5 }

cucsMgmtIfFsmTaskItem OBJECT-TYPE
    SYNTAX       CucsMgmtIfFsmTaskItem
    MAX-ACCESS   read-only
    STATUS       current
    DESCRIPTION
        "Cisco UCS mgmt:IfFsmTask:item managed object property"
    ::= { cucsMgmtIfFsmTaskEntry 6 }

cucsMgmtIfFsmTaskSeqId OBJECT-TYPE
    SYNTAX       Gauge32
    MAX-ACCESS   read-only
    STATUS       current
    DESCRIPTION
        "Cisco UCS mgmt:IfFsmTask:seqId managed object property"
    ::= { cucsMgmtIfFsmTaskEntry 7 }

cucsMgmtImporterTable OBJECT-TYPE
    SYNTAX           SEQUENCE OF CucsMgmtImporterEntry
    MAX-ACCESS       not-accessible
    STATUS           current
    DESCRIPTION
        "Cisco UCS mgmt:Importer managed object table"
    ::= { cucsMgmtObjects 11 }

cucsMgmtImporterEntry OBJECT-TYPE
    SYNTAX           CucsMgmtImporterEntry
    MAX-ACCESS       not-accessible
    STATUS           current
    DESCRIPTION
        "Entry for the cucsMgmtImporterTable table."
    INDEX { cucsMgmtImporterInstanceId }
    ::= { cucsMgmtImporterTable 1 }

CucsMgmtImporterEntry ::= SEQUENCE {
    cucsMgmtImporterInstanceId                                       CucsManagedObjectId,
    cucsMgmtImporterDn                                               CucsManagedObjectDn,
    cucsMgmtImporterRn                                               SnmpAdminString,
    cucsMgmtImporterAction                                           CucsMgmtImportAction,
    cucsMgmtImporterAdminState                                       CucsCommClientAdminState,
    cucsMgmtImporterDescr                                            SnmpAdminString,
    cucsMgmtImporterFsmDescr                                         SnmpAdminString,
    cucsMgmtImporterFsmPrev                                          SnmpAdminString,
    cucsMgmtImporterFsmProgr                                         Gauge32,
    cucsMgmtImporterFsmRmtInvErrCode                                 Gauge32,
    cucsMgmtImporterFsmRmtInvErrDescr                                SnmpAdminString,
    cucsMgmtImporterFsmRmtInvRslt                                    CucsConditionRemoteInvRslt,
    cucsMgmtImporterFsmStageDescr                                    SnmpAdminString,
    cucsMgmtImporterFsmStamp                                         DateAndTime,
    cucsMgmtImporterFsmStatus                                        SnmpAdminString,
    cucsMgmtImporterFsmTry                                           Gauge32,
    cucsMgmtImporterHostname                                         SnmpAdminString,
    cucsMgmtImporterIntId                                            SnmpAdminString,
    cucsMgmtImporterName                                             SnmpAdminString,
    cucsMgmtImporterPostAction                                       CucsMgmtAbsImporterPostAction,
    cucsMgmtImporterProto                                            CucsMgmtAbsImporterProto,
    cucsMgmtImporterPwd                                              SnmpAdminString,
    cucsMgmtImporterRemoteFile                                       SnmpAdminString,
    cucsMgmtImporterUser                                             SnmpAdminString,
    cucsMgmtImporterPolicyLevel                                      Gauge32,
    cucsMgmtImporterPolicyOwner                                      CucsPolicyPolicyOwner,
    cucsMgmtImporterOperStatus                                       CucsMgmtImportStatus
}

cucsMgmtImporterInstanceId OBJECT-TYPE
    SYNTAX       CucsManagedObjectId
    MAX-ACCESS   not-accessible
    STATUS       current
    DESCRIPTION
        "Instance identifier of the managed object."
    ::= { cucsMgmtImporterEntry 1 }

cucsMgmtImporterDn OBJECT-TYPE
    SYNTAX       CucsManagedObjectDn
    MAX-ACCESS   read-only
    STATUS       current
    DESCRIPTION
        "Cisco UCS mgmt:Importer:dn managed object property"
    ::= { cucsMgmtImporterEntry 2 }

cucsMgmtImporterRn OBJECT-TYPE
    SYNTAX       SnmpAdminString
    MAX-ACCESS   read-only
    STATUS       current
    DESCRIPTION
        "Cisco UCS mgmt:Importer:rn managed object property"
    ::= { cucsMgmtImporterEntry 3 }

cucsMgmtImporterAction OBJECT-TYPE
    SYNTAX       CucsMgmtImportAction
    MAX-ACCESS   read-only
    STATUS       current
    DESCRIPTION
        "Cisco UCS mgmt:Importer:action managed object property"
    ::= { cucsMgmtImporterEntry 4 }

cucsMgmtImporterAdminState OBJECT-TYPE
    SYNTAX       CucsCommClientAdminState
    MAX-ACCESS   read-only
    STATUS       current
    DESCRIPTION
        "Cisco UCS mgmt:Importer:adminState managed object property"
    ::= { cucsMgmtImporterEntry 5 }

cucsMgmtImporterDescr OBJECT-TYPE
    SYNTAX       SnmpAdminString
    MAX-ACCESS   read-only
    STATUS       current
    DESCRIPTION
        "Cisco UCS mgmt:Importer:descr managed object property"
    ::= { cucsMgmtImporterEntry 6 }

cucsMgmtImporterFsmDescr OBJECT-TYPE
    SYNTAX       SnmpAdminString
    MAX-ACCESS   read-only
    STATUS       current
    DESCRIPTION
        "Cisco UCS mgmt:Importer:fsmDescr managed object property"
    ::= { cucsMgmtImporterEntry 7 }

cucsMgmtImporterFsmPrev OBJECT-TYPE
    SYNTAX       SnmpAdminString
    MAX-ACCESS   read-only
    STATUS       current
    DESCRIPTION
        "Cisco UCS mgmt:Importer:fsmPrev managed object property"
    ::= { cucsMgmtImporterEntry 8 }

cucsMgmtImporterFsmProgr OBJECT-TYPE
    SYNTAX       Gauge32
    MAX-ACCESS   read-only
    STATUS       current
    DESCRIPTION
        "Cisco UCS mgmt:Importer:fsmProgr managed object property"
    ::= { cucsMgmtImporterEntry 9 }

cucsMgmtImporterFsmRmtInvErrCode OBJECT-TYPE
    SYNTAX       Gauge32
    MAX-ACCESS   read-only
    STATUS       current
    DESCRIPTION
        "Cisco UCS mgmt:Importer:fsmRmtInvErrCode managed object property"
    ::= { cucsMgmtImporterEntry 10 }

cucsMgmtImporterFsmRmtInvErrDescr OBJECT-TYPE
    SYNTAX       SnmpAdminString
    MAX-ACCESS   read-only
    STATUS       current
    DESCRIPTION
        "Cisco UCS mgmt:Importer:fsmRmtInvErrDescr managed
        object property"
    ::= { cucsMgmtImporterEntry 11 }

cucsMgmtImporterFsmRmtInvRslt OBJECT-TYPE
    SYNTAX       CucsConditionRemoteInvRslt
    MAX-ACCESS   read-only
    STATUS       current
    DESCRIPTION
        "Cisco UCS mgmt:Importer:fsmRmtInvRslt managed object property"
    ::= { cucsMgmtImporterEntry 12 }

cucsMgmtImporterFsmStageDescr OBJECT-TYPE
    SYNTAX       SnmpAdminString
    MAX-ACCESS   read-only
    STATUS       current
    DESCRIPTION
        "Cisco UCS mgmt:Importer:fsmStageDescr managed object property"
    ::= { cucsMgmtImporterEntry 13 }

cucsMgmtImporterFsmStamp OBJECT-TYPE
    SYNTAX       DateAndTime
    MAX-ACCESS   read-only
    STATUS       current
    DESCRIPTION
        "Cisco UCS mgmt:Importer:fsmStamp managed object property"
    ::= { cucsMgmtImporterEntry 14 }

cucsMgmtImporterFsmStatus OBJECT-TYPE
    SYNTAX       SnmpAdminString
    MAX-ACCESS   read-only
    STATUS       current
    DESCRIPTION
        "Cisco UCS mgmt:Importer:fsmStatus managed object property"
    ::= { cucsMgmtImporterEntry 15 }

cucsMgmtImporterFsmTry OBJECT-TYPE
    SYNTAX       Gauge32
    MAX-ACCESS   read-only
    STATUS       current
    DESCRIPTION
        "Cisco UCS mgmt:Importer:fsmTry managed object property"
    ::= { cucsMgmtImporterEntry 16 }

cucsMgmtImporterHostname OBJECT-TYPE
    SYNTAX       SnmpAdminString
    MAX-ACCESS   read-only
    STATUS       current
    DESCRIPTION
        "Cisco UCS mgmt:Importer:hostname managed object property"
    ::= { cucsMgmtImporterEntry 17 }

cucsMgmtImporterIntId OBJECT-TYPE
    SYNTAX       SnmpAdminString
    MAX-ACCESS   read-only
    STATUS       current
    DESCRIPTION
        "Cisco UCS mgmt:Importer:intId managed object property"
    ::= { cucsMgmtImporterEntry 18 }

cucsMgmtImporterName OBJECT-TYPE
    SYNTAX       SnmpAdminString
    MAX-ACCESS   read-only
    STATUS       current
    DESCRIPTION
        "Cisco UCS mgmt:Importer:name managed object property"
    ::= { cucsMgmtImporterEntry 19 }

cucsMgmtImporterPostAction OBJECT-TYPE
    SYNTAX       CucsMgmtAbsImporterPostAction
    MAX-ACCESS   read-only
    STATUS       current
    DESCRIPTION
        "Cisco UCS mgmt:Importer:postAction managed object property"
    ::= { cucsMgmtImporterEntry 20 }

cucsMgmtImporterProto OBJECT-TYPE
    SYNTAX       CucsMgmtAbsImporterProto
    MAX-ACCESS   read-only
    STATUS       current
    DESCRIPTION
        "Cisco UCS mgmt:Importer:proto managed object property"
    ::= { cucsMgmtImporterEntry 21 }

cucsMgmtImporterPwd OBJECT-TYPE
    SYNTAX       SnmpAdminString
    MAX-ACCESS   read-only
    STATUS       current
    DESCRIPTION
        "Cisco UCS mgmt:Importer:pwd managed object property"
    ::= { cucsMgmtImporterEntry 22 }

cucsMgmtImporterRemoteFile OBJECT-TYPE
    SYNTAX       SnmpAdminString
    MAX-ACCESS   read-only
    STATUS       current
    DESCRIPTION
        "Cisco UCS mgmt:Importer:remoteFile managed object property"
    ::= { cucsMgmtImporterEntry 23 }

cucsMgmtImporterUser OBJECT-TYPE
    SYNTAX       SnmpAdminString
    MAX-ACCESS   read-only
    STATUS       current
    DESCRIPTION
        "Cisco UCS mgmt:Importer:user managed object property"
    ::= { cucsMgmtImporterEntry 24 }

cucsMgmtImporterPolicyLevel OBJECT-TYPE
    SYNTAX       Gauge32
    MAX-ACCESS   read-only
    STATUS       current
    DESCRIPTION
        "Cisco UCS mgmt:Importer:policyLevel managed object property"
    ::= { cucsMgmtImporterEntry 25 }

cucsMgmtImporterPolicyOwner OBJECT-TYPE
    SYNTAX       CucsPolicyPolicyOwner
    MAX-ACCESS   read-only
    STATUS       current
    DESCRIPTION
        "Cisco UCS mgmt:Importer:policyOwner managed object property"
    ::= { cucsMgmtImporterEntry 26 }

cucsMgmtImporterOperStatus OBJECT-TYPE
    SYNTAX       CucsMgmtImportStatus
    MAX-ACCESS   read-only
    STATUS       current
    DESCRIPTION
        "Cisco UCS mgmt:Importer:operStatus managed object property"
    ::= { cucsMgmtImporterEntry 27 }

cucsMgmtImporterFsmTable OBJECT-TYPE
    SYNTAX           SEQUENCE OF CucsMgmtImporterFsmEntry
    MAX-ACCESS       not-accessible
    STATUS           current
    DESCRIPTION
        "Cisco UCS mgmt:ImporterFsm managed object table"
    ::= { cucsMgmtObjects 31 }

cucsMgmtImporterFsmEntry OBJECT-TYPE
    SYNTAX           CucsMgmtImporterFsmEntry
    MAX-ACCESS       not-accessible
    STATUS           current
    DESCRIPTION
        "Entry for the cucsMgmtImporterFsmTable table."
    INDEX { cucsMgmtImporterFsmInstanceId }
    ::= { cucsMgmtImporterFsmTable 1 }

CucsMgmtImporterFsmEntry ::= SEQUENCE {
    cucsMgmtImporterFsmInstanceId                                    CucsManagedObjectId,
    cucsMgmtImporterFsmDn                                            CucsManagedObjectDn,
    cucsMgmtImporterFsmRn                                            SnmpAdminString,
    cucsMgmtImporterFsmCompletionTime                                DateAndTime,
    cucsMgmtImporterFsmCurrentFsm                                    CucsMgmtImporterFsmCurrentFsm,
    cucsMgmtImporterFsmDescrData                                     SnmpAdminString,
    cucsMgmtImporterFsmFsmStatus                                     CucsFsmFsmStageStatus,
    cucsMgmtImporterFsmProgress                                      Gauge32,
    cucsMgmtImporterFsmRmtErrCode                                    Gauge32,
    cucsMgmtImporterFsmRmtErrDescr                                   SnmpAdminString,
    cucsMgmtImporterFsmRmtRslt                                       CucsConditionRemoteInvRslt
}

cucsMgmtImporterFsmInstanceId OBJECT-TYPE
    SYNTAX       CucsManagedObjectId
    MAX-ACCESS   not-accessible
    STATUS       current
    DESCRIPTION
        "Instance identifier of the managed object."
    ::= { cucsMgmtImporterFsmEntry 1 }

cucsMgmtImporterFsmDn OBJECT-TYPE
    SYNTAX       CucsManagedObjectDn
    MAX-ACCESS   read-only
    STATUS       current
    DESCRIPTION
        "Cisco UCS mgmt:ImporterFsm:dn managed object property"
    ::= { cucsMgmtImporterFsmEntry 2 }

cucsMgmtImporterFsmRn OBJECT-TYPE
    SYNTAX       SnmpAdminString
    MAX-ACCESS   read-only
    STATUS       current
    DESCRIPTION
        "Cisco UCS mgmt:ImporterFsm:rn managed object property"
    ::= { cucsMgmtImporterFsmEntry 3 }

cucsMgmtImporterFsmCompletionTime OBJECT-TYPE
    SYNTAX       DateAndTime
    MAX-ACCESS   read-only
    STATUS       current
    DESCRIPTION
        "Cisco UCS mgmt:ImporterFsm:completionTime managed
        object property"
    ::= { cucsMgmtImporterFsmEntry 4 }

cucsMgmtImporterFsmCurrentFsm OBJECT-TYPE
    SYNTAX       CucsMgmtImporterFsmCurrentFsm
    MAX-ACCESS   read-only
    STATUS       current
    DESCRIPTION
        "Cisco UCS mgmt:ImporterFsm:currentFsm managed object property"
    ::= { cucsMgmtImporterFsmEntry 5 }

cucsMgmtImporterFsmDescrData OBJECT-TYPE
    SYNTAX       SnmpAdminString
    MAX-ACCESS   read-only
    STATUS       current
    DESCRIPTION
        "Cisco UCS mgmt:ImporterFsm:descr managed object property"
    ::= { cucsMgmtImporterFsmEntry 6 }

cucsMgmtImporterFsmFsmStatus OBJECT-TYPE
    SYNTAX       CucsFsmFsmStageStatus
    MAX-ACCESS   read-only
    STATUS       current
    DESCRIPTION
        "Cisco UCS mgmt:ImporterFsm:fsmStatus managed object property"
    ::= { cucsMgmtImporterFsmEntry 7 }

cucsMgmtImporterFsmProgress OBJECT-TYPE
    SYNTAX       Gauge32
    MAX-ACCESS   read-only
    STATUS       current
    DESCRIPTION
        "Cisco UCS mgmt:ImporterFsm:progress managed object property"
    ::= { cucsMgmtImporterFsmEntry 8 }

cucsMgmtImporterFsmRmtErrCode OBJECT-TYPE
    SYNTAX       Gauge32
    MAX-ACCESS   read-only
    STATUS       current
    DESCRIPTION
        "Cisco UCS mgmt:ImporterFsm:rmtErrCode managed object property"
    ::= { cucsMgmtImporterFsmEntry 9 }

cucsMgmtImporterFsmRmtErrDescr OBJECT-TYPE
    SYNTAX       SnmpAdminString
    MAX-ACCESS   read-only
    STATUS       current
    DESCRIPTION
        "Cisco UCS mgmt:ImporterFsm:rmtErrDescr managed object property"
    ::= { cucsMgmtImporterFsmEntry 10 }

cucsMgmtImporterFsmRmtRslt OBJECT-TYPE
    SYNTAX       CucsConditionRemoteInvRslt
    MAX-ACCESS   read-only
    STATUS       current
    DESCRIPTION
        "Cisco UCS mgmt:ImporterFsm:rmtRslt managed object property"
    ::= { cucsMgmtImporterFsmEntry 11 }

cucsMgmtImporterFsmStageTable OBJECT-TYPE
    SYNTAX           SEQUENCE OF CucsMgmtImporterFsmStageEntry
    MAX-ACCESS       not-accessible
    STATUS           current
    DESCRIPTION
        "Cisco UCS mgmt:ImporterFsmStage managed object table"
    ::= { cucsMgmtObjects 32 }

cucsMgmtImporterFsmStageEntry OBJECT-TYPE
    SYNTAX           CucsMgmtImporterFsmStageEntry
    MAX-ACCESS       not-accessible
    STATUS           current
    DESCRIPTION
        "Entry for the cucsMgmtImporterFsmStageTable table."
    INDEX { cucsMgmtImporterFsmStageInstanceId }
    ::= { cucsMgmtImporterFsmStageTable 1 }

CucsMgmtImporterFsmStageEntry ::= SEQUENCE {
    cucsMgmtImporterFsmStageInstanceId                               CucsManagedObjectId,
    cucsMgmtImporterFsmStageDn                                       CucsManagedObjectDn,
    cucsMgmtImporterFsmStageRn                                       SnmpAdminString,
    cucsMgmtImporterFsmStageDescrData                                SnmpAdminString,
    cucsMgmtImporterFsmStageLastUpdateTime                           DateAndTime,
    cucsMgmtImporterFsmStageName                                     CucsMgmtImporterFsmStageName,
    cucsMgmtImporterFsmStageOrder                                    Gauge32,
    cucsMgmtImporterFsmStageRetry                                    Gauge32,
    cucsMgmtImporterFsmStageStageStatus                              CucsFsmFsmStageStatus
}

cucsMgmtImporterFsmStageInstanceId OBJECT-TYPE
    SYNTAX       CucsManagedObjectId
    MAX-ACCESS   not-accessible
    STATUS       current
    DESCRIPTION
        "Instance identifier of the managed object."
    ::= { cucsMgmtImporterFsmStageEntry 1 }

cucsMgmtImporterFsmStageDn OBJECT-TYPE
    SYNTAX       CucsManagedObjectDn
    MAX-ACCESS   read-only
    STATUS       current
    DESCRIPTION
        "Cisco UCS mgmt:ImporterFsmStage:dn managed object property"
    ::= { cucsMgmtImporterFsmStageEntry 2 }

cucsMgmtImporterFsmStageRn OBJECT-TYPE
    SYNTAX       SnmpAdminString
    MAX-ACCESS   read-only
    STATUS       current
    DESCRIPTION
        "Cisco UCS mgmt:ImporterFsmStage:rn managed object property"
    ::= { cucsMgmtImporterFsmStageEntry 3 }

cucsMgmtImporterFsmStageDescrData OBJECT-TYPE
    SYNTAX       SnmpAdminString
    MAX-ACCESS   read-only
    STATUS       current
    DESCRIPTION
        "Cisco UCS mgmt:ImporterFsmStage:descr managed object property"
    ::= { cucsMgmtImporterFsmStageEntry 4 }

cucsMgmtImporterFsmStageLastUpdateTime OBJECT-TYPE
    SYNTAX       DateAndTime
    MAX-ACCESS   read-only
    STATUS       current
    DESCRIPTION
        "Cisco UCS mgmt:ImporterFsmStage:lastUpdateTime
        managed object property"
    ::= { cucsMgmtImporterFsmStageEntry 5 }

cucsMgmtImporterFsmStageName OBJECT-TYPE
    SYNTAX       CucsMgmtImporterFsmStageName
    MAX-ACCESS   read-only
    STATUS       current
    DESCRIPTION
        "Cisco UCS mgmt:ImporterFsmStage:name managed object property"
    ::= { cucsMgmtImporterFsmStageEntry 6 }

cucsMgmtImporterFsmStageOrder OBJECT-TYPE
    SYNTAX       Gauge32
    MAX-ACCESS   read-only
    STATUS       current
    DESCRIPTION
        "Cisco UCS mgmt:ImporterFsmStage:order managed object property"
    ::= { cucsMgmtImporterFsmStageEntry 7 }

cucsMgmtImporterFsmStageRetry OBJECT-TYPE
    SYNTAX       Gauge32
    MAX-ACCESS   read-only
    STATUS       current
    DESCRIPTION
        "Cisco UCS mgmt:ImporterFsmStage:retry managed object property"
    ::= { cucsMgmtImporterFsmStageEntry 8 }

cucsMgmtImporterFsmStageStageStatus OBJECT-TYPE
    SYNTAX       CucsFsmFsmStageStatus
    MAX-ACCESS   read-only
    STATUS       current
    DESCRIPTION
        "Cisco UCS mgmt:ImporterFsmStage:stageStatus managed
        object property"
    ::= { cucsMgmtImporterFsmStageEntry 9 }

cucsMgmtImporterFsmTaskTable OBJECT-TYPE
    SYNTAX           SEQUENCE OF CucsMgmtImporterFsmTaskEntry
    MAX-ACCESS       not-accessible
    STATUS           current
    DESCRIPTION
        "Cisco UCS mgmt:ImporterFsmTask managed object table"
    ::= { cucsMgmtObjects 12 }

cucsMgmtImporterFsmTaskEntry OBJECT-TYPE
    SYNTAX           CucsMgmtImporterFsmTaskEntry
    MAX-ACCESS       not-accessible
    STATUS           current
    DESCRIPTION
        "Entry for the cucsMgmtImporterFsmTaskTable table."
    INDEX { cucsMgmtImporterFsmTaskInstanceId }
    ::= { cucsMgmtImporterFsmTaskTable 1 }

CucsMgmtImporterFsmTaskEntry ::= SEQUENCE {
    cucsMgmtImporterFsmTaskInstanceId                                CucsManagedObjectId,
    cucsMgmtImporterFsmTaskDn                                        CucsManagedObjectDn,
    cucsMgmtImporterFsmTaskRn                                        SnmpAdminString,
    cucsMgmtImporterFsmTaskCompletion                                CucsFsmCompletion,
    cucsMgmtImporterFsmTaskFlags                                     CucsFsmFlags,
    cucsMgmtImporterFsmTaskItem                                      CucsMgmtImporterFsmTaskItem,
    cucsMgmtImporterFsmTaskSeqId                                     Gauge32
}

cucsMgmtImporterFsmTaskInstanceId OBJECT-TYPE
    SYNTAX       CucsManagedObjectId
    MAX-ACCESS   not-accessible
    STATUS       current
    DESCRIPTION
        "Instance identifier of the managed object."
    ::= { cucsMgmtImporterFsmTaskEntry 1 }

cucsMgmtImporterFsmTaskDn OBJECT-TYPE
    SYNTAX       CucsManagedObjectDn
    MAX-ACCESS   read-only
    STATUS       current
    DESCRIPTION
        "Cisco UCS mgmt:ImporterFsmTask:dn managed object property"
    ::= { cucsMgmtImporterFsmTaskEntry 2 }

cucsMgmtImporterFsmTaskRn OBJECT-TYPE
    SYNTAX       SnmpAdminString
    MAX-ACCESS   read-only
    STATUS       current
    DESCRIPTION
        "Cisco UCS mgmt:ImporterFsmTask:rn managed object property"
    ::= { cucsMgmtImporterFsmTaskEntry 3 }

cucsMgmtImporterFsmTaskCompletion OBJECT-TYPE
    SYNTAX       CucsFsmCompletion
    MAX-ACCESS   read-only
    STATUS       current
    DESCRIPTION
        "Cisco UCS mgmt:ImporterFsmTask:completion managed
        object property"
    ::= { cucsMgmtImporterFsmTaskEntry 4 }

cucsMgmtImporterFsmTaskFlags OBJECT-TYPE
    SYNTAX       CucsFsmFlags
    MAX-ACCESS   read-only
    STATUS       current
    DESCRIPTION
        "Cisco UCS mgmt:ImporterFsmTask:flags managed object property"
    ::= { cucsMgmtImporterFsmTaskEntry 5 }

cucsMgmtImporterFsmTaskItem OBJECT-TYPE
    SYNTAX       CucsMgmtImporterFsmTaskItem
    MAX-ACCESS   read-only
    STATUS       current
    DESCRIPTION
        "Cisco UCS mgmt:ImporterFsmTask:item managed object property"
    ::= { cucsMgmtImporterFsmTaskEntry 6 }

cucsMgmtImporterFsmTaskSeqId OBJECT-TYPE
    SYNTAX       Gauge32
    MAX-ACCESS   read-only
    STATUS       current
    DESCRIPTION
        "Cisco UCS mgmt:ImporterFsmTask:seqId managed object property"
    ::= { cucsMgmtImporterFsmTaskEntry 7 }

cucsMgmtInbandProfileTable OBJECT-TYPE
    SYNTAX           SEQUENCE OF CucsMgmtInbandProfileEntry
    MAX-ACCESS       not-accessible
    STATUS           current
    DESCRIPTION
        "Cisco UCS mgmt:InbandProfile managed object table"
    ::= { cucsMgmtObjects 38 }

cucsMgmtInbandProfileEntry OBJECT-TYPE
    SYNTAX           CucsMgmtInbandProfileEntry
    MAX-ACCESS       not-accessible
    STATUS           current
    DESCRIPTION
        "Entry for the cucsMgmtInbandProfileTable table."
    INDEX { cucsMgmtInbandProfileInstanceId }
    ::= { cucsMgmtInbandProfileTable 1 }

CucsMgmtInbandProfileEntry ::= SEQUENCE {
    cucsMgmtInbandProfileInstanceId                                  CucsManagedObjectId,
    cucsMgmtInbandProfileDn                                          CucsManagedObjectDn,
    cucsMgmtInbandProfileRn                                          SnmpAdminString,
    cucsMgmtInbandProfileDefaultVlanName                             SnmpAdminString,
    cucsMgmtInbandProfileName                                        SnmpAdminString,
    cucsMgmtInbandProfilePoolName                                    SnmpAdminString,
    cucsMgmtInbandProfileMonitorInterval                             Gauge32,
    cucsMgmtInbandProfilePolicyOwner                                 CucsPolicyPolicyOwner
}

cucsMgmtInbandProfileInstanceId OBJECT-TYPE
    SYNTAX       CucsManagedObjectId
    MAX-ACCESS   not-accessible
    STATUS       current
    DESCRIPTION
        "Instance identifier of the managed object."
    ::= { cucsMgmtInbandProfileEntry 1 }

cucsMgmtInbandProfileDn OBJECT-TYPE
    SYNTAX       CucsManagedObjectDn
    MAX-ACCESS   read-only
    STATUS       current
    DESCRIPTION
        "Cisco UCS mgmt:InbandProfile:dn managed object property"
    ::= { cucsMgmtInbandProfileEntry 2 }

cucsMgmtInbandProfileRn OBJECT-TYPE
    SYNTAX       SnmpAdminString
    MAX-ACCESS   read-only
    STATUS       current
    DESCRIPTION
        "Cisco UCS mgmt:InbandProfile:rn managed object property"
    ::= { cucsMgmtInbandProfileEntry 3 }

cucsMgmtInbandProfileDefaultVlanName OBJECT-TYPE
    SYNTAX       SnmpAdminString
    MAX-ACCESS   read-only
    STATUS       current
    DESCRIPTION
        "Cisco UCS mgmt:InbandProfile:defaultVlanName managed
        object property"
    ::= { cucsMgmtInbandProfileEntry 4 }

cucsMgmtInbandProfileName OBJECT-TYPE
    SYNTAX       SnmpAdminString
    MAX-ACCESS   read-only
    STATUS       current
    DESCRIPTION
        "Cisco UCS mgmt:InbandProfile:name managed object property"
    ::= { cucsMgmtInbandProfileEntry 5 }

cucsMgmtInbandProfilePoolName OBJECT-TYPE
    SYNTAX       SnmpAdminString
    MAX-ACCESS   read-only
    STATUS       current
    DESCRIPTION
        "Cisco UCS mgmt:InbandProfile:poolName managed object property"
    ::= { cucsMgmtInbandProfileEntry 6 }

cucsMgmtInbandProfileMonitorInterval OBJECT-TYPE
    SYNTAX       Gauge32
    MAX-ACCESS   read-only
    STATUS       current
    DESCRIPTION
        "Cisco UCS mgmt:InbandProfile:monitorInterval managed
        object property"
    ::= { cucsMgmtInbandProfileEntry 7 }

cucsMgmtInbandProfilePolicyOwner OBJECT-TYPE
    SYNTAX       CucsPolicyPolicyOwner
    MAX-ACCESS   read-only
    STATUS       current
    DESCRIPTION
        "Cisco UCS mgmt:InbandProfile:policyOwner managed object property"
    ::= { cucsMgmtInbandProfileEntry 8 }

cucsMgmtIntAuthPolicyTable OBJECT-TYPE
    SYNTAX           SEQUENCE OF CucsMgmtIntAuthPolicyEntry
    MAX-ACCESS       not-accessible
    STATUS           current
    DESCRIPTION
        "Cisco UCS mgmt:IntAuthPolicy managed object table"
    ::= { cucsMgmtObjects 13 }

cucsMgmtIntAuthPolicyEntry OBJECT-TYPE
    SYNTAX           CucsMgmtIntAuthPolicyEntry
    MAX-ACCESS       not-accessible
    STATUS           current
    DESCRIPTION
        "Entry for the cucsMgmtIntAuthPolicyTable table."
    INDEX { cucsMgmtIntAuthPolicyInstanceId }
    ::= { cucsMgmtIntAuthPolicyTable 1 }

CucsMgmtIntAuthPolicyEntry ::= SEQUENCE {
    cucsMgmtIntAuthPolicyInstanceId                                  CucsManagedObjectId,
    cucsMgmtIntAuthPolicyDn                                          CucsManagedObjectDn,
    cucsMgmtIntAuthPolicyRn                                          SnmpAdminString,
    cucsMgmtIntAuthPolicyMethod                                      CucsMgmtIntAuthPolicyMethod,
    cucsMgmtIntAuthPolicyName                                        SnmpAdminString,
    cucsMgmtIntAuthPolicyPwd                                         SnmpAdminString
}

cucsMgmtIntAuthPolicyInstanceId OBJECT-TYPE
    SYNTAX       CucsManagedObjectId
    MAX-ACCESS   not-accessible
    STATUS       current
    DESCRIPTION
        "Instance identifier of the managed object."
    ::= { cucsMgmtIntAuthPolicyEntry 1 }

cucsMgmtIntAuthPolicyDn OBJECT-TYPE
    SYNTAX       CucsManagedObjectDn
    MAX-ACCESS   read-only
    STATUS       current
    DESCRIPTION
        "Cisco UCS mgmt:IntAuthPolicy:dn managed object property"
    ::= { cucsMgmtIntAuthPolicyEntry 2 }

cucsMgmtIntAuthPolicyRn OBJECT-TYPE
    SYNTAX       SnmpAdminString
    MAX-ACCESS   read-only
    STATUS       current
    DESCRIPTION
        "Cisco UCS mgmt:IntAuthPolicy:rn managed object property"
    ::= { cucsMgmtIntAuthPolicyEntry 3 }

cucsMgmtIntAuthPolicyMethod OBJECT-TYPE
    SYNTAX       CucsMgmtIntAuthPolicyMethod
    MAX-ACCESS   read-only
    STATUS       current
    DESCRIPTION
        "Cisco UCS mgmt:IntAuthPolicy:method managed object property"
    ::= { cucsMgmtIntAuthPolicyEntry 4 }

cucsMgmtIntAuthPolicyName OBJECT-TYPE
    SYNTAX       SnmpAdminString
    MAX-ACCESS   read-only
    STATUS       current
    DESCRIPTION
        "Cisco UCS mgmt:IntAuthPolicy:name managed object property"
    ::= { cucsMgmtIntAuthPolicyEntry 5 }

cucsMgmtIntAuthPolicyPwd OBJECT-TYPE
    SYNTAX       SnmpAdminString
    MAX-ACCESS   read-only
    STATUS       current
    DESCRIPTION
        "Cisco UCS mgmt:IntAuthPolicy:pwd managed object property"
    ::= { cucsMgmtIntAuthPolicyEntry 6 }

cucsMgmtInterfaceTable OBJECT-TYPE
    SYNTAX           SEQUENCE OF CucsMgmtInterfaceEntry
    MAX-ACCESS       not-accessible
    STATUS           current
    DESCRIPTION
        "Cisco UCS mgmt:Interface managed object table"
    ::= { cucsMgmtObjects 39 }

cucsMgmtInterfaceEntry OBJECT-TYPE
    SYNTAX           CucsMgmtInterfaceEntry
    MAX-ACCESS       not-accessible
    STATUS           current
    DESCRIPTION
        "Entry for the cucsMgmtInterfaceTable table."
    INDEX { cucsMgmtInterfaceInstanceId }
    ::= { cucsMgmtInterfaceTable 1 }

CucsMgmtInterfaceEntry ::= SEQUENCE {
    cucsMgmtInterfaceInstanceId                                      CucsManagedObjectId,
    cucsMgmtInterfaceDn                                              CucsManagedObjectDn,
    cucsMgmtInterfaceRn                                              SnmpAdminString,
    cucsMgmtInterfaceConfigMessage                                   SnmpAdminString,
    cucsMgmtInterfaceConfigState                                     CucsMgmtConfigState,
    cucsMgmtInterfaceIpV4State                                       CucsVnicExternalMgmtIPMode,
    cucsMgmtInterfaceIpV6State                                       CucsVnicExternalMgmtIPMode,
    cucsMgmtInterfaceMode                                            CucsMgmtMode,
    cucsMgmtInterfaceOperState                                       CucsMgmtOperState,
    cucsMgmtInterfaceIsDefaultDerived                                TruthValue,
    cucsMgmtInterfaceMonitorInterval                                 Gauge32
}

cucsMgmtInterfaceInstanceId OBJECT-TYPE
    SYNTAX       CucsManagedObjectId
    MAX-ACCESS   not-accessible
    STATUS       current
    DESCRIPTION
        "Instance identifier of the managed object."
    ::= { cucsMgmtInterfaceEntry 1 }

cucsMgmtInterfaceDn OBJECT-TYPE
    SYNTAX       CucsManagedObjectDn
    MAX-ACCESS   read-only
    STATUS       current
    DESCRIPTION
        "Cisco UCS mgmt:Interface:dn managed object property"
    ::= { cucsMgmtInterfaceEntry 2 }

cucsMgmtInterfaceRn OBJECT-TYPE
    SYNTAX       SnmpAdminString
    MAX-ACCESS   read-only
    STATUS       current
    DESCRIPTION
        "Cisco UCS mgmt:Interface:rn managed object property"
    ::= { cucsMgmtInterfaceEntry 3 }

cucsMgmtInterfaceConfigMessage OBJECT-TYPE
    SYNTAX       SnmpAdminString
    MAX-ACCESS   read-only
    STATUS       current
    DESCRIPTION
        "Cisco UCS mgmt:Interface:configMessage managed object property"
    ::= { cucsMgmtInterfaceEntry 4 }

cucsMgmtInterfaceConfigState OBJECT-TYPE
    SYNTAX       CucsMgmtConfigState
    MAX-ACCESS   read-only
    STATUS       current
    DESCRIPTION
        "Cisco UCS mgmt:Interface:configState managed object property"
    ::= { cucsMgmtInterfaceEntry 5 }

cucsMgmtInterfaceIpV4State OBJECT-TYPE
    SYNTAX       CucsVnicExternalMgmtIPMode
    MAX-ACCESS   read-only
    STATUS       current
    DESCRIPTION
        "Cisco UCS mgmt:Interface:ipV4State managed object property"
    ::= { cucsMgmtInterfaceEntry 6 }

cucsMgmtInterfaceIpV6State OBJECT-TYPE
    SYNTAX       CucsVnicExternalMgmtIPMode
    MAX-ACCESS   read-only
    STATUS       current
    DESCRIPTION
        "Cisco UCS mgmt:Interface:ipV6State managed object property"
    ::= { cucsMgmtInterfaceEntry 7 }

cucsMgmtInterfaceMode OBJECT-TYPE
    SYNTAX       CucsMgmtMode
    MAX-ACCESS   read-only
    STATUS       current
    DESCRIPTION
        "Cisco UCS mgmt:Interface:mode managed object property"
    ::= { cucsMgmtInterfaceEntry 8 }

cucsMgmtInterfaceOperState OBJECT-TYPE
    SYNTAX       CucsMgmtOperState
    MAX-ACCESS   read-only
    STATUS       current
    DESCRIPTION
        "Cisco UCS mgmt:Interface:operState managed object property"
    ::= { cucsMgmtInterfaceEntry 9 }

cucsMgmtInterfaceIsDefaultDerived OBJECT-TYPE
    SYNTAX       TruthValue
    MAX-ACCESS   read-only
    STATUS       current
    DESCRIPTION
        "Cisco UCS mgmt:Interface:isDefaultDerived managed
        object property"
    ::= { cucsMgmtInterfaceEntry 10 }

cucsMgmtInterfaceMonitorInterval OBJECT-TYPE
    SYNTAX       Gauge32
    MAX-ACCESS   read-only
    STATUS       current
    DESCRIPTION
        "Cisco UCS mgmt:Interface:monitorInterval managed object property"
    ::= { cucsMgmtInterfaceEntry 11 }

cucsMgmtKmipTable OBJECT-TYPE
    SYNTAX           SEQUENCE OF CucsMgmtKmipEntry
    MAX-ACCESS       not-accessible
    STATUS           current
    DESCRIPTION
        "Cisco UCS mgmt:Kmip managed object table"
    ::= { cucsMgmtObjects 72 }

cucsMgmtKmipEntry OBJECT-TYPE
    SYNTAX           CucsMgmtKmipEntry
    MAX-ACCESS       not-accessible
    STATUS           current
    DESCRIPTION
        "Entry for the cucsMgmtKmipTable table."
    INDEX { cucsMgmtKmipInstanceId }
    ::= { cucsMgmtKmipTable 1 }

CucsMgmtKmipEntry ::= SEQUENCE {
    cucsMgmtKmipInstanceId                                           CucsManagedObjectId,
    cucsMgmtKmipDn                                                   CucsManagedObjectDn,
    cucsMgmtKmipRn                                                   SnmpAdminString,
    cucsMgmtKmipCaCertificate                                        SnmpAdminString,
    cucsMgmtKmipCertSignRequest                                      SnmpAdminString,
    cucsMgmtKmipCertStatus                                           CucsPkiCertStatus,
    cucsMgmtKmipCertificate                                          SnmpAdminString,
    cucsMgmtKmipPriConnStatus                                        SnmpAdminString,
    cucsMgmtKmipSecConnStatus                                        SnmpAdminString
}

cucsMgmtKmipInstanceId OBJECT-TYPE
    SYNTAX       CucsManagedObjectId
    MAX-ACCESS   not-accessible
    STATUS       current
    DESCRIPTION
        "Instance identifier of the managed object."
    ::= { cucsMgmtKmipEntry 1 }

cucsMgmtKmipDn OBJECT-TYPE
    SYNTAX       CucsManagedObjectDn
    MAX-ACCESS   read-only
    STATUS       current
    DESCRIPTION
        "Cisco UCS mgmt:Kmip:dn managed object property"
    ::= { cucsMgmtKmipEntry 2 }

cucsMgmtKmipRn OBJECT-TYPE
    SYNTAX       SnmpAdminString
    MAX-ACCESS   read-only
    STATUS       current
    DESCRIPTION
        "Cisco UCS mgmt:Kmip:rn managed object property"
    ::= { cucsMgmtKmipEntry 3 }

cucsMgmtKmipCaCertificate OBJECT-TYPE
    SYNTAX       SnmpAdminString
    MAX-ACCESS   read-only
    STATUS       current
    DESCRIPTION
        "Cisco UCS mgmt:Kmip:caCertificate managed object property"
    ::= { cucsMgmtKmipEntry 4 }

cucsMgmtKmipCertSignRequest OBJECT-TYPE
    SYNTAX       SnmpAdminString
    MAX-ACCESS   read-only
    STATUS       current
    DESCRIPTION
        "Cisco UCS mgmt:Kmip:certSignRequest managed object property"
    ::= { cucsMgmtKmipEntry 5 }

cucsMgmtKmipCertStatus OBJECT-TYPE
    SYNTAX       CucsPkiCertStatus
    MAX-ACCESS   read-only
    STATUS       current
    DESCRIPTION
        "Cisco UCS mgmt:Kmip:certStatus managed object property"
    ::= { cucsMgmtKmipEntry 6 }

cucsMgmtKmipCertificate OBJECT-TYPE
    SYNTAX       SnmpAdminString
    MAX-ACCESS   read-only
    STATUS       current
    DESCRIPTION
        "Cisco UCS mgmt:Kmip:certificate managed object property"
    ::= { cucsMgmtKmipEntry 7 }

cucsMgmtKmipPriConnStatus OBJECT-TYPE
    SYNTAX       SnmpAdminString
    MAX-ACCESS   read-only
    STATUS       current
    DESCRIPTION
        "Cisco UCS mgmt:Kmip:priConnStatus managed object property"
    ::= { cucsMgmtKmipEntry 8 }

cucsMgmtKmipSecConnStatus OBJECT-TYPE
    SYNTAX       SnmpAdminString
    MAX-ACCESS   read-only
    STATUS       current
    DESCRIPTION
        "Cisco UCS mgmt:Kmip:secConnStatus managed object property"
    ::= { cucsMgmtKmipEntry 9 }

cucsMgmtKmipCertPolicyTable OBJECT-TYPE
    SYNTAX           SEQUENCE OF CucsMgmtKmipCertPolicyEntry
    MAX-ACCESS       not-accessible
    STATUS           current
    DESCRIPTION
        "Cisco UCS mgmt:KmipCertPolicy managed object table"
    ::= { cucsMgmtObjects 73 }

cucsMgmtKmipCertPolicyEntry OBJECT-TYPE
    SYNTAX           CucsMgmtKmipCertPolicyEntry
    MAX-ACCESS       not-accessible
    STATUS           current
    DESCRIPTION
        "Entry for the cucsMgmtKmipCertPolicyTable table."
    INDEX { cucsMgmtKmipCertPolicyInstanceId }
    ::= { cucsMgmtKmipCertPolicyTable 1 }

CucsMgmtKmipCertPolicyEntry ::= SEQUENCE {
    cucsMgmtKmipCertPolicyInstanceId                                 CucsManagedObjectId,
    cucsMgmtKmipCertPolicyDn                                         CucsManagedObjectDn,
    cucsMgmtKmipCertPolicyRn                                         SnmpAdminString,
    cucsMgmtKmipCertPolicyCountryCode                                SnmpAdminString,
    cucsMgmtKmipCertPolicyDescr                                      SnmpAdminString,
    cucsMgmtKmipCertPolicyEmailAddr                                  SnmpAdminString,
    cucsMgmtKmipCertPolicyIntId                                      SnmpAdminString,
    cucsMgmtKmipCertPolicyLocality                                   SnmpAdminString,
    cucsMgmtKmipCertPolicyName                                       SnmpAdminString,
    cucsMgmtKmipCertPolicyOrgName                                    SnmpAdminString,
    cucsMgmtKmipCertPolicyOrgUnitName                                SnmpAdminString,
    cucsMgmtKmipCertPolicyPolicyLevel                                Gauge32,
    cucsMgmtKmipCertPolicyPolicyOwner                                CucsPolicyPolicyOwner,
    cucsMgmtKmipCertPolicyState                                      SnmpAdminString,
    cucsMgmtKmipCertPolicyValidity                                   Gauge32
}

cucsMgmtKmipCertPolicyInstanceId OBJECT-TYPE
    SYNTAX       CucsManagedObjectId
    MAX-ACCESS   not-accessible
    STATUS       current
    DESCRIPTION
        "Instance identifier of the managed object."
    ::= { cucsMgmtKmipCertPolicyEntry 1 }

cucsMgmtKmipCertPolicyDn OBJECT-TYPE
    SYNTAX       CucsManagedObjectDn
    MAX-ACCESS   read-only
    STATUS       current
    DESCRIPTION
        "Cisco UCS mgmt:KmipCertPolicy:dn managed object property"
    ::= { cucsMgmtKmipCertPolicyEntry 2 }

cucsMgmtKmipCertPolicyRn OBJECT-TYPE
    SYNTAX       SnmpAdminString
    MAX-ACCESS   read-only
    STATUS       current
    DESCRIPTION
        "Cisco UCS mgmt:KmipCertPolicy:rn managed object property"
    ::= { cucsMgmtKmipCertPolicyEntry 3 }

cucsMgmtKmipCertPolicyCountryCode OBJECT-TYPE
    SYNTAX       SnmpAdminString
    MAX-ACCESS   read-only
    STATUS       current
    DESCRIPTION
        "Cisco UCS mgmt:KmipCertPolicy:countryCode managed
        object property"
    ::= { cucsMgmtKmipCertPolicyEntry 4 }

cucsMgmtKmipCertPolicyDescr OBJECT-TYPE
    SYNTAX       SnmpAdminString
    MAX-ACCESS   read-only
    STATUS       current
    DESCRIPTION
        "Cisco UCS mgmt:KmipCertPolicy:descr managed object property"
    ::= { cucsMgmtKmipCertPolicyEntry 5 }

cucsMgmtKmipCertPolicyEmailAddr OBJECT-TYPE
    SYNTAX       SnmpAdminString
    MAX-ACCESS   read-only
    STATUS       current
    DESCRIPTION
        "Cisco UCS mgmt:KmipCertPolicy:emailAddr managed object property"
    ::= { cucsMgmtKmipCertPolicyEntry 6 }

cucsMgmtKmipCertPolicyIntId OBJECT-TYPE
    SYNTAX       SnmpAdminString
    MAX-ACCESS   read-only
    STATUS       current
    DESCRIPTION
        "Cisco UCS mgmt:KmipCertPolicy:intId managed object property"
    ::= { cucsMgmtKmipCertPolicyEntry 7 }

cucsMgmtKmipCertPolicyLocality OBJECT-TYPE
    SYNTAX       SnmpAdminString
    MAX-ACCESS   read-only
    STATUS       current
    DESCRIPTION
        "Cisco UCS mgmt:KmipCertPolicy:locality managed object property"
    ::= { cucsMgmtKmipCertPolicyEntry 8 }

cucsMgmtKmipCertPolicyName OBJECT-TYPE
    SYNTAX       SnmpAdminString
    MAX-ACCESS   read-only
    STATUS       current
    DESCRIPTION
        "Cisco UCS mgmt:KmipCertPolicy:name managed object property"
    ::= { cucsMgmtKmipCertPolicyEntry 9 }

cucsMgmtKmipCertPolicyOrgName OBJECT-TYPE
    SYNTAX       SnmpAdminString
    MAX-ACCESS   read-only
    STATUS       current
    DESCRIPTION
        "Cisco UCS mgmt:KmipCertPolicy:orgName managed object property"
    ::= { cucsMgmtKmipCertPolicyEntry 10 }

cucsMgmtKmipCertPolicyOrgUnitName OBJECT-TYPE
    SYNTAX       SnmpAdminString
    MAX-ACCESS   read-only
    STATUS       current
    DESCRIPTION
        "Cisco UCS mgmt:KmipCertPolicy:orgUnitName managed
        object property"
    ::= { cucsMgmtKmipCertPolicyEntry 11 }

cucsMgmtKmipCertPolicyPolicyLevel OBJECT-TYPE
    SYNTAX       Gauge32
    MAX-ACCESS   read-only
    STATUS       current
    DESCRIPTION
        "Cisco UCS mgmt:KmipCertPolicy:policyLevel managed
        object property"
    ::= { cucsMgmtKmipCertPolicyEntry 12 }

cucsMgmtKmipCertPolicyPolicyOwner OBJECT-TYPE
    SYNTAX       CucsPolicyPolicyOwner
    MAX-ACCESS   read-only
    STATUS       current
    DESCRIPTION
        "Cisco UCS mgmt:KmipCertPolicy:policyOwner managed
        object property"
    ::= { cucsMgmtKmipCertPolicyEntry 13 }

cucsMgmtKmipCertPolicyState OBJECT-TYPE
    SYNTAX       SnmpAdminString
    MAX-ACCESS   read-only
    STATUS       current
    DESCRIPTION
        "Cisco UCS mgmt:KmipCertPolicy:state managed object property"
    ::= { cucsMgmtKmipCertPolicyEntry 14 }

cucsMgmtKmipCertPolicyValidity OBJECT-TYPE
    SYNTAX       Gauge32
    MAX-ACCESS   read-only
    STATUS       current
    DESCRIPTION
        "Cisco UCS mgmt:KmipCertPolicy:validity managed object property"
    ::= { cucsMgmtKmipCertPolicyEntry 15 }

cucsMgmtPmonEntryTable OBJECT-TYPE
    SYNTAX           SEQUENCE OF CucsMgmtPmonEntryEntry
    MAX-ACCESS       not-accessible
    STATUS           current
    DESCRIPTION
        "Cisco UCS mgmt:PmonEntry managed object table"
    ::= { cucsMgmtObjects 14 }

cucsMgmtPmonEntryEntry OBJECT-TYPE
    SYNTAX           CucsMgmtPmonEntryEntry
    MAX-ACCESS       not-accessible
    STATUS           current
    DESCRIPTION
        "Entry for the cucsMgmtPmonEntryTable table."
    INDEX { cucsMgmtPmonEntryInstanceId }
    ::= { cucsMgmtPmonEntryTable 1 }

CucsMgmtPmonEntryEntry ::= SEQUENCE {
    cucsMgmtPmonEntryInstanceId                                      CucsManagedObjectId,
    cucsMgmtPmonEntryDn                                              CucsManagedObjectDn,
    cucsMgmtPmonEntryRn                                              SnmpAdminString,
    cucsMgmtPmonEntryExitSignal                                      Gauge32,
    cucsMgmtPmonEntryFullPathname                                    SnmpAdminString,
    cucsMgmtPmonEntryHeapSize                                        Unsigned64,
    cucsMgmtPmonEntryHeapSize16Gb                                    Unsigned64,
    cucsMgmtPmonEntryLastExitCode                                    Gauge32,
    cucsMgmtPmonEntryMaxRetries                                      Gauge32,
    cucsMgmtPmonEntryName                                            SnmpAdminString,
    cucsMgmtPmonEntryRetries                                         Gauge32,
    cucsMgmtPmonEntrySpuriousRetries                                 Gauge32,
    cucsMgmtPmonEntryState                                           CucsMgmtPmonEntryState,
    cucsMgmtPmonEntrySwitchId                                        CucsNetworkSwitchId,
    cucsMgmtPmonEntryWorkingDirectory                                SnmpAdminString
}

cucsMgmtPmonEntryInstanceId OBJECT-TYPE
    SYNTAX       CucsManagedObjectId
    MAX-ACCESS   not-accessible
    STATUS       current
    DESCRIPTION
        "Instance identifier of the managed object."
    ::= { cucsMgmtPmonEntryEntry 1 }

cucsMgmtPmonEntryDn OBJECT-TYPE
    SYNTAX       CucsManagedObjectDn
    MAX-ACCESS   read-only
    STATUS       current
    DESCRIPTION
        "Cisco UCS mgmt:PmonEntry:dn managed object property"
    ::= { cucsMgmtPmonEntryEntry 2 }

cucsMgmtPmonEntryRn OBJECT-TYPE
    SYNTAX       SnmpAdminString
    MAX-ACCESS   read-only
    STATUS       current
    DESCRIPTION
        "Cisco UCS mgmt:PmonEntry:rn managed object property"
    ::= { cucsMgmtPmonEntryEntry 3 }

cucsMgmtPmonEntryExitSignal OBJECT-TYPE
    SYNTAX       Gauge32
    MAX-ACCESS   read-only
    STATUS       current
    DESCRIPTION
        "Cisco UCS mgmt:PmonEntry:exitSignal managed object property"
    ::= { cucsMgmtPmonEntryEntry 4 }

cucsMgmtPmonEntryFullPathname OBJECT-TYPE
    SYNTAX       SnmpAdminString
    MAX-ACCESS   read-only
    STATUS       current
    DESCRIPTION
        "Cisco UCS mgmt:PmonEntry:fullPathname managed object property"
    ::= { cucsMgmtPmonEntryEntry 5 }

cucsMgmtPmonEntryHeapSize OBJECT-TYPE
    SYNTAX       Unsigned64
    MAX-ACCESS   read-only
    STATUS       current
    DESCRIPTION
        "Cisco UCS mgmt:PmonEntry:heapSize managed object property"
    ::= { cucsMgmtPmonEntryEntry 6 }

cucsMgmtPmonEntryHeapSize16Gb OBJECT-TYPE
    SYNTAX       Unsigned64
    MAX-ACCESS   read-only
    STATUS       current
    DESCRIPTION
        "Cisco UCS mgmt:PmonEntry:heapSize16Gb managed object property"
    ::= { cucsMgmtPmonEntryEntry 7 }

cucsMgmtPmonEntryLastExitCode OBJECT-TYPE
    SYNTAX       Gauge32
    MAX-ACCESS   read-only
    STATUS       current
    DESCRIPTION
        "Cisco UCS mgmt:PmonEntry:lastExitCode managed object property"
    ::= { cucsMgmtPmonEntryEntry 8 }

cucsMgmtPmonEntryMaxRetries OBJECT-TYPE
    SYNTAX       Gauge32
    MAX-ACCESS   read-only
    STATUS       current
    DESCRIPTION
        "Cisco UCS mgmt:PmonEntry:maxRetries managed object property"
    ::= { cucsMgmtPmonEntryEntry 9 }

cucsMgmtPmonEntryName OBJECT-TYPE
    SYNTAX       SnmpAdminString
    MAX-ACCESS   read-only
    STATUS       current
    DESCRIPTION
        "Cisco UCS mgmt:PmonEntry:name managed object property"
    ::= { cucsMgmtPmonEntryEntry 10 }

cucsMgmtPmonEntryRetries OBJECT-TYPE
    SYNTAX       Gauge32
    MAX-ACCESS   read-only
    STATUS       current
    DESCRIPTION
        "Cisco UCS mgmt:PmonEntry:retries managed object property"
    ::= { cucsMgmtPmonEntryEntry 11 }

cucsMgmtPmonEntrySpuriousRetries OBJECT-TYPE
    SYNTAX       Gauge32
    MAX-ACCESS   read-only
    STATUS       current
    DESCRIPTION
        "Cisco UCS mgmt:PmonEntry:spuriousRetries managed object property"
    ::= { cucsMgmtPmonEntryEntry 12 }

cucsMgmtPmonEntryState OBJECT-TYPE
    SYNTAX       CucsMgmtPmonEntryState
    MAX-ACCESS   read-only
    STATUS       current
    DESCRIPTION
        "Cisco UCS mgmt:PmonEntry:state managed object property"
    ::= { cucsMgmtPmonEntryEntry 13 }

cucsMgmtPmonEntrySwitchId OBJECT-TYPE
    SYNTAX       CucsNetworkSwitchId
    MAX-ACCESS   read-only
    STATUS       current
    DESCRIPTION
        "Cisco UCS mgmt:PmonEntry:switchId managed object property"
    ::= { cucsMgmtPmonEntryEntry 14 }

cucsMgmtPmonEntryWorkingDirectory OBJECT-TYPE
    SYNTAX       SnmpAdminString
    MAX-ACCESS   read-only
    STATUS       current
    DESCRIPTION
        "Cisco UCS mgmt:PmonEntry:workingDirectory managed
        object property"
    ::= { cucsMgmtPmonEntryEntry 15 }

cucsMgmtProfDerivedInterfaceTable OBJECT-TYPE
    SYNTAX           SEQUENCE OF CucsMgmtProfDerivedInterfaceEntry
    MAX-ACCESS       not-accessible
    STATUS           current
    DESCRIPTION
        "Cisco UCS mgmt:ProfDerivedInterface managed object table"
    ::= { cucsMgmtObjects 40 }

cucsMgmtProfDerivedInterfaceEntry OBJECT-TYPE
    SYNTAX           CucsMgmtProfDerivedInterfaceEntry
    MAX-ACCESS       not-accessible
    STATUS           current
    DESCRIPTION
        "Entry for the cucsMgmtProfDerivedInterfaceTable table."
    INDEX { cucsMgmtProfDerivedInterfaceInstanceId }
    ::= { cucsMgmtProfDerivedInterfaceTable 1 }

CucsMgmtProfDerivedInterfaceEntry ::= SEQUENCE {
    cucsMgmtProfDerivedInterfaceInstanceId                           CucsManagedObjectId,
    cucsMgmtProfDerivedInterfaceDn                                   CucsManagedObjectDn,
    cucsMgmtProfDerivedInterfaceRn                                   SnmpAdminString,
    cucsMgmtProfDerivedInterfaceConfigMessage                        SnmpAdminString,
    cucsMgmtProfDerivedInterfaceConfigState                          CucsMgmtConfigState,
    cucsMgmtProfDerivedInterfaceIpV4State                            CucsVnicExternalMgmtIPMode,
    cucsMgmtProfDerivedInterfaceIpV6State                            CucsVnicExternalMgmtIPMode,
    cucsMgmtProfDerivedInterfaceMode                                 CucsMgmtMode,
    cucsMgmtProfDerivedInterfaceOperState                            CucsMgmtOperState,
    cucsMgmtProfDerivedInterfaceMonitorInterval                      Gauge32
}

cucsMgmtProfDerivedInterfaceInstanceId OBJECT-TYPE
    SYNTAX       CucsManagedObjectId
    MAX-ACCESS   not-accessible
    STATUS       current
    DESCRIPTION
        "Instance identifier of the managed object."
    ::= { cucsMgmtProfDerivedInterfaceEntry 1 }

cucsMgmtProfDerivedInterfaceDn OBJECT-TYPE
    SYNTAX       CucsManagedObjectDn
    MAX-ACCESS   read-only
    STATUS       current
    DESCRIPTION
        "Cisco UCS mgmt:ProfDerivedInterface:dn managed object property"
    ::= { cucsMgmtProfDerivedInterfaceEntry 2 }

cucsMgmtProfDerivedInterfaceRn OBJECT-TYPE
    SYNTAX       SnmpAdminString
    MAX-ACCESS   read-only
    STATUS       current
    DESCRIPTION
        "Cisco UCS mgmt:ProfDerivedInterface:rn managed object property"
    ::= { cucsMgmtProfDerivedInterfaceEntry 3 }

cucsMgmtProfDerivedInterfaceConfigMessage OBJECT-TYPE
    SYNTAX       SnmpAdminString
    MAX-ACCESS   read-only
    STATUS       current
    DESCRIPTION
        "Cisco UCS mgmt:ProfDerivedInterface:configMessage
        managed object property"
    ::= { cucsMgmtProfDerivedInterfaceEntry 4 }

cucsMgmtProfDerivedInterfaceConfigState OBJECT-TYPE
    SYNTAX       CucsMgmtConfigState
    MAX-ACCESS   read-only
    STATUS       current
    DESCRIPTION
        "Cisco UCS mgmt:ProfDerivedInterface:configState
        managed object property"
    ::= { cucsMgmtProfDerivedInterfaceEntry 5 }

cucsMgmtProfDerivedInterfaceIpV4State OBJECT-TYPE
    SYNTAX       CucsVnicExternalMgmtIPMode
    MAX-ACCESS   read-only
    STATUS       current
    DESCRIPTION
        "Cisco UCS mgmt:ProfDerivedInterface:ipV4State
        managed object property"
    ::= { cucsMgmtProfDerivedInterfaceEntry 6 }

cucsMgmtProfDerivedInterfaceIpV6State OBJECT-TYPE
    SYNTAX       CucsVnicExternalMgmtIPMode
    MAX-ACCESS   read-only
    STATUS       current
    DESCRIPTION
        "Cisco UCS mgmt:ProfDerivedInterface:ipV6State
        managed object property"
    ::= { cucsMgmtProfDerivedInterfaceEntry 7 }

cucsMgmtProfDerivedInterfaceMode OBJECT-TYPE
    SYNTAX       CucsMgmtMode
    MAX-ACCESS   read-only
    STATUS       current
    DESCRIPTION
        "Cisco UCS mgmt:ProfDerivedInterface:mode managed object property"
    ::= { cucsMgmtProfDerivedInterfaceEntry 8 }

cucsMgmtProfDerivedInterfaceOperState OBJECT-TYPE
    SYNTAX       CucsMgmtOperState
    MAX-ACCESS   read-only
    STATUS       current
    DESCRIPTION
        "Cisco UCS mgmt:ProfDerivedInterface:operState
        managed object property"
    ::= { cucsMgmtProfDerivedInterfaceEntry 9 }

cucsMgmtProfDerivedInterfaceMonitorInterval OBJECT-TYPE
    SYNTAX       Gauge32
    MAX-ACCESS   read-only
    STATUS       current
    DESCRIPTION
        "Cisco UCS mgmt:ProfDerivedInterface:monitorInterval
        managed object property"
    ::= { cucsMgmtProfDerivedInterfaceEntry 10 }

cucsMgmtSecurityTable OBJECT-TYPE
    SYNTAX           SEQUENCE OF CucsMgmtSecurityEntry
    MAX-ACCESS       not-accessible
    STATUS           current
    DESCRIPTION
        "Cisco UCS mgmt:Security managed object table"
    ::= { cucsMgmtObjects 74 }

cucsMgmtSecurityEntry OBJECT-TYPE
    SYNTAX           CucsMgmtSecurityEntry
    MAX-ACCESS       not-accessible
    STATUS           current
    DESCRIPTION
        "Entry for the cucsMgmtSecurityTable table."
    INDEX { cucsMgmtSecurityInstanceId }
    ::= { cucsMgmtSecurityTable 1 }

CucsMgmtSecurityEntry ::= SEQUENCE {
    cucsMgmtSecurityInstanceId                                       CucsManagedObjectId,
    cucsMgmtSecurityDn                                               CucsManagedObjectDn,
    cucsMgmtSecurityRn                                               SnmpAdminString
}

cucsMgmtSecurityInstanceId OBJECT-TYPE
    SYNTAX       CucsManagedObjectId
    MAX-ACCESS   not-accessible
    STATUS       current
    DESCRIPTION
        "Instance identifier of the managed object."
    ::= { cucsMgmtSecurityEntry 1 }

cucsMgmtSecurityDn OBJECT-TYPE
    SYNTAX       CucsManagedObjectDn
    MAX-ACCESS   read-only
    STATUS       current
    DESCRIPTION
        "Cisco UCS mgmt:Security:dn managed object property"
    ::= { cucsMgmtSecurityEntry 2 }

cucsMgmtSecurityRn OBJECT-TYPE
    SYNTAX       SnmpAdminString
    MAX-ACCESS   read-only
    STATUS       current
    DESCRIPTION
        "Cisco UCS mgmt:Security:rn managed object property"
    ::= { cucsMgmtSecurityEntry 3 }

cucsMgmtVnetTable OBJECT-TYPE
    SYNTAX           SEQUENCE OF CucsMgmtVnetEntry
    MAX-ACCESS       not-accessible
    STATUS           current
    DESCRIPTION
        "Cisco UCS mgmt:Vnet managed object table"
    ::= { cucsMgmtObjects 41 }

cucsMgmtVnetEntry OBJECT-TYPE
    SYNTAX           CucsMgmtVnetEntry
    MAX-ACCESS       not-accessible
    STATUS           current
    DESCRIPTION
        "Entry for the cucsMgmtVnetTable table."
    INDEX { cucsMgmtVnetInstanceId }
    ::= { cucsMgmtVnetTable 1 }

CucsMgmtVnetEntry ::= SEQUENCE {
    cucsMgmtVnetInstanceId                                           CucsManagedObjectId,
    cucsMgmtVnetDn                                                   CucsManagedObjectDn,
    cucsMgmtVnetRn                                                   SnmpAdminString,
    cucsMgmtVnetConfigState                                          CucsMgmtConfigState,
    cucsMgmtVnetId                                                   Gauge32,
    cucsMgmtVnetName                                                 SnmpAdminString
}

cucsMgmtVnetInstanceId OBJECT-TYPE
    SYNTAX       CucsManagedObjectId
    MAX-ACCESS   not-accessible
    STATUS       current
    DESCRIPTION
        "Instance identifier of the managed object."
    ::= { cucsMgmtVnetEntry 1 }

cucsMgmtVnetDn OBJECT-TYPE
    SYNTAX       CucsManagedObjectDn
    MAX-ACCESS   read-only
    STATUS       current
    DESCRIPTION
        "Cisco UCS mgmt:Vnet:dn managed object property"
    ::= { cucsMgmtVnetEntry 2 }

cucsMgmtVnetRn OBJECT-TYPE
    SYNTAX       SnmpAdminString
    MAX-ACCESS   read-only
    STATUS       current
    DESCRIPTION
        "Cisco UCS mgmt:Vnet:rn managed object property"
    ::= { cucsMgmtVnetEntry 3 }

cucsMgmtVnetConfigState OBJECT-TYPE
    SYNTAX       CucsMgmtConfigState
    MAX-ACCESS   read-only
    STATUS       current
    DESCRIPTION
        "Cisco UCS mgmt:Vnet:configState managed object property"
    ::= { cucsMgmtVnetEntry 4 }

cucsMgmtVnetId OBJECT-TYPE
    SYNTAX       Gauge32
    MAX-ACCESS   read-only
    STATUS       current
    DESCRIPTION
        "Cisco UCS mgmt:Vnet:id managed object property"
    ::= { cucsMgmtVnetEntry 5 }

cucsMgmtVnetName OBJECT-TYPE
    SYNTAX       SnmpAdminString
    MAX-ACCESS   read-only
    STATUS       current
    DESCRIPTION
        "Cisco UCS mgmt:Vnet:name managed object property"
    ::= { cucsMgmtVnetEntry 6 }

END
