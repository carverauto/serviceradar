-- MIB file created 04-Dec-2002 18:55:53, by
--   SMICng version 2.2.11-beta(PRO)(Solaris), January 20, 2001. Enterprise key cisco.com

ALTIGA-CERT-STATS-MIB DEFINITIONS ::= BEGIN

-- From file: "ALTIGA-CERT-STATS-MIB.my"
-- Compile options "4 7 F H N W 03 06 0B 0G 0N 0T"

IMPORTS
    alStatsCert, alCertGroup
            FROM ALTIGA-MIB
    alCertMibModule
            FROM ALTIGA-GLOBAL-REG
    Counter, Gauge, IpAddress
            FROM RFC1155-SMI
    OBJECT-TYPE
            FROM RFC-1212;

altigaCertStatsMibModule OBJECT IDENTIFIER ::= { alCertMibModule 2 }
-- MODULE-IDENTITY
--  LastUpdated
--    200209051300Z
--  OrgName
--    Cisco Systems, Inc.
--  ContactInfo
--    Cisco Systems
--     170 W Tasman Drive
--     San Jose, CA  95134
--     USA
--    
--     Tel: +1 800 553-NETS
--     E-mail: cs-cvpn3000@cisco.com
--  Descr
--    The Altiga Digital Certificates Statistics MIB models counters and objects that are
--     of management interest for digital certificates.
--    
--     Acronyms
--     The following acronyms are used in this document:
--    
--       CA:         Certificate Authority
--    
--       CRL:        Certificate Revocation List
--    
--       IP:         Internet Protocol
--    
--       MIB:        Management Information Base
--    
--  RevDate
--    200209051300Z
--  RevDescr
--    Added module compliance.
--  RevDate
--    200207100000Z
--  RevDescr
--    Updated with new header

alStatsCertGlobal OBJECT IDENTIFIER ::= { alStatsCert 1 }
altigaCertStatsMibConformance OBJECT IDENTIFIER ::= { altigaCertStatsMibModule 1 }
altigaCertStatsMibCompliances OBJECT IDENTIFIER ::= { altigaCertStatsMibConformance 1 }

alCertStatsServerTable OBJECT-TYPE
    SYNTAX SEQUENCE OF AlCertStatsServerEntry
    ACCESS not-accessible
    STATUS mandatory
    DESCRIPTION
        "List table listing the CA servers."
    ::= { alStatsCert 2 }

alCertStatsServerEntry OBJECT-TYPE
    SYNTAX AlCertStatsServerEntry
    ACCESS not-accessible
    STATUS mandatory
    DESCRIPTION
        "An entry representing a CA server."
    INDEX { alCertStatsServerIndex }
    ::= { alCertStatsServerTable 1 }

AlCertStatsServerEntry ::= SEQUENCE {
    alCertStatsServerIndex INTEGER,
    alCertStatsServerAddress IpAddress,
    alCertStatsServerPortNumber INTEGER,
    alCertStatsServerCertRequests Counter,
    alCertStatsServerCertRetransmissions Counter,
    alCertStatsServerCertRcvd Counter,
    alCertStatsServerCertPendingRequests Gauge,
    alCertStatsServerCertTimeouts Counter,
    alCertStatsServerCRLRequests Counter,
    alCertStatsServerCRLRetransmissions Counter,
    alCertStatsServerCRLRcvd Counter,
    alCertStatsServerCRLPendingRequests Gauge,
    alCertStatsServerCRLTimeouts Counter
    }

alCertStatsServerIndex OBJECT-TYPE
    SYNTAX INTEGER(0..2147483647)
    ACCESS read-only
    STATUS mandatory
    DESCRIPTION
        "Index of this CA."
    ::= { alCertStatsServerEntry 1 }

alCertStatsServerAddress OBJECT-TYPE
    SYNTAX IpAddress
    ACCESS read-only
    STATUS mandatory
    DESCRIPTION
        "The IP address of this CA."
    ::= { alCertStatsServerEntry 2 }

alCertStatsServerPortNumber OBJECT-TYPE
    SYNTAX INTEGER
    ACCESS read-only
    STATUS mandatory
    DESCRIPTION
        "The port number of this CA."
    ::= { alCertStatsServerEntry 3 }

alCertStatsServerCertRequests OBJECT-TYPE
    SYNTAX Counter
    ACCESS read-only
    STATUS mandatory
    DESCRIPTION
        "The total number of certificate request packets sent
         to this CA since client start-up. This does not
         include retransmissions."
    ::= { alCertStatsServerEntry 4 }

alCertStatsServerCertRetransmissions OBJECT-TYPE
    SYNTAX Counter
    ACCESS read-only
    STATUS mandatory
    DESCRIPTION
        "The total number of certificate request packets
         retransmitted to this CA since client start-up."
    ::= { alCertStatsServerEntry 5 }

alCertStatsServerCertRcvd OBJECT-TYPE
    SYNTAX Counter
    ACCESS read-only
    STATUS mandatory
    DESCRIPTION
        "The total number of certificates received from
         this server since client start-up."
    ::= { alCertStatsServerEntry 6 }

alCertStatsServerCertPendingRequests OBJECT-TYPE
    SYNTAX Gauge
    ACCESS read-only
    STATUS mandatory
    DESCRIPTION
        "The total number of certificate request packets
         destined for this server that have not yet timed out
         or received a response. This variable is incremented
         when certificate request is sent and decremented due to
         receipt of a certificate, a timeout or retransmission."
    ::= { alCertStatsServerEntry 7 }

alCertStatsServerCertTimeouts OBJECT-TYPE
    SYNTAX Counter
    ACCESS read-only
    STATUS mandatory
    DESCRIPTION
        "The total number of certificate timeouts to this
         server since client startup."
    ::= { alCertStatsServerEntry 8 }

alCertStatsServerCRLRequests OBJECT-TYPE
    SYNTAX Counter
    ACCESS read-only
    STATUS mandatory
    DESCRIPTION
        "The total number of CRL request packets sent
         to this CA since client start-up. This does not
         include retransmissions."
    ::= { alCertStatsServerEntry 9 }

alCertStatsServerCRLRetransmissions OBJECT-TYPE
    SYNTAX Counter
    ACCESS read-only
    STATUS mandatory
    DESCRIPTION
        "The total number of CRL request packets
         retransmitted to this CA since client start-up."
    ::= { alCertStatsServerEntry 10 }

alCertStatsServerCRLRcvd OBJECT-TYPE
    SYNTAX Counter
    ACCESS read-only
    STATUS mandatory
    DESCRIPTION
        "The total number of CRL received from
         this server since client start-up."
    ::= { alCertStatsServerEntry 11 }

alCertStatsServerCRLPendingRequests OBJECT-TYPE
    SYNTAX Gauge
    ACCESS read-only
    STATUS mandatory
    DESCRIPTION
        "The total number of CRL request packets
         destined for this server that have not yet timed out
         or received a response. This variable is incremented
         when certificate request is sent and decremented due to
         receipt of a certificate, a timeout or retransmission."
    ::= { alCertStatsServerEntry 12 }

alCertStatsServerCRLTimeouts OBJECT-TYPE
    SYNTAX Counter
    ACCESS read-only
    STATUS mandatory
    DESCRIPTION
        "The total number of CRL timeouts to this server since
         client startup."
    ::= { alCertStatsServerEntry 13 }

altigaCertStatsGroup OBJECT IDENTIFIER ::= { alCertGroup 2 }
-- OBJECT-GROUP
--  Status
--    mandatory
--  Descr
--    The objects for Cert statistics.
--  objects
--    alCertStatsServerIndex, alCertStatsServerAddress, 
--    alCertStatsServerPortNumber, alCertStatsServerCertRequests, 
--    alCertStatsServerCertRetransmissions, 
--    alCertStatsServerCertRcvd, 
--    alCertStatsServerCertPendingRequests, 
--    alCertStatsServerCertTimeouts, alCertStatsServerCRLRequests, 
--    alCertStatsServerCRLRetransmissions, alCertStatsServerCRLRcvd, 
--    alCertStatsServerCRLPendingRequests, 
--    alCertStatsServerCRLTimeouts

altigaCertStatsMibCompliance OBJECT IDENTIFIER ::= { altigaCertStatsMibCompliances 1 }
-- MODULE-COMPLIANCE
--  Status
--    mandatory
--  Descr
--    The compliance statement for agents which 
--     implement the Altiga Digital Certificates Statistics MIB.
--  Module
--    >>current<<
--   MandGroup
--    altigaCertStatsGroup


END
