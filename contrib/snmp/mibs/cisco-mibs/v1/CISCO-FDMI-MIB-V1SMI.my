-- MIB file created 19-Nov-2003 11:32:08, by
--   SMICng version 2.2.11-beta(PRO)(Solaris), January 20, 2001. Enterprise key cisco.com

CISCO-FDMI-MIB DEFINITIONS ::= BEGIN

-- From file: "CISCO-FDMI-MIB.my"
-- Compile options "4 7 F H N W 03 06 0B 0G 0N 0T"

IMPORTS
    TruthValue
            FROM SNMPv2-TC-v1
    SnmpAdminString
            FROM SNMP-FRAMEWORK-MIB
    ciscoMgmt
            FROM CISCO-SMI
    FcNameId
            FROM CISCO-ST-TC
    vsanIndex, notifyVsanIndex
            FROM CISCO-VSAN-MIB
    Gauge
            FROM RFC1155-SMI
    OBJECT-TYPE
            FROM RFC-1212
    TRAP-TYPE
            FROM RFC-1215;

ciscoFdmiMIB OBJECT IDENTIFIER ::= { ciscoMgmt 373 }
-- MODULE-IDENTITY
--  LastUpdated
--    200311070000Z
--  OrgName
--    Cisco Systems Inc. 
--  ContactInfo
--         Cisco Systems
--          Customer Service
--    Postal: 170 W Tasman Drive
--          San Jose, CA  95134
--          USA
--    Tel: +1 800 553 -NETS
--    E-mail: cs-san@cisco.com
--  Descr
--    Fabric Device Management Interface (FDMI) MIB. This MIB
--    module defines objects for managing the devices such as
--    HBA (Host Bus Adapter). It provides device information 
--    which have registered with an FC fabric using FDMI.  
--    For more information on FDMI, refer to Fibre Channel 
--    Generic Services-4 Section 6.7 : Fabric Device 
--    Management Interface.
--  RevDate
--    200311070000Z
--  RevDescr
--    Updated with the mib number got from CANA.
--  RevDate
--    200308240000Z
--  RevDescr
--    Initial version of this MIB module.

ciscoFdmiMIBNotifications OBJECT IDENTIFIER ::= { ciscoFdmiMIB 0 }
ciscoFdmiMIBObjects OBJECT IDENTIFIER ::= { ciscoFdmiMIB 1 }
ciscoFdmiMIBConformance OBJECT IDENTIFIER ::= { ciscoFdmiMIB 2 }
cfdmiConfig     OBJECT IDENTIFIER ::= { ciscoFdmiMIBObjects 1 }
cfdmiInfo       OBJECT IDENTIFIER ::= { ciscoFdmiMIBObjects 2 }
cfdmiStatistics OBJECT IDENTIFIER ::= { ciscoFdmiMIBObjects 3 }
ciscoFdmiMIBCompliances OBJECT IDENTIFIER ::= { ciscoFdmiMIBConformance 1 }
ciscoFdmiMIBGroups OBJECT IDENTIFIER ::= { ciscoFdmiMIBConformance 2 }

CFdmiRejectReasonCode ::= INTEGER {
        invalidCommandCode(1),
        unableToPerformCmdReq(2),
        invalidSize(3)
        }
-- TEXTUAL-CONVENTION
--  Status
--    mandatory
--  Descr
--    The reason codes for FDMI rejects for HBA requests.
--      invalidCommandCode (1) - invalid command code in the 
--                     request
--      unableToPerformCmdReq (2) - FDMI not able to perform
--                     the command requested
--      invalidSize (3) - invalid size 
--    .
--  Refer
--    Fibre Channel Generic Services-4 Section
--     6.7.4.6 : Reason Code Explanation.

CFdmiRejectReasonCodeExpl ::= INTEGER {
        noAdditionalExpl(1),
        hbaAlreadyRegistered(2),
        attrForSpecifiedHbaNotReg(3),
        hbaAttrMultiAttribSameType(4),
        invalidHbaAttrBlockLen(5),
        reqdHbaAttrNotPresent(6),
        origPortNotInRegPortList(7),
        hbaIdNotInRegPortList(8),
        portAttrNotRegistered(9),
        portNotRegistered(10),
        portAttrMultiAttrSameType(11),
        invalidPortAttrBlockLen(12),
        none(13)
        }
-- TEXTUAL-CONVENTION
--  Status
--    mandatory
--  Descr
--    The explanations for reason codes for FDMI rejects for
--    HBA requests.
--      noAdditionalExpl (1)            - No Additional 
--            Explanation
--      hbaAlreadyRegistered (2)        - HBA already 
--            registered
--      attrForSpecifiedHbaNotReg (3)   - Attributes for 
--            specified HBA not registered
--      hbaAttrMultiAttribSameType (4)  - HBA attributes 
--            block contains multiple attributes of same type
--      invalidHbaAttrBlockLen (5)      - Invalid HBA 
--            attribute block length
--      reqdHbaAttrNotPresent (6)       - Required HBA
--            attributes not present
--      origPortNotInRegPortList (7)    - Originating port not 
--            in registered Port list
--      hbaIdNotInRegPortList (8)       - HBA Id is not
--            registered port list
--      portAttrNotRegistered (9)       - Port attributes not 
--            registered
--      portNotRegistered (10)          - port not registered
--      portAttrMultiAttrSameType (11)  - port attribute block
--            contains multiple attributes of same type
--      invalidPortAttrBlockLen (12)    - Invalid port 
--            attribute block length
--      none (13)                       - not known or 
--            reserved
--    .
--  Refer
--    Fibre Channel Generic Services-4 Section
--     6.7.4.6 : Reason Code Explanation.

cfdmiRejectRegNotifyEnable OBJECT-TYPE
    SYNTAX TruthValue
--    Rsyntax INTEGER {
--        true(1),
--        false(2)
--        }
    ACCESS read-write
    STATUS mandatory
    DESCRIPTION
        "This object specifies if the FDMI should
        generate 'cfdmiRejectRegNotify' notifications.
         
        If value of this object is 'true', then the 
        notification is generated when a registration request is
        rejected. 
        If it is 'false', the notification is not generated."
    DEFVAL { false }
    ::= { cfdmiConfig 1 }

cfdmiHbaInfoTable OBJECT-TYPE
    SYNTAX SEQUENCE OF CfdmiHbaInfoEntry
    ACCESS not-accessible
    STATUS mandatory
    DESCRIPTION
        "This table lists all the HBAs registered with the 
        Fabric Device Management Interface."
    ::= { cfdmiInfo 1 }

cfdmiHbaInfoEntry OBJECT-TYPE
    SYNTAX CfdmiHbaInfoEntry
    ACCESS not-accessible
    STATUS mandatory
    DESCRIPTION
        "An entry (conceptual row) in the cfdmiHbaInfoTable. It
        provides information that has been registered with FDMI
        by a HBA, identified by cfdmiHbaInfoId, where the
        registration was received on the VSAN identified by
        vsanIndex. 
        If the HBA has registered some but not all of the 
        information represented by the columnar objects in this 
        table, then the value of the unregistered objects will 
        be either: the zero-length string (for string-based 
        objects) or the zero value (for interger-based objects)."
    INDEX { vsanIndex, cfdmiHbaInfoId }
    ::= { cfdmiHbaInfoTable 1 }

CfdmiHbaInfoEntry ::= SEQUENCE {
    cfdmiHbaInfoId FcNameId,
    cfdmiHbaInfoNodeName FcNameId,
    cfdmiHbaInfoMfg SnmpAdminString,
    cfdmiHbaInfoSn SnmpAdminString,
    cfdmiHbaInfoModel SnmpAdminString,
    cfdmiHbaInfoModelDescr SnmpAdminString,
    cfdmiHbaInfoHwVer SnmpAdminString,
    cfdmiHbaInfoDriverVer SnmpAdminString,
    cfdmiHbaInfoOptROMVer SnmpAdminString,
    cfdmiHbaInfoFwVer SnmpAdminString,
    cfdmiHbaInfoOSInfo SnmpAdminString,
    cfdmiHbaInfoMaxCTPayload Gauge
    }

cfdmiHbaInfoId OBJECT-TYPE
    SYNTAX FcNameId
--    Rsyntax OCTET STRING(SIZE(8))
    ACCESS not-accessible
    STATUS mandatory
    DESCRIPTION
        "The WWN of this HBA."
    REFERENCE
        "Fibre Channel Generic Services-4 Rev 7.6 
        Section 6.7.4.5.1 ."
    ::= { cfdmiHbaInfoEntry 1 }

cfdmiHbaInfoNodeName OBJECT-TYPE
    SYNTAX FcNameId
--    Rsyntax OCTET STRING(SIZE(8))
    ACCESS read-only
    STATUS mandatory
    DESCRIPTION
        "The WWN of the node containing this HBA. "
    REFERENCE
        "Fibre Channel Generic Services-4 Rev 7.6 
        Section 6.7.4.4.2.6 ."
    ::= { cfdmiHbaInfoEntry 2 }

cfdmiHbaInfoMfg OBJECT-TYPE
    SYNTAX SnmpAdminString(SIZE(0..63))
--    Rsyntax OCTET STRING(SIZE(0..63))
    ACCESS read-only
    STATUS mandatory
    DESCRIPTION
        "The name of the manufacturer of this HBA."
    REFERENCE
        "Fibre Channel Generic Services-4 Rev 7.6 
        Section 6.7.4.4.2.2 ."
    ::= { cfdmiHbaInfoEntry 3 }

cfdmiHbaInfoSn OBJECT-TYPE
    SYNTAX SnmpAdminString(SIZE(0..63))
--    Rsyntax OCTET STRING(SIZE(0..63))
    ACCESS read-only
    STATUS mandatory
    DESCRIPTION
        "The serial number of this HBA."
    REFERENCE
        "Fibre Channel Generic Services-4 Rev 7.6 
        Section 6.7.4.4.2.3 ."
    ::= { cfdmiHbaInfoEntry 4 }

cfdmiHbaInfoModel OBJECT-TYPE
    SYNTAX SnmpAdminString(SIZE(0..255))
--    Rsyntax OCTET STRING(SIZE(0..255))
    ACCESS read-only
    STATUS mandatory
    DESCRIPTION
        "The model of this HBA."
    REFERENCE
        "Fibre Channel Generic Services-4 Rev 7.6 
        Section 6.7.4.4.2.4 ."
    ::= { cfdmiHbaInfoEntry 5 }

cfdmiHbaInfoModelDescr OBJECT-TYPE
    SYNTAX SnmpAdminString(SIZE(0..255))
--    Rsyntax OCTET STRING(SIZE(0..255))
    ACCESS read-only
    STATUS mandatory
    DESCRIPTION
        "The string that describes the model of this HBA."
    REFERENCE
        "Fibre Channel Generic Services-4 Rev 7.6 
        Section 6.7.4.4.2.5 ."
    ::= { cfdmiHbaInfoEntry 6 }

cfdmiHbaInfoHwVer OBJECT-TYPE
    SYNTAX SnmpAdminString(SIZE(0..255))
--    Rsyntax OCTET STRING(SIZE(0..255))
    ACCESS read-only
    STATUS mandatory
    DESCRIPTION
        "The hardware version of this HBA."
    REFERENCE
        "Fibre Channel Generic Services-4 Rev 7.6 
        Section 6.7.4.4.2.8 ."
    ::= { cfdmiHbaInfoEntry 7 }

cfdmiHbaInfoDriverVer OBJECT-TYPE
    SYNTAX SnmpAdminString(SIZE(0..255))
--    Rsyntax OCTET STRING(SIZE(0..255))
    ACCESS read-only
    STATUS mandatory
    DESCRIPTION
        "The version level of the driver software controlling 
        this HBA."
    REFERENCE
        "Fibre Channel Generic Services-4 Rev 7.6 
        Section 6.7.4.4.2.9 ."
    ::= { cfdmiHbaInfoEntry 8 }

cfdmiHbaInfoOptROMVer OBJECT-TYPE
    SYNTAX SnmpAdminString(SIZE(0..255))
--    Rsyntax OCTET STRING(SIZE(0..255))
    ACCESS read-only
    STATUS mandatory
    DESCRIPTION
        "The version of the Option ROM or the BIOS of this HBA."
    REFERENCE
        "Fibre Channel Generic Services-4 Rev 7.6 
        Section 6.7.4.4.2.10 ."
    ::= { cfdmiHbaInfoEntry 9 }

cfdmiHbaInfoFwVer OBJECT-TYPE
    SYNTAX SnmpAdminString(SIZE(0..255))
--    Rsyntax OCTET STRING(SIZE(0..255))
    ACCESS read-only
    STATUS mandatory
    DESCRIPTION
        "The version of the firmware executed by this HBA."
    REFERENCE
        "Fibre Channel Generic Services-4 Rev 7.6 
        Section 6.7.4.4.2.11 ."
    ::= { cfdmiHbaInfoEntry 10 }

cfdmiHbaInfoOSInfo OBJECT-TYPE
    SYNTAX SnmpAdminString(SIZE(0..255))
--    Rsyntax OCTET STRING(SIZE(0..255))
    ACCESS read-only
    STATUS mandatory
    DESCRIPTION
        "The type and version of the operating system 
        controlling this HBA."
    REFERENCE
        "Fibre Channel Generic Services-4 Rev 7.6 
        Section 6.7.4.4.2.12 ."
    ::= { cfdmiHbaInfoEntry 11 }

cfdmiHbaInfoMaxCTPayload OBJECT-TYPE
    SYNTAX Gauge
--  Units
--    32-bit words
    ACCESS read-only
    STATUS mandatory
    DESCRIPTION
        "The maximum size of the Common Transport (CT) payload 
        including all CT headers but no FC frame header(s), 
        that may be send or received by application software 
        resident in the host containing this HBA."
    REFERENCE
        "Fibre Channel Generic Services-4 Rev 7.6 
        Section 6.7.4.4.2.13 ."
    ::= { cfdmiHbaInfoEntry 12 }

cfdmiHbaPortTable OBJECT-TYPE
    SYNTAX SEQUENCE OF CfdmiHbaPortEntry
    ACCESS not-accessible
    STATUS mandatory
    DESCRIPTION
        "List of ports registered with Fibre Channel Device 
        Management Interface."
    ::= { cfdmiInfo 2 }

cfdmiHbaPortEntry OBJECT-TYPE
    SYNTAX CfdmiHbaPortEntry
    ACCESS not-accessible
    STATUS mandatory
    DESCRIPTION
        "An entry (conceptual row) in the cfdmiHbaPortTable. It
        contains information about the Nx_port, on this HBA,
        identified by cfdmiHbaInfoId, where the registration
        of the HBA with FDMI was received on the VSAN identified
        by vsanIndex.
        If the HBA has registered some but not all of the 
        information represented by the columnar objects in this 
        table, then the value of the unregistered objects will 
        be either: the zero-length string (for string-based 
        objects) or the zero value (for interger-based objects)."
    INDEX { vsanIndex, cfdmiHbaInfoId, cfdmiHbaPortId }
    ::= { cfdmiHbaPortTable 1 }

CfdmiHbaPortEntry ::= SEQUENCE {
    cfdmiHbaPortId FcNameId,
    cfdmiHbaPortSupportedFC4Type OCTET STRING,
    cfdmiHbaPortSupportedSpeed Gauge,
    cfdmiHbaPortCurrentSpeed Gauge,
    cfdmiHbaPortMaxFrameSize Gauge,
    cfdmiHbaPortOsDevName SnmpAdminString,
    cfdmiHbaPortHostName SnmpAdminString
    }

cfdmiHbaPortId OBJECT-TYPE
    SYNTAX FcNameId
--    Rsyntax OCTET STRING(SIZE(8))
    ACCESS not-accessible
    STATUS mandatory
    DESCRIPTION
        "The WWN of this port."
    REFERENCE
        "Fibre Channel Generic Services-4 Rev 7.6 
        Section 6.7.4.4.3.3 ."
    ::= { cfdmiHbaPortEntry 1 }

cfdmiHbaPortSupportedFC4Type OBJECT-TYPE
    SYNTAX OCTET STRING
    ACCESS read-only
    STATUS mandatory
    DESCRIPTION
        "The supported FC-4 types attribute registered for this 
        port on this VSAN."
    REFERENCE
        "Fibre Channel Generic Services-4 Rev 7.6 
        Section 6.7.4.4.3.6 and Section 5.2.3.8 . "
    ::= { cfdmiHbaPortEntry 2 }

cfdmiHbaPortSupportedSpeed OBJECT-TYPE
    SYNTAX Gauge
    ACCESS read-only
    STATUS mandatory
    DESCRIPTION
        "The supported speed registered for this port on this
        VSAN. "
    REFERENCE
        "Fibre Channel Generic Services-4 Rev 7.6 
        Section 6.7.4.4.3.8 ."
    ::= { cfdmiHbaPortEntry 3 }

cfdmiHbaPortCurrentSpeed OBJECT-TYPE
    SYNTAX Gauge
    ACCESS read-only
    STATUS mandatory
    DESCRIPTION
        "The current speed registered for this port on this 
        VSAN. "
    REFERENCE
        "Fibre Channel Generic Services-4 Rev 7.6 
        Section 6.7.4.4.3.9 ."
    ::= { cfdmiHbaPortEntry 4 }

cfdmiHbaPortMaxFrameSize OBJECT-TYPE
    SYNTAX Gauge
    ACCESS read-only
    STATUS mandatory
    DESCRIPTION
        "The maximum frame size attribute registered for this
        port on this VSAN."
    REFERENCE
        "Fibre Channel Generic Services-4 Rev 7.6 
        Section 6.7.4.4.3.10 ."
    ::= { cfdmiHbaPortEntry 5 }

cfdmiHbaPortOsDevName OBJECT-TYPE
    SYNTAX SnmpAdminString(SIZE(0..255))
--    Rsyntax OCTET STRING(SIZE(0..255))
    ACCESS read-only
    STATUS mandatory
    DESCRIPTION
        "The OS Device Name attribute registered for this port
        on this VSAN."
    REFERENCE
        "Fibre Channel Generic Services-4 Rev 7.6 
        Section 6.7.4.4.3.11 ."
    ::= { cfdmiHbaPortEntry 6 }

cfdmiHbaPortHostName OBJECT-TYPE
    SYNTAX SnmpAdminString(SIZE(0..255))
--    Rsyntax OCTET STRING(SIZE(0..255))
    ACCESS read-only
    STATUS mandatory
    DESCRIPTION
        "The name of the host associated with this port."
    REFERENCE
        "Fibre Channel Generic Services-4, Late Comment
         Section 6.7.4.4.3.12 ."
    ::= { cfdmiHbaPortEntry 7 }

cfdmiRejectReasonCode OBJECT-TYPE
    SYNTAX CFdmiRejectReasonCode
--    Rsyntax INTEGER {
--        invalidCommandCode(1),
--        unableToPerformCmdReq(2),
--        invalidSize(3)
--        }
    ACCESS not-accessible
    STATUS mandatory
    DESCRIPTION
        "The registration reject reason code. This object
        contains the reason code corresponding to the most
        recent FDMI Registration request failure."
    ::= { cfdmiInfo 3 }

cfdmiRejectReasonCodeExpl OBJECT-TYPE
    SYNTAX CFdmiRejectReasonCodeExpl
--    Rsyntax INTEGER {
--        noAdditionalExpl(1),
--        hbaAlreadyRegistered(2),
--        attrForSpecifiedHbaNotReg(3),
--        hbaAttrMultiAttribSameType(4),
--        invalidHbaAttrBlockLen(5),
--        reqdHbaAttrNotPresent(6),
--        origPortNotInRegPortList(7),
--        hbaIdNotInRegPortList(8),
--        portAttrNotRegistered(9),
--        portNotRegistered(10),
--        portAttrMultiAttrSameType(11),
--        invalidPortAttrBlockLen(12),
--        none(13)
--        }
    ACCESS not-accessible
    STATUS mandatory
    DESCRIPTION
        "The registration reject reason code explanation. This
        object contains the reason code explanation if the 
        above object has a reason code corresponding to  
        'Unable to perform command request'. This object like
        the one above, corresponds to the most recent FDMI
        Registration request rejection."
    ::= { cfdmiInfo 4 }

cfdmiNotifyRegOperType OBJECT-TYPE
    SYNTAX INTEGER {
        regHBA(1),
        regHAT(2),
        regPRT(3),
        regPA(4)
        }
    ACCESS not-accessible
    STATUS mandatory
    DESCRIPTION
        "The type of registration operation.
        'regHBA' - register HBA.
        'regHAT' - register HBA attributes.
        'regPRT' - register port.
        'regPA'  - register port attributes. "
    ::= { cfdmiInfo 5 }

cfdmiNotifyHBAPortId OBJECT-TYPE
    SYNTAX FcNameId
--    Rsyntax OCTET STRING(SIZE(8))
    ACCESS not-accessible
    STATUS mandatory
    DESCRIPTION
        "The identifier to be sent in cfdmiRejectRegNotify.
        The value of this object would be HBA identifier if
        the value of 'notifyRegOperType' is either 'regHBA' or
        'regHAT'. The value of this object would be port
        identifier if the value of 'notifyRegOperType' is either
        'regPRT' or 'regPA'. "
    ::= { cfdmiInfo 6 }

cfdmiRejectRegNotify TRAP-TYPE
-- Reverse mappable trap
    ENTERPRISE ciscoFdmiMIB
    VARIABLES {
        notifyVsanIndex, cfdmiNotifyRegOperType, 
        cfdmiNotifyHBAPortId, cfdmiRejectReasonCode, 
        cfdmiRejectReasonCodeExpl }
--  Status
--    mandatory
    DESCRIPTION
        "This notification is generated by the FDMI
        whenever it rejects a registration request. The FDMI
        should update the 'cfdmiRejectReasonCode' and 
        'cfdmiRejectReasonCodeExpl' objects with
        the corresponding reason code and reason code 
        explanation before sending the notification. These 
        two objects are also included along with the 
        notification to provide the reason for the reject."
    ::= 1

cfdmiConfigGroup OBJECT IDENTIFIER ::= { ciscoFdmiMIBGroups 1 }
-- OBJECT-GROUP
--  Status
--    mandatory
--  Descr
--    A collection of objects for configuring FDMI.
--  objects
--    cfdmiRejectRegNotifyEnable

cfdmiHbaInformationGroup OBJECT IDENTIFIER ::= { ciscoFdmiMIBGroups 2 }
-- OBJECT-GROUP
--  Status
--    mandatory
--  Descr
--    A collection of objects for HBA Information.
--  objects
--    cfdmiHbaInfoNodeName, cfdmiHbaInfoMfg, cfdmiHbaInfoSn, 
--    cfdmiHbaInfoModel, cfdmiHbaInfoModelDescr, cfdmiHbaInfoHwVer, 
--    cfdmiHbaInfoDriverVer, cfdmiHbaInfoOptROMVer, 
--    cfdmiHbaInfoFwVer, cfdmiHbaInfoOSInfo, 
--    cfdmiHbaInfoMaxCTPayload, cfdmiRejectReasonCode, 
--    cfdmiRejectReasonCodeExpl, cfdmiNotifyRegOperType, 
--    cfdmiNotifyHBAPortId

cfdmiHbaPortInformationGroup OBJECT IDENTIFIER ::= { ciscoFdmiMIBGroups 3 }
-- OBJECT-GROUP
--  Status
--    mandatory
--  Descr
--    A collection of objects for HBA port information.
--  objects
--    cfdmiHbaPortSupportedFC4Type, cfdmiHbaPortSupportedSpeed, 
--    cfdmiHbaPortCurrentSpeed, cfdmiHbaPortMaxFrameSize, 
--    cfdmiHbaPortOsDevName, cfdmiHbaPortHostName

cfdmiNotificationGroup OBJECT IDENTIFIER ::= { ciscoFdmiMIBGroups 4 }
-- NOTIFICATION-GROUP
--  Status
--    mandatory
--  Descr
--    A collection of notifications for managing FDMI.
--  notifications
--    cfdmiRejectRegNotify

ciscoFdmiMIBCompliance OBJECT IDENTIFIER ::= { ciscoFdmiMIBCompliances 1 }
-- MODULE-COMPLIANCE
--  Status
--    mandatory
--  Descr
--    The compliance statement for entities which
--     implement the CISCO-FDMI-MIB.
--  Module
--    >>current<<
--   MandGroup
--    cfdmiConfigGroup
--   MandGroup
--    cfdmiHbaInformationGroup
--   MandGroup
--    cfdmiHbaPortInformationGroup
--   MandGroup
--    cfdmiNotificationGroup


END
