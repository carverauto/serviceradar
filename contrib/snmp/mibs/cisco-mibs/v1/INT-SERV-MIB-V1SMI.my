-- MIB file created 19-Mar-2002 14:48:00, by
--   SMICng version 2.2.11-beta(PRO)(Solaris), January 20, 2001. Enterprise key cisco.com

INT-SERV-MIB DEFINITIONS ::= BEGIN

-- From file: "INT-SERV-MIB.my"
-- Compile options "4 7 F H N W 03 06 0B 0G 0N 0T"

IMPORTS
    mib-2
            FROM SNMPv2-SMI-v1
    RowStatus, TruthValue, TestAndIncr
            FROM SNMPv2-TC-v1
    ifIndex, InterfaceIndex
            FROM IF-MIB
    Counter, Gauge
            FROM RFC1155-SMI
    OBJECT-TYPE
            FROM RFC-1212;

intSrv OBJECT IDENTIFIER ::= { mib-2 52 }
-- MODULE-IDENTITY
--  LastUpdated
--    9710030642Z
--  OrgName
--    IETF Integrated Services Working Group
--  ContactInfo
--           Fred Baker
--    Postal: Cisco Systems
--            519 Lado Drive
--            Santa Barbara, California 93111
--    Tel:    +1 805 681 0115
--    E-Mail: fred@cisco.com
--    
--            John Krawczyk
--    Postal: ArrowPoint Communications
--            235 Littleton Road
--            Westford, Massachusetts 01886
--    Tel:    +1 508 692 5875
--    E-Mail: jjk@tiac.net
--  Descr
--    The MIB module to describe the Integrated Services
--    Protocol

intSrvObjects   OBJECT IDENTIFIER ::= { intSrv 1 }
intSrvGenObjects OBJECT IDENTIFIER ::= { intSrv 2 }
intSrvNotifications OBJECT IDENTIFIER ::= { intSrv 3 }
intSrvConformance OBJECT IDENTIFIER ::= { intSrv 4 }
intSrvGroups    OBJECT IDENTIFIER ::= { intSrvConformance 1 }
intSrvCompliances OBJECT IDENTIFIER ::= { intSrvConformance 2 }

SessionNumber ::= INTEGER(0..2147483647)
-- TEXTUAL-CONVENTION
--  Status
--    mandatory
--  Descr
--    The Session  Number  convention  is  used  for
--    numbers  identifying  sessions or saved PATH or
--    RESV information. It is a number in  the  range
--    returned  by  a TestAndIncr variable, having no
--    protocol meaning whatsoever but serving instead
--    as simple identifier.
--    
--    The alternative was a very complex instance  or
--    instance object that became unwieldy.

Protocol ::= INTEGER(1..255)
-- TEXTUAL-CONVENTION
--  DspHint
--    d
--  Status
--    mandatory
--  Descr
--    The value of the IP Protocol field  of  an  IP
--    Datagram  Header.  This identifies the protocol
--    layer above IP.  For example, the  value  6  is
--    used  for TCP and the value 17 is used for UDP.
--    The values of this field are defined in the As-
--    signed Numbers RFC.

SessionType ::= INTEGER(1..255)
-- TEXTUAL-CONVENTION
--  Status
--    mandatory
--  Descr
--    The value of the C-Type field of a Session ob-
--    ject,  as  defined  in  the RSVP specification.
--    This value  determines  the  lengths  of  octet
--    strings  and use of certain objects such as the
--    'port' variables. If the C-Type  calls  for  an
--    IP6  address, one would expect all source, des-
--    tination, and next/previous hop addresses to be
--    16  bytes long, and for the ports to be UDP/TCP
--    port numbers, for example.

Port ::= OCTET STRING(SIZE(2..4))
-- TEXTUAL-CONVENTION
--  DspHint
--    d
--  Status
--    mandatory
--  Descr
--    The value of the UDP or TCP Source or Destina-
--    tion  Port field, a virtual destination port or
--    generalized port identifier used with the IPSEC
--    Authentication Header or Encapsulating Security
--    Payload, or other session discriminator.  If it
--    is  not  used, the value should be of length 0.
--    This pair, when coupled with the  IP  Addresses
--    of the source and destination system and the IP
--    protocol  field,  uniquely  identifies  a  data
--    stream.

MessageSize ::= INTEGER(0..2147483647)
-- TEXTUAL-CONVENTION
--  DspHint
--    d
--  Status
--    mandatory
--  Descr
--    The size of a message in bytes. This  is  used
--    to  specify  the  minimum and maximum size of a
--    message along an integrated services route.

BitRate ::= INTEGER(0..2147483647)
-- TEXTUAL-CONVENTION
--  DspHint
--    d
--  Status
--    mandatory
--  Descr
--    The rate, in bits/second, that data  may  move
--    in  the context.  Applicable contexts minimally
--    include the speed of an  interface  or  virtual
--    circuit, the data rate of a (potentially aggre-
--    gated) data flow, or the data rate to be  allo-
--    cated for use by a flow.

BurstSize ::= INTEGER(0..2147483647)
-- TEXTUAL-CONVENTION
--  DspHint
--    d
--  Status
--    mandatory
--  Descr
--    The number of octets of IP Data, including  IP
--    Headers, that a stream may send without concern
--    for policing.

QosService ::= INTEGER {
        bestEffort(1),
        guaranteedDelay(2),
        controlledLoad(5)
        }
-- TEXTUAL-CONVENTION
--  Status
--    mandatory
--  Descr
--    The class of service in use by a flow.

intSrvIfAttribTable OBJECT-TYPE
    SYNTAX SEQUENCE OF IntSrvIfAttribEntry
    ACCESS not-accessible
    STATUS mandatory
    DESCRIPTION
        "The reservable attributes of the system's  in-
        terfaces."
    ::= { intSrvObjects 1 }

intSrvIfAttribEntry OBJECT-TYPE
    SYNTAX IntSrvIfAttribEntry
    ACCESS not-accessible
    STATUS mandatory
    DESCRIPTION
        "The reservable attributes of  a  given  inter-
        face."
    INDEX { ifIndex }
    ::= { intSrvIfAttribTable 1 }

IntSrvIfAttribEntry ::= SEQUENCE {
    intSrvIfAttribAllocatedBits BitRate,
    intSrvIfAttribMaxAllocatedBits BitRate,
    intSrvIfAttribAllocatedBuffer BurstSize,
    intSrvIfAttribFlows Gauge,
    intSrvIfAttribPropagationDelay INTEGER,
    intSrvIfAttribStatus RowStatus
    }

intSrvIfAttribAllocatedBits OBJECT-TYPE
    SYNTAX BitRate
--    Rsyntax INTEGER(0..2147483647)
--  Units
--    Bits per second
    ACCESS read-only
    STATUS mandatory
    DESCRIPTION
        "The number of bits/second currently  allocated
        to reserved sessions on the interface."
    ::= { intSrvIfAttribEntry 1 }

intSrvIfAttribMaxAllocatedBits OBJECT-TYPE
    SYNTAX BitRate
--    Rsyntax INTEGER(0..2147483647)
--  Units
--    Bits per second
    ACCESS read-write
    STATUS mandatory
    DESCRIPTION
        "The maximum number of bits/second that may  be
        allocated  to  reserved  sessions on the inter-
        face."
    ::= { intSrvIfAttribEntry 2 }

intSrvIfAttribAllocatedBuffer OBJECT-TYPE
    SYNTAX BurstSize
--    Rsyntax INTEGER(0..2147483647)
--  Units
--    Bytes
    ACCESS read-only
    STATUS mandatory
    DESCRIPTION
        "The amount of buffer space  required  to  hold
        the simultaneous burst of all reserved flows on
        the interface."
    ::= { intSrvIfAttribEntry 3 }

intSrvIfAttribFlows OBJECT-TYPE
    SYNTAX Gauge
    ACCESS read-only
    STATUS mandatory
    DESCRIPTION
        "The number of reserved flows currently  active
        on  this  interface.  A flow can be created ei-
        ther from a reservation protocol (such as  RSVP
        or ST-II) or via configuration information."
    ::= { intSrvIfAttribEntry 4 }

intSrvIfAttribPropagationDelay OBJECT-TYPE
    SYNTAX INTEGER
--  Units
--    microseconds
    ACCESS read-write
    STATUS mandatory
    DESCRIPTION
        "The amount of propagation delay that this  in-
        terface  introduces  in addition to that intro-
        diced by bit propagation delays."
    DEFVAL { 0 }
    ::= { intSrvIfAttribEntry 5 }

intSrvIfAttribStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "'active' on interfaces that are configured for
        RSVP."
    ::= { intSrvIfAttribEntry 6 }

intSrvFlowTable OBJECT-TYPE
    SYNTAX SEQUENCE OF IntSrvFlowEntry
    ACCESS not-accessible
    STATUS mandatory
    DESCRIPTION
        "Information describing the reserved flows  us-
        ing the system's interfaces."
    ::= { intSrvObjects 2 }

intSrvFlowEntry OBJECT-TYPE
    SYNTAX IntSrvFlowEntry
    ACCESS not-accessible
    STATUS mandatory
    DESCRIPTION
        "Information describing the use of a given  in-
        terface   by   a   given   flow.   The  counter
        intSrvFlowPoliced starts counting  at  the  in-
        stallation of the flow."
    INDEX { intSrvFlowNumber }
    ::= { intSrvFlowTable 1 }

IntSrvFlowEntry ::= SEQUENCE {
    intSrvFlowNumber SessionNumber,
    intSrvFlowType SessionType,
    intSrvFlowOwner INTEGER,
    intSrvFlowDestAddr OCTET STRING,
    intSrvFlowSenderAddr OCTET STRING,
    intSrvFlowDestAddrLength INTEGER,
    intSrvFlowSenderAddrLength INTEGER,
    intSrvFlowProtocol Protocol,
    intSrvFlowDestPort Port,
    intSrvFlowPort Port,
    intSrvFlowFlowId INTEGER,
    intSrvFlowInterface InterfaceIndex,
    intSrvFlowIfAddr OCTET STRING,
    intSrvFlowRate BitRate,
    intSrvFlowBurst BurstSize,
    intSrvFlowWeight INTEGER,
    intSrvFlowQueue INTEGER,
    intSrvFlowMinTU MessageSize,
    intSrvFlowMaxTU MessageSize,
    intSrvFlowBestEffort Counter,
    intSrvFlowPoliced Counter,
    intSrvFlowDiscard TruthValue,
    intSrvFlowService QosService,
    intSrvFlowOrder INTEGER,
    intSrvFlowStatus RowStatus
    }

intSrvFlowNumber OBJECT-TYPE
    SYNTAX SessionNumber
--    Rsyntax INTEGER(0..2147483647)
    ACCESS not-accessible
    STATUS mandatory
    DESCRIPTION
        "The number of this flow.  This is for SNMP In-
        dexing purposes only and has no relation to any
        protocol value."
    ::= { intSrvFlowEntry 1 }

intSrvFlowType OBJECT-TYPE
    SYNTAX SessionType
--    Rsyntax INTEGER(1..255)
    ACCESS read-write
    STATUS mandatory
    DESCRIPTION
        "The type of session (IP4, IP6, IP6  with  flow
        information, etc)."
    ::= { intSrvFlowEntry 2 }

intSrvFlowOwner OBJECT-TYPE
    SYNTAX INTEGER {
        other(1),
        rsvp(2),
        management(3)
        }
    ACCESS read-write
    STATUS mandatory
    DESCRIPTION
        "The process that installed this  flow  in  the
        queue policy database."
    ::= { intSrvFlowEntry 3 }

intSrvFlowDestAddr OBJECT-TYPE
    SYNTAX OCTET STRING(SIZE(4..16))
    ACCESS read-write
    STATUS mandatory
    DESCRIPTION
        "The destination address used by all senders in
        this  session.   This object may not be changed
        when the value of the RowStatus object is  'ac-
        tive'."
    ::= { intSrvFlowEntry 4 }

intSrvFlowSenderAddr OBJECT-TYPE
    SYNTAX OCTET STRING(SIZE(4..16))
    ACCESS read-write
    STATUS mandatory
    DESCRIPTION
        "The source address of the sender  selected  by
        this  reservation.  The value of all zeroes in-
        dicates 'all senders'.  This object may not  be
        changed  when the value of the RowStatus object
        is 'active'."
    ::= { intSrvFlowEntry 5 }

intSrvFlowDestAddrLength OBJECT-TYPE
    SYNTAX INTEGER(0..128)
    ACCESS read-write
    STATUS mandatory
    DESCRIPTION
        "The length of the destination address in bits.
        This  is  the CIDR Prefix Length, which for IP4
        hosts and multicast addresses is 32 bits.  This
        object may not be changed when the value of the
        RowStatus object is 'active'."
    ::= { intSrvFlowEntry 6 }

intSrvFlowSenderAddrLength OBJECT-TYPE
    SYNTAX INTEGER(0..128)
    ACCESS read-write
    STATUS mandatory
    DESCRIPTION
        "The length of the sender's  address  in  bits.
        This  is  the CIDR Prefix Length, which for IP4
        hosts and multicast addresses is 32 bits.  This
        object may not be changed when the value of the
        RowStatus object is 'active'."
    ::= { intSrvFlowEntry 7 }

intSrvFlowProtocol OBJECT-TYPE
    SYNTAX Protocol
--    Rsyntax INTEGER(1..255)
    ACCESS read-write
    STATUS mandatory
    DESCRIPTION
        "The IP Protocol used by a session.   This  ob-
        ject  may  not be changed when the value of the
        RowStatus object is 'active'."
    ::= { intSrvFlowEntry 8 }

intSrvFlowDestPort OBJECT-TYPE
    SYNTAX Port
--    Rsyntax OCTET STRING(SIZE(2..4))
    ACCESS read-write
    STATUS mandatory
    DESCRIPTION
        "The UDP or TCP port number used as a  destina-
        tion  port for all senders in this session.  If
        the  IP   protocol   in   use,   specified   by
        intSrvResvFwdProtocol,  is 50 (ESP) or 51 (AH),
        this  represents  a  virtual  destination  port
        number.   A value of zero indicates that the IP
        protocol in use does not have ports.  This  ob-
        ject  may  not be changed when the value of the
        RowStatus object is 'active'."
    ::= { intSrvFlowEntry 9 }

intSrvFlowPort OBJECT-TYPE
    SYNTAX Port
--    Rsyntax OCTET STRING(SIZE(2..4))
    ACCESS read-write
    STATUS mandatory
    DESCRIPTION
        "The UDP or TCP port number used  as  a  source
        port  for  this sender in this session.  If the
        IP    protocol    in    use,    specified    by
        intSrvResvFwdProtocol  is  50 (ESP) or 51 (AH),
        this represents a generalized  port  identifier
        (GPI).   A  value of zero indicates that the IP
        protocol in use does not have ports.  This  ob-
        ject  may  not be changed when the value of the
        RowStatus object is 'active'."
    ::= { intSrvFlowEntry 10 }

intSrvFlowFlowId OBJECT-TYPE
    SYNTAX INTEGER(0..16777215)
    ACCESS read-only
    STATUS mandatory
    DESCRIPTION
        "The flow ID that  this  sender  is  using,  if
        this  is  an IPv6 session."
    ::= { intSrvFlowEntry 11 }

intSrvFlowInterface OBJECT-TYPE
    SYNTAX InterfaceIndex
--    Rsyntax INTEGER(1..2147483647)
    ACCESS read-write
    STATUS mandatory
    DESCRIPTION
        "The ifIndex value of the  interface  on  which
        this reservation exists."
    ::= { intSrvFlowEntry 12 }

intSrvFlowIfAddr OBJECT-TYPE
    SYNTAX OCTET STRING(SIZE(4..16))
    ACCESS read-write
    STATUS mandatory
    DESCRIPTION
        "The IP Address on the ifEntry  on  which  this
        reservation  exists.  This is present primarily
        to support those interfaces which layer  multi-
        ple IP Addresses on the interface."
    ::= { intSrvFlowEntry 13 }

intSrvFlowRate OBJECT-TYPE
    SYNTAX BitRate
--    Rsyntax INTEGER(0..2147483647)
--  Units
--    bits per second
    ACCESS read-write
    STATUS mandatory
    DESCRIPTION
        "The Reserved Rate of the sender's data stream.
        If this is a Controlled Load service flow, this
        rate is derived from the Tspec  rate  parameter
        (r).   If  this  is  a Guaranteed service flow,
        this rate is derived from  the  Rspec  clearing
        rate parameter (R)."
    ::= { intSrvFlowEntry 14 }

intSrvFlowBurst OBJECT-TYPE
    SYNTAX BurstSize
--    Rsyntax INTEGER(0..2147483647)
--  Units
--    bytes
    ACCESS read-write
    STATUS mandatory
    DESCRIPTION
        "The size of the largest  burst  expected  from
        the sender at a time.
        
        If this is less than  the  sender's  advertised
        burst  size, the receiver is asking the network
        to provide flow pacing  beyond  what  would  be
        provided  under normal circumstances. Such pac-
        ing is at the network's option."
    ::= { intSrvFlowEntry 15 }

intSrvFlowWeight OBJECT-TYPE
    SYNTAX INTEGER
    ACCESS read-write
    STATUS mandatory
    DESCRIPTION
        "The weight used  to  prioritize  the  traffic.
        Note  that the interpretation of this object is
        implementation-specific,   as   implementations
        vary in their use of weighting procedures."
    ::= { intSrvFlowEntry 16 }

intSrvFlowQueue OBJECT-TYPE
    SYNTAX INTEGER
    ACCESS read-write
    STATUS mandatory
    DESCRIPTION
        "The number of the queue used by this  traffic.
        Note  that the interpretation of this object is
        implementation-specific,   as   implementations
        vary in their use of queue identifiers."
    ::= { intSrvFlowEntry 17 }

intSrvFlowMinTU OBJECT-TYPE
    SYNTAX MessageSize
--    Rsyntax INTEGER(0..2147483647)
    ACCESS read-write
    STATUS mandatory
    DESCRIPTION
        "The minimum message size for  this  flow.  The
        policing  algorithm will treat smaller messages
        as though they are this size."
    ::= { intSrvFlowEntry 18 }

intSrvFlowMaxTU OBJECT-TYPE
    SYNTAX MessageSize
--    Rsyntax INTEGER(0..2147483647)
    ACCESS read-write
    STATUS mandatory
    DESCRIPTION
        "The maximum datagram size for this  flow  that
        will conform to the traffic specification. This
        value cannot exceed the MTU of the interface."
    ::= { intSrvFlowEntry 19 }

intSrvFlowBestEffort OBJECT-TYPE
    SYNTAX Counter
    ACCESS read-only
    STATUS mandatory
    DESCRIPTION
        "The number of packets that  were  remanded  to
        best effort service."
    ::= { intSrvFlowEntry 20 }

intSrvFlowPoliced OBJECT-TYPE
    SYNTAX Counter
    ACCESS read-only
    STATUS mandatory
    DESCRIPTION
        "The number of packets policed since the incep-
        tion of the flow's service."
    ::= { intSrvFlowEntry 21 }

intSrvFlowDiscard OBJECT-TYPE
    SYNTAX TruthValue
--    Rsyntax INTEGER {
--        true(1),
--        false(2)
--        }
    ACCESS read-write
    STATUS mandatory
    DESCRIPTION
        "If 'true', the flow  is  to  incur  loss  when
        traffic is policed.  If 'false', policed traff-
        ic is treated as best effort traffic."
    DEFVAL { false }
    ::= { intSrvFlowEntry 22 }

intSrvFlowService OBJECT-TYPE
    SYNTAX QosService
--    Rsyntax INTEGER {
--        bestEffort(1),
--        guaranteedDelay(2),
--        controlledLoad(5)
--        }
    ACCESS read-only
    STATUS mandatory
    DESCRIPTION
        "The QoS service being applied to this flow."
    ::= { intSrvFlowEntry 23 }

intSrvFlowOrder OBJECT-TYPE
    SYNTAX INTEGER(0..65535)
    ACCESS read-write
    STATUS mandatory
    DESCRIPTION
        "In the event of ambiguity, the order in  which
        the  classifier  should  make  its comparisons.
        The row with intSrvFlowOrder=0 is tried  first,
        and  comparisons  proceed  in  the order of in-
        creasing value.  Non-serial implementations  of
        the classifier should emulate this behavior."
    ::= { intSrvFlowEntry 24 }

intSrvFlowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "'active' for all active  flows.   This  object
        may be used to install static classifier infor-
        mation, delete classifier information,  or  au-
        thorize such."
    ::= { intSrvFlowEntry 25 }

intSrvFlowNewIndex OBJECT-TYPE
    SYNTAX TestAndIncr
--    Rsyntax INTEGER(0..2147483647)
    ACCESS read-write
    STATUS mandatory
    DESCRIPTION
        "This  object  is  used  to  assign  values  to
        intSrvFlowNumber  as described in 'Textual Con-
        ventions  for  SNMPv2'.   The  network  manager
        reads  the  object,  and  then writes the value
        back in the SET that creates a new instance  of
        intSrvFlowEntry.   If  the  SET  fails with the
        code 'inconsistentValue', then the process must
        be  repeated; If the SET succeeds, then the ob-
        ject is incremented, and the  new  instance  is
        created according to the manager's directions."
    ::= { intSrvGenObjects 1 }

intSrvIfAttribGroup OBJECT IDENTIFIER ::= { intSrvGroups 1 }
-- OBJECT-GROUP
--  Status
--    mandatory
--  Descr
--    These objects are required  for  Systems  sup-
--    porting the Integrated Services Architecture.
--  objects
--    intSrvIfAttribAllocatedBits, intSrvIfAttribMaxAllocatedBits, 
--    intSrvIfAttribAllocatedBuffer, intSrvIfAttribFlows, 
--    intSrvIfAttribPropagationDelay, intSrvIfAttribStatus

intSrvFlowsGroup OBJECT IDENTIFIER ::= { intSrvGroups 2 }
-- OBJECT-GROUP
--  Status
--    mandatory
--  Descr
--    These objects are required  for  Systems  sup-
--    porting the Integrated Services Architecture.
--  objects
--    intSrvFlowType, intSrvFlowOwner, intSrvFlowDestAddr, 
--    intSrvFlowSenderAddr, intSrvFlowDestAddrLength, 
--    intSrvFlowSenderAddrLength, intSrvFlowProtocol, 
--    intSrvFlowDestPort, intSrvFlowPort, intSrvFlowFlowId, 
--    intSrvFlowInterface, intSrvFlowBestEffort, intSrvFlowRate, 
--    intSrvFlowBurst, intSrvFlowWeight, intSrvFlowQueue, 
--    intSrvFlowMinTU, intSrvFlowMaxTU, intSrvFlowDiscard, 
--    intSrvFlowPoliced, intSrvFlowService, intSrvFlowIfAddr, 
--    intSrvFlowOrder, intSrvFlowStatus

intSrvGenObjectsGroup OBJECT IDENTIFIER ::= { intSrvGroups 3 }
-- OBJECT-GROUP
--  Status
--    mandatory
--  Descr
--    These objects are required  for  Systems  sup-
--    porting the Integrated Services Architecture.
--  objects
--    intSrvFlowNewIndex

intSrvCompliance OBJECT IDENTIFIER ::= { intSrvCompliances 1 }
-- MODULE-COMPLIANCE
--  Status
--    mandatory
--  Descr
--    The compliance statement 
--  Module
--    >>current<<
--   MandGroup
--    intSrvIfAttribGroup
--   MandGroup
--    intSrvFlowsGroup
--   MandGroup
--    intSrvGenObjectsGroup
--   ObjVar
--    intSrvFlowType
--   ObjVar
--    intSrvFlowOwner
--   ObjVar
--    intSrvFlowDestAddr
--   ObjVar
--    intSrvFlowSenderAddr
--   ObjVar
--    intSrvFlowDestAddrLength
--   ObjVar
--    intSrvFlowSenderAddrLength
--   ObjVar
--    intSrvFlowProtocol
--   ObjVar
--    intSrvFlowDestPort
--   ObjVar
--    intSrvFlowPort
--   ObjVar
--    intSrvFlowFlowId
--   ObjVar
--    intSrvFlowInterface
--   ObjVar
--    intSrvFlowRate
--   ObjVar
--    intSrvFlowBurst
--   ObjVar
--    intSrvFlowWeight
--   ObjVar
--    intSrvFlowQueue
--   ObjVar
--    intSrvFlowMinTU
--   ObjVar
--    intSrvFlowMaxTU
--   ObjVar
--    intSrvFlowStatus


END
