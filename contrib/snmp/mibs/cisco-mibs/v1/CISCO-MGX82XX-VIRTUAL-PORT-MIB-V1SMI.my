-- MIB file created 24-Oct-2002 19:29:34, by
--   SMICng version 2.2.11-beta(PRO)(Solaris), January 20, 2001. Enterprise key cisco.com

CISCO-MGX82XX-VIRTUAL-PORT-MIB DEFINITIONS ::= BEGIN

-- From file: "CISCO-MGX82XX-VIRTUAL-PORT-MIB.my"
-- Compile options "4 7 F H N W 03 06 0B 0G 0N 0T"

IMPORTS
    virtualInterface
            FROM BASIS-MIB
    ciscoWan
            FROM CISCOWAN-SMI
    Counter
            FROM RFC1155-SMI
    OBJECT-TYPE
            FROM RFC-1212;

ciscoMgx82xxVirtualPortMIB OBJECT IDENTIFIER ::= { ciscoWan 38 }
-- MODULE-IDENTITY
--  LastUpdated
--    200208300000Z
--  OrgName
--    Cisco Systems, Inc.
--  ContactInfo
--           Cisco Systems
--            Customer Service
--    
--    Postal: 170 W Tasman Drive
--            San Jose, CA  95134
--            USA
--    
--            Tel: +1 800 553-NETS
--    
--    E-mail: cs-wanatm@cisco.com
--  Descr
--    The MIB module for configuration ond reporting
--    statistics of virtual ports in PXM1 Service module
--    in MGX82xx series.
--  RevDate
--    200208300000Z
--  RevDescr
--    Initial version of the MIB.
--    
--    The content of this MIB was originally available
--    in CISCO-WAN-AXIPOP-MIB defined using SMIv1.
--    The applicable objects from CISCO-WAN-AXIPOP-MIB
--    are defined using SMIv2 in this MIB. Also the
--    descriptions of some of the objects have been 
--    modified.

virtualInterfaceCnf OBJECT IDENTIFIER ::= { virtualInterface 1 }
virtualInterfaceCnt OBJECT IDENTIFIER ::= { virtualInterface 2 }
virtualInterfaceQbinCnf OBJECT IDENTIFIER ::= { virtualInterface 3 }
virtualInterfaceQbinCnt OBJECT IDENTIFIER ::= { virtualInterface 4 }
cmvPortMIBConformance OBJECT IDENTIFIER ::= { ciscoMgx82xxVirtualPortMIB 2 }
cmvPortMIBGroups OBJECT IDENTIFIER ::= { cmvPortMIBConformance 1 }
cmvPortMIBCompliances OBJECT IDENTIFIER ::= { cmvPortMIBConformance 2 }

vrtlIntrConfigTable OBJECT-TYPE
    SYNTAX SEQUENCE OF VrtlIntrConfigEntry
    ACCESS not-accessible
    STATUS mandatory
    DESCRIPTION
        "Virtual Interface Configuration Table."
    ::= { virtualInterfaceCnf 1 }

vrtlIntrConfigEntry OBJECT-TYPE
    SYNTAX VrtlIntrConfigEntry
    ACCESS not-accessible
    STATUS mandatory
    DESCRIPTION
        "An entry in the Virtual Interface configuration Table."
    INDEX { configVrtlIntrNum }
    ::= { vrtlIntrConfigTable 1 }

VrtlIntrConfigEntry ::= SEQUENCE {
    configVrtlIntrNum INTEGER,
    vrtlIntrPortNum INTEGER,
    vrtlIntrState INTEGER,
    vrtlIntrMaxQueMem INTEGER,
    vrtlIntrMinCellRate INTEGER,
    vrtlIntrMaxCellRate INTEGER,
    vrtlIntrCurrConfigPaths INTEGER
    }

configVrtlIntrNum OBJECT-TYPE
    SYNTAX INTEGER(1..32)
    ACCESS read-only
    STATUS mandatory
    DESCRIPTION
        "Virtual Interface Number. There are totaly.
        32 Virtual Interfaces on the card (egress)."
    ::= { vrtlIntrConfigEntry 1 }

vrtlIntrPortNum OBJECT-TYPE
    SYNTAX INTEGER(0..4)
    ACCESS read-write
    STATUS mandatory
    DESCRIPTION
        "Port number which will be connected to the
        Virtual Interface. Value zero meens that this
        virtual interface is not connected to any port."
    ::= { vrtlIntrConfigEntry 2 }

vrtlIntrState OBJECT-TYPE
    SYNTAX INTEGER {
        down(1),
        up(2)
        }
    ACCESS read-write
    STATUS mandatory
    DESCRIPTION
        "Virtual Interface State."
    ::= { vrtlIntrConfigEntry 3 }

vrtlIntrMaxQueMem OBJECT-TYPE
    SYNTAX INTEGER(1..8)
    ACCESS read-write
    STATUS mandatory
    DESCRIPTION
        "Virtual Interface's Max queue memory.
        1 = 4Kcells
        2 = 8Kcells
        3 = 16Kcells
        4 = 32Kcells
        5 = 64Kcells
        6 = 128Kcells
        7 = 256Kcells
        8 = 512Kcells."
    ::= { vrtlIntrConfigEntry 4 }

vrtlIntrMinCellRate OBJECT-TYPE
    SYNTAX INTEGER(103384..353208)
    ACCESS read-write
    STATUS mandatory
    DESCRIPTION
        "Virtual Interface's minimum cell rate.
        The default value: 
        for OC12 port is 1412832 cells/sec 
        for OC3  port is  353208 cells/sec 
        for T3   port is   96000 cells/sec
        for E3   port is   80000 cells/sec"
    ::= { vrtlIntrConfigEntry 5 }

vrtlIntrMaxCellRate OBJECT-TYPE
    SYNTAX INTEGER(103384..353208)
    ACCESS read-write
    STATUS mandatory
    DESCRIPTION
        "Virtual Interface's maximum cell rate.
         The default value:
        for OC12 port is 1412832 cells/sec 
        for OC3  port is  353208 cells/sec 
        for T3   port is   96000 cells/sec
        for E3   port is   80000 cells/sec"
    ::= { vrtlIntrConfigEntry 6 }

vrtlIntrCurrConfigPaths OBJECT-TYPE
    SYNTAX INTEGER
    ACCESS read-only
    STATUS mandatory
    DESCRIPTION
        "This is not a configurable parameter.
               This gives the count of paths currently configured on this
               virtual interface."
    ::= { vrtlIntrConfigEntry 7 }

vrtlIntrCounterTable OBJECT-TYPE
    SYNTAX SEQUENCE OF VrtlIntrCounterEntry
    ACCESS not-accessible
    STATUS mandatory
    DESCRIPTION
        "Virtual Interface Counter32s Table."
    ::= { virtualInterfaceCnt 1 }

vrtlIntrCounterEntry OBJECT-TYPE
    SYNTAX VrtlIntrCounterEntry
    ACCESS not-accessible
    STATUS mandatory
    DESCRIPTION
        "An entry in the Virtual Interface Counter32 Table."
    INDEX { countVrtlIntrNum }
    ::= { vrtlIntrCounterTable 1 }

VrtlIntrCounterEntry ::= SEQUENCE {
    countVrtlIntrNum INTEGER,
    vrtlIntrTotalCellCnt Counter,
    vrtlIntrTotalQbinCellCnt Counter,
    vrtlIntrRxdValidOAMCellCnt Counter,
    vrtlIntrRxdRmCellCnt Counter,
    vrtlIntrRxdClpUntaggedCellCnt Counter,
    vrtlIntrRxdClpTaggedCellCnt Counter,
    vrtlIntrRxdClpUntaggedDiscardedCellCnt Counter,
    vrtlIntrRxdClpTaggedDiscardedCellCnt Counter,
    vrtlIntrXmtdOAMCellCnt Counter,
    vrtlIntrXmtdRmCellCnt Counter,
    vrtlIntrXmtdClpUntaggedCellCnt Counter,
    vrtlIntrXmtdClpTaggedCellCnt Counter
    }

countVrtlIntrNum OBJECT-TYPE
    SYNTAX INTEGER(1..32)
    ACCESS read-only
    STATUS mandatory
    DESCRIPTION
        "Virtual Interface Number."
    ::= { vrtlIntrCounterEntry 1 }

vrtlIntrTotalCellCnt OBJECT-TYPE
    SYNTAX Counter
    ACCESS read-only
    STATUS mandatory
    DESCRIPTION
        " 
        Total number of cells (VC plus Qbin) that belong to 
        this Virtual Interface."
    ::= { vrtlIntrCounterEntry 2 }

vrtlIntrTotalQbinCellCnt OBJECT-TYPE
    SYNTAX Counter
    ACCESS read-only
    STATUS mandatory
    DESCRIPTION
        "Total number of cells in the Qbin belonging 
        to this Virtual Interface."
    ::= { vrtlIntrCounterEntry 3 }

vrtlIntrRxdValidOAMCellCnt OBJECT-TYPE
    SYNTAX Counter
    ACCESS read-only
    STATUS mandatory
    DESCRIPTION
        "Total number of OAM cell received."
    ::= { vrtlIntrCounterEntry 4 }

vrtlIntrRxdRmCellCnt OBJECT-TYPE
    SYNTAX Counter
    ACCESS read-only
    STATUS mandatory
    DESCRIPTION
        "Total number of RM cells Received."
    ::= { vrtlIntrCounterEntry 5 }

vrtlIntrRxdClpUntaggedCellCnt OBJECT-TYPE
    SYNTAX Counter
    ACCESS read-only
    STATUS mandatory
    DESCRIPTION
        "Total number of CLP-0 cells Received."
    ::= { vrtlIntrCounterEntry 6 }

vrtlIntrRxdClpTaggedCellCnt OBJECT-TYPE
    SYNTAX Counter
    ACCESS read-only
    STATUS mandatory
    DESCRIPTION
        "Total number of CLP-1 cells Received."
    ::= { vrtlIntrCounterEntry 7 }

vrtlIntrRxdClpUntaggedDiscardedCellCnt OBJECT-TYPE
    SYNTAX Counter
    ACCESS read-only
    STATUS mandatory
    DESCRIPTION
        "Total number of CLP-0 cells discarded at Ingress."
    ::= { vrtlIntrCounterEntry 8 }

vrtlIntrRxdClpTaggedDiscardedCellCnt OBJECT-TYPE
    SYNTAX Counter
    ACCESS read-only
    STATUS mandatory
    DESCRIPTION
        "Total number of CLP-1 cells discarded at Ingress."
    ::= { vrtlIntrCounterEntry 9 }

vrtlIntrXmtdOAMCellCnt OBJECT-TYPE
    SYNTAX Counter
    ACCESS read-only
    STATUS mandatory
    DESCRIPTION
        "Total number of OAM cells transmitted."
    ::= { vrtlIntrCounterEntry 10 }

vrtlIntrXmtdRmCellCnt OBJECT-TYPE
    SYNTAX Counter
    ACCESS read-only
    STATUS mandatory
    DESCRIPTION
        "Total number of RM(Resource Monitoring)
                      cells transmitted."
    ::= { vrtlIntrCounterEntry 11 }

vrtlIntrXmtdClpUntaggedCellCnt OBJECT-TYPE
    SYNTAX Counter
    ACCESS read-only
    STATUS mandatory
    DESCRIPTION
        "Total number of CLP-0 cells transmitted."
    ::= { vrtlIntrCounterEntry 12 }

vrtlIntrXmtdClpTaggedCellCnt OBJECT-TYPE
    SYNTAX Counter
    ACCESS read-only
    STATUS mandatory
    DESCRIPTION
        "Total number of CLP-1 cells transmitted."
    ::= { vrtlIntrCounterEntry 13 }

vrtlIntrQbinConfigTable OBJECT-TYPE
    SYNTAX SEQUENCE OF VrtlIntrQbinConfigEntry
    ACCESS not-accessible
    STATUS mandatory
    DESCRIPTION
        "Virtual Interface QBin Configuration Table."
    ::= { virtualInterfaceQbinCnf 1 }

vrtlIntrQbinConfigEntry OBJECT-TYPE
    SYNTAX VrtlIntrQbinConfigEntry
    ACCESS not-accessible
    STATUS mandatory
    DESCRIPTION
        "An entry in the Virtual Interface Qbin Config Table."
    INDEX { queConfigVrtlIntrNum, queConfigVrtlIntrQbinNum }
    ::= { vrtlIntrQbinConfigTable 1 }

VrtlIntrQbinConfigEntry ::= SEQUENCE {
    queConfigVrtlIntrNum INTEGER,
    queConfigVrtlIntrQbinNum INTEGER,
    vrtlIntrQbinState INTEGER,
    vrtlIntrQbinPri INTEGER,
    vrtlIntrQbinRate INTEGER,
    vrtlIntrQbinDiscardSelection INTEGER,
    vrtlIntrQbinMaxThreshold INTEGER,
    vrtlIntrQbinClpHiThreshold INTEGER,
    vrtlIntrQbinClpLoThreshold INTEGER,
    vrtlIntrQbinFrameDiscardThreshold INTEGER,
    vrtlIntrQbinEfciThreshold INTEGER
    }

queConfigVrtlIntrNum OBJECT-TYPE
    SYNTAX INTEGER(1..32)
    ACCESS read-only
    STATUS mandatory
    DESCRIPTION
        " Virtual Interface Number."
    ::= { vrtlIntrQbinConfigEntry 1 }

queConfigVrtlIntrQbinNum OBJECT-TYPE
    SYNTAX INTEGER(1..16)
    ACCESS read-only
    STATUS mandatory
    DESCRIPTION
        " Virtual Interface Qbin Number. There are totaly 16  Qbin
          per Virtual Interface."
    ::= { vrtlIntrQbinConfigEntry 2 }

vrtlIntrQbinState OBJECT-TYPE
    SYNTAX INTEGER {
        down(1),
        up(2)
        }
    ACCESS read-write
    STATUS mandatory
    DESCRIPTION
        "Virtual Interface QBIN state."
    ::= { vrtlIntrQbinConfigEntry 3 }

vrtlIntrQbinPri OBJECT-TYPE
    SYNTAX INTEGER(1..16)
    ACCESS read-write
    STATUS mandatory
    DESCRIPTION
        "This indicates the priority of the QBIN service 
          within the Virtual Interface."
    ::= { vrtlIntrQbinConfigEntry 4 }

vrtlIntrQbinRate OBJECT-TYPE
    SYNTAX INTEGER(0..353208)
    ACCESS read-write
    STATUS mandatory
    DESCRIPTION
        "The rate at which cells in the QBIN are serviced.
          Max Cell rate for OC3 interface is 353208 cell/sec."
    ::= { vrtlIntrQbinConfigEntry 5 }

vrtlIntrQbinDiscardSelection OBJECT-TYPE
    SYNTAX INTEGER {
        clpHysteresis(1),
        frameDiscard(3)
        }
    ACCESS read-write
    STATUS mandatory
    DESCRIPTION
        " Virtual Interface QBin Congestion control option."
    DEFVAL { clpHysteresis }
    ::= { vrtlIntrQbinConfigEntry 6 }

vrtlIntrQbinMaxThreshold OBJECT-TYPE
    SYNTAX INTEGER(0..512000)
    ACCESS read-write
    STATUS mandatory
    DESCRIPTION
        "Max cells that can be queued in the QBIN.
         The Get value will be different from the Set 
         value because of FW internal round up."
    ::= { vrtlIntrQbinConfigEntry 7 }

vrtlIntrQbinClpHiThreshold OBJECT-TYPE
    SYNTAX INTEGER(0..512000)
    ACCESS read-write
    STATUS mandatory
    DESCRIPTION
        "The threshold above which the tagged cells 
         will be dropped.
         The Get value will be different from the Set 
         value because of FW internal round up."
    ::= { vrtlIntrQbinConfigEntry 8 }

vrtlIntrQbinClpLoThreshold OBJECT-TYPE
    SYNTAX INTEGER(0..512000)
    ACCESS read-write
    STATUS mandatory
    DESCRIPTION
        "Valid only if congestion control is set to 
         CLP hysterises. The threshold upto which the 
         dropping of the tagged cells should continue once 
         it has crossed CLP HI threshold.
         The Get value will be different from the Set 
         value because of FW internal round up."
    ::= { vrtlIntrQbinConfigEntry 9 }

vrtlIntrQbinFrameDiscardThreshold OBJECT-TYPE
    SYNTAX INTEGER(0..512000)
    ACCESS read-write
    STATUS mandatory
    DESCRIPTION
        "Valid only if congestion control is set to 
         Frame Discard. It is the threshold after which 
         the QE will start discarding the entire frame 
         if one or more cells of the frame is discarded..
         The Get value will be different from the Set 
         value because of FW internal round up."
    ::= { vrtlIntrQbinConfigEntry 10 }

vrtlIntrQbinEfciThreshold OBJECT-TYPE
    SYNTAX INTEGER(0..512000)
    ACCESS read-write
    STATUS mandatory
    DESCRIPTION
        "The threshold above which the EFCI bits of 
         the cell is set.
         The Get value will be different from the Set 
         value because of FW internal round up."
    ::= { vrtlIntrQbinConfigEntry 11 }

vrtlIntrQbinCounterTable OBJECT-TYPE
    SYNTAX SEQUENCE OF VrtlIntrQbinCounterEntry
    ACCESS not-accessible
    STATUS mandatory
    DESCRIPTION
        "Virtual Interface QBin Counter Table."
    ::= { virtualInterfaceQbinCnt 1 }

vrtlIntrQbinCounterEntry OBJECT-TYPE
    SYNTAX VrtlIntrQbinCounterEntry
    ACCESS not-accessible
    STATUS mandatory
    DESCRIPTION
        "An entry in the Virtual Interface Qbin Counter Table.
                      Each entry contains information on the statistics supported
                      for an interface."
    INDEX { queConuterVrtlIntrNum, queCounterVrtlIntrQbinNum }
    ::= { vrtlIntrQbinCounterTable 1 }

VrtlIntrQbinCounterEntry ::= SEQUENCE {
    queConuterVrtlIntrNum INTEGER,
    queCounterVrtlIntrQbinNum INTEGER,
    vrtlIntrQbinCurrentCellCnt Counter,
    vrtlIntrQbinRxdCellCnt Counter,
    vrtlIntrQbinTxdCellCnt Counter,
    vrtlIntrQbinDiscardedCellCnt Counter
    }

queConuterVrtlIntrNum OBJECT-TYPE
    SYNTAX INTEGER(1..32)
    ACCESS read-only
    STATUS mandatory
    DESCRIPTION
        " Virtual Interface Number."
    ::= { vrtlIntrQbinCounterEntry 1 }

queCounterVrtlIntrQbinNum OBJECT-TYPE
    SYNTAX INTEGER(1..16)
    ACCESS read-only
    STATUS mandatory
    DESCRIPTION
        "Virtual Interface Qbin Number. There are totaly 16  Qbin
          per Virtual Interface."
    ::= { vrtlIntrQbinCounterEntry 2 }

vrtlIntrQbinCurrentCellCnt OBJECT-TYPE
    SYNTAX Counter
    ACCESS read-only
    STATUS mandatory
    DESCRIPTION
        " Total number of cells currently in the Qbin."
    ::= { vrtlIntrQbinCounterEntry 3 }

vrtlIntrQbinRxdCellCnt OBJECT-TYPE
    SYNTAX Counter
    ACCESS read-only
    STATUS mandatory
    DESCRIPTION
        " Total number of cells arrived to the QBIN."
    ::= { vrtlIntrQbinCounterEntry 4 }

vrtlIntrQbinTxdCellCnt OBJECT-TYPE
    SYNTAX Counter
    ACCESS read-only
    STATUS mandatory
    DESCRIPTION
        "Total number of cells departured from QBIN."
    ::= { vrtlIntrQbinCounterEntry 5 }

vrtlIntrQbinDiscardedCellCnt OBJECT-TYPE
    SYNTAX Counter
    ACCESS read-only
    STATUS mandatory
    DESCRIPTION
        "Total number of arrivals to QBIN which were discarded."
    ::= { vrtlIntrQbinCounterEntry 6 }

cmvPortConfGroup OBJECT IDENTIFIER ::= { cmvPortMIBGroups 1 }
-- OBJECT-GROUP
--  Status
--    mandatory
--  Descr
--    The collection of objects which are used for
--    configuring Virtual Ports in PXM1 service module.
--  objects
--    configVrtlIntrNum, vrtlIntrPortNum, vrtlIntrState, 
--    vrtlIntrMaxQueMem, vrtlIntrMinCellRate, vrtlIntrMaxCellRate, 
--    vrtlIntrCurrConfigPaths

cmvPortStatsGroup OBJECT IDENTIFIER ::= { cmvPortMIBGroups 2 }
-- OBJECT-GROUP
--  Status
--    mandatory
--  Descr
--    The collection of objects related to
--    statistics for Virtual Ports in PXM1 service module.
--  objects
--    countVrtlIntrNum, vrtlIntrTotalCellCnt, 
--    vrtlIntrTotalQbinCellCnt, vrtlIntrRxdValidOAMCellCnt, 
--    vrtlIntrRxdRmCellCnt, vrtlIntrRxdClpUntaggedCellCnt, 
--    vrtlIntrRxdClpTaggedCellCnt, 
--    vrtlIntrRxdClpUntaggedDiscardedCellCnt, 
--    vrtlIntrRxdClpTaggedDiscardedCellCnt, vrtlIntrXmtdOAMCellCnt, 
--    vrtlIntrXmtdRmCellCnt, vrtlIntrXmtdClpUntaggedCellCnt, 
--    vrtlIntrXmtdClpTaggedCellCnt

cmvPortQbinConfGroup OBJECT IDENTIFIER ::= { cmvPortMIBGroups 3 }
-- OBJECT-GROUP
--  Status
--    mandatory
--  Descr
--    The collection of objects related to
--    configuration of Qbin related things in PXM1
--    service module.
--  objects
--    queConfigVrtlIntrNum, queConfigVrtlIntrQbinNum, 
--    vrtlIntrQbinState, vrtlIntrQbinPri, vrtlIntrQbinRate, 
--    vrtlIntrQbinDiscardSelection, vrtlIntrQbinMaxThreshold, 
--    vrtlIntrQbinClpHiThreshold, vrtlIntrQbinClpLoThreshold, 
--    vrtlIntrQbinFrameDiscardThreshold, vrtlIntrQbinEfciThreshold

cmvPortQbinStatsGroup OBJECT IDENTIFIER ::= { cmvPortMIBGroups 4 }
-- OBJECT-GROUP
--  Status
--    mandatory
--  Descr
--    The collection of objects related to
--    statistics for Qbin related things in PXM1
--    service module.
--  objects
--    queConuterVrtlIntrNum, queCounterVrtlIntrQbinNum, 
--    vrtlIntrQbinCurrentCellCnt, vrtlIntrQbinRxdCellCnt, 
--    vrtlIntrQbinTxdCellCnt, vrtlIntrQbinDiscardedCellCnt

cmvPortCompliance OBJECT IDENTIFIER ::= { cmvPortMIBCompliances 1 }
-- MODULE-COMPLIANCE
--  Status
--    mandatory
--  Descr
--    The compliance statement for objects related
--    to SRM MIB.
--  Module
--    >>current<<
--   MandGroup
--    cmvPortConfGroup
--   MandGroup
--    cmvPortStatsGroup
--   MandGroup
--    cmvPortQbinConfGroup
--   MandGroup
--    cmvPortQbinStatsGroup


END
