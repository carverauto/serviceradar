-- MIB file created 08-Apr-2013 01:00:23, by
--   SMICng version 2.2.11-beta(PRO)(Solaris), January 20, 2001. Enterprise key cisco.com

DSG-IF-MIB DEFINITIONS ::= BEGIN

-- From file: "DSG-IF-MIB.my"
-- Compile options "4 7 F H N W 03 06 0B 0G 0N 0T"

IMPORTS
    TruthValue, MacAddress, RowStatus
            FROM SNMPv2-TC-v1
    InetAddressType, InetAddress, InetAddressPrefixLength, 
    InetPortNumber
            FROM INET-ADDRESS-MIB
    SnmpAdminString
            FROM SNMP-FRAMEWORK-MIB
    InterfaceIndex, ifIndex
            FROM IF-MIB
    clabProjDocsis
            FROM CLAB-DEF-MIB
    Gauge
            FROM RFC1155-SMI
    OBJECT-TYPE
            FROM RFC-1212;

dsgIfMIB OBJECT IDENTIFIER ::= { clabProjDocsis 3 }
-- MODULE-IDENTITY
--  LastUpdated
--    200903230000Z
--  OrgName
--    Cable Television Laboratories, Inc
--  ContactInfo
--    Postal: Cable Television Laboratories, Inc.
--    858 Coal Creek Circle
--    Louisville, Colorado 80027
--    U.S.A.
--    Phone : +1 303-661-9100
--    Fax : +1 303-661-9199
--    E-mail:
--  Descr
--    This is the MIB Module for the DOCSIS Set-top Gateway
--    (DSG). The DSG provides a one-way IP datagram transport
--    for Out-Of-Band (OOB) messaging to cable set-top clients.
--    The one-way IP datagram transport is called a DSG Tunnel.
--    A DSG Tunnel carrying either a broadcast, unicast or
--    multicast IP datagram stream originating at the DOCSIS
--    Set-top Gateway and carrying Out-Of-Band messages intended
--    for set-top clients. It is carried over one or more
--    downstream DOCSIS channels.
--    Multiple DSG tunnels may exist on a single downstream
--    DOCSIS channel.
--  RevDate
--    200903230000Z
--  RevDescr
--    Initial revision, published as part of DOCSIS Set-top
--    Gateway Specification.

dsgIfMIBNotifications OBJECT IDENTIFIER ::= { dsgIfMIB 0 }
dsgIfMIBObjects OBJECT IDENTIFIER ::= { dsgIfMIB 1 }
dsgIfMIBConformance OBJECT IDENTIFIER ::= { dsgIfMIB 2 }
dsgIfClassifier OBJECT IDENTIFIER ::= { dsgIfMIBObjects 1 }
dsgIfTunnel     OBJECT IDENTIFIER ::= { dsgIfMIBObjects 2 }
dsgIfTunnelGrpToChannel OBJECT IDENTIFIER ::= { dsgIfMIBObjects 3 }
dsgIfDownstreamChannel OBJECT IDENTIFIER ::= { dsgIfMIBObjects 4 }
dsgIfDCD        OBJECT IDENTIFIER ::= { dsgIfMIBObjects 5 }
dsgIfConformance OBJECT IDENTIFIER ::= { dsgIfMIB 4 }
dsgIfGroups     OBJECT IDENTIFIER ::= { dsgIfConformance 1 }
dsgIfCompliances OBJECT IDENTIFIER ::= { dsgIfConformance 2 }

dsgIfClassifierTable OBJECT-TYPE
    SYNTAX SEQUENCE OF DsgIfClassifierEntry
    ACCESS not-accessible
    STATUS mandatory
    DESCRIPTION
        "The Classifier Table contains attributes use to classify
        inbound packets into the tunnel and classifiers for the DSG
        clients, encoding in the DCD messages on the downstream
        channels to which the classifiers apply."
    ::= { dsgIfClassifier 1 }

dsgIfClassifierEntry OBJECT-TYPE
    SYNTAX DsgIfClassifierEntry
    ACCESS not-accessible
    STATUS mandatory
    DESCRIPTION
        "An entry in the Classifier Table. Rows are created
        by an SNMP SET request setting the value of
        dsgIfClassRowStatus to 'createAndGo'. Each entry is created
        for a tunnel, index by dsgTunnelIndex.
        Rows are deleted by an SNMP SET request setting the value
        of dsgIfClassRowStatus to 'destroy'."
    INDEX { dsgIfTunnelIndex, dsgIfClassId }
    ::= { dsgIfClassifierTable 1 }

DsgIfClassifierEntry ::= SEQUENCE {
    dsgIfClassId Gauge,
    dsgIfClassPriority Gauge,
    dsgIfClassSrcIpAddrType InetAddressType,
    dsgIfClassSrcIpAddr InetAddress,
    dsgIfClassSrcIpPrefixLength InetAddressPrefixLength,
    dsgIfClassDestIpAddressType InetAddressType,
    dsgIfClassDestIpAddress InetAddress,
    dsgIfClassDestPortStart InetPortNumber,
    dsgIfClassDestPortEnd InetPortNumber,
    dsgIfClassRowStatus RowStatus,
    dsgIfClassIncludeInDCD TruthValue
    }

dsgIfClassId OBJECT-TYPE
    SYNTAX Gauge(1..65535)
    ACCESS not-accessible
    STATUS mandatory
    DESCRIPTION
        "The index that provides a unique classifier (in a DSG
        Agent). This value corresponds to the Classifier ID TLV
        in the DCD message."
    ::= { dsgIfClassifierEntry 1 }

dsgIfClassPriority OBJECT-TYPE
    SYNTAX Gauge(0..255)
    ACCESS read-write
    STATUS mandatory
    DESCRIPTION
        "The priority of this classifier.
        Default value 0 indicates lowest priority."
    DEFVAL { 0 }
    ::= { dsgIfClassifierEntry 2 }

dsgIfClassSrcIpAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "The type of internet address of dsgIfClassSrcIpAddress."
    DEFVAL { ipv4 }
    ::= { dsgIfClassifierEntry 3 }

dsgIfClassSrcIpAddr OBJECT-TYPE
    SYNTAX InetAddress
--    Rsyntax OCTET STRING(SIZE(0..255))
    ACCESS read-write
    STATUS mandatory
    DESCRIPTION
        "The source IP address to be matched for this classifier.
        A value 0 for this object indicates a match of any IP
        address. A value that contains non-zero bits
        outside the range indicated by dsgIfClassSrcIpPrefixLength
        is invalid and should be rejected."
    DEFVAL { ''H }
    ::= { dsgIfClassifierEntry 4 }

dsgIfClassSrcIpPrefixLength OBJECT-TYPE
    SYNTAX InetAddressPrefixLength
--    Rsyntax Gauge
    ACCESS read-write
    STATUS mandatory
    DESCRIPTION
        "The length of the CIDR Prefix carried in
        dsgIfClassSrcIpAddr. In IPv4 addresses, a length of 32 indicates
        a match of a single host address, and a length between
        0 and 32 indicates the use of a CIDR Prefix. A length of
        0 is not allowed. This object is irrelevant and not used
        when dsgIfClassSrcIpAddr value is 0."
    DEFVAL { 32 }
    ::= { dsgIfClassifierEntry 5 }

dsgIfClassDestIpAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "The type of internet address of dsgIfClassDestIpAddress."
    DEFVAL { ipv4 }
    ::= { dsgIfClassifierEntry 6 }

dsgIfClassDestIpAddress OBJECT-TYPE
    SYNTAX InetAddress
--    Rsyntax OCTET STRING(SIZE(0..255))
    ACCESS read-write
    STATUS mandatory
    DESCRIPTION
        "The destination IP address to be matched for this
        classifier."
    DEFVAL { ''H }
    ::= { dsgIfClassifierEntry 7 }

dsgIfClassDestPortStart OBJECT-TYPE
    SYNTAX InetPortNumber
--    Rsyntax Gauge(0..65535)
    ACCESS read-write
    STATUS mandatory
    DESCRIPTION
        "This is the inclusive lower bound of the transport-layer
        source port range that is to be matched."
    DEFVAL { 0 }
    ::= { dsgIfClassifierEntry 8 }

dsgIfClassDestPortEnd OBJECT-TYPE
    SYNTAX InetPortNumber
--    Rsyntax Gauge(0..65535)
    ACCESS read-write
    STATUS mandatory
    DESCRIPTION
        "This is the inclusive higher bound of the transport-layer
        source port range that is to be matched."
    DEFVAL { 65535 }
    ::= { dsgIfClassifierEntry 9 }

dsgIfClassRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of the row. A value of active(1) indicates
        that this classifier is applied to this tunnel.
        A value of notInService(2) indicates that matching of
        the packets are ignored and this classifier parameters
        will not be included in the DCD message."
    ::= { dsgIfClassifierEntry 10 }

dsgIfClassIncludeInDCD OBJECT-TYPE
    SYNTAX TruthValue
--    Rsyntax INTEGER {
--        true(1),
--        false(2)
--        }
    ACCESS read-write
    STATUS mandatory
    DESCRIPTION
        "Indicates whether or not this DSG Classifier will
        be sent in DCD messages for use as a Layer-3 and
        Layer-4 packet filter by the DSG eCM."
    DEFVAL { false }
    ::= { dsgIfClassifierEntry 11 }

dsgIfTunnelTable OBJECT-TYPE
    SYNTAX SEQUENCE OF DsgIfTunnelEntry
    ACCESS not-accessible
    STATUS mandatory
    DESCRIPTION
        "The DSG Tunnel Table contains group(s) of tunnel(s).
        Each tunnel is associated to the destination MAC address."
    ::= { dsgIfTunnel 1 }

dsgIfTunnelEntry OBJECT-TYPE
    SYNTAX DsgIfTunnelEntry
    ACCESS not-accessible
    STATUS mandatory
    DESCRIPTION
        "An entry in the DSG Tunnel Table. Rows are created by
        an SNMP SET request setting the value of
        dsgIfTunnelRowStatus to 'createAndGo'.
        Each entry associated to a tunnel. A dsgIfTunnelGroupIndex
        represents a group of tunnels that could be associated to
        one or more downstream. Each dsgIfTunnelIndex represents
        a tunnel.
        Rows are deleted by an SNMP SET request setting the
        value of dsgIfTunnelRowStatus to 'destroy'."
    INDEX { dsgIfTunnelIndex }
    ::= { dsgIfTunnelTable 1 }

DsgIfTunnelEntry ::= SEQUENCE {
    dsgIfTunnelIndex Gauge,
    dsgIfTunnelGroupIndex Gauge,
    dsgIfTunnelClientIdListIndex Gauge,
    dsgIfTunnelMacAddress MacAddress,
    dsgIfTunnelServiceClassName SnmpAdminString,
    dsgIfTunnelRowStatus RowStatus
    }

dsgIfTunnelIndex OBJECT-TYPE
    SYNTAX Gauge
    ACCESS not-accessible
    STATUS mandatory
    DESCRIPTION
        "The index into the DSG Tunnel table that represent
        a tunnel."
    ::= { dsgIfTunnelEntry 1 }

dsgIfTunnelGroupIndex OBJECT-TYPE
    SYNTAX Gauge
    ACCESS read-write
    STATUS mandatory
    DESCRIPTION
        "This index represents a group of tunnels that could be
        associated to one or more downstream which mapped
        to dsgIfTunnelGrpIndex."
    ::= { dsgIfTunnelEntry 2 }

dsgIfTunnelClientIdListIndex OBJECT-TYPE
    SYNTAX Gauge
    ACCESS read-write
    STATUS mandatory
    DESCRIPTION
        "This index represents a group of client id(s)
        which mapped to dsgIfClientIdListIndex."
    ::= { dsgIfTunnelEntry 3 }

dsgIfTunnelMacAddress OBJECT-TYPE
    SYNTAX MacAddress
--    Rsyntax OCTET STRING(SIZE(6))
    ACCESS read-write
    STATUS mandatory
    DESCRIPTION
        "The DSG tunnel destination MAC address."
    DEFVAL { '000000000000'H }
    ::= { dsgIfTunnelEntry 4 }

dsgIfTunnelServiceClassName OBJECT-TYPE
    SYNTAX SnmpAdminString
--    Rsyntax OCTET STRING(SIZE(0..255))
    ACCESS read-write
    STATUS mandatory
    DESCRIPTION
        "The Service Class Name that associated to the
        docsQosServiceClassName(in DOCS-QOS-MIB). Creation of a
        Service Class MUST be configured through the
        docsQosServiceClassTable. Only partial of the
        docsQosServiceClassTable objects are applicable to the
        DSG service class thus some are ignored.
        If the referenced parameter is not present in the
        corresponding DOCSIS QOS Parameter Set, the default
        value of this object is a zero length string."
    REFERENCE
        "SP-RFIv1.1-I10-030730, Appendix C.2.2.3.4"
    ::= { dsgIfTunnelEntry 5 }

dsgIfTunnelRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of the row. A value of notInService(2)
        indicates that this tunnel is disabled and no OOB traffic
        will be forwarded to DSG clients and this tunnel parameters
        will not be included in the DCD message."
    ::= { dsgIfTunnelEntry 6 }

dsgIfTunnelGrpToChannelTable OBJECT-TYPE
    SYNTAX SEQUENCE OF DsgIfTunnelGrpToChannelEntry
    ACCESS not-accessible
    STATUS mandatory
    DESCRIPTION
        "The DSG Tunnel Group to Channel Table associates a group
        of tunnels to one or more downstream channel."
    ::= { dsgIfTunnelGrpToChannel 1 }

dsgIfTunnelGrpToChannelEntry OBJECT-TYPE
    SYNTAX DsgIfTunnelGrpToChannelEntry
    ACCESS not-accessible
    STATUS mandatory
    DESCRIPTION
        "An entry in the DSG Tunnel Table. Rows are created by
        an SNMP SET request setting the value of
        dsgIfTunnelGrpRowStatus to 'createAndGo'.
        Rows are deleted by an SNMP SET request setting the
        value of dsgIfTunnelRowStatus to 'destroy'."
    INDEX { dsgIfTunnelGrpIndex, dsgIfTunnelGrpChannelIndex }
    ::= { dsgIfTunnelGrpToChannelTable 1 }

DsgIfTunnelGrpToChannelEntry ::= SEQUENCE {
    dsgIfTunnelGrpIndex Gauge,
    dsgIfTunnelGrpChannelIndex Gauge,
    dsgIfTunnelGrpDsIfIndex InterfaceIndex,
    dsgIfTunnelGrpRulePriority Gauge,
    dsgIfTunnelGrpUcidList OCTET STRING,
    dsgIfTunnelGrpVendorParamId Gauge,
    dsgIfTunnelGrpRowStatus RowStatus
    }

dsgIfTunnelGrpIndex OBJECT-TYPE
    SYNTAX Gauge
    ACCESS not-accessible
    STATUS mandatory
    DESCRIPTION
        "The index into this table."
    ::= { dsgIfTunnelGrpToChannelEntry 1 }

dsgIfTunnelGrpChannelIndex OBJECT-TYPE
    SYNTAX Gauge
    ACCESS not-accessible
    STATUS mandatory
    DESCRIPTION
        "The index into this table."
    ::= { dsgIfTunnelGrpToChannelEntry 2 }

dsgIfTunnelGrpDsIfIndex OBJECT-TYPE
    SYNTAX InterfaceIndex
--    Rsyntax INTEGER(1..2147483647)
    ACCESS read-write
    STATUS mandatory
    DESCRIPTION
        "The downstream ifIndex that will be associated to
        this group of tunnel(s)."
    ::= { dsgIfTunnelGrpToChannelEntry 3 }

dsgIfTunnelGrpRulePriority OBJECT-TYPE
    SYNTAX Gauge(0..255)
    ACCESS read-write
    STATUS mandatory
    DESCRIPTION
        "The DSG rule priority determines the order of which
        channel and its associated UCIDs should be applied by
        the DSG client. The default value is 0, which is the lowest
        priority."
    DEFVAL { 0 }
    ::= { dsgIfTunnelGrpToChannelEntry 4 }

dsgIfTunnelGrpUcidList OBJECT-TYPE
    SYNTAX OCTET STRING(SIZE(0..255))
    ACCESS read-write
    STATUS mandatory
    DESCRIPTION
        "The list of Upstream Channel ID (UCID) values (octets)
        for which the DSG rule applies. A DSG client matches this
        parameter if its UCID value is included in the list. The
        default value of zero length string indicates that this
        DSG Rule applies to all DSG clients."
    DEFVAL { "" }
    ::= { dsgIfTunnelGrpToChannelEntry 5 }

dsgIfTunnelGrpVendorParamId OBJECT-TYPE
    SYNTAX Gauge
    ACCESS read-write
    STATUS mandatory
    DESCRIPTION
        "The index of vendor parameter, dsgIfVendorParamId in the
        dsgIfVendorParamTable describing the vendor specific DSG
        parameters. If no associated entry in dsgIfVendorParamTable
        exists, this value is 0."
    DEFVAL { 0 }
    ::= { dsgIfTunnelGrpToChannelEntry 6 }

dsgIfTunnelGrpRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this row. The value of notInService(2)
        indicates that this tunnel group is disabled and no OOB
        traffic on all the associated tunnel(s) will be forwarded
        to DSG clients and all parameters will not be included in
        the DCD message."
    ::= { dsgIfTunnelGrpToChannelEntry 7 }

dsgIfDownstreamTable OBJECT-TYPE
    SYNTAX SEQUENCE OF DsgIfDownstreamEntry
    ACCESS not-accessible
    STATUS mandatory
    DESCRIPTION
        "The DSG Downstream Table contains the associated timers,
        vendor specific parameters index and the channel list
        index to a specific downstream."
    ::= { dsgIfDownstreamChannel 1 }

dsgIfDownstreamEntry OBJECT-TYPE
    SYNTAX DsgIfDownstreamEntry
    ACCESS not-accessible
    STATUS mandatory
    DESCRIPTION
        "An entry in the DSG Downstream Table.
        An entry in this table exists for each ifEntry with
        an ifType of docsCableDownstream(128)."
    INDEX { ifIndex }
    ::= { dsgIfDownstreamTable 1 }

DsgIfDownstreamEntry ::= SEQUENCE {
    dsgIfDownTimerIndex Gauge,
    dsgIfDownVendorParamId Gauge,
    dsgIfDownChannelListIndex Gauge,
    dsgIfDownEnableDCD TruthValue
    }

dsgIfDownTimerIndex OBJECT-TYPE
    SYNTAX Gauge
    ACCESS read-write
    STATUS mandatory
    DESCRIPTION
        "The index into the timer table, dsgIfTimerTable providing
        the timers used by the DSG client(s).
        The default value 0 indicates there is no associated
        timers that need to be sent in the DCD message."
    DEFVAL { 0 }
    ::= { dsgIfDownstreamEntry 1 }

dsgIfDownVendorParamId OBJECT-TYPE
    SYNTAX Gauge
    ACCESS read-write
    STATUS mandatory
    DESCRIPTION
        "The index of vendor parameter, dsgIfVendorParamId in the
        dsgIfVendorParamTable describing the vendor specific DSG
        parameters. If no associated entry in dsgIfVendorParamTable
        exists, this value is 0."
    DEFVAL { 0 }
    ::= { dsgIfDownstreamEntry 2 }

dsgIfDownChannelListIndex OBJECT-TYPE
    SYNTAX Gauge
    ACCESS read-write
    STATUS mandatory
    DESCRIPTION
        "The index of a the downstream frequency channel lists,
        dsgIfChannelListIndex in the dsgIfChannelListTable
        providing the list of downstream frequencies that
        contain DSG tunnels."
    DEFVAL { 0 }
    ::= { dsgIfDownstreamEntry 3 }

dsgIfDownEnableDCD OBJECT-TYPE
    SYNTAX TruthValue
--    Rsyntax INTEGER {
--        true(1),
--        false(2)
--        }
    ACCESS read-write
    STATUS mandatory
    DESCRIPTION
        "Used to enable or disable DCD messages to be sent on this
        downstream channel. The value is always true(1) for those
        downstreams that contains one or many DSG Tunnels."
    ::= { dsgIfDownstreamEntry 4 }

dsgIfClientIdTable OBJECT-TYPE
    SYNTAX SEQUENCE OF DsgIfClientIdEntry
    ACCESS not-accessible
    STATUS mandatory
    DESCRIPTION
        "The Client Identification Table contains the client
        identification type and value. It also contains the
        vendor specific parameter identification. There could
        be multiple client ids associated to a tunnel, grouped
        by the dsgIfClientIdListIndex."
    ::= { dsgIfDCD 1 }

dsgIfClientIdEntry OBJECT-TYPE
    SYNTAX DsgIfClientIdEntry
    ACCESS not-accessible
    STATUS mandatory
    DESCRIPTION
        "An entry in the Client Id Table. Rows are created
        by an SNMP SET request setting the value of
        dsgIfClientRowStatus to 'createAndGo'.
        Rows are deleted by an SNMP SET request setting the
        value of dsgIfClientIdRowStatus to 'destroy'."
    INDEX { dsgIfClientIdListIndex, dsgIfClientIdIndex }
    ::= { dsgIfClientIdTable 1 }

DsgIfClientIdEntry ::= SEQUENCE {
    dsgIfClientIdListIndex Gauge,
    dsgIfClientIdIndex Gauge,
    dsgIfClientIdType INTEGER,
    dsgIfClientIdValue OCTET STRING,
    dsgIfClientVendorParamId Gauge,
    dsgIfClientRowStatus RowStatus
    }

dsgIfClientIdListIndex OBJECT-TYPE
    SYNTAX Gauge
    ACCESS not-accessible
    STATUS mandatory
    DESCRIPTION
        "The index to this table."
    ::= { dsgIfClientIdEntry 1 }

dsgIfClientIdIndex OBJECT-TYPE
    SYNTAX Gauge
    ACCESS not-accessible
    STATUS mandatory
    DESCRIPTION
        "The index to each entry of the Client Id."
    ::= { dsgIfClientIdEntry 2 }

dsgIfClientIdType OBJECT-TYPE
    SYNTAX INTEGER {
        broadcast(1),
        macAddress(2),
        caSystemId(3),
        applicationId(4)
        }
    ACCESS read-write
    STATUS mandatory
    DESCRIPTION
        "The Client Identification type. A DSG client id of type
        broadcast(1) received by all DSG client(s). A DSG client
        id of type macAddress(2) is received by the DSG client that
        has been assigned with this MAC address where the first 3
        bytes is the Organization Unique Identifier (OUI). A DSG
        client id of type caSystemId(3) is received by the DSG
        client that has been assigned a CA_system_ID. A DSG client
        id of type applicationId(4) is received by the DSG client
        that has been assigned an application ID."
    DEFVAL { broadcast }
    ::= { dsgIfClientIdEntry 3 }

dsgIfClientIdValue OBJECT-TYPE
    SYNTAX OCTET STRING(SIZE(6))
    ACCESS read-write
    STATUS mandatory
    DESCRIPTION
        "The Client Identification Value. The content depends on
        the value of the dsgIfClientIdType. The dsgIfClientIdType
        of a type broadcast(1), the value is empty string. The type
        of macAddress(2), the value represents the well known MAC
        address. The type of caSystemId(3) the value represents the
        CA System Id. The type of applicationId(4) the value
        represents the application Id."
    DEFVAL { '000000000000'H }
    ::= { dsgIfClientIdEntry 4 }

dsgIfClientVendorParamId OBJECT-TYPE
    SYNTAX Gauge
    ACCESS read-write
    STATUS mandatory
    DESCRIPTION
        "The index of the vendor parameter id, dsgIfVendorParamId
        in the dsgIfVendorParamTable describing the vendor specific
        DSG parameters. If no associated entry in
        dsgIfVendorParamTable exists, this value is 0."
    DEFVAL { 0 }
    ::= { dsgIfClientIdEntry 5 }

dsgIfClientRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of the row."
    ::= { dsgIfClientIdEntry 6 }

dsgIfVendorParamTable OBJECT-TYPE
    SYNTAX SEQUENCE OF DsgIfVendorParamEntry
    ACCESS not-accessible
    STATUS mandatory
    DESCRIPTION
        "The DSG Vendor Parameter Table allows vendors to send
        specific parameters to the DSG clients within a DSG
        rule or within the DSG Configuration block in a
        DCD message."
    ::= { dsgIfDCD 2 }

dsgIfVendorParamEntry OBJECT-TYPE
    SYNTAX DsgIfVendorParamEntry
    ACCESS not-accessible
    STATUS mandatory
    DESCRIPTION
        "An entry in the DSG Vendor Parameter Table. Rows are
        created by an SNMP SET request setting the value of
        dsgIfVendorRowStatus to 'createAndGo'. Each entry
        represents one or more vendor??s specific parameters.
        Rows are deleted by an SNMP SET request setting the
        value of dsgIfVendorRowStatus to 'destroy'.
        There are limits to the amount of vendor specific
        information that can be carried in a DSG Rule or
        DSG Configuration block. An SNMP SET request which
        would result in these limits being exceeded should be
        rejected."
    INDEX { dsgIfVendorParamId, dsgIfVendorIndex }
    ::= { dsgIfVendorParamTable 1 }

DsgIfVendorParamEntry ::= SEQUENCE {
    dsgIfVendorParamId Gauge,
    dsgIfVendorIndex Gauge,
    dsgIfVendorOUI OCTET STRING,
    dsgIfVendorValue OCTET STRING,
    dsgIfVendorRowStatus RowStatus
    }

dsgIfVendorParamId OBJECT-TYPE
    SYNTAX Gauge
    ACCESS not-accessible
    STATUS mandatory
    DESCRIPTION
        "The index of the table."
    ::= { dsgIfVendorParamEntry 1 }

dsgIfVendorIndex OBJECT-TYPE
    SYNTAX Gauge
    ACCESS not-accessible
    STATUS mandatory
    DESCRIPTION
        "The Vendor Specific Index."
    ::= { dsgIfVendorParamEntry 2 }

dsgIfVendorOUI OBJECT-TYPE
    SYNTAX OCTET STRING(SIZE(3))
    ACCESS read-write
    STATUS mandatory
    DESCRIPTION
        "The Vendor assigned Organization Unique Id (OUI)."
    DEFVAL { '000000'H }
    ::= { dsgIfVendorParamEntry 3 }

dsgIfVendorValue OBJECT-TYPE
    SYNTAX OCTET STRING(SIZE(0..50))
    ACCESS read-write
    STATUS mandatory
    DESCRIPTION
        "The Vendor Specific Parameter Value."
    DEFVAL { "" }
    ::= { dsgIfVendorParamEntry 4 }

dsgIfVendorRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of the row."
    ::= { dsgIfVendorParamEntry 5 }

dsgIfChannelListTable OBJECT-TYPE
    SYNTAX SEQUENCE OF DsgIfChannelListEntry
    ACCESS not-accessible
    STATUS mandatory
    DESCRIPTION
        "The DSG Channel List Table contains list of one or
        multiple downstream frequencies that are carrying DSG
        tunnel(s)."
    ::= { dsgIfDCD 3 }

dsgIfChannelListEntry OBJECT-TYPE
    SYNTAX DsgIfChannelListEntry
    ACCESS not-accessible
    STATUS mandatory
    DESCRIPTION
        "An entry in the DSG Channel List Table. Rows are
        created by an SNMP SET request setting the value of
        dsgIfChannelRowStatus to 'createAndGo'.
        Rows are deleted by an SNMP SET request setting the value
        of dsgIfChannelRowStatus to 'destroy'."
    INDEX { dsgIfChannelListIndex, dsgIfChannelIndex }
    ::= { dsgIfChannelListTable 1 }

DsgIfChannelListEntry ::= SEQUENCE {
    dsgIfChannelListIndex Gauge,
    dsgIfChannelIndex Gauge,
    dsgIfChannelDsFreq INTEGER,
    dsgIfChannelRowStatus RowStatus
    }

dsgIfChannelListIndex OBJECT-TYPE
    SYNTAX Gauge
    ACCESS not-accessible
    STATUS mandatory
    DESCRIPTION
        "The index to this table."
    ::= { dsgIfChannelListEntry 1 }

dsgIfChannelIndex OBJECT-TYPE
    SYNTAX Gauge
    ACCESS not-accessible
    STATUS mandatory
    DESCRIPTION
        "The index for each downstream frequency that
        contains the DSG tunnel(s)."
    ::= { dsgIfChannelListEntry 2 }

dsgIfChannelDsFreq OBJECT-TYPE
    SYNTAX INTEGER(0..1000000000)
--  Units
--    hertz
    ACCESS read-write
    STATUS mandatory
    DESCRIPTION
        "The DOCSIS downstream center frequency. The receive
        frequency MUST be a multiple of 62500Hz."
    DEFVAL { 0 }
    ::= { dsgIfChannelListEntry 3 }

dsgIfChannelRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of the row."
    ::= { dsgIfChannelListEntry 4 }

dsgIfTimerTable OBJECT-TYPE
    SYNTAX SEQUENCE OF DsgIfTimerEntry
    ACCESS not-accessible
    STATUS mandatory
    DESCRIPTION
        "The DSG Timer Table contains timers that are sent to
        the DSG client(s) via the DCD message."
    ::= { dsgIfDCD 4 }

dsgIfTimerEntry OBJECT-TYPE
    SYNTAX DsgIfTimerEntry
    ACCESS not-accessible
    STATUS mandatory
    DESCRIPTION
        "An entry in the DSG Timer Table. Rows are created
        by an SNMP SET request setting the value of
        dsgIfTimerRowStatus to 'createAndGo'.
        Rows are deleted by an SNMP SET request setting the value
        of dsgIfTimerRowStatus to 'destroy'."
    INDEX { dsgIfTimerIndex }
    ::= { dsgIfTimerTable 1 }

DsgIfTimerEntry ::= SEQUENCE {
    dsgIfTimerIndex Gauge,
    dsgIfTimerTdsg1 Gauge,
    dsgIfTimerTdsg2 Gauge,
    dsgIfTimerTdsg3 Gauge,
    dsgIfTimerTdsg4 Gauge,
    dsgIfTimerRowStatus RowStatus
    }

dsgIfTimerIndex OBJECT-TYPE
    SYNTAX Gauge
    ACCESS not-accessible
    STATUS mandatory
    DESCRIPTION
        "The index to this table."
    ::= { dsgIfTimerEntry 1 }

dsgIfTimerTdsg1 OBJECT-TYPE
    SYNTAX Gauge(1..65535)
--  Units
--    second
    ACCESS read-write
    STATUS mandatory
    DESCRIPTION
        "Initialization Timeout. This is the timeout period
        for the DSG packets during initialization of the DSG
        client. The default value is 2 seconds."
    DEFVAL { 2 }
    ::= { dsgIfTimerEntry 2 }

dsgIfTimerTdsg2 OBJECT-TYPE
    SYNTAX Gauge(1..65535)
--  Units
--    second
    ACCESS read-write
    STATUS mandatory
    DESCRIPTION
        "Operational Timeout. This is the timeout period for
        the DSG packets during normal operation of the DSG client.
        Default value is 10 minutes."
    DEFVAL { 600 }
    ::= { dsgIfTimerEntry 3 }

dsgIfTimerTdsg3 OBJECT-TYPE
    SYNTAX Gauge(0..65535)
--  Units
--    second
    ACCESS read-write
    STATUS mandatory
    DESCRIPTION
        "Two-way retry timer. This is the retry timer that
        determines when the DSG client attempts to reconnect
        with the DSG Agent and established two-way connectivity.
        Default value is 5 minutes. The value 0 indicates that
        the client will continuously retry two-way operation."
    DEFVAL { 300 }
    ::= { dsgIfTimerEntry 4 }

dsgIfTimerTdsg4 OBJECT-TYPE
    SYNTAX Gauge(0..65535)
--  Units
--    second
    ACCESS read-write
    STATUS mandatory
    DESCRIPTION
        "One-way retry timer. The retry timer that determines
        when the client attempts to rescan for a DOCSIS
        downstream channel that contains DSG packets after a
        dsgIfTimerTdsg1 or dsgIfTimerTdsg2 timeout.
        Default value is 30 minutes. The value 0 indicates that
        the client will immediately begin scanning upon
        dsgIfTimerTdsg1 or dsgIfTimerTdsg2 timeout."
    DEFVAL { 1800 }
    ::= { dsgIfTimerEntry 5 }

dsgIfTimerRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of the row."
    ::= { dsgIfTimerEntry 6 }

dsgIfClassifierGroup OBJECT IDENTIFIER ::= { dsgIfGroups 1 }
-- OBJECT-GROUP
--  Status
--    mandatory
--  Descr
--    A collection of objects providing the classifier
--    configuration.
--  objects
--    dsgIfClassPriority, dsgIfClassSrcIpAddrType, 
--    dsgIfClassSrcIpAddr, dsgIfClassSrcIpPrefixLength, 
--    dsgIfClassDestIpAddressType, dsgIfClassDestIpAddress, 
--    dsgIfClassDestPortStart, dsgIfClassDestPortEnd, 
--    dsgIfClassRowStatus, dsgIfClassIncludeInDCD

dsgIfBaseGroup OBJECT IDENTIFIER ::= { dsgIfGroups 2 }
-- OBJECT-GROUP
--  Status
--    mandatory
--  Descr
--    A collection of objects providing DSG Tunnel and Channel
--    configuration.
--  objects
--    dsgIfTunnelGroupIndex, dsgIfTunnelClientIdListIndex, 
--    dsgIfTunnelMacAddress, dsgIfTunnelServiceClassName, 
--    dsgIfTunnelRowStatus, dsgIfTunnelGrpDsIfIndex, 
--    dsgIfTunnelGrpRulePriority, dsgIfTunnelGrpUcidList, 
--    dsgIfTunnelGrpVendorParamId, dsgIfTunnelGrpRowStatus, 
--    dsgIfDownTimerIndex, dsgIfDownVendorParamId, 
--    dsgIfDownChannelListIndex, dsgIfDownEnableDCD

dsgIfDCDGroup OBJECT IDENTIFIER ::= { dsgIfGroups 3 }
-- OBJECT-GROUP
--  Status
--    mandatory
--  Descr
--    A collection of objects providing Timers configuration.
--  objects
--    dsgIfClientIdType, dsgIfClientIdValue, 
--    dsgIfClientVendorParamId, dsgIfClientRowStatus, 
--    dsgIfVendorOUI, dsgIfVendorValue, dsgIfVendorRowStatus, 
--    dsgIfChannelDsFreq, dsgIfChannelRowStatus, dsgIfTimerTdsg1, 
--    dsgIfTimerTdsg2, dsgIfTimerTdsg3, dsgIfTimerTdsg4, 
--    dsgIfTimerRowStatus

dsgIfBasicCompliance OBJECT IDENTIFIER ::= { dsgIfCompliances 1 }
-- MODULE-COMPLIANCE
--  Status
--    mandatory
--  Descr
--    The compliance statement for DOCSIS Set-top Gateway
--    systems.
--  Module
--    >>current<<
--   OptGroup
--    dsgIfClassifierGroup
--   OptGroup
--    dsgIfBaseGroup
--   OptGroup
--    dsgIfDCDGroup


END
