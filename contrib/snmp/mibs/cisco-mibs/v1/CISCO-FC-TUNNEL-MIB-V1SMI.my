-- MIB file created 18-Nov-2010 15:44:43, by
--   SMICng version 2.2.11-beta(PRO)(Solaris), January 20, 2001. Enterprise key cisco.com

CISCO-FC-TUNNEL-MIB DEFINITIONS ::= BEGIN

-- From file: "CISCO-FC-TUNNEL-MIB.my"
-- Compile options "4 7 F H N W 03 06 0B 0G 0N 0T"

IMPORTS
    InterfaceIndex
            FROM IF-MIB
    RowStatus, TruthValue
            FROM SNMPv2-TC-v1
    ciscoMgmt
            FROM CISCO-SMI
    InetAddressType, InetAddress
            FROM INET-ADDRESS-MIB
    SnmpAdminString
            FROM SNMP-FRAMEWORK-MIB
    Counter, Gauge
            FROM RFC1155-SMI
    OBJECT-TYPE
            FROM RFC-1212;

ciscoFiberChannelTunnelMIB OBJECT IDENTIFIER ::= { ciscoMgmt 9999 }
-- MODULE-IDENTITY
--  LastUpdated
--    200203081700Z
--  OrgName
--    Cisco Systems, Inc.
--  ContactInfo
--    Postal: Cisco Systems, Inc.
--        170 West Tasman Drive
--        San Jose, CA 95134-1706
--        USA
--    
--        Tel: +1 408 526 4000
--    
--        E-mail: cs-cat6000@cisco.com
--  Descr
--    The CISCO-FC-TUNNEL-MIB is used to configure Fiber Channel
--     (FC) tunneled by other protocols, i.e. TCP (Transmision
--     Control Protocol) or UDP (User Datagram Protocol), and
--     monitor the status of the tunnels.  And Fiber Channel
--     Command and Data messages can be tunneled by those
--     protocols through the internet to extend the Fiber Channel
--     network.
--  RevDate
--    200203081700Z
--  RevDescr
--    Initial version. Only supports Fiber Channel TCP
--     tunneling.

ciscoFCTunnelMIBNotifi OBJECT IDENTIFIER ::= { ciscoFiberChannelTunnelMIB 0 }
ciscoFCTunnelMIBObjects OBJECT IDENTIFIER ::= { ciscoFiberChannelTunnelMIB 1 }
ciscoFCTunnelMIBConform OBJECT IDENTIFIER ::= { ciscoFiberChannelTunnelMIB 2 }
cftTcpTunnelObjects OBJECT IDENTIFIER ::= { ciscoFCTunnelMIBObjects 1 }
cftTunnelMIBCompliances OBJECT IDENTIFIER ::= { ciscoFCTunnelMIBConform 1 }
cftTunnelMIBGroups OBJECT IDENTIFIER ::= { ciscoFCTunnelMIBConform 2 }

cftMaxTcpTunnels OBJECT-TYPE
    SYNTAX Gauge
    ACCESS read-only
    STATUS mandatory
    DESCRIPTION
        "Maximum number of Fiber Channel TCP tunnels that can be built
         per Fiber Channel interface."
    ::= { cftTcpTunnelObjects 1 }

cftTcpTunnelTable OBJECT-TYPE
    SYNTAX SEQUENCE OF CftTcpTunnelEntry
    ACCESS not-accessible
    STATUS mandatory
    DESCRIPTION
        "This table contains TCP tunnels' information for FC interfaces.
         FC can use these TCP tunnels to communicate with each other
         through the internet.  The TCP tunnels will help to build up
         reliable connections between FC interfaces to exchange FC
         Command and Data information.
        
         This table is for configuring the TCP tunnels and monitoring
         the status of tunnels.  And the number of entries in this
         table is decided by the MIB object cftMaxTcpTunnels."
    REFERENCE
        "RFC 793, Transmission Control Protocol.
         RFC 2581, TCP Congestion Control"
    ::= { cftTcpTunnelObjects 2 }

cftTcpTunnelEntry OBJECT-TYPE
    SYNTAX CftTcpTunnelEntry
    ACCESS not-accessible
    STATUS mandatory
    DESCRIPTION
        "An entry contains the configuration and status objects of a
         TCP tunnel.  The configuration includes the TCP connection
         4-tuples, source IP, destination IP, source port , destination
         port, and some other TCP connection's options.  The status
         includes the TCP connections and Tunnel's administration and
         operation.
        
         For each TCP tunnel, there are 2 TCP connections that will be
         built up in the tunneling.  One is for FC Command
         communication and the other is for FC Data communication."
    INDEX { cftFiberChannelIf, --?? IMPLIED may cause problems
            IMPLIED cftTcpTunnelName }
    ::= { cftTcpTunnelTable 1 }

CftTcpTunnelEntry ::= SEQUENCE {
    cftFiberChannelIf InterfaceIndex,
    cftTcpTunnelName SnmpAdminString,
    cftTcpTunnelSrcIpType InetAddressType,
    cftTcpTunnelSrcIp InetAddress,
    cftTcpTunnelDestIpType InetAddressType,
    cftTcpTunnelDestIp InetAddress,
    cftTcpTunnelCmdSrcPort Gauge,
    cftTcpTunnelCmdDestPort Gauge,
    cftTcpTunnelDataSrcPort Gauge,
    cftTcpTunnelDataDestPort Gauge,
    cftTcpTunnelCmdMWS INTEGER,
    cftTcpTunnelDataMWS INTEGER,
    cftTcpTunnelCmdKeepAliveTime Gauge,
    cftTcpTunnelDataKeepAliveTime Gauge,
    cftTcpTunnelCmdSelectiveAck TruthValue,
    cftTcpTunnelDataSelectiveAck TruthValue,
    cftTcpTunnelCmdConnectStatus INTEGER,
    cftTcpTunnelDataConnectStatus INTEGER,
    cftTcpTunnelOperStatus INTEGER,
    cftTcpTunnelStatus RowStatus
    }

cftFiberChannelIf OBJECT-TYPE
    SYNTAX InterfaceIndex
--    Rsyntax INTEGER(1..2147483647)
    ACCESS not-accessible
    STATUS mandatory
    DESCRIPTION
        "The interface index of the FC interface with TCP tunneling
         capable."
    ::= { cftTcpTunnelEntry 1 }

cftTcpTunnelName OBJECT-TYPE
    SYNTAX SnmpAdminString(SIZE(1..20))
--    Rsyntax OCTET STRING(SIZE(1..20))
    ACCESS not-accessible
    STATUS mandatory
    DESCRIPTION
        "The name of the FC TCP tunnel."
    ::= { cftTcpTunnelEntry 2 }

cftTcpTunnelSrcIpType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "The source IP address type of the FC TCP tunnel."
    ::= { cftTcpTunnelEntry 3 }

cftTcpTunnelSrcIp OBJECT-TYPE
    SYNTAX InetAddress
--    Rsyntax OCTET STRING(SIZE(0..255))
    ACCESS read-write
    STATUS mandatory
    DESCRIPTION
        "The source IP address of the FC TCP tunnel.  The type of the
         IP address is determined by the object cftTcpTunnelSrcIpType in
         the same entry."
    ::= { cftTcpTunnelEntry 4 }

cftTcpTunnelDestIpType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "The destination IP address type of the FC TCP tunnel."
    ::= { cftTcpTunnelEntry 5 }

cftTcpTunnelDestIp OBJECT-TYPE
    SYNTAX InetAddress
--    Rsyntax OCTET STRING(SIZE(0..255))
    ACCESS read-write
    STATUS mandatory
    DESCRIPTION
        "The destination IP address of the FC TCP tunnel.  The type of
         the IP address is determined by the object
         cftTcpTunnelDestIpType in the same entry."
    ::= { cftTcpTunnelEntry 6 }

cftTcpTunnelCmdSrcPort OBJECT-TYPE
    SYNTAX Gauge(1025..65535)
    ACCESS read-write
    STATUS mandatory
    DESCRIPTION
        "The source port of the TCP connection for FC Command
         communication."
    ::= { cftTcpTunnelEntry 7 }

cftTcpTunnelCmdDestPort OBJECT-TYPE
    SYNTAX Gauge(1025..65535)
    ACCESS read-write
    STATUS mandatory
    DESCRIPTION
        "The destination port of the TCP connection for FC Command
         communication."
    ::= { cftTcpTunnelEntry 8 }

cftTcpTunnelDataSrcPort OBJECT-TYPE
    SYNTAX Gauge(1025..65535)
    ACCESS read-write
    STATUS mandatory
    DESCRIPTION
        "The source port of the TCP connection for FC Data
         communication."
    ::= { cftTcpTunnelEntry 9 }

cftTcpTunnelDataDestPort OBJECT-TYPE
    SYNTAX Gauge(1025..65535)
    ACCESS read-write
    STATUS mandatory
    DESCRIPTION
        "The destination port of the TCP connection for FC Data
         communication."
    ::= { cftTcpTunnelEntry 10 }

cftTcpTunnelCmdMWS OBJECT-TYPE
    SYNTAX INTEGER {
        ws32kbytes(1),
        ws128kbytes(2),
        ws256kbytes(3),
        ws512kbytes(4)
        }
    ACCESS read-write
    STATUS mandatory
    DESCRIPTION
        "The maximum window size of the TCP connection for FC Command
         communication.
         ws32kbytes : means the window size is 32 kilo-bytes.
         ws128kbytes : means the window size is 128 kilo-bytes.
         ws256kbytes : means the window size is 256 kilo-bytes.
         ws512kbytes : means the window size is 512 kilo-bytes."
    DEFVAL { ws32kbytes }
    ::= { cftTcpTunnelEntry 11 }

cftTcpTunnelDataMWS OBJECT-TYPE
    SYNTAX INTEGER {
        ws32kbytes(1),
        ws128kbytes(2),
        ws256kbytes(3),
        ws512kbytes(4)
        }
    ACCESS read-write
    STATUS mandatory
    DESCRIPTION
        "The maximum window size of the TCP connection for FC Data
         communication.
         ws32kbytes : means the window size is 32 kilo-bytes.
         ws128kbytes : means the window size is 128 kilo-bytes.
         ws256kbytes : means the window size is 256 kilo-bytes.
         ws512kbytes : means the window size is 512 kilo-bytes."
    DEFVAL { ws32kbytes }
    ::= { cftTcpTunnelEntry 12 }

cftTcpTunnelCmdKeepAliveTime OBJECT-TYPE
    SYNTAX Gauge(3600..10800)
--  Units
--    seconds
    ACCESS read-write
    STATUS mandatory
    DESCRIPTION
        "The keep alive time of the TCP connection for FC Command
         communication."
    DEFVAL { 7200 }
    ::= { cftTcpTunnelEntry 13 }

cftTcpTunnelDataKeepAliveTime OBJECT-TYPE
    SYNTAX Gauge(3600..10800)
--  Units
--    seconds
    ACCESS read-write
    STATUS mandatory
    DESCRIPTION
        "The keep alive time of the TCP connection for FC Data
         communication."
    DEFVAL { 7200 }
    ::= { cftTcpTunnelEntry 14 }

cftTcpTunnelCmdSelectiveAck OBJECT-TYPE
    SYNTAX TruthValue
--    Rsyntax INTEGER {
--        true(1),
--        false(2)
--        }
    ACCESS read-write
    STATUS mandatory
    DESCRIPTION
        "The selective acknowledge option of the TCP connection for FC
         Command communication."
    DEFVAL { false }
    ::= { cftTcpTunnelEntry 15 }

cftTcpTunnelDataSelectiveAck OBJECT-TYPE
    SYNTAX TruthValue
--    Rsyntax INTEGER {
--        true(1),
--        false(2)
--        }
    ACCESS read-write
    STATUS mandatory
    DESCRIPTION
        "The selective acknowledge option of the TCP connection for FC
         Data communication."
    DEFVAL { true }
    ::= { cftTcpTunnelEntry 16 }

cftTcpTunnelCmdConnectStatus OBJECT-TYPE
    SYNTAX INTEGER {
        connected(1),
        notConnected(2)
        }
    ACCESS read-only
    STATUS mandatory
    DESCRIPTION
        "The status of the TCP connection for FC Command communication.
        
         connected(1) means the TCP connection for FC Command
         has been connected for communication.
         notConnected(2) means the TCP connection for FC Command is not
         successful."
    ::= { cftTcpTunnelEntry 17 }

cftTcpTunnelDataConnectStatus OBJECT-TYPE
    SYNTAX INTEGER {
        connected(1),
        notConnected(2)
        }
    ACCESS read-only
    STATUS mandatory
    DESCRIPTION
        "The status of the TCP connection for FC Data communication.
        
         connected(1) means the TCP connection for FC Data has been
         connected for communication.
         notConnected(2) means the TCP connection for FC Data is not
         successful."
    ::= { cftTcpTunnelEntry 18 }

cftTcpTunnelOperStatus OBJECT-TYPE
    SYNTAX INTEGER {
        up(1),
        down(2)
        }
    ACCESS read-only
    STATUS mandatory
    DESCRIPTION
        "The operational status of this TCP tunnel.
        
         up(1) means this TCP tunnel is up and active.
         down(2) means this TCP tunnel is not active."
    ::= { cftTcpTunnelEntry 19 }

cftTcpTunnelStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this TCP tunnel entry.  If this object is active,
         the other objects in the same row cannot be modified by the
         management station."
    ::= { cftTcpTunnelEntry 20 }

cftTcpTunnelStatsTable OBJECT-TYPE
    SYNTAX SEQUENCE OF CftTcpTunnelStatsEntry
    ACCESS not-accessible
    STATUS mandatory
    DESCRIPTION
        "The table of traffic statistics information for FC tunnels. The
         entries in this table are shown only if the cftTcpTunnelStatus
         object of the corresponding entries are active in the
         cftTcpTunnelTable."
    ::= { cftTcpTunnelObjects 3 }

cftTcpTunnelStatsEntry OBJECT-TYPE
    SYNTAX CftTcpTunnelStatsEntry
    ACCESS not-accessible
    STATUS mandatory
    DESCRIPTION
        "The entry is indexed by the same index in the
         cftTcpTunnelTable. And this entry contains statistics
         information of FC Command TCP connection and FC Data TCP
         connection."
    INDEX { cftFiberChannelIf, --?? IMPLIED may cause problems
            IMPLIED cftTcpTunnelName }
    ::= { cftTcpTunnelStatsTable 1 }

CftTcpTunnelStatsEntry ::= SEQUENCE {
    cftTcpTunnelCmdRxSegmentOctets Counter,
    cftTcpTunnelDataRxSegmentOctets Counter,
    cftTcpTunnelCmdRxPrestufOctets Counter,
    cftTcpTunnelDataRxPrestufOctets Counter,
    cftTcpTunnelCmdRxPoststufOctets Counter,
    cftTcpTunnelDataRxPoststufOctets Counter,
    cftTcpTunnelCmdTxOctets Counter,
    cftTcpTunnelDataTxOctets Counter,
    cftTcpTunnelCmdTxPkts Counter,
    cftTcpTunnelDataTxPkts Counter,
    cftTcpTunnelCmdTxDrops Counter,
    cftTcpTunnelDataTxDrops Counter
    }

cftTcpTunnelCmdRxSegmentOctets OBJECT-TYPE
    SYNTAX --?? syntax is not convertable to SMIv1
           Counter
--  Units
--    bytes
    ACCESS read-only
    STATUS mandatory
    DESCRIPTION
        "Number of TCP segment bytes received in the FC TCP Command
         connection."
    ::= { cftTcpTunnelStatsEntry 1 }

cftTcpTunnelDataRxSegmentOctets OBJECT-TYPE
    SYNTAX --?? syntax is not convertable to SMIv1
           Counter
--  Units
--    bytes
    ACCESS read-only
    STATUS mandatory
    DESCRIPTION
        "Number of TCP segment bytes received in the FC TCP Data
         connection."
    ::= { cftTcpTunnelStatsEntry 2 }

cftTcpTunnelCmdRxPrestufOctets OBJECT-TYPE
    SYNTAX --?? syntax is not convertable to SMIv1
           Counter
--  Units
--    bytes
    ACCESS read-only
    STATUS mandatory
    DESCRIPTION
        "Number of bytes received before stuffing the internal hardware
         bus header in the FC TCP Command connection."
    ::= { cftTcpTunnelStatsEntry 3 }

cftTcpTunnelDataRxPrestufOctets OBJECT-TYPE
    SYNTAX --?? syntax is not convertable to SMIv1
           Counter
--  Units
--    bytes
    ACCESS read-only
    STATUS mandatory
    DESCRIPTION
        "Number of bytes received before stuffing the internal hardware
         bus header in the FC TCP Data connection."
    ::= { cftTcpTunnelStatsEntry 4 }

cftTcpTunnelCmdRxPoststufOctets OBJECT-TYPE
    SYNTAX --?? syntax is not convertable to SMIv1
           Counter
--  Units
--    bytes
    ACCESS read-only
    STATUS mandatory
    DESCRIPTION
        "Number of bytes received after stuffing the internal hardward
         bus header in the FC TCP Command connection."
    ::= { cftTcpTunnelStatsEntry 5 }

cftTcpTunnelDataRxPoststufOctets OBJECT-TYPE
    SYNTAX --?? syntax is not convertable to SMIv1
           Counter
--  Units
--    bytes
    ACCESS read-only
    STATUS mandatory
    DESCRIPTION
        "Number of bytes received after stuffing the internal hardward
         bus header in the FC TCP Data connection."
    ::= { cftTcpTunnelStatsEntry 6 }

cftTcpTunnelCmdTxOctets OBJECT-TYPE
    SYNTAX --?? syntax is not convertable to SMIv1
           Counter
--  Units
--    bytes
    ACCESS read-only
    STATUS mandatory
    DESCRIPTION
        "Number of bytes sent in the FC TCP Command connection."
    ::= { cftTcpTunnelStatsEntry 7 }

cftTcpTunnelDataTxOctets OBJECT-TYPE
    SYNTAX --?? syntax is not convertable to SMIv1
           Counter
--  Units
--    bytes
    ACCESS read-only
    STATUS mandatory
    DESCRIPTION
        "Number of bytes sent in the FC TCP Data connection."
    ::= { cftTcpTunnelStatsEntry 8 }

cftTcpTunnelCmdTxPkts OBJECT-TYPE
    SYNTAX Counter
--  Units
--    packets
    ACCESS read-only
    STATUS mandatory
    DESCRIPTION
        "Number of packets sent in the FC TCP Command
         connection."
    ::= { cftTcpTunnelStatsEntry 9 }

cftTcpTunnelDataTxPkts OBJECT-TYPE
    SYNTAX Counter
--  Units
--    packets
    ACCESS read-only
    STATUS mandatory
    DESCRIPTION
        "Number of packets sent in the FC TCP Data
         connection."
    ::= { cftTcpTunnelStatsEntry 10 }

cftTcpTunnelCmdTxDrops OBJECT-TYPE
    SYNTAX Counter
--  Units
--    packets
    ACCESS read-only
    STATUS mandatory
    DESCRIPTION
        "Number of packets dropped in the FC TCP Command
         connection."
    ::= { cftTcpTunnelStatsEntry 11 }

cftTcpTunnelDataTxDrops OBJECT-TYPE
    SYNTAX Counter
--  Units
--    packets
    ACCESS read-only
    STATUS mandatory
    DESCRIPTION
        "Number of packets dropped in the FC TCP Data
         connection."
    ::= { cftTcpTunnelStatsEntry 12 }

cftIfTcpTable OBJECT-TYPE
    SYNTAX SEQUENCE OF CftIfTcpEntry
    ACCESS not-accessible
    STATUS mandatory
    DESCRIPTION
        "This table contains the statistics information of the Fiber
         Channel interface with the ability of TCP tunneling."
    REFERENCE
        "RFC 793, Transmission Control Protocol."
    ::= { cftTcpTunnelObjects 4 }

cftIfTcpEntry OBJECT-TYPE
    SYNTAX CftIfTcpEntry
    ACCESS not-accessible
    STATUS mandatory
    DESCRIPTION
        "This entry contains TCP statistics information for a given
         FC interface with the ability of TCP tunneling."
    INDEX { cftIfTcpIndex }
    ::= { cftIfTcpTable 1 }

CftIfTcpEntry ::= SEQUENCE {
    cftIfTcpIndex InterfaceIndex,
    cftIfTcpConnInit Counter,
    cftIfTcpConnAccepted Counter,
    cftIfTcpConnEstablished Counter,
    cftIfTcpConnDrops Counter,
    cftIfTcpConnClosed Counter,
    cftIfTcpTxPkts Counter,
    cftIfTcpTxDataPkts Counter,
    cftIfTcpTxDataOctets Counter,
    cftIfTcpRetxDataPkts Counter,
    cftIfTcpRetxDataOctets Counter,
    cftIfTcpRxPkts Counter,
    cftIfTcpRxInSequencePkts Counter,
    cftIfTcpRxInSequenceOctets Counter,
    cftIfTcpRxCcksumErrPkts Counter,
    cftIfTcpRxBadOffsetPkts Counter,
    cftIfTcpRxOutOfOrderPkts Counter,
    cftIfTcpRxOutOfOrderOctets Counter
    }

cftIfTcpIndex OBJECT-TYPE
    SYNTAX InterfaceIndex
--    Rsyntax INTEGER(1..2147483647)
    ACCESS not-accessible
    STATUS mandatory
    DESCRIPTION
        "The interface index of the FC interface capable of
         carrying TCP tunnels."
    ::= { cftIfTcpEntry 1 }

cftIfTcpConnInit OBJECT-TYPE
    SYNTAX Counter
    ACCESS read-only
    STATUS mandatory
    DESCRIPTION
        "Number of TCP connections initiated."
    ::= { cftIfTcpEntry 2 }

cftIfTcpConnAccepted OBJECT-TYPE
    SYNTAX Counter
    ACCESS read-only
    STATUS mandatory
    DESCRIPTION
        "Number of TCP requested connections accepted."
    ::= { cftIfTcpEntry 3 }

cftIfTcpConnEstablished OBJECT-TYPE
    SYNTAX Counter
    ACCESS read-only
    STATUS mandatory
    DESCRIPTION
        "Number of TCP connections established."
    ::= { cftIfTcpEntry 4 }

cftIfTcpConnDrops OBJECT-TYPE
    SYNTAX Counter
    ACCESS read-only
    STATUS mandatory
    DESCRIPTION
        "Number of TCP connections dropped."
    ::= { cftIfTcpEntry 5 }

cftIfTcpConnClosed OBJECT-TYPE
    SYNTAX Counter
    ACCESS read-only
    STATUS mandatory
    DESCRIPTION
        "Number of TCP connections closed.  This includes those
         connections dropped."
    ::= { cftIfTcpEntry 6 }

cftIfTcpTxPkts OBJECT-TYPE
    SYNTAX Counter
    ACCESS read-only
    STATUS mandatory
    DESCRIPTION
        "Number of TCP transmitting packets.  This includes
         TCP control and data packets."
    ::= { cftIfTcpEntry 7 }

cftIfTcpTxDataPkts OBJECT-TYPE
    SYNTAX Counter
    ACCESS read-only
    STATUS mandatory
    DESCRIPTION
        "Number of TCP transmitting data packets.
         This doesn't include those TCP control traffic."
    ::= { cftIfTcpEntry 8 }

cftIfTcpTxDataOctets OBJECT-TYPE
    SYNTAX Counter
    ACCESS read-only
    STATUS mandatory
    DESCRIPTION
        "Number of TCP transmitting data octets.
         This doesn't include those TCP control traffic."
    ::= { cftIfTcpEntry 9 }

cftIfTcpRetxDataPkts OBJECT-TYPE
    SYNTAX Counter
    ACCESS read-only
    STATUS mandatory
    DESCRIPTION
        "Number of TCP re-transmitting data packets.
         This doesn't include those TCP control traffic."
    ::= { cftIfTcpEntry 10 }

cftIfTcpRetxDataOctets OBJECT-TYPE
    SYNTAX Counter
    ACCESS read-only
    STATUS mandatory
    DESCRIPTION
        "Number of TCP re-transmitting data octets.
         This doesn't include those TCP control traffic."
    ::= { cftIfTcpEntry 11 }

cftIfTcpRxPkts OBJECT-TYPE
    SYNTAX Counter
    ACCESS read-only
    STATUS mandatory
    DESCRIPTION
        "Number of TCP packets received."
    ::= { cftIfTcpEntry 12 }

cftIfTcpRxInSequencePkts OBJECT-TYPE
    SYNTAX Counter
    ACCESS read-only
    STATUS mandatory
    DESCRIPTION
        "Number of TCP packets received in sequence."
    ::= { cftIfTcpEntry 13 }

cftIfTcpRxInSequenceOctets OBJECT-TYPE
    SYNTAX Counter
    ACCESS read-only
    STATUS mandatory
    DESCRIPTION
        "Number of TCP octets received in sequence."
    ::= { cftIfTcpEntry 14 }

cftIfTcpRxCcksumErrPkts OBJECT-TYPE
    SYNTAX Counter
    ACCESS read-only
    STATUS mandatory
    DESCRIPTION
        "Number of TCP packets received with checksum error."
    ::= { cftIfTcpEntry 15 }

cftIfTcpRxBadOffsetPkts OBJECT-TYPE
    SYNTAX Counter
    ACCESS read-only
    STATUS mandatory
    DESCRIPTION
        "Number of TCP packets received with bad offset."
    ::= { cftIfTcpEntry 16 }

cftIfTcpRxOutOfOrderPkts OBJECT-TYPE
    SYNTAX Counter
    ACCESS read-only
    STATUS mandatory
    DESCRIPTION
        "Number of out-of-order TCP packets received."
    ::= { cftIfTcpEntry 17 }

cftIfTcpRxOutOfOrderOctets OBJECT-TYPE
    SYNTAX Counter
    ACCESS read-only
    STATUS mandatory
    DESCRIPTION
        "Number of out-of-order TCP octets received."
    ::= { cftIfTcpEntry 18 }

cftIfTcpExtTable OBJECT-TYPE
    SYNTAX SEQUENCE OF CftIfTcpExtEntry
    ACCESS not-accessible
    STATUS mandatory
    DESCRIPTION
        "This table contains the statistics information of the Fiber
         Channel interface with the ability of TCP tunneling.  This
         table is an extension of cftIfTcpTable and this table
         provides more specific counters that not all TCP protocol
         stack will support."
    REFERENCE
        "RFC 793, Transmission Control Protocol.
         RFC 2581, TCP Congestion Control"
    ::= { cftTcpTunnelObjects 5 }

cftIfTcpExtEntry OBJECT-TYPE
    SYNTAX CftIfTcpExtEntry
    ACCESS not-accessible
    STATUS mandatory
    DESCRIPTION
        "This entry contains TCP statistics information for a given
         FC interface with the ability of TCP tunneling."
    INDEX { cftIfTcpIndex }
    ::= { cftIfTcpExtTable 1 }

CftIfTcpExtEntry ::= SEQUENCE {
    cftIfTcpEmbryonicConnDrops Counter,
    cftIfTcpSegsTryToGetRTT Counter,
    cftIfTcpSegsSucceedToGetRTT Counter,
    cftIfTcpDelayedAcksSent Counter,
    cftIfTcpConnDroppedRxTimeout Counter,
    cftIfTcpRetransmitTimeout Counter,
    cftIfTcpPersistTimeout Counter,
    cftIfTcpKeepaliveTimeout Counter,
    cftIfTcpKeepaliveProbesSent Counter,
    cftIfTcpConnDroppedInKeepalive Counter,
    cftIfTcpConnDroppedInPersist Counter,
    cftIfTcpConnDrainedByNoMemory Counter,
    cftIfTcpAckOnlyPkts Counter,
    cftIfTcpTxWindowProbes Counter,
    cftIfTcpTxURGPkts Counter,
    cftIfTcpTxWindowUpdateOnlyPkts Counter,
    cftIfTcpTxControlPkts Counter,
    cftIfTcpRxDroppedByNoMemory Counter,
    cftIfTcpRxTooShort Counter,
    cftIfTcpRxDupOnlyPkts Counter,
    cftIfTcpRxDupOnlyOctets Counter,
    cftIfTcpRxDupDataPkts Counter,
    cftIfTcpRxDupOctetsInPartDupPkts Counter,
    cftIfTcpRxDataAfterWindowPkts Counter,
    cftIfTcpRxDataAfterWindowOctets Counter,
    cftIfTcpRxPktsAfterConnClose Counter,
    cftIfTcpRxWindowProbesPkts Counter,
    cftIfTcpRxDupAcks Counter,
    cftIfTcpRxAcksForUnsentData Counter,
    cftIfTcpRxAcksPkts Counter,
    cftIfTcpOctetAckedByRxAcks Counter,
    cftIfTcpRxWindowUpdatePkts Counter,
    cftIfTcpSegDropByPAWS Counter,
    cftIfTcpTxSackFackDataPkts Counter,
    cftIfTcpTxSackFackDataOctets Counter,
    cftIfTcpRetxSackFackDataPkts Counter,
    cftIfTcpRetxSackFackDataOctets Counter,
    cftIfTcpSackFackConnClosed Counter,
    cftIfTcpRetxSackFackTimeouts Counter,
    cftIfTcpHdrPredictOkForAcks Counter,
    cftIfTcpHdrPredictOkForDataPkts Counter
    }

cftIfTcpEmbryonicConnDrops OBJECT-TYPE
    SYNTAX Counter
    ACCESS read-only
    STATUS mandatory
    DESCRIPTION
        "Number of TCP embryonic connections dropped.  The embryonic
         drop counter tells the user how many times the connections
         did not go through because of not receiving a reply for the
         SYN packets - which gives a measure for the quality of the
         path between the two peers."
    ::= { cftIfTcpExtEntry 1 }

cftIfTcpSegsTryToGetRTT OBJECT-TYPE
    SYNTAX Counter
    ACCESS read-only
    STATUS mandatory
    DESCRIPTION
        "Number of TCP segments which try to get RTT (Round Trip Time)."
    ::= { cftIfTcpExtEntry 2 }

cftIfTcpSegsSucceedToGetRTT OBJECT-TYPE
    SYNTAX Counter
    ACCESS read-only
    STATUS mandatory
    DESCRIPTION
        "Number of TCP segments which get RTT (Round Trip Time)
         successfully."
    ::= { cftIfTcpExtEntry 3 }

cftIfTcpDelayedAcksSent OBJECT-TYPE
    SYNTAX Counter
    ACCESS read-only
    STATUS mandatory
    DESCRIPTION
        "number of TCP delayed ACKs sent."
    REFERENCE
        "RFC 1072, TCP Extensions for Long-Delay Paths,
         Section 4.2 (A)"
    ::= { cftIfTcpExtEntry 4 }

cftIfTcpConnDroppedRxTimeout OBJECT-TYPE
    SYNTAX Counter
    ACCESS read-only
    STATUS mandatory
    DESCRIPTION
        "Number of TCP connections dropped because of receiving
         timeout."
    ::= { cftIfTcpExtEntry 5 }

cftIfTcpRetransmitTimeout OBJECT-TYPE
    SYNTAX Counter
    ACCESS read-only
    STATUS mandatory
    DESCRIPTION
        "Number of TCP retransmitting timeouts."
    ::= { cftIfTcpExtEntry 6 }

cftIfTcpPersistTimeout OBJECT-TYPE
    SYNTAX Counter
    ACCESS read-only
    STATUS mandatory
    DESCRIPTION
        "Number of TCP persisting timeouts."
    ::= { cftIfTcpExtEntry 7 }

cftIfTcpKeepaliveTimeout OBJECT-TYPE
    SYNTAX Counter
    ACCESS read-only
    STATUS mandatory
    DESCRIPTION
        "Number of TCP keepalive timeouts."
    ::= { cftIfTcpExtEntry 8 }

cftIfTcpKeepaliveProbesSent OBJECT-TYPE
    SYNTAX Counter
    ACCESS read-only
    STATUS mandatory
    DESCRIPTION
        "Number of TCP keep-alive probes sent."
    ::= { cftIfTcpExtEntry 9 }

cftIfTcpConnDroppedInKeepalive OBJECT-TYPE
    SYNTAX Counter
    ACCESS read-only
    STATUS mandatory
    DESCRIPTION
        "Number of TCP connections dropped in keepalive."
    ::= { cftIfTcpExtEntry 10 }

cftIfTcpConnDroppedInPersist OBJECT-TYPE
    SYNTAX Counter
    ACCESS read-only
    STATUS mandatory
    DESCRIPTION
        "Number of TCP connections dropped in persisting."
    ::= { cftIfTcpExtEntry 11 }

cftIfTcpConnDrainedByNoMemory OBJECT-TYPE
    SYNTAX Counter
    ACCESS read-only
    STATUS mandatory
    DESCRIPTION
        "Number of TCP connections drained dut to memory shortage."
    ::= { cftIfTcpExtEntry 12 }

cftIfTcpAckOnlyPkts OBJECT-TYPE
    SYNTAX Counter
    ACCESS read-only
    STATUS mandatory
    DESCRIPTION
        "Number of TCP packets sent with only ACK flag on."
    ::= { cftIfTcpExtEntry 13 }

cftIfTcpTxWindowProbes OBJECT-TYPE
    SYNTAX Counter
    ACCESS read-only
    STATUS mandatory
    DESCRIPTION
        "Number of TCP window probing packets sent."
    ::= { cftIfTcpExtEntry 14 }

cftIfTcpTxURGPkts OBJECT-TYPE
    SYNTAX Counter
    ACCESS read-only
    STATUS mandatory
    DESCRIPTION
        "Number of TCP packets sent with URG flag on."
    ::= { cftIfTcpExtEntry 15 }

cftIfTcpTxWindowUpdateOnlyPkts OBJECT-TYPE
    SYNTAX Counter
    ACCESS read-only
    STATUS mandatory
    DESCRIPTION
        "Number of TCP packets sent only for only updating the window
         size."
    ::= { cftIfTcpExtEntry 16 }

cftIfTcpTxControlPkts OBJECT-TYPE
    SYNTAX Counter
    ACCESS read-only
    STATUS mandatory
    DESCRIPTION
        "Number of TCP packets sent with SYN, FIN, or RST flags on."
    ::= { cftIfTcpExtEntry 17 }

cftIfTcpRxDroppedByNoMemory OBJECT-TYPE
    SYNTAX Counter
    ACCESS read-only
    STATUS mandatory
    DESCRIPTION
        "Number of receiving TCP packets dropped because of lacking of
         memory."
    ::= { cftIfTcpExtEntry 18 }

cftIfTcpRxTooShort OBJECT-TYPE
    SYNTAX Counter
    ACCESS read-only
    STATUS mandatory
    DESCRIPTION
        "Number of TCP packets received with too short length."
    ::= { cftIfTcpExtEntry 19 }

cftIfTcpRxDupOnlyPkts OBJECT-TYPE
    SYNTAX Counter
    ACCESS read-only
    STATUS mandatory
    DESCRIPTION
        "Number of duplicated TCP packets received."
    ::= { cftIfTcpExtEntry 20 }

cftIfTcpRxDupOnlyOctets OBJECT-TYPE
    SYNTAX Counter
    ACCESS read-only
    STATUS mandatory
    DESCRIPTION
        "Number of duplicated TCP octets received."
    ::= { cftIfTcpExtEntry 21 }

cftIfTcpRxDupDataPkts OBJECT-TYPE
    SYNTAX Counter
    ACCESS read-only
    STATUS mandatory
    DESCRIPTION
        "Number of TCP packets received with duplicated data."
    ::= { cftIfTcpExtEntry 22 }

cftIfTcpRxDupOctetsInPartDupPkts OBJECT-TYPE
    SYNTAX Counter
    ACCESS read-only
    STATUS mandatory
    DESCRIPTION
        "Number of duplicated TCP octets received in part of duplicated
         packets."
    ::= { cftIfTcpExtEntry 23 }

cftIfTcpRxDataAfterWindowPkts OBJECT-TYPE
    SYNTAX Counter
    ACCESS read-only
    STATUS mandatory
    DESCRIPTION
        "Number of TCP packets with data received after window."
    ::= { cftIfTcpExtEntry 24 }

cftIfTcpRxDataAfterWindowOctets OBJECT-TYPE
    SYNTAX Counter
    ACCESS read-only
    STATUS mandatory
    DESCRIPTION
        "Number of TCP octets with data received after window."
    ::= { cftIfTcpExtEntry 25 }

cftIfTcpRxPktsAfterConnClose OBJECT-TYPE
    SYNTAX Counter
    ACCESS read-only
    STATUS mandatory
    DESCRIPTION
        "Number of TCP packets received after the connection close."
    ::= { cftIfTcpExtEntry 26 }

cftIfTcpRxWindowProbesPkts OBJECT-TYPE
    SYNTAX Counter
    ACCESS read-only
    STATUS mandatory
    DESCRIPTION
        "Number of TCP window probing packets received."
    ::= { cftIfTcpExtEntry 27 }

cftIfTcpRxDupAcks OBJECT-TYPE
    SYNTAX Counter
    ACCESS read-only
    STATUS mandatory
    DESCRIPTION
        "Number of duplicated TCP acknowledge packets received."
    ::= { cftIfTcpExtEntry 28 }

cftIfTcpRxAcksForUnsentData OBJECT-TYPE
    SYNTAX Counter
    ACCESS read-only
    STATUS mandatory
    DESCRIPTION
        "Number of TCP acknowledge packets received for unsent data."
    ::= { cftIfTcpExtEntry 29 }

cftIfTcpRxAcksPkts OBJECT-TYPE
    SYNTAX Counter
    ACCESS read-only
    STATUS mandatory
    DESCRIPTION
        "Number of TCP packets received with ACK flag on."
    ::= { cftIfTcpExtEntry 30 }

cftIfTcpOctetAckedByRxAcks OBJECT-TYPE
    SYNTAX Counter
    ACCESS read-only
    STATUS mandatory
    DESCRIPTION
        "Number of TCP octets received with ACK flag on."
    ::= { cftIfTcpExtEntry 31 }

cftIfTcpRxWindowUpdatePkts OBJECT-TYPE
    SYNTAX Counter
    ACCESS read-only
    STATUS mandatory
    DESCRIPTION
        "Number of TCP packets received for updating window size."
    ::= { cftIfTcpExtEntry 32 }

cftIfTcpSegDropByPAWS OBJECT-TYPE
    SYNTAX Counter
    ACCESS read-only
    STATUS mandatory
    DESCRIPTION
        "Number of TCP segments dropped due to Protection Against
         Wrapped Sequence Number (PAWS) algorithm."
    REFERENCE
        "RFC 2883, An Extension to the Selective Acknowledgement (SACK)
         Option for TCP"
    ::= { cftIfTcpExtEntry 33 }

cftIfTcpTxSackFackDataPkts OBJECT-TYPE
    SYNTAX Counter
    ACCESS read-only
    STATUS mandatory
    DESCRIPTION
        "Number of TCP data packets sent with SACK option on."
    REFERENCE
        "RFC 2018, TCP Selective Acknowledgment Options
         RFC 2883, An Extension to the Selective Acknowledgement (SACK)
         Option for TCP"
    ::= { cftIfTcpExtEntry 34 }

cftIfTcpTxSackFackDataOctets OBJECT-TYPE
    SYNTAX Counter
    ACCESS read-only
    STATUS mandatory
    DESCRIPTION
        "Number of TCP data octets sent with SACK option on."
    ::= { cftIfTcpExtEntry 35 }

cftIfTcpRetxSackFackDataPkts OBJECT-TYPE
    SYNTAX Counter
    ACCESS read-only
    STATUS mandatory
    DESCRIPTION
        "Number of TCP data packets re-sent with SACK option on."
    ::= { cftIfTcpExtEntry 36 }

cftIfTcpRetxSackFackDataOctets OBJECT-TYPE
    SYNTAX Counter
    ACCESS read-only
    STATUS mandatory
    DESCRIPTION
        "Number of TCP data octets re-sent with SACK option on."
    ::= { cftIfTcpExtEntry 37 }

cftIfTcpSackFackConnClosed OBJECT-TYPE
    SYNTAX Counter
    ACCESS read-only
    STATUS mandatory
    DESCRIPTION
        "Number of TCP connections closed with SACK option on."
    ::= { cftIfTcpExtEntry 38 }

cftIfTcpRetxSackFackTimeouts OBJECT-TYPE
    SYNTAX Counter
    ACCESS read-only
    STATUS mandatory
    DESCRIPTION
        "Number of TCP timeouts re-sent with SACK option on."
    ::= { cftIfTcpExtEntry 39 }

cftIfTcpHdrPredictOkForAcks OBJECT-TYPE
    SYNTAX Counter
    ACCESS read-only
    STATUS mandatory
    DESCRIPTION
        "Number of times the header predication code is hit by TCP
         packets with ACK option on."
    ::= { cftIfTcpExtEntry 40 }

cftIfTcpHdrPredictOkForDataPkts OBJECT-TYPE
    SYNTAX Counter
    ACCESS read-only
    STATUS mandatory
    DESCRIPTION
        "Number of times the header predication code is hit by the
         packets of FC Data TCP connection."
    ::= { cftIfTcpExtEntry 41 }

cftTcpTunnelConfigGroup OBJECT IDENTIFIER ::= { cftTunnelMIBGroups 1 }
-- OBJECT-GROUP
--  Status
--    mandatory
--  Descr
--    The collection of objects which are used to describe and
--     configure Fiber Channal TCP tunneling.
--  objects
--    cftMaxTcpTunnels, cftTcpTunnelSrcIpType, cftTcpTunnelSrcIp, 
--    cftTcpTunnelDestIpType, cftTcpTunnelDestIp, 
--    cftTcpTunnelCmdSrcPort, cftTcpTunnelCmdDestPort, 
--    cftTcpTunnelDataSrcPort, cftTcpTunnelDataDestPort, 
--    cftTcpTunnelCmdMWS, cftTcpTunnelDataMWS, 
--    cftTcpTunnelCmdKeepAliveTime, cftTcpTunnelDataKeepAliveTime, 
--    cftTcpTunnelCmdSelectiveAck, cftTcpTunnelDataSelectiveAck, 
--    cftTcpTunnelCmdConnectStatus, cftTcpTunnelDataConnectStatus, 
--    cftTcpTunnelOperStatus, cftTcpTunnelStatus

cftTcpTunnelStatGroup OBJECT IDENTIFIER ::= { cftTunnelMIBGroups 2 }
-- OBJECT-GROUP
--  Status
--    mandatory
--  Descr
--    The collection of objects which are used to monitor the traffic
--     of TCP tunnels.
--  objects
--    cftTcpTunnelCmdRxSegmentOctets, 
--    cftTcpTunnelDataRxSegmentOctets, 
--    cftTcpTunnelCmdRxPrestufOctets, 
--    cftTcpTunnelDataRxPrestufOctets, 
--    cftTcpTunnelCmdRxPoststufOctets, 
--    cftTcpTunnelDataRxPoststufOctets, cftTcpTunnelCmdTxOctets, 
--    cftTcpTunnelDataTxOctets, cftTcpTunnelCmdTxPkts, 
--    cftTcpTunnelDataTxPkts, cftTcpTunnelCmdTxDrops, 
--    cftTcpTunnelDataTxDrops

cftIfTcpGroup OBJECT IDENTIFIER ::= { cftTunnelMIBGroups 3 }
-- OBJECT-GROUP
--  Status
--    mandatory
--  Descr
--    The collection of objects which are used to monitor the status
--     and statistics information of the TCP stack for the tunneled
--     Fiber Channel interface.
--  objects
--    cftIfTcpConnInit, cftIfTcpConnAccepted, 
--    cftIfTcpConnEstablished, cftIfTcpConnDrops, 
--    cftIfTcpConnClosed, cftIfTcpTxPkts, cftIfTcpTxDataPkts, 
--    cftIfTcpTxDataOctets, cftIfTcpRetxDataPkts, 
--    cftIfTcpRetxDataOctets, cftIfTcpRxPkts, 
--    cftIfTcpRxInSequencePkts, cftIfTcpRxInSequenceOctets, 
--    cftIfTcpRxCcksumErrPkts, cftIfTcpRxBadOffsetPkts, 
--    cftIfTcpRxOutOfOrderPkts, cftIfTcpRxOutOfOrderOctets

cftIfTcpExtGroup OBJECT IDENTIFIER ::= { cftTunnelMIBGroups 4 }
-- OBJECT-GROUP
--  Status
--    mandatory
--  Descr
--    The collection of objects which are used to monitor the status
--     and statistics information of the TCP stack for the tunneled
--     Fiber Channel interface.  This extension group provides more
--     detail and specific statistics information that not all the
--     TCP stack will support.
--  objects
--    cftIfTcpEmbryonicConnDrops, cftIfTcpSegsTryToGetRTT, 
--    cftIfTcpSegsSucceedToGetRTT, cftIfTcpDelayedAcksSent, 
--    cftIfTcpConnDroppedRxTimeout, cftIfTcpRetransmitTimeout, 
--    cftIfTcpPersistTimeout, cftIfTcpKeepaliveTimeout, 
--    cftIfTcpKeepaliveProbesSent, cftIfTcpConnDroppedInKeepalive, 
--    cftIfTcpConnDroppedInPersist, cftIfTcpConnDrainedByNoMemory, 
--    cftIfTcpAckOnlyPkts, cftIfTcpTxWindowProbes, 
--    cftIfTcpTxURGPkts, cftIfTcpTxWindowUpdateOnlyPkts, 
--    cftIfTcpTxControlPkts, cftIfTcpRxDroppedByNoMemory, 
--    cftIfTcpRxTooShort, cftIfTcpRxDupOnlyPkts, 
--    cftIfTcpRxDupOnlyOctets, cftIfTcpRxDupDataPkts, 
--    cftIfTcpRxDupOctetsInPartDupPkts, 
--    cftIfTcpRxDataAfterWindowPkts, 
--    cftIfTcpRxDataAfterWindowOctets, cftIfTcpRxPktsAfterConnClose, 
--    cftIfTcpRxWindowProbesPkts, cftIfTcpRxDupAcks, 
--    cftIfTcpRxAcksForUnsentData, cftIfTcpRxAcksPkts, 
--    cftIfTcpOctetAckedByRxAcks, cftIfTcpRxWindowUpdatePkts, 
--    cftIfTcpSegDropByPAWS, cftIfTcpTxSackFackDataPkts, 
--    cftIfTcpTxSackFackDataOctets, cftIfTcpRetxSackFackDataPkts, 
--    cftIfTcpRetxSackFackDataOctets, cftIfTcpSackFackConnClosed, 
--    cftIfTcpRetxSackFackTimeouts, cftIfTcpHdrPredictOkForAcks, 
--    cftIfTcpHdrPredictOkForDataPkts

cftTunnelMIBComplianceV01 OBJECT IDENTIFIER ::= { cftTunnelMIBCompliances 1 }
-- MODULE-COMPLIANCE
--  Status
--    mandatory
--  Descr
--    A Fiber Channel tunneling implementation that lists the
--     groups supporting configuration tunnels and statistics
--     information of the tunnels.
--  Module
--    >>current<<
--   MandGroup
--    cftTcpTunnelConfigGroup
--   ObjVar
--    cftTcpTunnelSrcIpType
--   ObjVar
--    cftTcpTunnelDestIpType
--   ObjVar
--    cftTcpTunnelCmdSelectiveAck


END
