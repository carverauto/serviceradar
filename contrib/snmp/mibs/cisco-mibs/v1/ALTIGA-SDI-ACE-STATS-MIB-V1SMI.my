-- MIB file created 03-Dec-2002 13:08:52, by
--   SMICng version 2.2.11-beta(PRO)(Solaris), January 20, 2001. Enterprise key cisco.com

ALTIGA-SDI-ACE-STATS-MIB DEFINITIONS ::= BEGIN

-- From file: "ALTIGA-SDI-ACE-STATS-MIB.my"
-- Compile options "4 7 F H N W 03 06 0B 0G 0N 0T"

IMPORTS
    alACEServerStats, alACEServerGroup
            FROM ALTIGA-MIB
    alACEServerMibModule
            FROM ALTIGA-GLOBAL-REG
    Counter, Gauge, IpAddress
            FROM RFC1155-SMI
    OBJECT-TYPE
            FROM RFC-1212;

altigaACEStatsMibModule OBJECT IDENTIFIER ::= { alACEServerMibModule 1 }
-- MODULE-IDENTITY
--  LastUpdated
--    200209051300Z
--  OrgName
--    Cisco Systems, Inc.
--  ContactInfo
--    Cisco Systems 
--     170 W Tasman Drive 
--     San Jose, CA  95134 
--     USA 
--    
--     Tel: +1 800 553-NETS 
--     E-mail: cs-cvpn3000@cisco.com
--  Descr
--    The Altiga SDI ACE Server Statistics MIB models counters and objects that are 
--     of management interest for SDI ACE Server. 
--     
--     Acronyms 
--     The following acronyms are used in this document: 
--    
--       ACE:        Access Control Encryption 
--    
--       MIB:        Management Information Base 
--    
--       PIN:        Personal Identification Number 
--    
--       SDI:        Security Dynamics Technologies, Inc 
--     
--  RevDate
--    200209051300Z
--  RevDescr
--    Added module compliance.
--  RevDate
--    200207100000Z
--  RevDescr
--    Updated with new header

alCfgACEGlobal  OBJECT IDENTIFIER ::= { alACEServerStats 1 }
altigaACEStatsMibConformance OBJECT IDENTIFIER ::= { altigaACEStatsMibModule 1 }
altigaACEStatsMibCompliances OBJECT IDENTIFIER ::= { altigaACEStatsMibConformance 1 }

alACEServerTable OBJECT-TYPE
    SYNTAX SEQUENCE OF AlACEServerEntry
    ACCESS not-accessible
    STATUS mandatory
    DESCRIPTION
        "The list of authentication servers."
    ::= { alACEServerStats 2 }

alACEServerEntry OBJECT-TYPE
    SYNTAX AlACEServerEntry
    ACCESS not-accessible
    STATUS mandatory
    DESCRIPTION
        "An entry in the alAuthServerTable."
    INDEX { alACEPrimaryIndex, alACEServerIndex }
    ::= { alACEServerTable 1 }

AlACEServerEntry ::= SEQUENCE {
    alACEPrimaryIndex INTEGER,
    alACEServerIndex INTEGER,
    alACEServerPriority INTEGER,
    alACEServerAddress IpAddress,
    alACEServerPort INTEGER,
    alACEServerRetries Counter,
    alACEServerTimeout Counter,
    alACEServerGroupId Gauge,
    alACEServerAuthSuccesses Counter,
    alACEServerAuthFailures Counter,
    alACEServerBadCodeSent Counter,
    alACEServerBadPinSent Counter
    }

alACEPrimaryIndex OBJECT-TYPE
    SYNTAX INTEGER(0..2147483647)
    ACCESS read-only
    STATUS mandatory
    DESCRIPTION
        "The index of the configured primary server"
    ::= { alACEServerEntry 1 }

alACEServerIndex OBJECT-TYPE
    SYNTAX INTEGER(0..10)
    ACCESS read-only
    STATUS mandatory
    DESCRIPTION
        "The index of this server into the server list"
    ::= { alACEServerEntry 2 }

alACEServerPriority OBJECT-TYPE
    SYNTAX INTEGER(0..10)
    ACCESS read-only
    STATUS mandatory
    DESCRIPTION
        "The priority as computed by loadbalancing"
    ::= { alACEServerEntry 3 }

alACEServerAddress OBJECT-TYPE
    SYNTAX IpAddress
    ACCESS read-only
    STATUS mandatory
    DESCRIPTION
        "Resolved address from the ACE Server."
    ::= { alACEServerEntry 4 }

alACEServerPort OBJECT-TYPE
    SYNTAX INTEGER(0..65535)
    ACCESS read-only
    STATUS mandatory
    DESCRIPTION
        "Port over ride for this entry"
    ::= { alACEServerEntry 5 }

alACEServerRetries OBJECT-TYPE
    SYNTAX Counter
    ACCESS read-only
    STATUS mandatory
    DESCRIPTION
        "Number of retries for this server."
    ::= { alACEServerEntry 6 }

alACEServerTimeout OBJECT-TYPE
    SYNTAX Counter
    ACCESS read-only
    STATUS mandatory
    DESCRIPTION
        "Timeout, in seconds to access this server."
    ::= { alACEServerEntry 7 }

alACEServerGroupId OBJECT-TYPE
    SYNTAX Gauge
    ACCESS read-only
    STATUS mandatory
    DESCRIPTION
        "The group that this authentication server entry belongs to."
    ::= { alACEServerEntry 8 }

alACEServerAuthSuccesses OBJECT-TYPE
    SYNTAX Counter
    ACCESS read-only
    STATUS mandatory
    DESCRIPTION
        "number of auth successes."
    ::= { alACEServerEntry 9 }

alACEServerAuthFailures OBJECT-TYPE
    SYNTAX Counter
    ACCESS read-only
    STATUS mandatory
    DESCRIPTION
        "number of failures for this server."
    ::= { alACEServerEntry 10 }

alACEServerBadCodeSent OBJECT-TYPE
    SYNTAX Counter
    ACCESS read-only
    STATUS mandatory
    DESCRIPTION
        "number of Bad Code sent to  this server."
    ::= { alACEServerEntry 11 }

alACEServerBadPinSent OBJECT-TYPE
    SYNTAX Counter
    ACCESS read-only
    STATUS mandatory
    DESCRIPTION
        "number of Bad Pin sent to this server."
    ::= { alACEServerEntry 12 }

altigaACEServerGroup OBJECT IDENTIFIER ::= { alACEServerGroup 1 }
-- OBJECT-GROUP
--  Status
--    mandatory
--  Descr
--    The objects for ACE-STATS.
--  objects
--    alACEPrimaryIndex, alACEServerIndex, alACEServerPriority, 
--    alACEServerAddress, alACEServerPort, alACEServerRetries, 
--    alACEServerTimeout, alACEServerGroupId, 
--    alACEServerAuthSuccesses, alACEServerAuthFailures, 
--    alACEServerBadCodeSent, alACEServerBadPinSent

altigaACEStatsMibCompliance OBJECT IDENTIFIER ::= { altigaACEStatsMibCompliances 1 }
-- MODULE-COMPLIANCE
--  Status
--    mandatory
--  Descr
--    The compliance statement for agents which  
--     implement the Altiga ACE Server Statistics MIB.
--  Module
--    >>current<<
--   MandGroup
--    altigaACEServerGroup


END
