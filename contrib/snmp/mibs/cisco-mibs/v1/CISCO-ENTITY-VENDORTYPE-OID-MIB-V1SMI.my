-- MIB file created 23-Dec-2016 01:10:56, by
--   SMICng version 2.2.11-beta(PRO)(Solaris), January 20, 2001. Enterprise key cisco.com

CISCO-ENTITY-VENDORTYPE-OID-MIB DEFINITIONS ::= BEGIN

-- From file: "CISCO-ENTITY-VENDORTYPE-OID-MIB.my"
-- Compile options "4 7 F H N W 03 06 0B 0G 0N 0T"

IMPORTS
    ciscoModules
            FROM CISCO-SMI;

ciscoEntityVendortypeOIDMIB OBJECT IDENTIFIER ::= { ciscoModules 3 }
-- MODULE-IDENTITY
--  LastUpdated
--    201612230000Z
--  OrgName
--    Cisco Systems, Inc.
--  ContactInfo
--           Cisco Systems
--     Customer Service
--    
--    Postal: 170 W Tasman Drive
--     San Jose, CA  95134
--     USA
--    
--       Tel: +1 800 553-NETS
--    
--    E-mail: cs-snmp@cisco.com
--  Descr
--    This module defines the object identifiers that are
--    assigned to various components on cisco products,
--    which are used by the entPhysicalTable of the ENTITY-MIB
--    to uniquely identify the type of each physical entry.
--  RevDate
--    201412090000Z
--  RevDescr
--    Added following OIDs:
--                   cevChassisME6340ACA, cevChassisME6340DCA,
--                   cevChassisME6340DCB, cevChassisCat296024TT,
--                   cevChassisCat296048TT, cevContainerFabric13Slot,
--                   cevPowerSupply6340PWRDC, cevPowerSupply6340PWRAC,
--                   cevFanTrayUbr10012, cevPowerSupplyUbr10012AC,
--                   cevPowerSupplyUbr10012DC, cevVwic2T1E1Ran,
--                   cevModuleCat296024TT,cevModuleCat296048TT
--                   cevCat6kMsfc2a, cevCat6kWs6340Sup,
--                   cevCat6kWs6340LcA, cevCat6kWs6340LcB,
--                   cevPortAdslAnnexA, cevPortAdslAnnexB
--  RevDate
--    200504280930Z
--  RevDescr
--    Added following OIDs:
--                   cevUbrTccPlus
--  RevDate
--    200504181930Z
--  RevDescr
--    Added following OIDs:
--    cevChassisCat6kMsfc2a, cevChassisCe611K9
--    cevContainer9513RearFanBay, cevNme16Es1GeNoPwr,
--    cevNmeX24Es1GeNoPwr, cevNmeXd24Es2StNoPwr,
--    cevNmeXd48Es2GeNoPwr, cevCpuCat6kMsfc2a,
--    cevGsrCsc12404B, cevGsrCsc12406B,
--    cevGsrCsc12410B, cevGsrCsc12416B,
--    cevONS1553010G4ChASp, cevONS1553010G4ChBSp,
--    cevONS1553010G4ChCSp, cevONS1553010G4ChDSp,
--    cevONS1553010G4ChESp, cevONS1553010G4ChFSp,
--    cevONS1553010G4ChGSp, cevONS1553010G4ChHSp,
--    cevONS1553010G4ChA, cevONS1553010G4ChB,
--    cevONS1553010G4ChC, cevONS1553010G4ChD,
--    cevONS1553010G4ChE, cevONS1553010G4ChF,
--    cevONS1553010G4ChG, cevONS1553010G4ChH,
--    cevONS1553010G32ChSp, cevONS1553010G32Ch,
--    cevSFPOc3smsr, cevSFPOc12smsr, cevSFPOc48mm.
--  RevDate
--    200204051400Z
--  RevDescr
--    CANA Assignments.
--  RevDate
--    9708051930Z
--  RevDescr
--    Miscellaneous updates.

cevMIBObjects   OBJECT IDENTIFIER ::= { ciscoEntityVendortypeOIDMIB 1 }
cevOther        OBJECT IDENTIFIER ::= { cevMIBObjects 1 }
cevOtherUnknownCard OBJECT IDENTIFIER ::= { cevOther 1 }
cevOtherMoH     OBJECT IDENTIFIER ::= { cevOther 2 }
cevNmeApaLink   OBJECT IDENTIFIER ::= { cevOther 3 }
cevOtherSce8000Scm OBJECT IDENTIFIER ::= { cevOther 5 }
cevOtherSce8000Sip OBJECT IDENTIFIER ::= { cevOther 6 }
cevOtherCscLink OBJECT IDENTIFIER ::= { cevOther 8 }
cevOtherPHY     OBJECT IDENTIFIER ::= { cevOther 9 }
cevAcceleratorAsa5506 OBJECT IDENTIFIER ::= { cevOther 10 }
cevAcceleratorAsa5506W OBJECT IDENTIFIER ::= { cevOther 11 }
cevAcceleratorAsa5508 OBJECT IDENTIFIER ::= { cevOther 12 }
cevAcceleratorAsa5506K7 OBJECT IDENTIFIER ::= { cevOther 13 }
cevAcceleratorAsa5508K7 OBJECT IDENTIFIER ::= { cevOther 14 }
cevAcceleratorAsa5506H OBJECT IDENTIFIER ::= { cevOther 15 }
cevAcceleratorAsa5516 OBJECT IDENTIFIER ::= { cevOther 16 }
cevUnknown      OBJECT IDENTIFIER ::= { cevMIBObjects 2 }
cevChassis      OBJECT IDENTIFIER ::= { cevMIBObjects 3 }
cevChassisUnknown OBJECT IDENTIFIER ::= { cevChassis 1 }
cevChassis2000  OBJECT IDENTIFIER ::= { cevChassis 2 }
cevChassis2500  OBJECT IDENTIFIER ::= { cevChassis 3 }
cevChassis2501  OBJECT IDENTIFIER ::= { cevChassis 4 }
cevChassis2502  OBJECT IDENTIFIER ::= { cevChassis 5 }
cevChassis2503  OBJECT IDENTIFIER ::= { cevChassis 6 }
cevChassis2504  OBJECT IDENTIFIER ::= { cevChassis 7 }
cevChassis2505  OBJECT IDENTIFIER ::= { cevChassis 8 }
cevChassis2506  OBJECT IDENTIFIER ::= { cevChassis 9 }
cevChassis2507  OBJECT IDENTIFIER ::= { cevChassis 10 }
cevChassis2508  OBJECT IDENTIFIER ::= { cevChassis 11 }
cevChassis2509  OBJECT IDENTIFIER ::= { cevChassis 12 }
cevChassis2510  OBJECT IDENTIFIER ::= { cevChassis 13 }
cevChassis2511  OBJECT IDENTIFIER ::= { cevChassis 14 }
cevChassis2512  OBJECT IDENTIFIER ::= { cevChassis 15 }
cevChassis2513  OBJECT IDENTIFIER ::= { cevChassis 16 }
cevChassis2514  OBJECT IDENTIFIER ::= { cevChassis 17 }
cevChassis2515  OBJECT IDENTIFIER ::= { cevChassis 18 }
cevChassis2516  OBJECT IDENTIFIER ::= { cevChassis 19 }
cevChassis2517  OBJECT IDENTIFIER ::= { cevChassis 20 }
cevChassis2518  OBJECT IDENTIFIER ::= { cevChassis 21 }
cevChassis2519  OBJECT IDENTIFIER ::= { cevChassis 22 }
cevChassis2520  OBJECT IDENTIFIER ::= { cevChassis 23 }
cevChassis2521  OBJECT IDENTIFIER ::= { cevChassis 24 }
cevChassis2522  OBJECT IDENTIFIER ::= { cevChassis 25 }
cevChassis2523  OBJECT IDENTIFIER ::= { cevChassis 26 }
cevChassis2524  OBJECT IDENTIFIER ::= { cevChassis 27 }
cevChassis2525  OBJECT IDENTIFIER ::= { cevChassis 28 }
cevChassis3000  OBJECT IDENTIFIER ::= { cevChassis 29 }
cevChassis3104  OBJECT IDENTIFIER ::= { cevChassis 30 }
cevChassis3204  OBJECT IDENTIFIER ::= { cevChassis 31 }
cevChassisIGS   OBJECT IDENTIFIER ::= { cevChassis 32 }
cevChassis2501LANFRADFX OBJECT IDENTIFIER ::= { cevChassis 33 }
cevChassis2501FRADFX OBJECT IDENTIFIER ::= { cevChassis 34 }
cevChassis2502LANFRADFX OBJECT IDENTIFIER ::= { cevChassis 35 }
cevChassisWSX3011 OBJECT IDENTIFIER ::= { cevChassis 36 }
cevChassisAccessProEC OBJECT IDENTIFIER ::= { cevChassis 37 }
cevChassisAccessProRC OBJECT IDENTIFIER ::= { cevChassis 38 }
cevChassisWSX5301 OBJECT IDENTIFIER ::= { cevChassis 39 }
cevChassisAS2509RJ OBJECT IDENTIFIER ::= { cevChassis 40 }
cevChassisAS2511RJ OBJECT IDENTIFIER ::= { cevChassis 41 }
cevChassis3800  OBJECT IDENTIFIER ::= { cevChassis 42 }
cevChassis3620  OBJECT IDENTIFIER ::= { cevChassis 43 }
cevChassis3640  OBJECT IDENTIFIER ::= { cevChassis 44 }
cevChassis7204  OBJECT IDENTIFIER ::= { cevChassis 45 }
cevChassis7206  OBJECT IDENTIFIER ::= { cevChassis 46 }
cevChassisAS5300 OBJECT IDENTIFIER ::= { cevChassis 47 }
cevChassisAs5800RS OBJECT IDENTIFIER ::= { cevChassis 49 }
cevChassisAs5800DS OBJECT IDENTIFIER ::= { cevChassis 50 }
cevChassis7202  OBJECT IDENTIFIER ::= { cevChassis 51 }
cevChassisRpm   OBJECT IDENTIFIER ::= { cevChassis 52 }
cevChassis1710  OBJECT IDENTIFIER ::= { cevChassis 53 }
cevChassis1720  OBJECT IDENTIFIER ::= { cevChassis 54 }
cevChassisCat8540Msr OBJECT IDENTIFIER ::= { cevChassis 55 }
cevChassisCat8540Csr OBJECT IDENTIFIER ::= { cevChassis 56 }
cevChassisUbr7246 OBJECT IDENTIFIER ::= { cevChassis 57 }
cevChassis7576  OBJECT IDENTIFIER ::= { cevChassis 58 }
cevChassis3660  OBJECT IDENTIFIER ::= { cevChassis 59 }
cevChassis1401  OBJECT IDENTIFIER ::= { cevChassis 60 }
cevChassis2613  OBJECT IDENTIFIER ::= { cevChassis 61 }
cevChassis2610  OBJECT IDENTIFIER ::= { cevChassis 62 }
cevChassis2612  OBJECT IDENTIFIER ::= { cevChassis 63 }
cevChassis2611  OBJECT IDENTIFIER ::= { cevChassis 64 }
cevChassis2620  OBJECT IDENTIFIER ::= { cevChassis 65 }
cevChassis2621  OBJECT IDENTIFIER ::= { cevChassis 66 }
cevChassisCat8510Csr OBJECT IDENTIFIER ::= { cevChassis 67 }
cevChassisUbr7223 OBJECT IDENTIFIER ::= { cevChassis 68 }
cevChassis6400Nrp OBJECT IDENTIFIER ::= { cevChassis 69 }
cevChassis801   OBJECT IDENTIFIER ::= { cevChassis 70 }
cevChassis802   OBJECT IDENTIFIER ::= { cevChassis 71 }
cevChassis803   OBJECT IDENTIFIER ::= { cevChassis 72 }
cevChassis804   OBJECT IDENTIFIER ::= { cevChassis 73 }
cevChassis7206Vxr OBJECT IDENTIFIER ::= { cevChassis 74 }
cevChassis7204Vxr OBJECT IDENTIFIER ::= { cevChassis 75 }
cevChassis1750  OBJECT IDENTIFIER ::= { cevChassis 76 }
cevChassisCat2924XLv OBJECT IDENTIFIER ::= { cevChassis 77 }
cevChassisCat2924CXLv OBJECT IDENTIFIER ::= { cevChassis 78 }
cevChassisCat2912XL OBJECT IDENTIFIER ::= { cevChassis 79 }
cevChassisCat2924MXL OBJECT IDENTIFIER ::= { cevChassis 80 }
cevChassisCat2912MfXL OBJECT IDENTIFIER ::= { cevChassis 81 }
cevChassis1538M OBJECT IDENTIFIER ::= { cevChassis 82 }
cevChassis1548M OBJECT IDENTIFIER ::= { cevChassis 83 }
cevChassisFasthub100 OBJECT IDENTIFIER ::= { cevChassis 84 }
cevChassisPIXFirewall OBJECT IDENTIFIER ::= { cevChassis 85 }
cevChassisMGX8850 OBJECT IDENTIFIER ::= { cevChassis 86 }
cevChassisMGX8820 OBJECT IDENTIFIER ::= { cevChassis 87 }
cevChassisCat8510Msr OBJECT IDENTIFIER ::= { cevChassis 88 }
cevChassisCat8515Msr OBJECT IDENTIFIER ::= { cevChassis 89 }
cevChassisIGX8410 OBJECT IDENTIFIER ::= { cevChassis 90 }
cevChassisIGX8420 OBJECT IDENTIFIER ::= { cevChassis 91 }
cevChassisIGX8430 OBJECT IDENTIFIER ::= { cevChassis 92 }
cevChassisIGX8450 OBJECT IDENTIFIER ::= { cevChassis 93 }
cevChassisBPX8620 OBJECT IDENTIFIER ::= { cevChassis 95 }
cevChassisBPX8650 OBJECT IDENTIFIER ::= { cevChassis 96 }
cevChassisBPX8680 OBJECT IDENTIFIER ::= { cevChassis 97 }
cevChassisCacheEngine OBJECT IDENTIFIER ::= { cevChassis 98 }
cevChassisCat6000 OBJECT IDENTIFIER ::= { cevChassis 99 }
cevChassisMC3810 OBJECT IDENTIFIER ::= { cevChassis 100 }
cevChassisIGXSes OBJECT IDENTIFIER ::= { cevChassis 102 }
cevChassisLocalDirector OBJECT IDENTIFIER ::= { cevChassis 103 }
cevChassis805   OBJECT IDENTIFIER ::= { cevChassis 104 }
cevChassisCat3508GXL OBJECT IDENTIFIER ::= { cevChassis 105 }
cevChassisCat3512XL OBJECT IDENTIFIER ::= { cevChassis 106 }
cevChassisCat3524XL OBJECT IDENTIFIER ::= { cevChassis 107 }
cevChassisCat2908XL OBJECT IDENTIFIER ::= { cevChassis 108 }
cevChassisCat2916MXL OBJECT IDENTIFIER ::= { cevChassis 109 }
cevChassis1417  OBJECT IDENTIFIER ::= { cevChassis 111 }
cevChassisOpticalRegenerator OBJECT IDENTIFIER ::= { cevChassis 112 }
cevChassis6100  OBJECT IDENTIFIER ::= { cevChassis 113 }
cevChassis6130  OBJECT IDENTIFIER ::= { cevChassis 114 }
cevChassis6260  OBJECT IDENTIFIER ::= { cevChassis 115 }
cevChassisCat2924XL OBJECT IDENTIFIER ::= { cevChassis 116 }
cevChassisCat2924CXL OBJECT IDENTIFIER ::= { cevChassis 117 }
cevChassisUbr924 OBJECT IDENTIFIER ::= { cevChassis 118 }
cevChassisWsX6302Msm OBJECT IDENTIFIER ::= { cevChassis 119 }
cevChassisCat5kRsfc OBJECT IDENTIFIER ::= { cevChassis 120 }
cevChassis7120Quadt1 OBJECT IDENTIFIER ::= { cevChassis 122 }
cevChassis7120T3 OBJECT IDENTIFIER ::= { cevChassis 123 }
cevChassis7120E3 OBJECT IDENTIFIER ::= { cevChassis 124 }
cevChassis7120At3 OBJECT IDENTIFIER ::= { cevChassis 125 }
cevChassis7120Ae3 OBJECT IDENTIFIER ::= { cevChassis 126 }
cevChassis7120Smi3 OBJECT IDENTIFIER ::= { cevChassis 127 }
cevChassis7140Dualt3 OBJECT IDENTIFIER ::= { cevChassis 128 }
cevChassis7140Duale3 OBJECT IDENTIFIER ::= { cevChassis 129 }
cevChassis7140Dualat3 OBJECT IDENTIFIER ::= { cevChassis 130 }
cevChassis7140Dualae3 OBJECT IDENTIFIER ::= { cevChassis 131 }
cevChassis7140Dualmm3 OBJECT IDENTIFIER ::= { cevChassis 132 }
cevChassis827QuadV OBJECT IDENTIFIER ::= { cevChassis 133 }
cevChassisUbr7246Vxr OBJECT IDENTIFIER ::= { cevChassis 134 }
cevChassis12016 OBJECT IDENTIFIER ::= { cevChassis 136 }
cevChassisAs5400 OBJECT IDENTIFIER ::= { cevChassis 137 }
cevChassis7140Octt1 OBJECT IDENTIFIER ::= { cevChassis 138 }
cevChassis7140Dualfe OBJECT IDENTIFIER ::= { cevChassis 139 }
cevChassisCat3548XL OBJECT IDENTIFIER ::= { cevChassis 140 }
cevChassisCat6006 OBJECT IDENTIFIER ::= { cevChassis 141 }
cevChassisCat6009 OBJECT IDENTIFIER ::= { cevChassis 142 }
cevChassisCat6506 OBJECT IDENTIFIER ::= { cevChassis 143 }
cevChassisCat6509 OBJECT IDENTIFIER ::= { cevChassis 144 }
cevChassis827   OBJECT IDENTIFIER ::= { cevChassis 145 }
cevChassisAS5200 OBJECT IDENTIFIER ::= { cevChassis 146 }
cevChassis12008 OBJECT IDENTIFIER ::= { cevChassis 147 }
cevChassis12012 OBJECT IDENTIFIER ::= { cevChassis 148 }
cevChassisMc3810V3 OBJECT IDENTIFIER ::= { cevChassis 149 }
cevChassis7507z OBJECT IDENTIFIER ::= { cevChassis 151 }
cevChassis7513z OBJECT IDENTIFIER ::= { cevChassis 152 }
cevChassis7507mx OBJECT IDENTIFIER ::= { cevChassis 153 }
cevChassis7513mx OBJECT IDENTIFIER ::= { cevChassis 154 }
cevChassisUbr912C OBJECT IDENTIFIER ::= { cevChassis 155 }
cevChassisUbr912S OBJECT IDENTIFIER ::= { cevChassis 156 }
cevChassisUbr914 OBJECT IDENTIFIER ::= { cevChassis 157 }
cevChassis6160  OBJECT IDENTIFIER ::= { cevChassis 160 }
cevChassisCat2948gL3 OBJECT IDENTIFIER ::= { cevChassis 161 }
cevChassisCat4232L3 OBJECT IDENTIFIER ::= { cevChassis 164 }
cevChassisOpticalRegeneratorDCPower OBJECT IDENTIFIER ::= { cevChassis 165 }
cevChassisCVA122 OBJECT IDENTIFIER ::= { cevChassis 171 }
cevChassisCVA124 OBJECT IDENTIFIER ::= { cevChassis 172 }
cevChassisAs5850 OBJECT IDENTIFIER ::= { cevChassis 173 }
cevChassisMGX8240 OBJECT IDENTIFIER ::= { cevChassis 176 }
cevChassisAs5350 OBJECT IDENTIFIER ::= { cevChassis 178 }
cevChassisMGX8950 OBJECT IDENTIFIER ::= { cevChassis 181 }
cevChassisUbr925 OBJECT IDENTIFIER ::= { cevChassis 182 }
cevChassisUbr10012 OBJECT IDENTIFIER ::= { cevChassis 183 }
cevChassisCat4kGateway OBJECT IDENTIFIER ::= { cevChassis 184 }
cevChassis120168r OBJECT IDENTIFIER ::= { cevChassis 185 }
cevChassis2650  OBJECT IDENTIFIER ::= { cevChassis 186 }
cevChassis2651  OBJECT IDENTIFIER ::= { cevChassis 187 }
cevChassis826   OBJECT IDENTIFIER ::= { cevChassis 189 }
cevChassisCat295012 OBJECT IDENTIFIER ::= { cevChassis 190 }
cevChassisCat295024 OBJECT IDENTIFIER ::= { cevChassis 191 }
cevChassis1751  OBJECT IDENTIFIER ::= { cevChassis 193 }
cevChassis1730Iad8Fxs OBJECT IDENTIFIER ::= { cevChassis 194 }
cevChassis1730Iad16Fxs OBJECT IDENTIFIER ::= { cevChassis 195 }
cevChassis626   OBJECT IDENTIFIER ::= { cevChassis 196 }
cevChassis627   OBJECT IDENTIFIER ::= { cevChassis 197 }
cevChassis633   OBJECT IDENTIFIER ::= { cevChassis 198 }
cevChassis673   OBJECT IDENTIFIER ::= { cevChassis 199 }
cevChassis675   OBJECT IDENTIFIER ::= { cevChassis 200 }
cevChassis675e  OBJECT IDENTIFIER ::= { cevChassis 201 }
cevChassis676   OBJECT IDENTIFIER ::= { cevChassis 202 }
cevChassis677   OBJECT IDENTIFIER ::= { cevChassis 203 }
cevChassis678   OBJECT IDENTIFIER ::= { cevChassis 204 }
cevChassis3661Ac OBJECT IDENTIFIER ::= { cevChassis 205 }
cevChassis3661Dc OBJECT IDENTIFIER ::= { cevChassis 206 }
cevChassis3662Ac OBJECT IDENTIFIER ::= { cevChassis 207 }
cevChassis3662Dc OBJECT IDENTIFIER ::= { cevChassis 208 }
cevChassis3662AcCo OBJECT IDENTIFIER ::= { cevChassis 209 }
cevChassis3662DcCo OBJECT IDENTIFIER ::= { cevChassis 210 }
cevChassisUbr7111 OBJECT IDENTIFIER ::= { cevChassis 211 }
cevChassisUbr7114 OBJECT IDENTIFIER ::= { cevChassis 213 }
cevChassis12010 OBJECT IDENTIFIER ::= { cevChassis 215 }
cevChassis8110  OBJECT IDENTIFIER ::= { cevChassis 216 }
cevChassisSOHO77 OBJECT IDENTIFIER ::= { cevChassis 220 }
cevChassisSOHO76 OBJECT IDENTIFIER ::= { cevChassis 221 }
cevChassis7150Dualfe OBJECT IDENTIFIER ::= { cevChassis 222 }
cevChassis7150Octt1 OBJECT IDENTIFIER ::= { cevChassis 223 }
cevChassis7150Dualt3 OBJECT IDENTIFIER ::= { cevChassis 224 }
cevChassisCat2950t24 OBJECT IDENTIFIER ::= { cevChassis 226 }
cevChassisVPS1110 OBJECT IDENTIFIER ::= { cevChassis 227 }
cevChassisContentEngine OBJECT IDENTIFIER ::= { cevChassis 228 }
cevChassisIAD2420 OBJECT IDENTIFIER ::= { cevChassis 229 }
cevChassis677i  OBJECT IDENTIFIER ::= { cevChassis 230 }
cevChassis674   OBJECT IDENTIFIER ::= { cevChassis 231 }
cevChassisDPA7630 OBJECT IDENTIFIER ::= { cevChassis 232 }
cevChassisCat355024 OBJECT IDENTIFIER ::= { cevChassis 233 }
cevChassisCat355048 OBJECT IDENTIFIER ::= { cevChassis 234 }
cevChassisCat355012T OBJECT IDENTIFIER ::= { cevChassis 235 }
cevChassisCVA122E OBJECT IDENTIFIER ::= { cevChassis 238 }
cevChassisCVA124E OBJECT IDENTIFIER ::= { cevChassis 239 }
cevChassisURM   OBJECT IDENTIFIER ::= { cevChassis 240 }
cevChassisURM2FE OBJECT IDENTIFIER ::= { cevChassis 241 }
cevChassisURM2FE2V OBJECT IDENTIFIER ::= { cevChassis 242 }
cevChassisCAP340 OBJECT IDENTIFIER ::= { cevChassis 245 }
cevChassisDPA7610 OBJECT IDENTIFIER ::= { cevChassis 247 }
cevChassis828   OBJECT IDENTIFIER ::= { cevChassis 248 }
cevChassisSOHO78 OBJECT IDENTIFIER ::= { cevChassis 249 }
cevChassis806   OBJECT IDENTIFIER ::= { cevChassis 250 }
cevChassis12416 OBJECT IDENTIFIER ::= { cevChassis 251 }
cevChassisCat2948gL3Dc OBJECT IDENTIFIER ::= { cevChassis 252 }
cevChassisCat4908gL3Dc OBJECT IDENTIFIER ::= { cevChassis 253 }
cevChassis12406 OBJECT IDENTIFIER ::= { cevChassis 254 }
cevChassisPIXFirewall506 OBJECT IDENTIFIER ::= { cevChassis 255 }
cevChassisPIXFirewall515 OBJECT IDENTIFIER ::= { cevChassis 256 }
cevChassisPIXFirewall520 OBJECT IDENTIFIER ::= { cevChassis 257 }
cevChassisPIXFirewall525 OBJECT IDENTIFIER ::= { cevChassis 258 }
cevChassisPIXFirewall535 OBJECT IDENTIFIER ::= { cevChassis 259 }
cevChassis12410 OBJECT IDENTIFIER ::= { cevChassis 260 }
cevChassis811   OBJECT IDENTIFIER ::= { cevChassis 261 }
cevChassis813   OBJECT IDENTIFIER ::= { cevChassis 262 }
cevChassis10720 OBJECT IDENTIFIER ::= { cevChassis 263 }
cevChassisMWR1900 OBJECT IDENTIFIER ::= { cevChassis 264 }
cevChassis4224  OBJECT IDENTIFIER ::= { cevChassis 265 }
cevChassisWSC6513 OBJECT IDENTIFIER ::= { cevChassis 266 }
cevChassisCisco7603 OBJECT IDENTIFIER ::= { cevChassis 267 }
cevChassisCisco7606 OBJECT IDENTIFIER ::= { cevChassis 268 }
cevChassis7401ASR OBJECT IDENTIFIER ::= { cevChassis 269 }
cevChassis1105  OBJECT IDENTIFIER ::= { cevChassis 271 }
cevChassisONS15540ESP OBJECT IDENTIFIER ::= { cevChassis 272 }
cevChassisCe507 OBJECT IDENTIFIER ::= { cevChassis 275 }
cevChassisCe560 OBJECT IDENTIFIER ::= { cevChassis 276 }
cevChassisCe590 OBJECT IDENTIFIER ::= { cevChassis 277 }
cevChassisCe7320 OBJECT IDENTIFIER ::= { cevChassis 278 }
cevChassis2691  OBJECT IDENTIFIER ::= { cevChassis 279 }
cevChassis3725  OBJECT IDENTIFIER ::= { cevChassis 280 }
cevChassis1760  OBJECT IDENTIFIER ::= { cevChassis 282 }
cevChassisPIXFirewall501 OBJECT IDENTIFIER ::= { cevChassis 283 }
cevChassis2610M OBJECT IDENTIFIER ::= { cevChassis 284 }
cevChassis2611M OBJECT IDENTIFIER ::= { cevChassis 285 }
cevChassis12404 OBJECT IDENTIFIER ::= { cevChassis 289 }
cevChassis9004  OBJECT IDENTIFIER ::= { cevChassis 290 }
cevChassisCat295012G OBJECT IDENTIFIER ::= { cevChassis 293 }
cevChassisCat295024G OBJECT IDENTIFIER ::= { cevChassis 294 }
cevChassisCat295048G OBJECT IDENTIFIER ::= { cevChassis 295 }
cevChassisCat355012G OBJECT IDENTIFIER ::= { cevChassis 297 }
cevChassisCE507AV OBJECT IDENTIFIER ::= { cevChassis 298 }
cevChassisCE560AV OBJECT IDENTIFIER ::= { cevChassis 299 }
cevChassisIE2105 OBJECT IDENTIFIER ::= { cevChassis 300 }
cevChassis3745  OBJECT IDENTIFIER ::= { cevChassis 301 }
cevChassis10005 OBJECT IDENTIFIER ::= { cevChassis 302 }
cevChassis10008 OBJECT IDENTIFIER ::= { cevChassis 303 }
cevChassis7304  OBJECT IDENTIFIER ::= { cevChassis 304 }
cevChassis7505  OBJECT IDENTIFIER ::= { cevChassis 305 }
cevChassis1721  OBJECT IDENTIFIER ::= { cevChassis 310 }
cevChassisCat4000Sup3 OBJECT IDENTIFIER ::= { cevChassis 311 }
cevChassis827H  OBJECT IDENTIFIER ::= { cevChassis 312 }
cevChassisSOHO77H OBJECT IDENTIFIER ::= { cevChassis 313 }
cevChassisCat4006 OBJECT IDENTIFIER ::= { cevChassis 314 }
cevChassisCat355024Mmf OBJECT IDENTIFIER ::= { cevChassis 315 }
cevChassisWSC6503 OBJECT IDENTIFIER ::= { cevChassis 316 }
cevChassisPIXFirewall506E OBJECT IDENTIFIER ::= { cevChassis 317 }
cevChassisPIXFirewall515E OBJECT IDENTIFIER ::= { cevChassis 318 }
cevChassisCat355024Dc OBJECT IDENTIFIER ::= { cevChassis 319 }
cevChassisCe2636 OBJECT IDENTIFIER ::= { cevChassis 320 }
cevChassisCeDw2636 OBJECT IDENTIFIER ::= { cevChassis 321 }
cevChassis14MGX8830 OBJECT IDENTIFIER ::= { cevChassis 323 }
cevChassisONS15530NEBS OBJECT IDENTIFIER ::= { cevChassis 325 }
cevChassisONS15530ETSI OBJECT IDENTIFIER ::= { cevChassis 326 }
cevChassisSOHO71 OBJECT IDENTIFIER ::= { cevChassis 327 }
cevChassis6400UAC OBJECT IDENTIFIER ::= { cevChassis 328 }
cevChassisRPMPR OBJECT IDENTIFIER ::= { cevChassis 329 }
cevChassis2610XM OBJECT IDENTIFIER ::= { cevChassis 330 }
cevChassis2611XM OBJECT IDENTIFIER ::= { cevChassis 331 }
cevChassis2620XM OBJECT IDENTIFIER ::= { cevChassis 332 }
cevChassis2621XM OBJECT IDENTIFIER ::= { cevChassis 333 }
cevChassis2650XM OBJECT IDENTIFIER ::= { cevChassis 334 }
cevChassis2651XM OBJECT IDENTIFIER ::= { cevChassis 335 }
cevChassisCat295024GDc OBJECT IDENTIFIER ::= { cevChassis 336 }
cevChassisONS15540ESPx OBJECT IDENTIFIER ::= { cevChassis 337 }
cevChassisC7301 OBJECT IDENTIFIER ::= { cevChassis 340 }
cevChassis12816 OBJECT IDENTIFIER ::= { cevChassis 341 }
cevChassis12810 OBJECT IDENTIFIER ::= { cevChassis 342 }
cevChassisCat295024sx OBJECT IDENTIFIER ::= { cevChassis 347 }
cevChassisAs5400HPX OBJECT IDENTIFIER ::= { cevChassis 348 }
cevChassisAs5350HPX OBJECT IDENTIFIER ::= { cevChassis 349 }
cevChassisCat2955T12 OBJECT IDENTIFIER ::= { cevChassis 350 }
cevChassisCat2955C12 OBJECT IDENTIFIER ::= { cevChassis 351 }
cevChassis837   OBJECT IDENTIFIER ::= { cevChassis 354 }
cevChassisSOHO97 OBJECT IDENTIFIER ::= { cevChassis 355 }
cevChassis831   OBJECT IDENTIFIER ::= { cevChassis 356 }
cevChassisSOHO91 OBJECT IDENTIFIER ::= { cevChassis 357 }
cevChassis836   OBJECT IDENTIFIER ::= { cevChassis 358 }
cevChassisSOHO96 OBJECT IDENTIFIER ::= { cevChassis 359 }
cevChassisCat4507 OBJECT IDENTIFIER ::= { cevChassis 360 }
cevChassisCat4506 OBJECT IDENTIFIER ::= { cevChassis 361 }
cevChassisCat4503 OBJECT IDENTIFIER ::= { cevChassis 362 }
cevChassis7507  OBJECT IDENTIFIER ::= { cevChassis 363 }
cevChassis7513  OBJECT IDENTIFIER ::= { cevChassis 364 }
cevChassisAIRAP1100 OBJECT IDENTIFIER ::= { cevChassis 365 }
cevChassisCat2955S12 OBJECT IDENTIFIER ::= { cevChassis 367 }
cevChassisCisco7609 OBJECT IDENTIFIER ::= { cevChassis 368 }
cevChassisWSC65509 OBJECT IDENTIFIER ::= { cevChassis 369 }
cevChassisCat375024 OBJECT IDENTIFIER ::= { cevChassis 370 }
cevChassisCat375048 OBJECT IDENTIFIER ::= { cevChassis 371 }
cevChassisCat375024TS OBJECT IDENTIFIER ::= { cevChassis 372 }
cevChassisCat375024T OBJECT IDENTIFIER ::= { cevChassis 373 }
cevChassisMWR1941DC OBJECT IDENTIFIER ::= { cevChassis 374 }
cevChassisDSC9506 OBJECT IDENTIFIER ::= { cevChassis 375 }
cevChassisDSC9509 OBJECT IDENTIFIER ::= { cevChassis 376 }
cevChassisDSC9513 OBJECT IDENTIFIER ::= { cevChassis 377 }
cevChassisONS15201 OBJECT IDENTIFIER ::= { cevChassis 378 }
cevChassisONS15252 OBJECT IDENTIFIER ::= { cevChassis 379 }
cevChassisMdsDSX9216 OBJECT IDENTIFIER ::= { cevChassis 380 }
cevChassisVG200 OBJECT IDENTIFIER ::= { cevChassis 381 }
cevChassisAIRAP1210 OBJECT IDENTIFIER ::= { cevChassis 382 }
cevChassisCat375048PS OBJECT IDENTIFIER ::= { cevChassis 383 }
cevChassisCat375024PS OBJECT IDENTIFIER ::= { cevChassis 384 }
cevChassisCe510 OBJECT IDENTIFIER ::= { cevChassis 385 }
cevChassisCe565 OBJECT IDENTIFIER ::= { cevChassis 386 }
cevChassisCe7305 OBJECT IDENTIFIER ::= { cevChassis 387 }
cevChassisCe7325 OBJECT IDENTIFIER ::= { cevChassis 388 }
cevChassisCe4630 OBJECT IDENTIFIER ::= { cevChassis 389 }
cevChassisCe4650 OBJECT IDENTIFIER ::= { cevChassis 390 }
cevChassisCat297024 OBJECT IDENTIFIER ::= { cevChassis 391 }
cevChassisCisco7613 OBJECT IDENTIFIER ::= { cevChassis 392 }
cevChassisCat3750Ge12Sfp OBJECT IDENTIFIER ::= { cevChassis 394 }
cevChassisCr4450 OBJECT IDENTIFIER ::= { cevChassis 395 }
cevChassisAIRBR1410 OBJECT IDENTIFIER ::= { cevChassis 396 }
cevChassisWSC6509neba OBJECT IDENTIFIER ::= { cevChassis 397 }
cevChassisCat4510 OBJECT IDENTIFIER ::= { cevChassis 398 }
cevChassisCisco1711 OBJECT IDENTIFIER ::= { cevChassis 399 }
cevChassisCisco1712 OBJECT IDENTIFIER ::= { cevChassis 400 }
cevChassisCisco1701 OBJECT IDENTIFIER ::= { cevChassis 401 }
cevChassis29408TT OBJECT IDENTIFIER ::= { cevChassis 402 }
cevChassis29408TF OBJECT IDENTIFIER ::= { cevChassis 403 }
cevChassis3825  OBJECT IDENTIFIER ::= { cevChassis 404 }
cevChassis3845  OBJECT IDENTIFIER ::= { cevChassis 405 }
cevChassis2430Iad24Fxs OBJECT IDENTIFIER ::= { cevChassis 406 }
cevChassis2431Iad8Fxs OBJECT IDENTIFIER ::= { cevChassis 407 }
cevChassis2431Iad16Fxs OBJECT IDENTIFIER ::= { cevChassis 408 }
cevChassis2431Iad1T1E1 OBJECT IDENTIFIER ::= { cevChassis 409 }
cevChassis2432Iad24Fxs OBJECT IDENTIFIER ::= { cevChassis 410 }
cevChassisDSC9140K9 OBJECT IDENTIFIER ::= { cevChassis 411 }
cevChassisAirAp350IOS OBJECT IDENTIFIER ::= { cevChassis 412 }
cevChassis3220  OBJECT IDENTIFIER ::= { cevChassis 413 }
cevChassisDSC9120K9 OBJECT IDENTIFIER ::= { cevChassis 414 }
cevChassisCat295024LreSt997 OBJECT IDENTIFIER ::= { cevChassis 415 }
cevChassisCat6kSup720 OBJECT IDENTIFIER ::= { cevChassis 416 }
cevChassisVG224 OBJECT IDENTIFIER ::= { cevChassis 417 }
cevChassisCat295048T OBJECT IDENTIFIER ::= { cevChassis 418 }
cevChassisCat295048SX OBJECT IDENTIFIER ::= { cevChassis 419 }
cevChassisCat297024TS OBJECT IDENTIFIER ::= { cevChassis 420 }
cevChassisCrs116Fabric OBJECT IDENTIFIER ::= { cevChassis 421 }
cevChassisCrs116LineCard OBJECT IDENTIFIER ::= { cevChassis 422 }
cevChassisCrs18LineCard OBJECT IDENTIFIER ::= { cevChassis 423 }
cevChassisCat356048PS OBJECT IDENTIFIER ::= { cevChassis 424 }
cevChassisCat356024PS OBJECT IDENTIFIER ::= { cevChassis 425 }
cevChassisAIRBR1300 OBJECT IDENTIFIER ::= { cevChassis 426 }
cevChassis12004 OBJECT IDENTIFIER ::= { cevChassis 427 }
cevChassis12006 OBJECT IDENTIFIER ::= { cevChassis 428 }
cevChassis851   OBJECT IDENTIFIER ::= { cevChassis 429 }
cevChassis857   OBJECT IDENTIFIER ::= { cevChassis 430 }
cevChassis876   OBJECT IDENTIFIER ::= { cevChassis 431 }
cevChassis877   OBJECT IDENTIFIER ::= { cevChassis 432 }
cevChassis878   OBJECT IDENTIFIER ::= { cevChassis 433 }
cevChassis871   OBJECT IDENTIFIER ::= { cevChassis 434 }
cevChassisUmg9820 OBJECT IDENTIFIER ::= { cevChassis 435 }
cevChassis2811  OBJECT IDENTIFIER ::= { cevChassis 436 }
cevChassis2821  OBJECT IDENTIFIER ::= { cevChassis 437 }
cevChassis2851  OBJECT IDENTIFIER ::= { cevChassis 438 }
cevChassisCat375024ME OBJECT IDENTIFIER ::= { cevChassis 439 }
cevChassisMdsDSC9216AK9 OBJECT IDENTIFIER ::= { cevChassis 442 }
cevChassis3201WMIC OBJECT IDENTIFIER ::= { cevChassis 443 }
cevChassisCat3750G16TD OBJECT IDENTIFIER ::= { cevChassis 444 }
cevChassis1718  OBJECT IDENTIFIER ::= { cevChassis 445 }
cevChassisIGESM OBJECT IDENTIFIER ::= { cevChassis 446 }
cevChassisASA5510 OBJECT IDENTIFIER ::= { cevChassis 447 }
cevChassisASA5520 OBJECT IDENTIFIER ::= { cevChassis 448 }
cevChassisASA5540 OBJECT IDENTIFIER ::= { cevChassis 449 }
cevChassis1841  OBJECT IDENTIFIER ::= { cevChassis 450 }
cevChassis2801  OBJECT IDENTIFIER ::= { cevChassis 451 }
cevChassisCe511K9 OBJECT IDENTIFIER ::= { cevChassis 452 }
cevChassisCe566K9 OBJECT IDENTIFIER ::= { cevChassis 453 }
cevChassisASA5560 OBJECT IDENTIFIER ::= { cevChassis 454 }
cevChassisMGX8880 OBJECT IDENTIFIER ::= { cevChassis 455 }
cevChassisCe7306K9 OBJECT IDENTIFIER ::= { cevChassis 456 }
cevChassisCe7326K9 OBJECT IDENTIFIER ::= { cevChassis 457 }
cevChassisCat3750G24PS OBJECT IDENTIFIER ::= { cevChassis 458 }
cevChassisCat3750G48PS OBJECT IDENTIFIER ::= { cevChassis 459 }
cevChassisCat3750G48TS OBJECT IDENTIFIER ::= { cevChassis 460 }
cevChassisCat297048TS OBJECT IDENTIFIER ::= { cevChassis 461 }
cevChassisDSX9132K9 OBJECT IDENTIFIER ::= { cevChassis 462 }
cevChassisDSX9116K9 OBJECT IDENTIFIER ::= { cevChassis 463 }
cevChassisBMGX8830 OBJECT IDENTIFIER ::= { cevChassis 464 }
cevChassisBMGX8850 OBJECT IDENTIFIER ::= { cevChassis 465 }
cevChassisWsC4948 OBJECT IDENTIFIER ::= { cevChassis 466 }
cevChassisCe501K9 OBJECT IDENTIFIER ::= { cevChassis 467 }
cevChassisCat3560G24PS OBJECT IDENTIFIER ::= { cevChassis 468 }
cevChassisCat3560G24TS OBJECT IDENTIFIER ::= { cevChassis 469 }
cevChassisCat3560G48PS OBJECT IDENTIFIER ::= { cevChassis 470 }
cevChassisCat3560G48TS OBJECT IDENTIFIER ::= { cevChassis 471 }
cevChassisDSC9216iK9 OBJECT IDENTIFIER ::= { cevChassis 472 }
cevChassisAs5400XM OBJECT IDENTIFIER ::= { cevChassis 473 }
cevChassisAs5350XM OBJECT IDENTIFIER ::= { cevChassis 474 }
cevChassisAIRAP1130 OBJECT IDENTIFIER ::= { cevChassis 475 }
cevChassisCisco7604 OBJECT IDENTIFIER ::= { cevChassis 476 }
cevChassisWsC494810GE OBJECT IDENTIFIER ::= { cevChassis 477 }
cevChassisCat3750G24TS1U OBJECT IDENTIFIER ::= { cevChassis 478 }
cevChassis371098HP001 OBJECT IDENTIFIER ::= { cevChassis 480 }
cevChassisSB101 OBJECT IDENTIFIER ::= { cevChassis 481 }
cevChassisSB106 OBJECT IDENTIFIER ::= { cevChassis 482 }
cevChassisSB107 OBJECT IDENTIFIER ::= { cevChassis 483 }
cevChassisCat356024TS OBJECT IDENTIFIER ::= { cevChassis 484 }
cevChassisCat356048TS OBJECT IDENTIFIER ::= { cevChassis 485 }
cevChassisONS15310 OBJECT IDENTIFIER ::= { cevChassis 486 }
cevChassis1801  OBJECT IDENTIFIER ::= { cevChassis 487 }
cevChassis1802  OBJECT IDENTIFIER ::= { cevChassis 488 }
cevChassis1803  OBJECT IDENTIFIER ::= { cevChassis 489 }
cevChassis1811  OBJECT IDENTIFIER ::= { cevChassis 490 }
cevChassis1812  OBJECT IDENTIFIER ::= { cevChassis 491 }
cevWLSEChassis1130 OBJECT IDENTIFIER ::= { cevChassis 492 }
cevWLSEChassis1030 OBJECT IDENTIFIER ::= { cevChassis 493 }
cevChassisIDS4210 OBJECT IDENTIFIER ::= { cevChassis 495 }
cevChassisIDS4215 OBJECT IDENTIFIER ::= { cevChassis 496 }
cevChassisIDS4235 OBJECT IDENTIFIER ::= { cevChassis 497 }
cevChassisIDS4240 OBJECT IDENTIFIER ::= { cevChassis 498 }
cevChassisIDS4250 OBJECT IDENTIFIER ::= { cevChassis 499 }
cevChassisIDS4250SX OBJECT IDENTIFIER ::= { cevChassis 500 }
cevChassisIDS4250XL OBJECT IDENTIFIER ::= { cevChassis 501 }
cevChassisIDS4255 OBJECT IDENTIFIER ::= { cevChassis 502 }
cevChassisCat375024FS OBJECT IDENTIFIER ::= { cevChassis 503 }
cevChassisWSC6504E OBJECT IDENTIFIER ::= { cevChassis 504 }
cevChassisIGESMSFP OBJECT IDENTIFIER ::= { cevChassis 505 }
cevChasisFe6326K9 OBJECT IDENTIFIER ::= { cevChassis 506 }
cevChassisFe7326K9 OBJECT IDENTIFIER ::= { cevChassis 508 }
cevChassisFe511K9 OBJECT IDENTIFIER ::= { cevChassis 509 }
cevChassisSCEDispatcher OBJECT IDENTIFIER ::= { cevChassis 510 }
cevChassisSCE2000 OBJECT IDENTIFIER ::= { cevChassis 511 }
cevChassisSCE1000 OBJECT IDENTIFIER ::= { cevChassis 512 }
cevChassisAIRAP1240 OBJECT IDENTIFIER ::= { cevChassis 513 }
cevChassisDSC902020K9 OBJECT IDENTIFIER ::= { cevChassis 514 }
cevChassisFe611K9 OBJECT IDENTIFIER ::= { cevChassis 515 }
cevChassisCat3750Ge12SfpDc OBJECT IDENTIFIER ::= { cevChassis 520 }
cevChassisCat296024 OBJECT IDENTIFIER ::= { cevChassis 521 }
cevChassisCat296048 OBJECT IDENTIFIER ::= { cevChassis 522 }
cevChassisCat2960G24 OBJECT IDENTIFIER ::= { cevChassis 523 }
cevChassisCat2960G48 OBJECT IDENTIFIER ::= { cevChassis 524 }
cevChassisCat6kMsfc2a OBJECT IDENTIFIER ::= { cevChassis 529 }
cevChassisCe611K9 OBJECT IDENTIFIER ::= { cevChassis 530 }
cevChassisME6340ACA OBJECT IDENTIFIER ::= { cevChassis 531 }
cevChassisME6340DCA OBJECT IDENTIFIER ::= { cevChassis 532 }
cevChassisME6340DCB OBJECT IDENTIFIER ::= { cevChassis 533 }
cevChassisCat296024TT OBJECT IDENTIFIER ::= { cevChassis 534 }
cevChassisCat296048TT OBJECT IDENTIFIER ::= { cevChassis 535 }
cevChassisIGESMSFPT OBJECT IDENTIFIER ::= { cevChassis 536 }
cevChassisMec6524gs8s OBJECT IDENTIFIER ::= { cevChassis 537 }
cevChassisMec6524gt8s OBJECT IDENTIFIER ::= { cevChassis 538 }
cevChassisPaldron OBJECT IDENTIFIER ::= { cevChassis 541 }
cevChassisIGESMT OBJECT IDENTIFIER ::= { cevChassis 542 }
cevChassisCatCE50024TT OBJECT IDENTIFIER ::= { cevChassis 543 }
cevChassisCatCE50024LC OBJECT IDENTIFIER ::= { cevChassis 544 }
cevChassisCatCE50024PC OBJECT IDENTIFIER ::= { cevChassis 545 }
cevChassisCatCE50012TC OBJECT IDENTIFIER ::= { cevChassis 546 }
cevChassis5750  OBJECT IDENTIFIER ::= { cevChassis 547 }
cevChassisMWR1941DCA OBJECT IDENTIFIER ::= { cevChassis 548 }
cevChassis815   OBJECT IDENTIFIER ::= { cevChassis 549 }
cevChassis240024TSA OBJECT IDENTIFIER ::= { cevChassis 550 }
cevChassis240024TSD OBJECT IDENTIFIER ::= { cevChassis 551 }
cevChassis340024TSA OBJECT IDENTIFIER ::= { cevChassis 552 }
cevChassis340024TSD OBJECT IDENTIFIER ::= { cevChassis 553 }
cevChassisFe2636 OBJECT IDENTIFIER ::= { cevChassis 556 }
cevChassisIDS4220 OBJECT IDENTIFIER ::= { cevChassis 557 }
cevChassisIDS4230 OBJECT IDENTIFIER ::= { cevChassis 558 }
cevChassisASA5505 OBJECT IDENTIFIER ::= { cevChassis 560 }
cevChassisWS3020HPQ OBJECT IDENTIFIER ::= { cevChassis 561 }
cevChassisWS3030DEL OBJECT IDENTIFIER ::= { cevChassis 562 }
cevChassisWLSE1133 OBJECT IDENTIFIER ::= { cevChassis 563 }
cevChassisASA5550 OBJECT IDENTIFIER ::= { cevChassis 564 }
cevChassisWae612K9 OBJECT IDENTIFIER ::= { cevChassis 565 }
cevChassisAirap1250 OBJECT IDENTIFIER ::= { cevChassis 567 }
cevChassisCe512K9 OBJECT IDENTIFIER ::= { cevChassis 568 }
cevChassisFe512K9 OBJECT IDENTIFIER ::= { cevChassis 569 }
cevChassisCe612K9 OBJECT IDENTIFIER ::= { cevChassis 570 }
cevChassisFe612K9 OBJECT IDENTIFIER ::= { cevChassis 571 }
cevChassisOe512K9 OBJECT IDENTIFIER ::= { cevChassis 573 }
cevChassisOe612K9 OBJECT IDENTIFIER ::= { cevChassis 574 }
cevChassisCat3750G24WS OBJECT IDENTIFIER ::= { cevChassis 575 }
cevChassisCrs14LineCard OBJECT IDENTIFIER ::= { cevChassis 576 }
cevChassisMe3400g12CsA OBJECT IDENTIFIER ::= { cevChassis 577 }
cevChassisMe3400g12CsD OBJECT IDENTIFIER ::= { cevChassis 578 }
cevChassis877M  OBJECT IDENTIFIER ::= { cevChassis 579 }
cevChassis1801M OBJECT IDENTIFIER ::= { cevChassis 580 }
cevChassisWsCbs3040Fsc OBJECT IDENTIFIER ::= { cevChassis 581 }
cevChassisSpaIPSEC2g2 OBJECT IDENTIFIER ::= { cevChassis 582 }
cevChassisOe511K9 OBJECT IDENTIFIER ::= { cevChassis 583 }
cevChassisOe611K9 OBJECT IDENTIFIER ::= { cevChassis 584 }
cevChassisOe7326K9 OBJECT IDENTIFIER ::= { cevChassis 585 }
cevChassisMe492410GE OBJECT IDENTIFIER ::= { cevChassis 586 }
cevChassisDSC9124 OBJECT IDENTIFIER ::= { cevChassis 587 }
cevChassisCat3750E48TD OBJECT IDENTIFIER ::= { cevChassis 588 }
cevChassisCat3750E24TD OBJECT IDENTIFIER ::= { cevChassis 589 }
cevChassisCat3750E24PD OBJECT IDENTIFIER ::= { cevChassis 590 }
cevChassisCat3750E48PD OBJECT IDENTIFIER ::= { cevChassis 591 }
cevChassisCat3560E24TD OBJECT IDENTIFIER ::= { cevChassis 592 }
cevChassisCat3560E48TD OBJECT IDENTIFIER ::= { cevChassis 593 }
cevChassisCat3560E24PD OBJECT IDENTIFIER ::= { cevChassis 594 }
cevChassisCat3560E48PD OBJECT IDENTIFIER ::= { cevChassis 595 }
cevChassisCat35608PC OBJECT IDENTIFIER ::= { cevChassis 596 }
cevChassisCat29608TC OBJECT IDENTIFIER ::= { cevChassis 597 }
cevChassisCat2960G8TC OBJECT IDENTIFIER ::= { cevChassis 598 }
cevChassisCisco7606S OBJECT IDENTIFIER ::= { cevChassis 599 }
cevChassisCisco7609S OBJECT IDENTIFIER ::= { cevChassis 600 }
cevChassisDSIBMFC OBJECT IDENTIFIER ::= { cevChassis 601 }
cevChassisIPSVirtual OBJECT IDENTIFIER ::= { cevChassis 602 }
cevChassis3250  OBJECT IDENTIFIER ::= { cevChassis 603 }
cevChassis3205WMIC OBJECT IDENTIFIER ::= { cevChassis 604 }
cevChassisCisco5720 OBJECT IDENTIFIER ::= { cevChassis 605 }
cevChassisMe3400g2csA OBJECT IDENTIFIER ::= { cevChassis 607 }
cevChassis7201  OBJECT IDENTIFIER ::= { cevChassis 608 }
cevChassisNmWae OBJECT IDENTIFIER ::= { cevChassis 609 }
cevChassisACE4710K9 OBJECT IDENTIFIER ::= { cevChassis 610 }
cevChassisN7Kc7010 OBJECT IDENTIFIER ::= { cevChassis 612 }
cevChassisUbr7225Vxr OBJECT IDENTIFIER ::= { cevChassis 613 }
cevChassisWSC6509ve OBJECT IDENTIFIER ::= { cevChassis 615 }
cevChassisDSC9134 OBJECT IDENTIFIER ::= { cevChassis 616 }
cevChassisCisco7603S OBJECT IDENTIFIER ::= { cevChassis 617 }
cevChassis5740  OBJECT IDENTIFIER ::= { cevChassis 620 }
cevChassis867   OBJECT IDENTIFIER ::= { cevChassis 623 }
cevChassis881   OBJECT IDENTIFIER ::= { cevChassis 624 }
cevChassis881G  OBJECT IDENTIFIER ::= { cevChassis 625 }
cevChassisIad881F OBJECT IDENTIFIER ::= { cevChassis 626 }
cevChassisIad881B OBJECT IDENTIFIER ::= { cevChassis 627 }
cevChassis881Srst OBJECT IDENTIFIER ::= { cevChassis 628 }
cevChassis886   OBJECT IDENTIFIER ::= { cevChassis 629 }
cevChassis886G  OBJECT IDENTIFIER ::= { cevChassis 630 }
cevChassisIad886F OBJECT IDENTIFIER ::= { cevChassis 631 }
cevChassisIad886B OBJECT IDENTIFIER ::= { cevChassis 632 }
cevChassis886Srst OBJECT IDENTIFIER ::= { cevChassis 633 }
cevChassis887   OBJECT IDENTIFIER ::= { cevChassis 634 }
cevChassis887G  OBJECT IDENTIFIER ::= { cevChassis 635 }
cevChassisIad887F OBJECT IDENTIFIER ::= { cevChassis 636 }
cevChassisIad887B OBJECT IDENTIFIER ::= { cevChassis 637 }
cevChassis887Srst OBJECT IDENTIFIER ::= { cevChassis 638 }
cevChassis888G  OBJECT IDENTIFIER ::= { cevChassis 640 }
cevChassisIad888F OBJECT IDENTIFIER ::= { cevChassis 641 }
cevChassisIad888B OBJECT IDENTIFIER ::= { cevChassis 642 }
cevChassis888Srst OBJECT IDENTIFIER ::= { cevChassis 643 }
cevChassis891   OBJECT IDENTIFIER ::= { cevChassis 644 }
cevChassis892   OBJECT IDENTIFIER ::= { cevChassis 645 }
cevChassis885D3 OBJECT IDENTIFIER ::= { cevChassis 646 }
cevChassisIad885FD3 OBJECT IDENTIFIER ::= { cevChassis 647 }
cevChassis885EJ3 OBJECT IDENTIFIER ::= { cevChassis 648 }
cevChassis7816H OBJECT IDENTIFIER ::= { cevChassis 649 }
cevChassisSce8000 OBJECT IDENTIFIER ::= { cevChassis 650 }
cevChassisMdsDSC9222i OBJECT IDENTIFIER ::= { cevChassis 651 }
cevChassis860Ap OBJECT IDENTIFIER ::= { cevChassis 653 }
cevChassis880Ap OBJECT IDENTIFIER ::= { cevChassis 654 }
cevChassis890Ap OBJECT IDENTIFIER ::= { cevChassis 655 }
cevChassis1900Ap OBJECT IDENTIFIER ::= { cevChassis 656 }
cevChassis340024FSA OBJECT IDENTIFIER ::= { cevChassis 657 }
cevChassisCat4503e OBJECT IDENTIFIER ::= { cevChassis 658 }
cevChassisCat4506e OBJECT IDENTIFIER ::= { cevChassis 659 }
cevChassisCat4507re OBJECT IDENTIFIER ::= { cevChassis 660 }
cevChassisCat4510re OBJECT IDENTIFIER ::= { cevChassis 661 }
cevChassisUc520s8U4FxoK9 OBJECT IDENTIFIER ::= { cevChassis 662 }
cevChassisUc520s8U4FxoWK9 OBJECT IDENTIFIER ::= { cevChassis 663 }
cevChassisUc520s8U2BriK9 OBJECT IDENTIFIER ::= { cevChassis 664 }
cevChassisUc520s8U2BriWK9 OBJECT IDENTIFIER ::= { cevChassis 665 }
cevChassisUc520s16U4FxoK9 OBJECT IDENTIFIER ::= { cevChassis 666 }
cevChassisUc520s16U4FxoWK9 OBJECT IDENTIFIER ::= { cevChassis 667 }
cevChassisUc520s16U2BriK9 OBJECT IDENTIFIER ::= { cevChassis 668 }
cevChassisUc520s16U2BriWK9 OBJECT IDENTIFIER ::= { cevChassis 669 }
cevChassisUc520m32U8FxoK9 OBJECT IDENTIFIER ::= { cevChassis 670 }
cevChassisUc520m32U8FxoW OBJECT IDENTIFIER ::= { cevChassis 671 }
cevChassisUc520m32U4BriK9 OBJECT IDENTIFIER ::= { cevChassis 672 }
cevChassisUc520m32U4BriW OBJECT IDENTIFIER ::= { cevChassis 673 }
cevChassisUc520m48U12FxoK9 OBJECT IDENTIFIER ::= { cevChassis 674 }
cevChassisUc520m48U12FxoW OBJECT IDENTIFIER ::= { cevChassis 675 }
cevChassisUc520m48U6BriK9 OBJECT IDENTIFIER ::= { cevChassis 676 }
cevChassisUc520m48U6BriW OBJECT IDENTIFIER ::= { cevChassis 677 }
cevChassisUc520m48U1T1E1FK9 OBJECT IDENTIFIER ::= { cevChassis 678 }
cevChassisUc520m48U1T1E1BK9 OBJECT IDENTIFIER ::= { cevChassis 679 }
cevChassisCE5208PC OBJECT IDENTIFIER ::= { cevChassis 680 }
cevChassis7828H OBJECT IDENTIFIER ::= { cevChassis 681 }
cevChassis7816I OBJECT IDENTIFIER ::= { cevChassis 682 }
cevChassis7828I OBJECT IDENTIFIER ::= { cevChassis 683 }
cevChassis1861Uc2BK9 OBJECT IDENTIFIER ::= { cevChassis 684 }
cevChassis1861Uc4FK9 OBJECT IDENTIFIER ::= { cevChassis 685 }
cevChassis1861Srst2BK9 OBJECT IDENTIFIER ::= { cevChassis 686 }
cevChassis1861Srst4FK9 OBJECT IDENTIFIER ::= { cevChassis 687 }
cevChassisOe7330K9 OBJECT IDENTIFIER ::= { cevChassis 688 }
cevChassisOe7350K9 OBJECT IDENTIFIER ::= { cevChassis 689 }
cevChassisCat296048TCS OBJECT IDENTIFIER ::= { cevChassis 694 }
cevChassisCat296024TCS OBJECT IDENTIFIER ::= { cevChassis 695 }
cevChassisCat296024S OBJECT IDENTIFIER ::= { cevChassis 696 }
cevChassisCat296024PC OBJECT IDENTIFIER ::= { cevChassis 697 }
cevChassisCat296024LT OBJECT IDENTIFIER ::= { cevChassis 698 }
cevChassisCat2960PD8TT OBJECT IDENTIFIER ::= { cevChassis 699 }
cevChassisASR1002 OBJECT IDENTIFIER ::= { cevChassis 700 }
cevChassisASR1004 OBJECT IDENTIFIER ::= { cevChassis 701 }
cevChassisASR1006 OBJECT IDENTIFIER ::= { cevChassis 702 }
cevChassisWsC4900M OBJECT IDENTIFIER ::= { cevChassis 703 }
cevChassisASA5580 OBJECT IDENTIFIER ::= { cevChassis 704 }
cevChassisCatRfgw OBJECT IDENTIFIER ::= { cevChassis 705 }
cevChassisCE52024PC OBJECT IDENTIFIER ::= { cevChassis 706 }
cevChassisCE52024LC OBJECT IDENTIFIER ::= { cevChassis 707 }
cevChassisCE52024TT OBJECT IDENTIFIER ::= { cevChassis 708 }
cevChassisCE520G24TC OBJECT IDENTIFIER ::= { cevChassis 709 }
cevChassis1861Srst2BCueK9 OBJECT IDENTIFIER ::= { cevChassis 710 }
cevChassis1861Srst4FCueK9 OBJECT IDENTIFIER ::= { cevChassis 711 }
cevChassisVgd1t3 OBJECT IDENTIFIER ::= { cevChassis 712 }
cevChassisCat3560e12d OBJECT IDENTIFIER ::= { cevChassis 718 }
cevChassisN5kC5020pBf OBJECT IDENTIFIER ::= { cevChassis 719 }
cevChassisN5kC5020pBd OBJECT IDENTIFIER ::= { cevChassis 720 }
cevChassisCat3560E12SD OBJECT IDENTIFIER ::= { cevChassis 721 }
cevChassisOe674 OBJECT IDENTIFIER ::= { cevChassis 722 }
cevChassisIE30004TC OBJECT IDENTIFIER ::= { cevChassis 723 }
cevChassisIE30008TC OBJECT IDENTIFIER ::= { cevChassis 724 }
cevChassisRAIE1783MS06 OBJECT IDENTIFIER ::= { cevChassis 725 }
cevChassisRAIE1783MS10T OBJECT IDENTIFIER ::= { cevChassis 726 }
cevChassis2435Iad8Fxs OBJECT IDENTIFIER ::= { cevChassis 727 }
cevChassisVG204 OBJECT IDENTIFIER ::= { cevChassis 728 }
cevChassisVG202 OBJECT IDENTIFIER ::= { cevChassis 729 }
cevChassisCat291824TT OBJECT IDENTIFIER ::= { cevChassis 730 }
cevChassisCat291824TC OBJECT IDENTIFIER ::= { cevChassis 731 }
cevChassisCat291848TT OBJECT IDENTIFIER ::= { cevChassis 732 }
cevChassisCat291848TC OBJECT IDENTIFIER ::= { cevChassis 733 }
cevChassis1805  OBJECT IDENTIFIER ::= { cevChassis 734 }
cevChassisUc52024u4briK9 OBJECT IDENTIFIER ::= { cevChassis 735 }
cevChassisUc52024u8fxoK9 OBJECT IDENTIFIER ::= { cevChassis 736 }
cevChassisUc520s8u2briWJK9 OBJECT IDENTIFIER ::= { cevChassis 737 }
cevChassisUc520s16u2briWJK9 OBJECT IDENTIFIER ::= { cevChassis 738 }
cevChassisVSIntSP OBJECT IDENTIFIER ::= { cevChassis 739 }
cevChassisVSSP  OBJECT IDENTIFIER ::= { cevChassis 740 }
cevChassisVSHydecoder OBJECT IDENTIFIER ::= { cevChassis 741 }
cevChassisVSDecoder OBJECT IDENTIFIER ::= { cevChassis 742 }
cevChassisVSEncoder1P OBJECT IDENTIFIER ::= { cevChassis 743 }
cevChassisCiscoMwr2941Dc OBJECT IDENTIFIER ::= { cevChassis 745 }
cevChassisOe574 OBJECT IDENTIFIER ::= { cevChassis 746 }
cevChassisOe474 OBJECT IDENTIFIER ::= { cevChassis 747 }
cevChassisOe274 OBJECT IDENTIFIER ::= { cevChassis 748 }
cevChassis7816c OBJECT IDENTIFIER ::= { cevChassis 749 }
cevChassisAp801agn OBJECT IDENTIFIER ::= { cevChassis 750 }
cevChassisAp801gn OBJECT IDENTIFIER ::= { cevChassis 751 }
cevChassisC1861WSrst4FCueK9 OBJECT IDENTIFIER ::= { cevChassis 752 }
cevChassisC1861WSrst2BCueK9 OBJECT IDENTIFIER ::= { cevChassis 753 }
cevChassisC1861WSrst4FK9 OBJECT IDENTIFIER ::= { cevChassis 754 }
cevChassisC1861WSrst2BK9 OBJECT IDENTIFIER ::= { cevChassis 755 }
cevChassisC1861WUc4FK9 OBJECT IDENTIFIER ::= { cevChassis 756 }
cevChassisC1861WUc2BK9 OBJECT IDENTIFIER ::= { cevChassis 757 }
cevChassisMe3400e24tsM OBJECT IDENTIFIER ::= { cevChassis 758 }
cevChassisMe3400eg12csM OBJECT IDENTIFIER ::= { cevChassis 759 }
cevChassisMe3400eg2csA OBJECT IDENTIFIER ::= { cevChassis 760 }
cevChassisCe674 OBJECT IDENTIFIER ::= { cevChassis 761 }
cevChassisCAM35 OBJECT IDENTIFIER ::= { cevChassis 762 }
cevChassisCe7341 OBJECT IDENTIFIER ::= { cevChassis 763 }
cevChassisCe7371 OBJECT IDENTIFIER ::= { cevChassis 764 }
cevChassisWsCbs3125gS OBJECT IDENTIFIER ::= { cevChassis 768 }
cevChassisWsC492810GE OBJECT IDENTIFIER ::= { cevChassis 770 }
cevChassisCat296048TTS OBJECT IDENTIFIER ::= { cevChassis 771 }
cevChassisCat29608TCS OBJECT IDENTIFIER ::= { cevChassis 772 }
cevChassisSr520FE OBJECT IDENTIFIER ::= { cevChassis 774 }
cevChassisSr520ADSL OBJECT IDENTIFIER ::= { cevChassis 775 }
cevChassisSr520ADSLi OBJECT IDENTIFIER ::= { cevChassis 776 }
cevChassisN7Kc7018 OBJECT IDENTIFIER ::= { cevChassis 777 }
cevChassisCat356012PCS OBJECT IDENTIFIER ::= { cevChassis 778 }
cevChassisCat296048PSTL OBJECT IDENTIFIER ::= { cevChassis 779 }
cevChassisASR9010 OBJECT IDENTIFIER ::= { cevChassis 780 }
cevChassisASR9006 OBJECT IDENTIFIER ::= { cevChassis 781 }
cevChassisASR14K4 OBJECT IDENTIFIER ::= { cevChassis 782 }
cevChassisASR14K8 OBJECT IDENTIFIER ::= { cevChassis 783 }
cevChassisCat3560v224tsD OBJECT IDENTIFIER ::= { cevChassis 784 }
cevChassisCat3560v224ts OBJECT IDENTIFIER ::= { cevChassis 785 }
cevChassisCat3560v224ps OBJECT IDENTIFIER ::= { cevChassis 786 }
cevChassisCat3750v224ts OBJECT IDENTIFIER ::= { cevChassis 787 }
cevChassisCat3750v224ps OBJECT IDENTIFIER ::= { cevChassis 788 }
cevChassisCat3560v248ts OBJECT IDENTIFIER ::= { cevChassis 789 }
cevChassisCat3560v248ps OBJECT IDENTIFIER ::= { cevChassis 790 }
cevChassisCat3750v248ts OBJECT IDENTIFIER ::= { cevChassis 791 }
cevChassisCat3750v248ps OBJECT IDENTIFIER ::= { cevChassis 792 }
cevChassisAirbr1430 OBJECT IDENTIFIER ::= { cevChassis 793 }
cevChassisNamApp2204rj45 OBJECT IDENTIFIER ::= { cevChassis 794 }
cevChassisNamApp2220 OBJECT IDENTIFIER ::= { cevChassis 795 }
cevChassisAIRAP1141 OBJECT IDENTIFIER ::= { cevChassis 796 }
cevChassisAIRAP1142 OBJECT IDENTIFIER ::= { cevChassis 797 }
cevChassisN5kC5010pBf OBJECT IDENTIFIER ::= { cevChassis 798 }
cevChassisASR9010DC OBJECT IDENTIFIER ::= { cevChassis 799 }
cevChassisASR9006DC OBJECT IDENTIFIER ::= { cevChassis 800 }
cevChassis18xxx OBJECT IDENTIFIER ::= { cevChassis 801 }
cevChassisc887Vdsl2 OBJECT IDENTIFIER ::= { cevChassis 802 }
cevChassisC1941 OBJECT IDENTIFIER ::= { cevChassis 803 }
cevChassisC2901 OBJECT IDENTIFIER ::= { cevChassis 804 }
cevChassisC2911 OBJECT IDENTIFIER ::= { cevChassis 805 }
cevChassisC2921 OBJECT IDENTIFIER ::= { cevChassis 806 }
cevChassisC2951 OBJECT IDENTIFIER ::= { cevChassis 807 }
cevChassisC3925 OBJECT IDENTIFIER ::= { cevChassis 808 }
cevChassisC3945 OBJECT IDENTIFIER ::= { cevChassis 809 }
cevChassisEsw52024pK9 OBJECT IDENTIFIER ::= { cevChassis 810 }
cevChassisEsw54024pK9 OBJECT IDENTIFIER ::= { cevChassis 811 }
cevChassisEsw52048pK9 OBJECT IDENTIFIER ::= { cevChassis 812 }
cevChassisEsw52024K9 OBJECT IDENTIFIER ::= { cevChassis 813 }
cevChassisEsw54024K9 OBJECT IDENTIFIER ::= { cevChassis 814 }
cevChassisEsw52048K9 OBJECT IDENTIFIER ::= { cevChassis 815 }
cevChassisEsw54048K9 OBJECT IDENTIFIER ::= { cevChassis 816 }
cevChassisNamApp2204sfp OBJECT IDENTIFIER ::= { cevChassis 817 }
cevChassisSR520T1 OBJECT IDENTIFIER ::= { cevChassis 818 }
cevChassisN2kC2148T1GE OBJECT IDENTIFIER ::= { cevChassis 820 }
cevChassisC1941W OBJECT IDENTIFIER ::= { cevChassis 827 }
cevChassisC888E OBJECT IDENTIFIER ::= { cevChassis 828 }
cevChassisC888EG OBJECT IDENTIFIER ::= { cevChassis 829 }
cevChassisIad888EF OBJECT IDENTIFIER ::= { cevChassis 830 }
cevChassisIad888EB OBJECT IDENTIFIER ::= { cevChassis 831 }
cevChassisC888ESRST OBJECT IDENTIFIER ::= { cevChassis 832 }
cevChassis3845nv OBJECT IDENTIFIER ::= { cevChassis 833 }
cevChassis3825nv OBJECT IDENTIFIER ::= { cevChassis 834 }
cevChassisWSC235048TD OBJECT IDENTIFIER ::= { cevChassis 836 }
cevChassis887M  OBJECT IDENTIFIER ::= { cevChassis 837 }
cevChassisASR9010AC OBJECT IDENTIFIER ::= { cevChassis 838 }
cevChassisASR9006AC OBJECT IDENTIFIER ::= { cevChassis 839 }
cevChassisN1KV  OBJECT IDENTIFIER ::= { cevChassis 840 }
cevChassisUCSN10S6100 OBJECT IDENTIFIER ::= { cevChassis 847 }
cevChassisCDScde420 OBJECT IDENTIFIER ::= { cevChassis 848 }
cevChassisCDScde220 OBJECT IDENTIFIER ::= { cevChassis 849 }
cevChassisCDScde110 OBJECT IDENTIFIER ::= { cevChassis 850 }
cevChassisCiscoCeVirtualBlade OBJECT IDENTIFIER ::= { cevChassis 851 }
cevChassisASR1002F OBJECT IDENTIFIER ::= { cevChassis 852 }
cevChassisADE2120 OBJECT IDENTIFIER ::= { cevChassis 853 }
cevChassisAIRAP3501 OBJECT IDENTIFIER ::= { cevChassis 860 }
cevChassisAIRAP3502 OBJECT IDENTIFIER ::= { cevChassis 861 }
cevChassisCDScde200 OBJECT IDENTIFIER ::= { cevChassis 862 }
cevChassisCDScde100 OBJECT IDENTIFIER ::= { cevChassis 863 }
cevChassisCDScde300 OBJECT IDENTIFIER ::= { cevChassis 864 }
cevChassisCDScde400 OBJECT IDENTIFIER ::= { cevChassis 865 }
cevChassisSps2004B OBJECT IDENTIFIER ::= { cevChassis 869 }
cevChassisSps204B OBJECT IDENTIFIER ::= { cevChassis 870 }
cevChassisAp541nAK9 OBJECT IDENTIFIER ::= { cevChassis 874 }
cevChassisAp541nEK9 OBJECT IDENTIFIER ::= { cevChassis 875 }
cevChassisAp541nNK9 OBJECT IDENTIFIER ::= { cevChassis 876 }
cevChassisSRP521 OBJECT IDENTIFIER ::= { cevChassis 877 }
cevChassisSRP526 OBJECT IDENTIFIER ::= { cevChassis 878 }
cevChassisSRP527 OBJECT IDENTIFIER ::= { cevChassis 879 }
cevChassisSRP541 OBJECT IDENTIFIER ::= { cevChassis 880 }
cevChassisSRP546 OBJECT IDENTIFIER ::= { cevChassis 881 }
cevChassisSRP547 OBJECT IDENTIFIER ::= { cevChassis 882 }
cevChassisVS510FXO OBJECT IDENTIFIER ::= { cevChassis 883 }
cevChassis887GVdsl2 OBJECT IDENTIFIER ::= { cevChassis 884 }
cevChassis887SrstVdsl2 OBJECT IDENTIFIER ::= { cevChassis 885 }
cevChassis59xx  OBJECT IDENTIFIER ::= { cevChassis 895 }
cevChassisCat296024LCS OBJECT IDENTIFIER ::= { cevChassis 896 }
cevChassisCat296024PCS OBJECT IDENTIFIER ::= { cevChassis 897 }
cevChassisCat296048PSTS OBJECT IDENTIFIER ::= { cevChassis 898 }
cevChassisCiscoNMWAE900 OBJECT IDENTIFIER ::= { cevChassis 900 }
cevChassisCiscoNMWAE700 OBJECT IDENTIFIER ::= { cevChassis 901 }
cevChassis5940  OBJECT IDENTIFIER ::= { cevChassis 902 }
cevChassisN4KIBMEth OBJECT IDENTIFIER ::= { cevChassis 903 }
cevChassisASR1001 OBJECT IDENTIFIER ::= { cevChassis 904 }
cevChassisASR1013 OBJECT IDENTIFIER ::= { cevChassis 905 }
cevChassisCDScde205 OBJECT IDENTIFIER ::= { cevChassis 906 }
cevChassisNexus1010 OBJECT IDENTIFIER ::= { cevChassis 907 }
cevChassisRaie1783Rms06t OBJECT IDENTIFIER ::= { cevChassis 908 }
cevChassisRaie1783Rms10t OBJECT IDENTIFIER ::= { cevChassis 909 }
cevChassisMXE5600 OBJECT IDENTIFIER ::= { cevChassis 910 }
cevChassisEsw5408pK9 OBJECT IDENTIFIER ::= { cevChassis 911 }
cevChassisEsw5208pK9 OBJECT IDENTIFIER ::= { cevChassis 912 }
cevChassisN2kC2232PP10GE OBJECT IDENTIFIER ::= { cevChassis 913 }
cevChassisN2kC2248TP1GE OBJECT IDENTIFIER ::= { cevChassis 914 }
cevChassisWsC4948e10GE OBJECT IDENTIFIER ::= { cevChassis 915 }
cevChassis1921k9 OBJECT IDENTIFIER ::= { cevChassis 928 }
cevChassis1905k9 OBJECT IDENTIFIER ::= { cevChassis 929 }
cevChassisN4KIBMCiscoEth OBJECT IDENTIFIER ::= { cevChassis 930 }
cevChassisASA5585 OBJECT IDENTIFIER ::= { cevChassis 931 }
cevChassisN7Kc7009 OBJECT IDENTIFIER ::= { cevChassis 932 }
cevChassisMwr2941DcA OBJECT IDENTIFIER ::= { cevChassis 933 }
cevChassisOeNm302 OBJECT IDENTIFIER ::= { cevChassis 937 }
cevChassisOeNm502 OBJECT IDENTIFIER ::= { cevChassis 938 }
cevChassisOeNm522 OBJECT IDENTIFIER ::= { cevChassis 939 }
cevChassisOeSmSre700 OBJECT IDENTIFIER ::= { cevChassis 940 }
cevChassisOeSmSre900 OBJECT IDENTIFIER ::= { cevChassis 941 }
cevChassisCDScde2202s3 OBJECT IDENTIFIER ::= { cevChassis 944 }
cevChassisWsC3750x24 OBJECT IDENTIFIER ::= { cevChassis 945 }
cevChassisWsC3750x48 OBJECT IDENTIFIER ::= { cevChassis 946 }
cevChassisWsC3750x24P OBJECT IDENTIFIER ::= { cevChassis 947 }
cevChassisWsC3750x48P OBJECT IDENTIFIER ::= { cevChassis 948 }
cevChassisWsC3560x24 OBJECT IDENTIFIER ::= { cevChassis 949 }
cevChassisWsC3560x48 OBJECT IDENTIFIER ::= { cevChassis 950 }
cevChassis1841Ck9 OBJECT IDENTIFIER ::= { cevChassis 957 }
cevChassis2801Ck9 OBJECT IDENTIFIER ::= { cevChassis 958 }
cevChassis2811Ck9 OBJECT IDENTIFIER ::= { cevChassis 959 }
cevChassis2821Ck9 OBJECT IDENTIFIER ::= { cevChassis 960 }
cevChassis3825Ck9 OBJECT IDENTIFIER ::= { cevChassis 962 }
cevChassis3845Ck9 OBJECT IDENTIFIER ::= { cevChassis 963 }
cevChassisAIRAP1262 OBJECT IDENTIFIER ::= { cevChassis 966 }
cevChassisAIRAP1261 OBJECT IDENTIFIER ::= { cevChassis 967 }
cevChassis892F  OBJECT IDENTIFIER ::= { cevChassis 968 }
cevChassisMe3600x24fsM OBJECT IDENTIFIER ::= { cevChassis 969 }
cevChassisMe3600x24tsM OBJECT IDENTIFIER ::= { cevChassis 970 }
cevChassisMe3800x24fsM OBJECT IDENTIFIER ::= { cevChassis 971 }
cevChassisCGR2010 OBJECT IDENTIFIER ::= { cevChassis 972 }
cevChassisWsC2960s48tsS OBJECT IDENTIFIER ::= { cevChassis 973 }
cevChassisWsC2960s24tsS OBJECT IDENTIFIER ::= { cevChassis 974 }
cevChassisWsC2960s48fpdL OBJECT IDENTIFIER ::= { cevChassis 975 }
cevChassisWsC2960s48lpdL OBJECT IDENTIFIER ::= { cevChassis 976 }
cevChassisWsC2960s48tdL OBJECT IDENTIFIER ::= { cevChassis 977 }
cevChassisWsC2960s24pdL OBJECT IDENTIFIER ::= { cevChassis 978 }
cevChassisWsC2960s24tdL OBJECT IDENTIFIER ::= { cevChassis 979 }
cevChassisWsC2960s48fpsL OBJECT IDENTIFIER ::= { cevChassis 980 }
cevChassisWsC2960s48lpsL OBJECT IDENTIFIER ::= { cevChassis 981 }
cevChassisWsC2960s24psL OBJECT IDENTIFIER ::= { cevChassis 982 }
cevChassisWsC2960s48tsL OBJECT IDENTIFIER ::= { cevChassis 983 }
cevChassisWsC2960S24tsL OBJECT IDENTIFIER ::= { cevChassis 984 }
cevChassis1906Ck9 OBJECT IDENTIFIER ::= { cevChassis 985 }
cevChassisAIRAP1042 OBJECT IDENTIFIER ::= { cevChassis 986 }
cevChassisAIRAP1041 OBJECT IDENTIFIER ::= { cevChassis 987 }
cevChassis887Va OBJECT IDENTIFIER ::= { cevChassis 988 }
cevChassis886Va OBJECT IDENTIFIER ::= { cevChassis 989 }
cevChassis867Va OBJECT IDENTIFIER ::= { cevChassis 990 }
cevChassis887VaM OBJECT IDENTIFIER ::= { cevChassis 991 }
cevChassisASR1001IDC2pOc3Pos OBJECT IDENTIFIER ::= { cevChassis 992 }
cevChassisASR1001IDC4pT3 OBJECT IDENTIFIER ::= { cevChassis 993 }
cevChassisASR1001IDC4pGE OBJECT IDENTIFIER ::= { cevChassis 994 }
cevChassisASR1001IDC8pCT1E1 OBJECT IDENTIFIER ::= { cevChassis 995 }
cevChassisASR1001IDCHDD OBJECT IDENTIFIER ::= { cevChassis 996 }
cevChassisCat2960cPD8TT OBJECT IDENTIFIER ::= { cevChassis 997 }
cevChassisCGS252024TC OBJECT IDENTIFIER ::= { cevChassis 998 }
cevChassisCGS252016S8PC OBJECT IDENTIFIER ::= { cevChassis 999 }
cevChassisWsC236048TdS OBJECT IDENTIFIER ::= { cevChassis 1002 }
cevChassisN2kC2232TT10GE OBJECT IDENTIFIER ::= { cevChassis 1003 }
cevChassisN2kC2232TP10GE OBJECT IDENTIFIER ::= { cevChassis 1004 }
cevChassisN2kC2248TT1GE OBJECT IDENTIFIER ::= { cevChassis 1005 }
cevChassisN2kC2224TP1GE OBJECT IDENTIFIER ::= { cevChassis 1006 }
cevChassisCDScde250 OBJECT IDENTIFIER ::= { cevChassis 1007 }
cevChassisN5kC5548p OBJECT IDENTIFIER ::= { cevChassis 1008 }
cevChassis881G2 OBJECT IDENTIFIER ::= { cevChassis 1009 }
cevChassisWsC3750v224fsS OBJECT IDENTIFIER ::= { cevChassis 1010 }
cevChassisOeVWaas OBJECT IDENTIFIER ::= { cevChassis 1011 }
cevChassisCrs16SB OBJECT IDENTIFIER ::= { cevChassis 1012 }
cevChassisCat2960cG8TC OBJECT IDENTIFIER ::= { cevChassis 1014 }
cevChassisECDS1100 OBJECT IDENTIFIER ::= { cevChassis 1017 }
cevChassisECDS3100 OBJECT IDENTIFIER ::= { cevChassis 1018 }
cevChassisIE301016S8PC OBJECT IDENTIFIER ::= { cevChassis 1019 }
cevChassisIE301024TC OBJECT IDENTIFIER ::= { cevChassis 1020 }
cevChassisWsC4948ef10GE OBJECT IDENTIFIER ::= { cevChassis 1023 }
cevChassisWave284K9 OBJECT IDENTIFIER ::= { cevChassis 1024 }
cevChassisWave584K9 OBJECT IDENTIFIER ::= { cevChassis 1025 }
cevChassisWave684K9 OBJECT IDENTIFIER ::= { cevChassis 1026 }
cevChassisWave7441K9 OBJECT IDENTIFIER ::= { cevChassis 1027 }
cevChassisWave7471K9 OBJECT IDENTIFIER ::= { cevChassis 1028 }
cevChassisWave7626K9 OBJECT IDENTIFIER ::= { cevChassis 1029 }
cevChassisCat292848TCC OBJECT IDENTIFIER ::= { cevChassis 1032 }
cevChassisCat292824TCC OBJECT IDENTIFIER ::= { cevChassis 1033 }
cevChassisCat292824LTC OBJECT IDENTIFIER ::= { cevChassis 1034 }
cevChassisGrwicDes2s8pc OBJECT IDENTIFIER ::= { cevChassis 1036 }
cevChassisGrwicDes6s OBJECT IDENTIFIER ::= { cevChassis 1037 }
cevChassisN5kC5596Up OBJECT IDENTIFIER ::= { cevChassis 1038 }
cevChassisC1861eUc2BriK9 OBJECT IDENTIFIER ::= { cevChassis 1039 }
cevChassisC1861eUc4FxoK9 OBJECT IDENTIFIER ::= { cevChassis 1040 }
cevChassisC1861eSrstFK9 OBJECT IDENTIFIER ::= { cevChassis 1041 }
cevChassisC1861eSrstBK9 OBJECT IDENTIFIER ::= { cevChassis 1042 }
cevChassisC1861eSrstCFK9 OBJECT IDENTIFIER ::= { cevChassis 1043 }
cevChassisC1861eSrstCBK9 OBJECT IDENTIFIER ::= { cevChassis 1044 }
cevChassis88XG2DSL OBJECT IDENTIFIER ::= { cevChassis 1045 }
cevChassisN2kC2248TPE1GE OBJECT IDENTIFIER ::= { cevChassis 1046 }
cevChassisWave8541 OBJECT IDENTIFIER ::= { cevChassis 1047 }
cevChassisWave7571 OBJECT IDENTIFIER ::= { cevChassis 1048 }
cevChassisWave7541 OBJECT IDENTIFIER ::= { cevChassis 1049 }
cevChassisWave694 OBJECT IDENTIFIER ::= { cevChassis 1050 }
cevChassisWave594 OBJECT IDENTIFIER ::= { cevChassis 1051 }
cevChassisWave294 OBJECT IDENTIFIER ::= { cevChassis 1052 }
cevChassis5915  OBJECT IDENTIFIER ::= { cevChassis 1053 }
cevChassis86xVAE OBJECT IDENTIFIER ::= { cevChassis 1055 }
cevChassisAp802gn OBJECT IDENTIFIER ::= { cevChassis 1056 }
cevChassisN2kB22HPP OBJECT IDENTIFIER ::= { cevChassis 1058 }
cevChassisN2kC2248GVP OBJECT IDENTIFIER ::= { cevChassis 1059 }
cevChassisN3kC3064PQ OBJECT IDENTIFIER ::= { cevChassis 1060 }
cevChassisN2kC2232TM10GE OBJECT IDENTIFIER ::= { cevChassis 1061 }
cevChassisUCSFI6248UP OBJECT IDENTIFIER ::= { cevChassis 1062 }
cevChassisUCSFI6296UP OBJECT IDENTIFIER ::= { cevChassis 1063 }
cevChassis2811ve OBJECT IDENTIFIER ::= { cevChassis 1064 }
cevChassis1841ve OBJECT IDENTIFIER ::= { cevChassis 1065 }
cevChassis2960c8tcS OBJECT IDENTIFIER ::= { cevChassis 1066 }
cevChassis2960c8tcL OBJECT IDENTIFIER ::= { cevChassis 1067 }
cevChassis2960c8pcL OBJECT IDENTIFIER ::= { cevChassis 1068 }
cevChassis2960c12pcL OBJECT IDENTIFIER ::= { cevChassis 1069 }
cevChassis3560cpd8ptS OBJECT IDENTIFIER ::= { cevChassis 1070 }
cevChassis886Vag7K9 OBJECT IDENTIFIER ::= { cevChassis 1071 }
cevChassis887VagSK9 OBJECT IDENTIFIER ::= { cevChassis 1072 }
cevChassis887Vag7K9 OBJECT IDENTIFIER ::= { cevChassis 1073 }
cevChassis887Vamg7K9 OBJECT IDENTIFIER ::= { cevChassis 1074 }
cevChassis888Eg7K9 OBJECT IDENTIFIER ::= { cevChassis 1075 }
cevChassis881GUK9 OBJECT IDENTIFIER ::= { cevChassis 1076 }
cevChassis881GSK9 OBJECT IDENTIFIER ::= { cevChassis 1077 }
cevChassis881GVK9 OBJECT IDENTIFIER ::= { cevChassis 1078 }
cevChassis881GBK9 OBJECT IDENTIFIER ::= { cevChassis 1079 }
cevChassis881G7K9 OBJECT IDENTIFIER ::= { cevChassis 1080 }
cevChassis881G7AK9 OBJECT IDENTIFIER ::= { cevChassis 1081 }
cevChassisN5kC5548UP OBJECT IDENTIFIER ::= { cevChassis 1084 }
cevChassis881W  OBJECT IDENTIFIER ::= { cevChassis 1085 }
cevChassis886VAW OBJECT IDENTIFIER ::= { cevChassis 1086 }
cevChassis887VAMW OBJECT IDENTIFIER ::= { cevChassis 1087 }
cevChassis887VAW OBJECT IDENTIFIER ::= { cevChassis 1088 }
cevChassis819G  OBJECT IDENTIFIER ::= { cevChassis 1089 }
cevChassis819HG OBJECT IDENTIFIER ::= { cevChassis 1090 }
cevChassisIAD886VA OBJECT IDENTIFIER ::= { cevChassis 1091 }
cevChassisIAD886VAJ OBJECT IDENTIFIER ::= { cevChassis 1092 }
cevChassisIAD887VA OBJECT IDENTIFIER ::= { cevChassis 1093 }
cevChassisIAD887VAM OBJECT IDENTIFIER ::= { cevChassis 1094 }
cevChassisPCM   OBJECT IDENTIFIER ::= { cevChassis 1095 }
cevChassisDSavsm OBJECT IDENTIFIER ::= { cevChassis 1102 }
cevChassisEcdsVB OBJECT IDENTIFIER ::= { cevChassis 1104 }
cevChassisN3kC3064PQ10GE OBJECT IDENTIFIER ::= { cevChassis 1105 }
cevChassisN3kC3048TP1GE OBJECT IDENTIFIER ::= { cevChassis 1106 }
cevChassisN3kC3016Q40GE OBJECT IDENTIFIER ::= { cevChassis 1107 }
cevChassisASR903 OBJECT IDENTIFIER ::= { cevChassis 1118 }
cevChassis3560c12pcS OBJECT IDENTIFIER ::= { cevChassis 1121 }
cevChassis3560c8pcS OBJECT IDENTIFIER ::= { cevChassis 1122 }
cevChassisCrs8SB OBJECT IDENTIFIER ::= { cevChassis 1123 }
cevChassisRAIE1783BMS06S OBJECT IDENTIFIER ::= { cevChassis 1124 }
cevChassisRAIE1783BMS06T OBJECT IDENTIFIER ::= { cevChassis 1125 }
cevChassisRAIE1783BMS06SG OBJECT IDENTIFIER ::= { cevChassis 1126 }
cevChassisRAIE1783BMS10C OBJECT IDENTIFIER ::= { cevChassis 1127 }
cevChassisRAIE1783BMS06TG OBJECT IDENTIFIER ::= { cevChassis 1128 }
cevChassisRAIE1783BMS10CG OBJECT IDENTIFIER ::= { cevChassis 1129 }
cevChassisRAIE1783BMS20C OBJECT IDENTIFIER ::= { cevChassis 1130 }
cevChassisRAIE1783BMS20CG OBJECT IDENTIFIER ::= { cevChassis 1131 }
cevChassisRAIE1783BMS20CGPK OBJECT IDENTIFIER ::= { cevChassis 1132 }
cevChassisIE20004TS OBJECT IDENTIFIER ::= { cevChassis 1133 }
cevChassisIE20004T OBJECT IDENTIFIER ::= { cevChassis 1134 }
cevChassisIE20004TSG OBJECT IDENTIFIER ::= { cevChassis 1135 }
cevChassisIE20004TG OBJECT IDENTIFIER ::= { cevChassis 1136 }
cevChassisIE20008TC OBJECT IDENTIFIER ::= { cevChassis 1137 }
cevChassisIE20008TCG OBJECT IDENTIFIER ::= { cevChassis 1138 }
cevChassisIE200016TC OBJECT IDENTIFIER ::= { cevChassis 1139 }
cevChassisIE200016TCG OBJECT IDENTIFIER ::= { cevChassis 1140 }
cevChassisIE200016TCGX OBJECT IDENTIFIER ::= { cevChassis 1141 }
cevChassisASR5000CHSSYSK9 OBJECT IDENTIFIER ::= { cevChassis 1145 }
cevChassisASR55CHSSYS OBJECT IDENTIFIER ::= { cevChassis 1146 }
cevChassisN7Kc7004 OBJECT IDENTIFIER ::= { cevChassis 1147 }
cevChassisASR901 OBJECT IDENTIFIER ::= { cevChassis 1159 }
cevChassisASR901E OBJECT IDENTIFIER ::= { cevChassis 1160 }
cevChassisOeSmSre710 OBJECT IDENTIFIER ::= { cevChassis 1161 }
cevChassisOeSmSre910 OBJECT IDENTIFIER ::= { cevChassis 1162 }
cevChassisN3kC3064PQ10GX OBJECT IDENTIFIER ::= { cevChassis 1163 }
cevChassisCSR1000v OBJECT IDENTIFIER ::= { cevChassis 1165 }
cevChassisFlowAgent3000 OBJECT IDENTIFIER ::= { cevChassis 1166 }
cevChassisASR1002X OBJECT IDENTIFIER ::= { cevChassis 1167 }
cevChassisNamApp2304 OBJECT IDENTIFIER ::= { cevChassis 1168 }
cevChassisNamApp2320 OBJECT IDENTIFIER ::= { cevChassis 1169 }
cevChassisECDS50IVB OBJECT IDENTIFIER ::= { cevChassis 1173 }
cevChassisN5kC5596TFA OBJECT IDENTIFIER ::= { cevChassis 1175 }
cevChassisASR9001 OBJECT IDENTIFIER ::= { cevChassis 1178 }
cevChassis819GM OBJECT IDENTIFIER ::= { cevChassis 1188 }
cevChassis819HGM OBJECT IDENTIFIER ::= { cevChassis 1189 }
cevChassisN2kC2232TME10GE OBJECT IDENTIFIER ::= { cevChassis 1190 }
cevChassisCDScde2502s6 OBJECT IDENTIFIER ::= { cevChassis 1191 }
cevChassisCDScde2502m0 OBJECT IDENTIFIER ::= { cevChassis 1192 }
cevChassisCDScde2502s8 OBJECT IDENTIFIER ::= { cevChassis 1193 }
cevChassisASA1000V OBJECT IDENTIFIER ::= { cevChassis 1194 }
cevChassisISR4400 OBJECT IDENTIFIER ::= { cevChassis 1195 }
cevChassisMe3600x24CxM OBJECT IDENTIFIER ::= { cevChassis 1196 }
cevChassisA9014CFD OBJECT IDENTIFIER ::= { cevChassis 1197 }
cevChassisA9014CFtD OBJECT IDENTIFIER ::= { cevChassis 1198 }
cevChassisMDE10XVB OBJECT IDENTIFIER ::= { cevChassis 1199 }
cevChassisWsC4500x16 OBJECT IDENTIFIER ::= { cevChassis 1202 }
cevChassisWsC4500x32 OBJECT IDENTIFIER ::= { cevChassis 1203 }
cevChassisN2kC2248PQ10GE OBJECT IDENTIFIER ::= { cevChassis 1205 }
cevChassisCDScde2502s9 OBJECT IDENTIFIER ::= { cevChassis 1206 }
cevChassisCDScde2502s10 OBJECT IDENTIFIER ::= { cevChassis 1207 }
cevChassisCDScdeGeneric OBJECT IDENTIFIER ::= { cevChassis 1208 }
cevChassisN2kB22FTSP OBJECT IDENTIFIER ::= { cevChassis 1210 }
cevChassisN2kB22DELLP OBJECT IDENTIFIER ::= { cevChassis 1211 }
cevChassisASR9922Dc OBJECT IDENTIFIER ::= { cevChassis 1225 }
cevChassisASR9922Ac OBJECT IDENTIFIER ::= { cevChassis 1226 }
cevChassisN6kC600496Q OBJECT IDENTIFIER ::= { cevChassis 1237 }
cevChassisN3kC3548P10G OBJECT IDENTIFIER ::= { cevChassis 1238 }
cevChassisN3kC3064TQ10GT OBJECT IDENTIFIER ::= { cevChassis 1239 }
cevChassis86xVAEW OBJECT IDENTIFIER ::= { cevChassis 1240 }
cevChassisASR9912AC OBJECT IDENTIFIER ::= { cevChassis 1241 }
cevChassisASR9912DC OBJECT IDENTIFIER ::= { cevChassis 1242 }
cevChassisOeKWaas OBJECT IDENTIFIER ::= { cevChassis 1243 }
cevChassisasr1000 OBJECT IDENTIFIER ::= { cevChassis 1244 }
cevChassisCDScde2202s4 OBJECT IDENTIFIER ::= { cevChassis 1245 }
cevChassisISR4441 OBJECT IDENTIFIER ::= { cevChassis 1246 }
cevChassisISR4442 OBJECT IDENTIFIER ::= { cevChassis 1247 }
cevChassisISR4451 OBJECT IDENTIFIER ::= { cevChassis 1248 }
cevChassisISR4452 OBJECT IDENTIFIER ::= { cevChassis 1249 }
cevChassisASR1002XC OBJECT IDENTIFIER ::= { cevChassis 1250 }
cevChassisAIRAP1553 OBJECT IDENTIFIER ::= { cevChassis 1251 }
cevChassisAIRAP1552 OBJECT IDENTIFIER ::= { cevChassis 1252 }
cevChassisAIRAP1602 OBJECT IDENTIFIER ::= { cevChassis 1253 }
cevChassisAIRAP1601 OBJECT IDENTIFIER ::= { cevChassis 1254 }
cevChassisAIRAP2602 OBJECT IDENTIFIER ::= { cevChassis 1255 }
cevChassisAIRAP2601 OBJECT IDENTIFIER ::= { cevChassis 1256 }
cevChassisAIRAP3602 OBJECT IDENTIFIER ::= { cevChassis 1257 }
cevChassisAIRAP3601 OBJECT IDENTIFIER ::= { cevChassis 1258 }
cevChassisWsC2960x48fpdL OBJECT IDENTIFIER ::= { cevChassis 1259 }
cevChassisWsC2960x48lpdL OBJECT IDENTIFIER ::= { cevChassis 1260 }
cevChassisWsC2960x48tdL OBJECT IDENTIFIER ::= { cevChassis 1261 }
cevChassisWsC2960x24pdL OBJECT IDENTIFIER ::= { cevChassis 1262 }
cevChassisWsC2960x24tdL OBJECT IDENTIFIER ::= { cevChassis 1263 }
cevChassisWsC2960x48fpsL OBJECT IDENTIFIER ::= { cevChassis 1264 }
cevChassisWsC2960x48lpsL OBJECT IDENTIFIER ::= { cevChassis 1265 }
cevChassisWsC2960x24psL OBJECT IDENTIFIER ::= { cevChassis 1266 }
cevChassisWsC2960x48tsL OBJECT IDENTIFIER ::= { cevChassis 1267 }
cevChassisWsC2960x24tsL OBJECT IDENTIFIER ::= { cevChassis 1268 }
cevChassisWsC2960x24psqL OBJECT IDENTIFIER ::= { cevChassis 1269 }
cevChassisWsC2960x48lpsS OBJECT IDENTIFIER ::= { cevChassis 1270 }
cevChassisWsC2960x24psS OBJECT IDENTIFIER ::= { cevChassis 1271 }
cevChassisWsC2960x48tsLL OBJECT IDENTIFIER ::= { cevChassis 1272 }
cevChassisWsC2960x24tsLL OBJECT IDENTIFIER ::= { cevChassis 1273 }
cevChassisWsC3560x48U OBJECT IDENTIFIER ::= { cevChassis 1274 }
cevChassisWsC3560x24U OBJECT IDENTIFIER ::= { cevChassis 1275 }
cevChassisWsC3750x48U OBJECT IDENTIFIER ::= { cevChassis 1276 }
cevChassisWsC3750x24U OBJECT IDENTIFIER ::= { cevChassis 1277 }
cevChassisIE200016TCGP OBJECT IDENTIFIER ::= { cevChassis 1278 }
cevChassisIE200016TCGEP OBJECT IDENTIFIER ::= { cevChassis 1279 }
cevChassisIE200016TCGNXP OBJECT IDENTIFIER ::= { cevChassis 1280 }
cevChassisRAIE1783BMS12T4E2CGL OBJECT IDENTIFIER ::= { cevChassis 1281 }
cevChassisRAIE1783BMS12T4E2CGP OBJECT IDENTIFIER ::= { cevChassis 1282 }
cevChassisRAIE1783BMS12T4E2CGNK OBJECT IDENTIFIER ::= { cevChassis 1283 }
cevChassisIE20008TCGN OBJECT IDENTIFIER ::= { cevChassis 1284 }
cevChassisIE200016TCGN OBJECT IDENTIFIER ::= { cevChassis 1285 }
cevChassisRAIE1783BMS10CGN OBJECT IDENTIFIER ::= { cevChassis 1286 }
cevChassisRAIE1783BMS20CGN OBJECT IDENTIFIER ::= { cevChassis 1287 }
cevChassisNexus1010X OBJECT IDENTIFIER ::= { cevChassis 1288 }
cevChassisNexus1110S OBJECT IDENTIFIER ::= { cevChassis 1289 }
cevChassisNexus1110XL OBJECT IDENTIFIER ::= { cevChassis 1290 }
cevChassisNexus1110X OBJECT IDENTIFIER ::= { cevChassis 1291 }
cevChassisNexus1000VKVM OBJECT IDENTIFIER ::= { cevChassis 1292 }
cevChassisNexus1000VMH OBJECT IDENTIFIER ::= { cevChassis 1294 }
cevChassisVG202XM OBJECT IDENTIFIER ::= { cevChassis 1295 }
cevChassisVG204XM OBJECT IDENTIFIER ::= { cevChassis 1296 }
cevChassisAsr9904AC OBJECT IDENTIFIER ::= { cevChassis 1301 }
cevChassisAsr9904DC OBJECT IDENTIFIER ::= { cevChassis 1302 }
cevChassisME2600X OBJECT IDENTIFIER ::= { cevChassis 1303 }
cevChassisNCSCHASSIS OBJECT IDENTIFIER ::= { cevChassis 1304 }
cevChassisC6807xl OBJECT IDENTIFIER ::= { cevChassis 1305 }
cevChassisN6kC600164P OBJECT IDENTIFIER ::= { cevChassis 1308 }
cevChassis131WsC385024U OBJECT IDENTIFIER ::= { cevChassis 1309 }
cevChassis131WsC385048U OBJECT IDENTIFIER ::= { cevChassis 1310 }
cevChassisDSC9250IK9 OBJECT IDENTIFIER ::= { cevChassis 1326 }
cevChassisDSC9710 OBJECT IDENTIFIER ::= { cevChassis 1327 }
cevChassisC6880xle OBJECT IDENTIFIER ::= { cevChassis 1328 }
cevChassisIE2000U16TCGP OBJECT IDENTIFIER ::= { cevChassis 1338 }
cevChassisN2kB22IBMP OBJECT IDENTIFIER ::= { cevChassis 1339 }
cevChassisN6kC600164T OBJECT IDENTIFIER ::= { cevChassis 1340 }
cevChassisWsC2960P48PstL OBJECT IDENTIFIER ::= { cevChassis 1342 }
cevChassisWsC2960P24PcL OBJECT IDENTIFIER ::= { cevChassis 1343 }
cevChassisWsC2960P24LcL OBJECT IDENTIFIER ::= { cevChassis 1344 }
cevChassisWsC2960P48TcL OBJECT IDENTIFIER ::= { cevChassis 1345 }
cevChassisWsC2960P24TcL OBJECT IDENTIFIER ::= { cevChassis 1346 }
cevChassisWsC2960P48PstS OBJECT IDENTIFIER ::= { cevChassis 1347 }
cevChassisWsC2960P24PcS OBJECT IDENTIFIER ::= { cevChassis 1348 }
cevChassisWsC2960P24LcS OBJECT IDENTIFIER ::= { cevChassis 1349 }
cevChassisWsC2960P48TcS OBJECT IDENTIFIER ::= { cevChassis 1350 }
cevChassisWsC2960P24TcS OBJECT IDENTIFIER ::= { cevChassis 1351 }
cevChassisN77c7718 OBJECT IDENTIFIER ::= { cevChassis 1352 }
cevChassisN77c7710 OBJECT IDENTIFIER ::= { cevChassis 1353 }
cevChassisN77c7706 OBJECT IDENTIFIER ::= { cevChassis 1354 }
cevChassisWsC2960XR48FpdI OBJECT IDENTIFIER ::= { cevChassis 1355 }
cevChassisWsC2960XR48LpdI OBJECT IDENTIFIER ::= { cevChassis 1356 }
cevChassisWsC2960XR48TdI OBJECT IDENTIFIER ::= { cevChassis 1357 }
cevChassisWsC2960XR24PdI OBJECT IDENTIFIER ::= { cevChassis 1358 }
cevChassisWsC2960XR24TdI OBJECT IDENTIFIER ::= { cevChassis 1359 }
cevChassisWsC2960XR48FpsI OBJECT IDENTIFIER ::= { cevChassis 1360 }
cevChassisWsC2960XR48LpsI OBJECT IDENTIFIER ::= { cevChassis 1361 }
cevChassisWsC2960XR48TsI OBJECT IDENTIFIER ::= { cevChassis 1362 }
cevChassisWsC2960XR24PsI OBJECT IDENTIFIER ::= { cevChassis 1363 }
cevChassisWsC2960XR24TsI OBJECT IDENTIFIER ::= { cevChassis 1364 }
cevChassisA901S4SGFD OBJECT IDENTIFIER ::= { cevChassis 1375 }
cevChassisA901S3SGFD OBJECT IDENTIFIER ::= { cevChassis 1376 }
cevChassisA901S2SGFD OBJECT IDENTIFIER ::= { cevChassis 1377 }
cevChassisA901S3SGFAH OBJECT IDENTIFIER ::= { cevChassis 1378 }
cevChassisA901S2SGFAH OBJECT IDENTIFIER ::= { cevChassis 1379 }
cevChassisASR901AC10G OBJECT IDENTIFIER ::= { cevChassis 1380 }
cevChassisASR901DC10G OBJECT IDENTIFIER ::= { cevChassis 1381 }
cevChassisASR901eAC10G OBJECT IDENTIFIER ::= { cevChassis 1382 }
cevChassisASR901eDC10G OBJECT IDENTIFIER ::= { cevChassis 1383 }
cevChassisIE2000U4STSG OBJECT IDENTIFIER ::= { cevChassis 1384 }
cevChassisC881  OBJECT IDENTIFIER ::= { cevChassis 1385 }
cevChassisC886VA OBJECT IDENTIFIER ::= { cevChassis 1386 }
cevChassisC887VA OBJECT IDENTIFIER ::= { cevChassis 1387 }
cevChassisN3KC3172PQ10GE OBJECT IDENTIFIER ::= { cevChassis 1388 }
cevChassisN3KC3172TQ10GT OBJECT IDENTIFIER ::= { cevChassis 1389 }
cevChassisN3KC3132Q40GE OBJECT IDENTIFIER ::= { cevChassis 1390 }
cevChassisN3KC3132Q40GS OBJECT IDENTIFIER ::= { cevChassis 1391 }
cevChassisASR9001S OBJECT IDENTIFIER ::= { cevChassis 1392 }
cevChassisIE20008T67B OBJECT IDENTIFIER ::= { cevChassis 1393 }
cevChassisIE200016T67B OBJECT IDENTIFIER ::= { cevChassis 1394 }
cevChassisIE200024T67B OBJECT IDENTIFIER ::= { cevChassis 1395 }
cevChassisIE20008T67PGE OBJECT IDENTIFIER ::= { cevChassis 1396 }
cevChassisIE200016T67PGE OBJECT IDENTIFIER ::= { cevChassis 1397 }
cevChassisRAIE1783ZMS8TA OBJECT IDENTIFIER ::= { cevChassis 1398 }
cevChassisRAIE1783ZMS16TA OBJECT IDENTIFIER ::= { cevChassis 1399 }
cevChassisRAIE1783ZMS24TA OBJECT IDENTIFIER ::= { cevChassis 1400 }
cevChassisRAIE1783ZMS4T4E2TGP OBJECT IDENTIFIER ::= { cevChassis 1401 }
cevChassisRAIE1783ZMS8T8E2TGP OBJECT IDENTIFIER ::= { cevChassis 1402 }
cevChassisC888  OBJECT IDENTIFIER ::= { cevChassis 1403 }
cevChassisC891F OBJECT IDENTIFIER ::= { cevChassis 1404 }
cevChassisC891FW OBJECT IDENTIFIER ::= { cevChassis 1405 }
cevChassisASR1001X OBJECT IDENTIFIER ::= { cevChassis 1406 }
cevChassis1783WAP5100xK9 OBJECT IDENTIFIER ::= { cevChassis 1407 }
cevChassisCDScde2502s5 OBJECT IDENTIFIER ::= { cevChassis 1408 }
cevChassisN5KC56128P OBJECT IDENTIFIER ::= { cevChassis 1409 }
cevChassisN5KC5672UP OBJECT IDENTIFIER ::= { cevChassis 1410 }
cevChassisIE2000U4TG OBJECT IDENTIFIER ::= { cevChassis 1412 }
cevChassisIE2000U4TSG OBJECT IDENTIFIER ::= { cevChassis 1413 }
cevChassisIE2000U8TCG OBJECT IDENTIFIER ::= { cevChassis 1414 }
cevChassisIE2000U16TCG OBJECT IDENTIFIER ::= { cevChassis 1415 }
cevChassisIE2000U16TCGX OBJECT IDENTIFIER ::= { cevChassis 1416 }
cevChassisN3KC3132Q40GX OBJECT IDENTIFIER ::= { cevChassis 1417 }
cevChassisVG310 OBJECT IDENTIFIER ::= { cevChassis 1418 }
cevChassisVG320 OBJECT IDENTIFIER ::= { cevChassis 1419 }
cevChassisDSC9706 OBJECT IDENTIFIER ::= { cevChassis 1420 }
cevChassisAIRAP3702 OBJECT IDENTIFIER ::= { cevChassis 1421 }
cevChassisAIRAP702 OBJECT IDENTIFIER ::= { cevChassis 1422 }
cevChassisAIRAP1532 OBJECT IDENTIFIER ::= { cevChassis 1423 }
cevChassisC6800IA48FPD OBJECT IDENTIFIER ::= { cevChassis 1424 }
cevChassisC6800IA48TD OBJECT IDENTIFIER ::= { cevChassis 1425 }
cevChassisNCS4016SAAC OBJECT IDENTIFIER ::= { cevChassis 1426 }
cevChassis131WsC385024S OBJECT IDENTIFIER ::= { cevChassis 1433 }
cevChassis131WsC385012S OBJECT IDENTIFIER ::= { cevChassis 1434 }
cevChassisASR902 OBJECT IDENTIFIER ::= { cevChassis 1449 }
cevChassisVASA  OBJECT IDENTIFIER ::= { cevChassis 1451 }
cevChassisUCSFIM6324 OBJECT IDENTIFIER ::= { cevChassis 1454 }
cevChassisN9Kc9508 OBJECT IDENTIFIER ::= { cevChassis 1467 }
cevChassisME12006sAO OBJECT IDENTIFIER ::= { cevChassis 1469 }
cevChassisME12006sD OBJECT IDENTIFIER ::= { cevChassis 1470 }
cevChassisME12006sA OBJECT IDENTIFIER ::= { cevChassis 1471 }
cevChassis1783SR OBJECT IDENTIFIER ::= { cevChassis 1472 }
cevChassisWapAP702 OBJECT IDENTIFIER ::= { cevChassis 1475 }
cevChassisWapAP2602 OBJECT IDENTIFIER ::= { cevChassis 1476 }
cevChassisWapAP1602 OBJECT IDENTIFIER ::= { cevChassis 1477 }
cevChassisISR4431 OBJECT IDENTIFIER ::= { cevChassis 1485 }
cevChassisC6880x OBJECT IDENTIFIER ::= { cevChassis 1486 }
cevChassisAIRAP2702 OBJECT IDENTIFIER ::= { cevChassis 1487 }
cevChassisUCSFI6332 OBJECT IDENTIFIER ::= { cevChassis 1488 }
cevChassisN6kC6004 OBJECT IDENTIFIER ::= { cevChassis 1489 }
cevChassisAsr9000V24vDcA OBJECT IDENTIFIER ::= { cevChassis 1490 }
cevChassisDSC9148SK9 OBJECT IDENTIFIER ::= { cevChassis 1491 }
cevChassisRT1081K9 OBJECT IDENTIFIER ::= { cevChassis 1494 }
cevChassisRT1091FK9 OBJECT IDENTIFIER ::= { cevChassis 1495 }
cevChassisRT2241K9 OBJECT IDENTIFIER ::= { cevChassis 1496 }
cevChassisRT2221K9 OBJECT IDENTIFIER ::= { cevChassis 1497 }
cevChassisRT2241WCK9 OBJECT IDENTIFIER ::= { cevChassis 1498 }
cevChassisRT3211K9 OBJECT IDENTIFIER ::= { cevChassis 1499 }
cevChassisRT3221K9 OBJECT IDENTIFIER ::= { cevChassis 1500 }
cevChassisRT3201K9 OBJECT IDENTIFIER ::= { cevChassis 1501 }
cevChassisN9Kc9516 OBJECT IDENTIFIER ::= { cevChassis 1506 }
cevChassisN9Kc9504 OBJECT IDENTIFIER ::= { cevChassis 1507 }
cevChassisN9KC9396PX OBJECT IDENTIFIER ::= { cevChassis 1508 }
cevChassisN9KC9396TX OBJECT IDENTIFIER ::= { cevChassis 1509 }
cevChassisN9KC93128TX OBJECT IDENTIFIER ::= { cevChassis 1510 }
cevChassisISR4351 OBJECT IDENTIFIER ::= { cevChassis 1511 }
cevChassisVSGateway OBJECT IDENTIFIER ::= { cevChassis 1519 }
cevChassisPrime OBJECT IDENTIFIER ::= { cevChassis 1520 }
cevChassis897VAB OBJECT IDENTIFIER ::= { cevChassis 1521 }
cevChassisC385012X48U OBJECT IDENTIFIER ::= { cevChassis 1537 }
cevChassisC385024XU OBJECT IDENTIFIER ::= { cevChassis 1538 }
cevChassisN5kC5696Q OBJECT IDENTIFIER ::= { cevChassis 1539 }
cevChassisN2KC2348TQ OBJECT IDENTIFIER ::= { cevChassis 1540 }
cevChassisN2KC2348UPQ OBJECT IDENTIFIER ::= { cevChassis 1541 }
cevChassisC6800IA48FPDR OBJECT IDENTIFIER ::= { cevChassis 1542 }
cevChassisISR4331 OBJECT IDENTIFIER ::= { cevChassis 1544 }
cevChassisNCSFSYSS OBJECT IDENTIFIER ::= { cevChassis 1545 }
cevChassisIE40004TC4GE OBJECT IDENTIFIER ::= { cevChassis 1546 }
cevChassisIE40008T4GE OBJECT IDENTIFIER ::= { cevChassis 1547 }
cevChassisIE40008S4GE OBJECT IDENTIFIER ::= { cevChassis 1548 }
cevChassisIE40004T4P4GE OBJECT IDENTIFIER ::= { cevChassis 1549 }
cevChassisIE400016T4GE OBJECT IDENTIFIER ::= { cevChassis 1550 }
cevChassisIE40004S8P4GE OBJECT IDENTIFIER ::= { cevChassis 1551 }
cevChassisIE40008GT4GE OBJECT IDENTIFIER ::= { cevChassis 1552 }
cevChassisIE40008GS4GE OBJECT IDENTIFIER ::= { cevChassis 1553 }
cevChassisIE40004GC4GP4GE OBJECT IDENTIFIER ::= { cevChassis 1554 }
cevChassisIE400016GT4GE OBJECT IDENTIFIER ::= { cevChassis 1555 }
cevChassisIE40008GT8GP4GE OBJECT IDENTIFIER ::= { cevChassis 1556 }
cevChassisIE40004GS8GP4GE OBJECT IDENTIFIER ::= { cevChassis 1557 }
cevChassisRAIE1783HMS4C4CGN OBJECT IDENTIFIER ::= { cevChassis 1558 }
cevChassisRAIE1783HMS8T4CGN OBJECT IDENTIFIER ::= { cevChassis 1559 }
cevChassisRAIE1783HMS8S4CGN OBJECT IDENTIFIER ::= { cevChassis 1560 }
cevChassisRAIE1783HMS4T4E4CGN OBJECT IDENTIFIER ::= { cevChassis 1561 }
cevChassisRAIE1783HMS16T4CGN OBJECT IDENTIFIER ::= { cevChassis 1562 }
cevChassisRAIE1783HMS4S8E4CGN OBJECT IDENTIFIER ::= { cevChassis 1563 }
cevChassisRAIE1783HMS8TG4CGN OBJECT IDENTIFIER ::= { cevChassis 1564 }
cevChassisRAIE1783HMS8SG4CGN OBJECT IDENTIFIER ::= { cevChassis 1565 }
cevChassisRAIE1783HMS4EG8CGN OBJECT IDENTIFIER ::= { cevChassis 1566 }
cevChassisRAIE1783HMS16TG4CGN OBJECT IDENTIFIER ::= { cevChassis 1567 }
cevChassisRAIE1783HMS8TG8EG4CGN OBJECT IDENTIFIER ::= { cevChassis 1568 }
cevChassisRAIE1783HMS4SG8EG4CGN OBJECT IDENTIFIER ::= { cevChassis 1569 }
cevChassisN2KC2232TQ OBJECT IDENTIFIER ::= { cevChassis 1571 }
cevChassisASR9010ACv2 OBJECT IDENTIFIER ::= { cevChassis 1572 }
cevChassisASR9010DCv2 OBJECT IDENTIFIER ::= { cevChassis 1573 }
cevChassisASR9006ACv2 OBJECT IDENTIFIER ::= { cevChassis 1574 }
cevChassisASR9006DCv2 OBJECT IDENTIFIER ::= { cevChassis 1575 }
cevChassisISR4321 OBJECT IDENTIFIER ::= { cevChassis 1576 }
cevChassisASR901eDC10GS OBJECT IDENTIFIER ::= { cevChassis 1577 }
cevChassisASR901eAC10GS OBJECT IDENTIFIER ::= { cevChassis 1578 }
cevChassisNCS4009SAAC OBJECT IDENTIFIER ::= { cevChassis 1579 }
cevChassisNCS4009SADC OBJECT IDENTIFIER ::= { cevChassis 1580 }
cevChassisCiscoQvPCDI OBJECT IDENTIFIER ::= { cevChassis 1585 }
cevChassisCiscoQvPC OBJECT IDENTIFIER ::= { cevChassis 1586 }
cevChassisWSC3560CX8PTS OBJECT IDENTIFIER ::= { cevChassis 1587 }
cevChassisWSC3560CX8XPDS OBJECT IDENTIFIER ::= { cevChassis 1588 }
cevChassisWSC3560CX12PDS OBJECT IDENTIFIER ::= { cevChassis 1589 }
cevChassisWSC3560CX12TCS OBJECT IDENTIFIER ::= { cevChassis 1590 }
cevChassisWSC3560CX12PCS OBJECT IDENTIFIER ::= { cevChassis 1591 }
cevChassisWSC3560CX8TCS OBJECT IDENTIFIER ::= { cevChassis 1592 }
cevChassisWSC3560CX8PCS OBJECT IDENTIFIER ::= { cevChassis 1593 }
cevChassisWSC2960CX8TCL OBJECT IDENTIFIER ::= { cevChassis 1594 }
cevChassisIOG910GK9 OBJECT IDENTIFIER ::= { cevChassis 1595 }
cevChassisIOG910WK9 OBJECT IDENTIFIER ::= { cevChassis 1596 }
cevChassisIOG910K9 OBJECT IDENTIFIER ::= { cevChassis 1597 }
cevChassisASR1006X OBJECT IDENTIFIER ::= { cevChassis 1598 }
cevChassisASR1009X OBJECT IDENTIFIER ::= { cevChassis 1599 }
cevChassisAsa5506 OBJECT IDENTIFIER ::= { cevChassis 1600 }
cevChassisAsa5506W OBJECT IDENTIFIER ::= { cevChassis 1601 }
cevChassisAsa5508 OBJECT IDENTIFIER ::= { cevChassis 1602 }
cevChassisAsa5506K7 OBJECT IDENTIFIER ::= { cevChassis 1603 }
cevChassisAsa5508K7 OBJECT IDENTIFIER ::= { cevChassis 1604 }
cevChassisC385012XS OBJECT IDENTIFIER ::= { cevChassis 1605 }
cevChassisC385024XS OBJECT IDENTIFIER ::= { cevChassis 1606 }
cevChassisC385048XS OBJECT IDENTIFIER ::= { cevChassis 1607 }
cevChassisAIRAP1702 OBJECT IDENTIFIER ::= { cevChassis 1608 }
cevChassisN3KC3164Q40GE OBJECT IDENTIFIER ::= { cevChassis 1609 }
cevChassisCCE8RU OBJECT IDENTIFIER ::= { cevChassis 1610 }
cevChassisCCE13RU OBJECT IDENTIFIER ::= { cevChassis 1611 }
cevChassisCCE18RU OBJECT IDENTIFIER ::= { cevChassis 1612 }
cevChassis891x24X OBJECT IDENTIFIER ::= { cevChassis 1614 }
cevChassisAsr9KvV2Ac OBJECT IDENTIFIER ::= { cevChassis 1615 }
cevChassisAsr9KvV2DcA OBJECT IDENTIFIER ::= { cevChassis 1616 }
cevChassisAsr9KvV2DcE OBJECT IDENTIFIER ::= { cevChassis 1617 }
cevChassiscBR8  OBJECT IDENTIFIER ::= { cevChassis 1618 }
cevChassisN5KC5624Q OBJECT IDENTIFIER ::= { cevChassis 1619 }
cevChassisN5KC5648Q OBJECT IDENTIFIER ::= { cevChassis 1620 }
cevChassisN5KC5672UP16G OBJECT IDENTIFIER ::= { cevChassis 1621 }
cevChassisAIRAP1572 OBJECT IDENTIFIER ::= { cevChassis 1623 }
cevChassisAIRAP702w OBJECT IDENTIFIER ::= { cevChassis 1624 }
cevChassisN9KC9332PQ OBJECT IDENTIFIER ::= { cevChassis 1625 }
cevChassisN9KC9372PX OBJECT IDENTIFIER ::= { cevChassis 1626 }
cevChassisN9KC9372TX OBJECT IDENTIFIER ::= { cevChassis 1627 }
cevChassisCiscoQvPCVSM OBJECT IDENTIFIER ::= { cevChassis 1630 }
cevChassisRAIE1783ZMS4T4E2TGN OBJECT IDENTIFIER ::= { cevChassis 1632 }
cevChassisRAIE1783ZMS8T8E2TGN OBJECT IDENTIFIER ::= { cevChassis 1633 }
cevChassisRAIE1783HMS8TG4CGR OBJECT IDENTIFIER ::= { cevChassis 1636 }
cevChassisRAIE1783HMS8SG4CGR OBJECT IDENTIFIER ::= { cevChassis 1637 }
cevChassisRAIE1783HMS4EG8CGR OBJECT IDENTIFIER ::= { cevChassis 1638 }
cevChassisRAIE1783HMS16TG4CGR OBJECT IDENTIFIER ::= { cevChassis 1639 }
cevChassisRAIE1783HMS8TG8EG4CGR OBJECT IDENTIFIER ::= { cevChassis 1640 }
cevChassisRAIE1783HMS4SG8EG4CGR OBJECT IDENTIFIER ::= { cevChassis 1641 }
cevChassisCDScde2802s5 OBJECT IDENTIFIER ::= { cevChassis 1642 }
cevChassisCDScde2802s10 OBJECT IDENTIFIER ::= { cevChassis 1643 }
cevChassisCDScde2802s21 OBJECT IDENTIFIER ::= { cevChassis 1644 }
cevChassisCDScde2802h0 OBJECT IDENTIFIER ::= { cevChassis 1645 }
cevChassisCDScde2802h13 OBJECT IDENTIFIER ::= { cevChassis 1646 }
cevChassisCDScde2802h26 OBJECT IDENTIFIER ::= { cevChassis 1647 }
cevChassisN77c7702 OBJECT IDENTIFIER ::= { cevChassis 1648 }
cevChassis841Mx4X OBJECT IDENTIFIER ::= { cevChassis 1650 }
cevChassis841Mx8X OBJECT IDENTIFIER ::= { cevChassis 1651 }
cevChassisN2kC2332TQ10GT OBJECT IDENTIFIER ::= { cevChassis 1652 }
cevChassisSce10000 OBJECT IDENTIFIER ::= { cevChassis 1654 }
cevChassisIE500012S12P10G OBJECT IDENTIFIER ::= { cevChassis 1655 }
cevChassisRAIE1783IMS28NAC OBJECT IDENTIFIER ::= { cevChassis 1656 }
cevChassisRAIE1783IMS28NDC OBJECT IDENTIFIER ::= { cevChassis 1657 }
cevChassisRAIE1783IMS28RAC OBJECT IDENTIFIER ::= { cevChassis 1658 }
cevChassisRAIE1783IMS28RDC OBJECT IDENTIFIER ::= { cevChassis 1659 }
cevChassisDSC9396SK9 OBJECT IDENTIFIER ::= { cevChassis 1660 }
cevChassisAIRAPIW3702 OBJECT IDENTIFIER ::= { cevChassis 1661 }
cevChassisAsa5506H OBJECT IDENTIFIER ::= { cevChassis 1663 }
cevChassisAsa5516 OBJECT IDENTIFIER ::= { cevChassis 1664 }
cevChassis819GWLTE OBJECT IDENTIFIER ::= { cevChassis 1665 }
cevChassisN3kC3548P10GX OBJECT IDENTIFIER ::= { cevChassis 1666 }
cevChassisciscoIR829GWLTEVZAK9 OBJECT IDENTIFIER ::= { cevChassis 1668 }
cevChassisciscoIR829GWLTENAAK9 OBJECT IDENTIFIER ::= { cevChassis 1669 }
cevChassisciscoIR829GWLTEGAEK9 OBJECT IDENTIFIER ::= { cevChassis 1670 }
cevChassisciscoIR829GWLTEGAZK9 OBJECT IDENTIFIER ::= { cevChassis 1671 }
cevChassisciscoIR829GWLTEMAAK9 OBJECT IDENTIFIER ::= { cevChassis 1672 }
cevChassisNCS4016SADC OBJECT IDENTIFIER ::= { cevChassis 1673 }
cevChassisASR1002HX OBJECT IDENTIFIER ::= { cevChassis 1674 }
cevChassisN9KC93120TX OBJECT IDENTIFIER ::= { cevChassis 1675 }
cevChassisASR9910 OBJECT IDENTIFIER ::= { cevChassis 1676 }
cevChassisISA30004C OBJECT IDENTIFIER ::= { cevChassis 1677 }
cevChassisISA30002C2F OBJECT IDENTIFIER ::= { cevChassis 1678 }
cevChassisRAISA1783SAD4T0S OBJECT IDENTIFIER ::= { cevChassis 1679 }
cevChassisRAISA1783SAD2T2S OBJECT IDENTIFIER ::= { cevChassis 1680 }
cevChassisISA4000 OBJECT IDENTIFIER ::= { cevChassis 1681 }
cevChassisNCS5508CHASSIS OBJECT IDENTIFIER ::= { cevChassis 1682 }
cevChassisDSC9718 OBJECT IDENTIFIER ::= { cevChassis 1683 }
cevChassisN2KC2348TQ10GE OBJECT IDENTIFIER ::= { cevChassis 1684 }
cevChassisN9KC9264PQ OBJECT IDENTIFIER ::= { cevChassis 1690 }
cevChassisN3KC31128PQ OBJECT IDENTIFIER ::= { cevChassis 1691 }
cevChassisN3KC3132QXOE OBJECT IDENTIFIER ::= { cevChassis 1692 }
cevChassisN3KC3172PQOE OBJECT IDENTIFIER ::= { cevChassis 1693 }
cevChassisN3KC3172TQOE OBJECT IDENTIFIER ::= { cevChassis 1694 }
cevChassisN3KC3064XOE OBJECT IDENTIFIER ::= { cevChassis 1695 }
cevChassisN3KC3048OE OBJECT IDENTIFIER ::= { cevChassis 1696 }
cevChassisN3KC3232C OBJECT IDENTIFIER ::= { cevChassis 1697 }
cevChassisNamApp2420 OBJECT IDENTIFIER ::= { cevChassis 1698 }
cevChassisNamApp2440 OBJECT IDENTIFIER ::= { cevChassis 1699 }
cevChassisFlowAgent3300 OBJECT IDENTIFIER ::= { cevChassis 1700 }
cevChassisFPRC9300AC OBJECT IDENTIFIER ::= { cevChassis 1701 }
cevChassisFPRC9300DC OBJECT IDENTIFIER ::= { cevChassis 1702 }
cevChassisC899GLTEJPK9 OBJECT IDENTIFIER ::= { cevChassis 1703 }
cevChassisNcs5001 OBJECT IDENTIFIER ::= { cevChassis 1704 }
cevChassisNcs5002 OBJECT IDENTIFIER ::= { cevChassis 1705 }
cevChassisN3KC3132QV OBJECT IDENTIFIER ::= { cevChassis 1706 }
cevChassisFPRC9300 OBJECT IDENTIFIER ::= { cevChassis 1707 }
cevChassisIE500016S12P OBJECT IDENTIFIER ::= { cevChassis 1710 }
cevChassisC819GLTEMNAK9 OBJECT IDENTIFIER ::= { cevChassis 1711 }
cevChassisN9KC9372PXE OBJECT IDENTIFIER ::= { cevChassis 1712 }
cevChassisN9KC9372TXE OBJECT IDENTIFIER ::= { cevChassis 1713 }
cevChassisFPR4110 OBJECT IDENTIFIER ::= { cevChassis 1714 }
cevChassisFPR4120 OBJECT IDENTIFIER ::= { cevChassis 1715 }
cevChassisFPR4140 OBJECT IDENTIFIER ::= { cevChassis 1716 }
cevChassis898EAGLTELAK9 OBJECT IDENTIFIER ::= { cevChassis 1721 }
cevChassis897VAGLTELAK9 OBJECT IDENTIFIER ::= { cevChassis 1722 }
cevChassis819GWLTELACK9 OBJECT IDENTIFIER ::= { cevChassis 1723 }
cevChassis819GWLTELAQK9 OBJECT IDENTIFIER ::= { cevChassis 1724 }
cevChassis819GWLTELANK9 OBJECT IDENTIFIER ::= { cevChassis 1725 }
cevChassisN3KC3132QXL40GX OBJECT IDENTIFIER ::= { cevChassis 1726 }
cevChassisN3KC3172PQXL10GE OBJECT IDENTIFIER ::= { cevChassis 1727 }
cevChassisN3KC3172TQXL10GT OBJECT IDENTIFIER ::= { cevChassis 1728 }
cevChassisNCS4216SA OBJECT IDENTIFIER ::= { cevChassis 1729 }
cevChassisNCS4206SA OBJECT IDENTIFIER ::= { cevChassis 1730 }
cevChassisNCS4202SA OBJECT IDENTIFIER ::= { cevChassis 1731 }
cevChassisASR901CC OBJECT IDENTIFIER ::= { cevChassis 1732 }
cevChassisASR901ECC OBJECT IDENTIFIER ::= { cevChassis 1733 }
cevChassisASR901DC10GCC OBJECT IDENTIFIER ::= { cevChassis 1734 }
cevChassisASR901EDC10GCC OBJECT IDENTIFIER ::= { cevChassis 1735 }
cevChassisASR901DC10GSCC OBJECT IDENTIFIER ::= { cevChassis 1736 }
cevChassisASR92012SZIMCC OBJECT IDENTIFIER ::= { cevChassis 1737 }
cevChassisN3KC3172PQZ810GE OBJECT IDENTIFIER ::= { cevChassis 1738 }
cevChassisIE10004TLM OBJECT IDENTIFIER ::= { cevChassis 1739 }
cevChassisIE10006TLM OBJECT IDENTIFIER ::= { cevChassis 1740 }
cevChassisIE10004PTSLM OBJECT IDENTIFIER ::= { cevChassis 1741 }
cevChassisIE10008PTSLM OBJECT IDENTIFIER ::= { cevChassis 1742 }
cevChassisN3KC3264Q OBJECT IDENTIFIER ::= { cevChassis 1743 }
cevChassisN9KC92160YC OBJECT IDENTIFIER ::= { cevChassis 1744 }
cevChassisN9KC9272Q OBJECT IDENTIFIER ::= { cevChassis 1745 }
cevChassisISR4451B OBJECT IDENTIFIER ::= { cevChassis 1751 }
cevChassisISR4431B OBJECT IDENTIFIER ::= { cevChassis 1752 }
cevChassisISR4351B OBJECT IDENTIFIER ::= { cevChassis 1753 }
cevChassisISR4331B OBJECT IDENTIFIER ::= { cevChassis 1754 }
cevChassisISR4321B OBJECT IDENTIFIER ::= { cevChassis 1755 }
cevChassisNCS5508S OBJECT IDENTIFIER ::= { cevChassis 1756 }
cevChassisNCS5011 OBJECT IDENTIFIER ::= { cevChassis 1757 }
cevChassisN3KC31108PCV OBJECT IDENTIFIER ::= { cevChassis 1758 }
cevChassisN3KC31108TCV OBJECT IDENTIFIER ::= { cevChassis 1759 }
cevChassisRAIE1783IMS28GNAC OBJECT IDENTIFIER ::= { cevChassis 1760 }
cevChassisRAIE1783IMS28GNDC OBJECT IDENTIFIER ::= { cevChassis 1761 }
cevChassisRAIE1783IMS28GRAC OBJECT IDENTIFIER ::= { cevChassis 1762 }
cevChassisRAIE1783IMS28GRDC OBJECT IDENTIFIER ::= { cevChassis 1763 }
cevChassisCisco819GLTELAK9 OBJECT IDENTIFIER ::= { cevChassis 1764 }
cevChassisCisco899GLTELAK9 OBJECT IDENTIFIER ::= { cevChassis 1765 }
cevChassisC897vagwlte OBJECT IDENTIFIER ::= { cevChassis 1766 }
cevChassisC886vagwlte OBJECT IDENTIFIER ::= { cevChassis 1767 }
cevChassisCPUC897vagwlte OBJECT IDENTIFIER ::= { cevChassis 1768 }
cevChassisCPUC886vag OBJECT IDENTIFIER ::= { cevChassis 1769 }
cevChassisASR1001HX OBJECT IDENTIFIER ::= { cevChassis 1776 }
cevChassisN3KC3172PQXL10GE16 OBJECT IDENTIFIER ::= { cevChassis 1777 }
cevChassisN3KC3172PQXLOE OBJECT IDENTIFIER ::= { cevChassis 1778 }
cevChassisN3KC3132Q40GEOE OBJECT IDENTIFIER ::= { cevChassis 1779 }
cevChassisN3KC3232COE OBJECT IDENTIFIER ::= { cevChassis 1780 }
cevChassisN3KC3264QOE OBJECT IDENTIFIER ::= { cevChassis 1781 }
cevChassisN3KC3132QVOE OBJECT IDENTIFIER ::= { cevChassis 1782 }
cevChassisN3KC31108PCVOE OBJECT IDENTIFIER ::= { cevChassis 1783 }
cevChassisN3KC31108TCVOE OBJECT IDENTIFIER ::= { cevChassis 1784 }
cevChassisNCS4201SA OBJECT IDENTIFIER ::= { cevChassis 1785 }
cevChassisNCS1002 OBJECT IDENTIFIER ::= { cevChassis 1786 }
cevChassisCiscoFpr4110td OBJECT IDENTIFIER ::= { cevChassis 1787 }
cevChassisCiscoFpr4120td OBJECT IDENTIFIER ::= { cevChassis 1788 }
cevChassisCiscoFpr4140td OBJECT IDENTIFIER ::= { cevChassis 1789 }
cevChassisCiscoFpr4150td OBJECT IDENTIFIER ::= { cevChassis 1790 }
cevChassisCiscoFpr9000SM24td OBJECT IDENTIFIER ::= { cevChassis 1791 }
cevChassisCiscoFpr9000SM24Ntd OBJECT IDENTIFIER ::= { cevChassis 1792 }
cevChassisCiscoFpr9000SM36td OBJECT IDENTIFIER ::= { cevChassis 1793 }
cevChassisCiscoFpr9000SM44 OBJECT IDENTIFIER ::= { cevChassis 1794 }
cevChassisCiscoFTDVVMW OBJECT IDENTIFIER ::= { cevChassis 1795 }
cevChassisCiscoFTDVAWS OBJECT IDENTIFIER ::= { cevChassis 1796 }
cevChassisCiscoFTDVKVM OBJECT IDENTIFIER ::= { cevChassis 1797 }
cevChassisCiscoFTDVHYPERV OBJECT IDENTIFIER ::= { cevChassis 1798 }
cevChassisCiscoFTDVAZURE OBJECT IDENTIFIER ::= { cevChassis 1799 }
cevChassisWSC2960L24TSLL OBJECT IDENTIFIER ::= { cevChassis 1802 }
cevChassisWSC2960L24PSLL OBJECT IDENTIFIER ::= { cevChassis 1803 }
cevChassisWSC2960L48TSLL OBJECT IDENTIFIER ::= { cevChassis 1804 }
cevChassisWSC2960L48PSLL OBJECT IDENTIFIER ::= { cevChassis 1805 }
cevChassisWSC2960L16TSLL OBJECT IDENTIFIER ::= { cevChassis 1806 }
cevChassisWSC2960L16PSLL OBJECT IDENTIFIER ::= { cevChassis 1807 }
cevChassisWSC2960L8TSLL OBJECT IDENTIFIER ::= { cevChassis 1808 }
cevChassisWSC2960L8PSLL OBJECT IDENTIFIER ::= { cevChassis 1809 }
cevChassisIE40104S24P OBJECT IDENTIFIER ::= { cevChassis 1810 }
cevChassisIE401016S12P OBJECT IDENTIFIER ::= { cevChassis 1811 }
cevChassisN9KC93180YCEX OBJECT IDENTIFIER ::= { cevChassis 1812 }
cevChassis86xVAEV2 OBJECT IDENTIFIER ::= { cevChassis 1818 }
cevChassisStealthWatch2404 OBJECT IDENTIFIER ::= { cevChassis 1821 }
cevChassisStealthWatch2420 OBJECT IDENTIFIER ::= { cevChassis 1822 }
cevChassisNamApp2404 OBJECT IDENTIFIER ::= { cevChassis 1823 }
cevchassisN9KC93108TCEX OBJECT IDENTIFIER ::= { cevChassis 1824 }
cevChassisN1KVhv OBJECT IDENTIFIER ::= { cevChassis 1827 }
cevChassisCSP2100 OBJECT IDENTIFIER ::= { cevChassis 1831 }
cevChassisNCS4216F2BSA OBJECT IDENTIFIER ::= { cevChassis 1836 }
cevChassisFPR2KDC OBJECT IDENTIFIER ::= { cevChassis 1840 }
cevChassisFPR2KAC OBJECT IDENTIFIER ::= { cevChassis 1841 }
cevChassisFpr2140td OBJECT IDENTIFIER ::= { cevChassis 1846 }
cevChassisFpr2130td OBJECT IDENTIFIER ::= { cevChassis 1847 }
cevChassisFpr2120td OBJECT IDENTIFIER ::= { cevChassis 1848 }
cevChassisFpr2110td OBJECT IDENTIFIER ::= { cevChassis 1849 }
cevChassisN9KC93180YCFX OBJECT IDENTIFIER ::= { cevChassis 1850 }
cevChassisN9KC93108TCFX OBJECT IDENTIFIER ::= { cevChassis 1893 }
cevChassisDSC9132U OBJECT IDENTIFIER ::= { cevChassis 1894 }
cevChassisDSC9232U OBJECT IDENTIFIER ::= { cevChassis 1895 }
cevBackplane    OBJECT IDENTIFIER ::= { cevMIBObjects 4 }
cevBackplaneAtm OBJECT IDENTIFIER ::= { cevBackplane 4 }
cevBackplaneCat5500 OBJECT IDENTIFIER ::= { cevBackplane 5 }
cevBackplaneCat6400 OBJECT IDENTIFIER ::= { cevBackplane 6 }
cevBackplaneCat8510 OBJECT IDENTIFIER ::= { cevBackplane 7 }
cevBackplaneCat8540 OBJECT IDENTIFIER ::= { cevBackplane 8 }
cevBackplaneMGX8850 OBJECT IDENTIFIER ::= { cevBackplane 9 }
cevBackplaneMGX8820 OBJECT IDENTIFIER ::= { cevBackplane 10 }
cevBackplaneBPXSes OBJECT IDENTIFIER ::= { cevBackplane 11 }
cevBackplaneIGXSes OBJECT IDENTIFIER ::= { cevBackplane 12 }
cevBackplaneCat6000 OBJECT IDENTIFIER ::= { cevBackplane 13 }
cevBackplaneCat6500 OBJECT IDENTIFIER ::= { cevBackplane 14 }
cevBackplaneMGX8950 OBJECT IDENTIFIER ::= { cevBackplane 15 }
cevBackplaneONS15540Fixed OBJECT IDENTIFIER ::= { cevBackplane 16 }
cevBackplaneCat4006 OBJECT IDENTIFIER ::= { cevBackplane 18 }
cevBackplaneMGX8830 OBJECT IDENTIFIER ::= { cevBackplane 19 }
cevBackplaneONS15530 OBJECT IDENTIFIER ::= { cevBackplane 20 }
cevBackplaneCat4507 OBJECT IDENTIFIER ::= { cevBackplane 23 }
cevBackplaneCat4503 OBJECT IDENTIFIER ::= { cevBackplane 24 }
cevBackplaneCat4506 OBJECT IDENTIFIER ::= { cevBackplane 25 }
cevBackplaneDSC9506 OBJECT IDENTIFIER ::= { cevBackplane 26 }
cevBackplaneDSC9509 OBJECT IDENTIFIER ::= { cevBackplane 27 }
cevBackplaneDSC9513 OBJECT IDENTIFIER ::= { cevBackplane 28 }
cevBackplaneONS15540ESPx OBJECT IDENTIFIER ::= { cevBackplane 29 }
cevBackplaneUnknown OBJECT IDENTIFIER ::= { cevBackplane 30 }
cevBackplaneCat4510 OBJECT IDENTIFIER ::= { cevBackplane 31 }
cevBackplaneDSC9140K9 OBJECT IDENTIFIER ::= { cevBackplane 32 }
cevBackplaneBMGX8850 OBJECT IDENTIFIER ::= { cevBackplane 33 }
cevBackplaneBMGX8950 OBJECT IDENTIFIER ::= { cevBackplane 34 }
cevBackplaneCisco7600 OBJECT IDENTIFIER ::= { cevBackplane 35 }
cevBackplaneBMGX8830 OBJECT IDENTIFIER ::= { cevBackplane 36 }
cevBackplaneDSC9216AK9 OBJECT IDENTIFIER ::= { cevBackplane 37 }
cevBackplaneMGX8880 OBJECT IDENTIFIER ::= { cevBackplane 38 }
cevBackplane6SlotsRCON8850 OBJECT IDENTIFIER ::= { cevBackplane 39 }
cevBackplane4SlotsRCON8850 OBJECT IDENTIFIER ::= { cevBackplane 40 }
cevBackplane4SlotsRCON8830 OBJECT IDENTIFIER ::= { cevBackplane 41 }
cevBackplaneDSX9116K9 OBJECT IDENTIFIER ::= { cevBackplane 42 }
cevBackplaneONS15310 OBJECT IDENTIFIER ::= { cevBackplane 43 }
cevBackplaneCat4503e OBJECT IDENTIFIER ::= { cevBackplane 48 }
cevBackplaneCat4506e OBJECT IDENTIFIER ::= { cevBackplane 49 }
cevBackplaneCat4507re OBJECT IDENTIFIER ::= { cevBackplane 50 }
cevBackplaneCat4510re OBJECT IDENTIFIER ::= { cevBackplane 51 }
cevBackplaneN7Kc7010 OBJECT IDENTIFIER ::= { cevBackplane 52 }
cevBackplaneCatRfgw OBJECT IDENTIFIER ::= { cevBackplane 53 }
cevBackplaneN7Kc7018 OBJECT IDENTIFIER ::= { cevBackplane 55 }
cevBackplaneMXE5600 OBJECT IDENTIFIER ::= { cevBackplane 56 }
cevBackplaneN7Kc7009 OBJECT IDENTIFIER ::= { cevBackplane 57 }
cevBackplaneN7Kc7004 OBJECT IDENTIFIER ::= { cevBackplane 61 }
cevBackplaneDSC9710 OBJECT IDENTIFIER ::= { cevBackplane 63 }
cevBackplaneN77c7718 OBJECT IDENTIFIER ::= { cevBackplane 64 }
cevBackplaneN77c7710 OBJECT IDENTIFIER ::= { cevBackplane 65 }
cevBackplaneN77c7706 OBJECT IDENTIFIER ::= { cevBackplane 66 }
cevBackplaneCat6800 OBJECT IDENTIFIER ::= { cevBackplane 67 }
cevBackplaneDSC9706 OBJECT IDENTIFIER ::= { cevBackplane 68 }
cevBackplaneNCS4K OBJECT IDENTIFIER ::= { cevBackplane 69 }
cevBackplaneN77c7702 OBJECT IDENTIFIER ::= { cevBackplane 70 }
cevBackplaneDSC9718 OBJECT IDENTIFIER ::= { cevBackplane 71 }
cevBackplaneNCS1002 OBJECT IDENTIFIER ::= { cevBackplane 76 }
cevContainer    OBJECT IDENTIFIER ::= { cevMIBObjects 5 }
cevContainerSlot OBJECT IDENTIFIER ::= { cevContainer 1 }
cevContainerDaughterCard OBJECT IDENTIFIER ::= { cevContainer 2 }
cevContainerPCMCIA OBJECT IDENTIFIER ::= { cevContainer 12 }
cevContainerDSPModuleSlot OBJECT IDENTIFIER ::= { cevContainer 16 }
cevContainerCat8500Carrier OBJECT IDENTIFIER ::= { cevContainer 17 }
cevContainerCat8500CpuSwitchAndFeature OBJECT IDENTIFIER ::= { cevContainer 18 }
cevContainerCat8500CpuSwitchAndFeaturePFQ OBJECT IDENTIFIER ::= { cevContainer 19 }
cevContainerCat8500SuperCarrier OBJECT IDENTIFIER ::= { cevContainer 20 }
cevContainerCat8500CpuRoute OBJECT IDENTIFIER ::= { cevContainer 21 }
cevContainerCat8500Switch10GAndFC OBJECT IDENTIFIER ::= { cevContainer 22 }
cevContainerCat8500Switch10GNoFC OBJECT IDENTIFIER ::= { cevContainer 23 }
cevContainerDslamSlot OBJECT IDENTIFIER ::= { cevContainer 24 }
cevContainerC6260PsSlot OBJECT IDENTIFIER ::= { cevContainer 25 }
cevContainerC6260FanSlot OBJECT IDENTIFIER ::= { cevContainer 26 }
cevContainerDslamControllerSlot OBJECT IDENTIFIER ::= { cevContainer 27 }
cevContainerDslamNi2DcSlot OBJECT IDENTIFIER ::= { cevContainer 28 }
cevContainerPsmSlot OBJECT IDENTIFIER ::= { cevContainer 31 }
cevContainerSmSlot OBJECT IDENTIFIER ::= { cevContainer 32 }
cevContainerMGX8800FanTray OBJECT IDENTIFIER ::= { cevContainer 33 }
cevContainerSrmSlot OBJECT IDENTIFIER ::= { cevContainer 34 }
cevContainerMGX8800ACPSTray OBJECT IDENTIFIER ::= { cevContainer 35 }
cevContainerSESFanTray OBJECT IDENTIFIER ::= { cevContainer 36 }
cevContainer12012TopBlowerBay OBJECT IDENTIFIER ::= { cevContainer 37 }
cevContainer12012BottomBlowerBay OBJECT IDENTIFIER ::= { cevContainer 38 }
cevContainer12012ModuleBay OBJECT IDENTIFIER ::= { cevContainer 39 }
cevContainer12012SwitchFabricBay OBJECT IDENTIFIER ::= { cevContainer 40 }
cevContainer12012PowerSupplyBay OBJECT IDENTIFIER ::= { cevContainer 41 }
cevContainer12008PowerBlowerBay OBJECT IDENTIFIER ::= { cevContainer 42 }
cevContainer12008MainBlowerBay OBJECT IDENTIFIER ::= { cevContainer 43 }
cevContainer12008ModuleBay OBJECT IDENTIFIER ::= { cevContainer 44 }
cevContainer12008SwitchFabricBay OBJECT IDENTIFIER ::= { cevContainer 45 }
cevContainer12008PowerSupplyBay OBJECT IDENTIFIER ::= { cevContainer 46 }
cevContainerC6160PsSlot OBJECT IDENTIFIER ::= { cevContainer 48 }
cevContainerC6160FanSlot OBJECT IDENTIFIER ::= { cevContainer 49 }
cevContainerMGXXm60Slot OBJECT IDENTIFIER ::= { cevContainer 52 }
cevContainerCat8500CMPMCarrier OBJECT IDENTIFIER ::= { cevContainer 55 }
cevContainer12010TopBlowerBay OBJECT IDENTIFIER ::= { cevContainer 56 }
cevContainer12010BottomBlowerBay OBJECT IDENTIFIER ::= { cevContainer 57 }
cevContainer12010UpperModuleBay OBJECT IDENTIFIER ::= { cevContainer 58 }
cevContainer12010LowerModuleBay OBJECT IDENTIFIER ::= { cevContainer 59 }
cevContainer12010SwitchFabricBay OBJECT IDENTIFIER ::= { cevContainer 60 }
cevContainer12010PowerSupplyBay OBJECT IDENTIFIER ::= { cevContainer 61 }
cevContainer12010PowerBlowerBay OBJECT IDENTIFIER ::= { cevContainer 62 }
cevContainer12010MainBlowerBay OBJECT IDENTIFIER ::= { cevContainer 63 }
cevContainer12406ModuleBay OBJECT IDENTIFIER ::= { cevContainer 64 }
cevContainer12406FabricAlarmBay OBJECT IDENTIFIER ::= { cevContainer 65 }
cevContainer12406PowerSupplyBay OBJECT IDENTIFIER ::= { cevContainer 66 }
cevContainer12406MainBlowerBay OBJECT IDENTIFIER ::= { cevContainer 67 }
cevContainer12410TopBlowerBay OBJECT IDENTIFIER ::= { cevContainer 68 }
cevContainer12410BottomBlowerBay OBJECT IDENTIFIER ::= { cevContainer 69 }
cevContainer12410UpperModuleBay OBJECT IDENTIFIER ::= { cevContainer 70 }
cevContainer12410LowerModuleBay OBJECT IDENTIFIER ::= { cevContainer 71 }
cevContainer12410SwitchFabricBay OBJECT IDENTIFIER ::= { cevContainer 72 }
cevContainer12410PowerSupplyBay OBJECT IDENTIFIER ::= { cevContainer 73 }
cevContainer12410PowerBlowerBay OBJECT IDENTIFIER ::= { cevContainer 74 }
cevContainer12410MainBlowerBay OBJECT IDENTIFIER ::= { cevContainer 75 }
cevContainerONS15540CardSlot OBJECT IDENTIFIER ::= { cevContainer 76 }
cevContainerONS15540FanTraySlot OBJECT IDENTIFIER ::= { cevContainer 77 }
cevContainerONS15540TspSubslot OBJECT IDENTIFIER ::= { cevContainer 78 }
cevContainerONS15540MDXSubslot OBJECT IDENTIFIER ::= { cevContainer 79 }
cevContainerONS15540SubCardSlot OBJECT IDENTIFIER ::= { cevContainer 80 }
cevContainer12404ModuleBay OBJECT IDENTIFIER ::= { cevContainer 81 }
cevContainer12404FabricAlarmBay OBJECT IDENTIFIER ::= { cevContainer 82 }
cevContainer12404PowerSupplyBay OBJECT IDENTIFIER ::= { cevContainer 83 }
cevContainer12404MainBlowerBay OBJECT IDENTIFIER ::= { cevContainer 84 }
cevContainerC7304PowerSupplyBay OBJECT IDENTIFIER ::= { cevContainer 85 }
cevContainerC10KSlot OBJECT IDENTIFIER ::= { cevContainer 86 }
cevContainerC10KPowerSupplySlot OBJECT IDENTIFIER ::= { cevContainer 87 }
cevContainerC10KFanTraySlot OBJECT IDENTIFIER ::= { cevContainer 88 }
cevContainerC10KFlashCardSlot OBJECT IDENTIFIER ::= { cevContainer 89 }
cevContainerCat4kFanTrayBay OBJECT IDENTIFIER ::= { cevContainer 90 }
cevContainerCat4kPowerSupplyBay OBJECT IDENTIFIER ::= { cevContainer 91 }
cevContainerCat4kPEMBay OBJECT IDENTIFIER ::= { cevContainer 92 }
cevContainer12016PowerBlowerBay OBJECT IDENTIFIER ::= { cevContainer 93 }
cevContainer12016LowerModuleBay OBJECT IDENTIFIER ::= { cevContainer 94 }
cevContainer12016SwitchFabricBay OBJECT IDENTIFIER ::= { cevContainer 95 }
cevContainer12016PowerSupplyBay OBJECT IDENTIFIER ::= { cevContainer 96 }
cevContainer12016TopBlowerBay OBJECT IDENTIFIER ::= { cevContainer 97 }
cevContainer12016BottomBlowerBay OBJECT IDENTIFIER ::= { cevContainer 98 }
cevContainer12016UpperModuleBay OBJECT IDENTIFIER ::= { cevContainer 99 }
cevContainerONS15530CardSlot OBJECT IDENTIFIER ::= { cevContainer 100 }
cevContainerONS15530FanTraySlot OBJECT IDENTIFIER ::= { cevContainer 102 }
cevContainerONS15530PSSlot OBJECT IDENTIFIER ::= { cevContainer 103 }
cevContainerONS15530SubCardSlot OBJECT IDENTIFIER ::= { cevContainer 104 }
cevContainerONS15530PortSlot OBJECT IDENTIFIER ::= { cevContainer 105 }
cevContainerONS15540PortSlot OBJECT IDENTIFIER ::= { cevContainer 106 }
cevContainerCat4kContainerPSBay OBJECT IDENTIFIER ::= { cevContainer 111 }
cevContainerSPABay OBJECT IDENTIFIER ::= { cevContainer 114 }
cevContainerSFP OBJECT IDENTIFIER ::= { cevContainer 115 }
cevContainerGsrAlarmSlot OBJECT IDENTIFIER ::= { cevContainer 116 }
cevContainerGsrPowerSupplySlot OBJECT IDENTIFIER ::= { cevContainer 117 }
cevContainerGsrFanBlowerSlot OBJECT IDENTIFIER ::= { cevContainer 118 }
cevContainerGsrSwitchFabricSlot OBJECT IDENTIFIER ::= { cevContainer 119 }
cevContainerONS15252CardSlot OBJECT IDENTIFIER ::= { cevContainer 120 }
cevContainerONS15201CardSlot OBJECT IDENTIFIER ::= { cevContainer 121 }
cevContainerSupFabricSlot OBJECT IDENTIFIER ::= { cevContainer 122 }
cevContainerLineCardSlot OBJECT IDENTIFIER ::= { cevContainer 123 }
cevContainer9506PowerSupplyBay OBJECT IDENTIFIER ::= { cevContainer 124 }
cevContainer9509PowerSupplyBay OBJECT IDENTIFIER ::= { cevContainer 125 }
cevContainer9513PowerSupplyBay OBJECT IDENTIFIER ::= { cevContainer 126 }
cevContainer9506FanBay OBJECT IDENTIFIER ::= { cevContainer 127 }
cevContainer9509FanBay OBJECT IDENTIFIER ::= { cevContainer 128 }
cevContainer9513FanBay OBJECT IDENTIFIER ::= { cevContainer 129 }
cevContainer9216FanBay OBJECT IDENTIFIER ::= { cevContainer 130 }
cevContainer9216PowerSupplyBay OBJECT IDENTIFIER ::= { cevContainer 131 }
cevContainerC7300CCPA OBJECT IDENTIFIER ::= { cevContainer 132 }
cevContainerPABay OBJECT IDENTIFIER ::= { cevContainer 133 }
cevChassisCr4430 OBJECT IDENTIFIER ::= { cevContainer 134 }
cevMgx2uPlenumFanTray OBJECT IDENTIFIER ::= { cevContainer 135 }
cevContainerMDSPowerSupplyBay OBJECT IDENTIFIER ::= { cevContainer 136 }
cevContainerMDSFanTrayBay OBJECT IDENTIFIER ::= { cevContainer 137 }
cevContainerFlashCardSlot OBJECT IDENTIFIER ::= { cevContainer 138 }
cevContainerFanTraySlot OBJECT IDENTIFIER ::= { cevContainer 139 }
cevContainerPowerSupplyBay OBJECT IDENTIFIER ::= { cevContainer 140 }
cevContainerPowerSupply OBJECT IDENTIFIER ::= { cevContainer 141 }
cevContainerGbic OBJECT IDENTIFIER ::= { cevContainer 142 }
cevContainerCrs1RPSlot OBJECT IDENTIFIER ::= { cevContainer 143 }
cevContainerCrs1LCDRPSlot OBJECT IDENTIFIER ::= { cevContainer 144 }
cevContainerCrs1FabricSlot OBJECT IDENTIFIER ::= { cevContainer 145 }
cevContainerCrs1AlarmSlot OBJECT IDENTIFIER ::= { cevContainer 146 }
cevContainerCrs1PowerSupplySlot OBJECT IDENTIFIER ::= { cevContainer 147 }
cevContainerCrs1FanSlot OBJECT IDENTIFIER ::= { cevContainer 148 }
cevContainerPowerSupplySlot OBJECT IDENTIFIER ::= { cevContainer 149 }
cevContainerVtt OBJECT IDENTIFIER ::= { cevContainer 150 }
cevContainerClock OBJECT IDENTIFIER ::= { cevContainer 151 }
cevContainer10GigBasePort OBJECT IDENTIFIER ::= { cevContainer 152 }
cevContainerUmg9820ProcessorCard OBJECT IDENTIFIER ::= { cevContainer 153 }
cevContainerUmg9820PowerSupplyBay OBJECT IDENTIFIER ::= { cevContainer 154 }
cevContainerUmg9820QamModuleSlot OBJECT IDENTIFIER ::= { cevContainer 155 }
cevContainerUmg9820FanTraySlot OBJECT IDENTIFIER ::= { cevContainer 156 }
cevContainer9116FanBay OBJECT IDENTIFIER ::= { cevContainer 157 }
cevContainer9116PowerSupplyBay OBJECT IDENTIFIER ::= { cevContainer 158 }
cevContainerONS15310CardSlot OBJECT IDENTIFIER ::= { cevContainer 159 }
cevContainerGSR6Blwr OBJECT IDENTIFIER ::= { cevContainer 160 }
cevContainerGSR10GSR16Blwr OBJECT IDENTIFIER ::= { cevContainer 161 }
cevContainer9513RearFanBay OBJECT IDENTIFIER ::= { cevContainer 162 }
cevContainerFabricSlot OBJECT IDENTIFIER ::= { cevContainer 163 }
cevContainerCrs18RPSlot OBJECT IDENTIFIER ::= { cevContainer 164 }
cevContainerCrs18FabricSlot OBJECT IDENTIFIER ::= { cevContainer 165 }
cevContainerCrs1FabricShelfControllerSlot OBJECT IDENTIFIER ::= { cevContainer 166 }
cevContainerCrs1FabricSwitchFabricSlot OBJECT IDENTIFIER ::= { cevContainer 167 }
cevContainerCrs1FabricFiberModuleSlot OBJECT IDENTIFIER ::= { cevContainer 168 }
cevContainerCrs1FabricLEDModuleSlot OBJECT IDENTIFIER ::= { cevContainer 169 }
cevPowerSupplyCrs1PowerSupplyShelf OBJECT IDENTIFIER ::= { cevContainer 170 }
cevContainerTransceiver OBJECT IDENTIFIER ::= { cevContainer 171 }
cevContainer9124PowerSupplyBay OBJECT IDENTIFIER ::= { cevContainer 173 }
cevContainer9124FanBay OBJECT IDENTIFIER ::= { cevContainer 174 }
cevContainerC3KPowerSupply OBJECT IDENTIFIER ::= { cevContainer 175 }
cevContainerC3KRemotePowerSupply OBJECT IDENTIFIER ::= { cevContainer 176 }
cevContainerC3KBlower OBJECT IDENTIFIER ::= { cevContainer 177 }
cevContainer9222iFanBay OBJECT IDENTIFIER ::= { cevContainer 178 }
cevContainerN7Kc7010PowerSupplyBay OBJECT IDENTIFIER ::= { cevContainer 179 }
cevContainerN7KC7010MainFanBay OBJECT IDENTIFIER ::= { cevContainer 180 }
cevContainerN7KC7010FabricFanBay OBJECT IDENTIFIER ::= { cevContainer 181 }
cevContainerASR1000RPSlot OBJECT IDENTIFIER ::= { cevContainer 182 }
cevContainerASR1000FPSlot OBJECT IDENTIFIER ::= { cevContainer 183 }
cevContainerASR1000CCSlot OBJECT IDENTIFIER ::= { cevContainer 184 }
cevContainerASR1000PowerSupplyBay OBJECT IDENTIFIER ::= { cevContainer 185 }
cevContainerN5kC5020FanBay OBJECT IDENTIFIER ::= { cevContainer 186 }
cevContainerN5kC5020PowerSupplyBay OBJECT IDENTIFIER ::= { cevContainer 187 }
cevContainerASR9KFanTraySlot OBJECT IDENTIFIER ::= { cevContainer 188 }
cevContainerASR9KPowerSupplySlotDC OBJECT IDENTIFIER ::= { cevContainer 189 }
cevContainerASR9KPowerSupplySlotAC OBJECT IDENTIFIER ::= { cevContainer 190 }
cevContainerASR9KRSPSlot OBJECT IDENTIFIER ::= { cevContainer 191 }
cevContainerASR9KLCSlot OBJECT IDENTIFIER ::= { cevContainer 192 }
cevContainerN7Kc7018PowerSupplyBay OBJECT IDENTIFIER ::= { cevContainer 193 }
cevContainerN7KC7018FanBay OBJECT IDENTIFIER ::= { cevContainer 194 }
cevContainerCrs1PowerShelfSlot OBJECT IDENTIFIER ::= { cevContainer 195 }
cevContainerN5kC5010FanBay OBJECT IDENTIFIER ::= { cevContainer 196 }
cevContainerN5kC5010PowerSupplyBay OBJECT IDENTIFIER ::= { cevContainer 197 }
cevContainerXFP OBJECT IDENTIFIER ::= { cevContainer 198 }
cevContainerAsr14kPowerSupplySlot OBJECT IDENTIFIER ::= { cevContainer 199 }
cevContainerAsr14kPowerShelfSlot OBJECT IDENTIFIER ::= { cevContainer 200 }
cevContainerAsr14kFanTraySlot OBJECT IDENTIFIER ::= { cevContainer 201 }
cevContainerAsr14kFabricCardSlot OBJECT IDENTIFIER ::= { cevContainer 202 }
cevContainerAsr14kFPSlot OBJECT IDENTIFIER ::= { cevContainer 203 }
cevContainerAsr14kRPSlot OBJECT IDENTIFIER ::= { cevContainer 204 }
cevContainerHardDiskSlot OBJECT IDENTIFIER ::= { cevContainer 205 }
cevContainerNexusLogicalFabric OBJECT IDENTIFIER ::= { cevContainer 206 }
cevContainerN2kC2148T1GEPowerSupplyBay OBJECT IDENTIFIER ::= { cevContainer 207 }
cevContainerN2kC2148T1GEFanBay OBJECT IDENTIFIER ::= { cevContainer 208 }
cevContainerUCSN10S6100FanBay OBJECT IDENTIFIER ::= { cevContainer 209 }
cevContainerUCSN10S6100PowerSupplyBay OBJECT IDENTIFIER ::= { cevContainer 210 }
cevContainerMXE5600PowerSupplyBay OBJECT IDENTIFIER ::= { cevContainer 213 }
cevContainerMXE5600FanTray OBJECT IDENTIFIER ::= { cevContainer 214 }
cevContainerN2kC2248TP1GEPowerSupplyBay OBJECT IDENTIFIER ::= { cevContainer 218 }
cevContainerN7Kc7009PowerSupplyBay OBJECT IDENTIFIER ::= { cevContainer 219 }
cevContainerN7KC7009FanBay OBJECT IDENTIFIER ::= { cevContainer 220 }
cevContainerFruLinkModuleSlot OBJECT IDENTIFIER ::= { cevContainer 221 }
cevContainerFlexStackModuleSlot OBJECT IDENTIFIER ::= { cevContainer 222 }
cevContainerMXE5600ShelfManagerBay OBJECT IDENTIFIER ::= { cevContainer 223 }
cevContainerMXE5600NpmSlot OBJECT IDENTIFIER ::= { cevContainer 224 }
cevContainerMXE5600MpmSlot OBJECT IDENTIFIER ::= { cevContainer 225 }
cevContainerN5KC5548FanBay OBJECT IDENTIFIER ::= { cevContainer 226 }
cevContainerN5kC5548PowerSupplyBay OBJECT IDENTIFIER ::= { cevContainer 227 }
cevContainerCrs18PowerShelfVirtual OBJECT IDENTIFIER ::= { cevContainer 228 }
cevContainer40GigBasePort OBJECT IDENTIFIER ::= { cevContainer 229 }
cevContainerSAMBay OBJECT IDENTIFIER ::= { cevContainer 230 }
cevContainerN5KC5596FanBay OBJECT IDENTIFIER ::= { cevContainer 231 }
cevContainerN5kC5596PowerSupplyBay OBJECT IDENTIFIER ::= { cevContainer 232 }
cevContainerN3KC3064FanBay OBJECT IDENTIFIER ::= { cevContainer 235 }
cevContainerUCS6248FanBay OBJECT IDENTIFIER ::= { cevContainer 236 }
cevContainerUCS6248PowerSupplyBay OBJECT IDENTIFIER ::= { cevContainer 237 }
cevContainerUCS6296FanBay OBJECT IDENTIFIER ::= { cevContainer 238 }
cevContainerUCS6296PowerSupplyBay OBJECT IDENTIFIER ::= { cevContainer 239 }
cevContainerDIMM8541Slot OBJECT IDENTIFIER ::= { cevContainer 240 }
cevContainerDIMM7571Slot OBJECT IDENTIFIER ::= { cevContainer 241 }
cevContainerDIMM7541Slot OBJECT IDENTIFIER ::= { cevContainer 242 }
cevContainerDIMM694Slot OBJECT IDENTIFIER ::= { cevContainer 243 }
cevContainerDIMM594Slot OBJECT IDENTIFIER ::= { cevContainer 244 }
cevContainerDIMM294Slot OBJECT IDENTIFIER ::= { cevContainer 245 }
cevContainerASR900RSPSlot OBJECT IDENTIFIER ::= { cevContainer 246 }
cevContainerASR900PowerSupplyBay OBJECT IDENTIFIER ::= { cevContainer 247 }
cevContainerASR900FanTrayBay OBJECT IDENTIFIER ::= { cevContainer 248 }
cevContainerIMBay OBJECT IDENTIFIER ::= { cevContainer 249 }
cevContainerN7Kc7004FanBay OBJECT IDENTIFIER ::= { cevContainer 250 }
cevContainerN7Kc7004PowerSupplyBay OBJECT IDENTIFIER ::= { cevContainer 251 }
cevContainerN3KC3048FanBay OBJECT IDENTIFIER ::= { cevContainer 252 }
cevContainerESGPSBay OBJECT IDENTIFIER ::= { cevContainer 253 }
cevContainerESGPOEConvBay OBJECT IDENTIFIER ::= { cevContainer 254 }
cevContainerESGFanTrayBay OBJECT IDENTIFIER ::= { cevContainer 255 }
cevContainerESG2000RPSlot OBJECT IDENTIFIER ::= { cevContainer 256 }
cevContainerESG2000FPSlot OBJECT IDENTIFIER ::= { cevContainer 257 }
cevContainerESGNGSMSlot OBJECT IDENTIFIER ::= { cevContainer 258 }
cevContainerNGWICBay OBJECT IDENTIFIER ::= { cevContainer 259 }
cevContainerN6kC6004FanBay OBJECT IDENTIFIER ::= { cevContainer 262 }
cevContainerN6kC6004PowerSupplyBay OBJECT IDENTIFIER ::= { cevContainer 263 }
cevContainerASR9KSwitchFabricSlot OBJECT IDENTIFIER ::= { cevContainer 264 }
cevContainerCFP OBJECT IDENTIFIER ::= { cevContainer 265 }
cevContainerISR4400ESMSlot OBJECT IDENTIFIER ::= { cevContainer 268 }
cevContainerISR4400PSBay OBJECT IDENTIFIER ::= { cevContainer 269 }
cevContainerISR4400FanTrayBay OBJECT IDENTIFIER ::= { cevContainer 270 }
cevContainerISR4400POEBay OBJECT IDENTIFIER ::= { cevContainer 271 }
cevContainerISR4400InternalPOEBay OBJECT IDENTIFIER ::= { cevContainer 272 }
cevContainerDSC9710FanBay OBJECT IDENTIFIER ::= { cevContainer 273 }
cevContainerMDS9250iFanBay OBJECT IDENTIFIER ::= { cevContainer 274 }
cevContainerNCSProcessorSlot OBJECT IDENTIFIER ::= { cevContainer 275 }
cevContainerNCSLineCardSlot OBJECT IDENTIFIER ::= { cevContainer 276 }
cevContainerNCSFabcardSlot OBJECT IDENTIFIER ::= { cevContainer 277 }
cevContainerNCSPwrTraySlot OBJECT IDENTIFIER ::= { cevContainer 278 }
cevContainerNCSFanTraySlot OBJECT IDENTIFIER ::= { cevContainer 279 }
cevContainerNCSPwrSupSlot OBJECT IDENTIFIER ::= { cevContainer 280 }
cevContainerNCSDisplaySlot OBJECT IDENTIFIER ::= { cevContainer 281 }
cevContainerN77c7718PowerSupplyBay OBJECT IDENTIFIER ::= { cevContainer 282 }
cevContainerN77c7710PowerSupplyBay OBJECT IDENTIFIER ::= { cevContainer 283 }
cevContainerN77c7706PowerSupplyBay OBJECT IDENTIFIER ::= { cevContainer 284 }
cevContainerN77c7718FanBay OBJECT IDENTIFIER ::= { cevContainer 285 }
cevContainerN77c7710FanBay OBJECT IDENTIFIER ::= { cevContainer 286 }
cevContainerN77c7706FanBay OBJECT IDENTIFIER ::= { cevContainer 287 }
cevContainerCXP OBJECT IDENTIFIER ::= { cevContainer 288 }
cevContainerCPAK OBJECT IDENTIFIER ::= { cevContainer 289 }
cevContainerPsConverter OBJECT IDENTIFIER ::= { cevContainer 290 }
cevContainerQIron22Qzinc2 OBJECT IDENTIFIER ::= { cevContainer 292 }
cevContainerDSC9706 OBJECT IDENTIFIER ::= { cevContainer 293 }
cevContainerNCS4KRPS OBJECT IDENTIFIER ::= { cevContainer 294 }
cevContainerNCS4KLCS OBJECT IDENTIFIER ::= { cevContainer 295 }
cevContainerNCS4KFCS OBJECT IDENTIFIER ::= { cevContainer 296 }
cevContainerNCS4KPFS OBJECT IDENTIFIER ::= { cevContainer 297 }
cevContainerNCS4KFTS OBJECT IDENTIFIER ::= { cevContainer 298 }
cevContainerNCS4KCIS OBJECT IDENTIFIER ::= { cevContainer 299 }
cevContainerNCS4KECUS OBJECT IDENTIFIER ::= { cevContainer 300 }
cevContainerN9Kc9508FanBay OBJECT IDENTIFIER ::= { cevContainer 301 }
cevContainerN9Kc9508PowerSupplyBay OBJECT IDENTIFIER ::= { cevContainer 302 }
cevContainerASR5000SPCSlot OBJECT IDENTIFIER ::= { cevContainer 303 }
cevContainerASR5000PTACSlot OBJECT IDENTIFIER ::= { cevContainer 304 }
cevContainerASR5000RCCSlot OBJECT IDENTIFIER ::= { cevContainer 305 }
cevContainerASR5000SPIOSlot OBJECT IDENTIFIER ::= { cevContainer 306 }
cevContainerASR5000LCSlot OBJECT IDENTIFIER ::= { cevContainer 307 }
cevContainerASR5000FanTraySlot OBJECT IDENTIFIER ::= { cevContainer 308 }
cevContainerASR5000PowerSupplySlot OBJECT IDENTIFIER ::= { cevContainer 309 }
cevContainerASR5500MMIOSlot OBJECT IDENTIFIER ::= { cevContainer 310 }
cevContainerASR5500DPCSlot OBJECT IDENTIFIER ::= { cevContainer 311 }
cevContainerASR5500FSCSlot OBJECT IDENTIFIER ::= { cevContainer 312 }
cevContainerASR5500SSCSlot OBJECT IDENTIFIER ::= { cevContainer 313 }
cevContainerASR5500SIOSlot OBJECT IDENTIFIER ::= { cevContainer 314 }
cevContainerASR5500FanTraySlot OBJECT IDENTIFIER ::= { cevContainer 315 }
cevContainerASR5500PowerSupplySlot OBJECT IDENTIFIER ::= { cevContainer 316 }
cevContainerDSC48SFAN OBJECT IDENTIFIER ::= { cevContainer 317 }
cevContainerN9Kc9516FanBay OBJECT IDENTIFIER ::= { cevContainer 318 }
cevContainerN9Kc9504FanBay OBJECT IDENTIFIER ::= { cevContainer 319 }
cevContainerN9KC9300FanBay2 OBJECT IDENTIFIER ::= { cevContainer 320 }
cevContainerN9KC9300FanBay1 OBJECT IDENTIFIER ::= { cevContainer 321 }
cevContainerISRSSDSlot OBJECT IDENTIFIER ::= { cevContainer 322 }
cevContainerNIMSlot OBJECT IDENTIFIER ::= { cevContainer 323 }
cevContainerISRPVDMSlot OBJECT IDENTIFIER ::= { cevContainer 324 }
cevContainerN5KC56128FanBay OBJECT IDENTIFIER ::= { cevContainer 327 }
cevContainerNXAPowerSupplyBay OBJECT IDENTIFIER ::= { cevContainer 328 }
cevContainerN6kC6001FanBay OBJECT IDENTIFIER ::= { cevContainer 329 }
cevContainerNCS4KSFP OBJECT IDENTIFIER ::= { cevContainer 330 }
cevContainerNCS4KPwrSupSlot OBJECT IDENTIFIER ::= { cevContainer 331 }
cevContainerNCS6KSwitchCard OBJECT IDENTIFIER ::= { cevContainer 332 }
cevContainerUSB OBJECT IDENTIFIER ::= { cevContainer 333 }
cevContainerCCEPowerSupplyBay OBJECT IDENTIFIER ::= { cevContainer 334 }
cevContainerCCEFanTraySlot OBJECT IDENTIFIER ::= { cevContainer 335 }
cevContainerN77c7702PowerSupplyBay OBJECT IDENTIFIER ::= { cevContainer 336 }
cevContainerN77c7702FanBay OBJECT IDENTIFIER ::= { cevContainer 337 }
cevContainerASR1000XFanTrayBay OBJECT IDENTIFIER ::= { cevContainer 338 }
cevContainerDSCAC1200W OBJECT IDENTIFIER ::= { cevContainer 339 }
cevContainerDSC96SFAN OBJECT IDENTIFIER ::= { cevContainer 340 }
cevContainerDSCAC973KW OBJECT IDENTIFIER ::= { cevContainer 344 }
cevContainerDSC9718FAN OBJECT IDENTIFIER ::= { cevContainer 345 }
cevContainerN9kc9264PQFanBay OBJECT IDENTIFIER ::= { cevContainer 346 }
cevContainerNC55SysControllerSlot OBJECT IDENTIFIER ::= { cevContainer 347 }
cevContainerNC55FabricCardSlot OBJECT IDENTIFIER ::= { cevContainer 348 }
cevContainerNC55LineCardSlot OBJECT IDENTIFIER ::= { cevContainer 349 }
cevContainerNC55RouteProcessorSlot OBJECT IDENTIFIER ::= { cevContainer 350 }
cevContainerNC55BlankPwrSup OBJECT IDENTIFIER ::= { cevContainer 351 }
cevContainerNC55DCPwrSup OBJECT IDENTIFIER ::= { cevContainer 352 }
cevContainerNC55ACPwrSup OBJECT IDENTIFIER ::= { cevContainer 353 }
cevContainerNC55UnivPwrSup OBJECT IDENTIFIER ::= { cevContainer 354 }
cevContainerNC55FanTray OBJECT IDENTIFIER ::= { cevContainer 355 }
cevContainerQSFP28SR OBJECT IDENTIFIER ::= { cevContainer 356 }
cevContainerQSFP28CR OBJECT IDENTIFIER ::= { cevContainer 357 }
cevContainerQSFP28LR OBJECT IDENTIFIER ::= { cevContainer 358 }
cevContainerFPRLogicalFabric OBJECT IDENTIFIER ::= { cevContainer 359 }
cevContainerFPRC9300PowerSupplyBay OBJECT IDENTIFIER ::= { cevContainer 361 }
cevContainerFPRC9300FanBay OBJECT IDENTIFIER ::= { cevContainer 362 }
cevContainerFPR4KFanBay OBJECT IDENTIFIER ::= { cevContainer 363 }
cevContainerFPR4KPowerSupplyBay OBJECT IDENTIFIER ::= { cevContainer 364 }
cevContainerQSFP28AOC OBJECT IDENTIFIER ::= { cevContainer 365 }
cevContainerCbr8PowerShelfSlot OBJECT IDENTIFIER ::= { cevContainer 366 }
cevContainerQSFP28CWDM OBJECT IDENTIFIER ::= { cevContainer 367 }
cevContainerNonCiscoQSFP28SR OBJECT IDENTIFIER ::= { cevContainer 368 }
cevContainerNonCiscoQSFP28LR OBJECT IDENTIFIER ::= { cevContainer 369 }
cevContainerNonCiscoQSFP28CR OBJECT IDENTIFIER ::= { cevContainer 370 }
cevContainerNonCiscoQSFP28AOC OBJECT IDENTIFIER ::= { cevContainer 371 }
cevContainerNonCiscoQSFP28CWDM OBJECT IDENTIFIER ::= { cevContainer 372 }
cevContainerNCS420XRSP OBJECT IDENTIFIER ::= { cevContainer 373 }
cevContainerNCS4216RSP OBJECT IDENTIFIER ::= { cevContainer 374 }
cevContainerNCS1002LineCardVirtual OBJECT IDENTIFIER ::= { cevContainer 377 }
cevContainerNCS1002RP OBJECT IDENTIFIER ::= { cevContainer 378 }
cevContainerPowerModuleSlot OBJECT IDENTIFIER ::= { cevContainer 379 }
cevContainerFPR2KFanBay OBJECT IDENTIFIER ::= { cevContainer 384 }
cevContainerFPR2KPowerSupplyBay OBJECT IDENTIFIER ::= { cevContainer 385 }
cevContainerQSFP OBJECT IDENTIFIER ::= { cevContainer 390 }
cevPowerSupply  OBJECT IDENTIFIER ::= { cevMIBObjects 6 }
cevPowerSupplyAC1360W OBJECT IDENTIFIER ::= { cevPowerSupply 1 }
cevPowerSupplyDC1360W OBJECT IDENTIFIER ::= { cevPowerSupply 2 }
cevPowerSupplyAC1000W OBJECT IDENTIFIER ::= { cevPowerSupply 3 }
cevPowerSupplyDC1000W OBJECT IDENTIFIER ::= { cevPowerSupply 4 }
cevPowerSupplyPowerone OBJECT IDENTIFIER ::= { cevPowerSupply 5 }
cevPowerSupplyAstec OBJECT IDENTIFIER ::= { cevPowerSupply 6 }
cevPowerSupplyMinus48VDC OBJECT IDENTIFIER ::= { cevPowerSupply 7 }
cevPowerSupplyEmpty OBJECT IDENTIFIER ::= { cevPowerSupply 8 }
cevPowerSupplyAC1100W OBJECT IDENTIFIER ::= { cevPowerSupply 9 }
cevPowerSupplyAC1200W OBJECT IDENTIFIER ::= { cevPowerSupply 10 }
cevPowerSupplyDC1200W OBJECT IDENTIFIER ::= { cevPowerSupply 11 }
cevPowerSupplyPem OBJECT IDENTIFIER ::= { cevPowerSupply 12 }
cevPowerSupplyAC2000W OBJECT IDENTIFIER ::= { cevPowerSupply 13 }
cevPowerSupplyDC2000W OBJECT IDENTIFIER ::= { cevPowerSupply 14 }
cevPowerSupply6260DC OBJECT IDENTIFIER ::= { cevPowerSupply 15 }
cevPowerSupply6260AC OBJECT IDENTIFIER ::= { cevPowerSupply 16 }
cevPowerSupplyMGX8800Pem OBJECT IDENTIFIER ::= { cevPowerSupply 17 }
cevPowerSupply12012DC OBJECT IDENTIFIER ::= { cevPowerSupply 18 }
cevPowerSupply12012AC OBJECT IDENTIFIER ::= { cevPowerSupply 19 }
cevPowerSupply12008DC OBJECT IDENTIFIER ::= { cevPowerSupply 20 }
cevPowerSupply12008AC OBJECT IDENTIFIER ::= { cevPowerSupply 21 }
cevPowerSupplyDC2500W OBJECT IDENTIFIER ::= { cevPowerSupply 22 }
cevPowerSupplyAC1050W OBJECT IDENTIFIER ::= { cevPowerSupply 23 }
cevPowerSupplyAC2500W OBJECT IDENTIFIER ::= { cevPowerSupply 24 }
cevPowerSupply6160DC OBJECT IDENTIFIER ::= { cevPowerSupply 25 }
cevPowerSupplyAC4000W OBJECT IDENTIFIER ::= { cevPowerSupply 28 }
cevPowerSupplyDC4000W OBJECT IDENTIFIER ::= { cevPowerSupply 29 }
cevPowerSupply12010DC OBJECT IDENTIFIER ::= { cevPowerSupply 31 }
cevPowerSupply12010AC OBJECT IDENTIFIER ::= { cevPowerSupply 32 }
cevPowerSupply5850DC OBJECT IDENTIFIER ::= { cevPowerSupply 33 }
cevPowerSupply12406DC OBJECT IDENTIFIER ::= { cevPowerSupply 34 }
cevPowerSupply12406AC OBJECT IDENTIFIER ::= { cevPowerSupply 35 }
cevPowerSupply12410DC OBJECT IDENTIFIER ::= { cevPowerSupply 36 }
cevPowerSupply12410AC OBJECT IDENTIFIER ::= { cevPowerSupply 37 }
cevPowerSupplyAC1900W OBJECT IDENTIFIER ::= { cevPowerSupply 38 }
cevPowerSupplyDC1900W OBJECT IDENTIFIER ::= { cevPowerSupply 39 }
cevPowerSupplyDC950W OBJECT IDENTIFIER ::= { cevPowerSupply 40 }
cevPowerSupplyAC950W OBJECT IDENTIFIER ::= { cevPowerSupply 41 }
cevPowerSupply12404DC OBJECT IDENTIFIER ::= { cevPowerSupply 42 }
cevPowerSupply12404AC OBJECT IDENTIFIER ::= { cevPowerSupply 43 }
cevPowerSupplyBP7513AC1200W OBJECT IDENTIFIER ::= { cevPowerSupply 44 }
cevPowerSupplyBP7513DC1200W OBJECT IDENTIFIER ::= { cevPowerSupply 45 }
cevPowerSupplyBP7505AC600W OBJECT IDENTIFIER ::= { cevPowerSupply 46 }
cevPowerSupplyBP7505DC600W OBJECT IDENTIFIER ::= { cevPowerSupply 47 }
cevPowerSupplyBP7507AC700W OBJECT IDENTIFIER ::= { cevPowerSupply 48 }
cevPowerSupplyBP7507DC700W OBJECT IDENTIFIER ::= { cevPowerSupply 49 }
cevPowerSupplyAC1900W6 OBJECT IDENTIFIER ::= { cevPowerSupply 50 }
cevPowerSupplyC7300AC OBJECT IDENTIFIER ::= { cevPowerSupply 51 }
cevPowerSupplyC7300DC OBJECT IDENTIFIER ::= { cevPowerSupply 52 }
cevPowerSupplyAC600W OBJECT IDENTIFIER ::= { cevPowerSupply 53 }
cevPowerSupplyDC600W OBJECT IDENTIFIER ::= { cevPowerSupply 54 }
cevPowerSupplyC10KDC OBJECT IDENTIFIER ::= { cevPowerSupply 55 }
cevPowerSupplyC10KAC OBJECT IDENTIFIER ::= { cevPowerSupply 56 }
cevPowerSupply15530AC OBJECT IDENTIFIER ::= { cevPowerSupply 59 }
cevPowerSupply15530DC OBJECT IDENTIFIER ::= { cevPowerSupply 60 }
cevPowerSupplyAC3000W OBJECT IDENTIFIER ::= { cevPowerSupply 61 }
cevPowerSupply12016DC OBJECT IDENTIFIER ::= { cevPowerSupply 63 }
cevPowerSupply12016AC OBJECT IDENTIFIER ::= { cevPowerSupply 64 }
cevPowerSupplyDC3000W OBJECT IDENTIFIER ::= { cevPowerSupply 70 }
cevPowerSupplyCat3750AC50W12V OBJECT IDENTIFIER ::= { cevPowerSupply 71 }
cevPowerSupplyCat3750AC102W12V OBJECT IDENTIFIER ::= { cevPowerSupply 72 }
cevPowerSupplyCat3750AC204W12V OBJECT IDENTIFIER ::= { cevPowerSupply 73 }
cevPowerSupplyCat3750AC252W12V OBJECT IDENTIFIER ::= { cevPowerSupply 74 }
cevPowerSupplyDsCac2500W OBJECT IDENTIFIER ::= { cevPowerSupply 76 }
cevPowerSupplyRedDsCac2500W OBJECT IDENTIFIER ::= { cevPowerSupply 77 }
cevPowerSupplyDsCdc2500W OBJECT IDENTIFIER ::= { cevPowerSupply 78 }
cevPowerSupplyRedDsCdc2500W OBJECT IDENTIFIER ::= { cevPowerSupply 79 }
cevPowerSupplyDsCac4000WUs OBJECT IDENTIFIER ::= { cevPowerSupply 80 }
cevPowerSupplyRedDsCac4000WUs OBJECT IDENTIFIER ::= { cevPowerSupply 81 }
cevPowerSupplyDsCac4000WInt OBJECT IDENTIFIER ::= { cevPowerSupply 82 }
cevPowerSupplyRedDsCac4000WInt OBJECT IDENTIFIER ::= { cevPowerSupply 83 }
cevPowerSupplyDsCac1900W OBJECT IDENTIFIER ::= { cevPowerSupply 84 }
cevPowerSupplyRedDsCac1900W OBJECT IDENTIFIER ::= { cevPowerSupply 85 }
cevPowerSupplyDsCdc1900W OBJECT IDENTIFIER ::= { cevPowerSupply 86 }
cevPowerSupplyRedDsCdc1900W OBJECT IDENTIFIER ::= { cevPowerSupply 87 }
cevPowerSupplyRedDsCac845W OBJECT IDENTIFIER ::= { cevPowerSupply 88 }
cevPowerSupplyDsCac845W OBJECT IDENTIFIER ::= { cevPowerSupply 89 }
cevPowerSupplyUnknown OBJECT IDENTIFIER ::= { cevPowerSupply 90 }
cevPowerSupplyC2970AC156W12V OBJECT IDENTIFIER ::= { cevPowerSupply 91 }
cevPowerSupplyAc150W OBJECT IDENTIFIER ::= { cevPowerSupply 92 }
cevPowerSupplyC7200AC OBJECT IDENTIFIER ::= { cevPowerSupply 93 }
cevPowerSupplyC7200DC OBJECT IDENTIFIER ::= { cevPowerSupply 94 }
cevPowerSupplyAc465W OBJECT IDENTIFIER ::= { cevPowerSupply 95 }
cevPowerSupplyDsCac300W OBJECT IDENTIFIER ::= { cevPowerSupply 96 }
cevPowerSupplyRedDsCac300W OBJECT IDENTIFIER ::= { cevPowerSupply 97 }
cevPowerSupplyAc1400W OBJECT IDENTIFIER ::= { cevPowerSupply 98 }
cevPowerSupplyC2970AC204W12V OBJECT IDENTIFIER ::= { cevPowerSupply 99 }
cevPowerSupplyCrs1PowerSupply OBJECT IDENTIFIER ::= { cevPowerSupply 100 }
cevPowerSupplyCrs1PowerZone OBJECT IDENTIFIER ::= { cevPowerSupply 101 }
cevPowerSupplyAC6000W OBJECT IDENTIFIER ::= { cevPowerSupply 102 }
cevPowerSupplyDc150W OBJECT IDENTIFIER ::= { cevPowerSupply 103 }
cevPowerSupplyAC2700W OBJECT IDENTIFIER ::= { cevPowerSupply 104 }
cevPowerSupplyDC2700W OBJECT IDENTIFIER ::= { cevPowerSupply 105 }
cevPowerSupplyPwrC45300AC OBJECT IDENTIFIER ::= { cevPowerSupply 106 }
cevPowerSupplyPwrC45300DC OBJECT IDENTIFIER ::= { cevPowerSupply 107 }
cevPowerSupplyAC2900WE OBJECT IDENTIFIER ::= { cevPowerSupply 108 }
cevPowerSupplyAC6000WE OBJECT IDENTIFIER ::= { cevPowerSupply 109 }
cevPowerSupplyAC8700WE OBJECT IDENTIFIER ::= { cevPowerSupply 110 }
cevPowerSupplyPWR2700AC4 OBJECT IDENTIFIER ::= { cevPowerSupply 111 }
cevPowerSupplyPWR2700DC4 OBJECT IDENTIFIER ::= { cevPowerSupply 112 }
cevPowerSupplyPWRC49AC300W OBJECT IDENTIFIER ::= { cevPowerSupply 113 }
cevPowerSupplyPWRC49DC300W OBJECT IDENTIFIER ::= { cevPowerSupply 114 }
cevPowerSupplyGSR6PemAC OBJECT IDENTIFIER ::= { cevPowerSupply 115 }
cevPowerSupplyGSR6PemDC OBJECT IDENTIFIER ::= { cevPowerSupply 116 }
cevPowerSupplyGSR10PemAC OBJECT IDENTIFIER ::= { cevPowerSupply 117 }
cevPowerSupplyGSR10PemDC OBJECT IDENTIFIER ::= { cevPowerSupply 118 }
cevPowerSupplyGSR4PemAC OBJECT IDENTIFIER ::= { cevPowerSupply 119 }
cevPowerSupplyGSR4PemDC OBJECT IDENTIFIER ::= { cevPowerSupply 120 }
cevPowerSupplyGSR16PemAC OBJECT IDENTIFIER ::= { cevPowerSupply 121 }
cevPowerSupplyGSR16PemDC OBJECT IDENTIFIER ::= { cevPowerSupply 122 }
cevPowerSupplyC451400DCSP OBJECT IDENTIFIER ::= { cevPowerSupply 123 }
cevPowerSupplyAc125W OBJECT IDENTIFIER ::= { cevPowerSupply 124 }
cevPowerSupplyAc60W OBJECT IDENTIFIER ::= { cevPowerSupply 125 }
cevPowerSupplyC454200ACv OBJECT IDENTIFIER ::= { cevPowerSupply 126 }
cevPowerSupply400wDC OBJECT IDENTIFIER ::= { cevPowerSupply 127 }
cevPowerSupplyEnh12404AC OBJECT IDENTIFIER ::= { cevPowerSupply 128 }
cevPowerSupplyEnh12404DC OBJECT IDENTIFIER ::= { cevPowerSupply 129 }
cevPowerSupplyEnh12406AC OBJECT IDENTIFIER ::= { cevPowerSupply 130 }
cevPowerSupplyEnh12406DC OBJECT IDENTIFIER ::= { cevPowerSupply 131 }
cevPowerSupplyEnh12410AC OBJECT IDENTIFIER ::= { cevPowerSupply 132 }
cevPowerSupplyEnh12410DC OBJECT IDENTIFIER ::= { cevPowerSupply 133 }
cevPowerSupplyEnh12416AC OBJECT IDENTIFIER ::= { cevPowerSupply 134 }
cevPowerSupplyEnh12416DC OBJECT IDENTIFIER ::= { cevPowerSupply 135 }
cevPowerSupply76xxDC2500W OBJECT IDENTIFIER ::= { cevPowerSupply 136 }
cevPowerSupply76xxAC3000W OBJECT IDENTIFIER ::= { cevPowerSupply 137 }
cevPowerSupply76xxAC4000US OBJECT IDENTIFIER ::= { cevPowerSupply 138 }
cevPowerSupply76xxAC4000INT OBJECT IDENTIFIER ::= { cevPowerSupply 139 }
cevPowerSupply76xxAC6000W OBJECT IDENTIFIER ::= { cevPowerSupply 140 }
cevPowerSupplyDC100W OBJECT IDENTIFIER ::= { cevPowerSupply 141 }
cevPowerSupplyDsCAD6000W OBJECT IDENTIFIER ::= { cevPowerSupply 144 }
cevPowerSupplyCat2960AC60W12V OBJECT IDENTIFIER ::= { cevPowerSupply 145 }
cevPowerSupplyCat2960AC125W12V OBJECT IDENTIFIER ::= { cevPowerSupply 146 }
cevPowerSupplyCat2960AC210W12V OBJECT IDENTIFIER ::= { cevPowerSupply 147 }
cevPowerSupply6340PWRDC OBJECT IDENTIFIER ::= { cevPowerSupply 148 }
cevPowerSupply6340PWRAC OBJECT IDENTIFIER ::= { cevPowerSupply 149 }
cevPowerSupplyUbr10012AC OBJECT IDENTIFIER ::= { cevPowerSupply 150 }
cevPowerSupplyUbr10012DC OBJECT IDENTIFIER ::= { cevPowerSupply 151 }
cevPowerSupply400wAC OBJECT IDENTIFIER ::= { cevPowerSupply 152 }
cevPowerSupplyCE500AC60W12V OBJECT IDENTIFIER ::= { cevPowerSupply 153 }
cevPowerSupplyCE500AC375W48V OBJECT IDENTIFIER ::= { cevPowerSupply 154 }
cevPowerSupplyCE500AC75W48V OBJECT IDENTIFIER ::= { cevPowerSupply 155 }
cevPowerSupplyCE500AC168W12V OBJECT IDENTIFIER ::= { cevPowerSupply 156 }
cevPowerSupplyCat3750AC210W12V OBJECT IDENTIFIER ::= { cevPowerSupply 157 }
cevPowerSupplyCat3750AC375W48V OBJECT IDENTIFIER ::= { cevPowerSupply 158 }
cevPowerSupplyAC50W OBJECT IDENTIFIER ::= { cevPowerSupply 159 }
cevPowerSupplyDC50W OBJECT IDENTIFIER ::= { cevPowerSupply 160 }
cevPowerSupplyCrs116PowerShelfACDelta OBJECT IDENTIFIER ::= { cevPowerSupply 161 }
cevPowerSupplyCrs116PowerShelfACWye OBJECT IDENTIFIER ::= { cevPowerSupply 162 }
cevPowerSupplyCrs116PowerShelfDC OBJECT IDENTIFIER ::= { cevPowerSupply 163 }
cevPowerSupplyCrs116ACRectifier OBJECT IDENTIFIER ::= { cevPowerSupply 164 }
cevPowerSupplyCrs116DCPEM OBJECT IDENTIFIER ::= { cevPowerSupply 165 }
cevPowerSupplyDsCac3000W OBJECT IDENTIFIER ::= { cevPowerSupply 167 }
cevPowerSupplyPWR6000DC OBJECT IDENTIFIER ::= { cevPowerSupply 168 }
cevPowerSupplyCrs18ACRectifier OBJECT IDENTIFIER ::= { cevPowerSupply 169 }
cevPowerSupplyCrs18DCPem OBJECT IDENTIFIER ::= { cevPowerSupply 170 }
cevPowerSupplyCrs18ACDelta OBJECT IDENTIFIER ::= { cevPowerSupply 171 }
cevPowerSupplyCrs18ACW OBJECT IDENTIFIER ::= { cevPowerSupply 172 }
cevPowerSupplyCrs18DC OBJECT IDENTIFIER ::= { cevPowerSupply 173 }
cevPowerSupplyCrs18PduACD OBJECT IDENTIFIER ::= { cevPowerSupply 174 }
cevPowerSupplyCrs18PduACW OBJECT IDENTIFIER ::= { cevPowerSupply 175 }
cevPowerSupplyCrs18PduDC OBJECT IDENTIFIER ::= { cevPowerSupply 176 }
cevPowerSupplyCrs1FcACD OBJECT IDENTIFIER ::= { cevPowerSupply 177 }
cevPowerSupplyCrs1FcACW OBJECT IDENTIFIER ::= { cevPowerSupply 178 }
cevPowerSupplyCrs1FcDC OBJECT IDENTIFIER ::= { cevPowerSupply 179 }
cevPowerSupplyCrs14PowerShelfAC OBJECT IDENTIFIER ::= { cevPowerSupply 180 }
cevPowerSupplyCrs14PowerShelfDC OBJECT IDENTIFIER ::= { cevPowerSupply 181 }
cevPowerSupplyCrs14PowerSupplyDC OBJECT IDENTIFIER ::= { cevPowerSupply 182 }
cevPowerSupplyCrs14PowerSupplyAC OBJECT IDENTIFIER ::= { cevPowerSupply 183 }
cevPowerSupplyC3KPWR265WAC OBJECT IDENTIFIER ::= { cevPowerSupply 184 }
cevPowerSupplyC3KPWR265WDC OBJECT IDENTIFIER ::= { cevPowerSupply 185 }
cevPowerSupplyC3KPWR750WAC OBJECT IDENTIFIER ::= { cevPowerSupply 186 }
cevPowerSupplyCat2960AC36W12V OBJECT IDENTIFIER ::= { cevPowerSupply 188 }
cevPowerSupplyCat3560AC173W48V OBJECT IDENTIFIER ::= { cevPowerSupply 189 }
cevPowerSupplyAC345 OBJECT IDENTIFIER ::= { cevPowerSupply 190 }
cevPowerSupplyC3KPWR1150WAC OBJECT IDENTIFIER ::= { cevPowerSupply 191 }
cevPowerSupplyPwrRPS2300 OBJECT IDENTIFIER ::= { cevPowerSupply 192 }
cevPowerSupplyCrs14DcPim OBJECT IDENTIFIER ::= { cevPowerSupply 193 }
cevPowerSupplyDC1500W OBJECT IDENTIFIER ::= { cevPowerSupply 194 }
cevPowerSupplyC7201AC OBJECT IDENTIFIER ::= { cevPowerSupply 195 }
cevPowerSupplyC7201DC OBJECT IDENTIFIER ::= { cevPowerSupply 196 }
cevPowerSupplyCE520AC173W48V OBJECT IDENTIFIER ::= { cevPowerSupply 197 }
cevPowerSupplyAC100W OBJECT IDENTIFIER ::= { cevPowerSupply 198 }
cevPowerSupplyN7KAC5600W OBJECT IDENTIFIER ::= { cevPowerSupply 199 }
cevPowerSupplyASR1002AC OBJECT IDENTIFIER ::= { cevPowerSupply 200 }
cevPowerSupplyASR1002DC OBJECT IDENTIFIER ::= { cevPowerSupply 201 }
cevPowerSupplyASR1004AC OBJECT IDENTIFIER ::= { cevPowerSupply 202 }
cevPowerSupplyASR1004DC OBJECT IDENTIFIER ::= { cevPowerSupply 203 }
cevPowerSupplyASR1006AC OBJECT IDENTIFIER ::= { cevPowerSupply 204 }
cevPowerSupplyASR1006DC OBJECT IDENTIFIER ::= { cevPowerSupply 205 }
cevPowerSupplyASR1000Unknown OBJECT IDENTIFIER ::= { cevPowerSupply 206 }
cevPowerSupplyC49M1000AC OBJECT IDENTIFIER ::= { cevPowerSupply 207 }
cevPowerSupplyC49M1000DC OBJECT IDENTIFIER ::= { cevPowerSupply 208 }
cevPowerSupplyN7KAC7500W OBJECT IDENTIFIER ::= { cevPowerSupply 209 }
cevPowerSupplyCE520LCAC135W12V OBJECT IDENTIFIER ::= { cevPowerSupply 210 }
cevPowerSupplyCE520PCAC558W12V OBJECT IDENTIFIER ::= { cevPowerSupply 211 }
cevPowerSupplyCE520TTAC60W12V OBJECT IDENTIFIER ::= { cevPowerSupply 212 }
cevPowerSupplyCE520GTCAC125W12V OBJECT IDENTIFIER ::= { cevPowerSupply 213 }
cevPowerSupplyN7KAC6000W OBJECT IDENTIFIER ::= { cevPowerSupply 214 }
cevPowerSupplyDc4500W OBJECT IDENTIFIER ::= { cevPowerSupply 215 }
cevPowerSupplyIE3000AC OBJECT IDENTIFIER ::= { cevPowerSupply 216 }
cevPowerSupplyN5kPac1200W OBJECT IDENTIFIER ::= { cevPowerSupply 217 }
cevPowerSupplyCat2918AC60W12V OBJECT IDENTIFIER ::= { cevPowerSupply 218 }
cevPowerSupplyC3KPWR300WAC OBJECT IDENTIFIER ::= { cevPowerSupply 220 }
cevPowerSupplyC3KPWR300WDC OBJECT IDENTIFIER ::= { cevPowerSupply 221 }
cevPowerSupplyDCPowerSupply OBJECT IDENTIFIER ::= { cevPowerSupply 222 }
cevPowerSupplyACPowerSupply OBJECT IDENTIFIER ::= { cevPowerSupply 223 }
cevPowerSupplyN7KAC7500WINT OBJECT IDENTIFIER ::= { cevPowerSupply 228 }
cevPowerSupplyN7KAC7500WUS OBJECT IDENTIFIER ::= { cevPowerSupply 229 }
cevPowerSupplyN5kPac550W OBJECT IDENTIFIER ::= { cevPowerSupply 230 }
cevPowerSupplyASR9KDC2100W OBJECT IDENTIFIER ::= { cevPowerSupply 231 }
cevPowerSupplyASR9KDC1500W OBJECT IDENTIFIER ::= { cevPowerSupply 232 }
cevPowerSupplyASR9KAC3KW OBJECT IDENTIFIER ::= { cevPowerSupply 233 }
cevPowerSupplyCrs16dcPemB OBJECT IDENTIFIER ::= { cevPowerSupply 234 }
cevPowerSupplyC3900PWRPOE OBJECT IDENTIFIER ::= { cevPowerSupply 235 }
cevPowerSupplyC3900PWRAC OBJECT IDENTIFIER ::= { cevPowerSupply 236 }
cevPowerSupplyC2921C2951PWRPOE OBJECT IDENTIFIER ::= { cevPowerSupply 237 }
cevPowerSupplyC2921C2951PWRAC OBJECT IDENTIFIER ::= { cevPowerSupply 238 }
cevPowerSupplyC2911PWRPOE OBJECT IDENTIFIER ::= { cevPowerSupply 239 }
cevPowerSupplyC2911PWRAC OBJECT IDENTIFIER ::= { cevPowerSupply 240 }
cevPowerSupplyC2901PWRPOE OBJECT IDENTIFIER ::= { cevPowerSupply 241 }
cevPowerSupplyC1941C2901PWRAC OBJECT IDENTIFIER ::= { cevPowerSupply 242 }
cevPowerSupplyC1941PWRPOE OBJECT IDENTIFIER ::= { cevPowerSupply 243 }
cevPowerSupplyC3900PWRDC OBJECT IDENTIFIER ::= { cevPowerSupply 244 }
cevPowerSupplyC2921C2951PWRDC OBJECT IDENTIFIER ::= { cevPowerSupply 245 }
cevPowerSupplyC2911PWRDC OBJECT IDENTIFIER ::= { cevPowerSupply 246 }
cevPowerSupplyC2921C2951RPSADPTR OBJECT IDENTIFIER ::= { cevPowerSupply 247 }
cevPowerSupplyC2911RPSADPTR OBJECT IDENTIFIER ::= { cevPowerSupply 248 }
cevPowerSupplyN2kPac200W OBJECT IDENTIFIER ::= { cevPowerSupply 249 }
cevPowerSupplyC456000ACV OBJECT IDENTIFIER ::= { cevPowerSupply 250 }
cevPowerUCSN10PAC1550W OBJECT IDENTIFIER ::= { cevPowerSupply 251 }
cevPowerSupplyN7KDC6000W OBJECT IDENTIFIER ::= { cevPowerSupply 253 }
cevPowerSupplyCrs18PowerShelfDCModular OBJECT IDENTIFIER ::= { cevPowerSupply 254 }
cevPowerSupplyCrs18PowerShelfACModular OBJECT IDENTIFIER ::= { cevPowerSupply 255 }
cevPowerSupplyCrs116FCCPowerShelfDCModular OBJECT IDENTIFIER ::= { cevPowerSupply 256 }
cevPowerSupplyCrs116FCCPowerShelfACModular OBJECT IDENTIFIER ::= { cevPowerSupply 257 }
cevPowerSupplyCrs1DCPowerModule OBJECT IDENTIFIER ::= { cevPowerSupply 258 }
cevPowerSupplyCrs1ACPowerModule OBJECT IDENTIFIER ::= { cevPowerSupply 259 }
cevPowerSupplyCrs116LCCPowerShelfDCModular OBJECT IDENTIFIER ::= { cevPowerSupply 260 }
cevPowerSupplyCrs116LCCPowerShelfACModular OBJECT IDENTIFIER ::= { cevPowerSupply 261 }
cevPowerSupplyCat2960AC123W12V OBJECT IDENTIFIER ::= { cevPowerSupply 262 }
cevPowerSupplyCat2960AC370W12V OBJECT IDENTIFIER ::= { cevPowerSupply 263 }
cevPowerSupplyCat2960AC235W12V OBJECT IDENTIFIER ::= { cevPowerSupply 264 }
cevPowerSupplyCat2960AC525W12V OBJECT IDENTIFIER ::= { cevPowerSupply 265 }
cevPowerSupplyASR1001AC OBJECT IDENTIFIER ::= { cevPowerSupply 267 }
cevPowerSupplyASR1001DC OBJECT IDENTIFIER ::= { cevPowerSupply 268 }
cevPowerSupplyASR1013AC OBJECT IDENTIFIER ::= { cevPowerSupply 269 }
cevPowerSupplyASR1013DC OBJECT IDENTIFIER ::= { cevPowerSupply 270 }
cevPowerSupplyC1941PWRAC OBJECT IDENTIFIER ::= { cevPowerSupply 271 }
cevPowerSupplyASR1002DC24V OBJECT IDENTIFIER ::= { cevPowerSupply 272 }
cevPowerSupplyN2kC2200Pac400W OBJECT IDENTIFIER ::= { cevPowerSupply 273 }
cevPowerSupplyC3kxPwr350wAc OBJECT IDENTIFIER ::= { cevPowerSupply 278 }
cevPowerSupplyC3kxPwr715wAc OBJECT IDENTIFIER ::= { cevPowerSupply 279 }
cevPowerSupplyC3kxPwr1100wAc OBJECT IDENTIFIER ::= { cevPowerSupply 280 }
cevPowerSupplyPWRME3KXAC OBJECT IDENTIFIER ::= { cevPowerSupply 282 }
cevPowerSupplyPWRME3KXDC OBJECT IDENTIFIER ::= { cevPowerSupply 283 }
cevPowerSupplyCGR20xxCGS25xxPWRACPOE OBJECT IDENTIFIER ::= { cevPowerSupply 284 }
cevPowerSupplyCGR20xxCGS25xxPWRDCPOE OBJECT IDENTIFIER ::= { cevPowerSupply 285 }
cevPowerSupplyMXE5600 OBJECT IDENTIFIER ::= { cevPowerSupply 286 }
cevPowerSupplyC7225AC OBJECT IDENTIFIER ::= { cevPowerSupply 287 }
cevPowerSupplyPWRC49EAC300WR OBJECT IDENTIFIER ::= { cevPowerSupply 288 }
cevPowerSupplyC2360Pwr135wac OBJECT IDENTIFIER ::= { cevPowerSupply 290 }
cevPowerSupplyN55Pac750W OBJECT IDENTIFIER ::= { cevPowerSupply 291 }
cevPowerSupplyCrs16PshDcB OBJECT IDENTIFIER ::= { cevPowerSupply 293 }
cevPowerSupplyCrs16PshAcB OBJECT IDENTIFIER ::= { cevPowerSupply 294 }
cevPowerSupplyPWRC49EAC300WF OBJECT IDENTIFIER ::= { cevPowerSupply 295 }
cevPowerSupplyPWRC49DC300WF OBJECT IDENTIFIER ::= { cevPowerSupply 296 }
cevPowerSupplyN2kN2200Pdc400W OBJECT IDENTIFIER ::= { cevPowerSupply 297 }
cevPowerSupplyASR1000PS OBJECT IDENTIFIER ::= { cevPowerSupply 298 }
cevPowerSupplyCat2928AC60W12V OBJECT IDENTIFIER ::= { cevPowerSupply 299 }
cevPowerSupplyCat2928AC100W12V OBJECT IDENTIFIER ::= { cevPowerSupply 300 }
cevPowerSupplyPwrXPS2200 OBJECT IDENTIFIER ::= { cevPowerSupply 301 }
cevPowerSupplyN55Pac1100W OBJECT IDENTIFIER ::= { cevPowerSupply 302 }
cevPowerSupplyN2kN2200Pac400WB OBJECT IDENTIFIER ::= { cevPowerSupply 303 }
cevPowerSupplyUCS6248UpAC750W OBJECT IDENTIFIER ::= { cevPowerSupply 306 }
cevPowerSupplyUCS6248UpDC750W OBJECT IDENTIFIER ::= { cevPowerSupply 307 }
cevPowerSupplyUCS6296UpDC1100W OBJECT IDENTIFIER ::= { cevPowerSupply 308 }
cevPowerSupplyUCS6296UpAC1100W OBJECT IDENTIFIER ::= { cevPowerSupply 309 }
cevPowerSupplyN7KDC3KW OBJECT IDENTIFIER ::= { cevPowerSupply 310 }
cevPowerSupplyCat2960CAC167W OBJECT IDENTIFIER ::= { cevPowerSupply 311 }
cevPowerSupplyCat2960CAC36W12V OBJECT IDENTIFIER ::= { cevPowerSupply 312 }
cevPowerSupplyN7KAC3KW OBJECT IDENTIFIER ::= { cevPowerSupply 313 }
cevPowerSupplyN55Pdc750W OBJECT IDENTIFIER ::= { cevPowerSupply 314 }
cevPowerSupplyOe8541 OBJECT IDENTIFIER ::= { cevPowerSupply 315 }
cevPowerSupplyOe7571 OBJECT IDENTIFIER ::= { cevPowerSupply 316 }
cevPowerSupplyOe7541 OBJECT IDENTIFIER ::= { cevPowerSupply 317 }
cevPowerSupplyOe694 OBJECT IDENTIFIER ::= { cevPowerSupply 318 }
cevPowerSupplyOe594 OBJECT IDENTIFIER ::= { cevPowerSupply 319 }
cevPowerSupplyOe294 OBJECT IDENTIFIER ::= { cevPowerSupply 320 }
cevPowerSupplyASA5555PSInput OBJECT IDENTIFIER ::= { cevPowerSupply 324 }
cevPowerSupplyN2kN2200Pac400W OBJECT IDENTIFIER ::= { cevPowerSupply 325 }
cevPowerSupplyN55Pac750WB OBJECT IDENTIFIER ::= { cevPowerSupply 326 }
cevPowerSupplyN55Pac1100WB OBJECT IDENTIFIER ::= { cevPowerSupply 327 }
cevPowerSupplyASR900DC500W OBJECT IDENTIFIER ::= { cevPowerSupply 328 }
cevPowerSupplyCrs8PshDcB OBJECT IDENTIFIER ::= { cevPowerSupply 330 }
cevPowerSupplyCrs8PshAcB OBJECT IDENTIFIER ::= { cevPowerSupply 331 }
cevPowerSupplyASR5KPfu OBJECT IDENTIFIER ::= { cevPowerSupply 332 }
cevPowerSupplyASR55PFU OBJECT IDENTIFIER ::= { cevPowerSupply 333 }
cevPowerSupplyIE2000AC OBJECT IDENTIFIER ::= { cevPowerSupply 334 }
cevPowerSupplyC459000ACV OBJECT IDENTIFIER ::= { cevPowerSupply 337 }
cevPowerSupplyN2kN2200Pdc350WB OBJECT IDENTIFIER ::= { cevPowerSupply 338 }
cevPowerSupplyVG350PWRAC OBJECT IDENTIFIER ::= { cevPowerSupply 339 }
cevPowerSupplyVG350PWRDC OBJECT IDENTIFIER ::= { cevPowerSupply 340 }
cevPowerSupplyASR9KAC3KWV2 OBJECT IDENTIFIER ::= { cevPowerSupply 341 }
cevPowerSupplyASR9KDC2100WV2 OBJECT IDENTIFIER ::= { cevPowerSupply 342 }
cevPowerSupplyASR9KAC750W OBJECT IDENTIFIER ::= { cevPowerSupply 343 }
cevPowerSupplyASR9KDC750W OBJECT IDENTIFIER ::= { cevPowerSupply 344 }
cevPowerSupplyISR4400PWR1000 OBJECT IDENTIFIER ::= { cevPowerSupply 345 }
cevPowerSupplyISR4400PWR450 OBJECT IDENTIFIER ::= { cevPowerSupply 346 }
cevPowerSupplyC4KXPWR750DCF OBJECT IDENTIFIER ::= { cevPowerSupply 347 }
cevPowerSupplyC4KXPWR750ACF OBJECT IDENTIFIER ::= { cevPowerSupply 348 }
cevPowerSupplyC4KXPWR750DCR OBJECT IDENTIFIER ::= { cevPowerSupply 349 }
cevPowerSupplyC4KXPWR750ACR OBJECT IDENTIFIER ::= { cevPowerSupply 350 }
cevPowerSupplyNXAPac200WB OBJECT IDENTIFIER ::= { cevPowerSupply 351 }
cevPowerSupplyNXAPac200W OBJECT IDENTIFIER ::= { cevPowerSupply 352 }
cevPowerSupplyISR4400Unknown OBJECT IDENTIFIER ::= { cevPowerSupply 353 }
cevPowerSupplyASR9000vGenericPm OBJECT IDENTIFIER ::= { cevPowerSupply 354 }
cevPowerSupplyNXAPac1100W OBJECT IDENTIFIER ::= { cevPowerSupply 355 }
cevPowerSupplyNXAPac1100WB OBJECT IDENTIFIER ::= { cevPowerSupply 359 }
cevPowerSupplyN3kPac400WB OBJECT IDENTIFIER ::= { cevPowerSupply 360 }
cevPowerSupplyN3kPac400W OBJECT IDENTIFIER ::= { cevPowerSupply 361 }
cevPowerSupplyNXAPAC500W OBJECT IDENTIFIER ::= { cevPowerSupply 362 }
cevPowerSupplyNXAPAC500WB OBJECT IDENTIFIER ::= { cevPowerSupply 363 }
cevPowerSupplyISR4400PS OBJECT IDENTIFIER ::= { cevPowerSupply 364 }
cevPowerSupplyN55PDC1100W OBJECT IDENTIFIER ::= { cevPowerSupply 365 }
cevPowerSupplyASA5545PSInputSensor OBJECT IDENTIFIER ::= { cevPowerSupply 366 }
cevPowerSupplyASA5555PSInputSensor OBJECT IDENTIFIER ::= { cevPowerSupply 367 }
cevPowerSupplyASA5545K7PSInputSensor OBJECT IDENTIFIER ::= { cevPowerSupply 368 }
cevPowerSupplyASA5555K7PSInputSensor OBJECT IDENTIFIER ::= { cevPowerSupply 369 }
cevPowerSupplyCat2960XAC173W OBJECT IDENTIFIER ::= { cevPowerSupply 370 }
cevPowerSupplyC6880X3KWAC OBJECT IDENTIFIER ::= { cevPowerSupply 372 }
cevPowerSupplyC6880X3KWDC OBJECT IDENTIFIER ::= { cevPowerSupply 373 }
cevPowerSupplyDS9710 OBJECT IDENTIFIER ::= { cevPowerSupply 374 }
cevPowerSupplyPWR2KWDCV2 OBJECT IDENTIFIER ::= { cevPowerSupply 375 }
cevPowerSupplyPWR3KWACV2 OBJECT IDENTIFIER ::= { cevPowerSupply 376 }
cevPowerSupplyNCSDCPWRTRAY OBJECT IDENTIFIER ::= { cevPowerSupply 377 }
cevPowerSupplyNCSACPWRTRAY OBJECT IDENTIFIER ::= { cevPowerSupply 378 }
cevPowerSupplyDSC50I300AC OBJECT IDENTIFIER ::= { cevPowerSupply 380 }
cevPowerSupplyDSCAC973KW OBJECT IDENTIFIER ::= { cevPowerSupply 381 }
cevPowerSupplyDSCDC973KW OBJECT IDENTIFIER ::= { cevPowerSupply 382 }
cevPowerSupplyN77AC3KW OBJECT IDENTIFIER ::= { cevPowerSupply 383 }
cevPowerSupplyN77DC3KW OBJECT IDENTIFIER ::= { cevPowerSupply 384 }
cevPowerSupplyC6800XL3KWAC OBJECT IDENTIFIER ::= { cevPowerSupply 385 }
cevPowerSupplyC2960XR250W OBJECT IDENTIFIER ::= { cevPowerSupply 390 }
cevPowerSupplyC2960XR640W OBJECT IDENTIFIER ::= { cevPowerSupply 391 }
cevPowerSupplyC2960XR1025W OBJECT IDENTIFIER ::= { cevPowerSupply 392 }
cevPowerSupplyVG3X0PWRAC OBJECT IDENTIFIER ::= { cevPowerSupply 397 }
cevPowerSupplyVG3X0PWRDC OBJECT IDENTIFIER ::= { cevPowerSupply 398 }
cevPowerSupplyNXAPDC500W OBJECT IDENTIFIER ::= { cevPowerSupply 399 }
cevPowerSupplyNXAPDC500WB OBJECT IDENTIFIER ::= { cevPowerSupply 400 }
cevPowerSupplyC2960XR60W OBJECT IDENTIFIER ::= { cevPowerSupply 401 }
cevPowerSupplyC2960XR450W OBJECT IDENTIFIER ::= { cevPowerSupply 402 }
cevPowerSupplyC2960XR835W OBJECT IDENTIFIER ::= { cevPowerSupply 403 }
cevPowerSupplyN9KAC3000W OBJECT IDENTIFIER ::= { cevPowerSupply 404 }
cevPowerSupplyN9KPac1200WB OBJECT IDENTIFIER ::= { cevPowerSupply 405 }
cevPowerSupplyN9KPac1200W OBJECT IDENTIFIER ::= { cevPowerSupply 406 }
cevPowerSupplyN9KPac650WB OBJECT IDENTIFIER ::= { cevPowerSupply 407 }
cevPowerSupplyN9KPac650W OBJECT IDENTIFIER ::= { cevPowerSupply 408 }
cevPowerSupplyISR4430PWR250 OBJECT IDENTIFIER ::= { cevPowerSupply 409 }
cevPowerSupplyASR1001XAC OBJECT IDENTIFIER ::= { cevPowerSupply 414 }
cevPowerSupplyASR1001XDC OBJECT IDENTIFIER ::= { cevPowerSupply 415 }
cevPowerSupply30WAC OBJECT IDENTIFIER ::= { cevPowerSupply 416 }
cevPowerSupply60WAC OBJECT IDENTIFIER ::= { cevPowerSupply 417 }
cevPowerSupply60WACV2 OBJECT IDENTIFIER ::= { cevPowerSupply 418 }
cevPowerSupply125WAC OBJECT IDENTIFIER ::= { cevPowerSupply 419 }
cevPowerSupplyRT2241PWRAC OBJECT IDENTIFIER ::= { cevPowerSupply 420 }
cevPowerSupplyRT3201PWRAC OBJECT IDENTIFIER ::= { cevPowerSupply 421 }
cevPowerSupplyRT3211PWRAC OBJECT IDENTIFIER ::= { cevPowerSupply 422 }
cevPowerSupplyRT3211PWRDC OBJECT IDENTIFIER ::= { cevPowerSupply 423 }
cevPowerSupplyRT32PWRAC OBJECT IDENTIFIER ::= { cevPowerSupply 424 }
cevPowerSupplyRT3211RPSADPTR OBJECT IDENTIFIER ::= { cevPowerSupply 425 }
cevPowerSupplyRT32RPSADPTR OBJECT IDENTIFIER ::= { cevPowerSupply 426 }
cevPowerSupplyDSC48S300AC OBJECT IDENTIFIER ::= { cevPowerSupply 439 }
cevPowerSupplyISR4430PWR250DC OBJECT IDENTIFIER ::= { cevPowerSupply 440 }
cevPowerSupplyISR4430PWR500ACIP OBJECT IDENTIFIER ::= { cevPowerSupply 441 }
cevPowerSupplyISR4330PWR250AC OBJECT IDENTIFIER ::= { cevPowerSupply 442 }
cevPowerSupplyISR4330PWR500ACIP OBJECT IDENTIFIER ::= { cevPowerSupply 443 }
cevPowerSupplyISR4320PWR110AC OBJECT IDENTIFIER ::= { cevPowerSupply 444 }
cevPowerSupplyISR4320PWR230ACIP OBJECT IDENTIFIER ::= { cevPowerSupply 445 }
cevPowerSupply540WPSU OBJECT IDENTIFIER ::= { cevPowerSupply 446 }
cevPowerSupplyNXAPHV500WB OBJECT IDENTIFIER ::= { cevPowerSupply 447 }
cevPowerSupplyNXAPHV500W OBJECT IDENTIFIER ::= { cevPowerSupply 448 }
cevPowerSupplyNXAPHV1100WB OBJECT IDENTIFIER ::= { cevPowerSupply 449 }
cevPowerSupplyNXAPHV1100W OBJECT IDENTIFIER ::= { cevPowerSupply 450 }
cevPowerSupplyUCS6248HVDC750W OBJECT IDENTIFIER ::= { cevPowerSupply 451 }
cevPowerSupplyASR1000XAC750W OBJECT IDENTIFIER ::= { cevPowerSupply 452 }
cevPowerSupplyASR1000XAC1100W OBJECT IDENTIFIER ::= { cevPowerSupply 453 }
cevPowerSupplyNCS4kAC2750W OBJECT IDENTIFIER ::= { cevPowerSupply 454 }
cevPowerSupplyNCS4KDCPWRTRAY OBJECT IDENTIFIER ::= { cevPowerSupply 455 }
cevPowerSupplyContainerNCS4KPwrSupSlot OBJECT IDENTIFIER ::= { cevPowerSupply 456 }
cevPowerSupplyNCS4KACPWRTRAY OBJECT IDENTIFIER ::= { cevPowerSupply 457 }
cevPowerSupplyNCS4kDCPEM OBJECT IDENTIFIER ::= { cevPowerSupply 458 }
cevPowerSupplyCCEAC OBJECT IDENTIFIER ::= { cevPowerSupply 459 }
cevPowerSupplyCCEDC OBJECT IDENTIFIER ::= { cevPowerSupply 460 }
cevPowerSupplyASR92024SZIM OBJECT IDENTIFIER ::= { cevPowerSupply 463 }
cevPowerSupplyASR92024SZM OBJECT IDENTIFIER ::= { cevPowerSupply 464 }
cevPowerSupplyASR92024TZM OBJECT IDENTIFIER ::= { cevPowerSupply 465 }
cevPowerSupplyNCS4KPwrTrayDCDM OBJECT IDENTIFIER ::= { cevPowerSupply 466 }
cevPowerSupplyNCS4KPwrTrayDM OBJECT IDENTIFIER ::= { cevPowerSupply 467 }
cevPowerSupplyASR920PWRA OBJECT IDENTIFIER ::= { cevPowerSupply 471 }
cevPowerSupplyASR920PWRD OBJECT IDENTIFIER ::= { cevPowerSupply 472 }
cevPowerSupplyC2911PWRDCPOE OBJECT IDENTIFIER ::= { cevPowerSupply 473 }
cevPowerSupplyCat300W OBJECT IDENTIFIER ::= { cevPowerSupply 474 }
cevPowerSupplyCat42W OBJECT IDENTIFIER ::= { cevPowerSupply 475 }
cevPowerSupplyUCS6296HVDC1100W OBJECT IDENTIFIER ::= { cevPowerSupply 476 }
cevPowerSupplyASR1000XDC950W OBJECT IDENTIFIER ::= { cevPowerSupply 477 }
cevPowerSupplySCE10000AC1200W OBJECT IDENTIFIER ::= { cevPowerSupply 480 }
cevPowerSupplySCE10000DC930W OBJECT IDENTIFIER ::= { cevPowerSupply 481 }
cevPowerSupplyDSCAC1200WE OBJECT IDENTIFIER ::= { cevPowerSupply 482 }
cevPowerSupplyDSCAC1200W OBJECT IDENTIFIER ::= { cevPowerSupply 483 }
cevPowerSupplyC6880X3500WHVAC OBJECT IDENTIFIER ::= { cevPowerSupply 496 }
cevPowerSupplyPWRC3750WACR OBJECT IDENTIFIER ::= { cevPowerSupply 501 }
cevPowerSupplyPWRC3750WDCR OBJECT IDENTIFIER ::= { cevPowerSupply 502 }
cevPowerSupplyPWRC3750WACF OBJECT IDENTIFIER ::= { cevPowerSupply 503 }
cevPowerSupplyPWRC3750WDCF OBJECT IDENTIFIER ::= { cevPowerSupply 504 }
cevPowerSupplyISR4400PWR450DC OBJECT IDENTIFIER ::= { cevPowerSupply 508 }
cevPowerSupplyNC55UnivPSU OBJECT IDENTIFIER ::= { cevPowerSupply 509 }
cevPowerSupplyNC55DCPSU OBJECT IDENTIFIER ::= { cevPowerSupply 510 }
cevPowerSupplyNC55ACPSU OBJECT IDENTIFIER ::= { cevPowerSupply 511 }
cevPowerSupply1783IMXAC OBJECT IDENTIFIER ::= { cevPowerSupply 512 }
cevPowerSupply1783IMXDC OBJECT IDENTIFIER ::= { cevPowerSupply 513 }
cevPowerSupplyFPR9KPSAC OBJECT IDENTIFIER ::= { cevPowerSupply 514 }
cevPowerSupplyFPR9KPSDC OBJECT IDENTIFIER ::= { cevPowerSupply 515 }
cevPowerSupplyN7KHV3500W OBJECT IDENTIFIER ::= { cevPowerSupply 516 }
cevPowerSupplyN77HV3500W OBJECT IDENTIFIER ::= { cevPowerSupply 517 }
cevPowerSupplyN9KPuv1200W OBJECT IDENTIFIER ::= { cevPowerSupply 520 }
cevPowerSupplyNEBS650WAC OBJECT IDENTIFIER ::= { cevPowerSupply 521 }
cevPowerSupplyNXAPAC650WPI OBJECT IDENTIFIER ::= { cevPowerSupply 522 }
cevPowerSupplyNXAPAC650WPE OBJECT IDENTIFIER ::= { cevPowerSupply 523 }
cevPowerSupplyNXAPAC1200WPI OBJECT IDENTIFIER ::= { cevPowerSupply 524 }
cevPowerSupplyNXAPAC1200WPE OBJECT IDENTIFIER ::= { cevPowerSupply 525 }
cevPowerSupplyUCSPSU6332DC OBJECT IDENTIFIER ::= { cevPowerSupply 526 }
cevPowerSupplyN9KPAC3000WB OBJECT IDENTIFIER ::= { cevPowerSupply 527 }
cevPowerSupplyNCS5KPAC650WBK OBJECT IDENTIFIER ::= { cevPowerSupply 528 }
cevPowerSupplyNCS5KPAC650WFR OBJECT IDENTIFIER ::= { cevPowerSupply 529 }
cevPowerSupplyNCS5KPDC930WFR OBJECT IDENTIFIER ::= { cevPowerSupply 530 }
cevPowerSupplyNCS5KPDC930WBK OBJECT IDENTIFIER ::= { cevPowerSupply 531 }
cevPowerSupplyN9KPDC3000WB OBJECT IDENTIFIER ::= { cevPowerSupply 532 }
cevPowerSupplyNCS4K OBJECT IDENTIFIER ::= { cevPowerSupply 537 }
cevPowerSupplyASR1000XHV1100W OBJECT IDENTIFIER ::= { cevPowerSupply 538 }
cevPowerSupplyISA30004CPSInput OBJECT IDENTIFIER ::= { cevPowerSupply 539 }
cevPowerSupplyISA30002C2FPSInput OBJECT IDENTIFIER ::= { cevPowerSupply 540 }
cevPowerSupplyRAISA1783SAD4T0SPSInput OBJECT IDENTIFIER ::= { cevPowerSupply 541 }
cevPowerSupplyRAISA1783SAD2T2SPSInput OBJECT IDENTIFIER ::= { cevPowerSupply 542 }
cevPowerSupplyNCS4KPWR400A OBJECT IDENTIFIER ::= { cevPowerSupply 543 }
cevPowerSupplyNCS4KPWR400D OBJECT IDENTIFIER ::= { cevPowerSupply 544 }
cevPowerSupplyNCS4KPWR400DE OBJECT IDENTIFIER ::= { cevPowerSupply 545 }
cevPowerSupplyNCS4KPWR900D2 OBJECT IDENTIFIER ::= { cevPowerSupply 546 }
cevPowerSupplyA900PWR900A OBJECT IDENTIFIER ::= { cevPowerSupply 547 }
cevPowerSupplyA900PWR900D OBJECT IDENTIFIER ::= { cevPowerSupply 548 }
cevPowerSupplyNCS4KDC250W OBJECT IDENTIFIER ::= { cevPowerSupply 549 }
cevPowerSupplyNCS4KAC250W OBJECT IDENTIFIER ::= { cevPowerSupply 550 }
cevPowerSupplyNCS1100WACFW OBJECT IDENTIFIER ::= { cevPowerSupply 551 }
cevPowerSupplyNCS1100WACRV OBJECT IDENTIFIER ::= { cevPowerSupply 552 }
cevPowerSupplyNCS950WDCFW OBJECT IDENTIFIER ::= { cevPowerSupply 553 }
cevPowerSupplyNCS1100WDCRV OBJECT IDENTIFIER ::= { cevPowerSupply 554 }
cevPowerSupplyNCS1002AC2KW OBJECT IDENTIFIER ::= { cevPowerSupply 561 }
cevPowerSupplyNCS4216PWRFAN OBJECT IDENTIFIER ::= { cevPowerSupply 572 }
cevPowerSupplyNXAPDC930WPI OBJECT IDENTIFIER ::= { cevPowerSupply 573 }
cevPowerSupplyNXAPDC930WPE OBJECT IDENTIFIER ::= { cevPowerSupply 574 }
cevPowerSupplyFPR2KDC OBJECT IDENTIFIER ::= { cevPowerSupply 575 }
cevPowerSupplyFPR2KAC OBJECT IDENTIFIER ::= { cevPowerSupply 576 }
cevPowerSupplyNCS1002DC2KW OBJECT IDENTIFIER ::= { cevPowerSupply 577 }
cevPowerSupplyDSCHV3500W OBJECT IDENTIFIER ::= { cevPowerSupply 578 }
cevPowerSupplyDSCHV3dot5KW OBJECT IDENTIFIER ::= { cevPowerSupply 582 }
cevFan          OBJECT IDENTIFIER ::= { cevMIBObjects 7 }
cevFanC6260FanTray OBJECT IDENTIFIER ::= { cevFan 3 }
cevFanSinglePulse OBJECT IDENTIFIER ::= { cevFan 4 }
cevFanDualPulse OBJECT IDENTIFIER ::= { cevFan 5 }
cevFan12012FanTray3 OBJECT IDENTIFIER ::= { cevFan 6 }
cevFan12008FanTray6 OBJECT IDENTIFIER ::= { cevFan 7 }
cevFan12008FanTray4 OBJECT IDENTIFIER ::= { cevFan 8 }
cevFanC6160FanTray OBJECT IDENTIFIER ::= { cevFan 9 }
cevFanC6100FanTray OBJECT IDENTIFIER ::= { cevFan 11 }
cevFan12010FanTray3 OBJECT IDENTIFIER ::= { cevFan 13 }
cevFan12406FanTray3 OBJECT IDENTIFIER ::= { cevFan 14 }
cevFan12410FanTray3 OBJECT IDENTIFIER ::= { cevFan 15 }
cevFanONS15540FanTray8 OBJECT IDENTIFIER ::= { cevFan 16 }
cevFan12404FanTray7 OBJECT IDENTIFIER ::= { cevFan 17 }
cevFanBP7513MainFan OBJECT IDENTIFIER ::= { cevFan 18 }
cevFanBP7513PS1Fan OBJECT IDENTIFIER ::= { cevFan 19 }
cevFanBP7513PS2Fan OBJECT IDENTIFIER ::= { cevFan 20 }
cevFan7505Fan   OBJECT IDENTIFIER ::= { cevFan 21 }
cevFan7507Fan   OBJECT IDENTIFIER ::= { cevFan 22 }
cevFanC7300PowerSupplyFan OBJECT IDENTIFIER ::= { cevFan 23 }
cevFanC7300FanModule OBJECT IDENTIFIER ::= { cevFan 24 }
cevFanTrayC10008 OBJECT IDENTIFIER ::= { cevFan 25 }
cevFanTrayC10005 OBJECT IDENTIFIER ::= { cevFan 26 }
cevFanCat4kFanTray OBJECT IDENTIFIER ::= { cevFan 27 }
cevFanCat4kPowerSupplyFan OBJECT IDENTIFIER ::= { cevFan 28 }
cevFanC6160ITempFanTray OBJECT IDENTIFIER ::= { cevFan 29 }
cevFanONS15530FanTray6 OBJECT IDENTIFIER ::= { cevFan 30 }
cevFan12016FanTray3 OBJECT IDENTIFIER ::= { cevFan 31 }
cevFanCat3750CFM26 OBJECT IDENTIFIER ::= { cevFan 34 }
cevFanDs6SlotFanTray OBJECT IDENTIFIER ::= { cevFan 35 }
cevFanDs9SlotFanTray OBJECT IDENTIFIER ::= { cevFan 36 }
cevFanDs13SlotFanTray OBJECT IDENTIFIER ::= { cevFan 37 }
cevFanTrayUnknown OBJECT IDENTIFIER ::= { cevFan 38 }
cevFanDs2SlotFanTray OBJECT IDENTIFIER ::= { cevFan 39 }
cevFanCat3710CFM26 OBJECT IDENTIFIER ::= { cevFan 40 }
cevFanCat37xx12 OBJECT IDENTIFIER ::= { cevFan 41 }
cevFanWS9SlotFanTray OBJECT IDENTIFIER ::= { cevFan 42 }
cevFanMod9FanTray OBJECT IDENTIFIER ::= { cevFan 43 }
cevFanCat2970CFM26 OBJECT IDENTIFIER ::= { cevFan 44 }
cevFanDs1RUFanTray OBJECT IDENTIFIER ::= { cevFan 45 }
cevFanFanMod3   OBJECT IDENTIFIER ::= { cevFan 46 }
cevFanWSC6k6SlotFan OBJECT IDENTIFIER ::= { cevFan 47 }
cevFanWSC6k6SlotFan2 OBJECT IDENTIFIER ::= { cevFan 48 }
cevFanWSC6k9SlotFan OBJECT IDENTIFIER ::= { cevFan 49 }
cevFanWSC6k9SlotFan2 OBJECT IDENTIFIER ::= { cevFan 50 }
cevFanWSC6509NebFan OBJECT IDENTIFIER ::= { cevFan 51 }
cevFanWSC6k13SlotFan OBJECT IDENTIFIER ::= { cevFan 52 }
cevFanWSC6k13SlotFan2 OBJECT IDENTIFIER ::= { cevFan 53 }
cevFanFanMod3HS OBJECT IDENTIFIER ::= { cevFan 54 }
cevFanWSC6509NebFan2 OBJECT IDENTIFIER ::= { cevFan 55 }
cevFanFanMod6   OBJECT IDENTIFIER ::= { cevFan 56 }
cevFanFanMod6HS OBJECT IDENTIFIER ::= { cevFan 57 }
cevFanCrs1Fan   OBJECT IDENTIFIER ::= { cevFan 58 }
cevFanCat3560CFM26 OBJECT IDENTIFIER ::= { cevFan 59 }
cevFanDs1RUFanTray9116 OBJECT IDENTIFIER ::= { cevFan 60 }
cevFanWSC6506eFanTray OBJECT IDENTIFIER ::= { cevFan 61 }
cevFanWSC6509eFanTray OBJECT IDENTIFIER ::= { cevFan 62 }
cevFanWSC6513eFanTray OBJECT IDENTIFIER ::= { cevFan 63 }
cevFanWSC6503eFanTray OBJECT IDENTIFIER ::= { cevFan 64 }
cevFanUmg9820FanTray OBJECT IDENTIFIER ::= { cevFan 65 }
cevFanMod4HS    OBJECT IDENTIFIER ::= { cevFan 66 }
cevFanC4kFCFanTray OBJECT IDENTIFIER ::= { cevFan 67 }
cevFan12410EnhFanTray3 OBJECT IDENTIFIER ::= { cevFan 68 }
cevFan12406EnhFanTray3 OBJECT IDENTIFIER ::= { cevFan 69 }
cevFan12416EnhFanTray3 OBJECT IDENTIFIER ::= { cevFan 70 }
cevFan12404FanTray6 OBJECT IDENTIFIER ::= { cevFan 71 }
cevFan12404EnhFanTray6 OBJECT IDENTIFIER ::= { cevFan 72 }
cevFan9513FanTrayR OBJECT IDENTIFIER ::= { cevFan 73 }
cevFanCat2960CFM22 OBJECT IDENTIFIER ::= { cevFan 74 }
cevFanCat2960CFM26 OBJECT IDENTIFIER ::= { cevFan 75 }
cevFanTrayUbr10012 OBJECT IDENTIFIER ::= { cevFan 76 }
cevFanC6524     OBJECT IDENTIFIER ::= { cevFan 77 }
cevFanCatEx500CFM22 OBJECT IDENTIFIER ::= { cevFan 78 }
cevFanCatEx500CFM32 OBJECT IDENTIFIER ::= { cevFan 79 }
cevFanCat3750CFM35 OBJECT IDENTIFIER ::= { cevFan 80 }
cevFanCFM15     OBJECT IDENTIFIER ::= { cevFan 81 }
cevFanCrs1FabricFanTray OBJECT IDENTIFIER ::= { cevFan 82 }
cevModuleCrs116FanTray OBJECT IDENTIFIER ::= { cevFan 83 }
cevModuleCrs18FanTray OBJECT IDENTIFIER ::= { cevFan 84 }
cevModuleCrs14FanTray OBJECT IDENTIFIER ::= { cevFan 85 }
cevFanC3KBLWR60CFM OBJECT IDENTIFIER ::= { cevFan 86 }
cevFanMod6ShsFanTray OBJECT IDENTIFIER ::= { cevFan 87 }
cevFanMod9ShsFanTray OBJECT IDENTIFIER ::= { cevFan 88 }
cevFanMod9StFanTray OBJECT IDENTIFIER ::= { cevFan 89 }
cevFanBlwrRPS2300 OBJECT IDENTIFIER ::= { cevFan 90 }
cevFanACE4710K9CpuFan OBJECT IDENTIFIER ::= { cevFan 91 }
cevFanACE4710K9DimmFan OBJECT IDENTIFIER ::= { cevFan 92 }
cevFanACE4710K9PciFan OBJECT IDENTIFIER ::= { cevFan 93 }
cevFanWSC6509veFan OBJECT IDENTIFIER ::= { cevFan 94 }
cevFanMod3ShsFanTray OBJECT IDENTIFIER ::= { cevFan 95 }
cevFanSce8000FanTray OBJECT IDENTIFIER ::= { cevFan 96 }
cevFanN7Kc7010MainFanTray OBJECT IDENTIFIER ::= { cevFan 97 }
cevFanN7KC7010FabricFanTray OBJECT IDENTIFIER ::= { cevFan 98 }
cevFanASR1002   OBJECT IDENTIFIER ::= { cevFan 99 }
cevFanASR1004   OBJECT IDENTIFIER ::= { cevFan 100 }
cevFanASR1006   OBJECT IDENTIFIER ::= { cevFan 101 }
cevFanCe520Cfm22 OBJECT IDENTIFIER ::= { cevFan 102 }
cevFanCe520Cfm32 OBJECT IDENTIFIER ::= { cevFan 103 }
cevFanN5kC5020Fan OBJECT IDENTIFIER ::= { cevFan 104 }
cevFanCat2918Cfm22 OBJECT IDENTIFIER ::= { cevFan 105 }
cevFanC3KFAN16CFM OBJECT IDENTIFIER ::= { cevFan 106 }
cevFanPowerSupplyFan OBJECT IDENTIFIER ::= { cevFan 107 }
cevFanN7Kc7018FanTray OBJECT IDENTIFIER ::= { cevFan 109 }
cevFanCrs16lccFntrB OBJECT IDENTIFIER ::= { cevFan 110 }
cevFanASR14K4FanTray OBJECT IDENTIFIER ::= { cevFan 111 }
cevFanASR14K8FanTray OBJECT IDENTIFIER ::= { cevFan 112 }
cevFanN5kC5010Fan OBJECT IDENTIFIER ::= { cevFan 113 }
cevFanASR9KFan  OBJECT IDENTIFIER ::= { cevFan 114 }
cevFanASR9010   OBJECT IDENTIFIER ::= { cevFan 115 }
cevFanASR9006   OBJECT IDENTIFIER ::= { cevFan 116 }
cevFanASR14K4Fan OBJECT IDENTIFIER ::= { cevFan 117 }
cevFanASR14K8Fan OBJECT IDENTIFIER ::= { cevFan 118 }
cevFanCrs14Fan  OBJECT IDENTIFIER ::= { cevFan 119 }
cevFanCrs18Fan  OBJECT IDENTIFIER ::= { cevFan 120 }
cevFanCrs116Fan OBJECT IDENTIFIER ::= { cevFan 121 }
cevFanN2kC2148TFan OBJECT IDENTIFIER ::= { cevFan 122 }
cevContainerUCSN10S6100Fan1 OBJECT IDENTIFIER ::= { cevFan 124 }
cevFanCat2960CFM32 OBJECT IDENTIFIER ::= { cevFan 125 }
cevFanContainerUCSN10Fan2 OBJECT IDENTIFIER ::= { cevFan 126 }
cevFanN7Kc7009FanTray OBJECT IDENTIFIER ::= { cevFan 129 }
cevFanMEFanTray OBJECT IDENTIFIER ::= { cevFan 130 }
cevFanMXE5600   OBJECT IDENTIFIER ::= { cevFan 131 }
cevFanC2360Fan  OBJECT IDENTIFIER ::= { cevFan 132 }
cevFanASR1001FanTray OBJECT IDENTIFIER ::= { cevFan 133 }
cevFanASR1000Fan OBJECT IDENTIFIER ::= { cevFan 134 }
cevFanN5548PFan OBJECT IDENTIFIER ::= { cevFan 135 }
cevFanCrs16FanTrB OBJECT IDENTIFIER ::= { cevFan 139 }
cevFanCat2928Cfm22 OBJECT IDENTIFIER ::= { cevFan 140 }
cevFanCat2928Cfm32 OBJECT IDENTIFIER ::= { cevFan 141 }
cevFanBlwrXPS2200 OBJECT IDENTIFIER ::= { cevFan 142 }
cevFanN5596UPFan OBJECT IDENTIFIER ::= { cevFan 143 }
cevFanN2kC2248TBFan OBJECT IDENTIFIER ::= { cevFan 144 }
cevFanN2kC2232TBFan OBJECT IDENTIFIER ::= { cevFan 145 }
cevFanN3kC3064Fan OBJECT IDENTIFIER ::= { cevFan 148 }
cevFanUCS6248UPFan OBJECT IDENTIFIER ::= { cevFan 149 }
cevFanUCS6296UPFan OBJECT IDENTIFIER ::= { cevFan 150 }
cevFanOe694     OBJECT IDENTIFIER ::= { cevFan 151 }
cevFanOe594     OBJECT IDENTIFIER ::= { cevFan 152 }
cevFanOe294     OBJECT IDENTIFIER ::= { cevFan 153 }
cevFanOe7571    OBJECT IDENTIFIER ::= { cevFan 154 }
cevFanOe7541    OBJECT IDENTIFIER ::= { cevFan 155 }
cevFanOe8541    OBJECT IDENTIFIER ::= { cevFan 156 }
cevFanCrs16SBFan OBJECT IDENTIFIER ::= { cevFan 157 }
cevFanCrs16FabricFan OBJECT IDENTIFIER ::= { cevFan 158 }
cevFanASA5555PSFan OBJECT IDENTIFIER ::= { cevFan 160 }
cevFanASA5555ChassisFan OBJECT IDENTIFIER ::= { cevFan 167 }
cevFanN3kC3064FanB OBJECT IDENTIFIER ::= { cevFan 173 }
cevFanASR903FanTray OBJECT IDENTIFIER ::= { cevFan 174 }
cevFanASR900Fan OBJECT IDENTIFIER ::= { cevFan 175 }
cevFanASR5KFANTLW OBJECT IDENTIFIER ::= { cevFan 176 }
cevFanASR5KFANTUP OBJECT IDENTIFIER ::= { cevFan 177 }
cevFanASR55FANTF OBJECT IDENTIFIER ::= { cevFan 178 }
cevFanASR55FANTR OBJECT IDENTIFIER ::= { cevFan 179 }
cevFanN7Kc7004FanTray OBJECT IDENTIFIER ::= { cevFan 180 }
cevFanN3kC3048Fan OBJECT IDENTIFIER ::= { cevFan 181 }
cevFanN3kC3048FanB OBJECT IDENTIFIER ::= { cevFan 182 }
cevFanASR9001   OBJECT IDENTIFIER ::= { cevFan 183 }
cevFanTrayISR4400 OBJECT IDENTIFIER ::= { cevFan 185 }
cevFanAsr9922Fan OBJECT IDENTIFIER ::= { cevFan 187 }
cevFanAirstrikeCpuBlower OBJECT IDENTIFIER ::= { cevFan 188 }
cevFanMod13SeFanTray OBJECT IDENTIFIER ::= { cevFan 189 }
cevFanN6kC600496PQFanB OBJECT IDENTIFIER ::= { cevFan 190 }
cevFanN6kC600496PQFanF OBJECT IDENTIFIER ::= { cevFan 191 }
cevFanN3kC3548PFanB OBJECT IDENTIFIER ::= { cevFan 192 }
cevFanN3kC3548PFan OBJECT IDENTIFIER ::= { cevFan 193 }
cevFanA9K9912FAN OBJECT IDENTIFIER ::= { cevFan 194 }
cevFanISR4400Fan OBJECT IDENTIFIER ::= { cevFan 195 }
cevFanAsr9010FanV2 OBJECT IDENTIFIER ::= { cevFan 196 }
cevFanCat2960XCFM23 OBJECT IDENTIFIER ::= { cevFan 197 }
cevFanCat2960XCFM38 OBJECT IDENTIFIER ::= { cevFan 198 }
cevFanDSC9710   OBJECT IDENTIFIER ::= { cevFan 200 }
cevFanAsr9904Fan OBJECT IDENTIFIER ::= { cevFan 201 }
cevFanNCSFANTRAY OBJECT IDENTIFIER ::= { cevFan 202 }
cevFanDSC50I    OBJECT IDENTIFIER ::= { cevFan 203 }
cevFanC6880xFan OBJECT IDENTIFIER ::= { cevFan 204 }
cevFanCrs18SBFan OBJECT IDENTIFIER ::= { cevFan 205 }
cevFanCrs18FanTrayB OBJECT IDENTIFIER ::= { cevFan 206 }
cevFanN77c7718Fan OBJECT IDENTIFIER ::= { cevFan 207 }
cevFanN77c7710Fan OBJECT IDENTIFIER ::= { cevFan 208 }
cevFanN77c7706Fan OBJECT IDENTIFIER ::= { cevFan 209 }
cevFanC6807xlFan OBJECT IDENTIFIER ::= { cevFan 210 }
cevFanNCSFan    OBJECT IDENTIFIER ::= { cevFan 211 }
cevFanN3KC3172TQFAN OBJECT IDENTIFIER ::= { cevFan 213 }
cevFanN3KC3172TQFANB OBJECT IDENTIFIER ::= { cevFan 214 }
cevFanN3KC3172PQFANB OBJECT IDENTIFIER ::= { cevFan 215 }
cevFanN3KC3172PQFAN OBJECT IDENTIFIER ::= { cevFan 216 }
cevFanN3KC3132FAN OBJECT IDENTIFIER ::= { cevFan 217 }
cevFanN3KC3132FANB OBJECT IDENTIFIER ::= { cevFan 218 }
cevFanDSC9706FAN OBJECT IDENTIFIER ::= { cevFan 219 }
cevFanNCS4KFTA  OBJECT IDENTIFIER ::= { cevFan 220 }
cevFanNCS4KLCCFan OBJECT IDENTIFIER ::= { cevFan 221 }
cevFanN9Kc9508FanTray OBJECT IDENTIFIER ::= { cevFan 222 }
cevFanTrayISR4430 OBJECT IDENTIFIER ::= { cevFan 223 }
cevFanASR1001XFanTray OBJECT IDENTIFIER ::= { cevFan 225 }
cevFanASR902FanTray OBJECT IDENTIFIER ::= { cevFan 226 }
cevFanN56128FanB OBJECT IDENTIFIER ::= { cevFan 227 }
cevFanN56128FanF OBJECT IDENTIFIER ::= { cevFan 228 }
cevFanDSC48SFAN OBJECT IDENTIFIER ::= { cevFan 229 }
cevFanN9Kc9516FanTray OBJECT IDENTIFIER ::= { cevFan 230 }
cevFanN9Kc9504FanTray OBJECT IDENTIFIER ::= { cevFan 231 }
cevFanN9Kc9300FanTray2B OBJECT IDENTIFIER ::= { cevFan 232 }
cevFanN9Kc9300FanTray2 OBJECT IDENTIFIER ::= { cevFan 233 }
cevFanN9Kc9300FanTray1B OBJECT IDENTIFIER ::= { cevFan 234 }
cevFanN9Kc9300FanTray1 OBJECT IDENTIFIER ::= { cevFan 235 }
cevFanAsr9922FanV2 OBJECT IDENTIFIER ::= { cevFan 236 }
cevFanNXAFAN30CFMB OBJECT IDENTIFIER ::= { cevFan 237 }
cevFanNXAFAN30CFMF OBJECT IDENTIFIER ::= { cevFan 238 }
cevFanASR9001V2 OBJECT IDENTIFIER ::= { cevFan 239 }
cevFanN6kC6001FanF OBJECT IDENTIFIER ::= { cevFan 240 }
cevFanN6kC6001FanB OBJECT IDENTIFIER ::= { cevFan 241 }
cevFanNCSFFANTRAY OBJECT IDENTIFIER ::= { cevFan 242 }
cevFanTrayISR4330 OBJECT IDENTIFIER ::= { cevFan 244 }
cevFanTrayISR4320 OBJECT IDENTIFIER ::= { cevFan 245 }
cevFanASR1000XFanTray OBJECT IDENTIFIER ::= { cevFan 246 }
cevFanAsa5508ChassisFan OBJECT IDENTIFIER ::= { cevFan 247 }
cevFanAsa5508K7ChassisFan OBJECT IDENTIFIER ::= { cevFan 248 }
cevFanAsr9KvV2Fan OBJECT IDENTIFIER ::= { cevFan 250 }
cevFanASR920FanTray15ru OBJECT IDENTIFIER ::= { cevFan 251 }
cevFanASR920FanTray1ru OBJECT IDENTIFIER ::= { cevFan 252 }
cevFanN5K5696FanB OBJECT IDENTIFIER ::= { cevFan 253 }
cevFanN5K5696FanF OBJECT IDENTIFIER ::= { cevFan 254 }
cevFanN77c7702Fan OBJECT IDENTIFIER ::= { cevFan 255 }
cevFanASR9006V2 OBJECT IDENTIFIER ::= { cevFan 257 }
cevFanN9KC9300FAN3B OBJECT IDENTIFIER ::= { cevFan 258 }
cevFanSce10000Fan OBJECT IDENTIFIER ::= { cevFan 261 }
cevFanDSC96SFANE OBJECT IDENTIFIER ::= { cevFan 262 }
cevFanDSC96SFANI OBJECT IDENTIFIER ::= { cevFan 263 }
cevFanAsa5516ChassisFan OBJECT IDENTIFIER ::= { cevFan 264 }
cevFanASR1002HXFanTray OBJECT IDENTIFIER ::= { cevFan 266 }
cevFanAsr9910Fan OBJECT IDENTIFIER ::= { cevFan 267 }
cevFanDSC9718FAN OBJECT IDENTIFIER ::= { cevFan 269 }
cevFanT3R       OBJECT IDENTIFIER ::= { cevFan 275 }
cevFanT3F       OBJECT IDENTIFIER ::= { cevFan 276 }
cevFanNC55FanTray OBJECT IDENTIFIER ::= { cevFan 277 }
cevFanNC55Fan   OBJECT IDENTIFIER ::= { cevFan 278 }
cevFanNCS5001FANBK OBJECT IDENTIFIER ::= { cevFan 279 }
cevFanNCS5001FANFR OBJECT IDENTIFIER ::= { cevFan 280 }
cevFanNCS5002FANFR OBJECT IDENTIFIER ::= { cevFan 281 }
cevFanNCS5002FANBK OBJECT IDENTIFIER ::= { cevFan 282 }
cevFanNCS4K     OBJECT IDENTIFIER ::= { cevFan 285 }
cevFanASR1001HXFanTray OBJECT IDENTIFIER ::= { cevFan 287 }
cevFanNCS4202   OBJECT IDENTIFIER ::= { cevFan 288 }
cevFanNCS4201   OBJECT IDENTIFIER ::= { cevFan 289 }
cevFanASR920FanTray2ruCc OBJECT IDENTIFIER ::= { cevFan 290 }
cevFanNCS1002FanTray OBJECT IDENTIFIER ::= { cevFan 291 }
cevFanNCS5011FANFR OBJECT IDENTIFIER ::= { cevFan 298 }
cevFanNCS5011FANBK OBJECT IDENTIFIER ::= { cevFan 299 }
cevFanNCS4216F2BFAN OBJECT IDENTIFIER ::= { cevFan 301 }
cevFanFPR2KCoolingFan OBJECT IDENTIFIER ::= { cevFan 302 }
cevSensor       OBJECT IDENTIFIER ::= { cevMIBObjects 8 }
cevSensorMGX8800Temp OBJECT IDENTIFIER ::= { cevSensor 11 }
cevSensorMGX8800PSVoltage OBJECT IDENTIFIER ::= { cevSensor 12 }
cevSensorMGX8800FanSpeed OBJECT IDENTIFIER ::= { cevSensor 13 }
cevSensorONS15540Temp OBJECT IDENTIFIER ::= { cevSensor 14 }
cevSensorONS15540Power OBJECT IDENTIFIER ::= { cevSensor 15 }
cevSensor7500ChassisInterface OBJECT IDENTIFIER ::= { cevSensor 16 }
cevSensorC7300InletTempVoltage OBJECT IDENTIFIER ::= { cevSensor 17 }
cevSensorC7300OutletTempVoltage OBJECT IDENTIFIER ::= { cevSensor 18 }
cevSensorC7300HotspotTempVoltage OBJECT IDENTIFIER ::= { cevSensor 19 }
cevSensorC7300NseDbTempVoltage OBJECT IDENTIFIER ::= { cevSensor 20 }
cevSensorC7300PSFanState OBJECT IDENTIFIER ::= { cevSensor 21 }
cevSensorC10KInletTemp OBJECT IDENTIFIER ::= { cevSensor 22 }
cevSensorC10000CoreTemp OBJECT IDENTIFIER ::= { cevSensor 23 }
cevSensorCat4kTemp OBJECT IDENTIFIER ::= { cevSensor 24 }
cevSensorONS15530Temp OBJECT IDENTIFIER ::= { cevSensor 25 }
cevSensorONS15530Power OBJECT IDENTIFIER ::= { cevSensor 26 }
cevSensorVxsmVoltage OBJECT IDENTIFIER ::= { cevSensor 27 }
cevSensorVxsmTemp OBJECT IDENTIFIER ::= { cevSensor 28 }
cevSensor15302701Temp OBJECT IDENTIFIER ::= { cevSensor 29 }
cevSensorUnknown OBJECT IDENTIFIER ::= { cevSensor 30 }
cevSensorModuleDeviceTemp OBJECT IDENTIFIER ::= { cevSensor 31 }
cevSensorClock  OBJECT IDENTIFIER ::= { cevSensor 32 }
cevSensorVtt    OBJECT IDENTIFIER ::= { cevSensor 33 }
cevSensorModulePowerOutputFail OBJECT IDENTIFIER ::= { cevSensor 34 }
cevSensorModuleOutletTemp OBJECT IDENTIFIER ::= { cevSensor 35 }
cevSensorModuleInletTemp OBJECT IDENTIFIER ::= { cevSensor 36 }
cevSensorFanTrayStatus OBJECT IDENTIFIER ::= { cevSensor 37 }
cevSensorPSFan  OBJECT IDENTIFIER ::= { cevSensor 38 }
cevSensorPSOutput OBJECT IDENTIFIER ::= { cevSensor 39 }
cevSensorPSInput OBJECT IDENTIFIER ::= { cevSensor 40 }
cevSensorCrs1Voltage OBJECT IDENTIFIER ::= { cevSensor 41 }
cevSensorCrs1Temp OBJECT IDENTIFIER ::= { cevSensor 42 }
cevSensorCrs1Current OBJECT IDENTIFIER ::= { cevSensor 43 }
cevSensorCrs1FanSpeed OBJECT IDENTIFIER ::= { cevSensor 44 }
cevSensorModuleDeviceVoltage OBJECT IDENTIFIER ::= { cevSensor 45 }
cevSensorTransceiverRxPwr OBJECT IDENTIFIER ::= { cevSensor 46 }
cevSensorTransceiverTxPwr OBJECT IDENTIFIER ::= { cevSensor 47 }
cevSensorTransceiverCurrent OBJECT IDENTIFIER ::= { cevSensor 48 }
cevSensorTransceiverVoltage OBJECT IDENTIFIER ::= { cevSensor 49 }
cevSensorTransceiverTemp OBJECT IDENTIFIER ::= { cevSensor 50 }
cevSensorModuleFanUpgradeRequired OBJECT IDENTIFIER ::= { cevSensor 51 }
cevSensorModuleInsufficientCooling OBJECT IDENTIFIER ::= { cevSensor 52 }
cevSensorPSFanIncompatible OBJECT IDENTIFIER ::= { cevSensor 55 }
cevSensorACE4710K9CPUTemp OBJECT IDENTIFIER ::= { cevSensor 56 }
cevSensorACE4710K9AmbientTemp OBJECT IDENTIFIER ::= { cevSensor 57 }
cevSensorCpuFanSpeed OBJECT IDENTIFIER ::= { cevSensor 58 }
cevSensorACE4710K9DimmFanSpeed OBJECT IDENTIFIER ::= { cevSensor 59 }
cevSensorACE4710K9PciFanSpeed OBJECT IDENTIFIER ::= { cevSensor 60 }
cevSensorModuleDeviceCurrent OBJECT IDENTIFIER ::= { cevSensor 61 }
cevSensorCrs16dcPemB OBJECT IDENTIFIER ::= { cevSensor 62 }
cevSensorExternalContact OBJECT IDENTIFIER ::= { cevSensor 63 }
cevSensorFanSpeed OBJECT IDENTIFIER ::= { cevSensor 64 }
cevSensorCrs1PwrVoltage OBJECT IDENTIFIER ::= { cevSensor 65 }
cevSensorCrs1Led OBJECT IDENTIFIER ::= { cevSensor 66 }
cevSensorMXE5600Temp OBJECT IDENTIFIER ::= { cevSensor 67 }
cevSensorMXE5600FanSpeed OBJECT IDENTIFIER ::= { cevSensor 68 }
cevSensorMXE5600Voltage OBJECT IDENTIFIER ::= { cevSensor 69 }
cevSensorMXE5600Current OBJECT IDENTIFIER ::= { cevSensor 70 }
cevSensorModuleDevicePower OBJECT IDENTIFIER ::= { cevSensor 132 }
cevSensorModuleDeviceFanRotation OBJECT IDENTIFIER ::= { cevSensor 133 }
cevSensorModuleDevicePressure OBJECT IDENTIFIER ::= { cevSensor 134 }
cevSensorVoltagesensor OBJECT IDENTIFIER ::= { cevSensor 135 }
cevSensorCursensor OBJECT IDENTIFIER ::= { cevSensor 136 }
cevSensorTempsensor OBJECT IDENTIFIER ::= { cevSensor 137 }
cevSensorLEDsensor OBJECT IDENTIFIER ::= { cevSensor 138 }
cevSensorFanSpeedsensor OBJECT IDENTIFIER ::= { cevSensor 139 }
cevSensorMultiSensorModule OBJECT IDENTIFIER ::= { cevSensor 140 }
cevSensorPowersensor OBJECT IDENTIFIER ::= { cevSensor 141 }
cevSensorDiagStatus OBJECT IDENTIFIER ::= { cevSensor 143 }
cevSensorNCS4KVol OBJECT IDENTIFIER ::= { cevSensor 144 }
cevSensorNCS4KCur OBJECT IDENTIFIER ::= { cevSensor 145 }
cevSensorNCS4KTemp OBJECT IDENTIFIER ::= { cevSensor 146 }
cevSensorNCS4KLED OBJECT IDENTIFIER ::= { cevSensor 147 }
cevSensorNCS4KFanSpeed OBJECT IDENTIFIER ::= { cevSensor 148 }
cevSensorNCS4KMultiHostingMod OBJECT IDENTIFIER ::= { cevSensor 149 }
cevSensorNCS4KPressure OBJECT IDENTIFIER ::= { cevSensor 150 }
cevSensorASR5000CardTemp OBJECT IDENTIFIER ::= { cevSensor 151 }
cevSensorASR5000CardVoltage OBJECT IDENTIFIER ::= { cevSensor 152 }
cevSensorASR5000FanTemp OBJECT IDENTIFIER ::= { cevSensor 153 }
cevSensorASR5500CardTemp OBJECT IDENTIFIER ::= { cevSensor 154 }
cevSensorASR5500CardVoltage OBJECT IDENTIFIER ::= { cevSensor 155 }
cevSensorASR5500CardPower OBJECT IDENTIFIER ::= { cevSensor 156 }
cevSensorASR5500CardAirFlow OBJECT IDENTIFIER ::= { cevSensor 157 }
cevSensorASR5500CardBinary OBJECT IDENTIFIER ::= { cevSensor 158 }
cevSensorASR5500CardPercentage OBJECT IDENTIFIER ::= { cevSensor 159 }
cevSensorASR5500CardCurrent OBJECT IDENTIFIER ::= { cevSensor 160 }
cevSensorASR5500FanTemp OBJECT IDENTIFIER ::= { cevSensor 161 }
cevSensorAsa5508ChassisFanSensor OBJECT IDENTIFIER ::= { cevSensor 162 }
cevSensorAsa5508K7ChassisFanSensor OBJECT IDENTIFIER ::= { cevSensor 163 }
cevSensorAsa5506CpuTempSensor OBJECT IDENTIFIER ::= { cevSensor 164 }
cevSensorAsa5506WCpuTempSensor OBJECT IDENTIFIER ::= { cevSensor 165 }
cevSensorAsa5508CpuTempSensor OBJECT IDENTIFIER ::= { cevSensor 166 }
cevSensorAsa5506K7CpuTempSensor OBJECT IDENTIFIER ::= { cevSensor 167 }
cevSensorAsa5508K7CpuTempSensor OBJECT IDENTIFIER ::= { cevSensor 168 }
cevSensorAsa5506AcceleratorTempSensor OBJECT IDENTIFIER ::= { cevSensor 169 }
cevSensorAsa5506WAcceleratorTempSensor OBJECT IDENTIFIER ::= { cevSensor 170 }
cevSensorAsa5508AcceleratorTempSensor OBJECT IDENTIFIER ::= { cevSensor 171 }
cevSensorAsa5506K7AcceleratorTempSensor OBJECT IDENTIFIER ::= { cevSensor 172 }
cevSensorAsa5508K7AcceleratorTempSensor OBJECT IDENTIFIER ::= { cevSensor 173 }
cevSensorAsa5506ChassisTempSensor OBJECT IDENTIFIER ::= { cevSensor 174 }
cevSensorAsa5506WChassisTempSensor OBJECT IDENTIFIER ::= { cevSensor 175 }
cevSensorAsa5508ChassisTempSensor OBJECT IDENTIFIER ::= { cevSensor 176 }
cevSensorAsa5506K7ChassisTempSensor OBJECT IDENTIFIER ::= { cevSensor 177 }
cevSensorAsa5508K7ChassisTempSensor OBJECT IDENTIFIER ::= { cevSensor 178 }
cevSensorNCS4kPowersensor OBJECT IDENTIFIER ::= { cevSensor 179 }
cevSensorAsa5516ChassisFanSensor OBJECT IDENTIFIER ::= { cevSensor 180 }
cevSensorAsa5506HCpuTempSensor OBJECT IDENTIFIER ::= { cevSensor 181 }
cevSensorAsa5516CpuTempSensor OBJECT IDENTIFIER ::= { cevSensor 182 }
cevSensorAsa5506HAcceleratorTempSensor OBJECT IDENTIFIER ::= { cevSensor 183 }
cevSensorAsa5516AcceleratorTempSensor OBJECT IDENTIFIER ::= { cevSensor 184 }
cevSensorAsa5506HChassisTempSensor OBJECT IDENTIFIER ::= { cevSensor 185 }
cevSensorAsa5516ChassisTempSensor OBJECT IDENTIFIER ::= { cevSensor 186 }
cevSensorISA30004CCpuTempSensor OBJECT IDENTIFIER ::= { cevSensor 187 }
cevSensorRAISA1783SAD2T2SCpuTempSensor OBJECT IDENTIFIER ::= { cevSensor 188 }
cevSensorISA30002C2FCpuTempSensor OBJECT IDENTIFIER ::= { cevSensor 189 }
cevSensorRAISA1783SAD4T0SCpuTempSensor OBJECT IDENTIFIER ::= { cevSensor 190 }
cevSensorISA4000CpuTempSensor OBJECT IDENTIFIER ::= { cevSensor 191 }
cevSensorISA30004CPTS OBJECT IDENTIFIER ::= { cevSensor 192 }
cevSensorISA30002C2FPTS OBJECT IDENTIFIER ::= { cevSensor 193 }
cevSensorRAISA4T0SProcessorcardTS OBJECT IDENTIFIER ::= { cevSensor 194 }
cevSensorRAISA2T2SProcessorcardTS OBJECT IDENTIFIER ::= { cevSensor 195 }
cevSensorISA4000PTS OBJECT IDENTIFIER ::= { cevSensor 196 }
cevSensorISA30004CPowercardTS OBJECT IDENTIFIER ::= { cevSensor 197 }
cevSensorISA30002C2FPowercardTS OBJECT IDENTIFIER ::= { cevSensor 198 }
cevSensorISA30004CPortcardTS OBJECT IDENTIFIER ::= { cevSensor 199 }
cevSensorISA30002C2FPortcardTS OBJECT IDENTIFIER ::= { cevSensor 200 }
cevSensorRAISA4T0SPowercardTS OBJECT IDENTIFIER ::= { cevSensor 201 }
cevSensorRAISA2T2SPowercardTS OBJECT IDENTIFIER ::= { cevSensor 202 }
cevSensorRAISA4T0SPortcardTS OBJECT IDENTIFIER ::= { cevSensor 203 }
cevSensorRAISA2T2SPortcardTS OBJECT IDENTIFIER ::= { cevSensor 204 }
cevSensorISA4000PowercardTS OBJECT IDENTIFIER ::= { cevSensor 205 }
cevSensorISA4000PortcardTS OBJECT IDENTIFIER ::= { cevSensor 206 }
cevSensorISA30004CPS OBJECT IDENTIFIER ::= { cevSensor 207 }
cevSensorISA30002C2FPS OBJECT IDENTIFIER ::= { cevSensor 208 }
cevSensorRAISA1783SAD4T0SPS OBJECT IDENTIFIER ::= { cevSensor 209 }
cevSensorRAISA1783SAD2T2SPS OBJECT IDENTIFIER ::= { cevSensor 210 }
cevSensorModuleDeviceSNR OBJECT IDENTIFIER ::= { cevSensor 211 }
cevSensorModuleDeviceISI OBJECT IDENTIFIER ::= { cevSensor 212 }
cevSensorModuleDevicePAM OBJECT IDENTIFIER ::= { cevSensor 213 }
cevSensorModuleDevicePreFECBER OBJECT IDENTIFIER ::= { cevSensor 214 }
cevSensorModuleDeviceUncorrectedBER OBJECT IDENTIFIER ::= { cevSensor 215 }
cevSensorModuleDeviceTECCurrent OBJECT IDENTIFIER ::= { cevSensor 216 }
cevSensorModuleDevDiffLaserFrequency OBJECT IDENTIFIER ::= { cevSensor 217 }
cevSensorModuleDeviceDiffLaserTemp OBJECT IDENTIFIER ::= { cevSensor 218 }
cevModule       OBJECT IDENTIFIER ::= { cevMIBObjects 9 }
cevModuleUnknownCard OBJECT IDENTIFIER ::= { cevModule 1 }
cevModuleCommonCards OBJECT IDENTIFIER ::= { cevModule 2 }
cevWicSerial1t  OBJECT IDENTIFIER ::= { cevModuleCommonCards 1 }
cevWicST3420    OBJECT IDENTIFIER ::= { cevModuleCommonCards 5 }
cevWicST2186    OBJECT IDENTIFIER ::= { cevModuleCommonCards 6 }
cevWicU3420     OBJECT IDENTIFIER ::= { cevModuleCommonCards 7 }
cevWicU2091     OBJECT IDENTIFIER ::= { cevModuleCommonCards 8 }
cevWicU20912081 OBJECT IDENTIFIER ::= { cevModuleCommonCards 9 }
cevWicST2186Leased OBJECT IDENTIFIER ::= { cevModuleCommonCards 10 }
cevVicFxs       OBJECT IDENTIFIER ::= { cevModuleCommonCards 11 }
cevVicFxo       OBJECT IDENTIFIER ::= { cevModuleCommonCards 12 }
cevVicEm        OBJECT IDENTIFIER ::= { cevModuleCommonCards 13 }
cevAimCompression OBJECT IDENTIFIER ::= { cevModuleCommonCards 14 }
cevWvic1dsuT1   OBJECT IDENTIFIER ::= { cevModuleCommonCards 16 }
cevWvic1dsuE1   OBJECT IDENTIFIER ::= { cevModuleCommonCards 17 }
cevWvic2dsuT1   OBJECT IDENTIFIER ::= { cevModuleCommonCards 18 }
cevWvic2dsuE1   OBJECT IDENTIFIER ::= { cevModuleCommonCards 19 }
cevWvic2dsuT1Di OBJECT IDENTIFIER ::= { cevModuleCommonCards 20 }
cevWvic2dsuE1Di OBJECT IDENTIFIER ::= { cevModuleCommonCards 21 }
cevAimEncryption OBJECT IDENTIFIER ::= { cevModuleCommonCards 22 }
cevPmNmToAim    OBJECT IDENTIFIER ::= { cevModuleCommonCards 23 }
cevDfc8ce1      OBJECT IDENTIFIER ::= { cevModuleCommonCards 24 }
cevDfc8ct1      OBJECT IDENTIFIER ::= { cevModuleCommonCards 25 }
cevDfcCt3       OBJECT IDENTIFIER ::= { cevModuleCommonCards 26 }
cevDfcNp108     OBJECT IDENTIFIER ::= { cevModuleCommonCards 27 }
cevWicSerial2as OBJECT IDENTIFIER ::= { cevModuleCommonCards 29 }
cevWicCsuDsuFT1 OBJECT IDENTIFIER ::= { cevModuleCommonCards 30 }
cevIsaIpsecMppe OBJECT IDENTIFIER ::= { cevModuleCommonCards 31 }
cevWicDslsar20150 OBJECT IDENTIFIER ::= { cevModuleCommonCards 32 }
cevDfc2ce1      OBJECT IDENTIFIER ::= { cevModuleCommonCards 35 }
cevDfcNp60      OBJECT IDENTIFIER ::= { cevModuleCommonCards 37 }
cevSpeNp6       OBJECT IDENTIFIER ::= { cevModuleCommonCards 43 }
cevWvic2dsuT1DIR OBJECT IDENTIFIER ::= { cevModuleCommonCards 47 }
cevWvic2dsuE1DIR OBJECT IDENTIFIER ::= { cevModuleCommonCards 48 }
cevVic4vpFxsDid OBJECT IDENTIFIER ::= { cevModuleCommonCards 49 }
cevVic4fxoUsM1  OBJECT IDENTIFIER ::= { cevModuleCommonCards 50 }
cevVic4fxoM2M3  OBJECT IDENTIFIER ::= { cevModuleCommonCards 51 }
cevVic4fxoCAMA  OBJECT IDENTIFIER ::= { cevModuleCommonCards 52 }
cevWicEthernet  OBJECT IDENTIFIER ::= { cevModuleCommonCards 55 }
cevCeSA6DC      OBJECT IDENTIFIER ::= { cevModuleCommonCards 56 }
cevCeSA6AC      OBJECT IDENTIFIER ::= { cevModuleCommonCards 57 }
cevCeSA12AC     OBJECT IDENTIFIER ::= { cevModuleCommonCards 58 }
cevC2610XM1Fe   OBJECT IDENTIFIER ::= { cevModuleCommonCards 59 }
cevC2611XM2Fe   OBJECT IDENTIFIER ::= { cevModuleCommonCards 60 }
cevC2620XM1Fe   OBJECT IDENTIFIER ::= { cevModuleCommonCards 61 }
cevC2621XM2Fe   OBJECT IDENTIFIER ::= { cevModuleCommonCards 62 }
cevC2650XM1Fe   OBJECT IDENTIFIER ::= { cevModuleCommonCards 63 }
cevC2651XM2Fe   OBJECT IDENTIFIER ::= { cevModuleCommonCards 64 }
cevVic8fxoUsM1  OBJECT IDENTIFIER ::= { cevModuleCommonCards 65 }
cevCeSA14       OBJECT IDENTIFIER ::= { cevModuleCommonCards 66 }
cevWicDslsar20174Isdn OBJECT IDENTIFIER ::= { cevModuleCommonCards 67 }
cevWicDslsar20174Pots OBJECT IDENTIFIER ::= { cevModuleCommonCards 68 }
cevSpaIpSec2G   OBJECT IDENTIFIER ::= { cevModuleCommonCards 69 }
cevNmSe         OBJECT IDENTIFIER ::= { cevModuleCommonCards 70 }
cevAimSe        OBJECT IDENTIFIER ::= { cevModuleCommonCards 71 }
cevWicSe        OBJECT IDENTIFIER ::= { cevModuleCommonCards 72 }
cevCeDs2100     OBJECT IDENTIFIER ::= { cevModuleCommonCards 73 }
cevDfc16ce1     OBJECT IDENTIFIER ::= { cevModuleCommonCards 74 }
cevDfc16ct1     OBJECT IDENTIFIER ::= { cevModuleCommonCards 75 }
cevSpa2pOc3Atm  OBJECT IDENTIFIER ::= { cevModuleCommonCards 76 }
cevSpa4pOc3Atm  OBJECT IDENTIFIER ::= { cevModuleCommonCards 77 }
cevSpa1pOc12Atm OBJECT IDENTIFIER ::= { cevModuleCommonCards 78 }
cevSpa1pOc48Atm OBJECT IDENTIFIER ::= { cevModuleCommonCards 80 }
cevSpa2pOc3Pos  OBJECT IDENTIFIER ::= { cevModuleCommonCards 83 }
cevSpa4pOc3Pos  OBJECT IDENTIFIER ::= { cevModuleCommonCards 84 }
cevSpa1pOc12Pos OBJECT IDENTIFIER ::= { cevModuleCommonCards 85 }
cevSpa2pOc12Pos OBJECT IDENTIFIER ::= { cevModuleCommonCards 86 }
cevSpa8pOc12Pos OBJECT IDENTIFIER ::= { cevModuleCommonCards 87 }
cevSpa4pFe7304  OBJECT IDENTIFIER ::= { cevModuleCommonCards 88 }
cevSpa2pGe7304  OBJECT IDENTIFIER ::= { cevModuleCommonCards 89 }
cevWicEswitch4  OBJECT IDENTIFIER ::= { cevModuleCommonCards 90 }
cevWicBri3086u  OBJECT IDENTIFIER ::= { cevModuleCommonCards 91 }
cevSpa1pOc192PosRprXfp OBJECT IDENTIFIER ::= { cevModuleCommonCards 92 }
cevSpa1pOc192PosRprSmLr OBJECT IDENTIFIER ::= { cevModuleCommonCards 94 }
cevSpa1pOc192PosRprVsr OBJECT IDENTIFIER ::= { cevModuleCommonCards 95 }
cevSpa2pT3E3Serial OBJECT IDENTIFIER ::= { cevModuleCommonCards 96 }
cevSpa4pT3E3Serial OBJECT IDENTIFIER ::= { cevModuleCommonCards 97 }
cevSpa8pCT1E1   OBJECT IDENTIFIER ::= { cevModuleCommonCards 98 }
cevSpa2pCT3     OBJECT IDENTIFIER ::= { cevModuleCommonCards 99 }
cevSpa4pCT3     OBJECT IDENTIFIER ::= { cevModuleCommonCards 100 }
cevNmAONS       OBJECT IDENTIFIER ::= { cevModuleCommonCards 101 }
cevHwic4fe      OBJECT IDENTIFIER ::= { cevModuleCommonCards 102 }
cevHwic9fes     OBJECT IDENTIFIER ::= { cevModuleCommonCards 103 }
cevHwic4fes     OBJECT IDENTIFIER ::= { cevModuleCommonCards 104 }
cevHwic4ilp     OBJECT IDENTIFIER ::= { cevModuleCommonCards 105 }
cevHwic9ilp     OBJECT IDENTIFIER ::= { cevModuleCommonCards 106 }
cevSpa10pGe     OBJECT IDENTIFIER ::= { cevModuleCommonCards 107 }
cevSpa1p10GeXfp OBJECT IDENTIFIER ::= { cevModuleCommonCards 108 }
cevSpa5pGe      OBJECT IDENTIFIER ::= { cevModuleCommonCards 109 }
cevSpa2pGe      OBJECT IDENTIFIER ::= { cevModuleCommonCards 115 }
cevCompactFlash64MB OBJECT IDENTIFIER ::= { cevModuleCommonCards 116 }
cevCompactFlash128MB OBJECT IDENTIFIER ::= { cevModuleCommonCards 117 }
cevCompactFlash256MB OBJECT IDENTIFIER ::= { cevModuleCommonCards 118 }
cevCompactFlash512MB OBJECT IDENTIFIER ::= { cevModuleCommonCards 119 }
cevCompactFlash OBJECT IDENTIFIER ::= { cevModuleCommonCards 120 }
cevSpa1pChOc3Stm1 OBJECT IDENTIFIER ::= { cevModuleCommonCards 121 }
cevFlashCard48MB OBJECT IDENTIFIER ::= { cevModuleCommonCards 122 }
cevFlashCard64MB OBJECT IDENTIFIER ::= { cevModuleCommonCards 123 }
cevFlashCard128MB OBJECT IDENTIFIER ::= { cevModuleCommonCards 124 }
cevFlashCard256MB OBJECT IDENTIFIER ::= { cevModuleCommonCards 125 }
cevFlashCard512MB OBJECT IDENTIFIER ::= { cevModuleCommonCards 126 }
cevFlashCard    OBJECT IDENTIFIER ::= { cevModuleCommonCards 127 }
cevHwicdot11abg OBJECT IDENTIFIER ::= { cevModuleCommonCards 128 }
cevHwicdot11bg  OBJECT IDENTIFIER ::= { cevModuleCommonCards 129 }
cevAimVpnBp     OBJECT IDENTIFIER ::= { cevModuleCommonCards 130 }
cevAimVpnEp     OBJECT IDENTIFIER ::= { cevModuleCommonCards 131 }
cevNmVpnMp      OBJECT IDENTIFIER ::= { cevModuleCommonCards 132 }
cevAimVpnHp     OBJECT IDENTIFIER ::= { cevModuleCommonCards 133 }
cevAimVpnBp2    OBJECT IDENTIFIER ::= { cevModuleCommonCards 134 }
cevAimVpnEp2    OBJECT IDENTIFIER ::= { cevModuleCommonCards 135 }
cevAimVpnHp2    OBJECT IDENTIFIER ::= { cevModuleCommonCards 136 }
cevAimVpnBp2Plus OBJECT IDENTIFIER ::= { cevModuleCommonCards 137 }
cevAimVpnEp2Plus OBJECT IDENTIFIER ::= { cevModuleCommonCards 138 }
cevAimVpnHp2Plus OBJECT IDENTIFIER ::= { cevModuleCommonCards 139 }
cevHwicAdslBriPots OBJECT IDENTIFIER ::= { cevModuleCommonCards 140 }
cevHwicAdslBriIsdn OBJECT IDENTIFIER ::= { cevModuleCommonCards 141 }
cevHwicAdslIsdn OBJECT IDENTIFIER ::= { cevModuleCommonCards 142 }
cevHwicAdslPots OBJECT IDENTIFIER ::= { cevModuleCommonCards 143 }
cevSpa2pOc48PosRprHH OBJECT IDENTIFIER ::= { cevModuleCommonCards 144 }
cevNMCueEc      OBJECT IDENTIFIER ::= { cevModuleCommonCards 146 }
cevC180xdot11abg OBJECT IDENTIFIER ::= { cevModuleCommonCards 147 }
cevC180xdot11bg OBJECT IDENTIFIER ::= { cevModuleCommonCards 148 }
cevC180x8ilp    OBJECT IDENTIFIER ::= { cevModuleCommonCards 149 }
cevDfcDl108     OBJECT IDENTIFIER ::= { cevModuleCommonCards 150 }
cevDfcDl60      OBJECT IDENTIFIER ::= { cevModuleCommonCards 151 }
cevNmWlanController OBJECT IDENTIFIER ::= { cevModuleCommonCards 152 }
cevWicCsuDsuFT1v2 OBJECT IDENTIFIER ::= { cevModuleCommonCards 153 }
cevSpa8xfeTx    OBJECT IDENTIFIER ::= { cevModuleCommonCards 154 }
cevNMIntegratedServiceEngine OBJECT IDENTIFIER ::= { cevModuleCommonCards 155 }
cevNmWaEngine   OBJECT IDENTIFIER ::= { cevModuleCommonCards 156 }
cevSpa2pGeV2    OBJECT IDENTIFIER ::= { cevModuleCommonCards 157 }
cevSpa5pGeV2    OBJECT IDENTIFIER ::= { cevModuleCommonCards 158 }
cevSpa8pGeV2    OBJECT IDENTIFIER ::= { cevModuleCommonCards 159 }
cevSpa10pGeV2   OBJECT IDENTIFIER ::= { cevModuleCommonCards 160 }
cevSpa1p10GeXfpV2 OBJECT IDENTIFIER ::= { cevModuleCommonCards 161 }
cevSpa8xfeTxV2  OBJECT IDENTIFIER ::= { cevModuleCommonCards 162 }
cevModuleCrs14OC192IRPlim OBJECT IDENTIFIER ::= { cevModuleCommonCards 163 }
cevSpa8xGe      OBJECT IDENTIFIER ::= { cevModuleCommonCards 164 }
cevSpa8xoc3Pos  OBJECT IDENTIFIER ::= { cevModuleCommonCards 166 }
cevSpa4xoc12Pos OBJECT IDENTIFIER ::= { cevModuleCommonCards 167 }
cevWic1ShdslV3  OBJECT IDENTIFIER ::= { cevModuleCommonCards 168 }
cevUsbFlash     OBJECT IDENTIFIER ::= { cevModuleCommonCards 169 }
cevUsbToken     OBJECT IDENTIFIER ::= { cevModuleCommonCards 170 }
cevUsbHub       OBJECT IDENTIFIER ::= { cevModuleCommonCards 171 }
cevVEncM        OBJECT IDENTIFIER ::= { cevModuleCommonCards 172 }
cevUsbDevice    OBJECT IDENTIFIER ::= { cevModuleCommonCards 173 }
cevSpa1pOc48PosSfp OBJECT IDENTIFIER ::= { cevModuleCommonCards 174 }
cevSpa4pOc48PosSfp OBJECT IDENTIFIER ::= { cevModuleCommonCards 175 }
cevIpRanOpt4P   OBJECT IDENTIFIER ::= { cevModuleCommonCards 176 }
cevAimIps1      OBJECT IDENTIFIER ::= { cevModuleCommonCards 177 }
cevAimIps2      OBJECT IDENTIFIER ::= { cevModuleCommonCards 178 }
cevNmCips       OBJECT IDENTIFIER ::= { cevModuleCommonCards 180 }
cevHwic1fe      OBJECT IDENTIFIER ::= { cevModuleCommonCards 181 }
cevHwic2fe      OBJECT IDENTIFIER ::= { cevModuleCommonCards 182 }
cevHwicBriU82912 OBJECT IDENTIFIER ::= { cevModuleCommonCards 183 }
cevHwicBri4bST  OBJECT IDENTIFIER ::= { cevModuleCommonCards 184 }
cevModuleCrs1RPB OBJECT IDENTIFIER ::= { cevModuleCommonCards 185 }
cevModuleCrs1FccSCGe OBJECT IDENTIFIER ::= { cevModuleCommonCards 186 }
cevModuleCrs1SPAInfCard OBJECT IDENTIFIER ::= { cevModuleCommonCards 187 }
cevModule4OC192DptIr OBJECT IDENTIFIER ::= { cevModuleCommonCards 188 }
cevModuleCrs116mFabricCard OBJECT IDENTIFIER ::= { cevModuleCommonCards 189 }
cevHwicAdslPotsAnnexM OBJECT IDENTIFIER ::= { cevModuleCommonCards 190 }
cevSpa4pOc3PosV2 OBJECT IDENTIFIER ::= { cevModuleCommonCards 191 }
cevCVRX2SFP     OBJECT IDENTIFIER ::= { cevModuleCommonCards 192 }
cevSpaIPSEC2g2  OBJECT IDENTIFIER ::= { cevModuleCommonCards 193 }
cevSpa8pCt1e1CemAtm OBJECT IDENTIFIER ::= { cevModuleCommonCards 194 }
cevSpa24pCt1e1CemAtm OBJECT IDENTIFIER ::= { cevModuleCommonCards 195 }
cevSpa2pCt3e3CemAtm OBJECT IDENTIFIER ::= { cevModuleCommonCards 196 }
cevSpa1pChoc3CemAtm OBJECT IDENTIFIER ::= { cevModuleCommonCards 197 }
cevSpa1x10geWlV2 OBJECT IDENTIFIER ::= { cevModuleCommonCards 198 }
cevSpa1x10geDwdmV2 OBJECT IDENTIFIER ::= { cevModuleCommonCards 199 }
cevSpa1pChoc48Ds3 OBJECT IDENTIFIER ::= { cevModuleCommonCards 200 }
cevSpa1pChoc12Ds0 OBJECT IDENTIFIER ::= { cevModuleCommonCards 201 }
cevAimAtm8      OBJECT IDENTIFIER ::= { cevModuleCommonCards 202 }
cevSpa4xtSerial OBJECT IDENTIFIER ::= { cevModuleCommonCards 203 }
cevSpa1xOC3AtmV2 OBJECT IDENTIFIER ::= { cevModuleCommonCards 204 }
cevSpa2xOC3AtmV2 OBJECT IDENTIFIER ::= { cevModuleCommonCards 205 }
cevSpa3xOC3AtmV2 OBJECT IDENTIFIER ::= { cevModuleCommonCards 206 }
cevSpa1xOC12AtmV2 OBJECT IDENTIFIER ::= { cevModuleCommonCards 207 }
cevNmTransOptSrvcEng1 OBJECT IDENTIFIER ::= { cevModuleCommonCards 208 }
cevAimTransOptSrvcEng1 OBJECT IDENTIFIER ::= { cevModuleCommonCards 209 }
cevNmTransOptSrvcEng2 OBJECT IDENTIFIER ::= { cevModuleCommonCards 210 }
cevAimTransOptSrvcEng2 OBJECT IDENTIFIER ::= { cevModuleCommonCards 211 }
cevOnboardSe    OBJECT IDENTIFIER ::= { cevModuleCommonCards 212 }
cevAimIpsK9     OBJECT IDENTIFIER ::= { cevModuleCommonCards 213 }
cevNmeApaModule OBJECT IDENTIFIER ::= { cevModuleCommonCards 214 }
cevHwicVdslPots OBJECT IDENTIFIER ::= { cevModuleCommonCards 215 }
cevHwicVdslIsdn OBJECT IDENTIFIER ::= { cevModuleCommonCards 216 }
cevWsIpsec3     OBJECT IDENTIFIER ::= { cevModuleCommonCards 217 }
cevHwic2as      OBJECT IDENTIFIER ::= { cevModuleCommonCards 218 }
cevHwic2t       OBJECT IDENTIFIER ::= { cevModuleCommonCards 219 }
cevHwic1t       OBJECT IDENTIFIER ::= { cevModuleCommonCards 220 }
cevHwic1dsuT1   OBJECT IDENTIFIER ::= { cevModuleCommonCards 221 }
cevDsx930418fk9 OBJECT IDENTIFIER ::= { cevModuleCommonCards 222 }
cevC7600SSC400  OBJECT IDENTIFIER ::= { cevModuleCommonCards 223 }
cevWSSSC600     OBJECT IDENTIFIER ::= { cevModuleCommonCards 224 }
cevSpa2pGeSynce OBJECT IDENTIFIER ::= { cevModuleCommonCards 225 }
cevSpa2pChoc12Ds0 OBJECT IDENTIFIER ::= { cevModuleCommonCards 226 }
cevAimVpnSsl1   OBJECT IDENTIFIER ::= { cevModuleCommonCards 227 }
cevAimVpnSsl2   OBJECT IDENTIFIER ::= { cevModuleCommonCards 228 }
cevAimVpnSsl3   OBJECT IDENTIFIER ::= { cevModuleCommonCards 229 }
cevWsIpsec2     OBJECT IDENTIFIER ::= { cevModuleCommonCards 230 }
cevCVRX2SFP10G  OBJECT IDENTIFIER ::= { cevModuleCommonCards 231 }
cevHardDisk     OBJECT IDENTIFIER ::= { cevModuleCommonCards 232 }
cevIsmSre300K9  OBJECT IDENTIFIER ::= { cevModuleCommonCards 234 }
cevSmSre700K9   OBJECT IDENTIFIER ::= { cevModuleCommonCards 237 }
cevSmSre900K9   OBJECT IDENTIFIER ::= { cevModuleCommonCards 239 }
cevSpaWmaSw     OBJECT IDENTIFIER ::= { cevModuleCommonCards 240 }
cevHwic4ShdslEfm OBJECT IDENTIFIER ::= { cevModuleCommonCards 242 }
cevAimAxp102    OBJECT IDENTIFIER ::= { cevModuleCommonCards 243 }
cevAim2Axp104   OBJECT IDENTIFIER ::= { cevModuleCommonCards 244 }
cevNmAxp302     OBJECT IDENTIFIER ::= { cevModuleCommonCards 245 }
cevNmAxp502     OBJECT IDENTIFIER ::= { cevModuleCommonCards 246 }
cevNmAxp522     OBJECT IDENTIFIER ::= { cevModuleCommonCards 247 }
cevWicGshdslEfm OBJECT IDENTIFIER ::= { cevModuleCommonCards 248 }
cevNmeIss       OBJECT IDENTIFIER ::= { cevModuleCommonCards 249 }
cevNmeVmss216   OBJECT IDENTIFIER ::= { cevModuleCommonCards 250 }
cevNmeVmssHp32  OBJECT IDENTIFIER ::= { cevModuleCommonCards 251 }
cevNmeVmss2Hp32 OBJECT IDENTIFIER ::= { cevModuleCommonCards 252 }
cevNmeVmssHp16  OBJECT IDENTIFIER ::= { cevModuleCommonCards 253 }
cevNmeVmss16    OBJECT IDENTIFIER ::= { cevModuleCommonCards 254 }
cevNamWaasVirtualBlade OBJECT IDENTIFIER ::= { cevModuleCommonCards 260 }
cevSpaDsp       OBJECT IDENTIFIER ::= { cevModuleCommonCards 273 }
cevModuleCrs4S140GFabricCard OBJECT IDENTIFIER ::= { cevModuleCommonCards 274 }
cevModuleCrs8S140GFabricCard OBJECT IDENTIFIER ::= { cevModuleCommonCards 275 }
cevModuleCrs16S140GFabricCard OBJECT IDENTIFIER ::= { cevModuleCommonCards 276 }
cevModuleCrs16S140GFabricCardMulti OBJECT IDENTIFIER ::= { cevModuleCommonCards 277 }
cevModuleCrs1140GFCCSFC OBJECT IDENTIFIER ::= { cevModuleCommonCards 278 }
cevC3KxNm1g     OBJECT IDENTIFIER ::= { cevModuleCommonCards 279 }
cevC3KxNm10g    OBJECT IDENTIFIER ::= { cevModuleCommonCards 280 }
cevHwic2tC      OBJECT IDENTIFIER ::= { cevModuleCommonCards 282 }
cevHwic1tC      OBJECT IDENTIFIER ::= { cevModuleCommonCards 283 }
cevHwic4fesC    OBJECT IDENTIFIER ::= { cevModuleCommonCards 284 }
cevHwic9fesC    OBJECT IDENTIFIER ::= { cevModuleCommonCards 285 }
cevVwic2Mft1G703C OBJECT IDENTIFIER ::= { cevModuleCommonCards 286 }
cevVwic2Mft2G703C OBJECT IDENTIFIER ::= { cevModuleCommonCards 287 }
cevNmEswitch16C OBJECT IDENTIFIER ::= { cevModuleCommonCards 288 }
cevC2960sStack  OBJECT IDENTIFIER ::= { cevModuleCommonCards 291 }
cevHardiskIdc   OBJECT IDENTIFIER ::= { cevModuleCommonCards 292 }
cevEhwic4esg    OBJECT IDENTIFIER ::= { cevModuleCommonCards 293 }
cevEhwicD8esg   OBJECT IDENTIFIER ::= { cevModuleCommonCards 294 }
cevEhwicD8esgP  OBJECT IDENTIFIER ::= { cevModuleCommonCards 295 }
cevEhwic4esgP   OBJECT IDENTIFIER ::= { cevModuleCommonCards 296 }
cevVmssSmSre700K9 OBJECT IDENTIFIER ::= { cevModuleCommonCards 297 }
cevVmssSmSre900K9 OBJECT IDENTIFIER ::= { cevModuleCommonCards 298 }
cevIssSmSre700K9 OBJECT IDENTIFIER ::= { cevModuleCommonCards 299 }
cevIssSmSre900K9 OBJECT IDENTIFIER ::= { cevModuleCommonCards 300 }
cevModem3gGsm504A OBJECT IDENTIFIER ::= { cevModuleCommonCards 301 }
cevModem3gGsm504G OBJECT IDENTIFIER ::= { cevModuleCommonCards 302 }
cevCvrCfp4sfp10g OBJECT IDENTIFIER ::= { cevModuleCommonCards 303 }
cevModem3gCdma5728V OBJECT IDENTIFIER ::= { cevModuleCommonCards 304 }
cevModem3gGsmMC8705 OBJECT IDENTIFIER ::= { cevModuleCommonCards 305 }
cevModem3gGsmMC8795 OBJECT IDENTIFIER ::= { cevModuleCommonCards 306 }
cevModem3gGsmMc8705A OBJECT IDENTIFIER ::= { cevModuleCommonCards 313 }
cevHardDisk8541 OBJECT IDENTIFIER ::= { cevModuleCommonCards 314 }
cevHardDisk7571 OBJECT IDENTIFIER ::= { cevModuleCommonCards 315 }
cevHardDisk7541 OBJECT IDENTIFIER ::= { cevModuleCommonCards 316 }
cevHardDisk694  OBJECT IDENTIFIER ::= { cevModuleCommonCards 317 }
cevHardDisk594  OBJECT IDENTIFIER ::= { cevModuleCommonCards 318 }
cevHardDisk294  OBJECT IDENTIFIER ::= { cevModuleCommonCards 319 }
cevModuleDIMM8541 OBJECT IDENTIFIER ::= { cevModuleCommonCards 320 }
cevModuleDIMM7541 OBJECT IDENTIFIER ::= { cevModuleCommonCards 321 }
cevModuleDIMM7571 OBJECT IDENTIFIER ::= { cevModuleCommonCards 322 }
cevModuleDIMM294 OBJECT IDENTIFIER ::= { cevModuleCommonCards 323 }
cevModuleDIMM694 OBJECT IDENTIFIER ::= { cevModuleCommonCards 324 }
cevModuleDIMM594 OBJECT IDENTIFIER ::= { cevModuleCommonCards 325 }
cevModuleIOM294 OBJECT IDENTIFIER ::= { cevModuleCommonCards 328 }
cevModuleIOM594 OBJECT IDENTIFIER ::= { cevModuleCommonCards 329 }
cevModuleIOM694 OBJECT IDENTIFIER ::= { cevModuleCommonCards 330 }
cevModuleIOM7541 OBJECT IDENTIFIER ::= { cevModuleCommonCards 331 }
cevModuleIOM7571 OBJECT IDENTIFIER ::= { cevModuleCommonCards 332 }
cevModuleIOM8541 OBJECT IDENTIFIER ::= { cevModuleCommonCards 333 }
cevIM8pGeCu     OBJECT IDENTIFIER ::= { cevModuleCommonCards 334 }
cevIM8pGeSFP    OBJECT IDENTIFIER ::= { cevModuleCommonCards 335 }
cevIM16pT1E1    OBJECT IDENTIFIER ::= { cevModuleCommonCards 336 }
cevIM1p10GeXfp  OBJECT IDENTIFIER ::= { cevModuleCommonCards 337 }
cevIM4pOc3R1pOc12 OBJECT IDENTIFIER ::= { cevModuleCommonCards 338 }
cevEp1p40GeQsfp OBJECT IDENTIFIER ::= { cevModuleCommonCards 343 }
cevEp2p40GeQsfp OBJECT IDENTIFIER ::= { cevModuleCommonCards 344 }
cevMpa2X10GE    OBJECT IDENTIFIER ::= { cevModuleCommonCards 350 }
cevMpa4X10GE    OBJECT IDENTIFIER ::= { cevModuleCommonCards 351 }
cevMpa20X1GE    OBJECT IDENTIFIER ::= { cevModuleCommonCards 352 }
cevMpa1X40GE    OBJECT IDENTIFIER ::= { cevModuleCommonCards 353 }
cevMpa2X40GE    OBJECT IDENTIFIER ::= { cevModuleCommonCards 354 }
cevModuleNic2x10GeSfp OBJECT IDENTIFIER ::= { cevModuleCommonCards 359 }
cevModuleNic4x10GeSfp OBJECT IDENTIFIER ::= { cevModuleCommonCards 360 }
cevModuleNic4x1GeSfp OBJECT IDENTIFIER ::= { cevModuleCommonCards 361 }
cevModule4portNic4x1GeCu OBJECT IDENTIFIER ::= { cevModuleCommonCards 362 }
cevModule1xNitrox3 OBJECT IDENTIFIER ::= { cevModuleCommonCards 363 }
cevModule4xNitrox3 OBJECT IDENTIFIER ::= { cevModuleCommonCards 364 }
cevSpaHDwbdSfp  OBJECT IDENTIFIER ::= { cevModuleCommonCards 365 }
cevSpa8pT3E3Serial OBJECT IDENTIFIER ::= { cevModuleCommonCards 366 }
cevSolidStateDisk8541 OBJECT IDENTIFIER ::= { cevModuleCommonCards 367 }
cevSolidStateDisk7541 OBJECT IDENTIFIER ::= { cevModuleCommonCards 368 }
cevSolidStateDisk7571 OBJECT IDENTIFIER ::= { cevModuleCommonCards 369 }
cevSolidStateDisk694 OBJECT IDENTIFIER ::= { cevModuleCommonCards 370 }
cevSolidStateDisk594 OBJECT IDENTIFIER ::= { cevModuleCommonCards 371 }
cevSolidStateDisk294 OBJECT IDENTIFIER ::= { cevModuleCommonCards 372 }
cevWaveInlnGe4T OBJECT IDENTIFIER ::= { cevModuleCommonCards 373 }
cevWaveInlnGe8T OBJECT IDENTIFIER ::= { cevModuleCommonCards 374 }
cevWaveInlnGe4SX OBJECT IDENTIFIER ::= { cevModuleCommonCards 375 }
cevWave10Ge2SFP OBJECT IDENTIFIER ::= { cevModuleCommonCards 376 }
cevIM32pT1E1    OBJECT IDENTIFIER ::= { cevModuleCommonCards 377 }
cevA9kMpa8X10GE OBJECT IDENTIFIER ::= { cevModuleCommonCards 378 }
cevA9KMpa8X10GE OBJECT IDENTIFIER ::= { cevModuleCommonCards 379 }
cevIom4GeInln   OBJECT IDENTIFIER ::= { cevModuleCommonCards 380 }
cevIom8GeInln   OBJECT IDENTIFIER ::= { cevModuleCommonCards 381 }
cevIom4GefInln  OBJECT IDENTIFIER ::= { cevModuleCommonCards 382 }
cevIom2X10Ge    OBJECT IDENTIFIER ::= { cevModuleCommonCards 383 }
cevSfpH10GbCu5M OBJECT IDENTIFIER ::= { cevModuleCommonCards 384 }
cevWaveScGe12T  OBJECT IDENTIFIER ::= { cevModuleCommonCards 385 }
cevWaveScGe12Sfp OBJECT IDENTIFIER ::= { cevModuleCommonCards 386 }
cevWaveSc10Ge4Sfp OBJECT IDENTIFIER ::= { cevModuleCommonCards 387 }
cevWaveApnvGe12T OBJECT IDENTIFIER ::= { cevModuleCommonCards 388 }
cevWaveApnvGe12Sfp OBJECT IDENTIFIER ::= { cevModuleCommonCards 389 }
cevWaveApnv10Ge4Sfp OBJECT IDENTIFIER ::= { cevModuleCommonCards 390 }
cevModuleNCSFCS OBJECT IDENTIFIER ::= { cevModuleCommonCards 403 }
cevModuleNCS10X100GMK OBJECT IDENTIFIER ::= { cevModuleCommonCards 404 }
cevModuleNCS10X100GMP OBJECT IDENTIFIER ::= { cevModuleCommonCards 405 }
cevModuleNCSRP  OBJECT IDENTIFIER ::= { cevModuleCommonCards 406 }
cevIM14pSerial  OBJECT IDENTIFIER ::= { cevModuleCommonCards 407 }
cevModuleNCSCRFT OBJECT IDENTIFIER ::= { cevModuleCommonCards 413 }
cevModuleCommonCardsPSEASIC OBJECT IDENTIFIER ::= { cevModuleCommonCards 414 }
cevModuleCommonCardsFIA OBJECT IDENTIFIER ::= { cevModuleCommonCards 415 }
cevModulePowerController OBJECT IDENTIFIER ::= { cevModuleCommonCards 418 }
cevModuleDIMM   OBJECT IDENTIFIER ::= { cevModuleCommonCards 419 }
cevModuleNCS10X100GLP OBJECT IDENTIFIER ::= { cevModuleCommonCards 420 }
cevModuleNCS10X100GLK OBJECT IDENTIFIER ::= { cevModuleCommonCards 421 }
cevModuleFPD    OBJECT IDENTIFIER ::= { cevModuleCommonCards 422 }
cevModuleI2CMUX OBJECT IDENTIFIER ::= { cevModuleCommonCards 423 }
cevModulePCIESwitch OBJECT IDENTIFIER ::= { cevModuleCommonCards 424 }
cevModuleStorage OBJECT IDENTIFIER ::= { cevModuleCommonCards 425 }
cevModuleControlSwitch OBJECT IDENTIFIER ::= { cevModuleCommonCards 426 }
cevModuleC3KxNm4x10g OBJECT IDENTIFIER ::= { cevModuleCommonCards 427 }
cevModuleNCS4K20TOS OBJECT IDENTIFIER ::= { cevModuleCommonCards 428 }
cevModuleNC6410X100GMK OBJECT IDENTIFIER ::= { cevModuleCommonCards 429 }
cevModuleNC6610X100GLK OBJECT IDENTIFIER ::= { cevModuleCommonCards 430 }
cevModuleNCS4KTSP OBJECT IDENTIFIER ::= { cevModuleCommonCards 431 }
cevModuleNCS4KFCM OBJECT IDENTIFIER ::= { cevModuleCommonCards 432 }
cevModuleNCS4KFCS OBJECT IDENTIFIER ::= { cevModuleCommonCards 433 }
cevModuleNCS4K2HW OBJECT IDENTIFIER ::= { cevModuleCommonCards 434 }
cevModuleNCS4K2HOK OBJECT IDENTIFIER ::= { cevModuleCommonCards 435 }
cevModuleNCS4K24LROS OBJECT IDENTIFIER ::= { cevModuleCommonCards 436 }
cevModuleFabIntAcessASIC OBJECT IDENTIFIER ::= { cevModuleCommonCards 437 }
cevModuleNCS4KChassisLCASIC OBJECT IDENTIFIER ::= { cevModuleCommonCards 438 }
cevModuleNCS4KFProgDEvice OBJECT IDENTIFIER ::= { cevModuleCommonCards 439 }
cevModuleNCS4KInterIC OBJECT IDENTIFIER ::= { cevModuleCommonCards 440 }
cevModuleNCS4KPCIESwitch OBJECT IDENTIFIER ::= { cevModuleCommonCards 441 }
cevModuleNCS4KDataStorage OBJECT IDENTIFIER ::= { cevModuleCommonCards 442 }
cevModuleNCS4KCtrlTrafficSwitch OBJECT IDENTIFIER ::= { cevModuleCommonCards 443 }
cevModuleNCS4KDIMMCPU OBJECT IDENTIFIER ::= { cevModuleCommonCards 444 }
cevModulePseAsicPlim OBJECT IDENTIFIER ::= { cevModuleCommonCards 445 }
cevModuleCisco60P10GeSFPPlusLsrLC OBJECT IDENTIFIER ::= { cevModuleCommonCards 446 }
cevModuleCisco30P10GeSFPPlusLsrLC OBJECT IDENTIFIER ::= { cevModuleCommonCards 447 }
cevModuleCisco15P10GeSFPPlusLsrLC OBJECT IDENTIFIER ::= { cevModuleCommonCards 448 }
cevModuleCisco15P10GeSFPPlusLC OBJECT IDENTIFIER ::= { cevModuleCommonCards 449 }
cevModuleCisco30P10GeSFPPlusLC OBJECT IDENTIFIER ::= { cevModuleCommonCards 450 }
cevModuleCisco60P10GeSFPPlusLC OBJECT IDENTIFIER ::= { cevModuleCommonCards 451 }
cevModuleVirtualBlade OBJECT IDENTIFIER ::= { cevModuleCommonCards 452 }
cevModuleASA55125515ASAIC6GECUA OBJECT IDENTIFIER ::= { cevModuleCommonCards 453 }
cevModuleASA5525ASAIC6GECUB OBJECT IDENTIFIER ::= { cevModuleCommonCards 454 }
cevModuleASA55455555ASAIC6GECUC OBJECT IDENTIFIER ::= { cevModuleCommonCards 455 }
cevModuleASA55125515ASAIC6GESFPA OBJECT IDENTIFIER ::= { cevModuleCommonCards 456 }
cevModuleASA5525ASAIC6GESFPB OBJECT IDENTIFIER ::= { cevModuleCommonCards 457 }
cevModuleASA55455555ASAIC6GESFPC OBJECT IDENTIFIER ::= { cevModuleCommonCards 458 }
cevModuleNCS4KDCPWF OBJECT IDENTIFIER ::= { cevModuleCommonCards 459 }
cevModuleNCS4KECU OBJECT IDENTIFIER ::= { cevModuleCommonCards 460 }
cevPEhwic4Esg   OBJECT IDENTIFIER ::= { cevModuleCommonCards 470 }
cevPEhwicD8Esg  OBJECT IDENTIFIER ::= { cevModuleCommonCards 471 }
cevPWic1BStV3   OBJECT IDENTIFIER ::= { cevModuleCommonCards 472 }
cevPhwic1Adsl   OBJECT IDENTIFIER ::= { cevModuleCommonCards 473 }
cevPhwic1Adslm  OBJECT IDENTIFIER ::= { cevModuleCommonCards 474 }
cevPHwic1Dsut1  OBJECT IDENTIFIER ::= { cevModuleCommonCards 475 }
cevPHwic1t      OBJECT IDENTIFIER ::= { cevModuleCommonCards 476 }
cevPHwic2as     OBJECT IDENTIFIER ::= { cevModuleCommonCards 477 }
cevPHwic2Fe     OBJECT IDENTIFIER ::= { cevModuleCommonCards 478 }
cevPHwic2t      OBJECT IDENTIFIER ::= { cevModuleCommonCards 479 }
cevPIsmSre300K9 OBJECT IDENTIFIER ::= { cevModuleCommonCards 480 }
cevSpa14pSaSerial OBJECT IDENTIFIER ::= { cevModuleCommonCards 481 }
cevModuleCrs1FccSc22GeB OBJECT IDENTIFIER ::= { cevModuleCommonCards 483 }
cevPEhwicVaMMDslA OBJECT IDENTIFIER ::= { cevModuleCommonCards 484 }
cevPEhwicVaMMDslM OBJECT IDENTIFIER ::= { cevModuleCommonCards 485 }
cevSPA1XOC12PS  OBJECT IDENTIFIER ::= { cevModuleCommonCards 486 }
cevModuleNCSFSCSW OBJECT IDENTIFIER ::= { cevModuleCommonCards 487 }
cevModuleNCSFSC OBJECT IDENTIFIER ::= { cevModuleCommonCards 488 }
cevModuleNCSFFC OBJECT IDENTIFIER ::= { cevModuleCommonCards 489 }
cevModuleNC6FCMC OBJECT IDENTIFIER ::= { cevModuleCommonCards 490 }
cevModuleA900IMA8S1Z OBJECT IDENTIFIER ::= { cevModuleCommonCards 491 }
cevModuleA900IMA8T1Z OBJECT IDENTIFIER ::= { cevModuleCommonCards 492 }
cevModuleA900IMA2Z OBJECT IDENTIFIER ::= { cevModuleCommonCards 493 }
cevModuleNCS4009FCS OBJECT IDENTIFIER ::= { cevModuleCommonCards 494 }
cevModuleNCS4KEthContMod OBJECT IDENTIFIER ::= { cevModuleCommonCards 495 }
cevModuleNCS4KProcContHub OBJECT IDENTIFIER ::= { cevModuleCommonCards 496 }
cevModuleNCS4KCPU OBJECT IDENTIFIER ::= { cevModuleCommonCards 497 }
cevModuleNCS4KDaughterboard OBJECT IDENTIFIER ::= { cevModuleCommonCards 498 }
cevModuleNCS4KMotherboard OBJECT IDENTIFIER ::= { cevModuleCommonCards 499 }
cevModuleNCS4KASIC OBJECT IDENTIFIER ::= { cevModuleCommonCards 500 }
cevModuleNCS4KGENNUM OBJECT IDENTIFIER ::= { cevModuleCommonCards 501 }
cevModuleNCS4KEAGLE OBJECT IDENTIFIER ::= { cevModuleCommonCards 502 }
cevModuleNCS4KGEARBOX OBJECT IDENTIFIER ::= { cevModuleCommonCards 503 }
cevModuleNCS4KCRFT OBJECT IDENTIFIER ::= { cevModuleCommonCards 504 }
cevModuleNCSFCB2B OBJECT IDENTIFIER ::= { cevModuleCommonCards 505 }
cevModuleNCSSfpPlusOpticsMod OBJECT IDENTIFIER ::= { cevModuleCommonCards 506 }
cevModuleNCS6KSRTCAM OBJECT IDENTIFIER ::= { cevModuleCommonCards 507 }
cevModuleNCS6K210X100GMK OBJECT IDENTIFIER ::= { cevModuleCommonCards 508 }
cevModuleNCS6K210X100GLK OBJECT IDENTIFIER ::= { cevModuleCommonCards 509 }
cevModuleNCS6K230X10GMS OBJECT IDENTIFIER ::= { cevModuleCommonCards 510 }
cevModuleNCS6K230X10GLS OBJECT IDENTIFIER ::= { cevModuleCommonCards 511 }
cevModuleSPAETHER24xGE4x10GECU OBJECT IDENTIFIER ::= { cevModuleCommonCards 512 }
cevModuleSPAETHER24xGE4x10GESFP OBJECT IDENTIFIER ::= { cevModuleCommonCards 513 }
cevModuleSPAETHER24xGE4x10GE OBJECT IDENTIFIER ::= { cevModuleCommonCards 514 }
cevModuleSPAETHER12xGE2x10GEDUAL OBJECT IDENTIFIER ::= { cevModuleCommonCards 515 }
cevModuleSPAETHER2xGE4x10GEDUAL OBJECT IDENTIFIER ::= { cevModuleCommonCards 516 }
cevModuleSPAETHER10xGE2x10GEDUAL OBJECT IDENTIFIER ::= { cevModuleCommonCards 517 }
cevModuleA900IMA32D OBJECT IDENTIFIER ::= { cevModuleCommonCards 518 }
cevModuleA900IMA8D OBJECT IDENTIFIER ::= { cevModuleCommonCards 519 }
cevModuleC3KxNm8x10g OBJECT IDENTIFIER ::= { cevModuleCommonCards 521 }
cevModuleC3KxNm2x40g OBJECT IDENTIFIER ::= { cevModuleCommonCards 522 }
cevCVRCFP2CPAK10 OBJECT IDENTIFIER ::= { cevModuleCommonCards 530 }
cevCVRCFP2CPAK4 OBJECT IDENTIFIER ::= { cevModuleCommonCards 531 }
cevCVR4SFP10GQSFP OBJECT IDENTIFIER ::= { cevModuleCommonCards 532 }
cevModuleNC55RP OBJECT IDENTIFIER ::= { cevModuleCommonCards 533 }
cevModuleNC55SC OBJECT IDENTIFIER ::= { cevModuleCommonCards 534 }
cevModuleNC55LC36X100G OBJECT IDENTIFIER ::= { cevModuleCommonCards 535 }
cevModuleNC55FC OBJECT IDENTIFIER ::= { cevModuleCommonCards 536 }
cevModuleNCS4K2HOPWC2 OBJECT IDENTIFIER ::= { cevModuleCommonCards 537 }
cevMpa20X10GE   OBJECT IDENTIFIER ::= { cevModuleCommonCards 545 }
cevModuleNC6FCU OBJECT IDENTIFIER ::= { cevModuleCommonCards 546 }
cevModuleNcs5000RP OBJECT IDENTIFIER ::= { cevModuleCommonCards 547 }
cevModuleNcs4016FC2M OBJECT IDENTIFIER ::= { cevModuleCommonCards 548 }
cevModuleNcs4K4HOPK OBJECT IDENTIFIER ::= { cevModuleCommonCards 549 }
cevModuleNC620x100GEMC OBJECT IDENTIFIER ::= { cevModuleCommonCards 550 }
cevModuleNC6FanTray2 OBJECT IDENTIFIER ::= { cevModuleCommonCards 551 }
cevModuleCVRCPAKQSFP40 OBJECT IDENTIFIER ::= { cevModuleCommonCards 552 }
cevModuleNCS4009FC2S OBJECT IDENTIFIER ::= { cevModuleCommonCards 553 }
cevModuleNCS5001ACCKIT OBJECT IDENTIFIER ::= { cevModuleCommonCards 554 }
cevModuleNCS5002ACCKIT OBJECT IDENTIFIER ::= { cevModuleCommonCards 555 }
cevModuleNCS5002FLTBK OBJECT IDENTIFIER ::= { cevModuleCommonCards 556 }
cevModuleNCS5002FLTFR OBJECT IDENTIFIER ::= { cevModuleCommonCards 557 }
cevModuleNC55LC24X100SE OBJECT IDENTIFIER ::= { cevModuleCommonCards 558 }
cevModuleNC55LC36X100GS OBJECT IDENTIFIER ::= { cevModuleCommonCards 559 }
cevModuleNC55LC18H18F OBJECT IDENTIFIER ::= { cevModuleCommonCards 560 }
cevModuleTCAM   OBJECT IDENTIFIER ::= { cevModuleCommonCards 562 }
cevModuleOBFL   OBJECT IDENTIFIER ::= { cevModuleCommonCards 563 }
cevMpa2X100GE   OBJECT IDENTIFIER ::= { cevModuleCommonCards 568 }
cevMpa1X100GE   OBJECT IDENTIFIER ::= { cevModuleCommonCards 569 }
cevModuleNCS42001HPK OBJECT IDENTIFIER ::= { cevModuleCommonCards 590 }
cevModuleNCS42001T8LRPS OBJECT IDENTIFIER ::= { cevModuleCommonCards 591 }
cevModuleNCS42001T16GPS OBJECT IDENTIFIER ::= { cevModuleCommonCards 592 }
cevModuleNCS42008E1T1CE OBJECT IDENTIFIER ::= { cevModuleCommonCards 593 }
cevModuleNCS42001T8S20CS OBJECT IDENTIFIER ::= { cevModuleCommonCards 594 }
cevModuleNCS420048T1E1CE OBJECT IDENTIFIER ::= { cevModuleCommonCards 595 }
cevModuleNCS420048T3E3CE OBJECT IDENTIFIER ::= { cevModuleCommonCards 596 }
cevModuleNCS42001T8S10CS OBJECT IDENTIFIER ::= { cevModuleCommonCards 597 }
cevModuleNCS42008TPS OBJECT IDENTIFIER ::= { cevModuleCommonCards 598 }
cevModuleNCS42002QP OBJECT IDENTIFIER ::= { cevModuleCommonCards 599 }
cevModuleNCS42001T8S10MS OBJECT IDENTIFIER ::= { cevModuleCommonCards 600 }
cevModuleA900IMA48DC OBJECT IDENTIFIER ::= { cevModuleCommonCards 601 }
cevModuleA900IMA48TC OBJECT IDENTIFIER ::= { cevModuleCommonCards 602 }
cevModuleNC55LC18X100GS OBJECT IDENTIFIER ::= { cevModuleCommonCards 603 }
cevModuleNCS42004T12GPS OBJECT IDENTIFIER ::= { cevModuleCommonCards 605 }
cevModuleA900IMA1Z8SC OBJECT IDENTIFIER ::= { cevModuleCommonCards 607 }
cevModuleSPAETHER12XGE4X10GE OBJECT IDENTIFIER ::= { cevModuleCommonCards 608 }
cevMpa20X10GECM OBJECT IDENTIFIER ::= { cevModuleCommonCards 609 }
cevMpa2X100GECM OBJECT IDENTIFIER ::= { cevModuleCommonCards 610 }
cevModuleFprUS23070 OBJECT IDENTIFIER ::= { cevModuleCommonCards 612 }
cevModuleFprUS23071 OBJECT IDENTIFIER ::= { cevModuleCommonCards 613 }
cevCVRQSFPSFP10G OBJECT IDENTIFIER ::= { cevModuleCommonCards 624 }
cevModuleC36xxType OBJECT IDENTIFIER ::= { cevModule 3 }
cevPmCpm1e2w    OBJECT IDENTIFIER ::= { cevModuleC36xxType 1 }
cevPmCpm2e2w    OBJECT IDENTIFIER ::= { cevModuleC36xxType 2 }
cevPmCpm1e1r2w  OBJECT IDENTIFIER ::= { cevModuleC36xxType 3 }
cevPmCt1Csu     OBJECT IDENTIFIER ::= { cevModuleC36xxType 4 }
cevPm2ct1Csu    OBJECT IDENTIFIER ::= { cevModuleC36xxType 5 }
cevPmCt1Dsx1    OBJECT IDENTIFIER ::= { cevModuleC36xxType 6 }
cevPm2ct1Dsx1   OBJECT IDENTIFIER ::= { cevModuleC36xxType 7 }
cevPmCe1Balanced OBJECT IDENTIFIER ::= { cevModuleC36xxType 8 }
cevPm2ce1Balanced OBJECT IDENTIFIER ::= { cevModuleC36xxType 9 }
cevPmCe1Unbalanced OBJECT IDENTIFIER ::= { cevModuleC36xxType 10 }
cevPm2ce1Unbalanced OBJECT IDENTIFIER ::= { cevModuleC36xxType 11 }
cevPm4bU        OBJECT IDENTIFIER ::= { cevModuleC36xxType 12 }
cevPm4bSt       OBJECT IDENTIFIER ::= { cevModuleC36xxType 13 }
cevPm8bU        OBJECT IDENTIFIER ::= { cevModuleC36xxType 14 }
cevPm8bSt       OBJECT IDENTIFIER ::= { cevModuleC36xxType 15 }
cevPm4as        OBJECT IDENTIFIER ::= { cevModuleC36xxType 16 }
cevPm8as        OBJECT IDENTIFIER ::= { cevModuleC36xxType 17 }
cevPm4e         OBJECT IDENTIFIER ::= { cevModuleC36xxType 18 }
cevPm1e         OBJECT IDENTIFIER ::= { cevModuleC36xxType 19 }
cevPmM4t        OBJECT IDENTIFIER ::= { cevModuleC36xxType 21 }
cevPm16a        OBJECT IDENTIFIER ::= { cevModuleC36xxType 22 }
cevPm32a        OBJECT IDENTIFIER ::= { cevModuleC36xxType 23 }
cevPmC36001fe   OBJECT IDENTIFIER ::= { cevModuleC36xxType 24 }
cevPmC3600Compression OBJECT IDENTIFIER ::= { cevModuleC36xxType 25 }
cevPmDmodem     OBJECT IDENTIFIER ::= { cevModuleC36xxType 26 }
cevPm8admodem   OBJECT IDENTIFIER ::= { cevModuleC36xxType 27 }
cevPm16admodem  OBJECT IDENTIFIER ::= { cevModuleC36xxType 28 }
cevVpm2v        OBJECT IDENTIFIER ::= { cevModuleC36xxType 29 }
cevVpm4v        OBJECT IDENTIFIER ::= { cevModuleC36xxType 30 }
cevPmC36001feTx OBJECT IDENTIFIER ::= { cevModuleC36xxType 31 }
cevPmC36001feFx OBJECT IDENTIFIER ::= { cevModuleC36xxType 32 }
cevPm1fe1t1     OBJECT IDENTIFIER ::= { cevModuleC36xxType 33 }
cevPm1fe2t1     OBJECT IDENTIFIER ::= { cevModuleC36xxType 34 }
cevPm1fe1e1     OBJECT IDENTIFIER ::= { cevModuleC36xxType 35 }
cevPm1fe2e1     OBJECT IDENTIFIER ::= { cevModuleC36xxType 36 }
cevPm1fe1t1Csu  OBJECT IDENTIFIER ::= { cevModuleC36xxType 37 }
cevPm1fe2t1Csu  OBJECT IDENTIFIER ::= { cevModuleC36xxType 38 }
cevC36xx2feTx   OBJECT IDENTIFIER ::= { cevModuleC36xxType 39 }
cevPmOc3mm      OBJECT IDENTIFIER ::= { cevModuleC36xxType 40 }
cevPmOc3mmVpd   OBJECT IDENTIFIER ::= { cevModuleC36xxType 41 }
cevPmOc3smiVpd  OBJECT IDENTIFIER ::= { cevModuleC36xxType 42 }
cevPmOc3smlVpd  OBJECT IDENTIFIER ::= { cevModuleC36xxType 43 }
cevPmOc3sml     OBJECT IDENTIFIER ::= { cevModuleC36xxType 44 }
cevPmOc3smi     OBJECT IDENTIFIER ::= { cevModuleC36xxType 45 }
cevVic2fxoEu    OBJECT IDENTIFIER ::= { cevModuleC36xxType 46 }
cevVic2fxoM3    OBJECT IDENTIFIER ::= { cevModuleC36xxType 47 }
cevVic2fxoM4    OBJECT IDENTIFIER ::= { cevModuleC36xxType 48 }
cevVic2fxoM5    OBJECT IDENTIFIER ::= { cevModuleC36xxType 49 }
cevVic2fxoM6    OBJECT IDENTIFIER ::= { cevModuleC36xxType 50 }
cevVic2fxoM7    OBJECT IDENTIFIER ::= { cevModuleC36xxType 51 }
cevVic2fxoM8    OBJECT IDENTIFIER ::= { cevModuleC36xxType 52 }
cevVic2ST2086   OBJECT IDENTIFIER ::= { cevModuleC36xxType 53 }
cevHdv          OBJECT IDENTIFIER ::= { cevModuleC36xxType 54 }
cevNm1fe2w      OBJECT IDENTIFIER ::= { cevModuleC36xxType 59 }
cevNm2fe2w      OBJECT IDENTIFIER ::= { cevModuleC36xxType 60 }
cevNm1fe1r2w    OBJECT IDENTIFIER ::= { cevModuleC36xxType 61 }
cevNm2w         OBJECT IDENTIFIER ::= { cevModuleC36xxType 62 }
cevC36xx1feTx   OBJECT IDENTIFIER ::= { cevModuleC36xxType 63 }
cevAimLc4e1Compression OBJECT IDENTIFIER ::= { cevModuleC36xxType 64 }
cevVic2fxoM1    OBJECT IDENTIFIER ::= { cevModuleC36xxType 65 }
cevVic2fxoM2    OBJECT IDENTIFIER ::= { cevModuleC36xxType 68 }
cevPmDs3        OBJECT IDENTIFIER ::= { cevModuleC36xxType 69 }
cevPmE3         OBJECT IDENTIFIER ::= { cevModuleC36xxType 70 }
cevVic2vpFxsDid OBJECT IDENTIFIER ::= { cevModuleC36xxType 74 }
cevVic2ST2086NtTe OBJECT IDENTIFIER ::= { cevModuleC36xxType 75 }
cevNmAic64      OBJECT IDENTIFIER ::= { cevModuleC36xxType 76 }
cevMIX366064    OBJECT IDENTIFIER ::= { cevModuleC36xxType 77 }
cevWicAsync1am  OBJECT IDENTIFIER ::= { cevModuleC36xxType 78 }
cevWicAsync2am  OBJECT IDENTIFIER ::= { cevModuleC36xxType 79 }
cevAim4Dsps     OBJECT IDENTIFIER ::= { cevModuleC36xxType 81 }
cevHdaNm4fxs    OBJECT IDENTIFIER ::= { cevModuleC36xxType 82 }
cevC2610M       OBJECT IDENTIFIER ::= { cevModuleC36xxType 84 }
cevC2611M       OBJECT IDENTIFIER ::= { cevModuleC36xxType 85 }
cevNm1t3e3      OBJECT IDENTIFIER ::= { cevModuleC36xxType 91 }
cevNm1ct3e3     OBJECT IDENTIFIER ::= { cevModuleC36xxType 92 }
cevNm8ct1e1     OBJECT IDENTIFIER ::= { cevModuleC36xxType 93 }
cevHdaEm4fxo    OBJECT IDENTIFIER ::= { cevModuleC36xxType 94 }
cevNm16AS       OBJECT IDENTIFIER ::= { cevModuleC36xxType 95 }
cevNm1ct1e1Pri  OBJECT IDENTIFIER ::= { cevModuleC36xxType 102 }
cevNm2ct1e1Pri  OBJECT IDENTIFIER ::= { cevModuleC36xxType 103 }
cevNmCeoip4t1e1 OBJECT IDENTIFIER ::= { cevModuleC36xxType 104 }
cevNmCeoip4Serial OBJECT IDENTIFIER ::= { cevModuleC36xxType 105 }
cevNm1aOc3mmEp  OBJECT IDENTIFIER ::= { cevModuleC36xxType 106 }
cevNm1aOc3smiEp OBJECT IDENTIFIER ::= { cevModuleC36xxType 107 }
cevNm1aOc3smlEp OBJECT IDENTIFIER ::= { cevModuleC36xxType 108 }
cevNmCids       OBJECT IDENTIFIER ::= { cevModuleC36xxType 109 }
cevHwic1GeSfp   OBJECT IDENTIFIER ::= { cevModuleC36xxType 119 }
cevPortHdDsp    OBJECT IDENTIFIER ::= { cevModuleC36xxType 120 }
cevHdv2port0    OBJECT IDENTIFIER ::= { cevModuleC36xxType 121 }
cevHdv2port2    OBJECT IDENTIFIER ::= { cevModuleC36xxType 122 }
cevHdv2port1    OBJECT IDENTIFIER ::= { cevModuleC36xxType 123 }
cevNmAtm25      OBJECT IDENTIFIER ::= { cevModuleC36xxType 124 }
cevNmNam        OBJECT IDENTIFIER ::= { cevModuleC36xxType 125 }
cevNm8amV2      OBJECT IDENTIFIER ::= { cevModuleC36xxType 126 }
cevNm16amV2     OBJECT IDENTIFIER ::= { cevModuleC36xxType 127 }
cevCpuC28112fe  OBJECT IDENTIFIER ::= { cevModuleC36xxType 129 }
cevCpuC28212ge  OBJECT IDENTIFIER ::= { cevModuleC36xxType 130 }
cevCpuC28512ge  OBJECT IDENTIFIER ::= { cevModuleC36xxType 131 }
cevHWicSerial4t OBJECT IDENTIFIER ::= { cevModuleC36xxType 132 }
cevHWicSerial4as OBJECT IDENTIFIER ::= { cevModuleC36xxType 133 }
cevHWicSerial8as OBJECT IDENTIFIER ::= { cevModuleC36xxType 134 }
cevHWicSerial8a OBJECT IDENTIFIER ::= { cevModuleC36xxType 135 }
cevHWicSerial16a OBJECT IDENTIFIER ::= { cevModuleC36xxType 136 }
cevNm1AOc3Pom   OBJECT IDENTIFIER ::= { cevModuleC36xxType 137 }
cevHWic1DOCSIS20CableModem OBJECT IDENTIFIER ::= { cevModuleC36xxType 146 }
cevNm8ce1t1Pri  OBJECT IDENTIFIER ::= { cevModuleC36xxType 148 }
cevHWic4t1e1    OBJECT IDENTIFIER ::= { cevModuleC36xxType 149 }
cevHWic2ce1t1Pri OBJECT IDENTIFIER ::= { cevModuleC36xxType 150 }
cevHWic1ce1t1Pri OBJECT IDENTIFIER ::= { cevModuleC36xxType 151 }
cevHWic1DOCSIS20CableModemEJ OBJECT IDENTIFIER ::= { cevModuleC36xxType 152 }
cevHwic1t1e1    OBJECT IDENTIFIER ::= { cevModuleC36xxType 154 }
cevHwic4Shdsl   OBJECT IDENTIFIER ::= { cevModuleC36xxType 157 }
cevHwic2Shdsl   OBJECT IDENTIFIER ::= { cevModuleC36xxType 158 }
cevNmRvpnSterra OBJECT IDENTIFIER ::= { cevModuleC36xxType 159 }
cevNmRvpn       OBJECT IDENTIFIER ::= { cevModuleC36xxType 160 }
cevNmSpclSrvcEng OBJECT IDENTIFIER ::= { cevModuleC36xxType 161 }
cevNmIntgrtdSrvcEng2 OBJECT IDENTIFIER ::= { cevModuleC36xxType 162 }
cevHWIC1Ser     OBJECT IDENTIFIER ::= { cevModuleC36xxType 163 }
cevHWIC2Ser     OBJECT IDENTIFIER ::= { cevModuleC36xxType 164 }
cevInternalServiceModuleAIM OBJECT IDENTIFIER ::= { cevModuleC36xxType 165 }
cevSm1nm        OBJECT IDENTIFIER ::= { cevModuleC36xxType 167 }
cevSm2k15Es1GePoe OBJECT IDENTIFIER ::= { cevModuleC36xxType 168 }
cevSm3k15Es1GePoe OBJECT IDENTIFIER ::= { cevModuleC36xxType 169 }
cevSm3k16GePoe  OBJECT IDENTIFIER ::= { cevModuleC36xxType 170 }
cevSm2k23Es1Ge  OBJECT IDENTIFIER ::= { cevModuleC36xxType 171 }
cevSm2k23Es1GePoe OBJECT IDENTIFIER ::= { cevModuleC36xxType 172 }
cevSm3k23Es1GePoe OBJECT IDENTIFIER ::= { cevModuleC36xxType 173 }
cevSm3k24GePoe  OBJECT IDENTIFIER ::= { cevModuleC36xxType 174 }
cevSmXd2k48Es2SFP OBJECT IDENTIFIER ::= { cevModuleC36xxType 175 }
cevSmXd3k48Es2SFPPoe OBJECT IDENTIFIER ::= { cevModuleC36xxType 176 }
cevSmXd3k48Ge2SFPPoe OBJECT IDENTIFIER ::= { cevModuleC36xxType 177 }
cevHwic4ce1t1Pri OBJECT IDENTIFIER ::= { cevModuleC36xxType 180 }
cevEHwic1GeSfpCu OBJECT IDENTIFIER ::= { cevModuleC36xxType 181 }
cevEhwic3gEvdo  OBJECT IDENTIFIER ::= { cevModuleC36xxType 182 }
cevEhwic3gHspaU OBJECT IDENTIFIER ::= { cevModuleC36xxType 183 }
cevSm1pa        OBJECT IDENTIFIER ::= { cevModuleC36xxType 184 }
cevSm1Stm1Smi   OBJECT IDENTIFIER ::= { cevModuleC36xxType 185 }
cevSm1Stm1Mm    OBJECT IDENTIFIER ::= { cevModuleC36xxType 186 }
cevEhwic3gHspa7 OBJECT IDENTIFIER ::= { cevModuleC36xxType 187 }
cevIsmVpnSsl3   OBJECT IDENTIFIER ::= { cevModuleC36xxType 188 }
cevIsmVpnSsl2   OBJECT IDENTIFIER ::= { cevModuleC36xxType 189 }
cevIsmVpnSsl1   OBJECT IDENTIFIER ::= { cevModuleC36xxType 190 }
cevEhwic3gHspa7A OBJECT IDENTIFIER ::= { cevModuleC36xxType 191 }
cevEhwic3gMm    OBJECT IDENTIFIER ::= { cevModuleC36xxType 192 }
cevEhwic4gLteA  OBJECT IDENTIFIER ::= { cevModuleC36xxType 193 }
cevEhwic4gLteG  OBJECT IDENTIFIER ::= { cevModuleC36xxType 194 }
cevEhwic4gLteV  OBJECT IDENTIFIER ::= { cevModuleC36xxType 195 }
cevSm1T3E3      OBJECT IDENTIFIER ::= { cevModuleC36xxType 196 }
cevSM32A        OBJECT IDENTIFIER ::= { cevModuleC36xxType 197 }
cevSmD48FxsE    OBJECT IDENTIFIER ::= { cevModuleC36xxType 202 }
cevSmD72Fxs     OBJECT IDENTIFIER ::= { cevModuleC36xxType 203 }
cevNgsmXd3k48ge2sfpPoeplus OBJECT IDENTIFIER ::= { cevModuleC36xxType 206 }
cevNgsm3k24gePoeplus OBJECT IDENTIFIER ::= { cevModuleC36xxType 207 }
cevNgsm3k16gePoeplus OBJECT IDENTIFIER ::= { cevModuleC36xxType 208 }
cevGrwicSerial4t OBJECT IDENTIFIER ::= { cevModuleC36xxType 209 }
cevEhwic4gLteJp OBJECT IDENTIFIER ::= { cevModuleC36xxType 210 }
cevEhwic4gLteBe OBJECT IDENTIFIER ::= { cevModuleC36xxType 211 }
cevPEhwic1GeSfpCu OBJECT IDENTIFIER ::= { cevModuleC36xxType 212 }
cevPEhwic3gHspa7 OBJECT IDENTIFIER ::= { cevModuleC36xxType 213 }
cevPHwicSerial16a OBJECT IDENTIFIER ::= { cevModuleC36xxType 214 }
cevPhwic1Ce1T1Pri OBJECT IDENTIFIER ::= { cevModuleC36xxType 215 }
cevPHwic2Ce1t1Pri OBJECT IDENTIFIER ::= { cevModuleC36xxType 216 }
cevPHwicSerial4As OBJECT IDENTIFIER ::= { cevModuleC36xxType 217 }
cevPHwicSerial4t OBJECT IDENTIFIER ::= { cevModuleC36xxType 218 }
cevPHwic4T1E1   OBJECT IDENTIFIER ::= { cevModuleC36xxType 219 }
cevPHwicSerial8a OBJECT IDENTIFIER ::= { cevModuleC36xxType 220 }
cevPHwicSerial8as OBJECT IDENTIFIER ::= { cevModuleC36xxType 221 }
cevPIsmVpn29    OBJECT IDENTIFIER ::= { cevModuleC36xxType 222 }
cevPVic2Fxo2    OBJECT IDENTIFIER ::= { cevModuleC36xxType 223 }
cevPVic2Fxo4    OBJECT IDENTIFIER ::= { cevModuleC36xxType 224 }
cevPSm2k23Es1Ge OBJECT IDENTIFIER ::= { cevModuleC36xxType 225 }
cevPSm3k16GePoe OBJECT IDENTIFIER ::= { cevModuleC36xxType 226 }
cevPSmXd2k48Es2SFP OBJECT IDENTIFIER ::= { cevModuleC36xxType 227 }
cevPSmXd3k48Es2SFPPoe OBJECT IDENTIFIER ::= { cevModuleC36xxType 228 }
cevPSmXd3k48Ge2SFPPoe OBJECT IDENTIFIER ::= { cevModuleC36xxType 229 }
cevPSm2k15Es1GePoe OBJECT IDENTIFIER ::= { cevModuleC36xxType 230 }
cevPSm2k23Es1GePoe OBJECT IDENTIFIER ::= { cevModuleC36xxType 231 }
cevPSm3k15Es1GePoe OBJECT IDENTIFIER ::= { cevModuleC36xxType 232 }
cevPSm3k23Es1GePoe OBJECT IDENTIFIER ::= { cevModuleC36xxType 233 }
cevPSm3k24GePoe OBJECT IDENTIFIER ::= { cevModuleC36xxType 234 }
cevPSm1nm       OBJECT IDENTIFIER ::= { cevModuleC36xxType 235 }
cevPHdv2port2   OBJECT IDENTIFIER ::= { cevModuleC36xxType 236 }
cevEhwic4gLteLA OBJECT IDENTIFIER ::= { cevModuleC36xxType 246 }
cevEhwic4gLteCI OBJECT IDENTIFIER ::= { cevModuleC36xxType 247 }
cevEhwic4gLteJN OBJECT IDENTIFIER ::= { cevModuleC36xxType 248 }
cevModuleVipPortAdapters OBJECT IDENTIFIER ::= { cevModule 4 }
cevPa1fe        OBJECT IDENTIFIER ::= { cevModuleVipPortAdapters 1 }
cevPa8e         OBJECT IDENTIFIER ::= { cevModuleVipPortAdapters 2 }
cevPa4e         OBJECT IDENTIFIER ::= { cevModuleVipPortAdapters 3 }
cevPa5e         OBJECT IDENTIFIER ::= { cevModuleVipPortAdapters 4 }
cevPa4t         OBJECT IDENTIFIER ::= { cevModuleVipPortAdapters 5 }
cevPa4r         OBJECT IDENTIFIER ::= { cevModuleVipPortAdapters 6 }
cevPaFddi       OBJECT IDENTIFIER ::= { cevModuleVipPortAdapters 7 }
cevSaEncryption OBJECT IDENTIFIER ::= { cevModuleVipPortAdapters 8 }
cevPaAh1t       OBJECT IDENTIFIER ::= { cevModuleVipPortAdapters 9 }
cevPaAh2t       OBJECT IDENTIFIER ::= { cevModuleVipPortAdapters 10 }
cevPaA8tV35     OBJECT IDENTIFIER ::= { cevModuleVipPortAdapters 12 }
cevPa1feTxIsl   OBJECT IDENTIFIER ::= { cevModuleVipPortAdapters 13 }
cevPa1feFxIsl   OBJECT IDENTIFIER ::= { cevModuleVipPortAdapters 14 }
cevPa1feTxNisl  OBJECT IDENTIFIER ::= { cevModuleVipPortAdapters 15 }
cevSaCompression OBJECT IDENTIFIER ::= { cevModuleVipPortAdapters 16 }
cevPaAtmLite1   OBJECT IDENTIFIER ::= { cevModuleVipPortAdapters 17 }
cevPaCt3        OBJECT IDENTIFIER ::= { cevModuleVipPortAdapters 18 }
cevPaOc3smMuxCbrt1 OBJECT IDENTIFIER ::= { cevModuleVipPortAdapters 19 }
cevPaOc3smMuxCbr120e1 OBJECT IDENTIFIER ::= { cevModuleVipPortAdapters 20 }
cevPaOc3smMuxCbr75e1 OBJECT IDENTIFIER ::= { cevModuleVipPortAdapters 21 }
cevPaOc3mmMuxCbrt1 OBJECT IDENTIFIER ::= { cevModuleVipPortAdapters 22 }
cevPaOc3mmMuxCbr120e1 OBJECT IDENTIFIER ::= { cevModuleVipPortAdapters 23 }
cevPaOc3mmMuxCbr75e1 OBJECT IDENTIFIER ::= { cevModuleVipPortAdapters 24 }
cevPaDs3MuxCbrt1 OBJECT IDENTIFIER ::= { cevModuleVipPortAdapters 25 }
cevPaE3MuxCbr120e1 OBJECT IDENTIFIER ::= { cevModuleVipPortAdapters 26 }
cevPaE3smMuxCbr75e1 OBJECT IDENTIFIER ::= { cevModuleVipPortAdapters 27 }
cevPa8bSt       OBJECT IDENTIFIER ::= { cevModuleVipPortAdapters 28 }
cevPa4bU        OBJECT IDENTIFIER ::= { cevModuleVipPortAdapters 29 }
cevPaFddiFd     OBJECT IDENTIFIER ::= { cevModuleVipPortAdapters 30 }
cevPaJt2        OBJECT IDENTIFIER ::= { cevModuleVipPortAdapters 31 }
cevPaPosdw      OBJECT IDENTIFIER ::= { cevModuleVipPortAdapters 32 }
cevPa4me1Bal    OBJECT IDENTIFIER ::= { cevModuleVipPortAdapters 33 }
cevPa2ce1Balanced OBJECT IDENTIFIER ::= { cevModuleVipPortAdapters 34 }
cevPa2ct1       OBJECT IDENTIFIER ::= { cevModuleVipPortAdapters 35 }
cevPa1vg        OBJECT IDENTIFIER ::= { cevModuleVipPortAdapters 36 }
cevPaAtmdxDs3   OBJECT IDENTIFIER ::= { cevModuleVipPortAdapters 37 }
cevPaAtmdxE3    OBJECT IDENTIFIER ::= { cevModuleVipPortAdapters 38 }
cevPaAtmdxSmlOc3 OBJECT IDENTIFIER ::= { cevModuleVipPortAdapters 39 }
cevPaAtmdxSmiOc3 OBJECT IDENTIFIER ::= { cevModuleVipPortAdapters 40 }
cevPaAtmdxMmOc3 OBJECT IDENTIFIER ::= { cevModuleVipPortAdapters 41 }
cevPaA8tX21     OBJECT IDENTIFIER ::= { cevModuleVipPortAdapters 42 }
cevPaA8tRs232   OBJECT IDENTIFIER ::= { cevModuleVipPortAdapters 43 }
cevPa4me1Unbal  OBJECT IDENTIFIER ::= { cevModuleVipPortAdapters 44 }
cevPa4rFdx      OBJECT IDENTIFIER ::= { cevModuleVipPortAdapters 45 }
cevPa1e3        OBJECT IDENTIFIER ::= { cevModuleVipPortAdapters 46 }
cevPa2e3        OBJECT IDENTIFIER ::= { cevModuleVipPortAdapters 47 }
cevPa1t3        OBJECT IDENTIFIER ::= { cevModuleVipPortAdapters 48 }
cevPa2t3        OBJECT IDENTIFIER ::= { cevModuleVipPortAdapters 49 }
cevPa2ce1Unbalanced OBJECT IDENTIFIER ::= { cevModuleVipPortAdapters 50 }
cevPa14eSwitch  OBJECT IDENTIFIER ::= { cevModuleVipPortAdapters 51 }
cevas58001fedsi OBJECT IDENTIFIER ::= { cevModuleVipPortAdapters 52 }
cevPa1feFxNisl  OBJECT IDENTIFIER ::= { cevModuleVipPortAdapters 53 }
cevPaIo1fe      OBJECT IDENTIFIER ::= { cevModuleVipPortAdapters 54 }
cevPaIo         OBJECT IDENTIFIER ::= { cevModuleVipPortAdapters 55 }
cevPa2feTx      OBJECT IDENTIFIER ::= { cevModuleVipPortAdapters 56 }
cevPa2feFx      OBJECT IDENTIFIER ::= { cevModuleVipPortAdapters 57 }
cevPaGe         OBJECT IDENTIFIER ::= { cevModuleVipPortAdapters 59 }
cevPaPosswSm    OBJECT IDENTIFIER ::= { cevModuleVipPortAdapters 60 }
cevPaPosswMm    OBJECT IDENTIFIER ::= { cevModuleVipPortAdapters 61 }
cevPaPosswLr    OBJECT IDENTIFIER ::= { cevModuleVipPortAdapters 62 }
cevPa4ct1Csu    OBJECT IDENTIFIER ::= { cevModuleVipPortAdapters 63 }
cevPa8ct1Csu    OBJECT IDENTIFIER ::= { cevModuleVipPortAdapters 64 }
cevPa8ct1       OBJECT IDENTIFIER ::= { cevModuleVipPortAdapters 65 }
cevPa8ce1       OBJECT IDENTIFIER ::= { cevModuleVipPortAdapters 66 }
cevPaVxc2t1e1   OBJECT IDENTIFIER ::= { cevModuleVipPortAdapters 67 }
cevPaVxb2t1e1   OBJECT IDENTIFIER ::= { cevModuleVipPortAdapters 68 }
cevPaAtmOc12Mm  OBJECT IDENTIFIER ::= { cevModuleVipPortAdapters 69 }
cevPaAtmOc12Smi OBJECT IDENTIFIER ::= { cevModuleVipPortAdapters 70 }
cevPaMct3       OBJECT IDENTIFIER ::= { cevModuleVipPortAdapters 71 }
cevPaMc2t3      OBJECT IDENTIFIER ::= { cevModuleVipPortAdapters 72 }
cevPa1t3Plus    OBJECT IDENTIFIER ::= { cevModuleVipPortAdapters 73 }
cevPa2t3Plus    OBJECT IDENTIFIER ::= { cevModuleVipPortAdapters 74 }
cevPaPosOc12Mm  OBJECT IDENTIFIER ::= { cevModuleVipPortAdapters 75 }
cevPaPosOc12Sm  OBJECT IDENTIFIER ::= { cevModuleVipPortAdapters 76 }
cevPaImaT1      OBJECT IDENTIFIER ::= { cevModuleVipPortAdapters 77 }
cevPaImaE1      OBJECT IDENTIFIER ::= { cevModuleVipPortAdapters 78 }
cevSrpPaOc12Mm  OBJECT IDENTIFIER ::= { cevModuleVipPortAdapters 79 }
cevSrpPaOc12SmIr OBJECT IDENTIFIER ::= { cevModuleVipPortAdapters 80 }
cevSrpPaOc12Lr  OBJECT IDENTIFIER ::= { cevModuleVipPortAdapters 81 }
cevPa2ct1Csu    OBJECT IDENTIFIER ::= { cevModuleVipPortAdapters 82 }
cevPa2ce1       OBJECT IDENTIFIER ::= { cevModuleVipPortAdapters 83 }
cevPaMcx2te1    OBJECT IDENTIFIER ::= { cevModuleVipPortAdapters 84 }
cevPaMcx4te1    OBJECT IDENTIFIER ::= { cevModuleVipPortAdapters 85 }
cevPaMcx8te1    OBJECT IDENTIFIER ::= { cevModuleVipPortAdapters 86 }
cevSrpPaOc12SmXr OBJECT IDENTIFIER ::= { cevModuleVipPortAdapters 87 }
cevPaMcStm1Smi  OBJECT IDENTIFIER ::= { cevModuleVipPortAdapters 90 }
cevPaMcStm1Mm   OBJECT IDENTIFIER ::= { cevModuleVipPortAdapters 91 }
cevPa2feTxI82543 OBJECT IDENTIFIER ::= { cevModuleVipPortAdapters 92 }
cevPa2feFxI82543 OBJECT IDENTIFIER ::= { cevModuleVipPortAdapters 93 }
cevPaDualWideGe OBJECT IDENTIFIER ::= { cevModuleVipPortAdapters 94 }
cevPaVxa1T1E124 OBJECT IDENTIFIER ::= { cevModuleVipPortAdapters 95 }
cevPaVxa1T1E130 OBJECT IDENTIFIER ::= { cevModuleVipPortAdapters 96 }
cevPaMcT1E1     OBJECT IDENTIFIER ::= { cevModuleVipPortAdapters 97 }
cevPaMcx8te1M   OBJECT IDENTIFIER ::= { cevModuleVipPortAdapters 99 }
cevPa1ce3       OBJECT IDENTIFIER ::= { cevModuleVipPortAdapters 100 }
cevPa2OC3PosSw  OBJECT IDENTIFIER ::= { cevModuleVipPortAdapters 101 }
cevPa2feFxIsl   OBJECT IDENTIFIER ::= { cevModuleVipPortAdapters 102 }
cevPa4Dtr       OBJECT IDENTIFIER ::= { cevModuleVipPortAdapters 103 }
cevPaVmHda8FxsDid OBJECT IDENTIFIER ::= { cevModuleVipPortAdapters 104 }
cevPa1OC3PosSw  OBJECT IDENTIFIER ::= { cevModuleVipPortAdapters 105 }
cevPaA6mmOc3    OBJECT IDENTIFIER ::= { cevModuleVipPortAdapters 106 }
cevPaA6SmiOc3   OBJECT IDENTIFIER ::= { cevModuleVipPortAdapters 107 }
cevPaA6SmlOc3   OBJECT IDENTIFIER ::= { cevModuleVipPortAdapters 108 }
cevPaA6Ds3      OBJECT IDENTIFIER ::= { cevModuleVipPortAdapters 109 }
cevPaA6E3       OBJECT IDENTIFIER ::= { cevModuleVipPortAdapters 110 }
cevPaMcx4te1Q   OBJECT IDENTIFIER ::= { cevModuleVipPortAdapters 111 }
cevPaMct3ec     OBJECT IDENTIFIER ::= { cevModuleVipPortAdapters 112 }
cevPaMc2t3ec    OBJECT IDENTIFIER ::= { cevModuleVipPortAdapters 113 }
cevPa1t3e3ec    OBJECT IDENTIFIER ::= { cevModuleVipPortAdapters 114 }
cevPa2t3e3ec    OBJECT IDENTIFIER ::= { cevModuleVipPortAdapters 115 }
cevModuleCpuType OBJECT IDENTIFIER ::= { cevModule 5 }
cevC7200Io1fe   OBJECT IDENTIFIER ::= { cevModuleCpuType 1 }
cevC7200Io      OBJECT IDENTIFIER ::= { cevModuleCpuType 2 }
cevCpuAS5300    OBJECT IDENTIFIER ::= { cevModuleCpuType 3 }
cevCpuRpm       OBJECT IDENTIFIER ::= { cevModuleCpuType 7 }
cevCpu2600      OBJECT IDENTIFIER ::= { cevModuleCpuType 8 }
cevCpu7200Npe300 OBJECT IDENTIFIER ::= { cevModuleCpuType 9 }
cevCpu1400      OBJECT IDENTIFIER ::= { cevModuleCpuType 10 }
cevCpu800       OBJECT IDENTIFIER ::= { cevModuleCpuType 11 }
cevCpuPSM1Gbps  OBJECT IDENTIFIER ::= { cevModuleCpuType 12 }
cevCpu7200Npe175 OBJECT IDENTIFIER ::= { cevModuleCpuType 14 }
cevCpu7200Npe225 OBJECT IDENTIFIER ::= { cevModuleCpuType 15 }
cevCpu1417      OBJECT IDENTIFIER ::= { cevModuleCpuType 17 }
cevCpuPsm11oc12 OBJECT IDENTIFIER ::= { cevModuleCpuType 18 }
cevCpuOpticalRegenerator OBJECT IDENTIFIER ::= { cevModuleCpuType 19 }
cevCpuUbr924    OBJECT IDENTIFIER ::= { cevModuleCpuType 20 }
cevCpu7120      OBJECT IDENTIFIER ::= { cevModuleCpuType 21 }
cevCpu7140      OBJECT IDENTIFIER ::= { cevModuleCpuType 22 }
cevCpuPsm12t3e3 OBJECT IDENTIFIER ::= { cevModuleCpuType 23 }
cevCpuPsm14oc3  OBJECT IDENTIFIER ::= { cevModuleCpuType 24 }
cevCpu7200Npe100 OBJECT IDENTIFIER ::= { cevModuleCpuType 26 }
cevCpu7200Npe150 OBJECT IDENTIFIER ::= { cevModuleCpuType 27 }
cevCpu7200Npe200 OBJECT IDENTIFIER ::= { cevModuleCpuType 28 }
cevCpuCreRp     OBJECT IDENTIFIER ::= { cevModuleCpuType 29 }
cevCpuCreFp     OBJECT IDENTIFIER ::= { cevModuleCpuType 30 }
cevCpuAs5400    OBJECT IDENTIFIER ::= { cevModuleCpuType 31 }
cevCpuAS5200    OBJECT IDENTIFIER ::= { cevModuleCpuType 34 }
cevCpuGrp       OBJECT IDENTIFIER ::= { cevModuleCpuType 35 }
cevCpuMc3810V3  OBJECT IDENTIFIER ::= { cevModuleCpuType 36 }
cevCpuAs5850    OBJECT IDENTIFIER ::= { cevModuleCpuType 38 }
cevCpu7200Npe400 OBJECT IDENTIFIER ::= { cevModuleCpuType 39 }
cevCpuAs5350    OBJECT IDENTIFIER ::= { cevModuleCpuType 40 }
cevCpuRsp4Plus  OBJECT IDENTIFIER ::= { cevModuleCpuType 41 }
cevCpuUbr91x    OBJECT IDENTIFIER ::= { cevModuleCpuType 42 }
cevCpu7150      OBJECT IDENTIFIER ::= { cevModuleCpuType 43 }
cevCpuPXMB45Gbps OBJECT IDENTIFIER ::= { cevModuleCpuType 44 }
cevCpuONS15540  OBJECT IDENTIFIER ::= { cevModuleCpuType 47 }
cevCpuRsp16     OBJECT IDENTIFIER ::= { cevModuleCpuType 48 }
cevCpuPrp1      OBJECT IDENTIFIER ::= { cevModuleCpuType 49 }
cevCpuC7300Nse100 OBJECT IDENTIFIER ::= { cevModuleCpuType 50 }
cevCpuPXM1E1Gbps OBJECT IDENTIFIER ::= { cevModuleCpuType 51 }
cevCpuPXM1E2Oc12 OBJECT IDENTIFIER ::= { cevModuleCpuType 52 }
cevCpuPXM1E8Oc3 OBJECT IDENTIFIER ::= { cevModuleCpuType 53 }
cevCpuPXM1E8T3E3 OBJECT IDENTIFIER ::= { cevModuleCpuType 54 }
cevCpuPXM1EComboT3E3Oc3 OBJECT IDENTIFIER ::= { cevModuleCpuType 55 }
cevCpu7200Npeg1 OBJECT IDENTIFIER ::= { cevModuleCpuType 56 }
cevCpu26912fe   OBJECT IDENTIFIER ::= { cevModuleCpuType 57 }
cevCpu37452fe   OBJECT IDENTIFIER ::= { cevModuleCpuType 58 }
cevCpu37252fe   OBJECT IDENTIFIER ::= { cevModuleCpuType 59 }
cevCpu36311fe   OBJECT IDENTIFIER ::= { cevModuleCpuType 60 }
cevCpu19002fe   OBJECT IDENTIFIER ::= { cevModuleCpuType 61 }
cevCpuONS15530SW OBJECT IDENTIFIER ::= { cevModuleCpuType 62 }
cevCpu6400Nsp   OBJECT IDENTIFIER ::= { cevModuleCpuType 63 }
cevCpu6400Nrp   OBJECT IDENTIFIER ::= { cevModuleCpuType 64 }
cevCpu6400Nrp2  OBJECT IDENTIFIER ::= { cevModuleCpuType 65 }
cevCpu6400Nrp2Sv OBJECT IDENTIFIER ::= { cevModuleCpuType 66 }
cevCpuPXM1E4Oc3 OBJECT IDENTIFIER ::= { cevModuleCpuType 67 }
cevCpu1700      OBJECT IDENTIFIER ::= { cevModuleCpuType 68 }
cevCpu7301Npeg1 OBJECT IDENTIFIER ::= { cevModuleCpuType 71 }
cevCpuPXM1E16t1e1 OBJECT IDENTIFIER ::= { cevModuleCpuType 72 }
cevCpu7300Nse100Plus OBJECT IDENTIFIER ::= { cevModuleCpuType 73 }
cevCpuPxm1eB8t3e34Oc3 OBJECT IDENTIFIER ::= { cevModuleCpuType 74 }
cevCpu4604      OBJECT IDENTIFIER ::= { cevModuleCpuType 75 }
cevCpu4224      OBJECT IDENTIFIER ::= { cevModuleCpuType 76 }
cevCpuAs5400HPX OBJECT IDENTIFIER ::= { cevModuleCpuType 77 }
cevCpuAs5350HPX OBJECT IDENTIFIER ::= { cevModuleCpuType 78 }
cevCpuAs5850tb  OBJECT IDENTIFIER ::= { cevModuleCpuType 80 }
cevCpuC7300Npeg100 OBJECT IDENTIFIER ::= { cevModuleCpuType 81 }
cevCpuMdsCpp    OBJECT IDENTIFIER ::= { cevModuleCpuType 82 }
cevCpuMdsDpp    OBJECT IDENTIFIER ::= { cevModuleCpuType 83 }
cevCpuMdsSup    OBJECT IDENTIFIER ::= { cevModuleCpuType 84 }
cevCpu2430Iad24Fxs OBJECT IDENTIFIER ::= { cevModuleCpuType 85 }
cevCpu2431Iad8Fxs OBJECT IDENTIFIER ::= { cevModuleCpuType 86 }
cevCpu2431Iad16Fxs OBJECT IDENTIFIER ::= { cevModuleCpuType 87 }
cevCpu2431Iad1T1E1 OBJECT IDENTIFIER ::= { cevModuleCpuType 88 }
cevCpu2432Iad24Fxs OBJECT IDENTIFIER ::= { cevModuleCpuType 89 }
cevCpu3220      OBJECT IDENTIFIER ::= { cevModuleCpuType 90 }
cevCpuVG224     OBJECT IDENTIFIER ::= { cevModuleCpuType 91 }
cevCpuCat6kWsSup720RP OBJECT IDENTIFIER ::= { cevModuleCpuType 92 }
cevCpuCat6kMsfc OBJECT IDENTIFIER ::= { cevModuleCpuType 93 }
cevCpuCat6kMsfc2 OBJECT IDENTIFIER ::= { cevModuleCpuType 94 }
cevCpuCat6kWsxSup12ge OBJECT IDENTIFIER ::= { cevModuleCpuType 95 }
cevCpuCat6kWsxSup22ge OBJECT IDENTIFIER ::= { cevModuleCpuType 96 }
cevCpuCat6kWsxSup1a2ge OBJECT IDENTIFIER ::= { cevModuleCpuType 97 }
cevCpuCat6kWsSup720SP OBJECT IDENTIFIER ::= { cevModuleCpuType 98 }
cevCpu3845ge2   OBJECT IDENTIFIER ::= { cevModuleCpuType 99 }
cevCpu3825ge2   OBJECT IDENTIFIER ::= { cevModuleCpuType 100 }
cevCpuCrs1AsmpRoute OBJECT IDENTIFIER ::= { cevModuleCpuType 101 }
cevCpuCrs1DsmpRoute OBJECT IDENTIFIER ::= { cevModuleCpuType 102 }
cevCpuCrs1pfeAsic OBJECT IDENTIFIER ::= { cevModuleCpuType 103 }
cevCpuCrs1EgressqAsic OBJECT IDENTIFIER ::= { cevModuleCpuType 104 }
cevCpuCrs1FabricqAsic OBJECT IDENTIFIER ::= { cevModuleCpuType 105 }
cevCpuCrs1IngressqAsic OBJECT IDENTIFIER ::= { cevModuleCpuType 106 }
cevCpuCrs1SPLC  OBJECT IDENTIFIER ::= { cevModuleCpuType 107 }
cevCpuCrs1SPFC  OBJECT IDENTIFIER ::= { cevModuleCpuType 108 }
cevCpu1800Mod   OBJECT IDENTIFIER ::= { cevModuleCpuType 109 }
cevCpuPrp2      OBJECT IDENTIFIER ::= { cevModuleCpuType 110 }
cevCpuCat6kWsSup32ge OBJECT IDENTIFIER ::= { cevModuleCpuType 111 }
cevCpuCat6kWsSup3210ge OBJECT IDENTIFIER ::= { cevModuleCpuType 112 }
cevCpuAs5400XM  OBJECT IDENTIFIER ::= { cevModuleCpuType 113 }
cevCpuAs5350XM  OBJECT IDENTIFIER ::= { cevModuleCpuType 114 }
cevCpu1800      OBJECT IDENTIFIER ::= { cevModuleCpuType 115 }
cevCpu7200Npeg2 OBJECT IDENTIFIER ::= { cevModuleCpuType 118 }
cevCpuCat6kMsfc2a OBJECT IDENTIFIER ::= { cevModuleCpuType 119 }
cevCpuC28012fe  OBJECT IDENTIFIER ::= { cevModuleCpuType 120 }
cevCpuIXP2350WestportNP OBJECT IDENTIFIER ::= { cevModuleCpuType 121 }
cevCpuC7300Nse150 OBJECT IDENTIFIER ::= { cevModuleCpuType 122 }
cevCpuCre1Rp    OBJECT IDENTIFIER ::= { cevModuleCpuType 123 }
cevCpuCre2Rp    OBJECT IDENTIFIER ::= { cevModuleCpuType 124 }
cevCpuCre3Rp    OBJECT IDENTIFIER ::= { cevModuleCpuType 125 }
cevCpuCre1Fp    OBJECT IDENTIFIER ::= { cevModuleCpuType 126 }
cevCpuCre2Fp    OBJECT IDENTIFIER ::= { cevModuleCpuType 127 }
cevCpuCre3Fp    OBJECT IDENTIFIER ::= { cevModuleCpuType 128 }
cevCpu7600Sip600DC OBJECT IDENTIFIER ::= { cevModuleCpuType 130 }
cevCpuCat6kVsF6kMsfc3 OBJECT IDENTIFIER ::= { cevModuleCpuType 131 }
cevCpuCat6kVsS72010G OBJECT IDENTIFIER ::= { cevModuleCpuType 132 }
cevCpu7201Npeg2 OBJECT IDENTIFIER ::= { cevModuleCpuType 133 }
cevCpuSamiDc8548H OBJECT IDENTIFIER ::= { cevModuleCpuType 134 }
cevCpuUC500     OBJECT IDENTIFIER ::= { cevModuleCpuType 135 }
cevCpuBroadcomSB1A OBJECT IDENTIFIER ::= { cevModuleCpuType 138 }
cevCpuCrs1SPLCB OBJECT IDENTIFIER ::= { cevModuleCpuType 139 }
cevCpuUc520s    OBJECT IDENTIFIER ::= { cevModuleCpuType 140 }
cevCpuUc520m    OBJECT IDENTIFIER ::= { cevModuleCpuType 141 }
cevCpu1861      OBJECT IDENTIFIER ::= { cevModuleCpuType 144 }
cevCpuTraffic   OBJECT IDENTIFIER ::= { cevModuleCpuType 145 }
cevCpuCat6kWsSup32Pge OBJECT IDENTIFIER ::= { cevModuleCpuType 146 }
cevCpuCat6kWsSup32P10ge OBJECT IDENTIFIER ::= { cevModuleCpuType 147 }
cevCpuCat6kWsF6kPisa OBJECT IDENTIFIER ::= { cevModuleCpuType 148 }
cevCpuCrs1PlimAsic OBJECT IDENTIFIER ::= { cevModuleCpuType 152 }
cevCpu2435Iad8Fxs OBJECT IDENTIFIER ::= { cevModuleCpuType 153 }
cevCpuVG204     OBJECT IDENTIFIER ::= { cevModuleCpuType 154 }
cevCpuVG202     OBJECT IDENTIFIER ::= { cevModuleCpuType 155 }
cevCpu2941      OBJECT IDENTIFIER ::= { cevModuleCpuType 157 }
cevCPU8641D     OBJECT IDENTIFIER ::= { cevModuleCpuType 158 }
cevCpuCat6kVsSup2t10g OBJECT IDENTIFIER ::= { cevModuleCpuType 159 }
cevCpu19412ge   OBJECT IDENTIFIER ::= { cevModuleCpuType 160 }
cevCpu29012ge   OBJECT IDENTIFIER ::= { cevModuleCpuType 161 }
cevCpu29113ge   OBJECT IDENTIFIER ::= { cevModuleCpuType 162 }
cevCpu29213ge   OBJECT IDENTIFIER ::= { cevModuleCpuType 163 }
cevCpu29513ge   OBJECT IDENTIFIER ::= { cevModuleCpuType 164 }
cevCpu39253ge   OBJECT IDENTIFIER ::= { cevModuleCpuType 165 }
cevCpu39453ge   OBJECT IDENTIFIER ::= { cevModuleCpuType 166 }
cevCpuSr520T1   OBJECT IDENTIFIER ::= { cevModuleCpuType 167 }
cevCpu1941w2ge  OBJECT IDENTIFIER ::= { cevModuleCpuType 168 }
cevCpu3825nvge2 OBJECT IDENTIFIER ::= { cevModuleCpuType 169 }
cevCpu3845nvge2 OBJECT IDENTIFIER ::= { cevModuleCpuType 170 }
cevCpuCrs1SPFP  OBJECT IDENTIFIER ::= { cevModuleCpuType 175 }
cevCpu3900SPE2004ge OBJECT IDENTIFIER ::= { cevModuleCpuType 179 }
cevCpu3900Spe100K9 OBJECT IDENTIFIER ::= { cevModuleCpuType 182 }
cevCpu3900Spe150K9 OBJECT IDENTIFIER ::= { cevModuleCpuType 183 }
cevCpu3900SPE2504ge OBJECT IDENTIFIER ::= { cevModuleCpuType 186 }
cevCpuCrs1FP140 OBJECT IDENTIFIER ::= { cevModuleCpuType 187 }
cevCpuCrs1MSC140G OBJECT IDENTIFIER ::= { cevModuleCpuType 188 }
cevCpuC1841C2fek9 OBJECT IDENTIFIER ::= { cevModuleCpuType 189 }
cevCpuC2801C2fek9 OBJECT IDENTIFIER ::= { cevModuleCpuType 190 }
cevCpuC2811C2fek9 OBJECT IDENTIFIER ::= { cevModuleCpuType 191 }
cevCpuC2821C2gek9 OBJECT IDENTIFIER ::= { cevModuleCpuType 192 }
cevCpu3825C2gek9 OBJECT IDENTIFIER ::= { cevModuleCpuType 194 }
cevCpu3845C2gek9 OBJECT IDENTIFIER ::= { cevModuleCpuType 195 }
cevCpuCGR20102ge OBJECT IDENTIFIER ::= { cevModuleCpuType 198 }
cevCpu1906Ck9   OBJECT IDENTIFIER ::= { cevModuleCpuType 199 }
cevCpuDsp       OBJECT IDENTIFIER ::= { cevModuleCpuType 201 }
cevCpu5915      OBJECT IDENTIFIER ::= { cevModuleCpuType 202 }
cevCpu86xVAE    OBJECT IDENTIFIER ::= { cevModuleCpuType 212 }
cevCpuCryptoAsic OBJECT IDENTIFIER ::= { cevModuleCpuType 213 }
cevCpu2811ve2fe OBJECT IDENTIFIER ::= { cevModuleCpuType 214 }
cevCpu1841ve2fe OBJECT IDENTIFIER ::= { cevModuleCpuType 215 }
cevCpu819HG     OBJECT IDENTIFIER ::= { cevModuleCpuType 216 }
cevCpu819G      OBJECT IDENTIFIER ::= { cevModuleCpuType 217 }
cevCpu881W      OBJECT IDENTIFIER ::= { cevModuleCpuType 218 }
cevCpu886VAW    OBJECT IDENTIFIER ::= { cevModuleCpuType 219 }
cevCpu887VAMW   OBJECT IDENTIFIER ::= { cevModuleCpuType 220 }
cevCpu887VAW    OBJECT IDENTIFIER ::= { cevModuleCpuType 221 }
cevCpuAsaSm1    OBJECT IDENTIFIER ::= { cevModuleCpuType 222 }
cevCpuAsaSm1K7  OBJECT IDENTIFIER ::= { cevModuleCpuType 223 }
cevCpuCrsLSP140 OBJECT IDENTIFIER ::= { cevModuleCpuType 234 }
cevCpuCre5Fp    OBJECT IDENTIFIER ::= { cevModuleCpuType 243 }
cevCpuCre5Rp    OBJECT IDENTIFIER ::= { cevModuleCpuType 244 }
cevCpuVG350     OBJECT IDENTIFIER ::= { cevModuleCpuType 245 }
cevCpu819HGW    OBJECT IDENTIFIER ::= { cevModuleCpuType 250 }
cevCpu819H      OBJECT IDENTIFIER ::= { cevModuleCpuType 251 }
cevCpu819HWD    OBJECT IDENTIFIER ::= { cevModuleCpuType 252 }
cevCpu812G      OBJECT IDENTIFIER ::= { cevModuleCpuType 253 }
cevCpu812GCIFI  OBJECT IDENTIFIER ::= { cevModuleCpuType 254 }
cevCpu819HGM    OBJECT IDENTIFIER ::= { cevModuleCpuType 255 }
cevCpu819GM     OBJECT IDENTIFIER ::= { cevModuleCpuType 256 }
cevCpuCgrSup    OBJECT IDENTIFIER ::= { cevModuleCpuType 266 }
cevCpu86xVAEW   OBJECT IDENTIFIER ::= { cevModuleCpuType 267 }
cevCpuvg202xm   OBJECT IDENTIFIER ::= { cevModuleCpuType 268 }
cevCpuvg204xm   OBJECT IDENTIFIER ::= { cevModuleCpuType 269 }
cevCpuC6880x    OBJECT IDENTIFIER ::= { cevModuleCpuType 270 }
cevCpu1783SR    OBJECT IDENTIFIER ::= { cevModuleCpuType 280 }
cevCpuTypeCPU   OBJECT IDENTIFIER ::= { cevModuleCpuType 281 }
cevCpuC881      OBJECT IDENTIFIER ::= { cevModuleCpuType 282 }
cevCpuC886VA    OBJECT IDENTIFIER ::= { cevModuleCpuType 283 }
cevCpuC887VA    OBJECT IDENTIFIER ::= { cevModuleCpuType 284 }
cevCpuC888      OBJECT IDENTIFIER ::= { cevModuleCpuType 285 }
cevCpuC891F     OBJECT IDENTIFIER ::= { cevModuleCpuType 286 }
cevCpuC891FW    OBJECT IDENTIFIER ::= { cevModuleCpuType 287 }
cevCpuVG310     OBJECT IDENTIFIER ::= { cevModuleCpuType 288 }
cevCpuVG320     OBJECT IDENTIFIER ::= { cevModuleCpuType 289 }
cevCpuCat6kSup  OBJECT IDENTIFIER ::= { cevModuleCpuType 290 }
cevCPURT1081K9  OBJECT IDENTIFIER ::= { cevModuleCpuType 293 }
cevCPURT1091K9  OBJECT IDENTIFIER ::= { cevModuleCpuType 294 }
cevCpuRT2241K9  OBJECT IDENTIFIER ::= { cevModuleCpuType 295 }
cevCpuRT2221K9  OBJECT IDENTIFIER ::= { cevModuleCpuType 296 }
cevCpuRT2241WCK9 OBJECT IDENTIFIER ::= { cevModuleCpuType 297 }
cevCpuRT3211K9  OBJECT IDENTIFIER ::= { cevModuleCpuType 298 }
cevCpuRT3221K9  OBJECT IDENTIFIER ::= { cevModuleCpuType 299 }
cevCpuRT3201K9  OBJECT IDENTIFIER ::= { cevModuleCpuType 300 }
cevCpu897VAB    OBJECT IDENTIFIER ::= { cevModuleCpuType 306 }
cevCpuCrs1LSPX  OBJECT IDENTIFIER ::= { cevModuleCpuType 307 }
cevCpuCrs1FPX   OBJECT IDENTIFIER ::= { cevModuleCpuType 308 }
cevCpuCrs1MSCX  OBJECT IDENTIFIER ::= { cevModuleCpuType 309 }
cevCpuAsa5506   OBJECT IDENTIFIER ::= { cevModuleCpuType 312 }
cevCpuAsa5506W  OBJECT IDENTIFIER ::= { cevModuleCpuType 313 }
cevCpuAsa5508   OBJECT IDENTIFIER ::= { cevModuleCpuType 314 }
cevCpuAsa5506K7 OBJECT IDENTIFIER ::= { cevModuleCpuType 315 }
cevCpuAsa5508K7 OBJECT IDENTIFIER ::= { cevModuleCpuType 316 }
cevCpu891x24X   OBJECT IDENTIFIER ::= { cevModuleCpuType 318 }
cevCpu841Mx4X   OBJECT IDENTIFIER ::= { cevModuleCpuType 321 }
cevCpu841Mx8X   OBJECT IDENTIFIER ::= { cevModuleCpuType 322 }
cevCpuCrs1MSCXL OBJECT IDENTIFIER ::= { cevModuleCpuType 323 }
cevCpuCrs1FPXL  OBJECT IDENTIFIER ::= { cevModuleCpuType 324 }
cevCpuN9kCpu    OBJECT IDENTIFIER ::= { cevModuleCpuType 325 }
cevCpuAsa5506H  OBJECT IDENTIFIER ::= { cevModuleCpuType 326 }
cevCpuAsa5516   OBJECT IDENTIFIER ::= { cevModuleCpuType 327 }
cevCpuC819GWLTE OBJECT IDENTIFIER ::= { cevModuleCpuType 328 }
cevCpuISA30004C OBJECT IDENTIFIER ::= { cevModuleCpuType 329 }
cevCpuISA30002C2F OBJECT IDENTIFIER ::= { cevModuleCpuType 330 }
cevCpuRAISA1783SAD4T0S OBJECT IDENTIFIER ::= { cevModuleCpuType 331 }
cevCpuRAISA1783SAD2T2S OBJECT IDENTIFIER ::= { cevModuleCpuType 332 }
cevCpuISA4000   OBJECT IDENTIFIER ::= { cevModuleCpuType 333 }
cevCpu86xVAEV2  OBJECT IDENTIFIER ::= { cevModuleCpuType 334 }
cevModuleCscType OBJECT IDENTIFIER ::= { cevModule 6 }
cevModuleC7xxxType OBJECT IDENTIFIER ::= { cevModule 7 }
cevC7xxxMc14a   OBJECT IDENTIFIER ::= { cevModuleC7xxxType 1 }
cevC7xxxMc16a   OBJECT IDENTIFIER ::= { cevModuleC7xxxType 2 }
cevC7xxxMc11    OBJECT IDENTIFIER ::= { cevModuleC7xxxType 3 }
cevC7xxxMc12a   OBJECT IDENTIFIER ::= { cevModuleC7xxxType 4 }
cevC7xxxMc11a   OBJECT IDENTIFIER ::= { cevModuleC7xxxType 5 }
cevC7xxxIo1feTxIsl OBJECT IDENTIFIER ::= { cevModuleC7xxxType 6 }
cevC7xxxMc28    OBJECT IDENTIFIER ::= { cevModuleC7xxxType 8 }
cevVip480       OBJECT IDENTIFIER ::= { cevModuleC7xxxType 9 }
cevVip450       OBJECT IDENTIFIER ::= { cevModuleC7xxxType 10 }
cevC7xxxIoEGE   OBJECT IDENTIFIER ::= { cevModuleC7xxxType 11 }
cevC7xxxIo2FE   OBJECT IDENTIFIER ::= { cevModuleC7xxxType 12 }
cevC7xxxEIP     OBJECT IDENTIFIER ::= { cevModuleC7xxxType 16 }
cevC7xxxFIP     OBJECT IDENTIFIER ::= { cevModuleC7xxxType 17 }
cevC7xxxSrsFIP  OBJECT IDENTIFIER ::= { cevModuleC7xxxType 18 }
cevC7xxxTRIP    OBJECT IDENTIFIER ::= { cevModuleC7xxxType 19 }
cevC7xxxSrsTRIP OBJECT IDENTIFIER ::= { cevModuleC7xxxType 20 }
cevC7xxxFSIP    OBJECT IDENTIFIER ::= { cevModuleC7xxxType 21 }
cevC7xxxSSIP    OBJECT IDENTIFIER ::= { cevModuleC7xxxType 22 }
cevC7xxxMIP     OBJECT IDENTIFIER ::= { cevModuleC7xxxType 23 }
cevC7xxxSMIP    OBJECT IDENTIFIER ::= { cevModuleC7xxxType 24 }
cevC7xxxVIP2    OBJECT IDENTIFIER ::= { cevModuleC7xxxType 25 }
cevC7xxxVIP250  OBJECT IDENTIFIER ::= { cevModuleC7xxxType 26 }
cevC7xxxRSP1    OBJECT IDENTIFIER ::= { cevModuleC7xxxType 27 }
cevC7xxxRSP2    OBJECT IDENTIFIER ::= { cevModuleC7xxxType 28 }
cevC7xxxRSP4    OBJECT IDENTIFIER ::= { cevModuleC7xxxType 29 }
cevC7xxxPosIP   OBJECT IDENTIFIER ::= { cevModuleC7xxxType 30 }
cevC7xxxFeIP2   OBJECT IDENTIFIER ::= { cevModuleC7xxxType 31 }
cevC73004Oc3PosMm OBJECT IDENTIFIER ::= { cevModuleC7xxxType 33 }
cevC73004Oc3PosSmIr OBJECT IDENTIFIER ::= { cevModuleC7xxxType 34 }
cevC73004Oc3PosSmLr OBJECT IDENTIFIER ::= { cevModuleC7xxxType 35 }
cevC7300Oc48PosSmSr OBJECT IDENTIFIER ::= { cevModuleC7xxxType 36 }
cevC7300Oc48PosSmIr OBJECT IDENTIFIER ::= { cevModuleC7xxxType 37 }
cevC7300Oc48PosSmLr OBJECT IDENTIFIER ::= { cevModuleC7xxxType 38 }
cevC7500AIP     OBJECT IDENTIFIER ::= { cevModuleC7xxxType 58 }
cevC7500CIP     OBJECT IDENTIFIER ::= { cevModuleC7xxxType 59 }
cevC7500CIP2    OBJECT IDENTIFIER ::= { cevModuleC7xxxType 60 }
cevC7500GEIP    OBJECT IDENTIFIER ::= { cevModuleC7xxxType 61 }
cevC7500FEIP    OBJECT IDENTIFIER ::= { cevModuleC7xxxType 62 }
cevC7xxxSIP     OBJECT IDENTIFIER ::= { cevModuleC7xxxType 63 }
cevC7xxxRSP     OBJECT IDENTIFIER ::= { cevModuleC7xxxType 64 }
cevC7xxxHSSI    OBJECT IDENTIFIER ::= { cevModuleC7xxxType 65 }
cevC7411        OBJECT IDENTIFIER ::= { cevModuleC7xxxType 66 }
cevC7411IoGE    OBJECT IDENTIFIER ::= { cevModuleC7xxxType 67 }
cevC7301        OBJECT IDENTIFIER ::= { cevModuleC7xxxType 68 }
cevC7301IoGE    OBJECT IDENTIFIER ::= { cevModuleC7xxxType 69 }
cevVip680       OBJECT IDENTIFIER ::= { cevModuleC7xxxType 70 }
cevC7300CCPA    OBJECT IDENTIFIER ::= { cevModuleC7xxxType 76 }
cevC7304MSC100  OBJECT IDENTIFIER ::= { cevModuleC7xxxType 77 }
cevC73006E3     OBJECT IDENTIFIER ::= { cevModuleC7xxxType 78 }
cevC73001Oc12Atm OBJECT IDENTIFIER ::= { cevModuleC7xxxType 79 }
cevC7200Vsa     OBJECT IDENTIFIER ::= { cevModuleC7xxxType 81 }
cevModuleC4xxxType OBJECT IDENTIFIER ::= { cevModule 8 }
cevC4xxxUnknown OBJECT IDENTIFIER ::= { cevModuleC4xxxType 1 }
cevC4xxxNp4Gb   OBJECT IDENTIFIER ::= { cevModuleC4xxxType 2 }
cevC4wsx4548GbRj45VPlus OBJECT IDENTIFIER ::= { cevModuleC4xxxType 3 }
cevCat4kWsx4948e10GE OBJECT IDENTIFIER ::= { cevModuleC4xxxType 4 }
cevCat4kWsx45Sup7LE OBJECT IDENTIFIER ::= { cevModuleC4xxxType 5 }
cevCat4kWsx45Sup8e OBJECT IDENTIFIER ::= { cevModuleC4xxxType 6 }
cevNIM4gLteNA7354 OBJECT IDENTIFIER ::= { cevModuleC4xxxType 7 }
cevNIM4gLteGA7304 OBJECT IDENTIFIER ::= { cevModuleC4xxxType 8 }
cevNIM4gLteVZ7350 OBJECT IDENTIFIER ::= { cevModuleC4xxxType 9 }
cevNIM4gLteST7350 OBJECT IDENTIFIER ::= { cevModuleC4xxxType 10 }
cevNIM4gLteLA7430 OBJECT IDENTIFIER ::= { cevModuleC4xxxType 13 }
cevNIM4gLteALA7430 OBJECT IDENTIFIER ::= { cevModuleC4xxxType 14 }
cevNIM4gLteAEA7455 OBJECT IDENTIFIER ::= { cevModuleC4xxxType 15 }
cevModuleAS5200Type OBJECT IDENTIFIER ::= { cevModule 9 }
cevAS5200Carrier OBJECT IDENTIFIER ::= { cevModuleAS5200Type 1 }
cevAS5200DtdCarrier OBJECT IDENTIFIER ::= { cevModuleAS5200Type 2 }
cevPmAS5xxx12m56k OBJECT IDENTIFIER ::= { cevModuleAS5200Type 3 }
cevPmAS5xxx12mV110 OBJECT IDENTIFIER ::= { cevModuleAS5200Type 4 }
cevModuleC25xxType OBJECT IDENTIFIER ::= { cevModule 10 }
cevModuleAS5300Type OBJECT IDENTIFIER ::= { cevModule 11 }
cevAS53004ct1   OBJECT IDENTIFIER ::= { cevModuleAS5300Type 1 }
cevAS53004ce1   OBJECT IDENTIFIER ::= { cevModuleAS5300Type 2 }
cevPmDtdCarrier OBJECT IDENTIFIER ::= { cevModuleAS5300Type 3 }
cevPmDtd6m      OBJECT IDENTIFIER ::= { cevModuleAS5300Type 4 }
cevAS5300Carrier OBJECT IDENTIFIER ::= { cevModuleAS5300Type 5 }
cevPmAS5xxx12m  OBJECT IDENTIFIER ::= { cevModuleAS5300Type 6 }
cevAS5300VoiceCarrierCard OBJECT IDENTIFIER ::= { cevModuleAS5300Type 7 }
cevAS5300Dspmc542 OBJECT IDENTIFIER ::= { cevModuleAS5300Type 8 }
cevAS5300Dsp    OBJECT IDENTIFIER ::= { cevModuleAS5300Type 9 }
cevAS5300PmDtd12m OBJECT IDENTIFIER ::= { cevModuleAS5300Type 10 }
cevAS53008ct14t OBJECT IDENTIFIER ::= { cevModuleAS5300Type 11 }
cevAS53008ce14t OBJECT IDENTIFIER ::= { cevModuleAS5300Type 12 }
cevAS53004ct14t OBJECT IDENTIFIER ::= { cevModuleAS5300Type 13 }
cevAS53004ce14t OBJECT IDENTIFIER ::= { cevModuleAS5300Type 14 }
cevAS5300Amazon2Carrier OBJECT IDENTIFIER ::= { cevModuleAS5300Type 15 }
cevAS5300Dspm6c549 OBJECT IDENTIFIER ::= { cevModuleAS5300Type 16 }
cevModuleAS5800Type OBJECT IDENTIFIER ::= { cevModule 12 }
cevMAs5800Dsc   OBJECT IDENTIFIER ::= { cevModuleAS5800Type 1 }
cevMAs5800E1    OBJECT IDENTIFIER ::= { cevModuleAS5800Type 2 }
cevMAs5800T1    OBJECT IDENTIFIER ::= { cevModuleAS5800Type 3 }
cevMAs5800MicaHmm OBJECT IDENTIFIER ::= { cevModuleAS5800Type 4 }
cevMAs5800T3    OBJECT IDENTIFIER ::= { cevModuleAS5800Type 5 }
cevMAs5800FeDsi OBJECT IDENTIFIER ::= { cevModuleAS5800Type 6 }
cevMAs5800MicaDmm OBJECT IDENTIFIER ::= { cevModuleAS5800Type 7 }
cevMAs5800Vcc   OBJECT IDENTIFIER ::= { cevModuleAS5800Type 8 }
cevMAs5800Dspm6c549 OBJECT IDENTIFIER ::= { cevModuleAS5800Type 9 }
cevMAs5800Dsp   OBJECT IDENTIFIER ::= { cevModuleAS5800Type 10 }
cevModuleFabricType OBJECT IDENTIFIER ::= { cevModule 14 }
cev12012Sfc     OBJECT IDENTIFIER ::= { cevModuleFabricType 3 }
cev12012Csc     OBJECT IDENTIFIER ::= { cevModuleFabricType 4 }
cev12008Sfc8    OBJECT IDENTIFIER ::= { cevModuleFabricType 5 }
cev12008Csc8    OBJECT IDENTIFIER ::= { cevModuleFabricType 6 }
cev12016Sfc16   OBJECT IDENTIFIER ::= { cevModuleFabricType 7 }
cev12016Csc16   OBJECT IDENTIFIER ::= { cevModuleFabricType 8 }
cev12016Sfc16Oc192 OBJECT IDENTIFIER ::= { cevModuleFabricType 9 }
cev12016Csc16Oc192 OBJECT IDENTIFIER ::= { cevModuleFabricType 10 }
cev12010Sfc10   OBJECT IDENTIFIER ::= { cevModuleFabricType 11 }
cev12010Csc10   OBJECT IDENTIFIER ::= { cevModuleFabricType 12 }
cev12406Sfc6    OBJECT IDENTIFIER ::= { cevModuleFabricType 13 }
cev12406Csc6    OBJECT IDENTIFIER ::= { cevModuleFabricType 14 }
cev12410Sfc10   OBJECT IDENTIFIER ::= { cevModuleFabricType 15 }
cev12410Csc10   OBJECT IDENTIFIER ::= { cevModuleFabricType 16 }
cev12404Csc64   OBJECT IDENTIFIER ::= { cevModuleFabricType 17 }
cev12816Csc16Oc768 OBJECT IDENTIFIER ::= { cevModuleFabricType 18 }
cev12810Csc10Oc768 OBJECT IDENTIFIER ::= { cevModuleFabricType 19 }
cev12810Sfc10Oc768 OBJECT IDENTIFIER ::= { cevModuleFabricType 20 }
cev12816Sfc16Oc768 OBJECT IDENTIFIER ::= { cevModuleFabricType 21 }
cev12006CscAdvncd OBJECT IDENTIFIER ::= { cevModuleFabricType 22 }
cev12010CscAdvncd OBJECT IDENTIFIER ::= { cevModuleFabricType 23 }
cev12016CscAdvncd OBJECT IDENTIFIER ::= { cevModuleFabricType 24 }
cev12006SfcAdvncd OBJECT IDENTIFIER ::= { cevModuleFabricType 25 }
cev12010SfcAdvncd OBJECT IDENTIFIER ::= { cevModuleFabricType 26 }
cev12016SfcAdvncd OBJECT IDENTIFIER ::= { cevModuleFabricType 27 }
cev12004FabAdvncd OBJECT IDENTIFIER ::= { cevModuleFabricType 28 }
cev12816Csc16Oc768B OBJECT IDENTIFIER ::= { cevModuleFabricType 29 }
cev12810Csc10Oc768B OBJECT IDENTIFIER ::= { cevModuleFabricType 30 }
cevModuleFabricTypeAsic OBJECT IDENTIFIER ::= { cevModuleFabricType 45 }
cevModuleDaughterCard OBJECT IDENTIFIER ::= { cevModule 15 }
cevDslamNi2Controller OBJECT IDENTIFIER ::= { cevModuleDaughterCard 4 }
cevWvic2dsuE1DiG703 OBJECT IDENTIFIER ::= { cevModuleDaughterCard 5 }
cevWvic1dsuE1G703 OBJECT IDENTIFIER ::= { cevModuleDaughterCard 6 }
cevDspmPvdm3    OBJECT IDENTIFIER ::= { cevModuleDaughterCard 7 }
cevDspmPvdm1    OBJECT IDENTIFIER ::= { cevModuleDaughterCard 12 }
cevDspmPvdm2    OBJECT IDENTIFIER ::= { cevModuleDaughterCard 13 }
cevDspmPvdm4    OBJECT IDENTIFIER ::= { cevModuleDaughterCard 14 }
cevDspmPvdm5    OBJECT IDENTIFIER ::= { cevModuleDaughterCard 15 }
cevHdaEm10fxs   OBJECT IDENTIFIER ::= { cevModuleDaughterCard 17 }
cevHdaEm4dsp    OBJECT IDENTIFIER ::= { cevModuleDaughterCard 18 }
cevC7300Nse100Db OBJECT IDENTIFIER ::= { cevModuleDaughterCard 19 }
cevCeScsi2636   OBJECT IDENTIFIER ::= { cevModuleDaughterCard 24 }
cevCeIde2636    OBJECT IDENTIFIER ::= { cevModuleDaughterCard 25 }
cevVic4vpFxs4Did OBJECT IDENTIFIER ::= { cevModuleDaughterCard 26 }
cevC7300Nse100PlusDb OBJECT IDENTIFIER ::= { cevModuleDaughterCard 27 }
cevModuleCat4000DaughterCardType OBJECT IDENTIFIER ::= { cevModuleDaughterCard 28 }
cevCat4kDCWsf4531 OBJECT IDENTIFIER ::= { cevModuleCat4000DaughterCardType 1 }
cevCat4kDCWsu4504FxMt OBJECT IDENTIFIER ::= { cevModuleCat4000DaughterCardType 2 }
cevVwic2Mft1T1E1 OBJECT IDENTIFIER ::= { cevModuleDaughterCard 29 }
cevVwic2Mft1G703 OBJECT IDENTIFIER ::= { cevModuleDaughterCard 30 }
cevVwic2Mft2T1E1 OBJECT IDENTIFIER ::= { cevModuleDaughterCard 31 }
cevVwic2Mft2G703 OBJECT IDENTIFIER ::= { cevModuleDaughterCard 32 }
cevEcMft32      OBJECT IDENTIFIER ::= { cevModuleDaughterCard 33 }
cevEcMft64      OBJECT IDENTIFIER ::= { cevModuleDaughterCard 34 }
cevEm4Fxs4Fxo   OBJECT IDENTIFIER ::= { cevModuleDaughterCard 35 }
cevEm6Fxo       OBJECT IDENTIFIER ::= { cevModuleDaughterCard 36 }
cevEm4BriNtTe   OBJECT IDENTIFIER ::= { cevModuleDaughterCard 37 }
cevpvdm2dsphalf OBJECT IDENTIFIER ::= { cevModuleDaughterCard 38 }
cevpvdm2dsp4    OBJECT IDENTIFIER ::= { cevModuleDaughterCard 39 }
cevpvdm2dsp3    OBJECT IDENTIFIER ::= { cevModuleDaughterCard 40 }
cevpvdm2dsp2    OBJECT IDENTIFIER ::= { cevModuleDaughterCard 41 }
cevpvdm2dsp1    OBJECT IDENTIFIER ::= { cevModuleDaughterCard 42 }
cevpvdm2hwecan3 OBJECT IDENTIFIER ::= { cevModuleDaughterCard 43 }
cevpvdm2hwecan2 OBJECT IDENTIFIER ::= { cevModuleDaughterCard 44 }
cevpvdm2hwecan1 OBJECT IDENTIFIER ::= { cevModuleDaughterCard 45 }
cevNetworkProcessor OBJECT IDENTIFIER ::= { cevModuleDaughterCard 46 }
cevVic2Mft1T1E1 OBJECT IDENTIFIER ::= { cevModuleDaughterCard 47 }
cevVic2Mft2T1E1 OBJECT IDENTIFIER ::= { cevModuleDaughterCard 48 }
cevEm2Hda4Fxo   OBJECT IDENTIFIER ::= { cevModuleDaughterCard 49 }
cevVic1J1       OBJECT IDENTIFIER ::= { cevModuleDaughterCard 50 }
cevWic1amV2     OBJECT IDENTIFIER ::= { cevModuleDaughterCard 51 }
cevWic2amV2     OBJECT IDENTIFIER ::= { cevModuleDaughterCard 52 }
cevPvdmII12dm   OBJECT IDENTIFIER ::= { cevModuleDaughterCard 53 }
cevVwic2T1E1Ran OBJECT IDENTIFIER ::= { cevModuleDaughterCard 59 }
cev7300Nse150Db OBJECT IDENTIFIER ::= { cevModuleDaughterCard 60 }
cevVic3Em2      OBJECT IDENTIFIER ::= { cevModuleDaughterCard 61 }
cevVic3FxsDid2  OBJECT IDENTIFIER ::= { cevModuleDaughterCard 62 }
cevVic3FxsDid4  OBJECT IDENTIFIER ::= { cevModuleDaughterCard 63 }
cevHdaEm3FxsDid8 OBJECT IDENTIFIER ::= { cevModuleDaughterCard 64 }
cev1DOCSIS20CableModemDC OBJECT IDENTIFIER ::= { cevModuleDaughterCard 65 }
cev1DOCSIS20CableModemDCEJ OBJECT IDENTIFIER ::= { cevModuleDaughterCard 66 }
cevAsmM2900Top  OBJECT IDENTIFIER ::= { cevModuleDaughterCard 67 }
cevVic3FxsEDid2 OBJECT IDENTIFIER ::= { cevModuleDaughterCard 68 }
cevModuleASR9KLCDb OBJECT IDENTIFIER ::= { cevModuleDaughterCard 69 }
cevModemWan3g   OBJECT IDENTIFIER ::= { cevModuleDaughterCard 70 }
cevModulePVDM3c64 OBJECT IDENTIFIER ::= { cevModuleDaughterCard 73 }
cevModulePVDM3c32 OBJECT IDENTIFIER ::= { cevModuleDaughterCard 74 }
cevModulePVDM3c128 OBJECT IDENTIFIER ::= { cevModuleDaughterCard 75 }
cevModulePVDM3c192 OBJECT IDENTIFIER ::= { cevModuleDaughterCard 76 }
cevModulePVDM3c256 OBJECT IDENTIFIER ::= { cevModuleDaughterCard 77 }
cevNM2838       OBJECT IDENTIFIER ::= { cevModuleDaughterCard 78 }
cevPANO2838     OBJECT IDENTIFIER ::= { cevModuleDaughterCard 79 }
cevVwic3Mft4T1E1 OBJECT IDENTIFIER ::= { cevModuleDaughterCard 82 }
cevVwic3Mft1T1E1 OBJECT IDENTIFIER ::= { cevModuleDaughterCard 83 }
cevVwic3Mft1G703 OBJECT IDENTIFIER ::= { cevModuleDaughterCard 84 }
cevVwic3Mft2T1E1 OBJECT IDENTIFIER ::= { cevModuleDaughterCard 85 }
cevVwic3Mft2G703 OBJECT IDENTIFIER ::= { cevModuleDaughterCard 86 }
cevPrp3Smdc     OBJECT IDENTIFIER ::= { cevModuleDaughterCard 87 }
cevModemWan4g   OBJECT IDENTIFIER ::= { cevModuleDaughterCard 88 }
cevMdcC6880xPfc OBJECT IDENTIFIER ::= { cevModuleDaughterCard 89 }
cevMdcC6880xlePfc OBJECT IDENTIFIER ::= { cevModuleDaughterCard 90 }
cevMdcC6880xDfc OBJECT IDENTIFIER ::= { cevModuleDaughterCard 91 }
cevMdcC6880xleDfc OBJECT IDENTIFIER ::= { cevModuleDaughterCard 92 }
cevPWic1AmV2    OBJECT IDENTIFIER ::= { cevModuleDaughterCard 93 }
cevPVwic3Mft1G703 OBJECT IDENTIFIER ::= { cevModuleDaughterCard 94 }
cevPVwic3Mft1T1E1 OBJECT IDENTIFIER ::= { cevModuleDaughterCard 95 }
cevPVwic3Mft2G703 OBJECT IDENTIFIER ::= { cevModuleDaughterCard 96 }
cevPVwic3Mft2T1E1 OBJECT IDENTIFIER ::= { cevModuleDaughterCard 97 }
cevPVwic3Mft4T1E1 OBJECT IDENTIFIER ::= { cevModuleDaughterCard 98 }
cevModulePPVDM3c128 OBJECT IDENTIFIER ::= { cevModuleDaughterCard 99 }
cevModulePPVDM3c16 OBJECT IDENTIFIER ::= { cevModuleDaughterCard 100 }
cevModulePPVDM3c192 OBJECT IDENTIFIER ::= { cevModuleDaughterCard 101 }
cevModulePPVDM3c256 OBJECT IDENTIFIER ::= { cevModuleDaughterCard 102 }
cevModulePPVDM3c32 OBJECT IDENTIFIER ::= { cevModuleDaughterCard 103 }
cevModulePPVDM3c64 OBJECT IDENTIFIER ::= { cevModuleDaughterCard 104 }
cevPVic3Em2     OBJECT IDENTIFIER ::= { cevModuleDaughterCard 105 }
cevPVic3Fxs2Did OBJECT IDENTIFIER ::= { cevModuleDaughterCard 106 }
cevPVic3Fxs4Did OBJECT IDENTIFIER ::= { cevModuleDaughterCard 107 }
cevCbr8Gemini1  OBJECT IDENTIFIER ::= { cevModuleDaughterCard 112 }
cevCbr8Gemini2  OBJECT IDENTIFIER ::= { cevModuleDaughterCard 113 }
cevCbr8Leoben1  OBJECT IDENTIFIER ::= { cevModuleDaughterCard 114 }
cevCbr8Leoben3  OBJECT IDENTIFIER ::= { cevModuleDaughterCard 115 }
cevCbr8SupDc    OBJECT IDENTIFIER ::= { cevModuleDaughterCard 116 }
cevCbr8SupPicDc OBJECT IDENTIFIER ::= { cevModuleDaughterCard 117 }
cevCat4kWsuaSup9e OBJECT IDENTIFIER ::= { cevModuleDaughterCard 118 }
cevModuleGBICs  OBJECT IDENTIFIER ::= { cevModule 16 }
cevMGBIC1000BaseLX OBJECT IDENTIFIER ::= { cevModuleGBICs 1 }
cevMGBIC1000BaseSX OBJECT IDENTIFIER ::= { cevModuleGBICs 2 }
cevMGBIC1000BaseCX OBJECT IDENTIFIER ::= { cevModuleGBICs 3 }
cevMGBIC1000BaseLH OBJECT IDENTIFIER ::= { cevModuleGBICs 4 }
cevMGBIC1000BaseZX OBJECT IDENTIFIER ::= { cevModuleGBICs 5 }
cevMGBIC1000BaseCXSTACK OBJECT IDENTIFIER ::= { cevModuleGBICs 6 }
cevMGBIC1000BaseT OBJECT IDENTIFIER ::= { cevModuleGBICs 7 }
cevMGBICDWDM6061 OBJECT IDENTIFIER ::= { cevModuleGBICs 16 }
cevMGBICDWDM5979 OBJECT IDENTIFIER ::= { cevModuleGBICs 17 }
cevMGBICDWDM5898 OBJECT IDENTIFIER ::= { cevModuleGBICs 18 }
cevMGBICDWDM5817 OBJECT IDENTIFIER ::= { cevModuleGBICs 19 }
cevMGBICDWDM5655 OBJECT IDENTIFIER ::= { cevModuleGBICs 20 }
cevMGBICDWDM5575 OBJECT IDENTIFIER ::= { cevModuleGBICs 21 }
cevMGBICDWDM5494 OBJECT IDENTIFIER ::= { cevModuleGBICs 22 }
cevMGBICDWDM5413 OBJECT IDENTIFIER ::= { cevModuleGBICs 23 }
cevMGBICDWDM5252 OBJECT IDENTIFIER ::= { cevModuleGBICs 24 }
cevMGBICDWDM5172 OBJECT IDENTIFIER ::= { cevModuleGBICs 25 }
cevMGBICDWDM5092 OBJECT IDENTIFIER ::= { cevModuleGBICs 26 }
cevMGBICDWDM5012 OBJECT IDENTIFIER ::= { cevModuleGBICs 27 }
cevMGBICDWDM4851 OBJECT IDENTIFIER ::= { cevModuleGBICs 28 }
cevMGBICDWDM4772 OBJECT IDENTIFIER ::= { cevModuleGBICs 29 }
cevMGBICDWDM4692 OBJECT IDENTIFIER ::= { cevModuleGBICs 30 }
cevMGBICDWDM4612 OBJECT IDENTIFIER ::= { cevModuleGBICs 31 }
cevMGBICDWDM4453 OBJECT IDENTIFIER ::= { cevModuleGBICs 32 }
cevMGBICDWDM4373 OBJECT IDENTIFIER ::= { cevModuleGBICs 33 }
cevMGBICDWDM4294 OBJECT IDENTIFIER ::= { cevModuleGBICs 34 }
cevMGBICDWDM4214 OBJECT IDENTIFIER ::= { cevModuleGBICs 35 }
cevMGBICDWDM4056 OBJECT IDENTIFIER ::= { cevModuleGBICs 36 }
cevMGBICDWDM3977 OBJECT IDENTIFIER ::= { cevModuleGBICs 37 }
cevMGBICDWDM3898 OBJECT IDENTIFIER ::= { cevModuleGBICs 38 }
cevMGBICDWDM3819 OBJECT IDENTIFIER ::= { cevModuleGBICs 39 }
cevMGBICDWDM3661 OBJECT IDENTIFIER ::= { cevModuleGBICs 40 }
cevMGBICDWDM3582 OBJECT IDENTIFIER ::= { cevModuleGBICs 41 }
cevMGBICDWDM3504 OBJECT IDENTIFIER ::= { cevModuleGBICs 42 }
cevMGBICDWDM3425 OBJECT IDENTIFIER ::= { cevModuleGBICs 43 }
cevMGBICDWDM3268 OBJECT IDENTIFIER ::= { cevModuleGBICs 44 }
cevMGBICDWDM3190 OBJECT IDENTIFIER ::= { cevModuleGBICs 45 }
cevMGBICDWDM3112 OBJECT IDENTIFIER ::= { cevModuleGBICs 46 }
cevMGBICDWDM3033 OBJECT IDENTIFIER ::= { cevModuleGBICs 47 }
cevMGBICXWDMRxOnly OBJECT IDENTIFIER ::= { cevModuleGBICs 48 }
cevMGBIC1490BaseBX10D OBJECT IDENTIFIER ::= { cevModuleGBICs 49 }
cevMGBIC1310BaseBX10U OBJECT IDENTIFIER ::= { cevModuleGBICs 50 }
cevMGBICDWDM6141 OBJECT IDENTIFIER ::= { cevModuleGBICs 51 }
cevMGBICDWDM5736 OBJECT IDENTIFIER ::= { cevModuleGBICs 52 }
cevMGBICDWDM5332 OBJECT IDENTIFIER ::= { cevModuleGBICs 53 }
cevMGBICDWDM4931 OBJECT IDENTIFIER ::= { cevModuleGBICs 54 }
cevMGBICDWDM4532 OBJECT IDENTIFIER ::= { cevModuleGBICs 55 }
cevMGBICDWDM4134 OBJECT IDENTIFIER ::= { cevModuleGBICs 56 }
cevMGBICDWDM3739 OBJECT IDENTIFIER ::= { cevModuleGBICs 57 }
cevMGBICDWDM3346 OBJECT IDENTIFIER ::= { cevModuleGBICs 58 }
cevModuleC6xxxType OBJECT IDENTIFIER ::= { cevModule 17 }
cevC6xxxSlcCap8 OBJECT IDENTIFIER ::= { cevModuleC6xxxType 1 }
cevC6xxxNtcOc3si OBJECT IDENTIFIER ::= { cevModuleC6xxxType 2 }
cevC6xxxNtcOc3mm OBJECT IDENTIFIER ::= { cevModuleC6xxxType 3 }
cevC6xxxNtcStm1si OBJECT IDENTIFIER ::= { cevModuleC6xxxType 4 }
cevC6xxxNtcStm1mm OBJECT IDENTIFIER ::= { cevModuleC6xxxType 5 }
cevC6xxxSlcDmt8 OBJECT IDENTIFIER ::= { cevModuleC6xxxType 6 }
cevC6xxxSlcDmt16 OBJECT IDENTIFIER ::= { cevModuleC6xxxType 7 }
cevC6xxxNtcDs3  OBJECT IDENTIFIER ::= { cevModuleC6xxxType 8 }
cevC6xxxOsm1Oc48PosSs OBJECT IDENTIFIER ::= { cevModuleC6xxxType 10 }
cevC6xxxOsm1Oc48PosSl OBJECT IDENTIFIER ::= { cevModuleC6xxxType 11 }
cevC6xxxOsm1Oc48PosSi OBJECT IDENTIFIER ::= { cevModuleC6xxxType 12 }
cevC6xxxOsm2Oc12PosSl OBJECT IDENTIFIER ::= { cevModuleC6xxxType 15 }
cevC6xxxOsm4Oc12PosSl OBJECT IDENTIFIER ::= { cevModuleC6xxxType 16 }
cevC6xxxOsm2Oc12PosMm OBJECT IDENTIFIER ::= { cevModuleC6xxxType 17 }
cevC6xxxOsm4Oc12PosMm OBJECT IDENTIFIER ::= { cevModuleC6xxxType 18 }
cevC6xxxOsm2Oc12PosSi OBJECT IDENTIFIER ::= { cevModuleC6xxxType 19 }
cevC6xxxOsm4Oc12PosSi OBJECT IDENTIFIER ::= { cevModuleC6xxxType 20 }
cevC6xxxOsm8Oc3PosSi OBJECT IDENTIFIER ::= { cevModuleC6xxxType 21 }
cevC6xxxOsm16Oc3PosSi OBJECT IDENTIFIER ::= { cevModuleC6xxxType 22 }
cevC6xxxOsm8Oc3PosMm OBJECT IDENTIFIER ::= { cevModuleC6xxxType 23 }
cevC6xxxOsm16Oc3PosMm OBJECT IDENTIFIER ::= { cevModuleC6xxxType 24 }
cevC6xxxOsm8Oc3PosSl OBJECT IDENTIFIER ::= { cevModuleC6xxxType 25 }
cevC6xxxOsm16Oc3PosSl OBJECT IDENTIFIER ::= { cevModuleC6xxxType 26 }
cevC6xxx4GeWanGbic OBJECT IDENTIFIER ::= { cevModuleC6xxxType 27 }
cevC6xxxOsm4ge4oc12ChDs3SmIr OBJECT IDENTIFIER ::= { cevModuleC6xxxType 31 }
cevC6xxxOsm4ge8oc12ChDs3SmIr OBJECT IDENTIFIER ::= { cevModuleC6xxxType 32 }
cevC6xxxOsm4geoc48ChDs3SmSr OBJECT IDENTIFIER ::= { cevModuleC6xxxType 33 }
ceC6xxxOsm4ge2oc48ChDs3SmSr OBJECT IDENTIFIER ::= { cevModuleC6xxxType 34 }
cevC6xxxOsm4geoc48ChDs3SmIr OBJECT IDENTIFIER ::= { cevModuleC6xxxType 35 }
cevC6xxxOsm4ge2oc48ChDs3SmIr OBJECT IDENTIFIER ::= { cevModuleC6xxxType 36 }
cevC6xxxOsm4geoc12ChDs3SmIr OBJECT IDENTIFIER ::= { cevModuleC6xxxType 37 }
cevC6xxxOsm4ge2oc12ChDs3SmIr OBJECT IDENTIFIER ::= { cevModuleC6xxxType 38 }
cevC6xxxOsm2Oc12AtmMmPlus OBJECT IDENTIFIER ::= { cevModuleC6xxxType 40 }
cevC6xxxOsm2Oc12AtmSiPlus OBJECT IDENTIFIER ::= { cevModuleC6xxxType 41 }
cevC6xxx4GeWanGbicPlus OBJECT IDENTIFIER ::= { cevModuleC6xxxType 42 }
cevC6xxxOsm1Oc48PosSsPlus OBJECT IDENTIFIER ::= { cevModuleC6xxxType 43 }
cevC6xxxOsm1Oc48PosSiPlus OBJECT IDENTIFIER ::= { cevModuleC6xxxType 44 }
cevC6xxxOsm1Oc48PosSlPlus OBJECT IDENTIFIER ::= { cevModuleC6xxxType 45 }
cevC6xxxOsm4Oc12PosSiPlus OBJECT IDENTIFIER ::= { cevModuleC6xxxType 46 }
cevC6xxxOsm2Oc12PosMmPlus OBJECT IDENTIFIER ::= { cevModuleC6xxxType 47 }
cevC6xxxOsm4Oc3PosSiPlus OBJECT IDENTIFIER ::= { cevModuleC6xxxType 48 }
cevC6xxxOsm8Oc3PosSiPlus OBJECT IDENTIFIER ::= { cevModuleC6xxxType 49 }
cevC6xxxOsm8Oc3PosSlPlus OBJECT IDENTIFIER ::= { cevModuleC6xxxType 50 }
cevC6xxxOsm16Oc3PosSiPlus OBJECT IDENTIFIER ::= { cevModuleC6xxxType 51 }
cevC6xxxOsm12Ct3T1 OBJECT IDENTIFIER ::= { cevModuleC6xxxType 52 }
cevC6xxxCwpa2   OBJECT IDENTIFIER ::= { cevModuleC6xxxType 53 }
cevC6xxxSIP200  OBJECT IDENTIFIER ::= { cevModuleC6xxxType 54 }
cevC6xxxSIP400  OBJECT IDENTIFIER ::= { cevModuleC6xxxType 55 }
cevC6xxxSIP600  OBJECT IDENTIFIER ::= { cevModuleC6xxxType 56 }
cevC6xxxOsm2Oc12PosSiPlus OBJECT IDENTIFIER ::= { cevModuleC6xxxType 57 }
cevC6xxxOsm4Oc3PosSi OBJECT IDENTIFIER ::= { cevModuleC6xxxType 58 }
cevC6xxxOsm4Oc3PosSl OBJECT IDENTIFIER ::= { cevModuleC6xxxType 59 }
cevC6xxxOsm4Oc3PosMm OBJECT IDENTIFIER ::= { cevModuleC6xxxType 60 }
cevC6xxxOsm24Ct3T1 OBJECT IDENTIFIER ::= { cevModuleC6xxxType 61 }
cevCat6kWsx6600 OBJECT IDENTIFIER ::= { cevModuleC6xxxType 62 }
cevC6xxxSSC600  OBJECT IDENTIFIER ::= { cevModuleC6xxxType 63 }
cevC6xxxSSC400  OBJECT IDENTIFIER ::= { cevModuleC6xxxType 64 }
cevC6xxxRSP720Base OBJECT IDENTIFIER ::= { cevModuleC6xxxType 65 }
cevC6xxxRSP32GEBase OBJECT IDENTIFIER ::= { cevModuleC6xxxType 66 }
cevC6xxxRSP3210GEBase OBJECT IDENTIFIER ::= { cevModuleC6xxxType 67 }
cevC6xxxRSP720  OBJECT IDENTIFIER ::= { cevModuleC6xxxType 68 }
cevC6xxxRSP32   OBJECT IDENTIFIER ::= { cevModuleC6xxxType 69 }
cevC6xxxSIP600DC OBJECT IDENTIFIER ::= { cevModuleC6xxxType 71 }
cevC6xxxRSP720MsfcNaboo OBJECT IDENTIFIER ::= { cevModuleC6xxxType 72 }
cevC6xxxRSP720PfcGanges OBJECT IDENTIFIER ::= { cevModuleC6xxxType 73 }
cevC6xxxEsm20G  OBJECT IDENTIFIER ::= { cevModuleC6xxxType 74 }
cevC6xxxEsm20GCpuDc OBJECT IDENTIFIER ::= { cevModuleC6xxxType 75 }
cevC6xxxEsm20GPfc3CxlDc OBJECT IDENTIFIER ::= { cevModuleC6xxxType 76 }
cevC6xxxEsm20GPfc3CDc OBJECT IDENTIFIER ::= { cevModuleC6xxxType 77 }
cevC6xxxEsm20G2x10gDc OBJECT IDENTIFIER ::= { cevModuleC6xxxType 78 }
cevC6xxxEsm20G20x1gDc OBJECT IDENTIFIER ::= { cevModuleC6xxxType 79 }
cevC6xxxRSP72010GEBase OBJECT IDENTIFIER ::= { cevModuleC6xxxType 80 }
cevC6xxxEs20C3c OBJECT IDENTIFIER ::= { cevModuleC6xxxType 81 }
cevC6xxxEs40C3c OBJECT IDENTIFIER ::= { cevModuleC6xxxType 82 }
cevC6xxxEs20C3cxl OBJECT IDENTIFIER ::= { cevModuleC6xxxType 83 }
cevC6xxxEs40C3cxl OBJECT IDENTIFIER ::= { cevModuleC6xxxType 84 }
cevC6xxxEs20G3c OBJECT IDENTIFIER ::= { cevModuleC6xxxType 85 }
cevC6xxxEs2Tg3c OBJECT IDENTIFIER ::= { cevModuleC6xxxType 86 }
cevC6xxxEs40G3c OBJECT IDENTIFIER ::= { cevModuleC6xxxType 87 }
cevC6xxxEs4Tg3c OBJECT IDENTIFIER ::= { cevModuleC6xxxType 88 }
cevC6xxxEs20G3cxl OBJECT IDENTIFIER ::= { cevModuleC6xxxType 89 }
cevC6xxxEs2Tg3cxl OBJECT IDENTIFIER ::= { cevModuleC6xxxType 90 }
cevC6xxxEs40G3cxl OBJECT IDENTIFIER ::= { cevModuleC6xxxType 91 }
cevC6xxxEs4Tg3cxl OBJECT IDENTIFIER ::= { cevModuleC6xxxType 92 }
cevC6xxxMsfc4   OBJECT IDENTIFIER ::= { cevModuleC6xxxType 93 }
cevC6xxxPfc3c   OBJECT IDENTIFIER ::= { cevModuleC6xxxType 94 }
cevC6xxxPfc3cxl OBJECT IDENTIFIER ::= { cevModuleC6xxxType 95 }
cevC6xxxEs2Tg20GDc OBJECT IDENTIFIER ::= { cevModuleC6xxxType 96 }
cevC6xxxEs1Tg10GDc OBJECT IDENTIFIER ::= { cevModuleC6xxxType 97 }
cevC6xxxEsBase  OBJECT IDENTIFIER ::= { cevModuleC6xxxType 98 }
cevC6xxxEsPfc3CxlDc OBJECT IDENTIFIER ::= { cevModuleC6xxxType 99 }
cevC6xxxEsPfc3CDc OBJECT IDENTIFIER ::= { cevModuleC6xxxType 100 }
cevC6xxxEs20GDc OBJECT IDENTIFIER ::= { cevModuleC6xxxType 101 }
cevC6xxxEs2TgDc OBJECT IDENTIFIER ::= { cevModuleC6xxxType 102 }
cevC6xxxEs40GDc OBJECT IDENTIFIER ::= { cevModuleC6xxxType 103 }
cevC6xxxEs4TgDc OBJECT IDENTIFIER ::= { cevModuleC6xxxType 104 }
cevC6xxxEsItu2TgDc OBJECT IDENTIFIER ::= { cevModuleC6xxxType 105 }
cevC6xxxEsItu4TgDc OBJECT IDENTIFIER ::= { cevModuleC6xxxType 106 }
cevC6xxxEsItu2Tg3cxl OBJECT IDENTIFIER ::= { cevModuleC6xxxType 107 }
cevC6xxxEsItu4Tg3cxl OBJECT IDENTIFIER ::= { cevModuleC6xxxType 108 }
cevC6xxxEsT     OBJECT IDENTIFIER ::= { cevModuleC6xxxType 109 }
cevC6xxxEsItu2Tg3c OBJECT IDENTIFIER ::= { cevModuleC6xxxType 110 }
cevC6xxxEsItu4Tg3c OBJECT IDENTIFIER ::= { cevModuleC6xxxType 111 }
cevC6xxxEst20gDc OBJECT IDENTIFIER ::= { cevModuleC6xxxType 112 }
cevC6xxxEst40gDc OBJECT IDENTIFIER ::= { cevModuleC6xxxType 113 }
cevC6xxxEstItu2tgDc OBJECT IDENTIFIER ::= { cevModuleC6xxxType 114 }
cevC6xxxEstItu4tgDc OBJECT IDENTIFIER ::= { cevModuleC6xxxType 115 }
cevC6xxxEst20G3Cxl OBJECT IDENTIFIER ::= { cevModuleC6xxxType 116 }
cevC6xxxEst40G3Cxl OBJECT IDENTIFIER ::= { cevModuleC6xxxType 117 }
cevC6xxxEstItu2TG3Cxl OBJECT IDENTIFIER ::= { cevModuleC6xxxType 118 }
cevC6xxxEstItu4TG3Cxl OBJECT IDENTIFIER ::= { cevModuleC6xxxType 119 }
cevC6xxxEsTXc20G OBJECT IDENTIFIER ::= { cevModuleC6xxxType 120 }
cevC6xxxEsTXc40G OBJECT IDENTIFIER ::= { cevModuleC6xxxType 121 }
cevC6xxxEsT8Tg  OBJECT IDENTIFIER ::= { cevModuleC6xxxType 122 }
cevC6xxxEsXt8TG OBJECT IDENTIFIER ::= { cevModuleC6xxxType 123 }
cevC6xxxIA48FPD OBJECT IDENTIFIER ::= { cevModuleC6xxxType 124 }
cevC6xxxIA48TD  OBJECT IDENTIFIER ::= { cevModuleC6xxxType 125 }
cevModuleGsrType OBJECT IDENTIFIER ::= { cevModule 18 }
cevGsrOc12Chsts3Mm OBJECT IDENTIFIER ::= { cevModuleGsrType 1 }
cevGsrOc12Chsts3Sm OBJECT IDENTIFIER ::= { cevModuleGsrType 2 }
cevGsrQoc12Mm   OBJECT IDENTIFIER ::= { cevModuleGsrType 3 }
cevGsrQoc12Sm   OBJECT IDENTIFIER ::= { cevModuleGsrType 4 }
cevPosOc48SmLrFc OBJECT IDENTIFIER ::= { cevModuleGsrType 5 }
cevPosQoc3SmL   OBJECT IDENTIFIER ::= { cevModuleGsrType 6 }
cevPos8oc3Mm    OBJECT IDENTIFIER ::= { cevModuleGsrType 7 }
cevPos8oc3Ir    OBJECT IDENTIFIER ::= { cevModuleGsrType 8 }
cevPos8oc3Lr    OBJECT IDENTIFIER ::= { cevModuleGsrType 9 }
cevPos16oc3Mm   OBJECT IDENTIFIER ::= { cevModuleGsrType 10 }
cevPos16oc3Ir   OBJECT IDENTIFIER ::= { cevModuleGsrType 11 }
cevPos16oc3Lr   OBJECT IDENTIFIER ::= { cevModuleGsrType 12 }
cevGsr8feTx     OBJECT IDENTIFIER ::= { cevModuleGsrType 13 }
cevGsr8feFx     OBJECT IDENTIFIER ::= { cevModuleGsrType 14 }
cevSsrpOc48SmSr OBJECT IDENTIFIER ::= { cevModuleGsrType 15 }
cevSsrpOc48SmLr OBJECT IDENTIFIER ::= { cevModuleGsrType 16 }
cevPosQoc12SmLr OBJECT IDENTIFIER ::= { cevModuleGsrType 17 }
cevPosQoc12MmSr OBJECT IDENTIFIER ::= { cevModuleGsrType 18 }
cevPosOc48SmSrFc OBJECT IDENTIFIER ::= { cevModuleGsrType 19 }
cevPosOc48SmLrSc OBJECT IDENTIFIER ::= { cevModuleGsrType 20 }
cevPosOc48SmSrSc OBJECT IDENTIFIER ::= { cevModuleGsrType 21 }
cevSrpOc12SmIr  OBJECT IDENTIFIER ::= { cevModuleGsrType 22 }
cevSrpOc12SmLr  OBJECT IDENTIFIER ::= { cevModuleGsrType 23 }
cevSrpOc12Mm    OBJECT IDENTIFIER ::= { cevModuleGsrType 24 }
cevPosEnOc48SrSc OBJECT IDENTIFIER ::= { cevModuleGsrType 25 }
cevPosEnOc48SrFc OBJECT IDENTIFIER ::= { cevModuleGsrType 26 }
cevPosEnOc48LrSc OBJECT IDENTIFIER ::= { cevModuleGsrType 27 }
cevPosEnOc48LrFc OBJECT IDENTIFIER ::= { cevModuleGsrType 28 }
cevPosEnQoc12Sr OBJECT IDENTIFIER ::= { cevModuleGsrType 29 }
cevPosEnQoc12Ir OBJECT IDENTIFIER ::= { cevModuleGsrType 30 }
cevCopper6ds3   OBJECT IDENTIFIER ::= { cevModuleGsrType 31 }
cevCopper12ds3  OBJECT IDENTIFIER ::= { cevModuleGsrType 32 }
cevPosOc192SmIrFc OBJECT IDENTIFIER ::= { cevModuleGsrType 33 }
cevPosOc192SmSrFc OBJECT IDENTIFIER ::= { cevModuleGsrType 34 }
cevPosOc192SmIrSc OBJECT IDENTIFIER ::= { cevModuleGsrType 35 }
cevPosOc192SmSrSc OBJECT IDENTIFIER ::= { cevModuleGsrType 36 }
cevPos4Oc3Mm    OBJECT IDENTIFIER ::= { cevModuleGsrType 37 }
cevPos4Oc3Sm    OBJECT IDENTIFIER ::= { cevModuleGsrType 38 }
cevPosOc12Mm    OBJECT IDENTIFIER ::= { cevModuleGsrType 39 }
cevPosOc12Sm    OBJECT IDENTIFIER ::= { cevModuleGsrType 40 }
cevAtmOc12Mm    OBJECT IDENTIFIER ::= { cevModuleGsrType 41 }
cevAtmOc12Sm    OBJECT IDENTIFIER ::= { cevModuleGsrType 42 }
cevPosOc48MmL   OBJECT IDENTIFIER ::= { cevModuleGsrType 43 }
cevAtm4Oc3Sm    OBJECT IDENTIFIER ::= { cevModuleGsrType 44 }
cevAtm4Oc3Mm    OBJECT IDENTIFIER ::= { cevModuleGsrType 45 }
cevOc12ChDs3Mm  OBJECT IDENTIFIER ::= { cevModuleGsrType 46 }
cevOc12ChDs3Sm  OBJECT IDENTIFIER ::= { cevModuleGsrType 47 }
cevGsrGe        OBJECT IDENTIFIER ::= { cevModuleGsrType 48 }
cevGsr3ge       OBJECT IDENTIFIER ::= { cevModuleGsrType 49 }
cevGsrAlarm16   OBJECT IDENTIFIER ::= { cevModuleGsrType 50 }
cevGsrBusBoard16 OBJECT IDENTIFIER ::= { cevModuleGsrType 51 }
cevSrpOc12SmXr  OBJECT IDENTIFIER ::= { cevModuleGsrType 52 }
cevPosEnQoc12Mm OBJECT IDENTIFIER ::= { cevModuleGsrType 53 }
cevPosEnQoc48SmSrFc OBJECT IDENTIFIER ::= { cevModuleGsrType 54 }
cevPosEnQoc48SmSrSc OBJECT IDENTIFIER ::= { cevModuleGsrType 55 }
cevPosEnQoc48SmLrSc OBJECT IDENTIFIER ::= { cevModuleGsrType 56 }
cevPosEnQoc48SmLrFc OBJECT IDENTIFIER ::= { cevModuleGsrType 57 }
cevGsr6Ct3      OBJECT IDENTIFIER ::= { cevModuleGsrType 58 }
cevPosEnOc192SmLrFc OBJECT IDENTIFIER ::= { cevModuleGsrType 59 }
cevPosEnOc192SmLrSc OBJECT IDENTIFIER ::= { cevModuleGsrType 60 }
cevPosEnOc192SmVsrSc OBJECT IDENTIFIER ::= { cevModuleGsrType 61 }
cevPosEnOc192SmVsrFc OBJECT IDENTIFIER ::= { cevModuleGsrType 62 }
cevGsrQoc12Chstsds3SmIrSc OBJECT IDENTIFIER ::= { cevModuleGsrType 66 }
cevGsrQoc12Chstsds3MmSrSc OBJECT IDENTIFIER ::= { cevModuleGsrType 67 }
cevGsrOc48Chstsds3MmSrSc OBJECT IDENTIFIER ::= { cevModuleGsrType 68 }
cevGsrOc48Chstsds3SmIrSc OBJECT IDENTIFIER ::= { cevModuleGsrType 69 }
cevGsrOc48Chstsds3SmLrSc OBJECT IDENTIFIER ::= { cevModuleGsrType 70 }
cevGsr16Oc3Chstsds3MmSrSc OBJECT IDENTIFIER ::= { cevModuleGsrType 71 }
cevGsr16Oc3Chstsds3SmIrSc OBJECT IDENTIFIER ::= { cevModuleGsrType 72 }
cevGsr16Oc3Chstsds3SmLrSc OBJECT IDENTIFIER ::= { cevModuleGsrType 73 }
cevGsr2Oc3ChDs1 OBJECT IDENTIFIER ::= { cevModuleGsrType 74 }
cevSsrpOc192SmLr OBJECT IDENTIFIER ::= { cevModuleGsrType 75 }
cevSsrpOc192SmIr OBJECT IDENTIFIER ::= { cevModuleGsrType 76 }
cevSsrpOc192SmSr OBJECT IDENTIFIER ::= { cevModuleGsrType 77 }
cevSsrpOc192SmVsr OBJECT IDENTIFIER ::= { cevModuleGsrType 78 }
cev2Oc12ChDs3Sm OBJECT IDENTIFIER ::= { cevModuleGsrType 80 }
cevGsrAlarm10   OBJECT IDENTIFIER ::= { cevModuleGsrType 81 }
cevGsrBusBoard10 OBJECT IDENTIFIER ::= { cevModuleGsrType 82 }
cevGsrOc48Chstsds3SmSrSc OBJECT IDENTIFIER ::= { cevModuleGsrType 83 }
cevGsrE48PosOc48SmSrSc OBJECT IDENTIFIER ::= { cevModuleGsrType 84 }
cevGsrE48PosOc48SmLrSc OBJECT IDENTIFIER ::= { cevModuleGsrType 85 }
cevGsrE48PosQoc12SmIrSc OBJECT IDENTIFIER ::= { cevModuleGsrType 86 }
cevGsrE48Pos16oc3SmIrSc OBJECT IDENTIFIER ::= { cevModuleGsrType 87 }
cevCopper6e3    OBJECT IDENTIFIER ::= { cevModuleGsrType 88 }
cevCopper12e3   OBJECT IDENTIFIER ::= { cevModuleGsrType 89 }
cevGsrE48Pos16oc3SmIrLc OBJECT IDENTIFIER ::= { cevModuleGsrType 93 }
cevGsr16oc3Chstsds3SmIrLc OBJECT IDENTIFIER ::= { cevModuleGsrType 94 }
cevGsrOc12ChDs1SmIrSc OBJECT IDENTIFIER ::= { cevModuleGsrType 95 }
cevGsrAlarm6    OBJECT IDENTIFIER ::= { cevModuleGsrType 96 }
cevPosEnQoc48Vsr OBJECT IDENTIFIER ::= { cevModuleGsrType 97 }
cevPosEnQoc48MmSrSc OBJECT IDENTIFIER ::= { cevModuleGsrType 98 }
cevPosEnQoc48SmIrSc OBJECT IDENTIFIER ::= { cevModuleGsrType 99 }
cevPosEnQoc48SmIrFc OBJECT IDENTIFIER ::= { cevModuleGsrType 100 }
cevPosEnQoc48SmVlrSc OBJECT IDENTIFIER ::= { cevModuleGsrType 101 }
cevPosEnQoc48SmVlrFc OBJECT IDENTIFIER ::= { cevModuleGsrType 102 }
cevPosEnQoc48SmElrSc OBJECT IDENTIFIER ::= { cevModuleGsrType 103 }
cevPosEnQoc48SmElrFc OBJECT IDENTIFIER ::= { cevModuleGsrType 104 }
cevPosEnOc192Vsr OBJECT IDENTIFIER ::= { cevModuleGsrType 105 }
cevPosEnOc192SmSr2Sc OBJECT IDENTIFIER ::= { cevModuleGsrType 106 }
cevPosEnOc192SmSr2Fc OBJECT IDENTIFIER ::= { cevModuleGsrType 107 }
cevPosEnOc192SmVlrSc OBJECT IDENTIFIER ::= { cevModuleGsrType 108 }
cevPosEnOc192SmVlrFc OBJECT IDENTIFIER ::= { cevModuleGsrType 109 }
cevPosEnOc192SmElrSc OBJECT IDENTIFIER ::= { cevModuleGsrType 110 }
cevPosEnOc192SmElrFc OBJECT IDENTIFIER ::= { cevModuleGsrType 111 }
cevGsrEn8Oc3    OBJECT IDENTIFIER ::= { cevModuleGsrType 112 }
cevGsr1p10ge    OBJECT IDENTIFIER ::= { cevModuleGsrType 113 }
cevGsrE48PosOc48SmIrSc OBJECT IDENTIFIER ::= { cevModuleGsrType 114 }
cevGsrEOc192SmLrSc OBJECT IDENTIFIER ::= { cevModuleGsrType 116 }
cevGsrEOc192SmVsrSc OBJECT IDENTIFIER ::= { cevModuleGsrType 117 }
cevGsrEOc192SmVsrFc OBJECT IDENTIFIER ::= { cevModuleGsrType 118 }
cevGsrEOc192SmSrFc OBJECT IDENTIFIER ::= { cevModuleGsrType 119 }
cevGsrEOc192SmSrSc OBJECT IDENTIFIER ::= { cevModuleGsrType 120 }
cevGsrEOc192SmLrFc OBJECT IDENTIFIER ::= { cevModuleGsrType 121 }
cevGsrEQoc48SmLrFc OBJECT IDENTIFIER ::= { cevModuleGsrType 122 }
cevGsrEQoc48SmLrSc OBJECT IDENTIFIER ::= { cevModuleGsrType 123 }
cevGsrEQoc48SmVsrSc OBJECT IDENTIFIER ::= { cevModuleGsrType 124 }
cevGsrEQoc48SmVsrFc OBJECT IDENTIFIER ::= { cevModuleGsrType 125 }
cevGsrEQoc48SmSrFc OBJECT IDENTIFIER ::= { cevModuleGsrType 126 }
cevGsrEQoc48SmSrSc OBJECT IDENTIFIER ::= { cevModuleGsrType 127 }
cevGsrEQoc48Vsr OBJECT IDENTIFIER ::= { cevModuleGsrType 128 }
cevGsrEQoc48SmSr2Sc OBJECT IDENTIFIER ::= { cevModuleGsrType 129 }
cevGsrEQoc48SmSr2Fc OBJECT IDENTIFIER ::= { cevModuleGsrType 130 }
cevGsrEQoc48MmSrSc OBJECT IDENTIFIER ::= { cevModuleGsrType 131 }
cevGsrEQoc48SmIrSc OBJECT IDENTIFIER ::= { cevModuleGsrType 132 }
cevGsrEQoc48SmIrFc OBJECT IDENTIFIER ::= { cevModuleGsrType 133 }
cevGsrEQoc48SmVlrSc OBJECT IDENTIFIER ::= { cevModuleGsrType 134 }
cevGsrEQoc48SmVlrFc OBJECT IDENTIFIER ::= { cevModuleGsrType 135 }
cevGsrEQoc48SmElrSc OBJECT IDENTIFIER ::= { cevModuleGsrType 136 }
cevGsrEQoc48SmElrFc OBJECT IDENTIFIER ::= { cevModuleGsrType 137 }
cevGsrEOc192Vsr OBJECT IDENTIFIER ::= { cevModuleGsrType 138 }
cevGsrEOc192SmSr2Sc OBJECT IDENTIFIER ::= { cevModuleGsrType 139 }
cevGsrEOc192SmSr2Fc OBJECT IDENTIFIER ::= { cevModuleGsrType 140 }
cevGsrEOc192MmSrSc OBJECT IDENTIFIER ::= { cevModuleGsrType 141 }
cevGsrEOc192SmIrSc OBJECT IDENTIFIER ::= { cevModuleGsrType 142 }
cevGsrEOc192SmIrFc OBJECT IDENTIFIER ::= { cevModuleGsrType 143 }
cevGsrEOc192SmVlrSc OBJECT IDENTIFIER ::= { cevModuleGsrType 144 }
cevGsrEOc192SmVlrFc OBJECT IDENTIFIER ::= { cevModuleGsrType 145 }
cevGsrEOc192SmElrSc OBJECT IDENTIFIER ::= { cevModuleGsrType 146 }
cevGsrEOc192SmElrFc OBJECT IDENTIFIER ::= { cevModuleGsrType 147 }
cevSsrp2Oc48SrpSmSrLc OBJECT IDENTIFIER ::= { cevModuleGsrType 148 }
cevSsrp2Oc48SrpSmIrLc OBJECT IDENTIFIER ::= { cevModuleGsrType 149 }
cevSsrp2Oc48SrpSmLrLc OBJECT IDENTIFIER ::= { cevModuleGsrType 150 }
cevSsrp2Oc48PosSmSrLc OBJECT IDENTIFIER ::= { cevModuleGsrType 151 }
cevSsrp2Oc48PosSmIrLc OBJECT IDENTIFIER ::= { cevModuleGsrType 152 }
cevSsrp2Oc48PosSmLrLc OBJECT IDENTIFIER ::= { cevModuleGsrType 153 }
cevGsrE48PosQoc12MmSrSc OBJECT IDENTIFIER ::= { cevModuleGsrType 155 }
cevGsrGeFe      OBJECT IDENTIFIER ::= { cevModuleGsrType 156 }
cevGsrE48Atm4oc12SmIrSc OBJECT IDENTIFIER ::= { cevModuleGsrType 157 }
cevGsrE48Atm4oc12MmSrSc OBJECT IDENTIFIER ::= { cevModuleGsrType 158 }
cevGsrE48Atm4oc3SmIrSc OBJECT IDENTIFIER ::= { cevModuleGsrType 159 }
cevGsrE48Atm4oc3MmSrSc OBJECT IDENTIFIER ::= { cevModuleGsrType 160 }
cevGsrE48Pos4oc3SmIrLc OBJECT IDENTIFIER ::= { cevModuleGsrType 162 }
cevGsrE48Pos8oc3SmIrLc OBJECT IDENTIFIER ::= { cevModuleGsrType 166 }
cevSsrp2Oc12E48SmIr OBJECT IDENTIFIER ::= { cevModuleGsrType 167 }
cevSsrp2Oc12E48SmXr OBJECT IDENTIFIER ::= { cevModuleGsrType 168 }
cevSsrp1Oc12E48SmIr OBJECT IDENTIFIER ::= { cevModuleGsrType 169 }
cevSsrp1Oc12E48SmXr OBJECT IDENTIFIER ::= { cevModuleGsrType 170 }
cevGsrSIP600    OBJECT IDENTIFIER ::= { cevModuleGsrType 171 }
cevGsr4pge      OBJECT IDENTIFIER ::= { cevModuleGsrType 173 }
cevGsrAtmEn8Oc3Mm OBJECT IDENTIFIER ::= { cevModuleGsrType 174 }
cevGsr2Oc192Pos OBJECT IDENTIFIER ::= { cevModuleGsrType 175 }
cevGsr8Oc48Pos  OBJECT IDENTIFIER ::= { cevModuleGsrType 176 }
cevGsrOc48Msr   OBJECT IDENTIFIER ::= { cevModuleGsrType 177 }
cevPosE2Oc192Vsr OBJECT IDENTIFIER ::= { cevModuleGsrType 178 }
cevPosE2Oc192SmSr2Sc OBJECT IDENTIFIER ::= { cevModuleGsrType 179 }
cevPosE2Oc192SmSr2Fc OBJECT IDENTIFIER ::= { cevModuleGsrType 180 }
cevPosE2Oc192SmSrSc OBJECT IDENTIFIER ::= { cevModuleGsrType 181 }
cevPosE2Oc192SmSrFc OBJECT IDENTIFIER ::= { cevModuleGsrType 182 }
cevPosE2Oc192SmIrSc OBJECT IDENTIFIER ::= { cevModuleGsrType 183 }
cevPosE2Oc192SmIrFc OBJECT IDENTIFIER ::= { cevModuleGsrType 184 }
cevPosE2Oc192SmLrSc OBJECT IDENTIFIER ::= { cevModuleGsrType 185 }
cevPosE2Oc192SmLrFc OBJECT IDENTIFIER ::= { cevModuleGsrType 186 }
cevPosE2Oc192SmVlrSc OBJECT IDENTIFIER ::= { cevModuleGsrType 187 }
cevPosE2Oc192SmVlrFc OBJECT IDENTIFIER ::= { cevModuleGsrType 188 }
cevPosE2Oc192SmElrSc OBJECT IDENTIFIER ::= { cevModuleGsrType 189 }
cevPosE2Oc192SmElrFc OBJECT IDENTIFIER ::= { cevModuleGsrType 190 }
cevGsr6Ds3e3Smb OBJECT IDENTIFIER ::= { cevModuleGsrType 191 }
cevGsr6Ds3e3Ct3Smb OBJECT IDENTIFIER ::= { cevModuleGsrType 192 }
cevGsr2Oc3Chds1ds3e3SmIrSc OBJECT IDENTIFIER ::= { cevModuleGsrType 193 }
cevGsrService   OBJECT IDENTIFIER ::= { cevModuleGsrType 194 }
cevGsrSIP601    OBJECT IDENTIFIER ::= { cevModuleGsrType 195 }
cevGsrSIP501    OBJECT IDENTIFIER ::= { cevModuleGsrType 196 }
cevGsrSIP401    OBJECT IDENTIFIER ::= { cevModuleGsrType 197 }
cevGsrSsrp2Oc48Lc OBJECT IDENTIFIER ::= { cevModuleGsrType 198 }
cevGsrE384Cec   OBJECT IDENTIFIER ::= { cevModuleGsrType 200 }
cevModuleRpmType OBJECT IDENTIFIER ::= { cevModule 19 }
cevAtmdxRpm     OBJECT IDENTIFIER ::= { cevModuleRpmType 1 }
cevModuleCat8500Type OBJECT IDENTIFIER ::= { cevModule 20 }
cevCat8500CpuSwitch OBJECT IDENTIFIER ::= { cevModuleCat8500Type 1 }
cevCat8500FeatureFpga OBJECT IDENTIFIER ::= { cevModuleCat8500Type 2 }
cevCat8500FeatureAsic OBJECT IDENTIFIER ::= { cevModuleCat8500Type 3 }
cevCat8500FeaturePVC OBJECT IDENTIFIER ::= { cevModuleCat8500Type 4 }
cevCat8500FeUTP8p16k OBJECT IDENTIFIER ::= { cevModuleCat8500Type 5 }
cevCat8500FeUTP8p64k OBJECT IDENTIFIER ::= { cevModuleCat8500Type 6 }
cevCat8500FeMMF8p16k OBJECT IDENTIFIER ::= { cevModuleCat8500Type 7 }
cevCat8500FeMMF8p64k OBJECT IDENTIFIER ::= { cevModuleCat8500Type 8 }
cevCat8500FeUTP16p16k OBJECT IDENTIFIER ::= { cevModuleCat8500Type 9 }
cevCat8500FeUTP16p64k OBJECT IDENTIFIER ::= { cevModuleCat8500Type 10 }
cevCat8500FeMMF16p16k OBJECT IDENTIFIER ::= { cevModuleCat8500Type 11 }
cevCat8500FeMMF16p64k OBJECT IDENTIFIER ::= { cevModuleCat8500Type 12 }
cevCat8500GeF1p16k OBJECT IDENTIFIER ::= { cevModuleCat8500Type 13 }
cevCat8500GeF1p64k OBJECT IDENTIFIER ::= { cevModuleCat8500Type 14 }
cevCat8500GeF2p16k OBJECT IDENTIFIER ::= { cevModuleCat8500Type 15 }
cevCat8500GeF2p64k OBJECT IDENTIFIER ::= { cevModuleCat8500Type 16 }
cevCat8500FeBridge4p OBJECT IDENTIFIER ::= { cevModuleCat8500Type 17 }
cevCat8500RouteProc OBJECT IDENTIFIER ::= { cevModuleCat8500Type 18 }
cevCat8500Switch10GProc OBJECT IDENTIFIER ::= { cevModuleCat8500Type 19 }
cevCat8500FeatureNetClock OBJECT IDENTIFIER ::= { cevModuleCat8500Type 20 }
cevCat8500FeatureABR OBJECT IDENTIFIER ::= { cevModuleCat8500Type 21 }
cevCat8500FeatureLite OBJECT IDENTIFIER ::= { cevModuleCat8500Type 22 }
cevCat8500m16pOC3Mm OBJECT IDENTIFIER ::= { cevModuleCat8500Type 23 }
cevCat8500m16pOC3Sm OBJECT IDENTIFIER ::= { cevModuleCat8500Type 24 }
cevCat8500m4pOC12Mm OBJECT IDENTIFIER ::= { cevModuleCat8500Type 25 }
cevCat8500m4pOC12Sm OBJECT IDENTIFIER ::= { cevModuleCat8500Type 26 }
cevCat8500m4pOC3Utp5 OBJECT IDENTIFIER ::= { cevModuleCat8500Type 27 }
cevCat8500m4pOC3Mixed OBJECT IDENTIFIER ::= { cevModuleCat8500Type 28 }
cevCat8500m4pOC3Sm OBJECT IDENTIFIER ::= { cevModuleCat8500Type 29 }
cevCat8500m4pOC3Mm OBJECT IDENTIFIER ::= { cevModuleCat8500Type 30 }
cevCat8500mATM25 OBJECT IDENTIFIER ::= { cevModuleCat8500Type 31 }
cevCat8500m4pE3 OBJECT IDENTIFIER ::= { cevModuleCat8500Type 32 }
cevCat8500m4pDs3 OBJECT IDENTIFIER ::= { cevModuleCat8500Type 33 }
cevCat8500mCbr75E1 OBJECT IDENTIFIER ::= { cevModuleCat8500Type 34 }
cevCat8500mCbr120E1 OBJECT IDENTIFIER ::= { cevModuleCat8500Type 35 }
cevCat8500mCbrT1 OBJECT IDENTIFIER ::= { cevModuleCat8500Type 36 }
cevCat8500mE1   OBJECT IDENTIFIER ::= { cevModuleCat8500Type 37 }
cevCat8500mT1   OBJECT IDENTIFIER ::= { cevModuleCat8500Type 38 }
cevCat8500mE1Bnc OBJECT IDENTIFIER ::= { cevModuleCat8500Type 39 }
cevCat8500mE3   OBJECT IDENTIFIER ::= { cevModuleCat8500Type 40 }
cevCat8500mDs3  OBJECT IDENTIFIER ::= { cevModuleCat8500Type 41 }
cevCat8500m4pFrCE1 OBJECT IDENTIFIER ::= { cevModuleCat8500Type 42 }
cevCat8500m1pFrCT3 OBJECT IDENTIFIER ::= { cevModuleCat8500Type 43 }
cevCat8500GeF8p64k OBJECT IDENTIFIER ::= { cevModuleCat8500Type 44 }
cevCat8500mArm1p64k OBJECT IDENTIFIER ::= { cevModuleCat8500Type 45 }
cevCat8500mArm2p64k OBJECT IDENTIFIER ::= { cevModuleCat8500Type 46 }
cevCat8500mOC48c1pSm OBJECT IDENTIFIER ::= { cevModuleCat8500Type 47 }
cevCat8500mIma8pT1 OBJECT IDENTIFIER ::= { cevModuleCat8500Type 48 }
cevCat8500mIma8pE1 OBJECT IDENTIFIER ::= { cevModuleCat8500Type 49 }
cevCat8500mATM25m4p OBJECT IDENTIFIER ::= { cevModuleCat8500Type 50 }
cevCat8500mOC121pMm OBJECT IDENTIFIER ::= { cevModuleCat8500Type 51 }
cevCat8500mOC121pSm OBJECT IDENTIFIER ::= { cevModuleCat8500Type 52 }
cevCat8500m1pOC12Mixed OBJECT IDENTIFIER ::= { cevModuleCat8500Type 53 }
cevCat8500mFimBridge OBJECT IDENTIFIER ::= { cevModuleCat8500Type 54 }
cevCat8500mFimOC12Mm OBJECT IDENTIFIER ::= { cevModuleCat8500Type 55 }
cevCat8500Ge1pXpif16k OBJECT IDENTIFIER ::= { cevModuleCat8500Type 56 }
cevCat8500Ge1pXpif64k OBJECT IDENTIFIER ::= { cevModuleCat8500Type 57 }
cevCat8500Ge1pXpif256k OBJECT IDENTIFIER ::= { cevModuleCat8500Type 58 }
cevCat8500Atm1pXpif64kOc12SmIr OBJECT IDENTIFIER ::= { cevModuleCat8500Type 59 }
cevCat8500Atm1pXpif256kOc12SmIr OBJECT IDENTIFIER ::= { cevModuleCat8500Type 60 }
cevCat8500Atm1pXpif64kOc12Mm OBJECT IDENTIFIER ::= { cevModuleCat8500Type 61 }
cevCat8500Atm1pXpif256kOc12Mm OBJECT IDENTIFIER ::= { cevModuleCat8500Type 62 }
cevCat8500Atm1pXpif64kOc3SmIr OBJECT IDENTIFIER ::= { cevModuleCat8500Type 63 }
cevCat8500Atm1pXpif256kOc3SmIr OBJECT IDENTIFIER ::= { cevModuleCat8500Type 64 }
cevCat8500Atm1pXpif64kOc3Mm OBJECT IDENTIFIER ::= { cevModuleCat8500Type 65 }
cevCat8500Atm1pXpif256kOc3Mm OBJECT IDENTIFIER ::= { cevModuleCat8500Type 66 }
cevCat8500Pos1pXpif64kOc12SmIr OBJECT IDENTIFIER ::= { cevModuleCat8500Type 67 }
cevCat8500Pos1pXpif256kOc12SmIr OBJECT IDENTIFIER ::= { cevModuleCat8500Type 68 }
cevCat8500Pos1pXpif64kOc12SmLr OBJECT IDENTIFIER ::= { cevModuleCat8500Type 69 }
cevCat8500Pos1pXpif256kOc12SmLr OBJECT IDENTIFIER ::= { cevModuleCat8500Type 70 }
cevModuleWASCommonCards OBJECT IDENTIFIER ::= { cevModule 21 }
cevAusm8t1      OBJECT IDENTIFIER ::= { cevModuleWASCommonCards 1 }
cevAusm8e1      OBJECT IDENTIFIER ::= { cevModuleWASCommonCards 2 }
cevCesm8t1      OBJECT IDENTIFIER ::= { cevModuleWASCommonCards 3 }
cevCesm8e1      OBJECT IDENTIFIER ::= { cevModuleWASCommonCards 4 }
cevFrsm8t1      OBJECT IDENTIFIER ::= { cevModuleWASCommonCards 5 }
cevFrsm8e1      OBJECT IDENTIFIER ::= { cevModuleWASCommonCards 6 }
cevFrsm4x21     OBJECT IDENTIFIER ::= { cevModuleWASCommonCards 7 }
cevFrsm2hssi    OBJECT IDENTIFIER ::= { cevModuleWASCommonCards 8 }
cevAxsm1Oc48    OBJECT IDENTIFIER ::= { cevModuleWASCommonCards 9 }
cevAxsm4Oc12    OBJECT IDENTIFIER ::= { cevModuleWASCommonCards 10 }
cevAxsm8Oc3     OBJECT IDENTIFIER ::= { cevModuleWASCommonCards 11 }
cevAxsm16Oc3    OBJECT IDENTIFIER ::= { cevModuleWASCommonCards 12 }
cevAxsm16T3E3   OBJECT IDENTIFIER ::= { cevModuleWASCommonCards 13 }
cevCesm1t3      OBJECT IDENTIFIER ::= { cevModuleWASCommonCards 14 }
cevCesm1e3      OBJECT IDENTIFIER ::= { cevModuleWASCommonCards 15 }
cevVism8t1      OBJECT IDENTIFIER ::= { cevModuleWASCommonCards 16 }
cevVism8e1      OBJECT IDENTIFIER ::= { cevModuleWASCommonCards 17 }
cevMGXRpm       OBJECT IDENTIFIER ::= { cevModuleWASCommonCards 18 }
cevMGXSrm3t3    OBJECT IDENTIFIER ::= { cevModuleWASCommonCards 19 }
cevEnhAxsm1oc12 OBJECT IDENTIFIER ::= { cevModuleWASCommonCards 20 }
cevEnhAxsm2oc12 OBJECT IDENTIFIER ::= { cevModuleWASCommonCards 21 }
cevEnhAxsm4oc3  OBJECT IDENTIFIER ::= { cevModuleWASCommonCards 22 }
cevEnhAxsm8oc3  OBJECT IDENTIFIER ::= { cevModuleWASCommonCards 23 }
cevEnhAxsm4stm1 OBJECT IDENTIFIER ::= { cevModuleWASCommonCards 24 }
cevEnhAxsm8stm1 OBJECT IDENTIFIER ::= { cevModuleWASCommonCards 25 }
cevEnhAxsm8t3e3 OBJECT IDENTIFIER ::= { cevModuleWASCommonCards 26 }
cevEnhAxsm16t3e3 OBJECT IDENTIFIER ::= { cevModuleWASCommonCards 27 }
cevEnhAxsm8t1   OBJECT IDENTIFIER ::= { cevModuleWASCommonCards 28 }
cevEnhAxsm16t1  OBJECT IDENTIFIER ::= { cevModuleWASCommonCards 29 }
cevEnhAxsm8e1   OBJECT IDENTIFIER ::= { cevModuleWASCommonCards 30 }
cevEnhAxsm16e1  OBJECT IDENTIFIER ::= { cevModuleWASCommonCards 31 }
cevAxsm2oc12    OBJECT IDENTIFIER ::= { cevModuleWASCommonCards 32 }
cevMGXRpmPr     OBJECT IDENTIFIER ::= { cevModuleWASCommonCards 34 }
cevFrsm4V35     OBJECT IDENTIFIER ::= { cevModuleWASCommonCards 38 }
cevFrsm2Ct3     OBJECT IDENTIFIER ::= { cevModuleWASCommonCards 39 }
cevFrsm2t3      OBJECT IDENTIFIER ::= { cevModuleWASCommonCards 40 }
cevFrsm2e3      OBJECT IDENTIFIER ::= { cevModuleWASCommonCards 41 }
cevAusmB8t1     OBJECT IDENTIFIER ::= { cevModuleWASCommonCards 42 }
cevAusmB8e1     OBJECT IDENTIFIER ::= { cevModuleWASCommonCards 43 }
cevVixm4oc12    OBJECT IDENTIFIER ::= { cevModuleWASCommonCards 45 }
cevVixm16oc3    OBJECT IDENTIFIER ::= { cevModuleWASCommonCards 46 }
cevCesmB8e1     OBJECT IDENTIFIER ::= { cevModuleWASCommonCards 49 }
cevCesmB8t1     OBJECT IDENTIFIER ::= { cevModuleWASCommonCards 50 }
cevFrsmC8e1     OBJECT IDENTIFIER ::= { cevModuleWASCommonCards 51 }
cevFrsmC8t1     OBJECT IDENTIFIER ::= { cevModuleWASCommonCards 52 }
cevFrsmB2hssi   OBJECT IDENTIFIER ::= { cevModuleWASCommonCards 53 }
cevFrsmB12In1   OBJECT IDENTIFIER ::= { cevModuleWASCommonCards 54 }
cevHsfr12t3     OBJECT IDENTIFIER ::= { cevModuleWASCommonCards 55 }
cevHsfr12e3     OBJECT IDENTIFIER ::= { cevModuleWASCommonCards 56 }
cevFrsm12t3     OBJECT IDENTIFIER ::= { cevModuleWASCommonCards 57 }
cevFrsm12e3     OBJECT IDENTIFIER ::= { cevModuleWASCommonCards 58 }
cevFrsmB2T3     OBJECT IDENTIFIER ::= { cevModuleWASCommonCards 59 }
cevMgxSrme1Sts3 OBJECT IDENTIFIER ::= { cevModuleWASCommonCards 60 }
cevMgxSrm3t3NoBc OBJECT IDENTIFIER ::= { cevModuleWASCommonCards 61 }
cevMgxSrmeNoBc  OBJECT IDENTIFIER ::= { cevModuleWASCommonCards 62 }
cevAxsmEn16t1e1 OBJECT IDENTIFIER ::= { cevModuleWASCommonCards 63 }
cevAxsmEn32t1e1 OBJECT IDENTIFIER ::= { cevModuleWASCommonCards 64 }
cevFrsmB2e3     OBJECT IDENTIFIER ::= { cevModuleWASCommonCards 66 }
cevVismPr8t1    OBJECT IDENTIFIER ::= { cevModuleWASCommonCards 70 }
cevVismPr8e1    OBJECT IDENTIFIER ::= { cevModuleWASCommonCards 71 }
cevMGXSrmE1Oc3  OBJECT IDENTIFIER ::= { cevModuleWASCommonCards 72 }
cevAxsm2Oc48    OBJECT IDENTIFIER ::= { cevModuleWASCommonCards 73 }
cevAxsm8Oc12    OBJECT IDENTIFIER ::= { cevModuleWASCommonCards 74 }
cevVxsm4Oc3     OBJECT IDENTIFIER ::= { cevModuleWASCommonCards 81 }
cevMGXSrm4Oc3   OBJECT IDENTIFIER ::= { cevModuleWASCommonCards 82 }
cevMpsm8t1e1    OBJECT IDENTIFIER ::= { cevModuleWASCommonCards 87 }
cevMpsm8t1Atm   OBJECT IDENTIFIER ::= { cevModuleWASCommonCards 88 }
cevMpsm8t1Fr    OBJECT IDENTIFIER ::= { cevModuleWASCommonCards 89 }
cevMpsm8t1Ces   OBJECT IDENTIFIER ::= { cevModuleWASCommonCards 90 }
cevMpsm8e1Atm   OBJECT IDENTIFIER ::= { cevModuleWASCommonCards 91 }
cevMpsm8e1Fr    OBJECT IDENTIFIER ::= { cevModuleWASCommonCards 92 }
cevMpsm8e1Ces   OBJECT IDENTIFIER ::= { cevModuleWASCommonCards 93 }
cevMpsm16t1e1   OBJECT IDENTIFIER ::= { cevModuleWASCommonCards 94 }
cevMpsm16t1Atm  OBJECT IDENTIFIER ::= { cevModuleWASCommonCards 95 }
cevMpsm16t1Fr   OBJECT IDENTIFIER ::= { cevModuleWASCommonCards 96 }
cevMpsm16t1Ces  OBJECT IDENTIFIER ::= { cevModuleWASCommonCards 97 }
cevMpsm16e1Atm  OBJECT IDENTIFIER ::= { cevModuleWASCommonCards 98 }
cevMpsm16e1Fr   OBJECT IDENTIFIER ::= { cevModuleWASCommonCards 99 }
cevMpsm16e1Ces  OBJECT IDENTIFIER ::= { cevModuleWASCommonCards 100 }
cevMpsm155t3e3  OBJECT IDENTIFIER ::= { cevModuleWASCommonCards 101 }
cevMGXSm        OBJECT IDENTIFIER ::= { cevModuleWASCommonCards 102 }
cevVxsm48t1e1   OBJECT IDENTIFIER ::= { cevModuleWASCommonCards 103 }
cevVxsm3T3E3    OBJECT IDENTIFIER ::= { cevModuleWASCommonCards 104 }
cevVxsm6t3e3    OBJECT IDENTIFIER ::= { cevModuleWASCommonCards 105 }
cevVxsm6t3      OBJECT IDENTIFIER ::= { cevModuleWASCommonCards 106 }
cevMpsm16t1e1Ppp OBJECT IDENTIFIER ::= { cevModuleWASCommonCards 107 }
cevMpsm155t3e3Ppp OBJECT IDENTIFIER ::= { cevModuleWASCommonCards 108 }
cevModule38xxType OBJECT IDENTIFIER ::= { cevModule 22 }
cevMc3810Vcm3   OBJECT IDENTIFIER ::= { cevModule38xxType 1 }
cevMc3810Bvm    OBJECT IDENTIFIER ::= { cevModule38xxType 2 }
cevMc3810AvmFxoUk OBJECT IDENTIFIER ::= { cevModule38xxType 3 }
cevMc3810AvmFxoGer OBJECT IDENTIFIER ::= { cevModule38xxType 4 }
cevMc3810Hcm2   OBJECT IDENTIFIER ::= { cevModule38xxType 5 }
cevMc3810Hcm6   OBJECT IDENTIFIER ::= { cevModule38xxType 6 }
cevMc3810AvmFxoPr3 OBJECT IDENTIFIER ::= { cevModule38xxType 7 }
cevMc3810AvmFxoPr2 OBJECT IDENTIFIER ::= { cevModule38xxType 8 }
cevMc3810Vdm    OBJECT IDENTIFIER ::= { cevModule38xxType 9 }
cevMc3810ApmFxsDid OBJECT IDENTIFIER ::= { cevModule38xxType 10 }
cevMc3810BvmNtTe OBJECT IDENTIFIER ::= { cevModule38xxType 11 }
cevMc3810Hcm1   OBJECT IDENTIFIER ::= { cevModule38xxType 12 }
cevMc3810Hcm3   OBJECT IDENTIFIER ::= { cevModule38xxType 13 }
cevMc3810Hcm4   OBJECT IDENTIFIER ::= { cevModule38xxType 14 }
cevMc3810Hcm5   OBJECT IDENTIFIER ::= { cevModule38xxType 15 }
cevSmSre710K9   OBJECT IDENTIFIER ::= { cevModule38xxType 17 }
cevSmSre910K9   OBJECT IDENTIFIER ::= { cevModule38xxType 18 }
cevPSmSre710K9  OBJECT IDENTIFIER ::= { cevModule38xxType 19 }
cevPSmSre910K9  OBJECT IDENTIFIER ::= { cevModule38xxType 20 }
cevModuleCat29xxType OBJECT IDENTIFIER ::= { cevModule 23 }
cevX2914        OBJECT IDENTIFIER ::= { cevModuleCat29xxType 1 }
cevX2922        OBJECT IDENTIFIER ::= { cevModuleCat29xxType 2 }
cevX2914V       OBJECT IDENTIFIER ::= { cevModuleCat29xxType 3 }
cevX2922V       OBJECT IDENTIFIER ::= { cevModuleCat29xxType 4 }
cevX2924V       OBJECT IDENTIFIER ::= { cevModuleCat29xxType 5 }
cevX2951        OBJECT IDENTIFIER ::= { cevModuleCat29xxType 6 }
cevX2961        OBJECT IDENTIFIER ::= { cevModuleCat29xxType 7 }
cevX2971        OBJECT IDENTIFIER ::= { cevModuleCat29xxType 8 }
cevX2972        OBJECT IDENTIFIER ::= { cevModuleCat29xxType 9 }
cevX2931        OBJECT IDENTIFIER ::= { cevModuleCat29xxType 10 }
cevModuleCat297024 OBJECT IDENTIFIER ::= { cevModuleCat29xxType 12 }
cevModuleCat297024TS OBJECT IDENTIFIER ::= { cevModuleCat29xxType 13 }
cevModuleCat297048TS OBJECT IDENTIFIER ::= { cevModuleCat29xxType 14 }
cevModuleCat296024 OBJECT IDENTIFIER ::= { cevModuleCat29xxType 15 }
cevModuleCat296048 OBJECT IDENTIFIER ::= { cevModuleCat29xxType 16 }
cevModuleCat2960G24 OBJECT IDENTIFIER ::= { cevModuleCat29xxType 17 }
cevModuleCat2960G48 OBJECT IDENTIFIER ::= { cevModuleCat29xxType 18 }
cevModuleCat296024TT OBJECT IDENTIFIER ::= { cevModuleCat29xxType 19 }
cevModuleCat296048TT OBJECT IDENTIFIER ::= { cevModuleCat29xxType 20 }
cevModuleCat29608TC OBJECT IDENTIFIER ::= { cevModuleCat29xxType 21 }
cevModuleCat2960G8TC OBJECT IDENTIFIER ::= { cevModuleCat29xxType 22 }
cevModuleCat296048TCS OBJECT IDENTIFIER ::= { cevModuleCat29xxType 23 }
cevModuleCat296024TCS OBJECT IDENTIFIER ::= { cevModuleCat29xxType 24 }
cevModuleCat296024S OBJECT IDENTIFIER ::= { cevModuleCat29xxType 25 }
cevModuleCat296024PC OBJECT IDENTIFIER ::= { cevModuleCat29xxType 26 }
cevModuleCat296024LT OBJECT IDENTIFIER ::= { cevModuleCat29xxType 27 }
cevModuleCat2960PD8TT OBJECT IDENTIFIER ::= { cevModuleCat29xxType 28 }
cevModuleCat291824TT OBJECT IDENTIFIER ::= { cevModuleCat29xxType 29 }
cevModuleCat291824TC OBJECT IDENTIFIER ::= { cevModuleCat29xxType 30 }
cevModuleCat291848TT OBJECT IDENTIFIER ::= { cevModuleCat29xxType 31 }
cevModuleCat291848TC OBJECT IDENTIFIER ::= { cevModuleCat29xxType 32 }
cevModuleCat296048TTS OBJECT IDENTIFIER ::= { cevModuleCat29xxType 33 }
cevModuleCat29608TCS OBJECT IDENTIFIER ::= { cevModuleCat29xxType 34 }
cevModuleCat296048PSTL OBJECT IDENTIFIER ::= { cevModuleCat29xxType 35 }
cevModuleCat296024LCS OBJECT IDENTIFIER ::= { cevModuleCat29xxType 36 }
cevModuleCat296024PCS OBJECT IDENTIFIER ::= { cevModuleCat29xxType 37 }
cevModuleCat296048PSTS OBJECT IDENTIFIER ::= { cevModuleCat29xxType 38 }
cevModuleWsC2960s48tsS OBJECT IDENTIFIER ::= { cevModuleCat29xxType 39 }
cevModuleWsC2960s24tsS OBJECT IDENTIFIER ::= { cevModuleCat29xxType 40 }
cevModuleWsC2960s48fpdL OBJECT IDENTIFIER ::= { cevModuleCat29xxType 41 }
cevModuleWsC2960s48lpdL OBJECT IDENTIFIER ::= { cevModuleCat29xxType 42 }
cevModuleWsC2960s48tdL OBJECT IDENTIFIER ::= { cevModuleCat29xxType 43 }
cevModuleWsC2960s24pdL OBJECT IDENTIFIER ::= { cevModuleCat29xxType 44 }
cevModuleWsC2960s24tdL OBJECT IDENTIFIER ::= { cevModuleCat29xxType 45 }
cevModuleWsC2960s48fpsL OBJECT IDENTIFIER ::= { cevModuleCat29xxType 46 }
cevModuleWsC2960s48lpsL OBJECT IDENTIFIER ::= { cevModuleCat29xxType 47 }
cevModuleWsC2960s24psL OBJECT IDENTIFIER ::= { cevModuleCat29xxType 48 }
cevModuleWsC2960s48tsL OBJECT IDENTIFIER ::= { cevModuleCat29xxType 49 }
cevModuleWsC2960S24tsL OBJECT IDENTIFIER ::= { cevModuleCat29xxType 50 }
cevModuleCat2960cPD8TT OBJECT IDENTIFIER ::= { cevModuleCat29xxType 51 }
cevModuleCat2960cG8TC OBJECT IDENTIFIER ::= { cevModuleCat29xxType 53 }
cevModuleCat292824TCC OBJECT IDENTIFIER ::= { cevModuleCat29xxType 54 }
cevModuleCat292824LTC OBJECT IDENTIFIER ::= { cevModuleCat29xxType 55 }
cevModuleCat292848TCC OBJECT IDENTIFIER ::= { cevModuleCat29xxType 56 }
cevModuleWsC2960C8tcS OBJECT IDENTIFIER ::= { cevModuleCat29xxType 57 }
cevModuleWsC2960C8tcL OBJECT IDENTIFIER ::= { cevModuleCat29xxType 58 }
cevModuleWsC2960C8pcL OBJECT IDENTIFIER ::= { cevModuleCat29xxType 59 }
cevModuleWsC2960C12pcL OBJECT IDENTIFIER ::= { cevModuleCat29xxType 60 }
cevModuleWsC2960x48fpdL OBJECT IDENTIFIER ::= { cevModuleCat29xxType 68 }
cevModuleWsC2960x48lpdL OBJECT IDENTIFIER ::= { cevModuleCat29xxType 69 }
cevModuleWsC2960x48tdL OBJECT IDENTIFIER ::= { cevModuleCat29xxType 70 }
cevModuleWsC2960x24pdL OBJECT IDENTIFIER ::= { cevModuleCat29xxType 71 }
cevModuleWsC2960x24tdL OBJECT IDENTIFIER ::= { cevModuleCat29xxType 72 }
cevModuleWsC2960x48fpsL OBJECT IDENTIFIER ::= { cevModuleCat29xxType 73 }
cevModuleWsC2960x48lpsL OBJECT IDENTIFIER ::= { cevModuleCat29xxType 74 }
cevModuleWsC2960x24psL OBJECT IDENTIFIER ::= { cevModuleCat29xxType 75 }
cevModuleWsC2960x48tsL OBJECT IDENTIFIER ::= { cevModuleCat29xxType 76 }
cevModuleWsC2960x24tsL OBJECT IDENTIFIER ::= { cevModuleCat29xxType 77 }
cevModuleWsC2960x24psqL OBJECT IDENTIFIER ::= { cevModuleCat29xxType 78 }
cevModuleWsC2960x48lpsS OBJECT IDENTIFIER ::= { cevModuleCat29xxType 79 }
cevModuleWsC2960x24psS OBJECT IDENTIFIER ::= { cevModuleCat29xxType 80 }
cevModuleWsC2960x48tsLL OBJECT IDENTIFIER ::= { cevModuleCat29xxType 81 }
cevModuleWsC2960x24tsLL OBJECT IDENTIFIER ::= { cevModuleCat29xxType 82 }
cevModuleC2960XStack OBJECT IDENTIFIER ::= { cevModuleCat29xxType 83 }
cevModuleC2960XFex OBJECT IDENTIFIER ::= { cevModuleCat29xxType 84 }
cevModuleC2960XFexStack OBJECT IDENTIFIER ::= { cevModuleCat29xxType 85 }
cevModuleWsC2960P48PstL OBJECT IDENTIFIER ::= { cevModuleCat29xxType 86 }
cevModuleWsC2960P24PcL OBJECT IDENTIFIER ::= { cevModuleCat29xxType 87 }
cevModuleWsC2960P24LcL OBJECT IDENTIFIER ::= { cevModuleCat29xxType 88 }
cevModuleWsC2960P48TcL OBJECT IDENTIFIER ::= { cevModuleCat29xxType 89 }
cevModuleWsC2960P24TcL OBJECT IDENTIFIER ::= { cevModuleCat29xxType 90 }
cevModuleWsC2960P48PstS OBJECT IDENTIFIER ::= { cevModuleCat29xxType 91 }
cevModuleWsC2960P24PcS OBJECT IDENTIFIER ::= { cevModuleCat29xxType 92 }
cevModuleWsC2960P24LcS OBJECT IDENTIFIER ::= { cevModuleCat29xxType 93 }
cevModuleWsC2960P48TcS OBJECT IDENTIFIER ::= { cevModuleCat29xxType 94 }
cevModuleWsC2960P24TcS OBJECT IDENTIFIER ::= { cevModuleCat29xxType 95 }
cevModuleWsC2960XR48FpdI OBJECT IDENTIFIER ::= { cevModuleCat29xxType 96 }
cevModuleWsC2960XR48LpdI OBJECT IDENTIFIER ::= { cevModuleCat29xxType 97 }
cevModuleWsC2960XR48TdI OBJECT IDENTIFIER ::= { cevModuleCat29xxType 98 }
cevModuleWsC2960XR24PdI OBJECT IDENTIFIER ::= { cevModuleCat29xxType 99 }
cevModuleWsC2960XR24TdI OBJECT IDENTIFIER ::= { cevModuleCat29xxType 100 }
cevModuleWsC2960XR48FpsI OBJECT IDENTIFIER ::= { cevModuleCat29xxType 101 }
cevModuleWsC2960XR48LpsI OBJECT IDENTIFIER ::= { cevModuleCat29xxType 102 }
cevModuleWsC2960XR48TsI OBJECT IDENTIFIER ::= { cevModuleCat29xxType 103 }
cevModuleWsC2960XR24PsI OBJECT IDENTIFIER ::= { cevModuleCat29xxType 104 }
cevModuleWsC2960XR24TsI OBJECT IDENTIFIER ::= { cevModuleCat29xxType 105 }
cevModuleWsC2960CX8TCL OBJECT IDENTIFIER ::= { cevModuleCat29xxType 142 }
cevModuleCat2960L24TSLL OBJECT IDENTIFIER ::= { cevModuleCat29xxType 146 }
cevModuleCat2960L8TSLL OBJECT IDENTIFIER ::= { cevModuleCat29xxType 147 }
cevModuleCat2960L16TSLL OBJECT IDENTIFIER ::= { cevModuleCat29xxType 148 }
cevModuleCat2960L48TSLL OBJECT IDENTIFIER ::= { cevModuleCat29xxType 149 }
cevModuleCat2960L48PSLL OBJECT IDENTIFIER ::= { cevModuleCat29xxType 150 }
cevModuleCat2960L16PSLL OBJECT IDENTIFIER ::= { cevModuleCat29xxType 151 }
cevModuleCat2960L8PSLL OBJECT IDENTIFIER ::= { cevModuleCat29xxType 152 }
cevModuleCat2960L24PSLL OBJECT IDENTIFIER ::= { cevModuleCat29xxType 153 }
cevModuleOscillatorType OBJECT IDENTIFIER ::= { cevModule 24 }
cevStratum3     OBJECT IDENTIFIER ::= { cevModuleOscillatorType 1 }
cevStratum4     OBJECT IDENTIFIER ::= { cevModuleOscillatorType 2 }
cevModuleDslamType OBJECT IDENTIFIER ::= { cevModule 25 }
cevNi2WanOc3mmSubOc3mm OBJECT IDENTIFIER ::= { cevModuleDslamType 1 }
cevNi2WanDs3Sub2Ds3 OBJECT IDENTIFIER ::= { cevModuleDslamType 2 }
cevAtuc1p2Cap   OBJECT IDENTIFIER ::= { cevModuleDslamType 3 }
cevAtuc1p2Dmt   OBJECT IDENTIFIER ::= { cevModuleDslamType 4 }
cevAtuc1p4Dmt   OBJECT IDENTIFIER ::= { cevModuleDslamType 5 }
cevLim          OBJECT IDENTIFIER ::= { cevModuleDslamType 6 }
cevNi2WanOc3smSubOc3sm OBJECT IDENTIFIER ::= { cevModuleDslamType 7 }
cevNi2WanE3Sub2E3 OBJECT IDENTIFIER ::= { cevModuleDslamType 8 }
cevNi2WanDs3Sub8Ds1Ima OBJECT IDENTIFIER ::= { cevModuleDslamType 9 }
cevAtuc1p4Cap   OBJECT IDENTIFIER ::= { cevModuleDslamType 10 }
cevStuc1p4      OBJECT IDENTIFIER ::= { cevModuleDslamType 11 }
cevAtuc1p4FlexiDmt OBJECT IDENTIFIER ::= { cevModuleDslamType 13 }
cevAtuc1p4FlexiCap OBJECT IDENTIFIER ::= { cevModuleDslamType 14 }
cevAtuc1p4Flexi OBJECT IDENTIFIER ::= { cevModuleDslamType 15 }
cevAtuc1p4DmtIsdn OBJECT IDENTIFIER ::= { cevModuleDslamType 16 }
cevNi2WanOc3smSub2Ds3 OBJECT IDENTIFIER ::= { cevModuleDslamType 17 }
cevNi2WanOc3mmSub2Ds3 OBJECT IDENTIFIER ::= { cevModuleDslamType 18 }
cevAtuc1p8DmtItemp OBJECT IDENTIFIER ::= { cevModuleDslamType 21 }
cevStuc1p8Itemp OBJECT IDENTIFIER ::= { cevModuleDslamType 22 }
cevNi2WanDs3Sub2Ds3Rev2 OBJECT IDENTIFIER ::= { cevModuleDslamType 35 }
cevNi2WanOc3smSubOc3smRev2 OBJECT IDENTIFIER ::= { cevModuleDslamType 36 }
cevNi2WanOc3mmSubOc3mmRev2 OBJECT IDENTIFIER ::= { cevModuleDslamType 37 }
cevNi2WanOc3smSub2Ds3Rev2 OBJECT IDENTIFIER ::= { cevModuleDslamType 38 }
cevNi2WanOc3mmSub2Ds3Rev2 OBJECT IDENTIFIER ::= { cevModuleDslamType 39 }
cevNi2WanOc3smSubOc3smItemp OBJECT IDENTIFIER ::= { cevModuleDslamType 40 }
cevIo6100DS3    OBJECT IDENTIFIER ::= { cevModuleDslamType 43 }
cevIo6160DS3    OBJECT IDENTIFIER ::= { cevModuleDslamType 44 }
cevIo6260OC3    OBJECT IDENTIFIER ::= { cevModuleDslamType 45 }
cevIo6260Ds3T1  OBJECT IDENTIFIER ::= { cevModuleDslamType 46 }
cevModuleWASBackCards OBJECT IDENTIFIER ::= { cevModule 26 }
cevLmBnc2t3     OBJECT IDENTIFIER ::= { cevModuleWASBackCards 1 }
cevLmBnc2e3     OBJECT IDENTIFIER ::= { cevModuleWASBackCards 2 }
cevLmDb154x21   OBJECT IDENTIFIER ::= { cevModuleWASBackCards 3 }
cevLmScsi22hssi OBJECT IDENTIFIER ::= { cevModuleWASBackCards 4 }
cevLmRj488t1    OBJECT IDENTIFIER ::= { cevModuleWASBackCards 5 }
cevLmRj488t1R   OBJECT IDENTIFIER ::= { cevModuleWASBackCards 6 }
cevLmRj488e1    OBJECT IDENTIFIER ::= { cevModuleWASBackCards 7 }
cevLmRj488e1R   OBJECT IDENTIFIER ::= { cevModuleWASBackCards 8 }
cevLmSmb8e1     OBJECT IDENTIFIER ::= { cevModuleWASBackCards 9 }
cevLmSmb8e1R    OBJECT IDENTIFIER ::= { cevModuleWASBackCards 10 }
cevLmPsmUI      OBJECT IDENTIFIER ::= { cevModuleWASBackCards 11 }
cevLmMmf4oc3    OBJECT IDENTIFIER ::= { cevModuleWASBackCards 12 }
cevLmSmfIr4oc3  OBJECT IDENTIFIER ::= { cevModuleWASBackCards 13 }
cevLmSmfLr4oc3  OBJECT IDENTIFIER ::= { cevModuleWASBackCards 14 }
cevLmSmfIr1oc12 OBJECT IDENTIFIER ::= { cevModuleWASBackCards 15 }
cevLmSmfLr1oc12 OBJECT IDENTIFIER ::= { cevModuleWASBackCards 16 }
cevLmS3Ui       OBJECT IDENTIFIER ::= { cevModuleWASBackCards 17 }
cevLm1feTx      OBJECT IDENTIFIER ::= { cevModuleWASBackCards 18 }
cevLm1feFx      OBJECT IDENTIFIER ::= { cevModuleWASBackCards 19 }
cevLm1mmfFddi   OBJECT IDENTIFIER ::= { cevModuleWASBackCards 20 }
cevLm1smfFddi   OBJECT IDENTIFIER ::= { cevModuleWASBackCards 21 }
cevLmRj454e     OBJECT IDENTIFIER ::= { cevModuleWASBackCards 22 }
cevLmMmf8oc3    OBJECT IDENTIFIER ::= { cevModuleWASBackCards 23 }
cevLmSmfIr8oc3  OBJECT IDENTIFIER ::= { cevModuleWASBackCards 24 }
cevLmSmfLr8oc3  OBJECT IDENTIFIER ::= { cevModuleWASBackCards 25 }
cevLmSmfIr1oc48 OBJECT IDENTIFIER ::= { cevModuleWASBackCards 26 }
cevLmSmfLr1oc48 OBJECT IDENTIFIER ::= { cevModuleWASBackCards 27 }
cevLmPsmHD      OBJECT IDENTIFIER ::= { cevModuleWASBackCards 28 }
cevLmSmb8t3     OBJECT IDENTIFIER ::= { cevModuleWASBackCards 29 }
cevLmSmb8e3     OBJECT IDENTIFIER ::= { cevModuleWASBackCards 30 }
cevLmSmb4stm1   OBJECT IDENTIFIER ::= { cevModuleWASBackCards 31 }
cevLmSmfIr2oc12 OBJECT IDENTIFIER ::= { cevModuleWASBackCards 32 }
cevLmSmfLr2oc12 OBJECT IDENTIFIER ::= { cevModuleWASBackCards 33 }
cevLmSmfSr1oc48 OBJECT IDENTIFIER ::= { cevModuleWASBackCards 34 }
cevLmSmfXlr1oc48 OBJECT IDENTIFIER ::= { cevModuleWASBackCards 35 }
cevLmBnc3t3     OBJECT IDENTIFIER ::= { cevModuleWASBackCards 36 }
cevLmSmfIr1Oc48B OBJECT IDENTIFIER ::= { cevModuleWASBackCards 37 }
cevLmSmfLr1Oc48B OBJECT IDENTIFIER ::= { cevModuleWASBackCards 38 }
cevLmSmfSr1Oc48B OBJECT IDENTIFIER ::= { cevModuleWASBackCards 39 }
cevLmSmfIr2Oc12B OBJECT IDENTIFIER ::= { cevModuleWASBackCards 40 }
cevLmSmfLr2Oc12B OBJECT IDENTIFIER ::= { cevModuleWASBackCards 41 }
cevLmSmfIr1Oc12C OBJECT IDENTIFIER ::= { cevModuleWASBackCards 42 }
cevLmSmfLr1Oc12C OBJECT IDENTIFIER ::= { cevModuleWASBackCards 43 }
cevLmMmf4Oc3C   OBJECT IDENTIFIER ::= { cevModuleWASBackCards 44 }
cevLmSmfIr4Oc3C OBJECT IDENTIFIER ::= { cevModuleWASBackCards 45 }
cevLmSmfLr4Oc3C OBJECT IDENTIFIER ::= { cevModuleWASBackCards 46 }
cevLmSmfXlr1Oc48B OBJECT IDENTIFIER ::= { cevModuleWASBackCards 51 }
cevLm1feTxcp    OBJECT IDENTIFIER ::= { cevModuleWASBackCards 55 }
cevLmSmfIr8Oc3C OBJECT IDENTIFIER ::= { cevModuleWASBackCards 58 }
cevLmSmfLr8Oc3C OBJECT IDENTIFIER ::= { cevModuleWASBackCards 59 }
cevLmMmf8Oc3C   OBJECT IDENTIFIER ::= { cevModuleWASBackCards 60 }
cevLmSmfIr1Oc3  OBJECT IDENTIFIER ::= { cevModuleWASBackCards 61 }
cevLmSmfLr1Oc3  OBJECT IDENTIFIER ::= { cevModuleWASBackCards 62 }
cevLmSmb1Stm1   OBJECT IDENTIFIER ::= { cevModuleWASBackCards 63 }
cevLmScsi2B2hssi OBJECT IDENTIFIER ::= { cevModuleWASBackCards 64 }
cevLm12In18s    OBJECT IDENTIFIER ::= { cevModuleWASBackCards 65 }
cevLmSmb6e3     OBJECT IDENTIFIER ::= { cevModuleWASBackCards 66 }
cevLmComboT3E3Oc3 OBJECT IDENTIFIER ::= { cevModuleWASBackCards 67 }
cevLmRj488t1e1  OBJECT IDENTIFIER ::= { cevModuleWASBackCards 68 }
cevLmMcc16e1    OBJECT IDENTIFIER ::= { cevModuleWASBackCards 69 }
cevLmRj4816t1e1 OBJECT IDENTIFIER ::= { cevModuleWASBackCards 70 }
cevLmSmfIr2Oc12c OBJECT IDENTIFIER ::= { cevModuleWASBackCards 71 }
cevLmSmfLr2Oc12c OBJECT IDENTIFIER ::= { cevModuleWASBackCards 72 }
cevLmSmb8Stm1   OBJECT IDENTIFIER ::= { cevModuleWASBackCards 82 }
cevLmSmf8Oc3Sfp OBJECT IDENTIFIER ::= { cevModuleWASBackCards 83 }
cevLmRbbn16t1e1 OBJECT IDENTIFIER ::= { cevModuleWASBackCards 84 }
cevLmSmfSr1Oc192 OBJECT IDENTIFIER ::= { cevModuleWASBackCards 85 }
cevLmSmfIr1Oc192 OBJECT IDENTIFIER ::= { cevModuleWASBackCards 86 }
cevLmSmfLr1Oc192 OBJECT IDENTIFIER ::= { cevModuleWASBackCards 87 }
cevLmSmfXlr1Oc192 OBJECT IDENTIFIER ::= { cevModuleWASBackCards 88 }
cevLmMcc8oc3    OBJECT IDENTIFIER ::= { cevModuleWASBackCards 89 }
cevLmRbbn16t1e11N OBJECT IDENTIFIER ::= { cevModuleWASBackCards 92 }
cevLmMcc16e11N  OBJECT IDENTIFIER ::= { cevModuleWASBackCards 93 }
cevLmRed16t1e1  OBJECT IDENTIFIER ::= { cevModuleWASBackCards 94 }
cevLmSfp2Oc3    OBJECT IDENTIFIER ::= { cevModuleWASBackCards 95 }
cevLmSmb2Oc3EL  OBJECT IDENTIFIER ::= { cevModuleWASBackCards 96 }
cevLmBnc3t3e3   OBJECT IDENTIFIER ::= { cevModuleWASBackCards 97 }
cevLmRed2Oc3    OBJECT IDENTIFIER ::= { cevModuleWASBackCards 98 }
cevLmRed3t3e3   OBJECT IDENTIFIER ::= { cevModuleWASBackCards 99 }
cevLmSmf4Oc12   OBJECT IDENTIFIER ::= { cevModuleWASBackCards 100 }
cevLmChamp24t1e1 OBJECT IDENTIFIER ::= { cevModuleWASBackCards 101 }
cevLmSmb3t3e3   OBJECT IDENTIFIER ::= { cevModuleWASBackCards 102 }
cevLmVxsmSmfIr4Oc3 OBJECT IDENTIFIER ::= { cevModuleWASBackCards 103 }
cevLmVxsmSmfLr4Oc3 OBJECT IDENTIFIER ::= { cevModuleWASBackCards 104 }
cevLmVxsm4Oc3R  OBJECT IDENTIFIER ::= { cevModuleWASBackCards 105 }
cevLmVxsmMmf4Oc3 OBJECT IDENTIFIER ::= { cevModuleWASBackCards 106 }
cevLm4V35       OBJECT IDENTIFIER ::= { cevModuleWASBackCards 107 }
cevLm4X21       OBJECT IDENTIFIER ::= { cevModuleWASBackCards 108 }
cevLmMgxXfUIB   OBJECT IDENTIFIER ::= { cevModuleWASBackCards 109 }
cevLm5efegeTx   OBJECT IDENTIFIER ::= { cevModuleWASBackCards 110 }
cevLmPsmHDV     OBJECT IDENTIFIER ::= { cevModuleWASBackCards 111 }
cevModuleUbrType OBJECT IDENTIFIER ::= { cevModule 27 }
cevUbrMc16s     OBJECT IDENTIFIER ::= { cevModuleUbrType 2 }
cevUbrMc11      OBJECT IDENTIFIER ::= { cevModuleUbrType 3 }
cevUbrMc11c     OBJECT IDENTIFIER ::= { cevModuleUbrType 4 }
cevUbrMc12c     OBJECT IDENTIFIER ::= { cevModuleUbrType 5 }
cevUbrMc14c     OBJECT IDENTIFIER ::= { cevModuleUbrType 6 }
cevUbrMc16a     OBJECT IDENTIFIER ::= { cevModuleUbrType 7 }
cevUbrMc16b     OBJECT IDENTIFIER ::= { cevModuleUbrType 8 }
cevUbrMc16c     OBJECT IDENTIFIER ::= { cevModuleUbrType 9 }
cevUbrMc16e     OBJECT IDENTIFIER ::= { cevModuleUbrType 10 }
cevUbrMc28c     OBJECT IDENTIFIER ::= { cevModuleUbrType 11 }
cevUbrMc26      OBJECT IDENTIFIER ::= { cevModuleUbrType 12 }
cevUbr912C      OBJECT IDENTIFIER ::= { cevModuleUbrType 13 }
cevUbr912S      OBJECT IDENTIFIER ::= { cevModuleUbrType 14 }
cevUbr914R      OBJECT IDENTIFIER ::= { cevModuleUbrType 15 }
cevUbrClk       OBJECT IDENTIFIER ::= { cevModuleUbrType 16 }
cevUbr925       OBJECT IDENTIFIER ::= { cevModuleUbrType 17 }
cevUbrMc26c     OBJECT IDENTIFIER ::= { cevModuleUbrType 18 }
cevUbrMc28cf    OBJECT IDENTIFIER ::= { cevModuleUbrType 21 }
cevUbrMc28cBnc  OBJECT IDENTIFIER ::= { cevModuleUbrType 22 }
cevUbrMc26cf    OBJECT IDENTIFIER ::= { cevModuleUbrType 23 }
cevUbrMc26cBnc  OBJECT IDENTIFIER ::= { cevModuleUbrType 24 }
cevUbrDlc24     OBJECT IDENTIFIER ::= { cevModuleUbrType 26 }
cevUbrMc28j     OBJECT IDENTIFIER ::= { cevModuleUbrType 33 }
cevUbrMc28u     OBJECT IDENTIFIER ::= { cevModuleUbrType 34 }
cevUbrMc16u     OBJECT IDENTIFIER ::= { cevModuleUbrType 35 }
cevUbrMc28x     OBJECT IDENTIFIER ::= { cevModuleUbrType 36 }
cevUbrMc16x     OBJECT IDENTIFIER ::= { cevModuleUbrType 37 }
cevUbrMc520uD   OBJECT IDENTIFIER ::= { cevModuleUbrType 38 }
cevUbrMc520uF   OBJECT IDENTIFIER ::= { cevModuleUbrType 39 }
cevUbrTccPlus   OBJECT IDENTIFIER ::= { cevModuleUbrType 41 }
cevUbrMc16uE    OBJECT IDENTIFIER ::= { cevModuleUbrType 42 }
cevUbrMc28uE    OBJECT IDENTIFIER ::= { cevModuleUbrType 43 }
cevUbrDtcc      OBJECT IDENTIFIER ::= { cevModuleUbrType 44 }
cevUbrMc88v     OBJECT IDENTIFIER ::= { cevModuleUbrType 46 }
cevUbrmc2020    OBJECT IDENTIFIER ::= { cevModuleUbrType 47 }
cevUbrMc3g60Mha OBJECT IDENTIFIER ::= { cevModuleUbrType 48 }
cevUbrMc3g60rphy OBJECT IDENTIFIER ::= { cevModuleUbrType 49 }
cevUbrcBR8      OBJECT IDENTIFIER ::= { cevModuleUbrType 50 }
cevModuleCmccType OBJECT IDENTIFIER ::= { cevModule 28 }
cevCmccCip      OBJECT IDENTIFIER ::= { cevModuleCmccType 1 }
cevCmccCip2     OBJECT IDENTIFIER ::= { cevModuleCmccType 2 }
cevCmccPa1ec    OBJECT IDENTIFIER ::= { cevModuleCmccType 3 }
cevCmccPa1pc    OBJECT IDENTIFIER ::= { cevModuleCmccType 4 }
cevCmccPa1ec4   OBJECT IDENTIFIER ::= { cevModuleCmccType 5 }
cevModuleCat6000Type OBJECT IDENTIFIER ::= { cevModule 29 }
cevCat6kWsxSup12ge OBJECT IDENTIFIER ::= { cevModuleCat6000Type 2 }
cevCat6kWsx6408Gbic OBJECT IDENTIFIER ::= { cevModuleCat6000Type 3 }
cevCat6kWsx6224Fx100Mt OBJECT IDENTIFIER ::= { cevModuleCat6000Type 4 }
cevCat6kWsx6248Rj45 OBJECT IDENTIFIER ::= { cevModuleCat6000Type 5 }
cevCat6kWsx6248Tel OBJECT IDENTIFIER ::= { cevModuleCat6000Type 6 }
cevCat6kWsx6302Msm OBJECT IDENTIFIER ::= { cevModuleCat6000Type 7 }
cevCat6kWsx6024Mtrj OBJECT IDENTIFIER ::= { cevModuleCat6000Type 9 }
cevCat6kMsfc2   OBJECT IDENTIFIER ::= { cevModuleCat6000Type 10 }
cevCat6kWsx6316GeTx OBJECT IDENTIFIER ::= { cevModuleCat6000Type 11 }
cevCat6kWsx6416Gbic OBJECT IDENTIFIER ::= { cevModuleCat6000Type 12 }
cevCat6kWsx6324100Fx OBJECT IDENTIFIER ::= { cevModuleCat6000Type 13 }
cevCat6kWsx6348Rj45 OBJECT IDENTIFIER ::= { cevModuleCat6000Type 14 }
cevCat6kWsx650210ge OBJECT IDENTIFIER ::= { cevModuleCat6000Type 15 }
cevCat6kWsx6066SlbApc OBJECT IDENTIFIER ::= { cevModuleCat6000Type 16 }
cevCat6kWsx6548Rj45 OBJECT IDENTIFIER ::= { cevModuleCat6000Type 18 }
cevCat6kWsx6248aTel OBJECT IDENTIFIER ::= { cevModuleCat6000Type 19 }
cevCat6kWsxSup22ge OBJECT IDENTIFIER ::= { cevModuleCat6000Type 20 }
cevCat6kWsc6500SFM OBJECT IDENTIFIER ::= { cevModuleCat6000Type 21 }
cevCat6kWsc6500SFM2 OBJECT IDENTIFIER ::= { cevModuleCat6000Type 22 }
cevCat6kWsx6816GBIC OBJECT IDENTIFIER ::= { cevModuleCat6000Type 23 }
cevCat6kWsx6600Audio OBJECT IDENTIFIER ::= { cevModuleCat6000Type 27 }
cevCat6kWsx6348RJ21 OBJECT IDENTIFIER ::= { cevModuleCat6000Type 28 }
cevCat6kWsx6516GBIC OBJECT IDENTIFIER ::= { cevModuleCat6000Type 29 }
cevCat6kWsxSup1a2ge OBJECT IDENTIFIER ::= { cevModuleCat6000Type 30 }
cevCat6kWsx6548RJ21 OBJECT IDENTIFIER ::= { cevModuleCat6000Type 31 }
cevCat6kWsx6416GEMT OBJECT IDENTIFIER ::= { cevModuleCat6000Type 32 }
cevCat6kWsx6380NAM OBJECT IDENTIFIER ::= { cevModuleCat6000Type 33 }
cevCat6kWsx6248aRJ45 OBJECT IDENTIFIER ::= { cevModuleCat6000Type 34 }
cevCat6kWsx6408aGbic OBJECT IDENTIFIER ::= { cevModuleCat6000Type 35 }
cevCat6kWsx6381IDS OBJECT IDENTIFIER ::= { cevModuleCat6000Type 36 }
cevCat6kWsx6524MmMT OBJECT IDENTIFIER ::= { cevModuleCat6000Type 37 }
cevCat6kWsx6516GeTx OBJECT IDENTIFIER ::= { cevModuleCat6000Type 38 }
cevCat6kWsx650110Gex4 OBJECT IDENTIFIER ::= { cevModuleCat6000Type 39 }
cevCat6kWsx6816Oc3Mm OBJECT IDENTIFIER ::= { cevModuleCat6000Type 40 }
cevCat6kWsf6kVpwr OBJECT IDENTIFIER ::= { cevModuleCat6000Type 41 }
cevCat6kWsSvcNam1 OBJECT IDENTIFIER ::= { cevModuleCat6000Type 42 }
cevCat6kWsSvcNam2 OBJECT IDENTIFIER ::= { cevModuleCat6000Type 43 }
cevCat6kWsSvcFwm1 OBJECT IDENTIFIER ::= { cevModuleCat6000Type 44 }
cevCat6kWsSvcSsl1 OBJECT IDENTIFIER ::= { cevModuleCat6000Type 45 }
cevCat6kWsx6516aGBIC OBJECT IDENTIFIER ::= { cevModuleCat6000Type 46 }
cevCat6kIpSecVPNSm OBJECT IDENTIFIER ::= { cevModuleCat6000Type 49 }
cevCat6kWsSup720 OBJECT IDENTIFIER ::= { cevModuleCat6000Type 50 }
cevCat6kWsSup720Base OBJECT IDENTIFIER ::= { cevModuleCat6000Type 51 }
cevCat6kWsx680210Ge OBJECT IDENTIFIER ::= { cevModuleCat6000Type 52 }
cevCat6kWsx6832Sfp OBJECT IDENTIFIER ::= { cevModuleCat6000Type 53 }
cevCat6kWsx6748GeTx OBJECT IDENTIFIER ::= { cevModuleCat6000Type 54 }
cevCat6kWsx670410Ge OBJECT IDENTIFIER ::= { cevModuleCat6000Type 55 }
cevCat6kWsx6748Sfp OBJECT IDENTIFIER ::= { cevModuleCat6000Type 56 }
cevCat6kWsx6724Sfp OBJECT IDENTIFIER ::= { cevModuleCat6000Type 57 }
cevCat6kWsf6kPfc OBJECT IDENTIFIER ::= { cevModuleCat6000Type 58 }
cevCat6kWsf6kPfc2 OBJECT IDENTIFIER ::= { cevModuleCat6000Type 59 }
cevCat6kWsf6kDfc OBJECT IDENTIFIER ::= { cevModuleCat6000Type 60 }
cevCat6kWsf6kPfc3a OBJECT IDENTIFIER ::= { cevModuleCat6000Type 61 }
cevCat6kWsf6kDfc3a OBJECT IDENTIFIER ::= { cevModuleCat6000Type 62 }
cevCat6kWsx6148GeTx OBJECT IDENTIFIER ::= { cevModuleCat6000Type 63 }
cevCat6kWsx6148Rj21 OBJECT IDENTIFIER ::= { cevModuleCat6000Type 64 }
cevCat6kWsx6148Rj45 OBJECT IDENTIFIER ::= { cevModuleCat6000Type 65 }
cevCat6kMWAMBlade OBJECT IDENTIFIER ::= { cevModuleCat6000Type 66 }
cevCat6kWsx6548GeTx OBJECT IDENTIFIER ::= { cevModuleCat6000Type 67 }
cevCat6kWsf6700dfc3a OBJECT IDENTIFIER ::= { cevModuleCat6000Type 68 }
cevCat6kWsx6324100FxSm OBJECT IDENTIFIER ::= { cevModuleCat6000Type 69 }
cevCat6kWsc6000cl OBJECT IDENTIFIER ::= { cevModuleCat6000Type 70 }
cevCat6kWsc6513cl OBJECT IDENTIFIER ::= { cevModuleCat6000Type 71 }
cevClk7600      OBJECT IDENTIFIER ::= { cevModuleCat6000Type 72 }
cevCat6kWsc6kvtt OBJECT IDENTIFIER ::= { cevModuleCat6000Type 73 }
cevCat6kWsx6302aMsm OBJECT IDENTIFIER ::= { cevModuleCat6000Type 74 }
cevCat6kMemC6kAta164M OBJECT IDENTIFIER ::= { cevModuleCat6000Type 75 }
cevCat6kMemC6kCptfl64M OBJECT IDENTIFIER ::= { cevModuleCat6000Type 76 }
cevCat6kMemC6kCptfl128M OBJECT IDENTIFIER ::= { cevModuleCat6000Type 77 }
cevCat6kMemC6kCptfl256M OBJECT IDENTIFIER ::= { cevModuleCat6000Type 78 }
cevCat6kMemC6kFlc16M OBJECT IDENTIFIER ::= { cevModuleCat6000Type 79 }
cevCat6kMemC6kFlc24M OBJECT IDENTIFIER ::= { cevModuleCat6000Type 80 }
cevCat6kWsSvcIdsm2 OBJECT IDENTIFIER ::= { cevModuleCat6000Type 81 }
cevCat6kWssvcidsupg OBJECT IDENTIFIER ::= { cevModuleCat6000Type 82 }
cevCat6kWsx6148x2Rj45 OBJECT IDENTIFIER ::= { cevModuleCat6000Type 83 }
cevCat6kWsf6kFe48x2Af OBJECT IDENTIFIER ::= { cevModuleCat6000Type 84 }
cevCat6kWsf6kFe48Af OBJECT IDENTIFIER ::= { cevModuleCat6000Type 85 }
cevCat6kWsf6kGe48Af OBJECT IDENTIFIER ::= { cevModuleCat6000Type 86 }
cevCat6kWsf6kVpwrGe OBJECT IDENTIFIER ::= { cevModuleCat6000Type 87 }
cevCat6kWsf6700cfc OBJECT IDENTIFIER ::= { cevModuleCat6000Type 88 }
cevCat6kWsSvcWlan1K9 OBJECT IDENTIFIER ::= { cevModuleCat6000Type 89 }
cevCat6kWsx6624Fxs OBJECT IDENTIFIER ::= { cevModuleCat6000Type 90 }
cevCat6kWsSvcAon1 OBJECT IDENTIFIER ::= { cevModuleCat6000Type 91 }
cevCat6kWsSup32ge OBJECT IDENTIFIER ::= { cevModuleCat6000Type 92 }
cevCat6kWsSup3210ge OBJECT IDENTIFIER ::= { cevModuleCat6000Type 93 }
cevCat6kPSDBlade OBJECT IDENTIFIER ::= { cevModuleCat6000Type 94 }
cevCat6kWsc6kvtte OBJECT IDENTIFIER ::= { cevModuleCat6000Type 95 }
cevCat6kWsx6066SlbsK9 OBJECT IDENTIFIER ::= { cevModuleCat6000Type 98 }
cevCat6kWsf6kpfc3b OBJECT IDENTIFIER ::= { cevModuleCat6000Type 99 }
cevCat6kWsf6kdfc3b OBJECT IDENTIFIER ::= { cevModuleCat6000Type 100 }
cevCat6kWsf6700dfc3b OBJECT IDENTIFIER ::= { cevModuleCat6000Type 101 }
cevCat6kWsf6kpfc3bxl OBJECT IDENTIFIER ::= { cevModuleCat6000Type 102 }
cevCat6kWsf6kdfc3bxl OBJECT IDENTIFIER ::= { cevModuleCat6000Type 103 }
cevCat6kWsf6700dfc3bxl OBJECT IDENTIFIER ::= { cevModuleCat6000Type 104 }
cevCat6kCsg     OBJECT IDENTIFIER ::= { cevModuleCat6000Type 105 }
cevCat6kMsfc2a  OBJECT IDENTIFIER ::= { cevModuleCat6000Type 106 }
cevCat6kWs6340Sup OBJECT IDENTIFIER ::= { cevModuleCat6000Type 107 }
cevCat6kWs6340LcA OBJECT IDENTIFIER ::= { cevModuleCat6000Type 108 }
cevCat6kWs6340LcB OBJECT IDENTIFIER ::= { cevModuleCat6000Type 109 }
cevCat6kMec6524gs8s OBJECT IDENTIFIER ::= { cevModuleCat6000Type 110 }
cevCat6kMec6524gt8s OBJECT IDENTIFIER ::= { cevModuleCat6000Type 111 }
cevCat6kMec6524Msfc2a OBJECT IDENTIFIER ::= { cevModuleCat6000Type 114 }
cevCat6kMec6524Pfc3c OBJECT IDENTIFIER ::= { cevModuleCat6000Type 115 }
cevCat6kWsx6196Rj21 OBJECT IDENTIFIER ::= { cevModuleCat6000Type 116 }
cevCat6kWsx6148FeSfp OBJECT IDENTIFIER ::= { cevModuleCat6000Type 117 }
cevCat6kWsx6148aGeTx OBJECT IDENTIFIER ::= { cevModuleCat6000Type 118 }
cevCat6kWsx6148aRj45 OBJECT IDENTIFIER ::= { cevModuleCat6000Type 119 }
cevCat6kAce10K9 OBJECT IDENTIFIER ::= { cevModuleCat6000Type 120 }
cevCat6kWsg6483 OBJECT IDENTIFIER ::= { cevModuleCat6000Type 122 }
cevCat6kWsg6485 OBJECT IDENTIFIER ::= { cevModuleCat6000Type 123 }
cevCat6kWsg6488 OBJECT IDENTIFIER ::= { cevModuleCat6000Type 124 }
cevCat6kWsg6489 OBJECT IDENTIFIER ::= { cevModuleCat6000Type 125 }
cevCat6kWsSvcWebVpnK9 OBJECT IDENTIFIER ::= { cevModuleCat6000Type 126 }
cevCat6kSAMIBB  OBJECT IDENTIFIER ::= { cevModuleCat6000Type 127 }
cevCat6kWsx6708a10ge OBJECT IDENTIFIER ::= { cevModuleCat6000Type 128 }
cevCat6kWsx670810ge OBJECT IDENTIFIER ::= { cevModuleCat6000Type 129 }
cevCat6kWsf6700Dfc3c OBJECT IDENTIFIER ::= { cevModuleCat6000Type 131 }
cevCat6kWsf6700Dfc3cxl OBJECT IDENTIFIER ::= { cevModuleCat6000Type 132 }
cevCat6kVsS72010G OBJECT IDENTIFIER ::= { cevModuleCat6000Type 133 }
cevCat6kVsf6kPfc3c OBJECT IDENTIFIER ::= { cevModuleCat6000Type 134 }
cevCat6kVsf6kPfc3cxl OBJECT IDENTIFIER ::= { cevModuleCat6000Type 135 }
cevCat6kVsF6kMsfc3 OBJECT IDENTIFIER ::= { cevModuleCat6000Type 136 }
cevCat6kWsF6kPisa OBJECT IDENTIFIER ::= { cevModuleCat6000Type 137 }
cevCat6kVsF6kPfc4xl OBJECT IDENTIFIER ::= { cevModuleCat6000Type 138 }
cevCat6kWsF6kDfc4exl OBJECT IDENTIFIER ::= { cevModuleCat6000Type 139 }
cevCat6kWsx671610Ge OBJECT IDENTIFIER ::= { cevModuleCat6000Type 142 }
cevCat6kVsF6kPfc4 OBJECT IDENTIFIER ::= { cevModuleCat6000Type 143 }
cevCat6kWsF6kDfc4e OBJECT IDENTIFIER ::= { cevModuleCat6000Type 144 }
cevCat6kWsSup32Pge OBJECT IDENTIFIER ::= { cevModuleCat6000Type 145 }
cevCat6kWsSup32P10ge OBJECT IDENTIFIER ::= { cevModuleCat6000Type 146 }
cevCat6kWsx690810g OBJECT IDENTIFIER ::= { cevModuleCat6000Type 148 }
cevCat6kWsc6513Ecl OBJECT IDENTIFIER ::= { cevModuleCat6000Type 155 }
cevCat6kWsSvcWism OBJECT IDENTIFIER ::= { cevModuleCat6000Type 156 }
cevCat6kWsSvcNam1S250 OBJECT IDENTIFIER ::= { cevModuleCat6000Type 157 }
cevCat6kWsSvcNam2S250 OBJECT IDENTIFIER ::= { cevModuleCat6000Type 158 }
cevCat6kWsF6kDfc4a OBJECT IDENTIFIER ::= { cevModuleCat6000Type 159 }
cevCat6kWsF6kDfc4axl OBJECT IDENTIFIER ::= { cevModuleCat6000Type 160 }
cevCat6kVsSup2t10g OBJECT IDENTIFIER ::= { cevModuleCat6000Type 163 }
cevCat6kVsF6kMsfc5 OBJECT IDENTIFIER ::= { cevModuleCat6000Type 164 }
cevCat6kWsf6k48At OBJECT IDENTIFIER ::= { cevModuleCat6000Type 166 }
cevCat6kWsx6148eGe45At OBJECT IDENTIFIER ::= { cevModuleCat6000Type 167 }
cevCat6kWsx671610T OBJECT IDENTIFIER ::= { cevModuleCat6000Type 168 }
cevCat6kWsSvcAsaSm1 OBJECT IDENTIFIER ::= { cevModuleCat6000Type 169 }
cevCat6kWsx6148eGeTx OBJECT IDENTIFIER ::= { cevModuleCat6000Type 172 }
cevCat6kWsx690440g OBJECT IDENTIFIER ::= { cevModuleCat6000Type 174 }
cevCat6kWsSvcNam3K9 OBJECT IDENTIFIER ::= { cevModuleCat6000Type 175 }
cevCat6kWsx6848Tx OBJECT IDENTIFIER ::= { cevModuleCat6000Type 176 }
cevCat6kWsx6848sfp OBJECT IDENTIFIER ::= { cevModuleCat6000Type 178 }
cevCat6kWsx6824sfp OBJECT IDENTIFIER ::= { cevModuleCat6000Type 179 }
cevCat6kWsx681610ge OBJECT IDENTIFIER ::= { cevModuleCat6000Type 181 }
cevCat6kWsx681610t OBJECT IDENTIFIER ::= { cevModuleCat6000Type 182 }
cevCat6kACE20K9 OBJECT IDENTIFIER ::= { cevModuleCat6000Type 184 }
cevCat6kWsSvcWism2 OBJECT IDENTIFIER ::= { cevModuleCat6000Type 185 }
cevCat6kWsSvcAsaSm1K7 OBJECT IDENTIFIER ::= { cevModuleCat6000Type 186 }
cevCat6kWsSvcVse1K9 OBJECT IDENTIFIER ::= { cevModuleCat6000Type 187 }
cevCat6kSvcAppProc1 OBJECT IDENTIFIER ::= { cevModuleCat6000Type 188 }
cevCat6kC6880xSup OBJECT IDENTIFIER ::= { cevModuleCat6000Type 189 }
cevCat6kC6880xleSup OBJECT IDENTIFIER ::= { cevModuleCat6000Type 190 }
cevCat6kC6880x16p10g OBJECT IDENTIFIER ::= { cevModuleCat6000Type 191 }
cevCat6kC6880xle16p10g OBJECT IDENTIFIER ::= { cevModuleCat6000Type 192 }
cevCat6kC6800xl33vCon OBJECT IDENTIFIER ::= { cevModuleCat6000Type 195 }
cevCat6kC680032p10g OBJECT IDENTIFIER ::= { cevModuleCat6000Type 196 }
cevCat6kC680032p10gxl OBJECT IDENTIFIER ::= { cevModuleCat6000Type 197 }
cevCat6kC680016p10g OBJECT IDENTIFIER ::= { cevModuleCat6000Type 198 }
cevCat6kC680016p10gxl OBJECT IDENTIFIER ::= { cevModuleCat6000Type 199 }
cevCat6kC68008p10g OBJECT IDENTIFIER ::= { cevModuleCat6000Type 200 }
cevCat6kC68008p10gxl OBJECT IDENTIFIER ::= { cevModuleCat6000Type 201 }
cevCat6kIA48FPDR OBJECT IDENTIFIER ::= { cevModuleCat6000Type 210 }
cevCat6kPrimus  OBJECT IDENTIFIER ::= { cevModuleCat6000Type 211 }
cevCat6kOptimus OBJECT IDENTIFIER ::= { cevModuleCat6000Type 212 }
cevCat6kRodimus OBJECT IDENTIFIER ::= { cevModuleCat6000Type 213 }
cevCat6kTransformer OBJECT IDENTIFIER ::= { cevModuleCat6000Type 214 }
cevCat6kC6800Sup6t OBJECT IDENTIFIER ::= { cevModuleCat6000Type 215 }
cevCat6kC6800Sup6txl OBJECT IDENTIFIER ::= { cevModuleCat6000Type 216 }
cevModuleCat5000Type OBJECT IDENTIFIER ::= { cevModule 30 }
cevCat5kRsfc    OBJECT IDENTIFIER ::= { cevModuleCat5000Type 1 }
cevModule7100Type OBJECT IDENTIFIER ::= { cevModule 31 }
cevIo2feTxIsl   OBJECT IDENTIFIER ::= { cevModule7100Type 1 }
cevIsmIpsecMppe OBJECT IDENTIFIER ::= { cevModule7100Type 2 }
cev7100VPNAccelerator OBJECT IDENTIFIER ::= { cevModule7100Type 3 }
cev7100VPNAcceleratorModule2 OBJECT IDENTIFIER ::= { cevModule7100Type 4 }
cev7100VPNAcceleratorAES OBJECT IDENTIFIER ::= { cevModule7100Type 5 }
cev7100VPNAM2Plus OBJECT IDENTIFIER ::= { cevModule7100Type 6 }
cevModule10000Type OBJECT IDENTIFIER ::= { cevModule 32 }
cevPos1oc12     OBJECT IDENTIFIER ::= { cevModule10000Type 1 }
cevP6Ct3        OBJECT IDENTIFIER ::= { cevModule10000Type 2 }
cevGe           OBJECT IDENTIFIER ::= { cevModule10000Type 3 }
cevAtm1Oc12     OBJECT IDENTIFIER ::= { cevModule10000Type 4 }
cevP1COc12      OBJECT IDENTIFIER ::= { cevModule10000Type 5 }
cevP4Chstm1     OBJECT IDENTIFIER ::= { cevModule10000Type 6 }
cev24feTx       OBJECT IDENTIFIER ::= { cevModule10000Type 8 }
cev24feFxMm     OBJECT IDENTIFIER ::= { cevModule10000Type 9 }
cev24feFxSm     OBJECT IDENTIFIER ::= { cevModule10000Type 10 }
cevSrpOc48SmSr  OBJECT IDENTIFIER ::= { cevModule10000Type 11 }
cevSrpOc48SmIr  OBJECT IDENTIFIER ::= { cevModule10000Type 12 }
cevPos6oc3      OBJECT IDENTIFIER ::= { cevModule10000Type 13 }
cevAtm4oc3      OBJECT IDENTIFIER ::= { cevModule10000Type 14 }
cevP8E3Ds3      OBJECT IDENTIFIER ::= { cevModule10000Type 15 }
cevSrpPos1oc48SmSr OBJECT IDENTIFIER ::= { cevModule10000Type 16 }
cevSrpPos1oc48SmLr OBJECT IDENTIFIER ::= { cevModule10000Type 17 }
cevC10K48MbFlashCard OBJECT IDENTIFIER ::= { cevModule10000Type 18 }
cevC10K128MbFlashCard OBJECT IDENTIFIER ::= { cevModule10000Type 19 }
cevP24ChE1T1    OBJECT IDENTIFIER ::= { cevModule10000Type 22 }
cev4Ge8FeTx     OBJECT IDENTIFIER ::= { cevModule10000Type 23 }
cev4Ge8FeFxMm   OBJECT IDENTIFIER ::= { cevModule10000Type 24 }
cev4Ge8FeFxSm   OBJECT IDENTIFIER ::= { cevModule10000Type 25 }
cevSrpOc48SmLr1 OBJECT IDENTIFIER ::= { cevModule10000Type 26 }
cevSrpOc48SmLr2 OBJECT IDENTIFIER ::= { cevModule10000Type 27 }
cevP8Fe         OBJECT IDENTIFIER ::= { cevModule10000Type 30 }
cevP8Ds3E3Atm   OBJECT IDENTIFIER ::= { cevModule10000Type 31 }
cevC10720Mnt    OBJECT IDENTIFIER ::= { cevModule10000Type 32 }
cevPosSrpOc48SmSr OBJECT IDENTIFIER ::= { cevModule10000Type 34 }
cevPosSrpOc48SmIr OBJECT IDENTIFIER ::= { cevModule10000Type 35 }
cevPosSrpOc48SmLr1 OBJECT IDENTIFIER ::= { cevModule10000Type 36 }
cevPosSrpOc48SmLr2 OBJECT IDENTIFIER ::= { cevModule10000Type 37 }
cevC10KJacket   OBJECT IDENTIFIER ::= { cevModule10000Type 38 }
cev24feTxB      OBJECT IDENTIFIER ::= { cevModule10000Type 39 }
cev4Ge8FeTxB    OBJECT IDENTIFIER ::= { cevModule10000Type 40 }
cevRprSrpOc48   OBJECT IDENTIFIER ::= { cevModule10000Type 41 }
cevP4Ct3        OBJECT IDENTIFIER ::= { cevModule10000Type 42 }
cevAtm4oc3stm1Lr OBJECT IDENTIFIER ::= { cevModule10000Type 43 }
cevModuleAs5400Type OBJECT IDENTIFIER ::= { cevModule 33 }
cevAs5400DfcCarrier OBJECT IDENTIFIER ::= { cevModuleAs5400Type 1 }
cevAs5400DfcNp348 OBJECT IDENTIFIER ::= { cevModuleAs5400Type 2 }
cevAs5400DfcNp192 OBJECT IDENTIFIER ::= { cevModuleAs5400Type 3 }
cevAs5400XMDfcCarrier OBJECT IDENTIFIER ::= { cevModuleAs5400Type 4 }
cevAs5400XMVFC  OBJECT IDENTIFIER ::= { cevModuleAs5400Type 5 }
cevModuleCat4000Type OBJECT IDENTIFIER ::= { cevModule 35 }
cevCat4232L3    OBJECT IDENTIFIER ::= { cevModuleCat4000Type 1 }
cevCat4kGateway OBJECT IDENTIFIER ::= { cevModuleCat4000Type 2 }
cevCat4kWsx4014 OBJECT IDENTIFIER ::= { cevModuleCat4000Type 3 }
cevCat4kWsx4124FxMt OBJECT IDENTIFIER ::= { cevModuleCat4000Type 4 }
cevCat4kWsx4148FxMt OBJECT IDENTIFIER ::= { cevModuleCat4000Type 5 }
cevCat4kWsx4148Rj OBJECT IDENTIFIER ::= { cevModuleCat4000Type 6 }
cevCat4kWsx4148Rj21 OBJECT IDENTIFIER ::= { cevModuleCat4000Type 7 }
cevCat4kWsx4148Rj45V OBJECT IDENTIFIER ::= { cevModuleCat4000Type 8 }
cevCat4kWsx4232GbRj OBJECT IDENTIFIER ::= { cevModuleCat4000Type 9 }
cevCat4kWsx4232RjXx OBJECT IDENTIFIER ::= { cevModuleCat4000Type 10 }
cevCat4kWsx4306Gb OBJECT IDENTIFIER ::= { cevModuleCat4000Type 11 }
cevCat4kWsx4418Gb OBJECT IDENTIFIER ::= { cevModuleCat4000Type 12 }
cevCat4kWsx44122GbTx OBJECT IDENTIFIER ::= { cevModuleCat4000Type 13 }
cevCat4kWsx4424GbRj45 OBJECT IDENTIFIER ::= { cevModuleCat4000Type 14 }
cevCat4kWsx4448GbLx OBJECT IDENTIFIER ::= { cevModuleCat4000Type 15 }
cevCat4kWsx4448GbRj45 OBJECT IDENTIFIER ::= { cevModuleCat4000Type 16 }
cevCat4kPEM     OBJECT IDENTIFIER ::= { cevModuleCat4000Type 17 }
cevCat4kWsx4515 OBJECT IDENTIFIER ::= { cevModuleCat4000Type 18 }
cevCat4kWsx4148LxMt OBJECT IDENTIFIER ::= { cevModuleCat4000Type 19 }
cevCat4kWsx4248Rj45V OBJECT IDENTIFIER ::= { cevModuleCat4000Type 20 }
cevCat4kWsx4516 OBJECT IDENTIFIER ::= { cevModuleCat4000Type 21 }
cevCat4kWsx4013Plus OBJECT IDENTIFIER ::= { cevModuleCat4000Type 22 }
cevCat4kWsx4248Rj21V OBJECT IDENTIFIER ::= { cevModuleCat4000Type 23 }
cevCat4kWsx4302Gb OBJECT IDENTIFIER ::= { cevModuleCat4000Type 24 }
cevCat4kWsx4548GbRj45V OBJECT IDENTIFIER ::= { cevModuleCat4000Type 25 }
cevCat4kWsx4548GbRj45 OBJECT IDENTIFIER ::= { cevModuleCat4000Type 26 }
cevCat4kWsx4712Qam24B OBJECT IDENTIFIER ::= { cevModuleCat4000Type 27 }
cevCat4kWsx4148FeBdLc OBJECT IDENTIFIER ::= { cevModuleCat4000Type 28 }
cevCat4kWsx4124Rj OBJECT IDENTIFIER ::= { cevModuleCat4000Type 29 }
cevCat4kWsx4224Rj45V OBJECT IDENTIFIER ::= { cevModuleCat4000Type 30 }
cevCat4kWsx4524GbRj45V OBJECT IDENTIFIER ::= { cevModuleCat4000Type 31 }
cevCat4kWsx4506GBT OBJECT IDENTIFIER ::= { cevModuleCat4000Type 32 }
cevCat4kWsxSvcNam OBJECT IDENTIFIER ::= { cevModuleCat4000Type 33 }
cevCat4kWsx4448GbSfp OBJECT IDENTIFIER ::= { cevModuleCat4000Type 34 }
cevCat4kWsX4013PlusTS OBJECT IDENTIFIER ::= { cevModuleCat4000Type 35 }
cevCat4kWsx4kClock OBJECT IDENTIFIER ::= { cevModuleCat4000Type 36 }
cevCat4kWsx4948 OBJECT IDENTIFIER ::= { cevModuleCat4000Type 37 }
cevCat4kWsx451610GE OBJECT IDENTIFIER ::= { cevModuleCat4000Type 38 }
cevCat4kWsx4013Plus10GE OBJECT IDENTIFIER ::= { cevModuleCat4000Type 40 }
cevCat4kWsx494810GE OBJECT IDENTIFIER ::= { cevModuleCat4000Type 42 }
cevCat4kWsx4kMux OBJECT IDENTIFIER ::= { cevModuleCat4000Type 43 }
cevCat4kWsx490410ge OBJECT IDENTIFIER ::= { cevModuleCat4000Type 44 }
cevCat4kWsx4900M OBJECT IDENTIFIER ::= { cevModuleCat4000Type 45 }
cevCat4kWsx490810ge OBJECT IDENTIFIER ::= { cevModuleCat4000Type 46 }
cevCat4kWsx4920Gbrj45 OBJECT IDENTIFIER ::= { cevModuleCat4000Type 47 }
cevCat4kWsx4590 OBJECT IDENTIFIER ::= { cevModuleCat4000Type 48 }
cevCatWsx4624SfpE OBJECT IDENTIFIER ::= { cevModuleCat4000Type 49 }
cevCat4kWsx492810GE OBJECT IDENTIFIER ::= { cevModuleCat4000Type 50 }
cevCat4kWsx4548GbRj45VPlus OBJECT IDENTIFIER ::= { cevModuleCat4000Type 51 }
cevCat4kWsx490810GRj45 OBJECT IDENTIFIER ::= { cevModuleCat4000Type 52 }
cevCat4kWsx4948ef10GE OBJECT IDENTIFIER ::= { cevModuleCat4000Type 54 }
cevCat4kC4kxNm8 OBJECT IDENTIFIER ::= { cevModuleCat4000Type 55 }
cevCat4kWsx4500x16 OBJECT IDENTIFIER ::= { cevModuleCat4000Type 56 }
cevCat4kWsx4500x32 OBJECT IDENTIFIER ::= { cevModuleCat4000Type 57 }
cevModuleCVAType OBJECT IDENTIFIER ::= { cevModule 36 }
cevCVA122       OBJECT IDENTIFIER ::= { cevModuleCVAType 1 }
cevCVA124       OBJECT IDENTIFIER ::= { cevModuleCVAType 2 }
cevCVA122E      OBJECT IDENTIFIER ::= { cevModuleCVAType 3 }
cevCVA124E      OBJECT IDENTIFIER ::= { cevModuleCVAType 4 }
cevModuleAs5850Type OBJECT IDENTIFIER ::= { cevModule 37 }
cevAs5850EPM2Ge OBJECT IDENTIFIER ::= { cevModuleAs5850Type 1 }
cevAs5850Ct3Up216 OBJECT IDENTIFIER ::= { cevModuleAs5850Type 2 }
cevAs58508Ce1Up216 OBJECT IDENTIFIER ::= { cevModuleAs5850Type 3 }
cevAs58xxUp324  OBJECT IDENTIFIER ::= { cevModuleAs5850Type 4 }
cevAs585024E1   OBJECT IDENTIFIER ::= { cevModuleAs5850Type 5 }
cevAs585024T1   OBJECT IDENTIFIER ::= { cevModuleAs5850Type 6 }
cevModuleAs5350Type OBJECT IDENTIFIER ::= { cevModule 38 }
cevAs5350XMDfcCarrier OBJECT IDENTIFIER ::= { cevModuleAs5350Type 2 }
cevModule24xxType OBJECT IDENTIFIER ::= { cevModule 39 }
cevIad2420Vm8fxs OBJECT IDENTIFIER ::= { cevModule24xxType 1 }
cevIad242016fxs OBJECT IDENTIFIER ::= { cevModule24xxType 2 }
cevIad2420VmPwr OBJECT IDENTIFIER ::= { cevModule24xxType 3 }
cevIad2420Adsl  OBJECT IDENTIFIER ::= { cevModule24xxType 4 }
cevIad2420Hcm1  OBJECT IDENTIFIER ::= { cevModule24xxType 5 }
cevIad2420Hcm2  OBJECT IDENTIFIER ::= { cevModule24xxType 6 }
cevIad2420Hcm3  OBJECT IDENTIFIER ::= { cevModule24xxType 7 }
cevIad2420Hcm4  OBJECT IDENTIFIER ::= { cevModule24xxType 8 }
cevIad2420Hcm5  OBJECT IDENTIFIER ::= { cevModule24xxType 9 }
cevIad2420Hcm6  OBJECT IDENTIFIER ::= { cevModule24xxType 10 }
cevIad2420Cpu   OBJECT IDENTIFIER ::= { cevModule24xxType 11 }
cevIad2420MfmE1Unbalanced OBJECT IDENTIFIER ::= { cevModule24xxType 12 }
cevIad2420MfmE1Dsx1Csu OBJECT IDENTIFIER ::= { cevModule24xxType 13 }
cevIad2420MfmT1Dsx1Csu OBJECT IDENTIFIER ::= { cevModule24xxType 14 }
cevIad24208fxo  OBJECT IDENTIFIER ::= { cevModule24xxType 15 }
cevIad242016fxsOffPremise OBJECT IDENTIFIER ::= { cevModule24xxType 18 }
cevIad2430Ob8Fxs OBJECT IDENTIFIER ::= { cevModule24xxType 19 }
cevIad2430Ob16Fxs OBJECT IDENTIFIER ::= { cevModule24xxType 20 }
cevIad2430Ob24Fxs OBJECT IDENTIFIER ::= { cevModule24xxType 21 }
cevIad2430ObT1E1 OBJECT IDENTIFIER ::= { cevModule24xxType 22 }
cevIad2435ObT1E1 OBJECT IDENTIFIER ::= { cevModule24xxType 23 }
cevIad2435Ob8Fxs OBJECT IDENTIFIER ::= { cevModule24xxType 24 }
cevVG204Ob4Fxs  OBJECT IDENTIFIER ::= { cevModule24xxType 25 }
cevVG202Ob2Fxs  OBJECT IDENTIFIER ::= { cevModule24xxType 26 }
cevVg202xmOb2fxs OBJECT IDENTIFIER ::= { cevModule24xxType 27 }
cevVg204xmOb4fxs OBJECT IDENTIFIER ::= { cevModule24xxType 28 }
cevVg3x0ob24fxs OBJECT IDENTIFIER ::= { cevModule24xxType 29 }
cevModule10000Bases OBJECT IDENTIFIER ::= { cevModule 40 }
cevM10000BaseLX4 OBJECT IDENTIFIER ::= { cevModule10000Bases 2 }
cevM10000BaseEX4 OBJECT IDENTIFIER ::= { cevModule10000Bases 3 }
cevM10000BaseLR OBJECT IDENTIFIER ::= { cevModule10000Bases 4 }
cevM10000BaseER OBJECT IDENTIFIER ::= { cevModule10000Bases 5 }
cevM10000BaseSX4 OBJECT IDENTIFIER ::= { cevModule10000Bases 6 }
cevM10000BaseSR OBJECT IDENTIFIER ::= { cevModule10000Bases 7 }
cevM10000BaseCX4 OBJECT IDENTIFIER ::= { cevModule10000Bases 8 }
cevM10000BaseZR OBJECT IDENTIFIER ::= { cevModule10000Bases 9 }
cev10GBaseLW    OBJECT IDENTIFIER ::= { cevModule10000Bases 10 }
cev10GBaseEW    OBJECT IDENTIFIER ::= { cevModule10000Bases 11 }
cev10GBaseSW    OBJECT IDENTIFIER ::= { cevModule10000Bases 12 }
cev10GBaseEdc1310 OBJECT IDENTIFIER ::= { cevModule10000Bases 13 }
cev10GBaseDwdm3033 OBJECT IDENTIFIER ::= { cevModule10000Bases 14 }
cev10GBaseDwdm3112 OBJECT IDENTIFIER ::= { cevModule10000Bases 15 }
cev10GBaseDwdm3190 OBJECT IDENTIFIER ::= { cevModule10000Bases 16 }
cev10GBaseDwdm3268 OBJECT IDENTIFIER ::= { cevModule10000Bases 17 }
cev10GBaseDwdm3425 OBJECT IDENTIFIER ::= { cevModule10000Bases 18 }
cev10GBaseDwdm3504 OBJECT IDENTIFIER ::= { cevModule10000Bases 19 }
cev10GBaseDwdm3582 OBJECT IDENTIFIER ::= { cevModule10000Bases 20 }
cev10GBaseDwdm3661 OBJECT IDENTIFIER ::= { cevModule10000Bases 21 }
cev10GBaseDwdm3819 OBJECT IDENTIFIER ::= { cevModule10000Bases 22 }
cev10GBaseDwdm3898 OBJECT IDENTIFIER ::= { cevModule10000Bases 23 }
cev10GBaseDwdm3977 OBJECT IDENTIFIER ::= { cevModule10000Bases 24 }
cev10GBaseDwdm4056 OBJECT IDENTIFIER ::= { cevModule10000Bases 25 }
cev10GBaseDwdm4214 OBJECT IDENTIFIER ::= { cevModule10000Bases 26 }
cev10GBaseDwdm4294 OBJECT IDENTIFIER ::= { cevModule10000Bases 27 }
cev10GBaseDwdm4373 OBJECT IDENTIFIER ::= { cevModule10000Bases 28 }
cev10GBaseDwdm4453 OBJECT IDENTIFIER ::= { cevModule10000Bases 29 }
cev10GBaseDwdm4612 OBJECT IDENTIFIER ::= { cevModule10000Bases 30 }
cev10GBaseDwdm4692 OBJECT IDENTIFIER ::= { cevModule10000Bases 31 }
cev10GBaseDwdm4772 OBJECT IDENTIFIER ::= { cevModule10000Bases 32 }
cev10GBaseDwdm4851 OBJECT IDENTIFIER ::= { cevModule10000Bases 33 }
cev10GBaseDwdm5012 OBJECT IDENTIFIER ::= { cevModule10000Bases 34 }
cev10GBaseDwdm5092 OBJECT IDENTIFIER ::= { cevModule10000Bases 35 }
cev10GBaseDwdm5172 OBJECT IDENTIFIER ::= { cevModule10000Bases 36 }
cev10GBaseDwdm5252 OBJECT IDENTIFIER ::= { cevModule10000Bases 37 }
cev10GBaseDwdm5413 OBJECT IDENTIFIER ::= { cevModule10000Bases 38 }
cev10GBaseDwdm5494 OBJECT IDENTIFIER ::= { cevModule10000Bases 39 }
cev10GBaseDwdm5575 OBJECT IDENTIFIER ::= { cevModule10000Bases 40 }
cev10GBaseDwdm5655 OBJECT IDENTIFIER ::= { cevModule10000Bases 41 }
cev10GBaseDwdm5817 OBJECT IDENTIFIER ::= { cevModule10000Bases 42 }
cev10GBaseDwdm5898 OBJECT IDENTIFIER ::= { cevModule10000Bases 43 }
cev10GBaseDwdm5979 OBJECT IDENTIFIER ::= { cevModule10000Bases 44 }
cev10GBaseDwdm6061 OBJECT IDENTIFIER ::= { cevModule10000Bases 45 }
cev10GBaseRec   OBJECT IDENTIFIER ::= { cevModule10000Bases 46 }
cevModuleONS15540Type OBJECT IDENTIFIER ::= { cevModule 42 }
cevONS15540LCMBTspProtect OBJECT IDENTIFIER ::= { cevModuleONS15540Type 1 }
cevONS15540LCMBTspEast OBJECT IDENTIFIER ::= { cevModuleONS15540Type 2 }
cevONS15540LCMBTspWest OBJECT IDENTIFIER ::= { cevModuleONS15540Type 3 }
cevONS15540MDXMBOSC OBJECT IDENTIFIER ::= { cevModuleONS15540Type 4 }
cevONS15540MDXMB OBJECT IDENTIFIER ::= { cevModuleONS15540Type 5 }
cevONS15540Tsp1Ch0102MmSc OBJECT IDENTIFIER ::= { cevModuleONS15540Type 6 }
cevONS15540Tsp1Ch0304MmSc OBJECT IDENTIFIER ::= { cevModuleONS15540Type 7 }
cevONS15540Tsp1Ch0506MmSc OBJECT IDENTIFIER ::= { cevModuleONS15540Type 8 }
cevONS15540Tsp1Ch0708MmSc OBJECT IDENTIFIER ::= { cevModuleONS15540Type 9 }
cevONS15540Tsp1Ch0910MmSc OBJECT IDENTIFIER ::= { cevModuleONS15540Type 10 }
cevONS15540Tsp1Ch1112MmSc OBJECT IDENTIFIER ::= { cevModuleONS15540Type 11 }
cevONS15540Tsp1Ch1314MmSc OBJECT IDENTIFIER ::= { cevModuleONS15540Type 12 }
cevONS15540Tsp1Ch1516MmSc OBJECT IDENTIFIER ::= { cevModuleONS15540Type 13 }
cevONS15540Tsp1Ch1718MmSc OBJECT IDENTIFIER ::= { cevModuleONS15540Type 14 }
cevONS15540Tsp1Ch1920MmSc OBJECT IDENTIFIER ::= { cevModuleONS15540Type 15 }
cevONS15540Tsp1Ch2122MmSc OBJECT IDENTIFIER ::= { cevModuleONS15540Type 16 }
cevONS15540Tsp1Ch2324MmSc OBJECT IDENTIFIER ::= { cevModuleONS15540Type 17 }
cevONS15540Tsp1Ch2526MmSc OBJECT IDENTIFIER ::= { cevModuleONS15540Type 18 }
cevONS15540Tsp1Ch2728MmSc OBJECT IDENTIFIER ::= { cevModuleONS15540Type 19 }
cevONS15540Tsp1Ch2930MmSc OBJECT IDENTIFIER ::= { cevModuleONS15540Type 20 }
cevONS15540Tsp1Ch3132MmSc OBJECT IDENTIFIER ::= { cevModuleONS15540Type 21 }
cevONS15540Tsp1Ch0102SmSc OBJECT IDENTIFIER ::= { cevModuleONS15540Type 22 }
cevONS15540Tsp1Ch0304SmSc OBJECT IDENTIFIER ::= { cevModuleONS15540Type 23 }
cevONS15540Tsp1Ch0506SmSc OBJECT IDENTIFIER ::= { cevModuleONS15540Type 24 }
cevONS15540Tsp1Ch0708SmSc OBJECT IDENTIFIER ::= { cevModuleONS15540Type 25 }
cevONS15540Tsp1Ch0910SmSc OBJECT IDENTIFIER ::= { cevModuleONS15540Type 26 }
cevONS15540Tsp1Ch1112SmSc OBJECT IDENTIFIER ::= { cevModuleONS15540Type 27 }
cevONS15540Tsp1Ch1314SmSc OBJECT IDENTIFIER ::= { cevModuleONS15540Type 28 }
cevONS15540Tsp1Ch1516SmSc OBJECT IDENTIFIER ::= { cevModuleONS15540Type 29 }
cevONS15540Tsp1Ch1718SmSc OBJECT IDENTIFIER ::= { cevModuleONS15540Type 30 }
cevONS15540Tsp1Ch1920SmSc OBJECT IDENTIFIER ::= { cevModuleONS15540Type 31 }
cevONS15540Tsp1Ch2122SmSc OBJECT IDENTIFIER ::= { cevModuleONS15540Type 32 }
cevONS15540Tsp1Ch2324SmSc OBJECT IDENTIFIER ::= { cevModuleONS15540Type 33 }
cevONS15540Tsp1Ch2526SmSc OBJECT IDENTIFIER ::= { cevModuleONS15540Type 34 }
cevONS15540Tsp1Ch2728SmSc OBJECT IDENTIFIER ::= { cevModuleONS15540Type 35 }
cevONS15540Tsp1Ch2930SmSc OBJECT IDENTIFIER ::= { cevModuleONS15540Type 36 }
cevONS15540Tsp1Ch3132SmSc OBJECT IDENTIFIER ::= { cevModuleONS15540Type 37 }
cevONS15540MDX4ChA OBJECT IDENTIFIER ::= { cevModuleONS15540Type 38 }
cevONS15540MDX4ChB OBJECT IDENTIFIER ::= { cevModuleONS15540Type 39 }
cevONS15540MDX4ChC OBJECT IDENTIFIER ::= { cevModuleONS15540Type 40 }
cevONS15540MDX4ChD OBJECT IDENTIFIER ::= { cevModuleONS15540Type 41 }
cevONS15540MDX4ChE OBJECT IDENTIFIER ::= { cevModuleONS15540Type 42 }
cevONS15540MDX4ChF OBJECT IDENTIFIER ::= { cevModuleONS15540Type 43 }
cevONS15540MDX4ChG OBJECT IDENTIFIER ::= { cevModuleONS15540Type 44 }
cevONS15540MDX4ChH OBJECT IDENTIFIER ::= { cevModuleONS15540Type 45 }
cevONS15540MDX8ChAB OBJECT IDENTIFIER ::= { cevModuleONS15540Type 46 }
cevONS15540MDX8ChCD OBJECT IDENTIFIER ::= { cevModuleONS15540Type 47 }
cevONS15540MDX8ChEF OBJECT IDENTIFIER ::= { cevModuleONS15540Type 48 }
cevONS15540MDX8ChGH OBJECT IDENTIFIER ::= { cevModuleONS15540Type 49 }
cevONS15540MDX4ChAOSC OBJECT IDENTIFIER ::= { cevModuleONS15540Type 50 }
cevONS15540MDX4ChBOSC OBJECT IDENTIFIER ::= { cevModuleONS15540Type 51 }
cevONS15540MDX4ChCOSC OBJECT IDENTIFIER ::= { cevModuleONS15540Type 52 }
cevONS15540MDX4ChDOSC OBJECT IDENTIFIER ::= { cevModuleONS15540Type 53 }
cevONS15540MDX4ChEOSC OBJECT IDENTIFIER ::= { cevModuleONS15540Type 54 }
cevONS15540MDX4ChFOSC OBJECT IDENTIFIER ::= { cevModuleONS15540Type 55 }
cevONS15540MDX4ChGOSC OBJECT IDENTIFIER ::= { cevModuleONS15540Type 56 }
cevONS15540MDX4ChHOSC OBJECT IDENTIFIER ::= { cevModuleONS15540Type 57 }
cevONS15540MDX8ChABOSC OBJECT IDENTIFIER ::= { cevModuleONS15540Type 58 }
cevONS15540MDX8ChCDOSC OBJECT IDENTIFIER ::= { cevModuleONS15540Type 59 }
cevONS15540MDX8ChEFOSC OBJECT IDENTIFIER ::= { cevModuleONS15540Type 60 }
cevONS15540MDX8ChGHOSC OBJECT IDENTIFIER ::= { cevModuleONS15540Type 61 }
cevONS15540MDX16ChADOSC OBJECT IDENTIFIER ::= { cevModuleONS15540Type 62 }
cevONS15540MDX16ChEH OBJECT IDENTIFIER ::= { cevModuleONS15540Type 63 }
cevONS15540Tsp2Ch0102 OBJECT IDENTIFIER ::= { cevModuleONS15540Type 64 }
cevONS15540Tsp2Ch0304 OBJECT IDENTIFIER ::= { cevModuleONS15540Type 65 }
cevONS15540Tsp2Ch0506 OBJECT IDENTIFIER ::= { cevModuleONS15540Type 66 }
cevONS15540Tsp2Ch0708 OBJECT IDENTIFIER ::= { cevModuleONS15540Type 67 }
cevONS15540Tsp2Ch0910 OBJECT IDENTIFIER ::= { cevModuleONS15540Type 68 }
cevONS15540Tsp2Ch1112 OBJECT IDENTIFIER ::= { cevModuleONS15540Type 69 }
cevONS15540Tsp2Ch1314 OBJECT IDENTIFIER ::= { cevModuleONS15540Type 70 }
cevONS15540Tsp2Ch1516 OBJECT IDENTIFIER ::= { cevModuleONS15540Type 71 }
cevONS15540Tsp2Ch1718 OBJECT IDENTIFIER ::= { cevModuleONS15540Type 72 }
cevONS15540Tsp2Ch1920 OBJECT IDENTIFIER ::= { cevModuleONS15540Type 73 }
cevONS15540Tsp2Ch2122 OBJECT IDENTIFIER ::= { cevModuleONS15540Type 74 }
cevONS15540Tsp2Ch2324 OBJECT IDENTIFIER ::= { cevModuleONS15540Type 75 }
cevONS15540Tsp2Ch2526 OBJECT IDENTIFIER ::= { cevModuleONS15540Type 76 }
cevONS15540Tsp2Ch2728 OBJECT IDENTIFIER ::= { cevModuleONS15540Type 77 }
cevONS15540Tsp2Ch2930 OBJECT IDENTIFIER ::= { cevModuleONS15540Type 78 }
cevONS15540Tsp2Ch3132 OBJECT IDENTIFIER ::= { cevModuleONS15540Type 79 }
cevONS15540LCMB10GOC192c OBJECT IDENTIFIER ::= { cevModuleONS15540Type 80 }
cevONS15540ESPxLCMBTspSp OBJECT IDENTIFIER ::= { cevModuleONS15540Type 81 }
cevONS15540ESPxLCMBTsp OBJECT IDENTIFIER ::= { cevModuleONS15540Type 82 }
cevONS15540ESPxLCMB10GOC192cSp OBJECT IDENTIFIER ::= { cevModuleONS15540Type 83 }
cevONS15540ESPxLCMB10GOC192c OBJECT IDENTIFIER ::= { cevModuleONS15540Type 84 }
cevONS15540LCDC10G OBJECT IDENTIFIER ::= { cevModuleONS15540Type 85 }
cevONS15540ESPxMDXMBOsc OBJECT IDENTIFIER ::= { cevModuleONS15540Type 86 }
cevONS15540ESPxMDXMB OBJECT IDENTIFIER ::= { cevModuleONS15540Type 87 }
cevONS15540ESPxMDXMBOscESP OBJECT IDENTIFIER ::= { cevModuleONS15540Type 88 }
cevONS15540ESPxMDXMBESP OBJECT IDENTIFIER ::= { cevModuleONS15540Type 89 }
cevONS1554010GigITUCh01 OBJECT IDENTIFIER ::= { cevModuleONS15540Type 90 }
cevONS1554010GigITUCh02 OBJECT IDENTIFIER ::= { cevModuleONS15540Type 91 }
cevONS1554010GigITUCh03 OBJECT IDENTIFIER ::= { cevModuleONS15540Type 92 }
cevONS1554010GigITUCh04 OBJECT IDENTIFIER ::= { cevModuleONS15540Type 93 }
cevONS1554010GigITUCh05 OBJECT IDENTIFIER ::= { cevModuleONS15540Type 94 }
cevONS1554010GigITUCh06 OBJECT IDENTIFIER ::= { cevModuleONS15540Type 95 }
cevONS1554010GigITUCh07 OBJECT IDENTIFIER ::= { cevModuleONS15540Type 96 }
cevONS1554010GigITUCh08 OBJECT IDENTIFIER ::= { cevModuleONS15540Type 97 }
cevONS1554010GigITUCh09 OBJECT IDENTIFIER ::= { cevModuleONS15540Type 98 }
cevONS1554010GigITUCh10 OBJECT IDENTIFIER ::= { cevModuleONS15540Type 99 }
cevONS1554010GigITUCh11 OBJECT IDENTIFIER ::= { cevModuleONS15540Type 100 }
cevONS1554010GigITUCh12 OBJECT IDENTIFIER ::= { cevModuleONS15540Type 101 }
cevONS1554010GigITUCh13 OBJECT IDENTIFIER ::= { cevModuleONS15540Type 102 }
cevONS1554010GigITUCh14 OBJECT IDENTIFIER ::= { cevModuleONS15540Type 103 }
cevONS1554010GigITUCh15 OBJECT IDENTIFIER ::= { cevModuleONS15540Type 104 }
cevONS1554010GigITUCh16 OBJECT IDENTIFIER ::= { cevModuleONS15540Type 105 }
cevONS1554010GigITUCh17 OBJECT IDENTIFIER ::= { cevModuleONS15540Type 106 }
cevONS1554010GigITUCh18 OBJECT IDENTIFIER ::= { cevModuleONS15540Type 107 }
cevONS1554010GigITUCh19 OBJECT IDENTIFIER ::= { cevModuleONS15540Type 108 }
cevONS1554010GigITUCh20 OBJECT IDENTIFIER ::= { cevModuleONS15540Type 109 }
cevONS1554010GigITUCh21 OBJECT IDENTIFIER ::= { cevModuleONS15540Type 110 }
cevONS1554010GigITUCh22 OBJECT IDENTIFIER ::= { cevModuleONS15540Type 111 }
cevONS1554010GigITUCh23 OBJECT IDENTIFIER ::= { cevModuleONS15540Type 112 }
cevONS1554010GigITUCh24 OBJECT IDENTIFIER ::= { cevModuleONS15540Type 113 }
cevONS1554010GigITUCh25 OBJECT IDENTIFIER ::= { cevModuleONS15540Type 114 }
cevONS1554010GigITUCh26 OBJECT IDENTIFIER ::= { cevModuleONS15540Type 115 }
cevONS1554010GigITUCh27 OBJECT IDENTIFIER ::= { cevModuleONS15540Type 116 }
cevONS1554010GigITUCh28 OBJECT IDENTIFIER ::= { cevModuleONS15540Type 117 }
cevONS1554010GigITUCh29 OBJECT IDENTIFIER ::= { cevModuleONS15540Type 118 }
cevONS1554010GigITUCh30 OBJECT IDENTIFIER ::= { cevModuleONS15540Type 119 }
cevONS1554010GigITUCh31 OBJECT IDENTIFIER ::= { cevModuleONS15540Type 120 }
cevONS1554010GigITUCh32 OBJECT IDENTIFIER ::= { cevModuleONS15540Type 121 }
cevONS15540OC192cITUCh01 OBJECT IDENTIFIER ::= { cevModuleONS15540Type 122 }
cevONS15540OC192cITUCh02 OBJECT IDENTIFIER ::= { cevModuleONS15540Type 123 }
cevONS15540OC192cITUCh03 OBJECT IDENTIFIER ::= { cevModuleONS15540Type 124 }
cevONS15540OC192cITUCh04 OBJECT IDENTIFIER ::= { cevModuleONS15540Type 125 }
cevONS15540OC192cITUCh05 OBJECT IDENTIFIER ::= { cevModuleONS15540Type 126 }
cevONS15540OC192cITUCh06 OBJECT IDENTIFIER ::= { cevModuleONS15540Type 127 }
cevONS15540OC192cITUCh07 OBJECT IDENTIFIER ::= { cevModuleONS15540Type 128 }
cevONS15540OC192cITUCh08 OBJECT IDENTIFIER ::= { cevModuleONS15540Type 129 }
cevONS15540OC192cITUCh09 OBJECT IDENTIFIER ::= { cevModuleONS15540Type 130 }
cevONS15540OC192cITUCh10 OBJECT IDENTIFIER ::= { cevModuleONS15540Type 131 }
cevONS15540OC192cITUCh11 OBJECT IDENTIFIER ::= { cevModuleONS15540Type 132 }
cevONS15540OC192cITUCh12 OBJECT IDENTIFIER ::= { cevModuleONS15540Type 133 }
cevONS15540OC192cITUCh13 OBJECT IDENTIFIER ::= { cevModuleONS15540Type 134 }
cevONS15540OC192cITUCh14 OBJECT IDENTIFIER ::= { cevModuleONS15540Type 135 }
cevONS15540OC192cITUCh15 OBJECT IDENTIFIER ::= { cevModuleONS15540Type 136 }
cevONS15540OC192cITUCh16 OBJECT IDENTIFIER ::= { cevModuleONS15540Type 137 }
cevONS15540OC192cITUCh17 OBJECT IDENTIFIER ::= { cevModuleONS15540Type 138 }
cevONS15540OC192cITUCh18 OBJECT IDENTIFIER ::= { cevModuleONS15540Type 139 }
cevONS15540OC192cITUCh19 OBJECT IDENTIFIER ::= { cevModuleONS15540Type 140 }
cevONS15540OC192cITUCh20 OBJECT IDENTIFIER ::= { cevModuleONS15540Type 141 }
cevONS15540OC192cITUCh21 OBJECT IDENTIFIER ::= { cevModuleONS15540Type 142 }
cevONS15540OC192cITUCh22 OBJECT IDENTIFIER ::= { cevModuleONS15540Type 143 }
cevONS15540OC192cITUCh23 OBJECT IDENTIFIER ::= { cevModuleONS15540Type 144 }
cevONS15540OC192cITUCh24 OBJECT IDENTIFIER ::= { cevModuleONS15540Type 145 }
cevONS15540OC192cITUCh25 OBJECT IDENTIFIER ::= { cevModuleONS15540Type 146 }
cevONS15540OC192cITUCh26 OBJECT IDENTIFIER ::= { cevModuleONS15540Type 147 }
cevONS15540OC192cITUCh27 OBJECT IDENTIFIER ::= { cevModuleONS15540Type 148 }
cevONS15540OC192cITUCh28 OBJECT IDENTIFIER ::= { cevModuleONS15540Type 149 }
cevONS15540OC192cITUCh29 OBJECT IDENTIFIER ::= { cevModuleONS15540Type 150 }
cevONS15540OC192cITUCh30 OBJECT IDENTIFIER ::= { cevModuleONS15540Type 151 }
cevONS15540OC192cITUCh31 OBJECT IDENTIFIER ::= { cevModuleONS15540Type 152 }
cevONS15540OC192cITUCh32 OBJECT IDENTIFIER ::= { cevModuleONS15540Type 153 }
cevONS15540ESPxMDX4ChA OBJECT IDENTIFIER ::= { cevModuleONS15540Type 154 }
cevONS15540ESPxMDX4ChB OBJECT IDENTIFIER ::= { cevModuleONS15540Type 155 }
cevONS15540ESPxMDX4ChC OBJECT IDENTIFIER ::= { cevModuleONS15540Type 156 }
cevONS15540ESPxMDX4ChD OBJECT IDENTIFIER ::= { cevModuleONS15540Type 157 }
cevONS15540ESPxMDX4ChE OBJECT IDENTIFIER ::= { cevModuleONS15540Type 158 }
cevONS15540ESPxMDX4ChF OBJECT IDENTIFIER ::= { cevModuleONS15540Type 159 }
cevONS15540ESPxMDX4ChG OBJECT IDENTIFIER ::= { cevModuleONS15540Type 160 }
cevONS15540ESPxMDX4ChH OBJECT IDENTIFIER ::= { cevModuleONS15540Type 161 }
cevONS15540ESPxMDX8ChAB OBJECT IDENTIFIER ::= { cevModuleONS15540Type 162 }
cevONS15540ESPxMDX8ChCD OBJECT IDENTIFIER ::= { cevModuleONS15540Type 163 }
cevONS15540ESPxMDX8ChEF OBJECT IDENTIFIER ::= { cevModuleONS15540Type 164 }
cevONS15540ESPxMDX8ChGH OBJECT IDENTIFIER ::= { cevModuleONS15540Type 165 }
cevONS15540ESPxMDX16ChEH OBJECT IDENTIFIER ::= { cevModuleONS15540Type 166 }
cevONS15540ESPxMDX4ChAOSC OBJECT IDENTIFIER ::= { cevModuleONS15540Type 167 }
cevONS15540ESPxMDX4ChBOSC OBJECT IDENTIFIER ::= { cevModuleONS15540Type 168 }
cevONS15540ESPxMDX4ChCOSC OBJECT IDENTIFIER ::= { cevModuleONS15540Type 169 }
cevONS15540ESPxMDX4ChDOSC OBJECT IDENTIFIER ::= { cevModuleONS15540Type 170 }
cevONS15540ESPxMDX4ChEOSC OBJECT IDENTIFIER ::= { cevModuleONS15540Type 171 }
cevONS15540ESPxMDX4ChFOSC OBJECT IDENTIFIER ::= { cevModuleONS15540Type 172 }
cevONS15540ESPxMDX4ChGOSC OBJECT IDENTIFIER ::= { cevModuleONS15540Type 173 }
cevONS15540ESPxMDX4ChHOSC OBJECT IDENTIFIER ::= { cevModuleONS15540Type 174 }
cevONS15540ESPxMDX8ChABOSC OBJECT IDENTIFIER ::= { cevModuleONS15540Type 175 }
cevONS15540ESPxMDX8ChCDOSC OBJECT IDENTIFIER ::= { cevModuleONS15540Type 176 }
cevONS15540ESPxMDX8ChEFOSC OBJECT IDENTIFIER ::= { cevModuleONS15540Type 177 }
cevONS15540ESPxMDX8ChGHOSC OBJECT IDENTIFIER ::= { cevModuleONS15540Type 178 }
cevONS15540ESPxMDX16ChADOSC OBJECT IDENTIFIER ::= { cevModuleONS15540Type 179 }
cevONS15540ESPxMDX32ChOSC OBJECT IDENTIFIER ::= { cevModuleONS15540Type 180 }
cevONS15540EspPxPSM OBJECT IDENTIFIER ::= { cevModuleONS15540Type 181 }
cevONS15540ESPxVOA1ITUCh1 OBJECT IDENTIFIER ::= { cevModuleONS15540Type 182 }
cevONS15540ESPxVOA1ITUCh2 OBJECT IDENTIFIER ::= { cevModuleONS15540Type 183 }
cevONS15540ESPxVOA1ITUCh3 OBJECT IDENTIFIER ::= { cevModuleONS15540Type 184 }
cevONS15540ESPxVOA1ITUCh4 OBJECT IDENTIFIER ::= { cevModuleONS15540Type 185 }
cevONS15540ESPxVOA1ITUCh5 OBJECT IDENTIFIER ::= { cevModuleONS15540Type 186 }
cevONS15540ESPxVOA1ITUCh6 OBJECT IDENTIFIER ::= { cevModuleONS15540Type 187 }
cevONS15540ESPxVOA1ITUCh7 OBJECT IDENTIFIER ::= { cevModuleONS15540Type 188 }
cevONS15540ESPxVOA1ITUCh8 OBJECT IDENTIFIER ::= { cevModuleONS15540Type 189 }
cevONS15540ESPxVOA1ITUCh9 OBJECT IDENTIFIER ::= { cevModuleONS15540Type 190 }
cevONS15540ESPxVOA1ITUCh10 OBJECT IDENTIFIER ::= { cevModuleONS15540Type 191 }
cevONS15540ESPxVOA1ITUCh11 OBJECT IDENTIFIER ::= { cevModuleONS15540Type 192 }
cevONS15540ESPxVOA1ITUCh12 OBJECT IDENTIFIER ::= { cevModuleONS15540Type 193 }
cevONS15540ESPxVOA1ITUCh13 OBJECT IDENTIFIER ::= { cevModuleONS15540Type 194 }
cevONS15540ESPxVOA1ITUCh14 OBJECT IDENTIFIER ::= { cevModuleONS15540Type 195 }
cevONS15540ESPxVOA1ITUCh15 OBJECT IDENTIFIER ::= { cevModuleONS15540Type 196 }
cevONS15540ESPxVOA1ITUCh16 OBJECT IDENTIFIER ::= { cevModuleONS15540Type 197 }
cevONS15540ESPxVOA1ITUCh17 OBJECT IDENTIFIER ::= { cevModuleONS15540Type 198 }
cevONS15540ESPxVOA1ITUCh18 OBJECT IDENTIFIER ::= { cevModuleONS15540Type 199 }
cevONS15540ESPxVOA1ITUCh19 OBJECT IDENTIFIER ::= { cevModuleONS15540Type 200 }
cevONS15540ESPxVOA1ITUCh20 OBJECT IDENTIFIER ::= { cevModuleONS15540Type 201 }
cevONS15540ESPxVOA1ITUCh21 OBJECT IDENTIFIER ::= { cevModuleONS15540Type 202 }
cevONS15540ESPxVOA1ITUCh22 OBJECT IDENTIFIER ::= { cevModuleONS15540Type 203 }
cevONS15540ESPxVOA1ITUCh23 OBJECT IDENTIFIER ::= { cevModuleONS15540Type 204 }
cevONS15540ESPxVOA1ITUCh24 OBJECT IDENTIFIER ::= { cevModuleONS15540Type 205 }
cevONS15540ESPxVOA1ITUCh25 OBJECT IDENTIFIER ::= { cevModuleONS15540Type 206 }
cevONS15540ESPxVOA1ITUCh26 OBJECT IDENTIFIER ::= { cevModuleONS15540Type 207 }
cevONS15540ESPxVOA1ITUCh27 OBJECT IDENTIFIER ::= { cevModuleONS15540Type 208 }
cevONS15540ESPxVOA1ITUCh28 OBJECT IDENTIFIER ::= { cevModuleONS15540Type 209 }
cevONS15540ESPxVOA1ITUCh29 OBJECT IDENTIFIER ::= { cevModuleONS15540Type 210 }
cevONS15540ESPxVOA1ITUCh30 OBJECT IDENTIFIER ::= { cevModuleONS15540Type 211 }
cevONS15540ESPxVOA1ITUCh31 OBJECT IDENTIFIER ::= { cevModuleONS15540Type 212 }
cevONS15540ESPxVOA1ITUCh32 OBJECT IDENTIFIER ::= { cevModuleONS15540Type 213 }
cevONS15540ESPxVOA1ITUCh33 OBJECT IDENTIFIER ::= { cevModuleONS15540Type 214 }
cevONS15540ESPxVOA2ITUCh0102 OBJECT IDENTIFIER ::= { cevModuleONS15540Type 215 }
cevONS15540ESPxVOA2ITUCh0304 OBJECT IDENTIFIER ::= { cevModuleONS15540Type 216 }
cevONS15540ESPxVOA2ITUCh0506 OBJECT IDENTIFIER ::= { cevModuleONS15540Type 217 }
cevONS15540ESPxVOA2ITUCh0708 OBJECT IDENTIFIER ::= { cevModuleONS15540Type 218 }
cevONS15540ESPxVOA2ITUCh0910 OBJECT IDENTIFIER ::= { cevModuleONS15540Type 219 }
cevONS15540ESPxVOA2ITUCh1112 OBJECT IDENTIFIER ::= { cevModuleONS15540Type 220 }
cevONS15540ESPxVOA2ITUCh1314 OBJECT IDENTIFIER ::= { cevModuleONS15540Type 221 }
cevONS15540ESPxVOA2ITUCh1516 OBJECT IDENTIFIER ::= { cevModuleONS15540Type 222 }
cevONS15540ESPxVOA2ITUCh1718 OBJECT IDENTIFIER ::= { cevModuleONS15540Type 223 }
cevONS15540ESPxVOA2ITUCh1920 OBJECT IDENTIFIER ::= { cevModuleONS15540Type 224 }
cevONS15540ESPxVOA2ITUCh2122 OBJECT IDENTIFIER ::= { cevModuleONS15540Type 225 }
cevONS15540ESPxVOA2ITUCh2324 OBJECT IDENTIFIER ::= { cevModuleONS15540Type 226 }
cevONS15540ESPxVOA2ITUCh2526 OBJECT IDENTIFIER ::= { cevModuleONS15540Type 227 }
cevONS15540ESPxVOA2ITUCh2728 OBJECT IDENTIFIER ::= { cevModuleONS15540Type 228 }
cevONS15540ESPxVOA2ITUCh2930 OBJECT IDENTIFIER ::= { cevModuleONS15540Type 229 }
cevONS15540ESPxVOA2ITUCh3132 OBJECT IDENTIFIER ::= { cevModuleONS15540Type 230 }
cevONS15540ESPxVOA4 OBJECT IDENTIFIER ::= { cevModuleONS15540Type 231 }
cevModuleGsrPortAdapterType OBJECT IDENTIFIER ::= { cevModule 43 }
cevGsrPaUnknown OBJECT IDENTIFIER ::= { cevModuleGsrPortAdapterType 1 }
cevGsrPa1Ge     OBJECT IDENTIFIER ::= { cevModuleGsrPortAdapterType 2 }
cevGsrPa3Ge     OBJECT IDENTIFIER ::= { cevModuleGsrPortAdapterType 3 }
cevGsrPa24Fe    OBJECT IDENTIFIER ::= { cevModuleGsrPortAdapterType 4 }
cevModuleC4224Type OBJECT IDENTIFIER ::= { cevModule 47 }
cevC42241FeTx   OBJECT IDENTIFIER ::= { cevModuleC4224Type 1 }
cevC422424FeTx  OBJECT IDENTIFIER ::= { cevModuleC4224Type 2 }
cevModuleONS15530Type OBJECT IDENTIFIER ::= { cevModule 44 }
cevONS15530LCMBOsc OBJECT IDENTIFIER ::= { cevModuleONS15530Type 1 }
cevONS15530Osc  OBJECT IDENTIFIER ::= { cevModuleONS15530Type 2 }
cevONS15530MDX4ChA OBJECT IDENTIFIER ::= { cevModuleONS15530Type 3 }
cevONS15530MDX4ChB OBJECT IDENTIFIER ::= { cevModuleONS15530Type 4 }
cevONS15530MDX4ChC OBJECT IDENTIFIER ::= { cevModuleONS15530Type 5 }
cevONS15530MDX4ChD OBJECT IDENTIFIER ::= { cevModuleONS15530Type 6 }
cevONS15530MDX4ChE OBJECT IDENTIFIER ::= { cevModuleONS15530Type 7 }
cevONS15530MDX4ChF OBJECT IDENTIFIER ::= { cevModuleONS15530Type 8 }
cevONS15530MDX4ChG OBJECT IDENTIFIER ::= { cevModuleONS15530Type 9 }
cevONS15530MDX4ChH OBJECT IDENTIFIER ::= { cevModuleONS15530Type 10 }
cevONS15530MDX4ChAOsc OBJECT IDENTIFIER ::= { cevModuleONS15530Type 11 }
cevONS15530MDX4ChBOsc OBJECT IDENTIFIER ::= { cevModuleONS15530Type 12 }
cevONS15530MDX4ChCOsc OBJECT IDENTIFIER ::= { cevModuleONS15530Type 13 }
cevONS15530MDX4ChDOsc OBJECT IDENTIFIER ::= { cevModuleONS15530Type 14 }
cevONS15530MDX4ChEOsc OBJECT IDENTIFIER ::= { cevModuleONS15530Type 15 }
cevONS15530MDX4ChFOsc OBJECT IDENTIFIER ::= { cevModuleONS15530Type 16 }
cevONS15530MDX4ChGOsc OBJECT IDENTIFIER ::= { cevModuleONS15530Type 17 }
cevONS15530MDX4ChHOsc OBJECT IDENTIFIER ::= { cevModuleONS15530Type 18 }
cevONS15530Tsp1Ch0102MmScSp OBJECT IDENTIFIER ::= { cevModuleONS15530Type 19 }
cevONS15530Tsp1Ch0304MmScSp OBJECT IDENTIFIER ::= { cevModuleONS15530Type 20 }
cevONS15530Tsp1Ch0506MmScSp OBJECT IDENTIFIER ::= { cevModuleONS15530Type 21 }
cevONS15530Tsp1Ch0708MmScSp OBJECT IDENTIFIER ::= { cevModuleONS15530Type 22 }
cevONS15530Tsp1Ch0910MmScSp OBJECT IDENTIFIER ::= { cevModuleONS15530Type 23 }
cevONS15530Tsp1Ch1112MmScSp OBJECT IDENTIFIER ::= { cevModuleONS15530Type 24 }
cevONS15530Tsp1Ch1314MmScSp OBJECT IDENTIFIER ::= { cevModuleONS15530Type 25 }
cevONS15530Tsp1Ch1516MmScSp OBJECT IDENTIFIER ::= { cevModuleONS15530Type 26 }
cevONS15530Tsp1Ch1718MmScSp OBJECT IDENTIFIER ::= { cevModuleONS15530Type 27 }
cevONS15530Tsp1Ch1920MmScSp OBJECT IDENTIFIER ::= { cevModuleONS15530Type 28 }
cevONS15530Tsp1Ch2122MmScSp OBJECT IDENTIFIER ::= { cevModuleONS15530Type 29 }
cevONS15530Tsp1Ch2324MmScSp OBJECT IDENTIFIER ::= { cevModuleONS15530Type 30 }
cevONS15530Tsp1Ch2526MmScSp OBJECT IDENTIFIER ::= { cevModuleONS15530Type 31 }
cevONS15530Tsp1Ch2728MmScSp OBJECT IDENTIFIER ::= { cevModuleONS15530Type 32 }
cevONS15530Tsp1Ch2930MmScSp OBJECT IDENTIFIER ::= { cevModuleONS15530Type 33 }
cevONS15530Tsp1Ch3132MmScSp OBJECT IDENTIFIER ::= { cevModuleONS15530Type 34 }
cevONS15530Tsp1Ch0102SmScSp OBJECT IDENTIFIER ::= { cevModuleONS15530Type 35 }
cevONS15530Tsp1Ch0304SmScSp OBJECT IDENTIFIER ::= { cevModuleONS15530Type 36 }
cevONS15530Tsp1Ch0506SmScSp OBJECT IDENTIFIER ::= { cevModuleONS15530Type 37 }
cevONS15530Tsp1Ch0708SmScSp OBJECT IDENTIFIER ::= { cevModuleONS15530Type 38 }
cevONS15530Tsp1Ch0910SmScSp OBJECT IDENTIFIER ::= { cevModuleONS15530Type 39 }
cevONS15530Tsp1Ch1112SmScSp OBJECT IDENTIFIER ::= { cevModuleONS15530Type 40 }
cevONS15530Tsp1Ch1314SmScSp OBJECT IDENTIFIER ::= { cevModuleONS15530Type 41 }
cevONS15530Tsp1Ch1516SmScSp OBJECT IDENTIFIER ::= { cevModuleONS15530Type 42 }
cevONS15530Tsp1Ch1718SmScSp OBJECT IDENTIFIER ::= { cevModuleONS15530Type 43 }
cevONS15530Tsp1Ch1920SmScSp OBJECT IDENTIFIER ::= { cevModuleONS15530Type 44 }
cevONS15530Tsp1Ch2122SmScSp OBJECT IDENTIFIER ::= { cevModuleONS15530Type 45 }
cevONS15530Tsp1Ch2324SmScSp OBJECT IDENTIFIER ::= { cevModuleONS15530Type 46 }
cevONS15530Tsp1Ch2526SmScSp OBJECT IDENTIFIER ::= { cevModuleONS15530Type 47 }
cevONS15530Tsp1Ch2728SmScSp OBJECT IDENTIFIER ::= { cevModuleONS15530Type 48 }
cevONS15530Tsp1Ch2930SmScSp OBJECT IDENTIFIER ::= { cevModuleONS15530Type 49 }
cevONS15530Tsp1Ch3132SmScSp OBJECT IDENTIFIER ::= { cevModuleONS15530Type 50 }
cevONS15530Tsp1Ch0102MmSc OBJECT IDENTIFIER ::= { cevModuleONS15530Type 51 }
cevONS15530Tsp1Ch0304MmSc OBJECT IDENTIFIER ::= { cevModuleONS15530Type 52 }
cevONS15530Tsp1Ch0506MmSc OBJECT IDENTIFIER ::= { cevModuleONS15530Type 53 }
cevONS15530Tsp1Ch0708MmSc OBJECT IDENTIFIER ::= { cevModuleONS15530Type 54 }
cevONS15530Tsp1Ch0910MmSc OBJECT IDENTIFIER ::= { cevModuleONS15530Type 55 }
cevONS15530Tsp1Ch1112MmSc OBJECT IDENTIFIER ::= { cevModuleONS15530Type 56 }
cevONS15530Tsp1Ch1314MmSc OBJECT IDENTIFIER ::= { cevModuleONS15530Type 57 }
cevONS15530Tsp1Ch1516MmSc OBJECT IDENTIFIER ::= { cevModuleONS15530Type 58 }
cevONS15530Tsp1Ch1718MmSc OBJECT IDENTIFIER ::= { cevModuleONS15530Type 59 }
cevONS15530Tsp1Ch1920MmSc OBJECT IDENTIFIER ::= { cevModuleONS15530Type 60 }
cevONS15530Tsp1Ch2122MmSc OBJECT IDENTIFIER ::= { cevModuleONS15530Type 61 }
cevONS15530Tsp1Ch2324MmSc OBJECT IDENTIFIER ::= { cevModuleONS15530Type 62 }
cevONS15530Tsp1Ch2526MmSc OBJECT IDENTIFIER ::= { cevModuleONS15530Type 63 }
cevONS15530Tsp1Ch2728MmSc OBJECT IDENTIFIER ::= { cevModuleONS15530Type 64 }
cevONS15530Tsp1Ch2930MmSc OBJECT IDENTIFIER ::= { cevModuleONS15530Type 65 }
cevONS15530Tsp1Ch3132MmSc OBJECT IDENTIFIER ::= { cevModuleONS15530Type 66 }
cevONS15530Tsp1Ch0102SmSc OBJECT IDENTIFIER ::= { cevModuleONS15530Type 67 }
cevONS15530Tsp1Ch0304SmSc OBJECT IDENTIFIER ::= { cevModuleONS15530Type 68 }
cevONS15530Tsp1Ch0506SmSc OBJECT IDENTIFIER ::= { cevModuleONS15530Type 69 }
cevONS15530Tsp1Ch0708SmSc OBJECT IDENTIFIER ::= { cevModuleONS15530Type 70 }
cevONS15530Tsp1Ch0910SmSc OBJECT IDENTIFIER ::= { cevModuleONS15530Type 71 }
cevONS15530Tsp1Ch1112SmSc OBJECT IDENTIFIER ::= { cevModuleONS15530Type 72 }
cevONS15530Tsp1Ch1314SmSc OBJECT IDENTIFIER ::= { cevModuleONS15530Type 73 }
cevONS15530Tsp1Ch1516SmSc OBJECT IDENTIFIER ::= { cevModuleONS15530Type 74 }
cevONS15530Tsp1Ch1718SmSc OBJECT IDENTIFIER ::= { cevModuleONS15530Type 75 }
cevONS15530Tsp1Ch1920SmSc OBJECT IDENTIFIER ::= { cevModuleONS15530Type 76 }
cevONS15530Tsp1Ch2122SmSc OBJECT IDENTIFIER ::= { cevModuleONS15530Type 77 }
cevONS15530Tsp1Ch2324SmSc OBJECT IDENTIFIER ::= { cevModuleONS15530Type 78 }
cevONS15530Tsp1Ch2526SmSc OBJECT IDENTIFIER ::= { cevModuleONS15530Type 79 }
cevONS15530Tsp1Ch2728SmSc OBJECT IDENTIFIER ::= { cevModuleONS15530Type 80 }
cevONS15530Tsp1Ch2930SmSc OBJECT IDENTIFIER ::= { cevModuleONS15530Type 81 }
cevONS15530Tsp1Ch3132SmSc OBJECT IDENTIFIER ::= { cevModuleONS15530Type 82 }
cevONS15530LCEscon10 OBJECT IDENTIFIER ::= { cevModuleONS15530Type 83 }
cevONS15500XvrEscon1310MmMTRJ OBJECT IDENTIFIER ::= { cevModuleONS15530Type 84 }
cevONS15530LC10GESmSc OBJECT IDENTIFIER ::= { cevModuleONS15530Type 85 }
cevONS1553010GCh01Sp OBJECT IDENTIFIER ::= { cevModuleONS15530Type 86 }
cevONS1553010GCh02Sp OBJECT IDENTIFIER ::= { cevModuleONS15530Type 87 }
cevONS1553010GCh03Sp OBJECT IDENTIFIER ::= { cevModuleONS15530Type 88 }
cevONS1553010GCh04Sp OBJECT IDENTIFIER ::= { cevModuleONS15530Type 89 }
cevONS1553010GCh05Sp OBJECT IDENTIFIER ::= { cevModuleONS15530Type 90 }
cevONS1553010GCh06Sp OBJECT IDENTIFIER ::= { cevModuleONS15530Type 91 }
cevONS1553010GCh07Sp OBJECT IDENTIFIER ::= { cevModuleONS15530Type 92 }
cevONS1553010GCh08Sp OBJECT IDENTIFIER ::= { cevModuleONS15530Type 93 }
cevONS1553010GCh09Sp OBJECT IDENTIFIER ::= { cevModuleONS15530Type 94 }
cevONS1553010GCh10Sp OBJECT IDENTIFIER ::= { cevModuleONS15530Type 95 }
cevONS1553010GCh11Sp OBJECT IDENTIFIER ::= { cevModuleONS15530Type 96 }
cevONS1553010GCh12Sp OBJECT IDENTIFIER ::= { cevModuleONS15530Type 97 }
cevONS1553010GCh13Sp OBJECT IDENTIFIER ::= { cevModuleONS15530Type 98 }
cevONS1553010GCh14Sp OBJECT IDENTIFIER ::= { cevModuleONS15530Type 99 }
cevONS1553010GCh15Sp OBJECT IDENTIFIER ::= { cevModuleONS15530Type 100 }
cevONS1553010GCh16Sp OBJECT IDENTIFIER ::= { cevModuleONS15530Type 101 }
cevONS1553010GCh17Sp OBJECT IDENTIFIER ::= { cevModuleONS15530Type 102 }
cevONS1553010GCh18Sp OBJECT IDENTIFIER ::= { cevModuleONS15530Type 103 }
cevONS1553010GCh19Sp OBJECT IDENTIFIER ::= { cevModuleONS15530Type 104 }
cevONS1553010GCh20Sp OBJECT IDENTIFIER ::= { cevModuleONS15530Type 105 }
cevONS1553010GCh21Sp OBJECT IDENTIFIER ::= { cevModuleONS15530Type 106 }
cevONS1553010GCh22Sp OBJECT IDENTIFIER ::= { cevModuleONS15530Type 107 }
cevONS1553010GCh23Sp OBJECT IDENTIFIER ::= { cevModuleONS15530Type 108 }
cevONS1553010GCh24Sp OBJECT IDENTIFIER ::= { cevModuleONS15530Type 109 }
cevONS1553010GCh25Sp OBJECT IDENTIFIER ::= { cevModuleONS15530Type 110 }
cevONS1553010GCh26Sp OBJECT IDENTIFIER ::= { cevModuleONS15530Type 111 }
cevONS1553010GCh27Sp OBJECT IDENTIFIER ::= { cevModuleONS15530Type 112 }
cevONS1553010GCh28Sp OBJECT IDENTIFIER ::= { cevModuleONS15530Type 113 }
cevONS1553010GCh29Sp OBJECT IDENTIFIER ::= { cevModuleONS15530Type 114 }
cevONS1553010GCh30Sp OBJECT IDENTIFIER ::= { cevModuleONS15530Type 115 }
cevONS1553010GCh31Sp OBJECT IDENTIFIER ::= { cevModuleONS15530Type 116 }
cevONS1553010GCh32Sp OBJECT IDENTIFIER ::= { cevModuleONS15530Type 117 }
cevONS1553010GCh01 OBJECT IDENTIFIER ::= { cevModuleONS15530Type 118 }
cevONS1553010GCh02 OBJECT IDENTIFIER ::= { cevModuleONS15530Type 119 }
cevONS1553010GCh03 OBJECT IDENTIFIER ::= { cevModuleONS15530Type 120 }
cevONS1553010GCh04 OBJECT IDENTIFIER ::= { cevModuleONS15530Type 121 }
cevONS1553010GCh05 OBJECT IDENTIFIER ::= { cevModuleONS15530Type 122 }
cevONS1553010GCh06 OBJECT IDENTIFIER ::= { cevModuleONS15530Type 123 }
cevONS1553010GCh07 OBJECT IDENTIFIER ::= { cevModuleONS15530Type 124 }
cevONS1553010GCh08 OBJECT IDENTIFIER ::= { cevModuleONS15530Type 125 }
cevONS1553010GCh09 OBJECT IDENTIFIER ::= { cevModuleONS15530Type 126 }
cevONS1553010GCh10 OBJECT IDENTIFIER ::= { cevModuleONS15530Type 127 }
cevONS1553010GCh11 OBJECT IDENTIFIER ::= { cevModuleONS15530Type 128 }
cevONS1553010GCh12 OBJECT IDENTIFIER ::= { cevModuleONS15530Type 129 }
cevONS1553010GCh13 OBJECT IDENTIFIER ::= { cevModuleONS15530Type 130 }
cevONS1553010GCh14 OBJECT IDENTIFIER ::= { cevModuleONS15530Type 131 }
cevONS1553010GCh15 OBJECT IDENTIFIER ::= { cevModuleONS15530Type 132 }
cevONS1553010GCh16 OBJECT IDENTIFIER ::= { cevModuleONS15530Type 133 }
cevONS1553010GCh17 OBJECT IDENTIFIER ::= { cevModuleONS15530Type 134 }
cevONS1553010GCh18 OBJECT IDENTIFIER ::= { cevModuleONS15530Type 135 }
cevONS1553010GCh19 OBJECT IDENTIFIER ::= { cevModuleONS15530Type 136 }
cevONS1553010GCh20 OBJECT IDENTIFIER ::= { cevModuleONS15530Type 137 }
cevONS1553010GCh21 OBJECT IDENTIFIER ::= { cevModuleONS15530Type 138 }
cevONS1553010GCh22 OBJECT IDENTIFIER ::= { cevModuleONS15530Type 139 }
cevONS1553010GCh23 OBJECT IDENTIFIER ::= { cevModuleONS15530Type 140 }
cevONS1553010GCh24 OBJECT IDENTIFIER ::= { cevModuleONS15530Type 141 }
cevONS1553010GCh25 OBJECT IDENTIFIER ::= { cevModuleONS15530Type 142 }
cevONS1553010GCh26 OBJECT IDENTIFIER ::= { cevModuleONS15530Type 143 }
cevONS1553010GCh27 OBJECT IDENTIFIER ::= { cevModuleONS15530Type 144 }
cevONS1553010GCh28 OBJECT IDENTIFIER ::= { cevModuleONS15530Type 145 }
cevONS1553010GCh29 OBJECT IDENTIFIER ::= { cevModuleONS15530Type 146 }
cevONS1553010GCh30 OBJECT IDENTIFIER ::= { cevModuleONS15530Type 147 }
cevONS1553010GCh31 OBJECT IDENTIFIER ::= { cevModuleONS15530Type 148 }
cevONS1553010GCh32 OBJECT IDENTIFIER ::= { cevModuleONS15530Type 149 }
cevONS15530FCGE8P OBJECT IDENTIFIER ::= { cevModuleONS15530Type 150 }
cevONS155302p5GCh0102Sp OBJECT IDENTIFIER ::= { cevModuleONS15530Type 151 }
cevONS155302p5GCh0304Sp OBJECT IDENTIFIER ::= { cevModuleONS15530Type 152 }
cevONS155302p5GCh0506Sp OBJECT IDENTIFIER ::= { cevModuleONS15530Type 153 }
cevONS155302p5GCh0708Sp OBJECT IDENTIFIER ::= { cevModuleONS15530Type 154 }
cevONS155302p5GCh0910Sp OBJECT IDENTIFIER ::= { cevModuleONS15530Type 155 }
cevONS155302p5GCh1112Sp OBJECT IDENTIFIER ::= { cevModuleONS15530Type 156 }
cevONS155302p5GCh1314Sp OBJECT IDENTIFIER ::= { cevModuleONS15530Type 157 }
cevONS155302p5GCh1516Sp OBJECT IDENTIFIER ::= { cevModuleONS15530Type 158 }
cevONS155302p5GCh1718Sp OBJECT IDENTIFIER ::= { cevModuleONS15530Type 159 }
cevONS155302p5GCh1920Sp OBJECT IDENTIFIER ::= { cevModuleONS15530Type 160 }
cevONS155302p5GCh2122Sp OBJECT IDENTIFIER ::= { cevModuleONS15530Type 161 }
cevONS155302p5GCh2324Sp OBJECT IDENTIFIER ::= { cevModuleONS15530Type 162 }
cevONS155302p5GCh2526Sp OBJECT IDENTIFIER ::= { cevModuleONS15530Type 163 }
cevONS155302p5GCh2728Sp OBJECT IDENTIFIER ::= { cevModuleONS15530Type 164 }
cevONS155302p5GCh2930Sp OBJECT IDENTIFIER ::= { cevModuleONS15530Type 165 }
cevONS155302p5GCh3132Sp OBJECT IDENTIFIER ::= { cevModuleONS15530Type 166 }
cevONS155302p5GCh0102 OBJECT IDENTIFIER ::= { cevModuleONS15530Type 167 }
cevONS155302p5GCh0304 OBJECT IDENTIFIER ::= { cevModuleONS15530Type 168 }
cevONS155302p5GCh0506 OBJECT IDENTIFIER ::= { cevModuleONS15530Type 169 }
cevONS155302p5GCh0708 OBJECT IDENTIFIER ::= { cevModuleONS15530Type 170 }
cevONS155302p5GCh0910 OBJECT IDENTIFIER ::= { cevModuleONS15530Type 171 }
cevONS155302p5GCh1112 OBJECT IDENTIFIER ::= { cevModuleONS15530Type 172 }
cevONS155302p5GCh1314 OBJECT IDENTIFIER ::= { cevModuleONS15530Type 173 }
cevONS155302p5GCh1516 OBJECT IDENTIFIER ::= { cevModuleONS15530Type 174 }
cevONS155302p5GCh1718 OBJECT IDENTIFIER ::= { cevModuleONS15530Type 175 }
cevONS155302p5GCh1920 OBJECT IDENTIFIER ::= { cevModuleONS15530Type 176 }
cevONS155302p5GCh2122 OBJECT IDENTIFIER ::= { cevModuleONS15530Type 177 }
cevONS155302p5GCh2324 OBJECT IDENTIFIER ::= { cevModuleONS15530Type 178 }
cevONS155302p5GCh2526 OBJECT IDENTIFIER ::= { cevModuleONS15530Type 179 }
cevONS155302p5GCh2728 OBJECT IDENTIFIER ::= { cevModuleONS15530Type 180 }
cevONS155302p5GCh2930 OBJECT IDENTIFIER ::= { cevModuleONS15530Type 181 }
cevONS155302p5GCh3132 OBJECT IDENTIFIER ::= { cevModuleONS15530Type 182 }
cevONS15530PSM  OBJECT IDENTIFIER ::= { cevModuleONS15530Type 183 }
cevONS15530LC2xFC4P OBJECT IDENTIFIER ::= { cevModuleONS15530Type 184 }
cevONS15530MRC8PCh0102Sp OBJECT IDENTIFIER ::= { cevModuleONS15530Type 185 }
cevONS15530MRC8PCh0304Sp OBJECT IDENTIFIER ::= { cevModuleONS15530Type 186 }
cevONS15530MRC8PCh0506Sp OBJECT IDENTIFIER ::= { cevModuleONS15530Type 187 }
cevONS15530MRC8PCh0708Sp OBJECT IDENTIFIER ::= { cevModuleONS15530Type 188 }
cevONS15530MRC8PCh0910Sp OBJECT IDENTIFIER ::= { cevModuleONS15530Type 189 }
cevONS15530MRC8PCh1112Sp OBJECT IDENTIFIER ::= { cevModuleONS15530Type 190 }
cevONS15530MRC8PCh1314Sp OBJECT IDENTIFIER ::= { cevModuleONS15530Type 191 }
cevONS15530MRC8PCh1516Sp OBJECT IDENTIFIER ::= { cevModuleONS15530Type 192 }
cevONS15530MRC8PCh1718Sp OBJECT IDENTIFIER ::= { cevModuleONS15530Type 193 }
cevONS15530MRC8PCh1920Sp OBJECT IDENTIFIER ::= { cevModuleONS15530Type 194 }
cevONS15530MRC8PCh2122Sp OBJECT IDENTIFIER ::= { cevModuleONS15530Type 195 }
cevONS15530MRC8PCh2324Sp OBJECT IDENTIFIER ::= { cevModuleONS15530Type 196 }
cevONS15530MRC8PCh2526Sp OBJECT IDENTIFIER ::= { cevModuleONS15530Type 197 }
cevONS15530MRC8PCh2728Sp OBJECT IDENTIFIER ::= { cevModuleONS15530Type 198 }
cevONS15530MRC8PCh2930Sp OBJECT IDENTIFIER ::= { cevModuleONS15530Type 199 }
cevONS15530MRC8PCh3132Sp OBJECT IDENTIFIER ::= { cevModuleONS15530Type 200 }
cevONS15530MRC8PCh0102 OBJECT IDENTIFIER ::= { cevModuleONS15530Type 201 }
cevONS15530MRC8PCh0304 OBJECT IDENTIFIER ::= { cevModuleONS15530Type 202 }
cevONS15530MRC8PCh0506 OBJECT IDENTIFIER ::= { cevModuleONS15530Type 203 }
cevONS15530MRC8PCh0708 OBJECT IDENTIFIER ::= { cevModuleONS15530Type 204 }
cevONS15530MRC8PCh0910 OBJECT IDENTIFIER ::= { cevModuleONS15530Type 205 }
cevONS15530MRC8PCh1112 OBJECT IDENTIFIER ::= { cevModuleONS15530Type 206 }
cevONS15530MRC8PCh1314 OBJECT IDENTIFIER ::= { cevModuleONS15530Type 207 }
cevONS15530MRC8PCh1516 OBJECT IDENTIFIER ::= { cevModuleONS15530Type 208 }
cevONS15530MRC8PCh1718 OBJECT IDENTIFIER ::= { cevModuleONS15530Type 209 }
cevONS15530MRC8PCh1920 OBJECT IDENTIFIER ::= { cevModuleONS15530Type 210 }
cevONS15530MRC8PCh2122 OBJECT IDENTIFIER ::= { cevModuleONS15530Type 211 }
cevONS15530MRC8PCh2324 OBJECT IDENTIFIER ::= { cevModuleONS15530Type 212 }
cevONS15530MRC8PCh2526 OBJECT IDENTIFIER ::= { cevModuleONS15530Type 213 }
cevONS15530MRC8PCh2728 OBJECT IDENTIFIER ::= { cevModuleONS15530Type 214 }
cevONS15530MRC8PCh2930 OBJECT IDENTIFIER ::= { cevModuleONS15530Type 215 }
cevONS15530MRC8PCh3132 OBJECT IDENTIFIER ::= { cevModuleONS15530Type 216 }
cevONS1553010G4ChASp OBJECT IDENTIFIER ::= { cevModuleONS15530Type 217 }
cevONS1553010G4ChBSp OBJECT IDENTIFIER ::= { cevModuleONS15530Type 218 }
cevONS1553010G4ChCSp OBJECT IDENTIFIER ::= { cevModuleONS15530Type 219 }
cevONS1553010G4ChDSp OBJECT IDENTIFIER ::= { cevModuleONS15530Type 220 }
cevONS1553010G4ChESp OBJECT IDENTIFIER ::= { cevModuleONS15530Type 221 }
cevONS1553010G4ChFSp OBJECT IDENTIFIER ::= { cevModuleONS15530Type 222 }
cevONS1553010G4ChGSp OBJECT IDENTIFIER ::= { cevModuleONS15530Type 223 }
cevONS1553010G4ChHSp OBJECT IDENTIFIER ::= { cevModuleONS15530Type 224 }
cevONS1553010G4ChA OBJECT IDENTIFIER ::= { cevModuleONS15530Type 225 }
cevONS1553010G4ChB OBJECT IDENTIFIER ::= { cevModuleONS15530Type 226 }
cevONS1553010G4ChC OBJECT IDENTIFIER ::= { cevModuleONS15530Type 227 }
cevONS1553010G4ChD OBJECT IDENTIFIER ::= { cevModuleONS15530Type 228 }
cevONS1553010G4ChE OBJECT IDENTIFIER ::= { cevModuleONS15530Type 229 }
cevONS1553010G4ChF OBJECT IDENTIFIER ::= { cevModuleONS15530Type 230 }
cevONS1553010G4ChG OBJECT IDENTIFIER ::= { cevModuleONS15530Type 231 }
cevONS1553010G4ChH OBJECT IDENTIFIER ::= { cevModuleONS15530Type 232 }
cevONS1553010G32ChSp OBJECT IDENTIFIER ::= { cevModuleONS15530Type 233 }
cevONS1553010G32Ch OBJECT IDENTIFIER ::= { cevModuleONS15530Type 234 }
cevModuleONS15500Type OBJECT IDENTIFIER ::= { cevModule 46 }
cevONS15500PEQ01A OBJECT IDENTIFIER ::= { cevModuleONS15500Type 1 }
cevONS15500PEQ01B OBJECT IDENTIFIER ::= { cevModuleONS15500Type 2 }
cevONS15500PEQ01C OBJECT IDENTIFIER ::= { cevModuleONS15500Type 3 }
cevONS15500PEQ01D OBJECT IDENTIFIER ::= { cevModuleONS15500Type 4 }
cevONS15500PEQ01E OBJECT IDENTIFIER ::= { cevModuleONS15500Type 5 }
cevONS15500PEQ01F OBJECT IDENTIFIER ::= { cevModuleONS15500Type 6 }
cevONS15500PEQ01G OBJECT IDENTIFIER ::= { cevModuleONS15500Type 7 }
cevONS15500PEQ01H OBJECT IDENTIFIER ::= { cevModuleONS15500Type 8 }
cevONS15500PEQ02AB OBJECT IDENTIFIER ::= { cevModuleONS15500Type 9 }
cevONS15500PEQ02CD OBJECT IDENTIFIER ::= { cevModuleONS15500Type 10 }
cevONS15500PEQ02EF OBJECT IDENTIFIER ::= { cevModuleONS15500Type 11 }
cevONS15500PEQ02GH OBJECT IDENTIFIER ::= { cevModuleONS15500Type 12 }
cevONS15500VOA01 OBJECT IDENTIFIER ::= { cevModuleONS15500Type 13 }
cevONS15500VOA02 OBJECT IDENTIFIER ::= { cevModuleONS15500Type 14 }
cevONS15500XvrEscon1310MTRJ OBJECT IDENTIFIER ::= { cevModuleONS15500Type 15 }
cevONS15500XvrEscon1310LC OBJECT IDENTIFIER ::= { cevModuleONS15500Type 16 }
cevONS15500XvrFC850LC OBJECT IDENTIFIER ::= { cevModuleONS15500Type 17 }
cevONS15500XvrFC850MTRJ OBJECT IDENTIFIER ::= { cevModuleONS15500Type 18 }
cevONS15500XvrFC1310LC OBJECT IDENTIFIER ::= { cevModuleONS15500Type 19 }
cevONS15500XvrFC1310MTRJ OBJECT IDENTIFIER ::= { cevModuleONS15500Type 20 }
cevONS15500XvrGE850LC OBJECT IDENTIFIER ::= { cevModuleONS15500Type 21 }
cevONS15500XvrGE850MTRJ OBJECT IDENTIFIER ::= { cevModuleONS15500Type 22 }
cevONS15500XvrGE1310LC OBJECT IDENTIFIER ::= { cevModuleONS15500Type 23 }
cevONS15500XvrGE1310MTRJ OBJECT IDENTIFIER ::= { cevModuleONS15500Type 24 }
cevONS15500XvrGEFC850LC OBJECT IDENTIFIER ::= { cevModuleONS15500Type 25 }
cevONS15500XvrGEFC850MTRJ OBJECT IDENTIFIER ::= { cevModuleONS15500Type 26 }
cevONS15500XvrGEFC1310LC OBJECT IDENTIFIER ::= { cevModuleONS15500Type 27 }
cevONS15500XvrGEFC1310MTRJ OBJECT IDENTIFIER ::= { cevModuleONS15500Type 28 }
cevONS15500XvrOC3Son1310MTRJ OBJECT IDENTIFIER ::= { cevModuleONS15500Type 29 }
cevONS15500XvrOC3Son1310LC OBJECT IDENTIFIER ::= { cevModuleONS15500Type 30 }
cevONS15500XvrOC12Son1310MTRJ OBJECT IDENTIFIER ::= { cevModuleONS15500Type 31 }
cevONS15500XvrOC12Son1310LC OBJECT IDENTIFIER ::= { cevModuleONS15500Type 32 }
cevONS15500XvrOC48Son1310MTRJ OBJECT IDENTIFIER ::= { cevModuleONS15500Type 33 }
cevONS15500XvrOC48Son1310LC OBJECT IDENTIFIER ::= { cevModuleONS15500Type 34 }
cevONS15500XvrLowMM1310LC OBJECT IDENTIFIER ::= { cevModuleONS15500Type 35 }
cevONS15500XvrLowSM1310LC OBJECT IDENTIFIER ::= { cevModuleONS15500Type 36 }
cevONS15500XvrMidMM1310LC OBJECT IDENTIFIER ::= { cevModuleONS15500Type 37 }
cevONS15500XvrMidSM1310LC OBJECT IDENTIFIER ::= { cevModuleONS15500Type 38 }
cevONS15500XvrHighSM1310LC OBJECT IDENTIFIER ::= { cevModuleONS15500Type 39 }
cevONS15500XvrT1 OBJECT IDENTIFIER ::= { cevModuleONS15500Type 40 }
cevONS15500XvrE1 OBJECT IDENTIFIER ::= { cevModuleONS15500Type 41 }
cevONS15500XvrDV OBJECT IDENTIFIER ::= { cevModuleONS15500Type 42 }
cevModuleONS15454Type OBJECT IDENTIFIER ::= { cevModule 48 }
cevONS15454FeCE100 OBJECT IDENTIFIER ::= { cevModuleONS15454Type 3 }
cevONS15454Ge10ML2 OBJECT IDENTIFIER ::= { cevModuleONS15454Type 4 }
cevONS15454Ge10CE2 OBJECT IDENTIFIER ::= { cevModuleONS15454Type 5 }
cevONS15454cptPtf25610GX4 OBJECT IDENTIFIER ::= { cevModuleONS15454Type 9 }
cevModuleCat37xxType OBJECT IDENTIFIER ::= { cevModule 50 }
cevModuleCat375024 OBJECT IDENTIFIER ::= { cevModuleCat37xxType 1 }
cevModuleCat375048 OBJECT IDENTIFIER ::= { cevModuleCat37xxType 2 }
cevModuleCat375024TS OBJECT IDENTIFIER ::= { cevModuleCat37xxType 3 }
cevModuleCat375024T OBJECT IDENTIFIER ::= { cevModuleCat37xxType 4 }
cevModuleCat3750Ge12Sfp OBJECT IDENTIFIER ::= { cevModuleCat37xxType 6 }
cevModuleCat375048PS OBJECT IDENTIFIER ::= { cevModuleCat37xxType 7 }
cevModuleCat375024PS OBJECT IDENTIFIER ::= { cevModuleCat37xxType 8 }
cevModuleCat375024ME OBJECT IDENTIFIER ::= { cevModuleCat37xxType 9 }
cevModuleCat3750G16TD OBJECT IDENTIFIER ::= { cevModuleCat37xxType 10 }
cevModuleCat3750G24PS OBJECT IDENTIFIER ::= { cevModuleCat37xxType 11 }
cevModuleCat3750G48PS OBJECT IDENTIFIER ::= { cevModuleCat37xxType 12 }
cevModuleCat3750G48TS OBJECT IDENTIFIER ::= { cevModuleCat37xxType 13 }
cevModuleCat3750G24TS1U OBJECT IDENTIFIER ::= { cevModuleCat37xxType 14 }
cevModuleCat375024FS OBJECT IDENTIFIER ::= { cevModuleCat37xxType 16 }
cevModuleCat3750Ge12SfpDc OBJECT IDENTIFIER ::= { cevModuleCat37xxType 17 }
cevModuleCat3750G24WS OBJECT IDENTIFIER ::= { cevModuleCat37xxType 18 }
cevModuleCat3750E24TD OBJECT IDENTIFIER ::= { cevModuleCat37xxType 19 }
cevModuleCat3750E48TD OBJECT IDENTIFIER ::= { cevModuleCat37xxType 20 }
cevModuleCat3750E48PD OBJECT IDENTIFIER ::= { cevModuleCat37xxType 21 }
cevModuleCat3750E24PD OBJECT IDENTIFIER ::= { cevModuleCat37xxType 22 }
cevModuleCat3750v248ps OBJECT IDENTIFIER ::= { cevModuleCat37xxType 23 }
cevModuleCat3750v248ts OBJECT IDENTIFIER ::= { cevModuleCat37xxType 24 }
cevModuleCat3750v224ps OBJECT IDENTIFIER ::= { cevModuleCat37xxType 25 }
cevModuleCat3750v224ts OBJECT IDENTIFIER ::= { cevModuleCat37xxType 26 }
cevModuleCat3750x24 OBJECT IDENTIFIER ::= { cevModuleCat37xxType 27 }
cevModuleCat3750x48 OBJECT IDENTIFIER ::= { cevModuleCat37xxType 28 }
cevModuleCat3750x24P OBJECT IDENTIFIER ::= { cevModuleCat37xxType 29 }
cevModuleCat3750x48P OBJECT IDENTIFIER ::= { cevModuleCat37xxType 30 }
cevModuleCat3750x48U OBJECT IDENTIFIER ::= { cevModuleCat37xxType 33 }
cevModuleCat3750x24U OBJECT IDENTIFIER ::= { cevModuleCat37xxType 34 }
cevModuleSFPType OBJECT IDENTIFIER ::= { cevModule 51 }
cevSFPOc3mm     OBJECT IDENTIFIER ::= { cevModuleSFPType 1 }
cevSFPOc12mm    OBJECT IDENTIFIER ::= { cevModuleSFPType 2 }
cevSFPOc48      OBJECT IDENTIFIER ::= { cevModuleSFPType 3 }
cevSFPOc3Oc12   OBJECT IDENTIFIER ::= { cevModuleSFPType 4 }
cevSFPOc3Oc12Oc48 OBJECT IDENTIFIER ::= { cevModuleSFPType 5 }
cevSFP1000BaseSx OBJECT IDENTIFIER ::= { cevModuleSFPType 6 }
cevSFP1000BaseLx OBJECT IDENTIFIER ::= { cevModuleSFPType 7 }
cevSFP1000BaseT OBJECT IDENTIFIER ::= { cevModuleSFPType 8 }
cevSFP1000BaseZx OBJECT IDENTIFIER ::= { cevModuleSFPType 9 }
cevSFPCwdm1470  OBJECT IDENTIFIER ::= { cevModuleSFPType 10 }
cevSFPCwdm1490  OBJECT IDENTIFIER ::= { cevModuleSFPType 11 }
cevSFPCwdm1510  OBJECT IDENTIFIER ::= { cevModuleSFPType 12 }
cevSFPCwdm1530  OBJECT IDENTIFIER ::= { cevModuleSFPType 13 }
cevSFPCwdm1550  OBJECT IDENTIFIER ::= { cevModuleSFPType 14 }
cevSFPCwdm1570  OBJECT IDENTIFIER ::= { cevModuleSFPType 15 }
cevSFPCwdm1590  OBJECT IDENTIFIER ::= { cevModuleSFPType 16 }
cevSFPCwdm1610  OBJECT IDENTIFIER ::= { cevModuleSFPType 17 }
cevSFP1000BaseLh OBJECT IDENTIFIER ::= { cevModuleSFPType 18 }
cevSFP1000BaseCx OBJECT IDENTIFIER ::= { cevModuleSFPType 19 }
cevSFPOc3smir   OBJECT IDENTIFIER ::= { cevModuleSFPType 20 }
cevSFPOc3smlr   OBJECT IDENTIFIER ::= { cevModuleSFPType 21 }
cevSFPOc12smir  OBJECT IDENTIFIER ::= { cevModuleSFPType 22 }
cevSFPOc12smlr  OBJECT IDENTIFIER ::= { cevModuleSFPType 23 }
cevSFPOc48smsr  OBJECT IDENTIFIER ::= { cevModuleSFPType 24 }
cevSFPOc48smir  OBJECT IDENTIFIER ::= { cevModuleSFPType 25 }
cevSFPOc48smlr  OBJECT IDENTIFIER ::= { cevModuleSFPType 26 }
cevXFPOc192smsr1 OBJECT IDENTIFIER ::= { cevModuleSFPType 27 }
cevXFPOc192smir2 OBJECT IDENTIFIER ::= { cevModuleSFPType 28 }
cevXFPOc192smlr2 OBJECT IDENTIFIER ::= { cevModuleSFPType 29 }
cevSFPCable50cm OBJECT IDENTIFIER ::= { cevModuleSFPType 30 }
cevSFPOc48smlr2 OBJECT IDENTIFIER ::= { cevModuleSFPType 33 }
cevSFPOc3smsr   OBJECT IDENTIFIER ::= { cevModuleSFPType 34 }
cevSFPOc12smsr  OBJECT IDENTIFIER ::= { cevModuleSFPType 35 }
cevSFPOc48mm    OBJECT IDENTIFIER ::= { cevModuleSFPType 36 }
cevSFPDwdm3033  OBJECT IDENTIFIER ::= { cevModuleSFPType 37 }
cevSFPDwdm3112  OBJECT IDENTIFIER ::= { cevModuleSFPType 38 }
cevSFPDwdm3190  OBJECT IDENTIFIER ::= { cevModuleSFPType 39 }
cevSFPDwdm3268  OBJECT IDENTIFIER ::= { cevModuleSFPType 40 }
cevSFPDwdm3425  OBJECT IDENTIFIER ::= { cevModuleSFPType 41 }
cevSFPDwdm3504  OBJECT IDENTIFIER ::= { cevModuleSFPType 42 }
cevSFPDwdm3582  OBJECT IDENTIFIER ::= { cevModuleSFPType 43 }
cevSFPDwdm3661  OBJECT IDENTIFIER ::= { cevModuleSFPType 44 }
cevSFPDwdm3819  OBJECT IDENTIFIER ::= { cevModuleSFPType 45 }
cevSFPDwdm3898  OBJECT IDENTIFIER ::= { cevModuleSFPType 46 }
cevSFPDwdm3977  OBJECT IDENTIFIER ::= { cevModuleSFPType 47 }
cevSFPDwdm4056  OBJECT IDENTIFIER ::= { cevModuleSFPType 48 }
cevSFPDwdm4214  OBJECT IDENTIFIER ::= { cevModuleSFPType 49 }
cevSFPDwdm4294  OBJECT IDENTIFIER ::= { cevModuleSFPType 50 }
cevSFPDwdm4373  OBJECT IDENTIFIER ::= { cevModuleSFPType 51 }
cevSFPDwdm4453  OBJECT IDENTIFIER ::= { cevModuleSFPType 52 }
cevSFPDwdm4612  OBJECT IDENTIFIER ::= { cevModuleSFPType 53 }
cevSFPDwdm4692  OBJECT IDENTIFIER ::= { cevModuleSFPType 54 }
cevSFPDwdm4772  OBJECT IDENTIFIER ::= { cevModuleSFPType 55 }
cevSFPDwdm4851  OBJECT IDENTIFIER ::= { cevModuleSFPType 56 }
cevSFPDwdm5012  OBJECT IDENTIFIER ::= { cevModuleSFPType 57 }
cevSFPDwdm5092  OBJECT IDENTIFIER ::= { cevModuleSFPType 58 }
cevSFPDwdm5172  OBJECT IDENTIFIER ::= { cevModuleSFPType 59 }
cevSFPDwdm5252  OBJECT IDENTIFIER ::= { cevModuleSFPType 60 }
cevSFPDwdm5413  OBJECT IDENTIFIER ::= { cevModuleSFPType 61 }
cevSFPDwdm5494  OBJECT IDENTIFIER ::= { cevModuleSFPType 62 }
cevSFPDwdm5575  OBJECT IDENTIFIER ::= { cevModuleSFPType 63 }
cevSFPDwdm5655  OBJECT IDENTIFIER ::= { cevModuleSFPType 64 }
cevSFPDwdm5817  OBJECT IDENTIFIER ::= { cevModuleSFPType 65 }
cevSFPDwdm5898  OBJECT IDENTIFIER ::= { cevModuleSFPType 66 }
cevSFPDwdm5979  OBJECT IDENTIFIER ::= { cevModuleSFPType 67 }
cevSFPDwdm6061  OBJECT IDENTIFIER ::= { cevModuleSFPType 68 }
cevSFP1000BaseBX10D OBJECT IDENTIFIER ::= { cevModuleSFPType 69 }
cevSFP1000BaseBX10U OBJECT IDENTIFIER ::= { cevModuleSFPType 70 }
cevSFP100BaseFX OBJECT IDENTIFIER ::= { cevModuleSFPType 71 }
cevSFP100BaseLX OBJECT IDENTIFIER ::= { cevModuleSFPType 72 }
cevSFP100BaseSX OBJECT IDENTIFIER ::= { cevModuleSFPType 73 }
cevSFP100BaseZX OBJECT IDENTIFIER ::= { cevModuleSFPType 74 }
cevSFP100BaseEX OBJECT IDENTIFIER ::= { cevModuleSFPType 75 }
cevSFP100BaseBX10D OBJECT IDENTIFIER ::= { cevModuleSFPType 76 }
cevSFP100BaseBX10U OBJECT IDENTIFIER ::= { cevModuleSFPType 77 }
cevSFPDwdmXFP6061 OBJECT IDENTIFIER ::= { cevModuleSFPType 78 }
cevSFPDwdmXFP5979 OBJECT IDENTIFIER ::= { cevModuleSFPType 79 }
cevSFPDwdmXFP5898 OBJECT IDENTIFIER ::= { cevModuleSFPType 80 }
cevSFPDwdmXFP5817 OBJECT IDENTIFIER ::= { cevModuleSFPType 81 }
cevSFPDwdmXFP5655 OBJECT IDENTIFIER ::= { cevModuleSFPType 82 }
cevSFPDwdmXFP5575 OBJECT IDENTIFIER ::= { cevModuleSFPType 83 }
cevSFPDwdmXFP5494 OBJECT IDENTIFIER ::= { cevModuleSFPType 84 }
cevSFPDwdmXFP5413 OBJECT IDENTIFIER ::= { cevModuleSFPType 85 }
cevSFPDwdmXFP5252 OBJECT IDENTIFIER ::= { cevModuleSFPType 86 }
cevSFPDwdmXFP5172 OBJECT IDENTIFIER ::= { cevModuleSFPType 87 }
cevSFPDwdmXFP5092 OBJECT IDENTIFIER ::= { cevModuleSFPType 88 }
cevSFPDwdmXFP5012 OBJECT IDENTIFIER ::= { cevModuleSFPType 89 }
cevSFPDwdmXFP4851 OBJECT IDENTIFIER ::= { cevModuleSFPType 90 }
cevSFPDwdmXFP4772 OBJECT IDENTIFIER ::= { cevModuleSFPType 91 }
cevSFPDwdmXFP4692 OBJECT IDENTIFIER ::= { cevModuleSFPType 92 }
cevSFPDwdmXFP4612 OBJECT IDENTIFIER ::= { cevModuleSFPType 93 }
cevSFPDwdmXFP4453 OBJECT IDENTIFIER ::= { cevModuleSFPType 94 }
cevSFPDwdmXFP4373 OBJECT IDENTIFIER ::= { cevModuleSFPType 95 }
cevSFPDwdmXFP4294 OBJECT IDENTIFIER ::= { cevModuleSFPType 96 }
cevSFPDwdmXFP4214 OBJECT IDENTIFIER ::= { cevModuleSFPType 97 }
cevSFPDwdmXFP4056 OBJECT IDENTIFIER ::= { cevModuleSFPType 98 }
cevSFPDwdmXFP3977 OBJECT IDENTIFIER ::= { cevModuleSFPType 99 }
cevSFPDwdmXFP3898 OBJECT IDENTIFIER ::= { cevModuleSFPType 100 }
cevSFPDwdmXFP3819 OBJECT IDENTIFIER ::= { cevModuleSFPType 101 }
cevSFPDwdmXFP3661 OBJECT IDENTIFIER ::= { cevModuleSFPType 102 }
cevSFPDwdmXFP3582 OBJECT IDENTIFIER ::= { cevModuleSFPType 103 }
cevSFPDwdmXFP3504 OBJECT IDENTIFIER ::= { cevModuleSFPType 104 }
cevSFPDwdmXFP3425 OBJECT IDENTIFIER ::= { cevModuleSFPType 105 }
cevSFPDwdmXFP3268 OBJECT IDENTIFIER ::= { cevModuleSFPType 106 }
cevSFPDwdmXFP3190 OBJECT IDENTIFIER ::= { cevModuleSFPType 107 }
cevSFPDwdmXFP3112 OBJECT IDENTIFIER ::= { cevModuleSFPType 108 }
cevSFPDwdmXFP3033 OBJECT IDENTIFIER ::= { cevModuleSFPType 109 }
cevSFPDwdm6141  OBJECT IDENTIFIER ::= { cevModuleSFPType 110 }
cevSFPDwdm5736  OBJECT IDENTIFIER ::= { cevModuleSFPType 111 }
cevSFPDwdm5332  OBJECT IDENTIFIER ::= { cevModuleSFPType 112 }
cevSFPDwdm4931  OBJECT IDENTIFIER ::= { cevModuleSFPType 113 }
cevSFPDwdm4532  OBJECT IDENTIFIER ::= { cevModuleSFPType 114 }
cevSFPDwdm4134  OBJECT IDENTIFIER ::= { cevModuleSFPType 115 }
cevSFPDwdm3739  OBJECT IDENTIFIER ::= { cevModuleSFPType 116 }
cevSFPDwdm3346  OBJECT IDENTIFIER ::= { cevModuleSFPType 117 }
cevSFPUnknown   OBJECT IDENTIFIER ::= { cevModuleSFPType 118 }
cevXFPUnknown   OBJECT IDENTIFIER ::= { cevModuleSFPType 119 }
cevSFPStm1E     OBJECT IDENTIFIER ::= { cevModuleSFPType 120 }
cevXFPmmsr      OBJECT IDENTIFIER ::= { cevModuleSFPType 121 }
cevXFR10gMMSR   OBJECT IDENTIFIER ::= { cevModuleSFPType 122 }
cevSFPTDwdmXfp  OBJECT IDENTIFIER ::= { cevModuleSFPType 123 }
cevXFP10GLR192SRL OBJECT IDENTIFIER ::= { cevModuleSFPType 124 }
cevXFP10GER192IRL OBJECT IDENTIFIER ::= { cevModuleSFPType 125 }
cevSFPCiscoSfpT3Ge OBJECT IDENTIFIER ::= { cevModuleSFPType 126 }
cevSFPT1E1Fe    OBJECT IDENTIFIER ::= { cevModuleSFPType 127 }
cevSFPT3E3Fe    OBJECT IDENTIFIER ::= { cevModuleSFPType 128 }
cevXFPDWDMXFPC  OBJECT IDENTIFIER ::= { cevModuleSFPType 129 }
cevXFP10GLROC192 OBJECT IDENTIFIER ::= { cevModuleSFPType 130 }
cevXFP10GER192IR OBJECT IDENTIFIER ::= { cevModuleSFPType 131 }
cevXFP10GZROC192 OBJECT IDENTIFIER ::= { cevModuleSFPType 132 }
cevXFP10GMMSR   OBJECT IDENTIFIER ::= { cevModuleSFPType 133 }
cevSFPGLC2BXD   OBJECT IDENTIFIER ::= { cevModuleSFPType 134 }
cevSFPGLC2BXU   OBJECT IDENTIFIER ::= { cevModuleSFPType 135 }
cevSFPGLCFE1002BX OBJECT IDENTIFIER ::= { cevModuleSFPType 136 }
cevSFPGLCFE1002BXU OBJECT IDENTIFIER ::= { cevModuleSFPType 137 }
cevSFPGlcSxMmd  OBJECT IDENTIFIER ::= { cevModuleSFPType 138 }
cevSFPGlcTe     OBJECT IDENTIFIER ::= { cevModuleSFPType 139 }
cevSFPGlcZxSmd  OBJECT IDENTIFIER ::= { cevModuleSFPType 140 }
cevSFPGlcExSmd  OBJECT IDENTIFIER ::= { cevModuleSFPType 141 }
cevSFPGlcLhSmd  OBJECT IDENTIFIER ::= { cevModuleSFPType 142 }
cevSFP100BaseF  OBJECT IDENTIFIER ::= { cevModuleSFPType 143 }
cevSFPDSSFPFC16GSW OBJECT IDENTIFIER ::= { cevModuleSFPType 144 }
cevSFDSSFPFC16GLW OBJECT IDENTIFIER ::= { cevModuleSFPType 145 }
cevSFPGLCGE100FX OBJECT IDENTIFIER ::= { cevModuleSFPType 146 }
cevSFPCwdmXFP1570 OBJECT IDENTIFIER ::= { cevModuleSFPType 147 }
cevSFPCwdmXFP1470 OBJECT IDENTIFIER ::= { cevModuleSFPType 148 }
cevSFPCwdmXFP1490 OBJECT IDENTIFIER ::= { cevModuleSFPType 149 }
cevSFPCwdmXFP1510 OBJECT IDENTIFIER ::= { cevModuleSFPType 150 }
cevSFPCwdmXFP1530 OBJECT IDENTIFIER ::= { cevModuleSFPType 151 }
cevSFPCwdmXFP1550 OBJECT IDENTIFIER ::= { cevModuleSFPType 152 }
cevSFPCwdmXFP1590 OBJECT IDENTIFIER ::= { cevModuleSFPType 153 }
cevSFPCwdmXFP1610 OBJECT IDENTIFIER ::= { cevModuleSFPType 154 }
cevSFP1000BaseBX40D OBJECT IDENTIFIER ::= { cevModuleSFPType 155 }
cevSFP1000BaseBX40U OBJECT IDENTIFIER ::= { cevModuleSFPType 156 }
cevSFP1000BaseBX80D OBJECT IDENTIFIER ::= { cevModuleSFPType 157 }
cevSFP1000BaseBX80U OBJECT IDENTIFIER ::= { cevModuleSFPType 158 }
cevSFP100BaseGlcExFe OBJECT IDENTIFIER ::= { cevModuleSFPType 159 }
cevSFP100BaseGlcZxFe OBJECT IDENTIFIER ::= { cevModuleSFPType 160 }
cevSFPONSSIGESX OBJECT IDENTIFIER ::= { cevModuleSFPType 186 }
cevSFPONSSIGELX OBJECT IDENTIFIER ::= { cevModuleSFPType 187 }
cevSFPONSSIGEZX OBJECT IDENTIFIER ::= { cevModuleSFPType 188 }
cevSFPONSSEZEEL OBJECT IDENTIFIER ::= { cevModuleSFPType 189 }
cevSFPONSSI2GS1 OBJECT IDENTIFIER ::= { cevModuleSFPType 190 }
cevSFPONSSI2GL1 OBJECT IDENTIFIER ::= { cevModuleSFPType 191 }
cevSFPONSSI2GL2 OBJECT IDENTIFIER ::= { cevModuleSFPType 192 }
cevSFPONSSEZ1   OBJECT IDENTIFIER ::= { cevModuleSFPType 193 }
cevSFP1000BaseBx40DI OBJECT IDENTIFIER ::= { cevModuleSFPType 194 }
cevSFP1000BaseBx40DAI OBJECT IDENTIFIER ::= { cevModuleSFPType 195 }
cevSFP1000BaseBx40UI OBJECT IDENTIFIER ::= { cevModuleSFPType 196 }
cevSFP1000BaseBx80DI OBJECT IDENTIFIER ::= { cevModuleSFPType 197 }
cevSFP1000BaseBx80UI OBJECT IDENTIFIER ::= { cevModuleSFPType 198 }
cevSFPGlcT      OBJECT IDENTIFIER ::= { cevModuleSFPType 199 }
cevSSFPOAM1000BaseZX OBJECT IDENTIFIER ::= { cevModuleSFPType 200 }
cevSSFPOAM1000BaseLX OBJECT IDENTIFIER ::= { cevModuleSFPType 201 }
cevSFPGLCBX40UI OBJECT IDENTIFIER ::= { cevModuleSFPType 202 }
cevSFPGLCBX40DI OBJECT IDENTIFIER ::= { cevModuleSFPType 203 }
cevSFPGLCBX40DAI OBJECT IDENTIFIER ::= { cevModuleSFPType 204 }
cevSFPGLCBX80UI OBJECT IDENTIFIER ::= { cevModuleSFPType 205 }
cevSFPGLCBX80DI OBJECT IDENTIFIER ::= { cevModuleSFPType 206 }
cevSFP100BaseGlcFeBxU OBJECT IDENTIFIER ::= { cevModuleSFPType 249 }
cevSFP100BaseGlcFeBxD OBJECT IDENTIFIER ::= { cevModuleSFPType 250 }
cevSFPGLCFETI   OBJECT IDENTIFIER ::= { cevModuleSFPType 251 }
cevSFPGLC2BXDI  OBJECT IDENTIFIER ::= { cevModuleSFPType 252 }
cevSFPASR9KvGlcFe100ex OBJECT IDENTIFIER ::= { cevModuleSFPType 254 }
cevSFPASR9KvGlcFe100zx OBJECT IDENTIFIER ::= { cevModuleSFPType 255 }
cevModuleONS15200Type OBJECT IDENTIFIER ::= { cevModule 52 }
cevONS15252Clip OBJECT IDENTIFIER ::= { cevModuleONS15200Type 1 }
cevONS15201Clip OBJECT IDENTIFIER ::= { cevModuleONS15200Type 2 }
cevONS15252Ncb  OBJECT IDENTIFIER ::= { cevModuleONS15200Type 3 }
cevModuleMDSType OBJECT IDENTIFIER ::= { cevModule 53 }
cevMDSDsX9530Sf1K9 OBJECT IDENTIFIER ::= { cevModuleMDSType 1 }
cevMDSRedDsX9530Sf1K9 OBJECT IDENTIFIER ::= { cevModuleMDSType 2 }
cevMDSDsX9016   OBJECT IDENTIFIER ::= { cevModuleMDSType 3 }
cevMDSDsX9032   OBJECT IDENTIFIER ::= { cevModuleMDSType 4 }
cevMDSDsX9032Smv OBJECT IDENTIFIER ::= { cevModuleMDSType 5 }
cevMDSDsX9308Smip OBJECT IDENTIFIER ::= { cevModuleMDSType 6 }
cevMDSDsX9560Smc OBJECT IDENTIFIER ::= { cevModuleMDSType 7 }
cevMDSDsSfpFc2Gsw OBJECT IDENTIFIER ::= { cevModuleMDSType 8 }
cevMDSDsSfpFc2Glw OBJECT IDENTIFIER ::= { cevModuleMDSType 9 }
cevMDSDsSfpGeSw OBJECT IDENTIFIER ::= { cevModuleMDSType 10 }
cevMDSDsSfpGeLw OBJECT IDENTIFIER ::= { cevModuleMDSType 11 }
cevMDSDsC9500Cl OBJECT IDENTIFIER ::= { cevModuleMDSType 12 }
cevMDSDsX9216K9Sup OBJECT IDENTIFIER ::= { cevModuleMDSType 13 }
cevMDSMemFld512M OBJECT IDENTIFIER ::= { cevModuleMDSType 14 }
cevMDSMemMd1G   OBJECT IDENTIFIER ::= { cevModuleMDSType 15 }
cevMDSDsC9509Cl OBJECT IDENTIFIER ::= { cevModuleMDSType 16 }
cevMDSDsC9506Cl OBJECT IDENTIFIER ::= { cevModuleMDSType 17 }
cevMDSDsX9140K9Sup OBJECT IDENTIFIER ::= { cevModuleMDSType 18 }
cevMDSDsX9120K9Sup OBJECT IDENTIFIER ::= { cevModuleMDSType 19 }
cevMDSDsX9032Sma OBJECT IDENTIFIER ::= { cevModuleMDSType 20 }
cevMDSDsX9216Mgt OBJECT IDENTIFIER ::= { cevModuleMDSType 21 }
cevMDSDsX930214K9 OBJECT IDENTIFIER ::= { cevModuleMDSType 22 }
cevMDSDsX9202   OBJECT IDENTIFIER ::= { cevModuleMDSType 23 }
cevMDSDsX9304Smip OBJECT IDENTIFIER ::= { cevModuleMDSType 24 }
cevMDSDsX9132K9Sup OBJECT IDENTIFIER ::= { cevModuleMDSType 25 }
cevMDSDsX9116K9Sup OBJECT IDENTIFIER ::= { cevModuleMDSType 26 }
cevMDSDsX9216IK9Sup OBJECT IDENTIFIER ::= { cevModuleMDSType 27 }
cevMDSDsX9530Sf2K9 OBJECT IDENTIFIER ::= { cevModuleMDSType 28 }
cevMDSDsX9112   OBJECT IDENTIFIER ::= { cevModuleMDSType 29 }
cevMDSDsX9124   OBJECT IDENTIFIER ::= { cevModuleMDSType 30 }
cevMDSDsX9148   OBJECT IDENTIFIER ::= { cevModuleMDSType 31 }
cevMDSDsX9704   OBJECT IDENTIFIER ::= { cevModuleMDSType 32 }
cevMDSDs13SltFab1 OBJECT IDENTIFIER ::= { cevModuleMDSType 33 }
cevMDSDsC9513Cl OBJECT IDENTIFIER ::= { cevModuleMDSType 34 }
cevMDSDsX9124S2K9 OBJECT IDENTIFIER ::= { cevModuleMDSType 35 }
cevMDSDsIBMFC   OBJECT IDENTIFIER ::= { cevModuleMDSType 36 }
cevMDSDsHPFC    OBJECT IDENTIFIER ::= { cevModuleMDSType 37 }
cevMDSDsX9222iK9Sup OBJECT IDENTIFIER ::= { cevModuleMDSType 38 }
cevMDSDxX930418K9 OBJECT IDENTIFIER ::= { cevModuleMDSType 39 }
cevMDSDsX9134S2K9 OBJECT IDENTIFIER ::= { cevModuleMDSType 40 }
cevMdsDSC9222iK9Sup OBJECT IDENTIFIER ::= { cevModuleMDSType 41 }
cevMDSDsX9248FC48Gbps OBJECT IDENTIFIER ::= { cevModuleMDSType 42 }
cevMDSDsX9248FC96Gbps OBJECT IDENTIFIER ::= { cevModuleMDSType 43 }
cevMDSDsX9316SSM OBJECT IDENTIFIER ::= { cevModuleMDSType 44 }
cevMDSDs13SltFab2 OBJECT IDENTIFIER ::= { cevModuleMDSType 45 }
cevMDSDsX922496k9 OBJECT IDENTIFIER ::= { cevModuleMDSType 46 }
cevMDSDsX9716K9 OBJECT IDENTIFIER ::= { cevModuleMDSType 52 }
cevMDSDsX9248x256K9 OBJECT IDENTIFIER ::= { cevModuleMDSType 53 }
cevMDSDsX9232x256K9 OBJECT IDENTIFIER ::= { cevModuleMDSType 54 }
cevMDSDs13SlotFabricEvia3 OBJECT IDENTIFIER ::= { cevModuleMDSType 55 }
cevMDSDsX9530Sf2AK9 OBJECT IDENTIFIER ::= { cevModuleMDSType 56 }
cevMDSDs9708HPK9 OBJECT IDENTIFIER ::= { cevModuleMDSType 57 }
cevMDSDs9708K9  OBJECT IDENTIFIER ::= { cevModuleMDSType 58 }
cevMDSDSX9448n768K9 OBJECT IDENTIFIER ::= { cevModuleMDSType 61 }
cevMDSDSX9848n480K9SM OBJECT IDENTIFIER ::= { cevModuleMDSType 62 }
cevMDSDSX97SF1K9SUP OBJECT IDENTIFIER ::= { cevModuleMDSType 63 }
cevMDSDSX9710FAB1 OBJECT IDENTIFIER ::= { cevModuleMDSType 64 }
cevMDS9710FCS   OBJECT IDENTIFIER ::= { cevModuleMDSType 65 }
cevMDS9250iIFSPS OBJECT IDENTIFIER ::= { cevModuleMDSType 66 }
cevMDS9250iIFSDC OBJECT IDENTIFIER ::= { cevModuleMDSType 67 }
cevMDSDSC9250i22PK9SUPFS OBJECT IDENTIFIER ::= { cevModuleMDSType 68 }
cevMDSDSX9848480K9 OBJECT IDENTIFIER ::= { cevModuleMDSType 69 }
cevMDSDSX9706FAB1 OBJECT IDENTIFIER ::= { cevModuleMDSType 70 }
cevMDSDSC9148SK9SUP OBJECT IDENTIFIER ::= { cevModuleMDSType 71 }
cevMDSDSC9396SK9SUP OBJECT IDENTIFIER ::= { cevModuleMDSType 72 }
cevMDSDSX97SF1EK9 OBJECT IDENTIFIER ::= { cevModuleMDSType 73 }
cevMDSDSX9718FAB1 OBJECT IDENTIFIER ::= { cevModuleMDSType 74 }
cevMDSDSX9334K9 OBJECT IDENTIFIER ::= { cevModuleMDSType 75 }
cevMDSDSX9824960K9 OBJECT IDENTIFIER ::= { cevModuleMDSType 76 }
cevMDSDSX96481536K9 OBJECT IDENTIFIER ::= { cevModuleMDSType 77 }
cevMDSDSC9132U  OBJECT IDENTIFIER ::= { cevModuleMDSType 78 }
cevMDSDSC9232U  OBJECT IDENTIFIER ::= { cevModuleMDSType 79 }
cevMDSM9132UFC16 OBJECT IDENTIFIER ::= { cevModuleMDSType 80 }
cevModuleC3220Type OBJECT IDENTIFIER ::= { cevModule 54 }
cevC3220Smic    OBJECT IDENTIFIER ::= { cevModuleC3220Type 1 }
cevC3220Fesmic  OBJECT IDENTIFIER ::= { cevModuleC3220Type 2 }
cevModuleCrs1Type OBJECT IDENTIFIER ::= { cevModule 55 }
cevModuleCrs1RP OBJECT IDENTIFIER ::= { cevModuleCrs1Type 1 }
cevModuleCrs1DRP OBJECT IDENTIFIER ::= { cevModuleCrs1Type 2 }
cevModuleCrs18sS123Fabric OBJECT IDENTIFIER ::= { cevModuleCrs1Type 3 }
cevModuleCrs116sS123Fabric OBJECT IDENTIFIER ::= { cevModuleCrs1Type 4 }
cevModuleCrs116dS123TFabric OBJECT IDENTIFIER ::= { cevModuleCrs1Type 5 }
cevModuleCrs116mS13Fabric OBJECT IDENTIFIER ::= { cevModuleCrs1Type 6 }
cevModuleCrs116mS2CCFabric OBJECT IDENTIFIER ::= { cevModuleCrs1Type 7 }
cevModuleCrs116mS2Fabric OBJECT IDENTIFIER ::= { cevModuleCrs1Type 8 }
cevModuleCrs1FanCtrllrLC OBJECT IDENTIFIER ::= { cevModuleCrs1Type 9 }
cevModuleCrs116mS2FanCtrllrFabric OBJECT IDENTIFIER ::= { cevModuleCrs1Type 10 }
cevModuleCrs1Alarm OBJECT IDENTIFIER ::= { cevModuleCrs1Type 11 }
cevModuleCrs116mFabricLED OBJECT IDENTIFIER ::= { cevModuleCrs1Type 12 }
cevModuleCrs1DRPPlim OBJECT IDENTIFIER ::= { cevModuleCrs1Type 13 }
cevModuleCrs116OC48Plim OBJECT IDENTIFIER ::= { cevModuleCrs1Type 14 }
cevModuleCrs14OC192VSRPlim OBJECT IDENTIFIER ::= { cevModuleCrs1Type 15 }
cevModuleCrs14OC192SRPlim OBJECT IDENTIFIER ::= { cevModuleCrs1Type 16 }
cevModulecrs14OC192LRPlim OBJECT IDENTIFIER ::= { cevModuleCrs1Type 17 }
cevModuleCrs1OC768VSRPlim OBJECT IDENTIFIER ::= { cevModuleCrs1Type 18 }
cevModuleCrs1OC768SRPlim OBJECT IDENTIFIER ::= { cevModuleCrs1Type 19 }
cevModuleCrs16x10GePlim OBJECT IDENTIFIER ::= { cevModuleCrs1Type 20 }
cevModuleCrs18x10GePlim OBJECT IDENTIFIER ::= { cevModuleCrs1Type 21 }
cevModuleCrs18RP OBJECT IDENTIFIER ::= { cevModuleCrs1Type 22 }
cevModuleCrs18Fabric OBJECT IDENTIFIER ::= { cevModuleCrs1Type 23 }
cevModuleCrs1FabricShelfController OBJECT IDENTIFIER ::= { cevModuleCrs1Type 24 }
cevModuleCrs1FabricSwitchFabric OBJECT IDENTIFIER ::= { cevModuleCrs1Type 25 }
cevModuleCrs1FabricLEDModule OBJECT IDENTIFIER ::= { cevModuleCrs1Type 26 }
cevModuleCrs1FabricOIMSingleSlot OBJECT IDENTIFIER ::= { cevModuleCrs1Type 27 }
cevModuleCrs1FabricOIMDualSlot OBJECT IDENTIFIER ::= { cevModuleCrs1Type 28 }
cevModuleCrs18dS123Fabric OBJECT IDENTIFIER ::= { cevModuleCrs1Type 29 }
cevModuleCrs18mS123Fabric OBJECT IDENTIFIER ::= { cevModuleCrs1Type 30 }
cevModuleCrs116dS123Fabric OBJECT IDENTIFIER ::= { cevModuleCrs1Type 31 }
cevModuleCrs1FccSc22Ge OBJECT IDENTIFIER ::= { cevModuleCrs1Type 32 }
cevModuleCrs1FccSFEc OBJECT IDENTIFIER ::= { cevModuleCrs1Type 33 }
cevModuleCrs14x10GeCDwdmPlim OBJECT IDENTIFIER ::= { cevModuleCrs1Type 34 }
cevModuleCrs14OC192CDwdmPlim OBJECT IDENTIFIER ::= { cevModuleCrs1Type 35 }
cevModuleCrs1OC768CDwdmPlim OBJECT IDENTIFIER ::= { cevModuleCrs1Type 36 }
cevModuleCrs1DRPBPlim OBJECT IDENTIFIER ::= { cevModuleCrs1Type 37 }
cevModuleCrs1DRPB OBJECT IDENTIFIER ::= { cevModuleCrs1Type 38 }
cevModuleCrs1OC768CDwdmDpskC OBJECT IDENTIFIER ::= { cevModuleCrs1Type 39 }
cevModuleCrs14FabricCard OBJECT IDENTIFIER ::= { cevModuleCrs1Type 42 }
cevModuleCrsASPLIM OBJECT IDENTIFIER ::= { cevModuleCrs1Type 43 }
cevModuleCrs4OC192DptLr OBJECT IDENTIFIER ::= { cevModuleCrs1Type 44 }
cevModuleCrs4OC192DptSr OBJECT IDENTIFIER ::= { cevModuleCrs1Type 45 }
cevModuleCrs4OC192DptVs OBJECT IDENTIFIER ::= { cevModuleCrs1Type 46 }
cevModuleCrs14x10GE OBJECT IDENTIFIER ::= { cevModuleCrs1Type 47 }
cevModuleCrs142x1GE OBJECT IDENTIFIER ::= { cevModuleCrs1Type 48 }
cevModuleCrs120x1GeFl OBJECT IDENTIFIER ::= { cevModuleCrs1Type 49 }
cevModuleCrs12x10GeFl OBJECT IDENTIFIER ::= { cevModuleCrs1Type 50 }
cevModuleCrs116Alarm OBJECT IDENTIFIER ::= { cevModuleCrs1Type 51 }
cevModuleCrs14x10GbeWLXfpPlim OBJECT IDENTIFIER ::= { cevModuleCrs1Type 52 }
cevModuleCrs18x10GbeWLXfpPlim OBJECT IDENTIFIER ::= { cevModuleCrs1Type 53 }
cevModuleCrs1LcB40G OBJECT IDENTIFIER ::= { cevModuleCrs1Type 54 }
cevModuleCrs1Lc40G OBJECT IDENTIFIER ::= { cevModuleCrs1Type 55 }
cevModuleCrs114X10GBEWLXFPPlim OBJECT IDENTIFIER ::= { cevModuleCrs1Type 56 }
cevModuleCrs120X10GBEWLXFPPlim OBJECT IDENTIFIER ::= { cevModuleCrs1Type 57 }
cevModuleCrs11X100GBEPlim OBJECT IDENTIFIER ::= { cevModuleCrs1Type 58 }
cevModuleCrs8Prp12g OBJECT IDENTIFIER ::= { cevModuleCrs1Type 59 }
cevModuleCrs8Prp6g OBJECT IDENTIFIER ::= { cevModuleCrs1Type 60 }
cevModuleCrs16Prp12g OBJECT IDENTIFIER ::= { cevModuleCrs1Type 61 }
cevModuleCrs16Prp6g OBJECT IDENTIFIER ::= { cevModuleCrs1Type 62 }
cevModuleCrs16FanCtB OBJECT IDENTIFIER ::= { cevModuleCrs1Type 63 }
cevModuleCrs16AlarmMB OBJECT IDENTIFIER ::= { cevModuleCrs1Type 64 }
cevModuleCrs16LccFCtB OBJECT IDENTIFIER ::= { cevModuleCrs1Type 65 }
cevModuleCrs114X10GBEDwdmXfpPlim OBJECT IDENTIFIER ::= { cevModuleCrs1Type 66 }
cevModuleCrs120X10GBEDwdmXfpPlim OBJECT IDENTIFIER ::= { cevModuleCrs1Type 67 }
cevModuleCrs14X40GBEOtu3Plim OBJECT IDENTIFIER ::= { cevModuleCrs1Type 68 }
cevModuleCrs11X100GBEDwdmPlim OBJECT IDENTIFIER ::= { cevModuleCrs1Type 69 }
cevModuleCrsCgsePlusPlim OBJECT IDENTIFIER ::= { cevModuleCrs1Type 72 }
cevModuleCrs140X10GEWLOPlim OBJECT IDENTIFIER ::= { cevModuleCrs1Type 73 }
cevModuleCrs14x100GELOPlim OBJECT IDENTIFIER ::= { cevModuleCrs1Type 74 }
cevModuleCrs12X100GELOFlex40Plim OBJECT IDENTIFIER ::= { cevModuleCrs1Type 75 }
cevModuleCrs400GEDWDMFLEX OBJECT IDENTIFIER ::= { cevModuleCrs1Type 76 }
cevModuleCat35xxType OBJECT IDENTIFIER ::= { cevModule 56 }
cevModuleCat356024PS OBJECT IDENTIFIER ::= { cevModuleCat35xxType 1 }
cevModuleCat356048PS OBJECT IDENTIFIER ::= { cevModuleCat35xxType 2 }
cevModuleCat3560G24PS OBJECT IDENTIFIER ::= { cevModuleCat35xxType 3 }
cevModuleCat3560G24TS OBJECT IDENTIFIER ::= { cevModuleCat35xxType 4 }
cevModuleCat3560G48PS OBJECT IDENTIFIER ::= { cevModuleCat35xxType 5 }
cevModuleCat3560G48TS OBJECT IDENTIFIER ::= { cevModuleCat35xxType 6 }
cevModuleCat356024TS OBJECT IDENTIFIER ::= { cevModuleCat35xxType 7 }
cevModuleCat356048TS OBJECT IDENTIFIER ::= { cevModuleCat35xxType 8 }
cevModuleCat3560E24TD OBJECT IDENTIFIER ::= { cevModuleCat35xxType 9 }
cevModuleCat3560E48TD OBJECT IDENTIFIER ::= { cevModuleCat35xxType 10 }
cevModuleCat3560E24PD OBJECT IDENTIFIER ::= { cevModuleCat35xxType 11 }
cevModuleCat3560E48PD OBJECT IDENTIFIER ::= { cevModuleCat35xxType 12 }
cevModuleCat35608PC OBJECT IDENTIFIER ::= { cevModuleCat35xxType 13 }
cevModuleCat3560e12d OBJECT IDENTIFIER ::= { cevModuleCat35xxType 14 }
cevModuleCat3560E12SD OBJECT IDENTIFIER ::= { cevModuleCat35xxType 15 }
cevModuleCat356012PCS OBJECT IDENTIFIER ::= { cevModuleCat35xxType 16 }
cevModuleCat3560v248ps OBJECT IDENTIFIER ::= { cevModuleCat35xxType 17 }
cevModuleCat3560v248ts OBJECT IDENTIFIER ::= { cevModuleCat35xxType 18 }
cevModuleCat3560v224ps OBJECT IDENTIFIER ::= { cevModuleCat35xxType 19 }
cevModuleCat3560v224ts OBJECT IDENTIFIER ::= { cevModuleCat35xxType 20 }
cevModuleCat3560v224tsD OBJECT IDENTIFIER ::= { cevModuleCat35xxType 21 }
cevModuleCat3560x24 OBJECT IDENTIFIER ::= { cevModuleCat35xxType 22 }
cevModuleCat3560x48 OBJECT IDENTIFIER ::= { cevModuleCat35xxType 23 }
cevModuleWsC3560CPD8ptS OBJECT IDENTIFIER ::= { cevModuleCat35xxType 28 }
cevModuleWsC3560C12pcS OBJECT IDENTIFIER ::= { cevModuleCat35xxType 29 }
cevModuleWsC3560C8pcS OBJECT IDENTIFIER ::= { cevModuleCat35xxType 30 }
cevModuleCat3560x48U OBJECT IDENTIFIER ::= { cevModuleCat35xxType 31 }
cevModuleCat3557x24U OBJECT IDENTIFIER ::= { cevModuleCat35xxType 32 }
cevModuleWsC3560CX8PTS OBJECT IDENTIFIER ::= { cevModuleCat35xxType 43 }
cevModuleWsC3560CX8XPDS OBJECT IDENTIFIER ::= { cevModuleCat35xxType 44 }
cevModuleWsC3560CX12PDS OBJECT IDENTIFIER ::= { cevModuleCat35xxType 45 }
cevModuleWsC3560CX12TCS OBJECT IDENTIFIER ::= { cevModuleCat35xxType 46 }
cevModuleWsC3560CX12PCS OBJECT IDENTIFIER ::= { cevModuleCat35xxType 47 }
cevModuleWsC3560CX8TCS OBJECT IDENTIFIER ::= { cevModuleCat35xxType 48 }
cevModuleWsC3560CX8PCS OBJECT IDENTIFIER ::= { cevModuleCat35xxType 49 }
cevModuleASA5523Type OBJECT IDENTIFIER ::= { cevModule 57 }
cevMASA5523IsmSsmIds20K9 OBJECT IDENTIFIER ::= { cevModuleASA5523Type 1 }
cevMASA5523PmSsmIO4ge OBJECT IDENTIFIER ::= { cevModuleASA5523Type 2 }
cevMASA5523IsmSsmIds10K9 OBJECT IDENTIFIER ::= { cevModuleASA5523Type 3 }
cevPmSsmIO4geInc OBJECT IDENTIFIER ::= { cevModuleASA5523Type 4 }
cevMASA5523IsmSsmCsc10 OBJECT IDENTIFIER ::= { cevModuleASA5523Type 5 }
cevMASA5523IsmSsmCsc20 OBJECT IDENTIFIER ::= { cevModuleASA5523Type 6 }
cevMASA5523IsmSsmIds40K9 OBJECT IDENTIFIER ::= { cevModuleASA5523Type 7 }
cevModuleUmg9820Type OBJECT IDENTIFIER ::= { cevModule 58 }
cevModuleUmg9820GigEProc OBJECT IDENTIFIER ::= { cevModuleUmg9820Type 1 }
cevModuleUmg9820QamCard OBJECT IDENTIFIER ::= { cevModuleUmg9820Type 2 }
cevModuleONS15310Type OBJECT IDENTIFIER ::= { cevModule 59 }
cevONS15310FeML100 OBJECT IDENTIFIER ::= { cevModuleONS15310Type 1 }
cevONS15310FeCE100 OBJECT IDENTIFIER ::= { cevModuleONS15310Type 2 }
cevONS15310Ge8CE2 OBJECT IDENTIFIER ::= { cevModuleONS15310Type 3 }
cevModuleX2s    OBJECT IDENTIFIER ::= { cevModule 60 }
cevMX210GBaseSR OBJECT IDENTIFIER ::= { cevModuleX2s 1 }
cevMX210GBaseLR OBJECT IDENTIFIER ::= { cevModuleX2s 2 }
cevMX210GBaseER OBJECT IDENTIFIER ::= { cevModuleX2s 3 }
cevMX210GBaseLX4 OBJECT IDENTIFIER ::= { cevModuleX2s 4 }
cevMX210GBaseCX4 OBJECT IDENTIFIER ::= { cevModuleX2s 5 }
cevMX210GBaseZR OBJECT IDENTIFIER ::= { cevModuleX2s 6 }
cevMX210GBaseLW OBJECT IDENTIFIER ::= { cevModuleX2s 7 }
cevMX210GBaseLRM OBJECT IDENTIFIER ::= { cevModuleX2s 8 }
cevMX210GBaseT  OBJECT IDENTIFIER ::= { cevModuleX2s 9 }
cevMX2s10GBaseWdmRxOnly OBJECT IDENTIFIER ::= { cevModuleX2s 10 }
cevMX2s10GBaseDwdm3033 OBJECT IDENTIFIER ::= { cevModuleX2s 11 }
cevMX2s10GBaseDwdm3112 OBJECT IDENTIFIER ::= { cevModuleX2s 13 }
cevMX2s10GBaseDwdm3190 OBJECT IDENTIFIER ::= { cevModuleX2s 14 }
cevMX2s10GBaseDwdm3268 OBJECT IDENTIFIER ::= { cevModuleX2s 15 }
cevMX2s10GBaseDwdm3425 OBJECT IDENTIFIER ::= { cevModuleX2s 16 }
cevMX2s10GBaseDwdm3504 OBJECT IDENTIFIER ::= { cevModuleX2s 17 }
cevMX2s10GBaseDwdm3582 OBJECT IDENTIFIER ::= { cevModuleX2s 18 }
cevMX2s10GBaseDwdm3661 OBJECT IDENTIFIER ::= { cevModuleX2s 19 }
cevMX2s10GBaseDwdm3819 OBJECT IDENTIFIER ::= { cevModuleX2s 20 }
cevMX2s10GBaseDwdm3898 OBJECT IDENTIFIER ::= { cevModuleX2s 21 }
cevMX2s10GBaseDwdm3977 OBJECT IDENTIFIER ::= { cevModuleX2s 22 }
cevMX2s10GBaseDwdm4056 OBJECT IDENTIFIER ::= { cevModuleX2s 23 }
cevMX2s10GBaseDwdm4214 OBJECT IDENTIFIER ::= { cevModuleX2s 24 }
cevMX2s10GBaseDwdm4294 OBJECT IDENTIFIER ::= { cevModuleX2s 25 }
cevMX2s10GBaseDwdm4373 OBJECT IDENTIFIER ::= { cevModuleX2s 26 }
cevMX2s10GBaseDwdm4453 OBJECT IDENTIFIER ::= { cevModuleX2s 27 }
cevMX2s10GBaseDwdm4612 OBJECT IDENTIFIER ::= { cevModuleX2s 28 }
cevMX2s10GBaseDwdm4692 OBJECT IDENTIFIER ::= { cevModuleX2s 29 }
cevMX2s10GBaseDwdm4772 OBJECT IDENTIFIER ::= { cevModuleX2s 30 }
cevMX2s10GBaseDwdm4851 OBJECT IDENTIFIER ::= { cevModuleX2s 31 }
cevMX2s10GBaseDwdm5012 OBJECT IDENTIFIER ::= { cevModuleX2s 32 }
cevMX2s10GBaseDwdm5092 OBJECT IDENTIFIER ::= { cevModuleX2s 33 }
cevMX2s10GBaseDwdm5172 OBJECT IDENTIFIER ::= { cevModuleX2s 34 }
cevMX2s10GBaseDwdm5252 OBJECT IDENTIFIER ::= { cevModuleX2s 35 }
cevMX2s10GBaseDwdm5413 OBJECT IDENTIFIER ::= { cevModuleX2s 36 }
cevMX2s10GBaseDwdm5494 OBJECT IDENTIFIER ::= { cevModuleX2s 37 }
cevMX2s10GBaseDwdm5575 OBJECT IDENTIFIER ::= { cevModuleX2s 38 }
cevMX2s10GBaseDwdm5655 OBJECT IDENTIFIER ::= { cevModuleX2s 39 }
cevMX2s10GBaseDwdm5817 OBJECT IDENTIFIER ::= { cevModuleX2s 40 }
cevMX2s10GBaseDwdm5898 OBJECT IDENTIFIER ::= { cevModuleX2s 41 }
cevMX2s10GBaseDwdm5979 OBJECT IDENTIFIER ::= { cevModuleX2s 42 }
cevMX2s10GBaseDwdm6061 OBJECT IDENTIFIER ::= { cevModuleX2s 43 }
cevMX210GEBaseT OBJECT IDENTIFIER ::= { cevModuleX2s 44 }
cevModuleCE5xxType OBJECT IDENTIFIER ::= { cevModule 63 }
cevModuleCE50024TT OBJECT IDENTIFIER ::= { cevModuleCE5xxType 1 }
cevModuleCE50024LC OBJECT IDENTIFIER ::= { cevModuleCE5xxType 2 }
cevModuleCE50024PC OBJECT IDENTIFIER ::= { cevModuleCE5xxType 3 }
cevModuleCE500G12TC OBJECT IDENTIFIER ::= { cevModuleCE5xxType 4 }
cevModuleCE5208PC OBJECT IDENTIFIER ::= { cevModuleCE5xxType 5 }
cevModuleCE52024PC OBJECT IDENTIFIER ::= { cevModuleCE5xxType 6 }
cevModuleCE52024TT OBJECT IDENTIFIER ::= { cevModuleCE5xxType 7 }
cevModuleCE52024LC OBJECT IDENTIFIER ::= { cevModuleCE5xxType 8 }
cevModule520G24TC OBJECT IDENTIFIER ::= { cevModuleCE5xxType 9 }
cevModuleMEType OBJECT IDENTIFIER ::= { cevModule 64 }
cevModuleME240024TS OBJECT IDENTIFIER ::= { cevModuleMEType 1 }
cevModuleME340024TS OBJECT IDENTIFIER ::= { cevModuleMEType 2 }
cevModuleME3400G12CS OBJECT IDENTIFIER ::= { cevModuleMEType 3 }
cevModuleME3400G2CS OBJECT IDENTIFIER ::= { cevModuleMEType 4 }
cevModuleME492410GE OBJECT IDENTIFIER ::= { cevModuleMEType 5 }
cevModuleME340024FS OBJECT IDENTIFIER ::= { cevModuleMEType 6 }
cevModuleME3400E24TS OBJECT IDENTIFIER ::= { cevModuleMEType 7 }
cevModuleME3400EG12CS OBJECT IDENTIFIER ::= { cevModuleMEType 8 }
cevModuleME3400EG2CS OBJECT IDENTIFIER ::= { cevModuleMEType 9 }
cevModuleME3600X24FS OBJECT IDENTIFIER ::= { cevModuleMEType 10 }
cevModuleME3600X24TS OBJECT IDENTIFIER ::= { cevModuleMEType 11 }
cevModuleME3800X24FS OBJECT IDENTIFIER ::= { cevModuleMEType 12 }
cevModuleCat4000EType OBJECT IDENTIFIER ::= { cevModule 65 }
cevCat4kWsx45Sup6e OBJECT IDENTIFIER ::= { cevModuleCat4000EType 1 }
cevCat4kWsx4648Rj45e OBJECT IDENTIFIER ::= { cevModuleCat4000EType 2 }
cevCat4kWsx4648Rj45ve OBJECT IDENTIFIER ::= { cevModuleCat4000EType 3 }
cevCat4kWsx4606X2e OBJECT IDENTIFIER ::= { cevModuleCat4000EType 4 }
cevCat4kWsx4624Sfpe OBJECT IDENTIFIER ::= { cevModuleCat4000EType 5 }
cevCat4kWsx4590E OBJECT IDENTIFIER ::= { cevModuleCat4000EType 7 }
cevCat4kWsx4648Rj45je OBJECT IDENTIFIER ::= { cevModuleCat4000EType 9 }
cevCat4kWsx4648Rj45vPlusE OBJECT IDENTIFIER ::= { cevModuleCat4000EType 10 }
cevCat4kWsx45Sup6LE OBJECT IDENTIFIER ::= { cevModuleCat4000EType 13 }
cevCat4kWsx45Sup7e OBJECT IDENTIFIER ::= { cevModuleCat4000EType 14 }
cevCat4kWsx4748Rj45VPlusE OBJECT IDENTIFIER ::= { cevModuleCat4000EType 15 }
cevCat4kWsx4712SfpPlusE OBJECT IDENTIFIER ::= { cevModuleCat4000EType 16 }
cevCat4kWsx4612SfpE OBJECT IDENTIFIER ::= { cevModuleCat4000EType 17 }
cevCat4kWsx4640CSfpE OBJECT IDENTIFIER ::= { cevModuleCat4000EType 18 }
cevCatWsX4748Rj45E OBJECT IDENTIFIER ::= { cevModuleCat4000EType 19 }
cevCat4kWsX4748NgpoeE OBJECT IDENTIFIER ::= { cevModuleCat4000EType 20 }
cevCat4kWsx4712SfpE OBJECT IDENTIFIER ::= { cevModuleCat4000EType 21 }
cevCat4kWsx4724SfpE OBJECT IDENTIFIER ::= { cevModuleCat4000EType 22 }
cevCat4kWsx4748SfpE OBJECT IDENTIFIER ::= { cevModuleCat4000EType 23 }
cevCat4kWsX474812X48uE OBJECT IDENTIFIER ::= { cevModuleCat4000EType 33 }
cevModuleN7KType OBJECT IDENTIFIER ::= { cevModule 66 }
cevN7KSup1      OBJECT IDENTIFIER ::= { cevModuleN7KType 1 }
cevN7KM148GT04  OBJECT IDENTIFIER ::= { cevModuleN7KType 2 }
cevN7KM132XP08  OBJECT IDENTIFIER ::= { cevModuleN7KType 3 }
cevN7Kc7010Fab40 OBJECT IDENTIFIER ::= { cevModuleN7KType 4 }
cevN7KM148GS11  OBJECT IDENTIFIER ::= { cevModuleN7KType 5 }
cevN7Kc7018Fab1 OBJECT IDENTIFIER ::= { cevModuleN7KType 6 }
cevN7KF132Xp15  OBJECT IDENTIFIER ::= { cevModuleN7KType 7 }
cevN7KM108X212  OBJECT IDENTIFIER ::= { cevModuleN7KType 8 }
cevN7KM108X212L OBJECT IDENTIFIER ::= { cevModuleN7KType 9 }
cevN7KM148GS11L OBJECT IDENTIFIER ::= { cevModuleN7KType 10 }
cevN7KM116XP22L OBJECT IDENTIFIER ::= { cevModuleN7KType 11 }
cevN7KM108XP22L OBJECT IDENTIFIER ::= { cevModuleN7KType 12 }
cevN7KM132XP12L OBJECT IDENTIFIER ::= { cevModuleN7KType 13 }
cevN7Kc7009Fab2 OBJECT IDENTIFIER ::= { cevModuleN7KType 14 }
cevN7Kc7010Fab2 OBJECT IDENTIFIER ::= { cevModuleN7KType 16 }
cevN7Kc7018Fab2 OBJECT IDENTIFIER ::= { cevModuleN7KType 17 }
cevN7KF248XP24  OBJECT IDENTIFIER ::= { cevModuleN7KType 18 }
cevN7KF248XT24  OBJECT IDENTIFIER ::= { cevModuleN7KType 19 }
cevN7KSUP2      OBJECT IDENTIFIER ::= { cevModuleN7KType 20 }
cevN7KM202CF22L OBJECT IDENTIFIER ::= { cevModuleN7KType 21 }
cevN7KM206FQ23L OBJECT IDENTIFIER ::= { cevModuleN7KType 22 }
cevN7KM148GT11L OBJECT IDENTIFIER ::= { cevModuleN7KType 23 }
cevN7KSMNAMK9   OBJECT IDENTIFIER ::= { cevModuleN7KType 27 }
cevN7KFabricExtenderConnectionCable OBJECT IDENTIFIER ::= { cevModuleN7KType 31 }
cevN7KM224XP23L OBJECT IDENTIFIER ::= { cevModuleN7KType 32 }
cevN7KSUP2E     OBJECT IDENTIFIER ::= { cevModuleN7KType 33 }
cevN7KForwardingEngine OBJECT IDENTIFIER ::= { cevModuleN7KType 34 }
cevN7KF306CK25  OBJECT IDENTIFIER ::= { cevModuleN7KType 35 }
cevN7KF312FQ25  OBJECT IDENTIFIER ::= { cevModuleN7KType 36 }
cevN7KF248XT25E OBJECT IDENTIFIER ::= { cevModuleN7KType 45 }
cevN7KF248XP25E OBJECT IDENTIFIER ::= { cevModuleN7KType 46 }
cevN7KM324FQ25L OBJECT IDENTIFIER ::= { cevModuleN7KType 48 }
cevN7KM348XP25L OBJECT IDENTIFIER ::= { cevModuleN7KType 51 }
cevModuleASA5580Type OBJECT IDENTIFIER ::= { cevModule 67 }
cevModuleASA5580Pm4x1geCu OBJECT IDENTIFIER ::= { cevModuleASA5580Type 1 }
cevModuleASA5580Pm4x1geFi OBJECT IDENTIFIER ::= { cevModuleASA5580Type 2 }
cevModuleASA5580Pm2x10geFi OBJECT IDENTIFIER ::= { cevModuleASA5580Type 3 }
cevModuleASR1000Type OBJECT IDENTIFIER ::= { cevModule 68 }
cevModuleASR1000RP1 OBJECT IDENTIFIER ::= { cevModuleASR1000Type 1 }
cevModuleASR1000ESP10 OBJECT IDENTIFIER ::= { cevModuleASR1000Type 2 }
cevModuleASR1000SIP10 OBJECT IDENTIFIER ::= { cevModuleASR1000Type 3 }
cevModuleASR1000UnknownRP OBJECT IDENTIFIER ::= { cevModuleASR1000Type 4 }
cevModuleASR1000UnknownESP OBJECT IDENTIFIER ::= { cevModuleASR1000Type 5 }
cevModuleASR1000UnknownSIP OBJECT IDENTIFIER ::= { cevModuleASR1000Type 6 }
cevModuleASR1002RP1 OBJECT IDENTIFIER ::= { cevModuleASR1000Type 7 }
cevModuleASR1000ESP5 OBJECT IDENTIFIER ::= { cevModuleASR1000Type 8 }
cevModuleASR1000ESP20 OBJECT IDENTIFIER ::= { cevModuleASR1000Type 9 }
cevModuleASR1002Spa4pGe OBJECT IDENTIFIER ::= { cevModuleASR1000Type 10 }
cevModuleASR1002SIP10 OBJECT IDENTIFIER ::= { cevModuleASR1000Type 11 }
cevModuleASR1000SIP40 OBJECT IDENTIFIER ::= { cevModuleASR1000Type 12 }
cevModuleASR1000RP2 OBJECT IDENTIFIER ::= { cevModuleASR1000Type 13 }
cevModuleASR1000ESP10N OBJECT IDENTIFIER ::= { cevModuleASR1000Type 14 }
cevModuleASR1002FESP OBJECT IDENTIFIER ::= { cevModuleASR1000Type 15 }
cevModuleASR1002FSIP10 OBJECT IDENTIFIER ::= { cevModuleASR1000Type 16 }
cevModuleASR1000ESP40 OBJECT IDENTIFIER ::= { cevModuleASR1000Type 17 }
cevModuleASR1001RP OBJECT IDENTIFIER ::= { cevModuleASR1000Type 18 }
cevModuleASR1001ESP OBJECT IDENTIFIER ::= { cevModuleASR1000Type 19 }
cevModuleASR1001SIP OBJECT IDENTIFIER ::= { cevModuleASR1000Type 20 }
cevModuleASR1001Spa4pGe OBJECT IDENTIFIER ::= { cevModuleASR1000Type 21 }
cevModuleASR1001IDC2xOc3Pos OBJECT IDENTIFIER ::= { cevModuleASR1000Type 22 }
cevModuleASR1001IDC4xT3 OBJECT IDENTIFIER ::= { cevModuleASR1000Type 23 }
cevModuleASR1001IDC8xChT1E1 OBJECT IDENTIFIER ::= { cevModuleASR1000Type 24 }
cevModuleASR1001IDC4xGe OBJECT IDENTIFIER ::= { cevModuleASR1000Type 25 }
cevModuleASR1001IDCHDD OBJECT IDENTIFIER ::= { cevModuleASR1000Type 26 }
cevModuleASR1002XRP OBJECT IDENTIFIER ::= { cevModuleASR1000Type 27 }
cevModuleASR1002XESP OBJECT IDENTIFIER ::= { cevModuleASR1000Type 28 }
cevModuleASR1002XSIP OBJECT IDENTIFIER ::= { cevModuleASR1000Type 29 }
cevModuleASR1002X6xGeBuiltIn OBJECT IDENTIFIER ::= { cevModuleASR1000Type 30 }
cevModuleASR1000ESP100 OBJECT IDENTIFIER ::= { cevModuleASR1000Type 31 }
cevModuleASR1000ESP200 OBJECT IDENTIFIER ::= { cevModuleASR1000Type 32 }
cevModuleASR1000ELC2xT20xGe OBJECT IDENTIFIER ::= { cevModuleASR1000Type 33 }
cevModuleASR1000ELC40GModule OBJECT IDENTIFIER ::= { cevModuleASR1000Type 34 }
cevModuleASR1002XCRP OBJECT IDENTIFIER ::= { cevModuleASR1000Type 35 }
cevModuleASR1002XCESP OBJECT IDENTIFIER ::= { cevModuleASR1000Type 36 }
cevModuleASR1002XCSIP OBJECT IDENTIFIER ::= { cevModuleASR1000Type 37 }
cevModuleASR1002XC2xGeBuiltIn OBJECT IDENTIFIER ::= { cevModuleASR1000Type 38 }
cevModuleASR1001XRP OBJECT IDENTIFIER ::= { cevModuleASR1000Type 39 }
cevModuleASR1001XESP OBJECT IDENTIFIER ::= { cevModuleASR1000Type 40 }
cevModuleASR1001XSIP OBJECT IDENTIFIER ::= { cevModuleASR1000Type 41 }
cevModuleASR1002HXRP OBJECT IDENTIFIER ::= { cevModuleASR1000Type 51 }
cevModuleASR1002HXESP OBJECT IDENTIFIER ::= { cevModuleASR1000Type 52 }
cevModuleASR1002HXMIP OBJECT IDENTIFIER ::= { cevModuleASR1000Type 53 }
cevModuleASR1001HXRP OBJECT IDENTIFIER ::= { cevModuleASR1000Type 56 }
cevModuleASR1001HXESP OBJECT IDENTIFIER ::= { cevModuleASR1000Type 57 }
cevModuleASR1001HXMIP OBJECT IDENTIFIER ::= { cevModuleASR1000Type 58 }
cevModuleCatRfgwType OBJECT IDENTIFIER ::= { cevModule 69 }
cevRfgwDtcc     OBJECT IDENTIFIER ::= { cevModuleCatRfgwType 1 }
cevRfgwQam48ABC OBJECT IDENTIFIER ::= { cevModuleCatRfgwType 2 }
cevRfgwPort4Qam OBJECT IDENTIFIER ::= { cevModuleCatRfgwType 3 }
cevRfgwRfswitch OBJECT IDENTIFIER ::= { cevModuleCatRfgwType 4 }
cevRfgwQam384ABC OBJECT IDENTIFIER ::= { cevModuleCatRfgwType 5 }
cevModuleVgdType OBJECT IDENTIFIER ::= { cevModule 70 }
cevVgdDfcCT3    OBJECT IDENTIFIER ::= { cevModuleVgdType 1 }
cevVgdDfcVFC    OBJECT IDENTIFIER ::= { cevModuleVgdType 2 }
cevVgdDfcCarrier OBJECT IDENTIFIER ::= { cevModuleVgdType 3 }
cevModuleIEType OBJECT IDENTIFIER ::= { cevModule 71 }
cevModuleIE30004TC OBJECT IDENTIFIER ::= { cevModuleIEType 1 }
cevModuleIE30008TC OBJECT IDENTIFIER ::= { cevModuleIEType 2 }
cevModuleIE30008TM OBJECT IDENTIFIER ::= { cevModuleIEType 3 }
cevModuleIE30008FM OBJECT IDENTIFIER ::= { cevModuleIEType 4 }
cevModuleRAIE1783MS06T OBJECT IDENTIFIER ::= { cevModuleIEType 5 }
cevModuleRAIE1783MS10T OBJECT IDENTIFIER ::= { cevModuleIEType 6 }
cevModuleRAIE1783MX08T OBJECT IDENTIFIER ::= { cevModuleIEType 7 }
cevModuleRAIE1783MX08F OBJECT IDENTIFIER ::= { cevModuleIEType 8 }
cevModuleIE301016S8PC OBJECT IDENTIFIER ::= { cevModuleIEType 9 }
cevModuleRAIE1783RMS06T OBJECT IDENTIFIER ::= { cevModuleIEType 13 }
cevModuleRAIE1783RMS10T OBJECT IDENTIFIER ::= { cevModuleIEType 14 }
cevModuleIE20004TS OBJECT IDENTIFIER ::= { cevModuleIEType 15 }
cevModuleIE20004T OBJECT IDENTIFIER ::= { cevModuleIEType 16 }
cevModuleIE20004TSG OBJECT IDENTIFIER ::= { cevModuleIEType 17 }
cevModuleIE20004TG OBJECT IDENTIFIER ::= { cevModuleIEType 18 }
cevModuleIE20008TC OBJECT IDENTIFIER ::= { cevModuleIEType 19 }
cevModuleIE20008TCG OBJECT IDENTIFIER ::= { cevModuleIEType 20 }
cevModuleIE200016TC OBJECT IDENTIFIER ::= { cevModuleIEType 21 }
cevModuleIE200016TCG OBJECT IDENTIFIER ::= { cevModuleIEType 22 }
cevModuleIE200016TCGX OBJECT IDENTIFIER ::= { cevModuleIEType 23 }
cevModuleRAIE1783BMS06SL OBJECT IDENTIFIER ::= { cevModuleIEType 24 }
cevModuleRAIE1783BMS06SA OBJECT IDENTIFIER ::= { cevModuleIEType 25 }
cevModuleRAIE1783BMS06TL OBJECT IDENTIFIER ::= { cevModuleIEType 26 }
cevModuleRAIE1783BMS06TA OBJECT IDENTIFIER ::= { cevModuleIEType 27 }
cevModuleRAIE1783BMS06SGL OBJECT IDENTIFIER ::= { cevModuleIEType 28 }
cevModuleRAIE1783BMS06SGA OBJECT IDENTIFIER ::= { cevModuleIEType 29 }
cevModuleRAIE1783BMS06TGL OBJECT IDENTIFIER ::= { cevModuleIEType 30 }
cevModuleRAIE1783BMS06TGA OBJECT IDENTIFIER ::= { cevModuleIEType 31 }
cevModuleRAIE1783BMS10CL OBJECT IDENTIFIER ::= { cevModuleIEType 32 }
cevModuleRAIE1783BMS10CA OBJECT IDENTIFIER ::= { cevModuleIEType 33 }
cevModuleRAIE1783BMS10CGL OBJECT IDENTIFIER ::= { cevModuleIEType 34 }
cevModuleRAIE1783BMS10CGA OBJECT IDENTIFIER ::= { cevModuleIEType 35 }
cevModuleRAIE1783BMS10CGP OBJECT IDENTIFIER ::= { cevModuleIEType 36 }
cevModuleRAIE1783BMS10CGN OBJECT IDENTIFIER ::= { cevModuleIEType 37 }
cevModuleRAIE1783BMS20CL OBJECT IDENTIFIER ::= { cevModuleIEType 38 }
cevModuleRAIE1783BMS20CA OBJECT IDENTIFIER ::= { cevModuleIEType 39 }
cevModuleRAIE1783BMS20CGL OBJECT IDENTIFIER ::= { cevModuleIEType 40 }
cevModuleRAIE1783BMS20CGP OBJECT IDENTIFIER ::= { cevModuleIEType 41 }
cevModuleRAIE1783BMS20CGPK OBJECT IDENTIFIER ::= { cevModuleIEType 42 }
cevModuleIE200016TCGP OBJECT IDENTIFIER ::= { cevModuleIEType 52 }
cevModuleIE200016TCGEP OBJECT IDENTIFIER ::= { cevModuleIEType 53 }
cevModuleIE200016TCGNXP OBJECT IDENTIFIER ::= { cevModuleIEType 54 }
cevModuleIE30004SM OBJECT IDENTIFIER ::= { cevModuleIEType 55 }
cevModuleIE30008SM OBJECT IDENTIFIER ::= { cevModuleIEType 56 }
cevModuleRAIE1783MX04S OBJECT IDENTIFIER ::= { cevModuleIEType 57 }
cevModuleRAIE1783MX08S OBJECT IDENTIFIER ::= { cevModuleIEType 58 }
cevModuleIE30004PC OBJECT IDENTIFIER ::= { cevModuleIEType 59 }
cevModuleIE30004PC4TC OBJECT IDENTIFIER ::= { cevModuleIEType 60 }
cevModuleRAIE1783MX04E OBJECT IDENTIFIER ::= { cevModuleIEType 61 }
cevModuleRAIE1783MX04T04E OBJECT IDENTIFIER ::= { cevModuleIEType 62 }
cevModuleIE20008TCGN OBJECT IDENTIFIER ::= { cevModuleIEType 63 }
cevModuleIE200016TCGN OBJECT IDENTIFIER ::= { cevModuleIEType 64 }
cevModuleRAIE1783BMS20CGN OBJECT IDENTIFIER ::= { cevModuleIEType 65 }
cevModuleRAIE1783BMS12T4E2CGL OBJECT IDENTIFIER ::= { cevModuleIEType 66 }
cevModuleRAIE1783BMS12T4E2CGP OBJECT IDENTIFIER ::= { cevModuleIEType 67 }
cevModuleRAIE1783BMS12T4E2CGNK OBJECT IDENTIFIER ::= { cevModuleIEType 68 }
cevModuleIem30004Pc OBJECT IDENTIFIER ::= { cevModuleIEType 69 }
cevModuleIem30004Pc4TC OBJECT IDENTIFIER ::= { cevModuleIEType 70 }
cevModule1783MX04E OBJECT IDENTIFIER ::= { cevModuleIEType 71 }
cevModule1783MX04T04E OBJECT IDENTIFIER ::= { cevModuleIEType 72 }
cevModuleIE20008T67B OBJECT IDENTIFIER ::= { cevModuleIEType 79 }
cevModuleIE200016T67B OBJECT IDENTIFIER ::= { cevModuleIEType 80 }
cevModuleIE200024T67B OBJECT IDENTIFIER ::= { cevModuleIEType 81 }
cevModuleIE20008T67PGE OBJECT IDENTIFIER ::= { cevModuleIEType 82 }
cevModuleIE200016T67PGE OBJECT IDENTIFIER ::= { cevModuleIEType 83 }
cevModuleRAIE1783ZMS8TA OBJECT IDENTIFIER ::= { cevModuleIEType 84 }
cevModuleRAIE1783ZMS16TA OBJECT IDENTIFIER ::= { cevModuleIEType 85 }
cevModuleRAIE1783ZMS24TA OBJECT IDENTIFIER ::= { cevModuleIEType 86 }
cevModuleRAIE1783ZMS4T4E2TGP OBJECT IDENTIFIER ::= { cevModuleIEType 87 }
cevModuleRAIE1783ZMS8T8E2TGP OBJECT IDENTIFIER ::= { cevModuleIEType 88 }
cevModuleIE2000U4STSG OBJECT IDENTIFIER ::= { cevModuleIEType 89 }
cevModuleIE2000U16TCGP OBJECT IDENTIFIER ::= { cevModuleIEType 90 }
cevModuleIE2000U4TG OBJECT IDENTIFIER ::= { cevModuleIEType 91 }
cevModuleIE2000U4TSG OBJECT IDENTIFIER ::= { cevModuleIEType 92 }
cevModuleIE2000U8TCG OBJECT IDENTIFIER ::= { cevModuleIEType 93 }
cevModuleIE2000U16TCG OBJECT IDENTIFIER ::= { cevModuleIEType 94 }
cevModuleIE2000U16TCGX OBJECT IDENTIFIER ::= { cevModuleIEType 95 }
cevModuleIE40004TC4GE OBJECT IDENTIFIER ::= { cevModuleIEType 96 }
cevModuleIE40008T4GE OBJECT IDENTIFIER ::= { cevModuleIEType 97 }
cevModuleIE40008S4GE OBJECT IDENTIFIER ::= { cevModuleIEType 98 }
cevModuleIE40004T4P4GE OBJECT IDENTIFIER ::= { cevModuleIEType 99 }
cevModuleIE400016T4GE OBJECT IDENTIFIER ::= { cevModuleIEType 100 }
cevModuleIE40004S8P4GE OBJECT IDENTIFIER ::= { cevModuleIEType 101 }
cevModuleIE40008GT4GE OBJECT IDENTIFIER ::= { cevModuleIEType 102 }
cevModuleIE40008GS4GE OBJECT IDENTIFIER ::= { cevModuleIEType 103 }
cevModuleIE40004GC4GP4GE OBJECT IDENTIFIER ::= { cevModuleIEType 104 }
cevModuleIE400016GT4GE OBJECT IDENTIFIER ::= { cevModuleIEType 105 }
cevModuleIE40008GT8GP4GE OBJECT IDENTIFIER ::= { cevModuleIEType 106 }
cevModuleIE40004GS8GP4GE OBJECT IDENTIFIER ::= { cevModuleIEType 107 }
cevModuleRAIE1783HMS4C4CGN OBJECT IDENTIFIER ::= { cevModuleIEType 108 }
cevModuleRAIE1783HMS8T4CGN OBJECT IDENTIFIER ::= { cevModuleIEType 109 }
cevModuleRAIE1783HMS8S4CGN OBJECT IDENTIFIER ::= { cevModuleIEType 110 }
cevModuleRAIE1783HMS4T4E4CGN OBJECT IDENTIFIER ::= { cevModuleIEType 111 }
cevModuleRAIE1783HMS16T4CGN OBJECT IDENTIFIER ::= { cevModuleIEType 112 }
cevModuleRAIE1783HMS4S8E4CGN OBJECT IDENTIFIER ::= { cevModuleIEType 113 }
cevModuleRAIE1783HMS8TG4CGN OBJECT IDENTIFIER ::= { cevModuleIEType 114 }
cevModuleRAIE1783HMS8SG4CGN OBJECT IDENTIFIER ::= { cevModuleIEType 115 }
cevModuleRAIE1783HMS4EG8CGN OBJECT IDENTIFIER ::= { cevModuleIEType 116 }
cevModuleRAIE1783HMS16TG4CGN OBJECT IDENTIFIER ::= { cevModuleIEType 117 }
cevModuleRAIE1783HMS8TG8EG4CGN OBJECT IDENTIFIER ::= { cevModuleIEType 118 }
cevModuleRAIE1783HMS4SG8EG4CGN OBJECT IDENTIFIER ::= { cevModuleIEType 119 }
cevModuleRAIE1783HMS8TG4CGR OBJECT IDENTIFIER ::= { cevModuleIEType 120 }
cevModuleRAIE1783HMS8SG4CGR OBJECT IDENTIFIER ::= { cevModuleIEType 121 }
cevModuleRAIE1783HMS4EG8CGR OBJECT IDENTIFIER ::= { cevModuleIEType 122 }
cevModuleRAIE1783HMS16TG4CGR OBJECT IDENTIFIER ::= { cevModuleIEType 123 }
cevModuleRAIE1783HMS8TG8EG4CGR OBJECT IDENTIFIER ::= { cevModuleIEType 124 }
cevModuleRAIE1783HMS4SG8EG4CGR OBJECT IDENTIFIER ::= { cevModuleIEType 125 }
cevModuleIE500012S12P10G OBJECT IDENTIFIER ::= { cevModuleIEType 126 }
cevModuleRAIE1783IMS28NAC OBJECT IDENTIFIER ::= { cevModuleIEType 127 }
cevModuleRAIE1783IMS28NDC OBJECT IDENTIFIER ::= { cevModuleIEType 128 }
cevModuleRAIE1783IMS28RAC OBJECT IDENTIFIER ::= { cevModuleIEType 129 }
cevModuleRAIE1783IMS28RDC OBJECT IDENTIFIER ::= { cevModuleIEType 130 }
cevModuleIE500016S12P OBJECT IDENTIFIER ::= { cevModuleIEType 131 }
cevModuleIE10004TLM OBJECT IDENTIFIER ::= { cevModuleIEType 132 }
cevModuleIE10006TLM OBJECT IDENTIFIER ::= { cevModuleIEType 133 }
cevModuleIE10004PTSLM OBJECT IDENTIFIER ::= { cevModuleIEType 134 }
cevModuleIE10008PTSLM OBJECT IDENTIFIER ::= { cevModuleIEType 135 }
cevModuleRAIE1783IMS28GNAC OBJECT IDENTIFIER ::= { cevModuleIEType 136 }
cevModuleRAIE1783IMS28GNDC OBJECT IDENTIFIER ::= { cevModuleIEType 137 }
cevModuleRAIE1783IMS28GRAC OBJECT IDENTIFIER ::= { cevModuleIEType 138 }
cevModuleRAIE1783IMS28GRDC OBJECT IDENTIFIER ::= { cevModuleIEType 139 }
cevModuleIE40104S24P OBJECT IDENTIFIER ::= { cevModuleIEType 142 }
cevModuleIE401016S12P OBJECT IDENTIFIER ::= { cevModuleIEType 143 }
cevModuleN5KType OBJECT IDENTIFIER ::= { cevModule 72 }
cevN5kM1008     OBJECT IDENTIFIER ::= { cevModuleN5KType 1 }
cevN5KM1404     OBJECT IDENTIFIER ::= { cevModuleN5KType 2 }
cevN5kM1Blnk    OBJECT IDENTIFIER ::= { cevModuleN5KType 3 }
cevN5KM1600     OBJECT IDENTIFIER ::= { cevModuleN5KType 4 }
cevN5kC5020FixedModule OBJECT IDENTIFIER ::= { cevModuleN5KType 5 }
cevN5kC5010FixedModule OBJECT IDENTIFIER ::= { cevModuleN5KType 6 }
cevN5kFabricExtenderConnection OBJECT IDENTIFIER ::= { cevModuleN5KType 7 }
cevN5kC5548pFixedModule OBJECT IDENTIFIER ::= { cevModuleN5KType 10 }
cevN5KN55M16P   OBJECT IDENTIFIER ::= { cevModuleN5KType 11 }
cevN5KN55M8P8FP OBJECT IDENTIFIER ::= { cevModuleN5KType 12 }
cevN5KN55M16UP  OBJECT IDENTIFIER ::= { cevModuleN5KType 13 }
cevN5KN55DL2    OBJECT IDENTIFIER ::= { cevModuleN5KType 14 }
cevN5KN55D160L3 OBJECT IDENTIFIER ::= { cevModuleN5KType 15 }
cevN5KN55M160L3 OBJECT IDENTIFIER ::= { cevModuleN5KType 16 }
cevN5KC5596UpFixedModule OBJECT IDENTIFIER ::= { cevModuleN5KType 17 }
cevN5KN55M16FP  OBJECT IDENTIFIER ::= { cevModuleN5KType 18 }
cevN5kC5548UPFixedModule OBJECT IDENTIFIER ::= { cevModuleN5KType 19 }
cevN5KN55M160L3V2 OBJECT IDENTIFIER ::= { cevModuleN5KType 20 }
cevN5KN55D160L3V2 OBJECT IDENTIFIER ::= { cevModuleN5KType 21 }
cevN5kC5596TFAFixedModule OBJECT IDENTIFIER ::= { cevModuleN5KType 22 }
cevN5KN55M12T   OBJECT IDENTIFIER ::= { cevModuleN5KType 23 }
cevN5KN55M4Q    OBJECT IDENTIFIER ::= { cevModuleN5KType 24 }
cevN5KN56M24UP2Q OBJECT IDENTIFIER ::= { cevModuleN5KType 25 }
cevN5KC56128PFixedModule OBJECT IDENTIFIER ::= { cevModuleN5KType 26 }
cevN5KC5672UPM6Q OBJECT IDENTIFIER ::= { cevModuleN5KType 27 }
cevN5KC5672UPFixedModule OBJECT IDENTIFIER ::= { cevModuleN5KType 28 }
cevN5KC5672UP16GFixedModule OBJECT IDENTIFIER ::= { cevModuleN5KType 29 }
cevN5KN5648M12QFIX OBJECT IDENTIFIER ::= { cevModuleN5KType 30 }
cevN5KN5624M12QFIX OBJECT IDENTIFIER ::= { cevModuleN5KType 31 }
cevN5KN5600M12Q OBJECT IDENTIFIER ::= { cevModuleN5KType 32 }
cevN5KC5648QFixedModule OBJECT IDENTIFIER ::= { cevModuleN5KType 33 }
cevN5KC5624QFixedModule OBJECT IDENTIFIER ::= { cevModuleN5KType 34 }
cevN5KN5696M12Q OBJECT IDENTIFIER ::= { cevModuleN5KType 35 }
cevN5KN5696M4C  OBJECT IDENTIFIER ::= { cevModuleN5KType 36 }
cevN5KN5696M20UP OBJECT IDENTIFIER ::= { cevModuleN5KType 37 }
cevN5KC5696QFixedModule OBJECT IDENTIFIER ::= { cevModuleN5KType 38 }
cevN5KN5600M16UP6Q OBJECT IDENTIFIER ::= { cevModuleN5KType 39 }
cevN5KN560072UP16GFC OBJECT IDENTIFIER ::= { cevModuleN5KType 40 }
cevN5KN560072UP16GFCM6Q OBJECT IDENTIFIER ::= { cevModuleN5KType 41 }
cevN5KN560072UP16GFCFC OBJECT IDENTIFIER ::= { cevModuleN5KType 42 }
cevModuleASA5505Type OBJECT IDENTIFIER ::= { cevModule 73 }
cevMASA5505IsmSscIps5K9 OBJECT IDENTIFIER ::= { cevModuleASA5505Type 1 }
cevModuleASR9KType OBJECT IDENTIFIER ::= { cevModule 74 }
cevModuleA9K8x10GEB OBJECT IDENTIFIER ::= { cevModuleASR9KType 1 }
cevModuleA9K8x10GEE OBJECT IDENTIFIER ::= { cevModuleASR9KType 2 }
cevModuleA9K4x10GEB OBJECT IDENTIFIER ::= { cevModuleASR9KType 3 }
cevModuleA9K4x10GEE OBJECT IDENTIFIER ::= { cevModuleASR9KType 4 }
cevModuleA9K40x1GEB OBJECT IDENTIFIER ::= { cevModuleASR9KType 5 }
cevModuleA9K40x1GEE OBJECT IDENTIFIER ::= { cevModuleASR9KType 6 }
cevModuleA9KRSP OBJECT IDENTIFIER ::= { cevModuleASR9KType 7 }
cevModuleA9KRSP4G OBJECT IDENTIFIER ::= { cevModuleASR9KType 8 }
cevModuleASR9KHost OBJECT IDENTIFIER ::= { cevModuleASR9KType 9 }
cevModuleA9K2x10GE20x1GEB OBJECT IDENTIFIER ::= { cevModuleASR9KType 10 }
cevModuleA9K8x10GELRB OBJECT IDENTIFIER ::= { cevModuleASR9KType 11 }
cevModuleA9K8x10GELRE OBJECT IDENTIFIER ::= { cevModuleASR9KType 12 }
cevModuleA9K40x1GEL OBJECT IDENTIFIER ::= { cevModuleASR9KType 13 }
cevModuleA9K4x10GEL OBJECT IDENTIFIER ::= { cevModuleASR9KType 14 }
cevModuleA9K8x10GEL OBJECT IDENTIFIER ::= { cevModuleASR9KType 15 }
cevModuleA9K2x10GE20x1GEE OBJECT IDENTIFIER ::= { cevModuleASR9KType 16 }
cevModuleA9KISM100 OBJECT IDENTIFIER ::= { cevModuleASR9KType 17 }
cevModuleA9KQFPSIP OBJECT IDENTIFIER ::= { cevModuleASR9KType 18 }
cevModuleA9KRSP8G OBJECT IDENTIFIER ::= { cevModuleASR9KType 19 }
cevModuleA9K2x10GE20x1GEL OBJECT IDENTIFIER ::= { cevModuleASR9KType 20 }
cevModuleA9K8x10GELRL OBJECT IDENTIFIER ::= { cevModuleASR9KType 21 }
cevModuleA9K16x10GEOVB OBJECT IDENTIFIER ::= { cevModuleASR9KType 22 }
cevModuleA9KQFPSIP500 OBJECT IDENTIFIER ::= { cevModuleASR9KType 23 }
cevModuleA9KServiceAcceleratorModule OBJECT IDENTIFIER ::= { cevModuleASR9KType 24 }
cevModuleA9KRsp440Se OBJECT IDENTIFIER ::= { cevModuleASR9KType 25 }
cevModuleA9KRsp440Tr OBJECT IDENTIFIER ::= { cevModuleASR9KType 26 }
cevModuleA9K1X100GeSe OBJECT IDENTIFIER ::= { cevModuleASR9KType 27 }
cevModuleA9K1X100GeTr OBJECT IDENTIFIER ::= { cevModuleASR9KType 28 }
cevModuleA9K36X10GeSe OBJECT IDENTIFIER ::= { cevModuleASR9KType 29 }
cevModuleA9K36X10GeTr OBJECT IDENTIFIER ::= { cevModuleASR9KType 30 }
cevModuleA9K2X100GeSe OBJECT IDENTIFIER ::= { cevModuleASR9KType 31 }
cevModuleA9K2X100GeTr OBJECT IDENTIFIER ::= { cevModuleASR9KType 32 }
cevModuleA9K24X10GeSe OBJECT IDENTIFIER ::= { cevModuleASR9KType 33 }
cevModuleA9K24X10GeTr OBJECT IDENTIFIER ::= { cevModuleASR9KType 34 }
cevModuleA9KMOD80SE OBJECT IDENTIFIER ::= { cevModuleASR9KType 35 }
cevModuleA9KMOD80TR OBJECT IDENTIFIER ::= { cevModuleASR9KType 36 }
cevModuleA9KMOD160SE OBJECT IDENTIFIER ::= { cevModuleASR9KType 37 }
cevModuleA9KMOD160TR OBJECT IDENTIFIER ::= { cevModuleASR9KType 38 }
cevModuleA9K9922RpSe OBJECT IDENTIFIER ::= { cevModuleASR9KType 39 }
cevModuleA9K9922RpTr OBJECT IDENTIFIER ::= { cevModuleASR9KType 40 }
cevModuleA9K9922Sfc110 OBJECT IDENTIFIER ::= { cevModuleASR9KType 41 }
cevModuleA9KVGenericLc OBJECT IDENTIFIER ::= { cevModuleASR9KType 42 }
cevModuleA9K9912SFC110 OBJECT IDENTIFIER ::= { cevModuleASR9KType 43 }
cevModuleA9K9912RpTr OBJECT IDENTIFIER ::= { cevModuleASR9KType 44 }
cevModuleA9K9912RpSe OBJECT IDENTIFIER ::= { cevModuleASR9KType 45 }
cevModuleA9KMODULEv OBJECT IDENTIFIER ::= { cevModuleASR9KType 46 }
cevModuleA9K9001Lc OBJECT IDENTIFIER ::= { cevModuleASR9KType 47 }
cevModuleA9K9001Rp OBJECT IDENTIFIER ::= { cevModuleASR9KType 48 }
cevModuleA9KSip7008G OBJECT IDENTIFIER ::= { cevModuleASR9KType 49 }
cevModuleA9K9001LcS OBJECT IDENTIFIER ::= { cevModuleASR9KType 53 }
cevModuleA9KVSM500 OBJECT IDENTIFIER ::= { cevModuleASR9KType 54 }
cevModuleA9K40x1GeSe OBJECT IDENTIFIER ::= { cevModuleASR9KType 55 }
cevModuleA9K40x1GeTr OBJECT IDENTIFIER ::= { cevModuleASR9KType 56 }
cevModuleA9K16x1G4x10GeTr OBJECT IDENTIFIER ::= { cevModuleASR9KType 57 }
cevModuleA9K16x1G4x10GeSe OBJECT IDENTIFIER ::= { cevModuleASR9KType 58 }
cevModuleA9K8X100GeLSe OBJECT IDENTIFIER ::= { cevModuleASR9KType 60 }
cevModuleA9KRsp880Se OBJECT IDENTIFIER ::= { cevModuleASR9KType 61 }
cevModuleA9KRsp880Tr OBJECT IDENTIFIER ::= { cevModuleASR9KType 62 }
cevModuleA9K9900Sfc2 OBJECT IDENTIFIER ::= { cevModuleASR9KType 63 }
cevModuleA99RpV2Se OBJECT IDENTIFIER ::= { cevModuleASR9KType 64 }
cevModuleA99RpV2Tr OBJECT IDENTIFIER ::= { cevModuleASR9KType 65 }
cevModuleA9K8X100GeCm OBJECT IDENTIFIER ::= { cevModuleASR9KType 66 }
cevModuleA998X100GeCm OBJECT IDENTIFIER ::= { cevModuleASR9KType 67 }
cevModuleA9K8X100GESE OBJECT IDENTIFIER ::= { cevModuleASR9KType 68 }
cevModuleA9K8x100GETR OBJECT IDENTIFIER ::= { cevModuleASR9KType 69 }
cevModuleA9K4X100GESE OBJECT IDENTIFIER ::= { cevModuleASR9KType 70 }
cevModuleA9K4X100GETR OBJECT IDENTIFIER ::= { cevModuleASR9KType 71 }
cevModuleA9912X100GE OBJECT IDENTIFIER ::= { cevModuleASR9KType 72 }
cevModuleA9912X100GECM OBJECT IDENTIFIER ::= { cevModuleASR9KType 73 }
cevModuleA99Rsp16G OBJECT IDENTIFIER ::= { cevModuleASR9KType 75 }
cevModuleA99Rsp32G OBJECT IDENTIFIER ::= { cevModuleASR9KType 76 }
cevModuleA9K9910SfcS OBJECT IDENTIFIER ::= { cevModuleASR9KType 77 }
cevModuleA9KMOD400TR OBJECT IDENTIFIER ::= { cevModuleASR9KType 78 }
cevModuleA9KMOD400SE OBJECT IDENTIFIER ::= { cevModuleASR9KType 79 }
cevModuleA9KMOD200SE OBJECT IDENTIFIER ::= { cevModuleASR9KType 80 }
cevModuleA9KMOD200TR OBJECT IDENTIFIER ::= { cevModuleASR9KType 81 }
cevModuleA998X100GESE OBJECT IDENTIFIER ::= { cevModuleASR9KType 82 }
cevModuleA998X100GETR OBJECT IDENTIFIER ::= { cevModuleASR9KType 83 }
cevModuleA994X100GESE OBJECT IDENTIFIER ::= { cevModuleASR9KType 84 }
cevModuleA994X100GETR OBJECT IDENTIFIER ::= { cevModuleASR9KType 85 }
cevModuleA99400GDWDMTR OBJECT IDENTIFIER ::= { cevModuleASR9KType 86 }
cevModuleA99MOD400TR OBJECT IDENTIFIER ::= { cevModuleASR9KType 87 }
cevModuleA99MOD400SE OBJECT IDENTIFIER ::= { cevModuleASR9KType 88 }
cevModuleA99MOD200TR OBJECT IDENTIFIER ::= { cevModuleASR9KType 89 }
cevModuleA99MOD200SE OBJECT IDENTIFIER ::= { cevModuleASR9KType 90 }
cevModuleA998X100GELSE OBJECT IDENTIFIER ::= { cevModuleASR9KType 91 }
cevModuleA9KMOD400CM OBJECT IDENTIFIER ::= { cevModuleASR9KType 98 }
cevModuleA9KMOD200CM OBJECT IDENTIFIER ::= { cevModuleASR9KType 99 }
cevModuleASR14KType OBJECT IDENTIFIER ::= { cevModule 75 }
cevModuleASR14K20x1GeFl OBJECT IDENTIFIER ::= { cevModuleASR14KType 1 }
cevModuleASR14K42x1GE OBJECT IDENTIFIER ::= { cevModuleASR14KType 2 }
cevModuleASR14K4x10GE OBJECT IDENTIFIER ::= { cevModuleASR14KType 3 }
cevModuleASR14K4FabricCard OBJECT IDENTIFIER ::= { cevModuleASR14KType 4 }
cevModuleASR14K8FabricCard OBJECT IDENTIFIER ::= { cevModuleASR14KType 5 }
cevModuleASR14KRP OBJECT IDENTIFIER ::= { cevModuleASR14KType 6 }
cevModuleASR14KFP40 OBJECT IDENTIFIER ::= { cevModuleASR14KType 7 }
cevModuleASR14KFPE OBJECT IDENTIFIER ::= { cevModuleASR14KType 8 }
cevModuleASR14K2x10WLFL OBJECT IDENTIFIER ::= { cevModuleASR14KType 9 }
cevModuleSFPPlusS OBJECT IDENTIFIER ::= { cevModule 76 }
cevSFP10GLR     OBJECT IDENTIFIER ::= { cevModuleSFPPlusS 1 }
cevSFP10GLRM    OBJECT IDENTIFIER ::= { cevModuleSFPPlusS 2 }
cevSFP10GSR     OBJECT IDENTIFIER ::= { cevModuleSFPPlusS 3 }
cevSFP10GUSR    OBJECT IDENTIFIER ::= { cevModuleSFPPlusS 4 }
cevSFP10GER     OBJECT IDENTIFIER ::= { cevModuleSFPPlusS 5 }
cevSFP10GLRMSM  OBJECT IDENTIFIER ::= { cevModuleSFPPlusS 7 }
cevSFP10GZR     OBJECT IDENTIFIER ::= { cevModuleSFPPlusS 8 }
cevSFP10GCU1M   OBJECT IDENTIFIER ::= { cevModuleSFPPlusS 9 }
cevSFP10GCU3M   OBJECT IDENTIFIER ::= { cevModuleSFPPlusS 10 }
cevSFP10GCU5M   OBJECT IDENTIFIER ::= { cevModuleSFPPlusS 11 }
cevSFP10GACU7M  OBJECT IDENTIFIER ::= { cevModuleSFPPlusS 12 }
cevSFPH10GbAcu10m OBJECT IDENTIFIER ::= { cevModuleSFPPlusS 13 }
cevSFPOe8541    OBJECT IDENTIFIER ::= { cevModuleSFPPlusS 14 }
cevSFPOe7571    OBJECT IDENTIFIER ::= { cevModuleSFPPlusS 15 }
cevSFPOe7541    OBJECT IDENTIFIER ::= { cevModuleSFPPlusS 16 }
cevSFPOe694     OBJECT IDENTIFIER ::= { cevModuleSFPPlusS 17 }
cevSFPOe594     OBJECT IDENTIFIER ::= { cevModuleSFPPlusS 18 }
cevSFPOe294     OBJECT IDENTIFIER ::= { cevModuleSFPPlusS 19 }
cevSFPDwdmSfp10g3190 OBJECT IDENTIFIER ::= { cevModuleSFPPlusS 20 }
cevSFPDwdmSfp10g3112 OBJECT IDENTIFIER ::= { cevModuleSFPPlusS 21 }
cevSFPDwdmSfp10g3033 OBJECT IDENTIFIER ::= { cevModuleSFPPlusS 22 }
cevSFPDwdmSfp10g3582 OBJECT IDENTIFIER ::= { cevModuleSFPPlusS 23 }
cevSFPDwdmSfp10g3504 OBJECT IDENTIFIER ::= { cevModuleSFPPlusS 24 }
cevSFPDwdmSfp10g3425 OBJECT IDENTIFIER ::= { cevModuleSFPPlusS 25 }
cevSFPDwdmSfp10g3347 OBJECT IDENTIFIER ::= { cevModuleSFPPlusS 26 }
cevSFPDwdmSfp10g3268 OBJECT IDENTIFIER ::= { cevModuleSFPPlusS 27 }
cevSFPDwdmSfp10g3977 OBJECT IDENTIFIER ::= { cevModuleSFPPlusS 28 }
cevSFPDwdmSfp10g3898 OBJECT IDENTIFIER ::= { cevModuleSFPPlusS 29 }
cevSFPDwdmSfp10g3819 OBJECT IDENTIFIER ::= { cevModuleSFPPlusS 30 }
cevSFPDwdmSfp10g3740 OBJECT IDENTIFIER ::= { cevModuleSFPPlusS 31 }
cevSFPDwdmSfp10g3661 OBJECT IDENTIFIER ::= { cevModuleSFPPlusS 32 }
cevSFPDwdmSfp10g4373 OBJECT IDENTIFIER ::= { cevModuleSFPPlusS 33 }
cevSFPDwdmSfp10g4294 OBJECT IDENTIFIER ::= { cevModuleSFPPlusS 34 }
cevSFPDwdmSfp10g4214 OBJECT IDENTIFIER ::= { cevModuleSFPPlusS 35 }
cevSFPDwdmSfp10g4135 OBJECT IDENTIFIER ::= { cevModuleSFPPlusS 36 }
cevSFPDwdmSfp10g4056 OBJECT IDENTIFIER ::= { cevModuleSFPPlusS 37 }
cevSFPDwdmSfp10g4772 OBJECT IDENTIFIER ::= { cevModuleSFPPlusS 38 }
cevSFPDwdmSfp10g4692 OBJECT IDENTIFIER ::= { cevModuleSFPPlusS 39 }
cevSFPDwdmSfp10g4612 OBJECT IDENTIFIER ::= { cevModuleSFPPlusS 40 }
cevSFPDwdmSfp10g4532 OBJECT IDENTIFIER ::= { cevModuleSFPPlusS 41 }
cevSFPDwdmSfp10g5172 OBJECT IDENTIFIER ::= { cevModuleSFPPlusS 42 }
cevSFPDwdmSfp10g5092 OBJECT IDENTIFIER ::= { cevModuleSFPPlusS 43 }
cevSFPDwdmSfp10g5012 OBJECT IDENTIFIER ::= { cevModuleSFPPlusS 44 }
cevSFPDwdmSfp10g4932 OBJECT IDENTIFIER ::= { cevModuleSFPPlusS 45 }
cevSFPDwdmSfp10g4851 OBJECT IDENTIFIER ::= { cevModuleSFPPlusS 46 }
cevSFPDwdmSfp10g5575 OBJECT IDENTIFIER ::= { cevModuleSFPPlusS 47 }
cevSFPDwdmSfp10g5494 OBJECT IDENTIFIER ::= { cevModuleSFPPlusS 48 }
cevSFPDwdmSfp10g5413 OBJECT IDENTIFIER ::= { cevModuleSFPPlusS 49 }
cevSFPDwdmSfp10g5333 OBJECT IDENTIFIER ::= { cevModuleSFPPlusS 50 }
cevSFPDwdmSfp10g5252 OBJECT IDENTIFIER ::= { cevModuleSFPPlusS 51 }
cevSFPDwdmSfp10g5979 OBJECT IDENTIFIER ::= { cevModuleSFPPlusS 52 }
cevSFPDwdmSfp10g5898 OBJECT IDENTIFIER ::= { cevModuleSFPPlusS 53 }
cevSFPDwdmSfp10g5817 OBJECT IDENTIFIER ::= { cevModuleSFPPlusS 54 }
cevSFPDwdmSfp10g5736 OBJECT IDENTIFIER ::= { cevModuleSFPPlusS 55 }
cevSFPDwdmSfp10g5655 OBJECT IDENTIFIER ::= { cevModuleSFPPlusS 56 }
cevSFPDwdmSfp10g6061 OBJECT IDENTIFIER ::= { cevModuleSFPPlusS 57 }
cevSFPDwdmSfp10g6141 OBJECT IDENTIFIER ::= { cevModuleSFPPlusS 58 }
cevSFPDwdmSfp10g4453 OBJECT IDENTIFIER ::= { cevModuleSFPPlusS 59 }
cevSFPFET10G    OBJECT IDENTIFIER ::= { cevModuleSFPPlusS 60 }
cevSFPSC10GTDwdmC OBJECT IDENTIFIER ::= { cevModuleSFPPlusS 61 }
cevSFPSC10GSR   OBJECT IDENTIFIER ::= { cevModuleSFPPlusS 62 }
cevSFPSC10GER   OBJECT IDENTIFIER ::= { cevModuleSFPPlusS 63 }
cevSFPSC10GLR   OBJECT IDENTIFIER ::= { cevModuleSFPPlusS 64 }
cevSFPSC10GZR   OBJECT IDENTIFIER ::= { cevModuleSFPPlusS 65 }
cevSFPSE10GLR   OBJECT IDENTIFIER ::= { cevModuleSFPPlusS 66 }
cevSFPSC10G303  OBJECT IDENTIFIER ::= { cevModuleSFPPlusS 67 }
cevSFPSC10G311  OBJECT IDENTIFIER ::= { cevModuleSFPPlusS 68 }
cevSFPSC10G319  OBJECT IDENTIFIER ::= { cevModuleSFPPlusS 69 }
cevSFPSC10G326  OBJECT IDENTIFIER ::= { cevModuleSFPPlusS 70 }
cevSFPSC10G334  OBJECT IDENTIFIER ::= { cevModuleSFPPlusS 71 }
cevSFPSC10G342  OBJECT IDENTIFIER ::= { cevModuleSFPPlusS 72 }
cevSFPSC10G350  OBJECT IDENTIFIER ::= { cevModuleSFPPlusS 73 }
cevSFPSC10G358  OBJECT IDENTIFIER ::= { cevModuleSFPPlusS 74 }
cevSFPSC10G366  OBJECT IDENTIFIER ::= { cevModuleSFPPlusS 75 }
cevSFPSC10G374  OBJECT IDENTIFIER ::= { cevModuleSFPPlusS 76 }
cevSFPSC10G381  OBJECT IDENTIFIER ::= { cevModuleSFPPlusS 77 }
cevSFPSC10G389  OBJECT IDENTIFIER ::= { cevModuleSFPPlusS 78 }
cevSFPSC10G397  OBJECT IDENTIFIER ::= { cevModuleSFPPlusS 79 }
cevSFPSC10G405  OBJECT IDENTIFIER ::= { cevModuleSFPPlusS 80 }
cevSFPSC10G415  OBJECT IDENTIFIER ::= { cevModuleSFPPlusS 81 }
cevSFPSC10G421  OBJECT IDENTIFIER ::= { cevModuleSFPPlusS 82 }
cevSFPSC10G429  OBJECT IDENTIFIER ::= { cevModuleSFPPlusS 83 }
cevSFPSC10G437  OBJECT IDENTIFIER ::= { cevModuleSFPPlusS 84 }
cevSFPSC10G445  OBJECT IDENTIFIER ::= { cevModuleSFPPlusS 85 }
cevSFPSC10G453  OBJECT IDENTIFIER ::= { cevModuleSFPPlusS 86 }
cevSFPSC10G461  OBJECT IDENTIFIER ::= { cevModuleSFPPlusS 87 }
cevSFPSC10G469  OBJECT IDENTIFIER ::= { cevModuleSFPPlusS 88 }
cevSFPSC10G477  OBJECT IDENTIFIER ::= { cevModuleSFPPlusS 89 }
cevSFPSC10G485  OBJECT IDENTIFIER ::= { cevModuleSFPPlusS 90 }
cevSFPSC10G493  OBJECT IDENTIFIER ::= { cevModuleSFPPlusS 91 }
cevSFPSC10G501  OBJECT IDENTIFIER ::= { cevModuleSFPPlusS 92 }
cevSFPSC10G509  OBJECT IDENTIFIER ::= { cevModuleSFPPlusS 93 }
cevSFPSC10G517  OBJECT IDENTIFIER ::= { cevModuleSFPPlusS 94 }
cevSFPSC10G525  OBJECT IDENTIFIER ::= { cevModuleSFPPlusS 95 }
cevSFPSC10G533  OBJECT IDENTIFIER ::= { cevModuleSFPPlusS 96 }
cevSFPSC10G541  OBJECT IDENTIFIER ::= { cevModuleSFPPlusS 97 }
cevSFPSC10G549  OBJECT IDENTIFIER ::= { cevModuleSFPPlusS 98 }
cevSFPSC10G557  OBJECT IDENTIFIER ::= { cevModuleSFPPlusS 99 }
cevSFPSC10G565  OBJECT IDENTIFIER ::= { cevModuleSFPPlusS 100 }
cevSFPSC10G573  OBJECT IDENTIFIER ::= { cevModuleSFPPlusS 101 }
cevSFPSC10G581  OBJECT IDENTIFIER ::= { cevModuleSFPPlusS 102 }
cevSFPSC10G589  OBJECT IDENTIFIER ::= { cevModuleSFPPlusS 103 }
cevSFPSC10G597  OBJECT IDENTIFIER ::= { cevModuleSFPPlusS 104 }
cevSFPSC10G606  OBJECT IDENTIFIER ::= { cevModuleSFPPlusS 105 }
cevSFPSC10G614  OBJECT IDENTIFIER ::= { cevModuleSFPPlusS 106 }
cevSFPPONSSI2GI1 OBJECT IDENTIFIER ::= { cevModuleSFPPlusS 114 }
cevSFPPONSSC10GEP618 OBJECT IDENTIFIER ::= { cevModuleSFPPlusS 115 }
cevSFPPONSSC10GEP614 OBJECT IDENTIFIER ::= { cevModuleSFPPlusS 116 }
cevSFPPONSSC10GEP610 OBJECT IDENTIFIER ::= { cevModuleSFPPlusS 117 }
cevSFPPONSSC10GEP606 OBJECT IDENTIFIER ::= { cevModuleSFPPlusS 118 }
cevSFPPONSSC10GEP602 OBJECT IDENTIFIER ::= { cevModuleSFPPlusS 119 }
cevSFPPONSSC10GEP597 OBJECT IDENTIFIER ::= { cevModuleSFPPlusS 120 }
cevSFPPONSSC10GEP593 OBJECT IDENTIFIER ::= { cevModuleSFPPlusS 121 }
cevSFPPONSSC10GEP589 OBJECT IDENTIFIER ::= { cevModuleSFPPlusS 122 }
cevSFPPONSSC10GEP585 OBJECT IDENTIFIER ::= { cevModuleSFPPlusS 123 }
cevSFPPONSSC10GEP581 OBJECT IDENTIFIER ::= { cevModuleSFPPlusS 124 }
cevSFPPONSSC10GEP577 OBJECT IDENTIFIER ::= { cevModuleSFPPlusS 125 }
cevSFPPONSSC10GEP573 OBJECT IDENTIFIER ::= { cevModuleSFPPlusS 126 }
cevSFPPONSSC10GEP569 OBJECT IDENTIFIER ::= { cevModuleSFPPlusS 127 }
cevSFPPONSSC10GEP565 OBJECT IDENTIFIER ::= { cevModuleSFPPlusS 128 }
cevSFPPONSSC10GEP561 OBJECT IDENTIFIER ::= { cevModuleSFPPlusS 129 }
cevSFPPONSSC10GEP557 OBJECT IDENTIFIER ::= { cevModuleSFPPlusS 130 }
cevSFPPONSSC10GEP553 OBJECT IDENTIFIER ::= { cevModuleSFPPlusS 131 }
cevSFPPONSSC10GEP549 OBJECT IDENTIFIER ::= { cevModuleSFPPlusS 132 }
cevSFPPONSSC10GEP545 OBJECT IDENTIFIER ::= { cevModuleSFPPlusS 133 }
cevSFPPONSSC10GEP541 OBJECT IDENTIFIER ::= { cevModuleSFPPlusS 134 }
cevSFPPONSSC10GEP537 OBJECT IDENTIFIER ::= { cevModuleSFPPlusS 135 }
cevSFPPONSSC10GEP533 OBJECT IDENTIFIER ::= { cevModuleSFPPlusS 136 }
cevSFPPONSSC10GEP529 OBJECT IDENTIFIER ::= { cevModuleSFPPlusS 137 }
cevSFPPONSSC10GEP525 OBJECT IDENTIFIER ::= { cevModuleSFPPlusS 138 }
cevSFPPONSSC10GEP521 OBJECT IDENTIFIER ::= { cevModuleSFPPlusS 139 }
cevSFPPONSSC10GEP517 OBJECT IDENTIFIER ::= { cevModuleSFPPlusS 140 }
cevSFPPONSSC10GEP513 OBJECT IDENTIFIER ::= { cevModuleSFPPlusS 141 }
cevSFPPONSSC10GEP509 OBJECT IDENTIFIER ::= { cevModuleSFPPlusS 142 }
cevSFPPONSSC10GEP505 OBJECT IDENTIFIER ::= { cevModuleSFPPlusS 143 }
cevSFPPONSSC10GEP501 OBJECT IDENTIFIER ::= { cevModuleSFPPlusS 144 }
cevSFPPONSSC10GEP497 OBJECT IDENTIFIER ::= { cevModuleSFPPlusS 145 }
cevSFPPONSSC10GEP493 OBJECT IDENTIFIER ::= { cevModuleSFPPlusS 146 }
cevSFPPONSSC10GEP489 OBJECT IDENTIFIER ::= { cevModuleSFPPlusS 147 }
cevSFPPONSSC10GEP485 OBJECT IDENTIFIER ::= { cevModuleSFPPlusS 148 }
cevSFPPONSSC10GEP481 OBJECT IDENTIFIER ::= { cevModuleSFPPlusS 149 }
cevSFPPONSSC10GEP477 OBJECT IDENTIFIER ::= { cevModuleSFPPlusS 150 }
cevSFPPONSSC10GEP473 OBJECT IDENTIFIER ::= { cevModuleSFPPlusS 151 }
cevSFPPONSSC10GEP469 OBJECT IDENTIFIER ::= { cevModuleSFPPlusS 152 }
cevSFPPONSSC10GEP465 OBJECT IDENTIFIER ::= { cevModuleSFPPlusS 153 }
cevSFPPONSSC10GEP461 OBJECT IDENTIFIER ::= { cevModuleSFPPlusS 154 }
cevSFPPONSSC10GEP457 OBJECT IDENTIFIER ::= { cevModuleSFPPlusS 155 }
cevSFPPONSSC10GEP453 OBJECT IDENTIFIER ::= { cevModuleSFPPlusS 156 }
cevSFPPONSSC10GEP449 OBJECT IDENTIFIER ::= { cevModuleSFPPlusS 157 }
cevSFPPONSSC10GEP445 OBJECT IDENTIFIER ::= { cevModuleSFPPlusS 158 }
cevSFPPONSSC10GEP441 OBJECT IDENTIFIER ::= { cevModuleSFPPlusS 159 }
cevSFPPONSSC10GEP437 OBJECT IDENTIFIER ::= { cevModuleSFPPlusS 160 }
cevSFPPONSSC10GEP433 OBJECT IDENTIFIER ::= { cevModuleSFPPlusS 161 }
cevSFPPONSSC10GEP429 OBJECT IDENTIFIER ::= { cevModuleSFPPlusS 162 }
cevSFPPONSSC10GEP425 OBJECT IDENTIFIER ::= { cevModuleSFPPlusS 163 }
cevSFPPONSSC10GEP421 OBJECT IDENTIFIER ::= { cevModuleSFPPlusS 164 }
cevSFPPONSSC10GEP417 OBJECT IDENTIFIER ::= { cevModuleSFPPlusS 165 }
cevSFPPONSSC10GEP413 OBJECT IDENTIFIER ::= { cevModuleSFPPlusS 166 }
cevSFPPONSSC10GEP409 OBJECT IDENTIFIER ::= { cevModuleSFPPlusS 167 }
cevSFPPONSSC10GEP405 OBJECT IDENTIFIER ::= { cevModuleSFPPlusS 168 }
cevSFPPONSSC10GEP401 OBJECT IDENTIFIER ::= { cevModuleSFPPlusS 169 }
cevSFPPONSSC10GEP397 OBJECT IDENTIFIER ::= { cevModuleSFPPlusS 170 }
cevSFPPONSSC10GEP393 OBJECT IDENTIFIER ::= { cevModuleSFPPlusS 171 }
cevSFPPONSSC10GEP389 OBJECT IDENTIFIER ::= { cevModuleSFPPlusS 172 }
cevSFPPONSSC10GEP385 OBJECT IDENTIFIER ::= { cevModuleSFPPlusS 173 }
cevSFPPONSSC10GEP381 OBJECT IDENTIFIER ::= { cevModuleSFPPlusS 174 }
cevSFPPONSSC10GEP377 OBJECT IDENTIFIER ::= { cevModuleSFPPlusS 175 }
cevSFPPONSSC10GEP374 OBJECT IDENTIFIER ::= { cevModuleSFPPlusS 176 }
cevSFPPONSSC10GEP370 OBJECT IDENTIFIER ::= { cevModuleSFPPlusS 177 }
cevSFPPONSSC10GEP366 OBJECT IDENTIFIER ::= { cevModuleSFPPlusS 178 }
cevSFPPONSSC10GEP362 OBJECT IDENTIFIER ::= { cevModuleSFPPlusS 179 }
cevSFPPONSSC10GEP358 OBJECT IDENTIFIER ::= { cevModuleSFPPlusS 180 }
cevSFPPONSSC10GEP354 OBJECT IDENTIFIER ::= { cevModuleSFPPlusS 181 }
cevSFPPONSSC10GEP350 OBJECT IDENTIFIER ::= { cevModuleSFPPlusS 182 }
cevSFPPONSSC10GEP346 OBJECT IDENTIFIER ::= { cevModuleSFPPlusS 183 }
cevSFPPONSSC10GEP342 OBJECT IDENTIFIER ::= { cevModuleSFPPlusS 184 }
cevSFPPONSSC10GEP338 OBJECT IDENTIFIER ::= { cevModuleSFPPlusS 185 }
cevSFPPONSSC10GEP334 OBJECT IDENTIFIER ::= { cevModuleSFPPlusS 186 }
cevSFPPONSSC10GEP330 OBJECT IDENTIFIER ::= { cevModuleSFPPlusS 187 }
cevSFPPONSSC10GEP326 OBJECT IDENTIFIER ::= { cevModuleSFPPlusS 188 }
cevSFPPONSSC10GEP322 OBJECT IDENTIFIER ::= { cevModuleSFPPlusS 189 }
cevSFPPONSSC10GEP319 OBJECT IDENTIFIER ::= { cevModuleSFPPlusS 190 }
cevSFPPONSSC10GEP315 OBJECT IDENTIFIER ::= { cevModuleSFPPlusS 191 }
cevSFPPONSSC10GEP311 OBJECT IDENTIFIER ::= { cevModuleSFPPlusS 192 }
cevSFPPONSSC10GEP307 OBJECT IDENTIFIER ::= { cevModuleSFPPlusS 193 }
cevSFPPONSSC10GEP303 OBJECT IDENTIFIER ::= { cevModuleSFPPlusS 194 }
cevSFPPONSSC10GC OBJECT IDENTIFIER ::= { cevModuleSFPPlusS 195 }
cevSFPCwdmSfp10g1610 OBJECT IDENTIFIER ::= { cevModuleSFPPlusS 196 }
cevSFPCwdmSfp10g1590 OBJECT IDENTIFIER ::= { cevModuleSFPPlusS 197 }
cevSFPCwdmSfp10g1570 OBJECT IDENTIFIER ::= { cevModuleSFPPlusS 198 }
cevSFPCwdmSfp10g1550 OBJECT IDENTIFIER ::= { cevModuleSFPPlusS 199 }
cevSFPCwdmSfp10g1530 OBJECT IDENTIFIER ::= { cevModuleSFPPlusS 200 }
cevSFPCwdmSfp10g1510 OBJECT IDENTIFIER ::= { cevModuleSFPPlusS 201 }
cevSFPCwdmSfp10g1490 OBJECT IDENTIFIER ::= { cevModuleSFPPlusS 202 }
cevSFPCwdmSfp10g1470 OBJECT IDENTIFIER ::= { cevModuleSFPPlusS 203 }
cevSFP10GBXDI   OBJECT IDENTIFIER ::= { cevModuleSFPPlusS 204 }
cevSFP10GBXUI   OBJECT IDENTIFIER ::= { cevModuleSFPPlusS 205 }
cevSFP10GBX40DI OBJECT IDENTIFIER ::= { cevModuleSFPPlusS 206 }
cevSFP10GBX40UI OBJECT IDENTIFIER ::= { cevModuleSFPPlusS 207 }
cevSFPQsfpPlusLROpticsMod OBJECT IDENTIFIER ::= { cevModuleSFPPlusS 208 }
cevSFPQsfpPlusSROpticsMod OBJECT IDENTIFIER ::= { cevModuleSFPPlusS 209 }
cevSFPPDWDMSFP10GC OBJECT IDENTIFIER ::= { cevModuleSFPPlusS 213 }
cevDWDMSFP10GCS OBJECT IDENTIFIER ::= { cevModuleSFPPlusS 214 }
cevSFP10GZRS    OBJECT IDENTIFIER ::= { cevModuleSFPPlusS 215 }
cevSFP10GERS    OBJECT IDENTIFIER ::= { cevModuleSFPPlusS 216 }
cevSFP10GLRS    OBJECT IDENTIFIER ::= { cevModuleSFPPlusS 217 }
cevSFP10GSRS    OBJECT IDENTIFIER ::= { cevModuleSFPPlusS 218 }
cevSFPONSSIOCVCOP OBJECT IDENTIFIER ::= { cevModuleSFPPlusS 219 }
cevSFPONSSIPDHVCOP OBJECT IDENTIFIER ::= { cevModuleSFPPlusS 220 }
cevDirectAttachCable10Gs OBJECT IDENTIFIER ::= { cevModule 77 }
cevSFPH10GBCU1M OBJECT IDENTIFIER ::= { cevDirectAttachCable10Gs 1 }
cevSFPH10GBCU5M OBJECT IDENTIFIER ::= { cevDirectAttachCable10Gs 2 }
cevSFPH10GBCU3M OBJECT IDENTIFIER ::= { cevDirectAttachCable10Gs 3 }
cevSFPH10GBCU7M OBJECT IDENTIFIER ::= { cevDirectAttachCable10Gs 4 }
cevSFPH10GBACU1M OBJECT IDENTIFIER ::= { cevDirectAttachCable10Gs 9 }
cevSFPH10GBACU3M OBJECT IDENTIFIER ::= { cevDirectAttachCable10Gs 10 }
cevSFPH10GBACU5M OBJECT IDENTIFIER ::= { cevDirectAttachCable10Gs 11 }
cevSFPH10GBACU15M OBJECT IDENTIFIER ::= { cevDirectAttachCable10Gs 12 }
cevSFPH10GBACU10M OBJECT IDENTIFIER ::= { cevDirectAttachCable10Gs 13 }
cevSFPH10GBACU7M OBJECT IDENTIFIER ::= { cevDirectAttachCable10Gs 14 }
cevSFPH10GBCU150CM OBJECT IDENTIFIER ::= { cevDirectAttachCable10Gs 15 }
cevSFPH10GBCU250CM OBJECT IDENTIFIER ::= { cevDirectAttachCable10Gs 16 }
cevSFP10GAOC1M  OBJECT IDENTIFIER ::= { cevDirectAttachCable10Gs 17 }
cevSFP10GAOC2M  OBJECT IDENTIFIER ::= { cevDirectAttachCable10Gs 18 }
cevSFP10GAOC3M  OBJECT IDENTIFIER ::= { cevDirectAttachCable10Gs 19 }
cevSFP10GAOC5M  OBJECT IDENTIFIER ::= { cevDirectAttachCable10Gs 20 }
cevSFP10GAOC7M  OBJECT IDENTIFIER ::= { cevDirectAttachCable10Gs 21 }
cevSFP10GAOC10M OBJECT IDENTIFIER ::= { cevDirectAttachCable10Gs 22 }
cevSFPH10GBCU200CM OBJECT IDENTIFIER ::= { cevDirectAttachCable10Gs 23 }
cevSFPH10GBAOC1M OBJECT IDENTIFIER ::= { cevDirectAttachCable10Gs 24 }
cevSFPH10GBAOC2M OBJECT IDENTIFIER ::= { cevDirectAttachCable10Gs 25 }
cevSFPH10GBAOC3M OBJECT IDENTIFIER ::= { cevDirectAttachCable10Gs 26 }
cevSFPH10GBAOC5M OBJECT IDENTIFIER ::= { cevDirectAttachCable10Gs 27 }
cevSFPH10GBAOC7M OBJECT IDENTIFIER ::= { cevDirectAttachCable10Gs 28 }
cevSFPH10GBAOC10M OBJECT IDENTIFIER ::= { cevDirectAttachCable10Gs 29 }
cevSFPH10GBCU10M OBJECT IDENTIFIER ::= { cevDirectAttachCable10Gs 30 }
cevQSFP4x10GAC7M OBJECT IDENTIFIER ::= { cevDirectAttachCable10Gs 31 }
cevQSFP4x10GAC10M OBJECT IDENTIFIER ::= { cevDirectAttachCable10Gs 32 }
cevModuleN2KType OBJECT IDENTIFIER ::= { cevModule 78 }
cevN2kC2148T1GEFixedModule OBJECT IDENTIFIER ::= { cevModuleN2KType 1 }
cevN2kC2232PP10GEFixedModule OBJECT IDENTIFIER ::= { cevModuleN2KType 2 }
cevN2kC2248TP1GEFixedModule OBJECT IDENTIFIER ::= { cevModuleN2KType 3 }
cevN2kC2224TP1GEFixedModule OBJECT IDENTIFIER ::= { cevModuleN2KType 4 }
cevN2kC2232TT10GEFixedModule OBJECT IDENTIFIER ::= { cevModuleN2KType 5 }
cevN2kC2232TP10GEFixedModule OBJECT IDENTIFIER ::= { cevModuleN2KType 6 }
cevN2kC2248TT1GEFixedModule OBJECT IDENTIFIER ::= { cevModuleN2KType 7 }
cevN2kC2248TPE1GEFixedModule OBJECT IDENTIFIER ::= { cevModuleN2KType 8 }
cevN2kB22HPPFixedModule OBJECT IDENTIFIER ::= { cevModuleN2KType 9 }
cevN2kM2800P    OBJECT IDENTIFIER ::= { cevModuleN2KType 10 }
cevN2kC2232TM10GEFixedModule OBJECT IDENTIFIER ::= { cevModuleN2KType 11 }
cevN2kC2232TME10GEFixedModule OBJECT IDENTIFIER ::= { cevModuleN2KType 12 }
cevN2kC2248PQ10GEFixedModule OBJECT IDENTIFIER ::= { cevModuleN2KType 13 }
cevN2kB22DELLPFixedModule OBJECT IDENTIFIER ::= { cevModuleN2KType 14 }
cevN2kB22FTSPFixedModule OBJECT IDENTIFIER ::= { cevModuleN2KType 15 }
cevN2kB22IBMPFixedModule OBJECT IDENTIFIER ::= { cevModuleN2KType 16 }
cevN2KC2348UPQFixedModule OBJECT IDENTIFIER ::= { cevModuleN2KType 17 }
cevN2KC2348TQFixedModule OBJECT IDENTIFIER ::= { cevModuleN2KType 18 }
cevN2KC2232TQFixedModule OBJECT IDENTIFIER ::= { cevModuleN2KType 19 }
cevN2KC2348TQ10GE OBJECT IDENTIFIER ::= { cevModuleN2KType 20 }
cevModuleN1KVType OBJECT IDENTIFIER ::= { cevModule 79 }
cevN1KVVSM      OBJECT IDENTIFIER ::= { cevModuleN1KVType 1 }
cevN1KVVEM      OBJECT IDENTIFIER ::= { cevModuleN1KVType 2 }
cevN1KVVXLANGateway OBJECT IDENTIFIER ::= { cevModuleN1KVType 3 }
cevN1KVInterCloudExtender OBJECT IDENTIFIER ::= { cevModuleN1KVType 4 }
cevN1KVInterCloudSwitch OBJECT IDENTIFIER ::= { cevModuleN1KVType 5 }
cevModuleUCSType OBJECT IDENTIFIER ::= { cevModule 80 }
cevUCSN10S6100FixedModule OBJECT IDENTIFIER ::= { cevModuleUCSType 1 }
cevUCSN10E0080  OBJECT IDENTIFIER ::= { cevModuleUCSType 2 }
cevUCSN10E0440  OBJECT IDENTIFIER ::= { cevModuleUCSType 3 }
cevUCSN10E0600  OBJECT IDENTIFIER ::= { cevModuleUCSType 4 }
cevUCSFIE16UP   OBJECT IDENTIFIER ::= { cevModuleUCSType 7 }
cevUCSFI6248UPFixedModule OBJECT IDENTIFIER ::= { cevModuleUCSType 8 }
cevUCSFI6296UPFixedModule OBJECT IDENTIFIER ::= { cevModuleUCSType 9 }
cevUCSFIDL2     OBJECT IDENTIFIER ::= { cevModuleUCSType 10 }
cevUCSFIM6324FixedModule OBJECT IDENTIFIER ::= { cevModuleUCSType 171 }
cevUCSFI6332FixedModule OBJECT IDENTIFIER ::= { cevModuleUCSType 172 }
cevUCSIOM2304Q  OBJECT IDENTIFIER ::= { cevModuleUCSType 176 }
cevModuleNexus1010Type OBJECT IDENTIFIER ::= { cevModule 81 }
cevNexus1010VSM OBJECT IDENTIFIER ::= { cevModuleNexus1010Type 1 }
cevNexusN1KVSANam OBJECT IDENTIFIER ::= { cevModuleNexus1010Type 2 }
cevModuleMxeType OBJECT IDENTIFIER ::= { cevModule 82 }
cevMxeNpm       OBJECT IDENTIFIER ::= { cevModuleMxeType 1 }
cevMxeMpm       OBJECT IDENTIFIER ::= { cevModuleMxeType 2 }
cevMxe5600ShelfManager OBJECT IDENTIFIER ::= { cevModuleMxeType 3 }
cevModuleASA5585Type OBJECT IDENTIFIER ::= { cevModule 83 }
cevASA5585Ssp10 OBJECT IDENTIFIER ::= { cevModuleASA5585Type 1 }
cevASA5585Ssp20 OBJECT IDENTIFIER ::= { cevModuleASA5585Type 2 }
cevASA5585Ssp40 OBJECT IDENTIFIER ::= { cevModuleASA5585Type 3 }
cevASA5585Ssp60 OBJECT IDENTIFIER ::= { cevModuleASA5585Type 4 }
cevASA5585IsmSspIps10 OBJECT IDENTIFIER ::= { cevModuleASA5585Type 5 }
cevASA5585IsmSspIps20 OBJECT IDENTIFIER ::= { cevModuleASA5585Type 6 }
cevASA5585IsmSspIps40 OBJECT IDENTIFIER ::= { cevModuleASA5585Type 7 }
cevASA5585IsmSspIps60 OBJECT IDENTIFIER ::= { cevModuleASA5585Type 8 }
cevMASA5585Ssp10K7 OBJECT IDENTIFIER ::= { cevModuleASA5585Type 9 }
cevMASA5585Ssp20K7 OBJECT IDENTIFIER ::= { cevModuleASA5585Type 10 }
cevMASA5585Ssp40K7 OBJECT IDENTIFIER ::= { cevModuleASA5585Type 11 }
cevMASA5585Ssp60K7 OBJECT IDENTIFIER ::= { cevModuleASA5585Type 12 }
cevMASA5585IsmSspIps10K7 OBJECT IDENTIFIER ::= { cevModuleASA5585Type 13 }
cevMASA5585IsmSspIps20K7 OBJECT IDENTIFIER ::= { cevModuleASA5585Type 14 }
cevMASA5585IsmSspIps40K7 OBJECT IDENTIFIER ::= { cevModuleASA5585Type 15 }
cevMASA5585IsmSspIps60K7 OBJECT IDENTIFIER ::= { cevModuleASA5585Type 16 }
cevMASA5585Nm8x10GE OBJECT IDENTIFIER ::= { cevModuleASA5585Type 17 }
cevMASA5585Nm4x10GE OBJECT IDENTIFIER ::= { cevModuleASA5585Type 18 }
cevMASA5585Nm20x1GE OBJECT IDENTIFIER ::= { cevModuleASA5585Type 19 }
cevMASA5585CxSsp40 OBJECT IDENTIFIER ::= { cevModuleASA5585Type 20 }
cevMASA5585CxSsp60 OBJECT IDENTIFIER ::= { cevModuleASA5585Type 21 }
cevMASA5585CxSsp10 OBJECT IDENTIFIER ::= { cevModuleASA5585Type 22 }
cevMASA5585CxSsp20 OBJECT IDENTIFIER ::= { cevModuleASA5585Type 23 }
cevMASA5585SFRSsp10 OBJECT IDENTIFIER ::= { cevModuleASA5585Type 24 }
cevMASA5585SFRSsp20 OBJECT IDENTIFIER ::= { cevModuleASA5585Type 25 }
cevMASA5585SFRSsp40 OBJECT IDENTIFIER ::= { cevModuleASA5585Type 26 }
cevMASA5585SFRSsp60 OBJECT IDENTIFIER ::= { cevModuleASA5585Type 27 }
cevModuleCFPs   OBJECT IDENTIFIER ::= { cevModule 84 }
cevCFP100GLR4   OBJECT IDENTIFIER ::= { cevModuleCFPs 1 }
cevCFP40GLR4    OBJECT IDENTIFIER ::= { cevModuleCFPs 2 }
cevCFP40GSR4    OBJECT IDENTIFIER ::= { cevModuleCFPs 3 }
cevCFP40GFR     OBJECT IDENTIFIER ::= { cevModuleCFPs 4 }
cevCFP100GSR10  OBJECT IDENTIFIER ::= { cevModuleCFPs 5 }
cevCFP100GER4   OBJECT IDENTIFIER ::= { cevModuleCFPs 6 }
cevCFPUnknown   OBJECT IDENTIFIER ::= { cevModuleCFPs 7 }
cevModuleN3KType OBJECT IDENTIFIER ::= { cevModule 85 }
cevN3kC3064PQfixedModule OBJECT IDENTIFIER ::= { cevModuleN3KType 1 }
cevN3kC3064PQ10GEFixedModule OBJECT IDENTIFIER ::= { cevModuleN3KType 2 }
cevN3kC3048TP1GEFixedModule OBJECT IDENTIFIER ::= { cevModuleN3KType 3 }
cevN3kC3016Q40GEFixedModule OBJECT IDENTIFIER ::= { cevModuleN3KType 4 }
cevN3kC3064Pq10GXFixedModule OBJECT IDENTIFIER ::= { cevModuleN3KType 5 }
cevN3kC3548P10GFixedModule OBJECT IDENTIFIER ::= { cevModuleN3KType 6 }
cevN3kC3064TQ10GTFixedModule OBJECT IDENTIFIER ::= { cevModuleN3KType 7 }
cevN3KC3172     OBJECT IDENTIFIER ::= { cevModuleN3KType 8 }
cevN3KC3172TQ   OBJECT IDENTIFIER ::= { cevModuleN3KType 9 }
cevN3KC3132TQ   OBJECT IDENTIFIER ::= { cevModuleN3KType 10 }
cevN3KC3132CR   OBJECT IDENTIFIER ::= { cevModuleN3KType 11 }
cevN3kC3164Q40GEFixedModule OBJECT IDENTIFIER ::= { cevModuleN3KType 12 }
cevN3kC3548P10GXFixedModule OBJECT IDENTIFIER ::= { cevModuleN3KType 13 }
cevN3KC3132QXOE OBJECT IDENTIFIER ::= { cevModuleN3KType 14 }
cevN3KC3172PQOE OBJECT IDENTIFIER ::= { cevModuleN3KType 15 }
cevN3KC3172TQOE OBJECT IDENTIFIER ::= { cevModuleN3KType 16 }
cevN3KC3064XOE  OBJECT IDENTIFIER ::= { cevModuleN3KType 17 }
cevN3KC3048OE   OBJECT IDENTIFIER ::= { cevModuleN3KType 18 }
cevN3kC3232CFixedModule OBJECT IDENTIFIER ::= { cevModuleN3KType 19 }
cevN3kC31128PQfixedModule OBJECT IDENTIFIER ::= { cevModuleN3KType 20 }
cevN3KC3132QXL  OBJECT IDENTIFIER ::= { cevModuleN3KType 21 }
cevN3KC3172PQXL OBJECT IDENTIFIER ::= { cevModuleN3KType 22 }
cevN3KC3172TQXL OBJECT IDENTIFIER ::= { cevModuleN3KType 23 }
cevN3KC3172PQZ8 OBJECT IDENTIFIER ::= { cevModuleN3KType 24 }
cevN3KC31108TCV OBJECT IDENTIFIER ::= { cevModuleN3KType 26 }
cevN3KC31108PCV OBJECT IDENTIFIER ::= { cevModuleN3KType 27 }
cevN3KC3132QV   OBJECT IDENTIFIER ::= { cevModuleN3KType 28 }
cevModuleCGSType OBJECT IDENTIFIER ::= { cevModule 86 }
cevModuleCGS252016S8PC OBJECT IDENTIFIER ::= { cevModuleCGSType 1 }
cevModuleCGS252024TC OBJECT IDENTIFIER ::= { cevModuleCGSType 2 }
cevModuleASR900Type OBJECT IDENTIFIER ::= { cevModule 87 }
cevModuleASR903RSP1A OBJECT IDENTIFIER ::= { cevModuleASR900Type 1 }
cevModuleASR900ESP OBJECT IDENTIFIER ::= { cevModuleASR900Type 2 }
cevModuleASR903RSP1B OBJECT IDENTIFIER ::= { cevModuleASR900Type 3 }
cevModuleASR903RSP2A64G OBJECT IDENTIFIER ::= { cevModuleASR900Type 4 }
cevModuleASR903RSP2A128G OBJECT IDENTIFIER ::= { cevModuleASR900Type 5 }
cevModuleASR92024SZIM OBJECT IDENTIFIER ::= { cevModuleASR900Type 6 }
cevModuleASR92024SZM OBJECT IDENTIFIER ::= { cevModuleASR900Type 7 }
cevModuleASR92024TZM OBJECT IDENTIFIER ::= { cevModuleASR900Type 8 }
cevModuleASR92012CZA OBJECT IDENTIFIER ::= { cevModuleASR900Type 9 }
cevModuleASR92012CZD OBJECT IDENTIFIER ::= { cevModuleASR900Type 10 }
cevModuleASR9204SZA OBJECT IDENTIFIER ::= { cevModuleASR900Type 11 }
cevModuleASR9204SZD OBJECT IDENTIFIER ::= { cevModuleASR900Type 12 }
cevModuleASR92010SZPA OBJECT IDENTIFIER ::= { cevModuleASR900Type 13 }
cevModuleASR92010SZPD OBJECT IDENTIFIER ::= { cevModuleASR900Type 14 }
cevModuleASR92012SZIMCC OBJECT IDENTIFIER ::= { cevModuleASR900Type 19 }
cevModuleASR900RSP3C200CC OBJECT IDENTIFIER ::= { cevModuleASR900Type 20 }
cevModuleASR5000Type OBJECT IDENTIFIER ::= { cevModule 88 }
cevModuleASR5K01100eK9 OBJECT IDENTIFIER ::= { cevModuleASR5000Type 1 }
cevModuleASR5K0110gMmK9 OBJECT IDENTIFIER ::= { cevModuleASR5000Type 2 }
cevModuleASR5K0110gSmK9 OBJECT IDENTIFIER ::= { cevModuleASR5000Type 3 }
cevModuleASR5K011G2LxK9 OBJECT IDENTIFIER ::= { cevModuleASR5000Type 4 }
cevModuleASR5K011G2SxK9 OBJECT IDENTIFIER ::= { cevModuleASR5000Type 5 }
cevModuleASR5K011G2TK9 OBJECT IDENTIFIER ::= { cevModuleASR5000Type 6 }
cevModuleASR5K011GELxK9 OBJECT IDENTIFIER ::= { cevModuleASR5000Type 7 }
cevModuleASR5K011GESxK9 OBJECT IDENTIFIER ::= { cevModuleASR5000Type 8 }
cevModuleASR5K011GETK9 OBJECT IDENTIFIER ::= { cevModuleASR5000Type 9 }
cevModuleASR5K01OC3MmK9 OBJECT IDENTIFIER ::= { cevModuleASR5000Type 10 }
cevModuleASR5K01OC3SmK9 OBJECT IDENTIFIER ::= { cevModuleASR5000Type 11 }
cevModuleASR5K041GeLxK9 OBJECT IDENTIFIER ::= { cevModuleASR5000Type 12 }
cevModuleASR5K041GeSxK9 OBJECT IDENTIFIER ::= { cevModuleASR5000Type 13 }
cevModuleASR5K041GeTK9 OBJECT IDENTIFIER ::= { cevModuleASR5000Type 14 }
cevModuleASR5K042GeLxK9 OBJECT IDENTIFIER ::= { cevModuleASR5000Type 15 }
cevModuleASR5K042GeSxK9 OBJECT IDENTIFIER ::= { cevModuleASR5000Type 16 }
cevModuleASR5K042GeTK9 OBJECT IDENTIFIER ::= { cevModuleASR5000Type 17 }
cevModuleASR5K08100eK9 OBJECT IDENTIFIER ::= { cevModuleASR5000Type 18 }
cevModuleASR5K4OC3CMmK9 OBJECT IDENTIFIER ::= { cevModuleASR5000Type 19 }
cevModuleASR5K4OC3CSmK9 OBJECT IDENTIFIER ::= { cevModuleASR5000Type 20 }
cevModuleASR5KC1OC3MnK9 OBJECT IDENTIFIER ::= { cevModuleASR5000Type 21 }
cevModuleASR5KC1OC3SmK9 OBJECT IDENTIFIER ::= { cevModuleASR5000Type 22 }
cevModuleASR5KC4OC3MmK9 OBJECT IDENTIFIER ::= { cevModuleASR5000Type 23 }
cevModuleASR5KC4OC3SmK9 OBJECT IDENTIFIER ::= { cevModuleASR5000Type 24 }
cevModuleASR5KppcK9 OBJECT IDENTIFIER ::= { cevModuleASR5000Type 25 }
cevModuleASR5Kpsc16gK9 OBJECT IDENTIFIER ::= { cevModuleASR5000Type 26 }
cevModuleASR5Kpsc32gK9 OBJECT IDENTIFIER ::= { cevModuleASR5000Type 27 }
cevModuleASR5Kpsc64gK9 OBJECT IDENTIFIER ::= { cevModuleASR5000Type 28 }
cevModuleASR5KpscK9 OBJECT IDENTIFIER ::= { cevModuleASR5000Type 29 }
cevModuleASR5KsmcK9 OBJECT IDENTIFIER ::= { cevModuleASR5000Type 30 }
cevModuleASR5KSps3BncK9 OBJECT IDENTIFIER ::= { cevModuleASR5000Type 31 }
cevModuleASR5KSps33pnK9 OBJECT IDENTIFIER ::= { cevModuleASR5000Type 32 }
cevModuleASR5KSpioBncK9 OBJECT IDENTIFIER ::= { cevModuleASR5000Type 33 }
cevModuleASR5KSpio3pnK9 OBJECT IDENTIFIER ::= { cevModuleASR5000Type 34 }
cevModuleASR5KRccK9 OBJECT IDENTIFIER ::= { cevModuleASR5000Type 35 }
cevModuleASR5500Type OBJECT IDENTIFIER ::= { cevModule 89 }
cevModuleASR55DPC OBJECT IDENTIFIER ::= { cevModuleASR5500Type 1 }
cevModuleASR55FSC OBJECT IDENTIFIER ::= { cevModuleASR5500Type 2 }
cevModuleASR55MIO10GL10 OBJECT IDENTIFIER ::= { cevModuleASR5500Type 3 }
cevModuleASR55MIO10GL20 OBJECT IDENTIFIER ::= { cevModuleASR5500Type 4 }
cevModuleASR55MIO10GS10 OBJECT IDENTIFIER ::= { cevModuleASR5500Type 5 }
cevModuleASR55MIO10GS20 OBJECT IDENTIFIER ::= { cevModuleASR5500Type 6 }
cevModuleASR55MIOBASE OBJECT IDENTIFIER ::= { cevModuleASR5500Type 7 }
cevModuleASR55SSC OBJECT IDENTIFIER ::= { cevModuleASR5500Type 8 }
cevModuleASR55DPC2 OBJECT IDENTIFIER ::= { cevModuleASR5500Type 9 }
cevModuleASR55UDPC2 OBJECT IDENTIFIER ::= { cevModuleASR5500Type 10 }
cevModuleASR55MIO2 OBJECT IDENTIFIER ::= { cevModuleASR5500Type 11 }
cevModuleCSR1000vType OBJECT IDENTIFIER ::= { cevModule 90 }
cevModuleCSR1000vRP OBJECT IDENTIFIER ::= { cevModuleCSR1000vType 1 }
cevModuleCSR1000vESP OBJECT IDENTIFIER ::= { cevModuleCSR1000vType 2 }
cevModuleCgrType OBJECT IDENTIFIER ::= { cevModule 91 }
cevModuleCGMPlc OBJECT IDENTIFIER ::= { cevModuleCgrType 18 }
cevModuleCGMGe  OBJECT IDENTIFIER ::= { cevModuleCgrType 19 }
cevModuleCGM3gEVDOSE OBJECT IDENTIFIER ::= { cevModuleCgrType 21 }
cevModuleCGM3gEVDOVE OBJECT IDENTIFIER ::= { cevModuleCgrType 22 }
cevModuleCGM3gHSPAAE OBJECT IDENTIFIER ::= { cevModuleCgrType 23 }
cevModuleCGM3gHSPAGE OBJECT IDENTIFIER ::= { cevModuleCgrType 24 }
cevModuleCGM3gHspaAbGE OBJECT IDENTIFIER ::= { cevModuleCgrType 25 }
cevModuleCGM4gLteGA7304 OBJECT IDENTIFIER ::= { cevModuleCgrType 26 }
cevModuleCGM4gLteNA7354 OBJECT IDENTIFIER ::= { cevModuleCgrType 27 }
cevModuleCGMServerX86C4F800 OBJECT IDENTIFIER ::= { cevModuleCgrType 28 }
cevModuleCGM4gLteNA7354MNAAB OBJECT IDENTIFIER ::= { cevModuleCgrType 29 }
cevModuleCGMServerX86C4F800D128 OBJECT IDENTIFIER ::= { cevModuleCgrType 30 }
cevModuleCGM4gLteLA7430 OBJECT IDENTIFIER ::= { cevModuleCgrType 31 }
cevModuleCGM4gLteEA7455 OBJECT IDENTIFIER ::= { cevModuleCgrType 32 }
cevModuleISR4400Type OBJECT IDENTIFIER ::= { cevModule 92 }
cevModuleISR4441RP OBJECT IDENTIFIER ::= { cevModuleISR4400Type 1 }
cevModuleISR4442RP OBJECT IDENTIFIER ::= { cevModuleISR4400Type 2 }
cevModuleISR4451RP OBJECT IDENTIFIER ::= { cevModuleISR4400Type 3 }
cevModuleISR4452RP OBJECT IDENTIFIER ::= { cevModuleISR4400Type 4 }
cevModuleISR4400RP OBJECT IDENTIFIER ::= { cevModuleISR4400Type 5 }
cevModuleISR4441FP OBJECT IDENTIFIER ::= { cevModuleISR4400Type 6 }
cevModuleISR4442FP OBJECT IDENTIFIER ::= { cevModuleISR4400Type 7 }
cevModuleISR4451FP OBJECT IDENTIFIER ::= { cevModuleISR4400Type 8 }
cevModuleISR4452FP OBJECT IDENTIFIER ::= { cevModuleISR4400Type 9 }
cevModuleISR4400FP OBJECT IDENTIFIER ::= { cevModuleISR4400Type 10 }
cevModuleISR4400NIM OBJECT IDENTIFIER ::= { cevModuleISR4400Type 11 }
cevModuleISR4441NIM OBJECT IDENTIFIER ::= { cevModuleISR4400Type 12 }
cevModuleISR4442NIM OBJECT IDENTIFIER ::= { cevModuleISR4400Type 13 }
cevModuleISR4451NIM OBJECT IDENTIFIER ::= { cevModuleISR4400Type 14 }
cevModuleISR4452NIM OBJECT IDENTIFIER ::= { cevModuleISR4400Type 15 }
cevModuleISR4400ESM OBJECT IDENTIFIER ::= { cevModuleISR4400Type 16 }
cevModuleISR4441ESM OBJECT IDENTIFIER ::= { cevModuleISR4400Type 17 }
cevModuleISR4442ESM OBJECT IDENTIFIER ::= { cevModuleISR4400Type 18 }
cevModuleISR4451ESM OBJECT IDENTIFIER ::= { cevModuleISR4400Type 19 }
cevModuleISR4452ESM OBJECT IDENTIFIER ::= { cevModuleISR4400Type 20 }
cevModuleISR44000FP4xGE OBJECT IDENTIFIER ::= { cevModuleISR4400Type 21 }
cevModuleISR4400InternalPOE OBJECT IDENTIFIER ::= { cevModuleISR4400Type 22 }
cevModuleISR4400ExternalPOE OBJECT IDENTIFIER ::= { cevModuleISR4400Type 42 }
cevModuleNGWICSerial1T OBJECT IDENTIFIER ::= { cevModuleISR4400Type 43 }
cevModuleNGWICSerial2T OBJECT IDENTIFIER ::= { cevModuleISR4400Type 44 }
cevModuleNGWICSerial4T OBJECT IDENTIFIER ::= { cevModuleISR4400Type 45 }
cevModuleISR4431RP OBJECT IDENTIFIER ::= { cevModuleISR4400Type 46 }
cevModuleISR4431FP OBJECT IDENTIFIER ::= { cevModuleISR4400Type 47 }
cevModuleISR4431NIM OBJECT IDENTIFIER ::= { cevModuleISR4400Type 48 }
cevModuleISR4451BRP OBJECT IDENTIFIER ::= { cevModuleISR4400Type 49 }
cevModuleISR4431BRP OBJECT IDENTIFIER ::= { cevModuleISR4400Type 50 }
cevModuleISR4451BFP OBJECT IDENTIFIER ::= { cevModuleISR4400Type 51 }
cevModuleISR4431BFP OBJECT IDENTIFIER ::= { cevModuleISR4400Type 52 }
cevModuleISR4451BNIM OBJECT IDENTIFIER ::= { cevModuleISR4400Type 53 }
cevModuleISR4431BNIM OBJECT IDENTIFIER ::= { cevModuleISR4400Type 54 }
cevModuleISR4451BESM OBJECT IDENTIFIER ::= { cevModuleISR4400Type 55 }
cevModuleQSFPPlusS OBJECT IDENTIFIER ::= { cevModule 93 }
cevQSFP40GLR4   OBJECT IDENTIFIER ::= { cevModuleQSFPPlusS 1 }
cevQSFP40GSR4   OBJECT IDENTIFIER ::= { cevModuleQSFPPlusS 2 }
cevQSFP40GSMSR4 OBJECT IDENTIFIER ::= { cevModuleQSFPPlusS 3 }
cevQSFP40GCR4Active OBJECT IDENTIFIER ::= { cevModuleQSFPPlusS 4 }
cevQSFP40GCR4Passive OBJECT IDENTIFIER ::= { cevModuleQSFPPlusS 5 }
cevSFPQSFP40GECSR4 OBJECT IDENTIFIER ::= { cevModuleQSFPPlusS 6 }
cevSFPQSFP40GELR4 OBJECT IDENTIFIER ::= { cevModuleQSFPPlusS 7 }
cevQSFP40GSRBD  OBJECT IDENTIFIER ::= { cevModuleQSFPPlusS 8 }
cevQSFP40GER4   OBJECT IDENTIFIER ::= { cevModuleQSFPPlusS 9 }
cevQSFP40GSR4S  OBJECT IDENTIFIER ::= { cevModuleQSFPPlusS 10 }
cevQSFP40GLR4LS OBJECT IDENTIFIER ::= { cevModuleQSFPPlusS 11 }
cevQSFP40GLR4S  OBJECT IDENTIFIER ::= { cevModuleQSFPPlusS 12 }
cevQSFP4X10GLRS OBJECT IDENTIFIER ::= { cevModuleQSFPPlusS 13 }
cevQSFPH40GAOC1M OBJECT IDENTIFIER ::= { cevModuleQSFPPlusS 14 }
cevQSFPH40GAOC2M OBJECT IDENTIFIER ::= { cevModuleQSFPPlusS 15 }
cevQSFPH40GAOC3M OBJECT IDENTIFIER ::= { cevModuleQSFPPlusS 16 }
cevQSFPH40GAOC5M OBJECT IDENTIFIER ::= { cevModuleQSFPPlusS 17 }
cevQSFPH40GAOC7M OBJECT IDENTIFIER ::= { cevModuleQSFPPlusS 18 }
cevQSFPH40GAOC10M OBJECT IDENTIFIER ::= { cevModuleQSFPPlusS 19 }
cevQSFPH40GAOC15M OBJECT IDENTIFIER ::= { cevModuleQSFPPlusS 20 }
cevQSFPH40GAOC20M OBJECT IDENTIFIER ::= { cevModuleQSFPPlusS 21 }
cevQSFPH40GAOC25M OBJECT IDENTIFIER ::= { cevModuleQSFPPlusS 22 }
cevQSFPH40GAOC30M OBJECT IDENTIFIER ::= { cevModuleQSFPPlusS 23 }
cevQSFP40GCSR4  OBJECT IDENTIFIER ::= { cevModuleQSFPPlusS 24 }
cevQSFPWSPQ40GLR4L OBJECT IDENTIFIER ::= { cevModuleQSFPPlusS 25 }
cevQSFP4X10GAOC1M OBJECT IDENTIFIER ::= { cevModuleQSFPPlusS 26 }
cevQSFP4X10GAOC2M OBJECT IDENTIFIER ::= { cevModuleQSFPPlusS 27 }
cevQSFP4X10GAOC3M OBJECT IDENTIFIER ::= { cevModuleQSFPPlusS 28 }
cevQSFP4X10GAOC5M OBJECT IDENTIFIER ::= { cevModuleQSFPPlusS 29 }
cevQSFP4X10GAOC7M OBJECT IDENTIFIER ::= { cevModuleQSFPPlusS 30 }
cevQSFP4X10GAOC10M OBJECT IDENTIFIER ::= { cevModuleQSFPPlusS 31 }
cevQSFPH40GCU05M OBJECT IDENTIFIER ::= { cevModuleQSFPPlusS 32 }
cevQSFPH40GCU1M OBJECT IDENTIFIER ::= { cevModuleQSFPPlusS 33 }
cevQSFPH40GCU2M OBJECT IDENTIFIER ::= { cevModuleQSFPPlusS 34 }
cevQSFPH40GCU3M OBJECT IDENTIFIER ::= { cevModuleQSFPPlusS 35 }
cevQSFPH40GCU4M OBJECT IDENTIFIER ::= { cevModuleQSFPPlusS 36 }
cevQSFPH40GCU5M OBJECT IDENTIFIER ::= { cevModuleQSFPPlusS 37 }
cevModuleN6KType OBJECT IDENTIFIER ::= { cevModule 95 }
cevN6KN6004XM20UP OBJECT IDENTIFIER ::= { cevModuleN6KType 1 }
cevN6KC6004M12Q OBJECT IDENTIFIER ::= { cevModuleN6KType 2 }
cevN6KC600496QFixedModule OBJECT IDENTIFIER ::= { cevModuleN6KType 3 }
cevN6KC6001M4Q  OBJECT IDENTIFIER ::= { cevModuleN6KType 4 }
cevN6KC600164PFixedModule OBJECT IDENTIFIER ::= { cevModuleN6KType 5 }
cevN6K48P10G    OBJECT IDENTIFIER ::= { cevModuleN6KType 6 }
cevN6K32Q40G    OBJECT IDENTIFIER ::= { cevModuleN6KType 7 }
cevN6K24Q40G    OBJECT IDENTIFIER ::= { cevModuleN6KType 8 }
cevN6KC600164TFixedModule OBJECT IDENTIFIER ::= { cevModuleN6KType 11 }
cevN6KN6002M24UP2Q OBJECT IDENTIFIER ::= { cevModuleN6KType 12 }
cevN6KN6002M24UP2Q16G OBJECT IDENTIFIER ::= { cevModuleN6KType 13 }
cevN6KC6002128PFixedModule OBJECT IDENTIFIER ::= { cevModuleN6KType 15 }
cevN6KC600172UPFixedModule OBJECT IDENTIFIER ::= { cevModuleN6KType 16 }
cevN6KN6004M12Q OBJECT IDENTIFIER ::= { cevModuleN6KType 18 }
cevN6KC6001M6Q  OBJECT IDENTIFIER ::= { cevModuleN6KType 19 }
cevModuleISRType OBJECT IDENTIFIER ::= { cevModule 96 }
cevModuleISRSM1T3E3 OBJECT IDENTIFIER ::= { cevModuleISRType 1 }
cevModuleISRSM6XGE OBJECT IDENTIFIER ::= { cevModuleISRType 2 }
cevModuleISRSM1X10GE4XGE OBJECT IDENTIFIER ::= { cevModuleISRType 3 }
cevModuleISRSmEs3x16P OBJECT IDENTIFIER ::= { cevModuleISRType 4 }
cevModuleISRSmEs3x24P OBJECT IDENTIFIER ::= { cevModuleISRType 5 }
cevModuleISRSmDEs3x48P OBJECT IDENTIFIER ::= { cevModuleISRType 6 }
cevModuleISRSSD OBJECT IDENTIFIER ::= { cevModuleISRType 7 }
cevModuleISRMSM50 OBJECT IDENTIFIER ::= { cevModuleISRType 8 }
cevModuleISRMSM100 OBJECT IDENTIFIER ::= { cevModuleISRType 9 }
cevModuleISRMSM200 OBJECT IDENTIFIER ::= { cevModuleISRType 10 }
cevModuleISRMSM300 OBJECT IDENTIFIER ::= { cevModuleISRType 11 }
cevModuleISRMSM400 OBJECT IDENTIFIER ::= { cevModuleISRType 12 }
cevModuleISRExtNIM OBJECT IDENTIFIER ::= { cevModuleISRType 13 }
cevModuleISRNIM1XGE OBJECT IDENTIFIER ::= { cevModuleISRType 14 }
cevModuleISRNIM2XGE OBJECT IDENTIFIER ::= { cevModuleISRType 15 }
cevModuleISRSMPVDM500 OBJECT IDENTIFIER ::= { cevModuleISRType 16 }
cevModuleISRSMPVDM1000 OBJECT IDENTIFIER ::= { cevModuleISRType 17 }
cevModuleISRSMPVDM2000 OBJECT IDENTIFIER ::= { cevModuleISRType 18 }
cevModuleISRSMPVDM3000 OBJECT IDENTIFIER ::= { cevModuleISRType 19 }
cevModuleISRSMX64A OBJECT IDENTIFIER ::= { cevModuleISRType 47 }
cevModuleISRNIM2BRIST OBJECT IDENTIFIER ::= { cevModuleISRType 48 }
cevModuleISRNIM4BRIST OBJECT IDENTIFIER ::= { cevModuleISRType 49 }
cevModuleN77Type OBJECT IDENTIFIER ::= { cevModule 97 }
cevN77c7718Fab2 OBJECT IDENTIFIER ::= { cevModuleN77Type 1 }
cevN77c7710Fab2 OBJECT IDENTIFIER ::= { cevModuleN77Type 2 }
cevN77c7706Fab2 OBJECT IDENTIFIER ::= { cevModuleN77Type 3 }
cevN77F248XP23E OBJECT IDENTIFIER ::= { cevModuleN77Type 4 }
cevN77SUP2E     OBJECT IDENTIFIER ::= { cevModuleN77Type 5 }
cevN77F324FQ25  OBJECT IDENTIFIER ::= { cevModuleN77Type 6 }
cevN77F348XP23  OBJECT IDENTIFIER ::= { cevModuleN77Type 7 }
cevN77F312CK26  OBJECT IDENTIFIER ::= { cevModuleN77Type 8 }
cevN77M312CQ26L OBJECT IDENTIFIER ::= { cevModuleN77Type 9 }
cevN77M324FQ25L OBJECT IDENTIFIER ::= { cevModuleN77Type 10 }
cevN77M348XP23L OBJECT IDENTIFIER ::= { cevModuleN77Type 11 }
cevModuleCat3KCAxType OBJECT IDENTIFIER ::= { cevModule 98 }
cevModuleCat365048PQ OBJECT IDENTIFIER ::= { cevModuleCat3KCAxType 1 }
cevModuleCat365048TQ OBJECT IDENTIFIER ::= { cevModuleCat3KCAxType 2 }
cevModuleCat385024u OBJECT IDENTIFIER ::= { cevModuleCat3KCAxType 3 }
cevModuleCat385048u OBJECT IDENTIFIER ::= { cevModuleCat3KCAxType 4 }
cevModuleCat365024TD OBJECT IDENTIFIER ::= { cevModuleCat3KCAxType 5 }
cevModuleCat365048TD OBJECT IDENTIFIER ::= { cevModuleCat3KCAxType 6 }
cevModuleCat365024PD OBJECT IDENTIFIER ::= { cevModuleCat3KCAxType 7 }
cevModuleCat365048PD OBJECT IDENTIFIER ::= { cevModuleCat3KCAxType 8 }
cevModuleCat365024TS OBJECT IDENTIFIER ::= { cevModuleCat3KCAxType 9 }
cevModuleCat365048TS OBJECT IDENTIFIER ::= { cevModuleCat3KCAxType 10 }
cevModuleCat365024PS OBJECT IDENTIFIER ::= { cevModuleCat3KCAxType 11 }
cevModuleCat365048PS OBJECT IDENTIFIER ::= { cevModuleCat3KCAxType 12 }
cevModuleCat385024T OBJECT IDENTIFIER ::= { cevModuleCat3KCAxType 13 }
cevModuleCat385048T OBJECT IDENTIFIER ::= { cevModuleCat3KCAxType 14 }
cevModuleCat385024P OBJECT IDENTIFIER ::= { cevModuleCat3KCAxType 15 }
cevModuleCat385048P OBJECT IDENTIFIER ::= { cevModuleCat3KCAxType 16 }
cevModuleCat385012S OBJECT IDENTIFIER ::= { cevModuleCat3KCAxType 17 }
cevModuleCat385024S OBJECT IDENTIFIER ::= { cevModuleCat3KCAxType 18 }
cevModule57xxwlc OBJECT IDENTIFIER ::= { cevModule 99 }
cevModuleCat5760wlc OBJECT IDENTIFIER ::= { cevModule57xxwlc 2 }
cevModuleCat5700wlc OBJECT IDENTIFIER ::= { cevModule57xxwlc 3 }
cevModuleN95KType OBJECT IDENTIFIER ::= { cevModule 100 }
cevN9KSUPA      OBJECT IDENTIFIER ::= { cevModuleN95KType 1 }
cevN9Kc9508FM   OBJECT IDENTIFIER ::= { cevModuleN95KType 2 }
cevN9kScA       OBJECT IDENTIFIER ::= { cevModuleN95KType 3 }
cevN9kX9564PX   OBJECT IDENTIFIER ::= { cevModuleN95KType 4 }
cevN9kX9564TX   OBJECT IDENTIFIER ::= { cevModuleN95KType 5 }
cevN9kX9636PQ   OBJECT IDENTIFIER ::= { cevModuleN95KType 6 }
cevN9KX9536PQ   OBJECT IDENTIFIER ::= { cevModuleN95KType 13 }
cevN9Kc9516FM   OBJECT IDENTIFIER ::= { cevModuleN95KType 14 }
cevN9Kc9504FM   OBJECT IDENTIFIER ::= { cevModuleN95KType 15 }
cevN9KX9464PX   OBJECT IDENTIFIER ::= { cevModuleN95KType 18 }
cevN9KX9464TX   OBJECT IDENTIFIER ::= { cevModuleN95KType 19 }
cevN9KX9432PQ   OBJECT IDENTIFIER ::= { cevModuleN95KType 20 }
cevN9KSUPB      OBJECT IDENTIFIER ::= { cevModuleN95KType 21 }
cevN9KX9632PC   OBJECT IDENTIFIER ::= { cevModuleN95KType 22 }
cevN9KX9464TX2  OBJECT IDENTIFIER ::= { cevModuleN95KType 23 }
cevN9kC9508FM2  OBJECT IDENTIFIER ::= { cevModuleN95KType 24 }
cevN9kC9504FM2  OBJECT IDENTIFIER ::= { cevModuleN95KType 25 }
cevN9KX9408PC   OBJECT IDENTIFIER ::= { cevModuleN95KType 26 }
cevN9KX9736Ce   OBJECT IDENTIFIER ::= { cevModuleN95KType 27 }
cevN9KC9504FMe  OBJECT IDENTIFIER ::= { cevModuleN95KType 28 }
cevN9KC9508FMe  OBJECT IDENTIFIER ::= { cevModuleN95KType 29 }
cevN9KX9736CEX  OBJECT IDENTIFIER ::= { cevModuleN95KType 32 }
cevN9KX9732CEX  OBJECT IDENTIFIER ::= { cevModuleN95KType 35 }
cevModuleCPAKType OBJECT IDENTIFIER ::= { cevModule 101 }
cevCPAK100GLR4  OBJECT IDENTIFIER ::= { cevModuleCPAKType 1 }
cevCPAK100GSR10 OBJECT IDENTIFIER ::= { cevModuleCPAKType 2 }
cevCPAK100GLR10 OBJECT IDENTIFIER ::= { cevModuleCPAKType 3 }
cevCPAK100GER4L OBJECT IDENTIFIER ::= { cevModuleCPAKType 4 }
cevCPAKUnknown  OBJECT IDENTIFIER ::= { cevModuleCPAKType 5 }
cevCPAK10X10GLR OBJECT IDENTIFIER ::= { cevModuleCPAKType 6 }
cevCPAK100GSR4  OBJECT IDENTIFIER ::= { cevModuleCPAKType 7 }
cevCPAK100GELR4 OBJECT IDENTIFIER ::= { cevModuleCPAKType 8 }
cevCPAK10X10GERL OBJECT IDENTIFIER ::= { cevModuleCPAKType 9 }
cevCPAK100GCWDM4 OBJECT IDENTIFIER ::= { cevModuleCPAKType 10 }
cevCPAK100GPSM4 OBJECT IDENTIFIER ::= { cevModuleCPAKType 11 }
cevCPAK100GLR4LANPHY OBJECT IDENTIFIER ::= { cevModuleCPAKType 12 }
cevDirectAttachCable40Gs OBJECT IDENTIFIER ::= { cevModule 102 }
cevQSFP4SFP10GCU1M OBJECT IDENTIFIER ::= { cevDirectAttachCable40Gs 1 }
cevQSFP4SFP10GCU3M OBJECT IDENTIFIER ::= { cevDirectAttachCable40Gs 2 }
cevQSFP4SFP10GCU5M OBJECT IDENTIFIER ::= { cevDirectAttachCable40Gs 3 }
cevQSFPH40GBCU1M OBJECT IDENTIFIER ::= { cevDirectAttachCable40Gs 4 }
cevQSFPH40GBCU3M OBJECT IDENTIFIER ::= { cevDirectAttachCable40Gs 5 }
cevQSFPH40GBCU5M OBJECT IDENTIFIER ::= { cevDirectAttachCable40Gs 6 }
cevQSFPH40GBACU7M OBJECT IDENTIFIER ::= { cevDirectAttachCable40Gs 7 }
cevQSFPH40GBACU10M OBJECT IDENTIFIER ::= { cevDirectAttachCable40Gs 8 }
cevQSFP4SFP10GACU7M OBJECT IDENTIFIER ::= { cevDirectAttachCable40Gs 9 }
cevQSFP4SFP10GACU10M OBJECT IDENTIFIER ::= { cevDirectAttachCable40Gs 10 }
cevModuleN93KType OBJECT IDENTIFIER ::= { cevModule 103 }
cevN9KM6PQ      OBJECT IDENTIFIER ::= { cevModuleN93KType 1 }
cevN9KM12PQ     OBJECT IDENTIFIER ::= { cevModuleN93KType 2 }
cevN9KC93128TXfixedModule OBJECT IDENTIFIER ::= { cevModuleN93KType 3 }
cevN9KC9396TXfixedModule OBJECT IDENTIFIER ::= { cevModuleN93KType 4 }
cevN9KC9396PXfixedModule OBJECT IDENTIFIER ::= { cevModuleN93KType 5 }
cevN9KC9372PXfixedModule OBJECT IDENTIFIER ::= { cevModuleN93KType 7 }
cevN9KC9372TXfixedModule OBJECT IDENTIFIER ::= { cevModuleN93KType 8 }
cevN9KC9332PQfixedModule OBJECT IDENTIFIER ::= { cevModuleN93KType 9 }
cevN9KM4PC      OBJECT IDENTIFIER ::= { cevModuleN93KType 10 }
cevN9KM6PQE     OBJECT IDENTIFIER ::= { cevModuleN93KType 11 }
cevN9KC93120TXFixedModule OBJECT IDENTIFIER ::= { cevModuleN93KType 16 }
cevN9KC93108TCEXFixedModule OBJECT IDENTIFIER ::= { cevModuleN93KType 18 }
cevN9KC93180YCFXFixedModule OBJECT IDENTIFIER ::= { cevModuleN93KType 20 }
cevN9KC93108TCFXFixedModule OBJECT IDENTIFIER ::= { cevModuleN93KType 22 }
cevModuleISR4300Type OBJECT IDENTIFIER ::= { cevModule 104 }
cevModuleISR4351RP OBJECT IDENTIFIER ::= { cevModuleISR4300Type 1 }
cevModuleISR4351FP OBJECT IDENTIFIER ::= { cevModuleISR4300Type 2 }
cevModuleISR4351NIM OBJECT IDENTIFIER ::= { cevModuleISR4300Type 3 }
cevModuleISR4351ESM OBJECT IDENTIFIER ::= { cevModuleISR4300Type 4 }
cevModuleISR4300FP3xGE OBJECT IDENTIFIER ::= { cevModuleISR4300Type 5 }
cevModuleISR4331RP OBJECT IDENTIFIER ::= { cevModuleISR4300Type 6 }
cevModuleISR4331FP OBJECT IDENTIFIER ::= { cevModuleISR4300Type 7 }
cevModuleISR4331NIM OBJECT IDENTIFIER ::= { cevModuleISR4300Type 8 }
cevModuleISR4331ESM OBJECT IDENTIFIER ::= { cevModuleISR4300Type 9 }
cevModuleISR4321RP OBJECT IDENTIFIER ::= { cevModuleISR4300Type 10 }
cevModuleISR4321FP OBJECT IDENTIFIER ::= { cevModuleISR4300Type 11 }
cevModuleISR4321NIM OBJECT IDENTIFIER ::= { cevModuleISR4300Type 12 }
cevModuleISR4300FP2xGE OBJECT IDENTIFIER ::= { cevModuleISR4300Type 13 }
cevModuleISR4351BRP OBJECT IDENTIFIER ::= { cevModuleISR4300Type 14 }
cevModuleISR4331BRP OBJECT IDENTIFIER ::= { cevModuleISR4300Type 15 }
cevModuleISR4321BRP OBJECT IDENTIFIER ::= { cevModuleISR4300Type 16 }
cevModuleISR4351BFP OBJECT IDENTIFIER ::= { cevModuleISR4300Type 17 }
cevModuleISR4331BFP OBJECT IDENTIFIER ::= { cevModuleISR4300Type 18 }
cevModuleISR4321BFP OBJECT IDENTIFIER ::= { cevModuleISR4300Type 19 }
cevModuleISR4351BNIM OBJECT IDENTIFIER ::= { cevModuleISR4300Type 20 }
cevModuleISR4331BNIM OBJECT IDENTIFIER ::= { cevModuleISR4300Type 21 }
cevModuleISR4321BNIM OBJECT IDENTIFIER ::= { cevModuleISR4300Type 22 }
cevModuleISR4351BESM OBJECT IDENTIFIER ::= { cevModuleISR4300Type 23 }
cevModuleISR4331BESM OBJECT IDENTIFIER ::= { cevModuleISR4300Type 24 }
cevModuleNIMType OBJECT IDENTIFIER ::= { cevModule 105 }
cevModuleNIM1MftT1E1 OBJECT IDENTIFIER ::= { cevModuleNIMType 1 }
cevModuleNIM2MftT1E1 OBJECT IDENTIFIER ::= { cevModuleNIMType 2 }
cevModuleNIM4MftT1E1 OBJECT IDENTIFIER ::= { cevModuleNIMType 3 }
cevModuleNIM8MftT1E1 OBJECT IDENTIFIER ::= { cevModuleNIMType 4 }
cevModuleNIM1CE1T1PRI OBJECT IDENTIFIER ::= { cevModuleNIMType 5 }
cevModuleNIM2CE1T1PRI OBJECT IDENTIFIER ::= { cevModuleNIMType 6 }
cevModuleNIM8CE1T1PRI OBJECT IDENTIFIER ::= { cevModuleNIMType 7 }
cevModuleNIMPVDM4c32 OBJECT IDENTIFIER ::= { cevModuleNIMType 8 }
cevModuleNIMPVDM4c64 OBJECT IDENTIFIER ::= { cevModuleNIMType 9 }
cevModuleNIMPVDM4c128 OBJECT IDENTIFIER ::= { cevModuleNIMType 10 }
cevModuleNIMPVDM4c192 OBJECT IDENTIFIER ::= { cevModuleNIMType 11 }
cevModuleNIMPVDM4c256 OBJECT IDENTIFIER ::= { cevModuleNIMType 12 }
cevModuleNIMSSD OBJECT IDENTIFIER ::= { cevModuleNIMType 13 }
cevModuleNIMHDD OBJECT IDENTIFIER ::= { cevModuleNIMType 14 }
cevModuleNIM2FXS OBJECT IDENTIFIER ::= { cevModuleNIMType 15 }
cevModuleNIM4FXS OBJECT IDENTIFIER ::= { cevModuleNIMType 16 }
cevModuleNIM2FXO OBJECT IDENTIFIER ::= { cevModuleNIMType 17 }
cevModuleNIM4FXO OBJECT IDENTIFIER ::= { cevModuleNIMType 18 }
cevModuleNIM2FXS4FXO OBJECT IDENTIFIER ::= { cevModuleNIMType 19 }
cevModuleNIM2EM OBJECT IDENTIFIER ::= { cevModuleNIMType 20 }
cevModuleNIM4EM OBJECT IDENTIFIER ::= { cevModuleNIMType 21 }
cevModuleNIM2BRI OBJECT IDENTIFIER ::= { cevModuleNIMType 22 }
cevModuleNIM4BRI OBJECT IDENTIFIER ::= { cevModuleNIMType 23 }
cevModuleNIMVABAnnexA OBJECT IDENTIFIER ::= { cevModuleNIMType 25 }
cevModuleNIMVAAnnexB OBJECT IDENTIFIER ::= { cevModuleNIMType 26 }
cevModuleNIMVABAnnexM OBJECT IDENTIFIER ::= { cevModuleNIMType 27 }
cevModuleNIM4ES2 OBJECT IDENTIFIER ::= { cevModuleNIMType 28 }
cevModuleNIM8ES2 OBJECT IDENTIFIER ::= { cevModuleNIMType 29 }
cevModuleNIM8ES2POE OBJECT IDENTIFIER ::= { cevModuleNIMType 30 }
cevModuleNIM16A OBJECT IDENTIFIER ::= { cevModuleNIMType 31 }
cevModuleNIM24A OBJECT IDENTIFIER ::= { cevModuleNIMType 32 }
cevModuleCXPType OBJECT IDENTIFIER ::= { cevModule 106 }
cevModuleCXP100GSR10 OBJECT IDENTIFIER ::= { cevModuleCXPType 1 }
cevModuleCXP100GSR12 OBJECT IDENTIFIER ::= { cevModuleCXPType 2 }
cevModuleASA5506Type OBJECT IDENTIFIER ::= { cevModule 107 }
cevModuleAsa5506SSD OBJECT IDENTIFIER ::= { cevModuleASA5506Type 1 }
cevModuleAsa5506WSSD OBJECT IDENTIFIER ::= { cevModuleASA5506Type 2 }
cevModuleAsa5506K7SSD OBJECT IDENTIFIER ::= { cevModuleASA5506Type 3 }
cevModuleAsa5506HSSD OBJECT IDENTIFIER ::= { cevModuleASA5506Type 4 }
cevModuleASA5508Type OBJECT IDENTIFIER ::= { cevModule 108 }
cevModuleAsa5508SSD OBJECT IDENTIFIER ::= { cevModuleASA5508Type 1 }
cevModuleAsa5508K7SSD OBJECT IDENTIFIER ::= { cevModuleASA5508Type 2 }
cevModuleCCEType OBJECT IDENTIFIER ::= { cevModule 109 }
cevModuleCCESup OBJECT IDENTIFIER ::= { cevModuleCCEType 1 }
cevModuleCCESupPic OBJECT IDENTIFIER ::= { cevModuleCCEType 2 }
cevModuleCCESsi OBJECT IDENTIFIER ::= { cevModuleCCEType 3 }
cevModuleCCESsiPic OBJECT IDENTIFIER ::= { cevModuleCCEType 4 }
cevModuleCCECbrRS422BaseRJ45 OBJECT IDENTIFIER ::= { cevModuleCCEType 5 }
cevModuleCCECbrBNC OBJECT IDENTIFIER ::= { cevModuleCCEType 6 }
cevModuleWIMType OBJECT IDENTIFIER ::= { cevModule 110 }
cevModuleWIM1T  OBJECT IDENTIFIER ::= { cevModuleWIMType 3 }
cevModuleWIM3G  OBJECT IDENTIFIER ::= { cevModuleWIMType 4 }
cevModuleISA3000Type OBJECT IDENTIFIER ::= { cevModule 111 }
cevModuleISA30004CSSD64 OBJECT IDENTIFIER ::= { cevModuleISA3000Type 1 }
cevModuleISA30002C2FSSD64 OBJECT IDENTIFIER ::= { cevModuleISA3000Type 2 }
cevModuleRAISA1783SAD4T0SSSD64 OBJECT IDENTIFIER ::= { cevModuleISA3000Type 3 }
cevModuleRAISA1783SAD2T2SSSD64 OBJECT IDENTIFIER ::= { cevModuleISA3000Type 4 }
cevModuleISA3000HardwareBypass OBJECT IDENTIFIER ::= { cevModuleISA3000Type 5 }
cevModuleRAISA1783HardwareBypass OBJECT IDENTIFIER ::= { cevModuleISA3000Type 6 }
cevModuleISA4000Type OBJECT IDENTIFIER ::= { cevModule 112 }
cevModuleISA4000SSD64 OBJECT IDENTIFIER ::= { cevModuleISA4000Type 1 }
cevModuleISA4000SSD128 OBJECT IDENTIFIER ::= { cevModuleISA4000Type 2 }
cevModuleCFP2Type OBJECT IDENTIFIER ::= { cevModule 113 }
cevModuleCFP2ONSCFP2WDM OBJECT IDENTIFIER ::= { cevModuleCFP2Type 1 }
cevModuleCFP2100GER4 OBJECT IDENTIFIER ::= { cevModuleCFP2Type 2 }
cevModuleN92KType OBJECT IDENTIFIER ::= { cevModule 114 }
cevN9KC9264PQ   OBJECT IDENTIFIER ::= { cevModuleN92KType 1 }
cevN9KC9264PQfixedModule OBJECT IDENTIFIER ::= { cevModuleN92KType 2 }
cevModuleN9KType OBJECT IDENTIFIER ::= { cevModule 115 }
cevN9KFabricExtenderConnectionCable OBJECT IDENTIFIER ::= { cevModuleN9KType 1 }
cevModuleFPRType OBJECT IDENTIFIER ::= { cevModule 116 }
cevFPR9KSUPFixedModule OBJECT IDENTIFIER ::= { cevModuleFPRType 1 }
cevFPRNetworkModule4X40G OBJECT IDENTIFIER ::= { cevModuleFPRType 2 }
cevFPRNetworkModule8X10G OBJECT IDENTIFIER ::= { cevModuleFPRType 3 }
cevFPR4120SUPFixedModule OBJECT IDENTIFIER ::= { cevModuleFPRType 4 }
cevFPR4140SUPFixedModule OBJECT IDENTIFIER ::= { cevModuleFPRType 5 }
cevFPR4110SUPFixedModule OBJECT IDENTIFIER ::= { cevModuleFPRType 7 }
cevFPRDNM2X100GF OBJECT IDENTIFIER ::= { cevModuleFPRType 8 }
cevFPRDNM2X100G OBJECT IDENTIFIER ::= { cevModuleFPRType 9 }
cevFPRNM6X10LRF OBJECT IDENTIFIER ::= { cevModuleFPRType 11 }
cevFPRNM6X10SRF OBJECT IDENTIFIER ::= { cevModuleFPRType 12 }
cevFPRNM6X1SXF  OBJECT IDENTIFIER ::= { cevModuleFPRType 13 }
cevFprUS23070   OBJECT IDENTIFIER ::= { cevModuleFPRType 14 }
cevFprUS23071   OBJECT IDENTIFIER ::= { cevModuleFPRType 15 }
cevFprUS23072   OBJECT IDENTIFIER ::= { cevModuleFPRType 16 }
cevFprUS23073   OBJECT IDENTIFIER ::= { cevModuleFPRType 17 }
cevFprUS23074   OBJECT IDENTIFIER ::= { cevModuleFPRType 18 }
cevModuleQSFP28 OBJECT IDENTIFIER ::= { cevModule 117 }
cevQSFP100GELR4 OBJECT IDENTIFIER ::= { cevModuleQSFP28 1 }
cevQSFP100GESR4 OBJECT IDENTIFIER ::= { cevModuleQSFP28 2 }
cevQSFP100GESR4S OBJECT IDENTIFIER ::= { cevModuleQSFP28 3 }
cevQSFP100GELR4S OBJECT IDENTIFIER ::= { cevModuleQSFP28 4 }
cevQSFP100GEAOC10M OBJECT IDENTIFIER ::= { cevModuleQSFP28 5 }
cevQSFP28Unknown OBJECT IDENTIFIER ::= { cevModuleQSFP28 6 }
cevQSFP100GEDWDM2 OBJECT IDENTIFIER ::= { cevModuleQSFP28 7 }
cevModuleQSFP28S OBJECT IDENTIFIER ::= { cevModule 118 }
cevQSFP100GSR4S OBJECT IDENTIFIER ::= { cevModuleQSFP28S 1 }
cevQSFP100GCWDM4S OBJECT IDENTIFIER ::= { cevModuleQSFP28S 2 }
cevQSFP100GPSM4S OBJECT IDENTIFIER ::= { cevModuleQSFP28S 3 }
cevQSFP100GLR4S OBJECT IDENTIFIER ::= { cevModuleQSFP28S 4 }
cevQSFP100GAOC1M OBJECT IDENTIFIER ::= { cevModuleQSFP28S 5 }
cevQSFP100GAOC2M OBJECT IDENTIFIER ::= { cevModuleQSFP28S 6 }
cevQSFP100GAOC3M OBJECT IDENTIFIER ::= { cevModuleQSFP28S 7 }
cevQSFP100GAOC5M OBJECT IDENTIFIER ::= { cevModuleQSFP28S 8 }
cevQSFP100GAOC7M OBJECT IDENTIFIER ::= { cevModuleQSFP28S 9 }
cevQSFP100GAOC10M OBJECT IDENTIFIER ::= { cevModuleQSFP28S 10 }
cevQSFP100GAOC15M OBJECT IDENTIFIER ::= { cevModuleQSFP28S 11 }
cevQSFP100GAOC20M OBJECT IDENTIFIER ::= { cevModuleQSFP28S 12 }
cevQSFP100GAOC25M OBJECT IDENTIFIER ::= { cevModuleQSFP28S 13 }
cevQSFP100GAOC30M OBJECT IDENTIFIER ::= { cevModuleQSFP28S 14 }
cevQSFP100GCU1M OBJECT IDENTIFIER ::= { cevModuleQSFP28S 15 }
cevQSFP100GCU2M OBJECT IDENTIFIER ::= { cevModuleQSFP28S 16 }
cevQSFP100GCU3M OBJECT IDENTIFIER ::= { cevModuleQSFP28S 17 }
cevQSFP100GCU4M OBJECT IDENTIFIER ::= { cevModuleQSFP28S 18 }
cevQSFP100GCU5M OBJECT IDENTIFIER ::= { cevModuleQSFP28S 19 }
cevQSFP4SFP25GCU1M OBJECT IDENTIFIER ::= { cevModuleQSFP28S 20 }
cevQSFP4SFP25GCU2M OBJECT IDENTIFIER ::= { cevModuleQSFP28S 21 }
cevQSFP4SFP25GCU3M OBJECT IDENTIFIER ::= { cevModuleQSFP28S 22 }
cevQSFP4SFP25GCU4M OBJECT IDENTIFIER ::= { cevModuleQSFP28S 23 }
cevQSFP4SFP25GCU5M OBJECT IDENTIFIER ::= { cevModuleQSFP28S 24 }
cevNonCiscoQSFP100GSR4 OBJECT IDENTIFIER ::= { cevModuleQSFP28S 25 }
cevNonCiscoQSFP100GLR4 OBJECT IDENTIFIER ::= { cevModuleQSFP28S 26 }
cevNonCiscoQSFP100GCWDM4 OBJECT IDENTIFIER ::= { cevModuleQSFP28S 27 }
cevNonCiscoQSFP100GCAOC OBJECT IDENTIFIER ::= { cevModuleQSFP28S 28 }
cevNonCiscoQSFP100GAOC OBJECT IDENTIFIER ::= { cevModuleQSFP28S 29 }
cevNonCiscoQSFP100GCR4 OBJECT IDENTIFIER ::= { cevModuleQSFP28S 30 }
cevQSFP100GSMSR OBJECT IDENTIFIER ::= { cevModuleQSFP28S 31 }
cevQSFPUnknown  OBJECT IDENTIFIER ::= { cevModuleQSFP28S 32 }
cevModuleNCS4K  OBJECT IDENTIFIER ::= { cevModule 119 }
cevModuleNCS4216RSP OBJECT IDENTIFIER ::= { cevModuleNCS4K 1 }
cevModuleNCS420XRSP OBJECT IDENTIFIER ::= { cevModuleNCS4K 2 }
cevModuleNCS4K4T12GPS OBJECT IDENTIFIER ::= { cevModuleNCS4K 3 }
cevModuleNCS4201RSP OBJECT IDENTIFIER ::= { cevModuleNCS4K 4 }
cevModuleASA5516Type OBJECT IDENTIFIER ::= { cevModule 120 }
cevModuleAsa5516SSD OBJECT IDENTIFIER ::= { cevModuleASA5516Type 1 }
cevModuleNCS1002 OBJECT IDENTIFIER ::= { cevModule 121 }
cevModuleNCS1002RP0 OBJECT IDENTIFIER ::= { cevModuleNCS1002 1 }
cevModuleSFP25S OBJECT IDENTIFIER ::= { cevModule 122 }
cevSFPH25GCU1M  OBJECT IDENTIFIER ::= { cevModuleSFP25S 1 }
cevSFPH25GCU2M  OBJECT IDENTIFIER ::= { cevModuleSFP25S 2 }
cevSFPH25GCU3M  OBJECT IDENTIFIER ::= { cevModuleSFP25S 3 }
cevSFPH25GCU5M  OBJECT IDENTIFIER ::= { cevModuleSFP25S 4 }
cevPort         OBJECT IDENTIFIER ::= { cevMIBObjects 10 }
cevPortUnknown  OBJECT IDENTIFIER ::= { cevPort 1 }
cevPortMCIEther OBJECT IDENTIFIER ::= { cevPort 2 }
cevPortMCISerial OBJECT IDENTIFIER ::= { cevPort 3 }
cevPortCBusSerial OBJECT IDENTIFIER ::= { cevPort 4 }
cevPortFddi     OBJECT IDENTIFIER ::= { cevPort 5 }
cevPortFddit    OBJECT IDENTIFIER ::= { cevPort 6 }
cevPortCBusTR   OBJECT IDENTIFIER ::= { cevPort 7 }
cevPortAsync    OBJECT IDENTIFIER ::= { cevPort 8 }
cevPortHSSI     OBJECT IDENTIFIER ::= { cevPort 9 }
cevPortT1       OBJECT IDENTIFIER ::= { cevPort 10 }
cevPortE1       OBJECT IDENTIFIER ::= { cevPort 11 }
cevPortBRI      OBJECT IDENTIFIER ::= { cevPort 12 }
cevPortAIP      OBJECT IDENTIFIER ::= { cevPort 13 }
cevPortCIP      OBJECT IDENTIFIER ::= { cevPort 14 }
cevPortVtyAsync OBJECT IDENTIFIER ::= { cevPort 15 }
cevPortFEIP     OBJECT IDENTIFIER ::= { cevPort 16 }
cevPortAsyncGroup OBJECT IDENTIFIER ::= { cevPort 17 }
cevPortVTemplate OBJECT IDENTIFIER ::= { cevPort 18 }
cevPortVAccess  OBJECT IDENTIFIER ::= { cevPort 19 }
cevPortT3       OBJECT IDENTIFIER ::= { cevPort 20 }
cevPortVGAnyLAN OBJECT IDENTIFIER ::= { cevPort 21 }
cevPortLance    OBJECT IDENTIFIER ::= { cevPort 22 }
cevPortATMS2000 OBJECT IDENTIFIER ::= { cevPort 23 }
cevPortSALI25   OBJECT IDENTIFIER ::= { cevPort 24 }
cevPortSonicT   OBJECT IDENTIFIER ::= { cevPort 25 }
cevPortOC3SUNI  OBJECT IDENTIFIER ::= { cevPort 26 }
cevPortOC12SUNI OBJECT IDENTIFIER ::= { cevPort 27 }
cevPortDS3SUNI  OBJECT IDENTIFIER ::= { cevPort 28 }
cevPortE3SUNI   OBJECT IDENTIFIER ::= { cevPort 29 }
cevPortDS3SUNIQUAD OBJECT IDENTIFIER ::= { cevPort 30 }
cevPortE3SUNIQUAD OBJECT IDENTIFIER ::= { cevPort 31 }
cevPortMK5025   OBJECT IDENTIFIER ::= { cevPort 32 }
cevPortTMS380   OBJECT IDENTIFIER ::= { cevPort 33 }
cevPortBSI      OBJECT IDENTIFIER ::= { cevPort 34 }
cevPortATMZR    OBJECT IDENTIFIER ::= { cevPort 35 }
cevPortHD64570  OBJECT IDENTIFIER ::= { cevPort 36 }
cevPortPCBus    OBJECT IDENTIFIER ::= { cevPort 37 }
cevPortQuiccEther OBJECT IDENTIFIER ::= { cevPort 38 }
cevPortQuiccSerial OBJECT IDENTIFIER ::= { cevPort 39 }
cevPortAMDP2    OBJECT IDENTIFIER ::= { cevPort 40 }
cevPortMIF68840 OBJECT IDENTIFIER ::= { cevPort 41 }
cevPortCYLEPA   OBJECT IDENTIFIER ::= { cevPort 42 }
cevPortS4T68360 OBJECT IDENTIFIER ::= { cevPort 43 }
cevPortIBM2692  OBJECT IDENTIFIER ::= { cevPort 44 }
cevPortMueslix  OBJECT IDENTIFIER ::= { cevPort 45 }
cevPortCD2430   OBJECT IDENTIFIER ::= { cevPort 46 }
cevPortILACC    OBJECT IDENTIFIER ::= { cevPort 47 }
cevPortNIC100   OBJECT IDENTIFIER ::= { cevPort 48 }
cevPortDCUATM   OBJECT IDENTIFIER ::= { cevPort 49 }
cevPortDCUATMPort OBJECT IDENTIFIER ::= { cevPort 50 }
cevPortTI1570   OBJECT IDENTIFIER ::= { cevPort 51 }
cevPortPOS      OBJECT IDENTIFIER ::= { cevPort 52 }
cevPortLoopBack OBJECT IDENTIFIER ::= { cevPort 53 }
cevPortLex      OBJECT IDENTIFIER ::= { cevPort 54 }
cevPortDialer   OBJECT IDENTIFIER ::= { cevPort 55 }
cevPortCIPLANAdapter OBJECT IDENTIFIER ::= { cevPort 56 }
cevPortBVI      OBJECT IDENTIFIER ::= { cevPort 57 }
cevPortOSPFVL   OBJECT IDENTIFIER ::= { cevPort 58 }
cevPortRinconSwitch OBJECT IDENTIFIER ::= { cevPort 59 }
cevPortSynALCATM OBJECT IDENTIFIER ::= { cevPort 60 }
cevPortSynALCBIGA OBJECT IDENTIFIER ::= { cevPort 61 }
cevPortSwitchTrunk OBJECT IDENTIFIER ::= { cevPort 62 }
cevPortC2KATM   OBJECT IDENTIFIER ::= { cevPort 63 }
cevPortDec21140A OBJECT IDENTIFIER ::= { cevPort 64 }
cevPortC5Ether  OBJECT IDENTIFIER ::= { cevPort 65 }
cevPortC5TR     OBJECT IDENTIFIER ::= { cevPort 66 }
cevPortEswitch  OBJECT IDENTIFIER ::= { cevPort 69 }
cevPortBITS     OBJECT IDENTIFIER ::= { cevPort 70 }
cevPortAdslCap  OBJECT IDENTIFIER ::= { cevPort 71 }
cevPortAdslDmt  OBJECT IDENTIFIER ::= { cevPort 72 }
cevPortSdsl2b1q OBJECT IDENTIFIER ::= { cevPort 73 }
cevPortEscon    OBJECT IDENTIFIER ::= { cevPort 74 }
cevPortParallel OBJECT IDENTIFIER ::= { cevPort 75 }
cevPortCipVirtual OBJECT IDENTIFIER ::= { cevPort 76 }
cevPortDs3      OBJECT IDENTIFIER ::= { cevPort 78 }
cevPortE3       OBJECT IDENTIFIER ::= { cevPort 79 }
cevPortOc3      OBJECT IDENTIFIER ::= { cevPort 80 }
cevPortHdvDsp   OBJECT IDENTIFIER ::= { cevPort 82 }
cevPortAdslFlexiDmt OBJECT IDENTIFIER ::= { cevPort 83 }
cevPortAdslFlexiCap OBJECT IDENTIFIER ::= { cevPort 84 }
cevPortAdslDmtIsdn OBJECT IDENTIFIER ::= { cevPort 85 }
cevPortRfMac    OBJECT IDENTIFIER ::= { cevPort 86 }
cevPortRfUs     OBJECT IDENTIFIER ::= { cevPort 87 }
cevPortRfDs     OBJECT IDENTIFIER ::= { cevPort 88 }
cevPortUbrClk   OBJECT IDENTIFIER ::= { cevPort 89 }
cevPortShdslTcpam OBJECT IDENTIFIER ::= { cevPort 90 }
cevPortShdslTcpamOptis OBJECT IDENTIFIER ::= { cevPort 91 }
cevPortGEIP     OBJECT IDENTIFIER ::= { cevPort 100 }
cevPortWDM      OBJECT IDENTIFIER ::= { cevPort 101 }
cevPortThru     OBJECT IDENTIFIER ::= { cevPort 102 }
cevPortFilter   OBJECT IDENTIFIER ::= { cevPort 103 }
cevPortWave     OBJECT IDENTIFIER ::= { cevPort 104 }
cevPortWavePatch OBJECT IDENTIFIER ::= { cevPort 105 }
cevPortTransparent OBJECT IDENTIFIER ::= { cevPort 106 }
cevPortDPT      OBJECT IDENTIFIER ::= { cevPort 107 }
cevPortOc12     OBJECT IDENTIFIER ::= { cevPort 108 }
cevPortGe       OBJECT IDENTIFIER ::= { cevPort 109 }
cevPortChOc12   OBJECT IDENTIFIER ::= { cevPort 110 }
cevPortChOc3Stm1 OBJECT IDENTIFIER ::= { cevPort 111 }
cevPortFilterGroup OBJECT IDENTIFIER ::= { cevPort 112 }
cevPortFilterBand OBJECT IDENTIFIER ::= { cevPort 113 }
cevPortChE1T1   OBJECT IDENTIFIER ::= { cevPort 114 }
cevPortASIMod   OBJECT IDENTIFIER ::= { cevPort 115 }
cevPortASIIn    OBJECT IDENTIFIER ::= { cevPort 116 }
cevPortASIOut   OBJECT IDENTIFIER ::= { cevPort 117 }
cevPortAimDsp   OBJECT IDENTIFIER ::= { cevPort 118 }
cevPortAtm      OBJECT IDENTIFIER ::= { cevPort 119 }
cevPortChSonet  OBJECT IDENTIFIER ::= { cevPort 120 }
cevPortChOcX    OBJECT IDENTIFIER ::= { cevPort 121 }
cevPortFe       OBJECT IDENTIFIER ::= { cevPort 123 }
cevPortDs3E3Atm OBJECT IDENTIFIER ::= { cevPort 125 }
cevPortFxs      OBJECT IDENTIFIER ::= { cevPort 126 }
cevPortFxo      OBJECT IDENTIFIER ::= { cevPort 127 }
cevPortEM       OBJECT IDENTIFIER ::= { cevPort 128 }
cevPortOc48     OBJECT IDENTIFIER ::= { cevPort 129 }
cevPortOc192    OBJECT IDENTIFIER ::= { cevPort 130 }
cevPortFibreChannel OBJECT IDENTIFIER ::= { cevPort 131 }
cevPortGigEthernet OBJECT IDENTIFIER ::= { cevPort 132 }
cevPortFibreChGigEth OBJECT IDENTIFIER ::= { cevPort 133 }
cevPortCatEthernet OBJECT IDENTIFIER ::= { cevPort 134 }
cevPortWaveOsc  OBJECT IDENTIFIER ::= { cevPort 135 }
cevPortWaveEthPhy OBJECT IDENTIFIER ::= { cevPort 136 }
cevPort10GigEthPhy OBJECT IDENTIFIER ::= { cevPort 137 }
cevPortEsconPhy OBJECT IDENTIFIER ::= { cevPort 138 }
cevPortGEFCPhy  OBJECT IDENTIFIER ::= { cevPort 139 }
cevPortVOAIn    OBJECT IDENTIFIER ::= { cevPort 140 }
cevPortVOAOut   OBJECT IDENTIFIER ::= { cevPort 141 }
cevPortVOAFilterIn OBJECT IDENTIFIER ::= { cevPort 142 }
cevPortVOAFilterOut OBJECT IDENTIFIER ::= { cevPort 143 }
cevPortVOAByPassIn OBJECT IDENTIFIER ::= { cevPort 144 }
cevPortVOAByPassOut OBJECT IDENTIFIER ::= { cevPort 145 }
cevPortGT96K    OBJECT IDENTIFIER ::= { cevPort 146 }
cevPortDSCC4    OBJECT IDENTIFIER ::= { cevPort 147 }
cevPortBaseTEther OBJECT IDENTIFIER ::= { cevPort 150 }
cevPortGESFP    OBJECT IDENTIFIER ::= { cevPort 151 }
cevPortWdmSplit OBJECT IDENTIFIER ::= { cevPort 152 }
cevPortWavePassThru OBJECT IDENTIFIER ::= { cevPort 153 }
cevPortDspPVDM  OBJECT IDENTIFIER ::= { cevPort 154 }
cevPortiScsi    OBJECT IDENTIFIER ::= { cevPort 155 }
cevPortVic2Did  OBJECT IDENTIFIER ::= { cevPort 156 }
cevPortWic1Adsl OBJECT IDENTIFIER ::= { cevPort 157 }
cevPortWic1Shdsl OBJECT IDENTIFIER ::= { cevPort 158 }
cevPortWic1Ethernet OBJECT IDENTIFIER ::= { cevPort 159 }
cevPort10GigBaseEX4 OBJECT IDENTIFIER ::= { cevPort 160 }
cevPort10GigBaseLR OBJECT IDENTIFIER ::= { cevPort 161 }
cevPort10GigBaseSX4 OBJECT IDENTIFIER ::= { cevPort 162 }
cevPort10GigBaseER OBJECT IDENTIFIER ::= { cevPort 163 }
cevPortGigUnsupported OBJECT IDENTIFIER ::= { cevPort 164 }
cevPortGigBaseZX OBJECT IDENTIFIER ::= { cevPort 165 }
cevPort10GigBaseCPX OBJECT IDENTIFIER ::= { cevPort 166 }
cevPort10GigBaseLX4 OBJECT IDENTIFIER ::= { cevPort 167 }
cevPortGigBaseLX OBJECT IDENTIFIER ::= { cevPort 168 }
cevPortGigBaseSX OBJECT IDENTIFIER ::= { cevPort 169 }
cevPortGigBaseCX OBJECT IDENTIFIER ::= { cevPort 170 }
cevPortGigBaseLH OBJECT IDENTIFIER ::= { cevPort 171 }
cevPortGigBaseT OBJECT IDENTIFIER ::= { cevPort 172 }
cevPortDslsar   OBJECT IDENTIFIER ::= { cevPort 173 }
cevPortAtm25    OBJECT IDENTIFIER ::= { cevPort 174 }
cevPortAnalogFxs OBJECT IDENTIFIER ::= { cevPort 175 }
cevPortE3Atm    OBJECT IDENTIFIER ::= { cevPort 176 }
cevPortDs3Atm   OBJECT IDENTIFIER ::= { cevPort 177 }
cevPortNetworkAnalysis OBJECT IDENTIFIER ::= { cevPort 178 }
cevPortIntrusionDetect OBJECT IDENTIFIER ::= { cevPort 180 }
cevPort10GigBaseLW OBJECT IDENTIFIER ::= { cevPort 181 }
cevPort10GigBaseEW OBJECT IDENTIFIER ::= { cevPort 182 }
cevPortGigBaseUnknown OBJECT IDENTIFIER ::= { cevPort 183 }
cevPort10GigBaseUnknown OBJECT IDENTIFIER ::= { cevPort 184 }
cevPort10GigBaseUnapproved OBJECT IDENTIFIER ::= { cevPort 185 }
cevPortGigBaseWdmRxOnly OBJECT IDENTIFIER ::= { cevPort 186 }
cevPortGigBaseDwdm3033 OBJECT IDENTIFIER ::= { cevPort 187 }
cevPortGigBaseDwdm3112 OBJECT IDENTIFIER ::= { cevPort 188 }
cevPortGigBaseDwdm3190 OBJECT IDENTIFIER ::= { cevPort 189 }
cevPortGigBaseDwdm3268 OBJECT IDENTIFIER ::= { cevPort 190 }
cevPortGigBaseDwdm3425 OBJECT IDENTIFIER ::= { cevPort 191 }
cevPortGigBaseDwdm3504 OBJECT IDENTIFIER ::= { cevPort 192 }
cevPortGigBaseDwdm3582 OBJECT IDENTIFIER ::= { cevPort 193 }
cevPortGigBaseDwdm3661 OBJECT IDENTIFIER ::= { cevPort 194 }
cevPortGigBaseDwdm3819 OBJECT IDENTIFIER ::= { cevPort 195 }
cevPortGigBaseDwdm3898 OBJECT IDENTIFIER ::= { cevPort 196 }
cevPortGigBaseDwdm3977 OBJECT IDENTIFIER ::= { cevPort 197 }
cevPortGigBaseDwdm4056 OBJECT IDENTIFIER ::= { cevPort 198 }
cevPortGigBaseDwdm4214 OBJECT IDENTIFIER ::= { cevPort 199 }
cevPortGigBaseDwdm4294 OBJECT IDENTIFIER ::= { cevPort 200 }
cevPortGigBaseDwdm4373 OBJECT IDENTIFIER ::= { cevPort 201 }
cevPortGigBaseDwdm4453 OBJECT IDENTIFIER ::= { cevPort 202 }
cevPortGigBaseDwdm4612 OBJECT IDENTIFIER ::= { cevPort 203 }
cevPortGigBaseDwdm4692 OBJECT IDENTIFIER ::= { cevPort 204 }
cevPortGigBaseDwdm4772 OBJECT IDENTIFIER ::= { cevPort 205 }
cevPortGigBaseDwdm4851 OBJECT IDENTIFIER ::= { cevPort 206 }
cevPortGigBaseDwdm5012 OBJECT IDENTIFIER ::= { cevPort 207 }
cevPortGigBaseDwdm5092 OBJECT IDENTIFIER ::= { cevPort 208 }
cevPortGigBaseDwdm5172 OBJECT IDENTIFIER ::= { cevPort 209 }
cevPortGigBaseDwdm5252 OBJECT IDENTIFIER ::= { cevPort 210 }
cevPortGigBaseDwdm5413 OBJECT IDENTIFIER ::= { cevPort 211 }
cevPortGigBaseDwdm5494 OBJECT IDENTIFIER ::= { cevPort 212 }
cevPortGigBaseDwdm5575 OBJECT IDENTIFIER ::= { cevPort 213 }
cevPortGigBaseDwdm5655 OBJECT IDENTIFIER ::= { cevPort 214 }
cevPortGigBaseDwdm5817 OBJECT IDENTIFIER ::= { cevPort 215 }
cevPortGigBaseDwdm5898 OBJECT IDENTIFIER ::= { cevPort 216 }
cevPortGigBaseDwdm5979 OBJECT IDENTIFIER ::= { cevPort 217 }
cevPortGigBaseDwdm6061 OBJECT IDENTIFIER ::= { cevPort 218 }
cevPort10GigBaseWdmRxOnly OBJECT IDENTIFIER ::= { cevPort 219 }
cevPort10GigBaseDwdm3033 OBJECT IDENTIFIER ::= { cevPort 220 }
cevPort10GigBaseDwdm3112 OBJECT IDENTIFIER ::= { cevPort 221 }
cevPort10GigBaseDwdm3190 OBJECT IDENTIFIER ::= { cevPort 222 }
cevPort10GigBaseDwdm3268 OBJECT IDENTIFIER ::= { cevPort 223 }
cevPort10GigBaseDwdm3425 OBJECT IDENTIFIER ::= { cevPort 224 }
cevPort10GigBaseDwdm3504 OBJECT IDENTIFIER ::= { cevPort 225 }
cevPort10GigBaseDwdm3582 OBJECT IDENTIFIER ::= { cevPort 226 }
cevPort10GigBaseDwdm3661 OBJECT IDENTIFIER ::= { cevPort 227 }
cevPort10GigBaseDwdm3819 OBJECT IDENTIFIER ::= { cevPort 228 }
cevPort10GigBaseDwdm3898 OBJECT IDENTIFIER ::= { cevPort 229 }
cevPort10GigBaseDwdm3977 OBJECT IDENTIFIER ::= { cevPort 230 }
cevPort10GigBaseDwdm4056 OBJECT IDENTIFIER ::= { cevPort 231 }
cevPort10GigBaseDwdm4214 OBJECT IDENTIFIER ::= { cevPort 232 }
cevPort10GigBaseDwdm4294 OBJECT IDENTIFIER ::= { cevPort 233 }
cevPort10GigBaseDwdm4373 OBJECT IDENTIFIER ::= { cevPort 234 }
cevPort10GigBaseDwdm4453 OBJECT IDENTIFIER ::= { cevPort 235 }
cevPort10GigBaseDwdm4612 OBJECT IDENTIFIER ::= { cevPort 236 }
cevPort10GigBaseDwdm4692 OBJECT IDENTIFIER ::= { cevPort 237 }
cevPort10GigBaseDwdm4772 OBJECT IDENTIFIER ::= { cevPort 238 }
cevPort10GigBaseDwdm4851 OBJECT IDENTIFIER ::= { cevPort 239 }
cevPort10GigBaseDwdm5012 OBJECT IDENTIFIER ::= { cevPort 240 }
cevPort10GigBaseDwdm5092 OBJECT IDENTIFIER ::= { cevPort 241 }
cevPort10GigBaseDwdm5172 OBJECT IDENTIFIER ::= { cevPort 242 }
cevPort10GigBaseDwdm5252 OBJECT IDENTIFIER ::= { cevPort 243 }
cevPort10GigBaseDwdm5413 OBJECT IDENTIFIER ::= { cevPort 244 }
cevPort10GigBaseDwdm5494 OBJECT IDENTIFIER ::= { cevPort 245 }
cevPort10GigBaseDwdm5575 OBJECT IDENTIFIER ::= { cevPort 246 }
cevPort10GigBaseDwdm5655 OBJECT IDENTIFIER ::= { cevPort 247 }
cevPort10GigBaseDwdm5817 OBJECT IDENTIFIER ::= { cevPort 248 }
cevPort10GigBaseDwdm5898 OBJECT IDENTIFIER ::= { cevPort 249 }
cevPort10GigBaseDwdm5979 OBJECT IDENTIFIER ::= { cevPort 250 }
cevPort10GigBaseDwdm6061 OBJECT IDENTIFIER ::= { cevPort 251 }
cevPortGigBaseBX10D OBJECT IDENTIFIER ::= { cevPort 252 }
cevPortGigBaseBX10U OBJECT IDENTIFIER ::= { cevPort 253 }
cevPortT1E1     OBJECT IDENTIFIER ::= { cevPort 254 }
cevPort2GFCPhy  OBJECT IDENTIFIER ::= { cevPort 255 }
cevPortLanWirelessApplication OBJECT IDENTIFIER ::= { cevPort 256 }
cevPortSEInternalFE OBJECT IDENTIFIER ::= { cevPort 257 }
cevPortCEInternalFE OBJECT IDENTIFIER ::= { cevPort 258 }
cevPortIpsecVpn OBJECT IDENTIFIER ::= { cevPort 259 }
cevPortSsl      OBJECT IDENTIFIER ::= { cevPort 260 }
cevPortFirewall OBJECT IDENTIFIER ::= { cevPort 261 }
cevPortDsp5441  OBJECT IDENTIFIER ::= { cevPort 263 }
cevPortDsp6415  OBJECT IDENTIFIER ::= { cevPort 264 }
cevPortHwicSerial OBJECT IDENTIFIER ::= { cevPort 265 }
cevPortAsi      OBJECT IDENTIFIER ::= { cevPort 266 }
cevPortQam      OBJECT IDENTIFIER ::= { cevPort 267 }
cevPortGigBaseBT OBJECT IDENTIFIER ::= { cevPort 268 }
cevPort100BaseUnknown OBJECT IDENTIFIER ::= { cevPort 269 }
cevPort100BaseUnapproved OBJECT IDENTIFIER ::= { cevPort 270 }
cevPort100BaseBX10D OBJECT IDENTIFIER ::= { cevPort 271 }
cevPort100BaseBX10U OBJECT IDENTIFIER ::= { cevPort 272 }
cevPort100BaseFX OBJECT IDENTIFIER ::= { cevPort 273 }
cevPort100BaseLX10 OBJECT IDENTIFIER ::= { cevPort 274 }
cevPort100BaseSX OBJECT IDENTIFIER ::= { cevPort 275 }
cevPortSM       OBJECT IDENTIFIER ::= { cevPort 276 }
cevPortT3E3     OBJECT IDENTIFIER ::= { cevPort 277 }
cevPortMultiRate OBJECT IDENTIFIER ::= { cevPort 278 }
cevPortWaveSonetPhy OBJECT IDENTIFIER ::= { cevPort 279 }
cevPortSDCC     OBJECT IDENTIFIER ::= { cevPort 280 }
cevPortAdslAnnexA OBJECT IDENTIFIER ::= { cevPort 281 }
cevPortAdslAnnexB OBJECT IDENTIFIER ::= { cevPort 282 }
cevPort10GigBaseZR OBJECT IDENTIFIER ::= { cevPort 285 }
cevPort10GigBaseCX4 OBJECT IDENTIFIER ::= { cevPort 286 }
cevPort10GigBaseSR OBJECT IDENTIFIER ::= { cevPort 287 }
cevPortGigBaseCwdm1610 OBJECT IDENTIFIER ::= { cevPort 288 }
cevPortGigBaseCwdm1590 OBJECT IDENTIFIER ::= { cevPort 289 }
cevPortGigBaseCwdm1550 OBJECT IDENTIFIER ::= { cevPort 290 }
cevPortGigBaseCwdm1530 OBJECT IDENTIFIER ::= { cevPort 291 }
cevPortGigBaseCwdm1510 OBJECT IDENTIFIER ::= { cevPort 292 }
cevPortGigBaseCwdm1490 OBJECT IDENTIFIER ::= { cevPort 293 }
cevPortGigBaseCwdm1470 OBJECT IDENTIFIER ::= { cevPort 294 }
cevPortGigBaseCwdm1570 OBJECT IDENTIFIER ::= { cevPort 295 }
cevPortUSB      OBJECT IDENTIFIER ::= { cevPort 296 }
cevPortSslVpn   OBJECT IDENTIFIER ::= { cevPort 297 }
cevPortCableModem OBJECT IDENTIFIER ::= { cevPort 298 }
cevNmeApaPort   OBJECT IDENTIFIER ::= { cevPort 299 }
cevPort10GigBase OBJECT IDENTIFIER ::= { cevPort 300 }
cevPort10GigBaseLRM OBJECT IDENTIFIER ::= { cevPort 301 }
cevPortdot11abg OBJECT IDENTIFIER ::= { cevPort 302 }
cevPortDti      OBJECT IDENTIFIER ::= { cevPort 303 }
cevPort10GigSFPPlus OBJECT IDENTIFIER ::= { cevPort 304 }
cevPortCscPort  OBJECT IDENTIFIER ::= { cevPort 305 }
cevPortGEXFP    OBJECT IDENTIFIER ::= { cevPort 306 }
cevPortGigBaseDwdm6141 OBJECT IDENTIFIER ::= { cevPort 307 }
cevPortGigBaseDwdm5736 OBJECT IDENTIFIER ::= { cevPort 308 }
cevPortGigBaseDwdm5332 OBJECT IDENTIFIER ::= { cevPort 309 }
cevPortGigBaseDwdm4931 OBJECT IDENTIFIER ::= { cevPort 310 }
cevPortGigBaseDwdm4532 OBJECT IDENTIFIER ::= { cevPort 311 }
cevPortGigBaseDwdm4134 OBJECT IDENTIFIER ::= { cevPort 312 }
cevPortGigBaseDwdm3739 OBJECT IDENTIFIER ::= { cevPort 313 }
cevPortGigBaseDwdm3346 OBJECT IDENTIFIER ::= { cevPort 314 }
cevPort10GigEthernet OBJECT IDENTIFIER ::= { cevPort 315 }
cevPortSEInternal OBJECT IDENTIFIER ::= { cevPort 316 }
cevPortGigBaseEX OBJECT IDENTIFIER ::= { cevPort 317 }
cevPort40GigEthernet OBJECT IDENTIFIER ::= { cevPort 318 }
cevPortAces     OBJECT IDENTIFIER ::= { cevPort 319 }
cevPort100GigEthernet OBJECT IDENTIFIER ::= { cevPort 320 }
cevPort40GigQSFPPlus OBJECT IDENTIFIER ::= { cevPort 321 }
cevPort100GECFP OBJECT IDENTIFIER ::= { cevPort 322 }
cevPortPlcG     OBJECT IDENTIFIER ::= { cevPort 323 }
cevPortWimaxG   OBJECT IDENTIFIER ::= { cevPort 324 }
cevPort3gCdmaG  OBJECT IDENTIFIER ::= { cevPort 325 }
cevPort3gGsmG   OBJECT IDENTIFIER ::= { cevPort 326 }
cevPortWpanG    OBJECT IDENTIFIER ::= { cevPort 327 }
cevPortDsp      OBJECT IDENTIFIER ::= { cevPort 328 }
cevPortCXP      OBJECT IDENTIFIER ::= { cevPort 331 }
cevPortCPAK     OBJECT IDENTIFIER ::= { cevPort 332 }
cevPortConsole  OBJECT IDENTIFIER ::= { cevPort 333 }
cevPortAlarmDSUB15 OBJECT IDENTIFIER ::= { cevPort 334 }
cevPortSseBreakout100GePort OBJECT IDENTIFIER ::= { cevPort 337 }
cevPortSseBreakout10GePort OBJECT IDENTIFIER ::= { cevPort 338 }
cevPortCisco10GeSFPPlusPOZR OBJECT IDENTIFIER ::= { cevPort 339 }
cevPortCisco10GeSFPPlusPOER OBJECT IDENTIFIER ::= { cevPort 340 }
cevPortCisco10GeSFPPlusPOSRX OBJECT IDENTIFIER ::= { cevPort 341 }
cevPortCisco10GeSFPPlusPOLRX OBJECT IDENTIFIER ::= { cevPort 342 }
cevPortCisco10GeSFPPlusPOLR OBJECT IDENTIFIER ::= { cevPort 343 }
cevPortCisco10GeSFPPlusPOSR OBJECT IDENTIFIER ::= { cevPort 344 }
cevPortPHwicSerial OBJECT IDENTIFIER ::= { cevPort 346 }
cevPortPT1E1    OBJECT IDENTIFIER ::= { cevPort 347 }
cevPortPHdvDsp  OBJECT IDENTIFIER ::= { cevPort 348 }
cevPortSerial   OBJECT IDENTIFIER ::= { cevPort 350 }
cevPortCPAKLR10 OBJECT IDENTIFIER ::= { cevPort 351 }
cevPortAdslAnnexM OBJECT IDENTIFIER ::= { cevPort 352 }
cevPortNCS4KUSB OBJECT IDENTIFIER ::= { cevPort 354 }
cevPortNCS4KGigEthernet OBJECT IDENTIFIER ::= { cevPort 355 }
cevPortNCS4KDWDMOptical OBJECT IDENTIFIER ::= { cevPort 356 }
cevPortC3794    OBJECT IDENTIFIER ::= { cevPort 358 }
cevPort25GigEthernet OBJECT IDENTIFIER ::= { cevPort 359 }
cevStack        OBJECT IDENTIFIER ::= { cevMIBObjects 11 }
cevStackUnknown OBJECT IDENTIFIER ::= { cevStack 1 }
cevStackCat37xx OBJECT IDENTIFIER ::= { cevStack 2 }
cevCat65xxVirtualSwitch OBJECT IDENTIFIER ::= { cevStack 3 }
cevCbs3120Stack OBJECT IDENTIFIER ::= { cevStack 5 }
cevC29xxStack   OBJECT IDENTIFIER ::= { cevStack 11 }
cevStackIosXrMultichassis OBJECT IDENTIFIER ::= { cevStack 12 }
cevStackCat4xxxVirtualSwitchStack OBJECT IDENTIFIER ::= { cevStack 13 }
cevStackFex     OBJECT IDENTIFIER ::= { cevStack 14 }
cevStackC68xxVirSwitch OBJECT IDENTIFIER ::= { cevStack 20 }
cevC35xxStack   OBJECT IDENTIFIER ::= { cevStack 21 }
cevMidplane     OBJECT IDENTIFIER ::= { cevMIBObjects 12 }
cevMidplaneUmg9820 OBJECT IDENTIFIER ::= { cevMidplane 1 }
cevTCAMType     OBJECT IDENTIFIER ::= { cevMIBObjects 13 }


END
