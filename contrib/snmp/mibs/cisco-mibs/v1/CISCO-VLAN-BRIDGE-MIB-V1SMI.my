-- automatically generated by mosy 7.1 #423 (jjohnson-ss20), do not edit!

CISCO-VLAN-BRIDGING-MIB DEFINITIONS ::= BEGIN


IMPORTS
	OBJECT-TYPE
		FROM RFC-1212
	vtpVlanIndex
		FROM CISCO-VTP-MIB
	ciscoMgmt
		FROM CISCO-SMI;

-- created from ciscoVlanBridgingMIB (9609120000Z)

ciscoVlanBridgingMIB OBJECT IDENTIFIER ::= { ciscoMgmt  56 }

ciscoVlanBridgingMIBObjects OBJECT IDENTIFIER ::= { ciscoVlanBridgingMIB  1 }

cvbStp OBJECT IDENTIFIER ::= { ciscoVlanBridgingMIBObjects  1 }

cvbStpTable OBJECT-TYPE
    SYNTAX  SEQUENCE OF CiscoVlanStpEntry
    ACCESS  not-accessible
    STATUS  mandatory
    DESCRIPTION
           "This table contains device STP status information
            for each VLAN."
    ::= { cvbStp  1 }

cvbStpEntry OBJECT-TYPE
    SYNTAX  CiscoVlanStpEntry
    ACCESS  not-accessible
    STATUS  mandatory
    DESCRIPTION
           "Device STP status for specified VLAN."
    INDEX   { vtpVlanIndex }
    ::= { cvbStpTable  1 }

CiscoVlanStpEntry ::=
    SEQUENCE {
        cvbStpForwardingMap
            OCTET STRING
    }

cvbStpForwardingMap OBJECT-TYPE
    SYNTAX  OCTET STRING
    ACCESS  read-only
    STATUS  mandatory
    DESCRIPTION
           "An indication of which ports are forwarding by spanning tree
            for the specified VLAN. The octet string contains one bit
            per port on the bridge for the specified VLAN. 

            Each bit within the octet string represents one port of the
            device.  The ordering of ports represented within the octet
            string is in the same order as in the RFC 1493 dot1dStpPortTable.

            The bit value interpretation is related to RFC 1493
            dot1dStpPortState values is as follows:
               1 = forwarding
               0 = disabled, blocking, listening, learning, broken, or
                   nonexistent"
    ::= { cvbStpEntry  2 }

ciscoVlanBridgingMIBConformance OBJECT IDENTIFIER ::= { ciscoVlanBridgingMIB  3 }

ciscoVlanBridgingMIBCompliances OBJECT IDENTIFIER ::= { ciscoVlanBridgingMIBConformance  1 }

ciscoVlanBridgingMIBGroups OBJECT IDENTIFIER ::= { ciscoVlanBridgingMIBConformance  2 }

ciscoVlanBridgingMIBCompliance OBJECT IDENTIFIER ::= { ciscoVlanBridgingMIBCompliances  1 }

ciscoVlanBridgingMIBGroup OBJECT IDENTIFIER ::= { ciscoVlanBridgingMIBGroups  1 }

END
