-- MIB file created 05-Sep-2004 08:51:21, by
--   SMICng version 2.2.11-beta(PRO)(Solaris), January 20, 2001. Enterprise key cisco.com

CISCO-ATM-CONN-INFO-MIB DEFINITIONS ::= BEGIN

-- From file: "CISCO-ATM-CONN-INFO-MIB.my"
-- Compile options "4 7 F H N W 03 06 0B 0G 0N 0T"

IMPORTS
    ifIndex
            FROM IF-MIB
    ciscoMgmt
            FROM CISCO-SMI
    Gauge
            FROM RFC1155-SMI
    OBJECT-TYPE
            FROM RFC-1212;

ciscoAtmConnInfoMIB OBJECT IDENTIFIER ::= { ciscoMgmt 9999 }
-- MODULE-IDENTITY
--  LastUpdated
--    200306160000Z
--  OrgName
--    Cisco Systems, Inc.
--  ContactInfo
--           Cisco Systems
--            Customer Service
--    
--    Postal: 170 W Tasman Drive
--            San Jose, CA  95134
--            USA
--    
--            Tel: +1 800 553-NETS
--    
--    E-mail: cs-wanatm@cisco.com
--  Descr
--    The MIB module for providing the parameters 
--     configured on an ATM interface.
--     Terminologies used:
--     SVC  : Switched Virtual Channel
--     SPVC : Soft Permanent Virtual Circuit
--     SPVP : Soft Permanent Virtual Path
--     SVPC : Switched Virtual Path Connection
--     DAX  : Connection with endpoints on the same 
--            ATM switch
--     P2p  : Point-to-point connection
--     P2mp : Point-to-multi-point connection
--     Root : The root of point-to-multipoint connection,
--            which is associated with a VPI/VCI
--     Leaf : Usually one point-to-multipoint connection
--            consists of one root and one or more leaves. 
--            Leaf is the branch point for point 
--            to multipoint connection that is 
--            associated with a VPI/VCI
--     Party: One or more party is associated with each 
--            leaf, all parties are associated with 
--            the same VPI/VCI that its leaf belongs to
--     
--     Source           Via Node           Destination
--     =======          =======            =======
--    A|     |B        C|     |D          E|     |F
--    ==+=====+==========+=====+============+=====+==
--     |     |          |     |            |     |     
--     =======          =======            =======
--     Each active connection has two terminating 
--     endpoints. 
--     In the above diagram, Endpoints A and F are 
--     terminating.
--     Of these the master endpoint of the connection 
--     initiates the routing of the call and is 
--     considered the calling party. The slave endpoint
--     is the called party which receives calls and is 
--     the destination of a call.
--     Any endpoints that are created either on Via nodes 
--     or on the node with the terminating endpoint in 
--     order to have a complete connections between 
--     endpoints A and F are said to be intermediate 
--     endpoints. In the above diagram, endpoints B, C, 
--     D and E are intermediate endpoints.
--     
--  RevDate
--    200306160000Z
--  RevDescr
--    Initial version of the MIB.

caciMIBNotifications OBJECT IDENTIFIER ::= { ciscoAtmConnInfoMIB 0 }
caciMIBObjects  OBJECT IDENTIFIER ::= { ciscoAtmConnInfoMIB 1 }
caciAtmConnInfo OBJECT IDENTIFIER ::= { caciMIBObjects 1 }
caciIfInfo      OBJECT IDENTIFIER ::= { caciAtmConnInfo 1 }
caciP2pConns    OBJECT IDENTIFIER ::= { caciAtmConnInfo 2 }
caciP2pEndpoints OBJECT IDENTIFIER ::= { caciAtmConnInfo 3 }
caciP2pIntEndpoints OBJECT IDENTIFIER ::= { caciAtmConnInfo 4 }
caciP2mpConns   OBJECT IDENTIFIER ::= { caciAtmConnInfo 5 }
caciGeneric     OBJECT IDENTIFIER ::= { caciAtmConnInfo 6 }
ciscoAtmConnInfoMIBConformance OBJECT IDENTIFIER ::= { ciscoAtmConnInfoMIB 2 }
ciscoAtmConnInfoMIBCompliances OBJECT IDENTIFIER ::= { ciscoAtmConnInfoMIBConformance 1 }
ciscoAtmConnInfoMIBGroups OBJECT IDENTIFIER ::= { ciscoAtmConnInfoMIBConformance 2 }

CaciGeneralConnEPCategory ::= INTEGER {
        caciP2p(1),
        caciP2mpR(2),
        caciP2mpL(3),
        caciP2mpPty(4)
        }
-- TEXTUAL-CONVENTION
--  Status
--    mandatory
--  Descr
--    General category for connection or endpoint types 
--     supported on the switch.
--     caciP2p    : Point to point connection
--     caciP2mpR  : Point to multi point root connection
--     caciP2mpL  : Point to multi point leaf connection
--     caciP2mpPty: Point to multi point party connection

CaciP2pConnCategory ::= INTEGER {
        caciP2pSvcc(1),
        caciP2pSvpc(2),
        caciP2pSpvcD(3),
        caciP2pSpvpD(4),
        caciP2pSpvcR(5),
        caciP2pSpvpR(6)
        }
-- TEXTUAL-CONVENTION
--  Status
--    mandatory
--  Descr
--    The connection category.
--     caciP2pSvcc : Point to point Svc connection
--     caciP2pSvpc : Point to point Svpc connection
--     caciP2pSpvcD: Point to point Spvc DAX connection
--     caciP2pSpvpD: Point to point Spvp DAX connection
--     caciP2pSpvcR: Point to point SPVC Routed connection
--     caciP2pSpvpR: Point to point Spvp Routed connection

CaciP2pEndpointCategory ::= INTEGER {
        caciP2pSpvcRPEP(1),
        caciP2pSpvcRNPEP(2),
        caciP2pSpvpRPEP(3),
        caciP2pSpvpRNPEP(4),
        caciP2pSpvcDEP(5),
        caciP2pSpvpDEP(6)
        }
-- TEXTUAL-CONVENTION
--  Status
--    mandatory
--  Descr
--    The terminating endpoint category.
--     caciP2pSpvcRPEP : Point to point Spvc 
--                       Routed Persistent endpoint
--     caciP2pSpvcRNPEP: Point to point Spvc 
--                       Routed Non-persistent endpoint
--     caciP2pSpvpRPEP : Point to point Spvp 
--                       Routed Persistent endpoint
--     caciP2pSpvpRNPEP: Point to point Spvp 
--                       Routed Non-persistent endpoint
--     caciP2pSpvcDEP  : Point to point Spvc 
--                       DAX endpoint
--     caciP2pSpvpDEP  : Point to point Spvp 
--                       DAX endpoint

CaciP2pIntEndpointCategory ::= INTEGER {
        caciP2pSvccIntEP(1),
        caciP2pSvpcIntEP(2),
        caciP2pSpvcRIntEP(3),
        caciP2pSpvpRIntEP(4)
        }
-- TEXTUAL-CONVENTION
--  Status
--    mandatory
--  Descr
--    The intermediate endpoint category.
--     caciP2pSvccIntEP : Point to point Svc 
--                        intermediate endpoint
--     caciP2pSvpcIntEP : Point to point Svpc 
--                        intermediate endpoint
--     caciP2pSpvcRIntEP: Point to point Spvc Routed 
--                        intermediate endpoint
--     caciP2pSpvpRIntEP: Point to point Spvp Routed 
--                        intermediate endpoint

CaciP2mpConnCategory ::= INTEGER {
        caciP2mpSvcRoot(1),
        caciP2mpSvcLeaf(2),
        caciP2mpSvcParty(3),
        caciP2mpSvpcRoot(4),
        caciP2mpSvpcLeaf(5),
        caciP2mpSvpcParty(6),
        caciP2mpSpvcP(7),
        caciP2mpSpvcNP(8),
        caciP2mpSpvcAct(9),
        caciP2mpSpvpP(10),
        caciP2mpSpvpNP(11),
        caciP2mpSpvpAct(12),
        caciP2mpSpvcPaP(13),
        caciP2mpSpvcPaAct(14),
        caciP2mpSpvpPaP(15),
        caciP2mpSpvpPaAct(16)
        }
-- TEXTUAL-CONVENTION
--  Status
--    mandatory
--  Descr
--    The point to multipoint connection category.
--     caciP2mpSvcRoot  : Point to multipoint Svc 
--                        root connection
--     caciP2mpSvcLeaf  : Point to multipoint Svc 
--                        leaf connection
--     caciP2mpSvcParty : Point to multipoint Svc 
--                        party connection
--     caciP2mpSvpcRoot : Point to multipoint Svpc 
--                        root connection
--     caciP2mpSvpcLeaf : Point to multipoint Svpc 
--                        leaf connection
--     caciP2mpSvpcParty: Point to multipoint Svpc 
--                        party connection
--     caciP2mpSpvcP    : Point to multipoint Spvc
--                        persistent connection
--     caciP2mpSpvcNP   : Point to multipoint Spvc
--                        non-persistent connection
--     caciP2mpSpvcAct  : Point to multipoint Spvc
--                        Active connection
--     caciP2mpSpvpP    : Point to multipoint Spvp
--                        persistent connection
--     caciP2mpSpvpNP   : Point to multipoint Spvp
--                        non-persistent connection
--     caciP2mpSpvpAct  : Point to multipoint Spvp
--                        active connection
--     caciP2mpSpvcPaP  : Point to multipoint Spvc
--                        party persistent connection
--     caciP2mpSpvcPaAct: Point to multipoint Spvc
--                        party active connection
--     caciP2mpSpvpPaP  : Point to multipoint Spvp
--                        party persistent connection
--     caciP2mpSpvpPaAct: Point to multipoint Spvp 
--                        party active connection

CaciATMEndpointCategory ::= INTEGER {
        caciTotalSpvc(1),
        caciP2pTotalInt(2),
        caciTotalMaster(3),
        caciTotalSlave(4)
        }
-- TEXTUAL-CONVENTION
--  Status
--    mandatory
--  Descr
--    The connection category.
--     caciTotalSpvc   : Total SPVC endpoints configured 
--                       on the ATM switch
--     caciP2pTotalInt : Total intermediate endpoints
--                       configured on the ATM switch
--     caciTotalMaster : Total master endpoints configured
--                       on the ATM switch
--     caciTotalSlave  : Total slave endpoints configured
--                       on the ATM switch

caciP2pTotalConfConns OBJECT-TYPE
    SYNTAX Gauge
    ACCESS read-only
    STATUS mandatory
    DESCRIPTION
        "This object specifies the total point to point
         connections that are configured on this ATM switch."
    ::= { caciGeneric 1 }

caciP2pMaxPossibleConns OBJECT-TYPE
    SYNTAX Gauge
    ACCESS read-only
    STATUS mandatory
    DESCRIPTION
        "This object specifies the upper limit of the 
         point to point and point to multipoint 
         connections that are allowed to be configured
         on this ATM switch."
    ::= { caciGeneric 2 }

caciMaxPossibleEndpoints OBJECT-TYPE
    SYNTAX Gauge
    ACCESS read-only
    STATUS mandatory
    DESCRIPTION
        "This object specifies the upper limit of all the 
         possible endpoints that are allowed to be 
         configured on this ATM switch."
    ::= { caciGeneric 3 }

caciGenericEndpointTable OBJECT-TYPE
    SYNTAX SEQUENCE OF CaciGenericEndpointEntry
    ACCESS not-accessible
    STATUS mandatory
    DESCRIPTION
        "The table contains number of connection per 
         CaciATMEndpointCategory."
    ::= { caciGeneric 4 }

caciGenericEndpointEntry OBJECT-TYPE
    SYNTAX CaciGenericEndpointEntry
    ACCESS not-accessible
    STATUS mandatory
    DESCRIPTION
        "An entry in the table specifying the number 
         of connections for the corresponding 
         CaciATMEndpointCategory."
    INDEX { caciATMEndpointCategory }
    ::= { caciGenericEndpointTable 1 }

CaciGenericEndpointEntry ::= SEQUENCE {
    caciATMEndpointCategory CaciATMEndpointCategory,
    caciTotalEndpoints Gauge
    }

caciATMEndpointCategory OBJECT-TYPE
    SYNTAX CaciATMEndpointCategory
--    Rsyntax INTEGER {
--        caciTotalSpvc(1),
--        caciP2pTotalInt(2),
--        caciTotalMaster(3),
--        caciTotalSlave(4)
--        }
    ACCESS not-accessible
    STATUS mandatory
    DESCRIPTION
        "Endpoint category corresponding to 
         CaciATMEndpointCategory."
    ::= { caciGenericEndpointEntry 1 }

caciTotalEndpoints OBJECT-TYPE
    SYNTAX Gauge
    ACCESS read-only
    STATUS mandatory
    DESCRIPTION
        "The total number of endpoints of 
         caciATMEndpointCategory configured 
         on this ATM switch."
    ::= { caciGenericEndpointEntry 2 }

caciConnInfoTable OBJECT-TYPE
    SYNTAX SEQUENCE OF CaciConnInfoEntry
    ACCESS not-accessible
    STATUS mandatory
    DESCRIPTION
        "The Connection Statistics table. 
         This table has the number of connections per interface."
    ::= { caciIfInfo 1 }

caciConnInfoEntry OBJECT-TYPE
    SYNTAX CaciConnInfoEntry
    ACCESS not-accessible
    STATUS mandatory
    DESCRIPTION
        "An entry in the caciConnInfoTable. 
         Each entry in ifTable with ifType 
         values: atm(37), atmLogical(80) or atmVirtual(149) 
         has an associated entry in this table."
    INDEX { ifIndex, caciGeneralConnEPCategory }
    ::= { caciConnInfoTable 1 }

CaciConnInfoEntry ::= SEQUENCE {
    caciGeneralConnEPCategory CaciGeneralConnEPCategory,
    caciNumUsedConns Gauge
    }

caciGeneralConnEPCategory OBJECT-TYPE
    SYNTAX CaciGeneralConnEPCategory
--    Rsyntax INTEGER {
--        caciP2p(1),
--        caciP2mpR(2),
--        caciP2mpL(3),
--        caciP2mpPty(4)
--        }
    ACCESS not-accessible
    STATUS mandatory
    DESCRIPTION
        "The general connection or endpoint category
         on this ATM switch."
    ::= { caciConnInfoEntry 1 }

caciNumUsedConns OBJECT-TYPE
    SYNTAX Gauge
    ACCESS read-only
    STATUS mandatory
    DESCRIPTION
        "This object specifies the total number of used 
         connections of type caciGeneralConnEPCategory 
         on this interface."
    ::= { caciConnInfoEntry 2 }

caciP2pConnTable OBJECT-TYPE
    SYNTAX SEQUENCE OF CaciP2pConnEntry
    ACCESS not-accessible
    STATUS mandatory
    DESCRIPTION
        "The table contains number of connection per 
         CaciP2pConnCategory."
    ::= { caciP2pConns 1 }

caciP2pConnEntry OBJECT-TYPE
    SYNTAX CaciP2pConnEntry
    ACCESS not-accessible
    STATUS mandatory
    DESCRIPTION
        "An entry in the table specifying the number 
         of connections for the corresponding CaciP2pConnCategory."
    INDEX { caciP2pConnectionCategory }
    ::= { caciP2pConnTable 1 }

CaciP2pConnEntry ::= SEQUENCE {
    caciP2pConnectionCategory CaciP2pConnCategory,
    caciP2pTotalConns Gauge
    }

caciP2pConnectionCategory OBJECT-TYPE
    SYNTAX CaciP2pConnCategory
--    Rsyntax INTEGER {
--        caciP2pSvcc(1),
--        caciP2pSvpc(2),
--        caciP2pSpvcD(3),
--        caciP2pSpvpD(4),
--        caciP2pSpvcR(5),
--        caciP2pSpvpR(6)
--        }
    ACCESS not-accessible
    STATUS mandatory
    DESCRIPTION
        "The connection category."
    ::= { caciP2pConnEntry 1 }

caciP2pTotalConns OBJECT-TYPE
    SYNTAX Gauge
    ACCESS read-only
    STATUS mandatory
    DESCRIPTION
        "The total number of P2p connections of type 
         CaciP2pConnCategory configured on this ATM switch."
    ::= { caciP2pConnEntry 2 }

caciP2pEndpointTable OBJECT-TYPE
    SYNTAX SEQUENCE OF CaciP2pEndpointEntry
    ACCESS not-accessible
    STATUS mandatory
    DESCRIPTION
        "The table contains number of endpoints per 
         CaciP2pEndpointCategory."
    ::= { caciP2pEndpoints 1 }

caciP2pEndpointEntry OBJECT-TYPE
    SYNTAX CaciP2pEndpointEntry
    ACCESS not-accessible
    STATUS mandatory
    DESCRIPTION
        "An entry in the table specifying the number 
         of endpoints for the corresponding 
         CaciP2pEndpointCategory."
    INDEX { caciP2pEndptCategory }
    ::= { caciP2pEndpointTable 1 }

CaciP2pEndpointEntry ::= SEQUENCE {
    caciP2pEndptCategory CaciP2pEndpointCategory,
    caciP2pTotalConfEndpoints Gauge
    }

caciP2pEndptCategory OBJECT-TYPE
    SYNTAX CaciP2pEndpointCategory
--    Rsyntax INTEGER {
--        caciP2pSpvcRPEP(1),
--        caciP2pSpvcRNPEP(2),
--        caciP2pSpvpRPEP(3),
--        caciP2pSpvpRNPEP(4),
--        caciP2pSpvcDEP(5),
--        caciP2pSpvpDEP(6)
--        }
    ACCESS not-accessible
    STATUS mandatory
    DESCRIPTION
        "The point to point endpoint category."
    ::= { caciP2pEndpointEntry 1 }

caciP2pTotalConfEndpoints OBJECT-TYPE
    SYNTAX Gauge
    ACCESS read-only
    STATUS mandatory
    DESCRIPTION
        "The number of total P2p enpoints of type 
         CaciP2pEndpointCategory configured on this ATM switch."
    ::= { caciP2pEndpointEntry 2 }

caciP2pIntEndpointTable OBJECT-TYPE
    SYNTAX SEQUENCE OF CaciP2pIntEndpointEntry
    ACCESS not-accessible
    STATUS mandatory
    DESCRIPTION
        "The table contains number of endpoints per 
         CaciP2pIntEndpointCategory."
    ::= { caciP2pIntEndpoints 1 }

caciP2pIntEndpointEntry OBJECT-TYPE
    SYNTAX CaciP2pIntEndpointEntry
    ACCESS not-accessible
    STATUS mandatory
    DESCRIPTION
        "An entry in the table specifying the number 
         of endpoints for the corresponding 
         CaciP2pIntEndpointCategory."
    INDEX { caciP2pIntEndptCategory }
    ::= { caciP2pIntEndpointTable 1 }

CaciP2pIntEndpointEntry ::= SEQUENCE {
    caciP2pIntEndptCategory CaciP2pIntEndpointCategory,
    caciP2pTotalIntEndpoints Gauge
    }

caciP2pIntEndptCategory OBJECT-TYPE
    SYNTAX CaciP2pIntEndpointCategory
--    Rsyntax INTEGER {
--        caciP2pSvccIntEP(1),
--        caciP2pSvpcIntEP(2),
--        caciP2pSpvcRIntEP(3),
--        caciP2pSpvpRIntEP(4)
--        }
    ACCESS not-accessible
    STATUS mandatory
    DESCRIPTION
        "The point to point intermediate endpoint category."
    ::= { caciP2pIntEndpointEntry 1 }

caciP2pTotalIntEndpoints OBJECT-TYPE
    SYNTAX Gauge
    ACCESS read-only
    STATUS mandatory
    DESCRIPTION
        "The total number of P2p intermediate enpoints of type 
         CaciP2pIntEndpointCategory present on this ATM switch."
    ::= { caciP2pIntEndpointEntry 2 }

caciP2mpConnTable OBJECT-TYPE
    SYNTAX SEQUENCE OF CaciP2mpConnEntry
    ACCESS not-accessible
    STATUS mandatory
    DESCRIPTION
        "The table contains number of connection per 
         CaciP2mpConnCategory."
    ::= { caciP2mpConns 1 }

caciP2mpConnEntry OBJECT-TYPE
    SYNTAX CaciP2mpConnEntry
    ACCESS not-accessible
    STATUS mandatory
    DESCRIPTION
        "An entry in the table specifying the number 
         of connections for the corresponding 
         CaciP2mpConnCategory."
    INDEX { caciP2mpConnectionCategory }
    ::= { caciP2mpConnTable 1 }

CaciP2mpConnEntry ::= SEQUENCE {
    caciP2mpConnectionCategory CaciP2mpConnCategory,
    caciP2mpTotalConfConns Gauge
    }

caciP2mpConnectionCategory OBJECT-TYPE
    SYNTAX CaciP2mpConnCategory
--    Rsyntax INTEGER {
--        caciP2mpSvcRoot(1),
--        caciP2mpSvcLeaf(2),
--        caciP2mpSvcParty(3),
--        caciP2mpSvpcRoot(4),
--        caciP2mpSvpcLeaf(5),
--        caciP2mpSvpcParty(6),
--        caciP2mpSpvcP(7),
--        caciP2mpSpvcNP(8),
--        caciP2mpSpvcAct(9),
--        caciP2mpSpvpP(10),
--        caciP2mpSpvpNP(11),
--        caciP2mpSpvpAct(12),
--        caciP2mpSpvcPaP(13),
--        caciP2mpSpvcPaAct(14),
--        caciP2mpSpvpPaP(15),
--        caciP2mpSpvpPaAct(16)
--        }
    ACCESS not-accessible
    STATUS mandatory
    DESCRIPTION
        "The point to multi point connection category."
    ::= { caciP2mpConnEntry 1 }

caciP2mpTotalConfConns OBJECT-TYPE
    SYNTAX Gauge
    ACCESS read-only
    STATUS mandatory
    DESCRIPTION
        "The total number of P2mp connections of type 
         CaciP2mpConnCategory configured on this ATM switch."
    ::= { caciP2mpConnEntry 2 }

ciscoConnInfoConfMIBGroup OBJECT IDENTIFIER ::= { ciscoAtmConnInfoMIBGroups 1 }
-- OBJECT-GROUP
--  Status
--    mandatory
--  Descr
--    Objects used for representing connection 
--     statistical details about an interface.
--  objects
--    caciNumUsedConns

ciscoP2pConnsMIBGroup OBJECT IDENTIFIER ::= { ciscoAtmConnInfoMIBGroups 2 }
-- OBJECT-GROUP
--  Status
--    mandatory
--  Descr
--    Objects used for representing the point to point 
--     connections of a particular CaP2pConnCategory.
--  objects
--    caciP2pTotalConns

ciscoP2pEndpointsMIBGroup OBJECT IDENTIFIER ::= { ciscoAtmConnInfoMIBGroups 3 }
-- OBJECT-GROUP
--  Status
--    mandatory
--  Descr
--    Objects used for representing the point to point 
--     endpoints of a particular CaP2pEndpointCategory.
--  objects
--    caciP2pTotalConfEndpoints

ciscoP2pIntEndpointsMIBGroup OBJECT IDENTIFIER ::= { ciscoAtmConnInfoMIBGroups 4 }
-- OBJECT-GROUP
--  Status
--    mandatory
--  Descr
--    Objects used for representing the point to point 
--     intermediate endpoints of a particular 
--     CaP2pIntEndpointCategory.
--  objects
--    caciP2pTotalIntEndpoints

ciscoP2mpConnsMIBGroup OBJECT IDENTIFIER ::= { ciscoAtmConnInfoMIBGroups 5 }
-- OBJECT-GROUP
--  Status
--    mandatory
--  Descr
--    Objects used for representing the point to multi point 
--     connections of a particular CaP2mpConnCategory.
--  objects
--    caciP2mpTotalConfConns

ciscoTotalConnsMIBGroup OBJECT IDENTIFIER ::= { ciscoAtmConnInfoMIBGroups 6 }
-- OBJECT-GROUP
--  Status
--    mandatory
--  Descr
--    Objects used for representing the total connections
--     on the ATM switch.
--  objects
--    caciP2pTotalConfConns, caciP2pMaxPossibleConns

ciscoTotalEndpointsMIBGroup OBJECT IDENTIFIER ::= { ciscoAtmConnInfoMIBGroups 7 }
-- OBJECT-GROUP
--  Status
--    mandatory
--  Descr
--    Objects used for representing the total endpoints 
--     on the ATM switch.
--  objects
--    caciMaxPossibleEndpoints, caciTotalEndpoints

ciscoAtmConnInfoMIBCompliance OBJECT IDENTIFIER ::= { ciscoAtmConnInfoMIBCompliances 1 }
-- MODULE-COMPLIANCE
--  Status
--    mandatory
--  Descr
--    The Compliance statement for ciscoAtm management group.
--  Module
--    >>current<<
--   MandGroup
--    ciscoConnInfoConfMIBGroup
--   MandGroup
--    ciscoTotalConnsMIBGroup
--   MandGroup
--    ciscoTotalEndpointsMIBGroup
--   OptGroup
--    ciscoP2pConnsMIBGroup
--   OptGroup
--    ciscoP2pEndpointsMIBGroup
--   OptGroup
--    ciscoP2pIntEndpointsMIBGroup
--   OptGroup
--    ciscoP2mpConnsMIBGroup


END
