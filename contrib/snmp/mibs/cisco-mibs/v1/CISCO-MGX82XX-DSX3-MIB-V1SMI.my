-- MIB file created 14-Jun-2003 22:30:12, by
--   SMICng version 2.2.11-beta(PRO)(Solaris), January 20, 2001. Enterprise key cisco.com

CISCO-MGX82XX-DSX3-MIB DEFINITIONS ::= BEGIN

-- From file: "CISCO-MGX82XX-DSX3-MIB.my"
-- Compile options "4 7 F H N W 03 06 0B 0G 0N 0T"

IMPORTS
    DisplayString
            FROM SNMPv2-TC-v1
    dsx3Line, dsx3Framing
            FROM BASIS-MIB
    ciscoWan
            FROM CISCOWAN-SMI
    Counter
            FROM RFC1155-SMI
    OBJECT-TYPE
            FROM RFC-1212;

ciscoMgx82xxDsx3MIB OBJECT IDENTIFIER ::= { ciscoWan 59 }
-- MODULE-IDENTITY
--  LastUpdated
--    200301110000Z
--  OrgName
--    Cisco Systems, Inc.
--  ContactInfo
--           Cisco Systems
--            Customer Service
--    
--    Postal: 170 W Tasman Drive
--            San Jose, CA  95134
--            USA
--    
--            Tel: +1 800 553-NETS
--    
--    E-mail: cs-wanatm@cisco.com
--  Descr
--    The MIB Module for DS3/E3 interface 
--    configuration , statistics and Alarm 
--    configuration.
--    
--    This MIB is supported in T3/E3 service modules
--    in MGX products. 
--    Some of the T3/E3 service modules(Cards) are:
--    
--     PXM1     : Processor Switch Module.
--     CESM-T3E3: Circuit Emulation Service Module
--     FRSM-VHS : Frame Relay Service Module. Includes
--                T3 and Channelized T3 categories.
--     FRSM-2CT3: Channelized FRSM Module
--     SRM-3T3  : Service Resource Module
--    
--    Terminologies Used :
--    
--      SDH     : SONET Digital Hierarchy
--      PLCP    : Physical Layer Convergence Procedure.
--      BERT    : Bit Error Rate Testing.
--      FEAC    : Far End Alarm Code.
--      OOF     : Out Of Frame.
--      AIS     : Alarm Indication Signal.
--      LOF     : Loss Of Frame.
--      RAI     : Remote Alarm Indication.
--      
--      HCS     : Header Check Sequence
--      HEC     : Header Error Control
--    
--      MA byte : Maintenance and Adaptation byte
--    
--      Tx MA Byte: This is explained in ITU-T G.832
--                  This Byte contains following fields:
--                    Payload type
--                    Payload dependent bits
--                    Timing maker bit
--           
--      Rx MA Byte: This is explained in ITU-T G.832
--                  This Byte contains following fields:
--                    Payload type
--                    Timing maker bit
--  RevDate
--    200301110000Z
--  RevDescr
--    Initial version of the MIB.
--    
--    The content of this MIB was originally available
--    in CISCO-WAN-AXIPOP-MIB defined using SMIv1.
--    The applicable objects from CISCO-WAN-AXIPOP-MIB
--    are defined using SMIv2 in this MIB. Also the
--    descriptions of some of the objects have been 
--    modified.

dsx3Config      OBJECT IDENTIFIER ::= { dsx3Line 1 }
dsx3AlarmConfig OBJECT IDENTIFIER ::= { dsx3Line 2 }
dsx3Alarm       OBJECT IDENTIFIER ::= { dsx3Line 3 }
dsx3Counter     OBJECT IDENTIFIER ::= { dsx3Line 4 }
dsx3PlcpConfig  OBJECT IDENTIFIER ::= { dsx3Framing 1 }
dsx3PlcpAlarmConfig OBJECT IDENTIFIER ::= { dsx3Framing 2 }
dsx3PlcpAlarm   OBJECT IDENTIFIER ::= { dsx3Framing 3 }
dsx3PlcpCounter OBJECT IDENTIFIER ::= { dsx3Framing 4 }
cmDsx3MIBConformance OBJECT IDENTIFIER ::= { ciscoMgx82xxDsx3MIB 2 }
cmDsx3MIBGroups OBJECT IDENTIFIER ::= { cmDsx3MIBConformance 1 }
cmDsx3MIBCompliances OBJECT IDENTIFIER ::= { cmDsx3MIBConformance 2 }

cwDsx3ConfigTable OBJECT-TYPE
    SYNTAX SEQUENCE OF CwDsx3ConfigEntry
    ACCESS not-accessible
    STATUS mandatory
    DESCRIPTION
        "The DS3/E3 Configuration table. There is one row for each
        DSX3 port in the system. The table size (number of 
        rows) is given by the value of dsx3LineNumOfValidEntries."
    ::= { dsx3Config 1 }

cwDsx3ConfigEntry OBJECT-TYPE
    SYNTAX CwDsx3ConfigEntry
    ACCESS not-accessible
    STATUS mandatory
    DESCRIPTION
        "An entry in the DSX3 Configuration table."
    INDEX { dsx3LineNum }
    ::= { cwDsx3ConfigTable 1 }

CwDsx3ConfigEntry ::= SEQUENCE {
    dsx3LineNum INTEGER,
    cwDsx3LineType INTEGER,
    cwDsx3LineCoding INTEGER,
    cwDsx3LineLength INTEGER,
    dsx3LineOOFCriteria INTEGER,
    dsx3LineAIScBitsCheck INTEGER,
    dsx3LineLoopbackCommand INTEGER,
    dsx3LineRcvFEACValidation INTEGER,
    dsx3LineXmtFEACCode INTEGER,
    dsx3LineBERTEnable INTEGER,
    dsx3LineBERTPattern INTEGER,
    dsx3LineBERTResult INTEGER,
    dsx3BERTResultClrButton INTEGER,
    dsx3TrailTraceOption INTEGER,
    dsx3TxTrailTrace DisplayString,
    dsx3RxTrailTrace DisplayString,
    dsx3TxTimingMarker INTEGER,
    dsx3RxTimingMarker INTEGER,
    dsx3TxPayloadType INTEGER,
    dsx3RxPayloadType INTEGER,
    dsx3TxTumf INTEGER,
    dsx3RxTumf INTEGER,
    dsx3LineEnable INTEGER,
    dsx3FarEndLoopbkLineNum INTEGER,
    dsx3LineXmtClockSrc INTEGER,
    dsx3FarEndLoopbkLineStatus INTEGER,
    dsx3LineEqualizer INTEGER,
    dsx3NearEndLoopbkLineStatus INTEGER,
    dsx3SubRateEnable INTEGER,
    dsx3DsuSelect INTEGER,
    dsx3LineRate INTEGER,
    dsx3LineScrambleEnable INTEGER
    }

dsx3LineNum OBJECT-TYPE
    SYNTAX INTEGER(1..2147483647)
    ACCESS read-only
    STATUS mandatory
    DESCRIPTION
        "This object is the identifier of a DS3/E3
        Interface on a managed device.
        
        The range supported depends upon the type of
        the card(controller card, service module).
        
        For 1 port Card :  Range is 1..1
           Example : CESM-T3E3
        
        For 2 Port Card :  Range is 1..2
           Example : PXM1-2T3E3.
        
        For 3 Port Card : Range is 1..3
           Example: SRM-3T3"
    ::= { cwDsx3ConfigEntry 1 }

cwDsx3LineType OBJECT-TYPE
    SYNTAX INTEGER {
        dsx3CbitParity(1),
        g832-g804(2),
        dsx3M23(3),
        g751(4),
        dsx3Unframed(5),
        e3Unframed(6)
        }
    ACCESS read-write
    STATUS mandatory
    DESCRIPTION
        "This variable indicates the variety of DS3 C-bit
        or E3 application implementing this interface.
        The type of interface affects the interpretation
        of the usage and error statistics. The rate of DS3
        is 44.736 Mbps and E3 is 34.368 Mbps.
        
        The values, in sequence, describe:
        
        TITLE:                     SPECIFICATION:
        
        dsx3CbitParity            ANSI T1.107a-1990   [9a]
        g832-g804                 ITU-T  G.832, G.804
        dsx3M23                   ANSI T1.107-1988    [9]
        g751                      ITU-T G.751
        CESM-T3 supports only ds3Unframed linetype.
        CESM-E3 supports only e3Unframed linetype."
    ::= { cwDsx3ConfigEntry 2 }

cwDsx3LineCoding OBJECT-TYPE
    SYNTAX INTEGER {
        dsx3B3ZS(1),
        e3HDB3(2)
        }
    ACCESS read-write
    STATUS mandatory
    DESCRIPTION
        "This variable describes the variety of Zero Code
        Suppression used on this interface, which in turn
        affects a number of its characteristics.
        
        dsx3B3ZS and e3HDB3 refer to the use of specified
        patterns of normal bits and bipolar violations
        which are used to replace sequences of zero bits
        of a specified length.
        
        dsx3B3ZS(1) : Bipolar 3-Zero Substitution(B3ZS) suppression.
        e3HDB3  (2) : High-Density Bipolar 3(HDB3) suppression."
    ::= { cwDsx3ConfigEntry 3 }

cwDsx3LineLength OBJECT-TYPE
    SYNTAX INTEGER {
        lessThan225(1),
        moreThan225(2)
        }
    ACCESS read-write
    STATUS mandatory
    DESCRIPTION
        "This object specifies the length of the 
        DS3 Line. This object provides information
        for line build out circuitry if it exists
        and can use this object to adjust the 
        line build out."
    ::= { cwDsx3ConfigEntry 4 }

dsx3LineOOFCriteria OBJECT-TYPE
    SYNTAX INTEGER {
        fBits3Of8(1),
        fBits3Of16(2),
        notApplicable(3)
        }
    ACCESS read-write
    STATUS mandatory
    DESCRIPTION
        "This object specifies the out of frame decision 
        criteria. 
        OOF is declared when errors are detected in  the 
        framing octets for four consecuitive frames.
        
        fBits3Of8(1) : an OOF condition is declared if at 
                       least 3 of 8 framing bits are in error.
        
        fBits3Of16(2): an OOF is declared if 3 of 16 framing 
                       bits are found to be in error.
        notApplicable(3) : used in case where it is not
                           applicable. This value can not be set.
        
        This object is not applicable when cwDsx3LineType is
        set to g832-g804(2) or g751(4).
        This object is not applicable for CESM-T3/E3"
    ::= { cwDsx3ConfigEntry 5 }

dsx3LineAIScBitsCheck OBJECT-TYPE
    SYNTAX INTEGER {
        checkCbits(1),
        ignorebits(2),
        notApplicable(3)
        }
    ACCESS read-write
    STATUS mandatory
    DESCRIPTION
        "If check C-Bits options is chosen then AIS is declared
        when 1010 pattern is found and C-Bits are all zero. 
        In the other case an AIS condition is declared when the
        AIS pattern 1010... is detected irrespective of the state
        of the C Bits.
        This object does not apply to the E3 interface.
        The value notApplicable(3) is used in case of interfaces
        where this object is not applicable.
        
        This object is not applicable for CESM-T3/E3."
    ::= { cwDsx3ConfigEntry 6 }

dsx3LineLoopbackCommand OBJECT-TYPE
    SYNTAX INTEGER {
        dsx3NoLoop(1),
        dsx3RemoteLineLoop(2),
        dsx3LocalLineLoop(3),
        dsx3InbndLocalLoopback(4)
        }
    ACCESS read-write
    STATUS mandatory
    DESCRIPTION
        "This variable represents the loopback configuration
        of the DS3/E3 interface.
        The values mean:
            dsx3NoLoop
                Not in the loopback state.  A device that is
                not capable of performing a loopback on
                the interface shall always return this as
                it's value.
            dsx3RemoteLineLoop
                Near End loops back Remote data
            dsx3LocalLineLoop
                Near End loops back Local data(outbound).
            dsx3InboundLoopback
                Near End in bound loopback Local data(inbound)."
    ::= { cwDsx3ConfigEntry 7 }

dsx3LineRcvFEACValidation OBJECT-TYPE
    SYNTAX INTEGER {
        fFEACCodes4Of5(1),
        fFEACCodes8Of10(2),
        fFEACCodesDisable(3)
        }
    ACCESS read-write
    STATUS mandatory
    DESCRIPTION
        "This entry specifies the FEAC code validation criteria.
        fFEACCodes4Of5(1) : a valid FEAC code is declared if
                            4 of 5 codes match.
        fFEACCodes8Of10(2): a valid FEAC code is declared if 
                            8 of 10 codes match.
        
        fFEACCodesDisable(3) : Do not respond to any valid FEAC code.
        This object is not applicable to E3 interface.
        
        This object is not supported in CESM-T3/E3."
    ::= { cwDsx3ConfigEntry 8 }

dsx3LineXmtFEACCode OBJECT-TYPE
    SYNTAX INTEGER {
        dsx3SendNoCode(1),
        dsx3SendLineCode(2),
        dsx3SendPayloadCode(3),
        dsx3SendResetCode(4),
        dsx3SendDS1LoopCode(5),
        dsx3SendTestPattern(6)
        }
    ACCESS read-write
    STATUS mandatory
    DESCRIPTION
        "This variable indicates what bit-oriented code to transmit
        over the far-end alarm and control (FEAC) channel.
        
        The values mean:
        
        dsx3SendNoCode
            sending looped or normal data
        dsx3SendLineCode
            sending a request for a line loopback
        dsx3SendPayloadCode
            sending a request for a payload loopback
        (i.e., all DS1/E1s in a DS3/E3 frame)
        dsx3SendResetCode
            sending a loopback deactivation request.
        dsx3SendDS1LoopCode
            sending a request to put part of DS1/E1 within
            T3/E3 respectively into loopback.
        dsx3SendTestPattern
            sending a test pattern.
        This object is not applicable for CESM-T3/E3"
    ::= { cwDsx3ConfigEntry 9 }

dsx3LineBERTEnable OBJECT-TYPE
    SYNTAX INTEGER {
        disabled(1),
        enabled(2)
        }
    ACCESS read-write
    STATUS mandatory
    DESCRIPTION
        "This object enables/disables the BERT function on
        an interface.
        
        The possible values are :
           disabled(1): disables port BERT functionality
           enabled (2): enables port BERT functionality.
                        value specified in dsx3LineBERTPattern
                        is transmitted over the interface.
                        The far end may be looped back and the 
                        test pattern verified."
    ::= { cwDsx3ConfigEntry 10 }

dsx3LineBERTPattern OBJECT-TYPE
    SYNTAX INTEGER {
        allZero(1),
        allOnes(2),
        alternateOneZero(3),
        doubleOneZero(4),
        userOneWord(5),
        userTwoWords(6),
        userThreeWords(7),
        userFourWords(8),
        pattern2p15minus1(9),
        pattern2p20minus1(10),
        pattern2p23minus1(11)
        }
    ACCESS read-write
    STATUS mandatory
    DESCRIPTION
        "This object defines the test bit pattern to be
        used for BERT.
        
        The possible values are :
        
          Repetitive Patterns
        
        allZero(1): All Zeroes(Continuous spaces).  This is 
                repeating pattern of zeros(...000...). 
                The use of this pattern is to test and verify 
                that the ones density policing mechanism is 
                functioning properly.  This pattern must be 
                used in circuits optioned for B8ZS.
        
        allOnes(2): All Ones(Continuous Marks).  This is repeating
                pattern of ones(...1111...).  This provides 
                testing of maximum power level requirements.
                The all one pattern test causes the repeater 
                to consume the maximum amount of power. 
                If there is insufficient DC span power then the
                repeater may begin to fail.
                Typically this pattern is used for a simple
                continuity check.  It may also be used to detect
                the presence of unwanted loop in the network.
        
        alternateOneZero(3): Alternate one/zero pattern(..1010..).  This
                pattern produces a 50% ones density.  It is
                used to stress the repeater's DC power
                consumption.
        
        doubleOneZero(4): Double alternate one/zero(..1100..).
        
         userOneWord(5),
         userTwoWords(6),
         userThreeWords(7),
         userFourWords(8),
         pattern2p15minus1(9) :
           This is the 2^15-1(32767 bit length)
           pattern as specified in ITU O.151.
           It has the maximum of 15(inverted) sequential zeros.
           This sequence is primarily intended for
           error and jitter measurements at bit
           rates of 1544, 2048, 6312, 8448,
           32064 and 44736 kbit/s.
        
         pattern2p20minus1(10): 
           This is the 2^20-1(1048575 bits in length)
           pattern specified in ITU O.153.It has
           the maximum of 19(non-inverted) sequential
           zeros.  This pattern is primarily intended 
           for error measurements at bit rates up to 
           73kbit/s.  This pattern stresses the 
           equalization and timing recovery circuitry 
           of line repeaters.
        
          pattern2p23minus1(11):
             This is the 2^23-1(1048575 bits in length) pattern."
    ::= { cwDsx3ConfigEntry 11 }

dsx3LineBERTResult OBJECT-TYPE
    SYNTAX INTEGER {
        bertFailed(1),
        bertPassed(2)
        }
    ACCESS read-only
    STATUS mandatory
    DESCRIPTION
        "Result of BERT Test. The value in this object
        is not applicable if dsx3LineBERTEnable is set to
        disabled(1)."
    ::= { cwDsx3ConfigEntry 12 }

dsx3BERTResultClrButton OBJECT-TYPE
    SYNTAX INTEGER {
        noAction(1),
        clear(2)
        }
    ACCESS read-write
    STATUS mandatory
    DESCRIPTION
        "Setting this object to clear(2) causes the BERT
        result field to get cleared."
    ::= { cwDsx3ConfigEntry 13 }

dsx3TrailTraceOption OBJECT-TYPE
    SYNTAX INTEGER {
        disable(1),
        enable(2)
        }
    ACCESS read-write
    STATUS mandatory
    DESCRIPTION
        "This object is used for enabling/disabling 
        G.832 Trail Trace. The trail trace is used to 
        repetitively transmit a trail access point identifier
        so that a trail receiving terminal can verify its 
        continued connection to the intended transmitter.
        It uses a 16-byte numbering format (see Rec E.164).
        The first byte of the string is a frame start marker 
        and includes the result of a CRC-7 calculation over 
        the previous frame. 
        
        The value of this object is set to disable(1) in case
        of cards where this feature is not supported.
        
        This object is not applicable for FRSM-VHS and
        CESM-T3/E3."
    REFERENCE
        "ITU-T G.832"
    ::= { cwDsx3ConfigEntry 14 }

dsx3TxTrailTrace OBJECT-TYPE
    SYNTAX DisplayString(SIZE(1..15))
--    Rsyntax OCTET STRING(SIZE(1..15))
    ACCESS read-write
    STATUS mandatory
    DESCRIPTION
        "This object is used for specifying the 
        data to be used for G.832 Trail Trace ID/String.
        This object is applicable only for E3 interfaces
        with G.832 framing.
        
        The trail trace ID is a 16 octet field that
        contains 1 octet of CRC-7(first octet) and 15
        octets of data.
        
        The CRC-7 is automatically calculated by the
        system(card supporting this feature).
        
        The format of the value is:
          Frame Start Marker Error(HEX): CRC-7
          Bytes 2-6   (ASCII) [Byte 1-5 of this object]
          Bytes 7-11  (ASCII) [Byte 6-10 of this object]
          Bytes 12-16 (ASCII) [Byte 11-15 of this object]
        
        This object is not applicable for FRSM-VHS and
        CESM-T3/E3."
    REFERENCE
        "ITU-T G.832"
    ::= { cwDsx3ConfigEntry 15 }

dsx3RxTrailTrace OBJECT-TYPE
    SYNTAX DisplayString(SIZE(1..15))
--    Rsyntax OCTET STRING(SIZE(1..15))
    ACCESS read-only
    STATUS mandatory
    DESCRIPTION
        "Received G.832 Trail Trace string. 
        The format of the value is:
          First byte indicates CRC-7(frame start marker).
          Bytes 2-6   (ASCII) [Byte 1-5 of this object]
          Bytes 7-11  (ASCII) [Byte 6-10 of this object]
          Bytes 12-16 (ASCII) [Byte 11-15 of this object]
          The value of all zeroes indicates bad CRC-7.
        
        This object is not applicable for FRSM-VHS and
        CESM-T3/E3."
    REFERENCE
        "ITU-T G.832"
    ::= { cwDsx3ConfigEntry 16 }

dsx3TxTimingMarker OBJECT-TYPE
    SYNTAX INTEGER {
        traceable(1),
        untraceable(2)
        }
    ACCESS read-write
    STATUS mandatory
    DESCRIPTION
        "Transmitted timing marker bit in G.832 MA byte.
        This object can be set to traceable(1) to indicate 
        that the timing source is traceable to a primary
        reference clock and is otherwise set to untraceable(2).
        
        This is always set to untraceable(2) in case of
        card where this feature is not supported.
        
        This feature is not supported in FRSM-VHS and
        CESM-T3/E3."
    REFERENCE
        "ITU-T G.832"
    ::= { cwDsx3ConfigEntry 17 }

dsx3RxTimingMarker OBJECT-TYPE
    SYNTAX INTEGER {
        traceable(1),
        untraceable(2)
        }
    ACCESS read-write
    STATUS mandatory
    DESCRIPTION
        "Received timing marker bit in G.832 MA byte.
        This object can be set to traceable(1) to indicate 
        that the timing source is tracable to a primary
        reference clock and is otherwise set to untraceable(2).
        
        This is always set to untraceable(2) in case of
        card where this feature is not supported.
        
        This feature is not supported in FRSM-VHS and
        CESM-T3/E3."
    REFERENCE
        "ITU-T G.832"
    ::= { cwDsx3ConfigEntry 18 }

dsx3TxPayloadType OBJECT-TYPE
    SYNTAX INTEGER {
        unequipped(1),
        equipped(2),
        atm(3),
        sdhtu12s(4)
        }
    ACCESS read-write
    STATUS mandatory
    DESCRIPTION
        "This object specifies the G.832 payload type
        for transmit data.
        
        The possible values are :
           
         unequipped (1): not carrying any payload
         equipped   (2): Equipped,non-specific
         atm        (3): ATM
         sdhtu12s   (4): SDH Elements mapping
        
        It is recommended that this object is not instantiated 
        in case of cards which does not support G.832 functionality.
        
        This is not supported in FRSM-VHS and CESM-T3/E3"
    REFERENCE
        "ITU-T G.832 section 2.1.2."
    DEFVAL { unequipped }
    ::= { cwDsx3ConfigEntry 19 }

dsx3RxPayloadType OBJECT-TYPE
    SYNTAX INTEGER {
        unequipped(1),
        equipped(2),
        atm(3),
        sdhtu12s(4)
        }
    ACCESS read-only
    STATUS mandatory
    DESCRIPTION
        "Received payload type field in G.832 byte
        
        The possible values are :
           
         unequipped (1): not carrying any payload
         equipped   (2): Equipped,non-specific
         atm        (3): ATM
         sdhtu12s   (4): SDH Elements mapping
        
        It is recommended that this object is not instantiated 
        in case of cards which does not support G.832 functionality.
        
        This is not supported in FRSM-VHS and CESM-T3/E3"
    REFERENCE
        "ITU-T G.832 section 2.1.2."
    ::= { cwDsx3ConfigEntry 20 }

dsx3TxTumf OBJECT-TYPE
    SYNTAX INTEGER(0..3)
    ACCESS read-only
    STATUS mandatory
    DESCRIPTION
        "This object contains the value of 
        Tributary Multiframe Indicator(bits 6 and 7 of MA byte)
        in case of TU-1xs mapping.
        
        This is not supported in FRSM-VHS and CESM-T3/E3."
    REFERENCE
        "ITU-T G.832, section 3.4.3"
    ::= { cwDsx3ConfigEntry 21 }

dsx3RxTumf OBJECT-TYPE
    SYNTAX INTEGER(0..3)
    ACCESS read-only
    STATUS mandatory
    DESCRIPTION
        "This object contains the value of 
        Tributary Multiframe Indicator(bits 6 and 7 of MA byte)
        in case of TU-1xs mapping.
        
        This object is not supported in FRSM-VHS 
        and CESM-T3/E3."
    REFERENCE
        "ITU-T G.832, section 3.4.3"
    ::= { cwDsx3ConfigEntry 22 }

dsx3LineEnable OBJECT-TYPE
    SYNTAX INTEGER {
        disable(1),
        enable(2),
        modify(3)
        }
    ACCESS read-write
    STATUS mandatory
    DESCRIPTION
        "This object is used for enabling/disabling an interface
        and modifying the interface configuration.
        
        The possible values are:
        
          disable (1): Interface is administratively down
          enable  (2): Interface is administratively up.
          modify  (3): Used for modifying the parameters
                       of an interface that has been already
                       enabled(administratively up).
          To modify the parameters of this table, the value
          of this object must be set to enable(2) or modify(3)."
    ::= { cwDsx3ConfigEntry 23 }

dsx3FarEndLoopbkLineNum OBJECT-TYPE
    SYNTAX INTEGER {
        ds1line1(1),
        ds1line2(2),
        ds1line3(3),
        ds1line4(4),
        ds1line5(5),
        ds1line6(6),
        ds1line7(7),
        ds1line8(8),
        ds1line9(9),
        ds1line10(10),
        ds1line11(11),
        ds1line12(12),
        ds1line13(13),
        ds1line14(14),
        ds1line15(15),
        ds1line16(16),
        ds1line17(17),
        ds1line18(18),
        ds1line19(19),
        ds1line20(20),
        ds1line21(21),
        ds1line22(22),
        ds1line23(23),
        ds1line24(24),
        ds1line25(25),
        ds1line26(26),
        ds1line27(27),
        ds1line28(28),
        ds1line29(29),
        ds3line(30)
        }
    ACCESS read-write
    STATUS mandatory
    DESCRIPTION
        "Specify which DS1 or DS3 line in the far-end for the 
        loopback testing.
        For CESM-T3/E3, only ds3line(30) is valid."
    ::= { cwDsx3ConfigEntry 24 }

dsx3LineXmtClockSrc OBJECT-TYPE
    SYNTAX INTEGER {
        backplaneClk(1),
        recoverClk(2),
        localClk(3)
        }
    ACCESS read-write
    STATUS mandatory
    DESCRIPTION
        "The source of the transmit clock.
        
          backplaneClk(2) : clock source is from the backplane.
          recoverClk  (3) : clock source is derived from another
                            t3 interface.
          localClk    (4) : clock source is from a local 
                            oscillator on the card"
    ::= { cwDsx3ConfigEntry 25 }

dsx3FarEndLoopbkLineStatus OBJECT-TYPE
    SYNTAX INTEGER(0..2147483647)
    ACCESS read-only
    STATUS mandatory
    DESCRIPTION
        "This is a bitmap of the DSX3 FarEnd line 
         loopback status bits 
        
        Bit Position    Loopback indicator 
        -----------    -----
        1              DS1 Line 1
        2              DS1 Line 2
        3              DS1 Line 3
        4              DS1 Line 4
        5              DS1 Line 5
        6              DS1 Line 6
        7              DS1 Line 7
        8              DS1 Line 8
        9              DS1 Line 9
        10             DS1 Line 10
        11             DS1 Line 11
        12             DS1 Line 12
        ...
        ...
        ...
        28             DS1 Line 28
        29             all DS1 Lines
        30             DSX3    
        For CESM-T3/E3, only DSX3 bit (bit 30) is valid."
    ::= { cwDsx3ConfigEntry 26 }

dsx3LineEqualizer OBJECT-TYPE
    SYNTAX INTEGER {
        intrnlequalizer(1),
        extequalizer(2)
        }
    ACCESS read-write
    STATUS mandatory
    DESCRIPTION
        "This object indicates whether the internal equalizer
        is being used or bypassed. Set this value depending on
        the line equipment to which the receiver is attached.
        
        intrnlequalizer(1): Use internal line equalizer
        extequalizer(2)   : Use External equalizer or bypass internal
                            equalizer."
    ::= { cwDsx3ConfigEntry 27 }

dsx3NearEndLoopbkLineStatus OBJECT-TYPE
    SYNTAX INTEGER(0..2147483647)
    ACCESS read-only
    STATUS mandatory
    DESCRIPTION
        "This is a bitmap of the DSX3 NearEnd line
          loopback status bits
          BitPosition    Loopback indicator
          -----------    -----
          1              DS1 Line 1
          2              DS1 Line 2
          3              DS1 Line 3
          4              DS1 Line 4
          5              DS1 Line 5
          6              DS1 Line 6
          7              DS1 Line 7
          8              DS1 Line 8
          9              DS1 Line 9
          10             DS1 Line 10
          11             DS1 Line 11
          12             DS1 Line 12
          ...
          ...
          ...
          28             DS1 Line 28
          29             DS1 Line 29
          30             DSX3     
        
        For CESM-T3/E3, only DSX3 bit (bit 30) is valid."
    ::= { cwDsx3ConfigEntry 28 }

dsx3SubRateEnable OBJECT-TYPE
    SYNTAX INTEGER {
        disable(1),
        enable(2)
        }
    ACCESS read-write
    STATUS mandatory
    DESCRIPTION
        "This variable controls whether the DS3 subrates are
        enabled or not. The DS3 subrate is part of
        DSU functionality.
        This object is currently supported only in FRSM-VHS
        cards.
        
        It is recommended that this object is not instantiated 
        in case of cards which does not support DSU functionality."
    DEFVAL { disable }
    ::= { cwDsx3ConfigEntry 29 }

dsx3DsuSelect OBJECT-TYPE
    SYNTAX INTEGER {
        dl3100Mode(1),
        adcKentroxMode(2),
        larsCom(3),
        clearChannel(4),
        dsuAlgorithm2(5),
        dsuAlgorithm3(6),
        dsuAlgorithm4(7),
        dsuAlgorithm5(8)
        }
    ACCESS read-write
    STATUS mandatory
    DESCRIPTION
        "The dsx3DsuSelect variable controls the type of DSU mode
        to be selected. The 'dsx3SubRateEnable' has to be set to 
        'enable' before selecting the mode in 'dsx3DsuSelect'.
        
        The possible values for this are :
        
        dl3100Mode     - Indicates compatibility with Digital Link Inc's
                         DL3100 DSU mode of operation. This mode permits
                         line rates to be in multiples of 300 Kbps.
        adcKentroxMode - Indicates compatibility with ADC Kentrox's DSU.
                         This mode permits line rates to be in multiples
                         of 500 Kbps.
        larsCom        - Indicates compatability with LarsCom DSU.
        clearChannel   - Indicates the standard G.751 framing format
                         (12 overhead bits and 1524 data bits in an E3
                         frame).This option is supported only in FRSM-2E3.
        dsuAlgorithm1  - dsuAlgorith4  - Presently this is not used in any of
                         the cards.
        This object is supported only in FRSM-VHS cards.
        
        It is recommended that this object is not instantiated 
        in case of cards which does not support DSU functionality."
    DEFVAL { dl3100Mode }
    ::= { cwDsx3ConfigEntry 30 }

dsx3LineRate OBJECT-TYPE
    SYNTAX INTEGER(300..44736)
--  Units
--    kbps
    ACCESS read-write
    STATUS mandatory
    DESCRIPTION
        "The desired line rate when 'dsx3SubRateEnable' is enabled.
        If dsx3DsuSelect is set to 'dl3100Mode', the line rate can
        be configured in steps of 300 Kbps.
        If dsx3DsuSelect is set to  'adcKentroxMode', the line rate can
        be configured in steps of 500 Kbps.
        
        This object is supported only in FRSM-VHS cards.
        
        It is recommended that this object is not instantiated 
        in case of cards which does not support DSU functionality."
    ::= { cwDsx3ConfigEntry 31 }

dsx3LineScrambleEnable OBJECT-TYPE
    SYNTAX INTEGER {
        disabled(1),
        enabled(2)
        }
    ACCESS read-write
    STATUS mandatory
    DESCRIPTION
        "This variable turns the scrambling feature ON/OFF
        The scrambling is a technique that enables framing
        to be maintained on certain medium-speed edge and 
        trunk interfaces.
        
        This object is ONLY applicable for FRSM-2T3/E3."
    ::= { cwDsx3ConfigEntry 32 }

dsx3LineNumOfValidEntries OBJECT-TYPE
    SYNTAX INTEGER(0..2147483647)
    ACCESS read-only
    STATUS mandatory
    DESCRIPTION
        "The number of DSX3 configuration entries (regardless
        of their current configuration) in the cwDsx3ConfigTable."
    ::= { dsx3Config 2 }

dsx3AlarmConfigTable OBJECT-TYPE
    SYNTAX SEQUENCE OF Dsx3AlarmConfigEntry
    ACCESS not-accessible
    STATUS mandatory
    DESCRIPTION
        "The DSX3 interface alarm configuration table. This table contains
        the parameters associated with detecting and declaring alarms for
        the interface. The parameters include severity of alarm, alarm
        integration parameters and 15 minute and 24 hour thresholds. 
        The number of rows is given by dsx3LineNumOfValidEntries."
    ::= { dsx3AlarmConfig 1 }

dsx3AlarmConfigEntry OBJECT-TYPE
    SYNTAX Dsx3AlarmConfigEntry
    ACCESS not-accessible
    STATUS mandatory
    DESCRIPTION
        "An entry in the DSX3 Alarm Configuration table.
        
        Thresholds may be configured for:
        
            Line Code Violations          (LCV), 
            LineErrored Seconds           (LES),
            Line Severely Errored Seconds (LSES), 
            P-bit Coding Violations       (PCV), 
            P-bit Errored Seconds         (PES), 
            P-bit Severely Errored Seconds(PSES), 
            Severely Errored Seconds      (SES), 
            Severely Errored Framing Seconds(SEFS), 
            Unavailable Seconds            (UAS),
            C-bit coding violations        (CCV),
            C-bit errored seconds          (CES),
            C-bit errored seconds          (CSES).
        Once these thresholds are exceeded, minor or major alarms
        are raised. Please refer to RFC2496 for descriptions of these
        errors."
    INDEX { dsx3LineNum }
    ::= { dsx3AlarmConfigTable 1 }

Dsx3AlarmConfigEntry ::= SEQUENCE {
    dsx3RedSeverity INTEGER,
    dsx3RAISeverity INTEGER,
    dsx3NEAlarmUpCount INTEGER,
    dsx3NEAlarmDownCount INTEGER,
    dsx3NEAlarmThreshold INTEGER,
    dsx3FEAlarmUpCount INTEGER,
    dsx3FEAlarmDownCount INTEGER,
    dsx3FEAlarmThreshold INTEGER,
    dsx3StatisticalAlarmSeverity INTEGER,
    dsx3LCV15MinThreshold INTEGER,
    dsx3LCV24HrThreshold INTEGER,
    dsx3LES15MinThreshold INTEGER,
    dsx3LES24HrThreshold INTEGER,
    dsx3LSES15MinThreshold INTEGER,
    dsx3LSES24HrThreshold INTEGER,
    dsx3PCV15MinThreshold INTEGER,
    dsx3PCV24HrThreshold INTEGER,
    dsx3PES15MinThreshold INTEGER,
    dsx3PES24HrThreshold INTEGER,
    dsx3PSES15MinThreshold INTEGER,
    dsx3PSES24HrThreshold INTEGER,
    dsx3SEFS15MinThreshold INTEGER,
    dsx3SEFS24HrThreshold INTEGER,
    dsx3AISS15MinThreshold INTEGER,
    dsx3AISS24HrThreshold INTEGER,
    dsx3UAS15MinThreshold INTEGER,
    dsx3UAS24HrThreshold INTEGER,
    dsx3E3BIP8CV15MinThreshold INTEGER,
    dsx3E3BIP8CV24HrThreshold INTEGER,
    dsx3E3BIP8ES15MinThreshold INTEGER,
    dsx3E3BIP8ES24HrThreshold INTEGER,
    dsx3E3BIP8SES15MinThreshold INTEGER,
    dsx3E3BIP8SES24HrThreshold INTEGER,
    dsx3CCV15MinThreshold INTEGER,
    dsx3CCV24HrThreshold INTEGER,
    dsx3CES15MinThreshold INTEGER,
    dsx3CES24HrThreshold INTEGER,
    dsx3CSES15MinThreshold INTEGER,
    dsx3CSES24HrThreshold INTEGER
    }

dsx3RedSeverity OBJECT-TYPE
    SYNTAX INTEGER {
        minor(1),
        major(2)
        }
    ACCESS read-write
    STATUS mandatory
    DESCRIPTION
        "This variable is used to setup the severity of RED
        alarm. So when LOS/LOF alarm is detected the card will
        send the alarm with appropriate severity status.
        A major alarm will cause audible notification
        and the MAJOR ALARM LED will be turned ON.
        A minor alarm will just turn on the MINOR ALARM LED.
        LOF detection is not applicable for CESM-8T3/E3."
    ::= { dsx3AlarmConfigEntry 1 }

dsx3RAISeverity OBJECT-TYPE
    SYNTAX INTEGER {
        minor(1),
        major(2)
        }
    ACCESS read-write
    STATUS mandatory
    DESCRIPTION
        "This variable is used to setup the severity of RAI
        alarm. So when RAI alarm is detected the card will
        send the alarm with appropriate severity status.
        A major alarm will cause the audible notification
        and the MAJOR ALARM LED will be turned ON.
        A minor alarm will just turn on the MINOR ALARM LED.
        This is not applicable for CESM-T3/E3."
    ::= { dsx3AlarmConfigEntry 2 }

dsx3NEAlarmUpCount OBJECT-TYPE
    SYNTAX INTEGER(0..2147483647)
    ACCESS read-write
    STATUS mandatory
    DESCRIPTION
        "This parameter specifies the increment to the
        Near End alarm integration counters. The local 
        alarms are LOS and LOF. The Default value is 6
        and the integration counter is incremented by
        this value every 10 ms while the alarm persists. 
        The counter is decremented by the value of 
        dsx3NEAlarmDnCount while there is no alarm 
        (the counter does not decrement below zero). 
        When the integration counter exceeds 
        dsx3NEAlarmThreshold an Alarm of the severity 
        specified for the particular NE alarm is declared.
        
        LOF detection is not applicable for CESM-T3/E3"
    ::= { dsx3AlarmConfigEntry 3 }

dsx3NEAlarmDownCount OBJECT-TYPE
    SYNTAX INTEGER(0..2147483647)
    ACCESS read-write
    STATUS mandatory
    DESCRIPTION
        "This parameter specifies the decrement to the 
        Near End alarm integration counters. The local 
        alarms are LOS and LOF. The Default value is 1 and 
        the integration counter is decremented by this value 
        every 10 ms while no alarm persists. The counter is 
        incremented by the value of dsx3NEAlarmUpCount
        while there is no alarm (the counter does not decrement below
        zero). When the integration counter reaches zero any Alarm
        previously declared is removed.
        
        LOF detection is not applicable for CESM-T3/E3"
    ::= { dsx3AlarmConfigEntry 4 }

dsx3NEAlarmThreshold OBJECT-TYPE
    SYNTAX INTEGER(0..2147483647)
    ACCESS read-write
    STATUS mandatory
    DESCRIPTION
        "The value set in this object determines the value that
        the alarm integration counter must reach for an near end
        Alarm to be declared. If the up count is 6, the down count
        is 1 and the threshold 1500, an Alarm is integrated in 
        2.5 sec and removed in 15 seconds."
    ::= { dsx3AlarmConfigEntry 5 }

dsx3FEAlarmUpCount OBJECT-TYPE
    SYNTAX INTEGER(0..2147483647)
    ACCESS read-write
    STATUS mandatory
    DESCRIPTION
        "This parameter specifies the increment to the 
        Far End alarm integration counters. The local alarms 
        are RAI and AIS. The Default value is 6 and the 
        integration counter is incremented by this value every 
        10 ms while the alarm persists. The counter is decremented 
        by the value of dsx3FEAlarmDnCount while there is no alarm 
        (the counter does not decrement below zero). 
        When the integration counter exceeds dsx3FEAlarmThreshold
        an Alarm of the severity specified for the particular far end
        alarm is declared. 
        
        This object is not applicable for CESM-T3/E3. "
    ::= { dsx3AlarmConfigEntry 6 }

dsx3FEAlarmDownCount OBJECT-TYPE
    SYNTAX INTEGER(0..2147483647)
    ACCESS read-write
    STATUS mandatory
    DESCRIPTION
        "This parameter specifies the decrement to the 
        Far End alarm integration counters. The local alarms 
        are AIS and RAI. The Default value is 1. The integration 
        counter is decremented by this value every 10 ms 
        (till zero), while no alarm persists. The counter is 
        incremented by the value of dsx3FEAlarmUpCount
        while there is no alarm.  When the integration counter
        decrements to zero any previously declared Alarm is removed.
        
        This object is not applicable for CESM-T3/E3. "
    ::= { dsx3AlarmConfigEntry 7 }

dsx3FEAlarmThreshold OBJECT-TYPE
    SYNTAX INTEGER(0..2147483647)
    ACCESS read-write
    STATUS mandatory
    DESCRIPTION
        "The value set in this object determines the value that
        the alarm integration counter must reach for an far end
        Alarm to be declared. If the up count is 6, the down count
        is 1 and the threshold 1500, an Alarm is integrated in 
        2.5 sec and removed in 15 seconds.
        This object is not applicable for CESM-T3/E3. "
    ::= { dsx3AlarmConfigEntry 8 }

dsx3StatisticalAlarmSeverity OBJECT-TYPE
    SYNTAX INTEGER {
        minor(1),
        major(2)
        }
    ACCESS read-write
    STATUS mandatory
    DESCRIPTION
        "This variable is used to setup the severity of 
        any of the Statistical alarms. So when a 
        Statistical Counter exceeds its specified threshold 
        the card will send the alarm with appropriate
        severity. A major alarm will cause the audible notification
        and the MAJOR ALARM LED will be turned ON.
        A minor alarm will just turn on the MINOR ALARM LED."
    ::= { dsx3AlarmConfigEntry 9 }

dsx3LCV15MinThreshold OBJECT-TYPE
    SYNTAX INTEGER(0..2147483647)
    ACCESS read-write
    STATUS mandatory
    DESCRIPTION
        "The value set in this object determines the value
         which when exceeded in a 15 minute window causes
        a statistical alarm to be declared."
    ::= { dsx3AlarmConfigEntry 10 }

dsx3LCV24HrThreshold OBJECT-TYPE
    SYNTAX INTEGER(0..2147483647)
    ACCESS read-write
    STATUS mandatory
    DESCRIPTION
        "The value set in this object determines the value
         which when exceeded in a sliding 24 hour window causes
        a statistical alarm to be declared. The threshold is
        checked every 15 minutes for the preceding 24 hour interval"
    ::= { dsx3AlarmConfigEntry 11 }

dsx3LES15MinThreshold OBJECT-TYPE
    SYNTAX INTEGER(0..2147483647)
    ACCESS read-write
    STATUS mandatory
    DESCRIPTION
        "The value set in this object determines the value
        which when exceeded in a 15 minute window causes
        a statistical alarm to be declared."
    ::= { dsx3AlarmConfigEntry 12 }

dsx3LES24HrThreshold OBJECT-TYPE
    SYNTAX INTEGER(0..2147483647)
    ACCESS read-write
    STATUS mandatory
    DESCRIPTION
        "The value set in this object determines the value
        which when exceeded in a sliding 24 hour window causes
        a statistical alarm to be declared. The threshold is
        checked every 15 minutes for the preceding 24 hour interval"
    ::= { dsx3AlarmConfigEntry 13 }

dsx3LSES15MinThreshold OBJECT-TYPE
    SYNTAX INTEGER(0..2147483647)
    ACCESS read-write
    STATUS mandatory
    DESCRIPTION
        "The value set in this object determines the value
        which when exceeded in a 15 minute window causes
        a statistical alarm to be declared."
    ::= { dsx3AlarmConfigEntry 14 }

dsx3LSES24HrThreshold OBJECT-TYPE
    SYNTAX INTEGER(0..2147483647)
    ACCESS read-write
    STATUS mandatory
    DESCRIPTION
        "The value set in this object determines the value
        which when exceeded in a sliding 24 hour window causes
        a statistical alarm to be declared. The threshold is
        checked every 15 minutes for the preceding 24 hour interval"
    ::= { dsx3AlarmConfigEntry 15 }

dsx3PCV15MinThreshold OBJECT-TYPE
    SYNTAX INTEGER(0..2147483647)
    ACCESS read-write
    STATUS mandatory
    DESCRIPTION
        "The value set in this object determines the 
        value which when exceeded in a 15 minute window 
        causes a statistical alarm to be declared.
        This object is not supported in CESM-T3/E3.
        This object is not applicable for E3 interface."
    ::= { dsx3AlarmConfigEntry 16 }

dsx3PCV24HrThreshold OBJECT-TYPE
    SYNTAX INTEGER(0..2147483647)
    ACCESS read-write
    STATUS mandatory
    DESCRIPTION
        "The value set in this object determines the 
        value which when exceeded in a sliding 24 hour 
        window causes a statistical alarm to be declared.
        The threshold is checked every 15 minutes for the 
        preceding 24 hour interval
        This object is not supported in CESM-T3/E3.
        This object is not applicable for E3 interface."
    ::= { dsx3AlarmConfigEntry 17 }

dsx3PES15MinThreshold OBJECT-TYPE
    SYNTAX INTEGER(0..2147483647)
    ACCESS read-write
    STATUS mandatory
    DESCRIPTION
        "The value set in this object determines the 
        value which when exceeded in a 15 minute window 
        causes a statistical alarm to be declared.
        This object is not supported in CESM-T3/E3.
        This object is not applicable for E3 interface."
    ::= { dsx3AlarmConfigEntry 18 }

dsx3PES24HrThreshold OBJECT-TYPE
    SYNTAX INTEGER(0..2147483647)
    ACCESS read-write
    STATUS mandatory
    DESCRIPTION
        "The value set in this object determines the 
        value which when exceeded in a sliding 24 hour 
        window causes a statistical alarm to be declared.
        The threshold is checked every 15 minutes for the 
        preceding 24 hour interval.
        This object is not supported in CESM-T3/E3
        This object is not applicable for E3 interface."
    ::= { dsx3AlarmConfigEntry 19 }

dsx3PSES15MinThreshold OBJECT-TYPE
    SYNTAX INTEGER(0..2147483647)
    ACCESS read-write
    STATUS mandatory
    DESCRIPTION
        "The value set in this object determines the value
         which when exceeded in a 15 minute window causes
         a statistical alarm to be declared.
        
         This object does not apply to the E3 interface.
        
         This object is not supported in CESM-T3/E3."
    ::= { dsx3AlarmConfigEntry 20 }

dsx3PSES24HrThreshold OBJECT-TYPE
    SYNTAX INTEGER(0..2147483647)
    ACCESS read-write
    STATUS mandatory
    DESCRIPTION
        "The value set in this object determines the 
        value which when exceeded in a sliding 24 hour 
        window causes a statistical alarm to be declared. 
        The threshold is checked every 15 minutes for the 
        preceding 24 hour interval.
        
        This object is not applicable for E3 interface.
        
        This object is not supported in CESM-T3/E3."
    ::= { dsx3AlarmConfigEntry 21 }

dsx3SEFS15MinThreshold OBJECT-TYPE
    SYNTAX INTEGER(0..2147483647)
    ACCESS read-write
    STATUS mandatory
    DESCRIPTION
        "The value set in this object determines the value
        which when exceeded in a 15 minute window causes
        a statistical alarm to be declared.
        This object is not supported in CESM-T3/E3"
    ::= { dsx3AlarmConfigEntry 22 }

dsx3SEFS24HrThreshold OBJECT-TYPE
    SYNTAX INTEGER(0..2147483647)
    ACCESS read-write
    STATUS mandatory
    DESCRIPTION
        "The value set in this object determines the value
        which when exceeded in a sliding 24 hour window causes
        a statistical alarm to be declared. The threshold is
        checked every 15 minutes for the preceding 24 hour interval.
        
        This object is not supported in CESM-T3/E3"
    ::= { dsx3AlarmConfigEntry 23 }

dsx3AISS15MinThreshold OBJECT-TYPE
    SYNTAX INTEGER(0..2147483647)
    ACCESS read-write
    STATUS mandatory
    DESCRIPTION
        "The value set in this object determines the value
        which when exceeded in a 15 minute window causes
        a statistical alarm to be declared.
        This object is not supported in CESM-T3/E3"
    ::= { dsx3AlarmConfigEntry 24 }

dsx3AISS24HrThreshold OBJECT-TYPE
    SYNTAX INTEGER(0..2147483647)
    ACCESS read-write
    STATUS mandatory
    DESCRIPTION
        "The value set in this object determines the value
        which when exceeded in a sliding 24 hour window causes
        a statistical alarm to be declared. The threshold is
        checked every 15 minutes for the preceding 24 hour interval
        This object is not supported in CESM-T3/E3"
    ::= { dsx3AlarmConfigEntry 25 }

dsx3UAS15MinThreshold OBJECT-TYPE
    SYNTAX INTEGER(0..2147483647)
    ACCESS read-write
    STATUS mandatory
    DESCRIPTION
        "The value set in this object determines the value
        which when exceeded in a 15 minute window causes
        a statistical alarm to be declared."
    ::= { dsx3AlarmConfigEntry 26 }

dsx3UAS24HrThreshold OBJECT-TYPE
    SYNTAX INTEGER(0..2147483647)
    ACCESS read-write
    STATUS mandatory
    DESCRIPTION
        "The value set in this object determines the value
        which when exceeded in a sliding 24 hour window causes
        a statistical alarm to be declared. The threshold is
        checked every 15 minutes for the preceding 24 hour interval"
    ::= { dsx3AlarmConfigEntry 27 }

dsx3E3BIP8CV15MinThreshold OBJECT-TYPE
    SYNTAX INTEGER(0..2147483647)
    ACCESS read-write
    STATUS mandatory
    DESCRIPTION
        "G.832 BIP-8 error monitoring byte. 15 minute
        threshold value.
        This has no significance to E3 with G.751 framing
        which is used in FRSM-VHS
        This object is not supported in CESM-T3/E3."
    ::= { dsx3AlarmConfigEntry 28 }

dsx3E3BIP8CV24HrThreshold OBJECT-TYPE
    SYNTAX INTEGER(0..2147483647)
    ACCESS read-write
    STATUS mandatory
    DESCRIPTION
        "G.832 BIP-8 error monitoring byte. 24 hour
         threshold value.
        
         This has no significance to E3 with G.751 framing
         which is used in FRSM-VHS.
        
         This object is not supported in CESM-T3/E3."
    ::= { dsx3AlarmConfigEntry 29 }

dsx3E3BIP8ES15MinThreshold OBJECT-TYPE
    SYNTAX INTEGER(0..2147483647)
    ACCESS read-write
    STATUS mandatory
    DESCRIPTION
        "G.832 BIP-8 error monitoring byte. 15 minute
         threshold value.
        
         This has no significance to E3 with G.751 framing
         which is used in FRSM-VHS.
        
         This object is not supported in CESM-T3/E3."
    ::= { dsx3AlarmConfigEntry 30 }

dsx3E3BIP8ES24HrThreshold OBJECT-TYPE
    SYNTAX INTEGER(0..2147483647)
    ACCESS read-write
    STATUS mandatory
    DESCRIPTION
        "G.832 BIP-8 error monitoring byte. 24 hour
         threshold value.
         This has no significance to E3 with G.751 framing
         which is used in FRSM-VHS
         This object is not supported in CESM-T3/E3"
    ::= { dsx3AlarmConfigEntry 31 }

dsx3E3BIP8SES15MinThreshold OBJECT-TYPE
    SYNTAX INTEGER(0..2147483647)
    ACCESS read-write
    STATUS mandatory
    DESCRIPTION
        "G.832 BIP-8 error monitoring byte. 15 minute
         threshold value.
         This has no significance to E3 with G.751 framing
         which is used in FRSM-VHS
         This object is not supported in CESM-T3/E3"
    ::= { dsx3AlarmConfigEntry 32 }

dsx3E3BIP8SES24HrThreshold OBJECT-TYPE
    SYNTAX INTEGER(0..2147483647)
    ACCESS read-write
    STATUS mandatory
    DESCRIPTION
        "G.832 BIP-8 error monitoring byte. 24 hour
         threshold value.
         This has no significance to E3 with G.751 framing
         which is used in FRSM-VHS
         This object is not supported in CESM-T3/E3"
    ::= { dsx3AlarmConfigEntry 33 }

dsx3CCV15MinThreshold OBJECT-TYPE
    SYNTAX INTEGER(0..2147483647)
    ACCESS read-write
    STATUS mandatory
    DESCRIPTION
        "The value set in this object determines the 
        value which when exceeded in a 15 minute window 
        causes a statistical alarm to be declared.
        
        This object is not applicable for E3 interface.
        
        This object is not supported in CESM-T3/E3."
    ::= { dsx3AlarmConfigEntry 34 }

dsx3CCV24HrThreshold OBJECT-TYPE
    SYNTAX INTEGER(0..2147483647)
    ACCESS read-write
    STATUS mandatory
    DESCRIPTION
        "The value set in this object determines the 
        value which when exceeded in a sliding 24 hour 
        window causes a statistical alarm to be declared.
        The threshold is checked every 15 minutes for the 
        preceding 24 hour interval
        
        This object is not applicable for E3 interface.
        
        This object is not supported in CESM-T3/E3."
    ::= { dsx3AlarmConfigEntry 35 }

dsx3CES15MinThreshold OBJECT-TYPE
    SYNTAX INTEGER(0..2147483647)
    ACCESS read-write
    STATUS mandatory
    DESCRIPTION
        "The value set in this object determines the 
        value which when exceeded in a 15 minute window 
        causes a statistical alarm to be declared.
        
        This object is not applicable for E3 interface.
        
        This object is not supported in CESM-T3/E3."
    ::= { dsx3AlarmConfigEntry 36 }

dsx3CES24HrThreshold OBJECT-TYPE
    SYNTAX INTEGER(0..2147483647)
    ACCESS read-write
    STATUS mandatory
    DESCRIPTION
        "The value set in this object determines the 
        value which when exceeded in a sliding 24 hour 
        window causes a statistical alarm to be declared.
        
        This object is not applicable for E3 interface.
        
        This object is not supported in CESM-T3/E3."
    ::= { dsx3AlarmConfigEntry 37 }

dsx3CSES15MinThreshold OBJECT-TYPE
    SYNTAX INTEGER(0..2147483647)
    ACCESS read-write
    STATUS mandatory
    DESCRIPTION
        "The value set in this object determines the value
        which when exceeded in a 15 minute window causes
        a statistical alarm to be declared.
        
        This object is not applicable for E3 interface.
        
        This object is not supported in CESM-T3/E3."
    ::= { dsx3AlarmConfigEntry 38 }

dsx3CSES24HrThreshold OBJECT-TYPE
    SYNTAX INTEGER(0..2147483647)
    ACCESS read-write
    STATUS mandatory
    DESCRIPTION
        "The value set in this object determines the value
        which when exceeded in a sliding 24 hour window causes
        a statistical alarm to be declared.
        
        This object is not applicable for E3 interface.
        
        This object is not supported in CESM-T3/E3."
    ::= { dsx3AlarmConfigEntry 39 }

dsx3AlarmTable OBJECT-TYPE
    SYNTAX SEQUENCE OF Dsx3AlarmEntry
    ACCESS not-accessible
    STATUS mandatory
    DESCRIPTION
        "The DSX3 interface alarm table. This table
        contains the performance statistics and Error Events
        based on 15 minute and/or 24 hour interval.
        
        Performance Parameters:
            LES  : Line Errored Seconds
            PES  : P-bit Errored Seconds
            PSES : P-bit Severely Errored Seconds
            CES  : C-bit Errored Seconds
            CSES : C-bit Severely Errored Seconds
            SEFS : Severely Errored Framing Seconds
            UAS  : Unavailable Seconds
        
        Error Events:
            BPV : Bipolar Violation
            EXZ : Excessive Zeros
            LCV : Line Coding Violation
            PCV : P-bit Coding Violation
            CCV : C-bit Coding Violation."
    REFERENCE
        "RFC 2496, Section 2.4.1 and 2.4.2"
    ::= { dsx3Alarm 1 }

dsx3AlarmEntry OBJECT-TYPE
    SYNTAX Dsx3AlarmEntry
    ACCESS not-accessible
    STATUS mandatory
    DESCRIPTION
        "An entry in the DSX3 Alarm table. The bucket
        statistics(15 minute and 24 hour interval statistics)
        are gathered for each ds3/e3 interface.
        Any entry is created automatically when ds3 interface
        is created."
    INDEX { dsx3LineNum }
    ::= { dsx3AlarmTable 1 }

Dsx3AlarmEntry ::= SEQUENCE {
    dsx3LineAlarmState INTEGER,
    dsx3LineStatisticalAlarmState INTEGER,
    dsx3LCVCurrent Counter,
    dsx3LCV15MinBucket Counter,
    dsx3LCV24HrBucket Counter,
    dsx3LESCurrent Counter,
    dsx3LES15MinBucket Counter,
    dsx3LES24HrBucket Counter,
    dsx3LSESCurrent Counter,
    dsx3LSES15MinBucket Counter,
    dsx3LSES24HrBucket Counter,
    dsx3PCVCurrent Counter,
    dsx3PCV15MinBucket Counter,
    dsx3PCV24HrBucket Counter,
    dsx3PESCurrent Counter,
    dsx3PES15MinBucket Counter,
    dsx3PES24HrBucket Counter,
    dsx3PSESCurrent Counter,
    dsx3PSES15MinBucket Counter,
    dsx3PSES24HrBucket Counter,
    dsx3SEFSCurrent Counter,
    dsx3SEFS15MinBucket Counter,
    dsx3SEFS24HrBucket Counter,
    dsx3AISSCurrent Counter,
    dsx3AISS15MinBucket Counter,
    dsx3AISS24HrBucket Counter,
    dsx3UASCurrent Counter,
    dsx3UAS15MinBucket Counter,
    dsx3UAS24HrBucket Counter,
    dsx3PercentLcvEFS INTEGER,
    dsx3E3BIP8CVCurrent Counter,
    dsx3E3BIP8CV15MinBucket Counter,
    dsx3E3BIP8CV24HrBucket Counter,
    dsx3E3BIP8ESCurrent Counter,
    dsx3E3BIP8ES15MinBucket Counter,
    dsx3E3BIP8ES24HrBucket Counter,
    dsx3E3BIP8SESCurrent Counter,
    dsx3E3BIP8SES15MinBucket Counter,
    dsx3E3BIP8SES24HrBucket Counter,
    dsx3LineAlarmClrButton INTEGER,
    dsx3CCVCurrent Counter,
    dsx3CCV15MinBucket Counter,
    dsx3CCV24HrBucket Counter,
    dsx3CESCurrent Counter,
    dsx3CES15MinBucket Counter,
    dsx3CES24HrBucket Counter,
    dsx3CSESCurrent Counter,
    dsx3CSES15MinBucket Counter,
    dsx3CSES24HrBucket Counter
    }

dsx3LineAlarmState OBJECT-TYPE
    SYNTAX INTEGER(0..2147483647)
    ACCESS read-only
    STATUS mandatory
    DESCRIPTION
        "This variable is a bitmap of the DSX3 Line ALarms
        on the card. A value of zero indicates no alarms.
        
        Itemized below are the individual bits:
        BitPosition    Alarm
        -----------    -----
        0              Receiving RAI
        1              Transmitting RAI
        2              Receiving AIS
        3              Transmitting AIS
        4              Receiving OOF
        5              Receiving LOS
        6              Near End Local Loopback in effect
        7              Near End Remote Loopback in effect
        8              Receiving test pattern
        9              Receive LCD
        10             Receiving C-bit Parity pattern"
    DEFVAL { 0 }
    ::= { dsx3AlarmEntry 1 }

dsx3LineStatisticalAlarmState OBJECT-TYPE
    SYNTAX INTEGER(0..2147483647)
    ACCESS read-only
    STATUS mandatory
    DESCRIPTION
        "This is a bitmap of the DSX3 Line Statistical
        Alarms on the card. Zero indicates no alarms.
        
        Itemized below are the individual alarm bits:
        
        BitPosition    Alarm
        -----------    -----
        0              LCV 15 minute threshold exceeded
        1              LCV 24 hour threshold exceeded
        2              LES 15 minute threshold exceeded
        3              LES 24 hour threshold exceeded
        4              LSES 15 minute threshold exceeded
        5              LSES 24 hour threshold exceeded
        6              PCV 15 minute threshold exceeded
        7              PCV 24 hour threshold exceeded
        8              PES 15 minute threshold exceeded
        9              PES 24 hour threshold exceeded
        10             PSES 15 minute threshold exceeded
        11             PSES 24 hour threshold exceeded
        12             SEFS 15 minute threshold exceeded
        13             SEFS 24 hour threshold exceeded
        14             AISS 15 minute threshold exceeded
        15             AISS 24 hour threshold exceeded
        16             UAS 15 minute threshold exceeded
        17             UAS 24 hour threshold exceeded
        18             BIP8CV/G.832 15 minute threshold exceeded
        19             BIP8CV/G.832 24 hour threshold exceeded
        20             BIP8ES/G.832 15 minute threshold exceeded
        21             BIP8ES/G.832 24 hour threshold exceeded
        22             BIP8SES/G.832 15 minute threshold exceeded
        23             BIP8SES/G.832 24 hour threshold exceeded
        24             CCV 15 minute threshold exceeded
        25             CCV 24 hour threshold exceeded
        26             CES 15 minute threshold exceeded
        27             CES 24 hour threshold exceeded
        28             CSES 15 minute threshold exceeded
        29             CSES 24 hour threshold exceeded
        
        Bits 18 to 23 do not have any significance if the framing is
        G.751(which is used in FRSM_VHS)
        only bits 0,1,2,3,4,5,16 and 17 are applicable to CESM-T3/E3.
        "
    DEFVAL { 0 }
    ::= { dsx3AlarmEntry 2 }

dsx3LCVCurrent OBJECT-TYPE
    SYNTAX Counter
    ACCESS read-only
    STATUS mandatory
    DESCRIPTION
        "The number of Line Code Violations(LCV)
        encountered by the interface in current 
        15 minute period."
    ::= { dsx3AlarmEntry 3 }

dsx3LCV15MinBucket OBJECT-TYPE
    SYNTAX Counter
    ACCESS read-only
    STATUS mandatory
    DESCRIPTION
        "The number of Line Code Violations(LCV)
        encountered by the interface in current 
        last 15 minute period."
    ::= { dsx3AlarmEntry 4 }

dsx3LCV24HrBucket OBJECT-TYPE
    SYNTAX Counter
    ACCESS read-only
    STATUS mandatory
    DESCRIPTION
        "The number of Line Code Violations(LCV)
        encountered by the interface in current 
        last 24 hour period."
    ::= { dsx3AlarmEntry 5 }

dsx3LESCurrent OBJECT-TYPE
    SYNTAX Counter
    ACCESS read-only
    STATUS mandatory
    DESCRIPTION
        "The number of Line Errored Seconds(LES)
        encountered by the interface in current 
        15 minute period."
    ::= { dsx3AlarmEntry 6 }

dsx3LES15MinBucket OBJECT-TYPE
    SYNTAX Counter
    ACCESS read-only
    STATUS mandatory
    DESCRIPTION
        "The number of Line Errored Seconds(LES)
        encountered by the interface in last
        15 minute period."
    ::= { dsx3AlarmEntry 7 }

dsx3LES24HrBucket OBJECT-TYPE
    SYNTAX Counter
    ACCESS read-only
    STATUS mandatory
    DESCRIPTION
        "The number of Line Errored Seconds(LES)
        encountered by the interface in last
        24 hour period."
    ::= { dsx3AlarmEntry 8 }

dsx3LSESCurrent OBJECT-TYPE
    SYNTAX Counter
    ACCESS read-only
    STATUS mandatory
    DESCRIPTION
        "The number of Line Severely Errored Seconds(LSES)
        encountered by the interface in current
        15 minute period."
    ::= { dsx3AlarmEntry 9 }

dsx3LSES15MinBucket OBJECT-TYPE
    SYNTAX Counter
    ACCESS read-only
    STATUS mandatory
    DESCRIPTION
        "The number of Line Severely Errored Seconds(LSES)
        encountered by the interface in last
        15 minute period."
    ::= { dsx3AlarmEntry 10 }

dsx3LSES24HrBucket OBJECT-TYPE
    SYNTAX Counter
    ACCESS read-only
    STATUS mandatory
    DESCRIPTION
        "The number of Line Severely Errored Seconds(LSES)
        encountered by the interface in last
        24 hour period."
    ::= { dsx3AlarmEntry 11 }

dsx3PCVCurrent OBJECT-TYPE
    SYNTAX Counter
    ACCESS read-only
    STATUS mandatory
    DESCRIPTION
        "The number of P-bit Coding Violations(PCV)
        encountered by the interface in current
        15 minute period.
        
        This object is not supported in CESM-T3/E3"
    ::= { dsx3AlarmEntry 12 }

dsx3PCV15MinBucket OBJECT-TYPE
    SYNTAX Counter
    ACCESS read-only
    STATUS mandatory
    DESCRIPTION
        "The number of P-bit Coding Violations(PCV)
        encountered by the interface in last
        15 minute period.
        
        This object is not supported in CESM-T3/E3"
    ::= { dsx3AlarmEntry 13 }

dsx3PCV24HrBucket OBJECT-TYPE
    SYNTAX Counter
    ACCESS read-only
    STATUS mandatory
    DESCRIPTION
        "The number of P-bit Coding Violations(PCV)
        encountered by the interface in last
        24 Hour period.
        
        This object is not supported in CESM-T3/E3"
    ::= { dsx3AlarmEntry 14 }

dsx3PESCurrent OBJECT-TYPE
    SYNTAX Counter
    ACCESS read-only
    STATUS mandatory
    DESCRIPTION
        "The number of P-bit Errored Seconds(PES)
        encountered by the interface in current
        15 minute period.
        
        This object is not supported in CESM-T3/E3"
    ::= { dsx3AlarmEntry 15 }

dsx3PES15MinBucket OBJECT-TYPE
    SYNTAX Counter
    ACCESS read-only
    STATUS mandatory
    DESCRIPTION
        "The number of P-bit Errored Seconds(PES)
        encountered by the interface in last
        15 minute period.
        
        This object is not supported in CESM-T3/E3"
    ::= { dsx3AlarmEntry 16 }

dsx3PES24HrBucket OBJECT-TYPE
    SYNTAX Counter
    ACCESS read-only
    STATUS mandatory
    DESCRIPTION
        "The number of P-bit Errored Seconds(PES)
        encountered by the interface in last
        24 Hour period.
        
        This object is not supported in CESM-T3/E3"
    ::= { dsx3AlarmEntry 17 }

dsx3PSESCurrent OBJECT-TYPE
    SYNTAX Counter
    ACCESS read-only
    STATUS mandatory
    DESCRIPTION
        "The number of P-bit Severely Errored 
        Seconds(PSES) encountered by the interface 
        in current 15 minute period.
        
        This object is not supported in CESM-T3/E3"
    ::= { dsx3AlarmEntry 18 }

dsx3PSES15MinBucket OBJECT-TYPE
    SYNTAX Counter
    ACCESS read-only
    STATUS mandatory
    DESCRIPTION
        "The number of P-bit Severely Errored 
        Seconds(PSES) encountered by the interface 
        in last 15 minute period.
        
        This object is not supported in CESM-T3/E3"
    ::= { dsx3AlarmEntry 19 }

dsx3PSES24HrBucket OBJECT-TYPE
    SYNTAX Counter
    ACCESS read-only
    STATUS mandatory
    DESCRIPTION
        "The number of P-bit Severely Errored 
        Seconds(PSES) encountered by the interface 
        in last 24 Hour period.
        
        This object is not supported in CESM-T3/E3"
    ::= { dsx3AlarmEntry 20 }

dsx3SEFSCurrent OBJECT-TYPE
    SYNTAX Counter
    ACCESS read-only
    STATUS mandatory
    DESCRIPTION
        "The number of Severely Errored Framing 
        Seconds(PSES) encountered by the interface 
        in current 15 minute period.
        
        This object is not supported in CESM-T3/E3"
    ::= { dsx3AlarmEntry 21 }

dsx3SEFS15MinBucket OBJECT-TYPE
    SYNTAX Counter
    ACCESS read-only
    STATUS mandatory
    DESCRIPTION
        "The number of Severely Errored Framing 
        Seconds(PSES) encountered by the interface 
        in last 15 minute period.
        
        This object is not supported in CESM-T3/E3"
    ::= { dsx3AlarmEntry 22 }

dsx3SEFS24HrBucket OBJECT-TYPE
    SYNTAX Counter
    ACCESS read-only
    STATUS mandatory
    DESCRIPTION
        "The number of Severely Errored Framing 
        Seconds(PSES) encountered by the interface 
        in last 24 Hour period.
        
        This object is not supported in CESM-T3/E3"
    ::= { dsx3AlarmEntry 23 }

dsx3AISSCurrent OBJECT-TYPE
    SYNTAX Counter
    ACCESS read-only
    STATUS mandatory
    DESCRIPTION
        "The number of AIS Severely Errored Seconds
        encountered by the interface in current 15 minute
        period.
        
        This object is not supported in CESM-T3/E3"
    ::= { dsx3AlarmEntry 24 }

dsx3AISS15MinBucket OBJECT-TYPE
    SYNTAX Counter
    ACCESS read-only
    STATUS mandatory
    DESCRIPTION
        "The number of AIS Severely Errored Seconds
        encountered by the interface in last 15 minute
        period.
        
        This object is not supported in CESM-T3/E3"
    ::= { dsx3AlarmEntry 25 }

dsx3AISS24HrBucket OBJECT-TYPE
    SYNTAX Counter
    ACCESS read-only
    STATUS mandatory
    DESCRIPTION
        "The number of AIS Severely Errored Seconds
        encountered by the interface in last 24 Hour
        period.
        
        This object is not supported in CESM-T3/E3"
    ::= { dsx3AlarmEntry 26 }

dsx3UASCurrent OBJECT-TYPE
    SYNTAX Counter
    ACCESS read-only
    STATUS mandatory
    DESCRIPTION
        "The number of Unavailable Seconds(UAS)
        encountered by the interface in current
        15 minute period."
    ::= { dsx3AlarmEntry 27 }

dsx3UAS15MinBucket OBJECT-TYPE
    SYNTAX Counter
    ACCESS read-only
    STATUS mandatory
    DESCRIPTION
        "The number of Unavailable Seconds(UAS)
        encountered by the interface in last
        15 minute period."
    ::= { dsx3AlarmEntry 28 }

dsx3UAS24HrBucket OBJECT-TYPE
    SYNTAX Counter
    ACCESS read-only
    STATUS mandatory
    DESCRIPTION
        "The number of Unavailable Seconds(UAS)
        encountered by the interface in last
        24 Hour period."
    ::= { dsx3AlarmEntry 29 }

dsx3PercentLcvEFS OBJECT-TYPE
    SYNTAX INTEGER(0..100)
    ACCESS read-only
    STATUS mandatory
    DESCRIPTION
        "This object gives the percentage of 
        seconds without any LCV Errors in the
        total elapsed seconds."
    ::= { dsx3AlarmEntry 30 }

dsx3E3BIP8CVCurrent OBJECT-TYPE
    SYNTAX Counter
    ACCESS read-only
    STATUS mandatory
    DESCRIPTION
        "The number of G.832 BIP-8 Coding Violations
        (CV) encountered by the interface in current
        15 minute period.
        
        This object is not supported in FRSM-VHS and
        CESM-T3/E3"
    ::= { dsx3AlarmEntry 31 }

dsx3E3BIP8CV15MinBucket OBJECT-TYPE
    SYNTAX Counter
    ACCESS read-only
    STATUS mandatory
    DESCRIPTION
        "The number of G.832 BIP-8 Coding Violations
        (CV) encountered by the interface in last
        15 minute period.
        
        This object is not supported in FRSM-VHS and
        CESM-T3/E3"
    ::= { dsx3AlarmEntry 32 }

dsx3E3BIP8CV24HrBucket OBJECT-TYPE
    SYNTAX Counter
    ACCESS read-only
    STATUS mandatory
    DESCRIPTION
        "The number of G.832 BIP-8 Coding Violations
        (CV) encountered by the interface in last
        24 Hour period.
        
        This object is not supported in FRSM-VHS and
        CESM-T3/E3"
    ::= { dsx3AlarmEntry 33 }

dsx3E3BIP8ESCurrent OBJECT-TYPE
    SYNTAX Counter
    ACCESS read-only
    STATUS mandatory
    DESCRIPTION
        "The number of G.832 BIP-8 Errored Seconds(ES)
        encountered by the interface in current
        15 minute period.
        
        This object is not supported in FRSM-VHS and
        CESM-T3/E3"
    ::= { dsx3AlarmEntry 34 }

dsx3E3BIP8ES15MinBucket OBJECT-TYPE
    SYNTAX Counter
    ACCESS read-only
    STATUS mandatory
    DESCRIPTION
        "The number of G.832 BIP-8 Errored Seconds(ES)
        encountered by the interface in last
        15 minute period.
        
        This object is not supported in FRSM-VHS and
        CESM-T3/E3"
    ::= { dsx3AlarmEntry 35 }

dsx3E3BIP8ES24HrBucket OBJECT-TYPE
    SYNTAX Counter
    ACCESS read-only
    STATUS mandatory
    DESCRIPTION
        "The number of G.832 BIP-8 Errored Seconds(ES)
        encountered by the interface in last
        24 Hour period.
        
        This object is not supported in FRSM-VHS and
        CESM-T3/E3"
    ::= { dsx3AlarmEntry 36 }

dsx3E3BIP8SESCurrent OBJECT-TYPE
    SYNTAX Counter
    ACCESS read-only
    STATUS mandatory
    DESCRIPTION
        "The number of G.832 BIP-8 Severely Errored Seconds(SES)
        encountered by the interface in current 15 minute period.
        
        This object is not supported in FRSM-VHS and
        CESM-T3/E3"
    ::= { dsx3AlarmEntry 37 }

dsx3E3BIP8SES15MinBucket OBJECT-TYPE
    SYNTAX Counter
    ACCESS read-only
    STATUS mandatory
    DESCRIPTION
        "The number of G.832 BIP-8 Severely Errored Seconds(SES)
        encountered by the interface in last 15 minute period.
        
        This object is not supported in FRSM-VHS and
        CESM-T3/E3"
    ::= { dsx3AlarmEntry 38 }

dsx3E3BIP8SES24HrBucket OBJECT-TYPE
    SYNTAX Counter
    ACCESS read-only
    STATUS mandatory
    DESCRIPTION
        "The number of G.832 BIP-8 Severely Errored Seconds(SES)
        encountered by the interface in last 24 Hour period.
        
        This object is not supported in FRSM-VHS and
        CESM-T3/E3"
    ::= { dsx3AlarmEntry 39 }

dsx3LineAlarmClrButton OBJECT-TYPE
    SYNTAX INTEGER {
        noAction(1),
        clear(2)
        }
    ACCESS read-write
    STATUS mandatory
    DESCRIPTION
        "Setting this object to dsx3LineAlarmClear will
         cause all the alarms statuses and counters to reset."
    ::= { dsx3AlarmEntry 40 }

dsx3CCVCurrent OBJECT-TYPE
    SYNTAX Counter
    ACCESS read-only
    STATUS mandatory
    DESCRIPTION
        "The number of C-bit Coding Violations(CCV)
        encountered by the interface in current
        15 minute period.
        
        This object is not supported in CESM-T3/E3"
    ::= { dsx3AlarmEntry 41 }

dsx3CCV15MinBucket OBJECT-TYPE
    SYNTAX Counter
    ACCESS read-only
    STATUS mandatory
    DESCRIPTION
        "The number of C-bit Coding Violations(CCV)
        encountered by the interface in last
        15 minute period.
        
        This object is not supported in CESM-T3/E3"
    ::= { dsx3AlarmEntry 42 }

dsx3CCV24HrBucket OBJECT-TYPE
    SYNTAX Counter
    ACCESS read-only
    STATUS mandatory
    DESCRIPTION
        "The number of C-bit Coding Violations(CCV)
        encountered by the interface in last
        24 Hour period.
        
        This object is not supported in CESM-T3/E3"
    ::= { dsx3AlarmEntry 43 }

dsx3CESCurrent OBJECT-TYPE
    SYNTAX Counter
    ACCESS read-only
    STATUS mandatory
    DESCRIPTION
        "The number of C-bit Errored Seconds(CES)
        encountered by the interface in current
        15 minute period.
        
        This object is not supported in CESM-T3/E3"
    ::= { dsx3AlarmEntry 44 }

dsx3CES15MinBucket OBJECT-TYPE
    SYNTAX Counter
    ACCESS read-only
    STATUS mandatory
    DESCRIPTION
        "The number of C-bit Errored Seconds(CES)
        encountered by the interface in last
        15 minute period.
        
        This object is not supported in CESM-T3/E3"
    ::= { dsx3AlarmEntry 45 }

dsx3CES24HrBucket OBJECT-TYPE
    SYNTAX Counter
    ACCESS read-only
    STATUS mandatory
    DESCRIPTION
        "The number of C-bit Errored Seconds(CES)
        encountered by the interface in last
        24 Hour period.
        
        This object is not supported in CESM-T3/E3"
    ::= { dsx3AlarmEntry 46 }

dsx3CSESCurrent OBJECT-TYPE
    SYNTAX Counter
    ACCESS read-only
    STATUS mandatory
    DESCRIPTION
        "The number of C-bit Severely Errored Seconds(CSES)
        encountered by the interface in current 15 minute period.
        
        This object is not supported in CESM-T3/E3"
    ::= { dsx3AlarmEntry 47 }

dsx3CSES15MinBucket OBJECT-TYPE
    SYNTAX Counter
    ACCESS read-only
    STATUS mandatory
    DESCRIPTION
        "The number of C-bit Severely Errored Seconds(CSES)
        encountered by the interface in last 15 minute period.
        
        This object is not supported in CESM-T3/E3"
    ::= { dsx3AlarmEntry 48 }

dsx3CSES24HrBucket OBJECT-TYPE
    SYNTAX Counter
    ACCESS read-only
    STATUS mandatory
    DESCRIPTION
        "The number of C-bit Severely Errored Seconds(CSES)
        encountered by the interface in last 24 Hour period.
        
        This object is not supported in CESM-T3/E3"
    ::= { dsx3AlarmEntry 49 }

dsx3CounterTable OBJECT-TYPE
    SYNTAX SEQUENCE OF Dsx3CounterEntry
    ACCESS not-accessible
    STATUS mandatory
    DESCRIPTION
        "This table is for ds3/e3 statistics. This table
        maintains the number of times the line encountered
        LOS, LOF, AIS, RAI, CCV and Framing Errors(FE)
        from the time it is up. Error statistics are
        cleared when the line is brought up from the failure
        state."
    ::= { dsx3Counter 1 }

dsx3CounterEntry OBJECT-TYPE
    SYNTAX Dsx3CounterEntry
    ACCESS not-accessible
    STATUS mandatory
    DESCRIPTION
        "An entry in the table. Statistics are gathered
        for each ds3/e3 interface. An entry is created
        automatically for each ds3/e3 interface that
        is activated."
    INDEX { dsx3LineNum }
    ::= { dsx3CounterTable 1 }

Dsx3CounterEntry ::= SEQUENCE {
    dsx3RcvLOSCount Counter,
    dsx3RcvOOFCount Counter,
    dsx3RAICount Counter,
    dsx3CCVCount Counter,
    dsx3FECount Counter,
    dsx3AtmHECCount Counter,
    dsx3AtmHECSecCount Counter,
    dsx3AtmSEHECSecCount Counter,
    dsx3CounterClrButton INTEGER,
    dsx3RcvPERRCounter Counter,
    dsx3RcvFEBECounter Counter,
    dsx3RcvEXZCounter Counter,
    dsx3LCVCount Counter
    }

dsx3RcvLOSCount OBJECT-TYPE
    SYNTAX Counter
    ACCESS read-only
    STATUS mandatory
    DESCRIPTION
        "The number of times the Loss of Signal was detected
         with or without integrating to LOS alarm."
    ::= { dsx3CounterEntry 1 }

dsx3RcvOOFCount OBJECT-TYPE
    SYNTAX Counter
    ACCESS read-only
    STATUS mandatory
    DESCRIPTION
        "The number of times the Out of Frame was detected
         with or without integrating to OOF alarm.
         This object is not supported in CESM-T3/E3"
    ::= { dsx3CounterEntry 2 }

dsx3RAICount OBJECT-TYPE
    SYNTAX Counter
    ACCESS read-only
    STATUS mandatory
    DESCRIPTION
        "The number of times Yellow Alarms was detected with
         or without integrating to RAI alarm.
         This object is not supported in CESM-T3/E3"
    ::= { dsx3CounterEntry 3 }

dsx3CCVCount OBJECT-TYPE
    SYNTAX Counter
    ACCESS read-only
    STATUS mandatory
    DESCRIPTION
        "The counter associated with the number of C Bit
         Coding Violations encountered by a DS3/E3 interface.
         This object is not supported in CESM-T3/E3"
    ::= { dsx3CounterEntry 4 }

dsx3FECount OBJECT-TYPE
    SYNTAX Counter
    ACCESS read-only
    STATUS mandatory
    DESCRIPTION
        "The number of Framing Pattern Errors encountered by
        a DS3/E3 interface.
        This object is not supported in CESM-T3/E3"
    ::= { dsx3CounterEntry 5 }

dsx3AtmHECCount OBJECT-TYPE
    SYNTAX Counter
    ACCESS read-only
    STATUS mandatory
    DESCRIPTION
        "The number of Header Check Sequence(HCS) Errors.
        This object is not supported in CESM-T3/E3"
    ::= { dsx3CounterEntry 6 }

dsx3AtmHECSecCount OBJECT-TYPE
    SYNTAX Counter
    ACCESS read-only
    STATUS mandatory
    DESCRIPTION
        "The number of HEC errored seconds.
        This object is not supported in CESM-T3/E3"
    ::= { dsx3CounterEntry 7 }

dsx3AtmSEHECSecCount OBJECT-TYPE
    SYNTAX Counter
    ACCESS read-only
    STATUS mandatory
    DESCRIPTION
        "The number of Severely HEC error seconds.
         This object is not supported in CESM-T3/E3"
    ::= { dsx3CounterEntry 8 }

dsx3CounterClrButton OBJECT-TYPE
    SYNTAX INTEGER {
        noAction(1),
        clear(2)
        }
    ACCESS read-write
    STATUS mandatory
    DESCRIPTION
        "This variable is used to clear all the counters."
    ::= { dsx3CounterEntry 9 }

dsx3RcvPERRCounter OBJECT-TYPE
    SYNTAX Counter
    ACCESS read-only
    STATUS mandatory
    DESCRIPTION
        "The number of P-bit parity error.
        This object is not supported in CESM-T3/E3"
    ::= { dsx3CounterEntry 10 }

dsx3RcvFEBECounter OBJECT-TYPE
    SYNTAX Counter
    ACCESS read-only
    STATUS mandatory
    DESCRIPTION
        "The number of Far-end block error.
        This object is not supported in CESM-T3/E3"
    ::= { dsx3CounterEntry 11 }

dsx3RcvEXZCounter OBJECT-TYPE
    SYNTAX Counter
    ACCESS read-only
    STATUS mandatory
    DESCRIPTION
        "The number of excessive zeros
        This object is not supported in CESM-T3/E3"
    ::= { dsx3CounterEntry 12 }

dsx3LCVCount OBJECT-TYPE
    SYNTAX Counter
    ACCESS read-only
    STATUS mandatory
    DESCRIPTION
        "The counter associated with the number of Line
        Coding Violations encountered by a DS3/E3 interface."
    ::= { dsx3CounterEntry 13 }

dsx3PlcpConfigTable OBJECT-TYPE
    SYNTAX SEQUENCE OF Dsx3PlcpConfigEntry
    ACCESS not-accessible
    STATUS mandatory
    DESCRIPTION
        "This table contains ATM interface DS3 PLCP
        configuration parameters."
    ::= { dsx3PlcpConfig 1 }

dsx3PlcpConfigEntry OBJECT-TYPE
    SYNTAX Dsx3PlcpConfigEntry
    ACCESS not-accessible
    STATUS mandatory
    DESCRIPTION
        "An entry in the DSX3 PLCP Configuration table."
    INDEX { dsx3PlcpNum }
    ::= { dsx3PlcpConfigTable 1 }

Dsx3PlcpConfigEntry ::= SEQUENCE {
    dsx3PlcpNum INTEGER,
    dsx3PlcpCellFraming INTEGER,
    dsx3PlcpPayloadScramble INTEGER,
    dsx3PlcpLoopCommand INTEGER
    }

dsx3PlcpNum OBJECT-TYPE
    SYNTAX INTEGER(1..2147483647)
    ACCESS read-only
    STATUS mandatory
    DESCRIPTION
        "This object identifies the dsx3 PLCP interface.
        The value of this object must be same as the value
        specified in 'dsx3LineNum' object from cwDsx3ConfigTable."
    ::= { dsx3PlcpConfigEntry 1 }

dsx3PlcpCellFraming OBJECT-TYPE
    SYNTAX INTEGER {
        framingByPlcp(1),
        framingbyAtmHec(2)
        }
    ACCESS read-only
    STATUS mandatory
    DESCRIPTION
        "The value for this object sets the cell delineation
        method used by the interface. The cell delineation
        defines how a receiving device recognizes the start
        and end of an ATM cell.
        
        framingByPlcp   (1): The ATM Cells are in predetermined
                             location within each PLCP row, so
                             no additional method is needed to
                             delineate ATM cells.
        framingByAtmHec (2): The Header Error Control field of the
                             ATM cell header is used to delineate
                             ATM cells."
    ::= { dsx3PlcpConfigEntry 2 }

dsx3PlcpPayloadScramble OBJECT-TYPE
    SYNTAX INTEGER {
        enableScrambling(1),
        disableScrambling(2)
        }
    ACCESS read-write
    STATUS mandatory
    DESCRIPTION
        "The value for this object is used for enabling/disabling
        PLCP cell scrambling."
    ::= { dsx3PlcpConfigEntry 3 }

dsx3PlcpLoopCommand OBJECT-TYPE
    SYNTAX INTEGER {
        noLoop(1),
        remoteLineLoop(2),
        localLineLoop(3)
        }
    ACCESS read-write
    STATUS mandatory
    DESCRIPTION
        "specifies the type of loopback on the line.
        
        The possible value(s) are :
          noLoop         (1): Not in loopback.
          remoteLineLoop (2): Remote Line Loopback.
          localLineLoop  (3): Local Line Loopback."
    ::= { dsx3PlcpConfigEntry 4 }

dsx3PlcpNumOfValidEntries OBJECT-TYPE
    SYNTAX INTEGER(0..2147483647)
    ACCESS read-only
    STATUS mandatory
    DESCRIPTION
        "This variable indicates the maximum number of 
        entries in cwDsx3ConfigTable."
    ::= { dsx3PlcpConfig 2 }

dsx3PlcpAlarmConfigTable OBJECT-TYPE
    SYNTAX SEQUENCE OF Dsx3PlcpAlarmConfigEntry
    ACCESS not-accessible
    STATUS mandatory
    DESCRIPTION
        "This table contains the ATM interface PLCP alarm
        parameters."
    ::= { dsx3PlcpAlarmConfig 1 }

dsx3PlcpAlarmConfigEntry OBJECT-TYPE
    SYNTAX Dsx3PlcpAlarmConfigEntry
    ACCESS not-accessible
    STATUS mandatory
    DESCRIPTION
        "An entry in the DSX3 PLCP Alarm Configuration table.
        
        Thresholds may be configured for:
        
            Errored Seconds           (ES)
            Coding Violations         (CV)
            Severely Errored Seconds  (SES)
            Unavailable Seconds       (UAS),
        Once these thresholds are exceeded, minor or major alarms
        are raised. Please refer to RFC2496 for descriptions of these
        errors."
    INDEX { dsx3PlcpNum }
    ::= { dsx3PlcpAlarmConfigTable 1 }

Dsx3PlcpAlarmConfigEntry ::= SEQUENCE {
    dsx3PlcpRedSeverity INTEGER,
    dsx3PlcpRAISeverity INTEGER,
    dsx3PlcpLssSeverity INTEGER,
    dsx3PlcpLssEnable INTEGER,
    dsx3PlcpLssCodeConnected INTEGER,
    dsx3PlcpLssCodeRxLinkDn INTEGER,
    dsx3PlcpLssCodeRxLinkUp INTEGER,
    dsx3PlcpStatisticalAlarmSeverity INTEGER,
    dsx3PlcpBip8CV15MinThreshold INTEGER,
    dsx3PlcpBip8CV24HrThreshold INTEGER,
    dsx3PlcpBip8ES15MinThreshold INTEGER,
    dsx3PlcpBip8ES24HrThreshold INTEGER,
    dsx3PlcpBip8SES15MinThreshold INTEGER,
    dsx3PlcpBip8SES24HrThreshold INTEGER,
    dsx3PlcpSEFS15MinThreshold INTEGER,
    dsx3PlcpSEFS24HrThreshold INTEGER,
    dsx3PlcpUAS15MinThreshold INTEGER,
    dsx3PlcpUAS24HrThreshold INTEGER
    }

dsx3PlcpRedSeverity OBJECT-TYPE
    SYNTAX INTEGER {
        minor(1),
        major(2)
        }
    ACCESS read-write
    STATUS mandatory
    DESCRIPTION
        "This variable is used to setup the severity of PLCP RED
        alarm. So when PLCP_OOF alarm is detected the card will
        declare the alarm with appropriate severity status.
        A major alarm will cause the audible notification
        and the MAJOR ALARM LED will be turned ON.
        A minor alarm will just turn on the MINOR ALARM LED."
    ::= { dsx3PlcpAlarmConfigEntry 1 }

dsx3PlcpRAISeverity OBJECT-TYPE
    SYNTAX INTEGER {
        minor(1),
        major(2)
        }
    ACCESS read-write
    STATUS mandatory
    DESCRIPTION
        "This variable is used to setup the severity of 
        PLCP RAI alarm. So when PLCP RAI alarm is detected
        the card will send the alarm with appropriate severity 
        status. 
        A major alarm will cause the audible notification
        and the MAJOR ALARM LED will be turned ON.
        A minor alarm will just turn on the MINOR ALARM LED."
    ::= { dsx3PlcpAlarmConfigEntry 2 }

dsx3PlcpLssSeverity OBJECT-TYPE
    SYNTAX INTEGER {
        minor(1),
        major(2)
        }
    ACCESS read-write
    STATUS mandatory
    DESCRIPTION
        "This variable is used to setup the severity of 
        PLCP RAI alarm. So when PLCP LSS alarm is detected
        the card will send the alarm with appropriate severity 
        status.
        A major alarm will cause the audible notification
        and the MAJOR ALARM LED will be turned ON.
        A minor alarm will just turn on the MINOR ALARM LED."
    ::= { dsx3PlcpAlarmConfigEntry 3 }

dsx3PlcpLssEnable OBJECT-TYPE
    SYNTAX INTEGER {
        lssEnable(1),
        lssDisable(2)
        }
    ACCESS read-write
    STATUS mandatory
    DESCRIPTION
        "This objects specifies whether the LSS feature is 
        enabled/disabled."
    ::= { dsx3PlcpAlarmConfigEntry 4 }

dsx3PlcpLssCodeConnected OBJECT-TYPE
    SYNTAX INTEGER(0..2147483647)
    ACCESS read-write
    STATUS mandatory
    DESCRIPTION
        "This object derfines the value of the LSS code 
        that is to be interpreted as Link Connected."
    ::= { dsx3PlcpAlarmConfigEntry 5 }

dsx3PlcpLssCodeRxLinkDn OBJECT-TYPE
    SYNTAX INTEGER(0..2147483647)
    ACCESS read-write
    STATUS mandatory
    DESCRIPTION
        "This object defines the value of the LSS code 
        that is to be identified as Receive Link Down."
    ::= { dsx3PlcpAlarmConfigEntry 6 }

dsx3PlcpLssCodeRxLinkUp OBJECT-TYPE
    SYNTAX INTEGER(0..2147483647)
    ACCESS read-write
    STATUS mandatory
    DESCRIPTION
        "This object defines the value of the LSS code that 
        is to be interpreted as Receive Link Up."
    ::= { dsx3PlcpAlarmConfigEntry 7 }

dsx3PlcpStatisticalAlarmSeverity OBJECT-TYPE
    SYNTAX INTEGER {
        minor(1),
        major(2)
        }
    ACCESS read-write
    STATUS mandatory
    DESCRIPTION
        "This variable sets up the severity of PLCP Statistical
        alarm. So when PLCP Statistical alarm is detected, the 
        card will send the alarm with appropriate severity.
        A major alarm will cause the audible notification
        and the MAJOR ALARM LED will be turned ON.
        A minor alarm will just turn on the MINOR ALARM LED."
    ::= { dsx3PlcpAlarmConfigEntry 8 }

dsx3PlcpBip8CV15MinThreshold OBJECT-TYPE
    SYNTAX INTEGER(0..2147483647)
    ACCESS read-write
    STATUS mandatory
    DESCRIPTION
        "The value set in this object determines the 
        value which when exceeded in a 15 minute window 
        causes a statistical alarm to be declared."
    ::= { dsx3PlcpAlarmConfigEntry 9 }

dsx3PlcpBip8CV24HrThreshold OBJECT-TYPE
    SYNTAX INTEGER(0..2147483647)
    ACCESS read-write
    STATUS mandatory
    DESCRIPTION
        "The value set in this object determines the 
        value which when exceeded in a sliding 24 hour 
        window causes a statistical alarm to be declared. 
        The threshold is checked every 15 minutes for the 
        preceding 24 hour interval"
    ::= { dsx3PlcpAlarmConfigEntry 10 }

dsx3PlcpBip8ES15MinThreshold OBJECT-TYPE
    SYNTAX INTEGER(0..2147483647)
    ACCESS read-write
    STATUS mandatory
    DESCRIPTION
        "The value set in this object determines the 
        value which when exceeded in a 15 minute window
        causes a statistical alarm to be declared."
    ::= { dsx3PlcpAlarmConfigEntry 11 }

dsx3PlcpBip8ES24HrThreshold OBJECT-TYPE
    SYNTAX INTEGER(0..2147483647)
    ACCESS read-write
    STATUS mandatory
    DESCRIPTION
        "The value set in this object determines the 
        value which when exceeded in a sliding 24 hour 
        window causes a statistical alarm to be declared.
        The threshold is checked every 15 minutes for the 
        preceding 24 hour interval"
    ::= { dsx3PlcpAlarmConfigEntry 12 }

dsx3PlcpBip8SES15MinThreshold OBJECT-TYPE
    SYNTAX INTEGER(0..2147483647)
    ACCESS read-write
    STATUS mandatory
    DESCRIPTION
        "The value set in this object determines the
        value which when exceeded in a 15 minute window 
        causes a statistical alarm to be declared."
    ::= { dsx3PlcpAlarmConfigEntry 13 }

dsx3PlcpBip8SES24HrThreshold OBJECT-TYPE
    SYNTAX INTEGER(0..2147483647)
    ACCESS read-write
    STATUS mandatory
    DESCRIPTION
        "The value set in this object determines the 
        value which when exceeded in a sliding 24 hour 
        window causes a statistical alarm to be declared. 
        The threshold is checked every 15 minutes for the 
        preceding 24 hour interval"
    ::= { dsx3PlcpAlarmConfigEntry 14 }

dsx3PlcpSEFS15MinThreshold OBJECT-TYPE
    SYNTAX INTEGER(0..2147483647)
    ACCESS read-write
    STATUS mandatory
    DESCRIPTION
        "The value set in this object determines the 
        value which when exceeded in a 15 minute window 
        causes a statistical alarm to be declared."
    ::= { dsx3PlcpAlarmConfigEntry 15 }

dsx3PlcpSEFS24HrThreshold OBJECT-TYPE
    SYNTAX INTEGER(0..2147483647)
    ACCESS read-write
    STATUS mandatory
    DESCRIPTION
        "The value set in this object determines the 
        value which when exceeded in a sliding 24 hour 
        window causes a statistical alarm to be declared.
        The threshold is checked every 15 minutes for the 
        preceding 24 hour interval"
    ::= { dsx3PlcpAlarmConfigEntry 16 }

dsx3PlcpUAS15MinThreshold OBJECT-TYPE
    SYNTAX INTEGER(0..2147483647)
    ACCESS read-write
    STATUS mandatory
    DESCRIPTION
        "The value set in this object determines the 
        value which when exceeded in a 15 minute window 
        causes a statistical alarm to be declared."
    ::= { dsx3PlcpAlarmConfigEntry 17 }

dsx3PlcpUAS24HrThreshold OBJECT-TYPE
    SYNTAX INTEGER(0..2147483647)
    ACCESS read-write
    STATUS mandatory
    DESCRIPTION
        "The value set in this object determines the 
        value which when exceeded in a sliding 24 hour 
        window causes a statistical alarm to be declared.
        The threshold is checked every 15 minutes for the 
        preceding 24 hour interval"
    ::= { dsx3PlcpAlarmConfigEntry 18 }

dsx3PlcpAlarmTable OBJECT-TYPE
    SYNTAX SEQUENCE OF Dsx3PlcpAlarmEntry
    ACCESS not-accessible
    STATUS mandatory
    DESCRIPTION
        "This table contains ATM interface DS3 PLCP
        alarm configuration."
    ::= { dsx3PlcpAlarm 1 }

dsx3PlcpAlarmEntry OBJECT-TYPE
    SYNTAX Dsx3PlcpAlarmEntry
    ACCESS not-accessible
    STATUS mandatory
    DESCRIPTION
        "An entry in the ATM DS3 PLCP alarm table.
        Bucket statistics (15 minute and 24 Hour interval)
        are gathered for each ds3/e3 interface automatically."
    INDEX { dsx3PlcpNum }
    ::= { dsx3PlcpAlarmTable 1 }

Dsx3PlcpAlarmEntry ::= SEQUENCE {
    dsx3PlcpLineAlarmState INTEGER,
    dsx3PlcpLineStatisticalAlarmState INTEGER,
    dsx3PlcpBip8CVCurrent Counter,
    dsx3PlcpBip8CV15MinBucket Counter,
    dsx3PlcpBip8CV24HrBucket Counter,
    dsx3PlcpBip8ESCurrent Counter,
    dsx3PlcpBip8ES15MinBucket Counter,
    dsx3PlcpBip8ES24HrBucket Counter,
    dsx3PlcpBip8SESCurrent Counter,
    dsx3PlcpBip8SES15MinBucket Counter,
    dsx3PlcpBip8SES24HrBucket Counter,
    dsx3PlcpSEFSCurrent Counter,
    dsx3PlcpSEFS15MinBucket Counter,
    dsx3PlcpSEFS24HrBucket Counter,
    dsx3PlcpUASCurrent Counter,
    dsx3PlcpUAS15MinBucket Counter,
    dsx3PlcpUAS24HrBucket Counter,
    dsx3PlcpAlarmClrButton INTEGER
    }

dsx3PlcpLineAlarmState OBJECT-TYPE
    SYNTAX INTEGER(0..511)
    ACCESS read-only
    STATUS mandatory
    DESCRIPTION
        "This variable is a bitmap of the DSX3 Line alarms.
        A value of zero indicates no alarms.
        
        Itemized below are the individual bits:
        
           BitPosition    Alarm
           -----------    -----
           0              Receiving RAI
           1              Transmitting RAI
           2              Receiving OOF
           3              Receiving LSS Link Up
           4              Transmitting LSS Link Up
           5              Receiving LSS Link Down
           6              Transmitting LSS Link Down
           7              Near End Local Loopback in effect
           8              Near End Remote Loopback in effect
                    "
    ::= { dsx3PlcpAlarmEntry 1 }

dsx3PlcpLineStatisticalAlarmState OBJECT-TYPE
    SYNTAX INTEGER(0..2147483647)
    ACCESS read-only
    STATUS mandatory
    DESCRIPTION
        "This variable is a bitmap of the DSX3 Line Statictical
        Alarms on the card. A value of zero indicates no alarms.
        
        Itemized below are the individual alarm bits:
        
        BitPosition    Alarm
        -----------    -----
        0              Bip8CV 15 minute threshold exceeded
        1              Bip8CV 24 hour threshold exceeded
        2              Bip8ES 15 minute threshold exceeded
        3              Bip8ES 24 hour threshold exceeded
        4              Bip8SES 15 minute threshold exceeded
        5              Bip8SES 24 hour threshold exceeded
        6              Plcp SEFS 15 minute threshold exceeded
        7              Plcp SEFS 24 hour threshold exceeded
        8              Plcp UAS 15 minute threshold exceeded
        9              Plcp UAS 24 hour threshold exceeded
                    "
    ::= { dsx3PlcpAlarmEntry 2 }

dsx3PlcpBip8CVCurrent OBJECT-TYPE
    SYNTAX Counter
    ACCESS read-only
    STATUS mandatory
    DESCRIPTION
        "This counter counts the number of 
        BIP-8 code violations encountered by the interface."
    ::= { dsx3PlcpAlarmEntry 3 }

dsx3PlcpBip8CV15MinBucket OBJECT-TYPE
    SYNTAX Counter
    ACCESS read-only
    STATUS mandatory
    DESCRIPTION
        "The counter associated with the number of 
        BIP-8 code violations in the last 15 minute period 
        encountered by the interface."
    ::= { dsx3PlcpAlarmEntry 4 }

dsx3PlcpBip8CV24HrBucket OBJECT-TYPE
    SYNTAX Counter
    ACCESS read-only
    STATUS mandatory
    DESCRIPTION
        "The counter associated with the number of 
        BIP-8 code violations in the last 24 hour period 
        encountered by the interface."
    ::= { dsx3PlcpAlarmEntry 5 }

dsx3PlcpBip8ESCurrent OBJECT-TYPE
    SYNTAX Counter
    ACCESS read-only
    STATUS mandatory
    DESCRIPTION
        "This counter counts the number of 
        BIP-8 code violations Errored Seconds
        encountered by the interface."
    ::= { dsx3PlcpAlarmEntry 6 }

dsx3PlcpBip8ES15MinBucket OBJECT-TYPE
    SYNTAX Counter
    ACCESS read-only
    STATUS mandatory
    DESCRIPTION
        "This counter counts the number of 
        BIP-8 code violations Errored Seconds in the 
        last 15 minutes encountered by the interface."
    ::= { dsx3PlcpAlarmEntry 7 }

dsx3PlcpBip8ES24HrBucket OBJECT-TYPE
    SYNTAX Counter
    ACCESS read-only
    STATUS mandatory
    DESCRIPTION
        "This counter counts the number of 
        BIP-8 code violations Errored Seconds in the
        last 24 hours encountered by the interface."
    ::= { dsx3PlcpAlarmEntry 8 }

dsx3PlcpBip8SESCurrent OBJECT-TYPE
    SYNTAX Counter
    ACCESS read-only
    STATUS mandatory
    DESCRIPTION
        "This counter counts the number of 
        Bip8 code violations Severely Errored Seconds
        encountered by the interface."
    ::= { dsx3PlcpAlarmEntry 9 }

dsx3PlcpBip8SES15MinBucket OBJECT-TYPE
    SYNTAX Counter
    ACCESS read-only
    STATUS mandatory
    DESCRIPTION
        "This counter counts the number of 
        BIP-8 Severely Errored Seconds in the last 
        15 minutes encountered by the interface."
    ::= { dsx3PlcpAlarmEntry 10 }

dsx3PlcpBip8SES24HrBucket OBJECT-TYPE
    SYNTAX Counter
    ACCESS read-only
    STATUS mandatory
    DESCRIPTION
        "This counter counts the number of 
        BIP-8 Severely Errored Seconds in the last
        24 hours encountered by the interface."
    ::= { dsx3PlcpAlarmEntry 11 }

dsx3PlcpSEFSCurrent OBJECT-TYPE
    SYNTAX Counter
    ACCESS read-only
    STATUS mandatory
    DESCRIPTION
        "This counter counts the number of 
        Severely Errored Framing Seconds
        encountered by the interface."
    ::= { dsx3PlcpAlarmEntry 12 }

dsx3PlcpSEFS15MinBucket OBJECT-TYPE
    SYNTAX Counter
    ACCESS read-only
    STATUS mandatory
    DESCRIPTION
        "This counter counts the number of 
        Severely Errored Framing Seconds in the last 
        15 minutes encountered by the interface."
    ::= { dsx3PlcpAlarmEntry 13 }

dsx3PlcpSEFS24HrBucket OBJECT-TYPE
    SYNTAX Counter
    ACCESS read-only
    STATUS mandatory
    DESCRIPTION
        "This counter counts the number of 
        Severely Errored Framing Seconds in the last 
        24 hours encountered by the interface."
    ::= { dsx3PlcpAlarmEntry 14 }

dsx3PlcpUASCurrent OBJECT-TYPE
    SYNTAX Counter
    ACCESS read-only
    STATUS mandatory
    DESCRIPTION
        "This counter counts the number of 
        Unavailable Seconds encountered by the interface."
    ::= { dsx3PlcpAlarmEntry 15 }

dsx3PlcpUAS15MinBucket OBJECT-TYPE
    SYNTAX Counter
    ACCESS read-only
    STATUS mandatory
    DESCRIPTION
        "This counter counts the number of 
        Unavailable Seconds in the last 15 minutes
        encountered by the interface."
    ::= { dsx3PlcpAlarmEntry 16 }

dsx3PlcpUAS24HrBucket OBJECT-TYPE
    SYNTAX Counter
    ACCESS read-only
    STATUS mandatory
    DESCRIPTION
        "This counter counts the number of 
        Unavailable Seconds in the last 24 hours
        encountered by the interface."
    ::= { dsx3PlcpAlarmEntry 17 }

dsx3PlcpAlarmClrButton OBJECT-TYPE
    SYNTAX INTEGER {
        dsx3PlcpAlarmNoAction(1),
        dsx3PlcpAlarmClear(2)
        }
    ACCESS read-write
    STATUS mandatory
    DESCRIPTION
        "This variable is used to clear all the alarms."
    ::= { dsx3PlcpAlarmEntry 18 }

dsx3PlcpCounterTable OBJECT-TYPE
    SYNTAX SEQUENCE OF Dsx3PlcpCounterEntry
    ACCESS not-accessible
    STATUS mandatory
    DESCRIPTION
        "The table for DS3 PLCP counter table."
    ::= { dsx3PlcpCounter 1 }

dsx3PlcpCounterEntry OBJECT-TYPE
    SYNTAX Dsx3PlcpCounterEntry
    ACCESS not-accessible
    STATUS mandatory
    DESCRIPTION
        "An entry in the DS3 PLCP counter table."
    INDEX { dsx3PlcpNum }
    ::= { dsx3PlcpCounterTable 1 }

Dsx3PlcpCounterEntry ::= SEQUENCE {
    dsx3PlcpRcvBip8Count Counter,
    dsx3PlcpRcvOOFCount Counter,
    dsx3PlcpRcvRAICount Counter,
    dsx3PlcpFECount Counter,
    dsx3PlcpFESecCount Counter,
    dsx3PlcpSEFESecCount Counter,
    dsx3PlcpFEBECount Counter,
    dsx3PlcpFEBESecCount Counter,
    dsx3PlcpSEFEBESecCount Counter,
    dsx3PlcpHECCount Counter,
    dsx3PlcpHECSecCount Counter,
    dsx3PlcpSEHECSecCount Counter,
    dsx3PlcpCounterClrButton INTEGER
    }

dsx3PlcpRcvBip8Count OBJECT-TYPE
    SYNTAX Counter
    ACCESS read-only
    STATUS mandatory
    DESCRIPTION
        "The number of BIP-8 errors encountered by
        the interface."
    ::= { dsx3PlcpCounterEntry 1 }

dsx3PlcpRcvOOFCount OBJECT-TYPE
    SYNTAX Counter
    ACCESS read-only
    STATUS mandatory
    DESCRIPTION
        "The number of times the Out of Frame(OOF) was detected
        with or without integrating to OOF alarm."
    ::= { dsx3PlcpCounterEntry 2 }

dsx3PlcpRcvRAICount OBJECT-TYPE
    SYNTAX Counter
    ACCESS read-only
    STATUS mandatory
    DESCRIPTION
        "The number of times Remote Alarm Indication(RAI)
        was detected with or without integrating to RAI alarm."
    ::= { dsx3PlcpCounterEntry 3 }

dsx3PlcpFECount OBJECT-TYPE
    SYNTAX Counter
    ACCESS read-only
    STATUS mandatory
    DESCRIPTION
        "The number of Framing Errors detected."
    ::= { dsx3PlcpCounterEntry 4 }

dsx3PlcpFESecCount OBJECT-TYPE
    SYNTAX Counter
    ACCESS read-only
    STATUS mandatory
    DESCRIPTION
        "The number of Framing Error errored seconds."
    ::= { dsx3PlcpCounterEntry 5 }

dsx3PlcpSEFESecCount OBJECT-TYPE
    SYNTAX Counter
    ACCESS read-only
    STATUS mandatory
    DESCRIPTION
        "The number of Severely errored Framing error seconds."
    ::= { dsx3PlcpCounterEntry 6 }

dsx3PlcpFEBECount OBJECT-TYPE
    SYNTAX Counter
    ACCESS read-only
    STATUS mandatory
    DESCRIPTION
        "The number of Far End Block Errors(FEBE) detected."
    ::= { dsx3PlcpCounterEntry 7 }

dsx3PlcpFEBESecCount OBJECT-TYPE
    SYNTAX Counter
    ACCESS read-only
    STATUS mandatory
    DESCRIPTION
        "The number of FEBE errored seconds."
    ::= { dsx3PlcpCounterEntry 8 }

dsx3PlcpSEFEBESecCount OBJECT-TYPE
    SYNTAX Counter
    ACCESS read-only
    STATUS mandatory
    DESCRIPTION
        "The number of Severely errored FEBE seconds."
    ::= { dsx3PlcpCounterEntry 9 }

dsx3PlcpHECCount OBJECT-TYPE
    SYNTAX Counter
    ACCESS read-only
    STATUS mandatory
    DESCRIPTION
        "The number of HCS Errors."
    ::= { dsx3PlcpCounterEntry 10 }

dsx3PlcpHECSecCount OBJECT-TYPE
    SYNTAX Counter
    ACCESS read-only
    STATUS mandatory
    DESCRIPTION
        "The number of HEC errored seconds."
    ::= { dsx3PlcpCounterEntry 11 }

dsx3PlcpSEHECSecCount OBJECT-TYPE
    SYNTAX Counter
    ACCESS read-only
    STATUS mandatory
    DESCRIPTION
        "The number of Severely HEC error seconds."
    ::= { dsx3PlcpCounterEntry 12 }

dsx3PlcpCounterClrButton OBJECT-TYPE
    SYNTAX INTEGER {
        dsx3PlcpCounterNoAction(1),
        dsx3PlcpCounterClear(2)
        }
    ACCESS read-write
    STATUS mandatory
    DESCRIPTION
        "This variable is used to clear all the counters."
    ::= { dsx3PlcpCounterEntry 13 }

dsx3PlcpCounterValidEntries OBJECT-TYPE
    SYNTAX INTEGER(0..2147483647)
    ACCESS read-only
    STATUS mandatory
    DESCRIPTION
        "The maximum number of entries in 
        the dsx3PlcpCounterTable."
    ::= { dsx3PlcpCounter 2 }

cmDsx3GeneralGroup OBJECT IDENTIFIER ::= { cmDsx3MIBGroups 1 }
-- OBJECT-GROUP
--  Status
--    mandatory
--  Descr
--    The collection of objects which are used for
--    providing number of entries in dsx3 and PLCP
--    tables.
--  objects
--    dsx3LineNumOfValidEntries, dsx3PlcpNumOfValidEntries, 
--    dsx3PlcpCounterValidEntries

cmDsx3ConfGroup OBJECT IDENTIFIER ::= { cmDsx3MIBGroups 2 }
-- OBJECT-GROUP
--  Status
--    mandatory
--  Descr
--    The collection of objects which are used for
--    configuring DS3/E3 interfaces.
--  objects
--    dsx3LineNum, cwDsx3LineType, cwDsx3LineCoding, 
--    cwDsx3LineLength, dsx3LineOOFCriteria, dsx3LineAIScBitsCheck, 
--    dsx3LineLoopbackCommand, dsx3LineXmtFEACCode, dsx3LineEnable, 
--    dsx3FarEndLoopbkLineNum, dsx3LineXmtClockSrc, 
--    dsx3FarEndLoopbkLineStatus, dsx3LineEqualizer, 
--    dsx3NearEndLoopbkLineStatus, dsx3SubRateEnable, dsx3DsuSelect, 
--    dsx3LineRate, dsx3LineScrambleEnable

cmDsx3E3ConfGroup OBJECT IDENTIFIER ::= { cmDsx3MIBGroups 3 }
-- OBJECT-GROUP
--  Status
--    mandatory
--  Descr
--    The collection of objects which are applicable
--    for E3 interfaces only.
--  objects
--    dsx3LineRcvFEACValidation, dsx3TrailTraceOption, 
--    dsx3TxTrailTrace, dsx3RxTrailTrace, dsx3TxTimingMarker, 
--    dsx3RxTimingMarker, dsx3TxPayloadType, dsx3RxPayloadType, 
--    dsx3TxTumf, dsx3RxTumf

cmDsx3BertConfigGroup OBJECT IDENTIFIER ::= { cmDsx3MIBGroups 4 }
-- OBJECT-GROUP
--  Status
--    mandatory
--  Descr
--    The collection of objects which are used for
--    BERT on DS3/E3 interfaces.
--  objects
--    dsx3LineBERTEnable, dsx3LineBERTPattern, dsx3LineBERTResult, 
--    dsx3BERTResultClrButton

cmDsx3StatsGroup OBJECT IDENTIFIER ::= { cmDsx3MIBGroups 5 }
-- OBJECT-GROUP
--  Status
--    mandatory
--  Descr
--    The collection of objects related to
--    DS3/E3 statistics.
--  objects
--    dsx3RcvLOSCount, dsx3RcvOOFCount, dsx3RAICount, dsx3CCVCount, 
--    dsx3FECount, dsx3AtmHECCount, dsx3AtmHECSecCount, 
--    dsx3AtmSEHECSecCount, dsx3CounterClrButton, 
--    dsx3RcvPERRCounter, dsx3RcvFEBECounter, dsx3RcvEXZCounter, 
--    dsx3LCVCount

cmDsx3E3AlarmConfGenGroup OBJECT IDENTIFIER ::= { cmDsx3MIBGroups 6 }
-- OBJECT-GROUP
--  Status
--    mandatory
--  Descr
--    The collection of objects used for
--    alarm configuration of DS3 and E3 interfaces.
--  objects
--    dsx3RedSeverity, dsx3RAISeverity, dsx3NEAlarmUpCount, 
--    dsx3NEAlarmDownCount, dsx3NEAlarmThreshold, 
--    dsx3FEAlarmUpCount, dsx3FEAlarmDownCount, 
--    dsx3FEAlarmThreshold, dsx3StatisticalAlarmSeverity, 
--    dsx3LCV15MinThreshold, dsx3LCV24HrThreshold, 
--    dsx3LES15MinThreshold, dsx3LES24HrThreshold, 
--    dsx3LSES15MinThreshold, dsx3LSES24HrThreshold, 
--    dsx3SEFS15MinThreshold, dsx3SEFS24HrThreshold, 
--    dsx3UAS15MinThreshold, dsx3UAS24HrThreshold

cmDsx3AlarmConfGroup OBJECT IDENTIFIER ::= { cmDsx3MIBGroups 7 }
-- OBJECT-GROUP
--  Status
--    mandatory
--  Descr
--    The collection of objects used for
--    alarm configuration of DS3 interfaces.
--  objects
--    dsx3PCV15MinThreshold, dsx3PCV24HrThreshold, 
--    dsx3PES15MinThreshold, dsx3PES24HrThreshold, 
--    dsx3PSES15MinThreshold, dsx3PSES24HrThreshold, 
--    dsx3AISS15MinThreshold, dsx3AISS24HrThreshold, 
--    dsx3CCV15MinThreshold, dsx3CCV24HrThreshold, 
--    dsx3CES15MinThreshold, dsx3CES24HrThreshold, 
--    dsx3CSES15MinThreshold, dsx3CSES24HrThreshold

cmDsx3E3AlarmConfGroup OBJECT IDENTIFIER ::= { cmDsx3MIBGroups 8 }
-- OBJECT-GROUP
--  Status
--    mandatory
--  Descr
--    The collection of objects used for
--    alarm configuration of E3 interfaces.
--  objects
--    dsx3E3BIP8CV15MinThreshold, dsx3E3BIP8CV24HrThreshold, 
--    dsx3E3BIP8ES15MinThreshold, dsx3E3BIP8ES24HrThreshold, 
--    dsx3E3BIP8SES15MinThreshold, dsx3E3BIP8SES24HrThreshold

cmDsx3AlarmStatsGenGroup OBJECT IDENTIFIER ::= { cmDsx3MIBGroups 9 }
-- OBJECT-GROUP
--  Status
--    mandatory
--  Descr
--    The collection of objects related to
--    performance statistics and error events
--    for ds3 end e3 interfaces.
--  objects
--    dsx3LineAlarmState, dsx3LineStatisticalAlarmState, 
--    dsx3LCVCurrent, dsx3LCV15MinBucket, dsx3LCV24HrBucket, 
--    dsx3LESCurrent, dsx3LES15MinBucket, dsx3LES24HrBucket, 
--    dsx3LSESCurrent, dsx3LSES15MinBucket, dsx3LSES24HrBucket, 
--    dsx3SEFSCurrent, dsx3SEFS15MinBucket, dsx3SEFS24HrBucket, 
--    dsx3UASCurrent, dsx3UAS15MinBucket, dsx3UAS24HrBucket, 
--    dsx3PercentLcvEFS, dsx3LineAlarmClrButton

cmDsx3AlarmStatsGroup OBJECT IDENTIFIER ::= { cmDsx3MIBGroups 10 }
-- OBJECT-GROUP
--  Status
--    mandatory
--  Descr
--    The collection of objects related to
--    performance statistics and error events
--    for ds3 interfaces.
--  objects
--    dsx3PCVCurrent, dsx3PCV15MinBucket, dsx3PCV24HrBucket, 
--    dsx3PESCurrent, dsx3PES15MinBucket, dsx3PES24HrBucket, 
--    dsx3PSESCurrent, dsx3PSES15MinBucket, dsx3PSES24HrBucket, 
--    dsx3AISSCurrent, dsx3AISS15MinBucket, dsx3AISS24HrBucket, 
--    dsx3CCVCurrent, dsx3CCV15MinBucket, dsx3CCV24HrBucket, 
--    dsx3CESCurrent, dsx3CES15MinBucket, dsx3CES24HrBucket, 
--    dsx3CSESCurrent, dsx3CSES15MinBucket, dsx3CSES24HrBucket

cmDsx3E3AlarmStatsGroup OBJECT IDENTIFIER ::= { cmDsx3MIBGroups 11 }
-- OBJECT-GROUP
--  Status
--    mandatory
--  Descr
--    The collection of objects related to
--    performance statistics and error events
--    for e3 interfaces.
--  objects
--    dsx3E3BIP8CVCurrent, dsx3E3BIP8CV15MinBucket, 
--    dsx3E3BIP8CV24HrBucket, dsx3E3BIP8ESCurrent, 
--    dsx3E3BIP8ES15MinBucket, dsx3E3BIP8ES24HrBucket, 
--    dsx3E3BIP8SESCurrent, dsx3E3BIP8SES15MinBucket, 
--    dsx3E3BIP8SES24HrBucket

cmDsx3PlcpConfGroup OBJECT IDENTIFIER ::= { cmDsx3MIBGroups 12 }
-- OBJECT-GROUP
--  Status
--    mandatory
--  Descr
--    The collection of objects related to
--    PLCP Configuration on DS3 interfaces.
--  objects
--    dsx3PlcpNum, dsx3PlcpCellFraming, dsx3PlcpPayloadScramble, 
--    dsx3PlcpLoopCommand

cmDsx3PlcpStatsGroup OBJECT IDENTIFIER ::= { cmDsx3MIBGroups 13 }
-- OBJECT-GROUP
--  Status
--    mandatory
--  Descr
--    The collection of objects related to
--    PLCP statistics on DS3 interfaces.
--  objects
--    dsx3PlcpRcvBip8Count, dsx3PlcpRcvOOFCount, 
--    dsx3PlcpRcvRAICount, dsx3PlcpFECount, dsx3PlcpFESecCount, 
--    dsx3PlcpSEFESecCount, dsx3PlcpFEBECount, dsx3PlcpFEBESecCount, 
--    dsx3PlcpSEFEBESecCount, dsx3PlcpHECCount, dsx3PlcpHECSecCount, 
--    dsx3PlcpSEHECSecCount, dsx3PlcpCounterClrButton

cmDsx3PlcpAlarmConfGroup OBJECT IDENTIFIER ::= { cmDsx3MIBGroups 14 }
-- OBJECT-GROUP
--  Status
--    mandatory
--  Descr
--    The collection of objects used for
--    PLCP Alarm configuration on DS3 interfaces.
--  objects
--    dsx3PlcpRedSeverity, dsx3PlcpRAISeverity, dsx3PlcpLssSeverity, 
--    dsx3PlcpLssEnable, dsx3PlcpLssCodeConnected, 
--    dsx3PlcpLssCodeRxLinkDn, dsx3PlcpLssCodeRxLinkUp, 
--    dsx3PlcpStatisticalAlarmSeverity, 
--    dsx3PlcpBip8CV15MinThreshold, dsx3PlcpBip8CV24HrThreshold, 
--    dsx3PlcpBip8ES15MinThreshold, dsx3PlcpBip8ES24HrThreshold, 
--    dsx3PlcpBip8SES15MinThreshold, dsx3PlcpBip8SES24HrThreshold, 
--    dsx3PlcpSEFS15MinThreshold, dsx3PlcpSEFS24HrThreshold, 
--    dsx3PlcpUAS15MinThreshold, dsx3PlcpUAS24HrThreshold

cmDsx3PlcpAlarmGroup OBJECT IDENTIFIER ::= { cmDsx3MIBGroups 15 }
-- OBJECT-GROUP
--  Status
--    mandatory
--  Descr
--    The collection of objects used for
--    PLCP Alarm configuration on DS3 interfaces.
--  objects
--    dsx3PlcpLineAlarmState, dsx3PlcpLineStatisticalAlarmState, 
--    dsx3PlcpBip8CVCurrent, dsx3PlcpBip8CV15MinBucket, 
--    dsx3PlcpBip8CV24HrBucket, dsx3PlcpBip8ESCurrent, 
--    dsx3PlcpBip8ES15MinBucket, dsx3PlcpBip8ES24HrBucket, 
--    dsx3PlcpBip8SESCurrent, dsx3PlcpBip8SES15MinBucket, 
--    dsx3PlcpBip8SES24HrBucket, dsx3PlcpSEFSCurrent, 
--    dsx3PlcpSEFS15MinBucket, dsx3PlcpSEFS24HrBucket, 
--    dsx3PlcpUASCurrent, dsx3PlcpUAS15MinBucket, 
--    dsx3PlcpUAS24HrBucket, dsx3PlcpAlarmClrButton

cmDsx3Compliance OBJECT IDENTIFIER ::= { cmDsx3MIBCompliances 1 }
-- MODULE-COMPLIANCE
--  Status
--    mandatory
--  Descr
--    The compliance statement for objects related
--    to DS3 MIB.
--  Module
--    >>current<<
--   MandGroup
--    cmDsx3GeneralGroup
--   MandGroup
--    cmDsx3ConfGroup
--   MandGroup
--    cmDsx3BertConfigGroup
--   MandGroup
--    cmDsx3StatsGroup
--   MandGroup
--    cmDsx3E3AlarmConfGenGroup
--   MandGroup
--    cmDsx3AlarmStatsGenGroup
--   MandGroup
--    cmDsx3PlcpConfGroup
--   MandGroup
--    cmDsx3PlcpStatsGroup
--   MandGroup
--    cmDsx3PlcpAlarmConfGroup
--   MandGroup
--    cmDsx3PlcpAlarmGroup
--   OptGroup
--    cmDsx3E3ConfGroup
--   OptGroup
--    cmDsx3AlarmConfGroup
--   OptGroup
--    cmDsx3E3AlarmConfGroup
--   OptGroup
--    cmDsx3AlarmStatsGroup
--   OptGroup
--    cmDsx3E3AlarmStatsGroup


END
