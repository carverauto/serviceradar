-- MIB file created 28-Jan-2003 17:12:35, by
--   SMICng version 2.2.11-beta(PRO)(Solaris), January 20, 2001. Enterprise key cisco.com

FIBRE-CHANNEL-FE-MIB DEFINITIONS ::= BEGIN

-- From file: "FIBRE-CHANNEL-FE-MIB.my"
-- Compile options "4 7 F H N W 03 06 0B 0G 0N 0T"

IMPORTS
    mib-2
            FROM SNMPv2-SMI-v1
    TruthValue, TimeStamp
            FROM SNMPv2-TC-v1
    SnmpAdminString
            FROM SNMP-FRAMEWORK-MIB
    Counter, Gauge
            FROM RFC1155-SMI
    OBJECT-TYPE
            FROM RFC-1212;

fcFeMIB OBJECT IDENTIFIER ::= { mib-2 75 }
-- MODULE-IDENTITY
--  LastUpdated
--    200005180000Z
--  OrgName
--    IETF IPFC Working Group
--  ContactInfo
--    Kha Sin Teow
--     Brocade Communications Systems,
--     1901 Guadalupe Parkway,
--     San Jose, CA 95131
--     U.S.A
--     Tel: +1 408 487 8180
--     Fax: +1 408 487 8190
--     Email: khasin@Brocade.COM
--    
--    WG Mailing list:ipfc@standards.gadzoox.com
--    To Subscribe: ipfc-request@standards.gadzoox.com
--    In Body: subscribe
--  Descr
--    The MIB module for Fibre Channel Fabric Element.
--  RevDate
--    200005180000Z
--  RevDescr
--    Initial revision, published as RFC 2837.

fcFeMIBObjects  OBJECT IDENTIFIER ::= { fcFeMIB 1 }
fcFeConfig      OBJECT IDENTIFIER ::= { fcFeMIBObjects 1 }
fcFeStatus      OBJECT IDENTIFIER ::= { fcFeMIBObjects 2 }
fcFeError       OBJECT IDENTIFIER ::= { fcFeMIBObjects 3 }
fcFeAccounting  OBJECT IDENTIFIER ::= { fcFeMIBObjects 4 }
fcFeCapabilities OBJECT IDENTIFIER ::= { fcFeMIBObjects 5 }
fcFeMIBConformance OBJECT IDENTIFIER ::= { fcFeMIB 2 }
fcFeMIBCompliances OBJECT IDENTIFIER ::= { fcFeMIBConformance 1 }
fcFeMIBGroups   OBJECT IDENTIFIER ::= { fcFeMIBConformance 2 }

MilliSeconds ::= Gauge
-- TEXTUAL-CONVENTION
--  Status
--    mandatory
--  Descr
--    Represents time unit value in milliseconds.

MicroSeconds ::= Gauge
-- TEXTUAL-CONVENTION
--  Status
--    mandatory
--  Descr
--    Represents time unit value in microseconds.

FcNameId ::= OCTET STRING(SIZE(8))
-- TEXTUAL-CONVENTION
--  Status
--    mandatory
--  Descr
--    Represents the Worldwide Name associated with
--     a Fibre Channel (FC) entity.

FcAddressId ::= OCTET STRING(SIZE(3))
-- TEXTUAL-CONVENTION
--  Status
--    mandatory
--  Descr
--    Represents Fibre Channel Address ID, a 24-bit
--     value unique within the address space of a Fabric.

FcRxDataFieldSize ::= INTEGER(128..2112)
-- TEXTUAL-CONVENTION
--  Status
--    mandatory
--  Descr
--    Represents the receive data field size of an
--     NxPort or FxPort.

FcBbCredit ::= INTEGER(0..32767)
-- TEXTUAL-CONVENTION
--  Status
--    mandatory
--  Descr
--    Represents the buffer-to-buffer credit of an
--     NxPort or FxPort.

FcphVersion ::= INTEGER(0..255)
-- TEXTUAL-CONVENTION
--  Status
--    mandatory
--  Descr
--    Represents the version of FC-PH supported by an
--     NxPort or FxPort.

FcStackedConnMode ::= INTEGER {
        none(1),
        transparent(2),
        lockedDown(3)
        }
-- TEXTUAL-CONVENTION
--  Status
--    mandatory
--  Descr
--    Represents an enumerated value used to indicate
--     the Class 1 Stacked Connect Mode supported by
--     an NxPort or FxPort.

FcCosCap ::= OCTET STRING(SIZE(1..2))
        -- BITS are:
        --   classF(0)
        --   class1(1)
        --   class2(2)
        --   class3(3)
        --   class4(4)
        --   class5(5)
        --   class6(6)
-- TEXTUAL-CONVENTION
--  Status
--    mandatory
--  Descr
--    Represents the class of service capability of an
--     NxPort or FxPort.

FcFeModuleCapacity ::= Gauge
-- TEXTUAL-CONVENTION
--  Status
--    mandatory
--  Descr
--    Represents the maximum number of modules within
--     a Fabric Element.

FcFeFxPortCapacity ::= Gauge
-- TEXTUAL-CONVENTION
--  Status
--    mandatory
--  Descr
--    Represents the maximum number of FxPorts within
--     a module.

FcFeModuleIndex ::= Gauge
-- TEXTUAL-CONVENTION
--  Status
--    mandatory
--  Descr
--    Represents the module index within a conceptual table.

FcFeFxPortIndex ::= Gauge
-- TEXTUAL-CONVENTION
--  Status
--    mandatory
--  Descr
--    Represents the FxPort index within a conceptual table.

FcFeNxPortIndex ::= INTEGER(1..126)
-- TEXTUAL-CONVENTION
--  Status
--    mandatory
--  Descr
--    Represents the NxPort index within a conceptual table.

FcBbCreditModel ::= INTEGER {
        regular(1),
        alternate(2)
        }
-- TEXTUAL-CONVENTION
--  Status
--    mandatory
--  Descr
--    Represents the BB_Credit model of an FxPort.

fcFeFabricName OBJECT-TYPE
    SYNTAX FcNameId
--    Rsyntax OCTET STRING(SIZE(8))
    ACCESS read-write
    STATUS mandatory
    DESCRIPTION
        "The Name_Identifier of the Fabric to which this Fabric
         Element belongs."
    ::= { fcFeConfig 1 }

fcFeElementName OBJECT-TYPE
    SYNTAX FcNameId
--    Rsyntax OCTET STRING(SIZE(8))
    ACCESS read-write
    STATUS mandatory
    DESCRIPTION
        "The Name_Identifier of the Fabric Element."
    ::= { fcFeConfig 2 }

fcFeModuleCapacity OBJECT-TYPE
    SYNTAX FcFeModuleCapacity
--    Rsyntax Gauge
    ACCESS read-only
    STATUS mandatory
    DESCRIPTION
        "The maximum number of modules in the Fabric Element,
         regardless of their current state."
    ::= { fcFeConfig 3 }

fcFeModuleTable OBJECT-TYPE
    SYNTAX SEQUENCE OF FcFeModuleEntry
    ACCESS not-accessible
    STATUS mandatory
    DESCRIPTION
        "A table that contains, one entry for each module in the
         Fabric Element, information of the modules."
    ::= { fcFeConfig 4 }

fcFeModuleEntry OBJECT-TYPE
    SYNTAX FcFeModuleEntry
    ACCESS not-accessible
    STATUS mandatory
    DESCRIPTION
        "An entry containing the configuration parameters of a
         module."
    INDEX { fcFeModuleIndex }
    ::= { fcFeModuleTable 1 }

FcFeModuleEntry ::= SEQUENCE {
    fcFeModuleIndex FcFeModuleIndex,
    fcFeModuleDescr SnmpAdminString,
    fcFeModuleObjectID OBJECT IDENTIFIER,
    fcFeModuleOperStatus INTEGER,
    fcFeModuleLastChange TimeStamp,
    fcFeModuleFxPortCapacity FcFeFxPortCapacity,
    fcFeModuleName FcNameId
    }

fcFeModuleIndex OBJECT-TYPE
    SYNTAX FcFeModuleIndex
--    Rsyntax Gauge
    ACCESS not-accessible
    STATUS mandatory
    DESCRIPTION
        "This object identifies the module within the Fabric Element
         for which this entry contains information. This value is
         never greater than fcFeModuleCapacity."
    ::= { fcFeModuleEntry 1 }

fcFeModuleDescr OBJECT-TYPE
    SYNTAX SnmpAdminString
--    Rsyntax OCTET STRING(SIZE(0..255))
    ACCESS read-only
    STATUS mandatory
    DESCRIPTION
        "A textual description of the module. This value should
         include the full name and version identification of the
         module."
    ::= { fcFeModuleEntry 2 }

fcFeModuleObjectID OBJECT-TYPE
    SYNTAX OBJECT IDENTIFIER
    ACCESS read-only
    STATUS mandatory
    DESCRIPTION
        "The vendor's authoritative identification of the module.
         This value may be allocated within the SMI enterprises
         subtree (1.3.6.1.4.1) and provides a straight-forward and
         unambiguous means for determining what kind of module is
         being managed.
        
         For example, this object could take the value
         1.3.6.1.4.1.99649.3.9 if vendor 'Neufe Inc.' was assigned
         the subtree 1.3.6.1.4.1.99649, and had assigned the
         identifier 1.3.6.1.4.1.99649.3.9 to its 'FeFiFo-16
         PlugInCard.'"
    ::= { fcFeModuleEntry 3 }

fcFeModuleOperStatus OBJECT-TYPE
    SYNTAX INTEGER {
        online(1),
        offline(2),
        testing(3),
        faulty(4)
        }
    ACCESS read-only
    STATUS mandatory
    DESCRIPTION
        "This object indicates the operational status of the module:
         online(1)   the module is functioning properly;
         offline(2)  the module is not available;
         testing(3)  the module is under testing; and
         faulty(4)   the module is defective in some way."
    ::= { fcFeModuleEntry 4 }

fcFeModuleLastChange OBJECT-TYPE
    SYNTAX TimeStamp
--    Rsyntax TimeTicks
    ACCESS read-only
    STATUS mandatory
    DESCRIPTION
        "This object contains the value of sysUpTime when the module
         entered its current operational status. A value of zero
         indicates that the operational status of the module has not
         changed since the agent last restarted."
    ::= { fcFeModuleEntry 5 }

fcFeModuleFxPortCapacity OBJECT-TYPE
    SYNTAX FcFeFxPortCapacity
--    Rsyntax Gauge
    ACCESS read-only
    STATUS mandatory
    DESCRIPTION
        "The number of FxPort that can be contained within the
         module. Within each module, the ports are uniquely numbered
         in the range from 1 to fcFeModuleFxPortCapacity inclusive.
         However, the numbers are not required to be contiguous."
    ::= { fcFeModuleEntry 6 }

fcFeModuleName OBJECT-TYPE
    SYNTAX FcNameId
--    Rsyntax OCTET STRING(SIZE(8))
    ACCESS read-write
    STATUS mandatory
    DESCRIPTION
        "The Name_Identifier of the module."
    ::= { fcFeModuleEntry 7 }

fcFxPortTable OBJECT-TYPE
    SYNTAX SEQUENCE OF FcFxPortEntry
    ACCESS not-accessible
    STATUS mandatory
    DESCRIPTION
        "A table that contains, one entry for each FxPort in the
         Fabric Element, configuration and service parameters of the
         FxPorts."
    ::= { fcFeConfig 5 }

fcFxPortEntry OBJECT-TYPE
    SYNTAX FcFxPortEntry
    ACCESS not-accessible
    STATUS mandatory
    DESCRIPTION
        "An entry containing the configuration and service parameters
         of a FxPort."
    INDEX { fcFeModuleIndex, fcFxPortIndex }
    ::= { fcFxPortTable 1 }

FcFxPortEntry ::= SEQUENCE {
    fcFxPortIndex FcFeFxPortIndex,
    fcFxPortName FcNameId,
    fcFxPortFcphVersionHigh FcphVersion,
    fcFxPortFcphVersionLow FcphVersion,
    fcFxPortBbCredit FcBbCredit,
    fcFxPortRxBufSize FcRxDataFieldSize,
    fcFxPortRatov MilliSeconds,
    fcFxPortEdtov MilliSeconds,
    fcFxPortCosSupported FcCosCap,
    fcFxPortIntermixSupported TruthValue,
    fcFxPortStackedConnMode FcStackedConnMode,
    fcFxPortClass2SeqDeliv TruthValue,
    fcFxPortClass3SeqDeliv TruthValue,
    fcFxPortHoldTime MicroSeconds
    }

fcFxPortIndex OBJECT-TYPE
    SYNTAX FcFeFxPortIndex
--    Rsyntax Gauge
    ACCESS not-accessible
    STATUS mandatory
    DESCRIPTION
        "This object identifies the FxPort within the module.  This
         number ranges from 1 to the value of fcFeModulePortCapacity
         for the associated module. The value remains constant for
         the identified FxPort until the module is re-initialized."
    ::= { fcFxPortEntry 1 }

fcFxPortName OBJECT-TYPE
    SYNTAX FcNameId
--    Rsyntax OCTET STRING(SIZE(8))
    ACCESS read-only
    STATUS mandatory
    DESCRIPTION
        "The World_wide Name of this FxPort.  Each FxPort has a
         unique Port World_wide Name within the Fabric."
    ::= { fcFxPortEntry 2 }

fcFxPortFcphVersionHigh OBJECT-TYPE
    SYNTAX FcphVersion
--    Rsyntax INTEGER(0..255)
    ACCESS read-only
    STATUS mandatory
    DESCRIPTION
        "The highest or most recent version of FC-PH that the FxPort
         is configured to support."
    ::= { fcFxPortEntry 3 }

fcFxPortFcphVersionLow OBJECT-TYPE
    SYNTAX FcphVersion
--    Rsyntax INTEGER(0..255)
    ACCESS read-only
    STATUS mandatory
    DESCRIPTION
        "The lowest or earliest version of FC-PH that the FxPort is
         configured to support."
    ::= { fcFxPortEntry 4 }

fcFxPortBbCredit OBJECT-TYPE
    SYNTAX FcBbCredit
--    Rsyntax INTEGER(0..32767)
--  Units
--    buffers
    ACCESS read-only
    STATUS mandatory
    DESCRIPTION
        "The total number of receive buffers available for holding
         Class 1 connect-request, Class 2 or 3 frames from the
         attached NxPort.  It is for buffer-to-buffer flow control
         in the direction from the attached NxPort (if applicable)
         to FxPort."
    ::= { fcFxPortEntry 5 }

fcFxPortRxBufSize OBJECT-TYPE
    SYNTAX FcRxDataFieldSize
--    Rsyntax INTEGER(128..2112)
--  Units
--    bytes
    ACCESS read-only
    STATUS mandatory
    DESCRIPTION
        "The largest Data_Field Size (in octets) for an FT_1 frame
         that can be received by the FxPort."
    ::= { fcFxPortEntry 6 }

fcFxPortRatov OBJECT-TYPE
    SYNTAX MilliSeconds
--    Rsyntax Gauge
--  Units
--    milliseconds
    ACCESS read-only
    STATUS mandatory
    DESCRIPTION
        "The Resource_Allocation_Timeout Value configured for the
         FxPort.  This is used as the timeout value for determining
         when to reuse an NxPort resource such as a
         Recovery_Qualifier.  It represents E_D_TOV (see next
         object) plus twice the maximum time that a frame may be
         delayed within the Fabric and still be delivered."
    ::= { fcFxPortEntry 7 }

fcFxPortEdtov OBJECT-TYPE
    SYNTAX MilliSeconds
--    Rsyntax Gauge
--  Units
--    milliseconds
    ACCESS read-only
    STATUS mandatory
    DESCRIPTION
        "The E_D_TOV value configured for the FxPort. The
         Error_Detect_Timeout Value is used as the timeout value for
         detecting an error condition."
    ::= { fcFxPortEntry 8 }

fcFxPortCosSupported OBJECT-TYPE
    SYNTAX FcCosCap
--    Rsyntax OCTET STRING(SIZE(1..2))
--         BITS are:
--           classF(0)
--           class1(1)
--           class2(2)
--           class3(3)
--           class4(4)
--           class5(5)
--           class6(6)
    ACCESS read-only
    STATUS mandatory
    DESCRIPTION
        "A value indicating the set of Classes of Service supported
         by the FxPort."
    ::= { fcFxPortEntry 9 }

fcFxPortIntermixSupported OBJECT-TYPE
    SYNTAX TruthValue
--    Rsyntax INTEGER {
--        true(1),
--        false(2)
--        }
    ACCESS read-only
    STATUS mandatory
    DESCRIPTION
        "A flag indicating whether or not the FxPort supports an
         Intermixed Dedicated Connection."
    ::= { fcFxPortEntry 10 }

fcFxPortStackedConnMode OBJECT-TYPE
    SYNTAX FcStackedConnMode
--    Rsyntax INTEGER {
--        none(1),
--        transparent(2),
--        lockedDown(3)
--        }
    ACCESS read-only
    STATUS mandatory
    DESCRIPTION
        "A value indicating the mode of Stacked Connect supported by
         the FxPort."
    ::= { fcFxPortEntry 11 }

fcFxPortClass2SeqDeliv OBJECT-TYPE
    SYNTAX TruthValue
--    Rsyntax INTEGER {
--        true(1),
--        false(2)
--        }
    ACCESS read-only
    STATUS mandatory
    DESCRIPTION
        "A flag indicating whether or not Class 2 Sequential
         Delivery is supported by the FxPort."
    ::= { fcFxPortEntry 12 }

fcFxPortClass3SeqDeliv OBJECT-TYPE
    SYNTAX TruthValue
--    Rsyntax INTEGER {
--        true(1),
--        false(2)
--        }
    ACCESS read-only
    STATUS mandatory
    DESCRIPTION
        "A flag indicating whether or not Class 3 Sequential
         Delivery is supported by the FxPort."
    ::= { fcFxPortEntry 13 }

fcFxPortHoldTime OBJECT-TYPE
    SYNTAX MicroSeconds
--    Rsyntax Gauge
--  Units
--    microseconds
    ACCESS read-only
    STATUS mandatory
    DESCRIPTION
        "The maximum time (in microseconds) that the FxPort shall
         hold a frame before discarding the frame if it is unable to
         deliver the frame. The value 0 means that the FxPort does
         not support this parameter."
    ::= { fcFxPortEntry 14 }

fcFxPortStatusTable OBJECT-TYPE
    SYNTAX SEQUENCE OF FcFxPortStatusEntry
    ACCESS not-accessible
    STATUS mandatory
    DESCRIPTION
        "A table that contains, one entry for each FxPort in the
         Fabric Element, operational status and parameters of the
         FxPorts."
    ::= { fcFeStatus 1 }

fcFxPortStatusEntry OBJECT-TYPE
    SYNTAX FcFxPortStatusEntry
    ACCESS not-accessible
    STATUS mandatory
    DESCRIPTION
        "An entry containing operational status and parameters of a
         FxPort."
    INDEX { fcFeModuleIndex, fcFxPortIndex }
-- Augments fcFxPortEntry
    ::= { fcFxPortStatusTable 1 }

FcFxPortStatusEntry ::= SEQUENCE {
    fcFxPortID FcAddressId,
    fcFxPortBbCreditAvailable Gauge,
    fcFxPortOperMode INTEGER,
    fcFxPortAdminMode INTEGER
    }

fcFxPortID OBJECT-TYPE
    SYNTAX FcAddressId
--    Rsyntax OCTET STRING(SIZE(3))
    ACCESS read-only
    STATUS mandatory
    DESCRIPTION
        "The address identifier by which this FxPort is identified
         within the Fabric.  The FxPort may assign its address
         identifier to its attached NxPort(s) during Fabric Login."
    ::= { fcFxPortStatusEntry 1 }

fcFxPortBbCreditAvailable OBJECT-TYPE
    SYNTAX Gauge
--  Units
--    buffers
    ACCESS read-only
    STATUS mandatory
    DESCRIPTION
        "The number of buffers currently available for receiving
         frames from the attached port in the buffer-to-buffer flow
         control. The value should be less than or equal to
         fcFxPortBbCredit."
    ::= { fcFxPortStatusEntry 2 }

fcFxPortOperMode OBJECT-TYPE
    SYNTAX INTEGER {
        unknown(1),
        fPort(2),
        flPort(3)
        }
    ACCESS read-only
    STATUS mandatory
    DESCRIPTION
        "The current operational mode of the FxPort."
    ::= { fcFxPortStatusEntry 3 }

fcFxPortAdminMode OBJECT-TYPE
    SYNTAX INTEGER {
        fPort(2),
        flPort(3)
        }
    ACCESS read-write
    STATUS mandatory
    DESCRIPTION
        "The desired operational mode of the FxPort."
    ::= { fcFxPortStatusEntry 4 }

fcFxPortPhysTable OBJECT-TYPE
    SYNTAX SEQUENCE OF FcFxPortPhysEntry
    ACCESS not-accessible
    STATUS mandatory
    DESCRIPTION
        "A table that contains, one entry for each FxPort in the
         Fabric Element, physical level status and parameters of the
         FxPorts."
    ::= { fcFeStatus 2 }

fcFxPortPhysEntry OBJECT-TYPE
    SYNTAX FcFxPortPhysEntry
    ACCESS not-accessible
    STATUS mandatory
    DESCRIPTION
        "An entry containing physical level status and parameters of
         a FxPort."
    INDEX { fcFeModuleIndex, fcFxPortIndex }
-- Augments fcFxPortEntry
    ::= { fcFxPortPhysTable 1 }

FcFxPortPhysEntry ::= SEQUENCE {
    fcFxPortPhysAdminStatus INTEGER,
    fcFxPortPhysOperStatus INTEGER,
    fcFxPortPhysLastChange TimeStamp,
    fcFxPortPhysRttov MilliSeconds
    }

fcFxPortPhysAdminStatus OBJECT-TYPE
    SYNTAX INTEGER {
        online(1),
        offline(2),
        testing(3)
        }
    ACCESS read-write
    STATUS mandatory
    DESCRIPTION
        "The desired state of the FxPort.  A management station may
         place the FxPort in a desired state by setting this object
         accordingly.  The testing(3) state indicates that no
         operational frames can be passed.  When a Fabric Element
         initializes, all FxPorts start with fcFxPortPhysAdminStatus
         in the offline(2) state.  As the result of either explicit
         management action or per configuration information
         accessible by the Fabric Element, fcFxPortPhysAdminStatus
         is then changed to either the online(1) or testing(3)
         states, or remains in the offline state."
    ::= { fcFxPortPhysEntry 1 }

fcFxPortPhysOperStatus OBJECT-TYPE
    SYNTAX INTEGER {
        online(1),
        offline(2),
        testing(3),
        linkFailure(4)
        }
    ACCESS read-only
    STATUS mandatory
    DESCRIPTION
        "The current operational status of the FxPort.  The
         testing(3) indicates that no operational frames can be
         passed.  If fcFxPortPhysAdminStatus is offline(2) then
         fcFxPortPhysOperStatus should be offline(2). If
         fcFxPortPhysAdminStatus is changed to online(1) then
         fcFxPortPhysOperStatus should change to online(1) if the
         FxPort is ready to accept Fabric Login request from the
         attached NxPort; it should proceed and remain in the link-
         failure(4) state if and only if there is a fault that
         prevents it from going to the online(1) state."
    ::= { fcFxPortPhysEntry 2 }

fcFxPortPhysLastChange OBJECT-TYPE
    SYNTAX TimeStamp
--    Rsyntax TimeTicks
    ACCESS read-only
    STATUS mandatory
    DESCRIPTION
        "The value of sysUpTime at the time the FxPort entered its
         current operational status. A value of zero indicates that
         the FxPort's operational status has not changed since the
         agent last restarted."
    ::= { fcFxPortPhysEntry 3 }

fcFxPortPhysRttov OBJECT-TYPE
    SYNTAX MilliSeconds
--    Rsyntax Gauge
--  Units
--    milliseconds
    ACCESS read-write
    STATUS mandatory
    DESCRIPTION
        "The Receiver_Transmitter_Timeout value of the FxPort. This
         is used by the receiver logic to detect Loss of
         Synchronization."
    ::= { fcFxPortPhysEntry 4 }

fcFxLoginTable OBJECT-TYPE
    SYNTAX SEQUENCE OF FcFxLoginEntry
    ACCESS not-accessible
    STATUS mandatory
    DESCRIPTION
        "A table that contains, one entry for each NxPort attached
         to a particular FxPort in the Fabric Element, services
         parameters established from the most recent Fabric Login,
         explicit or implicit. Note that an FxPort may have one or
         more NxPort attached to it."
    ::= { fcFeStatus 3 }

fcFxLoginEntry OBJECT-TYPE
    SYNTAX FcFxLoginEntry
    ACCESS not-accessible
    STATUS mandatory
    DESCRIPTION
        "An entry containing service parameters established from a
         successful Fabric Login."
    INDEX { fcFeModuleIndex, fcFxPortIndex, fcFxPortNxLoginIndex }
    ::= { fcFxLoginTable 1 }

FcFxLoginEntry ::= SEQUENCE {
    fcFxPortNxLoginIndex FcFeNxPortIndex,
    fcFxPortFcphVersionAgreed FcphVersion,
    fcFxPortNxPortBbCredit FcBbCredit,
    fcFxPortNxPortRxDataFieldSize FcRxDataFieldSize,
    fcFxPortCosSuppAgreed FcCosCap,
    fcFxPortIntermixSuppAgreed TruthValue,
    fcFxPortStackedConnModeAgreed FcStackedConnMode,
    fcFxPortClass2SeqDelivAgreed TruthValue,
    fcFxPortClass3SeqDelivAgreed TruthValue,
    fcFxPortNxPortName FcNameId,
    fcFxPortConnectedNxPort FcAddressId,
    fcFxPortBbCreditModel FcBbCreditModel
    }

fcFxPortNxLoginIndex OBJECT-TYPE
    SYNTAX FcFeNxPortIndex
--    Rsyntax INTEGER(1..126)
    ACCESS not-accessible
    STATUS mandatory
    DESCRIPTION
        "The object identifies the associated NxPort in the
         attachment for which the entry contains information."
    ::= { fcFxLoginEntry 1 }

fcFxPortFcphVersionAgreed OBJECT-TYPE
    SYNTAX FcphVersion
--    Rsyntax INTEGER(0..255)
    ACCESS read-only
    STATUS mandatory
    DESCRIPTION
        "The version of FC-PH that the FxPort has agreed to support
         from the Fabric Login"
    ::= { fcFxLoginEntry 2 }

fcFxPortNxPortBbCredit OBJECT-TYPE
    SYNTAX FcBbCredit
--    Rsyntax INTEGER(0..32767)
--  Units
--    buffers
    ACCESS read-only
    STATUS mandatory
    DESCRIPTION
        "The total number of buffers available for holding Class 1
         connect-request, Class 2 or Class 3 frames to be
         transmitted to the attached NxPort.  It is for buffer-to-
         buffer flow control in the direction from FxPort to NxPort.
         The buffer-to-buffer flow control mechanism is indicated in
         the respective fcFxPortBbCreditModel."
    ::= { fcFxLoginEntry 3 }

fcFxPortNxPortRxDataFieldSize OBJECT-TYPE
    SYNTAX FcRxDataFieldSize
--    Rsyntax INTEGER(128..2112)
--  Units
--    bytes
    ACCESS read-only
    STATUS mandatory
    DESCRIPTION
        "The Receive Data Field Size of the attached NxPort. This
         object specifies the largest Data Field Size for an FT_1
         frame that can be received by the NxPort."
    ::= { fcFxLoginEntry 4 }

fcFxPortCosSuppAgreed OBJECT-TYPE
    SYNTAX FcCosCap
--    Rsyntax OCTET STRING(SIZE(1..2))
--         BITS are:
--           classF(0)
--           class1(1)
--           class2(2)
--           class3(3)
--           class4(4)
--           class5(5)
--           class6(6)
    ACCESS read-only
    STATUS mandatory
    DESCRIPTION
        "A variable indicating that the attached NxPort has
         requested the FxPort for the support of classes of services
         and the FxPort has granted the request."
    ::= { fcFxLoginEntry 5 }

fcFxPortIntermixSuppAgreed OBJECT-TYPE
    SYNTAX TruthValue
--    Rsyntax INTEGER {
--        true(1),
--        false(2)
--        }
    ACCESS read-only
    STATUS mandatory
    DESCRIPTION
        "A variable indicating that the attached NxPort has
         requested the FxPort for the support of Intermix and the
         FxPort has granted the request. This flag is only valid if
         Class 1 service is supported."
    ::= { fcFxLoginEntry 6 }

fcFxPortStackedConnModeAgreed OBJECT-TYPE
    SYNTAX FcStackedConnMode
--    Rsyntax INTEGER {
--        none(1),
--        transparent(2),
--        lockedDown(3)
--        }
    ACCESS read-only
    STATUS mandatory
    DESCRIPTION
        "A variable indicating whether the FxPort has agreed to
         support stacked connect from the Fabric Login. This is only
         meaningful if Class 1 service has been agreed."
    ::= { fcFxLoginEntry 7 }

fcFxPortClass2SeqDelivAgreed OBJECT-TYPE
    SYNTAX TruthValue
--    Rsyntax INTEGER {
--        true(1),
--        false(2)
--        }
    ACCESS read-only
    STATUS mandatory
    DESCRIPTION
        "A variable indicating whether the FxPort has agreed to
         support Class 2 sequential delivery from the Fabric Login.
         This is only meaningful if Class 2 service has been
         agreed."
    ::= { fcFxLoginEntry 8 }

fcFxPortClass3SeqDelivAgreed OBJECT-TYPE
    SYNTAX TruthValue
--    Rsyntax INTEGER {
--        true(1),
--        false(2)
--        }
    ACCESS read-only
    STATUS mandatory
    DESCRIPTION
        "A flag indicating whether the FxPort has agreed to support
         Class 3 sequential delivery from the Fabric Login. This is
         only meaningful if Class 3 service has been agreed."
    ::= { fcFxLoginEntry 9 }

fcFxPortNxPortName OBJECT-TYPE
    SYNTAX FcNameId
--    Rsyntax OCTET STRING(SIZE(8))
    ACCESS read-only
    STATUS mandatory
    DESCRIPTION
        "The port name of the attached NxPort."
    ::= { fcFxLoginEntry 10 }

fcFxPortConnectedNxPort OBJECT-TYPE
    SYNTAX FcAddressId
--    Rsyntax OCTET STRING(SIZE(3))
    ACCESS read-only
    STATUS mandatory
    DESCRIPTION
        "The address identifier of the destination NxPort with which
         this FxPort is currently engaged in a either a Class 1 or
         loop connection. If this FxPort is not engaged in a
         connection, then the value of this object is '000000'H."
    ::= { fcFxLoginEntry 11 }

fcFxPortBbCreditModel OBJECT-TYPE
    SYNTAX FcBbCreditModel
--    Rsyntax INTEGER {
--        regular(1),
--        alternate(2)
--        }
    ACCESS read-write
    STATUS mandatory
    DESCRIPTION
        "This object identifies the BB_Credit model used by the
         FxPort."
    ::= { fcFxLoginEntry 12 }

fcFxPortErrorTable OBJECT-TYPE
    SYNTAX SEQUENCE OF FcFxPortErrorEntry
    ACCESS not-accessible
    STATUS mandatory
    DESCRIPTION
        "A table that contains, one entry for each FxPort, counters
         that record the numbers of errors detected."
    ::= { fcFeError 1 }

fcFxPortErrorEntry OBJECT-TYPE
    SYNTAX FcFxPortErrorEntry
    ACCESS not-accessible
    STATUS mandatory
    DESCRIPTION
        "An entry containing error counters of a FxPort."
    INDEX { fcFeModuleIndex, fcFxPortIndex }
-- Augments fcFxPortEntry
    ::= { fcFxPortErrorTable 1 }

FcFxPortErrorEntry ::= SEQUENCE {
    fcFxPortLinkFailures Counter,
    fcFxPortSyncLosses Counter,
    fcFxPortSigLosses Counter,
    fcFxPortPrimSeqProtoErrors Counter,
    fcFxPortInvalidTxWords Counter,
    fcFxPortInvalidCrcs Counter,
    fcFxPortDelimiterErrors Counter,
    fcFxPortAddressIdErrors Counter,
    fcFxPortLinkResetIns Counter,
    fcFxPortLinkResetOuts Counter,
    fcFxPortOlsIns Counter,
    fcFxPortOlsOuts Counter
    }

fcFxPortLinkFailures OBJECT-TYPE
    SYNTAX Counter
    ACCESS read-only
    STATUS mandatory
    DESCRIPTION
        "The number of link failures detected by this FxPort."
    ::= { fcFxPortErrorEntry 1 }

fcFxPortSyncLosses OBJECT-TYPE
    SYNTAX Counter
    ACCESS read-only
    STATUS mandatory
    DESCRIPTION
        "The number of loss of synchronization detected by the
         FxPort."
    ::= { fcFxPortErrorEntry 2 }

fcFxPortSigLosses OBJECT-TYPE
    SYNTAX Counter
    ACCESS read-only
    STATUS mandatory
    DESCRIPTION
        "The number of loss of signal detected by the FxPort."
    ::= { fcFxPortErrorEntry 3 }

fcFxPortPrimSeqProtoErrors OBJECT-TYPE
    SYNTAX Counter
    ACCESS read-only
    STATUS mandatory
    DESCRIPTION
        "The number of primitive sequence protocol errors detected
         by the FxPort."
    ::= { fcFxPortErrorEntry 4 }

fcFxPortInvalidTxWords OBJECT-TYPE
    SYNTAX Counter
    ACCESS read-only
    STATUS mandatory
    DESCRIPTION
        "The number of invalid transmission word detected by the
         FxPort."
    ::= { fcFxPortErrorEntry 5 }

fcFxPortInvalidCrcs OBJECT-TYPE
    SYNTAX Counter
    ACCESS read-only
    STATUS mandatory
    DESCRIPTION
        "The number of invalid CRC detected by this FxPort."
    ::= { fcFxPortErrorEntry 6 }

fcFxPortDelimiterErrors OBJECT-TYPE
    SYNTAX Counter
    ACCESS read-only
    STATUS mandatory
    DESCRIPTION
        "The number of Delimiter Errors detected by this FxPort."
    ::= { fcFxPortErrorEntry 7 }

fcFxPortAddressIdErrors OBJECT-TYPE
    SYNTAX Counter
    ACCESS read-only
    STATUS mandatory
    DESCRIPTION
        "The number of address identifier errors detected by this
         FxPort."
    ::= { fcFxPortErrorEntry 8 }

fcFxPortLinkResetIns OBJECT-TYPE
    SYNTAX Counter
    ACCESS read-only
    STATUS mandatory
    DESCRIPTION
        "The number of Link Reset Protocol received by this FxPort
         from the attached NxPort."
    ::= { fcFxPortErrorEntry 9 }

fcFxPortLinkResetOuts OBJECT-TYPE
    SYNTAX Counter
    ACCESS read-only
    STATUS mandatory
    DESCRIPTION
        "The number of Link Reset Protocol issued by this FxPort to
         the attached NxPort."
    ::= { fcFxPortErrorEntry 10 }

fcFxPortOlsIns OBJECT-TYPE
    SYNTAX Counter
    ACCESS read-only
    STATUS mandatory
    DESCRIPTION
        "The number of Offline Sequence received by this FxPort."
    ::= { fcFxPortErrorEntry 11 }

fcFxPortOlsOuts OBJECT-TYPE
    SYNTAX Counter
    ACCESS read-only
    STATUS mandatory
    DESCRIPTION
        "The number of Offline Sequence issued by this FxPort."
    ::= { fcFxPortErrorEntry 12 }

fcFxPortC1AccountingTable OBJECT-TYPE
    SYNTAX SEQUENCE OF FcFxPortC1AccountingEntry
    ACCESS not-accessible
    STATUS mandatory
    DESCRIPTION
        "A table that contains, one entry for each FxPort in the
         Fabric Element, Class 1 accounting information recorded
         since the management agent has re-initialized."
    ::= { fcFeAccounting 1 }

fcFxPortC1AccountingEntry OBJECT-TYPE
    SYNTAX FcFxPortC1AccountingEntry
    ACCESS not-accessible
    STATUS mandatory
    DESCRIPTION
        "An entry containing Class 1 accounting information for each
         FxPort."
    INDEX { fcFeModuleIndex, fcFxPortIndex }
-- Augments fcFxPortEntry
    ::= { fcFxPortC1AccountingTable 1 }

FcFxPortC1AccountingEntry ::= SEQUENCE {
    fcFxPortC1InFrames Counter,
    fcFxPortC1OutFrames Counter,
    fcFxPortC1InOctets Counter,
    fcFxPortC1OutOctets Counter,
    fcFxPortC1Discards Counter,
    fcFxPortC1FbsyFrames Counter,
    fcFxPortC1FrjtFrames Counter,
    fcFxPortC1InConnections Counter,
    fcFxPortC1OutConnections Counter,
    fcFxPortC1ConnTime MilliSeconds
    }

fcFxPortC1InFrames OBJECT-TYPE
    SYNTAX Counter
    ACCESS read-only
    STATUS mandatory
    DESCRIPTION
        "The number of Class 1 frames (other than Class 1 connect-
         request) received by this FxPort from its attached NxPort."
    ::= { fcFxPortC1AccountingEntry 1 }

fcFxPortC1OutFrames OBJECT-TYPE
    SYNTAX Counter
    ACCESS read-only
    STATUS mandatory
    DESCRIPTION
        "The number of Class 1 frames (other than Class 1 connect-
         request) delivered through this FxPort to its attached
         NxPort."
    ::= { fcFxPortC1AccountingEntry 2 }

fcFxPortC1InOctets OBJECT-TYPE
    SYNTAX Counter
    ACCESS read-only
    STATUS mandatory
    DESCRIPTION
        "The number of Class 1 frame octets, including the frame
         delimiters,  received by this FxPort from its attached
         NxPort."
    ::= { fcFxPortC1AccountingEntry 3 }

fcFxPortC1OutOctets OBJECT-TYPE
    SYNTAX Counter
    ACCESS read-only
    STATUS mandatory
    DESCRIPTION
        "The number of Class 1 frame octets, including the frame
         delimiters, delivered through this FxPort its attached
         NxPort."
    ::= { fcFxPortC1AccountingEntry 4 }

fcFxPortC1Discards OBJECT-TYPE
    SYNTAX Counter
    ACCESS read-only
    STATUS mandatory
    DESCRIPTION
        "The number of Class 1 frames discarded by this FxPort."
    ::= { fcFxPortC1AccountingEntry 5 }

fcFxPortC1FbsyFrames OBJECT-TYPE
    SYNTAX Counter
    ACCESS read-only
    STATUS mandatory
    DESCRIPTION
        "The number of F_BSY frames generated by this FxPort against
         Class 1 connect-request."
    ::= { fcFxPortC1AccountingEntry 6 }

fcFxPortC1FrjtFrames OBJECT-TYPE
    SYNTAX Counter
    ACCESS read-only
    STATUS mandatory
    DESCRIPTION
        "The number of F_RJT frames generated by this FxPort against
         Class 1 connect-request."
    ::= { fcFxPortC1AccountingEntry 7 }

fcFxPortC1InConnections OBJECT-TYPE
    SYNTAX Counter
    ACCESS read-only
    STATUS mandatory
    DESCRIPTION
        "The number of Class 1 connections successfully established
         in which the attached NxPort is the source of the connect-
         request."
    ::= { fcFxPortC1AccountingEntry 8 }

fcFxPortC1OutConnections OBJECT-TYPE
    SYNTAX Counter
    ACCESS read-only
    STATUS mandatory
    DESCRIPTION
        "The number of Class 1 connections successfully established
         in which the attached NxPort is the destination of the
         connect-request."
    ::= { fcFxPortC1AccountingEntry 9 }

fcFxPortC1ConnTime OBJECT-TYPE
    SYNTAX MilliSeconds
--    Rsyntax Gauge
--  Units
--    milliseconds
    ACCESS read-only
    STATUS mandatory
    DESCRIPTION
        "The cumulative time that this FxPort has been engaged in
         Class 1 connection.  The amount of time is counted from
         after a connect-request has been accepted until the
         connection is disengaged, either by an EOFdt or Link
         Reset."
    ::= { fcFxPortC1AccountingEntry 10 }

fcFxPortC2AccountingTable OBJECT-TYPE
    SYNTAX SEQUENCE OF FcFxPortC2AccountingEntry
    ACCESS not-accessible
    STATUS mandatory
    DESCRIPTION
        "A table that contains, one entry for each FxPort in the
         Fabric Element, Class 2 accounting information recorded
         since the management agent has re-initialized."
    ::= { fcFeAccounting 2 }

fcFxPortC2AccountingEntry OBJECT-TYPE
    SYNTAX FcFxPortC2AccountingEntry
    ACCESS not-accessible
    STATUS mandatory
    DESCRIPTION
        "An entry containing Class 2 accounting information for each
         FxPort."
    INDEX { fcFeModuleIndex, fcFxPortIndex }
-- Augments fcFxPortEntry
    ::= { fcFxPortC2AccountingTable 1 }

FcFxPortC2AccountingEntry ::= SEQUENCE {
    fcFxPortC2InFrames Counter,
    fcFxPortC2OutFrames Counter,
    fcFxPortC2InOctets Counter,
    fcFxPortC2OutOctets Counter,
    fcFxPortC2Discards Counter,
    fcFxPortC2FbsyFrames Counter,
    fcFxPortC2FrjtFrames Counter
    }

fcFxPortC2InFrames OBJECT-TYPE
    SYNTAX Counter
    ACCESS read-only
    STATUS mandatory
    DESCRIPTION
        "The number of Class 2 frames received by this FxPort from
         its attached NxPort."
    ::= { fcFxPortC2AccountingEntry 1 }

fcFxPortC2OutFrames OBJECT-TYPE
    SYNTAX Counter
    ACCESS read-only
    STATUS mandatory
    DESCRIPTION
        "The number of Class 2 frames delivered through this FxPort
         to its attached NxPort."
    ::= { fcFxPortC2AccountingEntry 2 }

fcFxPortC2InOctets OBJECT-TYPE
    SYNTAX Counter
    ACCESS read-only
    STATUS mandatory
    DESCRIPTION
        "The number of Class 2 frame octets, including the frame
         delimiters, received by this FxPort from its attached
         NxPort."
    ::= { fcFxPortC2AccountingEntry 3 }

fcFxPortC2OutOctets OBJECT-TYPE
    SYNTAX Counter
    ACCESS read-only
    STATUS mandatory
    DESCRIPTION
        "The number of Class 2 frame octets, including the frame
         delimiters, delivered through this FxPort to its attached
         NxPort."
    ::= { fcFxPortC2AccountingEntry 4 }

fcFxPortC2Discards OBJECT-TYPE
    SYNTAX Counter
    ACCESS read-only
    STATUS mandatory
    DESCRIPTION
        "The number of Class 2 frames discarded by this FxPort."
    ::= { fcFxPortC2AccountingEntry 5 }

fcFxPortC2FbsyFrames OBJECT-TYPE
    SYNTAX Counter
    ACCESS read-only
    STATUS mandatory
    DESCRIPTION
        "The number of F_BSY frames generated by this FxPort against
         Class 2 frames."
    ::= { fcFxPortC2AccountingEntry 6 }

fcFxPortC2FrjtFrames OBJECT-TYPE
    SYNTAX Counter
    ACCESS read-only
    STATUS mandatory
    DESCRIPTION
        "The number of F_RJT frames generated by this FxPort against
         Class 2 frames."
    ::= { fcFxPortC2AccountingEntry 7 }

fcFxPortC3AccountingTable OBJECT-TYPE
    SYNTAX SEQUENCE OF FcFxPortC3AccountingEntry
    ACCESS not-accessible
    STATUS mandatory
    DESCRIPTION
        "A table that contains, one entry for each FxPort in the
         Fabric Element, Class 3 accounting information recorded
         since the management agent has re-initialized."
    ::= { fcFeAccounting 3 }

fcFxPortC3AccountingEntry OBJECT-TYPE
    SYNTAX FcFxPortC3AccountingEntry
    ACCESS not-accessible
    STATUS mandatory
    DESCRIPTION
        "An entry containing Class 3 accounting information for each
         FxPort."
    INDEX { fcFeModuleIndex, fcFxPortIndex }
-- Augments fcFxPortEntry
    ::= { fcFxPortC3AccountingTable 1 }

FcFxPortC3AccountingEntry ::= SEQUENCE {
    fcFxPortC3InFrames Counter,
    fcFxPortC3OutFrames Counter,
    fcFxPortC3InOctets Counter,
    fcFxPortC3OutOctets Counter,
    fcFxPortC3Discards Counter
    }

fcFxPortC3InFrames OBJECT-TYPE
    SYNTAX Counter
    ACCESS read-only
    STATUS mandatory
    DESCRIPTION
        "The number of Class 3 frames received by this FxPort from
         its attached NxPort."
    ::= { fcFxPortC3AccountingEntry 1 }

fcFxPortC3OutFrames OBJECT-TYPE
    SYNTAX Counter
    ACCESS read-only
    STATUS mandatory
    DESCRIPTION
        "The number of Class 3 frames delivered through this FxPort
         to its attached NxPort."
    ::= { fcFxPortC3AccountingEntry 2 }

fcFxPortC3InOctets OBJECT-TYPE
    SYNTAX Counter
    ACCESS read-only
    STATUS mandatory
    DESCRIPTION
        "The number of Class 3 frame octets, including the frame
         delimiters, received by this FxPort from its attached
         NxPort."
    ::= { fcFxPortC3AccountingEntry 3 }

fcFxPortC3OutOctets OBJECT-TYPE
    SYNTAX Counter
    ACCESS read-only
    STATUS mandatory
    DESCRIPTION
        "The number of Class 3 frame octets, including the frame
         delimiters, delivered through this FxPort to its attached
         NxPort."
    ::= { fcFxPortC3AccountingEntry 4 }

fcFxPortC3Discards OBJECT-TYPE
    SYNTAX Counter
    ACCESS read-only
    STATUS mandatory
    DESCRIPTION
        "The number of Class 3 frames discarded by this FxPort."
    ::= { fcFxPortC3AccountingEntry 5 }

fcFxPortCapTable OBJECT-TYPE
    SYNTAX SEQUENCE OF FcFxPortCapEntry
    ACCESS not-accessible
    STATUS mandatory
    DESCRIPTION
        "A table that contains, one entry for each FxPort, the
         capabilities of the port within the Fabric Element."
    ::= { fcFeCapabilities 1 }

fcFxPortCapEntry OBJECT-TYPE
    SYNTAX FcFxPortCapEntry
    ACCESS not-accessible
    STATUS mandatory
    DESCRIPTION
        "An entry containing the Cap of a FxPort."
    INDEX { fcFeModuleIndex, fcFxPortIndex }
-- Augments fcFxPortEntry
    ::= { fcFxPortCapTable 1 }

FcFxPortCapEntry ::= SEQUENCE {
    fcFxPortCapFcphVersionHigh FcphVersion,
    fcFxPortCapFcphVersionLow FcphVersion,
    fcFxPortCapBbCreditMax FcBbCredit,
    fcFxPortCapBbCreditMin FcBbCredit,
    fcFxPortCapRxDataFieldSizeMax FcRxDataFieldSize,
    fcFxPortCapRxDataFieldSizeMin FcRxDataFieldSize,
    fcFxPortCapCos FcCosCap,
    fcFxPortCapIntermix TruthValue,
    fcFxPortCapStackedConnMode FcStackedConnMode,
    fcFxPortCapClass2SeqDeliv TruthValue,
    fcFxPortCapClass3SeqDeliv TruthValue,
    fcFxPortCapHoldTimeMax MicroSeconds,
    fcFxPortCapHoldTimeMin MicroSeconds
    }

fcFxPortCapFcphVersionHigh OBJECT-TYPE
    SYNTAX FcphVersion
--    Rsyntax INTEGER(0..255)
    ACCESS read-only
    STATUS mandatory
    DESCRIPTION
        "The highest or most recent version of FC-PH that the FxPort
         is capable of supporting."
    ::= { fcFxPortCapEntry 1 }

fcFxPortCapFcphVersionLow OBJECT-TYPE
    SYNTAX FcphVersion
--    Rsyntax INTEGER(0..255)
    ACCESS read-only
    STATUS mandatory
    DESCRIPTION
        "The lowest or earliest version of FC-PH that the FxPort is
         capable of supporting."
    ::= { fcFxPortCapEntry 2 }

fcFxPortCapBbCreditMax OBJECT-TYPE
    SYNTAX FcBbCredit
--    Rsyntax INTEGER(0..32767)
--  Units
--    buffers
    ACCESS read-only
    STATUS mandatory
    DESCRIPTION
        "The maximum number of receive buffers available for holding
         Class 1 connect-request, Class 2 or Class 3 frames from the
         attached NxPort."
    ::= { fcFxPortCapEntry 3 }

fcFxPortCapBbCreditMin OBJECT-TYPE
    SYNTAX FcBbCredit
--    Rsyntax INTEGER(0..32767)
--  Units
--    buffers
    ACCESS read-only
    STATUS mandatory
    DESCRIPTION
        "The minimum number of receive buffers available for holding
         Class 1 connect-request, Class 2 or Class 3 frames from the
         attached NxPort."
    ::= { fcFxPortCapEntry 4 }

fcFxPortCapRxDataFieldSizeMax OBJECT-TYPE
    SYNTAX FcRxDataFieldSize
--    Rsyntax INTEGER(128..2112)
--  Units
--    bytes
    ACCESS read-only
    STATUS mandatory
    DESCRIPTION
        "The maximum size in bytes of the Data Field in a frame that
         the FxPort is capable of receiving from its attached
         NxPort."
    ::= { fcFxPortCapEntry 5 }

fcFxPortCapRxDataFieldSizeMin OBJECT-TYPE
    SYNTAX FcRxDataFieldSize
--    Rsyntax INTEGER(128..2112)
--  Units
--    bytes
    ACCESS read-only
    STATUS mandatory
    DESCRIPTION
        "The minimum size in bytes of the Data Field in a frame that
         the FxPort is capable of receiving from its attached
         NxPort."
    ::= { fcFxPortCapEntry 6 }

fcFxPortCapCos OBJECT-TYPE
    SYNTAX FcCosCap
--    Rsyntax OCTET STRING(SIZE(1..2))
--         BITS are:
--           classF(0)
--           class1(1)
--           class2(2)
--           class3(3)
--           class4(4)
--           class5(5)
--           class6(6)
    ACCESS read-only
    STATUS mandatory
    DESCRIPTION
        "A value indicating the set of Classes of Service that the
         FxPort is capable of supporting."
    ::= { fcFxPortCapEntry 7 }

fcFxPortCapIntermix OBJECT-TYPE
    SYNTAX TruthValue
--    Rsyntax INTEGER {
--        true(1),
--        false(2)
--        }
    ACCESS read-only
    STATUS mandatory
    DESCRIPTION
        "A flag indicating whether or not the FxPort is capable of
         supporting the intermixing of Class 2 and Class 3 frames
         during a Class 1 connection. This flag is only valid if the
         port is capable of supporting Class 1 service."
    ::= { fcFxPortCapEntry 8 }

fcFxPortCapStackedConnMode OBJECT-TYPE
    SYNTAX FcStackedConnMode
--    Rsyntax INTEGER {
--        none(1),
--        transparent(2),
--        lockedDown(3)
--        }
    ACCESS read-only
    STATUS mandatory
    DESCRIPTION
        "A value indicating the mode of Stacked Connect request that
         the FxPort is capable of supporting."
    ::= { fcFxPortCapEntry 9 }

fcFxPortCapClass2SeqDeliv OBJECT-TYPE
    SYNTAX TruthValue
--    Rsyntax INTEGER {
--        true(1),
--        false(2)
--        }
    ACCESS read-only
    STATUS mandatory
    DESCRIPTION
        "A flag indicating whether or not the FxPort is capable of
         supporting Class 2 Sequential Delivery."
    ::= { fcFxPortCapEntry 10 }

fcFxPortCapClass3SeqDeliv OBJECT-TYPE
    SYNTAX TruthValue
--    Rsyntax INTEGER {
--        true(1),
--        false(2)
--        }
    ACCESS read-only
    STATUS mandatory
    DESCRIPTION
        "A flag indicating whether or not the FxPort is capable of
         supporting Class 3 Sequential Delivery."
    ::= { fcFxPortCapEntry 11 }

fcFxPortCapHoldTimeMax OBJECT-TYPE
    SYNTAX MicroSeconds
--    Rsyntax Gauge
--  Units
--    microseconds
    ACCESS read-only
    STATUS mandatory
    DESCRIPTION
        "The maximum holding time (in microseconds) that the FxPort
         is capable of supporting."
    ::= { fcFxPortCapEntry 12 }

fcFxPortCapHoldTimeMin OBJECT-TYPE
    SYNTAX MicroSeconds
--    Rsyntax Gauge
--  Units
--    microseconds
    ACCESS read-only
    STATUS mandatory
    DESCRIPTION
        "The minimum holding time (in microseconds) that the FxPort
         is capable of supporting."
    ::= { fcFxPortCapEntry 13 }

fcFeConfigGroup OBJECT IDENTIFIER ::= { fcFeMIBGroups 1 }
-- OBJECT-GROUP
--  Status
--    mandatory
--  Descr
--    A collection of objects providing the configuration and service
--     parameters of the Fabric Element, the modules, and FxPorts.
--  objects
--    fcFeFabricName, fcFeElementName, fcFeModuleCapacity, 
--    fcFeModuleDescr, fcFeModuleObjectID, fcFeModuleOperStatus, 
--    fcFeModuleLastChange, fcFeModuleFxPortCapacity, 
--    fcFeModuleName, fcFxPortName, fcFxPortFcphVersionHigh, 
--    fcFxPortFcphVersionLow, fcFxPortBbCredit, fcFxPortRxBufSize, 
--    fcFxPortRatov, fcFxPortEdtov, fcFxPortCosSupported, 
--    fcFxPortIntermixSupported, fcFxPortStackedConnMode, 
--    fcFxPortClass2SeqDeliv, fcFxPortClass3SeqDeliv, 
--    fcFxPortHoldTime

fcFeStatusGroup OBJECT IDENTIFIER ::= { fcFeMIBGroups 2 }
-- OBJECT-GROUP
--  Status
--    mandatory
--  Descr
--    A collection of objects providing the operational status and
--     established service parameters for the Fabric Element and the
--     attached NxPorts.
--  objects
--    fcFxPortID, fcFxPortBbCreditAvailable, fcFxPortOperMode, 
--    fcFxPortAdminMode, fcFxPortPhysAdminStatus, 
--    fcFxPortPhysOperStatus, fcFxPortPhysLastChange, 
--    fcFxPortPhysRttov, fcFxPortFcphVersionAgreed, 
--    fcFxPortNxPortBbCredit, fcFxPortNxPortRxDataFieldSize, 
--    fcFxPortCosSuppAgreed, fcFxPortIntermixSuppAgreed, 
--    fcFxPortStackedConnModeAgreed, fcFxPortClass2SeqDelivAgreed, 
--    fcFxPortClass3SeqDelivAgreed, fcFxPortNxPortName, 
--    fcFxPortConnectedNxPort, fcFxPortBbCreditModel

fcFeErrorGroup OBJECT IDENTIFIER ::= { fcFeMIBGroups 3 }
-- OBJECT-GROUP
--  Status
--    mandatory
--  Descr
--    A collection of objects providing various error
--     statistics detected by the FxPorts.
--  objects
--    fcFxPortLinkFailures, fcFxPortSyncLosses, fcFxPortSigLosses, 
--    fcFxPortPrimSeqProtoErrors, fcFxPortInvalidTxWords, 
--    fcFxPortInvalidCrcs, fcFxPortDelimiterErrors, 
--    fcFxPortAddressIdErrors, fcFxPortLinkResetIns, 
--    fcFxPortLinkResetOuts, fcFxPortOlsIns, fcFxPortOlsOuts

fcFeClass1AccountingGroup OBJECT IDENTIFIER ::= { fcFeMIBGroups 4 }
-- OBJECT-GROUP
--  Status
--    mandatory
--  Descr
--    A collection of objects providing various class 1
--    performance statistics detected by the FxPorts.
--  objects
--    fcFxPortC1InFrames, fcFxPortC1OutFrames, fcFxPortC1InOctets, 
--    fcFxPortC1OutOctets, fcFxPortC1Discards, fcFxPortC1FbsyFrames, 
--    fcFxPortC1FrjtFrames, fcFxPortC1InConnections, 
--    fcFxPortC1OutConnections, fcFxPortC1ConnTime

fcFeClass2AccountingGroup OBJECT IDENTIFIER ::= { fcFeMIBGroups 5 }
-- OBJECT-GROUP
--  Status
--    mandatory
--  Descr
--    A collection of objects providing various class 2
--    performance statistics detected by the FxPorts.
--  objects
--    fcFxPortC2InFrames, fcFxPortC2OutFrames, fcFxPortC2InOctets, 
--    fcFxPortC2OutOctets, fcFxPortC2Discards, fcFxPortC2FbsyFrames, 
--    fcFxPortC2FrjtFrames

fcFeClass3AccountingGroup OBJECT IDENTIFIER ::= { fcFeMIBGroups 6 }
-- OBJECT-GROUP
--  Status
--    mandatory
--  Descr
--    A collection of objects providing various class 3
--     performance statistics detected by the FxPorts.
--  objects
--    fcFxPortC3InFrames, fcFxPortC3OutFrames, fcFxPortC3InOctets, 
--    fcFxPortC3OutOctets, fcFxPortC3Discards

fcFeCapabilitiesGroup OBJECT IDENTIFIER ::= { fcFeMIBGroups 7 }
-- OBJECT-GROUP
--  Status
--    mandatory
--  Descr
--    A collection of objects providing the inherent
--     capability of each FxPort within the Fabric Element.
--  objects
--    fcFxPortCapFcphVersionHigh, fcFxPortCapFcphVersionLow, 
--    fcFxPortCapBbCreditMax, fcFxPortCapBbCreditMin, 
--    fcFxPortCapRxDataFieldSizeMax, fcFxPortCapRxDataFieldSizeMin, 
--    fcFxPortCapCos, fcFxPortCapIntermix, 
--    fcFxPortCapStackedConnMode, fcFxPortCapClass2SeqDeliv, 
--    fcFxPortCapClass3SeqDeliv, fcFxPortCapHoldTimeMax, 
--    fcFxPortCapHoldTimeMin

fcFeMIBMinimumCompliance OBJECT IDENTIFIER ::= { fcFeMIBCompliances 1 }
-- MODULE-COMPLIANCE
--  Status
--    mandatory
--  Descr
--    The minimum compliance statement for SNMP entities
--     which implement the FIBRE-CHANNEL-FE-MIB.
--  Module
--    >>current<<
--   MandGroup
--    fcFeConfigGroup
--   MandGroup
--    fcFeStatusGroup
--   MandGroup
--    fcFeErrorGroup
--   ObjVar
--    fcFeFabricName
--   ObjVar
--    fcFeElementName
--   ObjVar
--    fcFeModuleName
--   ObjVar
--    fcFxPortAdminMode
--   ObjVar
--    fcFxPortPhysAdminStatus
--   ObjVar
--    fcFxPortPhysRttov
--   ObjVar
--    fcFxPortBbCreditModel

fcFeMIBFullCompliance OBJECT IDENTIFIER ::= { fcFeMIBCompliances 2 }
-- MODULE-COMPLIANCE
--  Status
--    mandatory
--  Descr
--    The full compliance statement for SNMP entities
--     which implement the FIBRE-CHANNEL-FE-MIB.
--  Module
--    >>current<<
--   MandGroup
--    fcFeConfigGroup
--   MandGroup
--    fcFeStatusGroup
--   MandGroup
--    fcFeErrorGroup
--   MandGroup
--    fcFeCapabilitiesGroup
--   OptGroup
--    fcFeClass1AccountingGroup
--   OptGroup
--    fcFeClass2AccountingGroup
--   OptGroup
--    fcFeClass3AccountingGroup
--   ObjVar
--    fcFeFabricName
--   ObjVar
--    fcFeElementName
--   ObjVar
--    fcFeModuleName
--   ObjVar
--    fcFxPortAdminMode
--   ObjVar
--    fcFxPortPhysAdminStatus
--   ObjVar
--    fcFxPortPhysRttov
--   ObjVar
--    fcFxPortBbCreditModel


END
