-- MIB file created 07-Jul-2009 10:14:33, by
--   SMICng version 2.2.11-beta(PRO)(Solaris), January 20, 2001. Enterprise key cisco.com

CISCO-IETF-VPLS-LDP-MIB DEFINITIONS ::= BEGIN

-- From file: "CISCO-IETF-VPLS-LDP-MIB.my"
-- Compile options "4 7 F H N O W 03 06 0B 0G 0N 0T"

IMPORTS
    TruthValue
            FROM SNMPv2-TC-v1
    VPNId
            FROM VPN-TC-STD-MIB
    cvplsConfigIndex, cvplsPwBindIndex
            FROM CISCO-IETF-VPLS-GENERIC-MIB
    ciscoExperiment
            FROM CISCO-SMI
    Gauge
            FROM RFC1155-SMI
    OBJECT-TYPE
            FROM RFC-1212;

cvplsLdpMIB OBJECT IDENTIFIER ::= { ciscoExperiment 141 }
-- MODULE-IDENTITY
--  LastUpdated
--    200711221200Z
--  OrgName
--    Cisco Systems, Inc.
--  ContactInfo
--    Cisco Systems
--    Customer Service 
--    
--    Postal:  
--    170 W Tasman Drive 
--    San Jose, CA  95134 
--    USA 
--    
--    Tel: +1 800 553-NETS 
--    
--    E-mail: cs-l2vpn@cisco.com
--  Descr
--    This MIB module contains managed object definitions for
--    LDP signalled Virtual Private LAN Services as in
--    [L2VPN-VPLS-LDP]
--    
--    This MIB module enables the use of any underlying Pseudo Wire
--    network.
--    
--    This MIB is based on the following IETF document.
--    
--    http://www1.tools.ietf.org/html/draft-nadeau-l2vpn-vpls-mib-03
--  RevDate
--    200711221200Z
--  RevDescr
--    Initial version of this MIB.

cvplsLdpObjects OBJECT IDENTIFIER ::= { cvplsLdpMIB 1 }
cvplsLdpConformance OBJECT IDENTIFIER ::= { cvplsLdpMIB 2 }
cvplsLdpCompliances OBJECT IDENTIFIER ::= { cvplsLdpConformance 1 }
cvplsLdpGroups  OBJECT IDENTIFIER ::= { cvplsLdpConformance 2 }

cvplsLdpConfigTable OBJECT-TYPE
    SYNTAX SEQUENCE OF CvplsLdpConfigEntry
    ACCESS not-accessible
    STATUS mandatory
    DESCRIPTION
        "This table specifies information for configuring
        and monitoring LDP specific parameters for
        Virtual Private Lan Services(VPLS)."
    ::= { cvplsLdpObjects 1 }

cvplsLdpConfigEntry OBJECT-TYPE
    SYNTAX CvplsLdpConfigEntry
    ACCESS not-accessible
    STATUS mandatory
    DESCRIPTION
        "A row in this table represents LDP specific information
        for Virtual Private Lan Service(VPLS) in a packet network.
        It is indexed by cvplsConfigIndex, which uniquely
        identifies a single VPLS.
        
        A row is automatically created when a VPLS service is
        configured using LDP signalling.
        
        None of the read-create objects values can be
        changed when cvplsRowStatus is in the active(1)
        state. Changes are allowed when the cvplsRowStatus
        is in notInService(2) or notReady(3) states only.
        If the operator need to change one of the values
        for an active row the cvplsConfigRowStatus should be
        first changed to notInService(2), the objects may
        be changed now, and later to active(1) in order to
        re-initiate the signaling process with the new
        values in effect."
    INDEX { cvplsConfigIndex }
    ::= { cvplsLdpConfigTable 1 }

CvplsLdpConfigEntry ::= SEQUENCE {
    cvplsLdpConfigMacAddrWithdraw TruthValue
    }

cvplsLdpConfigMacAddrWithdraw OBJECT-TYPE
    SYNTAX TruthValue
--    Rsyntax INTEGER {
--        true(1),
--        false(2)
--        }
    ACCESS read-write
    STATUS mandatory
    DESCRIPTION
        "This object specifies if MAC address withdrawl is
        enabled in this service. If this object is true then
        Mac address withdrawl Learning is enabled. If false,
        then Mac Learning is disabled."
    DEFVAL { true }
    ::= { cvplsLdpConfigEntry 1 }

cvplsLdpPwBindTable OBJECT-TYPE
    SYNTAX SEQUENCE OF CvplsLdpPwBindEntry
    ACCESS not-accessible
    STATUS mandatory
    DESCRIPTION
        "This table provides LDP specific information for
        an association between a VPLS service and the
        corresponding Pseudo Wires. A service can have more
        than one Pseudo Wire association. Pseudo Wires are
        defined in the cpwTable."
    ::= { cvplsLdpObjects 2 }

cvplsLdpPwBindEntry OBJECT-TYPE
    SYNTAX CvplsLdpPwBindEntry
    ACCESS not-accessible
    STATUS mandatory
    DESCRIPTION
        "Each row represents an association between a
        VPLS instance and one or more Pseudo Wires
        defined in the cpwTable. Each index is unique
        in describing an entry in this table. However
        both indexes are required to define the one
        to many association of service to pseudowire.
        
        An entry in this table is instantiated only when 
        LDP signalling is used to configure VPLS service.
        
        Each entry in this table provides LDP specific
        information for the VPlS represented by 
        cvplsConfigIndex."
    INDEX { cvplsConfigIndex, cvplsPwBindIndex }
    ::= { cvplsLdpPwBindTable 1 }

CvplsLdpPwBindEntry ::= SEQUENCE {
    cvplsLdpPwBindMacAddressLimit Gauge
    }

cvplsLdpPwBindMacAddressLimit OBJECT-TYPE
    SYNTAX Gauge(0..4294967295)
    ACCESS read-write
    STATUS mandatory
    DESCRIPTION
        "The value of this object specifies the maximum number
        of learned and static entries allowed in the
        Forwarding database for this PW Binding. The value 0
        means there is no limit for this PW Binding."
    DEFVAL { 0 }
    ::= { cvplsLdpPwBindEntry 1 }

cvplsLdpGroup OBJECT IDENTIFIER ::= { cvplsLdpGroups 1 }
-- OBJECT-GROUP
--  Status
--    mandatory
--  Descr
--    The group of objects supporting
--    management of L2VPN VPLS services using LDP.
--  objects
--    cvplsLdpConfigMacAddrWithdraw, cvplsLdpPwBindMacAddressLimit

cvplsLdpModuleFullCompliance OBJECT IDENTIFIER ::= { cvplsLdpCompliances 1 }
-- MODULE-COMPLIANCE
--  Status
--    mandatory
--  Descr
--    Compliance requirement for implementations that
--    provide full support for CISCO-IETF-VPLS-LDP-MIB.
--    Such devices can then be monitored and configured using 
--    this MIB module.
--  Module
--    >>current<<
--   MandGroup
--    cvplsLdpGroup

cvplsLdpModuleReadOnlyCompliance OBJECT IDENTIFIER ::= { cvplsLdpCompliances 2 }
-- MODULE-COMPLIANCE
--  Status
--    mandatory
--  Descr
--    Compliance requirement for implementations that only
--    provide read-only support for CISCO-IETF-VPLS-LDP-MIB.
--    Such devices can then be monitored but cannot be
--    configured using this MIB modules.
--  Module
--    >>current<<
--   MandGroup
--    cvplsLdpGroup
--   ObjVar
--    cvplsLdpConfigMacAddrWithdraw
--   ObjVar
--    cvplsLdpPwBindMacAddressLimit


END
