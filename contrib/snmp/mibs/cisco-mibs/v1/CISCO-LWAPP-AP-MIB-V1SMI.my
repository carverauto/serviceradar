-- MIB file created 12-Jun-2012 23:59:45, by
--   SMICng version 2.2.11-beta(PRO)(Solaris), January 20, 2001. Enterprise key cisco.com

CISCO-LWAPP-AP-MIB DEFINITIONS ::= BEGIN

-- From file: "CISCO-LWAPP-AP-MIB.my"
-- Compile options "4 7 F H N W 03 06 0B 0G 0N 0T"

IMPORTS
    DisplayString, TruthValue, MacAddress, TimeInterval, RowStatus, 
    TimeStamp
            FROM SNMPv2-TC-v1
    SnmpAdminString
            FROM SNMP-FRAMEWORK-MIB
    PhysicalIndex
            FROM ENTITY-MIB
    InetAddressType, InetAddress, InetPortNumber
            FROM INET-ADDRESS-MIB
    CLApIfType, CLDot11Channel, CLApAssocFailureReason, 
    CLApDot11RadioSubband, CLApDot11RadioRole
            FROM CISCO-LWAPP-TC-MIB
    cldRegulatoryDomain
            FROM CISCO-LWAPP-DOT11-MIB
    ciscoMgmt
            FROM CISCO-SMI
    Counter, Gauge, TimeTicks
            FROM RFC1155-SMI
    OBJECT-TYPE
            FROM RFC-1212
    TRAP-TYPE
            FROM RFC-1215;

ciscoLwappApMIB OBJECT IDENTIFIER ::= { ciscoMgmt 513 }
-- MODULE-IDENTITY
--  LastUpdated
--    201206130000Z
--  OrgName
--    Cisco Systems Inc.
--  ContactInfo
--    Cisco Systems,
--    Customer Service
--    
--    Postal: 170 West Tasman Drive
--    San Jose, CA  95134
--    USA
--    
--    Tel: +1 800 553-NETS
--    
--    Email: cs-snmp@cisco.com
--  Descr
--    This MIB is intended to be implemented on all those
--    devices operating as Central Controllers (CC) that
--    terminate the Light Weight Access Point Protocol
--    tunnel from Light-weight LWAPP Access Points.
--    
--    This MIB provides configuration and status information
--    about the 802.11 Access Points that have joined the
--    controller.                 
--    
--    The relationship between CC and the LWAPP APs
--    can be depicted as follows:
--    
--    +......+     +......+     +......+           +......+
--    +      +     +      +     +      +           +      +
--    +  CC  +     +  CC  +     +  CC  +           +  CC  +
--    +      +     +      +     +      +           +      +
--    +......+     +......+     +......+           +......+
--    ..            .             .                 .
--    ..            .             .                 .
--    .  .            .             .                 .
--    .    .            .             .                 .
--    .      .            .             .                 .
--    .        .            .             .                 .
--    +......+ +......+     +......+      +......+          +......+
--    +      + +      +     +      +      +      +          +      +
--    +  AP  + +  AP  +     +  AP  +      +  AP  +          +  AP  +
--    +      + +      +     +      +      +      +          +      +
--    +......+ +......+     +......+      +......+          +......+
--    .              .             .                 .
--    .  .              .             .                 .
--    .    .              .             .                 .
--    .      .              .             .                 .
--    .        .              .             .                 .
--    +......+ +......+     +......+      +......+          +......+
--    +      + +      +     +      +      +      +          +      +
--    +  MN  + +  MN  +     +  MN  +      +  MN  +          +  MN  +
--    +      + +      +     +      +      +      +          +      +
--    +......+ +......+     +......+      +......+          +......+
--    
--    
--    The LWAPP tunnel exists between the controller and
--    the APs.  The MNs communicate with the APs through
--    the protocol defined by the 802.11 standard.
--    
--    LWAPP APs, upon bootup, discover and join one of the
--    controllers and the controller pushes the configuration,
--    that includes the WLAN parameters, to the LWAPP APs.
--    The APs then encapsulate all the 802.11 frames from
--    wireless clients inside LWAPP frames and forward
--    the LWAPP frames to the controller.
--    
--                       GLOSSARY
--    
--    Access Point ( AP )
--    
--    An entity that contains an 802.11 medium access
--    control ( MAC ) and physical layer ( PHY ) interface
--    and provides access to the distribution services via
--    the wireless medium for associated clients.  
--    
--    LWAPP APs encapsulate all the 802.11 frames in
--    LWAPP frames and sends it to the controller to which
--    it is logically connected.
--    
--    Basic Service Set Identifier (BSSID)
--    
--    The identifier for the service set comprising of
--    all the 802.11 stations under the control of
--    one coordinating Access Point.  This identifier
--    happens to be the MAC address of the dot11 radio
--    interface of the Access Point.  The wireless
--    clients that associate with the Access Point
--    get the wired uplink through this particular 
--    dot11 interface. 
--    
--    Central Controller ( CC )
--    
--    The central entity that terminates the LWAPP protocol
--    tunnel from the LWAPP APs.  Throughout this MIB,
--    this entity also referred to as 'controller'. 
--    
--    Light Weight Access Point Protocol ( LWAPP ) 
--    
--    This is a generic protocol that defines the 
--    communication between the Access Points and the
--    Central Controller. 
--    
--    Mobile Node ( MN )
--    
--    A roaming 802.11 wireless device in a wireless
--    network associated with an access point. 
--    
--    Station Management (SMT)
--    
--    This term refers to the internal management of the
--    802.11 protocol operations by the AP to work
--    cooperatively with the other APs and 802.11
--    devices in the network.
--    
--    Link Latency 
--    
--    Latency is round trip time between AP and controller.
--    There is a continuous heart-beat between AP and 
--    controller. AP calculates latency for each time and 
--    sends to controller.
--    
--    AMSDU
--    
--    Aggregate MAC Service Data Unit. A structure containing 
--    multiple MSDUs, transported within a single (unfragmented)  
--    or multiple (fragmented) Data MPDU. 
--    
--    DTLS
--    
--    Datagram Transport Layer Security (DTLS) protocol provides 
--    communications privacy for datagram protocols. The protocol 
--    allows client/server applications to communicate in a way 
--    that is designed to prevent eavesdropping, tampering, or 
--    message forgery. 
--    
--    WIPS
--    
--    Wireless Intrusion Prevention System (WIPS) is a network device 
--    that monitors the radio spectrum for the presence of 
--    unauthorized access points (intrusion detection), and can 
--    automatically take countermeasures (intrusion prevention).
--    
--    SE
--    
--    Spectrum Expert is an application software, which when 
--    connected to Spectrum Intelligent Access Point, provides 
--    detailed RF spectrum plots and data, and assist in diagnosing 
--    network problems. 
--    
--    REFERENCE
--    
--    [1] Part 11 Wireless LAN Medium Access Control ( MAC )
--    and Physical Layer ( PHY ) Specifications.
--    
--    [2] Draft-obara-capwap-lwapp-00.txt, IETF Light 
--    Weight Access Point Protocol.
--  RevDate
--    201206130000Z
--  RevDescr
--    Added ciscoLwappDot11IfAntennaGroup and
--    ciscoLwappRetransmitGroup
--  RevDate
--    201102070000Z
--  RevDescr
--    Addressed Approver's comments.
--  RevDate
--    201101210000Z
--  RevDescr
--    Addressed reviwer's comments.
--  RevDate
--    201101100000Z
--  RevDescr
--    Addressed reviewer's comments.
--  RevDate
--    201012130000Z
--  RevDescr
--    Addressed Reviwer's comments
--  RevDate
--    201008190000Z
--  RevDescr
--    Added cLApGlobal, cLApCredentials, cLSpectrum,
--    cLAp802dot1xSupplicant mib objects.
--    Added link latency tables, cLApEncryptionEnable.
--    cLApDot11RadioTable have been added to provide support
--    for subband radios.
--    AP uptime, join time, join taken time and Ethernet slot info
--    have been added to clApTable.  cLApEthernetIfTable which
--    provides Ethernet interface status and statistics information
--    has been added.
--    The group ciscoLwappApGroupSup3, ciscoLwappApGroupSup4,
--    ciscoLwappApNotifObjsGroup and ciscoLwappApNotifsGroup 
--    have been added.
--  RevDate
--    200701030000Z
--  RevDescr
--    The object cLApName has been added.
--  RevDate
--    200607180000Z
--  RevDescr
--    Added cLApEntPhysicalIndex object.
--  RevDate
--    200603300000Z
--  RevDescr
--    Initial version of this MIB module.

ciscoLwappApMIBNotifs OBJECT IDENTIFIER ::= { ciscoLwappApMIB 0 }
ciscoLwappApMIBObjects OBJECT IDENTIFIER ::= { ciscoLwappApMIB 1 }
ciscoLwappApMIBConform OBJECT IDENTIFIER ::= { ciscoLwappApMIB 2 }
ciscoLwappApMIBNotifObjects OBJECT IDENTIFIER ::= { ciscoLwappApMIB 3 }
ciscoLwappAp    OBJECT IDENTIFIER ::= { ciscoLwappApMIBObjects 1 }
ciscoLwappApIf  OBJECT IDENTIFIER ::= { ciscoLwappApMIBObjects 2 }
ciscoLwappApGlobal OBJECT IDENTIFIER ::= { ciscoLwappApMIBObjects 3 }
ciscoLwappApCredentials OBJECT IDENTIFIER ::= { ciscoLwappApMIBObjects 4 }
ciscoLwappLinkLatency OBJECT IDENTIFIER ::= { ciscoLwappApMIBObjects 5 }
ciscoLwappSpectrum OBJECT IDENTIFIER ::= { ciscoLwappApMIBObjects 6 }
ciscoLwappAp802dot1xSupplicant OBJECT IDENTIFIER ::= { ciscoLwappApMIBObjects 7 }
ciscoLwappApMIBCompliances OBJECT IDENTIFIER ::= { ciscoLwappApMIBConform 1 }
ciscoLwappApMIBGroups OBJECT IDENTIFIER ::= { ciscoLwappApMIBConform 2 }

cLApTable OBJECT-TYPE
    SYNTAX SEQUENCE OF CLApEntry
    ACCESS not-accessible
    STATUS mandatory
    DESCRIPTION
        "This table represents the information about the
        802.11 LWAPP Access Points that have joined the
        controller.
        
        LWAPP APs exchange configuration messages with the
        controller and get the required configuration for
        their 802.11 related operations, after they join the
        controller."
    ::= { ciscoLwappAp 1 }

cLApEntry OBJECT-TYPE
    SYNTAX CLApEntry
    ACCESS not-accessible
    STATUS mandatory
    DESCRIPTION
        "Each entry in this table provides information about
        one 802.11 LWAPP Access Point that has joined the
        controller.
        
        Entries are removed when the APs lose their
        association with the controller due to loss
        of communication."
    INDEX { cLApSysMacAddress }
    ::= { cLApTable 1 }

CLApEntry ::= SEQUENCE {
    cLApSysMacAddress MacAddress,
    cLApIfMacAddress MacAddress,
    cLApMaxNumberOfDot11Slots Gauge,
    cLApEntPhysicalIndex PhysicalIndex,
    cLApName SnmpAdminString,
    cLApUpTime TimeTicks,
    cLLwappUpTime TimeTicks,
    cLLwappJoinTakenTime TimeTicks,
    cLApMaxNumberOfEthernetSlots Gauge,
    cLApPrimaryControllerAddressType InetAddressType,
    cLApPrimaryControllerAddress InetAddress,
    cLApSecondaryControllerAddressType InetAddressType,
    cLApSecondaryControllerAddress InetAddress,
    cLApTertiaryControllerAddressType InetAddressType,
    cLApTertiaryControllerAddress InetAddress,
    cLApLastRebootReason INTEGER,
    cLApEncryptionEnable TruthValue,
    cLApFailoverPriority INTEGER,
    cLApPowerStatus INTEGER,
    cLApTelnetEnable TruthValue,
    cLApSshEnable TruthValue,
    cLApPreStdStateEnabled TruthValue,
    cLApPwrInjectorStateEnabled TruthValue,
    cLApPwrInjectorSelection INTEGER,
    cLApPwrInjectorSwMacAddr MacAddress,
    cLApWipsEnable TruthValue,
    cLApMonitorModeOptimization INTEGER,
    cLApDomainName SnmpAdminString,
    cLApNameServerAddressType InetAddressType,
    cLApNameServerAddress InetAddress,
    cLApAMSDUEnable TruthValue,
    cLApEncryptionSupported TruthValue,
    cLApRogueDetectionEnabled TruthValue,
    cLApTcpMss INTEGER,
    cLApDataEncryptionStatus TruthValue,
    cLApNsiKey DisplayString,
    cLApAdminStatus TruthValue,
    cLApPortNumber InetPortNumber,
    cLApRetransmitCount Gauge,
    cLApRetransmitTimeout Gauge
    }

cLApSysMacAddress OBJECT-TYPE
    SYNTAX MacAddress
--    Rsyntax OCTET STRING(SIZE(6))
    ACCESS not-accessible
    STATUS mandatory
    DESCRIPTION
        "This object represents the radio MAC address
        common to the dot11 interfaces of the AP
        and uniquely identifies an entry in this table."
    ::= { cLApEntry 1 }

cLApIfMacAddress OBJECT-TYPE
    SYNTAX MacAddress
--    Rsyntax OCTET STRING(SIZE(6))
    ACCESS read-only
    STATUS mandatory
    DESCRIPTION
        "This object represents the Ethernet MAC address of
        the AP."
    ::= { cLApEntry 2 }

cLApMaxNumberOfDot11Slots OBJECT-TYPE
    SYNTAX Gauge
    ACCESS read-only
    STATUS mandatory
    DESCRIPTION
        "This object represents the maximum number of
        802.11 radio interface slots in this AP."
    ::= { cLApEntry 3 }

cLApEntPhysicalIndex OBJECT-TYPE
    SYNTAX PhysicalIndex
--    Rsyntax INTEGER(1..2147483647)
    ACCESS read-only
    STATUS mandatory
    DESCRIPTION
        "This object provides the index value in the
        entPhysicalEntry corresponding to this AP."
    ::= { cLApEntry 4 }

cLApName OBJECT-TYPE
    SYNTAX SnmpAdminString(SIZE(0..32))
--    Rsyntax OCTET STRING(SIZE(0..32))
    ACCESS read-write
    STATUS mandatory
    DESCRIPTION
        "This object represents the administrative name
        assigned to the AP by the user. If an AP is not configured, 
        its factory default name will be ap:<last three byte 
        of MACAddress> eg. ap:af:12:be."
    ::= { cLApEntry 5 }

cLApUpTime OBJECT-TYPE
    SYNTAX TimeTicks
    ACCESS read-only
    STATUS mandatory
    DESCRIPTION
        "This object represents the time in hundredths
        of a second since the last time the AP rebooted."
    ::= { cLApEntry 6 }

cLLwappUpTime OBJECT-TYPE
    SYNTAX TimeTicks
    ACCESS read-only
    STATUS mandatory
    DESCRIPTION
        "This object represents the time in hundredths
        of a second since the last time the AP joined 
        the controller."
    ::= { cLApEntry 7 }

cLLwappJoinTakenTime OBJECT-TYPE
    SYNTAX TimeTicks
    ACCESS read-only
    STATUS mandatory
    DESCRIPTION
        "This object represents the time taken in hundredths
        of a second for the AP to join the controller. This 
        could be a significant value in Mesh environments."
    ::= { cLApEntry 8 }

cLApMaxNumberOfEthernetSlots OBJECT-TYPE
    SYNTAX Gauge
    ACCESS read-only
    STATUS mandatory
    DESCRIPTION
        "This object represents the maximum number of
        Ethernet slots in this AP."
    ::= { cLApEntry 9 }

cLApPrimaryControllerAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object represents the type of the primary
        controller's address made available through 
        cLApPrimaryControllerAddress."
    ::= { cLApEntry 10 }

cLApPrimaryControllerAddress OBJECT-TYPE
    SYNTAX InetAddress
--    Rsyntax OCTET STRING(SIZE(0..255))
    ACCESS read-write
    STATUS mandatory
    DESCRIPTION
        "This object represents the address of the primary
        controller that the APs will join."
    ::= { cLApEntry 11 }

cLApSecondaryControllerAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object represents the type of the secondary
        controller's address made available through 
        cLApSecondaryControllerAddress."
    ::= { cLApEntry 12 }

cLApSecondaryControllerAddress OBJECT-TYPE
    SYNTAX InetAddress
--    Rsyntax OCTET STRING(SIZE(0..255))
    ACCESS read-write
    STATUS mandatory
    DESCRIPTION
        "This object represents the address of the secondary
        controller that the APs will join."
    ::= { cLApEntry 13 }

cLApTertiaryControllerAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object represents the type of the tertiary
        controller's address made available through 
        cLApTertiaryControllerAddress."
    ::= { cLApEntry 14 }

cLApTertiaryControllerAddress OBJECT-TYPE
    SYNTAX InetAddress
--    Rsyntax OCTET STRING(SIZE(0..255))
    ACCESS read-write
    STATUS mandatory
    DESCRIPTION
        "This object represents the address of the tertiary
        controller that the APs will join."
    ::= { cLApEntry 15 }

cLApLastRebootReason OBJECT-TYPE
    SYNTAX INTEGER {
        --?? enum value of zero may cause problems
--        none(0),
        dot11gModeChange(1),
        ipAddressSet(2),
        ipAddressReset(3),
        rebootFromController(4),
        dhcpFallbackFail(5),
        discoveryFail(6),
        noJoinResponse(7),
        denyJoin(8),
        noConfigResponse(9),
        configController(10),
        imageUpgradeSuccess(11),
        imageOpcodeInvalid(12),
        imageCheckSumInvalid(13),
        imageDataTimeout(14),
        configFileInvalid(15),
        imageDownloadError(16),
        rebootFromConsole(17),
        rapOverAir(18),
        powerLow(19),
        crash(20),
        powerHigh(21),
        powerLoss(22),
        powerChange(23),
        componentFailure(24),
        watchdog(25)
        }
    ACCESS read-only
    STATUS mandatory
    DESCRIPTION
        "This object represents the reason for the last
        reboot of the AP.
         none                 - ap reported a reboot reason code
                                unknown to the controller.
         dot11gModeChange     - 11g mode change
         ipAddressSet         - set static ip address
         ipAddressReset       - reset static ip address
         rebootFromController - ap reboot initiated 
                                from controller
         dhcpFallbackFail     - could not fallback to dhcp
         discoveryFail        - could not send discovery
         noJoinResponse       - did not receive join response
         denyJoin             - deny join attempt at 
                                the controller
         noConfigResponse     - did not get config response
         configController     - found configured or master 
                                controller
         imageUpgradeSuccess  - image upgraded successfully
         imageOpcodeInvalid   - invalid image data opcode
         imageCheckSumInvalid - invalid image md5 checksum
         imageDataTimeout     - image data message timeout
         configFileInvalid    - invalid config file
         imageDownloadError   - image download process error
         rebootFromConsole    - reboot command from ap console
         rapOverAir           - root access point is connected 
                                over the air
         brownout             - ap rebooted due to power failure
         powerLow             - ap rebooted dued to low power
                                also called as brownout
         crash                - crashed due to software failure
         powerHigh            - rebooted due to power spike
         powerLoss            - rebooted due to power loss
         powerChange          - rebooted due to change in 
                                power source
         componentFailure     - rebooted due to component 
                                failure
         watchdog             - rebooted due to watch dog 
                                timer reset."
    ::= { cLApEntry 16 }

cLApEncryptionEnable OBJECT-TYPE
    SYNTAX TruthValue
--    Rsyntax INTEGER {
--        true(1),
--        false(2)
--        }
    ACCESS read-write
    STATUS mandatory
    DESCRIPTION
        "This object specifies whether encyrption between
        controller and AP is enabled or not. Encryption
        can only be enabled if ESM card in controller is 
        pluged in.
        
        A value of 'true' enables encryption between 
        controller and AP.
        
        A value of 'false' disables encryption between 
        controller and AP."
    DEFVAL { false }
    ::= { cLApEntry 18 }

cLApFailoverPriority OBJECT-TYPE
    SYNTAX INTEGER {
        low(1),
        medium(2),
        high(3),
        critical(4)
        }
    ACCESS read-write
    STATUS mandatory
    DESCRIPTION
        "This object represents the AP failover priority
        for an AP. If a higher priority AP wishes to join 
        the controller, it will be given preference over 
        a join request from a lower priority AP. Also if the 
        number of AP joined has reached the limit that the 
        controller can support then the controller can disassociate 
        an already joined lower priority AP. This priority will be 
        considered only if the cLApGlobalFailoverPriority is 
        Enabled on the controller."
    DEFVAL { low }
    ::= { cLApEntry 19 }

cLApPowerStatus OBJECT-TYPE
    SYNTAX INTEGER {
        low(1),
        fifteendotfour(2),
        sixteendoteight(3),
        full(4),
        external(5),
        mixedmode(6)
        }
    ACCESS read-only
    STATUS mandatory
    DESCRIPTION
        "This object represents the power status of the AP
        low             - The AP is drawing low power from 
                          Ethernet 
        fifteendotfour  - The AP is drawing 15.4 watts from 
                          Ethernet
        sixteendoteight - The AP is drawing 16.8 watts from
                          Ethernet
        full            - The power is high enough for 
                          normal operation of the AP. 
                          The power source could be 
                          Ethernet or external
        external        - The power source is not from
                          Ethernet.
        mixedmode       - The power is high enough for 
                          operation of AP. In this state 
                          one radio will operate in full 
                          power mode while the other radio 
                          will be powered off."
    ::= { cLApEntry 20 }

cLApTelnetEnable OBJECT-TYPE
    SYNTAX TruthValue
--    Rsyntax INTEGER {
--        true(1),
--        false(2)
--        }
    ACCESS read-write
    STATUS mandatory
    DESCRIPTION
        "This object specifies whether Telnet session
        can be established to the AP. 
        
        A value of 'true' indicates an Telnet session
        can be established to the AP. 
        
        A value of 'false' indicates an Telnet session
        cannot be established to the AP."
    DEFVAL { false }
    ::= { cLApEntry 21 }

cLApSshEnable OBJECT-TYPE
    SYNTAX TruthValue
--    Rsyntax INTEGER {
--        true(1),
--        false(2)
--        }
    ACCESS read-write
    STATUS mandatory
    DESCRIPTION
        "This object specifies whether SSH session
        can be established to the AP. 
        
        A value of 'true' indicates an SSH session
        can be established to the AP. 
        
        A value of 'false' indicates an SSH session
        cannot be established to the AP."
    DEFVAL { false }
    ::= { cLApEntry 22 }

cLApPreStdStateEnabled OBJECT-TYPE
    SYNTAX TruthValue
--    Rsyntax INTEGER {
--        true(1),
--        false(2)
--        }
    ACCESS read-write
    STATUS mandatory
    DESCRIPTION
        "This object represents whether the Pre-Standard state
        of the AP is enabled or disabled.
        
        A value of 'true' denotes that the Pre-Standard state
        of the AP is enabled,
        
        A value of 'false' denotes that the Pre-Standard state
        of the AP is disabled"
    ::= { cLApEntry 23 }

cLApPwrInjectorStateEnabled OBJECT-TYPE
    SYNTAX TruthValue
--    Rsyntax INTEGER {
--        true(1),
--        false(2)
--        }
    ACCESS read-write
    STATUS mandatory
    DESCRIPTION
        "This object represents whether the Power Injector state
        of the AP is enabled or disabled.
        
        A value of 'true' denotes that the Power Injector state
        of the AP is enabled,
        
        A value of 'false' denotes that the Power Injector state
        of the AP is disabled"
    ::= { cLApEntry 24 }

cLApPwrInjectorSelection OBJECT-TYPE
    SYNTAX INTEGER {
        unknown(1),
        installed(2),
        override(3)
        }
    ACCESS read-write
    STATUS mandatory
    DESCRIPTION
        "This object specifies the Power Injector selection
        value of the AP.
        
        'unknown'   - is returned if 
                      'cLApPwrInjectorStateEnabled'is set to false.
        'installed' - configure the MAC address of the 
                      switch port that has a Power Injector.
        'override'  - override the safety checks and assume 
                      a Power Injector is always installed."
    ::= { cLApEntry 25 }

cLApPwrInjectorSwMacAddr OBJECT-TYPE
    SYNTAX MacAddress
--    Rsyntax OCTET STRING(SIZE(6))
    ACCESS read-write
    STATUS mandatory
    DESCRIPTION
        "This object represents the Mac address of the
        switch port that has a power Injector and is 
        valid only when the 'cLApPwrInjectorSelection' 
        is in 'installed' mode.
        if SET to 00:00:00:00:00:00, AP will detect the 
        MAC address of the current switch port that has 
        a Power Injector"
    ::= { cLApEntry 26 }

cLApWipsEnable OBJECT-TYPE
    SYNTAX TruthValue
--    Rsyntax INTEGER {
--        true(1),
--        false(2)
--        }
    ACCESS read-write
    STATUS mandatory
    DESCRIPTION
        "This object represents if this AP is used
        as WIPS AP.
        A value of 'true' indicates that this AP is
        a WIPS AP.
        A value of 'false' indicates that this AP is
        not a WIPS AP. This applies only when the 
        AP is either in local or monitor mode."
    DEFVAL { false }
    ::= { cLApEntry 27 }

cLApMonitorModeOptimization OBJECT-TYPE
    SYNTAX INTEGER {
        all(1),
        tracking(2),
        wips(3),
        none(4)
        }
    ACCESS read-write
    STATUS mandatory
    DESCRIPTION
        "This object represents the monitor mode optimization
        on this device.
            all      - All optimization is enabled 
            tracking - Tracking is optimized 
            wips     - WIPS optimization is enabled
            none     - No optimization is enabled"
    ::= { cLApEntry 28 }

cLApDomainName OBJECT-TYPE
    SYNTAX SnmpAdminString
--    Rsyntax OCTET STRING(SIZE(0..255))
    ACCESS read-write
    STATUS mandatory
    DESCRIPTION
        "This represents the domain, to which the AP belongs.
        This attribute can be configured only if the static IP
        option is turned on in the AP."
    ::= { cLApEntry 29 }

cLApNameServerAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This represents the type of the IP address of the
        name server, made available through cLApNameServerAddress."
    ::= { cLApEntry 30 }

cLApNameServerAddress OBJECT-TYPE
    SYNTAX InetAddress
--    Rsyntax OCTET STRING(SIZE(0..255))
    ACCESS read-write
    STATUS mandatory
    DESCRIPTION
        "This represents the IP Address of the name server.
        This attribute can be configured only if the static IP
        option is turned on in the AP."
    ::= { cLApEntry 31 }

cLApAMSDUEnable OBJECT-TYPE
    SYNTAX TruthValue
--    Rsyntax INTEGER {
--        true(1),
--        false(2)
--        }
    ACCESS read-write
    STATUS mandatory
    DESCRIPTION
        "This object specifies the AMSDU status.
        A value of 'true' turns on the AMSDU.
        A value of 'false' turns off the AMSDU."
    DEFVAL { false }
    ::= { cLApEntry 32 }

cLApEncryptionSupported OBJECT-TYPE
    SYNTAX TruthValue
--    Rsyntax INTEGER {
--        true(1),
--        false(2)
--        }
    ACCESS read-write
    STATUS mandatory
    DESCRIPTION
        "This object specifies whether AP Supports
        DTLS encryption.                 
        A value of 'true' indicates encryption is supported.
        A value of 'false' indicates encryption is not supported."
    DEFVAL { false }
    ::= { cLApEntry 33 }

cLApRogueDetectionEnabled OBJECT-TYPE
    SYNTAX TruthValue
--    Rsyntax INTEGER {
--        true(1),
--        false(2)
--        }
    ACCESS read-write
    STATUS mandatory
    DESCRIPTION
        "This object specifies whether Rogue Detection
        is enabled in this AP.                 
        A value of 'true' enables Rogue Detection.
        A value of 'false' disables Rogue Detection.
        Rogue detection is not supported on sniffer 
        and rogue detector mode APs."
    DEFVAL { false }
    ::= { cLApEntry 34 }

cLApTcpMss OBJECT-TYPE
    SYNTAX INTEGER(0|536..1363)
    ACCESS read-write
    STATUS mandatory
    DESCRIPTION
        "This object specifies the TCP Maximum Segment Size
        for this AP.
        Permissible value are between 536 and 1363. This will
        also enable the TCP MSS flag for this AP.
        Value of 0 will disable the TCP MSS flag for this AP.
        Any change of value for cLApGlobalTcpMss will be 
        reflected to this object. 
        Value for this object can be change only when value of 
        cLApGlobalTcpMss is set as 0."
    ::= { cLApEntry 35 }

cLApDataEncryptionStatus OBJECT-TYPE
    SYNTAX TruthValue
--    Rsyntax INTEGER {
--        true(1),
--        false(2)
--        }
    ACCESS read-only
    STATUS mandatory
    DESCRIPTION
        "This object specifies the data encryption
        status of AP.
        
        A value of 'true' means data is encrypted between
                        AP and WLC.
        
        A value of 'false' means data is Plain Text between
                        AP and WLC."
    DEFVAL { false }
    ::= { cLApEntry 36 }

cLApNsiKey OBJECT-TYPE
    SYNTAX DisplayString(SIZE(0..32))
--    Rsyntax OCTET STRING(SIZE(0..32))
    ACCESS read-only
    STATUS mandatory
    DESCRIPTION
        "This object specifies the Network Spectrum Interface Key
        used when the AP is in Spectrum Expert Only Monitor Mode
        (SOMM).This object returns a non-zero value only when the 
        AP is SOMM mode."
    ::= { cLApEntry 37 }

cLApAdminStatus OBJECT-TYPE
    SYNTAX TruthValue
--    Rsyntax INTEGER {
--        true(1),
--        false(2)
--        }
    ACCESS read-write
    STATUS mandatory
    DESCRIPTION
        "This object specifies the Admin State of the AP,
        A value of 'true' enables the Admin State.
        A value of 'false' disables the Admin State."
    DEFVAL { false }
    ::= { cLApEntry 38 }

cLApPortNumber OBJECT-TYPE
    SYNTAX InetPortNumber
--    Rsyntax Gauge(0..65535)
    ACCESS read-only
    STATUS mandatory
    DESCRIPTION
        "This object specifies the port number on which
        the AP's traffic is coming through."
    ::= { cLApEntry 39 }

cLApRetransmitCount OBJECT-TYPE
    SYNTAX Gauge
--  Units
--    retries
    ACCESS read-write
    STATUS mandatory
    DESCRIPTION
        "This object specifies the retransmission count for the Access
        Point Control Packet.This value represents the number of packets
        retransmitted after which the Access Point falls back to another
        controller in case of failover.
        The global retransmit parameters are applicable for all Access 
        Points within a controller. The individual paramters per Access 
        Point, if configured takes precedence over the global values. 
        If an AccessPoint falls back from another controller(in case of
        failover), the values at the AP level has more precedence over 
        the global values in the controller with which it has joined."
    ::= { cLApEntry 40 }

cLApRetransmitTimeout OBJECT-TYPE
    SYNTAX Gauge
--  Units
--    seconds
    ACCESS read-write
    STATUS mandatory
    DESCRIPTION
        "This object specifies the retransmission timeout for the Access
        Point Control packet. This value represents the timeout for each
        retransmission, during the fallback of Access Point to another 
        controller in case of failover.
        The global retransmit parameters are applicable for all Access 
        Points within a controller. The individual paramters per Access
        Point, if configured takes precedence over the global values. 
        If an AccessPoint falls back from another controller(in case of
        failover), the values at the AP level has more precedence over 
        the global values in the controller with which it has joined."
    ::= { cLApEntry 41 }

cLApDot11IfTable OBJECT-TYPE
    SYNTAX SEQUENCE OF CLApDot11IfEntry
    ACCESS not-accessible
    STATUS mandatory
    DESCRIPTION
        "This table represents the information about the
        basic functional parameters corresponding to
        the dot11 interfaces of the APs that have joined
        the controller."
    ::= { ciscoLwappApIf 1 }

cLApDot11IfEntry OBJECT-TYPE
    SYNTAX CLApDot11IfEntry
    ACCESS not-accessible
    STATUS mandatory
    DESCRIPTION
        "An entry in this table represents the 802.11
        functional parameters of the dot11 interface of
        an AP that has joined the controller.
        
        Entries are added when the APs associate to this
        controller and deleted when they lose their
        association."
    INDEX { cLApSysMacAddress, cLApDot11IfSlotId }
    ::= { cLApDot11IfTable 1 }

CLApDot11IfEntry ::= SEQUENCE {
    cLApDot11IfSlotId Gauge,
    cLApDot11IfType CLApIfType,
    cLApDot11IfRegDomain DisplayString,
    cLApDot11nSupport TruthValue,
    cLAp11nChannelBandwidth INTEGER,
    cLApLomEnabled TruthValue,
    cLApLomFirstChannel CLDot11Channel,
    cLApLomSecondChannel CLDot11Channel,
    cLApLomThirdChannel CLDot11Channel,
    cLApLomFourthChannel CLDot11Channel,
    cLApExtensionChannel CLDot11Channel,
    cLApLegacyBeamForming INTEGER,
    cLApCdpOverAirEnabled TruthValue,
    cLApDot11IfAdminStatus TruthValue
    }

cLApDot11IfSlotId OBJECT-TYPE
    SYNTAX Gauge
    ACCESS not-accessible
    STATUS mandatory
    DESCRIPTION
        "This object represents the slot ID of a dot11
        interface on an AP. 
        
        The slot ID for a particular dot11 interface as
        represented by this object ranges from 0 to 
        cLApMaxNumberOfDot11Slots - 1."
    ::= { cLApDot11IfEntry 1 }

cLApDot11IfType OBJECT-TYPE
    SYNTAX CLApIfType
--    Rsyntax INTEGER {
--        dot11bg(1),
--        dot11a(2),
--        uwb(3)
--        }
    ACCESS read-only
    STATUS mandatory
    DESCRIPTION
        "This object represents the type of this dot11
        interface."
    ::= { cLApDot11IfEntry 2 }

cLApDot11IfRegDomain OBJECT-TYPE
    SYNTAX DisplayString(SIZE(1..255))
--    Rsyntax OCTET STRING(SIZE(1..255))
    ACCESS read-only
    STATUS mandatory
    DESCRIPTION
        "This object indicates the regulatory domain for
        this radio type on this AP."
    ::= { cLApDot11IfEntry 3 }

cLApDot11nSupport OBJECT-TYPE
    SYNTAX TruthValue
--    Rsyntax INTEGER {
--        true(1),
--        false(2)
--        }
    ACCESS read-only
    STATUS mandatory
    DESCRIPTION
        "This objects indicates whether 802.11n support is
        available on this AP."
    ::= { cLApDot11IfEntry 4 }

cLAp11nChannelBandwidth OBJECT-TYPE
    SYNTAX INTEGER {
        five(1),
        ten(2),
        twenty(3),
        forty(4)
        }
--  Units
--    mhz
    ACCESS read-write
    STATUS mandatory
    DESCRIPTION
        "This object indicates the channel bandwidth for
        this AP. This applies to 802.11n networks only."
    ::= { cLApDot11IfEntry 5 }

cLApLomEnabled OBJECT-TYPE
    SYNTAX TruthValue
--    Rsyntax INTEGER {
--        true(1),
--        false(2)
--        }
    ACCESS read-write
    STATUS deprecated
    DESCRIPTION
        "This object indicates whether this AP is being monitored
        by the location server. A value of 'true' indicates that 
        the monitoring is enabled. A value of 'false' indicates 
        that the monitoring is disabled."
    DEFVAL { false }
    ::= { cLApDot11IfEntry 6 }

cLApLomFirstChannel OBJECT-TYPE
    SYNTAX CLDot11Channel
--    Rsyntax Gauge(1..14|34|36|38|40|42|44|46|48|52|56|60|64|149|153|157|161)
    ACCESS read-write
    STATUS mandatory
    DESCRIPTION
        "This object represents the first location channel that is
        being monitored."
    ::= { cLApDot11IfEntry 7 }

cLApLomSecondChannel OBJECT-TYPE
    SYNTAX CLDot11Channel
--    Rsyntax Gauge(1..14|34|36|38|40|42|44|46|48|52|56|60|64|149|153|157|161)
    ACCESS read-write
    STATUS mandatory
    DESCRIPTION
        "This object represents the second location channel that
        is being monitored."
    ::= { cLApDot11IfEntry 8 }

cLApLomThirdChannel OBJECT-TYPE
    SYNTAX CLDot11Channel
--    Rsyntax Gauge(1..14|34|36|38|40|42|44|46|48|52|56|60|64|149|153|157|161)
    ACCESS read-write
    STATUS mandatory
    DESCRIPTION
        "This object represents the third location
        channel that is being monitored."
    ::= { cLApDot11IfEntry 9 }

cLApLomFourthChannel OBJECT-TYPE
    SYNTAX CLDot11Channel
--    Rsyntax Gauge(1..14|34|36|38|40|42|44|46|48|52|56|60|64|149|153|157|161)
    ACCESS read-write
    STATUS mandatory
    DESCRIPTION
        "This object represents the fourth location
        channel that is being monitored."
    ::= { cLApDot11IfEntry 10 }

cLApExtensionChannel OBJECT-TYPE
    SYNTAX CLDot11Channel
--    Rsyntax Gauge(1..14|34|36|38|40|42|44|46|48|52|56|60|64|149|153|157|161)
    ACCESS read-only
    STATUS mandatory
    DESCRIPTION
        "This object represents the extension channel. This is
        applicable when the channel bandwidth is set to 40mhz."
    ::= { cLApDot11IfEntry 11 }

cLApLegacyBeamForming OBJECT-TYPE
    SYNTAX INTEGER {
        enable(1),
        disable(2),
        notApplicable(3)
        }
    ACCESS read-write
    STATUS mandatory
    DESCRIPTION
        "This object indicates the status of legacy beam forming
        in this AP. This object is applicable only for
        11n supported APs.
        For APs that does not support legacy beam forming,
        a get request on this attribute will return 
        the value 'notApplicable'.
        A value of 'enable' indicates that the legacy
        Beam forming is enabled in this AP. 
        A value of 'false' indicates that the legacy
        Beam forming is disabled in this AP."
    DEFVAL { notApplicable }
    ::= { cLApDot11IfEntry 12 }

cLApCdpOverAirEnabled OBJECT-TYPE
    SYNTAX TruthValue
--    Rsyntax INTEGER {
--        true(1),
--        false(2)
--        }
    ACCESS read-write
    STATUS mandatory
    DESCRIPTION
        "This object indicates the status of Cisco Discovery
        Protocol(CDP) in this interface, represented by
        cLApDot11IfSlotId of the AP, represented by
        cLApSysMacAddress.
        A value of 'true' indicates that CDP is enabled in
        the dot11 interface(s) of this AP.
        A value of 'false' indicates that CDP is disabled in
        the dot11 interface(s) of this AP."
    ::= { cLApDot11IfEntry 13 }

cLApDot11IfAdminStatus OBJECT-TYPE
    SYNTAX TruthValue
--    Rsyntax INTEGER {
--        true(1),
--        false(2)
--        }
    ACCESS read-write
    STATUS mandatory
    DESCRIPTION
        "This object represents the AP's interface admin
        status.
        A value of 'true' indicates admin state as Up.
        A value of 'false' indicates admin state as Down."
    ::= { cLApDot11IfEntry 14 }

cLApEthernetIfTable OBJECT-TYPE
    SYNTAX SEQUENCE OF CLApEthernetIfEntry
    ACCESS not-accessible
    STATUS mandatory
    DESCRIPTION
        "This table represents the information about the
        basic functional parameters corresponding to
        the Ethernet interfaces of the APs that have joined
        the controller."
    ::= { ciscoLwappApIf 2 }

cLApEthernetIfEntry OBJECT-TYPE
    SYNTAX CLApEthernetIfEntry
    ACCESS not-accessible
    STATUS mandatory
    DESCRIPTION
        "An entry in this table represents the functional
        parameters of the Ethernet interface of an AP that
        has joined the controller.
        
        Entries are added when the APs associate to this
        controller and deleted when they lose their
        association."
    INDEX { cLApSysMacAddress, cLApEthernetIfSlotId }
    ::= { cLApEthernetIfTable 1 }

CLApEthernetIfEntry ::= SEQUENCE {
    cLApEthernetIfSlotId Gauge,
    cLApEthernetIfName SnmpAdminString,
    cLApEthernetIfMacAddress MacAddress,
    cLApEthernetIfAdminStatus INTEGER,
    cLApEthernetIfOperStatus INTEGER,
    cLApEthernetIfRxUcastPkts Counter,
    cLApEthernetIfRxNUcastPkts Counter,
    cLApEthernetIfTxUcastPkts Counter,
    cLApEthernetIfTxNUcastPkts Counter,
    cLApEthernetIfDuplex INTEGER,
    cLApEthernetIfLinkSpeed Gauge,
    cLApEthernetIfPOEPower INTEGER,
    cLApEthernetIfRxTotalBytes Counter,
    cLApEthernetIfTxTotalBytes Counter,
    cLApEthernetIfInputCrc Counter,
    cLApEthernetIfInputAborts Counter,
    cLApEthernetIfInputErrors Counter,
    cLApEthernetIfInputFrames Counter,
    cLApEthernetIfInputOverrun Counter,
    cLApEthernetIfInputDrops Counter,
    cLApEthernetIfInputResource Counter,
    cLApEthernetIfUnknownProtocol Counter,
    cLApEthernetIfRunts Counter,
    cLApEthernetIfGiants Counter,
    cLApEthernetIfThrottle Counter,
    cLApEthernetIfResets Counter,
    cLApEthernetIfOutputCollision Counter,
    cLApEthernetIfOutputNoBuffer Counter,
    cLApEthernetIfOutputResource Counter,
    cLApEthernetIfOutputUnderrun Counter,
    cLApEthernetIfOutputErrors Counter,
    cLApEthernetIfOutputTotalDrops Counter,
    cLApEthernetIfCdpEnabled TruthValue
    }

cLApEthernetIfSlotId OBJECT-TYPE
    SYNTAX Gauge
    ACCESS not-accessible
    STATUS mandatory
    DESCRIPTION
        "This object represents the slot ID of an Ethernet
        interface on an AP. 
        
        The slot ID for a particular Ethernet interface as
        represented by this object ranges from 0 to 
        cLApMaxNumberOfEthernetSlots - 1."
    ::= { cLApEthernetIfEntry 1 }

cLApEthernetIfName OBJECT-TYPE
    SYNTAX SnmpAdminString(SIZE(0..32))
--    Rsyntax OCTET STRING(SIZE(0..32))
    ACCESS read-only
    STATUS mandatory
    DESCRIPTION
        "This object represents the name of the
        Ethernet interface."
    ::= { cLApEthernetIfEntry 2 }

cLApEthernetIfMacAddress OBJECT-TYPE
    SYNTAX MacAddress
--    Rsyntax OCTET STRING(SIZE(6))
    ACCESS read-only
    STATUS mandatory
    DESCRIPTION
        "This object represents MAC address of the Ethernet
        interface in the slot represented by 
        cLApEthernetIfSlotId."
    ::= { cLApEthernetIfEntry 3 }

cLApEthernetIfAdminStatus OBJECT-TYPE
    SYNTAX INTEGER {
        up(1),
        down(2)
        }
    ACCESS read-write
    STATUS mandatory
    DESCRIPTION
        "This object represents the admin state of the physical
        Ethernet interface on the AP."
    ::= { cLApEthernetIfEntry 4 }

cLApEthernetIfOperStatus OBJECT-TYPE
    SYNTAX INTEGER {
        up(1),
        down(2)
        }
    ACCESS read-only
    STATUS mandatory
    DESCRIPTION
        "This object represents the operational state
        of the physical Ethernet interface on the AP."
    ::= { cLApEthernetIfEntry 5 }

cLApEthernetIfRxUcastPkts OBJECT-TYPE
    SYNTAX Counter
--  Units
--    packets
    ACCESS read-only
    STATUS mandatory
    DESCRIPTION
        "This object represents total number of unicast packets
        received on the interface."
    ::= { cLApEthernetIfEntry 6 }

cLApEthernetIfRxNUcastPkts OBJECT-TYPE
    SYNTAX Counter
--  Units
--    packets
    ACCESS read-only
    STATUS mandatory
    DESCRIPTION
        "This object represents total number of non-unicast or
        multicast packets received on the interface"
    ::= { cLApEthernetIfEntry 7 }

cLApEthernetIfTxUcastPkts OBJECT-TYPE
    SYNTAX Counter
--  Units
--    packets
    ACCESS read-only
    STATUS mandatory
    DESCRIPTION
        "This object represents total number of unicast packets
        transmitted on the interface."
    ::= { cLApEthernetIfEntry 8 }

cLApEthernetIfTxNUcastPkts OBJECT-TYPE
    SYNTAX Counter
--  Units
--    packets
    ACCESS read-only
    STATUS mandatory
    DESCRIPTION
        "This object represents total number of non-unicast or
        multicast packets transmitted on the interface"
    ::= { cLApEthernetIfEntry 9 }

cLApEthernetIfDuplex OBJECT-TYPE
    SYNTAX INTEGER {
        unknown(1),
        halfduplex(2),
        fullduplex(3),
        auto(4)
        }
    ACCESS read-only
    STATUS mandatory
    DESCRIPTION
        "This object represents interface's duplex mode"
    ::= { cLApEthernetIfEntry 10 }

cLApEthernetIfLinkSpeed OBJECT-TYPE
    SYNTAX Gauge
    ACCESS read-only
    STATUS mandatory
    DESCRIPTION
        "Speed of the interface in units of 1,000,000
        bits per second"
    ::= { cLApEthernetIfEntry 11 }

cLApEthernetIfPOEPower OBJECT-TYPE
    SYNTAX INTEGER {
        none(1),
        drawn(2),
        notdrawn(3)
        }
    ACCESS read-only
    STATUS mandatory
    DESCRIPTION
        "This object represents whether this interface supports
        Power Over Ethernet (POE)
        none     - POE is not supported
        drawn    - This interface supports POE, and power is
                   being drawn
        notdrawn - POE power is not drawn"
    ::= { cLApEthernetIfEntry 12 }

cLApEthernetIfRxTotalBytes OBJECT-TYPE
    SYNTAX Counter
--  Units
--    Bytes
    ACCESS read-only
    STATUS mandatory
    DESCRIPTION
        "This object represents total number of bytes in the
        error-free packets received on the interface."
    ::= { cLApEthernetIfEntry 13 }

cLApEthernetIfTxTotalBytes OBJECT-TYPE
    SYNTAX Counter
--  Units
--    Bytes
    ACCESS read-only
    STATUS mandatory
    DESCRIPTION
        "This object represents total number of bytes in the
        error-free packets transmitted on the interface."
    ::= { cLApEthernetIfEntry 14 }

cLApEthernetIfInputCrc OBJECT-TYPE
    SYNTAX Counter
--  Units
--    packets
    ACCESS read-only
    STATUS mandatory
    DESCRIPTION
        "This object represents total number of CRC error in
        packets received on the interface."
    ::= { cLApEthernetIfEntry 15 }

cLApEthernetIfInputAborts OBJECT-TYPE
    SYNTAX Counter
--  Units
--    packets
    ACCESS read-only
    STATUS mandatory
    DESCRIPTION
        "This object represents total number of packet aborted
        while receiving on the interface."
    ::= { cLApEthernetIfEntry 16 }

cLApEthernetIfInputErrors OBJECT-TYPE
    SYNTAX Counter
--  Units
--    packets
    ACCESS read-only
    STATUS mandatory
    DESCRIPTION
        "This object represents sum of all errors in the packets
        while receiving on the interface."
    ::= { cLApEthernetIfEntry 17 }

cLApEthernetIfInputFrames OBJECT-TYPE
    SYNTAX Counter
--  Units
--    packets
    ACCESS read-only
    STATUS mandatory
    DESCRIPTION
        "This object represents total number of packet received
        incorrectly having a CRC error and a noninteger number 
        of octets on the interface."
    ::= { cLApEthernetIfEntry 18 }

cLApEthernetIfInputOverrun OBJECT-TYPE
    SYNTAX Counter
--  Units
--    packets
    ACCESS read-only
    STATUS mandatory
    DESCRIPTION
        "This object represents the number of times the receiver
        hardware was incapable of handing received data to a 
        hardware buffer because the input rate exceeded the 
        receiver's capability to handle the data."
    ::= { cLApEthernetIfEntry 19 }

cLApEthernetIfInputDrops OBJECT-TYPE
    SYNTAX Counter
--  Units
--    packets
    ACCESS read-only
    STATUS mandatory
    DESCRIPTION
        "This object represents total number of packets dropped
        while receiving on the interface because the queue 
        was full."
    ::= { cLApEthernetIfEntry 20 }

cLApEthernetIfInputResource OBJECT-TYPE
    SYNTAX Counter
--  Units
--    packets
    ACCESS read-only
    STATUS mandatory
    DESCRIPTION
        "This object represents total number of resource errors in
        packets received on the interface."
    ::= { cLApEthernetIfEntry 21 }

cLApEthernetIfUnknownProtocol OBJECT-TYPE
    SYNTAX Counter
--  Units
--    packets
    ACCESS read-only
    STATUS mandatory
    DESCRIPTION
        "This object represents total number of packet discarded on
        the interface due to unknown protocol."
    ::= { cLApEthernetIfEntry 22 }

cLApEthernetIfRunts OBJECT-TYPE
    SYNTAX Counter
--  Units
--    packets
    ACCESS read-only
    STATUS mandatory
    DESCRIPTION
        "This object represents number of packets that
        are discarded because they are smaller than the 
        medium's minimum packet size."
    ::= { cLApEthernetIfEntry 23 }

cLApEthernetIfGiants OBJECT-TYPE
    SYNTAX Counter
--  Units
--    packets
    ACCESS read-only
    STATUS mandatory
    DESCRIPTION
        "This object represents number of packets that
        are discarded because they exceed the medium's 
        maximum packet size."
    ::= { cLApEthernetIfEntry 24 }

cLApEthernetIfThrottle OBJECT-TYPE
    SYNTAX Counter
    ACCESS read-only
    STATUS mandatory
    DESCRIPTION
        "This object represents total number of times the
        interface advised a sending NIC that it was 
        overwhelmed by packets being sent and to slow the 
        pace of delivery."
    ::= { cLApEthernetIfEntry 25 }

cLApEthernetIfResets OBJECT-TYPE
    SYNTAX Counter
    ACCESS read-only
    STATUS mandatory
    DESCRIPTION
        "This object represents number of times that an
        interface has been completely reset."
    ::= { cLApEthernetIfEntry 26 }

cLApEthernetIfOutputCollision OBJECT-TYPE
    SYNTAX Counter
--  Units
--    packets
    ACCESS read-only
    STATUS mandatory
    DESCRIPTION
        "This object represents total number of packet
        retransmitted due to an Ethernet collision."
    ::= { cLApEthernetIfEntry 27 }

cLApEthernetIfOutputNoBuffer OBJECT-TYPE
    SYNTAX Counter
--  Units
--    packets
    ACCESS read-only
    STATUS mandatory
    DESCRIPTION
        "This object represents total number of packets discarded
        because there was no buffer space."
    ::= { cLApEthernetIfEntry 28 }

cLApEthernetIfOutputResource OBJECT-TYPE
    SYNTAX Counter
--  Units
--    packets
    ACCESS read-only
    STATUS mandatory
    DESCRIPTION
        "This object represents total number of resource
        errors in packets transmitted on the interface."
    ::= { cLApEthernetIfEntry 29 }

cLApEthernetIfOutputUnderrun OBJECT-TYPE
    SYNTAX Counter
--  Units
--    packets
    ACCESS read-only
    STATUS mandatory
    DESCRIPTION
        "This object represents the number of times the transmitter
        has been running faster than the router can handle."
    ::= { cLApEthernetIfEntry 30 }

cLApEthernetIfOutputErrors OBJECT-TYPE
    SYNTAX Counter
--  Units
--    packets
    ACCESS read-only
    STATUS mandatory
    DESCRIPTION
        "This object represents sum of all errors that prevented
        the final transmission of packets out of the interface."
    ::= { cLApEthernetIfEntry 31 }

cLApEthernetIfOutputTotalDrops OBJECT-TYPE
    SYNTAX Counter
--  Units
--    packets
    ACCESS read-only
    STATUS mandatory
    DESCRIPTION
        "This object represents total number of packets dropped
        while transmitting from the interface because the queue 
        was full."
    ::= { cLApEthernetIfEntry 32 }

cLApEthernetIfCdpEnabled OBJECT-TYPE
    SYNTAX TruthValue
--    Rsyntax INTEGER {
--        true(1),
--        false(2)
--        }
    ACCESS read-write
    STATUS mandatory
    DESCRIPTION
        "This object indicates the status of Cisco Discovery
        Protocol(CDP) in this interface represented by
        cLApEthernetIfSlotId of the AP represented by
        cLApSysMacAddress.
        A value of 'true' indicates that CDP is enabled in
        this interface.
        A value of 'false' indicates that CDP is disabled in
        this interface."
    DEFVAL { true }
    ::= { cLApEthernetIfEntry 33 }

cLApDot11RadioTable OBJECT-TYPE
    SYNTAX SEQUENCE OF CLApDot11RadioEntry
    ACCESS not-accessible
    STATUS mandatory
    DESCRIPTION
        "This table represents the information about the
        basic functional parameters of the radios of the 
        APs that have joined the controller."
    ::= { ciscoLwappApIf 3 }

cLApDot11RadioEntry OBJECT-TYPE
    SYNTAX CLApDot11RadioEntry
    ACCESS not-accessible
    STATUS mandatory
    DESCRIPTION
        "An entry in this table represents the 802.11
        functional parameters of the radio of
        an AP that has joined the controller.
        
        Entries are added when the APs associate to this
        controller and deleted when they lose their
        association."
    INDEX { cLApSysMacAddress, cLApDot11IfSlotId }
    ::= { cLApDot11RadioTable 1 }

CLApDot11RadioEntry ::= SEQUENCE {
    cLApDot11RadioMACAddress MacAddress,
    cLApDot11RadioSubBand CLApDot11RadioSubband,
    cLApDot11RadioVersion DisplayString,
    cLApDot11IsBackhaul TruthValue,
    cLApDot11RadioRole CLApDot11RadioRole
    }

cLApDot11RadioMACAddress OBJECT-TYPE
    SYNTAX MacAddress
--    Rsyntax OCTET STRING(SIZE(6))
    ACCESS read-only
    STATUS mandatory
    DESCRIPTION
        "This object represents the base Mac address of
        the radio."
    ::= { cLApDot11RadioEntry 1 }

cLApDot11RadioSubBand OBJECT-TYPE
    SYNTAX CLApDot11RadioSubband
--    Rsyntax INTEGER {
--        all(1),
--        sub49(2),
--        sub52(3),
--        sub54(4),
--        sub58(5)
--        }
    ACCESS read-only
    STATUS mandatory
    DESCRIPTION
        "This object indicates the sub band on which
        this radio operates."
    ::= { cLApDot11RadioEntry 2 }

cLApDot11RadioVersion OBJECT-TYPE
    SYNTAX DisplayString(SIZE(1..50))
--    Rsyntax OCTET STRING(SIZE(1..50))
    ACCESS read-only
    STATUS mandatory
    DESCRIPTION
        "This attribute identifies firmware version
        of the radio."
    ::= { cLApDot11RadioEntry 3 }

cLApDot11IsBackhaul OBJECT-TYPE
    SYNTAX TruthValue
--    Rsyntax INTEGER {
--        true(1),
--        false(2)
--        }
    ACCESS read-only
    STATUS mandatory
    DESCRIPTION
        "This object represents whether this interface
        is backhaul radio or not."
    ::= { cLApDot11RadioEntry 4 }

cLApDot11RadioRole OBJECT-TYPE
    SYNTAX CLApDot11RadioRole
--    Rsyntax INTEGER {
--        ?? enum value of zero may cause problems
--        shutdown(0),
--        upDownlink(1),
--        uplink(2),
--        downlink(3),
--        access(4),
--        uplinkAccess(5),
--        downlinkAccess(6),
--        upDownlinkAccess(7),
--        unknown(8)
--        }
    ACCESS read-only
    STATUS mandatory
    DESCRIPTION
        "This attribute identifies role of the radio."
    ::= { cLApDot11RadioEntry 5 }

cLApCredentialGlobalUserName OBJECT-TYPE
    SYNTAX SnmpAdminString
--    Rsyntax OCTET STRING(SIZE(0..255))
    ACCESS read-write
    STATUS mandatory
    DESCRIPTION
        "This object represents the global username for
        all the APs already joined or will join the controller.
        This user name is used to access the console on the AP."
    ::= { ciscoLwappApCredentials 1 }

cLApCredentialGlobalPassword OBJECT-TYPE
    SYNTAX SnmpAdminString
--    Rsyntax OCTET STRING(SIZE(0..255))
    ACCESS read-write
    STATUS mandatory
    DESCRIPTION
        "This object represents the password corresponding to
        the user name represented by cLApCredentialGlobalUserName
        object."
    ::= { ciscoLwappApCredentials 2 }

cLApCredentialGlobalSecret OBJECT-TYPE
    SYNTAX SnmpAdminString
--    Rsyntax OCTET STRING(SIZE(0..255))
    ACCESS read-write
    STATUS mandatory
    DESCRIPTION
        "This object represents the secret key for
        all the APs already joined or will join the 
        controller. This provides read-write access 
        to the console on the AP."
    ::= { ciscoLwappApCredentials 3 }

cLApCredentialsTable OBJECT-TYPE
    SYNTAX SEQUENCE OF CLApCredentialsEntry
    ACCESS not-accessible
    STATUS mandatory
    DESCRIPTION
        "This table provides the information about the credentials
        of the 802.11 LWAPP Access Points that have joined the 
        controller. Rows are added to this table whenever, new APs 
        are joined to this controller, and rows are deleted 
        whenever APs gets disjoined from the controller."
    ::= { ciscoLwappApCredentials 4 }

cLApCredentialsEntry OBJECT-TYPE
    SYNTAX CLApCredentialsEntry
    ACCESS not-accessible
    STATUS mandatory
    DESCRIPTION
        "Each entry in this table provides information about
        one 802.11 LWAPP Access Point that has joined the
        controller. cLApSysMacAddress is the index which
        uniquely identifies every row in the table."
    INDEX { cLApSysMacAddress }
    ::= { cLApCredentialsTable 1 }

CLApCredentialsEntry ::= SEQUENCE {
    cLApCredentialUserName SnmpAdminString,
    cLApCredentialPassword SnmpAdminString,
    cLApCredentialSecret SnmpAdminString,
    cLApCredentialEnableGlobalCredentials TruthValue
    }

cLApCredentialUserName OBJECT-TYPE
    SYNTAX SnmpAdminString
--    Rsyntax OCTET STRING(SIZE(0..255))
    ACCESS read-write
    STATUS mandatory
    DESCRIPTION
        "This object represents the username for
        this AP."
    ::= { cLApCredentialsEntry 1 }

cLApCredentialPassword OBJECT-TYPE
    SYNTAX SnmpAdminString
--    Rsyntax OCTET STRING(SIZE(0..255))
    ACCESS read-write
    STATUS mandatory
    DESCRIPTION
        "This object represents the password corresponding to
        user name represented by cLApCredentialUserName object."
    ::= { cLApCredentialsEntry 2 }

cLApCredentialSecret OBJECT-TYPE
    SYNTAX SnmpAdminString
--    Rsyntax OCTET STRING(SIZE(0..255))
    ACCESS read-write
    STATUS mandatory
    DESCRIPTION
        "This object represents the secret key for
        the specific AP. This provides the read-write access
        on the console for this AP."
    ::= { cLApCredentialsEntry 3 }

cLApCredentialEnableGlobalCredentials OBJECT-TYPE
    SYNTAX TruthValue
--    Rsyntax INTEGER {
--        true(1),
--        false(2)
--        }
    ACCESS read-write
    STATUS mandatory
    DESCRIPTION
        "This object  specifies whether the global credentials
        for the AP is enabled or disabled.
        
        A value of 'true' enables the global username/password
        to be used for this AP and 'false' disables the global
        credentials and uses the credentials specific for this
        AP."
    ::= { cLApCredentialsEntry 4 }

cLApLinkLatencyTable OBJECT-TYPE
    SYNTAX SEQUENCE OF CLApLinkLatencyEntry
    ACCESS not-accessible
    STATUS mandatory
    DESCRIPTION
        "This table represents the link latency configuration
        for each AP. 
        An entry is automatically added to this table when 
        an Access Points Joins controller. 
        Entry is removed from this table when AP 
        disassociates from the controllers."
    ::= { ciscoLwappLinkLatency 1 }

cLApLinkLatencyEntry OBJECT-TYPE
    SYNTAX CLApLinkLatencyEntry
    ACCESS not-accessible
    STATUS mandatory
    DESCRIPTION
        "Each entry in this table provides configuration
        related to Link latency on each AP."
    INDEX { cLApSysMacAddress }
    ::= { cLApLinkLatencyTable 1 }

CLApLinkLatencyEntry ::= SEQUENCE {
    cLApLinkLatencyEnable TruthValue,
    cLApLinkLatencyReset TruthValue
    }

cLApLinkLatencyEnable OBJECT-TYPE
    SYNTAX TruthValue
--    Rsyntax INTEGER {
--        true(1),
--        false(2)
--        }
    ACCESS read-write
    STATUS mandatory
    DESCRIPTION
        "This object can be used to configure the Link
        Latency on the AP.             
        A value of 'true' indicates that the Link Latency
        is enabled.
        A value of 'false' indicates that the Link Latency 
        is disabled."
    DEFVAL { false }
    ::= { cLApLinkLatencyEntry 1 }

cLApLinkLatencyReset OBJECT-TYPE
    SYNTAX TruthValue
--    Rsyntax INTEGER {
--        true(1),
--        false(2)
--        }
    ACCESS read-write
    STATUS mandatory
    DESCRIPTION
        "This object can be used to reset the Link Latency
        stored at controller for an AP.             
        A value of true indicates that the Link Latency stats 
        is to be reset.
        A value of false on this during set will return error.
        A value of false will be returned on get."
    DEFVAL { false }
    ::= { cLApLinkLatencyEntry 2 }

cLApLinkLatencyStatsTable OBJECT-TYPE
    SYNTAX SEQUENCE OF CLApLinkLatencyStatsEntry
    ACCESS not-accessible
    STATUS mandatory
    DESCRIPTION
        "This table represents the link latency statistics
        calculated for each AP. 
        An entry is automatically added by the controller
        when a 'cLApLinkLatencyEnable' is enabled on an 
        Access Point. Entry is deleted when 
        'cLApLinkLatencyEnable' is disabled on the 
        Access Point."
    ::= { ciscoLwappLinkLatency 2 }

cLApLinkLatencyStatsEntry OBJECT-TYPE
    SYNTAX CLApLinkLatencyStatsEntry
    ACCESS not-accessible
    STATUS mandatory
    DESCRIPTION
        "Each entry in this table provides minimum, maximum
        and average Link latency for a Access Point. 
        Entries are removed when the Link Latency is disabled 
        on a Access Point."
    INDEX { cLApSysMacAddress }
    ::= { cLApLinkLatencyStatsTable 1 }

CLApLinkLatencyStatsEntry ::= SEQUENCE {
    cLApLinkLatencyStatsCurrent TimeInterval,
    cLApLinkLatencyStatsMin TimeInterval,
    cLApLinkLatencyStatsMax TimeInterval,
    cLApLinkLatencyTimeStamp TimeStamp,
    cLApDataLinkLatencyStatsCurrent TimeInterval,
    cLApDataLinkLatencyStatsMin TimeInterval,
    cLApDataLinkLatencyStatsMax TimeInterval,
    cLApDataLinkLatencyTimeStamp TimeStamp
    }

cLApLinkLatencyStatsCurrent OBJECT-TYPE
    SYNTAX TimeInterval
--    Rsyntax INTEGER(0..2147483647)
--  Units
--    milliseconds
    ACCESS read-only
    STATUS mandatory
    DESCRIPTION
        "This object represent the current Link latency recorded for
        this Access point."
    ::= { cLApLinkLatencyStatsEntry 1 }

cLApLinkLatencyStatsMin OBJECT-TYPE
    SYNTAX TimeInterval
--    Rsyntax INTEGER(0..2147483647)
--  Units
--    milliseconds
    ACCESS read-only
    STATUS mandatory
    DESCRIPTION
        "This object represent the minimum Link latency recorded for
        this Access point."
    ::= { cLApLinkLatencyStatsEntry 2 }

cLApLinkLatencyStatsMax OBJECT-TYPE
    SYNTAX TimeInterval
--    Rsyntax INTEGER(0..2147483647)
--  Units
--    milliseconds
    ACCESS read-only
    STATUS mandatory
    DESCRIPTION
        "This object represent the maximum Link latency recorded for
        this Access point."
    ::= { cLApLinkLatencyStatsEntry 3 }

cLApLinkLatencyTimeStamp OBJECT-TYPE
    SYNTAX TimeStamp
--    Rsyntax TimeTicks
--  Units
--    seconds
    ACCESS read-only
    STATUS mandatory
    DESCRIPTION
        "This object represents the timestamp, when the values are
        collected, as returned by the object 'cLApUpTime'."
    ::= { cLApLinkLatencyStatsEntry 4 }

cLApDataLinkLatencyStatsCurrent OBJECT-TYPE
    SYNTAX TimeInterval
--    Rsyntax INTEGER(0..2147483647)
--  Units
--    milliseconds
    ACCESS read-only
    STATUS mandatory
    DESCRIPTION
        "This object represent the current Data Link latency recorded
        for this Access point."
    ::= { cLApLinkLatencyStatsEntry 5 }

cLApDataLinkLatencyStatsMin OBJECT-TYPE
    SYNTAX TimeInterval
--    Rsyntax INTEGER(0..2147483647)
--  Units
--    milliseconds
    ACCESS read-only
    STATUS mandatory
    DESCRIPTION
        "This object represent the minimum Data Link latency recorded
        for this Access point."
    ::= { cLApLinkLatencyStatsEntry 6 }

cLApDataLinkLatencyStatsMax OBJECT-TYPE
    SYNTAX TimeInterval
--    Rsyntax INTEGER(0..2147483647)
--  Units
--    milliseconds
    ACCESS read-only
    STATUS mandatory
    DESCRIPTION
        "This object represent the maximum Data Link latency recorded
        for this Access point."
    ::= { cLApLinkLatencyStatsEntry 7 }

cLApDataLinkLatencyTimeStamp OBJECT-TYPE
    SYNTAX TimeStamp
--    Rsyntax TimeTicks
--  Units
--    seconds
    ACCESS read-only
    STATUS mandatory
    DESCRIPTION
        "This object represents the timestamp, when the values are
        collected, as returned by the object 'cLApUpTime'."
    ::= { cLApLinkLatencyStatsEntry 8 }

cLApIfSmtParamTable OBJECT-TYPE
    SYNTAX SEQUENCE OF CLApIfSmtParamEntry
    ACCESS not-accessible
    STATUS mandatory
    DESCRIPTION
        "This table represents the station management
        information in the APs that have joined the
        controller.  Information populated through the
        entries of this table is used by the AP to
        perform the expected 802.11 operations on
        the respective dot11 interfaces to coordinate with
        other 802.11 devices in the network.
        
        Since this table has the indices defined in the
        tables cLApTable and cLApDot11IfTable, an entry in
        this table is automatically removed when the
        respective entry is removed in either of those
        tables."
    ::= { ciscoLwappAp 2 }

cLApIfSmtParamEntry OBJECT-TYPE
    SYNTAX CLApIfSmtParamEntry
    ACCESS not-accessible
    STATUS mandatory
    DESCRIPTION
        "An entry in this table represents the information
        pertaining to one particular dot11 interface of
        this AP used to perform the 802.11 protocol
        operations on the respective dot11 interface.
        
        Rows are added or deleted to this table when
        APs join or leave the controller respectively."
    INDEX { cLApSysMacAddress, cLApDot11IfSlotId }
    ::= { cLApIfSmtParamTable 1 }

CLApIfSmtParamEntry ::= SEQUENCE {
    cLApIfSmtDot11Bssid MacAddress
    }

cLApIfSmtDot11Bssid OBJECT-TYPE
    SYNTAX MacAddress
--    Rsyntax OCTET STRING(SIZE(6))
    ACCESS read-only
    STATUS mandatory
    DESCRIPTION
        "This object defines the base BSSID of this AP, which
        is the MAC address of the radio interface of this
        AP."
    ::= { cLApIfSmtParamEntry 1 }

cLApCountryTable OBJECT-TYPE
    SYNTAX SEQUENCE OF CLApCountryEntry
    ACCESS not-accessible
    STATUS mandatory
    DESCRIPTION
        "This table represents the country settings for
        the 802.11 LWAPP Access Points that have joined the
        controller.
        An entry is automatically added by the controller 
        when a Access Point joins the controller. 
        The entry is removed when Access Point disasscociates 
        from the controller."
    ::= { ciscoLwappAp 3 }

cLApCountryEntry OBJECT-TYPE
    SYNTAX CLApCountryEntry
    ACCESS not-accessible
    STATUS mandatory
    DESCRIPTION
        "Each entry in this table provides country setting
        about one 802.11 LWAPP Access Point that has joined 
        the controller.
        Entries are removed when the APs lose their
        association with the controller due to loss
        of communication."
    INDEX { cLApSysMacAddress }
    ::= { cLApCountryTable 1 }

CLApCountryEntry ::= SEQUENCE {
    cLApCountryCode DisplayString,
    cLApCountryAllowed DisplayString
    }

cLApCountryCode OBJECT-TYPE
    SYNTAX DisplayString(SIZE(1..255))
--    Rsyntax OCTET STRING(SIZE(1..255))
    ACCESS read-write
    STATUS mandatory
    DESCRIPTION
        "This attribute identifies the country in which the
        AP is operating. This value is the 3 letter country  
        code."
    ::= { cLApCountryEntry 1 }

cLApCountryAllowed OBJECT-TYPE
    SYNTAX DisplayString(SIZE(1..255))
--    Rsyntax OCTET STRING(SIZE(1..255))
    ACCESS read-only
    STATUS mandatory
    DESCRIPTION
        "This attribute identifies the country in which the
        AP is operating. This value is a list of country  
        codes sperated by comma."
    ::= { cLApCountryEntry 2 }

ciscoLwappApIfRegulatoryDomainMismatchNotifEnabled OBJECT-TYPE
    SYNTAX TruthValue
--    Rsyntax INTEGER {
--        true(1),
--        false(2)
--        }
    ACCESS read-write
    STATUS mandatory
    DESCRIPTION
        "The object to control the generation of
        ciscoLwappApIfRegulatoryDomainMismatchNotif 
        notification.
        
        A value of 'true' indicates that the agent 
        generates ciscoLwappApIfRegulatoryDomainMismatchNotif 
        notification.
        
        A value of 'false' indicates that the agent doesn't
        generate ciscoLwappApIfRegulatoryDomainMismatchNotif
        notification."
    DEFVAL { true }
    ::= { ciscoLwappAp 4 }

ciscoLwappApCrashEnabled OBJECT-TYPE
    SYNTAX TruthValue
--    Rsyntax INTEGER {
--        true(1),
--        false(2)
--        }
    ACCESS read-write
    STATUS mandatory
    DESCRIPTION
        "The object to control the generation of
        ciscoLwappApCrash notification.
        
        A value of 'true' indicates that the agent generates
        ciscoLwappApCrash notification.
        
        A value of 'false' indicates that the agent doesn't
        generate ciscoLwappApCrash notification."
    DEFVAL { true }
    ::= { ciscoLwappAp 5 }

ciscoLwappApUnsupportedEnabled OBJECT-TYPE
    SYNTAX TruthValue
--    Rsyntax INTEGER {
--        true(1),
--        false(2)
--        }
    ACCESS read-write
    STATUS mandatory
    DESCRIPTION
        "The object to control the generation of
        ciscoLwappApUnsupported notification.
        
        A value of 'true' indicates that the agent generates
        ciscoLwappApUnsupported notification.
        
        A value of 'false' indicates that the agent doesn't
        generate ciscoLwappApUnsupported
        notification."
    DEFVAL { true }
    ::= { ciscoLwappAp 6 }

ciscoLwappApAssociatedEnabled OBJECT-TYPE
    SYNTAX TruthValue
--    Rsyntax INTEGER {
--        true(1),
--        false(2)
--        }
    ACCESS read-write
    STATUS mandatory
    DESCRIPTION
        "The object to control the generation of
        ciscoLwappApAssociated notification.
        
        A value of 'true' indicates that the agent generates
        ciscoLwappApAssociated notification.
        
        A value of 'false' indicates that the agent doesn't
        generate ciscoLwappApAssociated notification."
    DEFVAL { true }
    ::= { ciscoLwappAp 7 }

cLApSeClientTable OBJECT-TYPE
    SYNTAX SEQUENCE OF CLApSeClientEntry
    ACCESS not-accessible
    STATUS mandatory
    DESCRIPTION
        "This table represents the information about the
        details of Spectrum Expert client connected to 
        radio interface of APs"
    ::= { ciscoLwappApMIBObjects 8 }

cLApSeClientEntry OBJECT-TYPE
    SYNTAX CLApSeClientEntry
    ACCESS not-accessible
    STATUS mandatory
    DESCRIPTION
        "An entry in this table represents the details of
        Spectrum Expert client connected to APs"
    INDEX { cLApSysMacAddress, cLApDot11IfSlotId, cLApSeIndex }
    ::= { cLApSeClientTable 1 }

CLApSeClientEntry ::= SEQUENCE {
    cLApSeIndex INTEGER,
    cLApSeClientUserName SnmpAdminString,
    cLApSeClientIPAddrType InetAddressType,
    cLApSeClientIPAddr InetAddress,
    cLApSeClientDuration TimeInterval,
    cLApSeClientPort InetPortNumber
    }

cLApSeIndex OBJECT-TYPE
    SYNTAX INTEGER(0..2147483647)
    ACCESS not-accessible
    STATUS mandatory
    DESCRIPTION
        "This object indicates the index of the client
        running the Spectrum Expert instance."
    ::= { cLApSeClientEntry 1 }

cLApSeClientUserName OBJECT-TYPE
    SYNTAX SnmpAdminString
--    Rsyntax OCTET STRING(SIZE(0..255))
    ACCESS read-only
    STATUS mandatory
    DESCRIPTION
        "This object indicates the name of the
        client running the Spectrum Expert application"
    ::= { cLApSeClientEntry 2 }

cLApSeClientIPAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "This object indicates the client IP address type,
        that runs the SE application, made available 
        through cLApSeClientIPAddr"
    ::= { cLApSeClientEntry 3 }

cLApSeClientIPAddr OBJECT-TYPE
    SYNTAX InetAddress
--    Rsyntax OCTET STRING(SIZE(0..255))
    ACCESS read-only
    STATUS mandatory
    DESCRIPTION
        "This object indicates the client IP address,
        that runs the SE application"
    ::= { cLApSeClientEntry 4 }

cLApSeClientDuration OBJECT-TYPE
    SYNTAX TimeInterval
--    Rsyntax INTEGER(0..2147483647)
    ACCESS read-only
    STATUS mandatory
    DESCRIPTION
        "This object indicates the duration for which the SE client
        application has been up and running"
    ::= { cLApSeClientEntry 5 }

cLApSeClientPort OBJECT-TYPE
    SYNTAX InetPortNumber
--    Rsyntax Gauge(0..65535)
    ACCESS read-only
    STATUS mandatory
    DESCRIPTION
        "This object indicates the port from which the SE client
        application is running"
    ::= { cLApSeClientEntry 6 }

cLApFastHbTimerTable OBJECT-TYPE
    SYNTAX SEQUENCE OF CLApFastHbTimerEntry
    ACCESS not-accessible
    STATUS mandatory
    DESCRIPTION
        "This table contains entries for AP fast heartbeat
        timers configured in the controller. At startup,
        all the entries in this table are set up by the central
        controller.  A management application can later change
        the values in this table."
    ::= { ciscoLwappApGlobal 1 }

cLApFastHbTimerEntry OBJECT-TYPE
    SYNTAX CLApFastHbTimerEntry
    ACCESS not-accessible
    STATUS mandatory
    DESCRIPTION
        "A conceptual row in cLApFastHbTimerTable. There is an entry
        in this table for each AP type, as identified by a value of
        cLApFastHbTimerApType."
    INDEX { cLApFastHbTimerApType }
    ::= { cLApFastHbTimerTable 1 }

CLApFastHbTimerEntry ::= SEQUENCE {
    cLApFastHbTimerApType INTEGER,
    cLApFastHbTimerTimeout Gauge,
    cLApFastHbTimerEnabled TruthValue
    }

cLApFastHbTimerApType OBJECT-TYPE
    SYNTAX INTEGER {
        local(1),
        hreap(2)
        }
    ACCESS not-accessible
    STATUS mandatory
    DESCRIPTION
        "This object represents the AP type for this entry.
        local      - indicates that timer is for local mode APs
        hreap      - indicates that timer is for HREAP APs"
    ::= { cLApFastHbTimerEntry 1 }

cLApFastHbTimerTimeout OBJECT-TYPE
    SYNTAX Gauge(1..15)
--  Units
--    seconds
    ACCESS read-write
    STATUS mandatory
    DESCRIPTION
        "This object represents the timeout value for the heart
        beat timer. This value changes to 0 when
        cLApFastHbTimerEnabled is set to 'false'."
    ::= { cLApFastHbTimerEntry 2 }

cLApFastHbTimerEnabled OBJECT-TYPE
    SYNTAX TruthValue
--    Rsyntax INTEGER {
--        true(1),
--        false(2)
--        }
    ACCESS read-write
    STATUS mandatory
    DESCRIPTION
        "This object controls the Heartbeat Timer. A value of 'true'
        indicates that this timer is enabled. A value of 'false'
        indicates that this timer is disabled."
    ::= { cLApFastHbTimerEntry 3 }

cLApPrimaryDiscoveryTimeout OBJECT-TYPE
    SYNTAX Gauge(30..3600)
--  Units
--    seconds
    ACCESS read-write
    STATUS mandatory
    DESCRIPTION
        "This object represents the timeout for the primary AP
        discovery."
    DEFVAL { 120 }
    ::= { ciscoLwappApGlobal 3 }

cLApGlobalPrimaryControllerAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object represents the type of the primary controller's
        address made available through cLApPrimaryControllerAddress."
    ::= { ciscoLwappApGlobal 4 }

cLApGlobalPrimaryControllerAddress OBJECT-TYPE
    SYNTAX InetAddress
--    Rsyntax OCTET STRING(SIZE(0..255))
    ACCESS read-write
    STATUS mandatory
    DESCRIPTION
        "This object represents the address of the primary controller
        that the APs will join. The name and address should be 
        provided in the same set request. An address of all zeros 
        will unset the primary controller."
    ::= { ciscoLwappApGlobal 5 }

cLApGlobalPrimaryControllerName OBJECT-TYPE
    SYNTAX SnmpAdminString(SIZE(0..32))
--    Rsyntax OCTET STRING(SIZE(0..32))
    ACCESS read-write
    STATUS mandatory
    DESCRIPTION
        "This object represents the name of the primary controller
        that the APs will join."
    ::= { ciscoLwappApGlobal 6 }

cLApGlobalSecondaryControllerAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object represents the type of the secondary
        controller's address made available through 
        cLApSecondaryControllerAddress."
    ::= { ciscoLwappApGlobal 7 }

cLApGlobalSecondaryControllerAddress OBJECT-TYPE
    SYNTAX InetAddress
--    Rsyntax OCTET STRING(SIZE(0..255))
    ACCESS read-write
    STATUS mandatory
    DESCRIPTION
        "This object represents the address of the secondary
        controller that the APs will join. The name and address 
        should be provided in the same set request. An address 
        of all zeros will unset the secondary controller."
    ::= { ciscoLwappApGlobal 8 }

cLApGlobalSecondaryControllerName OBJECT-TYPE
    SYNTAX SnmpAdminString(SIZE(0..32))
--    Rsyntax OCTET STRING(SIZE(0..32))
    ACCESS read-write
    STATUS mandatory
    DESCRIPTION
        "This object represents the name of the secondary controller
        that the APs will join."
    ::= { ciscoLwappApGlobal 9 }

cLApGlobalFailoverPriority OBJECT-TYPE
    SYNTAX TruthValue
--    Rsyntax INTEGER {
--        true(1),
--        false(2)
--        }
    ACCESS read-write
    STATUS mandatory
    DESCRIPTION
        "This object represents the Global AP Failover priority.
        If Enabled, Priorities will be considered of the APs which 
        wishes to join the controller. Preference will be given to 
        the higher priority AP. If the number of associated AP has 
        already reached the limit then the controller will 
        disassociate a lower priority AP to accomodate a higher 
        priority AP. 
            Default is Disabled state."
    DEFVAL { false }
    ::= { ciscoLwappApGlobal 10 }

cLApGlobalTcpMss OBJECT-TYPE
    SYNTAX INTEGER(0|536..1363)
    ACCESS read-write
    STATUS mandatory
    DESCRIPTION
        "This object represents the Global AP TCP MSS value.
        Permissible value are between 536 and 1363. This will
        also enable the global TCP MSS flag.
        Value of 0 will disable the global TCP MSS flag.
        Any change of value for this object will be reflected
        to cLApTcpMss"
    ::= { ciscoLwappApGlobal 11 }

cLApGlobalDot11IfTable OBJECT-TYPE
    SYNTAX SEQUENCE OF CLApGlobalDot11IfEntry
    ACCESS not-accessible
    STATUS mandatory
    DESCRIPTION
        "This table is used to configure the global dot11
        parameters per slot id, represented by cLApDot11IfSlotId, 
        of the radio interface in all the APs joined with 
        the controller."
    ::= { ciscoLwappApGlobal 12 }

cLApGlobalDot11IfEntry OBJECT-TYPE
    SYNTAX CLApGlobalDot11IfEntry
    ACCESS not-accessible
    STATUS mandatory
    DESCRIPTION
        "This represents an entry in the
        cLApGlobalDot11IfTable."
    INDEX { cLApDot11IfSlotId }
    ::= { cLApGlobalDot11IfTable 1 }

CLApGlobalDot11IfEntry ::= SEQUENCE {
    cLApGlobalDot11IfCdpEnabled TruthValue
    }

cLApGlobalDot11IfCdpEnabled OBJECT-TYPE
    SYNTAX TruthValue
--    Rsyntax INTEGER {
--        true(1),
--        false(2)
--        }
    ACCESS read-write
    STATUS mandatory
    DESCRIPTION
        "This object is used to configure the Cisco Discovery
        Protocol(CDP) in the interface, represented by
        cLApDot11IfSlotId of the all the APs, joined in the 
        controller.
        
        Setting this object to a value of 'true' would turn on 
        the CDP on this slot.
        
        Setting this object to a value of 'false' would turn off the
        CDP on this slot, so that CDP advertisements are not sent.
        
        Read operation on this attribute will not be supported. 
        When queried this will return a value of 'false'."
    ::= { cLApGlobalDot11IfEntry 1 }

cLApGlobalEthernetIfTable OBJECT-TYPE
    SYNTAX SEQUENCE OF CLApGlobalEthernetIfEntry
    ACCESS not-accessible
    STATUS mandatory
    DESCRIPTION
        "This table is used to configure the global parameters
        on Ethernet interfaces of all the APs joined with the 
        controller."
    ::= { ciscoLwappApGlobal 13 }

cLApGlobalEthernetIfEntry OBJECT-TYPE
    SYNTAX CLApGlobalEthernetIfEntry
    ACCESS not-accessible
    STATUS mandatory
    DESCRIPTION
        "This represents an entry in
        cLApGlobalEthernetIfTable."
    INDEX { cLApEthernetIfSlotId }
    ::= { cLApGlobalEthernetIfTable 1 }

CLApGlobalEthernetIfEntry ::= SEQUENCE {
    cLApGlobalEthernetIfCdpEnabled TruthValue
    }

cLApGlobalEthernetIfCdpEnabled OBJECT-TYPE
    SYNTAX TruthValue
--    Rsyntax INTEGER {
--        true(1),
--        false(2)
--        }
    ACCESS read-write
    STATUS mandatory
    DESCRIPTION
        "This object is used to configure the Cisco Discovery
        Protocol(CDP) in the interface, represented by
        cLApEthernetIfSlotId of the all the APs, joined in 
        the controller.
        
        Setting this object to a value of 'true' would turn on 
        the CDP on this ethernet interface.
        
        Setting this object to a value of 'false' would turn off the
        CDP on this ethernet interface, so that CDP advertisements
        are not sent.
        
        Read operation on this attribute will not be supported. 
        When queried this will return a value of 'false'."
    ::= { cLApGlobalEthernetIfEntry 1 }

cLApGlobalRetransmitCount OBJECT-TYPE
    SYNTAX Gauge
--  Units
--    retries
    ACCESS read-write
    STATUS mandatory
    DESCRIPTION
        "This object specifies the retransmission count for the
        Control Packet of all the Access Points, joined to this 
        controller. This value represents the number of packets 
        retransmitted after which the Access Point falls back to 
        another controller in case of failover."
    ::= { ciscoLwappApGlobal 14 }

cLApGlobalRetransmitTimeout OBJECT-TYPE
    SYNTAX Gauge
--  Units
--    seconds
    ACCESS read-write
    STATUS mandatory
    DESCRIPTION
        "This object specifies the retransmission timeout for the
        Control Packet of all the Access Points, joined to this 
        controller. This value represents the timeout for each 
        retransmission, during the fallback of Access Point to 
        another controller in case of failover."
    ::= { ciscoLwappApGlobal 15 }

cLApDot11IfAntennaTable OBJECT-TYPE
    SYNTAX SEQUENCE OF CLApDot11IfAntennaEntry
    ACCESS not-accessible
    STATUS mandatory
    DESCRIPTION
        "This table represents the information about the
        basic functional parameters corresponding to
        the antenna on dot11 interfaces of the APs that have 
        joined the controller."
    ::= { ciscoLwappApIf 4 }

cLApDot11IfAntennaEntry OBJECT-TYPE
    SYNTAX CLApDot11IfAntennaEntry
    ACCESS not-accessible
    STATUS mandatory
    DESCRIPTION
        "An entry in this table represents the 802.11
        functional parameters of the dot11 interface of
        an AP that has joined the controller.
        
        Entries are added when the APs associate to this
        controller and deleted when they lose their
        association."
    INDEX { cLApSysMacAddress, cLApDot11IfSlotId, cLApDot11IfAntennaId }
    ::= { cLApDot11IfAntennaTable 1 }

CLApDot11IfAntennaEntry ::= SEQUENCE {
    cLApDot11IfAntennaId Gauge,
    cLApDot11IfAntennaTxEnable TruthValue,
    cLApDot11IfAntennaRxEnable TruthValue,
    cLApDot11IfAntennaEnable TruthValue
    }

cLApDot11IfAntennaId OBJECT-TYPE
    SYNTAX Gauge(1..3)
    ACCESS not-accessible
    STATUS mandatory
    DESCRIPTION
        "This object represents the antenna ID of a dot11
        interface on an AP. 
        The antenna Id for a particular dot11 interface on 
        a slot as represented by this object."
    ::= { cLApDot11IfAntennaEntry 1 }

cLApDot11IfAntennaTxEnable OBJECT-TYPE
    SYNTAX TruthValue
--    Rsyntax INTEGER {
--        true(1),
--        false(2)
--        }
    ACCESS read-write
    STATUS mandatory
    DESCRIPTION
        "This object specifies whether this antenna is allowed
        to trasmit or not.
        A value of 'true' enables the antenna to transmit.
        A value of 'false' disables the antenna to transmit.
        This object has been deprecated for cLApDot11IfAntennaEnable.
        cLApDot11IfAntennaTxEnable object is superseded by cLApDot11IfAntennaEnable."
    DEFVAL { true }
    ::= { cLApDot11IfAntennaEntry 2 }

cLApDot11IfAntennaRxEnable OBJECT-TYPE
    SYNTAX TruthValue
--    Rsyntax INTEGER {
--        true(1),
--        false(2)
--        }
    ACCESS read-write
    STATUS mandatory
    DESCRIPTION
        "This object specifies whether this antenna is allowed
        to recieve or not.
        A value of 'true' enables the antenna to receive.
        A value of 'false' disables the antenna to receive.
        This object has been deprecated for cLApDot11IfAntennaEnable.
        cLApDot11IfAntennaRxEnable object is superseded by cLApDot11IfAntennaEnable."
    DEFVAL { true }
    ::= { cLApDot11IfAntennaEntry 3 }

cLApDot11IfAntennaEnable OBJECT-TYPE
    SYNTAX TruthValue
--    Rsyntax INTEGER {
--        true(1),
--        false(2)
--        }
    ACCESS read-write
    STATUS mandatory
    DESCRIPTION
        "This object specifies whether this antenna is enabled or not.
        A value of 'true' enables the antenna.
        A value of 'false' disables the antenna."
    DEFVAL { true }
    ::= { cLApDot11IfAntennaEntry 4 }

cLApVlanIfTable OBJECT-TYPE
    SYNTAX SEQUENCE OF CLApVlanIfEntry
    ACCESS not-accessible
    STATUS mandatory
    DESCRIPTION
        "This table represents the information about the
        basic functional parameters corresponding to
        the Ethernet interfaces of the APs that have
        joined the controller."
    ::= { ciscoLwappApIf 5 }

cLApVlanIfEntry OBJECT-TYPE
    SYNTAX CLApVlanIfEntry
    ACCESS not-accessible
    STATUS mandatory
    DESCRIPTION
        "An entry in this table represents the VLAN
        functional parameters of the Ethernet interface of
        an AP that has joined the controller.
        Entries are added when the administrator creates
        an entry in this table."
    INDEX { cLApSysMacAddress, cLApVlanIfEthernetId }
    ::= { cLApVlanIfTable 1 }

CLApVlanIfEntry ::= SEQUENCE {
    cLApVlanIfEthernetId Gauge,
    cLApVlanIfMode INTEGER,
    cLApVlanIfEnable TruthValue,
    cLApVlanIfNativeVlanId Gauge
    }

cLApVlanIfEthernetId OBJECT-TYPE
    SYNTAX Gauge(0..3)
    ACCESS not-accessible
    STATUS mandatory
    DESCRIPTION
        "This object represents the ID of a Ethernet
        interface on an AP."
    ::= { cLApVlanIfEntry 1 }

cLApVlanIfMode OBJECT-TYPE
    SYNTAX INTEGER {
        normal(1),
        access(2),
        trunk(3)
        }
    ACCESS read-write
    STATUS mandatory
    DESCRIPTION
        "This object represents the mode this
        on this AP's Ethernet interface is
        configured for.
            normal - VLAN is not operating in access or trunk.
            access - VLAN is operating in access mode
            trunk  - VLAN is operating in trunk mode."
    DEFVAL { normal }
    ::= { cLApVlanIfEntry 2 }

cLApVlanIfEnable OBJECT-TYPE
    SYNTAX TruthValue
--    Rsyntax INTEGER {
--        true(1),
--        false(2)
--        }
    ACCESS read-write
    STATUS mandatory
    DESCRIPTION
        "This object specifies whether this interface  is
        enabled or not.
        A value of 'true' enables the interface.
        A value of 'false' will disable the interface. This will
        delete all entries on this AP's Ethernet interface."
    DEFVAL { true }
    ::= { cLApVlanIfEntry 3 }

cLApVlanIfNativeVlanId OBJECT-TYPE
    SYNTAX Gauge
    ACCESS read-write
    STATUS mandatory
    DESCRIPTION
        "This object represents the native VLAN ID
        assigned to this AP's Ethernet interface.
        This only applies when the icLApVlanIfMode
        is set to 'trunk'. For all other modes this
        return a value of zero."
    ::= { cLApVlanIfEntry 4 }

cLApVlanListTable OBJECT-TYPE
    SYNTAX SEQUENCE OF CLApVlanListEntry
    ACCESS not-accessible
    STATUS mandatory
    DESCRIPTION
        "This table represents the information about the
        basic functional parameters corresponding to
        the VLAN Ethernet interfaces of the APs that have 
        joined the controller."
    ::= { ciscoLwappApIf 6 }

cLApVlanListEntry OBJECT-TYPE
    SYNTAX CLApVlanListEntry
    ACCESS not-accessible
    STATUS mandatory
    DESCRIPTION
        "An entry in this table represents the VLAN
        functional parameters of the Ethernet interface of
        an AP that has joined the controller.
        Entries are added when the administrator creates 
        an entry in this table."
    INDEX { cLApSysMacAddress, cLApVlanIfEthernetId, cLApVlanListVlanId }
    ::= { cLApVlanListTable 1 }

CLApVlanListEntry ::= SEQUENCE {
    cLApVlanListVlanId Gauge,
    cLApVlanListRowStatus RowStatus
    }

cLApVlanListVlanId OBJECT-TYPE
    SYNTAX Gauge
    ACCESS not-accessible
    STATUS mandatory
    DESCRIPTION
        "This object represents the ID assigned to the
        VLAN on this AP's Ethernet interface."
    ::= { cLApVlanListEntry 1 }

cLApVlanListRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Used to add or delete an entry in this table."
    ::= { cLApVlanListEntry 2 }

cLApGlobal802dot1xAuthenticationEnabled OBJECT-TYPE
    SYNTAX TruthValue
--    Rsyntax INTEGER {
--        true(1),
--        false(2)
--        }
    ACCESS read-write
    STATUS mandatory
    DESCRIPTION
        "This object represents the Global AP 802.1x Supplicant
        Authentication feature.
        If configured as True, user can configure 8021.1x 
        authentication between lightweight access points and the 
        switch. The access point acts as an 802.1x supplicant and is 
        authenticated by the switch using EAP-FAST with anonymous 
        PAC provisioning.User can set global authentication settings 
        that all access points inherit as they join the controller. 
        This includes all access points that are currently joined to 
        the controller and any that join in the future. If desired, 
        user can override the global authentication settings and 
        assign unique authentication settings for a specific 
        access point.
        Default state is False."
    DEFVAL { false }
    ::= { ciscoLwappAp802dot1xSupplicant 1 }

cLApGlobal802dot1xSupplicantUsername OBJECT-TYPE
    SYNTAX SnmpAdminString
--    Rsyntax OCTET STRING(SIZE(0..255))
    ACCESS read-write
    STATUS mandatory
    DESCRIPTION
        "This object represents the 802.1x supplicant username that
        is to be inherited by all access points that join the 
        controller."
    ::= { ciscoLwappAp802dot1xSupplicant 2 }

cLApGlobal802dot1xSupplicantPassword OBJECT-TYPE
    SYNTAX SnmpAdminString
--    Rsyntax OCTET STRING(SIZE(0..255))
    ACCESS read-write
    STATUS mandatory
    DESCRIPTION
        "This object represents the 802.1x supplicant Password that
        is to be inherited by all access points that join the 
        controller. 
        A query on this OID will always return '****'."
    ::= { ciscoLwappAp802dot1xSupplicant 3 }

cLAp802dot1xSupplicantTable OBJECT-TYPE
    SYNTAX SEQUENCE OF CLAp802dot1xSupplicantEntry
    ACCESS not-accessible
    STATUS mandatory
    DESCRIPTION
        "This table provides the information about the 802.1x
        Supplicant credentials of the 802.11 LWAPP Access Points 
        that have joined the controller. Rows are added to this 
        table whenever, new APs are joined to this controller, 
        and rows are deleted whenever APs gets disjoined from 
        the controller."
    ::= { ciscoLwappAp802dot1xSupplicant 4 }

cLAp802dot1xSupplicantEntry OBJECT-TYPE
    SYNTAX CLAp802dot1xSupplicantEntry
    ACCESS not-accessible
    STATUS mandatory
    DESCRIPTION
        "Each entry in this table provides information about
        one 802.11 LWAPP Access Point that has joined the
        controller. cLApSysMacAddress is the index which
        uniquely identifies every row in the table."
    INDEX { cLApSysMacAddress }
    ::= { cLAp802dot1xSupplicantTable 1 }

CLAp802dot1xSupplicantEntry ::= SEQUENCE {
    cLAp802dot1xSupplicantOverrideEnabled TruthValue,
    cLAp802dot1xSupplicantOverrideUsername SnmpAdminString,
    cLAp802dot1xSupplicantOverridePassword SnmpAdminString
    }

cLAp802dot1xSupplicantOverrideEnabled OBJECT-TYPE
    SYNTAX TruthValue
--    Rsyntax INTEGER {
--        true(1),
--        false(2)
--        }
    ACCESS read-write
    STATUS mandatory
    DESCRIPTION
        "This object represents the individual AP level 802.1x
        Supplicant Authentication override parameters.
        If configured as True, user can override the Global AP 
        8021.1x authentication credentials by providing individual 
        AP level credentials.
        Default state is False."
    DEFVAL { false }
    ::= { cLAp802dot1xSupplicantEntry 1 }

cLAp802dot1xSupplicantOverrideUsername OBJECT-TYPE
    SYNTAX SnmpAdminString
--    Rsyntax OCTET STRING(SIZE(0..255))
    ACCESS read-write
    STATUS mandatory
    DESCRIPTION
        "This object represents the individual AP level 802.1x
        supplicant override username."
    ::= { cLAp802dot1xSupplicantEntry 2 }

cLAp802dot1xSupplicantOverridePassword OBJECT-TYPE
    SYNTAX SnmpAdminString
--    Rsyntax OCTET STRING(SIZE(0..255))
    ACCESS read-write
    STATUS mandatory
    DESCRIPTION
        "This object the individual AP level 802.1x supplicant
        override password. A query on this OID will always 
        return '****'."
    ::= { cLAp802dot1xSupplicantEntry 3 }

cLApDot11GlobalConfigTable OBJECT-TYPE
    SYNTAX SEQUENCE OF CLApDot11GlobalConfigEntry
    ACCESS not-accessible
    STATUS mandatory
    DESCRIPTION
        "This table represents the information about the
        global attributes of the radio interface, that would be
        applicable for all the APs that join the controller."
    ::= { ciscoLwappApIf 7 }

cLApDot11GlobalConfigEntry OBJECT-TYPE
    SYNTAX CLApDot11GlobalConfigEntry
    ACCESS not-accessible
    STATUS mandatory
    DESCRIPTION
        "An entry in this table represents the network
        level configurations of the radio interface.
        Entries cannot be added or deleted in this table."
    INDEX { cLApDot11IfType }
    ::= { cLApDot11GlobalConfigTable 1 }

CLApDot11GlobalConfigEntry ::= SEQUENCE {
    cLApNwLegacyBeamForming INTEGER,
    cLApNwTxPowerThreshold INTEGER
    }

cLApNwLegacyBeamForming OBJECT-TYPE
    SYNTAX INTEGER {
        enable(1),
        disable(2),
        notApplicable(3)
        }
    ACCESS read-write
    STATUS mandatory
    DESCRIPTION
        "This object indicates the status of legacy beam forming
        in this AP. This object is applicable only for
        11n supported APs.
        For APs that does not support legacy beam forming,
        a get request on this attribute will return
        the value 'notApplicable'.
        A value of 'enable' indicates that the legacy
        Beam forming is enabled in this AP.
        A value of 'false' indicates that the legacy
        Beam forming is disabled in this AP."
    DEFVAL { notApplicable }
    ::= { cLApDot11GlobalConfigEntry 1 }

cLApNwTxPowerThreshold OBJECT-TYPE
    SYNTAX INTEGER(-80..-50)
--  Units
--    dbm
    ACCESS read-write
    STATUS mandatory
    DESCRIPTION
        "This object represents the Global AP Transmit Power
        Threshold value. The permissible range is -80 dbm to -50 dbm"
    DEFVAL { -70 }
    ::= { cLApDot11GlobalConfigEntry 2 }

cLApAssocFailureReason OBJECT-TYPE
    SYNTAX CLApAssocFailureReason
--    Rsyntax INTEGER {
--        unknown(1),
--        notSupported(2)
--        }
    ACCESS not-accessible
    STATUS mandatory
    DESCRIPTION
        "This object specifies the failure reasons when
        a AP fails to associate with a controller."
    ::= { ciscoLwappApMIBNotifObjects 1 }

cLApRogueApMacAddress OBJECT-TYPE
    SYNTAX MacAddress
--    Rsyntax OCTET STRING(SIZE(6))
    ACCESS not-accessible
    STATUS mandatory
    DESCRIPTION
        "This object represents the radio MAC address
        common to the dot11 interfaces of the rogue AP."
    ::= { ciscoLwappApMIBNotifObjects 2 }

cLApDot11RadioChannelNumber OBJECT-TYPE
    SYNTAX CLDot11Channel
--    Rsyntax Gauge(1..14|34|36|38|40|42|44|46|48|52|56|60|64|149|153|157|161)
    ACCESS not-accessible
    STATUS mandatory
    DESCRIPTION
        "This object represents the channel number of the
        radio interface of the AP, represented by 
        cLApDot11IfType."
    ::= { ciscoLwappApMIBNotifObjects 3 }

cLApRogueApSsid OBJECT-TYPE
    SYNTAX SnmpAdminString
--    Rsyntax OCTET STRING(SIZE(0..255))
    ACCESS not-accessible
    STATUS mandatory
    DESCRIPTION
        "This object represents the SSID used by the
        rogue AP to intrude the network."
    ::= { ciscoLwappApMIBNotifObjects 4 }

cLApRogueType OBJECT-TYPE
    SYNTAX INTEGER {
        asleap(1),
        honeypot(2),
        other(3)
        }
    ACCESS not-accessible
    STATUS mandatory
    DESCRIPTION
        "This object represents the SSID of the used by the
        rogue AP to intrude the network."
    ::= { ciscoLwappApMIBNotifObjects 5 }

cLApWipsReason OBJECT-TYPE
    SYNTAX INTEGER {
        noMonitoringDevice(1)
        }
    ACCESS not-accessible
    STATUS mandatory
    DESCRIPTION
        "This object specifies the failure reasons for an AP
        when cLApWipsEnable is set to 'true'.
        
         noMonitoringDevice - No monitoring device 
         connected to collect WIPs information."
    ::= { ciscoLwappApMIBNotifObjects 6 }

cLApWipsClear OBJECT-TYPE
    SYNTAX TruthValue
--    Rsyntax INTEGER {
--        true(1),
--        false(2)
--        }
    ACCESS not-accessible
    STATUS mandatory
    DESCRIPTION
        "This object specifies whether this event is
        raise or clear.
        A value of 'true' indicates this event is cleared
        A value of 'false' indicates this even is raised."
    ::= { ciscoLwappApMIBNotifObjects 7 }

cLApIfUpDownFailureType OBJECT-TYPE
    SYNTAX INTEGER {
        detectedFailure(1),
        configuredReset(2)
        }
    ACCESS not-accessible
    STATUS mandatory
    DESCRIPTION
        "This object specifies the type of the
        AP interface failure.
        detectedFailure(1) - Failure of radio.
        configuredReset(2) - Reset due to manual 
                              configuration."
    ::= { ciscoLwappApMIBNotifObjects 8 }

cLApIfUpDownCause OBJECT-TYPE
    SYNTAX DisplayString
--    Rsyntax OCTET STRING(SIZE(0..255))
    ACCESS not-accessible
    STATUS mandatory
    DESCRIPTION
        "This object specifies the cause of the
        AP interface failure."
    ::= { ciscoLwappApMIBNotifObjects 9 }

cLApIfUpDownFailureCode OBJECT-TYPE
    SYNTAX DisplayString
--    Rsyntax OCTET STRING(SIZE(0..255))
    ACCESS not-accessible
    STATUS mandatory
    DESCRIPTION
        "This object specifies the code of the
        AP interface failure."
    ::= { ciscoLwappApMIBNotifObjects 10 }

ciscoLwappApIfRegulatoryDomainMismatchNotif TRAP-TYPE
-- Reverse mappable trap
    ENTERPRISE ciscoLwappApMIB
    VARIABLES {
        cLApName, cLApDot11IfType, cLApDot11IfRegDomain, 
        cldRegulatoryDomain }
--  Status
--    mandatory
    DESCRIPTION
        "This notification  is generated if an AP radio's regulatory
        domain doesn't match the country the controller is configured
        for.  Due to the mismatch, the AP will fail to associate with
        the controller."
    ::= 1

ciscoLwappApCrash TRAP-TYPE
-- Reverse mappable trap
    ENTERPRISE ciscoLwappApMIB
    VARIABLES {
        cLApName }
--  Status
--    obsolete
    DESCRIPTION
        "This notification is generated after an AP rejoins the
        controller after  a crash. Once the AP joins, the controller
        will get the crash file from the AP and sends this 
        notification."
    ::= 2

ciscoLwappApUnsupported TRAP-TYPE
-- Reverse mappable trap
    ENTERPRISE ciscoLwappApMIB
    VARIABLES {
        cLApName, cLApAssocFailureReason }
--  Status
--    mandatory
    DESCRIPTION
        "This notification is generated after an unsupported AP tries
        to join the controller."
    ::= 3

ciscoLwappApAssociated TRAP-TYPE
-- Reverse mappable trap
    ENTERPRISE ciscoLwappApMIB
    VARIABLES {
        cLApName, cLApLastRebootReason, cLApDataEncryptionStatus }
--  Status
--    mandatory
    DESCRIPTION
        "This notification is generated whenever an AP joins the
        controller successfully. This notification contains 
        information about the last reboot reason and Data 
        Encryption status of the AP."
    ::= 4

ciscoLwappApPower TRAP-TYPE
-- Reverse mappable trap
    ENTERPRISE ciscoLwappApMIB
    VARIABLES {
        cLApName, cLApPowerStatus }
--  Status
--    mandatory
    DESCRIPTION
        "This notification is generated whenever an AP detects low
        power from Ethernet."
    ::= 5

ciscoLwappApRogueApDetected TRAP-TYPE
-- Reverse mappable trap
    ENTERPRISE ciscoLwappApMIB
    VARIABLES {
        cLApSysMacAddress, cLApName, cLApRogueApMacAddress, 
        cLApEthernetIfSlotId, cLApDot11IfType, 
        cLApDot11RadioChannelNumber, cLApRogueApSsid, cLApRogueType }
--  Status
--    mandatory
    DESCRIPTION
        "This notification is generated whenever a rogue AP is
        detected."
    ::= 6

ciscoLwappApRogueApCleared TRAP-TYPE
-- Reverse mappable trap
    ENTERPRISE ciscoLwappApMIB
    VARIABLES {
        cLApSysMacAddress, cLApName, cLApRogueApMacAddress, 
        cLApEthernetIfSlotId, cLApDot11IfType, 
        cLApDot11RadioChannelNumber, cLApRogueApSsid, cLApRogueType }
--  Status
--    mandatory
    DESCRIPTION
        "This notification is generated whenever a rogue AP was
        detected and then subsequently if its been removed from 
        the network."
    ::= 7

ciscoLwappApWipsNotification TRAP-TYPE
-- Reverse mappable trap
    ENTERPRISE ciscoLwappApMIB
    VARIABLES {
        cLApName, cLApWipsReason, cLApWipsClear }
--  Status
--    mandatory
    DESCRIPTION
        "This notification is generated whenever a controller
        detects a WIPS event."
    ::= 8

ciscoLwappApNoDownlinkChannelNotify TRAP-TYPE
-- Reverse mappable trap
    ENTERPRISE ciscoLwappApMIB
    VARIABLES {
        cLApName }
--  Status
--    mandatory
    DESCRIPTION
        "This notification is generated when ever AP fails to find
        new downlink channel."
    ::= 9

ciscoLwappApIfUpNotify TRAP-TYPE
-- Reverse mappable trap
    ENTERPRISE ciscoLwappApMIB
    VARIABLES {
        cLApSysMacAddress, cLApDot11IfSlotId, cLApPortNumber, 
        cLApIfUpDownFailureType, cLApIfUpDownCause, 
        cLApIfUpDownFailureCode, cLApName }
--  Status
--    mandatory
    DESCRIPTION
        "This notification is generated when AP's Interface
        operational status goes up."
    ::= 10

ciscoLwappApIfDownNotify TRAP-TYPE
-- Reverse mappable trap
    ENTERPRISE ciscoLwappApMIB
    VARIABLES {
        cLApSysMacAddress, cLApDot11IfSlotId, cLApAdminStatus, 
        cLApDot11IfAdminStatus, cLApIfUpDownFailureType, 
        cLApIfUpDownCause, cLApIfUpDownFailureCode, cLApName }
--  Status
--    mandatory
    DESCRIPTION
        "This notification is generated when AP's Interface
        operational status goes down."
    ::= 11

ciscoLwappApGroup OBJECT IDENTIFIER ::= { ciscoLwappApMIBGroups 1 }
-- OBJECT-GROUP
--  Status
--    mandatory
--  Descr
--    This collection of objects represents the information
--    about the general attributes and functional 
--    parameters of those APs that have joined the
--    controller.
--  objects
--    cLApIfMacAddress, cLApMaxNumberOfDot11Slots, 
--    cLApIfSmtDot11Bssid

ciscoLwappApIfGroup OBJECT IDENTIFIER ::= { ciscoLwappApMIBGroups 2 }
-- OBJECT-GROUP
--  Status
--    mandatory
--  Descr
--    This collection of objects represents the information
--    about the dot11 interfaces of those APs that have 
--    joined the controller.
--  objects
--    cLApDot11IfType

ciscoLwappApGroupSup1 OBJECT IDENTIFIER ::= { ciscoLwappApMIBGroups 3 }
-- OBJECT-GROUP
--  Status
--    mandatory
--  Descr
--    This supplemental collection of objects represents the
--    information about the general attributes and functional 
--    parameters of those APs that have joined the
--    controller.
--  objects
--    cLApEntPhysicalIndex

ciscoLwappApGroupSup2 OBJECT IDENTIFIER ::= { ciscoLwappApMIBGroups 4 }
-- OBJECT-GROUP
--  Status
--    mandatory
--  Descr
--    This supplemental collection of objects represents the
--    name associated with those APs that have joined the
--    controller.
--  objects
--    cLApName

ciscoLwappApGroupSup3 OBJECT IDENTIFIER ::= { ciscoLwappApMIBGroups 5 }
-- OBJECT-GROUP
--  Status
--    mandatory
--  Descr
--    This supplemental collection of objects represents the
--    country and 802.11n related information for those APs 
--    that have joined the controller.
--  objects
--    cLApDot11IfRegDomain, cLApDot11nSupport, 
--    cLAp11nChannelBandwidth, cLApCountryCode, cLApCountryAllowed

ciscoLwappApNotifObjsGroup OBJECT IDENTIFIER ::= { ciscoLwappApMIBGroups 6 }
-- OBJECT-GROUP
--  Status
--    mandatory
--  Descr
--    This supplemental collection of objects represents the
--    information carried by the AP related notifications 
--    sent by the agent to a network management station.
--  objects
--    cLApAssocFailureReason

ciscoLwappApGroupSup4 OBJECT IDENTIFIER ::= { ciscoLwappApMIBGroups 8 }
-- OBJECT-GROUP
--  Status
--    deprecated
--  Descr
--    This supplemental collection of objects represents the
--    global and credential information for those APs 
--    that have joined the controller.
--    ciscoLwappApGroupSup4 object is superseded by ciscoLwappApGroupSup6.
--  objects
--    cLApUpTime, cLLwappUpTime, cLLwappJoinTakenTime, 
--    cLApMaxNumberOfEthernetSlots, 
--    cLApPrimaryControllerAddressType, 
--    cLApPrimaryControllerAddress, 
--    cLApSecondaryControllerAddressType, 
--    cLApSecondaryControllerAddress, 
--    cLApTertiaryControllerAddressType, 
--    cLApTertiaryControllerAddress, cLApLomEnabled, 
--    cLApLomFirstChannel, cLApLomSecondChannel, 
--    cLApLomThirdChannel, cLApLomFourthChannel, 
--    cLApCredentialGlobalUserName, cLApCredentialGlobalPassword, 
--    cLApCredentialGlobalSecret, cLApCredentialUserName, 
--    cLApCredentialPassword, cLApCredentialSecret, 
--    cLApCredentialEnableGlobalCredentials, cLApFastHbTimerTimeout, 
--    cLApFastHbTimerEnabled, cLApPrimaryDiscoveryTimeout, 
--    cLApGlobalPrimaryControllerAddressType, 
--    cLApGlobalPrimaryControllerAddress, 
--    cLApGlobalPrimaryControllerName, 
--    cLApGlobalSecondaryControllerAddressType, 
--    cLApGlobalSecondaryControllerAddress, 
--    cLApGlobalSecondaryControllerName, 
--    ciscoLwappApIfRegulatoryDomainMismatchNotifEnabled, 
--    ciscoLwappApCrashEnabled, ciscoLwappApUnsupportedEnabled, 
--    ciscoLwappApAssociatedEnabled, cLApLastRebootReason

ciscoLwappApEthernetIfGroup OBJECT IDENTIFIER ::= { ciscoLwappApMIBGroups 9 }
-- OBJECT-GROUP
--  Status
--    mandatory
--  Descr
--    This collection of objects represents the information
--    about the Ethernet interfaces of those APs that have
--    joined the controller.
--  objects
--    cLApEthernetIfName, cLApEthernetIfMacAddress, 
--    cLApEthernetIfAdminStatus, cLApEthernetIfOperStatus, 
--    cLApEthernetIfRxUcastPkts, cLApEthernetIfRxNUcastPkts, 
--    cLApEthernetIfTxUcastPkts, cLApEthernetIfTxNUcastPkts

ciscoLwappApRadioGroup OBJECT IDENTIFIER ::= { ciscoLwappApMIBGroups 10 }
-- OBJECT-GROUP
--  Status
--    mandatory
--  Descr
--    This collection of objects represents the information
--    about the Radios of those APs that have
--    joined the controller.
--  objects
--    cLApDot11RadioMACAddress, cLApDot11RadioSubBand, 
--    cLApDot11RadioVersion, cLApDot11IsBackhaul, 
--    cLApDot11RadioRole

ciscoLwappApGroupSup5 OBJECT IDENTIFIER ::= { ciscoLwappApMIBGroups 11 }
-- OBJECT-GROUP
--  Status
--    mandatory
--  Descr
--    This supplemental collection of objects represents
--    objects related to encryption and link latency of 
--    AP.
--  objects
--    cLApGlobalFailoverPriority, cLApFailoverPriority, 
--    cLApEncryptionEnable, cLApLinkLatencyEnable, 
--    cLApLinkLatencyReset, cLApLinkLatencyStatsCurrent, 
--    cLApLinkLatencyStatsMin, cLApLinkLatencyStatsMax, 
--    cLApLinkLatencyTimeStamp

ciscoLwappSeClientSup OBJECT IDENTIFIER ::= { ciscoLwappApMIBGroups 12 }
-- OBJECT-GROUP
--  Status
--    mandatory
--  Descr
--    This supplemental collection of objects represents the
--    Spectrum Expert client details connected to the APs.
--  objects
--    cLApSeClientUserName, cLApSeClientIPAddrType, 
--    cLApSeClientIPAddr, cLApSeClientDuration, cLApSeClientPort

ciscoLwappDot11IfAntennaGroup OBJECT IDENTIFIER ::= { ciscoLwappApMIBGroups 13 }
-- OBJECT-GROUP
--  Status
--    mandatory
--  Descr
--    This supplemental collection of objects represents the
--    antenna details corresponding to the dot11 interface of the
--    Access Points.
--  objects
--    cLApDot11IfAntennaEnable

ciscoLwappRetransmitGroup OBJECT IDENTIFIER ::= { ciscoLwappApMIBGroups 14 }
-- OBJECT-GROUP
--  Status
--    mandatory
--  Descr
--    This supplemental collection of objects represents the
--    retransmit parameters corresponding to the fallback of an
--    AccessPoint to another controller during failover.
--  objects
--    cLApRetransmitCount, cLApRetransmitTimeout, 
--    cLApGlobalRetransmitCount, cLApGlobalRetransmitTimeout

ciscoLwappApGroupSup6 OBJECT IDENTIFIER ::= { ciscoLwappApMIBGroups 15 }
-- OBJECT-GROUP
--  Status
--    mandatory
--  Descr
--    This supplemental collection of objects represents the
--    global and credential information for those APs 
--    that have joined the controller.
--  objects
--    cLApUpTime, cLLwappUpTime, cLLwappJoinTakenTime, 
--    cLApMaxNumberOfEthernetSlots, 
--    cLApPrimaryControllerAddressType, 
--    cLApPrimaryControllerAddress, 
--    cLApSecondaryControllerAddressType, 
--    cLApSecondaryControllerAddress, 
--    cLApTertiaryControllerAddressType, 
--    cLApTertiaryControllerAddress, cLApLomFirstChannel, 
--    cLApLomSecondChannel, cLApLomThirdChannel, 
--    cLApLomFourthChannel, cLApCredentialGlobalUserName, 
--    cLApCredentialGlobalPassword, cLApCredentialGlobalSecret, 
--    cLApCredentialUserName, cLApCredentialPassword, 
--    cLApCredentialSecret, cLApCredentialEnableGlobalCredentials, 
--    cLApFastHbTimerTimeout, cLApFastHbTimerEnabled, 
--    cLApPrimaryDiscoveryTimeout, 
--    cLApGlobalPrimaryControllerAddressType, 
--    cLApGlobalPrimaryControllerAddress, 
--    cLApGlobalPrimaryControllerName, 
--    cLApGlobalSecondaryControllerAddressType, 
--    cLApGlobalSecondaryControllerAddress, 
--    cLApGlobalSecondaryControllerName, 
--    ciscoLwappApIfRegulatoryDomainMismatchNotifEnabled, 
--    ciscoLwappApCrashEnabled, ciscoLwappApUnsupportedEnabled, 
--    ciscoLwappApAssociatedEnabled, cLApLastRebootReason

ciscoLwappApGroupSup7 OBJECT IDENTIFIER ::= { ciscoLwappApMIBGroups 17 }
-- OBJECT-GROUP
--  Status
--    mandatory
--  Descr
--    This supplemental collection of objects represents the
--    information about the general attributes and functional 
--    parameters of those APs that have joined the
--    controller.
--  objects
--    cLApTelnetEnable, cLApSshEnable, cLApPreStdStateEnabled, 
--    cLApPwrInjectorStateEnabled, cLApPwrInjectorSelection, 
--    cLApPwrInjectorSwMacAddr, cLApWipsEnable, 
--    cLApMonitorModeOptimization, cLApDomainName, 
--    cLApNameServerAddress, cLApAMSDUEnable, 
--    cLApEncryptionSupported, cLApRogueDetectionEnabled, 
--    cLApTcpMss, cLApAdminStatus, cLApLomEnabled, 
--    cLApLegacyBeamForming, cLApCdpOverAirEnabled, 
--    cLApDot11IfAdminStatus, cLApEthernetIfCdpEnabled, 
--    cLApGlobalTcpMss, cLApGlobalDot11IfCdpEnabled, 
--    cLApGlobalEthernetIfCdpEnabled, cLApVlanIfMode, 
--    cLApVlanIfEnable, cLApVlanIfNativeVlanId, 
--    cLApGlobal802dot1xAuthenticationEnabled, 
--    cLApGlobal802dot1xSupplicantPassword, 
--    cLApGlobal802dot1xSupplicantUsername, 
--    cLAp802dot1xSupplicantOverrideEnabled, 
--    cLAp802dot1xSupplicantOverrideUsername, 
--    cLAp802dot1xSupplicantOverridePassword, 
--    cLApNwLegacyBeamForming, cLApNwTxPowerThreshold, 
--    cLApVlanListRowStatus

ciscoLwappApNotifsGroup OBJECT IDENTIFIER ::= { ciscoLwappApMIBGroups 7 }
-- NOTIFICATION-GROUP
--  Status
--    deprecated
--  Descr
--    This supplemental collection of objects represents the
--    AP related notifications sent by the agent to a network
--    management station.
--    ciscoLwappApNotifsGroup object is superseded by ciscoLwappApNotifsGroupVer1.
--  notifications
--    ciscoLwappApIfRegulatoryDomainMismatchNotif, 
--    ciscoLwappApCrash, ciscoLwappApUnsupported, 
--    ciscoLwappApAssociated

ciscoLwappApNotifsGroupVer1 OBJECT IDENTIFIER ::= { ciscoLwappApMIBGroups 16 }
-- NOTIFICATION-GROUP
--  Status
--    mandatory
--  Descr
--    This supplemental collection of objects represents the
--    AP related notifications sent by the agent to a network
--    management station.
--  notifications
--    ciscoLwappApIfRegulatoryDomainMismatchNotif, 
--    ciscoLwappApUnsupported, ciscoLwappApAssociated

ciscoLwappApMIBCompliance OBJECT IDENTIFIER ::= { ciscoLwappApMIBCompliances 1 }
-- MODULE-COMPLIANCE
--  Status
--    deprecated
--  Descr
--    The compliance statement for the SNMP entities that
--    implement the ciscoLwappApMIB module.
--  Module
--    >>current<<
--   MandGroup
--    ciscoLwappApGroup
--   MandGroup
--    ciscoLwappApIfGroup

ciscoLwappApMIBComplianceRev1 OBJECT IDENTIFIER ::= { ciscoLwappApMIBCompliances 2 }
-- MODULE-COMPLIANCE
--  Status
--    deprecated
--  Descr
--    The compliance statement for the SNMP entities that
--    implement the ciscoLwappApMIB module.
--  Module
--    >>current<<
--   MandGroup
--    ciscoLwappApGroup
--   MandGroup
--    ciscoLwappApIfGroup
--   MandGroup
--    ciscoLwappApGroupSup1

ciscoLwappApMIBComplianceRev2 OBJECT IDENTIFIER ::= { ciscoLwappApMIBCompliances 3 }
-- MODULE-COMPLIANCE
--  Status
--    deprecated
--  Descr
--    The compliance statement for the SNMP entities that
--    implement the ciscoLwappApMIB module.
--  Module
--    >>current<<
--   MandGroup
--    ciscoLwappApGroup
--   MandGroup
--    ciscoLwappApIfGroup
--   MandGroup
--    ciscoLwappApGroupSup1
--   MandGroup
--    ciscoLwappApGroupSup2

ciscoLwappApMIBComplianceRev3 OBJECT IDENTIFIER ::= { ciscoLwappApMIBCompliances 4 }
-- MODULE-COMPLIANCE
--  Status
--    deprecated
--  Descr
--    The compliance statement for the SNMP entities that
--    implement the ciscoLwappApMIB module.
--  Module
--    >>current<<
--   MandGroup
--    ciscoLwappApGroup
--   MandGroup
--    ciscoLwappApIfGroup
--   MandGroup
--    ciscoLwappApGroupSup1
--   MandGroup
--    ciscoLwappApGroupSup2
--   MandGroup
--    ciscoLwappApGroupSup3
--   MandGroup
--    ciscoLwappApGroupSup4
--   MandGroup
--    ciscoLwappApNotifObjsGroup
--   MandGroup
--    ciscoLwappApNotifsGroup
--   MandGroup
--    ciscoLwappApGroupSup4
--   MandGroup
--    ciscoLwappApEthernetIfGroup
--   MandGroup
--    ciscoLwappApRadioGroup

ciscoLwappApMIBComplianceRev4 OBJECT IDENTIFIER ::= { ciscoLwappApMIBCompliances 5 }
-- MODULE-COMPLIANCE
--  Status
--    deprecated
--  Descr
--    The compliance statement for the SNMP entities that
--    implement the ciscoLwappApMIB module.
--  Module
--    >>current<<
--   MandGroup
--    ciscoLwappApGroup
--   MandGroup
--    ciscoLwappApIfGroup
--   MandGroup
--    ciscoLwappApGroupSup1
--   MandGroup
--    ciscoLwappApGroupSup2
--   MandGroup
--    ciscoLwappApGroupSup3
--   MandGroup
--    ciscoLwappApNotifObjsGroup
--   MandGroup
--    ciscoLwappApNotifsGroup
--   MandGroup
--    ciscoLwappApGroupSup4
--   MandGroup
--    ciscoLwappApEthernetIfGroup
--   MandGroup
--    ciscoLwappApRadioGroup
--   MandGroup
--    ciscoLwappApGroupSup5

ciscoLwappApMIBComplianceRev5 OBJECT IDENTIFIER ::= { ciscoLwappApMIBCompliances 6 }
-- MODULE-COMPLIANCE
--  Status
--    deprecated
--  Descr
--    The compliance statement for the SNMP entities that
--    implement the ciscoLwappApMIB module.
--  Module
--    >>current<<
--   MandGroup
--    ciscoLwappApGroup
--   MandGroup
--    ciscoLwappApIfGroup
--   MandGroup
--    ciscoLwappApGroupSup1
--   MandGroup
--    ciscoLwappApGroupSup2
--   MandGroup
--    ciscoLwappApGroupSup3
--   MandGroup
--    ciscoLwappApNotifObjsGroup
--   MandGroup
--    ciscoLwappApNotifsGroup
--   MandGroup
--    ciscoLwappApGroupSup4
--   MandGroup
--    ciscoLwappApEthernetIfGroup
--   MandGroup
--    ciscoLwappApRadioGroup
--   MandGroup
--    ciscoLwappApGroupSup5
--   MandGroup
--    ciscoLwappSeClientSup

ciscoLwappApMIBComplianceRev6 OBJECT IDENTIFIER ::= { ciscoLwappApMIBCompliances 7 }
-- MODULE-COMPLIANCE
--  Status
--    deprecated
--  Descr
--    The compliance statement for the SNMP entities that
--    implement the ciscoLwappApMIB module.
--  Module
--    >>current<<
--   MandGroup
--    ciscoLwappApGroup
--   MandGroup
--    ciscoLwappApIfGroup
--   MandGroup
--    ciscoLwappApGroupSup1
--   MandGroup
--    ciscoLwappApGroupSup2
--   MandGroup
--    ciscoLwappApGroupSup3
--   MandGroup
--    ciscoLwappApNotifObjsGroup
--   MandGroup
--    ciscoLwappApNotifsGroup
--   MandGroup
--    ciscoLwappApGroupSup4
--   MandGroup
--    ciscoLwappApEthernetIfGroup
--   MandGroup
--    ciscoLwappApRadioGroup
--   MandGroup
--    ciscoLwappApGroupSup5
--   MandGroup
--    ciscoLwappSeClientSup

ciscoLwappApMIBComplianceRev7 OBJECT IDENTIFIER ::= { ciscoLwappApMIBCompliances 8 }
-- MODULE-COMPLIANCE
--  Status
--    mandatory
--  Descr
--    The compliance statement for the SNMP entities that
--    implement the ciscoLwappApMIB module.
--  Module
--    >>current<<
--   MandGroup
--    ciscoLwappApGroup
--   MandGroup
--    ciscoLwappApIfGroup
--   MandGroup
--    ciscoLwappApGroupSup1
--   MandGroup
--    ciscoLwappApGroupSup2
--   MandGroup
--    ciscoLwappApGroupSup3
--   MandGroup
--    ciscoLwappApNotifObjsGroup
--   MandGroup
--    ciscoLwappApNotifsGroupVer1
--   MandGroup
--    ciscoLwappApGroupSup6
--   MandGroup
--    ciscoLwappApGroupSup7
--   MandGroup
--    ciscoLwappApEthernetIfGroup
--   MandGroup
--    ciscoLwappApRadioGroup
--   MandGroup
--    ciscoLwappApGroupSup5
--   MandGroup
--    ciscoLwappSeClientSup
--   MandGroup
--    ciscoLwappDot11IfAntennaGroup
--   MandGroup
--    ciscoLwappRetransmitGroup
--   ObjVar
--    cLApDot11IfAntennaEnable
--   ObjVar
--    cLApRetransmitCount
--   ObjVar
--    cLApRetransmitTimeout
--   ObjVar
--    cLApGlobalRetransmitCount
--   ObjVar
--    cLApGlobalRetransmitTimeout
--   ObjVar
--    cLApName
--   ObjVar
--    cLApPrimaryControllerAddress
--   ObjVar
--    cLApSecondaryControllerAddress
--   ObjVar
--    cLApTertiaryControllerAddress
--   ObjVar
--    cLApEncryptionEnable
--   ObjVar
--    cLApFailoverPriority
--   ObjVar
--    cLApTelnetEnable
--   ObjVar
--    cLApSshEnable
--   ObjVar
--    cLApPreStdStateEnabled
--   ObjVar
--    cLApPwrInjectorStateEnabled
--   ObjVar
--    cLApPwrInjectorSelection
--   ObjVar
--    cLApPwrInjectorSwMacAddr
--   ObjVar
--    cLApWipsEnable
--   ObjVar
--    cLApMonitorModeOptimization
--   ObjVar
--    cLApDomainName
--   ObjVar
--    cLApNameServerAddress
--   ObjVar
--    cLApAMSDUEnable
--   ObjVar
--    cLApEncryptionSupported
--   ObjVar
--    cLApRogueDetectionEnabled
--   ObjVar
--    cLApTcpMss
--   ObjVar
--    cLApAdminStatus
--   ObjVar
--    cLAp11nChannelBandwidth
--   ObjVar
--    cLApLomEnabled
--   ObjVar
--    cLApLomFirstChannel
--   ObjVar
--    cLApLomSecondChannel
--   ObjVar
--    cLApLomThirdChannel
--   ObjVar
--    cLApLomFourthChannel
--   ObjVar
--    cLApLegacyBeamForming
--   ObjVar
--    cLApCdpOverAirEnabled
--   ObjVar
--    cLApDot11IfAdminStatus
--   ObjVar
--    cLApEthernetIfAdminStatus
--   ObjVar
--    cLApEthernetIfCdpEnabled
--   ObjVar
--    cLApCredentialGlobalUserName
--   ObjVar
--    cLApCredentialGlobalPassword
--   ObjVar
--    cLApCredentialGlobalSecret
--   ObjVar
--    cLApLinkLatencyEnable
--   ObjVar
--    cLApLinkLatencyReset
--   ObjVar
--    cLApCountryCode
--   ObjVar
--    ciscoLwappApIfRegulatoryDomainMismatchNotifEnabled
--   ObjVar
--    ciscoLwappApCrashEnabled
--   ObjVar
--    ciscoLwappApUnsupportedEnabled
--   ObjVar
--    ciscoLwappApAssociatedEnabled
--   ObjVar
--    cLApPrimaryDiscoveryTimeout
--   ObjVar
--    cLApFastHbTimerTimeout
--   ObjVar
--    cLApFastHbTimerEnabled
--   ObjVar
--    cLApGlobalPrimaryControllerAddress
--   ObjVar
--    cLApGlobalSecondaryControllerAddress
--   ObjVar
--    cLApGlobalPrimaryControllerName
--   ObjVar
--    cLApGlobalSecondaryControllerName
--   ObjVar
--    cLApGlobalPrimaryControllerAddressType
--   ObjVar
--    cLApGlobalSecondaryControllerAddressType
--   ObjVar
--    cLApGlobalFailoverPriority
--   ObjVar
--    cLApGlobalTcpMss
--   ObjVar
--    cLApGlobalDot11IfCdpEnabled
--   ObjVar
--    cLApGlobalEthernetIfCdpEnabled
--   ObjVar
--    cLApVlanIfMode
--   ObjVar
--    cLApVlanIfEnable
--   ObjVar
--    cLApVlanIfNativeVlanId
--   ObjVar
--    cLApPrimaryControllerAddressType
--   ObjVar
--    cLApSecondaryControllerAddressType
--   ObjVar
--    cLApTertiaryControllerAddressType
--   ObjVar
--    cLApGlobal802dot1xAuthenticationEnabled
--   ObjVar
--    cLApGlobal802dot1xSupplicantPassword
--   ObjVar
--    cLApGlobal802dot1xSupplicantUsername
--   ObjVar
--    cLAp802dot1xSupplicantOverrideEnabled
--   ObjVar
--    cLAp802dot1xSupplicantOverrideUsername
--   ObjVar
--    cLAp802dot1xSupplicantOverridePassword
--   ObjVar
--    cLApNwLegacyBeamForming
--   ObjVar
--    cLApNwTxPowerThreshold
--   ObjVar
--    cLApCredentialUserName
--   ObjVar
--    cLApCredentialPassword
--   ObjVar
--    cLApCredentialSecret
--   ObjVar
--    cLApCredentialEnableGlobalCredentials
--   ObjVar
--    cLApVlanListRowStatus


END
