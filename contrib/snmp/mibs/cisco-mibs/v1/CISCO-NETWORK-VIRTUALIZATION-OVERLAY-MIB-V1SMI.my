-- MIB file created 28-Jan-2015 17:04:00, by
--   SMICng version 2.2.11-beta(PRO)(Solaris), January 20, 2001. Enterprise key cisco.com

CISCO-NETWORK-VIRTUALIZATION-OVERLAY-MIB DEFINITIONS ::= BEGIN

-- From file: "CISCO-NETWORK-VIRTUALIZATION-OVERLAY-MIB.my"
-- Compile options "4 7 F H N W 03 06 0B 0G 0N 0T"

IMPORTS
    DateAndTime, RowStatus, StorageType
            FROM SNMPv2-TC-v1
    SnmpAdminString
            FROM SNMP-FRAMEWORK-MIB
    InetAddressType, InetAddress
            FROM INET-ADDRESS-MIB
    InterfaceIndexOrZero
            FROM IF-MIB
    VlanIndexOrZero
            FROM CISCO-PRIVATE-VLAN-MIB
    ciscoMgmt
            FROM CISCO-SMI
    Gauge, Counter
            FROM RFC1155-SMI
    OBJECT-TYPE
            FROM RFC-1212;

ciscoNetworkVirtualizationOverlayMIB OBJECT IDENTIFIER ::= { ciscoMgmt 820 }
-- MODULE-IDENTITY
--  LastUpdated
--    201501260000Z
--  OrgName
--    Cisco Systems, Inc.
--  ContactInfo
--    Cisco Systems
--    Customer Service
--    
--    Postal: 170 W Tasman Drive
--    San Jose, CA  95134
--    USA
--    
--    Tel: +1 800 553-NETS
--    
--    E-mail: cs-snmp@cisco.com
--  Descr
--    This MIB module is for managing Network Virtualization Overlay
--    functionality on Cisco devices. 
--    
--    
--    The following terms are used throughout this MIB:
--    
--    NVE     Network Virtualization Endpoint
--    
--    NVGRE   Network Virtualization using Generic Routing
--            Encapsulation
--    
--    NVO     Network Virtualization Overlay
--    
--    VLAN    Virtual Local Area Network
--    
--    VNet    Virtual Network
--    
--    VNI     Virtual Network Identifier 
--    
--    VXLAN   Virtual Extensible LAN
--  RevDate
--    201501260000Z
--  RevDescr
--    Initial version of this MIB module.

cnvoMIBNotifs   OBJECT IDENTIFIER ::= { ciscoNetworkVirtualizationOverlayMIB 0 }
cnvoMIBObjects  OBJECT IDENTIFIER ::= { ciscoNetworkVirtualizationOverlayMIB 1 }
cnvoMIBConform  OBJECT IDENTIFIER ::= { ciscoNetworkVirtualizationOverlayMIB 2 }
cnvoNvoObjects  OBJECT IDENTIFIER ::= { cnvoMIBObjects 1 }
cnvoMIBCompliances OBJECT IDENTIFIER ::= { cnvoMIBConform 1 }
cnvoMIBGroups   OBJECT IDENTIFIER ::= { cnvoMIBConform 2 }

cnvoNvoTable OBJECT-TYPE
    SYNTAX SEQUENCE OF CnvoNvoEntry
    ACCESS not-accessible
    STATUS mandatory
    DESCRIPTION
        "This table provides network virtualization overlays
        configured on the system."
    ::= { cnvoNvoObjects 1 }

cnvoNvoEntry OBJECT-TYPE
    SYNTAX CnvoNvoEntry
    ACCESS not-accessible
    STATUS mandatory
    DESCRIPTION
        "An entry containing management information for network
        virtualization overlay."
    INDEX { cnvoNvoInstanceId }
    ::= { cnvoNvoTable 1 }

CnvoNvoEntry ::= SEQUENCE {
    cnvoNvoInstanceId Gauge,
    cnvoNvoEncapType INTEGER,
    cnvoNvoSourceInterface InterfaceIndexOrZero,
    cnvoNvoConfiguredVni SnmpAdminString,
    cnvoNvoStorageType StorageType,
    cnvoNvoRowStatus RowStatus
    }

cnvoNvoInstanceId OBJECT-TYPE
    SYNTAX Gauge
    ACCESS not-accessible
    STATUS mandatory
    DESCRIPTION
        "A unique number to identify a NVO instance."
    ::= { cnvoNvoEntry 1 }

cnvoNvoEncapType OBJECT-TYPE
    SYNTAX INTEGER {
        unknown(1),
        vxlan(2),
        nvgre(3)
        }
    ACCESS read-write
    STATUS mandatory
    DESCRIPTION
        "This object specifies the encapsulation type for the
        NVO instance.  
        
        'unknown' - The read-only value 'unknown' indicates that
                     encapsulation type is none of the following
        
        'vxlan'    - encapsulation type is VXLAN
        
        'nvgre'    - encapsulation type is NVGRE
        
        This object may be modified when the row is active."
    DEFVAL { vxlan }
    ::= { cnvoNvoEntry 2 }

cnvoNvoSourceInterface OBJECT-TYPE
    SYNTAX InterfaceIndexOrZero
--    Rsyntax INTEGER(0..2147483647)
    ACCESS read-write
    STATUS mandatory
    DESCRIPTION
        "This object specifies the Source Interface for
        the NVO instance.
        This object may be modified when the row is active."
    DEFVAL { 0 }
    ::= { cnvoNvoEntry 3 }

cnvoNvoConfiguredVni OBJECT-TYPE
    SYNTAX SnmpAdminString
--    Rsyntax OCTET STRING(SIZE(0..255))
    ACCESS read-only
    STATUS mandatory
    DESCRIPTION
        "This object indicates the list of VNIs associated with
        this NVO instance."
    ::= { cnvoNvoEntry 4 }

cnvoNvoStorageType OBJECT-TYPE
    SYNTAX StorageType
--    Rsyntax INTEGER {
--        other(1),
--        volatile(2),
--        nonVolatile(3),
--        permanent(4),
--        readOnly(5)
--        }
    ACCESS read-write
    STATUS mandatory
    DESCRIPTION
        "This object specifies the storage type for this
        conceptual row."
    DEFVAL { volatile }
    ::= { cnvoNvoEntry 5 }

cnvoNvoRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object specifies the status of this conceptual row."
    ::= { cnvoNvoEntry 6 }

cnvoVNetTable OBJECT-TYPE
    SYNTAX SEQUENCE OF CnvoVNetEntry
    ACCESS not-accessible
    STATUS mandatory
    DESCRIPTION
        "This table provides information for virtual
        networks on the system."
    ::= { cnvoNvoObjects 2 }

cnvoVNetEntry OBJECT-TYPE
    SYNTAX CnvoVNetEntry
    ACCESS not-accessible
    STATUS mandatory
    DESCRIPTION
        "An entry containing status information for a
        virtual network."
    INDEX { cnvoNvoInstanceId, cnvoVNetLocalVNetId }
    ::= { cnvoVNetTable 1 }

CnvoVNetEntry ::= SEQUENCE {
    cnvoVNetLocalVNetId Gauge,
    cnvoVNetIpMcastAddrType InetAddressType,
    cnvoVNetIpMcastAddr InetAddress,
    cnvoVNetVlan VlanIndexOrZero,
    cnvoVNetArpSuppression INTEGER,
    cnvoVNetReplication INTEGER,
    cnvoVNetHostReachability INTEGER,
    cnvoVNetVniType INTEGER,
    cnvoVNetIpVrfOrBridgeDomainName SnmpAdminString,
    cnvoVNetRouterMacAddr InetAddress
    }

cnvoVNetLocalVNetId OBJECT-TYPE
    SYNTAX Gauge
    ACCESS not-accessible
    STATUS mandatory
    DESCRIPTION
        "A unique number to identify a local virtual network."
    ::= { cnvoVNetEntry 1 }

cnvoVNetIpMcastAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "This object indicates the type of Internet address to be
        used as Multicast Group Address."
    ::= { cnvoVNetEntry 2 }

cnvoVNetIpMcastAddr OBJECT-TYPE
    SYNTAX InetAddress
--    Rsyntax OCTET STRING(SIZE(0..255))
    ACCESS read-write
    STATUS mandatory
    DESCRIPTION
        "This object specifies the Internet address to be used as
        Multicast Group Address.
        
        The type of this address is determined by
        cnvoVNetIpMcastAddrType."
    ::= { cnvoVNetEntry 3 }

cnvoVNetVlan OBJECT-TYPE
    SYNTAX VlanIndexOrZero
--    Rsyntax INTEGER(0..4095)
    ACCESS read-write
    STATUS mandatory
    DESCRIPTION
        "This object specifies the mapping vlan for the
        virtual network."
    ::= { cnvoVNetEntry 4 }

cnvoVNetArpSuppression OBJECT-TYPE
    SYNTAX INTEGER {
        arpSupON(1),
        arpSupOFF(2)
        }
    ACCESS read-write
    STATUS mandatory
    DESCRIPTION
        "This object specifies if ARP seppression is turned ON/OFF
        for the virtual network."
    ::= { cnvoVNetEntry 5 }

cnvoVNetReplication OBJECT-TYPE
    SYNTAX INTEGER {
        mcast(1),
        unconf(2),
        ucastBgp(3),
        ucastStatic(4)
        }
    ACCESS read-write
    STATUS mandatory
    DESCRIPTION
        "This object specifies the replication mode of the virtual
        network identifier."
    ::= { cnvoVNetEntry 6 }

cnvoVNetHostReachability OBJECT-TYPE
    SYNTAX INTEGER {
        unknown(1),
        hostReachabilityUnconf(2),
        dataPlaneL2(3),
        controlPlaneL3(4)
        }
    ACCESS read-write
    STATUS mandatory
    DESCRIPTION
        "This object specifies if the virtual network
        identifier is configured via data plane, control 
        plane or is unconfigured."
    ::= { cnvoVNetEntry 7 }

cnvoVNetVniType OBJECT-TYPE
    SYNTAX INTEGER {
        unknown(1),
        l2(2),
        l3(3)
        }
    ACCESS read-write
    STATUS mandatory
    DESCRIPTION
        "This object specifies the type of the virtual
        network identifier - unknown, L2 or L3."
    ::= { cnvoVNetEntry 8 }

cnvoVNetIpVrfOrBridgeDomainName OBJECT-TYPE
    SYNTAX SnmpAdminString
--    Rsyntax OCTET STRING(SIZE(0..255))
    ACCESS read-write
    STATUS mandatory
    DESCRIPTION
        "This object specifies the ip vrf (for L3 vni)
        or bridge-domain name (for L2 vni)
        virtual network identifier"
    ::= { cnvoVNetEntry 9 }

cnvoVNetRouterMacAddr OBJECT-TYPE
    SYNTAX InetAddress
--    Rsyntax OCTET STRING(SIZE(0..255))
    ACCESS read-only
    STATUS mandatory
    DESCRIPTION
        "This object indicates the hardware MAC of the
        physical router."
    ::= { cnvoVNetEntry 10 }

cnvoPeerTable OBJECT-TYPE
    SYNTAX SEQUENCE OF CnvoPeerEntry
    ACCESS not-accessible
    STATUS mandatory
    DESCRIPTION
        "This table provides information of remote peers
        for virtual network overlay on this system."
    ::= { cnvoNvoObjects 3 }

cnvoPeerEntry OBJECT-TYPE
    SYNTAX CnvoPeerEntry
    ACCESS not-accessible
    STATUS mandatory
    DESCRIPTION
        "An entry containing remote peer information
        for virtual network overlay."
    INDEX { cnvoNvoInstanceId, cnvoPeerIpAddrType, cnvoPeerIpAddr }
    ::= { cnvoPeerTable 1 }

CnvoPeerEntry ::= SEQUENCE {
    cnvoPeerIpAddrType InetAddressType,
    cnvoPeerIpAddr InetAddress,
    cnvoPeerUpTime DateAndTime,
    cnvoPeerLearningSourceType INTEGER
    }

cnvoPeerIpAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS not-accessible
    STATUS mandatory
    DESCRIPTION
        "This object indicates the type of Internet address of
        NVO peer."
    ::= { cnvoPeerEntry 1 }

cnvoPeerIpAddr OBJECT-TYPE
    SYNTAX InetAddress(SIZE(1..64))
--    Rsyntax OCTET STRING(SIZE(1..64))
    ACCESS not-accessible
    STATUS mandatory
    DESCRIPTION
        "This object indicates the Internet address of NVO peer.
        
        The type of this address is determined by
        cnvoPeerIpAddrType."
    ::= { cnvoPeerEntry 2 }

cnvoPeerUpTime OBJECT-TYPE
    SYNTAX DateAndTime
--    Rsyntax OCTET STRING(SIZE(8|11))
    ACCESS read-only
    STATUS mandatory
    DESCRIPTION
        "This object indicates the time at which the peer became up.
        This object contains value 0x0000010100000000 when the
        NVO peer is down."
    ::= { cnvoPeerEntry 3 }

cnvoPeerLearningSourceType OBJECT-TYPE
    SYNTAX INTEGER {
        unknown(1),
        dataPlane(2),
        controlPlane(3)
        }
    ACCESS read-only
    STATUS mandatory
    DESCRIPTION
        "This object indicates the way in which in peer was
        learnt - either via data plane or control plane."
    ::= { cnvoPeerEntry 4 }

cnvoVNetStatsTable OBJECT-TYPE
    SYNTAX SEQUENCE OF CnvoVNetStatsEntry
    ACCESS not-accessible
    STATUS mandatory
    DESCRIPTION
        "This table provides statistics information of virtual
        networks on the system."
    ::= { cnvoNvoObjects 4 }

cnvoVNetStatsEntry OBJECT-TYPE
    SYNTAX CnvoVNetStatsEntry
    ACCESS not-accessible
    STATUS mandatory
    DESCRIPTION
        "An entry containing statistics information for a
        virtual network."
    INDEX { cnvoNvoInstanceId, cnvoVNetLocalVNetId }
    ::= { cnvoVNetStatsTable 1 }

CnvoVNetStatsEntry ::= SEQUENCE {
    cnvoVNetOutUnicastPackets Counter,
    cnvoVNetOutUnicastBytes Counter,
    cnvoVNetOutMulticastPackets Counter,
    cnvoVNetOutMulticastBytes Counter,
    cnvoVNetInUnicastPackets Counter,
    cnvoVNetInUnicastBytes Counter,
    cnvoVNetInMulticastPackets Counter,
    cnvoVNetInMulticastBytes Counter
    }

cnvoVNetOutUnicastPackets OBJECT-TYPE
    SYNTAX --?? syntax is not convertable to SMIv1
           Counter
    ACCESS read-only
    STATUS mandatory
    DESCRIPTION
        "This object indicates the total number of unicast
        packets transmitted out of this virtual network."
    ::= { cnvoVNetStatsEntry 1 }

cnvoVNetOutUnicastBytes OBJECT-TYPE
    SYNTAX --?? syntax is not convertable to SMIv1
           Counter
    ACCESS read-only
    STATUS mandatory
    DESCRIPTION
        "This object indicates the number of bytes for unicast
        packet transmitted out of this virtual network."
    ::= { cnvoVNetStatsEntry 2 }

cnvoVNetOutMulticastPackets OBJECT-TYPE
    SYNTAX --?? syntax is not convertable to SMIv1
           Counter
    ACCESS read-only
    STATUS mandatory
    DESCRIPTION
        "This object indicates the number of multicast packets
        transmitted out of this virtual network."
    ::= { cnvoVNetStatsEntry 3 }

cnvoVNetOutMulticastBytes OBJECT-TYPE
    SYNTAX --?? syntax is not convertable to SMIv1
           Counter
    ACCESS read-only
    STATUS mandatory
    DESCRIPTION
        "This object indicates the number of bytes for multicast
        packet transmitted of this virtual network."
    ::= { cnvoVNetStatsEntry 4 }

cnvoVNetInUnicastPackets OBJECT-TYPE
    SYNTAX --?? syntax is not convertable to SMIv1
           Counter
    ACCESS read-only
    STATUS mandatory
    DESCRIPTION
        "This object indicates the number of unicast packets
        received by this virtual network."
    ::= { cnvoVNetStatsEntry 5 }

cnvoVNetInUnicastBytes OBJECT-TYPE
    SYNTAX --?? syntax is not convertable to SMIv1
           Counter
    ACCESS read-only
    STATUS mandatory
    DESCRIPTION
        "This object indicates the number of bytes for unicast
        packet received by this virtual network."
    ::= { cnvoVNetStatsEntry 6 }

cnvoVNetInMulticastPackets OBJECT-TYPE
    SYNTAX --?? syntax is not convertable to SMIv1
           Counter
    ACCESS read-only
    STATUS mandatory
    DESCRIPTION
        "This object indicates the number of multicast packets
        received by this virtual network."
    ::= { cnvoVNetStatsEntry 7 }

cnvoVNetInMulticastBytes OBJECT-TYPE
    SYNTAX --?? syntax is not convertable to SMIv1
           Counter
    ACCESS read-only
    STATUS mandatory
    DESCRIPTION
        "This object indicates the number of bytes for multicast
        packet received by this virtual network."
    ::= { cnvoVNetStatsEntry 8 }

cnvoNvoPeerStatsTable OBJECT-TYPE
    SYNTAX SEQUENCE OF CnvoNvoPeerStatsEntry
    ACCESS not-accessible
    STATUS mandatory
    DESCRIPTION
        "This table provides remote peers statistics information
        for virtual network overlay."
    ::= { cnvoNvoObjects 5 }

cnvoNvoPeerStatsEntry OBJECT-TYPE
    SYNTAX CnvoNvoPeerStatsEntry
    ACCESS not-accessible
    STATUS mandatory
    DESCRIPTION
        "An entry containing statistics information for a
        particular peer of a virtual network overlay."
    INDEX { cnvoNvoInstanceId, cnvoPeerIpAddrType, cnvoPeerIpAddr }
    ::= { cnvoNvoPeerStatsTable 1 }

CnvoNvoPeerStatsEntry ::= SEQUENCE {
    cnvoNvoPeerOutUnicastPackets Counter,
    cnvoNvoPeerOutUnicastBytes Counter,
    cnvoNvoPeerOutMulticastPackets Counter,
    cnvoNvoPeerOutMulticastBytes Counter,
    cnvoNvoPeerInUnicastPackets Counter,
    cnvoNvoPeerInUnicastBytes Counter,
    cnvoNvoPeerInMulticastPackets Counter,
    cnvoNvoPeerInMulticastBytes Counter
    }

cnvoNvoPeerOutUnicastPackets OBJECT-TYPE
    SYNTAX --?? syntax is not convertable to SMIv1
           Counter
    ACCESS read-only
    STATUS mandatory
    DESCRIPTION
        "This object indicates the number of unicast packets
        transmitted to the peer."
    ::= { cnvoNvoPeerStatsEntry 1 }

cnvoNvoPeerOutUnicastBytes OBJECT-TYPE
    SYNTAX --?? syntax is not convertable to SMIv1
           Counter
    ACCESS read-only
    STATUS mandatory
    DESCRIPTION
        "This object indicates the number of bytes for unicast
        packet transmitted to the peer."
    ::= { cnvoNvoPeerStatsEntry 2 }

cnvoNvoPeerOutMulticastPackets OBJECT-TYPE
    SYNTAX --?? syntax is not convertable to SMIv1
           Counter
    ACCESS read-only
    STATUS mandatory
    DESCRIPTION
        "This object indicates the number of multicast packets
        transmitted to the peer."
    ::= { cnvoNvoPeerStatsEntry 3 }

cnvoNvoPeerOutMulticastBytes OBJECT-TYPE
    SYNTAX --?? syntax is not convertable to SMIv1
           Counter
    ACCESS read-only
    STATUS mandatory
    DESCRIPTION
        "This object indicates the number of bytes for multicast
        packet transmitted to the peer."
    ::= { cnvoNvoPeerStatsEntry 4 }

cnvoNvoPeerInUnicastPackets OBJECT-TYPE
    SYNTAX --?? syntax is not convertable to SMIv1
           Counter
    ACCESS read-only
    STATUS mandatory
    DESCRIPTION
        "This object indicates the number of unicast packets
        received from the peer."
    ::= { cnvoNvoPeerStatsEntry 5 }

cnvoNvoPeerInUnicastBytes OBJECT-TYPE
    SYNTAX --?? syntax is not convertable to SMIv1
           Counter
    ACCESS read-only
    STATUS mandatory
    DESCRIPTION
        "This object indicates the number of bytes for unicast
        packet received from the peer."
    ::= { cnvoNvoPeerStatsEntry 6 }

cnvoNvoPeerInMulticastPackets OBJECT-TYPE
    SYNTAX --?? syntax is not convertable to SMIv1
           Counter
    ACCESS read-only
    STATUS mandatory
    DESCRIPTION
        "This object indicates the number of multicast packets
        received from the peer."
    ::= { cnvoNvoPeerStatsEntry 7 }

cnvoNvoPeerInMulticastBytes OBJECT-TYPE
    SYNTAX --?? syntax is not convertable to SMIv1
           Counter
    ACCESS read-only
    STATUS mandatory
    DESCRIPTION
        "This object indicates the number of bytes for multicast
        packet received from the peer."
    ::= { cnvoNvoPeerStatsEntry 8 }

cnvoNvoGroup OBJECT IDENTIFIER ::= { cnvoMIBGroups 1 }
-- OBJECT-GROUP
--  Status
--    mandatory
--  Descr
--    A collection of objects providing NVO information.
--  objects
--    cnvoNvoEncapType, cnvoNvoSourceInterface, 
--    cnvoNvoConfiguredVni, cnvoNvoStorageType, cnvoNvoRowStatus

cnvoVirtualNetworkGroup OBJECT IDENTIFIER ::= { cnvoMIBGroups 2 }
-- OBJECT-GROUP
--  Status
--    mandatory
--  Descr
--    A collection of objects providing VNI status information.
--  objects
--    cnvoVNetIpMcastAddrType, cnvoVNetIpMcastAddr, cnvoVNetVlan, 
--    cnvoVNetArpSuppression, cnvoVNetReplication, 
--    cnvoVNetHostReachability, cnvoVNetVniType, 
--    cnvoVNetIpVrfOrBridgeDomainName, cnvoVNetRouterMacAddr

cnvoPeerGroup OBJECT IDENTIFIER ::= { cnvoMIBGroups 3 }
-- OBJECT-GROUP
--  Status
--    mandatory
--  Descr
--    A collection of objects providing NVO peer information.
--  objects
--    cnvoPeerUpTime, cnvoPeerLearningSourceType

cnvoVirtualNetworkStatsGroup OBJECT IDENTIFIER ::= { cnvoMIBGroups 4 }
-- OBJECT-GROUP
--  Status
--    mandatory
--  Descr
--    A collection of objects providing virtual network
--    statistics information.
--  objects
--    cnvoVNetOutUnicastPackets, cnvoVNetOutUnicastBytes, 
--    cnvoVNetOutMulticastPackets, cnvoVNetOutMulticastBytes, 
--    cnvoVNetInUnicastPackets, cnvoVNetInUnicastBytes, 
--    cnvoVNetInMulticastPackets, cnvoVNetInMulticastBytes

cnvoNvoPerPeerOutUnicastStatsGroup OBJECT IDENTIFIER ::= { cnvoMIBGroups 5 }
-- OBJECT-GROUP
--  Status
--    mandatory
--  Descr
--    A collection of objects providing transmitted peer unicast
--    statistics information.
--  objects
--    cnvoNvoPeerOutUnicastPackets, cnvoNvoPeerOutUnicastBytes

cnvoNvoPerPeerInUnicastStatsGroup OBJECT IDENTIFIER ::= { cnvoMIBGroups 6 }
-- OBJECT-GROUP
--  Status
--    mandatory
--  Descr
--    A collection of objects providing received peer unicast
--    statistics information.
--  objects
--    cnvoNvoPeerInUnicastPackets, cnvoNvoPeerInUnicastBytes

cnvoNvoPerPeerInMulticastStatsGroup OBJECT IDENTIFIER ::= { cnvoMIBGroups 7 }
-- OBJECT-GROUP
--  Status
--    mandatory
--  Descr
--    A collection of objects providing received peer multicast
--    statistics information.
--  objects
--    cnvoNvoPeerInMulticastPackets, cnvoNvoPeerInMulticastBytes

cnvoNvoPerPeerOutMulticastStatsGroup OBJECT IDENTIFIER ::= { cnvoMIBGroups 8 }
-- OBJECT-GROUP
--  Status
--    mandatory
--  Descr
--    A collection of objects providing transmitted peer unicast
--    statistics information.
--  objects
--    cnvoNvoPeerOutMulticastPackets, cnvoNvoPeerOutMulticastBytes

cnvoMIBCompliance OBJECT IDENTIFIER ::= { cnvoMIBCompliances 1 }
-- MODULE-COMPLIANCE
--  Status
--    mandatory
--  Descr
--    The compliance statement for CISCO-NETWORK-VIRTUALIZATION-
--    OVERLAY-MIB.
--  Module
--    >>current<<
--   MandGroup
--    cnvoNvoGroup
--   MandGroup
--    cnvoVirtualNetworkGroup
--   MandGroup
--    cnvoPeerGroup
--   OptGroup
--    cnvoVirtualNetworkStatsGroup
--   OptGroup
--    cnvoNvoPerPeerOutUnicastStatsGroup
--   OptGroup
--    cnvoNvoPerPeerOutMulticastStatsGroup
--   OptGroup
--    cnvoNvoPerPeerInUnicastStatsGroup
--   OptGroup
--    cnvoNvoPerPeerInMulticastStatsGroup
--   ObjVar
--    cnvoNvoEncapType
--   ObjVar
--    cnvoNvoSourceInterface
--   ObjVar
--    cnvoNvoStorageType
--   ObjVar
--    cnvoNvoRowStatus


END
