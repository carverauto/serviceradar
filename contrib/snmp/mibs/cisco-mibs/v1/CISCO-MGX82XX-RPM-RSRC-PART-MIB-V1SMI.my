-- MIB file created 09-Oct-2002 21:04:44, by
--   SMICng version 2.2.11-beta(PRO)(Solaris), January 20, 2001. Enterprise key cisco.com

CISCO-MGX82XX-RPM-RSRC-PART-MIB DEFINITIONS ::= BEGIN

-- From file: "CISCO-MGX82XX-RPM-RSRC-PART-MIB.my"
-- Compile options "4 7 F H N W 03 06 0B 0G 0N 0T"

IMPORTS
    rpmInterface
            FROM BASIS-MIB
    ciscoWan
            FROM CISCOWAN-SMI
    OBJECT-TYPE
            FROM RFC-1212;

ciscoMgx82xxRpmRsrcPartMIB OBJECT IDENTIFIER ::= { ciscoWan 61 }
-- MODULE-IDENTITY
--  LastUpdated
--    200209170000Z
--  OrgName
--    Cisco Systems, Inc.
--  ContactInfo
--    Cisco Systems
--     Customer Service
--    
--    Postal: 170 W Tasman Drive
--     San Jose, CA  95134
--     USA
--    
--    Tel: +1 800 553-NETS
--    
--    E-mail: cs-wanatm@cisco.com
--  Descr
--    The MIB module to manage resource partition objects. 
--    A resource partition is configured on a RPM subinterface.
--    An administrator can partition connection related 
--    resources like VPI, VCI ranges, bandwidth and total 
--    amount of available connection entries in the switch 
--    through these MIB tables.
--  RevDate
--    200209170000Z
--  RevDescr
--    Initial version of the MIB.
--    
--    The content of this MIB was originally available
--    in CISCO-WAN-AXIPOP-MIB defined using SMIv1.
--    The applicable objects from CISCO-WAN-AXIPOP-MIB
--    are defined using SMIv2 in this MIB. Also the
--    descriptions of some of the objects have been 
--    modified.

rpmIfCnfResPart OBJECT IDENTIFIER ::= { rpmInterface 2 }
cmrRsrcPartMIBConformance OBJECT IDENTIFIER ::= { ciscoMgx82xxRpmRsrcPartMIB 3 }
cmrRsrcPartMIBCompliances OBJECT IDENTIFIER ::= { cmrRsrcPartMIBConformance 1 }
cmrRsrcPartMIBGroups OBJECT IDENTIFIER ::= { cmrRsrcPartMIBConformance 2 }

rpmIfCnfRscPartTable OBJECT-TYPE
    SYNTAX SEQUENCE OF RpmIfCnfRscPartEntry
    ACCESS not-accessible
    STATUS mandatory
    DESCRIPTION
        "The table is for RPM interface 
        resource partition."
    ::= { rpmIfCnfResPart 1 }

rpmIfCnfRscPartEntry OBJECT-TYPE
    SYNTAX RpmIfCnfRscPartEntry
    ACCESS not-accessible
    STATUS mandatory
    DESCRIPTION
        "An entry for resource partition configuration
        on a logical interface. A resource partition need
        to be configured before connections(or connection endpoints)
        can be added to the interface."
    INDEX { rpmIfRscSlotNum, rpmIfRscPartIfNum, rpmIfRscPartCtrlrNum }
    ::= { rpmIfCnfRscPartTable 1 }

RpmIfCnfRscPartEntry ::= SEQUENCE {
    rpmIfRscSlotNum INTEGER,
    rpmIfRscPartIfNum INTEGER,
    rpmIfRscPartCtrlrNum INTEGER,
    rpmIfRscPrtRowStatus INTEGER,
    rpmIfRscPrtIngrPctBandwidth INTEGER,
    rpmIfRscPrtEgrPctBandwidth INTEGER,
    rpmIfRscPrtVpiLow INTEGER,
    rpmIfRscPrtVpiHigh INTEGER,
    rpmIfRscPrtVciLow INTEGER,
    rpmIfRscPrtVciHigh INTEGER,
    rpmIfRscPrtMaxChans INTEGER
    }

rpmIfRscSlotNum OBJECT-TYPE
    SYNTAX INTEGER(1..30)
    ACCESS read-only
    STATUS mandatory
    DESCRIPTION
        "This object identifies the slot number of the 
        RPM card in MGX shelf."
    ::= { rpmIfCnfRscPartEntry 1 }

rpmIfRscPartIfNum OBJECT-TYPE
    SYNTAX INTEGER(1..2147483647)
    ACCESS read-only
    STATUS mandatory
    DESCRIPTION
        "This is backplane interface number.
        Currently there is only one interface and value
        1 is the only value supported."
    ::= { rpmIfCnfRscPartEntry 2 }

rpmIfRscPartCtrlrNum OBJECT-TYPE
    SYNTAX INTEGER {
        par(1),
        pnni(2),
        tag(3)
        }
    ACCESS read-only
    STATUS mandatory
    DESCRIPTION
        "This object identifies the type of the controller
        which owns the resource partition.
        
         par(1) : Portable Auto Route Controller. This is a controller
                  software implementing Cisco Proprietary protocol
                  for network routing and topology.
        
         pnni(2): Private Network-to-Network Interface(PNNI)
                  controller. This is a controller implementing
                  ATM Forum PNNI protocol for routing.
        
         tag(3) : Tag Switching(MPLS) controller. This is
                  a controller supporting MPLS protocol."
    ::= { rpmIfCnfRscPartEntry 3 }

rpmIfRscPrtRowStatus OBJECT-TYPE
    SYNTAX INTEGER {
        add(1),
        del(2),
        mod(3)
        }
    ACCESS read-only
    STATUS mandatory
    DESCRIPTION
        "This object contains the information on whether
        subinterface exists or being modified.
        
        add(1)  : sub-interface exists
        del(2)  : sub-interface deleted
        mod(2)  : sub-interface being modified"
    DEFVAL { del }
    ::= { rpmIfCnfRscPartEntry 4 }

rpmIfRscPrtIngrPctBandwidth OBJECT-TYPE
    SYNTAX INTEGER(0..100)
    ACCESS read-only
    STATUS mandatory
    DESCRIPTION
        "The percentage of logical interface bandwidth."
    DEFVAL { 0 }
    ::= { rpmIfCnfRscPartEntry 5 }

rpmIfRscPrtEgrPctBandwidth OBJECT-TYPE
    SYNTAX INTEGER(0..100)
    ACCESS read-only
    STATUS mandatory
    DESCRIPTION
        "The percentage of logical interface bandwidth."
    DEFVAL { 0 }
    ::= { rpmIfCnfRscPartEntry 6 }

rpmIfRscPrtVpiLow OBJECT-TYPE
    SYNTAX INTEGER(0..255)
    ACCESS read-only
    STATUS mandatory
    DESCRIPTION
        "The beginning of the VPI range 
        reserved for this partition."
    ::= { rpmIfCnfRscPartEntry 7 }

rpmIfRscPrtVpiHigh OBJECT-TYPE
    SYNTAX INTEGER(0..255)
    ACCESS read-only
    STATUS mandatory
    DESCRIPTION
        "The end of the VPI range 
        reserved for this partition."
    ::= { rpmIfCnfRscPartEntry 8 }

rpmIfRscPrtVciLow OBJECT-TYPE
    SYNTAX INTEGER(0..65535)
    ACCESS read-only
    STATUS mandatory
    DESCRIPTION
        "The beginning of the VCI range reserved
        for this partition.  This field is only 
        valid for logical interfaces configured 
        with a single VPI."
    ::= { rpmIfCnfRscPartEntry 9 }

rpmIfRscPrtVciHigh OBJECT-TYPE
    SYNTAX INTEGER(0..65535)
    ACCESS read-only
    STATUS mandatory
    DESCRIPTION
        "The end of the VCI range reserved 
        for this partition.  This field is 
        only valid for logical interfaces 
        configured with a single VPI."
    ::= { rpmIfCnfRscPartEntry 10 }

rpmIfRscPrtMaxChans OBJECT-TYPE
    SYNTAX INTEGER(0..4047)
    ACCESS read-only
    STATUS mandatory
    DESCRIPTION
        "This represents maximum number of 
        channels(connections) that are available 
        to the controller."
    ::= { rpmIfCnfRscPartEntry 11 }

cmrRsrcPartMIBGroup OBJECT IDENTIFIER ::= { cmrRsrcPartMIBGroups 1 }
-- OBJECT-GROUP
--  Status
--    mandatory
--  Descr
--    The collection of objects related to
--    configuration of Resource partition.
--  objects
--    rpmIfRscSlotNum, rpmIfRscPartIfNum, rpmIfRscPartCtrlrNum, 
--    rpmIfRscPrtRowStatus, rpmIfRscPrtIngrPctBandwidth, 
--    rpmIfRscPrtEgrPctBandwidth, rpmIfRscPrtVpiLow, 
--    rpmIfRscPrtVpiHigh, rpmIfRscPrtVciLow, rpmIfRscPrtVciHigh, 
--    rpmIfRscPrtMaxChans

cmrRsrcPartMIBCompliance OBJECT IDENTIFIER ::= { cmrRsrcPartMIBCompliances 1 }
-- MODULE-COMPLIANCE
--  Status
--    mandatory
--  Descr
--    The Compliance statement for Resource partition 
--     management group.
--  Module
--    >>current<<
--   MandGroup
--    cmrRsrcPartMIBGroup


END
