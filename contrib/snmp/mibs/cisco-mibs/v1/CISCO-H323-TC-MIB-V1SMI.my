-- MIB created 7/11/100 13:43:06, by
--   SMIC (the next generation) version 1.6.29, November 22, 1994.

CISCO-H323-TC-MIB DEFINITIONS ::= BEGIN

-- From file: "CISCO-H323-TC-MIB.my"

IMPORTS
    ciscoExperiment
            FROM CISCO-SMI;

ciscoH323TCMIB OBJECT IDENTIFIER ::= { ciscoExperiment 41 }
-- MODULE-IDENTITY
--  LastUpdated
--    200003100000Z
--  OrgName
--    Cisco Systems, Inc
--  ContactInfo
--            Cisco Systems
--             Customer Service
--    
--           Postal:  170 West Tasman Drive
--                    San Jose, CA  95134
--                    USA
--    
--           Tel:    +1 800 553-NETS
--    
--           E-mail: h323-support@cisco.com
--  Descr
--    The MIB Module defines a common set of Textual Conventions used
--    in mib modules supporting ITU-T H.323.0 and ITU-T H.225.0
--    Recommendations.
--  RevDate
--    9810091200Z
--  RevDescr
--    The initial version of the mib.
--  RevDate
--    200003100000Z
--  RevDescr
--    Removed CgkUtf8String as it is a duplicate definition of
--     SnmpAdminString.

CgkIA5String ::= OCTET STRING(SIZE(1..128))
-- TEXTUAL-CONVENTION
--  DspHint
--    128a
--  Status
--    mandatory
--  Descr
--    Corresponds to an IA5String.

CgkE164String ::= OCTET STRING(SIZE(1..128))
-- TEXTUAL-CONVENTION
--  DspHint
--    128a
--  Status
--    mandatory
--  Descr
--    An IA5String limited to the character set '0123456789*#,.' 

CgkTAddressTag ::= INTEGER {
--        other(0),
        ipv4(1),
        ipv6(2),
        ipx(3),
        nsap(4)
        }
-- TEXTUAL-CONVENTION
--  Status
--    mandatory
--  Descr
--    A tag to identify the type of the transport address contained 
--    in the TAddress data type.  The values correlate to the 
--    TransportAddress defined in the H.225.0 V2 ITU protocol
--    specification. The tag indicates how to interpret the value of
--    a TAddress data type defined in this specification.  All
--    TAddress values are in network byte order 
--    
--                    TAddress size       TAddress contents
--             ipv4      6 octets         IPv4 (4 octets), port (2 octets)
--             ipv6     18                IPv6 (16), port (2)
--             ipx      12                net (4), node (6), port (2)
--             nsap     1-20              nsap(1-20)
--             netbios  16                netbios(16)
--     

CgkNAddressTag ::= INTEGER {
--        other(0),
        ipv4(1),
        ipv6(2),
        ipx(3),
        nsap(4)
        }
-- TEXTUAL-CONVENTION
--  Status
--    mandatory
--  Descr
--    A tag to identify the type of the network address contained in the
--    CgkNAddress textual convention defined in this specification.  All
--    CgkNAddress values are in network byte order. 
--    
--                           NAddress size
--                    ipv4      4 octets
--                    ipv6     16
--                    ipx      10                net (4), node (6)
--                    nsap     1-20              nsap(1-20)
--           

CgkNAddress ::= OCTET STRING(SIZE(1..128))
-- TEXTUAL-CONVENTION
--  Status
--    mandatory
--  Descr
--    Denotes a network address.  An object defined with this syntax
--    must have a corresponding CgkNAddressTag object which identifies
--    the actual size and type.

CgkGlobalIdentifier ::= OCTET STRING(SIZE(16))
-- TEXTUAL-CONVENTION
--  Status
--    mandatory
--  Descr
--    A 16 octet field containing a unique identifier.  The
--    identifier contains the following fields:
--    
--       60 bit       nanosecond time (octets 0-6, low 4 bits of octet 7)
--       4  bit       version  (hi 4 bits of octet 7)
--       3  octet     0 (a variant field)
--       1  octet     hi 2bits 0, low 6bits clock sequence.
--       6  octet     MAC Address 
--    
--    See Reference for generation of this value.
--  Refer
--    ITU-T H225.0, Version 2 section 7.6

CgkAliasTag ::= INTEGER {
--        other(0),
        e164(1),
        h323Id(2),
        urlId(3),
        transportId(4),
        emailId(5),
        partyNumber(6)
        }
-- TEXTUAL-CONVENTION
--  Status
--    mandatory
--  Descr
--    A tag to identify the type of the Alias address contained in
--     the CgkAliasAddress data type.  The values correlate to the 
--     AliasAddress defined in the H.225.0 V2 ITU protocol specification. 
--     The tag indicates how to interpret the value of an AliasAddress 
--     data type defined in that specification.
--    
--                          AliasAddress contents
--             other        unknown
--             e164         CgkE164String
--             h323Id       CgkUtf8String
--             urlId        CgkIA5String containing a URL
--             transportId  CgkTAddressTag, TAddress
--             emailId      CgkIA5String containing e-mail address
--             partyNumber  contains PartyNumber (E164String)

CgkAliasAddress ::= OCTET STRING(SIZE(1..512))
-- TEXTUAL-CONVENTION
--  DspHint
--    512a
--  Status
--    mandatory
--  Descr
--    A data type corresponding to AliasAddress defined in H.225.0. 
--    The value of an object of this type has the syntax and
--    symantics identified by CgkAliasTag.  An object defined as
--    CgkAliasAddress must have a corresponding CgkAliasTag object.
--  Refer
--    ITU-T H225.0 Version 2 ANNEX H - H.225.0 Message Syntax (ASN.1)

CgkEndpointID ::= OCTET STRING(SIZE(1..128))
-- TEXTUAL-CONVENTION
--  Status
--    mandatory
--  Descr
--    A CgkUtf8String corresponding to EndpointIdentifer defined
--    in H.225.
--  Refer
--    ITU-T H225.0 Version 2 ANNEX H - H.225.0 Message Syntax (ASN.1)

CgkGatekeeperID ::= OCTET STRING(SIZE(1..128))
-- TEXTUAL-CONVENTION
--  Status
--    mandatory
--  Descr
--    A CgkUtf8String corresponding to GatekeeperIdentifier defined
--    in H.225.
--  Refer
--    ITU-T H225.0 Version 2 ANNEX H - H.225.0 Message Syntax (ASN.1)


END
