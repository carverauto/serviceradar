-- MIB file created 27-Feb-2009 10:11:20, by
--   SMICng version 2.2.11-beta(PRO)(Solaris), January 20, 2001. Enterprise key cisco.com

CISCO-RSCN-MIB DEFINITIONS ::= BEGIN

-- From file: "CISCO-RSCN-MIB.my"
-- Compile options "4 7 F H N O W 03 06 0B 0G 0N 0T"

IMPORTS
    TruthValue
            FROM SNMPv2-TC-v1
    FcAddressId
            FROM CISCO-ST-TC
    vsanIndex
            FROM CISCO-VSAN-MIB
    FcGs3RejectReasonCode
            FROM CISCO-NS-MIB
    ciscoMgmt
            FROM CISCO-SMI
    Counter, Gauge
            FROM RFC1155-SMI
    OBJECT-TYPE
            FROM RFC-1212
    TRAP-TYPE
            FROM RFC-1215;

ciscoRscnMIB OBJECT IDENTIFIER ::= { ciscoMgmt 292 }
-- MODULE-IDENTITY
--  LastUpdated
--    200809010000Z
--  OrgName
--    Cisco Systems Inc.
--  ContactInfo
--    Cisco Systems 
--    Customer Service 
--    Postal: 170 W Tasman Drive 
--    San Jose, CA  95134 
--    USA 
--    Tel: +1 800 553 -NETS 
--    E-mail: cs-san@cisco.com
--  Descr
--    The MIB module for the management of the Fibre 
--    Channel's Registered State Change Notification  
--    (RSCN) functionality, which is specified by 
--    FC-FLA and FC-FS. 
--    GLOSSARY : 
--    RSCN    - Registered State Change Notification. 
--              RSCN Notifications are sent to Nx_ports 
--              and other switches to notify that an event 
--              has occured. 
--    SW_RSCN - Switch Registered State Change Notification. 
--              SW_RSCN Notifications are sent to neighbouring 
--              switches in a fabric to notify that an 
--              event has occured. 
--     ELS    - Extended Link Service. 
--              RSCN Software module uses ELS frame formats  
--              to send RSCN messages. 
--     ILS    - Inter Link Service. 
--              RSCN Software module uses ILS frame formats 
--              to send SW-RSCN messages.
--  RevDate
--    200809010000Z
--  RevDescr
--    modified rscnEventTov range from '1..2000' to '0.2000'.
--  RevDate
--    200608170000Z
--  RevDescr
--    Added following notifications 
--    -rscnIlsRxRejectReqNotify 
--    -rscnElsRxRejectReqNotify 
--    
--    Added 2 new notification control objects: 
--    - rscnIlsRxRejectReqNotifyEnable 
--    - rscnElsRxRejectReqNotifyEnable 
--    
--    Added rscnNotifyControlGroupSup1 OBJECT-GROUP 
--    Added rscnRejectNotifyGroup NOTIFICATION-GROUP 
--    Added rscnMIBComplianceRev3 MODULE-COMPLIANCE
--  RevDate
--    200505060000Z
--  RevDescr
--    Added rscnEventTovTable.
--  RevDate
--    200310160000Z
--  RevDescr
--    Added rscnMultiPidTable.
--  RevDate
--    200209200000Z
--  RevDescr
--    Initial version of this MIB module.

ciscoRscnMIBObjects OBJECT IDENTIFIER ::= { ciscoRscnMIB 1 }
rscnMIBConformance OBJECT IDENTIFIER ::= { ciscoRscnMIB 2 }
rscnConfiguration OBJECT IDENTIFIER ::= { ciscoRscnMIBObjects 1 }
rscnStats       OBJECT IDENTIFIER ::= { ciscoRscnMIBObjects 2 }
rscnInformation OBJECT IDENTIFIER ::= { ciscoRscnMIBObjects 3 }
rscnNotification OBJECT IDENTIFIER ::= { ciscoRscnMIBObjects 4 }
rscnNotifications OBJECT IDENTIFIER ::= { rscnNotification 0 }
rscnMIBCompliances OBJECT IDENTIFIER ::= { rscnMIBConformance 1 }
rscnMIBGroups   OBJECT IDENTIFIER ::= { rscnMIBConformance 2 }

rscnScrNumber OBJECT-TYPE
    SYNTAX INTEGER(0..2147483647)
    ACCESS read-only
    STATUS mandatory
    DESCRIPTION
        "The number of Nx_Ports currently registered 
        to receive RSCNs."
    ::= { rscnConfiguration 1 }

rscnScrTable OBJECT-TYPE
    SYNTAX SEQUENCE OF RscnScrEntry
    ACCESS not-accessible
    STATUS mandatory
    DESCRIPTION
        "A table of Nx_Ports that have registered to 
        receive RSCNs on all VSANs configured on the  
        local switch."
    ::= { rscnConfiguration 2 }

rscnScrEntry OBJECT-TYPE
    SYNTAX RscnScrEntry
    ACCESS not-accessible
    STATUS mandatory
    DESCRIPTION
        "An entry (conceptual row) containing information 
        about one Nx_Port which has registered to receive 
        RSCNs on the VSAN indicated by vsanIndex."
    INDEX { vsanIndex, rscnScrFcId }
    ::= { rscnScrTable 1 }

RscnScrEntry ::= SEQUENCE {
    rscnScrFcId FcAddressId,
    rscnScrRegType INTEGER
    }

rscnScrFcId OBJECT-TYPE
    SYNTAX FcAddressId
--    Rsyntax OCTET STRING(SIZE(3))
    ACCESS not-accessible
    STATUS mandatory
    DESCRIPTION
        "The Fibre Channel Identifier (FC-ID) of the 
        subscribing Nx_Port."
    ::= { rscnScrEntry 1 }

rscnScrRegType OBJECT-TYPE
    SYNTAX INTEGER {
        fromFabricCtrlr(1),
        fromNxPort(2),
        fromBoth(3)
        }
    ACCESS read-only
    STATUS mandatory
    DESCRIPTION
        "This object indicates the type of registration 
        desired by the subscriber. 
        
        'fromFabricCtrlr' indicates RSCNs generated by the  
        Fabric Controller. 
        
        'fromNxPort' indicates RSCNs generated by  
        Nx_Ports. 
        
        'fromBoth' indicates RSCNs generated by Fabric 
        Controller and Nx_Ports."
    ::= { rscnScrEntry 2 }

rscnScrTotalRejects OBJECT-TYPE
    SYNTAX Counter
    ACCESS read-only
    STATUS mandatory
    DESCRIPTION
        "The total number of SCRs rejected 
        across all VSANs by the local switch."
    ::= { rscnStats 1 }

rscnRscnReqTotalRejects OBJECT-TYPE
    SYNTAX Counter
    ACCESS read-only
    STATUS mandatory
    DESCRIPTION
        "The total number of RSCN requests rejected 
        across all VSANs by the local switch."
    ::= { rscnStats 2 }

rscnSwRscnReqTotalRejects OBJECT-TYPE
    SYNTAX Counter
    ACCESS read-only
    STATUS mandatory
    DESCRIPTION
        "The total number of SW_RSCN requests rejected 
        across all VSANs by the local switch."
    ::= { rscnStats 3 }

rscnStatsTable OBJECT-TYPE
    SYNTAX SEQUENCE OF RscnStatsEntry
    ACCESS not-accessible
    STATUS mandatory
    DESCRIPTION
        "The statistics related to the RSCN module. The 
        statistics are maintained per VSAN."
    ::= { rscnStats 4 }

rscnStatsEntry OBJECT-TYPE
    SYNTAX RscnStatsEntry
    ACCESS not-accessible
    STATUS mandatory
    DESCRIPTION
        "An entry (conceptual row) in this table."
    INDEX { vsanIndex }
    ::= { rscnStatsTable 1 }

RscnStatsEntry ::= SEQUENCE {
    rscnRxScrs Counter,
    rscnRxRscns Counter,
    rscnTxRscns Counter,
    rscnRxSwRscns Counter,
    rscnTxSwRscns Counter,
    rscnScrRej Counter,
    rscnRscnReqRej Counter,
    rscnSwRscnReqRej Counter
    }

rscnRxScrs OBJECT-TYPE
    SYNTAX Counter
    ACCESS read-only
    STATUS mandatory
    DESCRIPTION
        "The number of SCRs received from Nx_Ports 
        on this VSAN."
    ::= { rscnStatsEntry 1 }

rscnRxRscns OBJECT-TYPE
    SYNTAX Counter
    ACCESS read-only
    STATUS mandatory
    DESCRIPTION
        "The number of RSCNs from Nx_Ports received on 
        this VSAN."
    ::= { rscnStatsEntry 2 }

rscnTxRscns OBJECT-TYPE
    SYNTAX Counter
    ACCESS read-only
    STATUS mandatory
    DESCRIPTION
        "The total number of RSCNs transmitted on this 
        VSAN."
    ::= { rscnStatsEntry 3 }

rscnRxSwRscns OBJECT-TYPE
    SYNTAX Counter
    ACCESS read-only
    STATUS mandatory
    DESCRIPTION
        "The number of Inter-Switch Registered State 
        Change Notifications (SW_RSCN) received on this 
        VSAN from other switches."
    ::= { rscnStatsEntry 4 }

rscnTxSwRscns OBJECT-TYPE
    SYNTAX Counter
    ACCESS read-only
    STATUS mandatory
    DESCRIPTION
        "The number of Inter-Switch Registered State 
        Change Notifications (SW_RSCN) transmitted 
        on this VSAN to other switches."
    ::= { rscnStatsEntry 5 }

rscnScrRej OBJECT-TYPE
    SYNTAX Counter
    ACCESS read-only
    STATUS mandatory
    DESCRIPTION
        "The number of SCR rejected on this VSAN."
    ::= { rscnStatsEntry 6 }

rscnRscnReqRej OBJECT-TYPE
    SYNTAX Counter
    ACCESS read-only
    STATUS mandatory
    DESCRIPTION
        "The number of RSCN requests rejected on this VSAN."
    ::= { rscnStatsEntry 7 }

rscnSwRscnReqRej OBJECT-TYPE
    SYNTAX Counter
    ACCESS read-only
    STATUS mandatory
    DESCRIPTION
        "The number of SW_RSCN requests rejected on this VSAN."
    ::= { rscnStatsEntry 8 }

rscnIlsRejReasonCode OBJECT-TYPE
    SYNTAX FcGs3RejectReasonCode
--    Rsyntax INTEGER {
--        none(1),
--        invalidCmdCode(2),
--        invalidVerLevel(3),
--        logicalError(4),
--        invalidIUSize(5),
--        logicalBusy(6),
--        protocolError(7),
--        unableToPerformCmdReq(8),
--        cmdNotSupported(9),
--        vendorError(10)
--        }
    ACCESS read-only
    STATUS mandatory
    DESCRIPTION
        "The reason code corresponding to an ILS 
        request rejection. This object contains the  
        reason code corresponding to the most recent  
        SCR or RSCN  request rejection by the RSCN  
        module."
    ::= { rscnInformation 1 }

rscnElsRejReasonCode OBJECT-TYPE
    SYNTAX FcGs3RejectReasonCode
--    Rsyntax INTEGER {
--        none(1),
--        invalidCmdCode(2),
--        invalidVerLevel(3),
--        logicalError(4),
--        invalidIUSize(5),
--        logicalBusy(6),
--        protocolError(7),
--        unableToPerformCmdReq(8),
--        cmdNotSupported(9),
--        vendorError(10)
--        }
    ACCESS read-only
    STATUS mandatory
    DESCRIPTION
        "The reason code corresponding to an ELS 
        request rejection. This object contains the 
        reason code corresponding the most recent 
        SW_RSCN request rejection by the RSCN module."
    ::= { rscnInformation 2 }

rscnIlsRejectReqNotifyEnable OBJECT-TYPE
    SYNTAX TruthValue
--    Rsyntax INTEGER {
--        true(1),
--        false(2)
--        }
    ACCESS read-write
    STATUS mandatory
    DESCRIPTION
        "This object specifies if the RSCN module should 
        generate 'rscnIlsRejectReqNotify' notifications. 
        
        If value of this object is 'true', then the  
        notification is generated when a SW_RSCN request  
        is rejected. 
        
        If it is 'false', the notification is not generated."
    DEFVAL { false }
    ::= { rscnConfiguration 3 }

rscnElsRejectReqNotifyEnable OBJECT-TYPE
    SYNTAX TruthValue
--    Rsyntax INTEGER {
--        true(1),
--        false(2)
--        }
    ACCESS read-write
    STATUS mandatory
    DESCRIPTION
        "This object specifies if the RSCN module should 
        generate 'rscnElsRejectReqNotify' notifications. 
        
        If value of this object is 'true', then  the  
        notification is generated when a SCR or RSCN request  
        is rejected.  
        
        If it is 'false', the notification is not generated."
    DEFVAL { false }
    ::= { rscnConfiguration 4 }

rscnNotifyFcId OBJECT-TYPE
    SYNTAX FcAddressId
--    Rsyntax OCTET STRING(SIZE(3))
    ACCESS not-accessible
    STATUS mandatory
    DESCRIPTION
        "The FC-ID of an Nx_Port. 
        This object is to be used in the notifications: 
        rscnElsRejectReqNotify, rscnIlsRejectReqNotify, 
        rscnElsRxRejectReqNotify and rscnIlsRxRejectReqNotify. 
        This object is defined since the rscnScrFcId 
        object in the rscnScrTable is not-accessible."
    ::= { rscnConfiguration 5 }

rscnMultiPidTable OBJECT-TYPE
    SYNTAX SEQUENCE OF RscnMultiPidEntry
    ACCESS not-accessible
    STATUS mandatory
    DESCRIPTION
        "This table contains the configuration information 
        for multi-pid option for all VSANs on the local 
        device."
    ::= { rscnConfiguration 6 }

rscnMultiPidEntry OBJECT-TYPE
    SYNTAX RscnMultiPidEntry
    ACCESS not-accessible
    STATUS mandatory
    DESCRIPTION
        "An entry (conceptual row) in this table."
    INDEX { vsanIndex }
    ::= { rscnMultiPidTable 1 }

RscnMultiPidEntry ::= SEQUENCE {
    rscnMultiPidEnable TruthValue
    }

rscnMultiPidEnable OBJECT-TYPE
    SYNTAX TruthValue
--    Rsyntax INTEGER {
--        true(1),
--        false(2)
--        }
    ACCESS read-write
    STATUS mandatory
    DESCRIPTION
        "This object specifies whether the multi-pid 
        option is enabled on this VSAN. 
        
        If this object is set to 'true', then the  
        multi-pid option is enabled. If this object is  
        set to 'false, then the multi-pid option is  
        disabled. 
        
        If the multi-pid option is enabled, then RSCNs 
        generated to the registered Nx ports may contain 
        more than one affected port ID. By enabling this 
        option, the number of RSCNs generated can be  
        reduced."
    DEFVAL { false }
    ::= { rscnMultiPidEntry 1 }

rscnEventTovTable OBJECT-TYPE
    SYNTAX SEQUENCE OF RscnEventTovEntry
    ACCESS not-accessible
    STATUS mandatory
    DESCRIPTION
        "This table contains the configuration information 
        for Event Time Out Value option for all VSANs on  
        the local device. The Event TOV value is used to 
        send the coalesced RSCNs to the registered user."
    ::= { rscnConfiguration 7 }

rscnEventTovEntry OBJECT-TYPE
    SYNTAX RscnEventTovEntry
    ACCESS not-accessible
    STATUS mandatory
    DESCRIPTION
        "An entry (conceptual row) in this table represents 
        the Event Time out value on a VSAN."
    INDEX { vsanIndex }
    ::= { rscnEventTovTable 1 }

RscnEventTovEntry ::= SEQUENCE {
    rscnEventTov Gauge
    }

rscnEventTov OBJECT-TYPE
    SYNTAX Gauge(0..2000)
--  Units
--    milli-secs
    ACCESS read-write
    STATUS mandatory
    DESCRIPTION
        "This object specifies the event time-out value 
        configured for the VSAN. This timeout value  
        corresponds to the coalescing timeout. 
        This object is used to merge a number of RSCNs  
        into a single frame and send them out when   
        timer expires. The value of zero indicates that  
        frames will not be coalesced."
    DEFVAL { 2000 }
    ::= { rscnEventTovEntry 1 }

rscnIlsRxRejectReqNotifyEnable OBJECT-TYPE
    SYNTAX TruthValue
--    Rsyntax INTEGER {
--        true(1),
--        false(2)
--        }
    ACCESS read-write
    STATUS mandatory
    DESCRIPTION
        "This object specifies if the RSCN module should 
        generate 'rscnIlsRxRejectReqNotify' notifications. 
        
        If value of this object is 'true', then 
        the notification is generated when a SW_RSCN 
        that is rejected by another device is received 
        on the local device. 
        
        If it is 'false', the notification is not generated."
    DEFVAL { false }
    ::= { rscnConfiguration 8 }

rscnElsRxRejectReqNotifyEnable OBJECT-TYPE
    SYNTAX TruthValue
--    Rsyntax INTEGER {
--        true(1),
--        false(2)
--        }
    ACCESS read-write
    STATUS mandatory
    DESCRIPTION
        "This object specifies if the RSCN module should 
        generate 'rscnElsRxRejectReqNotify' notifications. 
        
        If value of this object is 'true', then the 
        notification is generated when a RSCN request that is 
        rejected by another device is received on the local 
        device. 
        
        If it is 'false', the notification is not generated."
    DEFVAL { false }
    ::= { rscnConfiguration 9 }

rscnElsRejectReqNotify TRAP-TYPE
-- Reverse mappable trap
    ENTERPRISE rscnNotification
    VARIABLES {
        rscnElsRejReasonCode, rscnNotifyFcId }
--  Status
--    mandatory
    DESCRIPTION
        "This notification is generated by the RSCN module 
        on this switch whenever it rejects a SCR or RSCN  
        request. 
        
        The rscnScrFcId object indicates the FC-ID of the  
        sender of the request that was rejected."
    ::= 1

rscnIlsRejectReqNotify TRAP-TYPE
-- Reverse mappable trap
    ENTERPRISE rscnNotification
    VARIABLES {
        rscnIlsRejReasonCode, rscnNotifyFcId }
--  Status
--    mandatory
    DESCRIPTION
        "This notification is generated by the RSCN module 
        on this switch whenever it rejects a SW_RSCN  
        request. 
        
        The rscnScrFcId object contains the FC-ID of the 
        sender of the request that was rejected."
    ::= 2

rscnElsRxRejectReqNotify TRAP-TYPE
-- Reverse mappable trap
    ENTERPRISE rscnNotification
    VARIABLES {
        rscnElsRejReasonCode, rscnNotifyFcId }
--  Status
--    mandatory
    DESCRIPTION
        "This notification is generated by the RSCN module 
        on this switch whenever it receives a rejected  
        RSCN request. 
        
        The rscnScrFcId object indicates the FC-ID of the  
        sender where the request was rejected."
    ::= 3

rscnIlsRxRejectReqNotify TRAP-TYPE
-- Reverse mappable trap
    ENTERPRISE rscnNotification
    VARIABLES {
        rscnIlsRejReasonCode, rscnNotifyFcId }
--  Status
--    mandatory
    DESCRIPTION
        "This notification is generated by the RSCN module 
        on this switch whenever it receives a rejected  
        SW_RSCN request. 
        
        The rscnScrFcId object contains the FC-ID of the 
        sender where the request was rejected."
    ::= 4

rscnConfigGroup OBJECT IDENTIFIER ::= { rscnMIBGroups 1 }
-- OBJECT-GROUP
--  Status
--    deprecated
--  Descr
--    A collection of objects for configuring 
--    and displaying SCR entries.
--  objects
--    rscnScrNumber, rscnScrRegType, rscnNotifyFcId

rscnStatsGroup OBJECT IDENTIFIER ::= { rscnMIBGroups 2 }
-- OBJECT-GROUP
--  Status
--    mandatory
--  Descr
--    A collection of objects for displaying 
--    RSCN statistics.
--  objects
--    rscnScrTotalRejects, rscnRscnReqTotalRejects, 
--    rscnSwRscnReqTotalRejects, rscnRxScrs, rscnRxRscns, 
--    rscnTxRscns, rscnRxSwRscns, rscnTxSwRscns, rscnScrRej, 
--    rscnRscnReqRej, rscnSwRscnReqRej

rscnNotifyControlGroup OBJECT IDENTIFIER ::= { rscnMIBGroups 3 }
-- OBJECT-GROUP
--  Status
--    mandatory
--  Descr
--    A collection of notification control and 
--    notification information objects.
--  objects
--    rscnIlsRejReasonCode, rscnElsRejReasonCode, 
--    rscnIlsRejectReqNotifyEnable, rscnElsRejectReqNotifyEnable

rscnConfigGroupRev1 OBJECT IDENTIFIER ::= { rscnMIBGroups 5 }
-- OBJECT-GROUP
--  Status
--    mandatory
--  Descr
--    A collection of objects for configuring 
--    and displaying SCR entries and multi-pid 
--    option.
--  objects
--    rscnScrNumber, rscnScrRegType, rscnNotifyFcId, 
--    rscnMultiPidEnable

rscnConfigGroupRev1Sup1 OBJECT IDENTIFIER ::= { rscnMIBGroups 6 }
-- OBJECT-GROUP
--  Status
--    mandatory
--  Descr
--    A collection of object(s) for configuring 
--    the Event time out option.
--  objects
--    rscnEventTov

rscnNotifyControlGroupSup1 OBJECT IDENTIFIER ::= { rscnMIBGroups 8 }
-- OBJECT-GROUP
--  Status
--    mandatory
--  Descr
--    A collection of notification control objects.
--  objects
--    rscnIlsRxRejectReqNotifyEnable, 
--    rscnElsRxRejectReqNotifyEnable

rscnNotifyGroup OBJECT IDENTIFIER ::= { rscnMIBGroups 4 }
-- NOTIFICATION-GROUP
--  Status
--    mandatory
--  Descr
--    A collection of notifications for monitoring 
--    ILS and ELS request rejection by the RSCN 
--    module.
--  notifications
--    rscnIlsRejectReqNotify, rscnElsRejectReqNotify

rscnRejectNotifyGroup OBJECT IDENTIFIER ::= { rscnMIBGroups 7 }
-- NOTIFICATION-GROUP
--  Status
--    mandatory
--  Descr
--    A collection of notifications for monitoring 
--    ILS and ELS request rejection by other switches/  
--    devices.
--  notifications
--    rscnIlsRxRejectReqNotify, rscnElsRxRejectReqNotify

rscnMIBCompliance OBJECT IDENTIFIER ::= { rscnMIBCompliances 1 }
-- MODULE-COMPLIANCE
--  Status
--    deprecated
--  Descr
--    The compliance statement for entities which 
--    implement RSCN feature.
--  Module
--    >>current<<
--   MandGroup
--    rscnConfigGroup
--   MandGroup
--    rscnStatsGroup
--   MandGroup
--    rscnNotifyControlGroup
--   MandGroup
--    rscnNotifyGroup

rscnMIBComplianceRev1 OBJECT IDENTIFIER ::= { rscnMIBCompliances 2 }
-- MODULE-COMPLIANCE
--  Status
--    deprecated
--  Descr
--    The compliance statement for entities which 
--    implement RSCN feature.
--  Module
--    >>current<<
--   MandGroup
--    rscnConfigGroupRev1
--   MandGroup
--    rscnStatsGroup
--   MandGroup
--    rscnNotifyControlGroup
--   MandGroup
--    rscnNotifyGroup

rscnMIBComplianceRev2 OBJECT IDENTIFIER ::= { rscnMIBCompliances 3 }
-- MODULE-COMPLIANCE
--  Status
--    deprecated
--  Descr
--    The compliance statement for entities which 
--    implement RSCN feature.
--  Module
--    >>current<<
--   MandGroup
--    rscnConfigGroupRev1
--   MandGroup
--    rscnStatsGroup
--   MandGroup
--    rscnNotifyControlGroup
--   MandGroup
--    rscnNotifyGroup
--   MandGroup
--    rscnConfigGroupRev1Sup1

rscnMIBComplianceRev3 OBJECT IDENTIFIER ::= { rscnMIBCompliances 4 }
-- MODULE-COMPLIANCE
--  Status
--    mandatory
--  Descr
--    The compliance statement for entities which 
--    implement RSCN feature.
--  Module
--    >>current<<
--   MandGroup
--    rscnConfigGroupRev1
--   MandGroup
--    rscnStatsGroup
--   MandGroup
--    rscnNotifyControlGroup
--   MandGroup
--    rscnNotifyGroup
--   MandGroup
--    rscnConfigGroupRev1Sup1
--   MandGroup
--    rscnRejectNotifyGroup
--   MandGroup
--    rscnNotifyControlGroupSup1


END
