-- MIB file created 16-May-2003 10:10:29, by
--   SMICng version 2.2.11-beta(PRO)(Solaris), January 20, 2001. Enterprise key cisco.com

BASIS-SERIAL-MIB DEFINITIONS ::= BEGIN

-- From file: "BASIS-SERIAL-MIB.my"
-- Compile options "4 7 F H N W 03 06 0B 0G 0N 0T"

IMPORTS
    basisLines
            FROM BASIS-MIB
    ciscoWan
            FROM CISCOWAN-SMI
    OBJECT-TYPE
            FROM RFC-1212;

basisSerialMIB OBJECT IDENTIFIER ::= { ciscoWan 69 }
-- MODULE-IDENTITY
--  LastUpdated
--    200305030000Z
--  OrgName
--    Cisco Systems, Inc.
--  ContactInfo
--           Cisco Systems
--                Customer Service
--    
--        Postal: 170 W Tasman Drive
--                San Jose, CA  95134
--                USA
--    
--                Tel: +1 800 553-NETS
--    
--        E-mail: cs-wanatm@cisco.com
--  Descr
--    The MIB module to configure serial ports
--    in Processor Module and different Service 
--    Modules(cards) in MGX8850,MGX8250 and MGX8220
--    ATM Edge switches.
--  RevDate
--    200305030000Z
--  RevDescr
--    Initial version of the MIB.
--    
--    The content of this MIB was originally available
--    in CISCO-WAN-AXIPOP-MIB defined using SMIv1.
--    The applicable objects from CISCO-WAN-AXIPOP-MIB
--    are defined using SMIv2 in this MIB. Also the
--    descriptions of some of the objects have been 
--    modified.

serialInterface OBJECT IDENTIFIER ::= { basisLines 1 }
basisSerialMIBConformance OBJECT IDENTIFIER ::= { basisSerialMIB 2 }
basisSerialMIBGroups OBJECT IDENTIFIER ::= { basisSerialMIBConformance 1 }
basisSerialMIBCompliances OBJECT IDENTIFIER ::= { basisSerialMIBConformance 2 }

serialPortNumOfValidEntries OBJECT-TYPE
    SYNTAX INTEGER(1..2)
    ACCESS read-only
    STATUS mandatory
    DESCRIPTION
        "This object contains number of serial ports.
        This identifies the number of entries in
        serialInterfacetable."
    ::= { serialInterface 2 }

serialInterfaceTable OBJECT-TYPE
    SYNTAX SEQUENCE OF SerialInterfaceEntry
    ACCESS not-accessible
    STATUS mandatory
    DESCRIPTION
        "This table represents Physical serial interfaces in
        the module."
    ::= { serialInterface 1 }

serialInterfaceEntry OBJECT-TYPE
    SYNTAX SerialInterfaceEntry
    ACCESS not-accessible
    STATUS mandatory
    DESCRIPTION
        "An entry for each serial interface. 
        Each entry contains information on
        port type, port speed."
    INDEX { serialPortNum }
    ::= { serialInterfaceTable 1 }

SerialInterfaceEntry ::= SEQUENCE {
    serialPortNum INTEGER,
    serialPortType INTEGER,
    serialPortEnable INTEGER,
    serialPortbps INTEGER
    }

serialPortNum OBJECT-TYPE
    SYNTAX INTEGER(1..2)
    ACCESS read-only
    STATUS mandatory
    DESCRIPTION
        "This object identifies the serial port number.
        
        The value 1 is used for Console Port.
        The Console Port is also known as control port(CP).
        
        The value 2 is used for Maintenance Port
        and this can be used as SLIP
        (Serial Line Internet Protocol) interface.
        The Maintenance Port is also known as 
        Modem Port(MP)."
    ::= { serialInterfaceEntry 1 }

serialPortType OBJECT-TYPE
    SYNTAX INTEGER {
        main(1),
        debug(2)
        }
    ACCESS read-only
    STATUS mandatory
    DESCRIPTION
        "This object identifies the type of port.
        
        main(1)  : This is applicable for Maintenance Port
        debug(2) : This is applicable for Console Port."
    ::= { serialInterfaceEntry 2 }

serialPortEnable OBJECT-TYPE
    SYNTAX INTEGER {
        disable(1),
        enable(2)
        }
    ACCESS read-write
    STATUS mandatory
    DESCRIPTION
        "This object is used for enabling/disabling
        serial port."
    ::= { serialInterfaceEntry 3 }

serialPortbps OBJECT-TYPE
    SYNTAX INTEGER {
        bps9600(1),
        bps2400(2),
        bps19200(3)
        }
    ACCESS read-write
    STATUS mandatory
    DESCRIPTION
        "This object identifies the baud rate of the ports."
    DEFVAL { bps9600 }
    ::= { serialInterfaceEntry 4 }

basisSerialConfGroup OBJECT IDENTIFIER ::= { basisSerialMIBGroups 1 }
-- OBJECT-GROUP
--  Status
--    mandatory
--  Descr
--    The collection of objects which are used to represent
--    serial ports.
--  objects
--    serialPortNumOfValidEntries, serialPortNum, serialPortType, 
--    serialPortEnable, serialPortbps

basisSerialCompliance OBJECT IDENTIFIER ::= { basisSerialMIBCompliances 1 }
-- MODULE-COMPLIANCE
--  Status
--    mandatory
--  Descr
--    The compliance statement for objects related
--    to Serial Ports.
--  Module
--    >>current<<
--   MandGroup
--    basisSerialConfGroup


END
