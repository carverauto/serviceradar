-- MIB file created 17-Feb-2014 11:09:59, by
--   SMICng version 2.2.11-beta(PRO)(Solaris), January 20, 2001. Enterprise key cisco.com

CISCO-TRUSTSEC-MIB DEFINITIONS ::= BEGIN

-- From file: "CISCO-TRUSTSEC-MIB.my"
-- Compile options "4 7 F H N W 03 06 0B 0G 0N 0T"

IMPORTS
    TruthValue, DateAndTime, RowStatus
            FROM SNMPv2-TC-v1
    SnmpAdminString
            FROM SNMP-FRAMEWORK-MIB
    CtsSecurityGroupTag, CtsGenerationId, CtsPasswordEncryptionType, 
    CtsAcsAuthorityIdentity, CtsCredentialRecordType
            FROM CISCO-TRUSTSEC-TC-MIB
    ciscoMgmt
            FROM CISCO-SMI
    Counter, Gauge
            FROM RFC1155-SMI
    OBJECT-TYPE
            FROM RFC-1212
    TRAP-TYPE
            FROM RFC-1215;

ciscoTrustSecMIB OBJECT IDENTIFIER ::= { ciscoMgmt 730 }
-- MODULE-IDENTITY
--  LastUpdated
--    201401300000Z
--  OrgName
--    Cisco Systems, Inc.
--  ContactInfo
--    Cisco Systems
--    Customer Service
--    
--    Postal: 170 W Tasman Drive
--    San Jose, CA  95134
--    USA
--    
--    Tel: +1 800 553-NETS
--    
--    E-mail: cs-lan-switch-snmp@cisco.com
--  Descr
--    This MIB module is for the configuration of a network
--    device on the Cisco Trusted Security (TrustSec) system.
--    
--    TrustSec secures a network fabric by authenticating and
--    authorizing each device connecting to the network, allowing for
--    the encryption, authentication and replay protection of data
--    traffic on a hop by hop basis.
--    
--    Glossary :
--    
--    TrustSec - Cisco Trusted Security
--    
--    EAP-FAST - Extensible Authentication Protocol-Flexible
--               Authentication via Secure Tunneling (RFC 4851)
--    
--    PAC - Protected Access Credential
--          A credential dynamically downloaded from the
--          Access Control Server.
--    
--    ACS - Access Control Server
--    
--    SGT - Security Group Tag
--          A tag identifying its source, assigned to a packet on
--          ingress to a TrustSec cloud, and used to determine
--          security and other policy to be applied to it along
--          its path through the cloud.
--  RevDate
--    201401300000Z
--  RevDescr
--    Added following OBJECT-GROUP
--    - ciscoTrustSecCrtclAuthGroup
--    Added new compliance
--    - ciscoTrustSecMIBCompliance4.
--  RevDate
--    201209260000Z
--  RevDescr
--    Added following OBJECT-GROUP
--    - ciscoTrustSecSwKeystoreNotifsInfoGroup
--    - ciscoTrustSecSwKeystoreNotifsControlGroup
--    - ciscoTrustSecSwKeystoreNotifsGroup
--    - ciscoTrustSecFileErrNotifsInfoGroup
--    - ciscoTrustSecNotifsMessageStringInfoGroup
--    - ciscoTrustSecCacheFileNotifsControlGroup
--    - ciscoTrustSecCacheFileNotifsGroup
--    - ciscoTrustSecCtrDrbgNotifsControlGroup
--    - ciscoTrustSecCtrDrbgNotifsGroup
--    Added new compliance
--    - ciscoTrustSecMIBCompliance3.
--  RevDate
--    201103150000Z
--  RevDescr
--    Added support for ciscoTrustSecEnvSecGroupNameGroup.
--  RevDate
--    201009210000Z
--  RevDescr
--    Initial version of this MIB module.

ciscoTrustSecMIBNotifs OBJECT IDENTIFIER ::= { ciscoTrustSecMIB 0 }
ciscoTrustSecMIBObjects OBJECT IDENTIFIER ::= { ciscoTrustSecMIB 1 }
ciscoTrustSecMIBConform OBJECT IDENTIFIER ::= { ciscoTrustSecMIB 2 }
ctsCacheObjects OBJECT IDENTIFIER ::= { ciscoTrustSecMIBObjects 1 }
ctsSgtObjects   OBJECT IDENTIFIER ::= { ciscoTrustSecMIBObjects 2 }
ctsCredentialObjects OBJECT IDENTIFIER ::= { ciscoTrustSecMIBObjects 3 }
ctsEnvironmentDataObjects OBJECT IDENTIFIER ::= { ciscoTrustSecMIBObjects 4 }
ctsNotifsControlObjects OBJECT IDENTIFIER ::= { ciscoTrustSecMIBObjects 5 }
ctsNotifsInfoObjects OBJECT IDENTIFIER ::= { ciscoTrustSecMIBObjects 6 }
ctsCriticalAuthObjects OBJECT IDENTIFIER ::= { ciscoTrustSecMIBObjects 7 }
ciscoTrustSecMIBCompliances OBJECT IDENTIFIER ::= { ciscoTrustSecMIBConform 1 }
ciscoTrustSecMIBGroups OBJECT IDENTIFIER ::= { ciscoTrustSecMIBConform 2 }

ctsCacheEnabled OBJECT-TYPE
    SYNTAX TruthValue
--    Rsyntax INTEGER {
--        true(1),
--        false(2)
--        }
    ACCESS read-write
    STATUS mandatory
    DESCRIPTION
        "This object specifies if the TrustSec cache is enabled in
        the system."
    ::= { ctsCacheObjects 1 }

ctsCacheNvStorage OBJECT-TYPE
    SYNTAX SnmpAdminString
--    Rsyntax OCTET STRING(SIZE(0..255))
    ACCESS read-write
    STATUS mandatory
    DESCRIPTION
        "The object specifies the location on the device
        where TrustSec cache files will be created.
        
        The location may be specified in <device>:[directory] format,
        where <device> can be (but not limited to): bootdisk:, disk0:,
        disk1:.
        
        A zero length string for this object indicates that no location
        has been configured and system will decide the location of
        TrustSec cache files."
    ::= { ctsCacheObjects 2 }

ctsCacheClear OBJECT-TYPE
    SYNTAX INTEGER {
        none(1),
        all(2),
        authzPolicies(3),
        authzPoliciesPeer(4),
        authzPoliciesSgt(5),
        environmentData(6),
        interfaceController(7)
        }
    ACCESS read-write
    STATUS mandatory
    DESCRIPTION
        "This object allows user to clear the cache files for
        Cisco Trusted Security feature on this device.
        
        When read, this object always returns the value 'none'.
        
        'none'              - No operation.
        'all'               - Clear all the cached information
        'authzPolicies'     - Clear all the cached authorization
                              policies.
        'authzPoliciesPeer' - Clear the cached peer authorization
                              policies.
        'authzPoliciesSgt'  - Clear the cached SGT authorization
                              policies.
        'environmentData'   - Clear the cached environment data
        'interfaceController' - Clear the cached interface controller
                                data."
    ::= { ctsCacheObjects 3 }

ctsSecurityGroupTagId OBJECT-TYPE
    SYNTAX CtsSecurityGroupTag
--    Rsyntax Gauge(0..65535)
    ACCESS read-write
    STATUS mandatory
    DESCRIPTION
        "This object allows user to specify the SGT for the packets
        originating from this device.
        
        A value of zero for this object indicates that no SGT has been
        configured."
    ::= { ctsSgtObjects 1 }

ctsSgtAssignmentMethod OBJECT-TYPE
    SYNTAX INTEGER {
        none(1),
        ingress(2),
        egress(3)
        }
    ACCESS read-write
    STATUS mandatory
    DESCRIPTION
        "This object specifies the method used for assignment
        of TrustSec SGT for the line cards without TrustSec
        tagging capability.
        
        'none'    - assignment of TrustSec SGT is not enabled.
        
        'ingress' - 'ingress' method is used for the assignment of
                    TrustSec SGT.
        
        'egress'  - 'egress' method is used for the assignment of
                    TrustSec SGT."
    ::= { ctsSgtObjects 2 }

ctsDeviceId OBJECT-TYPE
    SYNTAX SnmpAdminString
--    Rsyntax OCTET STRING(SIZE(0..255))
    ACCESS read-write
    STATUS mandatory
    DESCRIPTION
        "This object allows user to specify the identifier for
        the device.
        
        This identifier and the device password (specified by
        ctsDevicePassword) are used together by the Cisco Trusted
        Security feature for authenticating the device.
        
        The value of this object must be set in the same PDU as
        ctsDevicePasswordType and ctsDevicePassword.
        
        The object may not be set to a zero length string.
        
        The system will return a zero length string for this object
        either when there is no value configured for this object or
        TrustSec credentials for the device have been cleared by
        setting ctsCredentialsClearAll to 'true'."
    ::= { ctsCredentialObjects 1 }

ctsDevicePasswordType OBJECT-TYPE
    SYNTAX CtsPasswordEncryptionType
--    Rsyntax INTEGER {
--        other(1),
--        none(2),
--        clearText(3),
--        typeSix(4),
--        typeSeven(5)
--        }
    ACCESS read-write
    STATUS mandatory
    DESCRIPTION
        "This object specifies the type of encryption employed
        to encrypt password in ctsDevicePassword object.
        
        Value for this object must be specified as 'clearText',
        'typeSix' or 'typeSeven' in order to configure the password in
        ctsDevicePassword.
        
        The value of this object must be set in the same PDU as
        ctsDevicePassword and ctsDeviceId.
        
        When read, value of this object must be 'none' if
        ctsDevicePassword is a zero length string.
        
        The value of this object may not be set to 'none' or 'other'."
    ::= { ctsCredentialObjects 2 }

ctsDevicePassword OBJECT-TYPE
    SYNTAX SnmpAdminString
--    Rsyntax OCTET STRING(SIZE(0..255))
    ACCESS read-write
    STATUS mandatory
    DESCRIPTION
        "This object allows user to specify the password for
        the device.
        
        This password and the device identifier (specified by
        ctsDeviceId) are used together by the Cisco Trusted Security
        feature for authenticating the device.
        
        The value of this object must be set in the same PDU as
        ctsDevicePasswordType and ctsDeviceId.
        
        The object may not be set to a zero length string.
        
        When read, this object always returns the value of a
        zero-length octet string."
    ::= { ctsCredentialObjects 3 }

ctsKeystoreType OBJECT-TYPE
    SYNTAX INTEGER {
        hardwareKeystore(1),
        softwareEmulation(2)
        }
    ACCESS read-only
    STATUS mandatory
    DESCRIPTION
        "This object indicates the type of keystore employed
        by the device.
        
        'hardwareKeystore'  - Keystore functionality is implemented
                              in hardware.
        'softwareEmulation' - Keystore functionality is emulated
                              in software."
    ::= { ctsCredentialObjects 4 }

ctsKeystoreFwVersion OBJECT-TYPE
    SYNTAX SnmpAdminString
--    Rsyntax OCTET STRING(SIZE(0..255))
    ACCESS read-only
    STATUS mandatory
    DESCRIPTION
        "This object indicates the firmware version of
        the hardware keystore.
        
        This object is only instantiated when the value of
        ctsKeystoreType is 'hardwareKeystore'."
    ::= { ctsCredentialObjects 5 }

ctsKeystoreFwAlerts OBJECT-TYPE
    SYNTAX Counter
    ACCESS read-only
    STATUS mandatory
    DESCRIPTION
        "This object indicates the number of hardware
        keystore alerts that occurred.
        
        This object is only instantiated when the value of
        ctsKeystoreType is 'hardwareKeystore'."
    ::= { ctsCredentialObjects 6 }

ctsKeystoreFwResets OBJECT-TYPE
    SYNTAX Counter
    ACCESS read-only
    STATUS mandatory
    DESCRIPTION
        "This object indicates the number of times
        the keystore firmware was reset.
        
        This object is only instantiated when the value of
        ctsKeystoreType is 'hardwareKeystore'."
    ::= { ctsCredentialObjects 7 }

ctsKeystoreRxTimeouts OBJECT-TYPE
    SYNTAX Counter
    ACCESS read-only
    STATUS mandatory
    DESCRIPTION
        "This object indicates the number of times the system
        timed out awaiting response from keystore firmware.
        
        This object is only instantiated when the value of
        ctsKeystoreType is 'hardwareKeystore'."
    ::= { ctsCredentialObjects 8 }

ctsKeystoreRxBadChecksums OBJECT-TYPE
    SYNTAX Counter
    ACCESS read-only
    STATUS mandatory
    DESCRIPTION
        "This object indicates the number of message fragments
        the system received from keystore firmware that had bad 
        checksum value.
        
        This object is only instantiated when the value of
        ctsKeystoreType is 'hardwareKeystore'."
    ::= { ctsCredentialObjects 9 }

ctsKeystoreRxBadFragmentLengths OBJECT-TYPE
    SYNTAX Counter
    ACCESS read-only
    STATUS mandatory
    DESCRIPTION
        "This object indicates the number of message fragments
        the system received from keystore firmware that had 
        illegal lengths.
        
        This object is only instantiated when the value of
        ctsKeystoreType is 'hardwareKeystore'."
    ::= { ctsCredentialObjects 10 }

ctsKeystoreCorruptions OBJECT-TYPE
    SYNTAX Counter
    ACCESS read-only
    STATUS mandatory
    DESCRIPTION
        "This object indicates the number of times keystore
        firmware reported detection of one or more corrupted 
        records in the hardware keystore.
        
        This object is only instantiated when the value of
        ctsKeystoreType is 'hardwareKeystore'."
    ::= { ctsCredentialObjects 11 }

ctsKeystorePasswordRecordTable OBJECT-TYPE
    SYNTAX SEQUENCE OF CtsKeystorePasswordRecordEntry
    ACCESS not-accessible
    STATUS mandatory
    DESCRIPTION
        "A list of Cisco Trusted Security password records stored in
        the hardware or software keystore of this device."
    ::= { ctsCredentialObjects 13 }

ctsKeystorePasswordRecordEntry OBJECT-TYPE
    SYNTAX CtsKeystorePasswordRecordEntry
    ACCESS not-accessible
    STATUS mandatory
    DESCRIPTION
        "An entry describing individual password record in the
        keystore of this device.
        
        An entry will be created or deleted from this table when a
        password record is added or removed from the keystore of
        this device."
    INDEX { --?? IMPLIED may cause problems
            IMPLIED ctsKeystorePasswordRecordName }
    ::= { ctsKeystorePasswordRecordTable 1 }

CtsKeystorePasswordRecordEntry ::= SEQUENCE {
    ctsKeystorePasswordRecordName SnmpAdminString,
    ctsKeystorePasswordRecordType CtsCredentialRecordType
    }

ctsKeystorePasswordRecordName OBJECT-TYPE
    SYNTAX SnmpAdminString(SIZE(1..64))
--    Rsyntax OCTET STRING(SIZE(1..64))
    ACCESS not-accessible
    STATUS mandatory
    DESCRIPTION
        "This object identifies a password record."
    ::= { ctsKeystorePasswordRecordEntry 1 }

ctsKeystorePasswordRecordType OBJECT-TYPE
    SYNTAX CtsCredentialRecordType
--    Rsyntax INTEGER {
--        simpleSecret(1),
--        pac(2)
--        }
    ACCESS read-only
    STATUS mandatory
    DESCRIPTION
        "This object indicates the type of credential in this record."
    ::= { ctsKeystorePasswordRecordEntry 2 }

ctsKeystorePacRecordTable OBJECT-TYPE
    SYNTAX SEQUENCE OF CtsKeystorePacRecordEntry
    ACCESS not-accessible
    STATUS mandatory
    DESCRIPTION
        "A list of Cisco Trusted Security PAC records stored in
        the hardware or software keystore of this device."
    ::= { ctsCredentialObjects 14 }

ctsKeystorePacRecordEntry OBJECT-TYPE
    SYNTAX CtsKeystorePacRecordEntry
    ACCESS not-accessible
    STATUS mandatory
    DESCRIPTION
        "An entry describing individual PAC record in the
        keystore of this device.
        
        An entry will be created or deleted by the system when a
        PAC record is added or removed from the keystore of this
        device."
    INDEX { --?? IMPLIED may cause problems
            IMPLIED ctsKeystorePacRecordName }
    ::= { ctsKeystorePacRecordTable 1 }

CtsKeystorePacRecordEntry ::= SEQUENCE {
    ctsKeystorePacRecordName CtsAcsAuthorityIdentity,
    ctsKeystorePacRecordType CtsCredentialRecordType
    }

ctsKeystorePacRecordName OBJECT-TYPE
    SYNTAX CtsAcsAuthorityIdentity(SIZE(1..64))
--    Rsyntax OCTET STRING(SIZE(1..64))
    ACCESS not-accessible
    STATUS mandatory
    DESCRIPTION
        "The name of this PAC record."
    ::= { ctsKeystorePacRecordEntry 1 }

ctsKeystorePacRecordType OBJECT-TYPE
    SYNTAX CtsCredentialRecordType
--    Rsyntax INTEGER {
--        simpleSecret(1),
--        pac(2)
--        }
    ACCESS read-only
    STATUS mandatory
    DESCRIPTION
        "This object indicates the type of credential in this record."
    ::= { ctsKeystorePacRecordEntry 2 }

ctsPacInfoTable OBJECT-TYPE
    SYNTAX SEQUENCE OF CtsPacInfoEntry
    ACCESS not-accessible
    STATUS mandatory
    DESCRIPTION
        "A list of PACs on this device."
    ::= { ctsCredentialObjects 15 }

ctsPacInfoEntry OBJECT-TYPE
    SYNTAX CtsPacInfoEntry
    ACCESS not-accessible
    STATUS mandatory
    DESCRIPTION
        "An entry providing management information of a particular PAC
        record.
        
        An entry can only be created dynamically by the system when
        a new PAC is installed in the keystore. An entry will be deleted
        from this table when the PAC is removed from the keystore by the
        system or by the user."
    INDEX { --?? IMPLIED may cause problems
            IMPLIED ctsPacAcsAuthId }
    ::= { ctsPacInfoTable 1 }

CtsPacInfoEntry ::= SEQUENCE {
    ctsPacAcsAuthId CtsAcsAuthorityIdentity,
    ctsPacAcsDescription SnmpAdminString,
    ctsPacType INTEGER,
    ctsPacExpirationTime DateAndTime,
    ctsPacTimeToRefresh Gauge,
    ctsPacStatus RowStatus
    }

ctsPacAcsAuthId OBJECT-TYPE
    SYNTAX CtsAcsAuthorityIdentity(SIZE(1..64))
--    Rsyntax OCTET STRING(SIZE(1..64))
    ACCESS not-accessible
    STATUS mandatory
    DESCRIPTION
        "This object indicates the unique authority identity of the
        ACS server from where the PAC was downloaded."
    ::= { ctsPacInfoEntry 1 }

ctsPacAcsDescription OBJECT-TYPE
    SYNTAX SnmpAdminString
--    Rsyntax OCTET STRING(SIZE(0..255))
    ACCESS read-only
    STATUS mandatory
    DESCRIPTION
        "This object indicates the description of the ACS server from
        where the PAC was downloaded."
    ::= { ctsPacInfoEntry 2 }

ctsPacType OBJECT-TYPE
    SYNTAX INTEGER {
        unknown(1),
        tunnel(2),
        machineAuthentication(3),
        userAuthorization(4),
        posture(5),
        ciscoTrustSec(6)
        }
    ACCESS read-only
    STATUS mandatory
    DESCRIPTION
        "This object indicates the type of PAC this entry represents.
        
        'unknown' -
         Any other type of PAC that is not covered below
        
        'tunnel' -
         Distributed shared secret between the peer and ACS that is
         used to establish a secure tunnel and convey the policy of
         what must and can occur in the tunnel.
        
        'machineAuthentication' -
         The Machine Authentication PAC contains information in the
         PAC opaque that identifies the machine.  It is meant to be
         used by a machine when network access is required and no user
         is logged in.
        
        'userAuthorization' -
         The User Authorization PAC contains information in the PAC
         opaque that identifies a user and provides authorization
         information.  The User Authorization PAC is used to provide
         user information during stateless session resumption so
         user authentication MAY be skipped.
        
        'posture' -
         Distributed posture checking and authorization result based
         on a previous posture validation.  A posture PAC can be used
         to optimize posture validation in the case of frequent
         revalidations.  This result is specific to the posture
         validation application and may be used outside the contents
         of EAP-FAST.
        
        'ciscoTrustSec' -
         A credential dynamically provisioned in phase 0 of EAP-FAST.
         It is used by Trustsec to set up secure communications with
         the server."
    ::= { ctsPacInfoEntry 3 }

ctsPacExpirationTime OBJECT-TYPE
    SYNTAX DateAndTime
--    Rsyntax OCTET STRING(SIZE(8|11))
    ACCESS read-only
    STATUS mandatory
    DESCRIPTION
        "This object indicates the time when this PAC will be expired."
    ::= { ctsPacInfoEntry 4 }

ctsPacTimeToRefresh OBJECT-TYPE
    SYNTAX Gauge
--  Units
--    seconds
    ACCESS read-only
    STATUS mandatory
    DESCRIPTION
        "This object indicates the time left for this PAC to be
        refreshed from the ACS."
    ::= { ctsPacInfoEntry 5 }

ctsPacStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to manage the deletion of rows
        in this table. This object only supports the values
        'active' and 'destroy'.
        
        Setting this object to 'destroy' deletes this PAC.
        
        When read, this object will always return 'active'."
    ::= { ctsPacInfoEntry 6 }

ctsCredentialsClearAll OBJECT-TYPE
    SYNTAX TruthValue
--    Rsyntax INTEGER {
--        true(1),
--        false(2)
--        }
    ACCESS read-write
    STATUS mandatory
    DESCRIPTION
        "This object allows user to clear all the PACs and Cisco
        Trusted Security credentials on the device.
        
        Setting the object to 'true' will clear all the PACs and
        credentials.
        
        When read, this object will always return 'false'."
    ::= { ctsCredentialObjects 16 }

ctsEnvDataLastDownloadStatus OBJECT-TYPE
    SYNTAX INTEGER {
        other(1),
        succeeded(2),
        failed(3),
        inprogress(4),
        incomplete(5),
        timedout(6),
        cleared(7)
        }
    ACCESS read-only
    STATUS mandatory
    DESCRIPTION
        "This object indicates the status of the last attempt to
        download the Environment Data.
        
        'other'     - Any other state not covered by below
                      enumerations.
        'succeeded' - Environment Data download completed successfully.
        'failed'    - Environment Data download failed.
        'inprogress'- Environment Data download is in progress.
        'incomplete'- Environment Data download is incomplete.
        'timedout'  - Environment Data download did not start and
                      timed out due to no response from the ACS.
        'cleared'   - Environment Data has been cleared by the user."
    ::= { ctsEnvironmentDataObjects 1 }

ctsEnvSecurityGroupTagId OBJECT-TYPE
    SYNTAX CtsSecurityGroupTag
--    Rsyntax Gauge(0..65535)
    ACCESS read-only
    STATUS mandatory
    DESCRIPTION
        "This object indicates the SGT for packets originating
        on this device downloaded from the ACS.
        
        A value of zero for this object indicates that no SGT has
        been downloaded from the ACS."
    ::= { ctsEnvironmentDataObjects 2 }

ctsEnvSecurityGroupTagGenId OBJECT-TYPE
    SYNTAX CtsGenerationId
--    Rsyntax OCTET STRING(SIZE(0..128))
    ACCESS read-only
    STATUS mandatory
    DESCRIPTION
        "This object indicates the generation identifier associated
        with the downloaded SGT on this device."
    ::= { ctsEnvironmentDataObjects 3 }

ctsEnvDataLastUpdate OBJECT-TYPE
    SYNTAX DateAndTime
--    Rsyntax OCTET STRING(SIZE(8|11))
    ACCESS read-only
    STATUS mandatory
    DESCRIPTION
        "This object indicates the last time Cisco Trusted Security
        Environment Data was successfully updated from ACS.
        
        This object will contain 0-1-1,00:00:00:0 if Environment Data
        has never been successfully updated from ACS."
    ::= { ctsEnvironmentDataObjects 4 }

ctsEnvDataRefreshInterval OBJECT-TYPE
    SYNTAX Gauge
--  Units
--    seconds
    ACCESS read-only
    STATUS mandatory
    DESCRIPTION
        "This object indicates the time interval for which
        Trusted Security Environment Data is valid.
        
        The Trusted Security Environment Data will be refreshed i.e.
        downloaded from the ACS after this time period has elapsed."
    ::= { ctsEnvironmentDataObjects 5 }

ctsEnvDataTimeLeft OBJECT-TYPE
    SYNTAX Gauge
--  Units
--    seconds
    ACCESS read-only
    STATUS mandatory
    DESCRIPTION
        "This object indicates the time left for the currently
        installed Trusted Security Environment Data to expire."
    ::= { ctsEnvironmentDataObjects 6 }

ctsEnvDataTimeToRefresh OBJECT-TYPE
    SYNTAX Gauge
--  Units
--    seconds
    ACCESS read-only
    STATUS mandatory
    DESCRIPTION
        "This object indicates the time interval after which
        Trusted Security Environment Data will be refreshed i.e.
        downloaded from the ACS due to Environment Data expiration
        or refresh failure."
    ::= { ctsEnvironmentDataObjects 7 }

ctsEnvDataSource OBJECT-TYPE
    SYNTAX INTEGER {
        none(1),
        cached(2),
        downloaded(3)
        }
    ACCESS read-only
    STATUS mandatory
    DESCRIPTION
        "This object indicates the source of current Environment Data
        installed on the system.
        
        'none'       - No Environment Data is currently installed.
        'cached'     - Environment Data is installed from non-volatile
                       storage on the system.
        'downloaded' - Environment Data is downloaded from the ACS."
    ::= { ctsEnvironmentDataObjects 8 }

ctsEnvDataAction OBJECT-TYPE
    SYNTAX INTEGER {
        none(1),
        refresh(2)
        }
    ACCESS read-write
    STATUS mandatory
    DESCRIPTION
        "This object allows user to specify the action to be taken for
        all the Cisco Trusted Security Environment Data on this device.
        
        When read, this object always returns the value 'none'.
        
        'none'    - No operation.
        'refresh' - Refresh all the Trusted Security Environment Data
                    on the device."
    ::= { ctsEnvironmentDataObjects 9 }

ctsEnvSecurityGroupNameTable OBJECT-TYPE
    SYNTAX SEQUENCE OF CtsEnvSecurityGroupNameEntry
    ACCESS not-accessible
    STATUS mandatory
    DESCRIPTION
        "A list of Security Group Names in Cisco Trusted Security
        environment."
    ::= { ctsEnvironmentDataObjects 16 }

ctsEnvSecurityGroupNameEntry OBJECT-TYPE
    SYNTAX CtsEnvSecurityGroupNameEntry
    ACCESS not-accessible
    STATUS mandatory
    DESCRIPTION
        "An entry listing the name assigned to each SGT in
        Cisco Trusted Security environment.
        
        Entries will be populated in this table when system downloads
        Security Group Name information as part of Trusted
        Security Environment Data."
    INDEX { ctsEnvSecurityGroupNameSgt }
    ::= { ctsEnvSecurityGroupNameTable 1 }

CtsEnvSecurityGroupNameEntry ::= SEQUENCE {
    ctsEnvSecurityGroupNameSgt CtsSecurityGroupTag,
    ctsEnvSecurityGroupNameSgtGenId CtsGenerationId,
    ctsEnvSecurityGroupNameSgtFlag OCTET STRING,
    ctsEnvSecurityGroupName SnmpAdminString
    }

ctsEnvSecurityGroupNameSgt OBJECT-TYPE
    SYNTAX CtsSecurityGroupTag(1..65535)
--    Rsyntax Gauge(1..65535)
    ACCESS not-accessible
    STATUS mandatory
    DESCRIPTION
        "This object identifies a SGT in Trusted Security environment."
    ::= { ctsEnvSecurityGroupNameEntry 1 }

ctsEnvSecurityGroupNameSgtGenId OBJECT-TYPE
    SYNTAX CtsGenerationId
--    Rsyntax OCTET STRING(SIZE(0..128))
    ACCESS read-only
    STATUS mandatory
    DESCRIPTION
        "This object indicates the Generation Identifier associated
        with this SGT."
    ::= { ctsEnvSecurityGroupNameEntry 2 }

ctsEnvSecurityGroupNameSgtFlag OBJECT-TYPE
    SYNTAX OCTET STRING(SIZE(1..2))
        -- BITS are:
        --   recognizedSgt(0)
        --   unicastSgt(1)
    ACCESS read-only
    STATUS mandatory
    DESCRIPTION
        "This object indicates the flag associated with this SGT.
        
        'recognizedSgt' - indicates a recognized SGT when set
                          to 1, else indicates a reserved SGT.
        'unicastSgt'    - indicates a unicast SGT when set
                          to 1, else indicates a multicast SGT."
    ::= { ctsEnvSecurityGroupNameEntry 3 }

ctsEnvSecurityGroupName OBJECT-TYPE
    SYNTAX SnmpAdminString
--    Rsyntax OCTET STRING(SIZE(0..255))
    ACCESS read-only
    STATUS mandatory
    DESCRIPTION
        "This object indicates the Security Group Name assigned
        to this SGT."
    ::= { ctsEnvSecurityGroupNameEntry 4 }

ctsFileErrNotifReason OBJECT-TYPE
    SYNTAX INTEGER {
        openFailedForWrite(1),
        writeFailed(2),
        openFailedForRead(3),
        readFailed(4),
        badMagic(5),
        unexpectedEof(6),
        badHeader(7)
        }
    ACCESS not-accessible
    STATUS mandatory
    DESCRIPTION
        "This object indicates the reason file error related
        notification was generated.
        
        'openFailedForWrite' - System failed to open a file to
                               write TrustSec information.
        'writeFailed'        - System failed to write TrustSec 
                               information to a file.
        'openFailedForRead'  - System failed to open a file to
                               read TrustSec information.
        'readFailed'         - System failed to read TrustSec
                               information from a file.
        'badMagic'           - A bad magic number was encountered 
                               for a TrustSec file.
        'unexpectedEof'      - A record of unexpected length is found in
                               TrustSec file.
        'badHeader'          - Bad file header was encountered for a
                               TrustSec file."
    ::= { ctsNotifsInfoObjects 1 }

ctsSwKeystoreSyncFailNotifReason OBJECT-TYPE
    SYNTAX INTEGER {
        ipcPortCreationFailed(1),
        ipcPortOpenFailed(2),
        ipcConnectionFailure(3),
        ipcSendFailure(4),
        standbyIncompatible(5),
        syncProcessCreationFailed(6)
        }
    ACCESS not-accessible
    STATUS mandatory
    DESCRIPTION
        "This object indicates the reason ctsSwKeystoreSyncFailNotif
        notification was generated. 
        
        'ipcPortCreationFailed' - Keystore information could not be
                                  synced because the system failed to
                                  create port for Inter-Process
                                  communication between the active
                                  and the standby supervisors.
        
        'ipcPortOpenFailed'     - Keystore information could not be
                                  synced because the system failed to
                                  open port for Inter-Process
                                  communication between the active
                                  and the standby supervisors.
        
        'ipcConnectionFailure'  - Keystore information could not be
                                  synced because Inter-Process
                                  communication connection failed
                                  between the active and the 
                                  standby supervisors.
        
        'ipcSendFailure'        - Keystore information could not be
                                  synced because Inter-Process
                                  Communication messages could not be
                                  sent to the standby supervisor.
        
        'standbyIncompatible'   - Keystore information could not be
                                  synced because the standby
                                  supervisor is not compatible with
                                  the active supervisor.
        
        'syncProcessCreationFailed' - Keystore information could not
                                  be synced because the system failed
                                  to create the sync process."
    ::= { ctsNotifsInfoObjects 2 }

ctsNotifMessageString OBJECT-TYPE
    SYNTAX SnmpAdminString
--    Rsyntax OCTET STRING(SIZE(0..255))
    ACCESS not-accessible
    STATUS mandatory
    DESCRIPTION
        "The object indicates additional information for a TrustSec
        notification."
    ::= { ctsNotifsInfoObjects 3 }

ctsSwKeystoreFileErrNotifEnable OBJECT-TYPE
    SYNTAX TruthValue
--    Rsyntax INTEGER {
--        true(1),
--        false(2)
--        }
    ACCESS read-write
    STATUS mandatory
    DESCRIPTION
        "This object specifies if the system generates
        ctsSwKeystoreFileErrNotif.
        
        A value of 'false' will prevent ctsSwKeystoreFileErrNotif
        notifications from being generated by this system."
    ::= { ctsNotifsControlObjects 1 }

ctsSwKeystoreSyncFailNotifEnable OBJECT-TYPE
    SYNTAX TruthValue
--    Rsyntax INTEGER {
--        true(1),
--        false(2)
--        }
    ACCESS read-write
    STATUS mandatory
    DESCRIPTION
        "This object specifies if the system generates
        ctsSwKeystoreSyncFailNotif.
        
        A value of 'false' will prevent ctsSwKeystoreSyncFailNotif
        notifications from being generated by this system."
    ::= { ctsNotifsControlObjects 2 }

ctsAuthzCacheFileErrNotifEnable OBJECT-TYPE
    SYNTAX TruthValue
--    Rsyntax INTEGER {
--        true(1),
--        false(2)
--        }
    ACCESS read-write
    STATUS mandatory
    DESCRIPTION
        "This object specifies if the system generates
        ctsAuthzCacheFileErrNotif.
        
        A value of 'false' will prevent ctsAuthzCacheFileErrNotif
        notifications from being generated by this system."
    ::= { ctsNotifsControlObjects 3 }

ctsCacheFileAccessErrNotifEnable OBJECT-TYPE
    SYNTAX TruthValue
--    Rsyntax INTEGER {
--        true(1),
--        false(2)
--        }
    ACCESS read-write
    STATUS mandatory
    DESCRIPTION
        "This object specifies if the system generates
        ctsCacheFileAccessErrNotif.
        
        A value of 'false' will prevent ctsCacheFileAccessErrNotif
        notifications from being generated by this system."
    ::= { ctsNotifsControlObjects 4 }

ctsSrcEntropyFailNotifEnable OBJECT-TYPE
    SYNTAX TruthValue
--    Rsyntax INTEGER {
--        true(1),
--        false(2)
--        }
    ACCESS read-write
    STATUS mandatory
    DESCRIPTION
        "This object specifies if the system generates
        ctsSrcEntropyFailNotif.
        
        A value of 'false' will prevent ctsSrcEntropyFailNotif
        notifications from being generated by this system."
    ::= { ctsNotifsControlObjects 5 }

ctsSapRandomNumberFailNotifEnable OBJECT-TYPE
    SYNTAX TruthValue
--    Rsyntax INTEGER {
--        true(1),
--        false(2)
--        }
    ACCESS read-write
    STATUS mandatory
    DESCRIPTION
        "This object specifies if the system generates
        ctsSapRandomNumberFailNotif.
        
        A value of 'false' will prevent ctsSapRandomNumberFailNotif
        notifications from being generated by this system."
    ::= { ctsNotifsControlObjects 6 }

ctsCriticalAuthEnabled OBJECT-TYPE
    SYNTAX TruthValue
--    Rsyntax INTEGER {
--        true(1),
--        false(2)
--        }
    ACCESS read-write
    STATUS mandatory
    DESCRIPTION
        "This object specifies if the Critical-Auth functionality
        is enabled in the system.
        
        Setting the object to 'true' will enable Critical-Auth
        functionality in the system and 'false' will disable the
        Critical-Auth functionality. Before enable ctsCriticalAuthEnable
        ctsCriticalAuthPeerSgt need to be configured."
    ::= { ctsCriticalAuthObjects 1 }

ctsCriticalAuthFallback OBJECT-TYPE
    SYNTAX INTEGER {
        default(1),
        cache(2)
        }
    ACCESS read-write
    STATUS mandatory
    DESCRIPTION
        "This object specifies the CTS Critical-Auth fallback
        policy. 
        
        default - Critical-Auth fallback policy is default.
        
        cache   - Critical-Auth fallback policy is cache."
    ::= { ctsCriticalAuthObjects 2 }

ctsCriticalAuthPeerSgt OBJECT-TYPE
    SYNTAX CtsSecurityGroupTag
--    Rsyntax Gauge(0..65535)
    ACCESS read-write
    STATUS mandatory
    DESCRIPTION
        "This object specifies the CTS Critical-Auth SGT tag
        of the remote peer.
        
        ctsCriticalAuthPeerSgt cannot be set to zero when
        ctsCriticalAuthEnable is enable.
        
        ctsCriticalAuthPeerSgtTrust will be set to untrusted by default
        during set operation of ctsCriticalAuthPeerSgt.
        
        User need to explicitly override the ctsCriticalAuthPeerSgtTrust
        to trusted if required."
    ::= { ctsCriticalAuthObjects 3 }

ctsCriticalAuthPeerSgtTrust OBJECT-TYPE
    SYNTAX TruthValue
--    Rsyntax INTEGER {
--        true(1),
--        false(2)
--        }
    ACCESS read-write
    STATUS mandatory
    DESCRIPTION
        "This object specifies the CTS Critical-Auth peer's sgt
        trust state.
        
        This object can only be set when ctsCriticalAuthPeerSgt is
        non-zero."
    ::= { ctsCriticalAuthObjects 4 }

ctsCriticalAuthDefaultPmk OBJECT-TYPE
    SYNTAX OCTET STRING(SIZE(0..32))
    ACCESS read-write
    STATUS mandatory
    DESCRIPTION
        "This object specifies the CTS Critical-Auth default PMK
        used by SAP.
        
        The purpose of this object is to only allow configuration of
        Critical-Auth PMK.
        
        The ctsCriticalAuthViewDefaultPmk object is used to display the
        default Critical-Auth PMK."
    ::= { ctsCriticalAuthObjects 5 }

ctsCriticalAuthViewDefaultPmk OBJECT-TYPE
    SYNTAX OCTET STRING(SIZE(0..255))
    ACCESS read-only
    STATUS mandatory
    DESCRIPTION
        "This object indicates the CTS Critical-Auth default PMK.
        
        The purpose of this object is to only display the configured
        Critical-Auth PMK.
        
        A zero length string for this objects indicates the SAP
        negotiation is disabled.
        
        The ctsCriticalAuthDefaultPmk object is used to configure 
        the PMK."
    ::= { ctsCriticalAuthObjects 6 }

ctsSwKeystoreFileErrNotif TRAP-TYPE
-- Reverse mappable trap
    ENTERPRISE ciscoTrustSecMIB
    VARIABLES {
        ctsFileErrNotifReason }
--  Status
--    mandatory
    DESCRIPTION
        "A ctsSwKeystoreFileErrNotif is generated when system
        encounters an error while performing operation on the
        software keystore file."
    ::= 1

ctsSwKeystoreSyncFailNotif TRAP-TYPE
-- Reverse mappable trap
    ENTERPRISE ciscoTrustSecMIB
    VARIABLES {
        ctsSwKeystoreSyncFailNotifReason }
--  Status
--    mandatory
    DESCRIPTION
        "A ctsSwKeystoreSyncFailNotifReason is generated when system
        fails to sync software keystore information from the active
        supervisor to the standby supervisor."
    ::= 2

ctsAuthzCacheFileErrNotif TRAP-TYPE
-- Reverse mappable trap
    ENTERPRISE ciscoTrustSecMIB
    VARIABLES {
        ctsFileErrNotifReason, ctsNotifMessageString }
--  Status
--    mandatory
    DESCRIPTION
        "A ctsAuthzCacheFileErrNotif is generated when the system
        encounters error downloading TrustSec authorization
        related environment data to a cache file."
    ::= 3

ctsCacheFileAccessErrNotif TRAP-TYPE
-- Reverse mappable trap
    ENTERPRISE ciscoTrustSecMIB
    VARIABLES {
        ctsFileErrNotifReason, ctsNotifMessageString }
--  Status
--    mandatory
    DESCRIPTION
        "A ctsCacheFileAccessErrNotif is generated when the
        system fails to perform open/read/write operation
        for a TrustSec cache file."
    ::= 4

ctsSrcEntropyFailNotif TRAP-TYPE
-- Reverse mappable trap
    ENTERPRISE ciscoTrustSecMIB
--  Status
--    mandatory
    DESCRIPTION
        "A ctsSrcEntropyFailNotif is generated when
        the periodic health tests for the CTR-DRBG (Counter-
        Deterministic Random Bit Generator) implementation
        fails due to issues with the source entropy."
    ::= 5

ctsSapRandomNumberFailNotif TRAP-TYPE
-- Reverse mappable trap
    ENTERPRISE ciscoTrustSecMIB
    VARIABLES {
        ctsNotifMessageString }
--  Status
--    mandatory
    DESCRIPTION
        "A ctsSapRandomNumberFailNotif is generated when the
        the system fails to obtain a random number from
        CTR-DRBG block for SAP (Security Association Protocol)
        key-counter."
    ::= 6

ciscoTrustSecCacheGroup OBJECT IDENTIFIER ::= { ciscoTrustSecMIBGroups 1 }
-- OBJECT-GROUP
--  Status
--    mandatory
--  Descr
--    A collection of objects that provides the cache configuration
--    for TrustSec in the system.
--  objects
--    ctsCacheEnabled, ctsCacheNvStorage, ctsCacheClear

ciscoTrustSecSgtGroup OBJECT IDENTIFIER ::= { ciscoTrustSecMIBGroups 2 }
-- OBJECT-GROUP
--  Status
--    mandatory
--  Descr
--    A collection of objects to manage SGT for TrustSec.
--  objects
--    ctsSecurityGroupTagId

ciscoTrustSecCredentialsGroup OBJECT IDENTIFIER ::= { ciscoTrustSecMIBGroups 3 }
-- OBJECT-GROUP
--  Status
--    mandatory
--  Descr
--    A collection of objects to manage credentials parameters for
--    TrustSec.
--  objects
--    ctsDeviceId, ctsDevicePasswordType, ctsDevicePassword, 
--    ctsKeystoreType, ctsKeystorePasswordRecordType, 
--    ctsKeystorePacRecordType, ctsPacAcsDescription, ctsPacType, 
--    ctsPacExpirationTime, ctsPacTimeToRefresh, ctsPacStatus, 
--    ctsCredentialsClearAll

ciscoTrustSecHwKeystoreInfoGroup OBJECT IDENTIFIER ::= { ciscoTrustSecMIBGroups 4 }
-- OBJECT-GROUP
--  Status
--    mandatory
--  Descr
--    A collection of objects to manage hardware keystore for
--    TrustSec.
--  objects
--    ctsKeystoreFwVersion, ctsKeystoreFwAlerts, 
--    ctsKeystoreFwResets, ctsKeystoreRxTimeouts, 
--    ctsKeystoreRxBadChecksums, ctsKeystoreRxBadFragmentLengths, 
--    ctsKeystoreCorruptions

ciscoTrustSecEnvDataGroup OBJECT IDENTIFIER ::= { ciscoTrustSecMIBGroups 5 }
-- OBJECT-GROUP
--  Status
--    mandatory
--  Descr
--    A collection of objects to manage Environment Data for
--    TrustSec.
--  objects
--    ctsEnvDataLastDownloadStatus, ctsEnvSecurityGroupTagId, 
--    ctsEnvSecurityGroupTagGenId, ctsEnvDataLastUpdate, 
--    ctsEnvDataRefreshInterval, ctsEnvDataTimeLeft, 
--    ctsEnvDataTimeToRefresh, ctsEnvDataSource, ctsEnvDataAction

ciscoTrustSecSgtAssignmentGroup OBJECT IDENTIFIER ::= { ciscoTrustSecMIBGroups 6 }
-- OBJECT-GROUP
--  Status
--    mandatory
--  Descr
--    A collection of objects to manage assignment of TrustSec SGT.
--  objects
--    ctsSgtAssignmentMethod

ciscoTrustSecEnvSecGroupNameGroup OBJECT IDENTIFIER ::= { ciscoTrustSecMIBGroups 7 }
-- OBJECT-GROUP
--  Status
--    mandatory
--  Descr
--    A collection of object(s) to manage Security Group Name
--    information for TrustSec.
--  objects
--    ctsEnvSecurityGroupNameSgtGenId, 
--    ctsEnvSecurityGroupNameSgtFlag, ctsEnvSecurityGroupName

ciscoTrustSecSwKeystoreNotifsInfoGroup OBJECT IDENTIFIER ::= { ciscoTrustSecMIBGroups 8 }
-- OBJECT-GROUP
--  Status
--    mandatory
--  Descr
--    A collection of object(s) to provide information
--    regarding software keystore notifications for TrustSec.
--  objects
--    ctsSwKeystoreSyncFailNotifReason

ciscoTrustSecSwKeystoreNotifsControlGroup OBJECT IDENTIFIER ::= { ciscoTrustSecMIBGroups 9 }
-- OBJECT-GROUP
--  Status
--    mandatory
--  Descr
--    A collection of object(s) to control software keystore
--    notifications for TrustSec.
--  objects
--    ctsSwKeystoreFileErrNotifEnable, 
--    ctsSwKeystoreSyncFailNotifEnable

ciscoTrustSecFileErrNotifsInfoGroup OBJECT IDENTIFIER ::= { ciscoTrustSecMIBGroups 11 }
-- OBJECT-GROUP
--  Status
--    mandatory
--  Descr
--    A collection of object(s) to provide information
--    regarding file error related notifications for TrustSec.
--  objects
--    ctsFileErrNotifReason

ciscoTrustSecNotifsMessageStringInfoGroup OBJECT IDENTIFIER ::= { ciscoTrustSecMIBGroups 12 }
-- OBJECT-GROUP
--  Status
--    mandatory
--  Descr
--    A collection of object(s) to provide information
--    regarding TrustSec notification.
--  objects
--    ctsNotifMessageString

ciscoTrustSecCacheFileNotifsControlGroup OBJECT IDENTIFIER ::= { ciscoTrustSecMIBGroups 13 }
-- OBJECT-GROUP
--  Status
--    mandatory
--  Descr
--    A collection of object(s) to control cache file
--    related notifications for TrustSec.
--  objects
--    ctsAuthzCacheFileErrNotifEnable, 
--    ctsCacheFileAccessErrNotifEnable

ciscoTrustSecCtrDrbgNotifsControlGroup OBJECT IDENTIFIER ::= { ciscoTrustSecMIBGroups 15 }
-- OBJECT-GROUP
--  Status
--    mandatory
--  Descr
--    A collection of object(s) to control CTR-DRBG related
--    notifications for TrustSec.
--  objects
--    ctsSrcEntropyFailNotifEnable, 
--    ctsSapRandomNumberFailNotifEnable

ciscoTrustSecCrtclAuthGroup OBJECT IDENTIFIER ::= { ciscoTrustSecMIBGroups 17 }
-- OBJECT-GROUP
--  Status
--    mandatory
--  Descr
--    A collection of CTS Critical Auth Config
--    objects
--  objects
--    ctsCriticalAuthEnabled, ctsCriticalAuthFallback, 
--    ctsCriticalAuthPeerSgt, ctsCriticalAuthPeerSgtTrust, 
--    ctsCriticalAuthDefaultPmk, ctsCriticalAuthViewDefaultPmk

ciscoTrustSecSwKeystoreNotifsGroup OBJECT IDENTIFIER ::= { ciscoTrustSecMIBGroups 10 }
-- NOTIFICATION-GROUP
--  Status
--    mandatory
--  Descr
--    A collection of software keystore related notifications for
--    TrustSec.
--  notifications
--    ctsSwKeystoreFileErrNotif, ctsSwKeystoreSyncFailNotif

ciscoTrustSecCacheFileNotifsGroup OBJECT IDENTIFIER ::= { ciscoTrustSecMIBGroups 14 }
-- NOTIFICATION-GROUP
--  Status
--    mandatory
--  Descr
--    A collection of TrustSec cache file related notifications.
--  notifications
--    ctsAuthzCacheFileErrNotif, ctsCacheFileAccessErrNotif

ciscoTrustSecCtrDrbgNotifsGroup OBJECT IDENTIFIER ::= { ciscoTrustSecMIBGroups 16 }
-- NOTIFICATION-GROUP
--  Status
--    mandatory
--  Descr
--    A collection of CTR-DRBG related notifications
--    for TrustSec.
--  notifications
--    ctsSrcEntropyFailNotif, ctsSapRandomNumberFailNotif

ciscoTrustSecMIBCompliance OBJECT IDENTIFIER ::= { ciscoTrustSecMIBCompliances 1 }
-- MODULE-COMPLIANCE
--  Status
--    deprecated
--  Descr
--    The compliance statement for the CISCO-TRUSTSEC-MIB.
--  Module
--    >>current<<
--   MandGroup
--    ciscoTrustSecCacheGroup
--   MandGroup
--    ciscoTrustSecSgtGroup
--   MandGroup
--    ciscoTrustSecCredentialsGroup
--   MandGroup
--    ciscoTrustSecHwKeystoreInfoGroup
--   MandGroup
--    ciscoTrustSecEnvDataGroup
--   OptGroup
--    ciscoTrustSecSgtAssignmentGroup
--   ObjVar
--    ctsCacheEnabled
--   ObjVar
--    ctsCacheNvStorage
--   ObjVar
--    ctsCacheClear
--   ObjVar
--    ctsSecurityGroupTagId
--   ObjVar
--    ctsSgtAssignmentMethod
--   ObjVar
--    ctsDeviceId
--   ObjVar
--    ctsDevicePasswordType
--   ObjVar
--    ctsDevicePassword
--   ObjVar
--    ctsPacStatus
--   ObjVar
--    ctsCredentialsClearAll
--   ObjVar
--    ctsEnvDataAction

ciscoTrustSecMIBCompliance2 OBJECT IDENTIFIER ::= { ciscoTrustSecMIBCompliances 2 }
-- MODULE-COMPLIANCE
--  Status
--    deprecated
--  Descr
--    The compliance statement for the CISCO-TRUSTSEC-MIB.
--  Module
--    >>current<<
--   MandGroup
--    ciscoTrustSecCacheGroup
--   MandGroup
--    ciscoTrustSecSgtGroup
--   MandGroup
--    ciscoTrustSecCredentialsGroup
--   MandGroup
--    ciscoTrustSecHwKeystoreInfoGroup
--   MandGroup
--    ciscoTrustSecEnvDataGroup
--   OptGroup
--    ciscoTrustSecSgtAssignmentGroup
--   OptGroup
--    ciscoTrustSecEnvSecGroupNameGroup
--   ObjVar
--    ctsCacheEnabled
--   ObjVar
--    ctsCacheNvStorage
--   ObjVar
--    ctsCacheClear
--   ObjVar
--    ctsSecurityGroupTagId
--   ObjVar
--    ctsSgtAssignmentMethod
--   ObjVar
--    ctsDeviceId
--   ObjVar
--    ctsDevicePasswordType
--   ObjVar
--    ctsDevicePassword
--   ObjVar
--    ctsPacStatus
--   ObjVar
--    ctsCredentialsClearAll
--   ObjVar
--    ctsEnvDataAction

ciscoTrustSecMIBCompliance3 OBJECT IDENTIFIER ::= { ciscoTrustSecMIBCompliances 3 }
-- MODULE-COMPLIANCE
--  Status
--    deprecated
--  Descr
--    The compliance statement for the CISCO-TRUSTSEC-MIB.
--  Module
--    >>current<<
--   MandGroup
--    ciscoTrustSecCacheGroup
--   MandGroup
--    ciscoTrustSecSgtGroup
--   MandGroup
--    ciscoTrustSecCredentialsGroup
--   MandGroup
--    ciscoTrustSecHwKeystoreInfoGroup
--   MandGroup
--    ciscoTrustSecEnvDataGroup
--   OptGroup
--    ciscoTrustSecSgtAssignmentGroup
--   OptGroup
--    ciscoTrustSecEnvSecGroupNameGroup
--   OptGroup
--    ciscoTrustSecSwKeystoreNotifsInfoGroup
--   OptGroup
--    ciscoTrustSecSwKeystoreNotifsControlGroup
--   OptGroup
--    ciscoTrustSecSwKeystoreNotifsGroup
--   OptGroup
--    ciscoTrustSecFileErrNotifsInfoGroup
--   OptGroup
--    ciscoTrustSecNotifsMessageStringInfoGroup
--   OptGroup
--    ciscoTrustSecCacheFileNotifsControlGroup
--   OptGroup
--    ciscoTrustSecCacheFileNotifsGroup
--   OptGroup
--    ciscoTrustSecCtrDrbgNotifsControlGroup
--   OptGroup
--    ciscoTrustSecCtrDrbgNotifsGroup
--   ObjVar
--    ctsCacheEnabled
--   ObjVar
--    ctsCacheNvStorage
--   ObjVar
--    ctsCacheClear
--   ObjVar
--    ctsSecurityGroupTagId
--   ObjVar
--    ctsSgtAssignmentMethod
--   ObjVar
--    ctsDeviceId
--   ObjVar
--    ctsDevicePasswordType
--   ObjVar
--    ctsDevicePassword
--   ObjVar
--    ctsPacStatus
--   ObjVar
--    ctsCredentialsClearAll
--   ObjVar
--    ctsEnvDataAction
--   ObjVar
--    ctsSwKeystoreFileErrNotifEnable
--   ObjVar
--    ctsSwKeystoreSyncFailNotifEnable
--   ObjVar
--    ctsAuthzCacheFileErrNotifEnable
--   ObjVar
--    ctsCacheFileAccessErrNotifEnable
--   ObjVar
--    ctsSrcEntropyFailNotifEnable
--   ObjVar
--    ctsSapRandomNumberFailNotifEnable

ciscoTrustSecMIBCompliance4 OBJECT IDENTIFIER ::= { ciscoTrustSecMIBCompliances 4 }
-- MODULE-COMPLIANCE
--  Status
--    mandatory
--  Descr
--    The compliance statement for the CISCO-TRUSTSEC-MIB.
--  Module
--    >>current<<
--   MandGroup
--    ciscoTrustSecCacheGroup
--   MandGroup
--    ciscoTrustSecSgtGroup
--   MandGroup
--    ciscoTrustSecCredentialsGroup
--   MandGroup
--    ciscoTrustSecHwKeystoreInfoGroup
--   MandGroup
--    ciscoTrustSecEnvDataGroup
--   OptGroup
--    ciscoTrustSecSgtAssignmentGroup
--   OptGroup
--    ciscoTrustSecEnvSecGroupNameGroup
--   OptGroup
--    ciscoTrustSecSwKeystoreNotifsInfoGroup
--   OptGroup
--    ciscoTrustSecSwKeystoreNotifsControlGroup
--   OptGroup
--    ciscoTrustSecSwKeystoreNotifsGroup
--   OptGroup
--    ciscoTrustSecFileErrNotifsInfoGroup
--   OptGroup
--    ciscoTrustSecNotifsMessageStringInfoGroup
--   OptGroup
--    ciscoTrustSecCacheFileNotifsControlGroup
--   OptGroup
--    ciscoTrustSecCacheFileNotifsGroup
--   OptGroup
--    ciscoTrustSecCtrDrbgNotifsControlGroup
--   OptGroup
--    ciscoTrustSecCtrDrbgNotifsGroup
--   OptGroup
--    ciscoTrustSecCrtclAuthGroup
--   ObjVar
--    ctsCacheEnabled
--   ObjVar
--    ctsCacheNvStorage
--   ObjVar
--    ctsCacheClear
--   ObjVar
--    ctsSecurityGroupTagId
--   ObjVar
--    ctsSgtAssignmentMethod
--   ObjVar
--    ctsDeviceId
--   ObjVar
--    ctsDevicePasswordType
--   ObjVar
--    ctsDevicePassword
--   ObjVar
--    ctsPacStatus
--   ObjVar
--    ctsCredentialsClearAll
--   ObjVar
--    ctsEnvDataAction
--   ObjVar
--    ctsSwKeystoreFileErrNotifEnable
--   ObjVar
--    ctsSwKeystoreSyncFailNotifEnable
--   ObjVar
--    ctsAuthzCacheFileErrNotifEnable
--   ObjVar
--    ctsCacheFileAccessErrNotifEnable
--   ObjVar
--    ctsSrcEntropyFailNotifEnable
--   ObjVar
--    ctsSapRandomNumberFailNotifEnable
--   ObjVar
--    ctsCriticalAuthEnabled
--   ObjVar
--    ctsCriticalAuthFallback
--   ObjVar
--    ctsCriticalAuthPeerSgt
--   ObjVar
--    ctsCriticalAuthPeerSgtTrust
--   ObjVar
--    ctsCriticalAuthDefaultPmk


END
