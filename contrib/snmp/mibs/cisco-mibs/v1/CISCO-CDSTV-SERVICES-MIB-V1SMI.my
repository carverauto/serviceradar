-- MIB file created 18-Jun-2010 12:32:11, by
--   SMICng version 2.2.11-beta(PRO)(Solaris), January 20, 2001. Enterprise key cisco.com

CISCO-CDSTV-SERVICES-MIB DEFINITIONS ::= BEGIN

-- From file: "CISCO-CDSTV-SERVICES-MIB.my"
-- Compile options "4 7 F H N W 03 06 0B 0G 0N 0T"

IMPORTS
    SnmpAdminString
            FROM SNMP-FRAMEWORK-MIB
    TruthValue
            FROM SNMPv2-TC-v1
    ciscoMgmt
            FROM CISCO-SMI
    Gauge
            FROM RFC1155-SMI
    OBJECT-TYPE
            FROM RFC-1212
    TRAP-TYPE
            FROM RFC-1215;

ciscoCdstvServicesMIB OBJECT IDENTIFIER ::= { ciscoMgmt 729 }
-- MODULE-IDENTITY
--  LastUpdated
--    201003290000Z
--  OrgName
--    Cisco Systems, Inc.
--  ContactInfo
--    Cisco Systems
--    Customer Service
--    
--    Postal: 170 W Tasman Drive
--    San Jose, CA  95134
--    USA
--    
--    Tel: +1 800 553-NETS
--    
--    E-mail: cs-cds@cisco.com
--  Descr
--    This MIB module defines service monitoring objects that
--    faciliate the management of the Cisco Content Delivery System
--    for TV (CDS-TV) product family.
--    
--    CDS-TV is a suite of products and software applications
--    providing ingest, storage, caching, streaming, playout and
--    on-demand delivery of video to television or set-top-box
--    clients.
--    
--    Abbreviations:
--    
--    CDS     Content Delivery System
--    ISA     Interactive Services Architecture
--    ISV     Integrated Streamer-Vault
--    FSI     File Service Interface
--    MSA     Managed Services Architecture
--    RTSP    Real-Time Streaming Protocol
--  RevDate
--    201003290000Z
--  RevDescr
--    Initial version of this MIB module.

ciscoCdstvServicesMIBNotifs OBJECT IDENTIFIER ::= { ciscoCdstvServicesMIB 0 }
ciscoCdstvServicesMIBObjects OBJECT IDENTIFIER ::= { ciscoCdstvServicesMIB 1 }
ciscoCdstvServicesMIBConform OBJECT IDENTIFIER ::= { ciscoCdstvServicesMIB 2 }
cdstvServiceTrapsEnable OBJECT IDENTIFIER ::= { ciscoCdstvServicesMIBObjects 2 }
ciscoCdstvServicesMIBCompliances OBJECT IDENTIFIER ::= { ciscoCdstvServicesMIBConform 1 }
ciscoCdstvServicesMIBGroups OBJECT IDENTIFIER ::= { ciscoCdstvServicesMIBConform 2 }

cdstvServicesMonitorTable OBJECT-TYPE
    SYNTAX SEQUENCE OF CdstvServicesMonitorTableEntry
    ACCESS not-accessible
    STATUS mandatory
    DESCRIPTION
        "This table lists the services being monitored."
    ::= { ciscoCdstvServicesMIBObjects 1 }

cdstvServicesMonitorTableEntry OBJECT-TYPE
    SYNTAX CdstvServicesMonitorTableEntry
    ACCESS not-accessible
    STATUS mandatory
    DESCRIPTION
        "An entry (conceptual row) in the cdstvServicesMonitorTable.
        Each entry represents a service configured to run on the server
        and its status (whether running or stopped). Rows are added for
        each configured service and the number of rows does not change
        for a particular server with a specific configuration."
    INDEX { cdstvServicesMonitorIndex }
    ::= { cdstvServicesMonitorTable 1 }

CdstvServicesMonitorTableEntry ::= SEQUENCE {
    cdstvServicesMonitorIndex Gauge,
    cdstvServiceName SnmpAdminString,
    cdstvServiceStatus INTEGER
    }

cdstvServicesMonitorIndex OBJECT-TYPE
    SYNTAX Gauge(1..4294967295)
    ACCESS not-accessible
    STATUS mandatory
    DESCRIPTION
        "A unique identifier for the services being monitored on this
        device, i.e. streamer, cache, vault or ISV."
    ::= { cdstvServicesMonitorTableEntry 1 }

cdstvServiceName OBJECT-TYPE
    SYNTAX SnmpAdminString
--    Rsyntax OCTET STRING(SIZE(0..255))
    ACCESS read-only
    STATUS mandatory
    DESCRIPTION
        "This object indicates the name of the service/process being
        monitored."
    ::= { cdstvServicesMonitorTableEntry 2 }

cdstvServiceStatus OBJECT-TYPE
    SYNTAX INTEGER {
        up(1),
        down(2)
        }
    ACCESS read-only
    STATUS mandatory
    DESCRIPTION
        "This object indicates the status of the service/process being
        monitored: up(1), or down(2)."
    ::= { cdstvServicesMonitorTableEntry 3 }

cdstvServiceUpNotifEnable OBJECT-TYPE
    SYNTAX TruthValue
--    Rsyntax INTEGER {
--        true(1),
--        false(2)
--        }
    ACCESS read-write
    STATUS mandatory
    DESCRIPTION
        "This object specifies whether cdstvServiceUp notification is
        generated by the system.
        
        Setting this object to 'true' will enable generation of
        cdstvServiceUp. 
        
        Setting this object to 'false' will disable generation of 
        cdstvServiceUp."
    ::= { cdstvServiceTrapsEnable 1 }

cdstvServiceDownNotifEnable OBJECT-TYPE
    SYNTAX TruthValue
--    Rsyntax INTEGER {
--        true(1),
--        false(2)
--        }
    ACCESS read-write
    STATUS mandatory
    DESCRIPTION
        "This object specifies whether cdstvServiceDown notification is
        generated by the system. 
        
        Setting this object to 'true' will enable generation of
        cdstvServiceDown. 
        
        Setting this object to 'false' will disable generation of 
        cdstvServiceDown"
    ::= { cdstvServiceTrapsEnable 2 }

cdstvServiceUp TRAP-TYPE
-- Reverse mappable trap
    ENTERPRISE ciscoCdstvServicesMIB
    VARIABLES {
        cdstvServiceName }
--  Status
--    mandatory
    DESCRIPTION
        "The SNMP entity generates the cdstvServiceUp notification when
        the status (indicated by the object cdstvServiceStatus) of a
        service being monitored (indicated by the object
        cdstvServiceName) changes to 'up'."
    ::= 1

cdstvServiceDown TRAP-TYPE
-- Reverse mappable trap
    ENTERPRISE ciscoCdstvServicesMIB
    VARIABLES {
        cdstvServiceName }
--  Status
--    mandatory
    DESCRIPTION
        "The SNMP entity generates the cdstvServiceDown notification
        when the status (indicated by the object cdstvServiceStatus) 
        of a service being monitored (indicated by the object 
        cdstvServiceName), changes to 'down'."
    ::= 2

ciscoCdstvServicesMIBMainObjectGroup OBJECT IDENTIFIER ::= { ciscoCdstvServicesMIBGroups 1 }
-- OBJECT-GROUP
--  Status
--    mandatory
--  Descr
--    A collection of objects that provide status of monitored
--    services.
--  objects
--    cdstvServiceName, cdstvServiceStatus

ciscoCdstvServicesMIBNotifEnableObjectGroup OBJECT IDENTIFIER ::= { ciscoCdstvServicesMIBGroups 3 }
-- OBJECT-GROUP
--  Status
--    mandatory
--  Descr
--    A collection of objects that enable/disable generation of
--    CDS-TV service notifications.
--  objects
--    cdstvServiceUpNotifEnable, cdstvServiceDownNotifEnable

ciscoCdstvServicesMIBNotificationGroup OBJECT IDENTIFIER ::= { ciscoCdstvServicesMIBGroups 2 }
-- NOTIFICATION-GROUP
--  Status
--    mandatory
--  Descr
--    A collection of notifications generated by this MIB module.
--  notifications
--    cdstvServiceUp, cdstvServiceDown

ciscoCdstvServicesMIBCompliance OBJECT IDENTIFIER ::= { ciscoCdstvServicesMIBCompliances 1 }
-- MODULE-COMPLIANCE
--  Status
--    mandatory
--  Descr
--    The compliance statement for the entities which
--    implement the Cisco CDS TV Services MIB.
--  Module
--    >>current<<
--   MandGroup
--    ciscoCdstvServicesMIBMainObjectGroup
--   MandGroup
--    ciscoCdstvServicesMIBNotificationGroup
--   OptGroup
--    ciscoCdstvServicesMIBNotifEnableObjectGroup
--   ObjVar
--    cdstvServiceUpNotifEnable
--   ObjVar
--    cdstvServiceDownNotifEnable


END
