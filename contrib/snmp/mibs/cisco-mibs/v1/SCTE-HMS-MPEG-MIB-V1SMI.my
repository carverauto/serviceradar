-- MIB file created 09-Apr-2014 05:11:46, by
--   SMICng version 2.2.11-beta(PRO)(Solaris), January 20, 2001. Enterprise key cisco.com

SCTE-HMS-MPEG-MIB DEFINITIONS ::= BEGIN

-- From file: "SCTE-HMS-MPEG-MIB.my"
-- Compile options "4 7 F H N W 03 06 0B 0G 0N 0T"

IMPORTS
    enterprises
            FROM SNMPv2-SMI-v1
    DateAndTime, TruthValue, RowPointer, AutonomousType
            FROM SNMPv2-TC-v1
    InterfaceIndex
            FROM IF-MIB
    InetAddress, InetAddressType, InetPortNumber
            FROM INET-ADDRESS-MIB
    HePIDValue, ProgDataType
            FROM SCTE-HMS-HEADENDIDENT-TC-MIB
    Counter, Gauge
            FROM RFC1155-SMI
    OBJECT-TYPE
            FROM RFC-1212;

heMpegCommonMIB OBJECT IDENTIFIER ::= { enterprises scteRoot(5591) scteHmsTree(1) insidePlantIdent(11) heDigital(5) heDigitalMPEG(4) 1 }
-- MODULE-IDENTITY
--  LastUpdated
--    200810031700Z
--  OrgName
--    SCTE HMS Subcommittee
--  ContactInfo
--    SCTE HMS Subcommittee, Chairman
--    mailto:standards@scte.org 
--  Descr
--    This MIB module is for representing MPEG equipment present in
--    the headend and is supported by a SNMP agent. It defines both 
--    the MPEG input and output MIB objects for managing
--    MPEG input and output transport streams, programs and elementary 
--    streams. It provides both input and output related statistics,
--    as well as program mapping and video session information. 
--    
--    All the tables, except mpegProgramMappingTable and 
--    mpegVideoSessionTable, capture and store the information
--    related to active transport streams only. Optional
--    MIB objects will have default values defined in this MIB file.
--  RevDate
--    200810031700Z
--  RevDescr
--    Resolved compile errors:
--    1. LAST-UPDATED date matches last REVISION date.
--    2. Removed illegal characters such as line feed (ascii 0xa0).
--    3. Added mpegInputTSActiveConnection to at least one conformance
--       group.
--    4. Removed extra mpegSessionsGroup in compliance statement.
--  RevDate
--    200810030649Z
--  RevDescr
--    1. Added mpegInputTSActiveConnection entry.
--    2. Added mpegInputTSOutputSessionCreateTime.
--    3. Added mpegInputUdpOriginationInputTSIndex.
--    4. Added mpegOutputUdpDestinationOutputTSIndex.
--  RevDate
--    200810030135Z
--  RevDescr
--    Fixed spelling mistakes.
--  RevDate
--    200810030000Z
--  RevDescr
--    Changes included in the SCTE F2F meetings 
--    July 9-10 and Sept 24-25
--    1. mpegInputTSEntry, mpegOutputTSEntry, mpegProgESEntry  are no
--    longer indexed by ifIndex.
--    2. mpegInputTSTransportType and mpegInputTSPacketsDetected 
--    removed from mpegInputTSEntry to accomodate the Input 
--    extensibility such as udpOrigination.
--    3. Added to mpegInputTSEntry  mpegInputTSConnectionType and 
--    mpegInputTSConnection.
--    4. mpegInputTSPatVersion and mpegInputTSCatVersion value -1 
--    added to indicate unknown or not supported.
--    5. MpegProgESEntry  sequence elements names updates to align 
--    with mpegProgES* prefix.
--    6. mpegStatsStreamTable renamed to mpegInputStatsTable. 
--    7. mpegInputStatsPcrJitter and mpegInputStatsMaxPacketJitter
--    support value -1 to indicate not supported measurement. 
--    8. Added mpegInputUdpOriginationTable and 
--    mpegOutputUdpOriginationTable to generalize the input/output TS 
--    construct.
--    9. Updated parent OID of mpegInsertPacketTable to reflect the
--    output nature of the construct.
--    10. Renamed mpegInsertPacketDeviceIndex as 
--    mpegInsertPacketDeviceIfIndex.
--    11. mpegOutputStatsTotalPackets set to 64 bits counter.  
--    12.mpegOutputStatsChannelUtilization units set to 1 tenth of 
--    percent.
--    13. Added to mpegOutputTSEntry  mpegOutputTSConnectionType 
--    and mpegOutputTSConnection.
--    14. mpegOutputProgNo changed ACCESS to read-only.
--    15. mpegOutputProgESPid renamed to mpegOutputProgElemStatsPid
--    to preserve the construct prefix MpegOutputProgElemStats*. 
--    16. Added mpegOutputUdpDestinationTable. 
--    17. Deleted mpegProgramMappingDeviceChannelId and 
--    mpegProgramMappingInputIfIndex from MpegProgramMappingEntry.
--    18. MpegVideoSessionEntry  Added:
--      mpegVideoSessionPIDRemap, mpegVideoSessionMode, 
--      mpegVideoSessionEncryptionType, mpegVideoSessionEncryptionInfo,
--      mpegVideoSessionBitRate, mpegVideoSessionSelectedInput.
--    19. MpegVideoSessionEntry  Deleted:  
--      mpegVideoSessionUdpPort, mpegVideoSessionDestAddrType,
--      mpegVideoSessionDestAddr, mpegVideoSessionSrcAddrType,
--      mpegVideoSessionSrcAddr.
--    20. Added mpegVideoSessionPtrTable.
--    21. Updated mpegInputProgESGroup and mpegOutputProgElemStatsGroup
--      description.
--    22. Updated OBJECT-GROUP mpegInputGroup, mpegInputProgESGroup,
--    mpegOutputGroup, mpegMappingsGroup, mpegSessionsGroup.   
--    23. Added mpegInputStatsPcrIntervalExceeds to the MPEG input 
--    statistics.
--    24. Added the table mpegInputUdpOriginationSessionTable.
--  RevDate
--    200802041700Z
--  RevDescr
--     Changes due to voting comments
--    1. Changed description of mpegInputTSPsiDetected.
--    2. Changed mpegInputTSRate, mpegInputTXMaxRate, mpegInsertPacketIndex, 
--    and mpegInsertPacketListId be Unsigned32 instead of Integer32.
--    3. Unit clause added to mpegOutputStatsAvailableBandwidth specifying bps.
--    4. Modified all references to QAM and used the word Device instead.
--    5. mpegOutputTSPmtInsertRate description changed, mpegOutputTSPmtInsertRate
--    value changed to tables/ms.
--    6. mpegProgramMappingInputProgIndex in description changed
--    rfDeviceInputProgIndex to mpegInputProgIndex.
--    7. mpegProgramMappingInputTSIndex in description changed
--    rfDeviceInputTSIndex to mpgetInputTSIndex.
--  RevDate
--    200712171700Z
--  RevDescr
--     Changes due to voting comments
--    1. Removed TEXTUAL-CONVENTION import
--    2. Reworded the last sentence of the Module definition.
--    3. Reordered MIB tree to fit under the heDigital branch.
--  RevDate
--    200710031700Z
--  RevDescr
--     Added SCTE-HMS-HEADENDIDENT-TC name for HePidValue, remove name from
--              this file. Created TC ProgDataType so it can be used everywhere. Removed
--              0 from enumerated types just for convention.

mpegMIBObjects OBJECT IDENTIFIER ::= { heMpegCommonMIB 1 }
-- OBJECT-IDENTITY
--  Status
--    mandatory
--  Descr
--    This branch specifies the MPEG Common MIB objects that can be common
--    to any device using MPEG.

mpegDigitalInputs OBJECT IDENTIFIER ::= { mpegMIBObjects 1 }
-- OBJECT-IDENTITY
--  Status
--    mandatory
--  Descr
--    This branch specifies the attributes of the incoming streams
--    to the MPEG device.

mpegOutputs OBJECT IDENTIFIER ::= { mpegMIBObjects 2 }
-- OBJECT-IDENTITY
--  Status
--    mandatory
--  Descr
--    This branch specifies the attributes of the output streams of
--    the MPEG device.

mpegMIBConformance OBJECT IDENTIFIER ::= { heMpegCommonMIB 2 }
-- OBJECT-IDENTITY
--  Status
--    mandatory
--  Descr
--    This branch describes the different MPEG MIB object groups and
--    the different levels of compliance.

mpegMIBCompliances OBJECT IDENTIFIER ::= { mpegMIBConformance 1 }
-- OBJECT-IDENTITY
--  Status
--    mandatory
--  Descr
--    The different levels of compliance to the MPEG MIB.

mpegMIBGroups OBJECT IDENTIFIER ::= { mpegMIBConformance 2 }
-- OBJECT-IDENTITY
--  Status
--    mandatory
--  Descr
--    The MPEG MIB object groups.

mpegLossOfSignalTimeout OBJECT-TYPE
    SYNTAX Gauge
--  Units
--    milliseconds
    ACCESS read-write
    STATUS mandatory
    DESCRIPTION
        "This object specifies the loss of signal timeout on any
        incoming stream."
    ::= { mpegDigitalInputs 1 }

mpegInputTSTable OBJECT-TYPE
    SYNTAX SEQUENCE OF MpegInputTSEntry
    ACCESS not-accessible
    STATUS mandatory
    DESCRIPTION
        "This table specifies the attributes of video sessions or SPTSs."
    ::= { mpegDigitalInputs 2 }

mpegInputTSEntry OBJECT-TYPE
    SYNTAX MpegInputTSEntry
    ACCESS not-accessible
    STATUS mandatory
    DESCRIPTION
        "Each entry specifies the attributes of a transport stream
        (SPTS/MPTS)."
    INDEX { mpegInputTSIndex }
    ::= { mpegInputTSTable 1 }

MpegInputTSEntry ::= SEQUENCE {
    mpegInputTSIndex Gauge,
    mpegInputTSType INTEGER,
    mpegInputTSConnectionType INTEGER,
    mpegInputTSConnection RowPointer,
    mpegInputTSActiveConnection RowPointer,
    mpegInputTSPsiDetected TruthValue,
    mpegInputTSStartTime DateAndTime,
    mpegInputTSResourceAllocated TruthValue,
    mpegInputTSNumPrograms Gauge,
    mpegInputTSRate Gauge,
    mpegInputTSMaxRate Gauge,
    mpegInputTSPatVersion INTEGER,
    mpegInputTSCatVersion INTEGER,
    mpegInputTSNitPid HePIDValue,
    mpegInputTSNumEmms Gauge,
    mpegInputTSTSID Gauge,
    mpegInputTSLock INTEGER
    }

mpegInputTSIndex OBJECT-TYPE
    SYNTAX Gauge
    ACCESS not-accessible
    STATUS mandatory
    DESCRIPTION
        "The unique identifier of the Input TS."
    ::= { mpegInputTSEntry 1 }

mpegInputTSType OBJECT-TYPE
    SYNTAX INTEGER {
        spts(1),
        mpts(2)
        }
    ACCESS read-only
    STATUS mandatory
    DESCRIPTION
        "The type of stream, e.g., SPTS or MPTS."
    ::= { mpegInputTSEntry 2 }

mpegInputTSConnectionType OBJECT-TYPE
    SYNTAX INTEGER {
        other(1),
        udp(2)
        }
    ACCESS read-only
    STATUS mandatory
    DESCRIPTION
        "The type of input flow of the stream.
        The value 'udp' indicates either unicast or multicast 
        udp origination flows."
    ::= { mpegInputTSEntry 3 }

mpegInputTSConnection OBJECT-TYPE
    SYNTAX RowPointer
--    Rsyntax OBJECT IDENTIFIER
    ACCESS read-only
    STATUS mandatory
    DESCRIPTION
        "The reference to the start of the data source table that
        feeds content to the input stream.
        For the Connection Type 'udp' this object contains the
        pointer to the first entry of the UDP Origination table
        
        Below is an example of the value expected for a Connection Type
        'udp'.
        An input stream (mpegInputTSIndex = 8) is being feed by a udp
        Connection (mpegInputUdpOriginationIndex = 4) with 3 associated
        udp streams each one identified by
        mpegInputUdpOriginationId = 1,2,3.
        
        mpegInputTSEntry
        TSIndex   ConnectionType  Connection
        1         1               <any>
        2         1               <any>
                   ...
        8         1               mpegInputUdpOriginationIfIndex.4.3
        9         2               <any>
        
        MpegInputUdpOriginationEntry
        UdpOriginationIndex            UdpOriginationId
        3                              1,4,5
        4                              1,2,3
                    ..."
    ::= { mpegInputTSEntry 4 }

mpegInputTSActiveConnection OBJECT-TYPE
    SYNTAX RowPointer
--    Rsyntax OBJECT IDENTIFIER
    ACCESS read-only
    STATUS mandatory
    DESCRIPTION
        "The reference to the instance of the data source that is
        feeding the input stream.
        For the Connection Type 'udp' this object contains the
        pointer to the UDP Origination table that the input Stream is
        using.
        
        Below is an example of the value expected for a Connection Type
        'udp'.
        An input stream (mpegInputTSIndex = 8) is being feed by a udp
        Connection (mpegInputUdpOriginationIndex = 4) have associated 3
        udp streams each one identified by
        mpegInputUdpOriginationId = 1,2,3. The Udp stream 3 is currently
        used by the input transport stream.
        
        mpegInputTSEntry
        TSIndex   ConnectionType  ActiveConnection
        1         1               <any>
        2         1               <any>
                   ...
        8         1               mpegInputUdpOriginationIfIndex.4.3
        9         2               <any>
        
        MpegInputUdpOriginationEntry
        UdpOriginationIndex            UdpOriginationId
        3                              1,4,5
        4                              1,2,3
                    ...
        Note in the example that the sub oid 4
        (in mpegInputUdpOriginationIfIndex.4.3) represents the sub-oid
        that aggregates all the udp origination flows associated with the
        transport stream."
    ::= { mpegInputTSEntry 5 }

mpegInputTSPsiDetected OBJECT-TYPE
    SYNTAX TruthValue
--    Rsyntax INTEGER {
--        true(1),
--        false(2)
--        }
    ACCESS read-only
    STATUS mandatory
    DESCRIPTION
        "A simple check that Program Specific Information has or has
        not been detected.
        The value 'true' indicates PSI was detected."
    ::= { mpegInputTSEntry 6 }

mpegInputTSStartTime OBJECT-TYPE
    SYNTAX DateAndTime
--    Rsyntax OCTET STRING(SIZE(8|11))
    ACCESS read-only
    STATUS mandatory
    DESCRIPTION
        "Specifies the time the MPEG device started receiving the
        stream, i.e., the time the entry was added to the table."
    ::= { mpegInputTSEntry 7 }

mpegInputTSResourceAllocated OBJECT-TYPE
    SYNTAX TruthValue
--    Rsyntax INTEGER {
--        true(1),
--        false(2)
--        }
    ACCESS read-only
    STATUS mandatory
    DESCRIPTION
        "If true, all resources have been allocated for the stream."
    ::= { mpegInputTSEntry 8 }

mpegInputTSNumPrograms OBJECT-TYPE
    SYNTAX Gauge
    ACCESS read-only
    STATUS mandatory
    DESCRIPTION
        "The number of programs in the input transport stream."
    ::= { mpegInputTSEntry 9 }

mpegInputTSRate OBJECT-TYPE
    SYNTAX Gauge
    ACCESS read-only
    STATUS mandatory
    DESCRIPTION
        "The data rate of the incoming program or SPTS."
    ::= { mpegInputTSEntry 10 }

mpegInputTSMaxRate OBJECT-TYPE
    SYNTAX Gauge
    ACCESS read-only
    STATUS mandatory
    DESCRIPTION
        "The maximum data rate of the incoming stream for either
        a variable or constant bit rate stream (VBR/CVR)."
    ::= { mpegInputTSEntry 11 }

mpegInputTSPatVersion OBJECT-TYPE
    SYNTAX INTEGER(-1..31)
    ACCESS read-only
    STATUS mandatory
    DESCRIPTION
        "Program Association Table version of the transport stream.
        The value -1 means PAT version is not supported for input 
        transport stream."
    DEFVAL { -1 }
    ::= { mpegInputTSEntry 12 }

mpegInputTSCatVersion OBJECT-TYPE
    SYNTAX INTEGER(-1..31)
    ACCESS read-only
    STATUS mandatory
    DESCRIPTION
        "The Conditional Access Table version number of transport
        stream. The value -1 means CAT version is not supported
        for input transport stream."
    DEFVAL { 0 }
    ::= { mpegInputTSEntry 13 }

mpegInputTSNitPid OBJECT-TYPE
    SYNTAX HePIDValue
--    Rsyntax Gauge(0..8191|65535)
    ACCESS read-only
    STATUS mandatory
    DESCRIPTION
        "NIT PID of the input transport stream."
    ::= { mpegInputTSEntry 14 }

mpegInputTSNumEmms OBJECT-TYPE
    SYNTAX Gauge
    ACCESS read-only
    STATUS mandatory
    DESCRIPTION
        "The number of EMMs in the input stream. The default value 9999
        means the device does not support encryption."
    DEFVAL { 9999 }
    ::= { mpegInputTSEntry 15 }

mpegInputTSTSID OBJECT-TYPE
    SYNTAX Gauge
    ACCESS read-only
    STATUS mandatory
    DESCRIPTION
        "The input TSID of the transport stream. A valid TSID is of 16
        bits length. If TSID is not supported, all 32-bits shall be set
        to 1."
    ::= { mpegInputTSEntry 16 }

mpegInputTSLock OBJECT-TYPE
    SYNTAX INTEGER {
        locked(1),
        notLocked(2),
        intermittent(3),
        notMonitored(4)
        }
    ACCESS read-only
    STATUS mandatory
    DESCRIPTION
        "Indicates the lock status of the transport stream.
        'intermittent' means the transport stream is transitioning between
        lock and unlock state over a period of time. This condition is 
        vendor-specific.
        'notMonitored' means the device is not tracking the locking state."
    ::= { mpegInputTSEntry 17 }

mpegInputProgTable OBJECT-TYPE
    SYNTAX SEQUENCE OF MpegInputProgEntry
    ACCESS not-accessible
    STATUS mandatory
    DESCRIPTION
        "The table describing the PSI of each incoming program."
    ::= { mpegDigitalInputs 3 }

mpegInputProgEntry OBJECT-TYPE
    SYNTAX MpegInputProgEntry
    ACCESS not-accessible
    STATUS mandatory
    DESCRIPTION
        "Each entry specifies the parameters for each incoming
        program."
    INDEX { mpegInputTSIndex, mpegInputProgIndex }
    ::= { mpegInputProgTable 1 }

MpegInputProgEntry ::= SEQUENCE {
    mpegInputProgIndex Gauge,
    mpegInputProgNo Gauge,
    mpegInputProgPmtVersion Gauge,
    mpegInputProgPmtPid HePIDValue,
    mpegInputProgPcrPid HePIDValue,
    mpegInputProgEcmPid HePIDValue,
    mpegInputProgNumElems Gauge,
    mpegInputProgNumEcms Gauge,
    mpegInputProgCaDescr OCTET STRING,
    mpegInputProgScte35Descr OCTET STRING,
    mpegInputProgScte18Descr OCTET STRING
    }

mpegInputProgIndex OBJECT-TYPE
    SYNTAX Gauge
    ACCESS not-accessible
    STATUS mandatory
    DESCRIPTION
        "This object serves as the third index of this mib table. The
        index should uniquely identify a program given a transport
        stream index. In other words, it's unique within same transport
        stream."
    ::= { mpegInputProgEntry 1 }

mpegInputProgNo OBJECT-TYPE
    SYNTAX Gauge
    ACCESS read-only
    STATUS mandatory
    DESCRIPTION
        "This object specifies the identifier of the program present
        in the transport stream of the incoming video stream. This
        information is contained in PAT table."
    ::= { mpegInputProgEntry 2 }

mpegInputProgPmtVersion OBJECT-TYPE
    SYNTAX Gauge
    ACCESS read-only
    STATUS mandatory
    DESCRIPTION
        "This object specifies the PMT version of the program. It is a
        5-bit unsigned integer. The default value of 0 means input
        program PMT version is no supported."
    DEFVAL { 0 }
    ::= { mpegInputProgEntry 3 }

mpegInputProgPmtPid OBJECT-TYPE
    SYNTAX HePIDValue
--    Rsyntax Gauge(0..8191|65535)
    ACCESS read-only
    STATUS mandatory
    DESCRIPTION
        "PMT PID of the program."
    ::= { mpegInputProgEntry 4 }

mpegInputProgPcrPid OBJECT-TYPE
    SYNTAX HePIDValue
--    Rsyntax Gauge(0..8191|65535)
    ACCESS read-only
    STATUS mandatory
    DESCRIPTION
        "PCR PID of the program."
    ::= { mpegInputProgEntry 5 }

mpegInputProgEcmPid OBJECT-TYPE
    SYNTAX HePIDValue
--    Rsyntax Gauge(0..8191|65535)
    ACCESS read-only
    STATUS mandatory
    DESCRIPTION
        "This object specifies the ECM PID of the program."
    ::= { mpegInputProgEntry 6 }

mpegInputProgNumElems OBJECT-TYPE
    SYNTAX Gauge
    ACCESS read-only
    STATUS mandatory
    DESCRIPTION
        "The number of elementary streams in the program."
    ::= { mpegInputProgEntry 7 }

mpegInputProgNumEcms OBJECT-TYPE
    SYNTAX Gauge
    ACCESS read-only
    STATUS mandatory
    DESCRIPTION
        "The number of ECMs for the program. The default value 9999
        means the device does not support encryption."
    DEFVAL { 9999 }
    ::= { mpegInputProgEntry 8 }

mpegInputProgCaDescr OBJECT-TYPE
    SYNTAX OCTET STRING(SIZE(0..256))
    ACCESS read-only
    STATUS mandatory
    DESCRIPTION
        "Conditional access descriptor is used to specify both 
        system-wide conditional access management information such as
        EMMS and elementary stream-specific information such as ECMs.
        If any elementary stream is scrambled, a CA descriptor shall be
        present for the program containing that elementary stream. This
        object specifies the CA descriptor for this program.  If the
        program does not have an associated CA descriptor, then this
        object has a zero-length string."
    ::= { mpegInputProgEntry 9 }

mpegInputProgScte35Descr OBJECT-TYPE
    SYNTAX OCTET STRING(SIZE(0..256))
    ACCESS read-only
    STATUS mandatory
    DESCRIPTION
        "SCTE 35 descriptor. If not present, a zero-length string is
        returned. This field is optional for some devices that supports
        large number of input programs due to the fact that extensive 
        decoding can be resource intensive and effect scalability. A
        zero-length string is returned. "
    ::= { mpegInputProgEntry 10 }

mpegInputProgScte18Descr OBJECT-TYPE
    SYNTAX OCTET STRING(SIZE(0..256))
    ACCESS read-only
    STATUS mandatory
    DESCRIPTION
        "SCTE 18 descriptor. If not present, a zero-length string is
        returned. This field is optional for some devices that supports
        large number of input programs due to the fact that extensive 
        decoding can be resource intensive and effect scalability. A
        zero-length string is returned. "
    ::= { mpegInputProgEntry 11 }

mpegProgESTable OBJECT-TYPE
    SYNTAX SEQUENCE OF MpegProgESEntry
    ACCESS not-accessible
    STATUS mandatory
    DESCRIPTION
        "This table contains information about the elementary streams
        in a program."
    ::= { mpegDigitalInputs 4 }

mpegProgESEntry OBJECT-TYPE
    SYNTAX MpegProgESEntry
    ACCESS not-accessible
    STATUS mandatory
    DESCRIPTION
        "A combination of mpegInputTSIndex, mpegInputProgIndex and 
        mpegProgESIndex uniquely identifies an entry in the mpegProgESTable."
    INDEX { mpegInputTSIndex, mpegInputProgIndex, mpegProgESIndex }
    ::= { mpegProgESTable 1 }

MpegProgESEntry ::= SEQUENCE {
    mpegProgESIndex Gauge,
    mpegProgESPID INTEGER,
    mpegProgESType ProgDataType,
    mpegProgESCaDescr OCTET STRING,
    mpegProgESScte35Descr OCTET STRING,
    mpegProgESScte18Descr OCTET STRING
    }

mpegProgESIndex OBJECT-TYPE
    SYNTAX Gauge
    ACCESS not-accessible
    STATUS mandatory
    DESCRIPTION
        "The unique index of the elementary stream."
    ::= { mpegProgESEntry 1 }

mpegProgESPID OBJECT-TYPE
    SYNTAX INTEGER
    ACCESS read-only
    STATUS mandatory
    DESCRIPTION
        "This is the PID for each transport stream packet which
        carries the program element."
    ::= { mpegProgESEntry 2 }

mpegProgESType OBJECT-TYPE
    SYNTAX ProgDataType
--    Rsyntax INTEGER {
--        video(1),
--        audio(2),
--        data(3),
--        other(4)
--        }
    ACCESS read-only
    STATUS mandatory
    DESCRIPTION
        "The type of elementary stream(video, audio, or data) of the
         incoming video session received from the video server."
    ::= { mpegProgESEntry 3 }

mpegProgESCaDescr OBJECT-TYPE
    SYNTAX OCTET STRING(SIZE(0..256))
    ACCESS read-only
    STATUS mandatory
    DESCRIPTION
        "CA descriptor associated with the elementary stream. If there
        is no CA descriptor for the elementary stream, then this object
        has a zero-length string."
    ::= { mpegProgESEntry 4 }

mpegProgESScte35Descr OBJECT-TYPE
    SYNTAX OCTET STRING(SIZE(0..256))
    ACCESS read-only
    STATUS mandatory
    DESCRIPTION
        "SCTE 35 descriptor. If not supported or present, a zero-length
        string is returned."
    ::= { mpegProgESEntry 5 }

mpegProgESScte18Descr OBJECT-TYPE
    SYNTAX OCTET STRING(SIZE(0..256))
    ACCESS read-only
    STATUS mandatory
    DESCRIPTION
        "SCTE 18 descriptor. If not supported or present, a zero-length 
        string is returned."
    ::= { mpegProgESEntry 6 }

mpegInputStatsTable OBJECT-TYPE
    SYNTAX SEQUENCE OF MpegInputStatsEntry
    ACCESS not-accessible
    STATUS mandatory
    DESCRIPTION
        "Stream statistics, SPTS or MPTS."
    ::= { mpegDigitalInputs 5 }

mpegInputStatsEntry OBJECT-TYPE
    SYNTAX MpegInputStatsEntry
    ACCESS not-accessible
    STATUS mandatory
    DESCRIPTION
        "Each entry describes statistics for each Input TS."
    INDEX { mpegInputTSIndex }
    ::= { mpegInputStatsTable 1 }

MpegInputStatsEntry ::= SEQUENCE {
    mpegInputStatsPcrJitter INTEGER,
    mpegInputStatsMaxPacketJitter INTEGER,
    mpegInputStatsPcrPackets Counter,
    mpegInputStatsNonPcrPackets Counter,
    mpegInputStatsUnexpectedPackets Counter,
    mpegInputStatsContinuityErrors Counter,
    mpegInputStatsSyncLossPackets Counter,
    mpegInputStatsPcrIntervalExceeds Counter
    }

mpegInputStatsPcrJitter OBJECT-TYPE
    SYNTAX INTEGER(-1..2147483647)
--  Units
--    nanoseconds
    ACCESS read-only
    STATUS mandatory
    DESCRIPTION
        "This object stores the difference between 
        the actual value of the PCR and its expected value. It is 
        expressed in nanoseconds. This object is default to -1 
        if it's not supported."
    ::= { mpegInputStatsEntry 1 }

mpegInputStatsMaxPacketJitter OBJECT-TYPE
    SYNTAX INTEGER(-1..2147483647)
--  Units
--    milliseconds
    ACCESS read-only
    STATUS mandatory
    DESCRIPTION
        "This object stores the measurement of the maximum variation 
         in arrival time or delay between individual packets. 
         It is expressed in milliseconds. This object is default to -1
         if it's not supported."
    ::= { mpegInputStatsEntry 2 }

mpegInputStatsPcrPackets OBJECT-TYPE
    SYNTAX Counter
    ACCESS read-only
    STATUS mandatory
    DESCRIPTION
        "This reflects the number of MPEG transport packets, having 
        PCR, received for the stream."
    ::= { mpegInputStatsEntry 3 }

mpegInputStatsNonPcrPackets OBJECT-TYPE
    SYNTAX Counter
    ACCESS read-only
    STATUS mandatory
    DESCRIPTION
        "This reflects the number of MPEG transport packets, without 
        PCR, received for the stream. "
    ::= { mpegInputStatsEntry 4 }

mpegInputStatsUnexpectedPackets OBJECT-TYPE
    SYNTAX Counter
    ACCESS read-only
    STATUS mandatory
    DESCRIPTION
        "This reflects the number of transport packets whose PIDs are
        not expected."
    ::= { mpegInputStatsEntry 5 }

mpegInputStatsContinuityErrors OBJECT-TYPE
    SYNTAX Counter
    ACCESS read-only
    STATUS mandatory
    DESCRIPTION
        "Transport packets have continuity counters.  Successive
        packets have contiguous values in the continuity counter.
        Continuity counter error occurs when the successive packets do
        not have contiguous value and discontinuity indicator is not 
        set. This object reflects the number of continuity counter
        errors."
    ::= { mpegInputStatsEntry 6 }

mpegInputStatsSyncLossPackets OBJECT-TYPE
    SYNTAX Counter
    ACCESS read-only
    STATUS mandatory
    DESCRIPTION
        "When a sync byte is missing in a MPEG packet this value is 
        incremented. This value indicates the number of MPEG packets
        that had missing sync byte per stream."
    ::= { mpegInputStatsEntry 7 }

mpegInputStatsPcrIntervalExceeds OBJECT-TYPE
    SYNTAX Counter
    ACCESS read-only
    STATUS mandatory
    DESCRIPTION
        "Indicates the number of times that the interval between two 
        successive PCR packets for any program in the transport stream
        exceeds 100 milliseconds."
    ::= { mpegInputStatsEntry 8 }

mpegInputUdpOriginationTable OBJECT-TYPE
    SYNTAX SEQUENCE OF MpegInputUdpOriginationEntry
    ACCESS not-accessible
    STATUS mandatory
    DESCRIPTION
        "Specifies the UDP unicast or multicast flows of an  
        input transport stram.
        For unicast it represents the UDP port and optionally 
        destination IP address of the input TS origination UDP IP flow.
        for Multicast it represents the set of SSM multicast groups
        of the input TS origination UDP IP flow."
    ::= { mpegDigitalInputs 6 }

mpegInputUdpOriginationEntry OBJECT-TYPE
    SYNTAX MpegInputUdpOriginationEntry
    ACCESS not-accessible
    STATUS mandatory
    DESCRIPTION
        "Each entry specifies the IP UDP information of the 
        input TS origination."
    INDEX { mpegInputUdpOriginationIndex, mpegInputUdpOriginationId }
    ::= { mpegInputUdpOriginationTable 1 }

MpegInputUdpOriginationEntry ::= SEQUENCE {
    mpegInputUdpOriginationIndex Gauge,
    mpegInputUdpOriginationId Gauge,
    mpegInputUdpOriginationIfIndex InterfaceIndex,
    mpegInputUdpOriginationInetAddrType InetAddressType,
    mpegInputUdpOriginationSrcInetAddr InetAddress,
    mpegInputUdpOriginationDestInetAddr InetAddress,
    mpegInputUdpOriginationDestPort InetPortNumber,
    mpegInputUdpOriginationActive TruthValue,
    mpegInputUdpOriginationPacketsDetected TruthValue,
    mpegInputUdpOriginationRank Gauge,
    mpegInputUdpOriginationInputTSIndex Gauge
    }

mpegInputUdpOriginationIndex OBJECT-TYPE
    SYNTAX Gauge
    ACCESS not-accessible
    STATUS mandatory
    DESCRIPTION
        "The unique identifier of the UDP input TS origination 
        information."
    ::= { mpegInputUdpOriginationEntry 1 }

mpegInputUdpOriginationId OBJECT-TYPE
    SYNTAX Gauge
    ACCESS not-accessible
    STATUS mandatory
    DESCRIPTION
        "The unique identifier of each UDP IP flow associated with the 
        input TS UDP origination."
    ::= { mpegInputUdpOriginationEntry 2 }

mpegInputUdpOriginationIfIndex OBJECT-TYPE
    SYNTAX InterfaceIndex
--    Rsyntax INTEGER(1..2147483647)
    ACCESS read-only
    STATUS mandatory
    DESCRIPTION
        "The interface index where the UDP flow is being received."
    ::= { mpegInputUdpOriginationEntry 3 }

mpegInputUdpOriginationInetAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "The address type associated with input TS origination 
        UDP IP flow. 'ipv4' and 'ipv6' are the only used types."
    ::= { mpegInputUdpOriginationEntry 4 }

mpegInputUdpOriginationSrcInetAddr OBJECT-TYPE
    SYNTAX InetAddress
--    Rsyntax OCTET STRING(SIZE(0..255))
    ACCESS read-only
    STATUS mandatory
    DESCRIPTION
        "For Multicast it represents the Source Specific Multicast 
        IP Address of the UDP IP flow.
        For unicast UDP IP flows is either the the IP source address
        of the IP flow or the all zeros address if unknown or irrelevant
        for the input TS."
    ::= { mpegInputUdpOriginationEntry 5 }

mpegInputUdpOriginationDestInetAddr OBJECT-TYPE
    SYNTAX InetAddress
--    Rsyntax OCTET STRING(SIZE(0..255))
    ACCESS read-only
    STATUS mandatory
    DESCRIPTION
        "For multicast it represents the group address of the SSM
        origination input TS.
        For unicast UDP IP flows is either the IP destination address
        of the udp flow  or the all zeros address if unknown or irrelevant
        for the input TS."
    ::= { mpegInputUdpOriginationEntry 6 }

mpegInputUdpOriginationDestPort OBJECT-TYPE
    SYNTAX InetPortNumber
--    Rsyntax Gauge(0..65535)
    ACCESS read-only
    STATUS mandatory
    DESCRIPTION
        "The UDP destination port of the UDP IP flow of the input TS."
    ::= { mpegInputUdpOriginationEntry 7 }

mpegInputUdpOriginationActive OBJECT-TYPE
    SYNTAX TruthValue
--    Rsyntax INTEGER {
--        true(1),
--        false(2)
--        }
    ACCESS read-only
    STATUS mandatory
    DESCRIPTION
        "The activation state of the UDP flow.
        The value 'true' indicates the UDP flow data stream is being 
        sensed or buffered for the input TS, independently of that 
        flow being used for a video session.
        Otherwise the value 'false' is reported.
        For multicast UDP origination flows the value 'true' indicates 
        the UDP flow was successfully joined."
    ::= { mpegInputUdpOriginationEntry 8 }

mpegInputUdpOriginationPacketsDetected OBJECT-TYPE
    SYNTAX TruthValue
--    Rsyntax INTEGER {
--        true(1),
--        false(2)
--        }
    ACCESS read-only
    STATUS mandatory
    DESCRIPTION
        "Indicates whether UDP flow packets are being detected.
        It is vendor dependent the determination if packets for a
        UDP flow are being detected."
    ::= { mpegInputUdpOriginationEntry 9 }

mpegInputUdpOriginationRank OBJECT-TYPE
    SYNTAX Gauge
    ACCESS read-only
    STATUS mandatory
    DESCRIPTION
        "Indicates the Rank Priority used to determine the UDP flow
        selected for the input TS processing and Video Session 
        assignments."
    ::= { mpegInputUdpOriginationEntry 10 }

mpegInputUdpOriginationInputTSIndex OBJECT-TYPE
    SYNTAX Gauge
    ACCESS read-only
    STATUS mandatory
    DESCRIPTION
        "The mpegInputTSIndex that this entry is associated with"
    ::= { mpegInputUdpOriginationEntry 11 }

mpegInsertPacketTable OBJECT-TYPE
    SYNTAX SEQUENCE OF MpegInsertPacketEntry
    ACCESS not-accessible
    STATUS mandatory
    DESCRIPTION
        "This table describes packet insertion information. Typical
        packets that are inserted at the RF output of a device are PSI,
        PSIP, and CVCT MPEG packets. These packets have their own PID.
        This table may be empty if the video device does not support
        packet insertion or do not have any packet insertion
        configured."
    ::= { mpegOutputs 1 }

mpegInsertPacketEntry OBJECT-TYPE
    SYNTAX MpegInsertPacketEntry
    ACCESS not-accessible
    STATUS mandatory
    DESCRIPTION
        "An entry in the Packet Management Table."
    INDEX { mpegInsertPacketIndex }
    ::= { mpegInsertPacketTable 1 }

MpegInsertPacketEntry ::= SEQUENCE {
    mpegInsertPacketIndex Gauge,
    mpegInsertPacketListId Gauge,
    mpegInsertPacketImmediateExecution TruthValue,
    mpegInsertPacketStartTime DateAndTime,
    mpegInsertPacketRepeat INTEGER,
    mpegInsertPacketContinuousFlag TruthValue,
    mpegInsertPacketRate Gauge,
    mpegInsertPacketDeviceIfIndex InterfaceIndex
    }

mpegInsertPacketIndex OBJECT-TYPE
    SYNTAX Gauge(1..65536)
    ACCESS not-accessible
    STATUS mandatory
    DESCRIPTION
        "Index of list of packets being inserted into all MPEG
        streams. This index is unique within the SNMP agent that
                may be managing multiple MPEG devices."
    ::= { mpegInsertPacketEntry 1 }

mpegInsertPacketListId OBJECT-TYPE
    SYNTAX Gauge(0..65535)
    ACCESS read-only
    STATUS mandatory
    DESCRIPTION
        "Reference number of packets being inserted into MPEG stream."
    ::= { mpegInsertPacketEntry 2 }

mpegInsertPacketImmediateExecution OBJECT-TYPE
    SYNTAX TruthValue
--    Rsyntax INTEGER {
--        true(1),
--        false(2)
--        }
    ACCESS read-only
    STATUS mandatory
    DESCRIPTION
        "If true, packet insertion starts immediately."
    ::= { mpegInsertPacketEntry 3 }

mpegInsertPacketStartTime OBJECT-TYPE
    SYNTAX DateAndTime
--    Rsyntax OCTET STRING(SIZE(8|11))
    ACCESS read-only
    STATUS mandatory
    DESCRIPTION
        "Unix epoch start time for insertions (if Immediate Execution
        is false)."
    ::= { mpegInsertPacketEntry 4 }

mpegInsertPacketRepeat OBJECT-TYPE
    SYNTAX INTEGER {
        repeat(1),
        oneTime(2)
        }
    ACCESS read-only
    STATUS mandatory
    DESCRIPTION
        "Indicates whether the insert packet is one-time or
        repetitive."
    ::= { mpegInsertPacketEntry 5 }

mpegInsertPacketContinuousFlag OBJECT-TYPE
    SYNTAX TruthValue
--    Rsyntax INTEGER {
--        true(1),
--        false(2)
--        }
    ACCESS read-only
    STATUS mandatory
    DESCRIPTION
        "If true, packet will be sent periodically, until cancelled."
    ::= { mpegInsertPacketEntry 6 }

mpegInsertPacketRate OBJECT-TYPE
    SYNTAX Gauge
--  Units
--    milliseconds
    ACCESS read-only
    STATUS mandatory
    DESCRIPTION
        "Rate at which packet list should be inserted."
    ::= { mpegInsertPacketEntry 7 }

mpegInsertPacketDeviceIfIndex OBJECT-TYPE
    SYNTAX InterfaceIndex
--    Rsyntax INTEGER(1..2147483647)
    ACCESS read-only
    STATUS mandatory
    DESCRIPTION
        "The ifIndex of the output device interface that the packet will
        be inserted at."
    ::= { mpegInsertPacketEntry 8 }

mpegOutputStatsTable OBJECT-TYPE
    SYNTAX SEQUENCE OF MpegOutputStatsEntry
    ACCESS not-accessible
    STATUS mandatory
    DESCRIPTION
        "The table specifies the diagnostic stats objects for the  
        outputs transport stream of an MPEG device."
    ::= { mpegOutputs 2 }

mpegOutputStatsEntry OBJECT-TYPE
    SYNTAX MpegOutputStatsEntry
    ACCESS not-accessible
    STATUS mandatory
    DESCRIPTION
        "Each entry specifies the diagnostics for each output TS."
    INDEX { mpegOutputTSIndex }
    ::= { mpegOutputStatsTable 1 }

MpegOutputStatsEntry ::= SEQUENCE {
    mpegOutputStatsDroppedPackets Counter,
    mpegOutputStatsFifoOverflow Counter,
    mpegOutputStatsFifoUnderflow Counter,
    mpegOutputStatsDataRate Gauge,
    mpegOutputStatsAvailableBandwidth Gauge,
    mpegOutputStatsChannelUtilization INTEGER,
    mpegOutputStatsTotalPackets Counter
    }

mpegOutputStatsDroppedPackets OBJECT-TYPE
    SYNTAX Counter
    ACCESS read-only
    STATUS mandatory
    DESCRIPTION
        "Number of MPEG packets dropped on this output transport stream."
    ::= { mpegOutputStatsEntry 1 }

mpegOutputStatsFifoOverflow OBJECT-TYPE
    SYNTAX Counter
    ACCESS read-only
    STATUS mandatory
    DESCRIPTION
        "Number of FIFO overflows on this output transport stream."
    ::= { mpegOutputStatsEntry 2 }

mpegOutputStatsFifoUnderflow OBJECT-TYPE
    SYNTAX Counter
    ACCESS read-only
    STATUS mandatory
    DESCRIPTION
        "Number of FIFO underflows on this output transport stream."
    ::= { mpegOutputStatsEntry 3 }

mpegOutputStatsDataRate OBJECT-TYPE
    SYNTAX Gauge
--  Units
--    bps
    ACCESS read-only
    STATUS mandatory
    DESCRIPTION
        "Data rate for the content on this output transport stream."
    ::= { mpegOutputStatsEntry 4 }

mpegOutputStatsAvailableBandwidth OBJECT-TYPE
    SYNTAX Gauge
--  Units
--    bps
    ACCESS read-only
    STATUS mandatory
    DESCRIPTION
        "Unused bandwidth on this port."
    ::= { mpegOutputStatsEntry 5 }

mpegOutputStatsChannelUtilization OBJECT-TYPE
    SYNTAX INTEGER(-1|0..1000)
--  Units
--    0.1 Percent
    ACCESS read-only
    STATUS mandatory
    DESCRIPTION
        "The current utilization of a channel defined as 
        (measured data rate / total bandwidth ) * 1000.
        If not applicable, a value of -1 is returned."
    ::= { mpegOutputStatsEntry 6 }

mpegOutputStatsTotalPackets OBJECT-TYPE
    SYNTAX --?? syntax is not convertable to SMIv1
           Counter
    ACCESS read-only
    STATUS mandatory
    DESCRIPTION
        "The total number of packets output for this transport stream
        since the start of the output stream."
    ::= { mpegOutputStatsEntry 7 }

mpegOutputTSTable OBJECT-TYPE
    SYNTAX SEQUENCE OF MpegOutputTSEntry
    ACCESS not-accessible
    STATUS mandatory
    DESCRIPTION
        "This table specifies the attributes of an outgoing transport
        stream SPTS or MPTS."
    ::= { mpegOutputs 3 }

mpegOutputTSEntry OBJECT-TYPE
    SYNTAX MpegOutputTSEntry
    ACCESS not-accessible
    STATUS mandatory
    DESCRIPTION
        "Each entry specifies the attributes of an output transport
        stream, SPTS or MPTS."
    INDEX { mpegOutputTSIndex }
    ::= { mpegOutputTSTable 1 }

MpegOutputTSEntry ::= SEQUENCE {
    mpegOutputTSIndex Gauge,
    mpegOutputTSType INTEGER,
    mpegOutputTSConnectionType INTEGER,
    mpegOutputTSConnection RowPointer,
    mpegOutputTSNumPrograms Gauge,
    mpegOutputTSTSID Gauge,
    mpegOutputTSNitPid HePIDValue,
    mpegOutputTSCaPid HePIDValue,
    mpegOutputTSCatInsertRate Gauge,
    mpegOutputTSPatInsertRate Gauge,
    mpegOutputTSPmtInsertRate Gauge,
    mpegOutputTSStartTime DateAndTime
    }

mpegOutputTSIndex OBJECT-TYPE
    SYNTAX Gauge
    ACCESS not-accessible
    STATUS mandatory
    DESCRIPTION
        "Table index. It uniquely identifies a mpegOutputTSEntry. 
        This index is independent from mpegOutputTSTSID."
    ::= { mpegOutputTSEntry 1 }

mpegOutputTSType OBJECT-TYPE
    SYNTAX INTEGER {
        spts(1),
        mpts(2)
        }
    ACCESS read-only
    STATUS mandatory
    DESCRIPTION
        "The type of stream, e.g., SPTS or MPTS."
    ::= { mpegOutputTSEntry 2 }

mpegOutputTSConnectionType OBJECT-TYPE
    SYNTAX INTEGER {
        other(1),
        qam(2),
        udp(3)
        }
    ACCESS read-only
    STATUS mandatory
    DESCRIPTION
        "The type of output flow of the stream.
        The value 'qam' indicates a QAM output for the stream
        The value 'udp' indicates either unicast or multicast 
        udp destination flows for the stream."
    ::= { mpegOutputTSEntry 3 }

mpegOutputTSConnection OBJECT-TYPE
    SYNTAX RowPointer
--    Rsyntax OBJECT IDENTIFIER
    ACCESS read-only
    STATUS mandatory
    DESCRIPTION
        "The reference to the instance of the output connection fpr the 
        output stream.
        For the Connection Type 'qam' this object contains the ifIndex object
        identifier of the QAM channel for the output stream.
        
        For the Connection Type 'udp' this object contains the 
        pointer to the UDP Destination table being used for the output stream.
        This is similar to mpegInputTSConnection - See description for details."
    ::= { mpegOutputTSEntry 4 }

mpegOutputTSNumPrograms OBJECT-TYPE
    SYNTAX Gauge
    ACCESS read-only
    STATUS mandatory
    DESCRIPTION
        "The number of programs in the output transport stream."
    ::= { mpegOutputTSEntry 5 }

mpegOutputTSTSID OBJECT-TYPE
    SYNTAX Gauge
    ACCESS read-only
    STATUS mandatory
    DESCRIPTION
        "The TSID of the output transport stream."
    ::= { mpegOutputTSEntry 6 }

mpegOutputTSNitPid OBJECT-TYPE
    SYNTAX HePIDValue
--    Rsyntax Gauge(0..8191|65535)
    ACCESS read-only
    STATUS mandatory
    DESCRIPTION
        "NIT PID of the outgoing transport stream."
    ::= { mpegOutputTSEntry 7 }

mpegOutputTSCaPid OBJECT-TYPE
    SYNTAX HePIDValue
--    Rsyntax Gauge(0..8191|65535)
    ACCESS read-only
    STATUS mandatory
    DESCRIPTION
        "The CA PID of the outgoing transport stream."
    ::= { mpegOutputTSEntry 8 }

mpegOutputTSCatInsertRate OBJECT-TYPE
    SYNTAX Gauge
--  Units
--    tables/ms
    ACCESS read-only
    STATUS mandatory
    DESCRIPTION
        "The CAT insertion rate."
    ::= { mpegOutputTSEntry 9 }

mpegOutputTSPatInsertRate OBJECT-TYPE
    SYNTAX Gauge
--  Units
--    tables/ms
    ACCESS read-only
    STATUS mandatory
    DESCRIPTION
        "The PAT table interval expressed in ms."
    ::= { mpegOutputTSEntry 10 }

mpegOutputTSPmtInsertRate OBJECT-TYPE
    SYNTAX Gauge
--  Units
--    tables/ms
    ACCESS read-only
    STATUS mandatory
    DESCRIPTION
        "The PMT insertion rate. This is expressed in tables/second."
    ::= { mpegOutputTSEntry 11 }

mpegOutputTSStartTime OBJECT-TYPE
    SYNTAX DateAndTime
--    Rsyntax OCTET STRING(SIZE(8|11))
    ACCESS read-only
    STATUS mandatory
    DESCRIPTION
        "This object specifies the time the MPEG device started 
        transmitting the output stream, i.e., the time the entry was
        added to the table.
        The support of this object is optional. If not supported, this
        object is default to a zero length string."
    ::= { mpegOutputTSEntry 12 }

mpegOutputProgTable OBJECT-TYPE
    SYNTAX SEQUENCE OF MpegOutputProgEntry
    ACCESS not-accessible
    STATUS mandatory
    DESCRIPTION
        "The table describing the PSI of each outgoing program."
    ::= { mpegOutputs 4 }

mpegOutputProgEntry OBJECT-TYPE
    SYNTAX MpegOutputProgEntry
    ACCESS not-accessible
    STATUS mandatory
    DESCRIPTION
        "Each entry specifies the parameters for each incoming  
        program."
    INDEX { mpegOutputTSIndex, mpegOutputProgIndex }
    ::= { mpegOutputProgTable 1 }

MpegOutputProgEntry ::= SEQUENCE {
    mpegOutputProgIndex Gauge,
    mpegOutputProgNo Gauge,
    mpegOutputProgPmtVersion Gauge,
    mpegOutputProgPmtPid HePIDValue,
    mpegOutputProgPcrPid HePIDValue,
    mpegOutputProgEcmPid HePIDValue,
    mpegOutputProgNumElems Gauge,
    mpegOutputProgNumEcms Gauge,
    mpegOutputProgCaDescr OCTET STRING,
    mpegOutputProgScte35Descr OCTET STRING,
    mpegOutputProgScte18Descr OCTET STRING
    }

mpegOutputProgIndex OBJECT-TYPE
    SYNTAX Gauge
    ACCESS not-accessible
    STATUS mandatory
    DESCRIPTION
        "This object is the table index for output program."
    ::= { mpegOutputProgEntry 1 }

mpegOutputProgNo OBJECT-TYPE
    SYNTAX Gauge
    ACCESS read-only
    STATUS mandatory
    DESCRIPTION
        "This object specifies the identifier of the program present
        in the transport stream of the outgoing program."
    ::= { mpegOutputProgEntry 2 }

mpegOutputProgPmtVersion OBJECT-TYPE
    SYNTAX Gauge
    ACCESS read-only
    STATUS mandatory
    DESCRIPTION
        "This object specifies the PMT version of the outgoing
        program. The default value of 0 means output program PMT
        version is not supported."
    DEFVAL { 0 }
    ::= { mpegOutputProgEntry 3 }

mpegOutputProgPmtPid OBJECT-TYPE
    SYNTAX HePIDValue
--    Rsyntax Gauge(0..8191|65535)
    ACCESS read-only
    STATUS mandatory
    DESCRIPTION
        "PMT PID of the outgoing program."
    ::= { mpegOutputProgEntry 4 }

mpegOutputProgPcrPid OBJECT-TYPE
    SYNTAX HePIDValue
--    Rsyntax Gauge(0..8191|65535)
    ACCESS read-only
    STATUS mandatory
    DESCRIPTION
        "PCR PID of the outgoing program."
    ::= { mpegOutputProgEntry 5 }

mpegOutputProgEcmPid OBJECT-TYPE
    SYNTAX HePIDValue
--    Rsyntax Gauge(0..8191|65535)
    ACCESS read-only
    STATUS mandatory
    DESCRIPTION
        "This object specifies the ECM PID of the outgoing program."
    ::= { mpegOutputProgEntry 6 }

mpegOutputProgNumElems OBJECT-TYPE
    SYNTAX Gauge
    ACCESS read-only
    STATUS mandatory
    DESCRIPTION
        "The number of elementary streams in the outgoing program."
    ::= { mpegOutputProgEntry 7 }

mpegOutputProgNumEcms OBJECT-TYPE
    SYNTAX Gauge
    ACCESS read-only
    STATUS mandatory
    DESCRIPTION
        "The number of ECMs for the outgoing program. The default value
        9999 means the device does not support encryption."
    DEFVAL { 9999 }
    ::= { mpegOutputProgEntry 8 }

mpegOutputProgCaDescr OBJECT-TYPE
    SYNTAX OCTET STRING(SIZE(0..256))
    ACCESS read-only
    STATUS mandatory
    DESCRIPTION
        "Conditional access descriptor is used to specify both 
        system-wide conditional access management information such as
        EMMS and elementary stream-specific information such as ECMs. 
        If any elementary stream is scrambled, a CA descriptor shall be
        present for the program containing that elementary stream.
        This object specifies the CA descriptor for this program. If 
        the outgoing program does not have an associated CA descriptor,
        then this object has a zero-length string."
    ::= { mpegOutputProgEntry 9 }

mpegOutputProgScte35Descr OBJECT-TYPE
    SYNTAX OCTET STRING(SIZE(0..256))
    ACCESS read-only
    STATUS mandatory
    DESCRIPTION
        "SCTE 35 descriptor in the outgoing program. This object is set 
        to a string of zero-length if there's no SCTE 35 descriptor in
        the outgoing program or not supported."
    ::= { mpegOutputProgEntry 10 }

mpegOutputProgScte18Descr OBJECT-TYPE
    SYNTAX OCTET STRING(SIZE(0..256))
    ACCESS read-only
    STATUS mandatory
    DESCRIPTION
        "SCTE 18 descriptor. If not present or not supported, a
        zero-length string is returned."
    ::= { mpegOutputProgEntry 11 }

mpegOutputProgElemStatsTable OBJECT-TYPE
    SYNTAX SEQUENCE OF MpegOutputProgElemStatsEntry
    ACCESS not-accessible
    STATUS mandatory
    DESCRIPTION
        "The stats associated with the elementary streams of an MPEG
        program."
    ::= { mpegOutputs 5 }

mpegOutputProgElemStatsEntry OBJECT-TYPE
    SYNTAX MpegOutputProgElemStatsEntry
    ACCESS not-accessible
    STATUS mandatory
    DESCRIPTION
        "Each entry constitutes the stats for a program associated with
        a transport stream."
    INDEX { mpegOutputTSIndex, mpegOutputProgIndex, mpegOutputProgElemStatsIndex }
    ::= { mpegOutputProgElemStatsTable 1 }

MpegOutputProgElemStatsEntry ::= SEQUENCE {
    mpegOutputProgElemStatsIndex Gauge,
    mpegOutputProgElemStatsPid HePIDValue,
    mpegOutputProgElemStatsElemType INTEGER,
    mpegOutputProgElemStatsDataRate INTEGER
    }

mpegOutputProgElemStatsIndex OBJECT-TYPE
    SYNTAX Gauge
    ACCESS not-accessible
    STATUS mandatory
    DESCRIPTION
        "The unique identifier of the elementary stream."
    ::= { mpegOutputProgElemStatsEntry 1 }

mpegOutputProgElemStatsPid OBJECT-TYPE
    SYNTAX HePIDValue
--    Rsyntax Gauge(0..8191|65535)
    ACCESS not-accessible
    STATUS mandatory
    DESCRIPTION
        "The Pid of output program elementary stream."
    ::= { mpegOutputProgElemStatsEntry 2 }

mpegOutputProgElemStatsElemType OBJECT-TYPE
    SYNTAX INTEGER {
        video(1),
        audio(2),
        data(3),
        scte18(4),
        scte35(5),
        unknown(6)
        }
    ACCESS read-only
    STATUS mandatory
    DESCRIPTION
        "The type of elementary stream (video, audio, or data) of the
        program. Some devices, such as device, may choose not to report
        exact type due to scalability issues, in which case, this object
        shall be set to unknown."
    ::= { mpegOutputProgElemStatsEntry 3 }

mpegOutputProgElemStatsDataRate OBJECT-TYPE
    SYNTAX INTEGER
--  Units
--    bps
    ACCESS read-only
    STATUS mandatory
    DESCRIPTION
        "The data rate of the elementary stream. Return -1 if not
        supported."
    ::= { mpegOutputProgElemStatsEntry 4 }

mpegOutputUdpDestinationTable OBJECT-TYPE
    SYNTAX SEQUENCE OF MpegOutputUdpDestinationEntry
    ACCESS not-accessible
    STATUS mandatory
    DESCRIPTION
        "Specifies the UDP unicast or multicast of the  
        output TS this entry references.
        For unicast it represents the UDP port and optionally 
        destination IP address of the output TS destination UDP IP flow.
        for Multicast it represents the set of SSM multicast groups
        of the output TS destination UDP IP flow."
    ::= { mpegOutputs 6 }

mpegOutputUdpDestinationEntry OBJECT-TYPE
    SYNTAX MpegOutputUdpDestinationEntry
    ACCESS not-accessible
    STATUS mandatory
    DESCRIPTION
        "Each entry specifies the IP UDP information of the 
        output TS destination."
    INDEX { mpegOutputUdpDestinationIndex, mpegOutputUdpDestinationId }
    ::= { mpegOutputUdpDestinationTable 1 }

MpegOutputUdpDestinationEntry ::= SEQUENCE {
    mpegOutputUdpDestinationIndex Gauge,
    mpegOutputUdpDestinationId Gauge,
    mpegOutputUdpDestinationIfIndex InterfaceIndex,
    mpegOutputUdpDestinationInetAddrType InetAddressType,
    mpegOutputUdpDestinationSrcInetAddr InetAddress,
    mpegOutputUdpDestinationDestInetAddr InetAddress,
    mpegOutputUdpDestinationDestPort InetPortNumber,
    mpegOutputUdpDestinationOutputTSIndex Gauge
    }

mpegOutputUdpDestinationIndex OBJECT-TYPE
    SYNTAX Gauge
    ACCESS not-accessible
    STATUS mandatory
    DESCRIPTION
        "The unique identifier of the UDP output TS destination 
        information."
    ::= { mpegOutputUdpDestinationEntry 1 }

mpegOutputUdpDestinationId OBJECT-TYPE
    SYNTAX Gauge
    ACCESS not-accessible
    STATUS mandatory
    DESCRIPTION
        "The unique identifier of each UDP IP flow associated with the 
        output TS UDP destination."
    ::= { mpegOutputUdpDestinationEntry 2 }

mpegOutputUdpDestinationIfIndex OBJECT-TYPE
    SYNTAX InterfaceIndex
--    Rsyntax INTEGER(1..2147483647)
    ACCESS read-only
    STATUS mandatory
    DESCRIPTION
        "The interface index where the UDP flow is being sent."
    ::= { mpegOutputUdpDestinationEntry 3 }

mpegOutputUdpDestinationInetAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "The address type associated with output TS destination 
        UDP IP flow."
    ::= { mpegOutputUdpDestinationEntry 4 }

mpegOutputUdpDestinationSrcInetAddr OBJECT-TYPE
    SYNTAX InetAddress
--    Rsyntax OCTET STRING(SIZE(0..255))
    ACCESS read-only
    STATUS mandatory
    DESCRIPTION
        "For Multicast it represents the Source Specific Multicast 
        IP Address of the UDP IP flow.
        For unicast UDP IP flows is either the the IP source address
        of the IP flow or the all zeros address if unknown or irrelevant
        for the destination output TS."
    ::= { mpegOutputUdpDestinationEntry 5 }

mpegOutputUdpDestinationDestInetAddr OBJECT-TYPE
    SYNTAX InetAddress
--    Rsyntax OCTET STRING(SIZE(0..255))
    ACCESS read-only
    STATUS mandatory
    DESCRIPTION
        "For multicast it represents the group address of the SSM
        destination output TS.
        For unicast UDP IP flows is either the IP destination address
        of the udp flow  or the all zeros address if unknown or irrelevant
        for the destination output TS."
    ::= { mpegOutputUdpDestinationEntry 6 }

mpegOutputUdpDestinationDestPort OBJECT-TYPE
    SYNTAX InetPortNumber
--    Rsyntax Gauge(0..65535)
    ACCESS read-only
    STATUS mandatory
    DESCRIPTION
        "The UDP port of the UDP IP flow of the output TS."
    ::= { mpegOutputUdpDestinationEntry 7 }

mpegOutputUdpDestinationOutputTSIndex OBJECT-TYPE
    SYNTAX Gauge
    ACCESS read-only
    STATUS mandatory
    DESCRIPTION
        "The mpegOutputTSIndex that this entry is associated with."
    ::= { mpegOutputUdpDestinationEntry 8 }

mpegProgramMappingTable OBJECT-TYPE
    SYNTAX SEQUENCE OF MpegProgramMappingEntry
    ACCESS not-accessible
    STATUS mandatory
    DESCRIPTION
        "This table describes program mappings, i.e., ties the input
        destination to the output destination for every program active
        in the device."
    ::= { mpegMIBObjects 3 }

mpegProgramMappingEntry OBJECT-TYPE
    SYNTAX MpegProgramMappingEntry
    ACCESS not-accessible
    STATUS mandatory
    DESCRIPTION
        "Each entry describes the mapping, i.e., ties input
        destination to output destination for a given program."
    INDEX { mpegProgramMappingIndex }
    ::= { mpegProgramMappingTable 1 }

MpegProgramMappingEntry ::= SEQUENCE {
    mpegProgramMappingIndex Gauge,
    mpegProgramMappingOutputProgIndex Gauge,
    mpegProgramMappingOutputTSIndex Gauge,
    mpegProgramMappingInputProgIndex Gauge,
    mpegProgramMappingInputTSIndex Gauge
    }

mpegProgramMappingIndex OBJECT-TYPE
    SYNTAX Gauge
    ACCESS not-accessible
    STATUS mandatory
    DESCRIPTION
        "The table index uniquely identifies an entry in mpegProgramMappingTable. 
        This index should be unique within the same SNMP agent that may be 
        managing multiple MPEG devices."
    ::= { mpegProgramMappingEntry 1 }

mpegProgramMappingOutputProgIndex OBJECT-TYPE
    SYNTAX Gauge
    ACCESS read-only
    STATUS mandatory
    DESCRIPTION
        "This object is set to mpegOutputProgIndex of the corresponding 
        entry in mpegOutputProgTable for a given output program."
    ::= { mpegProgramMappingEntry 2 }

mpegProgramMappingOutputTSIndex OBJECT-TYPE
    SYNTAX Gauge
    ACCESS read-only
    STATUS mandatory
    DESCRIPTION
        "This object is set to mpegOutputTSIndex of the
        corresponding entry in mpegOutputProgTable for a given output
        program."
    ::= { mpegProgramMappingEntry 3 }

mpegProgramMappingInputProgIndex OBJECT-TYPE
    SYNTAX Gauge
    ACCESS read-only
    STATUS mandatory
    DESCRIPTION
        "This object is set to the value of mpegInputProgIndex of the
        corresponding entry in mpegInputProgTable for a given input
        program."
    ::= { mpegProgramMappingEntry 4 }

mpegProgramMappingInputTSIndex OBJECT-TYPE
    SYNTAX Gauge
    ACCESS read-only
    STATUS mandatory
    DESCRIPTION
        "This object is set to the value of mpegInputTSIndex of the 
        corresponding entry in mpegInputProgTable for a given input 
        program."
    ::= { mpegProgramMappingEntry 5 }

mpegVideoSessionTable OBJECT-TYPE
    SYNTAX SEQUENCE OF MpegVideoSessionEntry
    ACCESS not-accessible
    STATUS mandatory
    DESCRIPTION
        "This table is used to store video session information. The
        session may be of VOD, SDV or DB type. It captures logical 
        information about a video stream, such as source and
        destination addresses, UDP port etc, and also ties it with its
        direct mapping of input and output programs.
        
        This table captures video sessions provisioned by both
        session-based and table-based method. It is capable to support
        N-M mapping of video programs that's required for redundant
        source or video stream cloning etc."
    ::= { mpegMIBObjects 4 }

mpegVideoSessionEntry OBJECT-TYPE
    SYNTAX MpegVideoSessionEntry
    ACCESS not-accessible
    STATUS mandatory
    DESCRIPTION
        "Each entry describes a logical video session."
    INDEX { mpegVideoSessionIndex }
    ::= { mpegVideoSessionTable 1 }

MpegVideoSessionEntry ::= SEQUENCE {
    mpegVideoSessionIndex Gauge,
    mpegVideoSessionPhyMappingIndex Gauge,
    mpegVideoSessionPIDRemap TruthValue,
    mpegVideoSessionMode INTEGER,
    mpegVideoSessionState INTEGER,
    mpegVideoSessionProvMethod INTEGER,
    mpegVideoSessionEncryptionType INTEGER,
    mpegVideoSessionEncryptionInfo AutonomousType,
    mpegVideoSessionBitRate Gauge,
    mpegVideoSessionID OCTET STRING,
    mpegVideoSessionSelectedInput RowPointer,
    mpegVideoSessionSelectedOutput RowPointer
    }

mpegVideoSessionIndex OBJECT-TYPE
    SYNTAX Gauge
    ACCESS not-accessible
    STATUS mandatory
    DESCRIPTION
        "The table index uniquely identifies an entry in 
        mpegVideoSessionTable.
        This index should be unique within the same SNMP agent that
        may be managing multiple MPEG devices."
    ::= { mpegVideoSessionEntry 1 }

mpegVideoSessionPhyMappingIndex OBJECT-TYPE
    SYNTAX Gauge
    ACCESS read-only
    STATUS mandatory
    DESCRIPTION
        "This object shall be set to mpegProgramMappingIndex of the
        corresponding mpegProgramMappingEntry which contains
        physical mapping between the input and output program."
    ::= { mpegVideoSessionEntry 2 }

mpegVideoSessionPIDRemap OBJECT-TYPE
    SYNTAX TruthValue
--    Rsyntax INTEGER {
--        true(1),
--        false(2)
--        }
    ACCESS read-only
    STATUS mandatory
    DESCRIPTION
        "This object value 'true' indicates that the session has PID
        remapping. The value 'false' indicates that the session has no
        PID remapping."
    ::= { mpegVideoSessionEntry 3 }

mpegVideoSessionMode OBJECT-TYPE
    SYNTAX INTEGER {
        other(1),
        passThrough(2),
        multiplexing(3)
        }
    ACCESS read-only
    STATUS mandatory
    DESCRIPTION
        "Indicates whether the transport stream is associated
        with a multiplexed session or is pass-through.
        For pass-through type transport streams, all elementary stream
        level information in optional."
    ::= { mpegVideoSessionEntry 4 }

mpegVideoSessionState OBJECT-TYPE
    SYNTAX INTEGER {
        active(1),
        provisioned(2)
        }
    ACCESS read-only
    STATUS mandatory
    DESCRIPTION
        "active means in-use, provisioned means not-in-use or active 
        such as video session provisioned for redundant source."
    ::= { mpegVideoSessionEntry 5 }

mpegVideoSessionProvMethod OBJECT-TYPE
    SYNTAX INTEGER {
        tableBased(1),
        sessionBased(2),
        other(3)
        }
    ACCESS read-only
    STATUS mandatory
    DESCRIPTION
        "The type of session, e.g., in QAM table-based or session-based."
    ::= { mpegVideoSessionEntry 6 }

mpegVideoSessionEncryptionType OBJECT-TYPE
    SYNTAX INTEGER {
        none(1),
        other(2),
        preencrypted(3),
        des(4),
        des3(5),
        aes(6),
        dvbCsa(7),
        pkey(8),
        mediac(9),
        dvs042(10)
        }
    ACCESS read-only
    STATUS mandatory
    DESCRIPTION
        "Indicates the encryption algorithm of the session."
    ::= { mpegVideoSessionEntry 7 }

mpegVideoSessionEncryptionInfo OBJECT-TYPE
    SYNTAX AutonomousType
--    Rsyntax OBJECT IDENTIFIER
    ACCESS read-only
    STATUS mandatory
    DESCRIPTION
        "Indicates a vendor-specific reference to information 
         associated to the session encryption algorithm."
    ::= { mpegVideoSessionEntry 8 }

mpegVideoSessionBitRate OBJECT-TYPE
    SYNTAX Gauge
--  Units
--    bps
    ACCESS read-only
    STATUS mandatory
    DESCRIPTION
        "Indicates a session throughtput in bps."
    ::= { mpegVideoSessionEntry 9 }

mpegVideoSessionID OBJECT-TYPE
    SYNTAX OCTET STRING(SIZE(0..16))
    ACCESS read-only
    STATUS mandatory
    DESCRIPTION
        "The session ID associated with the stream in the case of a
        session-based QAM. This is not applicable to a table-based QAM.
        This ID may be used by NMS system to uniquely identify an input 
        program to output program mapping."
    ::= { mpegVideoSessionEntry 10 }

mpegVideoSessionSelectedInput OBJECT-TYPE
    SYNTAX RowPointer
--    Rsyntax OBJECT IDENTIFIER
    ACCESS read-only
    STATUS mandatory
    DESCRIPTION
        "The reference to the entry of the input flow currently being
         used in the video session."
    ::= { mpegVideoSessionEntry 11 }

mpegVideoSessionSelectedOutput OBJECT-TYPE
    SYNTAX RowPointer
--    Rsyntax OBJECT IDENTIFIER
    ACCESS read-only
    STATUS mandatory
    DESCRIPTION
        "The reference to the entry of the output flow currently being
         used in the video session."
    ::= { mpegVideoSessionEntry 12 }

mpegVideoSessionPtrTable OBJECT-TYPE
    SYNTAX SEQUENCE OF MpegVideoSessionPtrEntry
    ACCESS not-accessible
    STATUS mandatory
    DESCRIPTION
        "This table is used to provide a quick reference of the 
        Program Mapping and input/output TS connection information 
        associated with a Video Session."
    ::= { mpegMIBObjects 5 }

mpegVideoSessionPtrEntry OBJECT-TYPE
    SYNTAX MpegVideoSessionPtrEntry
    ACCESS not-accessible
    STATUS mandatory
    DESCRIPTION
        "Each entry describes the associations with ProgramMapping and
        transport stream connections."
    INDEX { mpegVideoSessionIndex, mpegVideoSessionPtrInputProgIndex, mpegVideoSessionPtrInputTSIndex, mpegVideoSessionPtrInputTSConnType, mpegVideoSessionPtrInputTSConnection, mpegVideoSessionPtrOutputProgIndex, mpegVideoSessionPtrOutputTSIndex, mpegVideoSessionPtrOutputTSConnType, mpegVideoSessionPtrOutputTSConnection }
    ::= { mpegVideoSessionPtrTable 1 }

MpegVideoSessionPtrEntry ::= SEQUENCE {
    mpegVideoSessionPtrInputProgIndex Gauge,
    mpegVideoSessionPtrInputTSIndex Gauge,
    mpegVideoSessionPtrInputTSConnType Gauge,
    mpegVideoSessionPtrInputTSConnection Gauge,
    mpegVideoSessionPtrOutputProgIndex Gauge,
    mpegVideoSessionPtrOutputTSIndex Gauge,
    mpegVideoSessionPtrOutputTSConnType Gauge,
    mpegVideoSessionPtrOutputTSConnection Gauge,
    mpegVideoSessionPtrStatus INTEGER
    }

mpegVideoSessionPtrInputProgIndex OBJECT-TYPE
    SYNTAX Gauge
    ACCESS not-accessible
    STATUS mandatory
    DESCRIPTION
        "Indicates the Input Program index value of the video
         session."
    ::= { mpegVideoSessionPtrEntry 1 }

mpegVideoSessionPtrInputTSIndex OBJECT-TYPE
    SYNTAX Gauge
    ACCESS not-accessible
    STATUS mandatory
    DESCRIPTION
        "Indicates the input TS index value of the video
         session."
    ::= { mpegVideoSessionPtrEntry 2 }

mpegVideoSessionPtrInputTSConnType OBJECT-TYPE
    SYNTAX Gauge
    ACCESS not-accessible
    STATUS mandatory
    DESCRIPTION
        "Indicates the Input TS Connection type value of the video 
        session."
    ::= { mpegVideoSessionPtrEntry 3 }

mpegVideoSessionPtrInputTSConnection OBJECT-TYPE
    SYNTAX Gauge
    ACCESS not-accessible
    STATUS mandatory
    DESCRIPTION
        "Indicates the Input TS Connection value of the video 
        session."
    ::= { mpegVideoSessionPtrEntry 4 }

mpegVideoSessionPtrOutputProgIndex OBJECT-TYPE
    SYNTAX Gauge
    ACCESS not-accessible
    STATUS mandatory
    DESCRIPTION
        "Indicates the Output Program index value of the video
         session."
    ::= { mpegVideoSessionPtrEntry 5 }

mpegVideoSessionPtrOutputTSIndex OBJECT-TYPE
    SYNTAX Gauge
    ACCESS not-accessible
    STATUS mandatory
    DESCRIPTION
        "Indicates the Output TS index value of the video 
        session."
    ::= { mpegVideoSessionPtrEntry 6 }

mpegVideoSessionPtrOutputTSConnType OBJECT-TYPE
    SYNTAX Gauge
    ACCESS not-accessible
    STATUS mandatory
    DESCRIPTION
        "Indicates the Output TS Connection type value of the video 
        session."
    ::= { mpegVideoSessionPtrEntry 7 }

mpegVideoSessionPtrOutputTSConnection OBJECT-TYPE
    SYNTAX Gauge
    ACCESS not-accessible
    STATUS mandatory
    DESCRIPTION
        "Indicates the Output TS Connection value of the video 
        session."
    ::= { mpegVideoSessionPtrEntry 8 }

mpegVideoSessionPtrStatus OBJECT-TYPE
    SYNTAX INTEGER {
        active(1),
        closed(2)
        }
    ACCESS read-only
    STATUS mandatory
    DESCRIPTION
        "Indicates the status of the session.
        Only active sessions need to be reported."
    ::= { mpegVideoSessionPtrEntry 9 }

mpegInputTSOutputSessionTable OBJECT-TYPE
    SYNTAX SEQUENCE OF MpegInputTSOutputSessionEntry
    ACCESS not-accessible
    STATUS mandatory
    DESCRIPTION
        "Specifies the list of Output Session indexes that the
        Input TS entry is feeding. For unicast it will typically point
        to just one output Session. For multicast, it will point to
        all the output Sessions using this internally replicated
        input TS."
    ::= { mpegMIBObjects 6 }

mpegInputTSOutputSessionEntry OBJECT-TYPE
    SYNTAX MpegInputTSOutputSessionEntry
    ACCESS not-accessible
    STATUS mandatory
    DESCRIPTION
        "Each entry specifies the sessionID associated with the
        Input TS Entry Index."
    INDEX { mpegInputTSIndex, mpegVideoSessionIndex }
    ::= { mpegInputTSOutputSessionTable 1 }

MpegInputTSOutputSessionEntry ::= SEQUENCE {
    mpegInputTSOutputSessionCreateTime DateAndTime
    }

mpegInputTSOutputSessionCreateTime OBJECT-TYPE
    SYNTAX DateAndTime
--    Rsyntax OCTET STRING(SIZE(8|11))
    ACCESS read-only
    STATUS mandatory
    DESCRIPTION
        "Indicates the Creation Time of the session referenced by 
        this entry."
    ::= { mpegInputTSOutputSessionEntry 1 }

mpegInputGroup OBJECT IDENTIFIER ::= { mpegMIBGroups 1 }
-- OBJECT-GROUP
--  Status
--    mandatory
--  Descr
--    The input objects of the MPEG device.
--  objects
--    mpegInputTSType, mpegInputTSConnectionType, 
--    mpegInputTSConnection, mpegInputTSActiveConnection, 
--    mpegLossOfSignalTimeout, mpegInputTSPsiDetected, 
--    mpegInputTSStartTime, mpegInputTSResourceAllocated, 
--    mpegInputTSNumPrograms, mpegInputTSRate, mpegInputTSMaxRate, 
--    mpegInputTSPatVersion, mpegInputTSCatVersion, 
--    mpegInputTSNitPid, mpegInputTSNumEmms, mpegInputTSTSID, 
--    mpegInputTSLock, mpegInputUdpOriginationIfIndex, 
--    mpegInputUdpOriginationInetAddrType, 
--    mpegInputUdpOriginationSrcInetAddr, 
--    mpegInputUdpOriginationDestInetAddr, 
--    mpegInputUdpOriginationDestPort, 
--    mpegInputUdpOriginationActive, 
--    mpegInputUdpOriginationPacketsDetected, 
--    mpegInputUdpOriginationRank, 
--    mpegInputUdpOriginationInputTSIndex, mpegInputProgPmtVersion, 
--    mpegInputProgNo, mpegInputProgPmtVersion, mpegInputProgPmtPid, 
--    mpegInputProgPcrPid, mpegInputProgEcmPid, 
--    mpegInputProgNumElems, mpegInputProgNumEcms, 
--    mpegInputProgCaDescr, mpegInputProgScte35Descr, 
--    mpegInputProgScte18Descr, mpegInputStatsPcrPackets, 
--    mpegInputStatsNonPcrPackets, mpegInputStatsUnexpectedPackets, 
--    mpegInputStatsContinuityErrors, mpegInputStatsSyncLossPackets, 
--    mpegInputStatsPcrIntervalExceeds, mpegInputStatsPcrJitter, 
--    mpegInputStatsMaxPacketJitter

mpegInputProgESGroup OBJECT IDENTIFIER ::= { mpegMIBGroups 2 }
-- OBJECT-GROUP
--  Status
--    mandatory
--  Descr
--    This table contains information about the elementary streams
--    in a program. 
--  objects
--    mpegProgESScte18Descr, mpegProgESScte35Descr, 
--    mpegProgESCaDescr, mpegProgESPID, mpegProgESType

mpegOutputGroup OBJECT IDENTIFIER ::= { mpegMIBGroups 3 }
-- OBJECT-GROUP
--  Status
--    mandatory
--  Descr
--    The output objects of the MPEG device.
--  objects
--    mpegInsertPacketListId, mpegInsertPacketImmediateExecution, 
--    mpegInsertPacketStartTime, mpegInsertPacketRepeat, 
--    mpegInsertPacketContinuousFlag, mpegInsertPacketRate, 
--    mpegInsertPacketDeviceIfIndex, mpegOutputStatsDroppedPackets, 
--    mpegOutputStatsFifoOverflow, mpegOutputStatsFifoUnderflow, 
--    mpegOutputStatsDataRate, mpegOutputStatsAvailableBandwidth, 
--    mpegOutputProgNo, mpegOutputProgPmtVersion, 
--    mpegOutputProgPmtPid, mpegOutputProgPcrPid, 
--    mpegOutputProgEcmPid, mpegOutputProgNumElems, 
--    mpegOutputProgNumEcms, mpegOutputProgCaDescr, 
--    mpegOutputProgScte35Descr, mpegOutputTSType, 
--    mpegOutputTSConnectionType, mpegOutputTSConnection, 
--    mpegOutputTSNumPrograms, mpegOutputTSTSID, mpegOutputTSNitPid, 
--    mpegOutputTSCaPid, mpegOutputTSCatInsertRate, 
--    mpegOutputTSPatInsertRate, mpegOutputProgScte18Descr, 
--    mpegOutputTSPmtInsertRate, mpegOutputTSStartTime, 
--    mpegOutputUdpDestinationIfIndex, 
--    mpegOutputUdpDestinationInetAddrType, 
--    mpegOutputUdpDestinationSrcInetAddr, 
--    mpegOutputUdpDestinationDestInetAddr, 
--    mpegOutputUdpDestinationDestPort, 
--    mpegOutputUdpDestinationOutputTSIndex, 
--    mpegOutputStatsChannelUtilization, 
--    mpegOutputStatsTotalPackets

mpegOutputProgElemStatsGroup OBJECT IDENTIFIER ::= { mpegMIBGroups 4 }
-- OBJECT-GROUP
--  Status
--    mandatory
--  Descr
--    The stats associated with the elementary streams of an MPEG
--    program.
--  objects
--    mpegOutputProgElemStatsDataRate, 
--    mpegOutputProgElemStatsElemType

mpegMappingsGroup OBJECT IDENTIFIER ::= { mpegMIBGroups 5 }
-- OBJECT-GROUP
--  Status
--    mandatory
--  Descr
--    The group of objects describing program mappings within the
--    Device.
--  objects
--    mpegProgramMappingOutputProgIndex, 
--    mpegProgramMappingOutputTSIndex, 
--    mpegProgramMappingInputProgIndex, 
--    mpegProgramMappingInputTSIndex

mpegSessionsGroup OBJECT IDENTIFIER ::= { mpegMIBGroups 6 }
-- OBJECT-GROUP
--  Status
--    mandatory
--  Descr
--    The group of objects describing program mappings within the
--    Device.
--  objects
--    mpegVideoSessionPhyMappingIndex, mpegVideoSessionPIDRemap, 
--    mpegVideoSessionMode, mpegVideoSessionState, 
--    mpegVideoSessionProvMethod, mpegVideoSessionEncryptionType, 
--    mpegVideoSessionEncryptionInfo, mpegVideoSessionBitRate, 
--    mpegVideoSessionID, mpegVideoSessionSelectedInput, 
--    mpegVideoSessionSelectedOutput, mpegVideoSessionPtrStatus, 
--    mpegInputTSOutputSessionCreateTime

mpegSupport OBJECT IDENTIFIER ::= { mpegMIBCompliances 1 }
-- MODULE-COMPLIANCE
--  Status
--    mandatory
--  Descr
--    These objects describe the support level for MPEG.
--  Module
--    >>current<<
--   MandGroup
--    mpegInputGroup
--   MandGroup
--    mpegOutputGroup
--   OptGroup
--    mpegMappingsGroup
--   OptGroup
--    mpegSessionsGroup
--   OptGroup
--    mpegInputProgESGroup
--   OptGroup
--    mpegOutputProgElemStatsGroup


END
