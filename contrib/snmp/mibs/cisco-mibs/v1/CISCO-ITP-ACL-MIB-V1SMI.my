-- MIB file created 25-Oct-2001 16:44:13, by
--   SMICng version 2.2.11-beta(PRO)(Solaris), January 20, 2001. Enterprise key cisco.com

CISCO-ITP-ACL-MIB DEFINITIONS ::= BEGIN

-- From file: "CISCO-ITP-ACL-MIB.my"
-- Compile options "4 7 F H N W 03 06 0B 0G 0N 0T"

IMPORTS
    SnmpAdminString
            FROM SNMP-FRAMEWORK-MIB
    RowStatus, TimeStamp
            FROM SNMPv2-TC-v1
    CItpTcAclId, CItpTcEncodingSchemeValue, 
    CItpTcGlobalTitleSelector, CItpTcNAI, CItpTcNumberingPlan, 
    CItpTcPointCode, CItpTcPointCodeMask, CItpTcServiceIndicator, 
    CItpTcSubSystemNumber, CItpTcSubSystemNumberMask, 
    CItpTcTranslationType
            FROM CISCO-ITP-TC-MIB
    ciscoMgmt
            FROM CISCO-SMI
    Gauge
            FROM RFC1155-SMI
    OBJECT-TYPE
            FROM RFC-1212;

ciscoItpAclMIB OBJECT IDENTIFIER ::= { ciscoMgmt 227 }
-- MODULE-IDENTITY
--  LastUpdated
--    200108290000Z
--  OrgName
--    Cisco Systems, Inc.
--  ContactInfo
--           Cisco Systems, Inc
--            Customer Service
--    
--    Postal: 170 W. Tasman Drive
--            San Jose, CA  95134
--            USA
--    
--       Tel: +1 800 553-NETS
--    
--    E-mail: cs-ss7@cisco.com
--  Descr
--    The MIB for managing access lists that control
--     messages transported over Signalling System 
--     No. 7 (SS7) Network via Cisco IP Transfer
--     Point.  
--     
--     The Cisco IP Transfer Point (ITP) is a hardware 
--     and software solution that transports SS7 traffic 
--     using IP. Each ITP node provides function similar
--     to SS7 signaling point.   
--     
--     The relevant ITU documents describing this technology
--     is the ITU Q series, including ITU Q.700: Introduction
--     to CCITT Signalling System No. 7 and ITU Q.701 
--     Functional description of the message transfer part
--     (MTP) of Signalling System No. 7.
--  RevDate
--    200108290000Z
--  RevDescr
--    Initial version of this MIB module.

cItpAclMIBNotifs OBJECT IDENTIFIER ::= { ciscoItpAclMIB 0 }
cItpAclMIBObjects OBJECT IDENTIFIER ::= { ciscoItpAclMIB 1 }
cItpAclMIBConformance OBJECT IDENTIFIER ::= { ciscoItpAclMIB 2 }
cItpAclScalars  OBJECT IDENTIFIER ::= { cItpAclMIBObjects 1 }
cItpAclConfig   OBJECT IDENTIFIER ::= { cItpAclMIBObjects 2 }
cItpAclMIBCompliances OBJECT IDENTIFIER ::= { cItpAclMIBConformance 1 }
cItpAclMIBGroups OBJECT IDENTIFIER ::= { cItpAclMIBConformance 2 }

CItpAclAction ::= INTEGER {
        accept(1),
        discard(2)
        }
-- TEXTUAL-CONVENTION
--  Status
--    mandatory
--  Descr
--    The list of possible actions to be performed on a
--     packet when information in message matches an access
--     control entry .
--     
--     'accept'  : The matching packet is accepted for
--                 further processing.
--     'discard' : The matching packet is to be discarded
--                 without any further processing on this 
--                 packet.

cItpAclConfigLastChanged OBJECT-TYPE
    SYNTAX TimeStamp
--    Rsyntax TimeTicks
    ACCESS read-only
    STATUS mandatory
    DESCRIPTION
        "The value of sysUpTime at the time of the last
         creation or deletion of an entry in the cItpAclTable.
         If the local network management subsystem is 
         re-initialization, then this object contains the 
         sysUpTime at the time when this occurred. This value 
         can be used to prevent unnecessary walks of the
         cItpAclTable."
    ::= { cItpAclScalars 1 }

cItpAclTable OBJECT-TYPE
    SYNTAX SEQUENCE OF CItpAclTableEntry
    ACCESS not-accessible
    STATUS mandatory
    DESCRIPTION
        "A table of SP access controls. The access control
         definition controls which packets are accepted or
         rejected. The access control may be applied before
         sending the packet to the routing table or may be
         applied after the packet is processed by the routing
         table. Entries are added to this table via
         cItpAclRowStatus in accordance with the RowStatus
         convention."
    ::= { cItpAclConfig 1 }

cItpAclTableEntry OBJECT-TYPE
    SYNTAX CItpAclTableEntry
    ACCESS not-accessible
    STATUS mandatory
    DESCRIPTION
        "A list of Signalling Point access control attributes."
    INDEX { cItpAclId, cItpAclEntryType, cItpAclEntryNumber }
    ::= { cItpAclTable 1 }

CItpAclTableEntry ::= SEQUENCE {
    cItpAclId CItpTcAclId,
    cItpAclEntryType INTEGER,
    cItpAclEntryNumber Gauge,
    cItpAclAction CItpAclAction,
    cItpAclParameters OCTET STRING,
    cItpAclDpc CItpTcPointCode,
    cItpAclDpcMask CItpTcPointCodeMask,
    cItpAclOpc CItpTcPointCode,
    cItpAclOpcMask CItpTcPointCodeMask,
    cItpAclSi CItpTcServiceIndicator,
    cItpAclPattern SnmpAdminString,
    cItpAclOffset Gauge,
    cItpAclComment SnmpAdminString,
    cItpAclCgpa CItpTcPointCode,
    cItpAclCgpaMask CItpTcPointCodeMask,
    cItpAclCgpaSsn CItpTcSubSystemNumber,
    cItpAclCgpaSsnMask CItpTcSubSystemNumberMask,
    cItpAclCdpa CItpTcPointCode,
    cItpAclCdpaMask CItpTcPointCodeMask,
    cItpAclCdpaSsn CItpTcSubSystemNumber,
    cItpAclCdpaSsnMask CItpTcSubSystemNumberMask,
    cItpAclGtiSelector CItpTcGlobalTitleSelector,
    cItpAclGtiTranslateType CItpTcTranslationType,
    cItpAclGtiNumberingPlan CItpTcNumberingPlan,
    cItpAclGtiNai CItpTcNAI,
    cItpAclGtiEsv CItpTcEncodingSchemeValue,
    cItpAclAft CItpTcPointCode,
    cItpAclAftMask CItpTcPointCodeMask,
    cItpAclAftSsn CItpTcSubSystemNumber,
    cItpAclAftSsnMask CItpTcSubSystemNumberMask,
    cItpAclRowStatus RowStatus
    }

cItpAclId OBJECT-TYPE
    SYNTAX CItpTcAclId
--    Rsyntax Gauge(0|2700..2999)
    ACCESS not-accessible
    STATUS mandatory
    DESCRIPTION
        "The identifier used to select a list of access list
         entries. The administrator will select an valid 
         identifier within the specified range defined for 
         SS7 access lists."
    ::= { cItpAclTableEntry 1 }

cItpAclEntryType OBJECT-TYPE
    SYNTAX INTEGER {
        comment(1),
        entry(2)
        }
    ACCESS not-accessible
    STATUS mandatory
    DESCRIPTION
        "The list of possible entry types.
         'comments'  : A statement used to describe and document
                       access list entries.
         'entry'     : A access list entry."
    ::= { cItpAclTableEntry 2 }

cItpAclEntryNumber OBJECT-TYPE
    SYNTAX Gauge(1..65535)
    ACCESS not-accessible
    STATUS mandatory
    DESCRIPTION
        "An numeric value assigned to each access list entry.
         The entries of the same type must be unique. Entries 
         will be tested in ascending order."
    ::= { cItpAclTableEntry 3 }

cItpAclAction OBJECT-TYPE
    SYNTAX CItpAclAction
--    Rsyntax INTEGER {
--        accept(1),
--        discard(2)
--        }
    ACCESS read-write
    STATUS mandatory
    DESCRIPTION
        "The action to be performed on the packet that matched
         this access control."
    DEFVAL { accept }
    ::= { cItpAclTableEntry 4 }

cItpAclParameters OBJECT-TYPE
    SYNTAX OCTET STRING(SIZE(1..2))
        -- BITS are:
        --   si(0)
        --   dpc(1)
        --   dpcMask(2)
        --   opc(3)
        --   opcMask(4)
        --   pattern(5)
        --   comment(6)
        --   cgpa(7)
        --   cgpaMask(8)
        --   cdpa(9)
        --   cdpaMask(10)
        --   selector(11)
        --   aft(12)
        --   aftMask(13)
        --   all(14)
    ACCESS read-write
    STATUS mandatory
    DESCRIPTION
        "The cItpAclType object indicates which types of tests 
         will be processed on the each access list entry.
         Each may contain one or more filters. The filter will
         be processed ascending order(si,dpc...all). Each test 
         is evaluated and if true the packet is processed
         according to cItpAclAction. 
        
        'si'      : The cItpAclSi is the relevant column. The packet
                    is compared to cItpAclSi to determine if the 
                    packet matches this filter.
                    
        'dpc'     : The cItpAclDpc and cItpAclDpcMask are the relevant
                    columns. The packet is compared to cItpAclDpc
                    in conjunction with cItpAclDpcMask to determine
                    if the packet matches this access control.
                    The mask is first negated (~mask) and bitwise
                    AND is perform with mask and dpc.
                    
        'dpcMask' : Indicates that a mask is to be applied when the
                    dpc filter is specified. If the mask is not 
                    specified then the mask is assumed to be all 
                    zeros.
                
        'opc'     : cItpAclOpc and cItpAclOpcMask are the relevant
                    columns. The packet is compared to cItpAclOpc
                    in conjunction with cItpAclOpcMask to determine
                    if the packet matches this access control.
                    The mask is first negated (~mask) and bitwise
                    AND is perform with mask and opc.
                    
        'opcMask' : Indicates that a mask is to be applied when the
                    opc filter is specified. If the mask is not 
                    specified then the mask is assumed to be all 
                    zeros.
                
        'pattern' : cItpAclPattern and cItpAclOffset are the 
                    relevant columns. The matching criteria is 
                    based on matching the pattern specified by 
                    cItpAclPattern at offset cItpAclOffset from 
                    the start of the packet.
                    
        
        'comment' : The cItpAclComment object provides an entry 
                    that can be used to describe filters.
                     
        'cgpa'    : The cItpAclCgpa, cItpAclCgpaMask, 
                    cItpAclCgpaSsn and cItpAclCgpaSsnMask are the
                    relevant columns.  The Calling Party Point code
                    is compare with cItpAclCgpaPC using the 
                    ItpAclCgpaMask. Also, the cItpAclCgpaSsn 
                    and cItpAclCgpaSsnMask are compared if specified.
                    
        'cgpaMask': Indicates that a mask is to be applied when the
                    cgpa filter is specified. If the mask is not 
                    specified then the mask is assumed to be all 
                    zeros.
                    
        'cgpaSsn' : Indicates that a Subsystem Number(SSN) is to
                    be checked when the cgpa filter is specified. 
                    
        'cgpaSsnMask': Indicates that SSN mask is to be applied 
                    when checking the SSN number for the cgpa 
                    filter is specified. If the mask is not 
                    specified then the mask is assumed to be all 
                    zeros.
                    
        'cdpa'    : The cItpAclCdpa, cItpAclCdpaMask, 
                    cItpAclCdpaSsn and cItpAclCdpaSsnMask are the
                    relevant columns.  The Called Party Point code
                    is compared with cItpAclCcpa using the 
                    ItpAclCcpaMask. Also, the cItpAclCcpaSsn 
                    and cItpAclCcpaSsnMask are compared if specified.
                    
        'cdpaMask': Indicates that a mask is to be applied when the
                    cdpa filter is specified. If the mask is not 
                    specified then the mask is assumed to be all 
                    zeros.
                    
        'cdpaSsn' : Indicates that a SSN is to be checked when the
                    cdpa filter is specified. 
                    
        'cdpaSsnMask': Indicates that SSN mask is to be applied 
                    when checking the SSN number for the cdpa 
                    filter is specified. If the mask is not 
                    specified then the mask is assumed to be all 
                    zeros.
        
        'selector': The Global Title Selector is used to select 
                    which objects will be tested and in what order
                    the tests will be applied as follows.
                                                                      x
                    The types of translations are different based on 
                    the variant. In both, variants the translation 
                    type and other parameters are used to provide the 
                    following types of translations.
                    
                    - Intermediate GTT resulting in MSUs routed to a 
                      solitary point code
                      
                    - Intermediate GTT resulting in MSUs load 
                      balanced across two or more point codes
                      
                    - Final GTT routed to a solitary point code
                    
                    - Final GTT routed to a primary and backup 
                      point-code and SSN (dominant mode)
                      
                    - Final GTT load balanced across a group of 
                      point-codes and subsystems
                      
                    For ANSI the translation types are defined in 
                    TABLE B.1/T1.112.3 of TR-NWT-000246.  The ANSI 
                    selector table may be a simple flat table/array of 
                    256 Translation Types(0-255).  In this method of 
                    translation tables can be directly accessed using 
                    the translation type from the Called Party Point 
                    Code.  
                    
                    For ITU section 2.4.5 of ITU-T Q.714, defines the 
                    use of the Global Tile Indicator(GTI), along with 
                    Translation Type(TT), Network Plan(NP), and Nature 
                    of Address Indicator(NAI), as selectors for the 
                    table to perform the Global Title 
                    Translation(GTT).  In this cae the selector table 
                    must be searched using a combination oF GTI, TT, 
                    NP and NAI.  
                    
                    The objects cItpAclGtiSelector, 
                    cItpAclGtiTranslateType, cItpAclGtiNumberingPlan, 
                    cItpAclGtiNai, and cItpAclGtiEsv are the relevant 
                    columns.  These object will be used in the 
                    following order based on variant and translation 
                    type.  
                    
                    1 => cItpAclGtiNai
                    2 => cItpAclGtiTranslateType
                    3 => cItpAclGtiTranslateType
                             cItpAclGtiNumberingPlan
                                 cItpAclGtiEsv
                    4 => cItpAclGtiTranslateType
                             cItpAclGtiNumberingPlan
                                 cItpAclGtiNai
                                      cItpAclGtiEsv
                
                                          
        'aft'    :  The cItpAclAft, cItpAclAftMask, 
                    cItpAclAftSsn and cItpAclAftSsnMask are the
                    relevant columns.  The affected point code is 
                    compared with cItpAclAftPC using the 
                    ItpAclAftMask. Also, the cItpAclAftSsn 
                    and cItpAclAftSsnMask are compared if 
                    specified.
                    
        'aftMask':  Indicates that a mask is to be applied when the
                    aft filter is specified. If the mask is not 
                    specified then the mask is assumed to be all 
                    zeros.
                    
        'all'    :  Used in conjunction with cItpAclAction to specify
                    defaults for packet that did not match any 
                    specified access list entry."
    ::= { cItpAclTableEntry 5 }

cItpAclDpc OBJECT-TYPE
    SYNTAX CItpTcPointCode
--    Rsyntax Gauge(0..16777216)
    ACCESS read-write
    STATUS mandatory
    DESCRIPTION
        "The destination point code specified for this ACL. The 
         'dpc' bit in the cItpAclParameters object is used 
         indicate whether this object has been specified."
    ::= { cItpAclTableEntry 6 }

cItpAclDpcMask OBJECT-TYPE
    SYNTAX CItpTcPointCodeMask
--    Rsyntax Gauge(0..16777216)
    ACCESS read-write
    STATUS mandatory
    DESCRIPTION
        "The mask used to define which part of the point code
         in the packet is significant when comparing the  
         destination point code with cItpAclDpc. The 
         'dpcMask' bit in the cItpAclParameters object is used 
         indicate whether this object has been specified."
    ::= { cItpAclTableEntry 7 }

cItpAclOpc OBJECT-TYPE
    SYNTAX CItpTcPointCode
--    Rsyntax Gauge(0..16777216)
    ACCESS read-write
    STATUS mandatory
    DESCRIPTION
        "The origin point code specified in this ACL. The 
         'opc' bit in the cItpAclParameters object is used 
         indicate whether this object has been specified."
    ::= { cItpAclTableEntry 8 }

cItpAclOpcMask OBJECT-TYPE
    SYNTAX CItpTcPointCodeMask
--    Rsyntax Gauge(0..16777216)
    ACCESS read-write
    STATUS mandatory
    DESCRIPTION
        "The mask used to define which part of the origin
         point code in the packet is significant when comparing
         the origin point code with cItpAclDpc.  The 
         'opcMask' bit in the cItpAclParameters object is used 
         indicate whether this object has been specified."
    ::= { cItpAclTableEntry 9 }

cItpAclSi OBJECT-TYPE
    SYNTAX CItpTcServiceIndicator
--    Rsyntax INTEGER {
--        ?? enum value of zero may cause problems
--        snmm(0),
--        sntm(1),
--        spare2(2),
--        sccp(3),
--        tup(4),
--        isup(5),
--        dupc(6),
--        dupf(7),
--        mtup(8),
--        bisup(9),
--        sisup(10),
--        spare11(11),
--        spare12(12),
--        spare13(13),
--        spare14(14),
--        spare15(15)
--        }
    ACCESS read-write
    STATUS mandatory
    DESCRIPTION
        "The Service Indicator Octet. The 'si' bit in the 
         cItpAclParameters object is used indicate whether 
         this object has been specified."
    ::= { cItpAclTableEntry 10 }

cItpAclPattern OBJECT-TYPE
    SYNTAX SnmpAdminString(SIZE(0..40))
--    Rsyntax OCTET STRING(SIZE(0..40))
    ACCESS read-write
    STATUS mandatory
    DESCRIPTION
        "The pattern used to match a packet at offset
         cItpAclOffset.  The 'pattern' bit in the 
         cItpAclParameters object is used indicate whether
         this object has been specified."
    ::= { cItpAclTableEntry 11 }

cItpAclOffset OBJECT-TYPE
    SYNTAX Gauge(0..255)
    ACCESS read-write
    STATUS mandatory
    DESCRIPTION
        "The offset into the packet were we begin matching the
         pattern specified by cItpAclPattern is to start.  The 
         'pattern' bit in the cItpAclParameters object is used
         indicate whether this object has been specified."
    ::= { cItpAclTableEntry 12 }

cItpAclComment OBJECT-TYPE
    SYNTAX SnmpAdminString(SIZE(0..100))
--    Rsyntax OCTET STRING(SIZE(0..100))
    ACCESS read-write
    STATUS mandatory
    DESCRIPTION
        "A brief description used to document access list 
         entries.  The 'comment' bit in the cItpAclParameters 
         object is used indicate whether this object has been 
         specified."
    ::= { cItpAclTableEntry 13 }

cItpAclCgpa OBJECT-TYPE
    SYNTAX CItpTcPointCode
--    Rsyntax Gauge(0..16777216)
    ACCESS read-write
    STATUS mandatory
    DESCRIPTION
        "The Calling Party Point Code.  The 'cgpa' bit in the 
         cItpAclParameters object is used indicate whether this 
         object has been specified."
    ::= { cItpAclTableEntry 14 }

cItpAclCgpaMask OBJECT-TYPE
    SYNTAX CItpTcPointCodeMask
--    Rsyntax Gauge(0..16777216)
    ACCESS read-write
    STATUS mandatory
    DESCRIPTION
        "The Calling Party Point Code mask.  The 'cgpaMask' bit
         in the cItpAclParameters object is used indicate 
         whether this object has been specified."
    ::= { cItpAclTableEntry 15 }

cItpAclCgpaSsn OBJECT-TYPE
    SYNTAX CItpTcSubSystemNumber
--    Rsyntax Gauge(0|2..255)
    ACCESS read-write
    STATUS mandatory
    DESCRIPTION
        "The Calling Party Point Code subsystem number. The
         'cgpa' bit in the cItpAclParameters object is used 
         indicate whether this object has been specified."
    ::= { cItpAclTableEntry 16 }

cItpAclCgpaSsnMask OBJECT-TYPE
    SYNTAX CItpTcSubSystemNumberMask
--    Rsyntax Gauge(2..255)
    ACCESS read-write
    STATUS mandatory
    DESCRIPTION
        "The Calling Party Point Code subsystem number Mask.  
         The 'cgpa' bit in the cItpAclParameters object is used 
         indicate whether this object has been specified."
    ::= { cItpAclTableEntry 17 }

cItpAclCdpa OBJECT-TYPE
    SYNTAX CItpTcPointCode
--    Rsyntax Gauge(0..16777216)
    ACCESS read-write
    STATUS mandatory
    DESCRIPTION
        "The Called Party Point Code.  The 'cdpa' bit in the
         cItpAclParameters object is used indicate whether this
         object has been specified."
    ::= { cItpAclTableEntry 18 }

cItpAclCdpaMask OBJECT-TYPE
    SYNTAX CItpTcPointCodeMask
--    Rsyntax Gauge(0..16777216)
    ACCESS read-write
    STATUS mandatory
    DESCRIPTION
        "The Called Party Point Code mask.  The 'cdpaMask' bit
         in the cItpAclParameters object is used indicate 
         whether this object has been specified."
    ::= { cItpAclTableEntry 19 }

cItpAclCdpaSsn OBJECT-TYPE
    SYNTAX CItpTcSubSystemNumber
--    Rsyntax Gauge(0|2..255)
    ACCESS read-write
    STATUS mandatory
    DESCRIPTION
        "The Called Party Point Code subsystem number.  The 
         'cdpa' bit in the cItpAclParameters object is used 
         indicate whether this object has been specified."
    ::= { cItpAclTableEntry 20 }

cItpAclCdpaSsnMask OBJECT-TYPE
    SYNTAX CItpTcSubSystemNumberMask
--    Rsyntax Gauge(2..255)
    ACCESS read-write
    STATUS mandatory
    DESCRIPTION
        "The Called Party Point Code subsystem number Mask.  The
         'cdpa' bit in the cItpAclParameters object is used 
         indicate whether this object has been specified."
    ::= { cItpAclTableEntry 21 }

cItpAclGtiSelector OBJECT-TYPE
    SYNTAX CItpTcGlobalTitleSelector
--    Rsyntax INTEGER {
--        nai(1),
--        tt(2),
--        ttNpEs(3),
--        ttNpNaiEs(4)
--        }
    ACCESS read-write
    STATUS mandatory
    DESCRIPTION
        "The Global Title Selector.  The 'selector' bit in the
         cItpAclParameters object is used indicate whether this
         object has been specified."
    ::= { cItpAclTableEntry 22 }

cItpAclGtiTranslateType OBJECT-TYPE
    SYNTAX CItpTcTranslationType
--    Rsyntax INTEGER {
--        tt(1),
--        ssn(2)
--        }
    ACCESS read-write
    STATUS mandatory
    DESCRIPTION
        "The Global Title Translate Type. The 'selector' bit in
         the cItpAclParameters object is used indicate whether 
         this object has been specified."
    ::= { cItpAclTableEntry 23 }

cItpAclGtiNumberingPlan OBJECT-TYPE
    SYNTAX CItpTcNumberingPlan
--    Rsyntax INTEGER(0..255)
    ACCESS read-write
    STATUS mandatory
    DESCRIPTION
        "The Global Title Numbering Plan.  The 'selector' bit in
         the cItpAclParameters object is used indicate whether 
         this object has been specified."
    ::= { cItpAclTableEntry 24 }

cItpAclGtiNai OBJECT-TYPE
    SYNTAX CItpTcNAI
--    Rsyntax INTEGER(0..255)
    ACCESS read-write
    STATUS mandatory
    DESCRIPTION
        "The Global Title nature of address indicator.  The 
         'selector' bit in the cItpAclParameters object is 
         used indicate whether this object has been 
         specified."
    ::= { cItpAclTableEntry 25 }

cItpAclGtiEsv OBJECT-TYPE
    SYNTAX CItpTcEncodingSchemeValue
--    Rsyntax INTEGER(0..15)
    ACCESS read-write
    STATUS mandatory
    DESCRIPTION
        "The Global Title encoding scheme value.  The 
         'selector' bit in the cItpAclParameters object is
         used indicate whether this object has been 
         specified."
    ::= { cItpAclTableEntry 26 }

cItpAclAft OBJECT-TYPE
    SYNTAX CItpTcPointCode
--    Rsyntax Gauge(0..16777216)
    ACCESS read-write
    STATUS mandatory
    DESCRIPTION
        "The Affected Point Code.  The 'aft' bit in the 
         cItpAclParameters object is used indicate whether 
         this object has been specified."
    ::= { cItpAclTableEntry 27 }

cItpAclAftMask OBJECT-TYPE
    SYNTAX CItpTcPointCodeMask
--    Rsyntax Gauge(0..16777216)
    ACCESS read-write
    STATUS mandatory
    DESCRIPTION
        "The Affected Point Code mask.  The 'aftMask' bit in the
         cItpAclParameters object is used indicate whether 
         this object has been specified."
    ::= { cItpAclTableEntry 28 }

cItpAclAftSsn OBJECT-TYPE
    SYNTAX CItpTcSubSystemNumber
--    Rsyntax Gauge(0|2..255)
    ACCESS read-write
    STATUS mandatory
    DESCRIPTION
        "The Affected Point Code subsystem number.  The 'aft' 
         bit in the cItpAclParameters object is used indicate 
         whether this object has been specified."
    ::= { cItpAclTableEntry 29 }

cItpAclAftSsnMask OBJECT-TYPE
    SYNTAX CItpTcSubSystemNumberMask
--    Rsyntax Gauge(2..255)
    ACCESS read-write
    STATUS mandatory
    DESCRIPTION
        "The Affected Point Code subsystem number Mask.  The 
         'aft' bit in the cItpAclParameters object is used 
         indicate whether this object has been specified."
    ::= { cItpAclTableEntry 30 }

cItpAclRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object is used by a management station to 
         create or delete the row entry in cItpAcl  
         following the RowStatus textual convention."
    ::= { cItpAclTableEntry 31 }

cItpAclScalarGroup OBJECT IDENTIFIER ::= { cItpAclMIBGroups 1 }
-- OBJECT-GROUP
--  Status
--    mandatory
--  Descr
--    SP main objects.
--  objects
--    cItpAclConfigLastChanged

cItpAclAccessListGroup OBJECT IDENTIFIER ::= { cItpAclMIBGroups 2 }
-- OBJECT-GROUP
--  Status
--    mandatory
--  Descr
--    Signaling Point access control list objects.
--  objects
--    cItpAclAction, cItpAclParameters, cItpAclDpc, cItpAclDpcMask, 
--    cItpAclOpc, cItpAclOpcMask, cItpAclSi, cItpAclPattern, 
--    cItpAclOffset, cItpAclComment, cItpAclCgpa, cItpAclCgpaMask, 
--    cItpAclCgpaSsn, cItpAclCgpaSsnMask, cItpAclCdpa, 
--    cItpAclCdpaMask, cItpAclCdpaSsn, cItpAclCdpaSsnMask, 
--    cItpAclGtiSelector, cItpAclGtiTranslateType, 
--    cItpAclGtiNumberingPlan, cItpAclGtiNai, cItpAclGtiEsv, 
--    cItpAclAft, cItpAclAftMask, cItpAclAftSsn, cItpAclAftSsnMask, 
--    cItpAclRowStatus

cItpAclMIBCompliance OBJECT IDENTIFIER ::= { cItpAclMIBCompliances 1 }
-- MODULE-COMPLIANCE
--  Status
--    mandatory
--  Descr
--    The compliance statement for entities which implement
--    the Cisco SP MIB
--  Module
--    >>current<<
--   MandGroup
--    cItpAclScalarGroup
--   MandGroup
--    cItpAclAccessListGroup
--   ObjVar
--    cItpAclAction
--   ObjVar
--    cItpAclParameters
--   ObjVar
--    cItpAclDpc
--   ObjVar
--    cItpAclDpcMask
--   ObjVar
--    cItpAclOpc
--   ObjVar
--    cItpAclOpcMask
--   ObjVar
--    cItpAclSi
--   ObjVar
--    cItpAclPattern
--   ObjVar
--    cItpAclOffset
--   ObjVar
--    cItpAclComment
--   ObjVar
--    cItpAclCgpa
--   ObjVar
--    cItpAclCgpaMask
--   ObjVar
--    cItpAclCgpaSsn
--   ObjVar
--    cItpAclCgpaSsnMask
--   ObjVar
--    cItpAclCdpa
--   ObjVar
--    cItpAclCdpaMask
--   ObjVar
--    cItpAclCdpaSsn
--   ObjVar
--    cItpAclCdpaSsnMask
--   ObjVar
--    cItpAclGtiSelector
--   ObjVar
--    cItpAclGtiTranslateType
--   ObjVar
--    cItpAclGtiNumberingPlan
--   ObjVar
--    cItpAclGtiNai
--   ObjVar
--    cItpAclGtiEsv
--   ObjVar
--    cItpAclAft
--   ObjVar
--    cItpAclAftMask
--   ObjVar
--    cItpAclAftSsn
--   ObjVar
--    cItpAclAftSsnMask
--   ObjVar
--    cItpAclRowStatus


END
