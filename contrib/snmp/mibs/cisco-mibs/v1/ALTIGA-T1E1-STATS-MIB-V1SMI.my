-- MIB file created 04-Dec-2002 18:55:55, by
--   SMICng version 2.2.11-beta(PRO)(Solaris), January 20, 2001. Enterprise key cisco.com

ALTIGA-T1E1-STATS-MIB DEFINITIONS ::= BEGIN

-- From file: "ALTIGA-T1E1-STATS-MIB.my"
-- Compile options "4 7 F H N W 03 06 0B 0G 0N 0T"

IMPORTS
    RowStatus
            FROM SNMPv2-TC-v1
    alStatsT1E1, alT1E1Group
            FROM ALTIGA-MIB
    alT1E1MibModule
            FROM ALTIGA-GLOBAL-REG
    Counter
            FROM RFC1155-SMI
    OBJECT-TYPE
            FROM RFC-1212;

altigaT1E1StatsMibModule OBJECT IDENTIFIER ::= { alT1E1MibModule 2 }
-- MODULE-IDENTITY
--  LastUpdated
--    200209051300Z
--  OrgName
--    Cisco Systems, Inc.
--  ContactInfo
--    Cisco Systems 
--     170 W Tasman Drive 
--     San Jose, CA  95134 
--     USA 
--    
--     Tel: +1 800 553-NETS 
--     E-mail: cs-cvpn3000@cisco.com
--  Descr
--    The Altiga T1/E1 Statistics MIB models counters and objects that are 
--     of management interest. 
--     
--     Acronyms 
--     The following acronyms are used in this document: 
--    
--       MIB:        Management Information Base 
--    
--  RevDate
--    200209051300Z
--  RevDescr
--    Added module compliance.
--  RevDate
--    200207100000Z
--  RevDescr
--    Updated with new header

alStatsT1E1Global OBJECT IDENTIFIER ::= { alStatsT1E1 1 }
altigaT1E1StatsMibConformance OBJECT IDENTIFIER ::= { altigaT1E1StatsMibModule 1 }
altigaT1E1StatsMibCompliances OBJECT IDENTIFIER ::= { altigaT1E1StatsMibConformance 1 }

alT1E1StatsTable OBJECT-TYPE
    SYNTAX SEQUENCE OF AlT1E1StatsEntry
    ACCESS not-accessible
    STATUS mandatory
    DESCRIPTION
        "The T1/E1 interface statistics MIB."
    ::= { alStatsT1E1 2 }

alT1E1StatsEntry OBJECT-TYPE
    SYNTAX AlT1E1StatsEntry
    ACCESS not-accessible
    STATUS mandatory
    DESCRIPTION
        "An entry the alT1E1StatsTable."
    INDEX { alT1E1StatsSlot, alT1E1StatsConn }
    ::= { alT1E1StatsTable 1 }

AlT1E1StatsEntry ::= SEQUENCE {
    alT1E1StatsRowStatus RowStatus,
    alT1E1StatsSlot INTEGER,
    alT1E1StatsConn INTEGER,
    alT1E1StatsLineStatus INTEGER,
    alT1E1StatsElapsedSecs Counter,
    alT1E1StatsBPVs Counter,
    alT1E1StatsESs Counter,
    alT1E1StatsSESs Counter,
    alT1E1StatsBESs Counter,
    alT1E1StatsSEFSs Counter,
    alT1E1StatsUASs Counter,
    alT1E1StatsLCVs Counter,
    alT1E1StatsCSSs Counter,
    alT1E1StatsDMs Counter,
    alT1E1StatsPCVs Counter,
    alT1E1StatsLESs Counter
    }

alT1E1StatsRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this row."
    ::= { alT1E1StatsEntry 1 }

alT1E1StatsSlot OBJECT-TYPE
    SYNTAX INTEGER(0..2147483647)
    ACCESS read-only
    STATUS mandatory
    DESCRIPTION
        "The physical slot for this T1/E1 port. Part of the index."
    ::= { alT1E1StatsEntry 2 }

alT1E1StatsConn OBJECT-TYPE
    SYNTAX INTEGER(0..2147483647)
    ACCESS read-only
    STATUS mandatory
    DESCRIPTION
        "The physical connector for this T1/E1 port. Part of the index."
    ::= { alT1E1StatsEntry 3 }

alT1E1StatsLineStatus OBJECT-TYPE
    SYNTAX INTEGER {
        init(1),
        up(2),
        red(3),
        blue(4),
        yellow(5),
        loopback(6)
        }
    ACCESS read-only
    STATUS mandatory
    DESCRIPTION
        "The current status of the line."
    ::= { alT1E1StatsEntry 4 }

alT1E1StatsElapsedSecs OBJECT-TYPE
    SYNTAX Counter
    ACCESS read-only
    STATUS mandatory
    DESCRIPTION
        "The number of seconds this T1/E1 port has been running."
    ::= { alT1E1StatsEntry 5 }

alT1E1StatsBPVs OBJECT-TYPE
    SYNTAX Counter
    ACCESS read-only
    STATUS mandatory
    DESCRIPTION
        "The number of bipolar violations detected on this T1/E1 port."
    ::= { alT1E1StatsEntry 6 }

alT1E1StatsESs OBJECT-TYPE
    SYNTAX Counter
    ACCESS read-only
    STATUS mandatory
    DESCRIPTION
        "The number of errored seconds detected on this T1/E1 port."
    ::= { alT1E1StatsEntry 7 }

alT1E1StatsSESs OBJECT-TYPE
    SYNTAX Counter
    ACCESS read-only
    STATUS mandatory
    DESCRIPTION
        "The number of severly errored secondss detected on this T1/E1 port."
    ::= { alT1E1StatsEntry 8 }

alT1E1StatsBESs OBJECT-TYPE
    SYNTAX Counter
    ACCESS read-only
    STATUS mandatory
    DESCRIPTION
        "The number of bursty errored seconds detected on this T1/E1 port."
    ::= { alT1E1StatsEntry 9 }

alT1E1StatsSEFSs OBJECT-TYPE
    SYNTAX Counter
    ACCESS read-only
    STATUS mandatory
    DESCRIPTION
        "The number of severly errored framing seconds detected on this T1/E1 port."
    ::= { alT1E1StatsEntry 10 }

alT1E1StatsUASs OBJECT-TYPE
    SYNTAX Counter
    ACCESS read-only
    STATUS mandatory
    DESCRIPTION
        "The number of unavailable seconds detected on this T1/E1 port."
    ::= { alT1E1StatsEntry 11 }

alT1E1StatsLCVs OBJECT-TYPE
    SYNTAX Counter
    ACCESS read-only
    STATUS mandatory
    DESCRIPTION
        "The number of line coding violations detected on this T1/E1 port."
    ::= { alT1E1StatsEntry 12 }

alT1E1StatsCSSs OBJECT-TYPE
    SYNTAX Counter
    ACCESS read-only
    STATUS mandatory
    DESCRIPTION
        "The number of controlled slips detected on this T1/E1 port."
    ::= { alT1E1StatsEntry 13 }

alT1E1StatsDMs OBJECT-TYPE
    SYNTAX Counter
    ACCESS read-only
    STATUS mandatory
    DESCRIPTION
        "The number of degraded minutes detected on this T1/E1 port."
    ::= { alT1E1StatsEntry 14 }

alT1E1StatsPCVs OBJECT-TYPE
    SYNTAX Counter
    ACCESS read-only
    STATUS mandatory
    DESCRIPTION
        "The number of path coding violations detected on this T1/E1 port."
    ::= { alT1E1StatsEntry 15 }

alT1E1StatsLESs OBJECT-TYPE
    SYNTAX Counter
    ACCESS read-only
    STATUS mandatory
    DESCRIPTION
        "The number of line errored seconds detected on this T1/E1 port."
    ::= { alT1E1StatsEntry 16 }

altigaT1E1StatsGroup OBJECT IDENTIFIER ::= { alT1E1Group 2 }
-- OBJECT-GROUP
--  Status
--    mandatory
--  Descr
--    The objects for T1/E1 configuration.
--  objects
--    alT1E1StatsRowStatus, alT1E1StatsSlot, alT1E1StatsConn, 
--    alT1E1StatsLineStatus, alT1E1StatsElapsedSecs, 
--    alT1E1StatsBPVs, alT1E1StatsESs, alT1E1StatsSESs, 
--    alT1E1StatsBESs, alT1E1StatsSEFSs, alT1E1StatsUASs, 
--    alT1E1StatsLCVs, alT1E1StatsCSSs, alT1E1StatsDMs, 
--    alT1E1StatsPCVs, alT1E1StatsLESs

altigaT1E1StatsMibCompliance OBJECT IDENTIFIER ::= { altigaT1E1StatsMibCompliances 1 }
-- MODULE-COMPLIANCE
--  Status
--    mandatory
--  Descr
--    The compliance statement for agents which  
--     implement the Altiga T1/E1 Statistics MIB.
--  Module
--    >>current<<
--   MandGroup
--    altigaT1E1StatsGroup


END
