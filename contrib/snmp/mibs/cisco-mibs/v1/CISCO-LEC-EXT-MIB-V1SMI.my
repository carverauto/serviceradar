-- MIB created 6/25/99 12:57:23, by
--   SMIC (the next generation) version 1.6.29, November 22, 1994.

CISCO-LEC-EXT-MIB DEFINITIONS ::= BEGIN

-- From file: "CISCO-LEC-EXT-MIB.my"

IMPORTS
    OBJECT-TYPE
            FROM RFC-1212
    ciscoMgmt
            FROM CISCO-SMI
    lecIndex, 
    lecConfigEntry
            FROM LAN-EMULATION-CLIENT-MIB
    VlanIndex
            FROM CISCO-VTP-MIB;

ciscoLecExtMIB OBJECT IDENTIFIER ::= { ciscoMgmt 77 }
-- MODULE-IDENTITY
--  LastUpdated
--    9705091230Z
--  OrgName
--    Cisco Systems, Inc.
--  ContactInfo
--           Cisco Systems
--            Customer Service
--    
--    Postal: 170 W Tasman Drive
--            San Jose, CA  95134
--            USA
--    
--       Tel: +1 800 553-NETS
--    
--    E-mail: cs-atm@cisco.com
--  Descr
--    This MIB module is a Cisco extension to the ATM
--    Forum's LANE Client MIB.
--  RevDate
--    9705091230Z
--  RevDescr
--    Initial version of this MIB module.

ciscoLecExtMIBObjects OBJECT IDENTIFIER ::= { ciscoLecExtMIB 1 }
cLecExtVlan     OBJECT IDENTIFIER ::= { ciscoLecExtMIBObjects 1 }
ciscoLecExtMIBNotificationPrefix OBJECT IDENTIFIER ::= { ciscoLecExtMIB 2 }
ciscoLecExtMIBNotifications OBJECT IDENTIFIER ::= { ciscoLecExtMIBNotificationPrefix 0 }
ciscoLecExtMIBConformance OBJECT IDENTIFIER ::= { ciscoLecExtMIB 3 }
ciscoLecExtMIBCompliances OBJECT IDENTIFIER ::= { ciscoLecExtMIBConformance 1 }
ciscoLecExtMIBGroups OBJECT IDENTIFIER ::= { ciscoLecExtMIBConformance 2 }

cLecToVlanTable OBJECT-TYPE
    SYNTAX SEQUENCE OF CLecToVlanEntry
    ACCESS not-accessible
    STATUS mandatory
    DESCRIPTION
        "An extension to the lecConfig table in the
        LAN-EMULATION-CLIENT-MIB that identifies which VLAN a
        LEC is associated with."
    ::= { cLecExtVlan 1 }

cLecToVlanEntry OBJECT-TYPE
    SYNTAX CLecToVlanEntry
    ACCESS not-accessible
    STATUS mandatory
    DESCRIPTION
        " Each entry in this table shows the correlation
        between a LAN Emulation client and the VLAN that it
        extends."
    INDEX { lecIndex }
-- Augments lecConfigEntry FROM LAN-EMULATION-CLIENT-MIB
    ::= { cLecToVlanTable 1 }

CLecToVlanEntry ::= SEQUENCE {
    cLecToVlanId VlanIndex
    }

cLecToVlanId OBJECT-TYPE
    SYNTAX VlanIndex
--    Rsyntax INTEGER(0..1023)
    ACCESS read-write
    STATUS mandatory
    DESCRIPTION
        " The VLAN ID of the VLAN to which the specified LEC
        is attributed."
    ::= { cLecToVlanEntry 1 }

ciscoLecExtVlanMIBGroup OBJECT IDENTIFIER ::= { ciscoLecExtMIBGroups 1 }
-- OBJECT-GROUP
--  Status
--    mandatory
--  Descr
--    A collection of objects related to identifying
--    a LANE Client associated VLAN information.
--  objects
--    cLecToVlanId

ciscoLecExtMIBCompliance OBJECT IDENTIFIER ::= { ciscoLecExtMIBCompliances 1 }
-- MODULE-COMPLIANCE
--  Status
--    mandatory
--  Descr
--    This module should be implemented by all Cisco
--     devices supporting ATM LAN Emulation Clients.
--  Module
--    >>current<<
--   MandGroup
--    ciscoLecExtVlanMIBGroup


END
