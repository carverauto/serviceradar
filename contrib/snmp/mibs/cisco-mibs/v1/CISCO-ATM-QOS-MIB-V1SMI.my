-- MIB file created 16-Dec-2002 17:01:01, by
--   SMICng version 2.2.11-beta(PRO)(Solaris), January 20, 2001. Enterprise key cisco.com

CISCO-ATM-QOS-MIB DEFINITIONS ::= BEGIN

-- From file: "CISCO-ATM-QOS-MIB.my"
-- Compile options "4 7 F H N W 03 06 0B 0G 0N 0T"

IMPORTS
    ifIndex
            FROM IF-MIB
    atmVplVpi, atmVclVpi, atmVclVci
            FROM ATM-MIB
    AtmServiceCategory
            FROM ATM-FORUM-TC-MIB
    ciscoMgmt
            FROM CISCO-SMI
    Gauge
            FROM RFC1155-SMI
    OBJECT-TYPE
            FROM RFC-1212;

ciscoAtmQosMIB OBJECT IDENTIFIER ::= { ciscoMgmt 279 }
-- MODULE-IDENTITY
--  LastUpdated
--    200206100000Z
--  OrgName
--    Cisco Systems, Inc.
--  ContactInfo
--    Cisco Systems
--     Customer Service
--    
--     Postal: 170 W. Tasman Drive
--           San Jose, CA  95134
--           SA
--    
--     Tel: +1 800 553-NETS
--    
--     Email: cs-atm@cisco.com
--  Descr
--    The MIB is created to provide ATM QoS information in
--     these areas:
--     
--     1. Traffic shaping on a per-VC basis
--     2. Traffic shaping on a per-VP basis 
--     3. Per-VC queuing/buffering
--     
--     Although the initial requirements of the MIB are
--     driven to support the GSR TAZ line card,
--     CISCO-ATM-QOS-MIB is designed as a generic MIB to
--     support ATM interfaces across all platforms.
--     
--     Here are the tables defined in this MIB:
--     ciscoAtmQosVccTable 
--          - to provide information on traffic shaping on 
--            a per-VC basis.
--                           
--     ciscoAtmQosVpcTable 
--          - to provide information on traffic shaping on
--            a per-VP basis.
--         
--     ciscoAtmQosVcQueuingTable
--     ciscoAtmQosVcQueuingClassTable
--          - to provide information on per-VC
--            queuing/buffering.
--  RevDate
--    200206100000Z
--  RevDescr
--    Initial version of this MIB module.

ciscoAtmQosMIBNotifs OBJECT IDENTIFIER ::= { ciscoAtmQosMIB 0 }
ciscoAtmQosMIBObjects OBJECT IDENTIFIER ::= { ciscoAtmQosMIB 1 }
ciscoAtmQosMIBConform OBJECT IDENTIFIER ::= { ciscoAtmQosMIB 2 }
caqVccParams    OBJECT IDENTIFIER ::= { ciscoAtmQosMIBObjects 1 }
caqVpcParams    OBJECT IDENTIFIER ::= { ciscoAtmQosMIBObjects 2 }
caqQueuingParams OBJECT IDENTIFIER ::= { ciscoAtmQosMIBObjects 3 }
ciscoAtmQosMIBCompliances OBJECT IDENTIFIER ::= { ciscoAtmQosMIBConform 1 }
ciscoAtmQosMIBGroups OBJECT IDENTIFIER ::= { ciscoAtmQosMIBConform 2 }

VcParamConfigLocation ::= INTEGER {
        configDefault(1),
        configVcDirect(2),
        configVcClass(3),
        configVcClassSubInterface(4),
        configVcClassInterface(5)
        }
-- TEXTUAL-CONVENTION
--  Status
--    mandatory
--  Descr
--    The configuration source of a vc parameter:
--     1 - Not configured - using default
--     2 - Configured on vc directly
--     3 - VC-class configured on vc
--     4 - VC-class configured on sub-interface
--     5 - VC-class configured on main-interface.

VpState ::= INTEGER {
        vpStateInactive(1),
        vpStateActive(2)
        }
-- TEXTUAL-CONVENTION
--  Status
--    mandatory
--  Descr
--    States of virtual path:
--     1 - Inactive
--     2 - Active

caqVccParamsTable OBJECT-TYPE
    SYNTAX SEQUENCE OF CaqVccParamsEntry
    ACCESS not-accessible
    STATUS mandatory
    DESCRIPTION
        "This table is defined to provide QoS information for
         each active ATM VC existing on the interface."
    ::= { caqVccParams 1 }

caqVccParamsEntry OBJECT-TYPE
    SYNTAX CaqVccParamsEntry
    ACCESS not-accessible
    STATUS mandatory
    DESCRIPTION
        "This list contains the ATM QoS parameters provided by
         ciscoAtmQosVccEntry."
    INDEX { ifIndex, atmVclVpi, atmVclVci }
    ::= { caqVccParamsTable 1 }

CaqVccParamsEntry ::= SEQUENCE {
    caqVccParamsType AtmServiceCategory,
    caqVccParamsPcrIn0 Gauge,
    caqVccParamsPcrIn01 Gauge,
    caqVccParamsPcrOut0 Gauge,
    caqVccParamsPcrOut01 Gauge,
    caqVccParamsScrIn0 Gauge,
    caqVccParamsScrIn01 Gauge,
    caqVccParamsScrOut0 Gauge,
    caqVccParamsScrOut01 Gauge,
    caqVccParamsBcsIn0 Gauge,
    caqVccParamsBcsIn01 Gauge,
    caqVccParamsBcsOut0 Gauge,
    caqVccParamsBcsOut01 Gauge,
    caqVccParamsInheritLevel VcParamConfigLocation,
    caqVccParamsMcrIn Gauge,
    caqVccParamsMcrOut Gauge,
    caqVccParamsInvRdf Gauge,
    caqVccParamsInvRif Gauge,
    caqVccParamsRfl VcParamConfigLocation,
    caqVccParamsCdv Gauge,
    caqVccParamsCdvt Gauge,
    caqVccParamsIcr Gauge,
    caqVccParamsTbe Gauge,
    caqVccParamsFrtt Gauge,
    caqVccParamsNrm Gauge,
    caqVccParamsInvTrm Gauge,
    caqVccParamsInvCdf Gauge,
    caqVccParamsAdtf Gauge
    }

caqVccParamsType OBJECT-TYPE
    SYNTAX AtmServiceCategory
--    Rsyntax INTEGER {
--        other(1),
--        cbr(2),
--        rtVbr(3),
--        nrtVbr(4),
--        abr(5),
--        ubr(6)
--        }
    ACCESS read-write
    STATUS mandatory
    DESCRIPTION
        "The service category of this virtual circuit connection."
    ::= { caqVccParamsEntry 1 }

caqVccParamsPcrIn0 OBJECT-TYPE
    SYNTAX Gauge
    ACCESS read-write
    STATUS mandatory
    DESCRIPTION
        "Input Peak Cell Rate (PCR) in kbps with 
         Cell Loss Priority bit set to 0 (clp0)."
    ::= { caqVccParamsEntry 2 }

caqVccParamsPcrIn01 OBJECT-TYPE
    SYNTAX Gauge
    ACCESS read-write
    STATUS mandatory
    DESCRIPTION
        "Number of OAM F5 end to end loopback cells sent through
         the VCC."
    ::= { caqVccParamsEntry 3 }

caqVccParamsPcrOut0 OBJECT-TYPE
    SYNTAX Gauge
    ACCESS read-write
    STATUS mandatory
    DESCRIPTION
        "Output Peak Cell Rate (PCR) in kbps with
         Cell Loss Priority bit set to 0 (clp0)."
    ::= { caqVccParamsEntry 4 }

caqVccParamsPcrOut01 OBJECT-TYPE
    SYNTAX Gauge
    ACCESS read-write
    STATUS mandatory
    DESCRIPTION
        "Output Peak Cell Rate (PCR) in kbps with
         Cell Loss Priority bit set to 1 (clp01)."
    ::= { caqVccParamsEntry 5 }

caqVccParamsScrIn0 OBJECT-TYPE
    SYNTAX Gauge
    ACCESS read-write
    STATUS mandatory
    DESCRIPTION
        "Input Sustained Cell Rate (SCR) in kbps
         for connection with VBR type of QoS and
         Cell Loss Priority bit set to 0 (clp0)."
    ::= { caqVccParamsEntry 6 }

caqVccParamsScrIn01 OBJECT-TYPE
    SYNTAX Gauge
    ACCESS read-write
    STATUS mandatory
    DESCRIPTION
        "Input Sustained Cell Rate (SCR) in kbps
         for connection with VBR type of QoS and
         Cell Loss Priority bit set to 1 (clp01)."
    ::= { caqVccParamsEntry 7 }

caqVccParamsScrOut0 OBJECT-TYPE
    SYNTAX Gauge
    ACCESS read-write
    STATUS mandatory
    DESCRIPTION
        "Output Sustained Cell Rate (SCR) in kbps
         for connection with VBR type of QoS and
         Cell Loss Priority bit set to 0 (clp0)."
    ::= { caqVccParamsEntry 8 }

caqVccParamsScrOut01 OBJECT-TYPE
    SYNTAX Gauge
    ACCESS read-write
    STATUS mandatory
    DESCRIPTION
        "Output Sustained Cell Rate (SCR) in kbps
         for connection with VBR type of QoS and
         Cell Loss Priority bit set to 1 (clp01)."
    ::= { caqVccParamsEntry 9 }

caqVccParamsBcsIn0 OBJECT-TYPE
    SYNTAX Gauge
    ACCESS read-write
    STATUS mandatory
    DESCRIPTION
        "Input Burst Cell Size (BCS) for connection
         with VBR type of QoS and
         Cell Loss Priority bit set to 0 (clp0)."
    ::= { caqVccParamsEntry 10 }

caqVccParamsBcsIn01 OBJECT-TYPE
    SYNTAX Gauge
    ACCESS read-write
    STATUS mandatory
    DESCRIPTION
        "Input Burst Cell Size (BCS) for connection
         with VBR type of QoS and
         Cell Loss Priority bit set to 1 (clp01)."
    ::= { caqVccParamsEntry 11 }

caqVccParamsBcsOut0 OBJECT-TYPE
    SYNTAX Gauge
    ACCESS read-write
    STATUS mandatory
    DESCRIPTION
        "Output Burst Cell Size (BCS) for connection
         with VBR type of QoS and 
         Cell Loss Priority bit set to 0 (clp0)."
    ::= { caqVccParamsEntry 12 }

caqVccParamsBcsOut01 OBJECT-TYPE
    SYNTAX Gauge
    ACCESS read-write
    STATUS mandatory
    DESCRIPTION
        "Output Burst Cell Size (BCS) for connection
         with VBR type of QoS and
         Cell Loss Priority bit set to 1 (clp01)."
    ::= { caqVccParamsEntry 13 }

caqVccParamsInheritLevel OBJECT-TYPE
    SYNTAX VcParamConfigLocation
--    Rsyntax INTEGER {
--        configDefault(1),
--        configVcDirect(2),
--        configVcClass(3),
--        configVcClassSubInterface(4),
--        configVcClassInterface(5)
--        }
    ACCESS read-only
    STATUS mandatory
    DESCRIPTION
        "The source of configuration for peak cell rate."
    ::= { caqVccParamsEntry 14 }

caqVccParamsMcrIn OBJECT-TYPE
    SYNTAX Gauge
    ACCESS read-write
    STATUS mandatory
    DESCRIPTION
        "Input Minimum Cell Rate (MCR) in kbps for
         connection with VBR-nrt or ABR type of QoS."
    ::= { caqVccParamsEntry 15 }

caqVccParamsMcrOut OBJECT-TYPE
    SYNTAX Gauge
    ACCESS read-write
    STATUS mandatory
    DESCRIPTION
        "Output Minimum Cell Rate (MCR) in kbps for
         connection with VBR-nrt or ABR type of QoS."
    ::= { caqVccParamsEntry 16 }

caqVccParamsInvRdf OBJECT-TYPE
    SYNTAX Gauge
    ACCESS read-write
    STATUS mandatory
    DESCRIPTION
        "Inverse of rate decrease factor."
    ::= { caqVccParamsEntry 17 }

caqVccParamsInvRif OBJECT-TYPE
    SYNTAX Gauge
    ACCESS read-write
    STATUS mandatory
    DESCRIPTION
        "Inverse of rate increase factor."
    ::= { caqVccParamsEntry 18 }

caqVccParamsRfl OBJECT-TYPE
    SYNTAX VcParamConfigLocation
--    Rsyntax INTEGER {
--        configDefault(1),
--        configVcDirect(2),
--        configVcClass(3),
--        configVcClassSubInterface(4),
--        configVcClassInterface(5)
--        }
    ACCESS read-only
    STATUS mandatory
    DESCRIPTION
        "The source of configuration for rate factor."
    ::= { caqVccParamsEntry 19 }

caqVccParamsCdv OBJECT-TYPE
    SYNTAX Gauge
    ACCESS read-only
    STATUS mandatory
    DESCRIPTION
        "Cell delay variation."
    ::= { caqVccParamsEntry 20 }

caqVccParamsCdvt OBJECT-TYPE
    SYNTAX Gauge
    ACCESS read-write
    STATUS mandatory
    DESCRIPTION
        "Cell delay variation tolerance."
    ::= { caqVccParamsEntry 21 }

caqVccParamsIcr OBJECT-TYPE
    SYNTAX Gauge
    ACCESS read-write
    STATUS mandatory
    DESCRIPTION
        "Initial cell rate."
    ::= { caqVccParamsEntry 22 }

caqVccParamsTbe OBJECT-TYPE
    SYNTAX Gauge
    ACCESS read-write
    STATUS mandatory
    DESCRIPTION
        "Transient buffer exposure."
    ::= { caqVccParamsEntry 23 }

caqVccParamsFrtt OBJECT-TYPE
    SYNTAX Gauge
    ACCESS read-write
    STATUS mandatory
    DESCRIPTION
        "Fixed round-trip time."
    ::= { caqVccParamsEntry 24 }

caqVccParamsNrm OBJECT-TYPE
    SYNTAX Gauge
    ACCESS read-write
    STATUS mandatory
    DESCRIPTION
        "Maximum number of tx cells for each forward rm cell."
    ::= { caqVccParamsEntry 25 }

caqVccParamsInvTrm OBJECT-TYPE
    SYNTAX Gauge
    ACCESS read-write
    STATUS mandatory
    DESCRIPTION
        "Maximum time between forward rm cells."
    ::= { caqVccParamsEntry 26 }

caqVccParamsInvCdf OBJECT-TYPE
    SYNTAX Gauge
    ACCESS read-write
    STATUS mandatory
    DESCRIPTION
        "Inverse of cutoff decrease factor."
    ::= { caqVccParamsEntry 27 }

caqVccParamsAdtf OBJECT-TYPE
    SYNTAX Gauge
    ACCESS read-write
    STATUS mandatory
    DESCRIPTION
        "Allowed cell rate decrease time factor."
    ::= { caqVccParamsEntry 28 }

caqVpcParamsTable OBJECT-TYPE
    SYNTAX SEQUENCE OF CaqVpcParamsEntry
    ACCESS not-accessible
    STATUS mandatory
    DESCRIPTION
        "This table is defined to provide QoS information for
         each active ATM VP existing on the interface."
    ::= { caqVpcParams 1 }

caqVpcParamsEntry OBJECT-TYPE
    SYNTAX CaqVpcParamsEntry
    ACCESS not-accessible
    STATUS mandatory
    DESCRIPTION
        "This list contains the ATM QoS parameters provided by
         ciscoAtmQosVpcEntry."
    INDEX { ifIndex, atmVplVpi }
    ::= { caqVpcParamsTable 1 }

CaqVpcParamsEntry ::= SEQUENCE {
    caqVpcParamsVpState VpState,
    caqVpcParamsPeakRate Gauge,
    caqVpcParamsCesRate Gauge,
    caqVpcParamsDataVcCount INTEGER,
    caqVpcParamsCesVcCount INTEGER,
    caqVpcParamsVcdF4Seg INTEGER,
    caqVpcParamsVcdF4Ete INTEGER,
    caqVpcParamsScr Gauge,
    caqVpcParamsMbs Gauge,
    caqVpcParamsAvailBw Gauge
    }

caqVpcParamsVpState OBJECT-TYPE
    SYNTAX VpState
--    Rsyntax INTEGER {
--        vpStateInactive(1),
--        vpStateActive(2)
--        }
    ACCESS read-only
    STATUS mandatory
    DESCRIPTION
        "VP state of the current permanent virtual path."
    ::= { caqVpcParamsEntry 1 }

caqVpcParamsPeakRate OBJECT-TYPE
    SYNTAX Gauge
    ACCESS read-only
    STATUS mandatory
    DESCRIPTION
        "Maximum rate in kbps at which the associated
         permanent virtual path can transmit data."
    ::= { caqVpcParamsEntry 2 }

caqVpcParamsCesRate OBJECT-TYPE
    SYNTAX Gauge
    ACCESS read-only
    STATUS mandatory
    DESCRIPTION
        "Maximum rate in kbps at which CES VCs can transmit
         data with the associated permanent virtual path."
    ::= { caqVpcParamsEntry 3 }

caqVpcParamsDataVcCount OBJECT-TYPE
    SYNTAX INTEGER(0..65535)
    ACCESS read-only
    STATUS mandatory
    DESCRIPTION
        "Number of data VCs currently associated with
         the permanent virtual path."
    ::= { caqVpcParamsEntry 4 }

caqVpcParamsCesVcCount OBJECT-TYPE
    SYNTAX INTEGER(0..65535)
    ACCESS read-only
    STATUS mandatory
    DESCRIPTION
        "Number of CES VCs currently associated with
         the permanent virtual path."
    ::= { caqVpcParamsEntry 5 }

caqVpcParamsVcdF4Seg OBJECT-TYPE
    SYNTAX INTEGER(0..65535)
    ACCESS read-only
    STATUS mandatory
    DESCRIPTION
        "Vcd for F4 OAM segment processing."
    ::= { caqVpcParamsEntry 6 }

caqVpcParamsVcdF4Ete OBJECT-TYPE
    SYNTAX INTEGER(0..65535)
    ACCESS read-only
    STATUS mandatory
    DESCRIPTION
        "Vcd for F4 OAM end to end processing."
    ::= { caqVpcParamsEntry 7 }

caqVpcParamsScr OBJECT-TYPE
    SYNTAX Gauge
    ACCESS read-only
    STATUS mandatory
    DESCRIPTION
        "Sustained cell rate associated with the PVP."
    ::= { caqVpcParamsEntry 8 }

caqVpcParamsMbs OBJECT-TYPE
    SYNTAX Gauge
    ACCESS read-only
    STATUS mandatory
    DESCRIPTION
        "Maximum burst size associated with the PVP."
    ::= { caqVpcParamsEntry 9 }

caqVpcParamsAvailBw OBJECT-TYPE
    SYNTAX Gauge
    ACCESS read-only
    STATUS mandatory
    DESCRIPTION
        "Bandwidth in Kbps currently currently available
         on this PVP."
    ::= { caqVpcParamsEntry 10 }

caqQueuingParamsTable OBJECT-TYPE
    SYNTAX SEQUENCE OF CaqQueuingParamsEntry
    ACCESS not-accessible
    STATUS mandatory
    DESCRIPTION
        "This table provides queuing related information
         for a VC existing on an ATM interface."
    ::= { caqQueuingParams 1 }

caqQueuingParamsEntry OBJECT-TYPE
    SYNTAX CaqQueuingParamsEntry
    ACCESS not-accessible
    STATUS mandatory
    DESCRIPTION
        "This is defined as an entry in caqQueuingParamsTable."
    INDEX { ifIndex, atmVclVpi, atmVclVci }
    ::= { caqQueuingParamsTable 1 }

CaqQueuingParamsEntry ::= SEQUENCE {
    caqQueuingParamsMeanQDepth Gauge
    }

caqQueuingParamsMeanQDepth OBJECT-TYPE
    SYNTAX Gauge
    ACCESS read-only
    STATUS mandatory
    DESCRIPTION
        "Mean Queue Depth associated with the vc.  This value
         is calculated based on the actual queue depth on the
         interface and the exponential weighting constant."
    ::= { caqQueuingParamsEntry 1 }

caqQueuingParamsClassTable OBJECT-TYPE
    SYNTAX SEQUENCE OF CaqQueuingParamsClassEntry
    ACCESS not-accessible
    STATUS mandatory
    DESCRIPTION
        "This table provides queuing information for all 
         queuing classes associating with a VC."
    ::= { caqQueuingParams 2 }

caqQueuingParamsClassEntry OBJECT-TYPE
    SYNTAX CaqQueuingParamsClassEntry
    ACCESS not-accessible
    STATUS mandatory
    DESCRIPTION
        "This is defined as an entry in ciscoAtmQosVcQueuingClassTable
         to provide queuing information of a specific class."
    INDEX { ifIndex, atmVclVpi, atmVclVci, caqQueuingParamsClassIndex }
    ::= { caqQueuingParamsClassTable 1 }

CaqQueuingParamsClassEntry ::= SEQUENCE {
    caqQueuingParamsClassIndex INTEGER,
    caqQueuingParamsClassRandDrp Gauge,
    caqQueuingParamsClassTailDrp Gauge,
    caqQueuingParamsClassMinThre Gauge,
    caqQueuingParamsClassMaxThre Gauge,
    caqQueuingParamsClassMrkProb Gauge
    }

caqQueuingParamsClassIndex OBJECT-TYPE
    SYNTAX INTEGER(0..8)
    ACCESS not-accessible
    STATUS mandatory
    DESCRIPTION
        "A class index, which associates with an IP precedence
         (0 to 8), is defined to reference individual
         caqQueuingParamsClassEntry."
    ::= { caqQueuingParamsClassEntry 1 }

caqQueuingParamsClassRandDrp OBJECT-TYPE
    SYNTAX Gauge
    ACCESS read-only
    STATUS mandatory
    DESCRIPTION
        "Number of packets dropped when Mean Queue
         Length is between Minimum Threshold and
         Maximum Threshold range."
    ::= { caqQueuingParamsClassEntry 2 }

caqQueuingParamsClassTailDrp OBJECT-TYPE
    SYNTAX Gauge
    ACCESS read-only
    STATUS mandatory
    DESCRIPTION
        "Number of packets dropped because the Mean
         Queue Depth exceeds the Maximum Threshold value."
    ::= { caqQueuingParamsClassEntry 3 }

caqQueuingParamsClassMinThre OBJECT-TYPE
    SYNTAX Gauge
    ACCESS read-only
    STATUS mandatory
    DESCRIPTION
        "Minimum Threshold value in kbps."
    ::= { caqQueuingParamsClassEntry 4 }

caqQueuingParamsClassMaxThre OBJECT-TYPE
    SYNTAX Gauge
    ACCESS read-only
    STATUS mandatory
    DESCRIPTION
        "Maximum Threshold value in kbps."
    ::= { caqQueuingParamsClassEntry 5 }

caqQueuingParamsClassMrkProb OBJECT-TYPE
    SYNTAX Gauge
    ACCESS read-only
    STATUS mandatory
    DESCRIPTION
        "Mark probability denominator.  This is the value used
         in the calculation of a packet being dropped when
         the average queue size is between the minimum
         threshold and the maximum threshold."
    ::= { caqQueuingParamsClassEntry 6 }

ciscoAtmQosVccGroup OBJECT IDENTIFIER ::= { ciscoAtmQosMIBGroups 1 }
-- OBJECT-GROUP
--  Status
--    mandatory
--  Descr
--    A collection of objects providing per-VC 
--     ATM QoS related info.
--  objects
--    caqVccParamsType, caqVccParamsPcrIn0, caqVccParamsPcrIn01, 
--    caqVccParamsPcrOut0, caqVccParamsPcrOut01, caqVccParamsScrIn0, 
--    caqVccParamsScrIn01, caqVccParamsScrOut0, 
--    caqVccParamsScrOut01, caqVccParamsBcsIn0, caqVccParamsBcsIn01, 
--    caqVccParamsBcsOut0, caqVccParamsBcsOut01, 
--    caqVccParamsInheritLevel, caqVccParamsMcrIn, 
--    caqVccParamsMcrOut, caqVccParamsInvRdf, caqVccParamsInvRif, 
--    caqVccParamsRfl

ciscoAtmQosVccAddon1Group OBJECT IDENTIFIER ::= { ciscoAtmQosMIBGroups 2 }
-- OBJECT-GROUP
--  Status
--    mandatory
--  Descr
--    Add-on objects providing per-VC 
--     ATM QoS related info.
--  objects
--    caqVccParamsCdv, caqVccParamsCdvt, caqVccParamsIcr, 
--    caqVccParamsTbe, caqVccParamsFrtt, caqVccParamsNrm, 
--    caqVccParamsInvTrm, caqVccParamsInvCdf, caqVccParamsAdtf

ciscoAtmQosVpcGroup OBJECT IDENTIFIER ::= { ciscoAtmQosMIBGroups 3 }
-- OBJECT-GROUP
--  Status
--    mandatory
--  Descr
--    A collection of objects providing per-VP 
--     ATM QoS related info.
--  objects
--    caqVpcParamsVpState, caqVpcParamsPeakRate, 
--    caqVpcParamsCesRate, caqVpcParamsDataVcCount, 
--    caqVpcParamsCesVcCount, caqVpcParamsVcdF4Seg, 
--    caqVpcParamsVcdF4Ete, caqVpcParamsScr, caqVpcParamsMbs

ciscoAtmQosVpcAddon1Group OBJECT IDENTIFIER ::= { ciscoAtmQosMIBGroups 4 }
-- OBJECT-GROUP
--  Status
--    mandatory
--  Descr
--    Add-on objects providing per-VP 
--     ATM QoS related info.
--  objects
--    caqVpcParamsAvailBw

ciscoAtmQosVcQueuingGroup OBJECT IDENTIFIER ::= { ciscoAtmQosMIBGroups 5 }
-- OBJECT-GROUP
--  Status
--    mandatory
--  Descr
--    A collection of objects providing per-VC 
--     queuing/buffering related info.
--  objects
--    caqQueuingParamsMeanQDepth, caqQueuingParamsClassRandDrp, 
--    caqQueuingParamsClassTailDrp, caqQueuingParamsClassMinThre, 
--    caqQueuingParamsClassMaxThre, caqQueuingParamsClassMrkProb

ciscoAtmQosMIBCompliance OBJECT IDENTIFIER ::= { ciscoAtmQosMIBCompliances 1 }
-- MODULE-COMPLIANCE
--  Status
--    mandatory
--  Descr
--    The compliance statement for entities which implement
--    this Cisco ATM QoS MIB.
--  Module
--    >>current<<
--   MandGroup
--    ciscoAtmQosVccGroup
--   MandGroup
--    ciscoAtmQosVpcGroup
--   MandGroup
--    ciscoAtmQosVcQueuingGroup
--   ObjVar
--    caqVccParamsType
--   ObjVar
--    caqVccParamsPcrIn0
--   ObjVar
--    caqVccParamsPcrIn01
--   ObjVar
--    caqVccParamsPcrOut0
--   ObjVar
--    caqVccParamsPcrOut01
--   ObjVar
--    caqVccParamsScrIn0
--   ObjVar
--    caqVccParamsScrIn01
--   ObjVar
--    caqVccParamsScrOut0
--   ObjVar
--    caqVccParamsScrOut01
--   ObjVar
--    caqVccParamsBcsIn0
--   ObjVar
--    caqVccParamsBcsIn01
--   ObjVar
--    caqVccParamsBcsOut0
--   ObjVar
--    caqVccParamsBcsOut01
--   ObjVar
--    caqVccParamsMcrIn
--   ObjVar
--    caqVccParamsMcrOut
--   ObjVar
--    caqVccParamsInvRdf
--   ObjVar
--    caqVccParamsInvRif
--   ObjVar
--    caqVccParamsCdvt
--   ObjVar
--    caqVccParamsIcr
--   ObjVar
--    caqVccParamsTbe
--   ObjVar
--    caqVccParamsFrtt
--   ObjVar
--    caqVccParamsNrm
--   ObjVar
--    caqVccParamsInvTrm
--   OptGroup
--    ciscoAtmQosVccAddon1Group
--   OptGroup
--    ciscoAtmQosVpcAddon1Group


END
