-- MIB file created 27-Jun-2012 17:39:49, by
--   SMICng version 2.2.11-beta(PRO)(Solaris), January 20, 2001. Enterprise key cisco.com

CISCO-CDSTV-CS-STATS-MIB DEFINITIONS ::= BEGIN

-- From file: "CISCO-CDSTV-CS-STATS-MIB.my"
-- Compile options "4 7 F H N W 03 06 0B 0G 0N 0T"

IMPORTS
    TimeIntervalSec
            FROM CISCO-TC
    ciscoMgmt
            FROM CISCO-SMI
    Counter, Gauge
            FROM RFC1155-SMI
    OBJECT-TYPE
            FROM RFC-1212;

ciscoCdstvCsStatsMIB OBJECT IDENTIFIER ::= { ciscoMgmt 743 }
-- MODULE-IDENTITY
--  LastUpdated
--    201205170000Z
--  OrgName
--    Cisco Systems, Inc.
--  ContactInfo
--    Cisco Systems
--    Customer Service
--    
--    Postal: 170 W Tasman Drive
--    San Jose, CA  95134
--    USA
--    
--    Tel: +1 800 553-NETS
--    
--    E-mail: cs-cds@cisco.com
--  Descr
--    This MIB module defines objects describing the caching and
--    streaming statistics objects that facilitate the management of
--    the Cisco CDS-TV product family.
--    
--    CDS-TV is a suite of products and software applications
--    providing ingest, storage, caching, streaming, playout and
--    on-demand delivery of video to television or STB
--    clients.
--    
--    ACRONYMS
--    
--    CCP     Content Control Protocol
--    CDN     Content Distribution Network
--    CDS     Content Delivery System
--    ISA     Interactive Services Architecture
--    ISV     Integrated Streamer-Vault
--    FSI     File Service Interface
--    FTP     File Transfer Protocol
--    HTTP    Hyper-Text Transfer Protocol
--    MPEG    Motion Picture Experts Group
--    MSA     Managed Services Architecture
--    NDVR    Network Digital Video Recorder
--    RTSP    Real-Time Streaming Protocol
--    STB     Set-Top Box
--    VOD     Video On Demand
--    
--    
--    GLOSSARY
--    
--    Catcher: Device responsible for receiving content (typically
--    via
--    satellite dishes and antennae) from content providers or from a
--    Headend-In-The-Sky. 
--    
--    Content Ingest: Acquisition of content (from a source such as a
--    catcher or an FTP server) for the purpose of storing it locally
--    in a vault and making it available to streamers and caching
--    nodes as needed.
--    
--    Vault: Content delivery application responsible for ingesting
--    video content,  storing it, and making it available to
--    streamers.
--    
--    Caching Node: Content delivery application responsible for
--    caching content from a vault and streaming it to other caching
--    nodes or streamers.
--    
--    Streamer: Content delivery application responsible for
--    streaming video to STB's.
--  RevDate
--    201205170000Z
--  RevDescr
--    Added bandwidth reporting by content type support.
--  RevDate
--    201007290000Z
--  RevDescr
--    Added stream control message queue reporting support.
--  RevDate
--    201006040000Z
--  RevDescr
--    Initial version of this MIB module.

ciscoCdstvStatsMIBNotifs OBJECT IDENTIFIER ::= { ciscoCdstvCsStatsMIB 0 }
ciscoCdstvStatsMIBObjects OBJECT IDENTIFIER ::= { ciscoCdstvCsStatsMIB 1 }
ciscoCdstvStatsMIBConform OBJECT IDENTIFIER ::= { ciscoCdstvCsStatsMIB 2 }
ciscoCdstvCacheStats OBJECT IDENTIFIER ::= { ciscoCdstvStatsMIBObjects 1 }
ciscoCdstvStreamStats OBJECT IDENTIFIER ::= { ciscoCdstvStatsMIBObjects 2 }
ciscoCdstvStatsMIBCompliances OBJECT IDENTIFIER ::= { ciscoCdstvStatsMIBConform 1 }
ciscoCdstvStatsMIBGroups OBJECT IDENTIFIER ::= { ciscoCdstvStatsMIBConform 2 }

cdstvCacheCapacity OBJECT-TYPE
    SYNTAX Gauge(0..4294967295)
--  Units
--    kilobytes
    ACCESS read-only
    STATUS mandatory
    DESCRIPTION
        "This object indicates the total cache capacity of this
        streamer, caching node or ISV."
    ::= { ciscoCdstvCacheStats 1 }

cdstvCacheLevel OBJECT-TYPE
    SYNTAX Gauge
--  Units
--    kilobytes
    ACCESS read-only
    STATUS mandatory
    DESCRIPTION
        "This object indicates the used cache level for this streamer,
        caching node or ISV."
    ::= { ciscoCdstvCacheStats 2 }

cdstvFillReceiveStreams OBJECT-TYPE
    SYNTAX Gauge
--  Units
--    stream count
    ACCESS read-only
    STATUS mandatory
    DESCRIPTION
        "This object indicates the total number of cache fills
        this streamer, caching node or ISV gets from other devices. 
        For a streamer or ISV, the source devices can be vaults, caching
        nodes or neighboring streamers. For caching nodes, the source
        can be vaults or neighboring caching nodes. For streamers, this
        metric includes both CCP and HTTP streams."
    ::= { ciscoCdstvCacheStats 3 }

cdstvFillStreamCommittedBW OBJECT-TYPE
    SYNTAX Gauge
--  Units
--    kilobits
    ACCESS read-only
    STATUS mandatory
    DESCRIPTION
        "This object indicates the committed bandwidth for cache fills
        this streamer, caching node or ISV gets from other devices. For
        a streamer or ISV , the other devices can
        be vaults, caching nodes or neighboring streamers. For caching
        nodes, the other devices can be vaults or neighboring caching
        nodes. For streamers, this metric includes both CCP and HTTP
        streams."
    ::= { ciscoCdstvCacheStats 4 }

cdstvFillStreamActualBW OBJECT-TYPE
    SYNTAX Gauge
--  Units
--    kilobits
    ACCESS read-only
    STATUS mandatory
    DESCRIPTION
        "This object indicates the actual bandwidth of cache fills this
        streamer, caching node or ISV gets from other devices. For a
        streamer or ISV, the other devices can be vaults, caching nodes
        or neighboring streamers. For caching nodes, the other devices
        can be vaults or neighboring caching
        nodes. For streamers, this metric includes both CCP and HTTP
        streams."
    ::= { ciscoCdstvCacheStats 5 }

cdstvDiskReadStreams OBJECT-TYPE
    SYNTAX Gauge
--  Units
--    stream count
    ACCESS read-only
    STATUS mandatory
    DESCRIPTION
        "This object indicates the disk-read stream count for this
        streamer, caching node or ISV, i.e. the number of streams served
        from this device's disks."
    ::= { ciscoCdstvCacheStats 6 }

cdstvDiskReadBW OBJECT-TYPE
    SYNTAX Gauge
--  Units
--    kilobits
    ACCESS read-only
    STATUS mandatory
    DESCRIPTION
        "this object indicates the disk-read bandwidth for this
        streamer, caching node or ISV, i.e. the bandwidth of the streams
        read from this device's disk."
    ::= { ciscoCdstvCacheStats 7 }

cdstvCCPInfromVaultStreams OBJECT-TYPE
    SYNTAX Gauge
--  Units
--    stream count
    ACCESS read-only
    STATUS mandatory
    DESCRIPTION
        "This object indicates the number of CCP streams from a vault
        filling this device."
    ::= { ciscoCdstvCacheStats 8 }

cdstvCCPInFromVaultStreamBW OBJECT-TYPE
    SYNTAX Gauge
--  Units
--    kilobits
    ACCESS read-only
    STATUS mandatory
    DESCRIPTION
        "This object indicates the bandwidth of CCP streams from a
        vault filling this device."
    ::= { ciscoCdstvCacheStats 9 }

cdstvCCPInFromCacheStreams OBJECT-TYPE
    SYNTAX Gauge
--  Units
--    stream count
    ACCESS read-only
    STATUS mandatory
    DESCRIPTION
        "This object indicates the number of CCP streams from a caching
        node filling this caching node or streamer."
    ::= { ciscoCdstvCacheStats 10 }

cdstvCCPInFromCacheStreamBW OBJECT-TYPE
    SYNTAX Gauge
--  Units
--    kilobits
    ACCESS read-only
    STATUS mandatory
    DESCRIPTION
        "This object indicates the bandwidth of CCP streams from a
        caching node filling this device."
    ::= { ciscoCdstvCacheStats 11 }

cdstvCCPInFromStreamerStreamCount OBJECT-TYPE
    SYNTAX Gauge
--  Units
--    stream count
    ACCESS read-only
    STATUS mandatory
    DESCRIPTION
        "This object indicates the number of CCP streams from another
        streamer filling this streamer."
    ::= { ciscoCdstvCacheStats 12 }

cdstvCCPInFromStreamerStreamBW OBJECT-TYPE
    SYNTAX Gauge(0..4294967295)
--  Units
--    kilobits
    ACCESS read-only
    STATUS mandatory
    DESCRIPTION
        "This object indicates the bandwidth of CCP streams from other
        streamers filling this streamer."
    ::= { ciscoCdstvCacheStats 13 }

cdstvActiveStreams OBJECT-TYPE
    SYNTAX Gauge
--  Units
--    stream count
    ACCESS read-only
    STATUS mandatory
    DESCRIPTION
        "This object specifies the number of active streams from this
        device. For a streamer, this includes CCP streams going out to
        other
        streamers. For caching nodes and vaults, this includes CCP
        streams going out to streamers or caching nodes. For vaults,
        this includes mirroring traffic as well."
    ::= { ciscoCdstvStreamStats 1 }

cdstvActiveStreamBW OBJECT-TYPE
    SYNTAX Gauge
--  Units
--    kilobits
    ACCESS read-only
    STATUS mandatory
    DESCRIPTION
        "This object indicates the bandwidth of active streams from this
        device. For a streamer, this includes CCP streams going out to
        other streamers. For caching nodes and vaults, this includes
        CCP
        streams going out to streamers or caching nodes. For vaults,
        this includes mirroring traffic as well."
    ::= { ciscoCdstvStreamStats 2 }

cdstvUniqueStreams OBJECT-TYPE
    SYNTAX Gauge
--  Units
--    stream count
    ACCESS read-only
    STATUS mandatory
    DESCRIPTION
        "This object indicates the number of unique streams going out
        from this device."
    ::= { ciscoCdstvStreamStats 3 }

cdstvUniqueStreamBW OBJECT-TYPE
    SYNTAX Gauge
--  Units
--    kilobits
    ACCESS read-only
    STATUS mandatory
    DESCRIPTION
        "This object indicates the bandwidth of unique streams going out
        from this device."
    ::= { ciscoCdstvStreamStats 4 }

cdstvCCPOutStreams OBJECT-TYPE
    SYNTAX Gauge
--  Units
--    stream count
    ACCESS read-only
    STATUS mandatory
    DESCRIPTION
        "This object indicates the number of CCP streams going out from
        this device. For streamers, the destination is another
        streamer.
        For caching nodes, the destination is a streamer or another
        caching node. For vaults, the destination can be a streamer,
        caching node or vault."
    ::= { ciscoCdstvStreamStats 5 }

cdstvCCPOutStreamBW OBJECT-TYPE
    SYNTAX Gauge
--  Units
--    kilobits
    ACCESS read-only
    STATUS mandatory
    DESCRIPTION
        "This object indicates the bandwidth of CCP streams
        going out from this device. For streamers, the destination is
        another streamer. For caching nodes, the destination is a
        streamer or another caching node. For vaults, the destination
        can be a streamer, caching node or vault."
    ::= { ciscoCdstvStreamStats 6 }

cdstvHTTPOutStreams OBJECT-TYPE
    SYNTAX Gauge
--  Units
--    stream count
    ACCESS read-only
    STATUS mandatory
    DESCRIPTION
        "This object indicates the number of HTTP streams going out from
        this caching node to streamers in a CDN setup."
    ::= { ciscoCdstvStreamStats 7 }

cdstvHTTPOutStreamBW OBJECT-TYPE
    SYNTAX Gauge
--  Units
--    kilobits
    ACCESS read-only
    STATUS mandatory
    DESCRIPTION
        "This object indicates the bandwidth of HTTP streams going out
        from this caching node to streamers in a CDN setup."
    ::= { ciscoCdstvStreamStats 8 }

cdstvSessionSetupSuccess OBJECT-TYPE
    SYNTAX Counter
    ACCESS read-only
    STATUS mandatory
    DESCRIPTION
        "This object indicates the number of successfully setup
        sessions since the counter was reset (the reference). The 
        seconds elapsed since the reference is indicated by 
        cdstvSecondsSinceReference."
    ::= { ciscoCdstvStreamStats 9 }

cdstvSessionSetupFailures OBJECT-TYPE
    SYNTAX Counter
    ACCESS read-only
    STATUS mandatory
    DESCRIPTION
        "This object indicates the number of unsuccessfully setup
        (failed) sessions since the counter was reset (the reference).
        The seconds elapsed since the
        reference is indicated by cdstvSecondsSinceReference."
    ::= { ciscoCdstvStreamStats 10 }

cdstvSecondsSinceReference OBJECT-TYPE
    SYNTAX TimeIntervalSec
--    Rsyntax Gauge
    ACCESS read-only
    STATUS mandatory
    DESCRIPTION
        "This object indicates the seconds elapsed since the last time
        the database was restarted and hence the cdstvSessionSetupSucess
        and cdstvSessionSetupFailures counters were reset."
    ::= { ciscoCdstvStreamStats 11 }

cdstvStreamControlMessageQueueMax OBJECT-TYPE
    SYNTAX Gauge
--  Units
--    elements
    ACCESS read-only
    STATUS mandatory
    DESCRIPTION
        "This object indicates the maximum size of the stream control
        message queue used in CDS."
    ::= { ciscoCdstvStreamStats 12 }

cdstvStreamControlMessageQueueSize OBJECT-TYPE
    SYNTAX Gauge
--  Units
--    elements
    ACCESS read-only
    STATUS mandatory
    DESCRIPTION
        "This object indicates the current size of the stream control
        message queue, i.e. the number of elements in the queue."
    ::= { ciscoCdstvStreamStats 13 }

cdstvSkippedPlaylistElements OBJECT-TYPE
    SYNTAX Gauge
--  Units
--    elements
    ACCESS read-only
    STATUS mandatory
    DESCRIPTION
        "This object indicates the number of skipped playlist
        elements."
    ::= { ciscoCdstvStreamStats 14 }

cdstvStatsByContentTypeTable OBJECT-TYPE
    SYNTAX SEQUENCE OF CdstvStatsByContentTypeEntry
    ACCESS not-accessible
    STATUS mandatory
    DESCRIPTION
        "This table lists the fill (ingress) and stream (egress) counts
        as well as the bandwidth used by the ingress fills and egress
        streams on this streamer, differentiated by the content type."
    ::= { ciscoCdstvStreamStats 15 }

cdstvStatsByContentTypeEntry OBJECT-TYPE
    SYNTAX CdstvStatsByContentTypeEntry
    ACCESS not-accessible
    STATUS mandatory
    DESCRIPTION
        "An entry (conceptual row) in the cdstvStatsByContentTypeTable.
        Each entry represents a content type and its active ingress and
        egress counts, as well as the  bandwidth consumed by the active
        fills and streams, for this streamer. A row is added for each
        content type supported by a streamer and the number of rows does
        not change for a particular streamer."
    INDEX { cdstvContentType }
    ::= { cdstvStatsByContentTypeTable 1 }

CdstvStatsByContentTypeEntry ::= SEQUENCE {
    cdstvContentType INTEGER,
    cdstvActiveEgressCount Gauge,
    cdstvActiveEgressBW Gauge,
    cdstvActiveIngressCount Gauge,
    cdstvActiveIngressBW Gauge
    }

cdstvContentType OBJECT-TYPE
    SYNTAX INTEGER {
        legacyVod(1),
        ndvrUniqueCopy(2),
        ndvrCommonCopy(3)
        }
    ACCESS not-accessible
    STATUS mandatory
    DESCRIPTION
        "This object indicates the type of the content being ingested
        into or streamed out of a streamer. Possible values are:
        
        legacyVod(1)      - Legacy VOD Content
        ndvrUniqueCopy(2) - NDVR Unique Copy Content
        ndvrCommonCopy(3) - NDVR Common Copy Content"
    ::= { cdstvStatsByContentTypeEntry 1 }

cdstvActiveEgressCount OBJECT-TYPE
    SYNTAX Gauge
--  Units
--    stream count
    ACCESS read-only
    STATUS mandatory
    DESCRIPTION
        "This object indicates the number of active egress streams from
        this streamer for the type of content indicated by
        cdstvContentType."
    ::= { cdstvStatsByContentTypeEntry 2 }

cdstvActiveEgressBW OBJECT-TYPE
    SYNTAX Gauge
--  Units
--    kilobits
    ACCESS read-only
    STATUS mandatory
    DESCRIPTION
        "This object indicates the bandwidth consumed by active egress
        streams from this streamer for the type of content indicated by
        cdstvContentType."
    ::= { cdstvStatsByContentTypeEntry 3 }

cdstvActiveIngressCount OBJECT-TYPE
    SYNTAX Gauge
--  Units
--    fill count
    ACCESS read-only
    STATUS mandatory
    DESCRIPTION
        "This object indicates the number of active ingress fills into
        this streamer for the type of content indicated by
        cdstvContentType."
    ::= { cdstvStatsByContentTypeEntry 4 }

cdstvActiveIngressBW OBJECT-TYPE
    SYNTAX Gauge
--  Units
--    kilobits
    ACCESS read-only
    STATUS mandatory
    DESCRIPTION
        "This object indicates the bandwidth consumed by active ingress
        fills into this streamer for the type of content indicated by
        cdstvContentType."
    ::= { cdstvStatsByContentTypeEntry 5 }

cdstvHTTPInStreams OBJECT-TYPE
    SYNTAX Gauge
--  Units
--    stream count
    ACCESS read-only
    STATUS mandatory
    DESCRIPTION
        "This object indicates the number of HTTP streams filling this
        streamer."
    ::= { ciscoCdstvCacheStats 14 }

cdstvHTTPInStreamBW OBJECT-TYPE
    SYNTAX Gauge
--  Units
--    kilobits
    ACCESS read-only
    STATUS mandatory
    DESCRIPTION
        "This object indicates the bandwidth of HTTP streams filling
        this streamer."
    ::= { ciscoCdstvCacheStats 15 }

cdstvActiveIngestStreams OBJECT-TYPE
    SYNTAX Gauge
--  Units
--    stream count
    ACCESS read-only
    STATUS mandatory
    DESCRIPTION
        "This object indicates the number of active ingest streams
        filling this vault."
    ::= { ciscoCdstvCacheStats 16 }

cdstvActiveIngestStreamBW OBJECT-TYPE
    SYNTAX Gauge
--  Units
--    kilobits
    ACCESS read-only
    STATUS mandatory
    DESCRIPTION
        "This object indicates the bandwidth of active ingest streams
        filling this vault."
    ::= { ciscoCdstvCacheStats 17 }

ciscoCdstvStatsMIBCacheObjectGroup OBJECT IDENTIFIER ::= { ciscoCdstvStatsMIBGroups 1 }
-- OBJECT-GROUP
--  Status
--    mandatory
--  Descr
--    A collection of objects providing caching statistics.
--  objects
--    cdstvCacheCapacity, cdstvCacheLevel, cdstvFillReceiveStreams, 
--    cdstvFillStreamCommittedBW, cdstvFillStreamActualBW, 
--    cdstvDiskReadStreams, cdstvDiskReadBW, 
--    cdstvCCPInfromVaultStreams, cdstvCCPInFromVaultStreamBW, 
--    cdstvCCPInFromCacheStreams, cdstvCCPInFromCacheStreamBW, 
--    cdstvCCPInFromStreamerStreamCount, 
--    cdstvCCPInFromStreamerStreamBW, cdstvHTTPInStreams, 
--    cdstvHTTPInStreamBW, cdstvActiveIngestStreams, 
--    cdstvActiveIngestStreamBW

ciscoCdstvStatsMIBStreamObjectGroup OBJECT IDENTIFIER ::= { ciscoCdstvStatsMIBGroups 2 }
-- OBJECT-GROUP
--  Status
--    deprecated
--  Descr
--    A collection of objects providing streaming statistics.
--    ciscoCdstvStatsMIBStreamObjectGroup object is superseded by
--    ciscoCdstvStatsMIBStreamObjectGroup2.
--  objects
--    cdstvActiveStreams, cdstvActiveStreamBW, cdstvUniqueStreams, 
--    cdstvUniqueStreamBW, cdstvCCPOutStreams, cdstvCCPOutStreamBW, 
--    cdstvHTTPOutStreams, cdstvHTTPOutStreamBW, 
--    cdstvSessionSetupSuccess, cdstvSecondsSinceReference, 
--    cdstvSessionSetupFailures

ciscoCdstvStatsMIBStreamObjectGroup2 OBJECT IDENTIFIER ::= { ciscoCdstvStatsMIBGroups 3 }
-- OBJECT-GROUP
--  Status
--    deprecated
--  Descr
--    A collection of objects providing streaming statistics.
--    ciscoCdstvStatsMIBStreamObjectGroup2 object is superseded by
--    ciscoCdstvStatsMIBStreamObjectGroup3.
--  objects
--    cdstvActiveStreams, cdstvActiveStreamBW, cdstvUniqueStreams, 
--    cdstvUniqueStreamBW, cdstvCCPOutStreams, cdstvCCPOutStreamBW, 
--    cdstvHTTPOutStreams, cdstvHTTPOutStreamBW, 
--    cdstvSessionSetupSuccess, cdstvSessionSetupFailures, 
--    cdstvSecondsSinceReference, cdstvStreamControlMessageQueueMax, 
--    cdstvStreamControlMessageQueueSize, 
--    cdstvSkippedPlaylistElements

ciscoCdstvStatsMIBStreamObjectGroup3 OBJECT IDENTIFIER ::= { ciscoCdstvStatsMIBGroups 4 }
-- OBJECT-GROUP
--  Status
--    mandatory
--  Descr
--    A collection of objects providing streaming statistics.
--  objects
--    cdstvActiveStreams, cdstvActiveStreamBW, cdstvUniqueStreams, 
--    cdstvUniqueStreamBW, cdstvCCPOutStreams, cdstvCCPOutStreamBW, 
--    cdstvHTTPOutStreams, cdstvHTTPOutStreamBW, 
--    cdstvSessionSetupSuccess, cdstvSessionSetupFailures, 
--    cdstvSecondsSinceReference, cdstvStreamControlMessageQueueMax, 
--    cdstvStreamControlMessageQueueSize, 
--    cdstvSkippedPlaylistElements, cdstvActiveEgressCount, 
--    cdstvActiveEgressBW, cdstvActiveIngressCount, 
--    cdstvActiveIngressBW

ciscoCdstvStatsMIBModuleCompliance OBJECT IDENTIFIER ::= { ciscoCdstvStatsMIBCompliances 1 }
-- MODULE-COMPLIANCE
--  Status
--    obsolete
--  Descr
--    The compliance statement for the entities which
--    implement the CISCO-CDSTV-STATS-MIB.
--  Module
--    >>current<<
--   MandGroup
--    ciscoCdstvStatsMIBCacheObjectGroup
--   MandGroup
--    ciscoCdstvStatsMIBStreamObjectGroup

ciscoCdstvStatsMIBModuleCompliance2 OBJECT IDENTIFIER ::= { ciscoCdstvStatsMIBCompliances 2 }
-- MODULE-COMPLIANCE
--  Status
--    deprecated
--  Descr
--    The compliance statement for the entities which
--    implement the CISCO-CDSTV-STATS-MIB.
--  Module
--    >>current<<
--   MandGroup
--    ciscoCdstvStatsMIBCacheObjectGroup
--   MandGroup
--    ciscoCdstvStatsMIBStreamObjectGroup2

ciscoCdstvStatsMIBModuleCompliance3 OBJECT IDENTIFIER ::= { ciscoCdstvStatsMIBCompliances 3 }
-- MODULE-COMPLIANCE
--  Status
--    mandatory
--  Descr
--    The compliance statement for the entities which
--    implement the CISCO-CDSTV-STATS-MIB.
--  Module
--    >>current<<
--   MandGroup
--    ciscoCdstvStatsMIBCacheObjectGroup
--   MandGroup
--    ciscoCdstvStatsMIBStreamObjectGroup3


END
