-- MIB file created 01-Apr-2003 09:25:16, by
--   SMICng version 2.2.11-beta(PRO)(Solaris), January 20, 2001. Enterprise key cisco.com

FRAME-RELAY-DTE-MIB DEFINITIONS ::= BEGIN

-- From file: "FRAME-RELAY-DTE-MIB.my"
-- Compile options "4 7 F H N W 03 06 0B 0G 0N 0T"

IMPORTS
    RowStatus, TimeStamp
            FROM SNMPv2-TC-v1
    transmission
            FROM RFC1213-MIB
    InterfaceIndex
            FROM IF-MIB
    Counter
            FROM RFC1155-SMI
    OBJECT-TYPE
            FROM RFC-1212
    TRAP-TYPE
            FROM RFC-1215;

frameRelayDTE OBJECT IDENTIFIER ::= { transmission 32 }
-- MODULE-IDENTITY
--  LastUpdated
--    9705010229Z
--  OrgName
--    IETF IPLPDN Working Group
--  ContactInfo
--           Caralyn Brown
--    Postal: Cadia Networks, Inc.
--            1 Corporate Drive
--            Andover, Massachusetts  01810
--    Tel:    +1 508 689 2400 x133
--    E-Mail: cbrown@cadia.com
--    
--            Fred Baker
--    Postal: Cisco Systems
--            519 Lado Drive
--            Santa Barbara, California 93111
--    Tel:    +1 408 526 425
--    E-Mail: fred@cisco.com
--  Descr
--    The MIB module to describe the use of a Frame Relay
--    interface by a DTE.
--  RevDate
--    9705010229Z
--  RevDescr
--    Converted from SMIv1 to SMIv2. (Thus, indices are
--    read-only rather than being not-accessible.) Added
--    objects and made clarifications based on implementation
--    experience.
--  RevDate
--    9204010000Z
--  RevDescr
--    Published as RFC 1315, the initial version of this MIB
--    module.

frameRelayTrapControl OBJECT IDENTIFIER ::= { frameRelayDTE 4 }
frameRelayTraps OBJECT IDENTIFIER ::= { frameRelayDTE 0 }
frConformance   OBJECT IDENTIFIER ::= { frameRelayDTE 6 }
frGroups        OBJECT IDENTIFIER ::= { frConformance 1 }
frCompliances   OBJECT IDENTIFIER ::= { frConformance 2 }

DLCI ::= INTEGER(0..8388607)
-- TEXTUAL-CONVENTION
--  Status
--    mandatory
--  Descr
--    The range of DLCI values.  Note that this varies by
--    interface configuration; normally, interfaces may use
--    0..1023, but may be configured to use ranges as large
--    as 0..2^23.

frDlcmiTable OBJECT-TYPE
    SYNTAX SEQUENCE OF FrDlcmiEntry
    ACCESS not-accessible
    STATUS mandatory
    DESCRIPTION
        "The Parameters for the Data Link Connection Management
        Interface for the frame relay service on this
        interface."
    REFERENCE
        "American National Standard T1.617-1991, Annex D"
    ::= { frameRelayDTE 1 }

frDlcmiEntry OBJECT-TYPE
    SYNTAX FrDlcmiEntry
    ACCESS not-accessible
    STATUS mandatory
    DESCRIPTION
        "The Parameters for a particular Data Link Connection
        Management Interface."
    INDEX { frDlcmiIfIndex }
    ::= { frDlcmiTable 1 }

FrDlcmiEntry ::= SEQUENCE {
    frDlcmiIfIndex InterfaceIndex,
    frDlcmiState INTEGER,
    frDlcmiAddress INTEGER,
    frDlcmiAddressLen INTEGER,
    frDlcmiPollingInterval INTEGER,
    frDlcmiFullEnquiryInterval INTEGER,
    frDlcmiErrorThreshold INTEGER,
    frDlcmiMonitoredEvents INTEGER,
    frDlcmiMaxSupportedVCs DLCI,
    frDlcmiMulticast INTEGER,
    frDlcmiStatus INTEGER,
    frDlcmiRowStatus RowStatus
    }

frDlcmiIfIndex OBJECT-TYPE
    SYNTAX InterfaceIndex
--    Rsyntax INTEGER(1..2147483647)
    ACCESS read-only
    STATUS mandatory
    DESCRIPTION
        "The ifIndex value of the corresponding ifEntry."
    ::= { frDlcmiEntry 1 }

frDlcmiState OBJECT-TYPE
    SYNTAX INTEGER {
        noLmiConfigured(1),
        lmiRev1(2),
        ansiT1617D(3),
        ansiT1617B(4),
        itut933A(5),
        ansiT1617D1994(6)
        }
    ACCESS read-write
    STATUS mandatory
    DESCRIPTION
        "This variable states which Data Link Connection
        Management scheme is active (and by implication, what
        DLCI it uses) on the Frame Relay interface."
    REFERENCE
        "American National Standard T1.617-1991, American
        National Standard T1.617a-1994, ITU-T Recommendation
        Q.933 (03/93)."
    ::= { frDlcmiEntry 2 }

frDlcmiAddress OBJECT-TYPE
    SYNTAX INTEGER {
        q921(1),
        q922March90(2),
        q922November90(3),
        q922(4)
        }
    ACCESS read-write
    STATUS mandatory
    DESCRIPTION
        "This variable states which address format is in use on
        the Frame Relay interface."
    ::= { frDlcmiEntry 3 }

frDlcmiAddressLen OBJECT-TYPE
    SYNTAX INTEGER {
        twoOctets(2),
        threeOctets(3),
        fourOctets(4)
        }
    ACCESS read-write
    STATUS mandatory
    DESCRIPTION
        "This variable states the address length in octets.  In
        the case of Q922 format, the length indicates the
        entire length of the address including the control
        portion."
    ::= { frDlcmiEntry 4 }

frDlcmiPollingInterval OBJECT-TYPE
    SYNTAX INTEGER(5..30)
--  Units
--    seconds
    ACCESS read-write
    STATUS mandatory
    DESCRIPTION
        "This is the number of seconds between successive
        status enquiry messages."
    REFERENCE
        "American National Standard T1.617-1991, Section D.7
        Timer T391."
    DEFVAL { 10 }
    ::= { frDlcmiEntry 5 }

frDlcmiFullEnquiryInterval OBJECT-TYPE
    SYNTAX INTEGER(1..255)
    ACCESS read-write
    STATUS mandatory
    DESCRIPTION
        "Number of status enquiry intervals that pass before
        issuance of a full status enquiry message."
    REFERENCE
        "American National Standard T1.617-1991, Section D.7
        Counter N391."
    DEFVAL { 6 }
    ::= { frDlcmiEntry 6 }

frDlcmiErrorThreshold OBJECT-TYPE
    SYNTAX INTEGER(1..10)
    ACCESS read-write
    STATUS mandatory
    DESCRIPTION
        "This is the maximum number of unanswered Status
        Enquiries the equipment shall accept before declaring
        the interface down."
    REFERENCE
        "American National Standard T1.617-1991, Section D.5.1
        Counter N392."
    DEFVAL { 3 }
    ::= { frDlcmiEntry 7 }

frDlcmiMonitoredEvents OBJECT-TYPE
    SYNTAX INTEGER(1..10)
    ACCESS read-write
    STATUS mandatory
    DESCRIPTION
        "This is the number of status polling intervals over
        which the error threshold is counted.  For example, if
        within 'MonitoredEvents' number of events the station
        receives 'ErrorThreshold' number of errors, the
        interface is marked as down."
    REFERENCE
        "American National Standard T1.617-1991, Section D.5.2
        Counter N393."
    DEFVAL { 4 }
    ::= { frDlcmiEntry 8 }

frDlcmiMaxSupportedVCs OBJECT-TYPE
    SYNTAX DLCI
--    Rsyntax INTEGER(0..8388607)
    ACCESS read-write
    STATUS mandatory
    DESCRIPTION
        "The maximum number of Virtual Circuits allowed for
        this interface.  Usually dictated by the Frame Relay
        network.
        
        In response to a SET, if a value less than zero or
        higher than the agent's maximal capability is
        configured, the agent should respond badValue"
    ::= { frDlcmiEntry 9 }

frDlcmiMulticast OBJECT-TYPE
    SYNTAX INTEGER {
        nonBroadcast(1),
        broadcast(2)
        }
    ACCESS read-write
    STATUS mandatory
    DESCRIPTION
        "This indicates whether the Frame Relay interface is
        using a multicast service."
    ::= { frDlcmiEntry 10 }

frDlcmiStatus OBJECT-TYPE
    SYNTAX INTEGER {
        running(1),
        fault(2),
        initializing(3)
        }
    ACCESS read-only
    STATUS mandatory
    DESCRIPTION
        "This indicates the status of the Frame Relay interface
        as determined by the performance of the dlcmi.  If no
        dlcmi is running, the Frame Relay interface will stay
        in the running state indefinitely."
    ::= { frDlcmiEntry 11 }

frDlcmiRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "SNMP Version 2 Row Status Variable.  Writable objects
        in the table may be written in any RowStatus state."
    ::= { frDlcmiEntry 12 }

frCircuitTable OBJECT-TYPE
    SYNTAX SEQUENCE OF FrCircuitEntry
    ACCESS not-accessible
    STATUS mandatory
    DESCRIPTION
        "A table containing information about specific Data
        Link Connections (DLC) or virtual circuits."
    ::= { frameRelayDTE 2 }

frCircuitEntry OBJECT-TYPE
    SYNTAX FrCircuitEntry
    ACCESS not-accessible
    STATUS mandatory
    DESCRIPTION
        "The information regarding a single Data Link
        Connection.  Discontinuities in the counters contained
        in this table are indicated by the value in
        frCircuitCreationTime."
    INDEX { frCircuitIfIndex, frCircuitDlci }
    ::= { frCircuitTable 1 }

FrCircuitEntry ::= SEQUENCE {
    frCircuitIfIndex InterfaceIndex,
    frCircuitDlci DLCI,
    frCircuitState INTEGER,
    frCircuitReceivedFECNs Counter,
    frCircuitReceivedBECNs Counter,
    frCircuitSentFrames Counter,
    frCircuitSentOctets Counter,
    frCircuitReceivedFrames Counter,
    frCircuitReceivedOctets Counter,
    frCircuitCreationTime TimeStamp,
    frCircuitLastTimeChange TimeStamp,
    frCircuitCommittedBurst INTEGER,
    frCircuitExcessBurst INTEGER,
    frCircuitThroughput INTEGER,
    frCircuitMulticast INTEGER,
    frCircuitType INTEGER,
    frCircuitDiscards Counter,
    frCircuitReceivedDEs Counter,
    frCircuitSentDEs Counter,
    frCircuitLogicalIfIndex InterfaceIndex,
    frCircuitRowStatus RowStatus
    }

frCircuitIfIndex OBJECT-TYPE
    SYNTAX InterfaceIndex
--    Rsyntax INTEGER(1..2147483647)
    ACCESS read-only
    STATUS mandatory
    DESCRIPTION
        "The ifIndex Value of the ifEntry this virtual circuit
        is layered onto."
    ::= { frCircuitEntry 1 }

frCircuitDlci OBJECT-TYPE
    SYNTAX DLCI
--    Rsyntax INTEGER(0..8388607)
    ACCESS read-only
    STATUS mandatory
    DESCRIPTION
        "The Data Link Connection Identifier for this virtual
        circuit."
    REFERENCE
        "American National Standard T1.618-1991, Section 3.3.6"
    ::= { frCircuitEntry 2 }

frCircuitState OBJECT-TYPE
    SYNTAX INTEGER {
        invalid(1),
        active(2),
        inactive(3)
        }
    ACCESS read-write
    STATUS mandatory
    DESCRIPTION
        "Indicates whether the particular virtual circuit is
        operational.  In the absence of a Data Link Connection
        Management Interface, virtual circuit entries (rows)
        may be created by setting virtual circuit state to
        'active', or deleted by changing Circuit state to
        'invalid'.
        
        Whether or not the row actually disappears is left to
        the implementation, so this object may actually read as
        'invalid' for some arbitrary length of time.  It is
        also legal to set the state of a virtual circuit to
        'inactive' to temporarily disable a given circuit.
        
        The use of 'invalid' is deprecated in this SNMP Version
        2 MIB, in favor of frCircuitRowStatus."
    DEFVAL { active }
    ::= { frCircuitEntry 3 }

frCircuitReceivedFECNs OBJECT-TYPE
    SYNTAX Counter
    ACCESS read-only
    STATUS mandatory
    DESCRIPTION
        "Number of frames received from the network indicating
        forward congestion since the virtual circuit was
        created.  This occurs when the remote DTE sets the FECN
        flag, or when a switch in the network enqueues the
        frame to a trunk whose transmission queue is
        congested."
    REFERENCE
        "American National Standard T1.618-1991, Section 3.3.3"
    ::= { frCircuitEntry 4 }

frCircuitReceivedBECNs OBJECT-TYPE
    SYNTAX Counter
    ACCESS read-only
    STATUS mandatory
    DESCRIPTION
        "Number of frames received from the network indicating
        backward congestion since the virtual circuit was
        created.  This occurs when the remote DTE sets the BECN
        flag, or when a switch in the network receives the
        frame from a trunk whose transmission queue is
        congested."
    REFERENCE
        "American National Standard T1.618-1991, Section 3.3.4"
    ::= { frCircuitEntry 5 }

frCircuitSentFrames OBJECT-TYPE
    SYNTAX Counter
    ACCESS read-only
    STATUS mandatory
    DESCRIPTION
        "The number of frames sent from this virtual circuit
        since it was created."
    ::= { frCircuitEntry 6 }

frCircuitSentOctets OBJECT-TYPE
    SYNTAX Counter
    ACCESS read-only
    STATUS mandatory
    DESCRIPTION
        "The number of octets sent from this virtual circuit
        since it was created.  Octets counted are the full
        frame relay header and the payload, but do not include
        the flag characters or CRC."
    ::= { frCircuitEntry 7 }

frCircuitReceivedFrames OBJECT-TYPE
    SYNTAX Counter
    ACCESS read-only
    STATUS mandatory
    DESCRIPTION
        "Number of frames received over this virtual circuit
        since it was created."
    ::= { frCircuitEntry 8 }

frCircuitReceivedOctets OBJECT-TYPE
    SYNTAX Counter
    ACCESS read-only
    STATUS mandatory
    DESCRIPTION
        "Number of octets received over this virtual circuit
        since it was created.  Octets counted include the full
        frame relay header, but do not include the flag
        characters or the CRC."
    ::= { frCircuitEntry 9 }

frCircuitCreationTime OBJECT-TYPE
    SYNTAX TimeStamp
--    Rsyntax TimeTicks
    ACCESS read-only
    STATUS mandatory
    DESCRIPTION
        "The value of sysUpTime when the virtual circuit was
        created, whether by the Data Link Connection Management
        Interface or by a SetRequest."
    ::= { frCircuitEntry 10 }

frCircuitLastTimeChange OBJECT-TYPE
    SYNTAX TimeStamp
--    Rsyntax TimeTicks
    ACCESS read-only
    STATUS mandatory
    DESCRIPTION
        "The value of sysUpTime when last there was a change in
        the virtual circuit state"
    ::= { frCircuitEntry 11 }

frCircuitCommittedBurst OBJECT-TYPE
    SYNTAX INTEGER(0..2147483647)
    ACCESS read-write
    STATUS mandatory
    DESCRIPTION
        "This variable indicates the maximum amount of data, in
        bits, that the network agrees to transfer under normal
        conditions, during the measurement interval."
    REFERENCE
        "American National Standard T1.617-1991, Section
        6.5.19"
    DEFVAL { 0 }
    ::= { frCircuitEntry 12 }

frCircuitExcessBurst OBJECT-TYPE
    SYNTAX INTEGER(0..2147483647)
    ACCESS read-write
    STATUS mandatory
    DESCRIPTION
        "This variable indicates the maximum amount of
        uncommitted data bits that the network will attempt to
        deliver over the measurement interval.
        
        By default, if not configured when creating the entry,
        the Excess Information Burst Size is set to the value
        of ifSpeed."
    REFERENCE
        "American National Standard T1.617-1991, Section
        6.5.19"
    ::= { frCircuitEntry 13 }

frCircuitThroughput OBJECT-TYPE
    SYNTAX INTEGER(0..2147483647)
    ACCESS read-write
    STATUS mandatory
    DESCRIPTION
        "Throughput is the average number of 'Frame Relay
        Information Field' bits transferred per second across a
        user network interface in one direction, measured over
        the measurement interval.
        
        If the configured committed burst rate and throughput
        are both non-zero, the measurement interval, T, is
            T=frCircuitCommittedBurst/frCircuitThroughput.
        
        If the configured committed burst rate and throughput
        are both zero, the measurement interval, T, is
                   T=frCircuitExcessBurst/ifSpeed."
    REFERENCE
        "American National Standard T1.617-1991, Section
        6.5.19"
    DEFVAL { 0 }
    ::= { frCircuitEntry 14 }

frCircuitMulticast OBJECT-TYPE
    SYNTAX INTEGER {
        unicast(1),
        oneWay(2),
        twoWay(3),
        nWay(4)
        }
    ACCESS read-write
    STATUS mandatory
    DESCRIPTION
        "This indicates whether this VC is used as a unicast VC
        (i.e. not multicast) or the type of multicast service
        subscribed to"
    REFERENCE
        "Frame Relay PVC Multicast Service and Protocol
        Description Implementation: FRF.7 Frame Relay Forum
        Technical Committe October 21, 1994"
    DEFVAL { unicast }
    ::= { frCircuitEntry 15 }

frCircuitType OBJECT-TYPE
    SYNTAX INTEGER {
        static(1),
        dynamic(2)
        }
    ACCESS read-only
    STATUS mandatory
    DESCRIPTION
        "Indication of whether the VC was manually created
        (static), or dynamically created (dynamic) via the data
        link control management interface."
    ::= { frCircuitEntry 16 }

frCircuitDiscards OBJECT-TYPE
    SYNTAX Counter
    ACCESS read-only
    STATUS mandatory
    DESCRIPTION
        "The number of inbound frames dropped because of format
        errors, or because the VC is inactive."
    ::= { frCircuitEntry 17 }

frCircuitReceivedDEs OBJECT-TYPE
    SYNTAX Counter
    ACCESS read-only
    STATUS mandatory
    DESCRIPTION
        "Number of frames received from the network indicating
        that they were eligible for discard since the virtual
        circuit was created.  This occurs when the remote DTE
        sets the DE flag, or when in remote DTE's switch
        detects that the frame was received as Excess Burst
        data."
    REFERENCE
        "American National Standard T1.618-1991, Section 3.3.4"
    ::= { frCircuitEntry 18 }

frCircuitSentDEs OBJECT-TYPE
    SYNTAX Counter
    ACCESS read-only
    STATUS mandatory
    DESCRIPTION
        "Number of frames sent to the network indicating that
        they were eligible for discard since the virtual
        circuit was created.   This occurs when the local DTE
        sets the DE flag, indicating that during Network
        congestion situations those frames should be discarded
        in preference of other frames sent without the DE bit
        set."
    REFERENCE
        "American National  Standard  T1.618-1991, Section
        3.3.4"
    ::= { frCircuitEntry 19 }

frCircuitLogicalIfIndex OBJECT-TYPE
    SYNTAX InterfaceIndex
--    Rsyntax INTEGER(1..2147483647)
    ACCESS read-write
    STATUS mandatory
    DESCRIPTION
        "Normally the same value as frDlcmiIfIndex, but
        different when an implementation associates a virtual
        ifEntry with a DLC or set of DLCs in order to associate
        higher layer objects such as the ipAddrEntry with a
        subset of the virtual circuits on a Frame Relay
        interface. The type of such ifEntries is defined by the
        higher layer object; for example, if PPP/Frame Relay is
        implemented, the ifType of this ifEntry would be PPP.
        If it is not so defined, as would be the case with an
        ipAddrEntry, it should be of type Other."
    ::= { frCircuitEntry 20 }

frCircuitRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create a new row or modify or
        destroy an existing row in the manner described in the
        definition of the RowStatus textual convention.
        Writable objects in the table may be written in any
        RowStatus state."
    ::= { frCircuitEntry 21 }

frErrTable OBJECT-TYPE
    SYNTAX SEQUENCE OF FrErrEntry
    ACCESS not-accessible
    STATUS mandatory
    DESCRIPTION
        "A table containing information about Errors on the
        Frame Relay interface.  Discontinuities in the counters
        contained in this table are the same as apply to the
        ifEntry associated with the Interface."
    ::= { frameRelayDTE 3 }

frErrEntry OBJECT-TYPE
    SYNTAX FrErrEntry
    ACCESS not-accessible
    STATUS mandatory
    DESCRIPTION
        "The error information for a single frame relay
        interface."
    INDEX { frErrIfIndex }
    ::= { frErrTable 1 }

FrErrEntry ::= SEQUENCE {
    frErrIfIndex InterfaceIndex,
    frErrType INTEGER,
    frErrData OCTET STRING,
    frErrTime TimeStamp,
    frErrFaults Counter,
    frErrFaultTime TimeStamp
    }

frErrIfIndex OBJECT-TYPE
    SYNTAX InterfaceIndex
--    Rsyntax INTEGER(1..2147483647)
    ACCESS read-only
    STATUS mandatory
    DESCRIPTION
        "The ifIndex Value of the corresponding ifEntry."
    ::= { frErrEntry 1 }

frErrType OBJECT-TYPE
    SYNTAX INTEGER {
        unknownError(1),
        receiveShort(2),
        receiveLong(3),
        illegalAddress(4),
        unknownAddress(5),
        dlcmiProtoErr(6),
        dlcmiUnknownIE(7),
        dlcmiSequenceErr(8),
        dlcmiUnknownRpt(9),
        noErrorSinceReset(10)
        }
    ACCESS read-only
    STATUS mandatory
    DESCRIPTION
        "The type of error that was last seen  on  this interface:
        
        receiveShort: frame was not long enough to allow
                demultiplexing - the address field was incomplete,
                or for virtual circuits using Multiprotocol over
                Frame Relay, the protocol identifier was missing
                or incomplete.
        
        receiveLong: frame exceeded maximum length configured for this
                     interface.
        
        illegalAddress: address field did not match configured format.
        
        unknownAddress: frame received on a virtual circuit which was not
                        active or administratively disabled.
        
        dlcmiProtoErr: unspecified error occurred when attempting to
                       interpret link maintenance frame.
        
        dlcmiUnknownIE: link maintenance frame contained an Information
                        Element type which is not valid for the
                        configured link maintenance protocol.
        
        dlcmiSequenceErr: link maintenance frame contained a sequence
                          number other than the expected value.
        
        dlcmiUnknownRpt: link maintenance frame contained a Report Type
                         Information Element whose value was not valid
                         for the configured link maintenance protocol.
        
        noErrorSinceReset: no errors have been detected since the last
                           cold start or warm start."
    ::= { frErrEntry 2 }

frErrData OBJECT-TYPE
    SYNTAX OCTET STRING(SIZE(1..1600))
    ACCESS read-only
    STATUS mandatory
    DESCRIPTION
        "An octet string containing as much of the error packet
        as possible.  As a minimum, it must contain the Q.922
        Address or as much as was delivered.  It is desirable
        to include all header and demultiplexing information."
    ::= { frErrEntry 3 }

frErrTime OBJECT-TYPE
    SYNTAX TimeStamp
--    Rsyntax TimeTicks
    ACCESS read-only
    STATUS mandatory
    DESCRIPTION
        "The value of sysUpTime at which the error was
        detected."
    ::= { frErrEntry 4 }

frErrFaults OBJECT-TYPE
    SYNTAX Counter
    ACCESS read-only
    STATUS mandatory
    DESCRIPTION
        "The number of times the interface has gone down since
        it was initialized."
    ::= { frErrEntry 5 }

frErrFaultTime OBJECT-TYPE
    SYNTAX TimeStamp
--    Rsyntax TimeTicks
    ACCESS read-only
    STATUS mandatory
    DESCRIPTION
        "The value of sysUpTime at the time when the interface
        was taken down due to excessive errors.  Excessive
        errors is defined as the time when a DLCMI exceeds the
        frDlcmiErrorThreshold number of errors within
        frDlcmiMonitoredEvents. See FrDlcmiEntry for further
        details."
    ::= { frErrEntry 6 }

frTrapState OBJECT-TYPE
    SYNTAX INTEGER {
        enabled(1),
        disabled(2)
        }
    ACCESS read-write
    STATUS mandatory
    DESCRIPTION
        "This variable indicates whether the system produces
        the frDLCIStatusChange trap."
    DEFVAL { disabled }
    ::= { frameRelayTrapControl 1 }

frTrapMaxRate OBJECT-TYPE
    SYNTAX INTEGER(0..3600000)
    ACCESS read-write
    STATUS mandatory
    DESCRIPTION
        "This variable indicates the number of milliseconds
        that must elapse between trap emissions.  If events
        occur more rapidly, the impementation may simply fail
        to trap, or may queue traps until an appropriate time."
    DEFVAL { 0 }
    ::= { frameRelayTrapControl 2 }

frDLCIStatusChange TRAP-TYPE
-- Reverse mappable trap
    ENTERPRISE frameRelayDTE
    VARIABLES {
        frCircuitState }
--  Status
--    mandatory
    DESCRIPTION
        "This trap indicates that the indicated Virtual Circuit
        has changed state.  It has either been created or
        invalidated, or has toggled between the active and
        inactive states.  If, however, the reason for the state
        change is due to the DLCMI going down, per-DLCI traps
        should not be generated."
    ::= 1

frPortGroup OBJECT IDENTIFIER ::= { frGroups 1 }
-- OBJECT-GROUP
--  Status
--    mandatory
--  Descr
--    The objects necessary to control the Link Management
--    Interface for a Frame Relay Interface as well as
--    maintain the error statistics on this interface.
--  objects
--    frDlcmiIfIndex, frDlcmiState, frDlcmiAddress, 
--    frDlcmiAddressLen, frDlcmiPollingInterval, 
--    frDlcmiFullEnquiryInterval, frDlcmiErrorThreshold, 
--    frDlcmiMonitoredEvents, frDlcmiMaxSupportedVCs, 
--    frDlcmiMulticast, frDlcmiStatus, frDlcmiRowStatus

frCircuitGroup OBJECT IDENTIFIER ::= { frGroups 2 }
-- OBJECT-GROUP
--  Status
--    mandatory
--  Descr
--    The objects necessary to control the Virtual Circuits
--    layered onto a Frame Relay Interface.
--  objects
--    frCircuitIfIndex, frCircuitDlci, frCircuitState, 
--    frCircuitReceivedFECNs, frCircuitReceivedBECNs, 
--    frCircuitSentFrames, frCircuitSentOctets, 
--    frCircuitReceivedFrames, frCircuitReceivedOctets, 
--    frCircuitCreationTime, frCircuitLastTimeChange, 
--    frCircuitCommittedBurst, frCircuitExcessBurst, 
--    frCircuitThroughput, frCircuitMulticast, frCircuitType, 
--    frCircuitDiscards, frCircuitReceivedDEs, frCircuitSentDEs, 
--    frCircuitLogicalIfIndex, frCircuitRowStatus

frTrapGroup OBJECT IDENTIFIER ::= { frGroups 3 }
-- OBJECT-GROUP
--  Status
--    mandatory
--  Descr
--    The objects necessary to control a Frame Relay
--    Interface's notification messages.
--  objects
--    frTrapState, frTrapMaxRate

frErrGroup OBJECT IDENTIFIER ::= { frGroups 4 }
-- OBJECT-GROUP
--  Status
--    mandatory
--  Descr
--    Objects designed to assist in debugging Frame Relay
--    Interfaces.
--  objects
--    frErrIfIndex, frErrType, frErrData, frErrTime, frErrFaults, 
--    frErrFaultTime

frPortGroup0 OBJECT IDENTIFIER ::= { frGroups 6 }
-- OBJECT-GROUP
--  Status
--    mandatory
--  Descr
--    The objects necessary to control the Link Management
--    Interface for a Frame Relay Interface as well as
--    maintain the error statistics on this interface from
--    RFC 1315.
--  objects
--    frDlcmiIfIndex, frDlcmiState, frDlcmiAddress, 
--    frDlcmiAddressLen, frDlcmiPollingInterval, 
--    frDlcmiFullEnquiryInterval, frDlcmiErrorThreshold, 
--    frDlcmiMonitoredEvents, frDlcmiMaxSupportedVCs, 
--    frDlcmiMulticast

frCircuitGroup0 OBJECT IDENTIFIER ::= { frGroups 7 }
-- OBJECT-GROUP
--  Status
--    mandatory
--  Descr
--    The objects necessary to control the Virtual Circuits
--    layered onto a Frame Relay Interface from RFC 1315.
--  objects
--    frCircuitIfIndex, frCircuitDlci, frCircuitState, 
--    frCircuitReceivedFECNs, frCircuitReceivedBECNs, 
--    frCircuitSentFrames, frCircuitSentOctets, 
--    frCircuitReceivedFrames, frCircuitReceivedOctets, 
--    frCircuitCreationTime, frCircuitLastTimeChange, 
--    frCircuitCommittedBurst, frCircuitExcessBurst, 
--    frCircuitThroughput

frErrGroup0 OBJECT IDENTIFIER ::= { frGroups 8 }
-- OBJECT-GROUP
--  Status
--    mandatory
--  Descr
--    Objects designed to assist in debugging Frame Relay
--    Interfaces from RFC 1315.
--  objects
--    frErrIfIndex, frErrType, frErrData, frErrTime

frTrapGroup0 OBJECT IDENTIFIER ::= { frGroups 9 }
-- OBJECT-GROUP
--  Status
--    mandatory
--  Descr
--    The objects necessary to control a Frame Relay
--    Interface's notification messages from RFC 1315.
--  objects
--    frTrapState

frNotificationGroup OBJECT IDENTIFIER ::= { frGroups 5 }
-- NOTIFICATION-GROUP
--  Status
--    mandatory
--  Descr
--    Traps which may be used to enhance event driven
--    management of the interface.
--  notifications
--    frDLCIStatusChange

frCompliance OBJECT IDENTIFIER ::= { frCompliances 1 }
-- MODULE-COMPLIANCE
--  Status
--    mandatory
--  Descr
--    The compliance statement 
--  Module
--    >>current<<
--   MandGroup
--    frPortGroup
--   MandGroup
--    frCircuitGroup
--   OptGroup
--    frErrGroup
--   OptGroup
--    frTrapGroup
--   OptGroup
--    frNotificationGroup
--   ObjVar
--    frDlcmiRowStatus
--   ObjVar
--    frCircuitRowStatus

frCompliance0 OBJECT IDENTIFIER ::= { frCompliances 2 }
-- MODULE-COMPLIANCE
--  Status
--    mandatory
--  Descr
--    The compliance statement for objects and the trap
--    defined in RFC 1315.
--  Module
--    >>current<<
--   MandGroup
--    frPortGroup0
--   MandGroup
--    frCircuitGroup0
--   OptGroup
--    frErrGroup0
--   OptGroup
--    frTrapGroup0
--   OptGroup
--    frNotificationGroup


END
