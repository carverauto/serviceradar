-- MIB file created 08-Apr-2013 09:55:20, by
--   SMICng version 2.2.11-beta(PRO)(Solaris), January 20, 2001. Enterprise key cisco.com

CISCO-IF-EXTENSION-MIB DEFINITIONS ::= BEGIN

-- From file: "CISCO-IF-EXTENSION-MIB.my"
-- Compile options "4 7 F H N W 03 06 0B 0G 0N 0T"

IMPORTS
    TruthValue, TimeStamp, DisplayString
            FROM SNMPv2-TC-v1
    ifIndex, InterfaceIndexOrZero, ifName, ifType, ifAdminStatus, 
    ifOperStatus
            FROM IF-MIB
    entPhysicalIndex
            FROM ENTITY-MIB
    SnmpAdminString
            FROM SNMP-FRAMEWORK-MIB
    IfOperStatusReason
            FROM CISCO-TC
    ciscoMgmt
            FROM CISCO-SMI
    Counter, Gauge
            FROM RFC1155-SMI
    OBJECT-TYPE
            FROM RFC-1212
    TRAP-TYPE
            FROM RFC-1215;

ciscoIfExtensionMIB OBJECT IDENTIFIER ::= { ciscoMgmt 276 }
-- MODULE-IDENTITY
--  LastUpdated
--    201303130000Z
--  OrgName
--    Cisco Systems, Inc.
--  ContactInfo
--    Cisco Systems
--    Customer Service
--    
--    Postal: 170 West Tasman Drive
--    San Jose, CA  95134
--    USA
--    
--    Tel: +1 800 553-NETS
--    
--    E-mail: cs-core-mibs@cisco.com,
--    cs-lan-switch-snmp@cisco.com
--  Descr
--    A MIB module for extending the IF-MIB (RFC2863)
--    to add objects which provide additional information
--    about interfaces not available in other MIBS.
--    This MIB replaces the OLD-CISCO-INTERFACES-MIB.
--    
--    GLOSSARY :
--    
--    Virtual Switch - A physical switch partitioned into 
--            multiple logical switches.
--    
--    Interface Sharing - An interface can be shared among 
--            multiple virtual switches.
--    
--    Speed Group - An interface is capable of operating in any one of
--    the speed range depending on the capability of the hardware.
--    
--    Virtual Link (VL) - Virtual Link is a logical connectivity 
--        between two end points. A physical interface can 
--        have multiple Virtual Links.
--    
--    No Drop Virtual Link - According to 802.3 standard, 
--        No drop specifies lossless service on a virtual link.
--    
--    Drop Virtual Link - According to 802.3 standard,
--        Traffic drop may occur on this virtual Link.
--  RevDate
--    201303130000Z
--  RevDescr
--    Added new object cieIfTransceiverFrequencyConfig,
--     cieIfFillPatternConfig, cieIfIgnoreBitErrorsConfig and
--     cieIfIgnoreInterruptThresholdConfig to cieIfInterfaceTable.
--     - Added a new group 
--       ciscoIfExtensionTableIntfGroup3SupR02
--     - Deprecated ciscoIfExtensionMIBCompliance13
--     - Added ciscoIfExtensionMIBCompliance14.
--  RevDate
--    201209050000Z
--  RevDescr
--    Added new object cieLinkUpDownConfig.
--    - Added a new group cieLinkUpDownNotifConfigGroup.
--    - Deprecated cieLinkUpDownEnable.
--    - Deprecated cieStandardLinkUpDownVarbinds.
--    - Deprecated ciscoIfExtensionMIBCompliance13.
--    - Added ciscoIfExtensionMIBCompliance14.
--  RevDate
--    201106270000Z
--  RevDescr
--    Added new object cieIfSharedConfig and
--    cieIfSpeedGroupConfig to cieIfInterfaceTable.
--    Add cieIfVlStatsTable.
--    - Added a new group 
--    ciscoIfExtensionTableIntfGroup3SupR01 and 
--    cieIfVlStatsGroup
--    - Deprecated ciscoIfExtensionMIBCompliance12
--    - Added ciscoIfExtensionMIBCompliance13.
--  RevDate
--    200902260000Z
--  RevDescr
--    Added Textual Convention InterfaceOwnershipList
--    - Added new object cieInterfaceOwnershipBitmap
--    - Added new group cieIfStatusListGroupSup1
--    - Deprecated ciscoIfExtensionMIBCompliance11
--    - Added ciscoIfExtensionMIBCompliance12
--  RevDate
--    200812090000Z
--  RevDescr
--    Added new object cieIfOwner to
--    cieIfInterfaceTable.
--    - Added a new group 
--    ciscoIfExtensionTableIntfGroup3
--    - Deprecated ciscoIfExtensionTableIntfGroup2
--    - Deprecated ciscoIfExtensionMIBCompliance10
--    - Added ciscoIfExtensionMIBCompliance11
--  RevDate
--    200810060000Z
--  RevDescr
--    Added a new textual Convention IfIndexPersistenceState.
--    - Added scalar object cieIfIndexGlobalPersistence to
--      ciscoIfExtSystemConfig. 
--    - Deprecated scalar object cieIfIndexPersistence to
--      ciscoIfExtSystemConfig.
--    - Added a new object cieIfIndexPersistenceControl in 
--      cieIfIndexPersistenceTable.
--    - Deprecated an object cieIfIndexPersistenceEnabled in 
--      cieIfIndexPersistenceTable.
--    - Added a new group cieIfIndexPersistenceControlGroup.
--    - Deprecated the group cieIfIndexPersistenceGroup.
--    - Added ciscoIfExtensionMIBCompliance10
--    - Deprecated ciscoIfExtensionMIBCompliance9
--  RevDate
--    200807310000Z
--  RevDescr
--    Added cieIfOperStatusCause to the objects in the
--    notification cieDelayedLinkUpDownNotif.
--  RevDate
--    200807080000Z
--  RevDescr
--    Added notification cieDelayedLinkUpDownNotif
--    - Added scalar objects cieDelayedLinkUpDownNotifEnable and 
--      cieDelayedLinkUpDownNotifDelay to ciscoIfExtSystemConfig.
--    - Added the following groups:
--              cieDelayedLinkUpDownNotifNotifGroup
--              cieDelayedLinkUpDownNotifNotifEnableGroup
--    - Deprecated ciscoIfExtensionMIBCompliance7
--    - Added ciscoIfExtensionMIBCompliance8.
--  RevDate
--    200806230000Z
--  RevDescr
--    Added scalar object cieIfIndexPersistence to
--    ciscoIfExtSystemConfig.
--    - Added a new Table cieIfIndexPersistenceTable. 
--    - Added a new object cieIfIndexPersistenceEnabled in 
--    cieIfIndexPersistenceTable.
--    - Added a new group cieIfIndexPersistenceGroup.
--    - Deprecated ciscoIfExtensionMIBCompliance7
--    - Added ciscoIfExtensionMIBCompliance8
--  RevDate
--    200707230000Z
--  RevDescr
--    Added cieIfInterval in cieIfUtilTable. Changed
--    the description of objects in cieIfUtilTable.
--    Added ciscoIfExtUtilIntervalGroup.
--  RevDate
--    200611010000Z
--  RevDescr
--    Add support for asymetrical interfaces speeds.
--    
--    - Added following objects in cieIfInterfaceTable 
--      cieIfSpeedReceive 
--      cieIfHighSpeedReceive 
--    - Added ciscoIfExtensionAsymmetricalSpeedGroup OBJECT-GROUP 
--    - Added ciscoIfExtensionMIBCompliance6 MODULE-COMPLIANCE
--  RevDate
--    200504280000Z
--  RevDescr
--    Added:
--    - cieLinkUp & cieLinkDown notifications.
--    - object to control sending: only standard 
--      linkUp/linkDown OR only cieLinkUp/cieLinkDown
--      OR both.
--    - object to control sending only standard defined
--      varbinds in linkUp/linkDown OR additional varbinds
--      in addition to standard defined.
--  RevDate
--    200501250000Z
--  RevDescr
--    Updated the description of cieIfDot1dBaseMappingEntry.
--  RevDate
--    200409080000Z
--  RevDescr
--    Added new objects 'cieIfOperStatusCause' and
--    'cieIfOperStatusCauseDescr' in cieIfInterfaceTable.
--    Added a new table 'cieIfStatusListTable'.
--  RevDate
--    200311140000Z
--  RevDescr
--    Added new objects cieIfName and cieIfIndex for the
--    'ifName' to 'ifIndex' mapping.  Deprecated the
--    ciscoIfExtensionMIBCompliance2 compliance.
--    Added ciscoIfExtensionMIBCompliance3 and
--    ciscoIfExtIfNameMappingGroup.
--  RevDate
--    200308120000Z
--  RevDescr
--    Added ciscoIfExtDot1dBaseMappingGroup.
--  RevDate
--    200307170000Z
--  RevDescr
--    Added ciscoIfExtUtilizationGroup.
--  RevDate
--    200306250000Z
--  RevDescr
--    Added the object cieSystemMtu and
--    ciscoIfExtSystemGroup.
--    Added ciscoIfExtDot1qCustomEtherType and
--    ciscoIfExtDot1qEtherTypeGroup.
--  RevDate
--    200210120000Z
--  RevDescr
--    Added the objects cieIfDhcpMode, cieIfMtu,
--    cieIfContextName to cieIfInterfaceTable.
--    Deprecated the ciscoIfExtensionMIBCompliance
--    compliance.  Added ciscoIfExtensionMIBCompliance1.
--    Added ciscoIfExtensionTableIntfGroup1.
--  RevDate
--    200207240000Z
--  RevDescr
--    Initial version of the MIB module.

ciscoIfExtensionMIBNotifications OBJECT IDENTIFIER ::= { ciscoIfExtensionMIB 0 }
ciscoIfExtensionMIBObjects OBJECT IDENTIFIER ::= { ciscoIfExtensionMIB 1 }
ciscoIfExtensionMIBConformance OBJECT IDENTIFIER ::= { ciscoIfExtensionMIB 2 }
ciscoIfExtensionStats OBJECT IDENTIFIER ::= { ciscoIfExtensionMIBObjects 1 }
ciscoIfExtSystemConfig OBJECT IDENTIFIER ::= { ciscoIfExtensionMIBObjects 2 }
ciscoIfExtDot1qCustomEtherType OBJECT IDENTIFIER ::= { ciscoIfExtensionMIBObjects 3 }
ciscoIfExtUtilization OBJECT IDENTIFIER ::= { ciscoIfExtensionMIBObjects 4 }
ciscoIfExtDot1dBaseMapping OBJECT IDENTIFIER ::= { ciscoIfExtensionMIBObjects 5 }
ciscoIfExtIfNameMapping OBJECT IDENTIFIER ::= { ciscoIfExtensionMIBObjects 6 }
ciscoIfExtensionMIBCompliances OBJECT IDENTIFIER ::= { ciscoIfExtensionMIBConformance 1 }
ciscoIfExtensionMIBGroups OBJECT IDENTIFIER ::= { ciscoIfExtensionMIBConformance 2 }

InterfaceIndexList ::= OCTET STRING(SIZE(0..256))
-- TEXTUAL-CONVENTION
--  Status
--    mandatory
--  Descr
--    This textual convention defines the 'ifIndex' for a
--    set of 64 interfaces in a module.
--    
--    Each 4 bytes within the value of an object of this
--    type is combined together to represent the interface
--    index of a particular port in the module (i.e., each
--    4 byte group represents the 'ifIndex' of an interface).
--    
--    The first 4 bytes (byte 1, byte 2, byte 3 and byte 4)
--    combined represent the 'ifIndex' of an interface.
--    While the second 4 bytes (byte 5, byte 6, byte 7 and
--    byte 8) represent the 'ifIndex' for the next interface
--    in the module, and so on.
--    
--    If there are only 'n' interfaces in a set of 64
--    interfaces in the module, then bytes after the '4n'
--    byte in this object are irrelevant.

InterfaceOperModeList ::= OCTET STRING(SIZE(0..64))
-- TEXTUAL-CONVENTION
--  Status
--    mandatory
--  Descr
--    This textual convention defines the operational mode
--    for a set of 64 interfaces in a module.
--    
--    The operational mode of an interface is represented
--    by the value defined in the textual convention
--    'InterfaceOperMode' (defined in CISCO-ST-TC).
--    
--    Each 'byte' within the value of an object of this
--    type, specifies the operational mode of an interface
--    in the module.
--    
--    The first byte (byte 1) represents the operational
--    mode of an interface in the module, whose 'ifIndex'
--    is represented by the corresponding instance of
--    'cieInterfacesIndex' object in its first 4 bytes.
--    
--    The second byte (byte 2) represents the operational
--    mode of an interface in the module, whose 'ifIndex'
--    is represented by the corresponding instance of
--    'cieInterfacesIndex' object in its second 4 bytes.
--    
--    If there are only 'n' interfaces in a set of 64
--    interfaces in the module, then bytes after the 'n'
--    byte in this object are irrelevant.

InterfaceOperCauseList ::= OCTET STRING(SIZE(0..128))
-- TEXTUAL-CONVENTION
--  Status
--    mandatory
--  Descr
--    This textual convention defines the operational
--    status cause for a set of 64 interfaces in a module.
--    
--    The operational status cause of an interface is
--    represented by the value defined in the textual
--    convention 'IfOperStatusReason' (defined in CISCO-TC).
--    
--    Each 2 bytes within the value of an object of this
--    type is combined together to represent the operational
--    status cause of a particular interface in the module
--    (i.e., each 2 byte group represents the
--    'cieIfOperStatusCause' of an interface).
--    
--    The first 2 bytes (byte 1 and byte 2) of this object,
--    represents the operational status cause of an
--    interface in the module, whose 'ifIndex' is
--    represented by the corresponding instance of
--    'cieInterfacesIndex' object in its first 4 bytes.
--    
--    The next 2 bytes (byte 3 and byte 4) of this object,
--    represents the operational status cause of an
--    interface in the module, whose 'ifIndex' is
--    represented by the corresponding instance of
--    'cieInterfacesIndex' object in the next 4 bytes
--    respectively.
--    
--    If there are only 'n' interfaces in a set of 64
--    interfaces in the module, then bytes after the
--    '2n' byte in this object are irrelevant.

InterfaceOwnershipList ::= OCTET STRING(SIZE(0..8))
-- TEXTUAL-CONVENTION
--  Status
--    mandatory
--  Descr
--    This textual convention defines the status for a set of
--    64 interfaces in a module regarding whether or not each 
--    interface is administratively assigned a name of the current 
--    owner of the interface resource as per the object cieIfOwner,
--    defined on that interface. 
--    
--    Each 'bit' within the value of an object of this type, 
--    specifies whether the corresponding interface on the module 
--    has been administratively assigned a name of the current
--    owner of the interface resource. In other words, each bit 
--    represents whether the corresponding interface is 'owned' 
--    or not. This bit is set to 1 if the interface is owned. 
--    It is 0 otherwise.
--    
--    The first bit (bit 1) in byte 1 represents whether the 
--    interface, whose 'ifIndex' is represented by the corresponding 
--    instance of 'cieInterfacesIndex' object in its first 4 bytes, 
--    is owned or not.
--    
--    The second byte (byte 2) in byte 2 represents whether the 
--    interface, whose 'ifIndex' is represented by the corresponding 
--    instance of 'cieInterfacesIndex' object in its second 4 bytes, 
--    is owned or not.
--    
--    If there are only 'n' interfaces in a set of 64 interfaces in 
--    the module, then bits after the 'n' bit in this object are 
--    irrelevant and set to 0.

IfIndexPersistenceState ::= INTEGER {
        disable(1),
        enable(2),
        global(3)
        }
-- TEXTUAL-CONVENTION
--  Status
--    mandatory
--  Descr
--    This textual convention is used to define the state of ifIndex
--    Persistence for both global as well as interface level.
--    
--    The global object, cieIfIndexGlobalPersistence can have two
--    state of ifIndex Persistence i.e. either enable or disable. At
--    interface level, the object cieIfIndexPersistenceControl can
--    take all the three values enable/disable/global.

cieIfPacketStatsTable OBJECT-TYPE
    SYNTAX SEQUENCE OF CieIfPacketStatsEntry
    ACCESS not-accessible
    STATUS mandatory
    DESCRIPTION
        "This  table contains interface packet
        statistics which are not available in 
        IF-MIB(RFC2863). 
        
        As an example, some interfaces to which
        objects in this table are applicable are
        as follows :
        
                o Ethernet
                o FastEthernet
                o ATM
                o BRI
                o Sonet
                o GigabitEthernet
        
        Some objects defined in this table may be 
        applicable to physical interfaces only.
        As a result, this table may be sparse for
        some logical interfaces."
    ::= { ciscoIfExtensionStats 1 }

cieIfPacketStatsEntry OBJECT-TYPE
    SYNTAX CieIfPacketStatsEntry
    ACCESS not-accessible
    STATUS mandatory
    DESCRIPTION
        "An entry into the cieIfPacketStatsTable."
    INDEX { ifIndex }
    ::= { cieIfPacketStatsTable 1 }

CieIfPacketStatsEntry ::= SEQUENCE {
    cieIfLastInTime Gauge,
    cieIfLastOutTime Gauge,
    cieIfLastOutHangTime Gauge,
    cieIfInRuntsErrs Counter,
    cieIfInGiantsErrs Counter,
    cieIfInFramingErrs Counter,
    cieIfInOverrunErrs Counter,
    cieIfInIgnored Counter,
    cieIfInAbortErrs Counter,
    cieIfInputQueueDrops Counter,
    cieIfOutputQueueDrops Counter,
    cieIfPacketDiscontinuityTime TimeStamp
    }

cieIfLastInTime OBJECT-TYPE
    SYNTAX Gauge
--  Units
--    milliseconds
    ACCESS read-only
    STATUS mandatory
    DESCRIPTION
        "This object represents the elapsed time in
        milliseconds since last protocol input 
        packet was received.
        
        Discontinuities in the value of this variable
        can occur at re-initialization of the
        management system, and at other times as 
        indicated by the values of 
        cieIfPacketDiscontinuityTime."
    ::= { cieIfPacketStatsEntry 1 }

cieIfLastOutTime OBJECT-TYPE
    SYNTAX Gauge
--  Units
--    milliseconds
    ACCESS read-only
    STATUS mandatory
    DESCRIPTION
        "This object represents the elapsed time in
        milliseconds since last protocol  output 
        packet was transmitted.
        
        Discontinuities in the value of this variable
        can occur at re-initialization of the
        management system, and at other times as 
        indicated by the values of 
        cieIfPacketDiscontinuityTime."
    ::= { cieIfPacketStatsEntry 2 }

cieIfLastOutHangTime OBJECT-TYPE
    SYNTAX Gauge
--  Units
--    milliseconds
    ACCESS read-only
    STATUS mandatory
    DESCRIPTION
        "This object represents the elapsed time in
        milliseconds since last protocol    output
        packet could not be successfully transmitted.
        
        Discontinuities in the value of this variable
        can occur at re-initialization of the
        management system, and at other times as 
        indicated by the values of 
        cieIfPacketDiscontinuityTime."
    ::= { cieIfPacketStatsEntry 3 }

cieIfInRuntsErrs OBJECT-TYPE
    SYNTAX Counter
    ACCESS read-only
    STATUS mandatory
    DESCRIPTION
        "The number of packets input on a particular
        physical interface which were dropped as
        they were smaller than the minimum allowable 
        physical media limit.
        
        Discontinuities in the value of this variable
        can occur at re-initialization of the
        management system, and at other times as 
        indicated by the values of 
        cieIfPacketDiscontinuityTime."
    ::= { cieIfPacketStatsEntry 4 }

cieIfInGiantsErrs OBJECT-TYPE
    SYNTAX Counter
    ACCESS read-only
    STATUS mandatory
    DESCRIPTION
        "The number of input packets on a particular
        physical interface which were dropped as 
        they were larger than the ifMtu (largest 
        permitted  size of a packet which can be 
        sent/received on an interface).
        
        Discontinuities in the value of this variable
        can occur at re-initialization of the
        management system, and at other times as 
        indicated by the values of 
        cieIfPacketDiscontinuityTime."
    ::= { cieIfPacketStatsEntry 5 }

cieIfInFramingErrs OBJECT-TYPE
    SYNTAX Counter
    ACCESS read-only
    STATUS mandatory
    DESCRIPTION
        "The number of input packets on a physical
        interface which were misaligned or had
        framing errors. This happens when the 
        format of the incoming packet on a physical
        interface is incorrect.
        
        Discontinuities in the value of this variable
        can occur at re-initialization of the
        management system, and at other times as 
        indicated by the values of 
        cieIfPacketDiscontinuityTime."
    ::= { cieIfPacketStatsEntry 6 }

cieIfInOverrunErrs OBJECT-TYPE
    SYNTAX Counter
    ACCESS read-only
    STATUS mandatory
    DESCRIPTION
        "The number of input packets which arrived
        on a particular physical interface which 
        were too quick for the hardware to receive
        and hence the receiver ran out of buffers.
        
        Discontinuities in the value of this variable
        can occur at re-initialization of the
        management system, and at other times as 
        indicated by the values of 
        cieIfPacketDiscontinuityTime."
    ::= { cieIfPacketStatsEntry 7 }

cieIfInIgnored OBJECT-TYPE
    SYNTAX Counter
    ACCESS read-only
    STATUS mandatory
    DESCRIPTION
        "The number of input packets which were simply
        ignored by this physical interface due to 
        insufficient resources to handle the incoming
        packets.
        
        For example, this could indicate that the input
        receive buffers are not available or that the
        receiver lost a packet.
        
        Discontinuities in the value of this variable
        can occur at re-initialization of the
        management system, and at other times as 
        indicated by the values of 
        cieIfPacketDiscontinuityTime."
    ::= { cieIfPacketStatsEntry 8 }

cieIfInAbortErrs OBJECT-TYPE
    SYNTAX Counter
    ACCESS read-only
    STATUS mandatory
    DESCRIPTION
        "Number of input packets which were dropped
        because the receiver aborted.
        
        Examples of this could be when an abort
        sequence aborted the input frame or when
        there is a collision in an ethernet segment.
        
        Discontinuities in the value of this variable
        can occur at re-initialization of the
        management system, and at other times as 
        indicated by the values of 
        cieIfPacketDiscontinuityTime."
    ::= { cieIfPacketStatsEntry 9 }

cieIfInputQueueDrops OBJECT-TYPE
    SYNTAX Counter
    ACCESS read-only
    STATUS mandatory
    DESCRIPTION
        "The number of input packets which were
        dropped.
        
        Some reasons why this object could be 
        incremented are:
        
        o  Input queue is full.
        o  Errors at the receiver hardware 
           while receiving the packet.
        
        Discontinuities in the value of this variable
        can occur at re-initialization of the
        management system, and at other times as 
        indicated by the values of 
        cieIfPacketDiscontinuityTime."
    ::= { cieIfPacketStatsEntry 10 }

cieIfOutputQueueDrops OBJECT-TYPE
    SYNTAX Counter
    ACCESS read-only
    STATUS mandatory
    DESCRIPTION
        "This object indicates the  number of output
        packets dropped by the interface even though
        no error had been detected to prevent them
        being transmitted. 
        
        The packet could be dropped for many reasons,
        which could range from the interface being
        down to errors in the format of the packet.
        
        Discontinuities in the value of this variable
        can occur at re-initialization of the
        management system, and at other times as 
        indicated by the values of 
        cieIfPacketDiscontinuityTime."
    ::= { cieIfPacketStatsEntry 11 }

cieIfPacketDiscontinuityTime OBJECT-TYPE
    SYNTAX TimeStamp
--    Rsyntax TimeTicks
    ACCESS read-only
    STATUS mandatory
    DESCRIPTION
        "The value of sysUpTime on the most recent
        occasion at which this interface's  counters
        suffered a discontinuity. 
        
        If no such discontinuities have occurred 
        since the last re-initialization of the 
        local management subsystem, then this 
        object contains a value of zero."
    ::= { cieIfPacketStatsEntry 12 }

cieIfInterfaceTable OBJECT-TYPE
    SYNTAX SEQUENCE OF CieIfInterfaceEntry
    ACCESS not-accessible
    STATUS mandatory
    DESCRIPTION
        "This  table contains objects which provide
        more information about interface  
        properties not available in IF-MIB
        (RFC 2863).
        
        Some objects defined in this table may be
        applicable to physical interfaces only.
        As a result, this table may be sparse for
        logical interfaces."
    ::= { ciscoIfExtensionStats 2 }

cieIfInterfaceEntry OBJECT-TYPE
    SYNTAX CieIfInterfaceEntry
    ACCESS not-accessible
    STATUS mandatory
    DESCRIPTION
        "An entry into the cieIfInterfaceTable."
    INDEX { ifIndex }
    ::= { cieIfInterfaceTable 1 }

CieIfInterfaceEntry ::= SEQUENCE {
    cieIfResetCount Counter,
    cieIfKeepAliveEnabled TruthValue,
    cieIfStateChangeReason SnmpAdminString,
    cieIfCarrierTransitionCount Counter,
    cieIfInterfaceDiscontinuityTime TimeStamp,
    cieIfDhcpMode TruthValue,
    cieIfMtu INTEGER,
    cieIfContextName OCTET STRING,
    cieIfOperStatusCause IfOperStatusReason,
    cieIfOperStatusCauseDescr SnmpAdminString,
    cieIfSpeedReceive Gauge,
    cieIfHighSpeedReceive Gauge,
    cieIfOwner DisplayString,
    cieIfSharedConfig INTEGER,
    cieIfSpeedGroupConfig INTEGER,
    cieIfTransceiverFrequencyConfig INTEGER,
    cieIfFillPatternConfig INTEGER,
    cieIfIgnoreBitErrorsConfig TruthValue,
    cieIfIgnoreInterruptThresholdConfig TruthValue
    }

cieIfResetCount OBJECT-TYPE
    SYNTAX Counter
    ACCESS read-only
    STATUS mandatory
    DESCRIPTION
        "The number of times the interface was
        internally reset and brought up.
        
        Some of the actions which can cause this
        counter to increment are :
        
        o  Bringing an interface up using the 
           interface CLI command.
        
        o  Clearing the interface with the exec
           CLI command.
        
        o  Bringing the interface up via SNMP.
        
        Discontinuities in the value of this variable
        can occur at re-initialization of the
        management system, and at other times as 
        indicated by the values of 
        cieIfInterfaceDiscontinuityTime."
    ::= { cieIfInterfaceEntry 1 }

cieIfKeepAliveEnabled OBJECT-TYPE
    SYNTAX TruthValue
--    Rsyntax INTEGER {
--        true(1),
--        false(2)
--        }
    ACCESS read-write
    STATUS mandatory
    DESCRIPTION
        "A keepalive is a small, layer-2 message
        that is transmitted by a network device 
        to let directly-connected network devices
        know of its presence.
        
        This object returns 'true' if keepalives
        are enabled on this interface. If keepalives
        are not enabled, 'false' is returned.
        
        Setting this object to TRUE or FALSE enables
        or disables (respectively) keepalive on this 
        interface."
    ::= { cieIfInterfaceEntry 2 }

cieIfStateChangeReason OBJECT-TYPE
    SYNTAX SnmpAdminString
--    Rsyntax OCTET STRING(SIZE(0..255))
    ACCESS read-only
    STATUS mandatory
    DESCRIPTION
        "This object displays a human-readable
        textual string which describes the 
        cause of the last state change of the 
        interface.
        
        Examples of the values this object
        can take are:
        
        o  'Lost Carrier'
        o  'administratively down'
        o  'up'
        o  'down'"
    ::= { cieIfInterfaceEntry 3 }

cieIfCarrierTransitionCount OBJECT-TYPE
    SYNTAX Counter
    ACCESS read-only
    STATUS mandatory
    DESCRIPTION
        "Number of times interface saw the carrier
        signal transition.
        
        For example, if a T1 line is unplugged, 
        then framer will detect the loss of signal 
        (LOS) on the line  and will count it as a
        transition.
        
        Discontinuities in the value of this variable
        can occur at re-initialization of the
        management system, and at other times as 
        indicated by the values of 
        cieIfInterfaceDiscontinuityTime."
    ::= { cieIfInterfaceEntry 4 }

cieIfInterfaceDiscontinuityTime OBJECT-TYPE
    SYNTAX TimeStamp
--    Rsyntax TimeTicks
    ACCESS read-only
    STATUS mandatory
    DESCRIPTION
        "The value of sysUpTime on the most recent
        occasion at which this interface's  counters 
        suffered  a discontinuity. 
        
        If no such discontinuities have occurred 
        since the last re-initialization of the 
        local management subsystem, then this 
        object contains a value of zero."
    ::= { cieIfInterfaceEntry 5 }

cieIfDhcpMode OBJECT-TYPE
    SYNTAX TruthValue
--    Rsyntax INTEGER {
--        true(1),
--        false(2)
--        }
    ACCESS read-write
    STATUS mandatory
    DESCRIPTION
        "The DHCP mode configured by the
        administrator.
        If 'true' the DHCP is enabled. In which
        case an IP address is requested in DHCP.
        This is in addition to any that are 
        configured by the administrator in
        'ciiIPAddressTable' or 'ciiIPIfAddressTable'
        in CISCO-IP-IF-MIB.
        If 'false' the DHCP is disabled. In which
        case all IP addresses are configured by the
        administrator in 'ciiIPAddressTable' or 
        'ciiIPIfAddressTable'.
        For interfaces, for which DHCP cannot be or
        is not supported, then this object has the
        value 'false'."
    DEFVAL { false }
    ::= { cieIfInterfaceEntry 6 }

cieIfMtu OBJECT-TYPE
    SYNTAX INTEGER(40..2147483647)
    ACCESS read-write
    STATUS mandatory
    DESCRIPTION
        "The MTU configured by the administrator.
        This object is exactly same as 'ifMtu' in 
        ifTable from IF-MIB for the same ifIndex
        value , except that it is configurable by the
        administrator. For more description of this
        object refer to 'ifMtu' in IF-MIB."
    DEFVAL { 1500 }
    ::= { cieIfInterfaceEntry 7 }

cieIfContextName OBJECT-TYPE
    SYNTAX OCTET STRING(SIZE(0..32))
    ACCESS read-only
    STATUS mandatory
    DESCRIPTION
        "The ContextName denotes the interface
        'context' and is used to logically separate
        the MIB management.
        RFC 2571 and RFC 2737 describe this approach.
        When the agent supports a different SNMP 
        context, as detailed in RFC 2571 and 
        RFC 2737, for different interfaces, then the
        value of this object specifies the context
        name used for this interface."
    DEFVAL { "" }
    ::= { cieIfInterfaceEntry 8 }

cieIfOperStatusCause OBJECT-TYPE
    SYNTAX IfOperStatusReason
--    Rsyntax INTEGER {
--        other(1),
--        none(2),
--        hwFailure(3),
--        loopbackDiagFailure(4),
--        errorDisabled(5),
--        swFailure(6),
--        linkFailure(7),
--        offline(8),
--        nonParticipating(9),
--        initializing(10),
--        vsanInactive(11),
--        adminDown(12),
--        channelAdminDown(13),
--        channelOperSuspended(14),
--        channelConfigurationInProgress(15),
--        rcfInProgress(16),
--        elpFailureIsolation(17),
--        escFailureIsolation(18),
--        domainOverlapIsolation(19),
--        domainAddrAssignFailureIsolation(20),
--        domainOtherSideEportIsolation(21),
--        domainInvalidRcfReceived(22),
--        domainManagerDisabled(23),
--        zoneMergeFailureIsolation(24),
--        vsanMismatchIsolation(25),
--        parentDown(26),
--        srcPortNotBound(27),
--        interfaceRemoved(28),
--        fcotNotPresent(29),
--        fcotVendorNotSupported(30),
--        incompatibleAdminMode(31),
--        incompatibleAdminSpeed(32),
--        suspendedByMode(33),
--        suspendedBySpeed(34),
--        suspendedByWWN(35),
--        domainMaxReTxFailure(36),
--        eppFailure(37),
--        portVsanMismatchIsolation(38),
--        loopbackIsolation(39),
--        upgradeInProgress(40),
--        incompatibleAdminRxBbCredit(41),
--        incompatibleAdminRxBufferSize(42),
--        portChannelMembersDown(43),
--        zoneRemoteNoRespIsolation(44),
--        firstPortUpAsEport(45),
--        firstPortNotUp(46),
--        peerFCIPPortClosedConnection(47),
--        peerFCIPPortResetConnection(48),
--        fcipPortMaxReTx(49),
--        fcipPortKeepAliveTimerExpire(50),
--        fcipPortPersistTimerExpire(51),
--        fcipPortSrcLinkDown(52),
--        fcipPortSrcAdminDown(53),
--        fcipPortAdminCfgChange(54),
--        fcipSrcPortRemoved(55),
--        fcipSrcModuleNotOnline(56),
--        invalidConfig(57),
--        portBindFailure(58),
--        portFabricBindFailure(59),
--        noCommonVsanIsolation(60),
--        ficonVsanDown(61),
--        invalidAttachment(62),
--        portBlocked(63),
--        incomAdminRxBbCreditPerBuf(64),
--        tooManyInvalidFlogis(65),
--        deniedDueToPortBinding(66),
--        elpFailureRevMismatch(67),
--        elpFailureClassFParamErr(68),
--        elpFailureClassNParamErr(69),
--        elpFailureUnknownFlowCtlCode(70),
--        elpFailureInvalidFlowCtlParam(71),
--        elpFailureInvalidPortName(72),
--        elpFailureInvalidSwitchName(73),
--        elpFailureRatovEdtovMismatch(74),
--        elpFailureLoopbackDetected(75),
--        elpFailureInvalidTxBbCredit(76),
--        elpFailureInvalidPayloadSize(77),
--        bundleMisCfg(78),
--        bitErrRuntimeThreshExceeded(79),
--        linkFailLinkReset(80),
--        linkFailPortInitFail(81),
--        linkFailPortUnusable(82),
--        linkFailLossOfSignal(83),
--        linkFailLossOfSync(84),
--        linkFailNosRcvd(85),
--        linkFailOLSRcvd(86),
--        linkFailDebounceTimeout(87),
--        linkFailLrRcvd(88),
--        linkFailCreditLoss(89),
--        linkFailRxQOverflow(90),
--        linkFailTooManyInterrupts(91),
--        linkFailLipRcvdBb(92),
--        linkFailBbCreditLoss(93),
--        linkFailOpenPrimSignalTimeout(94),
--        linkFailOpenPrimSignalReturned(95),
--        linkFailLipF8Rcvd(96),
--        linkFailLineCardPortShutdown(97),
--        fcspAuthenfailure(98),
--        fcotChecksumError(99),
--        ohmsExtLoopbackTest(100),
--        invalidFabricBindExchange(101),
--        tovMismatch(102),
--        ficonNotEnabled(103),
--        ficonNoPortNumber(104),
--        ficonBeingEnabled(105),
--        ePortProhibited(106),
--        portGracefulShutdown(107),
--        trunkNotFullyActive(108),
--        fabricBindingSwitchWwnNotFound(109),
--        fabricBindingDomainInvalid(110),
--        fabricBindingDbMismatch(111),
--        fabricBindingNoRspFromPeer(112),
--        dpvmVsanSuspended(113),
--        dpvmVsanNotFound(114),
--        trackedPortDown(115),
--        ecSuspendedOnLoop(116),
--        isolateBundleMisCfg(117),
--        noPeerBundleSupport(118),
--        portBringupIsolation(119),
--        domainNotAllowedIsolated(120),
--        virtualIvrDomainOverlapIsolation(121),
--        outOfService(122),
--        portAuthFailed(123),
--        bundleStandby(124),
--        portConnectorTypeErr(125),
--        errorDisabledReInitLmtReached(126),
--        ficonDupPortNum(127),
--        localRcf(128),
--        twoSwitchesWithSameWWN(129),
--        invalidOtherSidePrincEFPReqRecd(130),
--        domainOther(131),
--        elpFailureAllZeroPeerWWNRcvd(132),
--        preferredPathIsolation(133),
--        fcRedirectIsolation(134),
--        portActLicenseNotAvailable(135),
--        sdmIsolation(136),
--        fcidAllocationFailed(137),
--        externallyDisabled(138),
--        unavailableNPVUpstreamPort(139),
--        unavailableNPVPrefUpstreamPort(140),
--        sfpReadError(141),
--        stickyDownOnLinkFailure(142),
--        tooManyLinkFlapsErr(143),
--        unidirectionalUDLD(144),
--        txRxLoopUDLD(145),
--        neighborMismatchUDLD(146),
--        authzPending(147),
--        hotStdbyInBundle(148),
--        incompleteConfig(149),
--        incompleteTunnelCfg(150),
--        hwProgrammingFailed(151),
--        tunnelDstUnreachable(152),
--        suspendByMtu(153),
--        sfpInvalid(154),
--        sfpAbsent(155),
--        portCapabilitiesUnknown(156),
--        channelErrDisabled(157),
--        vrfMismatch(158),
--        vrfForwardReferencing(159),
--        dupTunnelConfigDetected(160),
--        primaryVLANDown(161),
--        vrfUnusable(162),
--        errDisableHandShkFailure(163),
--        errDisabledBPDUGuard(164),
--        dot1xSecViolationErrDisabled(165),
--        emptyEchoUDLD(166),
--        vfTaggingCapErr(167),
--        portDisabled(168),
--        tunnelModeNotConfigured(169),
--        tunnelSrcNotConfigured(170),
--        tunnelDstNotConfigured(171),
--        tunnelUnableToResolveSrcIP(172),
--        tunnelUnableToResolveDstIP(173),
--        tunnelVrfDown(174),
--        sifAdminDown(175),
--        phyIntfDown(176),
--        ifSifLimitExceeded(177),
--        sifHoldDown(178),
--        noFcoe(179),
--        dcxCompatMismatch(180),
--        isolateBundleLimitExceeded(181),
--        sifNotBound(182),
--        errDisabledLacpMiscfg(183),
--        satFabricIfDown(184),
--        invalidSatFabricIf(185),
--        noRemoteChassis(186),
--        vicEnableNotReceived(187),
--        vicDisableReceived(188),
--        vlanVsanMappingNotEnabled(189),
--        stpNotFwdingInFcoeMappedVlan(190),
--        moduleOffline(191),
--        udldAggModeLinkFailure(192),
--        stpInconsVpcPeerDisabled(193),
--        setPortStateFailed(194),
--        suspendedByVpc(195),
--        vpcCfgInProgress(196),
--        vpcPeerLinkDown(197),
--        vpcNoRspFromPeer(198),
--        protoPortSuspend(199),
--        tunnelSrcDown(200),
--        cdpInfoUnavailable(201),
--        fexSfpInvalid(202),
--        errDisabledIpConflict(203),
--        fcotClkRateMismatch(204),
--        portGuardTrustSecViolation(205),
--        sdpTimeout(206),
--        satIncompatTopo(207),
--        waitForFlogi(208),
--        satNotConfigured(209),
--        npivNotEnabledInUpstream(210),
--        vsanMismatchWithUpstreamSwPort(211),
--        portGuardBitErrRate(212),
--        portGuardSigLoss(213),
--        portGuardSyncLoss(214),
--        portGuardLinkReset(215),
--        portGuardCreditLoss(216),
--        ipQosMgrPolicyAppFailure(217),
--        pauseRateLimitErrDisabled(218),
--        lstGrpUplinkDown(219),
--        stickyDnLinkFailure(220),
--        routerMacFailure(221),
--        dcxMultipleMsapIds(222),
--        dcxHundredPdusRcvdNoAck(223),
--        enmSatIncompatibleUplink(224),
--        enmLoopDetected(225),
--        nonStickyExternallyDisabled(226),
--        subGroupIdNotAssigned(227),
--        vemUnlicensed(228),
--        profileNotFound(229),
--        nonExistentVlan(230),
--        vlanInvalidType(231),
--        vlanDown(232),
--        vpcPeerUpgrade(233),
--        ipQosDcbxpCompatFailure(234),
--        nonCiscoHbaVfTag(235),
--        domainIdConfigMismatch(236),
--        sfpSpeedMismatch(237),
--        xcvrInitializing(238),
--        xcvrAbsent(239),
--        xcvrInvalid(240),
--        vfcBindingInvalid(241),
--        vlanNotFcoeEnabled(242),
--        pvlanNativeVlanErr(243),
--        ethL2VlanDown(244),
--        ethIntfInvalidBinding(245),
--        pmonFailure(246),
--        l3NotReady(247),
--        speedMismatch(248),
--        flowControlMismatch(249),
--        vdcMode(250),
--        suspendedDueToMinLinks(251),
--        enmPinFailLinkDown(252),
--        inactiveM1PortFpathActiveVlan(253),
--        parentPortDown(254),
--        moduleRemoved(255),
--        corePortMct(256),
--        nonCorePortMct(257),
--        ficonInorderNotActive(258),
--        invalidEncapsulation(259),
--        modemLineDeasserted(260),
--        ipSecHndshkInProgress(261),
--        sfpEthCompliantErr(262),
--        cellularModemUnattached(263),
--        outOfGlblRxBuffers(264),
--        sfpFcCompliantErr(265),
--        ethIntfNotLicensed(266),
--        domainIdsInvalid(267),
--        fabricNameInvalid(268),
--        ficonNoPortSwapLogicalPort(269),
--        ficonInvalidPortNum(270),
--        remotePortInL2vpnDown(271),
--        suspendedDueToNoLacpPdus(272),
--        fcotValidationFailedAtDriver(273),
--        unsupportedTransceiverMd5DigestNotSame(274),
--        unsupportedTransceiver(275),
--        adminStateConfigChange(276),
--        vlanAllowedList(277),
--        vlanAllowedListOverride(278),
--        vlanAllowedListAdd(279),
--        vlanAllowedRemove(280),
--        vlanCfgStateChange(281),
--        vlanCfgDelete(282),
--        pppPeerNotResponding(283),
--        pppAuthFailed(284),
--        xcvrAuthFailed(285),
--        badFramesRcvdFromLink(286)
--        }
    ACCESS read-only
    STATUS mandatory
    DESCRIPTION
        "This object represents the detailed
        operational cause reason for the current 
        operational state of the interface. 
        The current operational state of the interface 
        is given by the 'ifOperStatus' defined 
        in IF-MIB. 
        
        The corresponding instance of 
        'cieIfOperStatusCauseDescr' must be used to 
        get the information about the operational 
        cause value mentioned in this object.
        
        For interfaces whose 'ifOperStatus' is 'down' 
        the objects 'cieIfOperStatusCause' and 
        'cieIfOperStatusCauseDescr' together provides 
        the information about the operational cause 
        reason and the description of the cause. 
        
        The value of this object will be 'none' for
        all the 'ifOperStatus' values except for 
        'down'. Its value will be one status cause 
        defined in the 'IfOperStatusReason' textual 
        convention if 'ifOperStatus' is 'down'. 
        
        The value of this object will be 'other' 
        if the operational status cause is not one 
        defined in 'IfOperStatusReason'."
    ::= { cieIfInterfaceEntry 9 }

cieIfOperStatusCauseDescr OBJECT-TYPE
    SYNTAX SnmpAdminString
--    Rsyntax OCTET STRING(SIZE(0..255))
    ACCESS read-only
    STATUS mandatory
    DESCRIPTION
        "The description for the cause of current
        operational state of the interface, given 
        by the object 'cieIfOperStatusCause'.
        
        For an interface whose 'ifOperStatus' is not
        'down' the value of this object will be 
        'none'."
    ::= { cieIfInterfaceEntry 10 }

cieIfSpeedReceive OBJECT-TYPE
    SYNTAX Gauge
    ACCESS read-only
    STATUS mandatory
    DESCRIPTION
        "An estimate of the interface's current receive bandwidth in
        bits per second.  This object is provided for interface with
        asymmetric interface speeds like ADSL and should be used in
        conjunction with ifSpeed object.  For interfaces which do not
        vary in bandwidth or for those where no accurate estimation can
        be made, this object should contain the nominal bandwidth. If
        the bandwidth of the interface is greater than the maximum value
        reportable by this object then this object should report its
        maximum value (4,294,967,295) and ifHighSpeed must be used to
        report the interace's speed.  For a sub-layer which has no
        concept of bandwidth, this object should be zero."
    ::= { cieIfInterfaceEntry 11 }

cieIfHighSpeedReceive OBJECT-TYPE
    SYNTAX Gauge
    ACCESS read-only
    STATUS mandatory
    DESCRIPTION
        "An estimate of the interface's current receive bandwidth in
        units of 1,000,000 bits per second.  If this object reports a
        value of `n' then the speed of the interface is somewhere in the
        range of `n-500,000' to `n+499,999'.  For interfaces which do
        not vary in bandwidth or for those where no accurate estimation
        can be made, this object should contain the nominal bandwidth. 
        For a sub-layer which has no concept of bandwidth, this object
        should be zero."
    ::= { cieIfInterfaceEntry 12 }

cieIfOwner OBJECT-TYPE
    SYNTAX DisplayString(SIZE(0..80))
--    Rsyntax OCTET STRING(SIZE(0..80))
    ACCESS read-write
    STATUS mandatory
    DESCRIPTION
        "This data type is used to model an administratively assigned
        name of the current owner of the interface resource. This 
        information is taken from the NVT ASCII character set.  It is 
        suggested that this name contain one or more of the following: 
        SnmpEngineID, IP address, management station name, network 
        manager's name, location, or phone number.
        SNMP access control is articulated entirely in terms of the 
        contents of MIB views; access to a particular SNMP object 
        instance depends only upon its presence or absence in a 
        particular MIB view and never upon its value or the value of 
        related object instances.
        Thus, this object affords resolution of resource contention 
        only among cooperating managers; this object realizes no access
        control function with respect to uncooperative parties."
    ::= { cieIfInterfaceEntry 13 }

cieIfSharedConfig OBJECT-TYPE
    SYNTAX INTEGER {
        notApplicable(1),
        ownerDedicated(2),
        ownerShared(3),
        sharedOnly(4)
        }
    ACCESS read-only
    STATUS mandatory
    DESCRIPTION
        "This object indicates the current configuration of
        interface sharing on the given interface.
        
        'notApplicable' - the interface sharing configuration on 
                    this interface is not applicable. 
        'ownerDedicated' - the interface is in the dedicated mode
                    to the binding physical interface.
        'ownerShared' - the interface is shared amongst virtual switches
                 and this interface physically belongs to a its 
                 virtual switch.  
        'sharedOnly' - the interface is in purely shared mode."
    ::= { cieIfInterfaceEntry 14 }

cieIfSpeedGroupConfig OBJECT-TYPE
    SYNTAX INTEGER {
        notApplicable(1),
        tenG(2),
        oneTwoFourEightG(3),
        twoFourEightSixteenG(4)
        }
    ACCESS read-write
    STATUS mandatory
    DESCRIPTION
        "This object specifies the current speed group
        configuration on the given interface.
        
        'notApplicable' - the interface speed group configuration on
                    this interface is not applicable. It is a 
                    read-only value.
        '10G' - the interface speed group configuration on
                    this interface as 10G.
        '1G-2G-4G-8G' - the interface speed group configuration 
                    on this interface as 1G-2G-4G-8G.
        '2G-4G-8G-16G' - the interface speed group configuration 
                    on this interface as 2G-4G-8G-16G."
    ::= { cieIfInterfaceEntry 15 }

cieIfTransceiverFrequencyConfig OBJECT-TYPE
    SYNTAX INTEGER {
        notApplicable(1),
        fibreChannel(2),
        ethernet(3)
        }
    ACCESS read-write
    STATUS mandatory
    DESCRIPTION
        "This object specifies the current transceiver frequency
        configuration on the given interface.
        
        'notApplicable' - the interface transceiver frequency 
              configuration on this interface 
              is not applicable. It is a read-only value.
        'FibreChannel' - the interface transceiver frequency
             configuration on this interface as 
                         Fibre Channel.
        'Ethernet'   -  the interface transceiver frequency on
             this interface as Ethernet."
    DEFVAL { fibreChannel }
    ::= { cieIfInterfaceEntry 16 }

cieIfFillPatternConfig OBJECT-TYPE
    SYNTAX INTEGER {
        arbff8G(1),
        idle8G(2)
        }
    ACCESS read-write
    STATUS mandatory
    DESCRIPTION
        "This object specifies the current switchport fill pattern
        configuration on the given interface.
        
        'arbff8G' - the inter frame gap fill pattern is
           ARBFF for 8G speed.
        'idle8G' - the inter frame gap fill pattern is
             IDLE for 8G speed."
    DEFVAL { arbff8G }
    ::= { cieIfInterfaceEntry 17 }

cieIfIgnoreBitErrorsConfig OBJECT-TYPE
    SYNTAX TruthValue
--    Rsyntax INTEGER {
--        true(1),
--        false(2)
--        }
    ACCESS read-write
    STATUS mandatory
    DESCRIPTION
        "This object specifies the current switchport biterrors
        configuration on the given interface.
        
        If 'true(1)' the ignore bit errors is enabled.In which case
        the interface ignores bit errors.
        If 'false(2)' the ignore bit errors is disabled. In which 
        case the interface acts on the bit errors. 
        For interfaces, for which bit errors 
        is not supported, then this object has the
        value 'true(1)'."
    DEFVAL { true }
    ::= { cieIfInterfaceEntry 18 }

cieIfIgnoreInterruptThresholdConfig OBJECT-TYPE
    SYNTAX TruthValue
--    Rsyntax INTEGER {
--        true(1),
--        false(2)
--        }
    ACCESS read-write
    STATUS mandatory
    DESCRIPTION
        "This object specifies the current interrupt threshold
        configuration on the given interface.
        
        'If 'true(1)' the ignore interrupt thresholds is enabled.
        In which case the interface ignores interrupt thresholds.
        If 'false(2)' the ignore interrupt thresholds is disabled.
        In which case the interface acts on the interrupt 
        thresholds. 
        For interfaces, for which interrupt thresholds 
        is not supported, then this object has the 
        value 'true(1)'."
    DEFVAL { true }
    ::= { cieIfInterfaceEntry 19 }

cieIfStatusListTable OBJECT-TYPE
    SYNTAX SEQUENCE OF CieIfStatusListEntry
    ACCESS not-accessible
    STATUS mandatory
    DESCRIPTION
        "This table contains objects for providing
        the 'ifIndex', interface operational mode and 
        interface operational cause for all the 
        interfaces in the modules.
        
        This table contains one entry for each 
        64 interfaces in an module.
        
        This table provides efficient way of encoding 
        'ifIndex', interface operational mode and
        interface operational cause, from the point 
        of retrieval, by combining the values a set 
        of 64 interfaces in a single MIB object."
    ::= { ciscoIfExtensionStats 3 }

cieIfStatusListEntry OBJECT-TYPE
    SYNTAX CieIfStatusListEntry
    ACCESS not-accessible
    STATUS mandatory
    DESCRIPTION
        "Each entry represents the 'ifIndex',
        interface operational mode and interface 
        operational cause for a set of 64 interfaces 
        in a module."
    INDEX { entPhysicalIndex, cieIfStatusListIndex }
    ::= { cieIfStatusListTable 1 }

CieIfStatusListEntry ::= SEQUENCE {
    cieIfStatusListIndex Gauge,
    cieInterfacesIndex InterfaceIndexList,
    cieInterfacesOperMode InterfaceOperModeList,
    cieInterfacesOperCause InterfaceOperCauseList,
    cieInterfaceOwnershipBitmap InterfaceOwnershipList
    }

cieIfStatusListIndex OBJECT-TYPE
    SYNTAX Gauge(1..33554432)
    ACCESS not-accessible
    STATUS mandatory
    DESCRIPTION
        "An arbitrary integer value, greater than
        zero, which identifies a list of 64 interfaces
        within a module."
    ::= { cieIfStatusListEntry 1 }

cieInterfacesIndex OBJECT-TYPE
    SYNTAX InterfaceIndexList
--    Rsyntax OCTET STRING(SIZE(0..256))
    ACCESS read-only
    STATUS mandatory
    DESCRIPTION
        "This object represents the 'ifIndex' for a
        set of 64 interfaces in the module."
    ::= { cieIfStatusListEntry 2 }

cieInterfacesOperMode OBJECT-TYPE
    SYNTAX InterfaceOperModeList
--    Rsyntax OCTET STRING(SIZE(0..64))
    ACCESS read-only
    STATUS mandatory
    DESCRIPTION
        "This object represents the operational mode
        for a set of 64 interfaces in the module."
    ::= { cieIfStatusListEntry 3 }

cieInterfacesOperCause OBJECT-TYPE
    SYNTAX InterfaceOperCauseList
--    Rsyntax OCTET STRING(SIZE(0..128))
    ACCESS read-only
    STATUS mandatory
    DESCRIPTION
        "This object represents the operational status
        cause for a set of 64 interfaces in the 
        module."
    ::= { cieIfStatusListEntry 4 }

cieInterfaceOwnershipBitmap OBJECT-TYPE
    SYNTAX InterfaceOwnershipList
--    Rsyntax OCTET STRING(SIZE(0..8))
    ACCESS read-only
    STATUS mandatory
    DESCRIPTION
        "This object indicates the status for a set of 64 interfaces
        in a module regarding whether or not each interface is 
        administratively assigned a name of the current owner of the 
        interface resource as per cieIfOwner."
    ::= { cieIfStatusListEntry 5 }

cieIfVlStatsTable OBJECT-TYPE
    SYNTAX SEQUENCE OF CieIfVlStatsEntry
    ACCESS not-accessible
    STATUS mandatory
    DESCRIPTION
        "This table contains VL (Virtual Link) statistics
        for a capable interface.
        
        Objects defined in this table may be 
        applicable to physical interfaces only."
    ::= { ciscoIfExtensionStats 4 }

cieIfVlStatsEntry OBJECT-TYPE
    SYNTAX CieIfVlStatsEntry
    ACCESS not-accessible
    STATUS mandatory
    DESCRIPTION
        "Each row contains managed objects for
        Virtual Link statistics on interface capable of 
        providing this information."
    INDEX { ifIndex }
    ::= { cieIfVlStatsTable 1 }

CieIfVlStatsEntry ::= SEQUENCE {
    cieIfNoDropVlInPkts Counter,
    cieIfNoDropVlInOctets Counter,
    cieIfNoDropVlOutPkts Counter,
    cieIfNoDropVlOutOctets Counter,
    cieIfDropVlInPkts Counter,
    cieIfDropVlInOctets Counter,
    cieIfDropVlOutPkts Counter,
    cieIfDropVlOutOctets Counter
    }

cieIfNoDropVlInPkts OBJECT-TYPE
    SYNTAX --?? syntax is not convertable to SMIv1
           Counter
    ACCESS read-only
    STATUS mandatory
    DESCRIPTION
        "This object indicates the number of input
        packets on all No-Drop Virtual Links belonged 
        to this interface."
    ::= { cieIfVlStatsEntry 1 }

cieIfNoDropVlInOctets OBJECT-TYPE
    SYNTAX --?? syntax is not convertable to SMIv1
           Counter
    ACCESS read-only
    STATUS mandatory
    DESCRIPTION
        "This object indicates the number of input
        octets on all No-Drop Virtual Links belonged 
        to this interface."
    ::= { cieIfVlStatsEntry 2 }

cieIfNoDropVlOutPkts OBJECT-TYPE
    SYNTAX --?? syntax is not convertable to SMIv1
           Counter
    ACCESS read-only
    STATUS mandatory
    DESCRIPTION
        "This object indicates the number of output
        packets on all No-Drop Virtual Links belonged 
        to this interface."
    ::= { cieIfVlStatsEntry 3 }

cieIfNoDropVlOutOctets OBJECT-TYPE
    SYNTAX --?? syntax is not convertable to SMIv1
           Counter
    ACCESS read-only
    STATUS mandatory
    DESCRIPTION
        "This object indicates the number of output
        octets on all No-Drop Virtual Links belonged 
        to this interface."
    ::= { cieIfVlStatsEntry 4 }

cieIfDropVlInPkts OBJECT-TYPE
    SYNTAX --?? syntax is not convertable to SMIv1
           Counter
    ACCESS read-only
    STATUS mandatory
    DESCRIPTION
        "This object indicates the number of input
        packets on all Drop Virtual Links belonged 
        to this interface."
    ::= { cieIfVlStatsEntry 5 }

cieIfDropVlInOctets OBJECT-TYPE
    SYNTAX --?? syntax is not convertable to SMIv1
           Counter
    ACCESS read-only
    STATUS mandatory
    DESCRIPTION
        "This object indicates the number of input
        octets on all Drop Virtual Links belonged 
        to this interface."
    ::= { cieIfVlStatsEntry 6 }

cieIfDropVlOutPkts OBJECT-TYPE
    SYNTAX --?? syntax is not convertable to SMIv1
           Counter
    ACCESS read-only
    STATUS mandatory
    DESCRIPTION
        "This object indicates the number of output
        packets on all Drop Virtual Links belonged 
        to this interface."
    ::= { cieIfVlStatsEntry 7 }

cieIfDropVlOutOctets OBJECT-TYPE
    SYNTAX --?? syntax is not convertable to SMIv1
           Counter
    ACCESS read-only
    STATUS mandatory
    DESCRIPTION
        "This object indicates the number of output
        octets on all Drop Virtual Links belonged 
        to this interface."
    ::= { cieIfVlStatsEntry 8 }

cieSystemMtu OBJECT-TYPE
    SYNTAX INTEGER
    ACCESS read-write
    STATUS mandatory
    DESCRIPTION
        "Global system MTU in octets.
        This object specifies the MTU on all interfaces.
        However, the value specified by cieIfMtu
        takes precedence for an interface, which means
        that the interface's MTU uses the value
        specified by cieIfMtu, if it is configured."
    DEFVAL { 1500 }
    ::= { ciscoIfExtSystemConfig 1 }

cieLinkUpDownEnable OBJECT-TYPE
    SYNTAX OCTET STRING(SIZE(1..2))
        -- BITS are:
        --   standard(0)
        --   cisco(1)
    ACCESS read-write
    STATUS deprecated
    DESCRIPTION
        "Indicates whether cieLinkUp/cieLinkDown
        or standard mib-II defined linkUp/Down or
        both, notifications should be generated
        for the interfaces in the system.
        
        'standard'  - only generate standard defined
                      mib-II linkUp/linkDown notification
                      if 'ifLinkUpDownTrapEnable' for 
                      the interface is 'enabled'.
        'cisco'     - only generate cieLinkUp/cieLinkDown
                      notifications for an interface if
                      the 'ifLinkUpDownTrapEnable' for the
                      interface is 'enabled'.
        
        If both bits are selected then linkUp/linkDown and
        cieLinkUp/cieLinkDown are both generated for an 
        interface if the 'ifLinkUpDownTrapEnable' for the
        interface is 'enabled'."
    DEFVAL { '80'h }
    ::= { ciscoIfExtSystemConfig 2 }

cieStandardLinkUpDownVarbinds OBJECT-TYPE
    SYNTAX INTEGER {
        standard(1),
        additional(2),
        other(3)
        }
    ACCESS read-write
    STATUS deprecated
    DESCRIPTION
        "Indicates whether to send the extra
        varbinds in addition to the varbinds defined 
        in linkUp/linkDown notifications.
        
        'standard'   - only send the varbinds defined in
                       the standard linkUp/linkDown
                       notification.  
        'additional' - send the extra varbinds in addition 
                       to the defined ones.
        'other'      - any other config not covered by the above.
                       This value is read-only."
    DEFVAL { additional }
    ::= { ciscoIfExtSystemConfig 3 }

cieIfIndexPersistence OBJECT-TYPE
    SYNTAX TruthValue
--    Rsyntax INTEGER {
--        true(1),
--        false(2)
--        }
    ACCESS read-write
    STATUS deprecated
    DESCRIPTION
        "This object specifies whether ifIndex values persist across
        reinitialization of the device.
        
        ifIndex persistence means that the mapping between the ifDescr
        object values and the ifIndex object values will be retained
        across reboots.
        
        Applications such as device inventory, billing, and fault
        detection depend on the maintenance of the correspondence
        between particular ifIndex values and their interfaces. During
        reboot or insertion of a new card, the data to correlate the
        interfaces to the ifIndex may become invalid in absence of
        ifIndex persistence feature.
        
        ifIndex persistence for an interface ensures ifIndex value for
        the interface will remain the same after a system reboot.
        Hence, this feature allows users to avoid the workarounds
        required for consistent interface identification across
        reinitialization.
        
        Due to change in syntax, this object is deprecated by
        cieIfIndexGlobalPersistence."
    DEFVAL { false }
    ::= { ciscoIfExtSystemConfig 4 }

cieIfIndexPersistenceTable OBJECT-TYPE
    SYNTAX SEQUENCE OF CieIfIndexPersistenceEntry
    ACCESS not-accessible
    STATUS mandatory
    DESCRIPTION
        "This table lists configuration data relating to ifIndex
        persistence.
        
        This table has a sparse dependent relationship on the ifTable,
        containing a row for each ifEntry corresponding to an interface
        for which ifIndex persistence is supported."
    ::= { ciscoIfExtSystemConfig 5 }

cieIfIndexPersistenceEntry OBJECT-TYPE
    SYNTAX CieIfIndexPersistenceEntry
    ACCESS not-accessible
    STATUS mandatory
    DESCRIPTION
        "Each entry represents ifindex persistence configuration for an
        interface specified by ifIndex. Whenever an interface which
        supports ifindex persistence is created/destroyed in the
        ifTable, the corresponding ifindex persistence entry is
        created/destroyed respectively. Some of the interfaces may not
        support ifindex persistence, for example, a dynamic interface,
        such as a PPP connection or a IP subscriber interface."
    INDEX { ifIndex }
    ::= { cieIfIndexPersistenceTable 1 }

CieIfIndexPersistenceEntry ::= SEQUENCE {
    cieIfIndexPersistenceEnabled TruthValue,
    cieIfIndexPersistenceControl IfIndexPersistenceState
    }

cieIfIndexPersistenceEnabled OBJECT-TYPE
    SYNTAX TruthValue
--    Rsyntax INTEGER {
--        true(1),
--        false(2)
--        }
    ACCESS read-write
    STATUS deprecated
    DESCRIPTION
        "This object specifies whether the interface's ifIndex value
        persist across reinitialization.
        
        Due to change in syntax, this object is deprecated by
        cieIfIndexPersistenceControl."
    DEFVAL { true }
    ::= { cieIfIndexPersistenceEntry 1 }

cieIfIndexPersistenceControl OBJECT-TYPE
    SYNTAX IfIndexPersistenceState
--    Rsyntax INTEGER {
--        disable(1),
--        enable(2),
--        global(3)
--        }
    ACCESS read-write
    STATUS mandatory
    DESCRIPTION
        "This object specifies whether the interface's ifIndex value
        persist across reinitialization. In global state, the interface
        uses the global setting data for persistence i.e.
        cieIfIndexGlobalPersistence."
    DEFVAL { global }
    ::= { cieIfIndexPersistenceEntry 2 }

cieDelayedLinkUpDownNotifEnable OBJECT-TYPE
    SYNTAX TruthValue
--    Rsyntax INTEGER {
--        true(1),
--        false(2)
--        }
    ACCESS read-write
    STATUS mandatory
    DESCRIPTION
        "This object specifies whether the system generates a
        cieDelayedLinkUpDownNotif notification."
    DEFVAL { false }
    ::= { ciscoIfExtSystemConfig 6 }

cieDelayedLinkUpDownNotifDelay OBJECT-TYPE
    SYNTAX Gauge(1..60)
--  Units
--    minutes
    ACCESS read-write
    STATUS mandatory
    DESCRIPTION
        "This object specifies the interval of time an interface's
        operational status must remain stable following a transition
        before the system will generate a cieDelayedLinkUpDownNotif."
    DEFVAL { 4 }
    ::= { ciscoIfExtSystemConfig 7 }

cieIfIndexGlobalPersistence OBJECT-TYPE
    SYNTAX IfIndexPersistenceState
--    Rsyntax INTEGER {
--        disable(1),
--        enable(2),
--        global(3)
--        }
    ACCESS read-write
    STATUS mandatory
    DESCRIPTION
        "This object specifies whether ifIndex values persist across
        reinitialization of the device.
        
        ifIndex persistence means that the mapping between the ifDescr
        object values and the ifIndex object values will be retained
        across reboots.
        
        Applications such as device inventory, billing, and fault
        detection depend on the maintenance of the correspondence
        between particular ifIndex values and their interfaces. During
        reboot or insertion of a new card, the data to correlate the
        interfaces to the ifIndex may become invalid in absence of
        ifIndex persistence feature.
        
        ifIndex persistence for an interface ensures ifIndex value for
        the interface will remain the same after a system reboot. Hence,
        this feature allows users to avoid the workarounds required for
        consistent interface identification across reinitialization.
        
        The allowed values for this object are either enable or disable.
        global value is not allowed."
    DEFVAL { disable }
    ::= { ciscoIfExtSystemConfig 8 }

cieLinkUpDownConfig OBJECT-TYPE
    SYNTAX OCTET STRING(SIZE(1..2))
        -- BITS are:
        --   standardLinkUp(0)
        --   standardLinkDown(1)
        --   additionalLinkUp(2)
        --   additionalLinkDown(3)
        --   ciscoLinkUp(4)
        --   ciscoLinkDown(5)
    ACCESS read-write
    STATUS mandatory
    DESCRIPTION
        "This object specifies whether standard mib-II defined linkUp/
        linkDown, extended linkUp/linkDown (with extra varbinds in
        addition to the varbinds defined in linkUp/linkDown) or
        cieLinkUp/cieLinkDown notifications should be generated for
        the interfaces in the system.
        
        'standardLinkUp'     - generate standard defined mib-II 
                               linkUp notification if 
                               'ifLinkUpDownTrapEnable' for the 
                               interface is 'enabled'.
        'standardLinkDown'   - generate standard defined mib-II 
                               linkDown notification if 
                               'ifLinkUpDownTrapEnable' for the 
                               interface is 'enabled'.  
        'additionalLinkUp'   - generate linkUp notification with
                               additional varbinds if 
                               'ifLinkUpDownTrapEnable' for the 
                               interface is 'enabled'.  
        'additionalLinkDown' - generate linkDown notification with
                               additional varbinds if 
                               'ifLinkUpDownTrapEnable' for the 
                               interface is 'enabled'.
        'ciscoLinkUp'        - generate cieLinkUp notification
                               if the 'ifLinkUpDownTrapEnable' for the
                               interface is 'enabled'.
        'ciscoLinkDown'      - generate cieLinkDown notification
                               if the 'ifLinkUpDownTrapEnable' for the
                               interface is 'enabled'.
        
        If multiple bits are set then multiple notifications will
        be generated for an interface if the 'ifLinkUpDownTrapEnable' 
        for the interface is 'enabled'."
    ::= { ciscoIfExtSystemConfig 9 }

cieIfDot1qCustomEtherTypeTable OBJECT-TYPE
    SYNTAX SEQUENCE OF CieIfDot1qCustomEtherTypeEntry
    ACCESS not-accessible
    STATUS mandatory
    DESCRIPTION
        "A list of the interfaces that support
        the 802.1q custom Ethertype feature."
    ::= { ciscoIfExtDot1qCustomEtherType 1 }

cieIfDot1qCustomEtherTypeEntry OBJECT-TYPE
    SYNTAX CieIfDot1qCustomEtherTypeEntry
    ACCESS not-accessible
    STATUS mandatory
    DESCRIPTION
        "An entry containing the custom EtherType
        information for the interface.
        
        Only interfaces with custom 802.1q
        ethertype control are listed in the 
        table."
    INDEX { ifIndex }
    ::= { cieIfDot1qCustomEtherTypeTable 1 }

CieIfDot1qCustomEtherTypeEntry ::= SEQUENCE {
    cieIfDot1qCustomAdminEtherType INTEGER,
    cieIfDot1qCustomOperEtherType INTEGER
    }

cieIfDot1qCustomAdminEtherType OBJECT-TYPE
    SYNTAX INTEGER(0..65535)
    ACCESS read-write
    STATUS mandatory
    DESCRIPTION
        "The Dot1qEtherType allow administrator
        to select a non-standard (other than 0x8100)
        2-byte ethertype for the interface to 
        interoperate with third party vendor's system
        that do not use the standard 0x8100 ethertype
        to identify 802.1q-tagged frames.
        
        The current administrative value of the 
        802.1q ethertype for the interface.  The
        administrative 802.1q ethertype value may 
        differ from the operational 802.1q ethertype
        value.  On some platforms, 802.1q ethertype
        may be assigned per group rather than per port.
        If multiple ports belong to a port group,
        the 802.1q ethertype assigned to any of
        the ports in such group will apply to all
        ports in the same group.
        
        To configure non-standard dot1q ethertype
        is only recommended when the Cisco device
        is connected to any third party vendor device.
        Also be advised that the custom ethertype value
        needs to be changed in the whole cloud of 
        Cisco device with the same custom ethertype 
        value if the third party device are separated 
        by number of Cisco device in the middle."
    ::= { cieIfDot1qCustomEtherTypeEntry 1 }

cieIfDot1qCustomOperEtherType OBJECT-TYPE
    SYNTAX INTEGER(0..65535)
    ACCESS read-only
    STATUS mandatory
    DESCRIPTION
        "The current operational value of the
        802.1q ethertype for the interface."
    ::= { cieIfDot1qCustomEtherTypeEntry 2 }

cieIfUtilTable OBJECT-TYPE
    SYNTAX SEQUENCE OF CieIfUtilEntry
    ACCESS not-accessible
    STATUS mandatory
    DESCRIPTION
        "This table contains the interface utilization
        rates for inbound and outbound traffic on an
        interface."
    ::= { ciscoIfExtUtilization 1 }

cieIfUtilEntry OBJECT-TYPE
    SYNTAX CieIfUtilEntry
    ACCESS not-accessible
    STATUS mandatory
    DESCRIPTION
        "An entry containing utilization rates for the
        interface.
        
        Every interface for which the  inbound and 
        outbound traffic information is available
        has a corresponding entry in this table."
    INDEX { ifIndex }
    ::= { cieIfUtilTable 1 }

CieIfUtilEntry ::= SEQUENCE {
    cieIfInPktRate Counter,
    cieIfInOctetRate Counter,
    cieIfOutPktRate Counter,
    cieIfOutOctetRate Counter,
    cieIfInterval Gauge
    }

cieIfInPktRate OBJECT-TYPE
    SYNTAX --?? syntax is not convertable to SMIv1
           Counter
--  Units
--    packets per second
    ACCESS read-only
    STATUS mandatory
    DESCRIPTION
        "By default, this is the five minute
        exponentially-decayed moving average of the
        inbound packet rate for this interface.
        However, if the corresponding instance of
        cieIfInterval is instantiated with a value
        which specifies an interval different from
        5-minutes, then cieIfInPktRate is the
        exponentially-decayed moving average of inbound
        packet rate over this different time interval."
    ::= { cieIfUtilEntry 1 }

cieIfInOctetRate OBJECT-TYPE
    SYNTAX --?? syntax is not convertable to SMIv1
           Counter
--  Units
--    octets per second
    ACCESS read-only
    STATUS mandatory
    DESCRIPTION
        "By default, this is the five minute
        exponentially-decayed moving average of the
        inbound octet rate for this interface.
        However, if the corresponding instance of
        cieIfInterval is instantiated with a value
        which specifies an interval different from
        5-minutes, then cieIfInOctetRate is the
        exponentially-decayed moving average of inbound
        octet rate over this different time interval."
    ::= { cieIfUtilEntry 2 }

cieIfOutPktRate OBJECT-TYPE
    SYNTAX --?? syntax is not convertable to SMIv1
           Counter
--  Units
--    packets per second
    ACCESS read-only
    STATUS mandatory
    DESCRIPTION
        "By default, this is the five minute
        exponentially-decayed moving average of the
        outbound packet rate for this interface.
        However, if the corresponding instance of
        cieIfInterval is instantiated with a value
        which specifies an interval different from
        5-minutes, then cieIfOutPktRate is the
        exponentially-decayed moving average of outbound
        packet rate over this different time interval."
    ::= { cieIfUtilEntry 3 }

cieIfOutOctetRate OBJECT-TYPE
    SYNTAX --?? syntax is not convertable to SMIv1
           Counter
--  Units
--    octets per second
    ACCESS read-only
    STATUS mandatory
    DESCRIPTION
        "By default, this is the five minute
        exponentially-decayed moving average of the
        outbound octet rate for this interface.
        However, if the corresponding instance of
        cieIfInterval is instantiated with a value
        which specifies an interval different from
        5-minutes, then cieIfOutOctetRate is the
        exponentially-decayed moving average of outbound
        octet rate over this different time interval."
    ::= { cieIfUtilEntry 4 }

cieIfInterval OBJECT-TYPE
    SYNTAX Gauge(1..4294967295)
--  Units
--    seconds
    ACCESS read-write
    STATUS mandatory
    DESCRIPTION
        "This object specifies the time interval over which
        the inbound and outbound traffic rates are
        calculated for this interface."
    ::= { cieIfUtilEntry 5 }

cieIfDot1dBaseMappingTable OBJECT-TYPE
    SYNTAX SEQUENCE OF CieIfDot1dBaseMappingEntry
    ACCESS not-accessible
    STATUS mandatory
    DESCRIPTION
        "This table contains the mappings of the
        ifIndex of an interface to its
        corresponding dot1dBasePort value."
    REFERENCE
        "dot1dBasePort is defined in BRIDGE-MIB."
    ::= { ciscoIfExtDot1dBaseMapping 1 }

cieIfDot1dBaseMappingEntry OBJECT-TYPE
    SYNTAX CieIfDot1dBaseMappingEntry
    ACCESS not-accessible
    STATUS mandatory
    DESCRIPTION
        "An entry containing the mapping between
        the ifIndex value of an interface and its
        corresponding dot1dBasePort value.
        
        Every interface which has been assigned
        a dot1dBasePort value by the system
        has a corresponding entry in this table."
    REFERENCE
        "dot1dBasePort is defined in BRIDGE-MIB."
    INDEX { ifIndex }
    ::= { cieIfDot1dBaseMappingTable 1 }

CieIfDot1dBaseMappingEntry ::= SEQUENCE {
    cieIfDot1dBaseMappingPort INTEGER
    }

cieIfDot1dBaseMappingPort OBJECT-TYPE
    SYNTAX INTEGER(1..65535)
    ACCESS read-only
    STATUS mandatory
    DESCRIPTION
        "The dot1dBasePort value for this interface."
    REFERENCE
        "dot1dBasePort is defined in BRIDGE-MIB."
    ::= { cieIfDot1dBaseMappingEntry 1 }

cieIfNameMappingTable OBJECT-TYPE
    SYNTAX SEQUENCE OF CieIfNameMappingEntry
    ACCESS not-accessible
    STATUS mandatory
    DESCRIPTION
        "This table contains objects for providing
        the 'ifName' to 'ifIndex' mapping.
        This table contains one entry for each
        valid 'ifName' available in the system.
        Upon the first request, the implementation
        of this table will get all the available
        ifNames, and it will populate the entries
        in this table, it maintains this ifNames
        in a cache for ~30 seconds."
    ::= { ciscoIfExtIfNameMapping 1 }

cieIfNameMappingEntry OBJECT-TYPE
    SYNTAX CieIfNameMappingEntry
    ACCESS not-accessible
    STATUS mandatory
    DESCRIPTION
        "An entry into the cieIfNameMappingTable."
    INDEX { cieIfName }
    ::= { cieIfNameMappingTable 1 }

CieIfNameMappingEntry ::= SEQUENCE {
    cieIfName DisplayString,
    cieIfIndex InterfaceIndexOrZero
    }

cieIfName OBJECT-TYPE
    SYNTAX DisplayString(SIZE(1..112))
--    Rsyntax OCTET STRING(SIZE(1..112))
    ACCESS not-accessible
    STATUS mandatory
    DESCRIPTION
        "Represents an interface name mentioned
        in the 'ifName' object of this system."
    ::= { cieIfNameMappingEntry 1 }

cieIfIndex OBJECT-TYPE
    SYNTAX InterfaceIndexOrZero
--    Rsyntax INTEGER(0..2147483647)
    ACCESS read-only
    STATUS mandatory
    DESCRIPTION
        "This object represents the 'ifIndex'
        corresponding to the interface name mentioned
        in the 'cieIfName' object of this instance.
        If the 'ifName' mentioned in the 'cieIfName' 
        object of this instance corresponds to multiple
        'ifIndex' values, then the value of this object
        is the numerically smallest of those multiple 
        'ifIndex' values."
    ::= { cieIfNameMappingEntry 2 }

cieLinkDown TRAP-TYPE
-- Reverse mappable trap
    ENTERPRISE ciscoIfExtensionMIB
    VARIABLES {
        ifIndex, ifAdminStatus, ifOperStatus, ifName, ifType }
--  Status
--    mandatory
    DESCRIPTION
        "A cisco specific linkDown notification
        signifies that the SNMP entity, acting in an
        agent role, has detected that the ifOperStatus
        object for one of its communication links is
        about to enter the down state from some other
        state (but not from the notPresent state).
        The varbinds for this notification indicate the
        interface information of the communication
        link."
    ::= 1

cieLinkUp TRAP-TYPE
-- Reverse mappable trap
    ENTERPRISE ciscoIfExtensionMIB
    VARIABLES {
        ifIndex, ifAdminStatus, ifOperStatus, ifName, ifType }
--  Status
--    mandatory
    DESCRIPTION
        "A cisco specific linkUp trap signifies that
        the SNMP entity, acting in an agent role, has
        detected that the ifOperStatus object for one
        of its communication links left the down state
        and transitioned into some other state (but not
        into the notPresent state). The varbinds for
        this notification indicate the interface
        information of the communication link."
    ::= 2

cieDelayedLinkUpDownNotif TRAP-TYPE
-- Reverse mappable trap
    ENTERPRISE ciscoIfExtensionMIB
    VARIABLES {
        ifAdminStatus, ifOperStatus, ifName, ifType, 
        cieIfOperStatusCause }
--  Status
--    mandatory
    DESCRIPTION
        "This notification indicates when an interface's operational
        status has transitioned and remained in that state for a time
        specified by cieDelayedLinkUpDownDelay."
    ::= 3

ciscoIfExtensionTablePacketGroup OBJECT IDENTIFIER ::= { ciscoIfExtensionMIBGroups 1 }
-- OBJECT-GROUP
--  Status
--    mandatory
--  Descr
--    A collection of objects containing packet
--    statistics for a given interface.
--  objects
--    cieIfLastInTime, cieIfLastOutTime, cieIfLastOutHangTime, 
--    cieIfInRuntsErrs, cieIfInGiantsErrs, cieIfInFramingErrs, 
--    cieIfInOverrunErrs, cieIfInIgnored, cieIfInAbortErrs, 
--    cieIfInputQueueDrops, cieIfOutputQueueDrops, 
--    cieIfPacketDiscontinuityTime

ciscoIfExtensionTableIntfGroup OBJECT IDENTIFIER ::= { ciscoIfExtensionMIBGroups 2 }
-- OBJECT-GROUP
--  Status
--    mandatory
--  Descr
--    A collection of objects containing
--    information about properties of 
--    interfaces.
--  objects
--    cieIfResetCount, cieIfKeepAliveEnabled, 
--    cieIfStateChangeReason, cieIfCarrierTransitionCount, 
--    cieIfInterfaceDiscontinuityTime

ciscoIfExtensionTableIntfGroup1 OBJECT IDENTIFIER ::= { ciscoIfExtensionMIBGroups 3 }
-- OBJECT-GROUP
--  Status
--    deprecated
--  Descr
--    A collection of objects containing
--    information about properties of 
--    interfaces.
--  objects
--    cieIfDhcpMode, cieIfMtu, cieIfContextName

ciscoIfExtensionSystemGroup OBJECT IDENTIFIER ::= { ciscoIfExtensionMIBGroups 4 }
-- OBJECT-GROUP
--  Status
--    mandatory
--  Descr
--    A collection of objects providing
--    global system-wise information about
--    interfaces.
--  objects
--    cieSystemMtu

ciscoIfExtDot1qEtherTypeGroup OBJECT IDENTIFIER ::= { ciscoIfExtensionMIBGroups 5 }
-- OBJECT-GROUP
--  Status
--    mandatory
--  Descr
--    A collection of objects providing
--    the information about 802.1q 
--    custom EtherType on the 
--    interface.
--  objects
--    cieIfDot1qCustomAdminEtherType, cieIfDot1qCustomOperEtherType

ciscoIfExtUtilizationGroup OBJECT IDENTIFIER ::= { ciscoIfExtensionMIBGroups 6 }
-- OBJECT-GROUP
--  Status
--    mandatory
--  Descr
--    A collection of objects containing
--    information about utilization rates of
--    interfaces.
--  objects
--    cieIfInPktRate, cieIfInOctetRate, cieIfOutPktRate, 
--    cieIfOutOctetRate

ciscoIfExtDot1dBaseMappingGroup OBJECT IDENTIFIER ::= { ciscoIfExtensionMIBGroups 7 }
-- OBJECT-GROUP
--  Status
--    mandatory
--  Descr
--    A collection of objects containing
--    mapping information about the ifIndex values
--    of interfaces and their dot1dBasePort 
--    values.
--  objects
--    cieIfDot1dBaseMappingPort

ciscoIfExtIfNameMappingGroup OBJECT IDENTIFIER ::= { ciscoIfExtensionMIBGroups 8 }
-- OBJECT-GROUP
--  Status
--    mandatory
--  Descr
--    A collection of objects for the
--    'ifName' to 'ifIndex' mapping.
--  objects
--    cieIfIndex

ciscoIfExtensionTableIntfGroup2 OBJECT IDENTIFIER ::= { ciscoIfExtensionMIBGroups 9 }
-- OBJECT-GROUP
--  Status
--    deprecated
--  Descr
--    A collection of objects containing
--    information about properties of 
--    interfaces.
--  objects
--    cieIfDhcpMode, cieIfMtu, cieIfContextName, 
--    cieIfOperStatusCause, cieIfOperStatusCauseDescr

cieIfStatusListGroup OBJECT IDENTIFIER ::= { ciscoIfExtensionMIBGroups 10 }
-- OBJECT-GROUP
--  Status
--    mandatory
--  Descr
--    A collection of objects containing
--    information about set of interfaces.
--  objects
--    cieInterfacesIndex, cieInterfacesOperMode, 
--    cieInterfacesOperCause

cieLinkUpDownNotifEnableGroup OBJECT IDENTIFIER ::= { ciscoIfExtensionMIBGroups 11 }
-- OBJECT-GROUP
--  Status
--    deprecated
--  Descr
--    A collection of objects to control
--    'cieLinkUp/cieLinkDown' and standard mib-II 
--    defined 'linkUp/linkDown' notifications.
--  objects
--    cieLinkUpDownEnable, cieStandardLinkUpDownVarbinds

ciscoIfExtensionAsymmetricalSpeedGroup OBJECT IDENTIFIER ::= { ciscoIfExtensionMIBGroups 13 }
-- OBJECT-GROUP
--  Status
--    mandatory
--  Descr
--    An optional group used to provide information on asymmetrical
--    interface speeds.
--  objects
--    cieIfSpeedReceive, cieIfHighSpeedReceive

ciscoIfExtUtilIntervalGroup OBJECT IDENTIFIER ::= { ciscoIfExtensionMIBGroups 14 }
-- OBJECT-GROUP
--  Status
--    mandatory
--  Descr
--    A collection of objects containing
--    information about calculation interval for 
--    utilization rate on interfaces.
--  objects
--    cieIfInterval

cieIfIndexPersistenceGroup OBJECT IDENTIFIER ::= { ciscoIfExtensionMIBGroups 15 }
-- OBJECT-GROUP
--  Status
--    deprecated
--  Descr
--    A collection of objects containing information about ifIndex
--    Persistence of interfaces.
--    
--    Since cieIfIndexPersistence and cieIfIndexPersistenceEnabled are
--    deprecated, so, cieIfIndexPersistenceGroup containing these two
--    objects are deprecated by cieIfIndexPersistenceControlGroup.
--  objects
--    cieIfIndexPersistence, cieIfIndexPersistenceEnabled

cieDelayedLinkUpDownNotifNotifEnableGroup OBJECT IDENTIFIER ::= { ciscoIfExtensionMIBGroups 16 }
-- OBJECT-GROUP
--  Status
--    mandatory
--  Descr
--    The group of objects that help configure the
--    cieDelayedLinkUpDownNotif on the system.
--  objects
--    cieDelayedLinkUpDownNotifEnable, 
--    cieDelayedLinkUpDownNotifDelay

cieIfIndexPersistenceControlGroup OBJECT IDENTIFIER ::= { ciscoIfExtensionMIBGroups 18 }
-- OBJECT-GROUP
--  Status
--    mandatory
--  Descr
--    A collection of objects containing information about ifIndex
--    Persistence of interfaces.
--  objects
--    cieIfIndexGlobalPersistence, cieIfIndexPersistenceControl

ciscoIfExtensionTableIntfGroup3 OBJECT IDENTIFIER ::= { ciscoIfExtensionMIBGroups 19 }
-- OBJECT-GROUP
--  Status
--    mandatory
--  Descr
--    A collection of objects containing
--    information about properties of 
--    interfaces.
--  objects
--    cieIfDhcpMode, cieIfMtu, cieIfContextName, 
--    cieIfOperStatusCause, cieIfOperStatusCauseDescr, cieIfOwner

cieIfStatusListGroupSup1 OBJECT IDENTIFIER ::= { ciscoIfExtensionMIBGroups 20 }
-- OBJECT-GROUP
--  Status
--    mandatory
--  Descr
--    Additional objects containing information about a
--    set of interfaces.
--  objects
--    cieInterfaceOwnershipBitmap

cieIfVlStatsGroup OBJECT IDENTIFIER ::= { ciscoIfExtensionMIBGroups 21 }
-- OBJECT-GROUP
--  Status
--    mandatory
--  Descr
--    Objects containing information about a
--    VL (Virtual Link) statistics on an interface.
--  objects
--    cieIfNoDropVlInPkts, cieIfNoDropVlInOctets, 
--    cieIfNoDropVlOutPkts, cieIfNoDropVlOutOctets, 
--    cieIfDropVlInPkts, cieIfDropVlInOctets, cieIfDropVlOutPkts, 
--    cieIfDropVlOutOctets

ciscoIfExtensionTableIntfGroup3SupR01 OBJECT IDENTIFIER ::= { ciscoIfExtensionMIBGroups 22 }
-- OBJECT-GROUP
--  Status
--    mandatory
--  Descr
--    This group is supplement to ciscoIfExtensionTableIntfGroup3.
--  objects
--    cieIfSharedConfig, cieIfSpeedGroupConfig

cieLinkUpDownNotifConfigGroup OBJECT IDENTIFIER ::= { ciscoIfExtensionMIBGroups 23 }
-- OBJECT-GROUP
--  Status
--    mandatory
--  Descr
--    A collection of objects to control
--    'cieLinkUp/cieLinkDown' and standard mib-II 
--    defined 'linkUp/linkDown' notifications.
--  objects
--    cieLinkUpDownConfig

ciscoIfExtensionTableIntfGroup3SupR02 OBJECT IDENTIFIER ::= { ciscoIfExtensionMIBGroups 24 }
-- OBJECT-GROUP
--  Status
--    mandatory
--  Descr
--    This group is supplement to ciscoIfExtensionTableIntfGroup3SupR01.
--  objects
--    cieIfTransceiverFrequencyConfig, cieIfFillPatternConfig, 
--    cieIfIgnoreBitErrorsConfig, 
--    cieIfIgnoreInterruptThresholdConfig

cieLinkUpDownNotifGroup OBJECT IDENTIFIER ::= { ciscoIfExtensionMIBGroups 12 }
-- NOTIFICATION-GROUP
--  Status
--    mandatory
--  Descr
--    A collection of cisco specific linkUp and
--    linkDown notifications.
--  notifications
--    cieLinkDown, cieLinkUp

cieDelayedLinkUpDownNotifNotifGroup OBJECT IDENTIFIER ::= { ciscoIfExtensionMIBGroups 17 }
-- NOTIFICATION-GROUP
--  Status
--    mandatory
--  Descr
--    A collection for cisco specific delayed trap notifications.
--  notifications
--    cieDelayedLinkUpDownNotif

ciscoIfExtensionMIBCompliance OBJECT IDENTIFIER ::= { ciscoIfExtensionMIBCompliances 1 }
-- MODULE-COMPLIANCE
--  Status
--    deprecated
--  Descr
--    The compliance statement for entities which
--    implement the CISCO-IF-EXTENSION-MIB.
--  Module
--    >>current<<
--   MandGroup
--    ciscoIfExtensionTablePacketGroup
--   MandGroup
--    ciscoIfExtensionTableIntfGroup

ciscoIfExtensionMIBCompliance1 OBJECT IDENTIFIER ::= { ciscoIfExtensionMIBCompliances 2 }
-- MODULE-COMPLIANCE
--  Status
--    deprecated
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionTableIntfGroup1
--   OptGroup
--    ciscoIfExtensionSystemGroup
--   OptGroup
--    ciscoIfExtDot1qEtherTypeGroup
--   ObjVar
--    cieIfDhcpMode
--   ObjVar
--    cieIfMtu

ciscoIfExtensionMIBCompliance2 OBJECT IDENTIFIER ::= { ciscoIfExtensionMIBCompliances 3 }
-- MODULE-COMPLIANCE
--  Status
--    deprecated
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionTableIntfGroup1
--   OptGroup
--    ciscoIfExtensionSystemGroup
--   OptGroup
--    ciscoIfExtDot1qEtherTypeGroup
--   OptGroup
--    ciscoIfExtUtilizationGroup
--   OptGroup
--    ciscoIfExtDot1dBaseMappingGroup
--   ObjVar
--    cieIfDhcpMode
--   ObjVar
--    cieIfMtu

ciscoIfExtensionMIBCompliance3 OBJECT IDENTIFIER ::= { ciscoIfExtensionMIBCompliances 4 }
-- MODULE-COMPLIANCE
--  Status
--    deprecated
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionTableIntfGroup1
--   OptGroup
--    ciscoIfExtensionSystemGroup
--   OptGroup
--    ciscoIfExtDot1qEtherTypeGroup
--   OptGroup
--    ciscoIfExtUtilizationGroup
--   OptGroup
--    ciscoIfExtDot1dBaseMappingGroup
--   OptGroup
--    ciscoIfExtIfNameMappingGroup
--   ObjVar
--    cieIfDhcpMode
--   ObjVar
--    cieIfMtu

ciscoIfExtensionMIBCompliance4 OBJECT IDENTIFIER ::= { ciscoIfExtensionMIBCompliances 5 }
-- MODULE-COMPLIANCE
--  Status
--    deprecated
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionTableIntfGroup2
--   OptGroup
--    ciscoIfExtensionSystemGroup
--   OptGroup
--    ciscoIfExtDot1qEtherTypeGroup
--   OptGroup
--    ciscoIfExtUtilizationGroup
--   OptGroup
--    ciscoIfExtDot1dBaseMappingGroup
--   OptGroup
--    ciscoIfExtIfNameMappingGroup
--   OptGroup
--    cieIfStatusListGroup
--   ObjVar
--    cieIfDhcpMode
--   ObjVar
--    cieIfMtu

ciscoIfExtensionMIBCompliance5 OBJECT IDENTIFIER ::= { ciscoIfExtensionMIBCompliances 6 }
-- MODULE-COMPLIANCE
--  Status
--    deprecated
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionTableIntfGroup2
--   OptGroup
--    ciscoIfExtensionSystemGroup
--   OptGroup
--    ciscoIfExtDot1qEtherTypeGroup
--   OptGroup
--    ciscoIfExtUtilizationGroup
--   OptGroup
--    ciscoIfExtDot1dBaseMappingGroup
--   OptGroup
--    ciscoIfExtIfNameMappingGroup
--   OptGroup
--    cieIfStatusListGroup
--   OptGroup
--    cieLinkUpDownNotifEnableGroup
--   OptGroup
--    cieLinkUpDownNotifGroup
--   ObjVar
--    cieIfDhcpMode
--   ObjVar
--    cieIfMtu

ciscoIfExtensionMIBCompliance6 OBJECT IDENTIFIER ::= { ciscoIfExtensionMIBCompliances 7 }
-- MODULE-COMPLIANCE
--  Status
--    deprecated
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionTableIntfGroup2
--   OptGroup
--    ciscoIfExtensionSystemGroup
--   OptGroup
--    ciscoIfExtDot1qEtherTypeGroup
--   OptGroup
--    ciscoIfExtUtilizationGroup
--   OptGroup
--    ciscoIfExtDot1dBaseMappingGroup
--   OptGroup
--    ciscoIfExtIfNameMappingGroup
--   OptGroup
--    cieIfStatusListGroup
--   OptGroup
--    cieLinkUpDownNotifEnableGroup
--   OptGroup
--    cieLinkUpDownNotifGroup
--   OptGroup
--    ciscoIfExtensionAsymmetricalSpeedGroup
--   ObjVar
--    cieIfDhcpMode
--   ObjVar
--    cieIfMtu

ciscoIfExtensionMIBCompliance7 OBJECT IDENTIFIER ::= { ciscoIfExtensionMIBCompliances 8 }
-- MODULE-COMPLIANCE
--  Status
--    deprecated
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionTableIntfGroup2
--   OptGroup
--    ciscoIfExtensionSystemGroup
--   OptGroup
--    ciscoIfExtDot1qEtherTypeGroup
--   OptGroup
--    ciscoIfExtUtilizationGroup
--   OptGroup
--    ciscoIfExtDot1dBaseMappingGroup
--   OptGroup
--    ciscoIfExtIfNameMappingGroup
--   OptGroup
--    cieIfStatusListGroup
--   OptGroup
--    cieLinkUpDownNotifEnableGroup
--   OptGroup
--    cieLinkUpDownNotifGroup
--   OptGroup
--    ciscoIfExtensionAsymmetricalSpeedGroup
--   OptGroup
--    ciscoIfExtUtilIntervalGroup
--   ObjVar
--    cieIfDhcpMode
--   ObjVar
--    cieIfMtu

ciscoIfExtensionMIBCompliance8 OBJECT IDENTIFIER ::= { ciscoIfExtensionMIBCompliances 9 }
-- MODULE-COMPLIANCE
--  Status
--    deprecated
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionTableIntfGroup2
--   OptGroup
--    ciscoIfExtensionSystemGroup
--   OptGroup
--    ciscoIfExtDot1qEtherTypeGroup
--   OptGroup
--    ciscoIfExtUtilizationGroup
--   OptGroup
--    ciscoIfExtDot1dBaseMappingGroup
--   OptGroup
--    ciscoIfExtIfNameMappingGroup
--   OptGroup
--    cieIfStatusListGroup
--   OptGroup
--    cieLinkUpDownNotifEnableGroup
--   OptGroup
--    cieLinkUpDownNotifGroup
--   OptGroup
--    ciscoIfExtensionAsymmetricalSpeedGroup
--   OptGroup
--    ciscoIfExtUtilIntervalGroup
--   OptGroup
--    cieIfIndexPersistenceGroup
--   ObjVar
--    cieIfDhcpMode
--   ObjVar
--    cieIfMtu

ciscoIfExtensionMIBCompliance9 OBJECT IDENTIFIER ::= { ciscoIfExtensionMIBCompliances 10 }
-- MODULE-COMPLIANCE
--  Status
--    deprecated
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionTableIntfGroup2
--   OptGroup
--    ciscoIfExtensionSystemGroup
--   OptGroup
--    ciscoIfExtDot1qEtherTypeGroup
--   OptGroup
--    ciscoIfExtUtilizationGroup
--   OptGroup
--    ciscoIfExtDot1dBaseMappingGroup
--   OptGroup
--    ciscoIfExtIfNameMappingGroup
--   OptGroup
--    cieIfStatusListGroup
--   OptGroup
--    cieLinkUpDownNotifEnableGroup
--   OptGroup
--    cieLinkUpDownNotifGroup
--   OptGroup
--    ciscoIfExtensionAsymmetricalSpeedGroup
--   OptGroup
--    ciscoIfExtUtilIntervalGroup
--   OptGroup
--    cieDelayedLinkUpDownNotifNotifGroup
--   OptGroup
--    cieDelayedLinkUpDownNotifNotifEnableGroup
--   ObjVar
--    cieIfDhcpMode
--   ObjVar
--    cieIfMtu

ciscoIfExtensionMIBCompliance10 OBJECT IDENTIFIER ::= { ciscoIfExtensionMIBCompliances 11 }
-- MODULE-COMPLIANCE
--  Status
--    deprecated
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionTableIntfGroup2
--   OptGroup
--    ciscoIfExtensionSystemGroup
--   OptGroup
--    ciscoIfExtDot1qEtherTypeGroup
--   OptGroup
--    ciscoIfExtUtilizationGroup
--   OptGroup
--    ciscoIfExtDot1dBaseMappingGroup
--   OptGroup
--    ciscoIfExtIfNameMappingGroup
--   OptGroup
--    cieIfStatusListGroup
--   OptGroup
--    cieLinkUpDownNotifEnableGroup
--   OptGroup
--    cieLinkUpDownNotifGroup
--   OptGroup
--    ciscoIfExtensionAsymmetricalSpeedGroup
--   OptGroup
--    ciscoIfExtUtilIntervalGroup
--   OptGroup
--    cieDelayedLinkUpDownNotifNotifGroup
--   OptGroup
--    cieDelayedLinkUpDownNotifNotifEnableGroup
--   OptGroup
--    cieIfIndexPersistenceControlGroup
--   ObjVar
--    cieIfDhcpMode
--   ObjVar
--    cieIfMtu

ciscoIfExtensionMIBCompliance11 OBJECT IDENTIFIER ::= { ciscoIfExtensionMIBCompliances 12 }
-- MODULE-COMPLIANCE
--  Status
--    deprecated
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionSystemGroup
--   OptGroup
--    ciscoIfExtDot1qEtherTypeGroup
--   OptGroup
--    ciscoIfExtUtilizationGroup
--   OptGroup
--    ciscoIfExtDot1dBaseMappingGroup
--   OptGroup
--    ciscoIfExtIfNameMappingGroup
--   OptGroup
--    cieIfStatusListGroup
--   OptGroup
--    cieLinkUpDownNotifEnableGroup
--   OptGroup
--    cieLinkUpDownNotifGroup
--   OptGroup
--    ciscoIfExtensionAsymmetricalSpeedGroup
--   OptGroup
--    ciscoIfExtUtilIntervalGroup
--   OptGroup
--    cieDelayedLinkUpDownNotifNotifGroup
--   OptGroup
--    cieDelayedLinkUpDownNotifNotifEnableGroup
--   OptGroup
--    cieIfIndexPersistenceControlGroup
--   OptGroup
--    ciscoIfExtensionTableIntfGroup3
--   ObjVar
--    cieIfDhcpMode
--   ObjVar
--    cieIfMtu

ciscoIfExtensionMIBCompliance12 OBJECT IDENTIFIER ::= { ciscoIfExtensionMIBCompliances 13 }
-- MODULE-COMPLIANCE
--  Status
--    deprecated
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionSystemGroup
--   OptGroup
--    ciscoIfExtDot1qEtherTypeGroup
--   OptGroup
--    ciscoIfExtUtilizationGroup
--   OptGroup
--    ciscoIfExtDot1dBaseMappingGroup
--   OptGroup
--    ciscoIfExtIfNameMappingGroup
--   OptGroup
--    cieLinkUpDownNotifEnableGroup
--   OptGroup
--    cieLinkUpDownNotifGroup
--   OptGroup
--    ciscoIfExtensionAsymmetricalSpeedGroup
--   OptGroup
--    ciscoIfExtUtilIntervalGroup
--   OptGroup
--    cieDelayedLinkUpDownNotifNotifGroup
--   OptGroup
--    cieDelayedLinkUpDownNotifNotifEnableGroup
--   OptGroup
--    cieIfIndexPersistenceControlGroup
--   OptGroup
--    ciscoIfExtensionTableIntfGroup3
--   OptGroup
--    cieIfStatusListGroup
--   OptGroup
--    cieIfStatusListGroupSup1
--   ObjVar
--    cieIfDhcpMode
--   ObjVar
--    cieIfMtu

ciscoIfExtensionMIBCompliance13 OBJECT IDENTIFIER ::= { ciscoIfExtensionMIBCompliances 14 }
-- MODULE-COMPLIANCE
--  Status
--    deprecated
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionSystemGroup
--   OptGroup
--    ciscoIfExtDot1qEtherTypeGroup
--   OptGroup
--    ciscoIfExtUtilizationGroup
--   OptGroup
--    ciscoIfExtDot1dBaseMappingGroup
--   OptGroup
--    ciscoIfExtIfNameMappingGroup
--   OptGroup
--    cieLinkUpDownNotifEnableGroup
--   OptGroup
--    cieLinkUpDownNotifGroup
--   OptGroup
--    ciscoIfExtensionAsymmetricalSpeedGroup
--   OptGroup
--    ciscoIfExtUtilIntervalGroup
--   OptGroup
--    cieDelayedLinkUpDownNotifNotifGroup
--   OptGroup
--    cieDelayedLinkUpDownNotifNotifEnableGroup
--   OptGroup
--    cieIfIndexPersistenceControlGroup
--   OptGroup
--    cieIfStatusListGroup
--   OptGroup
--    cieIfStatusListGroupSup1
--   OptGroup
--    cieIfVlStatsGroup
--   OptGroup
--    ciscoIfExtensionTableIntfGroup3
--   OptGroup
--    ciscoIfExtensionTableIntfGroup3SupR01
--   ObjVar
--    cieIfDhcpMode
--   ObjVar
--    cieIfMtu
--   ObjVar
--    cieIfSpeedGroupConfig

ciscoIfExtensionMIBCompliance14 OBJECT IDENTIFIER ::= { ciscoIfExtensionMIBCompliances 15 }
-- MODULE-COMPLIANCE
--  Status
--    deprecated
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionSystemGroup
--   OptGroup
--    ciscoIfExtDot1qEtherTypeGroup
--   OptGroup
--    ciscoIfExtUtilizationGroup
--   OptGroup
--    ciscoIfExtDot1dBaseMappingGroup
--   OptGroup
--    ciscoIfExtIfNameMappingGroup
--   OptGroup
--    cieLinkUpDownNotifGroup
--   OptGroup
--    ciscoIfExtensionAsymmetricalSpeedGroup
--   OptGroup
--    ciscoIfExtUtilIntervalGroup
--   OptGroup
--    cieDelayedLinkUpDownNotifNotifGroup
--   OptGroup
--    cieDelayedLinkUpDownNotifNotifEnableGroup
--   OptGroup
--    cieIfIndexPersistenceControlGroup
--   OptGroup
--    cieIfStatusListGroup
--   OptGroup
--    cieIfStatusListGroupSup1
--   OptGroup
--    cieIfVlStatsGroup
--   OptGroup
--    ciscoIfExtensionTableIntfGroup3
--   OptGroup
--    ciscoIfExtensionTableIntfGroup3SupR01
--   OptGroup
--    cieLinkUpDownNotifConfigGroup
--   ObjVar
--    cieIfDhcpMode
--   ObjVar
--    cieIfMtu
--   ObjVar
--    cieIfSpeedGroupConfig

ciscoIfExtensionMIBCompliance15 OBJECT IDENTIFIER ::= { ciscoIfExtensionMIBCompliances 16 }
-- MODULE-COMPLIANCE
--  Status
--    mandatory
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionSystemGroup
--   OptGroup
--    ciscoIfExtDot1qEtherTypeGroup
--   OptGroup
--    ciscoIfExtUtilizationGroup
--   OptGroup
--    ciscoIfExtDot1dBaseMappingGroup
--   OptGroup
--    ciscoIfExtIfNameMappingGroup
--   OptGroup
--    cieLinkUpDownNotifGroup
--   OptGroup
--    ciscoIfExtensionAsymmetricalSpeedGroup
--   OptGroup
--    ciscoIfExtUtilIntervalGroup
--   OptGroup
--    cieDelayedLinkUpDownNotifNotifGroup
--   OptGroup
--    cieDelayedLinkUpDownNotifNotifEnableGroup
--   OptGroup
--    cieIfIndexPersistenceControlGroup
--   OptGroup
--    cieIfStatusListGroup
--   OptGroup
--    cieIfStatusListGroupSup1
--   OptGroup
--    cieIfVlStatsGroup
--   OptGroup
--    ciscoIfExtensionTableIntfGroup3
--   OptGroup
--    ciscoIfExtensionTableIntfGroup3SupR01
--   OptGroup
--    ciscoIfExtensionTableIntfGroup3SupR02
--   OptGroup
--    cieLinkUpDownNotifConfigGroup
--   ObjVar
--    cieIfDhcpMode
--   ObjVar
--    cieIfMtu
--   ObjVar
--    cieIfSpeedGroupConfig
--   ObjVar
--    cieIfTransceiverFrequencyConfig
--   ObjVar
--    cieIfFillPatternConfig
--   ObjVar
--    cieIfIgnoreBitErrorsConfig
--   ObjVar
--    cieIfIgnoreInterruptThresholdConfig


END
