-- MIB file created 26-Jul-2013 16:27:58, by
--   SMICng version 2.2.11-beta(PRO)(Solaris), January 20, 2001. Enterprise key cisco.com

CISCO-VLAN-IFTABLE-RELATIONSHIP-MIB DEFINITIONS ::= BEGIN

-- From file: "CISCO-VLAN-IFTABLE-RELATIONSHIP-MIB.my"
-- Compile options "4 7 F H N W 03 06 0B 0G 0N 0T"

IMPORTS
    InterfaceIndex
            FROM IF-MIB
    InterfaceIndexOrZero
            FROM CISCO-TC
    VlanIndex
            FROM CISCO-VTP-MIB
    ciscoMgmt
            FROM CISCO-SMI
    OBJECT-TYPE
            FROM RFC-1212;

ciscoVlanIfTableRelationshipMIB OBJECT IDENTIFIER ::= { ciscoMgmt 811 }
-- MODULE-IDENTITY
--  LastUpdated
--    201307150000Z
--  OrgName
--    Cisco Systems, Inc.
--  ContactInfo
--    Cisco Systems
--    Customer Service
--    
--    Postal: 170 W Tasman Drive
--            San Jose, CA  95134
--            USA
--    
--    Tel: +1 800 553-NETS
--    
--    E-mail: cs-snmp@cisco.com
--  Descr
--    Cisco VLAN ifTable Relationship MIB lists VLAN-id and ifIndex
--    information for routed VLAN interfaces.  
--    
--    A routed VLAN interface is the router interface or sub-interface 
--    to which the router's IP address on the VLAN is attached.  
--    For example, an ISL, SDE, or 802.1Q encapsulated
--    subinterface, or Switched Virtual Interface (SVI).
--  RevDate
--    201307150000Z
--  RevDescr
--    Initial version of this MIB module.

cviMIBObjects   OBJECT IDENTIFIER ::= { ciscoVlanIfTableRelationshipMIB 1 }
cviGlobals      OBJECT IDENTIFIER ::= { cviMIBObjects 1 }
cviMIBConformance OBJECT IDENTIFIER ::= { cviMIBObjects 3 }
cviMIBCompliances OBJECT IDENTIFIER ::= { cviMIBConformance 1 }
cviMIBGroups    OBJECT IDENTIFIER ::= { cviMIBConformance 2 }

cviVlanInterfaceIndexTable OBJECT-TYPE
    SYNTAX SEQUENCE OF CviVlanInterfaceIndexEntry
    ACCESS not-accessible
    STATUS mandatory
    DESCRIPTION
        "The cviVlanInterfaceIndexTable provides a way to
        translate a VLAN-id in to an ifIndex, so that 
        the routed VLAN interface's routing configuration 
        can be obtained from interface entry in ipRouteTable.
        
        Note that some routers can have interfaces to multiple
        VLAN management domains, and therefore can have multiple 
        routed VLAN interfaces which connect to different VLANs 
        having the same VLAN-id.  Thus, it is possible to have 
        multiple rows in this table for the same VLAN-id.
        
        The cviVlanInterfaceIndexTable also provides a way
        to find the VLAN-id from an ifTable VLAN's ifIndex."
    ::= { cviGlobals 1 }

cviVlanInterfaceIndexEntry OBJECT-TYPE
    SYNTAX CviVlanInterfaceIndexEntry
    ACCESS not-accessible
    STATUS mandatory
    DESCRIPTION
        "Each entry represents a routed VLAN interface, its
        corresponding physical port if any, and the ifTable entry
        for the routed VLAN interface.
        
        Entries are created by the agent when the routed VLAN interface
        is created.  Operational status of routing does not affect
        the entries listed here.  For routing configuration please refer
        to ipRouteTable.
        
        Entries are deleted by the agent when the routed VLAN interface
        is removed from the system configuration."
    INDEX { cviVlanId, cviPhysicalIfIndex }
    ::= { cviVlanInterfaceIndexTable 1 }

CviVlanInterfaceIndexEntry ::= SEQUENCE {
    cviVlanId VlanIndex,
    cviPhysicalIfIndex InterfaceIndexOrZero,
    cviRoutedVlanIfIndex InterfaceIndex
    }

cviVlanId OBJECT-TYPE
    SYNTAX VlanIndex
--    Rsyntax INTEGER(0..4095)
    ACCESS not-accessible
    STATUS mandatory
    DESCRIPTION
        "The VLAN-id number of the routed VLAN interface."
    ::= { cviVlanInterfaceIndexEntry 1 }

cviPhysicalIfIndex OBJECT-TYPE
    SYNTAX InterfaceIndexOrZero
--    Rsyntax INTEGER(0..2147483647)
    ACCESS not-accessible
    STATUS mandatory
    DESCRIPTION
        "For subinterfaces, this object is the ifIndex of the
        physical interface for the subinterface.
        
        For Switch Virtual Interfaces (SVIs), this object is zero."
    ::= { cviVlanInterfaceIndexEntry 2 }

cviRoutedVlanIfIndex OBJECT-TYPE
    SYNTAX InterfaceIndex
--    Rsyntax INTEGER(1..2147483647)
    ACCESS read-only
    STATUS mandatory
    DESCRIPTION
        "The index for the ifTable entry associated with
        this routed VLAN interface."
    ::= { cviVlanInterfaceIndexEntry 3 }

cviMIBGroup OBJECT IDENTIFIER ::= { cviMIBGroups 1 }
-- OBJECT-GROUP
--  Status
--    mandatory
--  Descr
--    A set of objects to obtain VLAN-ID and ifIndex
--    information for routed VLAN interfaces.
--  objects
--    cviRoutedVlanIfIndex

cviMIBCompliance OBJECT IDENTIFIER ::= { cviMIBCompliances 1 }
-- MODULE-COMPLIANCE
--  Status
--    mandatory
--  Descr
--    The compliance statement for entities which implement
--    the CISCO-VLAN-INTERFACE-MIB
--  Module
--    >>current<<
--   MandGroup
--    cviMIBGroup


END
