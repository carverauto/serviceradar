-- MIB file created 21-Sep-2015 03:33:08, by
--   SMICng version 2.2.11-beta(PRO)(Solaris), January 20, 2001. Enterprise key cisco.com

CISCO-QP-LBG-MIB DEFINITIONS ::= BEGIN

-- From file: "CISCO-QP-LBG-MIB.my"
-- Compile options "4 7 F H N W 03 06 0B 0G 0N 0T"

IMPORTS
    InetAddress, InetAddressType
            FROM INET-ADDRESS-MIB
    MacAddress, TruthValue
            FROM SNMPv2-TC-v1
    entPhysicalIndex
            FROM ENTITY-MIB
    ifDescr
            FROM IF-MIB
    ciscoMgmt
            FROM CISCO-SMI
    Gauge
            FROM RFC1155-SMI
    OBJECT-TYPE
            FROM RFC-1212
    TRAP-TYPE
            FROM RFC-1215;

ciscoQpLbgMIB OBJECT IDENTIFIER ::= { ciscoMgmt 824 }
-- MODULE-IDENTITY
--  LastUpdated
--    201509210000Z
--  OrgName
--    Cisco Systems, Inc.
--  ContactInfo
--    Cisco Systems
--    Customer Service
--    
--    Postal: 170 W Tasman Drive
--            San Jose, CA  95134
--            USA
--    
--    Tel: +1 800 553-NETS
--    
--    E-mail: cs-rfgw10@cisco.com
--  Descr
--    This MIB module represents the Qam-Partition (QP) and Load
--    Balance Group (LBG) parameters in  the headend and it is 
--    supported by an snmp agent. It defines objects for managing 
--    both QP and LBG.
--  RevDate
--    201509210000Z
--  RevDescr
--    The table cqlqamPartitionTable describes the various
--    parameters of QP such as QP's state, protocol,
--    management IP, server IP, server state, associated 
--    QAM details and configured video route details.
--    
--    The table cqlloadBalanceGroupTable describes the LBG 
--    parameters such as total bandwidth, available bandwidth 
--    and reserved bandwidth of QAM & IP based sessions.
--    
--    The table cqllbgrouteTable describes the destination IP, 
--    udp range, reserved bandwidth of routes configured under 
--    LBG and flow count per route.
--    
--    Following objects were added to the MIB to provide trap 
--    notification support for the over subscribed Qam.
--    
--    cqlQamOverSubscribedAlert
--    cqlQamOverSubscribedEnable
--    
--    Added object cqlqpServerIpList of type OCTET STRING for
--    displaying multiple server IP's.
--  RevDate
--    201408270000Z
--  RevDescr
--    Latest version of this MIB module.

ciscoQpLbgNotifs OBJECT IDENTIFIER ::= { ciscoQpLbgMIB 0 }
ciscoQpLbgObjects OBJECT IDENTIFIER ::= { ciscoQpLbgMIB 1 }
ciscoQpLbgConform OBJECT IDENTIFIER ::= { ciscoQpLbgMIB 2 }
ciscoQpLbgCompliances OBJECT IDENTIFIER ::= { ciscoQpLbgConform 1 }
ciscoQpLbgGroups OBJECT IDENTIFIER ::= { ciscoQpLbgConform 2 }

cqlqamPartitionTable OBJECT-TYPE
    SYNTAX SEQUENCE OF CqlqamPartitionEntry
    ACCESS not-accessible
    STATUS mandatory
    DESCRIPTION
        "This table describes the various parameters of QP
        such as QP's state, protocol, management IP, server IP,
        server state, information related to qam and video routes."
    ::= { ciscoQpLbgObjects 1 }

cqlqamPartitionEntry OBJECT-TYPE
    SYNTAX CqlqamPartitionEntry
    ACCESS not-accessible
    STATUS mandatory
    DESCRIPTION
        "Each entry corresponds to the configuration of a QP."
    INDEX { cqlqpIndex }
    ::= { cqlqamPartitionTable 1 }

CqlqamPartitionEntry ::= SEQUENCE {
    cqlqpIndex Gauge,
    cqlqpId Gauge,
    cqlqpMgmtIpAddrType InetAddressType,
    cqlqpMgmtIp InetAddress,
    cqlqpServerIpAddrType InetAddressType,
    cqlqpServerIp InetAddress,
    cqlqpState INTEGER,
    cqlqpProtocol INTEGER,
    cqlqpKeepAliveTime Gauge,
    cqlqpServerState INTEGER,
    cqlqpGqiMacAddr MacAddress,
    cqlqpGqiResetInterval Gauge,
    cqlqpNumQams Gauge,
    cqlqpQamCarrrierList OCTET STRING,
    cqlqpNumRoutes Gauge,
    cqlqpRouteDetails OCTET STRING,
    cqlqpErmiErrpComponentName OCTET STRING,
    cqlqpErmiErrpStreamingZone OCTET STRING,
    cqlqpErmiErrpHoldTime Gauge,
    cqlqpErmiErrpConnnectTime Gauge,
    cqlqpErmiErrpConnectRetry Gauge,
    cqlqpErmiRtspConnectTime Gauge,
    cqlqpErmiRtspConnectRetry Gauge,
    cqlqpErmiRtspKeepAliveTime Gauge,
    cqlqpErmiRtspSessionTimeout Gauge,
    cqlqpQamOversubscribedStatus TruthValue,
    cqlqpServerIpList OCTET STRING
    }

cqlqpIndex OBJECT-TYPE
    SYNTAX Gauge
    ACCESS not-accessible
    STATUS mandatory
    DESCRIPTION
        "Table Index. This index uniquely identifies the QP."
    ::= { cqlqamPartitionEntry 1 }

cqlqpId OBJECT-TYPE
    SYNTAX Gauge
    ACCESS read-only
    STATUS mandatory
    DESCRIPTION
        "This object specifies the QP Id."
    ::= { cqlqamPartitionEntry 2 }

cqlqpMgmtIpAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "The type of the Management address as defined inetAddressType.
        The supported address types are IPv4 and IPv6."
    DEFVAL { ipv4 }
    ::= { cqlqamPartitionEntry 3 }

cqlqpMgmtIp OBJECT-TYPE
    SYNTAX InetAddress
--    Rsyntax OCTET STRING(SIZE(0..255))
    ACCESS read-only
    STATUS mandatory
    DESCRIPTION
        "This object specifies the Management IP address of a QP."
    ::= { cqlqamPartitionEntry 4 }

cqlqpServerIpAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "The type of the Server address as defined inetAddressType. The
        supported address types are IPv4 and IPv6."
    ::= { cqlqamPartitionEntry 5 }

cqlqpServerIp OBJECT-TYPE
    SYNTAX InetAddress
--    Rsyntax OCTET STRING(SIZE(0..255))
    ACCESS read-only
    STATUS mandatory
    DESCRIPTION
        "Server IP of the QP."
    ::= { cqlqamPartitionEntry 6 }

cqlqpState OBJECT-TYPE
    SYNTAX INTEGER {
        inactive(1),
        init(2),
        active(3)
        }
    ACCESS read-only
    STATUS mandatory
    DESCRIPTION
        "This object specifies the state of the QP. The following are
        the valid states. 
        
        inactive(1) 
                   QP is in inactive state.
        init(2) 
                   QP is in init state.
        active(3) 
                   QP is in active state."
    ::= { cqlqamPartitionEntry 7 }

cqlqpProtocol OBJECT-TYPE
    SYNTAX INTEGER {
        gqi(1),
        ermi(2)
        }
    ACCESS read-only
    STATUS mandatory
    DESCRIPTION
        "This object specifies the QP Protocol.
        
        Gqi(1)
        Ermi(2)"
    ::= { cqlqamPartitionEntry 8 }

cqlqpKeepAliveTime OBJECT-TYPE
    SYNTAX Gauge
--  Units
--    seconds
    ACCESS read-only
    STATUS mandatory
    DESCRIPTION
        "This object specifies the keepalive timer in
        seconds for a QP."
    ::= { cqlqamPartitionEntry 9 }

cqlqpServerState OBJECT-TYPE
    SYNTAX INTEGER {
        disconnected(1),
        connected(2)
        }
    ACCESS read-only
    STATUS mandatory
    DESCRIPTION
        "This object specifies the Server state of the QP.
        
        disconnected(1)
                      Server is in disconnected state.
        connected(2) 
                      Server is in connected state."
    ::= { cqlqamPartitionEntry 10 }

cqlqpGqiMacAddr OBJECT-TYPE
    SYNTAX MacAddress
--    Rsyntax OCTET STRING(SIZE(6))
    ACCESS read-only
    STATUS mandatory
    DESCRIPTION
        "This object specifies the MAC address of a QP, applicable only
        for GQI Protocol."
    ::= { cqlqamPartitionEntry 11 }

cqlqpGqiResetInterval OBJECT-TYPE
    SYNTAX Gauge
--  Units
--    seconds
    ACCESS read-only
    STATUS mandatory
    DESCRIPTION
        "This object specifies Reset interval for a QP. It is applicable
        only for GQI protocol."
    ::= { cqlqamPartitionEntry 12 }

cqlqpNumQams OBJECT-TYPE
    SYNTAX Gauge
    ACCESS read-only
    STATUS mandatory
    DESCRIPTION
        "The total number of qams associated with the QP."
    ::= { cqlqamPartitionEntry 13 }

cqlqpQamCarrrierList OBJECT-TYPE
    SYNTAX OCTET STRING
    ACCESS read-only
    STATUS mandatory
    DESCRIPTION
        "This object specifies the list of Qam carriers associated with
        the QP."
    ::= { cqlqamPartitionEntry 14 }

cqlqpNumRoutes OBJECT-TYPE
    SYNTAX Gauge
    ACCESS read-only
    STATUS mandatory
    DESCRIPTION
        "The total number of routes associated with the QP."
    ::= { cqlqamPartitionEntry 15 }

cqlqpRouteDetails OBJECT-TYPE
    SYNTAX OCTET STRING
    ACCESS read-only
    STATUS mandatory
    DESCRIPTION
        "Route details of the QP. It includes the configured IP and also
        the highest and lowest UDP range."
    ::= { cqlqamPartitionEntry 16 }

cqlqpErmiErrpComponentName OBJECT-TYPE
    SYNTAX OCTET STRING
    ACCESS read-only
    STATUS mandatory
    DESCRIPTION
        "Component Name for the QP, applicable only for ERMI protocol."
    ::= { cqlqamPartitionEntry 17 }

cqlqpErmiErrpStreamingZone OBJECT-TYPE
    SYNTAX OCTET STRING
    ACCESS read-only
    STATUS mandatory
    DESCRIPTION
        "Streaming zone for the QP, applicable only for ERMI protocol."
    ::= { cqlqamPartitionEntry 18 }

cqlqpErmiErrpHoldTime OBJECT-TYPE
    SYNTAX Gauge
--  Units
--    seconds
    ACCESS read-only
    STATUS mandatory
    DESCRIPTION
        "Hold Time in seconds for the QP, applicable only for ERMI
        protocol."
    DEFVAL { 90 }
    ::= { cqlqamPartitionEntry 19 }

cqlqpErmiErrpConnnectTime OBJECT-TYPE
    SYNTAX Gauge
--  Units
--    seconds
    ACCESS read-only
    STATUS mandatory
    DESCRIPTION
        "Connect Time in seconds for the QP, applicable only for ERMI
        protocol."
    DEFVAL { 10 }
    ::= { cqlqamPartitionEntry 20 }

cqlqpErmiErrpConnectRetry OBJECT-TYPE
    SYNTAX Gauge
--  Units
--    seconds
    ACCESS read-only
    STATUS mandatory
    DESCRIPTION
        "Connection retry in seconds for the QP. It is applicable only
        for ERMI protocol."
    DEFVAL { 0 }
    ::= { cqlqamPartitionEntry 21 }

cqlqpErmiRtspConnectTime OBJECT-TYPE
    SYNTAX Gauge
--  Units
--    seconds
    ACCESS read-only
    STATUS mandatory
    DESCRIPTION
        "Connect time in seconds for the QP. It is applicable only for
        ERMI protocol."
    DEFVAL { 200 }
    ::= { cqlqamPartitionEntry 22 }

cqlqpErmiRtspConnectRetry OBJECT-TYPE
    SYNTAX Gauge
--  Units
--    seconds
    ACCESS read-only
    STATUS mandatory
    DESCRIPTION
        "Connect retry in seconds for the QP, applicable
        only for ERMI protocol."
    DEFVAL { 0 }
    ::= { cqlqamPartitionEntry 23 }

cqlqpErmiRtspKeepAliveTime OBJECT-TYPE
    SYNTAX Gauge
--  Units
--    seconds
    ACCESS read-only
    STATUS mandatory
    DESCRIPTION
        "Connection timeout in seconds for the QP. It is applicable only
        for ERMI protocol."
    DEFVAL { 300 }
    ::= { cqlqamPartitionEntry 24 }

cqlqpErmiRtspSessionTimeout OBJECT-TYPE
    SYNTAX Gauge
--  Units
--    seconds
    ACCESS read-only
    STATUS mandatory
    DESCRIPTION
        "Session Timeout in seconds for the QP. It is applicable
        only for ERMI protocol."
    DEFVAL { 10800 }
    ::= { cqlqamPartitionEntry 25 }

cqlqpQamOversubscribedStatus OBJECT-TYPE
    SYNTAX TruthValue
--    Rsyntax INTEGER {
--        true(1),
--        false(2)
--        }
    ACCESS read-only
    STATUS mandatory
    DESCRIPTION
        "This object specifies oversubscription status of a Qam.
        The value 'True' indicates the Qam is oversubscribed.
        Otherwise the value 'False' is reported."
    DEFVAL { false }
    ::= { cqlqamPartitionEntry 26 }

cqlqpServerIpList OBJECT-TYPE
    SYNTAX OCTET STRING
    ACCESS read-only
    STATUS mandatory
    DESCRIPTION
        "List of Server IP's for the QP."
    ::= { cqlqamPartitionEntry 27 }

cqlloadBalanceGroupTable OBJECT-TYPE
    SYNTAX SEQUENCE OF CqlloadBalanceGroupEntry
    ACCESS not-accessible
    STATUS mandatory
    DESCRIPTION
        "This table describes the total bandwidth and the
        reserved bandwidth of QAM/IP based sessions."
    ::= { ciscoQpLbgObjects 2 }

cqlloadBalanceGroupEntry OBJECT-TYPE
    SYNTAX CqlloadBalanceGroupEntry
    ACCESS not-accessible
    STATUS mandatory
    DESCRIPTION
        "Each entry corresponds to the parameters of a LBG."
    INDEX { entPhysicalIndex, cqllbgIndex }
    ::= { cqlloadBalanceGroupTable 1 }

CqlloadBalanceGroupEntry ::= SEQUENCE {
    cqllbgIndex Gauge,
    cqllbgTotalBandwidth Gauge,
    cqllbgQamRsvBandwidth Gauge,
    cqllbgIpRsvBandwidth Gauge,
    cqllbgAvailableBandwidth Gauge
    }

cqllbgIndex OBJECT-TYPE
    SYNTAX Gauge
    ACCESS not-accessible
    STATUS mandatory
    DESCRIPTION
        "This index is to identify the LBG group within the slot."
    ::= { cqlloadBalanceGroupEntry 1 }

cqllbgTotalBandwidth OBJECT-TYPE
    SYNTAX Gauge
--  Units
--    Kbps
    ACCESS read-only
    STATUS mandatory
    DESCRIPTION
        "This object specifies the total bandwidth in Kbps of a LBG."
    ::= { cqlloadBalanceGroupEntry 2 }

cqllbgQamRsvBandwidth OBJECT-TYPE
    SYNTAX Gauge
--  Units
--    Kbps
    ACCESS read-only
    STATUS mandatory
    DESCRIPTION
        "This object specifies the total reserved bandwidth in Kbps for
        depi sessions."
    ::= { cqlloadBalanceGroupEntry 3 }

cqllbgIpRsvBandwidth OBJECT-TYPE
    SYNTAX Gauge
--  Units
--    Kbps
    ACCESS read-only
    STATUS mandatory
    DESCRIPTION
        "This object specifies the total reserved bandwidth
        in Kbps for video sessions."
    ::= { cqlloadBalanceGroupEntry 4 }

cqllbgAvailableBandwidth OBJECT-TYPE
    SYNTAX Gauge
--  Units
--    Kbps
    ACCESS read-only
    STATUS mandatory
    DESCRIPTION
        "This object specifies the available bandwidth in Kbps. This may
        be calculated as (TotalBandwidth - (QamRsvBandwidth +
        IpRsvBandwith))."
    ::= { cqlloadBalanceGroupEntry 5 }

cqllbgrouteTable OBJECT-TYPE
    SYNTAX SEQUENCE OF CqllbgrouteEntry
    ACCESS not-accessible
    STATUS mandatory
    DESCRIPTION
        "This table describes the route parameters such as
        QP id,destination ip, low and high udp range, reserved and
        allocated bandwidth."
    ::= { ciscoQpLbgObjects 3 }

cqllbgrouteEntry OBJECT-TYPE
    SYNTAX CqllbgrouteEntry
    ACCESS not-accessible
    STATUS mandatory
    DESCRIPTION
        "Each entry corresponds to the parameters of a route."
    INDEX { entPhysicalIndex, cqllbgRouteIndex }
    ::= { cqllbgrouteTable 1 }

CqllbgrouteEntry ::= SEQUENCE {
    cqllbgRouteIndex Gauge,
    cqllbgQpId Gauge,
    cqllbgDstIpAddrType InetAddressType,
    cqllbgDstIpAddr InetAddress,
    cqllbgUdpPortRangeMin Gauge,
    cqllbgUdpPortRangeMax Gauge,
    cqllbgGqiIngressPort Gauge,
    cqllbgRsvBandwidth Gauge,
    cqllbgAllocatedBandwidth Gauge,
    cqllbgNumFlows Gauge
    }

cqllbgRouteIndex OBJECT-TYPE
    SYNTAX Gauge
    ACCESS not-accessible
    STATUS mandatory
    DESCRIPTION
        "The table index. This is the index which uniquely identifies
        the
        route within the LBG group."
    ::= { cqllbgrouteEntry 1 }

cqllbgQpId OBJECT-TYPE
    SYNTAX Gauge
    ACCESS read-only
    STATUS mandatory
    DESCRIPTION
        "This object specifies the QP ID. The range of the QP is between
        1 and 50."
    ::= { cqllbgrouteEntry 2 }

cqllbgDstIpAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "The type of the destination address as defined inetAddressType.
        The supported address types are IPv4 and IPv6."
    DEFVAL { ipv4 }
    ::= { cqllbgrouteEntry 3 }

cqllbgDstIpAddr OBJECT-TYPE
    SYNTAX InetAddress
--    Rsyntax OCTET STRING(SIZE(0..255))
    ACCESS read-only
    STATUS mandatory
    DESCRIPTION
        "Destination IP address of the route to which the incoming
        packets are routed to."
    ::= { cqllbgrouteEntry 4 }

cqllbgUdpPortRangeMin OBJECT-TYPE
    SYNTAX Gauge
    ACCESS read-only
    STATUS mandatory
    DESCRIPTION
        "The lowest UDP port of the UDP port range that can be used."
    ::= { cqllbgrouteEntry 5 }

cqllbgUdpPortRangeMax OBJECT-TYPE
    SYNTAX Gauge
    ACCESS read-only
    STATUS mandatory
    DESCRIPTION
        "The highest UDP port of the UDP port range that can be used."
    ::= { cqllbgrouteEntry 6 }

cqllbgGqiIngressPort OBJECT-TYPE
    SYNTAX Gauge
    ACCESS read-only
    STATUS mandatory
    DESCRIPTION
        "Ingress port of a QP, applicable only for GQI protocol."
    ::= { cqllbgrouteEntry 7 }

cqllbgRsvBandwidth OBJECT-TYPE
    SYNTAX Gauge
--  Units
--    Kbps
    ACCESS read-only
    STATUS mandatory
    DESCRIPTION
        "Reserved bandwidth is the total bitrate reserved on
        this route in Kbps."
    ::= { cqllbgrouteEntry 8 }

cqllbgAllocatedBandwidth OBJECT-TYPE
    SYNTAX Gauge
--  Units
--    Kbps
    ACCESS read-only
    STATUS mandatory
    DESCRIPTION
        "The total bandwidth being used by sessions using this route in
        Kbps."
    ::= { cqllbgrouteEntry 9 }

cqllbgNumFlows OBJECT-TYPE
    SYNTAX Gauge
    ACCESS read-only
    STATUS mandatory
    DESCRIPTION
        "Number of sessions currently use this route to forward this
        traffic in Kbps."
    ::= { cqllbgrouteEntry 10 }

cqlQpNotifyEnable OBJECT-TYPE
    SYNTAX TruthValue
--    Rsyntax INTEGER {
--        true(1),
--        false(2)
--        }
    ACCESS read-write
    STATUS mandatory
    DESCRIPTION
        "This object specifies whether the system generates
        cqlQpStateChange notifications. A false value will prevent
        cqlQpStateChange notifications from being generated by this
        system."
    DEFVAL { false }
    ::= { ciscoQpLbgObjects 4 }

cqlQamNotifyEnable OBJECT-TYPE
    SYNTAX TruthValue
--    Rsyntax INTEGER {
--        true(1),
--        false(2)
--        }
    ACCESS read-write
    STATUS mandatory
    DESCRIPTION
        "This object specifies whether the system generates cqlQamAdd or
        cqlQamDelete notifications. A false value will prevent cqlQamAdd
        or cqlQamDelete notifications from being generated by this
        system."
    DEFVAL { false }
    ::= { ciscoQpLbgObjects 5 }

cqlRouteNotifyEnable OBJECT-TYPE
    SYNTAX TruthValue
--    Rsyntax INTEGER {
--        true(1),
--        false(2)
--        }
    ACCESS read-write
    STATUS mandatory
    DESCRIPTION
        "This object specifies whether the system produces cqlRouteAdd
        or cqlRouteDelete notifications. A false value will prevent 
        cqlRouteAdd or cqlRouteDelete notifications  from being
        generated by this system."
    DEFVAL { false }
    ::= { ciscoQpLbgObjects 6 }

cqlQamOverSubscribedEnable OBJECT-TYPE
    SYNTAX TruthValue
--    Rsyntax INTEGER {
--        true(1),
--        false(2)
--        }
    ACCESS read-write
    STATUS mandatory
    DESCRIPTION
        "This object specifies whether the system produces
        cqlQamOverSubscribedAlert notifications. A false value will 
        prevent cqlQamOverSubscribedAlert notifications from being
        generated by the system."
    DEFVAL { false }
    ::= { ciscoQpLbgObjects 7 }

cqlQpStateChange TRAP-TYPE
-- Reverse mappable trap
    ENTERPRISE ciscoQpLbgMIB
    VARIABLES {
        cqlqpState }
--  Status
--    mandatory
    DESCRIPTION
        "The device generates this notification when a QP state
        has changed and the value of cqlQpNotifyEnable is 'true'."
    ::= 1

cqlQamAdd TRAP-TYPE
-- Reverse mappable trap
    ENTERPRISE ciscoQpLbgMIB
    VARIABLES {
        cqlqpId, ifDescr }
--  Status
--    mandatory
    DESCRIPTION
        "The device generates this notification when a qam has
        been added to QP and the value of cqlQamNotifyEnable 
        is 'true'."
    ::= 2

cqlQamDelete TRAP-TYPE
-- Reverse mappable trap
    ENTERPRISE ciscoQpLbgMIB
    VARIABLES {
        cqlqpId, ifDescr }
--  Status
--    mandatory
    DESCRIPTION
        "The device generates this notification when a qam has
        been deleted from QP and the value of cqlQamNotifyEnable 
        is 'true'."
    ::= 3

cqlLbgRouteAdd TRAP-TYPE
-- Reverse mappable trap
    ENTERPRISE ciscoQpLbgMIB
    VARIABLES {
        cqlqpRouteDetails }
--  Status
--    mandatory
    DESCRIPTION
        "The device generates this notification when a route has
        been added to QP and the value of cqlRouteNotifyEnable 
        is 'true'."
    ::= 4

cqlLbgRouteDelete TRAP-TYPE
-- Reverse mappable trap
    ENTERPRISE ciscoQpLbgMIB
    VARIABLES {
        cqlqpRouteDetails }
--  Status
--    mandatory
    DESCRIPTION
        "The device generates this notification when a route has been
        deleted from QP and the value of cqlRouteNotifyEnable is
        'true'."
    ::= 5

cqlQamOverSubscribedAlert TRAP-TYPE
-- Reverse mappable trap
    ENTERPRISE ciscoQpLbgMIB
    VARIABLES {
        ifDescr, cqlqpQamOversubscribedStatus }
--  Status
--    mandatory
    DESCRIPTION
        "The device generates this notification when a qam
        has been oversubscribed or cleared. This will be
        enabled when the object cqlQamOverSubscribedEnable 
        is set to 'true'."
    ::= 6

cqlciscoQpObjectGroup OBJECT IDENTIFIER ::= { ciscoQpLbgGroups 3 }
-- OBJECT-GROUP
--  Status
--    deprecated
--  Descr
--    A collection of objects providing information 
--    about the QP parameters.
--    cqlciscoQpObjectGroup object is 
--    superseded by cqlciscoQpObjectGroup1.
--  objects
--    cqlqpId, cqlqpMgmtIp, cqlqpState, cqlqpProtocol, 
--    cqlqpKeepAliveTime, cqlqpGqiResetInterval, cqlqpServerIp, 
--    cqlqpServerState, cqlqpGqiMacAddr, cqlqpNumQams, 
--    cqlqpQamCarrrierList, cqlqpNumRoutes, cqlqpRouteDetails, 
--    cqlqpErmiErrpComponentName, cqlqpErmiErrpStreamingZone, 
--    cqlqpErmiErrpConnectRetry, cqlqpErmiErrpConnnectTime, 
--    cqlqpErmiErrpHoldTime, cqlqpErmiRtspConnectRetry, 
--    cqlqpErmiRtspConnectTime, cqlqpErmiRtspKeepAliveTime, 
--    cqlqpErmiRtspSessionTimeout, cqlqpMgmtIpAddrType, 
--    cqlqpServerIpAddrType

cqlciscoLbgObjectGroup OBJECT IDENTIFIER ::= { ciscoQpLbgGroups 4 }
-- OBJECT-GROUP
--  Status
--    mandatory
--  Descr
--    A collection of objects providing
--    information about the LBG parameters.
--  objects
--    cqllbgTotalBandwidth, cqllbgQamRsvBandwidth, 
--    cqllbgIpRsvBandwidth, cqllbgAvailableBandwidth

cqlciscoLbgRouteObjectGroup OBJECT IDENTIFIER ::= { ciscoQpLbgGroups 5 }
-- OBJECT-GROUP
--  Status
--    mandatory
--  Descr
--    A collection of objects providing information about the LBG
--    route parameters.
--  objects
--    cqllbgQpId, cqllbgDstIpAddr, cqllbgUdpPortRangeMin, 
--    cqllbgUdpPortRangeMax, cqllbgGqiIngressPort, 
--    cqllbgAllocatedBandwidth, cqllbgRsvBandwidth, cqllbgNumFlows, 
--    cqllbgDstIpAddrType

cqlciscoQpLbgNotifsControlGroup OBJECT IDENTIFIER ::= { ciscoQpLbgGroups 6 }
-- OBJECT-GROUP
--  Status
--    deprecated
--  Descr
--    A collection of objects providing information
--    about the notification enables.
--    cqlciscoQpLbgNotifsControlGroup object is 
--    superseded by cqlciscoQpLbgNotifsControlGroup1.
--  objects
--    cqlQpNotifyEnable, cqlQamNotifyEnable, cqlRouteNotifyEnable

cqlciscoQpObjectGroup1 OBJECT IDENTIFIER ::= { ciscoQpLbgGroups 8 }
-- OBJECT-GROUP
--  Status
--    mandatory
--  Descr
--    A collection of objects providing information
--    about the QP parameters.
--  objects
--    cqlqpId, cqlqpMgmtIpAddrType, cqlqpMgmtIp, 
--    cqlqpServerIpAddrType, cqlqpServerIp, cqlqpState, 
--    cqlqpProtocol, cqlqpKeepAliveTime, cqlqpServerState, 
--    cqlqpGqiMacAddr, cqlqpGqiResetInterval, cqlqpNumQams, 
--    cqlqpQamCarrrierList, cqlqpNumRoutes, cqlqpRouteDetails, 
--    cqlqpErmiErrpComponentName, cqlqpErmiErrpStreamingZone, 
--    cqlqpErmiErrpHoldTime, cqlqpErmiErrpConnnectTime, 
--    cqlqpErmiErrpConnectRetry, cqlqpErmiRtspConnectTime, 
--    cqlqpErmiRtspConnectRetry, cqlqpErmiRtspKeepAliveTime, 
--    cqlqpErmiRtspSessionTimeout, cqlqpQamOversubscribedStatus, 
--    cqlqpServerIpList

cqlciscoQpLbgNotifsControlGroup1 OBJECT IDENTIFIER ::= { ciscoQpLbgGroups 9 }
-- OBJECT-GROUP
--  Status
--    mandatory
--  Descr
--    A collection of objects providing information
--    about the notification enables.
--  objects
--    cqlQpNotifyEnable, cqlQamNotifyEnable, cqlRouteNotifyEnable, 
--    cqlQamOverSubscribedEnable

cqlciscoQpNotifsGroup OBJECT IDENTIFIER ::= { ciscoQpLbgGroups 1 }
-- NOTIFICATION-GROUP
--  Status
--    deprecated
--  Descr
--    A collection of QP notifications that may 
--    optionally be implemented.
--    cqlciscoQpNotifsGroup object is 
--    superseded by cqlciscoQpNotifsGroup1.
--  notifications
--    cqlQpStateChange, cqlQamAdd, cqlQamDelete

cqlciscoLbgNotifsGroup OBJECT IDENTIFIER ::= { ciscoQpLbgGroups 2 }
-- NOTIFICATION-GROUP
--  Status
--    mandatory
--  Descr
--    A collection of LBG notifications
--    that may optionally be implemented.
--  notifications
--    cqlLbgRouteAdd, cqlLbgRouteDelete

cqlciscoQpNotifsGroup1 OBJECT IDENTIFIER ::= { ciscoQpLbgGroups 7 }
-- NOTIFICATION-GROUP
--  Status
--    mandatory
--  Descr
--    A collection of QP notifications that may
--    optionally be implemented.
--  notifications
--    cqlQpStateChange, cqlQamAdd, cqlQamDelete, 
--    cqlQamOverSubscribedAlert

cqlciscoQpLbgCompliance OBJECT IDENTIFIER ::= { ciscoQpLbgCompliances 1 }
-- MODULE-COMPLIANCE
--  Status
--    deprecated
--  Descr
--    These objects describe the support level
--    for QP and LBG.
--  Module
--    >>current<<
--   MandGroup
--    cqlciscoLbgRouteObjectGroup
--   OptGroup
--    cqlciscoQpNotifsGroup
--   OptGroup
--    cqlciscoQpObjectGroup
--   OptGroup
--    cqlciscoQpLbgNotifsControlGroup
--   OptGroup
--    cqlciscoLbgNotifsGroup
--   OptGroup
--    cqlciscoLbgObjectGroup

cqlciscoQpLbgCompliance1 OBJECT IDENTIFIER ::= { ciscoQpLbgCompliances 2 }
-- MODULE-COMPLIANCE
--  Status
--    mandatory
--  Descr
--    These objects describe the support level
--    for QP and LBG.
--  Module
--    >>current<<
--   MandGroup
--    cqlciscoLbgRouteObjectGroup
--   OptGroup
--    cqlciscoLbgNotifsGroup
--   OptGroup
--    cqlciscoLbgObjectGroup
--   OptGroup
--    cqlciscoQpNotifsGroup1
--   OptGroup
--    cqlciscoQpObjectGroup1
--   OptGroup
--    cqlciscoQpLbgNotifsControlGroup1


END
