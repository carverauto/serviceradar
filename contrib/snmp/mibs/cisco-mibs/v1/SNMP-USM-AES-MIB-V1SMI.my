-- MIB file created 28-Feb-2007 18:14:31, by
--   SMICng version 2.2.11-beta(PRO)(Solaris), January 20, 2001. Enterprise key cisco.com

SNMP-USM-AES-MIB DEFINITIONS ::= BEGIN

-- From file: "SNMP-USM-AES-MIB.my"
-- Compile options "4 7 F H N O W 03 06 0B 0G 0N 0T"

IMPORTS
    snmpModules
            FROM SNMPv2-SMI-v1
    snmpPrivProtocols
            FROM SNMP-FRAMEWORK-MIB;

snmpUsmAesMIB OBJECT IDENTIFIER ::= { snmpModules 20 }
-- MODULE-IDENTITY
--  LastUpdated
--    200406140000Z
--  OrgName
--    IETF
--  ContactInfo
--    Uri Blumenthal
--     Lucent Technologies / Bell Labs
--     67 Whippany Rd.
--     14D-318
--     Whippany, NJ  07981, USA
--     973-386-2163
--     uri@bell-labs.com
--    
--     Fabio Maino
--     Andiamo Systems, Inc.
--     375 East Tasman Drive
--     San Jose, CA  95134, USA
--     408-853-7530
--     fmaino@andiamo.com
--    
--     Keith McCloghrie
--     Cisco Systems, Inc.
--     170 West Tasman Drive
--     San Jose, CA  95134-1706, USA
--    
--     408-526-5260
--     kzm@cisco.com
--  Descr
--    Definitions of Object Identities needed for
--     the use of AES by SNMP's User-based Security
--     Model.
--    
--     Copyright (C) The Internet Society (2004).
--    
--    This version of this MIB module is part of RFC 3826;
--    see the RFC itself for full legal notices.
--    Supplementary information may be available on
--    http://www.ietf.org/copyrights/ianamib.html.
--  RevDate
--    200406140000Z
--  RevDescr
--    Initial version, published as RFC3826

usmAesCfb128Protocol OBJECT IDENTIFIER ::= { snmpPrivProtocols 4 }
-- OBJECT-IDENTITY
--  Status
--    mandatory
--  Descr
--    The CFB128-AES-128 Privacy Protocol.
--  Refer
--    - Specification for the ADVANCED ENCRYPTION
--       STANDARD. Federal Information Processing
--       Standard (FIPS) Publication 197.
--       (November 2001).
--    
--     - Dworkin, M., NIST Recommendation for Block
--       Cipher Modes of Operation, Methods and
--       Techniques. NIST Special Publication 800-38A
--       (December 2001).


END
