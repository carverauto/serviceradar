-- MIB created 6/25/99 12:56:49, by
--   SMIC (the next generation) version 1.6.29, November 22, 1994.

CISCO-ATM-SERVICE-REGISTRY-MIB DEFINITIONS ::= BEGIN

-- From file: "CISCO-ATM-SERVICE-REGISTRY-MIB.my"

IMPORTS
    Integer32
            FROM SNMPv2-SMI-v1
    OBJECT-TYPE
            FROM RFC-1212
    RowStatus
            FROM SNMPv2-TC-v1
    ciscoMgmt
            FROM CISCO-SMI;

ciscoAtmServiceRegistryMIB OBJECT IDENTIFIER ::= { ciscoMgmt 50 }
-- MODULE-IDENTITY
--  LastUpdated
--    9602210000Z
--  OrgName
--    Cisco Systems, Inc.
--  ContactInfo
--           Cisco Systems
--            Customer Service
--    
--    Postal: 170 W. Tasman Drive
--            San Jose, CA  95134-1706
--            USA
--    
--       Tel: +1 800 553-NETS
--    
--    E-mail: cs-snmp@cisco.com
--  Descr
--    A MIB module to allow an NMS to monitor and
--    configure the information which an ATM switch
--    makes available via the ILMI's Service Registry
--    Table.
--  RevDate
--    9602040000Z
--  RevDescr
--    Initial version of this MIB module.

ciscoAtmServiceRegistryMIBObjects OBJECT IDENTIFIER ::= { ciscoAtmServiceRegistryMIB 1 }
asrSrvcRegMIBConformance OBJECT IDENTIFIER ::= { ciscoAtmServiceRegistryMIB 3 }
asrSrvcRegMIBCompliances OBJECT IDENTIFIER ::= { asrSrvcRegMIBConformance 1 }
asrSrvcRegMIBGroups OBJECT IDENTIFIER ::= { asrSrvcRegMIBConformance 2 }

AtmAddr ::= OCTET STRING(SIZE(0 | 8 | 13 | 20))
-- TEXTUAL-CONVENTION
--  Status
--    mandatory
--  Descr
--    The ATM address used by the network entity.  The
--    address types are: no address (0 octets), E.164 (8
--    octets), network prefix (13 octets), and NSAP (20
--    octets).  Note: The E.164 address is encoded in
--    BCD format.

InterfaceIndexOrZero ::= Integer32(0..2147483647)
-- TEXTUAL-CONVENTION
--  DspHint
--    d
--  Status
--    mandatory
--  Descr
--    Either the value 0, or the ifIndex value of an
--    ATM Interface.

asrSrvcRegTable OBJECT-TYPE
    SYNTAX SEQUENCE OF AsrSrvcRegEntry
    ACCESS not-accessible
    STATUS mandatory
    DESCRIPTION
        "The table implemented by an ATM switch to allow
        monitoring and control of the ATM addresses of
        registered services which it makes avaiable to ATM
        end-systems via the ILMI across its UNIs."
    ::= { ciscoAtmServiceRegistryMIBObjects 1 }

asrSrvcRegEntry OBJECT-TYPE
    SYNTAX AsrSrvcRegEntry
    ACCESS not-accessible
    STATUS mandatory
    DESCRIPTION
        "Information about a single service provider that is 
        to be made available to the user-side of one or more
        ATM UNIs.  An entry, for which asrSrvcRegPort has a
        non-zero value, is a specific assignment to that UNI;
        an entry for which asrSrvcRegPort is zero applies to
        all UNIs for which this table contains no specific
        assignments."
    INDEX { asrSrvcRegPort, asrSrvcRegServiceID, asrSrvcRegAddressIndex }
    ::= { asrSrvcRegTable 1 }

AsrSrvcRegEntry ::= SEQUENCE {
    asrSrvcRegPort InterfaceIndexOrZero,
    asrSrvcRegServiceID OBJECT IDENTIFIER,
    asrSrvcRegATMAddress AtmAddr,
    asrSrvcRegAddressIndex Integer32,
    asrSrvcRegParm1 OCTET STRING,
    asrSrvcRegRowStatus RowStatus
    }

asrSrvcRegPort OBJECT-TYPE
    SYNTAX InterfaceIndexOrZero
--    Rsyntax Integer32(0..2147483647)
    ACCESS not-accessible
    STATUS mandatory
    DESCRIPTION
        "Either the value 0, or the ifIndex value of an
        the ATM Interface.  A row for which this object has a
        non-zero value is a specific assignment to that UNI;
        a row for which this object is zero applies to
        all UNIs for which this table contains no specific
        assignments.
        
        Some switches may only support this object with the
        value of zero."
    ::= { asrSrvcRegEntry 1 }

asrSrvcRegServiceID OBJECT-TYPE
    SYNTAX OBJECT IDENTIFIER
    ACCESS not-accessible
    STATUS mandatory
    DESCRIPTION
        "The service identifier which uniquely identifies
        the type of service at the address given by the
        corresponding value of asrSrvcRegATMAddress.
        
        Specific values for this identifier are defined in
        the ILMI specification (e.g., asrSrvcRegLecs) or
        elsewhere."
    ::= { asrSrvcRegEntry 2 }

asrSrvcRegATMAddress OBJECT-TYPE
    SYNTAX AtmAddr
--    Rsyntax OCTET STRING(SIZE(0 | 8 | 13 | 20))
    ACCESS read-write
    STATUS mandatory
    DESCRIPTION
        "An ATM address to which the ATM end-system on this
        UNI can attempt to establish a connection for the
        service."
    ::= { asrSrvcRegEntry 3 }

asrSrvcRegAddressIndex OBJECT-TYPE
    SYNTAX Integer32(0..2147483647)
    ACCESS not-accessible
    STATUS mandatory
    DESCRIPTION
        "An arbitrary integer to differentiate multiple rows
        containing different ATM addresses for the same service
        on the same UNI."
    ::= { asrSrvcRegEntry 4 }

asrSrvcRegParm1 OBJECT-TYPE
    SYNTAX OCTET STRING
    ACCESS read-write
    STATUS mandatory
    DESCRIPTION
        "An octet string used according to the value of 
        asrSrvcRegServiceID."
    ::= { asrSrvcRegEntry 5 }

asrSrvcRegRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this row.  No object in the row can
        be modified while the value of this object is
        'active'."
    ::= { asrSrvcRegEntry 6 }

asrSrvcRegMIBGroup OBJECT IDENTIFIER ::= { asrSrvcRegMIBGroups 1 }
-- OBJECT-GROUP
--  Status
--    mandatory
--  Descr
--    A collection of objects providing monitoring and
--            control of ATM addresses of services which an ATM
--            switch is to make available via the ILMI.
--  objects
--    asrSrvcRegATMAddress, asrSrvcRegParm1, asrSrvcRegRowStatus

asrSrvcRegMIBCompliance OBJECT IDENTIFIER ::= { asrSrvcRegMIBCompliances 1 }
-- MODULE-COMPLIANCE
--  Status
--    mandatory
--  Descr
--    The compliance statement for ATM switches which
--            implement the Cisco Service Registry MIB
--  Module
--    >>current<<
--   MandGroup
--    asrSrvcRegMIBGroup


END
