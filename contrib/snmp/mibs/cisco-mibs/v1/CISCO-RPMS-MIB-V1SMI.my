-- MIB file created 16-May-2002 12:32:08, by
--   SMICng version 2.2.11-beta(PRO)(Solaris), January 20, 2001. Enterprise key cisco.com

CISCO-RPMS-MIB DEFINITIONS ::= BEGIN

-- From file: "CISCO-RPMS-MIB.my"
-- Compile options "4 7 F H N W 03 06 0B 0G 0N 0T"

IMPORTS
    RowStatus, TimeStamp
            FROM SNMPv2-TC-v1
    SnmpAdminString
            FROM SNMP-FRAMEWORK-MIB
    ciscoExperiment
            FROM CISCO-SMI
    Counter, Gauge
            FROM RFC1155-SMI
    OBJECT-TYPE
            FROM RFC-1212
    TRAP-TYPE
            FROM RFC-1215;

ciscoRpmsMIB OBJECT IDENTIFIER ::= { ciscoExperiment 84 }
-- MODULE-IDENTITY
--  LastUpdated
--    200204170000Z
--  OrgName
--    Cisco Systems, Inc.
--  ContactInfo
--    Cisco Systems
--     Customer Service
--    
--    Postal: 170 W Tasman Drive
--     San Jose, CA  95134
--     USA
--    
--    Tel: +1 800 553-NETS
--    
--    E-mail: cs-rpms@cisco.com
--  Descr
--    This MIB contains objects pertinent to a Resource
--    Policy Management System (RPMS) server.
--    
--    RPMS is a key component of Cisco Any Service Any Port
--    (ASAP) solution and provides the ability to
--    dynamically share resources across network access 
--    servers (NAS). RPMS enables enforcement of Service
--    Level Agreements(SLA) between wholesale providers and
--    their customers. Such SLA enforcement is done at call
--    pre-authentication stage. An SLA is conceptually a set
--    of clauses (limits) that dictate how voice, dial 
--    and/or virtual private data network (VPDN) services 
--    will be provided by the wholesaler.
--  RevDate
--    200204170000Z
--  RevDescr
--    Updated name from Resource Pool Manager Server to 
--     Resource Policy Management System (RPMS). This 
--     reflects product change,
--     Corrected omission of 'crpmsVpdnGroupCpEntryStatus'
--     from 'crpmsVpdnGroup' object group in initial
--     release,
--     Updated E-Mail contact to correct list for rpms.
--  RevDate
--    200111010000Z
--  RevDescr
--    Initial version of this MIB module.

ciscoRpmsMIBObjects OBJECT IDENTIFIER ::= { ciscoRpmsMIB 1 }
crpmsSystem     OBJECT IDENTIFIER ::= { ciscoRpmsMIBObjects 1 }
crpmsCustomerProfile OBJECT IDENTIFIER ::= { ciscoRpmsMIBObjects 2 }
crpmsVpdn       OBJECT IDENTIFIER ::= { ciscoRpmsMIBObjects 3 }
crpmsNotif      OBJECT IDENTIFIER ::= { ciscoRpmsMIBObjects 4 }
ciscoRpmsMIBNotificationPrefix OBJECT IDENTIFIER ::= { ciscoRpmsMIB 2 }
ciscoRpmsMIBNotifications OBJECT IDENTIFIER ::= { ciscoRpmsMIBNotificationPrefix 0 }
ciscoRpmsMIBConformance OBJECT IDENTIFIER ::= { ciscoRpmsMIB 3 }
ciscoRpmsMIBCompliances OBJECT IDENTIFIER ::= { ciscoRpmsMIBConformance 1 }
ciscoRpmsMIBGroups OBJECT IDENTIFIER ::= { ciscoRpmsMIBConformance 2 }

crpmsSubsystemTable OBJECT-TYPE
    SYNTAX SEQUENCE OF CrpmsSubsystemEntry
    ACCESS not-accessible
    STATUS mandatory
    DESCRIPTION
        "This table contains currently working RPMS
        subsystems. Each row contains the name of the
        subsystem and its uptime since last initialization."
    ::= { crpmsSystem 1 }

crpmsSubsystemEntry OBJECT-TYPE
    SYNTAX CrpmsSubsystemEntry
    ACCESS not-accessible
    STATUS mandatory
    DESCRIPTION
        "A subsystem entry contains information of a RPMS
        subsystem. At the system startup, if a subsystem fails
        to initialize itself, it will not appear in this table.
        If a subsystem becomes unavailable, its corresponding
        row will be removed from this table."
    INDEX { crpmsSubsystemIndex }
    ::= { crpmsSubsystemTable 1 }

CrpmsSubsystemEntry ::= SEQUENCE {
    crpmsSubsystemIndex Gauge,
    crpmsSubsystemName SnmpAdminString,
    crpmsSubsystemUptime TimeStamp
    }

crpmsSubsystemIndex OBJECT-TYPE
    SYNTAX Gauge(1..128)
    ACCESS not-accessible
    STATUS mandatory
    DESCRIPTION
        "An unique value, greater than zero, for each subsystem.
        It is recommended that values are assigned contiguously
        starting from 1."
    ::= { crpmsSubsystemEntry 1 }

crpmsSubsystemName OBJECT-TYPE
    SYNTAX SnmpAdminString(SIZE(1..31))
--    Rsyntax OCTET STRING(SIZE(1..31))
    ACCESS read-only
    STATUS mandatory
    DESCRIPTION
        "The name of the subsystem entry."
    ::= { crpmsSubsystemEntry 2 }

crpmsSubsystemUptime OBJECT-TYPE
    SYNTAX TimeStamp
--    Rsyntax TimeTicks
    ACCESS read-only
    STATUS mandatory
    DESCRIPTION
        "The time (in hundredths of a second) since the
        subsystem was last (re)initialized."
    ::= { crpmsSubsystemEntry 3 }

crpmsCpTable OBJECT-TYPE
    SYNTAX SEQUENCE OF CrpmsCpEntry
    ACCESS not-accessible
    STATUS mandatory
    DESCRIPTION
        "The customer profile table contains information about
        all SLAs hosted on an SLA Server."
    ::= { crpmsCustomerProfile 1 }

crpmsCpEntry OBJECT-TYPE
    SYNTAX CrpmsCpEntry
    ACCESS not-accessible
    STATUS mandatory
    DESCRIPTION
        "A customer profile (Cp) entry contains information about
        a specific customer. A customer profile is a set of limits
        associated with a customer. These limits control how
        RPMS will respond to an incoming call under various
        scenarios."
    INDEX { --?? IMPLIED may cause problems
            IMPLIED crpmsCpName }
    ::= { crpmsCpTable 1 }

CrpmsCpEntry ::= SEQUENCE {
    crpmsCpName SnmpAdminString,
    crpmsCpLimit Gauge,
    crpmsCpOverflowLimit Gauge,
    crpmsCpActiveCalls Gauge,
    crpmsCpActiveOverflowCalls Gauge,
    crpmsCpAttemptedCalls Counter,
    crpmsCpAttemptedOverflowCalls Counter,
    crpmsCpRejections Counter,
    crpmsCpOverflowRejections Counter,
    crpmsCpLimitThreshold Gauge,
    crpmsCpOverflowLimitThreshold Gauge,
    crpmsCpCallRejectionThreshold Gauge,
    crpmsCpOverflowRejectThreshold Gauge,
    crpmsCpEntryStatus RowStatus
    }

crpmsCpName OBJECT-TYPE
    SYNTAX SnmpAdminString(SIZE(1..31))
--    Rsyntax OCTET STRING(SIZE(1..31))
    ACCESS not-accessible
    STATUS mandatory
    DESCRIPTION
        "The name of the customer profile. This name uniquely
        identifies the customer profile in the RPMS system."
    ::= { crpmsCpEntry 1 }

crpmsCpLimit OBJECT-TYPE
    SYNTAX Gauge
    ACCESS read-write
    STATUS mandatory
    DESCRIPTION
        "The maximum number of concurrent calls allowed
        in this customer profile. Once this limit is exceeded,
        RPMS will reject any new calls unless an overflow limit
        (crpmsCpOverflowLimit) is configured for this customer."
    DEFVAL { 0 }
    ::= { crpmsCpEntry 2 }

crpmsCpOverflowLimit OBJECT-TYPE
    SYNTAX Gauge
    ACCESS read-write
    STATUS mandatory
    DESCRIPTION
        "The maximum number of calls allowed after the customer
        profile limit(crpmsCpLimit) has been reached. Such calls
        are termed overflow calls."
    DEFVAL { 0 }
    ::= { crpmsCpEntry 3 }

crpmsCpActiveCalls OBJECT-TYPE
    SYNTAX Gauge
    ACCESS read-only
    STATUS mandatory
    DESCRIPTION
        "Number of current active calls for this customer
        profile."
    ::= { crpmsCpEntry 4 }

crpmsCpActiveOverflowCalls OBJECT-TYPE
    SYNTAX Gauge
    ACCESS read-only
    STATUS mandatory
    DESCRIPTION
        "Number of current active overflow calls for this 
        customer profile."
    ::= { crpmsCpEntry 5 }

crpmsCpAttemptedCalls OBJECT-TYPE
    SYNTAX Counter
    ACCESS read-only
    STATUS mandatory
    DESCRIPTION
        "Total number of attempted calls (both successful and 
        failed) for this customer profile."
    ::= { crpmsCpEntry 6 }

crpmsCpAttemptedOverflowCalls OBJECT-TYPE
    SYNTAX Counter
    ACCESS read-only
    STATUS mandatory
    DESCRIPTION
        "Number of attempted overflow calls (both successful 
        and failed) for this customer profile."
    ::= { crpmsCpEntry 7 }

crpmsCpRejections OBJECT-TYPE
    SYNTAX Counter
    ACCESS read-only
    STATUS mandatory
    DESCRIPTION
        "Total number of rejected calls for this customer 
        profile (crpmsCpOverflowRejections plus rejections
        due to unavailable resources)."
    ::= { crpmsCpEntry 8 }

crpmsCpOverflowRejections OBJECT-TYPE
    SYNTAX Counter
    ACCESS read-only
    STATUS mandatory
    DESCRIPTION
        "Number of rejected overflow calls for this customer 
        profile."
    ::= { crpmsCpEntry 9 }

crpmsCpLimitThreshold OBJECT-TYPE
    SYNTAX Gauge(0..100)
--  Units
--    percent
    ACCESS read-write
    STATUS mandatory
    DESCRIPTION
        "A threshold defined for the customer profile limit
         (crpmsCpLimit). It represents the percentage of the limit
         which, when crossed triggers a crpmsRisingAlarm or a 
         crpmsFallingAlarm notification (refer to the notification
         definitions in this MIB for more details). 
        
         A value of 100 percent cannot be exceeded and therefore 
         disables this threshold setting. A value of 0 percent is 
         always exceeded."
    DEFVAL { 100 }
    ::= { crpmsCpEntry 10 }

crpmsCpOverflowLimitThreshold OBJECT-TYPE
    SYNTAX Gauge(0..100)
--  Units
--    percent
    ACCESS read-write
    STATUS mandatory
    DESCRIPTION
        "A threshold defined for the customer profile overflow
         limit (crpmsCpOverflowLimit). It represents the percentage
         of the limit that when exceeded triggers a crpmsRisingAlarm
         or a crpmsFallingAlarm notification (refer to the 
         notification definitions in this MIB for more details).
        
         A value of 100 percent cannot be exceeded and therefore 
         disables this threshold setting. A value of 0 percent is 
         always exceeded."
    DEFVAL { 100 }
    ::= { crpmsCpEntry 11 }

crpmsCpCallRejectionThreshold OBJECT-TYPE
    SYNTAX Gauge(0..100)
--  Units
--    percent
    ACCESS read-write
    STATUS mandatory
    DESCRIPTION
        "A threshold defined for the number of customer profile
         rejected calls (crpmsCpRejections) as a percentage of the
         number of attempted calls (crpmsCpAttemptedCalls) which,
         when crossed, triggers a crpmsRisingAlarm or 
         crpmsFallingAlarm notification (refer to the notification
         definitions in this MIB for more details).
        
         A value of 100 percent cannot be exceeded and therefore 
         disables this threshold setting. A value of 0 percent is 
         always exceeded."
    DEFVAL { 100 }
    ::= { crpmsCpEntry 12 }

crpmsCpOverflowRejectThreshold OBJECT-TYPE
    SYNTAX Gauge(0..100)
--  Units
--    percent
    ACCESS read-write
    STATUS mandatory
    DESCRIPTION
        "A threshold defined for the number of customer profile
         rejected overflow calls (crpmsCpOverflowRejections) as a 
         percentage of the number of attempted overflow calls 
         (crpmsCpAttemptedOverflowCalls) which, when crossed, 
         triggers a crpmsRisingAlarm or a crpmsFallingAlarm  
         notification (refer to the notification definitions in this
         MIB for more details).
        
         A value of 100 percent cannot be exceeded and therefore 
         disables this threshold setting. A value of 0 percent is 
         always exceeded."
    DEFVAL { 100 }
    ::= { crpmsCpEntry 13 }

crpmsCpEntryStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Used to create, delete or modify this row. None of the 
        columnar objects can be modified except this one, when
        the row is active."
    ::= { crpmsCpEntry 14 }

crpmsVpdnGroupTable OBJECT-TYPE
    SYNTAX SEQUENCE OF CrpmsVpdnGroupEntry
    ACCESS not-accessible
    STATUS mandatory
    DESCRIPTION
        "A VPDN group manages a number of sessions. A VPDN 
        session may use a MLP link, which is contained within 
        a particular MLP bundle. A VPDN group has a limit of 
        maximal sessions, the number of bundles that this
        VPDN group can allocate, and the number of links for
        each bundle.
        
        The VPDN group table contains information about VPDN 
        group of a RPMS server, each group a row. If a row is 
        added or removed, its corresponding row in the 
        crpmsVpdnGroupCpTable has to be added or removed as 
        well."
    ::= { crpmsVpdn 1 }

crpmsVpdnGroupEntry OBJECT-TYPE
    SYNTAX CrpmsVpdnGroupEntry
    ACCESS not-accessible
    STATUS mandatory
    DESCRIPTION
        "A VPDN group entry contains information about
         a specific VPDN group. VPDN groups contain the
         necessary setting to establish a VPDN session
         (tunneling protocol, home gateway information, and 
         other data) as well as limits on various parameters
         (maximum concurrent sessions, MLP bundles, etc.)."
    INDEX { --?? IMPLIED may cause problems
            IMPLIED crpmsVpdnGroupName }
    ::= { crpmsVpdnGroupTable 1 }

CrpmsVpdnGroupEntry ::= SEQUENCE {
    crpmsVpdnGroupName SnmpAdminString,
    crpmsVpdnTunnelId SnmpAdminString,
    crpmsVpdnTunnelProtocol INTEGER,
    crpmsVpdnLimit Gauge,
    crpmsVpdnOverflowLimit Gauge,
    crpmsVpdnMlpBundleLimit Gauge,
    crpmsVpdnLinksPerBundleLimit Gauge,
    crpmsVpdnBundles Gauge,
    crpmsVpdnActiveCalls Gauge,
    crpmsVpdnActiveOverflowCalls Gauge,
    crpmsVpdnRejections Counter,
    crpmsVpdnSizeRejections Counter,
    crpmsVpdnLimitThreshold Gauge,
    crpmsVpdnEntryStatus RowStatus
    }

crpmsVpdnGroupName OBJECT-TYPE
    SYNTAX SnmpAdminString(SIZE(1..31))
--    Rsyntax OCTET STRING(SIZE(1..31))
    ACCESS not-accessible
    STATUS mandatory
    DESCRIPTION
        "The name of the VPDN group. This name uniquely 
        identifies a VPDN group in the RPMS system."
    ::= { crpmsVpdnGroupEntry 1 }

crpmsVpdnTunnelId OBJECT-TYPE
    SYNTAX SnmpAdminString
--    Rsyntax OCTET STRING(SIZE(0..255))
    ACCESS read-only
    STATUS mandatory
    DESCRIPTION
        "The tunnel Id of the VPDN group.
        For Cisco IOS 12.05T and later, the tunnel id matches
        the remote name configured on the HGW router. The 
        following is an example:
        
        vpdn-group 1
        accept dialin l2tp virtual-template 1 remote isp1
        local name hg
        
        For old Cisco IOS releases, the tunnel id matches the
        incoming statement:
        
        vpdn incoming isp1 hgw virtual-template 1
        
        In above examples, the object has the value isp1."
    ::= { crpmsVpdnGroupEntry 2 }

crpmsVpdnTunnelProtocol OBJECT-TYPE
    SYNTAX INTEGER {
        l2f(1),
        l2tp(2)
        }
    ACCESS read-write
    STATUS mandatory
    DESCRIPTION
        "The protocol used by the tunnel of the VPDN group.
         There are only 2 possible value:
         l2f  - Layer 2 Forwarding Protocol
         l2tp - Layer 2 Tunneling Protocol"
    DEFVAL { l2f }
    ::= { crpmsVpdnGroupEntry 3 }

crpmsVpdnLimit OBJECT-TYPE
    SYNTAX Gauge
    ACCESS read-write
    STATUS mandatory
    DESCRIPTION
        "Limit of the resource pool for this VPDN group."
    DEFVAL { 0 }
    ::= { crpmsVpdnGroupEntry 4 }

crpmsVpdnOverflowLimit OBJECT-TYPE
    SYNTAX Gauge
    ACCESS read-write
    STATUS mandatory
    DESCRIPTION
        "Limit of the overflow pool for this VPDN group."
    DEFVAL { 0 }
    ::= { crpmsVpdnGroupEntry 5 }

crpmsVpdnMlpBundleLimit OBJECT-TYPE
    SYNTAX Gauge
    ACCESS read-write
    STATUS mandatory
    DESCRIPTION
        "Limit of MLP (multilink protocol) bundles for this 
        VPDN group."
    DEFVAL { 0 }
    ::= { crpmsVpdnGroupEntry 6 }

crpmsVpdnLinksPerBundleLimit OBJECT-TYPE
    SYNTAX Gauge
    ACCESS read-write
    STATUS mandatory
    DESCRIPTION
        "Limit of links per bundle for this VPDN group."
    DEFVAL { 0 }
    ::= { crpmsVpdnGroupEntry 7 }

crpmsVpdnBundles OBJECT-TYPE
    SYNTAX Gauge
    ACCESS read-only
    STATUS mandatory
    DESCRIPTION
        "The number of active MLP bundles in the tunnel 
         of the VPDN group."
    ::= { crpmsVpdnGroupEntry 8 }

crpmsVpdnActiveCalls OBJECT-TYPE
    SYNTAX Gauge
    ACCESS read-only
    STATUS mandatory
    DESCRIPTION
        "The number of active calls that belong to this VPDN 
        group."
    ::= { crpmsVpdnGroupEntry 9 }

crpmsVpdnActiveOverflowCalls OBJECT-TYPE
    SYNTAX Gauge
    ACCESS read-only
    STATUS mandatory
    DESCRIPTION
        "The number of active overflow calls that belong to 
        this VPDN group."
    ::= { crpmsVpdnGroupEntry 10 }

crpmsVpdnRejections OBJECT-TYPE
    SYNTAX Counter
    ACCESS read-only
    STATUS mandatory
    DESCRIPTION
        "The number of calls rejected because one of the group 
        limits (crpmsVpdnOverflowLimit, crpmsVpdnMlpBundleLimit 
        and crpmsVpdnLinksPerBundleLimit) was exceeded."
    ::= { crpmsVpdnGroupEntry 11 }

crpmsVpdnSizeRejections OBJECT-TYPE
    SYNTAX Counter
    ACCESS read-only
    STATUS mandatory
    DESCRIPTION
        "The number of rejected calls of the VPDN group, because 
        the max allowed size limit (crpmsVpdnOverflowLimit + 
        crpmsVpdnLimit) was exceeded."
    ::= { crpmsVpdnGroupEntry 12 }

crpmsVpdnLimitThreshold OBJECT-TYPE
    SYNTAX Gauge(0..100)
--  Units
--    percent
    ACCESS read-write
    STATUS mandatory
    DESCRIPTION
        "A threshold defined for the vpdn group limit 
         (crpmsVpdnLimit) which, when crossed, triggers a 
         crpmsRisingAlarm or a crpmsFallingAlarm notification
         (refer to the notification definitions in this MIB
         for more details).
        
         A value of 100 percent cannot be exceeded and therefore 
         disables this threshold setting. A value of 0 percent is 
         always exceeded."
    DEFVAL { 100 }
    ::= { crpmsVpdnGroupEntry 13 }

crpmsVpdnEntryStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Used to create, delete or modify this row. None of the 
        columnar objects can be modified except this one, when
        the row is active."
    ::= { crpmsVpdnGroupEntry 14 }

crpmsVpdnGroupCpTable OBJECT-TYPE
    SYNTAX SEQUENCE OF CrpmsVpdnGroupCpEntry
    ACCESS not-accessible
    STATUS mandatory
    DESCRIPTION
        "A VPDN group can be associated with a number of customer
        profiles, this table represents this relationship. It's
        double indexed by index of crpmsVpdnGroupTable and index
        of crpmsCpTable. If rows are added to or removed from
        one of two tables, Its corresponding row(s) in this
        table will be added or removed as well."
    ::= { crpmsVpdn 2 }

crpmsVpdnGroupCpEntry OBJECT-TYPE
    SYNTAX CrpmsVpdnGroupCpEntry
    ACCESS not-accessible
    STATUS mandatory
    DESCRIPTION
        "A VPDN group customer profile entry contains information 
        of SLA associated with this VPDN group."
    INDEX { crpmsVpdnGroupCpVpdnGroupName, --?? IMPLIED may cause problems
            IMPLIED crpmsVpdnGroupCpCpName }
    ::= { crpmsVpdnGroupCpTable 1 }

CrpmsVpdnGroupCpEntry ::= SEQUENCE {
    crpmsVpdnGroupCpVpdnGroupName SnmpAdminString,
    crpmsVpdnGroupCpCpName SnmpAdminString,
    crpmsVpdnGroupCpEntryStatus RowStatus
    }

crpmsVpdnGroupCpVpdnGroupName OBJECT-TYPE
    SYNTAX SnmpAdminString(SIZE(1..31))
--    Rsyntax OCTET STRING(SIZE(1..31))
    ACCESS not-accessible
    STATUS mandatory
    DESCRIPTION
        "The name of VPDN groups in the table."
    ::= { crpmsVpdnGroupCpEntry 1 }

crpmsVpdnGroupCpCpName OBJECT-TYPE
    SYNTAX SnmpAdminString(SIZE(1..31))
--    Rsyntax OCTET STRING(SIZE(1..31))
    ACCESS not-accessible
    STATUS mandatory
    DESCRIPTION
        "The name of customer profile in the table."
    ::= { crpmsVpdnGroupCpEntry 2 }

crpmsVpdnGroupCpEntryStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Used to create, delete or modify this row. None of the 
        columnar objects can be modified except this one, when
        the row is active."
    ::= { crpmsVpdnGroupCpEntry 3 }

crpmsAlarmObject OBJECT-TYPE
    SYNTAX OBJECT IDENTIFIER
    ACCESS not-accessible
    STATUS mandatory
    DESCRIPTION
        "The object identifier of the destination object 
        related to the notification. For example, if 
        crpmsCpLimitThreshold is crossed, this variable
        should have the OID of crpmsCpLimit."
    ::= { crpmsNotif 1 }

crpmsAlarmValue OBJECT-TYPE
    SYNTAX Gauge
    ACCESS not-accessible
    STATUS mandatory
    DESCRIPTION
        "The current value that caused the threshold alarm
        to be sent."
    ::= { crpmsNotif 2 }

crpmsAlarmThresholdObject OBJECT-TYPE
    SYNTAX OBJECT IDENTIFIER
    ACCESS not-accessible
    STATUS mandatory
    DESCRIPTION
        "The object identifier of the Threshold that is related
         to the notification. For example, if 
              crpmsCpLimitThreshold is crossed, this variable should
              have the OID of crpmsCpLimitThreshold."
    ::= { crpmsNotif 3 }

crpmsRisingAlarm TRAP-TYPE
-- Reverse mappable trap
    ENTERPRISE ciscoRpmsMIBNotificationPrefix
    VARIABLES {
        crpmsAlarmObject, crpmsAlarmValue, 
        crpmsAlarmThresholdObject }
--  Status
--    mandatory
    DESCRIPTION
        "This trap is generated to notify the manager(s) that 
         one of the thresholds is crossed in rising direction
         (exceeded).
         
         The same trap will not be generated until the sample 
         value falls below the threshold low water mark and rises
         to cross it again.
        
         NOTE: A threshold low water mark is by default 90% of the
               actual threshold percentage (threshold * 90%) integer
               rounded."
    ::= 1

crpmsFallingAlarm TRAP-TYPE
-- Reverse mappable trap
    ENTERPRISE ciscoRpmsMIBNotificationPrefix
    VARIABLES {
        crpmsAlarmObject, crpmsAlarmValue, 
        crpmsAlarmThresholdObject }
--  Status
--    mandatory
    DESCRIPTION
        "This trap is generated to notify the manager(s) that one
         of the thresholds is crossed in the falling direction
         (reaches the threshold low water mark after being exceeded).
        
         The same trap will not be generated until the sample 
         value rises above the threshold and reaches the low water
         mark again.
        
         NOTE: A threshold low water mark is by default 90% of the
               actual threshold percentage (threshold * 90%) integer
               rounded."
    ::= 2

crpmsSystemGroup OBJECT IDENTIFIER ::= { ciscoRpmsMIBGroups 1 }
-- OBJECT-GROUP
--  Status
--    mandatory
--  Descr
--    This group contains a table providing the general 
--    system level information.
--  objects
--    crpmsSubsystemName, crpmsSubsystemUptime

crpmsCpGroup OBJECT IDENTIFIER ::= { ciscoRpmsMIBGroups 2 }
-- OBJECT-GROUP
--  Status
--    mandatory
--  Descr
--    This group contains a table providing the information 
--    of customer profile.
--  objects
--    crpmsCpLimit, crpmsCpOverflowLimit, crpmsCpActiveCalls, 
--    crpmsCpActiveOverflowCalls, crpmsCpAttemptedCalls, 
--    crpmsCpAttemptedOverflowCalls, crpmsCpRejections, 
--    crpmsCpOverflowRejections, crpmsCpLimitThreshold, 
--    crpmsCpOverflowLimitThreshold, crpmsCpCallRejectionThreshold, 
--    crpmsCpOverflowRejectThreshold, crpmsCpEntryStatus

crpmsVpdnGroup OBJECT IDENTIFIER ::= { ciscoRpmsMIBGroups 3 }
-- OBJECT-GROUP
--  Status
--    mandatory
--  Descr
--    This group contains tables providing the information 
--    of VPDN.
--  objects
--    crpmsVpdnTunnelId, crpmsVpdnTunnelProtocol, crpmsVpdnLimit, 
--    crpmsVpdnOverflowLimit, crpmsVpdnMlpBundleLimit, 
--    crpmsVpdnLinksPerBundleLimit, crpmsVpdnBundles, 
--    crpmsVpdnActiveCalls, crpmsVpdnActiveOverflowCalls, 
--    crpmsVpdnRejections, crpmsVpdnSizeRejections, 
--    crpmsVpdnLimitThreshold, crpmsVpdnEntryStatus, 
--    crpmsVpdnGroupCpEntryStatus

crpmsNotifGroup OBJECT IDENTIFIER ::= { ciscoRpmsMIBGroups 4 }
-- OBJECT-GROUP
--  Status
--    mandatory
--  Descr
--    This group contains helper objects specifying
--    notifications.
--  objects
--    crpmsAlarmObject, crpmsAlarmValue, crpmsAlarmThresholdObject

crpmsThresholdNotifGroup OBJECT IDENTIFIER ::= { ciscoRpmsMIBGroups 5 }
-- NOTIFICATION-GROUP
--  Status
--    mandatory
--  Descr
--    This group contains threshold crossing related alarms and
--     notifications.
--  notifications
--    crpmsRisingAlarm, crpmsFallingAlarm

ciscoRpmsMIBCompliance OBJECT IDENTIFIER ::= { ciscoRpmsMIBCompliances 1 }
-- MODULE-COMPLIANCE
--  Status
--    mandatory
--  Descr
--    The compliance statement for entities which implement
--    the Cisco-RPMS-MIB
--  Module
--    >>current<<
--   MandGroup
--    crpmsSystemGroup
--   MandGroup
--    crpmsCpGroup
--   MandGroup
--    crpmsVpdnGroup
--   MandGroup
--    crpmsNotifGroup
--   MandGroup
--    crpmsThresholdNotifGroup
--   ObjVar
--    crpmsSubsystemName
--   ObjVar
--    crpmsSubsystemUptime
--   ObjVar
--    crpmsCpActiveCalls
--   ObjVar
--    crpmsCpActiveOverflowCalls
--   ObjVar
--    crpmsCpAttemptedCalls
--   ObjVar
--    crpmsCpAttemptedOverflowCalls
--   ObjVar
--    crpmsCpRejections
--   ObjVar
--    crpmsCpOverflowRejections
--   ObjVar
--    crpmsVpdnTunnelId
--   ObjVar
--    crpmsVpdnBundles
--   ObjVar
--    crpmsVpdnActiveCalls
--   ObjVar
--    crpmsVpdnActiveOverflowCalls
--   ObjVar
--    crpmsVpdnRejections
--   ObjVar
--    crpmsVpdnSizeRejections


END
