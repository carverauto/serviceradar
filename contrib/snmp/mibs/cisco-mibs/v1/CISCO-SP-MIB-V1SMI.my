-- MIB file created 20-Jan-2006 11:53:32, by
--   SMICng version 2.2.11-beta(PRO)(Solaris), January 20, 2001. Enterprise key cisco.com

CISCO-SP-MIB DEFINITIONS ::= BEGIN

-- From file: "CISCO-SP-MIB.my"
-- Compile options "4 7 F H N O W 03 06 0B 0G 0N 0T"

IMPORTS
    InterfaceIndexOrZero
            FROM CISCO-TC
    DisplayString, TimeStamp, TruthValue
            FROM SNMPv2-TC-v1
    ciscoExperiment
            FROM CISCO-SMI
    Counter, Gauge, TimeTicks
            FROM RFC1155-SMI
    OBJECT-TYPE
            FROM RFC-1212
    TRAP-TYPE
            FROM RFC-1215;

ciscoSpMIB OBJECT IDENTIFIER ::= { ciscoExperiment 73 }
-- MODULE-IDENTITY
--  LastUpdated
--    200601160000Z
--  OrgName
--    Cisco Systems, Inc.
--  ContactInfo
--           Cisco Systems, Inc
--            Customer Service
--    
--    Postal: 170 W. Tasman Drive
--            San Jose, CA  95134
--            USA
--    
--       Tel: +1 800 553-NETS
--    
--    E-mail: cs-ss7@cisco.com
--  Descr
--    The MIB for managing the SS7 Signalling Point (SP)
--    implemented in the Cisco IOS SS7 offload product.  The
--    relevant ITU documents describing this technology is
--    the ITU Q series, including ITU Q.700: Introduction to
--    CCITT Signalling System No. 7 and ITU Q.701 Functional
--    description of the message transfer part (MTP) of
--    Signalling System No. 7.
--    
--    This MIB models the SP as follows:
--    
--    The SP is associated with one or more point codes.
--    Each pointcode is associated with:
--      an ss7 variant, timers, and linksets.
--    
--    Linksets contain:
--      destination point code 
--      linkset byte/packet statistics,
--      accounting information per DPC and OPC
--      violation accounting information per DPC and OPC
--      links,
--      reference to incoming and outgoing ACL
--      reference to a routing table for each SS7 packet type
--    
--    Links contain:
--      timers, and byte/packet statistics.
--    
--    The figure below provides a diagrammatic representation
--    of the relationships. Each box may be replicated
--    providing multiple instances of the object. 
--    
--    '===>' indicates that the object to the left contains
--    a reference to the object to the right.
--    
--    '###>' indicates that the object to the left contains
--    an instance of the object to the right.
--    
--    The down arrow indicates that the object being pointed
--    to contains snmp indices of the objects above it.
--    
--    
--      ________________
--     |                |
--     |      Sp        |###> point code, timers
--     |________________|
--             |
--             V
--      ________________
--     |                |
--     |                |===> Accounting
--     |    Linkset     |===> Violation Accounting
--     |                |===> Incoming ACL
--     |                |===> Outgoing ACL
--     |________________|===> Routing Tables.
--             |
--             V
--      ________________
--     |     Link       |###> timers
--     |________________|===> statistics
--    
--    
--    
--  RevDate
--    200601160000Z
--  RevDescr
--    The CISCO-SP-MIB is obsolete and has been replaced 
--     by the combination of the CISCO-ITP-TC-MIB and 
--     CISCO-ITP-GSP-MIB.
--    
--     Updated the mib to import Unsigned32 from SNMPv2-SMI 
--     instead of CISCO-TC.
--     Modified the syntax of CSpRouteTableName and 
--     CSpLinksetId to OCTET STRING.
--     Changed the order of objects in cSpAccountingTableEntry
--     SEQUENCE.
--     Added the notification group ciscoSpNotificationsGroup
--     and included it in the MODULE-COMPLIANCE as optional.
--  RevDate
--    200106070000Z
--  RevDescr
--    Initial version of this MIB module.

ciscoSpMIBObjects OBJECT IDENTIFIER ::= { ciscoSpMIB 1 }
cSpScalars      OBJECT IDENTIFIER ::= { ciscoSpMIBObjects 1 }
cSpLinkset      OBJECT IDENTIFIER ::= { ciscoSpMIBObjects 2 }
cSpLink         OBJECT IDENTIFIER ::= { ciscoSpMIBObjects 3 }
cSpRoute        OBJECT IDENTIFIER ::= { ciscoSpMIBObjects 4 }
cSpAccessControlList OBJECT IDENTIFIER ::= { ciscoSpMIBObjects 5 }
cSpAccounting   OBJECT IDENTIFIER ::= { ciscoSpMIBObjects 6 }
cSpNotificationsEnable OBJECT IDENTIFIER ::= { ciscoSpMIBObjects 7 }
ciscoSpMIBNotificationPrefix OBJECT IDENTIFIER ::= { ciscoSpMIB 2 }
ciscoSpMIBNotifications OBJECT IDENTIFIER ::= { ciscoSpMIBNotificationPrefix 0 }
ciscoSpMIBConformance OBJECT IDENTIFIER ::= { ciscoSpMIB 3 }
ciscoSpMIBCompliances OBJECT IDENTIFIER ::= { ciscoSpMIBConformance 1 }
ciscoSpMIBGroups OBJECT IDENTIFIER ::= { ciscoSpMIBConformance 2 }

CSpPointCode ::= Gauge(0..16777216)
-- TEXTUAL-CONVENTION
--  Status
--    mandatory
--  Descr
--    The SS7 network node address as specified in the
--    International Telecommunication Union standard Q.708:
--    Specifications of Signalling System No. 7 - Numbering
--    of International Signalling Point Codes, and by ANSI
--    T1.111.8 Numbering of Signalling Point Codes.

CSpSs7Variant ::= INTEGER {
        ansi(1),
        itu(2)
        }
-- TEXTUAL-CONVENTION
--  Status
--    mandatory
--  Descr
--    The list of SS7 variants.
--    'ANSI'    : The ANSI variant of the SS7 specification.
--    'ITU'     : The ITU variant of the SS7 specification.

CSpLinkType ::= INTEGER {
        other(1),
        serial(2),
        sctpIp(3)
        }
-- TEXTUAL-CONVENTION
--  Status
--    mandatory
--  Descr
--    The link types.
--    'other'  : This link is of some type not listed below.
--    'serial' : This link is an serial link transporting
--                 SS7 traffic.
--    'sctpIp' : This a SCTP/IP link.

CSpLinkSLC ::= Gauge(0..15)
-- TEXTUAL-CONVENTION
--  Status
--    mandatory
--  Descr
--    The Signalling Link Code. This is the link identifier
--    within a linkset.

CSpLinksetId ::= OCTET STRING(SIZE(1..19))
-- TEXTUAL-CONVENTION
--  Status
--    mandatory
--  Descr
--    The configured name associated with an Sp Linkset.

CSpAclAction ::= INTEGER {
        accept(1),
        discard(2)
        }
-- TEXTUAL-CONVENTION
--  Status
--    mandatory
--  Descr
--    The list of possible actions to be performed on a
--    packet who's point code matches an access control.
--    'accept'  : The matching packet is accepted for
--                further processing.
--    'discard' : The matching packet is to be discarded
--                without any further processing on this 
--                packet.

CSpOsiState ::= INTEGER {
        active(1),
        inactive(2),
        inhibited(3),
        uninhibited(4),
        shut(5),
        noshut(6)
        }
-- TEXTUAL-CONVENTION
--  Status
--    mandatory
--  Descr
--    The list of possible link/linkset statuses.
--    'active'     : Traffic may flow over this link/linkset
--    'inactive'   : Traffic cannot flow over this 
--                   link/linkset.
--    'inhibited'  : Traffic cannot flow over this 
--                   link/linkset. This state was reached
--                   as a result of administrative action.
--    'uninhibited': The link/linkset is available at the
--                   MTP3 layer. 
--    'shut       ': The link/linkset has been forced to an
--                   unavailable state by an administrative
--                   action.
--    'noshut     ': The link/linkset has been removed from
--                   an unavailable state by an 
--                   administrative action.

CSpAclId ::= Gauge(0..2999)
-- TEXTUAL-CONVENTION
--  Status
--    mandatory
--  Descr
--    An numeric Identifier used to specify and access list 
--     used to permit and deny packets based on MTP3 
--     information.

CSpRouteTableName ::= OCTET STRING(SIZE(1..19))
-- TEXTUAL-CONVENTION
--  Status
--    mandatory
--  Descr
--    The configured name associated with an SP Route
--    Table.

CSpAclSi ::= Gauge(0..15)
-- TEXTUAL-CONVENTION
--  Status
--    mandatory
--  Descr
--    The list of possible Service Indicator values. This
--    identifies the type of SS7 packet.
--    
--    The service indicator codes for the international
--    signalling network are allocated as follows:
--    
--    0 Signalling network management messages (SNMM)
--    1 Signalling network testing and maintenance
--        messages (SNTM)
--    2 Spare 2
--    3 SCCP
--    4 Telephone User Part (TUP)
--    5 ISDN User Part      (ISUP)
--    6 Data User Part, call and circuit-related 
--        messages (DUPC)
--    7 Data User Part, facility registration and 
--        cancellation messages (DUPF)
--    8 Reserved for MTP Testing User Part (MTUP)
--    9 Broadband ISDN User Part  (BISUP)
--    10 Satellite ISDN User Part (SISUP)
--    11 Spare
--    12 Spare
--    13 Spare
--    14 Spare
--    15 Spare
--    Reference: ITU Q.704 Signalling network functions 
--               and messages section 14.2.1 Service
--               indicator.

CSpRouteStatus ::= INTEGER {
        available(1),
        restricted(2),
        unavailable(3)
        }
-- TEXTUAL-CONVENTION
--  Status
--    mandatory
--  Descr
--    The status of the route from the perspective of the 
--     SP. 
--    'available'   : Route is available for routing of 
--                    packets.
--    'restricted'  : Route has been restricted from 
--                    routing.
--    'unavailable' : Route is unavailable for routing of 
--                    packets.

cSpSs7Variant OBJECT-TYPE
    SYNTAX CSpSs7Variant
--    Rsyntax INTEGER {
--        ansi(1),
--        itu(2)
--        }
    ACCESS read-only
    STATUS mandatory
    DESCRIPTION
        "The SS7 variant implemented in this SP."
    ::= { cSpScalars 1 }

cSpPointCode OBJECT-TYPE
    SYNTAX CSpPointCode
--    Rsyntax Gauge(0..16777216)
    ACCESS read-only
    STATUS mandatory
    DESCRIPTION
        "The point code for this SP."
    ::= { cSpScalars 2 }

cSpMtp2T01 OBJECT-TYPE
    SYNTAX Gauge
--  Units
--    milli-seconds
    ACCESS read-only
    STATUS mandatory
    DESCRIPTION
        "Alignment ready timer. The default and valid range is
        dependant on the value of cSpSs7Variant. The ranges 
        are defined in the following references."
    REFERENCE
        "ITU Q.703 Signalling Link.
        ANSI T1.111.3 Telecommunications - Signaling system
        No. 7 (SS7)-Message Transfer Part (MTP)."
    ::= { cSpScalars 3 }

cSpMtp2T02 OBJECT-TYPE
    SYNTAX Gauge
--  Units
--    100 milli-seconds
    ACCESS read-only
    STATUS mandatory
    DESCRIPTION
        "Not aligned timer. The default and valid range is
        dependant on the value of cSpSs7Variant.
        The ranges are defined in the following references.
        
        This timer is only applicable if cSpLinkType
        is serial. A get on this object will return a
        zero if cSpLinkType is not serial."
    REFERENCE
        "ITU Q.703 Signalling Link.
        ANSI T1.111.3 Telecommunications - Signaling system
        No. 7 (SS7)-Message Transfer Part (MTP)."
    ::= { cSpScalars 4 }

cSpMtp2T03 OBJECT-TYPE
    SYNTAX Gauge
--  Units
--    milli-seconds
    ACCESS read-only
    STATUS mandatory
    DESCRIPTION
        "Aligned timer. The default and valid range is
        dependant on the value of cSpSs7Variant. The ranges 
        are defined in the following references."
    REFERENCE
        "ITU Q.703 Signalling Link.
        ANSI T1.111.3 Telecommunications - Signaling system
        No. 7 (SS7)-Message Transfer Part (MTP)."
    ::= { cSpScalars 5 }

cSpMtp2T4N OBJECT-TYPE
    SYNTAX Gauge
--  Units
--    milli-seconds
    ACCESS read-only
    STATUS mandatory
    DESCRIPTION
        "Proving period timer normal timer. The default and
        valid range is dependant on the value of
        cSpSs7Variant. The ranges are defined in the 
        following references. "
    REFERENCE
        "ITU Q.703 Signalling Link.
        ANSI T1.111.3 Telecommunications - Signaling system
        No. 7 (SS7)-Message Transfer Part (MTP)."
    ::= { cSpScalars 6 }

cSpMtp2T4E OBJECT-TYPE
    SYNTAX Gauge
--  Units
--    milli-seconds
    ACCESS read-only
    STATUS mandatory
    DESCRIPTION
        "Proving period timer emergency timer. The default and
        valid range is dependant on the value of
        cSpSs7Variant.  The ranges are defined in the 
        following references."
    REFERENCE
        "ITU Q.703 Signalling Link.
        ANSI T1.111.3 Telecommunications - Signaling system
        No. 7 (SS7)-Message Transfer Part (MTP)."
    ::= { cSpScalars 7 }

cSpMtp2T05 OBJECT-TYPE
    SYNTAX Gauge
--  Units
--    milli-seconds
    ACCESS read-only
    STATUS mandatory
    DESCRIPTION
        "Sending SIB timer. The default and valid range is
        dependant on the value of cSpSs7Variant.
        The ranges are defined in the following references."
    REFERENCE
        "ITU Q.703 Signalling Link.
        ANSI T1.111.3 Telecommunications - Signaling system
        No. 7 (SS7)-Message Transfer Part (MTP)."
    ::= { cSpScalars 8 }

cSpMtp2T06 OBJECT-TYPE
    SYNTAX Gauge
--  Units
--    milli-seconds.
    ACCESS read-only
    STATUS mandatory
    DESCRIPTION
        "Remote congestion timer. The default and valid range is
        dependant on the value of cSpSs7Variant.
        The ranges are defined in the following references."
    REFERENCE
        "ITU Q.703 Signalling Link.
        ANSI T1.111.3 Telecommunications - Signaling system
        No. 7 (SS7)-Message Transfer Part (MTP)."
    ::= { cSpScalars 9 }

cSpMtp2T07 OBJECT-TYPE
    SYNTAX Gauge
--  Units
--    milli-seconds.
    ACCESS read-only
    STATUS mandatory
    DESCRIPTION
        "Excessive delay of acknowledgement timer. The default
        and valid range is dependant on the value of
        cSpSs7Variant. The ranges are defined in the following
        references."
    REFERENCE
        "ITU Q.703 Signalling Link.
        ANSI T1.111.3 Telecommunications - Signaling system
        No. 7 (SS7)-Message Transfer Part (MTP)."
    ::= { cSpScalars 10 }

cSpMtp2T08 OBJECT-TYPE
    SYNTAX Gauge
    ACCESS read-only
    STATUS mandatory
    DESCRIPTION
        "Interval timer for error interval monitor."
    REFERENCE
        "ITU Q.703 Signalling Link.
        ANSI T1.111.3 Telecommunications - Signaling system
        No. 7 (SS7)-Message Transfer Part (MTP)."
    ::= { cSpScalars 11 }

cSpMtp3T01 OBJECT-TYPE
    SYNTAX Gauge
    ACCESS read-only
    STATUS mandatory
    DESCRIPTION
        "Delay to avoid message mis-sequencing on changeover."
    REFERENCE
        "ITU Q.704 Signalling network functions and messages.
        ANSI T1.111 Telecommunications - Signaling system
        No. 7 (SS7)-Message Transfer Part (MTP)."
    ::= { cSpScalars 12 }

cSpMtp3T02 OBJECT-TYPE
    SYNTAX Gauge
    ACCESS read-only
    STATUS mandatory
    DESCRIPTION
        "Waiting for changeover acknowledgement."
    REFERENCE
        "ITU Q.704 Signalling network functions and messages.
        ANSI T1.111 Telecommunications - Signaling system
        No. 7 (SS7)-Message Transfer Part (MTP)."
    ::= { cSpScalars 13 }

cSpMtp3T03 OBJECT-TYPE
    SYNTAX Gauge
    ACCESS read-only
    STATUS mandatory
    DESCRIPTION
        "Time controlled diversion-delay to avoid
        mis-sequencing on change back."
    REFERENCE
        "ITU Q.704 Signalling network functions and messages.
        ANSI T1.111 Telecommunications - Signaling system
        No. 7 (SS7)-Message Transfer Part (MTP)."
    ::= { cSpScalars 14 }

cSpMtp3T04 OBJECT-TYPE
    SYNTAX Gauge
    ACCESS read-only
    STATUS mandatory
    DESCRIPTION
        "Waiting for change back acknowledgement (first
        attempt)."
    REFERENCE
        "ITU Q.704 Signalling network functions and messages.
        ANSI T1.111 Telecommunications - Signaling system
        No. 7 (SS7)-Message Transfer Part (MTP)."
    ::= { cSpScalars 15 }

cSpMtp3T05 OBJECT-TYPE
    SYNTAX Gauge
    ACCESS read-only
    STATUS mandatory
    DESCRIPTION
        "Waiting for change back acknowledgement (second
        attempt)."
    REFERENCE
        "ITU Q.704 Signalling network functions and messages.
        ANSI T1.111 Telecommunications - Signaling system
        No. 7 (SS7)-Message Transfer Part (MTP)."
    ::= { cSpScalars 16 }

cSpMtp3T06 OBJECT-TYPE
    SYNTAX Gauge
    ACCESS read-only
    STATUS mandatory
    DESCRIPTION
        "Delay to avoid message mis-sequencing on controlled
        rerouting."
    REFERENCE
        "ITU Q.704 Signalling network functions and messages.
        ANSI T1.111 Telecommunications - Signaling system
        No. 7 (SS7)-Message Transfer Part (MTP)."
    ::= { cSpScalars 17 }

cSpMtp3T07 OBJECT-TYPE
    SYNTAX Gauge
    ACCESS read-only
    STATUS mandatory
    DESCRIPTION
        "Waiting for signalling data link connection
        acknowledgement."
    REFERENCE
        "ITU Q.704 Signalling network functions and messages.
        ANSI T1.111 Telecommunications - Signaling system
        No. 7 (SS7)-Message Transfer Part (MTP)."
    ::= { cSpScalars 18 }

cSpMtp3T08 OBJECT-TYPE
    SYNTAX Gauge
    ACCESS read-only
    STATUS mandatory
    DESCRIPTION
        "Transfer prohibited inhibition timer (transient
        solution)."
    REFERENCE
        "ITU Q.704 Signalling network functions and messages.
        ANSI T1.111 Telecommunications - Signaling system
        No. 7 (SS7)-Message Transfer Part (MTP)."
    ::= { cSpScalars 19 }

cSpMtp3T10 OBJECT-TYPE
    SYNTAX Gauge
    ACCESS read-only
    STATUS mandatory
    DESCRIPTION
        "Waiting to repeat signalling routeset test message."
    REFERENCE
        "ITU Q.704 Signalling network functions and messages.
        ANSI T1.111 Telecommunications - Signaling system
        No. 7 (SS7)-Message Transfer Part (MTP)."
    ::= { cSpScalars 20 }

cSpMtp3T11 OBJECT-TYPE
    SYNTAX Gauge
    ACCESS read-only
    STATUS mandatory
    DESCRIPTION
        "Transfer restricted timer. (This is one way of
        implementing the function described in 13.4/Q.704 and
        mainly intended to simplify SPs.)."
    REFERENCE
        "ITU Q.704 Signalling network functions and messages.
        ANSI T1.111 Telecommunications - Signaling system
        No. 7 (SS7)-Message Transfer Part (MTP)."
    ::= { cSpScalars 21 }

cSpMtp3T12 OBJECT-TYPE
    SYNTAX Gauge
    ACCESS read-only
    STATUS mandatory
    DESCRIPTION
        "Waiting for uninhibit acknowledgement."
    REFERENCE
        "ITU Q.704 Signalling network functions and messages.
        ANSI T1.111 Telecommunications - Signaling system
        No. 7 (SS7)-Message Transfer Part (MTP)."
    ::= { cSpScalars 22 }

cSpMtp3T13 OBJECT-TYPE
    SYNTAX Gauge
    ACCESS read-only
    STATUS mandatory
    DESCRIPTION
        "Waiting for force uninhibit."
    REFERENCE
        "ITU Q.704 Signalling network functions and messages.
        ANSI T1.111 Telecommunications - Signaling system
        No. 7 (SS7)-Message Transfer Part (MTP)."
    ::= { cSpScalars 23 }

cSpMtp3T14 OBJECT-TYPE
    SYNTAX Gauge
    ACCESS read-only
    STATUS mandatory
    DESCRIPTION
        "Waiting for inhibition acknowledgement."
    REFERENCE
        "ITU Q.704 Signalling network functions and messages.
        ANSI T1.111 Telecommunications - Signaling system
        No. 7 (SS7)-Message Transfer Part (MTP)."
    ::= { cSpScalars 24 }

cSpMtp3T15 OBJECT-TYPE
    SYNTAX Gauge
    ACCESS read-only
    STATUS mandatory
    DESCRIPTION
        "Waiting to start signalling routeset congestion
        test."
    REFERENCE
        "ITU Q.704 Signalling network functions and messages.
        ANSI T1.111 Telecommunications - Signaling system
        No. 7 (SS7)-Message Transfer Part (MTP)."
    ::= { cSpScalars 25 }

cSpMtp3T16 OBJECT-TYPE
    SYNTAX Gauge
    ACCESS read-only
    STATUS mandatory
    DESCRIPTION
        "Waiting for routeset congestion status update."
    REFERENCE
        "ITU Q.704 Signalling network functions and messages.
        ANSI T1.111 Telecommunications - Signaling system
        No. 7 (SS7)-Message Transfer Part (MTP)."
    ::= { cSpScalars 26 }

cSpMtp3T17 OBJECT-TYPE
    SYNTAX Gauge
    ACCESS read-only
    STATUS mandatory
    DESCRIPTION
        "Delay to avoid oscillation of initial alignment
        failure and link restart."
    REFERENCE
        "ITU Q.704 Signalling network functions and messages.
        ANSI T1.111 Telecommunications - Signaling system
        No. 7 (SS7)-Message Transfer Part (MTP)."
    ::= { cSpScalars 27 }

cSpMtp3T18 OBJECT-TYPE
    SYNTAX Gauge
    ACCESS read-only
    STATUS mandatory
    DESCRIPTION
        "Timer within a signalling point whose MTP restarts,
        for supervising link and linkset activation as well as
        the receipt of routing information."
    REFERENCE
        "ITU Q.704 Signalling network functions and messages.
        ANSI T1.111 Telecommunications - Signaling system
        No. 7 (SS7)-Message Transfer Part (MTP)."
    ::= { cSpScalars 28 }

cSpMtp3T19 OBJECT-TYPE
    SYNTAX Gauge
    ACCESS read-only
    STATUS mandatory
    DESCRIPTION
        "Supervision timer during MTP restart to avoid
        possible ping-pong of TFP, TFR2) and TRA messages."
    REFERENCE
        "ITU Q.704 Signalling network functions and messages.
        ANSI T1.111 Telecommunications - Signaling system
        No. 7 (SS7)-Message Transfer Part (MTP)."
    ::= { cSpScalars 29 }

cSpMtp3T20 OBJECT-TYPE
    SYNTAX Gauge
    ACCESS read-only
    STATUS mandatory
    DESCRIPTION
        "Overall MTP restart timer at the signalling point
        whose MTP restarts. Overall MTP restart timer at a
        signalling point adjacent to one whose MTP restarts."
    REFERENCE
        "ITU Q.704 Signalling network functions and messages.
        ANSI T1.111 Telecommunications - Signaling system
        No. 7 (SS7)-Message Transfer Part (MTP)."
    ::= { cSpScalars 30 }

cSpMtp3T21 OBJECT-TYPE
    SYNTAX Gauge
    ACCESS read-only
    STATUS mandatory
    DESCRIPTION
        "Overall MTP restart timer at a signalling point
        adjacent to one whose MTP restarts."
    REFERENCE
        "ITU Q.704 Signalling network functions and messages.
        ANSI T1.111 Telecommunications - Signaling system
        No. 7 (SS7)-Message Transfer Part (MTP)."
    ::= { cSpScalars 31 }

cSpMtp3T22 OBJECT-TYPE
    SYNTAX Gauge
    ACCESS read-only
    STATUS mandatory
    DESCRIPTION
        "Local inhibit test timer."
    REFERENCE
        "ITU Q.704 Signalling network functions and messages.
        ANSI T1.111 Telecommunications - Signaling system
        No. 7 (SS7)-Message Transfer Part (MTP)."
    ::= { cSpScalars 32 }

cSpMtp3T23 OBJECT-TYPE
    SYNTAX Gauge
    ACCESS read-only
    STATUS mandatory
    DESCRIPTION
        "Remote inhibit test timer."
    REFERENCE
        "ITU Q.704 Signalling network functions and messages.
        ANSI T1.111 Telecommunications - Signaling system
        No. 7 (SS7)-Message Transfer Part (MTP)."
    ::= { cSpScalars 33 }

cSpMtp3T24 OBJECT-TYPE
    SYNTAX Gauge
    ACCESS read-only
    STATUS mandatory
    DESCRIPTION
        "Stabilizing timer after removal of local processor
        outage, used in LPO latching to RPO (national option)"
    REFERENCE
        "ITU Q.704 Signalling network functions and messages.
        ANSI T1.111 Telecommunications - Signaling system
        No. 7 (SS7)-Message Transfer Part (MTP)."
    ::= { cSpScalars 34 }

cSpMtp3T25 OBJECT-TYPE
    SYNTAX Gauge
--  Units
--    seconds.
    ACCESS read-only
    STATUS mandatory
    DESCRIPTION
        "Timer at Signalling Point (SP) adjacent to restarting
        SP, waiting for traffic restart allowed message."
    REFERENCE
        "ANSI T1.111 Telecommunications - Signaling system
        No. 7 (SS7)-Message Transfer Part (MTP)"
    ::= { cSpScalars 35 }

cSpMtp3T26 OBJECT-TYPE
    SYNTAX Gauge
--  Units
--    seconds.
    ACCESS read-only
    STATUS mandatory
    DESCRIPTION
        "Timer at restarting SP waiting to repeat traffic
        restart waiting message."
    REFERENCE
        "ANSI T1.111 Telecommunications - Signaling system
        No. 7 (SS7)-Message Transfer Part (MTP)"
    ::= { cSpScalars 36 }

cSpMtp3T27 OBJECT-TYPE
    SYNTAX Gauge
--  Units
--    seconds.
    ACCESS read-only
    STATUS mandatory
    DESCRIPTION
        "Minimum duration of unavailability for full restart."
    REFERENCE
        "ANSI T1.111 Telecommunications - Signaling system
        No. 7 (SS7)-Message Transfer Part (MTP)"
    ::= { cSpScalars 37 }

cSpMtp3T28 OBJECT-TYPE
    SYNTAX Gauge
--  Units
--    seconds.
    ACCESS read-only
    STATUS mandatory
    DESCRIPTION
        "Timer at SP adjacent to restarting SP waiting for
        traffic restart waiting message."
    REFERENCE
        "ANSI T1.111 Telecommunications - Signaling system
        No. 7 (SS7)-Message Transfer Part (MTP)"
    ::= { cSpScalars 38 }

cSpMtp3T29 OBJECT-TYPE
    SYNTAX Gauge
--  Units
--    seconds.
    ACCESS read-only
    STATUS mandatory
    DESCRIPTION
        "Timer started when TRA sent in response to unexpected
        TRA or TRW."
    REFERENCE
        "ANSI T1.111 Telecommunications - Signaling system
        No. 7 (SS7)-Message Transfer Part (MTP)"
    ::= { cSpScalars 39 }

cSpMtp3T30 OBJECT-TYPE
    SYNTAX Gauge
--  Units
--    seconds.
    ACCESS read-only
    STATUS mandatory
    DESCRIPTION
        "Timer to limit sending of TFPs and TFRs in response
        to unexpected TRA or TRW."
    REFERENCE
        "ANSI T1.111 Telecommunications - Signaling system
        No. 7 (SS7)-Message Transfer Part (MTP)"
    ::= { cSpScalars 40 }

cSpMtp3T31 OBJECT-TYPE
    SYNTAX Gauge
--  Units
--    seconds.
    ACCESS read-only
    STATUS mandatory
    DESCRIPTION
        "False link congestion detection timer."
    REFERENCE
        "ANSI T1.111 Telecommunications - Signaling system
        No. 7 (SS7)-Message Transfer Part (MTP)"
    ::= { cSpScalars 41 }

cSpMtp3T32 OBJECT-TYPE
    SYNTAX Gauge
--  Units
--    seconds.
    ACCESS read-only
    STATUS mandatory
    DESCRIPTION
        "Link oscillation timer - Procedure A."
    REFERENCE
        "ANSI T1.111 Telecommunications - Signaling system
        No. 7 (SS7)-Message Transfer Part (MTP)"
    ::= { cSpScalars 42 }

cSpMtp3T33 OBJECT-TYPE
    SYNTAX Gauge
--  Units
--    seconds.
    ACCESS read-only
    STATUS mandatory
    DESCRIPTION
        "Probation timer for link oscillation - Procedure B."
    REFERENCE
        "ANSI T1.111 Telecommunications - Signaling system
        No. 7 (SS7)-Message Transfer Part (MTP)"
    ::= { cSpScalars 43 }

cSpMtp3T34 OBJECT-TYPE
    SYNTAX Gauge
--  Units
--    seconds.
    ACCESS read-only
    STATUS mandatory
    DESCRIPTION
        "Suspension timer for link oscillation - Procedure B."
    REFERENCE
        "ANSI T1.111 Telecommunications - Signaling system
        No. 7 (SS7)-Message Transfer Part (MTP)"
    ::= { cSpScalars 44 }

cSpLinksetTable OBJECT-TYPE
    SYNTAX SEQUENCE OF CSpLinksetTableEntry
    ACCESS not-accessible
    STATUS mandatory
    DESCRIPTION
        "A table of linksets for this SP. "
    ::= { cSpLinkset 1 }

cSpLinksetTableEntry OBJECT-TYPE
    SYNTAX CSpLinksetTableEntry
    ACCESS not-accessible
    STATUS mandatory
    DESCRIPTION
        "A list of SP linkset attributes for a particular SP
        entity."
    INDEX { cSpLinksetName }
    ::= { cSpLinksetTable 1 }

CSpLinksetTableEntry ::= SEQUENCE {
    cSpLinksetName CSpLinksetId,
    cSpLinksetAdjacentPointCode CSpPointCode,
    cSpLinksetState CSpOsiState,
    cSpLinksetInboundAcl CSpAclId,
    cSpLinksetOutboundAcl CSpAclId,
    cSpLinksetSnmmRouteTableName CSpRouteTableName,
    cSpLinksetSntmRouteTableName CSpRouteTableName,
    cSpLinksetSpare2RouteTableName CSpRouteTableName,
    cSpLinksetSccpRouteTableName CSpRouteTableName,
    cSpLinksetTupRouteTableName CSpRouteTableName,
    cSpLinksetIsupRouteTableName CSpRouteTableName,
    cSpLinksetDupcRouteTableName CSpRouteTableName,
    cSpLinksetDupfRouteTableName CSpRouteTableName,
    cSpLinksetMtupRouteTableName CSpRouteTableName,
    cSpLinksetBisupRouteTableName CSpRouteTableName,
    cSpLinksetSisupRouteTableName CSpRouteTableName,
    cSpLinksetSpare11RouteTableName CSpRouteTableName,
    cSpLinksetSpare12RouteTableName CSpRouteTableName,
    cSpLinksetSpare13RouteTableName CSpRouteTableName,
    cSpLinksetSpare14RouteTableName CSpRouteTableName,
    cSpLinksetSpare15RouteTableName CSpRouteTableName,
    cSpLinksetAccountingEnabled TruthValue,
    cSpLinksetNumLinks Gauge,
    cSpLinksetPacketsSent Counter,
    cSpLinksetHCPacketsSent Counter,
    cSpLinksetPacketsRcvd Counter,
    cSpLinksetHCPacketsRcvd Counter,
    cSpLinksetBytesSent Counter,
    cSpLinksetHCBytesSent Counter,
    cSpLinksetBytesRcvd Counter,
    cSpLinksetHCBytesRcvd Counter,
    cSpLinksetDurationInService TimeTicks,
    cSpLinksetDurationOutService TimeTicks,
    cSpLinksetMtp2T01 Gauge,
    cSpLinksetMtp2T02 Gauge,
    cSpLinksetMtp2T03 Gauge,
    cSpLinksetMtp2T4N Gauge,
    cSpLinksetMtp2T4E Gauge,
    cSpLinksetMtp2T05 Gauge,
    cSpLinksetMtp2T06 Gauge,
    cSpLinksetMtp2T07 Gauge,
    cSpLinksetMtp2T08 Gauge,
    cSpLinksetMtp3T01 Gauge,
    cSpLinksetMtp3T02 Gauge,
    cSpLinksetMtp3T03 Gauge,
    cSpLinksetMtp3T04 Gauge,
    cSpLinksetMtp3T05 Gauge,
    cSpLinksetMtp3T06 Gauge,
    cSpLinksetMtp3T07 Gauge,
    cSpLinksetMtp3T08 Gauge,
    cSpLinksetMtp3T10 Gauge,
    cSpLinksetMtp3T11 Gauge,
    cSpLinksetMtp3T12 Gauge,
    cSpLinksetMtp3T13 Gauge,
    cSpLinksetMtp3T14 Gauge,
    cSpLinksetMtp3T15 Gauge,
    cSpLinksetMtp3T16 Gauge,
    cSpLinksetMtp3T17 Gauge,
    cSpLinksetMtp3T18 Gauge,
    cSpLinksetMtp3T19 Gauge,
    cSpLinksetMtp3T20 Gauge,
    cSpLinksetMtp3T21 Gauge,
    cSpLinksetMtp3T22 Gauge,
    cSpLinksetMtp3T23 Gauge,
    cSpLinksetMtp3T24 Gauge,
    cSpLinksetMtp3T25 Gauge,
    cSpLinksetMtp3T26 Gauge,
    cSpLinksetMtp3T27 Gauge,
    cSpLinksetMtp3T28 Gauge,
    cSpLinksetMtp3T29 Gauge,
    cSpLinksetMtp3T30 Gauge,
    cSpLinksetMtp3T31 Gauge,
    cSpLinksetMtp3T32 Gauge,
    cSpLinksetMtp3T33 Gauge,
    cSpLinksetMtp3T34 Gauge
    }

cSpLinksetName OBJECT-TYPE
    SYNTAX CSpLinksetId
--    Rsyntax OCTET STRING(SIZE(1..19))
    ACCESS not-accessible
    STATUS mandatory
    DESCRIPTION
        "The name of the linkset."
    ::= { cSpLinksetTableEntry 1 }

cSpLinksetAdjacentPointCode OBJECT-TYPE
    SYNTAX CSpPointCode
--    Rsyntax Gauge(0..16777216)
    ACCESS read-only
    STATUS mandatory
    DESCRIPTION
        "The point code to which this linkset is connected."
    ::= { cSpLinksetTableEntry 2 }

cSpLinksetState OBJECT-TYPE
    SYNTAX CSpOsiState
--    Rsyntax INTEGER {
--        active(1),
--        inactive(2),
--        inhibited(3),
--        uninhibited(4),
--        shut(5),
--        noshut(6)
--        }
    ACCESS read-only
    STATUS mandatory
    DESCRIPTION
        "The status of this linkset."
    ::= { cSpLinksetTableEntry 3 }

cSpLinksetInboundAcl OBJECT-TYPE
    SYNTAX CSpAclId
--    Rsyntax Gauge(0..2999)
    ACCESS read-only
    STATUS mandatory
    DESCRIPTION
        "Packets are filtered against this access control list 
         before they are passed to the routing function.  A
         value of zero indicates that no access control list
         is present."
    ::= { cSpLinksetTableEntry 4 }

cSpLinksetOutboundAcl OBJECT-TYPE
    SYNTAX CSpAclId
--    Rsyntax Gauge(0..2999)
    ACCESS read-only
    STATUS mandatory
    DESCRIPTION
        "Packets are filtered against this access control list 
         after they have passed through the routing function.  
         A value of zero indicates that no access control list
         is present."
    ::= { cSpLinksetTableEntry 5 }

cSpLinksetSnmmRouteTableName OBJECT-TYPE
    SYNTAX CSpRouteTableName
--    Rsyntax OCTET STRING(SIZE(1..19))
    ACCESS read-only
    STATUS mandatory
    DESCRIPTION
        "The routing table for signalling network management
        messages."
    REFERENCE
        "ITU Q.704 Signalling network functions and messages,
        section 14.2.1."
    ::= { cSpLinksetTableEntry 6 }

cSpLinksetSntmRouteTableName OBJECT-TYPE
    SYNTAX CSpRouteTableName
--    Rsyntax OCTET STRING(SIZE(1..19))
    ACCESS read-only
    STATUS mandatory
    DESCRIPTION
        "The routing table for signalling network test and
        maintenance messages."
    REFERENCE
        "ITU Q.704 Signalling network functions and messages,
        section 14.2.1."
    ::= { cSpLinksetTableEntry 7 }

cSpLinksetSpare2RouteTableName OBJECT-TYPE
    SYNTAX CSpRouteTableName
--    Rsyntax OCTET STRING(SIZE(1..19))
    ACCESS read-only
    STATUS mandatory
    DESCRIPTION
        "This routing table has been defined as a spare
        routing table by the standards committee."
    REFERENCE
        "ITU Q.704 Signalling network functions and messages,
        section 14.2.1."
    ::= { cSpLinksetTableEntry 8 }

cSpLinksetSccpRouteTableName OBJECT-TYPE
    SYNTAX CSpRouteTableName
--    Rsyntax OCTET STRING(SIZE(1..19))
    ACCESS read-only
    STATUS mandatory
    DESCRIPTION
        "The routing table for SS7 Signaling Connection
        Control Part(SCCP) messages."
    REFERENCE
        "ITU Q.704 Signalling network functions and messages,
        section 14.2.1."
    ::= { cSpLinksetTableEntry 9 }

cSpLinksetTupRouteTableName OBJECT-TYPE
    SYNTAX CSpRouteTableName
--    Rsyntax OCTET STRING(SIZE(1..19))
    ACCESS read-only
    STATUS mandatory
    DESCRIPTION
        "The routing table for Telephone User Part(TUP) 
         messages."
    REFERENCE
        "ITU Q.704 Signalling network functions and messages,
        section 14.2.1."
    ::= { cSpLinksetTableEntry 10 }

cSpLinksetIsupRouteTableName OBJECT-TYPE
    SYNTAX CSpRouteTableName
--    Rsyntax OCTET STRING(SIZE(1..19))
    ACCESS read-only
    STATUS mandatory
    DESCRIPTION
        "The routing table for ISDN User Part messages."
    REFERENCE
        "ITU Q.704 Signalling network functions and messages,
        section 14.2.1."
    ::= { cSpLinksetTableEntry 11 }

cSpLinksetDupcRouteTableName OBJECT-TYPE
    SYNTAX CSpRouteTableName
--    Rsyntax OCTET STRING(SIZE(1..19))
    ACCESS read-only
    STATUS mandatory
    DESCRIPTION
        "The routing table for Data User Part (call and
        circuit-related messages)."
    REFERENCE
        "ITU Q.704 Signalling network functions and messages,
        section 14.2.1."
    ::= { cSpLinksetTableEntry 12 }

cSpLinksetDupfRouteTableName OBJECT-TYPE
    SYNTAX CSpRouteTableName
--    Rsyntax OCTET STRING(SIZE(1..19))
    ACCESS read-only
    STATUS mandatory
    DESCRIPTION
        "The routing table for Data User Part (facility
        registration and cancellation messages)."
    REFERENCE
        "ITU Q.704 Signalling network functions and messages,
        section 14.2.1."
    ::= { cSpLinksetTableEntry 13 }

cSpLinksetMtupRouteTableName OBJECT-TYPE
    SYNTAX CSpRouteTableName
--    Rsyntax OCTET STRING(SIZE(1..19))
    ACCESS read-only
    STATUS mandatory
    DESCRIPTION
        "The routing table for MTP Testing User Part
        messages."
    REFERENCE
        "ITU Q.704 Signalling network functions and messages,
        section 14.2.1."
    ::= { cSpLinksetTableEntry 14 }

cSpLinksetBisupRouteTableName OBJECT-TYPE
    SYNTAX CSpRouteTableName
--    Rsyntax OCTET STRING(SIZE(1..19))
    ACCESS read-only
    STATUS mandatory
    DESCRIPTION
        "The routing table for Broadband ISDN User Part(BISUP)
        messages."
    REFERENCE
        "ITU Q.704 Signalling network functions and messages,
        section 14.2.1."
    ::= { cSpLinksetTableEntry 15 }

cSpLinksetSisupRouteTableName OBJECT-TYPE
    SYNTAX CSpRouteTableName
--    Rsyntax OCTET STRING(SIZE(1..19))
    ACCESS read-only
    STATUS mandatory
    DESCRIPTION
        "The routing table for Satellite ISDN User Part(SISUP)
        messages."
    REFERENCE
        "ITU Q.704 Signalling network functions and messages,
        section 14.2.1."
    ::= { cSpLinksetTableEntry 16 }

cSpLinksetSpare11RouteTableName OBJECT-TYPE
    SYNTAX CSpRouteTableName
--    Rsyntax OCTET STRING(SIZE(1..19))
    ACCESS read-only
    STATUS mandatory
    DESCRIPTION
        "This routing table has been defined as a spare
        routing table by the standards committee."
    REFERENCE
        "ITU Q.704 Signalling network functions and messages,
        section 14.2.1."
    ::= { cSpLinksetTableEntry 17 }

cSpLinksetSpare12RouteTableName OBJECT-TYPE
    SYNTAX CSpRouteTableName
--    Rsyntax OCTET STRING(SIZE(1..19))
    ACCESS read-only
    STATUS mandatory
    DESCRIPTION
        "This routing table has been defined as a spare
        routing table by the standards committee."
    REFERENCE
        "ITU Q.704 Signalling network functions and messages,
        section 14.2.1."
    ::= { cSpLinksetTableEntry 18 }

cSpLinksetSpare13RouteTableName OBJECT-TYPE
    SYNTAX CSpRouteTableName
--    Rsyntax OCTET STRING(SIZE(1..19))
    ACCESS read-only
    STATUS mandatory
    DESCRIPTION
        "This routing table has been defined as a spare
        routing table by the standards committee."
    REFERENCE
        "ITU Q.704 Signalling network functions and messages,
        section 14.2.1."
    ::= { cSpLinksetTableEntry 19 }

cSpLinksetSpare14RouteTableName OBJECT-TYPE
    SYNTAX CSpRouteTableName
--    Rsyntax OCTET STRING(SIZE(1..19))
    ACCESS read-only
    STATUS mandatory
    DESCRIPTION
        "This routing table has been defined as a spare
        routing table by the standards committee."
    REFERENCE
        "ITU Q.704 Signalling network functions and messages,
        section 14.2.1."
    ::= { cSpLinksetTableEntry 20 }

cSpLinksetSpare15RouteTableName OBJECT-TYPE
    SYNTAX CSpRouteTableName
--    Rsyntax OCTET STRING(SIZE(1..19))
    ACCESS read-only
    STATUS mandatory
    DESCRIPTION
        "This routing table has been defined as a spare
        routing table by the standards committee."
    REFERENCE
        "ITU Q.704 Signalling network functions and messages,
        section 14.2.1."
    ::= { cSpLinksetTableEntry 21 }

cSpLinksetAccountingEnabled OBJECT-TYPE
    SYNTAX TruthValue
--    Rsyntax INTEGER {
--        true(1),
--        false(2)
--        }
    ACCESS read-only
    STATUS mandatory
    DESCRIPTION
        "This indicates if accounting for this linkset is
        enabled.
        
        'true'  Indicates that the accounting function is
                enabled for this linkset and is being
                accumulated in cSpAccountingTable.
        
        'false' Indicates that the accounting function is 
                disabled."
    DEFVAL { false }
    ::= { cSpLinksetTableEntry 22 }

cSpLinksetNumLinks OBJECT-TYPE
    SYNTAX Gauge
    ACCESS read-only
    STATUS mandatory
    DESCRIPTION
        "The number of links in this linkset."
    ::= { cSpLinksetTableEntry 23 }

cSpLinksetPacketsSent OBJECT-TYPE
    SYNTAX Counter
--  Units
--    packets
    ACCESS read-only
    STATUS mandatory
    DESCRIPTION
        "The number of packets(message signal units) 
         transmitted by this linkset(Q752/3.3)."
    ::= { cSpLinksetTableEntry 24 }

cSpLinksetHCPacketsSent OBJECT-TYPE
    SYNTAX --?? syntax is not convertable to SMIv1
           Counter
--  Units
--    packets
    ACCESS read-only
    STATUS mandatory
    DESCRIPTION
        "The number of packets(message signal units) 
         transmitted by this linkset(Q752/3.3). This is the 
         64-bit version of cSpLinksetPacketsSent."
    ::= { cSpLinksetTableEntry 25 }

cSpLinksetPacketsRcvd OBJECT-TYPE
    SYNTAX Counter
--  Units
--    packets
    ACCESS read-only
    STATUS mandatory
    DESCRIPTION
        "The number of packets(message signal units) received 
         by this linkset(Q752/3.5)."
    ::= { cSpLinksetTableEntry 26 }

cSpLinksetHCPacketsRcvd OBJECT-TYPE
    SYNTAX --?? syntax is not convertable to SMIv1
           Counter
--  Units
--    packets
    ACCESS read-only
    STATUS mandatory
    DESCRIPTION
        "The number of packets(message signal units) received 
         by this linkset(Q752/3.5). This is the 64-bit 
         version of cSpLinksetPacketsRcvd."
    ::= { cSpLinksetTableEntry 27 }

cSpLinksetBytesSent OBJECT-TYPE
    SYNTAX Counter
--  Units
--    bytes
    ACCESS read-only
    STATUS mandatory
    DESCRIPTION
        "The number of bytes transmitted by this 
         linkset(Q752/3.1)."
    ::= { cSpLinksetTableEntry 28 }

cSpLinksetHCBytesSent OBJECT-TYPE
    SYNTAX --?? syntax is not convertable to SMIv1
           Counter
--  Units
--    bytes
    ACCESS read-only
    STATUS mandatory
    DESCRIPTION
        "The number of bytes transmitted by this 
         linkset(Q752/3.1). This is the 64-bit version of 
         cSpLinksetBytesSent."
    ::= { cSpLinksetTableEntry 29 }

cSpLinksetBytesRcvd OBJECT-TYPE
    SYNTAX Counter
--  Units
--    bytes
    ACCESS read-only
    STATUS mandatory
    DESCRIPTION
        "The number of bytes received by this 
         linkset(Q752/3.4)."
    ::= { cSpLinksetTableEntry 30 }

cSpLinksetHCBytesRcvd OBJECT-TYPE
    SYNTAX --?? syntax is not convertable to SMIv1
           Counter
--  Units
--    bytes
    ACCESS read-only
    STATUS mandatory
    DESCRIPTION
        "The number of bytes received by this 
         linkset(Q752/3.4). This is the 64-bit version of 
         cSpLinksetBytesRcvd."
    ::= { cSpLinksetTableEntry 31 }

cSpLinksetDurationInService OBJECT-TYPE
    SYNTAX TimeTicks
    ACCESS read-only
    STATUS mandatory
    DESCRIPTION
        "Time linkset was providing service related to 
         Q752/Table 4.2."
    ::= { cSpLinksetTableEntry 32 }

cSpLinksetDurationOutService OBJECT-TYPE
    SYNTAX TimeTicks
    ACCESS read-only
    STATUS mandatory
    DESCRIPTION
        "Time linkset was Out-of-Service as required for 
         Q752/Table 4.2."
    ::= { cSpLinksetTableEntry 33 }

cSpLinksetMtp2T01 OBJECT-TYPE
    SYNTAX Gauge
--  Units
--    100 milli-seconds
    ACCESS read-only
    STATUS mandatory
    DESCRIPTION
        "Alignment ready timer. The default and valid range is
        dependant on the value of cSpSs7Variant.
        The ranges are defined in the following references."
    REFERENCE
        "ITU Q.703 Signalling Link.
        ANSI T1.111.3 Telecommunications - Signaling system
        No. 7 (SS7)-Message Transfer Part (MTP)."
    ::= { cSpLinksetTableEntry 34 }

cSpLinksetMtp2T02 OBJECT-TYPE
    SYNTAX Gauge
--  Units
--    100 milli-seconds
    ACCESS read-only
    STATUS mandatory
    DESCRIPTION
        "Not aligned timer. The default and valid range is
        dependant on the value of cSpSs7Variant.
        The ranges are defined in the following references.
        
        This timer is only applicable if cSpLinkType
        is serial."
    REFERENCE
        "ITU Q.703 Signalling Link.
        ANSI T1.111.3 Telecommunications - Signaling system
        No. 7 (SS7)-Message Transfer Part (MTP)."
    ::= { cSpLinksetTableEntry 35 }

cSpLinksetMtp2T03 OBJECT-TYPE
    SYNTAX Gauge
--  Units
--    100 milli-seconds
    ACCESS read-only
    STATUS mandatory
    DESCRIPTION
        "Aligned timer. The default and valid range is
        dependant on the value of cSpSs7Variant.
        The ranges are defined in the following references.
        
        This timer is only applicable if cSpLinkType
        is serial."
    REFERENCE
        "ITU Q.703 Signalling Link.
        ANSI T1.111.3 Telecommunications - Signaling system
        No. 7 (SS7)-Message Transfer Part (MTP)."
    ::= { cSpLinksetTableEntry 36 }

cSpLinksetMtp2T4N OBJECT-TYPE
    SYNTAX Gauge
--  Units
--    100 milli-seconds
    ACCESS read-only
    STATUS mandatory
    DESCRIPTION
        "Proving period timer normal timer. The default and
        valid range is dependant on the value of
        cSpSs7Variant. The ranges are defined in the
        following references."
    REFERENCE
        "ITU Q.703 Signalling Link.
        ANSI T1.111.3 Telecommunications - Signaling system
        No. 7 (SS7)-Message Transfer Part (MTP)."
    ::= { cSpLinksetTableEntry 37 }

cSpLinksetMtp2T4E OBJECT-TYPE
    SYNTAX Gauge
--  Units
--    100 milli-seconds
    ACCESS read-only
    STATUS mandatory
    DESCRIPTION
        "Proving period timer emergency timer. The default and
        valid range is dependant on the value of
        cSpSs7Variant. The ranges are defined in the following 
        references.
        
        This timer is only applicable if cSpLinkType
        is serial."
    REFERENCE
        "ITU Q.703 Signalling Link.
        ANSI T1.111.3 Telecommunications - Signaling system
        No. 7 (SS7)-Message Transfer Part (MTP)."
    ::= { cSpLinksetTableEntry 38 }

cSpLinksetMtp2T05 OBJECT-TYPE
    SYNTAX Gauge
--  Units
--    milli-seconds
    ACCESS read-only
    STATUS mandatory
    DESCRIPTION
        "Sending SIB timer. The default and valid range is
        dependant on the value of cSpSs7Variant.
        The ranges are defined in the following references.
        
        This timer is only applicable if cSpLinkType
        is serial."
    REFERENCE
        "ITU Q.703 Signalling Link.
        ANSI T1.111.3 Telecommunications - Signaling system
        No. 7 (SS7)-Message Transfer Part (MTP)."
    ::= { cSpLinksetTableEntry 39 }

cSpLinksetMtp2T06 OBJECT-TYPE
    SYNTAX Gauge
--  Units
--    100 milli-seconds.
    ACCESS read-only
    STATUS mandatory
    DESCRIPTION
        "Remote congestion timer. The default and valid range is
        dependant on the value of cSpSs7Variant.
        The ranges are defined in the following references."
    REFERENCE
        "ITU Q.703 Signalling Link.
        ANSI T1.111.3 Telecommunications - Signaling system
        No. 7 (SS7)-Message Transfer Part (MTP)."
    ::= { cSpLinksetTableEntry 40 }

cSpLinksetMtp2T07 OBJECT-TYPE
    SYNTAX Gauge
--  Units
--    100 milli-seconds.
    ACCESS read-only
    STATUS mandatory
    DESCRIPTION
        "Excessive delay of acknowledgement timer. The default
         and valid range is dependant on the value of
         cSpSs7Variant The ranges are defined in the following 
         references.
        
         This timer is only applicable if cSpLinkType
         is serial."
    REFERENCE
        "ITU Q.703 Signalling Link.
        ANSI T1.111.3 Telecommunications - Signaling system
        No. 7 (SS7)-Message Transfer Part (MTP)."
    ::= { cSpLinksetTableEntry 41 }

cSpLinksetMtp2T08 OBJECT-TYPE
    SYNTAX Gauge
    ACCESS read-only
    STATUS mandatory
    DESCRIPTION
        "Interval timer for error interval monitor.
        Note that this timer is only applicable if cSpLinkType
        is serial."
    REFERENCE
        "ITU Q.703 Signalling Link.
        ANSI T1.111.3 Telecommunications - Signaling system
        No. 7 (SS7)-Message Transfer Part (MTP)."
    ::= { cSpLinksetTableEntry 42 }

cSpLinksetMtp3T01 OBJECT-TYPE
    SYNTAX Gauge
    ACCESS read-only
    STATUS mandatory
    DESCRIPTION
        "Delay to avoid message mis-sequencing on changeover."
    REFERENCE
        "ITU Q.704 Signalling network functions and messages.
        ANSI T1.111 Telecommunications - Signaling system
        No. 7 (SS7)-Message Transfer Part (MTP)."
    ::= { cSpLinksetTableEntry 43 }

cSpLinksetMtp3T02 OBJECT-TYPE
    SYNTAX Gauge
    ACCESS read-only
    STATUS mandatory
    DESCRIPTION
        "Waiting for changeover acknowledgement."
    REFERENCE
        "ITU Q.704 Signalling network functions and messages.
        ANSI T1.111 Telecommunications - Signaling system
        No. 7 (SS7)-Message Transfer Part (MTP)."
    ::= { cSpLinksetTableEntry 44 }

cSpLinksetMtp3T03 OBJECT-TYPE
    SYNTAX Gauge
    ACCESS read-only
    STATUS mandatory
    DESCRIPTION
        "Time controlled diversion-delay to avoid
        mis-sequencing on change back."
    REFERENCE
        "ITU Q.704 Signalling network functions and messages.
        ANSI T1.111 Telecommunications - Signaling system
        No. 7 (SS7)-Message Transfer Part (MTP)."
    ::= { cSpLinksetTableEntry 45 }

cSpLinksetMtp3T04 OBJECT-TYPE
    SYNTAX Gauge
    ACCESS read-only
    STATUS mandatory
    DESCRIPTION
        "Waiting for change back acknowledgement (first
        attempt)."
    REFERENCE
        "ITU Q.704 Signalling network functions and messages.
        ANSI T1.111 Telecommunications - Signaling system
        No. 7 (SS7)-Message Transfer Part (MTP)."
    ::= { cSpLinksetTableEntry 46 }

cSpLinksetMtp3T05 OBJECT-TYPE
    SYNTAX Gauge
    ACCESS read-only
    STATUS mandatory
    DESCRIPTION
        "Waiting for change back acknowledgement (second
        attempt)."
    REFERENCE
        "ITU Q.704 Signalling network functions and messages.
        ANSI T1.111 Telecommunications - Signaling system
        No. 7 (SS7)-Message Transfer Part (MTP)."
    ::= { cSpLinksetTableEntry 47 }

cSpLinksetMtp3T06 OBJECT-TYPE
    SYNTAX Gauge
    ACCESS read-only
    STATUS mandatory
    DESCRIPTION
        "Delay to avoid message mis-sequencing on controlled
        rerouting."
    REFERENCE
        "ITU Q.704 Signalling network functions and messages.
        ANSI T1.111 Telecommunications - Signaling system
        No. 7 (SS7)-Message Transfer Part (MTP)."
    ::= { cSpLinksetTableEntry 48 }

cSpLinksetMtp3T07 OBJECT-TYPE
    SYNTAX Gauge
    ACCESS read-only
    STATUS mandatory
    DESCRIPTION
        "Waiting for signalling data link connection
        acknowledgement."
    REFERENCE
        "ITU Q.704 Signalling network functions and messages.
        ANSI T1.111 Telecommunications - Signaling system
        No. 7 (SS7)-Message Transfer Part (MTP)."
    ::= { cSpLinksetTableEntry 49 }

cSpLinksetMtp3T08 OBJECT-TYPE
    SYNTAX Gauge
    ACCESS read-only
    STATUS mandatory
    DESCRIPTION
        "Transfer prohibited inhibition timer (transient
        solution)."
    REFERENCE
        "ITU Q.704 Signalling network functions and messages.
        ANSI T1.111 Telecommunications - Signaling system
        No. 7 (SS7)-Message Transfer Part (MTP)."
    ::= { cSpLinksetTableEntry 50 }

cSpLinksetMtp3T10 OBJECT-TYPE
    SYNTAX Gauge
    ACCESS read-only
    STATUS mandatory
    DESCRIPTION
        "Waiting to repeat signalling routeset test message."
    REFERENCE
        "ITU Q.704 Signalling network functions and messages.
        ANSI T1.111 Telecommunications - Signaling system
        No. 7 (SS7)-Message Transfer Part (MTP)."
    ::= { cSpLinksetTableEntry 51 }

cSpLinksetMtp3T11 OBJECT-TYPE
    SYNTAX Gauge
    ACCESS read-only
    STATUS mandatory
    DESCRIPTION
        "Transfer restricted timer. (This is one way of
        implementing the function described in 13.4/Q.704 and
        mainly intended to simplify SPs.)."
    REFERENCE
        "ITU Q.704 Signalling network functions and messages.
        ANSI T1.111 Telecommunications - Signaling system
        No. 7 (SS7)-Message Transfer Part (MTP)."
    ::= { cSpLinksetTableEntry 52 }

cSpLinksetMtp3T12 OBJECT-TYPE
    SYNTAX Gauge
    ACCESS read-only
    STATUS mandatory
    DESCRIPTION
        "Waiting for uninhibit acknowledgement."
    REFERENCE
        "ITU Q.704 Signalling network functions and messages.
        ANSI T1.111 Telecommunications - Signaling system
        No. 7 (SS7)-Message Transfer Part (MTP)."
    ::= { cSpLinksetTableEntry 53 }

cSpLinksetMtp3T13 OBJECT-TYPE
    SYNTAX Gauge
    ACCESS read-only
    STATUS mandatory
    DESCRIPTION
        "Waiting for force uninhibit."
    REFERENCE
        "ITU Q.704 Signalling network functions and messages.
        ANSI T1.111 Telecommunications - Signaling system
        No. 7 (SS7)-Message Transfer Part (MTP)."
    ::= { cSpLinksetTableEntry 54 }

cSpLinksetMtp3T14 OBJECT-TYPE
    SYNTAX Gauge
    ACCESS read-only
    STATUS mandatory
    DESCRIPTION
        "Waiting for inhibition acknowledgement."
    REFERENCE
        "ITU Q.704 Signalling network functions and messages.
        ANSI T1.111 Telecommunications - Signaling system
        No. 7 (SS7)-Message Transfer Part (MTP)."
    ::= { cSpLinksetTableEntry 55 }

cSpLinksetMtp3T15 OBJECT-TYPE
    SYNTAX Gauge
    ACCESS read-only
    STATUS mandatory
    DESCRIPTION
        "Waiting to start signalling routeset congestion
        test."
    REFERENCE
        "ITU Q.704 Signalling network functions and messages.
        ANSI T1.111 Telecommunications - Signaling system
        No. 7 (SS7)-Message Transfer Part (MTP)."
    ::= { cSpLinksetTableEntry 56 }

cSpLinksetMtp3T16 OBJECT-TYPE
    SYNTAX Gauge
    ACCESS read-only
    STATUS mandatory
    DESCRIPTION
        "Waiting for routeset congestion status update."
    REFERENCE
        "ITU Q.704 Signalling network functions and messages.
        ANSI T1.111 Telecommunications - Signaling system
        No. 7 (SS7)-Message Transfer Part (MTP)."
    ::= { cSpLinksetTableEntry 57 }

cSpLinksetMtp3T17 OBJECT-TYPE
    SYNTAX Gauge
    ACCESS read-only
    STATUS mandatory
    DESCRIPTION
        "Delay to avoid oscillation of initial alignment
        failure and link restart."
    REFERENCE
        "ITU Q.704 Signalling network functions and messages.
        ANSI T1.111 Telecommunications - Signaling system
        No. 7 (SS7)-Message Transfer Part (MTP)."
    ::= { cSpLinksetTableEntry 58 }

cSpLinksetMtp3T18 OBJECT-TYPE
    SYNTAX Gauge
    ACCESS read-only
    STATUS mandatory
    DESCRIPTION
        "Timer within a signalling point whose MTP restarts,
        for supervising link and linkset activation as well as
        the receipt of routing information."
    REFERENCE
        "ITU Q.704 Signalling network functions and messages.
        ANSI T1.111 Telecommunications - Signaling system
        No. 7 (SS7)-Message Transfer Part (MTP)."
    ::= { cSpLinksetTableEntry 59 }

cSpLinksetMtp3T19 OBJECT-TYPE
    SYNTAX Gauge
    ACCESS read-only
    STATUS mandatory
    DESCRIPTION
        "Supervision timer during MTP restart to avoid
        possible ping-pong of TFP, TFR2) and TRA messages."
    REFERENCE
        "ITU Q.704 Signalling network functions and messages.
        ANSI T1.111 Telecommunications - Signaling system
        No. 7 (SS7)-Message Transfer Part (MTP)."
    ::= { cSpLinksetTableEntry 60 }

cSpLinksetMtp3T20 OBJECT-TYPE
    SYNTAX Gauge
    ACCESS read-only
    STATUS mandatory
    DESCRIPTION
        "Overall MTP restart timer at the signalling point
        whose MTP restarts. Overall MTP restart timer at a
        signalling point adjacent to one whose MTP restarts."
    REFERENCE
        "ITU Q.704 Signalling network functions and messages.
        ANSI T1.111 Telecommunications - Signaling system
        No. 7 (SS7)-Message Transfer Part (MTP)."
    ::= { cSpLinksetTableEntry 61 }

cSpLinksetMtp3T21 OBJECT-TYPE
    SYNTAX Gauge
    ACCESS read-only
    STATUS mandatory
    DESCRIPTION
        "Overall MTP restart timer at a signalling point
        adjacent to one whose MTP restarts."
    REFERENCE
        "ITU Q.704 Signalling network functions and messages.
        ANSI T1.111 Telecommunications - Signaling system
        No. 7 (SS7)-Message Transfer Part (MTP)."
    ::= { cSpLinksetTableEntry 62 }

cSpLinksetMtp3T22 OBJECT-TYPE
    SYNTAX Gauge
    ACCESS read-only
    STATUS mandatory
    DESCRIPTION
        "Local inhibit test timer."
    REFERENCE
        "ITU Q.704 Signalling network functions and messages.
        ANSI T1.111 Telecommunications - Signaling system
        No. 7 (SS7)-Message Transfer Part (MTP)."
    ::= { cSpLinksetTableEntry 63 }

cSpLinksetMtp3T23 OBJECT-TYPE
    SYNTAX Gauge
    ACCESS read-only
    STATUS mandatory
    DESCRIPTION
        "Remote inhibit test timer."
    REFERENCE
        "ITU Q.704 Signalling network functions and messages.
        ANSI T1.111 Telecommunications - Signaling system
        No. 7 (SS7)-Message Transfer Part (MTP)."
    ::= { cSpLinksetTableEntry 64 }

cSpLinksetMtp3T24 OBJECT-TYPE
    SYNTAX Gauge
    ACCESS read-only
    STATUS mandatory
    DESCRIPTION
        "Stabilizing timer after removal of local processor
        outage, used in LPO latching to RPO (national option)"
    REFERENCE
        "ITU Q.704 Signalling network functions and messages.
        ANSI T1.111 Telecommunications - Signaling system
        No. 7 (SS7)-Message Transfer Part (MTP)."
    ::= { cSpLinksetTableEntry 65 }

cSpLinksetMtp3T25 OBJECT-TYPE
    SYNTAX Gauge
    ACCESS read-only
    STATUS mandatory
    DESCRIPTION
        "Timer at Signalling Point (SP) adjacent to restarting
        SP, waiting for traffic restart allowed message."
    REFERENCE
        "ANSI T1.111 Telecommunications - Signaling system
        No. 7 (SS7)-Message Transfer Part (MTP)."
    ::= { cSpLinksetTableEntry 66 }

cSpLinksetMtp3T26 OBJECT-TYPE
    SYNTAX Gauge
    ACCESS read-only
    STATUS mandatory
    DESCRIPTION
        "Timer at restarting SP waiting to repeat traffic
        restart waiting message."
    REFERENCE
        "ANSI T1.111 Telecommunications - Signaling system
        No. 7 (SS7)-Message Transfer Part (MTP)."
    ::= { cSpLinksetTableEntry 67 }

cSpLinksetMtp3T27 OBJECT-TYPE
    SYNTAX Gauge
    ACCESS read-only
    STATUS mandatory
    DESCRIPTION
        "Minimum duration of unavailability for full restart."
    REFERENCE
        "ANSI T1.111 Telecommunications - Signaling system
        No. 7 (SS7)-Message Transfer Part (MTP)."
    ::= { cSpLinksetTableEntry 68 }

cSpLinksetMtp3T28 OBJECT-TYPE
    SYNTAX Gauge
    ACCESS read-only
    STATUS mandatory
    DESCRIPTION
        "Timer at SP adjacent to restarting SP waiting for
        traffic restart waiting message."
    REFERENCE
        "ANSI T1.111 Telecommunications - Signaling system
        No. 7 (SS7)-Message Transfer Part (MTP)."
    ::= { cSpLinksetTableEntry 69 }

cSpLinksetMtp3T29 OBJECT-TYPE
    SYNTAX Gauge
    ACCESS read-only
    STATUS mandatory
    DESCRIPTION
        "Timer started when TRA sent in response to unexpected
        TRA or TRW."
    REFERENCE
        "ANSI T1.111 Telecommunications - Signaling system
        No. 7 (SS7)-Message Transfer Part (MTP)."
    ::= { cSpLinksetTableEntry 70 }

cSpLinksetMtp3T30 OBJECT-TYPE
    SYNTAX Gauge
    ACCESS read-only
    STATUS mandatory
    DESCRIPTION
        "Timer to limit sending of TFPs and TFRs in response
        to unexpected TRA or TRW."
    REFERENCE
        "ANSI T1.111 Telecommunications - Signaling system
        No. 7 (SS7)-Message Transfer Part (MTP)."
    ::= { cSpLinksetTableEntry 71 }

cSpLinksetMtp3T31 OBJECT-TYPE
    SYNTAX Gauge
    ACCESS read-only
    STATUS mandatory
    DESCRIPTION
        "False link congestion detection timer."
    REFERENCE
        "ANSI T1.111 Telecommunications - Signaling system
        No. 7 (SS7)-Message Transfer Part (MTP)."
    ::= { cSpLinksetTableEntry 72 }

cSpLinksetMtp3T32 OBJECT-TYPE
    SYNTAX Gauge
    ACCESS read-only
    STATUS mandatory
    DESCRIPTION
        "Link oscillation timer - Procedure A."
    REFERENCE
        "ANSI T1.111 Telecommunications - Signaling system
        No. 7 (SS7)-Message Transfer Part (MTP)."
    ::= { cSpLinksetTableEntry 73 }

cSpLinksetMtp3T33 OBJECT-TYPE
    SYNTAX Gauge
    ACCESS read-only
    STATUS mandatory
    DESCRIPTION
        "Probation timer for link oscillation - Procedure B."
    REFERENCE
        "ANSI T1.111 Telecommunications - Signaling system
        No. 7 (SS7)-Message Transfer Part (MTP)."
    ::= { cSpLinksetTableEntry 74 }

cSpLinksetMtp3T34 OBJECT-TYPE
    SYNTAX Gauge
    ACCESS read-only
    STATUS mandatory
    DESCRIPTION
        "Suspension timer for link oscillation - Procedure B."
    REFERENCE
        "ANSI T1.111 Telecommunications - Signaling system
        No. 7 (SS7)-Message Transfer Part (MTP)."
    ::= { cSpLinksetTableEntry 75 }

cSpLinkTable OBJECT-TYPE
    SYNTAX SEQUENCE OF CSpLinkTableEntry
    ACCESS not-accessible
    STATUS mandatory
    DESCRIPTION
        "A table of SP links for this SP."
    ::= { cSpLink 1 }

cSpLinkTableEntry OBJECT-TYPE
    SYNTAX CSpLinkTableEntry
    ACCESS not-accessible
    STATUS mandatory
    DESCRIPTION
        "A list of SP link attributes."
    INDEX { cSpLinksetName, cSpLinkSlc }
    ::= { cSpLinkTable 1 }

CSpLinkTableEntry ::= SEQUENCE {
    cSpLinkSlc CSpLinkSLC,
    cSpLinkState CSpOsiState,
    cSpLinkType CSpLinkType,
    cSpLinkifIndex InterfaceIndexOrZero,
    cSpLinkSctpAssociation INTEGER,
    cSpLinkMtp3PacketsRcvd Counter,
    cSpLinkMtp3PacketsSent Counter,
    cSpLinkHCMtp3PacketsRcvd Counter,
    cSpLinkHCMtp3PacketsSent Counter,
    cSpLinkMtp3BytesRcvd Counter,
    cSpLinkMtp3BytesSent Counter,
    cSpLinkHCMtp3BytesRcvd Counter,
    cSpLinkHCMtp3BytesSent Counter,
    cSpLinkMtp2T01 Gauge,
    cSpLinkMtp2T02 Gauge,
    cSpLinkMtp2T03 Gauge,
    cSpLinkMtp2T4N Gauge,
    cSpLinkMtp2T4E Gauge,
    cSpLinkMtp2T05 Gauge,
    cSpLinkMtp2T06 Gauge,
    cSpLinkMtp2T07 Gauge,
    cSpLinkMtp2T08 Gauge,
    cSpLinkMtp3T01 Gauge,
    cSpLinkMtp3T02 Gauge,
    cSpLinkMtp3T03 Gauge,
    cSpLinkMtp3T04 Gauge,
    cSpLinkMtp3T05 Gauge,
    cSpLinkMtp3T06 Gauge,
    cSpLinkMtp3T07 Gauge,
    cSpLinkMtp3T08 Gauge,
    cSpLinkMtp3T10 Gauge,
    cSpLinkMtp3T11 Gauge,
    cSpLinkMtp3T12 Gauge,
    cSpLinkMtp3T13 Gauge,
    cSpLinkMtp3T14 Gauge,
    cSpLinkMtp3T15 Gauge,
    cSpLinkMtp3T16 Gauge,
    cSpLinkMtp3T17 Gauge,
    cSpLinkMtp3T18 Gauge,
    cSpLinkMtp3T19 Gauge,
    cSpLinkMtp3T20 Gauge,
    cSpLinkMtp3T21 Gauge,
    cSpLinkMtp3T22 Gauge,
    cSpLinkMtp3T23 Gauge,
    cSpLinkMtp3T24 Gauge,
    cSpLinkMtp3T25 Gauge,
    cSpLinkMtp3T26 Gauge,
    cSpLinkMtp3T27 Gauge,
    cSpLinkMtp3T28 Gauge,
    cSpLinkMtp3T29 Gauge,
    cSpLinkMtp3T30 Gauge,
    cSpLinkMtp3T31 Gauge,
    cSpLinkMtp3T32 Gauge,
    cSpLinkMtp3T33 Gauge,
    cSpLinkMtp3T34 Gauge,
    cSpLinkXmitQueueDepth Gauge,
    cSpLinkXmitQueueDepthHigh Gauge,
    cSpLinkXmitQueueDepthHighReset TimeStamp,
    cSpLinkCongestionState Gauge,
    cSpLinkCongestionAbate1 Gauge,
    cSpLinkCongestionAbate2 Gauge,
    cSpLinkCongestionAbate3 Gauge,
    cSpLinkCongestionOnset1 Gauge,
    cSpLinkCongestionOnset2 Gauge,
    cSpLinkCongestionOnset3 Gauge,
    cSpLinkSigLinkTest TruthValue,
    cSpLinkQ752T1E1 TimeTicks,
    cSpLinkQ752T1E2 Counter,
    cSpLinkQ752T1E3 Counter,
    cSpLinkQ752T1E4 Counter,
    cSpLinkQ752T1E5 Counter,
    cSpLinkQ752T1E6 Counter,
    cSpLinkQ752T1E7 Counter,
    cSpLinkQ752T1E8 Counter,
    cSpLinkQ752T1E9 Counter,
    cSpLinkQ752T1E10 Counter,
    cSpLinkQ752T1E11 Counter,
    cSpLinkQ752T2E1 TimeTicks,
    cSpLinkQ752T2E5 TimeTicks,
    cSpLinkQ752T2E6 TimeTicks,
    cSpLinkQ752T2E7 TimeTicks,
    cSpLinkQ752T2E9 TimeTicks,
    cSpLinkQ752T2E10 Counter,
    cSpLinkQ752T2E15 TimeTicks,
    cSpLinkQ752T2E16 Counter,
    cSpLinkQ752T2E18 Counter,
    cSpLinkMtp3PacketsRetrans Counter,
    cSpLinkMtp3BytesRetrans Counter,
    cSpLinkQ752T3E6 Counter,
    cSpLinkQ752T3E7 TimeTicks,
    cSpLinkQ752T3E10L1 Counter,
    cSpLinkQ752T3E10L2 Counter,
    cSpLinkQ752T3E10L3 Counter,
    cSpLinkQ752T3E11L1 Counter,
    cSpLinkQ752T3E11L2 Counter,
    cSpLinkQ752T3E11L3 Counter
    }

cSpLinkSlc OBJECT-TYPE
    SYNTAX CSpLinkSLC
--    Rsyntax Gauge(0..15)
    ACCESS not-accessible
    STATUS mandatory
    DESCRIPTION
        "The Signalling Link Code for this link."
    REFERENCE
        "ITU Q.704 Signalling network functions and messages.
        ANSI T1.111 Telecommunications - Signaling system
        No. 7 (SS7)-Message Transfer Part (MTP)."
    ::= { cSpLinkTableEntry 1 }

cSpLinkState OBJECT-TYPE
    SYNTAX CSpOsiState
--    Rsyntax INTEGER {
--        active(1),
--        inactive(2),
--        inhibited(3),
--        uninhibited(4),
--        shut(5),
--        noshut(6)
--        }
    ACCESS read-only
    STATUS mandatory
    DESCRIPTION
        "The status of this link."
    ::= { cSpLinkTableEntry 2 }

cSpLinkType OBJECT-TYPE
    SYNTAX CSpLinkType
--    Rsyntax INTEGER {
--        other(1),
--        serial(2),
--        sctpIp(3)
--        }
    ACCESS read-only
    STATUS mandatory
    DESCRIPTION
        "The link type."
    REFERENCE
        "For SCTP see RFC 2960."
    ::= { cSpLinkTableEntry 3 }

cSpLinkifIndex OBJECT-TYPE
    SYNTAX InterfaceIndexOrZero
--    Rsyntax INTEGER(0..2147483647)
    ACCESS read-only
    STATUS mandatory
    DESCRIPTION
        "If the link type specified by cSpLinkType  is serial,
        this is the ifIndex specified in MIB-2, otherwise no
        significance is to be placed on this value."
    REFERENCE
        "RFC1213.txt"
    ::= { cSpLinkTableEntry 4 }

cSpLinkSctpAssociation OBJECT-TYPE
    SYNTAX INTEGER(-1..65535)
    ACCESS read-only
    STATUS mandatory
    DESCRIPTION
        "If the link type specified by cSpLinkType is sctpIp,
        this is the sctpAssocId defined in the CISCO-SCTP-MIB.
        Where value greater than or equal to zero indicates
        a valid association and negative one indicates an 
        invalid association. This value will always be set to 
        negative one when cSpLinkType is set to the two value."
    ::= { cSpLinkTableEntry 5 }

cSpLinkMtp3PacketsRcvd OBJECT-TYPE
    SYNTAX Counter
--  Units
--    packets
    ACCESS read-only
    STATUS mandatory
    DESCRIPTION
        "The number of MTP3 packets received by this link.
        This measurement is specified in Q752/3.5"
    ::= { cSpLinkTableEntry 6 }

cSpLinkMtp3PacketsSent OBJECT-TYPE
    SYNTAX Counter
--  Units
--    packets
    ACCESS read-only
    STATUS mandatory
    DESCRIPTION
        "The number of MTP3 packets sent by this link.
        This measurement is specified in Q752/3.3"
    ::= { cSpLinkTableEntry 7 }

cSpLinkHCMtp3PacketsRcvd OBJECT-TYPE
    SYNTAX --?? syntax is not convertable to SMIv1
           Counter
--  Units
--    bytes
    ACCESS read-only
    STATUS mandatory
    DESCRIPTION
        "The number of MTP3 packets received by this link.
         This is the 64-bit version of cSpLinkMtp3PacketsRcvd.
        This measurement is specified in Q752/3.5"
    ::= { cSpLinkTableEntry 8 }

cSpLinkHCMtp3PacketsSent OBJECT-TYPE
    SYNTAX --?? syntax is not convertable to SMIv1
           Counter
--  Units
--    bytes
    ACCESS read-only
    STATUS mandatory
    DESCRIPTION
        "The number of MTP3 packets sent by this link.
         This is the 64-bit version of cSpLinkMtp3PacketsSent.
         This measurement is specified in Q752/3.3"
    ::= { cSpLinkTableEntry 9 }

cSpLinkMtp3BytesRcvd OBJECT-TYPE
    SYNTAX Counter
--  Units
--    bytes
    ACCESS read-only
    STATUS mandatory
    DESCRIPTION
        "The number of MTP3 bytes received by this link.
         This measurement is specified in Q752/3.4"
    ::= { cSpLinkTableEntry 10 }

cSpLinkMtp3BytesSent OBJECT-TYPE
    SYNTAX Counter
--  Units
--    bytes
    ACCESS read-only
    STATUS mandatory
    DESCRIPTION
        "The number of MTP3 bytes sent by this link.
         This measurement is specified in Q752/3.1"
    ::= { cSpLinkTableEntry 11 }

cSpLinkHCMtp3BytesRcvd OBJECT-TYPE
    SYNTAX --?? syntax is not convertable to SMIv1
           Counter
--  Units
--    bytes
    ACCESS read-only
    STATUS mandatory
    DESCRIPTION
        "The number of MTP3 bytes received by this link.
         This is the 64-bit version of cSpLinkMtp3BytesRcvd.
         This measurement is specified in Q752/3.4"
    ::= { cSpLinkTableEntry 12 }

cSpLinkHCMtp3BytesSent OBJECT-TYPE
    SYNTAX --?? syntax is not convertable to SMIv1
           Counter
--  Units
--    bytes
    ACCESS read-only
    STATUS mandatory
    DESCRIPTION
        "The number of MTP3 bytes sent by this link.
         This is the 64-bit version of cSpLinkMtp3BytesSent.
         This measurement is specified in Q752/3.1"
    ::= { cSpLinkTableEntry 13 }

cSpLinkMtp2T01 OBJECT-TYPE
    SYNTAX Gauge
--  Units
--    100 milli-seconds
    ACCESS read-only
    STATUS mandatory
    DESCRIPTION
        "Alignment ready timer. The default and valid range is
        dependant on the value of cSpSs7Variant.
        The ranges are defined in the following references.
        
        This timer is only applicable if cSpLinkType value is 
        equal to 'serial'. A get on this object will return a
        zero if cSpLinkType is not serial."
    REFERENCE
        "ITU Q.703 Signalling Link.
        ANSI T1.111.3 Telecommunications - Signaling system
        No. 7 (SS7)-Message Transfer Part (MTP)."
    ::= { cSpLinkTableEntry 14 }

cSpLinkMtp2T02 OBJECT-TYPE
    SYNTAX Gauge
--  Units
--    100 milli-seconds
    ACCESS read-only
    STATUS mandatory
    DESCRIPTION
        "Not aligned timer. The default and valid range is
        dependant on the value of cSpSs7Variant.
        The ranges are defined in the following references.
        
        This timer is only applicable if cSpLinkType
        is serial. A get on this object will return a
        zero if cSpLinkType is not serial."
    REFERENCE
        "ITU Q.703 Signalling Link.
        ANSI T1.111.3 Telecommunications - Signaling system
        No. 7 (SS7)-Message Transfer Part (MTP)."
    ::= { cSpLinkTableEntry 15 }

cSpLinkMtp2T03 OBJECT-TYPE
    SYNTAX Gauge
--  Units
--    100 milli-seconds
    ACCESS read-only
    STATUS mandatory
    DESCRIPTION
        "Aligned timer. The default and valid range is
        dependant on the value of cSpSs7Variant.
        The ranges are defined in the following references.
        
        This timer is only applicable if cSpLinkType
        is serial. A get on this object will return a
        zero if cSpLinkType is not serial."
    REFERENCE
        "ITU Q.703 Signalling Link.
        ANSI T1.111.3 Telecommunications - Signaling system
        No. 7 (SS7)-Message Transfer Part (MTP)."
    ::= { cSpLinkTableEntry 16 }

cSpLinkMtp2T4N OBJECT-TYPE
    SYNTAX Gauge
--  Units
--    100 milli-seconds
    ACCESS read-only
    STATUS mandatory
    DESCRIPTION
        "Proving period timer normal timer. The default and
        valid range is dependant on the value of
        cSpSs7Variant. The ranges are defined in the
        following references."
    REFERENCE
        "ITU Q.703 Signalling Link.
        ANSI T1.111.3 Telecommunications - Signaling system
        No. 7 (SS7)-Message Transfer Part (MTP)."
    ::= { cSpLinkTableEntry 17 }

cSpLinkMtp2T4E OBJECT-TYPE
    SYNTAX Gauge
--  Units
--    100 milli-seconds
    ACCESS read-only
    STATUS mandatory
    DESCRIPTION
        "Proving period timer emergency timer. The default and
        valid range is dependant on the value of
        cSpSs7Variant. The ranges are defined in the following 
        references.
        
        This timer is only applicable if cSpLinkType
        is serial. A get on this object will return a
        zero if cSpLinkType is not serial."
    REFERENCE
        "ITU Q.703 Signalling Link.
        ANSI T1.111.3 Telecommunications - Signaling system
        No. 7 (SS7)-Message Transfer Part (MTP)."
    ::= { cSpLinkTableEntry 18 }

cSpLinkMtp2T05 OBJECT-TYPE
    SYNTAX Gauge
--  Units
--    milli-seconds
    ACCESS read-only
    STATUS mandatory
    DESCRIPTION
        "Sending SIB timer. The default and valid range is
        dependant on the value of cSpSs7Variant.
        The ranges are defined in the following references.
        
        This timer is only applicable if cSpLinkType
        is serial. A get on this object will return a
        zero if cSpLinkType is not serial."
    REFERENCE
        "ITU Q.703 Signalling Link.
        ANSI T1.111.3 Telecommunications - Signaling system
        No. 7 (SS7)-Message Transfer Part (MTP)."
    ::= { cSpLinkTableEntry 19 }

cSpLinkMtp2T06 OBJECT-TYPE
    SYNTAX Gauge
--  Units
--    100 milli-seconds.
    ACCESS read-only
    STATUS mandatory
    DESCRIPTION
        "Remote congestion timer. The default and valid range is
        dependant on the value of cSpSs7Variant.
        The ranges are defined in the following references.
        
        This timer is only applicable if cSpLinkType
        is serial. A get on this object will return a
        zero if cSpLinkType is not serial."
    REFERENCE
        "ITU Q.703 Signalling Link.
        ANSI T1.111.3 Telecommunications - Signaling system
        No. 7 (SS7)-Message Transfer Part (MTP)."
    ::= { cSpLinkTableEntry 20 }

cSpLinkMtp2T07 OBJECT-TYPE
    SYNTAX Gauge
--  Units
--    100 milli-seconds.
    ACCESS read-only
    STATUS mandatory
    DESCRIPTION
        "Excessive delay of acknowledgement timer. The default
        and valid range is dependant on the value of
        cSpSs7Variant The ranges are defined in the following 
        references.
        
        This timer is only applicable if cSpLinkType
        is serial. A get on this object will return a
        zero if cSpLinkType is not serial."
    REFERENCE
        "ITU Q.703 Signalling Link.
        ANSI T1.111.3 Telecommunications - Signaling system
        No. 7 (SS7)-Message Transfer Part (MTP)."
    ::= { cSpLinkTableEntry 21 }

cSpLinkMtp2T08 OBJECT-TYPE
    SYNTAX Gauge
    ACCESS read-only
    STATUS mandatory
    DESCRIPTION
        "Interval timer for error interval monitor.
        Note that this timer is only applicable if cSpLinkType
        is serial. A get on this object will return a
        zero if cSpLinkType is not serial."
    REFERENCE
        "ITU Q.703 Signalling Link.
        ANSI T1.111.3 Telecommunications - Signaling system
        No. 7 (SS7)-Message Transfer Part (MTP)."
    ::= { cSpLinkTableEntry 22 }

cSpLinkMtp3T01 OBJECT-TYPE
    SYNTAX Gauge
    ACCESS read-only
    STATUS mandatory
    DESCRIPTION
        "Delay to avoid message mis-sequencing on changeover."
    REFERENCE
        "ITU Q.704 Signalling network functions and messages.
        ANSI T1.111 Telecommunications - Signaling system
        No. 7 (SS7)-Message Transfer Part (MTP)."
    ::= { cSpLinkTableEntry 23 }

cSpLinkMtp3T02 OBJECT-TYPE
    SYNTAX Gauge
    ACCESS read-only
    STATUS mandatory
    DESCRIPTION
        "Waiting for changeover acknowledgement."
    REFERENCE
        "ITU Q.704 Signalling network functions and messages.
        ANSI T1.111 Telecommunications - Signaling system
        No. 7 (SS7)-Message Transfer Part (MTP)."
    ::= { cSpLinkTableEntry 24 }

cSpLinkMtp3T03 OBJECT-TYPE
    SYNTAX Gauge
    ACCESS read-only
    STATUS mandatory
    DESCRIPTION
        "Time controlled diversion-delay to avoid
        mis-sequencing on change back."
    REFERENCE
        "ITU Q.704 Signalling network functions and messages.
        ANSI T1.111 Telecommunications - Signaling system
        No. 7 (SS7)-Message Transfer Part (MTP)."
    ::= { cSpLinkTableEntry 25 }

cSpLinkMtp3T04 OBJECT-TYPE
    SYNTAX Gauge
    ACCESS read-only
    STATUS mandatory
    DESCRIPTION
        "Waiting for change back acknowledgement (first
        attempt)."
    REFERENCE
        "ITU Q.704 Signalling network functions and messages.
        ANSI T1.111 Telecommunications - Signaling system
        No. 7 (SS7)-Message Transfer Part (MTP)."
    ::= { cSpLinkTableEntry 26 }

cSpLinkMtp3T05 OBJECT-TYPE
    SYNTAX Gauge
    ACCESS read-only
    STATUS mandatory
    DESCRIPTION
        "Waiting for change back acknowledgement (second
        attempt)."
    REFERENCE
        "ITU Q.704 Signalling network functions and messages.
        ANSI T1.111 Telecommunications - Signaling system
        No. 7 (SS7)-Message Transfer Part (MTP)."
    ::= { cSpLinkTableEntry 27 }

cSpLinkMtp3T06 OBJECT-TYPE
    SYNTAX Gauge
    ACCESS read-only
    STATUS mandatory
    DESCRIPTION
        "Delay to avoid message mis-sequencing on controlled
        rerouting."
    REFERENCE
        "ITU Q.704 Signalling network functions and messages.
        ANSI T1.111 Telecommunications - Signaling system
        No. 7 (SS7)-Message Transfer Part (MTP)."
    ::= { cSpLinkTableEntry 28 }

cSpLinkMtp3T07 OBJECT-TYPE
    SYNTAX Gauge
    ACCESS read-only
    STATUS mandatory
    DESCRIPTION
        "Waiting for signalling data link connection
        acknowledgement."
    REFERENCE
        "ITU Q.704 Signalling network functions and messages.
        ANSI T1.111 Telecommunications - Signaling system
        No. 7 (SS7)-Message Transfer Part (MTP)."
    ::= { cSpLinkTableEntry 29 }

cSpLinkMtp3T08 OBJECT-TYPE
    SYNTAX Gauge
    ACCESS read-only
    STATUS mandatory
    DESCRIPTION
        "Transfer prohibited inhibition timer (transient
        solution)."
    REFERENCE
        "ITU Q.704 Signalling network functions and messages.
        ANSI T1.111 Telecommunications - Signaling system
        No. 7 (SS7)-Message Transfer Part (MTP)."
    ::= { cSpLinkTableEntry 30 }

cSpLinkMtp3T10 OBJECT-TYPE
    SYNTAX Gauge
    ACCESS read-only
    STATUS mandatory
    DESCRIPTION
        "Waiting to repeat signalling routeset test message."
    REFERENCE
        "ITU Q.704 Signalling network functions and messages.
        ANSI T1.111 Telecommunications - Signaling system
        No. 7 (SS7)-Message Transfer Part (MTP)."
    ::= { cSpLinkTableEntry 31 }

cSpLinkMtp3T11 OBJECT-TYPE
    SYNTAX Gauge
    ACCESS read-only
    STATUS mandatory
    DESCRIPTION
        "Transfer restricted timer. (This is one way of
        implementing the function described in 13.4/Q.704 and
        mainly intended to simplify SPs.)."
    REFERENCE
        "ITU Q.704 Signalling network functions and messages.
        ANSI T1.111 Telecommunications - Signaling system
        No. 7 (SS7)-Message Transfer Part (MTP)."
    ::= { cSpLinkTableEntry 32 }

cSpLinkMtp3T12 OBJECT-TYPE
    SYNTAX Gauge
    ACCESS read-only
    STATUS mandatory
    DESCRIPTION
        "Waiting for uninhibit acknowledgement."
    REFERENCE
        "ITU Q.704 Signalling network functions and messages.
        ANSI T1.111 Telecommunications - Signaling system
        No. 7 (SS7)-Message Transfer Part (MTP)."
    ::= { cSpLinkTableEntry 33 }

cSpLinkMtp3T13 OBJECT-TYPE
    SYNTAX Gauge
    ACCESS read-only
    STATUS mandatory
    DESCRIPTION
        "Waiting for force uninhibit."
    REFERENCE
        "ITU Q.704 Signalling network functions and messages.
        ANSI T1.111 Telecommunications - Signaling system
        No. 7 (SS7)-Message Transfer Part (MTP)."
    ::= { cSpLinkTableEntry 34 }

cSpLinkMtp3T14 OBJECT-TYPE
    SYNTAX Gauge
    ACCESS read-only
    STATUS mandatory
    DESCRIPTION
        "Waiting for inhibition acknowledgement."
    REFERENCE
        "ITU Q.704 Signalling network functions and messages.
        ANSI T1.111 Telecommunications - Signaling system
        No. 7 (SS7)-Message Transfer Part (MTP)."
    ::= { cSpLinkTableEntry 35 }

cSpLinkMtp3T15 OBJECT-TYPE
    SYNTAX Gauge
    ACCESS read-only
    STATUS mandatory
    DESCRIPTION
        "Waiting to start signalling routeset congestion
        test."
    REFERENCE
        "ITU Q.704 Signalling network functions and messages.
        ANSI T1.111 Telecommunications - Signaling system
        No. 7 (SS7)-Message Transfer Part (MTP)."
    ::= { cSpLinkTableEntry 36 }

cSpLinkMtp3T16 OBJECT-TYPE
    SYNTAX Gauge
    ACCESS read-only
    STATUS mandatory
    DESCRIPTION
        "Waiting for routeset congestion status update."
    REFERENCE
        "ITU Q.704 Signalling network functions and messages.
        ANSI T1.111 Telecommunications - Signaling system
        No. 7 (SS7)-Message Transfer Part (MTP)."
    ::= { cSpLinkTableEntry 37 }

cSpLinkMtp3T17 OBJECT-TYPE
    SYNTAX Gauge
    ACCESS read-only
    STATUS mandatory
    DESCRIPTION
        "Delay to avoid oscillation of initial alignment
        failure and link restart."
    REFERENCE
        "ITU Q.704 Signalling network functions and messages.
        ANSI T1.111 Telecommunications - Signaling system
        No. 7 (SS7)-Message Transfer Part (MTP)."
    ::= { cSpLinkTableEntry 38 }

cSpLinkMtp3T18 OBJECT-TYPE
    SYNTAX Gauge
    ACCESS read-only
    STATUS mandatory
    DESCRIPTION
        "Timer within a signalling point whose MTP restarts,
        for supervising link and linkset activation as well as
        the receipt of routing information."
    REFERENCE
        "ITU Q.704 Signalling network functions and messages.
        ANSI T1.111 Telecommunications - Signaling system
        No. 7 (SS7)-Message Transfer Part (MTP)."
    ::= { cSpLinkTableEntry 39 }

cSpLinkMtp3T19 OBJECT-TYPE
    SYNTAX Gauge
    ACCESS read-only
    STATUS mandatory
    DESCRIPTION
        "Supervision timer during MTP restart to avoid
        possible ping-pong of TFP, TFR2) and TRA messages."
    REFERENCE
        "ITU Q.704 Signalling network functions and messages.
        ANSI T1.111 Telecommunications - Signaling system
        No. 7 (SS7)-Message Transfer Part (MTP)."
    ::= { cSpLinkTableEntry 40 }

cSpLinkMtp3T20 OBJECT-TYPE
    SYNTAX Gauge
    ACCESS read-only
    STATUS mandatory
    DESCRIPTION
        "Overall MTP restart timer at the signalling point
        whose MTP restarts. Overall MTP restart timer at a
        signalling point adjacent to one whose MTP restarts."
    REFERENCE
        "ITU Q.704 Signalling network functions and messages.
        ANSI T1.111 Telecommunications - Signaling system
        No. 7 (SS7)-Message Transfer Part (MTP)."
    ::= { cSpLinkTableEntry 41 }

cSpLinkMtp3T21 OBJECT-TYPE
    SYNTAX Gauge
    ACCESS read-only
    STATUS mandatory
    DESCRIPTION
        "Overall MTP restart timer at a signalling point
        adjacent to one whose MTP restarts."
    REFERENCE
        "ITU Q.704 Signalling network functions and messages.
        ANSI T1.111 Telecommunications - Signaling system
        No. 7 (SS7)-Message Transfer Part (MTP)."
    ::= { cSpLinkTableEntry 42 }

cSpLinkMtp3T22 OBJECT-TYPE
    SYNTAX Gauge
    ACCESS read-only
    STATUS mandatory
    DESCRIPTION
        "Local inhibit test timer."
    REFERENCE
        "ITU Q.704 Signalling network functions and messages.
        ANSI T1.111 Telecommunications - Signaling system
        No. 7 (SS7)-Message Transfer Part (MTP)."
    ::= { cSpLinkTableEntry 43 }

cSpLinkMtp3T23 OBJECT-TYPE
    SYNTAX Gauge
    ACCESS read-only
    STATUS mandatory
    DESCRIPTION
        "Remote inhibit test timer."
    REFERENCE
        "ITU Q.704 Signalling network functions and messages.
        ANSI T1.111 Telecommunications - Signaling system
        No. 7 (SS7)-Message Transfer Part (MTP)."
    ::= { cSpLinkTableEntry 44 }

cSpLinkMtp3T24 OBJECT-TYPE
    SYNTAX Gauge
    ACCESS read-only
    STATUS mandatory
    DESCRIPTION
        "Stabilizing timer after removal of local processor
        outage, used in LPO latching to RPO (national option)"
    REFERENCE
        "ITU Q.704 Signalling network functions and messages.
        ANSI T1.111 Telecommunications - Signaling system
        No. 7 (SS7)-Message Transfer Part (MTP)."
    ::= { cSpLinkTableEntry 45 }

cSpLinkMtp3T25 OBJECT-TYPE
    SYNTAX Gauge
    ACCESS read-only
    STATUS mandatory
    DESCRIPTION
        "Timer at Signalling Point (SP) adjacent to restarting
        SP, waiting for traffic restart allowed message."
    REFERENCE
        "ANSI T1.111 Telecommunications - Signaling system
        No. 7 (SS7)-Message Transfer Part (MTP)."
    ::= { cSpLinkTableEntry 46 }

cSpLinkMtp3T26 OBJECT-TYPE
    SYNTAX Gauge
    ACCESS read-only
    STATUS mandatory
    DESCRIPTION
        "Timer at restarting SP waiting to repeat traffic
        restart waiting message."
    REFERENCE
        "ANSI T1.111 Telecommunications - Signaling system
        No. 7 (SS7)-Message Transfer Part (MTP)."
    ::= { cSpLinkTableEntry 47 }

cSpLinkMtp3T27 OBJECT-TYPE
    SYNTAX Gauge
    ACCESS read-only
    STATUS mandatory
    DESCRIPTION
        "Minimum duration of unavailability for full restart."
    REFERENCE
        "ANSI T1.111 Telecommunications - Signaling system
        No. 7 (SS7)-Message Transfer Part (MTP)."
    ::= { cSpLinkTableEntry 48 }

cSpLinkMtp3T28 OBJECT-TYPE
    SYNTAX Gauge
    ACCESS read-only
    STATUS mandatory
    DESCRIPTION
        "Timer at SP adjacent to restarting SP waiting for
                traffic restart waiting message."
    REFERENCE
        "ANSI T1.111 Telecommunications - Signaling system
        No. 7 (SS7)-Message Transfer Part (MTP)."
    ::= { cSpLinkTableEntry 49 }

cSpLinkMtp3T29 OBJECT-TYPE
    SYNTAX Gauge
    ACCESS read-only
    STATUS mandatory
    DESCRIPTION
        "Timer started when TRA sent in response to unexpected
        TRA or TRW."
    REFERENCE
        "ANSI T1.111 Telecommunications - Signaling system
        No. 7 (SS7)-Message Transfer Part (MTP)."
    ::= { cSpLinkTableEntry 50 }

cSpLinkMtp3T30 OBJECT-TYPE
    SYNTAX Gauge
    ACCESS read-only
    STATUS mandatory
    DESCRIPTION
        "Timer to limit sending of TFPs and TFRs in response
        to unexpected TRA or TRW."
    REFERENCE
        "ANSI T1.111 Telecommunications - Signaling system
        No. 7 (SS7)-Message Transfer Part (MTP)."
    ::= { cSpLinkTableEntry 51 }

cSpLinkMtp3T31 OBJECT-TYPE
    SYNTAX Gauge
    ACCESS read-only
    STATUS mandatory
    DESCRIPTION
        "False link congestion detection timer."
    REFERENCE
        "ANSI T1.111 Telecommunications - Signaling system
        No. 7 (SS7)-Message Transfer Part (MTP)."
    ::= { cSpLinkTableEntry 52 }

cSpLinkMtp3T32 OBJECT-TYPE
    SYNTAX Gauge
    ACCESS read-only
    STATUS mandatory
    DESCRIPTION
        "Link oscillation timer - Procedure A."
    REFERENCE
        "ANSI T1.111 Telecommunications - Signaling system
        No. 7 (SS7)-Message Transfer Part (MTP)."
    ::= { cSpLinkTableEntry 53 }

cSpLinkMtp3T33 OBJECT-TYPE
    SYNTAX Gauge
    ACCESS read-only
    STATUS mandatory
    DESCRIPTION
        "Probation timer for link oscillation - Procedure B."
    REFERENCE
        "ANSI T1.111 Telecommunications - Signaling system
        No. 7 (SS7)-Message Transfer Part (MTP)."
    ::= { cSpLinkTableEntry 54 }

cSpLinkMtp3T34 OBJECT-TYPE
    SYNTAX Gauge
    ACCESS read-only
    STATUS mandatory
    DESCRIPTION
        "Suspension timer for link oscillation - Procedure B."
    REFERENCE
        "ANSI T1.111 Telecommunications - Signaling system
        No. 7 (SS7)-Message Transfer Part (MTP)."
    ::= { cSpLinkTableEntry 55 }

cSpLinkXmitQueueDepth OBJECT-TYPE
    SYNTAX Gauge
    ACCESS read-only
    STATUS mandatory
    DESCRIPTION
        "Number of packets waiting to be sent over this link."
    ::= { cSpLinkTableEntry 56 }

cSpLinkXmitQueueDepthHigh OBJECT-TYPE
    SYNTAX Gauge
    ACCESS read-write
    STATUS mandatory
    DESCRIPTION
        "This is the maximum number of packets waiting
        to be sent over this link since the last time this
         value was reset as indicated by 
         cSpLinkXmitQueueDepthHighReset. 
         Resetting this object is achieved by setting this
         object to 0. Attempting to set this object to any
         other value will result in a wrongValue error."
    ::= { cSpLinkTableEntry 57 }

cSpLinkXmitQueueDepthHighReset OBJECT-TYPE
    SYNTAX TimeStamp
--    Rsyntax TimeTicks
    ACCESS read-only
    STATUS mandatory
    DESCRIPTION
        "This indicates when cSpLinkXmitQueueDepthHigh
        was set to 0."
    ::= { cSpLinkTableEntry 58 }

cSpLinkCongestionState OBJECT-TYPE
    SYNTAX Gauge(0..3)
    ACCESS read-only
    STATUS mandatory
    DESCRIPTION
        "The signalling link congestion status of this link. 0
        is the least congestion level, 3 is the highest
        congestion level."
    REFERENCE
        "ITU Q.704 Signalling network functions and messages.
        ANSI T1.111 Telecommunications - Signaling system
        No. 7 (SS7)-Signalling network functions and messages
        2.3.5.2."
    ::= { cSpLinkTableEntry 59 }

cSpLinkCongestionAbate1 OBJECT-TYPE
    SYNTAX Gauge
    ACCESS read-only
    STATUS mandatory
    DESCRIPTION
        "Threshold used to abate congestion level 1."
    ::= { cSpLinkTableEntry 60 }

cSpLinkCongestionAbate2 OBJECT-TYPE
    SYNTAX Gauge
    ACCESS read-only
    STATUS mandatory
    DESCRIPTION
        "Threshold used to abate congestion level 2."
    ::= { cSpLinkTableEntry 61 }

cSpLinkCongestionAbate3 OBJECT-TYPE
    SYNTAX Gauge
    ACCESS read-only
    STATUS mandatory
    DESCRIPTION
        "Threshold used to abate congestion level 3."
    ::= { cSpLinkTableEntry 62 }

cSpLinkCongestionOnset1 OBJECT-TYPE
    SYNTAX Gauge
    ACCESS read-only
    STATUS mandatory
    DESCRIPTION
        "Threshold used to mark onset of congestion level 1."
    ::= { cSpLinkTableEntry 63 }

cSpLinkCongestionOnset2 OBJECT-TYPE
    SYNTAX Gauge
    ACCESS read-only
    STATUS mandatory
    DESCRIPTION
        "Threshold used to mark onset of congestion level 2."
    ::= { cSpLinkTableEntry 64 }

cSpLinkCongestionOnset3 OBJECT-TYPE
    SYNTAX Gauge
    ACCESS read-only
    STATUS mandatory
    DESCRIPTION
        "Threshold used to mark onset of congestion level 3."
    ::= { cSpLinkTableEntry 65 }

cSpLinkSigLinkTest OBJECT-TYPE
    SYNTAX TruthValue
--    Rsyntax INTEGER {
--        true(1),
--        false(2)
--        }
    ACCESS read-only
    STATUS mandatory
    DESCRIPTION
        "Indicated if signalling link test is enabled on this
        link.
        
        true  : signalling link test is enabled.
        false : signalling link test not enabled."
    DEFVAL { true }
    ::= { cSpLinkTableEntry 66 }

cSpLinkQ752T1E1 OBJECT-TYPE
    SYNTAX TimeTicks
    ACCESS read-only
    STATUS mandatory
    DESCRIPTION
        "Duration of link in the In-Service state Q752/1.1."
    ::= { cSpLinkTableEntry 67 }

cSpLinkQ752T1E2 OBJECT-TYPE
    SYNTAX Counter
    ACCESS read-only
    STATUS mandatory
    DESCRIPTION
        "Count of Signalling Link failures - All reasons Q752/1.2."
    ::= { cSpLinkTableEntry 68 }

cSpLinkQ752T1E3 OBJECT-TYPE
    SYNTAX Counter
    ACCESS read-only
    STATUS mandatory
    DESCRIPTION
        "Count of Signalling Link failures - Abnormal FIBR/BSNR 
         Q752/1.4."
    ::= { cSpLinkTableEntry 69 }

cSpLinkQ752T1E4 OBJECT-TYPE
    SYNTAX Counter
    ACCESS read-only
    STATUS mandatory
    DESCRIPTION
        "Count of Signalling Link failures - Excessive delay of 
         acknowledgement Q752/1.4."
    ::= { cSpLinkTableEntry 70 }

cSpLinkQ752T1E5 OBJECT-TYPE
    SYNTAX Counter
    ACCESS read-only
    STATUS mandatory
    DESCRIPTION
        "Count of Signalling Link failures - Excessive error rate 
         Q752/1.5."
    ::= { cSpLinkTableEntry 71 }

cSpLinkQ752T1E6 OBJECT-TYPE
    SYNTAX Counter
    ACCESS read-only
    STATUS mandatory
    DESCRIPTION
        "Count of Signalling Link failures - Excessive duration 
         of congestion Q752/1.6."
    ::= { cSpLinkTableEntry 72 }

cSpLinkQ752T1E7 OBJECT-TYPE
    SYNTAX Counter
    ACCESS read-only
    STATUS mandatory
    DESCRIPTION
        "Count of alignment or proving errors Q752/1.7."
    ::= { cSpLinkTableEntry 73 }

cSpLinkQ752T1E8 OBJECT-TYPE
    SYNTAX Counter
    ACCESS read-only
    STATUS mandatory
    DESCRIPTION
        "Count of signal units received in error Q752/1.8."
    ::= { cSpLinkTableEntry 74 }

cSpLinkQ752T1E9 OBJECT-TYPE
    SYNTAX Counter
    ACCESS read-only
    STATUS mandatory
    DESCRIPTION
        "Count of negative acknowledgements received Q752/1.9."
    ::= { cSpLinkTableEntry 75 }

cSpLinkQ752T1E10 OBJECT-TYPE
    SYNTAX Counter
    ACCESS read-only
    STATUS mandatory
    DESCRIPTION
        "Count of 'local automatic changeover' events
            Q752/1.10."
    ::= { cSpLinkTableEntry 76 }

cSpLinkQ752T1E11 OBJECT-TYPE
    SYNTAX Counter
    ACCESS read-only
    STATUS mandatory
    DESCRIPTION
        "Count of 'local automatic changeback' events Q752/1.11."
    ::= { cSpLinkTableEntry 77 }

cSpLinkQ752T2E1 OBJECT-TYPE
    SYNTAX TimeTicks
    ACCESS read-only
    STATUS mandatory
    DESCRIPTION
        "Duration of Signalling Link unavailable(for any reason)
         Q752/2.1."
    ::= { cSpLinkTableEntry 78 }

cSpLinkQ752T2E5 OBJECT-TYPE
    SYNTAX TimeTicks
    ACCESS read-only
    STATUS mandatory
    DESCRIPTION
        "Duration of Signalling Link unavailable due to local 
         management actions Q752/2.5."
    ::= { cSpLinkTableEntry 79 }

cSpLinkQ752T2E6 OBJECT-TYPE
    SYNTAX TimeTicks
    ACCESS read-only
    STATUS mandatory
    DESCRIPTION
        "Duration of Signalling Link unavailable due to remote 
         management actions Q752/2.6."
    ::= { cSpLinkTableEntry 80 }

cSpLinkQ752T2E7 OBJECT-TYPE
    SYNTAX TimeTicks
    ACCESS read-only
    STATUS mandatory
    DESCRIPTION
        "Duration of Signalling Link unavailable due to link 
         failure Q752/2.7."
    ::= { cSpLinkTableEntry 81 }

cSpLinkQ752T2E9 OBJECT-TYPE
    SYNTAX TimeTicks
    ACCESS read-only
    STATUS mandatory
    DESCRIPTION
        "Duration of Signalling Link unavailable due to remote 
         processor outage Q752/2.9."
    ::= { cSpLinkTableEntry 82 }

cSpLinkQ752T2E10 OBJECT-TYPE
    SYNTAX Counter
    ACCESS read-only
    STATUS mandatory
    DESCRIPTION
        "Count of 'remote processor outage' events Q752/2.10 and
         Q752/2.11.  The standard only requires that events are
         issued.  The entries have been combined into a single 
         entry to track all occurrences of these event types."
    ::= { cSpLinkTableEntry 83 }

cSpLinkQ752T2E15 OBJECT-TYPE
    SYNTAX TimeTicks
    ACCESS read-only
    STATUS mandatory
    DESCRIPTION
        "Duration of local busy Q752/2.15."
    ::= { cSpLinkTableEntry 84 }

cSpLinkQ752T2E16 OBJECT-TYPE
    SYNTAX Counter
    ACCESS read-only
    STATUS mandatory
    DESCRIPTION
        "Count of local inhibition Q752/2.16 and Q752/2.17.
         The standard only requires that events are issued.
         The entries have been combined into a single 
         entry to track all occurrences of these event types."
    ::= { cSpLinkTableEntry 85 }

cSpLinkQ752T2E18 OBJECT-TYPE
    SYNTAX Counter
    ACCESS read-only
    STATUS mandatory
    DESCRIPTION
        "Count of remote inhibition Q752/2.18 and Q752/2.19.
         The standard only requires that events are issued.
         The entries have been combined into a single 
         entry to track all occurrences of these event types."
    ::= { cSpLinkTableEntry 86 }

cSpLinkMtp3PacketsRetrans OBJECT-TYPE
    SYNTAX Counter
--  Units
--    packets
    ACCESS read-only
    STATUS mandatory
    DESCRIPTION
        "The number of MTP3 packets retransmitted on this link.
         This measurement is specified in Q752/3.2"
    ::= { cSpLinkTableEntry 87 }

cSpLinkMtp3BytesRetrans OBJECT-TYPE
    SYNTAX Counter
--  Units
--    bytes
    ACCESS read-only
    STATUS mandatory
    DESCRIPTION
        "The number of MTP3 bytes retransmitted on this link.
         This measurement is specified in Q752/3.2"
    ::= { cSpLinkTableEntry 88 }

cSpLinkQ752T3E6 OBJECT-TYPE
    SYNTAX Counter
--  Units
--    events
    ACCESS read-only
    STATUS mandatory
    DESCRIPTION
        "The number times this signalling link was marked
         congested. This measurement is specified in Q752/3.6"
    ::= { cSpLinkTableEntry 89 }

cSpLinkQ752T3E7 OBJECT-TYPE
    SYNTAX TimeTicks
    ACCESS read-only
    STATUS mandatory
    DESCRIPTION
        "Cumulative duration of signalling link congestion 
          Q752/3.7."
    ::= { cSpLinkTableEntry 90 }

cSpLinkQ752T3E10L1 OBJECT-TYPE
    SYNTAX Counter
--  Units
--    Packets
    ACCESS read-only
    STATUS mandatory
    DESCRIPTION
        "The number of packets(MSUs) discarded due to signalling 
         link level 1 congestion Q752/3.10"
    ::= { cSpLinkTableEntry 91 }

cSpLinkQ752T3E10L2 OBJECT-TYPE
    SYNTAX Counter
--  Units
--    Packets
    ACCESS read-only
    STATUS mandatory
    DESCRIPTION
        "The number of packets(MSUs) discard due to signalling 
         link level 2 congestion Q752/3.10"
    ::= { cSpLinkTableEntry 92 }

cSpLinkQ752T3E10L3 OBJECT-TYPE
    SYNTAX Counter
--  Units
--    Packets
    ACCESS read-only
    STATUS mandatory
    DESCRIPTION
        "The number of packets(MSUs) discard due to signalling 
         link level 3 congestion Q752/3.10"
    ::= { cSpLinkTableEntry 93 }

cSpLinkQ752T3E11L1 OBJECT-TYPE
    SYNTAX Counter
--  Units
--    bytes
    ACCESS read-only
    STATUS mandatory
    DESCRIPTION
        "The number times this signalling link entered congestion
         level 1 and packets were discarded. This measurement is 
         specified in Q752/3.11"
    ::= { cSpLinkTableEntry 94 }

cSpLinkQ752T3E11L2 OBJECT-TYPE
    SYNTAX Counter
--  Units
--    bytes
    ACCESS read-only
    STATUS mandatory
    DESCRIPTION
        "The number times this signalling link entered congestion
         level 2 and packets were discarded. This measurement is 
         specified in Q752/3.11"
    ::= { cSpLinkTableEntry 95 }

cSpLinkQ752T3E11L3 OBJECT-TYPE
    SYNTAX Counter
--  Units
--    bytes
    ACCESS read-only
    STATUS mandatory
    DESCRIPTION
        "The number times this signalling link entered congestion
         level 3 and packets were discarded. This measurement is 
         specified in Q752/3.11"
    ::= { cSpLinkTableEntry 96 }

cSpRouteTable OBJECT-TYPE
    SYNTAX SEQUENCE OF CSpRouteTableEntry
    ACCESS not-accessible
    STATUS mandatory
    DESCRIPTION
        "The route table for determining the linkset that a
         packet must traverse to arrive at its destination node
         given by the destination point code."
    ::= { cSpRoute 1 }

cSpRouteTableEntry OBJECT-TYPE
    SYNTAX CSpRouteTableEntry
    ACCESS not-accessible
    STATUS mandatory
    DESCRIPTION
        "A list statements used to route mtp3 packets. 
         Information in packets are matched against the
         information in each route statements and the 
         packet is sent on the selected linkset."
    INDEX { cSpRouteTableName, cSpRouteDpc, cSpRouteDestLsCost, cSpRouteDestLinkset, cSpRouteMask }
    ::= { cSpRouteTable 1 }

CSpRouteTableEntry ::= SEQUENCE {
    cSpRouteTableName CSpRouteTableName,
    cSpRouteDpc CSpPointCode,
    cSpRouteDestLsCost Gauge,
    cSpRouteDestLinkset CSpLinksetId,
    cSpRouteMask Gauge,
    cSpRouteStatus CSpRouteStatus
    }

cSpRouteTableName OBJECT-TYPE
    SYNTAX CSpRouteTableName
--    Rsyntax OCTET STRING(SIZE(1..19))
    ACCESS not-accessible
    STATUS mandatory
    DESCRIPTION
        "The configured name for this route table."
    ::= { cSpRouteTableEntry 1 }

cSpRouteDpc OBJECT-TYPE
    SYNTAX CSpPointCode
--    Rsyntax Gauge(0..16777216)
    ACCESS not-accessible
    STATUS mandatory
    DESCRIPTION
        "The destination point code."
    ::= { cSpRouteTableEntry 2 }

cSpRouteDestLsCost OBJECT-TYPE
    SYNTAX Gauge(1..9)
    ACCESS not-accessible
    STATUS mandatory
    DESCRIPTION
        "The cost assigned to this linkset matching this
        route. Higher numbers represent higher cost."
    ::= { cSpRouteTableEntry 3 }

cSpRouteDestLinkset OBJECT-TYPE
    SYNTAX CSpLinksetId
--    Rsyntax OCTET STRING(SIZE(1..19))
    ACCESS not-accessible
    STATUS mandatory
    DESCRIPTION
        "The linkset that the packet is to be forwarded to on
        matching this route."
    ::= { cSpRouteTableEntry 4 }

cSpRouteMask OBJECT-TYPE
    SYNTAX Gauge
    ACCESS not-accessible
    STATUS mandatory
    DESCRIPTION
        "The mask used to define which part of
        cSpRouteDpc  is significant when comparing
        the cSpRouteDpc  to the destination code
        point in the packet to be routed."
    ::= { cSpRouteTableEntry 5 }

cSpRouteStatus OBJECT-TYPE
    SYNTAX CSpRouteStatus
--    Rsyntax INTEGER {
--        available(1),
--        restricted(2),
--        unavailable(3)
--        }
    ACCESS read-only
    STATUS mandatory
    DESCRIPTION
        "The status of the route from the perspective of the 
         Signaling Point."
    ::= { cSpRouteTableEntry 6 }

cSpAclTable OBJECT-TYPE
    SYNTAX SEQUENCE OF CSpAclTableEntry
    ACCESS not-accessible
    STATUS mandatory
    DESCRIPTION
        "A table of SP access controls. The access control
        definition controls which packets are accepted or
        rejected. The access control may be applied before
        sending the packet to the routing table or may be
        applied after the packet is processed by the routing
        table."
    ::= { cSpAccessControlList 1 }

cSpAclTableEntry OBJECT-TYPE
    SYNTAX CSpAclTableEntry
    ACCESS not-accessible
    STATUS mandatory
    DESCRIPTION
        "A list of SP access control attributes."
    INDEX { cSpAclId, cSpAclEntryNumber }
    ::= { cSpAclTable 1 }

CSpAclTableEntry ::= SEQUENCE {
    cSpAclId CSpAclId,
    cSpAclEntryNumber Gauge,
    cSpAclType INTEGER,
    cSpAclDpc CSpPointCode,
    cSpAclDpcMask Gauge,
    cSpAclOpc CSpPointCode,
    cSpAclOpcMask Gauge,
    cSpAclSi CSpAclSi,
    cSpAclPattern DisplayString,
    cSpAclOffset Gauge,
    cSpAclAction CSpAclAction
    }

cSpAclId OBJECT-TYPE
    SYNTAX CSpAclId
--    Rsyntax Gauge(0..2999)
    ACCESS not-accessible
    STATUS mandatory
    DESCRIPTION
        "The identifier for this ACL."
    ::= { cSpAclTableEntry 1 }

cSpAclEntryNumber OBJECT-TYPE
    SYNTAX Gauge
    ACCESS not-accessible
    STATUS mandatory
    DESCRIPTION
        "An numeric value assigned to each access list entry.
        The values start with zero and increase by one."
    ::= { cSpAclTableEntry 2 }

cSpAclType OBJECT-TYPE
    SYNTAX INTEGER {
        dpc(1),
        opc(2),
        pattern(3),
        sio(4)
        }
    ACCESS read-only
    STATUS mandatory
    DESCRIPTION
        "This indicates which columns are used in determining
        the matching criteria for this access control.
        
        'dpc' : cSpAclDpc and cSpAclDpcMask are the relevant
                columns. The packet is compared to cSpAclDpc
                in conjunction with cSpAclDpcMask to determine
                if the packet matches this access control.
        'opc' : cSpAclOpc and cSpAclOpcMask are the relevant
                columns. The packet is compared to cSpAclOpc
                in conjunction with cSpAclOpcMask to determine
                if the packet matches this access control.
        'pattern' : cSpAclPattern and cSpAclOffset are the 
                relevant columns. The matching criteria is 
                based on matching the pattern specified by 
                cSpAclPattern at offset cSpAclOffset from 
                the start of the packet.
        'sio' : cSpAclSi is the relevant column. The SIO
                field of the packet is compared to cSpAclSi
                and a match is based on equality. "
    ::= { cSpAclTableEntry 3 }

cSpAclDpc OBJECT-TYPE
    SYNTAX CSpPointCode
--    Rsyntax Gauge(0..16777216)
    ACCESS read-only
    STATUS mandatory
    DESCRIPTION
        "The destination point code specified for this ACL."
    ::= { cSpAclTableEntry 4 }

cSpAclDpcMask OBJECT-TYPE
    SYNTAX Gauge
    ACCESS read-only
    STATUS mandatory
    DESCRIPTION
        "The mask used to define which part of the point code
        in the packet is significant when comparing the
        destination point code with cSpAclDpc."
    ::= { cSpAclTableEntry 5 }

cSpAclOpc OBJECT-TYPE
    SYNTAX CSpPointCode
--    Rsyntax Gauge(0..16777216)
    ACCESS read-only
    STATUS mandatory
    DESCRIPTION
        "The origin point code specified in this ACL."
    ::= { cSpAclTableEntry 6 }

cSpAclOpcMask OBJECT-TYPE
    SYNTAX Gauge
    ACCESS read-only
    STATUS mandatory
    DESCRIPTION
        "The mask used to define which part of the origin
        point code in the packet is significant when comparing
        the origin point code with cSpAclDpc."
    ::= { cSpAclTableEntry 7 }

cSpAclSi OBJECT-TYPE
    SYNTAX CSpAclSi
--    Rsyntax Gauge(0..15)
    ACCESS read-only
    STATUS mandatory
    DESCRIPTION
        "The Service Indicator Octet."
    ::= { cSpAclTableEntry 8 }

cSpAclPattern OBJECT-TYPE
    SYNTAX DisplayString(SIZE(0..32))
--    Rsyntax OCTET STRING(SIZE(0..32))
    ACCESS read-only
    STATUS mandatory
    DESCRIPTION
        "The pattern used to match a packet at offset
        cSpAclOffset."
    DEFVAL { "" }
    ::= { cSpAclTableEntry 9 }

cSpAclOffset OBJECT-TYPE
    SYNTAX Gauge
    ACCESS read-only
    STATUS mandatory
    DESCRIPTION
        "The offset into the packet were we begin matching the
        pattern specified by cSpAclPattern is to start."
    ::= { cSpAclTableEntry 10 }

cSpAclAction OBJECT-TYPE
    SYNTAX CSpAclAction
--    Rsyntax INTEGER {
--        accept(1),
--        discard(2)
--        }
    ACCESS read-only
    STATUS mandatory
    DESCRIPTION
        "The action to be performed on the packet that matched
        this access control."
    ::= { cSpAclTableEntry 11 }

cSpAccountingTable OBJECT-TYPE
    SYNTAX SEQUENCE OF CSpAccountingTableEntry
    ACCESS not-accessible
    STATUS mandatory
    DESCRIPTION
        "A table of packet and byte counts for packets that
        match an ACL in the linkset's inbound ACL and in the
        outbound ACL. These counters are updated no more
        frequently than the value specified by
        cSpAccCheckPointPeriod. Polling more frequently than
        this period results in the same values being
        returned."
    ::= { cSpAccounting 1 }

cSpAccountingTableEntry OBJECT-TYPE
    SYNTAX CSpAccountingTableEntry
    ACCESS not-accessible
    STATUS mandatory
    DESCRIPTION
        "A list of accounting objects."
    INDEX { cSpAccTableId, cSpLinksetName, cSpAccDpc, cSpAccOpc }
    ::= { cSpAccountingTable 1 }

CSpAccountingTableEntry ::= SEQUENCE {
    cSpAccTableId INTEGER,
    cSpAccDpc CSpPointCode,
    cSpAccOpc CSpPointCode,
    cSpAccRcvdPackets Counter,
    cSpAccHCRcvdPackets Counter,
    cSpAccSentPackets Counter,
    cSpAccHCSentPackets Counter,
    cSpAccRcvdBytes Counter,
    cSpAccHCRcvdBytes Counter,
    cSpAccSentBytes Counter,
    cSpAccHCSentBytes Counter,
    cSpAccSnmmRcvdPackets Counter,
    cSpAccHCSnmmRcvdPackets Counter,
    cSpAccSnmmRcvdBytes Counter,
    cSpAccHCSnmmRcvdBytes Counter,
    cSpAccSnmmSentPackets Counter,
    cSpAccHCSnmmSentPackets Counter,
    cSpAccSnmmSentBytes Counter,
    cSpAccHCSnmmSentBytes Counter,
    cSpAccSntmRcvdPackets Counter,
    cSpAccHCSntmRcvdPackets Counter,
    cSpAccSntmRcvdBytes Counter,
    cSpAccHCSntmRcvdBytes Counter,
    cSpAccSntmSentPackets Counter,
    cSpAccHCSntmSentPackets Counter,
    cSpAccSntmSentBytes Counter,
    cSpAccHCSntmSentBytes Counter,
    cSpAccSpare2RcvdPackets Counter,
    cSpAccHCSpare2RcvdPackets Counter,
    cSpAccSpare2RcvdBytes Counter,
    cSpAccHCSpare2RcvdBytes Counter,
    cSpAccSpare2SentPackets Counter,
    cSpAccHCSpare2SentPackets Counter,
    cSpAccSpare2SentBytes Counter,
    cSpAccHCSpare2SentBytes Counter,
    cSpAccSccpRcvdPackets Counter,
    cSpAccHCSccpRcvdPackets Counter,
    cSpAccSccpRcvdBytes Counter,
    cSpAccHCSccpRcvdBytes Counter,
    cSpAccSccpSentPackets Counter,
    cSpAccHCSccpSentPackets Counter,
    cSpAccSccpSentBytes Counter,
    cSpAccHCSccpSentBytes Counter,
    cSpAccTupRcvdPackets Counter,
    cSpAccHCTupRcvdPackets Counter,
    cSpAccTupRcvdBytes Counter,
    cSpAccHCTupRcvdBytes Counter,
    cSpAccTupSentPackets Counter,
    cSpAccHCTupSentPackets Counter,
    cSpAccTupSentBytes Counter,
    cSpAccHCTupSentBytes Counter,
    cSpAccIsupRcvdPackets Counter,
    cSpAccHCIsupRcvdPackets Counter,
    cSpAccIsupRcvdBytes Counter,
    cSpAccHCIsupRcvdBytes Counter,
    cSpAccIsupSentPackets Counter,
    cSpAccHCIsupSentPackets Counter,
    cSpAccIsupSentBytes Counter,
    cSpAccHCIsupSentBytes Counter,
    cSpAccDupcRcvdPackets Counter,
    cSpAccHCDupcRcvdPackets Counter,
    cSpAccDupcRcvdBytes Counter,
    cSpAccHCDupcRcvdBytes Counter,
    cSpAccDupcSentPackets Counter,
    cSpAccHCDupcSentPackets Counter,
    cSpAccDupcSentBytes Counter,
    cSpAccHCDupcSentBytes Counter,
    cSpAccDupfRcvdPackets Counter,
    cSpAccHCDupfRcvdPackets Counter,
    cSpAccDupfRcvdBytes Counter,
    cSpAccHCDupfRcvdBytes Counter,
    cSpAccDupfSentPackets Counter,
    cSpAccHCDupfSentPackets Counter,
    cSpAccDupfSentBytes Counter,
    cSpAccHCDupfSentBytes Counter,
    cSpAccMtupRcvdPackets Counter,
    cSpAccHCMtupRcvdPackets Counter,
    cSpAccMtupRcvdBytes Counter,
    cSpAccHCMtupRcvdBytes Counter,
    cSpAccMtupSentPackets Counter,
    cSpAccHCMtupSentPackets Counter,
    cSpAccMtupSentBytes Counter,
    cSpAccHCMtupSentBytes Counter,
    cSpAccBisupRcvdPackets Counter,
    cSpAccHCBisupRcvdPackets Counter,
    cSpAccBisupRcvdBytes Counter,
    cSpAccHCBisupRcvdBytes Counter,
    cSpAccBisupSentPackets Counter,
    cSpAccHCBisupSentPackets Counter,
    cSpAccBisupSentBytes Counter,
    cSpAccHCBisupSentBytes Counter,
    cSpAccSisupRcvdPackets Counter,
    cSpAccHCSisupRcvdPackets Counter,
    cSpAccSisupRcvdBytes Counter,
    cSpAccHCSisupRcvdBytes Counter,
    cSpAccSisupSentPackets Counter,
    cSpAccHCSisupSentPackets Counter,
    cSpAccSisupSentBytes Counter,
    cSpAccHCSisupSentBytes Counter,
    cSpAccSpare11RcvdPackets Counter,
    cSpAccHCSpare11RcvdPackets Counter,
    cSpAccSpare11RcvdBytes Counter,
    cSpAccHCSpare11RcvdBytes Counter,
    cSpAccSpare11SentPackets Counter,
    cSpAccHCSpare11SentPackets Counter,
    cSpAccSpare11SentBytes Counter,
    cSpAccHCSpare11SentBytes Counter,
    cSpAccSpare12RcvdPackets Counter,
    cSpAccHCSpare12RcvdPackets Counter,
    cSpAccSpare12RcvdBytes Counter,
    cSpAccHCSpare12RcvdBytes Counter,
    cSpAccSpare12SentPackets Counter,
    cSpAccHCSpare12SentPackets Counter,
    cSpAccSpare12SentBytes Counter,
    cSpAccHCSpare12SentBytes Counter,
    cSpAccSpare13RcvdPackets Counter,
    cSpAccHCSpare13RcvdPackets Counter,
    cSpAccSpare13RcvdBytes Counter,
    cSpAccHCSpare13RcvdBytes Counter,
    cSpAccSpare13SentPackets Counter,
    cSpAccHCSpare13SentPackets Counter,
    cSpAccSpare13SentBytes Counter,
    cSpAccHCSpare13SentBytes Counter,
    cSpAccSpare14RcvdPackets Counter,
    cSpAccHCSpare14RcvdPackets Counter,
    cSpAccSpare14RcvdBytes Counter,
    cSpAccHCSpare14RcvdBytes Counter,
    cSpAccSpare14SentPackets Counter,
    cSpAccHCSpare14SentPackets Counter,
    cSpAccSpare14SentBytes Counter,
    cSpAccHCSpare14SentBytes Counter,
    cSpAccSpare15RcvdPackets Counter,
    cSpAccHCSpare15RcvdPackets Counter,
    cSpAccSpare15RcvdBytes Counter,
    cSpAccHCSpare15RcvdBytes Counter,
    cSpAccSpare15SentPackets Counter,
    cSpAccHCSpare15SentPackets Counter,
    cSpAccSpare15SentBytes Counter,
    cSpAccHCSpare15SentBytes Counter
    }

cSpAccTableId OBJECT-TYPE
    SYNTAX INTEGER {
        passed(1),
        violation(2)
        }
    ACCESS not-accessible
    STATUS mandatory
    DESCRIPTION
        "The accounting table identifier.
        'passed'    : signifies that this table instance
                      represents statistics for packets that
                      matched an ACL in the linkset's
                      inbound ACL and in the outbound ACL.
        'violation' : signifies that this table instance
                      represents statistics for packets that
                      did not match an ACL in the linkset's
                      inbound ACL and in the outbound ACL."
    ::= { cSpAccountingTableEntry 1 }

cSpAccDpc OBJECT-TYPE
    SYNTAX CSpPointCode
--    Rsyntax Gauge(0..16777216)
    ACCESS not-accessible
    STATUS mandatory
    DESCRIPTION
        "The destination point code."
    ::= { cSpAccountingTableEntry 2 }

cSpAccOpc OBJECT-TYPE
    SYNTAX CSpPointCode
--    Rsyntax Gauge(0..16777216)
    ACCESS not-accessible
    STATUS mandatory
    DESCRIPTION
        "The origin point code."
    ::= { cSpAccountingTableEntry 3 }

cSpAccRcvdPackets OBJECT-TYPE
    SYNTAX Counter
--  Units
--    packets
    ACCESS read-only
    STATUS mandatory
    DESCRIPTION
        "Sum of all received packets for this linkset, DPC and
        OPC combination."
    ::= { cSpAccountingTableEntry 4 }

cSpAccHCRcvdPackets OBJECT-TYPE
    SYNTAX --?? syntax is not convertable to SMIv1
           Counter
--  Units
--    packets
    ACCESS read-only
    STATUS mandatory
    DESCRIPTION
        "Sum of all received packets for this linkset, DPC and
        OPC combination. This is the 64 bit version of
        cSpAccRcvdPackets    ."
    ::= { cSpAccountingTableEntry 5 }

cSpAccSentPackets OBJECT-TYPE
    SYNTAX Counter
--  Units
--    packets
    ACCESS read-only
    STATUS mandatory
    DESCRIPTION
        "Sum of all transmitted packets for this linkset, DPC
        and OPC combination."
    ::= { cSpAccountingTableEntry 6 }

cSpAccHCSentPackets OBJECT-TYPE
    SYNTAX --?? syntax is not convertable to SMIv1
           Counter
--  Units
--    packets
    ACCESS read-only
    STATUS mandatory
    DESCRIPTION
        "Sum of all transmitted packets for this linkset, DPC
        and OPC combination. This is the 64 bit version of
        cSpAccSentPackets   ."
    ::= { cSpAccountingTableEntry 7 }

cSpAccRcvdBytes OBJECT-TYPE
    SYNTAX Counter
--  Units
--    bytes
    ACCESS read-only
    STATUS mandatory
    DESCRIPTION
        "Sum of all received bytes for this linkset, DPC and
        OPC combination."
    ::= { cSpAccountingTableEntry 8 }

cSpAccHCRcvdBytes OBJECT-TYPE
    SYNTAX --?? syntax is not convertable to SMIv1
           Counter
--  Units
--    bytes
    ACCESS read-only
    STATUS mandatory
    DESCRIPTION
        "Sum of all received bytes for this linkset, DPC and
        OPC combination. This is the 64 bit version of
        cSpAccRcvdBytes    ."
    ::= { cSpAccountingTableEntry 9 }

cSpAccSentBytes OBJECT-TYPE
    SYNTAX Counter
--  Units
--    bytes
    ACCESS read-only
    STATUS mandatory
    DESCRIPTION
        "Sum of all transmitted bytes for this linkset, DPC
        and OPC combination."
    ::= { cSpAccountingTableEntry 10 }

cSpAccHCSentBytes OBJECT-TYPE
    SYNTAX --?? syntax is not convertable to SMIv1
           Counter
--  Units
--    bytes
    ACCESS read-only
    STATUS mandatory
    DESCRIPTION
        "Sum of all transmitted bytes for this linkset, DPC
        and OPC combination. This is the 64 bit version of
        cSpAccSentBytes   ."
    ::= { cSpAccountingTableEntry 11 }

cSpAccSnmmRcvdPackets OBJECT-TYPE
    SYNTAX Counter
--  Units
--    packets
    ACCESS read-only
    STATUS mandatory
    DESCRIPTION
        "Count of Signalling Network Management (SNM) packets
        received on this linkset, DPC and OPC combination."
    ::= { cSpAccountingTableEntry 12 }

cSpAccHCSnmmRcvdPackets OBJECT-TYPE
    SYNTAX --?? syntax is not convertable to SMIv1
           Counter
--  Units
--    packets
    ACCESS read-only
    STATUS mandatory
    DESCRIPTION
        "Count of Signalling Network Management (SNM) packets
        received on this linkset, DPC and OPC
        combination. This is the 64 bit version of
        cSpAccSnmmRcvdPackets    ."
    ::= { cSpAccountingTableEntry 13 }

cSpAccSnmmRcvdBytes OBJECT-TYPE
    SYNTAX Counter
--  Units
--    bytes
    ACCESS read-only
    STATUS mandatory
    DESCRIPTION
        "Count of bytes contained in the Signalling
        Network Management (SNM) messages received on this
        linkset, DPC and OPC combination."
    ::= { cSpAccountingTableEntry 14 }

cSpAccHCSnmmRcvdBytes OBJECT-TYPE
    SYNTAX --?? syntax is not convertable to SMIv1
           Counter
--  Units
--    bytes
    ACCESS read-only
    STATUS mandatory
    DESCRIPTION
        "Count of bytes contained in the Signalling Network
        Management (SNM) messages received on this linkset,
        DPC and OPC combination. This is the 64 bit version of
        cSpAccSnmmRcvdBytes    ."
    ::= { cSpAccountingTableEntry 15 }

cSpAccSnmmSentPackets OBJECT-TYPE
    SYNTAX Counter
--  Units
--    packets
    ACCESS read-only
    STATUS mandatory
    DESCRIPTION
        "Count of Signalling Network Management (SNM) packets
        transmitted on this linkset, DPC and OPC combination."
    ::= { cSpAccountingTableEntry 16 }

cSpAccHCSnmmSentPackets OBJECT-TYPE
    SYNTAX --?? syntax is not convertable to SMIv1
           Counter
--  Units
--    packets
    ACCESS read-only
    STATUS mandatory
    DESCRIPTION
        "Count of Signalling Network Management (SNM) packets
        transmitted on this linkset, DPC and OPC
        combination. This is the 64 bit version of
        cSpAccSnmmSentPackets   ."
    ::= { cSpAccountingTableEntry 17 }

cSpAccSnmmSentBytes OBJECT-TYPE
    SYNTAX Counter
--  Units
--    bytes
    ACCESS read-only
    STATUS mandatory
    DESCRIPTION
        "Count of Signalling Network Management (SNM) bytes
        transmitted on this linkset, DPC and OPC combination."
    ::= { cSpAccountingTableEntry 18 }

cSpAccHCSnmmSentBytes OBJECT-TYPE
    SYNTAX --?? syntax is not convertable to SMIv1
           Counter
--  Units
--    bytes
    ACCESS read-only
    STATUS mandatory
    DESCRIPTION
        "Count of Signalling Network Management (SNM) bytes
        transmitted on this linkset, DPC and OPC
        combination. This is the 64 bit version of
        cSpAccSnmmSentBytes   ."
    ::= { cSpAccountingTableEntry 19 }

cSpAccSntmRcvdPackets OBJECT-TYPE
    SYNTAX Counter
--  Units
--    packets
    ACCESS read-only
    STATUS mandatory
    DESCRIPTION
        "Count of Signalling Network Testing and maintenance
        (MTN) packets received on this linkset, DPC and OPC
        combination."
    ::= { cSpAccountingTableEntry 20 }

cSpAccHCSntmRcvdPackets OBJECT-TYPE
    SYNTAX --?? syntax is not convertable to SMIv1
           Counter
--  Units
--    packets
    ACCESS read-only
    STATUS mandatory
    DESCRIPTION
        "Count of Signalling Network Testing and maintenance
        (MTN) packets received on this linkset, DPC and OPC
        combination. This is the 64 bit version of
        cSpAccSntmRcvdPackets    ."
    ::= { cSpAccountingTableEntry 21 }

cSpAccSntmRcvdBytes OBJECT-TYPE
    SYNTAX Counter
--  Units
--    bytes
    ACCESS read-only
    STATUS mandatory
    DESCRIPTION
        "Count of Signalling Network Testing and maintenance
        (MTN) bytes received on this linkset, DPC and OPC
        combination."
    ::= { cSpAccountingTableEntry 22 }

cSpAccHCSntmRcvdBytes OBJECT-TYPE
    SYNTAX --?? syntax is not convertable to SMIv1
           Counter
--  Units
--    bytes
    ACCESS read-only
    STATUS mandatory
    DESCRIPTION
        "Count of Signalling Network Testing and maintenance
        (MTN) bytes received on this linkset, DPC and OPC
        combination. This is the 64 bit version of
        cSpAccSntmRcvdBytes    ."
    ::= { cSpAccountingTableEntry 23 }

cSpAccSntmSentPackets OBJECT-TYPE
    SYNTAX Counter
--  Units
--    packets
    ACCESS read-only
    STATUS mandatory
    DESCRIPTION
        "Count of Signalling Network Testing and maintenance
        (MTN) packets transmitted on this linkset, DPC and OPC
        combination."
    ::= { cSpAccountingTableEntry 24 }

cSpAccHCSntmSentPackets OBJECT-TYPE
    SYNTAX --?? syntax is not convertable to SMIv1
           Counter
--  Units
--    packets
    ACCESS read-only
    STATUS mandatory
    DESCRIPTION
        "Count of Signalling Network Testing and maintenance
        (MTN) packets transmitted on this linkset, DPC and OPC
        combination. This is the 64 bit version of
        cSpAccSntmSentPackets   ."
    ::= { cSpAccountingTableEntry 25 }

cSpAccSntmSentBytes OBJECT-TYPE
    SYNTAX Counter
--  Units
--    bytes
    ACCESS read-only
    STATUS mandatory
    DESCRIPTION
        "Count of Signalling Network Testing and maintenance
        (MTN) bytes transmitted on this linkset, DPC and OPC
        combination."
    ::= { cSpAccountingTableEntry 26 }

cSpAccHCSntmSentBytes OBJECT-TYPE
    SYNTAX --?? syntax is not convertable to SMIv1
           Counter
--  Units
--    bytes
    ACCESS read-only
    STATUS mandatory
    DESCRIPTION
        "Count of Signalling Network Testing and maintenance
        (MTN) bytes transmitted on this linkset, DPC and OPC
        combination. This is the 64 bit version of
        cSpAccSntmSentBytes   ."
    ::= { cSpAccountingTableEntry 27 }

cSpAccSpare2RcvdPackets OBJECT-TYPE
    SYNTAX Counter
--  Units
--    packets
    ACCESS read-only
    STATUS mandatory
    DESCRIPTION
        "Count of packets with Service Indicator value 2
        received on this linkset, DPC and OPC combination."
    ::= { cSpAccountingTableEntry 28 }

cSpAccHCSpare2RcvdPackets OBJECT-TYPE
    SYNTAX --?? syntax is not convertable to SMIv1
           Counter
--  Units
--    packets
    ACCESS read-only
    STATUS mandatory
    DESCRIPTION
        "Count of packets with Service Indicator value 2
        received on this linkset, DPC and OPC combination.
        This is the 64 bit version of
        cSpAccSpare2RcvdPackets    ."
    ::= { cSpAccountingTableEntry 29 }

cSpAccSpare2RcvdBytes OBJECT-TYPE
    SYNTAX Counter
--  Units
--    bytes
    ACCESS read-only
    STATUS mandatory
    DESCRIPTION
        "Count of bytes with Service Indicator value 2
        received on this linkset, DPC and OPC combination."
    ::= { cSpAccountingTableEntry 30 }

cSpAccHCSpare2RcvdBytes OBJECT-TYPE
    SYNTAX --?? syntax is not convertable to SMIv1
           Counter
--  Units
--    bytes
    ACCESS read-only
    STATUS mandatory
    DESCRIPTION
        "Count of bytes with Service Indicator value 2
        received on this linkset, DPC and OPC combination.
        This is the 64 bit version of
        cSpAccSpare2RcvdBytes    ."
    ::= { cSpAccountingTableEntry 31 }

cSpAccSpare2SentPackets OBJECT-TYPE
    SYNTAX Counter
--  Units
--    packets
    ACCESS read-only
    STATUS mandatory
    DESCRIPTION
        "Count of packets with Service Indicator value 2
        transmitted on this linkset, DPC and OPC combination."
    ::= { cSpAccountingTableEntry 32 }

cSpAccHCSpare2SentPackets OBJECT-TYPE
    SYNTAX --?? syntax is not convertable to SMIv1
           Counter
--  Units
--    packets
    ACCESS read-only
    STATUS mandatory
    DESCRIPTION
        "Count of packets with Service Indicator value 2
        transmitted on this linkset, DPC and OPC combination.
        This is the 64 bit version of
        cSpAccSpare2SentPackets   ."
    ::= { cSpAccountingTableEntry 33 }

cSpAccSpare2SentBytes OBJECT-TYPE
    SYNTAX Counter
--  Units
--    bytes
    ACCESS read-only
    STATUS mandatory
    DESCRIPTION
        "Count of bytes with Service Indicator value 2
        transmitted on this linkset, DPC and OPC combination."
    ::= { cSpAccountingTableEntry 34 }

cSpAccHCSpare2SentBytes OBJECT-TYPE
    SYNTAX --?? syntax is not convertable to SMIv1
           Counter
--  Units
--    bytes
    ACCESS read-only
    STATUS mandatory
    DESCRIPTION
        "Count of bytes with Service Indicator value 2
        transmitted on this linkset, DPC and OPC combination.
        This is the 64 bit version of
        cSpAccSpare2SentBytes   ."
    ::= { cSpAccountingTableEntry 35 }

cSpAccSccpRcvdPackets OBJECT-TYPE
    SYNTAX Counter
--  Units
--    packets
    ACCESS read-only
    STATUS mandatory
    DESCRIPTION
        "Count of Signaling Connection Control Part (SCCP)
        packets received on this linkset, DPC and OPC
        combination."
    ::= { cSpAccountingTableEntry 36 }

cSpAccHCSccpRcvdPackets OBJECT-TYPE
    SYNTAX --?? syntax is not convertable to SMIv1
           Counter
--  Units
--    packets
    ACCESS read-only
    STATUS mandatory
    DESCRIPTION
        "Count of Signaling Connection Control Part (SCCP)
        packets received on this linkset, DPC and OPC
        combination. This is the 64 bit version of
        cSpAccSccpRcvdPackets    ."
    ::= { cSpAccountingTableEntry 37 }

cSpAccSccpRcvdBytes OBJECT-TYPE
    SYNTAX Counter
--  Units
--    bytes
    ACCESS read-only
    STATUS mandatory
    DESCRIPTION
        "Count of Signaling Connection Control Part (SCCP)
        bytes received on this linkset, DPC and OPC
        combination."
    ::= { cSpAccountingTableEntry 38 }

cSpAccHCSccpRcvdBytes OBJECT-TYPE
    SYNTAX --?? syntax is not convertable to SMIv1
           Counter
--  Units
--    bytes
    ACCESS read-only
    STATUS mandatory
    DESCRIPTION
        "Count of Signaling Connection Control Part (SCCP)
        bytes received on this linkset, DPC and OPC
        combination. This is the 64 bit version of
        cSpAccSccpRcvdBytes    ."
    ::= { cSpAccountingTableEntry 39 }

cSpAccSccpSentPackets OBJECT-TYPE
    SYNTAX Counter
--  Units
--    packets
    ACCESS read-only
    STATUS mandatory
    DESCRIPTION
        "Count of Signaling Connection Control Part (SCCP)
        packets transmitted on this linkset, DPC and OPC
        combination."
    ::= { cSpAccountingTableEntry 40 }

cSpAccHCSccpSentPackets OBJECT-TYPE
    SYNTAX --?? syntax is not convertable to SMIv1
           Counter
--  Units
--    packets
    ACCESS read-only
    STATUS mandatory
    DESCRIPTION
        "Count of Signaling Connection Control Part (SCCP)
        packets transmitted on this linkset, DPC and OPC
        combination. This is the 64 bit version of
        cSpAccSccpSentPackets   ."
    ::= { cSpAccountingTableEntry 41 }

cSpAccSccpSentBytes OBJECT-TYPE
    SYNTAX Counter
--  Units
--    bytes
    ACCESS read-only
    STATUS mandatory
    DESCRIPTION
        "Count of Signaling Connection Control Part (SCCP)
        bytes transmitted on this linkset, DPC and OPC
        combination."
    ::= { cSpAccountingTableEntry 42 }

cSpAccHCSccpSentBytes OBJECT-TYPE
    SYNTAX --?? syntax is not convertable to SMIv1
           Counter
--  Units
--    bytes
    ACCESS read-only
    STATUS mandatory
    DESCRIPTION
        "Count of Signaling Connection Control Part (SCCP)
        bytes transmitted on this linkset, DPC and OPC
        combination. This is the 64 bit version of
        cSpAccSccpSentBytes   ."
    ::= { cSpAccountingTableEntry 43 }

cSpAccTupRcvdPackets OBJECT-TYPE
    SYNTAX Counter
--  Units
--    packets
    ACCESS read-only
    STATUS mandatory
    DESCRIPTION
        "Count of Telephone User Part (TUP) packets received
        on this linkset, DPC and OPC combination."
    ::= { cSpAccountingTableEntry 44 }

cSpAccHCTupRcvdPackets OBJECT-TYPE
    SYNTAX --?? syntax is not convertable to SMIv1
           Counter
--  Units
--    packets
    ACCESS read-only
    STATUS mandatory
    DESCRIPTION
        "Count of Telephone User Part (TUP) packets received
        on this linkset, DPC and OPC combination. This is the
        64 bit version of cSpAccTupRcvdPackets    ."
    ::= { cSpAccountingTableEntry 45 }

cSpAccTupRcvdBytes OBJECT-TYPE
    SYNTAX Counter
--  Units
--    bytes
    ACCESS read-only
    STATUS mandatory
    DESCRIPTION
        "Count of Telephone User Part (TUP) bytes received on
        this linkset, DPC and OPC combination."
    ::= { cSpAccountingTableEntry 46 }

cSpAccHCTupRcvdBytes OBJECT-TYPE
    SYNTAX --?? syntax is not convertable to SMIv1
           Counter
--  Units
--    bytes
    ACCESS read-only
    STATUS mandatory
    DESCRIPTION
        "Count of Telephone User Part (TUP) bytes received on
        this linkset, DPC and OPC combination. This is the 64
        bit version of cSpAccTupRcvdBytes    ."
    ::= { cSpAccountingTableEntry 47 }

cSpAccTupSentPackets OBJECT-TYPE
    SYNTAX Counter
--  Units
--    packets
    ACCESS read-only
    STATUS mandatory
    DESCRIPTION
        "Count of Telephone User Part (TUP) packets
        transmitted on this linkset, DPC and OPC combination."
    ::= { cSpAccountingTableEntry 48 }

cSpAccHCTupSentPackets OBJECT-TYPE
    SYNTAX --?? syntax is not convertable to SMIv1
           Counter
--  Units
--    packets
    ACCESS read-only
    STATUS mandatory
    DESCRIPTION
        "Count of Telephone User Part (TUP) packets
        transmitted on this linkset, DPC and OPC
        combination. This is the 64 bit version of
        cSpAccTupSentPackets   ."
    ::= { cSpAccountingTableEntry 49 }

cSpAccTupSentBytes OBJECT-TYPE
    SYNTAX Counter
--  Units
--    bytes
    ACCESS read-only
    STATUS mandatory
    DESCRIPTION
        "Count of Telephone User Part (TUP) bytes transmitted
        on this linkset, DPC and OPC combination."
    ::= { cSpAccountingTableEntry 50 }

cSpAccHCTupSentBytes OBJECT-TYPE
    SYNTAX --?? syntax is not convertable to SMIv1
           Counter
--  Units
--    bytes
    ACCESS read-only
    STATUS mandatory
    DESCRIPTION
        "Count of Telephone User Part (TUP) bytes transmitted
        on this linkset, DPC and OPC combination. This is the
        64 bit version of cSpAccTupSentBytes   ."
    ::= { cSpAccountingTableEntry 51 }

cSpAccIsupRcvdPackets OBJECT-TYPE
    SYNTAX Counter
--  Units
--    packets
    ACCESS read-only
    STATUS mandatory
    DESCRIPTION
        "Count of ISDN User Part (ISUP) packets received on
        this linkset, DPC and OPC combination."
    ::= { cSpAccountingTableEntry 52 }

cSpAccHCIsupRcvdPackets OBJECT-TYPE
    SYNTAX --?? syntax is not convertable to SMIv1
           Counter
--  Units
--    packets
    ACCESS read-only
    STATUS mandatory
    DESCRIPTION
        "Count of ISDN User Part (ISUP) packets received on
        this linkset, DPC and OPC combination. This is the 64
        bit version of cSpAccIsupRcvdPackets    ."
    ::= { cSpAccountingTableEntry 53 }

cSpAccIsupRcvdBytes OBJECT-TYPE
    SYNTAX Counter
--  Units
--    bytes
    ACCESS read-only
    STATUS mandatory
    DESCRIPTION
        "Count of ISDN User Part (ISUP) bytes received on this
        linkset, DPC and OPC combination."
    ::= { cSpAccountingTableEntry 54 }

cSpAccHCIsupRcvdBytes OBJECT-TYPE
    SYNTAX --?? syntax is not convertable to SMIv1
           Counter
--  Units
--    bytes
    ACCESS read-only
    STATUS mandatory
    DESCRIPTION
        "Count of ISDN User Part (ISUP) bytes received on this
        linkset, DPC and OPC combination. This is the 64 bit
        version of cSpAccIsupRcvdBytes    ."
    ::= { cSpAccountingTableEntry 55 }

cSpAccIsupSentPackets OBJECT-TYPE
    SYNTAX Counter
--  Units
--    packets
    ACCESS read-only
    STATUS mandatory
    DESCRIPTION
        "Count of ISDN User Part (ISUP) packets transmitted on
        this linkset, DPC and OPC combination."
    ::= { cSpAccountingTableEntry 56 }

cSpAccHCIsupSentPackets OBJECT-TYPE
    SYNTAX --?? syntax is not convertable to SMIv1
           Counter
--  Units
--    packets
    ACCESS read-only
    STATUS mandatory
    DESCRIPTION
        "Count of ISDN User Part (ISUP) packets transmitted on
        this linkset, DPC and OPC combination. This is the 64
        bit version of cSpAccIsupSentPackets   ."
    ::= { cSpAccountingTableEntry 57 }

cSpAccIsupSentBytes OBJECT-TYPE
    SYNTAX Counter
--  Units
--    bytes
    ACCESS read-only
    STATUS mandatory
    DESCRIPTION
        "Count of ISDN User Part (ISUP) bytes transmitted on
        this linkset, DPC and OPC combination."
    ::= { cSpAccountingTableEntry 58 }

cSpAccHCIsupSentBytes OBJECT-TYPE
    SYNTAX --?? syntax is not convertable to SMIv1
           Counter
--  Units
--    bytes
    ACCESS read-only
    STATUS mandatory
    DESCRIPTION
        "Count of ISDN User Part (ISUP) bytes transmitted on
        this linkset, DPC and OPC combination. This is the 64
        bit version of cSpAccIsupSentBytes   ."
    ::= { cSpAccountingTableEntry 59 }

cSpAccDupcRcvdPackets OBJECT-TYPE
    SYNTAX Counter
--  Units
--    packets
    ACCESS read-only
    STATUS mandatory
    DESCRIPTION
        "Count of Data User Part (call and circuit-related
        messages) - Dupc packets received on this linkset, DPC
        and OPC combination."
    ::= { cSpAccountingTableEntry 60 }

cSpAccHCDupcRcvdPackets OBJECT-TYPE
    SYNTAX --?? syntax is not convertable to SMIv1
           Counter
--  Units
--    packets
    ACCESS read-only
    STATUS mandatory
    DESCRIPTION
        "Count of Data User Part (call and circuit-related
        messages) - Dupc packets received on this linkset, DPC
        and OPC combination. This is the 64 bit version of
        cSpAccDupcRcvdPackets    ."
    ::= { cSpAccountingTableEntry 61 }

cSpAccDupcRcvdBytes OBJECT-TYPE
    SYNTAX Counter
--  Units
--    bytes
    ACCESS read-only
    STATUS mandatory
    DESCRIPTION
        "Count of Dupc bytes received on this linkset, DPC and
        OPC combination."
    ::= { cSpAccountingTableEntry 62 }

cSpAccHCDupcRcvdBytes OBJECT-TYPE
    SYNTAX --?? syntax is not convertable to SMIv1
           Counter
--  Units
--    bytes
    ACCESS read-only
    STATUS mandatory
    DESCRIPTION
        "Count of Dupc bytes received on this linkset, DPC and
        OPC combination. This is the 64 bit version of
        cSpAccDupcRcvdBytes    ."
    ::= { cSpAccountingTableEntry 63 }

cSpAccDupcSentPackets OBJECT-TYPE
    SYNTAX Counter
--  Units
--    packets
    ACCESS read-only
    STATUS mandatory
    DESCRIPTION
        "Count of Dupc packets transmitted on this linkset,
        DPC and OPC combination."
    ::= { cSpAccountingTableEntry 64 }

cSpAccHCDupcSentPackets OBJECT-TYPE
    SYNTAX --?? syntax is not convertable to SMIv1
           Counter
--  Units
--    packets
    ACCESS read-only
    STATUS mandatory
    DESCRIPTION
        "Count of Dupc packets transmitted on this linkset,
        DPC and OPC combination. This is the 64 bit version of
        cSpAccDupcSentPackets   ."
    ::= { cSpAccountingTableEntry 65 }

cSpAccDupcSentBytes OBJECT-TYPE
    SYNTAX Counter
--  Units
--    bytes
    ACCESS read-only
    STATUS mandatory
    DESCRIPTION
        "Count of Dupc bytes transmitted on this linkset, DPC
        and OPC combination."
    ::= { cSpAccountingTableEntry 66 }

cSpAccHCDupcSentBytes OBJECT-TYPE
    SYNTAX --?? syntax is not convertable to SMIv1
           Counter
--  Units
--    bytes
    ACCESS read-only
    STATUS mandatory
    DESCRIPTION
        "Count of Dupc bytes transmitted on this linkset, DPC
        and OPC combination. This is the 64 bit version of
        cSpAccDupcSentBytes   ."
    ::= { cSpAccountingTableEntry 67 }

cSpAccDupfRcvdPackets OBJECT-TYPE
    SYNTAX Counter
--  Units
--    packets
    ACCESS read-only
    STATUS mandatory
    DESCRIPTION
        "Count of Data User Part (facility registration and
        cancellation messages) - Dupf packets received on this
        linkset, DPC and OPC combination."
    ::= { cSpAccountingTableEntry 68 }

cSpAccHCDupfRcvdPackets OBJECT-TYPE
    SYNTAX --?? syntax is not convertable to SMIv1
           Counter
--  Units
--    packets
    ACCESS read-only
    STATUS mandatory
    DESCRIPTION
        "Count of Data User Part (facility registration and
        cancellation messages) - Dupf packets received on this
        linkset, DPC and OPC combination. This is the 64 bit
        version of cSpAccDupfRcvdPackets    ."
    ::= { cSpAccountingTableEntry 69 }

cSpAccDupfRcvdBytes OBJECT-TYPE
    SYNTAX Counter
--  Units
--    bytes
    ACCESS read-only
    STATUS mandatory
    DESCRIPTION
        "Count of Dupf bytes received on this linkset, DPC and
        OPC combination."
    ::= { cSpAccountingTableEntry 70 }

cSpAccHCDupfRcvdBytes OBJECT-TYPE
    SYNTAX --?? syntax is not convertable to SMIv1
           Counter
--  Units
--    bytes
    ACCESS read-only
    STATUS mandatory
    DESCRIPTION
        "Count of Dupf bytes received on this linkset, DPC and
        OPC combination. This is the 64 bit version of
        cSpAccDupfRcvdBytes    ."
    ::= { cSpAccountingTableEntry 71 }

cSpAccDupfSentPackets OBJECT-TYPE
    SYNTAX Counter
--  Units
--    packets
    ACCESS read-only
    STATUS mandatory
    DESCRIPTION
        "Count of Dupf packets transmitted on this linkset,
        DPC and OPC combination."
    ::= { cSpAccountingTableEntry 72 }

cSpAccHCDupfSentPackets OBJECT-TYPE
    SYNTAX --?? syntax is not convertable to SMIv1
           Counter
--  Units
--    packets
    ACCESS read-only
    STATUS mandatory
    DESCRIPTION
        "Count of Dupf packets transmitted on this linkset,
        DPC and OPC combination. This is the 64 bit version of
        cSpAccDupfSentPackets   ."
    ::= { cSpAccountingTableEntry 73 }

cSpAccDupfSentBytes OBJECT-TYPE
    SYNTAX Counter
--  Units
--    bytes
    ACCESS read-only
    STATUS mandatory
    DESCRIPTION
        "Count of Dupf bytes transmitted on this linkset, DPC
        and OPC combination."
    ::= { cSpAccountingTableEntry 74 }

cSpAccHCDupfSentBytes OBJECT-TYPE
    SYNTAX --?? syntax is not convertable to SMIv1
           Counter
--  Units
--    bytes
    ACCESS read-only
    STATUS mandatory
    DESCRIPTION
        "Count of Dupf bytes transmitted on this linkset, DPC
        and OPC combination. This is the 64 bit version of
        cSpAccDupfSentBytes   ."
    ::= { cSpAccountingTableEntry 75 }

cSpAccMtupRcvdPackets OBJECT-TYPE
    SYNTAX Counter
--  Units
--    packets
    ACCESS read-only
    STATUS mandatory
    DESCRIPTION
        "Count of Reserved for MTP Testing User Part (Mtup)
        packets received on this linkset, DPC and OPC
        combination."
    ::= { cSpAccountingTableEntry 76 }

cSpAccHCMtupRcvdPackets OBJECT-TYPE
    SYNTAX --?? syntax is not convertable to SMIv1
           Counter
--  Units
--    packets
    ACCESS read-only
    STATUS mandatory
    DESCRIPTION
        "Count of Reserved for MTP Testing User Part (Mtup)
        packets received on this linkset, DPC and OPC
        combination. This is the 64 bit version of
        cSpAccMtupRcvdPackets    ."
    ::= { cSpAccountingTableEntry 77 }

cSpAccMtupRcvdBytes OBJECT-TYPE
    SYNTAX Counter
--  Units
--    bytes
    ACCESS read-only
    STATUS mandatory
    DESCRIPTION
        "Count of Reserved for MTP Testing User Part (Mtup)
        bytes received on this linkset, DPC and OPC
        combination."
    ::= { cSpAccountingTableEntry 78 }

cSpAccHCMtupRcvdBytes OBJECT-TYPE
    SYNTAX --?? syntax is not convertable to SMIv1
           Counter
--  Units
--    bytes
    ACCESS read-only
    STATUS mandatory
    DESCRIPTION
        "Count of Reserved for MTP Testing User Part (Mtup)
        bytes received on this linkset, DPC and OPC
        combination. This is the 64 bit version of
        cSpAccMtupRcvdBytes    ."
    ::= { cSpAccountingTableEntry 79 }

cSpAccMtupSentPackets OBJECT-TYPE
    SYNTAX Counter
--  Units
--    packets
    ACCESS read-only
    STATUS mandatory
    DESCRIPTION
        "Count of Reserved for MTP Testing User Part (Mtup)
        packets transmitted on this linkset, DPC and OPC
        combination."
    ::= { cSpAccountingTableEntry 80 }

cSpAccHCMtupSentPackets OBJECT-TYPE
    SYNTAX --?? syntax is not convertable to SMIv1
           Counter
--  Units
--    packets
    ACCESS read-only
    STATUS mandatory
    DESCRIPTION
        "Count of Reserved for MTP Testing User Part (Mtup)
        packets transmitted on this linkset, DPC and OPC
        combination. This is the 64 bit version of
        cSpAccMtupSentPackets   ."
    ::= { cSpAccountingTableEntry 81 }

cSpAccMtupSentBytes OBJECT-TYPE
    SYNTAX Counter
--  Units
--    bytes
    ACCESS read-only
    STATUS mandatory
    DESCRIPTION
        "Count of Reserved for MTP Testing User Part (Mtup)
        bytes transmitted on this linkset, DPC and OPC
        combination."
    ::= { cSpAccountingTableEntry 82 }

cSpAccHCMtupSentBytes OBJECT-TYPE
    SYNTAX --?? syntax is not convertable to SMIv1
           Counter
--  Units
--    bytes
    ACCESS read-only
    STATUS mandatory
    DESCRIPTION
        "Count of Reserved for MTP Testing User Part (Mtup)
        bytes transmitted on this linkset, DPC and OPC
        combination. This is the 64 bit version of
        cSpAccMtupSentBytes   ."
    ::= { cSpAccountingTableEntry 83 }

cSpAccBisupRcvdPackets OBJECT-TYPE
    SYNTAX Counter
--  Units
--    packets
    ACCESS read-only
    STATUS mandatory
    DESCRIPTION
        "Count of Broadband ISDN User Part (Bisup) packets
        received on this linkset, DPC and OPC combination."
    ::= { cSpAccountingTableEntry 84 }

cSpAccHCBisupRcvdPackets OBJECT-TYPE
    SYNTAX --?? syntax is not convertable to SMIv1
           Counter
--  Units
--    packets
    ACCESS read-only
    STATUS mandatory
    DESCRIPTION
        "Count of Broadband ISDN User Part (Bisup) packets
        received on this linkset, DPC and OPC
        combination. This is the 64 bit version of
        cSpAccBisupRcvdPackets    ."
    ::= { cSpAccountingTableEntry 85 }

cSpAccBisupRcvdBytes OBJECT-TYPE
    SYNTAX Counter
--  Units
--    bytes
    ACCESS read-only
    STATUS mandatory
    DESCRIPTION
        "Count of Broadband ISDN User Part (Bisup) bytes
        received on this linkset, DPC and OPC combination."
    ::= { cSpAccountingTableEntry 86 }

cSpAccHCBisupRcvdBytes OBJECT-TYPE
    SYNTAX --?? syntax is not convertable to SMIv1
           Counter
--  Units
--    bytes
    ACCESS read-only
    STATUS mandatory
    DESCRIPTION
        "Count of Broadband ISDN User Part (Bisup) bytes
        received on this linkset, DPC and OPC
        combination. This is the 64 bit version of
        cSpAccBisupRcvdBytes    ."
    ::= { cSpAccountingTableEntry 87 }

cSpAccBisupSentPackets OBJECT-TYPE
    SYNTAX Counter
--  Units
--    packets
    ACCESS read-only
    STATUS mandatory
    DESCRIPTION
        "Count of Broadband ISDN User Part (Bisup) packets
        transmitted on this linkset, DPC and OPC combination."
    ::= { cSpAccountingTableEntry 88 }

cSpAccHCBisupSentPackets OBJECT-TYPE
    SYNTAX --?? syntax is not convertable to SMIv1
           Counter
--  Units
--    packets
    ACCESS read-only
    STATUS mandatory
    DESCRIPTION
        "Count of Broadband ISDN User Part (Bisup) packets
        transmitted on this linkset, DPC and OPC
        combination. This is the 64 bit version of
        cSpAccBisupSentPackets   ."
    ::= { cSpAccountingTableEntry 89 }

cSpAccBisupSentBytes OBJECT-TYPE
    SYNTAX Counter
--  Units
--    bytes
    ACCESS read-only
    STATUS mandatory
    DESCRIPTION
        "Count of Broadband ISDN User Part (Bisup) bytes
        transmitted on this linkset, DPC and OPC combination."
    ::= { cSpAccountingTableEntry 90 }

cSpAccHCBisupSentBytes OBJECT-TYPE
    SYNTAX --?? syntax is not convertable to SMIv1
           Counter
--  Units
--    bytes
    ACCESS read-only
    STATUS mandatory
    DESCRIPTION
        "Count of Broadband ISDN User Part (Bisup) bytes
        transmitted on this linkset, DPC and OPC
        combination. This is the 64 bit version of
        cSpAccBisupSentBytes   ."
    ::= { cSpAccountingTableEntry 91 }

cSpAccSisupRcvdPackets OBJECT-TYPE
    SYNTAX Counter
--  Units
--    packets
    ACCESS read-only
    STATUS mandatory
    DESCRIPTION
        "Count of Satellite ISDN User Part (Sisup) packets
        received on this linkset, DPC and OPC combination."
    ::= { cSpAccountingTableEntry 92 }

cSpAccHCSisupRcvdPackets OBJECT-TYPE
    SYNTAX --?? syntax is not convertable to SMIv1
           Counter
--  Units
--    packets
    ACCESS read-only
    STATUS mandatory
    DESCRIPTION
        "Count of Satellite ISDN User Part (Sisup) packets
        received on this linkset, DPC and OPC
        combination. This is the 64 bit version of
        cSpAccSisupRcvdPackets    ."
    ::= { cSpAccountingTableEntry 93 }

cSpAccSisupRcvdBytes OBJECT-TYPE
    SYNTAX Counter
--  Units
--    bytes
    ACCESS read-only
    STATUS mandatory
    DESCRIPTION
        "Count of Satellite ISDN User Part (Sisup) bytes
        received on this linkset, DPC and OPC combination."
    ::= { cSpAccountingTableEntry 94 }

cSpAccHCSisupRcvdBytes OBJECT-TYPE
    SYNTAX --?? syntax is not convertable to SMIv1
           Counter
--  Units
--    bytes
    ACCESS read-only
    STATUS mandatory
    DESCRIPTION
        "Count of Satellite ISDN User Part (Sisup) bytes
        received on this linkset, DPC and OPC
        combination. This is the 64 bit version of
        cSpAccSisupRcvdBytes    ."
    ::= { cSpAccountingTableEntry 95 }

cSpAccSisupSentPackets OBJECT-TYPE
    SYNTAX Counter
--  Units
--    packets
    ACCESS read-only
    STATUS mandatory
    DESCRIPTION
        "Count of Satellite ISDN User Part (Sisup) packets
        transmitted on this linkset, DPC and OPC combination."
    ::= { cSpAccountingTableEntry 96 }

cSpAccHCSisupSentPackets OBJECT-TYPE
    SYNTAX --?? syntax is not convertable to SMIv1
           Counter
--  Units
--    packets
    ACCESS read-only
    STATUS mandatory
    DESCRIPTION
        "Count of Satellite ISDN User Part (Sisup) packets
        transmitted on this linkset, DPC and OPC
        combination. This is the 64 bit version of
        cSpAccSisupSentPackets   ."
    ::= { cSpAccountingTableEntry 97 }

cSpAccSisupSentBytes OBJECT-TYPE
    SYNTAX Counter
--  Units
--    bytes
    ACCESS read-only
    STATUS mandatory
    DESCRIPTION
        "Count of Satellite ISDN User Part (Sisup) bytes
        transmitted on this linkset, DPC and OPC combination."
    ::= { cSpAccountingTableEntry 98 }

cSpAccHCSisupSentBytes OBJECT-TYPE
    SYNTAX --?? syntax is not convertable to SMIv1
           Counter
--  Units
--    bytes
    ACCESS read-only
    STATUS mandatory
    DESCRIPTION
        "Count of Satellite ISDN User Part (Sisup) bytes
        transmitted on this linkset, DPC and OPC
        combination. This is the 64 bit version of
        cSpAccSisupSentBytes   ."
    ::= { cSpAccountingTableEntry 99 }

cSpAccSpare11RcvdPackets OBJECT-TYPE
    SYNTAX Counter
--  Units
--    packets
    ACCESS read-only
    STATUS mandatory
    DESCRIPTION
        "Count of packets with Service Indicator value 11
        received on this linkset, DPC and OPC combination."
    ::= { cSpAccountingTableEntry 100 }

cSpAccHCSpare11RcvdPackets OBJECT-TYPE
    SYNTAX --?? syntax is not convertable to SMIv1
           Counter
--  Units
--    packets
    ACCESS read-only
    STATUS mandatory
    DESCRIPTION
        "Count of packets with Service Indicator value 11
        received on this linkset, DPC and OPC combination.
        This is the 64 bit version of
        cSpAccSpare11RcvdPackets    ."
    ::= { cSpAccountingTableEntry 101 }

cSpAccSpare11RcvdBytes OBJECT-TYPE
    SYNTAX Counter
--  Units
--    bytes
    ACCESS read-only
    STATUS mandatory
    DESCRIPTION
        "Count of bytes with Service Indicator value 11
        received on this linkset, DPC and OPC combination."
    ::= { cSpAccountingTableEntry 102 }

cSpAccHCSpare11RcvdBytes OBJECT-TYPE
    SYNTAX --?? syntax is not convertable to SMIv1
           Counter
--  Units
--    bytes
    ACCESS read-only
    STATUS mandatory
    DESCRIPTION
        "Count of bytes with Service Indicator value 11
        received on this linkset, DPC and OPC
        combination. This is the 64 bit version of
        cSpAccSpare11RcvdBytes    ."
    ::= { cSpAccountingTableEntry 103 }

cSpAccSpare11SentPackets OBJECT-TYPE
    SYNTAX Counter
--  Units
--    packets
    ACCESS read-only
    STATUS mandatory
    DESCRIPTION
        "Count of packets with Service Indicator value 11
        transmitted on this linkset, DPC and OPC combination."
    ::= { cSpAccountingTableEntry 104 }

cSpAccHCSpare11SentPackets OBJECT-TYPE
    SYNTAX --?? syntax is not convertable to SMIv1
           Counter
--  Units
--    packets
    ACCESS read-only
    STATUS mandatory
    DESCRIPTION
        "Count of packets with Service Indicator value 11
        transmitted on this linkset, DPC and OPC
        combination. This is the 64 bit version of
        cSpAccSpare11SentPackets   ."
    ::= { cSpAccountingTableEntry 105 }

cSpAccSpare11SentBytes OBJECT-TYPE
    SYNTAX Counter
--  Units
--    bytes
    ACCESS read-only
    STATUS mandatory
    DESCRIPTION
        "Count of bytes with Service Indicator value 11
        transmitted on this linkset, DPC and OPC combination."
    ::= { cSpAccountingTableEntry 106 }

cSpAccHCSpare11SentBytes OBJECT-TYPE
    SYNTAX --?? syntax is not convertable to SMIv1
           Counter
--  Units
--    bytes
    ACCESS read-only
    STATUS mandatory
    DESCRIPTION
        "Count of bytes with Service Indicator value 11
        transmitted on this linkset, DPC and OPC combination.
        This is the 64 bit version of
        cSpAccSpare11SentBytes   ."
    ::= { cSpAccountingTableEntry 107 }

cSpAccSpare12RcvdPackets OBJECT-TYPE
    SYNTAX Counter
--  Units
--    packets
    ACCESS read-only
    STATUS mandatory
    DESCRIPTION
        "Count of packets with Service Indicator value 12
        received on this linkset, DPC and OPC combination."
    ::= { cSpAccountingTableEntry 108 }

cSpAccHCSpare12RcvdPackets OBJECT-TYPE
    SYNTAX --?? syntax is not convertable to SMIv1
           Counter
--  Units
--    packets
    ACCESS read-only
    STATUS mandatory
    DESCRIPTION
        "Count of packets with Service Indicator value 12
        received on this linkset, DPC and OPC combination.
        This is the 64 bit version of
        cSpAccSpare12RcvdPackets    ."
    ::= { cSpAccountingTableEntry 109 }

cSpAccSpare12RcvdBytes OBJECT-TYPE
    SYNTAX Counter
--  Units
--    bytes
    ACCESS read-only
    STATUS mandatory
    DESCRIPTION
        "Count of bytes with Service Indicator value 12
        received on this linkset, DPC and OPC combination."
    ::= { cSpAccountingTableEntry 110 }

cSpAccHCSpare12RcvdBytes OBJECT-TYPE
    SYNTAX --?? syntax is not convertable to SMIv1
           Counter
--  Units
--    bytes
    ACCESS read-only
    STATUS mandatory
    DESCRIPTION
        "Count of bytes with Service Indicator value 12
        received on this linkset, DPC and OPC
        combination. This is the 64 bit version of
        cSpAccSpare12RcvdBytes    ."
    ::= { cSpAccountingTableEntry 111 }

cSpAccSpare12SentPackets OBJECT-TYPE
    SYNTAX Counter
--  Units
--    packets
    ACCESS read-only
    STATUS mandatory
    DESCRIPTION
        "Count of packets with Service Indicator value 12
        transmitted on this linkset, DPC and OPC combination."
    ::= { cSpAccountingTableEntry 112 }

cSpAccHCSpare12SentPackets OBJECT-TYPE
    SYNTAX --?? syntax is not convertable to SMIv1
           Counter
--  Units
--    packets
    ACCESS read-only
    STATUS mandatory
    DESCRIPTION
        "Count of packets with Service Indicator value 12
        transmitted on this linkset, DPC and OPC
        combination. This is the 64 bit version of
        cSpAccSpare12SentPackets   ."
    ::= { cSpAccountingTableEntry 113 }

cSpAccSpare12SentBytes OBJECT-TYPE
    SYNTAX Counter
--  Units
--    bytes
    ACCESS read-only
    STATUS mandatory
    DESCRIPTION
        "Count of bytes with Service Indicator value 12
        transmitted on this linkset, DPC and OPC combination."
    ::= { cSpAccountingTableEntry 114 }

cSpAccHCSpare12SentBytes OBJECT-TYPE
    SYNTAX --?? syntax is not convertable to SMIv1
           Counter
--  Units
--    bytes
    ACCESS read-only
    STATUS mandatory
    DESCRIPTION
        "Count of bytes with Service Indicator value 12
        transmitted on this linkset, DPC and OPC combination.
        This is the 64 bit version of
        cSpAccSpare12SentBytes   ."
    ::= { cSpAccountingTableEntry 115 }

cSpAccSpare13RcvdPackets OBJECT-TYPE
    SYNTAX Counter
--  Units
--    packets
    ACCESS read-only
    STATUS mandatory
    DESCRIPTION
        "Count of packets with Service Indicator value 13
        received on this linkset, DPC and OPC combination."
    ::= { cSpAccountingTableEntry 116 }

cSpAccHCSpare13RcvdPackets OBJECT-TYPE
    SYNTAX --?? syntax is not convertable to SMIv1
           Counter
--  Units
--    packets
    ACCESS read-only
    STATUS mandatory
    DESCRIPTION
        "Count of packets with Service Indicator value 13
        received on this linkset, DPC and OPC combination.
        This is the 64 bit version of
        cSpAccSpare13RcvdPackets    ."
    ::= { cSpAccountingTableEntry 117 }

cSpAccSpare13RcvdBytes OBJECT-TYPE
    SYNTAX Counter
--  Units
--    bytes
    ACCESS read-only
    STATUS mandatory
    DESCRIPTION
        "Count of bytes with Service Indicator value 13
        received on this linkset, DPC and OPC combination."
    ::= { cSpAccountingTableEntry 118 }

cSpAccHCSpare13RcvdBytes OBJECT-TYPE
    SYNTAX --?? syntax is not convertable to SMIv1
           Counter
--  Units
--    bytes
    ACCESS read-only
    STATUS mandatory
    DESCRIPTION
        "Count of bytes with Service Indicator value 13
        received on this linkset, DPC and OPC
        combination. This is the 64 bit version of
        cSpAccSpare13RcvdBytes    ."
    ::= { cSpAccountingTableEntry 119 }

cSpAccSpare13SentPackets OBJECT-TYPE
    SYNTAX Counter
--  Units
--    packets
    ACCESS read-only
    STATUS mandatory
    DESCRIPTION
        "Count of packets with Service Indicator value 13
        transmitted on this linkset, DPC and OPC combination."
    ::= { cSpAccountingTableEntry 120 }

cSpAccHCSpare13SentPackets OBJECT-TYPE
    SYNTAX --?? syntax is not convertable to SMIv1
           Counter
--  Units
--    packets
    ACCESS read-only
    STATUS mandatory
    DESCRIPTION
        "Count of packets with Service Indicator value 13
        transmitted on this linkset, DPC and OPC
        combination. This is the 64 bit version of
        cSpAccSpare13SentPackets   ."
    ::= { cSpAccountingTableEntry 121 }

cSpAccSpare13SentBytes OBJECT-TYPE
    SYNTAX Counter
--  Units
--    bytes
    ACCESS read-only
    STATUS mandatory
    DESCRIPTION
        "Count of bytes with Service Indicator value 13
        transmitted on this linkset, DPC and OPC combination."
    ::= { cSpAccountingTableEntry 122 }

cSpAccHCSpare13SentBytes OBJECT-TYPE
    SYNTAX --?? syntax is not convertable to SMIv1
           Counter
--  Units
--    bytes
    ACCESS read-only
    STATUS mandatory
    DESCRIPTION
        "Count of bytes with Service Indicator value 13
        transmitted on this linkset, DPC and OPC combination.
        This is the 64 bit version of
        cSpAccSpare13SentBytes   ."
    ::= { cSpAccountingTableEntry 123 }

cSpAccSpare14RcvdPackets OBJECT-TYPE
    SYNTAX Counter
--  Units
--    packets
    ACCESS read-only
    STATUS mandatory
    DESCRIPTION
        "Count of packets with Service Indicator value 14
        received on this linkset, DPC and OPC combination."
    ::= { cSpAccountingTableEntry 124 }

cSpAccHCSpare14RcvdPackets OBJECT-TYPE
    SYNTAX --?? syntax is not convertable to SMIv1
           Counter
--  Units
--    packets
    ACCESS read-only
    STATUS mandatory
    DESCRIPTION
        "Count of packets with Service Indicator value 14
        received on this linkset, DPC and OPC combination.
        This is the 64 bit version of
        cSpAccSpare14RcvdPackets    ."
    ::= { cSpAccountingTableEntry 125 }

cSpAccSpare14RcvdBytes OBJECT-TYPE
    SYNTAX Counter
--  Units
--    bytes
    ACCESS read-only
    STATUS mandatory
    DESCRIPTION
        "Count of bytes with Service Indicator value 14
        received on this linkset, DPC and OPC combination."
    ::= { cSpAccountingTableEntry 126 }

cSpAccHCSpare14RcvdBytes OBJECT-TYPE
    SYNTAX --?? syntax is not convertable to SMIv1
           Counter
--  Units
--    bytes
    ACCESS read-only
    STATUS mandatory
    DESCRIPTION
        "Count of bytes with Service Indicator value 14
        received on this linkset, DPC and OPC
        combination. This is the 64 bit version of
        cSpAccSpare14RcvdBytes    ."
    ::= { cSpAccountingTableEntry 127 }

cSpAccSpare14SentPackets OBJECT-TYPE
    SYNTAX Counter
--  Units
--    packets
    ACCESS read-only
    STATUS mandatory
    DESCRIPTION
        "Count of packets with Service Indicator value 14
        transmitted on this linkset, DPC and OPC combination."
    ::= { cSpAccountingTableEntry 128 }

cSpAccHCSpare14SentPackets OBJECT-TYPE
    SYNTAX --?? syntax is not convertable to SMIv1
           Counter
--  Units
--    packets
    ACCESS read-only
    STATUS mandatory
    DESCRIPTION
        "Count of packets with Service Indicator value 14
        transmitted on this linkset, DPC and OPC
        combination. This is the 64 bit version of
        cSpAccSpare14SentPackets   ."
    ::= { cSpAccountingTableEntry 129 }

cSpAccSpare14SentBytes OBJECT-TYPE
    SYNTAX Counter
--  Units
--    bytes
    ACCESS read-only
    STATUS mandatory
    DESCRIPTION
        "Count of bytes with Service Indicator value 14
        transmitted on this linkset, DPC and OPC combination."
    ::= { cSpAccountingTableEntry 130 }

cSpAccHCSpare14SentBytes OBJECT-TYPE
    SYNTAX --?? syntax is not convertable to SMIv1
           Counter
--  Units
--    bytes
    ACCESS read-only
    STATUS mandatory
    DESCRIPTION
        "Count of bytes with Service Indicator value 15
        transmitted on this linkset, DPC and OPC combination.
        This is the 64 bit version of
        cSpAccSpare15SentBytes   ."
    ::= { cSpAccountingTableEntry 131 }

cSpAccSpare15RcvdPackets OBJECT-TYPE
    SYNTAX Counter
--  Units
--    packets
    ACCESS read-only
    STATUS mandatory
    DESCRIPTION
        "Count of packets with Service Indicator value 15
        received on this linkset, DPC and OPC combination."
    ::= { cSpAccountingTableEntry 132 }

cSpAccHCSpare15RcvdPackets OBJECT-TYPE
    SYNTAX --?? syntax is not convertable to SMIv1
           Counter
--  Units
--    packets
    ACCESS read-only
    STATUS mandatory
    DESCRIPTION
        "Count of packets with Service Indicator value 15
        received on this linkset, DPC and OPC combination.
        This is the 64 bit version of
        cSpAccSpare15RcvdPackets    ."
    ::= { cSpAccountingTableEntry 133 }

cSpAccSpare15RcvdBytes OBJECT-TYPE
    SYNTAX Counter
--  Units
--    bytes
    ACCESS read-only
    STATUS mandatory
    DESCRIPTION
        "Count of bytes with Service Indicator value 15
        received on this linkset, DPC and OPC combination."
    ::= { cSpAccountingTableEntry 134 }

cSpAccHCSpare15RcvdBytes OBJECT-TYPE
    SYNTAX --?? syntax is not convertable to SMIv1
           Counter
--  Units
--    bytes
    ACCESS read-only
    STATUS mandatory
    DESCRIPTION
        "Count of bytes with Service Indicator value 15
        received on this linkset, DPC and OPC
        combination. This is the 64 bit version of
        cSpAccSpare15RcvdBytes    ."
    ::= { cSpAccountingTableEntry 135 }

cSpAccSpare15SentPackets OBJECT-TYPE
    SYNTAX Counter
--  Units
--    packets
    ACCESS read-only
    STATUS mandatory
    DESCRIPTION
        "Count of packets with Service Indicator value 15
        transmitted on this linkset, DPC and OPC combination."
    ::= { cSpAccountingTableEntry 136 }

cSpAccHCSpare15SentPackets OBJECT-TYPE
    SYNTAX --?? syntax is not convertable to SMIv1
           Counter
--  Units
--    packets
    ACCESS read-only
    STATUS mandatory
    DESCRIPTION
        "Count of packets with Service Indicator value 15
        transmitted on this linkset, DPC and OPC
        combination. This is the 64 bit version of
        cSpAccSpare15SentPackets   ."
    ::= { cSpAccountingTableEntry 137 }

cSpAccSpare15SentBytes OBJECT-TYPE
    SYNTAX Counter
--  Units
--    bytes
    ACCESS read-only
    STATUS mandatory
    DESCRIPTION
        "Count of bytes with Service Indicator value 15
        transmitted on this linkset, DPC and OPC combination."
    ::= { cSpAccountingTableEntry 138 }

cSpAccHCSpare15SentBytes OBJECT-TYPE
    SYNTAX --?? syntax is not convertable to SMIv1
           Counter
--  Units
--    bytes
    ACCESS read-only
    STATUS mandatory
    DESCRIPTION
        "Count of bytes with Service Indicator value 15
        transmitted on this linkset, DPC and OPC combination.
        This is the 64 bit version of
        cSpAccSpare15SentBytes   ."
    ::= { cSpAccountingTableEntry 139 }

cSpLsStateChangeNotifEnabled OBJECT-TYPE
    SYNTAX TruthValue
--    Rsyntax INTEGER {
--        true(1),
--        false(2)
--        }
    ACCESS read-write
    STATUS mandatory
    DESCRIPTION
        "The SP linkset notification truth value.
        'true'  Indicates that ciscoSpLinksetStateChange
                notification is to be generated when the state
                changes. That is, the notification generation 
                is enabled.
        'false' Indicates that ciscoSpLinksetStateChange
                notification generation is disabled."
    DEFVAL { true }
    ::= { cSpNotificationsEnable 1 }

cSpLnkStateChangeNotifEnabled OBJECT-TYPE
    SYNTAX TruthValue
--    Rsyntax INTEGER {
--        true(1),
--        false(2)
--        }
    ACCESS read-write
    STATUS mandatory
    DESCRIPTION
        "The SP link notification truth value.
        'true'  Indicates that ciscoSpLinkStateChange
                notification is to be generated when the state
                changes. That is, the notification generation 
                is enabled.
        'false' Indicates that ciscoSpLinkStateChange
                notification generation is disabled."
    DEFVAL { true }
    ::= { cSpNotificationsEnable 2 }

ciscoSpLinksetStateChange TRAP-TYPE
-- Reverse mappable trap
    ENTERPRISE ciscoSpMIBNotificationPrefix
    VARIABLES {
        cSpLinksetState }
--  Status
--    mandatory
    DESCRIPTION
        "The notification generated when a linkset
        changes to a new state.  The value of
        cSpLinksetState  indicates the new state."
    ::= 1

ciscoSpLinkStateChange TRAP-TYPE
-- Reverse mappable trap
    ENTERPRISE ciscoSpMIBNotificationPrefix
    VARIABLES {
        cSpLinkState }
--  Status
--    mandatory
    DESCRIPTION
        "The notification generated when a SP 
         link changes state. The value of
         cSpLinkState  indicates the new state."
    ::= 2

ciscoSpSwitchGroup OBJECT IDENTIFIER ::= { ciscoSpMIBGroups 1 }
-- OBJECT-GROUP
--  Status
--    mandatory
--  Descr
--    SP main objects.
--  objects
--    cSpPointCode, cSpSs7Variant, cSpMtp2T01, cSpMtp2T02, 
--    cSpMtp2T03, cSpMtp2T4N, cSpMtp2T4E, cSpMtp2T05, cSpMtp2T06, 
--    cSpMtp2T07, cSpMtp2T08, cSpMtp3T01, cSpMtp3T02, cSpMtp3T03, 
--    cSpMtp3T04, cSpMtp3T05, cSpMtp3T06, cSpMtp3T07, cSpMtp3T08, 
--    cSpMtp3T10, cSpMtp3T11, cSpMtp3T12, cSpMtp3T13, cSpMtp3T14, 
--    cSpMtp3T15, cSpMtp3T16, cSpMtp3T17, cSpMtp3T18, cSpMtp3T19, 
--    cSpMtp3T20, cSpMtp3T21, cSpMtp3T22, cSpMtp3T23, cSpMtp3T24, 
--    cSpMtp3T25, cSpMtp3T26, cSpMtp3T27, cSpMtp3T28, cSpMtp3T29, 
--    cSpMtp3T30, cSpMtp3T31, cSpMtp3T32, cSpMtp3T33, cSpMtp3T34

ciscoSpLinksetGroup OBJECT IDENTIFIER ::= { ciscoSpMIBGroups 2 }
-- OBJECT-GROUP
--  Status
--    mandatory
--  Descr
--    SP linkset objects.
--  objects
--    cSpLinksetAdjacentPointCode, cSpLinksetState, 
--    cSpLinksetInboundAcl, cSpLinksetOutboundAcl, 
--    cSpLinksetSnmmRouteTableName, cSpLinksetSntmRouteTableName, 
--    cSpLinksetSpare2RouteTableName, cSpLinksetSccpRouteTableName, 
--    cSpLinksetTupRouteTableName, cSpLinksetIsupRouteTableName, 
--    cSpLinksetDupcRouteTableName, cSpLinksetDupfRouteTableName, 
--    cSpLinksetMtupRouteTableName, cSpLinksetBisupRouteTableName, 
--    cSpLinksetSisupRouteTableName, 
--    cSpLinksetSpare11RouteTableName, 
--    cSpLinksetSpare12RouteTableName, 
--    cSpLinksetSpare13RouteTableName, 
--    cSpLinksetSpare14RouteTableName, 
--    cSpLinksetSpare15RouteTableName, cSpLinksetAccountingEnabled, 
--    cSpLinksetNumLinks, cSpLinksetPacketsSent, 
--    cSpLinksetHCPacketsSent, cSpLinksetPacketsRcvd, 
--    cSpLinksetHCPacketsRcvd, cSpLinksetBytesSent, 
--    cSpLinksetHCBytesSent, cSpLinksetBytesRcvd, 
--    cSpLinksetHCBytesRcvd, cSpLinksetDurationInService, 
--    cSpLinksetDurationOutService, cSpLinksetMtp2T01, 
--    cSpLinksetMtp2T02, cSpLinksetMtp2T03, cSpLinksetMtp2T4N, 
--    cSpLinksetMtp2T4E, cSpLinksetMtp2T05, cSpLinksetMtp2T06, 
--    cSpLinksetMtp2T07, cSpLinksetMtp2T08, cSpLinksetMtp3T01, 
--    cSpLinksetMtp3T02, cSpLinksetMtp3T03, cSpLinksetMtp3T04, 
--    cSpLinksetMtp3T05, cSpLinksetMtp3T06, cSpLinksetMtp3T07, 
--    cSpLinksetMtp3T08, cSpLinksetMtp3T10, cSpLinksetMtp3T11, 
--    cSpLinksetMtp3T12, cSpLinksetMtp3T13, cSpLinksetMtp3T14, 
--    cSpLinksetMtp3T15, cSpLinksetMtp3T16, cSpLinksetMtp3T17, 
--    cSpLinksetMtp3T18, cSpLinksetMtp3T19, cSpLinksetMtp3T20, 
--    cSpLinksetMtp3T21, cSpLinksetMtp3T22, cSpLinksetMtp3T23, 
--    cSpLinksetMtp3T24, cSpLinksetMtp3T25, cSpLinksetMtp3T26, 
--    cSpLinksetMtp3T27, cSpLinksetMtp3T28, cSpLinksetMtp3T29, 
--    cSpLinksetMtp3T30, cSpLinksetMtp3T31, cSpLinksetMtp3T32, 
--    cSpLinksetMtp3T33, cSpLinksetMtp3T34

ciscoSpLinkGroup OBJECT IDENTIFIER ::= { ciscoSpMIBGroups 3 }
-- OBJECT-GROUP
--  Status
--    mandatory
--  Descr
--    SP link objects.
--  objects
--    cSpLinkState, cSpLinkType, cSpLinkifIndex, 
--    cSpLinkSctpAssociation, cSpLinkMtp3PacketsRcvd, 
--    cSpLinkMtp3PacketsSent, cSpLinkHCMtp3PacketsRcvd, 
--    cSpLinkHCMtp3PacketsSent, cSpLinkMtp3BytesRcvd, 
--    cSpLinkMtp3BytesSent, cSpLinkHCMtp3BytesRcvd, 
--    cSpLinkHCMtp3BytesSent, cSpLinkMtp2T01, cSpLinkMtp2T02, 
--    cSpLinkMtp2T03, cSpLinkMtp2T4N, cSpLinkMtp2T4E, 
--    cSpLinkMtp2T05, cSpLinkMtp2T06, cSpLinkMtp2T07, 
--    cSpLinkMtp2T08, cSpLinkMtp3T01, cSpLinkMtp3T02, 
--    cSpLinkMtp3T03, cSpLinkMtp3T04, cSpLinkMtp3T05, 
--    cSpLinkMtp3T06, cSpLinkMtp3T07, cSpLinkMtp3T08, 
--    cSpLinkMtp3T10, cSpLinkMtp3T11, cSpLinkMtp3T12, 
--    cSpLinkMtp3T13, cSpLinkMtp3T14, cSpLinkMtp3T15, 
--    cSpLinkMtp3T16, cSpLinkMtp3T17, cSpLinkMtp3T18, 
--    cSpLinkMtp3T19, cSpLinkMtp3T20, cSpLinkMtp3T21, 
--    cSpLinkMtp3T22, cSpLinkMtp3T23, cSpLinkMtp3T24, 
--    cSpLinkMtp3T25, cSpLinkMtp3T26, cSpLinkMtp3T27, 
--    cSpLinkMtp3T28, cSpLinkMtp3T29, cSpLinkMtp3T30, 
--    cSpLinkMtp3T31, cSpLinkMtp3T32, cSpLinkMtp3T33, 
--    cSpLinkMtp3T34, cSpLinkXmitQueueDepth, 
--    cSpLinkXmitQueueDepthHigh, cSpLinkXmitQueueDepthHighReset, 
--    cSpLinkCongestionState, cSpLinkCongestionAbate1, 
--    cSpLinkCongestionAbate2, cSpLinkCongestionAbate3, 
--    cSpLinkCongestionOnset1, cSpLinkCongestionOnset2, 
--    cSpLinkCongestionOnset3, cSpLinkSigLinkTest, cSpLinkQ752T1E1, 
--    cSpLinkQ752T1E2, cSpLinkQ752T1E3, cSpLinkQ752T1E4, 
--    cSpLinkQ752T1E5, cSpLinkQ752T1E6, cSpLinkQ752T1E7, 
--    cSpLinkQ752T1E8, cSpLinkQ752T1E9, cSpLinkQ752T1E10, 
--    cSpLinkQ752T1E11, cSpLinkQ752T2E1, cSpLinkQ752T2E5, 
--    cSpLinkQ752T2E6, cSpLinkQ752T2E7, cSpLinkQ752T2E9, 
--    cSpLinkQ752T2E10, cSpLinkQ752T2E15, cSpLinkQ752T2E16, 
--    cSpLinkQ752T2E18, cSpLinkMtp3PacketsRetrans, 
--    cSpLinkMtp3BytesRetrans, cSpLinkQ752T3E6, cSpLinkQ752T3E7, 
--    cSpLinkQ752T3E10L1, cSpLinkQ752T3E10L2, cSpLinkQ752T3E10L3, 
--    cSpLinkQ752T3E11L1, cSpLinkQ752T3E11L2, cSpLinkQ752T3E11L3

ciscoSpRouteGroup OBJECT IDENTIFIER ::= { ciscoSpMIBGroups 4 }
-- OBJECT-GROUP
--  Status
--    mandatory
--  Descr
--    SP route table objects.
--  objects
--    cSpRouteStatus

ciscoSpAccessListGroup OBJECT IDENTIFIER ::= { ciscoSpMIBGroups 5 }
-- OBJECT-GROUP
--  Status
--    mandatory
--  Descr
--    SP access control list objects.
--  objects
--    cSpAclType, cSpAclDpc, cSpAclDpcMask, cSpAclOpc, 
--    cSpAclOpcMask, cSpAclSi, cSpAclPattern, cSpAclOffset, 
--    cSpAclAction

ciscoSpAccountingGroup OBJECT IDENTIFIER ::= { ciscoSpMIBGroups 6 }
-- OBJECT-GROUP
--  Status
--    mandatory
--  Descr
--    SP accounting objects.
--  objects
--    cSpAccRcvdPackets, cSpAccHCRcvdPackets, cSpAccSentPackets, 
--    cSpAccHCSentPackets, cSpAccRcvdBytes, cSpAccHCRcvdBytes, 
--    cSpAccSentBytes, cSpAccHCSentBytes, cSpAccSnmmRcvdPackets, 
--    cSpAccHCSnmmRcvdPackets, cSpAccSnmmRcvdBytes, 
--    cSpAccHCSnmmRcvdBytes, cSpAccSnmmSentPackets, 
--    cSpAccHCSnmmSentPackets, cSpAccSnmmSentBytes, 
--    cSpAccHCSnmmSentBytes, cSpAccSntmRcvdPackets, 
--    cSpAccHCSntmRcvdPackets, cSpAccSntmRcvdBytes, 
--    cSpAccHCSntmRcvdBytes, cSpAccSntmSentPackets, 
--    cSpAccHCSntmSentPackets, cSpAccSntmSentBytes, 
--    cSpAccHCSntmSentBytes, cSpAccSpare2RcvdPackets, 
--    cSpAccHCSpare2RcvdPackets, cSpAccSpare2RcvdBytes, 
--    cSpAccHCSpare2RcvdBytes, cSpAccSpare2SentPackets, 
--    cSpAccHCSpare2SentPackets, cSpAccSpare2SentBytes, 
--    cSpAccHCSpare2SentBytes, cSpAccSccpRcvdPackets, 
--    cSpAccHCSccpRcvdPackets, cSpAccSccpRcvdBytes, 
--    cSpAccHCSccpRcvdBytes, cSpAccSccpSentPackets, 
--    cSpAccHCSccpSentPackets, cSpAccSccpSentBytes, 
--    cSpAccHCSccpSentBytes, cSpAccTupRcvdPackets, 
--    cSpAccHCTupRcvdPackets, cSpAccTupRcvdBytes, 
--    cSpAccHCTupRcvdBytes, cSpAccTupSentPackets, 
--    cSpAccHCTupSentPackets, cSpAccTupSentBytes, 
--    cSpAccHCTupSentBytes, cSpAccIsupRcvdPackets, 
--    cSpAccHCIsupRcvdPackets, cSpAccIsupRcvdBytes, 
--    cSpAccHCIsupRcvdBytes, cSpAccIsupSentPackets, 
--    cSpAccHCIsupSentPackets, cSpAccIsupSentBytes, 
--    cSpAccHCIsupSentBytes, cSpAccDupcRcvdPackets, 
--    cSpAccHCDupcRcvdPackets, cSpAccDupcRcvdBytes, 
--    cSpAccHCDupcRcvdBytes, cSpAccDupcSentPackets, 
--    cSpAccHCDupcSentPackets, cSpAccDupcSentBytes, 
--    cSpAccHCDupcSentBytes, cSpAccDupfRcvdPackets, 
--    cSpAccHCDupfRcvdPackets, cSpAccDupfRcvdBytes, 
--    cSpAccHCDupfRcvdBytes, cSpAccDupfSentPackets, 
--    cSpAccHCDupfSentPackets, cSpAccDupfSentBytes, 
--    cSpAccHCDupfSentBytes, cSpAccMtupRcvdPackets, 
--    cSpAccHCMtupRcvdPackets, cSpAccMtupRcvdBytes, 
--    cSpAccHCMtupRcvdBytes, cSpAccMtupSentPackets, 
--    cSpAccHCMtupSentPackets, cSpAccMtupSentBytes, 
--    cSpAccHCMtupSentBytes, cSpAccBisupRcvdPackets, 
--    cSpAccHCBisupRcvdPackets, cSpAccBisupRcvdBytes, 
--    cSpAccHCBisupRcvdBytes, cSpAccBisupSentPackets, 
--    cSpAccHCBisupSentPackets, cSpAccBisupSentBytes, 
--    cSpAccHCBisupSentBytes, cSpAccSisupRcvdPackets, 
--    cSpAccHCSisupRcvdPackets, cSpAccSisupRcvdBytes, 
--    cSpAccHCSisupRcvdBytes, cSpAccSisupSentPackets, 
--    cSpAccHCSisupSentPackets, cSpAccSisupSentBytes, 
--    cSpAccHCSisupSentBytes, cSpAccSpare11RcvdPackets, 
--    cSpAccHCSpare11RcvdPackets, cSpAccSpare11RcvdBytes, 
--    cSpAccHCSpare11RcvdBytes, cSpAccSpare11SentPackets, 
--    cSpAccHCSpare11SentPackets, cSpAccSpare11SentBytes, 
--    cSpAccHCSpare11SentBytes, cSpAccSpare12RcvdPackets, 
--    cSpAccHCSpare12RcvdPackets, cSpAccSpare12RcvdBytes, 
--    cSpAccHCSpare12RcvdBytes, cSpAccSpare12SentPackets, 
--    cSpAccHCSpare12SentPackets, cSpAccSpare12SentBytes, 
--    cSpAccHCSpare12SentBytes, cSpAccSpare13RcvdPackets, 
--    cSpAccHCSpare13RcvdPackets, cSpAccSpare13RcvdBytes, 
--    cSpAccHCSpare13RcvdBytes, cSpAccSpare13SentPackets, 
--    cSpAccHCSpare13SentPackets, cSpAccSpare13SentBytes, 
--    cSpAccHCSpare13SentBytes, cSpAccSpare14RcvdPackets, 
--    cSpAccHCSpare14RcvdPackets, cSpAccSpare14RcvdBytes, 
--    cSpAccHCSpare14RcvdBytes, cSpAccSpare14SentPackets, 
--    cSpAccHCSpare14SentPackets, cSpAccSpare14SentBytes, 
--    cSpAccHCSpare14SentBytes, cSpAccSpare15RcvdPackets, 
--    cSpAccHCSpare15RcvdPackets, cSpAccSpare15RcvdBytes, 
--    cSpAccHCSpare15RcvdBytes, cSpAccSpare15SentPackets, 
--    cSpAccHCSpare15SentPackets, cSpAccSpare15SentBytes, 
--    cSpAccHCSpare15SentBytes

ciscoSpNotificationsEnableGroup OBJECT IDENTIFIER ::= { ciscoSpMIBGroups 7 }
-- OBJECT-GROUP
--  Status
--    mandatory
--  Descr
--    SP enable notification objects.
--  objects
--    cSpLsStateChangeNotifEnabled, cSpLnkStateChangeNotifEnabled

ciscoSpNotificationsGroup OBJECT IDENTIFIER ::= { ciscoSpMIBGroups 8 }
-- NOTIFICATION-GROUP
--  Status
--    mandatory
--  Descr
--    The collection of notifications used to indicate
--     wrapped and unwrapped node state information.
--  notifications
--    ciscoSpLinksetStateChange, ciscoSpLinkStateChange

ciscoSpMIBCompliance OBJECT IDENTIFIER ::= { ciscoSpMIBCompliances 1 }
-- MODULE-COMPLIANCE
--  Status
--    mandatory
--  Descr
--    The compliance statement for entities which implement
--    the Cisco SP MIB
--  Module
--    >>current<<
--   MandGroup
--    ciscoSpSwitchGroup
--   MandGroup
--    ciscoSpLinksetGroup
--   MandGroup
--    ciscoSpLinkGroup
--   MandGroup
--    ciscoSpRouteGroup
--   MandGroup
--    ciscoSpAccessListGroup
--   MandGroup
--    ciscoSpAccountingGroup
--   MandGroup
--    ciscoSpNotificationsEnableGroup
--   OptGroup
--    ciscoSpNotificationsGroup


END
