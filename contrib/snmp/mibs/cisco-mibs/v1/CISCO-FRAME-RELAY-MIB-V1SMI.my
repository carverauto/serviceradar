-- MIB file created 15-Sep-2003 14:10:26, by
--   SMICng version 2.2.11-beta(PRO)(Solaris), January 20, 2001. Enterprise key cisco.com

CISCO-FRAME-RELAY-MIB DEFINITIONS ::= BEGIN

-- From file: "CISCO-FRAME-RELAY-MIB.my"
-- Compile options "4 7 F H N W 03 06 0B 0G 0N 0T"

IMPORTS
    DisplayString, TruthValue
            FROM SNMPv2-TC-v1
    ciscoMgmt
            FROM CISCO-SMI
    InterfaceIndex
            FROM IF-MIB
    ifIndex
            FROM RFC1213-MIB
    frDlcmiIfIndex, frCircuitIfIndex, frCircuitDlci
            FROM RFC1315-MIB
    Counter, IpAddress
            FROM RFC1155-SMI
    OBJECT-TYPE
            FROM RFC-1212;

ciscoFrameRelayMIB OBJECT IDENTIFIER ::= { ciscoMgmt 49 }
-- MODULE-IDENTITY
--  LastUpdated
--    200010130000Z
--  OrgName
--    Cisco Systems, Inc.
--  ContactInfo
--           Cisco Systems
--            Customer Service
--    
--    Postal: 170 W Tasman Drive
--            San Jose, CA  95134
--            USA
--    
--       Tel: +1 800 553-NETS
--    
--    E-mail: cs-framerelay@cisco.com
--  Descr
--    Cisco Frame Relay MIB
--  RevDate
--    200010130000Z
--  RevDescr
--    (1) Added objects of FR Switching, FR Fragmentation 
--    and FR/ATM Interworking.
--    (2) Objects for per PVC I/O rate is added to 
--    cfrExtCircuitTable
--  RevDate
--    200005220000Z
--  RevDescr
--    (1) Added  ELMI subgroup for ELMI objects.
--  RevDate
--    200005160000Z
--  RevDescr
--    (1) Added Traffic Shaping parameter objects to
--    cfrExtCircuitTable.
--    (2) Deprecated cfrSvcMinThruputOut and 
--    cfrSvcMinThruputIn. Added cfrExtCircuitMinThruputOut 
--    and cfrExtCircuitMinThruputIn in cfrExtCircuitTable 
--    inorder to make them applicable to both PVC/SVC. 
--    (3) Added cfrExtCircuitBandwidth object to 
--    cfrExtCircuitTable.
--  RevDate
--    200004260000Z
--  RevDescr
--    (1) add an integer value for cfrMapPayloadCompressType;
--    (2) reword the Description statements for 
--          { cfrMapPayloadCompressType,
--          cfrExtCircuitUncompressIns,
--          cfrExtCircuitUncompressOuts }
--    so that they are not limited to software compression.
--  RevDate
--    9908210000Z
--  RevDescr
--    (1) Added cfrExtCircuitUncompressOuts and
--    cfrExtCircuitUncompressIns to the circuit subgroup;
--    (2) Added cfrMapRtpHdrCompress and cfrMapPayloadCompressType
--    to the mapping subgroup;
--    (3) cfrMapPayloadCompress becomes deprecated, obsoleted
--    by cfrMapPayloadCompressType;
--    (4) frCircuitSentOctets and frCircuitReceivedOctets
--    per RFC1315 will reflect the number of bytes in Frame Relay
--    frames sent to and received from the physical layer. Same
--    effect is applied to ifOutOctets and ifInOctets as well
--    when ifIndex refers to a Frame Relay subinterface.
--  RevDate
--    9608150000Z
--  RevDescr
--    Initial version of this MIB module.

ciscoFrMIBObjects OBJECT IDENTIFIER ::= { ciscoFrameRelayMIB 1 }
cfrLmiObjs      OBJECT IDENTIFIER ::= { ciscoFrMIBObjects 1 }
cfrCircuitObjs  OBJECT IDENTIFIER ::= { ciscoFrMIBObjects 2 }
cfrMapObjs      OBJECT IDENTIFIER ::= { ciscoFrMIBObjects 3 }
cfrSvcObjs      OBJECT IDENTIFIER ::= { ciscoFrMIBObjects 4 }
cfrElmiObjs     OBJECT IDENTIFIER ::= { ciscoFrMIBObjects 5 }
cfrFragObjs     OBJECT IDENTIFIER ::= { ciscoFrMIBObjects 6 }
cfrConnectionObjs OBJECT IDENTIFIER ::= { ciscoFrMIBObjects 7 }
ciscoFrMIBConformance OBJECT IDENTIFIER ::= { ciscoFrameRelayMIB 3 }
ciscoFrMIBCompliances OBJECT IDENTIFIER ::= { ciscoFrMIBConformance 1 }
ciscoFrMIBGroups OBJECT IDENTIFIER ::= { ciscoFrMIBConformance 2 }

DlciNumber ::= INTEGER(0..1023)
-- TEXTUAL-CONVENTION
--  Status
--    mandatory
--  Descr
--    Numerical format of Data Link Connection Identifier
--    (DLCI) in decimal, identical to the 'DLCI' as INTEGER
--    of 0..DLCINumber in RFC1315. The maximum value depends
--    on Frame Relay implementation, which is currently set
--    to be 1023 for 2-octet address format per UNI
--    Implementation Agreement FRF.1.

CfrMapProtocols ::= INTEGER {
        arp(1),
        serialArp(6),
        ip(7),
        xns(10),
        novell(11),
        apollo(12),
        vines(13),
        appletalk(16),
        ieeeSpanning(18),
        decnet(22),
        clns(25),
        rsrb(37),
        bridge(38),
        stun(39),
        frArp(40),
        uncompressedTcp(47),
        compressedTcp(48),
        llc2(49),
        frSwitch(53),
        dlsw(63),
        nhrp(74),
        compressedRtp(83),
        wildcard(999)
        }
-- TEXTUAL-CONVENTION
--  Status
--    mandatory
--  Descr
--    Cisco link types (network protocols) that run
--    over Frame Relay. Associated values, except for
--    wildcard, match assigned values of internal software
--    respectively.

cfrLmiTable OBJECT-TYPE
    SYNTAX SEQUENCE OF CfrLmiEntry
    ACCESS not-accessible
    STATUS mandatory
    DESCRIPTION
        "Table of Frame Relay LMI information that are
        either supplemental to the frDlcmiTable of RFC 1315
        or specific to Cisco's implementation."
    REFERENCE
        "American National Standard T1.617-1991, Annex D"
    ::= { cfrLmiObjs 1 }

cfrLmiEntry OBJECT-TYPE
    SYNTAX CfrLmiEntry
    ACCESS not-accessible
    STATUS mandatory
    DESCRIPTION
        "Each entry of the table contains information
        of Frame Relay LMI over one physical interface.
        They are mostly FR generic and some Cisco specific."
    INDEX { frDlcmiIfIndex }
-- Augments frDlcmiEntry FROM RFC1315-MIB
    ::= { cfrLmiTable 1 }

CfrLmiEntry ::= SEQUENCE {
    cfrLmiLinkstatus INTEGER,
    cfrLmiLinkType INTEGER,
    cfrLmiEnquiryIns Counter,
    cfrLmiEnquiryOuts Counter,
    cfrLmiStatusIns Counter,
    cfrLmiStatusOuts Counter,
    cfrLmiUpdateStatusIns Counter,
    cfrLmiUpdateStatusOuts Counter,
    cfrLmiStatusTimeouts Counter,
    cfrLmiStatusEnqTimeouts Counter,
    cfrLmiN392Dce INTEGER,
    cfrLmiN393Dce INTEGER,
    cfrLmiT392Dce INTEGER
    }

cfrLmiLinkstatus OBJECT-TYPE
    SYNTAX INTEGER {
        up(1),
        down(2)
        }
    ACCESS read-only
    STATUS mandatory
    DESCRIPTION
        "Data link status via LMI."
    ::= { cfrLmiEntry 1 }

cfrLmiLinkType OBJECT-TYPE
    SYNTAX INTEGER {
        dte(1),
        dce(2),
        nni(3)
        }
    ACCESS read-only
    STATUS mandatory
    DESCRIPTION
        "Frame Relay link type."
    ::= { cfrLmiEntry 2 }

cfrLmiEnquiryIns OBJECT-TYPE
    SYNTAX Counter
--  Units
--    messages
    ACCESS read-only
    STATUS mandatory
    DESCRIPTION
        "Number of Status Enquiry messages received."
    ::= { cfrLmiEntry 3 }

cfrLmiEnquiryOuts OBJECT-TYPE
    SYNTAX Counter
--  Units
--    messages
    ACCESS read-only
    STATUS mandatory
    DESCRIPTION
        "Number of Status Enquiry messages sent."
    ::= { cfrLmiEntry 4 }

cfrLmiStatusIns OBJECT-TYPE
    SYNTAX Counter
--  Units
--    messages
    ACCESS read-only
    STATUS mandatory
    DESCRIPTION
        "Number of Status messages received."
    ::= { cfrLmiEntry 5 }

cfrLmiStatusOuts OBJECT-TYPE
    SYNTAX Counter
--  Units
--    messages
    ACCESS read-only
    STATUS mandatory
    DESCRIPTION
        "Number of Status messages sent."
    ::= { cfrLmiEntry 6 }

cfrLmiUpdateStatusIns OBJECT-TYPE
    SYNTAX Counter
--  Units
--    messages
    ACCESS read-only
    STATUS mandatory
    DESCRIPTION
        "Number of Update Status messages received."
    ::= { cfrLmiEntry 7 }

cfrLmiUpdateStatusOuts OBJECT-TYPE
    SYNTAX Counter
--  Units
--    messages
    ACCESS read-only
    STATUS mandatory
    DESCRIPTION
        "Number of Update Status messages sent"
    ::= { cfrLmiEntry 8 }

cfrLmiStatusTimeouts OBJECT-TYPE
    SYNTAX Counter
--  Units
--    times
    ACCESS read-only
    STATUS mandatory
    DESCRIPTION
        "Number of times when timeout occurred on waiting
        for Status message"
    ::= { cfrLmiEntry 9 }

cfrLmiStatusEnqTimeouts OBJECT-TYPE
    SYNTAX Counter
--  Units
--    times
    ACCESS read-only
    STATUS mandatory
    DESCRIPTION
        "Number of times when timeout occurred on waiting
        for Status Enquiry message"
    ::= { cfrLmiEntry 10 }

cfrLmiN392Dce OBJECT-TYPE
    SYNTAX INTEGER(0..10)
    ACCESS read-only
    STATUS mandatory
    DESCRIPTION
        "LMI error threshold for DCE interface.
        For DTE, value becomes 0."
    ::= { cfrLmiEntry 11 }

cfrLmiN393Dce OBJECT-TYPE
    SYNTAX INTEGER(0..10)
    ACCESS read-only
    STATUS mandatory
    DESCRIPTION
        "LMI monitored event count for DCE interface.
        For DTE, value becomes zero (0)."
    ::= { cfrLmiEntry 12 }

cfrLmiT392Dce OBJECT-TYPE
    SYNTAX INTEGER(0..30)
--  Units
--    seconds
    ACCESS read-only
    STATUS mandatory
    DESCRIPTION
        "DCE polling verification timer for DCE interface
        For DTE, the value becomes zero (0)."
    ::= { cfrLmiEntry 13 }

cfrCircuitTable OBJECT-TYPE
    SYNTAX SEQUENCE OF CfrCircuitEntry
    ACCESS not-accessible
    STATUS mandatory
    DESCRIPTION
        "Table of descriptive and statistics information
        that are generic to Frame Relay virtual circuits."
    ::= { cfrCircuitObjs 1 }

cfrCircuitEntry OBJECT-TYPE
    SYNTAX CfrCircuitEntry
    ACCESS not-accessible
    STATUS mandatory
    DESCRIPTION
        "Each entry of the table contains information of a
        circuit that are not included in frCircuitTable of
        RFC1315 but are generic to Frame Relay."
    INDEX { frCircuitIfIndex, frCircuitDlci }
-- Augments frCircuitEntry FROM RFC1315-MIB
    ::= { cfrCircuitTable 1 }

CfrCircuitEntry ::= SEQUENCE {
    cfrCircuitDEins Counter,
    cfrCircuitDEouts Counter,
    cfrCircuitDropPktsOuts Counter,
    cfrCircuitType INTEGER
    }

cfrCircuitDEins OBJECT-TYPE
    SYNTAX Counter
--  Units
--    packets
    ACCESS read-only
    STATUS mandatory
    DESCRIPTION
        "Number of packets received with the Discarded
        Eligibility indictor (the DE bit) set."
    ::= { cfrCircuitEntry 1 }

cfrCircuitDEouts OBJECT-TYPE
    SYNTAX Counter
--  Units
--    packets
    ACCESS read-only
    STATUS mandatory
    DESCRIPTION
        "Number of packets transmitted with DE bit set."
    ::= { cfrCircuitEntry 2 }

cfrCircuitDropPktsOuts OBJECT-TYPE
    SYNTAX Counter
--  Units
--    packets
    ACCESS read-only
    STATUS mandatory
    DESCRIPTION
        "Number of discarded packets that were to be sent."
    ::= { cfrCircuitEntry 3 }

cfrCircuitType OBJECT-TYPE
    SYNTAX INTEGER {
        pvc(1),
        svc(2)
        }
    ACCESS read-only
    STATUS mandatory
    DESCRIPTION
        "Basic circuit type"
    ::= { cfrCircuitEntry 4 }

cfrExtCircuitTable OBJECT-TYPE
    SYNTAX SEQUENCE OF CfrExtCircuitEntry
    ACCESS not-accessible
    STATUS mandatory
    DESCRIPTION
        "Table of Cisco implementation specific FR
        circuit information. This is a Cisco extension
        for the frCircuitTable of RFC 1315."
    ::= { cfrCircuitObjs 2 }

cfrExtCircuitEntry OBJECT-TYPE
    SYNTAX CfrExtCircuitEntry
    ACCESS not-accessible
    STATUS mandatory
    DESCRIPTION
        "Each entry of the table contains information
        of a Frame Relay virtual circuit that are specific
        to Cisco implementation."
    INDEX { frCircuitIfIndex, frCircuitDlci }
-- Augments frCircuitEntry FROM RFC1315-MIB
    ::= { cfrExtCircuitTable 1 }

CfrExtCircuitEntry ::= SEQUENCE {
    cfrExtCircuitIfName DisplayString,
    cfrExtCircuitIfType INTEGER,
    cfrExtCircuitSubifIndex InterfaceIndex,
    cfrExtCircuitMapStatus INTEGER,
    cfrExtCircuitCreateType INTEGER,
    cfrExtCircuitMulticast TruthValue,
    cfrExtCircuitRoutedDlci DlciNumber,
    cfrExtCircuitRoutedIf InterfaceIndex,
    cfrExtCircuitUncompressIns Counter,
    cfrExtCircuitUncompressOuts Counter,
    cfrExtCircuitFECNOuts Counter,
    cfrExtCircuitBECNOuts Counter,
    cfrExtCircuitMinThruputOut INTEGER,
    cfrExtCircuitMinThruputIn INTEGER,
    cfrExtCircuitBcastPktOuts Counter,
    cfrExtCircuitBcastByteOuts Counter,
    cfrExtCircuitBandwidth INTEGER,
    cfrExtCircuitShapeByteLimit INTEGER,
    cfrExtCircuitShapeInterval INTEGER,
    cfrExtCircuitShapeByteIncrement INTEGER,
    cfrExtCircuitShapePkts Counter,
    cfrExtCircuitShapeBytes Counter,
    cfrExtCircuitShapePktsDelay Counter,
    cfrExtCircuitShapeBytesDelay Counter,
    cfrExtCircuitShapeActive TruthValue,
    cfrExtCircuitShapeAdapting INTEGER,
    cfrExtCircuitTxDataRate INTEGER,
    cfrExtCircuitTxPktRate INTEGER,
    cfrExtCircuitRcvDataRate INTEGER,
    cfrExtCircuitRcvPktRate INTEGER
    }

cfrExtCircuitIfName OBJECT-TYPE
    SYNTAX DisplayString
--    Rsyntax OCTET STRING(SIZE(0..255))
    ACCESS read-only
    STATUS mandatory
    DESCRIPTION
        "The textual name of the main interface or the 
        subinterface that this DLCI is associated with.
        This is the same name string of an interface used
        in the configuration and all console displays,
        such as 'serial 0', 'serial 3/0.3', etc."
    ::= { cfrExtCircuitEntry 1 }

cfrExtCircuitIfType OBJECT-TYPE
    SYNTAX INTEGER {
        mainInterface(1),
        pointToPoint(2),
        multipoint(3)
        }
    ACCESS read-only
    STATUS mandatory
    DESCRIPTION
        "Type of the subinterface this DLCI is associated
        with, if configured."
    ::= { cfrExtCircuitEntry 2 }

cfrExtCircuitSubifIndex OBJECT-TYPE
    SYNTAX InterfaceIndex
--    Rsyntax INTEGER(1..2147483647)
    ACCESS read-only
    STATUS mandatory
    DESCRIPTION
        "For value greater than zero (0), it indicates
        the network management interface index
        for the subinterface associated with
        this DLCI. Value 0 means the DLCI is not
        associated with any subinterface."
    ::= { cfrExtCircuitEntry 3 }

cfrExtCircuitMapStatus OBJECT-TYPE
    SYNTAX INTEGER(0..2047)
    ACCESS read-only
    STATUS mandatory
    DESCRIPTION
        "The mapping protocols (internally considered as
        the 'link type') applied on this circuit.
        The value ranges from 0 to 2047.
        For point-to-point DLCI, the value stays zero.
        Otherwise, the value is a sum. It initially takes
        the value zero, then, for each type of Protocol,
        2 raised to a power is added to the sum.
        The following table presents respective power and
        equivalent value for each applicable type:
        
                Protocol        Power    Value
                --------        -----    -----
                IP              0        1
                IPX             1        2
                Appletalk       2        4
                XNS             3        8
                VINES           4        16
                DECnet          5        32
                CLNS            6        64
                Bridging        7        128
                RSRB            8        256
                STUN            9        512
                LLC2            10       1024
        
        For example, value 3 means the circuit's mapping
        protocols include IP and IPX. (3 = 2**1 + 2**0,
        where 0 corresponds to IP and 1 to IPX.) Value 0
        means there is currently no mapping protocol for
        the circuit.
        See cfrMapTable for more mapping information."
    ::= { cfrExtCircuitEntry 4 }

cfrExtCircuitCreateType OBJECT-TYPE
    SYNTAX INTEGER {
        dynamic(1),
        static(2)
        }
    ACCESS read-only
    STATUS mandatory
    DESCRIPTION
        "Identify the last source of the circuit's creation."
    ::= { cfrExtCircuitEntry 5 }

cfrExtCircuitMulticast OBJECT-TYPE
    SYNTAX TruthValue
--    Rsyntax INTEGER {
--        true(1),
--        false(2)
--        }
    ACCESS read-only
    STATUS mandatory
    DESCRIPTION
        "Indicate if this DLCI is a multicast DLCI."
    ::= { cfrExtCircuitEntry 6 }

cfrExtCircuitRoutedDlci OBJECT-TYPE
    SYNTAX DlciNumber
--    Rsyntax INTEGER(0..1023)
    ACCESS read-only
    STATUS mandatory
    DESCRIPTION
        "The routed DLCI to pair up with this DLCI
        for switching function. NOTE: Value zero (0)
        indicates that there is no such routed DLCI
        corresponding to this DLCI."
    ::= { cfrExtCircuitEntry 7 }

cfrExtCircuitRoutedIf OBJECT-TYPE
    SYNTAX InterfaceIndex
--    Rsyntax INTEGER(1..2147483647)
    ACCESS read-only
    STATUS mandatory
    DESCRIPTION
        "The interface for the routed DLCI that pairs up
        with this DLCI for switching. Value greater than 0
        is the InterfaceIndex for that interface. Value
        zero (0) indicates that there is no such routed DLCI
        corresponding to this DLCI."
    ::= { cfrExtCircuitEntry 8 }

cfrExtCircuitUncompressIns OBJECT-TYPE
    SYNTAX Counter
--  Units
--    octets
    ACCESS read-only
    STATUS mandatory
    DESCRIPTION
        "Number of inbound octets of the data packets,
        accounted at Frame Relay level after FRF.9
        payload decompression is applied. In the case of
        non-FRF.9, this value could be identical to
        frCircuitReceivedOctets, unless otherwise noted."
    ::= { cfrExtCircuitEntry 9 }

cfrExtCircuitUncompressOuts OBJECT-TYPE
    SYNTAX Counter
--  Units
--    octets
    ACCESS read-only
    STATUS mandatory
    DESCRIPTION
        "Number of outbound octets of the data packets,
        accounted at Frame Relay level before FRF.9
        payload compression is applied. In the case of
        non-FRF.9, this value could be identical to
        frCircuitSentOctets, unless otherwise noted."
    ::= { cfrExtCircuitEntry 10 }

cfrExtCircuitFECNOuts OBJECT-TYPE
    SYNTAX Counter
    ACCESS read-only
    STATUS mandatory
    DESCRIPTION
        "Total number of frames sent out to the network 
        indicating forward congestion."
    ::= { cfrExtCircuitEntry 11 }

cfrExtCircuitBECNOuts OBJECT-TYPE
    SYNTAX Counter
    ACCESS read-only
    STATUS mandatory
    DESCRIPTION
        "Total number of frames sent out to the network 
        indicating backward congestion."
    ::= { cfrExtCircuitEntry 12 }

cfrExtCircuitMinThruputOut OBJECT-TYPE
    SYNTAX INTEGER(9600..1544000)
--  Units
--    bits per second
    ACCESS read-only
    STATUS mandatory
    DESCRIPTION
        "Circuit's outgoing minimal Throughput based on 
        configuration."
    ::= { cfrExtCircuitEntry 13 }

cfrExtCircuitMinThruputIn OBJECT-TYPE
    SYNTAX INTEGER(9600..1544000)
--  Units
--    bits per second
    ACCESS read-only
    STATUS mandatory
    DESCRIPTION
        "Circuit's incoming minimal Throughput based on
        configuration."
    ::= { cfrExtCircuitEntry 14 }

cfrExtCircuitBcastPktOuts OBJECT-TYPE
    SYNTAX Counter
    ACCESS read-only
    STATUS mandatory
    DESCRIPTION
        "Total number of broadcast packets sent out to the 
         network."
    ::= { cfrExtCircuitEntry 15 }

cfrExtCircuitBcastByteOuts OBJECT-TYPE
    SYNTAX Counter
    ACCESS read-only
    STATUS mandatory
    DESCRIPTION
        "Total number of bytes sent out to the network in 
        broadcast packets."
    ::= { cfrExtCircuitEntry 16 }

cfrExtCircuitBandwidth OBJECT-TYPE
    SYNTAX INTEGER(0..16777215)
--  Units
--    bits per second
    ACCESS read-only
    STATUS mandatory
    DESCRIPTION
        "Bandwidth of the virtual circuit, acquired from 
        Cisco typed LMI Full Status message."
    ::= { cfrExtCircuitEntry 17 }

cfrExtCircuitShapeByteLimit OBJECT-TYPE
    SYNTAX INTEGER(125..2147483647)
--  Units
--    octets
    ACCESS read-only
    STATUS mandatory
    DESCRIPTION
        "Maximum number of tokens a token bucket can hold in any
        time interval in case of traffic shaping."
    ::= { cfrExtCircuitEntry 18 }

cfrExtCircuitShapeInterval OBJECT-TYPE
    SYNTAX INTEGER(10..125)
--  Units
--    milliseconds
    ACCESS read-only
    STATUS mandatory
    DESCRIPTION
        "Committed rate measurement interval."
    ::= { cfrExtCircuitEntry 19 }

cfrExtCircuitShapeByteIncrement OBJECT-TYPE
    SYNTAX INTEGER(125..2147483647)
--  Units
--    octets
    ACCESS read-only
    STATUS mandatory
    DESCRIPTION
        "Number of tokens added into the token bucket per time
        interval in case of traffic shaping."
    ::= { cfrExtCircuitEntry 20 }

cfrExtCircuitShapePkts OBJECT-TYPE
    SYNTAX Counter
    ACCESS read-only
    STATUS mandatory
    DESCRIPTION
        "Total number of packets that went through traffic 
        shaping."
    ::= { cfrExtCircuitEntry 21 }

cfrExtCircuitShapeBytes OBJECT-TYPE
    SYNTAX Counter
--  Units
--    octets
    ACCESS read-only
    STATUS mandatory
    DESCRIPTION
        "Total number of bytes that went through traffic 
        shaping."
    ::= { cfrExtCircuitEntry 22 }

cfrExtCircuitShapePktsDelay OBJECT-TYPE
    SYNTAX Counter
    ACCESS read-only
    STATUS mandatory
    DESCRIPTION
        "Total number of packets that were delayed by the 
        traffic shaper."
    ::= { cfrExtCircuitEntry 23 }

cfrExtCircuitShapeBytesDelay OBJECT-TYPE
    SYNTAX Counter
--  Units
--    octets
    ACCESS read-only
    STATUS mandatory
    DESCRIPTION
        "Total number of bytes that were delayed by the 
        traffic shaper."
    ::= { cfrExtCircuitEntry 24 }

cfrExtCircuitShapeActive OBJECT-TYPE
    SYNTAX TruthValue
--    Rsyntax INTEGER {
--        true(1),
--        false(2)
--        }
    ACCESS read-only
    STATUS mandatory
    DESCRIPTION
        "Shows whether shaping is active or not."
    ::= { cfrExtCircuitEntry 25 }

cfrExtCircuitShapeAdapting OBJECT-TYPE
    SYNTAX INTEGER {
        none(1),
        becn(2),
        foreSight(3)
        }
    ACCESS read-only
    STATUS mandatory
    DESCRIPTION
        "Type of Adaptive Shaping configured.
        none(1)      - No adaptive shaping configured
        becn(2)      - Backward Explicit Congestion Notification
        foreSight(3) - ForeSight is the network traffic control 
                       software used in Cisco WAN switches"
    ::= { cfrExtCircuitEntry 26 }

cfrExtCircuitTxDataRate OBJECT-TYPE
    SYNTAX INTEGER(1..45000000)
    ACCESS read-only
    STATUS mandatory
    DESCRIPTION
        "The average rate (bytes/second) at which data is 
        transmitted in this circuit. "
    ::= { cfrExtCircuitEntry 27 }

cfrExtCircuitTxPktRate OBJECT-TYPE
    SYNTAX INTEGER(1..45000000)
    ACCESS read-only
    STATUS mandatory
    DESCRIPTION
        "The average number of packets sent in a second in this 
        circuit."
    ::= { cfrExtCircuitEntry 28 }

cfrExtCircuitRcvDataRate OBJECT-TYPE
    SYNTAX INTEGER(1..45000000)
    ACCESS read-only
    STATUS mandatory
    DESCRIPTION
        "The average rate (bytes/second) at which data is 
        received in this circuit. "
    ::= { cfrExtCircuitEntry 29 }

cfrExtCircuitRcvPktRate OBJECT-TYPE
    SYNTAX INTEGER(1..45000000)
    ACCESS read-only
    STATUS mandatory
    DESCRIPTION
        "The average number of packets received in a second in 
        this circuit. "
    ::= { cfrExtCircuitEntry 30 }

cfrMapTable OBJECT-TYPE
    SYNTAX SEQUENCE OF CfrMapEntry
    ACCESS not-accessible
    STATUS mandatory
    DESCRIPTION
        "Table of protocols and addresses mapping
        information of FR virtual circuit."
    ::= { cfrMapObjs 1 }

cfrMapEntry OBJECT-TYPE
    SYNTAX CfrMapEntry
    ACCESS not-accessible
    STATUS mandatory
    DESCRIPTION
        "Each entry of the table contains one mapping 
        information of a Frame Relay virtual circuit."
    INDEX { frCircuitIfIndex, frCircuitDlci, cfrMapIndex }
    ::= { cfrMapTable 1 }

CfrMapEntry ::= SEQUENCE {
    cfrMapIndex INTEGER,
    cfrMapProtocol CfrMapProtocols,
    cfrMapAddress OCTET STRING,
    cfrMapType INTEGER,
    cfrMapEncaps INTEGER,
    cfrMapBroadcast TruthValue,
    cfrMapPayloadCompress TruthValue,
    cfrMapTcpHdrCompress INTEGER,
    cfrMapRtpHdrCompress INTEGER,
    cfrMapPayloadCompressType INTEGER
    }

cfrMapIndex OBJECT-TYPE
    SYNTAX INTEGER(1..999)
    ACCESS read-only
    STATUS mandatory
    DESCRIPTION
        "An arbitrary Index to the mapping information
        associated with a certain circuit. The maximum
        value is arbitrarily picked which is considered
        sufficient for usual configuration."
    ::= { cfrMapEntry 1 }

cfrMapProtocol OBJECT-TYPE
    SYNTAX CfrMapProtocols
--    Rsyntax INTEGER {
--        arp(1),
--        serialArp(6),
--        ip(7),
--        xns(10),
--        novell(11),
--        apollo(12),
--        vines(13),
--        appletalk(16),
--        ieeeSpanning(18),
--        decnet(22),
--        clns(25),
--        rsrb(37),
--        bridge(38),
--        stun(39),
--        frArp(40),
--        uncompressedTcp(47),
--        compressedTcp(48),
--        llc2(49),
--        frSwitch(53),
--        dlsw(63),
--        nhrp(74),
--        compressedRtp(83),
--        wildcard(999)
--        }
    ACCESS read-only
    STATUS mandatory
    DESCRIPTION
        "Mapping protocol for this circuit."
    ::= { cfrMapEntry 2 }

cfrMapAddress OBJECT-TYPE
    SYNTAX OCTET STRING(SIZE(0..64))
    ACCESS read-only
    STATUS mandatory
    DESCRIPTION
        "Mapping protocol address at remote end for
        this DLCI.
        NOTE: For point-to-point DLCI, the string is fixed
        to be point-to-point."
    ::= { cfrMapEntry 3 }

cfrMapType OBJECT-TYPE
    SYNTAX INTEGER {
        static(1),
        dynamic(2),
        svc(3)
        }
    ACCESS read-only
    STATUS mandatory
    DESCRIPTION
        "Type for the map creation."
    ::= { cfrMapEntry 4 }

cfrMapEncaps OBJECT-TYPE
    SYNTAX INTEGER {
        ietf(1),
        cisco(2)
        }
    ACCESS read-only
    STATUS mandatory
    DESCRIPTION
        "Indication of the encapsulation type for this
        mapping protocol."
    ::= { cfrMapEntry 5 }

cfrMapBroadcast OBJECT-TYPE
    SYNTAX TruthValue
--    Rsyntax INTEGER {
--        true(1),
--        false(2)
--        }
    ACCESS read-only
    STATUS mandatory
    DESCRIPTION
        "Broadcast enabled or disabled."
    ::= { cfrMapEntry 6 }

cfrMapPayloadCompress OBJECT-TYPE
    SYNTAX TruthValue
--    Rsyntax INTEGER {
--        true(1),
--        false(2)
--        }
    ACCESS read-only
    STATUS deprecated
    DESCRIPTION
        "Indicate if payload compression is enabled."
    ::= { cfrMapEntry 7 }

cfrMapTcpHdrCompress OBJECT-TYPE
    SYNTAX INTEGER {
        inapplicable(1),
        passive(2),
        active(3)
        }
    ACCESS read-only
    STATUS mandatory
    DESCRIPTION
        "TCP header compression type, if applicable."
    ::= { cfrMapEntry 8 }

cfrMapRtpHdrCompress OBJECT-TYPE
    SYNTAX INTEGER {
        inapplicable(1),
        passive(2),
        active(3)
        }
    ACCESS read-only
    STATUS mandatory
    DESCRIPTION
        "RTP header compression type, if applicable.
        The value 'passive' means that the header of an
        outgoing RTP/IP packet is compressed only if an
        incoming RTP/IP packet had a compressed header.
        The value 'active' means the header of every outgoing
        RTP/IP packet is compressed."
    ::= { cfrMapEntry 9 }

cfrMapPayloadCompressType OBJECT-TYPE
    SYNTAX INTEGER {
        inapplicable(1),
        cisco(2),
        frf9Software(3),
        frf9Hardware(4)
        }
    ACCESS read-only
    STATUS mandatory
    DESCRIPTION
        "FR payload compression type, if applicable.
        FRF.9 is the Frame Relay Forum Implementation Agreement
        on FR payload compression. The compression can be done
        by either software or hardware (when equipped with the
        supporting hardware), depending on configuration."
    REFERENCE
        "Frame Relay Forum document number FRF.9"
    ::= { cfrMapEntry 10 }

cfrSvcTable OBJECT-TYPE
    SYNTAX SEQUENCE OF CfrSvcEntry
    ACCESS not-accessible
    STATUS mandatory
    DESCRIPTION
        "Table of FR SVC specific, descriptive
        and statistics information."
    ::= { cfrSvcObjs 1 }

cfrSvcEntry OBJECT-TYPE
    SYNTAX CfrSvcEntry
    ACCESS not-accessible
    STATUS mandatory
    DESCRIPTION
        "Each entry of the table contains circuit information
        specific to a Frame Relay Switched Virtual Circuit."
    INDEX { frCircuitIfIndex, frCircuitDlci }
    ::= { cfrSvcTable 1 }

CfrSvcEntry ::= SEQUENCE {
    cfrSvcAddrLocal OCTET STRING,
    cfrSvcAddrRemote OCTET STRING,
    cfrSvcThroughputIn INTEGER,
    cfrSvcMinThruputOut INTEGER,
    cfrSvcMinThruputIn INTEGER,
    cfrSvcCommitBurstIn INTEGER,
    cfrSvcExcessBurstIn INTEGER,
    cfrSvcIdleTime INTEGER
    }

cfrSvcAddrLocal OBJECT-TYPE
    SYNTAX OCTET STRING(SIZE(0..64))
    ACCESS read-only
    STATUS mandatory
    DESCRIPTION
        "Local E.164/X.125 address for the circuit."
    ::= { cfrSvcEntry 1 }

cfrSvcAddrRemote OBJECT-TYPE
    SYNTAX OCTET STRING(SIZE(0..64))
    ACCESS read-only
    STATUS mandatory
    DESCRIPTION
        "Remote E.164/X.125 address for the circuit."
    ::= { cfrSvcEntry 2 }

cfrSvcThroughputIn OBJECT-TYPE
    SYNTAX INTEGER(9600..1544000)
--  Units
--    bits per second
    ACCESS read-only
    STATUS mandatory
    DESCRIPTION
        "Circuit's incoming throughput. For outgoing 
        throughput (commonly referred to as CIR) see
        frCircuitThroughput per RFC1315."
    ::= { cfrSvcEntry 3 }

cfrSvcMinThruputOut OBJECT-TYPE
    SYNTAX INTEGER(9600..1544000)
--  Units
--    bits per second
    ACCESS read-only
    STATUS deprecated
    DESCRIPTION
        "Circuit's outgoing minimal Throughput."
    ::= { cfrSvcEntry 4 }

cfrSvcMinThruputIn OBJECT-TYPE
    SYNTAX INTEGER(9600..1544000)
--  Units
--    bits per second
    ACCESS read-only
    STATUS deprecated
    DESCRIPTION
        "Circuit's incoming minimal Throughput."
    ::= { cfrSvcEntry 5 }

cfrSvcCommitBurstIn OBJECT-TYPE
    SYNTAX INTEGER(9600..1544000)
    ACCESS read-only
    STATUS mandatory
    DESCRIPTION
        "Circuit's incoming Committed Burst Rate.
        See ANSI and/or ITU specifications for
        definition and calculations. For outgoing
        CBR, see frCircuitCommittedBurst per RFC 1315."
    ::= { cfrSvcEntry 6 }

cfrSvcExcessBurstIn OBJECT-TYPE
    SYNTAX INTEGER(9600..2440000)
    ACCESS read-only
    STATUS mandatory
    DESCRIPTION
        "Circuit's incoming Excess Burst Rate.
        See ANSI and/or ITU specifications for
        definition and calculations. For outgoing
        EBR, see frCircuitExcessBurst per RFC 1315."
    ::= { cfrSvcEntry 7 }

cfrSvcIdleTime OBJECT-TYPE
    SYNTAX INTEGER
--  Units
--    seconds
    ACCESS read-only
    STATUS mandatory
    DESCRIPTION
        "Circuit's idle time period. If expires, the
        circuit is cleared."
    ::= { cfrSvcEntry 8 }

cfrElmiIpAddr OBJECT-TYPE
    SYNTAX IpAddress
    ACCESS read-only
    STATUS mandatory
    DESCRIPTION
        "This object represents the Management address of the
         device used for address registration. 
         Network management station can send management
         messages to this IP address. This can be 
         user configured address or the address of one of the
         interfaces on the device. If address registration is
         disabled then this will have a value of 0.0.0.0. 
         This object is accessible only if the ELMI protocol 
         is supported on the device"
    ::= { cfrElmiObjs 1 }

cfrElmiTable OBJECT-TYPE
    SYNTAX SEQUENCE OF CfrElmiEntry
    ACCESS not-accessible
    STATUS mandatory
    DESCRIPTION
        "Table of CISCO Frame Relay ELMI information that is
         specific to CISCO implementation"
    ::= { cfrElmiObjs 2 }

cfrElmiEntry OBJECT-TYPE
    SYNTAX CfrElmiEntry
    ACCESS not-accessible
    STATUS mandatory
    DESCRIPTION
        "Each entry of the table contains information about a
         physical interface. The table can be accessible only
         if the device supports ELMI protocol and if LMI is
         enabled on the interface."
    INDEX { ifIndex }
    ::= { cfrElmiTable 1 }

CfrElmiEntry ::= SEQUENCE {
    cfrElmiLinkStatus INTEGER,
    cfrElmiArStatus INTEGER,
    cfrElmiRemoteStatus INTEGER
    }

cfrElmiLinkStatus OBJECT-TYPE
    SYNTAX INTEGER {
        enabled(1),
        disabled(2)
        }
    ACCESS read-only
    STATUS mandatory
    DESCRIPTION
        "This variable states whether Enhanced Link Management
         Interface(ELMI) protocol is enabled or not on a 
         frame relay interface."
    ::= { cfrElmiEntry 1 }

cfrElmiArStatus OBJECT-TYPE
    SYNTAX INTEGER {
        enabled(1),
        disabled(2)
        }
    ACCESS read-only
    STATUS mandatory
    DESCRIPTION
        "This variable states whether the Enhanced Link
         Management Interface(ELMI) address registration(AR)
         mechanism is enabled or not on a frame relay 
         interface. A value of 1 indicates ELMI AR is 
         supported on the interface. A value of 2 indicates
         ELMI AR is supported but the user disabled the
         exchange of IP address and ifIndex with the
         neighboring device. This object doesn't have any
         significance if cfrElmiLinkStatus is disabled
         on the interface."
    ::= { cfrElmiEntry 2 }

cfrElmiRemoteStatus OBJECT-TYPE
    SYNTAX INTEGER {
        enabled(1),
        disabled(2)
        }
    ACCESS read-only
    STATUS mandatory
    DESCRIPTION
        "This variable states the Enhanced Link 
         Management(ELMI) status on the other end of the
         interface. If cfrElmiLinkStatus is enabled on the
         other end a value of 1 will be returned,
         else 2 will be returned. This object doesn't have any
         significance if cfrElmiLinkStatus is disabled on the
         interface"
    ::= { cfrElmiEntry 3 }

cfrElmiNeighborTable OBJECT-TYPE
    SYNTAX SEQUENCE OF CfrElmiNeighborEntry
    ACCESS not-accessible
    STATUS mandatory
    DESCRIPTION
        "Table of CISCO Frame Relay Neighbor ELMI information
         that is specific to CISCO implementation."
    ::= { cfrElmiObjs 3 }

cfrElmiNeighborEntry OBJECT-TYPE
    SYNTAX CfrElmiNeighborEntry
    ACCESS not-accessible
    STATUS mandatory
    DESCRIPTION
        "Each entry of the table contains information of the
         neighboring device connected to a physical interface.
         The entry will be present only if ELMI is enabled on
         the neighboring device interface. If the value of the
         cfrElmiRemoteStatus in the cfrElmiEntry is 1 then a 
         valid entry exists for the interface. If ELMI is not 
         supported on the remote end then, the neighbor 
         information for the interface will not be present"
    INDEX { ifIndex }
    ::= { cfrElmiNeighborTable 1 }

CfrElmiNeighborEntry ::= SEQUENCE {
    cfrElmiNeighborArStatus INTEGER,
    cfrElmiNeighborIpAddress IpAddress,
    cfrElmiNeighborIfIndex InterfaceIndex,
    cfrElmiNeighborVendorName DisplayString,
    cfrElmiNeighborPlatformName DisplayString,
    cfrElmiNeighborDeviceName DisplayString
    }

cfrElmiNeighborArStatus OBJECT-TYPE
    SYNTAX INTEGER {
        notsupported(1),
        enabled(2),
        disabled(3)
        }
    ACCESS read-only
    STATUS mandatory
    DESCRIPTION
        "This variable indicates the status of ELMI Address 
         registration(AR) on the neighboring device. A value 
         of 1 indicates ELMI AR is not supported on the 
         neighboring device. A value of 2 indicates ELMI AR is
         enabled on the interface. A value of 3 indicates AR is
         supported, but user disabled the exchange of IP 
         address and ifIndex with the neighbor."
    ::= { cfrElmiNeighborEntry 1 }

cfrElmiNeighborIpAddress OBJECT-TYPE
    SYNTAX IpAddress
    ACCESS read-only
    STATUS mandatory
    DESCRIPTION
        "The Management IP address of the neighboring device 
         to which the other end of this interface is 
         connected. Network management system can use this
         address to send management messages to the device.
         If address registration is not supported on the
         remote end then the value will be 0.0.0.0.
         NMS uses this object in the topology discovery of the
         network."
    ::= { cfrElmiNeighborEntry 2 }

cfrElmiNeighborIfIndex OBJECT-TYPE
    SYNTAX InterfaceIndex
--    Rsyntax INTEGER(1..2147483647)
    ACCESS read-only
    STATUS mandatory
    DESCRIPTION
        "The Interface index of the neighboring device to 
         which this interface is connected. If the value of
         cfrElmiNeighborArStatus is 2 then this will have a
         valid value. If the value of cfrElmiNeighborArStatus
         is 3 or 1 then value of this object will be 0. NMS
         uses this object in the topology discovery of the
         network."
    ::= { cfrElmiNeighborEntry 3 }

cfrElmiNeighborVendorName OBJECT-TYPE
    SYNTAX DisplayString
--    Rsyntax OCTET STRING(SIZE(0..255))
    ACCESS read-only
    STATUS mandatory
    DESCRIPTION
        "Vendor name of the neighboring device to which the
         other end of this interface is connected."
    ::= { cfrElmiNeighborEntry 4 }

cfrElmiNeighborPlatformName OBJECT-TYPE
    SYNTAX DisplayString
--    Rsyntax OCTET STRING(SIZE(0..255))
    ACCESS read-only
    STATUS mandatory
    DESCRIPTION
        "Platform name of the neighboring device to which the
         other end of this interface is connected."
    ::= { cfrElmiNeighborEntry 5 }

cfrElmiNeighborDeviceName OBJECT-TYPE
    SYNTAX DisplayString
--    Rsyntax OCTET STRING(SIZE(0..255))
    ACCESS read-only
    STATUS mandatory
    DESCRIPTION
        "Device name of the neighboring device to which the
         other end of this interface is connected."
    ::= { cfrElmiNeighborEntry 6 }

cfrFragTable OBJECT-TYPE
    SYNTAX SEQUENCE OF CfrFragEntry
    ACCESS not-accessible
    STATUS mandatory
    DESCRIPTION
        "Table of Frame Relay Fragmentation information. 
        These are specific to Cisco's implementation."
    ::= { cfrFragObjs 1 }

cfrFragEntry OBJECT-TYPE
    SYNTAX CfrFragEntry
    ACCESS not-accessible
    STATUS mandatory
    DESCRIPTION
        "Each entry of the table contains details of 
        fragmentation configured on  this circuit. "
    INDEX { frCircuitIfIndex, frCircuitDlci }
    ::= { cfrFragTable 1 }

CfrFragEntry ::= SEQUENCE {
    cfrFragSize INTEGER,
    cfrFragType DisplayString,
    cfrFragInPkts Counter,
    cfrFragOutPkts Counter,
    cfrFragInOctets Counter,
    cfrFragOutOctets Counter,
    cfrFragNotInPkts Counter,
    cfrFragNotOutPkts Counter,
    cfrFragNotInOctets Counter,
    cfrFragNotOutOctets Counter,
    cfrFragAssembledInPkts Counter,
    cfrFragAssembledInOctets Counter,
    cfrFragPreOutPkts Counter,
    cfrFragPreOutOctets Counter,
    cfrFragDroppedReAssembledInPkts Counter,
    cfrFragDroppedFragmentedOutPkts Counter,
    cfrFragTimeoutsIn INTEGER,
    cfrFragOutOfSeqFragPkts Counter,
    cfrFragUnexpectedBBitSetPkts Counter,
    cfrFragSeqMissedPkts Counter,
    cfrFragInterleavedOutPkts Counter
    }

cfrFragSize OBJECT-TYPE
    SYNTAX INTEGER(16..1600)
--  Units
--    octets
    ACCESS read-only
    STATUS mandatory
    DESCRIPTION
        "cfrFragSize defines the payload size of a fragment 
        and it excludes the FR headers and any FR fragmentation
        header."
    ::= { cfrFragEntry 1 }

cfrFragType OBJECT-TYPE
    SYNTAX DisplayString
--    Rsyntax OCTET STRING(SIZE(0..255))
    ACCESS read-only
    STATUS mandatory
    DESCRIPTION
        "Fragmentation type configured by the user. The types
        supported are end-to-end, VoFR-cisco and VoFR."
    ::= { cfrFragEntry 2 }

cfrFragInPkts OBJECT-TYPE
    SYNTAX Counter
--  Units
--    packets
    ACCESS read-only
    STATUS mandatory
    DESCRIPTION
        "Total number of frames received that have a 
        fragmentation header."
    ::= { cfrFragEntry 3 }

cfrFragOutPkts OBJECT-TYPE
    SYNTAX Counter
--  Units
--    packets
    ACCESS read-only
    STATUS mandatory
    DESCRIPTION
        "Total number of fragments that are transmitted with a
        fragmenation header."
    ::= { cfrFragEntry 4 }

cfrFragInOctets OBJECT-TYPE
    SYNTAX Counter
--  Units
--    octets
    ACCESS read-only
    STATUS mandatory
    DESCRIPTION
        "Total number of bytes received in frames that have a 
        fragmentation header. The number of bytes include the
        FR header."
    ::= { cfrFragEntry 5 }

cfrFragOutOctets OBJECT-TYPE
    SYNTAX Counter
--  Units
--    octets
    ACCESS read-only
    STATUS mandatory
    DESCRIPTION
        "Total number of bytes that are transmitted in frames
        with a fragmenation header. The number of bytes also
        includes the FR header."
    ::= { cfrFragEntry 6 }

cfrFragNotInPkts OBJECT-TYPE
    SYNTAX Counter
--  Units
--    packets
    ACCESS read-only
    STATUS mandatory
    DESCRIPTION
        "Total number of frames received that do not require 
        reassembly and therefore will not contain the 
        fragmentation header. This counter is valid only when
        end-to-end fragmentation type is set."
    ::= { cfrFragEntry 7 }

cfrFragNotOutPkts OBJECT-TYPE
    SYNTAX Counter
--  Units
--    packets
    ACCESS read-only
    STATUS mandatory
    DESCRIPTION
        "Total number of frames transmitted without fragmenting
        and therefore will not contain the fragmentation header.
        This counter is valid only when end-to-end fragmentation
        type is set."
    ::= { cfrFragEntry 8 }

cfrFragNotInOctets OBJECT-TYPE
    SYNTAX Counter
--  Units
--    octets
    ACCESS read-only
    STATUS mandatory
    DESCRIPTION
        "Total number of bytes received in frames that do not 
        require reassembly and therefore will not contain the 
        fragmentation header. This counter is valid only when
        end-to-end fragmentation type is set."
    ::= { cfrFragEntry 9 }

cfrFragNotOutOctets OBJECT-TYPE
    SYNTAX Counter
--  Units
--    octets
    ACCESS read-only
    STATUS mandatory
    DESCRIPTION
        "Total number of bytes transmitted in frames that are
        not fragmented and therefore will not contain the 
        fragmentation header. This counter is valid only when 
        end-to-end fragmentation type is set."
    ::= { cfrFragEntry 10 }

cfrFragAssembledInPkts OBJECT-TYPE
    SYNTAX Counter
--  Units
--    packets
    ACCESS read-only
    STATUS mandatory
    DESCRIPTION
        "Total number of fully reassembled frames. It also 
        counts the number of packets received without FR 
        fragmentation header (i.e. in un-fragmentated pkts)."
    ::= { cfrFragEntry 11 }

cfrFragAssembledInOctets OBJECT-TYPE
    SYNTAX Counter
--  Units
--    octets
    ACCESS read-only
    STATUS mandatory
    DESCRIPTION
        "Total number of bytes received in fully reassembled 
        frames. It also counts the number of packets received
        without FR fragmentation header (i.e.in un-fragmentated
        pkts)."
    ::= { cfrFragEntry 12 }

cfrFragPreOutPkts OBJECT-TYPE
    SYNTAX Counter
--  Units
--    packets
    ACCESS read-only
    STATUS mandatory
    DESCRIPTION
        "Total number of frames fragmented and trasmitted. It 
        also counts the number of packets trasmitted without FR
        fragmentation header (i.e. in un-fragmentated pkts)."
    ::= { cfrFragEntry 13 }

cfrFragPreOutOctets OBJECT-TYPE
    SYNTAX Counter
--  Units
--    octets
    ACCESS read-only
    STATUS mandatory
    DESCRIPTION
        "Total number of bytes transmitted in fragmented frames.
        It also counts the number of bytes trasmitted in frames
        without FR fragmentation header (i.e. in un-fragmentated
        pkts)."
    ::= { cfrFragEntry 14 }

cfrFragDroppedReAssembledInPkts OBJECT-TYPE
    SYNTAX Counter
--  Units
--    packets
    ACCESS read-only
    STATUS mandatory
    DESCRIPTION
        "Number of received fragments dropped for reasons such
        as : running out of memory, receiving segments out of 
        sequence, receiving an unexpected frame with a B bit 
        set, timing out on a reassembling frame."
    ::= { cfrFragEntry 15 }

cfrFragDroppedFragmentedOutPkts OBJECT-TYPE
    SYNTAX Counter
--  Units
--    packets
    ACCESS read-only
    STATUS mandatory
    DESCRIPTION
        "Number of fragments dropped because of running 
        out of memory."
    ::= { cfrFragEntry 16 }

cfrFragTimeoutsIn OBJECT-TYPE
    SYNTAX INTEGER(0..1000)
    ACCESS read-only
    STATUS mandatory
    DESCRIPTION
        "Number of reassemble timer timeouts for this circuit.
        A frame requiring more than two minutes to fully 
        reassemble is dropped and timeout will be incremented
        by one."
    ::= { cfrFragEntry 17 }

cfrFragOutOfSeqFragPkts OBJECT-TYPE
    SYNTAX Counter
--  Units
--    packets
    ACCESS read-only
    STATUS mandatory
    DESCRIPTION
        "Indicates the total number of packets received with an
        unexpected sequence number. All fragments being 
        reassembled are dropped. Start a new packet with the
        received segment only if the B bit is set on the 
        segment. Otherwise the new segment is also dropped."
    ::= { cfrFragEntry 18 }

cfrFragUnexpectedBBitSetPkts OBJECT-TYPE
    SYNTAX Counter
--  Units
--    packets
    ACCESS read-only
    STATUS mandatory
    DESCRIPTION
        "Number of fragments received in this circuit with 
        a B bit set. All fragments being reassembled are dropped
        and a new packet is started with this segment."
    ::= { cfrFragEntry 19 }

cfrFragSeqMissedPkts OBJECT-TYPE
    SYNTAX Counter
--  Units
--    packets
    ACCESS read-only
    STATUS mandatory
    DESCRIPTION
        "Number of fragments received in this circuit with 
        skipped sequence number."
    ::= { cfrFragEntry 20 }

cfrFragInterleavedOutPkts OBJECT-TYPE
    SYNTAX Counter
--  Units
--    packets
    ACCESS read-only
    STATUS mandatory
    DESCRIPTION
        "Number of packets that have been interleaved between 
        segments."
    ::= { cfrFragEntry 21 }

cfrConnectionTable OBJECT-TYPE
    SYNTAX SEQUENCE OF CfrConnectionEntry
    ACCESS not-accessible
    STATUS mandatory
    DESCRIPTION
        "Table of Frame Relay/Frame Relay and Frame Relay/ATM
        Network/Service Interworking connection information. 
        These are specific to Cisco's implementation."
    ::= { cfrConnectionObjs 1 }

cfrConnectionEntry OBJECT-TYPE
    SYNTAX CfrConnectionEntry
    ACCESS not-accessible
    STATUS mandatory
    DESCRIPTION
        "Each entry of the table contains information of a
        connection that is established for Frame Relay/Frame 
        Relay and Frame Relay/ATM Network/Service Interworking."
    INDEX { frCircuitIfIndex, frCircuitDlci }
    ::= { cfrConnectionTable 1 }

CfrConnectionEntry ::= SEQUENCE {
    cfrConnName DisplayString,
    cfrConnID INTEGER,
    cfrConnState DisplayString,
    cfrConnSegment1Name DisplayString,
    cfrConnSegment1VCGroup DisplayString,
    cfrConnSegment1Dlci DlciNumber,
    cfrConnSegment2Name DisplayString,
    cfrConnSegment2Vpi INTEGER,
    cfrConnSegment2Vci INTEGER,
    cfrConnServiceTranslation INTEGER,
    cfrConnFrSscsDlci DlciNumber,
    cfrConnEfciBit INTEGER,
    cfrConnDeBit INTEGER,
    cfrConnClpBit INTEGER
    }

cfrConnName OBJECT-TYPE
    SYNTAX DisplayString
--    Rsyntax OCTET STRING(SIZE(0..255))
    ACCESS read-only
    STATUS mandatory
    DESCRIPTION
        "The textual name of a for FR/FR or FR/ATM  
        Network/Service Interworking connection."
    ::= { cfrConnectionEntry 1 }

cfrConnID OBJECT-TYPE
    SYNTAX INTEGER(1..2000)
    ACCESS read-only
    STATUS mandatory
    DESCRIPTION
        "The numerical identifier of a FR/FR or FR/ATM  
        Network/Service Interworking connection."
    ::= { cfrConnectionEntry 2 }

cfrConnState OBJECT-TYPE
    SYNTAX DisplayString
--    Rsyntax OCTET STRING(SIZE(0..255))
    ACCESS read-only
    STATUS mandatory
    DESCRIPTION
        "Status of a FR/FR or FR/ATM  Network/Service 
        Interworking connection."
    ::= { cfrConnectionEntry 3 }

cfrConnSegment1Name OBJECT-TYPE
    SYNTAX DisplayString
--    Rsyntax OCTET STRING(SIZE(0..255))
    ACCESS read-only
    STATUS mandatory
    DESCRIPTION
        "The textual name used to identify the first segment of 
        a FR/FR or FR/ATM  Network/Service Interworking 
        connection."
    ::= { cfrConnectionEntry 4 }

cfrConnSegment1VCGroup OBJECT-TYPE
    SYNTAX DisplayString
--    Rsyntax OCTET STRING(SIZE(0..255))
    ACCESS read-only
    STATUS mandatory
    DESCRIPTION
        "The textual name used to identify the VC-Group in the
        first segment of a Frame Relay/ATM  Network Interworking
        (FRF.5)connection. 
        This field is not applicabe in case of,
                 FRF.8 (Frame Relay/ATM  Service Interworking)
                 and
                 FR-FR connectione. "
    ::= { cfrConnectionEntry 5 }

cfrConnSegment1Dlci OBJECT-TYPE
    SYNTAX DlciNumber
--    Rsyntax INTEGER(0..1023)
    ACCESS read-only
    STATUS mandatory
    DESCRIPTION
        "The DLCI used as the first segment of a FR-FR or FR-ATM
        Network/Service Interworking connection."
    ::= { cfrConnectionEntry 6 }

cfrConnSegment2Name OBJECT-TYPE
    SYNTAX DisplayString
--    Rsyntax OCTET STRING(SIZE(0..255))
    ACCESS read-only
    STATUS mandatory
    DESCRIPTION
        "The interface on which second segment of a FR-FR or 
        FR-ATM  Network/Service Interworking connection is 
        configured."
    ::= { cfrConnectionEntry 7 }

cfrConnSegment2Vpi OBJECT-TYPE
    SYNTAX INTEGER(0..4095)
    ACCESS read-only
    STATUS mandatory
    DESCRIPTION
        "The value of  VPI, in the ATM connection, used as the
        second segment of a FR-ATM  Network/Service Interworking
        connection. In case of FR-FR connection, the same will 
        be used to display the DLCI used as the second segment."
    ::= { cfrConnectionEntry 8 }

cfrConnSegment2Vci OBJECT-TYPE
    SYNTAX INTEGER(0..4095)
    ACCESS read-only
    STATUS mandatory
    DESCRIPTION
        "The value of  VCI, in the ATM connection, used as the
        second segment of a FR-ATM  Network/Service Interworking
        connection. In case of FR-FR connection, this is not 
        supported."
    ::= { cfrConnectionEntry 9 }

cfrConnServiceTranslation OBJECT-TYPE
    SYNTAX INTEGER {
        serviceTranslationEnabled(1),
        serviceTranslationNotEnabled(2)
        }
    ACCESS read-only
    STATUS mandatory
    DESCRIPTION
        "Shows whether Service Translation Mode is supported or
        not. Translation Mode is the interworking of 
        internetworking (routed and/or bridged) protocols used 
        in FR-ATM  Service PVC Interworking(FRF.8).
        This is not supported in case of FRF.5 (FR-ATM network
        Interworking) and FR-FR connections."
    ::= { cfrConnectionEntry 10 }

cfrConnFrSscsDlci OBJECT-TYPE
    SYNTAX DlciNumber
--    Rsyntax INTEGER(0..1023)
    ACCESS read-only
    STATUS mandatory
    DESCRIPTION
        "The DLCI value used at the FR-SSCS layer. This is one of
        connection multiplexing methods used in Frame Relay/ATM  
        Network Interworking.
        Not supported in case of FRF.8 (FR-ATM Service PVC 
        Interworking) and FR-FR connections"
    ::= { cfrConnectionEntry 11 }

cfrConnEfciBit OBJECT-TYPE
    SYNTAX INTEGER {
        mapFecn(1),
        notMapFecn(2)
        }
    ACCESS read-only
    STATUS mandatory
    DESCRIPTION
        "Shows whether the FECN field in the FR frame is mapped 
        to the ATM EFCI field of every cell generated out of the 
        FR frame. This is used to indicate congestion in FR to
        ATM direction in case of Frame Relay/ATM  Service PVC 
        Interworking.
        Not supported in FRF.5 (Frame Relay/ATM Network 
        Interworking and FR-FR connections."
    ::= { cfrConnectionEntry 12 }

cfrConnDeBit OBJECT-TYPE
    SYNTAX INTEGER {
        noMapClp(1),
        mapClp(2),
        setDe0(3),
        setDe1(4)
        }
    ACCESS read-only
    STATUS mandatory
    DESCRIPTION
        "The method of operation for loss priority mapping in the
        B-ISDN to FR direction..
        Not supported in case of FR-FR connection."
    ::= { cfrConnectionEntry 13 }

cfrConnClpBit OBJECT-TYPE
    SYNTAX INTEGER {
        setClpTo0AndCopyDeToFrsscsDe(1),
        setClpTo1AndCopyDeToFrsscsDe(2),
        copyDeToFrsscsDeAndClp(3),
        copyDeToClp(4),
        setClp1(5),
        setClp0(6)
        }
    ACCESS read-only
    STATUS mandatory
    DESCRIPTION
        "The method of operation used to map loss priority
        mapping in the FR to ATM direction.
        Not supported in case of FR-FR connection."
    ::= { cfrConnectionEntry 14 }

ciscoFrMIBGroup OBJECT IDENTIFIER ::= { ciscoFrMIBGroups 1 }
-- OBJECT-GROUP
--  Status
--    deprecated
--  Descr
--    The compliance statement for entities which implement
--    this Cisco Frame Relay MIB.
--  objects
--    cfrLmiLinkstatus, cfrLmiLinkType, cfrLmiEnquiryIns, 
--    cfrLmiEnquiryOuts, cfrLmiStatusIns, cfrLmiStatusOuts, 
--    cfrLmiUpdateStatusIns, cfrLmiUpdateStatusOuts, 
--    cfrLmiStatusTimeouts, cfrLmiStatusEnqTimeouts, cfrLmiN392Dce, 
--    cfrLmiN393Dce, cfrLmiT392Dce, cfrCircuitDEins, 
--    cfrCircuitDEouts, cfrCircuitDropPktsOuts, cfrCircuitType, 
--    cfrExtCircuitIfName, cfrExtCircuitIfType, 
--    cfrExtCircuitSubifIndex, cfrExtCircuitMapStatus, 
--    cfrExtCircuitCreateType, cfrExtCircuitMulticast, 
--    cfrExtCircuitRoutedDlci, cfrExtCircuitRoutedIf, cfrMapIndex, 
--    cfrMapProtocol, cfrMapAddress, cfrMapType, cfrMapEncaps, 
--    cfrMapBroadcast, cfrMapPayloadCompress, cfrMapTcpHdrCompress, 
--    cfrSvcAddrLocal, cfrSvcAddrRemote, cfrSvcThroughputIn, 
--    cfrSvcMinThruputOut, cfrSvcMinThruputIn, cfrSvcCommitBurstIn, 
--    cfrSvcExcessBurstIn, cfrSvcIdleTime

ciscoFrMIBGroupRev1 OBJECT IDENTIFIER ::= { ciscoFrMIBGroups 2 }
-- OBJECT-GROUP
--  Status
--    deprecated
--  Descr
--    A collection of objects providing router's
--    Frame Relay configuration and statistics
--    information that are additional to the IETF
--    standard Frame Relay DTE MIB.
--  objects
--    cfrLmiLinkstatus, cfrLmiLinkType, cfrLmiEnquiryIns, 
--    cfrLmiEnquiryOuts, cfrLmiStatusIns, cfrLmiStatusOuts, 
--    cfrLmiUpdateStatusIns, cfrLmiUpdateStatusOuts, 
--    cfrLmiStatusTimeouts, cfrLmiStatusEnqTimeouts, cfrLmiN392Dce, 
--    cfrLmiN393Dce, cfrLmiT392Dce, cfrCircuitDEins, 
--    cfrCircuitDEouts, cfrCircuitDropPktsOuts, cfrCircuitType, 
--    cfrExtCircuitIfName, cfrExtCircuitIfType, 
--    cfrExtCircuitSubifIndex, cfrExtCircuitMapStatus, 
--    cfrExtCircuitCreateType, cfrExtCircuitMulticast, 
--    cfrExtCircuitRoutedDlci, cfrExtCircuitRoutedIf, 
--    cfrExtCircuitUncompressIns, cfrExtCircuitUncompressOuts, 
--    cfrMapIndex, cfrMapProtocol, cfrMapAddress, cfrMapType, 
--    cfrMapEncaps, cfrMapBroadcast, cfrMapTcpHdrCompress, 
--    cfrMapRtpHdrCompress, cfrMapPayloadCompressType, 
--    cfrSvcAddrLocal, cfrSvcAddrRemote, cfrSvcThroughputIn, 
--    cfrSvcMinThruputOut, cfrSvcMinThruputIn, cfrSvcCommitBurstIn, 
--    cfrSvcExcessBurstIn, cfrSvcIdleTime

ciscoFrLmiMIBGroup OBJECT IDENTIFIER ::= { ciscoFrMIBGroups 3 }
-- OBJECT-GROUP
--  Status
--    mandatory
--  Descr
--    A collection of objects providing router's
--     Frame Relay LMI configuration and statistics
--     information either supplemental to the 
--     frDlcmiTable of RFC 1315 or specific to Cisco's 
--     implementation.
--  objects
--    cfrLmiLinkstatus, cfrLmiLinkType, cfrLmiEnquiryIns, 
--    cfrLmiEnquiryOuts, cfrLmiStatusIns, cfrLmiStatusOuts, 
--    cfrLmiUpdateStatusIns, cfrLmiUpdateStatusOuts, 
--    cfrLmiStatusTimeouts, cfrLmiStatusEnqTimeouts, cfrLmiN392Dce, 
--    cfrLmiN393Dce, cfrLmiT392Dce

ciscoFrCircuitMIBGroup OBJECT IDENTIFIER ::= { ciscoFrMIBGroups 4 }
-- OBJECT-GROUP
--  Status
--    mandatory
--  Descr
--    A collection of objects providing information of a
--    circuit that are not included in frCircuitTable of
--    RFC1315 but are generic to Frame Relay.
--  objects
--    cfrCircuitDEins, cfrCircuitDEouts, cfrCircuitDropPktsOuts, 
--    cfrCircuitType

ciscoExtCircuitMIBGroup OBJECT IDENTIFIER ::= { ciscoFrMIBGroups 5 }
-- OBJECT-GROUP
--  Status
--    deprecated
--  Descr
--    A collection of objects that provide Cisco 
--    implementation specific FR circuit information. 
--    This is a Cisco extension for the frCircuitTable 
--    of RFC 1315.
--  objects
--    cfrExtCircuitIfName, cfrExtCircuitIfType, 
--    cfrExtCircuitSubifIndex, cfrExtCircuitMapStatus, 
--    cfrExtCircuitCreateType, cfrExtCircuitMulticast, 
--    cfrExtCircuitRoutedDlci, cfrExtCircuitRoutedIf, 
--    cfrExtCircuitUncompressIns, cfrExtCircuitUncompressOuts, 
--    cfrExtCircuitFECNOuts, cfrExtCircuitBECNOuts, 
--    cfrExtCircuitMinThruputOut, cfrExtCircuitMinThruputIn, 
--    cfrExtCircuitBcastPktOuts, cfrExtCircuitBcastByteOuts, 
--    cfrExtCircuitBandwidth

ciscoExtCircuitMIBGroup1 OBJECT IDENTIFIER ::= { ciscoFrMIBGroups 13 }
-- OBJECT-GROUP
--  Status
--    mandatory
--  Descr
--    A collection of objects that provide Cisco
--    implementation specific FR circuit information.
--    This is a Cisco extension for the frCircuitTable
--    of RFC 1315.
--  objects
--    cfrExtCircuitIfName, cfrExtCircuitIfType, 
--    cfrExtCircuitSubifIndex, cfrExtCircuitMapStatus, 
--    cfrExtCircuitCreateType, cfrExtCircuitMulticast, 
--    cfrExtCircuitRoutedDlci, cfrExtCircuitRoutedIf, 
--    cfrExtCircuitUncompressIns, cfrExtCircuitUncompressOuts, 
--    cfrExtCircuitFECNOuts, cfrExtCircuitBECNOuts, 
--    cfrExtCircuitMinThruputOut, cfrExtCircuitMinThruputIn, 
--    cfrExtCircuitBcastPktOuts, cfrExtCircuitBcastByteOuts, 
--    cfrExtCircuitBandwidth, cfrExtCircuitTxDataRate, 
--    cfrExtCircuitTxPktRate, cfrExtCircuitRcvDataRate, 
--    cfrExtCircuitRcvPktRate

ciscoFrTsMIBGroup OBJECT IDENTIFIER ::= { ciscoFrMIBGroups 6 }
-- OBJECT-GROUP
--  Status
--    mandatory
--  Descr
--    A collection of objects that provide information
--    about Frame Relay Traffic Shaping. These are 
--    additional to the IETF standard Frame Relay DTE MIB.
--  objects
--    cfrExtCircuitShapeByteLimit, cfrExtCircuitShapeInterval, 
--    cfrExtCircuitShapeByteIncrement, cfrExtCircuitShapePkts, 
--    cfrExtCircuitShapeBytes, cfrExtCircuitShapePktsDelay, 
--    cfrExtCircuitShapeBytesDelay, cfrExtCircuitShapeActive, 
--    cfrExtCircuitShapeAdapting

ciscoFrMapMIBGroup OBJECT IDENTIFIER ::= { ciscoFrMIBGroups 7 }
-- OBJECT-GROUP
--  Status
--    mandatory
--  Descr
--    A collection of objects to provide mapping 
--    information of a Frame Relay virtual circuit.
--    These are additional to the IETF standard 
--    Frame Relay DTE MIB.
--  objects
--    cfrMapIndex, cfrMapProtocol, cfrMapAddress, cfrMapType, 
--    cfrMapEncaps, cfrMapBroadcast, cfrMapTcpHdrCompress, 
--    cfrMapRtpHdrCompress, cfrMapPayloadCompressType

ciscoFrSvcMIBGroup OBJECT IDENTIFIER ::= { ciscoFrMIBGroups 8 }
-- OBJECT-GROUP
--  Status
--    mandatory
--  Descr
--    A collection of objects to provide circuit
--    information specific to a Frame Relay Switched
--    Virtual Circuit.This is in addition to the IETF 
--    standard Frame Relay DTE MIB.
--  objects
--    cfrSvcAddrLocal, cfrSvcAddrRemote, cfrSvcThroughputIn, 
--    cfrSvcCommitBurstIn, cfrSvcExcessBurstIn, cfrSvcIdleTime

ciscoFrElmiMIBGroup OBJECT IDENTIFIER ::= { ciscoFrMIBGroups 9 }
-- OBJECT-GROUP
--  Status
--    deprecated
--  Descr
--    A collection of objects providing router's
--    ELMI information.
--  objects
--    cfrElmiIpAddr, cfrElmiArStatus, cfrElmiRemoteStatus, 
--    cfrElmiNeighborArStatus, cfrElmiNeighborIpAddress, 
--    cfrElmiNeighborIfIndex, cfrElmiNeighborVendorName, 
--    cfrElmiNeighborPlatformName, cfrElmiNeighborDeviceName

ciscoFrElmiMIBGroup1 OBJECT IDENTIFIER ::= { ciscoFrMIBGroups 10 }
-- OBJECT-GROUP
--  Status
--    mandatory
--  Descr
--    A collection of objects providing router's
--    ELMI information.
--  objects
--    cfrElmiIpAddr, cfrElmiArStatus, cfrElmiRemoteStatus, 
--    cfrElmiNeighborArStatus, cfrElmiNeighborIpAddress, 
--    cfrElmiNeighborIfIndex, cfrElmiNeighborVendorName, 
--    cfrElmiNeighborPlatformName, cfrElmiNeighborDeviceName, 
--    cfrElmiLinkStatus

ciscoFrFragMIBGroup OBJECT IDENTIFIER ::= { ciscoFrMIBGroups 11 }
-- OBJECT-GROUP
--  Status
--    mandatory
--  Descr
--    A collection of objects providing router's
--    fragmentation information.
--  objects
--    cfrFragSize, cfrFragType, cfrFragInPkts, cfrFragOutPkts, 
--    cfrFragInOctets, cfrFragOutOctets, cfrFragNotInPkts, 
--    cfrFragNotOutPkts, cfrFragNotInOctets, cfrFragNotOutOctets, 
--    cfrFragAssembledInPkts, cfrFragAssembledInOctets, 
--    cfrFragPreOutPkts, cfrFragPreOutOctets, 
--    cfrFragDroppedReAssembledInPkts, 
--    cfrFragDroppedFragmentedOutPkts, cfrFragTimeoutsIn, 
--    cfrFragOutOfSeqFragPkts, cfrFragUnexpectedBBitSetPkts, 
--    cfrFragSeqMissedPkts, cfrFragInterleavedOutPkts

ciscoFrConnMIBGroup OBJECT IDENTIFIER ::= { ciscoFrMIBGroups 12 }
-- OBJECT-GROUP
--  Status
--    mandatory
--  Descr
--    A collection of objects providing router's
--    fragmentation information.
--  objects
--    cfrConnName, cfrConnID, cfrConnState, cfrConnSegment1Name, 
--    cfrConnSegment1VCGroup, cfrConnSegment1Dlci, 
--    cfrConnSegment2Name, cfrConnSegment2Vpi, cfrConnSegment2Vci, 
--    cfrConnServiceTranslation, cfrConnFrSscsDlci, cfrConnEfciBit, 
--    cfrConnDeBit, cfrConnClpBit

ciscoFrMIBCompliance OBJECT IDENTIFIER ::= { ciscoFrMIBCompliances 1 }
-- MODULE-COMPLIANCE
--  Status
--    obsolete
--  Descr
--    The compliance statement for entities which implement
--    this Cisco Frame Relay MIB.
--  Module
--    >>current<<
--   MandGroup
--    ciscoFrMIBGroup

ciscoFrMIBCompliancesRev1 OBJECT IDENTIFIER ::= { ciscoFrMIBCompliances 2 }
-- MODULE-COMPLIANCE
--  Status
--    obsolete
--  Descr
--    The compliance statement for entities which implement
--    this Cisco Frame Relay MIB.
--  Module
--    >>current<<
--   MandGroup
--    ciscoFrMIBGroupRev1

ciscoFrMIBCompliancesRev2 OBJECT IDENTIFIER ::= { ciscoFrMIBCompliances 3 }
-- MODULE-COMPLIANCE
--  Status
--    obsolete
--  Descr
--    The compliance statement for entities which implement
--    this Cisco Frame Relay MIB.
--  Module
--    >>current<<
--   MandGroup
--    ciscoFrLmiMIBGroup
--   MandGroup
--    ciscoFrCircuitMIBGroup
--   MandGroup
--    ciscoExtCircuitMIBGroup
--   MandGroup
--    ciscoFrTsMIBGroup
--   MandGroup
--    ciscoFrMapMIBGroup
--   MandGroup
--    ciscoFrSvcMIBGroup

ciscoFrMIBCompliancesRev3 OBJECT IDENTIFIER ::= { ciscoFrMIBCompliances 4 }
-- MODULE-COMPLIANCE
--  Status
--    deprecated
--  Descr
--    The compliance statement for entities which implement
--    this Cisco Frame Relay MIB.
--  Module
--    >>current<<
--   MandGroup
--    ciscoFrLmiMIBGroup
--   MandGroup
--    ciscoFrCircuitMIBGroup
--   MandGroup
--    ciscoExtCircuitMIBGroup
--   MandGroup
--    ciscoFrTsMIBGroup
--   MandGroup
--    ciscoFrMapMIBGroup
--   MandGroup
--    ciscoFrSvcMIBGroup
--   MandGroup
--    ciscoFrElmiMIBGroup

ciscoFrMIBCompliancesRev4 OBJECT IDENTIFIER ::= { ciscoFrMIBCompliances 5 }
-- MODULE-COMPLIANCE
--  Status
--    mandatory
--  Descr
--    The compliance statement for entities which implement
--    this Cisco Frame Relay MIB.
--  Module
--    >>current<<
--   MandGroup
--    ciscoFrLmiMIBGroup
--   MandGroup
--    ciscoFrCircuitMIBGroup
--   MandGroup
--    ciscoExtCircuitMIBGroup1
--   MandGroup
--    ciscoFrTsMIBGroup
--   MandGroup
--    ciscoFrMapMIBGroup
--   MandGroup
--    ciscoFrSvcMIBGroup
--   MandGroup
--    ciscoFrElmiMIBGroup1
--   MandGroup
--    ciscoFrFragMIBGroup
--   MandGroup
--    ciscoFrConnMIBGroup


END
