-- MIB file created 26-Aug-2008 17:40:10, by
--   SMICng version 2.2.11-beta(PRO)(Solaris), January 20, 2001. Enterprise key cisco.com

IPV6-FLOW-LABEL-MIB DEFINITIONS ::= BEGIN

-- From file: "IPV6-FLOW-LABEL-MIB.my"
-- Compile options "4 7 F H N O W 03 06 0B 0G 0N 0T"

IMPORTS
    mib-2
            FROM SNMPv2-SMI-v1;

ipv6FlowLabelMIB OBJECT IDENTIFIER ::= { mib-2 103 }
-- MODULE-IDENTITY
--  LastUpdated
--    200308280000Z
--  OrgName
--    IETF Operations and Management Area
--  ContactInfo
--    Bert Wijnen (Editor) 
--     Lucent Technologies 
--     Schagen 33 
--     3461 GL Linschoten 
--     Netherlands 
--     Phone: +31 348-407-775 
--     EMail: bwijnen@lucent.com 
--    
--     Send comments to <mibs@ops.ietf.org>. 
--  Descr
--    This MIB module provides commonly used textual 
--     conventions for IPv6 Flow Labels. 
--    
--     Copyright (C) The Internet Society (2003).  This 
--     version of this MIB module is part of RFC 3595, 
--     see the RFC itself for full legal notices. 
--  RevDate
--    200308280000Z
--  RevDescr
--    Initial version, published as RFC 3595.

IPv6FlowLabel ::= INTEGER(0..1048575)
-- TEXTUAL-CONVENTION
--  DspHint
--    d
--  Status
--    mandatory
--  Descr
--    The flow identifier or Flow Label in an IPv6 
--     packet header that may be used to discriminate 
--     traffic flows. 
--  Refer
--    Internet Protocol, Version 6 (IPv6) specification, 
--     section 6.  RFC 2460. 

IPv6FlowLabelOrAny ::= INTEGER(-1|0..1048575)
-- TEXTUAL-CONVENTION
--  DspHint
--    d
--  Status
--    mandatory
--  Descr
--    The flow identifier or Flow Label in an IPv6 
--     packet header that may be used to discriminate 
--     traffic flows.  The value of -1 is used to 
--     indicate a wildcard, i.e. any value. 


END
