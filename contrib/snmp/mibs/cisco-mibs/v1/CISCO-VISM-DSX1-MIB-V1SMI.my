-- MIB file created 29-Nov-2005 10:33:50, by
--   SMICng version 2.2.11-beta(PRO)(Solaris), January 20, 2001. Enterprise key cisco.com

CISCO-VISM-DSX1-MIB DEFINITIONS ::= BEGIN

-- From file: "CISCO-VISM-DSX1-MIB.my"
-- Compile options "4 7 F H N O W 03 06 0B 0G 0N 0T"

IMPORTS
    DisplayString, TruthValue, TimeStamp
            FROM SNMPv2-TC-v1
    dsx1
            FROM BASIS-MIB
    dsx1AlmGrp
            FROM CISCO-MGX82XX-DSX1-MIB
    ciscoWan
            FROM CISCOWAN-SMI
    Counter, Gauge
            FROM RFC1155-SMI
    OBJECT-TYPE
            FROM RFC-1212;

ciscoVismDsx1MIB OBJECT IDENTIFIER ::= { ciscoWan 79 }
-- MODULE-IDENTITY
--  LastUpdated
--    200509300000Z
--  OrgName
--    Cisco Systems, Inc.
--  ContactInfo
--    Cisco Systems
--     Customer Service
--    
--     Postal: 170 W Tasman Drive
--             San Jose, CA  95134
--             USA
--    
--     Tel: +1 800 553-NETS
--    
--     E-mail: cs-wanatm@cisco.com
--  Descr
--    The MIB module to configure DS1/E1 interface 
--     objects in a Voice Interworking Service Module
--     (VISM) module. This MIB is an extension
--     to CISCO-MGX82XX-DSX1-MIB for DS1/E1 configuration
--     in VISM.
--    
--     Terms used:
--     CID:  Channel Identifier
--     CAS:  Channel Associated Signaling
--     CCS:  Common Channel Signaling
--     DTMF: Dual Tone Multi Frequency
--     NSE:  Name Signal Event
--     NTE:  Name Telephony Event
--     PVC:  Permanent Virtual Circuit
--  RevDate
--    200509300000Z
--  RevDescr
--    Added new objects:
--       - vismDsx1AlarmLogEnable
--       - vismDsx1AlarmLogAdminTimer
--       - vismDsx1AlarmLogOperTimer
--       - vismDsx1ElectricalSignalEnable
--  RevDate
--    200501200000Z
--  RevDescr
--    Added new object:
--       - vismDsx1V110Enable
--  RevDate
--    200404160000Z
--  RevDescr
--    Added new objects
--       - dsx1TxUncontrolledSlips
--       - dsx1RxUncontrolledSlips
--       - dsx1TxFrameSlips
--       - dsx1RxFrameSlips
--       - vismDsx1TotalTxUncontrolledSlips
--       - vismDsx1TotalTxFrameSlips
--       - vismDsx1TotalRxUncontrolledSlips
--       - vismDsx1TotalRxFrameSlips
--       The above counters maintain slip 
--       statistics for the system.
--       - vismSlipCntDiscontinuityTime
--       
--  RevDate
--    200403090000Z
--  RevDescr
--    Added new object
--       - vismBearerBusyCode
--  RevDate
--    200402170000Z
--  RevDescr
--    The following MIB are deprecated prior to SMIv2
--     conversion, vismEcanToneDisable, vismEcanCnfNRN
--     and vismCadenceTime.
--  RevDate
--    200402150000Z
--  RevDescr
--    Initial version of the MIB.
--    
--     The content of this MIB was originally available
--     in SMIv1 version. The MIB has been converted to
--     SMIv2 version and descriptions of some of the
--     objects have been modified.

dsx1Vism        OBJECT IDENTIFIER ::= { dsx1 5 }
dsx1VismCnfGrp  OBJECT IDENTIFIER ::= { dsx1Vism 1 }
dsx1VismStatsGrp OBJECT IDENTIFIER ::= { dsx1Vism 2 }
cvDsx1MIBConformance OBJECT IDENTIFIER ::= { ciscoVismDsx1MIB 2 }
cvDsx1MIBGroups OBJECT IDENTIFIER ::= { cvDsx1MIBConformance 1 }
cvDsx1MIBCompliances OBJECT IDENTIFIER ::= { cvDsx1MIBConformance 2 }

dsx1VismCnfGrpTable OBJECT-TYPE
    SYNTAX SEQUENCE OF Dsx1VismCnfGrpEntry
    ACCESS not-accessible
    STATUS mandatory
    DESCRIPTION
        "The VISM specific DS1/E1 configuration table. This table
         contains the additional VISM configuration information
         for DS1/E1."
    ::= { dsx1VismCnfGrp 1 }

dsx1VismCnfGrpEntry OBJECT-TYPE
    SYNTAX Dsx1VismCnfGrpEntry
    ACCESS not-accessible
    STATUS mandatory
    DESCRIPTION
        "An entry in the VISM Dsx1 Configuration table.
         An entry is created when a DS1/E1 is added.
         An entry is deleted when a DS1/E1 is deleted.
        
         The DS1/E1 is specify by 'lineEnable' object
         in CISCO-MGX82XX-DSX1-MIB. "
    INDEX { vismLineNum }
    ::= { dsx1VismCnfGrpTable 1 }

Dsx1VismCnfGrpEntry ::= SEQUENCE {
    vismLineNum INTEGER,
    vismEcanEnabled INTEGER,
    vismEcanToneDisable INTEGER,
    vismEcanCnfNRN INTEGER,
    vismEcanTail INTEGER,
    vismEcanREC INTEGER,
    vismCompCnfVAD INTEGER,
    vismSignalingType INTEGER,
    vismCcsChannels INTEGER,
    vismCadenceTime INTEGER,
    vismTrunkConditionEnable TruthValue,
    vismDsx1CircuitIdentifier DisplayString,
    vismDsx1TxDigitOrder INTEGER,
    vismDsx1TonePlanRegion DisplayString,
    vismDsx1TonePlanVersion INTEGER,
    vismDsx1RingingTO INTEGER,
    vismDsx1RingBackTO INTEGER,
    vismDsx1BusyTO INTEGER,
    vismDsx1ReorderTO INTEGER,
    vismDsx1DialTO INTEGER,
    vismDsx1StutterDialTO INTEGER,
    vismDsx1OffHookAlertTO INTEGER,
    vismDsx1RemoteRingback INTEGER,
    vismDsx1MidcallTpart INTEGER,
    vismDsx1MidcallTcrit INTEGER,
    vismDsx1Sa4Byte INTEGER,
    vismDsx1Sa5Byte INTEGER,
    vismDsx1Sa6Byte INTEGER,
    vismDsx1Sa7Byte INTEGER,
    vismDsx1Sa8Byte INTEGER,
    vismDsx1State INTEGER,
    vismDsx1AdminStateControl INTEGER,
    vismBearerBusyCode INTEGER,
    vismDsx1V110Enable TruthValue,
    vismDsx1AlarmLogEnable TruthValue,
    vismDsx1AlarmLogAdminTimer Gauge,
    vismDsx1AlarmLogOperTimer Gauge,
    vismDsx1ElectricalSignalEnable TruthValue
    }

vismLineNum OBJECT-TYPE
    SYNTAX INTEGER(1..8)
    ACCESS read-only
    STATUS mandatory
    DESCRIPTION
        "This object identifies the DS1/E1 interface number."
    ::= { dsx1VismCnfGrpEntry 1 }

vismEcanEnabled OBJECT-TYPE
    SYNTAX INTEGER {
        disable(1),
        enable(2)
        }
    ACCESS read-write
    STATUS mandatory
    DESCRIPTION
        "This object disable/enable echo cancellation.
         'disable' : disable echo cancellation.
         'enable'  : enable echo cancellation."
    DEFVAL { enable }
    ::= { dsx1VismCnfGrpEntry 2 }

vismEcanToneDisable OBJECT-TYPE
    SYNTAX INTEGER {
        ignore(1),
        g-164(2),
        reserve(3),
        g-165(4)
        }
    ACCESS read-only
    STATUS deprecated
    DESCRIPTION
        "This object determines the behavior of the echo canceler
         in the presence of a modem.
         
         'ignore': Ignore 2100 Hz modem answer tone.
         'g-164' : G-164 mode, disable the canceler for all
                   the tones, phase reversing or not.
         'reserve': Reserved setting the value to 'reserve(3)'
                    results in BadValue error.
         'g-165':  G.165 mode, disable the canceler for phase
                   reversing tone only (V.8 modulated phase
                   reversing tone as well as the V.fast non
                   standard phase reversing tone)."
    DEFVAL { g-165 }
    ::= { dsx1VismCnfGrpEntry 3 }

vismEcanCnfNRN OBJECT-TYPE
    SYNTAX INTEGER {
        reenableOnModemData(1),
        reenableOnCallEnd(2)
        }
    ACCESS read-only
    STATUS deprecated
    DESCRIPTION
        "Echo canceler re-enable (NRN). This object
         determines when an echo canceler re-enable
         and begins cancellation after it has been
         disabled.
         
         'reenableOnModemData': Re-enable canceler when modem
                                data is gone (low energy).
         'reenableOnCallEnd' :  Re-enable canceler at end of call,
                                This object is not applicable
                                when vismEcanToneDisable 'ignore'."
    DEFVAL { reenableOnModemData }
    ::= { dsx1VismCnfGrpEntry 4 }

vismEcanTail OBJECT-TYPE
    SYNTAX INTEGER(24..128)
--  Units
--    milliseconds
    ACCESS read-write
    STATUS mandatory
    DESCRIPTION
        "This object identifies the maximum tail.  The object
         should be set just higher than the worst round trip delay
         anticipated. Convergence times may increase for longer
         tails and more resource will be used.
        
         Only following discrete values are allowed:
         24, 32, 48, 64, 80, 96, 112 and 128."
    DEFVAL { 32 }
    ::= { dsx1VismCnfGrpEntry 5 }

vismEcanREC OBJECT-TYPE
    SYNTAX INTEGER {
        cancelOnly(1),
        suppressResidual(2),
        reserved(3),
        comfortNoise(4)
        }
    ACCESS read-write
    STATUS mandatory
    DESCRIPTION
        "Residual Echo Control (REC) instructs the canceler
         how to treat echo remaining after cancellation.
        
         'cancelOnly'      : REC is disabled.
         'suppressResidual': The residual echo is replaced
                             with silence.
         'comfortNoise'    : Noise is injected in place of
                             residual echo at the same level
                             as the ambient noise at the near
                             end.
         'reserved'        : Results in BadValue error."
    DEFVAL { suppressResidual }
    ::= { dsx1VismCnfGrpEntry 6 }

vismCompCnfVAD OBJECT-TYPE
    SYNTAX INTEGER {
        disable(1),
        enable(2)
        }
    ACCESS read-write
    STATUS mandatory
    DESCRIPTION
        "This object identifies VAD (Voice Activity Detection).
        
        'disable': Disable VAD on the compression DSPs.
        'enable' : Enable VAD on the compression DSPs. "
    DEFVAL { enable }
    ::= { dsx1VismCnfGrpEntry 7 }

vismSignalingType OBJECT-TYPE
    SYNTAX INTEGER {
        cas(1),
        ccs(2),
        none(3)
        }
    ACCESS read-write
    STATUS mandatory
    DESCRIPTION
        "This object specifies the type of signaling used for 
         the line.
        
         'cas'  : Channel Associated Signaling.
         'ccs'  : Common Channel Signaling.
         'none' : No signaling used.
        
         This cannot be modified if endpoints are present. 
         and if CIDs/CCS channels are associated with this
         line in aal2Trunking mode.
        
         Setting of this object to CAS signaling type is
         not allowed if any of the DS0s on this line have
         loop back set to RemoteLoop or if any of the
         DS0's has ds0InsertLocalCas enabled. RemoteLoop and
         ds0InsertLocalCas from CISCO-VISM-DSX0-MIB.  
        
         Line signaling type cannot be changed if there
         are endpoints present, irrespective of
         mode/application."
    DEFVAL { none }
    ::= { dsx1VismCnfGrpEntry 8 }

vismCcsChannels OBJECT-TYPE
    SYNTAX INTEGER(0..2147483647)
    ACCESS read-write
    STATUS mandatory
    DESCRIPTION
        "This object describes the CCS signaling channels or 
         DS0s (also referred to as D-channel). 
         It is used only for lines configured as CCS signaling type. 
         It is a bit map of the DS0s configured as D channel. A one 
         in the bit position represents that DS0 as the D channel. 
         In most of the applications, only one D channel per T or E 
         span is required. However, since some applications may 
         require multiple D channels, this is supported by providing
         a bit map.
         This attribute is set by 'addccs' CLI command."
    ::= { dsx1VismCnfGrpEntry 9 }

vismCadenceTime OBJECT-TYPE
    SYNTAX INTEGER(50..200)
--  Units
--    milliseconds
    ACCESS read-only
    STATUS deprecated
    DESCRIPTION
        "This object describes the cadence time for CAS signals.
         This object is applicable only for CAS backhaul
         applications. For trunking application it is not applicable."
    DEFVAL { 100 }
    ::= { dsx1VismCnfGrpEntry 10 }

vismTrunkConditionEnable OBJECT-TYPE
    SYNTAX TruthValue
--    Rsyntax INTEGER {
--        true(1),
--        false(2)
--        }
    ACCESS read-write
    STATUS mandatory
    DESCRIPTION
        "This object determines if trunk conditioning should be 
         enabled or disabled on this line. If this object is 
         set to true(1), VISM will do trunk conditioning on 
         the affected DS0s on this line when it sees an 
         alarm (AIS) on the ATM side, instead of sending AIS 
         on the line side.
        
         If there are endpoints or CCS channels enabled on a line 
         then setting of this object is not allowed.
        
         Trunk conditioning: VISM will transmit idle code pattern 
         for the first 2.5 secs and then will transmit seized code 
         which is configured in ds0IdleCode and ds0SeizedCode 
         respectively, ds0IdleCode and ds0SeizedCode from 
         CISCO-VISM-DSX0-MIB. 
        
         This object is applicable only in trunking application.
        
         This object can be set in all applications but will be 
         applicable in trunking application only."
    DEFVAL { false }
    ::= { dsx1VismCnfGrpEntry 11 }

vismDsx1CircuitIdentifier OBJECT-TYPE
    SYNTAX DisplayString
--    Rsyntax OCTET STRING(SIZE(0..255))
    ACCESS read-write
    STATUS mandatory
    DESCRIPTION
        "This object is the identifier of a T1/E1 line.
         It contains alphanumeric description of a line for the
         purpose of better identification."
    ::= { dsx1VismCnfGrpEntry 12 }

vismDsx1TxDigitOrder OBJECT-TYPE
    SYNTAX INTEGER {
        aniThenDnis(1),
        dnisThenAni(2)
        }
    ACCESS read-write
    STATUS mandatory
    DESCRIPTION
        "When the call agent hands the ANI (Automatic 
         Number Identification, denoting the calling party number)
         and the DNIS (Destination Number Identification Service, 
         indicating the called party number) to the gateway for 
         dialing out, the gateway (by default) dials out the ANI
         followed by the DNIS. This object indicates the order in 
         which ANI and DNIs will be dialed out from this 
         (outgoing) interface."
    DEFVAL { aniThenDnis }
    ::= { dsx1VismCnfGrpEntry 13 }

vismDsx1TonePlanRegion OBJECT-TYPE
    SYNTAX DisplayString(SIZE(1..64))
--    Rsyntax OCTET STRING(SIZE(1..64))
    ACCESS read-write
    STATUS mandatory
    DESCRIPTION
        "This object specifies regional tone plan string. If the
         value of the object is 'NULL' then it will be considered  
         non usable, and non 'NULL' is (usable or activated 
         and related to an entry in the vismTonePlanTable table).
         This object must be compatible with the 
         vismDsx1TonePlanVersion object below, where both objects
         must either be NULL or where both objects must be non NULL.
        
         The vismTonePlanTable table consists of 32 slots which 
         are configurable (provisionable) followed by a release 
         dependent number of slots for built-in entries which are 
         not configurable, but loaded from values stored in the
         internal firmware of the release.  As releases are continued,
         the number of built-in slots will typically increase.  
         The total number of slots in this table consists of the sum 
         of the 32 provisionable slots plus an unspecified number of
         built-in slots and the built-in number and this sum
         represents the size of this table.
        
         In the case where these two objects are non NULL, this
         object, along with the vismDsx1TonePlanVersion object below, 
         must exactly match an entry in the vismTonePlanTable.  
         In the case where these objects are considered to be a NULL
         object, its behavior and contents are described in 
         paragraph five of this description block.
        
         The allowed range and contents of this object in the 
         non NULL case is the same as the tonePlanRegionName
         object in the vismTonePlanTable. This object will thus 
         consist of a 1 to 64 alphabetic, numeric, or underscore
         character string, with no embedded spaces.  And this object 
         plus the vismDsx1TonePlanVersion object below, must exactly 
         match an existing valid entry in the vismTonePlanTable,
         vismTonePlanTable is specify in CISCO-WAN-VISM-TONE-PLAN-MIB.
        
         In the case where this object is NULL, this object will 
         consist of a single space character of size one.  A NULL 
         value for this object will make the vismDsx1RingingTO, 
         vismDsx1RingBackTO, vismDsx1BusyTO, vismDsx1ReorderTO,
         vismDsx1DialTO, vismDsx1StutterDialTO,
         vismDsx1OffHookAlertTO, and vismDsx1RemoteRingback."
    ::= { dsx1VismCnfGrpEntry 14 }

vismDsx1TonePlanVersion OBJECT-TYPE
    SYNTAX INTEGER(0..2147483647)
    ACCESS read-write
    STATUS mandatory
    DESCRIPTION
        "This object will either be considered NULL
         (i.e. non usable) or non NULL (usable or activated 
         and related to an entry in the vismTonePlanTable table).
         This object must be compatible with the 
         vismDsx1TonePlanRegion object above, where both objects 
         must either be NULL or where both objects must be non NULL.
         The vismTonePlanTable table consists of 32 slots which 
         are configurable (provisionable) followed by a release 
         dependent number of slots for built-in entries which are 
         not configurable, but loaded from values stored in the
         internal firmware of the release. As releases are continued,
         the number of built-in slots will typically increase.  
         The total number of slots in this table consists of the sum 
         of the 32 provisionable slots plus an unspecified
         number of built-in slots and the built-in number and this 
         sum represents the size of this table.
        
         In the case where these two objects are non NULL, this
         object, along with the vismDsx1TonePlanRegion object
         above, must exactly match an entry in the
         vismTonePlanTable.  In the case where these objects
         are considered to be a NULL object, its behavior and
         contents are described in paragraph five of this
         description block.
        
         The allowed range and contents of this object in the non
         NULL case is the same as the tonePlanVersionNumber object
         in the vismTonePlanTable. This object will thus consist of 
         a non zero numeric value.  And this object plus the 
         vismDsx1TonePlanRegion object above, must exactly match 
         an existing valid entry in the vismTonePlanTable.
        
         In the case where this object is NULL, this object will 
         consist of a zero numeric value.  A NULL value for this 
         object will make the vismDsx1RingingTO, vismDsx1RingBackTO, 
         vismDsx1BusyTO, vismDsx1ReorderTO, vismDsx1DialTO, 
         vismDsx1StutterDialTO, vismDsx1OffHookAlertTO, and
         vismDsx1RemoteRingback."
    ::= { dsx1VismCnfGrpEntry 15 }

vismDsx1RingingTO OBJECT-TYPE
    SYNTAX INTEGER(0..3600)
--  Units
--    seconds
    ACCESS read-write
    STATUS mandatory
    DESCRIPTION
        "Time in seconds for which the ringing cadence will be
         generated towards the basic PBX unless interrupted 
         (e.g. by the answer from the called party or a delete 
         connection command from the Call Agent). This is also
         the time for which remote inband ring back tone will be
         played towards the packet network. The value Zero indicates 
         that the cadence will be generated indefinitely unless 
         interrupted.
        
         This MIB object is not applicable unless the value of
         vismDsx1TonePlanRegion and vismDsx1TonePlanVersion MIB
         objects are not 'NULL' string."
    DEFVAL { 180 }
    ::= { dsx1VismCnfGrpEntry 16 }

vismDsx1RingBackTO OBJECT-TYPE
    SYNTAX INTEGER(0..3600)
--  Units
--    seconds
    ACCESS read-write
    STATUS mandatory
    DESCRIPTION
        "Time in seconds for which the local ring back tone 
         (towards the TDM) will be generated unless interrupted 
         (e.g. by the answer from the called party or a delete 
         connection command from the Call Agent). The value Zero 
         indicates that the tone will be generated indefinitely 
         unless interrupted.
        
         This MIB object is not applicable unless the value of
         vismDsx1TonePlanRegion and vismDsx1TonePlanVersion MIB
         objects are not 'NULL' string."
    DEFVAL { 180 }
    ::= { dsx1VismCnfGrpEntry 17 }

vismDsx1BusyTO OBJECT-TYPE
    SYNTAX INTEGER(0..3600)
--  Units
--    seconds
    ACCESS read-write
    STATUS mandatory
    DESCRIPTION
        "Time in seconds for which the busy tone will be 
         generated unless interrupted (e.g. by the hangup from 
         the calling party). The value Zero indicates that the
         tone will be generated indefinitely unless interrupted.
        
         This MIB object is not applicable unless the value of
         vismDsx1TonePlanRegion and vismDsx1TonePlanVersion MIB
         objects are not 'NULL' string."
    DEFVAL { 30 }
    ::= { dsx1VismCnfGrpEntry 18 }

vismDsx1ReorderTO OBJECT-TYPE
    SYNTAX INTEGER(0..3600)
--  Units
--    seconds
    ACCESS read-write
    STATUS mandatory
    DESCRIPTION
        "Time in seconds for which the reorder/fast busy 
         tone will be generated unless interrupted 
         (e.g. by the hangup from the calling party). The value
         zero indicates that the tone will be generated
         indefinitely unless interrupted.
        
         This MIB object is not applicable unless the value of
         vismDsx1TonePlanRegion and vismDsx1TonePlanVersion MIB
         objects are not 'NULL' string."
    DEFVAL { 30 }
    ::= { dsx1VismCnfGrpEntry 19 }

vismDsx1DialTO OBJECT-TYPE
    SYNTAX INTEGER(0..3600)
--  Units
--    seconds
    ACCESS read-write
    STATUS mandatory
    DESCRIPTION
        "Time in seconds for which the dial tone will be 
         generated unless interrupted (e.g. by the first DTMF 
         digit from the calling party). The value Zero indicates
         that the tone will be generated indefinitely unless 
         interrupted.
        
         This MIB object is not applicable unless the value of
         vismDsx1TonePlanRegion and vismDsx1TonePlanVersion MIB
         objects are not 'NULL' string."
    DEFVAL { 16 }
    ::= { dsx1VismCnfGrpEntry 20 }

vismDsx1StutterDialTO OBJECT-TYPE
    SYNTAX INTEGER(0..3600)
--  Units
--    seconds
    ACCESS read-write
    STATUS mandatory
    DESCRIPTION
        "Time in seconds for which the stutter dial 
         tone/confirmation dial tone will be generated unless
         interrupted (e.g. by the first DTMF digit from the
         calling party). The value Zero indicates that the tone 
         will be generated indefinitely unless interrupted.
        
         This MIB object is not applicable unless the value of
         vismDsx1TonePlanRegion and vismDsx1TonePlanVersion MIB
         objects are not 'NULL' string."
    DEFVAL { 16 }
    ::= { dsx1VismCnfGrpEntry 21 }

vismDsx1OffHookAlertTO OBJECT-TYPE
    SYNTAX INTEGER(0..3600)
--  Units
--    seconds
    ACCESS read-write
    STATUS mandatory
    DESCRIPTION
        "Time in seconds for which the off-hook alert tone 
         will be generated unless interrupted (e.g. caller hangup). 
         The value Zero indicates that the tone will be generated
         indefinitely unless interrupted.
        
         This MIB object is not applicable unless the value of
         vismDsx1TonePlanRegion and vismDsx1TonePlanVersion MIB
         objects are not 'NULL' string."
    DEFVAL { 5 }
    ::= { dsx1VismCnfGrpEntry 22 }

vismDsx1RemoteRingback OBJECT-TYPE
    SYNTAX INTEGER {
        proxy(1),
        inband(2)
        }
    ACCESS read-write
    STATUS mandatory
    DESCRIPTION
        "This object specifies the remote ring back method on 
         endpoints on this DS1/E1. 
         This object can have the following values:
        
         'proxy(1)': This gateway sends the appropriate packet
                      (NSE, NTE, or AAL-2 Type 3) for ring back to 
                      the originating gateway which in turn generates 
                      the ringback tone towards the TDM network.
        
         'inband(2)': This gateway will generate the inband ringback
                      tone towards the originating gateway over the 
                      packet network and the originating gateway plays 
                      it.
        
         This MIB object is not applicable unless the value of
         vismDsx1TonePlanRegion and vismDsx1TonePlanVersion MIB
         objects are not 'NULL' string."
    DEFVAL { proxy }
    ::= { dsx1VismCnfGrpEntry 23 }

vismDsx1MidcallTpart OBJECT-TYPE
    SYNTAX INTEGER(10..10000)
--  Units
--    seconds
    ACCESS read-write
    STATUS mandatory
    DESCRIPTION
        "This object represents the partial dial timing in
         seconds and is used along with a digit map as the
         inter-digit timer. This object is used for both CAS 
         and non CAS endpoints when doing mid call DTMF 
         digit reporting. The timer is not started until 
         the first digit is entered, and the timer is 
         restarted after each new digit is entered until 
         either a digit map match or mismatch occurs."
    DEFVAL { 16 }
    ::= { dsx1VismCnfGrpEntry 24 }

vismDsx1MidcallTcrit OBJECT-TYPE
    SYNTAX INTEGER(0..10000)
--  Units
--    seconds
    ACCESS read-write
    STATUS mandatory
    DESCRIPTION
        "This object represents the critical timing in seconds.
         If used along with a digit map, the timer is started when
         the last digit is received i.e when no more digits
         are required for a digit map match. After this timer
         expires, the digit map match is assumed to be complete.
         If used without a digit map, the timer is started
         immediately and cancelled (but not restarted) as soon
         as a digit is entered.
         This object is used for both CAS and non CAS endpoints 
         when doing mid call DTMF digit reporting."
    DEFVAL { 4 }
    ::= { dsx1VismCnfGrpEntry 25 }

vismDsx1Sa4Byte OBJECT-TYPE
    SYNTAX INTEGER(0..255)
    ACCESS read-write
    STATUS mandatory
    DESCRIPTION
        "This is a spare bit on T1/E1 Framer reserved for 
         international standardization."
    DEFVAL { 0 }
    ::= { dsx1VismCnfGrpEntry 26 }

vismDsx1Sa5Byte OBJECT-TYPE
    SYNTAX INTEGER(0..255)
    ACCESS read-write
    STATUS mandatory
    DESCRIPTION
        "This is a spare bit on T1/E1 Framer reserved for
         international standardization."
    DEFVAL { 0 }
    ::= { dsx1VismCnfGrpEntry 27 }

vismDsx1Sa6Byte OBJECT-TYPE
    SYNTAX INTEGER(0..255)
    ACCESS read-write
    STATUS mandatory
    DESCRIPTION
        "This is a spare bit on T1/E1 Framer reserved for 
         international standardization."
    DEFVAL { 0 }
    ::= { dsx1VismCnfGrpEntry 28 }

vismDsx1Sa7Byte OBJECT-TYPE
    SYNTAX INTEGER(0..255)
    ACCESS read-write
    STATUS mandatory
    DESCRIPTION
        "This is a spare bit on T1/E1 Framer reserved for 
         international standardization."
    DEFVAL { 0 }
    ::= { dsx1VismCnfGrpEntry 29 }

vismDsx1Sa8Byte OBJECT-TYPE
    SYNTAX INTEGER(0..255)
    ACCESS read-write
    STATUS mandatory
    DESCRIPTION
        "This is a spare bit on T1/E1 Framer reserved for 
         international standardization."
    DEFVAL { 0 }
    ::= { dsx1VismCnfGrpEntry 30 }

vismDsx1State OBJECT-TYPE
    SYNTAX INTEGER {
        invalid(1),
        is(2),
        oos(3),
        poos(4),
        coos(5),
        inactive(6)
        }
    ACCESS read-only
    STATUS mandatory
    DESCRIPTION
        "This object will allow the line administrative state
         (in service and out of service) to be persistent.
         invalid (1) : invalid state.
         is      (2) : in service
         oos     (3) : out of service
         poos    (4) : pending out of service
         coos    (5) : command out of service
         inactive(6) : inactive"
    DEFVAL { inactive }
    ::= { dsx1VismCnfGrpEntry 31 }

vismDsx1AdminStateControl OBJECT-TYPE
    SYNTAX INTEGER {
        inService(1),
        forcefulOutOfService(2),
        gracefulOutOfService(3),
        inactive(4)
        }
    ACCESS read-write
    STATUS mandatory
    DESCRIPTION
        "This control object is used to change the service state of the
         line from 'is' to 'coos' or from 'coos'
         to 'is'. The resulting service state of the line is
         represented by vismDsx1State.
        
         'inService': Transition vismDsx1State to 'is'(in service).
                    In the course, the MG's MGCs may get notified 
                    of this transition, e.g. in the case of MGCP 
                    through emission of RSIPs to registered call 
                    agents according to policy.
        
         'forcefulOutOfService': Take the line out-of-service 
                    forcefully. This releases any resources at the 
                    line. In the course, the MGCs may get notified 
                    of this transition, e.g. in the case of MGCP 
                    through emission of RSIPs to registered call 
                    agents according to policy.
        
         'gracefulOutOfService': Take the line out-of-service
                    gracefully. If there are no resources
                    existing, vismDsx1State transitions to coos
                    immediately. If resources exist,
                    vismDsx1State transitions to poos thus
                    initiating a graceful shutdown. In the
                    course, the MG's MGCs may get notified of 
                    this transition, e.g. in the case of MGCP through 
                    emission of RSIPs to registered call agents 
                    according to policy.
         'inactive': Indicates the vismDsx1State is in inactive state. "
    DEFVAL { inactive }
    ::= { dsx1VismCnfGrpEntry 32 }

vismBearerBusyCode OBJECT-TYPE
    SYNTAX INTEGER(0..255)
    ACCESS read-write
    STATUS mandatory
    DESCRIPTION
        "This object is used when vismTrunkConditionEnable is
         enabled on a line. It is a configurable busy pattern
         sent out on the 'Bearer' on the channels, which are
         receiving remote ATM channel ID (CID) alarms.
         If this object is not set, it assumes a default value
         of 255 for E1 and 127 for T1."
    ::= { dsx1VismCnfGrpEntry 33 }

vismDsx1V110Enable OBJECT-TYPE
    SYNTAX TruthValue
--    Rsyntax INTEGER {
--        true(1),
--        false(2)
--        }
    ACCESS read-write
    STATUS mandatory
    DESCRIPTION
        "This object specifies whether V.110 detection on the
         line is enabled or disabled. 
         If the value of this object is 'true', V.110 detection
         on the line is enabled.
         If the value of this object is 'false', V.110 detection
         on the line is disabled.
         The vismSignalingType object must be set to
         ccs when enabling V.110 detection."
    DEFVAL { false }
    ::= { dsx1VismCnfGrpEntry 34 }

vismDsx1AlarmLogEnable OBJECT-TYPE
    SYNTAX TruthValue
--    Rsyntax INTEGER {
--        true(1),
--        false(2)
--        }
    ACCESS read-write
    STATUS mandatory
    DESCRIPTION
        "This object specifies whether detailed alarm logging 
         on the DS1 is enabled or disabled. 
         If this object is true, detailed alarm logging for
         the DS1 will be enabled.
         If this object is false, detailed alarm logging for 
         the DS1 will be disabled.
         When this object is enabled, vismDsx1AlarmLogAdminTimer
         will indicate the time configured in minutes for which 
         this object will continue to remain enabled. While,
         vismDsx1AlarmLogOperTimer will indicate the time in
         minutes remaining for the alarm logging to continue to
         remain enabled. 
         Alarm logging can be disabled before the time specified
         in vismDsx1AlarmLogAdminTimer runs out. If alarm logging
         is disabled before the timer runs out, then on re-enabling
         the logging, the vismDsx1AlarmLogAdminTimer will need to be
         reconfigured as well."
    DEFVAL { false }
    ::= { dsx1VismCnfGrpEntry 35 }

vismDsx1AlarmLogAdminTimer OBJECT-TYPE
    SYNTAX Gauge(0..2147483647)
--  Units
--    minutes
    ACCESS read-write
    STATUS mandatory
    DESCRIPTION
        "This object specifies the time for which the detailed 
         alarm logging for the DS1 will remain active.
         The value in this object can be set and is valid only 
         if vismDsx1AlarmLogEnable for this DS1 is set to true.
         If this object is set to 0, it indicates that the alarm 
         logging will remain active forever.
         Once set, this object can be overwritten as long as 
         vismDsx1AlarmLogEnable is true. If this is done, the 
         vismDsx1AlarmLogAdminTimer will be refreshed to take the 
         new value set in this object."
    DEFVAL { 7200 }
    ::= { dsx1VismCnfGrpEntry 36 }

vismDsx1AlarmLogOperTimer OBJECT-TYPE
    SYNTAX Gauge(0..2147483647)
--  Units
--    minutes
    ACCESS read-only
    STATUS mandatory
    DESCRIPTION
        "This object specifies the time remaining in minutes for 
         which the detailed alarm logging will remain active on 
         the DS1.
         When this value becomes 0, it indicates that the DS1 
         has run through the time specified in 
         vismDsx1AlarmLogOperTimer. This will cause the 
         vismDsx1AlarmLogEnable to be set to false.
         If vismDsx1AlarmLogAdminTimer is overwritten with a new 
         value, this object will also be set to reflect the new value."
    ::= { dsx1VismCnfGrpEntry 37 }

vismDsx1ElectricalSignalEnable OBJECT-TYPE
    SYNTAX TruthValue
--    Rsyntax INTEGER {
--        true(1),
--        false(2)
--        }
    ACCESS read-write
    STATUS mandatory
    DESCRIPTION
        "This object specifies whether electrical signal on the 
         line is enabled or disabled.
         If the value of this object is 'true', electrical signal
         on the line is enabled.
         If the value of this object is 'false', electrical signal
         on the line is disabled."
    DEFVAL { true }
    ::= { dsx1VismCnfGrpEntry 38 }

dsx1VismStatsGrpTable OBJECT-TYPE
    SYNTAX SEQUENCE OF Dsx1VismStatsGrpEntry
    ACCESS not-accessible
    STATUS mandatory
    DESCRIPTION
        "The VISM specific DS1/E1 statistics table. This table
         contains the additional VISM statistics information
         for DS1/E1."
    ::= { dsx1VismStatsGrp 1 }

dsx1VismStatsGrpEntry OBJECT-TYPE
    SYNTAX Dsx1VismStatsGrpEntry
    ACCESS not-accessible
    STATUS mandatory
    DESCRIPTION
        "An entry in the VISM Dsx1 Statistics table.
         This entry augments the corresponding entry in 
         the dsx1VismCnfGrpTable. "
    INDEX { vismLineNum }
-- Augments dsx1VismCnfGrpEntry
    ::= { dsx1VismStatsGrpTable 1 }

Dsx1VismStatsGrpEntry ::= SEQUENCE {
    vismDsx1TotalTxUncontrolledSlips Counter,
    vismDsx1TotalTxFrameSlips Counter,
    vismDsx1TotalRxUncontrolledSlips Counter,
    vismDsx1TotalRxFrameSlips Counter,
    vismSlipCntDiscontinuityTime TimeStamp
    }

vismDsx1TotalTxUncontrolledSlips OBJECT-TYPE
    SYNTAX Counter
    ACCESS read-only
    STATUS mandatory
    DESCRIPTION
        "The number of accumulative uncontrolled slips in the 
         transmit direction."
    ::= { dsx1VismStatsGrpEntry 1 }

vismDsx1TotalTxFrameSlips OBJECT-TYPE
    SYNTAX Counter
    ACCESS read-only
    STATUS mandatory
    DESCRIPTION
        "The number of accumulative frame slips in the 
         transmit direction."
    ::= { dsx1VismStatsGrpEntry 2 }

vismDsx1TotalRxUncontrolledSlips OBJECT-TYPE
    SYNTAX Counter
    ACCESS read-only
    STATUS mandatory
    DESCRIPTION
        "The number of accumulative uncontrolled slips in the 
         receive direction."
    ::= { dsx1VismStatsGrpEntry 3 }

vismDsx1TotalRxFrameSlips OBJECT-TYPE
    SYNTAX Counter
    ACCESS read-only
    STATUS mandatory
    DESCRIPTION
        "The number of accumulative frame slips in the 
         receive direction."
    ::= { dsx1VismStatsGrpEntry 4 }

vismSlipCntDiscontinuityTime OBJECT-TYPE
    SYNTAX TimeStamp
--    Rsyntax TimeTicks
    ACCESS read-only
    STATUS mandatory
    DESCRIPTION
        "This object will represent the timestamp since sysUpTime 
         when the statistics in this interval were discontinued.
         If this has the default value then it indicates that the 
         statistics in this interval have not been discontinued."
    DEFVAL { 0 }
    ::= { dsx1VismStatsGrpEntry 5 }

dsx1AlmHistoryTable OBJECT-TYPE
    SYNTAX SEQUENCE OF Dsx1AlmHistoryEntry
    ACCESS not-accessible
    STATUS mandatory
    DESCRIPTION
        "The TDM line interface alarm history table."
    ::= { dsx1AlmGrp 2 }

dsx1AlmHistoryEntry OBJECT-TYPE
    SYNTAX Dsx1AlmHistoryEntry
    ACCESS not-accessible
    STATUS mandatory
    DESCRIPTION
        "An entry in the DS1/E1 Alarm History table."
    INDEX { almlineNumber, almIntervalNumber }
    ::= { dsx1AlmHistoryTable 1 }

Dsx1AlmHistoryEntry ::= SEQUENCE {
    almlineNumber INTEGER,
    almIntervalNumber INTEGER,
    lCV Counter,
    lES Counter,
    lSES Counter,
    cRC Counter,
    cRCES Counter,
    cRCSES Counter,
    sEFS Counter,
    aISS Counter,
    uAS Counter,
    percentErrorFreeSecs INTEGER,
    rcvLOSCnt Counter,
    rcvOOFCnt Counter,
    rcvRAICnt Counter,
    rcvFECnt Counter,
    dsx1AlmClrButton INTEGER,
    dsx1TxUncontrolledSlips Counter,
    dsx1RxUncontrolledSlips Counter,
    dsx1TxFrameSlips Counter,
    dsx1RxFrameSlips Counter
    }

almlineNumber OBJECT-TYPE
    SYNTAX INTEGER(1..8)
    ACCESS read-only
    STATUS mandatory
    DESCRIPTION
        "This object is the identifier of a DS1/E1 Interface
         on a managed device."
    ::= { dsx1AlmHistoryEntry 1 }

almIntervalNumber OBJECT-TYPE
    SYNTAX INTEGER(1..96)
    ACCESS read-only
    STATUS mandatory
    DESCRIPTION
        "This is the alarm interval number which associates with 
         time interval alarms occurred."
    ::= { dsx1AlmHistoryEntry 2 }

lCV OBJECT-TYPE
    SYNTAX Counter
    ACCESS read-only
    STATUS mandatory
    DESCRIPTION
        "The accumulated number of Line code 
         violations encountered on the DS1 interface."
    ::= { dsx1AlmHistoryEntry 3 }

lES OBJECT-TYPE
    SYNTAX Counter
    ACCESS read-only
    STATUS mandatory
    DESCRIPTION
        "The accumulated number of Line code 
         violations Errored Seconds encountered on the
         DS1 interface."
    ::= { dsx1AlmHistoryEntry 4 }

lSES OBJECT-TYPE
    SYNTAX Counter
    ACCESS read-only
    STATUS mandatory
    DESCRIPTION
        "The accumulated number of LCV (Line Code Violations)
         Severely Errored Seconds encountered on 
         the DS1 interface."
    ::= { dsx1AlmHistoryEntry 5 }

cRC OBJECT-TYPE
    SYNTAX Counter
    ACCESS read-only
    STATUS mandatory
    DESCRIPTION
        "The accumulated number of P Bit code
         violations encountered on the DS1 interface."
    ::= { dsx1AlmHistoryEntry 6 }

cRCES OBJECT-TYPE
    SYNTAX Counter
    ACCESS read-only
    STATUS mandatory
    DESCRIPTION
        "The accumulated number of PVC Errored 
         Seconds encountered on the DS1 interface."
    ::= { dsx1AlmHistoryEntry 7 }

cRCSES OBJECT-TYPE
    SYNTAX Counter
    ACCESS read-only
    STATUS mandatory
    DESCRIPTION
        "The accumulated number of P Bit code 
         violations Severely Errored Seconds encountered 
         on the DS1 interface."
    ::= { dsx1AlmHistoryEntry 8 }

sEFS OBJECT-TYPE
    SYNTAX Counter
    ACCESS read-only
    STATUS mandatory
    DESCRIPTION
        "The accumulated number of Severely
         Errored Framing Seconds encountered on the 
         DS1 interface."
    ::= { dsx1AlmHistoryEntry 9 }

aISS OBJECT-TYPE
    SYNTAX Counter
    ACCESS read-only
    STATUS mandatory
    DESCRIPTION
        "The accumulated number of AIS 
         Severely Errored Seconds encountered on the
         DS1 interface."
    ::= { dsx1AlmHistoryEntry 10 }

uAS OBJECT-TYPE
    SYNTAX Counter
    ACCESS read-only
    STATUS mandatory
    DESCRIPTION
        "The accumulated number of Unavailable 
         Seconds encountered on the DS1 interface."
    ::= { dsx1AlmHistoryEntry 11 }

percentErrorFreeSecs OBJECT-TYPE
    SYNTAX INTEGER(0..100)
    ACCESS read-only
    STATUS mandatory
    DESCRIPTION
        "The accumulated the percentage of 
         LCV (Line Code Violation) Error Free Seconds."
    ::= { dsx1AlmHistoryEntry 12 }

rcvLOSCnt OBJECT-TYPE
    SYNTAX Counter
    ACCESS read-only
    STATUS mandatory
    DESCRIPTION
        "The accumulated number of LOS (Loss of Signal)  
         detected with or without integrating to LOS alarm
         on the DS1 interface."
    ::= { dsx1AlmHistoryEntry 13 }

rcvOOFCnt OBJECT-TYPE
    SYNTAX Counter
    ACCESS read-only
    STATUS mandatory
    DESCRIPTION
        "The accumulated number of OOF (Out of Frame) 
         detected with or without integrating to OOF alarm
         on the DS1 interface."
    ::= { dsx1AlmHistoryEntry 14 }

rcvRAICnt OBJECT-TYPE
    SYNTAX Counter
    ACCESS read-only
    STATUS mandatory
    DESCRIPTION
        "The accumulated number of Yellow Alarms
         detected with or without integrating to RAI alarm
         on the DS1 interface."
    ::= { dsx1AlmHistoryEntry 15 }

rcvFECnt OBJECT-TYPE
    SYNTAX Counter
    ACCESS read-only
    STATUS mandatory
    DESCRIPTION
        "The accumulated number of Framing Pattern Errors 
         encountered on a DS1/E1 interface."
    ::= { dsx1AlmHistoryEntry 16 }

dsx1AlmClrButton OBJECT-TYPE
    SYNTAX INTEGER {
        noaction(1),
        clear(2)
        }
    ACCESS read-write
    STATUS mandatory
    DESCRIPTION
        "This variable is used to clear all the 
         alarms for the line/interval."
    ::= { dsx1AlmHistoryEntry 17 }

dsx1TxUncontrolledSlips OBJECT-TYPE
    SYNTAX Counter
    ACCESS read-only
    STATUS mandatory
    DESCRIPTION
        "This counter counts the number of uncontrolled
         slips in the transmit direction during this 
         interval."
    ::= { dsx1AlmHistoryEntry 18 }

dsx1RxUncontrolledSlips OBJECT-TYPE
    SYNTAX Counter
    ACCESS read-only
    STATUS mandatory
    DESCRIPTION
        "This counter counts the number of uncontrolled
         slips in the receive direction during this
         interval."
    ::= { dsx1AlmHistoryEntry 19 }

dsx1TxFrameSlips OBJECT-TYPE
    SYNTAX Counter
    ACCESS read-only
    STATUS mandatory
    DESCRIPTION
        "This counter counts the number of frame
         slips in the transmit direction during this 
         interval."
    ::= { dsx1AlmHistoryEntry 20 }

dsx1RxFrameSlips OBJECT-TYPE
    SYNTAX Counter
    ACCESS read-only
    STATUS mandatory
    DESCRIPTION
        "This counter counts the number of frame
         slips in the receive direction during this 
         interval."
    ::= { dsx1AlmHistoryEntry 21 }

cvDsx1ConfGroup OBJECT IDENTIFIER ::= { cvDsx1MIBGroups 1 }
-- OBJECT-GROUP
--  Status
--    deprecated
--  Descr
--    The collection of objects used for
--     DS1/E1 interfaces.
--  objects
--    vismLineNum, vismEcanEnabled, vismEcanToneDisable, 
--    vismEcanCnfNRN, vismEcanTail, vismEcanREC, vismCompCnfVAD, 
--    vismSignalingType, vismCcsChannels, vismCadenceTime, 
--    vismTrunkConditionEnable, vismDsx1CircuitIdentifier, 
--    vismDsx1TxDigitOrder, vismDsx1TonePlanRegion, 
--    vismDsx1TonePlanVersion, vismDsx1RingingTO, 
--    vismDsx1RingBackTO, vismDsx1BusyTO, vismDsx1ReorderTO, 
--    vismDsx1DialTO, vismDsx1StutterDialTO, vismDsx1OffHookAlertTO, 
--    vismDsx1RemoteRingback, vismDsx1MidcallTpart, 
--    vismDsx1MidcallTcrit, vismDsx1Sa4Byte, vismDsx1Sa5Byte, 
--    vismDsx1Sa6Byte, vismDsx1Sa7Byte, vismDsx1Sa8Byte, 
--    vismDsx1State, vismDsx1AdminStateControl

cvDsx1AlmHistoryGroup OBJECT IDENTIFIER ::= { cvDsx1MIBGroups 2 }
-- OBJECT-GROUP
--  Status
--    deprecated
--  Descr
--    The collection of objects related to
--     DS1/E1 alarm history.
--  objects
--    almlineNumber, almIntervalNumber, lCV, lES, lSES, cRC, cRCES, 
--    cRCSES, sEFS, aISS, uAS, percentErrorFreeSecs, rcvLOSCnt, 
--    rcvOOFCnt, rcvRAICnt, rcvFECnt, dsx1AlmClrButton

cvDsx1ConfGroupRev1 OBJECT IDENTIFIER ::= { cvDsx1MIBGroups 3 }
-- OBJECT-GROUP
--  Status
--    deprecated
--  Descr
--    The collection of objects related to
--     DS1/E1 in VISM
--  objects
--    vismLineNum, vismEcanEnabled, vismEcanTail, vismEcanREC, 
--    vismCompCnfVAD, vismSignalingType, vismCcsChannels, 
--    vismTrunkConditionEnable, vismDsx1CircuitIdentifier, 
--    vismDsx1TxDigitOrder, vismDsx1TonePlanRegion, 
--    vismDsx1TonePlanVersion, vismDsx1RingingTO, 
--    vismDsx1RingBackTO, vismDsx1BusyTO, vismDsx1ReorderTO, 
--    vismDsx1DialTO, vismDsx1StutterDialTO, vismDsx1OffHookAlertTO, 
--    vismDsx1RemoteRingback, vismDsx1MidcallTpart, 
--    vismDsx1MidcallTcrit, vismDsx1Sa4Byte, vismDsx1Sa5Byte, 
--    vismDsx1Sa6Byte, vismDsx1Sa7Byte, vismDsx1Sa8Byte, 
--    vismDsx1State, vismDsx1AdminStateControl

cvDsx1ConfGroupRev2 OBJECT IDENTIFIER ::= { cvDsx1MIBGroups 4 }
-- OBJECT-GROUP
--  Status
--    mandatory
--  Descr
--    The collection of objects related to
--     DS1/E1 in VISM
--  objects
--    vismLineNum, vismEcanEnabled, vismEcanTail, vismEcanREC, 
--    vismCompCnfVAD, vismSignalingType, vismCcsChannels, 
--    vismTrunkConditionEnable, vismDsx1CircuitIdentifier, 
--    vismDsx1TxDigitOrder, vismDsx1TonePlanRegion, 
--    vismDsx1TonePlanVersion, vismDsx1RingingTO, 
--    vismDsx1RingBackTO, vismDsx1BusyTO, vismDsx1ReorderTO, 
--    vismDsx1DialTO, vismDsx1StutterDialTO, vismDsx1OffHookAlertTO, 
--    vismDsx1RemoteRingback, vismDsx1MidcallTpart, 
--    vismDsx1MidcallTcrit, vismDsx1Sa4Byte, vismDsx1Sa5Byte, 
--    vismDsx1Sa6Byte, vismDsx1Sa7Byte, vismDsx1Sa8Byte, 
--    vismDsx1State, vismDsx1AdminStateControl, vismBearerBusyCode

cvDsx1AlmHistoryGroupRev1 OBJECT IDENTIFIER ::= { cvDsx1MIBGroups 5 }
-- OBJECT-GROUP
--  Status
--    mandatory
--  Descr
--    The collection of objects related to
--     DS1/E1 alarm history.
--  objects
--    almlineNumber, almIntervalNumber, lCV, lES, lSES, cRC, cRCES, 
--    cRCSES, sEFS, aISS, uAS, percentErrorFreeSecs, rcvLOSCnt, 
--    rcvOOFCnt, rcvRAICnt, rcvFECnt, dsx1AlmClrButton, 
--    dsx1TxUncontrolledSlips, dsx1TxFrameSlips, 
--    dsx1RxUncontrolledSlips, dsx1RxFrameSlips

cvDsx1StatsGroup OBJECT IDENTIFIER ::= { cvDsx1MIBGroups 6 }
-- OBJECT-GROUP
--  Status
--    mandatory
--  Descr
--    The collection of objects related to
--     DS1/E1 in VISM
--  objects
--    vismDsx1TotalTxUncontrolledSlips, vismDsx1TotalTxFrameSlips, 
--    vismDsx1TotalRxUncontrolledSlips, vismDsx1TotalRxFrameSlips, 
--    vismSlipCntDiscontinuityTime

cvDsx1ConfGroupSup1 OBJECT IDENTIFIER ::= { cvDsx1MIBGroups 7 }
-- OBJECT-GROUP
--  Status
--    mandatory
--  Descr
--    The collection of objects related to
--     DS1/E1 in VISM
--  objects
--    vismDsx1V110Enable

cvDsx1AlarmLogGroup OBJECT IDENTIFIER ::= { cvDsx1MIBGroups 8 }
-- OBJECT-GROUP
--  Status
--    mandatory
--  Descr
--    The collection of objects related to
--     DS1/E1 in VISM.
--  objects
--    vismDsx1AlarmLogEnable, vismDsx1AlarmLogAdminTimer, 
--    vismDsx1AlarmLogOperTimer

cvDsx1ElecSigGroup OBJECT IDENTIFIER ::= { cvDsx1MIBGroups 9 }
-- OBJECT-GROUP
--  Status
--    mandatory
--  Descr
--    The collection of objects related to
--     DS1/E1 electrical signals in VISM.
--  objects
--    vismDsx1ElectricalSignalEnable

cvDsx1Compliance OBJECT IDENTIFIER ::= { cvDsx1MIBCompliances 1 }
-- MODULE-COMPLIANCE
--  Status
--    deprecated
--  Descr
--    The compliance statement for objects related
--     to VISM DS1/E1 MIB.
--  Module
--    >>current<<
--   MandGroup
--    cvDsx1ConfGroup
--   MandGroup
--    cvDsx1AlmHistoryGroup

cvDsx1ComplianceRev1 OBJECT IDENTIFIER ::= { cvDsx1MIBCompliances 2 }
-- MODULE-COMPLIANCE
--  Status
--    deprecated
--  Descr
--    The compliance statement for objects related
--     to VISM DS1/E1 MIB.
--  Module
--    >>current<<
--   MandGroup
--    cvDsx1ConfGroupRev1
--   MandGroup
--    cvDsx1AlmHistoryGroup

cvDsx1ComplianceRev2 OBJECT IDENTIFIER ::= { cvDsx1MIBCompliances 3 }
-- MODULE-COMPLIANCE
--  Status
--    deprecated
--  Descr
--    The compliance statement for objects related
--     to VISM DS1/E1 MIB.
--  Module
--    >>current<<
--   MandGroup
--    cvDsx1ConfGroupRev2
--   MandGroup
--    cvDsx1AlmHistoryGroup

cvDsx1ComplianceRev3 OBJECT IDENTIFIER ::= { cvDsx1MIBCompliances 4 }
-- MODULE-COMPLIANCE
--  Status
--    deprecated
--  Descr
--    The compliance statement for objects related
--     to VISM DS1/E1 MIB.
--  Module
--    >>current<<
--   MandGroup
--    cvDsx1ConfGroupRev2
--   MandGroup
--    cvDsx1AlmHistoryGroupRev1
--   MandGroup
--    cvDsx1StatsGroup

cvDsx1ComplianceRev4 OBJECT IDENTIFIER ::= { cvDsx1MIBCompliances 5 }
-- MODULE-COMPLIANCE
--  Status
--    deprecated
--  Descr
--    The compliance statement for objects related
--     to VISM DS1/E1 MIB.
--  Module
--    >>current<<
--   MandGroup
--    cvDsx1ConfGroupRev2
--   MandGroup
--    cvDsx1AlmHistoryGroupRev1
--   MandGroup
--    cvDsx1StatsGroup
--   OptGroup
--    cvDsx1ConfGroupSup1

cvDsx1ComplianceRev5 OBJECT IDENTIFIER ::= { cvDsx1MIBCompliances 6 }
-- MODULE-COMPLIANCE
--  Status
--    mandatory
--  Descr
--    The compliance statement for objects related
--     to VISM DS1/E1 MIB.
--  Module
--    >>current<<
--   MandGroup
--    cvDsx1ConfGroupRev2
--   MandGroup
--    cvDsx1AlmHistoryGroupRev1
--   MandGroup
--    cvDsx1StatsGroup
--   OptGroup
--    cvDsx1ConfGroupSup1
--   OptGroup
--    cvDsx1AlarmLogGroup
--   OptGroup
--    cvDsx1ElecSigGroup


END
