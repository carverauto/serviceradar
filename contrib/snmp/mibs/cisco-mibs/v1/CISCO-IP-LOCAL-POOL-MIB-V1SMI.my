-- MIB file created 03-Dec-2010 19:42:31, by
--   SMICng version 2.2.11-beta(PRO)(Solaris), January 20, 2001. Enterprise key cisco.com

CISCO-IP-LOCAL-POOL-MIB DEFINITIONS ::= BEGIN

-- From file: "CISCO-IP-LOCAL-POOL-MIB.my"
-- Compile options "4 7 F H N W 03 06 0B 0G 0N 0T"

IMPORTS
    TruthValue, RowStatus
            FROM SNMPv2-TC-v1
    InetAddressType, InetAddress
            FROM INET-ADDRESS-MIB
    InterfaceIndexOrZero
            FROM IF-MIB
    SnmpAdminString
            FROM SNMP-FRAMEWORK-MIB
    ciscoMgmt
            FROM CISCO-SMI
    Gauge
            FROM RFC1155-SMI
    OBJECT-TYPE
            FROM RFC-1212
    TRAP-TYPE
            FROM RFC-1215;

ciscoIpLocalPoolMIB OBJECT IDENTIFIER ::= { ciscoMgmt 326 }
-- MODULE-IDENTITY
--  LastUpdated
--    200711120000Z
--  OrgName
--    Cisco Systems, Inc.
--  ContactInfo
--    Cisco Systems
--    Customer Service
--    
--    Postal: 170 W Tasman Drive
--    San Jose, CA  95134
--    USA
--    
--    Tel: +1 800 553-NETS
--    
--    E-mail: cs-snmp@cisco.com
--  Descr
--    This MIB defines the configuration and monitoring capabilities
--    relating to local IP pools.
--    
--    Local IP pools have the following characteristics:
--    
--    - An IP local pool consists of one or more IP address ranges.
--    
--    - An IP pool group consists of one or more IP local pools.
--    
--    - An IP local pool can only belong to one IP pool group.
--    
--    - IP local pools that belong to different groups can have
--      overlapping addresses.
--    
--    - IP local pool names are unique even when they belong to
--      different groups.
--    
--    - Addresses within an IP pool group can not overlap.
--    
--    - IP local pools without an explicit group name are considered
--      members of the base system group.  In this MIB, the base
--      system group is represented by a null IP pool group name.
--    
--    This MIB defines objects that expose the relationship between
--    IP pool groups and IP local pools.  There exist other objects
--    that maintain statistics about the address usage of IP local
--    pools.
--  RevDate
--    200711120000Z
--  RevDescr
--    Added one object to the cIpLocalPoolConfigTable:
--    - cIpLocalPoolPriority
--    
--    Added ciscoIpLocalPoolMIBCompliance2 MODULE-COMPLIANCE 
--    Added ciscoIpLocalPoolPriorityGroup OBJECT-GROUP
--  RevDate
--    200501110000Z
--  RevDescr
--    Added two objects to the cIpLocalPoolStatsTable:
--    - cIpLocalPoolPercentAddrThldLo
--    - cIpLocalPoolPercentAddrThldHi
--    
--    Added two notifications:
--    - cilpPercentAddrUsedHiNotif
--    - cilpPercentAddrUsedLoNotif
--  RevDate
--    200304032000Z
--  RevDescr
--    Initial version of this MIB module.

ciscoIpLocalPoolMIBNotifs OBJECT IDENTIFIER ::= { ciscoIpLocalPoolMIB 0 }
ciscoIpLocalPoolMIBObjects OBJECT IDENTIFIER ::= { ciscoIpLocalPoolMIB 1 }
ciscoIpLocalPoolMIBConform OBJECT IDENTIFIER ::= { ciscoIpLocalPoolMIB 2 }
cIpLocalPoolConfig OBJECT IDENTIFIER ::= { ciscoIpLocalPoolMIBObjects 1 }
cIpLocalPoolGroup OBJECT IDENTIFIER ::= { ciscoIpLocalPoolMIBObjects 2 }
cIpLocalPoolStats OBJECT IDENTIFIER ::= { ciscoIpLocalPoolMIBObjects 3 }
ciscoIpLocalPoolMIBCompliances OBJECT IDENTIFIER ::= { ciscoIpLocalPoolMIBConform 1 }
ciscoIpLocalPoolMIBGroups OBJECT IDENTIFIER ::= { ciscoIpLocalPoolMIBConform 2 }

CIpLocalPoolName ::= OCTET STRING(SIZE(1..48))
-- TEXTUAL-CONVENTION
--  Status
--    mandatory
--  Descr
--    A non-empty string that uniquely identifies an IP local pool.

CIpLocalPoolGroupNameOrNull ::= OCTET STRING(SIZE(0..48))
-- TEXTUAL-CONVENTION
--  Status
--    mandatory
--  Descr
--    A string that uniquely identifies an IP pool group. The value
--    of null is object-specific and must therefore be defined as part
--    of the description of any object which uses this syntax.

CIpLocalPoolPercentage ::= Gauge(0..100)
-- TEXTUAL-CONVENTION
--  DspHint
--    d-2
--  Status
--    mandatory
--  Descr
--    A percentage associated with the addresses used in a IP local
--    pool.

cIpLocalPoolNotificationsEnable OBJECT-TYPE
    SYNTAX TruthValue
--    Rsyntax INTEGER {
--        true(1),
--        false(2)
--        }
    ACCESS read-write
    STATUS mandatory
    DESCRIPTION
        "An indication of whether the notifications defined by the
        ciscoIpLocalPoolNotifGroup are enabled."
    ::= { cIpLocalPoolConfig 1 }

cIpLocalPoolConfigTable OBJECT-TYPE
    SYNTAX SEQUENCE OF CIpLocalPoolConfigEntry
    ACCESS not-accessible
    STATUS mandatory
    DESCRIPTION
        "This table manages the creation, modification, and deletion
        of IP local pools using the RowStatus textual convention.  An
        entry in this table defines an IP address range that is
        associated with an IP local pool.
        
        A conceptual row in this table can not be modified while
        cIpLocalPoolRowStatus is set to 'active'.
        
        Since IP local pool names are unique even when they belong to
        different groups, and addresses within a group can not overlap,
        a row in this table is uniquely indexed by the pool name, and by
        the low address of the IP local pool together with its address
        type."
    ::= { cIpLocalPoolConfig 2 }

cIpLocalPoolConfigEntry OBJECT-TYPE
    SYNTAX CIpLocalPoolConfigEntry
    ACCESS not-accessible
    STATUS mandatory
    DESCRIPTION
        "Each entry provides information about a particular IP local
        pool, including the number of free and used addresses and its priority."
    INDEX { cIpLocalPoolName, cIpLocalPoolAddrType, cIpLocalPoolAddressLo }
    ::= { cIpLocalPoolConfigTable 1 }

CIpLocalPoolConfigEntry ::= SEQUENCE {
    cIpLocalPoolName CIpLocalPoolName,
    cIpLocalPoolAddrType InetAddressType,
    cIpLocalPoolAddressLo InetAddress,
    cIpLocalPoolAddressHi InetAddress,
    cIpLocalPoolFreeAddrs Gauge,
    cIpLocalPoolInUseAddrs Gauge,
    cIpLocalPoolGroupContainedIn CIpLocalPoolGroupNameOrNull,
    cIpLocalPoolRowStatus RowStatus,
    cIpLocalPoolPriority Gauge
    }

cIpLocalPoolName OBJECT-TYPE
    SYNTAX CIpLocalPoolName
--    Rsyntax OCTET STRING(SIZE(1..48))
    ACCESS not-accessible
    STATUS mandatory
    DESCRIPTION
        "An arbitrary non-empty string that uniquely identifies the IP
        local pool.  This name must be unique among all the local IP
        pools even when they belong to different pool groups."
    ::= { cIpLocalPoolConfigEntry 1 }

cIpLocalPoolAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS not-accessible
    STATUS mandatory
    DESCRIPTION
        "This object specifies the address type of cIpLocalPoolAddressLo
        and cIpLocalPoolAddressHi."
    ::= { cIpLocalPoolConfigEntry 2 }

cIpLocalPoolAddressLo OBJECT-TYPE
    SYNTAX InetAddress
--    Rsyntax OCTET STRING(SIZE(0..255))
    ACCESS not-accessible
    STATUS mandatory
    DESCRIPTION
        "This object specifies the first IP address of the range of IP
        addresses contained by this pool entry.  The address type of
        this object is described by cIpLocalPoolAddrType.
        
        This address must be less than or equal to the address in
        cIpLocalPoolAddressHi."
    ::= { cIpLocalPoolConfigEntry 3 }

cIpLocalPoolAddressHi OBJECT-TYPE
    SYNTAX InetAddress
--    Rsyntax OCTET STRING(SIZE(0..255))
    ACCESS read-write
    STATUS mandatory
    DESCRIPTION
        "This object specifies the last IP address of the range of IP
        addresses mapped by this pool entry.  The address type of this
        object is described by cIpLocalPoolAddrType.  If only a single
        address is being mapped, the value of this object is equal to
        the value of cIpLocalPoolAddressLo."
    ::= { cIpLocalPoolConfigEntry 4 }

cIpLocalPoolFreeAddrs OBJECT-TYPE
    SYNTAX Gauge
    ACCESS read-only
    STATUS mandatory
    DESCRIPTION
        "The number of IP addresses available for use in the range of
        IP addresses."
    ::= { cIpLocalPoolConfigEntry 5 }

cIpLocalPoolInUseAddrs OBJECT-TYPE
    SYNTAX Gauge
    ACCESS read-only
    STATUS mandatory
    DESCRIPTION
        "The number of IP addresses being used in the range of IP
        addresses."
    ::= { cIpLocalPoolConfigEntry 6 }

cIpLocalPoolGroupContainedIn OBJECT-TYPE
    SYNTAX CIpLocalPoolGroupNameOrNull
--    Rsyntax OCTET STRING(SIZE(0..48))
    ACCESS read-write
    STATUS mandatory
    DESCRIPTION
        "This object relates an IP local pool to its IP pool group.
        
        A null string indicates this IP local pool is not contained in a
        named IP pool group, but that it is contained in the base IP
        pool group.  An IP local pool can only belong to one IP pool
        group."
    DEFVAL { "" }
    ::= { cIpLocalPoolConfigEntry 7 }

cIpLocalPoolRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object facilitates the creation, or deletion of a
        conceptual row in this table."
    ::= { cIpLocalPoolConfigEntry 8 }

cIpLocalPoolPriority OBJECT-TYPE
    SYNTAX Gauge(1..255)
    ACCESS read-write
    STATUS mandatory
    DESCRIPTION
        "This object specifies priority of the IP local pool,
        where smaller value indicates the lower priority.
        The priority value is used in assigning IP Address 
        from local pools."
    DEFVAL { 1 }
    ::= { cIpLocalPoolConfigEntry 9 }

cIpLocalPoolGroupContainsTable OBJECT-TYPE
    SYNTAX SEQUENCE OF CIpLocalPoolGroupContainsEntry
    ACCESS not-accessible
    STATUS mandatory
    DESCRIPTION
        "A table which exposes the container/'containee' relationships
        between local IP pools and IP pool groups.
        
        Entries in this table are created or deleted as a by-product of
        creating or deleting entries in the cIpLocalPoolConfigTable.
        
        When an entry is created and activated in the
        cIpLocalPoolConfigTable table, an entry in this table will come
        into existence if it does not already exist.
        
        When an entry is deleted in the cIpLocalPoolConfigTable table,
        if there is no other entry existing in that table with the same
        cIpLocalPoolGroupContainedIn and cIpLocalPoolName, the entry in
        this table with the respective cIpLocalPoolGroupName and
        cIpLocalPoolName indices will be removed."
    ::= { cIpLocalPoolGroup 1 }

cIpLocalPoolGroupContainsEntry OBJECT-TYPE
    SYNTAX CIpLocalPoolGroupContainsEntry
    ACCESS not-accessible
    STATUS mandatory
    DESCRIPTION
        "Each entry describes single container/'containee'
        relationship.
        
        Pool names can only be associated with one group.  Pools carry
        implicit group identifiers because pool names can only be
        associated with one group.  An entry in this table describes
        such an association."
    INDEX { cIpLocalPoolGroupName, cIpLocalPoolChildIndex }
    ::= { cIpLocalPoolGroupContainsTable 1 }

CIpLocalPoolGroupContainsEntry ::= SEQUENCE {
    cIpLocalPoolGroupName CIpLocalPoolGroupNameOrNull,
    cIpLocalPoolChildIndex CIpLocalPoolName
    }

cIpLocalPoolGroupName OBJECT-TYPE
    SYNTAX CIpLocalPoolGroupNameOrNull
--    Rsyntax OCTET STRING(SIZE(0..48))
    ACCESS not-accessible
    STATUS mandatory
    DESCRIPTION
        "A unique group name that identifies the IP pool group.  The
        null string represents the base IP pool group."
    ::= { cIpLocalPoolGroupContainsEntry 1 }

cIpLocalPoolChildIndex OBJECT-TYPE
    SYNTAX CIpLocalPoolName
--    Rsyntax OCTET STRING(SIZE(1..48))
    ACCESS read-only
    STATUS mandatory
    DESCRIPTION
        "The value of cIpLocalPoolName for the contained IP local pool."
    ::= { cIpLocalPoolGroupContainsEntry 2 }

cIpLocalPoolGroupTable OBJECT-TYPE
    SYNTAX SEQUENCE OF CIpLocalPoolGroupEntry
    ACCESS not-accessible
    STATUS mandatory
    DESCRIPTION
        "This table provides statistics for configured IP pool groups.
        
        Entries in this table are created as the result of adding a new
        IP pool group to the cIpLocalPoolConfigTable.
        
        Entries in this table are deleted as the result of removing all
        IP local pools that are contained in an IP pool group in the
        cIpLocalPoolConfigTable.
        
        An entry in this table is uniquely indexed by IP pool group
        name."
    ::= { cIpLocalPoolGroup 2 }

cIpLocalPoolGroupEntry OBJECT-TYPE
    SYNTAX CIpLocalPoolGroupEntry
    ACCESS not-accessible
    STATUS mandatory
    DESCRIPTION
        "Each entry provides information about a particular IP pool
        group and the number of free and used addresses in an IP pool
        group."
    INDEX { cIpLocalPoolGroupName }
    ::= { cIpLocalPoolGroupTable 1 }

CIpLocalPoolGroupEntry ::= SEQUENCE {
    cIpLocalPoolGroupFreeAddrs Gauge,
    cIpLocalPoolGroupInUseAddrs Gauge
    }

cIpLocalPoolGroupFreeAddrs OBJECT-TYPE
    SYNTAX Gauge
    ACCESS read-only
    STATUS mandatory
    DESCRIPTION
        "The number of IP addresses available for use in the IP pool
        group."
    ::= { cIpLocalPoolGroupEntry 1 }

cIpLocalPoolGroupInUseAddrs OBJECT-TYPE
    SYNTAX Gauge
    ACCESS read-only
    STATUS mandatory
    DESCRIPTION
        "The number of IP addresses that have been allocated from the
        IP pool group."
    ::= { cIpLocalPoolGroupEntry 2 }

cIpLocalPoolStatsTable OBJECT-TYPE
    SYNTAX SEQUENCE OF CIpLocalPoolStatsEntry
    ACCESS not-accessible
    STATUS mandatory
    DESCRIPTION
        "A table providing statistics for each IP local pool.
        
        Entries in this table are created as the result of adding a new
        IP local pool to the cIpLocalPoolConfigTable.
        
        Entries in this table are deleted as the result of removing all
        the address ranges that are contained in an IP local pool in the
        cIpLocalPoolConfigTable.
        
        Entries in this table are uniquely indexed by the name of the IP
        local pool."
    ::= { cIpLocalPoolStats 1 }

cIpLocalPoolStatsEntry OBJECT-TYPE
    SYNTAX CIpLocalPoolStatsEntry
    ACCESS not-accessible
    STATUS mandatory
    DESCRIPTION
        "Each entry provides statistical information about a particular
        IP local pool, and the total number of free and used addresses
        of all the ranges in an IP local pool."
    INDEX { cIpLocalPoolName }
    ::= { cIpLocalPoolStatsTable 1 }

CIpLocalPoolStatsEntry ::= SEQUENCE {
    cIpLocalPoolStatFreeAddrs Gauge,
    cIpLocalPoolStatInUseAddrs Gauge,
    cIpLocalPoolStatHiWaterUsedAddrs Gauge,
    cIpLocalPoolStatInUseAddrThldLo Gauge,
    cIpLocalPoolStatInUseAddrThldHi Gauge,
    cIpLocalPoolPercentAddrThldLo CIpLocalPoolPercentage,
    cIpLocalPoolPercentAddrThldHi CIpLocalPoolPercentage
    }

cIpLocalPoolStatFreeAddrs OBJECT-TYPE
    SYNTAX Gauge
    ACCESS read-only
    STATUS mandatory
    DESCRIPTION
        "The number of IP addresses available for use in this IP local
        pool."
    ::= { cIpLocalPoolStatsEntry 1 }

cIpLocalPoolStatInUseAddrs OBJECT-TYPE
    SYNTAX Gauge
    ACCESS read-only
    STATUS mandatory
    DESCRIPTION
        "The number of IP addresses being used in this IP local pool."
    ::= { cIpLocalPoolStatsEntry 2 }

cIpLocalPoolStatHiWaterUsedAddrs OBJECT-TYPE
    SYNTAX Gauge
    ACCESS read-write
    STATUS mandatory
    DESCRIPTION
        "This object contains the high water mark of used addresses
        in an IP local pool since pool creation, since the system was
        restarted, or since this object was reset, whichever occurred
        last.  This object can only be set to zero, and by doing so, it
        is reset to the value of cIpLocalPoolStatInUseAddrs.
        
        Since the number of addresses in a pool can be reduced (e.g. by
        deleting one of its ranges), the value of this object may be
        greater than the sum of cIpLocalPoolStatFreeAddrs and
        cIpLocalPoolStatInUseAddrs."
    ::= { cIpLocalPoolStatsEntry 3 }

cIpLocalPoolStatInUseAddrThldLo OBJECT-TYPE
    SYNTAX Gauge(0..4294967295)
    ACCESS read-write
    STATUS mandatory
    DESCRIPTION
        "When the number of used addresses in an IP local pool falls
        below this threshold value, the ciscoIpLocalPoolInUseAddrNoti
        notification will be rearmed.
        
        The value of this object should never be greater than the value
        of cIpLocalPoolStatInUseAddrThldHi."
    DEFVAL { 0 }
    ::= { cIpLocalPoolStatsEntry 4 }

cIpLocalPoolStatInUseAddrThldHi OBJECT-TYPE
    SYNTAX Gauge(0..4294967295)
    ACCESS read-write
    STATUS mandatory
    DESCRIPTION
        "When the number of used addresses in an IP local pool
        is equal or exceeds this threshold value, a
        ciscoIpLocalPoolInUseAddrNoti notification will be generated.
        Once this notification is generated, it will be disarmed and it
        will not be generated again until the number of used address
        falls below the value indicated by
        cIpLocalPoolStatInUseAddrThldLo.
        
        The value of this object should never be smaller than the value
        of cIpLocalPoolStatInUseAddrThldLo."
    DEFVAL { 4294967295 }
    ::= { cIpLocalPoolStatsEntry 5 }

cIpLocalPoolPercentAddrThldLo OBJECT-TYPE
    SYNTAX CIpLocalPoolPercentage
--    Rsyntax Gauge(0..100)
    ACCESS read-write
    STATUS mandatory
    DESCRIPTION
        "When the percentage of used addresses in an IP local pool
        falls below this threshold value, a cilpPercentAddrUsedLoNotif
        notification will be generated.  Once the notification is
        generated, it will be disarmed and it will not be generated
        again until the number of used addresses equals or exceeds the
        value indicated by cIpLocalPoolPercentAddrThldHi.
        
        The value of this object should never be greater than the value
        of cIpLocalPoolPercentAddrThldHi."
    DEFVAL { 0 }
    ::= { cIpLocalPoolStatsEntry 6 }

cIpLocalPoolPercentAddrThldHi OBJECT-TYPE
    SYNTAX CIpLocalPoolPercentage
--    Rsyntax Gauge(0..100)
    ACCESS read-write
    STATUS mandatory
    DESCRIPTION
        "When the percentage of used addresses in an IP local pool
        is equal or exceeds this threshold value, a
        cilpPercentAddrUsedHiNotif notification will be generated. Once
        the notification is generated, it will be disarmed and it will
        not be generated again until the number of used addresses falls
        below the value indicated by cIpLocalPoolPercentAddrThldLo.
        
        The value of this object should never be smaller than the value
        of cIpLocalPoolPercentAddrThldLo."
    DEFVAL { 100 }
    ::= { cIpLocalPoolStatsEntry 7 }

cIpLocalPoolAllocTable OBJECT-TYPE
    SYNTAX SEQUENCE OF CIpLocalPoolAllocEntry
    ACCESS not-accessible
    STATUS mandatory
    DESCRIPTION
        "This table lists all addresses that have been allocated out of
        an IP local pool.
        
        Entries in this table are created when a remote peer allocates
        an address from one of the IP local pools in the
        cIpLocalPoolConfigTable.
        
        Entries in this table are deleted when a remote peer deallocates
        an address from one of the IP local pool in the
        cIpLocalPoolConfigTable.
        
        Entries in this table are uniquely indexed by the name of the IP
        local pool, and the allocated address, together with its address
        type."
    ::= { cIpLocalPoolStats 2 }

cIpLocalPoolAllocEntry OBJECT-TYPE
    SYNTAX CIpLocalPoolAllocEntry
    ACCESS not-accessible
    STATUS mandatory
    DESCRIPTION
        "Each entry refers to conceptual row that associates an IP
        addresses with the interface where the request was received, and
        the user that requested the address."
    INDEX { cIpLocalPoolName, cIpLocalPoolAllocAddrType, cIpLocalPoolAllocAddr }
    ::= { cIpLocalPoolAllocTable 1 }

CIpLocalPoolAllocEntry ::= SEQUENCE {
    cIpLocalPoolAllocAddrType InetAddressType,
    cIpLocalPoolAllocAddr InetAddress,
    cIpLocalPoolAllocIfIndex InterfaceIndexOrZero,
    cIpLocalPoolAllocUser SnmpAdminString
    }

cIpLocalPoolAllocAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS not-accessible
    STATUS mandatory
    DESCRIPTION
        "This object specifies the address type of
        cIpLocalPoolAllocAddr."
    ::= { cIpLocalPoolAllocEntry 1 }

cIpLocalPoolAllocAddr OBJECT-TYPE
    SYNTAX InetAddress
--    Rsyntax OCTET STRING(SIZE(0..255))
    ACCESS not-accessible
    STATUS mandatory
    DESCRIPTION
        "This object specifies the allocated IP address.  The address
        type of this object is described by cIpLocalPoolAllocAddrType."
    ::= { cIpLocalPoolAllocEntry 2 }

cIpLocalPoolAllocIfIndex OBJECT-TYPE
    SYNTAX InterfaceIndexOrZero
--    Rsyntax INTEGER(0..2147483647)
    ACCESS read-only
    STATUS mandatory
    DESCRIPTION
        "This object indicates the interface from which the allocation
        message was sent.
        
        In the case that the interface can not be determined, the value
        of this object will be zero."
    ::= { cIpLocalPoolAllocEntry 3 }

cIpLocalPoolAllocUser OBJECT-TYPE
    SYNTAX SnmpAdminString
--    Rsyntax OCTET STRING(SIZE(0..255))
    ACCESS read-only
    STATUS mandatory
    DESCRIPTION
        "This object indicates the user name of the person from whom the
        allocation message was sent.
        
        In the case that the user name can not be determined, the value
        of this object will the null string."
    ::= { cIpLocalPoolAllocEntry 4 }

ciscoIpLocalPoolInUseAddrNoti TRAP-TYPE
-- Reverse mappable trap
    ENTERPRISE ciscoIpLocalPoolMIB
    VARIABLES {
        cIpLocalPoolStatFreeAddrs, cIpLocalPoolStatInUseAddrs }
--  Status
--    mandatory
    DESCRIPTION
        "A notification indicating that number of used addresses of an
        IP local pool exceeded the threshold value indicated by
        cIpLocalPoolStatInUseAddrThldHi."
    ::= 1

cilpPercentAddrUsedLoNotif TRAP-TYPE
-- Reverse mappable trap
    ENTERPRISE ciscoIpLocalPoolMIB
    VARIABLES {
        cIpLocalPoolStatFreeAddrs, cIpLocalPoolStatInUseAddrs }
--  Status
--    mandatory
    DESCRIPTION
        "A notification indicating that the percentage of used addresses
        of an IP local pool went below the threshold value indicated by
        cIpLocalPoolPercentAddrThldLo."
    ::= 2

cilpPercentAddrUsedHiNotif TRAP-TYPE
-- Reverse mappable trap
    ENTERPRISE ciscoIpLocalPoolMIB
    VARIABLES {
        cIpLocalPoolStatFreeAddrs, cIpLocalPoolStatInUseAddrs }
--  Status
--    mandatory
    DESCRIPTION
        "A notification indicating that the percentage of used addresses
        of an IP local pool is equal to or exceeds the threshold value
        indicated by cIpLocalPoolPercentAddrThldHi."
    ::= 3

ciscoIpLocalPoolConfigGroup OBJECT IDENTIFIER ::= { ciscoIpLocalPoolMIBGroups 1 }
-- OBJECT-GROUP
--  Status
--    mandatory
--  Descr
--    Objects for providing configuration for IP local pools.
--  objects
--    cIpLocalPoolNotificationsEnable, cIpLocalPoolAddressHi, 
--    cIpLocalPoolFreeAddrs, cIpLocalPoolInUseAddrs, 
--    cIpLocalPoolGroupContainedIn, cIpLocalPoolRowStatus

ciscoIpLocalPoolGroupGroup OBJECT IDENTIFIER ::= { ciscoIpLocalPoolMIBGroups 2 }
-- OBJECT-GROUP
--  Status
--    mandatory
--  Descr
--    Objects for providing configuration for IP local pools.
--  objects
--    cIpLocalPoolChildIndex, cIpLocalPoolGroupFreeAddrs, 
--    cIpLocalPoolGroupInUseAddrs

ciscoIpLocalPoolStatsGroup OBJECT IDENTIFIER ::= { ciscoIpLocalPoolMIBGroups 3 }
-- OBJECT-GROUP
--  Status
--    mandatory
--  Descr
--    Objects for providing IP local pool statistics and status.
--  objects
--    cIpLocalPoolStatFreeAddrs, cIpLocalPoolStatInUseAddrs, 
--    cIpLocalPoolStatHiWaterUsedAddrs, 
--    cIpLocalPoolStatInUseAddrThldLo, 
--    cIpLocalPoolStatInUseAddrThldHi, cIpLocalPoolAllocIfIndex, 
--    cIpLocalPoolAllocUser

ciscoIpLocalPoolStatsGroupSup1 OBJECT IDENTIFIER ::= { ciscoIpLocalPoolMIBGroups 5 }
-- OBJECT-GROUP
--  Status
--    mandatory
--  Descr
--    Supplemental objects for providing IP local pool statistics and
--    status.
--  objects
--    cIpLocalPoolPercentAddrThldLo, cIpLocalPoolPercentAddrThldHi

ciscoIpLocalPoolPriorityGroup OBJECT IDENTIFIER ::= { ciscoIpLocalPoolMIBGroups 7 }
-- OBJECT-GROUP
--  Status
--    mandatory
--  Descr
--    A collection of object which provides priority configuration of IP local pools.
--  objects
--    cIpLocalPoolPriority

ciscoIpLocalPoolNotifGroup OBJECT IDENTIFIER ::= { ciscoIpLocalPoolMIBGroups 4 }
-- NOTIFICATION-GROUP
--  Status
--    mandatory
--  Descr
--    The collection of notifications used for monitoring IP local
--    pool utilization.
--  notifications
--    ciscoIpLocalPoolInUseAddrNoti

ciscoIpLocalPoolNotifGroupSup1 OBJECT IDENTIFIER ::= { ciscoIpLocalPoolMIBGroups 6 }
-- NOTIFICATION-GROUP
--  Status
--    mandatory
--  Descr
--    The collection of suplemantal notifications used for monitoring
--    IP local pool utilization.
--  notifications
--    cilpPercentAddrUsedLoNotif, cilpPercentAddrUsedHiNotif

ciscoIpLocalPoolMIBCompliance OBJECT IDENTIFIER ::= { ciscoIpLocalPoolMIBCompliances 1 }
-- MODULE-COMPLIANCE
--  Status
--    deprecated
--  Descr
--    The compliance statement for entities which implement the Cisco
--    IP Local Pool MIB.
--  Module
--    >>current<<
--   MandGroup
--    ciscoIpLocalPoolConfigGroup
--   MandGroup
--    ciscoIpLocalPoolStatsGroup
--   OptGroup
--    ciscoIpLocalPoolGroupGroup
--   ObjVar
--    cIpLocalPoolAddressHi
--   ObjVar
--    cIpLocalPoolGroupContainedIn
--   ObjVar
--    cIpLocalPoolRowStatus

ciscoIpLocalPoolMIBCompliance1 OBJECT IDENTIFIER ::= { ciscoIpLocalPoolMIBCompliances 2 }
-- MODULE-COMPLIANCE
--  Status
--    deprecated
--  Descr
--    The compliance statement for entities which implement the Cisco
--    IP Local Pool MIB.
--  Module
--    >>current<<
--   MandGroup
--    ciscoIpLocalPoolConfigGroup
--   MandGroup
--    ciscoIpLocalPoolStatsGroup
--   MandGroup
--    ciscoIpLocalPoolNotifGroup
--   OptGroup
--    ciscoIpLocalPoolGroupGroup
--   OptGroup
--    ciscoIpLocalPoolStatsGroupSup1
--   OptGroup
--    ciscoIpLocalPoolNotifGroupSup1
--   ObjVar
--    cIpLocalPoolAddressHi
--   ObjVar
--    cIpLocalPoolGroupContainedIn
--   ObjVar
--    cIpLocalPoolRowStatus

ciscoIpLocalPoolMIBCompliance2 OBJECT IDENTIFIER ::= { ciscoIpLocalPoolMIBCompliances 3 }
-- MODULE-COMPLIANCE
--  Status
--    mandatory
--  Descr
--    The compliance statement for entities which implement the Cisco
--    IP Local Pool MIB.
--  Module
--    >>current<<
--   MandGroup
--    ciscoIpLocalPoolConfigGroup
--   MandGroup
--    ciscoIpLocalPoolStatsGroup
--   MandGroup
--    ciscoIpLocalPoolNotifGroup
--   MandGroup
--    ciscoIpLocalPoolPriorityGroup
--   OptGroup
--    ciscoIpLocalPoolGroupGroup
--   OptGroup
--    ciscoIpLocalPoolStatsGroupSup1
--   OptGroup
--    ciscoIpLocalPoolNotifGroupSup1
--   ObjVar
--    cIpLocalPoolAddressHi
--   ObjVar
--    cIpLocalPoolGroupContainedIn
--   ObjVar
--    cIpLocalPoolRowStatus


END
