-- MIB file created 06-Jun-2011 14:20:16, by
--   SMICng version 2.2.11-beta(PRO)(Solaris), January 20, 2001. Enterprise key cisco.com

CISCO-GSLB-SYSTEM-MIB DEFINITIONS ::= BEGIN

-- From file: "CISCO-GSLB-SYSTEM-MIB.my"
-- Compile options "4 7 F H N W 03 06 0B 0G 0N 0T"

IMPORTS
    SnmpAdminString
            FROM SNMP-FRAMEWORK-MIB
    RowStatus, StorageType, TruthValue
            FROM SNMPv2-TC-v1
    InetAddressType, InetAddress, InetAddressDNS
            FROM INET-ADDRESS-MIB
    sysName
            FROM RFC1213-MIB
    InterfaceIndexOrZero
            FROM IF-MIB
    CiscoGslbNodeServices, CiscoGslbPeerStatus
            FROM CISCO-GSLB-TC-MIB
    ciscoMgmt
            FROM CISCO-SMI
    Counter, Gauge
            FROM RFC1155-SMI
    OBJECT-TYPE
            FROM RFC-1212
    TRAP-TYPE
            FROM RFC-1215;

ciscoGslbSystemMIB OBJECT IDENTIFIER ::= { ciscoMgmt 589 }
-- MODULE-IDENTITY
--  LastUpdated
--    201106060000Z
--  OrgName
--    Cisco Systems, Inc.
--  ContactInfo
--    Cisco Systems
--    Customer Service
--    
--    Postal: 170 W Tasman Drive
--    San Jose, CA  95134
--    USA
--    
--    Tel: +1 800 553-NETS
--    
--    E-mail: cs-slb@cisco.com
--  Descr
--    This MIB module defines objects for network and system
--    information of Global Server Load Balancer(GSLB) as a
--    network device.  A GSLB device is used to allocate the
--    least-loaded and proximate resource to the requester.
--    The MIB objects define information about GLSB status,
--    GSLB's peers (other GSLB devices available on its
--    network with which it interacts) information & status,
--    GSLB's proximity information related statistics, etc.
--    Further it defines related notifications.
--    
--    Acronyms and their description:
--    
--    DNS          : Domain Name Service (RFC1035).
--    
--    D-proxy      : Local DNS name server of the client.
--    
--    Proximity    : Refers to the distance or delay, in terms
--                   of network topology and not geographic
--                   distance, between the requesting client's
--                   D-proxy and the resources corresponding
--                   to that request.
--    
--    Proximity    : To respond to DNS requests with the most
--    probing        proximate answers, the GSLB device
--                   communicates with a probing device located
--                   in each proximity zone to gather round-trip
--                   time (RTT) metric information measured
--                   between the requesting client's D-proxy 
--                   and the zone.  The GSLB device then directs
--                   client requests to an available resource
--                   with the lowest RTT value.
--    
--    Probed       : This is the device to which the GSLB device
--    device         sends a proximity probe. This is done to
--                   learn the proximity of the device.
--    
--    DRP          : Director Response Protocol (DRP) is a
--                   simple User Datagram Protocol (UDP)
--                   based application developed by
--                   Cisco Systems, Inc.  DRP enables
--                   Cisco Distributed-Director product to
--                   perform global load distribution and
--                   content routing in a sophisticated manner
--                   that accounts for server availability,
--                   relative client-to-server topological
--                   proximities, and client-to-server link
--                   latency to determine the best server.
--                   Using routing table intelligence in the
--                   network infrastructure, Distributed-Director
--                   transparently redirects end-user service
--                   requests to the closest server, as
--                   determined by client-to-server topological
--                   proximity or client-to-server link latency,
--                   resulting in increased access performance
--                   seen by the end user.
--    
--    Region       : Higher-level geographical groupings that
--                   may contain one or more locations.  Each
--                   location should be assigned to a region.
--    
--    Location     : Grouping for devices with common
--                   geographical attributes.  A location is
--                   assigned to a region.
--                   A location is also assigned to a zone,
--                   which is used for proximity probing.
--    
--    Zone         : A network can be logically partioned into
--                   zones based on the arrangement of devices
--                   and network partion characteristics.
--                   A zone can be geographically related to
--                   data centers in a continent, a country,
--                   or a major city.  All devices, such as web
--                   servers in a data center, that are located
--                   in the same zone have the same proximity
--                   value when communicating with other areas
--                   of the Internet.  Within each zone, there
--                   is an active probing device that is
--                   configured to accept probing instructions
--                   from any GSLB device.  Probing here refers
--                   to the process of measuring RTT from one
--                   probing device to a requesting D-proxy.
--  RevDate
--    201106060000Z
--  RevDescr
--    -Deprecated cgsRegionTable and replaced it with
--    cgsRegionIdTable
--    
--    -Deprecated ciscoGslbSystemMIBCompliance and replaced it with
--    ciscoGslbSystemMIBComplianceRev1
--    
--    -Deprecated ciscoGslbSystemResourceGroup and replaced it with
--    ciscoGslbSystemResourceLocationGroup and 
--    ciscoGslbSystemResourceRegionGroup
--  RevDate
--    200612040000Z
--  RevDescr
--    Initial version of this MIB module.

ciscoGslbSystemMIBNotifs OBJECT IDENTIFIER ::= { ciscoGslbSystemMIB 0 }
ciscoGslbSystemMIBObjects OBJECT IDENTIFIER ::= { ciscoGslbSystemMIB 1 }
ciscoGslbSystemMIBConform OBJECT IDENTIFIER ::= { ciscoGslbSystemMIB 2 }
cgsNotifControl OBJECT IDENTIFIER ::= { ciscoGslbSystemMIBObjects 1 }
cgsNotifObjects OBJECT IDENTIFIER ::= { ciscoGslbSystemMIBObjects 2 }
cgsGeneral      OBJECT IDENTIFIER ::= { ciscoGslbSystemMIBObjects 3 }
cgsPeer         OBJECT IDENTIFIER ::= { ciscoGslbSystemMIBObjects 4 }
cgsProxZoneStats OBJECT IDENTIFIER ::= { ciscoGslbSystemMIBObjects 5 }
cgsResources    OBJECT IDENTIFIER ::= { ciscoGslbSystemMIBObjects 6 }
ciscoGslbSystemMIBCompliances OBJECT IDENTIFIER ::= { ciscoGslbSystemMIBConform 1 }
ciscoGslbSystemMIBGroups OBJECT IDENTIFIER ::= { ciscoGslbSystemMIBConform 2 }

cgsNodeService OBJECT-TYPE
    SYNTAX CiscoGslbNodeServices
--    Rsyntax INTEGER {
--        primary(1),
--        standby(2),
--        secondary(3)
--        }
    ACCESS read-write
    STATUS mandatory
    DESCRIPTION
        "This object specifies the type of role of the GSLB
        device amongst its peers."
    ::= { cgsGeneral 1 }

cgsNodeCommIfName OBJECT-TYPE
    SYNTAX SnmpAdminString
--    Rsyntax OCTET STRING(SIZE(0..255))
    ACCESS read-write
    STATUS mandatory
    DESCRIPTION
        "This object specifies the textual name of the interface
        used by the GSLB device to communicate with peer GSLB
        devices.  The value of this object must be same as the
        ifName reported by IF-MIB  for the interface instance."
    ::= { cgsGeneral 2 }

cgsNodeCommIfIndex OBJECT-TYPE
    SYNTAX InterfaceIndexOrZero
--    Rsyntax INTEGER(0..2147483647)
    ACCESS read-only
    STATUS mandatory
    DESCRIPTION
        "This object is used as an identifier for the interface
        used by the GSLB device to communicate with peer GSLB
        devices.  The value of this object must be same as the
        ifIndex reported by IF-MIB for the interface identified
        by cgsNodeCommIfName."
    ::= { cgsGeneral 3 }

cgsNodeStatus OBJECT-TYPE
    SYNTAX CiscoGslbPeerStatus
--    Rsyntax INTEGER {
--        inactive(1),
--        offline(2),
--        online(3)
--        }
    ACCESS read-only
    STATUS mandatory
    DESCRIPTION
        "This object specifies the status of the GSLB device as
        known on the GSLB network of peers."
    ::= { cgsGeneral 4 }

cgsNodeLocation OBJECT-TYPE
    SYNTAX SnmpAdminString(SIZE(1..80))
--    Rsyntax OCTET STRING(SIZE(1..80))
    ACCESS read-write
    STATUS mandatory
    DESCRIPTION
        "This object specifies the administratively assigned
        location for the GSLB device."
    ::= { cgsGeneral 5 }

cgsNodeRegion OBJECT-TYPE
    SYNTAX SnmpAdminString(SIZE(1..80))
--    Rsyntax OCTET STRING(SIZE(1..80))
    ACCESS read-only
    STATUS mandatory
    DESCRIPTION
        "This object specifies the administratively assigned
        region for the GSLB device.  This value corresponds to
        an instance of cgsLocationRegion from cgsLocationTable."
    ::= { cgsGeneral 6 }

cgsPeerTable OBJECT-TYPE
    SYNTAX SEQUENCE OF CgsPeerEntry
    ACCESS not-accessible
    STATUS mandatory
    DESCRIPTION
        "This table lists the information on peers in the GSLB
        network of devices."
    ::= { cgsPeer 1 }

cgsPeerEntry OBJECT-TYPE
    SYNTAX CgsPeerEntry
    ACCESS not-accessible
    STATUS mandatory
    DESCRIPTION
        "An entry in cgsPeerEntryTable.  Each entry contains
        information on the GSLB peers.  Entries are
        added/deleted when a GSLB peer device is added/deleted
        in GSLB network of peers."
    INDEX { cgsPeerAddressType, cgsPeerAddress }
    ::= { cgsPeerTable 1 }

CgsPeerEntry ::= SEQUENCE {
    cgsPeerAddressType InetAddressType,
    cgsPeerAddress InetAddress,
    cgsPeerLocation SnmpAdminString,
    cgsPeerDnsName InetAddressDNS,
    cgsPeerService CiscoGslbNodeServices,
    cgsPeerStatus CiscoGslbPeerStatus,
    cgsPeerVersion SnmpAdminString
    }

cgsPeerAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS not-accessible
    STATUS mandatory
    DESCRIPTION
        "This object specifies the IP address type of the
        GSLB peer."
    ::= { cgsPeerEntry 1 }

cgsPeerAddress OBJECT-TYPE
    SYNTAX InetAddress(SIZE(1..16))
--    Rsyntax OCTET STRING(SIZE(1..16))
    ACCESS not-accessible
    STATUS mandatory
    DESCRIPTION
        "This object specifies the GSLB peer IP address.
        The type of IP address is identified by
        cgsPeerAddressType."
    ::= { cgsPeerEntry 2 }

cgsPeerLocation OBJECT-TYPE
    SYNTAX SnmpAdminString(SIZE(1..80))
--    Rsyntax OCTET STRING(SIZE(1..80))
    ACCESS read-write
    STATUS mandatory
    DESCRIPTION
        "This object specifies the administratively assigned
        location of the GSLB peer.  Its value must be same as
        the value configured in cgsLocationTable."
    ::= { cgsPeerEntry 3 }

cgsPeerDnsName OBJECT-TYPE
    SYNTAX InetAddressDNS
--    Rsyntax OCTET STRING(SIZE(1..255))
    ACCESS read-only
    STATUS mandatory
    DESCRIPTION
        "This object specifies the host name assigned uniquely
        to a GSLB peer.  Its value is same as the value of
        sysName of the GSLB peer."
    ::= { cgsPeerEntry 4 }

cgsPeerService OBJECT-TYPE
    SYNTAX CiscoGslbNodeServices
--    Rsyntax INTEGER {
--        primary(1),
--        standby(2),
--        secondary(3)
--        }
    ACCESS read-only
    STATUS mandatory
    DESCRIPTION
        "This object specifies the type of role the GSLB peer
        has in a GSLB network of peers.  Its value is same as
        value of cgsNodeService of the GSLB peer."
    ::= { cgsPeerEntry 5 }

cgsPeerStatus OBJECT-TYPE
    SYNTAX CiscoGslbPeerStatus
--    Rsyntax INTEGER {
--        inactive(1),
--        offline(2),
--        online(3)
--        }
    ACCESS read-only
    STATUS mandatory
    DESCRIPTION
        "This object specifies the status of GSLB peer as
        known to the reporting GSLB device."
    ::= { cgsPeerEntry 6 }

cgsPeerVersion OBJECT-TYPE
    SYNTAX SnmpAdminString
--    Rsyntax OCTET STRING(SIZE(0..255))
    ACCESS read-only
    STATUS mandatory
    DESCRIPTION
        "This object specifies the software version installed
        on the GSLB peer."
    ::= { cgsPeerEntry 7 }

cgsProxZoneTable OBJECT-TYPE
    SYNTAX SEQUENCE OF CgsProxZoneEntry
    ACCESS not-accessible
    STATUS mandatory
    DESCRIPTION
        "This table is used for configuring proximity zones.
        It consists a  list of proximity probing statistics
        for each configured proximity zone."
    ::= { cgsProxZoneStats 1 }

cgsProxZoneEntry OBJECT-TYPE
    SYNTAX CgsProxZoneEntry
    ACCESS not-accessible
    STATUS mandatory
    DESCRIPTION
        "An entry in cgsProxZoneTable.  Each entry contains
        information on proximity zones and probing statistics.
        Entries can be added/deleted/modified by administrator
        action."
    INDEX { cgsProxZoneName }
    ::= { cgsProxZoneTable 1 }

CgsProxZoneEntry ::= SEQUENCE {
    cgsProxZoneName SnmpAdminString,
    cgsProxPrimaryAddressType InetAddressType,
    cgsProxPrimaryAddress InetAddress,
    cgsProxSecondaryAddressType InetAddressType,
    cgsProxSecondaryAddress InetAddress,
    cgsProxEchoSentReqs Counter,
    cgsProxEchoRcvdResps Counter,
    cgsProxSentMeasureReqs Counter,
    cgsProxRcvdMeasureResps Counter,
    cgsProxTotalSentReqs Counter,
    cgsProxTotalRcvdResps Counter,
    cgsProxSendRate Gauge,
    cgsProxRcvdRate Gauge,
    cgsProxPeakSendRate Gauge,
    cgsProxPeakRcvdRate Gauge,
    cgsProxStorageType StorageType,
    cgsProxRowStatus RowStatus
    }

cgsProxZoneName OBJECT-TYPE
    SYNTAX SnmpAdminString(SIZE(1..80))
--    Rsyntax OCTET STRING(SIZE(1..80))
    ACCESS not-accessible
    STATUS mandatory
    DESCRIPTION
        "This object specifies a name given uniquely for
        a proximity zone."
    ::= { cgsProxZoneEntry 1 }

cgsProxPrimaryAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object specifies the IP address type of the
        primary device being probed in the proximity zone."
    DEFVAL { ipv4 }
    ::= { cgsProxZoneEntry 2 }

cgsProxPrimaryAddress OBJECT-TYPE
    SYNTAX InetAddress
--    Rsyntax OCTET STRING(SIZE(0..255))
    ACCESS read-write
    STATUS mandatory
    DESCRIPTION
        "This object specifies the IP address of the primary
        device being probed  in the proximity zone.  The type of
        IP address is identified by cgsProxPrimaryAddressType.
        This object is mandatory for row creation."
    ::= { cgsProxZoneEntry 3 }

cgsProxSecondaryAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object specifies the IP address type of the
        secondary device that may be probed in the
        proximity zone."
    DEFVAL { ipv4 }
    ::= { cgsProxZoneEntry 4 }

cgsProxSecondaryAddress OBJECT-TYPE
    SYNTAX InetAddress
--    Rsyntax OCTET STRING(SIZE(0..255))
    ACCESS read-write
    STATUS mandatory
    DESCRIPTION
        "This object specifies the IP address of the secondary
        device that may be probed for proximity in the proximity
        zone.  The type of IP address is identified by
        cgsProxSecondaryAddressType."
    DEFVAL { "" }
    ::= { cgsProxZoneEntry 5 }

cgsProxEchoSentReqs OBJECT-TYPE
    SYNTAX Counter
--  Units
--    requests
    ACCESS read-only
    STATUS mandatory
    DESCRIPTION
        "This object indicates the number of DRP echo requests
        sent by GSLB to all probed devices."
    ::= { cgsProxZoneEntry 6 }

cgsProxEchoRcvdResps OBJECT-TYPE
    SYNTAX Counter
--  Units
--    responses
    ACCESS read-only
    STATUS mandatory
    DESCRIPTION
        "This object indicates the number of DRP echo responses
        received by GLSB from all probed devices."
    ::= { cgsProxZoneEntry 7 }

cgsProxSentMeasureReqs OBJECT-TYPE
    SYNTAX Counter
--  Units
--    requests
    ACCESS read-only
    STATUS mandatory
    DESCRIPTION
        "This object indicates the number of DRP measured
        requests sent by GSLB to all probed devices."
    ::= { cgsProxZoneEntry 8 }

cgsProxRcvdMeasureResps OBJECT-TYPE
    SYNTAX Counter
--  Units
--    responses
    ACCESS read-only
    STATUS mandatory
    DESCRIPTION
        "This object indicates the number of DRP measured
        responses received by GSLB from all probed devices."
    ::= { cgsProxZoneEntry 9 }

cgsProxTotalSentReqs OBJECT-TYPE
    SYNTAX Counter
--  Units
--    requests
    ACCESS read-only
    STATUS mandatory
    DESCRIPTION
        "This object indicates the total of DRP requests sent
        by GSLB to probed device in the proximity zone."
    ::= { cgsProxZoneEntry 10 }

cgsProxTotalRcvdResps OBJECT-TYPE
    SYNTAX Counter
--  Units
--    responses
    ACCESS read-only
    STATUS mandatory
    DESCRIPTION
        "This object indicates the total of DRP responses
        received by GSLB from all probed devices in the
        proximity zone."
    ::= { cgsProxZoneEntry 11 }

cgsProxSendRate OBJECT-TYPE
    SYNTAX Gauge
--  Units
--    rate per second
    ACCESS read-only
    STATUS mandatory
    DESCRIPTION
        "This object indicates the current transmitted DRP
        request rate per second."
    ::= { cgsProxZoneEntry 12 }

cgsProxRcvdRate OBJECT-TYPE
    SYNTAX Gauge
--  Units
--    rate per second
    ACCESS read-only
    STATUS mandatory
    DESCRIPTION
        "This object indicates the current received DRP response
        rate per second."
    ::= { cgsProxZoneEntry 13 }

cgsProxPeakSendRate OBJECT-TYPE
    SYNTAX Gauge
--  Units
--    rate per second
    ACCESS read-only
    STATUS mandatory
    DESCRIPTION
        "This object indicates the peak transmitted DRP request
        rate per second."
    ::= { cgsProxZoneEntry 14 }

cgsProxPeakRcvdRate OBJECT-TYPE
    SYNTAX Gauge
--  Units
--    rate per second
    ACCESS read-only
    STATUS mandatory
    DESCRIPTION
        "This object indicates the peak received DRP response
        rate per second."
    ::= { cgsProxZoneEntry 15 }

cgsProxStorageType OBJECT-TYPE
    SYNTAX StorageType
--    Rsyntax INTEGER {
--        other(1),
--        volatile(2),
--        nonVolatile(3),
--        permanent(4),
--        readOnly(5)
--        }
    ACCESS read-write
    STATUS mandatory
    DESCRIPTION
        "This object specifies the storage type for this
        conceptual row."
    DEFVAL { nonVolatile }
    ::= { cgsProxZoneEntry 16 }

cgsProxRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create/delete an entry in the
        cgsProxZoneTable."
    ::= { cgsProxZoneEntry 17 }

cgsRegionTable OBJECT-TYPE
    SYNTAX SEQUENCE OF CgsRegionEntry
    ACCESS not-accessible
    STATUS deprecated
    DESCRIPTION
        "This table is used to configure regions on the device.
        It consists a list of regions configured on the GSLB
        device."
    ::= { cgsResources 1 }

cgsRegionEntry OBJECT-TYPE
    SYNTAX CgsRegionEntry
    ACCESS not-accessible
    STATUS deprecated
    DESCRIPTION
        "An entry in cgsRegionTable.  Each entry contains the
        information about a region.  Entries can be
        added/deleted/modified by administrator action."
    INDEX { cgsRegionName }
    ::= { cgsRegionTable 1 }

CgsRegionEntry ::= SEQUENCE {
    cgsRegionName SnmpAdminString,
    cgsRegionComments SnmpAdminString,
    cgsRegionStorageType StorageType,
    cgsRegionRowStatus RowStatus
    }

cgsRegionName OBJECT-TYPE
    SYNTAX SnmpAdminString(SIZE(1..80))
--    Rsyntax OCTET STRING(SIZE(1..80))
    ACCESS not-accessible
    STATUS deprecated
    DESCRIPTION
        "This object specifies the name given uniquely for a
        region."
    ::= { cgsRegionEntry 1 }

cgsRegionComments OBJECT-TYPE
    SYNTAX SnmpAdminString
--    Rsyntax OCTET STRING(SIZE(0..255))
    ACCESS read-write
    STATUS deprecated
    DESCRIPTION
        "This object specifies the comments associated with the
        region."
    DEFVAL { "" }
    ::= { cgsRegionEntry 2 }

cgsRegionStorageType OBJECT-TYPE
    SYNTAX StorageType
--    Rsyntax INTEGER {
--        other(1),
--        volatile(2),
--        nonVolatile(3),
--        permanent(4),
--        readOnly(5)
--        }
    ACCESS read-write
    STATUS deprecated
    DESCRIPTION
        "This object specifies the storage type for this
        conceptual row."
    DEFVAL { nonVolatile }
    ::= { cgsRegionEntry 3 }

cgsRegionRowStatus OBJECT-TYPE
    SYNTAX RowStatus
--    Rsyntax INTEGER {
--        active(1),
--        notInService(2),
--        notReady(3),
--        createAndGo(4),
--        createAndWait(5),
--        destroy(6)
--        }
    ACCESS read-write
    STATUS deprecated
    DESCRIPTION
        "This object is used to create/delete an entry in the
        cgsRegionTable"
    ::= { cgsRegionEntry 4 }

cgsLocationTable OBJECT-TYPE
    SYNTAX SEQUENCE OF CgsLocationEntry
    ACCESS not-accessible
    STATUS mandatory
    DESCRIPTION
        "This table is used to configure locations on the device.
        It consists a list of locations configured on the GSLB
        device."
    ::= { cgsResources 2 }

cgsLocationEntry OBJECT-TYPE
    SYNTAX CgsLocationEntry
    ACCESS not-accessible
    STATUS mandatory
    DESCRIPTION
        "An entry in cgsLocationTable.  Each entry contains the
        information about a location.  Entries can be
        added/deleted/modified by administrator action."
    INDEX { cgsLocationName }
    ::= { cgsLocationTable 1 }

CgsLocationEntry ::= SEQUENCE {
    cgsLocationName SnmpAdminString,
    cgsLocationRegion SnmpAdminString,
    cgsLocationZone SnmpAdminString,
    cgsLocationComments SnmpAdminString,
    cgsLocationStorageType StorageType,
    cgsLocationRowStatus RowStatus
    }

cgsLocationName OBJECT-TYPE
    SYNTAX SnmpAdminString(SIZE(1..80))
--    Rsyntax OCTET STRING(SIZE(1..80))
    ACCESS not-accessible
    STATUS mandatory
    DESCRIPTION
        "This object specifies the name given uniquely for a
        location."
    ::= { cgsLocationEntry 1 }

cgsLocationRegion OBJECT-TYPE
    SYNTAX SnmpAdminString
--    Rsyntax OCTET STRING(SIZE(0..255))
    ACCESS read-write
    STATUS mandatory
    DESCRIPTION
        "This object specifies a region to which this location
        instance is associated.
        This object is mandatory for a row creation."
    ::= { cgsLocationEntry 2 }

cgsLocationZone OBJECT-TYPE
    SYNTAX SnmpAdminString
--    Rsyntax OCTET STRING(SIZE(0..255))
    ACCESS read-write
    STATUS mandatory
    DESCRIPTION
        "This object specifies a zone to which this location
        instance is associated."
    DEFVAL { "" }
    ::= { cgsLocationEntry 3 }

cgsLocationComments OBJECT-TYPE
    SYNTAX SnmpAdminString
--    Rsyntax OCTET STRING(SIZE(0..255))
    ACCESS read-write
    STATUS mandatory
    DESCRIPTION
        "This object specifies the comments associated with the
        location."
    DEFVAL { "" }
    ::= { cgsLocationEntry 4 }

cgsLocationStorageType OBJECT-TYPE
    SYNTAX StorageType
--    Rsyntax INTEGER {
--        other(1),
--        volatile(2),
--        nonVolatile(3),
--        permanent(4),
--        readOnly(5)
--        }
    ACCESS read-write
    STATUS mandatory
    DESCRIPTION
        "This object specifies the storage type for this
        conceptual row"
    DEFVAL { nonVolatile }
    ::= { cgsLocationEntry 5 }

cgsLocationRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create/delete an entry in the
        cgsLocationTable"
    ::= { cgsLocationEntry 6 }

cgsRegionIdTable OBJECT-TYPE
    SYNTAX SEQUENCE OF CgsRegionIdEntry
    ACCESS not-accessible
    STATUS mandatory
    DESCRIPTION
        "This table is used to configure regions on the device.
        It consists a list of regions configured on the GSLB
        device."
    ::= { cgsResources 3 }

cgsRegionIdEntry OBJECT-TYPE
    SYNTAX CgsRegionIdEntry
    ACCESS not-accessible
    STATUS mandatory
    DESCRIPTION
        "An entry in cgsRegionIdTable.Each entry contains the
        information about a region.  Entries can be
        added/deleted/modified by administrator action."
    INDEX { cgsRegionId }
    ::= { cgsRegionIdTable 1 }

CgsRegionIdEntry ::= SEQUENCE {
    cgsRegionId Gauge,
    cgsRegionIdName SnmpAdminString,
    cgsRegionIdComments SnmpAdminString,
    cgsReqCountPerRegionId Counter,
    cgsReqCountRatePerRegionId1Min Gauge,
    cgsReqCountRatePerRegionId5Min Gauge,
    cgsReqCountRatePerRegionId30Min Gauge,
    cgsReqCountRatePerRegionId4Hr Gauge,
    cgsAnswerCountPerRegionId Counter,
    cgsAnswerCountRatePerRegionId1Min Gauge,
    cgsAnswerCountRatePerRegionId5Min Gauge,
    cgsAnswerCountRatePerRegionId30Min Gauge,
    cgsAnswerCountRatePerRegionId4Hr Gauge,
    cgsUnAnswerCountPerRegionId Counter,
    cgsUnAnswerCountRatePerRegionId1Min Gauge,
    cgsUnAnswerCountRatePerRegionId5Min Gauge,
    cgsUnAnswerCountRatePerRegionId30Min Gauge,
    cgsUnAnswerCountRatePerRegionId4Hr Gauge,
    cgsRegionIdStorageType StorageType,
    cgsRegionIdRowStatus RowStatus
    }

cgsRegionId OBJECT-TYPE
    SYNTAX Gauge(1..4294967295)
    ACCESS not-accessible
    STATUS mandatory
    DESCRIPTION
        "This object uniquely identifies a region."
    ::= { cgsRegionIdEntry 1 }

cgsRegionIdName OBJECT-TYPE
    SYNTAX SnmpAdminString(SIZE(1..80))
--    Rsyntax OCTET STRING(SIZE(1..80))
    ACCESS read-write
    STATUS mandatory
    DESCRIPTION
        "This object specifies the name given uniquely for a
        region."
    ::= { cgsRegionIdEntry 2 }

cgsRegionIdComments OBJECT-TYPE
    SYNTAX SnmpAdminString
--    Rsyntax OCTET STRING(SIZE(0..255))
    ACCESS read-write
    STATUS mandatory
    DESCRIPTION
        "This object specifies the comments associated with the
        region."
    DEFVAL { "" }
    ::= { cgsRegionIdEntry 3 }

cgsReqCountPerRegionId OBJECT-TYPE
    SYNTAX Counter
--  Units
--    number of hits
    ACCESS read-only
    STATUS mandatory
    DESCRIPTION
        "This object indicates the total number of DNS requests
        received from this region since the GSLB device was last
        started."
    ::= { cgsRegionIdEntry 4 }

cgsReqCountRatePerRegionId1Min OBJECT-TYPE
    SYNTAX Gauge
--  Units
--    hits per second
    ACCESS read-only
    STATUS mandatory
    DESCRIPTION
        "This object indicates the average per second DNS requests
        received from this region, calculated during the last one 
        minute interval."
    ::= { cgsRegionIdEntry 5 }

cgsReqCountRatePerRegionId5Min OBJECT-TYPE
    SYNTAX Gauge
--  Units
--    hits per second
    ACCESS read-only
    STATUS mandatory
    DESCRIPTION
        "This object indicates the average per second DNS requests
        received from this region , calculated during the last 5 
        minute interval."
    ::= { cgsRegionIdEntry 6 }

cgsReqCountRatePerRegionId30Min OBJECT-TYPE
    SYNTAX Gauge
--  Units
--    hits per second
    ACCESS read-only
    STATUS mandatory
    DESCRIPTION
        "This object indicates the average per second DNS requests
        received from this region , calculated during the last 30
        minute interval."
    ::= { cgsRegionIdEntry 7 }

cgsReqCountRatePerRegionId4Hr OBJECT-TYPE
    SYNTAX Gauge
--  Units
--    hits per second
    ACCESS read-only
    STATUS mandatory
    DESCRIPTION
        "This object indicates the average per second DNS requests
        received from this region , calculated during the last 4
        hour interval."
    ::= { cgsRegionIdEntry 8 }

cgsAnswerCountPerRegionId OBJECT-TYPE
    SYNTAX Counter
--  Units
--    number of hits
    ACCESS read-only
    STATUS mandatory
    DESCRIPTION
        "This object indicates the total number of times answers in
        this region are used in replying for DNS queries, since the 
        GSLB device was last started."
    ::= { cgsRegionIdEntry 9 }

cgsAnswerCountRatePerRegionId1Min OBJECT-TYPE
    SYNTAX Gauge
--  Units
--    hits per second
    ACCESS read-only
    STATUS mandatory
    DESCRIPTION
        "This object indicates the average per second hit count for
        answers in this region, calculated during the last 1 minute
        interval."
    ::= { cgsRegionIdEntry 10 }

cgsAnswerCountRatePerRegionId5Min OBJECT-TYPE
    SYNTAX Gauge
--  Units
--    hits per second
    ACCESS read-only
    STATUS mandatory
    DESCRIPTION
        "This object indicates the average per second hit count for
        answers in this region, calculated during the last 5 minute
        interval."
    ::= { cgsRegionIdEntry 11 }

cgsAnswerCountRatePerRegionId30Min OBJECT-TYPE
    SYNTAX Gauge
--  Units
--    hits per second
    ACCESS read-only
    STATUS mandatory
    DESCRIPTION
        "This object indicates the average per second hit count for
        answers in this region, calculated during the last 30 minute
        interval."
    ::= { cgsRegionIdEntry 12 }

cgsAnswerCountRatePerRegionId4Hr OBJECT-TYPE
    SYNTAX Gauge
--  Units
--    hits per second
    ACCESS read-only
    STATUS mandatory
    DESCRIPTION
        "This object indicates the average per second hit count for
        answers in this region, calculated during the last 4 hour
        interval."
    ::= { cgsRegionIdEntry 13 }

cgsUnAnswerCountPerRegionId OBJECT-TYPE
    SYNTAX Counter
--  Units
--    number of hits
    ACCESS read-only
    STATUS mandatory
    DESCRIPTION
        "This object indicates the total number of times DNS requests
        from this region have not been answered, since the GSLB device
        was last started."
    ::= { cgsRegionIdEntry 14 }

cgsUnAnswerCountRatePerRegionId1Min OBJECT-TYPE
    SYNTAX Gauge
--  Units
--    hits per second
    ACCESS read-only
    STATUS mandatory
    DESCRIPTION
        "This object indicates the average per second unanswered
        DNS requests from this region, calculated during the last
        one minute."
    ::= { cgsRegionIdEntry 15 }

cgsUnAnswerCountRatePerRegionId5Min OBJECT-TYPE
    SYNTAX Gauge
--  Units
--    hits per second
    ACCESS read-only
    STATUS mandatory
    DESCRIPTION
        "This object indicates the average per second unanswered
        DNS requests from this region, calculated during the
        last 5 minute interval."
    ::= { cgsRegionIdEntry 16 }

cgsUnAnswerCountRatePerRegionId30Min OBJECT-TYPE
    SYNTAX Gauge
--  Units
--    hits per second
    ACCESS read-only
    STATUS mandatory
    DESCRIPTION
        "This object indicates the average per second unanswered
        DNS requests from this region, calculated during the 
        last 30 minute interval."
    ::= { cgsRegionIdEntry 17 }

cgsUnAnswerCountRatePerRegionId4Hr OBJECT-TYPE
    SYNTAX Gauge
--  Units
--    hits per second
    ACCESS read-only
    STATUS mandatory
    DESCRIPTION
        "This object indicates the average per second unanswered
        DNS requests from this region, calculated during the 
        last 4 hour interval."
    ::= { cgsRegionIdEntry 18 }

cgsRegionIdStorageType OBJECT-TYPE
    SYNTAX StorageType
--    Rsyntax INTEGER {
--        other(1),
--        volatile(2),
--        nonVolatile(3),
--        permanent(4),
--        readOnly(5)
--        }
    ACCESS read-write
    STATUS mandatory
    DESCRIPTION
        "This object specifies the storage type for this
        conceptual row."
    DEFVAL { nonVolatile }
    ::= { cgsRegionIdEntry 19 }

cgsRegionIdRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create/delete an entry in the
        cgsRegionIdTable. Users can modify all writable objects
        in this row when this object value is 'active'. The 
        cgsRegionIdName object need to be set to valid value
        by the users before user can activate the row."
    ::= { cgsRegionIdEntry 20 }

cgsPeerEventNotifEnable OBJECT-TYPE
    SYNTAX TruthValue
--    Rsyntax INTEGER {
--        true(1),
--        false(2)
--        }
    ACCESS read-write
    STATUS mandatory
    DESCRIPTION
        "This object defines the administrative state of sending
        notifications to signal a GSLB peer status change."
    DEFVAL { false }
    ::= { cgsNotifControl 1 }

cgsPeerPrevStatus OBJECT-TYPE
    SYNTAX CiscoGslbPeerStatus
--    Rsyntax INTEGER {
--        inactive(1),
--        offline(2),
--        online(3)
--        }
    ACCESS not-accessible
    STATUS mandatory
    DESCRIPTION
        "This object is used for sending the value of cgsPeerStatus
        before transitioning to new state."
    ::= { cgsNotifObjects 1 }

ciscoGslbSystemPeerEventStatus TRAP-TYPE
-- Reverse mappable trap
    ENTERPRISE ciscoGslbSystemMIB
    VARIABLES {
        sysName, cgsPeerDnsName, cgsPeerService, cgsPeerPrevStatus, 
        cgsPeerStatus }
--  Status
--    mandatory
    DESCRIPTION
        "This notification is sent when the value of
        cgsPeerStatus changes from one state to another.
        This notification is reported only by a GSLB device
        with cgsNodeService value of 'primary'."
    ::= 1

ciscoGslbSystemGeneralGroup OBJECT IDENTIFIER ::= { ciscoGslbSystemMIBGroups 1 }
-- OBJECT-GROUP
--  Status
--    mandatory
--  Descr
--    A collection of objects providing general GSLB status.
--  objects
--    cgsNodeService, cgsNodeCommIfName, cgsNodeCommIfIndex, 
--    cgsNodeStatus, cgsNodeLocation, cgsNodeRegion

ciscoGslbSystemPeerGroup OBJECT IDENTIFIER ::= { ciscoGslbSystemMIBGroups 2 }
-- OBJECT-GROUP
--  Status
--    mandatory
--  Descr
--    A collection of objects providing GSLB peer status.
--  objects
--    cgsPeerLocation, cgsPeerDnsName, cgsPeerService, 
--    cgsPeerStatus, cgsPeerVersion

ciscoGslbSystemProxZoneGroup OBJECT IDENTIFIER ::= { ciscoGslbSystemMIBGroups 3 }
-- OBJECT-GROUP
--  Status
--    mandatory
--  Descr
--    A collection of objects providing GSLB proximity
--    zone statistics.
--  objects
--    cgsProxPrimaryAddressType, cgsProxPrimaryAddress, 
--    cgsProxSecondaryAddressType, cgsProxSecondaryAddress, 
--    cgsProxEchoSentReqs, cgsProxEchoRcvdResps, 
--    cgsProxSentMeasureReqs, cgsProxRcvdMeasureResps, 
--    cgsProxTotalSentReqs, cgsProxTotalRcvdResps, cgsProxSendRate, 
--    cgsProxRcvdRate, cgsProxPeakSendRate, cgsProxPeakRcvdRate, 
--    cgsProxStorageType, cgsProxRowStatus

ciscoGslbSystemResourceGroup OBJECT IDENTIFIER ::= { ciscoGslbSystemMIBGroups 4 }
-- OBJECT-GROUP
--  Status
--    deprecated
--  Descr
--    A collection of objects providing GSLB resource
--    configurations.
--  objects
--    cgsRegionComments, cgsRegionStorageType, cgsRegionRowStatus, 
--    cgsLocationRegion, cgsLocationZone, cgsLocationComments, 
--    cgsLocationStorageType, cgsLocationRowStatus

ciscoGslbSystemNotifControlGroup OBJECT IDENTIFIER ::= { ciscoGslbSystemMIBGroups 5 }
-- OBJECT-GROUP
--  Status
--    mandatory
--  Descr
--    This group of objects controls the sending of
--    notifications defined in this MIB module.
--  objects
--    cgsPeerEventNotifEnable

ciscoGslbSystemNotifObjectsGroup OBJECT IDENTIFIER ::= { ciscoGslbSystemMIBGroups 6 }
-- OBJECT-GROUP
--  Status
--    mandatory
--  Descr
--    A collection of objects that convey information for
--    notifications defined in this MIB module.
--  objects
--    cgsPeerPrevStatus

ciscoGslbSystemResourceLocationGroup OBJECT IDENTIFIER ::= { ciscoGslbSystemMIBGroups 8 }
-- OBJECT-GROUP
--  Status
--    mandatory
--  Descr
--    A collection of objects providing GSLB location resource
--    configurations.
--  objects
--    cgsLocationRegion, cgsLocationZone, cgsLocationComments, 
--    cgsLocationStorageType, cgsLocationRowStatus

ciscoGslbSystemResourceRegionGroup OBJECT IDENTIFIER ::= { ciscoGslbSystemMIBGroups 9 }
-- OBJECT-GROUP
--  Status
--    mandatory
--  Descr
--    A collection of objects providing GSLB region resource
--    configurations.
--  objects
--    cgsRegionIdName, cgsRegionIdComments, cgsReqCountPerRegionId, 
--    cgsReqCountRatePerRegionId1Min, 
--    cgsReqCountRatePerRegionId5Min, 
--    cgsReqCountRatePerRegionId30Min, 
--    cgsReqCountRatePerRegionId4Hr, cgsAnswerCountPerRegionId, 
--    cgsAnswerCountRatePerRegionId1Min, 
--    cgsAnswerCountRatePerRegionId5Min, 
--    cgsAnswerCountRatePerRegionId30Min, 
--    cgsAnswerCountRatePerRegionId4Hr, cgsUnAnswerCountPerRegionId, 
--    cgsUnAnswerCountRatePerRegionId1Min, 
--    cgsUnAnswerCountRatePerRegionId5Min, 
--    cgsUnAnswerCountRatePerRegionId30Min, 
--    cgsUnAnswerCountRatePerRegionId4Hr, cgsRegionIdStorageType, 
--    cgsRegionIdRowStatus

ciscoGslbSystemNotifGroup OBJECT IDENTIFIER ::= { ciscoGslbSystemMIBGroups 7 }
-- NOTIFICATION-GROUP
--  Status
--    mandatory
--  Descr
--    A collection of objects providing GSLB System events.
--  notifications
--    ciscoGslbSystemPeerEventStatus

ciscoGslbSystemMIBCompliance OBJECT IDENTIFIER ::= { ciscoGslbSystemMIBCompliances 1 }
-- MODULE-COMPLIANCE
--  Status
--    deprecated
--  Descr
--    Compliance statement for entities which implement
--    the Cisco GSLB System MIB
--  Module
--    >>current<<
--   MandGroup
--    ciscoGslbSystemGeneralGroup
--   MandGroup
--    ciscoGslbSystemPeerGroup
--   MandGroup
--    ciscoGslbSystemProxZoneGroup
--   MandGroup
--    ciscoGslbSystemResourceGroup
--   MandGroup
--    ciscoGslbSystemNotifControlGroup
--   MandGroup
--    ciscoGslbSystemNotifObjectsGroup
--   MandGroup
--    ciscoGslbSystemNotifGroup

ciscoGslbSystemMIBComplianceRev1 OBJECT IDENTIFIER ::= { ciscoGslbSystemMIBCompliances 2 }
-- MODULE-COMPLIANCE
--  Status
--    mandatory
--  Descr
--    Compliance statement for entities which implement
--    the Cisco GSLB System MIB
--  Module
--    >>current<<
--   MandGroup
--    ciscoGslbSystemGeneralGroup
--   MandGroup
--    ciscoGslbSystemPeerGroup
--   MandGroup
--    ciscoGslbSystemProxZoneGroup
--   MandGroup
--    ciscoGslbSystemNotifControlGroup
--   MandGroup
--    ciscoGslbSystemNotifObjectsGroup
--   MandGroup
--    ciscoGslbSystemNotifGroup
--   MandGroup
--    ciscoGslbSystemResourceLocationGroup
--   MandGroup
--    ciscoGslbSystemResourceRegionGroup


END
