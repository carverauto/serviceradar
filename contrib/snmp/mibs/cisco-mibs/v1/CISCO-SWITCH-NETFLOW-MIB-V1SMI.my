-- MIB file created 29-Jun-2011 14:51:16, by
--   SMICng version 2.2.11-beta(PRO)(Solaris), January 20, 2001. Enterprise key cisco.com

CISCO-SWITCH-NETFLOW-MIB DEFINITIONS ::= BEGIN

-- From file: "CISCO-SWITCH-NETFLOW-MIB.my"
-- Compile options "4 7 F H N W 03 06 0B 0G 0N 0T"

IMPORTS
    TruthValue
            FROM SNMPv2-TC-v1
    entPhysicalIndex, entPhysicalDescr
            FROM ENTITY-MIB
    Percent
            FROM CISCO-QOS-PIB-MIB
    ciscoMgmt
            FROM CISCO-SMI
    Gauge
            FROM RFC1155-SMI
    OBJECT-TYPE
            FROM RFC-1212
    TRAP-TYPE
            FROM RFC-1215;

ciscoSwitchNetflowMIB OBJECT IDENTIFIER ::= { ciscoMgmt 737 }
-- MODULE-IDENTITY
--  LastUpdated
--    201005260000Z
--  OrgName
--    Cisco Systems, Inc.
--  ContactInfo
--    Cisco Systems
--    Customer Service
--    
--    Postal: 170 W Tasman Drive
--    San Jose, CA  95134
--    USA
--    
--    Tel: +1 800 553-NETS
--    
--    E-mail: cs-lan-switch-snmp@cisco.com
--  Descr
--    This MIB module defines management objects for the
--    Netflow features on Cisco Layer 2 and Layer 3 devices.
--  RevDate
--    201005260000Z
--  RevDescr
--    Initial version of this MIB module.

ciscoSwitchNetflowMIBNotifs OBJECT IDENTIFIER ::= { ciscoSwitchNetflowMIB 0 }
ciscoSwitchNetflowMIBObjects OBJECT IDENTIFIER ::= { ciscoSwitchNetflowMIB 1 }
ciscoSwitchNetflowMIBConform OBJECT IDENTIFIER ::= { ciscoSwitchNetflowMIB 2 }
csnAccounting   OBJECT IDENTIFIER ::= { ciscoSwitchNetflowMIBObjects 1 }
csnAccGlobal    OBJECT IDENTIFIER ::= { csnAccounting 1 }
csnAccNotifControl OBJECT IDENTIFIER ::= { csnAccounting 2 }
cshAccUsageThresh OBJECT IDENTIFIER ::= { csnAccounting 3 }
csnAccUtilization OBJECT IDENTIFIER ::= { csnAccounting 4 }
csnAccNetflowTableSize OBJECT IDENTIFIER ::= { csnAccounting 5 }
csnAccSampler   OBJECT IDENTIFIER ::= { csnAccounting 6 }
csnMIBCompliances OBJECT IDENTIFIER ::= { ciscoSwitchNetflowMIBConform 1 }
csnMIBGroups    OBJECT IDENTIFIER ::= { ciscoSwitchNetflowMIBConform 2 }

CsnNetflowDirectionTypes ::= INTEGER {
        none(1),
        ingress(2),
        egress(3),
        ingressAndEgress(4)
        }
-- TEXTUAL-CONVENTION
--  Status
--    mandatory
--  Descr
--    Defines the various Netflow direction types.
--    'none'             - no Netflow direction is supported.
--    
--    'ingress'          - Netflow direction is ingress.
--    
--    'egress'           - Netflow direction is egress.
--    
--    'ingressAndEgress' - Netflow direction is both
--                         ingress and egress.

csnNetflowDirectionType OBJECT-TYPE
    SYNTAX CsnNetflowDirectionTypes
--    Rsyntax INTEGER {
--        none(1),
--        ingress(2),
--        egress(3),
--        ingressAndEgress(4)
--        }
    ACCESS read-write
    STATUS mandatory
    DESCRIPTION
        "This object specifies the direction type of Netflow
        enabled on this system."
    ::= { csnAccGlobal 1 }

csnUsageThreshExceedNotifEnable OBJECT-TYPE
    SYNTAX TruthValue
--    Rsyntax INTEGER {
--        true(1),
--        false(2)
--        }
    ACCESS read-write
    STATUS mandatory
    DESCRIPTION
        "This object specifies whether the system produces the
        csnUsageThreshExceededNotif.
        
        A 'false' value will prevent csnUsageThreshExceededNotif
        notifications from being generated by this system."
    ::= { csnAccNotifControl 1 }

csnUsageThreshTable OBJECT-TYPE
    SYNTAX SEQUENCE OF CsnUsageThreshEntry
    ACCESS not-accessible
    STATUS mandatory
    DESCRIPTION
        "A table containing Netflow table usage monitoring
        configuration information."
    ::= { cshAccUsageThresh 1 }

csnUsageThreshEntry OBJECT-TYPE
    SYNTAX CsnUsageThreshEntry
    ACCESS not-accessible
    STATUS mandatory
    DESCRIPTION
        "A conceptual row of csnUsageThreshTable, containing
        the Netflow table usage monitoring configuration 
        information."
    INDEX { csnUsageDirection }
    ::= { csnUsageThreshTable 1 }

CsnUsageThreshEntry ::= SEQUENCE {
    csnUsageDirection CsnNetflowDirectionTypes,
    csnUsageThreshold Percent,
    csnUsageInterval Gauge
    }

csnUsageDirection OBJECT-TYPE
    SYNTAX CsnNetflowDirectionTypes
--    Rsyntax INTEGER {
--        none(1),
--        ingress(2),
--        egress(3),
--        ingressAndEgress(4)
--        }
    ACCESS not-accessible
    STATUS mandatory
    DESCRIPTION
        "This object specifies the direction of Netflow
        on the system."
    ::= { csnUsageThreshEntry 1 }

csnUsageThreshold OBJECT-TYPE
    SYNTAX Percent
--    Rsyntax INTEGER(0..100)
    ACCESS read-write
    STATUS mandatory
    DESCRIPTION
        "This object specifies the Netflow table usage threshold
        in percentage value.
        
        When the value of this object is set to zero, Netflow table
        usage monitoring is disabled.
        
        When the value of this object is set to greater than zero, 
        Netflow table usage monitoring is enabled."
    ::= { csnUsageThreshEntry 2 }

csnUsageInterval OBJECT-TYPE
    SYNTAX Gauge(1..4294967295)
--  Units
--    seconds
    ACCESS read-write
    STATUS mandatory
    DESCRIPTION
        "This object specifies the interval in seconds over
        which the Netflow table usage (the value of csnUtilization) 
        will be compared against the threshold specified by 
        csnUsageThreshold."
    ::= { csnUsageThreshEntry 3 }

csnUtilizationTable OBJECT-TYPE
    SYNTAX SEQUENCE OF CsnUtilizationEntry
    ACCESS not-accessible
    STATUS mandatory
    DESCRIPTION
        "A table containing Netflow table utilization information
        of each switching engine and a Newflow direction type."
    ::= { csnAccUtilization 1 }

csnUtilizationEntry OBJECT-TYPE
    SYNTAX CsnUtilizationEntry
    ACCESS not-accessible
    STATUS mandatory
    DESCRIPTION
        "A conceptual row of csnUtilizationTable, containing
        the Netflow table utilization information for a particular
        switching engine and a particular Netflow type."
    INDEX { entPhysicalIndex, csnUsageDirection }
    ::= { csnUtilizationTable 1 }

CsnUtilizationEntry ::= SEQUENCE {
    csnUtilization Percent
    }

csnUtilization OBJECT-TYPE
    SYNTAX Percent
--    Rsyntax INTEGER(0..100)
    ACCESS read-only
    STATUS mandatory
    DESCRIPTION
        "This object indicates the percentage of Netflow table
        utilization."
    ::= { csnUtilizationEntry 1 }

csnNetflowTableSizeTable OBJECT-TYPE
    SYNTAX SEQUENCE OF CsnNetflowTableSizeEntry
    ACCESS not-accessible
    STATUS mandatory
    DESCRIPTION
        "A table containing Netflow table size information
        of each Netflow type supported in the system."
    ::= { csnAccNetflowTableSize 1 }

csnNetflowTableSizeEntry OBJECT-TYPE
    SYNTAX CsnNetflowTableSizeEntry
    ACCESS not-accessible
    STATUS mandatory
    DESCRIPTION
        "A conceptual row of csnNetflowTableSizeTable, containing
        the Netflow table size information for a particular
        Netflow type."
    INDEX { csnUsageDirection }
    ::= { csnNetflowTableSizeTable 1 }

CsnNetflowTableSizeEntry ::= SEQUENCE {
    csnNetflowTableTotalEntries Gauge
    }

csnNetflowTableTotalEntries OBJECT-TYPE
    SYNTAX Gauge
    ACCESS read-only
    STATUS mandatory
    DESCRIPTION
        "This object indicates the total number of entries
        in the Netflow table for a particular Netflow 
        direction type."
    ::= { csnNetflowTableSizeEntry 1 }

csnSamplerTotal OBJECT-TYPE
    SYNTAX Gauge
    ACCESS read-only
    STATUS mandatory
    DESCRIPTION
        "This object indicates the total number of Netflow
        samplers in the device."
    ::= { csnAccSampler 1 }

csnSamplerAvailable OBJECT-TYPE
    SYNTAX Gauge
    ACCESS read-only
    STATUS mandatory
    DESCRIPTION
        "This object indicates the number of Netflow samplers
        available in the system."
    ::= { csnAccSampler 2 }

csnUsageThreshExceededNotif TRAP-TYPE
-- Reverse mappable trap
    ENTERPRISE ciscoSwitchNetflowMIB
    VARIABLES {
        entPhysicalDescr, csnUtilization, csnUsageThreshold, 
        csnUsageInterval }
--  Status
--    mandatory
    DESCRIPTION
        "A csnUsageThreshExceededNotif is sent if the Netflow
        table usage has exceeded the configured threshold
        specified by csnUsageThreshold."
    ::= 1

csnGlobalGroup OBJECT IDENTIFIER ::= { csnMIBGroups 1 }
-- OBJECT-GROUP
--  Status
--    mandatory
--  Descr
--    A collection of objects providing global Netflow
--    type configuration.
--  objects
--    csnNetflowDirectionType

csnUsageThreshNotifControlGroup OBJECT IDENTIFIER ::= { csnMIBGroups 2 }
-- OBJECT-GROUP
--  Status
--    mandatory
--  Descr
--    A collection of objects providing enabling/disabling
--    of the Netflow table usage threshold notifications.
--  objects
--    csnUsageThreshExceedNotifEnable

csnUsageThreshGroup OBJECT IDENTIFIER ::= { csnMIBGroups 3 }
-- OBJECT-GROUP
--  Status
--    mandatory
--  Descr
--    A collection of objects providing Netflow table usage
--    threshold information and configuration.
--  objects
--    csnUsageThreshold, csnUsageInterval

csnUtilizationGroup OBJECT IDENTIFIER ::= { csnMIBGroups 4 }
-- OBJECT-GROUP
--  Status
--    mandatory
--  Descr
--    A collection of objects providing Netflow utilization
--    information.
--  objects
--    csnUtilization

csnNetflowTableSizeGroup OBJECT IDENTIFIER ::= { csnMIBGroups 6 }
-- OBJECT-GROUP
--  Status
--    mandatory
--  Descr
--    A collection of objects providing Netflow table size
--    information.
--  objects
--    csnNetflowTableTotalEntries

csnSamplerGroup OBJECT IDENTIFIER ::= { csnMIBGroups 7 }
-- OBJECT-GROUP
--  Status
--    mandatory
--  Descr
--    A collection of objects providing Netflow sampler
--    information.
--  objects
--    csnSamplerTotal, csnSamplerAvailable

csnUsageThreshNotifGroup OBJECT IDENTIFIER ::= { csnMIBGroups 5 }
-- NOTIFICATION-GROUP
--  Status
--    mandatory
--  Descr
--    A collection of notifications providing Netflow table
--    usage threshold exceeded notification.
--  notifications
--    csnUsageThreshExceededNotif

csnMIBCompliance OBJECT IDENTIFIER ::= { csnMIBCompliances 1 }
-- MODULE-COMPLIANCE
--  Status
--    mandatory
--  Descr
--    The compliance statement for
--    CISCO-SWITCH-NETFLOW-MIB.
--  Module
--    >>current<<
--   MandGroup
--    csnGlobalGroup
--   OptGroup
--    csnUsageThreshNotifControlGroup
--   OptGroup
--    csnUsageThreshGroup
--   OptGroup
--    csnUtilizationGroup
--   OptGroup
--    csnUsageThreshNotifGroup
--   OptGroup
--    csnNetflowTableSizeGroup
--   OptGroup
--    csnSamplerGroup
--   ObjVar
--    csnNetflowDirectionType
--   ObjVar
--    csnUsageThreshExceedNotifEnable
--   ObjVar
--    csnUsageThreshold
--   ObjVar
--    csnUsageInterval


END
