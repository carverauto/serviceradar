-- MIB file created 16-Jul-2008 23:48:19, by
--   SMICng version 2.2.11-beta(PRO)(Solaris), January 20, 2001. Enterprise key cisco.com

IEEE8021-CFM-MIB DEFINITIONS ::= BEGIN

-- From file: "CISCO-IEEE-CFM-MIB.my"
-- Compile options "4 7 F H N O W 03 06 0B 0G 0N 0T"

IMPORTS
    TimeInterval, TimeStamp, RowStatus, TruthValue, MacAddress, 
    TDomain, TAddress
            FROM SNMPv2-TC-v1
    ciscoMgmt
            FROM CISCO-SMI
    InterfaceIndex, InterfaceIndexOrZero
            FROM IF-MIB
    VlanId
            FROM Q-BRIDGE-MIB
    Counter, Gauge
            FROM RFC1155-SMI
    OBJECT-TYPE
            FROM RFC-1212
    TRAP-TYPE
            FROM RFC-1215;

cdot1CfmMIB OBJECT IDENTIFIER ::= { ciscoMgmt 604 }
-- MODULE-IDENTITY
--  LastUpdated
--    200701240000Z
--  OrgName
--    Cisco, Inc.
--  ContactInfo
--            Cisco
--                  Customer Service
--    
--          Postal: 170 W Tasman Drive
--                  San Jose, CA 95134
--                  USA
--    
--          Tel:    +1 800 553-NETS
--          Email:  cs-ethermibs@cisco.com
--  Descr
--    Connectivity Fault Management module for managing IEEE 802.1ag
--  RevDate
--    200701240000Z
--  RevDescr
--    Initial version.

cdot1agNotifications OBJECT IDENTIFIER ::= { cdot1CfmMIB 0 }
cdot1agMIBObjects OBJECT IDENTIFIER ::= { cdot1CfmMIB 1 }
cdot1agConformance OBJECT IDENTIFIER ::= { cdot1CfmMIB 2 }
cdot1agStack    OBJECT IDENTIFIER ::= { cdot1agMIBObjects 1 }
cdot1agDefaultMd OBJECT IDENTIFIER ::= { cdot1agMIBObjects 2 }
cdot1agVlan     OBJECT IDENTIFIER ::= { cdot1agMIBObjects 3 }
cdot1agConfigErrorList OBJECT IDENTIFIER ::= { cdot1agMIBObjects 4 }
cdot1agMd       OBJECT IDENTIFIER ::= { cdot1agMIBObjects 5 }
cdot1agMa       OBJECT IDENTIFIER ::= { cdot1agMIBObjects 6 }
cdot1agMep      OBJECT IDENTIFIER ::= { cdot1agMIBObjects 7 }
cdot1agCompliances OBJECT IDENTIFIER ::= { cdot1agConformance 1 }
cdot1agGroups   OBJECT IDENTIFIER ::= { cdot1agConformance 2 }

Cdot1agMaintDomainNameType ::= INTEGER {
        none(1),
        dnsLikeName(2),
        macAddressAndUint(3),
        charString(4)
        }
-- TEXTUAL-CONVENTION
--  Status
--    mandatory
--  Descr
--    A value that represents a type (and thereby the format)
--     of a Cdot1agMaintDomainName.  The value can be one of
--     the following:
--    
--    
--     ieeeReserved(0)   Reserved for definition by IEEE 802.1
--                       recommend to not use zero unless
--                       absolutely needed.
--     none(1)           No format specified, usually because
--                       there is not (yet) a Maintenance
--                       Domain Name. In this case, a zero
--                       length OCTET STRING for the Domain
--                       Name field is acceptable.
--     dnsLikeName(2)    Domain Name like string, globally unique
--                       text string derived from a DNS name.
--     macAddrAndUint(3) MAC address + 2-octet (unsigned) integer.
--     charString(4)     RFC2579 DisplayString, except that the
--                       character codes 0-31 (decimal) are not
--                       used.
--     ieeeReserved(xx)  Reserved for definition by IEEE 802.1
--                       xx values can be [5..31] and [64..255]
--     ituReserved(xx)   Reserved for definition by  ITU-T Y.1731
--                       xx values range from [32..63]
--    
--     To support future extensions, the Cdot1agMaintDomainNameType
--     textual convention SHOULD NOT be sub-typed in object type
--     definitions.  It MAY be sub-typed in compliance statements in
--     order to require only a subset of these address types for a
--     compliant implementation.
--    
--     Implementations must ensure that Cdot1agMaintDomainNameType
--     objects and any dependent objects (e.g.,
--     Cdot1agMaintDomainName objects) are consistent.  An
--     inconsistentValue error must be generated if an attempt to
--     change an Cdot1agMaintDomainNameType object would, for
--     example, lead to an undefined Cdot1agMaintDomainName value.
--     In particular,
--     Cdot1agMaintDomainNameType/Cdot1agMaintDomainName pairs
--     must be changed together if the nameType changes.
--  Refer
--    802.1ag clause 21.6.5, Table 21-19

Cdot1agMaintDomainName ::= OCTET STRING(SIZE(1..43))
-- TEXTUAL-CONVENTION
--  Status
--    mandatory
--  Descr
--    Denotes a generic Maintenance Domain Name.
--    
--     A Cdot1agMaintDomainName value is always interpreted within
--     the context of a Cdot1agMaintDomainNameType value.  Every
--     usage of the Cdot1agMaintDomainName textual convention is
--     required to specify the Cdot1agMaintDomainNameType object
--     that provides the context.  It is suggested that the
--     Cdot1agMaintDomainNameType object be logically registered
--     before the object(s) that use the Cdot1agMaintDomainName
--     textual convention, if they appear in the same logical row.
--    
--     The value of a Cdot1agMaintDomainName object must always
--     be consistent with the value of the associated
--     Cdot1agMaintDomainNameType object. Attempts to set
--     an Cdot1agMaintDomainName object to a value inconsistent
--     with the associated Cdot1agMaintDomainNameType must fail
--     with an inconsistentValue error.
--    
--     When this textual convention is used as the syntax of an
--     index object, there may be issues with the limit of 128
--     sub-identifiers specified in SMIv2, IETF STD 58.  In this
--     case, the object definition MUST include a 'SIZE' clause
--     to limit the number of potential instance sub-identifiers;
--     otherwise the applicable constraints MUST be stated in
--     the appropriate conceptual row DESCRIPTION clauses, or
--     in the surrounding documentation if there is no single
--     DESCRIPTION clause that is appropriate.
--    
--     A value of none(1) in the associated
--     Cdot1agMaintDomainNameType object means that no Maintenance
--     Domain name is present, and the contents of the
--     Cdot1agMaintDomainName object are meaningless.
--    
--     See the DESCRIPTION of the Cdot1agMaintAssocNameType
--     TEXTUAL-CONVENTION for a discussion of the length limits on
--     the Maintenance Domain name and Maintenance Association name.
--  Refer
--    802.1ag clause 21.6.5

Cdot1agMaintAssocNameType ::= INTEGER {
        primaryVid(1),
        charString(2),
        unsignedInt16(3),
        rfc2865VpnId(4)
        }
-- TEXTUAL-CONVENTION
--  Status
--    mandatory
--  Descr
--    A value that represents a type (and thereby the format)
--     of a Cdot1agMaintAssocName.  The value can be one of
--     the following:
--    
--     ieeeReserved(0)   Reserved for definition by IEEE 802.1
--                       recommend to not use zero unless
--                       absolutely needed.
--     primaryVid(1)     Primary VLAN ID.
--                       12 bits represented in a 2-octet integer:
--                       - 4 least significant bits of the first
--                         byte contains the 4 most significant 
--                         bits of the 12 bits primary VID
--                       - second byte contains the 8 least
--                         significant bits of the primary VID
--    
--                              0 1 2 3 4 5 6 7 8
--                              +-+-+-+-+-+-+-+-+
--                              |0 0 0 0| (MSB) |
--                              +-+-+-+-+-+-+-+-+
--                              |  VID   LSB    |
--                              +-+-+-+-+-+-+-+-+
--    
--     charString(2)     RFC2579 DisplayString, except that the
--                       character codes 0-31 (decimal) are not
--                       used. (1..45) octets
--     unsignedInt16 (3) 2-octet integer/big endian
--     rfc2865VpnId(4)   RFC 2685 VPN ID
--                       3 octet VPN authority Organizationally
--                       Unique Identifier followed by 4 octet VPN
--                       index identifying VPN according to the OUI:
--    
--                              0 1 2 3 4 5 6 7 8
--                              +-+-+-+-+-+-+-+-+
--                              | VPN OUI (MSB) |
--                              +-+-+-+-+-+-+-+-+
--                              |   VPN OUI     |
--                              +-+-+-+-+-+-+-+-+
--                              | VPN OUI (LSB) |
--                              +-+-+-+-+-+-+-+-+
--                              |VPN Index (MSB)|
--                              +-+-+-+-+-+-+-+-+
--                              |  VPN Index    |
--                              +-+-+-+-+-+-+-+-+
--                              |  VPN Index    |
--                              +-+-+-+-+-+-+-+-+
--                              |VPN Index (LSB)|
--                              +-+-+-+-+-+-+-+-+
--    
--     ieeeReserved(xx)  Reserved for definition by IEEE 802.1
--                       xx values can be [5..31] and [64..255]
--     ituReserved(xx)   Reserved for definition by  ITU-T Y.1731
--                       xx values range from [32..63]
--    
--     To support future extensions, the Cdot1agMaintAssocNameType
--     textual convention SHOULD NOT be sub-typed in object type
--     definitions.  It MAY be sub-typed in compliance statements in
--     order to require only a subset of these address types for a
--     compliant implementation.
--    
--     Implementations must ensure that Cdot1agMaintAssocNameType
--     objects and any dependent objects (e.g.,
--     Cdot1agMaintAssocName objects) are consistent.  An
--     inconsistentValue error must be generated if an attempt to
--     change an Cdot1agMaintAssocNameType object would, for
--     example, lead to an undefined Cdot1agMaintAssocName value.
--     In particular,
--     Cdot1agMaintAssocNameType/Cdot1agMaintAssocName pairs
--     must be changed together if the nameType changes.
--    
--     The Maintenance Domain name and Maintenance Association name,
--     when put together into the CCM PDU, MUST total 48 octets or
--     less.  If the Cdot1agMaintDomainNameType object contains
--     none(1), then the Cdot1agMaintAssocName object MUST be
--     45 octets or less in length.  Otherwise, the length of
--     the Cdot1agMaintDomainName object plus the length of the
--     Cdot1agMaintAssocName object, added together, MUST total
--     less than or equal to 44 octets.
--  Refer
--    802.1ag clause 21.6.5.4, Table 21-20

Cdot1agMaintAssocName ::= OCTET STRING(SIZE(1..45))
-- TEXTUAL-CONVENTION
--  Status
--    mandatory
--  Descr
--    Denotes a generic Maintenance Association Name. It is the
--     part of the Maintenance Association Identifier which is
--     unique within the Maintenance Domain Name and is appended
--     to the Maintenance Domain Name to form the Maintenance
--     Association Identifier (MAID).
--    
--     A Cdot1agMaintAssocName value is always interpreted within
--     the context of a Cdot1agMaintAssocNameType value.  Every
--     usage of the Cdot1agMaintAssocName textual convention is
--     required to specify the Cdot1agMaintAssocNameType object
--     that provides the context.  It is suggested that the
--     Cdot1agMaintAssocNameType object be logically registered
--     before the object(s) that use the Cdot1agMaintAssocName
--     textual convention, if they appear in the same logical row.
--    
--     The value of a Cdot1agMaintAssocName object must 
--     always be consistent with the value of the associated
--     Cdot1agMaintAssocNameType object. Attempts to set
--     an Cdot1agMaintAssocName object to a value inconsistent
--     with the associated Cdot1agMaintAssocNameType must fail
--     with an inconsistentValue error.
--    
--     When this textual convention is used as the syntax of an
--     index object, there may be issues with the limit of 128
--     sub-identifiers specified in SMIv2, IETF STD 58.  In this
--     case, the object definition MUST include a 'SIZE' clause
--     to limit the number of potential instance sub-identifiers;
--     otherwise the applicable constraints MUST be stated in
--     the appropriate conceptual row DESCRIPTION clauses, or
--     in the surrounding documentation if there is no single
--     DESCRIPTION clause that is appropriate.
--  Refer
--    802.1ag clauses 21.6.5.4, 21.6.5.5, 21.6.5.6

Cdot1agMDLevel ::= INTEGER(0..7)
-- TEXTUAL-CONVENTION
--  DspHint
--    d
--  Status
--    mandatory
--  Descr
--    Integer identifying the Maintenance Domain Level (MD Level).
--     Higher numbers correspond to higher Maintenance Domains,
--     those with the greatest physical reach, with the highest
--     values for customers' CFM PDUs.  Lower numbers correspond
--     to lower Maintenance Domains, those with more limited
--     physical reach, with the lowest values for CFM PDUs
--     protecting single bridges or physical links.
--  Refer
--    802.1ag clauses 18.3, 21.4.1

Cdot1agMDLevelOrNone ::= INTEGER(-1|0..7)
-- TEXTUAL-CONVENTION
--  DspHint
--    d
--  Status
--    mandatory
--  Descr
--    Integer identifying the Maintenance Domain Level (MD Level).
--     Higher numbers correspond to higher Maintenance Domains,
--     those with the greatest physical reach, with the highest
--     values for customers' CFM packets.  Lower numbers correspond
--     to lower Maintenance Domains, those with more limited
--     physical reach, with the lowest values for CFM PDUs
--     protecting single bridges or physical links.
--    
--     The value (-1) is reserved to indicate that no MA Level has
--     been assigned.
--  Refer
--    802.1ag clauses 18.3, 12.14.3.1.3:c

Cdot1agMpDirection ::= INTEGER {
        down(1),
        up(2)
        }
-- TEXTUAL-CONVENTION
--  Status
--    mandatory
--  Descr
--    Indicates the direction in which the Maintenance
--     association (MEP or MIP) faces on the bridge port:
--    
--     down(1)    Sends Continuity Check Messages away from the
--                MAC Relay Entity.
--     up(2)      Sends Continuity Check Messages towards the
--                MAC Relay Entity.
--  Refer
--    802.1ag clauses 12.14.6.3.2:c

Cdot1agPortStatus ::= INTEGER {
        --?? enum value of zero may cause problems
        psNoPortStateTLV(0),
        psBlocked(1),
        psUp(2)
        }
-- TEXTUAL-CONVENTION
--  Status
--    mandatory
--  Descr
--    An enumerated value from he Port Status TLV from the last CCM
--     received from the last MEP. It indicates the ability of the
--     Bridge Port on which the transmitting MEP resides to pass
--     ordinary data, regardless of the status of the MAC
--     (Table 21-10).
--    
--     psNoPortStateTLV(0) Indicates either that no CCM has been
--                         received or that no port status TLV was
--                         present in the last CCM received.
--    
--     psBlocked(1)        Ordinary data cannot pass freely through
--                         the port on which the remote MEP resides.
--                         Value of enableRmepDefect is equal to
--                         false.
--    
--     psUp(2):            Ordinary data can pass freely through
--                         the port on which the remote MEP resides.
--                         Value of enableRmepDefect is equal to
--                         true.
--    
--     NOTE: A 0 value is used for psNoPortStateTLV, so that
--           additional code points can be added in a manner
--           consistent with the Cdot1agInterfaceStatus textual
--           convention.
--  Refer
--    802.1ag clause 12.14.7.6.3:f, 20.19.3 and 21.5.4

Cdot1agInterfaceStatus ::= INTEGER {
        --?? enum value of zero may cause problems
        isNoInterfaceStatusTLV(0),
        isUp(1),
        isDown(2),
        isTesting(3),
        isUnknown(4),
        isDormant(5),
        isNotPresent(6),
        isLowerLayerDown(7)
        }
-- TEXTUAL-CONVENTION
--  Status
--    mandatory
--  Descr
--    An enumerated value from the Interface Status TLV from the 
--     last CCM received from the last MEP. It indicates the status
--     of the Interface within which the MEP transmitting the CCM
--     is configured, or the next lower Interface in the Interface
--     Stack, if the MEP is not configured within an Interface.
--    
--    isNoInterfaceStatusTLV(0)  Indicates either that no CCM has been
--                       received or that no interface status TLV
--                       was present in the last CCM received.
--    
--    isUp(1)               The interface is ready to pass packets.
--    
--    isDown(2)             The interface cannot pass packets
--    
--    isTesting(3)          The interface is in some test mode.
--    
--    isUnknown(4)          The interface status cannot be determined
--                       for some reason.
--    
--    isDormant(5)          The interface is not in a state to pass
--                       packets but is in a pending state, waiting
--                       for some external event.
--    
--    isNotPresent(6)       Some component of the interface is missing
--    
--    isLowerLayerDown(7)   The interface is down due to state of the
--                       lower layer interfaces
--    
--     NOTE: A 0 value is used for isNoInterfaceStatusTLV, so that
--           these code points can be kept consistent with new code
--           points added to ifOperStatus in the IF-MIB.
--    
--  Refer
--    802.1ag clause 12.14.7.6.3:g, 20.19.4 and 21.5.5

Cdot1agHighestDefectPri ::= INTEGER {
        --?? enum value of zero may cause problems
        none(0),
        defRDICCM(1),
        defMACstatus(2),
        defRemoteCCM(3),
        defErrorCCM(4),
        defXconCCM(5)
        }
-- TEXTUAL-CONVENTION
--  Status
--    mandatory
--  Descr
--    An enumerated value, equal to the contents of the variable
--     highestDefect (20.33.9 and Table 20-1), indicating the
--     highest-priority defect that has been present since the MEP
--     Fault Notification Generator State Machine was last in the 
--     FNG_RESET state, either:
--    
--     none(0)           no defects since FNG_RESET
--     defRDICCM(1)      DefRDICCM
--     defMACstatus(2)   DefMACstatus
--     defRemoteCCM(3)   DefRemoteCCM
--     defErrorCCM(4)    DefErrorCCM
--     defXconCCM(5)     DefXconCCM
--    
--     The value 0 is used for no defects so that additional higher
--     priority values can be added, if needed, at a later time, and
--     so that these values correspond with those in
--     Cdot1agLowestAlarmPri.
--  Refer
--    802.1ag clause 20.1.2, 12.14.7.7.2:c and 20.33.9

Cdot1agLowestAlarmPri ::= INTEGER {
        allDef(1),
        macRemErrXcon(2),
        remErrXcon(3),
        errXcon(4),
        xcon(5),
        noXcon(6)
        }
-- TEXTUAL-CONVENTION
--  Status
--    mandatory
--  Descr
--    An integer value specifying the lowest priority defect
--     that is allowed to generate a Fault Alarm (20.9.5), either:
--    
--     allDef(1)           DefRDICCM, DefMACstatus, DefRemoteCCM,
--                         DefErrorCCM, and DefXconCCM;
--     macRemErrXcon(2)    Only DefMACstatus, DefRemoteCCM,
--                         DefErrorCCM, and DefXconCCM (default);
--     remErrXcon(3)       Only DefRemoteCCM, DefErrorCCM,
--                         and DefXconCCM;
--     errXcon(4)          Only DefErrorCCM and DefXconCCM;
--     xcon(5)             Only DefXconCCM; or
--     noXcon(6)           No defects DefXcon or lower are to be
--                         reported;
--  Refer
--    802.1ag clause 12.14.7.1.3:k and 20.9.5

Cdot1agMepId ::= Gauge(1..8191)
-- TEXTUAL-CONVENTION
--  DspHint
--    d
--  Status
--    mandatory
--  Descr
--    Maintenance association End Point Identifier (MEPID): A small
--     integer, unique over a given Maintenance Association,
--     identifying a specific MEP.
--  Refer
--    802.1ag clauses 3.19 and 19.2.1

Cdot1agMepIdOrZero ::= Gauge(0|1..8191)
-- TEXTUAL-CONVENTION
--  DspHint
--    d
--  Status
--    mandatory
--  Descr
--    Maintenance association End Point Identifier (MEPID): A small
--     integer, unique over a given Maintenance Association,
--     identifying a specific MEP.
--    
--     The special value 0 is allowed to indicate special cases, for
--     example that no MEPID is configured.
--    
--     Whenever an object is defined with this SYNTAX, then the
--     DESCRIPTION clause of such an object MUST specify what the
--     special value of 0 means.
--  Refer
--    802.1ag clause 19.2.1

Cdot1agMhfCreation ::= INTEGER {
        defMHFnone(1),
        defMHFdefault(2),
        defMHFexplicit(3),
        defMHFdefer(4)
        }
-- TEXTUAL-CONVENTION
--  Status
--    mandatory
--  Descr
--    Indicates if the Management Entity can create MHFs.
--     The valid values are:
--    
--     defMHFnone(1)      No MHFs can be created for this VID.
--     defMHFdefault(2)   MHFs can be created on this VID on any
--                        Bridge port through which this VID can
--                        pass.
--     defMHFexplicit(3)  MHFs can be created for this VID only on
--                        Bridge ports through which this VID can
--                        pass, and only if a MEP is created at some
--                        lower MD Level.
--     defMHFdefer(4)     The creation of MHFs is determined by the
--                        corresponding Maintenance Domain variable
--                        (cdot1agMaMhfCreation).
--  Refer
--    802.1ag clause 12.14.5.1.3:c and 22.2.3

Cdot1agIdPermission ::= INTEGER {
        sendIdNone(1),
        sendIdChassis(2),
        sendIdManage(3),
        sendIdChassisManage(4),
        sendIdDefer(5)
        }
-- TEXTUAL-CONVENTION
--  Status
--    mandatory
--  Descr
--    Indicates what, if anything, is to be included in the Sender
--     ID TLV transmitted in CCMs, LBMs, LTMs, and LTRs.  The valid
--     values are:
--    
--     sendIdNone(1)      The Sender ID TLV is not to be sent.
--     sendIdChassis(2)   The Chassis ID Length, Chassis ID
--                        Subtype, and Chassis ID fields of  the
--                        Sender ID TLV are to be sent.
--     sendIdManage(3)    The Management Address Length and
--                        Management Address of the Sender ID TLV
--                        are to be sent.
--     sendIdChassisManage(4) The Chassis ID Length, Chassis ID
--                        Subtype, Chassis ID, Management Address
--                        Length and Management Address fields are
--                        all to be sent.
--     sendIdDefer(5)     The contents of the Sender ID TLV are
--                        determined by the corresponding
--                        Maintenance Domain variable
--                        (cdot1agMaIdPermission).
--  Refer
--    802.1ag clause 12.14.6.1.3:d and 21.5.3

Cdot1agCcmInterval ::= INTEGER {
        --?? enum value of zero may cause problems
        intervalInvalid(0),
        interval300Hz(1),
        interval10ms(2),
        interval100ms(3),
        interval1s(4),
        interval10s(5),
        interval1min(6),
        interval10min(7)
        }
-- TEXTUAL-CONVENTION
--  Status
--    mandatory
--  Descr
--    Indicates the interval at which CCMs are sent by a MEP.
--     The possible values are:
--     intervalInvalid(0) No CCMs are sent (disabled).
--     interval300Hz(1)   CCMs are sent every 3 1/3 milliseconds
--                        (300Hz).
--     interval10ms(2)    CCMs are sent every 10 milliseconds.
--     interval100ms(3)   CCMs are sent every 100 milliseconds.
--     interval1s(4)      CCMs are sent every 1 second.
--     interval10s(5)     CCMs are sent every 10 seconds.
--     interval1min(6)    CCMs are sent every minute.
--     interval10min(7)   CCMs are sent every 10 minutes.
--    
--     Note: enumerations start at zero to match the 'CCM Interval
--           field' protocol field.
--  Refer
--    802.1ag clauses 12.14.6.1.3:e, 20.8.1 and 21.6.1.3

Cdot1agFngState ::= INTEGER {
        fngReset(1),
        fngDefect(2),
        fngReportDefect(3),
        fngDefectReported(4),
        fngDefectClearing(5)
        }
-- TEXTUAL-CONVENTION
--  Status
--    mandatory
--  Descr
--    Indicates the diferent states of the MEP Fault Notification
--     Generator State Machine.
--    
--     fngReset(1)            No defect has been present since the
--                            cdot1agMepFngResetTime timer
--                            expired, or since the state machine
--                            was last reset.
--    
--     fngDefect(2)           A defect is present, but not for a
--                            long enough time to be reported 
--                            (cdot1agMepFngAlarmTime).
--    
--     fngReportDefect(3)     A momentary state during which the
--                            defect is reported by sending a
--                            cdot1agFaultAlarm notification,
--                            if that action is enabled.
--    
--     fngDefectReported(4)   A defect is present, and some defect
--                            has been reported.
--    
--     fngDefectClearing(5)   No defect is present, but the
--                            cdot1agMepFngResetTime timer has
--                            not yet expired.
--  Refer
--    802.1ag clause 12.14.7.1.3:f and 20.35

Cdot1agRelayActionFieldValue ::= INTEGER {
        rlyHit(1),
        rlyFdb(2),
        rlyMpdb(3)
        }
-- TEXTUAL-CONVENTION
--  Status
--    mandatory
--  Descr
--    Possible values the Relay action field can take.
--  Refer
--    802.1ag clauses 12.14.7.5.3:g, 20.36.2.5, 21.9.5, and
--     Table 21-27

Cdot1agIngressActionFieldValue ::= INTEGER {
        ingOk(1),
        ingDown(2),
        ingBlocked(3),
        ingVid(4)
        }
-- TEXTUAL-CONVENTION
--  Status
--    mandatory
--  Descr
--    Possible values returned in the ingress action field.
--  Refer
--    802.1ag clauses 12.14.7.5.3:g, 20.36.2.6, 21.9.8.1, and
--     Table 21-30

Cdot1agEgressActionFieldValue ::= INTEGER {
        egrOK(1),
        egrDown(2),
        egrBlocked(3),
        egrVid(4)
        }
-- TEXTUAL-CONVENTION
--  Status
--    mandatory
--  Descr
--    Possible values returned in the egress action field
--  Refer
--    802.1ag clauses 12.14.7.5.3:o, 20.36.2.10, 21.9.9.1, and
--     Table 21-32

Cdot1agRemoteMepState ::= INTEGER {
        rMepIdle(1),
        rMepStart(2),
        rMepFailed(3),
        rMepOk(4)
        }
-- TEXTUAL-CONVENTION
--  Status
--    mandatory
--  Descr
--    Operational state of the remote MEP state machine.  This
--     state machine monitors the reception of valid CCMs from a
--     remote MEP with a specific MEPID.  It uses a timer that
--     expires in 3.5 times the length of time indicated by the
--     cdot1agMaCcmInterval object.
--    
--     rMepIdle(1)            Momentary state during reset.
--    
--     rMepStart(2)           The timer has not expired since the
--                            state machine was reset, and no valid
--                            CCM has yet been received.
--    
--     rMepFailed(3)          The timer has expired, both since the
--                            state machine was reset, and since a
--                            valid CCM was received.
--    
--     rMepOk(4)              The timer has not expired since a
--                            valid CCM was received.
--  Refer
--    802.1ag clauses 12.14.7.6.3:b, 20.22

Dot1afCfmIndexIntegerNextFree ::= Gauge(0..4294967295)
-- TEXTUAL-CONVENTION
--  DspHint
--    d
--  Status
--    mandatory
--  Descr
--    An integer which may be used as a new Index in a table.
--    
--     The special value of 0 indicates that no more new entries can
--     be created in the relevant table.
--    
--     When a MIB is used for configuration, an object with this
--     SYNTAX always contains a legal value (if non-zero) for an
--     index that is not currently used in the relevant table. The
--     Command Generator (Network Management Application) reads this
--     variable and uses the (non-zero) value read when creating a
--     new row with an SNMP SET.  When the SET is performed, the
--     Command Responder (agent) must determine whether the value is
--     indeed still unused; Two Network Management Applications may
--     attempt to create a row (configuration entry) simultaneously
--     and use the same value. If it is currently unused, the SET
--     succeeds and the Command Responder (agent) changes the value
--     of this object, according to an implementation-specific
--     algorithm.  If the value is in use, however, the SET fails.
--     The Network Management Application must then re-read this
--     variable to obtain a new usable value.
--    
--     An OBJECT-TYPE definition using this SYNTAX MUST specify the
--     relevant table for which the object is providing this
--     functionality.

Cdot1agMepDefects ::= OCTET STRING(SIZE(1..2))
        -- BITS are:
        --   bDefRDICCM(0)
        --   bDefMACstatus(1)
        --   bDefRemoteCCM(2)
        --   bDefErrorCCM(3)
        --   bDefXconCCM(4)
-- TEXTUAL-CONVENTION
--  Status
--    mandatory
--  Descr
--    A MEP can detect and report a number of defects, and multiple
--     defects can be present at the same time. These defects are:
--    
--     bDefRDICCM(0) A remote MEP is reported the RDI bit in its
--                  last CCM.
--     bDefMACstatus(1) Either some remote MEP is reporting its
--                  Interface Status TLV as not isUp, or all remote
--                  MEPs are reporting a Port Status TLV that
--                  contains some value other than psUp.
--     bDefRemoteCCM(2) The MEP is not receiving valid CCMs from at
--                  least one of the remote MEPs.
--     bDefErrorCCM(3) The MEP has received at least one invalid CCM
--                  whose CCM Interval has not yet timed out.
--     bDefXconCCM(4) The MEP has received at least one CCM from
--                  either another MAID or a lower MD Level whose
--                  CCM Interval has not yet timed out.
--  Refer
--    802.1ag clauses 12.14.7.1.3:o, 12.14.7.1.3:p, 12.14.7.1.3:q,
--     12.14.7.1.3:r, and 12.14.7.1.3:s.

Cdot1agConfigErrors ::= OCTET STRING(SIZE(1..2))
        -- BITS are:
        --   cfmLeak(0)
        --   conflictingVids(1)
        --   excessiveLevels(2)
        --   overlappedLevels(3)
-- TEXTUAL-CONVENTION
--  Status
--    mandatory
--  Descr
--    While making the MIP creation evaluation described in 802.1ag
--     clause 22.2.3, the management entity can encounter errors in
--     the configuration. These are possible errors that can be
--     encountered:
--    
--     CFMleak(0)   MA x is associated with a specific VID list,
--                  one or more of the VIDs in MA x can pass through
--                  the Bridge Port, no Down MEP is configured on
--                  any Bridge Port for MA x, and some other MA y,
--                  at a higher MD Level than MA x, and associated
--                  with at least one of the VID(s) also in MA x,
--                  does have a MEP configured on the Bridge Port.
--    
--     conflictingVids(1)  MA x is associated with a specific VID
--                  list, an Up MEP is configured on MA x on the
--                  Bridge Port, and some other MA y, associated
--                  with at least one of the VID(s) also in MA x,
--                  also has an Up MEP configured on some Bridge
--                  Port.
--    
--     ExcessiveLevels(2)  The number of different MD Levels at
--                  which MIPs are to be created on this port
--                  exceeds the Bridge's capabilities (see
--                  subclause 22.3).
--    
--     OverlappedLevels(3) A MEP is created for one VID at one MD
--                  Level, but a MEP is configured on another
--                  VID at that MD Level or higher, exceeding
--                  the Bridge's capabilities.
--  Refer
--    802.1ag clause 12.14.4.1.3:b and clauses 22.2.3 and 22.2.4

ClldpChassisIdSubtype ::= INTEGER {
        chassisComponent(1),
        interfaceAlias(2),
        portComponent(3),
        macAddress(4),
        networkAddress(5),
        interfaceName(6),
        local(7)
        }
-- TEXTUAL-CONVENTION
--  Status
--    mandatory
--  Descr
--    This TC describes the source of a chassis identifier.
--    
--    The enumeration 'chassisComponent(1)' represents a chassis
--    identifier based on the value of entPhysicalAlias object
--    (defined in IETF RFC 2737) for a chassis component (i.e.,
--    an entPhysicalClass value of 'chassis(3)').
--    
--    The enumeration 'interfaceAlias(2)' represents a chassis
--    identifier based on the value of ifAlias object (defined in
--    IETF RFC 2863) for an interface on the containing chassis.
--    
--    The enumeration 'portComponent(3)' represents a chassis
--    identifier based on the value of entPhysicalAlias object
--    (defined in IETF RFC 2737) for a port or backplane
--    component (i.e., entPhysicalClass value of 'port(10)' or
--    'backplane(4)'), within the containing chassis.
--    'backplane(4)'), within the containing chassis.
--    
--    The enumeration 'macAddress(4)' represents a chassis
--    identifier based on the value of a unicast source address
--    (encoded in network byte order and IEEE 802.3 canonical bit
--    order), of a port on the containing chassis as defined in
--    IEEE Std 802-2001.
--    
--    The enumeration 'networkAddress(5)' represents a chassis
--    identifier based on a network address, associated with
--    a particular chassis.  The encoded address is actually
--    composed of two fields.  The first field is a single octet,
--    representing the IANA AddressFamilyNumbers value for the
--    specific address type, and the second field is the network
--    address value.
--    
--    The enumeration 'interfaceName(6)' represents a chassis
--    identifier based on the value of ifName object (defined in
--    IETF RFC 2863) for an interface on the containing chassis.
--    
--    The enumeration 'local(7)' represents a chassis identifier
--    based on a locally defined value.

ClldpChassisId ::= OCTET STRING(SIZE(1..255))
-- TEXTUAL-CONVENTION
--  Status
--    mandatory
--  Descr
--    This TC describes the format of a chassis identifier string.
--    Objects of this type are always used with an associated
--    ClldpChassisIdSubtype object, which identifies the format of
--    the particular ClldpChassisId object instance.
--    
--    If the associated ClldpChassisIdSubtype object has a value of
--    'chassisComponent(1)', then the octet string identifies
--    a particular instance of the entPhysicalAlias object
--    (defined in IETF RFC 2737) for a chassis component (i.e.,
--    an entPhysicalClass value of 'chassis(3)').
--    
--    If the associated ClldpChassisIdSubtype object has a value
--    of 'interfaceAlias(2)', then the octet string identifies
--    a particular instance of the ifAlias object (defined in
--    IETF RFC 2863) for an interface on the containing chassis.
--    If the particular ifAlias object does not contain any values,
--    another chassis identifier type should be used.
--    
--    If the associated ClldpChassisIdSubtype object has a value
--    of 'portComponent(3)', then the octet string identifies a
--    particular instance of the entPhysicalAlias object (defined
--    in IETF RFC 2737) for a port or backplane component within
--    the containing chassis.
--    
--    If the associated ClldpChassisIdSubtype object has a value of
--    'macAddress(4)', then this string identifies a particular
--    unicast source address (encoded in network byte order and
--    'macAddress(4)', then this string identifies a particular
--    unicast source address (encoded in network byte order and
--    IEEE 802.3 canonical bit order), of a port on the containing
--    chassis as defined in IEEE Std 802-2001.
--    
--    If the associated ClldpChassisIdSubtype object has a value of
--    'networkAddress(5)', then this string identifies a particular
--    network address, encoded in network byte order, associated
--    with one or more ports on the containing chassis.  The first
--    octet contains the IANA Address Family Numbers enumeration
--    value for the specific address type, and octets 2 through
--    N contain the network address value in network byte order.
--    
--    If the associated ClldpChassisIdSubtype object has a value
--    of 'interfaceName(6)', then the octet string identifies
--    a particular instance of the ifName object (defined in
--    IETF RFC 2863) for an interface on the containing chassis.
--    If the particular ifName object does not contain any values,
--    another chassis identifier type should be used.
--    
--    If the associated ClldpChassisIdSubtype object has a value of
--    'local(7)', then this string identifies a locally assigned
--    Chassis ID.

ClldpPortIdSubtype ::= INTEGER {
        interfaceAlias(1),
        portComponent(2),
        macAddress(3),
        networkAddress(4),
        interfaceName(5),
        agentCircuitId(6),
        local(7)
        }
-- TEXTUAL-CONVENTION
--  Status
--    mandatory
--  Descr
--    This TC describes the source of a particular type of port
--    identifier used in the LLDP MIB.
--    
--    The enumeration 'interfaceAlias(1)' represents a port
--    
--    The enumeration 'interfaceAlias(1)' represents a port
--    identifier based on the ifAlias MIB object, defined in IETF
--    RFC 2863.
--    
--    The enumeration 'portComponent(2)' represents a port
--    identifier based on the value of entPhysicalAlias (defined in
--    IETF RFC 2737) for a port component (i.e., entPhysicalClass
--    value of 'port(10)'), within the containing chassis.
--    
--    The enumeration 'macAddress(3)' represents a port identifier
--    based on a unicast source address (encoded in network
--    byte order and IEEE 802.3 canonical bit order), which has
--    been detected by the agent and associated with a particular
--    port (IEEE Std 802-2001).
--    
--    The enumeration 'networkAddress(4)' represents a port
--    identifier based on a network address, detected by the agent
--    and associated with a particular port.
--    
--    The enumeration 'interfaceName(5)' represents a port
--    identifier based on the ifName MIB object, defined in IETF
--    RFC 2863.
--    
--    The enumeration 'agentCircuitId(6)' represents a port
--    identifier based on the agent-local identifier of the circuit
--    (defined in RFC 3046), detected by the agent and associated
--    with a particular port.
--    
--    The enumeration 'local(7)' represents a port identifier
--    based on a value locally assigned.

ClldpPortId ::= OCTET STRING(SIZE(1..255))
-- TEXTUAL-CONVENTION
--  Status
--    mandatory
--  Descr
--    This TC describes the format of a port identifier string.
--    Objects of this type are always used with an associated
--    ClldpPortIdSubtype object, which identifies the format of the
--    particular ClldpPortId object instance.
--    
--    If the associated ClldpPortIdSubtype object has a value of
--    'interfaceAlias(1)', then the octet string identifies a
--    particular instance of the ifAlias object (defined in IETF
--    RFC 2863).  If the particular ifAlias object does not contain
--    any values, another port identifier type should be used.
--    
--    If the associated ClldpPortIdSubtype object has a value of
--    'portComponent(2)', then the octet string identifies a
--    particular instance of the entPhysicalAlias object (defined
--    in IETF RFC 2737) for a port or backplane component.
--    
--    If the associated ClldpPortIdSubtype object has a value of
--    
--    If the associated ClldpPortIdSubtype object has a value of
--    'macAddress(3)', then this string identifies a particular
--    unicast source address (encoded in network byte order
--    and IEEE 802.3 canonical bit order) associated with the port
--    (IEEE Std 802-2001).
--    
--    If the associated ClldpPortIdSubtype object has a value of
--    'networkAddress(4)', then this string identifies a network
--    address associated with the port.  The first octet contains
--    the IANA AddressFamilyNumbers enumeration value for the
--    specific address type, and octets 2 through N contain the
--    networkAddress address value in network byte order.
--    
--    If the associated ClldpPortIdSubtype object has a value of
--    'interfaceName(5)', then the octet string identifies a
--    particular instance of the ifName object (defined in IETF
--    RFC 2863).  If the particular ifName object does not contain
--    any values, another port identifier type should be used.
--    
--    If the associated ClldpPortIdSubtype object has a value of
--    'agentCircuitId(6)', then this string identifies a agent-local
--    identifier of the circuit (defined in RFC 3046).
--    
--    If the associated ClldpPortIdSubtype object has a value of
--    'local(7)', then this string identifies a locally
--    assigned port ID.

ClldpManAddress ::= OCTET STRING(SIZE(1..31))
-- TEXTUAL-CONVENTION
--  Status
--    mandatory
--  Descr
--    The value of a management address associated with the LLDP
--    agent that may be used to reach higher layer entities to
--    assist discovery by network management.
--    
--    It should be noted that appropriate security credentials,
--    such as SNMP engineId, may be required to access the LLDP
--    agent using a management address.  These necessary credentials
--    should be known by the network management and the objects
--    associated with the credentials are not included in the
--    LLDP agent.

cdot1agStackTable OBJECT-TYPE
    SYNTAX SEQUENCE OF Cdot1agStackEntry
    ACCESS not-accessible
    STATUS mandatory
    DESCRIPTION
        "There is one CFM Stack table per bridge. It permits
         the retrieval of information about the Maintenance Points
         configured on any given interface."
    REFERENCE
        "802.1ag clauses 12.14.2"
    ::= { cdot1agStack 1 }

cdot1agStackEntry OBJECT-TYPE
    SYNTAX Cdot1agStackEntry
    ACCESS not-accessible
    STATUS mandatory
    DESCRIPTION
        "The Stack table entry"
    INDEX { cdot1agStackifIndex, cdot1agStackVlanIdOrNone, cdot1agStackMdLevel, cdot1agStackDirection }
    ::= { cdot1agStackTable 1 }

Cdot1agStackEntry ::= SEQUENCE {
    cdot1agStackifIndex InterfaceIndex,
    cdot1agStackVlanIdOrNone VlanId,
    cdot1agStackMdLevel Cdot1agMDLevel,
    cdot1agStackDirection Cdot1agMpDirection,
    cdot1agStackMdIndex Gauge,
    cdot1agStackMaIndex Gauge,
    cdot1agStackMepId Cdot1agMepIdOrZero,
    cdot1agStackMacAddress MacAddress
    }

cdot1agStackifIndex OBJECT-TYPE
    SYNTAX InterfaceIndex
--    Rsyntax INTEGER(1..2147483647)
    ACCESS not-accessible
    STATUS mandatory
    DESCRIPTION
        "This object represents the  Bridge Port or aggregated port
         on which MEPs or MHFs might be configured.
        
         Upon a restart of the system, the system SHALL, if necessary,
         change the value of this variable, and  rearrange the
         cdot1agStackTable, so that it indexes the entry in the
         interface table with the same value of ifAlias that it
         indexed before the system restart.  If no such entry exists,
         then the system SHALL delete all entries in the
         cdot1agStackTable with the interface index."
    REFERENCE
        "802.1ag clause 12.14.2.1.2:a"
    ::= { cdot1agStackEntry 1 }

cdot1agStackVlanIdOrNone OBJECT-TYPE
    SYNTAX VlanId
--    Rsyntax INTEGER(1..4094)
    ACCESS not-accessible
    STATUS mandatory
    DESCRIPTION
        "VLAN ID to which the MP is attached, or 0, if none."
    REFERENCE
        "802.1ag clause 12.14.2.1.2:d"
    ::= { cdot1agStackEntry 2 }

cdot1agStackMdLevel OBJECT-TYPE
    SYNTAX Cdot1agMDLevel
--    Rsyntax INTEGER(0..7)
    ACCESS not-accessible
    STATUS mandatory
    DESCRIPTION
        "MD Level of the Maintenance Point."
    REFERENCE
        "802.1ag clause 12.14.2.1.2:b"
    ::= { cdot1agStackEntry 3 }

cdot1agStackDirection OBJECT-TYPE
    SYNTAX Cdot1agMpDirection
--    Rsyntax INTEGER {
--        down(1),
--        up(2)
--        }
    ACCESS not-accessible
    STATUS mandatory
    DESCRIPTION
        "Direction in which the MP faces on the Bridge Port"
    REFERENCE
        "802.1ag clause 12.14.2.1.2:c"
    ::= { cdot1agStackEntry 4 }

cdot1agStackMdIndex OBJECT-TYPE
    SYNTAX Gauge
    ACCESS read-only
    STATUS mandatory
    DESCRIPTION
        "The index of the Maintenance Domain in the cdot1agMdTable
         to which the MP is associated, or 0, if none."
    REFERENCE
        "802.1ag clause 12.14.2.1.3:b"
    ::= { cdot1agStackEntry 5 }

cdot1agStackMaIndex OBJECT-TYPE
    SYNTAX Gauge
    ACCESS read-only
    STATUS mandatory
    DESCRIPTION
        "The index of the MA in the cdot1agMaTable to which the MP
         is associated, or 0, if none."
    REFERENCE
        "802.1ag clause 12.14.2.1.3:c"
    ::= { cdot1agStackEntry 6 }

cdot1agStackMepId OBJECT-TYPE
    SYNTAX Cdot1agMepIdOrZero
--    Rsyntax Gauge(0|1..8191)
    ACCESS read-only
    STATUS mandatory
    DESCRIPTION
        "If an MEP is configured, the MEPID, else 0"
    REFERENCE
        "802.1ag clause 12.14.2.1.3:d"
    ::= { cdot1agStackEntry 7 }

cdot1agStackMacAddress OBJECT-TYPE
    SYNTAX MacAddress
--    Rsyntax OCTET STRING(SIZE(6))
    ACCESS read-only
    STATUS mandatory
    DESCRIPTION
        "MAC address of the MP."
    REFERENCE
        "802.1ag clause 12.14.2.1.3:e"
    ::= { cdot1agStackEntry 8 }

cdot1agVlanTable OBJECT-TYPE
    SYNTAX SEQUENCE OF Cdot1agVlanEntry
    ACCESS not-accessible
    STATUS mandatory
    DESCRIPTION
        "This table defines the association of VIDs into VLANs.  There
         is an entry in this table for each VID that is:
             a) a VID belonging to a VLAN associated with more than
                one VID; and
             b) not the Primary VLAN of that VID.
         The entry in this table contains the Primary VID of the VLAN.
        
         By default, this table is empty, meaning that every VID is
         the Primary VID of a single-VID VLAN.
        
         VLANs that are associated with only one VID SHOULD NOT have
         an entry in this table.
        
         The writable objects in this table need to be persistent
         upon reboot or restart of a device."
    REFERENCE
        "802.1ag clauses 12.14.3.1.3:a, 12.14.3.2.2:a, 12.14.5.3.2:c,
         12.14.6.1.3:b, 22.1.5."
    ::= { cdot1agVlan 1 }

cdot1agVlanEntry OBJECT-TYPE
    SYNTAX Cdot1agVlanEntry
    ACCESS not-accessible
    STATUS mandatory
    DESCRIPTION
        "The VLAN table entry."
    INDEX { cdot1agVlanVid }
    ::= { cdot1agVlanTable 1 }

Cdot1agVlanEntry ::= SEQUENCE {
    cdot1agVlanVid VlanId,
    cdot1agVlanPrimaryVid VlanId,
    cdot1agVlanRowStatus RowStatus
    }

cdot1agVlanVid OBJECT-TYPE
    SYNTAX VlanId
--    Rsyntax INTEGER(1..4094)
    ACCESS not-accessible
    STATUS mandatory
    DESCRIPTION
        "This is a VLAN ID belonging to a VLAN that is associated with
         more than one VLAN ID, and this is not the Primary VID of the
         VLAN."
    ::= { cdot1agVlanEntry 1 }

cdot1agVlanPrimaryVid OBJECT-TYPE
    SYNTAX VlanId
--    Rsyntax INTEGER(1..4094)
    ACCESS read-write
    STATUS mandatory
    DESCRIPTION
        "This is the Primary VLAN ID of the VLAN with which this
         entry's cdot1agVlanVid is associated.  This value must not
         equal the value of cdot1agVlanVid."
    ::= { cdot1agVlanEntry 2 }

cdot1agVlanRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of the row.
        
         The writable columns in a row can not be changed if the row
         is active. All columns must have a valid value before a row
         can be activated."
    ::= { cdot1agVlanEntry 3 }

cdot1agDefaultMdDefLevel OBJECT-TYPE
    SYNTAX Cdot1agMDLevel
--    Rsyntax INTEGER(0..7)
    ACCESS read-write
    STATUS mandatory
    DESCRIPTION
        "A value indicating the MD Level at which MHFs are to be
         created, and Sender ID TLV transmission by those MHFs is to
         be controlled, for each cdot1agDefaultMdEntry whose
         cdot1agDefaultMdLevel object contains the value -1.
        
         After this initialization, this object needs to be persistent
         upon reboot or restart of a device."
    REFERENCE
        "802.1ag clause 12.14.3.1.3:c, 12.14.3.2.2:b"
    DEFVAL { 0 }
    ::= { cdot1agDefaultMd 1 }

cdot1agDefaultMdDefMhfCreation OBJECT-TYPE
    SYNTAX Cdot1agMhfCreation
--    Rsyntax INTEGER {
--        defMHFnone(1),
--        defMHFdefault(2),
--        defMHFexplicit(3),
--        defMHFdefer(4)
--        }
    ACCESS read-write
    STATUS mandatory
    DESCRIPTION
        "A value indicating if the Management entity can create MHFs
         (MIP Half Function) for the VID, for each
         cdot1agDefaultMdEntry whose cdot1agDefaultMdMhfCreation
         object contains the value defMHFdefer.  Since, in this
         variable, there is no encompassing Maintenance Domain, the
         value defMHFdefer takes the meaning of defMHFnone.
        
         After this initialization, this object needs to be persistent
         upon reboot or restart of a device."
    REFERENCE
        "802.1ag clause 12.14.3.1.3:d"
    DEFVAL { defMHFnone }
    ::= { cdot1agDefaultMd 2 }

cdot1agDefaultMdDefIdPermission OBJECT-TYPE
    SYNTAX Cdot1agIdPermission
--    Rsyntax INTEGER {
--        sendIdNone(1),
--        sendIdChassis(2),
--        sendIdManage(3),
--        sendIdChassisManage(4),
--        sendIdDefer(5)
--        }
    ACCESS read-write
    STATUS mandatory
    DESCRIPTION
        "Enumerated value indicating what, if anything, is to be
         included in the Sender ID TLV (21.5.3) transmitted by MHFs
         created by the Default Maintenance Domain, for each
         cdot1agDefaultMdEntry whose cdot1agDefaultMdIdPermission
         object contains the value sendIdDefer.  Since, in this
         variable, there is no encompassing Maintenance Domain, the
         value sendIdDefer takes the meaning of sendIdChassisManage.
        
         After this initialization, this object needs to be persistent
         upon reboot or restart of a device."
    REFERENCE
        "802.1ag clause 12.14.3.1.3:e"
    DEFVAL { sendIdNone }
    ::= { cdot1agDefaultMd 3 }

cdot1agDefaultMdTable OBJECT-TYPE
    SYNTAX SEQUENCE OF Cdot1agDefaultMdEntry
    ACCESS not-accessible
    STATUS mandatory
    DESCRIPTION
        "The Default MD Level Managed Object controls MHF creation for
         VIDs that are not attached to a specific Maintenance
         Association Managed Object, and Sender ID TLV transmission by
         those MHFs.
        
         For each Bridge Port, and for each VLAN ID whose data can
         pass through that Bridge Port, an entry in this table is
         used by the algorithm in subclause 22.2.3 only if there is no
         entry in the Maintenance Association table defining an MA
         for the same VLAN ID and MD Level as this table's entry, and
         on which MA an Up MEP is defined.  If there exists such an
         MA, that MA's objects are used by the algorithm in
         subclause 22.2.3 in place of this table entry's objects.  The
         agent maintains the value of cdot1agDefaultMdStatus to
         indicate whether this entry is overridden by an MA.
        
         When first initialized, the agent creates this table
         automatically with entries for all VLAN IDs,
         with the default values specified for each object.
        
         After this initialization, the writable objects in this
         table need to be persistent upon reboot or restart of a
         device."
    REFERENCE
        "802.1ag clause 12.14.3"
    ::= { cdot1agDefaultMd 4 }

cdot1agDefaultMdEntry OBJECT-TYPE
    SYNTAX Cdot1agDefaultMdEntry
    ACCESS not-accessible
    STATUS mandatory
    DESCRIPTION
        "The Default MD Level table entry."
    INDEX { cdot1agDefaultMdPrimaryVid }
    ::= { cdot1agDefaultMdTable 1 }

Cdot1agDefaultMdEntry ::= SEQUENCE {
    cdot1agDefaultMdPrimaryVid VlanId,
    cdot1agDefaultMdStatus TruthValue,
    cdot1agDefaultMdLevel Cdot1agMDLevelOrNone,
    cdot1agDefaultMdMhfCreation Cdot1agMhfCreation,
    cdot1agDefaultMdIdPermission Cdot1agIdPermission
    }

cdot1agDefaultMdPrimaryVid OBJECT-TYPE
    SYNTAX VlanId
--    Rsyntax INTEGER(1..4094)
    ACCESS not-accessible
    STATUS mandatory
    DESCRIPTION
        "The Primary VID of the VLAN to which this entry's objects
         apply"
    ::= { cdot1agDefaultMdEntry 1 }

cdot1agDefaultMdStatus OBJECT-TYPE
    SYNTAX TruthValue
--    Rsyntax INTEGER {
--        true(1),
--        false(2)
--        }
    ACCESS read-only
    STATUS mandatory
    DESCRIPTION
        "State of this Default MD Level table entry.  True if there is
         no entry in the Maintenance Association table defining an MA
         for the same VLAN ID and MD Level as this table's entry, and
         on which MA an Up MEP is defined, else false."
    REFERENCE
        "802.1ag clause 12.14.3.1.3:b"
    ::= { cdot1agDefaultMdEntry 2 }

cdot1agDefaultMdLevel OBJECT-TYPE
    SYNTAX Cdot1agMDLevelOrNone
--    Rsyntax INTEGER(-1|0..7)
    ACCESS read-write
    STATUS mandatory
    DESCRIPTION
        "A value indicating the MD Level at which MHFs are to be
         created, and Sender ID TLV transmission by those MHFs is to
         be controlled, for the VLAN to which this entry's objects
         apply.  If this object has the value -1, the MD Level for MHF
         creation for this VLAN is controlled by
         cdot1agDefaultMdDefLevel."
    REFERENCE
        "802.1ag clause 12.14.3.1.3:c, 12.14.3.2.2:b"
    DEFVAL { -1 }
    ::= { cdot1agDefaultMdEntry 3 }

cdot1agDefaultMdMhfCreation OBJECT-TYPE
    SYNTAX Cdot1agMhfCreation
--    Rsyntax INTEGER {
--        defMHFnone(1),
--        defMHFdefault(2),
--        defMHFexplicit(3),
--        defMHFdefer(4)
--        }
    ACCESS read-write
    STATUS mandatory
    DESCRIPTION
        "A value indicating if the Management entity can create MHFs
         (MIP Half Function) for this VID at this MD Level.  If this
         object has the value defMHFdefer, MHF creation for this VLAN
         is controlled by cdot1agDefaultMdDefMhfCreation.
        
         The value of this variable is meaningless if the values of
         cdot1agDefaultMdStatus is false."
    REFERENCE
        "802.1ag clause 12.14.3.1.3:d"
    DEFVAL { defMHFdefer }
    ::= { cdot1agDefaultMdEntry 4 }

cdot1agDefaultMdIdPermission OBJECT-TYPE
    SYNTAX Cdot1agIdPermission
--    Rsyntax INTEGER {
--        sendIdNone(1),
--        sendIdChassis(2),
--        sendIdManage(3),
--        sendIdChassisManage(4),
--        sendIdDefer(5)
--        }
    ACCESS read-write
    STATUS mandatory
    DESCRIPTION
        "Enumerated value indicating what, if anything, is to be
         included in the Sender ID TLV (21.5.3) transmitted by MHFs
         created by the Default Maintenance Domain.  If this object
         has the value sendIdDefer, Sender ID TLV transmission for
         this VLAN is controlled by cdot1agDefaultMdDefIdPermission.
        
         The value of this variable is meaningless if the values of
         cdot1agDefaultMdStatus is false."
    REFERENCE
        "802.1ag clause 12.14.3.1.3:e"
    DEFVAL { sendIdDefer }
    ::= { cdot1agDefaultMdEntry 5 }

cdot1agConfigErrorListTable OBJECT-TYPE
    SYNTAX SEQUENCE OF Cdot1agConfigErrorListEntry
    ACCESS not-accessible
    STATUS mandatory
    DESCRIPTION
        "The CFM Configuration Error List table provides a list of
         Interfaces and VIDs that are incorrectly configured."
    REFERENCE
        "802.1ag clause 12.14.4"
    ::= { cdot1agConfigErrorList 1 }

cdot1agConfigErrorListEntry OBJECT-TYPE
    SYNTAX Cdot1agConfigErrorListEntry
    ACCESS not-accessible
    STATUS mandatory
    DESCRIPTION
        "The Config Error List Table  entry"
    INDEX { cdot1agConfigErrorListVid, cdot1agConfigErrorListIfIndex }
    ::= { cdot1agConfigErrorListTable 1 }

Cdot1agConfigErrorListEntry ::= SEQUENCE {
    cdot1agConfigErrorListVid VlanId,
    cdot1agConfigErrorListIfIndex InterfaceIndex,
    cdot1agConfigErrorListErrorType Cdot1agConfigErrors
    }

cdot1agConfigErrorListVid OBJECT-TYPE
    SYNTAX VlanId
--    Rsyntax INTEGER(1..4094)
    ACCESS not-accessible
    STATUS mandatory
    DESCRIPTION
        "The VLAN ID of the VLAN with interfaces in error."
    REFERENCE
        "802.1ag Clause 12.14.4.1.2:a"
    ::= { cdot1agConfigErrorListEntry 1 }

cdot1agConfigErrorListIfIndex OBJECT-TYPE
    SYNTAX InterfaceIndex
--    Rsyntax INTEGER(1..2147483647)
    ACCESS not-accessible
    STATUS mandatory
    DESCRIPTION
        "This object is the IfIndex of the interface.
        
         Upon a restart of the system, the system SHALL, if necessary,
         change the value of this variable so that it indexes the
         entry in the interface table with the same value of ifAlias
         that it indexed before the system restart.  If no such
         entry exists, then the system SHALL delete any entries in
         cdot1agConfigErrorListTable indexed by that
         InterfaceIndex value."
    REFERENCE
        "802.1ag clause 12.14.4.1.2:b"
    ::= { cdot1agConfigErrorListEntry 2 }

cdot1agConfigErrorListErrorType OBJECT-TYPE
    SYNTAX Cdot1agConfigErrors
--    Rsyntax OCTET STRING(SIZE(1..2))
--         BITS are:
--           cfmLeak(0)
--           conflictingVids(1)
--           excessiveLevels(2)
--           overlappedLevels(3)
    ACCESS read-only
    STATUS mandatory
    DESCRIPTION
        "A vector of Boolean error conditions from 22.2.4, any of
         which may be true:
        
         0) CFMleak;
         1) ConflictingVids;
         2) ExcessiveLevels;
         3) OverlappedLevels."
    REFERENCE
        "802.1ag clause 12.14.4.1.3:b"
    ::= { cdot1agConfigErrorListEntry 3 }

cdot1agMdTableNextIndex OBJECT-TYPE
    SYNTAX Dot1afCfmIndexIntegerNextFree
--    Rsyntax Gauge(0..4294967295)
    ACCESS read-only
    STATUS mandatory
    DESCRIPTION
        "This object contains an unused value for cdot1agMdIndex in
         the cdot1agMdTable, or a zero to indicate that none exist."
    ::= { cdot1agMd 1 }

cdot1agMdTable OBJECT-TYPE
    SYNTAX SEQUENCE OF Cdot1agMdEntry
    ACCESS not-accessible
    STATUS mandatory
    DESCRIPTION
        "The Maintenance Domain table. Each row in the table
         represents a different Maintenance Domain.
        
         A Maintenance Domain is described in 802.1ag (3.22) as the
         network or the part of the network for which faults in
         connectivity are to be managed. The boundary of a Maintenance
         Domain is defined by a set of DSAPs, each of which can become
         a point of connectivity to a service instance."
    REFERENCE
        "802.1ag clauses 3.22 and 18.1"
    ::= { cdot1agMd 2 }

cdot1agMdEntry OBJECT-TYPE
    SYNTAX Cdot1agMdEntry
    ACCESS not-accessible
    STATUS mandatory
    DESCRIPTION
        "The Maintenance Domain table entry. This entry is not lost
         upon reboot. It is backed up by stable storage."
    INDEX { cdot1agMdIndex }
    ::= { cdot1agMdTable 1 }

Cdot1agMdEntry ::= SEQUENCE {
    cdot1agMdIndex Gauge,
    cdot1agMdFormat Cdot1agMaintDomainNameType,
    cdot1agMdName Cdot1agMaintDomainName,
    cdot1agMdMdLevel Cdot1agMDLevel,
    cdot1agMdMhfCreation Cdot1agMhfCreation,
    cdot1agMdMhfIdPermission Cdot1agIdPermission,
    cdot1agMdMaTableNextIndex Dot1afCfmIndexIntegerNextFree,
    cdot1agMdRowStatus RowStatus
    }

cdot1agMdIndex OBJECT-TYPE
    SYNTAX Gauge(1..4294967295)
    ACCESS not-accessible
    STATUS mandatory
    DESCRIPTION
        "The index to the Maintenance Domain table.
        
         cdot1agMdTableNextIndex needs to be inspected to find an
         available index for row-creation.
        
         Referential integrity is required i.e. the index needs to be
         persistent upon a reboot or restart of a device.  The index
         can never be reused for other Maintenance Domain.  The index
         value should keep increasing up to the time that they wrap
         around. This is to facilitate access control based on OID."
    ::= { cdot1agMdEntry 1 }

cdot1agMdFormat OBJECT-TYPE
    SYNTAX Cdot1agMaintDomainNameType
--    Rsyntax INTEGER {
--        none(1),
--        dnsLikeName(2),
--        macAddressAndUint(3),
--        charString(4)
--        }
    ACCESS read-write
    STATUS mandatory
    DESCRIPTION
        "The type (and thereby format) of the Maintenance Domain Name."
    REFERENCE
        "802.1ag clause 21.6.5.1"
    DEFVAL { charString }
    ::= { cdot1agMdEntry 2 }

cdot1agMdName OBJECT-TYPE
    SYNTAX Cdot1agMaintDomainName
--    Rsyntax OCTET STRING(SIZE(1..43))
    ACCESS read-write
    STATUS mandatory
    DESCRIPTION
        "The Maintenance Domain name. The type/format of this object
         is determined by the value of the cdot1agMdNameType object.
           
         Each Maintenance Domain has unique name amongst all those
         used or available to a service provider or operator.  It
         facilitates easy identification of administrative
         responsibility for each Maintenance Domain.
        
         Clause 3.24 defines a Maintenance Domain name as the
         identifier, unique over the domain for which CFM is to
         protect against accidental concatenation of Service
         Instances, of a particular Maintenance Domain."
    REFERENCE
        "802.1ag clauses 3.24, 12.14.5, and 21.6.5.3"
    DEFVAL { "DEFAULT" }
    ::= { cdot1agMdEntry 3 }

cdot1agMdMdLevel OBJECT-TYPE
    SYNTAX Cdot1agMDLevel
--    Rsyntax INTEGER(0..7)
    ACCESS read-write
    STATUS mandatory
    DESCRIPTION
        "The Maintenance Domain Level."
    REFERENCE
        "802.1ag clause 12.14.5.1.3:b"
    DEFVAL { 0 }
    ::= { cdot1agMdEntry 4 }

cdot1agMdMhfCreation OBJECT-TYPE
    SYNTAX Cdot1agMhfCreation
--    Rsyntax INTEGER {
--        defMHFnone(1),
--        defMHFdefault(2),
--        defMHFexplicit(3),
--        defMHFdefer(4)
--        }
    ACCESS read-write
    STATUS mandatory
    DESCRIPTION
        "Enumerated value indicating whether the management entity can
         create MHFs (MIP Half Function) for this Maintenance Domain."
    REFERENCE
        "802.1ag clause 12.14.5.1.3:c"
    DEFVAL { defMHFnone }
    ::= { cdot1agMdEntry 5 }

cdot1agMdMhfIdPermission OBJECT-TYPE
    SYNTAX Cdot1agIdPermission
--    Rsyntax INTEGER {
--        sendIdNone(1),
--        sendIdChassis(2),
--        sendIdManage(3),
--        sendIdChassisManage(4),
--        sendIdDefer(5)
--        }
    ACCESS read-write
    STATUS mandatory
    DESCRIPTION
        "Enumerated value indicating what, if anything, is to be
         included in the Sender ID TLV (21.5.3) transmitted by MPs
         configured in this Maintenance Domain.  Since, in this
         variable, there is no encompassing Maintenance Domain, the
         value sendIdDefer takes the meaning of sendIdChassisManage."
    REFERENCE
        "802.1ag clause 12.14.5.1.3:d"
    DEFVAL { sendIdNone }
    ::= { cdot1agMdEntry 6 }

cdot1agMdMaTableNextIndex OBJECT-TYPE
    SYNTAX Dot1afCfmIndexIntegerNextFree
--    Rsyntax Gauge(0..4294967295)
    ACCESS read-only
    STATUS mandatory
    DESCRIPTION
        "Value to be used as the index of the MA table entries for
         this Maintenance Domain when the management entity wants to
         create a new row in the MA table."
    ::= { cdot1agMdEntry 7 }

cdot1agMdRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of the row.
        
         The writable columns in a row can not be changed if the row
         is active. All columns must have a valid value before a row
         can be activated."
    ::= { cdot1agMdEntry 8 }

cdot1agMaTable OBJECT-TYPE
    SYNTAX SEQUENCE OF Cdot1agMaEntry
    ACCESS not-accessible
    STATUS mandatory
    DESCRIPTION
        "The Maintenance Association table.  Each row in the table
         represents an MA.  An MA is a set of MEPs, each configured
         with a single service instance.
        
         Creation of a Service Instance establishes a connectionless
         association among the selected DSAPs.  Configuring a
         Maintenance association End Point (MEP) at each of the
         DSAPs creates a Maintenance Association (MA) to monitor
         that connectionless connectivity.  The MA is identified by a
         Short MA Name that is unique within the Maintenance Domain
         and chosen to facilitate easy identification of the Service
         Instance.  Together, the Maintenance Domain Name and the
         Short MA Name form the Maintenance Association Identifier
         (MAID) that is carried in CFM Messages to identify
         incorrect connectivity among Service Instances.  A small
         integer, the Maintenance association End Point Identifier
         (MEPID), identifies each MEP among those configured on a
         single MA (802.1ag clauses 3.17 and 18.2).
        
         This table uses two indices, first index is the index of the
         Maintenance Domain table.
        
        The writable objects in this table need to be persistent
        upon reboot or restart of a device.
        "
    REFERENCE
        "802.1ag clause 18.2"
    ::= { cdot1agMa 1 }

cdot1agMaEntry OBJECT-TYPE
    SYNTAX Cdot1agMaEntry
    ACCESS not-accessible
    STATUS mandatory
    DESCRIPTION
        "The MA table entry."
    INDEX { cdot1agMdIndex, cdot1agMaIndex }
    ::= { cdot1agMaTable 1 }

Cdot1agMaEntry ::= SEQUENCE {
    cdot1agMaIndex Gauge,
    cdot1agMaPrimaryVlanId VlanId,
    cdot1agMaFormat Cdot1agMaintAssocNameType,
    cdot1agMaName Cdot1agMaintAssocName,
    cdot1agMaMhfCreation Cdot1agMhfCreation,
    cdot1agMaIdPermission Cdot1agIdPermission,
    cdot1agMaCcmInterval Cdot1agCcmInterval,
    cdot1agMaNumberOfVids Gauge,
    cdot1agMaRowStatus RowStatus
    }

cdot1agMaIndex OBJECT-TYPE
    SYNTAX Gauge(1..4294967295)
    ACCESS not-accessible
    STATUS mandatory
    DESCRIPTION
        "Index of the MA table cdot1agMdMaTableNextIndex needs to
         be inspected to find an available index for row-creation."
    ::= { cdot1agMaEntry 1 }

cdot1agMaPrimaryVlanId OBJECT-TYPE
    SYNTAX VlanId
--    Rsyntax INTEGER(1..4094)
    ACCESS read-write
    STATUS mandatory
    DESCRIPTION
        "The Primary VLAN ID with which the Maintenance Association is
         associated, or 0 if the MA is not attached to any VID.  If
         the MA is associated with more than one VID, the
         cdot1agVlanTable lists them."
    REFERENCE
        "802.1ag clause 12.14.6.1.3:b"
    ::= { cdot1agMaEntry 2 }

cdot1agMaFormat OBJECT-TYPE
    SYNTAX Cdot1agMaintAssocNameType
--    Rsyntax INTEGER {
--        primaryVid(1),
--        charString(2),
--        unsignedInt16(3),
--        rfc2865VpnId(4)
--        }
    ACCESS read-write
    STATUS mandatory
    DESCRIPTION
        "The type (and thereby format) of the Maintenance Association
         Name."
    REFERENCE
        "802.1ag clauses 21.6.5.4"
    ::= { cdot1agMaEntry 3 }

cdot1agMaName OBJECT-TYPE
    SYNTAX Cdot1agMaintAssocName
--    Rsyntax OCTET STRING(SIZE(1..45))
    ACCESS read-write
    STATUS mandatory
    DESCRIPTION
        "The Short Maintenance Association name. The type/format of
         this object is determined by the value of the
         cdot1agMaNameType object."
    REFERENCE
        "802.1ag clauses 21.6.5.6, and Table 21-20"
    ::= { cdot1agMaEntry 4 }

cdot1agMaMhfCreation OBJECT-TYPE
    SYNTAX Cdot1agMhfCreation
--    Rsyntax INTEGER {
--        defMHFnone(1),
--        defMHFdefault(2),
--        defMHFexplicit(3),
--        defMHFdefer(4)
--        }
    ACCESS read-write
    STATUS mandatory
    DESCRIPTION
        "Indicates if the Management entity can create MHFs (MIP Half
         Function) for this MA."
    REFERENCE
        "802.1ag clause 12.14.6.1.3:c"
    DEFVAL { defMHFdefer }
    ::= { cdot1agMaEntry 5 }

cdot1agMaIdPermission OBJECT-TYPE
    SYNTAX Cdot1agIdPermission
--    Rsyntax INTEGER {
--        sendIdNone(1),
--        sendIdChassis(2),
--        sendIdManage(3),
--        sendIdChassisManage(4),
--        sendIdDefer(5)
--        }
    ACCESS read-write
    STATUS mandatory
    DESCRIPTION
        "Enumerated value indicating what, if anything, is to be
         included in the Sender ID TLV (21.5.3) transmitted by MPs
         configured in this MA."
    REFERENCE
        "802.1ag clause 12.14.6.1.3:d"
    DEFVAL { sendIdDefer }
    ::= { cdot1agMaEntry 6 }

cdot1agMaCcmInterval OBJECT-TYPE
    SYNTAX Cdot1agCcmInterval
--    Rsyntax INTEGER {
--        ?? enum value of zero may cause problems
--        intervalInvalid(0),
--        interval300Hz(1),
--        interval10ms(2),
--        interval100ms(3),
--        interval1s(4),
--        interval10s(5),
--        interval1min(6),
--        interval10min(7)
--        }
    ACCESS read-write
    STATUS mandatory
    DESCRIPTION
        "Interval between CCM transmissions to be used by all MEPs
         in the MA."
    REFERENCE
        "802.1ag clause 12.14.6.1.3:e"
    DEFVAL { interval1s }
    ::= { cdot1agMaEntry 7 }

cdot1agMaNumberOfVids OBJECT-TYPE
    SYNTAX Gauge
    ACCESS read-write
    STATUS mandatory
    DESCRIPTION
        "The number of VIDs associated with the MA."
    REFERENCE
        "802.1ag clause 12.14.6.1.3:b"
    ::= { cdot1agMaEntry 8 }

cdot1agMaRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of the row.
        
         The writable columns in a row can not be changed if the row
         is active. All columns must have a valid value before a row
         can be activated."
    ::= { cdot1agMaEntry 9 }

cdot1agMaMepListTable OBJECT-TYPE
    SYNTAX SEQUENCE OF Cdot1agMaMepListEntry
    ACCESS not-accessible
    STATUS mandatory
    DESCRIPTION
        "List of MEPIDs (in any bridge) that belong to the same MA.
        
         Clause 12.14.6.1.3 specifies that a list of MEPIDs in all
         bridges in that MA, but since SNMP SMI does not allow to
         state in a MIB that an object in a table is an array, the 
         information has to be stored in another table with two
         indices, being the first index, the index of the table that 
         contains the list or array."
    REFERENCE
        "802.1ag clause 12.14.6.1.3:g"
    ::= { cdot1agMa 3 }

cdot1agMaMepListEntry OBJECT-TYPE
    SYNTAX Cdot1agMaMepListEntry
    ACCESS not-accessible
    STATUS mandatory
    DESCRIPTION
        "The known MEPS table entry."
    INDEX { cdot1agMdIndex, cdot1agMaIndex, cdot1agMaMepListIdentifier }
    ::= { cdot1agMaMepListTable 1 }

Cdot1agMaMepListEntry ::= SEQUENCE {
    cdot1agMaMepListIdentifier Cdot1agMepId,
    cdot1agMaMepListRowStatus RowStatus
    }

cdot1agMaMepListIdentifier OBJECT-TYPE
    SYNTAX Cdot1agMepId
--    Rsyntax Gauge(1..8191)
    ACCESS not-accessible
    STATUS mandatory
    DESCRIPTION
        "MEPID"
    REFERENCE
        "802.1ag clause 12.14.6.1.3:g"
    ::= { cdot1agMaMepListEntry 1 }

cdot1agMaMepListRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of the row. Read SNMPv2-TC (RFC1903) for an
         explanation of the possible values this object can take."
    ::= { cdot1agMaMepListEntry 2 }

cdot1agMepTable OBJECT-TYPE
    SYNTAX SEQUENCE OF Cdot1agMepEntry
    ACCESS not-accessible
    STATUS mandatory
    DESCRIPTION
        "The Maintenance Association End Point (MEP) table.
        
         Each row in the table represents a different MEP.  A MEP is
         an actively managed CFM entity, associated with a specific
         DSAP of a Service Instance, which can generate and receive
         CFM PDUs and track any responses.  It is an end point of a
         single Maintenance Association, and is an endpoint of a
         separate Maintenance Entity for each of the other MEPs in
         the same Maintenance Association (802.1ag clause 3.18).
        
         This table uses three indices. The first two indices are the
         indices of the Maintenance Domain and MA tables, the reason
         being that a MEP is always related to an MA and Maintenance
         Domain.
        
         The Transmit Loopback table.  Entries in this table are
         created/removed at the same time than entries in the MEP
         table are created/removed.
        
         The MEP table also stores all the managed objects for sending
         LBM and LTM.
        
         *LBM Managed objects
        
         LBM Managed objects in the MEP table 
         enables the management entity to initiate
         transmission of Loopback messages.  It will signal the MEP
         that it should transmit some number of Loopback messages
         and detect the detection (or lack thereof) of the
         corresponding Loopback messages.
        
         Steps to use entries in this table:
        
         1) Wait for cdot1agMepTransmitLbmStatus value to be
            'ready'.  To do this do this sequence:
            a. an SNMP GET for both SnmpSetSerialNo and
               cdot1agMepTransmitLbmStatus objects (in same SNMP
               PDU).
            b. Check if value for cdot1agMepTransmitLbmStatus is
               'ready'
               - if not, wait x seconds, go to step a above.
               - if yes, save the value of SnmpSetSerialNo and go
                 to step 2) below
         2) Change cdot1agMepTransmitLbmStatus value from 'ready' to
            'notReady' to ensure no other management entity will use
            the service. In order to not disturb a possible other NMS
            do this by sending an SNMP SET for both SnmpSetSerialNo 
            and cdot1agMepTransmitLbmStatus objects (in same SNMP
            PDU,  and make sure SNmpSetSerialNo is the first varBind).
            For the SnmpSetSerialNo varBind, use the value that you
            obtained in step 1)a.. This ensures that two cooperating
            NMSes will not step on each others toes.
         3) Setup the different data to be sent (number of messages,
            optional TLVs,...).
         4) Record the current values of cdot1agMepLbrIn,
            cdot1agMepLbrInOutOfOrder, and cdot1agMepLbrBadMsdu.
         6) Change cdot1agMepTransmitLbmStatus value from 'notReady'
            to 'transmit' to initiate transmission of Loopback
            messages.
         7) Check the value of cdot1agMepTransmitLbmResultOK to
            find out if the operation was successfully initiated or
            not.
         8) Monitor the value of cdot1agMepTransmitLbmMessages.
            When it reaches 0, the last LBM has been transmitted.
            Wait an additional 5 seconds to ensure that all LBRs have
            been returned.
         9) Compare cdot1agMepLbrIn, cdot1agMepLbrInOutOfOrder,
            and cdot1agMepLbrBadMsdu to their old values from step
            4, above, to get the results of the test.
        10) Change the cdot1agMepTransmitLbmStatus value back to
            'ready' to allow other management entities to use the
            table.
        
         *LTM Managed objects
         The LTM Managed objects in the MEP table are used in a manner
         similar to that described for LBM transmission, above.  Upon
         successfully initiating the transmission, the variables
         cdot1agMepTransmitLtmSeqNumber and
         cdot1agMepTransmitLtmEgressIdentifier return the information
         required to recover the results of the LTM from the
         cdot1agLtrTable."
    REFERENCE
        "802.1ag clauses 12.14.7 and 19.2"
    ::= { cdot1agMep 1 }

cdot1agMepEntry OBJECT-TYPE
    SYNTAX Cdot1agMepEntry
    ACCESS not-accessible
    STATUS mandatory
    DESCRIPTION
        "The MEP table entry"
    INDEX { cdot1agMdIndex, cdot1agMaIndex, cdot1agMepIdentifier }
    ::= { cdot1agMepTable 1 }

Cdot1agMepEntry ::= SEQUENCE {
    cdot1agMepIdentifier Cdot1agMepId,
    cdot1agMepIfIndex InterfaceIndexOrZero,
    cdot1agMepDirection Cdot1agMpDirection,
    cdot1agMepPrimaryVid Gauge,
    cdot1agMepActive TruthValue,
    cdot1agMepFngState Cdot1agFngState,
    cdot1agMepCciEnabled TruthValue,
    cdot1agMepCcmLtmPriority Gauge,
    cdot1agMepMacAddress MacAddress,
    cdot1agMepLowPrDef Cdot1agLowestAlarmPri,
    cdot1agMepFngAlarmTime TimeInterval,
    cdot1agMepFngResetTime TimeInterval,
    cdot1agMepHighestPrDefect Cdot1agHighestDefectPri,
    cdot1agMepDefects Cdot1agMepDefects,
    cdot1agMepErrorCcmLastFailure OCTET STRING,
    cdot1agMepXconCcmLastFailure OCTET STRING,
    cdot1agMepCcmSequenceErrors Counter,
    cdot1agMepCciSentCcms Counter,
    cdot1agMepNextLbmTransId Gauge,
    cdot1agMepLbrIn Counter,
    cdot1agMepLbrInOutOfOrder Counter,
    cdot1agMepLbrBadMsdu Counter,
    cdot1agMepLtmNextSeqNumber Gauge,
    cdot1agMepUnexpLtrIn Counter,
    cdot1agMepLbrOut Counter,
    cdot1agMepTransmitLbmStatus TruthValue,
    cdot1agMepTransmitLbmDestMacAddress MacAddress,
    cdot1agMepTransmitLbmDestMepId Cdot1agMepIdOrZero,
    cdot1agMepTransmitLbmDestIsMepId TruthValue,
    cdot1agMepTransmitLbmMessages INTEGER,
    cdot1agMepTransmitLbmDataTlv OCTET STRING,
    cdot1agMepTransmitLbmVlanPriority INTEGER,
    cdot1agMepTransmitLbmVlanDropEnable TruthValue,
    cdot1agMepTransmitLbmResultOK TruthValue,
    cdot1agMepTransmitLbmSeqNumber Gauge,
    cdot1agMepTransmitLtmStatus TruthValue,
    cdot1agMepTransmitLtmFlags OCTET STRING,
    cdot1agMepTransmitLtmTargetMacAddress MacAddress,
    cdot1agMepTransmitLtmTargetMepId Cdot1agMepIdOrZero,
    cdot1agMepTransmitLtmTargetIsMepId TruthValue,
    cdot1agMepTransmitLtmTtl Gauge,
    cdot1agMepTransmitLtmResult TruthValue,
    cdot1agMepTransmitLtmSeqNumber Gauge,
    cdot1agMepTransmitLtmEgressIdentifier OCTET STRING,
    cdot1agMepRowStatus RowStatus
    }

cdot1agMepIdentifier OBJECT-TYPE
    SYNTAX Cdot1agMepId
--    Rsyntax Gauge(1..8191)
    ACCESS not-accessible
    STATUS mandatory
    DESCRIPTION
        "Integer that is unique among all the MEPs in the same MA.
         Other definition is: a small integer, unique over a given
         Maintenance Association, identifying a specific Maintenance
         association End Point (3.19).
        
         MEP Identifier is also known as the MEPID."
    REFERENCE
        "802.1ag clauses 3.19, 19.2 and 12.14.7"
    ::= { cdot1agMepEntry 1 }

cdot1agMepIfIndex OBJECT-TYPE
    SYNTAX InterfaceIndexOrZero
--    Rsyntax INTEGER(0..2147483647)
    ACCESS read-write
    STATUS mandatory
    DESCRIPTION
        "This object is the interface index of the interface either a
         bridge port, or an aggregated IEEE 802.1 link within a bridge
         port, to which the MEP is attached.
        
         Upon a restart of the system, the system SHALL, if necessary,
         change the value of this variable so that it indexes the
         entry in the interface table with the same value of ifAlias
         that it indexed before the system restart.  If no such
         entry exists, then the system SHALL set this variable to 0."
    REFERENCE
        "802.1ag clause 12.14.7.1.3:b"
    ::= { cdot1agMepEntry 2 }

cdot1agMepDirection OBJECT-TYPE
    SYNTAX Cdot1agMpDirection
--    Rsyntax INTEGER {
--        down(1),
--        up(2)
--        }
    ACCESS read-write
    STATUS mandatory
    DESCRIPTION
        "The direction in which the MEP faces on the Bridge port."
    REFERENCE
        "802.1ag clauses 12.14.7.1.3:c and 19.2"
    ::= { cdot1agMepEntry 3 }

cdot1agMepPrimaryVid OBJECT-TYPE
    SYNTAX Gauge(0..16777215)
    ACCESS read-write
    STATUS mandatory
    DESCRIPTION
        "An integer indicating the Primary VID of the MEP, always
         one of the VIDs assigned to the MEP's MA.  The value 0
         indicates that either the Primary VID is that of the
         MEP's MA, or that the MEP's MA is associated with no VID."
    REFERENCE
        "802.1ag clauses 12.14.7.1.3:d"
    DEFVAL { 0 }
    ::= { cdot1agMepEntry 4 }

cdot1agMepActive OBJECT-TYPE
    SYNTAX TruthValue
--    Rsyntax INTEGER {
--        true(1),
--        false(2)
--        }
    ACCESS read-write
    STATUS mandatory
    DESCRIPTION
        "Administrative state of the MEP
        
         A Boolean indicating the administrative state of the MEP.
        
         True indicates that the MEP is to function normally, and
         false that it is to cease functioning."
    REFERENCE
        "802.1ag clauses 12.14.7.1.3:e and 20.9.1"
    DEFVAL { false }
    ::= { cdot1agMepEntry 5 }

cdot1agMepFngState OBJECT-TYPE
    SYNTAX Cdot1agFngState
--    Rsyntax INTEGER {
--        fngReset(1),
--        fngDefect(2),
--        fngReportDefect(3),
--        fngDefectReported(4),
--        fngDefectClearing(5)
--        }
    ACCESS read-only
    STATUS mandatory
    DESCRIPTION
        "Current state of the MEP Fault Notification Generator
         State Machine."
    REFERENCE
        "802.1ag clauses 12.14.7.1.3:f and 20.35"
    DEFVAL { fngReset }
    ::= { cdot1agMepEntry 6 }

cdot1agMepCciEnabled OBJECT-TYPE
    SYNTAX TruthValue
--    Rsyntax INTEGER {
--        true(1),
--        false(2)
--        }
    ACCESS read-write
    STATUS mandatory
    DESCRIPTION
        "If set to true, the MEP will generate CCM messages."
    REFERENCE
        "802.1ag clauses 12.14.7.1.3:g and 20.10.1"
    DEFVAL { false }
    ::= { cdot1agMepEntry 7 }

cdot1agMepCcmLtmPriority OBJECT-TYPE
    SYNTAX Gauge(0..7)
    ACCESS read-write
    STATUS mandatory
    DESCRIPTION
        "The priority value for CCMs and LTMs transmitted by the MEP.
         Default Value in the highest priority value allowed to pass
         through the bridge port for any of this MEPs VIDs.
         The management entity can obtain the default value for this 
         variable from the priority regeneration table by extracting the 
         highest priority value in this table on this MEPs bridge port.
         (1 is lowest, then 2, then 0, then 3-7)."
    REFERENCE
        "802.1ag clause 12.14.7.1.3:h"
    ::= { cdot1agMepEntry 8 }

cdot1agMepMacAddress OBJECT-TYPE
    SYNTAX MacAddress
--    Rsyntax OCTET STRING(SIZE(6))
    ACCESS read-only
    STATUS mandatory
    DESCRIPTION
        "MAC address of the MEP."
    REFERENCE
        "802.1ag clause 12.14.7.1.3:i and 19.4"
    ::= { cdot1agMepEntry 9 }

cdot1agMepLowPrDef OBJECT-TYPE
    SYNTAX Cdot1agLowestAlarmPri
--    Rsyntax INTEGER {
--        allDef(1),
--        macRemErrXcon(2),
--        remErrXcon(3),
--        errXcon(4),
--        xcon(5),
--        noXcon(6)
--        }
    ACCESS read-write
    STATUS mandatory
    DESCRIPTION
        "An integer value specifying the lowest priority defect 
         that is allowed to generate fault alarm."
    REFERENCE
        "802.1ag clause 12.14.7.1.3:k and 20.9.5 and Table 20-1"
    DEFVAL { macRemErrXcon }
    ::= { cdot1agMepEntry 10 }

cdot1agMepFngAlarmTime OBJECT-TYPE
    SYNTAX TimeInterval(250..1000)
--    Rsyntax INTEGER(250..1000)
    ACCESS read-write
    STATUS mandatory
    DESCRIPTION
        "The time that defects must be present before a Fault Alarm is
         issued (fngAlarmTime. 20.33.3) (default 2.5s)."
    REFERENCE
        "802.1ag clauses 12.14.7.1.3:l and 20.33.3"
    DEFVAL { 250 }
    ::= { cdot1agMepEntry 11 }

cdot1agMepFngResetTime OBJECT-TYPE
    SYNTAX TimeInterval(250..1000)
--    Rsyntax INTEGER(250..1000)
    ACCESS read-write
    STATUS mandatory
    DESCRIPTION
        "The time that defects must be absent before re-enabling a
         Fault Alarm (fngResetTime, 20.33.4) (default 10s)."
    REFERENCE
        "802.1ag clauses 12.14.7.1.3:m and 20.33.4"
    DEFVAL { 1000 }
    ::= { cdot1agMepEntry 12 }

cdot1agMepHighestPrDefect OBJECT-TYPE
    SYNTAX Cdot1agHighestDefectPri
--    Rsyntax INTEGER {
--        ?? enum value of zero may cause problems
--        none(0),
--        defRDICCM(1),
--        defMACstatus(2),
--        defRemoteCCM(3),
--        defErrorCCM(4),
--        defXconCCM(5)
--        }
    ACCESS read-only
    STATUS mandatory
    DESCRIPTION
        "The highest priority defect that has been present since the
         MEPs Fault Notification Generator State Machine was last in
         the FNG_RESET state."
    REFERENCE
        "802.1ag clause 12.14.7.1.3:n  20.33.9 and Table 21-1"
    ::= { cdot1agMepEntry 13 }

cdot1agMepDefects OBJECT-TYPE
    SYNTAX Cdot1agMepDefects
--    Rsyntax OCTET STRING(SIZE(1..2))
--         BITS are:
--           bDefRDICCM(0)
--           bDefMACstatus(1)
--           bDefRemoteCCM(2)
--           bDefErrorCCM(3)
--           bDefXconCCM(4)
    ACCESS read-only
    STATUS mandatory
    DESCRIPTION
        "A vector of Boolean error conditions from Table 20-1, any of
         which may be true:
        
         DefRDICCM(0)
         DefMACstatus(1)
         DefRemoteCCM(2)
         DefErrorCCM(3)
         DefXconCCM(4)"
    REFERENCE
        ".1ag clauses 12.14.7.1.3:o, 12.14.7.1.3:p, 12.14.7.1.3:q,
         12.14.7.1.3:r, 12.14.7.1.3:s, 20.21.3, 20.23.3, 20.33.5,
         20.33.6, 20.33.7."
    ::= { cdot1agMepEntry 14 }

cdot1agMepErrorCcmLastFailure OBJECT-TYPE
    SYNTAX OCTET STRING(SIZE(1..1522))
    ACCESS read-only
    STATUS mandatory
    DESCRIPTION
        "The last-received CCM that triggered an DefErrorCCM fault."
    REFERENCE
        "802.1ag clauses 12.14.7.1.3:t and 20.21.2"
    ::= { cdot1agMepEntry 15 }

cdot1agMepXconCcmLastFailure OBJECT-TYPE
    SYNTAX OCTET STRING(SIZE(1..1522))
    ACCESS read-only
    STATUS mandatory
    DESCRIPTION
        "The last-received CCM that triggered a DefXconCCM fault."
    REFERENCE
        "802.1ag clauses 12.14.7.1.3:u and 20.23.2"
    ::= { cdot1agMepEntry 16 }

cdot1agMepCcmSequenceErrors OBJECT-TYPE
    SYNTAX Counter
    ACCESS read-only
    STATUS mandatory
    DESCRIPTION
        "The total number of out-of-sequence CCMs received from all
         remote MEPs."
    REFERENCE
        "802.1ag clauses 12.14.7.1.3:v and 20.16.12"
    ::= { cdot1agMepEntry 17 }

cdot1agMepCciSentCcms OBJECT-TYPE
    SYNTAX Counter
    ACCESS read-only
    STATUS mandatory
    DESCRIPTION
        "Total number of Continuity Check messages transmitted."
    REFERENCE
        "802.1ag clauses 12.14.7.1.3:w and 20.10.2"
    ::= { cdot1agMepEntry 18 }

cdot1agMepNextLbmTransId OBJECT-TYPE
    SYNTAX Gauge
    ACCESS read-only
    STATUS mandatory
    DESCRIPTION
        "Next sequence number/transaction identifier to be sent in a
         Loopback message. This sequence number can be zero because
         it wraps around."
    REFERENCE
        "802.1ag clauses 12.14.7.1.3:x and 20.28.2"
    ::= { cdot1agMepEntry 19 }

cdot1agMepLbrIn OBJECT-TYPE
    SYNTAX Counter
    ACCESS read-only
    STATUS mandatory
    DESCRIPTION
        "Total number of valid, in-order Loopback Replies received."
    REFERENCE
        "802.1ag clause 12.14.7.1.3:y and 20.31.1"
    ::= { cdot1agMepEntry 20 }

cdot1agMepLbrInOutOfOrder OBJECT-TYPE
    SYNTAX Counter
    ACCESS read-only
    STATUS mandatory
    DESCRIPTION
        "The total number of valid, out-of-order Loopback Replies
         received."
    REFERENCE
        "802.1ag clause 12.14.7.1.3:z and 20.31.1"
    ::= { cdot1agMepEntry 21 }

cdot1agMepLbrBadMsdu OBJECT-TYPE
    SYNTAX Counter
    ACCESS read-only
    STATUS mandatory
    DESCRIPTION
        "(optional) The total number of LBRs received whose
         mac_service_data_unit did not match (except for the OpCode)
         that of the corresponding LBM (20.2.3)."
    REFERENCE
        "802.1ag clause 12.14.7.1.3:aa  20.2.3"
    ::= { cdot1agMepEntry 22 }

cdot1agMepLtmNextSeqNumber OBJECT-TYPE
    SYNTAX Gauge
    ACCESS read-only
    STATUS mandatory
    DESCRIPTION
        "Next transaction identifier/sequence number to be sent in a
         Linktrace message. This sequence number can be zero because
         it wraps around."
    REFERENCE
        "802.1ag clause 12.14.7.1.3:ab and 20.36.1"
    ::= { cdot1agMepEntry 23 }

cdot1agMepUnexpLtrIn OBJECT-TYPE
    SYNTAX Counter
    ACCESS read-only
    STATUS mandatory
    DESCRIPTION
        "The total number of unexpected LTRs received (20.39.1)."
    REFERENCE
        "802.1ag clause 12.14.7.1.3:ac  20.39.1"
    ::= { cdot1agMepEntry 24 }

cdot1agMepLbrOut OBJECT-TYPE
    SYNTAX Counter
    ACCESS read-only
    STATUS mandatory
    DESCRIPTION
        "Total number of Loopback Replies transmitted."
    REFERENCE
        "802.1ag clause 12.14.7.1.3:ad and 20.26.2"
    ::= { cdot1agMepEntry 25 }

cdot1agMepTransmitLbmStatus OBJECT-TYPE
    SYNTAX TruthValue
--    Rsyntax INTEGER {
--        true(1),
--        false(2)
--        }
    ACCESS read-write
    STATUS mandatory
    DESCRIPTION
        "A Boolean flag set to true by the bridge port to indicate
         that another LBM may be transmitted. 
         Reset to false by the MEP Loopback Initiator State Machine."
    DEFVAL { true }
    ::= { cdot1agMepEntry 26 }

cdot1agMepTransmitLbmDestMacAddress OBJECT-TYPE
    SYNTAX MacAddress
--    Rsyntax OCTET STRING(SIZE(6))
    ACCESS read-write
    STATUS mandatory
    DESCRIPTION
        "The Target MAC Address Field to be transmitted: A unicast
         destination MAC address.
         This address will be used if the value of the column
         cdot1agMepTransmitLbmDestIsMepId is 'false'."
    REFERENCE
        "802.1ag clause 12.14.7.3.2:b"
    ::= { cdot1agMepEntry 27 }

cdot1agMepTransmitLbmDestMepId OBJECT-TYPE
    SYNTAX Cdot1agMepIdOrZero
--    Rsyntax Gauge(0|1..8191)
    ACCESS read-write
    STATUS mandatory
    DESCRIPTION
        "The Maintenance association End Point Identifier of another
         MEP in the same Maintenance Association to which the LBM is
         to be sent.
         This address will be used if the value of the column
         cdot1agMepTransmitLbmDestIsMepId is 'true'."
    REFERENCE
        "802.1ag clause 12.14.7.3.2:b"
    ::= { cdot1agMepEntry 28 }

cdot1agMepTransmitLbmDestIsMepId OBJECT-TYPE
    SYNTAX TruthValue
--    Rsyntax INTEGER {
--        true(1),
--        false(2)
--        }
    ACCESS read-write
    STATUS mandatory
    DESCRIPTION
        "True indicates that MEPID of the target MEP is used for
         Loopback transmission.
         False indicates that unicast destination MAC address of the
         target MEP is used for Loopback transmission."
    REFERENCE
        "802.1ag clause 12.14.7.3.2:b"
    ::= { cdot1agMepEntry 29 }

cdot1agMepTransmitLbmMessages OBJECT-TYPE
    SYNTAX INTEGER(1..1024)
    ACCESS read-write
    STATUS mandatory
    DESCRIPTION
        "The number of Loopback messages to be transmitted."
    REFERENCE
        "802.1ag clause 12.14.7.3.2:c"
    DEFVAL { 1 }
    ::= { cdot1agMepEntry 30 }

cdot1agMepTransmitLbmDataTlv OBJECT-TYPE
    SYNTAX OCTET STRING(SIZE(0..1500))
    ACCESS read-write
    STATUS mandatory
    DESCRIPTION
        "An arbitrary amount of data to be included in the Data TLV,
         if the Data TLV is selected to be sent."
    REFERENCE
        "802.1ag clause 12.14.7.3.2:d"
    ::= { cdot1agMepEntry 31 }

cdot1agMepTransmitLbmVlanPriority OBJECT-TYPE
    SYNTAX INTEGER(0..7)
    ACCESS read-write
    STATUS mandatory
    DESCRIPTION
        "Priority. 3 bit value to be used in the VLAN tag, if present
         in the transmitted frame.
        
         The default value is CCM priority."
    REFERENCE
        "802.1ag clause 12.14.7.3.2:e"
    ::= { cdot1agMepEntry 32 }

cdot1agMepTransmitLbmVlanDropEnable OBJECT-TYPE
    SYNTAX TruthValue
--    Rsyntax INTEGER {
--        true(1),
--        false(2)
--        }
    ACCESS read-write
    STATUS mandatory
    DESCRIPTION
        "Drop Enable bit value to be used in the VLAN tag, if present
         in the transmitted frame.
        
         For more information about VLAN Drop Enable, please check
         IEEE 802.1ad."
    REFERENCE
        "802.1ag clause 12.14.7.3.2:e"
    DEFVAL { true }
    ::= { cdot1agMepEntry 33 }

cdot1agMepTransmitLbmResultOK OBJECT-TYPE
    SYNTAX TruthValue
--    Rsyntax INTEGER {
--        true(1),
--        false(2)
--        }
    ACCESS read-only
    STATUS mandatory
    DESCRIPTION
        "Indicates the result of the operation:
        
         - true       The Loopback Message(s) will be
                      (or has been) sent.
         - false      The Loopback Message(s) will not
                      be sent."
    REFERENCE
        "802.1ag clause 12.14.7.3.3:a"
    DEFVAL { true }
    ::= { cdot1agMepEntry 34 }

cdot1agMepTransmitLbmSeqNumber OBJECT-TYPE
    SYNTAX Gauge
    ACCESS read-only
    STATUS mandatory
    DESCRIPTION
        "The Loopback Transaction Identifier
        (cdot1agMepNextLbmTransId) of the first LBM (to be) sent.
         The value returned is undefined if
         cdot1agMepTransmitLbmResultOK is false."
    REFERENCE
        "802.1ag clause 12.14.7.3.3:a"
    ::= { cdot1agMepEntry 35 }

cdot1agMepTransmitLtmStatus OBJECT-TYPE
    SYNTAX TruthValue
--    Rsyntax INTEGER {
--        true(1),
--        false(2)
--        }
    ACCESS read-only
    STATUS mandatory
    DESCRIPTION
        "A Boolean flag set to true by the bridge port to indicate
         that another LTM may be transmitted. 
         Reset to false by the MEP Linktrace Initiator State Machine."
    DEFVAL { true }
    ::= { cdot1agMepEntry 36 }

cdot1agMepTransmitLtmFlags OBJECT-TYPE
    SYNTAX OCTET STRING(SIZE(1..2))
        -- BITS are:
        --   useFDBonly(0)
    ACCESS read-write
    STATUS mandatory
    DESCRIPTION
        "The flags field for LTMs transmitted by the MEP."
    REFERENCE
        "802.1ag clause 12.14.7.4.2:b and 20.37.1"
    DEFVAL { '80'h }
    ::= { cdot1agMepEntry 37 }

cdot1agMepTransmitLtmTargetMacAddress OBJECT-TYPE
    SYNTAX MacAddress
--    Rsyntax OCTET STRING(SIZE(6))
    ACCESS read-write
    STATUS mandatory
    DESCRIPTION
        "The Target MAC Address Field to be transmitted: A unicast
         destination MAC address.
         This address will be used if the value of the column
         cdot1agMepTransmitLtmTargetIsMepId is 'false'."
    REFERENCE
        "802.1ag clause 12.14.7.4.2:c"
    ::= { cdot1agMepEntry 38 }

cdot1agMepTransmitLtmTargetMepId OBJECT-TYPE
    SYNTAX Cdot1agMepIdOrZero
--    Rsyntax Gauge(0|1..8191)
    ACCESS read-write
    STATUS mandatory
    DESCRIPTION
        "An indication of the Target MAC Address Field to be
         transmitted:
         The Maintenance association End Point Identifier of
         another MEP in the same Maintenance Association
         This address will be used if the value of the column
         cdot1agMepTransmitLtmTargetIsMepId is 'true'."
    REFERENCE
        "802.1ag clause 12.14.7.4.2:c"
    ::= { cdot1agMepEntry 39 }

cdot1agMepTransmitLtmTargetIsMepId OBJECT-TYPE
    SYNTAX TruthValue
--    Rsyntax INTEGER {
--        true(1),
--        false(2)
--        }
    ACCESS read-write
    STATUS mandatory
    DESCRIPTION
        "True indicates that MEPID of the target MEP is used for
         Linktrace transmission.
         False indicates that unicast destination MAC address of the
         target MEP is used for Loopback transmission."
    REFERENCE
        "802.1ag clause 12.14.7.4.2:c"
    ::= { cdot1agMepEntry 40 }

cdot1agMepTransmitLtmTtl OBJECT-TYPE
    SYNTAX Gauge(0..255)
    ACCESS read-write
    STATUS mandatory
    DESCRIPTION
        "The LTM TTL field. Default value, if not specified, is 64.
         The TTL field indicates the number of hops remaining to the
         LTM.  Decremented by 1 by each Linktrace Responder that
         handles the LTM.  The value received in the LTM is returned
         in the LTR.  If 0 on input, the LTM is not transmitted to the
         next hop."
    REFERENCE
        "802.1ag clause 12.14.7.4.2:d and 21.8.4"
    DEFVAL { 64 }
    ::= { cdot1agMepEntry 41 }

cdot1agMepTransmitLtmResult OBJECT-TYPE
    SYNTAX TruthValue
--    Rsyntax INTEGER {
--        true(1),
--        false(2)
--        }
    ACCESS read-only
    STATUS mandatory
    DESCRIPTION
        "Indicates the result of the operation:
        
         - true    The Linktrace Message will be (or has been) sent.
         - false   The Linktrace Message will not be sent"
    REFERENCE
        "802.1ag clause 12.14.7.4.3:a"
    DEFVAL { true }
    ::= { cdot1agMepEntry 42 }

cdot1agMepTransmitLtmSeqNumber OBJECT-TYPE
    SYNTAX Gauge
    ACCESS read-only
    STATUS mandatory
    DESCRIPTION
        "The LTM Transaction Identifier
         (cdot1agMepLtmNextSeqNumber) of the LTM sent.
         The value returned is undefined if
         cdot1agMepTransmitLtmResult is false."
    REFERENCE
        "802.1ag clause 12.14.7.4.3:a"
    ::= { cdot1agMepEntry 43 }

cdot1agMepTransmitLtmEgressIdentifier OBJECT-TYPE
    SYNTAX OCTET STRING(SIZE(8))
    ACCESS read-write
    STATUS mandatory
    DESCRIPTION
        "Identifies the MEP Linktrace Initiator that is originating,
         or the Linktrace Responder that is forwarding, this LTM.
         The low-order six octets contain a 48-bit IEEE MAC address
         unique to the system in which the MEP Linktrace Initiator
         or Linktrace Responder resides.  The high-order two octets
         contain a value sufficient to uniquely identify the MEP
         Linktrace Initiator or Linktrace Responder within that system.
        
         For most Bridges, the address of any MAC attached to the
         Bridge will suffice for the low-order six octets, and 0 for
         the high-order octets.  In some situations, e.g. if multiple
         virtual Bridges utilizing emulated LANs are implemented in a
         single physical system, the high-order two octets can be used
         to differentiate among the transmitting entities.
        
         The value returned is undefined if
         cdot1agMepTransmitLtmResult is false."
    REFERENCE
        "802.1ag clause 12.14.7.4.3:b and 21.8.8"
    ::= { cdot1agMepEntry 44 }

cdot1agMepRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of the row.
        
         The writable columns in a row can not be changed if the row
         is active. All columns must have a valid value before a row
         can be activated."
    ::= { cdot1agMepEntry 45 }

cdot1agLtrTable OBJECT-TYPE
    SYNTAX SEQUENCE OF Cdot1agLtrEntry
    ACCESS not-accessible
    STATUS mandatory
    DESCRIPTION
        "This table extends the MEP table and contains a list of
         Linktrace replies received by a specific MEP in response to
         a linktrace message.
        
         SNMP SMI does not allow to state in a MIB that an object in
         a table is an array.  The solution is to take the index (or
         indices) of the first table and add one or more indices."
    REFERENCE
        "802.1ag clause 12.14.7.5"
    ::= { cdot1agMep 2 }

cdot1agLtrEntry OBJECT-TYPE
    SYNTAX Cdot1agLtrEntry
    ACCESS not-accessible
    STATUS mandatory
    DESCRIPTION
        "The Linktrace Reply table entry."
    INDEX { cdot1agMdIndex, cdot1agMaIndex, cdot1agMepIdentifier, cdot1agLtrSeqNumber, cdot1agLtrReceiveOrder }
    ::= { cdot1agLtrTable 1 }

Cdot1agLtrEntry ::= SEQUENCE {
    cdot1agLtrSeqNumber Gauge,
    cdot1agLtrReceiveOrder Gauge,
    cdot1agLtrTtl Gauge,
    cdot1agLtrForwarded TruthValue,
    cdot1agLtrTerminalMep TruthValue,
    cdot1agLtrLastEgressIdentifier OCTET STRING,
    cdot1agLtrNextEgressIdentifier OCTET STRING,
    cdot1agLtrRelay Cdot1agRelayActionFieldValue,
    cdot1agLtrChassisIdSubtype ClldpChassisIdSubtype,
    cdot1agLtrChassisId ClldpChassisId,
    cdot1agLtrManAddressDomain TDomain,
    cdot1agLtrManAddress TAddress,
    cdot1agLtrIngress Cdot1agIngressActionFieldValue,
    cdot1agLtrIngressMac MacAddress,
    cdot1agLtrIngressPortIdSubtype ClldpPortIdSubtype,
    cdot1agLtrIngressPortId ClldpPortId,
    cdot1agLtrEgress Cdot1agEgressActionFieldValue,
    cdot1agLtrEgressMac MacAddress,
    cdot1agLtrEgressPortIdSubtype ClldpPortIdSubtype,
    cdot1agLtrEgressPortId ClldpPortId,
    cdot1agLtrOrganizationSpecificTlv OCTET STRING
    }

cdot1agLtrSeqNumber OBJECT-TYPE
    SYNTAX Gauge(0..4294967295)
    ACCESS not-accessible
    STATUS mandatory
    DESCRIPTION
        "Transaction identifier/Sequence number returned by a previous
         transmit linktrace message command, indicating which LTM's
         response is going to be returned."
    REFERENCE
        "802.1ag clause 12.14.7.5.2:b"
    ::= { cdot1agLtrEntry 1 }

cdot1agLtrReceiveOrder OBJECT-TYPE
    SYNTAX Gauge(1..4294967295)
    ACCESS not-accessible
    STATUS mandatory
    DESCRIPTION
        "An index to distinguish among multiple LTRs with the same LTR
         Transaction Identifier field value.  cdot1agLtrReceiveOrder
         are assigned sequentially from 1, in the order that the
         Linktrace Initiator received the LTRs."
    REFERENCE
        "802.1ag clause 12.14.7.5.2:c"
    ::= { cdot1agLtrEntry 2 }

cdot1agLtrTtl OBJECT-TYPE
    SYNTAX Gauge(0..255)
    ACCESS read-only
    STATUS mandatory
    DESCRIPTION
        "TTL field value for a returned LTR."
    REFERENCE
        "802.1ag clause 12.14.7.5 and 20.36.2.2"
    ::= { cdot1agLtrEntry 3 }

cdot1agLtrForwarded OBJECT-TYPE
    SYNTAX TruthValue
--    Rsyntax INTEGER {
--        true(1),
--        false(2)
--        }
    ACCESS read-only
    STATUS mandatory
    DESCRIPTION
        "Indicates if a LTM was forwarded by the responding MP, as
         returned in the 'FwdYes' flag of the flags field."
    REFERENCE
        "802.1ag clauses 12.14.7.5.3:c and 20.36.2.1"
    ::= { cdot1agLtrEntry 4 }

cdot1agLtrTerminalMep OBJECT-TYPE
    SYNTAX TruthValue
--    Rsyntax INTEGER {
--        true(1),
--        false(2)
--        }
    ACCESS read-only
    STATUS mandatory
    DESCRIPTION
        "A boolean value stating whether the forwarded LTM reached a
         MEP enclosing its MA, as returned in the Terminal MEP flag of
         the Flags field."
    REFERENCE
        "802.1ag clauses 12.14.7.5.3:d and 20.36.2.1"
    ::= { cdot1agLtrEntry 5 }

cdot1agLtrLastEgressIdentifier OBJECT-TYPE
    SYNTAX OCTET STRING(SIZE(8))
    ACCESS read-only
    STATUS mandatory
    DESCRIPTION
        "An octet field holding the Last Egress Identifier returned
         in the LTR Egress Identifier TLV of the LTR.
         The Last Egress Identifier identifies the MEP Linktrace 
         Initiator that originated, or the Linktrace Responder that 
         forwarded, the LTM to which this LTR is the response.  This
         is the same value as the Egress Identifier TLV of that LTM."
    REFERENCE
        "802.1ag clauses 12.14.7.5.3:e and 20.36.2.3"
    ::= { cdot1agLtrEntry 6 }

cdot1agLtrNextEgressIdentifier OBJECT-TYPE
    SYNTAX OCTET STRING(SIZE(8))
    ACCESS read-only
    STATUS mandatory
    DESCRIPTION
        "An octet field holding the Next Egress Identifier returned
         in the LTR Egress Identifier TLV of the LTR.  The Next Egress
         Identifier Identifies the Linktrace Responder that
         transmitted this LTR, and can forward the LTM to the next
         hop.  This is the same value as the Egress Identifier TLV of
         the forwarded LTM, if any. If the FwdYes bit of the Flags
         field is false, the contents of this field are undefined,
         i.e. any value can be transmitted, and the field is ignored
         by the receiver."
    REFERENCE
        "802.1ag clauses 12.14.7.5.3:f and 20.36.2.4"
    ::= { cdot1agLtrEntry 7 }

cdot1agLtrRelay OBJECT-TYPE
    SYNTAX Cdot1agRelayActionFieldValue
--    Rsyntax INTEGER {
--        rlyHit(1),
--        rlyFdb(2),
--        rlyMpdb(3)
--        }
    ACCESS read-only
    STATUS mandatory
    DESCRIPTION
        "Value returned in the Relay Action field."
    REFERENCE
        "802.1ag clauses 12.14.7.5.3:g and 20.36.2.5"
    ::= { cdot1agLtrEntry 8 }

cdot1agLtrChassisIdSubtype OBJECT-TYPE
    SYNTAX ClldpChassisIdSubtype
--    Rsyntax INTEGER {
--        chassisComponent(1),
--        interfaceAlias(2),
--        portComponent(3),
--        macAddress(4),
--        networkAddress(5),
--        interfaceName(6),
--        local(7)
--        }
    ACCESS read-only
    STATUS mandatory
    DESCRIPTION
        "This object specifies the format of the Chassis ID returned
         in the Sender ID TLV of the LTR, if any.  This value is
         meaningless if the cdot1agLtrChassisId has a length of 0."
    REFERENCE
        "802.1ag clauses 12.14.7.5.3:h and 21.5.3.2"
    ::= { cdot1agLtrEntry 9 }

cdot1agLtrChassisId OBJECT-TYPE
    SYNTAX ClldpChassisId
--    Rsyntax OCTET STRING(SIZE(1..255))
    ACCESS read-only
    STATUS mandatory
    DESCRIPTION
        "The Chassis ID returned in the Sender ID TLV of the LTR, if
         any. The format of this object is determined by the
         value of the cdot1agLtrChassisIdSubtype object."
    REFERENCE
        "802.1ag clauses 12.14.7.5.3:i and 21.5.3.3"
    ::= { cdot1agLtrEntry 10 }

cdot1agLtrManAddressDomain OBJECT-TYPE
    SYNTAX TDomain
--    Rsyntax OBJECT IDENTIFIER
    ACCESS read-only
    STATUS mandatory
    DESCRIPTION
        "The TDomain that identifies the type and format of
         the related cdot1agMepDbManAddress object, used to access
         the SNMP agent of the system transmitting the LTR.  Received
         in the LTR Sender ID TLV from that system.
        
         Typical values will be one of (not all inclusive) list:
        
        
            snmpUDPDomain          (from SNMPv2-TM, RFC3417)
            snmpIeee802Domain      (from SNMP-IEEE802-TM-MIB, RFC4789)
        
         The value 'zeroDotZero' (from RFC2578) indicates 'no LTR
         Sender ID TLV received', in which case the related object
         cdot1agMepDbManAddress must have a zero-length OCTET STRING
         as a value."
    REFERENCE
        "802.1ag clauses 12.14.7.5.3:j, 21.5.3.5, 21.9.6"
    ::= { cdot1agLtrEntry 11 }

cdot1agLtrManAddress OBJECT-TYPE
    SYNTAX TAddress
--    Rsyntax OCTET STRING(SIZE(1..255))
    ACCESS read-only
    STATUS mandatory
    DESCRIPTION
        "The TAddress that can be used to access the SNMP
         agent of the system transmitting the CCM, received in the CCM
         Sender ID TLV from that system.
        
         If the related object cdot1agLtrManAddressDomain contains
         the value 'zeroDotZero', this object cdot1agLtrManAddress
         must have a zero-length OCTET STRING as a value."
    REFERENCE
        "802.1ag clauses 12.14.7.5.3:j, 21.5.3.7, 21.9.6"
    ::= { cdot1agLtrEntry 12 }

cdot1agLtrIngress OBJECT-TYPE
    SYNTAX Cdot1agIngressActionFieldValue
--    Rsyntax INTEGER {
--        ingOk(1),
--        ingDown(2),
--        ingBlocked(3),
--        ingVid(4)
--        }
    ACCESS read-only
    STATUS mandatory
    DESCRIPTION
        "The value returned in the Ingress Action Field of the LTM."
    REFERENCE
        "802.1ag clauses 12.14.7.5.3:k and 20.36.2.6"
    ::= { cdot1agLtrEntry 13 }

cdot1agLtrIngressMac OBJECT-TYPE
    SYNTAX MacAddress
--    Rsyntax OCTET STRING(SIZE(6))
    ACCESS read-only
    STATUS mandatory
    DESCRIPTION
        "MAC address returned in the ingress MAC address field."
    REFERENCE
        "802.1ag clauses 12.14.7.5.3:l and 20.36.2.7"
    ::= { cdot1agLtrEntry 14 }

cdot1agLtrIngressPortIdSubtype OBJECT-TYPE
    SYNTAX ClldpPortIdSubtype
--    Rsyntax INTEGER {
--        interfaceAlias(1),
--        portComponent(2),
--        macAddress(3),
--        networkAddress(4),
--        interfaceName(5),
--        agentCircuitId(6),
--        local(7)
--        }
    ACCESS read-only
    STATUS mandatory
    DESCRIPTION
        "Format of the Ingress Port ID."
    REFERENCE
        "802.1ag clauses 12.14.7.5.3:m and 20.36.2.8"
    ::= { cdot1agLtrEntry 15 }

cdot1agLtrIngressPortId OBJECT-TYPE
    SYNTAX ClldpPortId
--    Rsyntax OCTET STRING(SIZE(1..255))
    ACCESS read-only
    STATUS mandatory
    DESCRIPTION
        "Ingress Port ID. The format of this object is determined by
         the value of the cdot1agLtrIngressPortIdSubtype object."
    REFERENCE
        "802.1ag clauses 12.14.7.5.3:n and 20.36.2.9"
    ::= { cdot1agLtrEntry 16 }

cdot1agLtrEgress OBJECT-TYPE
    SYNTAX Cdot1agEgressActionFieldValue
--    Rsyntax INTEGER {
--        egrOK(1),
--        egrDown(2),
--        egrBlocked(3),
--        egrVid(4)
--        }
    ACCESS read-only
    STATUS mandatory
    DESCRIPTION
        "The value returned in the Egress Action Field of the LTM."
    REFERENCE
        "802.1ag clauses 12.14.7.5.3:o and 20.36.2.10"
    ::= { cdot1agLtrEntry 17 }

cdot1agLtrEgressMac OBJECT-TYPE
    SYNTAX MacAddress
--    Rsyntax OCTET STRING(SIZE(6))
    ACCESS read-only
    STATUS mandatory
    DESCRIPTION
        "MAC address returned in the egress MAC address field."
    REFERENCE
        "802.1ag clauses 12.14.7.5.3:p and 20.36.2.11"
    ::= { cdot1agLtrEntry 18 }

cdot1agLtrEgressPortIdSubtype OBJECT-TYPE
    SYNTAX ClldpPortIdSubtype
--    Rsyntax INTEGER {
--        interfaceAlias(1),
--        portComponent(2),
--        macAddress(3),
--        networkAddress(4),
--        interfaceName(5),
--        agentCircuitId(6),
--        local(7)
--        }
    ACCESS read-only
    STATUS mandatory
    DESCRIPTION
        "Format of the egress Port ID."
    REFERENCE
        "802.1ag clauses 12.14.7.5.3:q and 20.36.2.12"
    ::= { cdot1agLtrEntry 19 }

cdot1agLtrEgressPortId OBJECT-TYPE
    SYNTAX ClldpPortId
--    Rsyntax OCTET STRING(SIZE(1..255))
    ACCESS read-only
    STATUS mandatory
    DESCRIPTION
        "Egress Port ID. The format of this object is determined by
         the value of the cdot1agLtrEgressPortIdSubtype object."
    REFERENCE
        "802.1ag clauses 12.14.7.5.3:r and 20.36.2.13"
    ::= { cdot1agLtrEntry 20 }

cdot1agLtrOrganizationSpecificTlv OBJECT-TYPE
    SYNTAX OCTET STRING(SIZE(0|4..1500))
    ACCESS read-only
    STATUS mandatory
    DESCRIPTION
        "All Organization specific TLVs returned in the LTR, if
         any.  Includes all octets including and following the TLV
         Length field of each TLV, concatenated together."
    REFERENCE
        "802.1ag clauses 12.14.7.5.3:s, 21.5.2"
    ::= { cdot1agLtrEntry 21 }

cdot1agMepDbTable OBJECT-TYPE
    SYNTAX SEQUENCE OF Cdot1agMepDbEntry
    ACCESS not-accessible
    STATUS mandatory
    DESCRIPTION
        "The MEP Database. A database, maintained by every MEP, that
         maintains received information about other MEPs in the
         Maintenance Domain.
        
         The SMI does not allow to state in a MIB that an object in
         a table is an array. The solution is to take the index (or
         indices) of the first table and add one or more indices."
    REFERENCE
        "802.1ag clause 19.2.15"
    ::= { cdot1agMep 3 }

cdot1agMepDbEntry OBJECT-TYPE
    SYNTAX Cdot1agMepDbEntry
    ACCESS not-accessible
    STATUS mandatory
    DESCRIPTION
        "The MEP Database table entry."
    INDEX { cdot1agMdIndex, cdot1agMaIndex, cdot1agMepIdentifier, cdot1agMepDbRMepIdentifier }
    ::= { cdot1agMepDbTable 1 }

Cdot1agMepDbEntry ::= SEQUENCE {
    cdot1agMepDbRMepIdentifier Cdot1agMepId,
    cdot1agMepDbRMepState Cdot1agRemoteMepState,
    cdot1agMepDbRMepFailedOkTime TimeStamp,
    cdot1agMepDbMacAddress MacAddress,
    cdot1agMepDbRdi TruthValue,
    cdot1agMepDbPortStatusTlv Cdot1agPortStatus,
    cdot1agMepDbInterfaceStatusTlv Cdot1agInterfaceStatus,
    cdot1agMepDbChassisIdSubtype ClldpChassisIdSubtype,
    cdot1agMepDbChassisId ClldpChassisId,
    cdot1agMepDbManAddressDomain TDomain,
    cdot1agMepDbManAddress TAddress
    }

cdot1agMepDbRMepIdentifier OBJECT-TYPE
    SYNTAX Cdot1agMepId
--    Rsyntax Gauge(1..8191)
    ACCESS not-accessible
    STATUS mandatory
    DESCRIPTION
        "Maintenance association End Point Identifier of a remote MEP
         whose information from the MEP Database is to be returned."
    REFERENCE
        "802.1ag clause 12.14.7.6.2:b"
    ::= { cdot1agMepDbEntry 1 }

cdot1agMepDbRMepState OBJECT-TYPE
    SYNTAX Cdot1agRemoteMepState
--    Rsyntax INTEGER {
--        rMepIdle(1),
--        rMepStart(2),
--        rMepFailed(3),
--        rMepOk(4)
--        }
    ACCESS read-only
    STATUS mandatory
    DESCRIPTION
        "The operational state of the remote MEP IFF State machines."
    REFERENCE
        "802.1ag clause 12.14.7.6.3:b and 20.22"
    ::= { cdot1agMepDbEntry 2 }

cdot1agMepDbRMepFailedOkTime OBJECT-TYPE
    SYNTAX TimeStamp
--    Rsyntax TimeTicks
    ACCESS read-only
    STATUS mandatory
    DESCRIPTION
        "The time (SysUpTime) at which the IFF Remote MEP state machine
         last entered either the RMEP_FAILED or RMEP_OK state."
    REFERENCE
        "802.1ag clause 12.14.7.6.3:c"
    ::= { cdot1agMepDbEntry 3 }

cdot1agMepDbMacAddress OBJECT-TYPE
    SYNTAX MacAddress
--    Rsyntax OCTET STRING(SIZE(6))
    ACCESS read-only
    STATUS mandatory
    DESCRIPTION
        "The MAC address of the remote MEP."
    REFERENCE
        "802.1ag clause 12.14.7.6.3:d and 20.19.7"
    ::= { cdot1agMepDbEntry 4 }

cdot1agMepDbRdi OBJECT-TYPE
    SYNTAX TruthValue
--    Rsyntax INTEGER {
--        true(1),
--        false(2)
--        }
    ACCESS read-only
    STATUS mandatory
    DESCRIPTION
        "State of the RDI bit in the last received CCM (true for
         RDI=1), or false if none has been received."
    REFERENCE
        "802.1ag clauses 12.14.7.6.3:e and 20.19.2"
    ::= { cdot1agMepDbEntry 5 }

cdot1agMepDbPortStatusTlv OBJECT-TYPE
    SYNTAX Cdot1agPortStatus
--    Rsyntax INTEGER {
--        ?? enum value of zero may cause problems
--        psNoPortStateTLV(0),
--        psBlocked(1),
--        psUp(2)
--        }
    ACCESS read-only
    STATUS mandatory
    DESCRIPTION
        "An enumerated value of the Port status TLV received in the
         last CCM from the remote MEP or the default value
         psNoPortStateTLV indicating either no CCM has been received,
         or that nor port status TLV was received in the last CCM."
    REFERENCE
        "802.1ag clause 12.14.7.6.3:f and 20.19.3"
    DEFVAL { psNoPortStateTLV }
    ::= { cdot1agMepDbEntry 6 }

cdot1agMepDbInterfaceStatusTlv OBJECT-TYPE
    SYNTAX Cdot1agInterfaceStatus
--    Rsyntax INTEGER {
--        ?? enum value of zero may cause problems
--        isNoInterfaceStatusTLV(0),
--        isUp(1),
--        isDown(2),
--        isTesting(3),
--        isUnknown(4),
--        isDormant(5),
--        isNotPresent(6),
--        isLowerLayerDown(7)
--        }
    ACCESS read-only
    STATUS mandatory
    DESCRIPTION
        "An enumerated value of the Interface status TLV received
         in the last CCM from the remote MEP or the default value
         isNoInterfaceStatus TLV indicating either no CCM has been
         received, or that no interface status TLV was received in
         the last CCM."
    REFERENCE
        "802.1ag clause 12.14.7.6.3:g and 20.19.4"
    DEFVAL { isNoInterfaceStatusTLV }
    ::= { cdot1agMepDbEntry 7 }

cdot1agMepDbChassisIdSubtype OBJECT-TYPE
    SYNTAX ClldpChassisIdSubtype
--    Rsyntax INTEGER {
--        chassisComponent(1),
--        interfaceAlias(2),
--        portComponent(3),
--        macAddress(4),
--        networkAddress(5),
--        interfaceName(6),
--        local(7)
--        }
    ACCESS read-only
    STATUS mandatory
    DESCRIPTION
        "This object specifies the format of the Chassis ID received
         in the last CCM."
    REFERENCE
        "802.1ag clauses 12.14.7.6.3:h and 21.5.3.2"
    ::= { cdot1agMepDbEntry 8 }

cdot1agMepDbChassisId OBJECT-TYPE
    SYNTAX ClldpChassisId
--    Rsyntax OCTET STRING(SIZE(1..255))
    ACCESS read-only
    STATUS mandatory
    DESCRIPTION
        "The Chassis ID. The format of this object is determined by the
         value of the cdot1agLtrChassisIdSubtype object."
    REFERENCE
        "802.1ag clauses 12.14.7.6.3:h and 21.5.3.3"
    ::= { cdot1agMepDbEntry 9 }

cdot1agMepDbManAddressDomain OBJECT-TYPE
    SYNTAX TDomain
--    Rsyntax OBJECT IDENTIFIER
    ACCESS read-only
    STATUS mandatory
    DESCRIPTION
        "The TDomain that identifies the type and format of
         the related cdot1agMepDbManAddress object, used to access
         the SNMP agent of the system transmitting the CCM.  Received
         in the CCM Sender ID TLV from that system.
        
         Typical values will be one of (not all inclusive) list:
        
        
            snmpUDPDomain          (from SNMPv2-TM, RFC3417)
            snmpIeee802Domain      (from SNMP-IEEE802-TM-MIB, RFC4789)
        
         The value 'zeroDotZero' (from RFC2578) indicates 'no LTR
         Sender ID TLV received', in which case the related object
         cdot1agMepDbManAddress must have a zero-length OCTET STRING
         as a value."
    REFERENCE
        "802.1ag clauses 12.14.7.6.3:h, 21.5.3.5, 21.6.7"
    ::= { cdot1agMepDbEntry 10 }

cdot1agMepDbManAddress OBJECT-TYPE
    SYNTAX TAddress
--    Rsyntax OCTET STRING(SIZE(1..255))
    ACCESS read-only
    STATUS mandatory
    DESCRIPTION
        "The TAddress that can be used to access the SNMP
         agent of the system transmitting the CCM, received in the CCM
         Sender ID TLV from that system.
        
         If the related object cdot1agMepDbManAddressDomain contains
         the value 'zeroDotZero', this object cdot1agMepDbManAddress
         must have a zero-length OCTET STRING as a value."
    REFERENCE
        "802.1ag clauses 12.14.7.6.3:h, 21.5.3.7, 21.6.7"
    ::= { cdot1agMepDbEntry 11 }

cdot1agFaultAlarm TRAP-TYPE
-- Reverse mappable trap
    ENTERPRISE cdot1CfmMIB
    VARIABLES {
        cdot1agMepHighestPrDefect }
--  Status
--    mandatory
    DESCRIPTION
        "A MEP has a persistent defect condition. A notification
         (fault alarm) is sent to the management entity with the OID
         of the MEP that has detected the fault.
        
         Whenever a MEP has a persistent defect,
         it may or may not generate a Fault Alarm to warn the system
         administrator of the problem, as controlled by the MEP
         Fault Notification Generator State Machine and associated
         Managed Objects. Only the highest-priority defect, as shown
         in Table 20-1, is reported in the Fault Alarm.
        
         If a defect with a higher priority is raised after a Fault
         Alarm has been issued, another Fault Alarm is issued.
        
         The management entity receiving the notification can identify
         the system from the network source address of the
         notification, and can identify the MEP reporting the defect
         by the indices in the OID of the cdot1agMepHighestPrDefect
         variable in the notification:
        
            cdot1agMdIndex - Also the index of the MEP's
                               Maintenance Domain table entry
                               (cdot1agMdTable).
            cdot1agMaIndex - Also an index (with the MD table index)
                               of the MEP's Maintenance Association
                               table entry (cdot1agMaTable).
            cdot1agMepIdentifier - MEP Identifier and final index
                               into the MEP table (cdot1agMepTable)."
    REFERENCE
        "802.1ag clause 12.14.7.7"
    ::= 1

cdot1agStackGroup OBJECT IDENTIFIER ::= { cdot1agGroups 1 }
-- OBJECT-GROUP
--  Status
--    mandatory
--  Descr
--    Objects for the Stack group.
--  objects
--    cdot1agStackMdIndex, cdot1agStackMaIndex, cdot1agStackMepId, 
--    cdot1agStackMacAddress

cdot1agDefaultMdGroup OBJECT IDENTIFIER ::= { cdot1agGroups 2 }
-- OBJECT-GROUP
--  Status
--    mandatory
--  Descr
--    Objects for the Default MD Level group.
--  objects
--    cdot1agDefaultMdDefLevel, cdot1agDefaultMdDefMhfCreation, 
--    cdot1agDefaultMdDefIdPermission, cdot1agDefaultMdStatus, 
--    cdot1agDefaultMdLevel, cdot1agDefaultMdMhfCreation, 
--    cdot1agDefaultMdIdPermission

cdot1agVlanIdGroup OBJECT IDENTIFIER ::= { cdot1agGroups 3 }
-- OBJECT-GROUP
--  Status
--    mandatory
--  Descr
--    Objects for the VLAN ID group.
--  objects
--    cdot1agVlanPrimaryVid, cdot1agVlanRowStatus

cdot1agConfigErrorListGroup OBJECT IDENTIFIER ::= { cdot1agGroups 4 }
-- OBJECT-GROUP
--  Status
--    mandatory
--  Descr
--    Objects for the CFM Configuration Error List Group.
--  objects
--    cdot1agConfigErrorListErrorType

cdot1agMdGroup OBJECT IDENTIFIER ::= { cdot1agGroups 5 }
-- OBJECT-GROUP
--  Status
--    mandatory
--  Descr
--    Objects for the Maintenance Domain Group.
--  objects
--    cdot1agMdTableNextIndex, cdot1agMdName, cdot1agMdFormat, 
--    cdot1agMdMdLevel, cdot1agMdMhfCreation, 
--    cdot1agMdMhfIdPermission, cdot1agMdMaTableNextIndex, 
--    cdot1agMdRowStatus

cdot1agMaGroup OBJECT IDENTIFIER ::= { cdot1agGroups 6 }
-- OBJECT-GROUP
--  Status
--    mandatory
--  Descr
--    Objects for the MA group.
--  objects
--    cdot1agMaName, cdot1agMaPrimaryVlanId, cdot1agMaFormat, 
--    cdot1agMaMhfCreation, cdot1agMaIdPermission, 
--    cdot1agMaCcmInterval, cdot1agMaRowStatus, 
--    cdot1agMaNumberOfVids, cdot1agMaMepListRowStatus

cdot1agMepGroup OBJECT IDENTIFIER ::= { cdot1agGroups 7 }
-- OBJECT-GROUP
--  Status
--    mandatory
--  Descr
--    Objects for the MEP group.
--  objects
--    cdot1agMepIfIndex, cdot1agMepDirection, cdot1agMepPrimaryVid, 
--    cdot1agMepActive, cdot1agMepFngState, cdot1agMepCciEnabled, 
--    cdot1agMepCcmLtmPriority, cdot1agMepMacAddress, 
--    cdot1agMepLowPrDef, cdot1agMepFngAlarmTime, 
--    cdot1agMepFngResetTime, cdot1agMepHighestPrDefect, 
--    cdot1agMepDefects, cdot1agMepErrorCcmLastFailure, 
--    cdot1agMepXconCcmLastFailure, cdot1agMepCcmSequenceErrors, 
--    cdot1agMepCciSentCcms, cdot1agMepNextLbmTransId, 
--    cdot1agMepLbrIn, cdot1agMepLbrInOutOfOrder, 
--    cdot1agMepLbrBadMsdu, cdot1agMepLtmNextSeqNumber, 
--    cdot1agMepUnexpLtrIn, cdot1agMepLbrOut, 
--    cdot1agMepTransmitLbmStatus, 
--    cdot1agMepTransmitLbmDestMacAddress, 
--    cdot1agMepTransmitLbmDestMepId, 
--    cdot1agMepTransmitLbmDestIsMepId, 
--    cdot1agMepTransmitLbmMessages, cdot1agMepTransmitLbmDataTlv, 
--    cdot1agMepTransmitLbmVlanPriority, 
--    cdot1agMepTransmitLbmVlanDropEnable, 
--    cdot1agMepTransmitLbmResultOK, cdot1agMepTransmitLbmSeqNumber, 
--    cdot1agMepTransmitLtmStatus, cdot1agMepTransmitLtmFlags, 
--    cdot1agMepTransmitLtmTargetMacAddress, 
--    cdot1agMepTransmitLtmTargetMepId, 
--    cdot1agMepTransmitLtmTargetIsMepId, cdot1agMepTransmitLtmTtl, 
--    cdot1agMepTransmitLtmResult, cdot1agMepTransmitLtmSeqNumber, 
--    cdot1agMepTransmitLtmEgressIdentifier, cdot1agMepRowStatus, 
--    cdot1agLtrForwarded, cdot1agLtrRelay, 
--    cdot1agLtrChassisIdSubtype, cdot1agLtrChassisId, 
--    cdot1agLtrManAddress, cdot1agLtrManAddressDomain, 
--    cdot1agLtrIngress, cdot1agLtrIngressMac, 
--    cdot1agLtrIngressPortIdSubtype, cdot1agLtrIngressPortId, 
--    cdot1agLtrEgress, cdot1agLtrEgressMac, 
--    cdot1agLtrEgressPortIdSubtype, cdot1agLtrEgressPortId, 
--    cdot1agLtrTerminalMep, cdot1agLtrLastEgressIdentifier, 
--    cdot1agLtrNextEgressIdentifier, cdot1agLtrTtl, 
--    cdot1agLtrOrganizationSpecificTlv

cdot1agMepDbGroup OBJECT IDENTIFIER ::= { cdot1agGroups 8 }
-- OBJECT-GROUP
--  Status
--    mandatory
--  Descr
--    Objects for the MEP group.
--  objects
--    cdot1agMepDbRMepState, cdot1agMepDbRMepFailedOkTime, 
--    cdot1agMepDbMacAddress, cdot1agMepDbRdi, 
--    cdot1agMepDbPortStatusTlv, cdot1agMepDbInterfaceStatusTlv, 
--    cdot1agMepDbChassisIdSubtype, cdot1agMepDbChassisId, 
--    cdot1agMepDbManAddressDomain, cdot1agMepDbManAddress

cdot1agNotificationsGroup OBJECT IDENTIFIER ::= { cdot1agGroups 9 }
-- NOTIFICATION-GROUP
--  Status
--    mandatory
--  Descr
--    Objects for the Notifications group.
--  notifications
--    cdot1agFaultAlarm

cdot1agCompliance OBJECT IDENTIFIER ::= { cdot1agCompliances 1 }
-- MODULE-COMPLIANCE
--  Status
--    mandatory
--  Descr
--    The compliance statement for support of the CFM MIB module.
--  Module
--    >>current<<
--   MandGroup
--    cdot1agStackGroup
--   MandGroup
--    cdot1agDefaultMdGroup
--   MandGroup
--    cdot1agConfigErrorListGroup
--   MandGroup
--    cdot1agMdGroup
--   MandGroup
--    cdot1agMaGroup
--   MandGroup
--    cdot1agMepGroup
--   MandGroup
--    cdot1agMepDbGroup
--   MandGroup
--    cdot1agNotificationsGroup
--   OptGroup
--    cdot1agVlanIdGroup
--   ObjVar
--    cdot1agMdRowStatus
--   ObjVar
--    cdot1agMaRowStatus
--   ObjVar
--    cdot1agVlanRowStatus
--   ObjVar
--    cdot1agMaMepListRowStatus
--   ObjVar
--    cdot1agMepRowStatus


END
