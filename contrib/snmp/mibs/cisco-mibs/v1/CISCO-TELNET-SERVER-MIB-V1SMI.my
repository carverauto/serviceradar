-- MIB file created 07-Jul-2008 09:26:59, by
--   SMICng version 2.2.11-beta(PRO)(Solaris), January 20, 2001. Enterprise key cisco.com

CISCO-TELNET-SERVER-MIB DEFINITIONS ::= BEGIN

-- From file: "CISCO-TELNET-SERVER-MIB.my"
-- Compile options "4 7 F H N O W 03 06 0B 0G 0N 0T"

IMPORTS
    SnmpAdminString
            FROM SNMP-FRAMEWORK-MIB
    InetAddressType, InetAddress, InetPortNumber
            FROM INET-ADDRESS-MIB
    TruthValue
            FROM SNMPv2-TC-v1
    ciscoMgmt
            FROM CISCO-SMI
    Gauge
            FROM RFC1155-SMI
    OBJECT-TYPE
            FROM RFC-1212
    TRAP-TYPE
            FROM RFC-1215;

ciscoTelnetServerMIB OBJECT IDENTIFIER ::= { ciscoMgmt 630 }
-- MODULE-IDENTITY
--  LastUpdated
--    200705080000Z
--  OrgName
--    Cisco Systems, Inc.
--  ContactInfo
--    Cisco Systems
--    Postal: 170 W Tasman Drive
--    San Jose, CA  95134
--    USA
--    Tel: +1 800 553 -NETS
--    E-mail: cs-san@cisco.com,
--            cs-lan-switch-snmp@cisco.com
--  Descr
--    MIB module for displaying and configuring
--    Telnet related features in a device.
--    Telnet is a program to log into another computer over
--    a network, to execute commands in a remote machine.
--  RevDate
--    200705080000Z
--  RevDescr
--    Initial version of this MIB module.

ciscoTelnetServerMIBNotifs OBJECT IDENTIFIER ::= { ciscoTelnetServerMIB 0 }
ciscoTelnetServerMIBObjects OBJECT IDENTIFIER ::= { ciscoTelnetServerMIB 1 }
ciscoTelnetServerMIBConform OBJECT IDENTIFIER ::= { ciscoTelnetServerMIB 2 }
ciscoTelnetServerMIBCompliances OBJECT IDENTIFIER ::= { ciscoTelnetServerMIBConform 1 }
ciscoTelnetServerConfigObjects OBJECT IDENTIFIER ::= { ciscoTelnetServerMIBObjects 1 }
ciscoTelnetServerStatusObjects OBJECT IDENTIFIER ::= { ciscoTelnetServerMIBObjects 2 }
ciscoTelnetServerMIBGroups OBJECT IDENTIFIER ::= { ciscoTelnetServerMIBConform 2 }

ctsTelnetActivation OBJECT-TYPE
    SYNTAX TruthValue
--    Rsyntax INTEGER {
--        true(1),
--        false(2)
--        }
    ACCESS read-write
    STATUS mandatory
    DESCRIPTION
        "This object specifies whether the Telnet access service on
        the device is enabled."
    ::= { ciscoTelnetServerConfigObjects 1 }

ctsSessionEndedNotifEnable OBJECT-TYPE
    SYNTAX TruthValue
--    Rsyntax INTEGER {
--        true(1),
--        false(2)
--        }
    ACCESS read-write
    STATUS mandatory
    DESCRIPTION
        "This object controls whether the system produces
        ctsSessionEnded notifications. A 'false' value will prevent
        ctsSessionEnded notifications from being generated by this
        system."
    ::= { ciscoTelnetServerConfigObjects 2 }

ctsSessionStartedNotifEnable OBJECT-TYPE
    SYNTAX TruthValue
--    Rsyntax INTEGER {
--        true(1),
--        false(2)
--        }
    ACCESS read-write
    STATUS mandatory
    DESCRIPTION
        "This object controls whether the system produces
        ctsSessionStarted notifications. A 'false' value will prevent
        ctsSessionStarted notifications from being generated by this
        system."
    ::= { ciscoTelnetServerConfigObjects 3 }

ctsSessionDeniedNotifEnable OBJECT-TYPE
    SYNTAX TruthValue
--    Rsyntax INTEGER {
--        true(1),
--        false(2)
--        }
    ACCESS read-write
    STATUS mandatory
    DESCRIPTION
        "This object controls whether the system produces
        ctsSessionDenied notifications. A 'false' value will prevent
        ctsSessionDenied notifications from being generated by this
        system."
    ::= { ciscoTelnetServerConfigObjects 4 }

ctsSessionFailureNotifEnable OBJECT-TYPE
    SYNTAX TruthValue
--    Rsyntax INTEGER {
--        true(1),
--        false(2)
--        }
    ACCESS read-only
    STATUS mandatory
    DESCRIPTION
        "This object controls whether the system produces
        ctsSessionLoginFailure notifications. A 'false' value will
        prevent ctsSessionLoginFailure notifications from being
        generated by this system."
    ::= { ciscoTelnetServerConfigObjects 5 }

ctsSessionsTable OBJECT-TYPE
    SYNTAX SEQUENCE OF CtsSessionsEntry
    ACCESS not-accessible
    STATUS mandatory
    DESCRIPTION
        "This table provides data for each telnet session on an entity
        capable of running telnet server."
    ::= { ciscoTelnetServerStatusObjects 1 }

ctsSessionsEntry OBJECT-TYPE
    SYNTAX CtsSessionsEntry
    ACCESS not-accessible
    STATUS mandatory
    DESCRIPTION
        "An entry (conceptual row) in the ctsSessionsTable.
        This entry lists the data for the telnet session on the entity
        running the telnet server.
        
        An entry in the ctsSessionTable, that provides
        detailed information about all the existing telnet sessions on
        the device. 
        
        An entry will be created for every telnet session established
        on the device. The entry will be removed upon termination
        of the telnet session."
    INDEX { ctsSessionID }
    ::= { ctsSessionsTable 1 }

CtsSessionsEntry ::= SEQUENCE {
    ctsSessionID Gauge,
    ctsSessionDescription SnmpAdminString,
    ctsSessionClientAddressType InetAddressType,
    ctsSessionsClientAddress InetAddress,
    ctsSessionPID Gauge,
    ctsSessionUserID SnmpAdminString,
    ctsSessionTcpPort InetPortNumber
    }

ctsSessionID OBJECT-TYPE
    SYNTAX Gauge
    ACCESS not-accessible
    STATUS mandatory
    DESCRIPTION
        "An arbitrary index that uniquely identifies a Telnet Session."
    ::= { ctsSessionsEntry 1 }

ctsSessionDescription OBJECT-TYPE
    SYNTAX SnmpAdminString
--    Rsyntax OCTET STRING(SIZE(0..255))
    ACCESS read-only
    STATUS mandatory
    DESCRIPTION
        "Human readable description about the session."
    ::= { ctsSessionsEntry 2 }

ctsSessionClientAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "The type of Internet address of the client that requested this
        session."
    ::= { ctsSessionsEntry 3 }

ctsSessionsClientAddress OBJECT-TYPE
    SYNTAX InetAddress
--    Rsyntax OCTET STRING(SIZE(0..255))
    ACCESS read-only
    STATUS mandatory
    DESCRIPTION
        "The Internet address of the client that requested this session.
        The type of this address is determined by the value of the
        ctsSessionClientAddressType object."
    ::= { ctsSessionsEntry 4 }

ctsSessionPID OBJECT-TYPE
    SYNTAX Gauge
    ACCESS read-only
    STATUS mandatory
    DESCRIPTION
        "The object indicates the process ID of the process
        serving this telnet session on the device."
    ::= { ctsSessionsEntry 5 }

ctsSessionUserID OBJECT-TYPE
    SYNTAX SnmpAdminString
--    Rsyntax OCTET STRING(SIZE(0..255))
    ACCESS read-only
    STATUS mandatory
    DESCRIPTION
        "The object indicates user name associated with this
        telnet session."
    ::= { ctsSessionsEntry 6 }

ctsSessionTcpPort OBJECT-TYPE
    SYNTAX InetPortNumber
--    Rsyntax Gauge(0..65535)
    ACCESS read-only
    STATUS mandatory
    DESCRIPTION
        "The TCP source port number of the remote client."
    ::= { ctsSessionsEntry 7 }

ctsSessionEnded TRAP-TYPE
-- Reverse mappable trap
    ENTERPRISE ciscoTelnetServerMIB
    VARIABLES {
        ctsSessionClientAddressType, ctsSessionsClientAddress, 
        ctsSessionUserID, ctsSessionTcpPort }
--  Status
--    mandatory
    DESCRIPTION
        "This notification signifies that the agent entity has detected
        end of a telnet session."
    ::= 1

ctsSessionStarted TRAP-TYPE
-- Reverse mappable trap
    ENTERPRISE ciscoTelnetServerMIB
    VARIABLES {
        ctsSessionClientAddressType, ctsSessionsClientAddress, 
        ctsSessionUserID }
--  Status
--    mandatory
    DESCRIPTION
        "This notification is sent when the agent entity has accepted a
        new telnet session."
    ::= 2

ctsSessionDenied TRAP-TYPE
-- Reverse mappable trap
    ENTERPRISE ciscoTelnetServerMIB
    VARIABLES {
        ctsSessionClientAddressType, ctsSessionsClientAddress, 
        ctsSessionTcpPort }
--  Status
--    mandatory
    DESCRIPTION
        "This notification signifies that the agent has refused a telnet
        session."
    ::= 3

ctsSessionLoginFailure TRAP-TYPE
-- Reverse mappable trap
    ENTERPRISE ciscoTelnetServerMIB
    VARIABLES {
        ctsSessionClientAddressType, ctsSessionsClientAddress, 
        ctsSessionUserID, ctsSessionTcpPort }
--  Status
--    mandatory
    DESCRIPTION
        "This notification is sent when the agent entity has detected
        attempt to login with wrong credentials."
    ::= 4

ctsMIBSessionsObjectGroup OBJECT IDENTIFIER ::= { ciscoTelnetServerMIBGroups 1 }
-- OBJECT-GROUP
--  Status
--    mandatory
--  Descr
--    This group of objects maintains informative data for each
--    Telnet session on a device that runs Telnet Server.
--  objects
--    ctsSessionDescription, ctsSessionClientAddressType, 
--    ctsSessionsClientAddress, ctsTelnetActivation, ctsSessionPID, 
--    ctsSessionUserID, ctsSessionTcpPort

ctsSessionNotifsControlGroup OBJECT IDENTIFIER ::= { ciscoTelnetServerMIBGroups 3 }
-- OBJECT-GROUP
--  Status
--    mandatory
--  Descr
--    A collection of objects providing configuration information
--    applicable to all session notifications.
--  objects
--    ctsSessionEndedNotifEnable, ctsSessionStartedNotifEnable, 
--    ctsSessionDeniedNotifEnable, ctsSessionFailureNotifEnable

ctsMIBNotificationGroup OBJECT IDENTIFIER ::= { ciscoTelnetServerMIBGroups 2 }
-- NOTIFICATION-GROUP
--  Status
--    mandatory
--  Descr
--    This group contains notifications for this MIB.
--  notifications
--    ctsSessionEnded, ctsSessionStarted, ctsSessionDenied, 
--    ctsSessionLoginFailure

ciscoTelnetServerMIBCompliance OBJECT IDENTIFIER ::= { ciscoTelnetServerMIBCompliances 1 }
-- MODULE-COMPLIANCE
--  Status
--    mandatory
--  Descr
--    The compliance statement for SNMP Agents which implement this
--    MIB.
--  Module
--    >>current<<
--   MandGroup
--    ctsMIBSessionsObjectGroup
--   MandGroup
--    ctsMIBNotificationGroup
--   OptGroup
--    ctsSessionNotifsControlGroup


END
