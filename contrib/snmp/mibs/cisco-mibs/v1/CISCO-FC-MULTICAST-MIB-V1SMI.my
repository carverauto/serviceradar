-- MIB file created 05-Nov-2004 15:22:17, by
--   SMICng version 2.2.11-beta(PRO)(Solaris), January 20, 2001. Enterprise key cisco.com

CISCO-FC-MULTICAST-MIB DEFINITIONS ::= BEGIN

-- From file: "CISCO-FC-MULTICAST-MIB.my"
-- Compile options "4 7 F H N O W 03 06 0B 0G 0N 0T"

IMPORTS
    RowStatus
            FROM SNMPv2-TC-v1
    ciscoMgmt
            FROM CISCO-SMI
    vsanIndex
            FROM CISCO-VSAN-MIB
    DomainIdOrZero
            FROM CISCO-ST-TC
    OBJECT-TYPE
            FROM RFC-1212;

ciscoFcMulticastMIB OBJECT IDENTIFIER ::= { ciscoMgmt 435 }
-- MODULE-IDENTITY
--  LastUpdated
--    200410070000Z
--  OrgName
--    Cisco Systems Inc. 
--  ContactInfo
--         Cisco Systems
--          Customer Service
--    Postal: 170 W Tasman Drive
--          San Jose, CA  95134
--          USA
--    Tel: +1 800 553 -NETS
--    E-mail: cs-san@cisco.com
--  Descr
--    MIB module for monitoring and configuring 
--    Fibre Channel Multicast feature.
--  RevDate
--    200410070000Z
--  RevDescr
--    Initial version of this MIB module.

ciscoFcMulticastNotifications OBJECT IDENTIFIER ::= { ciscoFcMulticastMIB 0 }
ciscoFcMulticastMIBObjects OBJECT IDENTIFIER ::= { ciscoFcMulticastMIB 1 }
ciscoFcMulticaseConformance OBJECT IDENTIFIER ::= { ciscoFcMulticastMIB 2 }
cfmConfiguration OBJECT IDENTIFIER ::= { ciscoFcMulticastMIBObjects 1 }
ciscoFcMulticastMIBCompliances OBJECT IDENTIFIER ::= { ciscoFcMulticaseConformance 1 }
ciscoFcMulticastMIBGroups OBJECT IDENTIFIER ::= { ciscoFcMulticaseConformance 2 }

CfmMulticastRootMode ::= INTEGER {
        principalSwitch(1),
        lowestDomainSwitch(2)
        }
-- TEXTUAL-CONVENTION
--  Status
--    mandatory
--  Descr
--    The multicast Root Mode.
--     principalSwitch       - principal switch is used as the
--                             root for multicast tree 
--                             computation.
--     lowestDomainIdSwitch  - lowest domainId switch is used 
--                             as the root for mulitcast tree 
--                             computation.
--  Refer
--    Refer to FC-SW-2 REV 5.4 for information on principal 
--    switch and lowest domain id switch.

cfmMulticastRootTable OBJECT-TYPE
    SYNTAX SEQUENCE OF CfmMulticastRootEntry
    ACCESS not-accessible
    STATUS mandatory
    DESCRIPTION
        "This table allows the users to configure and monitor the
        FC Multicast parameters on all the VSANs configured on the 
        local switch.
        
        An entry is automatically created in this table if there
        is an entry in the fspfTable (defined in CISCO-FSPF-MIB) and
        fspfOperStatus (defined in CISCO-FSPF-MIB) for that
        entry is 'up'.
        
        An entry is automatically deleted from this table if
        either :
         a) the fspfOperStatus in the fspfTable entry for the 
            corresponding VSAN changes to 'down'.
                              or
         b) the fspfTable entry for the corresponding VSAN is
            deleted.
        
        Entries in this table can be created via 
        cfmMulticastRootRowStatus only as the means to specify 
        non-default parameter values for a VSAN either because the
        VSAN is suspended or fspfOperStatus (defined in 
        CISCO-FSPF-MIB) for that VSAN is 'down' (VSAN state is 
        indicated by object vsanOperState which is defined in 
        CISCO-VSAN-MIB).
        
        So an entry in this table exists when one or both of these
        conditions holds:
        - one or more configuration parameters have non-default
          values for a VSAN which is either suspended or the 
          fspfOperStatus for that VSAN is down.  
        - the fspfOperStatus for VSAN is 'up'.
        
        This has a number of consequences:
        - an entry exists for a suspended VSAN whenever that VSAN 
          has non-default parameters.
        - an entry cannot be created (via cfmMulticastRootRowStatus) 
          for a VSAN with default parameters; instead, the agent
          creates/deletes an entry for a VSAN with default
          parameters according to whether the fspfOperStatus is 'up' 
          or 'down'.
        - an entry can not be created via cfmMulticastRootRowStatus 
          unless non-default parameter values are (simultaneously) 
          configured for a VSAN whose fspfOperStatus is 'down'.
        - deleting an entry via cfmMulticastRootRowStatus when either
          the VSAN is suspended and configured with non-default 
          values or the VSAN is active, is equivalent to resetting
          its parameters to their default values.
          If an entry is configured with default-values and the 
          VSAN is in suspended state, then the entry would be 
          deleted."
    REFERENCE
        "For information FC multicast/root, refer to Fibre Channel 
        Switch Fabric-2  (FC-SW-2 REV 5.4) and Fibre Channel Switch 
        Fabric-3  (FC-SW-3 REV 6.6)."
    ::= { cfmConfiguration 1 }

cfmMulticastRootEntry OBJECT-TYPE
    SYNTAX CfmMulticastRootEntry
    ACCESS not-accessible
    STATUS mandatory
    DESCRIPTION
        "This entry contains the multicase parameters on this VSAN."
    INDEX { vsanIndex }
    ::= { cfmMulticastRootTable 1 }

CfmMulticastRootEntry ::= SEQUENCE {
    cfmMulticastRootConfigMode CfmMulticastRootMode,
    cfmMulticastRootOperMode CfmMulticastRootMode,
    cfmMulticastRootDomainId DomainIdOrZero,
    cfmMulticastRootRowStatus RowStatus
    }

cfmMulticastRootConfigMode OBJECT-TYPE
    SYNTAX CfmMulticastRootMode
--    Rsyntax INTEGER {
--        principalSwitch(1),
--        lowestDomainSwitch(2)
--        }
    ACCESS read-write
    STATUS mandatory
    DESCRIPTION
        "The configured multicast root mode on this VSAN."
    DEFVAL { principalSwitch }
    ::= { cfmMulticastRootEntry 1 }

cfmMulticastRootOperMode OBJECT-TYPE
    SYNTAX CfmMulticastRootMode
--    Rsyntax INTEGER {
--        principalSwitch(1),
--        lowestDomainSwitch(2)
--        }
    ACCESS read-only
    STATUS mandatory
    DESCRIPTION
        "The operational multicast root mode on this VSAN."
    ::= { cfmMulticastRootEntry 2 }

cfmMulticastRootDomainId OBJECT-TYPE
    SYNTAX DomainIdOrZero
--    Rsyntax INTEGER(0..239)
    ACCESS read-only
    STATUS mandatory
    DESCRIPTION
        "The domainID of the multicast root on this VSAN."
    ::= { cfmMulticastRootEntry 3 }

cfmMulticastRootRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of conceptual row on this VSAN.
        
        This object can be used to create an entry only if
        either the corresponding VSAN is suspended or the
        fspfOperStatus is down. If the VSAN is either 
        not-existent or fspfOperStatus is up, the create will fail."
    ::= { cfmMulticastRootEntry 4 }

cfmConfigurationGroup OBJECT IDENTIFIER ::= { ciscoFcMulticastMIBGroups 1 }
-- OBJECT-GROUP
--  Status
--    mandatory
--  Descr
--    A collection of objects for FC multicast 
--    configuration.
--  objects
--    cfmMulticastRootConfigMode, cfmMulticastRootOperMode, 
--    cfmMulticastRootDomainId, cfmMulticastRootRowStatus

ciscoFcMulticastMIBCompliance OBJECT IDENTIFIER ::= { ciscoFcMulticastMIBCompliances 1 }
-- MODULE-COMPLIANCE
--  Status
--    mandatory
--  Descr
--    The compliance statement for entities which implement the 
--    CISCO-FC-MULTICAST-MIB.
--  Module
--    >>current<<
--   MandGroup
--    cfmConfigurationGroup


END
