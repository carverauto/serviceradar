-- MIB file created 18-Nov-2010 15:48:31, by
--   SMICng version 2.2.11-beta(PRO)(Solaris), January 20, 2001. Enterprise key cisco.com

CISCO-APS-EXT-MIB DEFINITIONS ::= BEGIN

-- From file: "CISCO-APS-EXT-MIB.my"
-- Compile options "4 7 F H N W 03 06 0B 0G 0N 0T"

IMPORTS
    TruthValue
            FROM SNMPv2-TC-v1
    SnmpAdminString
            FROM SNMP-FRAMEWORK-MIB
    ciscoExperiment
            FROM CISCO-SMI
    cApsConfigName, cApsConfigName, cApsChanConfigGroupName, 
    cApsChanConfigNumber, CApsK1K2, cApsChanConfigGroupName, 
    cApsChanConfigNumber
            FROM CISCO-APS-MIB
    InetAddressType, InetAddress
            FROM INET-ADDRESS-MIB
    OBJECT-TYPE
            FROM RFC-1212;

cApsExtMIB OBJECT IDENTIFIER ::= { ciscoExperiment 72 }
-- MODULE-IDENTITY
--  LastUpdated
--    200301310000Z
--  OrgName
--    Cisco Systems, Inc.
--  ContactInfo
--    Cisco Systems, Inc. 
--     Customer Service 
--     Postal: 170 W. Tasman Drive 
--             San Jose, CA  95134-1706 
--             USA 
--     Tel: +1 800 553-NETS 
--     Email: optmgmt-dev@cisco.com
--  Descr
--    The Cisco APS Extension MIB extends the Cisco APS MIB  
--     in order to a) support path APS architectures and 
--     b) support interfaces other than SONET (e.g. Cisco 
--     CDL). 
--    
--     For configuration and monitoring of APS for CDL interfaces, 
--     all objects and notifications in the Cisco APS MIB apply, 
--     with the exception of the following: 
--     - cApsStatusK1K2Rcv and cApsStatusK1K2Trans in 
--       cApsStatusEntry, 
--     - cApsConfigSdBerThreshold and cApsConfigSfBerThreshold 
--       in cApsConfigEntry, 
--     - cApsChanStatusSignalDegrades and 
--       cApsChanStatusSignalFailures in cApsChanStatusEntry, 
--     - cApsStatusFEPLFs in cApsStatusEntry, 
--     - cApsEventFEPLF. 
--    
--     Whenever the description of an object in the Cisco APS MIB 
--     refers to a SONET LTE interface, this applies to CDL 
--     terminating interfaces as well. CDL interfaces have 
--     ifType values other than 'sonet'. 
--    
--     For SONET path APS support, whenever the description of an 
--     object in the Cisco APS MIB refers to a SONET LTE 
--     interface, this applies to SONET PTE interfaces as well. 
--     SONET PTE interfaces have ifType values 'sonetPath'. 
--  RevDate
--    200301310000Z
--  RevDescr
--    Updated the default value for the object  
--     cApsConfigSwitchoverEnableInterval. 
--  RevDate
--    200205310000Z
--  RevDescr
--    Added table cApsChanConfigExtTable which augments  
--    cApsChanConfigTable in CISCO-APS-MIB, and table 
--    cApsChanAssociationTable that provides for all  
--    protection/working channels, the associated working/protection 
--    channel IP address.  
--  RevDate
--    200205200000Z
--  RevDescr
--    Added objects for control of APS message transport and 
--     to show additional channel status information. 
--  RevDate
--    200105210000Z
--  RevDescr
--    The initial version of this MIB augments cApsConfigEntry (in 
--     the CISCO-APS-MIB) with two new APS configuration parameters, 
--     cApsConfigSpan and cApsConfigYcable, and cApsStatusEntry with 
--     two new status parameters, cApsStatusCdlApsBytesRcv and 
--     cApsStatusCdlApsBytesTrans. 

cApsExtMIBObjects OBJECT IDENTIFIER ::= { cApsExtMIB 1 }
cApsExtMIBConformance OBJECT IDENTIFIER ::= { cApsExtMIB 2 }
cApsExtGroups   OBJECT IDENTIFIER ::= { cApsExtMIBConformance 1 }
cApsExtCompliances OBJECT IDENTIFIER ::= { cApsExtMIBConformance 2 }

CdlApsBytes ::= OCTET STRING(SIZE(2))
-- TEXTUAL-CONVENTION
--  Status
--    mandatory
--  Descr
--    This Textual Convention describes an object that stores 
--     the APS protocol field used in CDL. The semantics of the 
--     CDL APS protocol field are similar to those of the 
--     SONET K1 and K2 byte APS protocol field. 

CApsMessageTransport ::= INTEGER {
        none(1),
        autoSelect(2),
        dcc(3),
        apsChannel(4),
        ip(5),
        osc(6)
        }
-- TEXTUAL-CONVENTION
--  Status
--    mandatory
--  Descr
--    The type of transport used to exchange APS protocol messages. 
--    
--     none 
--                
--       There is no APS message exchange between the endpoints  
--       of the associated channels. 
--    
--     autoSelect   
--    
--       APS automatically selects a transport mechanism 
--       to send APS messages.  The following transport 
--       mechanisms are attempted, in the following order 
--       of priority: 
--        - apsChannel 
--        - dcc 
--        - osc 
--    
--     dcc          
--    
--       APS messages are transmitted over the data communications  
--       channels (DCCs) in the overhead of the associated channels. 
--    
--     apsChannel 
--                  
--       APS messages are transmitted in overhead bytes of the 
--       associated channels that are defined specifically 
--       to carry APS messages. 
--    
--     ip 
--                
--       APS messages are transmitted over IP. The IP network can 
--       consist of any combination of data communication channels 
--       (DCCs), optical supervisory channels (OSCs), and 
--       out-of-band Data Communication Networks (DCNs). 
--    
--     osc 
--                
--       APS messages are transmitted over the Optical Supervisory  
--       Channel (OSC). 
--     

CApsChannelConfigNumber ::= INTEGER(0..14)
-- TEXTUAL-CONVENTION
--  Status
--    mandatory
--  Descr
--    This Textual Convention describes an object that is set to  
--     a unique channel number within an APS group.  
--     The value 0 indicates the null channel. The values 1-14  
--     define a working channel. 
--  Refer
--    Bellcore (Telcordia Technologies) GR-253-CORE,  
--     Issue 2,Revision 2 (January 1999), 5.3.2. 

cApsNotifiesEnable OBJECT-TYPE
    SYNTAX TruthValue
--    Rsyntax INTEGER {
--        true(1),
--        false(2)
--        }
    ACCESS read-write
    STATUS mandatory
    DESCRIPTION
        "When this object is set to 'true', it allows the generation of 
         the APS-related notifications defined in the CISCO-APS-MIB. 
         When this object is set to 'false', it prevents the generation 
         of the APS-related notifications defined in the CISCO-APS-MIB. 
         By default, this object is set to 'false'."
    ::= { cApsExtMIBObjects 1 }

cApsConfigExtTable OBJECT-TYPE
    SYNTAX SEQUENCE OF CApsConfigExtEntry
    ACCESS not-accessible
    STATUS mandatory
    DESCRIPTION
        "This table augments the cApsConfigTable."
    ::= { cApsExtMIBObjects 2 }

cApsConfigExtEntry OBJECT-TYPE
    SYNTAX CApsConfigExtEntry
    ACCESS not-accessible
    STATUS mandatory
    DESCRIPTION
        "A conceptual row in the cApsConfigExtTable."
    INDEX { --?? IMPLIED may cause problems
            IMPLIED cApsConfigName }
-- Augments cApsConfigEntry FROM CISCO-APS-MIB
    ::= { cApsConfigExtTable 1 }

CApsConfigExtEntry ::= SEQUENCE {
    cApsConfigSpan INTEGER,
    cApsConfigYcable INTEGER,
    cApsConfigMinSearchUpInterval INTEGER,
    cApsConfigMaxSearchUpInterval INTEGER,
    cApsConfigSwitchoverEnableInterval INTEGER,
    cApsConfigMessageTransport CApsMessageTransport,
    cApsConfigMessageHolddown INTEGER,
    cApsConfigMessageHolddownCount INTEGER,
    cApsConfigMessageMaxInterval INTEGER,
    cApsConfigFarEndGroupName SnmpAdminString,
    cApsConfigFarEndIpAddressType InetAddressType,
    cApsConfigFarEndIpAddress InetAddress
    }

cApsConfigSpan OBJECT-TYPE
    SYNTAX INTEGER {
        hopByHop(1),
        endToEnd(2)
        }
    ACCESS read-write
    STATUS mandatory
    DESCRIPTION
        "The span (hopByHop or endToEnd) for the APS group. 
        
         hopByHop 
        
         This refers to linear APS, e.g. linear SONET APS, or hopByHop 
         CDL APS. In a DWDM system, an APS channel may be associated 
         with either an individual wavelength or an optical fiber. 
         All APS channels within an APS group must be of the same type. 
         Systems that support linear APS on an individual wavelength  
         basis, must assign an ifIndex to each such wavelength. 
        
         endToEnd 
        
         This refers to path APS, e.g. endToEnd CDL APS. In this 
         configuration, each APS channel in the APS group is associated 
         with an endToEnd user path. This codepoint does not apply to 
         interfaces with an ifType value of 'sonet'. 
        
         This object may not be modified if the associated 
         cApsConfigRowStatus object is equal to 'active'. "
    DEFVAL { hopByHop }
    ::= { cApsConfigExtEntry 1 }

cApsConfigYcable OBJECT-TYPE
    SYNTAX INTEGER {
        noYcable(1),
        ycable(2),
        ycableXconnectCommon(3)
        }
    ACCESS read-write
    STATUS mandatory
    DESCRIPTION
        "The Y-cable configuration for the APS group associated with 
         user channels. 
        
         noYcable 
        
         The APS channels in the APS group are not connected to an 
         external Y-cable. 
        
         ycable 
        
         Two user-side interfaces (not necessarily SONET or CDL) are 
         connected to an external y-cable and are grouped into an APS 
         group for endToEnd APS. The received user signal is split 
         in the y-cable coupler and is received on both the interfaces. 
         However, only one interface must transmit toward the user at any 
         given time. With cApsConfigYcable set to 'ycable', the 
         cApsConfigSpan must be set to 'endToEnd'. There must be 
         only two APS channels in an APS group with cApsConfigYcable 
         set to 'ycable'. 
        
         ycableXconnectCommon 
        
         This refers to a configuration where two user-side interfaces 
         are connected to an external y-cable. The two signals received 
         on these interface are connected to the same cross connect in 
         the switch. The switch fabric selects one of the two received 
         signals, duplicates it, and forwards it to two network side 
         interfaces grouped for 1+1 linear APS. The received signal from 
         the network side is transmitted to only one user-side interface. 
         cApsConfigSpan is ignored if cApsConfigYcable is set to 
         'ycableXconnectCommon'. There must be only two APS channels in 
         an APS group with cApsConfigYcable set to 
         'ycableXconnectCommon'. 
        
         This object may not be modified if the associated 
         cApsConfigRowStatus object is equal to 'active'. 
        
         If this object is set to 'ycable' or 'ycableXconnectCommon', 
         the user must shut one of the two channels before setting 
         cApsConfigRowStatus to 'notInService'. "
    DEFVAL { noYcable }
    ::= { cApsConfigExtEntry 2 }

cApsConfigMinSearchUpInterval OBJECT-TYPE
    SYNTAX INTEGER(1..120)
    ACCESS read-write
    STATUS mandatory
    DESCRIPTION
        "This object is instantiated only when the standby interface 
         is not monitored. If both interfaces go down and the standby 
         interface is not monitored, successive switchovers may be used 
         in order to search for an interface that is up. 
        
         This object specifies the minimum time interval between 
         switchovers when both interfaces go down. A backoff algorithm 
         should be used to increase the time interval between 
         successive switchovers. "
    DEFVAL { 2 }
    ::= { cApsConfigExtEntry 3 }

cApsConfigMaxSearchUpInterval OBJECT-TYPE
    SYNTAX INTEGER(1..120)
--  Units
--    seconds
    ACCESS read-write
    STATUS mandatory
    DESCRIPTION
        "This object is instantiated only when the standby interface 
         is not monitored. If both interfaces go down and the standby 
         interface is not monitored, successive switchovers may be used 
         in order to search for an interface that is up. 
        
         This object specifies the maximum time interval between 
         switchovers when both interfaces go down. "
    DEFVAL { 32 }
    ::= { cApsConfigExtEntry 4 }

cApsConfigSwitchoverEnableInterval OBJECT-TYPE
    SYNTAX INTEGER(1..120)
--  Units
--    seconds
    ACCESS read-write
    STATUS mandatory
    DESCRIPTION
        "This object specifies the value of the timer to control 
         the minimum interval between switchovers. After a switchover, 
         APS is re-enabled only after this amount of time has elapsed, 
         in order to prevent quick successive switchovers. "
    DEFVAL { 3 }
    ::= { cApsConfigExtEntry 5 }

cApsConfigMessageTransport OBJECT-TYPE
    SYNTAX CApsMessageTransport
--    Rsyntax INTEGER {
--        none(1),
--        autoSelect(2),
--        dcc(3),
--        apsChannel(4),
--        ip(5),
--        osc(6)
--        }
    ACCESS read-write
    STATUS mandatory
    DESCRIPTION
        "This object specifies the type of transport configured for 
         exchange of APS protocol messages.  The type of transport 
         currently being used is indicated in the 
         cApsStatusMessageTransport object. 
        
         When this object is set to 'ip', values must be specified 
         for the cApsConfigFarEndIpAddressType, cApsConfigFarEndIpAddress 
         and cApsConfigFarEndGroupName objects. "
    DEFVAL { autoSelect }
    ::= { cApsConfigExtEntry 6 }

cApsConfigMessageHolddown OBJECT-TYPE
    SYNTAX INTEGER(100..10000)
--  Units
--    milliseconds
    ACCESS read-write
    STATUS mandatory
    DESCRIPTION
        "The value specified in this object applies when the value of 
         cApsStatusMessageTransport is 'dcc', 'ip', or 'osc'. 
        
         APS messages are exchanged between systems to support 
         bidirectional or linear operation. To avoid potential  
         system misbehavior in which APS messages would be  
         triggered in an uncontrolled fashion, a hold down timer  
         is introduced that prevents successive event-triggered 
         APS messages from being sent in too short a time 
         interval.  
        
         This object specifies the minimum time between 
         event driven requests. "
    DEFVAL { 5000 }
    ::= { cApsConfigExtEntry 7 }

cApsConfigMessageHolddownCount OBJECT-TYPE
    SYNTAX INTEGER(2..10)
    ACCESS read-write
    STATUS mandatory
    DESCRIPTION
        "The value specified in this object applies when the value of 
         cApsStatusMessageTransport is 'dcc', 'ip', or 'osc'. 
        
         The maximum number of APS messages that can be sent within  
         one cApsConfigMessageHolddown interval. "
    DEFVAL { 2 }
    ::= { cApsConfigExtEntry 8 }

cApsConfigMessageMaxInterval OBJECT-TYPE
    SYNTAX INTEGER(1000..120000)
--  Units
--    milliseconds
    ACCESS read-write
    STATUS mandatory
    DESCRIPTION
        "The value specified in this object applies when the value of 
         cApsStatusMessageTransport is 'dcc', 'ip', or 'osc'. 
        
         An APS message is sent unconditionally, whenever the amount 
         of time specified by this object has elapsed since the last 
         transmission of an APS message. "
    DEFVAL { 15000 }
    ::= { cApsConfigExtEntry 9 }

cApsConfigFarEndGroupName OBJECT-TYPE
    SYNTAX SnmpAdminString(SIZE(0..32))
--    Rsyntax OCTET STRING(SIZE(0..32))
    ACCESS read-write
    STATUS mandatory
    DESCRIPTION
        "The value specified in this object applies when the value of 
         cApsStatusMessageTransport is 'dcc', 'ip', or 'osc'. 
        
        APS messages, used to support bidirectional or linear  
         operation, can be sent out-of-band over an IP network. 
         In this case, this object is used to specify the a textual  
        name for the APS group at the far-end to which the message  
         is being sent. "
    ::= { cApsConfigExtEntry 10 }

cApsConfigFarEndIpAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object can be set only when the value of 
         cApsConfigMessageTransport is 'ip'. 
        
         This object specifies the type of IP address defined 
         in cApsConfigFarEndIpAddress. "
    DEFVAL { ipv4 }
    ::= { cApsConfigExtEntry 11 }

cApsConfigFarEndIpAddress OBJECT-TYPE
    SYNTAX InetAddress
--    Rsyntax OCTET STRING(SIZE(0..255))
    ACCESS read-write
    STATUS mandatory
    DESCRIPTION
        "This object can be set only when the value of 
         cApsConfigMessageTransport is 'ip'. 
        
         This object specifies the IP address of the far end, which is 
         used as the destination address in APS messages transmitted by 
         this network element. "
    ::= { cApsConfigExtEntry 12 }

cApsStatusExtTable OBJECT-TYPE
    SYNTAX SEQUENCE OF CApsStatusExtEntry
    ACCESS not-accessible
    STATUS mandatory
    DESCRIPTION
        "This table augments the cApsStatusTable. "
    ::= { cApsExtMIBObjects 3 }

cApsStatusExtEntry OBJECT-TYPE
    SYNTAX CApsStatusExtEntry
    ACCESS not-accessible
    STATUS mandatory
    DESCRIPTION
        "A conceptual row in the cApsStatusExtTable. "
    INDEX { --?? IMPLIED may cause problems
            IMPLIED cApsConfigName }
-- Augments cApsStatusEntry FROM CISCO-APS-MIB
    ::= { cApsStatusExtTable 1 }

CApsStatusExtEntry ::= SEQUENCE {
    cApsStatusCdlApsBytesRcv CdlApsBytes,
    cApsStatusCdlApsBytesTrans CdlApsBytes,
    cApsStatusMessageTransport CApsMessageTransport
    }

cApsStatusCdlApsBytesRcv OBJECT-TYPE
    SYNTAX CdlApsBytes
--    Rsyntax OCTET STRING(SIZE(2))
    ACCESS read-only
    STATUS mandatory
    DESCRIPTION
        "The current value of the APS bytes received on the 
         protection channel. This object applies only to CDL 
         interfaces. This is equivalent to  cApsStatusK1K2Rcv 
         for SONET. "
    ::= { cApsStatusExtEntry 1 }

cApsStatusCdlApsBytesTrans OBJECT-TYPE
    SYNTAX CdlApsBytes
--    Rsyntax OCTET STRING(SIZE(2))
    ACCESS read-only
    STATUS mandatory
    DESCRIPTION
        "The current value of the APS bytes transmitted on the 
         protection channel. This object applies only to CDL 
         interfaces. This is equivalent to  cApsStatusK1K2Trans 
         for SONET. "
    ::= { cApsStatusExtEntry 2 }

cApsStatusMessageTransport OBJECT-TYPE
    SYNTAX CApsMessageTransport
--    Rsyntax INTEGER {
--        none(1),
--        autoSelect(2),
--        dcc(3),
--        apsChannel(4),
--        ip(5),
--        osc(6)
--        }
    ACCESS read-only
    STATUS mandatory
    DESCRIPTION
        "This object specifies the type of transport currently being used 
         for exchange of APS protocol messages. 
        
         The value of this object is the same as the value specified in 
         the cApsConfigMessageTransport object, except when the value of 
         that object is 'autoSelect'.  In that case, the type of  
         transport that has been automatically selected is indicated  
         by this object. "
    ::= { cApsStatusExtEntry 3 }

cApsChanStatusExtTable OBJECT-TYPE
    SYNTAX SEQUENCE OF CApsChanStatusExtEntry
    ACCESS not-accessible
    STATUS mandatory
    DESCRIPTION
        "This table augments the cApsChanStatusTable. "
    ::= { cApsExtMIBObjects 4 }

cApsChanStatusExtEntry OBJECT-TYPE
    SYNTAX CApsChanStatusExtEntry
    ACCESS not-accessible
    STATUS mandatory
    DESCRIPTION
        "A conceptual row in the cApsChanStatusExtTable.  "
    INDEX { cApsChanConfigGroupName, cApsChanConfigNumber }
-- Augments cApsChanStatusEntry FROM CISCO-APS-MIB
    ::= { cApsChanStatusExtTable 1 }

CApsChanStatusExtEntry ::= SEQUENCE {
    cApsChanStatusExtRequest CApsK1K2
    }

cApsChanStatusExtRequest OBJECT-TYPE
    SYNTAX CApsK1K2
--    Rsyntax OCTET STRING(SIZE(2))
    ACCESS read-only
    STATUS mandatory
    DESCRIPTION
        "The highest priority local request for a channel in an APS  
         group. 
        
         This object uses only the 'Type of Request' part (bits 1-4)  
         of the K1 byte. "
    ::= { cApsChanStatusExtEntry 1 }

cApsChanConfigExtTable OBJECT-TYPE
    SYNTAX SEQUENCE OF CApsChanConfigExtEntry
    ACCESS not-accessible
    STATUS mandatory
    DESCRIPTION
        "This table augments the cApsChanConfigTable. "
    ::= { cApsExtMIBObjects 5 }

cApsChanConfigExtEntry OBJECT-TYPE
    SYNTAX CApsChanConfigExtEntry
    ACCESS not-accessible
    STATUS mandatory
    DESCRIPTION
        "A conceptual row in the cApsChanConfigExtTable. "
    INDEX { cApsChanConfigGroupName, cApsChanConfigNumber }
-- Augments cApsChanConfigEntry FROM CISCO-APS-MIB
    ::= { cApsChanConfigExtTable 1 }

CApsChanConfigExtEntry ::= SEQUENCE {
    cApsChanConfigReflectorMode TruthValue
    }

cApsChanConfigReflectorMode OBJECT-TYPE
    SYNTAX TruthValue
--    Rsyntax INTEGER {
--        true(1),
--        false(2)
--        }
    ACCESS read-only
    STATUS mandatory
    DESCRIPTION
        "Indicates whether the channel is in reflector mode or not. 
         Reflector mode establishes a communication channel 
         between the local PTE and the remote PTE at the other 
         end of the SONET path. 
         This object has a value of true(1), if reflector mode is 
         configured and a value of false(2), if the reflector mode 
         is not configured on the channel. 
         "
    ::= { cApsChanConfigExtEntry 1 }

cApsChanAssociationTable OBJECT-TYPE
    SYNTAX SEQUENCE OF CApsChanAssociationEntry
    ACCESS not-accessible
    STATUS mandatory
    DESCRIPTION
        "This table lists the configured IP address of the  
         protect/working interfaces. "
    ::= { cApsExtMIBObjects 6 }

cApsChanAssociationEntry OBJECT-TYPE
    SYNTAX CApsChanAssociationEntry
    ACCESS not-accessible
    STATUS mandatory
    DESCRIPTION
        "A conceptual row in cApsChanAssociationTable. "
    INDEX { cApsChanAssociationGroupName, cApsChanAssociationNumber, cApsChanAssociationMapNumber }
    ::= { cApsChanAssociationTable 1 }

CApsChanAssociationEntry ::= SEQUENCE {
    cApsChanAssociationGroupName SnmpAdminString,
    cApsChanAssociationNumber CApsChannelConfigNumber,
    cApsChanAssociationMapNumber CApsChannelConfigNumber,
    cApsChanAssociationIpAddressType InetAddressType,
    cApsChanAssociationIpAddress InetAddress
    }

cApsChanAssociationGroupName OBJECT-TYPE
    SYNTAX SnmpAdminString(SIZE(1..32))
--    Rsyntax OCTET STRING(SIZE(1..32))
    ACCESS not-accessible
    STATUS mandatory
    DESCRIPTION
        "A textual name for the APS group which this channel is 
         included in. "
    ::= { cApsChanAssociationEntry 1 }

cApsChanAssociationNumber OBJECT-TYPE
    SYNTAX CApsChannelConfigNumber
--    Rsyntax INTEGER(0..14)
    ACCESS not-accessible
    STATUS mandatory
    DESCRIPTION
        "This field is set to a unique working/protection channel  
         number within an APS group.  The value 0 indicates the 
         null channel. The values 1-14 define a working channel. "
    ::= { cApsChanAssociationEntry 2 }

cApsChanAssociationMapNumber OBJECT-TYPE
    SYNTAX CApsChannelConfigNumber
--    Rsyntax INTEGER(0..14)
    ACCESS not-accessible
    STATUS mandatory
    DESCRIPTION
        "This field is set to the associated working/protection  
         channel number corresponding to the field   
         cApsChanAssociationNumber within an APS group. 
         The value 0 indicates the null channel. The values 1-14  
         define a working channel. "
    ::= { cApsChanAssociationEntry 3 }

cApsChanAssociationIpAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        " 
         This object specifies the type of IP address defined 
         in cApsChanAssociationIpAddress. "
    ::= { cApsChanAssociationEntry 4 }

cApsChanAssociationIpAddress OBJECT-TYPE
    SYNTAX InetAddress
--    Rsyntax OCTET STRING(SIZE(0..255))
    ACCESS read-only
    STATUS mandatory
    DESCRIPTION
        "IP Address of the working/protection channel.  
         If cApsChanAssociationNumber represents a working channel  
         number, this object indicates the IP Address of the associated 
         protection channel. 
         If cApsChanAssociationNumber represents a protection channel 
         number, this object indicates the IP Address of the associated 
         working channel. "
    ::= { cApsChanAssociationEntry 5 }

cApsNotifiesEnableGroup OBJECT IDENTIFIER ::= { cApsExtGroups 1 }
-- OBJECT-GROUP
--  Status
--    mandatory
--  Descr
--    A managed object that controls the generation of APS-related  
--     notifications defined in the CISCO-APS-MIB. 
--  objects
--    cApsNotifiesEnable

cApsConfigPathExt OBJECT IDENTIFIER ::= { cApsExtGroups 2 }
-- OBJECT-GROUP
--  Status
--    mandatory
--  Descr
--    An augmentation to cApsConfigTable objects providing 
--     configuration information applicable to path APS architectures. 
--  objects
--    cApsConfigSpan

cApsConfigYcableExt OBJECT IDENTIFIER ::= { cApsExtGroups 3 }
-- OBJECT-GROUP
--  Status
--    mandatory
--  Descr
--    An augmentation to cApsConfigTable objects providing 
--     configuration information applicable to APS groups when Y cable 
--     protection is supported. 
--  objects
--    cApsConfigYcable

cApsConfigSearchExt OBJECT IDENTIFIER ::= { cApsExtGroups 4 }
-- OBJECT-GROUP
--  Status
--    mandatory
--  Descr
--    An augmentation to cApsConfigTable objects providing 
--     configuration information applicable to APS groups in which the 
--     standby interface is not monitored. 
--  objects
--    cApsConfigMinSearchUpInterval, cApsConfigMaxSearchUpInterval

cApsStatusCdlExt OBJECT IDENTIFIER ::= { cApsExtGroups 5 }
-- OBJECT-GROUP
--  Status
--    mandatory
--  Descr
--    An augmentation to cApsStatusTable objects providing status  
--     information applicable to APS groups for CDL. 
--  objects
--    cApsStatusCdlApsBytesRcv, cApsStatusCdlApsBytesTrans

cApsConfigSwitchoverTimerExt OBJECT IDENTIFIER ::= { cApsExtGroups 6 }
-- OBJECT-GROUP
--  Status
--    mandatory
--  Descr
--    An augmentation to cApsConfigTable objects providing 
--     configuration information to prevent quick successive  
--     switchovers. 
--  objects
--    cApsConfigSwitchoverEnableInterval

cApsConfigMessageExt OBJECT IDENTIFIER ::= { cApsExtGroups 7 }
-- OBJECT-GROUP
--  Status
--    mandatory
--  Descr
--    An augmentation to cApsConfigTable objects providing 
--     configuration information applicable to message 
--    transport used to exchange APS protocol messages. 
--  objects
--    cApsConfigMessageTransport, cApsConfigMessageHolddown, 
--    cApsConfigMessageHolddownCount, cApsConfigMessageMaxInterval, 
--    cApsConfigFarEndGroupName

cApsConfigIPExt OBJECT IDENTIFIER ::= { cApsExtGroups 8 }
-- OBJECT-GROUP
--  Status
--    mandatory
--  Descr
--    An augmentation to cApsConfigTable objects providing 
--     configuration information applicable to APS groups  
--     communicating over IP. 
--  objects
--    cApsConfigFarEndIpAddressType, cApsConfigFarEndIpAddress

cApsStatusMessageExt OBJECT IDENTIFIER ::= { cApsExtGroups 9 }
-- OBJECT-GROUP
--  Status
--    mandatory
--  Descr
--    An augmentation to cApsStatusTable objects providing 
--     status information applicable to message transport  
--     used to exchange APS protocol messages. 
--  objects
--    cApsStatusMessageTransport

cApsChanStatusRequestExt OBJECT IDENTIFIER ::= { cApsExtGroups 10 }
-- OBJECT-GROUP
--  Status
--    mandatory
--  Descr
--    An augmentation to cApsChanStatusTable objects providing 
--     additional status information for channels in APS groups. 
--  objects
--    cApsChanStatusExtRequest

cApsChanConfigExt OBJECT IDENTIFIER ::= { cApsExtGroups 11 }
-- OBJECT-GROUP
--  Status
--    mandatory
--  Descr
--    An augmentation to cApsChanConfigTable objects providing 
--     configuration information of channels in APS groups. 
--  objects
--    cApsChanConfigReflectorMode

cApsChanAssociationGroup OBJECT IDENTIFIER ::= { cApsExtGroups 12 }
-- OBJECT-GROUP
--  Status
--    mandatory
--  Descr
--    cApsChanAssociationTable object provides for all  
--    protection/working channels, the associated working/protection 
--    channel IP address.
--  objects
--    cApsChanAssociationIpAddressType, 
--    cApsChanAssociationIpAddress

cApsExtCompliance OBJECT IDENTIFIER ::= { cApsExtCompliances 1 }
-- MODULE-COMPLIANCE
--  Status
--    deprecated
--  Descr
--    The compliance statement for augmented APS groups.
--  Module
--    >>current<<
--   MandGroup
--    cApsNotifiesEnableGroup
--   MandGroup
--    cApsConfigPathExt
--   ObjVar
--    cApsConfigSpan
--   OptGroup
--    cApsConfigYcableExt
--   OptGroup
--    cApsConfigSearchExt
--   OptGroup
--    cApsStatusCdlExt

cApsExtCompliance2 OBJECT IDENTIFIER ::= { cApsExtCompliances 2 }
-- MODULE-COMPLIANCE
--  Status
--    mandatory
--  Descr
--    The compliance statement for augmented APS groups.
--  Module
--    >>current<<
--   MandGroup
--    cApsNotifiesEnableGroup
--   MandGroup
--    cApsConfigPathExt
--   ObjVar
--    cApsConfigSpan
--   OptGroup
--    cApsConfigYcableExt
--   OptGroup
--    cApsConfigSearchExt
--   OptGroup
--    cApsStatusCdlExt
--   OptGroup
--    cApsConfigMessageExt
--   OptGroup
--    cApsConfigSwitchoverTimerExt
--   ObjVar
--    cApsConfigMessageTransport
--   OptGroup
--    cApsConfigIPExt
--   OptGroup
--    cApsStatusMessageExt
--   OptGroup
--    cApsChanStatusRequestExt

cApsExtComplianceRev1 OBJECT IDENTIFIER ::= { cApsExtCompliances 3 }
-- MODULE-COMPLIANCE
--  Status
--    mandatory
--  Descr
--    The compliance statement for augmented APS groups. 
--  Module
--    >>current<<
--   MandGroup
--    cApsChanConfigExt
--   MandGroup
--    cApsChanAssociationGroup


END
