-- MIB file created 14-Jan-2014 22:58:16, by
--   SMICng version 2.2.11-beta(PRO)(Solaris), January 20, 2001. Enterprise key cisco.com

CISCO-LAG-MIB DEFINITIONS ::= BEGIN

-- From file: "CISCO-LAG-MIB.my"
-- Compile options "4 7 F H N W 03 06 0B 0G 0N 0T"

IMPORTS
    TruthValue
            FROM SNMPv2-TC-v1
    dot3adAggPortIndex, dot3adAggIndex
            FROM IEEE8023-LAG-MIB
    CiscoInterfaceIndexList
            FROM CISCO-TC
    ifIndex
            FROM IF-MIB
    ciscoMgmt
            FROM CISCO-SMI
    Gauge
            FROM RFC1155-SMI
    OBJECT-TYPE
            FROM RFC-1212;

ciscoLagMIB OBJECT IDENTIFIER ::= { ciscoMgmt 225 }
-- MODULE-IDENTITY
--  LastUpdated
--    201401140000Z
--  OrgName
--    Cisco Systems, Inc.
--  ContactInfo
--    Cisco Systems
--    Customer Service
--    
--    Postal: 170 W Tasman Drive
--    San Jose, CA  95134
--    USA
--    
--    Tel: +1 800 553-NETS
--    
--    E-mail:  cs-etherchan@cisco.com
--     cs-lan-switch-snmp@cisco.com
--  Descr
--    Cisco Link Aggregation module for managing IEEE Std
--    802.3ad.
--    
--    This MIB provides Link Aggregation information that are
--    either excluded by IEEE Std 802.3ad (IEEE8023-LAG-MIB)
--    or specific to Cisco products.
--  RevDate
--    201401140000Z
--  RevDescr
--    Added clagAggPortListInterfaceIndexGroup.
--  RevDate
--    201010200000Z
--  RevDescr
--    Added new enum values vlanIp(5) and ipPort(6) to
--     ClagDistributionProtocol textual convention.
--  RevDate
--    200911190000Z
--  RevDescr
--    Added clagAggRateGroup, clagAggChannelIfLacpGroup,
--    clagAggChannelIfHashDistMethodGroup, clagAggChannelIfMinLinkGroup
--    and clagAggHashDistGlobalGroup.
--  RevDate
--    200801080000Z
--  RevDescr
--    Modified the description of clagAggPortListPorts.
--  RevDate
--    200606210000Z
--  RevDescr
--    Added clagAggMaxAggregatorsGroup and modified the
--    description of clagAggPortListPorts.
--  RevDate
--    200406110000Z
--  RevDescr
--    Added clagAggPortListTable.
--  RevDate
--    200212130000Z
--  RevDescr
--    Added a new value vlanIpPort(4) in TEXTUAL-CONVENTION
--    ClagDistributionProtocol.
--    Added a new object clagAggDistributionMplsProtocol.
--  RevDate
--    200201020000Z
--  RevDescr
--    Modified Description of clagAggDistributionProtocol.
--  RevDate
--    200110230000Z
--  RevDescr
--    Initial version of this MIB module.
--    Support Distribution configuration for LACP, Aggregation 
--    protocol control, and  Administrative status for LACP.

clagMIBObjects  OBJECT IDENTIFIER ::= { ciscoLagMIB 1 }
clagGlobalConfigObjects OBJECT IDENTIFIER ::= { clagMIBObjects 1 }
clagAgg         OBJECT IDENTIFIER ::= { clagMIBObjects 2 }
clagAggPort     OBJECT IDENTIFIER ::= { clagMIBObjects 3 }
clagAggPortList OBJECT IDENTIFIER ::= { clagMIBObjects 4 }
clagAggChannelIntf OBJECT IDENTIFIER ::= { clagMIBObjects 5 }
clagMIBNotifications OBJECT IDENTIFIER ::= { ciscoLagMIB 2 }
clagMIBConformance OBJECT IDENTIFIER ::= { ciscoLagMIB 3 }
clagMIBCompliances OBJECT IDENTIFIER ::= { clagMIBConformance 1 }
clagMIBGroups   OBJECT IDENTIFIER ::= { clagMIBConformance 2 }

ClagDistributionProtocol ::= INTEGER {
        ip(1),
        mac(2),
        port(3),
        vlanIpPort(4),
        vlanIp(5),
        ipPort(6)
        }
-- TEXTUAL-CONVENTION
--  Status
--    mandatory
--  Descr
--    An enumerated type for all the supported load balancing
--    algorithms used on the port channel interface to distribute 
--    outgoing data frames among its component interaces, such 
--    as IP address.  
--    
--    ip(1)               IP address
--    mac(2)              MAC address 
--    port(3)             port number
--    vlanIpPort(4)       vlan number, IP address and
--                        port number
--    vlanIp(5)           VLAN number and IP address
--    ipPort(6)           IP address and port number

ClagDistributionAddressMode ::= INTEGER {
        source(1),
        destination(2),
        both(3)
        }
-- TEXTUAL-CONVENTION
--  Status
--    mandatory
--  Descr
--    An enumerated type for all the supported load
--    balancing address modes to distribute traffic
--    across multiple links.  The address mode can be 
--    source, destination, or both used on this port 
--    channel interface to distribute outgoing data frames 
--    among its component interfaces. 
--    
--    source(1)         Source address.
--    destination(2)    Destination address.
--    both(3)           both, Source and Destination.

ClagDistributionMplsProtocol ::= INTEGER {
        label(1),
        labelIp(2)
        }
-- TEXTUAL-CONVENTION
--  Status
--    mandatory
--  Descr
--    An enumerated type for all the supported load balancing
--    algorithms used on the port channel interface to distribute 
--    outgoing MPLS (Multi-Protocol Label Switching) data 
--    frames among its component interfaces, such as 
--    MPLS label.
--    
--    label(1)            MPLS label
--    labelIp(2)          MPLS label or IP address

ClagAggregationProtocol ::= INTEGER {
        lacp(1),
        pagp(2)
        }
-- TEXTUAL-CONVENTION
--  Status
--    mandatory
--  Descr
--    An enumerated type for all the supported aggregation
--    protocols.
--    
--    lacp(1)     Link Aggregation Control Protocol(LACP),
--                IEEE 802.3ad
--    pagp(2)     Port Aggregation Protocol

ClagPortAdminStatus ::= INTEGER {
        off(1),
        on(2),
        active(3),
        passive(4)
        }
-- TEXTUAL-CONVENTION
--  Status
--    mandatory
--  Descr
--    An enumerated type for all the LACP administrative states on
--    a particular aggregation port.
--    
--    off(1)          No LACP involved on the aggregation port.
--    
--    on(2)           The aggregation port always join link
--                    aggregation whithout any LACP protocol
--                    involved.
--    
--    active(3)       Active LACP indicates the port's preference
--                    to participate in the protocol regardless of
--                    Partner's control value.
--    
--    passive(4)      Passive indicates the port's preference for
--                    not transmitting LACP PDU unless its Partner's
--                    control value is Active LACP.

clagAggDistributionProtocol OBJECT-TYPE
    SYNTAX ClagDistributionProtocol
--    Rsyntax INTEGER {
--        ip(1),
--        mac(2),
--        port(3),
--        vlanIpPort(4),
--        vlanIp(5),
--        ipPort(6)
--        }
    ACCESS read-write
    STATUS mandatory
    DESCRIPTION
        "This object controls the load balancing algorithms
        used on this port channel interface to distribute outgoing 
        data frames among its component interfaces."
    ::= { clagGlobalConfigObjects 1 }

clagAggDistributionAddressMode OBJECT-TYPE
    SYNTAX ClagDistributionAddressMode
--    Rsyntax INTEGER {
--        source(1),
--        destination(2),
--        both(3)
--        }
    ACCESS read-write
    STATUS mandatory
    DESCRIPTION
        "The load balancing address mode for the device."
    ::= { clagGlobalConfigObjects 2 }

clagAggDistributionMplsProtocol OBJECT-TYPE
    SYNTAX ClagDistributionMplsProtocol
--    Rsyntax INTEGER {
--        label(1),
--        labelIp(2)
--        }
    ACCESS read-write
    STATUS mandatory
    DESCRIPTION
        "This object controls the load balancing algorithms
        used on this port channel interface to distribute 
        outgoing MPLS data frames among its component interfaces.
        
        This object is only instantiated on platforms which 
        support aggregation load balancing for MPLS packets."
    ::= { clagGlobalConfigObjects 3 }

clagAggMaxAggregators OBJECT-TYPE
    SYNTAX Gauge
    ACCESS read-only
    STATUS mandatory
    DESCRIPTION
        "This object indicates the maximum number of aggregators
        supported by the device."
    ::= { clagGlobalConfigObjects 4 }

clagAggHashDistMethodGlobalConfig OBJECT-TYPE
    SYNTAX INTEGER {
        adaptive(1),
        fixed(2)
        }
    ACCESS read-write
    STATUS mandatory
    DESCRIPTION
        "Specifies the global configuration for hash
        distribution method applied on a port channel 
        interface among its channel members.
        
        adaptive(1)  :  Adaptive hash distribution for the bundle
                        among port channel members.
        fixed(2)     :  Fixed hash distribution for the bundle
                        among port channel members."
    ::= { clagGlobalConfigObjects 5 }

clagAggProtocolTable OBJECT-TYPE
    SYNTAX SEQUENCE OF ClagAggProtocolEntry
    ACCESS not-accessible
    STATUS mandatory
    DESCRIPTION
        "A table that contains protocol information about every
        interface which supports link aggregation."
    ::= { clagAgg 1 }

clagAggProtocolEntry OBJECT-TYPE
    SYNTAX ClagAggProtocolEntry
    ACCESS not-accessible
    STATUS mandatory
    DESCRIPTION
        "Entry containing aggregation protocol type for a
        particular interface.  An entry is created in this
        table when its associated ifEntry is created and that 
        interface supports link aggregation.  The entry of this
        table is deleted when the associated ifEntry is removed."
    INDEX { ifIndex }
    ::= { clagAggProtocolTable 1 }

ClagAggProtocolEntry ::= SEQUENCE {
    clagAggProtocolType ClagAggregationProtocol
    }

clagAggProtocolType OBJECT-TYPE
    SYNTAX ClagAggregationProtocol
--    Rsyntax INTEGER {
--        lacp(1),
--        pagp(2)
--        }
    ACCESS read-write
    STATUS mandatory
    DESCRIPTION
        "The aggregation protocol type for the interface.
        
        On some platforms, aggregation protocol may be assigned per
        group.  The group can be a collection of the ports which belong
        to a module or system.  If the aggregation protocol is assigned
        to any of the ports in such group then the aggregation protocol
        will apply to all ports in the same group.
        
        On some platforms, aggregation protocol type  can be assigned
        per aggregator.  If multiple ports belong to a aggregator,
        the aggregation protocol assigned to any of the ports in such
        aggregator will apply to all ports in the same."
    ::= { clagAggProtocolEntry 1 }

clagAggPortTable OBJECT-TYPE
    SYNTAX SEQUENCE OF ClagAggPortEntry
    ACCESS not-accessible
    STATUS mandatory
    DESCRIPTION
        "A table that contains information about every
        aggregation port that is associated with this system.
        This table contains additional objects for the
        dot3adAggPortTable."
    REFERENCE
        "IEEE 802.3 Subclause 30.7.2"
    ::= { clagAggPort 1 }

clagAggPortEntry OBJECT-TYPE
    SYNTAX ClagAggPortEntry
    ACCESS not-accessible
    STATUS mandatory
    DESCRIPTION
        "An entry containing additional management information
        applicable to a particular aggregation port."
    INDEX { dot3adAggPortIndex }
-- Augments dot3adAggPortEntry FROM IEEE8023-LAG-MIB
    ::= { clagAggPortTable 1 }

ClagAggPortEntry ::= SEQUENCE {
    clagAggPortAdminStatus ClagPortAdminStatus,
    clagAggPortRate INTEGER
    }

clagAggPortAdminStatus OBJECT-TYPE
    SYNTAX ClagPortAdminStatus
--    Rsyntax INTEGER {
--        off(1),
--        on(2),
--        active(3),
--        passive(4)
--        }
    ACCESS read-write
    STATUS mandatory
    DESCRIPTION
        "The administrative status of the LACP protocol on this
        aggregation port."
    ::= { clagAggPortEntry 1 }

clagAggPortRate OBJECT-TYPE
    SYNTAX INTEGER {
        fast(1),
        normal(2)
        }
    ACCESS read-write
    STATUS mandatory
    DESCRIPTION
        "Specifies the requested exchange rate of LACP packets
        on this interface.
        fast(1)  :    The device requests its peers to send LACP packets 
                      at fast rate to this interface.
        normal(2):    The decice requests its peers to send LACP packets
                      at normal rate to this interface."
    ::= { clagAggPortEntry 2 }

clagAggPortListTable OBJECT-TYPE
    SYNTAX SEQUENCE OF ClagAggPortListEntry
    ACCESS not-accessible
    STATUS mandatory
    DESCRIPTION
        "This table augments the dot3adAggPortListTable and
        provides the complete list of ports associated with
        each Aggregator."
    REFERENCE
        "IEEE 802.3 Subclause 30.7.1.1.30"
    ::= { clagAggPortList 1 }

clagAggPortListEntry OBJECT-TYPE
    SYNTAX ClagAggPortListEntry
    ACCESS not-accessible
    STATUS mandatory
    DESCRIPTION
        "A list of the ports associated with a given Aggregator."
    INDEX { dot3adAggIndex }
-- Augments dot3adAggPortListEntry FROM IEEE8023-LAG-MIB
    ::= { clagAggPortListTable 1 }

ClagAggPortListEntry ::= SEQUENCE {
    clagAggPortListPorts OCTET STRING,
    clagAggPortListInterfaceIndexList CiscoInterfaceIndexList
    }

clagAggPortListPorts OBJECT-TYPE
    SYNTAX OCTET STRING(SIZE(2..256))
    ACCESS read-only
    STATUS mandatory
    DESCRIPTION
        "This object contains a list of ports currently associated
        with this Aggregator in the format of
        '[number_of_ports][cieIfDot1dBaseMappingPort1][...]
         [cieIfDot1dBaseMappingPortn]'
        
        where
        [number_of_ports] is of size 2 octet and indicates
        the number of ports contains in this object. It
        also indicates the number of cieIfDot1dBaseMappingPort field
        following this field. 
        
        [cieIfDot1dBaseMappingPort'n'] is the value of 
        cieIfDot1dBaseMappingPort of the 'n' port associated with this
        Aggregation and has size of 2 octets where n is up to
        [number_of_ports]."
    REFERENCE
        "IEEE 802.3 Subclause 30.7.1.1.30"
    ::= { clagAggPortListEntry 1 }

clagAggPortListInterfaceIndexList OBJECT-TYPE
    SYNTAX CiscoInterfaceIndexList
--    Rsyntax OCTET STRING(SIZE(0..256))
    ACCESS read-only
    STATUS mandatory
    DESCRIPTION
        "This object contains a list of ports currently associated
        with this Aggregator in the format of CiscoInterfaceIndexList."
    REFERENCE
        "IEEE 802.3 Subclause 30.7.1.1.30"
    ::= { clagAggPortListEntry 2 }

clagAggChannelIfTable OBJECT-TYPE
    SYNTAX SEQUENCE OF ClagAggChannelIfEntry
    ACCESS not-accessible
    STATUS mandatory
    DESCRIPTION
        "A table providing port channel
        configuration information for port channel
        interfaces identified by ifIndex."
    ::= { clagAggChannelIntf 1 }

clagAggChannelIfEntry OBJECT-TYPE
    SYNTAX ClagAggChannelIfEntry
    ACCESS not-accessible
    STATUS mandatory
    DESCRIPTION
        "An entry containing port channel
        configuration information for port 
        channel interfaces."
    INDEX { ifIndex }
    ::= { clagAggChannelIfTable 1 }

ClagAggChannelIfEntry ::= SEQUENCE {
    clagAggChannelIfFastSwitchOver TruthValue,
    clagAggChannelIfMaxBundle Gauge,
    clagAggChannelIfMinLink Gauge,
    clagAggChannelIfHashDistAdminMethod INTEGER,
    clagAggChannelIfHashDistOperMethod INTEGER
    }

clagAggChannelIfFastSwitchOver OBJECT-TYPE
    SYNTAX TruthValue
--    Rsyntax INTEGER {
--        true(1),
--        false(2)
--        }
    ACCESS read-write
    STATUS mandatory
    DESCRIPTION
        "Specifies whether LACP protocol fast switchover
        mode is enabled on this port channel interface
        or not."
    ::= { clagAggChannelIfEntry 1 }

clagAggChannelIfMaxBundle OBJECT-TYPE
    SYNTAX Gauge(1..4294967295)
    ACCESS read-write
    STATUS mandatory
    DESCRIPTION
        "Specifies the maximum number of member
        ports that can be bundled on this port
        channel interface for LACP protocol."
    ::= { clagAggChannelIfEntry 2 }

clagAggChannelIfMinLink OBJECT-TYPE
    SYNTAX Gauge
    ACCESS read-write
    STATUS mandatory
    DESCRIPTION
        "Specifies the minimum number of bundled member ports that are
        needed in order for this port channel interface to be
        operational.
        A value of zero for this object indicates that no minimum
        number of bundled member ports are required for this port
        channel interface to be operational."
    ::= { clagAggChannelIfEntry 3 }

clagAggChannelIfHashDistAdminMethod OBJECT-TYPE
    SYNTAX INTEGER {
        none(1),
        adaptive(2),
        fixed(3)
        }
    ACCESS read-write
    STATUS mandatory
    DESCRIPTION
        "Specifies the hash distribution method that is administratively
        configured on this port channel interface upon its channel 
        membership transition event. 
        
        none(1)      :  Hash distribution algorithm on this 
                        port channel interface is not specifically 
                        configured and global configuration of 
                        clagAggHashDistMethodGlobalConfig will
                        be applied on this port channel interface.
        adaptive(2)  :  Adaptive hash distribution for this port 
                        channel interface among its channel members.
        fixed(3)     :  Fixed hash distribution for this port channel
                        interface among its channel members."
    ::= { clagAggChannelIfEntry 4 }

clagAggChannelIfHashDistOperMethod OBJECT-TYPE
    SYNTAX INTEGER {
        other(1),
        adaptive(2),
        fixed(3)
        }
    ACCESS read-only
    STATUS mandatory
    DESCRIPTION
        "Specifies the operational hash distribution method
        for this port channel interface among the port channel members.
        
        other(1)        : None of the following. 
        adaptive(2)     : Adaptive hash distribution for the 
                          port channel interface among its 
                          channel members.
        fixed(3)        : Fixed hash distribution for the port
                          channel among channel members."
    ::= { clagAggChannelIfEntry 5 }

clagAggProtocolGroup OBJECT IDENTIFIER ::= { clagMIBGroups 1 }
-- OBJECT-GROUP
--  Status
--    mandatory
--  Descr
--    The object that provide aggregation protocol type of an
--    interface. These are additional to the IEEE Std 802.3ad
--    MIB.
--  objects
--    clagAggProtocolType

clagAggPortGroup OBJECT IDENTIFIER ::= { clagMIBGroups 2 }
-- OBJECT-GROUP
--  Status
--    mandatory
--  Descr
--    A collection of objects that provide admin status
--    about an aggregation port.  These are additional to the
--    IEEE Std 802.3ad MIB.
--  objects
--    clagAggPortAdminStatus

clagAggDistributionGroup OBJECT IDENTIFIER ::= { clagMIBGroups 3 }
-- OBJECT-GROUP
--  Status
--    mandatory
--  Descr
--    A collection of objects that provide the load balancing
--    information for an aggregator.  These are additional to
--    the IEEE Std 802.3ad MIB.
--  objects
--    clagAggDistributionProtocol, clagAggDistributionAddressMode

clagAggDistributionMplsGroup OBJECT IDENTIFIER ::= { clagMIBGroups 4 }
-- OBJECT-GROUP
--  Status
--    mandatory
--  Descr
--    A collection of objects that provide the load balancing
--    information for an aggregator for MPLS packets.  
--    These are additional to the IEEE Std 802.3ad MIB.
--  objects
--    clagAggDistributionMplsProtocol

clagAggPortListGroup OBJECT IDENTIFIER ::= { clagMIBGroups 5 }
-- OBJECT-GROUP
--  Status
--    mandatory
--  Descr
--    A collection of object that provides information about
--    ports in an aggregation.
--  objects
--    clagAggPortListPorts

clagAggMaxAggregatorsGroup OBJECT IDENTIFIER ::= { clagMIBGroups 6 }
-- OBJECT-GROUP
--  Status
--    mandatory
--  Descr
--    A collection of object that provides information about
--    the maximum number of aggregators supported by the 
--    device.
--  objects
--    clagAggMaxAggregators

clagAggRateGroup OBJECT IDENTIFIER ::= { clagMIBGroups 7 }
-- OBJECT-GROUP
--  Status
--    mandatory
--  Descr
--    A collection of object that provides information about
--    the rate at which LACP packets are ingressed on 
--    interfaces.
--  objects
--    clagAggPortRate

clagAggChannelIfLacpGroup OBJECT IDENTIFIER ::= { clagMIBGroups 8 }
-- OBJECT-GROUP
--  Status
--    mandatory
--  Descr
--    A collection of objects that provides information about
--    the LACP protocol configurations for port channel
--    interfaces.
--  objects
--    clagAggChannelIfFastSwitchOver, clagAggChannelIfMaxBundle

clagAggChannelIfHashDistMethodGroup OBJECT IDENTIFIER ::= { clagMIBGroups 9 }
-- OBJECT-GROUP
--  Status
--    mandatory
--  Descr
--    A collection of objects that provides information about
--    the port channel configurations of hash distribution
--    method on port channel interfaces.
--  objects
--    clagAggChannelIfHashDistAdminMethod, 
--    clagAggChannelIfHashDistOperMethod

clagAggHashDistGlobalGroup OBJECT IDENTIFIER ::= { clagMIBGroups 10 }
-- OBJECT-GROUP
--  Status
--    mandatory
--  Descr
--    A collection of object that provides information about global
--    configuration of hash distribution method on port channel 
--    interface.
--  objects
--    clagAggHashDistMethodGlobalConfig

clagAggChannelIfMinLinkGroup OBJECT IDENTIFIER ::= { clagMIBGroups 11 }
-- OBJECT-GROUP
--  Status
--    mandatory
--  Descr
--    A collection of objects that provides information about
--    the minimum link configurations for port channel
--    interfaces.
--  objects
--    clagAggChannelIfMinLink

clagAggPortListInterfaceIndexGroup OBJECT IDENTIFIER ::= { clagMIBGroups 12 }
-- OBJECT-GROUP
--  Status
--    mandatory
--  Descr
--    A collection of objects that provides information about
--     ports in an aggregation in the format of 
--     CiscoInterfaceIndexList.
--  objects
--    clagAggPortListInterfaceIndexList

clagMIBCompliance OBJECT IDENTIFIER ::= { clagMIBCompliances 1 }
-- MODULE-COMPLIANCE
--  Status
--    deprecated
--  Descr
--    The compliance statement for entities which implement
--    the Cisco Link Aggregation MIB
--  Module
--    >>current<<
--   MandGroup
--    clagAggProtocolGroup
--   MandGroup
--    clagAggPortGroup
--   OptGroup
--    clagAggDistributionGroup
--   ObjVar
--    clagAggProtocolType
--   ObjVar
--    clagAggPortAdminStatus

clagMIBCompliance2 OBJECT IDENTIFIER ::= { clagMIBCompliances 2 }
-- MODULE-COMPLIANCE
--  Status
--    deprecated
--  Descr
--    The compliance statement for entities which implement
--    the Cisco Link Aggregation MIB
--  Module
--    >>current<<
--   MandGroup
--    clagAggProtocolGroup
--   MandGroup
--    clagAggPortGroup
--   OptGroup
--    clagAggDistributionGroup
--   OptGroup
--    clagAggDistributionMplsGroup
--   ObjVar
--    clagAggProtocolType
--   ObjVar
--    clagAggPortAdminStatus

clagMIBCompliance3 OBJECT IDENTIFIER ::= { clagMIBCompliances 3 }
-- MODULE-COMPLIANCE
--  Status
--    deprecated
--  Descr
--    The compliance statement for entities which implement
--    the Cisco Link Aggregation MIB
--  Module
--    >>current<<
--   MandGroup
--    clagAggProtocolGroup
--   MandGroup
--    clagAggPortGroup
--   OptGroup
--    clagAggDistributionGroup
--   OptGroup
--    clagAggDistributionMplsGroup
--   OptGroup
--    clagAggPortListGroup
--   ObjVar
--    clagAggProtocolType
--   ObjVar
--    clagAggPortAdminStatus

clagMIBCompliance4 OBJECT IDENTIFIER ::= { clagMIBCompliances 4 }
-- MODULE-COMPLIANCE
--  Status
--    deprecated
--  Descr
--    The compliance statement for entities which implement
--    the Cisco Link Aggregation MIB
--  Module
--    >>current<<
--   MandGroup
--    clagAggProtocolGroup
--   MandGroup
--    clagAggPortGroup
--   OptGroup
--    clagAggDistributionGroup
--   OptGroup
--    clagAggDistributionMplsGroup
--   OptGroup
--    clagAggPortListGroup
--   OptGroup
--    clagAggMaxAggregatorsGroup
--   ObjVar
--    clagAggProtocolType
--   ObjVar
--    clagAggPortAdminStatus

clagMIBCompliance5 OBJECT IDENTIFIER ::= { clagMIBCompliances 5 }
-- MODULE-COMPLIANCE
--  Status
--    deprecated
--  Descr
--    The compliance statement for entities which implement
--    the Cisco Link Aggregation MIB
--  Module
--    >>current<<
--   MandGroup
--    clagAggProtocolGroup
--   MandGroup
--    clagAggPortGroup
--   OptGroup
--    clagAggDistributionGroup
--   OptGroup
--    clagAggDistributionMplsGroup
--   OptGroup
--    clagAggPortListGroup
--   OptGroup
--    clagAggMaxAggregatorsGroup
--   OptGroup
--    clagAggRateGroup
--   OptGroup
--    clagAggChannelIfLacpGroup
--   OptGroup
--    clagAggChannelIfHashDistMethodGroup
--   OptGroup
--    clagAggHashDistGlobalGroup
--   OptGroup
--    clagAggChannelIfMinLinkGroup
--   ObjVar
--    clagAggDistributionProtocol
--   ObjVar
--    clagAggDistributionAddressMode
--   ObjVar
--    clagAggDistributionMplsProtocol
--   ObjVar
--    clagAggHashDistMethodGlobalConfig
--   ObjVar
--    clagAggProtocolType
--   ObjVar
--    clagAggPortAdminStatus
--   ObjVar
--    clagAggPortRate
--   ObjVar
--    clagAggChannelIfFastSwitchOver
--   ObjVar
--    clagAggChannelIfMaxBundle
--   ObjVar
--    clagAggChannelIfMinLink
--   ObjVar
--    clagAggChannelIfHashDistAdminMethod

clagMIBCompliance6 OBJECT IDENTIFIER ::= { clagMIBCompliances 6 }
-- MODULE-COMPLIANCE
--  Status
--    mandatory
--  Descr
--    The compliance statement for entities which implement
--    the Cisco Link Aggregation MIB
--  Module
--    >>current<<
--   MandGroup
--    clagAggProtocolGroup
--   MandGroup
--    clagAggPortGroup
--   OptGroup
--    clagAggDistributionGroup
--   OptGroup
--    clagAggDistributionMplsGroup
--   OptGroup
--    clagAggPortListGroup
--   OptGroup
--    clagAggMaxAggregatorsGroup
--   OptGroup
--    clagAggRateGroup
--   OptGroup
--    clagAggChannelIfLacpGroup
--   OptGroup
--    clagAggChannelIfHashDistMethodGroup
--   OptGroup
--    clagAggHashDistGlobalGroup
--   OptGroup
--    clagAggChannelIfMinLinkGroup
--   OptGroup
--    clagAggPortListInterfaceIndexGroup
--   ObjVar
--    clagAggDistributionProtocol
--   ObjVar
--    clagAggDistributionAddressMode
--   ObjVar
--    clagAggDistributionMplsProtocol
--   ObjVar
--    clagAggHashDistMethodGlobalConfig
--   ObjVar
--    clagAggProtocolType
--   ObjVar
--    clagAggPortAdminStatus
--   ObjVar
--    clagAggPortRate
--   ObjVar
--    clagAggChannelIfFastSwitchOver
--   ObjVar
--    clagAggChannelIfMaxBundle
--   ObjVar
--    clagAggChannelIfMinLink
--   ObjVar
--    clagAggChannelIfHashDistAdminMethod


END
