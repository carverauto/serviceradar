-- MIB file created 03-Dec-2012 13:54:54, by
--   SMICng version 2.2.11-beta(PRO)(Solaris), January 20, 2001. Enterprise key cisco.com

CISCO-MPLS-LSR-EXT-STD-MIB DEFINITIONS ::= BEGIN

-- From file: "CISCO-MPLS-LSR-EXT-STD-MIB.my"
-- Compile options "4 7 F H N W 03 06 0B 0G 0N 0T"

IMPORTS
    RowPointer
            FROM SNMPv2-TC-v1
    mplsXCIndex, mplsXCInSegmentIndex, mplsXCOutSegmentIndex, 
    mplsInSegmentGroup, mplsOutSegmentGroup, mplsXCGroup, 
    mplsPerfGroup, mplsLsrNotificationGroup
            FROM MPLS-LSR-STD-MIB
    ciscoExperiment
            FROM CISCO-SMI
    OBJECT-TYPE
            FROM RFC-1212;

cmplsLsrExtStdMIB OBJECT IDENTIFIER ::= { ciscoExperiment 145 }
-- MODULE-IDENTITY
--  LastUpdated
--    201204300000Z
--  OrgName
--    Multiprotocol Label Switching (MPLS) Working Group
--  ContactInfo
--    Venkatesan Mahalingam
--    Dell Inc,
--    350 Holger way, San Jose, CA, USA
--    Email: venkat.mahalingams@gmail.com
--    
--    Kannan KV Sampath
--    Aricent,
--    India
--    Email: Kannan.Sampath@aricent.com
--    
--    Sam Aldrin
--    Huawei Technologies
--    2330 Central Express Way,
--    Santa Clara, CA 95051, USA
--    
--    Email:  aldrin.ietf@gmail.com
--    
--    Thomas D. Nadeau
--    CA Technologies
--    273 Corporate Drive, Portsmouth, NH, USA
--    Email: thomas.nadeau@ca.com
--  Descr
--    Copyright (c) 2012 IETF Trust and the persons identified
--    as the document authors.  All rights reserved.
--    
--    This MIB module contains generic object definitions for
--    
--    
--    MPLS LSR in transport networks.
--  RevDate
--    201202220000Z
--  RevDescr
--    MPLS LSR specific mib objects extension

cmplsLsrExtNotifications OBJECT IDENTIFIER ::= { cmplsLsrExtStdMIB 0 }
cmplsLsrExtObjects OBJECT IDENTIFIER ::= { cmplsLsrExtStdMIB 1 }
cmplsLsrExtConformance OBJECT IDENTIFIER ::= { cmplsLsrExtStdMIB 2 }
cmplsLsrExtGroups OBJECT IDENTIFIER ::= { cmplsLsrExtConformance 1 }
cmplsLsrExtCompliances OBJECT IDENTIFIER ::= { cmplsLsrExtConformance 2 }

cmplsXCExtTable OBJECT-TYPE
    SYNTAX SEQUENCE OF CmplsXCExtEntry
    ACCESS not-accessible
    STATUS mandatory
    DESCRIPTION
        "This table sparse augments the mplsXCTable of
        MPLS-LSR-STD-MIB [RFC3813] to provide MPLS-TP specific
        information about associated tunnel information"
    REFERENCE
        "1. Multiprotocol Label Switching (MPLS) Label Switching
              Router (LSR) Management Information Base (MIB), RFC 3813."
    ::= { cmplsLsrExtObjects 1 }

cmplsXCExtEntry OBJECT-TYPE
    SYNTAX CmplsXCExtEntry
    ACCESS not-accessible
    STATUS mandatory
    DESCRIPTION
        "An entry in this table extends the cross connect
        information represented by an entry in
        the mplsXCTable in MPLS-LSR-STD-MIB [RFC3813] through
        a sparse augmentation.  An entry can be created by
        a network administrator via SNMP SET commands, or in
        response to signaling protocol events."
    REFERENCE
        "1. Multiprotocol Label Switching (MPLS) Label Switching
              Router (LSR) Management Information Base (MIB), RFC 3813."
    INDEX { mplsXCIndex, mplsXCInSegmentIndex, mplsXCOutSegmentIndex }
    ::= { cmplsXCExtTable 1 }

CmplsXCExtEntry ::= SEQUENCE {
    cmplsXCExtTunnelPointer RowPointer,
    cmplsXCOppositeDirXCPtr RowPointer
    }

cmplsXCExtTunnelPointer OBJECT-TYPE
    SYNTAX RowPointer
--    Rsyntax OBJECT IDENTIFIER
    ACCESS read-write
    STATUS mandatory
    DESCRIPTION
        "This object indicates the back pointer to the tunnel
        entry segment.  This object cannot be modified if
        mplsXCRowStatus for the corresponding entry in the
        mplsXCTable is active(1)."
    REFERENCE
        "1. Multiprotocol Label Switching (MPLS) Label Switching
              Router (LSR) Management Information Base (MIB), RFC 3813."
    ::= { cmplsXCExtEntry 1 }

cmplsXCOppositeDirXCPtr OBJECT-TYPE
    SYNTAX RowPointer
--    Rsyntax OBJECT IDENTIFIER
    ACCESS read-write
    STATUS mandatory
    DESCRIPTION
        "This object indicates the pointer to the opposite
        direction XC entry.  This object cannot be modified if
        mplsXCRowStatus for the corresponding entry in the
        mplsXCTable is active(1)."
    REFERENCE
        "1. Multiprotocol Label Switching (MPLS) Label Switching
              Router (LSR) Management Information Base (MIB), RFC 3813."
    ::= { cmplsXCExtEntry 2 }

cmplsXCExtGroup OBJECT IDENTIFIER ::= { cmplsLsrExtGroups 1 }
-- OBJECT-GROUP
--  Status
--    mandatory
--  Descr
--    This object should be supported in order to access
--    the tunnel entry from XC entry.
--  objects
--    cmplsXCExtTunnelPointer, cmplsXCOppositeDirXCPtr

cmplsLsrExtModuleFullCompliance OBJECT IDENTIFIER ::= { cmplsLsrExtCompliances 1 }
-- MODULE-COMPLIANCE
--  Status
--    mandatory
--  Descr
--    Compliance statement for agents that provide full support
--    
--    for MPLS-LSR-EXT-STD-MIB.
--    The mandatory group has to be implemented by all LSRs
--    that originate, terminate, or act as transit for
--    TE-LSPs/tunnels.
--    In addition, depending on the type of tunnels supported,
--    other groups become mandatory as explained below.
--  Module
--    MPLS-LSR-STD-MIB
--   MandGroup
--    mplsInSegmentGroup
--   MandGroup
--    mplsOutSegmentGroup
--   MandGroup
--    mplsXCGroup
--   MandGroup
--    mplsPerfGroup
--   MandGroup
--    mplsLsrNotificationGroup
--  Module
--    >>current<<
--   MandGroup
--    cmplsXCExtGroup
--   ObjVar
--    cmplsXCExtTunnelPointer

cmplsLsrExtModuleReadOnlyCompliance OBJECT IDENTIFIER ::= { cmplsLsrExtCompliances 2 }
-- MODULE-COMPLIANCE
--  Status
--    mandatory
--  Descr
--    Compliance requirement for implementations that only
--    provide read-only support for MPLS-LSR-EXT-STD-MIB.
--    Such devices can then be monitored but cannot be
--    configured using this MIB module.
--  Module
--    MPLS-LSR-STD-MIB
--   MandGroup
--    mplsInterfaceGroup
--   MandGroup
--    mplsInSegmentGroup
--   MandGroup
--    mplsOutSegmentGroup
--   MandGroup
--    mplsXCGroup
--   MandGroup
--    mplsPerfGroup
--  Module
--    >>current<<
--   MandGroup
--    cmplsXCExtGroup
--   ObjVar
--    cmplsXCExtTunnelPointer
--   ObjVar
--    cmplsXCOppositeDirXCPtr


END
