-- MIB file created 21-Apr-2003 16:47:17, by
--   SMICng version 2.2.11-beta(PRO)(Solaris), January 20, 2001. Enterprise key cisco.com

CISCO-MGX82XX-ATM-UNI-PORT-MIB DEFINITIONS ::= BEGIN

-- From file: "CISCO-MGX82XX-ATM-UNI-PORT-MIB.my"
-- Compile options "4 7 F H N W 03 06 0B 0G 0N 0T"

IMPORTS
    AtmAddress, NetPrefix
            FROM ATM-FORUM-TC-MIB
    atmAddressRegistration
            FROM BASIS-MIB
    ciscoWan
            FROM CISCOWAN-SMI
    OBJECT-TYPE
            FROM RFC-1212;

ciscoMgx82xxAtmUniPortMIB OBJECT IDENTIFIER ::= { ciscoWan 71 }
-- MODULE-IDENTITY
--  LastUpdated
--    200304180000Z
--  OrgName
--    Cisco Systems, Inc.
--  ContactInfo
--           Cisco Systems
--                Customer Service
--    
--        Postal: 170 W Tasman Drive
--                San Jose, CA  95134
--                USA
--    
--                Tel: +1 800 553-NETS
--    
--        E-mail: cs-wanatm@cisco.com
--  Descr
--    The MIB module containing objects related to
--    user-side of the ATM UNI Port.
--    
--    The mib is applicable for MGX8250 and MGX8220 products.
--    Terminologies used:
--    
--    UNI     :  User Network Interface.
--  RevDate
--    200304180000Z
--  RevDescr
--    Initial version of the MIB.
--    
--    The content of this MIB was originally available
--    in CISCO-WAN-AXIPOP-MIB defined using SMIv1.
--    The applicable objects from CISCO-WAN-AXIPOP-MIB
--    are defined using SMIv2 in this MIB. Also the
--    descriptions of some of the objects have been 
--    modified.

atmNetPrefixGroup OBJECT IDENTIFIER ::= { atmAddressRegistration 1 }
atmAddressGroup OBJECT IDENTIFIER ::= { atmAddressRegistration 2 }
cmauPortMIBConformance OBJECT IDENTIFIER ::= { ciscoMgx82xxAtmUniPortMIB 2 }
cmauPortMIBGroups OBJECT IDENTIFIER ::= { cmauPortMIBConformance 1 }
cmauPortMIBCompliances OBJECT IDENTIFIER ::= { cmauPortMIBConformance 2 }

atmAddressTable OBJECT-TYPE
    SYNTAX SEQUENCE OF AtmAddressEntry
    ACCESS not-accessible
    STATUS mandatory
    DESCRIPTION
        "A table implemented by the network-side of an ATM 
        UNI port, containing the ATM-layer addresses in effect
        on the user-side of the UNI."
    ::= { atmAddressGroup 1 }

atmAddressEntry OBJECT-TYPE
    SYNTAX AtmAddressEntry
    ACCESS not-accessible
    STATUS mandatory
    DESCRIPTION
        "Information about a single ATM-layer address in effect 
        on the user-side of a UNI port."
    INDEX { axisAtmAddressPort, axisAtmAddressAtmAddress }
    ::= { atmAddressTable 1 }

AtmAddressEntry ::= SEQUENCE {
    axisAtmAddressPort INTEGER,
    axisAtmAddressAtmAddress AtmAddress,
    axisAtmAddressStatus INTEGER
    }

axisAtmAddressPort OBJECT-TYPE
    SYNTAX INTEGER(0..2147483647)
    ACCESS read-only
    STATUS mandatory
    DESCRIPTION
        "A unique value which identifies this port. The value of
        0 has the special meaning of identifying the local UNI."
    ::= { atmAddressEntry 1 }

axisAtmAddressAtmAddress OBJECT-TYPE
    SYNTAX AtmAddress
--    Rsyntax OCTET STRING(SIZE(8|20))
    ACCESS read-only
    STATUS mandatory
    DESCRIPTION
        "The ATM address which is in effect on the user-side 
        of the ATM UNI port."
    ::= { atmAddressEntry 2 }

axisAtmAddressStatus OBJECT-TYPE
    SYNTAX INTEGER {
        valid(1),
        invalid(2)
        }
    ACCESS read-only
    STATUS mandatory
    DESCRIPTION
        "An indication of the validity of the ATM address at
        the user-side of the UNI port."
    ::= { atmAddressEntry 3 }

atmNetPrefixTable OBJECT-TYPE
    SYNTAX SEQUENCE OF AtmNetPrefixEntry
    ACCESS not-accessible
    STATUS mandatory
    DESCRIPTION
        "A table implemented by the UNI Management Entity on
        the user-side of an ATM UNI port, containing the     
        network-prefix(es) for ATM-layer addresses
        in effect on the user-side of the UNI."
    ::= { atmNetPrefixGroup 1 }

atmNetPrefixEntry OBJECT-TYPE
    SYNTAX AtmNetPrefixEntry
    ACCESS not-accessible
    STATUS mandatory
    DESCRIPTION
        "An entry in the table, containing information about
        the ATM Prefix status."
    INDEX { axisAtmNetPrefixPort, axisAtmNetPrefixPrefix }
    ::= { atmNetPrefixTable 1 }

AtmNetPrefixEntry ::= SEQUENCE {
    axisAtmNetPrefixPort INTEGER,
    axisAtmNetPrefixPrefix NetPrefix,
    axisAtmNetPrefixAdminStatus INTEGER,
    axisAtmNetPrefixOperStatus INTEGER
    }

axisAtmNetPrefixPort OBJECT-TYPE
    SYNTAX INTEGER(0..2147483647)
    ACCESS read-only
    STATUS mandatory
    DESCRIPTION
        "The unique value which identifies the ILMI port."
    ::= { atmNetPrefixEntry 1 }

axisAtmNetPrefixPrefix OBJECT-TYPE
    SYNTAX NetPrefix
--    Rsyntax OCTET STRING(SIZE(8|13))
    ACCESS read-only
    STATUS mandatory
    DESCRIPTION
        "The network prefix for ATM addresses which is in effect
        on the user-side of the ATM UNI port."
    ::= { atmNetPrefixEntry 2 }

axisAtmNetPrefixAdminStatus OBJECT-TYPE
    SYNTAX INTEGER {
        valid(1),
        invalid(2)
        }
    ACCESS read-write
    STATUS mandatory
    DESCRIPTION
        "An indication of the validity of the network prefix 
        for ATM addresses, on the user-side of the UNI port."
    ::= { atmNetPrefixEntry 3 }

axisAtmNetPrefixOperStatus OBJECT-TYPE
    SYNTAX INTEGER {
        registering(1),
        de-registering(2),
        registered(3),
        de-registered(4),
        failRegistering(5),
        failDe-registering(6)
        }
    ACCESS read-only
    STATUS mandatory
    DESCRIPTION
        "An indication of the current registration state for
        the prefix."
    ::= { atmNetPrefixEntry 4 }

cmauAtmAddressGroup OBJECT IDENTIFIER ::= { cmauPortMIBGroups 1 }
-- OBJECT-GROUP
--  Status
--    mandatory
--  Descr
--    The collection of objects which are used to represent
--    ATM Port information.
--  objects
--    axisAtmAddressPort, axisAtmAddressAtmAddress, 
--    axisAtmAddressStatus

cmauNetPrefixGroup OBJECT IDENTIFIER ::= { cmauPortMIBGroups 2 }
-- OBJECT-GROUP
--  Status
--    mandatory
--  Descr
--    The collection of objects related to
--    ATM address prefix.
--  objects
--    axisAtmNetPrefixPort, axisAtmNetPrefixPrefix, 
--    axisAtmNetPrefixAdminStatus, axisAtmNetPrefixOperStatus

cmauPortCompliance OBJECT IDENTIFIER ::= { cmauPortMIBCompliances 1 }
-- MODULE-COMPLIANCE
--  Status
--    mandatory
--  Descr
--    The compliance statement for objects related
--    to ATM UNI ports.
--  Module
--    >>current<<
--   MandGroup
--    cmauAtmAddressGroup
--   MandGroup
--    cmauNetPrefixGroup


END
