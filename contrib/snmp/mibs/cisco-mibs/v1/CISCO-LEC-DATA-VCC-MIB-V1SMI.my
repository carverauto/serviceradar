-- MIB created 6/25/99 12:57:22, by
--   SMIC (the next generation) version 1.6.29, November 22, 1994.

CISCO-LEC-DATA-VCC-MIB DEFINITIONS ::= BEGIN

-- From file: "CISCO-LEC-DATA-VCC-MIB.my"

IMPORTS
    OBJECT-TYPE
            FROM RFC-1212
    ciscoMgmt
            FROM CISCO-SMI
    ifIndex
            FROM IF-MIB
    lecIndex, AtmLaneAddress
            FROM LAN-EMULATION-CLIENT-MIB
    atmVclVpi, atmVclVci
            FROM ATM-MIB;

ciscoLecDataVccMIB OBJECT IDENTIFIER ::= { ciscoMgmt 69 }
-- MODULE-IDENTITY
--  LastUpdated
--    9701060000Z
--  OrgName
--    Cisco Systems, Inc.
--  ContactInfo
--           Cisco Systems
--            Customer Service
--    
--    Postal: 170 W Tasman Drive
--            San Jose, CA  95134
--            USA
--    
--       Tel: +1 800 553-NETS
--    
--    E-mail: cs-atm@cisco.com
--  Descr
--    This MIB module is a Cisco extension to the ATM
--    Forum's LANE Client MIB.  This extension identifies
--    those VCCs which are being used to carry packets
--    sent on LANE Data Direct VCCs.
--  RevDate
--    9701060000Z
--  RevDescr
--    Initial version of this MIB module.

ciscoLecDataVccMIBObjects OBJECT IDENTIFIER ::= { ciscoLecDataVccMIB 1 }
cLecDataDirectVcc OBJECT IDENTIFIER ::= { ciscoLecDataVccMIBObjects 1 }
ciscoLecDataVccMIBNotificationPrefix OBJECT IDENTIFIER ::= { ciscoLecDataVccMIB 2 }
ciscoLecDataVccMIBNotifications OBJECT IDENTIFIER ::= { ciscoLecDataVccMIBNotificationPrefix 0 }
ciscoLecDataVccMIBConformance OBJECT IDENTIFIER ::= { ciscoLecDataVccMIB 3 }
ciscoLecDataVccMIBCompliances OBJECT IDENTIFIER ::= { ciscoLecDataVccMIBConformance 1 }
ciscoLecDataVccMIBGroups OBJECT IDENTIFIER ::= { ciscoLecDataVccMIBConformance 2 }

cLecDataDirectVccTable OBJECT-TYPE
    SYNTAX SEQUENCE OF CLecDataDirectVccEntry
    ACCESS not-accessible
    STATUS mandatory
    DESCRIPTION
        "A table containing entries for all VCCs used as
        LAN-Emulation Data Direct VCCs."
    ::= { cLecDataDirectVcc 1 }

cLecDataDirectVccEntry OBJECT-TYPE
    SYNTAX CLecDataDirectVccEntry
    ACCESS not-accessible
    STATUS mandatory
    DESCRIPTION
        "Each entry in this table represents a Data Direct VCC
        for a particular Emulated LAN (ELAN):
        
        - the ELAN is identified by the lecIndex value.
        - the VCC is identified by the combination of the
          interface (ifIndex, for which the corresponding
          ifType has the value atm(37)), the VPI (atmVclVpi)
          and the VCI (atmVclVci).
        
        Entries appear in the table as a LANE client
        establishes Data Direct VCs with other LANE clients
        and are removed when the VCs are dropped."
    INDEX { lecIndex, ifIndex, atmVclVpi, atmVclVci }
    ::= { cLecDataDirectVccTable 1 }

CLecDataDirectVccEntry ::= SEQUENCE {
    cLecDataDirectLocalAtmAddress AtmLaneAddress,
    cLecDataDirectRemoteAtmAddress AtmLaneAddress
    }

cLecDataDirectLocalAtmAddress OBJECT-TYPE
    SYNTAX AtmLaneAddress
--    Rsyntax OCTET STRING(SIZE(0 | 20))
    ACCESS read-only
    STATUS mandatory
    DESCRIPTION
        "The ATM Address of the local end of this Data Direct
        VCC."
    ::= { cLecDataDirectVccEntry 1 }

cLecDataDirectRemoteAtmAddress OBJECT-TYPE
    SYNTAX AtmLaneAddress
--    Rsyntax OCTET STRING(SIZE(0 | 20))
    ACCESS read-only
    STATUS mandatory
    DESCRIPTION
        "The ATM Address of the remote end of this Data Direct
        VCC."
    ::= { cLecDataDirectVccEntry 2 }

ciscoLecDataVccBaseMIBGroup OBJECT IDENTIFIER ::= { ciscoLecDataVccMIBGroups 1 }
-- OBJECT-GROUP
--  Status
--    mandatory
--  Descr
--    A collection of objects related to identifying
--    a LANE Client's Data Direct VCCs.
--  objects
--    cLecDataDirectLocalAtmAddress, cLecDataDirectRemoteAtmAddress

ciscoLecDataVccMIBCompliance OBJECT IDENTIFIER ::= { ciscoLecDataVccMIBCompliances 1 }
-- MODULE-COMPLIANCE
--  Status
--    mandatory
--  Descr
--    This module should be implemented by all Cisco
--     devices supporting ATM LAN Emulation Clients.
--  Module
--    >>current<<
--   MandGroup
--    ciscoLecDataVccBaseMIBGroup


END
