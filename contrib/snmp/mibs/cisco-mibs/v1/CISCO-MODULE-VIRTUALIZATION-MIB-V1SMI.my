-- MIB file created 31-May-2006 16:39:38, by
--   SMICng version 2.2.11-beta(PRO)(Solaris), January 20, 2001. Enterprise key cisco.com

CISCO-MODULE-VIRTUALIZATION-MIB DEFINITIONS ::= BEGIN

-- From file: "CISCO-MODULE-VIRTUALIZATION-MIB.my"
-- Compile options "4 7 F H N O W 03 06 0B 0G 0N 0T"

IMPORTS
    RowStatus, TruthValue, StorageType
            FROM SNMPv2-TC-v1
    SnmpAdminString
            FROM SNMP-FRAMEWORK-MIB
    entPhysicalIndex
            FROM ENTITY-MIB
    IANAifType
            FROM IANAifType-MIB
    CiscoResourceClass
            FROM CISCO-L4L7MODULE-RESOURCE-LIMIT-MIB
    CiscoURLString
            FROM CISCO-TC
    ciscoMgmt
            FROM CISCO-SMI
    Gauge
            FROM RFC1155-SMI
    OBJECT-TYPE
            FROM RFC-1212
    TRAP-TYPE
            FROM RFC-1215;

ciscoModuleVirtualizationMIB OBJECT IDENTIFIER ::= { ciscoMgmt 472 }
-- MODULE-IDENTITY
--  LastUpdated
--    200605290000Z
--  OrgName
--    Cisco Systems, Inc.
--  ContactInfo
--           Cisco Systems 
--           Customer Service 
--    
--    Postal: 170 W Tasman Drive 
--        San Jose, CA  95134 
--        USA 
--    
--       Tel: +1 800 553-NETS 
--    
--    E-mail: cs-l4l7security@cisco.com
--  Descr
--    This MIB provides a way to create virtual contexts, 
--    and managing them.  A virtual context is logical 
--    partition of a physical device.  The Virtual context 
--    provide different type of services and can be managed  
--    independently.  Each virtual context is an independent  
--    entity, with its own configuration and supports 
--    almost all the options that can be configured on 
--    stand-alone hardware.  Each context can have a separate  
--    management IP address that the user can Telnet/SSH into   
--    and send other requests(SNMP, FTP etc). 
--     
--    This MIB contains tables for creating/deleting virtual 
--    contexts and assigning interfaces and/or interface ranges 
--    to virtual contexts.
--  RevDate
--    200605290000Z
--  RevDescr
--    Corrected the contact E-mail id:  
--     cs-l4l7security@cisco.com
--  RevDate
--    200512120000Z
--  RevDescr
--    Initial version of the MIB module.

cmVirtualizationNotifs OBJECT IDENTIFIER ::= { ciscoModuleVirtualizationMIB 0 }
cmVirtualizationMIBObjects OBJECT IDENTIFIER ::= { ciscoModuleVirtualizationMIB 1 }
cmVirtualizationMIBConformance OBJECT IDENTIFIER ::= { ciscoModuleVirtualizationMIB 2 }
cmVirtualContext OBJECT IDENTIFIER ::= { cmVirtualizationMIBObjects 1 }
cmVirtualContextNotifControl OBJECT IDENTIFIER ::= { cmVirtualizationMIBObjects 2 }
cmVirtualContextNotifObjects OBJECT IDENTIFIER ::= { cmVirtualizationMIBObjects 3 }
cmVirtualizationCompliances OBJECT IDENTIFIER ::= { cmVirtualizationMIBConformance 1 }
cmVirtualizationGroups OBJECT IDENTIFIER ::= { cmVirtualizationMIBConformance 2 }

cmVirtualContextTable OBJECT-TYPE
    SYNTAX SEQUENCE OF CmVirtualContextEntry
    ACCESS not-accessible
    STATUS mandatory
    DESCRIPTION
        "This is the virtual context table.  A virtual context 
        can be created for a module.  This table is used for  
        creating/deleting virtual contexts.  The entries can be 
        created/deleted by SNMP and/or by console commands."
    ::= { cmVirtualContext 1 }

cmVirtualContextEntry OBJECT-TYPE
    SYNTAX CmVirtualContextEntry
    ACCESS not-accessible
    STATUS mandatory
    DESCRIPTION
        "An entry in virtual context table. Each entry 
        provides information about a particular virtual context. 
        To create a virtual context, following procedure is 
        used: 
        - choose the appropriate value for entPhysicalIndex 
          to point to an entry(with entPhysicaClass = 'module') 
          in entPhysicalTable. 
        - specify the name of the virtual context. 
        - create an entry in the table by specifying 
          ciscoVirtualContextRowStatus value of 
          'createAndGo' or 'createAndWait'. 
        
        One or more virtual contexts can be created in a module. 
        Each of these contexts are identified by a unique name. 
        Resources can be assigned/mapped to each virtual context. 
        Configurations and Monitoring can be done each virtual 
        context independent of each other.  Configuration changes in 
        one virtual context will not affect other."
    INDEX { entPhysicalIndex, cmVirtContextName }
    ::= { cmVirtualContextTable 1 }

CmVirtualContextEntry ::= SEQUENCE {
    cmVirtContextName SnmpAdminString,
    cmVirtContextDescr SnmpAdminString,
    cmVirtContextURL CiscoURLString,
    cmVirtContextResourceClass CiscoResourceClass,
    cmVirtContextStorageType StorageType,
    cmVirtContextRowStatus RowStatus
    }

cmVirtContextName OBJECT-TYPE
    SYNTAX SnmpAdminString
--    Rsyntax OCTET STRING(SIZE(0..255))
    ACCESS not-accessible
    STATUS mandatory
    DESCRIPTION
        "This object uniquely identifies a virtual context."
    ::= { cmVirtualContextEntry 1 }

cmVirtContextDescr OBJECT-TYPE
    SYNTAX SnmpAdminString
--    Rsyntax OCTET STRING(SIZE(0..255))
    ACCESS read-write
    STATUS mandatory
    DESCRIPTION
        "This object is used for configuring 
        the description of virtual context."
    DEFVAL { "" }
    ::= { cmVirtualContextEntry 2 }

cmVirtContextURL OBJECT-TYPE
    SYNTAX CiscoURLString
--    Rsyntax OCTET STRING(SIZE(1..255))
    ACCESS read-write
    STATUS mandatory
    DESCRIPTION
        "This object is used for configuring 
        the URL from which virtual context 
        configuration will be downloaded. 
        
        The configuration contains information 
        on anything that is configured in a  
        virtual context. 
        Some examples of possible values for this object are: 
            disk://[path/]filename 
            ftp://[user[:password]@]server/[path/]filename 
            tftp://server/[path/]filename 
            http://server/[path/]filename 
            https://server/[path/]filename. 
        NOTE: Above list is just an example. It does not  
        specify/limit only these values to be supported."
    ::= { cmVirtualContextEntry 3 }

cmVirtContextResourceClass OBJECT-TYPE
    SYNTAX CiscoResourceClass
--    Rsyntax OCTET STRING(SIZE(0..64))
    ACCESS read-write
    STATUS mandatory
    DESCRIPTION
        "This object is used for assigning 
        a resource class to a context.  
        The resource class contains information 
        on the resources that are managed/applicable 
        to a context.  The type of resources that 
        may be applicable are governed by the 
        CiscoResourceClass TEXTUAL CONVENTION. 
        This object value must correspond to an entry 
        in cmResourceClassTable."
    REFERENCE
        "cmResourceClassTable in CISCO-RESOURCE-LIMIT-MIB."
    ::= { cmVirtualContextEntry 4 }

cmVirtContextStorageType OBJECT-TYPE
    SYNTAX StorageType
--    Rsyntax INTEGER {
--        other(1),
--        volatile(2),
--        nonVolatile(3),
--        permanent(4),
--        readOnly(5)
--        }
    ACCESS read-write
    STATUS mandatory
    DESCRIPTION
        "The storage type for this conceptual row. 
        Conceptual rows having the value 'permanent' need not 
        allow write-access to any columnar objects in the row."
    DEFVAL { nonVolatile }
    ::= { cmVirtualContextEntry 5 }

cmVirtContextRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used for creating/deleting 
        entries in this table."
    ::= { cmVirtualContextEntry 6 }

cmVirtContextIfMapTable OBJECT-TYPE
    SYNTAX SEQUENCE OF CmVirtContextIfMapEntry
    ACCESS not-accessible
    STATUS mandatory
    DESCRIPTION
        "This table is used for assigning interfaces 
        to a virtual context.  This table will configure 
        the set of interfaces that can be used by a 
        virtual context."
    ::= { cmVirtualContext 2 }

cmVirtContextIfMapEntry OBJECT-TYPE
    SYNTAX CmVirtContextIfMapEntry
    ACCESS not-accessible
    STATUS mandatory
    DESCRIPTION
        "An entry in Interface Map table. 
        Each entry represents the interface or 
        interface range that are assigned to 
        a virtual context."
    INDEX { cmVirtContextName, cmVirtContextIfMapType, cmVirtContextIfMapIdLow }
    ::= { cmVirtContextIfMapTable 1 }

CmVirtContextIfMapEntry ::= SEQUENCE {
    cmVirtContextIfMapType IANAifType,
    cmVirtContextIfMapIdLow Gauge,
    cmVirtContextIfMapIdHigh Gauge,
    cmVirtContextIfMapStorageType StorageType,
    cmVirtContextIfMapRowStatus RowStatus
    }

cmVirtContextIfMapType OBJECT-TYPE
    SYNTAX IANAifType
--    Rsyntax INTEGER {
--        other(1),
--        regular1822(2),
--        hdh1822(3),
--        ddnX25(4),
--        rfc877x25(5),
--        ethernetCsmacd(6),
--        iso88023Csmacd(7),
--        iso88024TokenBus(8),
--        iso88025TokenRing(9),
--        iso88026Man(10),
--        starLan(11),
--        proteon10Mbit(12),
--        proteon80Mbit(13),
--        hyperchannel(14),
--        fddi(15),
--        lapb(16),
--        sdlc(17),
--        ds1(18),
--        e1(19),
--        basicISDN(20),
--        primaryISDN(21),
--        propPointToPointSerial(22),
--        ppp(23),
--        softwareLoopback(24),
--        eon(25),
--        ethernet3Mbit(26),
--        nsip(27),
--        slip(28),
--        ultra(29),
--        ds3(30),
--        sip(31),
--        frameRelay(32),
--        rs232(33),
--        para(34),
--        arcnet(35),
--        arcnetPlus(36),
--        atm(37),
--        miox25(38),
--        sonet(39),
--        x25ple(40),
--        iso88022llc(41),
--        localTalk(42),
--        smdsDxi(43),
--        frameRelayService(44),
--        v35(45),
--        hssi(46),
--        hippi(47),
--        modem(48),
--        aal5(49),
--        sonetPath(50),
--        sonetVT(51),
--        smdsIcip(52),
--        propVirtual(53),
--        propMultiplexor(54),
--        ieee80212(55),
--        fibreChannel(56),
--        hippiInterface(57),
--        frameRelayInterconnect(58),
--        aflane8023(59),
--        aflane8025(60),
--        cctEmul(61),
--        fastEther(62),
--        isdn(63),
--        v11(64),
--        v36(65),
--        g703at64k(66),
--        g703at2mb(67),
--        qllc(68),
--        fastEtherFX(69),
--        channel(70),
--        ieee80211(71),
--        ibm370parChan(72),
--        escon(73),
--        dlsw(74),
--        isdns(75),
--        isdnu(76),
--        lapd(77),
--        ipSwitch(78),
--        rsrb(79),
--        atmLogical(80),
--        ds0(81),
--        ds0Bundle(82),
--        bsc(83),
--        async(84),
--        cnr(85),
--        iso88025Dtr(86),
--        eplrs(87),
--        arap(88),
--        propCnls(89),
--        hostPad(90),
--        termPad(91),
--        frameRelayMPI(92),
--        x213(93),
--        adsl(94),
--        radsl(95),
--        sdsl(96),
--        vdsl(97),
--        iso88025CRFPInt(98),
--        myrinet(99),
--        voiceEM(100),
--        voiceFXO(101),
--        voiceFXS(102),
--        voiceEncap(103),
--        voiceOverIp(104),
--        atmDxi(105),
--        atmFuni(106),
--        atmIma(107),
--        pppMultilinkBundle(108),
--        ipOverCdlc(109),
--        ipOverClaw(110),
--        stackToStack(111),
--        virtualIpAddress(112),
--        mpc(113),
--        ipOverAtm(114),
--        iso88025Fiber(115),
--        tdlc(116),
--        gigabitEthernet(117),
--        hdlc(118),
--        lapf(119),
--        v37(120),
--        x25mlp(121),
--        x25huntGroup(122),
--        trasnpHdlc(123),
--        interleave(124),
--        fast(125),
--        ip(126),
--        docsCableMaclayer(127),
--        docsCableDownstream(128),
--        docsCableUpstream(129),
--        a12MppSwitch(130),
--        tunnel(131),
--        coffee(132),
--        ces(133),
--        atmSubInterface(134),
--        l2vlan(135),
--        l3ipvlan(136),
--        l3ipxvlan(137),
--        digitalPowerline(138),
--        mediaMailOverIp(139),
--        dtm(140),
--        dcn(141),
--        ipForward(142),
--        msdsl(143),
--        ieee1394(144),
--        if-gsn(145),
--        dvbRccMacLayer(146),
--        dvbRccDownstream(147),
--        dvbRccUpstream(148),
--        atmVirtual(149),
--        mplsTunnel(150),
--        srp(151),
--        voiceOverAtm(152),
--        voiceOverFrameRelay(153),
--        idsl(154),
--        compositeLink(155),
--        ss7SigLink(156),
--        propWirelessP2P(157),
--        frForward(158),
--        rfc1483(159),
--        usb(160),
--        ieee8023adLag(161),
--        bgppolicyaccounting(162),
--        frf16MfrBundle(163),
--        h323Gatekeeper(164),
--        h323Proxy(165),
--        mpls(166),
--        mfSigLink(167),
--        hdsl2(168),
--        shdsl(169),
--        ds1FDL(170),
--        pos(171),
--        dvbAsiIn(172),
--        dvbAsiOut(173),
--        plc(174),
--        nfas(175),
--        tr008(176),
--        gr303RDT(177),
--        gr303IDT(178),
--        isup(179),
--        propDocsWirelessMaclayer(180),
--        propDocsWirelessDownstream(181),
--        propDocsWirelessUpstream(182),
--        hiperlan2(183),
--        propBWAp2Mp(184),
--        sonetOverheadChannel(185),
--        digitalWrapperOverheadChannel(186),
--        aal2(187),
--        radioMAC(188),
--        atmRadio(189),
--        imt(190),
--        mvl(191),
--        reachDSL(192),
--        frDlciEndPt(193),
--        atmVciEndPt(194),
--        opticalChannel(195),
--        opticalTransport(196),
--        propAtm(197),
--        voiceOverCable(198),
--        infiniband(199),
--        teLink(200),
--        q2931(201),
--        virtualTg(202),
--        sipTg(203),
--        sipSig(204),
--        docsCableUpstreamChannel(205),
--        econet(206),
--        pon155(207),
--        pon622(208),
--        bridge(209),
--        linegroup(210),
--        voiceEMFGD(211),
--        voiceFGDEANA(212),
--        voiceDID(213),
--        mpegTransport(214),
--        sixToFour(215),
--        gtp(216),
--        pdnEtherLoop1(217),
--        pdnEtherLoop2(218),
--        opticalChannelGroup(219),
--        homepna(220),
--        gfp(221),
--        ciscoISLvlan(222),
--        actelisMetaLOOP(223),
--        fcipLink(224),
--        rpr(225),
--        qam(226),
--        lmp(227),
--        cblVectaStar(228),
--        docsCableMCmtsDownstream(229),
--        adsl2(230),
--        macSecControlledIF(231),
--        macSecUncontrolledIF(232),
--        aviciOpticalEther(233),
--        atmbond(234)
--        }
    ACCESS not-accessible
    STATUS mandatory
    DESCRIPTION
        "This object specifies the interface type 
        for which cmVirtContextIfMapIdHigh 
        and cmVirtContextIfMapIdLow are applicable."
    ::= { cmVirtContextIfMapEntry 1 }

cmVirtContextIfMapIdLow OBJECT-TYPE
    SYNTAX Gauge
    ACCESS not-accessible
    STATUS mandatory
    DESCRIPTION
        "This object specifies the interface that  
        can be assigned to a context.  This object 
        either represents an interface or lower value 
        of the interface range."
    ::= { cmVirtContextIfMapEntry 2 }

cmVirtContextIfMapIdHigh OBJECT-TYPE
    SYNTAX Gauge
    ACCESS read-write
    STATUS mandatory
    DESCRIPTION
        "This object specifies the interface that 
        will be assigned to a virtual context. 
        The non-zero value specifies the upper value 
        of the interface range.  This value must be 
        greater than the value in cmVirtContextIfMapIdLow. 
        The value zero specifies that value specified  
        in cmVirtContextIfMapIdLow is assigned."
    ::= { cmVirtContextIfMapEntry 3 }

cmVirtContextIfMapStorageType OBJECT-TYPE
    SYNTAX StorageType
--    Rsyntax INTEGER {
--        other(1),
--        volatile(2),
--        nonVolatile(3),
--        permanent(4),
--        readOnly(5)
--        }
    ACCESS read-write
    STATUS mandatory
    DESCRIPTION
        "The storage type for this conceptual row. 
        Conceptual rows having the value 'permanent' need not 
        allow write-access to any columnar objects in the row."
    DEFVAL { nonVolatile }
    ::= { cmVirtContextIfMapEntry 4 }

cmVirtContextIfMapRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used for creating/deleting 
        entries in this table."
    ::= { cmVirtContextIfMapEntry 5 }

cmVirtContextNotifEnable OBJECT-TYPE
    SYNTAX TruthValue
--    Rsyntax INTEGER {
--        true(1),
--        false(2)
--        }
    ACCESS read-write
    STATUS mandatory
    DESCRIPTION
        "This object is used for enabling/disabling 
        notifications related to virtual context."
    ::= { cmVirtualContextNotifControl 1 }

cmNotifVirtContextName OBJECT-TYPE
    SYNTAX SnmpAdminString
--    Rsyntax OCTET STRING(SIZE(0..255))
    ACCESS not-accessible
    STATUS mandatory
    DESCRIPTION
        "This object is used in notifications only. 
        This object contains the virtual context name. 
        (i.e. value of cmVirtContextName)."
    ::= { cmVirtualContextNotifObjects 1 }

cmVirtContextAdded TRAP-TYPE
-- Reverse mappable trap
    ENTERPRISE ciscoModuleVirtualizationMIB
    VARIABLES {
        cmNotifVirtContextName }
--  Status
--    mandatory
    DESCRIPTION
        "This notifications will be sent 
        when a virtual context is added."
    ::= 1

cmVirtContextRemoved TRAP-TYPE
-- Reverse mappable trap
    ENTERPRISE ciscoModuleVirtualizationMIB
    VARIABLES {
        cmNotifVirtContextName }
--  Status
--    mandatory
    DESCRIPTION
        "This notifications will be sent 
        when a virtual context is removed/deleted."
    ::= 2

cmVirtContextconfigGroup OBJECT IDENTIFIER ::= { cmVirtualizationGroups 1 }
-- OBJECT-GROUP
--  Status
--    mandatory
--  Descr
--    The collection of objects which are used to represent 
--    virtual contexts in a virtualized system.
--  objects
--    cmVirtContextDescr, cmVirtContextURL, 
--    cmVirtContextResourceClass, cmVirtContextStorageType, 
--    cmVirtContextRowStatus

cmVirtContextIfMapGroup OBJECT IDENTIFIER ::= { cmVirtualizationGroups 2 }
-- OBJECT-GROUP
--  Status
--    mandatory
--  Descr
--    The collection of objects which are used  
--    for assigning interfaces to a virtual context.
--  objects
--    cmVirtContextIfMapIdHigh, cmVirtContextIfMapStorageType, 
--    cmVirtContextIfMapRowStatus

cmVirtContextNotifControlGroup OBJECT IDENTIFIER ::= { cmVirtualizationGroups 3 }
-- OBJECT-GROUP
--  Status
--    mandatory
--  Descr
--    The collection of object to control notifications 
--    that are sent.
--  objects
--    cmVirtContextNotifEnable

cmVirtContextNotifObjectsGroup OBJECT IDENTIFIER ::= { cmVirtualizationGroups 4 }
-- OBJECT-GROUP
--  Status
--    mandatory
--  Descr
--    The collection of objects sent only in notifications.
--  objects
--    cmNotifVirtContextName

cmVirtContextNotificationGroup OBJECT IDENTIFIER ::= { cmVirtualizationGroups 5 }
-- NOTIFICATION-GROUP
--  Status
--    mandatory
--  Descr
--    The collection of objects which are used to represent 
--    virtual contexts in a virtualized system.
--  notifications
--    cmVirtContextAdded, cmVirtContextRemoved

cmVirtualizationCompliance OBJECT IDENTIFIER ::= { cmVirtualizationCompliances 1 }
-- MODULE-COMPLIANCE
--  Status
--    mandatory
--  Descr
--    The compliance statement for SNMP entities which implement 
--    virtualization MIB.
--  Module
--    >>current<<
--   MandGroup
--    cmVirtContextconfigGroup
--   OptGroup
--    cmVirtContextIfMapGroup
--   OptGroup
--    cmVirtContextNotifControlGroup
--   OptGroup
--    cmVirtContextNotificationGroup


END
