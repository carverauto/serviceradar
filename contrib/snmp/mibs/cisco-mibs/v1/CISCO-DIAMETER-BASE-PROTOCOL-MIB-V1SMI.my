-- MIB file created 03-Sep-2009 14:24:10, by
--   SMICng version 2.2.11-beta(PRO)(Solaris), January 20, 2001. Enterprise key cisco.com

CISCO-DIAMETER-BASE-PROTOCOL-MIB DEFINITIONS ::= BEGIN

-- From file: "CISCO-DIAMETER-BASE-PROTOCOL-MIB.my"
-- Compile options "4 7 F H N O W 03 06 0B 0G 0N 0T"

IMPORTS
    StorageType, TruthValue, RowStatus
            FROM SNMPv2-TC-v1
    InetAddress, InetAddressType
            FROM INET-ADDRESS-MIB
    SnmpAdminString
            FROM SNMP-FRAMEWORK-MIB
    ciscoExperiment
            FROM CISCO-SMI
    Counter, Gauge, IpAddress, TimeTicks
            FROM RFC1155-SMI
    OBJECT-TYPE
            FROM RFC-1212
    TRAP-TYPE
            FROM RFC-1215;

ciscoDiameterBasePMIB OBJECT IDENTIFIER ::= { ciscoExperiment 133 }
-- MODULE-IDENTITY
--  LastUpdated
--    200608240001Z
--  OrgName
--    Cisco Systems, Inc.
--  ContactInfo
--    Cisco Systems
--    Customer Service
--    
--    Postal: 170 W Tasman Drive
--    San Jose, CA  95134
--    USA
--    
--    Tel: +1 800 553-NETS
--    
--    E-mail: cs-aaa@cisco.com
--  Descr
--    The MIB module for entities implementing the
--    Diameter Base Protocol. Initial Cisco'ized version of the
--    IETF draft
--    draft-zorn-dime-diameter-base-protocol-mib-00.txt.
--  RevDate
--    200608240001Z
--  RevDescr
--    Initial version of this MIB module.

ciscoDiameterBasePMIBNotifs OBJECT IDENTIFIER ::= { ciscoDiameterBasePMIB 0 }
ciscoDiameterBasePMIBObjects OBJECT IDENTIFIER ::= { ciscoDiameterBasePMIB 1 }
ciscoDiameterBasePMIBConform OBJECT IDENTIFIER ::= { ciscoDiameterBasePMIB 2 }
cdbpLocalCfgs   OBJECT IDENTIFIER ::= { ciscoDiameterBasePMIBObjects 1 }
cdbpLocalStats  OBJECT IDENTIFIER ::= { ciscoDiameterBasePMIBObjects 2 }
cdbpPeerCfgs    OBJECT IDENTIFIER ::= { ciscoDiameterBasePMIBObjects 3 }
cdbpPeerStats   OBJECT IDENTIFIER ::= { ciscoDiameterBasePMIBObjects 4 }
cdbpRealmCfgs   OBJECT IDENTIFIER ::= { ciscoDiameterBasePMIBObjects 5 }
cdbpRealmStats  OBJECT IDENTIFIER ::= { ciscoDiameterBasePMIBObjects 6 }
cdbpTrapCfgs    OBJECT IDENTIFIER ::= { ciscoDiameterBasePMIBObjects 7 }
ciscoDiameterBasePMIBCompliances OBJECT IDENTIFIER ::= { ciscoDiameterBasePMIBConform 1 }
ciscoDiameterBasePMIBGroups OBJECT IDENTIFIER ::= { ciscoDiameterBasePMIBConform 2 }

ciscoDiaBaseProtEnableProtocolErrorNotif OBJECT-TYPE
    SYNTAX TruthValue
--    Rsyntax INTEGER {
--        true(1),
--        false(2)
--        }
    ACCESS read-write
    STATUS mandatory
    DESCRIPTION
        "Setting the value of this object to true(1)
        enables the ciscoDiaBaseProtProtocolErrorNotif
        notification."
    DEFVAL { false }
    ::= { cdbpTrapCfgs 1 }

ciscoDiaBaseProtEnableTransientFailureNotif OBJECT-TYPE
    SYNTAX TruthValue
--    Rsyntax INTEGER {
--        true(1),
--        false(2)
--        }
    ACCESS read-write
    STATUS mandatory
    DESCRIPTION
        "Setting the value of this object to true(1)
        enables the ciscoDiaBaseProtTransientFailureNotif 
        notification."
    DEFVAL { false }
    ::= { cdbpTrapCfgs 2 }

ciscoDiaBaseProtEnablePermanentFailureNotif OBJECT-TYPE
    SYNTAX TruthValue
--    Rsyntax INTEGER {
--        true(1),
--        false(2)
--        }
    ACCESS read-write
    STATUS mandatory
    DESCRIPTION
        "Setting the value of this object to true(1)
        enables the ciscoDiaBaseProtPermanentFailureNotif
        notification."
    DEFVAL { false }
    ::= { cdbpTrapCfgs 3 }

ciscoDiaBaseProtEnablePeerConnectionDownNotif OBJECT-TYPE
    SYNTAX TruthValue
--    Rsyntax INTEGER {
--        true(1),
--        false(2)
--        }
    ACCESS read-write
    STATUS mandatory
    DESCRIPTION
        "Setting the value of this object to true(1)
        enables the ciscoDiaBaseProtPeerConnectionDownNotif
        notification."
    DEFVAL { false }
    ::= { cdbpTrapCfgs 4 }

ciscoDiaBaseProtEnablePeerConnectionUpNotif OBJECT-TYPE
    SYNTAX TruthValue
--    Rsyntax INTEGER {
--        true(1),
--        false(2)
--        }
    ACCESS read-write
    STATUS mandatory
    DESCRIPTION
        "Setting the value of this object to true(1)
        enables the ciscoDiaBaseProtPeerConnectionUpNotif
        notification."
    DEFVAL { false }
    ::= { cdbpTrapCfgs 5 }

cdbpLocalId OBJECT-TYPE
    SYNTAX SnmpAdminString
--    Rsyntax OCTET STRING(SIZE(0..255))
    ACCESS read-only
    STATUS mandatory
    DESCRIPTION
        "The implementation identification string for the
        Diameter software in use on the system, for
        example; 'diameterd'"
    ::= { cdbpLocalCfgs 1 }

cdbpLocalIpAddrTable OBJECT-TYPE
    SYNTAX SEQUENCE OF CdbpLocalIpAddrEntry
    ACCESS not-accessible
    STATUS mandatory
    DESCRIPTION
        "The table listing the Diameter
        local host's IP Addresses."
    ::= { cdbpLocalCfgs 2 }

cdbpLocalIpAddrEntry OBJECT-TYPE
    SYNTAX CdbpLocalIpAddrEntry
    ACCESS not-accessible
    STATUS mandatory
    DESCRIPTION
        "A row entry representing a Diameter
        local host IP Address."
    INDEX { cdbpLocalIpAddrIndex }
    ::= { cdbpLocalIpAddrTable 1 }

CdbpLocalIpAddrEntry ::= SEQUENCE {
    cdbpLocalIpAddrIndex Gauge,
    cdbpLocalIpAddrType InetAddressType,
    cdbpLocalIpAddress InetAddress
    }

cdbpLocalIpAddrIndex OBJECT-TYPE
    SYNTAX Gauge(1..4294967295)
    ACCESS not-accessible
    STATUS mandatory
    DESCRIPTION
        "A number uniquely identifying the number
        of IP Addresses supported by this Diameter
        host."
    ::= { cdbpLocalIpAddrEntry 1 }

cdbpLocalIpAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "The type of internet address stored
        in cdbpLocalIpAddress."
    ::= { cdbpLocalIpAddrEntry 2 }

cdbpLocalIpAddress OBJECT-TYPE
    SYNTAX InetAddress
--    Rsyntax OCTET STRING(SIZE(0..255))
    ACCESS read-only
    STATUS mandatory
    DESCRIPTION
        "The IP-Address of the host, which is of the type
        specified in cdbpLocalIpAddrType."
    ::= { cdbpLocalIpAddrEntry 3 }

cdbpLocalTcpListenPort OBJECT-TYPE
    SYNTAX Gauge(1..65535)
    ACCESS read-only
    STATUS mandatory
    DESCRIPTION
        "This object represents Diameter TCP 'listen' port."
    ::= { cdbpLocalCfgs 3 }

cdbpLocalSctpListenPort OBJECT-TYPE
    SYNTAX Gauge(1..65535)
    ACCESS read-only
    STATUS mandatory
    DESCRIPTION
        "This object represents Diameter SCTP 'listen' port."
    ::= { cdbpLocalCfgs 4 }

cdbpLocalOriginHost OBJECT-TYPE
    SYNTAX SnmpAdminString
--    Rsyntax OCTET STRING(SIZE(0..255))
    ACCESS read-write
    STATUS mandatory
    DESCRIPTION
        "This object represents the Local Origin Host."
    DEFVAL { "" }
    ::= { cdbpLocalCfgs 5 }

cdbpLocalRealm OBJECT-TYPE
    SYNTAX SnmpAdminString
--    Rsyntax OCTET STRING(SIZE(0..255))
    ACCESS read-only
    STATUS mandatory
    DESCRIPTION
        "This object represents the Local Realm Name."
    DEFVAL { "" }
    ::= { cdbpLocalCfgs 6 }

cdbpRedundancyEnabled OBJECT-TYPE
    SYNTAX TruthValue
--    Rsyntax INTEGER {
--        true(1),
--        false(2)
--        }
    ACCESS read-write
    STATUS mandatory
    DESCRIPTION
        "This parameter indicates if cisco redundancy has been
        enabled, it is enabled if set to true and disabled if
        set to false."
    DEFVAL { false }
    ::= { cdbpLocalCfgs 7 }

cdbpRedundancyInfraState OBJECT-TYPE
    SYNTAX INTEGER {
        --?? enum value of zero may cause problems
        rfUnknown(0),
        rfDisabled(1),
        rfInitialization(2),
        rfNegotiation(3),
        rfStandbyCold(4),
        rfStandbyConfig(5),
        rfStandbyFileSys(6),
        rfStandbyBulk(7),
        rfStandbyHot(8),
        rfActiveFast(9),
        rfActiveDrain(10),
        rfActivePreconfig(11),
        rfActivePostconfig(12),
        rfActive(13),
        rfActiveExtraload(14)
        }
    ACCESS read-only
    STATUS mandatory
    DESCRIPTION
        "This parameter indicates the current state of cisco
        redundancy infrastructure state.
          rfUnknown(0)           - unknown state
          rfDisabled(1)          - RF is not functioning at this
                                   time
          rfInitialization(2)    - co-ordinating init with platform
          rfNegotiation(3)       - initial negotiation with peer to
                                   determine active-standby
          rfStandbyCold(4)       - peer is active, we're cold
          rfStandbyConfig(5)     - sync config from active to
                                   standby
          rfStandbyFileSys(6)    - sync file sys from active to
                                   standby
          rfStandbyBulk(7)       - clients bulk sync from active
                                   to standby
          rfStandbyHot(8)        - standby ready-n-able to be
                                   active
          rfActiveFast(9)        - immediate notification of
                                   standby going active
          rfActiveDrain(10)      - drain queued messages from peer
          rfActivePreconfig(11)  - active and before config
          rfActivePostconfig(12) - active and post config 
          rfActive(13)           - actively processing new calls
          rfActiveExtraload(14)  - actively processing new calls
                                   extra resources other Processing
                                   is failed and I have extra load."
    ::= { cdbpLocalCfgs 8 }

cdbpRedundancyLastSwitchover OBJECT-TYPE
    SYNTAX SnmpAdminString
--    Rsyntax OCTET STRING(SIZE(0..255))
    ACCESS read-only
    STATUS mandatory
    DESCRIPTION
        "This object represents the Last Switchover Time."
    ::= { cdbpLocalCfgs 9 }

cdbpLocalApplTable OBJECT-TYPE
    SYNTAX SEQUENCE OF CdbpLocalApplEntry
    ACCESS not-accessible
    STATUS mandatory
    DESCRIPTION
        "The table listing the Diameter applications
        supported by this server."
    ::= { cdbpLocalCfgs 10 }

cdbpLocalApplEntry OBJECT-TYPE
    SYNTAX CdbpLocalApplEntry
    ACCESS not-accessible
    STATUS mandatory
    DESCRIPTION
        "A row entry representing a Diameter
        application on this server."
    INDEX { cdbpLocalApplIndex }
    ::= { cdbpLocalApplTable 1 }

CdbpLocalApplEntry ::= SEQUENCE {
    cdbpLocalApplIndex Gauge,
    cdbpLocalApplStorageType StorageType,
    cdbpLocalApplRowStatus RowStatus
    }

cdbpLocalApplIndex OBJECT-TYPE
    SYNTAX Gauge(1..4294967295)
    ACCESS not-accessible
    STATUS mandatory
    DESCRIPTION
        "A number uniquely identifying a
        supported Diameter application. Upon reload, 
        cdbpLocalApplIndex values may be changed."
    ::= { cdbpLocalApplEntry 1 }

cdbpLocalApplStorageType OBJECT-TYPE
    SYNTAX StorageType
--    Rsyntax INTEGER {
--        other(1),
--        volatile(2),
--        nonVolatile(3),
--        permanent(4),
--        readOnly(5)
--        }
    ACCESS read-write
    STATUS mandatory
    DESCRIPTION
        "The storage type for this conceptual row. None of
        the columnar objects is writable when the conceptual
        row is permanent."
    REFERENCE
        "Textual Conventions for SMIv2, Section 2."
    DEFVAL { nonVolatile }
    ::= { cdbpLocalApplEntry 2 }

cdbpLocalApplRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this conceptual row.
        
        To create a row in this table, a manager must
        set this object to either createAndGo(4) or
        createAndWait(5).
        
        Until instances of all corresponding columns are
        appropriately configured, the value of the
        corresponding instance of the cdsgStatus column is
        'notReady'.
        
        In particular, a newly created row cannot be made
        active until the corresponding cdbpLocalApplIndex
        has been set.
        
        cdbpLocalApplIndex may not be modified while the
        value of this object is active(1):
        An attempt to set these objects while the value of
        cdbpLocalApplStatus is active(1) will result in
        an inconsistentValue error.
        
        Entries in this table with cdbpLocalApplStatus equal to
        active(1) remain in the table until destroyed.  
        
        Entries in this table with cdbpLocalApplStatus equal to 
        values other than active(1) will be destroyed after timeout
        (5 minutes)."
    ::= { cdbpLocalApplEntry 3 }

cdbpLocalVendorTable OBJECT-TYPE
    SYNTAX SEQUENCE OF CdbpLocalVendorEntry
    ACCESS not-accessible
    STATUS mandatory
    DESCRIPTION
        "The table listing the vendor IDs
        supported by local Diameter."
    ::= { cdbpLocalCfgs 11 }

cdbpLocalVendorEntry OBJECT-TYPE
    SYNTAX CdbpLocalVendorEntry
    ACCESS not-accessible
    STATUS mandatory
    DESCRIPTION
        "A row entry representing a
        vendor ID supported by local Diameter."
    INDEX { cdbpLocalVendorIndex }
    ::= { cdbpLocalVendorTable 1 }

CdbpLocalVendorEntry ::= SEQUENCE {
    cdbpLocalVendorIndex Gauge,
    cdbpLocalVendorId INTEGER,
    cdbpLocalVendorStorageType StorageType,
    cdbpLocalVendorRowStatus RowStatus
    }

cdbpLocalVendorIndex OBJECT-TYPE
    SYNTAX Gauge(1..4294967295)
    ACCESS not-accessible
    STATUS mandatory
    DESCRIPTION
        "A number uniquely identifying the vendor
        ID supported by local Diameter. Upon reload,
        cdbpLocalVendorIndex values may be changed."
    ::= { cdbpLocalVendorEntry 1 }

cdbpLocalVendorId OBJECT-TYPE
    SYNTAX INTEGER {
        --?? enum value of zero may cause problems
        diameterVendorIetf(0),
        diameterVendorCisco(9),
        diameterVendor3gpp(10415),
        diameterVendorVodafone(12645)
        }
    ACCESS read-write
    STATUS mandatory
    DESCRIPTION
        "The active vendor ID used for peer connections.
        diameterVendorIetf(0)         - Diameter vendor
                                        id ietf
        diameterVendorCisco(9)        - Diameter vendor
                                        id cisco
        diameterVendor3gpp(10415)     - Diameter vendor
                                        id 3gpp
        diameterVendorVodafone(12645) - Diameter vendor
                                        id vodafone."
    DEFVAL { diameterVendorIetf }
    ::= { cdbpLocalVendorEntry 2 }

cdbpLocalVendorStorageType OBJECT-TYPE
    SYNTAX StorageType
--    Rsyntax INTEGER {
--        other(1),
--        volatile(2),
--        nonVolatile(3),
--        permanent(4),
--        readOnly(5)
--        }
    ACCESS read-write
    STATUS mandatory
    DESCRIPTION
        "The storage type for this conceptual row.
        None of the objects are writable when the
        conceptual row is permanent."
    REFERENCE
        "Textual Conventions for SMIv2, Section 2."
    DEFVAL { nonVolatile }
    ::= { cdbpLocalVendorEntry 3 }

cdbpLocalVendorRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this conceptual row.
        
        To create a row in this table, a manager must
        set this object to either createAndGo(4) or
        createAndWait(5).
        
        Until instances of all corresponding columns are
        appropriately configured, the value of the
        corresponding instance of the cdbpLocalVendorRowStatus
        column is 'notReady'.
        
        In particular, a newly created row cannot be made
        active until the corresponding cdbpLocalVendorId has been
        set. 
        cdbpLocalVendorId may not be modified while the
        value of this object is active(1):
        An attempt to set these objects while the value of
        cdbpLocalVendorRowStatus is active(1) will result in
        an inconsistentValue error.
        
        Entries in this table with cdbpLocalVendorRowStatus equal to
        active(1) remain in the table until destroyed.  
        
        Entries in this table with cdbpLocalVendorRowStatus equal to
        values other than active(1) will be destroyed after timeout
        (5 minutes)."
    ::= { cdbpLocalVendorEntry 4 }

cdbpAppAdvToPeerTable OBJECT-TYPE
    SYNTAX SEQUENCE OF CdbpAppAdvToPeerEntry
    ACCESS not-accessible
    STATUS mandatory
    DESCRIPTION
        "The table listing the applications advertised by
        this host to each peer and the types of service
        supported: accounting, authentication or both."
    ::= { cdbpLocalCfgs 12 }

cdbpAppAdvToPeerEntry OBJECT-TYPE
    SYNTAX CdbpAppAdvToPeerEntry
    ACCESS not-accessible
    STATUS mandatory
    DESCRIPTION
        "A row entry representing a discovered or
        configured Diameter peer server."
    INDEX { cdbpPeerIndex, cdbpAppAdvToPeerVendorId, cdbpAppAdvToPeerIndex }
    ::= { cdbpAppAdvToPeerTable 1 }

CdbpAppAdvToPeerEntry ::= SEQUENCE {
    cdbpAppAdvToPeerVendorId Gauge,
    cdbpAppAdvToPeerIndex Gauge,
    cdbpAppAdvToPeerServices INTEGER,
    cdbpAppAdvToPeerStorageType StorageType,
    cdbpAppAdvToPeerRowStatus RowStatus
    }

cdbpAppAdvToPeerVendorId OBJECT-TYPE
    SYNTAX Gauge(1..4294967295)
    ACCESS not-accessible
    STATUS mandatory
    DESCRIPTION
        "The IANA Enterprise Code value assigned to
        the vendor of the Diameter device."
    ::= { cdbpAppAdvToPeerEntry 1 }

cdbpAppAdvToPeerIndex OBJECT-TYPE
    SYNTAX Gauge(1..4294967295)
    ACCESS not-accessible
    STATUS mandatory
    DESCRIPTION
        "A number uniquely identifying the Diameter
        applications advertised as supported by
        this host to each peer. Upon reload,
        cdbpAppAdvToPeerIndex values may be changed."
    ::= { cdbpAppAdvToPeerEntry 2 }

cdbpAppAdvToPeerServices OBJECT-TYPE
    SYNTAX INTEGER {
        acct(1),
        auth(2),
        both(3)
        }
    ACCESS read-only
    STATUS mandatory
    DESCRIPTION
        "The type of services supported for each application,
        accounting, authentication or both.
            acct(1)  -  accounting
            auth(2)  -  authentication
            both(3)  -  both accounting and authentication."
    ::= { cdbpAppAdvToPeerEntry 3 }

cdbpAppAdvToPeerStorageType OBJECT-TYPE
    SYNTAX StorageType
--    Rsyntax INTEGER {
--        other(1),
--        volatile(2),
--        nonVolatile(3),
--        permanent(4),
--        readOnly(5)
--        }
    ACCESS read-write
    STATUS mandatory
    DESCRIPTION
        "The storage type for this conceptual row.
        None of the objects are writable when the
        conceptual row is permanent."
    REFERENCE
        "Textual Conventions for SMIv2, Section 2."
    DEFVAL { nonVolatile }
    ::= { cdbpAppAdvToPeerEntry 4 }

cdbpAppAdvToPeerRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this conceptual row.
        
        To create a row in this table, a manager must
        set this object to either createAndGo(4) or
        createAndWait(5).
        
        Until instances of all corresponding columns are
        appropriately configured, the value of the
        corresponding instance of the cdbpAppAdvToPeerRowStatus
        column is 'notReady'.
        
        In particular, a newly created row cannot be made
        active until the corresponding cdbpAppAdvToPeerVendorId has
        been set.
        
        cdbpAppAdvToPeerVendorId may not be modified while the
        value of this object is active(1):
        An attempt to set these objects while the value of
        cdbpAppAdvToPeerRowStatus is active(1) will result in
        an inconsistentValue error.
        
        Entries in this table with cdbpAppAdvToPeerRowStatus equal
        to active(1) remain in the table until destroyed.  
        
        Entries in this table with cdbpAppAdvToPeerRowStatus equal
        to values other than active(1) will be destroyed after
        timeout (5 minutes)."
    ::= { cdbpAppAdvToPeerEntry 5 }

cdbpLocalStatsTotalPacketsIn OBJECT-TYPE
    SYNTAX Counter
--  Units
--    packets
    ACCESS read-only
    STATUS mandatory
    DESCRIPTION
        "The total number of packets received by Diameter
        Base Protocol."
    ::= { cdbpLocalStats 1 }

cdbpLocalStatsTotalPacketsOut OBJECT-TYPE
    SYNTAX Counter
--  Units
--    packets
    ACCESS read-only
    STATUS mandatory
    DESCRIPTION
        "The total number of packets transmitted by Diameter Base
        Protocol."
    ::= { cdbpLocalStats 2 }

cdbpLocalStatsTotalUpTime OBJECT-TYPE
    SYNTAX TimeTicks
    ACCESS read-only
    STATUS mandatory
    DESCRIPTION
        "This object represents the total time the Diameter server
        has been up until now."
    ::= { cdbpLocalStats 3 }

cdbpLocalResetTime OBJECT-TYPE
    SYNTAX TimeTicks
    ACCESS read-only
    STATUS mandatory
    DESCRIPTION
        "If the server keeps persistent state (e.g., a process)
        and supports a 'reset' operation (e.g., can be told to
        re-read configuration files), this value will be the
        time elapsed (in hundredths of a second) since the
        server was 'reset'.  For software that does not
        have persistence or does not support a 'reset'
        operation, this value will be zero."
    ::= { cdbpLocalStats 4 }

cdbpLocalConfigReset OBJECT-TYPE
    SYNTAX INTEGER {
        other(1),
        reset(2),
        initializing(3),
        running(4)
        }
    ACCESS read-write
    STATUS mandatory
    DESCRIPTION
        "Status/action object to reinitialize any persistent
        server state.  When set to reset(2), any persistent
        server state (such as a process) is reinitialized as
        if the server had just been started.  This value will
        never be returned by a read operation.  When read,
        one of the following values will be returned:
           other(1)        - server in some unknown state.
           reset(2)        - command to reinitialize server state.
           initializing(3) - server (re)initializing.
           running(4)      - server currently running."
    DEFVAL { other }
    ::= { cdbpLocalStats 5 }

cdbpPeerTable OBJECT-TYPE
    SYNTAX SEQUENCE OF CdbpPeerEntry
    ACCESS not-accessible
    STATUS mandatory
    DESCRIPTION
        "The table listing information regarding
        the discovered or configured Diameter
        peer servers."
    ::= { cdbpPeerCfgs 1 }

cdbpPeerEntry OBJECT-TYPE
    SYNTAX CdbpPeerEntry
    ACCESS not-accessible
    STATUS mandatory
    DESCRIPTION
        "A row entry representing a discovered
        or configured Diameter peer server."
    INDEX { cdbpPeerIndex }
    ::= { cdbpPeerTable 1 }

CdbpPeerEntry ::= SEQUENCE {
    cdbpPeerIndex Gauge,
    cdbpPeerId SnmpAdminString,
    cdbpPeerPortConnect Gauge,
    cdbpPeerPortListen Gauge,
    cdbpPeerProtocol INTEGER,
    cdbpPeerSecurity INTEGER,
    cdbpPeerFirmwareRevision Gauge,
    cdbpPeerStorageType StorageType,
    cdbpPeerRowStatus RowStatus
    }

cdbpPeerIndex OBJECT-TYPE
    SYNTAX Gauge(1..4294967295)
    ACCESS not-accessible
    STATUS mandatory
    DESCRIPTION
        "A number uniquely identifying each Diameter peer
        with which the host server communicates. Upon reload,
        cdbpPeerIndex values may be changed."
    ::= { cdbpPeerEntry 1 }

cdbpPeerId OBJECT-TYPE
    SYNTAX SnmpAdminString
--    Rsyntax OCTET STRING(SIZE(0..255))
    ACCESS read-write
    STATUS mandatory
    DESCRIPTION
        "The server identifier for the Diameter peer. It must
        be unique and non-empty."
    ::= { cdbpPeerEntry 2 }

cdbpPeerPortConnect OBJECT-TYPE
    SYNTAX Gauge(0..65535)
    ACCESS read-only
    STATUS mandatory
    DESCRIPTION
        "The connection port this server used
        to connect to the Diameter peer.
        If there is no active connection, this
        value will be zero(0)."
    DEFVAL { 0 }
    ::= { cdbpPeerEntry 3 }

cdbpPeerPortListen OBJECT-TYPE
    SYNTAX Gauge(1..65535)
    ACCESS read-write
    STATUS mandatory
    DESCRIPTION
        "The port the server is listening on."
    DEFVAL { 3868 }
    ::= { cdbpPeerEntry 4 }

cdbpPeerProtocol OBJECT-TYPE
    SYNTAX INTEGER {
        tcp(1),
        sctp(2)
        }
    ACCESS read-only
    STATUS mandatory
    DESCRIPTION
        "The transport protocol (tcp/sctp) the
        Diameter peer is using.
           tcp(1)  -  Transmission Control Protocol
           sctp(2) -  Stream Control Transmission Protocol."
    DEFVAL { tcp }
    ::= { cdbpPeerEntry 5 }

cdbpPeerSecurity OBJECT-TYPE
    SYNTAX INTEGER {
        other(1),
        tls(2),
        ipsec(3)
        }
    ACCESS read-only
    STATUS mandatory
    DESCRIPTION
        "The security the Diameter peer is using.
        other(1) - Unknown Security Protocol.
        tls(2)   - Transport Layer Security Protocol.
        ipsec(3) - Internet Protocol Security."
    DEFVAL { other }
    ::= { cdbpPeerEntry 6 }

cdbpPeerFirmwareRevision OBJECT-TYPE
    SYNTAX Gauge(1..4294967295)
    ACCESS read-only
    STATUS mandatory
    DESCRIPTION
        "Firmware revision of peer.  If no firmware
        revision, the revision of the Diameter software
        module may be reported instead."
    ::= { cdbpPeerEntry 7 }

cdbpPeerStorageType OBJECT-TYPE
    SYNTAX StorageType
--    Rsyntax INTEGER {
--        other(1),
--        volatile(2),
--        nonVolatile(3),
--        permanent(4),
--        readOnly(5)
--        }
    ACCESS read-write
    STATUS mandatory
    DESCRIPTION
        "The storage type for this conceptual row.
        Only cdbpPeerPortListen object is writable when the
        conceptual row is permanent."
    REFERENCE
        "Textual Conventions for SMIv2, Section 2."
    DEFVAL { nonVolatile }
    ::= { cdbpPeerEntry 8 }

cdbpPeerRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this conceptual row.
        
        To create a row in this table, a manager must
        set this object to either createAndGo(4) or
        createAndWait(5).
        
        Until instances of all corresponding columns are
        appropriately configured, the value of the
        corresponding instance of the cdbpPeerRowStatus column is
        'notReady'.
        
        In particular, a newly created row cannot be made
        active until the corresponding
        cdbpPeerId has been set.
        
        cdbpPeerId may not be modified while the
        value of this object is active(1):
        An attempt to set these objects while the value of
        cdbpPeerRowStatus is active(1) will result in
        an inconsistentValue error.
        
        Entries in this table with cdbpPeerRowStatus equal to
        active(1) remain in the table until destroyed.  
        
        Entries in this table with cdbpPeerRowStatus equal to 
        values other than active(1) will be destroyed after timeout
        (5 minutes)."
    ::= { cdbpPeerEntry 9 }

cdbpPeerIpAddrTable OBJECT-TYPE
    SYNTAX SEQUENCE OF CdbpPeerIpAddrEntry
    ACCESS not-accessible
    STATUS mandatory
    DESCRIPTION
        "The table listing the Diameter
        server IP Addresses."
    ::= { cdbpPeerCfgs 2 }

cdbpPeerIpAddrEntry OBJECT-TYPE
    SYNTAX CdbpPeerIpAddrEntry
    ACCESS not-accessible
    STATUS mandatory
    DESCRIPTION
        "A row entry representing peer
        Diameter server IP Addresses."
    INDEX { cdbpPeerIndex, cdbpPeerIpAddressIndex }
    ::= { cdbpPeerIpAddrTable 1 }

CdbpPeerIpAddrEntry ::= SEQUENCE {
    cdbpPeerIpAddressIndex Gauge,
    cdbpPeerIpAddressType InetAddressType,
    cdbpPeerIpAddress IpAddress
    }

cdbpPeerIpAddressIndex OBJECT-TYPE
    SYNTAX Gauge(1..4294967295)
    ACCESS not-accessible
    STATUS mandatory
    DESCRIPTION
        "A number uniquely identifying the number
        of IP Addresses supported by all Diameter
        peers."
    ::= { cdbpPeerIpAddrEntry 1 }

cdbpPeerIpAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "The type of address stored in
        diameterPeerIpAddress."
    ::= { cdbpPeerIpAddrEntry 2 }

cdbpPeerIpAddress OBJECT-TYPE
    SYNTAX IpAddress
    ACCESS read-write
    STATUS mandatory
    DESCRIPTION
        "The active IP Address(es) used for connections."
    ::= { cdbpPeerIpAddrEntry 3 }

cdbpAppAdvFromPeerTable OBJECT-TYPE
    SYNTAX SEQUENCE OF CdbpAppAdvFromPeerEntry
    ACCESS not-accessible
    STATUS mandatory
    DESCRIPTION
        "The table listing the applications advertised by
        each peer to this host and the types of service
        supported: accounting, authentication or both."
    ::= { cdbpPeerCfgs 3 }

cdbpAppAdvFromPeerEntry OBJECT-TYPE
    SYNTAX CdbpAppAdvFromPeerEntry
    ACCESS not-accessible
    STATUS mandatory
    DESCRIPTION
        "A row entry representing a discovered or
        configured Diameter peer server."
    INDEX { cdbpPeerIndex, cdbpAppAdvFromPeerVendorId, cdbpAppAdvFromPeerIndex }
    ::= { cdbpAppAdvFromPeerTable 1 }

CdbpAppAdvFromPeerEntry ::= SEQUENCE {
    cdbpAppAdvFromPeerVendorId Gauge,
    cdbpAppAdvFromPeerIndex Gauge,
    cdbpAppAdvFromPeerType INTEGER
    }

cdbpAppAdvFromPeerVendorId OBJECT-TYPE
    SYNTAX Gauge(1..4294967295)
    ACCESS not-accessible
    STATUS mandatory
    DESCRIPTION
        "The IANA Enterprise Code value assigned to
        the vendor of the Diameter device."
    ::= { cdbpAppAdvFromPeerEntry 1 }

cdbpAppAdvFromPeerIndex OBJECT-TYPE
    SYNTAX Gauge(1..4294967295)
    ACCESS not-accessible
    STATUS mandatory
    DESCRIPTION
        "A number uniquely identifying the applications
        advertised as supported from each Diameter peer."
    ::= { cdbpAppAdvFromPeerEntry 2 }

cdbpAppAdvFromPeerType OBJECT-TYPE
    SYNTAX INTEGER {
        acct(1),
        auth(2),
        both(3)
        }
    ACCESS read-only
    STATUS mandatory
    DESCRIPTION
        "The type of services supported for each application,
        accounting, authentication or both.
            acct(1)  -  accounting
            auth(2)  -  authentication
            both(3)  -  both accounting and authentication."
    ::= { cdbpAppAdvFromPeerEntry 3 }

cdbpPeerVendorTable OBJECT-TYPE
    SYNTAX SEQUENCE OF CdbpPeerVendorEntry
    ACCESS not-accessible
    STATUS mandatory
    DESCRIPTION
        "The table listing the Vendor IDs
        supported by the peer."
    ::= { cdbpPeerCfgs 4 }

cdbpPeerVendorEntry OBJECT-TYPE
    SYNTAX CdbpPeerVendorEntry
    ACCESS not-accessible
    STATUS mandatory
    DESCRIPTION
        "A row entry representing a
        Vendor ID supported by the peer."
    INDEX { cdbpPeerIndex, cdbpPeerVendorIndex }
    ::= { cdbpPeerVendorTable 1 }

CdbpPeerVendorEntry ::= SEQUENCE {
    cdbpPeerVendorIndex Gauge,
    cdbpPeerVendorId INTEGER,
    cdbpPeerVendorStorageType StorageType,
    cdbpPeerVendorRowStatus RowStatus
    }

cdbpPeerVendorIndex OBJECT-TYPE
    SYNTAX Gauge(1..4294967295)
    ACCESS not-accessible
    STATUS mandatory
    DESCRIPTION
        "A number uniquely identifying the Vendor
        ID supported by the peer. Upon reload,
        cdbpPeerVendorIndex values may be changed."
    ::= { cdbpPeerVendorEntry 1 }

cdbpPeerVendorId OBJECT-TYPE
    SYNTAX INTEGER {
        --?? enum value of zero may cause problems
        diameterVendorIetf(0),
        diameterVendorCisco(9),
        diameterVendor3gpp(10415),
        diameterVendorVodafone(12645)
        }
    ACCESS read-write
    STATUS mandatory
    DESCRIPTION
        "The active vendor ID used for peer connections.
        diameterVendorIetf(0)         - Diameter vendor
                                        id ietf
        diameterVendorCisco(9)        - Diameter vendor
                                        id cisco
        diameterVendor3gpp(10415)     - Diameter vendor
                                        id 3gpp
        diameterVendorVodafone(12645) - Diameter vendor
                                        id vodafone."
    DEFVAL { diameterVendorIetf }
    ::= { cdbpPeerVendorEntry 2 }

cdbpPeerVendorStorageType OBJECT-TYPE
    SYNTAX StorageType
--    Rsyntax INTEGER {
--        other(1),
--        volatile(2),
--        nonVolatile(3),
--        permanent(4),
--        readOnly(5)
--        }
    ACCESS read-write
    STATUS mandatory
    DESCRIPTION
        "The storage type for this conceptual row.
        None of the objects are writable when the
        conceptual row is permanent."
    REFERENCE
        "Textual Conventions for SMIv2, Section 2."
    DEFVAL { nonVolatile }
    ::= { cdbpPeerVendorEntry 3 }

cdbpPeerVendorRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this conceptual row.
        
        To create a row in this table, a manager must
        set this object to either createAndGo(4) or
        createAndWait(5).
        
        Until instances of all corresponding columns are
        appropriately configured, the value of the
        corresponding instance of the cdbpPeerVendorRowStatus column
        is 'notReady'.
        
        In particular, a newly created row cannot be made
        active until the corresponding cdbpPeerVendorId has been
        set. Also, a newly created row cannot be made active until
        the corresponding 'cdbpPeerIndex' has been set.
        
        cdbpPeerVendorId may not be modified while the
        value of this object is active(1):
        An attempt to set these objects while the value of
        cdbpPeerVendorRowStatus is active(1) will result in
        an inconsistentValue error.
        
        Entries in this table with cdbpPeerVendorRowStatus equal to
        active(1) remain in the table until destroyed.  
        
        Entries in this table with cdbpPeerVendorRowStatus equal to 
        values other than active(1) will be destroyed after timeout
        (5 minutes)."
    ::= { cdbpPeerVendorEntry 4 }

cdbpPeerStatsTable OBJECT-TYPE
    SYNTAX SEQUENCE OF CdbpPeerStatsEntry
    ACCESS not-accessible
    STATUS mandatory
    DESCRIPTION
        "The table listing the Diameter peer statistics."
    ::= { cdbpPeerStats 1 }

cdbpPeerStatsEntry OBJECT-TYPE
    SYNTAX CdbpPeerStatsEntry
    ACCESS not-accessible
    STATUS mandatory
    DESCRIPTION
        "A row entry representing a Diameter peer."
    INDEX { cdbpPeerIndex }
    ::= { cdbpPeerStatsTable 1 }

CdbpPeerStatsEntry ::= SEQUENCE {
    cdbpPeerStatsState INTEGER,
    cdbpPeerStatsStateDuration TimeTicks,
    cdbpPeerStatsLastDiscCause INTEGER,
    cdbpPeerStatsWhoInitDisconnect INTEGER,
    cdbpPeerStatsDWCurrentStatus INTEGER,
    cdbpPeerStatsTimeoutConnAtmpts Counter,
    cdbpPeerStatsASRsIn Counter,
    cdbpPeerStatsASRsOut Counter,
    cdbpPeerStatsASAsIn Counter,
    cdbpPeerStatsASAsOut Counter,
    cdbpPeerStatsACRsIn Counter,
    cdbpPeerStatsACRsOut Counter,
    cdbpPeerStatsACAsIn Counter,
    cdbpPeerStatsACAsOut Counter,
    cdbpPeerStatsCERsIn Counter,
    cdbpPeerStatsCERsOut Counter,
    cdbpPeerStatsCEAsIn Counter,
    cdbpPeerStatsCEAsOut Counter,
    cdbpPeerStatsDWRsIn Counter,
    cdbpPeerStatsDWRsOut Counter,
    cdbpPeerStatsDWAsIn Counter,
    cdbpPeerStatsDWAsOut Counter,
    cdbpPeerStatsDPRsIn Counter,
    cdbpPeerStatsDPRsOut Counter,
    cdbpPeerStatsDPAsIn Counter,
    cdbpPeerStatsDPAsOut Counter,
    cdbpPeerStatsRARsIn Counter,
    cdbpPeerStatsRARsOut Counter,
    cdbpPeerStatsRAAsIn Counter,
    cdbpPeerStatsRAAsOut Counter,
    cdbpPeerStatsSTRsIn Counter,
    cdbpPeerStatsSTRsOut Counter,
    cdbpPeerStatsSTAsIn Counter,
    cdbpPeerStatsSTAsOut Counter,
    cdbpPeerStatsDWReqTimer TimeTicks,
    cdbpPeerStatsRedirectEvents Counter,
    cdbpPeerStatsAccDupRequests Counter,
    cdbpPeerStatsMalformedReqsts Counter,
    cdbpPeerStatsAccsNotRecorded Counter,
    cdbpPeerStatsAccRetrans Counter,
    cdbpPeerStatsTotalRetrans Counter,
    cdbpPeerStatsAccPendReqstsOut Gauge,
    cdbpPeerStatsAccReqstsDropped Counter,
    cdbpPeerStatsHByHDropMessages Counter,
    cdbpPeerStatsEToEDupMessages Counter,
    cdbpPeerStatsUnknownTypes Counter,
    cdbpPeerStatsProtocolErrors Counter,
    cdbpPeerStatsTransientFailures Counter,
    cdbpPeerStatsPermanentFailures Counter,
    cdbpPeerStatsTransportDown Counter
    }

cdbpPeerStatsState OBJECT-TYPE
    SYNTAX INTEGER {
        closed(1),
        waitConnAck(2),
        waitICEA(3),
        elect(4),
        waitReturns(5),
        rOpen(6),
        iOpen(7),
        closing(8)
        }
    ACCESS read-only
    STATUS mandatory
    DESCRIPTION
        "Connection state in the Peer State Machine of
        the peer with which this Diameter server is
        communicating.
          closed(1)      - Connection closed with this peer.
          waitConnAck(2) - Waiting for an acknowledgment
                           from this peer.
          waitICEA(3)    - Waiting for a Capabilities-Exchange-
                           Answer from this peer.
          elect(4)       - When the peer and the server are both
                           trying to bring up a connection with
                           each other at the same time.  An
                           election process begins which
                           determines which socket remains open.
          waitReturns(5) - Waiting for election returns.
          r-open(6)      - Responder transport connection is
                           used for communication.
          i-open(7)      - Initiator transport connection is
                           used for communication.
          closing(8)     - Actively closing and doing cleanup."
    ::= { cdbpPeerStatsEntry 1 }

cdbpPeerStatsStateDuration OBJECT-TYPE
    SYNTAX TimeTicks
    ACCESS read-only
    STATUS mandatory
    DESCRIPTION
        "This object represents the Peer state duration."
    ::= { cdbpPeerStatsEntry 2 }

cdbpPeerStatsLastDiscCause OBJECT-TYPE
    SYNTAX INTEGER {
        rebooting(1),
        busy(2),
        doNotWantToTalk(3),
        election(4)
        }
    ACCESS read-only
    STATUS mandatory
    DESCRIPTION
        "The last cause for a peers disconnection.
        rebooting(1)       - A scheduled reboot is imminent.
        busy(2)            - The peer's internal resources are
                             constrained, and it has determined
                             that the transport connection needs
                             to be shutdown.
        doNotWantToTalk(3) - The peer has determined that
                             it does not see a need for the
                             transport connection to exist,
                             since it does not expect any
                             messages to be exchanged in
                             the foreseeable future.
        electionLost(4)    - The peer has determined that it
                             has lost the election process
                             and has therefore disconnected
                             the transport connection."
    ::= { cdbpPeerStatsEntry 3 }

cdbpPeerStatsWhoInitDisconnect OBJECT-TYPE
    SYNTAX INTEGER {
        host(1),
        peer(2)
        }
    ACCESS read-only
    STATUS mandatory
    DESCRIPTION
        "Did the host or peer initiate the disconnect?
        
        host(1) - If this server initiated the disconnect.
        peer(2) - If the peer with which this server was
                  connected initiated the disconnect."
    ::= { cdbpPeerStatsEntry 4 }

cdbpPeerStatsDWCurrentStatus OBJECT-TYPE
    SYNTAX INTEGER {
        okay(1),
        suspect(2),
        down(3),
        reopen(4)
        }
    ACCESS read-only
    STATUS mandatory
    DESCRIPTION
        "This object indicates the connection status.
        okay(1)    - Indicates the connection is presumed working.
        suspect(2) - Indicates the connection is possibly
                     congested or down.
        down(3)    - The peer is no longer reachable, causing
                     the transport connection to be shutdown.
        reopen(4)  - Three watchdog messages are exchanged with
                     accepted round trip times, and the connection
                     to the peer is considered stabilized."
    ::= { cdbpPeerStatsEntry 5 }

cdbpPeerStatsTimeoutConnAtmpts OBJECT-TYPE
    SYNTAX Counter
--  Units
--    attempts
    ACCESS read-only
    STATUS mandatory
    DESCRIPTION
        "If there is no transport connection with a peer,
        this is the number of times the server attempts
        to connect to that peer.  This is reset on
        disconnection."
    ::= { cdbpPeerStatsEntry 6 }

cdbpPeerStatsASRsIn OBJECT-TYPE
    SYNTAX Counter
--  Units
--    messages
    ACCESS read-only
    STATUS mandatory
    DESCRIPTION
        "Abort-Session-Request messages received
        from the peer."
    ::= { cdbpPeerStatsEntry 7 }

cdbpPeerStatsASRsOut OBJECT-TYPE
    SYNTAX Counter
--  Units
--    messages
    ACCESS read-only
    STATUS mandatory
    DESCRIPTION
        "Abort-Session-Request messages
        sent to the peer."
    ::= { cdbpPeerStatsEntry 8 }

cdbpPeerStatsASAsIn OBJECT-TYPE
    SYNTAX Counter
--  Units
--    messages
    ACCESS read-only
    STATUS mandatory
    DESCRIPTION
        "Number of Abort-Session-Answer
        messages received from the peer."
    ::= { cdbpPeerStatsEntry 9 }

cdbpPeerStatsASAsOut OBJECT-TYPE
    SYNTAX Counter
--  Units
--    messages
    ACCESS read-only
    STATUS mandatory
    DESCRIPTION
        "Number of Abort-Session-Answer
        messages sent to the peer."
    ::= { cdbpPeerStatsEntry 10 }

cdbpPeerStatsACRsIn OBJECT-TYPE
    SYNTAX Counter
--  Units
--    messages
    ACCESS read-only
    STATUS mandatory
    DESCRIPTION
        "Number of Accounting-Request messages
        received from the peer."
    ::= { cdbpPeerStatsEntry 11 }

cdbpPeerStatsACRsOut OBJECT-TYPE
    SYNTAX Counter
--  Units
--    messages
    ACCESS read-only
    STATUS mandatory
    DESCRIPTION
        "Number of Accounting-Request messages
        sent to the peer."
    ::= { cdbpPeerStatsEntry 12 }

cdbpPeerStatsACAsIn OBJECT-TYPE
    SYNTAX Counter
--  Units
--    messages
    ACCESS read-only
    STATUS mandatory
    DESCRIPTION
        "Number of Accounting-Answer messages
        received from the peer."
    ::= { cdbpPeerStatsEntry 13 }

cdbpPeerStatsACAsOut OBJECT-TYPE
    SYNTAX Counter
--  Units
--    messages
    ACCESS read-only
    STATUS mandatory
    DESCRIPTION
        "Number of Accounting-Answer messages
        sent to the peer."
    ::= { cdbpPeerStatsEntry 14 }

cdbpPeerStatsCERsIn OBJECT-TYPE
    SYNTAX Counter
--  Units
--    messages
    ACCESS read-only
    STATUS mandatory
    DESCRIPTION
        "Number of Capabilities-Exchange-Request
        messages received from the peer."
    ::= { cdbpPeerStatsEntry 15 }

cdbpPeerStatsCERsOut OBJECT-TYPE
    SYNTAX Counter
--  Units
--    messages
    ACCESS read-only
    STATUS mandatory
    DESCRIPTION
        "Number of Capabilities-Exchange-Request
        messages sent to the peer."
    ::= { cdbpPeerStatsEntry 16 }

cdbpPeerStatsCEAsIn OBJECT-TYPE
    SYNTAX Counter
--  Units
--    messages
    ACCESS read-only
    STATUS mandatory
    DESCRIPTION
        "Number of Capabilities-Exchange-Answer
        messages received from the peer."
    ::= { cdbpPeerStatsEntry 17 }

cdbpPeerStatsCEAsOut OBJECT-TYPE
    SYNTAX Counter
--  Units
--    messages
    ACCESS read-only
    STATUS mandatory
    DESCRIPTION
        "Number of Capabilities-Exchange-Answer
        messages sent to the peer."
    ::= { cdbpPeerStatsEntry 18 }

cdbpPeerStatsDWRsIn OBJECT-TYPE
    SYNTAX Counter
--  Units
--    messages
    ACCESS read-only
    STATUS mandatory
    DESCRIPTION
        "Number of Device-Watchdog-Request
        messages received from the peer."
    ::= { cdbpPeerStatsEntry 19 }

cdbpPeerStatsDWRsOut OBJECT-TYPE
    SYNTAX Counter
--  Units
--    messages
    ACCESS read-only
    STATUS mandatory
    DESCRIPTION
        "Number of Device-Watchdog-Request
        messages sent to the peer."
    ::= { cdbpPeerStatsEntry 20 }

cdbpPeerStatsDWAsIn OBJECT-TYPE
    SYNTAX Counter
--  Units
--    messages
    ACCESS read-only
    STATUS mandatory
    DESCRIPTION
        "Number of Device-Watchdog-Answer
        messages received from the peer."
    ::= { cdbpPeerStatsEntry 21 }

cdbpPeerStatsDWAsOut OBJECT-TYPE
    SYNTAX Counter
--  Units
--    messages
    ACCESS read-only
    STATUS mandatory
    DESCRIPTION
        "Number of Device-Watchdog-Answer
        messages sent to the peer."
    ::= { cdbpPeerStatsEntry 22 }

cdbpPeerStatsDPRsIn OBJECT-TYPE
    SYNTAX Counter
--  Units
--    messages
    ACCESS read-only
    STATUS mandatory
    DESCRIPTION
        "Number of Disconnect-Peer-Request messages
        received."
    ::= { cdbpPeerStatsEntry 23 }

cdbpPeerStatsDPRsOut OBJECT-TYPE
    SYNTAX Counter
--  Units
--    messages
    ACCESS read-only
    STATUS mandatory
    DESCRIPTION
        "Number of Disconnect-Peer-Request messages
        sent."
    ::= { cdbpPeerStatsEntry 24 }

cdbpPeerStatsDPAsIn OBJECT-TYPE
    SYNTAX Counter
--  Units
--    messages
    ACCESS read-only
    STATUS mandatory
    DESCRIPTION
        "Number of Disconnect-Peer-Answer messages
        received."
    ::= { cdbpPeerStatsEntry 25 }

cdbpPeerStatsDPAsOut OBJECT-TYPE
    SYNTAX Counter
--  Units
--    messages
    ACCESS read-only
    STATUS mandatory
    DESCRIPTION
        "Number of Disconnect-Peer-Answer messages
        sent."
    ::= { cdbpPeerStatsEntry 26 }

cdbpPeerStatsRARsIn OBJECT-TYPE
    SYNTAX Counter
--  Units
--    messages
    ACCESS read-only
    STATUS mandatory
    DESCRIPTION
        "Number of Re-Auth-Request messages
        received."
    ::= { cdbpPeerStatsEntry 27 }

cdbpPeerStatsRARsOut OBJECT-TYPE
    SYNTAX Counter
--  Units
--    messages
    ACCESS read-only
    STATUS mandatory
    DESCRIPTION
        "Number of Re-Auth-Request messages
        sent."
    ::= { cdbpPeerStatsEntry 28 }

cdbpPeerStatsRAAsIn OBJECT-TYPE
    SYNTAX Counter
--  Units
--    messages
    ACCESS read-only
    STATUS mandatory
    DESCRIPTION
        "Number of Re-Auth-Answer messages
        received."
    ::= { cdbpPeerStatsEntry 29 }

cdbpPeerStatsRAAsOut OBJECT-TYPE
    SYNTAX Counter
--  Units
--    messages
    ACCESS read-only
    STATUS mandatory
    DESCRIPTION
        "Number of Re-Auth-Answer messages
        sent."
    ::= { cdbpPeerStatsEntry 30 }

cdbpPeerStatsSTRsIn OBJECT-TYPE
    SYNTAX Counter
--  Units
--    messages
    ACCESS read-only
    STATUS mandatory
    DESCRIPTION
        "Number of Session-Termination-Request
        messages received from the peer."
    ::= { cdbpPeerStatsEntry 31 }

cdbpPeerStatsSTRsOut OBJECT-TYPE
    SYNTAX Counter
--  Units
--    messages
    ACCESS read-only
    STATUS mandatory
    DESCRIPTION
        "Number of Session-Termination-Request
        messages sent to the peer."
    ::= { cdbpPeerStatsEntry 32 }

cdbpPeerStatsSTAsIn OBJECT-TYPE
    SYNTAX Counter
--  Units
--    messages
    ACCESS read-only
    STATUS mandatory
    DESCRIPTION
        "Number of Session-Termination-Answer
        messages received from the peer."
    ::= { cdbpPeerStatsEntry 33 }

cdbpPeerStatsSTAsOut OBJECT-TYPE
    SYNTAX Counter
--  Units
--    messages
    ACCESS read-only
    STATUS mandatory
    DESCRIPTION
        "Number of Session-Termination-Answer
        messages sent to the peer."
    ::= { cdbpPeerStatsEntry 34 }

cdbpPeerStatsDWReqTimer OBJECT-TYPE
    SYNTAX TimeTicks
    ACCESS read-only
    STATUS mandatory
    DESCRIPTION
        "Device-Watchdog Request Timer, which
        is the interval between packets sent to
        peers."
    ::= { cdbpPeerStatsEntry 35 }

cdbpPeerStatsRedirectEvents OBJECT-TYPE
    SYNTAX Counter
    ACCESS read-only
    STATUS mandatory
    DESCRIPTION
        "Redirect Event count, which is the number
        of redirects sent from a peer."
    ::= { cdbpPeerStatsEntry 36 }

cdbpPeerStatsAccDupRequests OBJECT-TYPE
    SYNTAX Counter
    ACCESS read-only
    STATUS mandatory
    DESCRIPTION
        "The number of duplicate Diameter Accounting-Request
        packets received."
    ::= { cdbpPeerStatsEntry 37 }

cdbpPeerStatsMalformedReqsts OBJECT-TYPE
    SYNTAX Counter
    ACCESS read-only
    STATUS mandatory
    DESCRIPTION
        "The number of malformed Diameter
        packets received."
    ::= { cdbpPeerStatsEntry 38 }

cdbpPeerStatsAccsNotRecorded OBJECT-TYPE
    SYNTAX Counter
    ACCESS read-only
    STATUS mandatory
    DESCRIPTION
        "The number of Diameter Accounting-Request packets
        which were received and responded to but not
        recorded."
    ::= { cdbpPeerStatsEntry 39 }

cdbpPeerStatsAccRetrans OBJECT-TYPE
    SYNTAX Counter
    ACCESS read-only
    STATUS mandatory
    DESCRIPTION
        "The number of Diameter Accounting-Request packets
        retransmitted to this Diameter server."
    ::= { cdbpPeerStatsEntry 40 }

cdbpPeerStatsTotalRetrans OBJECT-TYPE
    SYNTAX Counter
    ACCESS read-only
    STATUS mandatory
    DESCRIPTION
        "The number of Diameter packets retransmitted
        to this Diameter server, not to include Diameter
        Accounting-Request packets retransmitted."
    ::= { cdbpPeerStatsEntry 41 }

cdbpPeerStatsAccPendReqstsOut OBJECT-TYPE
    SYNTAX Gauge
    ACCESS read-only
    STATUS mandatory
    DESCRIPTION
        "The number of Diameter Accounting-Request packets
        sent to this peer that have not yet timed out or
        received a response. This variable is incremented when an
        Accounting-Request is sent to this server and decremented
        due to receipt of an Accounting-Response, a timeout or
        a retransmission."
    ::= { cdbpPeerStatsEntry 42 }

cdbpPeerStatsAccReqstsDropped OBJECT-TYPE
    SYNTAX Counter
    ACCESS read-only
    STATUS mandatory
    DESCRIPTION
        "The number of Accounting-Requests to this server
        that have been dropped."
    ::= { cdbpPeerStatsEntry 43 }

cdbpPeerStatsHByHDropMessages OBJECT-TYPE
    SYNTAX Counter
    ACCESS read-only
    STATUS mandatory
    DESCRIPTION
        "An answer message that is received with an unknown
        hop-by-hop identifier.  Does not include accounting
        requests dropped."
    ::= { cdbpPeerStatsEntry 44 }

cdbpPeerStatsEToEDupMessages OBJECT-TYPE
    SYNTAX Counter
    ACCESS read-only
    STATUS mandatory
    DESCRIPTION
        "Duplicate answer messages that are to be locally
        consumed.  Does not include duplicate accounting
        requests received."
    ::= { cdbpPeerStatsEntry 45 }

cdbpPeerStatsUnknownTypes OBJECT-TYPE
    SYNTAX Counter
    ACCESS read-only
    STATUS mandatory
    DESCRIPTION
        "The number of Diameter packets of unknown type
        which were received."
    ::= { cdbpPeerStatsEntry 46 }

cdbpPeerStatsProtocolErrors OBJECT-TYPE
    SYNTAX Counter
    ACCESS read-only
    STATUS mandatory
    DESCRIPTION
        "This object represents the Number of protocol errors
        returned to peer, but not including redirects."
    ::= { cdbpPeerStatsEntry 47 }

cdbpPeerStatsTransientFailures OBJECT-TYPE
    SYNTAX Counter
    ACCESS read-only
    STATUS mandatory
    DESCRIPTION
        "This object represents the transient failure
        count."
    ::= { cdbpPeerStatsEntry 48 }

cdbpPeerStatsPermanentFailures OBJECT-TYPE
    SYNTAX Counter
    ACCESS read-only
    STATUS mandatory
    DESCRIPTION
        "This object represents the Number of permanent
        failures returned to peer."
    ::= { cdbpPeerStatsEntry 49 }

cdbpPeerStatsTransportDown OBJECT-TYPE
    SYNTAX Counter
    ACCESS read-only
    STATUS mandatory
    DESCRIPTION
        "This object represents the Number of unexpected
        transport failures."
    ::= { cdbpPeerStatsEntry 50 }

cdbpRealmKnownPeersTable OBJECT-TYPE
    SYNTAX SEQUENCE OF CdbpRealmKnownPeersEntry
    ACCESS not-accessible
    STATUS mandatory
    DESCRIPTION
        "The table listing the Diameter
        realms and known peers."
    ::= { cdbpRealmCfgs 1 }

cdbpRealmKnownPeersEntry OBJECT-TYPE
    SYNTAX CdbpRealmKnownPeersEntry
    ACCESS not-accessible
    STATUS mandatory
    DESCRIPTION
        "A row entry representing a Diameter
        realm and known peers."
    INDEX { cdbpRealmMessageRouteIndex, cdbpRealmKnownPeersIndex }
    ::= { cdbpRealmKnownPeersTable 1 }

CdbpRealmKnownPeersEntry ::= SEQUENCE {
    cdbpRealmKnownPeersIndex Gauge,
    cdbpRealmKnownPeers Gauge,
    cdbpRealmKnownPeersChosen INTEGER
    }

cdbpRealmKnownPeersIndex OBJECT-TYPE
    SYNTAX Gauge(1..4294967295)
    ACCESS not-accessible
    STATUS mandatory
    DESCRIPTION
        "A number uniquely identifying a peer
        known to this realm. Upon reload,
        cdbpRealmKnownPeersIndex values may be changed."
    ::= { cdbpRealmKnownPeersEntry 1 }

cdbpRealmKnownPeers OBJECT-TYPE
    SYNTAX Gauge(1..4294967295)
    ACCESS read-only
    STATUS mandatory
    DESCRIPTION
        "The index of the peer this realm knows about.
        This is an ordered list, where the ordering
        signifies the order in which the peers are
        tried.  Same as the cdbpPeerIndex"
    ::= { cdbpRealmKnownPeersEntry 2 }

cdbpRealmKnownPeersChosen OBJECT-TYPE
    SYNTAX INTEGER {
        roundRobin(1),
        loadBalance(2),
        firstPreferred(3),
        mostRecentFirst(4),
        other(5)
        }
    ACCESS read-only
    STATUS mandatory
    DESCRIPTION
        "How the realm chooses which peer to send
        packets to.
           roundRobin(1)      - The peer used for each transaction
                                is selected based on the order in
                                which peers are configured.
           loadBalance(2)     - The peer used for each transaction
                                is based on the load metric (maybe
                                implementation dependent) of all
                                peers defined for the realm, with
                                the least loaded server selected
                                first.
           firstPreferred(3)  - The first defined server is always
                                used for transactions unless
                                failover occurs.
           mostRecentFirst(4) - The most recently used server is
                                used first for each transaction."
    ::= { cdbpRealmKnownPeersEntry 3 }

cdbpRealmMessageRouteTable OBJECT-TYPE
    SYNTAX SEQUENCE OF CdbpRealmMessageRouteEntry
    ACCESS not-accessible
    STATUS mandatory
    DESCRIPTION
        "The table listing the Diameter
        realm-based message route information."
    ::= { cdbpRealmStats 1 }

cdbpRealmMessageRouteEntry OBJECT-TYPE
    SYNTAX CdbpRealmMessageRouteEntry
    ACCESS not-accessible
    STATUS mandatory
    DESCRIPTION
        "A row entry representing a Diameter
        realm based message route server."
    INDEX { cdbpRealmMessageRouteIndex }
    ::= { cdbpRealmMessageRouteTable 1 }

CdbpRealmMessageRouteEntry ::= SEQUENCE {
    cdbpRealmMessageRouteIndex Gauge,
    cdbpRealmMessageRouteRealm SnmpAdminString,
    cdbpRealmMessageRouteApp Gauge,
    cdbpRealmMessageRouteType INTEGER,
    cdbpRealmMessageRouteAction INTEGER,
    cdbpRealmMessageRouteACRsIn Counter,
    cdbpRealmMessageRouteACRsOut Counter,
    cdbpRealmMessageRouteACAsIn Counter,
    cdbpRealmMessageRouteACAsOut Counter,
    cdbpRealmMessageRouteRARsIn Counter,
    cdbpRealmMessageRouteRARsOut Counter,
    cdbpRealmMessageRouteRAAsIn Counter,
    cdbpRealmMessageRouteRAAsOut Counter,
    cdbpRealmMessageRouteSTRsIn Counter,
    cdbpRealmMessageRouteSTRsOut Counter,
    cdbpRealmMessageRouteSTAsIn Counter,
    cdbpRealmMessageRouteSTAsOut Counter,
    cdbpRealmMessageRouteASRsIn Counter,
    cdbpRealmMessageRouteASRsOut Counter,
    cdbpRealmMessageRouteASAsIn Counter,
    cdbpRealmMessageRouteASAsOut Counter,
    cdbpRealmMessageRouteAccRetrans Counter,
    cdbpRealmMessageRouteAccDupReqsts Counter,
    cdbpRealmMessageRoutePendReqstsOut Gauge,
    cdbpRealmMessageRouteReqstsDrop Counter
    }

cdbpRealmMessageRouteIndex OBJECT-TYPE
    SYNTAX Gauge(1..4294967295)
    ACCESS not-accessible
    STATUS mandatory
    DESCRIPTION
        "A number uniquely identifying each realm."
    ::= { cdbpRealmMessageRouteEntry 1 }

cdbpRealmMessageRouteRealm OBJECT-TYPE
    SYNTAX SnmpAdminString
--    Rsyntax OCTET STRING(SIZE(0..255))
    ACCESS read-only
    STATUS mandatory
    DESCRIPTION
        "This object represents the realm name"
    ::= { cdbpRealmMessageRouteEntry 2 }

cdbpRealmMessageRouteApp OBJECT-TYPE
    SYNTAX Gauge(1..4294967295)
    ACCESS read-only
    STATUS mandatory
    DESCRIPTION
        "Application id used to route packets
        to this realm."
    ::= { cdbpRealmMessageRouteEntry 3 }

cdbpRealmMessageRouteType OBJECT-TYPE
    SYNTAX INTEGER {
        acct(1),
        auth(2),
        both(3)
        }
    ACCESS read-only
    STATUS mandatory
    DESCRIPTION
        "The types of service supported for each
        realm application: accounting,
        authentication or both.
            acct(1)  -  accounting
            auth(2)  -  authentication
            both(3)  -  both accounting and authentication."
    ::= { cdbpRealmMessageRouteEntry 4 }

cdbpRealmMessageRouteAction OBJECT-TYPE
    SYNTAX INTEGER {
        local(1),
        relay(2),
        proxy(3),
        redirect(4)
        }
    ACCESS read-only
    STATUS mandatory
    DESCRIPTION
        "The action is used to identify how a
        message should be treated based on the realm,
        application and type.
           local(1)    - Diameter messages that resolve to a
                         route entry with the Local Action set to
                         Local can be satisfied locally, and do
                         not need to be routed to another server.
           relay(2)    - All Diameter messages that fall within
                         this category MUST be routed to a
                         next-hop server, without modifying any
                         non-routing AVPs.
           proxy(3)    - All Diameter messages that fall within this
                         category MUST be routed to a next-hop
                         server.
           redirect(4) - Diameter messages that fall within this
                         category MUST have the identity of the home
                         Diameter server(s) appended, and returned
                         to the sender of the message."
    ::= { cdbpRealmMessageRouteEntry 5 }

cdbpRealmMessageRouteACRsIn OBJECT-TYPE
    SYNTAX Counter
--  Units
--    messages
    ACCESS read-only
    STATUS mandatory
    DESCRIPTION
        "Number of Accounting-Request messages
        received from the realm."
    ::= { cdbpRealmMessageRouteEntry 6 }

cdbpRealmMessageRouteACRsOut OBJECT-TYPE
    SYNTAX Counter
--  Units
--    messages
    ACCESS read-only
    STATUS mandatory
    DESCRIPTION
        "Number of Accounting-Request messages
        sent to the realm."
    ::= { cdbpRealmMessageRouteEntry 7 }

cdbpRealmMessageRouteACAsIn OBJECT-TYPE
    SYNTAX Counter
--  Units
--    messages
    ACCESS read-only
    STATUS mandatory
    DESCRIPTION
        "Number of Accounting-Answer messages
        received from the realm."
    ::= { cdbpRealmMessageRouteEntry 8 }

cdbpRealmMessageRouteACAsOut OBJECT-TYPE
    SYNTAX Counter
--  Units
--    messages
    ACCESS read-only
    STATUS mandatory
    DESCRIPTION
        "Number of Accounting-Answer messages
        sent to the realm."
    ::= { cdbpRealmMessageRouteEntry 9 }

cdbpRealmMessageRouteRARsIn OBJECT-TYPE
    SYNTAX Counter
--  Units
--    messages
    ACCESS read-only
    STATUS mandatory
    DESCRIPTION
        "Number of Re-Auth-Request messages
        received from the realm."
    ::= { cdbpRealmMessageRouteEntry 10 }

cdbpRealmMessageRouteRARsOut OBJECT-TYPE
    SYNTAX Counter
--  Units
--    messages
    ACCESS read-only
    STATUS mandatory
    DESCRIPTION
        "Number of Re-Auth-Request messages
        sent to the realm."
    ::= { cdbpRealmMessageRouteEntry 11 }

cdbpRealmMessageRouteRAAsIn OBJECT-TYPE
    SYNTAX Counter
--  Units
--    messages
    ACCESS read-only
    STATUS mandatory
    DESCRIPTION
        "Number of Re-Auth-Answer messages
        received from the realm."
    ::= { cdbpRealmMessageRouteEntry 12 }

cdbpRealmMessageRouteRAAsOut OBJECT-TYPE
    SYNTAX Counter
--  Units
--    messages
    ACCESS read-only
    STATUS mandatory
    DESCRIPTION
        "Number of Re-Auth-Answer messages
        sent to the realm."
    ::= { cdbpRealmMessageRouteEntry 13 }

cdbpRealmMessageRouteSTRsIn OBJECT-TYPE
    SYNTAX Counter
--  Units
--    messages
    ACCESS read-only
    STATUS mandatory
    DESCRIPTION
        "Number of Session-Termination-Request messages
        received from the realm."
    ::= { cdbpRealmMessageRouteEntry 14 }

cdbpRealmMessageRouteSTRsOut OBJECT-TYPE
    SYNTAX Counter
--  Units
--    messages
    ACCESS read-only
    STATUS mandatory
    DESCRIPTION
        "Number of Session-Termination-Request messages
        sent to the realm."
    ::= { cdbpRealmMessageRouteEntry 15 }

cdbpRealmMessageRouteSTAsIn OBJECT-TYPE
    SYNTAX Counter
--  Units
--    messages
    ACCESS read-only
    STATUS mandatory
    DESCRIPTION
        "Number of Session-Termination-Answer messages
        received from the realm."
    ::= { cdbpRealmMessageRouteEntry 16 }

cdbpRealmMessageRouteSTAsOut OBJECT-TYPE
    SYNTAX Counter
--  Units
--    messages
    ACCESS read-only
    STATUS mandatory
    DESCRIPTION
        "Number of Session-Termination-Answer messages
        sent to the realm."
    ::= { cdbpRealmMessageRouteEntry 17 }

cdbpRealmMessageRouteASRsIn OBJECT-TYPE
    SYNTAX Counter
--  Units
--    messages
    ACCESS read-only
    STATUS mandatory
    DESCRIPTION
        "Number of Abort-Session-Request messages
        received from the realm."
    ::= { cdbpRealmMessageRouteEntry 18 }

cdbpRealmMessageRouteASRsOut OBJECT-TYPE
    SYNTAX Counter
--  Units
--    messages
    ACCESS read-only
    STATUS mandatory
    DESCRIPTION
        "Number of Abort-Session-Request messages
        sent to the realm."
    ::= { cdbpRealmMessageRouteEntry 19 }

cdbpRealmMessageRouteASAsIn OBJECT-TYPE
    SYNTAX Counter
--  Units
--    messages
    ACCESS read-only
    STATUS mandatory
    DESCRIPTION
        "Number of Abort-Session-Answer messages
        received from the realm."
    ::= { cdbpRealmMessageRouteEntry 20 }

cdbpRealmMessageRouteASAsOut OBJECT-TYPE
    SYNTAX Counter
--  Units
--    messages
    ACCESS read-only
    STATUS mandatory
    DESCRIPTION
        "Number of Abort-Session-Answer messages
        sent to the realm."
    ::= { cdbpRealmMessageRouteEntry 21 }

cdbpRealmMessageRouteAccRetrans OBJECT-TYPE
    SYNTAX Counter
    ACCESS read-only
    STATUS mandatory
    DESCRIPTION
        "The number of Diameter accounting packets
        retransmitted to this realm."
    ::= { cdbpRealmMessageRouteEntry 22 }

cdbpRealmMessageRouteAccDupReqsts OBJECT-TYPE
    SYNTAX Counter
    ACCESS read-only
    STATUS mandatory
    DESCRIPTION
        "The number of duplicate Diameter accounting
        packets sent to this realm."
    ::= { cdbpRealmMessageRouteEntry 23 }

cdbpRealmMessageRoutePendReqstsOut OBJECT-TYPE
    SYNTAX Gauge
    ACCESS read-only
    STATUS mandatory
    DESCRIPTION
        "The number of Diameter Accounting-Request packets
        sent to this peer that have not yet timed out or
        received a response. This variable is incremented when an
        Accounting-Request is sent to this server and decremented
        due to receipt of an Accounting-Response, a timeout or
        a retransmission."
    ::= { cdbpRealmMessageRouteEntry 24 }

cdbpRealmMessageRouteReqstsDrop OBJECT-TYPE
    SYNTAX Counter
    ACCESS read-only
    STATUS mandatory
    DESCRIPTION
        "The number of requests dropped by this realm."
    ::= { cdbpRealmMessageRouteEntry 25 }

ciscoDiaBaseProtProtocolErrorNotif TRAP-TYPE
-- Reverse mappable trap
    ENTERPRISE ciscoDiameterBasePMIB
    VARIABLES {
        cdbpPeerId, cdbpPeerStatsProtocolErrors }
--  Status
--    mandatory
    DESCRIPTION
        "An ciscoDiaBaseProtProtocolErrorNotif notification
        is sent when both the following conditions are true:
        1) the value of ciscoDiaBaseProtEnableProtocolErrorNotif 
           is true(1)
        2) the value of cdbpPeerStatsProtocolErrors changes.
        It can be utilized by an NMS to trigger
        logical/physical entity table maintenance polls."
    ::= 1

ciscoDiaBaseProtTransientFailureNotif TRAP-TYPE
-- Reverse mappable trap
    ENTERPRISE ciscoDiameterBasePMIB
    VARIABLES {
        cdbpPeerId, cdbpPeerStatsTransientFailures }
--  Status
--    mandatory
    DESCRIPTION
        "An ciscoDiaBaseProtTransientFailureNotif notification
        is sent when both the following conditions are true:
        1) the value of ciscoDiaBaseProtEnableTransientFailureNotif
           is true(1)
        2) the value of cdbpPeerStatsTransientFailures changes.
        It can be utilized by an NMS to trigger
        logical/physical entity table maintenance polls."
    ::= 2

ciscoDiaBaseProtPermanentFailureNotif TRAP-TYPE
-- Reverse mappable trap
    ENTERPRISE ciscoDiameterBasePMIB
    VARIABLES {
        cdbpPeerId, cdbpPeerStatsPermanentFailures }
--  Status
--    mandatory
    DESCRIPTION
        "An ciscoDiaBaseProtPermanentFailureNotif notification
        is sent when both the following conditions are true:
        1) the value of ciscoDiaBaseProtEnablePermanentFailureNotif
           is true(1)
        2) the value of cdbpPeerStatsPermanentFailures changes.
        It can be utilized by an NMS to trigger
        logical/physical entity table maintenance polls."
    ::= 3

ciscoDiaBaseProtPeerConnectionDownNotif TRAP-TYPE
-- Reverse mappable trap
    ENTERPRISE ciscoDiameterBasePMIB
    VARIABLES {
        cdbpLocalId, cdbpPeerId }
--  Status
--    mandatory
    DESCRIPTION
        "An ciscoDiaBaseProtPeerConnectionDownNotif notification
        is sent when both the following conditions are true: 
        1) the value of
        ciscoDiaBaseProtEnablePeerConnectionDownNotif is true(1)
        2) cdbpPeerStatsState changes to closed(1).
        It can be utilized by an NMS to trigger logical/physical
        entity table maintenance polls."
    ::= 4

ciscoDiaBaseProtPeerConnectionUpNotif TRAP-TYPE
-- Reverse mappable trap
    ENTERPRISE ciscoDiameterBasePMIB
    VARIABLES {
        cdbpLocalId, cdbpPeerId }
--  Status
--    mandatory
    DESCRIPTION
        "An ciscoDiaBaseProtPeerConnectionUpNotif notification
        is sent when both the following conditions are true:
        1) the value of ciscoDiaBaseProtEnablePeerConnectionUpNotif
        is true(1)
        2) the value of cdbpPeerStatsState changes to
        either rOpen(6)or iOpen(7).  It can be
        utilized by an NMS to trigger logical/physical entity
        table maintenance polls."
    ::= 5

ciscoDiameterBasePMIBLocalCfgGroup OBJECT IDENTIFIER ::= { ciscoDiameterBasePMIBGroups 1 }
-- OBJECT-GROUP
--  Status
--    mandatory
--  Descr
--    A collection of objects providing configuration common
--    to the server.
--  objects
--    cdbpLocalRealm, cdbpRedundancyEnabled, 
--    cdbpRedundancyInfraState, cdbpRedundancyLastSwitchover, 
--    cdbpLocalOriginHost, cdbpLocalVendorId, 
--    cdbpLocalVendorStorageType, cdbpLocalVendorRowStatus

ciscoDiameterBasePMIBPeerCfgGroup OBJECT IDENTIFIER ::= { ciscoDiameterBasePMIBGroups 2 }
-- OBJECT-GROUP
--  Status
--    mandatory
--  Descr
--    A collection of objects providing configuration
--    of the Diameter peers.
--  objects
--    cdbpPeerId, cdbpPeerPortConnect, cdbpPeerPortListen, 
--    cdbpPeerProtocol, cdbpPeerSecurity, cdbpPeerFirmwareRevision, 
--    cdbpPeerStorageType, cdbpPeerRowStatus, cdbpPeerIpAddressType, 
--    cdbpPeerIpAddress, cdbpPeerVendorId, 
--    cdbpPeerVendorStorageType, cdbpPeerVendorRowStatus

ciscoDiameterBasePMIBPeerStatsGroup OBJECT IDENTIFIER ::= { ciscoDiameterBasePMIBGroups 3 }
-- OBJECT-GROUP
--  Status
--    mandatory
--  Descr
--    A collection of objects providing statistics
--    of the Diameter peers.
--  objects
--    cdbpPeerStatsState, cdbpPeerStatsStateDuration, 
--    cdbpPeerStatsLastDiscCause, cdbpPeerStatsWhoInitDisconnect, 
--    cdbpPeerStatsDWCurrentStatus, cdbpPeerStatsTimeoutConnAtmpts, 
--    cdbpPeerStatsASRsIn, cdbpPeerStatsASRsOut, 
--    cdbpPeerStatsASAsIn, cdbpPeerStatsASAsOut, 
--    cdbpPeerStatsACRsIn, cdbpPeerStatsACRsOut, 
--    cdbpPeerStatsACAsIn, cdbpPeerStatsACAsOut, 
--    cdbpPeerStatsCERsIn, cdbpPeerStatsCERsOut, 
--    cdbpPeerStatsCEAsIn, cdbpPeerStatsCEAsOut, 
--    cdbpPeerStatsDWRsIn, cdbpPeerStatsDWRsOut, 
--    cdbpPeerStatsDWAsIn, cdbpPeerStatsDWAsOut, 
--    cdbpPeerStatsDPRsIn, cdbpPeerStatsDPRsOut, 
--    cdbpPeerStatsDPAsIn, cdbpPeerStatsDPAsOut, 
--    cdbpPeerStatsRARsIn, cdbpPeerStatsRARsOut, 
--    cdbpPeerStatsRAAsIn, cdbpPeerStatsRAAsOut, 
--    cdbpPeerStatsSTRsIn, cdbpPeerStatsSTRsOut, 
--    cdbpPeerStatsSTAsIn, cdbpPeerStatsSTAsOut, 
--    cdbpPeerStatsDWReqTimer, cdbpPeerStatsRedirectEvents, 
--    cdbpPeerStatsAccDupRequests, cdbpPeerStatsMalformedReqsts, 
--    cdbpPeerStatsAccsNotRecorded, cdbpPeerStatsAccRetrans, 
--    cdbpPeerStatsTotalRetrans, cdbpPeerStatsAccPendReqstsOut, 
--    cdbpPeerStatsAccReqstsDropped, cdbpPeerStatsHByHDropMessages, 
--    cdbpPeerStatsEToEDupMessages, cdbpPeerStatsUnknownTypes, 
--    cdbpPeerStatsProtocolErrors, cdbpPeerStatsTransientFailures, 
--    cdbpPeerStatsPermanentFailures, cdbpPeerStatsTransportDown

ciscoDiameterBasePMIBTrapCfgGroup OBJECT IDENTIFIER ::= { ciscoDiameterBasePMIBGroups 5 }
-- OBJECT-GROUP
--  Status
--    mandatory
--  Descr
--    A collection of objects providing configuration for
--    base protocol notifications.
--  objects
--    ciscoDiaBaseProtEnableProtocolErrorNotif, 
--    ciscoDiaBaseProtEnableTransientFailureNotif, 
--    ciscoDiaBaseProtEnablePermanentFailureNotif, 
--    ciscoDiaBaseProtEnablePeerConnectionDownNotif, 
--    ciscoDiaBaseProtEnablePeerConnectionUpNotif

ciscoDiameterBasePMIBLocalCfgSkippedGroup OBJECT IDENTIFIER ::= { ciscoDiameterBasePMIBGroups 6 }
-- OBJECT-GROUP
--  Status
--    mandatory
--  Descr
--    A collection of objects providing configuration common
--    to the server.
--  objects
--    cdbpLocalId, cdbpLocalIpAddrType, cdbpLocalIpAddress, 
--    cdbpLocalTcpListenPort, cdbpLocalSctpListenPort, 
--    cdbpLocalStatsTotalPacketsIn, cdbpLocalStatsTotalPacketsOut, 
--    cdbpLocalStatsTotalUpTime, cdbpLocalResetTime, 
--    cdbpLocalConfigReset, cdbpLocalApplStorageType, 
--    cdbpLocalApplRowStatus, cdbpAppAdvToPeerServices, 
--    cdbpAppAdvToPeerStorageType, cdbpAppAdvToPeerRowStatus

ciscoDiameterBasePMIBLocalStatsSkippedGroup OBJECT IDENTIFIER ::= { ciscoDiameterBasePMIBGroups 7 }
-- OBJECT-GROUP
--  Status
--    mandatory
--  Descr
--    A collection of objects providing statistics common
--    to the server.
--  objects
--    cdbpLocalStatsTotalPacketsIn, cdbpLocalStatsTotalPacketsOut, 
--    cdbpLocalStatsTotalUpTime, cdbpLocalResetTime, 
--    cdbpLocalConfigReset

ciscoDiameterBasePMIBPeerCfgSkippedGroup OBJECT IDENTIFIER ::= { ciscoDiameterBasePMIBGroups 8 }
-- OBJECT-GROUP
--  Status
--    mandatory
--  Descr
--    A collection of objects providing configuration for
--    Diameter peers.
--  objects
--    cdbpAppAdvFromPeerType

ciscoDiameterBasePMIBPeerStatsSkippedGroup OBJECT IDENTIFIER ::= { ciscoDiameterBasePMIBGroups 9 }
-- OBJECT-GROUP
--  Status
--    mandatory
--  Descr
--    A collection of objects providing statistics
--    of Diameter peers.
--  objects
--    cdbpPeerStatsDWCurrentStatus, cdbpPeerStatsDWReqTimer, 
--    cdbpPeerStatsRedirectEvents, cdbpPeerStatsAccDupRequests, 
--    cdbpPeerStatsEToEDupMessages

ciscoDiameterBasePMIBRealmCfgSkippedGroup OBJECT IDENTIFIER ::= { ciscoDiameterBasePMIBGroups 10 }
-- OBJECT-GROUP
--  Status
--    mandatory
--  Descr
--    A collection of objects providing configuration for
--    realm message routing.
--  objects
--    cdbpRealmKnownPeers, cdbpRealmKnownPeersChosen

ciscoDiameterBasePMIBRealmStatsSkippedGroup OBJECT IDENTIFIER ::= { ciscoDiameterBasePMIBGroups 11 }
-- OBJECT-GROUP
--  Status
--    mandatory
--  Descr
--    A collection of objects providing statistics
--    of realm message routing.
--  objects
--    cdbpRealmMessageRouteRealm, cdbpRealmMessageRouteApp, 
--    cdbpRealmMessageRouteType, cdbpRealmMessageRouteAction, 
--    cdbpRealmMessageRouteACRsIn, cdbpRealmMessageRouteACRsOut, 
--    cdbpRealmMessageRouteACAsIn, cdbpRealmMessageRouteACAsOut, 
--    cdbpRealmMessageRouteRARsIn, cdbpRealmMessageRouteRARsOut, 
--    cdbpRealmMessageRouteRAAsIn, cdbpRealmMessageRouteRAAsOut, 
--    cdbpRealmMessageRouteSTRsIn, cdbpRealmMessageRouteSTRsOut, 
--    cdbpRealmMessageRouteSTAsIn, cdbpRealmMessageRouteSTAsOut, 
--    cdbpRealmMessageRouteASRsIn, cdbpRealmMessageRouteASRsOut, 
--    cdbpRealmMessageRouteASAsIn, cdbpRealmMessageRouteASAsOut, 
--    cdbpRealmMessageRouteAccRetrans, 
--    cdbpRealmMessageRouteAccDupReqsts, 
--    cdbpRealmMessageRoutePendReqstsOut, 
--    cdbpRealmMessageRouteReqstsDrop

ciscoDiameterBasePMIBNotificationsGroup OBJECT IDENTIFIER ::= { ciscoDiameterBasePMIBGroups 4 }
-- NOTIFICATION-GROUP
--  Status
--    mandatory
--  Descr
--    The set of notifications which an agent is required
--    to implement.
--  notifications
--    ciscoDiaBaseProtProtocolErrorNotif, 
--    ciscoDiaBaseProtTransientFailureNotif, 
--    ciscoDiaBaseProtPermanentFailureNotif, 
--    ciscoDiaBaseProtPeerConnectionDownNotif, 
--    ciscoDiaBaseProtPeerConnectionUpNotif

ciscoDiameterBasePMIBCompliance OBJECT IDENTIFIER ::= { ciscoDiameterBasePMIBCompliances 1 }
-- MODULE-COMPLIANCE
--  Status
--    mandatory
--  Descr
--    The compliance statement for Diameter Base
--    Protocol entities.
--  Module
--    >>current<<
--   MandGroup
--    ciscoDiameterBasePMIBLocalCfgGroup
--   MandGroup
--    ciscoDiameterBasePMIBPeerCfgGroup
--   MandGroup
--    ciscoDiameterBasePMIBPeerStatsGroup
--   MandGroup
--    ciscoDiameterBasePMIBNotificationsGroup
--   MandGroup
--    ciscoDiameterBasePMIBTrapCfgGroup
--   OptGroup
--    ciscoDiameterBasePMIBLocalCfgSkippedGroup
--   OptGroup
--    ciscoDiameterBasePMIBLocalStatsSkippedGroup
--   OptGroup
--    ciscoDiameterBasePMIBPeerCfgSkippedGroup
--   OptGroup
--    ciscoDiameterBasePMIBPeerStatsSkippedGroup
--   OptGroup
--    ciscoDiameterBasePMIBRealmCfgSkippedGroup
--   OptGroup
--    ciscoDiameterBasePMIBRealmStatsSkippedGroup


END
