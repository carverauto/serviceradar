-- MIB file created 30-Apr-2012 14:46:47, by
--   SMICng version 2.2.11-beta(PRO)(Solaris), January 20, 2001. Enterprise key cisco.com

CISCO-MPLS-TC-EXT-STD-MIB DEFINITIONS ::= BEGIN

-- From file: "CISCO-MPLS-TC-EXT-STD-MIB.my"
-- Compile options "4 7 F H N W 03 06 0B 0G 0N 0T"

IMPORTS
    mplsStdMIB
            FROM MPLS-TC-STD-MIB
    ciscoExperiment
            FROM CISCO-SMI
    Gauge
            FROM RFC1155-SMI;

cmplsTcExtStdMIB OBJECT IDENTIFIER ::= { ciscoExperiment 144 }
-- MODULE-IDENTITY
--  LastUpdated
--    201202220000Z
--  OrgName
--    Multiprotocol Label Switching (MPLS) Working Group
--  ContactInfo
--    Venkatesan Mahalingam
--    Dell Inc,
--    350 Holger way, San Jose, CA, USA
--    Email: venkat.mahalingams@gmail.com
--    
--    Kannan KV Sampath
--    Aricent,
--    India
--    Email: Kannan.Sampath@aricent.com
--    
--    Sam Aldrin
--    Huawei Technologies
--    2330 Central Express Way,
--    Santa Clara, CA 95051, USA
--    Email:  aldrin.ietf@gmail.com
--    
--    Thomas D. Nadeau
--    CA Technologies
--    273 Corporate Drive, Portsmouth, NH, USA
--    Email: thomas.nadeau@ca.com
--  Descr
--    Copyright (c) 2012 IETF Trust and the persons identified
--    as the document authors.  All rights reserved.
--    
--    This MIB module contains Textual Conventions for
--    MPLS based transport networks.
--  RevDate
--    201202220000Z
--  RevDescr
--    MPLS Textual Convention Extensions

CMplsGlobalId ::= OCTET STRING(SIZE(4))
-- TEXTUAL-CONVENTION
--  Status
--    mandatory
--  Descr
--    This object contains the Textual Convention of IP based
--    operator unique identifier (Global_ID), the Global_ID can
--    contain the 2-octet or 4-octet value of the operator's
--    Autonomous System Number (ASN).
--    
--    It is expected that the Global_ID will be derived from
--    the globally unique ASN of the autonomous system hosting
--    the PEs containing the actual AIIs.
--    The presence of a Global_ID based on the operator's
--    ASN ensures that the AII will be globally unique.
--    
--    When the Global_ID is derived from a 2-octet AS number,
--    
--    
--    
--    the two high-order octets of this 4-octet identifier
--    MUST be set to zero.
--    Further ASN 0 is reserved.  A Global_ID of zero means
--    that no Global_ID is present.  Note that a Global_ID of
--    zero is limited to entities contained within a single
--    operator and MUST NOT be used across an NNI.
--    A non-zero Global_ID MUST be derived from an ASN owned by
--    the operator.

CMplsNodeId ::= Gauge
-- TEXTUAL-CONVENTION
--  DspHint
--    d
--  Status
--    mandatory
--  Descr
--    The Node_ID is assigned within the scope of the Global_ID.
--    The value 0(or 0.0.0.0 in dotted decimal notation) is
--    reserved and MUST NOT be used.
--    
--    When IPv4 addresses are in use, the value of this object
--    can be derived from the LSR's /32 IPv4 loop back address.
--    When IPv6 addresses are in use, the value of this object
--    can be a 32-bit value unique within the scope of
--    a Global_ID.
--    
--    Note that, when IP reach ability is not needed, the 32-bit
--    Node_ID is not required to have any association
--    with the IPv4 address space.

CMplsIccId ::= OCTET STRING(SIZE(1..6))
-- TEXTUAL-CONVENTION
--  Status
--    mandatory
--  Descr
--    The ICC is a string of one to six characters, each
--    character being either alphabetic (i.e.  A-Z) or
--    numeric (i.e. 0-9) characters.
--    Alphabetic characters in the ICC SHOULD be represented
--    
--    with upper case letters.

CMplsLocalId ::= Gauge(1..16777215)
-- TEXTUAL-CONVENTION
--  DspHint
--    d
--  Status
--    mandatory
--  Descr
--    This textual convention is used in accommodating the bigger
--    size Global_Node_ID and/or ICC with lower size LSR
--    identifier in order to index the mplsTunnelTable.
--    
--    The Local Identifier is configured between 1 and 16777215,
--    as valid IP address range starts from 16777216(01.00.00.00).
--    This range is chosen to identify the mplsTunnelTable's
--    Ingress/Egress LSR-id is IP address or Local identifier,
--    if the configured range is not IP address, administrator is
--    expected to retrieve the complete information
--    (Global_Node_ID or ICC) from mplsNodeConfigTable. This way,
--    existing mplsTunnelTable is reused for bidirectional tunnel
--    extensions for MPLS based transport networks.
--    
--    This Local Identifier allows the administrator to assign
--    a unique identifier to map Global_Node_ID and/or ICC.


END
