-- MIB file created 29-Mar-2004 18:08:34, by
--   SMICng version 2.2.11-beta(PRO)(Solaris), January 20, 2001. Enterprise key cisco.com

CISCO-VISM-PORT-MIB DEFINITIONS ::= BEGIN

-- From file: "CISCO-VISM-PORT-MIB.my"
-- Compile options "4 7 F H N W 03 06 0B 0G 0N 0T"

IMPORTS
    vismPort
            FROM BASIS-MIB
    ciscoWan
            FROM CISCOWAN-SMI
    OBJECT-TYPE
            FROM RFC-1212;

ciscoVismPortMIB OBJECT IDENTIFIER ::= { ciscoWan 92 }
-- MODULE-IDENTITY
--  LastUpdated
--    200310160000Z
--  OrgName
--    Cisco Systems, Inc.
--  ContactInfo
--           Cisco Systems 
--            Customer Service 
--    
--        Postal: 170 W Tasman Drive 
--                San Jose, CA  95134 
--                USA 
--    
--                Tel: +1 800 553-NETS 
--    
--        E-mail: cs-wanatm@cisco.com
--  Descr
--    The MIB module containing Port information for VISM service module.
--  RevDate
--    200310160000Z
--  RevDescr
--    Initial version of the MIB. 
--    
--    The content of this MIB was originally available 
--    in SMIv1 version. The MIB has been converted to 
--    SMIv2 version and descriptions of some of the objects 
--    have been modified.

vismPortCnfGrp  OBJECT IDENTIFIER ::= { vismPort 1 }
ciscoVismPortMIBConformance OBJECT IDENTIFIER ::= { ciscoVismPortMIB 2 }
ciscoVismPortMIBGroups OBJECT IDENTIFIER ::= { ciscoVismPortMIBConformance 1 }
ciscoVismPortMIBCompliances OBJECT IDENTIFIER ::= { ciscoVismPortMIBConformance 2 }

vismPortCnfGrpTable OBJECT-TYPE
    SYNTAX SEQUENCE OF VismPortCnfGrpEntry
    ACCESS not-accessible
    STATUS mandatory
    DESCRIPTION
        "Port configuration table for the virtual port. 
        Only one entry is allowed in this table. "
    ::= { vismPortCnfGrp 1 }

vismPortCnfGrpEntry OBJECT-TYPE
    SYNTAX VismPortCnfGrpEntry
    ACCESS not-accessible
    STATUS mandatory
    DESCRIPTION
        " An entry for logical port. "
    INDEX { vismPortNum }
    ::= { vismPortCnfGrpTable 1 }

VismPortCnfGrpEntry ::= SEQUENCE {
    vismPortNum INTEGER,
    vismPortRowStatus INTEGER,
    vismPortLineNum INTEGER,
    vismPortType INTEGER,
    vismPortDs0ConfigBitMap INTEGER,
    vismPortSpeed INTEGER,
    vismPortState INTEGER
    }

vismPortNum OBJECT-TYPE
    SYNTAX INTEGER(0..2147483647)
    ACCESS read-only
    STATUS mandatory
    DESCRIPTION
        "This is a logical port number. If PXM1 
         (Processor Switch Module) is the PXM 
         used on the shelf this object should be set to 1. 
         For PXM1E this object should be set to 255. "
    ::= { vismPortCnfGrpEntry 1 }

vismPortRowStatus OBJECT-TYPE
    SYNTAX INTEGER {
        add(1),
        del(2),
        mod(3)
        }
    ACCESS read-write
    STATUS mandatory
    DESCRIPTION
        "The object add, delete or modify a port. 
        
         'add' - add a port, a port acn only be added if the 
                 status is in 'del'. 
         'del' - delete a port, once a port is deleted 
                 the status is chane to 'del'. The port  
                 can only be deleted after deleting all the 
                 connections and the resource partition.  
         'mod' - modify a port and change status to 'mod'.  "
    ::= { vismPortCnfGrpEntry 2 }

vismPortLineNum OBJECT-TYPE
    SYNTAX INTEGER(0..8)
    ACCESS read-write
    STATUS mandatory
    DESCRIPTION
        "This represents the line number to which this port is associated. 
         Since the network port is not associated with any line, 
         line number 0 is returned on a GET. "
    DEFVAL { 0 }
    ::= { vismPortCnfGrpEntry 3 }

vismPortType OBJECT-TYPE
    SYNTAX INTEGER {
        voIP(1),
        userPort(2)
        }
    ACCESS read-write
    STATUS mandatory
    DESCRIPTION
        "The value of this object is always set to 'voIP'. 
         It indicates that network port. The same value 
         is used even when VISM supports VoAAL1 or VoAAL2. "
    DEFVAL { voIP }
    ::= { vismPortCnfGrpEntry 4 }

vismPortDs0ConfigBitMap OBJECT-TYPE
    SYNTAX INTEGER(0..16777215)
    ACCESS read-write
    STATUS mandatory
    DESCRIPTION
        "This respesents the bit map of DS0s which is used to create 
         this port.  Bit 0 represents DS0-1. 
         Since this object is not applicable to the network port,  
         value 0 is returned on a GET. "
    DEFVAL { 0 }
    ::= { vismPortCnfGrpEntry 5 }

vismPortSpeed OBJECT-TYPE
    SYNTAX INTEGER(1..5651320)
    ACCESS read-write
    STATUS mandatory
    DESCRIPTION
        "The speed of the port in cells per second. 
         It is used by VISM card to advertise virtual port bandwidth to  
         the controller, SVC(Switched Virtual Circuit) and 
         PVC(Permanent Virtual Circuit) connection admission 
         control and aggregate traffic clipping. 
        
         This object can be modified only when there is no existing 
         resource partition on the port. "
    DEFVAL { 5651320 }
    ::= { vismPortCnfGrpEntry 6 }

vismPortState OBJECT-TYPE
    SYNTAX INTEGER {
        notConfigured(1),
        active(2)
        }
    ACCESS read-only
    STATUS mandatory
    DESCRIPTION
        "This object indicates the state of the port. "
    ::= { vismPortCnfGrpEntry 7 }

ciscoVismPortGroup OBJECT IDENTIFIER ::= { ciscoVismPortMIBGroups 1 }
-- OBJECT-GROUP
--  Status
--    mandatory
--  Descr
--    The collection of objects which are used to represent 
--    VISM Port information.
--  objects
--    vismPortNum, vismPortRowStatus, vismPortLineNum, vismPortType, 
--    vismPortDs0ConfigBitMap, vismPortSpeed, vismPortState

ciscoVismPortCompliance OBJECT IDENTIFIER ::= { ciscoVismPortMIBCompliances 1 }
-- MODULE-COMPLIANCE
--  Status
--    mandatory
--  Descr
--    The compliance statement for objects related 
--    to VISM Port module.
--  Module
--    >>current<<
--   MandGroup
--    ciscoVismPortGroup
--   ObjVar
--    vismPortLineNum
--   ObjVar
--    vismPortType
--   ObjVar
--    vismPortDs0ConfigBitMap


END
