-- MIB file created 26-Jun-2003 17:13:28, by
--   SMICng version 2.2.11-beta(PRO)(Solaris), January 20, 2001. Enterprise key cisco.com

BASIS-ONLINE-DIAG-MIB DEFINITIONS ::= BEGIN

-- From file: "BASIS-ONLINE-DIAG-MIB.my"
-- Compile options "4 7 F H N W 03 06 0B 0G 0N 0T"

IMPORTS
    ciscoWan
            FROM CISCOWAN-SMI
    axisDiagnostics
            FROM BASIS-MIB
    OBJECT-TYPE
            FROM RFC-1212;

basisOnlineDiagMIB OBJECT IDENTIFIER ::= { ciscoWan 80 }
-- MODULE-IDENTITY
--  LastUpdated
--    200306110000Z
--  OrgName
--    Cisco Systems, Inc.
--  ContactInfo
--           Cisco Systems
--           Customer Service
--    
--    Postal: 170 W Tasman Drive
--           San Jose, CA  95134
--           USA
--    
--           Tel: +1 800 553-NETS
--    
--    E-mail: cs-wanatm@cisco.com
--  Descr
--    This MIB contains information on the online diagnostics
--    in MGX82xx(MGX8250, MGX8220, MGX8230 etc) products.
--  RevDate
--    200306110000Z
--  RevDescr
--    Initial version of the MIB.
--    
--    The content of this MIB was originally available
--    in CISCO-WAN-AXIPOP-MIB defined using SMIv1.
--    The applicable objects from CISCO-WAN-AXIPOP-MIB
--    are defined using SMIv2 in this MIB. Also the
--    descriptions of some of the objects have been 
--    modified.

onlineDiagnostics OBJECT IDENTIFIER ::= { axisDiagnostics 3 }
boDiagMIBConformance OBJECT IDENTIFIER ::= { basisOnlineDiagMIB 2 }
boDiagMIBCompliances OBJECT IDENTIFIER ::= { boDiagMIBConformance 1 }
boDiagMIBGroups OBJECT IDENTIFIER ::= { boDiagMIBConformance 2 }

diagType OBJECT-TYPE
    SYNTAX INTEGER {
        post(1),
        onlinediag(2)
        }
    ACCESS read-only
    STATUS mandatory
    DESCRIPTION
        "This is used to identify the type of diagnostics.
        
        post (1)      : Power On Self Test.
        onlineDiag(2) : Online Diagnostics. 
        
        When a trap is sent to report diagnostics results
        this is used as a varbind to indicate the type of 
        diagnostics."
    ::= { onlineDiagnostics 1 }

diagResult OBJECT-TYPE
    SYNTAX INTEGER {
        passed(1),
        failed(2)
        }
    ACCESS read-only
    STATUS mandatory
    DESCRIPTION
        "This is used to indicate the result of the diagnostics."
    ::= { onlineDiagnostics 2 }

diagTestId OBJECT-TYPE
    SYNTAX INTEGER(0..2147483647)
    ACCESS read-only
    STATUS mandatory
    DESCRIPTION
        "This is used to indicate the test number of the
        diagnostics test that failed. The value depends upon
        the implementation in the each of the MGX82xx product."
    ::= { onlineDiagnostics 3 }

boDiagGroup OBJECT IDENTIFIER ::= { boDiagMIBGroups 1 }
-- OBJECT-GROUP
--  Status
--    mandatory
--  Descr
--    A collection of objects providing the
--     online diagnostics information.
--  objects
--    diagType, diagResult, diagTestId

boDiagCompliance OBJECT IDENTIFIER ::= { boDiagMIBCompliances 1 }
-- MODULE-COMPLIANCE
--  Status
--    mandatory
--  Descr
--    The compliance statement for entities which implement
--    the basis online diagnostics MIB.
--  Module
--    >>current<<
--   MandGroup
--    boDiagGroup


END
