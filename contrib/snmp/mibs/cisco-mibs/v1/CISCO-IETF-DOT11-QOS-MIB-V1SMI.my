-- MIB file created 09-Oct-2002 13:11:51, by
--   SMICng version 2.2.11-beta(PRO)(Solaris), January 20, 2001. Enterprise key cisco.com

CISCO-IETF-DOT11-QOS-MIB DEFINITIONS ::= BEGIN

-- From file: "CISCO-IETF-DOT11-QOS-MIB.my"
-- Compile options "4 7 F H N W 03 06 0B 0G 0N 0T"

IMPORTS
    TruthValue
            FROM SNMPv2-TC-v1
    ifIndex
            FROM IF-MIB
    ciscoExperiment
            FROM CISCO-SMI
    Counter, Gauge
            FROM RFC1155-SMI
    OBJECT-TYPE
            FROM RFC-1212;

ciscoIetfDot11QosMIB OBJECT IDENTIFIER ::= { ciscoExperiment 89 }
-- MODULE-IDENTITY
--  LastUpdated
--    200203280000Z
--  OrgName
--    Cisco System Inc.
--  ContactInfo
--           Cisco Systems
--            Customer Service
--    
--    Postal: 170 West Tasman Drive,
--            San Jose CA 95134-1706.
--            USA
--    
--       Tel: +1 800 553-NETS
--    
--    E-mail: cs-dot11@cisco.com
--  Descr
--    This MIB module provides network management 
--    support for QoS on wireless LAN devices. All 
--    objects defined in this MIB are listed (object 
--    names have been modified to adopt Cisco MIB object 
--    naming convention) in the IEEE 802.11E November 
--    2001 draft. The original names of the objects
--    in the standard are included in the REFERENCE
--    clauses. The standard is still under development. 
--    The standard IEEE 802.11E MIB can replace some of
--    the MIB objects in this MIB once the standard is 
--    finalized.
--    
--    
--              GLOSSARY and ACRONYMS
--    
--    Access point (AP)
--        Transmitter/receiver (transceiver) device
--        that commonly connects and transports data
--        between a wireless network and a wired network.
--    
--    AIFS 
--        Arbitration Interframe Space. It is one of the 
--        five different IFSs defined to provide priority 
--        levels for access to the wireless media. It shall
--        be used by QSTAs to transmit data type frames 
--        (MPDUs) and management type frames (MMPDUs).
--    
--    BSS
--        IEEE 802.11 Basic Service Set (Radio Cell). The
--        BSS of an AP comprises of the stations directly
--        associating with the AP.
--    
--    CW
--        Contention Window. It is the time period between 
--        radio signal collisions caused by simultaneous 
--        broadcast from multiple wireless stations.
--        The contention window is used to compute the 
--        random backoff of the radio broadcast. The IEEE
--        802.11b does not specify the unit for the time
--        period.  
--    
--    CWP Factor 
--        Contention Window Persistence Factor. It indicates
--        the factor used in computing new CW values on every
--        15 unsuccessful attempt to transmit an MPDU or an 
--        MMPDU of a traffic category. It is a scaling factor
--        in units of 1/16 ths.
--    
--    IFS 
--        Inter-Frame Space is the time interval between 
--        frames. A STA shall determine that the medium
--        is idle through the use of the carrier sense 
--        function for the interval specified. In other
--        words, the size of the IFS determines the length
--        of the backoff time interval of a device to the
--        medium. In this case, the medium is the radio
--        wave spectrum. The IEEE 802.11b standard does not
--        specify any unit for the time interval.
--    
--    BSS
--        IEEE 802.11 Basic Service Set (Radio Cell). The
--    MAC
--        Medium Access Control. Layer 2 in the network 
--        model. 
--    
--    MPDU
--        MAC protocol data unit. The unit of data exchanged
--        between two peer MAC entities using the services 
--        of the physical layer (PHY).
--    
--    MMPDU
--        Management type MAC protocol data unit.
--    
--    MSDU
--        MAC service data unit. Information that is 
--        delivered as a unit between MAC service access 
--        points.
--    
--    QBSS 
--        Quality of service basic service set.
--    
--    QSTA 
--        QoS station.
--    
--    STA (WSTA)
--        A non-AP IEEE 802.11 wireless station.
--  RevDate
--    200203280000Z
--  RevDescr
--    Changing the name of cid11QosDiscardedFragments 
--    to cid11QosIfDiscardedFragments and description
--    to indicate it is for transmit fragments only.  
--    Updating the description of cid11QosDiscardedFrames
--    to indicate it is for transmit frame only. 
--    Modify the default value and range for cid11CWmin
--    and cid11CWmax.
--  RevDate
--    200201290000Z
--  RevDescr
--    Initial version of this MIB module.

ciscoIetfDot11QosMIBObjects OBJECT IDENTIFIER ::= { ciscoIetfDot11QosMIB 1 }
ciscoIetfDot11QosMIBConformance OBJECT IDENTIFIER ::= { ciscoIetfDot11QosMIB 2 }
ciscoIetfDot11QosConfig OBJECT IDENTIFIER ::= { ciscoIetfDot11QosMIBObjects 1 }
ciscoIetfDot11QosQueue OBJECT IDENTIFIER ::= { ciscoIetfDot11QosMIBObjects 2 }
ciscoIetfDot11QosStatistics OBJECT IDENTIFIER ::= { ciscoIetfDot11QosMIBObjects 3 }
ciscoIetfDot11QosMIBCompliances OBJECT IDENTIFIER ::= { ciscoIetfDot11QosMIBConformance 1 }
ciscoIetfDot11QosMIBGroups OBJECT IDENTIFIER ::= { ciscoIetfDot11QosMIBConformance 2 }

Cid11QosTrafficCategory ::= INTEGER {
        --?? enum value of zero may cause problems
        bestEffort(0),
        background(1),
        spare(2),
        excellentEffort(3),
        controlledLoad(4),
        interactiveVideo(5),
        interactiveVoice(6),
        networkControl(7)
        }
-- TEXTUAL-CONVENTION
--  Status
--    mandatory
--  Descr
--    This is the 802.1D IP traffic category. There are
--    a total of 8 categories. Each category can be 
--    mapped to a 802.1P priority level of IP packets.
--    The priority levels are implemented using the 
--    Precedence Bits in the IP packets. The default 
--    priority levels start from 'background', the 
--    lowest, to the highest, 'networkControl':
--        background(1)        - background traffic  
--                               (lowest priority)
--        spare(2)             - spare traffic
--                               (2nd lowest)
--        bestEffort(0)        - best effort delivery
--                               (this is the default 
--                               type for all traffic)
--        excellentEffort(3)   - execellent effect
--        controlledLoad(4)    - controlled load
--        interactiveVideo(5)  - video traffic
--        interactiveVoice(6)  - voice traffic
--        networkControl(7)    - network control 
--                               packets (highest).
--  Refer
--    IEEE 802.1D-1998, Annex H.2.10 and 
--    IEEE 802.11E-2001, section 7.5.1.

cid11QosConfigTable OBJECT-TYPE
    SYNTAX SEQUENCE OF Cid11QosConfigEntry
    ACCESS not-accessible
    STATUS mandatory
    DESCRIPTION
        "This table contains the basic set of attributes
        to configure QoS for a wireless LAN device. This
        table has a sparse dependent relationship with
        the ifTable. Each IEEE 802.11 wireless interface 
        has a set of configuration parameters for each IP
        network traffic category. For each entry in this
        table, there exists an entry in the ifTable of
        ifType ieee80211(71)."
    ::= { ciscoIetfDot11QosConfig 1 }

cid11QosConfigEntry OBJECT-TYPE
    SYNTAX Cid11QosConfigEntry
    ACCESS not-accessible
    STATUS mandatory
    DESCRIPTION
        "Each entry contains parameters to configure
        traffic contention window, AIFS, priority 
        and MSDU lifetime for each traffic category
        on an IEEE 802.11 interface."
    INDEX { ifIndex, cid11TrafficCategory }
    ::= { cid11QosConfigTable 1 }

Cid11QosConfigEntry ::= SEQUENCE {
    cid11TrafficCategory Cid11QosTrafficCategory,
    cid11CWmin Gauge,
    cid11CWmax Gauge,
    cid11CWPFactor Gauge,
    cid11AIFS Gauge,
    cid11TrafficPriority Gauge,
    cid11MSDULifetime Gauge
    }

cid11TrafficCategory OBJECT-TYPE
    SYNTAX Cid11QosTrafficCategory
--    Rsyntax INTEGER {
--        ?? enum value of zero may cause problems
--        bestEffort(0),
--        background(1),
--        spare(2),
--        excellentEffort(3),
--        controlledLoad(4),
--        interactiveVideo(5),
--        interactiveVoice(6),
--        networkControl(7)
--        }
    ACCESS not-accessible
    STATUS mandatory
    DESCRIPTION
        "This object specifies the traffic category."
    ::= { cid11QosConfigEntry 1 }

cid11CWmin OBJECT-TYPE
    SYNTAX Gauge(0..1023)
    ACCESS read-write
    STATUS mandatory
    DESCRIPTION
        "This specifies the minimum contention 
        window value for a traffic category. The
        backoff interval of a radio is calculated
        from a pseudo random integer drawn from 
        a uniform distribution over the interval 
        [1, CW+1], where CW is an integer within 
        the range of values of the cid11CWmin and 
        cid11CWmax."
    REFERENCE
        "dot11CWmin, IEEE 802.11E-2001/D1."
    DEFVAL { 0 }
    ::= { cid11QosConfigEntry 2 }

cid11CWmax OBJECT-TYPE
    SYNTAX Gauge(0..1023)
    ACCESS read-write
    STATUS mandatory
    DESCRIPTION
        "This object specifies the maximum contention 
        window value for a traffic category. The
        backoff interval of a radio is calculated
        from a pseudo random integer drawn from 
        a uniform distribution over the interval 
        [1, CW+1], where CW is an integer within 
        the range of values of the cid11CWmin and 
        cid11CWmax."
    REFERENCE
        "dot11CWmax, IEEE 802.11E-2001/D1."
    DEFVAL { 1023 }
    ::= { cid11QosConfigEntry 3 }

cid11CWPFactor OBJECT-TYPE
    SYNTAX Gauge(0..255)
    ACCESS read-write
    STATUS mandatory
    DESCRIPTION
        "This object specifies the contention window 
        persistence factor for a traffic category."
    REFERENCE
        "dot11CWPFactor, IEEE 802.11E-2001/D1."
    DEFVAL { 32 }
    ::= { cid11QosConfigEntry 4 }

cid11AIFS OBJECT-TYPE
    SYNTAX Gauge(2..10)
    ACCESS read-write
    STATUS mandatory
    DESCRIPTION
        "This object specifies the AIFS for a traffic
        category."
    REFERENCE
        "dot11AIFS, IEEE 802.11E-2001/D1."
    DEFVAL { 2 }
    ::= { cid11QosConfigEntry 5 }

cid11TrafficPriority OBJECT-TYPE
    SYNTAX Gauge(0..7)
    ACCESS read-write
    STATUS mandatory
    DESCRIPTION
        "This object specifies the actual priority this 
        agent is going to use to delivery packets for a 
        traffic category. This allows multiple traffic 
        categories to map to the same priority level.
        The priority 7 is the highest priority and 
        priority 1 is the lowest priority, with priority
        0, which is used for best effort traffic, ordered
        between priority 3 and priority 2. The resulting 
        default ordering is {7,6,5,4,3,0,2,1}. The default
        value is same as the traffic category value."
    REFERENCE
        "dot11PriorityMap, IEEE 802.11E-2001/D1
        and IEEE 802.1D-1998, Annex H.2.10."
    ::= { cid11QosConfigEntry 6 }

cid11MSDULifetime OBJECT-TYPE
    SYNTAX Gauge(0..65535)
    ACCESS read-write
    STATUS mandatory
    DESCRIPTION
        "This object specifies the MSDU lifetime for a
        traffic category."
    REFERENCE
        "dot11MSDULifetime, IEEE 802.11E-2001/D1."
    DEFVAL { 65535 }
    ::= { cid11QosConfigEntry 7 }

cid11QosSupportTable OBJECT-TYPE
    SYNTAX SEQUENCE OF Cid11QosSupportEntry
    ACCESS not-accessible
    STATUS mandatory
    DESCRIPTION
        "This table contains the attributes indicating
        QoS support information on the IEEE 802.11 
        interfaces of the device. This table has a 
        sparse dependent relationship with the ifTable.
        For each entry in this table, there exists an 
        entry in the ifTable of ifType ieee80211(71)."
    ::= { ciscoIetfDot11QosConfig 2 }

cid11QosSupportEntry OBJECT-TYPE
    SYNTAX Cid11QosSupportEntry
    ACCESS not-accessible
    STATUS mandatory
    DESCRIPTION
        "Each entry contains attributes to indicate
        if Qos and priority queue are supported for
        an IEEE 802.11 interface."
    INDEX { ifIndex }
    ::= { cid11QosSupportTable 1 }

Cid11QosSupportEntry ::= SEQUENCE {
    cid11QosOptionImplemented TruthValue,
    cid11QueuesAvailable Gauge
    }

cid11QosOptionImplemented OBJECT-TYPE
    SYNTAX TruthValue
--    Rsyntax INTEGER {
--        true(1),
--        false(2)
--        }
    ACCESS read-only
    STATUS mandatory
    DESCRIPTION
        "This object indicates if QoS is supported
        on this IEEE 802.11 network interface."
    REFERENCE
        "dot11QosOptionImplemented, IEEE 802.11E-2001/D1."
    ::= { cid11QosSupportEntry 1 }

cid11QueuesAvailable OBJECT-TYPE
    SYNTAX Gauge(4..8)
    ACCESS read-only
    STATUS mandatory
    DESCRIPTION
        "This object shows the number of QoS 
        priority queues are available on this 
        IEEE 802.11 network interface."
    REFERENCE
        "dot11QueuesAvailable, IEEE 802.11E-2001/D1."
    ::= { cid11QosSupportEntry 2 }

cid11QueueTable OBJECT-TYPE
    SYNTAX SEQUENCE OF Cid11QueueEntry
    ACCESS not-accessible
    STATUS mandatory
    DESCRIPTION
        "This table contains the queue weight and size  
        information and statistics for each traffic 
        category on each the IEEE 802.11 interface. This 
        table has a sparse dependent relationship with the
        ifTable. For each entry in this table, there exists 
        an entry in the ifTable of ifType ieee80211(71)."
    ::= { ciscoIetfDot11QosQueue 1 }

cid11QueueEntry OBJECT-TYPE
    SYNTAX Cid11QueueEntry
    ACCESS not-accessible
    STATUS mandatory
    DESCRIPTION
        "Each entry contains the current queue weight, size,
        and peak size information for each traffic category
        on an IEEE 802.11 interface."
    INDEX { ifIndex, cid11TrafficCategory }
    ::= { cid11QueueTable 1 }

Cid11QueueEntry ::= SEQUENCE {
    cid11QueueSize Gauge,
    cid11QueuePeakSize Counter
    }

cid11QueueSize OBJECT-TYPE
    SYNTAX Gauge(0..511)
    ACCESS read-only
    STATUS mandatory
    DESCRIPTION
        "This is the current QoS priority queue size
        for the traffic category."
    REFERENCE
        "dot11QueueSizeTC, IEEE 802.11E-2001/D1."
    ::= { cid11QueueEntry 1 }

cid11QueuePeakSize OBJECT-TYPE
    SYNTAX Counter
    ACCESS read-only
    STATUS mandatory
    DESCRIPTION
        "This is the peak QoS priority queue size
        for the traffic category."
    REFERENCE
        "dot11QueuePeakSizeTC, IEEE 802.11E-2001/D1."
    ::= { cid11QueueEntry 2 }

cid11QosStatisticsTable OBJECT-TYPE
    SYNTAX SEQUENCE OF Cid11QosStatisticsEntry
    ACCESS not-accessible
    STATUS mandatory
    DESCRIPTION
        "This table contains the QoS statistics 
        by traffic category on each the IEEE 802.11 
        network interface. This table has a sparse 
        dependent relationship with the ifTable.
        For each entry in this table, there exists an 
        entry in the ifTable of ifType ieee80211(71)."
    ::= { ciscoIetfDot11QosStatistics 1 }

cid11QosStatisticsEntry OBJECT-TYPE
    SYNTAX Cid11QosStatisticsEntry
    ACCESS not-accessible
    STATUS mandatory
    DESCRIPTION
        "Each entry contain QoS statistics for data
        transmission and receive for each traffic 
        category on an IEEE 802.11 interface."
    INDEX { ifIndex, cid11TrafficCategory }
    ::= { cid11QosStatisticsTable 1 }

Cid11QosStatisticsEntry ::= SEQUENCE {
    cid11QosReceivedMPDUs Counter,
    cid11QosReceivedRetries Counter,
    cid11QosDiscardedFrames Counter,
    cid11QosTransmittedFragments Counter,
    cid11QosFails Counter,
    cid11QosRetries Counter,
    cid11QosMutipleRetries Counter,
    cid11QosFrameDuplicates Counter,
    cid11QosReceivedFragments Counter,
    cid11QosTransmittedFrames Counter
    }

cid11QosReceivedMPDUs OBJECT-TYPE
    SYNTAX Counter
    ACCESS read-only
    STATUS mandatory
    DESCRIPTION
        "This is the counter for QoS MPDUs received on
        this IEEE 802.11 interface for the traffic 
        category."
    REFERENCE
        "dot11QoSMPDUsReceivedCountTC, IEEE 802.11E-2001/D1."
    ::= { cid11QosStatisticsEntry 1 }

cid11QosReceivedRetries OBJECT-TYPE
    SYNTAX Counter
    ACCESS read-only
    STATUS mandatory
    DESCRIPTION
        "This is the counter for Qos retries received on
        this IEEE 802.11 interface for the traffic category."
    REFERENCE
        "dot11QoSRetriesReceivedCountTC, IEEE 802.11E-2001/D1."
    ::= { cid11QosStatisticsEntry 2 }

cid11QosDiscardedFrames OBJECT-TYPE
    SYNTAX Counter
    ACCESS read-only
    STATUS mandatory
    DESCRIPTION
        "This is the counter for Qos discarded frames 
        transmitting from this IEEE 802.11 interface for
        the traffic category."
    REFERENCE
        "dot11QosDiscardedFrameCountTC, IEEE 802.11E-2001/D1."
    ::= { cid11QosStatisticsEntry 3 }

cid11QosTransmittedFragments OBJECT-TYPE
    SYNTAX Counter
    ACCESS read-only
    STATUS mandatory
    DESCRIPTION
        "This is the counter for Qos fragments transmitted 
        this IEEE 802.11 interface for the traffic 
        category."
    REFERENCE
        "dot11QosTransmittedFragmentCountTC, 
        IEEE 802.11E-2001/D1."
    ::= { cid11QosStatisticsEntry 4 }

cid11QosFails OBJECT-TYPE
    SYNTAX Counter
    ACCESS read-only
    STATUS mandatory
    DESCRIPTION
        "This is the counter for Qos failures on
        this IEEE 802.11 interface for the traffic category."
    REFERENCE
        "dot11QosFailedCountTC, IEEE 802.11E-2001/D1."
    ::= { cid11QosStatisticsEntry 5 }

cid11QosRetries OBJECT-TYPE
    SYNTAX Counter
    ACCESS read-only
    STATUS mandatory
    DESCRIPTION
        "This is the counter for Qos retries performed on
        this IEEE 802.11 interface for the traffic category."
    REFERENCE
        "dot11QosRetryCountTC, IEEE 802.11E-2001/D1."
    ::= { cid11QosStatisticsEntry 6 }

cid11QosMutipleRetries OBJECT-TYPE
    SYNTAX Counter
    ACCESS read-only
    STATUS mandatory
    DESCRIPTION
        "This is the counter for Qos multiple retries 
        performed on this IEEE 802.11 interface for the 
        traffic category."
    REFERENCE
        "dot11QosMutipleRetryCountTC, IEEE 802.11E-2001/D1."
    ::= { cid11QosStatisticsEntry 7 }

cid11QosFrameDuplicates OBJECT-TYPE
    SYNTAX Counter
    ACCESS read-only
    STATUS mandatory
    DESCRIPTION
        "This is the counter for Qos frame duplications
        performed on this IEEE 802.11 interface for the 
        traffic category."
    REFERENCE
        "dot11QosFrameDuplicateCountTC, IEEE 802.11E-2001/D1."
    ::= { cid11QosStatisticsEntry 8 }

cid11QosReceivedFragments OBJECT-TYPE
    SYNTAX Counter
    ACCESS read-only
    STATUS mandatory
    DESCRIPTION
        "This is the counter for Qos fragments received 
        on this IEEE 802.11 interface for the traffic 
        category."
    REFERENCE
        "dot11QosReceivedFragmentCountTC, 
        IEEE 802.11E-2001/D1."
    ::= { cid11QosStatisticsEntry 9 }

cid11QosTransmittedFrames OBJECT-TYPE
    SYNTAX Counter
    ACCESS read-only
    STATUS mandatory
    DESCRIPTION
        "This is the counter for Qos frames transmitted 
        from this IEEE 802.11 interface for the traffic 
        category."
    REFERENCE
        "dot11QosTransmittedFrameCountTC, 
        IEEE 802.11E-2001/D1."
    ::= { cid11QosStatisticsEntry 10 }

cid11QosIfStatisticsTable OBJECT-TYPE
    SYNTAX SEQUENCE OF Cid11QosIfStatisticsEntry
    ACCESS not-accessible
    STATUS mandatory
    DESCRIPTION
        "This table contains the attributes indicating
        QoS statistics on the IEEE 802.11 interfaces 
        of the device. This table has a sparse dependent
        relationship with the ifTable. For each entry in 
        this table, there exists an entry in the ifTable 
        of ifType ieee80211(71)."
    ::= { ciscoIetfDot11QosStatistics 2 }

cid11QosIfStatisticsEntry OBJECT-TYPE
    SYNTAX Cid11QosIfStatisticsEntry
    ACCESS not-accessible
    STATUS mandatory
    DESCRIPTION
        "Each entry contains attributes to support 
        QoS statistics on an IEEE 802.11 interface."
    INDEX { ifIndex }
    ::= { cid11QosIfStatisticsTable 1 }

Cid11QosIfStatisticsEntry ::= SEQUENCE {
    cid11QosIfDiscardedFragments Counter
    }

cid11QosIfDiscardedFragments OBJECT-TYPE
    SYNTAX Counter
    ACCESS read-only
    STATUS mandatory
    DESCRIPTION
        "This object counts the number of QoS discarded
        transmitting fragments."
    REFERENCE
        "dot11QosDiscardedFragments, 
        IEEE 802.11E-2001/D1."
    ::= { cid11QosIfStatisticsEntry 1 }

ciscoIetfDot11QosConfigGroup OBJECT IDENTIFIER ::= { ciscoIetfDot11QosMIBGroups 1 }
-- OBJECT-GROUP
--  Status
--    mandatory
--  Descr
--    Configurations for IEEE 802.11 QoS.
--  objects
--    cid11CWmin, cid11CWmax, cid11CWPFactor, cid11AIFS, 
--    cid11TrafficPriority, cid11MSDULifetime, 
--    cid11QosOptionImplemented, cid11QueuesAvailable

ciscoIetfDot11QosQueueGroup OBJECT IDENTIFIER ::= { ciscoIetfDot11QosMIBGroups 2 }
-- OBJECT-GROUP
--  Status
--    mandatory
--  Descr
--    Configurations and statistics for 
--    IEEE 802.11 QoS queue.
--  objects
--    cid11QueueSize, cid11QueuePeakSize

ciscoIetfDot11QosStatsGroup OBJECT IDENTIFIER ::= { ciscoIetfDot11QosMIBGroups 3 }
-- OBJECT-GROUP
--  Status
--    mandatory
--  Descr
--    Status and statistics for IEEE 802.11 QoS.
--  objects
--    cid11QosIfDiscardedFragments, cid11QosReceivedMPDUs, 
--    cid11QosReceivedRetries, cid11QosDiscardedFrames, 
--    cid11QosTransmittedFragments, cid11QosFails, cid11QosRetries, 
--    cid11QosMutipleRetries, cid11QosFrameDuplicates, 
--    cid11QosReceivedFragments, cid11QosTransmittedFrames

ciscoIetfDot11QosMIBCompliance OBJECT IDENTIFIER ::= { ciscoIetfDot11QosMIBCompliances 1 }
-- MODULE-COMPLIANCE
--  Status
--    mandatory
--  Descr
--    The compliance statement for the 
--    configuration and status groups.
--  Module
--    >>current<<
--   MandGroup
--    ciscoIetfDot11QosConfigGroup
--   MandGroup
--    ciscoIetfDot11QosQueueGroup
--   MandGroup
--    ciscoIetfDot11QosStatsGroup


END
