-- MIB file created 03-Sep-2009 14:24:10, by
--   SMICng version 2.2.11-beta(PRO)(Solaris), January 20, 2001. Enterprise key cisco.com

CISCO-DIAMETER-SG-MIB DEFINITIONS ::= BEGIN

-- From file: "CISCO-DIAMETER-SG-MIB.my"
-- Compile options "4 7 F H N O W 03 06 0B 0G 0N 0T"

IMPORTS
    StorageType, RowStatus
            FROM SNMPv2-TC-v1
    SnmpAdminString
            FROM SNMP-FRAMEWORK-MIB
    ciscoExperiment
            FROM CISCO-SMI
    Gauge
            FROM RFC1155-SMI
    OBJECT-TYPE
            FROM RFC-1212;

ciscoDiameterSGMIB OBJECT IDENTIFIER ::= { ciscoExperiment 132 }
-- MODULE-IDENTITY
--  LastUpdated
--    200609060000Z
--  OrgName
--    Cisco Systems, Inc.
--  ContactInfo
--    Cisco Systems
--    Customer Service
--    
--    Postal: 170 W Tasman Drive
--    San Jose, CA  95134
--    USA
--    
--    Tel: +1 800 553-NETS
--    
--    E-mail: cs-aaa@cisco.com
--  Descr
--    The MIB module for Cisco's Diameter Server Group
--    Entities. This MIB describes the SNMP MIB objects
--    that are supported in order to provide the ability
--    to fetch/configure the Diameter Server Groups.
--  RevDate
--    200609060000Z
--  RevDescr
--    Initial version of this MIB module.

ciscoDiameterSGMIBNotifs OBJECT IDENTIFIER ::= { ciscoDiameterSGMIB 0 }
ciscoDiameterSGMIBObjects OBJECT IDENTIFIER ::= { ciscoDiameterSGMIB 1 }
ciscoDiameterSGMIBConform OBJECT IDENTIFIER ::= { ciscoDiameterSGMIB 2 }
cdsgHostCfgs    OBJECT IDENTIFIER ::= { ciscoDiameterSGMIBObjects 1 }
ciscoDiameterSGMIBCompliances OBJECT IDENTIFIER ::= { ciscoDiameterSGMIBConform 1 }
ciscoDiameterSGMIBGroups OBJECT IDENTIFIER ::= { ciscoDiameterSGMIBConform 2 }

cdsgServerGroupTable OBJECT-TYPE
    SYNTAX SEQUENCE OF CdsgServerGroupEntry
    ACCESS not-accessible
    STATUS mandatory
    DESCRIPTION
        "The table listing the Diameter server group information.
        Entries are added to this table via cdsgServerGroupRowStatus in
        accordance with the RowStatus convention."
    ::= { cdsgHostCfgs 1 }

cdsgServerGroupEntry OBJECT-TYPE
    SYNTAX CdsgServerGroupEntry
    ACCESS not-accessible
    STATUS mandatory
    DESCRIPTION
        "A row entry representing a Diameter server group entry."
    INDEX { cdsgServerGroupIndex }
    ::= { cdsgServerGroupTable 1 }

CdsgServerGroupEntry ::= SEQUENCE {
    cdsgServerGroupIndex Gauge,
    cdsgServerGroupName SnmpAdminString,
    cdsgServerGroupStorageType StorageType,
    cdsgServerGroupRowStatus RowStatus
    }

cdsgServerGroupIndex OBJECT-TYPE
    SYNTAX Gauge(1..4294967295)
    ACCESS not-accessible
    STATUS mandatory
    DESCRIPTION
        "A number uniquely identifying each Diameter
        Server Group. An index that uniquely represents
        a Server Group.  This index is assigned arbitrarily
        by the SNMP engine and is not saved over reloads."
    ::= { cdsgServerGroupEntry 1 }

cdsgServerGroupName OBJECT-TYPE
    SYNTAX SnmpAdminString
--    Rsyntax OCTET STRING(SIZE(0..255))
    ACCESS read-write
    STATUS mandatory
    DESCRIPTION
        "The Server Group Name.
        It has to be unique and not an empty string."
    ::= { cdsgServerGroupEntry 2 }

cdsgServerGroupStorageType OBJECT-TYPE
    SYNTAX StorageType
--    Rsyntax INTEGER {
--        other(1),
--        volatile(2),
--        nonVolatile(3),
--        permanent(4),
--        readOnly(5)
--        }
    ACCESS read-write
    STATUS mandatory
    DESCRIPTION
        "The storage type for this conceptual row. An agent
        implementing the table must allow adding cdsgServerGroupName
        into the table. None of the columnar objects is writable
        when the conceptual row is permanent."
    REFERENCE
        "Textual Conventions for SMIv2, Section 2."
    DEFVAL { nonVolatile }
    ::= { cdsgServerGroupEntry 3 }

cdsgServerGroupRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this conceptual row.
        
        To create a row in this table, a manager must
        set this object to either createAndGo(4) or
        createAndWait(5).
        
        Until instances of all corresponding columns are
        appropriately configured, the value of the
        corresponding instance of the cdsgServerGroupRowStatus
        column is 'notReady'.
        
        In particular, a newly created row cannot be made
        active until the corresponding
        cdsgServerGroupName has been set.
        
        cdsgServerGroupName may not be modified while the
        value of this object is active(1):
        An attempt to set these objects while the value of
        cdsgServerGroupRowStatus is active(1) will result in
        an inconsistentValue error.
        
        Entries in this table with cdsgServerGroupRowStatus equal to
        active(1) remain in the table until destroyed.  
        
        Entries in this table with cdsgServerGroupRowStatus equal to
        values other than active(1) will be destroyed after timeout
        (5 minutes).
        
        Upon reload, cdsgServerGroupIndex values may be changed."
    ::= { cdsgServerGroupEntry 4 }

cdsgServerTable OBJECT-TYPE
    SYNTAX SEQUENCE OF CdsgServerEntry
    ACCESS not-accessible
    STATUS mandatory
    DESCRIPTION
        "The table listing information regarding the server
        which are part of the Diameter server groups.
        Entries are added to this table via cdsgServerRowStatus
        in accordance with the RowStatus convention. "
    ::= { cdsgHostCfgs 2 }

cdsgServerEntry OBJECT-TYPE
    SYNTAX CdsgServerEntry
    ACCESS not-accessible
    STATUS mandatory
    DESCRIPTION
        "A row entry representing a Diameter server group."
    INDEX { cdsgServerGroupIndex, cdsgServerIndex }
    ::= { cdsgServerTable 1 }

CdsgServerEntry ::= SEQUENCE {
    cdsgServerIndex Gauge,
    cdsgServerName SnmpAdminString,
    cdsgServerStorageType StorageType,
    cdsgServerRowStatus RowStatus
    }

cdsgServerIndex OBJECT-TYPE
    SYNTAX Gauge(1..4294967295)
    ACCESS not-accessible
    STATUS mandatory
    DESCRIPTION
        "A number uniquely identifying each Diameter Server.
        An index that uniquely represents a Server within a
        Server Group. This index is assigned arbitrarily
        by the SNMP engine and is not saved over reloads."
    ::= { cdsgServerEntry 1 }

cdsgServerName OBJECT-TYPE
    SYNTAX SnmpAdminString
--    Rsyntax OCTET STRING(SIZE(0..255))
    ACCESS read-write
    STATUS mandatory
    DESCRIPTION
        "The Server Name.
        It has to be unique and not an empty string."
    ::= { cdsgServerEntry 2 }

cdsgServerStorageType OBJECT-TYPE
    SYNTAX StorageType
--    Rsyntax INTEGER {
--        other(1),
--        volatile(2),
--        nonVolatile(3),
--        permanent(4),
--        readOnly(5)
--        }
    ACCESS read-write
    STATUS mandatory
    DESCRIPTION
        "The storage type for this conceptual row. An agent
        implementing the table must allow adding cdsgServerName
        into the table. None of the columnar objects is writable
        when the conceptual row is permanent."
    REFERENCE
        "Textual Conventions for SMIv2, Section 2."
    DEFVAL { nonVolatile }
    ::= { cdsgServerEntry 3 }

cdsgServerRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this conceptual row.
        
        To create a row in this table, a manager must
        set this object to either createAndGo(4) or
        createAndWait(5).
        
        This table is an extended table to the cdsgServerGroupTable
        and so an entry here must have a corresponding parent entry
        in the cdsgServerGroupTable as well. This would map all such
        entries with the same cdsgServerEntry under one single
        cdsgServerGroupEntry i.e these servers are under the server
        group represented by the cdsgServerGroupEntry.
        
        Until instances of all corresponding columns are
        appropriately configured, the value of the
        corresponding instance of the cdsgServerRowStatus column is
        'notReady'.
        
        In particular, a newly created row cannot be made
        active until the corresponding
        cdsgServerName has been set.
        
        cdsgServerName may not be modified while the
        value of this object is active(1):
        An attempt to set these objects while the value of
        cdsgServerRowStatus is active(1) will result in 
        an inconsistentValue error.
        Entries in this table with cdsgServerRowStatus equal to
        active(1) remain in the table until destroyed.  
        
        Entries in this table with cdsgServerRowStatus equal to 
        values other than active(1) will be destroyed after timeout
        (5 minutes).
        
        Upon reload, cdsgServerIndex values may be changed."
    ::= { cdsgServerEntry 4 }

ciscoDiameterSGHostCfgGroup OBJECT IDENTIFIER ::= { ciscoDiameterSGMIBGroups 1 }
-- OBJECT-GROUP
--  Status
--    mandatory
--  Descr
--    A collection of objects providing configuration common
--    to the server.
--  objects
--    cdsgServerGroupName, cdsgServerGroupRowStatus, 
--    cdsgServerGroupStorageType, cdsgServerName, 
--    cdsgServerRowStatus, cdsgServerStorageType

ciscoDiameterSGMIBCompliance OBJECT IDENTIFIER ::= { ciscoDiameterSGMIBCompliances 1 }
-- MODULE-COMPLIANCE
--  Status
--    mandatory
--  Descr
--    The compliance statement for Diameter Server Group
--    entities.
--  Module
--    >>current<<
--   MandGroup
--    ciscoDiameterSGHostCfgGroup


END
