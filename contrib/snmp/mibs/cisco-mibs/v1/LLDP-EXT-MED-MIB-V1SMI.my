-- MIB file created 06-Jul-2015 02:28:36, by
--   SMICng version 2.2.11-beta(PRO)(Solaris), January 20, 2001. Enterprise key cisco.com

LLDP-EXT-MED-MIB DEFINITIONS ::= BEGIN

-- From file: "LLDP-EXT-MED-MIB.my"
-- Compile options "4 7 F H N W 03 06 0B 0G 0N 0T"

IMPORTS
    TruthValue
            FROM SNMPv2-TC-v1
    lldpExtensions, lldpLocPortNum, lldpRemTimeMark, 
    lldpRemLocalPortNum, lldpRemIndex, lldpPortConfigPortNum, 
    lldpRemChassisIdSubtype, lldpRemChassisId
            FROM LLDP-MIB
    Dscp
            FROM DIFFSERV-DSCP-TC
    SnmpAdminString
            FROM SNMP-FRAMEWORK-MIB
    Gauge
            FROM RFC1155-SMI
    OBJECT-TYPE
            FROM RFC-1212
    TRAP-TYPE
            FROM RFC-1215;

lldpXMedMIB OBJECT IDENTIFIER ::= { lldpExtensions 4795 }
-- MODULE-IDENTITY
--  LastUpdated
--    200507280000Z
--  OrgName
--    TIA TR41.4 Working Group
--  ContactInfo
--      WG-URL: http://www.tiaonline.org/standards/sfg/scope.cfm#TR-41.4
--                 WG-EMail: tr41@tiacomm.org
--                  Contact: Chair, TIA TR-41
--                   Postal: Telecommunications Industry Association
--                           2500 Wilson Blvd., Suite 300
--                           Arlington, VA 22201 USA
--                      Tel: (703) 907-7700
--                   E-mail: tr41@tiacomm.org
--  Descr
--    The LLDP Management Information Base extension module for
--    TIA-TR41.4 media endpoint discovery information.
--    
--    In order to assure the uniqueness of the LLDP-MIB,
--    lldpXMedMIB is branched from lldpExtensions using the TIA OUI 
--    value as the node.  An OUI/'company_id' is a 24 bit globally 
--    unique assigned number referenced by various standards.
--    
--    Copyright (C) TIA (2005).  This version of this MIB module
--    is published as Section 13.3 of ANSI/TIA-1057.
--    
--    See the standard itself for full legal notices.
--  RevDate
--    200507280000Z
--  RevDescr
--    Published as part of ANSI/TIA-1057.

lldpXMedNotifications OBJECT IDENTIFIER ::= { lldpXMedMIB 0 }
lldpXMedObjects OBJECT IDENTIFIER ::= { lldpXMedMIB 1 }
lldpXMedConfig  OBJECT IDENTIFIER ::= { lldpXMedObjects 1 }
lldpXMedLocalData OBJECT IDENTIFIER ::= { lldpXMedObjects 2 }
lldpXMedRemoteData OBJECT IDENTIFIER ::= { lldpXMedObjects 3 }
lldpXMedConformance OBJECT IDENTIFIER ::= { lldpXMedMIB 2 }
lldpXMedCompliances OBJECT IDENTIFIER ::= { lldpXMedConformance 1 }
lldpXMedGroups  OBJECT IDENTIFIER ::= { lldpXMedConformance 2 }

LldpXMedDeviceClass ::= INTEGER {
        --?? enum value of zero may cause problems
--        notDefined(0),
        endpointClass1(1),
        endpointClass2(2),
        endpointClass3(3),
        networkConnectivity(4)
        }
-- TEXTUAL-CONVENTION
--  Status
--    mandatory
--  Descr
--    Device Class to which the device is a member.  
--    
--    A value of notDefined(0) indicates that the device 
--    has capabilities not covered by any of the LLDP-MED classes. 
--    
--    A value of endpointClass1(1) indicates that the device 
--    has endpoint class 1 capabilities. 
--    
--    A value of endpointClass2(2) indicates that the device 
--    has endpoint class 2 capabilities. 
--    
--    A value of endpointClass3(3) indicates that the device 
--    has endpoint class 3 capabilities. 
--    
--    A value of networkConnectivity(4) indicates that the device 
--    has network connectivity device capabilities. 

LldpXMedCapabilities ::= OCTET STRING(SIZE(1..2))
        -- BITS are:
        --   capabilities(0)
        --   networkPolicy(1)
        --   location(2)
        --   extendedPSE(3)
        --   extendedPD(4)
        --   inventory(5)
-- TEXTUAL-CONVENTION
--  Status
--    mandatory
--  Descr
--    Bitmap that includes the MED organizationally defined set of LLDP
--    TLVs the device is capable of and whose transmission is allowed on 
--    the local LLDP agent by network management.  
--    
--    Each bit in the bitmap corresponds to an LLDP-MED subtype associated  
--    with a specific TIA TR41.4 MED TLV.  
--    
--    Having the bit 'capabilities(0)' set indicates that the LLDP 
--    agent refers to the Capabilities TLVs.
--    
--    Having the bit 'networkPolicy(1)' set indicates that the LLDP 
--    agent refers to the Network Policy TLVs.
--    
--    Having the bit 'location(2)' set indicates that 
--    the LLDP agent refers to the Emergency Communications
--    System Location TLVs.
--    
--    Having the bit 'extendedPSE(3)' set indicates that 
--    the LLDP agent refers to the Extended PoE TLVs with PSE 
--    capabilities.
--    
--    Having the bit 'extendedPD(4)' set indicates that 
--    the LLDP agent refers to the Extended PoE TLVs with PD 
--    capabilities.
--    
--    Having the bit 'inventory(5)' set indicates that 
--    the LLDP agent refers to the Hardware Revision, Firmware 
--    Revision, Software Revision, Serial Number, Manufacturer Name, 
--    Model Name, and Asset ID TLVs.

LocationSubtype ::= INTEGER {
        unknown(1),
        coordinateBased(2),
        civicAddress(3),
        elin(4)
        }
-- TEXTUAL-CONVENTION
--  Status
--    mandatory
--  Descr
--    The location subtype advertised by the remote endpoint.
--    
--     A value coordinateBased(2) indicates that the location subtype
--     advertised by the endpoint is defined to use the relevant sub-
--     fields of the DHCP option for Coordinate LCI as specified in 
--     ANSI/TIA-1057, Section 10.2.4.3.1.
--    
--     A value civicAddress(3) indicates that the location subtype
--     advertised by the endpoint is defined to use the relevant sub-
--     fields of the DHCP option for Civic Address as specified in 
--     ANSI/TIA-1057, Section 10.2.4.3.2.
--    
--     A value elin(4) indicates that the location subtype 
--     advertised by the endpoint is defined to use the Emergency 
--     Location Information Number (ELIN) as specified in
--     ANSI/TIA-1057, Section 10.2.4.3.3.

PolicyAppType ::= OCTET STRING(SIZE(1..2))
        -- BITS are:
        --   unknown(0)
        --   voice(1)
        --   voiceSignaling(2)
        --   guestVoice(3)
        --   guestVoiceSignaling(4)
        --   softPhoneVoice(5)
        --   videoconferencing(6)
        --   streamingVideo(7)
        --   videoSignaling(8)
-- TEXTUAL-CONVENTION
--  Status
--    mandatory
--  Descr
--    The media type that defines the primary function of the
--     application for the policy advertised by an endpoint.
--    
--     Having the bit voice(1) set indicates that the media type defining
--     a primary function of the application for the policy advertised on 
--     the local port is voice. 
--    
--     Having the bit voiceSignaling(3) set indicates that the media type 
--     defining a primary function of the application for the policy 
--     advertised on the local port is voice signaling. 
--    
--     Having the bit guestVoice(4) set indicates that the media type 
--     Defining a primary function of the application for the policy            
--     advertised on the local port is guest voice. 
--    
--     Having the bit guestVoiceSignaling(5) set indicates that the media
--     type defining a primary function of the application for the policy 
--     advertised on the local port is guest voice signaling. 
--    
--     Having the bit softPhoneVoice(6) set indicates that the media type 
--     Defining a primary function of the application for the policy 
--     advertised on the local port is softphone voice. 
--    
--     Having the bit videoConferencing(7) set indicates that the media 
--     type defining a primary function of the application for the policy 
--     advertised on the local port is voice. 
--    
--     Having the bit streamingVideo(8) set indicates that the media type 
--     defining a primary function of the application for the policy 
--     advertised on  the local port is streaming video. 
--    
--     Having the bit videoSignaling(2) set indicates that the media type 
--     defining a primary function of the application for the policy 
--     advertised on the local port is video signaling.

lldpXMedLocDeviceClass OBJECT-TYPE
    SYNTAX LldpXMedDeviceClass
--    Rsyntax INTEGER {
--        ?? enum value of zero may cause problems
--        notDefined(0),
--        endpointClass1(1),
--        endpointClass2(2),
--        endpointClass3(3),
--        networkConnectivity(4)
--        }
    ACCESS read-only
    STATUS mandatory
    DESCRIPTION
        "Local Device Class."
    REFERENCE
        " ANSI/TIA-1057, Section 10.2.2.2"
    ::= { lldpXMedConfig 1 }

lldpXMedPortConfigTable OBJECT-TYPE
    SYNTAX SEQUENCE OF LldpXMedPortConfigEntry
    ACCESS not-accessible
    STATUS mandatory
    DESCRIPTION
        "A table that controls selection of LLDP TLVs to be transmitted 
        on individual ports."
    ::= { lldpXMedConfig 2 }

lldpXMedPortConfigEntry OBJECT-TYPE
    SYNTAX LldpXMedPortConfigEntry
    ACCESS not-accessible
    STATUS mandatory
    DESCRIPTION
        "LLDP configuration information that controls the
        transmission of the MED organizationally defined TLVs on
        LLDP transmission capable ports.
        
        This configuration object augments the lldpPortConfigEntry of
        the LLDP-MIB, therefore it is only present along with the port
        configuration defined by the associated lldpPortConfigEntry
        entry.
        
        Each active lldpXMedPortConfigEntry must be stored and 
        retrieved from non-volatile storage (along with the 
        corresponding lldpPortConfigEntry) after a re-initialization 
        of the management system."
    INDEX { lldpPortConfigPortNum }
-- Augments lldpPortConfigEntry FROM LLDP-MIB
    ::= { lldpXMedPortConfigTable 1 }

LldpXMedPortConfigEntry ::= SEQUENCE {
    lldpXMedPortCapSupported LldpXMedCapabilities,
    lldpXMedPortConfigTLVsTxEnable LldpXMedCapabilities,
    lldpXMedPortConfigNotifEnable TruthValue
    }

lldpXMedPortCapSupported OBJECT-TYPE
    SYNTAX LldpXMedCapabilities
--    Rsyntax OCTET STRING(SIZE(1..2))
--         BITS are:
--           capabilities(0)
--           networkPolicy(1)
--           location(2)
--           extendedPSE(3)
--           extendedPD(4)
--           inventory(5)
    ACCESS read-only
    STATUS mandatory
    DESCRIPTION
        "The bitmap includes the MED organizationally defined set of LLDP
        TLVs whose transmission is possible for the respective port
        on the LLDP agent of the device. Each bit in the bitmap corresponds
        to an LLDP-MED subtype associated with a specific TIA TR41.4 MED 
        optional TLV. If the bit is set, the agent supports the 
        corresponding TLV."
    REFERENCE
        "ANSI/TIA-1057, Section 10.2.2.3"
    ::= { lldpXMedPortConfigEntry 1 }

lldpXMedPortConfigTLVsTxEnable OBJECT-TYPE
    SYNTAX LldpXMedCapabilities
--    Rsyntax OCTET STRING(SIZE(1..2))
--         BITS are:
--           capabilities(0)
--           networkPolicy(1)
--           location(2)
--           extendedPSE(3)
--           extendedPD(4)
--           inventory(5)
    ACCESS read-write
    STATUS mandatory
    DESCRIPTION
        "The lldpXMedPortConfigTLVsTxEnable, defined as a bitmap,
        includes the MED organizationally defined set of LLDP
        TLVs whose transmission is allowed on the local LLDP agent by
        the network management.  Each bit in the bitmap corresponds
        to an LLDP-MED subtype associated with a specific TIA TR41.4 MED 
        optional TLV. If the bit is set, the agent will send the 
        corresponding TLV if the respective capability is supported per 
        port.
        
        Setting a bit with in this object for a non-supported capability
        shall have no functional effect and will result in an inconsistent
        value error returned to the management application. 
        
        There are other rules and restrictions that prevent arbitrary
        combinations of TLVs to be enabled on LLDP-MED devices according to
        the device classes. These rules are defined in Section 10.2.1, 
        Tables 5 - 9 of ANSI/TIA-1057. In case a management application 
        attempts to set this object to a value that does not follow the rules, 
        the set operation shall have and will result in an inconsistent 
        value error returned to the management application. 
        
        Setting this object to an empty set is valid and effectively 
        disables LLDP-MED on a per-port basis by disabling transmission of 
        all MED organizational TLVs. In this case the remote tables objects 
        in the LLDP-MED MIB corresponding to the respective port will not 
        be populated. 
         
        The default value for lldpXMedPortConfigTLVsTxEnable object
        is an empty set, which means no enumerated values are set.
        
        The value of this object must be restored from non-volatile
        storage after a re-initialization of the management system."
    REFERENCE
        "ANSI/TIA-1057, Section 10.2.2.3"
    DEFVAL { '00'h }
    ::= { lldpXMedPortConfigEntry 2 }

lldpXMedPortConfigNotifEnable OBJECT-TYPE
    SYNTAX TruthValue
--    Rsyntax INTEGER {
--        true(1),
--        false(2)
--        }
    ACCESS read-write
    STATUS mandatory
    DESCRIPTION
        "A value of 'true(1)' enables sending the topology change 
         traps on this port.
         A value of 'false(2)' disables sending the topology change 
         traps on this port."
    REFERENCE
        " ANSI/TIA-1057, Section 12.3"
    DEFVAL { false }
    ::= { lldpXMedPortConfigEntry 3 }

lldpXMedFastStartRepeatCount OBJECT-TYPE
    SYNTAX Gauge(1..10)
    ACCESS read-write
    STATUS mandatory
    DESCRIPTION
        "The number of times the fast start LLDPDU are being sent during the 
         activation of the fast start mechanism defined by LLDP-MED."
    REFERENCE
        " ANSI/TIA-1057, Section 11.2.1"
    DEFVAL { 3 }
    ::= { lldpXMedConfig 3 }

lldpXMedLocMediaPolicyTable OBJECT-TYPE
    SYNTAX SEQUENCE OF LldpXMedLocMediaPolicyEntry
    ACCESS not-accessible
    STATUS mandatory
    DESCRIPTION
        "This table contains one row per policy type per port 
         of media policy information (as a part of the MED 
         organizational extension) on the local system known 
         to this agent."
    ::= { lldpXMedLocalData 1 }

lldpXMedLocMediaPolicyEntry OBJECT-TYPE
    SYNTAX LldpXMedLocMediaPolicyEntry
    ACCESS not-accessible
    STATUS mandatory
    DESCRIPTION
        "Information about a particular policy on a specific 
         port component."
    INDEX { lldpLocPortNum, lldpXMedLocMediaPolicyAppType }
    ::= { lldpXMedLocMediaPolicyTable 1 }

LldpXMedLocMediaPolicyEntry ::= SEQUENCE {
    lldpXMedLocMediaPolicyAppType PolicyAppType,
    lldpXMedLocMediaPolicyVlanID INTEGER,
    lldpXMedLocMediaPolicyPriority INTEGER,
    lldpXMedLocMediaPolicyDscp Dscp,
    lldpXMedLocMediaPolicyUnknown TruthValue,
    lldpXMedLocMediaPolicyTagged TruthValue
    }

lldpXMedLocMediaPolicyAppType OBJECT-TYPE
    SYNTAX PolicyAppType
--    Rsyntax OCTET STRING(SIZE(1..2))
--         BITS are:
--           unknown(0)
--           voice(1)
--           voiceSignaling(2)
--           guestVoice(3)
--           guestVoiceSignaling(4)
--           softPhoneVoice(5)
--           videoconferencing(6)
--           streamingVideo(7)
--           videoSignaling(8)
    ACCESS not-accessible
    STATUS mandatory
    DESCRIPTION
        "The media type that defines the primary function of the
         application for the policy advertised by an endpoint."
    REFERENCE
        "ANSI/TIA-1057, Section 10.2.3.1"
    ::= { lldpXMedLocMediaPolicyEntry 1 }

lldpXMedLocMediaPolicyVlanID OBJECT-TYPE
    SYNTAX INTEGER(0|1..4094|4095)
    ACCESS read-only
    STATUS mandatory
    DESCRIPTION
        "An extension of the VLAN Identifier for the port, 
         as defined in IEEE 802.1P-1998.
        
         A value of 1 through 4094 is used to define a valid PVID.
        
         A value of 0 shall be used if the device is using priority tagged
         frames, meaning that only the 802.1p priority level is significant
         and the default VID of the ingress port is being used instead.
        
         A value of 4095 is reserved for implementation use."
    REFERENCE
        " ANSI/TIA-1057, Section 10.2.3.5"
    ::= { lldpXMedLocMediaPolicyEntry 2 }

lldpXMedLocMediaPolicyPriority OBJECT-TYPE
    SYNTAX INTEGER(0..7)
    ACCESS read-only
    STATUS mandatory
    DESCRIPTION
        "This object contains the value of the 802.1p priority
        which is associated with the given port on the
        local system."
    REFERENCE
        " ANSI/TIA-1057, Section 10.2.3.6 "
    ::= { lldpXMedLocMediaPolicyEntry 3 }

lldpXMedLocMediaPolicyDscp OBJECT-TYPE
    SYNTAX Dscp
--    Rsyntax INTEGER(0..63)
    ACCESS read-only
    STATUS mandatory
    DESCRIPTION
        "This object contains the value of the Differentiated Service
        Code Point (DSCP) as defined in IETF RFC 2474 and RFC 2475
        which is associated with the given port on the local system."
    REFERENCE
        " ANSI/TIA-1057, Section 10.2.3.7"
    ::= { lldpXMedLocMediaPolicyEntry 4 }

lldpXMedLocMediaPolicyUnknown OBJECT-TYPE
    SYNTAX TruthValue
--    Rsyntax INTEGER {
--        true(1),
--        false(2)
--        }
    ACCESS read-only
    STATUS mandatory
    DESCRIPTION
        "A value of 'true' indicates that the 
         network policy for the specified application type is 
         currently unknown.  In this case, the VLAN ID, the 
         layer 2 priority and the DSCP value fields are ignored.
         A value of 'false' indicates that this network policy 
         is defined  "
    REFERENCE
        " ANSI/TIA-1057, Section 10.2.3.2"
    ::= { lldpXMedLocMediaPolicyEntry 5 }

lldpXMedLocMediaPolicyTagged OBJECT-TYPE
    SYNTAX TruthValue
--    Rsyntax INTEGER {
--        true(1),
--        false(2)
--        }
    ACCESS read-only
    STATUS mandatory
    DESCRIPTION
        "A value of 'true' indicates that the application is using a 
         tagged VLAN.
         A value of 'false' indicates that for the specific application
         the device either is using an untagged VLAN or does not 
         support port based VLAN operation.  In this case, both the 
         VLAN ID and the Layer 2 priority fields are ignored and 
         only the DSCP value has relevance "
    REFERENCE
        " ANSI/TIA-1057, Section 10.2.3.3"
    ::= { lldpXMedLocMediaPolicyEntry 6 }

lldpXMedLocHardwareRev OBJECT-TYPE
    SYNTAX SnmpAdminString(SIZE(0..32))
--    Rsyntax OCTET STRING(SIZE(0..32))
    ACCESS read-only
    STATUS mandatory
    DESCRIPTION
        "The vendor-specific hardware revision string
        as advertised by the endpoint."
    REFERENCE
        " ANSI/TIA-1057, Section 10.2.6.1"
    ::= { lldpXMedLocalData 2 }

lldpXMedLocFirmwareRev OBJECT-TYPE
    SYNTAX SnmpAdminString(SIZE(0..32))
--    Rsyntax OCTET STRING(SIZE(0..32))
    ACCESS read-only
    STATUS mandatory
    DESCRIPTION
        "The vendor-specific firmware revision string
        as advertised by the endpoint."
    REFERENCE
        " ANSI/TIA-1057, Section 10.2.6.2"
    ::= { lldpXMedLocalData 3 }

lldpXMedLocSoftwareRev OBJECT-TYPE
    SYNTAX SnmpAdminString(SIZE(0..32))
--    Rsyntax OCTET STRING(SIZE(0..32))
    ACCESS read-only
    STATUS mandatory
    DESCRIPTION
        "The vendor-specific software revision string
        as advertised by the endpoint."
    REFERENCE
        " ANSI/TIA-1057, Section 10.2.6.3"
    ::= { lldpXMedLocalData 4 }

lldpXMedLocSerialNum OBJECT-TYPE
    SYNTAX SnmpAdminString(SIZE(0..32))
--    Rsyntax OCTET STRING(SIZE(0..32))
    ACCESS read-only
    STATUS mandatory
    DESCRIPTION
        "The vendor-specific serial number
        as advertised by the endpoint."
    REFERENCE
        " ANSI/TIA-1057, Section 10.2.6.4"
    ::= { lldpXMedLocalData 5 }

lldpXMedLocMfgName OBJECT-TYPE
    SYNTAX SnmpAdminString(SIZE(0..32))
--    Rsyntax OCTET STRING(SIZE(0..32))
    ACCESS read-only
    STATUS mandatory
    DESCRIPTION
        "The vendor-specific manufacturer name
        as advertised by the endpoint."
    REFERENCE
        " ANSI/TIA-1057, Section 10.2.6.5"
    ::= { lldpXMedLocalData 6 }

lldpXMedLocModelName OBJECT-TYPE
    SYNTAX SnmpAdminString(SIZE(0..32))
--    Rsyntax OCTET STRING(SIZE(0..32))
    ACCESS read-only
    STATUS mandatory
    DESCRIPTION
        "The vendor-specific model name
        as advertised by the endpoint."
    REFERENCE
        " ANSI/TIA-1057, Section 10.2.6.6"
    ::= { lldpXMedLocalData 7 }

lldpXMedLocAssetID OBJECT-TYPE
    SYNTAX SnmpAdminString(SIZE(0..32))
--    Rsyntax OCTET STRING(SIZE(0..32))
    ACCESS read-only
    STATUS mandatory
    DESCRIPTION
        "The vendor-specific asset tracking identifier
        as advertised by the endpoint."
    REFERENCE
        " ANSI/TIA-1057, Section 10.2.6.7"
    ::= { lldpXMedLocalData 8 }

lldpXMedLocLocationTable OBJECT-TYPE
    SYNTAX SEQUENCE OF LldpXMedLocLocationEntry
    ACCESS not-accessible
    STATUS mandatory
    DESCRIPTION
        "This table contains Location information as advertised
        by the local system.
        
        The information may be configured per port by a Location 
        Information Server (LIS) or other management application. 
        
        Multiple Location TLVs of different subtypes may be transmitted
        in the same PDU.
        
        The information in this table MUST be stored in non-volatile-memory 
        and persist over restart/reboot sequences."
    ::= { lldpXMedLocalData 9 }

lldpXMedLocLocationEntry OBJECT-TYPE
    SYNTAX LldpXMedLocLocationEntry
    ACCESS not-accessible
    STATUS mandatory
    DESCRIPTION
        "Information about Location information for the local device."
    INDEX { lldpLocPortNum, lldpXMedLocLocationSubtype }
    ::= { lldpXMedLocLocationTable 1 }

LldpXMedLocLocationEntry ::= SEQUENCE {
    lldpXMedLocLocationSubtype LocationSubtype,
    lldpXMedLocLocationInfo OCTET STRING
    }

lldpXMedLocLocationSubtype OBJECT-TYPE
    SYNTAX LocationSubtype
--    Rsyntax INTEGER {
--        unknown(1),
--        coordinateBased(2),
--        civicAddress(3),
--        elin(4)
--        }
    ACCESS not-accessible
    STATUS mandatory
    DESCRIPTION
        "The location subtype advertised by the local device."
    REFERENCE
        "ANSI/TIA-1057, Section 10.2.4.2"
    ::= { lldpXMedLocLocationEntry 1 }

lldpXMedLocLocationInfo OBJECT-TYPE
    SYNTAX OCTET STRING(SIZE(0..256))
    ACCESS read-write
    STATUS mandatory
    DESCRIPTION
        "The location information. Parsing of this information is 
         dependent upon the location subtype, as defined by the value of the 
         lldpXMedLocLocationSubtype object. "
    REFERENCE
        "ANSI/TIA-1057, Section 10.2.4.3"
    DEFVAL { "" }
    ::= { lldpXMedLocLocationEntry 2 }

lldpXMedLocXPoEDeviceType OBJECT-TYPE
    SYNTAX INTEGER {
        unknown(1),
        pseDevice(2),
        pdDevice(3),
        none(4)
        }
    ACCESS read-only
    STATUS mandatory
    DESCRIPTION
        "Defines the type of Power-via-MDI (Power over Ethernet) advertised
         by the local device.
        
         A value pseDevice(2) indicates that the device is advertised as a 
         Power Sourcing Entity (PSE).
        
         A value pdDevice(3) indicates that the device is advertised as a 
         Powered Device (PD).
        
         A value of none(4) indicates that the device does not support PoE."
    REFERENCE
        "ANSI/TIA-1057, Section 10.2.5.1"
    ::= { lldpXMedLocalData 10 }

lldpXMedLocXPoEPSEPortTable OBJECT-TYPE
    SYNTAX SEQUENCE OF LldpXMedLocXPoEPSEPortEntry
    ACCESS not-accessible
    STATUS mandatory
    DESCRIPTION
        "This table contains one row per port of PSE PoE
        information on the local system known to this agent."
    ::= { lldpXMedLocalData 11 }

lldpXMedLocXPoEPSEPortEntry OBJECT-TYPE
    SYNTAX LldpXMedLocXPoEPSEPortEntry
    ACCESS not-accessible
    STATUS mandatory
    DESCRIPTION
        "Information about a particular port PoE information."
    INDEX { lldpLocPortNum }
    ::= { lldpXMedLocXPoEPSEPortTable 1 }

LldpXMedLocXPoEPSEPortEntry ::= SEQUENCE {
    lldpXMedLocXPoEPSEPortPowerAv Gauge,
    lldpXMedLocXPoEPSEPortPDPriority INTEGER
    }

lldpXMedLocXPoEPSEPortPowerAv OBJECT-TYPE
    SYNTAX Gauge(0..1023)
--  Units
--    tenth of watt
    ACCESS read-only
    STATUS mandatory
    DESCRIPTION
        "This object contains the value of the power available from the
        PSE via this port expressed in units of 0.1 watts."
    REFERENCE
        " ANSI/TIA-1057, Section 10.2.5.4 "
    ::= { lldpXMedLocXPoEPSEPortEntry 1 }

lldpXMedLocXPoEPSEPortPDPriority OBJECT-TYPE
    SYNTAX INTEGER {
        unknown(1),
        critical(2),
        high(3),
        low(4)
        }
    ACCESS read-only
    STATUS mandatory
    DESCRIPTION
        "Reflects the PD power priority that is being advertised on this
         PSE port.
        
         If both locally configure priority and 
         ldpXMedRemXPoEPDPowerPriority are available on this port, it is
         a matter of local policy which one takes precedence. This object 
         reflects the active value on this port. 
        
         If the priority is not configured or known by the PD, the value 
         unknown(1) will be returned. 
        
         A value critical(2) indicates that the device advertises its power 
         Priority as critical, as per RFC 3621.
        
         A value high(3) indicates that the device advertises its power 
         Priority as high, as per RFC 3621.
        
         A value low(4) indicates that the device advertises its power 
         Priority as low, as per RFC 3621."
    REFERENCE
        "ANSI/TIA-1057, Section 10.2.5.3"
    ::= { lldpXMedLocXPoEPSEPortEntry 2 }

lldpXMedLocXPoEPSEPowerSource OBJECT-TYPE
    SYNTAX INTEGER {
        unknown(1),
        primary(2),
        backup(3)
        }
    ACCESS read-only
    STATUS mandatory
    DESCRIPTION
        "Defines the type of PSE Power Source advertised
         by the local device.
        
         A value primary(2) indicates that the device advertises its power 
         source as primary.
        
         A value backup(3) indicates that the device advertises its power 
         Source as backup."
    REFERENCE
        "ANSI/TIA-1057, Section 10.2.5.2"
    ::= { lldpXMedLocalData 12 }

lldpXMedLocXPoEPDPowerReq OBJECT-TYPE
    SYNTAX Gauge(0..1023)
--  Units
--    tenth of watt
    ACCESS read-only
    STATUS mandatory
    DESCRIPTION
        "This object contains the value of the power required by a 
        PD expressed in units of 0.1 watts."
    REFERENCE
        " ANSI/TIA-1057, Section 10.2.4.3 "
    ::= { lldpXMedLocalData 13 }

lldpXMedLocXPoEPDPowerSource OBJECT-TYPE
    SYNTAX INTEGER {
        unknown(1),
        fromPSE(2),
        local(3),
        localAndPSE(4)
        }
    ACCESS read-only
    STATUS mandatory
    DESCRIPTION
        "Defines the type of Power Source advertised as being used 
         by the local device.
        
         A value fromPSE(2) indicates that the device advertises its power 
         source as received from a PSE.
        
         A value local(3) indicates that the device advertises its power 
         source as local.
        
         A value localAndPSE(4) indicates that the device advertises its 
         power source as using both local and PSE power."
    REFERENCE
        "ANSI/TIA-1057, Section 10.2.5.2"
    ::= { lldpXMedLocalData 14 }

lldpXMedLocXPoEPDPowerPriority OBJECT-TYPE
    SYNTAX INTEGER {
        unknown(1),
        critical(2),
        high(3),
        low(4)
        }
    ACCESS read-only
    STATUS mandatory
    DESCRIPTION
        "Defines the priority advertised as being required by this PD.
        
         A value critical(2) indicates that the device advertises its power 
         Priority as critical, as per RFC 3621.
        
         A value high(3) indicates that the device advertises its power 
         Priority as high, as per RFC 3621.
        
         A value low(4) indicates that the device advertises its power 
         Priority as low, as per RFC 3621."
    REFERENCE
        "ANSI/TIA-1057, Section 10.2.5.3"
    ::= { lldpXMedLocalData 15 }

lldpXMedRemCapabilitiesTable OBJECT-TYPE
    SYNTAX SEQUENCE OF LldpXMedRemCapabilitiesEntry
    ACCESS not-accessible
    STATUS mandatory
    DESCRIPTION
        "A table that displays LLDP-MED capabilities of remote devices 
        connected to individual ports."
    ::= { lldpXMedRemoteData 1 }

lldpXMedRemCapabilitiesEntry OBJECT-TYPE
    SYNTAX LldpXMedRemCapabilitiesEntry
    ACCESS not-accessible
    STATUS mandatory
    DESCRIPTION
        "LLDP-MED capabilities of remote devices connected to the device 
        ports and communicating via LLDP-MED.
        
        The remote tables in the LLDP-MED MIB excepting this table may be 
        sparsely populate. An entry in one of these table is meaningful 
        and shall be populated by the agent only if the corresponding bits
        for the respective function are set in the objects in this table. "
    INDEX { lldpRemTimeMark, lldpRemLocalPortNum, lldpRemIndex }
    ::= { lldpXMedRemCapabilitiesTable 1 }

LldpXMedRemCapabilitiesEntry ::= SEQUENCE {
    lldpXMedRemCapSupported LldpXMedCapabilities,
    lldpXMedRemCapCurrent LldpXMedCapabilities,
    lldpXMedRemDeviceClass LldpXMedDeviceClass
    }

lldpXMedRemCapSupported OBJECT-TYPE
    SYNTAX LldpXMedCapabilities
--    Rsyntax OCTET STRING(SIZE(1..2))
--         BITS are:
--           capabilities(0)
--           networkPolicy(1)
--           location(2)
--           extendedPSE(3)
--           extendedPD(4)
--           inventory(5)
    ACCESS read-only
    STATUS mandatory
    DESCRIPTION
        "The bitmap includes the MED organizationally defined set of LLDP
        TLVs whose transmission is possible on the LLDP agent of the remote
        device connected to this port. Each bit in the bitmap corresponds
        to an LLDP-MED subtype associated with a specific TIA TR41.4 MED                
        optional TLV. If the bit is set, the agent has the capability 
        to support the corresponding TLV."
    REFERENCE
        "ANSI/TIA-1057, Sections 10.2.2.1"
    ::= { lldpXMedRemCapabilitiesEntry 1 }

lldpXMedRemCapCurrent OBJECT-TYPE
    SYNTAX LldpXMedCapabilities
--    Rsyntax OCTET STRING(SIZE(1..2))
--         BITS are:
--           capabilities(0)
--           networkPolicy(1)
--           location(2)
--           extendedPSE(3)
--           extendedPD(4)
--           inventory(5)
    ACCESS read-only
    STATUS mandatory
    DESCRIPTION
        "The bitmap includes the MED organizationally defined set of LLDP
        TLVs whose transmission is possible on the LLDP agent of the remote
        device connected to this port. Each bit in the bitmap corresponds
        to an LLDP-MED subtype associated with a specific TIA TR41.4 MED                
        optional TLV. If the bit is set, the agent currently supports the 
        corresponding TLV."
    REFERENCE
        "ANSI/TIA-1057, Sections 10.2.2.1"
    ::= { lldpXMedRemCapabilitiesEntry 2 }

lldpXMedRemDeviceClass OBJECT-TYPE
    SYNTAX LldpXMedDeviceClass
--    Rsyntax INTEGER {
--        ?? enum value of zero may cause problems
--        notDefined(0),
--        endpointClass1(1),
--        endpointClass2(2),
--        endpointClass3(3),
--        networkConnectivity(4)
--        }
    ACCESS read-only
    STATUS mandatory
    DESCRIPTION
        "Device Class as advertised by the device remotely connected to the 
         port."
    REFERENCE
        " ANSI/TIA-1057, Section 10.2.2.2"
    ::= { lldpXMedRemCapabilitiesEntry 3 }

lldpXMedRemMediaPolicyTable OBJECT-TYPE
    SYNTAX SEQUENCE OF LldpXMedRemMediaPolicyEntry
    ACCESS not-accessible
    STATUS mandatory
    DESCRIPTION
        "This table contains media policy information as advertised
        by the remote system.
        
        This table may be sparsely populated. Entries in this table are
        relevant only if the networkPolicy(0) bits in the 
        lldpXMedRemCapSupported and lldpXMedRemCapCurrent objects of the 
        corresponding ports are set."
    ::= { lldpXMedRemoteData 2 }

lldpXMedRemMediaPolicyEntry OBJECT-TYPE
    SYNTAX LldpXMedRemMediaPolicyEntry
    ACCESS not-accessible
    STATUS mandatory
    DESCRIPTION
        "Information about the per port per policy type policy 
         information for a particular physical network connection."
    INDEX { lldpRemTimeMark, lldpRemLocalPortNum, lldpRemIndex, lldpXMedRemMediaPolicyAppType }
    ::= { lldpXMedRemMediaPolicyTable 1 }

LldpXMedRemMediaPolicyEntry ::= SEQUENCE {
    lldpXMedRemMediaPolicyAppType PolicyAppType,
    lldpXMedRemMediaPolicyVlanID INTEGER,
    lldpXMedRemMediaPolicyPriority INTEGER,
    lldpXMedRemMediaPolicyDscp Dscp,
    lldpXMedRemMediaPolicyUnknown TruthValue,
    lldpXMedRemMediaPolicyTagged TruthValue
    }

lldpXMedRemMediaPolicyAppType OBJECT-TYPE
    SYNTAX PolicyAppType
--    Rsyntax OCTET STRING(SIZE(1..2))
--         BITS are:
--           unknown(0)
--           voice(1)
--           voiceSignaling(2)
--           guestVoice(3)
--           guestVoiceSignaling(4)
--           softPhoneVoice(5)
--           videoconferencing(6)
--           streamingVideo(7)
--           videoSignaling(8)
    ACCESS not-accessible
    STATUS mandatory
    DESCRIPTION
        "The media type that defines the primary function of the
         application for the policy advertised by the endpoint connected 
         remotely to this port."
    REFERENCE
        "ANSI/TIA-1057, Section 10.2.3.1"
    ::= { lldpXMedRemMediaPolicyEntry 1 }

lldpXMedRemMediaPolicyVlanID OBJECT-TYPE
    SYNTAX INTEGER(0|1..4094|4095)
    ACCESS read-only
    STATUS mandatory
    DESCRIPTION
        "An extension of the VLAN Identifier for the remote system
         connected to this port, as defined in IEEE 802.1P-1998.
         
         A value of 1 through 4094 is used to define a valid PVID.
         
         A value of 0 shall be used if the device is using priority tagged
         frames, meaning that only the 802.1p priority level is significant
         and the default VID of the ingress port is being used instead.
         
         A value of 4095 is reserved for implementation use."
    REFERENCE
        " ANSI/TIA-1057, Section 10.2.3.5"
    ::= { lldpXMedRemMediaPolicyEntry 2 }

lldpXMedRemMediaPolicyPriority OBJECT-TYPE
    SYNTAX INTEGER(0..7)
    ACCESS read-only
    STATUS mandatory
    DESCRIPTION
        "This object contains the value of the 802.1p priority
        which is associated with the remote system connected at
        given port."
    REFERENCE
        " ANSI/TIA-1057, Section 10.2.3.6"
    ::= { lldpXMedRemMediaPolicyEntry 3 }

lldpXMedRemMediaPolicyDscp OBJECT-TYPE
    SYNTAX Dscp
--    Rsyntax INTEGER(0..63)
    ACCESS read-only
    STATUS mandatory
    DESCRIPTION
        "This object contains the value of the Differentiated Service
        Code Point (DSCP) as defined in IETF RFC 2474 and RFC 2475
        which is associated with remote system connected at the port."
    REFERENCE
        " ANSI/TIA-1057, Section 10.2.3.7"
    ::= { lldpXMedRemMediaPolicyEntry 4 }

lldpXMedRemMediaPolicyUnknown OBJECT-TYPE
    SYNTAX TruthValue
--    Rsyntax INTEGER {
--        true(1),
--        false(2)
--        }
    ACCESS read-only
    STATUS mandatory
    DESCRIPTION
        "A value of 'true' indicates that the 
         network policy for the specified application type is 
         currently unknown.  In this case, the VLAN ID, the 
         layer 2 priority and the DSCP value fields are ignored.
         A value of 'false' indicates that this network policy 
         is defined."
    REFERENCE
        " ANSI/TIA-1057, Section 10.2.3.2"
    ::= { lldpXMedRemMediaPolicyEntry 5 }

lldpXMedRemMediaPolicyTagged OBJECT-TYPE
    SYNTAX TruthValue
--    Rsyntax INTEGER {
--        true(1),
--        false(2)
--        }
    ACCESS read-only
    STATUS mandatory
    DESCRIPTION
        "A value of 'true' indicates that the application is using a 
         tagged VLAN.
         A value of 'false' indicates that for the specific application
         the device either is using an untagged VLAN or does not 
         support port based VLAN operation.  In this case, both the 
         VLAN ID and the Layer 2 priority fields are ignored and 
         only the DSCP value has relevance "
    REFERENCE
        " ANSI/TIA-1057, Section 10.2.3.3"
    ::= { lldpXMedRemMediaPolicyEntry 6 }

lldpXMedRemInventoryTable OBJECT-TYPE
    SYNTAX SEQUENCE OF LldpXMedRemInventoryEntry
    ACCESS not-accessible
    STATUS mandatory
    DESCRIPTION
        "This table contains inventory information as advertised
        by the remote system.
        
        This table may be sparsely populated. Entries in this table are
        relevant only if the inventory(2) bits in the 
        lldpXMedRemCapSupported and lldpXMedRemCapCurrent objects of the 
        corresponding ports are set "
    ::= { lldpXMedRemoteData 3 }

lldpXMedRemInventoryEntry OBJECT-TYPE
    SYNTAX LldpXMedRemInventoryEntry
    ACCESS not-accessible
    STATUS mandatory
    DESCRIPTION
        "Information about inventory information for the remote devices
         connected to the ports."
    INDEX { lldpRemTimeMark, lldpRemLocalPortNum, lldpRemIndex }
    ::= { lldpXMedRemInventoryTable 1 }

LldpXMedRemInventoryEntry ::= SEQUENCE {
    lldpXMedRemHardwareRev SnmpAdminString,
    lldpXMedRemFirmwareRev SnmpAdminString,
    lldpXMedRemSoftwareRev SnmpAdminString,
    lldpXMedRemSerialNum SnmpAdminString,
    lldpXMedRemMfgName SnmpAdminString,
    lldpXMedRemModelName SnmpAdminString,
    lldpXMedRemAssetID SnmpAdminString
    }

lldpXMedRemHardwareRev OBJECT-TYPE
    SYNTAX SnmpAdminString(SIZE(0..32))
--    Rsyntax OCTET STRING(SIZE(0..32))
    ACCESS read-only
    STATUS mandatory
    DESCRIPTION
        "The vendor-specific hardware revision string
        as advertised by the remote endpoint."
    REFERENCE
        " ANSI/TIA-1057, Section 10.2.6.1"
    ::= { lldpXMedRemInventoryEntry 1 }

lldpXMedRemFirmwareRev OBJECT-TYPE
    SYNTAX SnmpAdminString(SIZE(0..32))
--    Rsyntax OCTET STRING(SIZE(0..32))
    ACCESS read-only
    STATUS mandatory
    DESCRIPTION
        "The vendor-specific firmware revision string
        as advertised by the remote endpoint."
    REFERENCE
        " ANSI/TIA-1057, Section 10.2.6.2"
    ::= { lldpXMedRemInventoryEntry 2 }

lldpXMedRemSoftwareRev OBJECT-TYPE
    SYNTAX SnmpAdminString(SIZE(0..32))
--    Rsyntax OCTET STRING(SIZE(0..32))
    ACCESS read-only
    STATUS mandatory
    DESCRIPTION
        "The vendor-specific software revision string
        as advertised by the remote endpoint."
    REFERENCE
        " ANSI/TIA-1057, Section 10.2.6.3"
    ::= { lldpXMedRemInventoryEntry 3 }

lldpXMedRemSerialNum OBJECT-TYPE
    SYNTAX SnmpAdminString(SIZE(0..32))
--    Rsyntax OCTET STRING(SIZE(0..32))
    ACCESS read-only
    STATUS mandatory
    DESCRIPTION
        "The vendor-specific serial number
        as advertised by the remote endpoint."
    REFERENCE
        " ANSI/TIA-1057, Section 10.2.6.4"
    ::= { lldpXMedRemInventoryEntry 4 }

lldpXMedRemMfgName OBJECT-TYPE
    SYNTAX SnmpAdminString(SIZE(0..32))
--    Rsyntax OCTET STRING(SIZE(0..32))
    ACCESS read-only
    STATUS mandatory
    DESCRIPTION
        "The vendor-specific manufacturer name
        as advertised by the remote endpoint."
    REFERENCE
        " ANSI/TIA-1057, Section 10.2.6.5"
    ::= { lldpXMedRemInventoryEntry 5 }

lldpXMedRemModelName OBJECT-TYPE
    SYNTAX SnmpAdminString(SIZE(0..32))
--    Rsyntax OCTET STRING(SIZE(0..32))
    ACCESS read-only
    STATUS mandatory
    DESCRIPTION
        "The vendor-specific model name
        as advertised by the remote endpoint."
    REFERENCE
        " ANSI/TIA-1057, Section 10.2.6.6"
    ::= { lldpXMedRemInventoryEntry 6 }

lldpXMedRemAssetID OBJECT-TYPE
    SYNTAX SnmpAdminString(SIZE(0..32))
--    Rsyntax OCTET STRING(SIZE(0..32))
    ACCESS read-only
    STATUS mandatory
    DESCRIPTION
        "The vendor-specific asset tracking identifier
        as advertised by the remote endpoint."
    REFERENCE
        " ANSI/TIA-1057, Section 10.2.6.7"
    ::= { lldpXMedRemInventoryEntry 7 }

lldpXMedRemLocationTable OBJECT-TYPE
    SYNTAX SEQUENCE OF LldpXMedRemLocationEntry
    ACCESS not-accessible
    STATUS mandatory
    DESCRIPTION
        "This table contains Location information as advertised
        by the remote system.
        
        This table may be sparsely populated. Entries in this table are
        relevant only if the Location(3) bits in the 
        lldpXMedRemCapSupported and lldpXMedRemCapCurrent objects of the 
        corresponding ports are set "
    ::= { lldpXMedRemoteData 4 }

lldpXMedRemLocationEntry OBJECT-TYPE
    SYNTAX LldpXMedRemLocationEntry
    ACCESS not-accessible
    STATUS mandatory
    DESCRIPTION
        "Information about Location information for the remote devices
         connected to the ports."
    INDEX { lldpRemTimeMark, lldpRemLocalPortNum, lldpRemIndex, lldpXMedRemLocationSubtype }
    ::= { lldpXMedRemLocationTable 1 }

LldpXMedRemLocationEntry ::= SEQUENCE {
    lldpXMedRemLocationSubtype LocationSubtype,
    lldpXMedRemLocationInfo OCTET STRING
    }

lldpXMedRemLocationSubtype OBJECT-TYPE
    SYNTAX LocationSubtype
--    Rsyntax INTEGER {
--        unknown(1),
--        coordinateBased(2),
--        civicAddress(3),
--        elin(4)
--        }
    ACCESS not-accessible
    STATUS mandatory
    DESCRIPTION
        "The location subtype advertised by the remote endpoint."
    REFERENCE
        "ANSI/TIA-1057, Section 10.2.4.2 "
    ::= { lldpXMedRemLocationEntry 1 }

lldpXMedRemLocationInfo OBJECT-TYPE
    SYNTAX OCTET STRING(SIZE(0..256))
    ACCESS read-only
    STATUS mandatory
    DESCRIPTION
        "The location information advertised by the remote endpoint.
         Parsing of this information is dependent upon the location  
         subtype, as defined by the value of the corresponding
         lldpXMedRemLocationSubType object. "
    REFERENCE
        "ANSI/TIA-1057, Section 10.2.4.3 "
    ::= { lldpXMedRemLocationEntry 2 }

lldpXMedRemXPoETable OBJECT-TYPE
    SYNTAX SEQUENCE OF LldpXMedRemXPoEEntry
    ACCESS not-accessible
    STATUS mandatory
    DESCRIPTION
        "This table contains information about the PoE device type
        as advertised by the remote system.
        
        This table is densely populated."
    ::= { lldpXMedRemoteData 5 }

lldpXMedRemXPoEEntry OBJECT-TYPE
    SYNTAX LldpXMedRemXPoEEntry
    ACCESS not-accessible
    STATUS mandatory
    DESCRIPTION
        "Information about PoE type of the remote devices
         connected to the ports."
    INDEX { lldpRemTimeMark, lldpRemLocalPortNum, lldpRemIndex }
    ::= { lldpXMedRemXPoETable 1 }

LldpXMedRemXPoEEntry ::= SEQUENCE {
    lldpXMedRemXPoEDeviceType INTEGER
    }

lldpXMedRemXPoEDeviceType OBJECT-TYPE
    SYNTAX INTEGER {
        unknown(1),
        pseDevice(2),
        pdDevice(3),
        none(4)
        }
    ACCESS read-only
    STATUS mandatory
    DESCRIPTION
        "Defines the type of Power-via-MDI (Power over Ethernet) advertised
         by the remote device.
        
         A value pseDevice(2) indicates that the device is advertised as a 
         Power Sourcing Entity (PSE).
        
         A value pdDevice(3) indicates that the device is advertised as a 
         Powered Device (PD).
        
         A value none(4) indicates that the device does not support PoE."
    REFERENCE
        "ANSI/TIA-1057, Section 10.2.5.1"
    ::= { lldpXMedRemXPoEEntry 1 }

lldpXMedRemXPoEPSETable OBJECT-TYPE
    SYNTAX SEQUENCE OF LldpXMedRemXPoEPSEEntry
    ACCESS not-accessible
    STATUS mandatory
    DESCRIPTION
        "This table contains extended PoE information as advertised
        by the remote devices of PSE type.
        
        This table may be sparsely populated. Entries in this table are
        relevant only if the extendedPSE(4) bits in the 
        lldpXMedRemCapSupported and lldpXMedRemCapCurrent objects of the 
        corresponding ports are set "
    ::= { lldpXMedRemoteData 6 }

lldpXMedRemXPoEPSEEntry OBJECT-TYPE
    SYNTAX LldpXMedRemXPoEPSEEntry
    ACCESS not-accessible
    STATUS mandatory
    DESCRIPTION
        "Information about Extended PoE PSE information for 
        the remote devices connected to the ports."
    INDEX { lldpRemTimeMark, lldpRemLocalPortNum, lldpRemIndex }
    ::= { lldpXMedRemXPoEPSETable 1 }

LldpXMedRemXPoEPSEEntry ::= SEQUENCE {
    lldpXMedRemXPoEPSEPowerAv Gauge,
    lldpXMedRemXPoEPSEPowerSource INTEGER,
    lldpXMedRemXPoEPSEPowerPriority INTEGER
    }

lldpXMedRemXPoEPSEPowerAv OBJECT-TYPE
    SYNTAX Gauge(0..1023)
--  Units
--    tenth of watt
    ACCESS read-only
    STATUS mandatory
    DESCRIPTION
        "This object contains the value of the power available from the
        PSE via this port expressed in units of 0.1 watts on the remote 
        device."
    REFERENCE
        " ANSI/TIA-1057, Section 10.2.5.4"
    ::= { lldpXMedRemXPoEPSEEntry 1 }

lldpXMedRemXPoEPSEPowerSource OBJECT-TYPE
    SYNTAX INTEGER {
        unknown(1),
        primary(2),
        backup(3)
        }
    ACCESS read-only
    STATUS mandatory
    DESCRIPTION
        "Defines the type of PSE Power Source advertised
         by the remote device.
        
         A value primary(2) indicates that the device advertises its power 
         source as primary.
        
         A value backup(3) indicates that the device advertises its power 
         Source as backup."
    REFERENCE
        "ANSI/TIA-1057, Section 10.2.5.2"
    ::= { lldpXMedRemXPoEPSEEntry 2 }

lldpXMedRemXPoEPSEPowerPriority OBJECT-TYPE
    SYNTAX INTEGER {
        unknown(1),
        critical(2),
        high(3),
        low(4)
        }
    ACCESS read-only
    STATUS mandatory
    DESCRIPTION
        "This object contains the value of the PSE power priority 
        advertised by the remote device.
        
        A value critical(2) indicates that the device advertises its power 
        priority as critical, as per RFC 3621.
        
        A value high(3) indicates that the device advertises its power 
        priority as high, as per RFC 3621.
        
        A value low(4) indicates that the device advertises its power 
        priority as low, as per RFC 3621."
    REFERENCE
        "ANSI/TIA-1057, Section 10.2.5.3"
    ::= { lldpXMedRemXPoEPSEEntry 3 }

lldpXMedRemXPoEPDTable OBJECT-TYPE
    SYNTAX SEQUENCE OF LldpXMedRemXPoEPDEntry
    ACCESS not-accessible
    STATUS mandatory
    DESCRIPTION
        "This table contains extended PoE information as advertised
        by the remote devices of PD type.
        
        This table may be sparsely populated. Entries in this table are
        relevant only if the extendedPD(5) bits in the 
        lldpXMedRemCapSupported and lldpXMedRemCapCurrent objects of the 
        corresponding ports are set "
    ::= { lldpXMedRemoteData 7 }

lldpXMedRemXPoEPDEntry OBJECT-TYPE
    SYNTAX LldpXMedRemXPoEPDEntry
    ACCESS not-accessible
    STATUS mandatory
    DESCRIPTION
        "Information about XPoEPD information for the remote devices
         connected to the ports."
    INDEX { lldpRemTimeMark, lldpRemLocalPortNum, lldpRemIndex }
    ::= { lldpXMedRemXPoEPDTable 1 }

LldpXMedRemXPoEPDEntry ::= SEQUENCE {
    lldpXMedRemXPoEPDPowerReq Gauge,
    lldpXMedRemXPoEPDPowerSource INTEGER,
    lldpXMedRemXPoEPDPowerPriority INTEGER
    }

lldpXMedRemXPoEPDPowerReq OBJECT-TYPE
    SYNTAX Gauge(0..1023)
--  Units
--    tenth of watt
    ACCESS read-only
    STATUS mandatory
    DESCRIPTION
        "This object contains the value of the power required by a 
        PD connected remotely to the port
        expressed in units of 0.1 watts."
    REFERENCE
        " ANSI/TIA-1057, Section 10.2.5.4 "
    ::= { lldpXMedRemXPoEPDEntry 1 }

lldpXMedRemXPoEPDPowerSource OBJECT-TYPE
    SYNTAX INTEGER {
        unknown(1),
        fromPSE(2),
        local(3),
        localAndPSE(4)
        }
    ACCESS read-only
    STATUS mandatory
    DESCRIPTION
        "Defines the type of Power Source advertised as being used 
         by the device connected remotely to the port.
        
         A value fromPSE(2) indicates that the device advertises its power 
         source as received from a PSE.
        
         A value local(3) indicates that the device advertises its power 
         source as local.
        
         A value localAndPSE(4) indicates that the device advertises its 
         power source as using both local and PSE power."
    REFERENCE
        "ANSI/TIA-1057, Section 10.2.5.2"
    ::= { lldpXMedRemXPoEPDEntry 2 }

lldpXMedRemXPoEPDPowerPriority OBJECT-TYPE
    SYNTAX INTEGER {
        unknown(1),
        critical(2),
        high(3),
        low(4)
        }
    ACCESS read-only
    STATUS mandatory
    DESCRIPTION
        "Defines the priority advertised as being required by the PD
         connected remotely to the port.
        
         A value critical(2) indicates that the device advertises its power 
         Priority as critical, as per RFC 3621.
        
         A value high(3) indicates that the device advertises its power 
         Priority as high, as per RFC 3621.
        
         A value low(4) indicates that the device advertises its power 
         Priority as low, as per RFC 3621."
    REFERENCE
        "ANSI/TIA-1057, Section 10.2.5.3"
    ::= { lldpXMedRemXPoEPDEntry 3 }

lldpXMedTopologyChangeDetected TRAP-TYPE
-- Reverse mappable trap
    ENTERPRISE lldpXMedMIB
    VARIABLES {
        lldpRemChassisIdSubtype, lldpRemChassisId, 
        lldpXMedRemDeviceClass }
--  Status
--    mandatory
    DESCRIPTION
        "A notification generated by the local device sensing
         a change in the topology that indicates that a new remote
         device attached to a local port, or a remote device disconnected 
         or moved from one port to another."
    ::= 1

lldpXMedConfigGroup OBJECT IDENTIFIER ::= { lldpXMedGroups 1 }
-- OBJECT-GROUP
--  Status
--    mandatory
--  Descr
--    The collection of objects which are used to configure or
--    describe the configuration or behavior of the LLDP-MED
--    organizational extension implementation.
--  objects
--    lldpXMedPortCapSupported, lldpXMedPortConfigTLVsTxEnable, 
--    lldpXMedPortConfigNotifEnable, lldpXMedFastStartRepeatCount, 
--    lldpXMedLocXPoEDeviceType, lldpXMedLocDeviceClass

lldpXMedOptMediaPolicyGroup OBJECT IDENTIFIER ::= { lldpXMedGroups 2 }
-- OBJECT-GROUP
--  Status
--    mandatory
--  Descr
--    The collection of objects which are used to represent LLDP
--    MED organizational extensions for Media Policy Information.
--  objects
--    lldpXMedLocMediaPolicyVlanID, lldpXMedLocMediaPolicyPriority, 
--    lldpXMedLocMediaPolicyDscp, lldpXMedLocMediaPolicyUnknown, 
--    lldpXMedLocMediaPolicyTagged

lldpXMedOptInventoryGroup OBJECT IDENTIFIER ::= { lldpXMedGroups 3 }
-- OBJECT-GROUP
--  Status
--    mandatory
--  Descr
--    The collection of objects which are used to represent LLDP
--    MED organizational extension for inventory Information.
--  objects
--    lldpXMedLocHardwareRev, lldpXMedLocFirmwareRev, 
--    lldpXMedLocSoftwareRev, lldpXMedLocSerialNum, 
--    lldpXMedLocMfgName, lldpXMedLocModelName, lldpXMedLocAssetID

lldpXMedOptLocationGroup OBJECT IDENTIFIER ::= { lldpXMedGroups 4 }
-- OBJECT-GROUP
--  Status
--    mandatory
--  Descr
--    The collection of objects which are used to represent LLDP
--    MED organizational extension for Location Information.
--  objects
--    lldpXMedLocLocationInfo

lldpXMedOptPoEPSEGroup OBJECT IDENTIFIER ::= { lldpXMedGroups 5 }
-- OBJECT-GROUP
--  Status
--    mandatory
--  Descr
--    The collection of objects which are used to represent LLDP
--    MED organizational extensions for PoE PSE Information.
--  objects
--    lldpXMedLocXPoEPSEPortPowerAv, 
--    lldpXMedLocXPoEPSEPortPDPriority, 
--    lldpXMedLocXPoEPSEPowerSource

lldpXMedOptPoEPDGroup OBJECT IDENTIFIER ::= { lldpXMedGroups 6 }
-- OBJECT-GROUP
--  Status
--    mandatory
--  Descr
--    The collection of objects which are used to represent LLDP
--    MED organizational extensions for PoE PD Information.
--  objects
--    lldpXMedLocXPoEPDPowerReq, lldpXMedLocXPoEPDPowerSource, 
--    lldpXMedLocXPoEPDPowerPriority

lldpXMedRemSysGroup OBJECT IDENTIFIER ::= { lldpXMedGroups 7 }
-- OBJECT-GROUP
--  Status
--    mandatory
--  Descr
--    The collection of objects which are used to represent LLDP-
--    MED organizational extension Remote Device Information.
--  objects
--    lldpXMedRemCapSupported, lldpXMedRemCapCurrent, 
--    lldpXMedRemDeviceClass, lldpXMedRemMediaPolicyVlanID, 
--    lldpXMedRemMediaPolicyPriority, lldpXMedRemMediaPolicyDscp, 
--    lldpXMedRemMediaPolicyUnknown, lldpXMedRemMediaPolicyTagged, 
--    lldpXMedRemHardwareRev, lldpXMedRemFirmwareRev, 
--    lldpXMedRemSoftwareRev, lldpXMedRemSerialNum, 
--    lldpXMedRemMfgName, lldpXMedRemModelName, lldpXMedRemAssetID, 
--    lldpXMedRemLocationInfo, lldpXMedRemXPoEDeviceType, 
--    lldpXMedRemXPoEPSEPowerAv, lldpXMedRemXPoEPSEPowerSource, 
--    lldpXMedRemXPoEPSEPowerPriority, lldpXMedRemXPoEPDPowerReq, 
--    lldpXMedRemXPoEPDPowerSource, lldpXMedRemXPoEPDPowerPriority

lldpXMedNotificationsGroup OBJECT IDENTIFIER ::= { lldpXMedGroups 8 }
-- NOTIFICATION-GROUP
--  Status
--    mandatory
--  Descr
--    Notifications sent by an LLDP-MED agent.
--  notifications
--    lldpXMedTopologyChangeDetected

lldpXMedCompliance OBJECT IDENTIFIER ::= { lldpXMedCompliances 1 }
-- MODULE-COMPLIANCE
--  Status
--    mandatory
--  Descr
--    The compliance statement for SNMP entities which implement
--    the LLDP MED extension MIB.
--  Module
--    >>current<<
--   MandGroup
--    lldpXMedConfigGroup
--   MandGroup
--    lldpXMedRemSysGroup
--   MandGroup
--    lldpXMedNotificationsGroup
--   OptGroup
--    lldpXMedOptMediaPolicyGroup
--   OptGroup
--    lldpXMedOptInventoryGroup
--   OptGroup
--    lldpXMedOptLocationGroup
--   OptGroup
--    lldpXMedOptPoEPSEGroup
--   OptGroup
--    lldpXMedOptPoEPDGroup


END
