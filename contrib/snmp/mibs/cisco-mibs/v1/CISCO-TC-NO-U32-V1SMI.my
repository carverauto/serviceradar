-- MIB created 11/14/100 16:04:03, by
--   SMIC (the next generation) version 1.6.29, November 22, 1994.

CISCO-TC-NO-U32 DEFINITIONS ::= BEGIN

-- From file: "CISCO-TC-NO-U32.my"

IMPORTS
    Gauge32, Integer32
            FROM SNMPv2-SMI-v1
    ciscoModules, ciscoProducts
            FROM CISCO-SMI;

ciscoTextualConventions OBJECT IDENTIFIER ::= { ciscoModules 1 }
-- MODULE-IDENTITY
--  LastUpdated
--    9810280000Z
--  OrgName
--    Cisco Systems, Inc.
--  ContactInfo
--           Cisco Systems
--     Customer Service
--    
--    Postal: 170 W Tasman Drive
--     San Jose, CA  95134
--     USA
--    
--       Tel: +1 800 553-NETS
--    
--    E-mail: cs-snmp@cisco.com
--  Descr
--    This module defines textual conventions used throughout
--    cisco enterprise mibs.
--  RevDate
--    9703130000Z
--  RevDescr
--    Added CountryCode textual convention.
--  RevDate
--    9703130000Z
--  RevDescr
--    Added SAPType textual convention.
--  RevDate
--    9608140000Z
--  RevDescr
--    Added InterfaceIndexOrZero textual convention.
--  RevDate
--    9607080000Z
--  RevDescr
--    Added new CiscoNetworkProtocol enumerations.
--  RevDate
--    9506070000Z
--  RevDescr
--    Miscellaneous updates/corrections, including making
--    CiscoNetworkProtocol enumerations contiguous.
--  RevDate
--    9810280000Z
--  RevDescr
--    Added Port and IpProtocol textual conventions.

CiscoNetworkProtocol ::= INTEGER {
        ip(1),
        decnet(2),
        pup(3),
        chaos(4),
        xns(5),
        x121(6),
        appletalk(7),
        clns(8),
        lat(9),
        vines(10),
        cons(11),
        apollo(12),
        stun(13),
        novell(14),
        qllc(15),
        snapshot(16),
        atmIlmi(17),
        bstun(18),
        x25pvc(19),
        unknown(65535)
        }
-- TEXTUAL-CONVENTION
--  Status
--    mandatory
--  Descr
--    Represents the different types of network layer protocols.

CiscoNetworkAddress ::= OCTET STRING
-- TEXTUAL-CONVENTION
--  DspHint
--    1x:
--  Status
--    mandatory
--  Descr
--    Represents a network layer address.  The length and format of
--    the address is protocol dependent as follows:
--    ip  4 octets
--    decnet  2 octets
--    pup  obsolete
--    chaos  2 octets
--    xns  10 octets
--      first 4 octets are the net number
--      last 6 octets are the host number
--    x121 
--    appletalk 3 octets
--      first 2 octets are the net number
--      last octet is the host number
--    clns
--    lat
--    vines  6 octets
--      first 4 octets are the net number
--      last 2 octets are the host number
--    cons
--    apollo  10 octets
--      first 4 octets are the net number
--      last 6 octets are the host number
--    stun   8 octets
--    novell  10 octets
--      first 4 octets are the net number
--      last 6 octets are the host number
--    qllc  6 octets
--    bstun  1 octet - bi-sync serial tunnel 
--    snapshot 1 octet
--    atmIlmi  4 octets
--    x25 pvc  2 octets (12 bits)

InterfaceIndexOrZero ::= Integer32(0..2147483647)
-- TEXTUAL-CONVENTION
--  DspHint
--    d
--  Status
--    mandatory
--  Descr
--    Either the value 0, or the ifIndex value of an
--    interface in the ifTable.

SAPType ::= Integer32(0..254)
-- TEXTUAL-CONVENTION
--  DspHint
--    1x:
--  Status
--    mandatory
--  Descr
--    Service Access Point - is a term that denotes the means
--     by which a user entity in layer n+1 accesses a service
--     of a provider entity in layer n.

CountryCode ::= OCTET STRING(SIZE(0 | 2))
-- TEXTUAL-CONVENTION
--  DspHint
--    2a
--  Status
--    mandatory
--  Descr
--    Represents a case-insensitive 2-letter country code taken from
--     ISO-3166. Unrecognized countries are represented as empty string.

EntPhysicalIndexOrZero ::= Integer32(0..2147483647)
-- TEXTUAL-CONVENTION
--  Status
--    mandatory
--  Descr
--    This textual convention is an extension of entPhysicalIndex.
--     If non-zero, the object is an entPhysicalIndex. If zero, no
--     appropriate entPhysicalIndex exists. Any additional semantics
--     are object specific.

CiscoRowOperStatus ::= INTEGER {
        active(1),
        activeDependencies(2),
        inactiveDependency(3),
        missingDependency(4)
        }
-- TEXTUAL-CONVENTION
--  Status
--    mandatory
--  Descr
--    Represents the operational status of an table entry.
--     This textual convention allows explicitly representing
--     the states of rows dependent on rows in other tables.
--    
--         active(1) -
--             Indicates this entry's RowStatus is active
--             and the RowStatus for each dependency is active.
--    
--         activeDependencies(2) -
--             Indicates that the RowStatus for each dependency
--             is active, but the entry's RowStatus is not active.
--    
--         inactiveDependency(3) -
--             Indicates that the RowStatus for at least one
--             dependency is not active.
--    
--         missingDependency(4) -
--             Indicates that at least one dependency does
--             not exist in it's table.

CiscoPort ::= INTEGER(0..65535)
-- TEXTUAL-CONVENTION
--  Status
--    mandatory
--  Descr
--    The TCP or UDP port number range.
--  Refer
--    Transmission Control Protocol. J. Postel. RFC793,
--    User Datagram Protocol. J. Postel. RFC768

CiscoIpProtocol ::= INTEGER(0..255)
-- TEXTUAL-CONVENTION
--  Status
--    mandatory
--  Descr
--    IP protocol number range.
--  Refer
--    Internet Protocol. J. Postel. RFC791


END
