-- MIB file created 17-Nov-2014 14:01:33, by
--   SMICng version 2.2.11-beta(PRO)(Solaris), January 20, 2001. Enterprise key cisco.com

CISCO-DTI-EXT-MIB DEFINITIONS ::= BEGIN

-- From file: "CISCO-DTI-EXT-MIB.my"
-- Compile options "4 7 F H N W 03 06 0B 0G 0N 0T"

IMPORTS
    TruthValue
            FROM SNMPv2-TC-v1
    dtiProtocolServerStatusFlag, dtiProtocolClientStatusFlag
            FROM DTI-MIB
    ciscoMgmt
            FROM CISCO-SMI
    OBJECT-TYPE
            FROM RFC-1212
    TRAP-TYPE
            FROM RFC-1215;

ciscoDtiExtMIB OBJECT IDENTIFIER ::= { ciscoMgmt 822 }
-- MODULE-IDENTITY
--  LastUpdated
--    201408220000Z
--  OrgName
--    Cisco Systems, Inc.
--  ContactInfo
--    Cisco Systems
--    Customer Service
--    
--    Postal: 170 W Tasman Drive
--            San Jose, CA  95134
--            USA
--    
--    Tel: +1 800 553-NETS
--    
--    E-mail: cs-rfgw10@cisco.com
--  Descr
--    This MIB module provides the trap objects necessary to monitor
--    the DOCSIS Timing Interface devices.
--  RevDate
--    201408220000Z
--  RevDescr
--    Latest version of this MIB module.

ciscoDtiExtNotifs OBJECT IDENTIFIER ::= { ciscoDtiExtMIB 0 }
ciscoDtiExtObjects OBJECT IDENTIFIER ::= { ciscoDtiExtMIB 1 }
ciscoDtiExtConform OBJECT IDENTIFIER ::= { ciscoDtiExtMIB 2 }
ciscoDtiExtCompliances OBJECT IDENTIFIER ::= { ciscoDtiExtConform 1 }
ciscoDtiExtGroups OBJECT IDENTIFIER ::= { ciscoDtiExtConform 2 }

cdeServerStatusChangeEnable OBJECT-TYPE
    SYNTAX TruthValue
--    Rsyntax INTEGER {
--        true(1),
--        false(2)
--        }
    ACCESS read-write
    STATUS mandatory
    DESCRIPTION
        "This object specifies whether the system produces
        cdeServerStatusChange notifications. A false 
        value will prevent cdeserverStatusChange
        notifications from being generated by this system."
    DEFVAL { false }
    ::= { ciscoDtiExtObjects 1 }

cdeClientStatusChangeEnable OBJECT-TYPE
    SYNTAX TruthValue
--    Rsyntax INTEGER {
--        true(1),
--        false(2)
--        }
    ACCESS read-write
    STATUS mandatory
    DESCRIPTION
        "This object specifies whether the system produces
        cdeClientStatusChange notifications. A false 
        value will prevent cdeClientStatusChange
        notifications from being generated by this system."
    DEFVAL { false }
    ::= { ciscoDtiExtObjects 2 }

cdeServerStatusChange TRAP-TYPE
-- Reverse mappable trap
    ENTERPRISE ciscoDtiExtMIB
    VARIABLES {
        dtiProtocolServerStatusFlag }
--  Status
--    mandatory
    DESCRIPTION
        "A cdeServerStatusChange notification is sent
        when the DTI Server state changes."
    ::= 1

cdeClientStatusChange TRAP-TYPE
-- Reverse mappable trap
    ENTERPRISE ciscoDtiExtMIB
    VARIABLES {
        dtiProtocolClientStatusFlag }
--  Status
--    mandatory
    DESCRIPTION
        "A cdeClientStatusChange notification is sent
        when the DTI client state changes."
    ::= 2

ciscoDtiExtNotifsControlGroup OBJECT IDENTIFIER ::= { ciscoDtiExtGroups 1 }
-- OBJECT-GROUP
--  Status
--    mandatory
--  Descr
--    Contains the group of objects for determining the status of DTI
--    client and server status.
--  objects
--    cdeServerStatusChangeEnable, cdeClientStatusChangeEnable

ciscoDtiExtNotifsGroup OBJECT IDENTIFIER ::= { ciscoDtiExtGroups 2 }
-- NOTIFICATION-GROUP
--  Status
--    mandatory
--  Descr
--    Contains the group of notification objects for DTI client and
--    server status.
--  notifications
--    cdeServerStatusChange, cdeClientStatusChange

ciscoDtiExtCompliance OBJECT IDENTIFIER ::= { ciscoDtiExtCompliances 1 }
-- MODULE-COMPLIANCE
--  Status
--    mandatory
--  Descr
--    This is a default module-compliance
--    containing default object groups.
--  Module
--    >>current<<
--   MandGroup
--    ciscoDtiExtNotifsControlGroup
--   MandGroup
--    ciscoDtiExtNotifsGroup


END
