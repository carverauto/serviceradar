-- MIB file created 03-May-2010 11:32:15, by
--   SMICng version 2.2.11-beta(PRO)(Solaris), January 20, 2001. Enterprise key cisco.com

CISCO-IMAGE-LICENSE-MGMT-MIB DEFINITIONS ::= BEGIN

-- From file: "CISCO-IMAGE-LICENSE-MGMT-MIB.my"
-- Compile options "4 7 F H N W 03 06 0B 0G 0N 0T"

IMPORTS
    TruthValue
            FROM SNMPv2-TC-v1
    SnmpAdminString
            FROM SNMP-FRAMEWORK-MIB
    entPhysicalIndex
            FROM ENTITY-MIB
    ciscoMgmt
            FROM CISCO-SMI
    Gauge
            FROM RFC1155-SMI
    OBJECT-TYPE
            FROM RFC-1212
    TRAP-TYPE
            FROM RFC-1215;

ciscoImageLicenseMgmtMIB OBJECT IDENTIFIER ::= { ciscoMgmt 640 }
-- MODULE-IDENTITY
--  LastUpdated
--    200710160000Z
--  OrgName
--    Cisco Systems Inc.
--  ContactInfo
--    Cisco Systems
--    Customer Service
--    Postal: 170 W Tasman Drive
--    San Jose, CA  95134
--    USA
--    Tel: +1 800 553 -NETS
--    E-mail: cs-snmp@cisco.com
--  Descr
--    The MIB module for managing the running image level
--    of a Cisco device. Cisco's licensing mechanism provides
--    flexibility to run a device on a chosen image level.
--    This mechanism is referred to as image level licensing.
--    Image level licensing leverages the universal image
--    based licensing solution.
--    
--    The image level licensing mechanism works as follows - 
--    
--    A universal image that contains all levels of software
--    packages is loaded on to the device. At boot time, the
--    device determines the highest level of license and brings
--    up the appropriate software features or subsystems.
--    The user can configure the image level with which the
--    device has to boot. The system will verify whether the
--    appropriate license is available for the configured image
--    level. The image level for the next boot will be determined
--    based on the availability of the license. The following
--    scenarios explains some use-cases of image level licensing:
--    
--    Scenario 1:
--    - Customer selects advsecurityk9 based image.
--    - Manufacturing installs advsecurity license on the device.
--    - This device will run all features that are part of the
--    base advsecurity license.
--    - Customer upgrades to advipservicesk9 license.
--    - The next boot level is set to advipservicesk9.
--    - The device will run advsecurityk9 feature until the
--    next reboot. After reboot the device will run 
--    advipservicesk9 features.
--    
--    Scenario 2:
--    - Customer selects advipservicesk9 based image.
--    - Manufacturing installs advipservices and advsecurity
--    license on the device.
--    - This device will run all features that are part of the
--    base advipservices license.
--    - No upgrades available for advipservices license.
--    
--    The user has to accept the End User License Agreement(EULA)
--    before using this MIB to configure the image level. 
--    
--    This MIB should be used in conjuntion with
--    CISCO-LICENSE-MGMT-MIB module to achieve the image level
--    licensing functionality.
--    
--    This MIB module defines objects which provides the different
--    image levels supported by the device and the license required
--    to enable a particular image level. It also defines objects
--    to let the user configure the required image level. The MIB 
--    module contains notification which will be triggered when
--    the user changes the image level for next boot. 
--    
--    The CISCO-LICENSE-MGMT-MIB module should be used to export
--    the EULA and to configure the required license.
--    
--    This MIB module is defined generically so it can be used for
--    both stand-alone as well as stackable devices. The
--    entPhysicalIndex imported from ENTITY-MIB is used to identify
--    the device uniquely.
--  RevDate
--    200710160000Z
--  RevDescr
--    Initial version of this MIB module.

ciscoImageLicenseMgmtMIBNotifs OBJECT IDENTIFIER ::= { ciscoImageLicenseMgmtMIB 0 }
ciscoImageLicenseMgmtMIBObjects OBJECT IDENTIFIER ::= { ciscoImageLicenseMgmtMIB 1 }
ciscoImageLicenseMgmtMIBConform OBJECT IDENTIFIER ::= { ciscoImageLicenseMgmtMIB 2 }
cilmNotifCntl   OBJECT IDENTIFIER ::= { ciscoImageLicenseMgmtMIBObjects 4 }
cilmModuleCompliances OBJECT IDENTIFIER ::= { ciscoImageLicenseMgmtMIBConform 1 }
cilmModuleGroups OBJECT IDENTIFIER ::= { ciscoImageLicenseMgmtMIBConform 2 }

BootImageLevel ::= OCTET STRING(SIZE(0..255))
-- TEXTUAL-CONVENTION
--  Status
--    mandatory
--  Descr
--    This textual convention is used to define
--    the image level. 
--    
--    If the device is running at advipservices 
--    image level, then the boot image level will
--    be 'advipservices'.

LicenseNameList ::= OCTET STRING(SIZE(0..255))
-- TEXTUAL-CONVENTION
--  Status
--    mandatory
--  Descr
--    This textual convention is used to define
--    the list of license names. If multiple licenses
--    are present then this string will contain all
--    the licenses seperated by the ',' character.
--    
--    If the license required to run a device at
--    advipservices image level is advipservices and
--    advsecurity, then the license name list will be
--    'advipservices,advsecurity'.

cilmBootImageLevelTable OBJECT-TYPE
    SYNTAX SEQUENCE OF CilmBootImageLevelEntry
    ACCESS not-accessible
    STATUS mandatory
    DESCRIPTION
        "A table that contains the configuration information of
        current and next boot image level. This table contains
        entries for each software module running in an image 
        loaded in the device. The software module is identified by
        cilmModuleName and the device is identified by 
        entPhysicalIndex."
    ::= { ciscoImageLicenseMgmtMIBObjects 1 }

cilmBootImageLevelEntry OBJECT-TYPE
    SYNTAX CilmBootImageLevelEntry
    ACCESS not-accessible
    STATUS mandatory
    DESCRIPTION
        "An entry in the table for each module containing the
        list of objects that define the configuration of next
        boot level. The following information is specified by
        the objects present in the table.
        
        - Current image level.
        - Configured image level for the next boot.
        - Actual image level for the next boot.
        - License store index for the current license.
        - License index of the current license.
        - License store index for the next boot license.
        - License index of the next boot license."
    INDEX { entPhysicalIndex, cilmModuleName }
    ::= { cilmBootImageLevelTable 1 }

CilmBootImageLevelEntry ::= SEQUENCE {
    cilmModuleName SnmpAdminString,
    cilmCurrentImageLevel BootImageLevel,
    cilmConfiguredBootImageLevel BootImageLevel,
    cilmNextBootImageLevel BootImageLevel,
    cilmCurrentLicenseStoreIndex Gauge,
    cilmCurrentLicenseIndex Gauge,
    cilmNextBootLicenseStoreIndex Gauge,
    cilmNextBootLicenseIndex Gauge
    }

cilmModuleName OBJECT-TYPE
    SYNTAX SnmpAdminString
--    Rsyntax OCTET STRING(SIZE(0..255))
    ACCESS not-accessible
    STATUS mandatory
    DESCRIPTION
        "This object is used as one of the two indices in
        cilmBootImageLevelTable. This object indicates the module
        name of the software package. There can be multiple
        modules in an image performing specific functionality.
        For example, in a wireless image there can be two modules
        - a base image module and a wireless module."
    ::= { cilmBootImageLevelEntry 1 }

cilmCurrentImageLevel OBJECT-TYPE
    SYNTAX BootImageLevel
--    Rsyntax OCTET STRING(SIZE(0..255))
    ACCESS read-only
    STATUS mandatory
    DESCRIPTION
        "This object indicates the current image level that
        the module is running."
    ::= { cilmBootImageLevelEntry 2 }

cilmConfiguredBootImageLevel OBJECT-TYPE
    SYNTAX BootImageLevel
--    Rsyntax OCTET STRING(SIZE(0..255))
    ACCESS read-write
    STATUS mandatory
    DESCRIPTION
        "This object indicates the configured image level
        of the module for the next boot.
        
        Note: The configured next boot image level may not 
        be the actual next boot image level. The actual next
        boot image level is denoted by cilmNextBootImageLevel
        which is determined based on the license availability."
    ::= { cilmBootImageLevelEntry 3 }

cilmNextBootImageLevel OBJECT-TYPE
    SYNTAX BootImageLevel
--    Rsyntax OCTET STRING(SIZE(0..255))
    ACCESS read-only
    STATUS mandatory
    DESCRIPTION
        "This object indicates the next boot image level. The
        next boot image level can be different from configured
        level. The next boot image level is determined based
        on the availability of required license."
    ::= { cilmBootImageLevelEntry 4 }

cilmCurrentLicenseStoreIndex OBJECT-TYPE
    SYNTAX Gauge
    ACCESS read-only
    STATUS mandatory
    DESCRIPTION
        "This object indicates the license store index where the
        currently used license is stored. This object has the same
        value as clmgmtLicenseStoreIndex object and uniquely
        identifies an entry in clmgmtLicenseStoreInfoTable in
        CISCO-LICENSE-MGMT-MIB.
        
        Note: The license store index can be '0' if no license is
        installed and device is running base image."
    ::= { cilmBootImageLevelEntry 5 }

cilmCurrentLicenseIndex OBJECT-TYPE
    SYNTAX Gauge
    ACCESS read-only
    STATUS mandatory
    DESCRIPTION
        "This object indicates the license index of the currently used
        license. This object has the same value as clmgmtLicenseIndex and
        uniquely identifies an entry in clmgmtLicenseInfoTable in
        CISCO-LICENSE-MGMT-MIB.
        
        Note: The license index can be '0' if no license is
        installed and device is running base image."
    ::= { cilmBootImageLevelEntry 6 }

cilmNextBootLicenseStoreIndex OBJECT-TYPE
    SYNTAX Gauge
    ACCESS read-only
    STATUS mandatory
    DESCRIPTION
        "This object indicates the license store index where the
        next boot license is stored. This object has the same
        value as clmgmtLicenseStoreIndex object and uniquely
        identifies an entry in clmgmtLicenseStoreInfoTable in
        CISCO-LICENSE-MGMT-MIB.
        
        Note: The license store index can be '0' if no license is
        installed for the next boot."
    ::= { cilmBootImageLevelEntry 7 }

cilmNextBootLicenseIndex OBJECT-TYPE
    SYNTAX Gauge
    ACCESS read-only
    STATUS mandatory
    DESCRIPTION
        "This object indicates the license index of the next boot
        license. This object has the same value as clmgmtLicenseIndex
        and uniquely identifies an entry in clmgmtLicenseInfoTable in
        CISCO-LICENSE-MGMT-MIB.
        
        Note: The license index can be '0' if no license is
        installed for the next boot."
    ::= { cilmBootImageLevelEntry 8 }

cilmImageLevelToLicenseMapTable OBJECT-TYPE
    SYNTAX SEQUENCE OF CilmImageLevelToLicenseMapEntry
    ACCESS not-accessible
    STATUS mandatory
    DESCRIPTION
        "This table contains the mapping between different
        image levels of each modules in the image and the
        license required to run the modules at a particular
        image level. This table can be used to identify the
        different image levels and the appropriate licenses 
        required for each."
    ::= { ciscoImageLicenseMgmtMIBObjects 2 }

cilmImageLevelToLicenseMapEntry OBJECT-TYPE
    SYNTAX CilmImageLevelToLicenseMapEntry
    ACCESS not-accessible
    STATUS mandatory
    DESCRIPTION
        "An entry in the table containing the following
        information.
        - The image levels at the which the modules can be run.
        - The license required to the run a module at a
        particular image level.
        - The priority of the license."
    INDEX { entPhysicalIndex, cilmModuleName, cilmImageLicenseMapIndex }
    ::= { cilmImageLevelToLicenseMapTable 1 }

CilmImageLevelToLicenseMapEntry ::= SEQUENCE {
    cilmImageLicenseMapIndex Gauge,
    cilmImageLicenseImageLevel BootImageLevel,
    cilmImageLicenseName LicenseNameList,
    cilmImageLicensePriority Gauge
    }

cilmImageLicenseMapIndex OBJECT-TYPE
    SYNTAX Gauge
    ACCESS not-accessible
    STATUS mandatory
    DESCRIPTION
        "This is a running index used to identify an entry
        of this table."
    ::= { cilmImageLevelToLicenseMapEntry 1 }

cilmImageLicenseImageLevel OBJECT-TYPE
    SYNTAX BootImageLevel
--    Rsyntax OCTET STRING(SIZE(0..255))
    ACCESS read-only
    STATUS mandatory
    DESCRIPTION
        "This object indicates the image level at which
        a module can be run. A module can be run at
        different image levels. An entry will be created
        in this table for every module and image level
        combination."
    ::= { cilmImageLevelToLicenseMapEntry 2 }

cilmImageLicenseName OBJECT-TYPE
    SYNTAX LicenseNameList
--    Rsyntax OCTET STRING(SIZE(0..255))
    ACCESS read-only
    STATUS mandatory
    DESCRIPTION
        "This object indicates the list of licenses needed to
        be installed for the module to run at the image level
        mentioned by cilmImageLicenseImageLevel object of this
        entry."
    ::= { cilmImageLevelToLicenseMapEntry 3 }

cilmImageLicensePriority OBJECT-TYPE
    SYNTAX Gauge(1..255)
    ACCESS read-only
    STATUS mandatory
    DESCRIPTION
        "This object indicates the priority of the image level
        mentioned by cilmImageLicenseImageLevel object of this
        entry. The image level with the highest priority license
        will be considered as the default level in the absense of
        next boot image level configuration. For example if there
        are three licenses l1, l2 and l3 in the ascending order of
        priority, then by default l1 will be the level at which the
        module will be running. If the next boot level is configured
        then the configuration will override the priority. The highest
        priority license supports a feature set which is a super set of
        all other licenses."
    ::= { cilmImageLevelToLicenseMapEntry 4 }

cilmEULAAccepted OBJECT-TYPE
    SYNTAX TruthValue
--    Rsyntax INTEGER {
--        true(1),
--        false(2)
--        }
    ACCESS read-write
    STATUS mandatory
    DESCRIPTION
        "This object when set to TRUE means that the user has
        accepted the END USER LICENSE AGREEMENT. This object
        has to be set to TRUE by the user before using the
        objects in the cilmBootImageLevelTable to configure
        the license."
    DEFVAL { false }
    ::= { ciscoImageLicenseMgmtMIBObjects 3 }

cilmImageLevelChangedNotif OBJECT-TYPE
    SYNTAX TruthValue
--    Rsyntax INTEGER {
--        true(1),
--        false(2)
--        }
    ACCESS read-write
    STATUS mandatory
    DESCRIPTION
        "Specify whether or not a notification should be
        generated on the detection of change in next boot
        image level.
        
        If set to TRUE, cilmBootImageLevelChanged notification
        will be generated. It is the responsibility of the
        management entity to ensure that the SNMP administrative
        model is configured in such a way as to allow the 
        notification to be delivered."
    REFERENCE
        "See also RFC3413 for explanation that notifications
        are under the ultimate control of the MIB module in
        this document."
    DEFVAL { false }
    ::= { cilmNotifCntl 1 }

cilmBootImageLevelChanged TRAP-TYPE
-- Reverse mappable trap
    ENTERPRISE ciscoImageLicenseMgmtMIB
    VARIABLES {
        cilmCurrentImageLevel, cilmConfiguredBootImageLevel }
--  Status
--    mandatory
    DESCRIPTION
        "This notification is triggered when next boot image level
        is changed in the management entity. The current and 
        configured image level are indicated by cilmCurrentImageLevel
        and cilmConfiguredBootImageLevel objects respectively."
    ::= 1

cilmAdminGroup OBJECT IDENTIFIER ::= { cilmModuleGroups 1 }
-- OBJECT-GROUP
--  Status
--    mandatory
--  Descr
--    Objects for performing license set operation for setting
--    next boot level.
--  objects
--    cilmCurrentImageLevel, cilmConfiguredBootImageLevel, 
--    cilmNextBootImageLevel, cilmCurrentLicenseStoreIndex, 
--    cilmCurrentLicenseIndex, cilmNextBootLicenseStoreIndex, 
--    cilmNextBootLicenseIndex, cilmEULAAccepted, 
--    cilmImageLevelChangedNotif

cilmOperGroup OBJECT IDENTIFIER ::= { cilmModuleGroups 2 }
-- OBJECT-GROUP
--  Status
--    mandatory
--  Descr
--    Objects for getting current image level configuration data.
--  objects
--    cilmImageLicenseImageLevel, cilmImageLicenseName, 
--    cilmImageLicensePriority

cilmNotifGroup OBJECT IDENTIFIER ::= { cilmModuleGroups 3 }
-- NOTIFICATION-GROUP
--  Status
--    mandatory
--  Descr
--    Objects for getting current image level configuration data.
--  notifications
--    cilmBootImageLevelChanged

cilmModuleCompliance OBJECT IDENTIFIER ::= { cilmModuleCompliances 1 }
-- MODULE-COMPLIANCE
--  Status
--    mandatory
--  Descr
--    Compliance statement for Cisco Image level license mgmt MIB.
--  Module
--    >>current<<
--   MandGroup
--    cilmAdminGroup
--   MandGroup
--    cilmNotifGroup
--   OptGroup
--    cilmOperGroup


END
