-- MIB created 4/07/98 01:48:41, by
--   SMIC (the next generation) version 1.6.29, November 22, 1994.

CISCO-ATM-DUAL-PHY-MIB DEFINITIONS ::= BEGIN

-- From file: "CISCO-ATM-DUAL-PHY-MIB.my"

IMPORTS
    Counter32
            FROM SNMPv2-SMI-v1
    OBJECT-TYPE
            FROM RFC-1212
    TRAP-TYPE
            FROM RFC-1215
    TruthValue
            FROM SNMPv2-TC-v1
    InterfaceIndexOrZero
            FROM CISCO-TC
    ifIndex, InterfaceIndex
            FROM IF-MIB
    ciscoMgmt
            FROM CISCO-SMI;

ciscoAtmDualPhyMIB OBJECT IDENTIFIER ::= { ciscoMgmt 60 }
-- MODULE-IDENTITY
--  LastUpdated
--    9608300000Z
--  OrgName
--    Cisco Systems, Inc.
--  ContactInfo
--     Cisco Systems
--     Customer Service
--    
--    Postal: 170 W. Tasman Drive
--     San Jose, CA  95134-1706
--     USA
--    
--       Tel: +1 800 553-NETS
--    
--    E-mail: cs-atm@cisco.com
--  Descr
--    Initial version of this MIB module.
--    
--    
--    Phy definition
--    
--    Throughout this document phy is used as an abbreviation
--    for Physical Interface.  In particular it refers to a
--    physical ATM jack on a Catalyst 5000 ATM card.  This card
--    can be fitted with either one or two physical jacks, only
--    one of which may be active at any given moment.  The second
--    phy serves as a redundant connector to the ATM backbone.
--    Note, however, that for logistical reasons, each phy has
--    a separate ifIndex.
--    
--    
--    Support of the phy by ifTable
--    
--    The dual phy entity on the c5K ATM line card is managed
--    using the ifTable.  Specific interpretations of ifTable
--    for the dual phy entity are as follows.
--    
--    Object   Use for dual phy entity
--    ======   =======================
--    
--    ifIndex  Each phy entity is represented by an ifEntry.
--    
--    ifDescr  Description of the phy entity.
--    
--    ifType   The value for the phy entity is other(1).
--    
--    ifSpeed  See [1].
--    
--    ifPhysAddress   An octet string of zero length, per [1].
--    
--    ifAdminStatus   See [1].
--    
--    ifOperStatus    See [1].  In addition, note that a phy can
--                            be in the up state but still not be the
--                            active phy.  However, the active phy will
--                            always be up.
--    
--    ifLastChange    See [1].
--    
--    ifName   See [1].
--    
--    ifLinkUpDownTrapEnable     disabled(2).
--    
--    ifHighSpeed      See [1]. 
--    
--    ifConnectorPresent true(1).
--    
--    
--    References
--    
--    [1] McCloghrie, K. and F. Kastenholz, Evolution of the
--    Interfaces Group of MIB-II, RFC 1573, Hughes LAN Systems,
--    FTP Software, January 1994.

ciscoAtmDualPhyMIBObjects OBJECT IDENTIFIER ::= { ciscoAtmDualPhyMIB 1 }
cadpStatistics  OBJECT IDENTIFIER ::= { ciscoAtmDualPhyMIBObjects 1 }
ciscoAtmDualPhyMIBTrapPrefix OBJECT IDENTIFIER ::= { ciscoAtmDualPhyMIB 2 }
ciscoAtmDualPhyMIBTraps OBJECT IDENTIFIER ::= { ciscoAtmDualPhyMIBTrapPrefix 0 }
ciscoAtmDualPhyMIBConformance OBJECT IDENTIFIER ::= { ciscoAtmDualPhyMIB 3 }
ciscoAtmDualPhyMIBCompliances OBJECT IDENTIFIER ::= { ciscoAtmDualPhyMIBConformance 1 }
ciscoAtmDualPhyMIBGroups OBJECT IDENTIFIER ::= { ciscoAtmDualPhyMIBConformance 2 }

cadpStatTable OBJECT-TYPE
    SYNTAX SEQUENCE OF CadpStatEntry
    ACCESS not-accessible
    STATUS mandatory
    DESCRIPTION
        "A table of status information about ATM phy."
    ::= { cadpStatistics 1 }

cadpStatEntry OBJECT-TYPE
    SYNTAX CadpStatEntry
    ACCESS not-accessible
    STATUS mandatory
    DESCRIPTION
        "An Atm Phy table entry, containing information about
        a phy on this ATM module."
    INDEX { ifIndex }
    ::= { cadpStatTable 1 }

CadpStatEntry ::= SEQUENCE {
    cadpStatLossOfSignal TruthValue,
    cadpStatFarEndReceiveFailure TruthValue,
    cadpStatActive TruthValue,
    cadpStatSectionBIP8Errors Counter32,
    cadpStatLineBIP824Errors Counter32,
    cadpStatLineFEBErrors Counter32,
    cadpStatPathBIP8Errors Counter32,
    cadpStatPathFEBErrors Counter32,
    cadpStatCorrectableHCSErrors Counter32,
    cadpStatUncorrectableHCSErrors Counter32
    }

cadpStatLossOfSignal OBJECT-TYPE
    SYNTAX TruthValue
--    Rsyntax INTEGER {
--        true(1),
--        false(2)
--        }
    ACCESS read-only
    STATUS mandatory
    DESCRIPTION
        "Set to true if the phy is currently experiencing a
        loss of signal (LOS) from its connected port.  Set to false
        if the phy is not experiencing a loss of signal."
    ::= { cadpStatEntry 1 }

cadpStatFarEndReceiveFailure OBJECT-TYPE
    SYNTAX TruthValue
--    Rsyntax INTEGER {
--        true(1),
--        false(2)
--        }
    ACCESS read-only
    STATUS mandatory
    DESCRIPTION
        "Set to true if the phy is currently experiencing a far
        end receive failure (FERF) with its connected port.  Set to
        false if the phy is not experiencing a far end receive
        failure."
    ::= { cadpStatEntry 2 }

cadpStatActive OBJECT-TYPE
    SYNTAX TruthValue
--    Rsyntax INTEGER {
--        true(1),
--        false(2)
--        }
    ACCESS read-only
    STATUS mandatory
    DESCRIPTION
        "Set to true when this phy is currently the active phy.
        Set to false when this phy is not the currently active phy."
    ::= { cadpStatEntry 5 }

cadpStatSectionBIP8Errors OBJECT-TYPE
    SYNTAX Counter32
    ACCESS read-only
    STATUS mandatory
    DESCRIPTION
        "The Bit Interleaved Parity 8 is an error checking code
        applied for quick isolation of faults.  Each bit in the
        B octets is set to 1 or 0 as necessary to obtain even
        parity over the previous frame.  The calculated BIP-8
        code for frame N is compared with the BIP-8 code extracted
        from the B1 byte of frame N+1.  Differences indicate that
        a section level bit error has occurred.
        
        Count of Section BIP-8 (Bit Interleaved Parity) errors
        that have been detected on this phy. "
    ::= { cadpStatEntry 6 }

cadpStatLineBIP824Errors OBJECT-TYPE
    SYNTAX Counter32
    ACCESS read-only
    STATUS mandatory
    DESCRIPTION
        "The Bit Interleaved Parity 8/24 is an error checking code
        based on even parity.  The calculated BIP code for frame N
        is compared with the BIP-8/24 code extracted from the B2
        byte(s) of frame N+1.  Any differences indicate that a
        line layer bit error has occurred.
        
        Count of line bit interleaved partiy (BIP-8/24) errors on
        this phy. "
    ::= { cadpStatEntry 7 }

cadpStatLineFEBErrors OBJECT-TYPE
    SYNTAX Counter32
    ACCESS read-only
    STATUS mandatory
    DESCRIPTION
        "The number of bits (binary 000 to 1000) in the previous
        BIP-8 that didn't match the even parity check are inserted
        by the transmitter.  The receiver checks for this in the 
        M0/M1 byte of the frame.  A non-zero value (legal range 
        is binary 0000 - 1000) indicates a line layer error in 
        the remote end.  Any other value is treated as no error.
        
        Count of Line Far End Bit Errors (FEBE) on this phy."
    ::= { cadpStatEntry 8 }

cadpStatPathBIP8Errors OBJECT-TYPE
    SYNTAX Counter32
    ACCESS read-only
    STATUS mandatory
    DESCRIPTION
        "The Bit Interleaved Parity 8 is an error checking code
        applied for quick isolation of faults.  Each bit in the
        B octets is set to 1 or 0 as necessary to obtain even
        parity over the previous frame.
        
        The calculated BIP-8 code for frame N is compared with
        the BIP-8 code extracted from the B3 byte of frame N+1.
        Differences indicate that a Path level bit error has
        occurred.
        
        Count of Path BIP-8 (Bit Interleaved Parity) errors that
        have been detected on this phy."
    ::= { cadpStatEntry 9 }

cadpStatPathFEBErrors OBJECT-TYPE
    SYNTAX Counter32
    ACCESS read-only
    STATUS mandatory
    DESCRIPTION
        "The number of B3 errors in the previous frame inserted
        by the transmitter.  The receiver checks for this in the
        G1 byte of the frame.  A non-zero value (legal range is
        binary 0000 - 1000) indicates a line layer error in
        the remote end.  Any other value is treated as no error.
        
        Count of Path Far End Bit Errors (FEBE) on this phy."
    ::= { cadpStatEntry 10 }

cadpStatCorrectableHCSErrors OBJECT-TYPE
    SYNTAX Counter32
    ACCESS read-only
    STATUS mandatory
    DESCRIPTION
        "The Header Checksum (HCS) is a CRC-8 calculation over
        the first 4 octets of the ATM cell header.  The received
        HCS is verified using the polynomial x^8 + x^2 + x + 1.
        The coset polynomial x^6 + x^4 + x^2 + 1, is added
        (modulo 2) to the received HCS octet before comparison
        with the calculated result.  Cells with single bit error
        in the HCS byte are corrected.  Cells with more than one
        bit error in the HCS byte are uncorrectable.
        
               Count of incoming cells on this phy with single bit error
               in the Header Checksum (HCS) byte"
    ::= { cadpStatEntry 11 }

cadpStatUncorrectableHCSErrors OBJECT-TYPE
    SYNTAX Counter32
    ACCESS read-only
    STATUS mandatory
    DESCRIPTION
        "The Header Checksum (HCS) is a CRC-8 calculation over
        the first 4 octets of the ATM cell header. The received
        HCS is verified using the polynomial x^8 + x^2 + x + 1.
        The coset polynomial x^6 + x^4 + x^2 + 1, is added
        (modulo 2) to the received HCS octet before comparison
        with the calculated result.  Cells with single bit error
        in the HCS byte are corrected.  Cells with more than one
        bit error in the HCS byte are uncorrectable.
        
        Count of uncorrectable Header Checksum (HCS) errors on
        this phy."
    ::= { cadpStatEntry 12 }

cadpStatOperActivePhy OBJECT-TYPE
    SYNTAX InterfaceIndexOrZero
--    Rsyntax Integer32(0..2147483647)
    ACCESS read-only
    STATUS mandatory
    DESCRIPTION
        "Returns the ifIndex of the phy which is currently the
        active phy.  A value of 0 indicates that no phy is
        currently active."
    ::= { cadpStatistics 2 }

cadpStatAdminActivePhy OBJECT-TYPE
    SYNTAX InterfaceIndex
--    Rsyntax Integer32
    ACCESS read-write
    STATUS mandatory
    DESCRIPTION
        "Returns the ifIndex of the phy which is the preferred
        active phy.  A value of 0 indicates that no phy is
        currently active.
        
        Setting this object to a value different from its current
        value causes the ATM module to make the indicated phy active,
        and the active phy inactive.
        
        Setting this object to its current value has no effect.
        
        After performing the phy change, the agent will update
        all phy information (including cadpStatOperActivePhy)
        and send a ciscoAtmDualPhyChange trap."
    ::= { cadpStatistics 3 }

ciscoAtmDualPhyChange TRAP-TYPE
-- Reverse mappable trap
    ENTERPRISE ciscoAtmDualPhyMIBTrapPrefix
    VARIABLES {
        cadpStatOperActivePhy }
--  Status
--    mandatory
    DESCRIPTION
        "A ciscoAtmDualPhyChange trap is sent when the active phy
        changes either because of a failure or because of user
        intervention (setting cadpStatAdminActivePhy, for example)."
    ::= 1

ciscoAtmDualPhyMIBGroup OBJECT IDENTIFIER ::= { ciscoAtmDualPhyMIBGroups 1 }
-- OBJECT-GROUP
--  Status
--    mandatory
--  Descr
--    A collection of objects providing ATM dual phy monitoring.
--  objects
--    cadpStatLossOfSignal, cadpStatFarEndReceiveFailure, 
--    cadpStatActive, cadpStatSectionBIP8Errors, 
--    cadpStatLineBIP824Errors, cadpStatLineFEBErrors, 
--    cadpStatPathBIP8Errors, cadpStatPathFEBErrors, 
--    cadpStatCorrectableHCSErrors, cadpStatUncorrectableHCSErrors, 
--    cadpStatAdminActivePhy, cadpStatOperActivePhy

ciscoAtmDualPhyMIBCompliance OBJECT IDENTIFIER ::= { ciscoAtmDualPhyMIBCompliances 1 }
-- MODULE-COMPLIANCE
--  Status
--    mandatory
--  Descr
--    The compliance statement for entities which implement
--    the Cisco Atm Dual Phy MIB.  This MIB is mandatory for
--    all Cisco ATM products with multiple phy.
--  Module
--    >>current<<
--   MandGroup
--    ciscoAtmDualPhyMIBGroup


END
