-- MIB file created 24-Nov-2004 15:51:55, by
--   SMICng version 2.2.11-beta(PRO)(Solaris), January 20, 2001. Enterprise key cisco.com

CISCO-VISM-ATM-TRUNK-MIB DEFINITIONS ::= BEGIN

-- From file: "CISCO-VISM-ATM-TRUNK-MIB.my"
-- Compile options "4 7 F H N O W 03 06 0B 0G 0N 0T"

IMPORTS
    TruthValue
            FROM SNMPv2-TC-v1
    voice, vismChanGrp
            FROM BASIS-MIB
    ciscoWan
            FROM CISCOWAN-SMI
    Counter, Gauge
            FROM RFC1155-SMI
    OBJECT-TYPE
            FROM RFC-1212;

ciscoVismAtmTrunkMIB OBJECT IDENTIFIER ::= { ciscoWan 87 }
-- MODULE-IDENTITY
--  LastUpdated
--    200404140000Z
--  OrgName
--    Cisco Systems, Inc.
--  ContactInfo
--           Cisco Systems
--            Customer Service
--    
--        Postal: 170 W Tasman Drive
--                San Jose, CA  95134
--                USA
--    
--                Tel: +1 800 553-NETS
--    
--        E-mail: cs-wanatm@cisco.com
--  Descr
--    The MIB module contain the Bearer and 
--     CID (Channel Identifier) connection information.
--  RevDate
--    200404140000Z
--  RevDescr
--    Added 
--        - bearerPeakXmtCellRate
--        - bearerCurrentXmtCellRate
--        - bearerPeakRcvCellRate
--        - bearerCurrentRcvCellRate
--        - bearerCurrentExtAISRcvCnts
--        - bearerCurrentExtRAIRcvCnts
--        - bearerCurrentConnAISCnts
--        - bearerCurrentConnRDICnts
--        - bearerCurrentExtAISXmtCnts
--        - bearerCurrentExtRAIXmtCnts
--     Statistics for bearer cell rates 
--     and alarm counts.
--  RevDate
--    200402050000Z
--  RevDescr
--    Added 
--        - vismAal2CidAdminState
--  RevDate
--    200312090000Z
--  RevDescr
--    Initial version of the MIB.
--    
--    The content of this MIB was originally available
--    in SMIv1 version. The MIB has been converted to
--    SMIv2 version and descriptions of some of the objects
--    have been modified.

bearerConnGrp   OBJECT IDENTIFIER ::= { voice 9 }
vismAal2CidGrp  OBJECT IDENTIFIER ::= { vismChanGrp 4 }
cvismAtmTrunkMIBConformance OBJECT IDENTIFIER ::= { ciscoVismAtmTrunkMIB 2 }
cvismAtmTrunkMIBGroups OBJECT IDENTIFIER ::= { cvismAtmTrunkMIBConformance 1 }
cvismAtmTrunkMIBCompliances OBJECT IDENTIFIER ::= { cvismAtmTrunkMIBConformance 2 }

bearerConnTable OBJECT-TYPE
    SYNTAX SEQUENCE OF BearerConnEntry
    ACCESS not-accessible
    STATUS mandatory
    DESCRIPTION
        "This table describes the statistical information
         available on a per-bearer connection basis.
         These values are applicable equally to an endpoint."
    ::= { bearerConnGrp 1 }

bearerConnEntry OBJECT-TYPE
    SYNTAX BearerConnEntry
    ACCESS not-accessible
    STATUS mandatory
    DESCRIPTION
        " Each entry in this table corresponds to a bearer 
          connection, that was setup by binding an endpoint with a 
          VC(Virtual channel)/CID pair, either through CLI or SNMP.
          The statistical counters in this table are generic voice 
          quality parameters that are equally applicable in all 
          types of Voice Over Packet adapations (VoIP, VoAAL1 and 
          VoAAL2). However, they are maintained only in the 
          PVC(Permanent virtual circuit) trunking model because, 
          these counters get reset in the switching model on a 
          per call basis.
          The entries in this table are implicitly created/deleted 
          at the time of creation/deletion of entries in the 
          vismAal2CidCnfTable."
    INDEX { bearerEndptNum }
    ::= { bearerConnTable 1 }

BearerConnEntry ::= SEQUENCE {
    bearerEndptNum INTEGER,
    bearerCid INTEGER,
    bearerLcn INTEGER,
    bearerSentPkts Counter,
    bearerRcvdPkts Counter,
    bearerSentOctets Counter,
    bearerRcvdOctets Counter,
    bearerLostPkts Counter,
    bearerJitter INTEGER,
    bearerLatency INTEGER,
    bearerAal2ExtAISCnts Counter,
    bearerAal2ExtRAICnts Counter,
    bearerAal2ConnAISCnts Counter,
    bearerAal2ConnRDICnts Counter,
    bearerCntClrButton INTEGER,
    bearerPeakXmtCellRate Gauge,
    bearerCurrentXmtCellRate Gauge,
    bearerPeakRcvCellRate Gauge,
    bearerCurrentRcvCellRate Gauge,
    bearerCurrentExtAISRcvCnts Counter,
    bearerCurrentExtRAIRcvCnts Counter,
    bearerCurrentConnAISCnts Counter,
    bearerCurrentConnRDICnts Counter,
    bearerCurrentExtAISXmtCnts Counter,
    bearerCurrentExtRAIXmtCnts Counter
    }

bearerEndptNum OBJECT-TYPE
    SYNTAX INTEGER(1..65535)
    ACCESS read-only
    STATUS mandatory
    DESCRIPTION
        "This attribute defines the index for the Bearer 
         Connection Table. This refers to the same value 
         as the index to the mgEndpointTable ie. mgEndpointNumber.
         This is define in CISCO-WAN-MG-MIB MIB."
    ::= { bearerConnEntry 1 }

bearerCid OBJECT-TYPE
    SYNTAX INTEGER
    ACCESS read-only
    STATUS mandatory
    DESCRIPTION
        "This attribute defines the CID associated with this 
         bearer connection. This refers to the same value as 
         vismAal2CidNum in the vismAal2CidCnfTable."
    ::= { bearerConnEntry 2 }

bearerLcn OBJECT-TYPE
    SYNTAX INTEGER(131..510)
    ACCESS read-only
    STATUS mandatory
    DESCRIPTION
        "This attribute defines the PVC or LCN(Logical Channel Number)
         number to which this bearer connection is associated with.
         This refers to the same value as in vismCnfChanNum in 
         vismChanCnfGrp table. This is define in CISCO-VISM-CONN-MIB 
         MIB."
    ::= { bearerConnEntry 3 }

bearerSentPkts OBJECT-TYPE
    SYNTAX Counter
    ACCESS read-only
    STATUS mandatory
    DESCRIPTION
        "This attribute defines the count of packets sent towards the
         network since this connection setup. "
    ::= { bearerConnEntry 4 }

bearerRcvdPkts OBJECT-TYPE
    SYNTAX Counter
    ACCESS read-only
    STATUS mandatory
    DESCRIPTION
        "This attribute defines the count of packets received from the
         network since this connection setup."
    ::= { bearerConnEntry 5 }

bearerSentOctets OBJECT-TYPE
    SYNTAX Counter
    ACCESS read-only
    STATUS mandatory
    DESCRIPTION
        "This attribute defines the count of bytes sent towards the
         network since this connection setup."
    ::= { bearerConnEntry 6 }

bearerRcvdOctets OBJECT-TYPE
    SYNTAX Counter
    ACCESS read-only
    STATUS mandatory
    DESCRIPTION
        "This attribute defines the count of bytes received from the
         network since this connection setup."
    ::= { bearerConnEntry 7 }

bearerLostPkts OBJECT-TYPE
    SYNTAX Counter
    ACCESS read-only
    STATUS mandatory
    DESCRIPTION
        "This attribute defines the count of packets lost in the
         egress direction (from the network). This is a computed
         number based on the expected number of packets and the
         actual number of packets arrived from the network."
    ::= { bearerConnEntry 8 }

bearerJitter OBJECT-TYPE
    SYNTAX INTEGER
--  Units
--    milliseconds
    ACCESS read-only
    STATUS mandatory
    DESCRIPTION
        "This attribute defines the jitter (a.k.a interarrival jitter) 
        This value is determined by the DSP(Digital Signal
         Processing) and obtained by the HOST processor
        upon querying the DSP on a periodic basis. "
    ::= { bearerConnEntry 9 }

bearerLatency OBJECT-TYPE
    SYNTAX INTEGER
--  Units
--    milliseconds
    ACCESS read-only
    STATUS mandatory
    DESCRIPTION
        "This attribute defines the latency (a.k.a end-to-end average
        transmission delay for a voice packet)."
    ::= { bearerConnEntry 10 }

bearerAal2ExtAISCnts OBJECT-TYPE
    SYNTAX Counter
    ACCESS read-only
    STATUS mandatory
    DESCRIPTION
        " This object contains the number of external AIS
          (Alarm Indication Signal) AAL2 Type3 packets received. 
        
          External AIS - is associated with a maintenance alarm 
          detected on a defective maintenance span, that is 
          transmitted in the direction of the defect as a substitute
          for normal signal. The purpose is to show the downstream 
          entities that a defect has been identified and to prevent
          other maintenance alrams consequent to this first defect.
        
          External AIS bit stream is represented by an all 1's 
          signal."
    REFERENCE
        "ITU-T Rec. M.20 sec. 5.4.2 a"
    ::= { bearerConnEntry 11 }

bearerAal2ExtRAICnts OBJECT-TYPE
    SYNTAX Counter
    ACCESS read-only
    STATUS mandatory
    DESCRIPTION
        "This object contains the number of external RAI
         (Remote Alarm Indication) AAL2 Type3 packets received. 
        
         External RAI - is a signal that is transmitted
         upstream from an entity that has detected defects 
         persisting long enough to constitute a received 
         signal failure. Its purpose is to report in the backward
         direction that there is an interruption of service in the
         forward direction."
    REFERENCE
        "ITU-T Rec. G.704 section 2.1.3.1.3"
    ::= { bearerConnEntry 12 }

bearerAal2ConnAISCnts OBJECT-TYPE
    SYNTAX Counter
    ACCESS read-only
    STATUS mandatory
    DESCRIPTION
        "This object contains the number of external Conn 
         AIS AAL2 Type2 packets received. 
        
         External Conn AIS - is transmitted in the downstream 
         direction from the AAL Type 2 connecting point that first 
         detects a defect affecting the AAL Type 2 connection; 
         this includes defects indicated by lower layers."
    REFERENCE
        "ITU-T Rec. I.610 sec 6.2.2.1.1.1"
    ::= { bearerConnEntry 13 }

bearerAal2ConnRDICnts OBJECT-TYPE
    SYNTAX Counter
    ACCESS read-only
    STATUS mandatory
    DESCRIPTION
        " This object contains the number of external Conn 
          RDI(Remote Defect Indication) AAL2 Type2 packets
          received. 
        
          External Conn RDI -  is a signal transmitted upstream 
          by an AAL Type 2 endpoint that is in an alarm state as
          the result of having received an AAL Type2 connection 
          AIS or having detected a defect that affects
          the AAL Type2 connection."
    ::= { bearerConnEntry 14 }

bearerCntClrButton OBJECT-TYPE
    SYNTAX INTEGER {
        noaction(1),
        clear(2)
        }
    ACCESS read-write
    STATUS mandatory
    DESCRIPTION
        " This object is used to clear bearerSentPkts, bearerRcvdPkts,
          bearerSentOctets, and bearerRcvdOctets."
    ::= { bearerConnEntry 15 }

bearerPeakXmtCellRate OBJECT-TYPE
    SYNTAX Gauge(1..2147483647)
--  Units
--    cells-per-second
    ACCESS read-only
    STATUS mandatory
    DESCRIPTION
        "Peak transmit ATM cell rate is the ATM cells 
         required to transmit peak AAL2 packets on a 
         CID per second since midnight as per system time; 
         the peak cell rate gets cleared every 24 hours 
         at midnight as per system time."
    ::= { bearerConnEntry 16 }

bearerCurrentXmtCellRate OBJECT-TYPE
    SYNTAX Gauge(1..2147483647)
--  Units
--    cells-per-second
    ACCESS read-only
    STATUS mandatory
    DESCRIPTION
        "Current transmit ATM cell rate is the ATM cells 
         required to transmit current AAL2 packets on a 
         CID per second."
    ::= { bearerConnEntry 17 }

bearerPeakRcvCellRate OBJECT-TYPE
    SYNTAX Gauge(1..2147483647)
--  Units
--    cells-per-second
    ACCESS read-only
    STATUS mandatory
    DESCRIPTION
        "Peak receive ATM cell rate is the ATM cells 
         required to receive peak AAL2 packets on a 
         CID per second since midnight as per system time; 
         the peak cell rate gets cleared every 24 hours 
         at midnight as per system time."
    ::= { bearerConnEntry 18 }

bearerCurrentRcvCellRate OBJECT-TYPE
    SYNTAX Gauge(1..2147483647)
--  Units
--    cells-per-second
    ACCESS read-only
    STATUS mandatory
    DESCRIPTION
        "Current receive ATM cell rate is the ATM cells 
         required to receive current AAL2 packets on a 
         CID per second."
    ::= { bearerConnEntry 19 }

bearerCurrentExtAISRcvCnts OBJECT-TYPE
    SYNTAX Counter
    ACCESS read-only
    STATUS mandatory
    DESCRIPTION
        "This object contains the count of external
         AIS AAL2 (Type 2) received on this
         bearerEndptNum since its creation."
    ::= { bearerConnEntry 20 }

bearerCurrentExtRAIRcvCnts OBJECT-TYPE
    SYNTAX Counter
    ACCESS read-only
    STATUS mandatory
    DESCRIPTION
        "This object contains the number of external
         RAI AAL2 (Type 2) received in this bearerEndptNum
         since its creation."
    ::= { bearerConnEntry 21 }

bearerCurrentConnAISCnts OBJECT-TYPE
    SYNTAX Counter
    ACCESS read-only
    STATUS mandatory
    DESCRIPTION
        "This object contains count of external Connection
         AIS AAL2 (Type 2) received in this bearerEndptNum
         since its creation."
    ::= { bearerConnEntry 22 }

bearerCurrentConnRDICnts OBJECT-TYPE
    SYNTAX Counter
    ACCESS read-only
    STATUS mandatory
    DESCRIPTION
        "This object contains the count of external Connection
         RDI (Remote Defect Indication) AAL2 (Type 2) received 
         in this bearerEndptNum since its creation."
    ::= { bearerConnEntry 23 }

bearerCurrentExtAISXmtCnts OBJECT-TYPE
    SYNTAX Counter
    ACCESS read-only
    STATUS mandatory
    DESCRIPTION
        "This object contains the count of external AIS
         AAL2 (Type 2) transmitted in this bearerEndptNum
         since its creation."
    ::= { bearerConnEntry 24 }

bearerCurrentExtRAIXmtCnts OBJECT-TYPE
    SYNTAX Counter
    ACCESS read-only
    STATUS mandatory
    DESCRIPTION
        "This object contains the count of external
         RAI AAL2 (Type 2) transmitted in this bearerEndptNum
         since its creation."
    ::= { bearerConnEntry 25 }

vismAal2CidCnfTable OBJECT-TYPE
    SYNTAX SEQUENCE OF VismAal2CidEntry
    ACCESS not-accessible
    STATUS mandatory
    DESCRIPTION
        "This table is defined to establish the binding between an
         endpoint and a PVC/CID pair in the case of AAL2 adaptation.
         This table is created and used in trunking mode VISM
         application only. 
        
         The maximum number of CIDs that can be configured depends
         on the current codec template being used as represented by
         vismAppliedTemplate object. The signaling type of the
         line has to be configured before adding any CID on that
         line."
    ::= { vismAal2CidGrp 1 }

vismAal2CidEntry OBJECT-TYPE
    SYNTAX VismAal2CidEntry
    ACCESS not-accessible
    STATUS mandatory
    DESCRIPTION
        "Identifies an entry for vismAal2CidCnfTable."
    INDEX { vismAal2CidLcn, vismAal2CidNum }
    ::= { vismAal2CidCnfTable 1 }

VismAal2CidEntry ::= SEQUENCE {
    vismAal2CidNum INTEGER,
    vismAal2CidLcn INTEGER,
    vismAal2EndptNum INTEGER,
    vismAal2CidRowStatus INTEGER,
    vismAal2CidType3Redundancy TruthValue,
    vismAal2CidVad TruthValue,
    vismAal2CidProfileType INTEGER,
    vismAal2CidProfileNum INTEGER,
    vismAal2CidCodecType INTEGER,
    vismAal2CidDtmfTransport TruthValue,
    vismAal2CidCasTransport TruthValue,
    vismAal2CidEcanEnable TruthValue,
    vismAal2InitVadTimer INTEGER,
    vismAal2CnfPktPeriod INTEGER,
    vismAal2CidICSEnable TruthValue,
    vismAal2CidState INTEGER,
    vismAal2CidFailReason INTEGER,
    vismAal2CidAdminState INTEGER
    }

vismAal2CidNum OBJECT-TYPE
    SYNTAX INTEGER(8..255)
    ACCESS read-only
    STATUS mandatory
    DESCRIPTION
        "This attribute defines part of the index for this table. 
         vismAal2CidNum is the CID of a voice channel. CID has to be
         the same at both endpoints for a connection. CID is 
         unique only within the context of a Virtual 
         Circuit (PVC or SVC)."
    ::= { vismAal2CidEntry 1 }

vismAal2CidLcn OBJECT-TYPE
    SYNTAX INTEGER(131..510)
    ACCESS read-only
    STATUS mandatory
    DESCRIPTION
        "This attribute defines part of the index for the 
         vismAal2CidCnfTable. Since CID is unique to a PVC, 
         a combination of LCN and CID uniquely identifies 
         a voice connection. This field refers to 
         vismCnfChanNum defined in vismChanCnfGrp of
         CISCO-VISM-CONN-MIB MIB."
    ::= { vismAal2CidEntry 2 }

vismAal2EndptNum OBJECT-TYPE
    SYNTAX INTEGER(1..65535)
    ACCESS read-write
    STATUS mandatory
    DESCRIPTION
        "This attribute defines the endpoint number to which this
         CID is associated. It is the same as mgEndpointNumber 
         defined in mgEndpointTable of CISCO-WAN-MG-MIB MIB. "
    ::= { vismAal2CidEntry 3 }

vismAal2CidRowStatus OBJECT-TYPE
    SYNTAX INTEGER {
        active(1),
        createAndGo(4),
        destroy(6)
        }
    ACCESS read-write
    STATUS mandatory
    DESCRIPTION
        "This variable allows to add or delete a CID.  A CID can
         only be added or deleted. Once added, modifying an
         entry is not allowed.
         'createAndGo': Use this to add an entry in this table.
         'active': This values is returned, once the row is created.
         'destroy': Use this to delete an entry from this table."
    ::= { vismAal2CidEntry 4 }

vismAal2CidType3Redundancy OBJECT-TYPE
    SYNTAX TruthValue
--    Rsyntax INTEGER {
--        true(1),
--        false(2)
--        }
    ACCESS read-write
    STATUS mandatory
    DESCRIPTION
        "This attribute defines whether the triple redundancy is
         supported for type 3 packets in AAL2 for this channel.
         When Triple redundancy is enabled for a channel, the
         Type 3 packets (CAS bits, dialled digits and user state
         control packets) are transmitted in triplicates with an
         interval defined as per the standards I.366.2. For
         channels which are quite reliable, triple redundancy
         can be disabled in order to save the bandwidth and the
         processing overheads. 
        
         The default value of this object is 'true(1)' if either
         vismAal2CidCasTransport or vismAal2CidDtmfTransport is
         'true(1)', otherwise the default value is 'false(2)'."
    ::= { vismAal2CidEntry 5 }

vismAal2CidVad OBJECT-TYPE
    SYNTAX TruthValue
--    Rsyntax INTEGER {
--        true(1),
--        false(2)
--        }
    ACCESS read-write
    STATUS mandatory
    DESCRIPTION
        "This attribute defines whether the VAD (Voice Activity 
         Detection) has to be applied on this channel, upon
         detection of silence. For algorithms that do not
         have VAD standards, Cisco-proprietary VAD can be 
         applied and the generic SID(Silence Information
         Descriptor) packet as specified in I.366.2 standards
         can be sent to the other end. 
        
         When the codec specify in vismAal2CidCodecType is
         'clearChannel' VAD has to be off."
    DEFVAL { false }
    ::= { vismAal2CidEntry 6 }

vismAal2CidProfileType OBJECT-TYPE
    SYNTAX INTEGER {
        itu(1),
        atm(2),
        custom(3),
        none(4)
        }
    ACCESS read-write
    STATUS mandatory
    DESCRIPTION
        "This attribute defines the profile type. The profile
         type defines which group of the profile tables the
         profile number should correspond to. There are three
         possible groups:
         'itu' - corresponding to the tables in ITU 
         format in the profile is being used.
         'atm' - This is not supported
         'custom' - VISM specific custom profiles."
    DEFVAL { custom }
    ::= { vismAal2CidEntry 7 }

vismAal2CidProfileNum OBJECT-TYPE
    SYNTAX INTEGER(0..2147483647)
    ACCESS read-write
    STATUS mandatory
    DESCRIPTION
        "This attribute defines the profile number. A profile
         is a set of entries, where each entry specifies an
         encoding format with a UUI(User-to-User Indication)
         range and length. This set defines a mapping that
         informs the receiver of a Type 1 packet how to
         interpret the packet contents, i.e. which encoding
         format in the profile is being used."
    DEFVAL { 100 }
    ::= { vismAal2CidEntry 8 }

vismAal2CidCodecType OBJECT-TYPE
    SYNTAX INTEGER {
        g711u(1),
        g711a(2),
        g726r32000(3),
        g729a(4),
        g729ab(5),
        clearChannel(6),
        g726r16000(7),
        g726r24000(8),
        g726r40000(9),
        g723h(11),
        g723ah(12),
        g723l(13),
        g723al(14),
        lossless(15)
        }
    ACCESS read-write
    STATUS mandatory
    DESCRIPTION
        "This attribute defines the codec Type used for the
         connection. 
        
        'g711u'        represents PCMU with 64 kbps.
        'g711a'        represents PCMA with 64 kbps.
        'g726r32000'   represents G.726 at rate 32 kbps
        'g726r16000'   represents G.726 at rate 16 kbps
        'g726r24000'   represents G.726 at rate 24 kbps
        'g726r40000'   represents G.726 at rate 40 kbps
        'g729a'        represents G.729 Annex A algorithm.
        'g729ab'       represents G.729 Annex A and Annex B algorithm.
        'clearChannel' represents CCD with 64 kbps.
        'g723h'        represents G.723.1-H at rate 6.3kbps.
        'g723ah'       represents G.723.1-H at rate 6.3kbps
                       with Silence Supression ON.
        'g723l'        represents G.723.1-L at rate 5.3kbps.
        'g723al'       represents G.723.1-L at rate 5.3kbps
                       with Silence Supression ON.
        'lossless'     represents Lossless
        
        Note : 
          1. When codec type is 'clearChannel', vismAal2CidProfileType
               and vismAal2CidProfileNum are not applicable and
               will be ignored.
        
          2. Value 10 is RESERVED. "
    ::= { vismAal2CidEntry 9 }

vismAal2CidDtmfTransport OBJECT-TYPE
    SYNTAX TruthValue
--    Rsyntax INTEGER {
--        true(1),
--        false(2)
--        }
    ACCESS read-write
    STATUS mandatory
    DESCRIPTION
        "This attribute defines whether the DTMF (Dual Tone Multi
         Frequency) digits need to be transported to the other
         end-point. "
    DEFVAL { true }
    ::= { vismAal2CidEntry 10 }

vismAal2CidCasTransport OBJECT-TYPE
    SYNTAX TruthValue
--    Rsyntax INTEGER {
--        true(1),
--        false(2)
--        }
    ACCESS read-write
    STATUS mandatory
    DESCRIPTION
        "This attribute defines whether the CAS(Channel 
        Associated Signaling) bits need to be transported 
        to the other endpoint. In the case of switching 
        application, the CAS bits are backhauled to the call agent 
        through xGCP(Gateway Control Protocol)-CAS protocol.
        
        Note that if the line signaling type is CAS the 
        default value is 'true(1)', else the default value
        is 'false(2)'."
    ::= { vismAal2CidEntry 11 }

vismAal2CidEcanEnable OBJECT-TYPE
    SYNTAX TruthValue
--    Rsyntax INTEGER {
--        true(1),
--        false(2)
--        }
    ACCESS read-write
    STATUS mandatory
    DESCRIPTION
        "This attribute defines whether Echo Cancellation has to
         be enabled on this connection. If it is set to 'true(1)',
         echo cancellation is enabled. If it is set to 'false(2)',
         echo cancellation is disabled."
    DEFVAL { true }
    ::= { vismAal2CidEntry 12 }

vismAal2InitVadTimer OBJECT-TYPE
    SYNTAX INTEGER(250..65535)
--  Units
--    milliseconds
    ACCESS read-write
    STATUS mandatory
    DESCRIPTION
        "This attribute defines the hangover time for VAD.
         Once the voice inactivity is detected, the gateway
         will wait for this duration before activating 
         silence suppression."
    DEFVAL { 250 }
    ::= { vismAal2CidEntry 13 }

vismAal2CnfPktPeriod OBJECT-TYPE
    SYNTAX INTEGER {
        five(5),
        ten(10),
        twenty(20),
        thirty(30),
        fourty(40)
        }
    ACCESS read-write
    STATUS mandatory
    DESCRIPTION
        " This object is used to configure the packetization
         period for a given codec. This packetization  period 
         has to be a valid entry in the profile table. Profile 
         type and number identify a unique profile table and one codec
         type in this table might have one or more packetization 
         period. This is applicable only if the vismAal2CidCodecType
         is 'g729a'. 
        
         The configurable values for 'g729a' are 10,20,30 & 40. 
         If a CID entry is configured with a codec other than 
         'g729a' then the user cannot configure the pkt period 
         for that codec and the pkt period is picked from the 
         profile table. 
        
         Hence when we do get/walk on this entry/table any one of
         the above values could be returned."
    REFERENCE
        "ITU specification I.366.2 annex P."
    DEFVAL { ten }
    ::= { vismAal2CidEntry 14 }

vismAal2CidICSEnable OBJECT-TYPE
    SYNTAX TruthValue
--    Rsyntax INTEGER {
--        true(1),
--        false(2)
--        }
    ACCESS read-write
    STATUS mandatory
    DESCRIPTION
        " This object is used to enable or disable the ICS(Idle 
          Channel Suppression) for a CID. This can be specified 
          while adding the CID and cannot be modified.
        
          When the Idle Channel Suppression is enabled the DSP
          will look for the idle CAS (ABCD bits) pattern specified 
          in ds0IdleCode in CISCO-VISM-DSX0-MIB MIB. If the 
          idle pattern is present the DSP stops generating voice 
          packets towards ATM side. By default the ds0IdleCode
          will be zero unless the user has configured it before 
          adding the CID. If the ds0IdleCode is changed after the
          CID is added it will have no affect unless the card is reset.
        
          ICS is applicable only for trunking application, in
          case of switching there is no need for ICS as the
          calls are teared down and set up dynamically."
    DEFVAL { false }
    ::= { vismAal2CidEntry 15 }

vismAal2CidState OBJECT-TYPE
    SYNTAX INTEGER {
        cidStateActive(1),
        cidStateFailed(2)
        }
    ACCESS read-only
    STATUS mandatory
    DESCRIPTION
        "Indicates the state of the CID.
         'cidStateActive' : The CID is in service and operational.
         'cidStateFailed' : The CID is in service but not
                            operational, e.g. because the PVC
                            that the CID belongs to is receiving
                            F5(Operation, Administration and
                            Maintenance Flow) level alarm.
        
         When VISM sees alarm on a CID (network side) sets
         this object to 'cidStateFailed', and an AIS will
         be sent on the ds0(Time Division Multiplexed
         voice channel) that this CID corresponds to. 
        
         If the whole PVC is in alarm then all the CIDs 
         on that PVC will be set to 'cidStateFailed', 
         trapVismChanFailed trap will be sent and all 
         the ds0's that corresponds to each of the CIDs
         on this PVC will be in alarm. 
        
         If VISM sees an alarm on a ds0 in a line then 
         an RAI(Remote Alarm Indication) will be sent
         on the CID that corresponds to this ds0, however
         the CID will not be put in failed state."
    ::= { vismAal2CidEntry 16 }

vismAal2CidFailReason OBJECT-TYPE
    SYNTAX INTEGER {
        self(1),
        highLevel(2),
        both(3),
        notFail(4)
        }
    ACCESS read-only
    STATUS mandatory
    DESCRIPTION
        "This object is used to indicate the CID failure
         reason.
         'self': fail because of non-PVC alarm
         'highLevel': fail because of PVC alarm
         'both': fail because of both PVC and non-PVC alarm
         'notFail': not fail"
    DEFVAL { notFail }
    ::= { vismAal2CidEntry 17 }

vismAal2CidAdminState OBJECT-TYPE
    SYNTAX INTEGER {
        cidPendingInService(1),
        cidInService(2),
        cidCommandedOutOfService(3),
        cidPendingOutOfService(4),
        cidUnknownState(5)
        }
    ACCESS read-write
    STATUS mandatory
    DESCRIPTION
        "This attribute defines the operational administrative 
         state of the bearer connection. 
        
         cidInService: This is an operational state of the bearer 
                       connection where it is ready to 
                       transmit/receive data/voice packets. 
                       The user can take the bearer connection 
                       into cidInService.
         cidCommandedOutOfService: This is an operational state of 
                       the bearer connection where it is not ready 
                       to transmit/receive data/voice packets.
                       The user can take the bearer connection 
                       into cidPendingOutOfService.
         cidPendingInService: It is a transient state. In this state 
                       the bearer connection is waiting for the user
                       to transition it to the cidInService state.
                       This value cannot be specified in a management
                       protocol set operation.
         cidPendingOutOfService: It is a transient state. In this 
                       state the bearer connection is waiting for the 
                       user to transition it to the cidOutOfService 
                       state. This value cannot be specified in a 
                       management protocol set operation.
         cidUnknownState: This is an abnormal state of the bearer 
                       connection. This state would indicate to the 
                       user that there is some data integrity issue
                       on the bearer administrative state.
         "
    DEFVAL { cidPendingInService }
    ::= { vismAal2CidEntry 18 }

ciscoVismBearerConnGroup OBJECT IDENTIFIER ::= { cvismAtmTrunkMIBGroups 1 }
-- OBJECT-GROUP
--  Status
--    deprecated
--  Descr
--    The collection of objects which are used to represent
--    VISM Bearer connection.
--  objects
--    bearerEndptNum, bearerCid, bearerLcn, bearerSentPkts, 
--    bearerRcvdPkts, bearerSentOctets, bearerRcvdOctets, 
--    bearerLostPkts, bearerJitter, bearerLatency, 
--    bearerAal2ExtAISCnts, bearerAal2ExtRAICnts, 
--    bearerAal2ConnAISCnts, bearerAal2ConnRDICnts, 
--    bearerCntClrButton

ciscoVismAAl2CidGroup OBJECT IDENTIFIER ::= { cvismAtmTrunkMIBGroups 2 }
-- OBJECT-GROUP
--  Status
--    deprecated
--  Descr
--    The collection of objects which are used to represent
--    VISM AAL2 CID connection.
--  objects
--    vismAal2CidNum, vismAal2CidLcn, vismAal2EndptNum, 
--    vismAal2CidRowStatus, vismAal2CidType3Redundancy, 
--    vismAal2CidVad, vismAal2CidProfileType, vismAal2CidProfileNum, 
--    vismAal2CidCodecType, vismAal2CidDtmfTransport, 
--    vismAal2CidCasTransport, vismAal2CidEcanEnable, 
--    vismAal2InitVadTimer, vismAal2CnfPktPeriod, 
--    vismAal2CidICSEnable, vismAal2CidState, vismAal2CidFailReason

ciscoVismAAl2CidGroupRev1 OBJECT IDENTIFIER ::= { cvismAtmTrunkMIBGroups 3 }
-- OBJECT-GROUP
--  Status
--    mandatory
--  Descr
--    The collection of objects which are used to represent
--    VISM AAL2 CID connection.
--  objects
--    vismAal2CidNum, vismAal2CidLcn, vismAal2EndptNum, 
--    vismAal2CidRowStatus, vismAal2CidType3Redundancy, 
--    vismAal2CidVad, vismAal2CidProfileType, vismAal2CidProfileNum, 
--    vismAal2CidCodecType, vismAal2CidDtmfTransport, 
--    vismAal2CidCasTransport, vismAal2CidEcanEnable, 
--    vismAal2InitVadTimer, vismAal2CnfPktPeriod, 
--    vismAal2CidICSEnable, vismAal2CidState, vismAal2CidFailReason, 
--    vismAal2CidAdminState

ciscoVismBearerConnGroupRev1 OBJECT IDENTIFIER ::= { cvismAtmTrunkMIBGroups 4 }
-- OBJECT-GROUP
--  Status
--    mandatory
--  Descr
--    The collection of objects which are used to represent
--    VISM Bearer connection.
--  objects
--    bearerEndptNum, bearerCid, bearerLcn, bearerSentPkts, 
--    bearerRcvdPkts, bearerSentOctets, bearerRcvdOctets, 
--    bearerLostPkts, bearerJitter, bearerLatency, 
--    bearerAal2ExtAISCnts, bearerAal2ExtRAICnts, 
--    bearerAal2ConnAISCnts, bearerAal2ConnRDICnts, 
--    bearerCntClrButton, bearerPeakXmtCellRate, 
--    bearerCurrentXmtCellRate, bearerPeakRcvCellRate, 
--    bearerCurrentRcvCellRate, bearerCurrentExtAISRcvCnts, 
--    bearerCurrentExtRAIRcvCnts, bearerCurrentConnAISCnts, 
--    bearerCurrentConnRDICnts, bearerCurrentExtAISXmtCnts, 
--    bearerCurrentExtRAIXmtCnts

cvismAtmTrunkCompliance OBJECT IDENTIFIER ::= { cvismAtmTrunkMIBCompliances 1 }
-- MODULE-COMPLIANCE
--  Status
--    deprecated
--  Descr
--    The compliance statement for objects related
--    to VISM Bearer and CID  Connection.
--  Module
--    >>current<<
--   MandGroup
--    ciscoVismBearerConnGroup
--   MandGroup
--    ciscoVismAAl2CidGroup

cvismAtmTrunkComplianceRev1 OBJECT IDENTIFIER ::= { cvismAtmTrunkMIBCompliances 2 }
-- MODULE-COMPLIANCE
--  Status
--    deprecated
--  Descr
--    The compliance statement for objects related
--    to VISM Bearer and CID  Connection.
--  Module
--    >>current<<
--   MandGroup
--    ciscoVismBearerConnGroup
--   MandGroup
--    ciscoVismAAl2CidGroupRev1

cvismAtmTrunkComplianceRev2 OBJECT IDENTIFIER ::= { cvismAtmTrunkMIBCompliances 3 }
-- MODULE-COMPLIANCE
--  Status
--    mandatory
--  Descr
--    The compliance statement for objects related
--    to VISM Bearer and CID  Connection.
--  Module
--    >>current<<
--   MandGroup
--    ciscoVismBearerConnGroupRev1
--   MandGroup
--    ciscoVismAAl2CidGroupRev1


END
