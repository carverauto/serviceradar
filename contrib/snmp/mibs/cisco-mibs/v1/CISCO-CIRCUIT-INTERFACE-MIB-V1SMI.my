-- MIB created 5/24/100 10:08:56, by
--   SMIC (the next generation) version 1.6.29, November 22, 1994.

CISCO-CIRCUIT-INTERFACE-MIB DEFINITIONS ::= BEGIN

-- From file: "CISCO-CIRCUIT-INTERFACE-MIB.my"

IMPORTS
    OBJECT-TYPE
            FROM RFC-1212
    RowStatus
            FROM SNMPv2-TC-v1
    SnmpAdminString
            FROM SNMP-FRAMEWORK-MIB
    ifIndex
            FROM IF-MIB
    ciscoMgmt
            FROM CISCO-SMI;

ciscoCircuitInterfaceMIB OBJECT IDENTIFIER ::= { ciscoMgmt 160 }
-- MODULE-IDENTITY
--  LastUpdated
--    200005090000Z
--  OrgName
--    Cisco Systems, Inc.
--  ContactInfo
--           Cisco Systems
--            Customer Service
--    
--    Postal: 170 W. Tasman Drive
--            San Jose, CA 95134
--            USA
--    
--    Tel: +1 800 553-NETS
--    
--    E-mail: cs-snmp@cisco.com
--  Descr
--    The MIB module to configure the circuit description
--    for an interface.
--    The circuit description can be used to describe and
--    identify circuits on interfaces like ATM,
--    frame-relay etc.
--  RevDate
--    200005090000Z
--  RevDescr
--    Initial version of this MIB module.

ciscoCircuitInterfaceMIBObjects OBJECT IDENTIFIER ::= { ciscoCircuitInterfaceMIB 1 }
cciDescription  OBJECT IDENTIFIER ::= { ciscoCircuitInterfaceMIBObjects 1 }
ciscoCircuitInterfaceMIBConformance OBJECT IDENTIFIER ::= { ciscoCircuitInterfaceMIB 3 }
ciscoCircuitInterfaceMIBCompliances OBJECT IDENTIFIER ::= { ciscoCircuitInterfaceMIBConformance 1 }
ciscoCircuitInterfaceMIBGroups OBJECT IDENTIFIER ::= { ciscoCircuitInterfaceMIBConformance 2 }

cciDescriptionTable OBJECT-TYPE
    SYNTAX SEQUENCE OF CciDescriptionEntry
    ACCESS not-accessible
    STATUS mandatory
    DESCRIPTION
        "This table contains a circuit description to identify
        circuit based interfaces like ATM, Frame-Relay etc.
        The circuit description could be used for example, to
        correlate performance statistics associated with the
        corresponding interfaces."
    ::= { cciDescription 1 }

cciDescriptionEntry OBJECT-TYPE
    SYNTAX CciDescriptionEntry
    ACCESS not-accessible
    STATUS mandatory
    DESCRIPTION
        "Each cciDescriptionEntry contains the circuit
        description for a particular circuit based interface.
        The entry is identified by the ifIndex which would
        typically correspond to circuit based interfaces.
        Interfaces with ifType equal to atm(37),
        frameRelay(32) frameRelayService(44) are some
        examples.
        
        Entries can only be created by management station
        action.
        Entries can be deleted by setting the cciStatus object
        to destroy(6). The agent will delete any cciEntry if
        the corresponding ifEntry is deleted.
        Entries are not maintained in any kind of NV-storage,
        and will not be recreated by the agent after a reboot."
    INDEX { ifIndex }
    ::= { cciDescriptionTable 1 }

CciDescriptionEntry ::= SEQUENCE {
    cciDescr SnmpAdminString,
    cciStatus RowStatus
    }

cciDescr OBJECT-TYPE
    SYNTAX SnmpAdminString(SIZE(0..255))
--    Rsyntax OCTET STRING(SIZE(0..255))
    ACCESS read-write
    STATUS mandatory
    DESCRIPTION
        "The circuit description of the interface. It has no
        default value."
    ::= { cciDescriptionEntry 1 }

cciStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The row status object, but with restricted values.
        Only two values are allowed for this object:
        createAndGo(4) and destroy(6).
        The row is created by specifying the value for
        cciDescr and setting this object to createAndGo(4).
        If the row creation is succesfull, the cciStatus
        would be active(1). In the active(1) state, the
        cciDescr can be modifed.
        The row is deleted by setting this object to
        destroy(6)."
    ::= { cciDescriptionEntry 2 }

ciscoCircuitInterfaceGroup OBJECT IDENTIFIER ::= { ciscoCircuitInterfaceMIBGroups 1 }
-- OBJECT-GROUP
--  Status
--    mandatory
--  Descr
--    The Cisco Circuit Interface MIB objects.
--  objects
--    cciDescr, cciStatus

ciscoCircuitInterfaceMIBCompliance OBJECT IDENTIFIER ::= { ciscoCircuitInterfaceMIBCompliances 1 }
-- MODULE-COMPLIANCE
--  Status
--    mandatory
--  Descr
--    The compliance statement for Cisco agents which
--    implement the Cisco Circuit Interface MIB.
--  Module
--    >>current<<
--   MandGroup
--    ciscoCircuitInterfaceGroup


END
