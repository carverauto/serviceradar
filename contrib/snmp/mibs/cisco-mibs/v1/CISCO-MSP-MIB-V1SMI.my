-- MIB file created 28-Feb-2014 07:45:30, by
--   SMICng version 2.2.11-beta(PRO)(Solaris), January 20, 2001. Enterprise key cisco.com

CISCO-MSP-MIB DEFINITIONS ::= BEGIN

-- From file: "CISCO-MSP-MIB.my"
-- Compile options "4 7 F H N W 03 06 0B 0G 0N 0T"

IMPORTS
    SnmpAdminString
            FROM SNMP-FRAMEWORK-MIB
    ifIndex
            FROM IF-MIB
    RowStatus, StorageType
            FROM SNMPv2-TC-v1
    ciscoMgmt
            FROM CISCO-SMI
    Gauge
            FROM RFC1155-SMI
    OBJECT-TYPE
            FROM RFC-1212;

ciscoMspMIB OBJECT IDENTIFIER ::= { ciscoMgmt 793 }
-- MODULE-IDENTITY
--  LastUpdated
--    201204190000Z
--  OrgName
--    Cisco Systems, Inc.
--  ContactInfo
--    Cisco Systems
--    Customer Service
--    
--    Postal: 170 W Tasman Drive
--    San Jose, CA  95134
--    USA
--    
--    Tel: +1 800 553-NETS
--    
--    E-mail: cs-medianet-metadata@cisco.com
--  Descr
--    Objective of media services proxy is to provide media services
--    to end-points and its flows identified by a set of
--    protocols. Media services include metadata and RSVP signaling.
--    
--          MIB Table Overview:
--          ==================
--          The MIB table consists of the following objects.
--          1.cMspGlobalStatus
--            To enable/disable MSP.
--          2.cMspGlobalProfile
--            Globally applied MSP profile.
--          3.cMspIfProfileTable
--            MSP profile applied on the interface.
--          4.cMspProfileTable
--            MSP profile table containing list of services
--             and parameter list for that service.
--          5.cMspRsvpParamsTable
--            RSVP parameter list. Used for RSVP reservation.
--          6.cMspMetaParamsTable
--            Metadata parameter list. Used for metadata signaling.
--  RevDate
--    201204190000Z
--  RevDescr
--    Initial version of this MIB module.

ciscoMspMIBNotifs OBJECT IDENTIFIER ::= { ciscoMspMIB 0 }
ciscoMspMIBObjects OBJECT IDENTIFIER ::= { ciscoMspMIB 1 }
ciscoMspMIBConform OBJECT IDENTIFIER ::= { ciscoMspMIB 2 }
ciscoMspMIBCompliances OBJECT IDENTIFIER ::= { ciscoMspMIBConform 1 }
ciscoMspMIBGroups OBJECT IDENTIFIER ::= { ciscoMspMIBConform 2 }

cMspGlobalStatus OBJECT-TYPE
    SYNTAX INTEGER {
        enable(1),
        disable(2)
        }
    ACCESS read-write
    STATUS mandatory
    DESCRIPTION
        "This object specifies whether media
        services proxy is enabled or disabled. 
        Default value is disabled."
    DEFVAL { disable }
    ::= { ciscoMspMIBObjects 1 }

cMspGlobalProfile OBJECT-TYPE
    SYNTAX SnmpAdminString(SIZE(1..100))
--    Rsyntax OCTET STRING(SIZE(1..100))
    ACCESS read-write
    STATUS mandatory
    DESCRIPTION
        "This object specifies the media services profile
        name globally enabled. This name corresponds to 
        an entry in media services profile table and
        using it the required services and parameters list
        are fetched and applied."
    ::= { ciscoMspMIBObjects 2 }

cMspIfProfileTable OBJECT-TYPE
    SYNTAX SEQUENCE OF CMspIfProfileEntry
    ACCESS not-accessible
    STATUS mandatory
    DESCRIPTION
        "This table specifies the media services
        profile applied to the interface."
    ::= { ciscoMspMIBObjects 3 }

cMspIfProfileEntry OBJECT-TYPE
    SYNTAX CMspIfProfileEntry
    ACCESS not-accessible
    STATUS mandatory
    DESCRIPTION
        "Each entry specifies the media services profile applied
        on a particular interface."
    INDEX { ifIndex }
    ::= { cMspIfProfileTable 1 }

CMspIfProfileEntry ::= SEQUENCE {
    cMspIfProfileName SnmpAdminString,
    cMspIfProfileStorageType StorageType,
    cMspIfProfileRowStatus RowStatus
    }

cMspIfProfileName OBJECT-TYPE
    SYNTAX SnmpAdminString(SIZE(1..100))
--    Rsyntax OCTET STRING(SIZE(1..100))
    ACCESS read-write
    STATUS mandatory
    DESCRIPTION
        "This object specifies the media services profile name
        applied on a particular interface. This name corresponds
        to an entry in the media services profile table and
        using it the required services and parameters list are 
        fetched and applied."
    ::= { cMspIfProfileEntry 1 }

cMspIfProfileStorageType OBJECT-TYPE
    SYNTAX StorageType
--    Rsyntax INTEGER {
--        other(1),
--        volatile(2),
--        nonVolatile(3),
--        permanent(4),
--        readOnly(5)
--        }
    ACCESS read-write
    STATUS mandatory
    DESCRIPTION
        "This object specifies the storage type for this
        conceptual row. Conceptual rows having the value
        'permanent' need not allow write-access to any 
        columnar objects in the row."
    DEFVAL { nonVolatile }
    ::= { cMspIfProfileEntry 2 }

cMspIfProfileRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object specifies the status of conceptual row of
        interface media services profile table."
    ::= { cMspIfProfileEntry 3 }

cMspProfileTable OBJECT-TYPE
    SYNTAX SEQUENCE OF CMspProfileEntry
    ACCESS not-accessible
    STATUS mandatory
    DESCRIPTION
        "This table specifies the configuration of media 
         services profile."
    ::= { ciscoMspMIBObjects 4 }

cMspProfileEntry OBJECT-TYPE
    SYNTAX CMspProfileEntry
    ACCESS not-accessible
    STATUS mandatory
    DESCRIPTION
        "Each entry specifies a media services
        profile and its attributes."
    INDEX { cMspProfileName }
    ::= { cMspProfileTable 1 }

CMspProfileEntry ::= SEQUENCE {
    cMspProfileName SnmpAdminString,
    cMspProfileService OCTET STRING,
    cMspProfileRsvp SnmpAdminString,
    cMspProfileMetadata SnmpAdminString,
    cMspProfileStorageType StorageType,
    cMspProfileRowStatus RowStatus
    }

cMspProfileName OBJECT-TYPE
    SYNTAX SnmpAdminString(SIZE(1..100))
--    Rsyntax OCTET STRING(SIZE(1..100))
    ACCESS read-write
    STATUS mandatory
    DESCRIPTION
        "This object specifies the name of media services profile."
    ::= { cMspProfileEntry 1 }

cMspProfileService OBJECT-TYPE
    SYNTAX OCTET STRING(SIZE(1..2))
        -- BITS are:
        --   rsvp(0)
        --   metadata(1)
    ACCESS read-write
    STATUS mandatory
    DESCRIPTION
        "This object specifies the list of services enabled
        for a media services profile."
    ::= { cMspProfileEntry 2 }

cMspProfileRsvp OBJECT-TYPE
    SYNTAX SnmpAdminString(SIZE(1..100))
--    Rsyntax OCTET STRING(SIZE(1..100))
    ACCESS read-write
    STATUS mandatory
    DESCRIPTION
        "This object specifies the name of the RSVP parameter list.
        This name corresponds to an entry in RSVP parameter list
        table and using this the RSVP parameters are fetched
        and applied when the media services profile is in use."
    ::= { cMspProfileEntry 3 }

cMspProfileMetadata OBJECT-TYPE
    SYNTAX SnmpAdminString(SIZE(1..100))
--    Rsyntax OCTET STRING(SIZE(1..100))
    ACCESS read-write
    STATUS mandatory
    DESCRIPTION
        "This object specifies the name of the metadata parameter list.
        This name corresponds to an entry in metadata parameter list
        table and using this the metadata parameters are fetched
        and applied when the media services profile is in use."
    ::= { cMspProfileEntry 4 }

cMspProfileStorageType OBJECT-TYPE
    SYNTAX StorageType
--    Rsyntax INTEGER {
--        other(1),
--        volatile(2),
--        nonVolatile(3),
--        permanent(4),
--        readOnly(5)
--        }
    ACCESS read-write
    STATUS mandatory
    DESCRIPTION
        "This object specifies the storage type for this
        conceptual row. Conceptual rows having the value
        'permanent' need not allow write-access to any 
        columnar objects in the row."
    DEFVAL { nonVolatile }
    ::= { cMspProfileEntry 5 }

cMspProfileRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object specifies the status of the conceptual
        row of media service profile table."
    ::= { cMspProfileEntry 6 }

cMspRsvpParamsTable OBJECT-TYPE
    SYNTAX SEQUENCE OF CMspRsvpParamsEntry
    ACCESS not-accessible
    STATUS mandatory
    DESCRIPTION
        "This table specifies the table of RSVP parameter lists to
        be used when the corresponding media services profile
        is in use."
    ::= { ciscoMspMIBObjects 5 }

cMspRsvpParamsEntry OBJECT-TYPE
    SYNTAX CMspRsvpParamsEntry
    ACCESS not-accessible
    STATUS mandatory
    DESCRIPTION
        "Each entry specifies a RSVP parameter list."
    INDEX { cMspRsvpParamsName }
    ::= { cMspRsvpParamsTable 1 }

CMspRsvpParamsEntry ::= SEQUENCE {
    cMspRsvpParamsName SnmpAdminString,
    cMspRsvpParamsBandwidth Gauge,
    cMspRsvpParamsPeakRate Gauge,
    cMspRsvpParamsMaxBurst Gauge,
    cMspRsvpParamsPriorityPrempt Gauge,
    cMspRsvpParamsPriorityDefend Gauge,
    cMspRsvpParamsStorageType StorageType,
    cMspRsvpParamsRowStatus RowStatus
    }

cMspRsvpParamsName OBJECT-TYPE
    SYNTAX SnmpAdminString(SIZE(1..100))
--    Rsyntax OCTET STRING(SIZE(1..100))
    ACCESS read-write
    STATUS mandatory
    DESCRIPTION
        "This object specifies the name of RSVP parameter list.
        This name is used in media services profile table to identify
        the RSVP parameter list and use it when the corresponding
        media services profile is applied."
    ::= { cMspRsvpParamsEntry 1 }

cMspRsvpParamsBandwidth OBJECT-TYPE
    SYNTAX Gauge(1..10000000)
--  Units
--    kbps
    ACCESS read-write
    STATUS mandatory
    DESCRIPTION
        "This object specifies the bandwidth to be used as value
        for RSVP bandwidth parameter when the corresponding media
        services profile is in use."
    ::= { cMspRsvpParamsEntry 2 }

cMspRsvpParamsPeakRate OBJECT-TYPE
    SYNTAX Gauge(1..10000000)
--  Units
--    kbps
    ACCESS read-write
    STATUS mandatory
    DESCRIPTION
        "This object specifies the peak rate to be used as a value
        for RSVP session peak rate parameter when the corresponding
         media services profile is in use."
    ::= { cMspRsvpParamsEntry 3 }

cMspRsvpParamsMaxBurst OBJECT-TYPE
    SYNTAX Gauge(1..65535)
--  Units
--    kB
    ACCESS read-write
    STATUS mandatory
    DESCRIPTION
        "This object specifies the max burst to be used as a value
        for RSVP max burst parameter when the corresponding media
        services profile is in use."
    ::= { cMspRsvpParamsEntry 4 }

cMspRsvpParamsPriorityPrempt OBJECT-TYPE
    SYNTAX Gauge(0..7)
    ACCESS read-write
    STATUS mandatory
    DESCRIPTION
        "This object specifies the preemption priority to be used as
        a value for RSVP priority preempt parameter when the
        corresponding media services profile is in use."
    ::= { cMspRsvpParamsEntry 5 }

cMspRsvpParamsPriorityDefend OBJECT-TYPE
    SYNTAX Gauge(0..7)
    ACCESS read-write
    STATUS mandatory
    DESCRIPTION
        "This object specifies the preemption defend to be used as a
        value for RSVP priority defend parameter when the
        corresponding media services profile is in use."
    ::= { cMspRsvpParamsEntry 6 }

cMspRsvpParamsStorageType OBJECT-TYPE
    SYNTAX StorageType
--    Rsyntax INTEGER {
--        other(1),
--        volatile(2),
--        nonVolatile(3),
--        permanent(4),
--        readOnly(5)
--        }
    ACCESS read-write
    STATUS mandatory
    DESCRIPTION
        "This object specifies the storage type for this
        conceptual row. Conceptual rows having the value
        'permanent' need not allow write-access to any 
        columnar objects in the row."
    DEFVAL { nonVolatile }
    ::= { cMspRsvpParamsEntry 7 }

cMspRsvpParamsRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object specifies the status of the conceptual row of
        the RSVP parameter list table."
    ::= { cMspRsvpParamsEntry 8 }

cMspMetaParamsTable OBJECT-TYPE
    SYNTAX SEQUENCE OF CMspMetaParamsEntry
    ACCESS not-accessible
    STATUS mandatory
    DESCRIPTION
        "This table specifies the table of metadata parameter lists to
        be used when the corresponding media services profile
        is in use."
    ::= { ciscoMspMIBObjects 6 }

cMspMetaParamsEntry OBJECT-TYPE
    SYNTAX CMspMetaParamsEntry
    ACCESS not-accessible
    STATUS mandatory
    DESCRIPTION
        "Each entry specifies a metadata parameter list."
    INDEX { cMspMetaParamsName }
    ::= { cMspMetaParamsTable 1 }

CMspMetaParamsEntry ::= SEQUENCE {
    cMspMetaParamsName SnmpAdminString,
    cMspMetaParamsBandwidth Gauge,
    cMspMetaParamsSyncSrc Gauge,
    cMspMetaParamsClockFreq Gauge,
    cMspMetaParamsSessId SnmpAdminString,
    cMspMetaParamsDomainName SnmpAdminString,
    cMspMetaParamsCname SnmpAdminString,
    cMspMetaParamsMimeType SnmpAdminString,
    cMspMetaParamsPayloadType Gauge,
    cMspMetaParamsSipUserName SnmpAdminString,
    cMspMetaParamsSipEmail SnmpAdminString,
    cMspMetaParamsAppName SnmpAdminString,
    cMspMetaParamsAppVendor SnmpAdminString,
    cMspMetaParamsAppVersion SnmpAdminString,
    cMspMetaParamsStorageType StorageType,
    cMspMetaParamsRowStatus RowStatus
    }

cMspMetaParamsName OBJECT-TYPE
    SYNTAX SnmpAdminString(SIZE(1..100))
--    Rsyntax OCTET STRING(SIZE(1..100))
    ACCESS read-write
    STATUS mandatory
    DESCRIPTION
        "This object specifies the name of metadata parameter list.
        This name is used in media services profile table to identify
        the metadata parameter list and use it when the corresponding
        media services profile is applied."
    ::= { cMspMetaParamsEntry 1 }

cMspMetaParamsBandwidth OBJECT-TYPE
    SYNTAX Gauge(1..10000000)
--  Units
--    kbps
    ACCESS read-write
    STATUS mandatory
    DESCRIPTION
        "This object specifies the bandwidth to be used as value
        for metadata bandwidth parameter when the corresponding
        media services profile is in use."
    ::= { cMspMetaParamsEntry 2 }

cMspMetaParamsSyncSrc OBJECT-TYPE
    SYNTAX Gauge
    ACCESS read-write
    STATUS mandatory
    DESCRIPTION
        "This object specifies the synchronization source to be used
        as value for metadata synchronization source parameter
        when the corresponding media services profile is in use."
    ::= { cMspMetaParamsEntry 3 }

cMspMetaParamsClockFreq OBJECT-TYPE
    SYNTAX Gauge
    ACCESS read-write
    STATUS mandatory
    DESCRIPTION
        "This object specifies the clock frequency to be used
        as value for metadata clock frequency parameter
        when the corresponding media services profile is in use."
    ::= { cMspMetaParamsEntry 4 }

cMspMetaParamsSessId OBJECT-TYPE
    SYNTAX SnmpAdminString(SIZE(0..80))
--    Rsyntax OCTET STRING(SIZE(0..80))
    ACCESS read-write
    STATUS mandatory
    DESCRIPTION
        "This object specifies the session ID to be used
        as value for metadata session ID parameter
        when the corresponding media services profile is in use."
    ::= { cMspMetaParamsEntry 5 }

cMspMetaParamsDomainName OBJECT-TYPE
    SYNTAX SnmpAdminString(SIZE(0..24))
--    Rsyntax OCTET STRING(SIZE(0..24))
    ACCESS read-write
    STATUS mandatory
    DESCRIPTION
        "This object specifies the domain name to be used
        as value for metadata domain name parameter
        when the corresponding media services profile is in use."
    ::= { cMspMetaParamsEntry 6 }

cMspMetaParamsCname OBJECT-TYPE
    SYNTAX SnmpAdminString(SIZE(0..24))
--    Rsyntax OCTET STRING(SIZE(0..24))
    ACCESS read-write
    STATUS mandatory
    DESCRIPTION
        "This object specifies the cname to be used
        as value for metadata cname parameter
        when the corresponding media services profile is in use.
        Cname represents SIP call canonical name."
    ::= { cMspMetaParamsEntry 7 }

cMspMetaParamsMimeType OBJECT-TYPE
    SYNTAX SnmpAdminString(SIZE(0..16))
--    Rsyntax OCTET STRING(SIZE(0..16))
    ACCESS read-write
    STATUS mandatory
    DESCRIPTION
        "This object specifies the mime type to be used
        as value for metadata mime type parameter
        when the corresponding media services profile is in use.
        Mime type represents the audio/video media type."
    ::= { cMspMetaParamsEntry 8 }

cMspMetaParamsPayloadType OBJECT-TYPE
    SYNTAX Gauge(0..127)
    ACCESS read-write
    STATUS mandatory
    DESCRIPTION
        "This object specifies the payload type to be used
        as value for metadata payload type parameter
        when the corresponding media services profile is in use."
    ::= { cMspMetaParamsEntry 9 }

cMspMetaParamsSipUserName OBJECT-TYPE
    SYNTAX SnmpAdminString(SIZE(0..16))
--    Rsyntax OCTET STRING(SIZE(0..16))
    ACCESS read-write
    STATUS mandatory
    DESCRIPTION
        "This object specifies the SIP user name to be used
        as value for metadata SIP user name parameter
        when the corresponding media services profile is in use."
    ::= { cMspMetaParamsEntry 10 }

cMspMetaParamsSipEmail OBJECT-TYPE
    SYNTAX SnmpAdminString(SIZE(0..24))
--    Rsyntax OCTET STRING(SIZE(0..24))
    ACCESS read-write
    STATUS mandatory
    DESCRIPTION
        "This object specifies the SIP email ID to be used
        as value for metadata SIP email ID parameter
        when the corresponding media services profile is in use."
    ::= { cMspMetaParamsEntry 11 }

cMspMetaParamsAppName OBJECT-TYPE
    SYNTAX SnmpAdminString(SIZE(0..40))
--    Rsyntax OCTET STRING(SIZE(0..40))
    ACCESS read-write
    STATUS mandatory
    DESCRIPTION
        "This object specifies the application name to be used
        as value for metadata application name parameter
        when the corresponding media services profile is in use."
    ::= { cMspMetaParamsEntry 12 }

cMspMetaParamsAppVendor OBJECT-TYPE
    SYNTAX SnmpAdminString(SIZE(0..40))
--    Rsyntax OCTET STRING(SIZE(0..40))
    ACCESS read-write
    STATUS mandatory
    DESCRIPTION
        "This object specifies the application vendor to be used
        as value for metadata application vendor parameter
        when the corresponding media services profile is in use."
    ::= { cMspMetaParamsEntry 13 }

cMspMetaParamsAppVersion OBJECT-TYPE
    SYNTAX SnmpAdminString(SIZE(0..40))
--    Rsyntax OCTET STRING(SIZE(0..40))
    ACCESS read-write
    STATUS mandatory
    DESCRIPTION
        "This object specifies the application version to be used
        as value for metadata application version parameter
        when the corresponding media services profile is in use."
    ::= { cMspMetaParamsEntry 14 }

cMspMetaParamsStorageType OBJECT-TYPE
    SYNTAX StorageType
--    Rsyntax INTEGER {
--        other(1),
--        volatile(2),
--        nonVolatile(3),
--        permanent(4),
--        readOnly(5)
--        }
    ACCESS read-write
    STATUS mandatory
    DESCRIPTION
        "This object specifies the storage type for this
        conceptual row. Conceptual rows having the value
        'permanent' need not allow write-access to any 
        columnar objects in the row."
    DEFVAL { nonVolatile }
    ::= { cMspMetaParamsEntry 15 }

cMspMetaParamsRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object specifies the row status of conceptual row
        of metadata parameter list table."
    ::= { cMspMetaParamsEntry 16 }

ciscoMspMIBScalarObjectGroup OBJECT IDENTIFIER ::= { ciscoMspMIBGroups 1 }
-- OBJECT-GROUP
--  Status
--    mandatory
--  Descr
--    A collection of scalar objects for media services.
--  objects
--    cMspGlobalStatus, cMspGlobalProfile

ciscoMspMIBIfProfileObjectGroup OBJECT IDENTIFIER ::= { ciscoMspMIBGroups 2 }
-- OBJECT-GROUP
--  Status
--    mandatory
--  Descr
--    A collection of objects for media services interface table.
--  objects
--    cMspIfProfileName, cMspIfProfileStorageType, 
--    cMspIfProfileRowStatus

ciscoMspMIBProfileNameObjectGroup OBJECT IDENTIFIER ::= { ciscoMspMIBGroups 3 }
-- OBJECT-GROUP
--  Status
--    mandatory
--  Descr
--    A collection of objects for media services profile.
--  objects
--    cMspProfileName, cMspProfileService, cMspProfileRsvp, 
--    cMspProfileMetadata, cMspProfileStorageType, 
--    cMspProfileRowStatus

ciscoMspMIBRsvpParamsObjectGroup OBJECT IDENTIFIER ::= { ciscoMspMIBGroups 4 }
-- OBJECT-GROUP
--  Status
--    mandatory
--  Descr
--    A collection of objects for RSVP parameters.
--  objects
--    cMspRsvpParamsName, cMspRsvpParamsBandwidth, 
--    cMspRsvpParamsPeakRate, cMspRsvpParamsMaxBurst, 
--    cMspRsvpParamsPriorityPrempt, cMspRsvpParamsPriorityDefend, 
--    cMspRsvpParamsStorageType, cMspRsvpParamsRowStatus

ciscoMspMIBMetaParamsObjectGroup OBJECT IDENTIFIER ::= { ciscoMspMIBGroups 5 }
-- OBJECT-GROUP
--  Status
--    mandatory
--  Descr
--    A collection of objects for metadata parameters.
--  objects
--    cMspMetaParamsName, cMspMetaParamsBandwidth, 
--    cMspMetaParamsSyncSrc, cMspMetaParamsClockFreq, 
--    cMspMetaParamsSessId, cMspMetaParamsDomainName, 
--    cMspMetaParamsCname, cMspMetaParamsMimeType, 
--    cMspMetaParamsPayloadType, cMspMetaParamsSipUserName, 
--    cMspMetaParamsSipEmail, cMspMetaParamsAppName, 
--    cMspMetaParamsAppVendor, cMspMetaParamsAppVersion, 
--    cMspMetaParamsStorageType, cMspMetaParamsRowStatus

ciscoMspMIBCompliance OBJECT IDENTIFIER ::= { ciscoMspMIBCompliances 1 }
-- MODULE-COMPLIANCE
--  Status
--    mandatory
--  Descr
--    This is a default module-compliance for ciscoMspMIB
--    containing default object groups.
--  Module
--    >>current<<
--   MandGroup
--    ciscoMspMIBScalarObjectGroup
--   MandGroup
--    ciscoMspMIBIfProfileObjectGroup
--   MandGroup
--    ciscoMspMIBProfileNameObjectGroup
--   MandGroup
--    ciscoMspMIBRsvpParamsObjectGroup
--   MandGroup
--    ciscoMspMIBMetaParamsObjectGroup


END
