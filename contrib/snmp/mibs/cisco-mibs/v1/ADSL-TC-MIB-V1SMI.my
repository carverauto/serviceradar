-- MIB file created 03-Dec-2001 17:12:21, by
--   SMICng version 2.2.11-beta(PRO)(Solaris), January 20, 2001. Enterprise key cisco.com

ADSL-TC-MIB DEFINITIONS ::= BEGIN

-- From file: "ADSL-TC-MIB.my"
-- Compile options "4 7 F H N W 03 06 0B 0G 0N 0T"

IMPORTS
    transmission
            FROM SNMPv2-SMI-v1
    Gauge
            FROM RFC1155-SMI;

adsltcmib OBJECT IDENTIFIER ::= { transmission 94 2 }
-- MODULE-IDENTITY
--  LastUpdated
--    9908190000Z
--  OrgName
--    IETF ADSL MIB Working Group
--  ContactInfo
--    
--    Gregory Bathrick
--    AG Communication Systems
--    A Subsidiary of Lucent Technologies
--    2500 W Utopia Rd.
--    Phoenix, AZ 85027 USA
--    Tel: +1 602-582-7679
--    Fax: +1 602-582-7697
--    E-mail: bathricg@agcs.com
--    
--    Faye Ly
--    Copper Mountain Networks
--    Norcal Office
--    2470 Embarcadero Way
--    Palo Alto, CA 94303
--    Tel: +1 650-858-8500
--    Fax: +1 650-858-8085
--    E-Mail: faye@coppermountain.com
--    IETF ADSL MIB Working Group (adsl@xlist.agcs.com)
--  Descr
--    The MIB module which provides a ADSL
--    Line Coding Textual Convention to be used
--    by ADSL Lines.
--  RevDate
--    9908190000Z
--  RevDescr
--    Initial Version, published as RFC 2662

AdslLineCodingType ::= INTEGER {
        other(1),
        dmt(2),
        cap(3),
        qam(4)
        }
-- TEXTUAL-CONVENTION
--  Status
--    mandatory
--  Descr
--    This data type is used as the syntax for the ADSL
--    Line Code.

AdslPerfCurrDayCount ::= Gauge
-- TEXTUAL-CONVENTION
--  Status
--    mandatory
--  Descr
--    A counter associated with interface performance
--    measurements in a current 1-day (24 hour) measurement
--    interval.
--    
--    The value of this counter starts at zero at the
--    beginning of an interval and is increased when
--    associated events occur, until the end of the
--    1-day interval.  At that time the value of the
--    counter is stored in the previous 1-day history
--    interval, if available, and the current interval
--    counter is restarted at zero.
--    
--    In the case where the agent has no valid data available
--    for this interval the corresponding object
--    instance is not available and upon a retrieval
--    request a corresponding error message shall be
--    returned to indicate that this instance does
--    not exist (for example, a noSuchName error for
--    SNMPv1 and a noSuchInstance for SNMPv2 GET
--    operation).

AdslPerfPrevDayCount ::= Gauge
-- TEXTUAL-CONVENTION
--  Status
--    mandatory
--  Descr
--    A counter associated with interface performance
--    measurements during the most previous 1-day (24 hour)
--    measurement interval.  The value of this counter is
--    equal to the value of the current day counter at
--    the end of its most recent interval.
--    
--    In the case where the agent has no valid data available
--    for this interval the corresponding object
--    instance is not available and upon a retrieval
--    request a corresponding error message shall be
--    returned to indicate that this instance does
--    not exist (for example, a noSuchName error for
--    SNMPv1 and a noSuchInstance for SNMPv2 GET
--    operation).

AdslPerfTimeElapsed ::= Gauge
-- TEXTUAL-CONVENTION
--  Status
--    mandatory
--  Descr
--    The number of seconds that have elapsed since
--    the beginning of the current measurement period.
--    If, for some reason, such as an adjustment in the
--    system's time-of-day clock, the current interval
--    exceeds the maximum value, the agent will return
--    the maximum value.


END
