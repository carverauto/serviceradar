-- MIB created 6/25/99 12:57:06, by
--   SMIC (the next generation) version 1.6.29, November 22, 1994.

CISCO-DIAL-CONTROL-MIB DEFINITIONS ::= BEGIN

-- From file: "CISCO-DIAL-CONTROL-MIB.my"

IMPORTS
    OBJECT-TYPE
            FROM RFC-1212
    DisplayString, TimeStamp
            FROM SNMPv2-TC-v1
    Unsigned32
            FROM CISCO-TC
    ciscoExperiment
            FROM CISCO-SMI
    AbsoluteCounter32
            FROM DIAL-CONTROL-MIB
    InterfaceIndex
            FROM IF-MIB;

ciscoDialControlMib OBJECT IDENTIFIER ::= { ciscoExperiment 25 }
-- MODULE-IDENTITY
--  LastUpdated
--    9801161546Z
--  OrgName
--    Cisco systems, Inc.
--  ContactInfo
--            Bibek Das
--     Postal: cisco Systems
--             170 West Tasman Drive
--             San Jose, CA 95134
--             U.S.A.
--     Phone:  +1 408 526 5225
--     E-mail: cs-isdn@cisco.com
--  Descr
--    The MIB module to describe call history information for
--     demand access and possibly other kinds of interfaces.

ciscoDialControlMibObjects OBJECT IDENTIFIER ::= { ciscoDialControlMib 1 }
cCallHistory    OBJECT IDENTIFIER ::= { ciscoDialControlMibObjects 4 }
ciscoDialControlMibConformance OBJECT IDENTIFIER ::= { ciscoDialControlMib 3 }
ciscoDialControlMibCompliances OBJECT IDENTIFIER ::= { ciscoDialControlMibConformance 1 }
ciscoDialControlMibGroups OBJECT IDENTIFIER ::= { ciscoDialControlMibConformance 2 }

cCallHistoryTable OBJECT-TYPE
    SYNTAX SEQUENCE OF CCallHistoryEntry
    ACCESS not-accessible
    STATUS mandatory
    DESCRIPTION
        "A table containing information about specific
         calls to a specific destination."
    ::= { cCallHistory 3 }

cCallHistoryEntry OBJECT-TYPE
    SYNTAX CCallHistoryEntry
    ACCESS not-accessible
    STATUS mandatory
    DESCRIPTION
        "The information regarding a single Connection."
    INDEX { cCallHistoryIndex }
    ::= { cCallHistoryTable 1 }

CCallHistoryEntry ::= SEQUENCE {
    cCallHistoryIndex Unsigned32,
    cCallHistorySetupTime TimeStamp,
    cCallHistoryPeerAddress DisplayString,
    cCallHistoryPeerSubAddress DisplayString,
    cCallHistoryPeerId INTEGER,
    cCallHistoryPeerIfIndex INTEGER,
    cCallHistoryLogicalIfIndex InterfaceIndex,
    cCallHistoryDisconnectCause OCTET STRING,
    cCallHistoryDisconnectText DisplayString,
    cCallHistoryConnectTime TimeStamp,
    cCallHistoryDisconnectTime TimeStamp,
    cCallHistoryCallOrigin INTEGER,
    cCallHistoryChargedUnits AbsoluteCounter32,
    cCallHistoryInfoType INTEGER,
    cCallHistoryTransmitPackets AbsoluteCounter32,
    cCallHistoryTransmitBytes AbsoluteCounter32,
    cCallHistoryReceivePackets AbsoluteCounter32,
    cCallHistoryReceiveBytes AbsoluteCounter32
    }

cCallHistoryIndex OBJECT-TYPE
    SYNTAX Unsigned32(1..4294967295)
--    Rsyntax Gauge32(1..4294967295)
    ACCESS not-accessible
    STATUS mandatory
    DESCRIPTION
        "A monotonically increasing integer for the sole purpose of
         indexing call disconnection events.  When it reaches the 
         maximum value, an extremely unlikely event, the agent wraps 
         the value back to 1 and may flush existing entries."
    ::= { cCallHistoryEntry 1 }

cCallHistorySetupTime OBJECT-TYPE
    SYNTAX TimeStamp
--    Rsyntax TimeTicks
    ACCESS read-only
    STATUS mandatory
    DESCRIPTION
        "The value of sysUpTime when the call setup was started.
         This will be useful for an NMS to sort the call history
         entry with call setup time. Also, this object
         can be useful in finding large delays between the time the
         call was started and the time the call was connected.
         For ISDN media, this will be the time when the setup
         message was received from or sent to the network.
         The value of this object is the same as callActiveSetupTime
         in the callActiveTable"
    ::= { cCallHistoryEntry 2 }

cCallHistoryPeerAddress OBJECT-TYPE
    SYNTAX DisplayString
--    Rsyntax OCTET STRING(SIZE(0..255))
    ACCESS read-only
    STATUS mandatory
    DESCRIPTION
        "The number this call was connected to. If the number is
         not available, then it will have a length of zero."
    ::= { cCallHistoryEntry 3 }

cCallHistoryPeerSubAddress OBJECT-TYPE
    SYNTAX DisplayString
--    Rsyntax OCTET STRING(SIZE(0..255))
    ACCESS read-only
    STATUS mandatory
    DESCRIPTION
        "The subaddress this call was connected to. If the subaddress
         is undefined or not available, this will be a zero length
         string."
    ::= { cCallHistoryEntry 4 }

cCallHistoryPeerId OBJECT-TYPE
    SYNTAX INTEGER(0..2147483647)
    ACCESS read-only
    STATUS mandatory
    DESCRIPTION
        "This is the Id value of the peer table entry
         to which this call was made. If a peer table entry
         for this call does not exist, the value of this object
         will be zero."
    ::= { cCallHistoryEntry 5 }

cCallHistoryPeerIfIndex OBJECT-TYPE
    SYNTAX INTEGER(0..2147483647)
    ACCESS read-only
    STATUS mandatory
    DESCRIPTION
        "This is the ifIndex value of the peer table entry
         to which this call was made. If a peer table entry
         for this call does not exist, the value of this object
         will be zero."
    ::= { cCallHistoryEntry 6 }

cCallHistoryLogicalIfIndex OBJECT-TYPE
    SYNTAX InterfaceIndex
--    Rsyntax Integer32
    ACCESS read-only
    STATUS mandatory
    DESCRIPTION
        "This is the ifIndex value of the logical interface through
         which this call was made. For ISDN media, this would be
         the ifIndex of the B channel which was used for this call."
    ::= { cCallHistoryEntry 7 }

cCallHistoryDisconnectCause OBJECT-TYPE
    SYNTAX OCTET STRING(SIZE(0..4))
    ACCESS read-only
    STATUS mandatory
    DESCRIPTION
        "The encoded network cause value associated with this call.
        
         The value of this object will depend on the interface type
         as well as on the protocol and protocol version being
         used on this interface. Some references for possible cause
         values are given below."
    REFERENCE
        "- Bellcore SR-NWT-001953, Generic Guidelines for
           ISDN Terminal Equipment On Basic Access Interfaces,
           chapter 5.2.5.8.
         - Bellcore SR-NWT-002343, ISDN Primary Rate Interface
           Generic Guidelines for Customer Premises Equipment,
           chapter 8.2.5.8.
         - ITU-T Q.931, Appendix I.
         - ITU-T X.25, CAUSE and DIAGNOSTIC field values.
         - German Telekom FTZ 1TR6, chapter 3.2.3.4.4.4."
    ::= { cCallHistoryEntry 8 }

cCallHistoryDisconnectText OBJECT-TYPE
    SYNTAX DisplayString
--    Rsyntax OCTET STRING(SIZE(0..255))
    ACCESS read-only
    STATUS mandatory
    DESCRIPTION
        "ASCII text describing the reason for call termination.
        
         This object exists because it would be impossible for
         a management station to store all possible cause values
         for all types of interfaces. It should be used only if
         a management station is unable to decode the value of
         dialCtlPeerStatsLastDisconnectCause."
    ::= { cCallHistoryEntry 9 }

cCallHistoryConnectTime OBJECT-TYPE
    SYNTAX TimeStamp
--    Rsyntax TimeTicks
    ACCESS read-only
    STATUS mandatory
    DESCRIPTION
        "The value of sysUpTime when the call was connected."
    ::= { cCallHistoryEntry 10 }

cCallHistoryDisconnectTime OBJECT-TYPE
    SYNTAX TimeStamp
--    Rsyntax TimeTicks
    ACCESS read-only
    STATUS mandatory
    DESCRIPTION
        "The value of sysUpTime when the call was disconnected."
    ::= { cCallHistoryEntry 11 }

cCallHistoryCallOrigin OBJECT-TYPE
    SYNTAX INTEGER {
        originate(1),
        answer(2),
        callback(3)
        }
    ACCESS read-only
    STATUS mandatory
    DESCRIPTION
        "The call origin."
    ::= { cCallHistoryEntry 12 }

cCallHistoryChargedUnits OBJECT-TYPE
    SYNTAX AbsoluteCounter32
--    Rsyntax Gauge32
    ACCESS read-only
    STATUS mandatory
    DESCRIPTION
        "The number of charged units for this connection.
         For incoming calls or if charging information is
         not supplied by the switch, the value of this object
         will be zero."
    ::= { cCallHistoryEntry 13 }

cCallHistoryInfoType OBJECT-TYPE
    SYNTAX INTEGER {
        other(1),
        speech(2),
        unrestrictedDigital(3),
        unrestrictedDigital56(4),
        restrictedDigital(5),
        audio31(6),
        audio7(7),
        video(8),
        packetSwitched(9),
        fax(10)
        }
    ACCESS read-only
    STATUS mandatory
    DESCRIPTION
        "The information type for this call."
    ::= { cCallHistoryEntry 14 }

cCallHistoryTransmitPackets OBJECT-TYPE
    SYNTAX AbsoluteCounter32
--    Rsyntax Gauge32
    ACCESS read-only
    STATUS mandatory
    DESCRIPTION
        "The number of packets which were transmitted while this
         call was active."
    ::= { cCallHistoryEntry 15 }

cCallHistoryTransmitBytes OBJECT-TYPE
    SYNTAX AbsoluteCounter32
--    Rsyntax Gauge32
    ACCESS read-only
    STATUS mandatory
    DESCRIPTION
        "The number of bytes which were transmitted while this
         call was active."
    ::= { cCallHistoryEntry 16 }

cCallHistoryReceivePackets OBJECT-TYPE
    SYNTAX AbsoluteCounter32
--    Rsyntax Gauge32
    ACCESS read-only
    STATUS mandatory
    DESCRIPTION
        "The number of packets which were received while this
         call was active."
    ::= { cCallHistoryEntry 17 }

cCallHistoryReceiveBytes OBJECT-TYPE
    SYNTAX AbsoluteCounter32
--    Rsyntax Gauge32
    ACCESS read-only
    STATUS mandatory
    DESCRIPTION
        "The number of bytes which were received while this
         call was active."
    ::= { cCallHistoryEntry 18 }

cCallHistoryGroup OBJECT IDENTIFIER ::= { ciscoDialControlMibGroups 1 }
-- OBJECT-GROUP
--  Status
--    mandatory
--  Descr
--    A collection of objects providing the Call History
--     capability.
--  objects
--    cCallHistorySetupTime, cCallHistoryPeerAddress, 
--    cCallHistoryPeerSubAddress, cCallHistoryPeerId, 
--    cCallHistoryPeerIfIndex, cCallHistoryLogicalIfIndex, 
--    cCallHistoryDisconnectCause, cCallHistoryDisconnectText, 
--    cCallHistoryConnectTime, cCallHistoryDisconnectTime, 
--    cCallHistoryCallOrigin, cCallHistoryChargedUnits, 
--    cCallHistoryInfoType, cCallHistoryTransmitPackets, 
--    cCallHistoryTransmitBytes, cCallHistoryReceivePackets, 
--    cCallHistoryReceiveBytes

ciscoDialControlMibCompliance OBJECT IDENTIFIER ::= { ciscoDialControlMibCompliances 1 }
-- MODULE-COMPLIANCE
--  Status
--    mandatory
--  Descr
--    The compliance statement for entities which
--     implement the DIAL CONTROL MIB
--  Module
--    >>current<<
--   MandGroup
--    cCallHistoryGroup


END
