-- MIB file created 03-Dec-2001 17:12:25, by
--   SMICng version 2.2.11-beta(PRO)(Solaris), January 20, 2001. Enterprise key cisco.com

CISCO-ADSL-CAP-LINE-MIB DEFINITIONS ::= BEGIN

-- From file: "CISCO-ADSL-CAP-LINE-MIB.my"
-- Compile options "4 7 F H N W 03 06 0B 0G 0N 0T"

IMPORTS
    TruthValue
            FROM SNMPv2-TC-v1
    ciscoMgmt
            FROM CISCO-SMI
    AdslPerfCurrDayCount, AdslPerfPrevDayCount
            FROM ADSL-TC-MIB
    adslAtucIntervalNumber, adslLineConfProfileName
            FROM ADSL-LINE-MIB
    ifIndex
            FROM IF-MIB
    PerfCurrentCount, PerfIntervalCount
            FROM PerfHist-TC-MIB
    Counter, Gauge
            FROM RFC1155-SMI
    OBJECT-TYPE
            FROM RFC-1212;

ciscoAdslLineCapMIB OBJECT IDENTIFIER ::= { ciscoMgmt 149 }
-- MODULE-IDENTITY
--  LastUpdated
--    200103010000Z
--  OrgName
--    Cisco Systems, Inc.
--  ContactInfo
--    Cisco Systems
--     Customer Service
--    
--     Postal: 170 W Tasman Drive
--     San Jose, CA 95134
--    
--     Tel: +1 800 553-NETS
--    
--     E-mail: cs-dslam.com
--  Descr
--    This MIB module serves as an enterprise-specific extension of
--    the ADSL-LINE-MIB.  The structure of this MIB module shadows
--    the structure of the ADSL-LINE-MIB, table for table.  The tables
--    defined by this MIB module contain managed objects that meet the
--    following criteria:
--    
--    1)  A managed object represents an attribute or characteristic
--        specific to CAP (Carrierless AM/PM) modems.
--    
--    2)  The ADSL-CAP-LINE-MIB does not already contain a managed
--        object representing the same information as this managed
--        object.
--    
--    Observe that entries contained by the tables in this MIB module
--    do not augment the corresponding entries in the ADSL-LINE-MIB,
--    as every modem represented by the ADSL-LINE-MIB is not
--    necessarily a CAP modem.
--    
--    Also observe that entries contained by the tables in this MIB
--    module do not augment the corresponding entries in the
--    ADSL-CAP-LINE-MIB, as this assumes that the ADSL-CAP-LINE-MIB
--    defines tables that correspond to every table defined by the
--    ADSL-LINE-MIB.  At this time, this assumption does not hold
--    true.
--    
--    *** ABBREVIATIONS, ACRONYMS, AND SYMBOLS ***
--    
--    ADSL - Asymmetric Digital Subscriber Line.
--    
--    ATM - Asynchronous Transfer Mode.
--    
--    ATU-C - ADSL Transceiver Unit, Central Office end.
--    
--    ATU-R - ADSL Transceiver Unit, Remote terminal end.
--    
--    BER - Bit Error Ratio.
--    
--    CAP - Carrierless Amplitude Modulation / Pulse Modulation.
--    
--    DSL - Digital Subscriber Line.
--    
--    SNR - Signal-to-Noise Ratio.
--    
--    STM - Synchronous Transfer Mode.
--    
--    *** DEFINITIONS ***
--    
--    DOWNSTREAM
--        The flow of data in the direction from the ATU-C to ATU-R.
--    
--    MARGIN (also referred to as 'SNR margin')
--        The difference between the SNR of the received signal and
--        the SNR required to provide a BER of 10E-7.
--    
--    SYMBOL
--        The number of bits the transmitter is capable of
--        multiplexing and modulating in a single signalling interval.
--    
--    SYMBOL RATE
--        The rate at which all symbols are transmitted.
--    
--    UPSTREAM
--        The flow of data in the direction from the ATU-R to ATU-C.
--  RevDate
--    200103010000Z
--  RevDescr
--    Changed MAX-ACCESS for cAdslAtucCapConfUp17KBaudEnable to
--     read-create due to the the bug fix of MAX-ACCESS in the
--     broken MIB object.

ciscoAdslLineCapMIBObjects OBJECT IDENTIFIER ::= { ciscoAdslLineCapMIB 1 }
cAdslLineCapMIBNotificationsPrefix OBJECT IDENTIFIER ::= { ciscoAdslLineCapMIB 2 }
cAdslLineCapMIBNotifications OBJECT IDENTIFIER ::= { cAdslLineCapMIBNotificationsPrefix 0 }
ciscoAdslLineCapMIBConformance OBJECT IDENTIFIER ::= { ciscoAdslLineCapMIB 3 }
ciscoAdslLineCapMIBCompliances OBJECT IDENTIFIER ::= { ciscoAdslLineCapMIBConformance 1 }
ciscoAdslLineCapMIBGroups OBJECT IDENTIFIER ::= { ciscoAdslLineCapMIBConformance 2 }

AdslLineCapDownstreamRate ::= INTEGER(0|256000|384000|512000|640000|768000|896000|960000|1024000|1280000|1600000|1920000|2240000|2560000|2688000|3200000|4480000|5120000|6272000|7168000)
-- TEXTUAL-CONVENTION
--  Status
--    mandatory
--  Descr
--    The downstream line rate at which an ADSL line can train at, 
--    given an ATU-C and ATU-R implementing the CAP line code.

AdslLineCapUpstreamRate ::= INTEGER(0|91000|272000|408000|544000|680000|816000|952000|1088000)
-- TEXTUAL-CONVENTION
--  Status
--    mandatory
--  Descr
--    The upstream line rate at which an ADSL line can train at, 
--    given an ATU-C and ATU-R implementing the CAP line code.

cAdslAtucCapPhysTable OBJECT-TYPE
    SYNTAX SEQUENCE OF CAdslAtucCapPhysEntry
    ACCESS not-accessible
    STATUS mandatory
    DESCRIPTION
        "This table extends the adslAtucPhysTable and contains
        enterprise-specific physical layer parameters for the ATU-C
        class devices supported by the system."
    ::= { ciscoAdslLineCapMIBObjects 2 }

cAdslAtucCapPhysEntry OBJECT-TYPE
    SYNTAX CAdslAtucCapPhysEntry
    ACCESS not-accessible
    STATUS mandatory
    DESCRIPTION
        "A set of enterprise-specific physical-layer parameters for an
        ATU-C class device supported by the system.  There exists an
        entry for each ifEntry with an ifType of adsl(94) and an
        adslLineCoding of cap(3)."
    INDEX { ifIndex }
    ::= { cAdslAtucCapPhysTable 1 }

CAdslAtucCapPhysEntry ::= SEQUENCE {
    cAdslAtucCapCurrState INTEGER,
    cAdslAtucCapCurrRxGain Gauge,
    cAdslAtucCapCurrRxSnr Gauge
    }

cAdslAtucCapCurrState OBJECT-TYPE
    SYNTAX INTEGER {
        other(1),
        idle(2),
        training(3),
        steadyState(4),
        downloading(5),
        downloadFailed(6),
        testing(7)
        }
    ACCESS read-only
    STATUS mandatory
    DESCRIPTION
        "This object specifies the state of the ATU-C transceiver.
        
        The value of this managed is 'idle' for an ATU-C that has
        been provisioned, but is not physically present in the system."
    ::= { cAdslAtucCapPhysEntry 1 }

cAdslAtucCapCurrRxGain OBJECT-TYPE
    SYNTAX Gauge
--  Units
--    tenth dB
    ACCESS read-only
    STATUS mandatory
    DESCRIPTION
        "This managed object represents the gain applied to the ATU-C
        receiver.
        
        The value of this managed object is '0' for an ATU-C that has
        been provisioned, but is not physically present in the system."
    ::= { cAdslAtucCapPhysEntry 2 }

cAdslAtucCapCurrRxSnr OBJECT-TYPE
    SYNTAX Gauge
--  Units
--    tenth dB
    ACCESS read-only
    STATUS mandatory
    DESCRIPTION
        "This managed object represents the signal-to-noise ratio
        measured across the the ATU-C receive pair.
        
        The value of this managed object is '0' for an ATU-C that has
        been provisioned, but is not physically present in the system."
    ::= { cAdslAtucCapPhysEntry 3 }

cAdslAturCapPhysTable OBJECT-TYPE
    SYNTAX SEQUENCE OF CAdslAturCapPhysEntry
    ACCESS not-accessible
    STATUS mandatory
    DESCRIPTION
        "This table extends the adslAturPhysTable and contains
        enterprise-specific physical layer parameters for the ATU-R
        class devices supported by the system."
    ::= { ciscoAdslLineCapMIBObjects 3 }

cAdslAturCapPhysEntry OBJECT-TYPE
    SYNTAX CAdslAturCapPhysEntry
    ACCESS not-accessible
    STATUS mandatory
    DESCRIPTION
        "A set of enterprise-specific physical-layer parameters for an
        ATU-R class device supported by the system.  There exists an
        entry for each ifEntry with an ifType of adsl(94) and an
        adslLineCoding of cap(3)."
    INDEX { ifIndex }
    ::= { cAdslAturCapPhysTable 1 }

CAdslAturCapPhysEntry ::= SEQUENCE {
    cAdslAturCapCurrRxGain Gauge
    }

cAdslAturCapCurrRxGain OBJECT-TYPE
    SYNTAX Gauge
--  Units
--    tenth dB
    ACCESS read-only
    STATUS mandatory
    DESCRIPTION
        "This managed object represents the gain applied to the ATU-R
        receiver.
        
        The value of this managed object is '0' if the corresponding
        ATU-C has been provisioned, but is not physically present in
        the system."
    ::= { cAdslAturCapPhysEntry 1 }

cAdslAtucCapPerfDataTable OBJECT-TYPE
    SYNTAX SEQUENCE OF CAdslAtucCapPerfDataEntry
    ACCESS not-accessible
    STATUS mandatory
    DESCRIPTION
        "This table extends the adslAtucPerfDataTable and contains
        enterprise-specific physical layer statistics for the ATU-C
        class devices supported by the system."
    ::= { ciscoAdslLineCapMIBObjects 6 }

cAdslAtucCapPerfDataEntry OBJECT-TYPE
    SYNTAX CAdslAtucCapPerfDataEntry
    ACCESS not-accessible
    STATUS mandatory
    DESCRIPTION
        "A set of enterprise-specific physical-layer statistics for an 
        ATU-C class device supported by the system.  There exists an
        entry for each ifEntry with an ifType of adsl(94) and an
        adslLineCoding of cap(3)."
    INDEX { ifIndex }
    ::= { cAdslAtucCapPerfDataTable 1 }

CAdslAtucCapPerfDataEntry ::= SEQUENCE {
    cAdslAtucCapPerfInitFailures Counter,
    cAdslAtucCapPerfCurr15MinInitFailures PerfCurrentCount,
    cAdslAtucCapPerfCurr1DayInitFailures AdslPerfCurrDayCount,
    cAdslAtucCapPerfPrev1DayInitFailures AdslPerfPrevDayCount
    }

cAdslAtucCapPerfInitFailures OBJECT-TYPE
    SYNTAX Counter
    ACCESS read-only
    STATUS mandatory
    DESCRIPTION
        "This object specifies the number of line initialization
        failures relative to sysUpTime."
    ::= { cAdslAtucCapPerfDataEntry 1 }

cAdslAtucCapPerfCurr15MinInitFailures OBJECT-TYPE
    SYNTAX PerfCurrentCount
--    Rsyntax Gauge
    ACCESS read-only
    STATUS mandatory
    DESCRIPTION
        "This object specifies the number of line initialization
        failures in the current 15-minute interval."
    ::= { cAdslAtucCapPerfDataEntry 2 }

cAdslAtucCapPerfCurr1DayInitFailures OBJECT-TYPE
    SYNTAX AdslPerfCurrDayCount
--    Rsyntax Gauge
    ACCESS read-only
    STATUS mandatory
    DESCRIPTION
        "This object specifies the number of line initialization
        failures in the current 1-day interval."
    ::= { cAdslAtucCapPerfDataEntry 3 }

cAdslAtucCapPerfPrev1DayInitFailures OBJECT-TYPE
    SYNTAX AdslPerfPrevDayCount
--    Rsyntax Gauge
    ACCESS read-only
    STATUS mandatory
    DESCRIPTION
        "This object specifies the number of line initialization
        failures in the previous 1-day interval."
    ::= { cAdslAtucCapPerfDataEntry 4 }

cAdslAtucCapIntervalTable OBJECT-TYPE
    SYNTAX SEQUENCE OF CAdslAtucCapIntervalEntry
    ACCESS not-accessible
    STATUS mandatory
    DESCRIPTION
        "This table extends the adslAtucIntervalTable and contains
        enterprise-specific physical layer statistics intervals for
        the ATU-C class devices supported by the system."
    ::= { ciscoAdslLineCapMIBObjects 8 }

cAdslAtucCapIntervalEntry OBJECT-TYPE
    SYNTAX CAdslAtucCapIntervalEntry
    ACCESS not-accessible
    STATUS mandatory
    DESCRIPTION
        "A 15-minute interval of enterprise-specific physical-layer
        statistics for an ATU-C class device supported by the system.
        There exists up to 96 entries for each ifEntry with an ifType
        of adsl(94) and an adslLineCoding of cap(3)."
    INDEX { ifIndex, adslAtucIntervalNumber }
    ::= { cAdslAtucCapIntervalTable 1 }

CAdslAtucCapIntervalEntry ::= SEQUENCE {
    cAdslAtucCapIntervalInitFailures PerfIntervalCount
    }

cAdslAtucCapIntervalInitFailures OBJECT-TYPE
    SYNTAX PerfIntervalCount
--    Rsyntax Gauge
    ACCESS read-only
    STATUS mandatory
    DESCRIPTION
        "This object specifies the number of line initialization
        failures in the interval."
    ::= { cAdslAtucCapIntervalEntry 1 }

cAdslLineCapConfProfileTable OBJECT-TYPE
    SYNTAX SEQUENCE OF CAdslLineCapConfProfileEntry
    ACCESS not-accessible
    STATUS mandatory
    DESCRIPTION
        "This table extends the adslLineConfProfileTable and contains
        enterprise-specific ADSL line configuration information."
    ::= { ciscoAdslLineCapMIBObjects 14 }

cAdslLineCapConfProfileEntry OBJECT-TYPE
    SYNTAX CAdslLineCapConfProfileEntry
    ACCESS not-accessible
    STATUS mandatory
    DESCRIPTION
        "A configuration profile containing enterprise-specific ADSL
        line configuration information."
    INDEX { --?? IMPLIED may cause problems
            IMPLIED adslLineConfProfileName }
    ::= { cAdslLineCapConfProfileTable 1 }

CAdslLineCapConfProfileEntry ::= SEQUENCE {
    cAdslLineCapConfTrainingMode INTEGER,
    cAdslLineCapConfInterleaveDelay INTEGER,
    cAdslLineCapConfCpeSignature INTEGER,
    cAdslAtucCapConfTargetSnrMgn INTEGER,
    cAdslAtucCapConfMinTxRate AdslLineCapDownstreamRate,
    cAdslAtucCapConfMaxTxRate AdslLineCapDownstreamRate,
    cAdslAtucCapConfDown136KBaudEnable TruthValue,
    cAdslAtucCapConfUp68KBaudEnable TruthValue,
    cAdslAtucCapConfUp17KBaudEnable TruthValue,
    cAdslAtucCapConfPsdmLevel INTEGER,
    cAdslAturCapConfTargetSnrMgn INTEGER,
    cAdslAturCapConfMinTxRate AdslLineCapUpstreamRate,
    cAdslAturCapConfMaxTxRate AdslLineCapUpstreamRate,
    cAdslAturCapConfPsdmLevel INTEGER
    }

cAdslLineCapConfTrainingMode OBJECT-TYPE
    SYNTAX INTEGER {
        standard(1),
        fast(2)
        }
    ACCESS read-write
    STATUS mandatory
    DESCRIPTION
        "This object specifies the mode employed by the ATU-C and
        ATU-R when training against each other.  One of two training
        modes can be employed:
        
        - Standard
            An ATU-C initiates a training sequence using the method
            defined by T1E1.4/99-161R3.  This training mode is the
            default for ADSL modems employing the CAP line code.
        
        - Fast
            An ATU-C initiates a vendor-specific training sequence that
            can possibly provide a shorter training sequence."
    REFERENCE
        "ANSI T1E1.4/99-161R3, Single-Carrier Rate Adaptive Digital
        Subscriber Line (RADSL)."
    DEFVAL { standard }
    ::= { cAdslLineCapConfProfileEntry 1 }

cAdslLineCapConfInterleaveDelay OBJECT-TYPE
    SYNTAX INTEGER {
        none(1),
        short(2),
        long(3)
        }
    ACCESS read-write
    STATUS mandatory
    DESCRIPTION
        "This object specifies the interleave delay for the
        downstream channel.  The value of this object specifies the
        mapping (relative spacing) between subsequent input bytes at
        the interleaver input and their placement in the bit stream
        at the interleaver output.  The value 'long' provides greater
        separation between consecutive input bytes in the output bit
        stream, thereby allowing for improved impulse noise immunity
        at the expense of payload latency."
    REFERENCE
        "ANSI T1E1.4/99-161R3, Single-Carrier Rate Adaptive Digital
        Subscriber Line (RADSL)."
    DEFVAL { short }
    ::= { cAdslLineCapConfProfileEntry 2 }

cAdslLineCapConfCpeSignature OBJECT-TYPE
    SYNTAX INTEGER(0..127)
    ACCESS read-write
    STATUS mandatory
    DESCRIPTION
        "This object specifies the value of the minimum CPE signature
        expected from ATU-R during training.  The value of the CPE
        signature corresponds to the software version of the ATU-R.
        
        If the CPE signature advertised by an ATU-R is less than the
        value of this object, then the ATU-C will be placed into an
        idle state, thereby preventing the line from training.
        
        In addition, the agent increments the value of the
        cAdslAtucCapPerfInitFailures object for each attempt to train
        by an ATU-R advertising a CPE signature less than the value of
        this object.  When a management client observes the value of
        cAdslAtucCapPerfInitFailures increasing, it should retrieve the
        value of the adslAturInvSerialNumber object (for more details,
        see the ADSL-LINE-MIB) .  This value of this object reflects the
        CPE signature advertised by an ATU-R implementing the CAP line
        code.  If the CPE signature of the ATU-R is not known, the value
        of the adslAturInvSerialNumber object should be a zero-length
        string."
    DEFVAL { 0 }
    ::= { cAdslLineCapConfProfileEntry 3 }

cAdslAtucCapConfTargetSnrMgn OBJECT-TYPE
    SYNTAX INTEGER(0..310)
--  Units
--    tenth dB
    ACCESS read-write
    STATUS mandatory
    DESCRIPTION
        "This object specifies the target SNR margin.  This is the
        desired noise margin the ATU-C must achieve with a BER of
        10-7 or better to successfully complete training."
    DEFVAL { 60 }
    ::= { cAdslLineCapConfProfileEntry 4 }

cAdslAtucCapConfMinTxRate OBJECT-TYPE
    SYNTAX AdslLineCapDownstreamRate
--    Rsyntax INTEGER(0|256000|384000|512000|640000|768000|896000|960000|1024000|1280000|1600000|1920000|2240000|2560000|2688000|3200000|4480000|5120000|6272000|7168000)
--  Units
--    bps
    ACCESS read-write
    STATUS mandatory
    DESCRIPTION
        "This object specifies the minimum acceptable downstream
        line rate."
    DEFVAL { 0 }
    ::= { cAdslLineCapConfProfileEntry 5 }

cAdslAtucCapConfMaxTxRate OBJECT-TYPE
    SYNTAX AdslLineCapDownstreamRate
--    Rsyntax INTEGER(0|256000|384000|512000|640000|768000|896000|960000|1024000|1280000|1600000|1920000|2240000|2560000|2688000|3200000|4480000|5120000|6272000|7168000)
--  Units
--    bps
    ACCESS read-write
    STATUS mandatory
    DESCRIPTION
        "This object specifies the desired line rate which the ATU-C
        will attempt to train at."
    DEFVAL { 640000 }
    ::= { cAdslLineCapConfProfileEntry 6 }

cAdslAtucCapConfDown136KBaudEnable OBJECT-TYPE
    SYNTAX TruthValue
--    Rsyntax INTEGER {
--        true(1),
--        false(2)
--        }
    ACCESS read-write
    STATUS mandatory
    DESCRIPTION
        "This object specifies whether the modem can train the
        downstream channel using a symbol rate of 136K symbols
        per second."
    REFERENCE
        "ANSI T1E1.4/99-161R3, Single-Carrier Rate Adaptive Digital
        Subscriber Line (RADSL)."
    DEFVAL { true }
    ::= { cAdslLineCapConfProfileEntry 7 }

cAdslAtucCapConfUp68KBaudEnable OBJECT-TYPE
    SYNTAX TruthValue
--    Rsyntax INTEGER {
--        true(1),
--        false(2)
--        }
    ACCESS read-write
    STATUS mandatory
    DESCRIPTION
        "This object specifies whether the modem can train the
        upstream channel using a symbol rate of 68K symbols
        per second.
        
        The value of this object does not effect whether the modem
        can train at any other symbol rate; that is, the values of
        this object and cAdslAtucCapConfUp17KBaudEnable are not
        mutually exclusive."
    REFERENCE
        "ANSI T1E1.4/99-161R3, Single-Carrier Rate Adaptive Digital
        Subscriber Line (RADSL)."
    DEFVAL { true }
    ::= { cAdslLineCapConfProfileEntry 8 }

cAdslAtucCapConfUp17KBaudEnable OBJECT-TYPE
    SYNTAX TruthValue
--    Rsyntax INTEGER {
--        true(1),
--        false(2)
--        }
    ACCESS read-write
    STATUS mandatory
    DESCRIPTION
        "This object specifies whether the modem can train the
        upstream channel using a symbol rate of 17K symbols
        per second.
        
        The value of this object does not effect whether the modem
        can train at any other symbol rate; that is, the values of
        this object and cAdslAtucCapConfUp68KBaudEnable are not
        mutually exclusive."
    REFERENCE
        "ANSI T1E1.4/99-161R3, Single-Carrier Rate Adaptive Digital
        Subscriber Line (RADSL)."
    DEFVAL { true }
    ::= { cAdslLineCapConfProfileEntry 9 }

cAdslAtucCapConfPsdmLevel OBJECT-TYPE
    SYNTAX INTEGER(-52|-49|-46|-43|-40|-37)
--  Units
--    dBm/Hz
    ACCESS read-write
    STATUS mandatory
    DESCRIPTION
        "This managed object specifies the nominal power output of the
        ATU-C across the entire transmit spectrum.  Observe that this
        implies the attenuation of the signal for some data rates.
        
        This value does not take effect until the modem has retrained
        against the ATU-C to which the ATU-R has a connection."
    REFERENCE
        "ANSI T1E1.4/99-161R3, Single-Carrier Rate Adaptive Digital
        Subscriber Line (RADSL)."
    DEFVAL { -40 }
    ::= { cAdslLineCapConfProfileEntry 10 }

cAdslAturCapConfTargetSnrMgn OBJECT-TYPE
    SYNTAX INTEGER(0..310)
--  Units
--    tenth dB
    ACCESS read-write
    STATUS mandatory
    DESCRIPTION
        "This object specifies the target SNR margin.  This is the
        desired noise margin the ATU-R must achieve with a BER of
        10-7 or better to successfully complete training."
    DEFVAL { 60 }
    ::= { cAdslLineCapConfProfileEntry 11 }

cAdslAturCapConfMinTxRate OBJECT-TYPE
    SYNTAX AdslLineCapUpstreamRate
--    Rsyntax INTEGER(0|91000|272000|408000|544000|680000|816000|952000|1088000)
--  Units
--    bps
    ACCESS read-write
    STATUS mandatory
    DESCRIPTION
        "This object specifies the minimum acceptable upstream
        line rate."
    DEFVAL { 0 }
    ::= { cAdslLineCapConfProfileEntry 12 }

cAdslAturCapConfMaxTxRate OBJECT-TYPE
    SYNTAX AdslLineCapUpstreamRate
--    Rsyntax INTEGER(0|91000|272000|408000|544000|680000|816000|952000|1088000)
--  Units
--    bps
    ACCESS read-write
    STATUS mandatory
    DESCRIPTION
        "This object specifies the desired line rate which the ATU-R
        will attempt to train at."
    DEFVAL { 91000 }
    ::= { cAdslLineCapConfProfileEntry 13 }

cAdslAturCapConfPsdmLevel OBJECT-TYPE
    SYNTAX INTEGER(-53|-50|-47|-44|-41|-38)
--  Units
--    dBm/Hz
    ACCESS read-write
    STATUS mandatory
    DESCRIPTION
        "This managed object specifies the nominal power output of the
        ATU-R across the entire transmit spectrum.  Observe that this
        implies the attenuation of the signal for some data rates.
        
        This value does not take effect until the modem has retrained 
        against the ATU-C to which the ATU-R has a connection."
    REFERENCE
        "ANSI T1E1.4/99-161R3, Single-Carrier Rate Adaptive Digital
        Subscriber Line (RADSL)."
    DEFVAL { -38 }
    ::= { cAdslLineCapConfProfileEntry 14 }

cAdslAtucCapBasicGroup OBJECT IDENTIFIER ::= { ciscoAdslLineCapMIBGroups 1 }
-- OBJECT-GROUP
--  Status
--    mandatory
--  Descr
--    A collection of managed objects defining the basic operation
--    of an ATU-C implementing the CAP line code.
--  objects
--    cAdslAtucCapCurrState, cAdslAtucCapCurrRxGain, 
--    cAdslAtucCapCurrRxSnr, cAdslAtucCapPerfInitFailures, 
--    cAdslLineCapConfTrainingMode, cAdslLineCapConfInterleaveDelay, 
--    cAdslLineCapConfCpeSignature, cAdslAtucCapConfTargetSnrMgn, 
--    cAdslAtucCapConfMinTxRate, cAdslAtucCapConfMaxTxRate, 
--    cAdslAtucCapConfDown136KBaudEnable, 
--    cAdslAtucCapConfUp68KBaudEnable, 
--    cAdslAtucCapConfUp17KBaudEnable, cAdslAtucCapConfPsdmLevel

cAdslAturBasicGroup OBJECT IDENTIFIER ::= { ciscoAdslLineCapMIBGroups 2 }
-- OBJECT-GROUP
--  Status
--    mandatory
--  Descr
--    A collection of managed objects defining the basic operation
--    of an ATU-R implementing the CAP line code.
--  objects
--    cAdslAturCapCurrRxGain, cAdslLineCapConfTrainingMode, 
--    cAdslAturCapConfTargetSnrMgn, cAdslAturCapConfMinTxRate, 
--    cAdslAturCapConfMaxTxRate, cAdslAturCapConfPsdmLevel

cAdslAturCapGroup OBJECT IDENTIFIER ::= { ciscoAdslLineCapMIBGroups 3 }
-- OBJECT-GROUP
--  Status
--    mandatory
--  Descr
--    A collection of managed objects defining the capability to
--    remotely manage a ATU-R.
--  objects
--    cAdslAturCapCurrRxGain, cAdslAturCapConfTargetSnrMgn, 
--    cAdslAturCapConfMinTxRate, cAdslAturCapConfMaxTxRate, 
--    cAdslAturCapConfPsdmLevel

cAdslAtucCapPM15MinIntervalGroup OBJECT IDENTIFIER ::= { ciscoAdslLineCapMIBGroups 4 }
-- OBJECT-GROUP
--  Status
--    mandatory
--  Descr
--    A collection of managed objects defining near-end performance
--    data collection capability using 15-minute intervals.
--  objects
--    cAdslAtucCapPerfCurr15MinInitFailures, 
--    cAdslAtucCapIntervalInitFailures

cAdslAtucCapPM1DayIntervalGroup OBJECT IDENTIFIER ::= { ciscoAdslLineCapMIBGroups 5 }
-- OBJECT-GROUP
--  Status
--    mandatory
--  Descr
--    A collection of managed objects defining near-end performance
--    data collection capability using 1-day intervals.
--  objects
--    cAdslAtucCapPerfCurr1DayInitFailures, 
--    cAdslAtucCapPerfPrev1DayInitFailures

ciscoAdslLineCapMIBAtucCompliance OBJECT IDENTIFIER ::= { ciscoAdslLineCapMIBCompliances 1 }
-- MODULE-COMPLIANCE
--  Status
--    mandatory
--  Descr
--    The compliance statement for entities that implement the
--    CISCO-ADSL-CAP-LINE-MIB.  Implementation of this MIB is
--    mandatory for any platform that supports one or more ADSL
--    line interfaces that implement the CAP line code.
--  Module
--    >>current<<
--   MandGroup
--    cAdslAtucCapBasicGroup
--   OptGroup
--    cAdslAturCapGroup
--   OptGroup
--    cAdslAtucCapPM15MinIntervalGroup
--   OptGroup
--    cAdslAtucCapPM1DayIntervalGroup

ciscoAdslLineCapMIBAturCompliance OBJECT IDENTIFIER ::= { ciscoAdslLineCapMIBCompliances 2 }
-- MODULE-COMPLIANCE
--  Status
--    mandatory
--  Descr
--    The compliance statement for entities that implement the
--    CISCO-ADSL-CAP-LINE-MIB and manage ADSL ATU-R class devices.
--    Implementation of this MIB is mandatory for any platform
--    that supports one or more ADSL line interfaces that implement
--    the CAP line code.
--  Module
--    >>current<<
--   MandGroup
--    cAdslAturBasicGroup


END
