-- MIB file created 17-May-2011 10:59:39, by
--   SMICng version 2.2.11-beta(PRO)(Solaris), January 20, 2001. Enterprise key cisco.com

CISCO-PPPOE-MIB DEFINITIONS ::= BEGIN

-- From file: "CISCO-PPPOE-MIB.my"
-- Compile options "4 7 F H N W 03 06 0B 0G 0N 0T"

IMPORTS
    ciscoMgmt
            FROM CISCO-SMI
    MacAddress, TruthValue
            FROM SNMPv2-TC-v1
    ifIndex, ifDescr
            FROM IF-MIB
    atmVclVpi, atmVclVci
--?? may need import of ifIndex from IF-MIB
            FROM ATM-MIB
    Percent
            FROM CISCO-QOS-PIB-MIB
    AtmVpIdentifier, AtmVcIdentifier
            FROM ATM-TC-MIB
    VlanId, VlanIndex
            FROM Q-BRIDGE-MIB
    Counter, Gauge
            FROM RFC1155-SMI
    OBJECT-TYPE
            FROM RFC-1212
    TRAP-TYPE
            FROM RFC-1215;

ciscoPppoeMIB OBJECT IDENTIFIER ::= { ciscoMgmt 194 }
-- MODULE-IDENTITY
--  LastUpdated
--    201104250000Z
--  OrgName
--    Cisco Systems, Inc.
--  ContactInfo
--                Cisco Systems
--                 Customer Service
--    
--     Postal:     170 W Tasman Drive 
--                 San Jose, CA 95134
--                 USA 
--    
--        Tel:     +1 800 553-NETS
--    
--     E-mail:     cs-ppp@cisco.com
--  Descr
--    Cisco PPPoE sessions management MIB Module.
--  RevDate
--    201104250000Z
--  RevDescr
--    Added following new groups
--        cPppoePerInterfaceGroup,
--        cPppoeSystemLimitsThresholdsNotifObjectsGroup
--        cPppoeSystemLimitsThresholdsNotifGroup and
--        cPppoeSystemLimitsThresholdsGroup.
--    Added a new compliance ciscoPppoeMIBBasicComplianceRev1 which 
--    deprecates ciscoPppoeMIBBasicCompliance. 
--  RevDate
--    200512210000Z
--  RevDescr
--    Updated the imports such that Unsigned32 is imported
--    from SNMPv2-SMI instead of CISCO-TC.
--  RevDate
--    200102200000Z
--  RevDescr
--    Initial version of this MIB module.

ciscoPppoeMIBObjects OBJECT IDENTIFIER ::= { ciscoPppoeMIB 1 }
cPppoeSystemSessionInfo OBJECT IDENTIFIER ::= { ciscoPppoeMIBObjects 1 }
cPppoeVcCfgInfo OBJECT IDENTIFIER ::= { ciscoPppoeMIBObjects 2 }
cPppoeVcSessionsInfo OBJECT IDENTIFIER ::= { ciscoPppoeMIBObjects 3 }
cPppoeSessionsPerInterfaceInfo OBJECT IDENTIFIER ::= { ciscoPppoeMIBObjects 4 }
cPppoeSystemSessionNotifyObjects OBJECT IDENTIFIER ::= { ciscoPppoeMIBObjects 5 }
ciscoPppoeMIBNotificationPrefix OBJECT IDENTIFIER ::= { ciscoPppoeMIB 2 }
ciscoPppoeMIBNotification OBJECT IDENTIFIER ::= { ciscoPppoeMIBNotificationPrefix 0 }
ciscoPppoeMIBConformance OBJECT IDENTIFIER ::= { ciscoPppoeMIB 3 }
ciscoPppoeMIBCompliances OBJECT IDENTIFIER ::= { ciscoPppoeMIBConformance 1 }
ciscoPppoeMIBGroups OBJECT IDENTIFIER ::= { ciscoPppoeMIBConformance 2 }

cPppoeSystemCurrSessions OBJECT-TYPE
    SYNTAX Gauge
--  Units
--    sessions
    ACCESS read-only
    STATUS mandatory
    DESCRIPTION
        "The current number of active PPPoE sessions within 
         this system."
    ::= { cPppoeSystemSessionInfo 1 }

cPppoeSystemHighWaterSessions OBJECT-TYPE
    SYNTAX Gauge
--  Units
--    sessions
    ACCESS read-only
    STATUS mandatory
    DESCRIPTION
        "The high water mark of the established PPPoE 
         sessions since the system was initialized."
    ::= { cPppoeSystemSessionInfo 2 }

cPppoeSystemMaxAllowedSessions OBJECT-TYPE
    SYNTAX Gauge
--  Units
--    sessions
    ACCESS read-write
    STATUS mandatory
    DESCRIPTION
        "Maximum number of allowed PPPoE sessions within
         the system."
    ::= { cPppoeSystemSessionInfo 3 }

cPppoeSystemThresholdSessions OBJECT-TYPE
    SYNTAX Gauge
--  Units
--    sessions
    ACCESS read-write
    STATUS mandatory
    DESCRIPTION
        "Threshold value of the established PPPoE sessions 
         within the system. Default value is equal to
         cPppoeSystemMaxSessionsConfigurable"
    ::= { cPppoeSystemSessionInfo 4 }

cPppoeSystemExceededSessionErrors OBJECT-TYPE
    SYNTAX Counter
    ACCESS read-only
    STATUS mandatory
    DESCRIPTION
        "The accumulated number of errors for 
         establishing PPPoE session in the system due 
         to the cPppoeSystemCurrSessions value exceeds 
         the cPppoeSystemMaxAllowedSessions value."
    ::= { cPppoeSystemSessionInfo 5 }

cPppoeSystemPerMacSessionlimit OBJECT-TYPE
    SYNTAX Gauge
    ACCESS read-write
    STATUS mandatory
    DESCRIPTION
        "This object provides limit on number of PPPoE sessions
         for a single client Ethernet MAC address. If the limit 
         is reached new session request from the client would 
         be denied"
    ::= { cPppoeSystemSessionInfo 6 }

cPppoeSystemPerMacIWFSessionlimit OBJECT-TYPE
    SYNTAX Gauge
    ACCESS read-write
    STATUS mandatory
    DESCRIPTION
        "This object provides limit on number of PPPoE sessions 
         with interworking flag(IWF) enabled, from a single client
         MAC address. If the limit is reached new session request 
         would be denied."
    ::= { cPppoeSystemSessionInfo 7 }

cPppoeSystemPerMacThrottleRatelimit OBJECT-TYPE
    SYNTAX Gauge
    ACCESS read-write
    STATUS mandatory
    DESCRIPTION
        "This object provides the rate limit at which PPPoE 
         session were created from a single client MAC address. 
         During a configured time interval, once the number of 
         new session requests coming from a particular client 
         MAC address reaches this limit, it's expected to have 
         delay in response for those clients."
    ::= { cPppoeSystemSessionInfo 8 }

cPppoeSystemPerVLANlimit OBJECT-TYPE
    SYNTAX Gauge
    ACCESS read-write
    STATUS mandatory
    DESCRIPTION
        "This object provides limit on number of PPPoE sessions 
         on a particular Vlan. If the limit is reached new session 
         request on this vlan would be denied."
    ::= { cPppoeSystemSessionInfo 9 }

cPppoeSystemPerVLANthrottleRatelimit OBJECT-TYPE
    SYNTAX Gauge
    ACCESS read-write
    STATUS mandatory
    DESCRIPTION
        "This object provides the rate limit at which PPPoE 
         session were created on a Vlan. During a configured
         time interval once the number of new session requests 
         coming on a particular Vlan reaches this limit, 
         it's expected to have delay in response for client 
         on this Vlan."
    ::= { cPppoeSystemSessionInfo 10 }

cPppoeSystemPerVClimit OBJECT-TYPE
    SYNTAX Gauge
    ACCESS read-write
    STATUS mandatory
    DESCRIPTION
        "This object provides limit on number of PPPoE sessions on 
         a particular ATM-VC. If the limit is reached new session 
         request on this VC would be denied."
    ::= { cPppoeSystemSessionInfo 11 }

cPppoeSystemPerVCThrottleRatelimit OBJECT-TYPE
    SYNTAX Gauge
    ACCESS read-write
    STATUS mandatory
    DESCRIPTION
        "This object provides the rate limit at which PPPoE 
         session were created on an ATM-VC. During a configured 
         time interval, once the number of new session requests 
         coming on an ATM-VC reaches this limit, it's expected to 
         have delay in response for those clients on this VC."
    ::= { cPppoeSystemSessionInfo 12 }

cPppoeSystemSessionLossThreshold OBJECT-TYPE
    SYNTAX Gauge
    ACCESS read-write
    STATUS mandatory
    DESCRIPTION
        "This object is used to monitor number of active PPPoE 
         sessions above a healthy watermark. If number of PPPoE
         sessions falls below this watermark then we can expect
         something wrong happened.  So we send out trap to user
         indicating session loss below watermark."
    ::= { cPppoeSystemSessionInfo 13 }

cPppoeSystemSessionLossPercent OBJECT-TYPE
    SYNTAX Percent
--    Rsyntax INTEGER(0..100)
    ACCESS read-write
    STATUS mandatory
    DESCRIPTION
        "This object is used to monitor the percentage of PPPoE 
         sessions going down at a configured time interval.
            
         During a time interval if percentage of PPPoE sessions 
         lost, falls above this object value, we send trap 
         indicating loss of sessions above percentage expected."
    ::= { cPppoeSystemSessionInfo 14 }

cPppoeSystemSessionClientMacAddress OBJECT-TYPE
    SYNTAX MacAddress
--    Rsyntax OCTET STRING(SIZE(6))
    ACCESS not-accessible
    STATUS mandatory
    DESCRIPTION
        "The client MAC address that is referred as a part
                of the notification information.
                Example: cPppoeSystemSessionPerMACLimitNotif"
    ::= { cPppoeSystemSessionNotifyObjects 1 }

cPppoeSystemSessionVlanID OBJECT-TYPE
    SYNTAX VlanId
--    Rsyntax INTEGER(1..4094)
    ACCESS not-accessible
    STATUS mandatory
    DESCRIPTION
        "The Vlan ID of PPPoE session that is referred as a 
                part of the notification information.
                Example: cPppoeSystemSessionPerVLANLimitNotif"
    ::= { cPppoeSystemSessionNotifyObjects 2 }

cPppoeSystemSessionInnerVlanID OBJECT-TYPE
    SYNTAX VlanIndex
--    Rsyntax Gauge
    ACCESS not-accessible
    STATUS mandatory
    DESCRIPTION
        "The inner Vlan ID of PPPoE QinQ session that is referred
                as a part of the notification information.
        
                Example: cPppoeSystemSessionPerVLANLimitNotif"
    ::= { cPppoeSystemSessionNotifyObjects 3 }

cPppoeSystemSessionVci OBJECT-TYPE
    SYNTAX AtmVcIdentifier
--    Rsyntax INTEGER(0..65535)
    ACCESS not-accessible
    STATUS mandatory
    DESCRIPTION
        "The ATM VCI of PPPoE session that is referred as a part
         of the  notification information.
        Example:cPppoeSystemSessionPerVCLimitTrap"
    ::= { cPppoeSystemSessionNotifyObjects 4 }

cPppoeSystemSessionVpi OBJECT-TYPE
    SYNTAX AtmVpIdentifier
--    Rsyntax INTEGER(0..4095)
    ACCESS not-accessible
    STATUS mandatory
    DESCRIPTION
        "The ATM VPI of PPPoE session that is referred as a part
         of the  notification information.
         Example: cPppoeSystemSessionPerVCLimitTrap"
    ::= { cPppoeSystemSessionNotifyObjects 5 }

cPppoeVcCfgTable OBJECT-TYPE
    SYNTAX SEQUENCE OF CPppoeVcCfgEntry
    ACCESS not-accessible
    STATUS mandatory
    DESCRIPTION
        "The table contains the PPPoE protocol related 
         configuration for the VCLs(ATM Interface 
         Virtual Channel Link)."
    ::= { cPppoeVcCfgInfo 1 }

cPppoeVcCfgEntry OBJECT-TYPE
    SYNTAX CPppoeVcCfgEntry
    ACCESS not-accessible
    STATUS mandatory
    DESCRIPTION
        "An entry containing additional PPPoE protocol 
         configuration related management information
         applicable to a particular VCL."
    INDEX { ifIndex, atmVclVpi, atmVclVci }
-- Augments atmVclEntry FROM ATM-MIB
    ::= { cPppoeVcCfgTable 1 }

CPppoeVcCfgEntry ::= SEQUENCE {
    cPppoeVcEnable TruthValue
    }

cPppoeVcEnable OBJECT-TYPE
    SYNTAX TruthValue
--    Rsyntax INTEGER {
--        true(1),
--        false(2)
--        }
    ACCESS read-write
    STATUS mandatory
    DESCRIPTION
        "This object specifies whether the PPPoE protocol
         should be enabled for this VCL. If the value of 
         this object is `false`, PPPoE protocol is 
         disabled; otherwise the PPPoE protocol is
         enabled."
    DEFVAL { false }
    ::= { cPppoeVcCfgEntry 1 }

cPppoeVcSessionsTable OBJECT-TYPE
    SYNTAX SEQUENCE OF CPppoeVcSessionsEntry
    ACCESS not-accessible
    STATUS mandatory
    DESCRIPTION
        "Table of configuration and statistics about the 
         number of PPPoE sessions on a list of VCLs(ATM 
         Interface Virtual Channel Link)."
    ::= { cPppoeVcSessionsInfo 1 }

cPppoeVcSessionsEntry OBJECT-TYPE
    SYNTAX CPppoeVcSessionsEntry
    ACCESS not-accessible
    STATUS mandatory
    DESCRIPTION
        "An entry in the table containing PPPoE session
         related information on a VCL. The entry of this
         table is created when the value of cPppoeVcEnable 
         object is set to `true` for the entry associated 
         VCL. The entry of this table is deleted when the
         of cPppoeVcEnable object set to `false` or the
         entry associated VCL is deleted from 
         atmVclTable."
    INDEX { ifIndex, atmVclVpi, atmVclVci }
    ::= { cPppoeVcSessionsTable 1 }

CPppoeVcSessionsEntry ::= SEQUENCE {
    cPppoeVcCurrSessions Gauge,
    cPppoeVcHighWaterSessions Gauge,
    cPppoeVcMaxAllowedSessions Gauge,
    cPppoeVcThresholdSessions Gauge,
    cPppoeVcExceededSessionErrors Counter
    }

cPppoeVcCurrSessions OBJECT-TYPE
    SYNTAX Gauge
--  Units
--    sessions
    ACCESS read-only
    STATUS mandatory
    DESCRIPTION
        "The current number of active PPPoE sessions on 
         the VCL."
    ::= { cPppoeVcSessionsEntry 1 }

cPppoeVcHighWaterSessions OBJECT-TYPE
    SYNTAX Gauge
--  Units
--    sessions
    ACCESS read-only
    STATUS mandatory
    DESCRIPTION
        "The high water mark of the established PPPoE 
         sessions on the VCL."
    ::= { cPppoeVcSessionsEntry 2 }

cPppoeVcMaxAllowedSessions OBJECT-TYPE
    SYNTAX Gauge
--  Units
--    sessions
    ACCESS read-write
    STATUS mandatory
    DESCRIPTION
        "The maximum number of allowed PPPoE sessions on 
         the VCL."
    ::= { cPppoeVcSessionsEntry 3 }

cPppoeVcThresholdSessions OBJECT-TYPE
    SYNTAX Gauge
--  Units
--    sessions
    ACCESS read-write
    STATUS mandatory
    DESCRIPTION
        "The Threshold value of the established PPPoE 
         sessions on the VCL. Default value is equal to 
         cPppoeVcMaxAllowedSessions."
    ::= { cPppoeVcSessionsEntry 4 }

cPppoeVcExceededSessionErrors OBJECT-TYPE
    SYNTAX Counter
--  Units
--    attempts
    ACCESS read-only
    STATUS mandatory
    DESCRIPTION
        "The accumulated number of errors for 
         establishing PPPoE session in the VC 
         due to the cPppoeVcCurrSessions value
         exceeds the cPppoeVcMaxAllowedSessions 
         value."
    ::= { cPppoeVcSessionsEntry 5 }

cPppoeSessionsPerInterfaceTable OBJECT-TYPE
    SYNTAX SEQUENCE OF CPppoeSessionsPerInterfaceEntry
    ACCESS not-accessible
    STATUS mandatory
    DESCRIPTION
        "A list of interfaces' PPPoE session information."
    ::= { cPppoeSessionsPerInterfaceInfo 1 }

cPppoeSessionsPerInterfaceEntry OBJECT-TYPE
    SYNTAX CPppoeSessionsPerInterfaceEntry
    ACCESS not-accessible
    STATUS mandatory
    DESCRIPTION
        "An entry in the table containing PPPoE sessions 
         information such as count information of various 
         states like PPP Termination Aggregation(PTA), 
         Forwarded(FWDED), Transient (TRANS) and TOTAL count and 
         the configured loss threshold per given physical 
         interface"
    INDEX { ifIndex }
    ::= { cPppoeSessionsPerInterfaceTable 1 }

CPppoeSessionsPerInterfaceEntry ::= SEQUENCE {
    cPppoeTotalSessions Gauge,
    cPppoePtaSessions Gauge,
    cPppoeFwdedSessions Gauge,
    cPppoeTransSessions Gauge,
    cPppoePerInterfaceSessionLossThreshold Gauge,
    cPppoePerInterfaceSessionLossPercent Gauge
    }

cPppoeTotalSessions OBJECT-TYPE
    SYNTAX Gauge
--  Units
--    sessions
    ACCESS read-only
    STATUS mandatory
    DESCRIPTION
        "The total number of PPPoE sessions which includes PPP
         Termination Aggregation(PTA), Forwarded(FWDED) and 
         Transient(TRANS) state on a physical interface. "
    ::= { cPppoeSessionsPerInterfaceEntry 1 }

cPppoePtaSessions OBJECT-TYPE
    SYNTAX Gauge
--  Units
--    sessions
    ACCESS read-only
    STATUS mandatory
    DESCRIPTION
        "Number of PPPoE sessions which are in PPP Termination  
         Aggregation(PTA) state on a particular physical 
        interface."
    ::= { cPppoeSessionsPerInterfaceEntry 2 }

cPppoeFwdedSessions OBJECT-TYPE
    SYNTAX Gauge
--  Units
--    sessions
    ACCESS read-only
    STATUS mandatory
    DESCRIPTION
        "Number of PPPoE sessions which are in Forwarded(FWDED)
         state on a particular physical interface."
    ::= { cPppoeSessionsPerInterfaceEntry 3 }

cPppoeTransSessions OBJECT-TYPE
    SYNTAX Gauge
--  Units
--    sessions
    ACCESS read-only
    STATUS mandatory
    DESCRIPTION
        "Number of PPPoE sessions which are in Transient(TRANS)
         state on a particular physical interface."
    ::= { cPppoeSessionsPerInterfaceEntry 4 }

cPppoePerInterfaceSessionLossThreshold OBJECT-TYPE
    SYNTAX Gauge
    ACCESS read-only
    STATUS mandatory
    DESCRIPTION
        "This object is used to monitor number of active PPPoE 
         sessions, initiated from a particular physical interface. 
         The sssion count is accumulation of all the pppoe session 
         came on a physical and its sub-interfaces. If this count 
         drops below this object water mark, we expect some 
         problem and send out trap indicating drop of sessions 
         below watermark."
    ::= { cPppoeSessionsPerInterfaceEntry 5 }

cPppoePerInterfaceSessionLossPercent OBJECT-TYPE
    SYNTAX Gauge
    ACCESS read-only
    STATUS mandatory
    DESCRIPTION
        "This object is used to monitor the percentage of PPPoE 
         sessions loss on a particular physical interface 
         including all of its sub-interfaces. If during a 
         configured interval of time, percentage of PPPoE 
         sessions lost on a physical interface is above this 
         object value we send a trap."
    ::= { cPppoeSessionsPerInterfaceEntry 6 }

cPppoeSystemSessionThresholdTrap TRAP-TYPE
-- Reverse mappable trap
    ENTERPRISE ciscoPppoeMIBNotificationPrefix
    VARIABLES {
        cPppoeSystemCurrSessions, cPppoeSystemMaxAllowedSessions, 
        cPppoeSystemThresholdSessions }
--  Status
--    mandatory
    DESCRIPTION
        "A notification indicating that number of active 
         sessions on the system exceeded system sessions 
         threshold value. System sessions threshold value 
         is indicated by cPppoeSystemThresholdSessions. 
        
         An  agent  must  not  generate  more  than  one
         cPppoeSessionThresholdTrap `trap-event` in a
         30 second period,  where a  `trap-event` is  the
         transmission of a single trap  PDU to a  list of
         trap destinations. If additional `the number of
         PPPoE  sessions  exceeds  threshold`  condition
         occur within the 30  second `throttling` period,
         then these  trap-events should be suppressed by
         the agent. An NMS should periodically check the
         value of  cPppoeCurrSessions to  detect  any
         missed cPppoeVcSessionThresholdTrap trap-events,
         e.g. due to throttling or transmission loss.
         Where 30 is the `throttling` period of trap-event."
    ::= 1

cPppoeVcSessionThresholdTrap TRAP-TYPE
-- Reverse mappable trap
    ENTERPRISE ciscoPppoeMIBNotificationPrefix
    VARIABLES {
        cPppoeVcCurrSessions, cPppoeVcMaxAllowedSessions, 
        cPppoeVcThresholdSessions }
--  Status
--    mandatory
    DESCRIPTION
        "A notification indicating that number of active 
         sessions on the  VC  exceeded vc sessions 
         threshold value. VC sessions threshold value is 
         indicated by cPppoeVcThresholdSessions.
        
         An  agent  must  not  generate  more  than  one
         cPppoeVcSessionThresholdTrap `trap-event` in a 
         30 second period,  where a  `trap-event` is  the
         transmission of a single trap  PDU to a  list of 
         trap destinations. If additional `the number of 
         PPPoE  sessions  exceeds  threshold`  condition 
         occur within the 30  second `throttling` period, 
         then these  trap-events should be suppressed by 
         the agent. An NMS should periodically check the 
         value of  cPppoeVcCurrSessions to  detect  any 
         missed cPppoeVcSessionThresholdTrap trap-events, 
         e.g. due to throttling or transmission loss. 
         Where 30 is the `throttling` period of trap-event."
    ::= 2

cPppoeSystemSessionPerMACLimitNotif TRAP-TYPE
-- Reverse mappable trap
    ENTERPRISE ciscoPppoeMIBNotificationPrefix
    VARIABLES {
        cPppoeSystemPerMacSessionlimit, 
        cPppoeSystemSessionClientMacAddress }
--  Status
--    mandatory
    DESCRIPTION
        "A notification indicating that number of active session
         from a particular client Ethernet MAC address has reached 
         the configured per MAC limit. There won't be any more 
         session possible from this client MAC address.
        
         An  agent  must  not  generate  more  than  one 
         cPppoeSystemSessionPerMACLimitNotif `trap-event` in a 
         30 second period,  where a  `trap-event` is  the 
         transmission of a single trap  PDU to a  list of 
         trap destinations. If additional `the number of 
         PPPoE  MAC sessions  exceeds the allowed limit`  condition 
         occur within the 30  second `throttling` period, 
         then these  trap-events should be suppressed by 
         the agent."
    ::= 3

cPppoeSystemSessionPerMACThrottleNotif TRAP-TYPE
-- Reverse mappable trap
    ENTERPRISE ciscoPppoeMIBNotificationPrefix
    VARIABLES {
        cPppoeSystemPerMacThrottleRatelimit, 
        cPppoeSystemSessionClientMacAddress }
--  Status
--    mandatory
    DESCRIPTION
        "A notification indicating that the number of new PPPoE 
         session requests coming in over a configured time 
         interval, from a particular client Ethernet MAC address,
         has crossed rate limit cPppoeSystemPerMacThrottleRatelimit.
         The client MAC address on which this event happened is 
         referred through object cPppoeSystemSessionClientMacAddress
         
         An agent should generate single 
         cPppoeSystemSessionPerMACThrottleNotif trap for configured
         time interval."
    ::= 4

cPppoeSystemSessionPerVLANLimitNotif TRAP-TYPE
-- Reverse mappable trap
    ENTERPRISE ciscoPppoeMIBNotificationPrefix
    VARIABLES {
        cPppoeSystemPerVLANlimit, ifDescr, 
        cPppoeSystemSessionVlanID, cPppoeSystemSessionInnerVlanID }
--  Status
--    mandatory
    DESCRIPTION
        "A notification indicating that number of active session on
         a Vlan has reached the maximum limit. There won't be any 
         new PPPoE session possible on this Vlan. The maximum limit 
         can be referred through object cPppoeSystemPerVLANlimit. 
         The Vlan ID of vlan can be referred though object 
         cPppoeSystemSessionVlanID. If Vlan is QinQ, 
         cPppoeSystemSessionInnerVlanID refers the 
         inner Vlan id. In case the vlan is not QinQ 
         cPppoeSystemSessionInnerVlanID will be zero. The interface
         details can be referred through ifDescr object.
        
         An  agent  must  not  generate  more  than  one 
         cPppoeSystemSessionPerVLANLimitNotif `trap-event` in a 
         30 second period,  where a  `trap-event` is  the 
         transmission of a single trap  PDU to a  list of 
         trap destinations. If additional `the number of 
         PPPoE sessions on this Vlan exceeds the allowed limit`
         condition occur within the 30  second `throttling` period, 
         then these  trap-events should be suppressed by 
         the agent."
    ::= 5

cPppoeSystemSessionPerVLANThrottleNotif TRAP-TYPE
-- Reverse mappable trap
    ENTERPRISE ciscoPppoeMIBNotificationPrefix
    VARIABLES {
        cPppoeSystemPerVLANthrottleRatelimit, ifDescr, 
        cPppoeSystemSessionVlanID, cPppoeSystemSessionInnerVlanID }
--  Status
--    mandatory
    DESCRIPTION
        "A notification indicating that the number of new PPPoE 
         session request coming on a particular Vlan, over a 
         configured time interval has reached rate limit. 
         The rate limit is referred through object 
         cPppoeSystemPerVLANthrottleRatelimit. 
         The Vlan ID of vlan can be referred though object 
         cPppoeSystemSessionVlanID. If Vlan is QinQ, 
         cPppoeSystemSessionInnerVlanID refers the
         inner Vlan Id. In case the vlan is not QinQ
         cPppoeSystemSessionInnerVlanID will be zero.  The 
         interface details can be referred through ifDescr object.
        
         An agent should generate single 
         cPppoeSystemSessionPerVLANThrottleNotif trap for the 
         configured time interval"
    ::= 6

cPppoeSystemSessionPerVCLimitNotif TRAP-TYPE
-- Reverse mappable trap
    ENTERPRISE ciscoPppoeMIBNotificationPrefix
    VARIABLES {
        cPppoeSystemPerVClimit, ifDescr, cPppoeSystemSessionVci, 
        cPppoeSystemSessionVpi }
--  Status
--    mandatory
    DESCRIPTION
        "A notification indicating that number of active sessions 
         for a ATM VCI/VPI has crossed the configured maximum 
         limit.  No more session would be possible on this VC 
         interface. The maximum limit can be referred through 
         object cPppoeSystemPerVClimit, The ATM VC details are
         referred via objects cPppoeSystemSessionVci, and
         cPppoeSystemSessionVpi. The Interface details can be 
         referred via ifDescr object.
        
         An  agent  must  not  generate  more  than  one 
         cPppoeSystemSessionPerVCLimitTrap `trap-event` in a 
         30 second period,  where a  `trap-event` is  the 
         transmission of a single trap  PDU to a  list of 
         trap destinations. If additional `the number of 
         PPPoE sessions on this VC exceeds the allowed limit` 
         condition occur within the 30  second `throttling` period, 
         then these  trap-events should be suppressed by 
         the agent."
    ::= 7

cPppoeSystemSessionPerVCThrottleNotif TRAP-TYPE
-- Reverse mappable trap
    ENTERPRISE ciscoPppoeMIBNotificationPrefix
    VARIABLES {
        cPppoeSystemPerVCThrottleRatelimit, ifDescr, 
        cPppoeSystemSessionVci, cPppoeSystemSessionVpi }
--  Status
--    mandatory
    DESCRIPTION
        "A notification indicating that the number of new PPPoE
         session request coming on a particular ATM VC, over a
         configured time interval has reached rate limit.
         The rate limit referred is referred through object 
         cPppoeSystemPerVLANthrottleRatelimit.
         The ATM VC details are referred via objects 
         cPppoeSystemSessionVci and cPppoeSystemSessionVpi. 
         The Interface details can be referred via ifDescr object.
        
         An agent should generate single
         cPppoeSystemSessionPerVLANThrottleNotif trap for the
         configured time interval"
    ::= 8

cPppoeSystemSessionLossThresholdNotif TRAP-TYPE
-- Reverse mappable trap
    ENTERPRISE ciscoPppoeMIBNotificationPrefix
    VARIABLES {
        cPppoeSystemSessionLossThreshold }
--  Status
--    mandatory
    DESCRIPTION
        "A notification indicating that number of PPPoE session
         count dropped below configured global threshold 
         watermark.  There will be only one trap send whenever
         count drops, further low count won't generate trap. 
         Number of PPPoE sessions count need to cross
        the watermark and drop below watermark to generate 
         trap again. The configured watermark can be referred
         through object cPppoeSystemSessionLossThreshold.
        
         An  agent  must  not  generate  more  than  one 
         cPppoeSystemSessionLossThresholdTrap `trap-event` in a 
         30 second period,  where a  `trap-event` is  the 
         transmission of a single trap  PDU to a  list of 
         trap destinations. If the PPPoE session count keep on
         fluctuating around the watermark during 30 seconds, then 
         these  trap-events should be suppressed by agent."
    ::= 9

cPppoePerInterfaceSessionLossThresholdNotif TRAP-TYPE
-- Reverse mappable trap
    ENTERPRISE ciscoPppoeMIBNotificationPrefix
    VARIABLES {
        ifDescr, cPppoePerInterfaceSessionLossThreshold }
--  Status
--    mandatory
    DESCRIPTION
        "A notification indicating that number of PPPoE session 
         initiated via a particular interface has dropped below
         the configured value for that interface.
         The interface details can be referred via ifDescr object,
         and the configured watermark can be referred through 
         cPppoePerInterfaceSessionLossThreshold object.
         
         There will be only one trap send whenever
         count drops, further low count won't generate trap. 
         Number of PPPoE sessions count need to cross
        the watermark and drop below watermark to generate 
         trap again.
        
         An  agent  must  not  generate  more  than  one 
         cPppoePerInterfaceSessionLossThresholdTrap `trap-event`
         in a 30 second period,  where a  `trap-event` is  the 
         transmission of a single trap  PDU to a  list of 
         trap destinations. If the PPPoE session count keep on
         fluctuating around the watermark during 30 seconds, then 
         these  trap-events should be suppressed by agent."
    ::= 10

cPppoeSystemSessionLossPercentNotif TRAP-TYPE
-- Reverse mappable trap
    ENTERPRISE ciscoPppoeMIBNotificationPrefix
    VARIABLES {
        cPppoeSystemSessionLossPercent }
--  Status
--    mandatory
    DESCRIPTION
        "A notification indicating that percentage of PPPoE session
         lost globally over a duration of time has crossed the 
         configured threshold. The configured percentage water mark
         can be referred through cPppoeSystemSessionLossPercent 
         object."
    ::= 11

cPppoePerInterfaceSessionLossPercentNotif TRAP-TYPE
-- Reverse mappable trap
    ENTERPRISE ciscoPppoeMIBNotificationPrefix
    VARIABLES {
        ifDescr, cPppoePerInterfaceSessionLossPercent }
--  Status
--    mandatory
    DESCRIPTION
        "A notification indicating that percentage of PPPoE sessions
         lost has crossed configured threshold value for a 
                particular interface. The interface details can be referred
                through ifDescr object, and the configured threshold for 
                the interface can be referred through 
                cPppoePerInterfaceSessionLossPercent."
    ::= 12

cPppoeSystemGroup OBJECT IDENTIFIER ::= { ciscoPppoeMIBGroups 1 }
-- OBJECT-GROUP
--  Status
--    mandatory
--  Descr
--    A collection of objects providing information about the 
--     PPPoE sessions on a system.
--  objects
--    cPppoeSystemCurrSessions, cPppoeSystemHighWaterSessions, 
--    cPppoeSystemMaxAllowedSessions, cPppoeSystemThresholdSessions, 
--    cPppoeSystemExceededSessionErrors

cPppoeVcCfgGroup OBJECT IDENTIFIER ::= { ciscoPppoeMIBGroups 2 }
-- OBJECT-GROUP
--  Status
--    mandatory
--  Descr
--    A collection of objects specifying PPPoE protocol 
--     related configuration on the VCL.
--  objects
--    cPppoeVcEnable

cPppoeVcSessionsGroup OBJECT IDENTIFIER ::= { ciscoPppoeMIBGroups 3 }
-- OBJECT-GROUP
--  Status
--    mandatory
--  Descr
--    A collection of objects providing information about the 
--     number of sessions on the VCL.
--  objects
--    cPppoeVcCurrSessions, cPppoeVcHighWaterSessions, 
--    cPppoeVcMaxAllowedSessions, cPppoeVcThresholdSessions, 
--    cPppoeVcExceededSessionErrors

cPppoePerInterfaceGroup OBJECT IDENTIFIER ::= { ciscoPppoeMIBGroups 5 }
-- OBJECT-GROUP
--  Status
--    mandatory
--  Descr
--     A collection of objects providing PPPoE per-interface
--      session state counts and configured threshold 
--    informations.
--  objects
--    cPppoeTotalSessions, cPppoePtaSessions, cPppoeFwdedSessions, 
--    cPppoeTransSessions, cPppoePerInterfaceSessionLossThreshold, 
--    cPppoePerInterfaceSessionLossPercent

cPppoeSystemLimitsThresholdsGroup OBJECT IDENTIFIER ::= { ciscoPppoeMIBGroups 6 }
-- OBJECT-GROUP
--  Status
--    mandatory
--  Descr
--    A collection of objects providing the session limit or 
--     throttling configuration. There are various Limitation 
--     we can impose on PPPoE Sessions it may be limit based on 
--     client-MAC or VLAN When ever the limitation is crossed
--     we send out traps.
--  objects
--    cPppoeSystemPerMacSessionlimit, 
--    cPppoeSystemPerMacIWFSessionlimit, 
--    cPppoeSystemPerMacThrottleRatelimit, cPppoeSystemPerVLANlimit, 
--    cPppoeSystemPerVLANthrottleRatelimit, cPppoeSystemPerVClimit, 
--    cPppoeSystemPerVCThrottleRatelimit, 
--    cPppoeSystemSessionLossThreshold, 
--    cPppoeSystemSessionLossPercent

cPppoeSystemLimitsThresholdsNotifObjectsGroup OBJECT IDENTIFIER ::= { ciscoPppoeMIBGroups 7 }
-- OBJECT-GROUP
--  Status
--    mandatory
--  Descr
--    This group is collection of notify objects which are 
--     used to carry notify information along with certain 
--     traps which implements Session restriction such as 
--     limit or throttling.
--  objects
--    cPppoeSystemSessionClientMacAddress, 
--    cPppoeSystemSessionVlanID, cPppoeSystemSessionInnerVlanID, 
--    cPppoeSystemSessionVci, cPppoeSystemSessionVpi

cPppoeNotificationsGroup OBJECT IDENTIFIER ::= { ciscoPppoeMIBGroups 4 }
-- NOTIFICATION-GROUP
--  Status
--    mandatory
--  Descr
--    The collection of notifications used to indicate
--     high PPPoE session volume information(e.g, the
--     number of current PPPoE sessions exceeds threshold  
--     setting for the system or a VCL).
--  notifications
--    cPppoeSystemSessionThresholdTrap, 
--    cPppoeVcSessionThresholdTrap

cPppoeSystemLimitsThresholdsNotifGroup OBJECT IDENTIFIER ::= { ciscoPppoeMIBGroups 8 }
-- NOTIFICATION-GROUP
--  Status
--    mandatory
--  Descr
--    This group is collection of notify objects used to 
--     send traps on various session restriction crossed.
--  notifications
--    cPppoeSystemSessionPerMACLimitNotif, 
--    cPppoeSystemSessionPerMACThrottleNotif, 
--    cPppoeSystemSessionPerVLANLimitNotif, 
--    cPppoeSystemSessionPerVLANThrottleNotif, 
--    cPppoeSystemSessionPerVCLimitNotif, 
--    cPppoeSystemSessionPerVCThrottleNotif, 
--    cPppoeSystemSessionLossThresholdNotif, 
--    cPppoePerInterfaceSessionLossThresholdNotif, 
--    cPppoeSystemSessionLossPercentNotif, 
--    cPppoePerInterfaceSessionLossPercentNotif

ciscoPppoeMIBBasicCompliance OBJECT IDENTIFIER ::= { ciscoPppoeMIBCompliances 1 }
-- MODULE-COMPLIANCE
--  Status
--    deprecated
--  Descr
--    The compliance statement for entities which implement
--     the Cisco Basic PPPoE MIB. 
--  Module
--    >>current<<
--   MandGroup
--    cPppoeSystemGroup
--   MandGroup
--    cPppoeVcCfgGroup
--   MandGroup
--    cPppoeVcSessionsGroup
--   MandGroup
--    cPppoePerInterfaceGroup
--   MandGroup
--    cPppoeNotificationsGroup

ciscoPppoeMIBBasicComplianceRev1 OBJECT IDENTIFIER ::= { ciscoPppoeMIBCompliances 2 }
-- MODULE-COMPLIANCE
--  Status
--    mandatory
--  Descr
--    The compliance statement for entities which implement
--     the Cisco Basic PPPoE MIB. 
--  Module
--    >>current<<
--   MandGroup
--    cPppoeSystemGroup
--   MandGroup
--    cPppoeVcCfgGroup
--   MandGroup
--    cPppoeVcSessionsGroup
--   MandGroup
--    cPppoePerInterfaceGroup
--   MandGroup
--    cPppoeNotificationsGroup
--   MandGroup
--    cPppoeSystemLimitsThresholdsGroup
--   MandGroup
--    cPppoeSystemLimitsThresholdsNotifObjectsGroup
--   MandGroup
--    cPppoeSystemLimitsThresholdsNotifGroup
--   ObjVar
--    cPppoeSystemPerMacSessionlimit
--   ObjVar
--    cPppoeSystemPerMacIWFSessionlimit
--   ObjVar
--    cPppoeSystemPerMacThrottleRatelimit
--   ObjVar
--    cPppoeSystemPerVLANlimit
--   ObjVar
--    cPppoeSystemPerVLANthrottleRatelimit
--   ObjVar
--    cPppoeSystemPerVClimit
--   ObjVar
--    cPppoeSystemPerVCThrottleRatelimit
--   ObjVar
--    cPppoeSystemSessionLossThreshold
--   ObjVar
--    cPppoeSystemSessionLossPercent


END
