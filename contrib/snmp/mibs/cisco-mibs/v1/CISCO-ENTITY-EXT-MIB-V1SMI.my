-- MIB file created 09-Sep-2015 00:29:35, by
--   SMICng version 2.2.11-beta(PRO)(Solaris), January 20, 2001. Enterprise key cisco.com

CISCO-ENTITY-EXT-MIB DEFINITIONS ::= BEGIN

-- From file: "CISCO-ENTITY-EXT-MIB.my"
-- Compile options "4 7 F H N W 03 06 0B 0G 0N 0T"

IMPORTS
    TruthValue
            FROM SNMPv2-TC-v1
    SnmpAdminString
            FROM SNMP-FRAMEWORK-MIB
    entPhysicalIndex, entPhysicalDescr, entPhysicalName, 
    entPhysicalContainedIn
            FROM ENTITY-MIB
    Unsigned64
            FROM CISCO-TC
    ciscoMgmt
            FROM CISCO-SMI
    Gauge
            FROM RFC1155-SMI
    OBJECT-TYPE
            FROM RFC-1212
    TRAP-TYPE
            FROM RFC-1215;

ciscoEntityExtMIB OBJECT IDENTIFIER ::= { ciscoMgmt 195 }
-- MODULE-IDENTITY
--  LastUpdated
--    201504170000Z
--  OrgName
--    Cisco Systems, Inc.
--  ContactInfo
--    Cisco Systems
--    Customer Service
--    
--    Postal: 170 W. Tasman Drive
--    San Jose, CA 95134
--    USA
--    
--    Tel: +1 800 553-NETS
--    
--    E-mail: cs-snmp@cisco.com
--  Descr
--    This MIB is an extension of the ENTITY-MIB
--    specified in RFC2737.
--    
--    This MIB module contains  Cisco-defined  extensions 
--    to the  entityPhysicalTable to represent information
--    related to entities of class module(entPhysicalClass
--    = 'module') which have a Processor.
--    
--    A processor module is defined as a physical entity
--    that has a CPU, RAM and NVRAM  so that
--    it can independently
--       - load a bootable image
--       - save configuration.
--    This module is the entry point for external
--    applications like SNMP Manager, CLI, FTP etc.
--    
--    Line card is an interface card         with at least a 
--    Processor and RAM. This might be referred to as 
--    Service Module in some cisco products.
--    
--    A configuration register is  a 16 bit 
--    software register.
--    The configuration register is mainly used to 
--    check for instructions on where to find the Cisco 
--    Operating System software.
--    Some other functions of configuration register are:
--     - To select a boot source and default boot filename.
--     - To enable or disable the Break function.
--     - To control broadcast addresses.
--     - To set the console terminal baud rate.
--     - To load operating software from Flash memory.
--     - To allow us to manually boot the system using the 
--       boot command at the bootstrap program prompt.
--    
--    Booting is the process of initializing the
--    hardware and starting the Operating System.
--  RevDate
--    201504170000Z
--  RevDescr
--    Added ceExtUSBModemTable,
--    ceExtUSBModemPlugInNotif, ceExtUSBModemPlugOutNotif,
--    ceExtEntUsbModemNotifEnable.
--  RevDate
--    201409120000Z
--  RevDescr
--    Changed the description ceExtEntDoorOpenNotif to
--    include ceExtEntDoorOpenNotif instead 
--    of ceExtEntDoorCloseNotif.
--  RevDate
--    201403270000Z
--  RevDescr
--    Changed the Max Access of ceExtEntDoorNotifEnable from
--    read-only to read-write.
--  RevDate
--    201308060000Z
--  RevDescr
--    Added following object to ciscoEntityExtMIBNotifications
--    ceExtBreakOutPortInserted
--    ceExtBreakOutPortRemoved
--    
--    Added following object to ceExtNotificationControlObjects
--    ceExtBreakOutPortNotifEnable
--    
--    Added the following new groups to ciscoEntityExtMIBGroups
--    ceExtBreakOutPortNotifGroup
--    ceExtBreakOutPortNotifControlGroup.
--    
--    Added a new compliance ciscoEntityExtMIBComplianceRev5 which
--    deprecates ciscoEntityExtMIBComplianceRev4
--    
--    A port can be configured to act as multiple interfaces.
--    Ex: One Hundred GigE port can act as 10 TenGigE interface
--    Breakout is the term that can be used to define this behaviour.
--    Alternatively slice term is also used. 
--    
--    When a breakout config is applied on the interface, the base 
--    interface will be replaced with multiple breakout interfaces. 
--    Reference to the base interface will be removed from the system 
--    and breakout interface will be made available. Vice versa will 
--    happen when breakout config will be removed from the system.
--  RevDate
--    201308050000Z
--  RevDescr
--    Added following new objects to ciscoEntityExtMIBNotifications.
--    ceExtEntDoorCloseNotif
--    ceExtEntDoorOpenNotif
--    
--    Added following new groups to ciscoEntityExtMIBGroups.
--    ceExtNotificationControlObjects.
--    
--    Added following new objects to ceExtNotificationControlObjects
--    ceExtEntDoorNotifEnable.
--    
--    Added the following new groups to ciscoEntityExtMIBGroups
--    ceExtEntDoorNotifGroup
--    ceExtEntDoorNotifControlGroup.
--    
--    Added a new compliance ciscoEntityExtMIBComplianceRev4 which
--    deprecates ciscoEntityExtMIBComplianceRev3.
--  RevDate
--    200811240000Z
--  RevDescr
--    Added following new objects to ceExtPhysicalProcessorTable.
--    ceExtProcessorRamOverflow and ceExtHCProcessorRam
--    
--    Added following new groups to ciscoEntityExtMIBGroups.
--    ceExtPhyProcessorOverflowGroup and ceExtPhyProcessorHCGroup.
--    
--    Added a new compliance ciscoEntityExtMIBComplianceRev3 which
--    deprecates ciscoEntityExtMIBComplianceRev2.
--  RevDate
--    200407060000Z
--  RevDescr
--    Added a new table object 'ceExtEntPhysicalTable' .
--  RevDate
--    200403030000Z
--  RevDescr
--    Importing Unsigned32 from SNMPv2-SMI, instead of CISCO-TC.
--  RevDate
--    200401260000Z
--  RevDescr
--    Added new enum to ceExtEntityLEDType.
--  RevDate
--    200308240000Z
--  RevDescr
--    Added ceExtEntityLEDTable.  Added ceExtKickstartImageList to
--    ceExtConfigRegTable.
--    Added new group ciscoEntityExtLEDGroup.
--    Added group ceExtSysBootImageListGroupRev1.
--  RevDate
--    200105170000Z
--  RevDescr
--    Corrected the description for the TC
--    ConfigRegisterValue.
--  RevDate
--    200104050000Z
--  RevDescr
--    Initial version of this MIB module.

ciscoEntityExtMIBObjects OBJECT IDENTIFIER ::= { ciscoEntityExtMIB 1 }
ceExtNotificationControlObjects OBJECT IDENTIFIER ::= { ciscoEntityExtMIBObjects 5 }
ceExtMIBNotificationPrefix OBJECT IDENTIFIER ::= { ciscoEntityExtMIB 2 }
ciscoEntityExtMIBNotifications OBJECT IDENTIFIER ::= { ceExtMIBNotificationPrefix 0 }
ciscoEntityExtMIBConformance OBJECT IDENTIFIER ::= { ciscoEntityExtMIB 3 }
ciscoEntityExtMIBCompliances OBJECT IDENTIFIER ::= { ciscoEntityExtMIBConformance 1 }
ciscoEntityExtMIBGroups OBJECT IDENTIFIER ::= { ciscoEntityExtMIBConformance 2 }

ConfigRegisterValue ::= OCTET STRING(SIZE(2))
-- TEXTUAL-CONVENTION
--  DspHint
--    2x
--  Status
--    mandatory
--  Descr
--    An Integer containing the value of config register.
--    
--    The definition of individual bits from right to left 
--    when set are as follows:
--    
--    00 to        
--    03                Boot Fields(Refer below for
--                   explanation).
--    
--    04 to 
--    05                Not Used.
--    
--    06                Causes system software to ignore the 
--                   contents of NVRAM.
--    
--    07                Enable the original equipment 
--                   manufacturer (OEM) bit.
--    
--    08                The Break function is disabled.
--    
--    09                Not used.
--    
--    10                Broadcast based on 0.0.0.0 IP address.
--    
--    11 to 
--    12                Defines the console baud rate as below:
--                   Bits 11 & 12 unset: 9600 baud(default),
--                   Bit 11 set & 12 unset: 4800 baud,
--                   Bit 11 unset & 12 set: 1200 baud,
--                   Bit 11 set & 12 set: 2400 baud
--    
--    13                Boots default Flash software if 
--                   network boot fails.
--    
--    14                IP broadcasts do not have network 
--                   numbers.
--    
--    15                Enables diagnostic messages and ignores 
--                   the contents of NVRAM.
--    
--    
--    Meanings for different values of Boot Fields
--    (Bits 00 to 03) are explained below:
--    
--    Value(in hex)        Description
--    ============    ===========
--    00                On powerup or reload, the system
--                   remains at the ROM monitor prompt 
--                   (rommon>), awaiting a user command 
--                   to boot the system manually by means 
--                   of the rommon boot command.
--    
--    01                On powerup or reload, the system loads
--                   the system image found in onboard 
--                   Flash memory.
--    
--    02 to                On powerup or reload, the system loads
--    0F                the system image specified by 
--                   ceExtSysBootImageList.
--                   It tries to boot the
--                   image in the order in which 
--                   the image names are entered in 
--                   ceExtSysBootImageList. If 
--                   it cannot boot any image in the
--                   ceExtSysBootImageList, it 
--                   stays in ROM monitor mode.

BootImageList ::= OCTET STRING(SIZE(0..255))
-- TEXTUAL-CONVENTION
--  Status
--    mandatory
--  Descr
--    This contains a list of  boot images,
--    each separated by the ';' (semi-colon) character.  
--    The following provides a syntax for parsing a single
--    boot image list item.
--    
--    <device>:[filename] | <URL>
--    
--    <device> can be (but not limited to):
--       flash, bootflash, slot0, rom, C
--    The transfer protocol used in the <URL>
--    can be (but not limited to):
--        tftp, ftp, rcp, mop.
--    
--    The following is en example containing two boot image
--    names:  
--       disk0:c7100-ik2s-mz;tftp://dirt/c7100-ik2s-mz
--    
--    If the filename is not  specified, then the
--    first file on the <device> will be used.
--    
--       If the last two characters in the returned value
--    are ';+' this indicates that additional boot image
--    items are configured on the device but can not
--    be returned because the maximum string size limitation
--    would be exceeded.
--    
--    For example:
--       disk0:image1;disk0:image2;+

ceExtPhysicalProcessorTable OBJECT-TYPE
    SYNTAX SEQUENCE OF CeExtPhysicalProcessorEntry
    ACCESS not-accessible
    STATUS mandatory
    DESCRIPTION
        "The ceExtPhysicalProcessorTable extends
        the ENTITY-MIB entPhysicalTable for modules
        (Non FRUs(Field Replacable Units) or FRUs)."
    REFERENCE
        "RFC2737: Section 2.12.1"
    ::= { ciscoEntityExtMIBObjects 1 }

ceExtPhysicalProcessorEntry OBJECT-TYPE
    SYNTAX CeExtPhysicalProcessorEntry
    ACCESS not-accessible
    STATUS mandatory
    DESCRIPTION
        "A ceExtPhysicalProcessorTable entry extends
        a corresponding entPhysicalTable entry of class
        module(entPhysicalClass = 'module').
        
        A processor module or line card which 
        has a processor will have an entry in
        this table.
        
        A processor module or line card having
        multiple processors and is a SMP(Symmetric
        multi processor) system will have only 
        one entry corresponding to all the processors 
        since the resources defined below are shared.
        
        A processor module or line card having
        multiple processors and is not an SMP system
        would register the processors as separate entities.
        
        Entries are created by the agent at the system power-up
        or module insertion.
        
        Entries are removed when the module is reset or removed."
    INDEX { entPhysicalIndex }
    ::= { ceExtPhysicalProcessorTable 1 }

CeExtPhysicalProcessorEntry ::= SEQUENCE {
    ceExtProcessorRam Gauge,
    ceExtNVRAMSize Gauge,
    ceExtNVRAMUsed Gauge,
    ceExtProcessorRamOverflow Gauge,
    ceExtHCProcessorRam Unsigned64
    }

ceExtProcessorRam OBJECT-TYPE
    SYNTAX Gauge
--  Units
--    bytes
    ACCESS read-only
    STATUS mandatory
    DESCRIPTION
        "Total number of bytes of RAM available on the
        Processor."
    ::= { ceExtPhysicalProcessorEntry 1 }

ceExtNVRAMSize OBJECT-TYPE
    SYNTAX Gauge
--  Units
--    bytes
    ACCESS read-only
    STATUS mandatory
    DESCRIPTION
        "Total number of bytes of NVRAM in the entity.
        
        A value of 0 for this object means the entity
        does not support NVRAM or NVRAM information 
        is not available."
    ::= { ceExtPhysicalProcessorEntry 2 }

ceExtNVRAMUsed OBJECT-TYPE
    SYNTAX Gauge
--  Units
--    bytes
    ACCESS read-only
    STATUS mandatory
    DESCRIPTION
        "Number of bytes of NVRAM in use. This object
        is irrelevant if ceExtNVRAMSize is 0."
    ::= { ceExtPhysicalProcessorEntry 3 }

ceExtProcessorRamOverflow OBJECT-TYPE
    SYNTAX Gauge
--  Units
--    bytes
    ACCESS read-only
    STATUS mandatory
    DESCRIPTION
        "This object represents the upper 32-bit of ceExtProcessorRam.
        This object needs to be supported only if the available RAM
        bytes exceeds 32-bit, otherwise this object value would be set
        to 0."
    ::= { ceExtPhysicalProcessorEntry 4 }

ceExtHCProcessorRam OBJECT-TYPE
    SYNTAX --?? syntax is not convertable to SMIv1
           Unsigned64
--    Rsyntax Counter64
--  Units
--    bytes
    ACCESS read-only
    STATUS mandatory
    DESCRIPTION
        "This object represents the total number of bytes of RAM
        available on the Processor. This object is a 64-bit version
        of ceExtProcessorRam."
    ::= { ceExtPhysicalProcessorEntry 5 }

ceExtConfigRegTable OBJECT-TYPE
    SYNTAX SEQUENCE OF CeExtConfigRegEntry
    ACCESS not-accessible
    STATUS mandatory
    DESCRIPTION
        "The ceExtConfigRegTable extends
        the ENTITY-MIB entPhysicalTable."
    REFERENCE
        "RFC2737: Section 2.12.1"
    ::= { ciscoEntityExtMIBObjects 2 }

ceExtConfigRegEntry OBJECT-TYPE
    SYNTAX CeExtConfigRegEntry
    ACCESS not-accessible
    STATUS mandatory
    DESCRIPTION
        "A ceExtConfigRegTable entry extends
        a corresponding entPhysicalTable entry of class
        module which has a configuration register.
        
        Entries are created by the agent at the system power-up
        or module insertion.
        
        Entries are removed when the module is reset or 
        removed."
    INDEX { entPhysicalIndex }
    ::= { ceExtConfigRegTable 1 }

CeExtConfigRegEntry ::= SEQUENCE {
    ceExtConfigRegister ConfigRegisterValue,
    ceExtConfigRegNext ConfigRegisterValue,
    ceExtSysBootImageList BootImageList,
    ceExtKickstartImageList BootImageList
    }

ceExtConfigRegister OBJECT-TYPE
    SYNTAX ConfigRegisterValue
--    Rsyntax OCTET STRING(SIZE(2))
    ACCESS read-only
    STATUS mandatory
    DESCRIPTION
        "The value of configuration register with which
        the processor module booted."
    ::= { ceExtConfigRegEntry 1 }

ceExtConfigRegNext OBJECT-TYPE
    SYNTAX ConfigRegisterValue
--    Rsyntax OCTET STRING(SIZE(2))
    ACCESS read-write
    STATUS mandatory
    DESCRIPTION
        "The value of configuration register in the
        processor module at next reboot. Just after 
        the reboot this has the same value as 
        ceExtConfigRegister."
    ::= { ceExtConfigRegEntry 2 }

ceExtSysBootImageList OBJECT-TYPE
    SYNTAX BootImageList
--    Rsyntax OCTET STRING(SIZE(0..255))
    ACCESS read-write
    STATUS mandatory
    DESCRIPTION
        "The list of system boot images which
        can be used for booting."
    DEFVAL { "" }
    ::= { ceExtConfigRegEntry 3 }

ceExtKickstartImageList OBJECT-TYPE
    SYNTAX BootImageList
--    Rsyntax OCTET STRING(SIZE(0..255))
    ACCESS read-write
    STATUS mandatory
    DESCRIPTION
        "The list of system kickstart images which
        can be used for booting."
    DEFVAL { "" }
    ::= { ceExtConfigRegEntry 4 }

ceExtEntityLEDTable OBJECT-TYPE
    SYNTAX SEQUENCE OF CeExtEntityLEDEntry
    ACCESS not-accessible
    STATUS mandatory
    DESCRIPTION
        "A table containing information of LED on an entity."
    ::= { ciscoEntityExtMIBObjects 3 }

ceExtEntityLEDEntry OBJECT-TYPE
    SYNTAX CeExtEntityLEDEntry
    ACCESS not-accessible
    STATUS mandatory
    DESCRIPTION
        "An entry (conceptual row) in the ceExtEntityLEDTable,
        containing information about an LED on an entity, identified by 
        entPhysicalIndex."
    INDEX { entPhysicalIndex, ceExtEntityLEDType }
    ::= { ceExtEntityLEDTable 1 }

CeExtEntityLEDEntry ::= SEQUENCE {
    ceExtEntityLEDType INTEGER,
    ceExtEntityLEDColor INTEGER
    }

ceExtEntityLEDType OBJECT-TYPE
    SYNTAX INTEGER {
        status(1),
        system(2),
        active(3),
        power(4),
        battery(5)
        }
    ACCESS not-accessible
    STATUS mandatory
    DESCRIPTION
        "The type of LED on this entity.
        'status' - indicates the entity status.
        'system' - indicates the overall system status. 
        'active' - the redundancy status of a module, for e.g.
                   supervisor module. 
        'power'  - indicates sufficient power availability for all 
                   modules.
        'battery'- indicates the battery status."
    REFERENCE
        "Cisco MDS 9500 Series Hardware Installation Guide,
        Product Overview."
    ::= { ceExtEntityLEDEntry 1 }

ceExtEntityLEDColor OBJECT-TYPE
    SYNTAX INTEGER {
        off(1),
        green(2),
        amber(3),
        red(4)
        }
    ACCESS read-only
    STATUS mandatory
    DESCRIPTION
        "The color of the LED."
    REFERENCE
        "Cisco MDS 9500 Series Multilayer Switches, Product
        Overview."
    ::= { ceExtEntityLEDEntry 2 }

ceExtEntPhysicalTable OBJECT-TYPE
    SYNTAX SEQUENCE OF CeExtEntPhysicalEntry
    ACCESS not-accessible
    STATUS mandatory
    DESCRIPTION
        "This table contains additional information about
        a particular physical entity.
        This table augments the 'entPhysicalTable'  of
        the ENTITY-MIB."
    REFERENCE
        "RFC2737: Section 2.12.1"
    ::= { ciscoEntityExtMIBObjects 4 }

ceExtEntPhysicalEntry OBJECT-TYPE
    SYNTAX CeExtEntPhysicalEntry
    ACCESS not-accessible
    STATUS mandatory
    DESCRIPTION
        "An entry (conceptual row) in the 'ceExtEntPhysicalTable',
        containing additional information about a physical entity, 
        identified by 'entPhysicalIndex'."
    INDEX { entPhysicalIndex }
-- Augments entPhysicalEntry FROM ENTITY-MIB
    ::= { ceExtEntPhysicalTable 1 }

CeExtEntPhysicalEntry ::= SEQUENCE {
    ceEntPhysicalSecondSerialNum SnmpAdminString
    }

ceEntPhysicalSecondSerialNum OBJECT-TYPE
    SYNTAX SnmpAdminString(SIZE(0..32))
--    Rsyntax OCTET STRING(SIZE(0..32))
    ACCESS read-write
    STATUS mandatory
    DESCRIPTION
        "This object represents the vendor-specific second
        serial number string for the physical entity. 
        The first serial number string of the physical
        entity is represented in the value of corresponding 
        instance of the 'entPhysicalSerialNum' object.
        
        On the first instantiation of an physical entity, the value
        of this object is the correct vendor-assigned second 
        serial number, if this information is available to the agent. 
        
        If the second serial number is unknown or non-existent, then 
        the value of this object will be a zero-length string instead.
        
        Note that implementations which can correctly identify the
        second serial numbers of all installed physical entities do 
        not need to provide write access to this object. 
        Agents which cannot provide non-volatile storage for the 
        second serial number strings are not required to implement 
        write access for this object.
        
        Not every physical component will have a serial number, or
        even need one.  Physical entities for which the associated
        value of the entPhysicalIsFRU object is equal to 'false(2)'
        (e.g., the repeater ports within a repeater module), do not
        need their own unique serial number. An agent does not have
        to provide write access for such entities, and may return a
        zero-length string.
        
        If write access is implemented for an instance of
        'ceEntPhysicalSecondSerialNum', and a value is written into 
        the instance, the agent must retain the supplied value in the
        'ceEntPhysicalSecondSerialNum' instance associated with the 
        same physical entity for as long as that entity remains
        instantiated. This includes instantiations across all re-
        initializations/reboots of the network management system,
        including those which result in a change of the physical
        entity's entPhysicalIndex value."
    DEFVAL { "" }
    ::= { ceExtEntPhysicalEntry 1 }

ceExtEntDoorNotifEnable OBJECT-TYPE
    SYNTAX TruthValue
--    Rsyntax INTEGER {
--        true(1),
--        false(2)
--        }
    ACCESS read-write
    STATUS mandatory
    DESCRIPTION
        "This object controls the generation of
        ceExtEntDoorCloseNotif and ceExtEntDoorOpenNotif 
        notifications as follows: 
        'true(1)' -  the generation of ceExtEntDoorCloseNotif
                     and ceExtEntDoorOpenNotif  
                     notifications are enabled. 
        'false(2)' - the generation of ceExtEntDoorCloseNotif
                     and ceExtEntDoorOpenNotif  
                     notifications are disabled."
    DEFVAL { false }
    ::= { ceExtNotificationControlObjects 1 }

ceExtEntBreakOutPortNotifEnable OBJECT-TYPE
    SYNTAX TruthValue
--    Rsyntax INTEGER {
--        true(1),
--        false(2)
--        }
    ACCESS read-only
    STATUS mandatory
    DESCRIPTION
        "This object controls the generation of
        ceExtBreakOutPortInserted and
         ceExtBreakOutPortRemoved as follows:
        'true(1)'  - the generation of ceExtBreakOutPortInserted
                           and ceExtBreakOutPortRemoved
                           notifications is enabled.
        'false(2)' - the generation of ceExtBreakOutPortInserted
                           and ceExtBreakOutPortRemoved
                           notifications is disabled."
    DEFVAL { false }
    ::= { ceExtNotificationControlObjects 2 }

ceExtEntUsbModemNotifEnable OBJECT-TYPE
    SYNTAX TruthValue
--    Rsyntax INTEGER {
--        true(1),
--        false(2)
--        }
    ACCESS read-write
    STATUS mandatory
    DESCRIPTION
        "This object controls the generation of
        ceExtUSBModemPlugInNotif and
         ceExtUSBModemPlugOutNotif as follows:
        'true(1)'  - the generation of ceExtUSBModemPlugInNotif
                           and ceExtUSBModemPlugOutNotif
                           notifications is enabled.
        'false(2)' - the generation of ceExtUSBModemPlugOutNotif
                           and ceExtUSBModemPlugOutNotif
                           notifications is disabled."
    DEFVAL { false }
    ::= { ceExtNotificationControlObjects 3 }

ceExtUSBModemTable OBJECT-TYPE
    SYNTAX SEQUENCE OF CeExtUSBModemEntry
    ACCESS not-accessible
    STATUS mandatory
    DESCRIPTION
        "A table containing information of USB MODEMs on an entity."
    ::= { ciscoEntityExtMIBObjects 6 }

ceExtUSBModemEntry OBJECT-TYPE
    SYNTAX CeExtUSBModemEntry
    ACCESS not-accessible
    STATUS mandatory
    DESCRIPTION
        "An entry (conceptual row) in the ceExtUSBModemTable,
        containing information about an USB MODEM on an entity, 
        identified by entPhysicalIndex."
    INDEX { entPhysicalIndex }
    ::= { ceExtUSBModemTable 1 }

CeExtUSBModemEntry ::= SEQUENCE {
    ceExtUSBModemIMEI SnmpAdminString,
    ceExtUSBModemIMSI SnmpAdminString,
    ceExtUSBModemServiceProvider SnmpAdminString,
    ceExtUSBModemSignalStrength SnmpAdminString
    }

ceExtUSBModemIMEI OBJECT-TYPE
    SYNTAX SnmpAdminString(SIZE(0..64))
--    Rsyntax OCTET STRING(SIZE(0..64))
    ACCESS read-only
    STATUS mandatory
    DESCRIPTION
        "The International Mobile Equipment Identifier (IMEI) of the
        USB-MODEM"
    REFERENCE
        "RFC 6155"
    ::= { ceExtUSBModemEntry 1 }

ceExtUSBModemIMSI OBJECT-TYPE
    SYNTAX SnmpAdminString(SIZE(0..64))
--    Rsyntax OCTET STRING(SIZE(0..64))
    ACCESS read-only
    STATUS mandatory
    DESCRIPTION
        "The International Mobile Subscriber Identifier(IMSI) -
        for a GSM USB MODEM."
    REFERENCE
        "RFC 4186"
    ::= { ceExtUSBModemEntry 2 }

ceExtUSBModemServiceProvider OBJECT-TYPE
    SYNTAX SnmpAdminString(SIZE(0..64))
--    Rsyntax OCTET STRING(SIZE(0..64))
    ACCESS read-only
    STATUS mandatory
    DESCRIPTION
        "The Service Provider name for a USB MODEM."
    ::= { ceExtUSBModemEntry 3 }

ceExtUSBModemSignalStrength OBJECT-TYPE
    SYNTAX SnmpAdminString(SIZE(0..64))
--    Rsyntax OCTET STRING(SIZE(0..64))
    ACCESS read-only
    STATUS mandatory
    DESCRIPTION
        "The signal strength of the USB MODEM."
    ::= { ceExtUSBModemEntry 4 }

ceExtEntDoorCloseNotif TRAP-TYPE
-- Reverse mappable trap
    ENTERPRISE ceExtMIBNotificationPrefix
    VARIABLES {
        entPhysicalDescr, entPhysicalName }
--  Status
--    mandatory
    DESCRIPTION
        "A ceExtEntDoorCloseNotif is generated if the door of an entity
        has been closed."
    ::= 1

ceExtEntDoorOpenNotif TRAP-TYPE
-- Reverse mappable trap
    ENTERPRISE ceExtMIBNotificationPrefix
    VARIABLES {
        entPhysicalDescr, entPhysicalName }
--  Status
--    mandatory
    DESCRIPTION
        "A ceExtEntDoorOpenNotif is generated if the door of an entity
        has been opened."
    ::= 2

ceExtBreakOutPortInserted TRAP-TYPE
-- Reverse mappable trap
    ENTERPRISE ceExtMIBNotificationPrefix
    VARIABLES {
        entPhysicalContainedIn, entPhysicalName }
--  Status
--    mandatory
    DESCRIPTION
        "The ceExtBreakOutPortInserted notification indicates
        that a Breakout port was inserted.  The varbind for
        this notification indicates the entPhysicalIndex of
        the inserted Breakout port, and the entPhysicalIndex
        of the BreakOut Port module that contains this port."
    ::= 3

ceExtBreakOutPortRemoved TRAP-TYPE
-- Reverse mappable trap
    ENTERPRISE ceExtMIBNotificationPrefix
    VARIABLES {
        entPhysicalContainedIn, entPhysicalName }
--  Status
--    mandatory
    DESCRIPTION
        "The ceExtBreakOutPortRemoved  notification indicates
        that a Breakout Port was removed.  The varbind for this
        notification indicates the entPhysicalIndex of the
        removed Breakout port, and the entPhysicalIndex
        of the BreakOut Port module that contains this port."
    ::= 4

ceExtUSBModemPlugInNotif TRAP-TYPE
-- Reverse mappable trap
    ENTERPRISE ceExtMIBNotificationPrefix
    VARIABLES {
        entPhysicalContainedIn, entPhysicalDescr }
--  Status
--    mandatory
    DESCRIPTION
        "The ceExtUSBModemPlugInNotif notification indicates that
        a USB MODEM was inserted. The varbind for this notification
        indicates the entPhysicalDescr of the inserted USB MODEM, 
        and the entPhysicalIndex of the USB MODEM's container."
    ::= 5

ceExtUSBModemPlugOutNotif TRAP-TYPE
-- Reverse mappable trap
    ENTERPRISE ceExtMIBNotificationPrefix
    VARIABLES {
        entPhysicalContainedIn, entPhysicalDescr }
--  Status
--    mandatory
    DESCRIPTION
        "The ceExtUSBModemPlugOutNotif notification indicates that
        a USB MODEM was removed. The varbind for this notification
        indicates the entPhysicalDescr of the removed USB MODEM,
        and the entPhysicalIndex of the USB MODEM's container."
    ::= 6

ceExtPhysicalProcessorGroup OBJECT IDENTIFIER ::= { ciscoEntityExtMIBGroups 1 }
-- OBJECT-GROUP
--  Status
--    mandatory
--  Descr
--    The collection of objects which give information about
--    the Processor RAM and NVRAM.
--  objects
--    ceExtProcessorRam, ceExtNVRAMSize, ceExtNVRAMUsed

ciscoEntityExtConfigRegGroup OBJECT IDENTIFIER ::= { ciscoEntityExtMIBGroups 2 }
-- OBJECT-GROUP
--  Status
--    mandatory
--  Descr
--    The collection of objects which give information about
--    configuration register.
--    
--    Implementation of this group is optional.
--  objects
--    ceExtConfigRegister, ceExtConfigRegNext

ceExtSysBootImageListGroup OBJECT IDENTIFIER ::= { ciscoEntityExtMIBGroups 3 }
-- OBJECT-GROUP
--  Status
--    mandatory
--  Descr
--    A group containing an object providing information
--    about the system boot images.
--    
--    Implementation of this group is optional.
--  objects
--    ceExtSysBootImageList

ciscoEntityExtLEDGroup OBJECT IDENTIFIER ::= { ciscoEntityExtMIBGroups 4 }
-- OBJECT-GROUP
--  Status
--    mandatory
--  Descr
--    A collection of objects for giving led information.
--  objects
--    ceExtEntityLEDColor

ceExtSysBootImageListGroupRev1 OBJECT IDENTIFIER ::= { ciscoEntityExtMIBGroups 5 }
-- OBJECT-GROUP
--  Status
--    mandatory
--  Descr
--    A group containing an object providing information
--    about the system boot images.
--    
--    Implementation of this group is optional.
--  objects
--    ceExtKickstartImageList

ciscoExtEntityPhysicalGroup OBJECT IDENTIFIER ::= { ciscoEntityExtMIBGroups 6 }
-- OBJECT-GROUP
--  Status
--    mandatory
--  Descr
--    The collection of objects for providing additional
--    information about the physical entity.
--    
--    Implementation of this group is optional.
--  objects
--    ceEntPhysicalSecondSerialNum

ceExtPhyProcessorOverflowGroup OBJECT IDENTIFIER ::= { ciscoEntityExtMIBGroups 7 }
-- OBJECT-GROUP
--  Status
--    mandatory
--  Descr
--    The collection of Overflow (upper 32-bit) objects which
--    provides information about physical processor, when the entity
--    runs on 64-bit Operating System (OS). This group is optional for
--    the entities which run on 32-bit OS.
--  objects
--    ceExtProcessorRamOverflow

ceExtPhyProcessorHCGroup OBJECT IDENTIFIER ::= { ciscoEntityExtMIBGroups 8 }
-- OBJECT-GROUP
--  Status
--    mandatory
--  Descr
--    The collection of High Capacity (HC) objects which provides
--    information about physical processor, when the entity runs on
--    64-bit Operating System (OS). This group is optional for the
--    entities which run on 32-bit OS.
--  objects
--    ceExtHCProcessorRam

ceExtEntDoorNotifControlGroup OBJECT IDENTIFIER ::= { ciscoEntityExtMIBGroups 10 }
-- OBJECT-GROUP
--  Status
--    mandatory
--  Descr
--    A collection of objects providing control for entity door
--    notifications.
--  objects
--    ceExtEntDoorNotifEnable

ceExtBreakOutPortNotifControlGroup OBJECT IDENTIFIER ::= { ciscoEntityExtMIBGroups 12 }
-- OBJECT-GROUP
--  Status
--    mandatory
--  Descr
--    A collection of objects providing control for Breakout
--    Port notifications.
--  objects
--    ceExtEntBreakOutPortNotifEnable

ceExtUSBModemGroup OBJECT IDENTIFIER ::= { ciscoEntityExtMIBGroups 13 }
-- OBJECT-GROUP
--  Status
--    mandatory
--  Descr
--    A collection of objects for giving USB MODEM
--    config information.
--  objects
--    ceExtUSBModemIMEI, ceExtUSBModemIMSI, 
--    ceExtUSBModemServiceProvider, ceExtUSBModemSignalStrength

ceExtUsbModemNotifControlGroup OBJECT IDENTIFIER ::= { ciscoEntityExtMIBGroups 15 }
-- OBJECT-GROUP
--  Status
--    mandatory
--  Descr
--    A collection of objects providing control for USB
--    MODEM notifications.
--  objects
--    ceExtEntUsbModemNotifEnable

ceExtEntDoorNotifGroup OBJECT IDENTIFIER ::= { ciscoEntityExtMIBGroups 9 }
-- NOTIFICATION-GROUP
--  Status
--    mandatory
--  Descr
--    A collection of objects providing the notification
--    information for door entitites.
--  notifications
--    ceExtEntDoorCloseNotif, ceExtEntDoorOpenNotif

ceExtBreakOutPortNotifGroup OBJECT IDENTIFIER ::= { ciscoEntityExtMIBGroups 11 }
-- NOTIFICATION-GROUP
--  Status
--    mandatory
--  Descr
--    A collection of objects providing the notification
--    information for supporting Breakout port feature.
--  notifications
--    ceExtBreakOutPortInserted, ceExtBreakOutPortRemoved

ceExtUsbModemNotificationsGroup OBJECT IDENTIFIER ::= { ciscoEntityExtMIBGroups 14 }
-- NOTIFICATION-GROUP
--  Status
--    mandatory
--  Descr
--    A collection of notifications for USB MODEM removal and
--    insertion.
--  notifications
--    ceExtUSBModemPlugInNotif, ceExtUSBModemPlugOutNotif

ciscoEntityExtMIBCompliance OBJECT IDENTIFIER ::= { ciscoEntityExtMIBCompliances 1 }
-- MODULE-COMPLIANCE
--  Status
--    deprecated
--  Descr
--    Compliance for SNMP Entities which support modules
--    with CPU, NVRAM and configuration register.
--  Module
--    >>current<<
--   MandGroup
--    ceExtPhysicalProcessorGroup
--   OptGroup
--    ciscoEntityExtConfigRegGroup
--   OptGroup
--    ceExtSysBootImageListGroup

ciscoEntityExtMIBComplianceRev1 OBJECT IDENTIFIER ::= { ciscoEntityExtMIBCompliances 2 }
-- MODULE-COMPLIANCE
--  Status
--    deprecated
--  Descr
--    Compliance for SNMP Entities which support modules
--    with CPU, NVRAM and configuration register.
--  Module
--    >>current<<
--   MandGroup
--    ceExtPhysicalProcessorGroup
--   OptGroup
--    ciscoEntityExtConfigRegGroup
--   OptGroup
--    ceExtSysBootImageListGroup
--   OptGroup
--    ciscoEntityExtLEDGroup
--   OptGroup
--    ceExtSysBootImageListGroupRev1

ciscoEntityExtMIBComplianceRev2 OBJECT IDENTIFIER ::= { ciscoEntityExtMIBCompliances 3 }
-- MODULE-COMPLIANCE
--  Status
--    deprecated
--  Descr
--    Compliance for SNMP Entities which support modules
--    with CPU, NVRAM and configuration register.
--  Module
--    >>current<<
--   MandGroup
--    ceExtPhysicalProcessorGroup
--   OptGroup
--    ciscoEntityExtConfigRegGroup
--   OptGroup
--    ceExtSysBootImageListGroup
--   OptGroup
--    ciscoEntityExtLEDGroup
--   OptGroup
--    ceExtSysBootImageListGroupRev1
--   OptGroup
--    ciscoExtEntityPhysicalGroup

ciscoEntityExtMIBComplianceRev3 OBJECT IDENTIFIER ::= { ciscoEntityExtMIBCompliances 4 }
-- MODULE-COMPLIANCE
--  Status
--    deprecated
--  Descr
--    Compliance for SNMP Entities which support modules
--    with CPU, NVRAM and configuration register.
--  Module
--    >>current<<
--   MandGroup
--    ceExtPhysicalProcessorGroup
--   OptGroup
--    ciscoEntityExtConfigRegGroup
--   OptGroup
--    ceExtSysBootImageListGroup
--   OptGroup
--    ciscoEntityExtLEDGroup
--   OptGroup
--    ceExtSysBootImageListGroupRev1
--   OptGroup
--    ciscoExtEntityPhysicalGroup
--   OptGroup
--    ceExtPhyProcessorOverflowGroup
--   OptGroup
--    ceExtPhyProcessorHCGroup

ciscoEntityExtMIBComplianceRev4 OBJECT IDENTIFIER ::= { ciscoEntityExtMIBCompliances 5 }
-- MODULE-COMPLIANCE
--  Status
--    deprecated
--  Descr
--    Compliance for SNMP Entities which support modules
--    with CPU, NVRAM and configuration register.
--  Module
--    >>current<<
--   MandGroup
--    ceExtPhysicalProcessorGroup
--   OptGroup
--    ciscoEntityExtConfigRegGroup
--   OptGroup
--    ceExtSysBootImageListGroup
--   OptGroup
--    ciscoEntityExtLEDGroup
--   OptGroup
--    ceExtSysBootImageListGroupRev1
--   OptGroup
--    ciscoExtEntityPhysicalGroup
--   OptGroup
--    ceExtPhyProcessorOverflowGroup
--   OptGroup
--    ceExtPhyProcessorHCGroup
--   OptGroup
--    ceExtEntDoorNotifGroup
--   OptGroup
--    ceExtEntDoorNotifControlGroup
--   ObjVar
--    ceExtConfigRegNext
--   ObjVar
--    ceExtSysBootImageList
--   ObjVar
--    ceExtKickstartImageList
--   ObjVar
--    ceEntPhysicalSecondSerialNum
--   ObjVar
--    ceExtEntDoorNotifEnable

ciscoEntityExtMIBComplianceRev5 OBJECT IDENTIFIER ::= { ciscoEntityExtMIBCompliances 6 }
-- MODULE-COMPLIANCE
--  Status
--    deprecated
--  Descr
--    Compliance for SNMP Entities which support modules
--    with CPU, NVRAM and configuration register.
--  Module
--    >>current<<
--   MandGroup
--    ceExtPhysicalProcessorGroup
--   OptGroup
--    ciscoEntityExtConfigRegGroup
--   OptGroup
--    ceExtSysBootImageListGroup
--   OptGroup
--    ciscoEntityExtLEDGroup
--   OptGroup
--    ceExtSysBootImageListGroupRev1
--   OptGroup
--    ciscoExtEntityPhysicalGroup
--   OptGroup
--    ceExtPhyProcessorOverflowGroup
--   OptGroup
--    ceExtPhyProcessorHCGroup
--   OptGroup
--    ceExtEntDoorNotifGroup
--   OptGroup
--    ceExtEntDoorNotifControlGroup
--   OptGroup
--    ceExtBreakOutPortNotifGroup
--   OptGroup
--    ceExtBreakOutPortNotifControlGroup
--   ObjVar
--    ceExtEntBreakOutPortNotifEnable

ciscoEntityExtMIBComplianceRev6 OBJECT IDENTIFIER ::= { ciscoEntityExtMIBCompliances 7 }
-- MODULE-COMPLIANCE
--  Status
--    mandatory
--  Descr
--    Compliance for SNMP Entities which support modules
--    with CPU, NVRAM and configuration register.
--  Module
--    >>current<<
--   MandGroup
--    ceExtPhysicalProcessorGroup
--   OptGroup
--    ciscoEntityExtConfigRegGroup
--   OptGroup
--    ceExtSysBootImageListGroup
--   OptGroup
--    ciscoEntityExtLEDGroup
--   OptGroup
--    ceExtSysBootImageListGroupRev1
--   OptGroup
--    ciscoExtEntityPhysicalGroup
--   OptGroup
--    ceExtPhyProcessorOverflowGroup
--   OptGroup
--    ceExtPhyProcessorHCGroup
--   OptGroup
--    ceExtEntDoorNotifGroup
--   OptGroup
--    ceExtEntDoorNotifControlGroup
--   OptGroup
--    ceExtBreakOutPortNotifGroup
--   OptGroup
--    ceExtBreakOutPortNotifControlGroup
--   OptGroup
--    ceExtUSBModemGroup
--   OptGroup
--    ceExtUsbModemNotificationsGroup
--   OptGroup
--    ceExtUsbModemNotifControlGroup
--   ObjVar
--    ceExtEntBreakOutPortNotifEnable
--   ObjVar
--    ceExtEntUsbModemNotifEnable


END
