-- MIB file created 25-Jan-2007 15:16:46, by
--   SMICng version 2.2.11-beta(PRO)(Solaris), January 20, 2001. Enterprise key cisco.com

CISCO-CAS-IF-EXT-MIB DEFINITIONS ::= BEGIN

-- From file: "CISCO-CAS-IF-EXT-MIB.my"
-- Compile options "4 7 F H N O W 03 06 0B 0G 0N 0T"

IMPORTS
    TruthValue, RowStatus
            FROM SNMPv2-TC-v1
    ConfigIterator, BulkConfigResult
            FROM CISCO-TC
    ifIndex
            FROM IF-MIB
--?? may need import of ifIndex from IF-MIB
    ccasGrpCfgIndex
--?? may need import of ifIndex from IF-MIB
                   , ccasGrpCfgIndex
            FROM CISCO-CAS-IF-MIB
    OwnerString
            FROM RMON-MIB
    ciscoMgmt
            FROM CISCO-SMI
    CvcCoderTypeRate, CvcFaxTransmitRate
            FROM CISCO-VOICE-COMMON-DIAL-CONTROL-MIB
    CiscoCodecPacketPeriod
            FROM CISCO-VOICE-AALX-PROFILE-MIB
    SnmpAdminString
            FROM SNMP-FRAMEWORK-MIB
    CVoiceTonePlanIndexOrZero, CCallControlProfileIndexOrZero, 
    cmgwIndex
            FROM CISCO-MEDIA-GATEWAY-MIB
    CH248Packages
            FROM CISCO-MEGACO-EXT-MIB
    Gauge
            FROM RFC1155-SMI
    OBJECT-TYPE
            FROM RFC-1212;

ciscoCasIfExtMIB OBJECT IDENTIFIER ::= { ciscoMgmt 314 }
-- MODULE-IDENTITY
--  LastUpdated
--    200511280000Z
--  OrgName
--    Cisco Systems, Inc.
--  ContactInfo
--            Cisco Systems
--             Customer Service
--    Postal: 170 W Tasman Drive
--            San Jose, CA 95134
--            USA
--       Tel: +1 800 553-NETS
--    E-mail: cs-voice-gateway@cisco.com
--  Descr
--    The MIB module is an extension of CISCO-CAS-IF-MIB.
--     It defines the attributes of a voice interface.
--  RevDate
--    200511280000Z
--  RevDescr
--    Added ccasIfExtVoiceCfgNoiseRegType object in
--     ccasIfExtVoiceCfgTable
--  RevDate
--    200406230000Z
--  RevDescr
--    Added the following objects in ccasIfExtVoiceCfgTable:
--         ccasIfExtVoiceCfgCasProfile
--         ccasIfExtVoiceCfgCasVariant
--         ccasIfExtVoiceCfgDs0ChannelsFail
--     and the following tables to provide CAS variant:
--         ccasIfExtProfileTable
--         ccasIfExtVariantTable
--         ccasIfExtIncomingLineSignalTable
--         ccasIfExtOutgoingLineSignalTable
--         ccasIfExtRegisterSignalTable
--         ccasIfExtLineSignalTimerTable
--         ccasIfExtRegSignalTimerTable
--         ccasIfExtGeneralConfigTable.
--  RevDate
--    200405260000Z
--  RevDescr
--    Deprecated the following objects in ccasIfExtVoiceCfgTable:
--         ccasIfExtVoiceCfgT38MaxFaxTxRate
--         ccasIfExtVoiceCfgT38HsPktPeriod
--         ccasIfExtVoiceCfgT38HsRedundancy
--     Added ccasIfExtVoiceCfgEventMappingIdx,
--           ccasIfExtVoiceCfgGatewayIndex to 
--     ccasIfExtVoiceCfgTable.
--  RevDate
--    200304170000Z
--  RevDescr
--    Initial version of this MIB module

ciscoCasIfExtMIBNotifications OBJECT IDENTIFIER ::= { ciscoCasIfExtMIB 0 }
ciscoCasIfExtMIBObjects OBJECT IDENTIFIER ::= { ciscoCasIfExtMIB 1 }
ccasIfExtConfig OBJECT IDENTIFIER ::= { ciscoCasIfExtMIBObjects 1 }
ccasIfExtProfile OBJECT IDENTIFIER ::= { ciscoCasIfExtMIBObjects 2 }
ccasIfExtConfigLineSignal OBJECT IDENTIFIER ::= { ciscoCasIfExtMIBObjects 3 }
ccasIfExtConfigRegisterSignal OBJECT IDENTIFIER ::= { ciscoCasIfExtMIBObjects 4 }
ccasIfExtConfigTimer OBJECT IDENTIFIER ::= { ciscoCasIfExtMIBObjects 5 }
ccasIfExtGeneralConfig OBJECT IDENTIFIER ::= { ciscoCasIfExtMIBObjects 6 }
ciscoCasIfExtMIBConformance OBJECT IDENTIFIER ::= { ciscoCasIfExtMIB 2 }
ccasIfExtMIBCompliances OBJECT IDENTIFIER ::= { ciscoCasIfExtMIBConformance 1 }
ccasIfExtMIBGroups OBJECT IDENTIFIER ::= { ciscoCasIfExtMIBConformance 2 }

CASLineSignal ::= OCTET STRING(SIZE(1))
-- TEXTUAL-CONVENTION
--  Status
--    mandatory
--  Descr
--    This textual convention defines line signals indicating the 
--     ABCD bits of CAS signaling, which represent the states of 
--     lines.
--     Each of A, B, C or D represents by two bit value :
--    
--    
--     b(bit)1 |  b0  |  value
--     ========================
--        0    |   0  |     0
--        0    |   1  |     1
--        1    |   0  |     2 ( don't care )
--        1    |   1  |     3 ( don't care ) 
--    
--    
--     The ABCD line signals are occupied in one byte, and 
--     in order:
--     . A  : bit 7, and 6       
--     . B  : bit 5, and 4  
--     . C  : bit 3, and 2  
--     . D  : bit 1, and 0 
--              
--          A    |     B   |    C    |    D
--     ========================================= 
--     | b1 | b0 | b1 | b0 | b1 | b0 | b1 | b0 |
--     ========================================= 
--     MSB 7                               LSB 0
--    

CASRegisterSignal ::= INTEGER {
        compelled(1),
        noncompelled(2),
        semicompelled(3)
        }
-- TEXTUAL-CONVENTION
--  Status
--    mandatory
--  Descr
--    This textual convention defines Register Signaling.
--    
--     Signals (tones) sent from the calling party to the called 
--     party are called forward register signals. 
--     Signals (tones) sent from the called party to the calling 
--     party are backward register signals. 
--    
--     Incoming registers (for incoming calls), receive forward 
--     register signals and return backward register signals.
--     . In compelled register signaling, the backward signal 
--       sent out of the incoming register in response to a forward 
--       register signal stays on until the forward register signal 
--       sent from the other end (outgoing register) is turned off. 
--       Compelled signaling should not be used over satellite links
--       due to latency. 
--     . In non-compelled and semi-compelled register signaling, the 
--       backward signals sent from the incoming register towards 
--       the other end (outgoing register) are pulses and not 
--       continuous.
--    
--     Outgoing registers (for outgoing calls) : send forward 
--     register signals and receive backward register signals.
--     . In compelled and semi-compelled register signaling, when a 
--       forward signal is sent, the tones stay on until the other 
--       end responds with the backward signal that signals the 
--       calling party to turn off the forward tone. The next 
--       forward tone is sent only after the backward tone has been 
--       turned off from the other end (incoming register). 
--       Compelled signaling should not be used for satellite links.
--     . In non-compelled signaling, the calling party sends the 
--       forward signals as pulses. That is, they are on for a 
--       short duration. 

CASForwardSignal ::= INTEGER {
        notApplicable(1),
        i1(2),
        i2(3),
        i3(4),
        i4(5),
        i5(6),
        i6(7),
        i7(8),
        i8(9),
        i9(10),
        i10(11),
        i11(12),
        i12(13),
        i13(14),
        i14(15),
        i15(16),
        ii1(17),
        ii2(18),
        ii3(19),
        ii4(20),
        ii5(21),
        ii6(22),
        ii7(23),
        ii8(24),
        ii9(25),
        ii10(26),
        ii11(27),
        ii12(28),
        ii13(29),
        ii14(30),
        ii15(31),
        iiI1(32),
        iiI2(33),
        iii3(34),
        iii4(35),
        iii5(36),
        iii6(37),
        iii7(38),
        iii8(39),
        iii9(40),
        iii10(41),
        iii11(42),
        iii12(43),
        iii13(44),
        iii14(45),
        iii15(46)
        }
-- TEXTUAL-CONVENTION
--  Status
--    mandatory
--  Descr
--    This textual convention defines all possible Group I, II,
--     and III Forward Signals in Signaling System R2.
--     The Forward Group I signals represent the called numbers,
--     calling party number and equipment requirements for the call. 
--     The Forward Group II signals are calling party's category
--     signal sent by outgoing R2 registers or by outgoing
--     international R2 registers in reply to the backward signals,
--     and give whether national or international working applies.
--     The Forward Group III are distinguished between DNIS and
--     ANI digits.
--  Refer
--     ITU-T recommendation Q.441

CASBackwardSignal ::= INTEGER {
        notApplicable(1),
        a1(2),
        a2(3),
        a3(4),
        a4(5),
        a5(6),
        a6(7),
        a7(8),
        a8(9),
        a9(10),
        a10(11),
        a11(12),
        a12(13),
        a13(14),
        a14(15),
        a15(16),
        b1(17),
        b2(18),
        b3(19),
        b4(20),
        b5(21),
        b6(22),
        b7(23),
        b8(24),
        b9(25),
        b10(26),
        b11(27),
        b12(28),
        b13(29),
        b14(30),
        b15(31),
        c1(32),
        c2(33),
        c3(34),
        c4(35),
        c5(36),
        c6(37),
        c7(38),
        c8(39),
        c9(40),
        c10(41),
        c11(42),
        c12(43),
        c13(44),
        c14(45),
        c15(46)
        }
-- TEXTUAL-CONVENTION
--  Status
--    mandatory
--  Descr
--    This textual convention defines all possible Group A, B and C 
--     Backward Signal in Signaling System R2.
--     The group-A tones are generally used to query the call setup 
--     related information from the outgoing register.
--     The group B signals convey information about the subscriber's 
--     line and equipment status.
--     Some countries use the Group-C tones to differentiate between 
--     ANI and DNIS related operations with the help to Group-III 
--     related tones.
--  Refer
--     ITU-T recommendation Q.441

CASCountryCode ::= INTEGER {
        itu(1),
        argentina(2),
        australia(3),
        bolivia(4),
        brazil(5),
        bulgaria(6),
        china(7),
        colombia(8),
        costaRica(9),
        croatia(10),
        eastEurope(11),
        ecuadorIT(12),
        ecuadorLME(13),
        greece(14),
        guatemala(15),
        hongKong(16),
        india(17),
        indonesia(18),
        israel(19),
        korea(20),
        laos(21),
        malaysia(22),
        malta(23),
        mongolia(24),
        newZealand(25),
        paraguay(26),
        peru(27),
        philippines(28),
        saudiArabia(29),
        singapore(30),
        southAfrica(31),
        telemex(32),
        telnor(33),
        thailand(34),
        uruguay(35),
        venezuela(36),
        vietnam(37),
        bemilcom(38)
        }
-- TEXTUAL-CONVENTION
--  Status
--    mandatory
--  Descr
--    This textual convention defines all possible countries
--     supported to CAS.

ccasIfExtVoiceCfgTable OBJECT-TYPE
    SYNTAX SEQUENCE OF CcasIfExtVoiceCfgEntry
    ACCESS not-accessible
    STATUS mandatory
    DESCRIPTION
        "The voice interface extended table defines the
         parameters related to the configuration of voice interfaces
         (DS0 group of DS1).
        
         This table extends the ccasVoiceCfgTable.
        
         Each table entry describes an instance of a voice interface
         configuration (DS0 group of DS1) in a media gateway."
    ::= { ccasIfExtConfig 1 }

ccasIfExtVoiceCfgEntry OBJECT-TYPE
    SYNTAX CcasIfExtVoiceCfgEntry
    ACCESS not-accessible
    STATUS mandatory
    DESCRIPTION
        "Each entry represents a voice interface (DS0 group of
         DS1) in a media gateway."
    INDEX { ifIndex, ccasGrpCfgIndex }
-- Augments ccasVoiceCfgEntry FROM CISCO-CAS-IF-MIB
    ::= { ccasIfExtVoiceCfgTable 1 }

CcasIfExtVoiceCfgEntry ::= SEQUENCE {
    ccasIfExtVoiceCfgLifNumber Gauge,
    ccasIfExtVoiceCfgCcntrlProfile CCallControlProfileIndexOrZero,
    ccasIfExtVoiceCfgVadEnabled TruthValue,
    ccasIfExtVoiceCfgContinuityTone1 Gauge,
    ccasIfExtVoiceCfgContinuityTone2 Gauge,
    ccasIfExtVoiceCfgModemPassThru INTEGER,
    ccasIfExtVoiceCfgUpspeedCodec CvcCoderTypeRate,
    ccasIfExtVoiceCfgT38MaxFaxTxRate CvcFaxTransmitRate,
    ccasIfExtVoiceCfgT38HsPktPeriod CiscoCodecPacketPeriod,
    ccasIfExtVoiceCfgT38HsRedundancy Gauge,
    ccasIfExtVoiceCfgRepetition ConfigIterator,
    ccasIfExtVoiceCfgBulkCfgOwner OwnerString,
    ccasIfExtVoiceCfgBulkCfgResult BulkConfigResult,
    ccasIfExtVoiceCfgVadTimer INTEGER,
    ccasIfExtVoiceCfgICSEnable TruthValue,
    ccasIfExtVoiceCfgICSIntTimer INTEGER,
    ccasIfExtVoiceCfgTonePlan CVoiceTonePlanIndexOrZero,
    ccasIfExtVoiceCfgGwyLinkId INTEGER,
    ccasIfExtVoiceCfgH248PkgIds CH248Packages,
    ccasIfExtVoiceCfgEventMappingIdx Gauge,
    ccasIfExtVoiceCfgGatewayIndex Gauge,
    ccasIfExtVoiceCfgCasProfile Gauge,
    ccasIfExtVoiceCfgCasVariant Gauge,
    ccasIfExtVoiceCfgDs0ChannelsFail OCTET STRING,
    ccasIfExtVoiceCfgNoiseRegType INTEGER
    }

ccasIfExtVoiceCfgLifNumber OBJECT-TYPE
    SYNTAX Gauge(0..255)
    ACCESS read-write
    STATUS mandatory
    DESCRIPTION
        "This object specifies the LIF (Logical InterFace) number
         associated with this voice interface.
        
         If this object is set to 0, this interface does not have 
         an associated LIF."
    DEFVAL { 0 }
    ::= { ccasIfExtVoiceCfgEntry 1 }

ccasIfExtVoiceCfgCcntrlProfile OBJECT-TYPE
    SYNTAX CCallControlProfileIndexOrZero
--    Rsyntax Gauge(0..65535)
    ACCESS read-write
    STATUS mandatory
    DESCRIPTION
        "This object specifies the index of call control profile that
         is used by this DS0 group.
         If the value of ccasGrpCfgServiceType is 'mgcp(6)', 
         this is the index of cxeCallCtrlProfileTable.
         If the value of ccasGrpCfgServiceType is 'h248(9)',
         this is the index of cmedxPropertyProfileTable.  
        
         The value of 0 means the DS0 group is not associated any
         Profile. The DS0 group is using the default Call
         Control parameters defined in the media gateway."
    DEFVAL { 0 }
    ::= { ccasIfExtVoiceCfgEntry 2 }

ccasIfExtVoiceCfgVadEnabled OBJECT-TYPE
    SYNTAX TruthValue
--    Rsyntax INTEGER {
--        true(1),
--        false(2)
--        }
    ACCESS read-write
    STATUS mandatory
    DESCRIPTION
        "The object specifies VAD (Voice Activity Detection)
         is enabled for the compression DSPs of this interface.
        
         The value of this object is 'false' if the voice 
         interface associated DS0 group uses null signaling.
         (The value of ccasGrpCfgType in ccasGrpCfgTable for the
         DS0 group is set to nullSignaling(16))."
    ::= { ccasIfExtVoiceCfgEntry 3 }

ccasIfExtVoiceCfgContinuityTone1 OBJECT-TYPE
    SYNTAX Gauge(1..4000)
--  Units
--    Hz
    ACCESS read-write
    STATUS mandatory
    DESCRIPTION
        "The object specifies the first frequency tone to be
         sent between the terminating and the originating gateways
         in the continuity test."
    DEFVAL { 2010 }
    ::= { ccasIfExtVoiceCfgEntry 4 }

ccasIfExtVoiceCfgContinuityTone2 OBJECT-TYPE
    SYNTAX Gauge(1..4000)
--  Units
--    Hz
    ACCESS read-write
    STATUS mandatory
    DESCRIPTION
        "The object specifies the second frequency tone to be
         sent between the terminating and the originating gateways
         in the continuity test."
    DEFVAL { 1780 }
    ::= { ccasIfExtVoiceCfgEntry 5 }

ccasIfExtVoiceCfgModemPassThru OBJECT-TYPE
    SYNTAX INTEGER {
        passThruDisabled(1),
        passThruCisco(2),
        passThruNse(3),
        passThruNseAal2(4),
        passThruCa(5),
        passThruTypeE(6),
        system(7),
        passThruNseCa(8)
        }
    ACCESS read-write
    STATUS mandatory
    DESCRIPTION
        "This object specifies the modem pass-through mode:
        
          (1) passThruDisabled: Modem pass-through is disabled
          (2) passThruCisco:    Cisco Proprietary PV (Protocol 
                                Violation) modem protocol used in
                                modem pass-through. 
          (3) passThruNse:      Name Signaling Events(NSE) used in
                                modem pass-through. 
          (4) passThruNseAal2:  Name Signaling Events(NSE) over AAL2
                                used in modem pass-through.
          (5) passThruCa:       Gateway modem pass-through is based
                                on Call Agent(CA) Control.
                                (This is a special way used by
                                 SGCP)
          (6) passThruTypeE:    FRF.11 Payload Type E packet used in
                                modem pass-through.
          (7) system:           System level modem pass-through 
                                configuration is used for the dial-peer.
          (8) passThruNseCa:    Name Signaling Events(NSE) over IP 
                                modem pass-through controlled by 
                                gateway in MGCP 1.0
         "
    DEFVAL { passThruNse }
    ::= { ccasIfExtVoiceCfgEntry 6 }

ccasIfExtVoiceCfgUpspeedCodec OBJECT-TYPE
    SYNTAX CvcCoderTypeRate
--    Rsyntax INTEGER {
--        other(1),
--        fax2400(2),
--        fax4800(3),
--        fax7200(4),
--        fax9600(5),
--        fax14400(6),
--        fax12000(7),
--        g729r8000(10),
--        g729Ar8000(11),
--        g726r16000(12),
--        g726r24000(13),
--        g726r32000(14),
--        g711ulawr64000(15),
--        g711Alawr64000(16),
--        g728r16000(17),
--        g723r6300(18),
--        g723r5300(19),
--        gsmr13200(20),
--        g729Br8000(21),
--        g729ABr8000(22),
--        g723Ar6300(23),
--        g723Ar5300(24),
--        ietfg729r8000(25),
--        gsmeEr12200(26),
--        clearChannel(27),
--        g726r40000(28),
--        llcc(29),
--        gsmAmrNb(30),
--        g722(31)
--        }
    ACCESS read-write
    STATUS mandatory
    DESCRIPTION
        "This object specifies the CODEC type to use for modem upspeed.
         Upspeed is to change the transmission rate of the voice 
         interface to a higher rate of CODEC type."
    ::= { ccasIfExtVoiceCfgEntry 7 }

ccasIfExtVoiceCfgT38MaxFaxTxRate OBJECT-TYPE
    SYNTAX CvcFaxTransmitRate
--    Rsyntax INTEGER {
--        none(1),
--        voiceRate(2),
--        fax2400(3),
--        fax4800(4),
--        fax7200(5),
--        fax9600(6),
--        fax14400(7),
--        fax12000(8)
--        }
    ACCESS read-write
    STATUS deprecated
    DESCRIPTION
        "This object specifies the maximum FAX relay transmission 
         rate."
    DEFVAL { fax14400 }
    ::= { ccasIfExtVoiceCfgEntry 8 }

ccasIfExtVoiceCfgT38HsPktPeriod OBJECT-TYPE
    SYNTAX CiscoCodecPacketPeriod
--    Rsyntax INTEGER {
--        pktPeriod5000us(1),
--        pktPeriod5500us(2),
--        pktPeriod5785us(3),
--        pktPeriod10000us(4),
--        pktPeriod15000us(5),
--        pktPeriod20000us(6),
--        pktPeriod25000us(7),
--        pktPeriod30000us(8),
--        pktPeriod35000us(9),
--        pktPeriod40000us(10),
--        pktPeriod45000us(11),
--        pktPeriod50000us(12),
--        pktPeriod55000us(13),
--        pktPeriod60000us(14),
--        pktPeriod65000us(15),
--        pktPeriod70000us(16),
--        pktPeriod75000us(17),
--        pktPeriod80000us(18),
--        pktPeriod85000us(19),
--        pktPeriod90000us(20)
--        }
--  Units
--    microseconds
    ACCESS read-write
    STATUS deprecated
    DESCRIPTION
        "This object specifies the period of time for primary high 
         speed (HS) data packet."
    DEFVAL { pktPeriod30000us }
    ::= { ccasIfExtVoiceCfgEntry 9 }

ccasIfExtVoiceCfgT38HsRedundancy OBJECT-TYPE
    SYNTAX Gauge(0..2)
--  Units
--    FAX packets
    ACCESS read-write
    STATUS deprecated
    DESCRIPTION
        "The object specifies the number of redundant FAX packets 
         for Internet FAX protocol (IFP) packet transmission. 
         The value of '0' indicates that no redundant Internet 
         FAX packets will be transmitted during the T.38 FAX 
         relay connection."
    REFERENCE
        "ITU-T T.38 Procedures for real-time Group 3 facsimile
         communicating over IP networks"
    DEFVAL { 0 }
    ::= { ccasIfExtVoiceCfgEntry 10 }

ccasIfExtVoiceCfgRepetition OBJECT-TYPE
    SYNTAX ConfigIterator
--    Rsyntax Gauge(1..4294967295)
    ACCESS read-write
    STATUS mandatory
    DESCRIPTION
        "This object is used to repeatedly apply the writable objects
         of ccasIfExtVoiceCfgTable specified in the same SNMP PDU 
         starting from the row specifies by the index of the instance
         for the number of rows specified in this object.
        
         The order of operation is iterated through the logical
         order of the DS0 group. Whether the iteration will be
         applied across the physical boundary or not is depended
         on the system implementation."
    DEFVAL { 1 }
    ::= { ccasIfExtVoiceCfgEntry 11 }

ccasIfExtVoiceCfgBulkCfgOwner OBJECT-TYPE
    SYNTAX OwnerString
--    Rsyntax OCTET STRING
    ACCESS read-write
    STATUS mandatory
    DESCRIPTION
        "This object is used for error checking of the operation
         specified in ccasIfExtVoiceCfgRepetition.
        
         The value of this object is set by the SNMP manager
         with its own identifier at the same time as issuing the bulk
         operation by setting ccasIfExtVoiceCfgRepetition.
         Later on, the SNMP manager should check the value of this
         object, if it is the same with the SNMP manager name,
         then the value of ccasIfExtVoiceCfgBulkCfgResult indicates
         the result of the bulk operation initiated by this SNMP 
         manager."
    ::= { ccasIfExtVoiceCfgEntry 12 }

ccasIfExtVoiceCfgBulkCfgResult OBJECT-TYPE
    SYNTAX BulkConfigResult
--    Rsyntax OCTET STRING(SIZE(0..255))
    ACCESS read-only
    STATUS mandatory
    DESCRIPTION
        "This object is used for error checking of the operation
         specified in ccasIfExtVoiceCfgRepetition.
        
         This object indicates the result of the bulk configuration
         initiated by the SNMP manager specified in the value of
         ccasIfExtVoiceCfgBulkCfgOwner."
    ::= { ccasIfExtVoiceCfgEntry 13 }

ccasIfExtVoiceCfgVadTimer OBJECT-TYPE
    SYNTAX INTEGER(250..65535)
--  Units
--    milliseconds
    ACCESS read-write
    STATUS mandatory
    DESCRIPTION
        "This object specifies the hangover time for VAD. 
        
         Once the voice inactivity is detected, gateway will wait 
         for this duration before activating silence suppression."
    DEFVAL { 250 }
    ::= { ccasIfExtVoiceCfgEntry 14 }

ccasIfExtVoiceCfgICSEnable OBJECT-TYPE
    SYNTAX TruthValue
--    Rsyntax INTEGER {
--        true(1),
--        false(2)
--        }
    ACCESS read-write
    STATUS mandatory
    DESCRIPTION
        "This object specifies whether the Idle Channel suppression 
         (ICS) is enabled for an AAL2 connection."
    DEFVAL { false }
    ::= { ccasIfExtVoiceCfgEntry 15 }

ccasIfExtVoiceCfgICSIntTimer OBJECT-TYPE
    SYNTAX INTEGER(0..65535)
--  Units
--    milliseconds
    ACCESS read-write
    STATUS mandatory
    DESCRIPTION
        "This object specifies a timeout value for ICS integration
         timer. This timer is started once channel idle is detected.
         When the timer is expired, the gateway will stop transmitting
         bearer data to network. Instead, the CAS keep-alive packets
         will be sent."
    DEFVAL { 5000 }
    ::= { ccasIfExtVoiceCfgEntry 16 }

ccasIfExtVoiceCfgTonePlan OBJECT-TYPE
    SYNTAX CVoiceTonePlanIndexOrZero
--    Rsyntax Gauge(0..65535)
    ACCESS read-write
    STATUS mandatory
    DESCRIPTION
        "This object specifies which tone plan the DS0 group is
         using for playing the tones."
    ::= { ccasIfExtVoiceCfgEntry 17 }

ccasIfExtVoiceCfgGwyLinkId OBJECT-TYPE
    SYNTAX INTEGER(0..2147483647)
    ACCESS read-write
    STATUS mandatory
    DESCRIPTION
        "This object specifies the H.248 media gateway link
         that this DS0 group belongs to.  
         This object is applicable only if the value of
         ccasGrpCfgServiceType is 'h248(9)'."
    ::= { ccasIfExtVoiceCfgEntry 18 }

ccasIfExtVoiceCfgH248PkgIds OBJECT-TYPE
    SYNTAX CH248Packages
--    Rsyntax OCTET STRING(SIZE(1..5))
--         BITS are:
--           pkgG(0)
--           pkgRoot(1)
--           pkgToneGen(2)
--           pkgToneDet(3)
--           pkgDG(4)
--           pkgDD(5)
--           pkgCG(6)
--           pkgCD(7)
--           pkgCT(8)
--           pkgNT(9)
--           pkgRTP(10)
--           pkgTDMC(11)
--           pkgAN(12)
--           pkgBCG(13)
--           pkgXCG(14)
--           pkgSrvTn(15)
--           pkgXsrvTn(16)
--           pkgChp(17)
--           pkgIT(18)
--           pkgLLTR(19)
--           pkgBCAS(20)
--           pkgRBS(21)
--           pkgOSES(22)
--           pkgAMET(23)
--           pkgBCASAddr(24)
--           pkgCASBlock(25)
--           pkgGRI(26)
--           rtcpxr(27)
--           xrbm(28)
--           qac(29)
--           pkgDS(30)
--           pkgETerm(31)
--           pkgXnq(32)
--           pkgCTYP(33)
--           pkgIPFAX(34)
    ACCESS read-write
    STATUS mandatory
    DESCRIPTION
        "This object specifies the H.248 packages supported in 
         this DS0 group.  
         This object is applicable only if the value of
         ccasGrpCfgServiceType is 'h248(9)'."
    ::= { ccasIfExtVoiceCfgEntry 19 }

ccasIfExtVoiceCfgEventMappingIdx OBJECT-TYPE
    SYNTAX Gauge(1..65535)
    ACCESS read-write
    STATUS mandatory
    DESCRIPTION
        "This object specifies the action of the voice band data
         signal events handling in this DS0 group.  
         The real-time detected voice band data events are categorized
         by VoiceBandDataEventType defined in 
         CISCO-VOICEBAND-DATA-PROFILE-MIB.
         The value of this object is cvbdpEventMappingIndex in
         cvbdpEventMappingTable.
         The event handling action is specified by the entry
         of cvbdpEventMappingTable indexed by the combination
         of the value of ccasIfExtVoiceCfgGatewayIndex, 
         the value of this object and real-time voice band
         data event specified by VoiceBandDataEventType."
    ::= { ccasIfExtVoiceCfgEntry 20 }

ccasIfExtVoiceCfgGatewayIndex OBJECT-TYPE
    SYNTAX Gauge(1..2147483647)
    ACCESS read-write
    STATUS mandatory
    DESCRIPTION
        "This object specifies the media gateway index that 
         this DS0 group belong to.  
         The value of this object is cmgwIndex in cMediaGwTable."
    ::= { ccasIfExtVoiceCfgEntry 21 }

ccasIfExtVoiceCfgCasProfile OBJECT-TYPE
    SYNTAX Gauge(0..65535)
    ACCESS read-write
    STATUS mandatory
    DESCRIPTION
        "This object specifies the index of CAS profile that
         is used by this DS0 group. The value of this object
         is ccasProfileIndex in ccasIfExtProfileTable.
         This object is applicable only when the DS0 group is
         in a DS1 line whose signal mode is configured for CAS
         signaling, which means the dsx1SignalMode of the DS1
         line is set to 'robbedBit(2)' for T1, or 'bitOriented(3)'
         for E1.
         If the DS1 is not configured for CAS and if the CAS 
         profile index, ccasIfExtDs0GrpCasProfile is specified, 
         the set operation will be rejected, and if it were not
         specified, it will default to a value 0.
         When the DS1 line is configured for CAS signaling,
         all the DS0 channels (ccasGrpCfgDs0Channels) in the 
         DS1 line must be in one and only one DS0 group.
         If the DS1 is configured for CAS and if the CAS profile 
         index, ccasIfExtDs0GrpCasProfile is not specified, 
         the default CAS profile is 1."
    ::= { ccasIfExtVoiceCfgEntry 22 }

ccasIfExtVoiceCfgCasVariant OBJECT-TYPE
    SYNTAX Gauge(0..65535)
    ACCESS read-write
    STATUS mandatory
    DESCRIPTION
        "This object specifies the index of CAS variant that
         is used by this DS0 group. The value of this object 
         is the same as the value of ccasVariantIndex in 
         ccasIfExtVariantTable.
        
         This object is applicable only when the DS0 group is
         in a DS1 line whose signal mode is configured for CAS
         signaling, which means the dsx1SignalMode of the DS1
         line is set to 'robbedBit(2)' for T1, or 'bitOriented(3)'
         for E1.
         When the DS1 line is configured for CAS signaling,
         all the DS0 channels (ccasGrpCfgDs0Channels) in the 
         DS1 line must be in one and only one DS0 group. 
        
         It is a mandatory object when DS1 is configured for CAS. 
         If the DS1 is not configured for CAS and 
         ccasIfExtDs0GrpCasVariant is specified, the set operation 
         will be rejected, and it has a default value 0 when it 
         is not specified.     "
    ::= { ccasIfExtVoiceCfgEntry 23 }

ccasIfExtVoiceCfgDs0ChannelsFail OBJECT-TYPE
    SYNTAX OCTET STRING(SIZE(4))
    ACCESS read-only
    STATUS mandatory
    DESCRIPTION
        "This object contains the bit map of the failure DS0 
         channels in the DS0 group.
         The MSB (most significant bit) is DS0 channel number 1.
         For T1, only higher 24 bits are used to specify the
         the CAS channels for the CAS group.
         A 1-bit indicates the failure channel in group
         and a 0-bit indicates it isn't."
    DEFVAL { '00000000'H }
    ::= { ccasIfExtVoiceCfgEntry 24 }

ccasIfExtVoiceCfgNoiseRegType OBJECT-TYPE
    SYNTAX INTEGER {
        none(1),
        simple(2),
        g711A2(3)
        }
    ACCESS read-write
    STATUS mandatory
    DESCRIPTION
        "This object specifies the type of comfort noise generation:
        
          (1) none: No comfort noise generation
          (2) simple: Cisco Proprietary comfort noise generation
          (3) g711A2: ITU G.711 Appendix II compliant
        
         This object is applicable only if 
         'ccasVoiceCfgNoiseRegEnable' is set to 'true'.
         When Voice Activation Detection(VAD) is enabled by 
         setting 'ccasIfExtVoiceCfgVadEnabled' to 'true',
         'ccasVoiceCfgNoiseRegEnable' indicates whether or not
         the background comfort noise should be played to fill
         the silence gaps.   
         If 'ccasVoiceCfgNoiseRegEnable'  
         is set to 'false', this object contains value 'none(1)'."
    REFERENCE
        "1. A comfort noise payload definition for ITU-T G.711
            use in packet-based multimedia communication systems, 
            ITU-T G.711 Appendix 2, Februrary, 2000.
         2. CISCO-CAS-IF-MIB, ccasVoiceCfgNoiseRegEnable "
    DEFVAL { simple }
    ::= { ccasIfExtVoiceCfgEntry 25 }

ccasIfExtDs0GrpCfgTable OBJECT-TYPE
    SYNTAX SEQUENCE OF CcasIfExtDs0GrpCfgEntry
    ACCESS not-accessible
    STATUS mandatory
    DESCRIPTION
        "The voice interface extended table defines the
         parameters related to the configuration of voice interfaces
         (DS0 group of DS1).
        
         This table extends the ccasVoiceCfgTable.
        
         Each table entry describes an instance of a voice interface
         configuration (DS0 group of DS1) in a media gateway."
    ::= { ccasIfExtConfig 3 }

ccasIfExtDs0GrpCfgEntry OBJECT-TYPE
    SYNTAX CcasIfExtDs0GrpCfgEntry
    ACCESS not-accessible
    STATUS mandatory
    DESCRIPTION
        "Each entry represents a DS0 group interface."
    INDEX { ifIndex, ccasGrpCfgIndex }
-- Augments ccasGrpCfgEntry FROM CISCO-CAS-IF-MIB
    ::= { ccasIfExtDs0GrpCfgTable 1 }

CcasIfExtDs0GrpCfgEntry ::= SEQUENCE {
    ccasIfExtDs0GrpRepetition ConfigIterator,
    ccasIfExtDs0GrpRepeatOwner OwnerString,
    ccasIfExtDs0GrpRepeatResult BulkConfigResult
    }

ccasIfExtDs0GrpRepetition OBJECT-TYPE
    SYNTAX ConfigIterator
--    Rsyntax Gauge(1..4294967295)
    ACCESS read-write
    STATUS mandatory
    DESCRIPTION
        "This object is used to repeatedly apply the writable objects
         of ccasIfExtDs0GrpCfgTable specified in the same SNMP PDU
         starting from the row specifies by the index of the instance
         for the number of rows specified in this object.
        
         The repetition operation works differently for different
         DS0 channel bitmap configuration. When the DS0 channel
         bitmap is configured to contain a single DS0 channel,
         the order of operation is iterated through the value of
         DS0 group and the logical order of DS0 channel; When the DS0
         channel bitmap is configured to contain more than one DS0
         channels, the order of operation is iterated through logical
         order of DS1 channel, and all the iteration operations use
         the same DS0 channel bitmap configuration.
        
         The repetition iteration will stop once the value of iterated
         value reaches its maximum limit. In the case of a single DS0
         channel configuration, the repetition will stop when either
         the value of the DS0 group or the DS0 channel has reached its
         maximum. For multiple DS0 channel configuration, the repetition
         will stop once the value of DS1 reaches its maximum."
    DEFVAL { 1 }
    ::= { ccasIfExtDs0GrpCfgEntry 1 }

ccasIfExtDs0GrpRepeatOwner OBJECT-TYPE
    SYNTAX OwnerString
--    Rsyntax OCTET STRING
    ACCESS read-write
    STATUS mandatory
    DESCRIPTION
        "This object is used for error checking of the operation
         specified in ccasIfExtDs0GrpRepetition.
        
         The value of this object is set by the SNMP manager
         with its own identifier at the same time as issuing the bulk
         operation by setting ccasIfExtDs0GrpRepetition.
         Later on, the SNMP manager should check the value of this
         object, if it is the same as the SNMP manager name,
         then the value of ccasIfExtDs0GrpRepeatResult indicates
         the result of the bulk operation initiated by this SNMP
         manager."
    ::= { ccasIfExtDs0GrpCfgEntry 2 }

ccasIfExtDs0GrpRepeatResult OBJECT-TYPE
    SYNTAX BulkConfigResult
--    Rsyntax OCTET STRING(SIZE(0..255))
    ACCESS read-only
    STATUS mandatory
    DESCRIPTION
        "This object is used for error checking of the operation
         specified in ccasIfExtDs0GrpRepetition.
        
         This object indicates the result of the repetition
         initiated by the SNMP manager specified in the value of
         ccasIfExtDs0GrpRepeatOwner."
    ::= { ccasIfExtDs0GrpCfgEntry 3 }

ccasIfExtProfileTable OBJECT-TYPE
    SYNTAX SEQUENCE OF CcasIfExtProfileEntry
    ACCESS not-accessible
    STATUS mandatory
    DESCRIPTION
        "This table specifies a list of CAS profiles. Each CAS profile
         consists of the configurable CAS attributes related to: 
         . Line signal timers table, ccasIfExtLineSignalTimerTable.
         . Register signals table, ccasIfExtRegisterSignalTable.
         . Register signal timers table, ccasIfExtRegSignalTimerTable.
         . General configurations table, ccasIfExtGeneralConfigTable.
        
         A CAS profile can be applied to a DS0 group of the DS1 line
         with CAS signaling. A DS1 line is configured for CAS signaling
         when its dsx1SignalMode is set to 'robbedBit(2)' for T1 or 
         'bitOriented(3)' for E1."
    ::= { ccasIfExtProfile 1 }

ccasIfExtProfileEntry OBJECT-TYPE
    SYNTAX CcasIfExtProfileEntry
    ACCESS not-accessible
    STATUS mandatory
    DESCRIPTION
        "Each entry represents a CAS profile in media gateway."
    INDEX { cmgwIndex, ccasProfileIndex }
    ::= { ccasIfExtProfileTable 1 }

CcasIfExtProfileEntry ::= SEQUENCE {
    ccasProfileIndex Gauge,
    ccasProfileLineSigTimer Gauge,
    ccasProfileRegisterSignal Gauge,
    ccasProfileRegSigTimer Gauge,
    ccasProfileGeneralCfg Gauge,
    ccasProfileRowStatus RowStatus
    }

ccasProfileIndex OBJECT-TYPE
    SYNTAX Gauge(1..65535)
    ACCESS not-accessible
    STATUS mandatory
    DESCRIPTION
        "This object uniquely identifies the CAS profile. 
         The value of 1 specifies the default CAS profile in the 
         media gateway."
    ::= { ccasIfExtProfileEntry 1 }

ccasProfileLineSigTimer OBJECT-TYPE
    SYNTAX Gauge(1..65535)
    ACCESS read-write
    STATUS mandatory
    DESCRIPTION
        "This object specifies the attributes of CAS line 
         signaling timers indicated by ccasLSTIndex in
         ccasIfExtLineSignalTimerTable."
    DEFVAL { 1 }
    ::= { ccasIfExtProfileEntry 2 }

ccasProfileRegisterSignal OBJECT-TYPE
    SYNTAX Gauge(1..65535)
    ACCESS read-write
    STATUS mandatory
    DESCRIPTION
        "This object specifies the attributes of CAS register 
         signals indicated by ccasRSIndex in
         ccasIfExtRegisterSignalTable."
    DEFVAL { 1 }
    ::= { ccasIfExtProfileEntry 3 }

ccasProfileRegSigTimer OBJECT-TYPE
    SYNTAX Gauge(1..65535)
    ACCESS read-write
    STATUS mandatory
    DESCRIPTION
        "This object specifies the attributes of CAS register 
         signaling timers indicated by ccasRSTIndex in
         ccasIfExtRegSignalTimerTable."
    DEFVAL { 1 }
    ::= { ccasIfExtProfileEntry 4 }

ccasProfileGeneralCfg OBJECT-TYPE
    SYNTAX Gauge(1..65535)
    ACCESS read-write
    STATUS mandatory
    DESCRIPTION
        "This object specifies the general CAS attributes indicated
         by ccasGCnfIndex in ccasIfExtGeneralConfigTable."
    DEFVAL { 1 }
    ::= { ccasIfExtProfileEntry 5 }

ccasProfileRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "When the entry is created, all the associated entries 
         indexed by the following objects must be existing:
             ccasProfileLineSigTimer,
             ccasProfileRegisterSignal,
             ccasProfileRegSigTimer,
             ccasProfileGeneralCfg.  
        
         The entry of the default CAS profile indexed by 1 is 
         created by the system automatically, it cannot be added,
         deleted, or modified."
    ::= { ccasIfExtProfileEntry 6 }

ccasIfExtVariantTable OBJECT-TYPE
    SYNTAX SEQUENCE OF CcasIfExtVariantEntry
    ACCESS not-accessible
    STATUS mandatory
    DESCRIPTION
        "This table specifies a list of CAS signaling protocols such as
         R2 CAS, Feature Group D Oprerator Services ( FGD OS). 
         Each CAS variant is downloaded to and parsed by 
         the media gateway.
         A CAS variant can be applied to a DS0 group of the DS1
         line with CAS signaling. A DS1 line is configured for CAS 
         signaling when its dsx1SignalMode is set to 'robbedBit(2)' 
         for T1 or 'bitOriented(3)' for E1."
    ::= { ccasIfExtProfile 2 }

ccasIfExtVariantEntry OBJECT-TYPE
    SYNTAX CcasIfExtVariantEntry
    ACCESS not-accessible
    STATUS mandatory
    DESCRIPTION
        "Each entry represents a CAS variant in media gateway.
        
         Upon the creation of the entry, the CAS variant 
         specified by ccasVariantFile will be downloaded to
         the media gateway. After the file is successfully parsed
         by the media gateway, a corresponding entry in 
         ccasIfExtIncomingLineSignalTable and a corresponding entry
         in ccasIfExtOutgoingLineSignalTable will be automatically
         created. 
         When the entry is deleted, the corresponding entry in
         ccasIfExtIncomingLineSignalTable and the corresponding entry
         in ccasIfExtOutgoingLineSignalTable will be deleted by the
         system automatically."
    INDEX { cmgwIndex, ccasVariantIndex }
    ::= { ccasIfExtVariantTable 1 }

CcasIfExtVariantEntry ::= SEQUENCE {
    ccasVariantIndex Gauge,
    ccasVariantFile SnmpAdminString,
    ccasVariantSource INTEGER,
    ccasVariantNumberCount Gauge,
    ccasVariantState INTEGER,
    ccasVariantRowStatus RowStatus
    }

ccasVariantIndex OBJECT-TYPE
    SYNTAX Gauge(1..65535)
    ACCESS not-accessible
    STATUS mandatory
    DESCRIPTION
        "An arbitrary value which uniquely identifies the CAS variant 
         in the media gateway."
    ::= { ccasIfExtVariantEntry 1 }

ccasVariantFile OBJECT-TYPE
    SYNTAX SnmpAdminString(SIZE(1..64))
--    Rsyntax OCTET STRING(SIZE(1..64))
    ACCESS read-write
    STATUS mandatory
    DESCRIPTION
        "This object specifies the valid file name with extension
         '.o' stored on the media gateway's hard disk.
         The CAS variant file can be transferred to the media
         gateway via FTP text file transfer mechanism."
    ::= { ccasIfExtVariantEntry 2 }

ccasVariantSource OBJECT-TYPE
    SYNTAX INTEGER {
        internal(1),
        external(2)
        }
    ACCESS read-write
    STATUS mandatory
    DESCRIPTION
        "This object specifies the source from where the CAS  
         variant file must be fetched. 
         . internal: Value indicates that the file is built 
           into the firmware.
         . external: Value indicates that the file is to be 
           downloaded from the media gateway."
    DEFVAL { internal }
    ::= { ccasIfExtVariantEntry 3 }

ccasVariantNumberCount OBJECT-TYPE
    SYNTAX Gauge
    ACCESS read-only
    STATUS mandatory
    DESCRIPTION
        "This object indicates the number of DS0 groups of the DS1
         line which are used for the CAS variant."
    ::= { ccasIfExtVariantEntry 4 }

ccasVariantState OBJECT-TYPE
    SYNTAX INTEGER {
        initInProgress(1),
        initSuccessfully(2),
        initFailed(3)
        }
    ACCESS read-only
    STATUS mandatory
    DESCRIPTION
        "This object indicates the configuration status of the  
         CAS variant.
         . initInProgress: The state machine is being initialized.
         . initSuccessfully: The state machine was initialized properly.
         . initFailed: The intialization failed."
    ::= { ccasIfExtVariantEntry 5 }

ccasVariantRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "When the entry is created, the ccasVariantFile object is 
         mandatory.
         The entry can be added or deleted, but not modified by
         the manager."
    ::= { ccasIfExtVariantEntry 6 }

ccasIfExtIncomingLineSignalTable OBJECT-TYPE
    SYNTAX SEQUENCE OF CcasIfExtIncomingLineSignalEntry
    ACCESS not-accessible
    STATUS mandatory
    DESCRIPTION
        "This table defines the parameters related to the incoming 
         line signals for CAS variant. 
         The appropriate signal definitions from this table will 
         be downloaded to the media gateway. The media gateway will 
         use the information provided in this table to match the 
         incoming bit pattern to a particular signal."
    ::= { ccasIfExtConfigLineSignal 1 }

ccasIfExtIncomingLineSignalEntry OBJECT-TYPE
    SYNTAX CcasIfExtIncomingLineSignalEntry
    ACCESS not-accessible
    STATUS mandatory
    DESCRIPTION
        "Each entry represents an incoming line signal definition 
         for the CAS variant corresponding to the CAS Variant index.
         Entries in this table are implicitly created when a CAS 
         variant file is parsed when an entry is created in the CAS 
         variant table to add a new variant. Entries are implicitly 
         removed when the CAS variant associated with these entries 
         is removed."
    INDEX { cmgwIndex, ccasVariantIndex, ccasILSSignalNameIndex }
    ::= { ccasIfExtIncomingLineSignalTable 1 }

CcasIfExtIncomingLineSignalEntry ::= SEQUENCE {
    ccasILSSignalNameIndex Gauge,
    ccasILSSignalName SnmpAdminString,
    ccasILSRxPattern CASLineSignal,
    ccasILSMatchedRxPattern CASLineSignal,
    ccasILSMatchedTxPattern CASLineSignal,
    ccasILSMinMakeTime Gauge,
    ccasILSMaxMakeTime Gauge,
    ccasILSMinBreakTime Gauge,
    ccasILSMaxBreakTime Gauge
    }

ccasILSSignalNameIndex OBJECT-TYPE
    SYNTAX Gauge(1..65535)
    ACCESS not-accessible
    STATUS mandatory
    DESCRIPTION
        "This object specifies the Signal Name index for the various  
         CAS line signals. 
         This object along with the cmgwIndex and ccasVariantIndex 
         identify an unique entry in this table."
    ::= { ccasIfExtIncomingLineSignalEntry 2 }

ccasILSSignalName OBJECT-TYPE
    SYNTAX SnmpAdminString(SIZE(1..64))
--    Rsyntax OCTET STRING(SIZE(1..64))
    ACCESS read-only
    STATUS mandatory
    DESCRIPTION
        "This object indicates CAS signal name corresponding to the 
         ccasILSSignalNameIndex.
         The media gateway uses ccasILSRxPattern along with following 
         objects:
         ccasILSMatchedRxPattern
         ccasILSMatchedTxPattern 
         ccasILSMinMakeTime                
         ccasILSMaxMakeTime                
         ccasILSMinBreakTime               
         ccasILSMaxBreakTime               
         to determine a ccasILSSignalName."
    ::= { ccasIfExtIncomingLineSignalEntry 3 }

ccasILSRxPattern OBJECT-TYPE
    SYNTAX CASLineSignal
--    Rsyntax OCTET STRING(SIZE(1))
    ACCESS read-only
    STATUS mandatory
    DESCRIPTION
        "This object indicates the ABCD bit pattern of the signal 
         being received on the DS0. "
    ::= { ccasIfExtIncomingLineSignalEntry 4 }

ccasILSMatchedRxPattern OBJECT-TYPE
    SYNTAX CASLineSignal
--    Rsyntax OCTET STRING(SIZE(1))
    ACCESS read-only
    STATUS mandatory
    DESCRIPTION
        "This object indicates the previous matched ABCD bit pattern 
         that was received on the DS0."
    ::= { ccasIfExtIncomingLineSignalEntry 5 }

ccasILSMatchedTxPattern OBJECT-TYPE
    SYNTAX CASLineSignal
--    Rsyntax OCTET STRING(SIZE(1))
    ACCESS read-only
    STATUS mandatory
    DESCRIPTION
        "This object indicates the current ABCD bit pattern being 
         transmitted on the DS0."
    ::= { ccasIfExtIncomingLineSignalEntry 6 }

ccasILSMinMakeTime OBJECT-TYPE
    SYNTAX Gauge(2..4294967295)
--  Units
--    milliseconds
    ACCESS read-write
    STATUS mandatory
    DESCRIPTION
        "This object specifies the minimum time for which the received
         pattern (ccasILSRxPattern) must persist to be considered 
         a valid state change or transition.
         If the state change lasts for less than this time, it does 
         not match the signal name.  "
    ::= { ccasIfExtIncomingLineSignalEntry 7 }

ccasILSMaxMakeTime OBJECT-TYPE
    SYNTAX Gauge(0..4294967295)
--  Units
--    milliseconds
    ACCESS read-write
    STATUS mandatory
    DESCRIPTION
        "This object specifies the maximum time for which the Rx 
         pattern (ccasILSRxPattern) must persist to be considered 
         a valid state change or transition.
         The value of 0 indicates there is no maximum make time 
         for this signal. 
         The value of ccasILSMaxMakeTime must be greater and equal
         ccasILSMinMakeTime. 
         If the value is non-zero and the state change lasts for  
         more than the maximum value specified, it does not match 
         the signal name."
    ::= { ccasIfExtIncomingLineSignalEntry 8 }

ccasILSMinBreakTime OBJECT-TYPE
    SYNTAX Gauge(0..4294967295)
--  Units
--    milliseconds
    ACCESS read-write
    STATUS mandatory
    DESCRIPTION
        "This object specifies the minimum time for which the ABCD  
         bit pattern being received on the line, and should go back 
         to its original signal pattern after the make pattern has 
         been asserted.
         The value of 0 indicates there is no minimum break time
         for this signal. 
         If the value is non-zero and the state change lasts for 
         less than the minimum break time specified, it does not 
         match the signal name."
    ::= { ccasIfExtIncomingLineSignalEntry 9 }

ccasILSMaxBreakTime OBJECT-TYPE
    SYNTAX Gauge(0..4294967295)
--  Units
--    milliseconds
    ACCESS read-write
    STATUS mandatory
    DESCRIPTION
        "This object specifies the maximum time for which the ABCD 
         bit pattern being received on the line, and go back to its 
         original signal pattern after the make pattern has been 
         asserted. 
         The value of 0 indicates there is no maximum break time 
         for this signal. 
         The value of ccasILSMaxBreakTime must be greater than and 
         equal ccasILSMinMakeTime.
         If the value is non-zero and the state change lasts longer
         than the maximum break time specified, it does not match 
         the signal name."
    ::= { ccasIfExtIncomingLineSignalEntry 10 }

ccasIfExtOutgoingLineSignalTable OBJECT-TYPE
    SYNTAX SEQUENCE OF CcasIfExtOutgoingLineSignalEntry
    ACCESS not-accessible
    STATUS mandatory
    DESCRIPTION
        "This table defines the parameters related to for the 
         outgoing line signals pertaining to that CAS variant."
    ::= { ccasIfExtConfigLineSignal 2 }

ccasIfExtOutgoingLineSignalEntry OBJECT-TYPE
    SYNTAX CcasIfExtOutgoingLineSignalEntry
    ACCESS not-accessible
    STATUS mandatory
    DESCRIPTION
        "Each entry represents an incoming line signal definition 
         for the CAS variant corresponding to the CAS Variant index.
         Entries in this table are implicitly created when a CAS 
         variant file is parsed when an entry is created in the CAS 
         variant table to add a new variant. Entries are implicitly 
         removed when the CAS variant associated with these entries 
         is removed."
    INDEX { cmgwIndex, ccasVariantIndex, ccasOLSSignalNameIndex }
    ::= { ccasIfExtOutgoingLineSignalTable 1 }

CcasIfExtOutgoingLineSignalEntry ::= SEQUENCE {
    ccasOLSSignalNameIndex Gauge,
    ccasOLSCasSignalName SnmpAdminString,
    ccasOLSTxPattern CASLineSignal,
    ccasOLSMakeTime Gauge,
    ccasOLSBreakTime Gauge
    }

ccasOLSSignalNameIndex OBJECT-TYPE
    SYNTAX Gauge(1..65535)
    ACCESS not-accessible
    STATUS mandatory
    DESCRIPTION
        "This object specifies the Signal Name index for the various 
         CAS Line signals. This object along with the ccasVariantIndex
         identify a unique entry in this table."
    ::= { ccasIfExtOutgoingLineSignalEntry 1 }

ccasOLSCasSignalName OBJECT-TYPE
    SYNTAX SnmpAdminString(SIZE(1..64))
--    Rsyntax OCTET STRING(SIZE(1..64))
    ACCESS read-only
    STATUS mandatory
    DESCRIPTION
        "This object indicates outgoing CAS signal name."
    ::= { ccasIfExtOutgoingLineSignalEntry 2 }

ccasOLSTxPattern OBJECT-TYPE
    SYNTAX CASLineSignal
--    Rsyntax OCTET STRING(SIZE(1))
    ACCESS read-only
    STATUS mandatory
    DESCRIPTION
        "This object indicates the ABCD transmit bit pattern."
    ::= { ccasIfExtOutgoingLineSignalEntry 3 }

ccasOLSMakeTime OBJECT-TYPE
    SYNTAX Gauge(0..4294967295)
--  Units
--    milliseconds
    ACCESS read-write
    STATUS mandatory
    DESCRIPTION
        "This object specifies the time value for which the Tx Pattern 
         being transmitted."
    ::= { ccasIfExtOutgoingLineSignalEntry 4 }

ccasOLSBreakTime OBJECT-TYPE
    SYNTAX Gauge(0..4294967295)
--  Units
--    milliseconds
    ACCESS read-write
    STATUS mandatory
    DESCRIPTION
        "This object specifies the time value for which the pattern 
         being transmitted will switch to the original pattern before 
         the Tx pattern was asserted on the line.
         The value of 0 indicates there is no break time for this 
         signal. "
    ::= { ccasIfExtOutgoingLineSignalEntry 5 }

ccasIfExtRegisterSignalTable OBJECT-TYPE
    SYNTAX SEQUENCE OF CcasIfExtRegisterSignalEntry
    ACCESS not-accessible
    STATUS mandatory
    DESCRIPTION
        "This table defines the signal to action definitions for the 
         Register signals for R2 variant."
    ::= { ccasIfExtConfigRegisterSignal 1 }

ccasIfExtRegisterSignalEntry OBJECT-TYPE
    SYNTAX CcasIfExtRegisterSignalEntry
    ACCESS not-accessible
    STATUS mandatory
    DESCRIPTION
        "Entries are configured per country. 
         When DS0 groups are associated with a CAS profile, it is  
         also associated with one of these entries if the CAS variant  
         is an R2 variant.
         Entries are explicitly created modified and deleted by  
         managers. When the country is specified, the rest of the 
         objects of this entry are populated with known defaults. 
         These can be overridden via configuration.
         Entries with index 1 are reserved for the ITU defaults. 
         This entry may not be added, modified or deleted. In this 
         table, no two actions can have the same signal defined for  
         it. The signal to action mapping should be unique. "
    INDEX { cmgwIndex, ccasRSIndex }
    ::= { ccasIfExtRegisterSignalTable 1 }

CcasIfExtRegisterSignalEntry ::= SEQUENCE {
    ccasRSIndex Gauge,
    ccasRSCountry CASCountryCode,
    ccasRSSubRegion SnmpAdminString,
    ccasBwdRSNextDigitANI CASBackwardSignal,
    ccasBwdRSNextDigitDNIS CASBackwardSignal,
    ccasBwdRSPrevDigit CASBackwardSignal,
    ccasBwdRSXtoGroupBSignals CASBackwardSignal,
    ccasBwdRSCongestion CASBackwardSignal,
    ccasBwdRSCallingPartyCategory CASBackwardSignal,
    ccasBwdRSAddrCompleteGroupA CASBackwardSignal,
    ccasBwdRSPrevNminus2Digit CASBackwardSignal,
    ccasBwdRSPrevNminus3Digit CASBackwardSignal,
    ccasBwdRSCountryCode CASBackwardSignal,
    ccasBwdRSLangDiscr CASBackwardSignal,
    ccasBwdRSNatureOfCircuit CASBackwardSignal,
    ccasBwdRSInfoEchoSuppressor CASBackwardSignal,
    ccasBwdRSInternationalCongst CASBackwardSignal,
    ccasBwdRSXtoGroupC CASBackwardSignal,
    ccasBwdRSRepeatLastDigit CASBackwardSignal,
    ccasBwdRSRepeatCalledDigit CASBackwardSignal,
    ccasBwdRSPlaySITTone CASBackwardSignal,
    ccasBwdRSSubscriberLineBusy CASBackwardSignal,
    ccasBwdRSNetworkCongstInGroupB CASBackwardSignal,
    ccasBwdRSInvalidDialedNumber CASBackwardSignal,
    ccasBwdRSSubLineFreeWithCharge CASBackwardSignal,
    ccasBwdRSSubLineFreeWithNoCharge CASBackwardSignal,
    ccasBwdRSSubLineOutOfOrder CASBackwardSignal,
    ccasBwdRSAnnouncement CASBackwardSignal,
    ccasBwdRSXtoGrpASendNextDNIS CASBackwardSignal,
    ccasBwdRSXtoGrpASendDNISFrmBeg CASBackwardSignal,
    ccasBwdRSXtoGrpAResendLastDNIS CASBackwardSignal,
    ccasBwdRSSSendCatSwGrpB CASBackwardSignal,
    ccasBwdRSSGrpCCong CASBackwardSignal,
    ccasFwdRSANIDigitAvailable CASForwardSignal,
    ccasFwdRSANIDigitNotAvailable CASForwardSignal,
    ccasFwdRSEndANICallingPartyNotRev CASForwardSignal,
    ccasFwdRSEndANICallingPartyRev CASForwardSignal,
    ccasFwdRSEndOfDNISDigit CASForwardSignal,
    ccasFwdRSNoCategoryAvailble CASForwardSignal,
    ccasFwdRSCCEchoSuppressor CASForwardSignal,
    ccasFwdRSCCNoEchoSuppressor CASForwardSignal,
    ccasFwdRSCCInsertEchoSuppressor CASForwardSignal,
    ccasFwdRSIncHalfEchoRequired CASForwardSignal,
    ccasFwdRSTestCall CASForwardSignal,
    ccasFwdRSSatelLinkIncluded CASForwardSignal,
    ccasFwdRSSatelLinkNotIncluded CASForwardSignal,
    ccasFwdRSDiscriminatorDigit CASForwardSignal,
    ccasFwdRSOtherLanguage CASForwardSignal,
    ccasFwdRSOtherLanguage1 CASForwardSignal,
    ccasFwdRSOtherLanguage2 CASForwardSignal,
    ccasFwdRSRequestNotAccepted CASForwardSignal,
    ccasFwdRSSubWithoutPriorNational CASForwardSignal,
    ccasFwdRSSubPriorNational CASForwardSignal,
    ccasFwdRSSubPriorInternational CASForwardSignal,
    ccasFwdRSMaintenanceEquipment CASForwardSignal,
    ccasFwdRSOperatorCall CASForwardSignal,
    ccasFwdRSDataTransNational CASForwardSignal,
    ccasFwdRSDataTransInternational CASForwardSignal,
    ccasFwdRSOperNoFwdTransFacility CASForwardSignal,
    ccasFwdRSOperFwdTransFacility CASForwardSignal,
    ccasFwdRSSubsrcWithMeter CASForwardSignal,
    ccasFwdRSSubsrcWithIDD CASForwardSignal,
    ccasRSInterpreFirstANIDigit INTEGER,
    ccasRSGetValueFromValidIndex Gauge,
    ccasRSSeqInfCollect SnmpAdminString,
    ccasRSSendFirstFwdSig INTEGER,
    ccasRSRowStatus RowStatus
    }

ccasRSIndex OBJECT-TYPE
    SYNTAX Gauge(1..65535)
    ACCESS not-accessible
    STATUS mandatory
    DESCRIPTION
        "This is an arbitrary index that uniquely identifies an
         entry in this table. This parameter is mandatory when 
         creating an entry. "
    ::= { ccasIfExtRegisterSignalEntry 1 }

ccasRSCountry OBJECT-TYPE
    SYNTAX CASCountryCode
--    Rsyntax INTEGER {
--        itu(1),
--        argentina(2),
--        australia(3),
--        bolivia(4),
--        brazil(5),
--        bulgaria(6),
--        china(7),
--        colombia(8),
--        costaRica(9),
--        croatia(10),
--        eastEurope(11),
--        ecuadorIT(12),
--        ecuadorLME(13),
--        greece(14),
--        guatemala(15),
--        hongKong(16),
--        india(17),
--        indonesia(18),
--        israel(19),
--        korea(20),
--        laos(21),
--        malaysia(22),
--        malta(23),
--        mongolia(24),
--        newZealand(25),
--        paraguay(26),
--        peru(27),
--        philippines(28),
--        saudiArabia(29),
--        singapore(30),
--        southAfrica(31),
--        telemex(32),
--        telnor(33),
--        thailand(34),
--        uruguay(35),
--        venezuela(36),
--        vietnam(37),
--        bemilcom(38)
--        }
    ACCESS read-write
    STATUS mandatory
    DESCRIPTION
        "This object specifies the country where the meaning for
         the signal definition/action applies. 
         This parameter is mandatory when creating an entry. 
         When the R2 country (ITU or other) is specified, the default 
         values for the rest of the MIB objects are populated based 
         on this."
    ::= { ccasIfExtRegisterSignalEntry 2 }

ccasRSSubRegion OBJECT-TYPE
    SYNTAX SnmpAdminString(SIZE(0..64))
--    Rsyntax OCTET STRING(SIZE(0..64))
    ACCESS read-write
    STATUS mandatory
    DESCRIPTION
        "This object is used to describe a variation within a  
         particular country."
    DEFVAL { "" }
    ::= { ccasIfExtRegisterSignalEntry 3 }

ccasBwdRSNextDigitANI OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal requesting 
         transmission of the next ANI digit (n + 1) after 
         reception of digit n.
         The default value is country specific.        "
    REFERENCE
        "ITU-T Q440 - Specifications of signaling system R2
                      Interregister Signaling.
                      Section 4.2.4.1 Backward signals."
    ::= { ccasIfExtRegisterSignalEntry 4 }

ccasBwdRSNextDigitDNIS OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal requesting 
         transmission of the next DNIS digit (n + 1) after 
         reception of digit n.
         The default value is country specific."
    REFERENCE
        "ITU-T Q440 - Specifications of signaling system R2
                      Interregister Signaling.
                      Section 4.2.4.1 Backward signals."
    ::= { ccasIfExtRegisterSignalEntry 5 }

ccasBwdRSPrevDigit OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal requesting 
         transmission of the previous ANI or DNIS digit (n - 1)
         after reception of digit n.
         The default value is country specific. "
    REFERENCE
        "ITU-T Q440 - Specifications of signaling system R2
                      Interregister Signaling.
                      Section 4.2.4.1 Backward signals."
    ::= { ccasIfExtRegisterSignalEntry 6 }

ccasBwdRSXtoGroupBSignals OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal indicating that the 
         incoming R2 register at the incoming end needs no additional 
         address digit and is about to go over to transmission of a 
         Group B signal conveying information about the condition of 
         the equipment at the incoming exchange or the condition of 
         the called subscribers line.
         The default value is country specific. "
    REFERENCE
        "ITU-T Q440 - Specifications of signaling system R2
                      Interregister Signaling.
                      Section 4.2.4.1 Backward signals."
    ::= { ccasIfExtRegisterSignalEntry 7 }

ccasBwdRSCongestion OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal indicating that:
         . Congestion of national links.
         . Congestion in selection stages of terminal international 
           or national exchanges.
         . Occurrence of time-out or abnormal release of a System 
           R2 register produced for any reason.
         The default value is country specific. "
    REFERENCE
        "ITU-T Q440 - Specifications of signaling system R2
                      Interregister Signaling.
                      Section 4.2.4.1 Backward signals."
    ::= { ccasIfExtRegisterSignalEntry 8 }

ccasBwdRSCallingPartyCategory OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal requesting for a  
         calling party category information or a Group II signal. 
         The default value is country specific. "
    REFERENCE
        "ITU-T Q440 - Specifications of signaling system R2
                      Interregister Signaling.
                      Section 4.2.4.1 Backward signals."
    ::= { ccasIfExtRegisterSignalEntry 9 }

ccasBwdRSAddrCompleteGroupA OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal indicating that the  
         R2 register at the incoming end needs no additional digit, 
         but will not send Group B signals. 
         The call has to be charged on answer.
         The default value is country specific.    "
    REFERENCE
        "ITU-T Q440 - Specifications of signaling system R2
                      Interregister Signaling.
                      Section 4.2.4.1 Backward signals."
    ::= { ccasIfExtRegisterSignalEntry 10 }

ccasBwdRSPrevNminus2Digit OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal requesting the
         sending of the ANI or DNIS digit (n - 2) after reception 
         of digit n.
         The default value is country specific."
    REFERENCE
        "ITU-T Q440 - Specifications of signaling system R2
                      Interregister Signaling.
                      Section 4.2.4.1 Backward signals."
    ::= { ccasIfExtRegisterSignalEntry 11 }

ccasBwdRSPrevNminus3Digit OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal requesting the
         sending  of the ANI or DNIS digit (n - 3) after reception 
         of digit n.
         The default value is country specific.   "
    REFERENCE
        "ITU-T Q440 - Specifications of signaling system R2
                      Interregister Signaling.
                      Section 4.2.4.1 Backward signals."
    ::= { ccasIfExtRegisterSignalEntry 12 }

ccasBwdRSCountryCode OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal requesting the  
         country code indicator.  
         The default value is country specific. "
    REFERENCE
        "ITU-T Q440 - Specifications of signaling system R2
                      Interregister Signaling.
                      Section 4.2.4.1 Backward signals."
    ::= { ccasIfExtRegisterSignalEntry 13 }

ccasBwdRSLangDiscr OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal requesting the  
         language digit or the discriminating digit.
         . Operator assistance: requesting a language digit. 
         . Automatic call: requesting a discriminating digit. 
         The default value is country specific. "
    REFERENCE
        "ITU-T Q440 - Specifications of signaling system R2
                      Interregister Signaling.
                      Section 4.2.4.1 Backward signals."
    ::= { ccasIfExtRegisterSignalEntry 14 }

ccasBwdRSNatureOfCircuit OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal requesting  
         information regarding the nature of the circuits involved 
         in the connection so far, i.e. satellite link or not. 
         The default value is country specific. "
    REFERENCE
        "ITU-T Q440 - Specifications of signaling system R2
                      Interregister Signaling.
                      Section 4.2.4.1 Backward signals."
    ::= { ccasIfExtRegisterSignalEntry 15 }

ccasBwdRSInfoEchoSuppressor OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal requesting  
         information regarding the nature of echo suppressor being 
         used in the connection.
         The default value is country specific. "
    REFERENCE
        "ITU-T Q440 - Specifications of signaling system R2
                      Interregister Signaling.
                      Section 4.2.4.1 Backward signals."
    ::= { ccasIfExtRegisterSignalEntry 16 }

ccasBwdRSInternationalCongst OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal indicating:
         . Congestion on international links.
         . Congestion in selection stages at an international 
           transit exchange or at a terminal international exchange 
           and/or its outgoing links.
         . Occurrence of time-out or abnormal release of a System R2 
           register produced for any reason.
         The default value is country specific. "
    REFERENCE
        "ITU-T Q440 - Specifications of signaling system R2
                      Interregister Signaling.
                      Section 4.2.4.1 Backward signals."
    ::= { ccasIfExtRegisterSignalEntry 17 }

ccasBwdRSXtoGroupC OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal requesting switch  
         to reception of group C signals.
         The default value is country specific. "
    ::= { ccasIfExtRegisterSignalEntry 18 }

ccasBwdRSRepeatLastDigit OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal requesting 
         resending of the last digit just sent out.
         The default value is country specific. "
    ::= { ccasIfExtRegisterSignalEntry 19 }

ccasBwdRSRepeatCalledDigit OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal requesting for 
         out pulsing of the called digits or DNIS from beginning.
         The default value is country specific. "
    ::= { ccasIfExtRegisterSignalEntry 20 }

ccasBwdRSPlaySITTone OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal indicating that 
         SIT tone should be played towards the calling party. 
         The default value is country specific.     "
    ::= { ccasIfExtRegisterSignalEntry 21 }

ccasBwdRSSubscriberLineBusy OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal indicating that  
         the line or lines connecting the called subscriber to 
         the exchange are busy or engaged.
         The default value is country specific.   "
    REFERENCE
        "ITU-T Q440 - Specifications of signaling system R2
                      Interregister Signaling.
                      Section 4.2.4.2 Backward signals."
    ::= { ccasIfExtRegisterSignalEntry 22 }

ccasBwdRSNetworkCongstInGroupB OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal indicating that 
         congestion condition has occured after the changeover 
         to Group B signals.
         The default value is country specific. "
    REFERENCE
        "ITU-T Q440 - Specifications of signaling system R2
                      Interregister Signaling.
                      Section 4.2.4.2 Backward signals."
    ::= { ccasIfExtRegisterSignalEntry 23 }

ccasBwdRSInvalidDialedNumber OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal indicating that the 
         dialed or called number is invalid or not in use (e.g. an 
         unused country code, an unused trunk code or subscriber 
         number that has not been allocated). 
         The default value is country specific."
    REFERENCE
        "ITU-T Q440 - Specifications of signaling system R2
                      Interregister Signaling.
                      Section 4.2.4.2 Backward signals."
    ::= { ccasIfExtRegisterSignalEntry 24 }

ccasBwdRSSubLineFreeWithCharge OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal indicating that  
         the called party's line is free and that the call has to  
         be charged on answer.
         The default value is country specific. "
    REFERENCE
        "ITU-T Q440 - Specifications of signaling system R2
                      Interregister Signaling.
                      Section 4.2.4.2 Backward signals."
    ::= { ccasIfExtRegisterSignalEntry 25 }

ccasBwdRSSubLineFreeWithNoCharge OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal indicating that  
         the called party line is free but is not to be charged 
         on answer.
         The default value is country specific. "
    REFERENCE
        "ITU-T Q440 - Specifications of signaling system R2
                      Interregister Signaling.
                      Section 4.2.4.2 Backward signals."
    ::= { ccasIfExtRegisterSignalEntry 26 }

ccasBwdRSSubLineOutOfOrder OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal indicating that the 
         called party line is out of service or faulty. 
         The default value is country specific. "
    REFERENCE
        "ITU-T Q440 - Specifications of signaling system R2
                      Interregister Signaling.
                      Section 4.2.4.2 Backward signals."
    ::= { ccasIfExtRegisterSignalEntry 27 }

ccasBwdRSAnnouncement OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal indicating that an 
         announcement follows this indication. 
         The default value is country specific. "
    ::= { ccasIfExtRegisterSignalEntry 28 }

ccasBwdRSXtoGrpASendNextDNIS OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal requesting the other 
         exchange to switch to reception of group A and send the next 
         DNIS digit.
         The default value is country specific. "
    ::= { ccasIfExtRegisterSignalEntry 29 }

ccasBwdRSXtoGrpASendDNISFrmBeg OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal requesting the other
         exchange to switch to reception of group A and send the DNIS 
         digits from the beginning. 
         The default value is country specific. "
    ::= { ccasIfExtRegisterSignalEntry 30 }

ccasBwdRSXtoGrpAResendLastDNIS OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal requesting the other 
         exchange to switch to reception of group A and resend the last 
         DNIS digit sent out.
         The default value is country specific. "
    ::= { ccasIfExtRegisterSignalEntry 31 }

ccasBwdRSSSendCatSwGrpB OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal requesting the end 
         receiving this signal to send the subscriber category 
         information and switch to grp B from group C.
         The default value is country specific. "
    ::= { ccasIfExtRegisterSignalEntry 32 }

ccasBwdRSSGrpCCong OBJECT-TYPE
    SYNTAX CASBackwardSignal
--    Rsyntax INTEGER {
--        notApplicable(1),
--        a1(2),
--        a2(3),
--        a3(4),
--        a4(5),
--        a5(6),
--        a6(7),
--        a7(8),
--        a8(9),
--        a9(10),
--        a10(11),
--        a11(12),
--        a12(13),
--        a13(14),
--        a14(15),
--        a15(16),
--        b1(17),
--        b2(18),
--        b3(19),
--        b4(20),
--        b5(21),
--        b6(22),
--        b7(23),
--        b8(24),
--        b9(25),
--        b10(26),
--        b11(27),
--        b12(28),
--        b13(29),
--        b14(30),
--        b15(31),
--        c1(32),
--        c2(33),
--        c3(34),
--        c4(35),
--        c5(36),
--        c6(37),
--        c7(38),
--        c8(39),
--        c9(40),
--        c10(41),
--        c11(42),
--        c12(43),
--        c13(44),
--        c14(45),
--        c15(46)
--        }
    ACCESS read-write
    STATUS mandatory
    DESCRIPTION
        "This object specifies a backward signal indicating that 
         congestion occurred in the network when in group C signaling 
         state.
         The default value is country specific. "
    ::= { ccasIfExtRegisterSignalEntry 33 }

ccasFwdRSANIDigitAvailable OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating that ANI 
         digits are available. 
         This is used in country variants like India to indicate
         that the ANI digits are available when the backward signal 
         requesting for ANI digits is received, before pulsing out 
         the actual ANI digits.
         The default value is country specific.   "
    ::= { ccasIfExtRegisterSignalEntry 34 }

ccasFwdRSANIDigitNotAvailable OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating that  
         there are no ANI digits available for out pulsing. 
         The default value is country specific.    "
    ::= { ccasIfExtRegisterSignalEntry 35 }

ccasFwdRSEndANICallingPartyNotRev OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating 
         that there are no more ANI digits to out pulse and the 
         calling party can not be revealed to the called party. 
         The default value is country specific.    "
    ::= { ccasIfExtRegisterSignalEntry 36 }

ccasFwdRSEndANICallingPartyRev OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating that 
         there are no more ANI digits to out pulse and the calling 
         party can be revealed to the called party. 
         The default value is country specific.    "
    ::= { ccasIfExtRegisterSignalEntry 37 }

ccasFwdRSEndOfDNISDigit OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating the end 
         of DNIS digits. 
         The default value is country specific."
    ::= { ccasIfExtRegisterSignalEntry 38 }

ccasFwdRSNoCategoryAvailble OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating that  
         there is no calling party category (information) available  
         to be sent out. 
         The default value is country specific."
    ::= { ccasIfExtRegisterSignalEntry 39 }

ccasFwdRSCCEchoSuppressor OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal. When it is used 
         as the first forward signal and it indicates that:
         . A country code will follow on an international link.
         . The call requires echo suppressors.
         The default value is country specific.   "
    REFERENCE
        "ITU-T Q440 - Specifications of signaling system R2
                      Interregister Signaling.
                      Section 4.2.3.1 Forward signals."
    ::= { ccasIfExtRegisterSignalEntry 40 }

ccasFwdRSCCNoEchoSuppressor OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal. When it is used
         as the first forward signal and it indicates that:
         . A country code will follow on an international link.
         . The call may not require any echo suppressor.
         The default value is country specific. "
    REFERENCE
        "ITU-T Q440 - Specifications of signaling system R2
                      Interregister Signaling.
                      Section 4.2.3.1 Forward signals."
    ::= { ccasIfExtRegisterSignalEntry 41 }

ccasFwdRSCCInsertEchoSuppressor OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal. When it is used 
         as the first forward signal and it indicates that:
         . A country code will follow on an international link.
         . The outgoing half echo suppressor has to be inserted.
         The default value is country specific.    "
    REFERENCE
        "ITU-T Q440 - Specifications of signaling system R2 
                      Interregister Signaling.
                      Section 4.2.3.1 Forward signals."
    ::= { ccasIfExtRegisterSignalEntry 42 }

ccasFwdRSIncHalfEchoRequired OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating that: 
         . The outgoing half echo suppressor has been inserted.
         . The incoming half echo suppressor is required. 
         The default value is country specific.    "
    REFERENCE
        "ITU-T Q440 - Specifications of signaling system R2 
                      Interregister Signaling.
                      Section 4.2.3.1 Forward signals."
    ::= { ccasIfExtRegisterSignalEntry 43 }

ccasFwdRSTestCall OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal. When it is used 
         as the first forward signal and indicates that the call  
         is being originated by test equipment.
         The default value is country specific. "
    REFERENCE
        "ITU-T Q440 - Specifications of signaling system R2 
                      Interregister Signaling.
                      Section 4.2.3.1 Forward signals."
    ::= { ccasIfExtRegisterSignalEntry 44 }

ccasFwdRSSatelLinkIncluded OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating that 
         a satellite link is included in the connection.
         This signal is sent in response to backward signal 
         requesting for nature of circuit. 
         The default value is country specific. "
    REFERENCE
        "ITU-T Q440 - Specifications of signaling system R2 
                      Interregister Signaling.
                      Section 4.2.3.1 Forward signals."
    ::= { ccasIfExtRegisterSignalEntry 45 }

ccasFwdRSSatelLinkNotIncluded OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating that 
         no satellite link is included in the connection.
         This signal is sent in response to backward signal 
         requesting for nature of circuit. 
         The default value is country specific. "
    REFERENCE
        "ITU-T Q440 - Specifications of signaling system R2 
                      Interregister Signaling.
                      Section 4.2.3.1 Forward signals."
    ::= { ccasIfExtRegisterSignalEntry 46 }

ccasFwdRSDiscriminatorDigit OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating the  
         digit that separates or distinguishes different information 
         blocks in the forward signals being generated or received. 
         The default value is country specific. "
    REFERENCE
        "ITU-T Q440 - Specifications of signaling system R2 
                      Interregister Signaling.
                      Section 4.2.3.1 Forward signals."
    ::= { ccasIfExtRegisterSignalEntry 47 }

ccasFwdRSOtherLanguage OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating that the
         language to be used for an operator assisted call.  
         The default value is country specific. "
    REFERENCE
        "ITU-T Q440 - Specifications of signaling system R2 
                      Interregister Signaling.
                      Section 4.2.3.1 Forward signals."
    ::= { ccasIfExtRegisterSignalEntry 48 }

ccasFwdRSOtherLanguage1 OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating that the
         language to be used for an operator assisted call.
         The default value is country specific. "
    REFERENCE
        "ITU-T Q440 - Specifications of signaling system R2 
                      Interregister Signaling.
                      Section 4.2.3.1 Forward signals."
    ::= { ccasIfExtRegisterSignalEntry 49 }

ccasFwdRSOtherLanguage2 OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating that the
         language to be used for an operator assisted call.
         The default value is country specific. "
    REFERENCE
        "ITU-T Q440 - Specifications of signaling system R2 
                      Interregister Signaling.
                      Section 4.2.3.1 Forward signals."
    ::= { ccasIfExtRegisterSignalEntry 50 }

ccasFwdRSRequestNotAccepted OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating that the 
         receiving backward signal could not be processed or defined.
         The default value is country specific. "
    REFERENCE
        "ITU-T Q440 - Specifications of signaling system R2 
                      Interregister Signaling.
                      Section 4.2.3.1 Forward signals."
    ::= { ccasIfExtRegisterSignalEntry 51 }

ccasFwdRSSubWithoutPriorNational OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating that the 
         call is set up from a subscriber's line and is non-priority.
         The default value is country specific. "
    REFERENCE
        "ITU-T Q440 - Specifications of signaling system R2 
                      Interregister Signaling.
                      Section 4.2.3.2 Forward signals."
    ::= { ccasIfExtRegisterSignalEntry 52 }

ccasFwdRSSubPriorNational OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating that the 
         call is set up from a subscriber's line to which priority 
         treatment of calls has been accorded. This signal is specified
         to national trunks only.
         The default value is country specific. "
    REFERENCE
        "ITU-T Q440 - Specifications of signaling system R2 
                      Interregister Signaling.
                      Section 4.2.3.2 Forward signals."
    ::= { ccasIfExtRegisterSignalEntry 53 }

ccasFwdRSSubPriorInternational OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating that the 
         call is set up from a subscriber's line to which priority 
         treatment of calls has been accorded. This signal is specified
         to international trunks only.
         The default value is country specific. "
    REFERENCE
        "ITU-T Q440 - Specifications of signaling system R2 
                      Interregister Signaling.
                      Section 4.2.3.2 Forward signals."
    ::= { ccasIfExtRegisterSignalEntry 54 }

ccasFwdRSMaintenanceEquipment OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating that  
         the call comes from maintenance equipment. 
         The default value is country specific. "
    REFERENCE
        "ITU-T Q440 - Specifications of signaling system R2 
                      Interregister Signaling.
                      Section 4.2.3.2 Forward signals."
    ::= { ccasIfExtRegisterSignalEntry 55 }

ccasFwdRSOperatorCall OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating that  
         the call is setup from an operator. 
         The default value is country specific. "
    REFERENCE
        "ITU-T Q440 - Specifications of signaling system R2 
                      Interregister Signaling.
                      Section 4.2.3.2 Forward signals."
    ::= { ccasIfExtRegisterSignalEntry 56 }

ccasFwdRSDataTransNational OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating that  
         the call is being used for national data transmission.
         The default value is country specific. "
    ::= { ccasIfExtRegisterSignalEntry 57 }

ccasFwdRSDataTransInternational OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating that  
         the call is being used for international data transmission. 
         The default value is country specific. "
    REFERENCE
        "ITU-T Q440 - Specifications of signaling system R2 
                      Interregister Signaling.
                      Section 4.2.3.2 Forward signals."
    ::= { ccasIfExtRegisterSignalEntry 58 }

ccasFwdRSOperNoFwdTransFacility OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating the call
         is being set up from a subscriber's line, operator's 
         position or from maintenance equipment and no forward 
         transfer signal will be used.
         The default value is country specific. "
    REFERENCE
        "ITU-T Q440 - Specifications of signaling system R2 
                      Interregister Signaling.
                      Section 4.2.3.2 Forward signals."
    ::= { ccasIfExtRegisterSignalEntry 59 }

ccasFwdRSOperFwdTransFacility OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating the call
         is set up from an operator's position with possibility of 
         recourse to the forward transfer facility.
         The default value is country specific. "
    REFERENCE
        "ITU-T Q440 - Specifications of signaling system R2 
                      Interregister Signaling.
                      Section 4.2.3.2 Forward signals."
    ::= { ccasIfExtRegisterSignalEntry 60 }

ccasFwdRSSubsrcWithMeter OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating the 
         subscribers have a meter.
         The default value is country specific. "
    ::= { ccasIfExtRegisterSignalEntry 61 }

ccasFwdRSSubsrcWithIDD OBJECT-TYPE
    SYNTAX CASForwardSignal
--    Rsyntax INTEGER {
--        notApplicable(1),
--        i1(2),
--        i2(3),
--        i3(4),
--        i4(5),
--        i5(6),
--        i6(7),
--        i7(8),
--        i8(9),
--        i9(10),
--        i10(11),
--        i11(12),
--        i12(13),
--        i13(14),
--        i14(15),
--        i15(16),
--        ii1(17),
--        ii2(18),
--        ii3(19),
--        ii4(20),
--        ii5(21),
--        ii6(22),
--        ii7(23),
--        ii8(24),
--        ii9(25),
--        ii10(26),
--        ii11(27),
--        ii12(28),
--        ii13(29),
--        ii14(30),
--        ii15(31),
--        iiI1(32),
--        iiI2(33),
--        iii3(34),
--        iii4(35),
--        iii5(36),
--        iii6(37),
--        iii7(38),
--        iii8(39),
--        iii9(40),
--        iii10(41),
--        iii11(42),
--        iii12(43),
--        iii13(44),
--        iii14(45),
--        iii15(46)
--        }
    ACCESS read-write
    STATUS mandatory
    DESCRIPTION
        "This object specifies a forward signal indicating the 
         subscribers have an International Direct Dial facility.
         The default value is country specific. "
    ::= { ccasIfExtRegisterSignalEntry 62 }

ccasRSInterpreFirstANIDigit OBJECT-TYPE
    SYNTAX INTEGER {
        firstANIDigit(1),
        aniAvailableOrNot(2),
        subscriberCategory(3)
        }
    ACCESS read-write
    STATUS mandatory
    DESCRIPTION
        "This object is used to interpret the meaning of the first 
         ANI digit for both receiving and transmitting when sent
         and received.
          .firstANIDigit: First ANI digit.
          .aniAvailableOrNot: Indication as to whether ANI is available 
           or not.
          .subscriberCategory: Subscriber category.
         The default value is country specific."
    ::= { ccasIfExtRegisterSignalEntry 63 }

ccasRSGetValueFromValidIndex OBJECT-TYPE
    SYNTAX Gauge(1..400)
    ACCESS read-write
    STATUS mandatory
    DESCRIPTION
        "This object specifies the entry index from which values 
         for the objects not specified in the set operation will 
         be copied over from. 
         If both the country index and this object are specified, 
         this object takes precedence. If this object is not 
         specified for an entry, it defaults to the entry index."
    ::= { ccasIfExtRegisterSignalEntry 64 }

ccasRSSeqInfCollect OBJECT-TYPE
    SYNTAX SnmpAdminString(SIZE(1..255))
--    Rsyntax OCTET STRING(SIZE(1..255))
    ACCESS read-write
    STATUS mandatory
    DESCRIPTION
        "This object determines the sequence in which information
         will be gathered by the incoming register.
        
         Only a set of predefined characters can be used in the
         octet string notation of the sequence. The special
         character and the alphabet strings allowed are listed below:
        
         '/' - Separator between different elements of information
               that should be collected.
          - Indicates how many digits of the following
               information element should be collected before
               switching to collecting the next information element.
               Number always precedes one of the information elements
               such as D or A. If no number is specified, all of the
               digits for that information element are collected
               before fetching digits for next info element.
        
         di   - DNIS/Destination number/dialed number/called number.
         si   - ANIS/Source number/calling number.
         sc   - Subscriber Category.
         cc   - Country Code.
         es   - Echo Suppression Information.
         noc  - Nature of Circuit.
         disc - Discriminator Digit.
         The default value is country specific."
    ::= { ccasIfExtRegisterSignalEntry 65 }

ccasRSSendFirstFwdSig OBJECT-TYPE
    SYNTAX INTEGER {
        dnisCCLangDisc(1),
        dnisLangDiscCC(2),
        cCLangDiscDnis(3),
        cCDnisLangDisc(4),
        langDiscCCDnis(5),
        langDiscDnisCC(6)
        }
    ACCESS read-write
    STATUS mandatory
    DESCRIPTION
        "This object specifies the information element that will 
         take precedence when being sent out as the first forward 
         register signal for an outgoing call. This can be either 
         the first DNIS digit, indication that country code follows 
         or the language/discriminator digit. When all the above 
         information is available at the GW, this object determines 
         which one will be sent out first for each option, list 
         is from most preferred to least preferred.
          .dniscclangdisc: First DNIS, country code indication, 
           language/discriminator.
          .dnislangdisccc: First DNIS, language/discriminator,   
           country code indication.
          .cclangdiscdnis: Country code indication, language/ 
           discriminator, first DNIS.
          .ccdnislangdisc: Country code indication, first DNIS, 
           language/discriminator.
          .langdiscccdnis: Language/discriminator, country code  
           indication, first DNIS.
          .langdiscdniscc: Language/discriminator, first DNIS, 
           country code indication.
        The default value is country specific."
    ::= { ccasIfExtRegisterSignalEntry 66 }

ccasRSRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used for adding, modifying, and deleting  
         the entries from the ccasRegisterSignalTable.
         A default entry with index value 1 is created at 
         initialization, and it cannot be modified or deleted."
    ::= { ccasIfExtRegisterSignalEntry 67 }

ccasIfExtLineSignalTimerTable OBJECT-TYPE
    SYNTAX SEQUENCE OF CcasIfExtLineSignalTimerEntry
    ACCESS not-accessible
    STATUS mandatory
    DESCRIPTION
        "This table defines all timers related to the CAS Line 
         signals."
    ::= { ccasIfExtConfigLineSignal 3 }

ccasIfExtLineSignalTimerEntry OBJECT-TYPE
    SYNTAX CcasIfExtLineSignalTimerEntry
    ACCESS not-accessible
    STATUS mandatory
    DESCRIPTION
        "Each entry represents a CAS Line Signal Timer in media 
         gateway."
    INDEX { cmgwIndex, ccasLSTIndex }
    ::= { ccasIfExtLineSignalTimerTable 1 }

CcasIfExtLineSignalTimerEntry ::= SEQUENCE {
    ccasLSTIndex Gauge,
    ccasLSTIdleGuardTimer Gauge,
    ccasLSTClearFwdTimer Gauge,
    ccasLSTClearBwdTimer Gauge,
    ccasLSTReleaseGuardTimer Gauge,
    ccasLSTCASGlareTimer Gauge,
    ccasLSTAnswerMeterDelayTimer Gauge,
    ccasLSTCASDebounceTimer Gauge,
    ccasLSTSeizeAckRspTimer Gauge,
    ccasLSTDelayBetRegAnsAndLineAns Gauge,
    ccasLSTSeizeAckToDigitTimer Gauge,
    ccasLSTRowStatus RowStatus
    }

ccasLSTIndex OBJECT-TYPE
    SYNTAX Gauge(1..65535)
    ACCESS not-accessible
    STATUS mandatory
    DESCRIPTION
        "An arbitrary index that uniquely identifies a  
         entry in the ccasIfExtLineSignalTimerTable.
         The index 1 is reserved for the default entry."
    ::= { ccasIfExtLineSignalTimerEntry 1 }

ccasLSTIdleGuardTimer OBJECT-TYPE
    SYNTAX Gauge(0..4294967295)
--  Units
--    milliseconds
    ACCESS read-write
    STATUS mandatory
    DESCRIPTION
        "This object specifies the maximum amount of time MG will 
         wait for receipt of the idle signal on the line.
         For T1 interfaces idle signal corresponds to on-hook
         pattern on line.
         For E1 interfaces idle signal corresponds to idle pattern 
         on line.
         The value of 0 indicates the timer will not be started 
         and MG would wait forever."
    REFERENCE
        "Bellcore Publication: TR-NPL-000258 - Compatibility 
         Information for Feature Group D Switched Access Service"
    DEFVAL { 10000 }
    ::= { ccasIfExtLineSignalTimerEntry 2 }

ccasLSTClearFwdTimer OBJECT-TYPE
    SYNTAX Gauge(0..4294967295)
--  Units
--    milliseconds
    ACCESS read-write
    STATUS mandatory
    DESCRIPTION
        "This object specifies the value of the timer that the GW 
         will start at the request of the controlling application 
         such as MGC for receipt of the clear forward signal on the 
         line.
         This object is applied to R2 CAS."
    REFERENCE
        "ITU-T Recommandation Q.118 Abnormal conditions, section 3."
    DEFVAL { 120000 }
    ::= { ccasIfExtLineSignalTimerEntry 3 }

ccasLSTClearBwdTimer OBJECT-TYPE
    SYNTAX Gauge(0..4294967295)
--  Units
--    milliseconds
    ACCESS read-write
    STATUS mandatory
    DESCRIPTION
        "This object specifies the value of the timer that the GW  
         will start at the request of the controlling application 
         such as MGC for receipt of the clear backward signal.
         This object is applied to R2 CAS."
    REFERENCE
        "ITU-T Recommandation Q.118 Abnormal conditions, section 3."
    DEFVAL { 120000 }
    ::= { ccasIfExtLineSignalTimerEntry 4 }

ccasLSTReleaseGuardTimer OBJECT-TYPE
    SYNTAX Gauge(0..4294967295)
--  Units
--    millliseconds
    ACCESS read-write
    STATUS mandatory
    DESCRIPTION
        "This object specifies the delay between reception of the 
         clear forward signal and the sending of the idle signal.  
         Upon reception of the clear forward signal, GW starts the 
         release guard timer. Upon expiry of this timer, the idle
         signal is generated.
         This timer is required to prevent seizing of the channel 
         immediately.
         This object is applied to R2 CAS."
    REFERENCE
        "Bellcore Publication: TR-NPL-000258
         Compatibility Information for Feature Group D Switched 
         Access Service."
    DEFVAL { 800 }
    ::= { ccasIfExtLineSignalTimerEntry 5 }

ccasLSTCASGlareTimer OBJECT-TYPE
    SYNTAX Gauge(0..4294967295)
--  Units
--    milliseconds
    ACCESS read-write
    STATUS mandatory
    DESCRIPTION
        "This object specifies the maximum amount of time MG will 
         wait for other end to back out when glare occurs on a DS0 
         line.  
         Change in incoming off-hook signal to on-hook signal 
         with-in this time frame indicates that other end has backed 
         down."
    REFERENCE
        "H248.25 basic cas package and MS packages"
    DEFVAL { 4000 }
    ::= { ccasIfExtLineSignalTimerEntry 6 }

ccasLSTAnswerMeterDelayTimer OBJECT-TYPE
    SYNTAX Gauge(0..4294967295)
--  Units
--    milliseconds
    ACCESS read-write
    STATUS mandatory
    DESCRIPTION
        "The object specifies the delay between generation of the 
         answer signal and the generation of the meter signal. 
         The GW will start this timer after having sent the line
         answer signal."
    DEFVAL { 600 }
    ::= { ccasIfExtLineSignalTimerEntry 7 }

ccasLSTCASDebounceTimer OBJECT-TYPE
    SYNTAX Gauge(1..4294967295)
--  Units
--    milliseconds
    ACCESS read-write
    STATUS mandatory
    DESCRIPTION
        "This object specifies the amount of time for which the line 
         signal should persist to be valid. 
         The value of ccasLSTCASDebounceTimer must be less than or 
         equal the value of following objects:
         ccasILSMinMakeTime,              
         ccasILSMaxMakeTime,             
         ccasILSMinBreakTime,             
         ccasILSMaxBreakTime in ccasIfExtIncomingLineSignalTable."
    DEFVAL { 5 }
    ::= { ccasIfExtLineSignalTimerEntry 8 }

ccasLSTSeizeAckRspTimer OBJECT-TYPE
    SYNTAX Gauge(0..4294967295)
--  Units
--    milliseconds
    ACCESS read-write
    STATUS mandatory
    DESCRIPTION
        "This object specifies the maximum amount of time MG will 
         wait for reception of seize ack signal.
         Seize Ack signal is expected in response of seize signal.
         This object is applied for both R2 CAS and non R2 CAS."
    REFERENCE
        "TIA-689-A: PBX and KTS Support of Enhanced 911
         Emergency Calling Service, section 5.2.3.3"
    DEFVAL { 200 }
    ::= { ccasIfExtLineSignalTimerEntry 9 }

ccasLSTDelayBetRegAnsAndLineAns OBJECT-TYPE
    SYNTAX Gauge(0..65535)
--  Units
--    seconds
    ACCESS read-write
    STATUS mandatory
    DESCRIPTION
        "This object specifies the timer that will be started 
         after register signaling completes successfully,
         within which the answer line signal should be 
         received.  
         This applies to outgoing R2 registers.
         The value of 0 indicates the timer will not be started 
         and MG would wait forever."
    REFERENCE
        "ITU-T Q.118 Abnormal Conditions Special Release 
         Arrangements, section 1."
    DEFVAL { 90 }
    ::= { ccasIfExtLineSignalTimerEntry 10 }

ccasLSTSeizeAckToDigitTimer OBJECT-TYPE
    SYNTAX Gauge(0..65535)
--  Units
--    seconds
    ACCESS read-write
    STATUS mandatory
    DESCRIPTION
        "This object specifies the amount of time that the GW 
         should wait for the reception address digits after  
         sending seize ack signal.
         The value of 0 indicates the timer will not be started 
         and MG would wait forever."
    REFERENCE
        "ITU-T Q.476 Abnormal Release of Outgoing and Incoming
         R2 Register, section 5.5.2.1"
    DEFVAL { 15 }
    ::= { ccasIfExtLineSignalTimerEntry 11 }

ccasLSTRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used for adding, deleting, and modifying  
         the entries from the ccasIfExtLineSignalTimerTable.
         A default entry with index value 1 is created at 
         initialization, and it cannot be modified or deleted."
    ::= { ccasIfExtLineSignalTimerEntry 12 }

ccasIfExtRegSignalTimerTable OBJECT-TYPE
    SYNTAX SEQUENCE OF CcasIfExtRegSignalTimerEntry
    ACCESS not-accessible
    STATUS mandatory
    DESCRIPTION
        "This table defines the timers related to the CAS register 
         signals."
    ::= { ccasIfExtConfigTimer 2 }

ccasIfExtRegSignalTimerEntry OBJECT-TYPE
    SYNTAX CcasIfExtRegSignalTimerEntry
    ACCESS not-accessible
    STATUS mandatory
    DESCRIPTION
        "Each entry represents a CAS Register Signal Timer in media 
         gateway."
    INDEX { cmgwIndex, ccasRSTIndex }
    ::= { ccasIfExtRegSignalTimerTable 1 }

CcasIfExtRegSignalTimerEntry ::= SEQUENCE {
    ccasRSTIndex Gauge,
    ccasRSTAnswerSigTimer Gauge,
    ccasRSTCompelledFwdToneOnTimer Gauge,
    ccasRSTCompelledFwdToneOffTimer Gauge,
    ccasRSTCompelledBwdToneOnTimer Gauge,
    ccasRSTOutFwdPulseOnTimer Gauge,
    ccasRSTOutFwdPulseOffTimer Gauge,
    ccasRSTIncFwdPulseOnTimer Gauge,
    ccasRSTBwdPulseOnTimer Gauge,
    ccasRSTIncomingRegSigDuration Gauge,
    ccasRSTOutgoingRegSigDuration Gauge,
    ccasRSTCalledPartyInterDigTimer Gauge,
    ccasRSTRowStatus RowStatus
    }

ccasRSTIndex OBJECT-TYPE
    SYNTAX Gauge(1..65535)
    ACCESS not-accessible
    STATUS mandatory
    DESCRIPTION
        "An arbitrary index that uniquely identifies a 
         entry in the ccasIfExtRegSignalTimerTable.
         The index of 1 is reserved for the default entry."
    ::= { ccasIfExtRegSignalTimerEntry 1 }

ccasRSTAnswerSigTimer OBJECT-TYPE
    SYNTAX Gauge(0..65535)
--  Units
--    seconds
    ACCESS read-write
    STATUS mandatory
    DESCRIPTION
        "This object specifies the timer that is started
         after having sent out the last forward digit within
         which the backward register answer signal should be
         received.
        
         Normally it would be same as the compelled forward tone 
         on timer, ccasRSTCompelledFwdToneOnTimer, but in some  
         country variants, this could be different.  "
    DEFVAL { 15 }
    ::= { ccasIfExtRegSignalTimerEntry 2 }

ccasRSTCompelledFwdToneOnTimer OBJECT-TYPE
    SYNTAX Gauge(0..65535)
--  Units
--    seconds
    ACCESS read-write
    STATUS mandatory
    DESCRIPTION
        "This object specifies the period for which the forward  
         digit tone stays on, waiting for a reception of the  
         backward signal in compelled signaling.
         This timer is started after the forward signal digit is 
         turned on."
    REFERENCE
        "ITU Q.476 Abnormal Release of Outgoing and Incoming
         R2 Register, section 5.5.1.1"
    DEFVAL { 15 }
    ::= { ccasIfExtRegSignalTimerEntry 3 }

ccasRSTCompelledFwdToneOffTimer OBJECT-TYPE
    SYNTAX Gauge(0..65535)
--  Units
--    seconds
    ACCESS read-write
    STATUS mandatory
    DESCRIPTION
        "This object specifies the period for which the forward 
         signal digit is turned off in compelled signaling. 
         This timer is started after the backward signal is 
         received and after the forward signal digit is turned 
         off on the outgoing interface. "
    REFERENCE
        "ITU Q.476 Abnormal Release of Outgoing and Incoming
         R2 Register, section 5.5.1.2"
    DEFVAL { 24 }
    ::= { ccasIfExtRegSignalTimerEntry 4 }

ccasRSTCompelledBwdToneOnTimer OBJECT-TYPE
    SYNTAX Gauge(0..65535)
--  Units
--    seconds
    ACCESS read-write
    STATUS mandatory
    DESCRIPTION
        "This object specifies the period for which the backward 
         signal stays on waiting for the forward digit signal to 
         go off in compelled signaling.  
         This timer is started after the backward signal is sent 
         in response to the forward signal digit. "
    DEFVAL { 15 }
    ::= { ccasIfExtRegSignalTimerEntry 5 }

ccasRSTOutFwdPulseOnTimer OBJECT-TYPE
    SYNTAX Gauge(0..65535)
--  Units
--    milliseconds
    ACCESS read-write
    STATUS mandatory
    DESCRIPTION
        "This object specifies the timer is started after the 
         forward digit tone is sent out. Tone is turned off 
         after the timer expires.
         This object applies to outgoing R2 registers where the 
         forward signals are sent as pulses for non-compelled
         signaling. "
    DEFVAL { 150 }
    ::= { ccasIfExtRegSignalTimerEntry 6 }

ccasRSTOutFwdPulseOffTimer OBJECT-TYPE
    SYNTAX Gauge(0..65535)
--  Units
--    milliseconds
    ACCESS read-write
    STATUS mandatory
    DESCRIPTION
        "This object specifies the interval between two forward 
         pulse tones. 
         This object applies to outgoing R2 registers where the  
         forward signals are sent as pulses for non-compelled
         signaling. "
    DEFVAL { 150 }
    ::= { ccasIfExtRegSignalTimerEntry 7 }

ccasRSTIncFwdPulseOnTimer OBJECT-TYPE
    SYNTAX Gauge(0..65535)
--  Units
--    milliseconds
    ACCESS read-write
    STATUS mandatory
    DESCRIPTION
        "This object specifies the period for which the forward  
         digit pulse can be on. The timer is started after the   
         forward digit signal is received, and stays on until 
         the forward digit being received is turned off. 
         This object applies to incoming R2 registers where the  
         forward signals are received as pulses for non-compelled
         signaling. "
    DEFVAL { 150 }
    ::= { ccasIfExtRegSignalTimerEntry 8 }

ccasRSTBwdPulseOnTimer OBJECT-TYPE
    SYNTAX Gauge(0..65535)
--  Units
--    milliseconds
    ACCESS read-write
    STATUS mandatory
    DESCRIPTION
        "This value specifies the period for which the backward  
         pulse is on before it is turned off. 
         This object applies to incoming R2 registers where the  
         forward signals are received either continuously or as  
         a pulse but the backward signals are sent as a pulse  
         in semi-compelled or non-compelled signaling mode 
         respectively.
        
         It also applies to compelled signaling where certain 
         backward signals are sent as pulses. "
    REFERENCE
        "ITU-T Q.442 Requirements Relating to Transmission 
         Coditions, section 4.3"
    DEFVAL { 150 }
    ::= { ccasIfExtRegSignalTimerEntry 9 }

ccasRSTIncomingRegSigDuration OBJECT-TYPE
    SYNTAX Gauge(0..65535)
--  Units
--    seconds
    ACCESS read-write
    STATUS mandatory
    DESCRIPTION
        "This object specifies the duration within which the register
         signaling should complete for an incoming call. 
         This timer is started as soon as the first forward register 
         signal is received. "
    DEFVAL { 180 }
    ::= { ccasIfExtRegSignalTimerEntry 10 }

ccasRSTOutgoingRegSigDuration OBJECT-TYPE
    SYNTAX Gauge(0..65535)
--  Units
--    seconds
    ACCESS read-write
    STATUS mandatory
    DESCRIPTION
        "This object specifies the duration within which the register
         signaling should complete for an outgoing call. 
         This timer is started when the first forward register signal
         is sent out. "
    DEFVAL { 180 }
    ::= { ccasIfExtRegSignalTimerEntry 11 }

ccasRSTCalledPartyInterDigTimer OBJECT-TYPE
    SYNTAX Gauge(0..65535)
--  Units
--    seconds
    ACCESS read-write
    STATUS mandatory
    DESCRIPTION
        "This object specifies the interdigit timer for the
         collection of called party number (DNIS) for R2 signaling
         when there is no digit map associated with the digits
         being gathered.
         This timer is started after receiving each called digit,
         and expiry of this timer indicates that there are no more
         called party digits to receive."
    REFERENCE
        "ITU-T Q.476 Abnormal Release of Outgoing and Incoming
         R2 Register, section 5.5.2"
    DEFVAL { 15 }
    ::= { ccasIfExtRegSignalTimerEntry 12 }

ccasRSTRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used for adding, deleting and modifying 
         the entries from the ccasIfExtRegSignalTimerTable.
         A default entry with index value 1 is created at 
         initialization, and it can not be modified or deleted."
    ::= { ccasIfExtRegSignalTimerEntry 13 }

ccasIfExtGeneralConfigTable OBJECT-TYPE
    SYNTAX SEQUENCE OF CcasIfExtGeneralConfigEntry
    ACCESS not-accessible
    STATUS mandatory
    DESCRIPTION
        "This table defines the general parameters related to 
         CAS variant."
    ::= { ccasIfExtGeneralConfig 1 }

ccasIfExtGeneralConfigEntry OBJECT-TYPE
    SYNTAX CcasIfExtGeneralConfigEntry
    ACCESS not-accessible
    STATUS mandatory
    DESCRIPTION
        "An entry represents a general attribute for CAS variant
         in media gateway."
    INDEX { cmgwIndex, ccasGCnfIndex }
    ::= { ccasIfExtGeneralConfigTable 1 }

CcasIfExtGeneralConfigEntry ::= SEQUENCE {
    ccasGCnfIndex Gauge,
    ccasGCnfGlarePolicy INTEGER,
    ccasGCnfParmSource INTEGER,
    ccasGCnfRegSigMode CASRegisterSignal,
    ccasGCnfLineSigType INTEGER,
    ccasGCnfRingBackType INTEGER,
    ccasGCnfIncCallHiFreqPower INTEGER,
    ccasGCnfIncCallLoFreqPower INTEGER,
    ccasGCnfIncCallNegTwist INTEGER,
    ccasGCnfIncCallPosTwist INTEGER,
    ccasGCnfIncCallBreakThreshold INTEGER,
    ccasGCnfOutCallLoFreqPower INTEGER,
    ccasGCnfOutCallPowerTwist INTEGER,
    ccasGCnfOutCadenceOntime Gauge,
    ccasGCnfOutCadenceOfftime Gauge,
    ccasGCnfCountryCode SnmpAdminString,
    ccasGCnfEchoCancellation INTEGER,
    ccasGCnfSubscriberCategory INTEGER,
    ccasGCnfNatureOfCircuit INTEGER,
    ccasGCnfCompelledSignalingType INTEGER,
    ccasGCnfTxDigitOrder INTEGER,
    ccasGCnfDigitDetectMode INTEGER,
    ccasGCnfMeteringRepIntThresh Gauge,
    ccasGCnfStartTimer Gauge,
    ccasGCnfLongTimer Gauge,
    ccasGCnfShortTimer Gauge,
    ccasGCnfLongDurationTimer Gauge,
    ccasGCnfMGCTimer Gauge,
    ccasGCnfDigitType INTEGER,
    ccasGCnfEndPointDirectional INTEGER,
    ccasGCnfPulseReceiveTimeout Gauge,
    ccasGCnfInitialDelay Gauge,
    ccasGCnfMaxNumCallParty Gauge,
    ccasGCnfRowStatus RowStatus
    }

ccasGCnfIndex OBJECT-TYPE
    SYNTAX Gauge(1..65535)
    ACCESS not-accessible
    STATUS mandatory
    DESCRIPTION
        "An arbitrary index that uniquely identifies a 
         entry in the ccasIfExtGeneralConfigTable.
         The index of 1 is reserved for the default entry.  "
    ::= { ccasIfExtGeneralConfigEntry 1 }

ccasGCnfGlarePolicy OBJECT-TYPE
    SYNTAX INTEGER {
        rptSzOnGlareTmrExp(1),
        rptSzOnGlareDet(2),
        rptRelOnGlareTmrExpAndGoOnHook(3),
        goOnHookOnGlareDet(4)
        }
    ACCESS read-write
    STATUS mandatory
    DESCRIPTION
        "This object specifies a glare policy. It is used only if 
         CAS DS0 directionality of the endpoint is bidirectional,
         and is applicable for non R2 variants.
          . rptSzOnGlareTmrExp (1): When glare is detected, the GW
            will wait for the timeout value specified in the glare 
            timer object or until incoming call attempt is removed by 
            the other exchange/switch. If the far end does not back 
            off due to wrong configuration, and the GW times out, 
            it reports the seize event to the controlling application.
          . rptSzOnGlareDet (2): When glare is detected, the GW will
            signal the seizure event to the controlling application.
          . rptRelOnGlareTmrExpAndGoOnHook (3): When glare is detected,
            the GW will wait for the timeout value specified in the
            glare timer object OR until incoming call attempt is 
            removed by the other exchange/switch. If the far end does 
            not back off, due to wrong configuration, and the GW times 
            out, it reports the release event and goes onhook, upon 
            detection of on hook from the far end the GW will send 
            the rlc event to the controlling application.
          . goOnHookOnGlareDet (4): When glare is detected, the GW
            will go on hook and let the far end switch continue."
    DEFVAL { rptSzOnGlareTmrExp }
    ::= { ccasIfExtGeneralConfigEntry 2 }

ccasGCnfParmSource OBJECT-TYPE
    SYNTAX INTEGER {
        casVariantFile(1),
        mib(2)
        }
    ACCESS read-write
    STATUS mandatory
    DESCRIPTION
        "This object indicates whether GW should read the CAS  
         related timer parameters from the CAS Variant file 
         downloaded for that endpoint or to read from the MIB.
         This gives the flexibility of configuring different CAS 
         related timer values for different endpoints associated  
         with the same CAS variant."
    DEFVAL { mib }
    ::= { ccasIfExtGeneralConfigEntry 3 }

ccasGCnfRegSigMode OBJECT-TYPE
    SYNTAX CASRegisterSignal
--    Rsyntax INTEGER {
--        compelled(1),
--        noncompelled(2),
--        semicompelled(3)
--        }
    ACCESS read-write
    STATUS mandatory
    DESCRIPTION
        "This object specifies the register signaling mode for a 
         R2 registers. "
    REFERENCE
        " ITU-T recommendation Q.440 Interregister Signaling."
    DEFVAL { compelled }
    ::= { ccasIfExtGeneralConfigEntry 4 }

ccasGCnfLineSigType OBJECT-TYPE
    SYNTAX INTEGER {
        digital(1),
        analog(2),
        pulse(3)
        }
    ACCESS read-write
    STATUS mandatory
    DESCRIPTION
        "This object specifies the line signaling type that will be 
         used for the R2 line signaling.  
         . digital (1): The digital line signaling is typically used 
           for PCM systems. Only A and B bits are used to indicate 
           line signaling states, while C and D bits may be optionally
           used.
         . analog (2): The analog line signaling is typically used for 
           carrier systems. Only A bit is used to represent tone-on
           and tone-off indication to signal the line signaling states,
           while the B, C, and D bit are fixed.
         . pulse (3): The Pulse type line signaling is typically used 
           for satellite links. It uses tones sent as pulses to  
           indicate line signaling states."
    REFERENCE
        " ITU-T recommendation Q.421, Q.411, ITU-T Supplement 7"
    DEFVAL { digital }
    ::= { ccasIfExtGeneralConfigEntry 5 }

ccasGCnfRingBackType OBJECT-TYPE
    SYNTAX INTEGER {
        wink(1),
        winkAndTone(2)
        }
    ACCESS read-write
    STATUS mandatory
    DESCRIPTION
        "This object specifies the ring back signal type of FGD 
         protocol.
         . wink (1): A pulse which is a timed transition from on  
           hook to off hook and back to on hook.
         . wink and tone (2): A pulse which is a timed transition  
           from on hook to off hook and back to on hook, and followed 
           by a tone with a frequency of  700Hz & 1700 Hz."
    REFERENCE
        "Bellcore Publication: TR-NPL-000258
         Compatibility Information for Feature Group D Switched 
         Access Service, appendix 6"
    DEFVAL { wink }
    ::= { ccasIfExtGeneralConfigEntry 6 }

ccasGCnfIncCallHiFreqPower OBJECT-TYPE
    SYNTAX INTEGER(-1000..1000)
--  Units
--    dBm
    ACCESS read-write
    STATUS mandatory
    DESCRIPTION
        "This object specifies the power of the high frequency signal 
         component for incoming call."
    REFERENCE
        "TIA-689-A: PBX and KTS Support of Enhanced 911
         Emergency Calling Service, section 5.2.3.10.1
         "
    ::= { ccasIfExtGeneralConfigEntry 7 }

ccasGCnfIncCallLoFreqPower OBJECT-TYPE
    SYNTAX INTEGER(-1000..1000)
--  Units
--    dBm
    ACCESS read-write
    STATUS mandatory
    DESCRIPTION
        "This object specifies the power of the low frequency signal 
         component for incoming call. "
    REFERENCE
        "TIA-689-A: PBX and KTS Support of Enhanced 911
         Emergency Calling Service, section 5.2.3.10.1
         "
    ::= { ccasIfExtGeneralConfigEntry 8 }

ccasGCnfIncCallNegTwist OBJECT-TYPE
    SYNTAX INTEGER(-1000..1000)
--  Units
--    dBm
    ACCESS read-write
    STATUS mandatory
    DESCRIPTION
        "This object specifies a negative power twist when the   
         power level of the low frequency component is set to 
         relatively higher than the high frequency component 
         for incoming call. "
    REFERENCE
        "TIA-689-A: PBX and KTS Support of Enhanced 911
         Emergency Calling Service, section 5.2.3.10.1
         "
    ::= { ccasIfExtGeneralConfigEntry 9 }

ccasGCnfIncCallPosTwist OBJECT-TYPE
    SYNTAX INTEGER(-1000..1000)
--  Units
--    dBm
    ACCESS read-write
    STATUS mandatory
    DESCRIPTION
        "This object specifies a positive power twist when the   
         power level of the high frequency component is set to 
         relatively higher than the low frequency component for 
         incoming call.           "
    REFERENCE
        "TIA-689-A: PBX and KTS Support of Enhanced 911
         Emergency Calling Service, section 5.2.3.10.1
         "
    ::= { ccasIfExtGeneralConfigEntry 10 }

ccasGCnfIncCallBreakThreshold OBJECT-TYPE
    SYNTAX INTEGER(-1000..1000)
--  Units
--    dBm
    ACCESS read-write
    STATUS mandatory
    DESCRIPTION
        "This object specifies a power level which is used for
         detection of on hook to off hook transition for incoming 
         call."
    REFERENCE
        "TIA-689-A: PBX and KTS Support of Enhanced 911
         Emergency Calling Service, section 5.2.3.10.1
         "
    ::= { ccasIfExtGeneralConfigEntry 11 }

ccasGCnfOutCallLoFreqPower OBJECT-TYPE
    SYNTAX INTEGER(-1000..1000)
--  Units
--    dBm
    ACCESS read-write
    STATUS mandatory
    DESCRIPTION
        "This object specifies the power level of the low frequency 
         component for outgoing call. 
         The power level of the high frequency component of outgoing 
         call is relative above or below the value specified in object 
         ccasGCnfOutCallPowerTwist.
         If the value of ccasGCnfOutCallPowerTwist is 0, the power
         level of the high frequency component as well as the low 
         frequency component is specified by this object."
    REFERENCE
        "Q.23, Q.24, EIA/TIA-464"
    ::= { ccasIfExtGeneralConfigEntry 12 }

ccasGCnfOutCallPowerTwist OBJECT-TYPE
    SYNTAX INTEGER(-1000..1000)
--  Units
--    dBm
    ACCESS read-write
    STATUS mandatory
    DESCRIPTION
        "This object specifies the relative power level of the
         high frequency component for outgoing call.
         When this object is set to 0, the power level of both
         frequency components is set to the same level.
         When this object is set to a positive value, the power
         level of the high frequency component is set to 
         relatively higher specified in this object than the 
         low frequency component, ccasGCnfOutCallLoFreqPower.  
         For example if ccasGCnfOutCallLoFreqPower is set to 
         -12 dBm and this object is set to 5, the power level
         of the high frequency component becomes -7 dBm.
         When this object is set to a negative value, the power
         level of the high frequency component is set to 
         relatively lower specified in this object than the low
         frequency component. 
         For example if ccasGCnfOutCallLoFreqPower is set to 
         -12 dBm and this object is set to -10, the power level 
         of the high frequency component becomes -22 dBm."
    REFERENCE
        "Q.23, Q.24, EIA/TIA-464"
    ::= { ccasIfExtGeneralConfigEntry 13 }

ccasGCnfOutCadenceOntime OBJECT-TYPE
    SYNTAX Gauge(0..65535)
--  Units
--    milliseconds
    ACCESS read-write
    STATUS mandatory
    DESCRIPTION
        "This object specifies the duration during which the digit 
         tone is generated for outgoing call. "
    ::= { ccasIfExtGeneralConfigEntry 14 }

ccasGCnfOutCadenceOfftime OBJECT-TYPE
    SYNTAX Gauge(0..65535)
--  Units
--    milliseconds
    ACCESS read-write
    STATUS mandatory
    DESCRIPTION
        "This object specifies the silence between digit tones
         for outgoing call."
    ::= { ccasIfExtGeneralConfigEntry 15 }

ccasGCnfCountryCode OBJECT-TYPE
    SYNTAX SnmpAdminString(SIZE(1..8))
--    Rsyntax OCTET STRING(SIZE(1..8))
    ACCESS read-write
    STATUS mandatory
    DESCRIPTION
        "This object specifies the country code digits."
    ::= { ccasIfExtGeneralConfigEntry 16 }

ccasGCnfEchoCancellation OBJECT-TYPE
    SYNTAX INTEGER {
        noEchoRequired(1),
        outgoingHalfEchoRequired(2),
        outgoingHalfEchoSuppressorInserted(3),
        incomingHalfEchoSuppressorRequired(4)
        }
    ACCESS read-write
    STATUS mandatory
    DESCRIPTION
        "This object specifies the echo cancellation mode, and  
         it is applicable to an outgoing R2 register."
    DEFVAL { outgoingHalfEchoRequired }
    ::= { ccasIfExtGeneralConfigEntry 17 }

ccasGCnfSubscriberCategory OBJECT-TYPE
    SYNTAX INTEGER {
        subscriberWithoutPriority(1),
        subscriberWithPriority(2),
        maintenanceEquipment(3),
        operatorCall(4),
        dataNationalTransmission(5),
        subscriberOrOperatorWithoutForwardTransfer(6),
        operatorWithForwardTransfer(7),
        dataInternationalTransmission(8)
        }
    ACCESS read-write
    STATUS mandatory
    DESCRIPTION
        "This object specifies the subscriber category types:
          . (1) subscriber without priority 
          . (2) subscriber with priority     
          . (3) maintenance equipment                      
          . (4) operator call                              
          . (5) data national transmission                  
          . (6) subscriber or operator without forward transfer 
          . (7) operator with forward transfer               
          . (8) data international transmission              "
    DEFVAL { subscriberWithoutPriority }
    ::= { ccasIfExtGeneralConfigEntry 18 }

ccasGCnfNatureOfCircuit OBJECT-TYPE
    SYNTAX INTEGER {
        notIncluded(1),
        included(2)
        }
    ACCESS read-write
    STATUS mandatory
    DESCRIPTION
        "This object specifies if there is any satellite link in
         the path:
         . (1) Satellite link is not included.  
         . (2) Satellite link is included."
    DEFVAL { notIncluded }
    ::= { ccasIfExtGeneralConfigEntry 19 }

ccasGCnfCompelledSignalingType OBJECT-TYPE
    SYNTAX INTEGER {
        enbloc(1),
        overlap(2),
        endtoend(3)
        }
    ACCESS read-write
    STATUS mandatory
    DESCRIPTION
        "This object specifies the Compelled Signaling type:
         . enbloc (1): The called number is forwarded in a block.
         . overlap (2): The called numder is forwarded one at a time.
         . endtoend (3): The signaling between register over two or
           more links in tandem without regeneration in intermediate 
           exchanges."
    DEFVAL { enbloc }
    ::= { ccasIfExtGeneralConfigEntry 20 }

ccasGCnfTxDigitOrder OBJECT-TYPE
    SYNTAX INTEGER {
        aniDnis(1),
        dnisAni(2)
        }
    ACCESS read-write
    STATUS mandatory
    DESCRIPTION
        "This object specifies the transmit digit order in which 
         ANI and DNIs will be dialled out when the controlling 
         application gives both the the calling party number and  
         the called party number to the CAS module for dialing out 
         in a single request."
    DEFVAL { dnisAni }
    ::= { ccasIfExtGeneralConfigEntry 21 }

ccasGCnfDigitDetectMode OBJECT-TYPE
    SYNTAX INTEGER {
        dtmf(1),
        mf(2),
        dp(3)
        }
    ACCESS read-write
    STATUS mandatory
    DESCRIPTION
        "This objects specifies the digit detect mode that the 
         GW should be opened with for reception of digits.
         . dtmf (1): Dual tone multifrequency
         . mf (2): Multifrequency
         . dp (3): Dial pulse
         This object applies to non R2 interfaces."
    DEFVAL { mf }
    ::= { ccasIfExtGeneralConfigEntry 22 }

ccasGCnfMeteringRepIntThresh OBJECT-TYPE
    SYNTAX Gauge(0..65535)
--  Units
--    milliseconds
    ACCESS read-write
    STATUS mandatory
    DESCRIPTION
        "This object specifies the duration between two consecutive
         metering pulses, if it changes more than value specified 
         in this parameter then an event will be triggered to MGC."
    DEFVAL { 10 }
    ::= { ccasIfExtGeneralConfigEntry 23 }

ccasGCnfStartTimer OBJECT-TYPE
    SYNTAX Gauge(0..10000)
--  Units
--    seconds
    ACCESS read-write
    STATUS mandatory
    DESCRIPTION
        "This object specifies the amount of time that the GW 
         must wait for receiving digits after generating the 
         seize ACK or start dial indication for an incoming 
         call. 
         The value of 0 indicates the timer will not be started 
         and GW would wait forever."
    DEFVAL { 16 }
    ::= { ccasIfExtGeneralConfigEntry 24 }

ccasGCnfLongTimer OBJECT-TYPE
    SYNTAX Gauge(0..10000)
--  Units
--    seconds
    ACCESS read-write
    STATUS mandatory
    DESCRIPTION
        "This object specifies the period between receiving 
         digits. The timer is not started until the first digit
         is received. 
         The GW starts this timer during digit collection when 
         at least one or more digits is required for a digit 
         string to match any allowed pattern in the digit map. 
         The timer is restarted after every new digit is 
         received. This continues until the digit string matches
         at least one pattern in the digit map.
         The value of 0 indicates the timer will not be started 
         and GW would wait forever. "
    DEFVAL { 16 }
    ::= { ccasIfExtGeneralConfigEntry 25 }

ccasGCnfShortTimer OBJECT-TYPE
    SYNTAX Gauge(0..10000)
--  Units
--    seconds
    ACCESS read-write
    STATUS mandatory
    DESCRIPTION
        "This object specifies the period between receiving 
         digits. 
         The GW starts this timer during digit collection when 
         the digit string that it has collected matches at least
         one pattern in the digit map, but reception of another 
         digit could change the match to a different pattern. 
         In this case, GW waits to confirm that no more digits 
         are received while this timer is running before 
         reporting the match to the MGC.
         The value of 0 indicates the timer will not be started 
         and GW would report immediately."
    DEFVAL { 4 }
    ::= { ccasIfExtGeneralConfigEntry 26 }

ccasGCnfLongDurationTimer OBJECT-TYPE
    SYNTAX Gauge(100..9900)
--  Units
--    milliseconds
    ACCESS read-write
    STATUS mandatory
    DESCRIPTION
        "This object specifies long duration event when placed 
         in front of a digit. It indicates that that position is 
         satisfied only if the duration of the event exceeds the 
         long-duration threshold."
    DEFVAL { 100 }
    ::= { ccasIfExtGeneralConfigEntry 27 }

ccasGCnfMGCTimer OBJECT-TYPE
    SYNTAX Gauge(0..100000)
--  Units
--    milliseconds
    ACCESS read-write
    STATUS mandatory
    DESCRIPTION
        "This object specifies the timer in the GW waiting for
         the MGC to provide the rest of the information for CAS
         signaling.
         During overlap CAS signaling, for an outgoing call, the
         MGC might specify a part of the digits to be signaled out 
         of the GW while it is waiting to collect the rest of 
         the information that also needs to be signaled. In this
         case, if the GW has finished signaling all the 
         available digits, it can start this timer to wait for 
         the MGC to specify the rest of the information. The 
         backward signal from the far end can also request for 
         information that the MGC has not yet specified to the 
         GW. In this case also, this timer is started to wait 
         for the MGC to provide the information needed by the GW."
    REFERENCE
        "H.248 International CAS Compelled Register Signaling 
         Packages (icasc), section 6.1.2"
    DEFVAL { 1000 }
    ::= { ccasIfExtGeneralConfigEntry 28 }

ccasGCnfDigitType OBJECT-TYPE
    SYNTAX INTEGER {
        dtmf(1),
        mf(2),
        dp(3)
        }
    ACCESS read-write
    STATUS mandatory
    DESCRIPTION
        "This object specifies the digit type to pulsed from the
         GW such as: 
         .dtmf - Dual tone multifrequency.
         .mf - Multifrequency.
         .dp - Dial pulse.      
         This parameter can be overridden by MGC. In the event 
         that the MGC does not specify the digit type, the value
         of this object is used."
    DEFVAL { mf }
    ::= { ccasIfExtGeneralConfigEntry 29 }

ccasGCnfEndPointDirectional OBJECT-TYPE
    SYNTAX INTEGER {
        bidirectional(1),
        incoming(2),
        outgoing(3)
        }
    ACCESS read-write
    STATUS mandatory
    DESCRIPTION
        "This object specifies the direction in which CAS calls 
         will be accepted on this endpoint.
         .bidirectional - Accepts both incoming and outgoing calls. 
         .incoming - Accepts incoming calls only. 
         .outgoing - Accepts outgoing calls only."
    DEFVAL { bidirectional }
    ::= { ccasIfExtGeneralConfigEntry 30 }

ccasGCnfPulseReceiveTimeout OBJECT-TYPE
    SYNTAX Gauge(0..100000)
--  Units
--    seconds
    ACCESS read-write
    STATUS mandatory
    DESCRIPTION
        "This object specifies the time that the MG should wait
         for the receipt of pulse (on hook pulse or off hook 
         pulse). 
         The value of 0 indicates the timer will not be started 
         and MG would wait forever."
    REFERENCE
        "H.248.25 Basis CAS Packages
         RBS (Robbed Bit Signal) Packet, section 9.2.1"
    DEFVAL { 0 }
    ::= { ccasIfExtGeneralConfigEntry 31 }

ccasGCnfInitialDelay OBJECT-TYPE
    SYNTAX Gauge(0..10000)
--  Units
--    milliseconds
    ACCESS read-write
    STATUS mandatory
    DESCRIPTION
        "This object specifies the initial delay that must be applied
         on an outgoing trunk before the digits are pulse out.
         The value of 0 indicates the timer, ccasGCnfInitialDelay 
         will start immediately."
    REFERENCE
        "H.248.25 Basis CAS Packages section 8.3.1"
    DEFVAL { 0 }
    ::= { ccasIfExtGeneralConfigEntry 32 }

ccasGCnfMaxNumCallParty OBJECT-TYPE
    SYNTAX Gauge(0..65535)
    ACCESS read-write
    STATUS mandatory
    DESCRIPTION
        "This object specifies the maximum number of calling party 
         digits to collect for reporting to the MGC.
         The MGC can overridden this value, and a value of 0 indicates
         that there is no limit and all numbers till end of calling 
         party signaling must be accumulated. "
    DEFVAL { 0 }
    ::= { ccasIfExtGeneralConfigEntry 33 }

ccasGCnfRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used for adding, modifying, deleting the  
         entries from the ccasExtIfGeneralConfigTable.
         A default entry with index value 1 is created at 
         initialization, and it can not be modified or deleted."
    ::= { ccasIfExtGeneralConfigEntry 34 }

ccasIfExtVoiceCfgGroup OBJECT IDENTIFIER ::= { ccasIfExtMIBGroups 1 }
-- OBJECT-GROUP
--  Status
--    deprecated
--  Descr
--    This group contains objects that apply to the DS0 group of
--     DS1 configuration in media gateways.
--  objects
--    ccasIfExtVoiceCfgLifNumber, ccasIfExtVoiceCfgCcntrlProfile, 
--    ccasIfExtVoiceCfgVadEnabled, ccasIfExtVoiceCfgContinuityTone1, 
--    ccasIfExtVoiceCfgContinuityTone2, 
--    ccasIfExtVoiceCfgModemPassThru, ccasIfExtVoiceCfgUpspeedCodec, 
--    ccasIfExtVoiceCfgT38MaxFaxTxRate, 
--    ccasIfExtVoiceCfgT38HsPktPeriod, 
--    ccasIfExtVoiceCfgT38HsRedundancy, ccasIfExtVoiceCfgVadTimer, 
--    ccasIfExtVoiceCfgICSEnable, ccasIfExtVoiceCfgICSIntTimer, 
--    ccasIfExtVoiceCfgTonePlan, ccasIfExtVoiceCfgGwyLinkId, 
--    ccasIfExtVoiceCfgH248PkgIds

ccasIfExtBulkGroup OBJECT IDENTIFIER ::= { ccasIfExtMIBGroups 2 }
-- OBJECT-GROUP
--  Status
--    mandatory
--  Descr
--    This group contains objects that apply to the bulk 
--     configuration for the DS0 group associated voice specific
--     parameters in media gateway.
--  objects
--    ccasIfExtVoiceCfgRepetition, ccasIfExtVoiceCfgBulkCfgOwner, 
--    ccasIfExtVoiceCfgBulkCfgResult, ccasIfExtDs0GrpRepetition, 
--    ccasIfExtDs0GrpRepeatOwner, ccasIfExtDs0GrpRepeatResult

ccasIfExtVoiceCfgGroupRev1 OBJECT IDENTIFIER ::= { ccasIfExtMIBGroups 3 }
-- OBJECT-GROUP
--  Status
--    mandatory
--  Descr
--    This group contains objects that apply to the DS0 group of
--     DS1 configuration in media gateways.
--  objects
--    ccasIfExtVoiceCfgLifNumber, ccasIfExtVoiceCfgCcntrlProfile, 
--    ccasIfExtVoiceCfgVadEnabled, ccasIfExtVoiceCfgContinuityTone1, 
--    ccasIfExtVoiceCfgContinuityTone2, 
--    ccasIfExtVoiceCfgModemPassThru, ccasIfExtVoiceCfgUpspeedCodec, 
--    ccasIfExtVoiceCfgVadTimer, ccasIfExtVoiceCfgICSEnable, 
--    ccasIfExtVoiceCfgICSIntTimer, ccasIfExtVoiceCfgTonePlan, 
--    ccasIfExtVoiceCfgGwyLinkId, ccasIfExtVoiceCfgH248PkgIds, 
--    ccasIfExtVoiceCfgEventMappingIdx, 
--    ccasIfExtVoiceCfgGatewayIndex

ccasIfExtVoiceCfgCasGroup OBJECT IDENTIFIER ::= { ccasIfExtMIBGroups 4 }
-- OBJECT-GROUP
--  Status
--    mandatory
--  Descr
--    This group contains objects that apply to the DS0 group of
--     DS1 configuration for CAS.
--  objects
--    ccasIfExtVoiceCfgCasProfile, ccasIfExtVoiceCfgCasVariant, 
--    ccasIfExtVoiceCfgDs0ChannelsFail

ccasIfExtProfileGroup OBJECT IDENTIFIER ::= { ccasIfExtMIBGroups 5 }
-- OBJECT-GROUP
--  Status
--    mandatory
--  Descr
--    A collection of objects providing information applicable
--     to CAS Profile.
--  objects
--    ccasProfileLineSigTimer, ccasProfileRegisterSignal, 
--    ccasProfileRegSigTimer, ccasProfileGeneralCfg, 
--    ccasProfileRowStatus, ccasVariantFile, ccasVariantSource, 
--    ccasVariantNumberCount, ccasVariantState, 
--    ccasVariantRowStatus

ccasIfExtConfigLineSignalGroup OBJECT IDENTIFIER ::= { ccasIfExtMIBGroups 6 }
-- OBJECT-GROUP
--  Status
--    mandatory
--  Descr
--    A collection of objects providing information applicable
--     to Line Signal. 
--  objects
--    ccasILSSignalName, ccasILSRxPattern, ccasILSMatchedRxPattern, 
--    ccasILSMatchedTxPattern, ccasILSMinMakeTime, 
--    ccasILSMaxMakeTime, ccasILSMinBreakTime, ccasILSMaxBreakTime, 
--    ccasOLSCasSignalName, ccasOLSTxPattern, ccasOLSMakeTime, 
--    ccasOLSBreakTime

ccasIfExtConfigRegisterSignalGroup OBJECT IDENTIFIER ::= { ccasIfExtMIBGroups 7 }
-- OBJECT-GROUP
--  Status
--    mandatory
--  Descr
--    A collection of objects providing information applicable
--     to Register Signal.
--  objects
--    ccasRSCountry, ccasRSSubRegion, ccasBwdRSNextDigitANI, 
--    ccasBwdRSNextDigitDNIS, ccasBwdRSPrevDigit, 
--    ccasBwdRSXtoGroupBSignals, ccasBwdRSCongestion, 
--    ccasBwdRSCallingPartyCategory, ccasBwdRSAddrCompleteGroupA, 
--    ccasBwdRSPrevNminus2Digit, ccasBwdRSPrevNminus3Digit, 
--    ccasBwdRSCountryCode, ccasBwdRSLangDiscr, 
--    ccasBwdRSNatureOfCircuit, ccasBwdRSInfoEchoSuppressor, 
--    ccasBwdRSInternationalCongst, ccasBwdRSXtoGroupC, 
--    ccasBwdRSRepeatLastDigit, ccasBwdRSRepeatCalledDigit, 
--    ccasBwdRSPlaySITTone, ccasBwdRSSubscriberLineBusy, 
--    ccasBwdRSNetworkCongstInGroupB, ccasBwdRSInvalidDialedNumber, 
--    ccasBwdRSSubLineFreeWithCharge, 
--    ccasBwdRSSubLineFreeWithNoCharge, ccasBwdRSSubLineOutOfOrder, 
--    ccasBwdRSAnnouncement, ccasBwdRSXtoGrpASendNextDNIS, 
--    ccasBwdRSXtoGrpASendDNISFrmBeg, 
--    ccasBwdRSXtoGrpAResendLastDNIS, ccasBwdRSSSendCatSwGrpB, 
--    ccasBwdRSSGrpCCong, ccasFwdRSANIDigitAvailable, 
--    ccasFwdRSANIDigitNotAvailable, 
--    ccasFwdRSEndANICallingPartyNotRev, 
--    ccasFwdRSEndANICallingPartyRev, ccasFwdRSEndOfDNISDigit, 
--    ccasFwdRSNoCategoryAvailble, ccasFwdRSCCEchoSuppressor, 
--    ccasFwdRSCCNoEchoSuppressor, ccasFwdRSCCInsertEchoSuppressor, 
--    ccasFwdRSIncHalfEchoRequired, ccasFwdRSTestCall, 
--    ccasFwdRSSatelLinkIncluded, ccasFwdRSSatelLinkNotIncluded, 
--    ccasFwdRSDiscriminatorDigit, ccasFwdRSOtherLanguage, 
--    ccasFwdRSOtherLanguage1, ccasFwdRSOtherLanguage2, 
--    ccasFwdRSRequestNotAccepted, ccasFwdRSSubWithoutPriorNational, 
--    ccasFwdRSSubPriorNational, ccasFwdRSSubPriorInternational, 
--    ccasFwdRSMaintenanceEquipment, ccasFwdRSOperatorCall, 
--    ccasFwdRSDataTransNational, ccasFwdRSDataTransInternational, 
--    ccasFwdRSOperNoFwdTransFacility, 
--    ccasFwdRSOperFwdTransFacility, ccasFwdRSSubsrcWithMeter, 
--    ccasFwdRSSubsrcWithIDD, ccasRSInterpreFirstANIDigit, 
--    ccasRSGetValueFromValidIndex, ccasRSSeqInfCollect, 
--    ccasRSSendFirstFwdSig, ccasRSRowStatus

ccasIfExtConfigTimerGroup OBJECT IDENTIFIER ::= { ccasIfExtMIBGroups 8 }
-- OBJECT-GROUP
--  Status
--    mandatory
--  Descr
--    A collection of objects providing information applicable
--     to timer.
--  objects
--    ccasLSTIdleGuardTimer, ccasLSTClearFwdTimer, 
--    ccasLSTClearBwdTimer, ccasLSTReleaseGuardTimer, 
--    ccasLSTCASGlareTimer, ccasLSTAnswerMeterDelayTimer, 
--    ccasLSTCASDebounceTimer, ccasLSTSeizeAckRspTimer, 
--    ccasLSTDelayBetRegAnsAndLineAns, ccasLSTSeizeAckToDigitTimer, 
--    ccasLSTRowStatus, ccasRSTAnswerSigTimer, 
--    ccasRSTCompelledFwdToneOnTimer, 
--    ccasRSTCompelledFwdToneOffTimer, 
--    ccasRSTCompelledBwdToneOnTimer, ccasRSTOutFwdPulseOnTimer, 
--    ccasRSTOutFwdPulseOffTimer, ccasRSTIncFwdPulseOnTimer, 
--    ccasRSTBwdPulseOnTimer, ccasRSTIncomingRegSigDuration, 
--    ccasRSTOutgoingRegSigDuration, 
--    ccasRSTCalledPartyInterDigTimer, ccasRSTRowStatus

ccasIfExtGeneralConfigGroup OBJECT IDENTIFIER ::= { ccasIfExtMIBGroups 9 }
-- OBJECT-GROUP
--  Status
--    mandatory
--  Descr
--    A collection of objects providing information applicable
--     to general CAS configuration.
--  objects
--    ccasGCnfGlarePolicy, ccasGCnfParmSource, ccasGCnfRegSigMode, 
--    ccasGCnfLineSigType, ccasGCnfRingBackType, 
--    ccasGCnfIncCallHiFreqPower, ccasGCnfIncCallLoFreqPower, 
--    ccasGCnfIncCallNegTwist, ccasGCnfIncCallPosTwist, 
--    ccasGCnfIncCallBreakThreshold, ccasGCnfOutCallLoFreqPower, 
--    ccasGCnfOutCallPowerTwist, ccasGCnfOutCadenceOntime, 
--    ccasGCnfOutCadenceOfftime, ccasGCnfCountryCode, 
--    ccasGCnfEchoCancellation, ccasGCnfSubscriberCategory, 
--    ccasGCnfNatureOfCircuit, ccasGCnfCompelledSignalingType, 
--    ccasGCnfTxDigitOrder, ccasGCnfDigitDetectMode, 
--    ccasGCnfMeteringRepIntThresh, ccasGCnfStartTimer, 
--    ccasGCnfLongTimer, ccasGCnfShortTimer, 
--    ccasGCnfLongDurationTimer, ccasGCnfMGCTimer, 
--    ccasGCnfDigitType, ccasGCnfEndPointDirectional, 
--    ccasGCnfPulseReceiveTimeout, ccasGCnfInitialDelay, 
--    ccasGCnfMaxNumCallParty, ccasGCnfRowStatus

ccasIfExtVoiceCfgGroupSup1 OBJECT IDENTIFIER ::= { ccasIfExtMIBGroups 10 }
-- OBJECT-GROUP
--  Status
--    mandatory
--  Descr
--    This group contains supplemental objects that apply to 
--     the voice configuration in media gateways.
--  objects
--    ccasIfExtVoiceCfgNoiseRegType

ccasIfExtMIBCompliance OBJECT IDENTIFIER ::= { ccasIfExtMIBCompliances 1 }
-- MODULE-COMPLIANCE
--  Status
--    deprecated
--  Descr
--    The compliance statement for the SNMP entities which implement
--     ciscoCasIfExtMIB.
--     This has been replaced by ccasIfExtMIBComplianceRev1.
--  Module
--    >>current<<
--   MandGroup
--    ccasIfExtVoiceCfgGroup
--   OptGroup
--    ccasIfExtBulkGroup

ccasIfExtMIBComplianceRev1 OBJECT IDENTIFIER ::= { ccasIfExtMIBCompliances 2 }
-- MODULE-COMPLIANCE
--  Status
--    deprecated
--  Descr
--    The compliance statement for the SNMP entities which implement
--     ciscoCasIfExtMIB.
--     This has been replaced by ccasIfExtMIBComplianceRev2.
--  Module
--    >>current<<
--   MandGroup
--    ccasIfExtVoiceCfgGroupRev1
--   OptGroup
--    ccasIfExtBulkGroup

ccasIfExtMIBComplianceRev2 OBJECT IDENTIFIER ::= { ccasIfExtMIBCompliances 3 }
-- MODULE-COMPLIANCE
--  Status
--    deprecated
--  Descr
--    The compliance statement for the SNMP entities which implement
--     ciscoCasIfExtMIB.
--     This has been replaced by ccasIfExtMIBComplianceRev3.
--  Module
--    >>current<<
--   MandGroup
--    ccasIfExtVoiceCfgGroupRev1
--   OptGroup
--    ccasIfExtBulkGroup
--   OptGroup
--    ccasIfExtVoiceCfgCasGroup
--   OptGroup
--    ccasIfExtProfileGroup
--   OptGroup
--    ccasIfExtConfigLineSignalGroup
--   OptGroup
--    ccasIfExtConfigRegisterSignalGroup
--   OptGroup
--    ccasIfExtConfigTimerGroup
--   OptGroup
--    ccasIfExtGeneralConfigGroup

ccasIfExtMIBComplianceRev3 OBJECT IDENTIFIER ::= { ccasIfExtMIBCompliances 4 }
-- MODULE-COMPLIANCE
--  Status
--    mandatory
--  Descr
--    The compliance statement for the SNMP entities which implement
--     ciscoCasIfExtMIB.
--  Module
--    >>current<<
--   MandGroup
--    ccasIfExtVoiceCfgGroupRev1
--   OptGroup
--    ccasIfExtBulkGroup
--   OptGroup
--    ccasIfExtVoiceCfgCasGroup
--   OptGroup
--    ccasIfExtProfileGroup
--   OptGroup
--    ccasIfExtConfigLineSignalGroup
--   OptGroup
--    ccasIfExtConfigRegisterSignalGroup
--   OptGroup
--    ccasIfExtConfigTimerGroup
--   OptGroup
--    ccasIfExtGeneralConfigGroup
--   OptGroup
--    ccasIfExtVoiceCfgGroupSup1


END
