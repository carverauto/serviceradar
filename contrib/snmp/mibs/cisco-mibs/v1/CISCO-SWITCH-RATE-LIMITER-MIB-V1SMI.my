-- MIB file created 16-May-2011 21:51:45, by
--   SMICng version 2.2.11-beta(PRO)(Solaris), January 20, 2001. Enterprise key cisco.com

CISCO-SWITCH-RATE-LIMITER-MIB DEFINITIONS ::= BEGIN

-- From file: "CISCO-SWITCH-RATE-LIMITER-MIB.my"
-- Compile options "4 7 F H N W 03 06 0B 0G 0N 0T"

IMPORTS
    entPhysicalIndex
            FROM ENTITY-MIB
    SnmpAdminString
            FROM SNMP-FRAMEWORK-MIB
    ciscoMgmt
            FROM CISCO-SMI
    Gauge, Counter
            FROM RFC1155-SMI
    OBJECT-TYPE
            FROM RFC-1212;

ciscoSwitchRateLimiterMIB OBJECT IDENTIFIER ::= { ciscoMgmt 773 }
-- MODULE-IDENTITY
--  LastUpdated
--    201105160000Z
--  OrgName
--    Cisco Systems, Inc.
--  ContactInfo
--    Cisco Systems
--    Customer Service
--    
--    Postal: 170 W Tasman Drive
--    San Jose, CA  95134
--    USA
--    
--    Tel: +1 800 553-NETS
--    
--    E-mail: cs-lan-switch-snmp@cisco.com
--  Descr
--    This MIB module defines management objects for the
--    Switch Rate Limiter features on Cisco Layer 2 and 
--    Layer 3 devices.
--    
--    Rate limits prevents redirected control packets for egress 
--    exceptions from overwhelming the supervisor module on a device.
--  RevDate
--    201105160000Z
--  RevDescr
--    Initial version of this MIB module.

ciscoSwitchRateLimiterMIBNotifs OBJECT IDENTIFIER ::= { ciscoSwitchRateLimiterMIB 0 }
ciscoSwitchRateLimiterMIBObjects OBJECT IDENTIFIER ::= { ciscoSwitchRateLimiterMIB 1 }
ciscoSwitchRateLimiterMIBConform OBJECT IDENTIFIER ::= { ciscoSwitchRateLimiterMIB 2 }
csrlRateLimiterInfo OBJECT IDENTIFIER ::= { ciscoSwitchRateLimiterMIBObjects 1 }
csrlGlobalRateLimiter OBJECT IDENTIFIER ::= { ciscoSwitchRateLimiterMIBObjects 2 }
csrlLocalRateLimiter OBJECT IDENTIFIER ::= { ciscoSwitchRateLimiterMIBObjects 3 }
csrlMIBCompliances OBJECT IDENTIFIER ::= { ciscoSwitchRateLimiterMIBConform 1 }
csrlMIBGroups   OBJECT IDENTIFIER ::= { ciscoSwitchRateLimiterMIBConform 2 }

csrlRateLimiterClassTable OBJECT-TYPE
    SYNTAX SEQUENCE OF CsrlRateLimiterClassEntry
    ACCESS not-accessible
    STATUS mandatory
    DESCRIPTION
        "A table containing descriptions of the rate limiter
        classes supported by the device."
    ::= { csrlRateLimiterInfo 1 }

csrlRateLimiterClassEntry OBJECT-TYPE
    SYNTAX CsrlRateLimiterClassEntry
    ACCESS not-accessible
    STATUS mandatory
    DESCRIPTION
        "A conceptual row containing the description of a particular
        rate limiter class."
    INDEX { csrlRateLimiterClassId }
    ::= { csrlRateLimiterClassTable 1 }

CsrlRateLimiterClassEntry ::= SEQUENCE {
    csrlRateLimiterClassId Gauge,
    csrlRateLimiterClassDescr SnmpAdminString
    }

csrlRateLimiterClassId OBJECT-TYPE
    SYNTAX Gauge(1..2147483647)
    ACCESS not-accessible
    STATUS mandatory
    DESCRIPTION
        "An arbitrary positive integer value that uniquely identifies a
        rate limiter class."
    ::= { csrlRateLimiterClassEntry 1 }

csrlRateLimiterClassDescr OBJECT-TYPE
    SYNTAX SnmpAdminString
--    Rsyntax OCTET STRING(SIZE(0..255))
    ACCESS read-only
    STATUS mandatory
    DESCRIPTION
        "This object indicates the description of the rate limiter class."
    ::= { csrlRateLimiterClassEntry 2 }

csrlGlobalRateLimiterTable OBJECT-TYPE
    SYNTAX SEQUENCE OF CsrlGlobalRateLimiterEntry
    ACCESS not-accessible
    STATUS mandatory
    DESCRIPTION
        "A table containing global configuration and statistics of
        rate limiter classes."
    ::= { csrlGlobalRateLimiter 1 }

csrlGlobalRateLimiterEntry OBJECT-TYPE
    SYNTAX CsrlGlobalRateLimiterEntry
    ACCESS not-accessible
    STATUS mandatory
    DESCRIPTION
        "A conceptual row containing global management information
        of a particular rate limiter class."
    INDEX { csrlRateLimiterClassId }
    ::= { csrlGlobalRateLimiterTable 1 }

CsrlGlobalRateLimiterEntry ::= SEQUENCE {
    csrlGlobalRateLimiterConfigured INTEGER,
    csrlGlobalRateLimiterAllowed Counter,
    csrlGlobalRateLimiterDropped Counter,
    csrlGlobalRateLimiterTotal Counter
    }

csrlGlobalRateLimiterConfigured OBJECT-TYPE
    SYNTAX INTEGER(-1|0..2147483647)
--  Units
--    packets per second
    ACCESS read-write
    STATUS mandatory
    DESCRIPTION
        "This object specifies the global rate limit configured
        for this rate limiter class.
        
        The global rate limit for this class is applied to every entity
        which does not have its local rate limit of same class configured,
        the value of the corresponding csrlLocalRateLimiterConfigured
        is -2. 
        
        A value of -1 indicates that the global rate limit for
        this rate limiter class is disabled.
        
        A value of 0 indicates that the system does not allow any
        packets for this rate limiter class to go through the
        supervisor."
    ::= { csrlGlobalRateLimiterEntry 1 }

csrlGlobalRateLimiterAllowed OBJECT-TYPE
    SYNTAX --?? syntax is not convertable to SMIv1
           Counter
--  Units
--    packets
    ACCESS read-only
    STATUS mandatory
    DESCRIPTION
        "This object indicates the number of packets allowed
        globally for this rate limiter class.
        
        When the value of csrlGlobalRateLimiterConfigured is -1,
        the value of this object is always 0."
    ::= { csrlGlobalRateLimiterEntry 2 }

csrlGlobalRateLimiterDropped OBJECT-TYPE
    SYNTAX --?? syntax is not convertable to SMIv1
           Counter
--  Units
--    packets
    ACCESS read-only
    STATUS mandatory
    DESCRIPTION
        "This object indicates the number of packets which have been
        dropped globally for this rate limiter class.
        
        When the value of csrlGlobalRateLimiterConfigured is -1,
        the value of this object is always 0."
    ::= { csrlGlobalRateLimiterEntry 3 }

csrlGlobalRateLimiterTotal OBJECT-TYPE
    SYNTAX --?? syntax is not convertable to SMIv1
           Counter
--  Units
--    packets
    ACCESS read-only
    STATUS mandatory
    DESCRIPTION
        "This object indicates the total number of packets
        have been processed globally for this rate limiter class.
        
        When the value of csrlGlobalRateLimiterConfigured is -1,
        the value of this object is always 0."
    ::= { csrlGlobalRateLimiterEntry 4 }

csrlLocalRateLimiterTable OBJECT-TYPE
    SYNTAX SEQUENCE OF CsrlLocalRateLimiterEntry
    ACCESS not-accessible
    STATUS mandatory
    DESCRIPTION
        "A table containing local rate limiter configuration and
        statistics for a specific entity.  For Example: A module
        on the device.
        
        A set of rate limiter class entries are added to this
        table when a rate limiter capable entity comes online.
        The same set of entries are deleted from this table when
        the entity goes offline."
    ::= { csrlLocalRateLimiter 1 }

csrlLocalRateLimiterEntry OBJECT-TYPE
    SYNTAX CsrlLocalRateLimiterEntry
    ACCESS not-accessible
    STATUS mandatory
    DESCRIPTION
        "A conceptual row containing the local rate limiter
        management information for a particular rate limiter
        capable entity."
    INDEX { entPhysicalIndex, csrlRateLimiterClassId }
    ::= { csrlLocalRateLimiterTable 1 }

CsrlLocalRateLimiterEntry ::= SEQUENCE {
    csrlLocalRateLimiterConfigured INTEGER,
    csrlLocalRateLimiterAllowed Counter,
    csrlLocalRateLimiterDropped Counter,
    csrlLocalRateLimiterTotal Counter
    }

csrlLocalRateLimiterConfigured OBJECT-TYPE
    SYNTAX INTEGER(-2|-1|0..2147483647)
--  Units
--    packets per second
    ACCESS read-write
    STATUS mandatory
    DESCRIPTION
        "This object specifies the local rate limit configured
        for this rate limiter class on this entity.
        
        A value of -2 indicates that the entity does not have 
        local rate limiter configured, and will pick up the
        configuration from csrlGlobalRateLimiterConfigured.
        
        A value of -1 indicates that this rate limiter class
        is disabled locally for this entity.
        
        A value of 0 indicates that the rate limiter 
        does not allow any packets from this entity for this rate
        limiter class to go through the supervisor."
    ::= { csrlLocalRateLimiterEntry 1 }

csrlLocalRateLimiterAllowed OBJECT-TYPE
    SYNTAX --?? syntax is not convertable to SMIv1
           Counter
--  Units
--    packets
    ACCESS read-only
    STATUS mandatory
    DESCRIPTION
        "This object indicates the number of packets allowed
        on this entity for this rate limiter class.
        
        When the value of csrlLocalRateLimiterConfigured is -1,
        the value of this object is always 0."
    ::= { csrlLocalRateLimiterEntry 2 }

csrlLocalRateLimiterDropped OBJECT-TYPE
    SYNTAX --?? syntax is not convertable to SMIv1
           Counter
--  Units
--    packets
    ACCESS read-only
    STATUS mandatory
    DESCRIPTION
        "This object indicates the number of packets dropped
        on this entity for this rate limiter class.
        
        When the value of csrlLocalRateLimiterConfigured is -1,
        the value of this object is always 0."
    ::= { csrlLocalRateLimiterEntry 3 }

csrlLocalRateLimiterTotal OBJECT-TYPE
    SYNTAX --?? syntax is not convertable to SMIv1
           Counter
--  Units
--    packets
    ACCESS read-only
    STATUS mandatory
    DESCRIPTION
        "This object indicates the number of packets processed
        on this entity for this rate limiter class.
        
        When the value of csrlLocalRateLimiterConfigured is -1,
        the value of this object is always 0."
    ::= { csrlLocalRateLimiterEntry 4 }

csrlRateLimiterClassGroup OBJECT IDENTIFIER ::= { csrlMIBGroups 1 }
-- OBJECT-GROUP
--  Status
--    mandatory
--  Descr
--    A collection of objects providing Rate Limiter Class
--    information.
--  objects
--    csrlRateLimiterClassDescr

csrlGlobalRateLimiterGroup OBJECT IDENTIFIER ::= { csrlMIBGroups 2 }
-- OBJECT-GROUP
--  Status
--    mandatory
--  Descr
--    A collection of objects providing global rate
--    limiter information.
--  objects
--    csrlGlobalRateLimiterConfigured, csrlGlobalRateLimiterAllowed, 
--    csrlGlobalRateLimiterDropped, csrlGlobalRateLimiterTotal

csrlLocalRateLimiterGroup OBJECT IDENTIFIER ::= { csrlMIBGroups 3 }
-- OBJECT-GROUP
--  Status
--    mandatory
--  Descr
--    A collection of objects providing local rate
--    limiter information.
--  objects
--    csrlLocalRateLimiterConfigured, csrlLocalRateLimiterAllowed, 
--    csrlLocalRateLimiterDropped, csrlLocalRateLimiterTotal

csrlMIBCompliance OBJECT IDENTIFIER ::= { csrlMIBCompliances 1 }
-- MODULE-COMPLIANCE
--  Status
--    mandatory
--  Descr
--    The compliance statement for
--    CISCO-SWITCH-RATE-LIMITER-MIB.my.
--  Module
--    >>current<<
--   MandGroup
--    csrlRateLimiterClassGroup
--   MandGroup
--    csrlGlobalRateLimiterGroup
--   MandGroup
--    csrlLocalRateLimiterGroup
--   ObjVar
--    csrlGlobalRateLimiterConfigured
--   ObjVar
--    csrlLocalRateLimiterConfigured


END
