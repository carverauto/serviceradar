-- MIB file created 25-Jun-2003 16:05:26, by
--   SMICng version 2.2.11-beta(PRO)(Solaris), January 20, 2001. Enterprise key cisco.com

CISCO-MGX82XX-CARD-FEATURE-MIB DEFINITIONS ::= BEGIN

-- From file: "CISCO-MGX82XX-CARD-FEATURE-MIB.my"
-- Compile options "4 7 F H N W 03 06 0B 0G 0N 0T"

IMPORTS
    cardSpecific
            FROM BASIS-MIB
    ciscoWan
            FROM CISCOWAN-SMI
    OBJECT-TYPE
            FROM RFC-1212;

ciscoMgx82xxCardFeatureMIB OBJECT IDENTIFIER ::= { ciscoWan 74 }
-- MODULE-IDENTITY
--  LastUpdated
--    200305050000Z
--  OrgName
--    Cisco Systems, Inc.
--  ContactInfo
--           Cisco Systems
--                Customer Service
--    
--        Postal: 170 W Tasman Drive
--                San Jose, CA  95134
--                USA
--    
--                Tel: +1 800 553-NETS
--    
--        E-mail: cs-wanatm@cisco.com
--  Descr
--    The MIB module which describes the features
--    supported in MGX82XX products.
--    This MIB Module provides the features supported
--    in Controller Cards in MGX8250 and MGX8220.
--    
--    Terminologies used:
--    
--    PXM : Processor Switch Module. This is controller
--          card in MGX8250.
--    ASC : AXIS Shelf Controller. This is controller
--          card in MGX8220.
--    VSI : Virtual Switch Interface, a hardware-independent 
--          switch control protocol. This allows a Switch to be
--          controlled by a multiple controllers such as PNNI, MPLS.
--          These control planes can be internal or external to the
--          switch.The VSI interface defines the messages and associated
--          functions which allow communication between the controller
--          and the switch.This interface is expected to support all
--          types of connections (voice,data,frame relay,ATM) for PVCs,
--          SPVCs and SVCs.
--    
--     Controller - Software ( and possibly hardware) which manages
--                  topology and network resources and performs VSI 
--                  Master function. This performs source routing 
--                  for end-to-end SVCs, including general call 
--                  acceptance GCAC,setup calls with other controllers.
--                  PNNI and MPLS are examples of controllers.
--  RevDate
--    200305050000Z
--  RevDescr
--    Initial version of the MIB.
--    
--    The content of this MIB was originally available
--    in CISCO-WAN-AXIPOP-MIB defined using SMIv1.
--    The applicable objects from CISCO-WAN-AXIPOP-MIB
--    are defined using SMIv2 in this MIB. Also the
--    descriptions of some of the objects have been 
--    modified.

ascFeatures     OBJECT IDENTIFIER ::= { cardSpecific 5 }
pxmFeatures     OBJECT IDENTIFIER ::= { cardSpecific 15 }
coreCardCommands OBJECT IDENTIFIER ::= { cardSpecific 20 }
cmCardFeatureMIBConformance OBJECT IDENTIFIER ::= { ciscoMgx82xxCardFeatureMIB 2 }
cmCardFeatureMIBGroups OBJECT IDENTIFIER ::= { cmCardFeatureMIBConformance 1 }
cmCardFeatureMIBCompliances OBJECT IDENTIFIER ::= { cmCardFeatureMIBConformance 2 }

vsiControllersAllowed OBJECT-TYPE
    SYNTAX INTEGER(0..16777215)
    ACCESS read-only
    STATUS mandatory
    DESCRIPTION
        "This respesents bit map of the VSI Controllers
        supported. 
        The bit positions are :
        
        BIT  0 - PAR(Portable AutoRoute Controller)
        BIT  1 - PNNI(Private network to network Interface)
        BIT  2 - TAG(Tag Switching or MPLS Controller)
        (e.g. A value of 1 in BIT 0 indicates the presence of PAR )
        Remaining bits are set to 0."
    ::= { pxmFeatures 1 }

apsCardAttributes OBJECT-TYPE
    SYNTAX INTEGER(0..255)
    ACCESS read-only
    STATUS mandatory
    DESCRIPTION
        "This respesents bit map of the APS card attributes
        supported. 
        The bit position supported are:
          BITs 0, 1     - unused
          BIT  2        - APS standard protocol configured
                         (1 = TRUE ; 0 = FALSE)
          BIT  3, 4 ,5  - unused
          BIT  6        - Card HW supports APS 1+1 on two cards
                          (1 = TRUE ; 0 = FALSE)
          BIT  7        - Card FW supports APS 
                          (1 = TRUE ; 0 = FALSE)
          Remaining bits are set to 0."
    ::= { pxmFeatures 2 }

trkCACEnable OBJECT-TYPE
    SYNTAX INTEGER {
        disable(1),
        enable(2)
        }
    ACCESS read-write
    STATUS mandatory
    DESCRIPTION
        "This MIB variable allows to add a new connection on 
        the feeder trunk even if it is over-subscribed."
    DEFVAL { disable }
    ::= { pxmFeatures 3 }

pxmCardCacMode OBJECT-TYPE
    SYNTAX INTEGER {
        pcrBasedCac(1),
        scrBasedCac(2)
        }
    ACCESS read-write
    STATUS mandatory
    DESCRIPTION
        "This object identifies the CAC mode set on a card.
        
        If this is set to pcrBasedCAC(1) then the CAC calculations
        will be done based on PCR on the connection. 
        
        If this set to scrBasedCAC(2) then the CAC calculations 
        are done based on the scr of the connections. 
        This will be applicable only if CAC is enabled
        (i.e trkCACEnable is set to enable(2))."
    DEFVAL { pcrBasedCac }
    ::= { pxmFeatures 4 }

redundancyAllowed OBJECT-TYPE
    SYNTAX INTEGER {
        redNotAllowed(1),
        redAllowed(2)
        }
    ACCESS read-only
    STATUS mandatory
    DESCRIPTION
        "This object identifies whether redundancy 
        is allowed in  MGX82XX shelf."
    ::= { ascFeatures 1 }

switchCoreCard OBJECT-TYPE
    SYNTAX INTEGER {
        noAction(1),
        doswitchcc(2),
        instswitchcc(3),
        fallbackswitchcc(4)
        }
    ACCESS read-write
    STATUS mandatory
    DESCRIPTION
        "This object is  used for performing switchover of
        core card set. The core card set includes Controller Card
        and Service Redundancy Module(SRM).
        
        The possible values are :
         noAction        (1): No operation
         doswitchcc      (2): Perform switchover operation
         instswitchcc    (3): Perform switchover operation
         fallbackswitchcc(4): "
    ::= { coreCardCommands 1 }

cmPxmCardFeatureGroup OBJECT IDENTIFIER ::= { cmCardFeatureMIBGroups 1 }
-- OBJECT-GROUP
--  Status
--    mandatory
--  Descr
--    The collection of objects which are used to represent
--    Processor Module(PXM) Features.
--  objects
--    vsiControllersAllowed, apsCardAttributes, trkCACEnable, 
--    pxmCardCacMode

cmAscCardFeatureGroup OBJECT IDENTIFIER ::= { cmCardFeatureMIBGroups 2 }
-- OBJECT-GROUP
--  Status
--    mandatory
--  Descr
--    The collection of objects which are used to represent
--    Axis Shelf Controller(ASC) Features.
--  objects
--    redundancyAllowed

cmCoreCardFeatureGroup OBJECT IDENTIFIER ::= { cmCardFeatureMIBGroups 3 }
-- OBJECT-GROUP
--  Status
--    mandatory
--  Descr
--    The collection of objects which are used to represent
--    core card related objects.
--  objects
--    switchCoreCard

cmCardFeatureCompliance OBJECT IDENTIFIER ::= { cmCardFeatureMIBCompliances 1 }
-- MODULE-COMPLIANCE
--  Status
--    mandatory
--  Descr
--    The compliance statement for objects related
--    to Frame Relay Ports.
--  Module
--    >>current<<
--   MandGroup
--    cmPxmCardFeatureGroup
--   MandGroup
--    cmAscCardFeatureGroup
--   MandGroup
--    cmCoreCardFeatureGroup


END
