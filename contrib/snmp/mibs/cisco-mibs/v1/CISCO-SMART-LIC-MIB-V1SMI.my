-- MIB file created 05-Apr-2016 10:24:23, by
--   SMICng version 2.2.11-beta(PRO)(Solaris), January 20, 2001. Enterprise key cisco.com

CISCO-SMART-LIC-MIB DEFINITIONS ::= BEGIN

-- From file: "CISCO-SMART-LIC-MIB.my"
-- Compile options "4 7 F H N W 03 06 0B 0G 0N 0T"

IMPORTS
    SnmpAdminString
            FROM SNMP-FRAMEWORK-MIB
    TruthValue
            FROM SNMPv2-TC-v1
    ciscoMgmt
            FROM CISCO-SMI
    Gauge
            FROM RFC1155-SMI
    OBJECT-TYPE
            FROM RFC-1212
    TRAP-TYPE
            FROM RFC-1215;

ciscoSmartLicMIB OBJECT IDENTIFIER ::= { ciscoMgmt 831 }
-- MODULE-IDENTITY
--  LastUpdated
--    201604050000Z
--  OrgName
--    Cisco Systems, Inc.
--  ContactInfo
--    Cisco Systems
--    Customer Service
--    
--    
--    Postal: 170 W Tasman Drive
--    
--    San Jose, CA  95134
--    
--    USA
--    
--    
--    Tel: +1 800 553-NETS
--    
--    
--    E-mail: ask-smartlicensing@cisco.com
--  Descr
--    The MIB module for managing licenses on the system.
--    The licensing mechanism provides flexibility to
--    enforce licensing for various features in the system.
--    
--    The following description introduces different concepts and
--    terminologies necessary to understand the MIB
--    definition and to perform license management.
--    
--    Product Instance: An instance of a Cisco software image that
--    runs on a hardware platform and requires some licensing
--    capability.
--    
--    Software ID tag: A string generated by the Cisco
--    Connected Software IT team to uniquely identify a Cisco 
--    software product.
--    
--    Smart Account: A Smart Licensing account that is created
--    for Cisco customers or partners to manage their Smart
--    Licensing product instances and licenses.  The account is
--    created on the Cisco Smart Software Manager portal.  An
--    enterprise account can have several virtual accounts (a.k.a.
--    pools) of licenses.  
--    
--    Cisco Smart Software Manager (CSSM): The Smart Licensing
--    back-end  system, hosted on Cisco IT infrastructure, is
--    responsible for managing all Smart Licensing services and
--    transactions.  It  provides a set of  APIs that the Smart Agent
--    can communicate with and an external-facing 
--    UI for Cisco customers and partners to log into and
--    manage their  Smart Licensing account.
--    
--    Registration Token: A token that is generated from the
--    Cisco Smart Software Manager.  The token is used to register a
--    product instance with the Cisco Smart Software Manager.
--    
--    Smart Agent: A Smart Licensing software client that runs
--    on a product instance and communicates with the Cisco Smart
--    Software Manager.
--    
--    Entitlement Tag: A unique string that identifies a
--    feature that can be enabled on a product instance.  The tags are
--    used by both the  Smart Agent and the Cisco Smart Software
--    Manager to track entitlement requests.  
--    
--    Transport Mode: The Smart Agent uses the Smart Call Home
--    (SCH) service as a transport medium to communicate with the
--    Smart Licensing back-end. 
--    
--    Crypto (LCS) Service: In addition to HTTPS exchanged
--    messages are further signed and verified on both sides to ensure
--    the authenticity of all communication.   The Smart Software
--    Licensing system uses a crypto service and underlying crypto
--    library (either CiscoSSL or PKI). The Smart Software Licensing
--    back-end leverages the Licensing Crypto Service (LCS) service.
--    
--    UDI: Unique Device Identifier that uniquely identifies a
--    device. Primarily it consists of a product ID, version ID and
--    serial number of the Customers device.
--    
--    Grace Period: A product enters into a grace period when
--    the authorization period expires. This is the result of
--    multiple authorization attempt failures which occurring 90 days
--    after the last successful authorization.  The grace period
--    continues until the grace period expires - 90 days after the
--    grace period starts.
--    
--    Counted License: Limits the number of similar entities that can
--    consume a license. For example, a counted    license when used
--    by a feature can limit the number of
--    IP phones that can connect or the number of tunnels that can be
--    created.
--    
--    Evaluation License: An Evaluation License grants the
--    right to a customer to enable functionality of a product
--    instance before registering it and without an explicit portal
--    based license for a limited amount of time.  This amount of time
--    ranges on average between 60 to 90 days.  Evaluation licenses
--    are available for most functionality, but may be limited  for a
--    variety of 
--    reasons such as legal, royalty, regulatory, or other
--    causes.
--    
--    This MIB module also defines various notifications that
--    will be triggered to asynchronously notify the management
--    application of any critical events.
--  RevDate
--    201604050000Z
--  RevDescr
--    Initial Version of Cisco Smart Licensing MIB

ciscoSlaMIBObjects OBJECT IDENTIFIER ::= { ciscoSmartLicMIB 0 }
ciscoSlaEntitlementInfo OBJECT IDENTIFIER ::= { ciscoSlaMIBObjects 5 }
ciscoSlaRegistrationStatusInfo OBJECT IDENTIFIER ::= { ciscoSlaMIBObjects 6 }
ciscoSlaRegisterTime OBJECT IDENTIFIER ::= { ciscoSlaRegistrationStatusInfo 5 }
ciscoSlaRenewTime OBJECT IDENTIFIER ::= { ciscoSlaRegistrationStatusInfo 6 }
ciscoSlaAuthorizationInfo OBJECT IDENTIFIER ::= { ciscoSlaMIBObjects 7 }
ciscoSlaAuthEvalPeriod OBJECT IDENTIFIER ::= { ciscoSlaAuthorizationInfo 4 }
ciscoSlaAuthRenewTime OBJECT IDENTIFIER ::= { ciscoSlaAuthorizationInfo 5 }
ciscoSlaNotifObjects OBJECT IDENTIFIER ::= { ciscoSlaMIBObjects 8 }
ciscoSlaMIBNotifs OBJECT IDENTIFIER ::= { ciscoSmartLicMIB 1 }
ciscoSlaMIBConform OBJECT IDENTIFIER ::= { ciscoSmartLicMIB 2 }
ciscoSlaMIBCompliances OBJECT IDENTIFIER ::= { ciscoSlaMIBConform 1 }
ciscoSlaMIBGroups OBJECT IDENTIFIER ::= { ciscoSlaMIBConform 2 }

ciscoSlaInstanceId OBJECT-TYPE
    SYNTAX Gauge
    ACCESS read-only
    STATUS mandatory
    DESCRIPTION
        "This object indicates the smart licence agent's instance
        number."
    ::= { ciscoSlaMIBObjects 1 }

ciscoSlaSUDIInfo OBJECT-TYPE
    SYNTAX SnmpAdminString
--    Rsyntax OCTET STRING(SIZE(0..255))
    ACCESS read-only
    STATUS mandatory
    DESCRIPTION
        "This object indicates the device identifier information"
    ::= { ciscoSlaMIBObjects 2 }

ciscoSlaVersion OBJECT-TYPE
    SYNTAX SnmpAdminString
--    Rsyntax OCTET STRING(SIZE(0..255))
    ACCESS read-only
    STATUS mandatory
    DESCRIPTION
        "This object indicates the smart licensing version information
        in the below shown sample format.
        sample format: Cisco Smart Licensing Agent, Version 1.1.0_290"
    ::= { ciscoSlaMIBObjects 3 }

ciscoSlaEnabled OBJECT-TYPE
    SYNTAX TruthValue
--    Rsyntax INTEGER {
--        true(1),
--        false(2)
--        }
    ACCESS read-only
    STATUS mandatory
    DESCRIPTION
        "This object indicates whether the smart licensing mode is
        enabled. A value of 'true' indicates the mode is enabled."
    ::= { ciscoSlaMIBObjects 4 }

ciscoSlaEntitlementInfoTable OBJECT-TYPE
    SYNTAX SEQUENCE OF CiscoSlaEntitlementInfoEntry
    ACCESS not-accessible
    STATUS mandatory
    DESCRIPTION
        "This table contains information about all entitlements being
        requested from this device"
    ::= { ciscoSlaEntitlementInfo 1 }

ciscoSlaEntitlementInfoEntry OBJECT-TYPE
    SYNTAX CiscoSlaEntitlementInfoEntry
    ACCESS not-accessible
    STATUS mandatory
    DESCRIPTION
        "An entry in ciscoSlaEntitlementInfoEntry. Each entry contains
        information about a entitlement requested on the device. This
        entry gets created when a license is requested successfully.
        Management application can not create these entries directly"
    INDEX { ciscoSlaEntitlementInfoIndex }
    ::= { ciscoSlaEntitlementInfoTable 1 }

CiscoSlaEntitlementInfoEntry ::= SEQUENCE {
    ciscoSlaEntitlementInfoIndex Gauge,
    ciscoSlaEntitlementRequestCount Gauge,
    ciscoSlaEntitlementTag SnmpAdminString,
    ciscoSlaEntitlementVersion SnmpAdminString,
    ciscoSlaEntitlementEnforceMode INTEGER,
    ciscoSlaEntitlementDescription SnmpAdminString,
    ciscoSlaEntitlementFeatureName SnmpAdminString
    }

ciscoSlaEntitlementInfoIndex OBJECT-TYPE
    SYNTAX Gauge
    ACCESS not-accessible
    STATUS mandatory
    DESCRIPTION
        "This object uniquely identifies an entitlement record"
    ::= { ciscoSlaEntitlementInfoEntry 1 }

ciscoSlaEntitlementRequestCount OBJECT-TYPE
    SYNTAX Gauge
    ACCESS read-only
    STATUS mandatory
    DESCRIPTION
        "Number of count that was requested for this entitlement tag. A
        value of 'zero' indicates that this entitlement is
        not in use."
    ::= { ciscoSlaEntitlementInfoEntry 2 }

ciscoSlaEntitlementTag OBJECT-TYPE
    SYNTAX SnmpAdminString
--    Rsyntax OCTET STRING(SIZE(0..255))
    ACCESS read-only
    STATUS mandatory
    DESCRIPTION
        "The tag name for the entitlement in use.
        This is abbreviated form of the entitlement tag."
    ::= { ciscoSlaEntitlementInfoEntry 3 }

ciscoSlaEntitlementVersion OBJECT-TYPE
    SYNTAX SnmpAdminString
--    Rsyntax OCTET STRING(SIZE(0..255))
    ACCESS read-only
    STATUS mandatory
    DESCRIPTION
        "This object indicates the entitlement version."
    ::= { ciscoSlaEntitlementInfoEntry 4 }

ciscoSlaEntitlementEnforceMode OBJECT-TYPE
    SYNTAX INTEGER {
        initialized(1),
        waiting(2),
        authorized(3),
        outOfCompliance(4),
        overage(5),
        evaluationPeriod(6),
        evaluationExpired(7),
        gracePeriod(8),
        gracePeriodExpired(9),
        disabled(10),
        invalidTag(11)
        }
    ACCESS read-only
    STATUS mandatory
    DESCRIPTION
        "This object indicates the enforce mode for the entitlement tag.
        
        In Entitlement notifications this will indicate the
        enforcement mode of an individual entitlement.
        In global notifications this indicates the overall
        enforcement mode in the agent."
    ::= { ciscoSlaEntitlementInfoEntry 5 }

ciscoSlaEntitlementDescription OBJECT-TYPE
    SYNTAX SnmpAdminString
--    Rsyntax OCTET STRING(SIZE(0..255))
    ACCESS read-only
    STATUS mandatory
    DESCRIPTION
        "This object indicates the description for the entitlements.
        This value is only available after the agent receives a
        response from CSSM to an Authorization request. If the
        description is unknown this object will contain a null string."
    ::= { ciscoSlaEntitlementInfoEntry 6 }

ciscoSlaEntitlementFeatureName OBJECT-TYPE
    SYNTAX SnmpAdminString
--    Rsyntax OCTET STRING(SIZE(0..255))
    ACCESS read-only
    STATUS mandatory
    DESCRIPTION
        "This value is the short feature name for the entitlement and is
        only available after the agent receives a response from CSSM to
        an Authorization request. If its value is unknown this object
        will contain a null string."
    ::= { ciscoSlaEntitlementInfoEntry 7 }

ciscoSlaRegistrationStatus OBJECT-TYPE
    SYNTAX INTEGER {
        notRegistered(1),
        registrationInProgress(2),
        registrationFailed(3),
        registrationRetryinProgress(4),
        registrationCompleted(5)
        }
    ACCESS read-only
    STATUS mandatory
    DESCRIPTION
        "Smart Agent Registration Status. This is the status of the
        registration  initiated using the token generated from the
        Cisco
        Licensing portal."
    ::= { ciscoSlaRegistrationStatusInfo 1 }

ciscoSlaVirtualAccount OBJECT-TYPE
    SYNTAX SnmpAdminString
--    Rsyntax OCTET STRING(SIZE(0..255))
    ACCESS read-only
    STATUS mandatory
    DESCRIPTION
        "The virtual account name created in the Licensing Portal to
        which this device will be registered."
    ::= { ciscoSlaRegistrationStatusInfo 2 }

ciscoSlaNextCertificateExpireTime OBJECT-TYPE
    SYNTAX Gauge
    ACCESS read-only
    STATUS mandatory
    DESCRIPTION
        "The next expiration date/time of ID Certificate in UTC epoch
        seconds."
    ::= { ciscoSlaRegistrationStatusInfo 3 }

ciscoSlaEnterpriseAccountName OBJECT-TYPE
    SYNTAX SnmpAdminString
--    Rsyntax OCTET STRING(SIZE(0..255))
    ACCESS read-only
    STATUS mandatory
    DESCRIPTION
        "The enterprise account name as configured in the Cisco
        Licensing Portal."
    ::= { ciscoSlaRegistrationStatusInfo 4 }

ciscoSlaRegisterInitTime OBJECT-TYPE
    SYNTAX Gauge
    ACCESS read-only
    STATUS mandatory
    DESCRIPTION
        "Time in UTC epoch seconds when the Registration of the Smart
        Agent
        was initialized."
    ::= { ciscoSlaRegisterTime 1 }

ciscoSlaRegisterSuccess OBJECT-TYPE
    SYNTAX TruthValue
--    Rsyntax INTEGER {
--        true(1),
--        false(2)
--        }
    ACCESS read-only
    STATUS mandatory
    DESCRIPTION
        "Status of the last attempted Registration of Smart Agent"
    ::= { ciscoSlaRegisterTime 2 }

ciscoSlaRegisterFailureReason OBJECT-TYPE
    SYNTAX SnmpAdminString
--    Rsyntax OCTET STRING(SIZE(0..255))
    ACCESS read-only
    STATUS mandatory
    DESCRIPTION
        "Reason for the failure of the last Registration Attempt"
    ::= { ciscoSlaRegisterTime 3 }

ciscoSlaRegisterNextRetryTime OBJECT-TYPE
    SYNTAX Gauge
    ACCESS read-only
    STATUS mandatory
    DESCRIPTION
        "Time in UTC epoch seconds when the next registration attempt
        will be made."
    ::= { ciscoSlaRegisterTime 4 }

ciscoSlaRenewInitTime OBJECT-TYPE
    SYNTAX Gauge
    ACCESS read-only
    STATUS mandatory
    DESCRIPTION
        "Time in UTC epoch seconds when the ID Cert renewal was
        initialized"
    ::= { ciscoSlaRenewTime 1 }

ciscoSlaRenewSuccess OBJECT-TYPE
    SYNTAX TruthValue
--    Rsyntax INTEGER {
--        true(1),
--        false(2)
--        }
    ACCESS read-only
    STATUS mandatory
    DESCRIPTION
        "Status of Renewal of ID Certificate"
    ::= { ciscoSlaRenewTime 2 }

ciscoSlaRenewFailureReason OBJECT-TYPE
    SYNTAX SnmpAdminString
--    Rsyntax OCTET STRING(SIZE(0..255))
    ACCESS read-only
    STATUS mandatory
    DESCRIPTION
        "Reason for the failure of the last attempted ID Cert Renewal"
    ::= { ciscoSlaRenewTime 3 }

ciscoSlaRenewNextRetryTime OBJECT-TYPE
    SYNTAX Gauge
    ACCESS read-only
    STATUS mandatory
    DESCRIPTION
        "Time in UTC epoch seconds when the next ID Cert  renewal will
        be tried."
    ::= { ciscoSlaRenewTime 4 }

ciscoSlaAuthExpireTime OBJECT-TYPE
    SYNTAX Gauge
    ACCESS read-only
    STATUS mandatory
    DESCRIPTION
        "The time in UTC epoch seconds  when the authorization will
        expire if
        not renewed"
    ::= { ciscoSlaAuthorizationInfo 1 }

ciscoSlaAuthComplianceStatus OBJECT-TYPE
    SYNTAX SnmpAdminString
--    Rsyntax OCTET STRING(SIZE(0..255))
    ACCESS read-only
    STATUS mandatory
    DESCRIPTION
        "Overall enforcement status of Smart Licensing in the device."
    ::= { ciscoSlaAuthorizationInfo 2 }

ciscoSlaAuthOOCStartTime OBJECT-TYPE
    SYNTAX Gauge
    ACCESS read-only
    STATUS mandatory
    DESCRIPTION
        "The  time in UTC epoch seconds Smart Agent entered Out of
        Compliance state for this
        device."
    ::= { ciscoSlaAuthorizationInfo 3 }

ciscoSlaAuthEvalPeriodInUse OBJECT-TYPE
    SYNTAX TruthValue
--    Rsyntax INTEGER {
--        true(1),
--        false(2)
--        }
    ACCESS read-only
    STATUS mandatory
    DESCRIPTION
        "Indicates if the Evaluation Period is in Use or not"
    ::= { ciscoSlaAuthEvalPeriod 1 }

ciscoSlaAuthEvalExpiredTime OBJECT-TYPE
    SYNTAX Gauge
    ACCESS read-only
    STATUS mandatory
    DESCRIPTION
        "Time in UTC epoch seconds  when the Evaluation Period had
        expired."
    ::= { ciscoSlaAuthEvalPeriod 2 }

ciscoSlaAuthEvalPeriodLeft OBJECT-TYPE
    SYNTAX Gauge
    ACCESS read-only
    STATUS mandatory
    DESCRIPTION
        "Amount of Time left in the Evaluation Period"
    ::= { ciscoSlaAuthEvalPeriod 3 }

ciscoSlaAuthRenewInitTime OBJECT-TYPE
    SYNTAX Gauge
    ACCESS read-only
    STATUS mandatory
    DESCRIPTION
        "Smart Agent Authorization Renewal Initialization Time in UTC
        epoch seconds"
    ::= { ciscoSlaAuthRenewTime 1 }

ciscoSlaAuthRenewSuccess OBJECT-TYPE
    SYNTAX TruthValue
--    Rsyntax INTEGER {
--        true(1),
--        false(2)
--        }
    ACCESS read-only
    STATUS mandatory
    DESCRIPTION
        "This object indicates the authorization renewal status. A
        value of 'true' indicates the renewal was successful."
    ::= { ciscoSlaAuthRenewTime 2 }

ciscoSlaAuthRenewFailureReason OBJECT-TYPE
    SYNTAX SnmpAdminString
--    Rsyntax OCTET STRING(SIZE(0..255))
    ACCESS read-only
    STATUS mandatory
    DESCRIPTION
        "This object indicates the reason for the failure of the last
        renewal request."
    ::= { ciscoSlaAuthRenewTime 3 }

ciscoSlaAuthRenewNextRetryTime OBJECT-TYPE
    SYNTAX Gauge
    ACCESS read-only
    STATUS mandatory
    DESCRIPTION
        "Time in UTC epoch seconds when the next renewal will be
        retried."
    ::= { ciscoSlaAuthRenewTime 4 }

ciscoSlaGlobalNotifEnable OBJECT-TYPE
    SYNTAX TruthValue
--    Rsyntax INTEGER {
--        true(1),
--        false(2)
--        }
    ACCESS read-write
    STATUS mandatory
    DESCRIPTION
        "This object indicates whether the device should generate
        the global notifications related to Smart Agent. This object
        enables/disables sending following notifications:
         ciscoSlaSmartAgentNotifyEnforcementMode,
         ciscoSlaSmartAgentNotifyReady,
         ciscoSlaSmartAgentNotifyEnabled,
         ciscoSlaSmartAgentNotifyDisabled,                            
         ciscoSlaSmartAgentNotifyRegisterFailed,                       
         ciscoSlaSmartAgentNotifyRegisterSuccess,                       
         ciscoSlaSmartAgentNotifyIdCertExpired,                       
         ciscoSlaSmartAgentNotifyIdCertRenewSuccess,
         ciscoSlaSmartAgentNotifyIdCertRenewFail,                      
         ciscoSlaSmartAgentNotifyAuthRenewSuccess,                      
         ciscoSlaSmartAgentNotifyAuthRenewFail,                       
         ciscoSlaSmartAgentNotifyCommunicationFailure,
         ciscoSlaSmartAgentNotifyCommunicationRestored,              
         ciscoSlaSmartAgentNotifyIdCertRenewNotStarted,         
         ciscoSlaSmartAgentNotifyIdCertOutOfRange,         
         ciscoSlaSmartAgentNotifySystemClockChanged,       
         ciscoSlaSmartAgentNotifyEvalExpiryWarning,      
         ciscoSlaSmartAgentNotifyEvalExpired,           
         ciscoSlaSmartAgentNotifyIdCertExpiryWarning"
    DEFVAL { true }
    ::= { ciscoSlaNotifObjects 1 }

ciscoSlaEntitlementNotifEnable OBJECT-TYPE
    SYNTAX TruthValue
--    Rsyntax INTEGER {
--        true(1),
--        false(2)
--        }
    ACCESS read-write
    STATUS mandatory
    DESCRIPTION
        "This object indicates whether the device should generate
        the  notifications related to entitlement enforce mode in Smart
        Agent. This object
        enables/disables sending following notifications:
        ciscoSlaSmartAgentNotifyEntitlementEnforceMode"
    DEFVAL { true }
    ::= { ciscoSlaNotifObjects 2 }

ciscoSlaSmartAgentNotifyEnforcementMode TRAP-TYPE
--?? Non-reverse mappable trap
    ENTERPRISE ciscoSlaMIBNotifs
    VARIABLES {
        ciscoSlaSUDIInfo, ciscoSlaEntitlementEnforceMode }
--  Status
--    mandatory
    DESCRIPTION
        "The device generates this notification when the overall
        enforcement mode in the agent changes."
    ::= 1

ciscoSlaSmartAgentNotifyReady TRAP-TYPE
--?? Non-reverse mappable trap
    ENTERPRISE ciscoSlaMIBNotifs
    VARIABLES {
        ciscoSlaSUDIInfo }
--  Status
--    mandatory
    DESCRIPTION
        "The device generates this notification when the Smart agent is
        initialized and ready."
    ::= 2

ciscoSlaSmartAgentNotifyEnabled TRAP-TYPE
--?? Non-reverse mappable trap
    ENTERPRISE ciscoSlaMIBNotifs
    VARIABLES {
        ciscoSlaSUDIInfo }
--  Status
--    mandatory
    DESCRIPTION
        "The device generates this notification when Smart licensing has
        been enabled."
    ::= 3

ciscoSlaSmartAgentNotifyDisabled TRAP-TYPE
--?? Non-reverse mappable trap
    ENTERPRISE ciscoSlaMIBNotifs
    VARIABLES {
        ciscoSlaSUDIInfo }
--  Status
--    mandatory
    DESCRIPTION
        "The device generates this notification when Smart licensing has
        been disabled"
    ::= 4

ciscoSlaSmartAgentNotifyRegisterFailed TRAP-TYPE
--?? Non-reverse mappable trap
    ENTERPRISE ciscoSlaMIBNotifs
    VARIABLES {
        ciscoSlaSUDIInfo }
--  Status
--    mandatory
    DESCRIPTION
        "The device generates this notification when Smart licensing
        registration with Cisco Software Manager has failed"
    ::= 5

ciscoSlaSmartAgentNotifyRegisterSuccess TRAP-TYPE
--?? Non-reverse mappable trap
    ENTERPRISE ciscoSlaMIBNotifs
    VARIABLES {
        ciscoSlaSUDIInfo }
--  Status
--    mandatory
    DESCRIPTION
        "The device generates this notification when smart licensing
        registration with Cisco Software Manager has succeeded."
    ::= 6

ciscoSlaSmartAgentNotifyIdCertExpired TRAP-TYPE
--?? Non-reverse mappable trap
    ENTERPRISE ciscoSlaMIBNotifs
    VARIABLES {
        ciscoSlaSUDIInfo }
--  Status
--    mandatory
    DESCRIPTION
        "The device generates this notification when Smart licensing ID
        (node) certificate has expired"
    ::= 7

ciscoSlaSmartAgentNotifyIdCertRenewSuccess TRAP-TYPE
--?? Non-reverse mappable trap
    ENTERPRISE ciscoSlaMIBNotifs
    VARIABLES {
        ciscoSlaSUDIInfo }
--  Status
--    mandatory
    DESCRIPTION
        "The device generates this notification when Smart licensing ID
        (node) certificate renewal has succeded."
    ::= 8

ciscoSlaSmartAgentNotifyIdCertRenewFail TRAP-TYPE
--?? Non-reverse mappable trap
    ENTERPRISE ciscoSlaMIBNotifs
    VARIABLES {
        ciscoSlaSUDIInfo }
--  Status
--    mandatory
    DESCRIPTION
        "The device generates this notification when Smart licensing ID
        (node) certificate renewal has failed."
    ::= 9

ciscoSlaSmartAgentNotifyAuthRenewSuccess TRAP-TYPE
--?? Non-reverse mappable trap
    ENTERPRISE ciscoSlaMIBNotifs
    VARIABLES {
        ciscoSlaSUDIInfo }
--  Status
--    mandatory
    DESCRIPTION
        "The device generates this notification when Smart licensing
        entitlement (AUTH) renew was successful."
    ::= 10

ciscoSlaSmartAgentNotifyAuthRenewFail TRAP-TYPE
--?? Non-reverse mappable trap
    ENTERPRISE ciscoSlaMIBNotifs
    VARIABLES {
        ciscoSlaSUDIInfo }
--  Status
--    mandatory
    DESCRIPTION
        "The device generates this notification when Smart licensing
        entitlement (AUTH) renew has failed"
    ::= 11

ciscoSlaSmartAgentNotifyCommunicationFailure TRAP-TYPE
--?? Non-reverse mappable trap
    ENTERPRISE ciscoSlaMIBNotifs
    VARIABLES {
        ciscoSlaSUDIInfo }
--  Status
--    mandatory
    DESCRIPTION
        "The device generates this notification when Smart Agent
        failed to communicate with CSSM."
    ::= 12

ciscoSlaSmartAgentNotifyCommunicationRestored TRAP-TYPE
--?? Non-reverse mappable trap
    ENTERPRISE ciscoSlaMIBNotifs
    VARIABLES {
        ciscoSlaSUDIInfo }
--  Status
--    mandatory
    DESCRIPTION
        "The device generates this notification when Smart Agent
        communication with CSSM has been restored"
    ::= 13

ciscoSlaSmartAgentNotifyIdCertRenewNotStarted TRAP-TYPE
--?? Non-reverse mappable trap
    ENTERPRISE ciscoSlaMIBNotifs
    VARIABLES {
        ciscoSlaSUDIInfo }
--  Status
--    mandatory
    DESCRIPTION
        "The device generates this notification when Smart Agent
        Id (Node) certificate renewal is not started"
    ::= 14

ciscoSlaSmartAgentNotifyEntitlementEnforceMode TRAP-TYPE
--?? Non-reverse mappable trap
    ENTERPRISE ciscoSlaMIBNotifs
    VARIABLES {
        ciscoSlaEntitlementRequestCount, ciscoSlaEntitlementTag, 
        ciscoSlaEntitlementVersion, ciscoSlaEntitlementEnforceMode, 
        ciscoSlaSUDIInfo }
--  Status
--    mandatory
    DESCRIPTION
        "The device generates this notification when the enforcement
        mode of an entitlement has changed."
    ::= 15

ciscoSlaSmartAgentNotifyIdCertOutOfRange TRAP-TYPE
--?? Non-reverse mappable trap
    ENTERPRISE ciscoSlaMIBNotifs
    VARIABLES {
        ciscoSlaSUDIInfo }
--  Status
--    mandatory
    DESCRIPTION
        "The device generates this notification when the ID certificate
        is out of the valid range after the system clock changed.
        It means the current time is either before the start time or
        after the end time of the certificate."
    ::= 16

ciscoSlaSmartAgentNotifySystemClockChanged TRAP-TYPE
--?? Non-reverse mappable trap
    ENTERPRISE ciscoSlaMIBNotifs
    VARIABLES {
        ciscoSlaSUDIInfo }
--  Status
--    mandatory
    DESCRIPTION
        "The device generates this notification when the system clock
        has changed."
    ::= 17

ciscoSlaSmartAgentNotifyEvalExpiryWarning TRAP-TYPE
--?? Non-reverse mappable trap
    ENTERPRISE ciscoSlaMIBNotifs
    VARIABLES {
        ciscoSlaSUDIInfo }
--  Status
--    mandatory
    DESCRIPTION
        "The device generates this notification to warn regarding the
        impending evaluation  time expiry."
    ::= 18

ciscoSlaSmartAgentNotifyEvalExpired TRAP-TYPE
--?? Non-reverse mappable trap
    ENTERPRISE ciscoSlaMIBNotifs
    VARIABLES {
        ciscoSlaSUDIInfo }
--  Status
--    mandatory
    DESCRIPTION
        "The device generates this notification to notify the expiration
        of the evaluation period."
    ::= 19

ciscoSlaSmartAgentNotifyIdCertExpiryWarning TRAP-TYPE
--?? Non-reverse mappable trap
    ENTERPRISE ciscoSlaMIBNotifs
    VARIABLES {
        ciscoSlaSUDIInfo }
--  Status
--    mandatory
    DESCRIPTION
        "The device generates this notification to warn regarding the
        impending expiry of the id (node) certificate."
    ::= 20

ciscoSlaMIBEntitlementInfoGroup OBJECT IDENTIFIER ::= { ciscoSlaMIBGroups 1 }
-- OBJECT-GROUP
--  Status
--    mandatory
--  Descr
--    A collection of objects for Entitlements requested and their
--    related information.
--  objects
--    ciscoSlaEntitlementRequestCount, ciscoSlaEntitlementTag, 
--    ciscoSlaEntitlementVersion, ciscoSlaEntitlementEnforceMode, 
--    ciscoSlaEntitlementFeatureName, 
--    ciscoSlaEntitlementDescription

ciscoSlaMIBRegistrationStatusInfoGroup OBJECT IDENTIFIER ::= { ciscoSlaMIBGroups 2 }
-- OBJECT-GROUP
--  Status
--    mandatory
--  Descr
--    A collection of objects representing the information regarding
--    the registration status of the device.
--  objects
--    ciscoSlaRegistrationStatus, ciscoSlaVirtualAccount, 
--    ciscoSlaNextCertificateExpireTime, 
--    ciscoSlaEnterpriseAccountName, ciscoSlaRegisterInitTime, 
--    ciscoSlaRegisterSuccess, ciscoSlaRenewInitTime, 
--    ciscoSlaRenewSuccess, ciscoSlaRenewFailureReason, 
--    ciscoSlaRenewNextRetryTime, ciscoSlaRegisterFailureReason, 
--    ciscoSlaRegisterNextRetryTime

ciscoSlaMIBAgentInfoGroup OBJECT IDENTIFIER ::= { ciscoSlaMIBGroups 4 }
-- OBJECT-GROUP
--  Status
--    mandatory
--  Descr
--    A collection of objects representing meta data related to Smart
--    Agent state
--  objects
--    ciscoSlaVersion, ciscoSlaEnabled, ciscoSlaSUDIInfo, 
--    ciscoSlaInstanceId

ciscoSlaMIBNotificationEnableGroup OBJECT IDENTIFIER ::= { ciscoSlaMIBGroups 6 }
-- OBJECT-GROUP
--  Status
--    mandatory
--  Descr
--    A collection of objects for controlling
--    (enabling/disabling) license notifications to a management
--    application.
--  objects
--    ciscoSlaGlobalNotifEnable, ciscoSlaEntitlementNotifEnable

ciscoSlaMIBAuthorizationInfoGroup OBJECT IDENTIFIER ::= { ciscoSlaMIBGroups 7 }
-- OBJECT-GROUP
--  Status
--    mandatory
--  Descr
--    A collection of MIB objects representing the Authorization
--    State
--    of the Smart Agent.
--  objects
--    ciscoSlaAuthExpireTime, ciscoSlaAuthComplianceStatus, 
--    ciscoSlaAuthOOCStartTime, ciscoSlaAuthRenewInitTime, 
--    ciscoSlaAuthRenewSuccess, ciscoSlaAuthRenewFailureReason, 
--    ciscoSlaAuthRenewNextRetryTime, ciscoSlaAuthEvalPeriodInUse, 
--    ciscoSlaAuthEvalExpiredTime, ciscoSlaAuthEvalPeriodLeft

ciscoSlaMIBGlobalNotificationGroup OBJECT IDENTIFIER ::= { ciscoSlaMIBGroups 3 }
-- NOTIFICATION-GROUP
--  Status
--    mandatory
--  Descr
--    A collection of global notifications related to Smart   Agent
--  notifications
--    ciscoSlaSmartAgentNotifyEnforcementMode, 
--    ciscoSlaSmartAgentNotifyReady, 
--    ciscoSlaSmartAgentNotifyEnabled, 
--    ciscoSlaSmartAgentNotifyDisabled, 
--    ciscoSlaSmartAgentNotifyRegisterFailed, 
--    ciscoSlaSmartAgentNotifyRegisterSuccess, 
--    ciscoSlaSmartAgentNotifyIdCertExpired, 
--    ciscoSlaSmartAgentNotifyIdCertRenewSuccess, 
--    ciscoSlaSmartAgentNotifyIdCertRenewFail, 
--    ciscoSlaSmartAgentNotifyAuthRenewSuccess, 
--    ciscoSlaSmartAgentNotifyAuthRenewFail, 
--    ciscoSlaSmartAgentNotifyCommunicationFailure, 
--    ciscoSlaSmartAgentNotifyCommunicationRestored, 
--    ciscoSlaSmartAgentNotifyIdCertRenewNotStarted, 
--    ciscoSlaSmartAgentNotifyIdCertOutOfRange, 
--    ciscoSlaSmartAgentNotifySystemClockChanged, 
--    ciscoSlaSmartAgentNotifyEvalExpiryWarning, 
--    ciscoSlaSmartAgentNotifyEvalExpired, 
--    ciscoSlaSmartAgentNotifyIdCertExpiryWarning

ciscoSlaMIBEntitlementNotifGroup OBJECT IDENTIFIER ::= { ciscoSlaMIBGroups 5 }
-- NOTIFICATION-GROUP
--  Status
--    mandatory
--  Descr
--    A collection of  notifications related to entitlement enforce
--    mode in SmartAgent
--  notifications
--    ciscoSlaSmartAgentNotifyEntitlementEnforceMode

ciscoSlaMIBCompliance OBJECT IDENTIFIER ::= { ciscoSlaMIBCompliances 1 }
-- MODULE-COMPLIANCE
--  Status
--    mandatory
--  Descr
--    Compliance statement for Cisco Smart license MIB.
--  Module
--    >>current<<
--   MandGroup
--    ciscoSlaMIBEntitlementInfoGroup
--   MandGroup
--    ciscoSlaMIBRegistrationStatusInfoGroup
--   MandGroup
--    ciscoSlaMIBGlobalNotificationGroup
--   MandGroup
--    ciscoSlaMIBAgentInfoGroup
--   MandGroup
--    ciscoSlaMIBEntitlementNotifGroup
--   MandGroup
--    ciscoSlaMIBNotificationEnableGroup
--   MandGroup
--    ciscoSlaMIBAuthorizationInfoGroup


END
