-- MIB file created 28-Oct-2010 14:58:12, by
--   SMICng version 2.2.11-beta(PRO)(Solaris), January 20, 2001. Enterprise key cisco.com

Printer-MIB DEFINITIONS ::= BEGIN

-- From file: "Printer-MIB.my"
-- Compile options "4 7 F H N W 03 06 0B 0G 0N 0T"

IMPORTS
    mib-2
            FROM SNMPv2-SMI-v1
    hrDeviceIndex, hrStorageIndex
            FROM HOST-RESOURCES-MIB
    InterfaceIndexOrZero
            FROM IF-MIB
    PrtCoverStatusTC, PrtGeneralResetTC, PrtChannelTypeTC, 
    PrtInterpreterLangFamilyTC, PrtInputTypeTC, PrtOutputTypeTC, 
    PrtMarkerMarkTechTC, PrtMarkerSuppliesTypeTC, PrtConsoleColorTC, 
    PrtConsoleDisableTC, PrtMediaPathTypeTC, PrtAlertGroupTC, 
    PrtAlertTrainingLevelTC, PrtAlertCodeTC
            FROM IANA-PRINTER-MIB
    IANACharset
            FROM IANA-CHARSET-MIB
    Counter, TimeTicks
            FROM RFC1155-SMI
    OBJECT-TYPE
            FROM RFC-1212
    TRAP-TYPE
            FROM RFC-1215;

printmib OBJECT IDENTIFIER ::= { mib-2 43 }
-- MODULE-IDENTITY
--  LastUpdated
--    200406020000Z
--  OrgName
--    PWG IEEE/ISTO Printer Working Group
--  ContactInfo
--    Harry Lewis
--    IBM
--    Phone (303) 924-5337
--    Email: harryl@us.ibm.com
--    http://www.pwg.org/index.html
--    
--    Send comments to the printmib WG using the Printer MIB
--    Project (PMP) Mailing List:  pmp@pwg.org
--    
--    For further information, access the PWG web page under 'Printer
--    MIB':      http://www.pwg.org/
--    
--    Implementers of this specification are encouraged to join the
--    pmp mailing list in order to participate in discussions on any
--    clarifications needed and registration proposals being reviewed
--    in order to achieve consensus.
--  Descr
--    The MIB module for management of printers.
--     Copyright (C) The Internet Society (2004). This
--     version of this MIB module was published
--     in RFC 3805. For full legal notices see the RFC itself.
--  RevDate
--    200406020000Z
--  RevDescr
--    Printer MIB v2.
--    Moved all enum groups to be maintained by IANA into new TCs
--       within the ianaPrinterMIB, which is contained in this
--       document.
--    New TCs created from enums defined within RFC 1759 Objects:
--       PrtPrintOrientationTC, PrtLocalizedDescriptionStringTC,
--       PrtConsoleDescriptionStringTC, PrtChannelStateTC,
--       PrtOutputStackingOrderTC, PrtOutputPageDeliveryOrientationTC,
--       PrtMarkerCounterUnitTC, PrtMarkerSuppliesSupplyUnitTC,
--       PrtMarkerSuppliesClassTC, PrtMarkerAddressabilityUnitTC,
--       PrtMarkerColorantRoleTC, PrtMediaPathMaxSpeedPrintUnitTC,
--       PrtInterpreterTwoWayTC, and PrtAlertSeverityLevelTC.
--    The following four TCs have been deprecated:
--       MediaUnit (replaced by PrtMediaUnitTC),
--       CapacityUnit (replaced by PrtCapacityUnitTC),
--       SubUnitStatus (replaced by PrtSubUnitStatusTC),
--       CodedCharSet (replaced by IANACharset in IANA Charset MIB)
--    Five new OBJECT-GROUPs: prtAuxilliarySheetGroup,
--       prtInputSwitchingGroup, prtGeneralV2Group,
--       prtAlertTableV2Group, prtChannelV2Group.
--    Nine new objects added to those groups:
--       prtAuxiliarySheetStartupPage, prtAuxiliarySheetBannerPage,
--       prtGeneralPrinterName, prtGeneralSerialNumber,
--       prtAlertCriticalEvents, prtAlertAllEvents,
--    
--       prtInputMediaLoadTimeout, prtInputNextIndex,
--       prtChannelInformation.
--    SYNTAX range changed from (0..65535) to (1..65535) for the
--       index objects prtStorageRefSeqNumber, prtDeviceRefSeqNumber,
--       and prtConsoleLightIndex.
--    SYNTAX range changed from (0..65535) to (0..2147483647) for the
--       objects prtStorageRefIndex and prtDeviceRefIndex to agree
--       with the Host Resources MIB.
--    Defined a range for the objects with a SYNTAX of Integer32:
--       prtOutputDefaultIndex, prtInputMediaDimFeedDirDeclared,
--       prtInputMediaDimXFeedDirDeclared, prtInputMaxCapacity,
--       prtInputCurrentLevel, prtInputMediaDimFeedDirChosen,
--       prtInputMediaDimXFeedDirChosen, prtInputMediaWeight,
--       prtInputMediaFormParts, prtOutputIndex,
--       prtOutputMaxCapacity, prtOutputRemainingCapacity,
--       prtOutputMaxDimFeedDir, prtOutputMaxDimXFeedDir,
--       prtOutputMinDimFeedDir, prtOutputMinDimXFeedDir,
--       prtMarkerAddressibilityFeedDir,
--       prtMarkerAddressibilityXFeedDir, prtMarkerNorthMargin,
--       prtMarkerSouthMargin, prtMarkerWestMargin,
--       prtMarkerEastMargin, prtMarkerSuppliesMaxCapacity,
--       prtMarkerSuppliesLevel, prtMarkerColorantTonality,
--       prtMediaPathMaxSpeed, prtMediaPathMaxMediaFeedDir,
--       prtMediaPathMaxMediaXFeedDir, prtMediaPathMinMediaFeedDir,
--       prtMediaPathMinMediaXFeedDir, prtChannelIndex,
--       prtChannelCurrentJobCntlLangIndex, prtInterpreterIndex,
--       prtChannelDefaultPageDescLangIndex, prtConsoleOnTime,
--       prtInterpreterFeedAddressibility, prtConsoleOffTime,
--       prtInterpreterXFeedAddressibility, prtAlertIndex,
--       prtAlertGroupIndex, prtAlertLocation.
--    Changed SYNTAX from Integer32 to InterfaceIndexOrZero for
--       prtChannelIfIndex.
--    Changed MAX-ACCESS of prtAlertIndex from not-accessible to
--       Read-only and added a compliance statement to allow a
--       MIN-ACCESS of accessible-for-notify.
--    One new NOTIFICATION-GROUP: prtAlertTrapGroup which contains
--       printerV2Alert.
--    In MODULE-COMPLIANCE prtMIBCompliance, new OBJECT-GROUPs and
--       the NOTIFICATION_GROUP, all in GROUP (not MANDATORY-GROUP)
--       clauses.  The nine new objects are optional, i.e., this
--       document is backward compatible with RFC 1759.
--  RevDate
--    199411250000Z
--  RevDescr
--    The original version of this MIB, published as RFC1759.

prtGeneral      OBJECT IDENTIFIER ::= { printmib 5 }
prtCover        OBJECT IDENTIFIER ::= { printmib 6 }
prtLocalization OBJECT IDENTIFIER ::= { printmib 7 }
prtInput        OBJECT IDENTIFIER ::= { printmib 8 }
prtOutput       OBJECT IDENTIFIER ::= { printmib 9 }
prtMarker       OBJECT IDENTIFIER ::= { printmib 10 }
prtMarkerSupplies OBJECT IDENTIFIER ::= { printmib 11 }
prtMarkerColorant OBJECT IDENTIFIER ::= { printmib 12 }
prtMediaPath    OBJECT IDENTIFIER ::= { printmib 13 }
prtChannel      OBJECT IDENTIFIER ::= { printmib 14 }
prtInterpreter  OBJECT IDENTIFIER ::= { printmib 15 }
prtConsoleDisplayBuffer OBJECT IDENTIFIER ::= { printmib 16 }
prtConsoleLights OBJECT IDENTIFIER ::= { printmib 17 }
prtAlert        OBJECT IDENTIFIER ::= { printmib 18 }
printerV2AlertPrefix OBJECT IDENTIFIER ::= { printerV1Alert 0 }
prtMIBConformance OBJECT IDENTIFIER ::= { printmib 2 }
prtMIBGroups    OBJECT IDENTIFIER ::= { prtMIBConformance 2 }
prtMIB2Groups   OBJECT IDENTIFIER ::= { prtMIBConformance 4 }

printerV1Alert OBJECT IDENTIFIER ::= { prtAlert 2 }
-- OBJECT-IDENTITY
--  Status
--    mandatory
--  Descr
--    The value of the enterprise-specific OID in an SNMPv1 trap
--    sent signaling a critical event in the prtAlertTable.

PrtMediaUnitTC ::= INTEGER {
        tenThousandthsOfInches(3),
        micrometers(4)
        }
-- TEXTUAL-CONVENTION
--  Status
--    mandatory
--  Descr
--    Units of measure for media dimensions.

MediaUnit ::= INTEGER {
        tenThousandthsOfInches(3),
        micrometers(4)
        }
-- TEXTUAL-CONVENTION
--  Status
--    deprecated
--  Descr
--    Units of measure for media dimensions.

PrtCapacityUnitTC ::= INTEGER {
        other(1),
        unknown(2),
        tenThousandthsOfInches(3),
        micrometers(4),
        sheets(8),
        feet(16),
        meters(17),
        items(18),
        percent(19)
        }
-- TEXTUAL-CONVENTION
--  Status
--    mandatory
--  Descr
--    Units of measure for media capacity.

CapacityUnit ::= INTEGER {
        tenThousandthsOfInches(3),
        micrometers(4),
        sheets(8),
        feet(16),
        meters(17)
        }
-- TEXTUAL-CONVENTION
--  Status
--    deprecated
--  Descr
--    Units of measure for media capacity.

PrtPrintOrientationTC ::= INTEGER {
        other(1),
        portrait(3),
        landscape(4)
        }
-- TEXTUAL-CONVENTION
--  Status
--    mandatory
--  Descr
--    A generic representation for printing orientation on a
--    'page'.

PrtSubUnitStatusTC ::= INTEGER(0..126)
-- TEXTUAL-CONVENTION
--  Status
--    mandatory
--  Descr
--    Status of a printer sub-unit.
--    
--    The SubUnitStatus is an integer that is the sum of 5 distinct
--    values, Availability, Non-Critical, Critical, On-line, and
--    Transitioning. These values are:
--    
--    Availability                           Value
--    
--        Available and Idle                  0       0000'b
--        Available and Standby               2       0010'b
--        Available and Active                4       0100'b
--        Available and Busy                  6       0110'b
--        Unavailable and OnRequest           1       0001'b
--        Unavailable because Broken          3       0011'b
--        Unknown                             5       0101'b
--    
--    Non-Critical
--        No Non-Critical Alerts              0       0000'b
--        Non-Critical Alerts                 8       1000'b
--    
--    Critical
--    
--        No Critical Alerts                  0       0000'b
--    
--        Critical Alerts                    16     1 0000'b
--    
--    On-Line
--    
--        State is On-Line                    0       0000'b
--        State is Off-Line                  32    10 0000'b
--    
--    Transitioning
--    
--        At intended state                   0       0000'b
--        Transitioning to intended state    64   100 0000'b

SubUnitStatus ::= INTEGER(0..126)
-- TEXTUAL-CONVENTION
--  Status
--    deprecated
--  Descr
--    Status of a printer sub-unit.
--    
--    The SubUnitStatus is an integer that is the sum of 5 distinct
--    values, Availability, Non-Critical, Critical, On-line, and
--    Transitioning. These values are:
--    
--    Availability                           Value
--        Available and Idle                  0       0000'b
--        Available and Standby               2       0010'b
--        Available and Active                4       0100'b
--        Available and Busy                  6       0110'b
--        Unavailable and OnRequest           1       0001'b
--        Unavailable because Broken          3       0011'b
--        Unknown                             5       0101'b
--    
--    Non-Critical
--        No Non-Critical Alerts              0       0000'b
--        Non-Critical Alerts                 8       1000'b
--    
--    Critical
--    
--        No Critical Alerts                  0       0000'b
--        Critical Alerts                    16     1 0000'b
--    
--    On-Line
--    
--        State is On-Line                    0       0000'b
--        State is Off-Line                  32    10 0000'b
--    
--    Transitioning
--    
--        At intended state                   0       0000'b
--        Transitioning to intended state    64   100 0000'b

PresentOnOff ::= INTEGER {
        other(1),
        on(3),
        off(4),
        notPresent(5)
        }
-- TEXTUAL-CONVENTION
--  Status
--    mandatory
--  Descr
--    Presence and configuration of a device or feature.

PrtLocalizedDescriptionStringTC ::= OCTET STRING(SIZE(0..255))
-- TEXTUAL-CONVENTION
--  Status
--    mandatory
--  Descr
--    An object MUST use this TEXTUAL-CONVENTION when its
--    'charset' is controlled by the value of
--    prtGeneralCurrentLocalization.

PrtConsoleDescriptionStringTC ::= OCTET STRING(SIZE(0..255))
-- TEXTUAL-CONVENTION
--  Status
--    mandatory
--  Descr
--    An object MUST use this TEXTUAL-CONVENTION when its
--    'charset' is controlled by the value of
--    prtConsoleLocalization.

CodedCharSet ::= INTEGER {
        other(1)
        }
-- TEXTUAL-CONVENTION
--  Status
--    deprecated
--  Descr
--    The original description clause from RFC 1759 [RFC1759] was
--    technically inaccurate and therefore has been deleted.

PrtChannelStateTC ::= INTEGER {
        other(1),
        printDataAccepted(3),
        noDataAccepted(4)
        }
-- TEXTUAL-CONVENTION
--  Status
--    mandatory
--  Descr
--    The state of this print job delivery channel. The value
--    determines whether print data is allowed through this channel.

PrtOutputStackingOrderTC ::= INTEGER {
        unknown(2),
        firstToLast(3),
        lastToFirst(4)
        }
-- TEXTUAL-CONVENTION
--  Status
--    mandatory
--  Descr
--    The current state of the stacking order for the associated
--    output sub-unit. 'firstToLast' means that as pages are output,
--    the front of the next page is placed against the back of the
--    previous page. 'lastToFirst' means that as pages are output,
--    the back of the next page is placed against the front of the
--    previous page.

PrtOutputPageDeliveryOrientationTC ::= INTEGER {
        faceUp(3),
        faceDown(4)
        }
-- TEXTUAL-CONVENTION
--  Status
--    mandatory
--  Descr
--    The reading surface that will be 'up' when pages are delivered
--    to the associated output sub-unit. Values are Face-Up and Face
--    Down (Note: interpretation of these values is, in general,
--    context-dependent based on locale; presentation of these values
--    to an end-user should be normalized to the expectations of the
--    user.

PrtMarkerCounterUnitTC ::= INTEGER {
        tenThousandthsOfInches(3),
        micrometers(4),
        characters(5),
        lines(6),
        impressions(7),
        sheets(8),
        dotRow(9),
        hours(11),
        feet(16),
        meters(17)
        }
-- TEXTUAL-CONVENTION
--  Status
--    mandatory
--  Descr
--    The unit that will be used by the printer when reporting
--    counter values for this marking sub-unit.  The
--    time units of measure are provided for a device like a
--    strip recorder that does not or cannot track the physical
--    dimensions of the media and does not use characters,
--    lines or sheets.

PrtMarkerSuppliesSupplyUnitTC ::= INTEGER {
        other(1),
        unknown(2),
        tenThousandthsOfInches(3),
        micrometers(4),
        impressions(7),
        sheets(8),
        hours(11),
        thousandthsOfOunces(12),
        tenthsOfGrams(13),
        hundrethsOfFluidOunces(14),
        tenthsOfMilliliters(15),
        feet(16),
        meters(17),
        items(18),
        percent(19)
        }
-- TEXTUAL-CONVENTION
--  Status
--    mandatory
--  Descr
--    Unit of this marker supply container/receptacle.

PrtMarkerSuppliesClassTC ::= INTEGER {
        other(1),
        supplyThatIsConsumed(3),
        receptacleThatIsFilled(4)
        }
-- TEXTUAL-CONVENTION
--  Status
--    mandatory
--  Descr
--    Indicates whether this supply entity represents a supply
--    that is consumed or a receptacle that is filled.

PrtMarkerColorantRoleTC ::= INTEGER {
        other(1),
        process(3),
        spot(4)
        }
-- TEXTUAL-CONVENTION
--  Status
--    mandatory
--  Descr
--    The role played by this colorant.

PrtMarkerAddressabilityUnitTC ::= INTEGER {
        tenThousandthsOfInches(3),
        micrometers(4)
        }
-- TEXTUAL-CONVENTION
--  Status
--    mandatory
--  Descr
--    The unit of measure of distances, as applied to the marker's
--    resolution.

PrtMediaPathMaxSpeedPrintUnitTC ::= INTEGER {
        tenThousandthsOfInchesPerHour(3),
        micrometersPerHour(4),
        charactersPerHour(5),
        linesPerHour(6),
        impressionsPerHour(7),
        sheetsPerHour(8),
        dotRowPerHour(9),
        feetPerHour(16),
        metersPerHour(17)
        }
-- TEXTUAL-CONVENTION
--  Status
--    mandatory
--  Descr
--    The unit of measure used in specifying the speed of all
--    media paths in the printer.

PrtInterpreterTwoWayTC ::= INTEGER {
        yes(3),
        no(4)
        }
-- TEXTUAL-CONVENTION
--  Status
--    mandatory
--  Descr
--    Indicates whether or not this interpreter returns information
--    back to the host.

PrtAlertSeverityLevelTC ::= INTEGER {
        other(1),
        critical(3),
        warning(4),
        warningBinaryChangeEvent(5)
        }
-- TEXTUAL-CONVENTION
--  Status
--    mandatory
--  Descr
--    The level of severity of this alert table entry.  The printer
--    determines the severity level assigned to each entry in the
--    table. A critical alert is binary by nature and definition. A
--    warning is defined to be a non-critical alert. The original and
--    most common warning is unary. The binary warning was added later
--    and given a more distinguished name.

prtGeneralTable OBJECT-TYPE
    SYNTAX SEQUENCE OF PrtGeneralEntry
    ACCESS not-accessible
    STATUS mandatory
    DESCRIPTION
        "A table of general information per printer.
        Objects in this table are defined in various
        places in the MIB, nearby the groups to
        which they apply.  They are all defined
        here to minimize the number of tables that would
        otherwise need to exist."
    ::= { prtGeneral 1 }

prtGeneralEntry OBJECT-TYPE
    SYNTAX PrtGeneralEntry
    ACCESS not-accessible
    STATUS mandatory
    DESCRIPTION
        "An entry exists in this table for each device entry in the
        host resources MIB device table with a device type of
        'printer'.
        
        NOTE: The above description has been modified from RFC 1759
        for clarification."
    INDEX { hrDeviceIndex }
    ::= { prtGeneralTable 1 }

PrtGeneralEntry ::= SEQUENCE {
    prtGeneralConfigChanges Counter,
    prtGeneralCurrentLocalization INTEGER,
    prtGeneralReset PrtGeneralResetTC,
    prtGeneralCurrentOperator OCTET STRING,
    prtGeneralServicePerson OCTET STRING,
    prtInputDefaultIndex INTEGER,
    prtOutputDefaultIndex INTEGER,
    prtMarkerDefaultIndex INTEGER,
    prtMediaPathDefaultIndex INTEGER,
    prtConsoleLocalization INTEGER,
    prtConsoleNumberOfDisplayLines INTEGER,
    prtConsoleNumberOfDisplayChars INTEGER,
    prtConsoleDisable PrtConsoleDisableTC,
    prtAuxiliarySheetStartupPage PresentOnOff,
    prtAuxiliarySheetBannerPage PresentOnOff,
    prtGeneralPrinterName OCTET STRING,
    prtGeneralSerialNumber OCTET STRING,
    prtAlertCriticalEvents Counter,
    prtAlertAllEvents Counter
    }

prtGeneralConfigChanges OBJECT-TYPE
    SYNTAX Counter
    ACCESS read-only
    STATUS mandatory
    DESCRIPTION
        "Counts configuration changes within the printer. A
        configuration change is defined to be an action that results in
        a change to any MIB object other than those that reflect status
        or level, or those that act as counters or gauges. In addition,
        any action that results in a row being added or deleted from
        any table in the Printer MIB is considered a configuration
        change. Such changes will often affect the capability of the
        printer to service certain types of print jobs. Management
        applications may cache infrequently changed configuration
        information about sub units within the printer. This object
        should be incremented whenever the agent wishes to notify
        management applications that any cached configuration
        information for this device is to be considered 'stale'. At
        this point, the management application should flush any
        configuration information cached about this device and fetch
        
        new configuration information.
        
        The following are examples of actions that would cause the
        prtGeneralConfigChanges object to be incremented:
        
        - Adding an output bin
        - Changing the media in a sensing input tray
        - Changing the value of prtInputMediaType
        
        Note that the prtGeneralConfigChanges counter would not be
        incremented when an input tray is temporarily removed to load
        additional paper or when the level of an input device changes.
        
        NOTE: The above description has been modified from RFC 1759
        for clarification."
    ::= { prtGeneralEntry 1 }

prtGeneralCurrentLocalization OBJECT-TYPE
    SYNTAX INTEGER(1..65535)
    ACCESS read-write
    STATUS mandatory
    DESCRIPTION
        "The value of the prtLocalizationIndex corresponding to the
        current language, country, and character set to be used for
        localized string values that are identified as being dependent
        on the value of this object.  Note that this object does not
        apply to localized strings in the prtConsole group or to any
        object that is not explicitly identified as being localized
        according to prtGeneralCurrentLocalization.  When an object's
        'charset' is controlled by the value of
        prtGeneralCurrentLocalization, it MUST specify
        PrtLocalizedDescriptionStringTC as its syntax.
        
        NOTE: The above description has been modified from RFC 1759
        for clarification."
    ::= { prtGeneralEntry 2 }

prtGeneralReset OBJECT-TYPE
    SYNTAX PrtGeneralResetTC
--    Rsyntax INTEGER {
--        notResetting(3),
--        powerCycleReset(4),
--        resetToNVRAM(5),
--        resetToFactoryDefaults(6)
--        }
    ACCESS read-write
    STATUS mandatory
    DESCRIPTION
        "Setting this value to 'powerCycleReset', 'resetToNVRAM', or
        'resetToFactoryDefaults' will result in the resetting of the
        printer.  When read, this object will always have the value
        
        'notResetting(3)', and a SET of the value 'notResetting' shall
        have no effect on the printer.  Some of the defined values are
        optional.  However, every implementation must support at least
        the values 'notResetting' and 'resetToNVRAM'."
    ::= { prtGeneralEntry 3 }

prtGeneralCurrentOperator OBJECT-TYPE
    SYNTAX OCTET STRING(SIZE(0..127))
    ACCESS read-write
    STATUS mandatory
    DESCRIPTION
        "The name of the person who is responsible for operating
        this printer.  It is suggested that this string include
        information that would enable other humans to reach the
        operator, such as a phone number.  As a convention to
        facilitate automatic notification of the operator by the
        agent or network management station, the phone number,
        fax number or email address should be indicated by the
        URL schemes 'tel:', 'fax:' and 'mailto:', respectively.
        If either the phone, fax, or email information is not
        available, then a line should not be included for this
        information.
        
        NOTE: For interoperability purposes, it is advisable to
        use email addresses formatted according to [RFC2822]
        requirements.
        
        NOTE: The above description has been modified from RFC 1759
        for clarification."
    ::= { prtGeneralEntry 4 }

prtGeneralServicePerson OBJECT-TYPE
    SYNTAX OCTET STRING(SIZE(0..127))
    ACCESS read-write
    STATUS mandatory
    DESCRIPTION
        "The name of the person responsible for servicing this
        printer.  It is suggested that this string include
        information that would enable other humans to reach the
        service person, such as a phone number.  As a convention
        to facilitate automatic notification of the operator by
        the agent or network management station, the phone
        number, fax number or email address should be indicated
        by the URL schemes 'tel:', 'fax:' and 'mailto:',
        respectively.  If either the phone, fax, or email
        information is not available, then a line should not
        
        be included for this information.
        
        NOTE: For interoperability purposes, it is advisable to use
        email addresses formatted per [RFC2822] requirements.
        
        NOTE: The above description has been modified from RFC 1759
        for clarification."
    ::= { prtGeneralEntry 5 }

prtInputDefaultIndex OBJECT-TYPE
    SYNTAX INTEGER(1..65535)
    ACCESS read-write
    STATUS mandatory
    DESCRIPTION
        "The value of prtInputIndex corresponding to the default input
        sub-unit: that is, this object selects the default source of
        input media."
    ::= { prtGeneralEntry 6 }

prtOutputDefaultIndex OBJECT-TYPE
    SYNTAX INTEGER(1..65535)
    ACCESS read-write
    STATUS mandatory
    DESCRIPTION
        "The value of prtOutputIndex corresponding to the default
        output sub-unit; that is, this object selects the default
        output destination."
    ::= { prtGeneralEntry 7 }

prtMarkerDefaultIndex OBJECT-TYPE
    SYNTAX INTEGER(1..65535)
    ACCESS read-write
    STATUS mandatory
    DESCRIPTION
        "The value of prtMarkerIndex corresponding to the
        default marker sub-unit; that is, this object selects the
        default marker."
    ::= { prtGeneralEntry 8 }

prtMediaPathDefaultIndex OBJECT-TYPE
    SYNTAX INTEGER(1..65535)
    ACCESS read-write
    STATUS mandatory
    DESCRIPTION
        "The value of prtMediaPathIndex corresponding to
        the default media path; that is, the selection of the
        default media path."
    ::= { prtGeneralEntry 9 }

prtConsoleLocalization OBJECT-TYPE
    SYNTAX INTEGER(1..65535)
    ACCESS read-write
    STATUS mandatory
    DESCRIPTION
        "The value of the prtLocalizationIndex corresponding to
        the language, country, and character set to be used for the
        console.  This localization applies both to the actual display
        on the console as well as the encoding of these console objects
        in management operations.  When an object's 'charset' is
        controlled by the value of prtConsoleLocalization, it MUST
        specify PrtConsoleDescriptionStringTC as its syntax.
        
        NOTE: The above description has been modified from RFC 1759
        for clarification."
    ::= { prtGeneralEntry 10 }

prtConsoleNumberOfDisplayLines OBJECT-TYPE
    SYNTAX INTEGER(0..65535)
    ACCESS read-only
    STATUS mandatory
    DESCRIPTION
        "The number of lines on the printer's physical
        display.  This value is 0 if there are no lines on the
        physical display or if there is no physical display"
    ::= { prtGeneralEntry 11 }

prtConsoleNumberOfDisplayChars OBJECT-TYPE
    SYNTAX INTEGER(0..65535)
    ACCESS read-only
    STATUS mandatory
    DESCRIPTION
        "The number of characters per line displayed on the physical
        
        display.  This value is 0 if there are no lines on the physical
        display or if there is no physical display"
    ::= { prtGeneralEntry 12 }

prtConsoleDisable OBJECT-TYPE
    SYNTAX PrtConsoleDisableTC
--    Rsyntax INTEGER {
--        enabled(3),
--        disabled(4)
--        }
    ACCESS read-write
    STATUS mandatory
    DESCRIPTION
        "This value indicates how input is (or is not) accepted from
        the operator console.
        
        NOTE: The above description has been modified from RFC 1759
        for clarification."
    ::= { prtGeneralEntry 13 }

prtAuxiliarySheetStartupPage OBJECT-TYPE
    SYNTAX PresentOnOff
--    Rsyntax INTEGER {
--        other(1),
--        on(3),
--        off(4),
--        notPresent(5)
--        }
    ACCESS read-write
    STATUS mandatory
    DESCRIPTION
        "Used to enable or disable printing a startup page.  If enabled,
        a startup page will be printed shortly after power-up, when the
        device is ready.  Typical startup pages include test patterns
        and/or printer configuration information."
    ::= { prtGeneralEntry 14 }

prtAuxiliarySheetBannerPage OBJECT-TYPE
    SYNTAX PresentOnOff
--    Rsyntax INTEGER {
--        other(1),
--        on(3),
--        off(4),
--        notPresent(5)
--        }
    ACCESS read-write
    STATUS mandatory
    DESCRIPTION
        "Used to enable or disable printing banner pages at the
        beginning of jobs.  This is a master switch which applies to all
        jobs, regardless of interpreter."
    ::= { prtGeneralEntry 15 }

prtGeneralPrinterName OBJECT-TYPE
    SYNTAX OCTET STRING(SIZE(0..127))
    ACCESS read-write
    STATUS mandatory
    DESCRIPTION
        "An administrator-specified name for this printer.  Depending
        upon implementation of this printer, the value of this object
        may or may not be same as the value for the MIB-II 'SysName'
        object."
    ::= { prtGeneralEntry 16 }

prtGeneralSerialNumber OBJECT-TYPE
    SYNTAX OCTET STRING(SIZE(0..255))
    ACCESS read-write
    STATUS mandatory
    DESCRIPTION
        "A recorded serial number for this device that indexes some
        type device catalog or inventory.  This value is usually set by
        the device manufacturer but the MIB supports the option of
        writing for this object for site-specific administration of
        device inventory or tracking."
    ::= { prtGeneralEntry 17 }

prtAlertCriticalEvents OBJECT-TYPE
    SYNTAX Counter
    ACCESS read-only
    STATUS mandatory
    DESCRIPTION
        "A running counter of the number of critical alert events that
        have been recorded in the alert table.  The value of this object
        is RESET in the event of a power cycle operation (i.e., the
        value is not persistent."
    ::= { prtGeneralEntry 18 }

prtAlertAllEvents OBJECT-TYPE
    SYNTAX Counter
    ACCESS read-only
    STATUS mandatory
    DESCRIPTION
        "A running counter of the total number of alert event entries
        (critical and non-critical) that have been recorded in the
        alert table"
    ::= { prtGeneralEntry 19 }

prtCoverTable OBJECT-TYPE
    SYNTAX SEQUENCE OF PrtCoverEntry
    ACCESS not-accessible
    STATUS mandatory
    DESCRIPTION
        "A table of the covers and interlocks of the printer."
    ::= { prtCover 1 }

prtCoverEntry OBJECT-TYPE
    SYNTAX PrtCoverEntry
    ACCESS not-accessible
    STATUS mandatory
    DESCRIPTION
        "Information about a cover or interlock.
        Entries may exist in the table for each device
        index with a device type of 'printer'.
        
        NOTE: The above description has been modified from RFC 1759
        for clarification."
    INDEX { hrDeviceIndex, prtCoverIndex }
    ::= { prtCoverTable 1 }

PrtCoverEntry ::= SEQUENCE {
    prtCoverIndex INTEGER,
    prtCoverDescription PrtLocalizedDescriptionStringTC,
    prtCoverStatus PrtCoverStatusTC
    }

prtCoverIndex OBJECT-TYPE
    SYNTAX INTEGER(1..65535)
    ACCESS not-accessible
    STATUS mandatory
    DESCRIPTION
        "A unique value used by the printer to identify this Cover sub
        
        unit.  Although these values may change due to a major
        reconfiguration of the device (e.g., the addition of new cover
        sub-units to the printer), values SHOULD remain stable across
        successive printer power cycles.
        
        NOTE: The above description has been modified from RFC 1759
        for clarification."
    ::= { prtCoverEntry 1 }

prtCoverDescription OBJECT-TYPE
    SYNTAX PrtLocalizedDescriptionStringTC
--    Rsyntax OCTET STRING(SIZE(0..255))
    ACCESS read-only
    STATUS mandatory
    DESCRIPTION
        "The manufacturer provided cover sub-mechanism name in the
        localization specified by prtGeneralCurrentLocalization."
    ::= { prtCoverEntry 2 }

prtCoverStatus OBJECT-TYPE
    SYNTAX PrtCoverStatusTC
--    Rsyntax INTEGER {
--        other(1),
--        unknown(2),
--        coverOpen(3),
--        coverClosed(4),
--        interlockOpen(5),
--        interlockClosed(6)
--        }
    ACCESS read-only
    STATUS mandatory
    DESCRIPTION
        "The status of this cover sub-unit."
    ::= { prtCoverEntry 3 }

prtLocalizationTable OBJECT-TYPE
    SYNTAX SEQUENCE OF PrtLocalizationEntry
    ACCESS not-accessible
    STATUS mandatory
    DESCRIPTION
        "The available localizations in this printer."
    ::= { prtLocalization 1 }

prtLocalizationEntry OBJECT-TYPE
    SYNTAX PrtLocalizationEntry
    ACCESS not-accessible
    STATUS mandatory
    DESCRIPTION
        "A description of a localization.
        Entries may exist in the table for each device
        index with a device type of 'printer'.
        
        NOTE: The above description has been modified from RFC 1759
        for clarification."
    INDEX { hrDeviceIndex, prtLocalizationIndex }
    ::= { prtLocalizationTable 1 }

PrtLocalizationEntry ::= SEQUENCE {
    prtLocalizationIndex INTEGER,
    prtLocalizationLanguage OCTET STRING,
    prtLocalizationCountry OCTET STRING,
    prtLocalizationCharacterSet IANACharset
    }

prtLocalizationIndex OBJECT-TYPE
    SYNTAX INTEGER(1..65535)
    ACCESS not-accessible
    STATUS mandatory
    DESCRIPTION
        "A unique value used by the printer to identify this
        localization entry.  Although these values may change due to a
        major reconfiguration of the device (e.g., the addition of new
        localization data to the printer), values SHOULD remain
        stable across successive printer power cycles.
        
        NOTE: The above description has been modified from RFC 1759
        for clarification."
    ::= { prtLocalizationEntry 1 }

prtLocalizationLanguage OBJECT-TYPE
    SYNTAX OCTET STRING(SIZE(2))
    ACCESS read-only
    STATUS mandatory
    DESCRIPTION
        "A two character language code from ISO 639.  Examples en,
        es, fr, de.  NOTE: These examples were shown as upper case in
        RFC 1759 and are now shown as lower case to agree with ISO 639."
    ::= { prtLocalizationEntry 2 }

prtLocalizationCountry OBJECT-TYPE
    SYNTAX OCTET STRING(SIZE(2))
    ACCESS read-only
    STATUS mandatory
    DESCRIPTION
        "A two character country code from ISO 3166, a blank string
        (two space characters) shall indicate that the country is not
        defined.  Examples: US, GB, FR, DE, ..."
    ::= { prtLocalizationEntry 3 }

prtLocalizationCharacterSet OBJECT-TYPE
    SYNTAX IANACharset
--    Rsyntax INTEGER {
--        other(1),
--        unknown(2),
--        csASCII(3),
--        csISOLatin1(4),
--        csISOLatin2(5),
--        csISOLatin3(6),
--        csISOLatin4(7),
--        csISOLatinCyrillic(8),
--        csISOLatinArabic(9),
--        csISOLatinGreek(10),
--        csISOLatinHebrew(11),
--        csISOLatin5(12),
--        csISOLatin6(13),
--        csISOTextComm(14),
--        csHalfWidthKatakana(15),
--        csJISEncoding(16),
--        csShiftJIS(17),
--        csEUCPkdFmtJapanese(18),
--        csEUCFixWidJapanese(19),
--        csISO4UnitedKingdom(20),
--        csISO11SwedishForNames(21),
--        csISO15Italian(22),
--        csISO17Spanish(23),
--        csISO21German(24),
--        csISO60DanishNorwegian(25),
--        csISO69French(26),
--        csISO10646UTF1(27),
--        csISO646basic1983(28),
--        csINVARIANT(29),
--        csISO2IntlRefVersion(30),
--        csNATSSEFI(31),
--        csNATSSEFIADD(32),
--        csNATSDANO(33),
--        csNATSDANOADD(34),
--        csISO10Swedish(35),
--        csKSC56011987(36),
--        csISO2022KR(37),
--        csEUCKR(38),
--        csISO2022JP(39),
--        csISO2022JP2(40),
--        csISO13JISC6220jp(41),
--        csISO14JISC6220ro(42),
--        csISO16Portuguese(43),
--        csISO18Greek7Old(44),
--        csISO19LatinGreek(45),
--        csISO25French(46),
--        csISO27LatinGreek1(47),
--        csISO5427Cyrillic(48),
--        csISO42JISC62261978(49),
--        csISO47BSViewdata(50),
--        csISO49INIS(51),
--        csISO50INIS8(52),
--        csISO51INISCyrillic(53),
--        csISO54271981(54),
--        csISO5428Greek(55),
--        csISO57GB1988(56),
--        csISO58GB231280(57),
--        csISO61Norwegian2(58),
--        csISO70VideotexSupp1(59),
--        csISO84Portuguese2(60),
--        csISO85Spanish2(61),
--        csISO86Hungarian(62),
--        csISO87JISX0208(63),
--        csISO88Greek7(64),
--        csISO89ASMO449(65),
--        csISO90(66),
--        csISO91JISC62291984a(67),
--        csISO92JISC62991984b(68),
--        csISO93JIS62291984badd(69),
--        csISO94JIS62291984hand(70),
--        csISO95JIS62291984handadd(71),
--        csISO96JISC62291984kana(72),
--        csISO2033(73),
--        csISO99NAPLPS(74),
--        csISO102T617bit(75),
--        csISO103T618bit(76),
--        csISO111ECMACyrillic(77),
--        csa71(78),
--        csa72(79),
--        csISO123CSAZ24341985gr(80),
--        csISO88596E(81),
--        csISO88596I(82),
--        csISO128T101G2(83),
--        csISO88598E(84),
--        csISO88598I(85),
--        csISO139CSN369103(86),
--        csISO141JUSIB1002(87),
--        csISO143IECP271(88),
--        csISO146Serbian(89),
--        csISO147Macedonian(90),
--        csISO150(91),
--        csISO151Cuba(92),
--        csISO6937Add(93),
--        csISO153GOST1976874(94),
--        csISO8859Supp(95),
--        csISO10367Box(96),
--        csISO158Lap(97),
--        csISO159JISX02121990(98),
--        csISO646Danish(99),
--        csUSDK(100),
--        csDKUS(101),
--        csKSC5636(102),
--        csUnicode11UTF7(103),
--        csISO2022CN(104),
--        csISO2022CNEXT(105),
--        csUTF8(106),
--        csISO885913(109),
--        csISO885914(110),
--        csISO885915(111),
--        csISO885916(112),
--        csGBK(113),
--        csGB18030(114),
--        csOSDEBCDICDF0415(115),
--        csOSDEBCDICDF03IRV(116),
--        csOSDEBCDICDF041(117),
--        csUnicode(1000),
--        csUCS4(1001),
--        csUnicodeASCII(1002),
--        csUnicodeLatin1(1003),
--        csUnicodeIBM1261(1005),
--        csUnicodeIBM1268(1006),
--        csUnicodeIBM1276(1007),
--        csUnicodeIBM1264(1008),
--        csUnicodeIBM1265(1009),
--        csUnicode11(1010),
--        csSCSU(1011),
--        csUTF7(1012),
--        csUTF16BE(1013),
--        csUTF16LE(1014),
--        csUTF16(1015),
--        csCESU8(1016),
--        csUTF32(1017),
--        csUTF32BE(1018),
--        csUTF32LE(1019),
--        csBOCU1(1020),
--        csWindows30Latin1(2000),
--        csWindows31Latin1(2001),
--        csWindows31Latin2(2002),
--        csWindows31Latin5(2003),
--        csHPRoman8(2004),
--        csAdobeStandardEncoding(2005),
--        csVenturaUS(2006),
--        csVenturaInternational(2007),
--        csDECMCS(2008),
--        csPC850Multilingual(2009),
--        csPCp852(2010),
--        csPC8CodePage437(2011),
--        csPC8DanishNorwegian(2012),
--        csPC862LatinHebrew(2013),
--        csPC8Turkish(2014),
--        csIBMSymbols(2015),
--        csIBMThai(2016),
--        csHPLegal(2017),
--        csHPPiFont(2018),
--        csHPMath8(2019),
--        csHPPSMath(2020),
--        csHPDesktop(2021),
--        csVenturaMath(2022),
--        csMicrosoftPublishing(2023),
--        csWindows31J(2024),
--        csGB2312(2025),
--        csBig5(2026),
--        csMacintosh(2027),
--        csIBM037(2028),
--        csIBM038(2029),
--        csIBM273(2030),
--        csIBM274(2031),
--        csIBM275(2032),
--        csIBM277(2033),
--        csIBM278(2034),
--        csIBM280(2035),
--        csIBM281(2036),
--        csIBM284(2037),
--        csIBM285(2038),
--        csIBM290(2039),
--        csIBM297(2040),
--        csIBM420(2041),
--        csIBM423(2042),
--        csIBM424(2043),
--        csIBM500(2044),
--        csIBM851(2045),
--        csIBM855(2046),
--        csIBM857(2047),
--        csIBM860(2048),
--        csIBM861(2049),
--        csIBM863(2050),
--        csIBM864(2051),
--        csIBM865(2052),
--        csIBM868(2053),
--        csIBM869(2054),
--        csIBM870(2055),
--        csIBM871(2056),
--        csIBM880(2057),
--        csIBM891(2058),
--        csIBM903(2059),
--        csIBBM904(2060),
--        csIBM905(2061),
--        csIBM918(2062),
--        csIBM1026(2063),
--        csIBMEBCDICATDE(2064),
--        csEBCDICATDEA(2065),
--        csEBCDICCAFR(2066),
--        csEBCDICDKNO(2067),
--        csEBCDICDKNOA(2068),
--        csEBCDICFISE(2069),
--        csEBCDICFISEA(2070),
--        csEBCDICFR(2071),
--        csEBCDICIT(2072),
--        csEBCDICPT(2073),
--        csEBCDICES(2074),
--        csEBCDICESA(2075),
--        csEBCDICESS(2076),
--        csEBCDICUK(2077),
--        csEBCDICUS(2078),
--        csUnknown8BiT(2079),
--        csMnemonic(2080),
--        csMnem(2081),
--        csVISCII(2082),
--        csVIQR(2083),
--        csKOI8R(2084),
--        csHZGB2312(2085),
--        csIBM866(2086),
--        csPC775Baltic(2087),
--        csKOI8U(2088),
--        csIBM00858(2089),
--        csIBM00924(2090),
--        csIBM01140(2091),
--        csIBM01141(2092),
--        csIBM01142(2093),
--        csIBM01143(2094),
--        csIBM01144(2095),
--        csIBM01145(2096),
--        csIBM01146(2097),
--        csIBM01147(2098),
--        csIBM01148(2099),
--        csIBM01149(2100),
--        csBig5HKSCS(2101),
--        csIBM1047(2102),
--        csPTCP154(2103),
--        csAmiga1251(2104),
--        csKOI7switched(2105),
--        cswindows1250(2250),
--        cswindows1251(2251),
--        cswindows1252(2252),
--        cswindows1253(2253),
--        cswindows1254(2254),
--        cswindows1255(2255),
--        cswindows1256(2256),
--        cswindows1257(2257),
--        cswindows1258(2258),
--        csTIS620(2259),
--        reserved(3000)
--        }
    ACCESS read-only
    STATUS mandatory
    DESCRIPTION
        "The coded character set used for this localization."
    ::= { prtLocalizationEntry 4 }

prtStorageRefTable OBJECT-TYPE
    SYNTAX SEQUENCE OF PrtStorageRefEntry
    ACCESS not-accessible
    STATUS mandatory
    DESCRIPTION
        "This table defines which printer, amongst multiple printers
        serviced by one agent, owns which storage units.
        
        NOTE: The above description has been modified from RFC 1759
        for clarification."
    ::= { prtGeneral 2 }

prtStorageRefEntry OBJECT-TYPE
    SYNTAX PrtStorageRefEntry
    ACCESS not-accessible
    STATUS mandatory
    DESCRIPTION
        "This table will have an entry for each entry in the Host
        Resources MIB storage table that represents storage associated
        with a printer managed by this agent.
        
        NOTE: The above description has been modified from RFC 1759
        for clarification."
    INDEX { hrStorageIndex, prtStorageRefSeqNumber }
    ::= { prtStorageRefTable 1 }

PrtStorageRefEntry ::= SEQUENCE {
    prtStorageRefSeqNumber INTEGER,
    prtStorageRefIndex INTEGER
    }

prtStorageRefSeqNumber OBJECT-TYPE
    SYNTAX INTEGER(1..65535)
    ACCESS not-accessible
    STATUS mandatory
    DESCRIPTION
        "This value will be unique amongst all entries with a common
        value of hrStorageIndex. This object allows a storage entry to
        point to the multiple printer devices with which it is
        associated."
    ::= { prtStorageRefEntry 1 }

prtStorageRefIndex OBJECT-TYPE
    SYNTAX INTEGER(0..2147483647)
    ACCESS read-only
    STATUS mandatory
    DESCRIPTION
        "The value of the hrDeviceIndex of the printer device that this
        storageEntry is associated with."
    ::= { prtStorageRefEntry 2 }

prtDeviceRefTable OBJECT-TYPE
    SYNTAX SEQUENCE OF PrtDeviceRefEntry
    ACCESS not-accessible
    STATUS mandatory
    DESCRIPTION
        "This table defines which printer, amongst multiple printers
        serviced by one agent, is associated with which devices.
        
        NOTE: The above description has been modified from RFC 1759
        
        for clarification."
    ::= { prtGeneral 3 }

prtDeviceRefEntry OBJECT-TYPE
    SYNTAX PrtDeviceRefEntry
    ACCESS not-accessible
    STATUS mandatory
    DESCRIPTION
        "This table will have an entry for each entry in the Host
        Resources MIB device table that represents a device associated
        with a printer managed by this agent.
        
        NOTE: The above description has been modified from RFC 1759
        for clarification."
    INDEX { hrDeviceIndex, prtDeviceRefSeqNumber }
    ::= { prtDeviceRefTable 1 }

PrtDeviceRefEntry ::= SEQUENCE {
    prtDeviceRefSeqNumber INTEGER,
    prtDeviceRefIndex INTEGER
    }

prtDeviceRefSeqNumber OBJECT-TYPE
    SYNTAX INTEGER(1..65535)
    ACCESS not-accessible
    STATUS mandatory
    DESCRIPTION
        "This value will be unique amongst all entries with a common
        value of hrDeviceIndex. This object allows a device entry to
        point to the multiple printer devices with which it is
        associated."
    ::= { prtDeviceRefEntry 1 }

prtDeviceRefIndex OBJECT-TYPE
    SYNTAX INTEGER(0..2147483647)
    ACCESS read-only
    STATUS mandatory
    DESCRIPTION
        "The value of the hrDeviceIndex of the printer device that this
        deviceEntry is associated with."
    ::= { prtDeviceRefEntry 2 }

prtInputTable OBJECT-TYPE
    SYNTAX SEQUENCE OF PrtInputEntry
    ACCESS not-accessible
    STATUS mandatory
    DESCRIPTION
        "A table of the devices capable of providing media for input to
        the printing process."
    ::= { prtInput 2 }

prtInputEntry OBJECT-TYPE
    SYNTAX PrtInputEntry
    ACCESS not-accessible
    STATUS mandatory
    DESCRIPTION
        "Attributes of a device capable of providing media for input to
        the printing process.  Entries may exist in the table for each
        device index with a device type of 'printer'.
        
        NOTE: The above description has been modified from RFC 1759
        for clarification."
    INDEX { hrDeviceIndex, prtInputIndex }
    ::= { prtInputTable 1 }

PrtInputEntry ::= SEQUENCE {
    prtInputIndex INTEGER,
    prtInputType PrtInputTypeTC,
    prtInputDimUnit PrtMediaUnitTC,
    prtInputMediaDimFeedDirDeclared INTEGER,
    prtInputMediaDimXFeedDirDeclared INTEGER,
    prtInputMediaDimFeedDirChosen INTEGER,
    prtInputMediaDimXFeedDirChosen INTEGER,
    prtInputCapacityUnit PrtCapacityUnitTC,
    prtInputMaxCapacity INTEGER,
    prtInputCurrentLevel INTEGER,
    prtInputStatus PrtSubUnitStatusTC,
    prtInputMediaName OCTET STRING,
    prtInputName OCTET STRING,
    prtInputVendorName OCTET STRING,
    prtInputModel OCTET STRING,
    prtInputVersion OCTET STRING,
    prtInputSerialNumber OCTET STRING,
    prtInputDescription PrtLocalizedDescriptionStringTC,
    prtInputSecurity PresentOnOff,
    prtInputMediaWeight INTEGER,
    prtInputMediaType OCTET STRING,
    prtInputMediaColor OCTET STRING,
    prtInputMediaFormParts INTEGER,
    prtInputMediaLoadTimeout INTEGER,
    prtInputNextIndex INTEGER
    }

prtInputIndex OBJECT-TYPE
    SYNTAX INTEGER(1..65535)
    ACCESS not-accessible
    STATUS mandatory
    DESCRIPTION
        "A unique value used by the printer to identify this input
        sub-unit.  Although these values may change due to a major
        reconfiguration of the device (e.g., the addition of new input
        sub-units to the printer), values SHOULD remain stable across
        successive printer power cycles.
        
        NOTE: The above description has been modified from RFC 1759
        for clarification."
    ::= { prtInputEntry 1 }

prtInputType OBJECT-TYPE
    SYNTAX PrtInputTypeTC
--    Rsyntax INTEGER {
--        other(1),
--        unknown(2),
--        sheetFeedAutoRemovableTray(3),
--        sheetFeedAutoNonRemovableTray(4),
--        sheetFeedManual(5),
--        continuousRoll(6),
--        continuousFanFold(7)
--        }
    ACCESS read-only
    STATUS mandatory
    DESCRIPTION
        "The type of technology (discriminated primarily according to
        feeder mechanism type) employed by the input sub-unit.  Note,
        the Input Class provides for a descriptor field to further
        qualify the other choice."
    ::= { prtInputEntry 2 }

prtInputDimUnit OBJECT-TYPE
    SYNTAX PrtMediaUnitTC
--    Rsyntax INTEGER {
--        tenThousandthsOfInches(3),
--        micrometers(4)
--        }
    ACCESS read-only
    STATUS mandatory
    DESCRIPTION
        "The unit of measurement for use calculating and relaying
         dimensional values for this input sub-unit."
    ::= { prtInputEntry 3 }

prtInputMediaDimFeedDirDeclared OBJECT-TYPE
    SYNTAX INTEGER(-2..2147483647)
    ACCESS read-write
    STATUS mandatory
    DESCRIPTION
        "This object provides the value of the declared dimension, in
        the feed direction, of the media that is (or, if empty, was or
        will be) in this input sub-unit.  The feed direction is the
        direction in which the media is fed on this sub-unit.  This
        dimension is measured in input sub-unit dimensional units
        (controlled by prtInputDimUnit, which uses PrtMediaUnitTC).  If
        this input sub-unit can reliably sense this value, the value is
        sensed by the printer and may not be changed by management
        requests.  Otherwise, the value may be changed.  The value (-1)
        means other and specifically means that this sub-unit places no
        restriction on this parameter.  The value (-2) indicates
        unknown."
    ::= { prtInputEntry 4 }

prtInputMediaDimXFeedDirDeclared OBJECT-TYPE
    SYNTAX INTEGER(-2..2147483647)
    ACCESS read-write
    STATUS mandatory
    DESCRIPTION
        "This object provides the value of the declared dimension, in
        the cross feed direction, of the media that is (or, if empty,
        was or will be) in this input sub-unit.  The cross  feed
        direction is ninety degrees relative to the feed direction
        associated with this sub-unit.  This dimension is measured in
        input sub-unit dimensional units (controlled by
        prtInputDimUnit,which uses PrtMediaUnitTC).  If this input sub-
        unit can reliably sense this value, the value is sensed by the
        printer and may not be changed by management requests.
        Otherwise, the value may be changed.  The value (-1) means other
        and specifically means that this sub-unit places no restriction
        on this parameter.  The value (-2) indicates unknown."
    ::= { prtInputEntry 5 }

prtInputMediaDimFeedDirChosen OBJECT-TYPE
    SYNTAX INTEGER(-2..2147483647)
    ACCESS read-only
    STATUS mandatory
    DESCRIPTION
        "The printer will act as if media of the chosen dimension (in
        the feed direction) is present in this input source.  Note that
        this value will be used even if the input tray is empty.  Feed
        dimension measurements are taken relative to the feed direction
        associated with that sub-unit and are in input sub-unit
        dimensional units (controlled by prtInputDimUnit, which uses
        PrtMediaUnitTC).  If the printer supports the declared
        dimension,the granted dimension is the same as the declared
        dimension.  If not, the granted dimension is set to the closest
        dimension that the printer supports when the declared dimension
        is set.  The value (-1) means other and specifically indicates
        that this sub-unit places no restriction on this parameter.  The
        value (-2)indicates unknown."
    ::= { prtInputEntry 6 }

prtInputMediaDimXFeedDirChosen OBJECT-TYPE
    SYNTAX INTEGER(-2..2147483647)
    ACCESS read-only
    STATUS mandatory
    DESCRIPTION
        "The printer will act as if media of the chosen dimension (in
        the cross feed direction) is present in this input source.  Note
        that this value will be used even if the input tray is empty.
        The cross feed direction is ninety degrees relative to the feed
        direction associated with this sub-unit.  This dimension is
        measured in input sub-unit dimensional units (controlled by
        prtInputDimUnit, which uses PrtMediaUnitTC).  If the printer
        supports the declare dimension, the granted dimension is the
        same as the declared dimension.  If not, the granted dimension
        is set to the closest dimension that the printer supports when
        the declared dimension is set.  The value (-1) means other and
        specifically indicates that this sub-unit places no restriction
        on this parameter.  The value (-2) indicates unknown."
    ::= { prtInputEntry 7 }

prtInputCapacityUnit OBJECT-TYPE
    SYNTAX PrtCapacityUnitTC
--    Rsyntax INTEGER {
--        other(1),
--        unknown(2),
--        tenThousandthsOfInches(3),
--        micrometers(4),
--        sheets(8),
--        feet(16),
--        meters(17),
--        items(18),
--        percent(19)
--        }
    ACCESS read-only
    STATUS mandatory
    DESCRIPTION
        "The unit of measurement for use in calculating and relaying
        capacity values for this input sub-unit."
    ::= { prtInputEntry 8 }

prtInputMaxCapacity OBJECT-TYPE
    SYNTAX INTEGER(-2..2147483647)
    ACCESS read-write
    STATUS mandatory
    DESCRIPTION
        "The maximum capacity of the input sub-unit in input sub-unit
        capacity units (PrtCapacityUnitTC).  There is no convention
        associated with the media itself so this value reflects claimed
        capacity.  If this input sub-unit can reliably sense this value,
        the value is sensed by the printer and may not be changed by
        management requests; otherwise, the value may be written (by a
        Remote Control Panel or a Management Application). The value
        (-1) means other and specifically indicates that the sub-unit
        places no restrictions on this parameter.  The value (-2) means
        unknown."
    ::= { prtInputEntry 9 }

prtInputCurrentLevel OBJECT-TYPE
    SYNTAX INTEGER(-3..2147483647)
    ACCESS read-write
    STATUS mandatory
    DESCRIPTION
        "The current capacity of the input sub-unit in input sub-unit
        capacity units (PrtCapacityUnitTC).  If this input sub-unit can
        reliably sense this value, the value is sensed by the printer
        and may not be changed by management requests; otherwise, the
        value may be written (by a Remote Control Panel or a Management
        Application).  The value (-1) means other and specifically
        indicates that the sub-unit places no restrictions on this
        parameter.  The value (-2) means unknown.  The value (-3) means
        that the printer knows that at least one unit remains."
    ::= { prtInputEntry 10 }

prtInputStatus OBJECT-TYPE
    SYNTAX PrtSubUnitStatusTC
--    Rsyntax INTEGER(0..126)
    ACCESS read-only
    STATUS mandatory
    DESCRIPTION
        "The current status of this input sub-unit."
    ::= { prtInputEntry 11 }

prtInputMediaName OBJECT-TYPE
    SYNTAX OCTET STRING(SIZE(0..63))
    ACCESS read-write
    STATUS mandatory
    DESCRIPTION
        "A description of the media contained in this input sub-unit;
        This description is to be used by a client to format and
        Localize a string for display to a human operator.  This
        description is not processed by the printer.  It is used to
        provide information not expressible in terms of the other
        media attributes (e.g., prtInputMediaDimFeedDirChosen,
        prtInputMediaDimXFeedDirChosen, prtInputMediaWeight,
        prtInputMediaType)."
    REFERENCE
        "The PWG Standardized Media Names specification [PWGMEDIA]
        contains the recommended values for this object.  See also
        RFC 3805 Appendix C,'Media Names', which lists the values
        Of standardized media names defined in ISO/IEC 10175."
    ::= { prtInputEntry 12 }

prtInputName OBJECT-TYPE
    SYNTAX OCTET STRING(SIZE(0..63))
    ACCESS read-write
    STATUS mandatory
    DESCRIPTION
        "The name assigned to this input sub-unit."
    ::= { prtInputEntry 13 }

prtInputVendorName OBJECT-TYPE
    SYNTAX OCTET STRING(SIZE(0..63))
    ACCESS read-only
    STATUS mandatory
    DESCRIPTION
        "The vendor name of this input sub-unit."
    ::= { prtInputEntry 14 }

prtInputModel OBJECT-TYPE
    SYNTAX OCTET STRING(SIZE(0..63))
    ACCESS read-only
    STATUS mandatory
    DESCRIPTION
        "The model name of this input sub-unit."
    ::= { prtInputEntry 15 }

prtInputVersion OBJECT-TYPE
    SYNTAX OCTET STRING(SIZE(0..63))
    ACCESS read-only
    STATUS mandatory
    DESCRIPTION
        "The version of this input sub-unit."
    ::= { prtInputEntry 16 }

prtInputSerialNumber OBJECT-TYPE
    SYNTAX OCTET STRING(SIZE(0..32))
    ACCESS read-only
    STATUS mandatory
    DESCRIPTION
        "The serial number assigned to this input sub-unit."
    ::= { prtInputEntry 17 }

prtInputDescription OBJECT-TYPE
    SYNTAX PrtLocalizedDescriptionStringTC
--    Rsyntax OCTET STRING(SIZE(0..255))
    ACCESS read-only
    STATUS mandatory
    DESCRIPTION
        "A free-form text description of this input sub-unit in the
        localization specified by  prtGeneralCurrentLocalization."
    ::= { prtInputEntry 18 }

prtInputSecurity OBJECT-TYPE
    SYNTAX PresentOnOff
--    Rsyntax INTEGER {
--        other(1),
--        on(3),
--        off(4),
--        notPresent(5)
--        }
    ACCESS read-write
    STATUS mandatory
    DESCRIPTION
        "Indicates if this input sub-unit has some security associated
        with it."
    ::= { prtInputEntry 19 }

prtInputMediaWeight OBJECT-TYPE
    SYNTAX INTEGER(-2..2147483647)
    ACCESS read-write
    STATUS mandatory
    DESCRIPTION
        "The weight of the medium associated with this input sub-unit
        in grams / per meter squared.  The value (-2) means unknown."
    ::= { prtInputEntry 20 }

prtInputMediaType OBJECT-TYPE
    SYNTAX OCTET STRING(SIZE(0..63))
    ACCESS read-write
    STATUS mandatory
    DESCRIPTION
        "The name of the type of medium associated with this input sub
        unit.  This name need not be processed by the printer; it might
        simply be displayed to an operator.
        
        NOTE: The above description has been modified from RFC 1759."
    REFERENCE
        "The PWG Standardized Media Names specification [PWGMEDIA],
        section 3 Media Type Names, contains the recommended values for
        this object.  Implementers may add additional string values.
        The naming conventions in ISO 9070 are recommended in order to
        avoid potential name clashes."
    ::= { prtInputEntry 21 }

prtInputMediaColor OBJECT-TYPE
    SYNTAX OCTET STRING(SIZE(0..63))
    ACCESS read-write
    STATUS mandatory
    DESCRIPTION
        "The name of the color of the medium associated with
        this input sub-unit using standardized string values.
        
        NOTE: The above description has been modified from RFC 1759."
    REFERENCE
        "The PWG Standardized Media Names specification [PWGMEDIA],
        section 4 Media Color Names, contains the recommended values
        for this object.  Implementers may add additional string values.
        The naming conventions in ISO 9070 are recommended in order to
        avoid potential name clashes."
    ::= { prtInputEntry 22 }

prtInputMediaFormParts OBJECT-TYPE
    SYNTAX INTEGER(-2..2147483647)
    ACCESS read-write
    STATUS mandatory
    DESCRIPTION
        "The number of parts associated with the medium
        associated with this input sub-unit if the medium is a
        multi-part form.  The value (-1) means other and
        specifically indicates that the device places no
        restrictions on this parameter.  The value (-2) means
        unknown."
    ::= { prtInputEntry 23 }

prtInputMediaLoadTimeout OBJECT-TYPE
    SYNTAX INTEGER(-2..2147483647)
    ACCESS read-write
    STATUS mandatory
    DESCRIPTION
        "When the printer is not able to print due to a subunit being
        empty or the requested media must be manually loaded, the
        printer will wait for the duration (in seconds) specified by
        this object.  Upon expiration of the time-out, the printer will
        take the action specified by prtInputNextIndex.
        
        The event which causes the printer to enter the waiting state
        is product specific.  If the printer is not waiting for manually
        fed media, it may switch from an empty subunit to a different
        subunit without waiting for the time-out to expire.
        
        A value of (-1) implies 'other' or 'infinite' which translates
        to 'wait forever'.  The action which causes printing to continue
        is product specific.  A value of (-2) implies 'unknown'."
    ::= { prtInputEntry 24 }

prtInputNextIndex OBJECT-TYPE
    SYNTAX INTEGER(-3..2147483647)
    ACCESS read-write
    STATUS mandatory
    DESCRIPTION
        "The value of prtInputIndex corresponding to the input subunit
        which will be used when this input subunit is emptied and the
        time-out specified by prtInputMediaLoadTimeout expires.  A value
        of zero(0) indicates that auto input switching will not occur
        when this input subunit is emptied.  If the time-out specified
        by prtInputLoadMediaTimeout expires and this value is zero(0),
        the job will be aborted.  A value of (-1) means other.  The
        value (-2)means 'unknown' and specifically indicates that an
        implementation specific method will determine the next input
        subunit to use at the time this subunit is emptied and the time
        out expires.  The value(-3) means input switching is not
        supported for this subunit."
    ::= { prtInputEntry 25 }

prtOutputTable OBJECT-TYPE
    SYNTAX SEQUENCE OF PrtOutputEntry
    ACCESS not-accessible
    STATUS mandatory
    DESCRIPTION
        "A table of the devices capable of receiving media delivered
        from the printing process."
    ::= { prtOutput 2 }

prtOutputEntry OBJECT-TYPE
    SYNTAX PrtOutputEntry
    ACCESS not-accessible
    STATUS mandatory
    DESCRIPTION
        "Attributes of a device capable of receiving media delivered
        from the printing process.  Entries may exist in the table for
        each device index with a device type of 'printer'.
        
        NOTE: The above description has been modified from RFC 1759
        for clarification."
    INDEX { hrDeviceIndex, prtOutputIndex }
    ::= { prtOutputTable 1 }

PrtOutputEntry ::= SEQUENCE {
    prtOutputIndex INTEGER,
    prtOutputType PrtOutputTypeTC,
    prtOutputCapacityUnit PrtCapacityUnitTC,
    prtOutputMaxCapacity INTEGER,
    prtOutputRemainingCapacity INTEGER,
    prtOutputStatus PrtSubUnitStatusTC,
    prtOutputName OCTET STRING,
    prtOutputVendorName OCTET STRING,
    prtOutputModel OCTET STRING,
    prtOutputVersion OCTET STRING,
    prtOutputSerialNumber OCTET STRING,
    prtOutputDescription PrtLocalizedDescriptionStringTC,
    prtOutputSecurity PresentOnOff,
    prtOutputDimUnit PrtMediaUnitTC,
    prtOutputMaxDimFeedDir INTEGER,
    prtOutputMaxDimXFeedDir INTEGER,
    prtOutputMinDimFeedDir INTEGER,
    prtOutputMinDimXFeedDir INTEGER,
    prtOutputStackingOrder PrtOutputStackingOrderTC,
    prtOutputPageDeliveryOrientation PrtOutputPageDeliveryOrientationTC,
    prtOutputBursting PresentOnOff,
    prtOutputDecollating PresentOnOff,
    prtOutputPageCollated PresentOnOff,
    prtOutputOffsetStacking PresentOnOff
    }

prtOutputIndex OBJECT-TYPE
    SYNTAX INTEGER(1..65535)
    ACCESS not-accessible
    STATUS mandatory
    DESCRIPTION
        "A unique value used by this printer to identify this output
        sub-unit.  Although these values may change due to a major
        reconfiguration of the sub-unit (e.g., the addition of new
        output devices to the printer), values SHOULD remain stable
        across successive printer power cycles.
        
        NOTE: The above description has been modified from RFC 1759
        for clarification."
    ::= { prtOutputEntry 1 }

prtOutputType OBJECT-TYPE
    SYNTAX PrtOutputTypeTC
--    Rsyntax INTEGER {
--        other(1),
--        unknown(2),
--        removableBin(3),
--        unRemovableBin(4),
--        continuousRollDevice(5),
--        mailBox(6),
--        continuousFanFold(7)
--        }
    ACCESS read-only
    STATUS mandatory
    DESCRIPTION
        "The type of technology supported by this output sub-unit."
    ::= { prtOutputEntry 2 }

prtOutputCapacityUnit OBJECT-TYPE
    SYNTAX PrtCapacityUnitTC
--    Rsyntax INTEGER {
--        other(1),
--        unknown(2),
--        tenThousandthsOfInches(3),
--        micrometers(4),
--        sheets(8),
--        feet(16),
--        meters(17),
--        items(18),
--        percent(19)
--        }
    ACCESS read-only
    STATUS mandatory
    DESCRIPTION
        "The unit of measurement for use in calculating and relaying
        capacity values for this output sub-unit."
    ::= { prtOutputEntry 3 }

prtOutputMaxCapacity OBJECT-TYPE
    SYNTAX INTEGER(-2..2147483647)
    ACCESS read-write
    STATUS mandatory
    DESCRIPTION
        "The maximum capacity of this output sub-unit in output sub-
        unit capacity units (PrtCapacityUnitTC).  There is no convention
        associated with the media itself so this value essentially
        reflects claimed capacity.  If this output sub-unit can reliably
        sense this value, the value is sensed by the printer and may
        not be changed by management requests; otherwise, the value may
        be written (by a Remote Control Panel or a Management
        Application).  The value (-1) means other and specifically
        indicates that the sub-unit places no restrictions on this
        parameter.  The value (-2) means unknown."
    ::= { prtOutputEntry 4 }

prtOutputRemainingCapacity OBJECT-TYPE
    SYNTAX INTEGER(-3..2147483647)
    ACCESS read-write
    STATUS mandatory
    DESCRIPTION
        "The remaining capacity of the possible output sub-unit
        capacity in output sub-unit capacity units
        (PrtCapacityUnitTC)of this output sub-unit.  If this output sub-
        unit can reliably sense this value, the value is sensed by the
        printer and may not be modified by management requests;
        
        otherwise, the value may be written (by a Remote Control Panel
        or a Management Application).  The value (-1) means other and
        specifically indicates that the sub-unit places no restrictions
        on this parameter.  The value (-2) means unknown.  The value
        (-3) means that the printer knows that there remains capacity
        for at least one unit."
    ::= { prtOutputEntry 5 }

prtOutputStatus OBJECT-TYPE
    SYNTAX PrtSubUnitStatusTC
--    Rsyntax INTEGER(0..126)
    ACCESS read-only
    STATUS mandatory
    DESCRIPTION
        "The current status of this output sub-unit."
    ::= { prtOutputEntry 6 }

prtOutputName OBJECT-TYPE
    SYNTAX OCTET STRING(SIZE(0..63))
    ACCESS read-write
    STATUS mandatory
    DESCRIPTION
        "The name assigned to this output sub-unit."
    ::= { prtOutputEntry 7 }

prtOutputVendorName OBJECT-TYPE
    SYNTAX OCTET STRING(SIZE(0..63))
    ACCESS read-only
    STATUS mandatory
    DESCRIPTION
        "The vendor name of this output sub-unit."
    ::= { prtOutputEntry 8 }

prtOutputModel OBJECT-TYPE
    SYNTAX OCTET STRING(SIZE(0..63))
    ACCESS read-only
    STATUS mandatory
    DESCRIPTION
        "The model name assigned to this output sub-unit.
        
        NOTE: The above description has been modified from RFC 1759
        for clarification."
    ::= { prtOutputEntry 9 }

prtOutputVersion OBJECT-TYPE
    SYNTAX OCTET STRING(SIZE(0..63))
    ACCESS read-only
    STATUS mandatory
    DESCRIPTION
        "The version of this output sub-unit."
    ::= { prtOutputEntry 10 }

prtOutputSerialNumber OBJECT-TYPE
    SYNTAX OCTET STRING(SIZE(0..63))
    ACCESS read-only
    STATUS mandatory
    DESCRIPTION
        "The serial number assigned to this output sub-unit."
    ::= { prtOutputEntry 11 }

prtOutputDescription OBJECT-TYPE
    SYNTAX PrtLocalizedDescriptionStringTC
--    Rsyntax OCTET STRING(SIZE(0..255))
    ACCESS read-only
    STATUS mandatory
    DESCRIPTION
        "A free-form text description of this output sub-unit in the
        localization specified by prtGeneralCurrentLocalization."
    ::= { prtOutputEntry 12 }

prtOutputSecurity OBJECT-TYPE
    SYNTAX PresentOnOff
--    Rsyntax INTEGER {
--        other(1),
--        on(3),
--        off(4),
--        notPresent(5)
--        }
    ACCESS read-write
    STATUS mandatory
    DESCRIPTION
        "Indicates if this output sub-unit has some security associated
        with it and if that security is enabled or not."
    ::= { prtOutputEntry 13 }

prtOutputDimUnit OBJECT-TYPE
    SYNTAX PrtMediaUnitTC
--    Rsyntax INTEGER {
--        tenThousandthsOfInches(3),
--        micrometers(4)
--        }
    ACCESS read-only
    STATUS mandatory
    DESCRIPTION
        "The unit of measurement for use in calculating and relaying
        dimensional values for this output sub-unit."
    ::= { prtOutputEntry 14 }

prtOutputMaxDimFeedDir OBJECT-TYPE
    SYNTAX INTEGER(-2..2147483647)
    ACCESS read-write
    STATUS mandatory
    DESCRIPTION
        "The maximum dimensions supported by this output sub-unit
        for measurements taken parallel relative to the feed
        direction associated with that sub-unit in output
        sub-unit dimensional units (controlled by prtOutputDimUnit,
        which uses PrtMediaUnitTC).  If this output sub-unit can
        reliably sense this value, the value is sensed by the printer
        and may not be changed with management protocol operations.
        The value (-1) means other and specifically indicates that the
        sub-unit places no restrictions on this parameter.  The value
        (-2) means unknown.
        
        NOTE: The above description has been modified from RFC 1759
        for clarification and to explain the purpose of (-1) and (-2)."
    ::= { prtOutputEntry 15 }

prtOutputMaxDimXFeedDir OBJECT-TYPE
    SYNTAX INTEGER(-2..2147483647)
    ACCESS read-write
    STATUS mandatory
    DESCRIPTION
        "The maximum dimensions supported by this output sub-unit
        for measurements taken ninety degrees relative to the
        feed direction associated with that sub-unit in output
        sub-unit dimensional units (controlled by prtOutputDimUnit,
        which uses PrtMediaUnitTC).  If this output sub-unit can
        reliably sense this value, the value is sensed by the printer
        and may not be changed with management protocol operations.
        The value (-1) means other and specifically indicates that the
        sub-unit places no restrictions on this parameter.  The value
        (-2) means unknown.
        
        NOTE: The above description has been modified from RFC 1759
        for clarification and to explain the purpose of (-1) and (-2)."
    ::= { prtOutputEntry 16 }

prtOutputMinDimFeedDir OBJECT-TYPE
    SYNTAX INTEGER(-2..2147483647)
    ACCESS read-write
    STATUS mandatory
    DESCRIPTION
        "The minimum dimensions supported by this output sub-unit
        for measurements taken parallel relative to the feed
        direction associated with that sub-unit in output
        sub-unit dimensional units (controlled by prtOutputDimUnit,
        which uses PrtMediaUnitTC).  If this output sub-unit can
        reliably sense this value, the value is sensed by the printer
        and may not be changed with management protocol operations.
        The value (-1) means other and specifically indicates that the
        sub-unit places no restrictions on this parameter.  The value
        (-2) means unknown.
        
        NOTE: The above description has been modified from RFC 1759
        for clarification and to explain the purpose of (-1) and (-2)."
    ::= { prtOutputEntry 17 }

prtOutputMinDimXFeedDir OBJECT-TYPE
    SYNTAX INTEGER(-2..2147483647)
    ACCESS read-write
    STATUS mandatory
    DESCRIPTION
        "The minimum dimensions supported by this output sub-unit
        for measurements taken ninety degrees relative to the
        feed direction associated with that sub-unit in output
        sub-unit dimensional units (controlled by prtOutputDimUnit,
        which uses PrtMediaUnitTC).  If this output sub-unit can
        reliably sense this value, the value is sensed by the printer
        and may not be changed with management protocol operations.
        The value (-1) means other and specifically indicates that the
        sub-unit places no restrictions on this parameter.  The value
        (-2) means unknown.
        
        NOTE: The above description has been modified from RFC 1759
        for clarification and to explain the purpose of (-1) and (-2)."
    ::= { prtOutputEntry 18 }

prtOutputStackingOrder OBJECT-TYPE
    SYNTAX PrtOutputStackingOrderTC
--    Rsyntax INTEGER {
--        unknown(2),
--        firstToLast(3),
--        lastToFirst(4)
--        }
    ACCESS read-write
    STATUS mandatory
    DESCRIPTION
        "The current state of the stacking order for the
        associated output sub-unit. 'FirstToLast' means
        that as pages are output the front of the next page is
        placed against the back of the previous page.
        'LasttoFirst' means that as pages are output the back
        of the next page is placed against the front of the
        previous page."
    ::= { prtOutputEntry 19 }

prtOutputPageDeliveryOrientation OBJECT-TYPE
    SYNTAX PrtOutputPageDeliveryOrientationTC
--    Rsyntax INTEGER {
--        faceUp(3),
--        faceDown(4)
--        }
    ACCESS read-write
    STATUS mandatory
    DESCRIPTION
        "The reading surface that will be 'up' when pages are
        delivered to the associated output sub-unit.  Values are
        faceUp and faceDown.  (Note: interpretation of these
        values is in general context-dependent based on locale;
        presentation of these values to an end-user should be
        normalized to the expectations of the user)."
    ::= { prtOutputEntry 20 }

prtOutputBursting OBJECT-TYPE
    SYNTAX PresentOnOff
--    Rsyntax INTEGER {
--        other(1),
--        on(3),
--        off(4),
--        notPresent(5)
--        }
    ACCESS read-write
    STATUS mandatory
    DESCRIPTION
        "This object indicates that the outputting sub-unit supports
        bursting, and if so, whether the feature is enabled.  Bursting
        is the process by which continuous media is separated into
        individual sheets, typically by bursting along pre-formed
        perforations."
    ::= { prtOutputEntry 21 }

prtOutputDecollating OBJECT-TYPE
    SYNTAX PresentOnOff
--    Rsyntax INTEGER {
--        other(1),
--        on(3),
--        off(4),
--        notPresent(5)
--        }
    ACCESS read-write
    STATUS mandatory
    DESCRIPTION
        "This object indicates that the output supports decollating,
        and if so, whether the feature is enabled.  Decollating is the
        process by which the individual parts within a multi-part form
        are separated and sorted into separate stacks for each part."
    ::= { prtOutputEntry 22 }

prtOutputPageCollated OBJECT-TYPE
    SYNTAX PresentOnOff
--    Rsyntax INTEGER {
--        other(1),
--        on(3),
--        off(4),
--        notPresent(5)
--        }
    ACCESS read-write
    STATUS mandatory
    DESCRIPTION
        "This object indicates that the output sub-unit supports page
        collation, and if so, whether the feature is enabled.  See RFC
        3805 Appendix A, Glossary Of Terms, for definition of how this
        document defines collation.
        
        NOTE: The above description has been modified from RFC 1759
        for clarification."
    ::= { prtOutputEntry 23 }

prtOutputOffsetStacking OBJECT-TYPE
    SYNTAX PresentOnOff
--    Rsyntax INTEGER {
--        other(1),
--        on(3),
--        off(4),
--        notPresent(5)
--        }
    ACCESS read-write
    STATUS mandatory
    DESCRIPTION
        "This object indicates that the output supports offset
        stacking,and if so, whether the feature is enabled.  See RFC
        3805 Appendix A, Glossary Of Terms,  for how Offset Stacking is
        defined by this document.
        
        NOTE: The above description has been modified from RFC 1759
        for clarification."
    ::= { prtOutputEntry 24 }

prtMarkerTable OBJECT-TYPE
    SYNTAX SEQUENCE OF PrtMarkerEntry
    ACCESS not-accessible
    STATUS mandatory
    DESCRIPTION
        "The marker table provides a description of each marker
        sub-unit contained within the printer.
        
        NOTE: The above description has been modified from RFC 1759
        for clarification."
    ::= { prtMarker 2 }

prtMarkerEntry OBJECT-TYPE
    SYNTAX PrtMarkerEntry
    ACCESS not-accessible
    STATUS mandatory
    DESCRIPTION
        "Entries in this table define the characteristics and status
        of each marker sub-unit in the printer.
        
        NOTE: The above description has been modified from RFC 1759
        for clarification."
    INDEX { hrDeviceIndex, prtMarkerIndex }
    ::= { prtMarkerTable 1 }

PrtMarkerEntry ::= SEQUENCE {
    prtMarkerIndex INTEGER,
    prtMarkerMarkTech PrtMarkerMarkTechTC,
    prtMarkerCounterUnit PrtMarkerCounterUnitTC,
    prtMarkerLifeCount Counter,
    prtMarkerPowerOnCount Counter,
    prtMarkerProcessColorants INTEGER,
    prtMarkerSpotColorants INTEGER,
    prtMarkerAddressabilityUnit PrtMarkerAddressabilityUnitTC,
    prtMarkerAddressabilityFeedDir INTEGER,
    prtMarkerAddressabilityXFeedDir INTEGER,
    prtMarkerNorthMargin INTEGER,
    prtMarkerSouthMargin INTEGER,
    prtMarkerWestMargin INTEGER,
    prtMarkerEastMargin INTEGER,
    prtMarkerStatus PrtSubUnitStatusTC
    }

prtMarkerIndex OBJECT-TYPE
    SYNTAX INTEGER(1..65535)
    ACCESS not-accessible
    STATUS mandatory
    DESCRIPTION
        "A unique value used by the printer to identify this marking
        SubUnit.  Although these values may change due to a major
        reconfiguration of the device (e.g., the addition of new marking
        sub-units to the printer), values SHOULD remain stable across
        successive printer power cycles.
        
        NOTE: The above description has been modified from RFC 1759
        for clarification."
    ::= { prtMarkerEntry 1 }

prtMarkerMarkTech OBJECT-TYPE
    SYNTAX PrtMarkerMarkTechTC
--    Rsyntax INTEGER {
--        other(1),
--        unknown(2),
--        electrophotographicLED(3),
--        electrophotographicLaser(4),
--        electrophotographicOther(5),
--        impactMovingHeadDotMatrix9pin(6),
--        impactMovingHeadDotMatrix24pin(7),
--        impactMovingHeadDotMatrixOther(8),
--        impactMovingHeadFullyFormed(9),
--        impactBand(10),
--        impactOther(11),
--        inkjetAqueous(12),
--        inkjetSolid(13),
--        inkjetOther(14),
--        pen(15),
--        thermalTransfer(16),
--        thermalSensitive(17),
--        thermalDiffusion(18),
--        thermalOther(19),
--        electroerosion(20),
--        electrostatic(21),
--        photographicMicrofiche(22),
--        photographicImagesetter(23),
--        photographicOther(24),
--        ionDeposition(25),
--        eBeam(26),
--        typesetter(27)
--        }
    ACCESS read-only
    STATUS mandatory
    DESCRIPTION
        "The type of marking technology used for this marking
        sub-unit."
    ::= { prtMarkerEntry 2 }

prtMarkerCounterUnit OBJECT-TYPE
    SYNTAX PrtMarkerCounterUnitTC
--    Rsyntax INTEGER {
--        tenThousandthsOfInches(3),
--        micrometers(4),
--        characters(5),
--        lines(6),
--        impressions(7),
--        sheets(8),
--        dotRow(9),
--        hours(11),
--        feet(16),
--        meters(17)
--        }
    ACCESS read-only
    STATUS mandatory
    DESCRIPTION
        "The unit that will be used by the printer when reporting
        counter values for this marking sub-unit.  The time units of
        measure are provided for a device like a strip recorder that
        does not or cannot track the physical dimensions of the media
        and does not use characters, lines or sheets."
    ::= { prtMarkerEntry 3 }

prtMarkerLifeCount OBJECT-TYPE
    SYNTAX Counter
    ACCESS read-only
    STATUS mandatory
    DESCRIPTION
        "The count of the number of units of measure counted during the
        
        life of printer using units of measure as specified by
        prtMarkerCounterUnit.
        
        Note: This object should be implemented as a persistent object
        with a reliable value throughout the lifetime of the printer."
    ::= { prtMarkerEntry 4 }

prtMarkerPowerOnCount OBJECT-TYPE
    SYNTAX Counter
    ACCESS read-only
    STATUS mandatory
    DESCRIPTION
        "The count of the number of units of measure counted since the
        equipment was most recently powered on using units of measure
        as specified by prtMarkerCounterUnit."
    ::= { prtMarkerEntry 5 }

prtMarkerProcessColorants OBJECT-TYPE
    SYNTAX INTEGER(0..65535)
    ACCESS read-only
    STATUS mandatory
    DESCRIPTION
        "The number of process colors supported by this marker.  A
        process color of 1 implies monochrome.  The value of this
        object and prtMarkerSpotColorants cannot both be 0.  The value
        of prtMarkerProcessColorants must be 0 or greater.
        
        NOTE: The above description has been modified from RFC 1759
        for clarification."
    ::= { prtMarkerEntry 6 }

prtMarkerSpotColorants OBJECT-TYPE
    SYNTAX INTEGER(0..65535)
    ACCESS read-only
    STATUS mandatory
    DESCRIPTION
        "The number of spot colors supported by this marker.  The value
        of this object and prtMarkerProcessColorants cannot both be 0.
        Must be 0 or greater.
        
        NOTE: The above description has been modified from RFC 1759
        for clarification."
    ::= { prtMarkerEntry 7 }

prtMarkerAddressabilityUnit OBJECT-TYPE
    SYNTAX PrtMarkerAddressabilityUnitTC
--    Rsyntax INTEGER {
--        tenThousandthsOfInches(3),
--        micrometers(4)
--        }
    ACCESS read-only
    STATUS mandatory
    DESCRIPTION
        "The unit of measure of distances, as applied to the marker's
        resolution.
        
        NOTE: The above description has been modified from RFC 1759
        for clarification."
    ::= { prtMarkerEntry 8 }

prtMarkerAddressabilityFeedDir OBJECT-TYPE
    SYNTAX INTEGER(-2..2147483647)
    ACCESS read-only
    STATUS mandatory
    DESCRIPTION
        "The maximum number of addressable marking positions in the
        feed direction per 10000 units of measure specified by
        prtMarkerAddressabilityUnit.  A value of (-1) implies 'other'
        or 'infinite' while a value of (-2) implies 'unknown'.
        
        NOTE: The above description has been modified from RFC 1759
        for clarification."
    ::= { prtMarkerEntry 9 }

prtMarkerAddressabilityXFeedDir OBJECT-TYPE
    SYNTAX INTEGER(-2..2147483647)
    ACCESS read-only
    STATUS mandatory
    DESCRIPTION
        "The maximum number of addressable marking positions in the
        cross feed direction in 10000 units of measure specified by
        prtMarkerAddressabilityUnit.  A value of (-1) implies 'other'
        or 'infinite' while a value of (-2) implies 'unknown'.
        
        NOTE: The above description has been modified from RFC 1759
        for clarification."
    ::= { prtMarkerEntry 10 }

prtMarkerNorthMargin OBJECT-TYPE
    SYNTAX INTEGER(-2..2147483647)
    ACCESS read-only
    STATUS mandatory
    DESCRIPTION
        "The margin, in units identified by prtMarkerAddressabilityUnit,
        from the leading edge of the medium as the medium flows through
        
        the marking engine with the side to be imaged facing the
        observer.  The leading edge is the North edge and the other
        edges are defined by the normal compass layout of  directions
        with the compass facing the observer.  Printing within the area
        bounded by all four margins is guaranteed for all interpreters.
        The value (-2) means unknown."
    ::= { prtMarkerEntry 11 }

prtMarkerSouthMargin OBJECT-TYPE
    SYNTAX INTEGER(-2..2147483647)
    ACCESS read-only
    STATUS mandatory
    DESCRIPTION
        "The margin from the South edge  (see prtMarkerNorthMargin) of
        the medium in units identified by prtMarkerAddressabilityUnit.
        Printing within the area bounded by all four margins  is
        guaranteed for all interpreters.  The value (-2) means unknown."
    ::= { prtMarkerEntry 12 }

prtMarkerWestMargin OBJECT-TYPE
    SYNTAX INTEGER(-2..2147483647)
    ACCESS read-only
    STATUS mandatory
    DESCRIPTION
        "The margin from the West edge (see prtMarkerNorthMargin) of
        the medium in units identified by prtMarkerAddressabilityUnit.
        Printing within the area bounded by all four margins is
        guaranteed for all interpreters.  The value (-2) means unknown."
    ::= { prtMarkerEntry 13 }

prtMarkerEastMargin OBJECT-TYPE
    SYNTAX INTEGER(-2..2147483647)
    ACCESS read-only
    STATUS mandatory
    DESCRIPTION
        "The margin from the East edge (see prtMarkerNorthMargin) of
        the medium in units identified by prtMarkerAddressabilityUnit.
        Printing within the area bounded by all four margins is
        guaranteed for all interpreters.  The value (-2) means unknown."
    ::= { prtMarkerEntry 14 }

prtMarkerStatus OBJECT-TYPE
    SYNTAX PrtSubUnitStatusTC
--    Rsyntax INTEGER(0..126)
    ACCESS read-only
    STATUS mandatory
    DESCRIPTION
        "The current status of this marker sub-unit."
    ::= { prtMarkerEntry 15 }

prtMarkerSuppliesTable OBJECT-TYPE
    SYNTAX SEQUENCE OF PrtMarkerSuppliesEntry
    ACCESS not-accessible
    STATUS mandatory
    DESCRIPTION
        "A table of the marker supplies available on this printer."
    ::= { prtMarkerSupplies 1 }

prtMarkerSuppliesEntry OBJECT-TYPE
    SYNTAX PrtMarkerSuppliesEntry
    ACCESS not-accessible
    STATUS mandatory
    DESCRIPTION
        "Attributes of a marker supply.  Entries may exist in the table
        for each device index with a device type of 'printer'.
        
        NOTE: The above description has been modified from RFC 1759
        for clarification."
    INDEX { hrDeviceIndex, prtMarkerSuppliesIndex }
    ::= { prtMarkerSuppliesTable 1 }

PrtMarkerSuppliesEntry ::= SEQUENCE {
    prtMarkerSuppliesIndex INTEGER,
    prtMarkerSuppliesMarkerIndex INTEGER,
    prtMarkerSuppliesColorantIndex INTEGER,
    prtMarkerSuppliesClass PrtMarkerSuppliesClassTC,
    prtMarkerSuppliesType PrtMarkerSuppliesTypeTC,
    prtMarkerSuppliesDescription PrtLocalizedDescriptionStringTC,
    prtMarkerSuppliesSupplyUnit PrtMarkerSuppliesSupplyUnitTC,
    prtMarkerSuppliesMaxCapacity INTEGER,
    prtMarkerSuppliesLevel INTEGER
    }

prtMarkerSuppliesIndex OBJECT-TYPE
    SYNTAX INTEGER(1..65535)
    ACCESS not-accessible
    STATUS mandatory
    DESCRIPTION
        "A unique value used by the printer to identify this marker
        supply.  Although these values may change due to a major
        reconfiguration of the device (e.g., the addition of new marker
        
        supplies to the printer), values SHOULD remain stable across
        successive printer power cycles.
        
        NOTE: The above description has been modified from RFC 1759
        for clarification."
    ::= { prtMarkerSuppliesEntry 1 }

prtMarkerSuppliesMarkerIndex OBJECT-TYPE
    SYNTAX INTEGER(0..65535)
    ACCESS read-only
    STATUS mandatory
    DESCRIPTION
        "The value of prtMarkerIndex corresponding to the marking sub
        unit with which this marker supply sub-unit is associated."
    ::= { prtMarkerSuppliesEntry 2 }

prtMarkerSuppliesColorantIndex OBJECT-TYPE
    SYNTAX INTEGER(0..65535)
    ACCESS read-only
    STATUS mandatory
    DESCRIPTION
        "The value of prtMarkerColorantIndex corresponding to the
        colorant with which this marker supply sub-unit is associated.
        This value shall be 0 if there is no colorant table or if this
        supply does not depend on a single specified colorant.
        NOTE: The above description has been modified from RFC 1759
        for clarification."
    ::= { prtMarkerSuppliesEntry 3 }

prtMarkerSuppliesClass OBJECT-TYPE
    SYNTAX PrtMarkerSuppliesClassTC
--    Rsyntax INTEGER {
--        other(1),
--        supplyThatIsConsumed(3),
--        receptacleThatIsFilled(4)
--        }
    ACCESS read-only
    STATUS mandatory
    DESCRIPTION
        "Indicates whether this supply entity represents a supply that
        is consumed or a receptacle that is filled.
        
        NOTE: The above description has been modified from RFC 1759
        for clarification."
    ::= { prtMarkerSuppliesEntry 4 }

prtMarkerSuppliesType OBJECT-TYPE
    SYNTAX PrtMarkerSuppliesTypeTC
--    Rsyntax INTEGER {
--        other(1),
--        unknown(2),
--        toner(3),
--        wasteToner(4),
--        ink(5),
--        inkCartridge(6),
--        inkRibbon(7),
--        wasteInk(8),
--        opc(9),
--        developer(10),
--        fuserOil(11),
--        solidWax(12),
--        ribbonWax(13),
--        wasteWax(14),
--        fuser(15),
--        coronaWire(16),
--        fuserOilWick(17),
--        cleanerUnit(18),
--        fuserCleaningPad(19),
--        transferUnit(20),
--        tonerCartridge(21),
--        fuserOiler(22),
--        water(23),
--        wasteWater(24),
--        glueWaterAdditive(25),
--        wastePaper(26),
--        bindingSupply(27),
--        bandingSupply(28),
--        stitchingWire(29),
--        shrinkWrap(30),
--        paperWrap(31),
--        staples(32),
--        inserts(33),
--        covers(34)
--        }
    ACCESS read-only
    STATUS mandatory
    DESCRIPTION
        "The type of this supply."
    ::= { prtMarkerSuppliesEntry 5 }

prtMarkerSuppliesDescription OBJECT-TYPE
    SYNTAX PrtLocalizedDescriptionStringTC
--    Rsyntax OCTET STRING(SIZE(0..255))
    ACCESS read-only
    STATUS mandatory
    DESCRIPTION
        "The description of this supply container/receptacle in the
        localization specified by prtGeneralCurrentLocalization."
    ::= { prtMarkerSuppliesEntry 6 }

prtMarkerSuppliesSupplyUnit OBJECT-TYPE
    SYNTAX PrtMarkerSuppliesSupplyUnitTC
--    Rsyntax INTEGER {
--        other(1),
--        unknown(2),
--        tenThousandthsOfInches(3),
--        micrometers(4),
--        impressions(7),
--        sheets(8),
--        hours(11),
--        thousandthsOfOunces(12),
--        tenthsOfGrams(13),
--        hundrethsOfFluidOunces(14),
--        tenthsOfMilliliters(15),
--        feet(16),
--        meters(17),
--        items(18),
--        percent(19)
--        }
    ACCESS read-only
    STATUS mandatory
    DESCRIPTION
        "Unit of measure of this marker supply container/receptacle.
        
        NOTE: The above description has been modified from RFC 1759
        for clarification."
    ::= { prtMarkerSuppliesEntry 7 }

prtMarkerSuppliesMaxCapacity OBJECT-TYPE
    SYNTAX INTEGER(-2..2147483647)
    ACCESS read-write
    STATUS mandatory
    DESCRIPTION
        "The maximum capacity of this supply container/receptacle
        expressed in prtMarkerSuppliesSupplyUnit.  If this supply
        container/receptacle can reliably sense this value, the value
        is reported by the printer and is read-only; otherwise, the
        value may be written (by a Remote Control Panel or a Management
        Application).  The value (-1) means other and specifically
        indicates that the sub-unit places no restrictions on this
        parameter.  The value (-2) means unknown."
    ::= { prtMarkerSuppliesEntry 8 }

prtMarkerSuppliesLevel OBJECT-TYPE
    SYNTAX INTEGER(-3..2147483647)
    ACCESS read-write
    STATUS mandatory
    DESCRIPTION
        "The current level if this supply is a container; the remaining
        space if this supply is a receptacle.  If this supply
        container/receptacle can reliably sense this value, the value
        is reported by the printer and is read-only; otherwise, the
        value may be written (by a Remote Control Panel or a Management
        Application).  The value (-1) means other and specifically
        indicates that the sub-unit places no restrictions on this
        parameter.  The value (-2) means unknown.  A value of (-3) means
        that the printer knows that there is some supply/remaining
        space, respectively."
    ::= { prtMarkerSuppliesEntry 9 }

prtMarkerColorantTable OBJECT-TYPE
    SYNTAX SEQUENCE OF PrtMarkerColorantEntry
    ACCESS not-accessible
    STATUS mandatory
    DESCRIPTION
        "A table of all of the colorants available on the printer."
    ::= { prtMarkerColorant 1 }

prtMarkerColorantEntry OBJECT-TYPE
    SYNTAX PrtMarkerColorantEntry
    ACCESS not-accessible
    STATUS mandatory
    DESCRIPTION
        "Attributes of a colorant available on the printer.  Entries may
        exist in the table for each device index with a device type of
        'printer'.
        
        NOTE: The above description has been modified from RFC 1759
        for clarification."
    INDEX { hrDeviceIndex, prtMarkerColorantIndex }
    ::= { prtMarkerColorantTable 1 }

PrtMarkerColorantEntry ::= SEQUENCE {
    prtMarkerColorantIndex INTEGER,
    prtMarkerColorantMarkerIndex INTEGER,
    prtMarkerColorantRole PrtMarkerColorantRoleTC,
    prtMarkerColorantValue OCTET STRING,
    prtMarkerColorantTonality INTEGER
    }

prtMarkerColorantIndex OBJECT-TYPE
    SYNTAX INTEGER(1..65535)
    ACCESS not-accessible
    STATUS mandatory
    DESCRIPTION
        "A unique value used by the printer to identify this colorant.
        Although these values may change due to a major reconfiguration
        of the device (e.g., the addition of new colorants to the
        printer) , values SHOULD remain stable across successive
        printer power cycles.
        
        NOTE: The above description has been modified from RFC 1759
        for clarification."
    ::= { prtMarkerColorantEntry 1 }

prtMarkerColorantMarkerIndex OBJECT-TYPE
    SYNTAX INTEGER(0..65535)
    ACCESS read-only
    STATUS mandatory
    DESCRIPTION
        "The value of prtMarkerIndex corresponding to the marker sub
        unit with which this colorant entry is associated."
    ::= { prtMarkerColorantEntry 2 }

prtMarkerColorantRole OBJECT-TYPE
    SYNTAX PrtMarkerColorantRoleTC
--    Rsyntax INTEGER {
--        other(1),
--        process(3),
--        spot(4)
--        }
    ACCESS read-only
    STATUS mandatory
    DESCRIPTION
        "The role played by this colorant."
    ::= { prtMarkerColorantEntry 3 }

prtMarkerColorantValue OBJECT-TYPE
    SYNTAX OCTET STRING(SIZE(0..255))
    ACCESS read-only
    STATUS mandatory
    DESCRIPTION
        "The name of the color of this colorant using standardized
        string names from ISO 10175 (DPA) and ISO 10180 (SPDL) such as:
            other
            unknown
            white
            red
            green
            blue
        
            cyan
            magenta
            yellow
            black
        Implementers may add additional string values.  The naming
        conventions in ISO 9070 are recommended in order to avoid
        potential name clashes"
    ::= { prtMarkerColorantEntry 4 }

prtMarkerColorantTonality OBJECT-TYPE
    SYNTAX INTEGER(2..2147483647)
    ACCESS read-only
    STATUS mandatory
    DESCRIPTION
        "The distinct levels of tonality realizable by a marking sub
        unit when using this colorant.  This value does not include the
        number of levels of tonal difference that an interpreter can
        obtain by techniques such as half toning.  This value must be at
        least 2."
    ::= { prtMarkerColorantEntry 5 }

prtMediaPathTable OBJECT-TYPE
    SYNTAX SEQUENCE OF PrtMediaPathEntry
    ACCESS not-accessible
    STATUS mandatory
    DESCRIPTION
        "The media path table includes both physical and logical paths
        within the printer.
        
        NOTE: The above description has been modified from RFC 1759
        for clarification."
    ::= { prtMediaPath 4 }

prtMediaPathEntry OBJECT-TYPE
    SYNTAX PrtMediaPathEntry
    ACCESS not-accessible
    STATUS mandatory
    DESCRIPTION
        "Entries may exist in the table for each device index with a
        device type of 'printer'  Each entry defines the physical
        characteristics of and the status of the media path.  The data
        provided indicates the maximum throughput and the media
        size limitations of these subunits.
        
        NOTE: The above description has been modified from RFC 1759
        for clarification."
    INDEX { hrDeviceIndex, prtMediaPathIndex }
    ::= { prtMediaPathTable 1 }

PrtMediaPathEntry ::= SEQUENCE {
    prtMediaPathIndex INTEGER,
    prtMediaPathMaxSpeedPrintUnit PrtMediaPathMaxSpeedPrintUnitTC,
    prtMediaPathMediaSizeUnit PrtMediaUnitTC,
    prtMediaPathMaxSpeed INTEGER,
    prtMediaPathMaxMediaFeedDir INTEGER,
    prtMediaPathMaxMediaXFeedDir INTEGER,
    prtMediaPathMinMediaFeedDir INTEGER,
    prtMediaPathMinMediaXFeedDir INTEGER,
    prtMediaPathType PrtMediaPathTypeTC,
    prtMediaPathDescription PrtLocalizedDescriptionStringTC,
    prtMediaPathStatus PrtSubUnitStatusTC
    }

prtMediaPathIndex OBJECT-TYPE
    SYNTAX INTEGER(1..65535)
    ACCESS not-accessible
    STATUS mandatory
    DESCRIPTION
        "A unique value used by the printer to identify this media
        path.  Although these values may change due to a major
        reconfiguration of the device (e.g., the addition of new media
        paths to the printer), values SHOULD remain stable across
        successive printer power cycles.
        
        NOTE: The above description has been modified from RFC 1759
        for clarification."
    ::= { prtMediaPathEntry 1 }

prtMediaPathMaxSpeedPrintUnit OBJECT-TYPE
    SYNTAX PrtMediaPathMaxSpeedPrintUnitTC
--    Rsyntax INTEGER {
--        tenThousandthsOfInchesPerHour(3),
--        micrometersPerHour(4),
--        charactersPerHour(5),
--        linesPerHour(6),
--        impressionsPerHour(7),
--        sheetsPerHour(8),
--        dotRowPerHour(9),
--        feetPerHour(16),
--        metersPerHour(17)
--        }
    ACCESS read-only
    STATUS mandatory
    DESCRIPTION
        "The unit of measure used in specifying the speed of all media
        paths in the printer."
    ::= { prtMediaPathEntry 2 }

prtMediaPathMediaSizeUnit OBJECT-TYPE
    SYNTAX PrtMediaUnitTC
--    Rsyntax INTEGER {
--        tenThousandthsOfInches(3),
--        micrometers(4)
--        }
    ACCESS read-only
    STATUS mandatory
    DESCRIPTION
        "The units of measure of media size for use in calculating and
        relaying dimensional values for all media paths in the
        printer."
    ::= { prtMediaPathEntry 3 }

prtMediaPathMaxSpeed OBJECT-TYPE
    SYNTAX INTEGER(-2..2147483647)
    ACCESS read-only
    STATUS mandatory
    DESCRIPTION
        "The maximum printing speed of this media path expressed in
        prtMediaPathMaxSpeedUnit's.  A value of (-1) implies 'other'."
    ::= { prtMediaPathEntry 4 }

prtMediaPathMaxMediaFeedDir OBJECT-TYPE
    SYNTAX INTEGER(-2..2147483647)
    ACCESS read-only
    STATUS mandatory
    DESCRIPTION
        "The maximum physical media size in the feed direction of this
        media path expressed in units of measure specified by
        PrtMediaPathMediaSizeUnit.  A value of (-1) implies 'unlimited'
        a value of (-2) implies 'unknown'.
        
        NOTE: The above description has been modified from RFC 1759
        for clarification."
    ::= { prtMediaPathEntry 5 }

prtMediaPathMaxMediaXFeedDir OBJECT-TYPE
    SYNTAX INTEGER(-2..2147483647)
    ACCESS read-only
    STATUS mandatory
    DESCRIPTION
        "The maximum physical media size across the feed direction of
        this media path expressed in units of measure specified by
        prtMediaPathMediaSizeUnit.  A value of (-2) implies 'unknown'.
        
        NOTE: The above description has been modified from RFC 1759
        for clarification."
    ::= { prtMediaPathEntry 6 }

prtMediaPathMinMediaFeedDir OBJECT-TYPE
    SYNTAX INTEGER(-2..2147483647)
    ACCESS read-only
    STATUS mandatory
    DESCRIPTION
        "The minimum physical media size in the feed direction of this
        media path expressed in units of measure specified by
        prtMediaPathMediaSizeUnit.  A value of (-2) implies 'unknown'.
        
        NOTE: The above description has been modified from RFC 1759
        for clarification."
    ::= { prtMediaPathEntry 7 }

prtMediaPathMinMediaXFeedDir OBJECT-TYPE
    SYNTAX INTEGER(-2..2147483647)
    ACCESS read-only
    STATUS mandatory
    DESCRIPTION
        "The minimum physical media size across the feed direction of
        this media path expressed in units of measure specified by
        prtMediaPathMediaSizeUnit.  A value of (-2) implies 'unknown'.
        
        NOTE: The above description has been modified from RFC 1759
        for clarification."
    ::= { prtMediaPathEntry 8 }

prtMediaPathType OBJECT-TYPE
    SYNTAX PrtMediaPathTypeTC
--    Rsyntax INTEGER {
--        other(1),
--        unknown(2),
--        longEdgeBindingDuplex(3),
--        shortEdgeBindingDuplex(4),
--        simplex(5)
--        }
    ACCESS read-only
    STATUS mandatory
    DESCRIPTION
        "The type of the media path for this media path."
    ::= { prtMediaPathEntry 9 }

prtMediaPathDescription OBJECT-TYPE
    SYNTAX PrtLocalizedDescriptionStringTC
--    Rsyntax OCTET STRING(SIZE(0..255))
    ACCESS read-only
    STATUS mandatory
    DESCRIPTION
        "The manufacturer-provided description of this media path in
        the localization specified by prtGeneralCurrentLocalization."
    ::= { prtMediaPathEntry 10 }

prtMediaPathStatus OBJECT-TYPE
    SYNTAX PrtSubUnitStatusTC
--    Rsyntax INTEGER(0..126)
    ACCESS read-only
    STATUS mandatory
    DESCRIPTION
        "The current status of this media path."
    ::= { prtMediaPathEntry 11 }

prtChannelTable OBJECT-TYPE
    SYNTAX SEQUENCE OF PrtChannelEntry
    ACCESS not-accessible
    STATUS mandatory
    DESCRIPTION
        "The channel table represents the set of input data sources
        which can provide print data to one or more of the
        interpreters available on a printer.
        
        NOTE: The above description has been modified from RFC 1759
        for clarification."
    ::= { prtChannel 1 }

prtChannelEntry OBJECT-TYPE
    SYNTAX PrtChannelEntry
    ACCESS not-accessible
    STATUS mandatory
    DESCRIPTION
        "Entries may exist in the table for each device index with a
        device type of 'printer'.  Each channel table entry is
        characterized by a unique protocol stack and/or addressing.
        The channel may also have printer dependent features that are
        associated with a printing language.
        
        NOTE: The above description has been modified from RFC 1759
        for clarification."
    INDEX { hrDeviceIndex, prtChannelIndex }
    ::= { prtChannelTable 1 }

PrtChannelEntry ::= SEQUENCE {
    prtChannelIndex INTEGER,
    prtChannelType PrtChannelTypeTC,
    prtChannelProtocolVersion OCTET STRING,
    prtChannelCurrentJobCntlLangIndex INTEGER,
    prtChannelDefaultPageDescLangIndex INTEGER,
    prtChannelState PrtChannelStateTC,
    prtChannelIfIndex InterfaceIndexOrZero,
    prtChannelStatus PrtSubUnitStatusTC,
    prtChannelInformation OCTET STRING
    }

prtChannelIndex OBJECT-TYPE
    SYNTAX INTEGER(1..65535)
    ACCESS not-accessible
    STATUS mandatory
    DESCRIPTION
        "A unique value used by the printer to identify this data
        channel.  Although these values may change due to a major
        reconfiguration of the device (e.g., the addition of new data
        channels to the printer), values SHOULD remain stable across
        successive printer power cycles.
        
        NOTE: The above description has been modified from RFC 1759
        for clarification."
    ::= { prtChannelEntry 1 }

prtChannelType OBJECT-TYPE
    SYNTAX PrtChannelTypeTC
--    Rsyntax INTEGER {
--        other(1),
--        unknown(2),
--        chSerialPort(3),
--        chParallelPort(4),
--        chIEEE1284Port(5),
--        chSCSIPort(6),
--        chAppleTalkPAP(7),
--        chLPDServer(8),
--        chNetwareRPrinter(9),
--        chNetwarePServer(10),
--        chPort9100(11),
--        chAppSocket(12),
--        chFTP(13),
--        chTFTP(14),
--        chDLCLLCPort(15),
--        chIBM3270(16),
--        chIBM5250(17),
--        chFax(18),
--        chIEEE1394(19),
--        chTransport1(20),
--        chCPAP(21),
--        chDCERemoteProcCall(22),
--        chONCRemoteProcCall(23),
--        chOLE(24),
--        chNamedPipe(25),
--        chPCPrint(26),
--        chServerMessageBlock(27),
--        chDPMF(28),
--        chDLLAPI(29),
--        chVxDAPI(30),
--        chSystemObjectManager(31),
--        chDECLAT(32),
--        chNPAP(33),
--        chUSB(34),
--        chIRDA(35),
--        chPrintXChange(36),
--        chPortTCP(37),
--        chBidirPortTCP(38),
--        chUNPP(39),
--        chAppleTalkADSP(40),
--        chPortSPX(41),
--        chPortHTTP(42),
--        chNDPS(43),
--        chIPP(44),
--        chSMTP(45)
--        }
    ACCESS read-only
    STATUS mandatory
    DESCRIPTION
        "The type of this print data channel.  This object provides the
        linkage to ChannelType-specific groups that may (conceptually)
        extend the prtChannelTable with additional details about that
        channel."
    ::= { prtChannelEntry 2 }

prtChannelProtocolVersion OBJECT-TYPE
    SYNTAX OCTET STRING(SIZE(0..63))
    ACCESS read-only
    STATUS mandatory
    DESCRIPTION
        "The version of the protocol used on this channel.  The format
        used for version numbering depends on prtChannelType."
    ::= { prtChannelEntry 3 }

prtChannelCurrentJobCntlLangIndex OBJECT-TYPE
    SYNTAX INTEGER(0..65535)
    ACCESS read-write
    STATUS mandatory
    DESCRIPTION
        "The value of prtInterpreterIndex corresponding to the Control
        Language Interpreter for this channel.  This interpreter defines
        the syntax used for control functions, such as querying or
        changing environment variables and identifying job boundaries
        (e.g., PJL, PostScript, NPAP).  A value of zero indicates that
        there is no current Job Control Language Interpreter for this
        channel.
        
        NOTE: The above description has been modified from RFC 1759
        for clarification."
    ::= { prtChannelEntry 4 }

prtChannelDefaultPageDescLangIndex OBJECT-TYPE
    SYNTAX INTEGER(0..65535)
    ACCESS read-write
    STATUS mandatory
    DESCRIPTION
        "The value of prtInterpreterIndex corresponding to the Page
        Description Language Interpreter for this channel.  This
        interpreter defines the default Page Description Language
        interpreter to be used for the print data unless the Control
        Language is used to select a specific interpreter (e.g., PCL,
        PostScript Language, auto-sense).  A value of zero indicates
        that there is no default page description language interpreter
        for this channel.
        
        NOTE: The above description has been modified from RFC 1759
        for clarification."
    ::= { prtChannelEntry 5 }

prtChannelState OBJECT-TYPE
    SYNTAX PrtChannelStateTC
--    Rsyntax INTEGER {
--        other(1),
--        printDataAccepted(3),
--        noDataAccepted(4)
--        }
    ACCESS read-write
    STATUS mandatory
    DESCRIPTION
        "The state of this print data channel.  The value determines
        whether control information and print data is allowed through
        this channel or not."
    ::= { prtChannelEntry 6 }

prtChannelIfIndex OBJECT-TYPE
    SYNTAX InterfaceIndexOrZero
--    Rsyntax INTEGER(0..2147483647)
    ACCESS read-write
    STATUS mandatory
    DESCRIPTION
        "The value of ifIndex in the ifTable; see the Interfaces Group
        MIB [RFC2863] which corresponds to this channel.
        When more than one row of the ifTable is relevant, this is the
        index of the row representing the topmost layer in the
        interface hierarchy.  A value of zero indicates that no
        interface is associated with this channel.
        
        NOTE: The above description has been modified from RFC 1759
        
        for clarification."
    ::= { prtChannelEntry 7 }

prtChannelStatus OBJECT-TYPE
    SYNTAX PrtSubUnitStatusTC
--    Rsyntax INTEGER(0..126)
    ACCESS read-only
    STATUS mandatory
    DESCRIPTION
        "The current status of the channel."
    ::= { prtChannelEntry 8 }

prtChannelInformation OBJECT-TYPE
    SYNTAX OCTET STRING(SIZE(0..255))
    ACCESS read-only
    STATUS mandatory
    DESCRIPTION
        "Auxiliary information to allow a printing application to use
        the channel for data submission to the printer.  An application
        capable of using a specific PrtChannelType should be able to
        use the combined information from the prtChannelInformation and
        other channel and interface group objects to 'bootstrap' its
        use of the channel.  prtChannelInformation is not intended to
        provide a general channel description, nor to provide
        information that is available once the channel is in use.
        
        The encoding and interpretation of the prtChannelInformation
        object is specific to channel type.  The description of each
        PrtChannelType enum value for which prtChannelInformation is
        defined specifies the appropriate encoding and interpretation,
        including interaction with other objects.  For channel types
        that do not specify a prtChannelInformation value, its value
        shall be null (0 length).
        
        When a new PrtChannelType enumeration value is registered, its
        accompanying description must specify the encoding and
        interpretation of the prtChannelInformation value for the
        channel type.  prtChannelInformation semantics for an existing
        PrtChannelType may be added or amended in the same manner as
        described in section 2.4.1 for type 2 enumeration values.
        
        The prtChannelInformation specifies values for a collection of
        channel attributes, represented as text according to the
        following rules:
        
        1. The prtChannelInformation is not affected by localization.
        
        2. The prtChannelInformation is a list of entries representing
        the attribute values.  Each entry consists of the following
        
        items, in order:
        
        a. A keyword, composed of alphabetic characters (A-Z, a-z)
        represented by their NVT ASCII [RFC854] codes, that
        identifies a channel attribute,
        
        b. The NVT ASCII code for an Equals Sign (=) (code 61) to
        delimit the keyword,
        
        c. A data value encoded using rules specific to the
        PrtChannelType to with the prtChannelInformation applies which
        must in no case allow an octet with value 10 (the NVT ASCII
        Line Feed code),
        
        d. the NVT ASCII code for a Line Feed character (code 10) to
        delimit the data value.
        
        No other octets shall be present.
        
        Keywords are case-sensitive.  Conventionally, keywords are
        capitalized (including each word of a multi-word keyword) and
        since they occupy space in the prtChannelInformation, they are
        kept short.
        
        3. If a channel attribute has multiple values, it is
        represented by multiple entries with the same keyword, each
        specifying one value. Otherwise, there shall be at most one
        entry for each attribute.
        
        4. By default, entries may appear in any order.  If there are
        ordering constraints for particular entries, these must be
        specified in their definitions.
        
        5. The prtChannelInformation value by default consists of text
        represented by NVT ASCII graphics character codes.  However,
        other representations may be specified:
        
        a. In cases where the prtChannelInformation value contains
        information not normally coded in textual form, whatever
        symbolic representation is conventionally used for the
        information should be used for encoding the
        prtChannelInformation value.  (For instance, a binary port value
        might be represented as a decimal number using NVT ASCII
        codes.)  Such encoding must be specified in the definition of
        the value.
        
        b. The value may contain textual information in a character set
        other than NVT ASCII graphics characters.  (For instance, an
        
        identifier might consist of ISO 10646 text encoded using the
        UTF-8 encoding scheme.)  Such a character set and its encoding
        must be specified in the definition of the value.
        
        6. For each PrtChannelType for which prtChannelInformation
        entries are defined, the descriptive text associated with the
        PrtChannelType enumeration value shall specify the following
        information for each entry:
        
        Title:        Brief description phrase, e.g.: 'Port name',
                      'Service Name', etc.
        
        Keyword:      The keyword value, e.g.: 'Port' or 'Service'
        
        Syntax:       The encoding of the entry value if it cannot be
                      directly represented by NVT ASCII.
        
        Status:       'Mandatory', 'Optional', or 'Conditionally
                      Mandatory'
        
        Multiplicity: 'Single' or 'Multiple' to indicate whether the
                      entry may be present multiple times.
        
        Description:  Description of the use of the entry, other
                      information required to complete the definition
                      (e.g.: ordering constraints, interactions between
                      entries).
        
        Applications that interpret prtChannelInformation should ignore
        unrecognized entries, so they are not affected if new entry
        types are added."
    ::= { prtChannelEntry 9 }

prtInterpreterTable OBJECT-TYPE
    SYNTAX SEQUENCE OF PrtInterpreterEntry
    ACCESS not-accessible
    STATUS mandatory
    DESCRIPTION
        "The interpreter table is a table representing the
        interpreters in the printer.  An entry shall be placed in the
        interpreter table for each interpreter on the printer.
        
        NOTE: The above description has been modified from RFC 1759
        for clarification."
    ::= { prtInterpreter 1 }

prtInterpreterEntry OBJECT-TYPE
    SYNTAX PrtInterpreterEntry
    ACCESS not-accessible
    STATUS mandatory
    DESCRIPTION
        "Entries may exist in the table for each device index with a
        device type of 'printer'.  Each table entry provides a complete
        description of the interpreter, including version information,
        rendering resolutions, default character sets, output
        orientation, and communication capabilities.
        
        NOTE: The above description has been modified from RFC 1759
        for clarification."
    INDEX { hrDeviceIndex, prtInterpreterIndex }
    ::= { prtInterpreterTable 1 }

PrtInterpreterEntry ::= SEQUENCE {
    prtInterpreterIndex INTEGER,
    prtInterpreterLangFamily PrtInterpreterLangFamilyTC,
    prtInterpreterLangLevel OCTET STRING,
    prtInterpreterLangVersion OCTET STRING,
    prtInterpreterDescription PrtLocalizedDescriptionStringTC,
    prtInterpreterVersion OCTET STRING,
    prtInterpreterDefaultOrientation PrtPrintOrientationTC,
    prtInterpreterFeedAddressability INTEGER,
    prtInterpreterXFeedAddressability INTEGER,
    prtInterpreterDefaultCharSetIn IANACharset,
    prtInterpreterDefaultCharSetOut IANACharset,
    prtInterpreterTwoWay PrtInterpreterTwoWayTC
    }

prtInterpreterIndex OBJECT-TYPE
    SYNTAX INTEGER(1..65535)
    ACCESS not-accessible
    STATUS mandatory
    DESCRIPTION
        "A unique value for each PDL or control language for which
        there exists an interpreter or emulator in the printer.  The
        value is used to identify this interpreter.  Although these
        values may change due to a major reconfiguration of the device
        (e.g., the addition of new interpreters to the printer), values
        SHOULD remain stable across successive printer power cycles.
        
        NOTE: The above description has been modified from RFC 1759
        for clarification."
    ::= { prtInterpreterEntry 1 }

prtInterpreterLangFamily OBJECT-TYPE
    SYNTAX PrtInterpreterLangFamilyTC
--    Rsyntax INTEGER {
--        other(1),
--        unknown(2),
--        langPCL(3),
--        langHPGL(4),
--        langPJL(5),
--        langPS(6),
--        langIPDS(7),
--        langPPDS(8),
--        langEscapeP(9),
--        langEpson(10),
--        langDDIF(11),
--        langInterpress(12),
--        langISO6429(13),
--        langLineData(14),
--        langMODCA(15),
--        langREGIS(16),
--        langSCS(17),
--        langSPDL(18),
--        langTEK4014(19),
--        langPDS(20),
--        langIGP(21),
--        langCodeV(22),
--        langDSCDSE(23),
--        langWPS(24),
--        langLN03(25),
--        langCCITT(26),
--        langQUIC(27),
--        langCPAP(28),
--        langDecPPL(29),
--        langSimpleText(30),
--        langNPAP(31),
--        langDOC(32),
--        langimPress(33),
--        langPinwriter(34),
--        langNPDL(35),
--        langNEC201PL(36),
--        langAutomatic(37),
--        langPages(38),
--        langLIPS(39),
--        langTIFF(40),
--        langDiagnostic(41),
--        langPSPrinter(42),
--        langCaPSL(43),
--        langEXCL(44),
--        langLCDS(45),
--        langXES(46),
--        langPCLXL(47),
--        langART(48),
--        langTIPSI(49),
--        langPrescribe(50),
--        langLinePrinter(51),
--        langIDP(52),
--        langXJCL(53),
--        langPDF(54),
--        langRPDL(55),
--        langIntermecIPL(56),
--        langUBIFingerprint(57),
--        langUBIDirectProtocol(58),
--        langFujitsu(59),
--        langCGM(60),
--        langJPEG(61),
--        langCALS1(62),
--        langCALS2(63),
--        langNIRS(64),
--        langC4(65)
--        }
    ACCESS read-only
    STATUS mandatory
    DESCRIPTION
        "The family name of a Page Description Language (PDL) or
        control language which this interpreter in the printer can
        interpret or emulate.
        
        NOTE: The above description has been modified from RFC 1759
        for clarification."
    ::= { prtInterpreterEntry 2 }

prtInterpreterLangLevel OBJECT-TYPE
    SYNTAX OCTET STRING(SIZE(0..31))
    ACCESS read-only
    STATUS mandatory
    DESCRIPTION
        "The level of the language which this interpreter is
        interpreting or emulating.  This might contain a value like
        '5e'for an interpreter which is emulating level 5e of the PCL
        language.  It might contain '2' for an interpreter which is
        emulating level 2 of the PostScript language.  Similarly it
        might contain '2' for an interpreter which is emulating level 2
        of the HPGL language."
    ::= { prtInterpreterEntry 3 }

prtInterpreterLangVersion OBJECT-TYPE
    SYNTAX OCTET STRING(SIZE(0..31))
    ACCESS read-only
    STATUS mandatory
    DESCRIPTION
        "The date code or version of the language which this
        interpreter is interpreting or emulating."
    ::= { prtInterpreterEntry 4 }

prtInterpreterDescription OBJECT-TYPE
    SYNTAX PrtLocalizedDescriptionStringTC
--    Rsyntax OCTET STRING(SIZE(0..255))
    ACCESS read-only
    STATUS mandatory
    DESCRIPTION
        "A string to identify this interpreter in the localization
        specified by prtGeneralCurrentLocalization as opposed to the
        language which is being interpreted.  It is anticipated that
        this string will allow manufacturers to unambiguously identify
        their interpreters."
    ::= { prtInterpreterEntry 5 }

prtInterpreterVersion OBJECT-TYPE
    SYNTAX OCTET STRING(SIZE(0..31))
    ACCESS read-only
    STATUS mandatory
    DESCRIPTION
        "The date code, version number, or other product specific
        information tied to this interpreter.  This value is associated
        with the interpreter, rather than with the version of the
        language which is being interpreted or emulated."
    ::= { prtInterpreterEntry 6 }

prtInterpreterDefaultOrientation OBJECT-TYPE
    SYNTAX PrtPrintOrientationTC
--    Rsyntax INTEGER {
--        other(1),
--        portrait(3),
--        landscape(4)
--        }
    ACCESS read-write
    STATUS mandatory
    DESCRIPTION
        "The current orientation default for this interpreter.  This
        value may be overridden for a particular job (e.g., by a
        command in the input data stream)."
    ::= { prtInterpreterEntry 7 }

prtInterpreterFeedAddressability OBJECT-TYPE
    SYNTAX INTEGER(-2..2147483647)
    ACCESS read-only
    STATUS mandatory
    DESCRIPTION
        "The maximum interpreter addressability in the feed
        direction in 10000 prtMarkerAddressabilityUnits (as specified
        by prtMarkerDefaultIndex) for this interpreter.  The
        value (-1) means other and specifically indicates that the
        sub-unit places no restrictions on this parameter.  The value
        (-2) means unknown.
        
        NOTE: The above description has been modified from RFC 1759
        for clarification."
    ::= { prtInterpreterEntry 8 }

prtInterpreterXFeedAddressability OBJECT-TYPE
    SYNTAX INTEGER(-2..2147483647)
    ACCESS read-only
    STATUS mandatory
    DESCRIPTION
        "The maximum interpreter addressability in the cross feed
        direction in 10000 prtMarkerAddressabilityUnits (as specified
        by prtMarkerDefaultIndex) for this interpreter.  The
        value (-1) means other and specifically indicates that the
        sub-unit places no restrictions on this parameter.  The value
        (-2) means unknown.
        
        NOTE: The above description has been modified from RFC 1759
        for clarification."
    ::= { prtInterpreterEntry 9 }

prtInterpreterDefaultCharSetIn OBJECT-TYPE
    SYNTAX IANACharset
--    Rsyntax INTEGER {
--        other(1),
--        unknown(2),
--        csASCII(3),
--        csISOLatin1(4),
--        csISOLatin2(5),
--        csISOLatin3(6),
--        csISOLatin4(7),
--        csISOLatinCyrillic(8),
--        csISOLatinArabic(9),
--        csISOLatinGreek(10),
--        csISOLatinHebrew(11),
--        csISOLatin5(12),
--        csISOLatin6(13),
--        csISOTextComm(14),
--        csHalfWidthKatakana(15),
--        csJISEncoding(16),
--        csShiftJIS(17),
--        csEUCPkdFmtJapanese(18),
--        csEUCFixWidJapanese(19),
--        csISO4UnitedKingdom(20),
--        csISO11SwedishForNames(21),
--        csISO15Italian(22),
--        csISO17Spanish(23),
--        csISO21German(24),
--        csISO60DanishNorwegian(25),
--        csISO69French(26),
--        csISO10646UTF1(27),
--        csISO646basic1983(28),
--        csINVARIANT(29),
--        csISO2IntlRefVersion(30),
--        csNATSSEFI(31),
--        csNATSSEFIADD(32),
--        csNATSDANO(33),
--        csNATSDANOADD(34),
--        csISO10Swedish(35),
--        csKSC56011987(36),
--        csISO2022KR(37),
--        csEUCKR(38),
--        csISO2022JP(39),
--        csISO2022JP2(40),
--        csISO13JISC6220jp(41),
--        csISO14JISC6220ro(42),
--        csISO16Portuguese(43),
--        csISO18Greek7Old(44),
--        csISO19LatinGreek(45),
--        csISO25French(46),
--        csISO27LatinGreek1(47),
--        csISO5427Cyrillic(48),
--        csISO42JISC62261978(49),
--        csISO47BSViewdata(50),
--        csISO49INIS(51),
--        csISO50INIS8(52),
--        csISO51INISCyrillic(53),
--        csISO54271981(54),
--        csISO5428Greek(55),
--        csISO57GB1988(56),
--        csISO58GB231280(57),
--        csISO61Norwegian2(58),
--        csISO70VideotexSupp1(59),
--        csISO84Portuguese2(60),
--        csISO85Spanish2(61),
--        csISO86Hungarian(62),
--        csISO87JISX0208(63),
--        csISO88Greek7(64),
--        csISO89ASMO449(65),
--        csISO90(66),
--        csISO91JISC62291984a(67),
--        csISO92JISC62991984b(68),
--        csISO93JIS62291984badd(69),
--        csISO94JIS62291984hand(70),
--        csISO95JIS62291984handadd(71),
--        csISO96JISC62291984kana(72),
--        csISO2033(73),
--        csISO99NAPLPS(74),
--        csISO102T617bit(75),
--        csISO103T618bit(76),
--        csISO111ECMACyrillic(77),
--        csa71(78),
--        csa72(79),
--        csISO123CSAZ24341985gr(80),
--        csISO88596E(81),
--        csISO88596I(82),
--        csISO128T101G2(83),
--        csISO88598E(84),
--        csISO88598I(85),
--        csISO139CSN369103(86),
--        csISO141JUSIB1002(87),
--        csISO143IECP271(88),
--        csISO146Serbian(89),
--        csISO147Macedonian(90),
--        csISO150(91),
--        csISO151Cuba(92),
--        csISO6937Add(93),
--        csISO153GOST1976874(94),
--        csISO8859Supp(95),
--        csISO10367Box(96),
--        csISO158Lap(97),
--        csISO159JISX02121990(98),
--        csISO646Danish(99),
--        csUSDK(100),
--        csDKUS(101),
--        csKSC5636(102),
--        csUnicode11UTF7(103),
--        csISO2022CN(104),
--        csISO2022CNEXT(105),
--        csUTF8(106),
--        csISO885913(109),
--        csISO885914(110),
--        csISO885915(111),
--        csISO885916(112),
--        csGBK(113),
--        csGB18030(114),
--        csOSDEBCDICDF0415(115),
--        csOSDEBCDICDF03IRV(116),
--        csOSDEBCDICDF041(117),
--        csUnicode(1000),
--        csUCS4(1001),
--        csUnicodeASCII(1002),
--        csUnicodeLatin1(1003),
--        csUnicodeIBM1261(1005),
--        csUnicodeIBM1268(1006),
--        csUnicodeIBM1276(1007),
--        csUnicodeIBM1264(1008),
--        csUnicodeIBM1265(1009),
--        csUnicode11(1010),
--        csSCSU(1011),
--        csUTF7(1012),
--        csUTF16BE(1013),
--        csUTF16LE(1014),
--        csUTF16(1015),
--        csCESU8(1016),
--        csUTF32(1017),
--        csUTF32BE(1018),
--        csUTF32LE(1019),
--        csBOCU1(1020),
--        csWindows30Latin1(2000),
--        csWindows31Latin1(2001),
--        csWindows31Latin2(2002),
--        csWindows31Latin5(2003),
--        csHPRoman8(2004),
--        csAdobeStandardEncoding(2005),
--        csVenturaUS(2006),
--        csVenturaInternational(2007),
--        csDECMCS(2008),
--        csPC850Multilingual(2009),
--        csPCp852(2010),
--        csPC8CodePage437(2011),
--        csPC8DanishNorwegian(2012),
--        csPC862LatinHebrew(2013),
--        csPC8Turkish(2014),
--        csIBMSymbols(2015),
--        csIBMThai(2016),
--        csHPLegal(2017),
--        csHPPiFont(2018),
--        csHPMath8(2019),
--        csHPPSMath(2020),
--        csHPDesktop(2021),
--        csVenturaMath(2022),
--        csMicrosoftPublishing(2023),
--        csWindows31J(2024),
--        csGB2312(2025),
--        csBig5(2026),
--        csMacintosh(2027),
--        csIBM037(2028),
--        csIBM038(2029),
--        csIBM273(2030),
--        csIBM274(2031),
--        csIBM275(2032),
--        csIBM277(2033),
--        csIBM278(2034),
--        csIBM280(2035),
--        csIBM281(2036),
--        csIBM284(2037),
--        csIBM285(2038),
--        csIBM290(2039),
--        csIBM297(2040),
--        csIBM420(2041),
--        csIBM423(2042),
--        csIBM424(2043),
--        csIBM500(2044),
--        csIBM851(2045),
--        csIBM855(2046),
--        csIBM857(2047),
--        csIBM860(2048),
--        csIBM861(2049),
--        csIBM863(2050),
--        csIBM864(2051),
--        csIBM865(2052),
--        csIBM868(2053),
--        csIBM869(2054),
--        csIBM870(2055),
--        csIBM871(2056),
--        csIBM880(2057),
--        csIBM891(2058),
--        csIBM903(2059),
--        csIBBM904(2060),
--        csIBM905(2061),
--        csIBM918(2062),
--        csIBM1026(2063),
--        csIBMEBCDICATDE(2064),
--        csEBCDICATDEA(2065),
--        csEBCDICCAFR(2066),
--        csEBCDICDKNO(2067),
--        csEBCDICDKNOA(2068),
--        csEBCDICFISE(2069),
--        csEBCDICFISEA(2070),
--        csEBCDICFR(2071),
--        csEBCDICIT(2072),
--        csEBCDICPT(2073),
--        csEBCDICES(2074),
--        csEBCDICESA(2075),
--        csEBCDICESS(2076),
--        csEBCDICUK(2077),
--        csEBCDICUS(2078),
--        csUnknown8BiT(2079),
--        csMnemonic(2080),
--        csMnem(2081),
--        csVISCII(2082),
--        csVIQR(2083),
--        csKOI8R(2084),
--        csHZGB2312(2085),
--        csIBM866(2086),
--        csPC775Baltic(2087),
--        csKOI8U(2088),
--        csIBM00858(2089),
--        csIBM00924(2090),
--        csIBM01140(2091),
--        csIBM01141(2092),
--        csIBM01142(2093),
--        csIBM01143(2094),
--        csIBM01144(2095),
--        csIBM01145(2096),
--        csIBM01146(2097),
--        csIBM01147(2098),
--        csIBM01148(2099),
--        csIBM01149(2100),
--        csBig5HKSCS(2101),
--        csIBM1047(2102),
--        csPTCP154(2103),
--        csAmiga1251(2104),
--        csKOI7switched(2105),
--        cswindows1250(2250),
--        cswindows1251(2251),
--        cswindows1252(2252),
--        cswindows1253(2253),
--        cswindows1254(2254),
--        cswindows1255(2255),
--        cswindows1256(2256),
--        cswindows1257(2257),
--        cswindows1258(2258),
--        csTIS620(2259),
--        reserved(3000)
--        }
    ACCESS read-write
    STATUS mandatory
    DESCRIPTION
        "The default coded character set for input octets encountered
        outside a context in which the Page Description Language
        established the interpretation of the octets.  (Input octets are
        presented to the interpreter through a path defined in the
        channel group.)"
    ::= { prtInterpreterEntry 10 }

prtInterpreterDefaultCharSetOut OBJECT-TYPE
    SYNTAX IANACharset
--    Rsyntax INTEGER {
--        other(1),
--        unknown(2),
--        csASCII(3),
--        csISOLatin1(4),
--        csISOLatin2(5),
--        csISOLatin3(6),
--        csISOLatin4(7),
--        csISOLatinCyrillic(8),
--        csISOLatinArabic(9),
--        csISOLatinGreek(10),
--        csISOLatinHebrew(11),
--        csISOLatin5(12),
--        csISOLatin6(13),
--        csISOTextComm(14),
--        csHalfWidthKatakana(15),
--        csJISEncoding(16),
--        csShiftJIS(17),
--        csEUCPkdFmtJapanese(18),
--        csEUCFixWidJapanese(19),
--        csISO4UnitedKingdom(20),
--        csISO11SwedishForNames(21),
--        csISO15Italian(22),
--        csISO17Spanish(23),
--        csISO21German(24),
--        csISO60DanishNorwegian(25),
--        csISO69French(26),
--        csISO10646UTF1(27),
--        csISO646basic1983(28),
--        csINVARIANT(29),
--        csISO2IntlRefVersion(30),
--        csNATSSEFI(31),
--        csNATSSEFIADD(32),
--        csNATSDANO(33),
--        csNATSDANOADD(34),
--        csISO10Swedish(35),
--        csKSC56011987(36),
--        csISO2022KR(37),
--        csEUCKR(38),
--        csISO2022JP(39),
--        csISO2022JP2(40),
--        csISO13JISC6220jp(41),
--        csISO14JISC6220ro(42),
--        csISO16Portuguese(43),
--        csISO18Greek7Old(44),
--        csISO19LatinGreek(45),
--        csISO25French(46),
--        csISO27LatinGreek1(47),
--        csISO5427Cyrillic(48),
--        csISO42JISC62261978(49),
--        csISO47BSViewdata(50),
--        csISO49INIS(51),
--        csISO50INIS8(52),
--        csISO51INISCyrillic(53),
--        csISO54271981(54),
--        csISO5428Greek(55),
--        csISO57GB1988(56),
--        csISO58GB231280(57),
--        csISO61Norwegian2(58),
--        csISO70VideotexSupp1(59),
--        csISO84Portuguese2(60),
--        csISO85Spanish2(61),
--        csISO86Hungarian(62),
--        csISO87JISX0208(63),
--        csISO88Greek7(64),
--        csISO89ASMO449(65),
--        csISO90(66),
--        csISO91JISC62291984a(67),
--        csISO92JISC62991984b(68),
--        csISO93JIS62291984badd(69),
--        csISO94JIS62291984hand(70),
--        csISO95JIS62291984handadd(71),
--        csISO96JISC62291984kana(72),
--        csISO2033(73),
--        csISO99NAPLPS(74),
--        csISO102T617bit(75),
--        csISO103T618bit(76),
--        csISO111ECMACyrillic(77),
--        csa71(78),
--        csa72(79),
--        csISO123CSAZ24341985gr(80),
--        csISO88596E(81),
--        csISO88596I(82),
--        csISO128T101G2(83),
--        csISO88598E(84),
--        csISO88598I(85),
--        csISO139CSN369103(86),
--        csISO141JUSIB1002(87),
--        csISO143IECP271(88),
--        csISO146Serbian(89),
--        csISO147Macedonian(90),
--        csISO150(91),
--        csISO151Cuba(92),
--        csISO6937Add(93),
--        csISO153GOST1976874(94),
--        csISO8859Supp(95),
--        csISO10367Box(96),
--        csISO158Lap(97),
--        csISO159JISX02121990(98),
--        csISO646Danish(99),
--        csUSDK(100),
--        csDKUS(101),
--        csKSC5636(102),
--        csUnicode11UTF7(103),
--        csISO2022CN(104),
--        csISO2022CNEXT(105),
--        csUTF8(106),
--        csISO885913(109),
--        csISO885914(110),
--        csISO885915(111),
--        csISO885916(112),
--        csGBK(113),
--        csGB18030(114),
--        csOSDEBCDICDF0415(115),
--        csOSDEBCDICDF03IRV(116),
--        csOSDEBCDICDF041(117),
--        csUnicode(1000),
--        csUCS4(1001),
--        csUnicodeASCII(1002),
--        csUnicodeLatin1(1003),
--        csUnicodeIBM1261(1005),
--        csUnicodeIBM1268(1006),
--        csUnicodeIBM1276(1007),
--        csUnicodeIBM1264(1008),
--        csUnicodeIBM1265(1009),
--        csUnicode11(1010),
--        csSCSU(1011),
--        csUTF7(1012),
--        csUTF16BE(1013),
--        csUTF16LE(1014),
--        csUTF16(1015),
--        csCESU8(1016),
--        csUTF32(1017),
--        csUTF32BE(1018),
--        csUTF32LE(1019),
--        csBOCU1(1020),
--        csWindows30Latin1(2000),
--        csWindows31Latin1(2001),
--        csWindows31Latin2(2002),
--        csWindows31Latin5(2003),
--        csHPRoman8(2004),
--        csAdobeStandardEncoding(2005),
--        csVenturaUS(2006),
--        csVenturaInternational(2007),
--        csDECMCS(2008),
--        csPC850Multilingual(2009),
--        csPCp852(2010),
--        csPC8CodePage437(2011),
--        csPC8DanishNorwegian(2012),
--        csPC862LatinHebrew(2013),
--        csPC8Turkish(2014),
--        csIBMSymbols(2015),
--        csIBMThai(2016),
--        csHPLegal(2017),
--        csHPPiFont(2018),
--        csHPMath8(2019),
--        csHPPSMath(2020),
--        csHPDesktop(2021),
--        csVenturaMath(2022),
--        csMicrosoftPublishing(2023),
--        csWindows31J(2024),
--        csGB2312(2025),
--        csBig5(2026),
--        csMacintosh(2027),
--        csIBM037(2028),
--        csIBM038(2029),
--        csIBM273(2030),
--        csIBM274(2031),
--        csIBM275(2032),
--        csIBM277(2033),
--        csIBM278(2034),
--        csIBM280(2035),
--        csIBM281(2036),
--        csIBM284(2037),
--        csIBM285(2038),
--        csIBM290(2039),
--        csIBM297(2040),
--        csIBM420(2041),
--        csIBM423(2042),
--        csIBM424(2043),
--        csIBM500(2044),
--        csIBM851(2045),
--        csIBM855(2046),
--        csIBM857(2047),
--        csIBM860(2048),
--        csIBM861(2049),
--        csIBM863(2050),
--        csIBM864(2051),
--        csIBM865(2052),
--        csIBM868(2053),
--        csIBM869(2054),
--        csIBM870(2055),
--        csIBM871(2056),
--        csIBM880(2057),
--        csIBM891(2058),
--        csIBM903(2059),
--        csIBBM904(2060),
--        csIBM905(2061),
--        csIBM918(2062),
--        csIBM1026(2063),
--        csIBMEBCDICATDE(2064),
--        csEBCDICATDEA(2065),
--        csEBCDICCAFR(2066),
--        csEBCDICDKNO(2067),
--        csEBCDICDKNOA(2068),
--        csEBCDICFISE(2069),
--        csEBCDICFISEA(2070),
--        csEBCDICFR(2071),
--        csEBCDICIT(2072),
--        csEBCDICPT(2073),
--        csEBCDICES(2074),
--        csEBCDICESA(2075),
--        csEBCDICESS(2076),
--        csEBCDICUK(2077),
--        csEBCDICUS(2078),
--        csUnknown8BiT(2079),
--        csMnemonic(2080),
--        csMnem(2081),
--        csVISCII(2082),
--        csVIQR(2083),
--        csKOI8R(2084),
--        csHZGB2312(2085),
--        csIBM866(2086),
--        csPC775Baltic(2087),
--        csKOI8U(2088),
--        csIBM00858(2089),
--        csIBM00924(2090),
--        csIBM01140(2091),
--        csIBM01141(2092),
--        csIBM01142(2093),
--        csIBM01143(2094),
--        csIBM01144(2095),
--        csIBM01145(2096),
--        csIBM01146(2097),
--        csIBM01147(2098),
--        csIBM01148(2099),
--        csIBM01149(2100),
--        csBig5HKSCS(2101),
--        csIBM1047(2102),
--        csPTCP154(2103),
--        csAmiga1251(2104),
--        csKOI7switched(2105),
--        cswindows1250(2250),
--        cswindows1251(2251),
--        cswindows1252(2252),
--        cswindows1253(2253),
--        cswindows1254(2254),
--        cswindows1255(2255),
--        cswindows1256(2256),
--        cswindows1257(2257),
--        cswindows1258(2258),
--        csTIS620(2259),
--        reserved(3000)
--        }
    ACCESS read-write
    STATUS mandatory
    DESCRIPTION
        "The default character set for data coming from this
        interpreter through the printer's output channel (i.e. the
        'backchannel')."
    ::= { prtInterpreterEntry 11 }

prtInterpreterTwoWay OBJECT-TYPE
    SYNTAX PrtInterpreterTwoWayTC
--    Rsyntax INTEGER {
--        yes(3),
--        no(4)
--        }
    ACCESS read-only
    STATUS mandatory
    DESCRIPTION
        "Indicates whether or not this interpreter returns information
        back to the host."
    ::= { prtInterpreterEntry 12 }

prtConsoleDisplayBufferTable OBJECT-TYPE
    SYNTAX SEQUENCE OF PrtConsoleDisplayBufferEntry
    ACCESS not-accessible
    STATUS mandatory
    DESCRIPTION
        "Physical display buffer for printer console display or
        operator panel
        
        NOTE: The above description has been modified from RFC 1759
        for clarification."
    ::= { prtConsoleDisplayBuffer 5 }

prtConsoleDisplayBufferEntry OBJECT-TYPE
    SYNTAX PrtConsoleDisplayBufferEntry
    ACCESS not-accessible
    STATUS mandatory
    DESCRIPTION
        "This table contains one entry for each physical line on
        the display.  Lines cannot be added or deleted.  Entries may
        exist in the table for each device index with a device type of
        'printer'.
        
        NOTE: The above description has been modified from RFC 1759
        
        for clarification."
    INDEX { hrDeviceIndex, prtConsoleDisplayBufferIndex }
    ::= { prtConsoleDisplayBufferTable 1 }

PrtConsoleDisplayBufferEntry ::= SEQUENCE {
    prtConsoleDisplayBufferIndex INTEGER,
    prtConsoleDisplayBufferText PrtConsoleDescriptionStringTC
    }

prtConsoleDisplayBufferIndex OBJECT-TYPE
    SYNTAX INTEGER(1..65535)
    ACCESS not-accessible
    STATUS mandatory
    DESCRIPTION
        "A unique value for each console line in the printer.  The value
        is used to identify this console line.  Although these values
        may change due to a major reconfiguration of the device (e.g.,
        the addition of new console lines to the printer).  Values
        SHOULD remain stable across successive printer power cycles.
        
        NOTE: The above description has been modified from RFC 1759
        for clarification."
    ::= { prtConsoleDisplayBufferEntry 1 }

prtConsoleDisplayBufferText OBJECT-TYPE
    SYNTAX PrtConsoleDescriptionStringTC
--    Rsyntax OCTET STRING(SIZE(0..255))
    ACCESS read-write
    STATUS mandatory
    DESCRIPTION
        "The content of a line in the logical display buffer of
        the operator's console of the printer.  When a write
        operation occurs, normally a critical message, to one of
        the LineText strings, the agent should make that line
        displayable if a physical display is present.  Writing a zero
        length string clears the line.  It is an implementation-
        specific matter as to whether the agent allows a line to be
        overwritten before it has been cleared.  Printer generated
        strings shall be in the localization specified by
        prtConsoleLocalization.Management Application generated strings
        should be localized by the Management Application."
    ::= { prtConsoleDisplayBufferEntry 2 }

prtConsoleLightTable OBJECT-TYPE
    SYNTAX SEQUENCE OF PrtConsoleLightEntry
    ACCESS not-accessible
    STATUS mandatory
    DESCRIPTION
        "The console light table provides a description and state
        information for each light present on the printer console.
        
        NOTE: The above description has been modified from RFC 1759
        for clarification."
    ::= { prtConsoleLights 6 }

prtConsoleLightEntry OBJECT-TYPE
    SYNTAX PrtConsoleLightEntry
    ACCESS not-accessible
    STATUS mandatory
    DESCRIPTION
        "Entries may exist in the table for each device index with a
        device type of 'printer'.
        
        NOTE: The above description has been modified from RFC 1759
        for clarification."
    INDEX { hrDeviceIndex, prtConsoleLightIndex }
    ::= { prtConsoleLightTable 1 }

PrtConsoleLightEntry ::= SEQUENCE {
    prtConsoleLightIndex INTEGER,
    prtConsoleOnTime INTEGER,
    prtConsoleOffTime INTEGER,
    prtConsoleColor PrtConsoleColorTC,
    prtConsoleDescription PrtConsoleDescriptionStringTC
    }

prtConsoleLightIndex OBJECT-TYPE
    SYNTAX INTEGER(1..65535)
    ACCESS not-accessible
    STATUS mandatory
    DESCRIPTION
        "A unique value used by the printer to identify this light.
        Although these values may change due to a major
        reconfiguration of the device (e.g., the addition of new lights
        to the printer).  Values SHOULD remain stable across successive
        printer power cycles.
        
        NOTE: The above description has been modified from RFC 1759
        for clarification."
    ::= { prtConsoleLightEntry 1 }

prtConsoleOnTime OBJECT-TYPE
    SYNTAX INTEGER(0..2147483647)
    ACCESS read-write
    STATUS mandatory
    DESCRIPTION
        "This object, in conjunction with prtConsoleOffTime, defines
        the current status of the light.  If both prtConsoleOnTime and
        prtConsoleOffTime are non-zero, the lamp is blinking and the
        values presented define the on time and off time, respectively,
        in milliseconds.  If prtConsoleOnTime is zero and
        prtConsoleOffTime is non-zero, the lamp is off.  If
        prtConsoleOffTime is zero and prtConsoleOnTime is non-zero, the
        lamp is on.  If both values are zero the lamp is off.
        
        NOTE: The above description has been modified from RFC 1759
        for clarification."
    ::= { prtConsoleLightEntry 2 }

prtConsoleOffTime OBJECT-TYPE
    SYNTAX INTEGER(0..2147483647)
    ACCESS read-write
    STATUS mandatory
    DESCRIPTION
        "This object, in conjunction with prtConsoleOnTime, defines the
        current status of the light.  If both prtConsoleOnTime and
        prtConsoleOffTime are non-zero, the lamp is blinking and the
        values presented define the on time and off time, respectively,
        in milliseconds.  If prtConsoleOnTime is zero and
        prtConsoleOffTime is non-zero, the lamp is off.  If
        prtConsoleOffTime is zero and prtConsoleOnTime is non-zero, the
        lamp is on.  If both values are zero the lamp is off.
        
        NOTE: The above description has been modified from RFC 1759
        for clarification."
    ::= { prtConsoleLightEntry 3 }

prtConsoleColor OBJECT-TYPE
    SYNTAX PrtConsoleColorTC
--    Rsyntax INTEGER {
--        other(1),
--        unknown(2),
--        white(3),
--        red(4),
--        green(5),
--        blue(6),
--        cyan(7),
--        magenta(8),
--        yellow(9),
--        orange(10)
--        }
    ACCESS read-only
    STATUS mandatory
    DESCRIPTION
        "The color of this light."
    ::= { prtConsoleLightEntry 4 }

prtConsoleDescription OBJECT-TYPE
    SYNTAX PrtConsoleDescriptionStringTC
--    Rsyntax OCTET STRING(SIZE(0..255))
    ACCESS read-only
    STATUS mandatory
    DESCRIPTION
        "The vendor description or label of this light in the
        localization specified by prtConsoleLocalization."
    ::= { prtConsoleLightEntry 5 }

prtAlertTable OBJECT-TYPE
    SYNTAX SEQUENCE OF PrtAlertEntry
    ACCESS not-accessible
    STATUS mandatory
    DESCRIPTION
        "The prtAlertTable lists all the critical and non-critical
        alerts currently active in the printer.  A critical alert is
        one that stops the printer from printing immediately and
        printing can not continue until the critical alert condition
        is eliminated.  Non-critical alerts are those items that do
        not stop printing but may at some future time.
        
        NOTE: The above description has been modified from RFC 1759
        for clarification."
    ::= { prtAlert 1 }

prtAlertEntry OBJECT-TYPE
    SYNTAX PrtAlertEntry
    ACCESS not-accessible
    STATUS mandatory
    DESCRIPTION
        "Entries may exist in the table for each device
        index with a device type of 'printer'.
        
        NOTE: The above description has been modified from RFC 1759
        for clarification."
    INDEX { hrDeviceIndex, prtAlertIndex }
    ::= { prtAlertTable 1 }

PrtAlertEntry ::= SEQUENCE {
    prtAlertIndex INTEGER,
    prtAlertSeverityLevel PrtAlertSeverityLevelTC,
    prtAlertTrainingLevel PrtAlertTrainingLevelTC,
    prtAlertGroup PrtAlertGroupTC,
    prtAlertGroupIndex INTEGER,
    prtAlertLocation INTEGER,
    prtAlertCode PrtAlertCodeTC,
    prtAlertDescription PrtLocalizedDescriptionStringTC,
    prtAlertTime TimeTicks
    }

prtAlertIndex OBJECT-TYPE
    SYNTAX INTEGER(1..2147483647)
    ACCESS read-only
    STATUS mandatory
    DESCRIPTION
        "The index value used to determine which alerts have been added
        or removed from the alert table.  This is an incrementing
        integer initialized to 1 when the printer is reset.  (i.e., The
        first event placed in the alert table after a reset of the
        printer shall have an index value of 1.)  When the printer adds
        an alert to the table, that alert is assigned the next higher
        integer value from the last item entered into the table.  If
        the index value reaches its maximum value, the next index value
        used must be 1.
        
        NOTE: The management application will read the alert table when
        a trap or event notification occurs or at a periodic rate and
        then parse the table to determine if any new entries were added
        by comparing the last known index value with the current
        highest index value.  The management application will then
        update its copy of the alert table.  When the printer discovers
        that an alert is no longer active, the printer shall remove the
        
        row for that alert from the table and shall reduce the number
        of rows in the table.  The printer may add or delete any number
        of rows from the table at any time.  The management station can
        detect when binary change alerts have been deleted by
        requesting an attribute of each alert, and noting alerts as
        deleted when that retrieval is not possible.  The objects
        'prtAlertCriticalEvents'and 'prtAlertAllEvents' in the
        'prtGeneralTable' reduce the need for management applications
        to scan the 'prtAlertTable'.
        
        NOTE: The above description has been modified from RFC 1759
        for clarification."
    ::= { prtAlertEntry 1 }

prtAlertSeverityLevel OBJECT-TYPE
    SYNTAX PrtAlertSeverityLevelTC
--    Rsyntax INTEGER {
--        other(1),
--        critical(3),
--        warning(4),
--        warningBinaryChangeEvent(5)
--        }
    ACCESS read-only
    STATUS mandatory
    DESCRIPTION
        "The level of severity of this alert table entry.  The printer
        determines the severity level assigned to each entry into the
        table."
    ::= { prtAlertEntry 2 }

prtAlertTrainingLevel OBJECT-TYPE
    SYNTAX PrtAlertTrainingLevelTC
--    Rsyntax INTEGER {
--        other(1),
--        unknown(2),
--        untrained(3),
--        trained(4),
--        fieldService(5),
--        management(6),
--        noInterventionRequired(7)
--        }
    ACCESS read-only
    STATUS mandatory
    DESCRIPTION
        "See TEXTUAL-CONVENTION PrtAlertTrainingLevelTC.
        
        NOTE: The above description has been modified from RFC 1759
        for clarification."
    ::= { prtAlertEntry 3 }

prtAlertGroup OBJECT-TYPE
    SYNTAX PrtAlertGroupTC
--    Rsyntax INTEGER {
--        other(1),
--        unknown(2),
--        hostResourcesMIBStorageTable(3),
--        hostResourcesMIBDeviceTable(4),
--        generalPrinter(5),
--        cover(6),
--        localization(7),
--        input(8),
--        output(9),
--        marker(10),
--        markerSupplies(11),
--        markerColorant(12),
--        mediaPath(13),
--        channel(14),
--        interpreter(15),
--        consoleDisplayBuffer(16),
--        consoleLights(17),
--        alert(18),
--        finDevice(30),
--        finSupply(31),
--        finSupplyMediaInput(32),
--        finAttribute(33)
--        }
    ACCESS read-only
    STATUS mandatory
    DESCRIPTION
        "The type of sub-unit within the printer model that this alert
        is related.  Input, output, and markers are examples of printer
        
        model groups, i.e., examples of types of sub-units.  Wherever
        possible, these enumerations match the sub-identifier that
        identifies the relevant table in the printmib."
    ::= { prtAlertEntry 4 }

prtAlertGroupIndex OBJECT-TYPE
    SYNTAX INTEGER(-1..2147483647)
    ACCESS read-only
    STATUS mandatory
    DESCRIPTION
        "The low-order index of the row within the table identified
        by prtAlertGroup that represents the sub-unit of the printer
        that caused this alert, or -1 if not applicable.  The
        combination of the prtAlertGroup and the prtAlertGroupIndex
        defines exactly which printer sub-unit caused the alert; for
        example, Input #3, Output#2, and Marker #1.  Every object in
        this MIB is indexed with hrDeviceIndex and optionally, another
        index variable.  If this other index variable is present in the
        table that generated the alert, it will be used as the value
        for this object.  Otherwise, this value shall be -1.
        
        NOTE: The above description has been modified from RFC 1759
        for clarification."
    ::= { prtAlertEntry 5 }

prtAlertLocation OBJECT-TYPE
    SYNTAX INTEGER(-2..2147483647)
    ACCESS read-only
    STATUS mandatory
    DESCRIPTION
        "The sub-unit location that is defined by the printer
        manufacturer to further refine the location of this alert
        within the designated sub-unit.  The location is used in
        conjunction with the Group and GroupIndex values; for example,
        there is an alert in Input #2 at location number 7.  The value
        (-2) indicates unknown.
        
        NOTE: The above description has been modified from RFC 1759
        for clarification."
    ::= { prtAlertEntry 6 }

prtAlertCode OBJECT-TYPE
    SYNTAX PrtAlertCodeTC
--    Rsyntax INTEGER {
--        other(1),
--        unknown(2),
--        coverOpen(3),
--        coverClosed(4),
--        interlockOpen(5),
--        interlockClosed(6),
--        configurationChange(7),
--        jam(8),
--        subunitMissing(9),
--        subunitLifeAlmostOver(10),
--        subunitLifeOver(11),
--        subunitAlmostEmpty(12),
--        subunitEmpty(13),
--        subunitAlmostFull(14),
--        subunitFull(15),
--        subunitNearLimit(16),
--        subunitAtLimit(17),
--        subunitOpened(18),
--        subunitClosed(19),
--        subunitTurnedOn(20),
--        subunitTurnedOff(21),
--        subunitOffline(22),
--        subunitPowerSaver(23),
--        subunitWarmingUp(24),
--        subunitAdded(25),
--        subunitRemoved(26),
--        subunitResourceAdded(27),
--        subunitResourceRemoved(28),
--        subunitRecoverableFailure(29),
--        subunitUnrecoverableFailure(30),
--        subunitRecoverableStorageError(31),
--        subunitUnrecoverableStorageError(32),
--        subunitMotorFailure(33),
--        subunitMemoryExhausted(34),
--        subunitUnderTemperature(35),
--        subunitOverTemperature(36),
--        subunitTimingFailure(37),
--        subunitThermistorFailure(38),
--        doorOpen(501),
--        doorClosed(502),
--        powerUp(503),
--        powerDown(504),
--        printerNMSReset(505),
--        printerManualReset(506),
--        printerReadyToPrint(507),
--        inputMediaTrayMissing(801),
--        inputMediaSizeChange(802),
--        inputMediaWeightChange(803),
--        inputMediaTypeChange(804),
--        inputMediaColorChange(805),
--        inputMediaFormPartsChange(806),
--        inputMediaSupplyLow(807),
--        inputMediaSupplyEmpty(808),
--        inputMediaChangeRequest(809),
--        inputManualInputRequest(810),
--        inputTrayPositionFailure(811),
--        inputTrayElevationFailure(812),
--        inputCannotFeedSizeSelected(813),
--        outputMediaTrayMissing(901),
--        outputMediaTrayAlmostFull(902),
--        outputMediaTrayFull(903),
--        outputMailboxSelectFailure(904),
--        markerFuserUnderTemperature(1001),
--        markerFuserOverTemperature(1002),
--        markerFuserTimingFailure(1003),
--        markerFuserThermistorFailure(1004),
--        markerAdjustingPrintQuality(1005),
--        markerTonerEmpty(1101),
--        markerInkEmpty(1102),
--        markerPrintRibbonEmpty(1103),
--        markerTonerAlmostEmpty(1104),
--        markerInkAlmostEmpty(1105),
--        markerPrintRibbonAlmostEmpty(1106),
--        markerWasteTonerReceptacleAlmostFull(1107),
--        markerWasteInkReceptacleAlmostFull(1108),
--        markerWasteTonerReceptacleFull(1109),
--        markerWasteInkReceptacleFull(1110),
--        markerOpcLifeAlmostOver(1111),
--        markerOpcLifeOver(1112),
--        markerDeveloperAlmostEmpty(1113),
--        markerDeveloperEmpty(1114),
--        markerTonerCartridgeMissing(1115),
--        mediaPathMediaTrayMissing(1301),
--        mediaPathMediaTrayAlmostFull(1302),
--        mediaPathMediaTrayFull(1303),
--        mediaPathCannotDuplexMediaSelected(1304),
--        interpreterMemoryIncrease(1501),
--        interpreterMemoryDecrease(1502),
--        interpreterCartridgeAdded(1503),
--        interpreterCartridgeDeleted(1504),
--        interpreterResourceAdded(1505),
--        interpreterResourceDeleted(1506),
--        interpreterResourceUnavailable(1507),
--        interpreterComplexPageEncountered(1509),
--        alertRemovalOfBinaryChangeEntry(1801)
--        }
    ACCESS read-only
    STATUS mandatory
    DESCRIPTION
        "See associated TEXTUAL-CONVENTION PrtAlertCodeTC.
        
        NOTE: The above description has been modified from RFC 1759
        for clarification."
    ::= { prtAlertEntry 7 }

prtAlertDescription OBJECT-TYPE
    SYNTAX PrtLocalizedDescriptionStringTC
--    Rsyntax OCTET STRING(SIZE(0..255))
    ACCESS read-only
    STATUS mandatory
    DESCRIPTION
        "A description of this alert entry in the localization
        specified by prtGeneralCurrentLocalization.  The description is
        provided by the printer to further elaborate on the enumerated
        alert or provide information in the case where the code is
        classified as 'other' or 'unknown'.  The printer is required to
        return a description string but the string may be a null
        string."
    ::= { prtAlertEntry 8 }

prtAlertTime OBJECT-TYPE
    SYNTAX TimeTicks
    ACCESS read-only
    STATUS mandatory
    DESCRIPTION
        "The value of sysUpTime at the time that this alert was
        generated."
    ::= { prtAlertEntry 9 }

printerV2Alert TRAP-TYPE
-- Reverse mappable trap
    ENTERPRISE printerV1Alert
    VARIABLES {
        prtAlertIndex, prtAlertSeverityLevel, prtAlertGroup, 
        prtAlertGroupIndex, prtAlertLocation, prtAlertCode }
--  Status
--    mandatory
    DESCRIPTION
        "This trap is sent whenever a critical event is added to the
        
        prtAlertTable.
        
        NOTE: The prtAlertIndex object was redundantly included in the
        bindings of the 'printerV2Alert' notification in RFC 1759, even
        though the value exists in the instance qualifier of all the
        other bindings.  This object has been retained to provide
        compatiblity with existing RFC 1759 implementaions."
    ::= 1

prtGeneralGroup OBJECT IDENTIFIER ::= { prtMIBGroups 1 }
-- OBJECT-GROUP
--  Status
--    mandatory
--  Descr
--    The general printer group.
--  objects
--    prtGeneralConfigChanges, prtGeneralCurrentLocalization, 
--    prtGeneralReset, prtCoverDescription, prtCoverStatus, 
--    prtLocalizationLanguage, prtLocalizationCountry, 
--    prtLocalizationCharacterSet, prtStorageRefIndex, 
--    prtDeviceRefIndex

prtResponsiblePartyGroup OBJECT IDENTIFIER ::= { prtMIBGroups 2 }
-- OBJECT-GROUP
--  Status
--    mandatory
--  Descr
--    The responsible party group contains contact information for
--    humans responsible for the printer.
--  objects
--    prtGeneralCurrentOperator, prtGeneralServicePerson

prtInputGroup OBJECT IDENTIFIER ::= { prtMIBGroups 3 }
-- OBJECT-GROUP
--  Status
--    mandatory
--  Descr
--    The input group.
--  objects
--    prtInputDefaultIndex, prtInputType, prtInputDimUnit, 
--    prtInputMediaDimFeedDirDeclared, 
--    prtInputMediaDimXFeedDirDeclared, 
--    prtInputMediaDimFeedDirChosen, prtInputMediaDimXFeedDirChosen, 
--    prtInputCapacityUnit, prtInputMaxCapacity, 
--    prtInputCurrentLevel, prtInputStatus, prtInputMediaName

prtExtendedInputGroup OBJECT IDENTIFIER ::= { prtMIBGroups 4 }
-- OBJECT-GROUP
--  Status
--    mandatory
--  Descr
--    The extended input group.
--  objects
--    prtInputName, prtInputVendorName, prtInputModel, 
--    prtInputVersion, prtInputSerialNumber, prtInputDescription, 
--    prtInputSecurity

prtInputMediaGroup OBJECT IDENTIFIER ::= { prtMIBGroups 5 }
-- OBJECT-GROUP
--  Status
--    mandatory
--  Descr
--    The input media group.
--  objects
--    prtInputMediaWeight, prtInputMediaType, prtInputMediaColor, 
--    prtInputMediaFormParts

prtOutputGroup OBJECT IDENTIFIER ::= { prtMIBGroups 6 }
-- OBJECT-GROUP
--  Status
--    mandatory
--  Descr
--    The output group.
--  objects
--    prtOutputDefaultIndex, prtOutputType, prtOutputCapacityUnit, 
--    prtOutputMaxCapacity, prtOutputRemainingCapacity, 
--    prtOutputStatus

prtExtendedOutputGroup OBJECT IDENTIFIER ::= { prtMIBGroups 7 }
-- OBJECT-GROUP
--  Status
--    mandatory
--  Descr
--    The extended output group.
--  objects
--    prtOutputName, prtOutputVendorName, prtOutputModel, 
--    prtOutputVersion, prtOutputSerialNumber, prtOutputDescription, 
--    prtOutputSecurity

prtOutputDimensionsGroup OBJECT IDENTIFIER ::= { prtMIBGroups 8 }
-- OBJECT-GROUP
--  Status
--    mandatory
--  Descr
--    The output dimensions group
--  objects
--    prtOutputDimUnit, prtOutputMaxDimFeedDir, 
--    prtOutputMaxDimXFeedDir, prtOutputMinDimFeedDir, 
--    prtOutputMinDimXFeedDir

prtOutputFeaturesGroup OBJECT IDENTIFIER ::= { prtMIBGroups 9 }
-- OBJECT-GROUP
--  Status
--    mandatory
--  Descr
--    The output features group.
--  objects
--    prtOutputStackingOrder, prtOutputPageDeliveryOrientation, 
--    prtOutputBursting, prtOutputDecollating, 
--    prtOutputPageCollated, prtOutputOffsetStacking

prtMarkerGroup OBJECT IDENTIFIER ::= { prtMIBGroups 10 }
-- OBJECT-GROUP
--  Status
--    mandatory
--  Descr
--    The marker group.
--  objects
--    prtMarkerDefaultIndex, prtMarkerMarkTech, 
--    prtMarkerCounterUnit, prtMarkerLifeCount, 
--    prtMarkerPowerOnCount, prtMarkerProcessColorants, 
--    prtMarkerSpotColorants, prtMarkerAddressabilityUnit, 
--    prtMarkerAddressabilityFeedDir, 
--    prtMarkerAddressabilityXFeedDir, prtMarkerNorthMargin, 
--    prtMarkerSouthMargin, prtMarkerWestMargin, 
--    prtMarkerEastMargin, prtMarkerStatus

prtMarkerSuppliesGroup OBJECT IDENTIFIER ::= { prtMIBGroups 11 }
-- OBJECT-GROUP
--  Status
--    mandatory
--  Descr
--    The marker supplies group.
--  objects
--    prtMarkerSuppliesMarkerIndex, prtMarkerSuppliesColorantIndex, 
--    prtMarkerSuppliesClass, prtMarkerSuppliesType, 
--    prtMarkerSuppliesDescription, prtMarkerSuppliesSupplyUnit, 
--    prtMarkerSuppliesMaxCapacity, prtMarkerSuppliesLevel

prtMarkerColorantGroup OBJECT IDENTIFIER ::= { prtMIBGroups 12 }
-- OBJECT-GROUP
--  Status
--    mandatory
--  Descr
--    The marker colorant group.
--  objects
--    prtMarkerColorantMarkerIndex, prtMarkerColorantRole, 
--    prtMarkerColorantValue, prtMarkerColorantTonality

prtMediaPathGroup OBJECT IDENTIFIER ::= { prtMIBGroups 13 }
-- OBJECT-GROUP
--  Status
--    mandatory
--  Descr
--    The media path group.
--  objects
--    prtMediaPathDefaultIndex, prtMediaPathMaxSpeedPrintUnit, 
--    prtMediaPathMediaSizeUnit, prtMediaPathMaxSpeed, 
--    prtMediaPathMaxMediaFeedDir, prtMediaPathMaxMediaXFeedDir, 
--    prtMediaPathMinMediaFeedDir, prtMediaPathMinMediaXFeedDir, 
--    prtMediaPathType, prtMediaPathDescription, prtMediaPathStatus

prtChannelGroup OBJECT IDENTIFIER ::= { prtMIBGroups 14 }
-- OBJECT-GROUP
--  Status
--    mandatory
--  Descr
--    The channel group.
--  objects
--    prtChannelType, prtChannelProtocolVersion, 
--    prtChannelCurrentJobCntlLangIndex, 
--    prtChannelDefaultPageDescLangIndex, prtChannelState, 
--    prtChannelIfIndex, prtChannelStatus

prtInterpreterGroup OBJECT IDENTIFIER ::= { prtMIBGroups 15 }
-- OBJECT-GROUP
--  Status
--    mandatory
--  Descr
--    The interpreter group.
--  objects
--    prtInterpreterLangFamily, prtInterpreterLangLevel, 
--    prtInterpreterLangVersion, prtInterpreterDescription, 
--    prtInterpreterVersion, prtInterpreterDefaultOrientation, 
--    prtInterpreterFeedAddressability, 
--    prtInterpreterXFeedAddressability, 
--    prtInterpreterDefaultCharSetIn, 
--    prtInterpreterDefaultCharSetOut, prtInterpreterTwoWay

prtConsoleGroup OBJECT IDENTIFIER ::= { prtMIBGroups 16 }
-- OBJECT-GROUP
--  Status
--    mandatory
--  Descr
--    The console group.
--  objects
--    prtConsoleLocalization, prtConsoleNumberOfDisplayLines, 
--    prtConsoleNumberOfDisplayChars, prtConsoleDisable, 
--    prtConsoleDisplayBufferText, prtConsoleOnTime, 
--    prtConsoleOffTime, prtConsoleColor, prtConsoleDescription

prtAlertTableGroup OBJECT IDENTIFIER ::= { prtMIBGroups 17 }
-- OBJECT-GROUP
--  Status
--    mandatory
--  Descr
--    The alert table group.
--  objects
--    prtAlertSeverityLevel, prtAlertTrainingLevel, prtAlertGroup, 
--    prtAlertGroupIndex, prtAlertLocation, prtAlertCode, 
--    prtAlertDescription

prtAlertTimeGroup OBJECT IDENTIFIER ::= { prtMIBGroups 18 }
-- OBJECT-GROUP
--  Status
--    mandatory
--  Descr
--    The alert time group. Implementation of prtAlertTime is
--    strongly RECOMMENDED.
--  objects
--    prtAlertTime

prtAuxiliarySheetGroup OBJECT IDENTIFIER ::= { prtMIBGroups 19 }
-- OBJECT-GROUP
--  Status
--    mandatory
--  Descr
--    The auxiliary sheet group.
--  objects
--    prtAuxiliarySheetStartupPage, prtAuxiliarySheetBannerPage

prtInputSwitchingGroup OBJECT IDENTIFIER ::= { prtMIBGroups 20 }
-- OBJECT-GROUP
--  Status
--    mandatory
--  Descr
--    The input switching group.
--  objects
--    prtInputMediaLoadTimeout, prtInputNextIndex

prtGeneralV2Group OBJECT IDENTIFIER ::= { prtMIBGroups 21 }
-- OBJECT-GROUP
--  Status
--    mandatory
--  Descr
--    The general printer group with new v2 objects.
--  objects
--    prtGeneralPrinterName, prtGeneralSerialNumber

prtAlertTableV2Group OBJECT IDENTIFIER ::= { prtMIBGroups 22 }
-- OBJECT-GROUP
--  Status
--    mandatory
--  Descr
--    The alert table group with new v2 objects and prtAlertIndex
--    changed to MAX-ACCESS of 'read-only' for inclusion in the trap
--    bindings (as originally defined in RFC 1759).
--  objects
--    prtAlertIndex, prtAlertCriticalEvents, prtAlertAllEvents

prtChannelV2Group OBJECT IDENTIFIER ::= { prtMIBGroups 23 }
-- OBJECT-GROUP
--  Status
--    mandatory
--  Descr
--    The channel group with a new v2 object.
--  objects
--    prtChannelInformation

prtAlertTrapGroup OBJECT IDENTIFIER ::= { prtMIBGroups 24 }
-- NOTIFICATION-GROUP
--  Status
--    mandatory
--  Descr
--    The alert trap group.
--  notifications
--    printerV2Alert

prtMIBCompliance OBJECT IDENTIFIER ::= { prtMIBConformance 1 }
-- MODULE-COMPLIANCE
--  Status
--    mandatory
--  Descr
--    The compliance statement for agents that implement the
--    printer MIB as defined by RFC 1759.
--  Module
--    >>current<<
--   MandGroup
--    prtGeneralGroup
--   MandGroup
--    prtInputGroup
--   MandGroup
--    prtOutputGroup
--   MandGroup
--    prtMarkerGroup
--   MandGroup
--    prtMediaPathGroup
--   MandGroup
--    prtChannelGroup
--   MandGroup
--    prtInterpreterGroup
--   MandGroup
--    prtConsoleGroup
--   MandGroup
--    prtAlertTableGroup
--   ObjVar
--    prtGeneralReset
--   ObjVar
--    prtConsoleOnTime
--   ObjVar
--    prtConsoleOffTime

prtMIB2Compliance OBJECT IDENTIFIER ::= { prtMIBConformance 3 }
-- MODULE-COMPLIANCE
--  Status
--    mandatory
--  Descr
--    The compliance statement for agents that implement the
--    printer MIB V2.
--  Module
--    >>current<<
--   MandGroup
--    prtGeneralGroup
--   MandGroup
--    prtInputGroup
--   MandGroup
--    prtOutputGroup
--   MandGroup
--    prtMarkerGroup
--   MandGroup
--    prtMediaPathGroup
--   MandGroup
--    prtChannelGroup
--   MandGroup
--    prtInterpreterGroup
--   MandGroup
--    prtConsoleGroup
--   MandGroup
--    prtAlertTableGroup
--   ObjVar
--    prtGeneralReset
--   ObjVar
--    prtGeneralCurrentLocalization
--   ObjVar
--    prtGeneralCurrentOperator
--   ObjVar
--    prtGeneralServicePerson
--   ObjVar
--    prtGeneralPrinterName
--   ObjVar
--    prtGeneralSerialNumber
--   ObjVar
--    prtInputDefaultIndex
--   ObjVar
--    prtInputMediaDimFeedDirDeclared
--   ObjVar
--    prtInputMaxCapacity
--   ObjVar
--    prtInputCurrentLevel
--   ObjVar
--    prtInputMediaName
--   ObjVar
--    prtInputName
--   ObjVar
--    prtInputSecurity
--   ObjVar
--    prtInputMediaWeight
--   ObjVar
--    prtInputMediaType
--   ObjVar
--    prtInputMediaColor
--   ObjVar
--    prtInputMediaFormParts
--   ObjVar
--    prtOutputDefaultIndex
--   ObjVar
--    prtOutputMaxCapacity
--   ObjVar
--    prtOutputRemainingCapacity
--   ObjVar
--    prtOutputName
--   ObjVar
--    prtOutputSecurity
--   ObjVar
--    prtOutputMaxDimFeedDir
--   ObjVar
--    prtOutputMaxDimXFeedDir
--   ObjVar
--    prtOutputMinDimFeedDir
--   ObjVar
--    prtOutputMinDimXFeedDir
--   ObjVar
--    prtOutputStackingOrder
--   ObjVar
--    prtOutputPageDeliveryOrientation
--   ObjVar
--    prtOutputBursting
--   ObjVar
--    prtOutputDecollating
--   ObjVar
--    prtOutputPageCollated
--   ObjVar
--    prtOutputOffsetStacking
--   ObjVar
--    prtMarkerDefaultIndex
--   ObjVar
--    prtMarkerSuppliesMaxCapacity
--   ObjVar
--    prtMarkerSuppliesLevel
--   ObjVar
--    prtMediaPathDefaultIndex
--   ObjVar
--    prtChannelCurrentJobCntlLangIndex
--   ObjVar
--    prtChannelDefaultPageDescLangIndex
--   ObjVar
--    prtChannelState
--   ObjVar
--    prtChannelIfIndex
--   ObjVar
--    prtInterpreterDefaultOrientation
--   ObjVar
--    prtInterpreterDefaultCharSetIn
--   ObjVar
--    prtInterpreterDefaultCharSetOut
--   ObjVar
--    prtConsoleLocalization
--   ObjVar
--    prtConsoleDisable
--   ObjVar
--    prtConsoleDisplayBufferText
--   ObjVar
--    prtConsoleOnTime
--   ObjVar
--    prtConsoleOffTime
--   ObjVar
--    prtAlertIndex
--   OptGroup
--    prtResponsiblePartyGroup
--   OptGroup
--    prtExtendedInputGroup
--   OptGroup
--    prtInputMediaGroup
--   OptGroup
--    prtExtendedOutputGroup
--   OptGroup
--    prtOutputDimensionsGroup
--   OptGroup
--    prtOutputFeaturesGroup
--   OptGroup
--    prtMarkerSuppliesGroup
--   OptGroup
--    prtMarkerColorantGroup
--   OptGroup
--    prtAlertTimeGroup
--   ObjVar
--    prtAuxiliarySheetStartupPage
--   ObjVar
--    prtAuxiliarySheetBannerPage
--   ObjVar
--    prtInputMediaLoadTimeout
--   ObjVar
--    prtInputNextIndex
--   OptGroup
--    prtAuxiliarySheetGroup
--   OptGroup
--    prtInputSwitchingGroup
--   OptGroup
--    prtGeneralV2Group
--   OptGroup
--    prtAlertTableV2Group
--   OptGroup
--    prtChannelV2Group
--   OptGroup
--    prtAlertTrapGroup


END
