-- MIB file created 13-Nov-2006 00:05:21, by
--   SMICng version 2.2.11-beta(PRO)(Solaris), January 20, 2001. Enterprise key cisco.com

ATM2-MIB DEFINITIONS ::= BEGIN

-- From file: "ATM2-MIB.my"
-- Compile options "4 7 F H N O W 03 06 0B 0G 0N 0T"

IMPORTS
    TruthValue, RowStatus, TimeStamp
            FROM SNMPv2-TC-v1
    SnmpAdminString
            FROM SNMP-FRAMEWORK-MIB
    InterfaceIndex, InterfaceIndexOrZero, ifIndex
            FROM IF-MIB
    atmMIBObjects
--?? may need import of ifIndex from IF-MIB
                 
--?? may need import of ifIndex from IF-MIB
                 , atmVplVpi
--?? may need import of ifIndex from IF-MIB
                            , atmVclVpi, atmVclVci, 
    atmVpCrossConnectIndex, atmVpCrossConnectLowIfIndex, 
    atmVpCrossConnectLowVpi, atmVpCrossConnectHighIfIndex, 
    atmVpCrossConnectHighVpi, atmVcCrossConnectIndex, 
    atmVcCrossConnectLowIfIndex, atmVcCrossConnectLowVpi, 
    atmVcCrossConnectLowVci, atmVcCrossConnectHighIfIndex, 
    atmVcCrossConnectHighVpi, atmVcCrossConnectHighVci
            FROM ATM-MIB
    AtmAddr, AtmSigDescrParamIndex, AtmInterfaceType, 
    AtmIlmiNetworkPrefix, AtmVcIdentifier, AtmVpIdentifier, 
    AtmTrafficDescrParamIndex
            FROM ATM-TC-MIB
    Counter, Gauge
            FROM RFC1155-SMI
    OBJECT-TYPE
            FROM RFC-1212
    TRAP-TYPE
            FROM RFC-1215;

atm2MIB OBJECT IDENTIFIER ::= { atmMIBObjects 14 }
-- MODULE-IDENTITY
--  LastUpdated
--    200309230000Z
--  OrgName
--    IETF AToMMIB Working Group
--  ContactInfo
--    AToMMIB WG
--        http://www.ietf.org/html.charters/atommib-charter.html
--      Editors:
--               Faye Ly
--      Postal:  Pedestal Networks
--               6503 Dumbarton Circle
--               Fremont, CA 94555
--               USA
--      Tel:     +1 510 896 2908
--      E-Mail:  faye@pedestalnetworks.com
--    
--               Michael Noto
--      Postal:  Cisco Systems
--               170 W. Tasman Drive
--               San Jose, CA 95134-1706
--               USA
--    
--      E-mail:  mnoto@cisco.com
--    
--               Andrew Smith
--      Postal:  Consultant
--    
--      E-Mail:  ah_smith@acm.org
--    
--               Ethan Mickey Spiegel
--      Postal:  Cisco Systems
--               170 W. Tasman Drive
--               San Jose, CA 95134-1706
--               USA
--      Tel:     +1 408 526 6408
--      Fax:     +1 408 526 6488
--      E-Mail:  mspiegel@cisco.com
--    
--               Kaj Tesink
--      Postal:  Telcordia Technologies
--               331 Newman Springs Road
--    
--               Red Bank, NJ 07701
--               USA
--      Tel:     +1 732 758 5254
--      E-mail:  kaj@research.telcordia.com
--  Descr
--    Copyright (C) The Internet Society (2003). This version of
--    this MIB module is part of RFC 3606; see the RFC itself for
--    full legal notices.
--    
--    This MIB Module is a supplement to the ATM-MIB
--    defined in RFC 2515.
--  RevDate
--    200309230000Z
--  RevDescr
--    Initial version of this MIB, published as RFC 3606.

atm2MIBObjects  OBJECT IDENTIFIER ::= { atm2MIB 1 }
atm2MIBTraps    OBJECT IDENTIFIER ::= { atm2MIB 2 }
atmPvcTraps     OBJECT IDENTIFIER ::= { atm2MIBTraps 1 }
atmPvcTrapsPrefix OBJECT IDENTIFIER ::= { atmPvcTraps 0 }
atm2MIBConformance OBJECT IDENTIFIER ::= { atm2MIB 3 }
atm2MIBGroups   OBJECT IDENTIFIER ::= { atm2MIBConformance 1 }
atm2MIBCompliances OBJECT IDENTIFIER ::= { atm2MIBConformance 2 }

atmSvcVpCrossConnectTable OBJECT-TYPE
    SYNTAX SEQUENCE OF AtmSvcVpCrossConnectEntry
    ACCESS not-accessible
    STATUS mandatory
    DESCRIPTION
        "The ATM SVPC Cross-Connect table.  A
        bi-directional VP cross-connect between two
        switched VPLs is modeled as one entry in this
        table.  A Soft PVPC cross-connect, between a
        soft permanent VPL and a switched VPL, is
        also modeled as one entry in this table."
    ::= { atm2MIBObjects 1 }

atmSvcVpCrossConnectEntry OBJECT-TYPE
    SYNTAX AtmSvcVpCrossConnectEntry
    ACCESS not-accessible
    STATUS mandatory
    DESCRIPTION
        "An entry in the ATM SVPC Cross-Connect table.
        This entry is used to model a bi-directional
        ATM VP cross-connect between two VPLs."
    INDEX { atmSvcVpCrossConnectIndex, atmSvcVpCrossConnectLowIfIndex, atmSvcVpCrossConnectLowVpi, atmSvcVpCrossConnectHighIfIndex, atmSvcVpCrossConnectHighVpi }
    ::= { atmSvcVpCrossConnectTable 1 }

AtmSvcVpCrossConnectEntry ::= SEQUENCE {
    atmSvcVpCrossConnectIndex INTEGER,
    atmSvcVpCrossConnectLowIfIndex InterfaceIndex,
    atmSvcVpCrossConnectLowVpi AtmVpIdentifier,
    atmSvcVpCrossConnectHighIfIndex InterfaceIndex,
    atmSvcVpCrossConnectHighVpi AtmVpIdentifier,
    atmSvcVpCrossConnectCreationTime TimeStamp,
    atmSvcVpCrossConnectRowStatus RowStatus
    }

atmSvcVpCrossConnectIndex OBJECT-TYPE
    SYNTAX INTEGER(1..2147483647)
    ACCESS not-accessible
    STATUS mandatory
    DESCRIPTION
        "A unique value to identify this SVPC
        cross-connect.  For each VP associated
        with this cross-connect, the agent reports
        this cross-connect index value in the
        atmVplCrossConnectIdentifer attribute of the
        
        corresponding atmVplTable entries."
    ::= { atmSvcVpCrossConnectEntry 1 }

atmSvcVpCrossConnectLowIfIndex OBJECT-TYPE
    SYNTAX InterfaceIndex
--    Rsyntax INTEGER(1..2147483647)
    ACCESS not-accessible
    STATUS mandatory
    DESCRIPTION
        "The value of this object is equal to the
        ifIndex value of the ATM interface port for this
        SVPC cross-connect.  The term low implies
        that this ATM interface has the numerically lower
        ifIndex value than the other ATM interface
        identified in the same atmSvcVpCrossConnectEntry."
    ::= { atmSvcVpCrossConnectEntry 2 }

atmSvcVpCrossConnectLowVpi OBJECT-TYPE
    SYNTAX AtmVpIdentifier
--    Rsyntax INTEGER(0..4095)
    ACCESS not-accessible
    STATUS mandatory
    DESCRIPTION
        "The value of this object is equal to the VPI
        value associated with the SVPC cross-connect
        at the ATM interface that is identified by
        atmSvcVpCrossConnectLowIfIndex.  The VPI value
        cannot exceed the number supported by the
        atmInterfaceCurrentMaxSvpcVpi at the low ATM interface
        port."
    ::= { atmSvcVpCrossConnectEntry 3 }

atmSvcVpCrossConnectHighIfIndex OBJECT-TYPE
    SYNTAX InterfaceIndex
--    Rsyntax INTEGER(1..2147483647)
    ACCESS not-accessible
    STATUS mandatory
    DESCRIPTION
        "The value of this object is equal to the
         ifIndex value of the ATM interface port for
         this SVC VP cross-connect.  The term high
         implies that this ATM interface has the
         numerically higher ifIndex value than the
         other ATM interface identified in the same
         atmSvcVpCrossConnectEntry."
    ::= { atmSvcVpCrossConnectEntry 4 }

atmSvcVpCrossConnectHighVpi OBJECT-TYPE
    SYNTAX AtmVpIdentifier
--    Rsyntax INTEGER(0..4095)
    ACCESS not-accessible
    STATUS mandatory
    DESCRIPTION
        "The value of this object is equal to the VPI
         value associated with the SVPC cross-connect
         at the ATM interface that is identified by
         atmSvcVpCrossConnectHighIfIndex.  The VPI value
         cannot exceed the number supported by the
         atmInterfaceCurrentMaxSvpcVpi at the high ATM interface
         port."
    ::= { atmSvcVpCrossConnectEntry 5 }

atmSvcVpCrossConnectCreationTime OBJECT-TYPE
    SYNTAX TimeStamp
--    Rsyntax TimeTicks
    ACCESS read-only
    STATUS mandatory
    DESCRIPTION
        "The value of the sysUpTime object
         at the time this bi-directional SVPC
         cross-connect was created.  If the current
         state was entered prior to the last
         re-initialization of the agent, then this
         object contains a zero value."
    ::= { atmSvcVpCrossConnectEntry 6 }

atmSvcVpCrossConnectRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to delete rows in the
         atmSvcVpCrossConnectTable."
    ::= { atmSvcVpCrossConnectEntry 7 }

atmSvcVcCrossConnectTable OBJECT-TYPE
    SYNTAX SEQUENCE OF AtmSvcVcCrossConnectEntry
    ACCESS not-accessible
    STATUS mandatory
    DESCRIPTION
        "The ATM SVCC Cross-Connect table.  A
         bi-directional VC cross-connect between two
         switched VCLs is modeled as one entry in
         this table.  A Soft PVCC cross-connect,
         between a soft permanent VCL and a switched
         VCL, is also modeled as one entry in this
         table."
    ::= { atm2MIBObjects 2 }

atmSvcVcCrossConnectEntry OBJECT-TYPE
    SYNTAX AtmSvcVcCrossConnectEntry
    ACCESS not-accessible
    STATUS mandatory
    DESCRIPTION
        "An entry in the ATM SVCC Cross-Connect table.
         This entry is used to model a bi-directional ATM
         VC cross-connect between two VCLs."
    INDEX { atmSvcVcCrossConnectIndex, atmSvcVcCrossConnectLowIfIndex, atmSvcVcCrossConnectLowVpi, atmSvcVcCrossConnectLowVci, atmSvcVcCrossConnectHighIfIndex, atmSvcVcCrossConnectHighVpi, atmSvcVcCrossConnectHighVci }
    ::= { atmSvcVcCrossConnectTable 1 }

AtmSvcVcCrossConnectEntry ::= SEQUENCE {
    atmSvcVcCrossConnectIndex INTEGER,
    atmSvcVcCrossConnectLowIfIndex InterfaceIndex,
    atmSvcVcCrossConnectLowVpi AtmVpIdentifier,
    atmSvcVcCrossConnectLowVci AtmVcIdentifier,
    atmSvcVcCrossConnectHighIfIndex InterfaceIndex,
    atmSvcVcCrossConnectHighVpi AtmVpIdentifier,
    atmSvcVcCrossConnectHighVci AtmVcIdentifier,
    atmSvcVcCrossConnectCreationTime TimeStamp,
    atmSvcVcCrossConnectRowStatus RowStatus
    }

atmSvcVcCrossConnectIndex OBJECT-TYPE
    SYNTAX INTEGER(1..2147483647)
    ACCESS not-accessible
    STATUS mandatory
    DESCRIPTION
        "A unique value to identify this SVCC cross-connect.
         For each VP associated with this cross-connect, the
         agent reports this cross-connect index value in the
         atmVclCrossConnectIdentifier attribute of the
         corresponding atmVplTable entries."
    ::= { atmSvcVcCrossConnectEntry 1 }

atmSvcVcCrossConnectLowIfIndex OBJECT-TYPE
    SYNTAX InterfaceIndex
--    Rsyntax INTEGER(1..2147483647)
    ACCESS not-accessible
    STATUS mandatory
    DESCRIPTION
        "The value of this object is equal to the
         ifIndex value of the ATM interface port for this
        
         SVCC cross-connect.  The term low implies that
         this ATM interface has the numerically lower
         ifIndex value than the other ATM interface
         identified in the same atmSvcVcCrossConnectEntry."
    ::= { atmSvcVcCrossConnectEntry 2 }

atmSvcVcCrossConnectLowVpi OBJECT-TYPE
    SYNTAX AtmVpIdentifier
--    Rsyntax INTEGER(0..4095)
    ACCESS not-accessible
    STATUS mandatory
    DESCRIPTION
        "The value of this object is equal to the VPI
         value associated with the SVCC cross-connect
         at the ATM interface that is identified by
         atmSvcVcCrossConnectLowIfIndex.  The VPI value
         cannot exceed the number supported by the
         atmInterfaceCurrentMaxSvccVpi at the low ATM interface
         port."
    ::= { atmSvcVcCrossConnectEntry 3 }

atmSvcVcCrossConnectLowVci OBJECT-TYPE
    SYNTAX AtmVcIdentifier
--    Rsyntax INTEGER(0..65535)
    ACCESS not-accessible
    STATUS mandatory
    DESCRIPTION
        "The value of this object is equal to the VCI
         value associated with the SVCC cross-connect
         at the ATM interface that is identified by
         atmSvcVcCrossConnectLowIfIndex.  The VCI value
         cannot exceed the number supported by the
         atmInterfaceCurrentMaxSvccVci at the low ATM interface
         port."
    ::= { atmSvcVcCrossConnectEntry 4 }

atmSvcVcCrossConnectHighIfIndex OBJECT-TYPE
    SYNTAX InterfaceIndex
--    Rsyntax INTEGER(1..2147483647)
    ACCESS not-accessible
    STATUS mandatory
    DESCRIPTION
        "The value of this object is equal to the
         ifIndex value for the ATM interface port for
         this SVCC cross-connect.  The term high implies
         that this ATM interface has the numerically
         higher ifIndex value than the other ATM interface
         identified in the same atmSvcVcCrossConnectEntry."
    ::= { atmSvcVcCrossConnectEntry 5 }

atmSvcVcCrossConnectHighVpi OBJECT-TYPE
    SYNTAX AtmVpIdentifier
--    Rsyntax INTEGER(0..4095)
    ACCESS not-accessible
    STATUS mandatory
    DESCRIPTION
        "The value of this object is equal to the VPI
         value associated with the SVCC cross-connect
         at the ATM interface that is identified by
         atmSvcVcCrossConnectHighIfIndex.  The VPI value
         cannot exceed the number supported by the
         atmInterfaceCurrentMaxSvccVpi at the high ATM interface
         port."
    ::= { atmSvcVcCrossConnectEntry 6 }

atmSvcVcCrossConnectHighVci OBJECT-TYPE
    SYNTAX AtmVcIdentifier
--    Rsyntax INTEGER(0..65535)
    ACCESS not-accessible
    STATUS mandatory
    DESCRIPTION
        "The value of this object is equal to the VCI
         value associated with the SVCC cross-connect
         at the ATM interface that is identified by
         atmSvcVcCrossConnectHighIfIndex.  The VCI value
         cannot exceed the number supported by the
         atmInterfaceMaxVciBits at the high ATM interface
         port."
    ::= { atmSvcVcCrossConnectEntry 7 }

atmSvcVcCrossConnectCreationTime OBJECT-TYPE
    SYNTAX TimeStamp
--    Rsyntax TimeTicks
    ACCESS read-only
    STATUS mandatory
    DESCRIPTION
        "The value of the sysUpTime object
         at the time this bi-directional SVCC
         cross-connect was created.  If the current
         state was entered prior to the last
         re-initialization of the agent, then this
         object contains a zero value."
    ::= { atmSvcVcCrossConnectEntry 8 }

atmSvcVcCrossConnectRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to delete rows in the
         atmSvcVcCrossConnectTable."
    ::= { atmSvcVcCrossConnectEntry 9 }

atmSigStatTable OBJECT-TYPE
    SYNTAX SEQUENCE OF AtmSigStatEntry
    ACCESS not-accessible
    STATUS mandatory
    DESCRIPTION
        "This table contains ATM interface signalling
        statistics, one entry per ATM signalling
        interface."
    ::= { atm2MIBObjects 3 }

atmSigStatEntry OBJECT-TYPE
    SYNTAX AtmSigStatEntry
    ACCESS not-accessible
    STATUS mandatory
    DESCRIPTION
        "This list contains signalling statistics variables."
    INDEX { ifIndex }
    ::= { atmSigStatTable 1 }

AtmSigStatEntry ::= SEQUENCE {
    atmSigSSCOPConEvents Counter,
    atmSigSSCOPErrdPdus Counter,
    atmSigDetectSetupAttempts Counter,
    atmSigEmitSetupAttempts Counter,
    atmSigDetectUnavailRoutes Counter,
    atmSigEmitUnavailRoutes Counter,
    atmSigDetectUnavailResrcs Counter,
    atmSigEmitUnavailResrcs Counter,
    atmSigDetectCldPtyEvents Counter,
    atmSigEmitCldPtyEvents Counter,
    atmSigDetectMsgErrors Counter,
    atmSigEmitMsgErrors Counter,
    atmSigDetectClgPtyEvents Counter,
    atmSigEmitClgPtyEvents Counter,
    atmSigDetectTimerExpireds Counter,
    atmSigEmitTimerExpireds Counter,
    atmSigDetectRestarts Counter,
    atmSigEmitRestarts Counter,
    atmSigInEstabls Counter,
    atmSigOutEstabls Counter
    }

atmSigSSCOPConEvents OBJECT-TYPE
    SYNTAX Counter
    ACCESS read-only
    STATUS mandatory
    DESCRIPTION
        "SSCOP Connection Events Counter.  This counter counts
         the sum of the following errors:
        
         1) SSCOP Connection Disconnect Counter
        
             The abnormal occurrence of this event is
             characterized by the expiry of Timer_NO_RESPONSE.
             (This event is communicated to the layer management
             with MAA-ERROR code P.  See ITU-T Q.2110.)
        
          2) SSCOP Connection Initiation Failure
        
             This condition indicates the inability to establish
             an SSCOP connection.  This event occurs whenever the
             number of expiries of the connection control timer
             (Timer_CC) equals or exceeds the MaxCC, or upon
             receipt of a connection reject message BGREJ PDU.
             (This event is communicated to layer management with
             MAA-ERROR code O.  See ITU-T Q.2110.)
        
          3) SSCOP Connection Re-Establ/Resynch
        
             This event occurs upon receipt of a BGN PDU or
             RS PDU."
    REFERENCE
        "ITU-T Recommendation Q.2110, Broadband
         Integrated Services Digital Network
         (B-ISDN) - ATM Adaptation Layer - Service
         Specific Connection Oriented Protocol (SSCOP)
         Specification, July 1994."
    ::= { atmSigStatEntry 1 }

atmSigSSCOPErrdPdus OBJECT-TYPE
    SYNTAX Counter
    ACCESS read-only
    STATUS mandatory
    DESCRIPTION
        "SSCOP Errored PDUs Counter.  This counter counts the
        sum of the following errors:
        
        1) Invalid PDUs.
           These are defined in SSCOP and consist of PDUs
           with an incorrect length (MAA-ERROR code U), an
           undefined PDU type code, or that are not 32-bit
           aligned.
        
        2) PDUs that result in MAA-ERROR codes and are
        
           discarded.
        
        See MAA-ERROR codes A-D, F-M, and Q-T defined in
        ITU-T Q.2110."
    REFERENCE
        "ITU-T Recommendation Q.2110, Broadband
         Integrated Services Digital Network
         (B-ISDN) - ATM Adaptation Layer - Service
         Specific Connection Oriented Protocol (SSCOP)
         Specification, July 1994."
    ::= { atmSigStatEntry 2 }

atmSigDetectSetupAttempts OBJECT-TYPE
    SYNTAX Counter
    ACCESS read-only
    STATUS mandatory
    DESCRIPTION
        "Call Setup Attempts Counter.  This counter counts
        the number of call setup attempts (both successful
        and unsuccessful) detected on this interface."
    ::= { atmSigStatEntry 3 }

atmSigEmitSetupAttempts OBJECT-TYPE
    SYNTAX Counter
    ACCESS read-only
    STATUS mandatory
    DESCRIPTION
        "Call Setup Attempts Counter.  This counter counts
        the number of call setup attempts (both successful
        and unsuccessful) transmitted on this interface."
    ::= { atmSigStatEntry 4 }

atmSigDetectUnavailRoutes OBJECT-TYPE
    SYNTAX Counter
    ACCESS read-only
    STATUS mandatory
    DESCRIPTION
        "Number of Route Unavailability detected on this interface.
        This counter is incremented when a RELEASE, RELEASE COMPLETE
        (only when not preceded by a RELEASE message for the same
        call), ADD PARTY REJECT, or STATUS message that
        contains one of the following cause code values is
        received (Note: These cause values
        apply to both UNI3.0 and UNI3.1):
        
        Cause Value            Meaning
        
           1            unallocated (unassigned) number
           2            no route to specified transit network
           3            no route to destination
        
        NOTE:  For this counter, RELEASE COMPLETE
        messages that are a reply to a previous RELEASE
        message and contain the same cause value, are
        redundant (for counting purposes) and should not
        be counted."
    ::= { atmSigStatEntry 5 }

atmSigEmitUnavailRoutes OBJECT-TYPE
    SYNTAX Counter
    ACCESS read-only
    STATUS mandatory
    DESCRIPTION
        "Number of Route Unavailability transmitted from this
        interface.  This counter is incremented when a RELEASE,
        RELEASE COMPLETE (only when not preceded by a RELEASE
        message for the same call), ADD PARTY REJECT, or
        STATUS message that contains one of the following cause
        code values is transmitted (Note: These cause values apply
        to both UNI3.0 and UNI3.1):
        
        Cause Value            Meaning
        
           1            unallocated (unassigned) number
           2            no route to specified transit network
           3            no route to destination
        
        NOTE:  For this counter, RELEASE COMPLETE
        messages that are a reply to a previous RELEASE
        message and contain the same cause value, are
        redundant (for counting purposes) and should not
        be counted."
    ::= { atmSigStatEntry 6 }

atmSigDetectUnavailResrcs OBJECT-TYPE
    SYNTAX Counter
    ACCESS read-only
    STATUS mandatory
    DESCRIPTION
        "Number of Resource Unavailability detected on this
        interface.  This counter is incremented when a RELEASE,
        RELEASE COMPLETE (only when not preceded by a RELEASE
        message for the same call), ADD PARTY REJECT, or
        STATUS message that contains one of the following
        
        cause code values is received (Note: These cause
        values apply to both UNI3.0 and UNI3.1 unless
        otherwise stated):
        
        Cause Value          Meaning
        
           35          requested VPCI/VCI not available
           37          user cell rate not available (UNI3.1
                       only)
           38          network out of order
           41          temporary failure
           45          no VPCI/VCI available
           47          resource unavailable, unspecified
           49          Quality of Service unavailable
           51          user cell rate not available (UNI3.0
                       only)
           58          bearer capability not presently
                       available
           63          Service or option not available,
                       unspecified
           92          too many pending add party requests
        
        NOTE:  For this counter, RELEASE COMPLETE
        messages that are a reply to a previous RELEASE
        message and contain the same cause value, are
        redundant (for counting purposes) and should not
        be counted."
    ::= { atmSigStatEntry 7 }

atmSigEmitUnavailResrcs OBJECT-TYPE
    SYNTAX Counter
    ACCESS read-only
    STATUS mandatory
    DESCRIPTION
        "Number of Resource Unavailability transmitted from this
        interface.  This counter is incremented when a RELEASE,
        RELEASE COMPLETE (only when not preceded by a RELEASE message
        for the same call), ADD PARTY REJECT, or STATUS message that
        contains one of the following cause code values is transmitted
        (Note: These cause values apply to both UNI3.0 and UNI3.1
        unless otherwise stated):
        
        Cause Value          Meaning
        
           35          requested VPCI/VCI not available
           37          user cell rate not available (UNI3.1
                       only)
           38          network out of order
        
           41          temporary failure
           45          no VPCI/VCI available
           47          resource unavailable, unspecified
           49          Quality of Service unavailable
           51          user cell rate not available (UNI3.0
                       only)
           58          bearer capability not presently
                       available
           63          Service or option not available,
                       unspecified
           92          too many pending add party requests
        
        NOTE:  For this counter, RELEASE COMPLETE messages that are a
        reply to a previous RELEASE message and contain the same cause
        value, are redundant (for counting purposes) and should not be
        counted."
    ::= { atmSigStatEntry 8 }

atmSigDetectCldPtyEvents OBJECT-TYPE
    SYNTAX Counter
    ACCESS read-only
    STATUS mandatory
    DESCRIPTION
        "Number of Called Party Responsible For Unsuccessful Call
        detected on this interface.  This counter is incremented when a
        RELEASE, RELEASE COMPLETE (only when not preceded by a RELEASE
        message for the same call), ADD PARTY REJECT, or STATUS message
        that contains one of the following cause code values is
        received (Note: These cause values apply to both UNI3.0 and
        UNI3.1):
        
        Cause Value         Meaning
        
           17           user busy
           18           no user responding
           21           call rejected
           22           number changed
           23           user rejects all calls with calling
                        line identification restriction (CLIR)
           27           destination out of order
           31           normal, unspecified
           88           incompatible destination
        
        NOTE:  For this counter, RELEASE COMPLETE messages that are a
        reply to a previous RELEASE message and contain the same cause
        value, are redundant (for counting purposes) and should not be
        
        counted.
        
        Note: Cause Value #30 'response to STATUS ENQUIRY' was not
        included in this memo since it did not apply to a hard
        failure."
    ::= { atmSigStatEntry 9 }

atmSigEmitCldPtyEvents OBJECT-TYPE
    SYNTAX Counter
    ACCESS read-only
    STATUS mandatory
    DESCRIPTION
        "Number of Called Party Responsible For Unsuccessful Call
        transmitted from this interface.  This counter is incremented
        when a RELEASE, RELEASE COMPLETE (only when not preceded by a
        RELEASE message for the same call), ADD PARTY REJECT, or STATUS
        message that contains one of the following cause code values is
        transmitted (Note: These cause values apply to both UNI3.0 and
        UNI3.1):
        
        Cause Value         Meaning
        
           17           user busy
           18           no user responding
           21           call rejected
           22           number changed
           23           user rejects all calls with calling
                        line identification restriction (CLIR)
           27           destination out of order
           31           normal, unspecified
           88           incompatible destination
        
        NOTE:  For this counter, RELEASE COMPLETE messages that are a
        reply to a previous RELEASE message and contain the same cause
        value, are redundant (for counting purposes) and should not be
        counted.
        
        Note: Cause Value #30 'response to STATUS ENQUIRY' was not
        included in this memo since it did not apply to a hard failure."
    ::= { atmSigStatEntry 10 }

atmSigDetectMsgErrors OBJECT-TYPE
    SYNTAX Counter
    ACCESS read-only
    STATUS mandatory
    DESCRIPTION
        "Number of Incorrect Messages detected on this interface.  The
        Incorrect Messages Counter reflects any sort of incorrect
        information in a message.  This includes:
        
        - RELEASE, RELEASE COMPLETE, ADD PARTY REJECT,
          and STATUS messages transmitted, that contain any of
          the Cause values listed below.
        
        - Ignored messages.  These messages are dropped
          because the message was so damaged that it could
          not be further processed.  A list of dropped
          messages is compiled below:
        
           1.  Message with invalid protocol discriminator
        
           2.  Message with errors in the call reference I.E.
                - Bits 5-8 of the first octet not equal to
                  '0000'
                - Bits 1-4 of the first octet indicating a
                  length other than 3 octets
                - RELEASE COMPLETE message received with a
                  call reference that does not relate to a
                  call active or in progress
                - SETUP message received with call reference
                  flag incorrectly set to 1
                - SETUP message received with a call
                  reference for a call that is already
                  active or in progress.
        
           3.  Message too short
        
        The following cause values are monitored by this counter (Note:
        These cause values apply to both UNI3.0 and UNI3.1 unless
        otherwise stated):
        
        Cause Value     Meaning
        
           10     VPCI/VCI unacceptable (UNI3.0 only)
           36     VPCI/VCI assignment failure (UNI3.1 only)
           81     invalid call reference value
           82     identified channel does not exist
           89     invalid endpoint reference
           96     mandatory information element is missing
           97     message type non-existent or not
                  implemented
           99     information element non-existent or not
                  implemented
        
           100    invalid information element contents
           101    message not compatible with call state
           104    incorrect message length
           111    protocol error, unspecified
        
           NOTE:  For this counter, RELEASE COMPLETE messages that are
           a reply to a previous RELEASE message and contain the same
           cause value, are redundant (for counting purposes) and
           should not be counted."
    ::= { atmSigStatEntry 11 }

atmSigEmitMsgErrors OBJECT-TYPE
    SYNTAX Counter
    ACCESS read-only
    STATUS mandatory
    DESCRIPTION
        "Number of Incorrect Messages transmitted on this interface.
        The Incorrect Messages Counter reflects any sort of incorrect
        information in a message.  This includes:
        
        - RELEASE, RELEASE COMPLETE, ADD PARTY REJECT,
          and STATUS messages transmitted or
          received, that contain any of the Cause values
          listed below.
        
        - Ignored messages.  These messages are dropped
          because the message was so damaged that it could
          not be further processed.  A list of dropped
          messages is compiled below:
        
           1.  Message with invalid protocol discriminator
        
           2.  Message with errors in the call reference I.E.
                - Bits 5-8 of the first octet not equal to
                  '0000'
                - Bits 1-4 of the first octet indicating a
                  length other than 3 octets
                - RELEASE COMPLETE message received with a
                  call reference that does not relate to a
                  call active or in progress
                - SETUP message received with call reference
                  flag incorrectly set to 1
                - SETUP message received with a call
                  reference for a call that is already
                  active or in progress.
        
           3.  Message too short
        
        The following cause values are monitored by this counter
        (Note: These cause values apply to both UNI3.0 and UNI3.1
        unless otherwise stated):
        
        Cause Value     Meaning
        
           10     VPCI/VCI unacceptable (UNI3.0 only)
           36     VPCI/VCI assignment failure (UNI3.1 only)
           81     invalid call reference value
           82     identified channel does not exist
           89     invalid endpoint reference
           96     mandatory information element is missing
           97     message type non-existent or not
                  implemented
           99     information element non-existent or not
                  implemented
           100    invalid information element contents
           101    message not compatible with call state
           104    incorrect message length
           111    protocol error, unspecified
        
           NOTE:  For this counter, RELEASE COMPLETE messages that are
           a reply to a previous RELEASE message and contain the same
           cause value, are redundant (for counting purposes) and
           should not be counted."
    ::= { atmSigStatEntry 12 }

atmSigDetectClgPtyEvents OBJECT-TYPE
    SYNTAX Counter
    ACCESS read-only
    STATUS mandatory
    DESCRIPTION
        "Number of Calling Party Events detected on this interface.
        This counter monitors error events that occur due to the
        originating user doing something wrong.  This counter is
        incremented when a RELEASE, RELEASE COMPLETE (only when not
        preceded by a RELEASE message for the same call), ADD PARTY
        REJECT, or STATUS message that contains one of the following
        cause code values is received (Note: These cause values
        apply to both UNI3.0 and UNI3.1):
        
        Cause Value     Meaning
        
           28     invalid number format (address incomplete)
           43     access information discarded
           57     bearer capability not authorized
           65     bearer capability not implemented
        
           73     unsupported combination of traffic
                  parameters
           78     AAL parameters cannot be supported (UNI3.1
                  only)
           91     invalid transit network selection
           93     AAL parameters cannot be supported (UNI3.0
                  only)
        
           NOTE:  For this counter, RELEASE COMPLETE messages that
           are a reply to a previous RELEASE message and contain
           the same cause value, are redundant (for counting purposes)
           and should not be counted."
    ::= { atmSigStatEntry 13 }

atmSigEmitClgPtyEvents OBJECT-TYPE
    SYNTAX Counter
    ACCESS read-only
    STATUS mandatory
    DESCRIPTION
        "Number of Calling Party Events transmitted from this interface.
        This counter monitors error events that occur due to the
        originating user doing something wrong.  This counter is
        incremented when a RELEASE, RELEASE COMPLETE (only when not
        preceded by a RELEASE message for the same call), ADD PARTY
        REJECT, or STATUS message that contains one of the following
        cause code values is transmitted (Note: These cause values
        apply to both UNI3.0 and UNI3.1):
        
        Cause Value     Meaning
        
           28     invalid number format (address incomplete)
           43     access information discarded
           57     bearer capability not authorized
           65     bearer capability not implemented
           73     unsupported combination of traffic
                  parameters
           78     AAL parameters cannot be supported (UNI3.1
                  only)
           91     invalid transit network selection
           93     AAL parameters cannot be supported (UNI3.0
                  only)
        
           NOTE:  For this counter, RELEASE COMPLETE messages that are
           a reply to a previous RELEASE message and contain the same
           cause value, are redundant (for counting purposes) and
           should not be counted."
    ::= { atmSigStatEntry 14 }

atmSigDetectTimerExpireds OBJECT-TYPE
    SYNTAX Counter
    ACCESS read-only
    STATUS mandatory
    DESCRIPTION
        "Number of Timer Expiries detected on this interface.  The Timer
        Expiries Counter provides a count of network timer expiries, and
        to some extent, host or switch timer expiries.  The conditions
        for incrementing this counter are:
        
           - Expiry of any network timer
        
           - Receipt of a RELEASE or RELEASE COMPLETE
             message with Cause #102, 'recovery on
             timer expiry'.
        
           NOTE:  For this counter, RELEASE COMPLETE messages that are
           a reply to a previous RELEASE message and contain the same
           cause value, are redundant (for counting purposes) and
           should not be counted."
    ::= { atmSigStatEntry 15 }

atmSigEmitTimerExpireds OBJECT-TYPE
    SYNTAX Counter
    ACCESS read-only
    STATUS mandatory
    DESCRIPTION
        "Number of Timer Expiries transmitted from this interface.
        The Timer Expiries Counter provides a count of network timer
        expiries, and to some extent, host or switch timer expiries.
        The conditions for incrementing this counter are:
        
           - Expiry of any network timer
        
           - Receipt of a RELEASE or RELEASE COMPLETE
             message with Cause #102, 'recovery on
             timer expiry'.
        
        NOTE:  For this counter, RELEASE COMPLETE messages that are a
        reply to a previous RELEASE message and contain the same cause
        value, are redundant (for counting purposes) and should not be
        counted."
    ::= { atmSigStatEntry 16 }

atmSigDetectRestarts OBJECT-TYPE
    SYNTAX Counter
    ACCESS read-only
    STATUS mandatory
    DESCRIPTION
        "Number of Restart Activity errors detected on this interface.
        The Restart Activity Counter provides a count of host, switch,
        or network restart activity.  This counter is incremented when
        receiving a RESTART message."
    ::= { atmSigStatEntry 17 }

atmSigEmitRestarts OBJECT-TYPE
    SYNTAX Counter
    ACCESS read-only
    STATUS mandatory
    DESCRIPTION
        "Number of Restart Activity errors transmitted from this
        interface.  The Restart Activity Counter provides a count of
        host, switch, or network restart activity.  This counter is
        incremented when transmitting a RESTART message."
    ::= { atmSigStatEntry 18 }

atmSigInEstabls OBJECT-TYPE
    SYNTAX Counter
    ACCESS read-only
    STATUS mandatory
    DESCRIPTION
        "Number of SVCs established at this signalling entity for
        incoming connections."
    ::= { atmSigStatEntry 19 }

atmSigOutEstabls OBJECT-TYPE
    SYNTAX Counter
    ACCESS read-only
    STATUS mandatory
    DESCRIPTION
        "Number of SVCs established at this signalling entity for
        outgoing connections."
    ::= { atmSigStatEntry 20 }

atmSigSupportTable OBJECT-TYPE
    SYNTAX SEQUENCE OF AtmSigSupportEntry
    ACCESS not-accessible
    STATUS mandatory
    DESCRIPTION
        "This table contains ATM local interface configuration
        parameters, one entry per ATM signalling interface."
    ::= { atm2MIBObjects 4 }

atmSigSupportEntry OBJECT-TYPE
    SYNTAX AtmSigSupportEntry
    ACCESS not-accessible
    STATUS mandatory
    DESCRIPTION
        "This list contains signalling configuration parameters
        and state variables."
    INDEX { ifIndex }
    ::= { atmSigSupportTable 1 }

AtmSigSupportEntry ::= SEQUENCE {
    atmSigSupportClgPtyNumDel INTEGER,
    atmSigSupportClgPtySubAddr INTEGER,
    atmSigSupportCldPtySubAddr INTEGER,
    atmSigSupportHiLyrInfo INTEGER,
    atmSigSupportLoLyrInfo INTEGER,
    atmSigSupportBlliRepeatInd INTEGER,
    atmSigSupportAALInfo INTEGER,
    atmSigSupportPrefCarrier OCTET STRING
    }

atmSigSupportClgPtyNumDel OBJECT-TYPE
    SYNTAX INTEGER {
        enabled(1),
        disabled(2)
        }
    ACCESS read-write
    STATUS mandatory
    DESCRIPTION
        "This object indicates whether the Calling Party Number
        Information Element is transferred to the called party
        address.  The value of this object can be:
        
          - enabled(1)  This Information Element is transferred
                        to the called party
        
          - disabled(2) This Information Element is NOT
                        transferred to the called party."
    ::= { atmSigSupportEntry 1 }

atmSigSupportClgPtySubAddr OBJECT-TYPE
    SYNTAX INTEGER {
        enabled(1),
        disabled(2)
        }
    ACCESS read-write
    STATUS mandatory
    DESCRIPTION
        "This object indicates whether to accept and transfer the Calling
        Party Subaddress Information Element from the calling party to
        the called party.  Calling party subaddress information shall
        only be transferred to the called party if calling party number
        delivery is enabled (i.e., atmSigSupportClgPtyNumDel =
        'enabled(1)'.  The value of this object can be:
        
          - enabled(1)  This Information Element is transferred
                        to the called party
        
          - disabled(2) This Information Element is NOT
                        transferred to the called party."
    ::= { atmSigSupportEntry 2 }

atmSigSupportCldPtySubAddr OBJECT-TYPE
    SYNTAX INTEGER {
        enabled(1),
        disabled(2)
        }
    ACCESS read-write
    STATUS mandatory
    DESCRIPTION
        "This object indicates whether to accept, transfer, and deliver
        the Called Party Subaddress Information Element from the calling
        party to the called party.  The value of this object can be:
        
          - enabled(1)  This Information Element is transferred
                        to the called party
        
          - disabled(2) This Information Element is NOT
                        transferred to the called party."
    ::= { atmSigSupportEntry 3 }

atmSigSupportHiLyrInfo OBJECT-TYPE
    SYNTAX INTEGER {
        enabled(1),
        disabled(2)
        }
    ACCESS read-write
    STATUS mandatory
    DESCRIPTION
        "This object indicates whether to accept, transfer, and deliver
        the Broadband High Layer Information Element from the calling
        party to the called party.  The value of this object can be:
        
          - enabled(1)  This Information Element is transferred
                        to the called party
        
          - disabled(2) This Information Element is NOT
                        transferred to the called party."
    ::= { atmSigSupportEntry 4 }

atmSigSupportLoLyrInfo OBJECT-TYPE
    SYNTAX INTEGER {
        enabled(1),
        disabled(2)
        }
    ACCESS read-write
    STATUS mandatory
    DESCRIPTION
        "This object indicates whether to accept, transfer, and deliver
        the Broadband Low Layer Information Element from the calling
        party to the called party.  The value of this object can be:
        
          - enabled(1)  This Information Element is transferred
                        to the called party
        
          - disabled(2) This Information Element is NOT
                        transferred to the called party."
    ::= { atmSigSupportEntry 5 }

atmSigSupportBlliRepeatInd OBJECT-TYPE
    SYNTAX INTEGER {
        enabled(1),
        disabled(2)
        }
    ACCESS read-write
    STATUS mandatory
    DESCRIPTION
        "This object indicates whether to accept, transfer, and deliver
        the Broadband Repeat Indicator with two or three instances of
        the Broadband Low Layer Information Element for low layer
        information selection from the calling party to the called
        party.  This object's value should always be disabled(2) if
        the value of atmSigSupportLolyrInfo is disabled(2).
        
        The value of this object can be:
        
        - enabled(1)  This Information Element is transferred
              to the called party
        
        - disabled(2) This Information Element is NOT
              transferred to the called party."
    ::= { atmSigSupportEntry 6 }

atmSigSupportAALInfo OBJECT-TYPE
    SYNTAX INTEGER {
        enabled(1),
        disabled(2)
        }
    ACCESS read-write
    STATUS mandatory
    DESCRIPTION
        "This object indicates whether to accept, transfer, and deliver
        the ATM Adaptation Layer Parameters Information Element from the
        calling party to the called party.  The value of this object can
        be:
        
          - enabled(1)  This Information Element is transferred
                        to the called party
        
          - disabled(2) This Information Element is NOT
                        transferred to the called party."
    ::= { atmSigSupportEntry 7 }

atmSigSupportPrefCarrier OBJECT-TYPE
    SYNTAX OCTET STRING(SIZE(0|4))
    ACCESS read-write
    STATUS mandatory
    DESCRIPTION
        "This parameter identifies the carrier to which intercarrier
        calls originated from this interface are routed when transit
        network selection information is not provided by the calling
        party.  If a Carrier Identification Code (CIC) is used the
        parameter shall contain the CIC.  For three-digit CICs, the first
        octet shall be '0' and the CIC is contained in the three
        following octets.  If the preferred carrier feature is not
        supported the value is a zero-length string."
    ::= { atmSigSupportEntry 8 }

atmSigDescrParamTable OBJECT-TYPE
    SYNTAX SEQUENCE OF AtmSigDescrParamEntry
    ACCESS not-accessible
    STATUS mandatory
    DESCRIPTION
        "A table contains signalling capabilities of VCLs except the
        Traffic Descriptor.  Traffic descriptors are described in
        the atmTrafficDescrParamTable."
    REFERENCE
        "ATM User-Network Interface Specification, Version 3.1 (UNI
        3.1), September 1994, Section 5.4.5 Variable Length
        Information Elements."
    ::= { atm2MIBObjects 5 }

atmSigDescrParamEntry OBJECT-TYPE
    SYNTAX AtmSigDescrParamEntry
    ACCESS not-accessible
    STATUS mandatory
    DESCRIPTION
        "Each entry in this table represents a
        set of signalling capabilities that can
        be applied to a VCL.  There is no requirement
        for unique entries, except that the index must
        be unique."
    INDEX { atmSigDescrParamIndex }
    ::= { atmSigDescrParamTable 1 }

AtmSigDescrParamEntry ::= SEQUENCE {
    atmSigDescrParamIndex AtmSigDescrParamIndex,
    atmSigDescrParamAalType INTEGER,
    atmSigDescrParamAalSscsType INTEGER,
    atmSigDescrParamBhliType INTEGER,
    atmSigDescrParamBhliInfo OCTET STRING,
    atmSigDescrParamBbcConnConf INTEGER,
    atmSigDescrParamBlliLayer2 INTEGER,
    atmSigDescrParamBlliLayer3 INTEGER,
    atmSigDescrParamBlliPktSize INTEGER,
    atmSigDescrParamBlliSnapId INTEGER,
    atmSigDescrParamBlliOuiPid OCTET STRING,
    atmSigDescrParamRowStatus RowStatus
    }

atmSigDescrParamIndex OBJECT-TYPE
    SYNTAX AtmSigDescrParamIndex
--    Rsyntax INTEGER(0..2147483647)
    ACCESS not-accessible
    STATUS mandatory
    DESCRIPTION
        "The value of this object is used by the
        atmVclGenSigDescrIndex object in the atmVclGenTable to
        identify a row in this table."
    ::= { atmSigDescrParamEntry 1 }

atmSigDescrParamAalType OBJECT-TYPE
    SYNTAX INTEGER {
        other(1),
        aal1(2),
        aal34(3),
        aal5(4),
        userDefined(5),
        aal2(6)
        }
    ACCESS read-write
    STATUS mandatory
    DESCRIPTION
        "The AAL type.  The value of this object is set to other(1)
        when not defined."
    DEFVAL { other }
    ::= { atmSigDescrParamEntry 2 }

atmSigDescrParamAalSscsType OBJECT-TYPE
    SYNTAX INTEGER {
        other(1),
        assured(2),
        nonassured(3),
        frameRelay(4),
        null(5)
        }
    ACCESS read-write
    STATUS mandatory
    DESCRIPTION
        "The SSCS type used by this entry."
    DEFVAL { other }
    ::= { atmSigDescrParamEntry 3 }

atmSigDescrParamBhliType OBJECT-TYPE
    SYNTAX INTEGER {
        other(1),
        iso(2),
        user(3),
        hiProfile(4),
        vendorSpecific(5)
        }
    ACCESS read-write
    STATUS mandatory
    DESCRIPTION
        "The Broadband high layer type."
    DEFVAL { other }
    ::= { atmSigDescrParamEntry 4 }

atmSigDescrParamBhliInfo OBJECT-TYPE
    SYNTAX OCTET STRING(SIZE(0..8))
    ACCESS read-write
    STATUS mandatory
    DESCRIPTION
        "The Broadband high layer information.  When
        atmSigDescrParamBhliType is set to iso(2), the value of this
        object is a zero length string.  When
        atmSigDescrParamBhliType is set to user(3), the value of
        this object is an octet string with length ranging from 0 to
        8.  When atmSigDescrParamBhliType is set to hiProfile(4),
        the value of this object is a length of 4 octet string
        containing user to user profile identifier.  When
        atmSigDescrParamBhliType is set to vendorSpecific(5), the
        value of this object is a length of 7 octet string, where
        the most significant 3 octets consist of a globally-
        administered OUI, and the least significant 4 octets are the
        vender administered application OUI."
    DEFVAL { ''H }
    ::= { atmSigDescrParamEntry 5 }

atmSigDescrParamBbcConnConf OBJECT-TYPE
    SYNTAX INTEGER {
        ptp(1),
        ptmp(2)
        }
    ACCESS read-write
    STATUS mandatory
    DESCRIPTION
        "The Broadband bearer capability user plane connection
         configuration parameter."
    DEFVAL { ptp }
    ::= { atmSigDescrParamEntry 6 }

atmSigDescrParamBlliLayer2 OBJECT-TYPE
    SYNTAX INTEGER {
        other(1),
        iso1745(2),
        q921(3),
        x25linklayer(4),
        x25multilink(5),
        lapb(6),
        hdlcArm(7),
        hdlcNrm(8),
        hdlcAbm(9),
        iso88022(10),
        x75slp(11),
        q922(12),
        userDef(13),
        iso7776(14)
        }
    ACCESS read-write
    STATUS mandatory
    DESCRIPTION
        "The Broadband low layer information, protocol type of layer
        2.  The value of this object is other(1) if layer 2 protocol
        is not used."
    DEFVAL { other }
    ::= { atmSigDescrParamEntry 7 }

atmSigDescrParamBlliLayer3 OBJECT-TYPE
    SYNTAX INTEGER {
        other(1),
        x25pkt(2),
        isoiec8208(3),
        x223iso8878(4),
        isoiec8473(5),
        t70(6),
        tr9577(7),
        userDef(8)
        }
    ACCESS read-write
    STATUS mandatory
    DESCRIPTION
        "The Broadband low layer information, protocol type of layer
        
        3.  The value of this object is other(1) if layer 3 protocol
        is not used."
    DEFVAL { other }
    ::= { atmSigDescrParamEntry 8 }

atmSigDescrParamBlliPktSize OBJECT-TYPE
    SYNTAX INTEGER {
        other(1),
        s16(2),
        s32(3),
        s64(4),
        s128(5),
        s256(6),
        s512(7),
        s1024(8),
        s2048(9),
        s4096(10)
        }
    ACCESS read-write
    STATUS mandatory
    DESCRIPTION
        "The default packet size defined in B-LLI."
    DEFVAL { other }
    ::= { atmSigDescrParamEntry 9 }

atmSigDescrParamBlliSnapId OBJECT-TYPE
    SYNTAX INTEGER {
        other(1),
        true(2),
        false(3)
        }
    ACCESS read-write
    STATUS mandatory
    DESCRIPTION
        "The SNAP ID used for Broadband low layer protocol layer 3.
        The value of this object is other(1) if
        atmSigDescrParamBlliLayer3 is set to other(1)."
    DEFVAL { other }
    ::= { atmSigDescrParamEntry 10 }

atmSigDescrParamBlliOuiPid OBJECT-TYPE
    SYNTAX OCTET STRING(SIZE(0|5))
    ACCESS read-write
    STATUS mandatory
    DESCRIPTION
        "The OUI/PID encoding for Broadband low layer protocol layer
        3.  The value of this object is a zero length string if
        atmSigDescrParamBlliLayer3 is set to other(1).  When used,
        it is always 5 octets with the most significant octet as the
        OUI Octet 1 and the least significant octet as the PID Octet
        2."
    DEFVAL { ''H }
    ::= { atmSigDescrParamEntry 11 }

atmSigDescrParamRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create and delete rows in the
        atmSigDescrParamTable."
    ::= { atmSigDescrParamEntry 12 }

atmIfRegisteredAddrTable OBJECT-TYPE
    SYNTAX SEQUENCE OF AtmIfRegisteredAddrEntry
    ACCESS not-accessible
    STATUS mandatory
    DESCRIPTION
        "This table contains a list of ATM addresses that can be used for
        calls to and from a given interface by a switch or service.  The
        ATM addresses are either registered by the endsystem via ILMI or
        statically configured.  This table does not expose PNNI
        reachability information.  ILMI registered addresses cannot be
        deleted using this table.  This table only applies to switches
        and network services."
    ::= { atm2MIBObjects 6 }

atmIfRegisteredAddrEntry OBJECT-TYPE
    SYNTAX AtmIfRegisteredAddrEntry
    ACCESS not-accessible
    STATUS mandatory
    DESCRIPTION
        "An entry in the ATM Interface Registered Address table."
    INDEX { ifIndex, atmIfRegAddrAddress }
    ::= { atmIfRegisteredAddrTable 1 }

AtmIfRegisteredAddrEntry ::= SEQUENCE {
    atmIfRegAddrAddress AtmAddr,
    atmIfRegAddrAddressSource INTEGER,
    atmIfRegAddrOrgScope INTEGER,
    atmIfRegAddrRowStatus RowStatus
    }

atmIfRegAddrAddress OBJECT-TYPE
    SYNTAX AtmAddr
--    Rsyntax OCTET STRING(SIZE(0..40))
    ACCESS not-accessible
    STATUS mandatory
    DESCRIPTION
        "An address registered for a given switch or service interface."
    ::= { atmIfRegisteredAddrEntry 1 }

atmIfRegAddrAddressSource OBJECT-TYPE
    SYNTAX INTEGER {
        other(1),
        static(2),
        dynamic(3)
        }
    ACCESS read-only
    STATUS mandatory
    DESCRIPTION
        "The type of address source for a given ATM Address. The value
        dynamic(3) is indicated when ILMI is used."
    ::= { atmIfRegisteredAddrEntry 2 }

atmIfRegAddrOrgScope OBJECT-TYPE
    SYNTAX INTEGER {
        localNetwork(1),
        localNetworkPlusOne(2),
        localNetworkPlusTwo(3),
        siteMinusOne(4),
        intraSite(5),
        sitePlusOne(6),
        organizationMinusOne(7),
        intraOrganization(8),
        organizationPlusOne(9),
        communityMinusOne(10),
        intraCommunity(11),
        communityPlusOne(12),
        regional(13),
        interRegional(14),
        global(15)
        }
    ACCESS read-write
    STATUS mandatory
    DESCRIPTION
        "This object indicates the organizational scope for
        the referenced address.  The information of the
        referenced address shall not be distributed outside
        the indicated scope.   Refer to Annex 5.3 of ATM
        Forum UNI Signalling 4.0 for guidelines regarding
        the use of organizational scopes.
        
        This value cannot be configured for ILMI-registered
        addresses.
        
        The default values for organizational scope are
        localNetwork(1) for ATM group addresses, and
        global(15) for individual addresses."
    ::= { atmIfRegisteredAddrEntry 3 }

atmIfRegAddrRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create and delete rows in the
        atmIfRegisteredAddrTable.  Rows created dynamically (e.g., ILMI-
        registered addresses) cannot be deleted using this object."
    ::= { atmIfRegisteredAddrEntry 4 }

atmVclAddrTable OBJECT-TYPE
    SYNTAX SEQUENCE OF AtmVclAddrEntry
    ACCESS not-accessible
    STATUS mandatory
    DESCRIPTION
        "This table provides a mapping between the atmVclTable and
        the ATM called party/calling party address.  This table can
        be used to retrieve the calling party and called party ATM
        address pair for a given VCL.  Note that there can be more
        than one pair of calling party and called party ATM
        addresses for a VCL in a point to multi-point call."
    ::= { atm2MIBObjects 7 }

atmVclAddrEntry OBJECT-TYPE
    SYNTAX AtmVclAddrEntry
    ACCESS not-accessible
    STATUS mandatory
    DESCRIPTION
        "Each entry in this table represents a binding between a VCL
        and an ATM address associated with this call.  This ATM
        
        address can be either the called party address or the
        calling party address.  There can be more than one pair of
        calling/called party ATM addresses associated with the VCL
        entry for point to multi-point calls.  Objects
        atmVclAddrType, and atmVclAddrRowStatus are
        required during row creation."
    INDEX { ifIndex, atmVclVpi, atmVclVci, atmVclAddrAddr }
    ::= { atmVclAddrTable 1 }

AtmVclAddrEntry ::= SEQUENCE {
    atmVclAddrAddr AtmAddr,
    atmVclAddrType INTEGER,
    atmVclAddrRowStatus RowStatus
    }

atmVclAddrAddr OBJECT-TYPE
    SYNTAX AtmAddr
--    Rsyntax OCTET STRING(SIZE(0..40))
    ACCESS not-accessible
    STATUS mandatory
    DESCRIPTION
        "An ATM address on one end of the VCL.  For SVCs, the agent
        supplies the value of this object at creation time.  For PVC
        VCL, the manager can supply the value of this object during
        or after the PVC VCL creation."
    ::= { atmVclAddrEntry 1 }

atmVclAddrType OBJECT-TYPE
    SYNTAX INTEGER {
        callingParty(1),
        calledParty(2)
        }
    ACCESS read-write
    STATUS mandatory
    DESCRIPTION
        "The type of ATM Address represented by the object
        atmVclAddrAddr.  Choices are either the calling party ATM
        address or the called party ATM address."
    ::= { atmVclAddrEntry 2 }

atmVclAddrRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or destroy an
        entry from this table.  Note that the manager entity
        
        can only destroy the PVC VCLs."
    ::= { atmVclAddrEntry 3 }

atmAddrVclTable OBJECT-TYPE
    SYNTAX SEQUENCE OF AtmAddrVclEntry
    ACCESS not-accessible
    STATUS mandatory
    DESCRIPTION
        "This table provides an alternative way to retrieve the
        atmVclTable.  This table can be used to retrieve the
        indexing to the atmVclTable by an ATM address."
    ::= { atm2MIBObjects 8 }

atmAddrVclEntry OBJECT-TYPE
    SYNTAX AtmAddrVclEntry
    ACCESS not-accessible
    STATUS mandatory
    DESCRIPTION
        "Each entry in this table represents an entry in the
        atmVclTable of the ATM-MIB by its ATM address.  The ATM
        address is either the calling or called party ATM address
        of the call.  Entries in this table are read only.
        They show up when entries are created in the
        atmVclAddrTable."
    REFERENCE
        "Tesink, K., Editor, Definitions of Managed Objects
         for ATM Management, RFC 2515, Bell Communications
         Research, February, 1999."
    INDEX { atmVclAddrAddr, atmAddrVclAtmIfIndex, atmAddrVclVpi, atmAddrVclVci }
    ::= { atmAddrVclTable 1 }

AtmAddrVclEntry ::= SEQUENCE {
    atmAddrVclAtmIfIndex InterfaceIndex,
    atmAddrVclVpi AtmVpIdentifier,
    atmAddrVclVci AtmVcIdentifier,
    atmAddrVclAddrType INTEGER
    }

atmAddrVclAtmIfIndex OBJECT-TYPE
    SYNTAX InterfaceIndex
--    Rsyntax INTEGER(1..2147483647)
    ACCESS not-accessible
    STATUS mandatory
    DESCRIPTION
        "The interface index of the ATM interface to which this
         VCL pertains.  This object combined with the
         atmAddrVclVpi and atmAddrVclVci objects serves as an
         index to the atmVclTable."
    ::= { atmAddrVclEntry 1 }

atmAddrVclVpi OBJECT-TYPE
    SYNTAX AtmVpIdentifier
--    Rsyntax INTEGER(0..4095)
    ACCESS not-accessible
    STATUS mandatory
    DESCRIPTION
        "The VPI value of the VCL.  This object combined with the
        atmAddrVclAtmIfIndex and atmAddrVclVci objects serves as
        an index to the atmVclTable."
    ::= { atmAddrVclEntry 2 }

atmAddrVclVci OBJECT-TYPE
    SYNTAX AtmVcIdentifier
--    Rsyntax INTEGER(0..65535)
    ACCESS not-accessible
    STATUS mandatory
    DESCRIPTION
        "The VCI value of the VCL.  This object combined with the
        atmAddrVclAtmIfIndex and atmAddrVclVpi objects serves as
        an index to the atmVclTable."
    ::= { atmAddrVclEntry 3 }

atmAddrVclAddrType OBJECT-TYPE
    SYNTAX INTEGER {
        callingParty(1),
        calledParty(2)
        }
    ACCESS read-only
    STATUS mandatory
    DESCRIPTION
        "The type of ATM Address represented by the object
        atmVclAddrAddr.  Choices are either calling party address
        or called party address."
    ::= { atmAddrVclEntry 4 }

atmVplStatTable OBJECT-TYPE
    SYNTAX SEQUENCE OF AtmVplStatEntry
    ACCESS not-accessible
    STATUS mandatory
    DESCRIPTION
        "This table contains all statistics counters per VPL.  It is
        used to monitor the usage of the VPL in terms of incoming
        cells and outgoing cells."
    ::= { atm2MIBObjects 9 }

atmVplStatEntry OBJECT-TYPE
    SYNTAX AtmVplStatEntry
    ACCESS not-accessible
    STATUS mandatory
    DESCRIPTION
        "Each entry in this table represents a VPL."
    INDEX { ifIndex, atmVplVpi }
    ::= { atmVplStatTable 1 }

AtmVplStatEntry ::= SEQUENCE {
    atmVplStatTotalCellIns Counter,
    atmVplStatClp0CellIns Counter,
    atmVplStatTotalDiscards Counter,
    atmVplStatClp0Discards Counter,
    atmVplStatTotalCellOuts Counter,
    atmVplStatClp0CellOuts Counter,
    atmVplStatClp0Tagged Counter
    }

atmVplStatTotalCellIns OBJECT-TYPE
    SYNTAX Counter
    ACCESS read-only
    STATUS mandatory
    DESCRIPTION
        "The total number of valid ATM cells received by this VPL
        including both CLP=0 and CLP=1 cells.  The cells are
        counted prior to the application of the traffic policing."
    ::= { atmVplStatEntry 1 }

atmVplStatClp0CellIns OBJECT-TYPE
    SYNTAX Counter
    ACCESS read-only
    STATUS mandatory
    DESCRIPTION
        "The number of valid ATM cells received by this VPL with
        CLP=0.  The cells are counted prior to the application of
        the traffic policing."
    ::= { atmVplStatEntry 2 }

atmVplStatTotalDiscards OBJECT-TYPE
    SYNTAX Counter
    ACCESS read-only
    STATUS mandatory
    DESCRIPTION
        "The total number of valid ATM cells discarded by the
        traffic policing entity.  This includes cells originally
        received with CLP=0 and CLP=1."
    ::= { atmVplStatEntry 3 }

atmVplStatClp0Discards OBJECT-TYPE
    SYNTAX Counter
    ACCESS read-only
    STATUS mandatory
    DESCRIPTION
        "The total number of valid ATM cells received with CLP=0 and
        discarded by the traffic policing entity."
    ::= { atmVplStatEntry 4 }

atmVplStatTotalCellOuts OBJECT-TYPE
    SYNTAX Counter
    ACCESS read-only
    STATUS mandatory
    DESCRIPTION
        "The total number of valid ATM cells transmitted  by this
        VPL.  This includes both CLP=0 and CLP=1 cells."
    ::= { atmVplStatEntry 5 }

atmVplStatClp0CellOuts OBJECT-TYPE
    SYNTAX Counter
    ACCESS read-only
    STATUS mandatory
    DESCRIPTION
        "The total number of valid ATM cells transmitted with CLP=0
        by this VPL."
    ::= { atmVplStatEntry 6 }

atmVplStatClp0Tagged OBJECT-TYPE
    SYNTAX Counter
    ACCESS read-only
    STATUS mandatory
    DESCRIPTION
        "The total number of valid ATM cells tagged by the traffic
        policing entity from CLP=0 to CLP=1."
    ::= { atmVplStatEntry 7 }

atmVplLogicalPortTable OBJECT-TYPE
    SYNTAX SEQUENCE OF AtmVplLogicalPortEntry
    ACCESS not-accessible
    STATUS mandatory
    DESCRIPTION
        "Indicates whether the VPL is an ATM Logical Port interface
        (ifType=80)."
    ::= { atm2MIBObjects 10 }

atmVplLogicalPortEntry OBJECT-TYPE
    SYNTAX AtmVplLogicalPortEntry
    ACCESS not-accessible
    STATUS mandatory
    DESCRIPTION
        "An entry with information about the ATM Logical Port
        interface."
    INDEX { ifIndex, atmVplVpi }
-- Augments atmVplEntry FROM ATM-MIB
    ::= { atmVplLogicalPortTable 1 }

AtmVplLogicalPortEntry ::= SEQUENCE {
    atmVplLogicalPortDef INTEGER,
    atmVplLogicalPortIndex InterfaceIndexOrZero
    }

atmVplLogicalPortDef OBJECT-TYPE
    SYNTAX INTEGER {
        notLogicalIf(1),
        isLogicalIf(2)
        }
    ACCESS read-write
    STATUS mandatory
    DESCRIPTION
        "Indicates whether the VPC at this VPL interface is an ATM
        Logical Port interface."
    DEFVAL { notLogicalIf }
    ::= { atmVplLogicalPortEntry 1 }

atmVplLogicalPortIndex OBJECT-TYPE
    SYNTAX InterfaceIndexOrZero
--    Rsyntax INTEGER(0..2147483647)
    ACCESS read-only
    STATUS mandatory
    DESCRIPTION
        "The ifTable index of the ATM logical port interface
        associated with this VPL. The distinguished value of zero
        indicates that the agent has not (yet) assigned such an
        ifTable Index. The zero value must be assigned by the agent
        if the value of atmVplLogicalPortDef is set to notLogicalIf,
        or if the VPL row is not active."
    ::= { atmVplLogicalPortEntry 2 }

atmVclStatTable OBJECT-TYPE
    SYNTAX SEQUENCE OF AtmVclStatEntry
    ACCESS not-accessible
    STATUS mandatory
    DESCRIPTION
        "This table contains all statistics counters per VCL.  It is
        used to monitor the usage of the VCL in terms of incoming
        cells and outgoing cells."
    ::= { atm2MIBObjects 11 }

atmVclStatEntry OBJECT-TYPE
    SYNTAX AtmVclStatEntry
    ACCESS not-accessible
    STATUS mandatory
    DESCRIPTION
        "Each entry in this table represents a VCL."
    INDEX { ifIndex, atmVclVpi, atmVclVci }
    ::= { atmVclStatTable 1 }

AtmVclStatEntry ::= SEQUENCE {
    atmVclStatTotalCellIns Counter,
    atmVclStatClp0CellIns Counter,
    atmVclStatTotalDiscards Counter,
    atmVclStatClp0Discards Counter,
    atmVclStatTotalCellOuts Counter,
    atmVclStatClp0CellOuts Counter,
    atmVclStatClp0Tagged Counter
    }

atmVclStatTotalCellIns OBJECT-TYPE
    SYNTAX Counter
    ACCESS read-only
    STATUS mandatory
    DESCRIPTION
        "The total number of valid ATM cells received by this VCL
        including both CLP=0 and CLP=1 cells.  The cells are counted
        prior to the application of the traffic policing."
    ::= { atmVclStatEntry 1 }

atmVclStatClp0CellIns OBJECT-TYPE
    SYNTAX Counter
    ACCESS read-only
    STATUS mandatory
    DESCRIPTION
        "The number of valid ATM cells received by this VCL with
        CLP=0.  The cells are counted prior to the application of
        the traffic policing."
    ::= { atmVclStatEntry 2 }

atmVclStatTotalDiscards OBJECT-TYPE
    SYNTAX Counter
    ACCESS read-only
    STATUS mandatory
    DESCRIPTION
        "The total number of valid ATM cells discarded by the
        traffic policing entity.  This includes cells originally
        received with CLP=0 and CLP=1."
    ::= { atmVclStatEntry 3 }

atmVclStatClp0Discards OBJECT-TYPE
    SYNTAX Counter
    ACCESS read-only
    STATUS mandatory
    DESCRIPTION
        "The total number of valid ATM cells received with CLP=0
         and discarded by the traffic policing entity."
    ::= { atmVclStatEntry 4 }

atmVclStatTotalCellOuts OBJECT-TYPE
    SYNTAX Counter
    ACCESS read-only
    STATUS mandatory
    DESCRIPTION
        "The total number of valid ATM cells transmitted  by this
        VCL.  This includes both CLP=0 and CLP=1 cells."
    ::= { atmVclStatEntry 5 }

atmVclStatClp0CellOuts OBJECT-TYPE
    SYNTAX Counter
    ACCESS read-only
    STATUS mandatory
    DESCRIPTION
        "The total number of valid ATM cells transmitted with CLP=0
        by this VCL."
    ::= { atmVclStatEntry 6 }

atmVclStatClp0Tagged OBJECT-TYPE
    SYNTAX Counter
    ACCESS read-only
    STATUS mandatory
    DESCRIPTION
        "The total number of valid ATM cells tagged by the traffic
        policing entity from CLP=0 to CLP=1."
    ::= { atmVclStatEntry 7 }

atmAal5VclStatTable OBJECT-TYPE
    SYNTAX SEQUENCE OF AtmAal5VclStatEntry
    ACCESS not-accessible
    STATUS mandatory
    DESCRIPTION
        "This table provides a collection of objects providing AAL5
        configuration and performance statistics of a VCL."
    ::= { atm2MIBObjects 12 }

atmAal5VclStatEntry OBJECT-TYPE
    SYNTAX AtmAal5VclStatEntry
    ACCESS not-accessible
    STATUS mandatory
    DESCRIPTION
        "Each entry in this table represents an AAL5 VCL, and
         is indexed by ifIndex values of AAL5 interfaces and
         the associated VPI/VCI values."
    INDEX { ifIndex, atmVclVpi, atmVclVci }
    ::= { atmAal5VclStatTable 1 }

AtmAal5VclStatEntry ::= SEQUENCE {
    atmAal5VclInPkts Counter,
    atmAal5VclOutPkts Counter,
    atmAal5VclInOctets Counter,
    atmAal5VclOutOctets Counter
    }

atmAal5VclInPkts OBJECT-TYPE
    SYNTAX Counter
    ACCESS read-only
    STATUS mandatory
    DESCRIPTION
        "The number of AAL5 CPCS PDUs received on the AAL5 VCC at
        the interface identified by the ifIndex."
    ::= { atmAal5VclStatEntry 1 }

atmAal5VclOutPkts OBJECT-TYPE
    SYNTAX Counter
    ACCESS read-only
    STATUS mandatory
    DESCRIPTION
        "The number of AAL5 CPCS PDUs transmitted on the AAL5 VCC
         at the interface identified by the ifIndex."
    ::= { atmAal5VclStatEntry 2 }

atmAal5VclInOctets OBJECT-TYPE
    SYNTAX Counter
    ACCESS read-only
    STATUS mandatory
    DESCRIPTION
        "The number of octets contained in AAL5 CPCS PDUs received
        on the AAL5 VCC at the interface identified by the ifIndex."
    ::= { atmAal5VclStatEntry 3 }

atmAal5VclOutOctets OBJECT-TYPE
    SYNTAX Counter
    ACCESS read-only
    STATUS mandatory
    DESCRIPTION
        "The number of octets contained in AAL5 CPCS PDUs
        transmitted on the AAL5 VCC at the interface identified by
        the ifIndex."
    ::= { atmAal5VclStatEntry 4 }

atmVclGenTable OBJECT-TYPE
    SYNTAX SEQUENCE OF AtmVclGenEntry
    ACCESS not-accessible
    STATUS mandatory
    DESCRIPTION
        "General Information for each VC."
    ::= { atm2MIBObjects 13 }

atmVclGenEntry OBJECT-TYPE
    SYNTAX AtmVclGenEntry
    ACCESS not-accessible
    STATUS mandatory
    DESCRIPTION
        "An entry with general information about the ATM VC."
    INDEX { ifIndex, atmVclVpi, atmVclVci }
-- Augments atmVclEntry FROM ATM-MIB
    ::= { atmVclGenTable 1 }

AtmVclGenEntry ::= SEQUENCE {
    atmVclGenSigDescrIndex AtmSigDescrParamIndex
    }

atmVclGenSigDescrIndex OBJECT-TYPE
    SYNTAX AtmSigDescrParamIndex
--    Rsyntax INTEGER(0..2147483647)
    ACCESS read-write
    STATUS mandatory
    DESCRIPTION
        "The value of this object identifies the row in the ATM
        Signalling Descriptor Parameter Table which applies to this
        VCL."
    ::= { atmVclGenEntry 1 }

atmInterfaceExtTable OBJECT-TYPE
    SYNTAX SEQUENCE OF AtmInterfaceExtEntry
    ACCESS not-accessible
    STATUS mandatory
    DESCRIPTION
        "This table contains ATM interface configuration and monitoring
        information not defined in the atmInterfaceConfTable from the
        ATM-MIB.  This includes the type of connection setup procedures,
        ILMI information, and information on the VPI/VCI range."
    REFERENCE
        "Tesink, K., Editor, Definitions of Managed Objects
         for ATM Management, RFC 2515, Bell Communications
         Research, February, 1999."
    ::= { atm2MIBObjects 14 }

atmInterfaceExtEntry OBJECT-TYPE
    SYNTAX AtmInterfaceExtEntry
    ACCESS not-accessible
    STATUS mandatory
    DESCRIPTION
        "An entry extends the atmInterfaceConfEntry defined in the ATM-
        MIB.  Each entry corresponds to an ATM interface."
    REFERENCE
        "Tesink, K., Editor, Definitions of Managed Objects
         for ATM Management, RFC 2515, Bell Communications
         Research, February, 1999."
    INDEX { ifIndex }
-- Augments atmInterfaceConfEntry FROM ATM-MIB
    ::= { atmInterfaceExtTable 1 }

AtmInterfaceExtEntry ::= SEQUENCE {
    atmIntfConfigType AtmInterfaceType,
    atmIntfActualType AtmInterfaceType,
    atmIntfConfigSide INTEGER,
    atmIntfActualSide INTEGER,
    atmIntfIlmiAdminStatus OCTET STRING,
    atmIntfIlmiOperStatus OCTET STRING,
    atmIntfIlmiFsmState INTEGER,
    atmIntfIlmiEstablishConPollIntvl INTEGER,
    atmIntfIlmiCheckConPollIntvl INTEGER,
    atmIntfIlmiConPollInactFactor INTEGER,
    atmIntfIlmiPublicPrivateIndctr INTEGER,
    atmInterfaceConfMaxSvpcVpi INTEGER,
    atmInterfaceCurrentMaxSvpcVpi INTEGER,
    atmInterfaceConfMaxSvccVpi INTEGER,
    atmInterfaceCurrentMaxSvccVpi INTEGER,
    atmInterfaceConfMinSvccVci INTEGER,
    atmInterfaceCurrentMinSvccVci INTEGER,
    atmIntfSigVccRxTrafficDescrIndex AtmTrafficDescrParamIndex,
    atmIntfSigVccTxTrafficDescrIndex AtmTrafficDescrParamIndex,
    atmIntfPvcFailures Counter,
    atmIntfCurrentlyFailingPVpls Gauge,
    atmIntfCurrentlyFailingPVcls Gauge,
    atmIntfPvcFailuresTrapEnable TruthValue,
    atmIntfPvcNotificationInterval INTEGER,
    atmIntfLeafSetupFailures Counter,
    atmIntfLeafSetupRequests Counter
    }

atmIntfConfigType OBJECT-TYPE
    SYNTAX AtmInterfaceType
--    Rsyntax INTEGER {
--        other(1),
--        autoConfig(2),
--        ituDss2(3),
--        atmfUni3Dot0(4),
--        atmfUni3Dot1(5),
--        atmfUni4Dot0(6),
--        atmfIispUni3Dot0(7),
--        atmfIispUni3Dot1(8),
--        atmfIispUni4Dot0(9),
--        atmfPnni1Dot0(10),
--        atmfBici2Dot0(11),
--        atmfUniPvcOnly(12),
--        atmfNniPvcOnly(13)
--        }
    ACCESS read-write
    STATUS mandatory
    DESCRIPTION
        "The type of connection setup procedures configured for the ATM
        interface.  Setting this variable to a value of 'other' is not
        allowed."
    DEFVAL { autoConfig }
    ::= { atmInterfaceExtEntry 1 }

atmIntfActualType OBJECT-TYPE
    SYNTAX AtmInterfaceType
--    Rsyntax INTEGER {
--        other(1),
--        autoConfig(2),
--        ituDss2(3),
--        atmfUni3Dot0(4),
--        atmfUni3Dot1(5),
--        atmfUni4Dot0(6),
--        atmfIispUni3Dot0(7),
--        atmfIispUni3Dot1(8),
--        atmfIispUni4Dot0(9),
--        atmfPnni1Dot0(10),
--        atmfBici2Dot0(11),
--        atmfUniPvcOnly(12),
--        atmfNniPvcOnly(13)
--        }
    ACCESS read-only
    STATUS mandatory
    DESCRIPTION
        "The type of connection setup procedures currently being used on
        the interface.  This may reflect a manually configured value for
        the interface type, or may be determined by other means such as
        auto-configuration.  A value of `autoConfig' indicates that
        auto-configuration was requested but has not yet been completed."
    ::= { atmInterfaceExtEntry 2 }

atmIntfConfigSide OBJECT-TYPE
    SYNTAX INTEGER {
        other(1),
        user(2),
        network(3)
        }
    ACCESS read-write
    STATUS mandatory
    DESCRIPTION
        "The configured role of the managed entity as one side of the ATM
        interface.  This value does not apply when the object
        atmIntfConfigType is set to `autoConfig', `atmfPnni1Dot0', or
        `atmfBici2Dot0'."
    ::= { atmInterfaceExtEntry 3 }

atmIntfActualSide OBJECT-TYPE
    SYNTAX INTEGER {
        other(1),
        user(2),
        network(3),
        symmetric(4)
        }
    ACCESS read-only
    STATUS mandatory
    DESCRIPTION
        "The current role used by the managed entity to represent one
        side of the ATM interface."
    ::= { atmInterfaceExtEntry 4 }

atmIntfIlmiAdminStatus OBJECT-TYPE
    SYNTAX OCTET STRING(SIZE(1..2))
        -- BITS are:
        --   ilmi(0)
        --   ilmiAddressRegistration(1)
        --   ilmiConnectivity(2)
        --   ilmiPvcPvpMgmt(3)
        --   ilmiSigVccParamNegotiation(4)
    ACCESS read-write
    STATUS mandatory
    DESCRIPTION
        "Indicates which components of ILMI are administratively enabled
        on this interface.  If the 'ilmi' bit is not set, then no ILMI
        components are operational.  ILMI components other than auto-
        configuration that are not represented in the value have their
        administrative status determined according to the 'ilmi' bit.
        The ILMI auto-configuration component is enabled/disabled by the
        atmIntfConfigType object."
    ::= { atmInterfaceExtEntry 5 }

atmIntfIlmiOperStatus OBJECT-TYPE
    SYNTAX OCTET STRING(SIZE(1..2))
        -- BITS are:
        --   ilmi(0)
        --   ilmiAddressRegistration(1)
        --   ilmiConnectivity(2)
        --   ilmiPvcPvpMgmt(3)
        --   ilmiSigVccParamNegotiation(4)
    ACCESS read-only
    STATUS mandatory
    DESCRIPTION
        "Indicates which components of ILMI are operational on this
        interface."
    ::= { atmInterfaceExtEntry 6 }

atmIntfIlmiFsmState OBJECT-TYPE
    SYNTAX INTEGER {
        stopped(1),
        linkFailing(2),
        establishing(3),
        configuring(4),
        retrievingNetworkPrefixes(5),
        registeringNetworkPrefixes(6),
        retrievingAddresses(7),
        registeringAddresses(8),
        verifying(9)
        }
    ACCESS read-only
    STATUS mandatory
    DESCRIPTION
        "Indicates the state of the ILMI Finite State Machine associated
        with this interface."
    REFERENCE
        "ATM Forum, Integrated Local Management Interface
         (ILMI) Specification, Version 4.0, af-ilmi-0065.000,
         September 1996, Appendix 1"
    ::= { atmInterfaceExtEntry 7 }

atmIntfIlmiEstablishConPollIntvl OBJECT-TYPE
    SYNTAX INTEGER(1..65535)
--  Units
--    seconds
    ACCESS read-write
    STATUS mandatory
    DESCRIPTION
        "The amount of time S between successive transmissions of ILMI
        messages on this interface for the purpose of detecting
        establishment of ILMI connectivity."
    REFERENCE
        "ATM Forum, Integrated Local Management Interface
         (ILMI) Specification, Version 4.0, af-ilmi-0065.000,
         September 1996, Section 8.3.1"
    DEFVAL { 1 }
    ::= { atmInterfaceExtEntry 8 }

atmIntfIlmiCheckConPollIntvl OBJECT-TYPE
    SYNTAX INTEGER(0..65535)
--  Units
--    seconds
    ACCESS read-write
    STATUS mandatory
    DESCRIPTION
        "The amount of time T between successive transmissions of ILMI
        messages on this interface for the purpose of detecting loss of
        ILMI connectivity.  The distinguished value zero disables ILMI
        connectivity procedures on this interface."
    REFERENCE
        "ATM Forum, Integrated Local Management Interface
         (ILMI) Specification, Version 4.0, af-ilmi-0065.000,
         September 1996, Section 8.3.1"
    DEFVAL { 5 }
    ::= { atmInterfaceExtEntry 9 }

atmIntfIlmiConPollInactFactor OBJECT-TYPE
    SYNTAX INTEGER(0..65535)
    ACCESS read-write
    STATUS mandatory
    DESCRIPTION
        "The number K of consecutive polls on this interface for which no
        ILMI response message is received before ILMI connectivity is
        declared lost."
    REFERENCE
        "ATM Forum, Integrated Local Management Interface
         (ILMI) Specification, Version 4.0, af-ilmi-0065.000,
         September 1996, Section 8.3.1"
    DEFVAL { 4 }
    ::= { atmInterfaceExtEntry 10 }

atmIntfIlmiPublicPrivateIndctr OBJECT-TYPE
    SYNTAX INTEGER {
        other(1),
        public(2),
        private(3)
        }
    ACCESS read-write
    STATUS mandatory
    DESCRIPTION
        "Specifies whether this end of the interface is advertised in
        ILMI as a device of the `public' or `private' type."
    DEFVAL { private }
    ::= { atmInterfaceExtEntry 11 }

atmInterfaceConfMaxSvpcVpi OBJECT-TYPE
    SYNTAX INTEGER(0..4095)
    ACCESS read-write
    STATUS mandatory
    DESCRIPTION
        "The maximum VPI that the signalling stack on the ATM interface
        is configured to support for allocation to switched virtual path
        connections."
    ::= { atmInterfaceExtEntry 12 }

atmInterfaceCurrentMaxSvpcVpi OBJECT-TYPE
    SYNTAX INTEGER(0..4095)
    ACCESS read-only
    STATUS mandatory
    DESCRIPTION
        "The maximum VPI that the signalling stack on the ATM interface
        may currently allocate to switched virtual path connections.
        This value is the minimum of atmInterfaceConfMaxSvpcVpi, and the
        atmInterfaceMaxSvpcVpi of the interface's UNI/NNI peer.
        
        If the interface does not negotiate with its peer to determine
        the maximum VPI that can be allocated to SVPCs on the interface,
        then the value of this object must equal
        atmInterfaceConfMaxSvpcVpi. "
    ::= { atmInterfaceExtEntry 13 }

atmInterfaceConfMaxSvccVpi OBJECT-TYPE
    SYNTAX INTEGER(0..4095)
    ACCESS read-write
    STATUS mandatory
    DESCRIPTION
        "The maximum VPI that the signalling stack on the ATM interface
        is configured to support for allocation to switched virtual
        channel connections."
    ::= { atmInterfaceExtEntry 14 }

atmInterfaceCurrentMaxSvccVpi OBJECT-TYPE
    SYNTAX INTEGER(0..4095)
    ACCESS read-only
    STATUS mandatory
    DESCRIPTION
        "The maximum VPI that the signalling stack on the ATM interface
        may currently allocate to switched virtual channel connections.
        This value is the minimum of atmInterfaceConfMaxSvccVpi, and the
        atmInterfaceConfMaxSvccVpi of the interface's UNI/NNI peer.
        
        If the interface does not negotiate with its peer to determine
        the maximum VPI that can be allocated to SVCCs on the interface,
        then the value of this object must equal
        atmInterfaceConfMaxSvccVpi."
    ::= { atmInterfaceExtEntry 15 }

atmInterfaceConfMinSvccVci OBJECT-TYPE
    SYNTAX INTEGER(0..65535)
    ACCESS read-write
    STATUS mandatory
    DESCRIPTION
        "The minimum VCI that the signalling stack on the ATM interface
        is configured to support for allocation to switched virtual
        channel connections."
    ::= { atmInterfaceExtEntry 16 }

atmInterfaceCurrentMinSvccVci OBJECT-TYPE
    SYNTAX INTEGER(0..65535)
    ACCESS read-only
    STATUS mandatory
    DESCRIPTION
        "The minimum VCI that the signalling stack on the ATM interface
        may currently allocate to switched virtual channel connections.
        This value is the maximum of atmInterfaceConfMinSvccVci, and the
        atmInterfaceConfMinSvccVci of the interface's UNI/NNI peer.
        If the interface does not negotiate with its peer to determine
        the minimum VCI that can be allocated to SVCCs on the interface,
        then the value of this object must equal
        atmInterfaceConfMinSvccVci."
    ::= { atmInterfaceExtEntry 17 }

atmIntfSigVccRxTrafficDescrIndex OBJECT-TYPE
    SYNTAX AtmTrafficDescrParamIndex
--    Rsyntax INTEGER(0..2147483647)
    ACCESS read-write
    STATUS mandatory
    DESCRIPTION
        "This object identifies the row in the atmTrafficDescrParamTable
        used during ILMI auto-configuration to specify the advertised
        signalling VCC traffic parameters for the receive direction.
        The traffic descriptor resulting from ILMI auto-configuration of
        the signalling VCC is indicated in the atmVclTable."
    ::= { atmInterfaceExtEntry 18 }

atmIntfSigVccTxTrafficDescrIndex OBJECT-TYPE
    SYNTAX AtmTrafficDescrParamIndex
--    Rsyntax INTEGER(0..2147483647)
    ACCESS read-write
    STATUS mandatory
    DESCRIPTION
        "This object identifies the row in the atmTrafficDescrParamTable
        used during ILMI auto-configuration to specify the advertised
        signalling VCC traffic parameters for the transmit direction.
        The traffic descriptor resulting from ILMI auto-configuration of
        the signalling VCC is indicated in the atmVclTable."
    ::= { atmInterfaceExtEntry 19 }

atmIntfPvcFailures OBJECT-TYPE
    SYNTAX Counter
    ACCESS read-only
    STATUS mandatory
    DESCRIPTION
        "The number of times the operational status of a PVPL or PVCL on
        this interface has gone down."
    ::= { atmInterfaceExtEntry 20 }

atmIntfCurrentlyFailingPVpls OBJECT-TYPE
    SYNTAX Gauge
    ACCESS read-only
    STATUS mandatory
    DESCRIPTION
        "The current number of VPLs on this interface for which there is
        an active row in the atmVplTable having an atmVplConnKind value
        of `pvc' and an atmVplOperStatus with a value other than `up'."
    ::= { atmInterfaceExtEntry 21 }

atmIntfCurrentlyFailingPVcls OBJECT-TYPE
    SYNTAX Gauge
    ACCESS read-only
    STATUS mandatory
    DESCRIPTION
        "The current number of VCLs on this interface for which there is
        an active row in the atmVclTable having an atmVclConnKind value
        of `pvc' and an atmVclOperStatus with a value other than `up'."
    ::= { atmInterfaceExtEntry 22 }

atmIntfPvcFailuresTrapEnable OBJECT-TYPE
    SYNTAX TruthValue
--    Rsyntax INTEGER {
--        true(1),
--        false(2)
--        }
    ACCESS read-write
    STATUS mandatory
    DESCRIPTION
        "Allows the generation of traps in response to PVCL or PVPL
        failures on this interface."
    DEFVAL { false }
    ::= { atmInterfaceExtEntry 23 }

atmIntfPvcNotificationInterval OBJECT-TYPE
    SYNTAX INTEGER(1..3600)
--  Units
--    seconds
    ACCESS read-write
    STATUS mandatory
    DESCRIPTION
        "The minimum interval between the sending of
        atmIntfPvcFailuresTrap notifications for this interface."
    DEFVAL { 30 }
    ::= { atmInterfaceExtEntry 24 }

atmIntfLeafSetupFailures OBJECT-TYPE
    SYNTAX Counter
    ACCESS read-only
    STATUS mandatory
    DESCRIPTION
        "Number of setup failures.  For root, this is the number of
        rejected setup requests and for leaf, this is the number of setup
        failure received."
    ::= { atmInterfaceExtEntry 25 }

atmIntfLeafSetupRequests OBJECT-TYPE
    SYNTAX Counter
    ACCESS read-only
    STATUS mandatory
    DESCRIPTION
        "Number of setup requests.  For root, this includes both incoming
        setup request and root intiated setup requests."
    ::= { atmInterfaceExtEntry 26 }

atmIlmiSrvcRegTable OBJECT-TYPE
    SYNTAX SEQUENCE OF AtmIlmiSrvcRegEntry
    ACCESS not-accessible
    STATUS mandatory
    DESCRIPTION
        "This table contains a list of all the ATM network services known
        by this device.
        
        The characteristics of these services are made available through
        the ILMI, using the ILMI general-purpose service registry MIB.
        These services may be made available to all ATM interfaces
        (atmIlmiSrvcRegIndex = 0) or to some specific ATM interfaces only
        (atmIlmiSrvcRegIndex = ATM interface index)."
    ::= { atm2MIBObjects 15 }

atmIlmiSrvcRegEntry OBJECT-TYPE
    SYNTAX AtmIlmiSrvcRegEntry
    ACCESS not-accessible
    STATUS mandatory
    DESCRIPTION
        "Information about a single service provider that is available to
        the user-side of an adjacent device through the ILMI.
        
        Implementors need to be aware that if the size of the
        atmIlmiSrvcRegServiceID exceeds 112 sub-identifiers then OIDs of
        
        column instances in this table will have more than 128 sub-
        identifiers and cannot be accessed using SNMPv1, SNMPv2, or
        SNMPv3."
    INDEX { atmIlmiSrvcRegIndex, atmIlmiSrvcRegServiceID, atmIlmiSrvcRegAddressIndex }
    ::= { atmIlmiSrvcRegTable 1 }

AtmIlmiSrvcRegEntry ::= SEQUENCE {
    atmIlmiSrvcRegIndex InterfaceIndexOrZero,
    atmIlmiSrvcRegServiceID OBJECT IDENTIFIER,
    atmIlmiSrvcRegAddressIndex INTEGER,
    atmIlmiSrvcRegATMAddress AtmAddr,
    atmIlmiSrvcRegParm1 OCTET STRING,
    atmIlmiSrvcRegRowStatus RowStatus
    }

atmIlmiSrvcRegIndex OBJECT-TYPE
    SYNTAX InterfaceIndexOrZero
--    Rsyntax INTEGER(0..2147483647)
    ACCESS not-accessible
    STATUS mandatory
    DESCRIPTION
        "The ATM interface where the service defined in this entry can be
        made available to an ATM device attached to this interface.
        
        The value of 0 has a special meaning: when an ATM service is
        defined in an entry whose atmIlmiSrvcRegIndex is zero, the ATM
        service is available to ATM devices connected to any ATM
        interface.  (default value(s)).
        
        When the user-side of an adjacent device queries the content of
        the ILMI service registry MIB (using the ILMI protocol), the
        local network-side responds with the ATM services defined in
        atmIlmiSrvcRegTable entries, provided that these entries are
        indexed by:
        
        - the corresponding ifIndex value (atmIlmiSrvcRegIndex
          equal to the ifIndex of the interface to which the
          adjacent device is connected) - zero (atmIlmiSrvcRegIndex=0)."
    ::= { atmIlmiSrvcRegEntry 1 }

atmIlmiSrvcRegServiceID OBJECT-TYPE
    SYNTAX OBJECT IDENTIFIER
    ACCESS not-accessible
    STATUS mandatory
    DESCRIPTION
        "This is the service identifier which uniquely identifies the
        
        type of service at the address provided in the table.  The object
        identifiers for the LAN Emulation Configuration Server (LECS) and
        the ATM Name Server (ANS) are defined in the ATM Forum ILMI
        Service Registry MIB.  The object identifiers for the ATMARP
        Server, the Multicast Address Resolution Server (MARS), and the
        NHRP Server (NHS) are defined in RFC 2601, RFC 2602, and RFC
        2603, respectively."
    ::= { atmIlmiSrvcRegEntry 2 }

atmIlmiSrvcRegAddressIndex OBJECT-TYPE
    SYNTAX INTEGER(1..2147483647)
    ACCESS not-accessible
    STATUS mandatory
    DESCRIPTION
        "An arbitrary integer to differentiate multiple rows containing
        different ATM addresses for the same service on the same
        interface.  This number need NOT be the same as the corresponding
        ILMI atmfSrvcRegAddressIndex MIB object."
    ::= { atmIlmiSrvcRegEntry 3 }

atmIlmiSrvcRegATMAddress OBJECT-TYPE
    SYNTAX AtmAddr
--    Rsyntax OCTET STRING(SIZE(0..40))
    ACCESS read-write
    STATUS mandatory
    DESCRIPTION
        "This is the full address of the service.  The user-side of the
        adjacent device may use this address to establish a connection
        with the service."
    ::= { atmIlmiSrvcRegEntry 4 }

atmIlmiSrvcRegParm1 OBJECT-TYPE
    SYNTAX OCTET STRING(SIZE(1..255))
    ACCESS read-write
    STATUS mandatory
    DESCRIPTION
        "An octet string used according to the value of
        atmIlmiSrvcRegServiceID."
    ::= { atmIlmiSrvcRegEntry 5 }

atmIlmiSrvcRegRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or destroy an entry from this
        table."
    ::= { atmIlmiSrvcRegEntry 6 }

atmIlmiNetworkPrefixTable OBJECT-TYPE
    SYNTAX SEQUENCE OF AtmIlmiNetworkPrefixEntry
    ACCESS not-accessible
    STATUS mandatory
    DESCRIPTION
        "A table specifying per-interface network prefix(es) supplied by
        the network side of the UNI during ILMI address registration.
        When no network prefixes are specified for a particular
        interface, one or more network prefixes based on the switch
        address(es) may be used for ILMI address registration."
    ::= { atm2MIBObjects 16 }

atmIlmiNetworkPrefixEntry OBJECT-TYPE
    SYNTAX AtmIlmiNetworkPrefixEntry
    ACCESS not-accessible
    STATUS mandatory
    DESCRIPTION
        "Information about a single network prefix supplied by the
        network side of the UNI during ILMI address registration.  Note
        that the index variable atmIlmiNetPrefixPrefix is a variable-
        length string, and as such the rule for variable-length strings
        in section 7.7 of RFC 2578 applies."
    INDEX { ifIndex, atmIlmiNetPrefixPrefix }
    ::= { atmIlmiNetworkPrefixTable 1 }

AtmIlmiNetworkPrefixEntry ::= SEQUENCE {
    atmIlmiNetPrefixPrefix AtmIlmiNetworkPrefix,
    atmIlmiNetPrefixRowStatus RowStatus
    }

atmIlmiNetPrefixPrefix OBJECT-TYPE
    SYNTAX AtmIlmiNetworkPrefix
--    Rsyntax OCTET STRING(SIZE(8|13))
    ACCESS not-accessible
    STATUS mandatory
    DESCRIPTION
        "The network prefix specified for use in ILMI address
        registration."
    ::= { atmIlmiNetworkPrefixEntry 1 }

atmIlmiNetPrefixRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Used to create, delete, activate and de-activate network
        prefixes used in ILMI address registration."
    ::= { atmIlmiNetworkPrefixEntry 2 }

atmSwitchAddressTable OBJECT-TYPE
    SYNTAX SEQUENCE OF AtmSwitchAddressEntry
    ACCESS not-accessible
    STATUS mandatory
    DESCRIPTION
        "This table contains one or more ATM endsystem addresses on a
        per-switch basis.  These addresses are used to identify the
        switch.  When no ILMI network prefixes are configured for certain
        interfaces, network prefixes based on the switch address(es) may
        be used for ILMI address registration."
    ::= { atm2MIBObjects 17 }

atmSwitchAddressEntry OBJECT-TYPE
    SYNTAX AtmSwitchAddressEntry
    ACCESS not-accessible
    STATUS mandatory
    DESCRIPTION
        "An entry in the ATM Switch Address table."
    INDEX { atmSwitchAddressIndex }
    ::= { atmSwitchAddressTable 1 }

AtmSwitchAddressEntry ::= SEQUENCE {
    atmSwitchAddressIndex INTEGER,
    atmSwitchAddressAddress OCTET STRING,
    atmSwitchAddressRowStatus RowStatus
    }

atmSwitchAddressIndex OBJECT-TYPE
    SYNTAX INTEGER(1..65535)
    ACCESS not-accessible
    STATUS mandatory
    DESCRIPTION
        "An arbitrary index used to enumerate the ATM endsystem addresses
        for this switch."
    ::= { atmSwitchAddressEntry 1 }

atmSwitchAddressAddress OBJECT-TYPE
    SYNTAX OCTET STRING(SIZE(13|20))
    ACCESS read-write
    STATUS mandatory
    DESCRIPTION
        "An ATM endsystem address or address prefix used to identify this
        switch.  When no ESI or SEL field is specified, the switch may
        generate the ESI and SEL fields automatically to obtain a
        complete 20-byte ATM endsystem address."
    ::= { atmSwitchAddressEntry 2 }

atmSwitchAddressRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Used to create, delete, activate, and de-activate addresses used
        to identify this switch."
    ::= { atmSwitchAddressEntry 3 }

atmVpCrossConnectXTable OBJECT-TYPE
    SYNTAX SEQUENCE OF AtmVpCrossConnectXEntry
    ACCESS not-accessible
    STATUS mandatory
    DESCRIPTION
        "This table contains one row per VP Cross-Connect represented in
        the atmVpCrossConnectTable."
    ::= { atm2MIBObjects 18 }

atmVpCrossConnectXEntry OBJECT-TYPE
    SYNTAX AtmVpCrossConnectXEntry
    ACCESS not-accessible
    STATUS mandatory
    DESCRIPTION
        "Information about a particular ATM VP Cross-Connect.
        Each entry provides an two objects that name the Cross-Connect.
        One is assigned by the Service User and the other by the Service
        Provider."
    INDEX { atmVpCrossConnectIndex, atmVpCrossConnectLowIfIndex, atmVpCrossConnectLowVpi, atmVpCrossConnectHighIfIndex, atmVpCrossConnectHighVpi }
-- Augments atmVpCrossConnectEntry FROM ATM-MIB
    ::= { atmVpCrossConnectXTable 1 }

AtmVpCrossConnectXEntry ::= SEQUENCE {
    atmVpCrossConnectUserName SnmpAdminString,
    atmVpCrossConnectProviderName SnmpAdminString
    }

atmVpCrossConnectUserName OBJECT-TYPE
    SYNTAX SnmpAdminString(SIZE(0..255))
--    Rsyntax OCTET STRING(SIZE(0..255))
    ACCESS read-write
    STATUS mandatory
    DESCRIPTION
        "This is a service user assigned textual representation of a VPC
        PVC."
    ::= { atmVpCrossConnectXEntry 1 }

atmVpCrossConnectProviderName OBJECT-TYPE
    SYNTAX SnmpAdminString(SIZE(0..255))
--    Rsyntax OCTET STRING(SIZE(0..255))
    ACCESS read-only
    STATUS mandatory
    DESCRIPTION
        "This is a system supplied textual representation of VPC PVC.  It
        is assigned by the service provider."
    ::= { atmVpCrossConnectXEntry 2 }

atmVcCrossConnectXTable OBJECT-TYPE
    SYNTAX SEQUENCE OF AtmVcCrossConnectXEntry
    ACCESS not-accessible
    STATUS mandatory
    DESCRIPTION
        "This table contains one row per VC Cross-Connect represented in
        the atmVcCrossConnectTable."
    ::= { atm2MIBObjects 19 }

atmVcCrossConnectXEntry OBJECT-TYPE
    SYNTAX AtmVcCrossConnectXEntry
    ACCESS not-accessible
    STATUS mandatory
    DESCRIPTION
        "Information about a particular ATM VC Cross-Connect.
        Each entry provides an two objects that name the Cross-Connect.
        One is assigned by the Service User and the other by the Service
        Provider."
    INDEX { atmVcCrossConnectIndex, atmVcCrossConnectLowIfIndex, atmVcCrossConnectLowVpi, atmVcCrossConnectLowVci, atmVcCrossConnectHighIfIndex, atmVcCrossConnectHighVpi, atmVcCrossConnectHighVci }
-- Augments atmVcCrossConnectEntry FROM ATM-MIB
    ::= { atmVcCrossConnectXTable 1 }

AtmVcCrossConnectXEntry ::= SEQUENCE {
    atmVcCrossConnectUserName SnmpAdminString,
    atmVcCrossConnectProviderName SnmpAdminString
    }

atmVcCrossConnectUserName OBJECT-TYPE
    SYNTAX SnmpAdminString(SIZE(0..255))
--    Rsyntax OCTET STRING(SIZE(0..255))
    ACCESS read-write
    STATUS mandatory
    DESCRIPTION
        "This is a service user assigned textual representation of a VCC
        
        PVC."
    ::= { atmVcCrossConnectXEntry 1 }

atmVcCrossConnectProviderName OBJECT-TYPE
    SYNTAX SnmpAdminString(SIZE(0..255))
--    Rsyntax OCTET STRING(SIZE(0..255))
    ACCESS read-only
    STATUS mandatory
    DESCRIPTION
        "This is a system supplied textual representation of VCC PVC.  It
        is assigned by the service provider."
    ::= { atmVcCrossConnectXEntry 2 }

atmCurrentlyFailingPVplTable OBJECT-TYPE
    SYNTAX SEQUENCE OF AtmCurrentlyFailingPVplEntry
    ACCESS not-accessible
    STATUS mandatory
    DESCRIPTION
        "A table indicating all VPLs for which there is an active row in
        the atmVplTable having an atmVplConnKind value of `pvc' and an
        atmVplOperStatus with a value other than `up'."
    ::= { atm2MIBObjects 20 }

atmCurrentlyFailingPVplEntry OBJECT-TYPE
    SYNTAX AtmCurrentlyFailingPVplEntry
    ACCESS not-accessible
    STATUS mandatory
    DESCRIPTION
        "Each entry in this table represents a VPL for which the
        atmVplRowStatus is `active', the atmVplConnKind is `pvc', and the
        atmVplOperStatus is other than `up'."
    INDEX { ifIndex, atmVplVpi }
    ::= { atmCurrentlyFailingPVplTable 1 }

AtmCurrentlyFailingPVplEntry ::= SEQUENCE {
    atmCurrentlyFailingPVplTimeStamp TimeStamp
    }

atmCurrentlyFailingPVplTimeStamp OBJECT-TYPE
    SYNTAX TimeStamp
--    Rsyntax TimeTicks
    ACCESS read-only
    STATUS mandatory
    DESCRIPTION
        "The time at which this PVPL began to fail."
    ::= { atmCurrentlyFailingPVplEntry 1 }

atmCurrentlyFailingPVclTable OBJECT-TYPE
    SYNTAX SEQUENCE OF AtmCurrentlyFailingPVclEntry
    ACCESS not-accessible
    STATUS mandatory
    DESCRIPTION
        "A table indicating all VCLs for which there is an active row in
        the atmVclTable having an atmVclConnKind value of `pvc' and an
        atmVclOperStatus with a value other than `up'."
    ::= { atm2MIBObjects 21 }

atmCurrentlyFailingPVclEntry OBJECT-TYPE
    SYNTAX AtmCurrentlyFailingPVclEntry
    ACCESS not-accessible
    STATUS mandatory
    DESCRIPTION
        "Each entry in this table represents a VCL for which the
        atmVclRowStatus is `active', the atmVclConnKind is `pvc', and the
        atmVclOperStatus is other than `up'."
    INDEX { ifIndex, atmVclVpi, atmVclVci }
    ::= { atmCurrentlyFailingPVclTable 1 }

AtmCurrentlyFailingPVclEntry ::= SEQUENCE {
    atmCurrentlyFailingPVclTimeStamp TimeStamp
    }

atmCurrentlyFailingPVclTimeStamp OBJECT-TYPE
    SYNTAX TimeStamp
--    Rsyntax TimeTicks
    ACCESS read-only
    STATUS mandatory
    DESCRIPTION
        "The time at which this PVCL began to fail."
    ::= { atmCurrentlyFailingPVclEntry 1 }

atmIntfPvcFailuresTrap TRAP-TYPE
-- Reverse mappable trap
    ENTERPRISE atmPvcTraps
    VARIABLES {
        ifIndex, atmIntfPvcFailures, atmIntfCurrentlyFailingPVpls, 
        atmIntfCurrentlyFailingPVcls }
--  Status
--    mandatory
    DESCRIPTION
        "A notification indicating that one or more PVPLs or PVCLs on
        this interface has failed since the last atmPvcFailuresTrap was
        sent.  If this trap has not been sent for the last
        atmIntfPvcNotificationInterval, then it will be sent on the next
        increment of atmIntfPvcFailures."
    ::= 1

atmCommonGroup OBJECT IDENTIFIER ::= { atm2MIBGroups 1 }
-- OBJECT-GROUP
--  Status
--    mandatory
--  Descr
--    A collection of objects providing information
--    for a Switch/Service/Host that implements
--    ATM interfaces.
--  objects
--    atmSigSSCOPConEvents, atmSigSSCOPErrdPdus, 
--    atmSigDetectSetupAttempts, atmSigEmitSetupAttempts, 
--    atmSigDetectUnavailRoutes, atmSigEmitUnavailRoutes, 
--    atmSigDetectUnavailResrcs, atmSigEmitUnavailResrcs, 
--    atmSigDetectCldPtyEvents, atmSigEmitCldPtyEvents, 
--    atmSigDetectMsgErrors, atmSigEmitMsgErrors, 
--    atmSigDetectClgPtyEvents, atmSigEmitClgPtyEvents, 
--    atmSigDetectTimerExpireds, atmSigEmitTimerExpireds, 
--    atmSigDetectRestarts, atmSigEmitRestarts, atmSigInEstabls, 
--    atmSigOutEstabls, atmVplLogicalPortDef, 
--    atmVplLogicalPortIndex, atmInterfaceConfMaxSvpcVpi, 
--    atmInterfaceCurrentMaxSvpcVpi, atmInterfaceConfMaxSvccVpi, 
--    atmInterfaceCurrentMaxSvccVpi, atmInterfaceConfMinSvccVci, 
--    atmInterfaceCurrentMinSvccVci, 
--    atmIntfSigVccRxTrafficDescrIndex, 
--    atmIntfSigVccTxTrafficDescrIndex, atmIntfPvcFailures, 
--    atmIntfCurrentlyFailingPVpls, atmIntfCurrentlyFailingPVcls, 
--    atmIntfPvcNotificationInterval, atmIntfPvcFailuresTrapEnable, 
--    atmIntfLeafSetupFailures, atmIntfLeafSetupRequests, 
--    atmIntfConfigType, atmIntfActualType, atmIntfConfigSide, 
--    atmIntfActualSide, atmIntfIlmiAdminStatus, 
--    atmIntfIlmiOperStatus, atmIntfIlmiFsmState, 
--    atmIntfIlmiEstablishConPollIntvl, 
--    atmIntfIlmiCheckConPollIntvl, atmIntfIlmiConPollInactFactor, 
--    atmIntfIlmiPublicPrivateIndctr, 
--    atmCurrentlyFailingPVplTimeStamp, 
--    atmCurrentlyFailingPVclTimeStamp

atmCommonStatsGroup OBJECT IDENTIFIER ::= { atm2MIBGroups 2 }
-- OBJECT-GROUP
--  Status
--    mandatory
--  Descr
--    A collection of objects providing information
--    
--    for a Switch/Service/Host that implements
--    ATM VCL and VPL Statistics
--  objects
--    atmVclStatTotalCellIns, atmVclStatClp0CellIns, 
--    atmVclStatTotalDiscards, atmVclStatClp0Discards, 
--    atmVclStatTotalCellOuts, atmVclStatClp0CellOuts, 
--    atmVclStatClp0Tagged, atmVplStatTotalCellIns, 
--    atmVplStatClp0CellIns, atmVplStatTotalDiscards, 
--    atmVplStatClp0Discards, atmVplStatTotalCellOuts, 
--    atmVplStatClp0CellOuts, atmVplStatClp0Tagged

atmSwitchServcGroup OBJECT IDENTIFIER ::= { atm2MIBGroups 3 }
-- OBJECT-GROUP
--  Status
--    mandatory
--  Descr
--    A collection of objects providing information
--    for a Switch/Service that implements ATM interfaces.
--  objects
--    atmIlmiSrvcRegATMAddress, atmIlmiSrvcRegParm1, 
--    atmIlmiSrvcRegRowStatus, atmIlmiNetPrefixRowStatus, 
--    atmSvcVpCrossConnectCreationTime, 
--    atmSvcVpCrossConnectRowStatus, 
--    atmSvcVcCrossConnectCreationTime, 
--    atmSvcVcCrossConnectRowStatus, atmIfRegAddrAddressSource, 
--    atmIfRegAddrOrgScope, atmIfRegAddrRowStatus

atmSwitchServcSigGroup OBJECT IDENTIFIER ::= { atm2MIBGroups 4 }
-- OBJECT-GROUP
--  Status
--    mandatory
--  Descr
--    A collection of objects providing information
--    for a Switch/Service that implements ATM signalling.
--  objects
--    atmSigSupportClgPtyNumDel, atmSigSupportClgPtySubAddr, 
--    atmSigSupportCldPtySubAddr, atmSigSupportHiLyrInfo, 
--    atmSigSupportLoLyrInfo, atmSigSupportBlliRepeatInd, 
--    atmSigSupportAALInfo, atmSigSupportPrefCarrier

atmSwitchGroup OBJECT IDENTIFIER ::= { atm2MIBGroups 6 }
-- OBJECT-GROUP
--  Status
--    mandatory
--  Descr
--    A collection of objects providing information
--    for an ATM switch.
--  objects
--    atmSwitchAddressAddress, atmSwitchAddressRowStatus

atmServcGroup OBJECT IDENTIFIER ::= { atm2MIBGroups 7 }
-- OBJECT-GROUP
--  Status
--    mandatory
--  Descr
--    A collection of objects providing information
--    for an ATM Network Service.
--  objects
--    atmVpCrossConnectUserName, atmVpCrossConnectProviderName, 
--    atmVcCrossConnectUserName, atmVcCrossConnectProviderName

atmHostGroup OBJECT IDENTIFIER ::= { atm2MIBGroups 8 }
-- OBJECT-GROUP
--  Status
--    mandatory
--  Descr
--    A collection of objects providing information
--    for a Host that implements ATM interfaces.
--  objects
--    atmAal5VclInPkts, atmAal5VclOutPkts, atmAal5VclInOctets, 
--    atmAal5VclOutOctets, atmVclAddrType, atmVclAddrRowStatus, 
--    atmAddrVclAddrType, atmVclGenSigDescrIndex

atmHostSigDescrGroup OBJECT IDENTIFIER ::= { atm2MIBGroups 9 }
-- OBJECT-GROUP
--  Status
--    mandatory
--  Descr
--    A collection of objects providing information
--    for a Host that implements ATM interfaces.
--  objects
--    atmSigDescrParamAalType, atmSigDescrParamAalSscsType, 
--    atmSigDescrParamBhliType, atmSigDescrParamBhliInfo, 
--    atmSigDescrParamBbcConnConf, atmSigDescrParamBlliLayer2, 
--    atmSigDescrParamBlliLayer3, atmSigDescrParamBlliPktSize, 
--    atmSigDescrParamBlliSnapId, atmSigDescrParamBlliOuiPid, 
--    atmSigDescrParamRowStatus

atmSwitchServcNotifGroup OBJECT IDENTIFIER ::= { atm2MIBGroups 5 }
-- NOTIFICATION-GROUP
--  Status
--    mandatory
--  Descr
--    A collection of notifications providing information
--    for a Switch/Service that implements ATM interfaces.
--  notifications
--    atmIntfPvcFailuresTrap

atm2MIBCompliance OBJECT IDENTIFIER ::= { atm2MIBCompliances 1 }
-- MODULE-COMPLIANCE
--  Status
--    mandatory
--  Descr
--    The compliance statement for SNMP entities which represent ATM
--     interfaces.  The compliance statements are used to determine
--     if a particular group or object applies to hosts,
--     networks/switches, or both.  The Common group is defined as
--     applicable to all three.
--  Module
--    >>current<<
--   MandGroup
--    atmCommonGroup
--   OptGroup
--    atmCommonStatsGroup
--   ObjVar
--    atmVplLogicalPortDef
--   ObjVar
--    atmIntfSigVccRxTrafficDescrIndex
--   ObjVar
--    atmIntfSigVccTxTrafficDescrIndex
--   ObjVar
--    atmCurrentlyFailingPVplTimeStamp
--   ObjVar
--    atmCurrentlyFailingPVclTimeStamp
--   ObjVar
--    atmIntfLeafSetupFailures
--   ObjVar
--    atmIntfLeafSetupRequests
--   OptGroup
--    atmSwitchServcGroup
--   ObjVar
--    atmIfRegAddrRowStatus
--   ObjVar
--    atmSvcVpCrossConnectRowStatus
--   ObjVar
--    atmSvcVcCrossConnectRowStatus
--   OptGroup
--    atmSwitchServcSigGroup
--   OptGroup
--    atmSwitchServcNotifGroup
--   OptGroup
--    atmSwitchGroup
--   OptGroup
--    atmServcGroup
--   OptGroup
--    atmHostGroup
--   ObjVar
--    atmVclAddrType
--   ObjVar
--    atmVclAddrRowStatus
--   OptGroup
--    atmHostSigDescrGroup


END
