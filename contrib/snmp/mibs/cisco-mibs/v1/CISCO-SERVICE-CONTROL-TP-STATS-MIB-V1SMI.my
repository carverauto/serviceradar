-- MIB file created 01-Jul-2008 10:20:13, by
--   SMICng version 2.2.11-beta(PRO)(Solaris), January 20, 2001. Enterprise key cisco.com

CISCO-SERVICE-CONTROL-TP-STATS-MIB DEFINITIONS ::= BEGIN

-- From file: "CISCO-SERVICE-CONTROL-TP-STATS-MIB.my"
-- Compile options "4 7 F H N O W 03 06 0B 0G 0N 0T"

IMPORTS
    entPhysicalIndex
            FROM ENTITY-MIB
    SnmpAdminString
            FROM SNMP-FRAMEWORK-MIB
    TimeStamp
            FROM SNMPv2-TC-v1
    ciscoMgmt
            FROM CISCO-SMI
    Counter, Gauge
            FROM RFC1155-SMI
    OBJECT-TYPE
            FROM RFC-1212;

ciscoServiceControlTpStatsMIB OBJECT IDENTIFIER ::= { ciscoMgmt 634 }
-- MODULE-IDENTITY
--  LastUpdated
--    200707220000Z
--  OrgName
--    Cisco Systems, Inc.
--  ContactInfo
--    Cisco Systems
--    Customer Service
--    
--    Postal: 170 W Tasman Drive
--    San Jose, CA  95134
--    USA
--    
--    Tel: +1 800 553-NETS
--    
--    E-mail: cs-excelsior-dev@cisco.com
--  Descr
--    This MIB provides information and statistics on the traffic
--    processor(s) of a service control entity, which is a network
--    element that monitors network traffic between network
--    subscribers based on user configured policies.
--    
--    A service control entity uses traffic processor(s) for packet
--    processing and flow handling in the host network.
--    
--    The traffic processor(s) data obtained from this MIB may also
--    reflect the general load in the system.
--  RevDate
--    200707220000Z
--  RevDescr
--    Initial version of this MIB module.

ciscoSCTpStatsMIBNotifs OBJECT IDENTIFIER ::= { ciscoServiceControlTpStatsMIB 0 }
ciscoSCTpStatsMIBObjects OBJECT IDENTIFIER ::= { ciscoServiceControlTpStatsMIB 1 }
ciscoSCTpStatsMIBConform OBJECT IDENTIFIER ::= { ciscoServiceControlTpStatsMIB 2 }
cscTpStatsMIBCompliances OBJECT IDENTIFIER ::= { ciscoSCTpStatsMIBConform 1 }
cscTpStatsMIBGroups OBJECT IDENTIFIER ::= { ciscoSCTpStatsMIBConform 2 }

cscTpTable OBJECT-TYPE
    SYNTAX SEQUENCE OF CscTpEntry
    ACCESS not-accessible
    STATUS mandatory
    DESCRIPTION
        "This table contains the traffic processor statistics."
    ::= { ciscoSCTpStatsMIBObjects 1 }

cscTpEntry OBJECT-TYPE
    SYNTAX CscTpEntry
    ACCESS not-accessible
    STATUS mandatory
    DESCRIPTION
        "This entry lists traffic data for packets and flows handled by
        the traffic processor, identified by the entPhysicalIndex for an
        entity with its entPhysicalClass equal to 'cpu' in  ENTITY-MIB."
    INDEX { entPhysicalIndex }
    ::= { cscTpTable 1 }

CscTpEntry ::= SEQUENCE {
    cscTpTotalHandledPackets Counter,
    cscTpTotalHandledFlows Counter,
    cscTpActiveFlows Gauge,
    cscTpTcpActiveFlows Gauge,
    cscTpUdpActiveFlows Gauge,
    cscTpTotalBlockedPackets Counter,
    cscTpTotalBlockedFlows Counter,
    cscTpTotalBandwidthDiscardedPackets Counter,
    cscTpTotalWredDiscardedPackets Counter,
    cscTpTotalFragments Counter,
    cscTpTotalNonIpPackets Counter,
    cscTpTotalIpChecksumErrPackets Counter,
    cscTpTotalIpLengthErrPackets Counter,
    cscTpTotalIpBroadcastPackets Counter,
    cscTpTotalTTLErrPackets Counter,
    cscTpTotalTcpUdpChksumErrPackets Counter,
    cscTpHandledPacketsRate Gauge,
    cscTpHandledFlowsRate Gauge,
    cscTpFlowsCapacityUtilization Gauge,
    cscTpServiceLoss Gauge
    }

cscTpTotalHandledPackets OBJECT-TYPE
    SYNTAX --?? syntax is not convertable to SMIv1
           Counter
--  Units
--    packets
    ACCESS read-only
    STATUS mandatory
    DESCRIPTION
        "This object indicates the number of packets handled by this
        traffic processor since last restart.
        
        Discontinuities in the value of this counter can occur at
        re-initialization of the management system, and at other times
        as indicated by the value of cscTpCounterDiscontinuityTime."
    ::= { cscTpEntry 1 }

cscTpTotalHandledFlows OBJECT-TYPE
    SYNTAX --?? syntax is not convertable to SMIv1
           Counter
--  Units
--    flows
    ACCESS read-only
    STATUS mandatory
    DESCRIPTION
        "This object indicates the number of flows handled by this
        traffic processor since last restart.
        
        Discontinuities in the value of this counter can occur at
        re-initialization of the management system, and at other times
        as indicated by the value of cscTpCounterDiscontinuityTime."
    ::= { cscTpEntry 2 }

cscTpActiveFlows OBJECT-TYPE
    SYNTAX Gauge
--  Units
--    flows
    ACCESS read-only
    STATUS mandatory
    DESCRIPTION
        "This object indicates the number of flows currently being
        handled by this traffic processor."
    ::= { cscTpEntry 3 }

cscTpTcpActiveFlows OBJECT-TYPE
    SYNTAX Gauge
--  Units
--    flows
    ACCESS read-only
    STATUS mandatory
    DESCRIPTION
        "This object indicates the number of TCP flows currently
        being handled by this traffic processor."
    ::= { cscTpEntry 4 }

cscTpUdpActiveFlows OBJECT-TYPE
    SYNTAX Gauge
--  Units
--    flows
    ACCESS read-only
    STATUS mandatory
    DESCRIPTION
        "This object indicates the number of UDP flows currently
        being handled by this traffic processor."
    ::= { cscTpEntry 5 }

cscTpTotalBlockedPackets OBJECT-TYPE
    SYNTAX Counter
--  Units
--    packets
    ACCESS read-only
    STATUS mandatory
    DESCRIPTION
        "This object indicates the number of packets discarded by this
        traffic processor due to application blocking rules.
        
        Discontinuities in the value of this counter can occur at
        re-initialization of the management system, and at other times
        as indicated by the value of cscTpCounterDiscontinuityTime."
    ::= { cscTpEntry 6 }

cscTpTotalBlockedFlows OBJECT-TYPE
    SYNTAX Counter
--  Units
--    flows
    ACCESS read-only
    STATUS mandatory
    DESCRIPTION
        "This object indicates the number of flows discarded by this
        traffic processor due to application blocking rules.
        
        Discontinuities in the value of this counter can occur at
        re-initialization of the management system, and at other times
        as indicated by the value of cscTpCounterDiscontinuityTime."
    ::= { cscTpEntry 7 }

cscTpTotalBandwidthDiscardedPackets OBJECT-TYPE
    SYNTAX Counter
--  Units
--    packets
    ACCESS read-only
    STATUS mandatory
    DESCRIPTION
        "This object indicates the number of packets discarded by this
        traffic processor due to subscriber bandwidth limitations.
        
        Discontinuities in the value of this counter can occur at
        re-initialization of the management system, and at other times
        as indicated by the value of cscTpCounterDiscontinuityTime."
    ::= { cscTpEntry 8 }

cscTpTotalWredDiscardedPackets OBJECT-TYPE
    SYNTAX Counter
--  Units
--    packets
    ACCESS read-only
    STATUS mandatory
    DESCRIPTION
        "This object indicates the number of packets discarded by this
        traffic processor due to congestion in the queues.
        
        Discontinuities in the value of this counter can occur at
        re-initialization of the management system, and at other times
        as indicated by the value of cscTpCounterDiscontinuityTime."
    ::= { cscTpEntry 9 }

cscTpTotalFragments OBJECT-TYPE
    SYNTAX --?? syntax is not convertable to SMIv1
           Counter
--  Units
--    packets
    ACCESS read-only
    STATUS mandatory
    DESCRIPTION
        "This object indicates the number of fragmented packets handled
        by this traffic processor.
        
        Discontinuities in the value of this counter can occur at
        re-initialization of the management system, and at other times
        as indicated by the value of cscTpCounterDiscontinuityTime."
    ::= { cscTpEntry 10 }

cscTpTotalNonIpPackets OBJECT-TYPE
    SYNTAX --?? syntax is not convertable to SMIv1
           Counter
--  Units
--    packets
    ACCESS read-only
    STATUS mandatory
    DESCRIPTION
        "This object indicates the number of non IP packets handled by
        this traffic processor.
        
        Discontinuities in the value of this counter can occur at
        re-initialization of the management system, and at other times
        as indicated by the value of cscTpCounterDiscontinuityTime."
    ::= { cscTpEntry 11 }

cscTpTotalIpChecksumErrPackets OBJECT-TYPE
    SYNTAX Counter
--  Units
--    num-of-packets
    ACCESS read-only
    STATUS mandatory
    DESCRIPTION
        "This object indicates the number of packets with IP checksum
        error handled by this traffic processor.
        
        Discontinuities in the value of this counter can occur at
        re-initialization of the management system, and at other times
        as indicated by the value of cscTpCounterDiscontinuityTime."
    ::= { cscTpEntry 12 }

cscTpTotalIpLengthErrPackets OBJECT-TYPE
    SYNTAX Counter
--  Units
--    packets
    ACCESS read-only
    STATUS mandatory
    DESCRIPTION
        "This object indicates the number of packets with IP length
        error handled by this traffic processor.
        
        Discontinuities in the value of this counter can occur at
        re-initialization of the management system, and at other times
        as indicated by the value of cscTpCounterDiscontinuityTime."
    ::= { cscTpEntry 13 }

cscTpTotalIpBroadcastPackets OBJECT-TYPE
    SYNTAX --?? syntax is not convertable to SMIv1
           Counter
--  Units
--    packets
    ACCESS read-only
    STATUS mandatory
    DESCRIPTION
        "This object indicates the number of IP broadcast packets
        handled by this traffic processor.
        
        Discontinuities in the value of this counter can occur at
        re-initialization of the management system, and at other times
        as indicated by the value of cscTpCounterDiscontinuityTime."
    ::= { cscTpEntry 14 }

cscTpTotalTTLErrPackets OBJECT-TYPE
    SYNTAX Counter
--  Units
--    packets
    ACCESS read-only
    STATUS mandatory
    DESCRIPTION
        "This object indicates the number of packets with TTL error
        handled by this traffic processor.
        
        Discontinuities in the value of this counter can occur at
        re-initialization of the management system, and at other times
        as indicated by the value of cscTpCounterDiscontinuityTime."
    ::= { cscTpEntry 15 }

cscTpTotalTcpUdpChksumErrPackets OBJECT-TYPE
    SYNTAX Counter
--  Units
--    packets
    ACCESS read-only
    STATUS mandatory
    DESCRIPTION
        "This object indicates the number of TCP/UDP packets with
        checksum error handled by this traffic processor.
        
        Discontinuities in the value of this counter can occur at
        re-initialization of the management system, and at other times
        as indicated by the value of cscTpCounterDiscontinuityTime."
    ::= { cscTpEntry 16 }

cscTpHandledPacketsRate OBJECT-TYPE
    SYNTAX Gauge
--  Units
--    packets per second
    ACCESS read-only
    STATUS mandatory
    DESCRIPTION
        "This object indicates the number of packets handled by this
        traffic processor per second."
    ::= { cscTpEntry 17 }

cscTpHandledFlowsRate OBJECT-TYPE
    SYNTAX Gauge
--  Units
--    flows per second
    ACCESS read-only
    STATUS mandatory
    DESCRIPTION
        "This object indicates the number of flow initiations per second on
        this traffic processor."
    ::= { cscTpEntry 18 }

cscTpFlowsCapacityUtilization OBJECT-TYPE
    SYNTAX Gauge(0..100)
--  Units
--    percent
    ACCESS read-only
    STATUS mandatory
    DESCRIPTION
        "This object indicates the percentage of open flows on this
        traffic processor out of the maximum supported number of flows 
        per traffic processor."
    ::= { cscTpEntry 19 }

cscTpServiceLoss OBJECT-TYPE
    SYNTAX Gauge(0..100000)
--  Units
--    0.001 percent
    ACCESS read-only
    STATUS mandatory
    DESCRIPTION
        "This object indicates the relative amount of service loss in
        this traffic processor, in units of 0.001%, since last restart."
    ::= { cscTpEntry 20 }

cscTpStatsTrafficCountersTable OBJECT-TYPE
    SYNTAX SEQUENCE OF CscTpStatsTrafficCountersEntry
    ACCESS not-accessible
    STATUS mandatory
    DESCRIPTION
        "This table contains various traffic counters pertaining to
        traffic processing by the service control entity. 
        These counters are defined, maintained and uniquely named by the
        service control entity hosted by traffic processor(s) at run
        time."
    ::= { ciscoSCTpStatsMIBObjects 2 }

cscTpStatsTrafficCountersEntry OBJECT-TYPE
    SYNTAX CscTpStatsTrafficCountersEntry
    ACCESS not-accessible
    STATUS mandatory
    DESCRIPTION
        "This entry contains the traffic counter data for a specific
        traffic counter defined by the service control entity at run
        time. The service control entity is indicated by
        entPhysicalIndex in the ENTITY-MIB with entPhysicalClass of
        either 'module' or 'chassis'."
    INDEX { entPhysicalIndex, cscTpStatsTrafficCounterIndex }
    ::= { cscTpStatsTrafficCountersTable 1 }

CscTpStatsTrafficCountersEntry ::= SEQUENCE {
    cscTpStatsTrafficCounterIndex Gauge,
    cscTpStatsTrafficCounterName SnmpAdminString,
    cscTpStatsTrafficCounterValue Counter,
    cscTpStatsTrafficCounterType INTEGER
    }

cscTpStatsTrafficCounterIndex OBJECT-TYPE
    SYNTAX Gauge(1..4294967295)
    ACCESS not-accessible
    STATUS mandatory
    DESCRIPTION
        "An index value that uniquely identifies the counter."
    ::= { cscTpStatsTrafficCountersEntry 1 }

cscTpStatsTrafficCounterName OBJECT-TYPE
    SYNTAX SnmpAdminString
--    Rsyntax OCTET STRING(SIZE(0..255))
    ACCESS read-only
    STATUS mandatory
    DESCRIPTION
        "This object indicates the human-readable name of this counter.
        The name is assigned by the service control entity when this
        counter is created at run time."
    ::= { cscTpStatsTrafficCountersEntry 2 }

cscTpStatsTrafficCounterValue OBJECT-TYPE
    SYNTAX --?? syntax is not convertable to SMIv1
           Counter
    ACCESS read-only
    STATUS mandatory
    DESCRIPTION
        "This object indicates a 64 bit counter value.
        
        Discontinuities in the value of this counter can occur at
        re-initialization of the management system, and at other times
        as indicated by the value of cscTpCounterDiscontinuityTime."
    ::= { cscTpStatsTrafficCountersEntry 3 }

cscTpStatsTrafficCounterType OBJECT-TYPE
    SYNTAX INTEGER {
        other(1),
        bytes(2),
        packets(3)
        }
    ACCESS read-only
    STATUS mandatory
    DESCRIPTION
        "Specifies the measurement unit of the traffic counters measured
        by cscTpStatsTrafficCounterValue and described by 
        cscTpStatsTrafficCounterName.
        'packets'       : counts by packets
        'bytes'         : counts by bytes
        'other'         : none of the above."
    ::= { cscTpStatsTrafficCountersEntry 4 }

cscTpCounterDiscontinuityTime OBJECT-TYPE
    SYNTAX TimeStamp
--    Rsyntax TimeTicks
    ACCESS read-only
    STATUS mandatory
    DESCRIPTION
        "The value of sysUpTime on the most recent occasion at which any
        one or more of the traffic processors's counters suffered a
        discontinuity. If no such discontinuities have occurred since
        the last re-initialization of the local management subsystem,
        then this object contains a zero value."
    ::= { ciscoSCTpStatsMIBObjects 3 }

cscTpStatsMIBObjectGroup OBJECT IDENTIFIER ::= { cscTpStatsMIBGroups 1 }
-- OBJECT-GROUP
--  Status
--    mandatory
--  Descr
--    This group is a collection of objects for traffic processor
--    counters related to handling data.
--  objects
--    cscTpTotalHandledPackets, cscTpTotalHandledFlows, 
--    cscTpActiveFlows, cscTpTcpActiveFlows, cscTpUdpActiveFlows, 
--    cscTpTotalBlockedPackets, cscTpTotalBlockedFlows, 
--    cscTpTotalBandwidthDiscardedPackets, 
--    cscTpTotalWredDiscardedPackets, cscTpTotalFragments, 
--    cscTpTotalNonIpPackets, cscTpTotalIpChecksumErrPackets, 
--    cscTpTotalIpLengthErrPackets, cscTpTotalIpBroadcastPackets, 
--    cscTpTotalTTLErrPackets, cscTpTotalTcpUdpChksumErrPackets, 
--    cscTpHandledPacketsRate, cscTpHandledFlowsRate, 
--    cscTpFlowsCapacityUtilization, cscTpServiceLoss

cscTpStatsMIBTrafficCntrsObjGroup OBJECT IDENTIFIER ::= { cscTpStatsMIBGroups 2 }
-- OBJECT-GROUP
--  Status
--    mandatory
--  Descr
--    This group is a collection of objects for general traffic
--    processor counters.
--  objects
--    cscTpStatsTrafficCounterValue, cscTpStatsTrafficCounterName, 
--    cscTpStatsTrafficCounterType

cscTpCounterDiscontinuityGroup OBJECT IDENTIFIER ::= { cscTpStatsMIBGroups 3 }
-- OBJECT-GROUP
--  Status
--    mandatory
--  Descr
--    A collection of objects providing information specific to
--    traffic processor counter discontinuities.
--  objects
--    cscTpCounterDiscontinuityTime

cscTpStatsMIBCompliance OBJECT IDENTIFIER ::= { cscTpStatsMIBCompliances 1 }
-- MODULE-COMPLIANCE
--  Status
--    mandatory
--  Descr
--    The compliance statement for SNMP Agents which implement this
--    MIB.
--  Module
--    >>current<<
--   MandGroup
--    cscTpStatsMIBObjectGroup
--   MandGroup
--    cscTpStatsMIBTrafficCntrsObjGroup
--   MandGroup
--    cscTpCounterDiscontinuityGroup


END
