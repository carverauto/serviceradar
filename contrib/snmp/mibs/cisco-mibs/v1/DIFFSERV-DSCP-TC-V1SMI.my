-- MIB file created 31-Mar-2006 10:15:53, by
--   SMICng version 2.2.11-beta(PRO)(Solaris), January 20, 2001. Enterprise key cisco.com

DIFFSERV-DSCP-TC DEFINITIONS ::= BEGIN

-- From file: "DIFFSERV-DSCP-TC.my"
-- Compile options "4 7 F H N O W 03 06 0B 0G 0N 0T"

IMPORTS
    mib-2
            FROM SNMPv2-SMI-v1;

diffServDSCPTC OBJECT IDENTIFIER ::= { mib-2 96 }
-- MODULE-IDENTITY
--  LastUpdated
--    200205090000Z
--  OrgName
--    IETF Differentiated Services WG
--  ContactInfo
--           Fred Baker
--            Cisco Systems
--            1121 Via Del Rey
--            Santa Barbara, CA 93117, USA
--            E-mail: fred@cisco.com
--    
--            Kwok Ho Chan
--            Nortel Networks
--            600 Technology Park Drive
--            Billerica, MA 01821, USA
--            E-mail: khchan@nortelnetworks.com
--    
--            Andrew Smith
--            Harbour Networks
--            Jiuling Building
--            21 North Xisanhuan Ave.
--            Beijing, 100089, PRC
--            E-mail: ah_smith@acm.org
--    
--              Differentiated Services Working Group:
--              diffserv@ietf.org
--  Descr
--    The Textual Conventions defined in this module should be used
--    whenever a Differentiated Services Code Point is used in a MIB.
--  RevDate
--    200205090000Z
--  RevDescr
--    Initial version, published as RFC 3289.

Dscp ::= INTEGER(0..63)
-- TEXTUAL-CONVENTION
--  DspHint
--    d
--  Status
--    mandatory
--  Descr
--    A Differentiated Services Code-Point that may be used for
--    marking a traffic stream.
--  Refer
--    RFC 2474, RFC 2780

DscpOrAny ::= INTEGER(-1|0..63)
-- TEXTUAL-CONVENTION
--  DspHint
--    d
--  Status
--    mandatory
--  Descr
--    The IP header Differentiated Services Code-Point that may be
--    
--    
--    
--    used for discriminating among traffic streams. The value -1 is
--    used to indicate a wild card i.e. any value.
--  Refer
--    RFC 2474, RFC 2780


END
