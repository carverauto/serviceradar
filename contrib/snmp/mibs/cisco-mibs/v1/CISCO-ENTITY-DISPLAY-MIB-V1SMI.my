-- MIB file created 07-Jun-2011 14:35:13, by
--   SMICng version 2.2.11-beta(PRO)(Solaris), January 20, 2001. Enterprise key cisco.com

CISCO-ENTITY-DISPLAY-MIB DEFINITIONS ::= BEGIN

-- From file: "CISCO-ENTITY-DISPLAY-MIB.my"
-- Compile options "4 7 F H N W 03 06 0B 0G 0N 0T"

IMPORTS
    TruthValue
            FROM SNMPv2-TC-v1
    SnmpAdminString
            FROM SNMP-FRAMEWORK-MIB
    entPhysicalIndex
            FROM ENTITY-MIB
    ciscoMgmt
            FROM CISCO-SMI
    Gauge
            FROM RFC1155-SMI
    OBJECT-TYPE
            FROM RFC-1212;

ciscoEntityDisplayMIB OBJECT IDENTIFIER ::= { ciscoMgmt 344 }
-- MODULE-IDENTITY
--  LastUpdated
--    200910050000Z
--  OrgName
--    Cisco Systems, Inc.
--  ContactInfo
--    Cisco Systems
--    Customer Service
--    
--    Postal: 170 W Tasman Drive
--    San Jose, CA  95134
--    USA
--    
--    Tel: +1 800 553-NETS
--    
--    E-mail: cs-displaymib@cisco.com
--  Descr
--    This MIB module provides information about the
--    status of display devices such as Light Emitting
--    Diodes (LEDs) and alphanumeric displays present
--    on the physical entities contained by the managed
--    system.
--  RevDate
--    200910050000Z
--  RevDescr
--    Added the enumeration 'greenAndAmber' to
--    CDisplayColor TEXTUAL-CONVENTION.
--    Added support for ceDisplayBeaconGroup.
--  RevDate
--    200303200000Z
--  RevDescr
--    Initial version of this MIB.

ciscoEntityDisplayMIBObjects OBJECT IDENTIFIER ::= { ciscoEntityDisplayMIB 1 }
ceDisplayMIBConformance OBJECT IDENTIFIER ::= { ciscoEntityDisplayMIB 2 }
ceDisplayMIBCompliances OBJECT IDENTIFIER ::= { ceDisplayMIBConformance 1 }
ceDisplayMIBGroups OBJECT IDENTIFIER ::= { ceDisplayMIBConformance 2 }

CDisplayType ::= INTEGER {
        led(1),
        alphanumeric(2)
        }
-- TEXTUAL-CONVENTION
--  Status
--    mandatory
--  Descr
--    An integer value that indicates the type of
--    display device.

CDisplayColor ::= INTEGER {
        unknown(1),
        white(2),
        red(3),
        green(4),
        yellow(5),
        amber(6),
        blue(7),
        greenAndAmber(8)
        }
-- TEXTUAL-CONVENTION
--  Status
--    mandatory
--  Descr
--    An integer value that describes the color of the
--    display.
--    
--    'greenAndAmber'    - Indicates that the display color
--                         toggles between green and amber.

CDisplayState ::= INTEGER {
        unknown(1),
        off(2),
        on(3),
        blinking(4)
        }
-- TEXTUAL-CONVENTION
--  Status
--    mandatory
--  Descr
--    An integer value that describes the state of the
--    display.

ceDisplayTable OBJECT-TYPE
    SYNTAX SEQUENCE OF CeDisplayEntry
    ACCESS not-accessible
    STATUS mandatory
    DESCRIPTION
        "This table provides information about the display
        devices on the physical entities in the managed
        system and their current display status."
    ::= { ciscoEntityDisplayMIBObjects 1 }

ceDisplayEntry OBJECT-TYPE
    SYNTAX CeDisplayEntry
    ACCESS not-accessible
    STATUS mandatory
    DESCRIPTION
        "An entry in the ceDisplayTable that provides
        information about an LED or an alphanumeric display
        in the system including its current display status."
    INDEX { entPhysicalIndex, ceDisplayIndex }
    ::= { ceDisplayTable 1 }

CeDisplayEntry ::= SEQUENCE {
    ceDisplayIndex Gauge,
    ceDisplayType CDisplayType,
    ceDisplayName SnmpAdminString,
    ceDisplayState CDisplayState,
    ceDisplayColor CDisplayColor,
    ceDisplayText SnmpAdminString
    }

ceDisplayIndex OBJECT-TYPE
    SYNTAX Gauge(1..1024)
    ACCESS not-accessible
    STATUS mandatory
    DESCRIPTION
        "An arbitrary index that uniquely identifies an LED or
        an alphanumeric display on the physical entity
        identified by entPhysicalIndex."
    ::= { ceDisplayEntry 1 }

ceDisplayType OBJECT-TYPE
    SYNTAX CDisplayType
--    Rsyntax INTEGER {
--        led(1),
--        alphanumeric(2)
--        }
    ACCESS read-only
    STATUS mandatory
    DESCRIPTION
        "This object indicates the type of display described
        in this entry. i.e. whether it is an LED display or
        an alphanumeric display."
    ::= { ceDisplayEntry 2 }

ceDisplayName OBJECT-TYPE
    SYNTAX SnmpAdminString
--    Rsyntax OCTET STRING(SIZE(0..255))
    ACCESS read-only
    STATUS mandatory
    DESCRIPTION
        "This object provides a human-readable string which is
        the name for the display device specified in this entry."
    ::= { ceDisplayEntry 3 }

ceDisplayState OBJECT-TYPE
    SYNTAX CDisplayState
--    Rsyntax INTEGER {
--        unknown(1),
--        off(2),
--        on(3),
--        blinking(4)
--        }
    ACCESS read-only
    STATUS mandatory
    DESCRIPTION
        "This object indicates the current display state for
        the display specified in this entry."
    ::= { ceDisplayEntry 4 }

ceDisplayColor OBJECT-TYPE
    SYNTAX CDisplayColor
--    Rsyntax INTEGER {
--        unknown(1),
--        white(2),
--        red(3),
--        green(4),
--        yellow(5),
--        amber(6),
--        blue(7),
--        greenAndAmber(8)
--        }
    ACCESS read-only
    STATUS mandatory
    DESCRIPTION
        "This object indicates the color currently seen on
        the display specified in this entry. If the display
        specified by this entry is an alphanumeric display,
        i.e. ceDisplayType is of type 'alphanumeric' then,
        color may not apply and the agent may choose to
        indicate this by setting this object to 'unknown'."
    ::= { ceDisplayEntry 5 }

ceDisplayText OBJECT-TYPE
    SYNTAX SnmpAdminString
--    Rsyntax OCTET STRING(SIZE(0..255))
    ACCESS read-only
    STATUS mandatory
    DESCRIPTION
        "This object provides a human-readable string which is
        the text currently displayed in the alphanumeric display
        specified in this entry. If the display specified by
        this entry is an LED, i.e. ceDisplayType is of type 'led'
        then, this object would be an empty string."
    ::= { ceDisplayEntry 6 }

ceDisplayBeaconTable OBJECT-TYPE
    SYNTAX SEQUENCE OF CeDisplayBeaconEntry
    ACCESS not-accessible
    STATUS mandatory
    DESCRIPTION
        "This table provides functionality to manage
        beacon display devices in the managed system."
    ::= { ciscoEntityDisplayMIBObjects 2 }

ceDisplayBeaconEntry OBJECT-TYPE
    SYNTAX CeDisplayBeaconEntry
    ACCESS not-accessible
    STATUS mandatory
    DESCRIPTION
        "An entry containing management information of
        beacon functionality of a particular beacon 
        display device.
        
        Only those display devices, as specified by 
        entPhysicalIndex in ENTITY-MIB, that support 
        beacon functionality will be populated in this 
        table."
    INDEX { entPhysicalIndex, ceDisplayIndex }
    ::= { ceDisplayBeaconTable 1 }

CeDisplayBeaconEntry ::= SEQUENCE {
    ceDisplayBeaconEnabled TruthValue
    }

ceDisplayBeaconEnabled OBJECT-TYPE
    SYNTAX TruthValue
--    Rsyntax INTEGER {
--        true(1),
--        false(2)
--        }
    ACCESS read-write
    STATUS mandatory
    DESCRIPTION
        "This object specifies if the beacon functionality is
        administratively enabled for this display device.
        
        'true'    - beacon functionality is administratively 
                    enabled
        'false'   - beacon functionality is administratively 
                    disabled."
    ::= { ceDisplayBeaconEntry 1 }

ceDisplayGroup OBJECT IDENTIFIER ::= { ceDisplayMIBGroups 1 }
-- OBJECT-GROUP
--  Status
--    mandatory
--  Descr
--    A collection of managed objects that provide information
--    about a display in the system including its current state.
--  objects
--    ceDisplayType, ceDisplayName, ceDisplayState

ceDisplayLEDGroup OBJECT IDENTIFIER ::= { ceDisplayMIBGroups 2 }
-- OBJECT-GROUP
--  Status
--    mandatory
--  Descr
--    A collection of objects relevant to LED display.
--  objects
--    ceDisplayColor

ceDisplayAlphaNumericGroup OBJECT IDENTIFIER ::= { ceDisplayMIBGroups 3 }
-- OBJECT-GROUP
--  Status
--    mandatory
--  Descr
--    A collection of objects relevant to alphanumeric display.
--  objects
--    ceDisplayText

ceDisplayBeaconGroup OBJECT IDENTIFIER ::= { ceDisplayMIBGroups 4 }
-- OBJECT-GROUP
--  Status
--    mandatory
--  Descr
--    A collection of objects relevant to beacon
--    functionality.
--  objects
--    ceDisplayBeaconEnabled

ceDisplayMIBCompliance OBJECT IDENTIFIER ::= { ceDisplayMIBCompliances 1 }
-- MODULE-COMPLIANCE
--  Status
--    deprecated
--  Descr
--    The compliance statement for entities that implement the
--    CISCO-ENTITY-DISPLAY-MIB.
--    
--    This compliance statement is deprecated and superceded by
--    ceDisplayMIBCompliance2.
--  Module
--    >>current<<
--   MandGroup
--    ceDisplayGroup
--   OptGroup
--    ceDisplayLEDGroup
--   OptGroup
--    ceDisplayAlphaNumericGroup

ceDisplayMIBCompliance2 OBJECT IDENTIFIER ::= { ceDisplayMIBCompliances 2 }
-- MODULE-COMPLIANCE
--  Status
--    mandatory
--  Descr
--    The compliance statement for entities that implement the
--    CISCO-ENTITY-DISPLAY-MIB.
--  Module
--    >>current<<
--   MandGroup
--    ceDisplayGroup
--   OptGroup
--    ceDisplayLEDGroup
--   OptGroup
--    ceDisplayAlphaNumericGroup
--   OptGroup
--    ceDisplayBeaconGroup
--   ObjVar
--    ceDisplayBeaconEnabled


END
