-- MIB file created 03-May-2010 11:33:01, by
--   SMICng version 2.2.11-beta(PRO)(Solaris), January 20, 2001. Enterprise key cisco.com

CISCO-VOICE-LMR-MIB DEFINITIONS ::= BEGIN

-- From file: "CISCO-VOICE-LMR-MIB.my"
-- Compile options "4 7 F H N W 03 06 0B 0G 0N 0T"

IMPORTS
    TruthValue
            FROM SNMPv2-TC-v1
    SnmpAdminString
            FROM SNMP-FRAMEWORK-MIB
    ciscoMgmt
            FROM CISCO-SMI
    Gauge
            FROM RFC1155-SMI
    OBJECT-TYPE
            FROM RFC-1212;

ciscoVoiceLmrMIB OBJECT IDENTIFIER ::= { ciscoMgmt 510 }
-- MODULE-IDENTITY
--  LastUpdated
--    200410140000Z
--  OrgName
--    Cisco Systems, Inc.
--  ContactInfo
--           Cisco Systems
--            Customer Service
--    
--    Postal: 170 W. Tasman Drive
--            San Jose, CA  95134
--            USA
--    
--    Tel: +1 800 553-NETS
--    
--    E-mail: cs-voice@cisco.com
--  Descr
--    This MIB module  provides management of voice tone
--     signal as static injected tone for Land Mobile Radio
--     The tone signal includes tone, pause, guard/idle tone.
--     User can configure a sequence of tone and pause to
--     be played out before any voice sample is played out.
--     These tones are used to wake up the radio and 
--     select the radio channel. During the voice playout,
--     a configured guard tone will be mixed with the voice
--     to keep the radio active. For some radio systems, 
--     there is no need for the guard tone, but a configured
--     idle tone is needed  to inform the radio that the
--     channel is idle. It is possible that the radio system
--     will generate guard/idle tone.  In that case,
--     the IOS can instruct the DSP to filter out the radio
--     generated guard/idle tone by enabling digital filter. 
--     Digital filter is able to filter out either 1950HZ or
--     2175HZ tone.
--  RevDate
--    200410140000Z
--  RevDescr
--    the initial version of the MIB.

cvlMIBObjects   OBJECT IDENTIFIER ::= { ciscoVoiceLmrMIB 1 }
cvlMIBConformance OBJECT IDENTIFIER ::= { ciscoVoiceLmrMIB 2 }
cvlToneObjects  OBJECT IDENTIFIER ::= { cvlMIBObjects 1 }
cvlMIBCompliances OBJECT IDENTIFIER ::= { cvlMIBConformance 1 }
cvlMIBGroups    OBJECT IDENTIFIER ::= { cvlMIBConformance 2 }

VoiceFrequency ::= Gauge(0..4000)
-- TEXTUAL-CONVENTION
--  DspHint
--    d
--  Status
--    mandatory
--  Descr
--    This textual convention is used to represent the
--     audible voice frequency between 1HZ to 4000HZ.
--     Value 0 indicates this textual convention is not
--     configured.

VoiceAmplitude ::= INTEGER(-30..3)
-- TEXTUAL-CONVENTION
--  DspHint
--    d
--  Status
--    mandatory
--  Descr
--    This textual convention is used to
--     represent the amplitude of voice between -30 
--     to 3 dbm.
--     dbm is the absolute output and input optical
--     power levels in mW.

LmrToneDuration ::= Gauge(0..500)
-- TEXTUAL-CONVENTION
--  DspHint
--    d
--  Status
--    mandatory
--  Descr
--    This textual convention is used to represent
--     the duration of tone played. It is measured in
--     milliseconds.

cvlClassTable OBJECT-TYPE
    SYNTAX SEQUENCE OF CvlClassEntry
    ACCESS not-accessible
    STATUS mandatory
    DESCRIPTION
        "The table contains the LMR guard/idle tone frequency
         and amplitude. It also specifies what frequency will be
         filtered out from radio voice input by dsp digital filter."
    ::= { cvlToneObjects 1 }

cvlClassEntry OBJECT-TYPE
    SYNTAX CvlClassEntry
    ACCESS not-accessible
    STATUS mandatory
    DESCRIPTION
        "A concept row in cvlClassTable. It has class name,
         tone frequency, tone amplitude, guard/idle tone
         indicator and digital filter information."
    INDEX { cvlClassIndex }
    ::= { cvlClassTable 1 }

CvlClassEntry ::= SEQUENCE {
    cvlClassIndex Gauge,
    cvlClassName SnmpAdminString,
    cvlDigitalFilter INTEGER,
    cvlGuardToneFreq VoiceFrequency,
    cvlGuardToneAmp VoiceAmplitude,
    cvlIdleToneFlag TruthValue
    }

cvlClassIndex OBJECT-TYPE
    SYNTAX Gauge(1..10000)
    ACCESS not-accessible
    STATUS mandatory
    DESCRIPTION
        "An arbitrary integer which increases monotonically to
         index the cvlClassTable."
    ::= { cvlClassEntry 1 }

cvlClassName OBJECT-TYPE
    SYNTAX SnmpAdminString(SIZE(0..19))
--    Rsyntax OCTET STRING(SIZE(0..19))
    ACCESS read-only
    STATUS mandatory
    DESCRIPTION
        "The object reflects the voice class name."
    ::= { cvlClassEntry 2 }

cvlDigitalFilter OBJECT-TYPE
    SYNTAX INTEGER {
        --?? enum value of zero may cause problems
--        digitalFilterNone(0),
        digitalFilter1950HZ(1),
        digitalFilter2175HZ(2)
        }
    ACCESS read-only
    STATUS mandatory
    DESCRIPTION
        "This object reflects which tone frequency should 
         be filtered out from radio input.
         "
--    DEFVAL { digitalFilterNone }
    ::= { cvlClassEntry 3 }

cvlGuardToneFreq OBJECT-TYPE
    SYNTAX VoiceFrequency
--    Rsyntax Gauge(0..4000)
    ACCESS read-only
    STATUS mandatory
    DESCRIPTION
        "This object reflects the guard/idle tone frequency between
         1-4000 HZ. If there is no guard/idle tone configured for
         this voice class, cvlGuardToneFreq has value 0."
    DEFVAL { 0 }
    ::= { cvlClassEntry 4 }

cvlGuardToneAmp OBJECT-TYPE
    SYNTAX VoiceAmplitude
--    Rsyntax INTEGER(-30..3)
    ACCESS read-only
    STATUS mandatory
    DESCRIPTION
        "This object reflects the guard/idle tone amplitude in dbm."
    DEFVAL { 0 }
    ::= { cvlClassEntry 5 }

cvlIdleToneFlag OBJECT-TYPE
    SYNTAX TruthValue
--    Rsyntax INTEGER {
--        true(1),
--        false(2)
--        }
    ACCESS read-only
    STATUS mandatory
    DESCRIPTION
        "This object reflects this voice class has guard/idle
         tone configured. true means guard tone and false means
         idle tone. "
    DEFVAL { false }
    ::= { cvlClassEntry 6 }

cvlSignalToneTable OBJECT-TYPE
    SYNTAX SEQUENCE OF CvlSignalToneEntry
    ACCESS not-accessible
    STATUS mandatory
    DESCRIPTION
        "The table contains the LMR injected tone information
         and playout sequence for voice class tone signal.
         The tones with same cvlSignalToneGroupIndex
         will be played out in ascending order of the 
         cvlSignalToneIndex.            "
    ::= { cvlToneObjects 2 }

cvlSignalToneEntry OBJECT-TYPE
    SYNTAX CvlSignalToneEntry
    ACCESS not-accessible
    STATUS mandatory
    DESCRIPTION
        "An entry in the table, containing information
         about a single tone."
    INDEX { cvlSignalToneGroupIndex, cvlSignalToneIndex }
    ::= { cvlSignalToneTable 1 }

CvlSignalToneEntry ::= SEQUENCE {
    cvlSignalToneGroupIndex Gauge,
    cvlSignalToneIndex Gauge,
    cvlSignalToneName SnmpAdminString,
    cvlSignalToneFreq VoiceFrequency,
    cvlSignalToneAmp VoiceAmplitude,
    cvlSignalToneDur LmrToneDuration
    }

cvlSignalToneGroupIndex OBJECT-TYPE
    SYNTAX Gauge(1..10000)
    ACCESS not-accessible
    STATUS mandatory
    DESCRIPTION
        "This object reflects a group of tones. 
         The tones with same cvlSignalToneGroupIndex
         will be played out in ascending order of the 
         cvlSignalToneIndex."
    ::= { cvlSignalToneEntry 1 }

cvlSignalToneIndex OBJECT-TYPE
    SYNTAX Gauge(1..10)
    ACCESS not-accessible
    STATUS mandatory
    DESCRIPTION
        "This object reflects the tone playout sequence in
         ascending order of the index for the tones with same
         cvlSignalToneGroupIndex value."
    ::= { cvlSignalToneEntry 2 }

cvlSignalToneName OBJECT-TYPE
    SYNTAX SnmpAdminString(SIZE(0..19))
--    Rsyntax OCTET STRING(SIZE(0..19))
    ACCESS read-only
    STATUS mandatory
    DESCRIPTION
        "The object reflects the tone signal class name."
    ::= { cvlSignalToneEntry 3 }

cvlSignalToneFreq OBJECT-TYPE
    SYNTAX VoiceFrequency
--    Rsyntax Gauge(0..4000)
    ACCESS read-only
    STATUS mandatory
    DESCRIPTION
        "This object reflects the tone frequency in HZ.
         If the value is 0 then no tone will be played out
         and can be used to provide pause during a sequence
         of tones."
    ::= { cvlSignalToneEntry 4 }

cvlSignalToneAmp OBJECT-TYPE
    SYNTAX VoiceAmplitude
--    Rsyntax INTEGER(-30..3)
    ACCESS read-only
    STATUS mandatory
    DESCRIPTION
        "This object reflects the signal tone amplitude in dbm."
    ::= { cvlSignalToneEntry 5 }

cvlSignalToneDur OBJECT-TYPE
    SYNTAX LmrToneDuration
--    Rsyntax Gauge(0..500)
    ACCESS read-only
    STATUS mandatory
    DESCRIPTION
        "This object reflects the signal tone duration."
    ::= { cvlSignalToneEntry 6 }

cvlToneClassGroup OBJECT IDENTIFIER ::= { cvlMIBGroups 1 }
-- OBJECT-GROUP
--  Status
--    mandatory
--  Descr
--    A collection of objects that provide info 
--     applicable to digital notch filter or guard/idle
--     tone.
--  objects
--    cvlClassName, cvlDigitalFilter, cvlGuardToneFreq, 
--    cvlGuardToneAmp, cvlIdleToneFlag

cvlToneSignalGroup OBJECT IDENTIFIER ::= { cvlMIBGroups 2 }
-- OBJECT-GROUP
--  Status
--    mandatory
--  Descr
--    A collection of objects that provide info 
--     applicable to either wake-up tone, function
--     selection or pause between tones. It also 
--     provides the info about the playout sequence
--     of the tones.
--  objects
--    cvlSignalToneName, cvlSignalToneFreq, cvlSignalToneAmp, 
--    cvlSignalToneDur

cvlMIBCompliance OBJECT IDENTIFIER ::= { cvlMIBCompliances 1 }
-- MODULE-COMPLIANCE
--  Status
--    mandatory
--  Descr
--    The compliance statements for the Cisco Land Mobile
--     Radio (LMR) MIB.
--  Module
--    >>current<<
--   MandGroup
--    cvlToneClassGroup
--   MandGroup
--    cvlToneSignalGroup


END
