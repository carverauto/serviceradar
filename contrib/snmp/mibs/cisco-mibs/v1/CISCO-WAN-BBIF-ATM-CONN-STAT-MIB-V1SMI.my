-- MIB file created 04-Jun-2003 18:09:11, by
--   SMICng version 2.2.11-beta(PRO)(Solaris), January 20, 2001. Enterprise key cisco.com

CISCO-WAN-BBIF-ATM-CONN-STAT-MIB DEFINITIONS ::= BEGIN

-- From file: "CISCO-WAN-BBIF-ATM-CONN-STAT-MIB.my"
-- Compile options "4 7 F H N W 03 06 0B 0G 0N 0T"

IMPORTS
    bbChanCntGrp
            FROM BASIS-MIB
    ciscoWan
            FROM CISCOWAN-SMI
    Counter
            FROM RFC1155-SMI
    OBJECT-TYPE
            FROM RFC-1212;

ciscoWanBbifAtmConnStatMIB OBJECT IDENTIFIER ::= { ciscoWan 36 }
-- MODULE-IDENTITY
--  LastUpdated
--    200210180000Z
--  OrgName
--    Cisco Systems, Inc.
--  ContactInfo
--           Cisco Systems
--            Customer Service
--    
--    Postal: 170 W Tasman Drive
--            San Jose, CA  95134
--            USA
--    
--            Tel: +1 800 553-NETS
--    
--    E-mail: cs-wanatm@cisco.com
--  Descr
--    This MIB module contains ATM Connection related
--    real time statistical counter objects. The ATM
--    connections are applicable to PXM1 service module.
--    in MGX82xx products.
--    
--    Logical Channel refers to ATM Connection(or connection
--    end point).
--    
--    Terminologies used:
--        broadband interface - Logical port on PXM1.
--        SCR  - Sustained Cell Rate
--        BT   - Burst Tolerance
--        PCR  - Peak Cell Rate
--        CDVT - Cell Delay Transfer Variance Tolerance
--    GCRA - The Generic Cell Rate Algorithm(GCRA) is used to
--        define comformance with repect to the traffic
--        contract. For each cell arrival, the GCRA determines
--    whether the cell conforms to the traffic contract
--    of the connection.
--    
--        GCRA1 - GCRA  Bucket 1. For CBR and UBR connections, only
--                GCRA-1 is needed to check for PCR, CDVT Conformance.
--    
--        GCRA2 - GCRA  Bucket 2. For VBR and ABR Connections, GCRA-1
--                is needed to check for PCR, CDVT conformance and
--                GCRA-2 for SCR, BT Conformance.
--    
--        EFCI - Explicit Forward Congestion Indication.
--        QE    - Queue Engine(QE).
--                This ASIC Provides the traffic management functions
--                related to VC queues, QoS queues and interface
--                queues. This management function is performed
--                for both directions of traffic(ingress, egress).
--        ingress - ingress traffic is defined as data flowing
--                  toward the switch fabric. Ingress data can come
--                  from either the Service Modules through the 
--                  backplane or the PXM1 Uplink back card.
--        egress  - Egress traffic is defined as data flowing
--                  away from the switch fabric.
--  RevDate
--    200210180000Z
--  RevDescr
--    Initial version of the MIB.
--    
--    The content of this MIB was originally available
--    in CISCO-WAN-AXIPOP-MIB defined using SMIv1.
--    The applicable objects from CISCO-WAN-AXIPOP-MIB
--    are defined using SMIv2 in this MIB. Also the
--    descriptions of some of the objects have been 
--    modified.

cwbAtmConnStatMIBConformance OBJECT IDENTIFIER ::= { ciscoWanBbifAtmConnStatMIB 2 }
cwbAtmConnStatMIBGroups OBJECT IDENTIFIER ::= { cwbAtmConnStatMIBConformance 1 }
cwbAtmConnStatMIBCompliances OBJECT IDENTIFIER ::= { cwbAtmConnStatMIBConformance 2 }

bbChanCntGrpTable OBJECT-TYPE
    SYNTAX SEQUENCE OF BbChanCntGrpEntry
    ACCESS not-accessible
    STATUS mandatory
    DESCRIPTION
        "This is the broadband channel statistics table."
    ::= { bbChanCntGrp 1 }

bbChanCntGrpEntry OBJECT-TYPE
    SYNTAX BbChanCntGrpEntry
    ACCESS not-accessible
    STATUS mandatory
    DESCRIPTION
        "An entry for statistics on logical channel.
        Each entry contains statistics for an ATM connection
        on broadband interface."
    INDEX { bbChanCntNum }
    ::= { bbChanCntGrpTable 1 }

BbChanCntGrpEntry ::= SEQUENCE {
    bbChanCntNum INTEGER,
    bbChanRcvClp0Cells Counter,
    bbChanRcvClp1Cells Counter,
    bbChanNonConformCellsAtGcra1Policer Counter,
    bbChanNonConformCellsAtGcra2Policer Counter,
    bbChanRcvEOFCells Counter,
    bbChanDscdClp0Cells Counter,
    bbChanDscdClp1Cells Counter,
    bbChanRcvCellsSent Counter,
    bbChanXmtClp0Cells Counter,
    bbChanXmtClp1Cells Counter,
    bbChanDscdClpZeroCellsToPort Counter,
    bbChanDscdClpOneCellsToPort Counter,
    bbChanCntClrButton INTEGER
    }

bbChanCntNum OBJECT-TYPE
    SYNTAX INTEGER(16..4111)
    ACCESS read-only
    STATUS mandatory
    DESCRIPTION
        "This object identifies the logical channel number. 
               The value for this object must be same as the value
               of 'bbChanCnfNum' from bbChanCnfGrpTable."
    REFERENCE
        "bbChanCnfNum is defined in CISCO-WAN-BBIF-ATM-CONN-MIB."
    ::= { bbChanCntGrpEntry 1 }

bbChanRcvClp0Cells OBJECT-TYPE
    SYNTAX Counter
    ACCESS read-only
    STATUS mandatory
    DESCRIPTION
        "CLP_0 Cells Received from broadband interface."
    ::= { bbChanCntGrpEntry 2 }

bbChanRcvClp1Cells OBJECT-TYPE
    SYNTAX Counter
    ACCESS read-only
    STATUS mandatory
    DESCRIPTION
        "CLP_1 Cells Received from broadband interface."
    ::= { bbChanCntGrpEntry 3 }

bbChanNonConformCellsAtGcra1Policer OBJECT-TYPE
    SYNTAX Counter
    ACCESS read-only
    STATUS mandatory
    DESCRIPTION
        "This object provides a count of the 
               nonconforming cells that are received at the
               first policing point(GCRA1 policer)."
    ::= { bbChanCntGrpEntry 4 }

bbChanNonConformCellsAtGcra2Policer OBJECT-TYPE
    SYNTAX Counter
    ACCESS read-only
    STATUS mandatory
    DESCRIPTION
        "This object provides a count of the 
               nonconforming cells that are received at the
               second policing point(GCRA2 policer)."
    ::= { bbChanCntGrpEntry 5 }

bbChanRcvEOFCells OBJECT-TYPE
    SYNTAX Counter
    ACCESS read-only
    STATUS mandatory
    DESCRIPTION
        "This object provides count of End Of Frame(EOF)
               cells that are received."
    ::= { bbChanCntGrpEntry 6 }

bbChanDscdClp0Cells OBJECT-TYPE
    SYNTAX Counter
    ACCESS read-only
    STATUS mandatory
    DESCRIPTION
        "This object provides a count of the CLP equal to
               0 that are received and then discarded."
    ::= { bbChanCntGrpEntry 7 }

bbChanDscdClp1Cells OBJECT-TYPE
    SYNTAX Counter
    ACCESS read-only
    STATUS mandatory
    DESCRIPTION
        "This object provides a count of the CLP equal to
               1 that are received and then discarded."
    ::= { bbChanCntGrpEntry 8 }

bbChanRcvCellsSent OBJECT-TYPE
    SYNTAX Counter
    ACCESS read-only
    STATUS mandatory
    DESCRIPTION
        "Number of cells received from broadband interface
               and sent out of the Queue Engine(QE device)."
    ::= { bbChanCntGrpEntry 9 }

bbChanXmtClp0Cells OBJECT-TYPE
    SYNTAX Counter
    ACCESS read-only
    STATUS mandatory
    DESCRIPTION
        "This object provides count of Number of cells 
        with EFCI=0 that are transmitted."
    ::= { bbChanCntGrpEntry 10 }

bbChanXmtClp1Cells OBJECT-TYPE
    SYNTAX Counter
    ACCESS read-only
    STATUS mandatory
    DESCRIPTION
        "This object provides count of Number of cells 
        with EFCI set that are transmitted."
    ::= { bbChanCntGrpEntry 11 }

bbChanDscdClpZeroCellsToPort OBJECT-TYPE
    SYNTAX Counter
    ACCESS read-only
    STATUS mandatory
    DESCRIPTION
        "Number of CLP = 0 cells discarded before 
               transmitted to broadband interface."
    ::= { bbChanCntGrpEntry 12 }

bbChanDscdClpOneCellsToPort OBJECT-TYPE
    SYNTAX Counter
    ACCESS read-only
    STATUS mandatory
    DESCRIPTION
        "Number of CLP = 1 cells discarded before 
               transmitted to broadband interface."
    ::= { bbChanCntGrpEntry 13 }

bbChanCntClrButton OBJECT-TYPE
    SYNTAX INTEGER {
        noAction(1),
        resetCounters(2)
        }
    ACCESS read-write
    STATUS mandatory
    DESCRIPTION
        "Writing a value of 2 resets all the counters."
    ::= { bbChanCntGrpEntry 14 }

cwbAtmConnStatsGroup OBJECT IDENTIFIER ::= { cwbAtmConnStatMIBGroups 1 }
-- OBJECT-GROUP
--  Status
--    mandatory
--  Descr
--    The objects related to broadband interface
--    connection statistics.
--  objects
--    bbChanCntNum, bbChanRcvClp0Cells, bbChanRcvClp1Cells, 
--    bbChanNonConformCellsAtGcra1Policer, 
--    bbChanNonConformCellsAtGcra2Policer, bbChanRcvEOFCells, 
--    bbChanDscdClp0Cells, bbChanDscdClp1Cells, bbChanRcvCellsSent, 
--    bbChanXmtClp0Cells, bbChanXmtClp1Cells, 
--    bbChanDscdClpZeroCellsToPort, bbChanDscdClpOneCellsToPort, 
--    bbChanCntClrButton

cwbAtmConnStatCompliance OBJECT IDENTIFIER ::= { cwbAtmConnStatMIBCompliances 1 }
-- MODULE-COMPLIANCE
--  Status
--    mandatory
--  Descr
--    The compliance statement for broadband
--    interface Connection Statstics MIB.
--  Module
--    >>current<<
--   MandGroup
--    cwbAtmConnStatsGroup


END
