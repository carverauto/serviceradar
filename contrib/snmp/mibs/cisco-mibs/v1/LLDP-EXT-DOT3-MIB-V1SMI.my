-- MIB file created 10-Jul-2014 20:16:51, by
--   SMICng version 2.2.11-beta(PRO)(Solaris), January 20, 2001. Enterprise key cisco.com

LLDP-EXT-DOT3-MIB DEFINITIONS ::= BEGIN

-- From file: "LLDP-EXT-DOT3-MIB.my"
-- Compile options "4 7 F H N W 03 06 0B 0G 0N 0T"

IMPORTS
    TruthValue
            FROM SNMPv2-TC-v1
    lldpExtensions, lldpLocPortNum, lldpRemTimeMark, 
    lldpRemLocalPortNum, lldpRemIndex, lldpPortConfigPortNum
            FROM LLDP-MIB
    OBJECT-TYPE
            FROM RFC-1212;

lldpXdot3MIB OBJECT IDENTIFIER ::= { lldpExtensions 4623 }
-- MODULE-IDENTITY
--  LastUpdated
--    200505060000Z
--  OrgName
--    IEEE 802.1 Working Group
--  ContactInfo
--      WG-URL: http://grouper.ieee.org/groups/802/1/index.html
--     WG-EMail: stds-802-1@ieee.org
--    
--      Contact: Paul Congdon
--       Postal: Hewlett-Packard Company
--               8000 Foothills Blvd. 
--               Roseville, CA 95747
--               USA
--          Tel: +1-916-785-5753
--       E-mail: paul_congdon@hp.com
--  Descr
--    The LLDP Management Information Base extension module for
--    IEEE 802.3 organizationally defined discovery information.
--    
--    In order to assure the uniqueness of the LLDP-MIB,
--    lldpXdot3MIB is branched from lldpExtensions using OUI value
--    as the node.  An OUI/'company_id' is a 24 bit globally unique
--    assigned number referenced by various standards.
--    
--    Copyright (C) IEEE (2005).  This version of this MIB module
--    is published as Annex G.6.1 of IEEE Std 802.1AB-2005;
--    see the standard itself for full legal notices.
--  RevDate
--    200505060000Z
--  RevDescr
--    Published as part of IEEE Std 802.1AB-2005 initial version.

lldpXdot3Objects OBJECT IDENTIFIER ::= { lldpXdot3MIB 1 }
lldpXdot3Config OBJECT IDENTIFIER ::= { lldpXdot3Objects 1 }
lldpXdot3LocalData OBJECT IDENTIFIER ::= { lldpXdot3Objects 2 }
lldpXdot3RemoteData OBJECT IDENTIFIER ::= { lldpXdot3Objects 3 }
lldpXdot3Conformance OBJECT IDENTIFIER ::= { lldpXdot3MIB 2 }
lldpXdot3Compliances OBJECT IDENTIFIER ::= { lldpXdot3Conformance 1 }
lldpXdot3Groups OBJECT IDENTIFIER ::= { lldpXdot3Conformance 2 }

LldpPowerPortClass ::= INTEGER {
        pClassPSE(1),
        pClassPD(2)
        }
-- TEXTUAL-CONVENTION
--  Status
--    mandatory
--  Descr
--    This TC describes the Power over Ethernet (PoE) port class.

LldpLinkAggStatusMap ::= OCTET STRING(SIZE(1..2))
        -- BITS are:
        --   aggCapable(0)
        --   aggEnabled(1)
-- TEXTUAL-CONVENTION
--  Status
--    mandatory
--  Descr
--    This TC describes the link aggregation status.
--    
--    The bit 'aggCapable(0)' indicates the link is capable of being
--    aggregated. 
--    
--    The bit 'aggEnabled(1)' indicates the link is currently in
--    aggregation.

lldpXdot3PortConfigTable OBJECT-TYPE
    SYNTAX SEQUENCE OF LldpXdot3PortConfigEntry
    ACCESS not-accessible
    STATUS mandatory
    DESCRIPTION
        "A table that controls selection of LLDP TLVs to be transmitted 
        on individual ports."
    ::= { lldpXdot3Config 1 }

lldpXdot3PortConfigEntry OBJECT-TYPE
    SYNTAX LldpXdot3PortConfigEntry
    ACCESS not-accessible
    STATUS mandatory
    DESCRIPTION
        "LLDP configuration information that controls the
        transmission of IEEE 802.3 organizationally defined TLVs on
        LLDP transmission capable ports.
        
        This configuration object augments the lldpPortConfigEntry of
        the LLDP-MIB, therefore it is only present along with the port
        configuration defined by the associated lldpPortConfigEntry
        entry.
        
        Each active lldpXdot3PortConfigEntry must be from non-volatile
        storage (along with the corresponding lldpPortConfigEntry)
        after a re-initialization of the management system."
    INDEX { lldpPortConfigPortNum }
-- Augments lldpPortConfigEntry FROM LLDP-MIB
    ::= { lldpXdot3PortConfigTable 1 }

LldpXdot3PortConfigEntry ::= SEQUENCE {
    lldpXdot3PortConfigTLVsTxEnable OCTET STRING
    }

lldpXdot3PortConfigTLVsTxEnable OBJECT-TYPE
    SYNTAX OCTET STRING(SIZE(1..2))
        -- BITS are:
        --   macPhyConfigStatus(0)
        --   powerViaMDI(1)
        --   linkAggregation(2)
        --   maxFrameSize(3)
    ACCESS read-write
    STATUS mandatory
    DESCRIPTION
        "The lldpXdot3PortConfigTLVsTxEnable, defined as a bitmap,
        includes the IEEE 802.3 organizationally defined set of LLDP
        TLVs whose transmission is allowed on the local LLDP agent by
        the network management.  Each bit in the bitmap corresponds
        to an IEEE 802.3 subtype associated with a specific IEEE
        802.3 optional TLV.  The bit 0 is not used since there is
        no corresponding subtype.
        
        The bit 'macPhyConfigStatus(0)' indicates that LLDP agent
        should transmit 'MAC/PHY configuration/status TLV'.
        
        The bit 'powerViaMDI(1)' indicates that LLDP agent should
        transmit 'Power via MDI TLV'.
        
        The bit 'linkAggregation(2)' indicates that LLDP agent should
        transmit 'Link Aggregation TLV'.
        
        The bit 'maxFrameSize(3)' indicates that LLDP agent should
        transmit 'Maximum-frame-size TLV'.
        
        The default value for lldpXdot3PortConfigTLVsTxEnable object
        is an empty set, which means no enumerated values are set.
        
        The value of this object must be restored from non-volatile
        storage after a re-initialization of the management system."
    REFERENCE
        "IEEE 802.1AB-2005 10.2.1.1"
    DEFVAL { '00'h }
    ::= { lldpXdot3PortConfigEntry 1 }

lldpXdot3LocPortTable OBJECT-TYPE
    SYNTAX SEQUENCE OF LldpXdot3LocPortEntry
    ACCESS not-accessible
    STATUS mandatory
    DESCRIPTION
        "This table contains one row per port of Ethernet port
        information (as a part of the LLDP 802.3 organizational
        extension) on the local system known to this agent."
    ::= { lldpXdot3LocalData 1 }

lldpXdot3LocPortEntry OBJECT-TYPE
    SYNTAX LldpXdot3LocPortEntry
    ACCESS not-accessible
    STATUS mandatory
    DESCRIPTION
        "Information about a particular port component."
    INDEX { lldpLocPortNum }
    ::= { lldpXdot3LocPortTable 1 }

LldpXdot3LocPortEntry ::= SEQUENCE {
    lldpXdot3LocPortAutoNegSupported TruthValue,
    lldpXdot3LocPortAutoNegEnabled TruthValue,
    lldpXdot3LocPortAutoNegAdvertisedCap OCTET STRING,
    lldpXdot3LocPortOperMauType INTEGER
    }

lldpXdot3LocPortAutoNegSupported OBJECT-TYPE
    SYNTAX TruthValue
--    Rsyntax INTEGER {
--        true(1),
--        false(2)
--        }
    ACCESS read-only
    STATUS mandatory
    DESCRIPTION
        "The truth value used to indicate whether the given port
        (associated with the local system) supports Auto-negotiation."
    REFERENCE
        "IEEE 802.1AB-2005 G.2.1"
    ::= { lldpXdot3LocPortEntry 1 }

lldpXdot3LocPortAutoNegEnabled OBJECT-TYPE
    SYNTAX TruthValue
--    Rsyntax INTEGER {
--        true(1),
--        false(2)
--        }
    ACCESS read-only
    STATUS mandatory
    DESCRIPTION
        "The truth value used to indicate whether port
        Auto-negotiation is enabled on the given port associated
        with the local system."
    REFERENCE
        "IEEE 802.1AB-2005 G.2.1"
    ::= { lldpXdot3LocPortEntry 2 }

lldpXdot3LocPortAutoNegAdvertisedCap OBJECT-TYPE
    SYNTAX OCTET STRING(SIZE(2))
    ACCESS read-only
    STATUS mandatory
    DESCRIPTION
        "This object contains the value (bitmap) of the
        ifMauAutoNegCapAdvertisedBits object (defined in IETF RFC
        3636) which is associated with the given port on the
        local system."
    REFERENCE
        "IEEE 802.1AB-2005 G.2.2"
    ::= { lldpXdot3LocPortEntry 3 }

lldpXdot3LocPortOperMauType OBJECT-TYPE
    SYNTAX INTEGER(0..2147483647)
    ACCESS read-only
    STATUS mandatory
    DESCRIPTION
        "An integer value that indicates the operational MAU type
        of the given port on the local system.
        
        This object contains the integer value derived from the
        list position of the corresponding dot3MauType as listed 
        in IETF RFC 3636 (or subsequent revisions) and is equal
        to the last number in the respective dot3MauType OID.
        
        For example, if the ifMauType object is dot3MauType1000BaseTHD
        which corresponds to {dot3MauType 29}, the numerical value of
        this field will be 29. For MAU types not listed in RFC 3636
        (or subsequent revisions), the value of this field shall be
        set to zero."
    REFERENCE
        "IEEE 802.1AB-2005 G.2.3"
    ::= { lldpXdot3LocPortEntry 4 }

lldpXdot3LocPowerTable OBJECT-TYPE
    SYNTAX SEQUENCE OF LldpXdot3LocPowerEntry
    ACCESS not-accessible
    STATUS mandatory
    DESCRIPTION
        "This table contains one row per port of power ethernet 
        information (as a part of the LLDP 802.3 organizational
        extension) on the local system known to this agent."
    ::= { lldpXdot3LocalData 2 }

lldpXdot3LocPowerEntry OBJECT-TYPE
    SYNTAX LldpXdot3LocPowerEntry
    ACCESS not-accessible
    STATUS mandatory
    DESCRIPTION
        "Information about a particular port component."
    INDEX { lldpLocPortNum }
    ::= { lldpXdot3LocPowerTable 1 }

LldpXdot3LocPowerEntry ::= SEQUENCE {
    lldpXdot3LocPowerPortClass LldpPowerPortClass,
    lldpXdot3LocPowerMDISupported TruthValue,
    lldpXdot3LocPowerMDIEnabled TruthValue,
    lldpXdot3LocPowerPairControlable TruthValue,
    lldpXdot3LocPowerPairs INTEGER,
    lldpXdot3LocPowerClass INTEGER
    }

lldpXdot3LocPowerPortClass OBJECT-TYPE
    SYNTAX LldpPowerPortClass
--    Rsyntax INTEGER {
--        pClassPSE(1),
--        pClassPD(2)
--        }
    ACCESS read-only
    STATUS mandatory
    DESCRIPTION
        "The value that identifies the port Class of the given port
        associated with the local system."
    REFERENCE
        "IEEE 802.1AB-2005 G.3.1"
    ::= { lldpXdot3LocPowerEntry 1 }

lldpXdot3LocPowerMDISupported OBJECT-TYPE
    SYNTAX TruthValue
--    Rsyntax INTEGER {
--        true(1),
--        false(2)
--        }
    ACCESS read-only
    STATUS mandatory
    DESCRIPTION
        "The truth value used to indicate whether the MDI power is
        supported on the given port associated with the local system."
    REFERENCE
        "IEEE 802.1AB-2005 G.3.1"
    ::= { lldpXdot3LocPowerEntry 2 }

lldpXdot3LocPowerMDIEnabled OBJECT-TYPE
    SYNTAX TruthValue
--    Rsyntax INTEGER {
--        true(1),
--        false(2)
--        }
    ACCESS read-only
    STATUS mandatory
    DESCRIPTION
        "The truth value used to identify whether MDI power is
        enabled on the given port associated with the local system."
    REFERENCE
        "IEEE 802.1AB-2005 G.3.1"
    ::= { lldpXdot3LocPowerEntry 3 }

lldpXdot3LocPowerPairControlable OBJECT-TYPE
    SYNTAX TruthValue
--    Rsyntax INTEGER {
--        true(1),
--        false(2)
--        }
    ACCESS read-only
    STATUS mandatory
    DESCRIPTION
        "The truth value is derived from the value of
        pethPsePortPowerPairsControlAbility object (defined in IETF
        RFC 3621) and is used to indicate whether the pair selection
        can be controlled on the given port associated with the
        local system."
    REFERENCE
        "IEEE 802.1AB-2005 G.3.1"
    ::= { lldpXdot3LocPowerEntry 4 }

lldpXdot3LocPowerPairs OBJECT-TYPE
    SYNTAX INTEGER(1|2)
    ACCESS read-only
    STATUS mandatory
    DESCRIPTION
        "This object contains the value of the pethPsePortPowerPairs
        object (defined in IETF RFC 3621) which is associated with
        the given port on the local system."
    REFERENCE
        "IEEE 802.1AB-2005 G.3.2"
    ::= { lldpXdot3LocPowerEntry 5 }

lldpXdot3LocPowerClass OBJECT-TYPE
    SYNTAX INTEGER(1|2|3|4|5)
    ACCESS read-only
    STATUS mandatory
    DESCRIPTION
        "This object contains the value of the
        pethPsePortPowerClassifications object (defined in IETF
        RFC 3621) which is associated with the given port on the
        local system."
    REFERENCE
        "IEEE 802.1AB-2005 G.3.3"
    ::= { lldpXdot3LocPowerEntry 6 }

lldpXdot3LocLinkAggTable OBJECT-TYPE
    SYNTAX SEQUENCE OF LldpXdot3LocLinkAggEntry
    ACCESS not-accessible
    STATUS mandatory
    DESCRIPTION
        "This table contains one row per port of link aggregation 
        information (as a part of the LLDP 802.3 organizational
        extension) on the local system known to this agent."
    ::= { lldpXdot3LocalData 3 }

lldpXdot3LocLinkAggEntry OBJECT-TYPE
    SYNTAX LldpXdot3LocLinkAggEntry
    ACCESS not-accessible
    STATUS mandatory
    DESCRIPTION
        "Link Aggregation information about a particular port
        component."
    INDEX { lldpLocPortNum }
    ::= { lldpXdot3LocLinkAggTable 1 }

LldpXdot3LocLinkAggEntry ::= SEQUENCE {
    lldpXdot3LocLinkAggStatus LldpLinkAggStatusMap,
    lldpXdot3LocLinkAggPortId INTEGER
    }

lldpXdot3LocLinkAggStatus OBJECT-TYPE
    SYNTAX LldpLinkAggStatusMap
--    Rsyntax OCTET STRING(SIZE(1..2))
--         BITS are:
--           aggCapable(0)
--           aggEnabled(1)
    ACCESS read-only
    STATUS mandatory
    DESCRIPTION
        "The bitmap value contains the link aggregation capabilities
        and the current aggregation status of the link."
    REFERENCE
        "IEEE 802.1AB-2005 G.4.1"
    ::= { lldpXdot3LocLinkAggEntry 1 }

lldpXdot3LocLinkAggPortId OBJECT-TYPE
    SYNTAX INTEGER(0|1..2147483647)
    ACCESS read-only
    STATUS mandatory
    DESCRIPTION
        "This object contains the IEEE 802.3 aggregated port
        identifier, aAggPortID (IEEE 802.3-2002, 30.7.2.1.1),
        derived from the ifNumber of the ifIndex for the port
        component in link aggregation.
        
        If the port is not in link aggregation state and/or it
        does not support link aggregation, this value should be set
        to zero."
    REFERENCE
        "IEEE 802.1AB-2005 G.4.2"
    ::= { lldpXdot3LocLinkAggEntry 2 }

lldpXdot3LocMaxFrameSizeTable OBJECT-TYPE
    SYNTAX SEQUENCE OF LldpXdot3LocMaxFrameSizeEntry
    ACCESS not-accessible
    STATUS mandatory
    DESCRIPTION
        "This table contains one row per port of maximum frame 
        size information (as a part of the LLDP 802.3 organizational
        extension) on the local system known to this agent."
    ::= { lldpXdot3LocalData 4 }

lldpXdot3LocMaxFrameSizeEntry OBJECT-TYPE
    SYNTAX LldpXdot3LocMaxFrameSizeEntry
    ACCESS not-accessible
    STATUS mandatory
    DESCRIPTION
        "Maximum Frame Size information about a particular port
        component."
    INDEX { lldpLocPortNum }
    ::= { lldpXdot3LocMaxFrameSizeTable 1 }

LldpXdot3LocMaxFrameSizeEntry ::= SEQUENCE {
    lldpXdot3LocMaxFrameSize INTEGER
    }

lldpXdot3LocMaxFrameSize OBJECT-TYPE
    SYNTAX INTEGER(0..65535)
    ACCESS read-only
    STATUS mandatory
    DESCRIPTION
        "An integer value indicating the maximum supported frame 
         size in octets on the given port of the local system."
    REFERENCE
        "IEEE 802.1AB-2005 G.5.1"
    ::= { lldpXdot3LocMaxFrameSizeEntry 1 }

lldpXdot3RemPortTable OBJECT-TYPE
    SYNTAX SEQUENCE OF LldpXdot3RemPortEntry
    ACCESS not-accessible
    STATUS mandatory
    DESCRIPTION
        "This table contains Ethernet port information (as a part
        of the LLDP 802.3 organizational extension) of the remote
        system."
    ::= { lldpXdot3RemoteData 1 }

lldpXdot3RemPortEntry OBJECT-TYPE
    SYNTAX LldpXdot3RemPortEntry
    ACCESS not-accessible
    STATUS mandatory
    DESCRIPTION
        "Information about a particular physical network connection."
    INDEX { lldpRemTimeMark, lldpRemLocalPortNum, lldpRemIndex }
    ::= { lldpXdot3RemPortTable 1 }

LldpXdot3RemPortEntry ::= SEQUENCE {
    lldpXdot3RemPortAutoNegSupported TruthValue,
    lldpXdot3RemPortAutoNegEnabled TruthValue,
    lldpXdot3RemPortAutoNegAdvertisedCap OCTET STRING,
    lldpXdot3RemPortOperMauType INTEGER
    }

lldpXdot3RemPortAutoNegSupported OBJECT-TYPE
    SYNTAX TruthValue
--    Rsyntax INTEGER {
--        true(1),
--        false(2)
--        }
    ACCESS read-only
    STATUS mandatory
    DESCRIPTION
        "The truth value used to indicate whether the given port
        (associated with remote system) supports Auto-negotiation."
    REFERENCE
        "IEEE 802.1AB-2005 G.2.1"
    ::= { lldpXdot3RemPortEntry 1 }

lldpXdot3RemPortAutoNegEnabled OBJECT-TYPE
    SYNTAX TruthValue
--    Rsyntax INTEGER {
--        true(1),
--        false(2)
--        }
    ACCESS read-only
    STATUS mandatory
    DESCRIPTION
        "The truth value used to indicate whether port
        Auto-negotiation is enabled on the given port associated
        with the remote system."
    REFERENCE
        "IEEE 802.1AB-2005 G.2.1"
    ::= { lldpXdot3RemPortEntry 2 }

lldpXdot3RemPortAutoNegAdvertisedCap OBJECT-TYPE
    SYNTAX OCTET STRING(SIZE(2))
    ACCESS read-only
    STATUS mandatory
    DESCRIPTION
        "This object contains the value (bitmap) of the
        ifMauAutoNegCapAdvertisedBits object (defined in IETF RFC
        3636) which is associated with the given port on the
        remote system."
    REFERENCE
        "IEEE 802.1AB-2005 G.2.2"
    ::= { lldpXdot3RemPortEntry 3 }

lldpXdot3RemPortOperMauType OBJECT-TYPE
    SYNTAX INTEGER(0..2147483647)
    ACCESS read-only
    STATUS mandatory
    DESCRIPTION
        "An integer value that indicates the operational MAU type
        of the sending device.
        
        This object contains the integer value derived from the
        list position of the corresponding dot3MauType as listed in
        in IETF RFC 3636 (or subsequent revisions) and is equal
        to the last number in the respective dot3MauType OID.
        
        For example, if the ifMauType object is dot3MauType1000BaseTHD
        which corresponds to {dot3MauType 29}, the numerical value of
        this field will be 29. For MAU types not listed in RFC 3636
        (or subsequent revisions), the value of this field shall be
        set to zero."
    REFERENCE
        "IEEE 802.1AB-2005 G.2.3"
    ::= { lldpXdot3RemPortEntry 4 }

lldpXdot3RemPowerTable OBJECT-TYPE
    SYNTAX SEQUENCE OF LldpXdot3RemPowerEntry
    ACCESS not-accessible
    STATUS mandatory
    DESCRIPTION
        "This table contains Ethernet power information (as a part
        of the LLDP 802.3 organizational extension) of the remote
        system."
    ::= { lldpXdot3RemoteData 2 }

lldpXdot3RemPowerEntry OBJECT-TYPE
    SYNTAX LldpXdot3RemPowerEntry
    ACCESS not-accessible
    STATUS mandatory
    DESCRIPTION
        "Information about a particular physical network connection."
    INDEX { lldpRemTimeMark, lldpRemLocalPortNum, lldpRemIndex }
    ::= { lldpXdot3RemPowerTable 1 }

LldpXdot3RemPowerEntry ::= SEQUENCE {
    lldpXdot3RemPowerPortClass LldpPowerPortClass,
    lldpXdot3RemPowerMDISupported TruthValue,
    lldpXdot3RemPowerMDIEnabled TruthValue,
    lldpXdot3RemPowerPairControlable TruthValue,
    lldpXdot3RemPowerPairs INTEGER,
    lldpXdot3RemPowerClass INTEGER
    }

lldpXdot3RemPowerPortClass OBJECT-TYPE
    SYNTAX LldpPowerPortClass
--    Rsyntax INTEGER {
--        pClassPSE(1),
--        pClassPD(2)
--        }
    ACCESS read-only
    STATUS mandatory
    DESCRIPTION
        "The value that identifies the port Class of the given port
        associated with the remote system."
    REFERENCE
        "IEEE 802.1AB-2005 G.3.1"
    ::= { lldpXdot3RemPowerEntry 1 }

lldpXdot3RemPowerMDISupported OBJECT-TYPE
    SYNTAX TruthValue
--    Rsyntax INTEGER {
--        true(1),
--        false(2)
--        }
    ACCESS read-only
    STATUS mandatory
    DESCRIPTION
        "The truth value used to indicate whether the MDI power
        is supported on the given port associated with the remote
        system."
    REFERENCE
        "IEEE 802.1AB-2005 G.3.1"
    ::= { lldpXdot3RemPowerEntry 2 }

lldpXdot3RemPowerMDIEnabled OBJECT-TYPE
    SYNTAX TruthValue
--    Rsyntax INTEGER {
--        true(1),
--        false(2)
--        }
    ACCESS read-only
    STATUS mandatory
    DESCRIPTION
        "The truth value used to identify whether MDI power is
        enabled on the given port associated with the remote system."
    REFERENCE
        "IEEE 802.1AB-2005 G.3.1"
    ::= { lldpXdot3RemPowerEntry 3 }

lldpXdot3RemPowerPairControlable OBJECT-TYPE
    SYNTAX TruthValue
--    Rsyntax INTEGER {
--        true(1),
--        false(2)
--        }
    ACCESS read-only
    STATUS mandatory
    DESCRIPTION
        "The truth value is derived from the value of
        pethPsePortPowerPairsControlAbility object (defined in IETF
        RFC 3621) and is used to indicate whether the pair selection
        can be controlled on the given port associated with the
        remote system."
    REFERENCE
        "IEEE 802.1AB-2005 G.3.1"
    ::= { lldpXdot3RemPowerEntry 4 }

lldpXdot3RemPowerPairs OBJECT-TYPE
    SYNTAX INTEGER(1|2)
    ACCESS read-only
    STATUS mandatory
    DESCRIPTION
        "This object contains the value of the pethPsePortPowerPairs
        object (defined in IETF RFC 3621) which is associated with
        the given port on the remote system."
    REFERENCE
        "IEEE 802.1AB-2005 G.3.2"
    ::= { lldpXdot3RemPowerEntry 5 }

lldpXdot3RemPowerClass OBJECT-TYPE
    SYNTAX INTEGER(1|2|3|4|5)
    ACCESS read-only
    STATUS mandatory
    DESCRIPTION
        "This object contains the value of the
        pethPsePortPowerClassifications object (defined in IETF
        RFC 3621) which is associated with the given port on the
        remote system."
    REFERENCE
        "IEEE 802.1AB-2005 G.3.3"
    ::= { lldpXdot3RemPowerEntry 6 }

lldpXdot3RemLinkAggTable OBJECT-TYPE
    SYNTAX SEQUENCE OF LldpXdot3RemLinkAggEntry
    ACCESS not-accessible
    STATUS mandatory
    DESCRIPTION
        "This table contains port link aggregation information
        (as a part of the LLDP 802.3 organizational extension)
        of the remote system."
    ::= { lldpXdot3RemoteData 3 }

lldpXdot3RemLinkAggEntry OBJECT-TYPE
    SYNTAX LldpXdot3RemLinkAggEntry
    ACCESS not-accessible
    STATUS mandatory
    DESCRIPTION
        "Link Aggregation information about remote system's port
        component."
    INDEX { lldpRemTimeMark, lldpRemLocalPortNum, lldpRemIndex }
    ::= { lldpXdot3RemLinkAggTable 1 }

LldpXdot3RemLinkAggEntry ::= SEQUENCE {
    lldpXdot3RemLinkAggStatus LldpLinkAggStatusMap,
    lldpXdot3RemLinkAggPortId INTEGER
    }

lldpXdot3RemLinkAggStatus OBJECT-TYPE
    SYNTAX LldpLinkAggStatusMap
--    Rsyntax OCTET STRING(SIZE(1..2))
--         BITS are:
--           aggCapable(0)
--           aggEnabled(1)
    ACCESS read-only
    STATUS mandatory
    DESCRIPTION
        "The bitmap value contains the link aggregation capabilities
        and the current aggregation status of the link."
    REFERENCE
        "IEEE 802.1AB-2005 G.4.1"
    ::= { lldpXdot3RemLinkAggEntry 1 }

lldpXdot3RemLinkAggPortId OBJECT-TYPE
    SYNTAX INTEGER(0|1..2147483647)
    ACCESS read-only
    STATUS mandatory
    DESCRIPTION
        "This object contains the IEEE 802.3 aggregated port
        identifier, aAggPortID (IEEE 802.3-2002, 30.7.2.1.1),
        derived from the ifNumber of the ifIndex for the port
        component associated with the remote system.
        
        If the remote port is not in link aggregation state and/or
        it does not support link aggregation, this value should be
        zero."
    REFERENCE
        "IEEE 802.1AB-2005 G.4.2"
    ::= { lldpXdot3RemLinkAggEntry 2 }

lldpXdot3RemMaxFrameSizeTable OBJECT-TYPE
    SYNTAX SEQUENCE OF LldpXdot3RemMaxFrameSizeEntry
    ACCESS not-accessible
    STATUS mandatory
    DESCRIPTION
        "This table contains one row per port of maximum frame 
        size information (as a part of the LLDP 802.3 organizational
        extension) of the remote system."
    ::= { lldpXdot3RemoteData 4 }

lldpXdot3RemMaxFrameSizeEntry OBJECT-TYPE
    SYNTAX LldpXdot3RemMaxFrameSizeEntry
    ACCESS not-accessible
    STATUS mandatory
    DESCRIPTION
        "Maximum Frame Size information about a particular port
        component."
    INDEX { lldpRemTimeMark, lldpRemLocalPortNum, lldpRemIndex }
    ::= { lldpXdot3RemMaxFrameSizeTable 1 }

LldpXdot3RemMaxFrameSizeEntry ::= SEQUENCE {
    lldpXdot3RemMaxFrameSize INTEGER
    }

lldpXdot3RemMaxFrameSize OBJECT-TYPE
    SYNTAX INTEGER(0..65535)
    ACCESS read-only
    STATUS mandatory
    DESCRIPTION
        "An integer value indicating the maximum supported frame 
         size in octets on the port component associated with the 
         remote system."
    REFERENCE
        "IEEE 802.1AB-2005 G.5.1"
    ::= { lldpXdot3RemMaxFrameSizeEntry 1 }

lldpXdot3ConfigGroup OBJECT IDENTIFIER ::= { lldpXdot3Groups 1 }
-- OBJECT-GROUP
--  Status
--    mandatory
--  Descr
--    The collection of objects which are used to configure the
--    LLDP 802.3 organizational extension implementation behavior.
--    
--    This group is mandatory for agents which implement the 
--    LLDP 802.3 organizational extension.
--  objects
--    lldpXdot3PortConfigTLVsTxEnable

lldpXdot3LocSysGroup OBJECT IDENTIFIER ::= { lldpXdot3Groups 2 }
-- OBJECT-GROUP
--  Status
--    mandatory
--  Descr
--    The collection of objects which are used to represent LLDP
--    802.3 organizational extension Local Device Information.
--    
--    This group is mandatory for agents which implement the 
--    LLDP 802.3 organizational extension in the TX mode.
--  objects
--    lldpXdot3LocPortAutoNegSupported, 
--    lldpXdot3LocPortAutoNegEnabled, 
--    lldpXdot3LocPortAutoNegAdvertisedCap, 
--    lldpXdot3LocPortOperMauType, lldpXdot3LocPowerPortClass, 
--    lldpXdot3LocPowerMDISupported, lldpXdot3LocPowerMDIEnabled, 
--    lldpXdot3LocPowerPairControlable, lldpXdot3LocPowerPairs, 
--    lldpXdot3LocPowerClass, lldpXdot3LocLinkAggStatus, 
--    lldpXdot3LocLinkAggPortId, lldpXdot3LocMaxFrameSize

lldpXdot3RemSysGroup OBJECT IDENTIFIER ::= { lldpXdot3Groups 3 }
-- OBJECT-GROUP
--  Status
--    mandatory
--  Descr
--    The collection of objects which are used to represent LLDP
--    802.3 organizational extension Local Device Information.
--    
--    This group is mandatory for agents which implement the 
--    LLDP 802.3 organizational extension in the RX mode.
--  objects
--    lldpXdot3RemPortAutoNegSupported, 
--    lldpXdot3RemPortAutoNegEnabled, 
--    lldpXdot3RemPortAutoNegAdvertisedCap, 
--    lldpXdot3RemPortOperMauType, lldpXdot3RemPowerPortClass, 
--    lldpXdot3RemPowerMDISupported, lldpXdot3RemPowerMDIEnabled, 
--    lldpXdot3RemPowerPairControlable, lldpXdot3RemPowerPairs, 
--    lldpXdot3RemPowerClass, lldpXdot3RemLinkAggStatus, 
--    lldpXdot3RemLinkAggPortId, lldpXdot3RemMaxFrameSize

lldpXdot3Compliance OBJECT IDENTIFIER ::= { lldpXdot3Compliances 1 }
-- MODULE-COMPLIANCE
--  Status
--    mandatory
--  Descr
--    The compliance statement for SNMP entities which implement
--    the LLDP 802.3 organizational extension MIB.
--  Module
--    >>current<<
--   MandGroup
--    lldpXdot3ConfigGroup
--   MandGroup
--    lldpXdot3LocSysGroup
--   MandGroup
--    lldpXdot3RemSysGroup


END
