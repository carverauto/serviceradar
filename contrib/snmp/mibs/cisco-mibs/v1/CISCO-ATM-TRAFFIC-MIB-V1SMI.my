-- MIB file created 25-Mar-2003 15:57:34, by
--   SMICng version 2.2.11-beta(PRO)(Solaris), January 20, 2001. Enterprise key cisco.com

CISCO-ATM-TRAFFIC-MIB DEFINITIONS ::= BEGIN

-- From file: "CISCO-ATM-TRAFFIC-MIB.my"
-- Compile options "4 7 F H N W 03 06 0B 0G 0N 0T"

IMPORTS
    atmTrafficDescrParamIndex
            FROM ATM-MIB
    ciscoExperiment
            FROM CISCO-SMI
    SnmpAdminString
            FROM SNMP-FRAMEWORK-MIB
    OBJECT-TYPE
            FROM RFC-1212;

ciscoAtmTrafficExtMIB OBJECT IDENTIFIER ::= { ciscoExperiment 11 }
-- MODULE-IDENTITY
--  LastUpdated
--    200208260000Z
--  OrgName
--    Cisco System Inc.
--  ContactInfo
--    Cisco Systems
--     Customer Service
--    
--     Postal: 170 W. Tasman Drive
--             San Jose, CA  95134
--             USA
--    
--     Tel: +1 800 553-NETS
--    
--     E-mail: cs-atm@cisco.com
--  Descr
--    This MIB module is an extension to traffic OIDs
--     and variables defined in rfc1695.
--  RevDate
--    200208260000Z
--  RevDescr
--    Deprecated atmNoClpNoScrCdvt as a similar object
--     atmNoClpNoScrCdvt defined in RFC-2514 can be used instead.
--  RevDate
--    200111010000Z
--  RevDescr
--    Added an object to identify the traffic descriptor by a 
--     name in human readable form.
--  RevDate
--    9705290000Z
--  RevDescr
--    Added traffic for types dual-leaky bucket and mcr support
--     made possible on the LS1010 by the Feature Card Per Flow
--     Queueing support for per-VC queueing hardware structures.

ciscoAtmTrafficExtMIBObjects OBJECT IDENTIFIER ::= { ciscoAtmTrafficExtMIB 1 }
ciscoAtmTrafficTypeExt OBJECT IDENTIFIER ::= { ciscoAtmTrafficExtMIBObjects 1 }
ciscoAtmTrafficTableExt OBJECT IDENTIFIER ::= { ciscoAtmTrafficExtMIBObjects 2 }
ciscoAtmTrafficExtMIBConformance OBJECT IDENTIFIER ::= { ciscoAtmTrafficExtMIB 3 }
ciscoAtmTrafficExtMIBCompliances OBJECT IDENTIFIER ::= { ciscoAtmTrafficExtMIBConformance 1 }
ciscoAtmTrafficExtMIBGroups OBJECT IDENTIFIER ::= { ciscoAtmTrafficExtMIBConformance 2 }

atmNoClpNoScrCdvt OBJECT IDENTIFIER ::= { ciscoAtmTrafficTypeExt 1 }
-- OBJECT-IDENTITY
--  Status
--    deprecated
--  Descr
--    Specifies peak cell rate for CLP, and
--     cell delay variation tolerance:
--     Parameter 1: CLP=0+1 peak cell rate in
--                  cells per second
--     Parameter 2: CDVT in cell-times
--     Parameter 3: not used
--     Parameter 4: not used
--     Parameter 5: not used.
--     This traffic descriptor is for cbr, abr
--     or ubr service categories, desiring to
--     specify the cdvt as well as pcr.

atmClpScrMbsCdvt OBJECT IDENTIFIER ::= { ciscoAtmTrafficTypeExt 2 }
-- OBJECT-IDENTITY
--  Status
--    mandatory
--  Descr
--    This traffic descriptor is for Peak
--     Cell Rate (PCR), Sustained Cell Rate (SCR),
--     Maximum Burst Size applied to SCR,
--     and Cell Delay Variation Tolerance
--     applied to PCR.
--     The use of the parameter vector for this type:
--     Parameter 1: CLP=0+1 peak cell rate in
--                  cells per second
--     Parameter 2: CLP=0 sustained cell rate in
--                  cells per second.
--     Parameter 3: maximum burst size in cells
--     Parameter 4: CDVT in cell-times
--     Parameter 5: not used.

atmNoClpScrMbsCdvt OBJECT IDENTIFIER ::= { ciscoAtmTrafficTypeExt 3 }
-- OBJECT-IDENTITY
--  Status
--    mandatory
--  Descr
--    This traffic descriptor is for Peak
--     Cell Rate (PCR), Sustained Cell Rate (SCR),
--     Maximum Burst Size applied to SCR,
--     and Cell Delay Variation Tolerance
--     applied to PCR.
--     The use of the parameter vector for this type:
--     Parameter 1: CLP=0+1 peak cell rate in
--                  cells per second
--     Parameter 2: CLP=0+1 sustained cell rate in
--                  cells per second.
--     Parameter 3: maximum burst size in cells
--     Parameter 4: CDVT in cell-times
--     Parameter 5: not used.

atmNoClpMcr OBJECT IDENTIFIER ::= { ciscoAtmTrafficTypeExt 4 }
-- OBJECT-IDENTITY
--  Status
--    mandatory
--  Descr
--    This traffic descriptor is for Peak
--     Cell Rate (PCR) and Minimum Cell Rate 
--     (MCR).
--     The use of the parameter vector for this type:
--     Parameter 1: CLP=0+1 peak cell rate in
--                  cells per second
--     Parameter 2: CLP=0+1 minimum cell rate in
--                  cells per second.
--     Parameter 3: not used.
--     Parameter 4: not used.
--     Parameter 5: not used.

atmNoClpMcrCdvt OBJECT IDENTIFIER ::= { ciscoAtmTrafficTypeExt 5 }
-- OBJECT-IDENTITY
--  Status
--    mandatory
--  Descr
--    This traffic descriptor is for Peak
--     Cell Rate (PCR), Minimum Cell Rate (MCR),
--     and Cell Delay Variation Tolerance
--     applied to PCR.
--     The use of the parameter vector for this type:
--     Parameter 1: CLP=0+1 peak cell rate in
--                  cells per second
--     Parameter 2: CDVT in cell-times
--     Parameter 3: CLP=0+1 minimum cell rate in
--                  cells per second.
--     Parameter 4: not used.
--     Parameter 5: not used.

atmTrafficDescrParamExtTable OBJECT-TYPE
    SYNTAX SEQUENCE OF AtmTrafficDescrParamExtEntry
    ACCESS not-accessible
    STATUS mandatory
    DESCRIPTION
        "Provide additional information specifying traffic parameters
         for a VC/VP."
    ::= { ciscoAtmTrafficTableExt 1 }

atmTrafficDescrParamExtEntry OBJECT-TYPE
    SYNTAX AtmTrafficDescrParamExtEntry
    ACCESS not-accessible
    STATUS mandatory
    DESCRIPTION
        " An entry in the Traffic Parameter Descriptor extension
          table."
    INDEX { atmTrafficDescrParamIndex }
-- Augments atmTrafficDescrParamEntry FROM ATM-MIB
    ::= { atmTrafficDescrParamExtTable 1 }

AtmTrafficDescrParamExtEntry ::= SEQUENCE {
    atmTrafficExplicitServCategory INTEGER,
    atmTrafficDerivedServCategory INTEGER,
    atmTrafficDescriptorName SnmpAdminString
    }

atmTrafficExplicitServCategory OBJECT-TYPE
    SYNTAX INTEGER {
        cbr(1),
        vbrRt(2),
        vbrNrt(3),
        abr(4),
        ubr(5),
        notDef(6)
        }
    ACCESS read-write
    STATUS mandatory
    DESCRIPTION
        "This objects indicates the Service Category
         specified by the Traffic Descriptor.
         If it is defined, the setting of this
         object determines the Service Category used
         for the connection. This then limits the
         possible Traffic Descriptor Types as follows:
        
         Explicit
         Service
         Category       Type may only be
         -----------------------------------------
         cbr            atmNoClpNoScr.
                        atmClpNoTaggingNoScr
                        atmClpTaggingNoScr
                        atmNoClpNoScrCdvt
        
         abr/ubr        atmNoTrafficDescriptor
                        atmNoClpNoScr.
                        atmNoClpNoScrCdvt
                        atmNoClpMcr -- ubr+/abr
                        atmNoClpMcrCdvt -- ubr+/abr
        
         vbr            atmNoClpScr
                        atmClpNoTaggingScr
                        atmClpTaggingScr
                        atmClpScrMbsCdvt
                        atmNoClpScrMbsCdvt
         -----------------------------------------
         If the settings of Service Category and Traffic
         Descriptor Type are not compatible, the row can
         not be made active."
    DEFVAL { notDef }
    ::= { atmTrafficDescrParamExtEntry 1 }

atmTrafficDerivedServCategory OBJECT-TYPE
    SYNTAX INTEGER {
        cbr(1),
        vbrRt(2),
        vbrNrt(3),
        abr(4),
        ubr(5)
        }
    ACCESS read-only
    STATUS mandatory
    DESCRIPTION
        "This object indicates the Service Category
         derived from the Traffic Descriptor. If the
         object atmTrafficExplicitServCategory has
         a defined value, then this object mirrors
         that value. If Explicit Service Category
         has the value notDef, then this object
         reflects the Service Category derived from
         the Traffic Descriptor Type as follows:
        
         Traffic Descriptor       Service
             Type                 Category
         -----------------------------------------
         atmNoTrafficDescriptor   ubr
        
         atmNoClpMcr              abr
         atmNoClpMcrCdvt          abr
        
         atmNoClpNoScr      --|
         atmClpNoTaggingNoScr |-- cbr
         atmClpTaggingNoScr   |
         atmNoClpNoScrCdvt  --|
        
         atmNoClpScr        --|
         atmClpNoTaggingScr   |-- vbr-rt
         atmClpScrMbsCdvt     |
         atmNoClpScrMbsCdvt   |
         atmClpTaggingScr   --|
         -----------------------------------------"
    ::= { atmTrafficDescrParamExtEntry 2 }

atmTrafficDescriptorName OBJECT-TYPE
    SYNTAX SnmpAdminString
--    Rsyntax OCTET STRING(SIZE(0..255))
    ACCESS read-write
    STATUS mandatory
    DESCRIPTION
        "A human readable string that contains the unique name
         of this Traffic Descriptor. 
         This object will return a zero-length string if value is
         not set."
    DEFVAL { "" }
    ::= { atmTrafficDescrParamExtEntry 3 }

ciscoAtmTrafficTableExtMIBGroup OBJECT IDENTIFIER ::= { ciscoAtmTrafficExtMIBGroups 1 }
-- OBJECT-GROUP
--  Status
--    mandatory
--  Descr
--    A collection of objects which provide extensions to  the
--     ATM Traffic Parameter Descriptor Table.
--  objects
--    atmTrafficExplicitServCategory, atmTrafficDerivedServCategory

ciscoAtmTrafficNmsGroup OBJECT IDENTIFIER ::= { ciscoAtmTrafficExtMIBGroups 2 }
-- OBJECT-GROUP
--  Status
--    mandatory
--  Descr
--    A collection of objects which provide additional
--     information for a management system.
--  objects
--    atmTrafficDescriptorName

ciscoAtmTrafficExtMIBCompliance OBJECT IDENTIFIER ::= { ciscoAtmTrafficExtMIBCompliances 1 }
-- MODULE-COMPLIANCE
--  Status
--    deprecated
--  Descr
--    The compliance statement for the Cisco ATM Traffic Extension MIB.
--  Module
--    >>current<<
--   MandGroup
--    ciscoAtmTrafficTableExtMIBGroup

ciscoAtmTrafficExtMIBComplianceRev1 OBJECT IDENTIFIER ::= { ciscoAtmTrafficExtMIBCompliances 2 }
-- MODULE-COMPLIANCE
--  Status
--    mandatory
--  Descr
--    The compliance statement for the Cisco ATM Traffic Extension MIB.
--  Module
--    >>current<<
--   MandGroup
--    ciscoAtmTrafficTableExtMIBGroup
--   OptGroup
--    ciscoAtmTrafficNmsGroup


END
