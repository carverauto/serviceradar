-- MIB file created 20-Sep-2009 18:33:22, by
--   SMICng version 2.2.11-beta(PRO)(Solaris), January 20, 2001. Enterprise key cisco.com

CISCO-NOTIFICATION-CONTROL-MIB DEFINITIONS ::= BEGIN

-- From file: "CISCO-NOTIFICATION-CONTROL-MIB.my"
-- Compile options "4 7 F H N O W 03 06 0B 0G 0N 0T"

IMPORTS
    AutonomousType, StorageType, RowStatus
            FROM SNMPv2-TC-v1
    SnmpAdminString
            FROM SNMP-FRAMEWORK-MIB
    ciscoMgmt
            FROM CISCO-SMI
    Gauge
            FROM RFC1155-SMI
    OBJECT-TYPE
            FROM RFC-1212;

ciscoNotificationControlMIB OBJECT IDENTIFIER ::= { ciscoMgmt 586 }
-- MODULE-IDENTITY
--  LastUpdated
--    200909200000Z
--  OrgName
--    Cisco Systems, Inc.
--  ContactInfo
--    Cisco Systems
--    Customer Service
--    
--    Postal: 170 W Tasman Drive
--    San Jose, CA  95134
--    USA
--    Tel: +1 800 553-NETS 
--    
--    E-mail: cs-wanatm@cisco.com
--  Descr
--    This MIB provides network management support to regulate
--    the transmission of notifications generated by a  
--    system providing networking services.  The system could  
--    be generating several notifications pertaining to  
--    various events.  Allowing every notification to be  
--    transmitted out may lead to the network being flooded  
--    with an excess of network management traffic.  Hence it  
--    is required to regulate the generation and transmission  
--    of notifications.  
--    
--                    GLOSSARY  
--    
--    Network Management Station (NMS)  
--    
--    An external network entity that monitors and manages the
--    network.
--  RevDate
--    200909200000Z
--  RevDescr
--    Added new object cNotifCtrlDescr to cNotifCtrlTable.Deprecated
--    cNotifCtrlMIBCompliance and added cNotifCtrlMIBComplianceRev1.
--  RevDate
--    200609270000Z
--  RevDescr
--    Initial version of this MIB module.

cNotifCtrlMIBObjects OBJECT IDENTIFIER ::= { ciscoNotificationControlMIB 1 }
cNotifCtrlConfig OBJECT IDENTIFIER ::= { cNotifCtrlMIBObjects 1 }
cNotifCtrlMIBConformance OBJECT IDENTIFIER ::= { ciscoNotificationControlMIB 2 }
cNotifCtrlMIBCompliances OBJECT IDENTIFIER ::= { cNotifCtrlMIBConformance 1 }
cNotifCtrlMIBGroups OBJECT IDENTIFIER ::= { cNotifCtrlMIBConformance 2 }

cNotifCtrlMode OBJECT-TYPE
    SYNTAX INTEGER {
        noControl(1),
        forcedControl(2),
        automaticControl(3)
        }
    ACCESS read-write
    STATUS mandatory
    DESCRIPTION
        "This object represents the notification control mode.
        The semantics are as follows. 
        
        noControl - There is no control on notifications. 
        
        forcedControl - All notifications configured through
        cNotifCtrlTable are filtered at all times.
        
        automaticControl - Notifications configured through
        cNotifCtrlTable are filtered only when number of 
        notifications generated exceeds the value represented 
        by cNotifCtrlThreshold in the given time interval 
        represented by cNotifCtrlSamplingInterval."
    DEFVAL { noControl }
    ::= { cNotifCtrlConfig 1 }

cNotifCtrlCurrentState OBJECT-TYPE
    SYNTAX INTEGER {
        controlOn(1),
        controlOff(2)
        }
    ACCESS read-only
    STATUS mandatory
    DESCRIPTION
        "This object represents the current state of notification
        control. The semantics are as follows.
        
        controlOn - This indicates that notifications configured in 
        cNotifCtrlTable are currently getting filtered on the
        system.  This object will always be 'controlOn', when 
        cNotifCtrlMode is 'forcedControl'.
        
        controlOff - This indicates that notifications configured 
        in cNotifCtrlTable are currently not being filtered on the
        system.  This object will always be 'controlOff', when 
        cNotifCtrlMode is 'noControl'. 
        
        If cNotifCtrlMode is set to 'automaticControl', the agent 
        sets this object to 'controlOn', when number of 
        notifications generated by  the system exceeds the value 
        represented by cNotifCtrlThreshold in the time interval 
        represented by cNotifCtrlSamplingInterval.  The agent sets 
        this object to 'controlOff', when the number of 
        notifications generated by the system falls below the value 
        represented by cNotifCtrlThreshold in the time interval 
        represented by  cNotifCtrlSamplingInterval."
    DEFVAL { controlOff }
    ::= { cNotifCtrlConfig 2 }

cNotifCtrlThreshold OBJECT-TYPE
    SYNTAX Gauge(1..4294967295)
--  Units
--    notifications
    ACCESS read-write
    STATUS mandatory
    DESCRIPTION
        "This object represents the threshold value to initiate
        controlling of notifications.  Notifications will be 
        controlled when the number of notifications generated 
        by this system exceeds the threshold represented by 
        this object in the sampling interval represented by
        cNotifCtrlSamplingInterval.  The configured value takes
        effect only when cNotifCtrlMode is set to 
        'automaticControl'."
    DEFVAL { 50 }
    ::= { cNotifCtrlConfig 3 }

cNotifCtrlSamplingInterval OBJECT-TYPE
    SYNTAX Gauge(1..4294967295)
--  Units
--    minutes
    ACCESS read-write
    STATUS mandatory
    DESCRIPTION
        "This object represents the sampling interval in which the
        notification generation rate will be monitored.  The 
        configured value takes effect only when cNotifCtrlMode is 
        set to 'automaticControl'."
    DEFVAL { 5 }
    ::= { cNotifCtrlConfig 4 }

cNotifCtrlTableSize OBJECT-TYPE
    SYNTAX Gauge(1..4294967295)
    ACCESS read-write
    STATUS mandatory
    DESCRIPTION
        "This object represents maximum number of rows possible in
        cNotifCtrlTable."
    DEFVAL { 200 }
    ::= { cNotifCtrlConfig 5 }

cNotifCtrlIndexNext OBJECT-TYPE
    SYNTAX Gauge(0..4294967295)
    ACCESS read-only
    STATUS mandatory
    DESCRIPTION
        "This object represents the next available free index in
        the cNotifCtrlTable.  This number can be used as an index 
        to create a valid entry into cNotifCtrlTable. 
        
        A value of 0 indicates that no free indices are available to
        create entries in cNotifCtrlTable."
    ::= { cNotifCtrlConfig 6 }

cNotifCtrlTable OBJECT-TYPE
    SYNTAX SEQUENCE OF CNotifCtrlEntry
    ACCESS not-accessible
    STATUS mandatory
    DESCRIPTION
        "This table represents the notifications to be controlled.
        To control a particular notification, user creates a row
        uniquely indexed by cNotifCtrlIndex using the
        cNotifCtrlRowStatus object.  The storage type of each row
        is indicated by  cNotifCtrlStorageType.
        
        The agent filters out the notification depending on the 
        current value of cNotifCtrlMode.  The agent also indicates 
        the current state of notification control through 
        cNotifCtrlCurrentState.
        
        This notification control mechanism is illustrated as follows.
        
        cNotifCtrlTable contains the list of notifications, that
        need to be controlled from the agent when 
        cNotifCtrlCurrentState is 'controlOn'.
        
        When cNotifCtrlMode is set to 'automaticControl', a timer is 
        started for the time interval represented by 
        cNotifCtrlSamplingInterval(eg: 10 mins) to monitor the number 
        of notifications being generated by the agent.  If the number
        of notifications generated exceeds the value represented by
        cNotifCtrlThreshold (eg: 100) before the timer expires, all
        notifications mentioned in cNotifCtrlTable are throttled.
        
        When the timer expires, it is restarted and the counter used
        to track the number of notifications generated is initialized to
        zero.  This controlling of notifications will continue until
        the number of notifications generated falls below the threshold
        in the given interval.
        
        When cNotifCtrlMode is set to 'forcedControl', all the
        notifications mentioned in cNotifCtrlTable are always
        throttled, irrespective of the values of
        threshold and sampling interval."
    ::= { cNotifCtrlConfig 7 }

cNotifCtrlEntry OBJECT-TYPE
    SYNTAX CNotifCtrlEntry
    ACCESS not-accessible
    STATUS mandatory
    DESCRIPTION
        "A conceptual row in cNotifCtrlTable and corresponds
        to the notification to be filtered."
    INDEX { cNotifCtrlIndex }
    ::= { cNotifCtrlTable 1 }

CNotifCtrlEntry ::= SEQUENCE {
    cNotifCtrlIndex Gauge,
    cNotifCtrlOID AutonomousType,
    cNotifCtrlStorageType StorageType,
    cNotifCtrlRowStatus RowStatus,
    cNotifCtrlDescr SnmpAdminString
    }

cNotifCtrlIndex OBJECT-TYPE
    SYNTAX Gauge(1..4294967295)
    ACCESS not-accessible
    STATUS mandatory
    DESCRIPTION
        "This object uniquely identifies an entry in cNotifCtrlTable."
    ::= { cNotifCtrlEntry 1 }

cNotifCtrlOID OBJECT-TYPE
    SYNTAX AutonomousType
--    Rsyntax OBJECT IDENTIFIER
    ACCESS read-write
    STATUS mandatory
    DESCRIPTION
        "This object represents the notification to be controlled."
    ::= { cNotifCtrlEntry 2 }

cNotifCtrlStorageType OBJECT-TYPE
    SYNTAX StorageType
--    Rsyntax INTEGER {
--        other(1),
--        volatile(2),
--        nonVolatile(3),
--        permanent(4),
--        readOnly(5)
--        }
    ACCESS read-write
    STATUS mandatory
    DESCRIPTION
        "This object represents the storage type for this
        conceptual row in cNotifCtrlTable. 
        
        A value of 'volatile' indicates that the entry won't be 
        persistent across system reloads.  A value of 'nonVolatile'
        indicates that the entry will be persistent across 
        system reloads."
    DEFVAL { nonVolatile }
    ::= { cNotifCtrlEntry 3 }

cNotifCtrlRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object represents the status of a conceptual row.
        
        Following objects are mandatory while creating an entry
        in this table: 
        
        cNotifCtrlOID 
        
        Entries can't be modified after the agent sets
        cNotifCtrlRowStatus to 'active'."
    ::= { cNotifCtrlEntry 4 }

cNotifCtrlDescr OBJECT-TYPE
    SYNTAX SnmpAdminString(SIZE(0..255))
--    Rsyntax OCTET STRING(SIZE(0..255))
    ACCESS read-write
    STATUS mandatory
    DESCRIPTION
        "This object specifies a human readable string which has more
        descriptive information about the notification."
    ::= { cNotifCtrlEntry 5 }

cNotifCtrlConfigGroup OBJECT IDENTIFIER ::= { cNotifCtrlMIBGroups 1 }
-- OBJECT-GROUP
--  Status
--    mandatory
--  Descr
--    This collection of objects represents the configuration,
--    monitoring and status parameters related to notification
--    control.
--  objects
--    cNotifCtrlMode, cNotifCtrlCurrentState, cNotifCtrlThreshold, 
--    cNotifCtrlSamplingInterval, cNotifCtrlTableSize, 
--    cNotifCtrlIndexNext, cNotifCtrlOID, cNotifCtrlStorageType, 
--    cNotifCtrlRowStatus

cNotifCtrlConfigExtGroup OBJECT IDENTIFIER ::= { cNotifCtrlMIBGroups 2 }
-- OBJECT-GROUP
--  Status
--    mandatory
--  Descr
--    The extended set of notification control variable(s).
--  objects
--    cNotifCtrlDescr

cNotifCtrlMIBCompliance OBJECT IDENTIFIER ::= { cNotifCtrlMIBCompliances 1 }
-- MODULE-COMPLIANCE
--  Status
--    deprecated
--  Descr
--    The compliance statement for the SNMP entities that
--    implement the ciscoNotifactionControlMIB module.
--  Module
--    >>current<<
--   MandGroup
--    cNotifCtrlConfigGroup
--   ObjVar
--    cNotifCtrlStorageType
--   ObjVar
--    cNotifCtrlRowStatus

cNotifCtrlMIBComplianceRev1 OBJECT IDENTIFIER ::= { cNotifCtrlMIBCompliances 2 }
-- MODULE-COMPLIANCE
--  Status
--    mandatory
--  Descr
--    The compliance statement for the SNMP entities that
--    implement the ciscoNotifactionControlMIB module.
--  Module
--    >>current<<
--   MandGroup
--    cNotifCtrlConfigGroup
--   OptGroup
--    cNotifCtrlConfigExtGroup
--   ObjVar
--    cNotifCtrlStorageType
--   ObjVar
--    cNotifCtrlRowStatus
--   ObjVar
--    cNotifCtrlDescr


END
