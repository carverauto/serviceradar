-- MIB created 9/05/100 11:41:19, by
--   SMIC (the next generation) version 1.6.29, November 22, 1994.

CISCO-VOICE-ENABLED-LINK-MIB DEFINITIONS ::= BEGIN

-- From file: "CISCO-VOICE-ENABLED-LINK-MIB.my"

IMPORTS
    OBJECT-TYPE
            FROM RFC-1212
    DisplayString, MacAddress
            FROM SNMPv2-TC-v1
    ciscoExperiment
            FROM CISCO-SMI;

ciscoVoiceEnabledLinkMIB OBJECT IDENTIFIER ::= { ciscoExperiment 53 }
-- MODULE-IDENTITY
--  LastUpdated
--    9905070000Z
--  OrgName
--    Cisco Systems, Inc.
--  ContactInfo
--           Cisco Systems
--            Customer Service
--    
--    Postal: 170 W. Tasman Drive
--            San Jose, CA  95134
--            USA
--    
--    Tel: +1 800 553-NETS
--    
--    E-mail: cs-voice@cisco.com
--  Descr
--    This MIB module provides information about Voice Enabled
--     ATM and Frame Relay Links used by the Cisco Switched
--     voice protocol.
--     The Cisco Switched voice protocol passes the default MAC
--     address for its node to the next node in the path, in both
--     call setup messages and keepalive requests and responses.
--     This MAC address is stored at the remote node to identify
--     where the incoming pvc originates. This information is then
--     used by the Cisco Voice Manager Application to determine
--     the voice network topology.

cvenabledlinkMIBObjects OBJECT IDENTIFIER ::= { ciscoVoiceEnabledLinkMIB 1 }
cvEnabledLink   OBJECT IDENTIFIER ::= { cvenabledlinkMIBObjects 1 }
ciscoVoiceEnabledLinkMIBNotificationPrefix OBJECT IDENTIFIER ::= { ciscoVoiceEnabledLinkMIB 2 }
ciscoVoiceEnabledLinkMIBNotifications OBJECT IDENTIFIER ::= { ciscoVoiceEnabledLinkMIBNotificationPrefix 0 }
ciscoVoiceEnabledlinkMIBConformance OBJECT IDENTIFIER ::= { ciscoVoiceEnabledLinkMIB 3 }
ciscoVoiceEnabledlinkMIBCompliances OBJECT IDENTIFIER ::= { ciscoVoiceEnabledlinkMIBConformance 1 }
ciscoVoiceEnabledlinkMIBGroups OBJECT IDENTIFIER ::= { ciscoVoiceEnabledlinkMIBConformance 2 }

cvEnabledDefaultMacAddr OBJECT-TYPE
    SYNTAX MacAddress
--    Rsyntax OCTET STRING(SIZE(6))
    ACCESS read-only
    STATUS mandatory
    DESCRIPTION
        "This item defines the Default MAC Address used by this
         node in call set up messages, keepalive requests and
         responses."
    ::= { cvEnabledLink 1 }

cvEnabledLinkTable OBJECT-TYPE
    SYNTAX SEQUENCE OF CvEnabledLinkEntry
    ACCESS not-accessible
    STATUS mandatory
    DESCRIPTION
        "This table contains information about ATM and Frame
         Relay Links used by voice over ATM and voice over Frame
         Relay calls."
    ::= { cvEnabledLink 2 }

cvEnabledLinkEntry OBJECT-TYPE
    SYNTAX CvEnabledLinkEntry
    ACCESS not-accessible
    STATUS mandatory
    DESCRIPTION
        "The information regarding a single ATM or Frame Relay
         Link. An entry of this table is created when its
         associated pvc is enabled for carrying Cisco Switched
         voice traffic. The entry is deleted when its associated
         pvc is no longer enabled for Cisco Switched voice
         traffic."
    INDEX { cvEnabledLinkIndex }
    ::= { cvEnabledLinkTable 1 }

CvEnabledLinkEntry ::= SEQUENCE {
    cvEnabledLinkIndex INTEGER,
    cvEnabledLinkType INTEGER,
    cvEnabledLinkInterfaceName DisplayString,
    cvEnabledLinkVpiDlci INTEGER,
    cvEnabledLinkVci INTEGER,
    cvEnabledLinkRemoteMacAddr MacAddress
    }

cvEnabledLinkIndex OBJECT-TYPE
    SYNTAX INTEGER(0..2147483648)
    ACCESS read-only
    STATUS mandatory
    DESCRIPTION
        "A monotonically increasing number, starting from zero,
         that is assigned to each link that is currently
         configured to carry Cisco Switched voice traffic. If a
         link is later unconfigured for voice traffic, the
         number assigned to it will not be reused. When the
         maximum value is reached, the value will wrap to zero
         and use a currently unassigned value."
    ::= { cvEnabledLinkEntry 1 }

cvEnabledLinkType OBJECT-TYPE
    SYNTAX INTEGER {
        atm(1),
        framerelay(2)
        }
    ACCESS read-only
    STATUS mandatory
    DESCRIPTION
        "The object defines the type of link, either ATM or
         Frame Relay."
    ::= { cvEnabledLinkEntry 2 }

cvEnabledLinkInterfaceName OBJECT-TYPE
    SYNTAX DisplayString
--    Rsyntax OCTET STRING(SIZE(0..255))
    ACCESS read-only
    STATUS mandatory
    DESCRIPTION
        "The object specifies the iFName of the peer interface
         that is used for the voice over ATM/FR call. A zero
         length string indicates that the value is unavailable."
    ::= { cvEnabledLinkEntry 3 }

cvEnabledLinkVpiDlci OBJECT-TYPE
    SYNTAX INTEGER(0..4095)
    ACCESS read-only
    STATUS mandatory
    DESCRIPTION
        "The VPI or DLCI used for this ATM/Frame Relay
         connection."
    ::= { cvEnabledLinkEntry 4 }

cvEnabledLinkVci OBJECT-TYPE
    SYNTAX INTEGER(0..65535)
    ACCESS read-only
    STATUS mandatory
    DESCRIPTION
        "The VCI used, if it is an ATM connection."
    ::= { cvEnabledLinkEntry 5 }

cvEnabledLinkRemoteMacAddr OBJECT-TYPE
    SYNTAX MacAddress
--    Rsyntax OCTET STRING(SIZE(6))
    ACCESS read-only
    STATUS mandatory
    DESCRIPTION
        "The default MAC address of the node at the other end of
         the link."
    ::= { cvEnabledLinkEntry 6 }

cvEnabledMacAddrGroup OBJECT IDENTIFIER ::= { ciscoVoiceEnabledlinkMIBGroups 1 }
-- OBJECT-GROUP
--  Status
--    mandatory
--  Descr
--    A collection of objects providing the Default Mac 
--     Address capability.
--  objects
--    cvEnabledDefaultMacAddr

cvEnabledLinkGroup OBJECT IDENTIFIER ::= { ciscoVoiceEnabledlinkMIBGroups 2 }
-- OBJECT-GROUP
--  Status
--    mandatory
--  Descr
--    A collection of objects providing the Voice Enabled Link
--     entry capability.
--  objects
--    cvEnabledLinkIndex, cvEnabledLinkType, 
--    cvEnabledLinkInterfaceName, cvEnabledLinkVpiDlci, 
--    cvEnabledLinkVci, cvEnabledLinkRemoteMacAddr

ciscoVoiceEnabledlinkMIBCompliance OBJECT IDENTIFIER ::= { ciscoVoiceEnabledlinkMIBCompliances 1 }
-- MODULE-COMPLIANCE
--  Status
--    mandatory
--  Descr
--    The compliance statement for entities which
--     implement the CISCO VOICE ENABLED LINK MIB
--  Module
--    >>current<<
--   MandGroup
--    cvEnabledMacAddrGroup
--   MandGroup
--    cvEnabledLinkGroup


END
