-- MIB file created 09-May-2013 00:57:37, by
--   SMICng version 2.2.11-beta(PRO)(Solaris), January 20, 2001. Enterprise key cisco.com

CISCO-VPC-MIB DEFINITIONS ::= BEGIN

-- From file: "CISCO-VPC-MIB.my"
-- Compile options "4 7 F H N W 03 06 0B 0G 0N 0T"

IMPORTS
    DateAndTime, TruthValue, MacAddress
            FROM SNMPv2-TC-v1
    InetAddress, InetAddressType, InetPortNumber
            FROM INET-ADDRESS-MIB
    CounterBasedGauge64
            FROM HCNUM-TC
    SnmpAdminString
            FROM SNMP-FRAMEWORK-MIB
    InterfaceIndex, InterfaceIndexOrZero
            FROM IF-MIB
    ciscoMgmt
            FROM CISCO-SMI
    Counter, Gauge
            FROM RFC1155-SMI
    OBJECT-TYPE
            FROM RFC-1212;

ciscoVpcMIB OBJECT IDENTIFIER ::= { ciscoMgmt 807 }
-- MODULE-IDENTITY
--  LastUpdated
--    201305090000Z
--  OrgName
--    Cisco Systems, Inc.
--  ContactInfo
--    Cisco Systems
--    Customer Service
--    
--    Postal: 170 W Tasman Drive
--    San Jose, CA 95134
--    USA
--    
--    Tel: +1 800 553-NETS
--    
--    E-mail: cs-lan-switch-snmp@cisco.com
--  Descr
--    This MIB module defines MIB objects which provide
--    management information for configuring and monitoring
--    of Virtual Port Channel(VPC) on Cisco devices.
--    
--    The following terms are used throughout this MIB:
--    
--    ISSU:  In Service Software Upgrade
--    ToS:   Type of Service
--    UDP:   User Datagram Protocol
--    VPC:   Virtual Port Channel
--    VRF:   Virtual Routing and Forwarding
--  RevDate
--    201305090000Z
--  RevDescr
--    Initial version of this MIB module.

ciscoVpcMIBNotifs OBJECT IDENTIFIER ::= { ciscoVpcMIB 0 }
ciscoVpcMIBObjects OBJECT IDENTIFIER ::= { ciscoVpcMIB 1 }
ciscoVpcMIBConformance OBJECT IDENTIFIER ::= { ciscoVpcMIB 2 }
cVpcPeerKeepAlive OBJECT IDENTIFIER ::= { ciscoVpcMIBObjects 1 }
cVpcRole        OBJECT IDENTIFIER ::= { ciscoVpcMIBObjects 2 }
cVpcStatistics  OBJECT IDENTIFIER ::= { ciscoVpcMIBObjects 3 }
cVpcStatus      OBJECT IDENTIFIER ::= { ciscoVpcMIBObjects 4 }
ciscoVpcMIBCompliances OBJECT IDENTIFIER ::= { ciscoVpcMIBConformance 1 }
ciscoVpcMIBGroups OBJECT IDENTIFIER ::= { ciscoVpcMIBConformance 2 }

cVpcPeerKeepAliveConfigTable OBJECT-TYPE
    SYNTAX SEQUENCE OF CVpcPeerKeepAliveConfigEntry
    ACCESS not-accessible
    STATUS mandatory
    DESCRIPTION
        "The table contains the VPC peer-keepalive link and message
        configuration information in the managed device."
    ::= { cVpcPeerKeepAlive 1 }

cVpcPeerKeepAliveConfigEntry OBJECT-TYPE
    SYNTAX CVpcPeerKeepAliveConfigEntry
    ACCESS not-accessible
    STATUS mandatory
    DESCRIPTION
        "An entry containing VPC peer-keepalive link and
        message configuration information."
    INDEX { cVpcPeerKeepAliveConfigDomainID }
    ::= { cVpcPeerKeepAliveConfigTable 1 }

CVpcPeerKeepAliveConfigEntry ::= SEQUENCE {
    cVpcPeerKeepAliveConfigDomainID Gauge,
    cVpcPeerKeepAliveDestAddrType InetAddressType,
    cVpcPeerKeepAliveDestAddr InetAddress,
    cVpcPeerKeepAliveSourceAddrType InetAddressType,
    cVpcPeerKeepAliveSourceAddr InetAddress,
    cVpcPeerKeepAliveUdpPort InetPortNumber,
    cVpcPeerKeepAliveInterval Gauge,
    cVpcPeerKeepAliveTimeout Gauge,
    cVpcPeerKeepAliveHoldTimeout Gauge,
    cVpcPeerKeepAliveTos Gauge,
    cVpcPeerKeepAlivePrecedence Gauge,
    cVpcPeerKeepAliveTosByte Gauge,
    cVpcPeerKeepAliveVrfName SnmpAdminString
    }

cVpcPeerKeepAliveConfigDomainID OBJECT-TYPE
    SYNTAX Gauge
    ACCESS not-accessible
    STATUS mandatory
    DESCRIPTION
        "An arbitrary value to uniquely identify the VPC management
        domain on the local system.
        
        Value zero indicates no VPC management domain has been
        configured for this device."
    ::= { cVpcPeerKeepAliveConfigEntry 1 }

cVpcPeerKeepAliveDestAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object specifies type of Internet address of destination
        address for peer device."
    ::= { cVpcPeerKeepAliveConfigEntry 2 }

cVpcPeerKeepAliveDestAddr OBJECT-TYPE
    SYNTAX InetAddress
--    Rsyntax OCTET STRING(SIZE(0..255))
    ACCESS read-write
    STATUS mandatory
    DESCRIPTION
        "This object specifies destination ip address of peer device.
        
        The type of this address is determined by the
        cVpcPeerKeepAliveDestAddrType object."
    ::= { cVpcPeerKeepAliveConfigEntry 3 }

cVpcPeerKeepAliveSourceAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object specifies type of Internet address of source
        address used for peer-keepalive hello messages."
    ::= { cVpcPeerKeepAliveConfigEntry 4 }

cVpcPeerKeepAliveSourceAddr OBJECT-TYPE
    SYNTAX InetAddress
--    Rsyntax OCTET STRING(SIZE(0..255))
    ACCESS read-write
    STATUS mandatory
    DESCRIPTION
        "This object specifies source address used in this
        peer-keepalive hello messages.
        
        The type of this address is determined by the
        cVpcPeerKeepAliveSourceAddrType object."
    ::= { cVpcPeerKeepAliveConfigEntry 5 }

cVpcPeerKeepAliveUdpPort OBJECT-TYPE
    SYNTAX InetPortNumber
--    Rsyntax Gauge(0..65535)
    ACCESS read-write
    STATUS mandatory
    DESCRIPTION
        "This object specifies UDP Port number used for
        peer-keepalive hello messages."
    DEFVAL { 3200 }
    ::= { cVpcPeerKeepAliveConfigEntry 6 }

cVpcPeerKeepAliveInterval OBJECT-TYPE
    SYNTAX Gauge
--  Units
--    milli-seconds
    ACCESS read-write
    STATUS mandatory
    DESCRIPTION
        "This object specifies the interval of peer-keepalive
        hello messages."
    DEFVAL { 1000 }
    ::= { cVpcPeerKeepAliveConfigEntry 7 }

cVpcPeerKeepAliveTimeout OBJECT-TYPE
    SYNTAX Gauge
--  Units
--    seconds
    ACCESS read-write
    STATUS mandatory
    DESCRIPTION
        "This object specifies the timeout of peer-keepalive
        hello messages."
    DEFVAL { 5 }
    ::= { cVpcPeerKeepAliveConfigEntry 8 }

cVpcPeerKeepAliveHoldTimeout OBJECT-TYPE
    SYNTAX Gauge
--  Units
--    seconds
    ACCESS read-write
    STATUS mandatory
    DESCRIPTION
        "This object specifies hold timeout to ignore stale
        peer alive messages."
    DEFVAL { 3 }
    ::= { cVpcPeerKeepAliveConfigEntry 9 }

cVpcPeerKeepAliveTos OBJECT-TYPE
    SYNTAX Gauge(0..15)
    ACCESS read-write
    STATUS mandatory
    DESCRIPTION
        "This object specifies the ToS value used for peer-keepalive
        hello messages."
    ::= { cVpcPeerKeepAliveConfigEntry 10 }

cVpcPeerKeepAlivePrecedence OBJECT-TYPE
    SYNTAX Gauge(0..7)
    ACCESS read-write
    STATUS mandatory
    DESCRIPTION
        "This object specifies the Precedence value used for peer-keepalive
        hello messages."
    ::= { cVpcPeerKeepAliveConfigEntry 11 }

cVpcPeerKeepAliveTosByte OBJECT-TYPE
    SYNTAX Gauge(0..255)
    ACCESS read-write
    STATUS mandatory
    DESCRIPTION
        "This object specifies the ToS-Byte value used for peer-keepalive
        messages.
        
        Only low eight-bit byte of this double word is used.  Bit 0 is reserved.
        Bits 1 to 5 represent the value of cVpcPeerKeepAliveTos. Bits 6 to 8 
        come into cVpcPeerKeepAlivePrecedence. ToS-Byte indicates the value of 
        the whole byte including ToS, Precedence and reserved bit 0."
    DEFVAL { 192 }
    ::= { cVpcPeerKeepAliveConfigEntry 12 }

cVpcPeerKeepAliveVrfName OBJECT-TYPE
    SYNTAX SnmpAdminString
--    Rsyntax OCTET STRING(SIZE(0..255))
    ACCESS read-write
    STATUS mandatory
    DESCRIPTION
        "This object specifies the VRF name to be used for peer-keepalive
        messages routing."
    DEFVAL { "management" }
    ::= { cVpcPeerKeepAliveConfigEntry 13 }

cVpcPeerKeepAliveTable OBJECT-TYPE
    SYNTAX SEQUENCE OF CVpcPeerKeepAliveEntry
    ACCESS not-accessible
    STATUS mandatory
    DESCRIPTION
        "The table contains the VPC peer-keepalive link status
        information in the managed device."
    ::= { cVpcPeerKeepAlive 2 }

cVpcPeerKeepAliveEntry OBJECT-TYPE
    SYNTAX CVpcPeerKeepAliveEntry
    ACCESS not-accessible
    STATUS mandatory
    DESCRIPTION
        "An entry containing VPC peer-keepalive link status information."
    INDEX { cVpcPeerKeepAliveDomainID }
    ::= { cVpcPeerKeepAliveTable 1 }

CVpcPeerKeepAliveEntry ::= SEQUENCE {
    cVpcPeerKeepAliveDomainID Gauge,
    cVpcPeerKeepAliveStatus INTEGER,
    cVpcPeerKeepAliveTime CounterBasedGauge64,
    cVpcPeerKeepAliveMsgSendStatus INTEGER,
    cVpcPeerKeepAliveMsgLastSendTime DateAndTime,
    cVpcPeerKeepAliveMsgSendInterface InterfaceIndexOrZero,
    cVpcPeerKeepAliveMsgRcvrStatus INTEGER,
    cVpcPeerKeepAliveMsgLastReceiveTime DateAndTime,
    cVpcPeerKeepAliveMsgReceiveInterface InterfaceIndexOrZero
    }

cVpcPeerKeepAliveDomainID OBJECT-TYPE
    SYNTAX Gauge
    ACCESS not-accessible
    STATUS mandatory
    DESCRIPTION
        "An arbitrary value to uniquely identify the VPC management
        domain on the local system.
        
        Value zero indicates there is no VPC management domain
        being configured for this device."
    ::= { cVpcPeerKeepAliveEntry 1 }

cVpcPeerKeepAliveStatus OBJECT-TYPE
    SYNTAX INTEGER {
        disabled(1),
        alive(2),
        peerUnreachable(3),
        aliveButDomainIdDismatch(4),
        suspendedAsISSU(5),
        suspendedAsDestIPUnreachable(6),
        suspendedAsVRFUnusable(7),
        misconfigured(8)
        }
    ACCESS read-only
    STATUS mandatory
    DESCRIPTION
        "This object indicates VPC peer keep-alive status.
        
        disabled(1) : Peer-keepalive is disabled.
        
        alive(2) : Peer-keepalive is alive.
        
        peerUnreachable(3) : Peer is unreachable through
        Peer-keepalive link.
        
        aliveButDomainIdDismatch(4) : Peer-keepalive is alive, 
        but VPC domain doesn't match with each other.
        
        suspendedAsISSU(5) : Peer-keepalive is suspended during ISSU.
        
        suspendedAsDestIPUnreachable(6) : Peer-keepalive is suspended
        since destination ip is unreachable.
        
        suspendedAsVRFUnusable(7) : Peer-keepalive is suspended since
        the current VRF is unusable.
        
        misconfigured(8) : Misconfigure Peer-keepalive feature."
    ::= { cVpcPeerKeepAliveEntry 2 }

cVpcPeerKeepAliveTime OBJECT-TYPE
    SYNTAX --?? syntax is not convertable to SMIv1
           CounterBasedGauge64
--    Rsyntax Counter64
--  Units
--    milli-seconds
    ACCESS read-only
    STATUS mandatory
    DESCRIPTION
        "This object indicates the time (in msec) since the peer
        became alive.
        
        It will hold value 0 if peer-keepalive never becomes alive."
    ::= { cVpcPeerKeepAliveEntry 3 }

cVpcPeerKeepAliveMsgSendStatus OBJECT-TYPE
    SYNTAX INTEGER {
        success(1),
        failure(2)
        }
    ACCESS read-only
    STATUS mandatory
    DESCRIPTION
        "This object indicates VPC peer keep-alive message sending
        status."
    ::= { cVpcPeerKeepAliveEntry 4 }

cVpcPeerKeepAliveMsgLastSendTime OBJECT-TYPE
    SYNTAX DateAndTime
--    Rsyntax OCTET STRING(SIZE(8|11))
    ACCESS read-only
    STATUS mandatory
    DESCRIPTION
        "This object indicates date and time of VPC peer
        keep-alive message last send.
        
        This object contains value 0x0000010100000000, if
        peer-keepalive message has never been sent."
    ::= { cVpcPeerKeepAliveEntry 5 }

cVpcPeerKeepAliveMsgSendInterface OBJECT-TYPE
    SYNTAX InterfaceIndexOrZero
--    Rsyntax INTEGER(0..2147483647)
    ACCESS read-only
    STATUS mandatory
    DESCRIPTION
        "This object indicates the ifIndex of interface of VPC
        peer keep-alive message sent on."
    ::= { cVpcPeerKeepAliveEntry 6 }

cVpcPeerKeepAliveMsgRcvrStatus OBJECT-TYPE
    SYNTAX INTEGER {
        success(1),
        failure(2)
        }
    ACCESS read-only
    STATUS mandatory
    DESCRIPTION
        "This object indicates VPC peer keep-alive message
        receiving status."
    ::= { cVpcPeerKeepAliveEntry 7 }

cVpcPeerKeepAliveMsgLastReceiveTime OBJECT-TYPE
    SYNTAX DateAndTime
--    Rsyntax OCTET STRING(SIZE(8|11))
    ACCESS read-only
    STATUS mandatory
    DESCRIPTION
        "This object indicates date and time of VPC peer
        keep-alive message last received.
        
        This object contains value 0x0000010100000000, if
        peer-keepalive message has never been received."
    ::= { cVpcPeerKeepAliveEntry 8 }

cVpcPeerKeepAliveMsgReceiveInterface OBJECT-TYPE
    SYNTAX InterfaceIndexOrZero
--    Rsyntax INTEGER(0..2147483647)
    ACCESS read-only
    STATUS mandatory
    DESCRIPTION
        "This object indicates the ifIndex of interface of
        VPC peer keep-alive message last received."
    ::= { cVpcPeerKeepAliveEntry 9 }

cVpcRoleTable OBJECT-TYPE
    SYNTAX SEQUENCE OF CVpcRoleEntry
    ACCESS not-accessible
    STATUS mandatory
    DESCRIPTION
        "The table contains the VPC role status
        information in the managed device."
    ::= { cVpcRole 1 }

cVpcRoleEntry OBJECT-TYPE
    SYNTAX CVpcRoleEntry
    ACCESS not-accessible
    STATUS mandatory
    DESCRIPTION
        "An entry containing VPC role information."
    INDEX { cVpcRoleDomainID }
    ::= { cVpcRoleTable 1 }

CVpcRoleEntry ::= SEQUENCE {
    cVpcRoleDomainID Gauge,
    cVpcRoleStatus INTEGER,
    cVpcDualActiveDetectionStatus TruthValue,
    cVpcSystemAdminMacAddress MacAddress,
    cVpcSystemOperMacAddress MacAddress,
    cVpcLocalOperMacAddress MacAddress,
    cVpcSystemAdminPriority Gauge,
    cVpcSystemOperPriority Gauge,
    cVpcLocalRoleAdminPriority Gauge,
    cVpcLocalRoleOperPriority Gauge
    }

cVpcRoleDomainID OBJECT-TYPE
    SYNTAX Gauge
    ACCESS not-accessible
    STATUS mandatory
    DESCRIPTION
        "An arbitrary value to uniquely identify the VPC management
        domain on the local system.
        
        Value zero indicates there is no VPC management domain
        being configured for this device."
    ::= { cVpcRoleEntry 1 }

cVpcRoleStatus OBJECT-TYPE
    SYNTAX INTEGER {
        primarySecondary(1),
        primary(2),
        secondaryPrimary(3),
        secondary(4),
        noneEstablished(5)
        }
    ACCESS read-only
    STATUS mandatory
    DESCRIPTION
        "This object indicates the VPC role status of the peer device.
        
        primarySecondary(1) : primary, and operational secondary.
        
        primary(2) : primary, and operational primary.
        
        secondaryPrimary(3) : secondary, and operational primary.
        
        secondary(4) : secondary, and operational secondary.
        
        noneEstabished(5) : none peer device."
    ::= { cVpcRoleEntry 2 }

cVpcDualActiveDetectionStatus OBJECT-TYPE
    SYNTAX TruthValue
--    Rsyntax INTEGER {
--        true(1),
--        false(2)
--        }
    ACCESS read-only
    STATUS mandatory
    DESCRIPTION
        "This object indicates the dual active detection
        status of peer device.
        
        true(1) : indicate that Dual Active is detected.
        
        false(2) : indicate that Dual Active is not detected."
    ::= { cVpcRoleEntry 3 }

cVpcSystemAdminMacAddress OBJECT-TYPE
    SYNTAX MacAddress
--    Rsyntax OCTET STRING(SIZE(6))
    ACCESS read-write
    STATUS mandatory
    DESCRIPTION
        "This object specifies VPC system MAC address."
    ::= { cVpcRoleEntry 4 }

cVpcSystemOperMacAddress OBJECT-TYPE
    SYNTAX MacAddress
--    Rsyntax OCTET STRING(SIZE(6))
    ACCESS read-only
    STATUS mandatory
    DESCRIPTION
        "This object indicates VPC system operational MAC address."
    ::= { cVpcRoleEntry 5 }

cVpcLocalOperMacAddress OBJECT-TYPE
    SYNTAX MacAddress
--    Rsyntax OCTET STRING(SIZE(6))
    ACCESS read-only
    STATUS mandatory
    DESCRIPTION
        "This object indicates VPC local system operational
        MAC address."
    ::= { cVpcRoleEntry 6 }

cVpcSystemAdminPriority OBJECT-TYPE
    SYNTAX Gauge
    ACCESS read-write
    STATUS mandatory
    DESCRIPTION
        "This object specifies VPC system priority."
    ::= { cVpcRoleEntry 7 }

cVpcSystemOperPriority OBJECT-TYPE
    SYNTAX Gauge
    ACCESS read-only
    STATUS mandatory
    DESCRIPTION
        "This object indicates VPC system operational priority."
    ::= { cVpcRoleEntry 8 }

cVpcLocalRoleAdminPriority OBJECT-TYPE
    SYNTAX Gauge
    ACCESS read-write
    STATUS mandatory
    DESCRIPTION
        "This object specifies VPC local role priority."
    ::= { cVpcRoleEntry 9 }

cVpcLocalRoleOperPriority OBJECT-TYPE
    SYNTAX Gauge
    ACCESS read-only
    STATUS mandatory
    DESCRIPTION
        "This object indicates VPC local role operational priority."
    ::= { cVpcRoleEntry 10 }

cVpcStatsPeerKeepAliveTable OBJECT-TYPE
    SYNTAX SEQUENCE OF CVpcStatsPeerKeepAliveEntry
    ACCESS not-accessible
    STATUS mandatory
    DESCRIPTION
        "The table contains the statistics of VPC peer-keepalive
        messages in the managed device."
    ::= { cVpcStatistics 1 }

cVpcStatsPeerKeepAliveEntry OBJECT-TYPE
    SYNTAX CVpcStatsPeerKeepAliveEntry
    ACCESS not-accessible
    STATUS mandatory
    DESCRIPTION
        "An entry containing statistics of the VPC peer-keepalive
        messages."
    INDEX { cVpcStatsPeerKeepAliveDomainID }
    ::= { cVpcStatsPeerKeepAliveTable 1 }

CVpcStatsPeerKeepAliveEntry ::= SEQUENCE {
    cVpcStatsPeerKeepAliveDomainID Gauge,
    cVpcStatsPeerKeepAliveMsgsSent Counter,
    cVpcStatsPeerKeepAliveMsgsRcved Counter,
    cVpcStatsPeerKeepAliveAvgInterval Gauge,
    cVpcStatsPeerStatusChangeCount Counter
    }

cVpcStatsPeerKeepAliveDomainID OBJECT-TYPE
    SYNTAX Gauge
    ACCESS not-accessible
    STATUS mandatory
    DESCRIPTION
        "An arbitrary value to uniquely identify the VPC management
        domain on the local system.
        
        Value zero indicates there is no VPC management domain
        being configured for this device."
    ::= { cVpcStatsPeerKeepAliveEntry 1 }

cVpcStatsPeerKeepAliveMsgsSent OBJECT-TYPE
    SYNTAX Counter
    ACCESS read-only
    STATUS mandatory
    DESCRIPTION
        "This object indicates the number of peer-keepalive
        messages sent to peer."
    ::= { cVpcStatsPeerKeepAliveEntry 2 }

cVpcStatsPeerKeepAliveMsgsRcved OBJECT-TYPE
    SYNTAX Counter
    ACCESS read-only
    STATUS mandatory
    DESCRIPTION
        "This object indicates the number of peer-keepalive
        messages received from peer."
    ::= { cVpcStatsPeerKeepAliveEntry 3 }

cVpcStatsPeerKeepAliveAvgInterval OBJECT-TYPE
    SYNTAX Gauge
--  Units
--    seconds
    ACCESS read-only
    STATUS mandatory
    DESCRIPTION
        "This object indicates the average interval for
        the peer-keepalive messages received from peer."
    ::= { cVpcStatsPeerKeepAliveEntry 4 }

cVpcStatsPeerStatusChangeCount OBJECT-TYPE
    SYNTAX Counter
    ACCESS read-only
    STATUS mandatory
    DESCRIPTION
        "This object indicates the number of times that
        the peer status gets changed."
    ::= { cVpcStatsPeerKeepAliveEntry 5 }

cVpcStatusPeerLinkTable OBJECT-TYPE
    SYNTAX SEQUENCE OF CVpcStatusPeerLinkEntry
    ACCESS not-accessible
    STATUS mandatory
    DESCRIPTION
        "The table contains the list of VPC peer-links in
        the managed device."
    ::= { cVpcStatus 1 }

cVpcStatusPeerLinkEntry OBJECT-TYPE
    SYNTAX CVpcStatusPeerLinkEntry
    ACCESS not-accessible
    STATUS mandatory
    DESCRIPTION
        "An entry containing VPC peer-link management information
        applicable to a particular VPC domain."
    INDEX { cVpcStatusPeerLinkDomainID }
    ::= { cVpcStatusPeerLinkTable 1 }

CVpcStatusPeerLinkEntry ::= SEQUENCE {
    cVpcStatusPeerLinkDomainID Gauge,
    cVpcStatusPeerLinkIfIndex InterfaceIndex
    }

cVpcStatusPeerLinkDomainID OBJECT-TYPE
    SYNTAX Gauge
    ACCESS not-accessible
    STATUS mandatory
    DESCRIPTION
        "An arbitrary value to uniquely identify the VPC management
        domain."
    ::= { cVpcStatusPeerLinkEntry 1 }

cVpcStatusPeerLinkIfIndex OBJECT-TYPE
    SYNTAX InterfaceIndex
--    Rsyntax INTEGER(1..2147483647)
    ACCESS read-only
    STATUS mandatory
    DESCRIPTION
        "The value of the ifIndex corresponding to the peer link of
        this VPC domain."
    ::= { cVpcStatusPeerLinkEntry 2 }

cVpcStatusHostLinkTable OBJECT-TYPE
    SYNTAX SEQUENCE OF CVpcStatusHostLinkEntry
    ACCESS not-accessible
    STATUS mandatory
    DESCRIPTION
        "The table contains the VPC host-link summary information in
        the managed device."
    ::= { cVpcStatus 2 }

cVpcStatusHostLinkEntry OBJECT-TYPE
    SYNTAX CVpcStatusHostLinkEntry
    ACCESS not-accessible
    STATUS mandatory
    DESCRIPTION
        "An entry containing VPC host-link summary information."
    INDEX { cVpcStatusHostLinkDomainID, cVpcStatusHostLinkVpcID }
    ::= { cVpcStatusHostLinkTable 1 }

CVpcStatusHostLinkEntry ::= SEQUENCE {
    cVpcStatusHostLinkDomainID Gauge,
    cVpcStatusHostLinkVpcID Gauge,
    cVpcStatusHostLinkIfIndex InterfaceIndexOrZero,
    cVpcStatusHostLinkStatus INTEGER,
    cVpcStatusHostLinkConsistencyStatus INTEGER,
    cVpcStatusHostLinkConsistencyDetail SnmpAdminString
    }

cVpcStatusHostLinkDomainID OBJECT-TYPE
    SYNTAX Gauge
    ACCESS not-accessible
    STATUS mandatory
    DESCRIPTION
        "An arbitrary value to uniquely identify the VPC management
        domain."
    ::= { cVpcStatusHostLinkEntry 1 }

cVpcStatusHostLinkVpcID OBJECT-TYPE
    SYNTAX Gauge
    ACCESS not-accessible
    STATUS mandatory
    DESCRIPTION
        "An arbitrary value to uniquely identify a VPC link between
        the host and the switch for a given VPC management domain."
    ::= { cVpcStatusHostLinkEntry 2 }

cVpcStatusHostLinkIfIndex OBJECT-TYPE
    SYNTAX InterfaceIndexOrZero
--    Rsyntax INTEGER(0..2147483647)
    ACCESS read-only
    STATUS mandatory
    DESCRIPTION
        "The value of the ifIndex corresponding to a host-link
        interface."
    ::= { cVpcStatusHostLinkEntry 3 }

cVpcStatusHostLinkStatus OBJECT-TYPE
    SYNTAX INTEGER {
        down(1),
        downStar(2),
        up(3)
        }
    ACCESS read-only
    STATUS mandatory
    DESCRIPTION
        "This object indicates the current status of VPC host-link.
        
        down(1) : Host link is down.
        
        downStar(2) : Local host link is down, forwarding via vPC 
        peer-link.
        
        up(3) : Host link is up."
    ::= { cVpcStatusHostLinkEntry 4 }

cVpcStatusHostLinkConsistencyStatus OBJECT-TYPE
    SYNTAX INTEGER {
        success(1),
        failed(2),
        notApplicable(3)
        }
    ACCESS read-only
    STATUS mandatory
    DESCRIPTION
        "This object indicates the status of configuration consistency
        check of this VPC host link."
    ::= { cVpcStatusHostLinkEntry 5 }

cVpcStatusHostLinkConsistencyDetail OBJECT-TYPE
    SYNTAX SnmpAdminString
--    Rsyntax OCTET STRING(SIZE(0..255))
    ACCESS read-only
    STATUS mandatory
    DESCRIPTION
        "This object indicates the reason of consistency check
        status change detail."
    ::= { cVpcStatusHostLinkEntry 6 }

cVpcPeerKeepAliveConfigInfoGroup OBJECT IDENTIFIER ::= { ciscoVpcMIBGroups 1 }
-- OBJECT-GROUP
--  Status
--    mandatory
--  Descr
--    A collection of objects providing peer-keepalive link
--    and messages configuration information.
--  objects
--    cVpcPeerKeepAliveDestAddrType, cVpcPeerKeepAliveDestAddr, 
--    cVpcPeerKeepAliveSourceAddrType, cVpcPeerKeepAliveSourceAddr, 
--    cVpcPeerKeepAliveUdpPort, cVpcPeerKeepAliveInterval, 
--    cVpcPeerKeepAliveTimeout, cVpcPeerKeepAliveHoldTimeout, 
--    cVpcPeerKeepAliveTos, cVpcPeerKeepAlivePrecedence, 
--    cVpcPeerKeepAliveTosByte, cVpcPeerKeepAliveVrfName

cVpcPeerKeepAliveStatusInfoGroup OBJECT IDENTIFIER ::= { ciscoVpcMIBGroups 2 }
-- OBJECT-GROUP
--  Status
--    mandatory
--  Descr
--    A collection of objects providing peer-keepalive
--    status information.
--  objects
--    cVpcPeerKeepAliveStatus, cVpcPeerKeepAliveTime, 
--    cVpcPeerKeepAliveMsgSendStatus, 
--    cVpcPeerKeepAliveMsgLastSendTime, 
--    cVpcPeerKeepAliveMsgSendInterface, 
--    cVpcPeerKeepAliveMsgRcvrStatus, 
--    cVpcPeerKeepAliveMsgLastReceiveTime, 
--    cVpcPeerKeepAliveMsgReceiveInterface

cVpcMIBRoleGroup OBJECT IDENTIFIER ::= { ciscoVpcMIBGroups 3 }
-- OBJECT-GROUP
--  Status
--    mandatory
--  Descr
--    A collection of objects providing peer-keepalive
--    role information.
--  objects
--    cVpcRoleStatus, cVpcDualActiveDetectionStatus, 
--    cVpcSystemAdminMacAddress, cVpcSystemOperMacAddress, 
--    cVpcLocalOperMacAddress, cVpcSystemAdminPriority, 
--    cVpcSystemOperPriority, cVpcLocalRoleAdminPriority, 
--    cVpcLocalRoleOperPriority

cVpcMIBStatisticsGroup OBJECT IDENTIFIER ::= { ciscoVpcMIBGroups 4 }
-- OBJECT-GROUP
--  Status
--    mandatory
--  Descr
--    A collection of objects providing peer-keepalive
--    statistics information.
--  objects
--    cVpcStatsPeerKeepAliveMsgsSent, 
--    cVpcStatsPeerKeepAliveMsgsRcved, 
--    cVpcStatsPeerKeepAliveAvgInterval, 
--    cVpcStatsPeerStatusChangeCount

cVpcMIBPeerLinkStatusGroup OBJECT IDENTIFIER ::= { ciscoVpcMIBGroups 5 }
-- OBJECT-GROUP
--  Status
--    mandatory
--  Descr
--    A collection of objects providing peer-link status
--    information
--  objects
--    cVpcStatusPeerLinkIfIndex

cVpcMIBHostLinkStatusGroup OBJECT IDENTIFIER ::= { ciscoVpcMIBGroups 6 }
-- OBJECT-GROUP
--  Status
--    mandatory
--  Descr
--    A collection of objects providing host-link VPC
--    status information.
--  objects
--    cVpcStatusHostLinkIfIndex, cVpcStatusHostLinkStatus, 
--    cVpcStatusHostLinkConsistencyStatus, 
--    cVpcStatusHostLinkConsistencyDetail

ciscoVpcMIBCompliance OBJECT IDENTIFIER ::= { ciscoVpcMIBCompliances 1 }
-- MODULE-COMPLIANCE
--  Status
--    mandatory
--  Descr
--    The compliance statement for CISCO-VPC-MIB.
--  Module
--    >>current<<
--   MandGroup
--    cVpcPeerKeepAliveConfigInfoGroup
--   MandGroup
--    cVpcPeerKeepAliveStatusInfoGroup
--   MandGroup
--    cVpcMIBRoleGroup
--   MandGroup
--    cVpcMIBStatisticsGroup
--   MandGroup
--    cVpcMIBPeerLinkStatusGroup
--   MandGroup
--    cVpcMIBHostLinkStatusGroup
--   ObjVar
--    cVpcPeerKeepAliveDestAddrType
--   ObjVar
--    cVpcPeerKeepAliveDestAddr
--   ObjVar
--    cVpcPeerKeepAliveSourceAddrType
--   ObjVar
--    cVpcPeerKeepAliveSourceAddr
--   ObjVar
--    cVpcPeerKeepAliveUdpPort
--   ObjVar
--    cVpcPeerKeepAliveInterval
--   ObjVar
--    cVpcPeerKeepAliveTimeout
--   ObjVar
--    cVpcPeerKeepAliveHoldTimeout
--   ObjVar
--    cVpcPeerKeepAliveTos
--   ObjVar
--    cVpcPeerKeepAlivePrecedence
--   ObjVar
--    cVpcPeerKeepAliveTosByte
--   ObjVar
--    cVpcPeerKeepAliveVrfName
--   ObjVar
--    cVpcSystemAdminMacAddress
--   ObjVar
--    cVpcSystemAdminPriority
--   ObjVar
--    cVpcLocalRoleAdminPriority


END
