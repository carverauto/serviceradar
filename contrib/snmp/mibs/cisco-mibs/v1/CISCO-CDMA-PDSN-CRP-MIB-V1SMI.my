-- MIB file created 03-May-2010 11:32:42, by
--   SMICng version 2.2.11-beta(PRO)(Solaris), January 20, 2001. Enterprise key cisco.com

CISCO-CDMA-PDSN-CRP-MIB DEFINITIONS ::= BEGIN

-- From file: "CISCO-CDMA-PDSN-CRP-MIB.my"
-- Compile options "4 7 F H N W 03 06 0B 0G 0N 0T"

IMPORTS
    TruthValue
            FROM SNMPv2-TC-v1
    InetAddress, InetAddressType
            FROM INET-ADDRESS-MIB
    ciscoMgmt
            FROM CISCO-SMI
    Counter, Gauge
            FROM RFC1155-SMI
    OBJECT-TYPE
            FROM RFC-1212;

ciscoCdmaPdsnCrpMIB OBJECT IDENTIFIER ::= { ciscoMgmt 957 }
-- MODULE-IDENTITY
--  LastUpdated
--    200407270000Z
--  OrgName
--    Cisco Systems, Inc.
--  ContactInfo
--            Cisco Systems 
--             Customer Service 
--    
--    Postal: 170 W Tasman Drive 
--             San Jose, CA  95134 
--             USA 
--    
--       Tel: +1 800 553-NETS 
--    
--    E-mail: cdma@cisco.com
--  Descr
--    This MIB is to support the Closed RP feature of CDMA 
--     PDSN that supports wireless data communication  
--     through 3G CDMA radio access technology.  PDSN acts 
--     as a foreign agent that establishes, maintains and 
--     terminates the link layer to a mobile station. 
--    
--     The high level architecture of a third generation  
--     CDMA2000 network is shown below: 
--    
--    +========+=+               +=========+          +=========+ 
--    | RAdio  |P|               |         |   Data   |  Home   | 
--    | Network|C|- Closed RP   -|  PDSN   |-  Core  -| Network | 
--    |  (RAN) |F|  Interface    |         |  Network |         | 
--    +========+=+               +=========+   (DCN)  +=========+ 
--    /|\                    Foreign Agent         Home Agent 
--    |                        (FA)                  (HA) 
--    |   Visited Access 
--    |  Provider Network                
--    |                                  
--    \|/                                 
--    +========+ 
--    | Mobile | 
--    | Station| 
--    |  (MS)  | 
--    +========+ 
--    
--    The following diagram illustrates protocols usage by the 
--    CDMA2000 network elements: 
--    
--    MS ===== RAN ======== PDSN ======== DCN ====== Home Network 
--    |        |  Closed RP |                        | 
--    |        +=signaling==+                        | 
--    |                     |                        | 
--    |                     +...L2TP/L2F tunnelling..+ 
--    |                     |                        | 
--    +======== PPP ========+                        | 
--    |                     |                        | 
--    |                     +..Mobile IP tunnelling..+ 
--    |                                              | 
--    |                                              | 
--    |                                              | 
--    +=================Mobile IP====================+ 
--    |                                              | 
--    |                                              | 
--    +======================data====================+ 
--    
--    
--     The CDMA PDSN CRP MIB provides operational information 
--     for a Closed RP implementation.  The following areas  
--     are managed: 
--    
--         1) Global PDSN information.  This area contains  
--            generic information such as the number of  
--            incoming call requests, incoming call replies  
--            etc., 
--    
--     Acronyms and terms: 
--    
--       CDMA            Code Division Multiple Access 
--    
--       DCN             Data Core Network 
--    
--       ESN             Electronic Serial Number 
--    
--       FA              Foreign Agent 
--    
--       HA              Home Agent 
--    
--       IMSI            International Mobile Station  
--                       Identifier 
--    
--       IS              In service 
--    
--       IRM             International Roaming MIN 
--    
--       MC              Mobile Client 
--    
--       MIN             Mobile Identifier Number 
--    
--       MSID            Mobile Station Identifier 
--    
--       MS              Mobile Station 
--        
--       MN              Mobile Node 
--    
--       MoIP            Mobile IP 
--    
--       NAI             Network Access Identifier    
--       
--       OOS             Out of service 
--    
--       PCF             Packet Control Function 
--    
--       PDSN            Packet Data Serving Node 
--    
--       RAN             Radio Network 
--    
--       RP              Radio Packet 
--        
--       CANID           Current Access Network Identifier 
--        
--       PANID           Previous Access Network Identifier 
--        
--       BSID            Base Station Identifier 
--        
--       CVSE            Customer/Vendor Specific Extension 
--        
--       SO/So           Service Option. 
--                       The Service Option is a parameter  
--                       that specifies the air interface  
--                       between MS and RN for packet  
--                       data service. 
--                      
--    
--       Mobile Station/ A host or router that changes its  
--       Mobile Node     point of attachment from one  
--                       network or subnetwork to another. 
--                       A mobile node may change its  
--                       location without changing its 
--                       IP address. 
--    
--       Mobile IP       Protocol enhancements that allow  
--                       transparent routing of IP datagrams 
--                       to mobile nodes.  Refer to RFC 2002 
--                       for more details. 
--    
--       Mobile Client   A component which can interact with 
--                       MoIP entities such as Foreign Agent 
--                       and Home Agent. 
--    
--       Home Agent      A router on a mobile node's home  
--                       network which tunnels datagrams for  
--                       delivery to the mobile node when it 
--                       is away from home, and maintains  
--                       current location information for the 
--                       mobile node.  Refer to RFC 2002 for  
--                       more details. 
--    
--       Foreign Agent   A router on a mobile node's visited 
--                       network which provides routing  
--                       services to the mobile node while  
--                       registered.  The foreign agent  
--                       delivers datagrams to the mobile 
--                       node that were tunneled by the  
--                       mobile node's home agent.  For  
--                       datagrams sent by a mobile node, the 
--                       foreign agent may serve as a default 
--                       router for registered mobile nodes. 
--                       Refer to RFC 2002 for more details. 
--    
--       Proxy           Mechanism used by PDSN to provide  
--       Mobile Ip       MoIP services to a MS which does 
--                       not implement a mobile client.  PDSN 
--                       will be the proxy MC for the MS. 
--    
--       Simple IP       IP routing used by a MS when MoIP 
--                       services are not needed. 
--    
--       PDSN flow       A conversation between one user  
--                       (identified by an IP address) and  
--                       a HA using a PDSN session. 
--    
--       PDSN session    A PPP connection between a MS and  
--                       the PDSN.  One session may contain  
--                       one or multiple PDSN flows. 
--    
--       PCF             Physical interface connecting the  
--                       RAN to a PDSN 
--    
--       L2TP            Layer 2 Tunneling Protocol 
--                        
--       ICRQ            Incoming Call Request 
--       ICRP            Incoming Call Reply 
--       ICCN            Incoming Call Connected 
--       CDN             Call Disconnect.
--  RevDate
--    200407270000Z
--  RevDescr
--    Initial revision of this MIB module.

ccpcMIBObjects  OBJECT IDENTIFIER ::= { ciscoCdmaPdsnCrpMIB 1 }
ccpcSystemInfo  OBJECT IDENTIFIER ::= { ccpcMIBObjects 1 }
ccpcPerfStats   OBJECT IDENTIFIER ::= { ccpcMIBObjects 2 }
ccpcMIBConformance OBJECT IDENTIFIER ::= { ciscoCdmaPdsnCrpMIB 2 }
ccpcMIBCompliances OBJECT IDENTIFIER ::= { ccpcMIBConformance 1 }
ccpcMIBGroups   OBJECT IDENTIFIER ::= { ccpcMIBConformance 2 }

ccpcEnabled OBJECT-TYPE
    SYNTAX TruthValue
--    Rsyntax INTEGER {
--        true(1),
--        false(2)
--        }
    ACCESS read-only
    STATUS mandatory
    DESCRIPTION
        "An indication of whether CRP feature 
         is enabled."
    ::= { ccpcSystemInfo 1 }

ccpcSessionTotal OBJECT-TYPE
    SYNTAX Gauge
    ACCESS read-only
    STATUS mandatory
    DESCRIPTION
        "The total number of sessions currently established  
         with this system."
    ::= { ccpcSystemInfo 2 }

ccpcPcfPerfStatsTable OBJECT-TYPE
    SYNTAX SEQUENCE OF CcpcPcfPerfStatsEntry
    ACCESS not-accessible
    STATUS mandatory
    DESCRIPTION
        "PDSN PCF table.  Contains the reference about PCF in  
         the RAN currently interacting with the PDSN.  An entry 
         is created when a L2TP tunnel is established with 
         PCF.  An entry is deleted when the tunnel is deleted."
    ::= { ccpcPerfStats 1 }

ccpcPcfPerfStatsEntry OBJECT-TYPE
    SYNTAX CcpcPcfPerfStatsEntry
    ACCESS not-accessible
    STATUS mandatory
    DESCRIPTION
        "A conceptual row in the PCF CRP Stats table."
    INDEX { ccpcPcfIpAddressType, ccpcPcfIpAddress }
    ::= { ccpcPcfPerfStatsTable 1 }

CcpcPcfPerfStatsEntry ::= SEQUENCE {
    ccpcPcfIpAddressType InetAddressType,
    ccpcPcfIpAddress InetAddress,
    ccpcPcfRcvdIcrqs Counter,
    ccpcPcfAcptdIcrqs Counter,
    ccpcPcfDroppedIcrqs Counter,
    ccpcPcfSentIcrps Counter,
    ccpcPcfRcvdIccns Counter,
    ccpcPcfAcptdIccns Counter,
    ccpcPcfDroppedIccns Counter,
    ccpcPcfRcvdCdns Counter,
    ccpcPcfSentCdns Counter,
    ccpcPcfDroppedCdns Counter,
    ccpcPcfRcvdZlbs Counter,
    ccpcPcfSentZlbs Counter
    }

ccpcPcfIpAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS not-accessible
    STATUS mandatory
    DESCRIPTION
        "Represents the type of the address specified by 
        ccpcPcfIpAddress."
    ::= { ccpcPcfPerfStatsEntry 1 }

ccpcPcfIpAddress OBJECT-TYPE
    SYNTAX InetAddress
--    Rsyntax OCTET STRING(SIZE(0..255))
    ACCESS not-accessible
    STATUS mandatory
    DESCRIPTION
        "The IP address of the PCF that serves the  
         mobile node."
    ::= { ccpcPcfPerfStatsEntry 2 }

ccpcPcfRcvdIcrqs OBJECT-TYPE
    SYNTAX Counter
    ACCESS read-only
    STATUS mandatory
    DESCRIPTION
        "Total number of Incoming-Call-Requests received 
         to establish a L2TP session since the L2TP 
        tunnel was established with PCF."
    ::= { ccpcPcfPerfStatsEntry 3 }

ccpcPcfAcptdIcrqs OBJECT-TYPE
    SYNTAX Counter
    ACCESS read-only
    STATUS mandatory
    DESCRIPTION
        "Total number of Incoming-Call-Requests accepted 
         since the L2TP tunnel was established with PCF."
    ::= { ccpcPcfPerfStatsEntry 4 }

ccpcPcfDroppedIcrqs OBJECT-TYPE
    SYNTAX Counter
    ACCESS read-only
    STATUS mandatory
    DESCRIPTION
        "Total number of Incoming-Call-Requests denied 
         since the L2TP tunnel was established with PCF."
    ::= { ccpcPcfPerfStatsEntry 5 }

ccpcPcfSentIcrps OBJECT-TYPE
    SYNTAX Counter
    ACCESS read-only
    STATUS mandatory
    DESCRIPTION
        "Total number of Incoming-Call-Replies sent  
         since the L2TP tunnel was established with PCF."
    ::= { ccpcPcfPerfStatsEntry 6 }

ccpcPcfRcvdIccns OBJECT-TYPE
    SYNTAX Counter
    ACCESS read-only
    STATUS mandatory
    DESCRIPTION
        "Total number of Incoming-Call-Connected messages 
         received since the L2TP tunnel was established  
         with PCF."
    ::= { ccpcPcfPerfStatsEntry 7 }

ccpcPcfAcptdIccns OBJECT-TYPE
    SYNTAX Counter
    ACCESS read-only
    STATUS mandatory
    DESCRIPTION
        "Total number of Incoming-Call-Connected messages 
         accepted since the L2TP tunnel was established  
         with PCF."
    ::= { ccpcPcfPerfStatsEntry 8 }

ccpcPcfDroppedIccns OBJECT-TYPE
    SYNTAX Counter
    ACCESS read-only
    STATUS mandatory
    DESCRIPTION
        "Total number of Incoming-Call-Connected messages 
         accepted since the L2TP tunnel was established  
         with PCF."
    ::= { ccpcPcfPerfStatsEntry 9 }

ccpcPcfRcvdCdns OBJECT-TYPE
    SYNTAX Counter
    ACCESS read-only
    STATUS mandatory
    DESCRIPTION
        "Total number of Call-Disconnect-Notify messages  
         received to tear down L2TP session since the  
         L2TP tunnel was established with PCF."
    ::= { ccpcPcfPerfStatsEntry 10 }

ccpcPcfSentCdns OBJECT-TYPE
    SYNTAX Counter
    ACCESS read-only
    STATUS mandatory
    DESCRIPTION
        "Total number of Call-Disconnect-Notify messages 
         sent to PCF to tear down L2TP session since the  
         L2TP tunnel was established with PCF."
    ::= { ccpcPcfPerfStatsEntry 11 }

ccpcPcfDroppedCdns OBJECT-TYPE
    SYNTAX Counter
    ACCESS read-only
    STATUS mandatory
    DESCRIPTION
        "Total number of Call-Disconnect-Notify messages  
         dropped since the L2TP tunnel was established  
         with PCF."
    ::= { ccpcPcfPerfStatsEntry 12 }

ccpcPcfRcvdZlbs OBJECT-TYPE
    SYNTAX Counter
    ACCESS read-only
    STATUS mandatory
    DESCRIPTION
        "Total number of Zero-Length-Buffer messages received 
         since the L2TP tunnel was established with PCF."
    ::= { ccpcPcfPerfStatsEntry 13 }

ccpcPcfSentZlbs OBJECT-TYPE
    SYNTAX Counter
    ACCESS read-only
    STATUS mandatory
    DESCRIPTION
        "Total number of Zero-Length-Buffer messages sent 
         since the L2TP tunnel was established with PCF."
    ::= { ccpcPcfPerfStatsEntry 14 }

ccpcSystemGrp OBJECT IDENTIFIER ::= { ccpcMIBGroups 1 }
-- OBJECT-GROUP
--  Status
--    mandatory
--  Descr
--    A collection of objects needed for PDSN R2.1 network 
--     management.
--  objects
--    ccpcEnabled, ccpcSessionTotal

ccpcPerfGrp OBJECT IDENTIFIER ::= { ccpcMIBGroups 2 }
-- OBJECT-GROUP
--  Status
--    mandatory
--  Descr
--    A collection of objects needed for PDSN R1.2 network 
--     management.
--  objects
--    ccpcPcfRcvdIcrqs, ccpcPcfAcptdIcrqs, ccpcPcfDroppedIcrqs, 
--    ccpcPcfSentIcrps, ccpcPcfRcvdIccns, ccpcPcfAcptdIccns, 
--    ccpcPcfDroppedIccns, ccpcPcfRcvdCdns, ccpcPcfSentCdns, 
--    ccpcPcfDroppedCdns, ccpcPcfRcvdZlbs, ccpcPcfSentZlbs

ccpcMIBCompliance OBJECT IDENTIFIER ::= { ccpcMIBCompliances 1 }
-- MODULE-COMPLIANCE
--  Status
--    mandatory
--  Descr
--    The compliance statement for entities which implement 
--     the CDMA PDSN Management MIB for R2.0
--  Module
--    >>current<<
--   MandGroup
--    ccpcSystemGrp
--   MandGroup
--    ccpcPerfGrp


END
