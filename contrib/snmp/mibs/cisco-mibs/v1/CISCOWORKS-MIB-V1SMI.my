-- MIB file created 09-Jul-2003 09:31:49, by
--   SMICng version 2.2.11-beta(PRO)(Solaris), January 20, 2001. Enterprise key cisco.com

CISCOWORKS-MIB DEFINITIONS ::= BEGIN

-- From file: "CISCOWORKS-MIB.my"
-- Compile options "4 7 F H N W 03 06 0B 0G 0N 0T"

IMPORTS
    sysUpTime
            FROM RFC1213-MIB
    DisplayString
            FROM SNMPv2-TC-v1
    ciscoworks
            FROM CISCO-SMI
    OBJECT-TYPE
            FROM RFC-1212
    TRAP-TYPE
            FROM RFC-1215;

cwLogMIB OBJECT IDENTIFIER ::= { ciscoworks 1 }
-- MODULE-IDENTITY
--  LastUpdated
--    200302180000Z
--  OrgName
--    Cisco Systems, Inc.
--  ContactInfo
--           Cisco Systems
--            Customer Service
--         
--    Postal: 170 W. Tasman Drive
--            San Jose, CA 95134
--            USA
--    
--       Tel: +1 800 553-NETS
--    e-mail: cs-snmp@cisco.com
--  Descr
--     This MIB describes the traps and trap and trap 
--      variables used by CiscoWorks.  Originally the 
--      CiscoWorks classic nmlogd process forwarded 
--      messages logged by applications and devices to 
--      NM platforms as traps.  Now it is used by 
--      CiscoWorks Blue to send DLSw and APPN/SNASw 
--      traps to NM platforms.
--  RevDate
--    200302180000Z
--  RevDescr
--    Updated for SNMPv2 and for publishing.
--  RevDate
--    199504020000Z
--  RevDescr
--    Initial version of this MIB module.

cwLog           OBJECT IDENTIFIER ::= { cwLogMIB 1 }
cwTrapsPrefix   OBJECT IDENTIFIER ::= { cwLogMIB 2 }
cwMIBConform    OBJECT IDENTIFIER ::= { cwLogMIB 3 }
cwTraps         OBJECT IDENTIFIER ::= { cwTrapsPrefix 0 }
ciscoCwMIBCompliances OBJECT IDENTIFIER ::= { cwMIBConform 1 }
ciscoCwMIBGroups OBJECT IDENTIFIER ::= { cwMIBConform 2 }

cwLogDate OBJECT-TYPE
    SYNTAX DisplayString(SIZE(15))
--    Rsyntax OCTET STRING(SIZE(15))
    ACCESS read-only
    STATUS mandatory
    DESCRIPTION
        "Date in the format of 'MMM DD HH:MM:SS' when the message
         is logged.  The time zone used is configured on 
         CiscoWorks workstation."
    ::= { cwLog 1 }

cwLogSource OBJECT-TYPE
    SYNTAX INTEGER {
        other(1),
        ciscoworks(2),
        device(3)
        }
    ACCESS read-only
    STATUS mandatory
    DESCRIPTION
        "The source of the log message as follows. 
          'other'      - The source of the log entry is a source
                         other than ciscoworks application or 
                         Cisco device.
          'ciscoworks' - Indicates the message is generated by 
                         CiscoWorks applications (e.g. nmpolld).
          'device'     - Indicates the message is generated by 
                         Cisco devices."
    ::= { cwLog 2 }

cwLogApp OBJECT-TYPE
    SYNTAX DisplayString(SIZE(0..32))
--    Rsyntax OCTET STRING(SIZE(0..32))
    ACCESS read-only
    STATUS mandatory
    DESCRIPTION
        "The name of the application that generates the log 
         message If the message is generated by a device, this
         string will be empty."
    ::= { cwLog 3 }

cwLogMsg OBJECT-TYPE
    SYNTAX DisplayString(SIZE(0..255))
--    Rsyntax OCTET STRING(SIZE(0..255))
    ACCESS read-only
    STATUS mandatory
    DESCRIPTION
        "The text of the log message."
    ::= { cwLog 4 }

cwAppLogTrap TRAP-TYPE
-- Reverse mappable trap
    ENTERPRISE cwTrapsPrefix
    VARIABLES {
        sysUpTime, cwLogDate, cwLogSource, cwLogApp, cwLogMsg }
--  Status
--    mandatory
    DESCRIPTION
        "A cwAppLogTrap is sent by nmlogd when a CiscoWorks 
         application logs a message to system log file on 
         CiscoWorks workstation.  This is also sent by
         CiscoWorks Blue processes."
    ::= 1

cwDevLogTrap TRAP-TYPE
-- Reverse mappable trap
    ENTERPRISE cwTrapsPrefix
    VARIABLES {
        sysUpTime, cwLogDate, cwLogSource, cwLogMsg }
--  Status
--    mandatory
    DESCRIPTION
        "A cwDevLogTrap is sent by nmlogd when a device logs
         a message to system log file on CiscoWorks 
         workstation."
    ::= 2

ciscoCwObjectsGroup OBJECT IDENTIFIER ::= { ciscoCwMIBGroups 7 }
-- OBJECT-GROUP
--  Status
--    mandatory
--  Descr
--    Cisco Works Objects Group
--  objects
--    cwLogDate, cwLogSource, cwLogApp, cwLogMsg

ciscoCwNotificationsGroup OBJECT IDENTIFIER ::= { ciscoCwMIBGroups 12 }
-- NOTIFICATION-GROUP
--  Status
--    mandatory
--  Descr
--    Cisco Works Notification Objects Group.
--  notifications
--    cwAppLogTrap, cwDevLogTrap

ciscoCwMIBCompliance OBJECT IDENTIFIER ::= { ciscoCwMIBCompliances 1 }
-- MODULE-COMPLIANCE
--  Status
--    mandatory
--  Descr
--    The compliance statement for entities which 
--     implement the CISCOWORKS-MIB.
--  Module
--    >>current<<
--   MandGroup
--    ciscoCwObjectsGroup
--   MandGroup
--    ciscoCwNotificationsGroup


END
