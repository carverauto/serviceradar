-- MIB file created 06-Jan-2003 17:45:38, by
--   SMICng version 2.2.11-beta(PRO)(Solaris), January 20, 2001. Enterprise key cisco.com

CISCO-HC-ALARM-MIB DEFINITIONS ::= BEGIN

-- From file: "CISCO-HC-ALARM-MIB.my"
-- Compile options "4 7 F H N W 03 06 0B 0G 0N 0T"

IMPORTS
    RowStatus, VariablePointer, StorageType
            FROM SNMPv2-TC-v1
    CounterBasedGauge64
            FROM HCNUM-TC
    OwnerString, rmonEventGroup
            FROM RMON-MIB
    ciscoExperiment
            FROM CISCO-SMI
    Counter, Gauge
            FROM RFC1155-SMI
    OBJECT-TYPE
            FROM RFC-1212
    TRAP-TYPE
            FROM RFC-1215;

ciscoHcAlarmMIB OBJECT IDENTIFIER ::= { ciscoExperiment 93 }
-- MODULE-IDENTITY
--  LastUpdated
--    200210050000Z
--  OrgName
--    Cisco Systems, Inc.
--  ContactInfo
--         Cisco Systems 
--          Customer Service 
--    Postal: 170 W Tasman Drive 
--          San Jose, CA  95134 
--          USA 
--    Tel: +1 800 553 -NETS 
--    E-mail: cs-san@cisco.com
--  Descr
--    This module defines Remote Monitoring MIB extensions for 
--    High Capacity Alarms.
--  RevDate
--    200210050000Z
--  RevDescr
--    Initial version of the High Capacity Alarm MIB module. 
--    RFC Editor).

cHcAlarmObjects OBJECT IDENTIFIER ::= { ciscoHcAlarmMIB 1 }
cHcAlarmNotifications OBJECT IDENTIFIER ::= { ciscoHcAlarmMIB 2 }
cHcAlarmConformance OBJECT IDENTIFIER ::= { ciscoHcAlarmMIB 3 }
cHcAlarmControlObjects OBJECT IDENTIFIER ::= { cHcAlarmObjects 1 }
cHcAlarmCapabilitiesObjects OBJECT IDENTIFIER ::= { cHcAlarmObjects 2 }
cHcAlarmNotifPrefix OBJECT IDENTIFIER ::= { cHcAlarmNotifications 0 }
cHcAlarmCompliances OBJECT IDENTIFIER ::= { cHcAlarmConformance 1 }
cHcAlarmGroups  OBJECT IDENTIFIER ::= { cHcAlarmConformance 2 }

CHcValueStatus ::= INTEGER {
        valueNotAvailable(1),
        valuePositive(2),
        valueNegative(3)
        }
-- TEXTUAL-CONVENTION
--  Status
--    mandatory
--  Descr
--    This data type indicates the validity and sign of the data 
--    in associated object instances which represent the absolute 
--    value of a high capacity numeric quantity.  Such an object 
--    may be represented with one or more object instances. An 
--    object of type CHcValueStatus MUST be defined within the  
--    same structure as the object(s) representing the high  
--    capacity absolute value. 
--    
--    If the associated object instance(s) representing the high 
--    capacity absolute value could not be accessed during the 
--    sampling interval, and is therefore invalid, then the 
--    associated CHcValueStatus object will contain the value 
--    'valueNotAvailable(1)'. 
--    
--    If the associated object instance(s) representing the high 
--    capacity absolute value are valid and actual value of the 
--    sample is greater than or equal to zero, then the associated 
--    CHcValueStatus object will contain the value 
--    'valuePositive(2)'. 
--    
--    If the associated object instance(s) representing the high 
--    capacity absolute value are valid and the actual value of 
--    the sample is less than zero, then the associated 
--    CHcValueStatus object will contain the value 
--    'valueNegative(3)'.  The associated absolute value should be 
--    multiplied by -1 to obtain the true sample value.

cHcAlarmTable OBJECT-TYPE
    SYNTAX SEQUENCE OF CHcAlarmEntry
    ACCESS not-accessible
    STATUS mandatory
    DESCRIPTION
        "A list of entries for the configuration of high capacity 
        alarms."
    ::= { cHcAlarmControlObjects 1 }

cHcAlarmEntry OBJECT-TYPE
    SYNTAX CHcAlarmEntry
    ACCESS not-accessible
    STATUS mandatory
    DESCRIPTION
        "A conceptual row in the cHcAlarmTable. Entries are usually 
        created in this table by management application action, but 
        may also be created by agent action as well."
    INDEX { cHcAlarmIndex }
    ::= { cHcAlarmTable 1 }

CHcAlarmEntry ::= SEQUENCE {
    cHcAlarmIndex INTEGER,
    cHcAlarmInterval INTEGER,
    cHcAlarmVariable VariablePointer,
    cHcAlarmSampleType INTEGER,
    cHcAlarmAbsValue CounterBasedGauge64,
    cHcAlarmValueStatus CHcValueStatus,
    cHcAlarmStartupAlarm INTEGER,
    cHcAlarmRisingThreshAbsValueLo Gauge,
    cHcAlarmRisingThreshAbsValueHi Gauge,
    cHcAlarmRisingThresholdValStatus CHcValueStatus,
    cHcAlarmFallingThreshAbsValueLo Gauge,
    cHcAlarmFallingThreshAbsValueHi Gauge,
    cHcAlarmFallingThrsholdValStatus CHcValueStatus,
    cHcAlarmRisingEventIndex INTEGER,
    cHcAlarmFallingEventIndex INTEGER,
    cHcAlarmValueFailedAttempts Counter,
    cHcAlarmOwner OwnerString,
    cHcAlarmStorageType StorageType,
    cHcAlarmStatus RowStatus
    }

cHcAlarmIndex OBJECT-TYPE
    SYNTAX INTEGER(1..65535)
    ACCESS not-accessible
    STATUS mandatory
    DESCRIPTION
        "An arbitrary integer index value used to uniquely identify 
        this high capacity alarm entry."
    ::= { cHcAlarmEntry 1 }

cHcAlarmInterval OBJECT-TYPE
    SYNTAX INTEGER(1..2147483647)
--  Units
--    seconds
    ACCESS read-write
    STATUS mandatory
    DESCRIPTION
        "The interval in seconds over which the data is sampled and 
        compared with the rising and falling thresholds.  When 
        setting this variable, care should be taken in the case of 
        deltaValue sampling - the interval should be set short 
        enough that the sampled variable is very unlikely to 
        increase or decrease by more than 2^63 - 1 during a single 
        sampling interval. 
        
        This object may not be modified if the associated 
        cHcAlarmStatus object is equal to active(1)."
    ::= { cHcAlarmEntry 2 }

cHcAlarmVariable OBJECT-TYPE
    SYNTAX VariablePointer
--    Rsyntax OBJECT IDENTIFIER
    ACCESS read-write
    STATUS mandatory
    DESCRIPTION
        "The object identifier of the particular variable to be 
        sampled.  Only variables that resolve to an ASN.1 primitive 
        type of INTEGER (INTEGER, Integer32, Counter32, Counter64, 
        Gauge, or TimeTicks) may be sampled. 
        
        Because SNMP access control is articulated entirely in terms 
        of the contents of MIB views, no access control mechanism 
        exists that can restrict the value of this object to 
        identify only those objects that exist in a particular MIB 
        view.  Because there is thus no acceptable means of 
        restricting the read access that could be obtained through 
        the alarm mechanism, the probe must only grant write access 
        to this object in those views that have read access to all 
        objects on the probe. 
        
        This object may not be modified if the associated 
        cHcAlarmStatus object is equal to active(1)."
    ::= { cHcAlarmEntry 3 }

cHcAlarmSampleType OBJECT-TYPE
    SYNTAX INTEGER {
        absoluteValue(1),
        deltaValue(2)
        }
    ACCESS read-write
    STATUS mandatory
    DESCRIPTION
        "The method of sampling the selected variable and 
        calculating the value to be compared against the thresholds. 
        If the value of this object is absoluteValue(1), the value 
        of the selected variable will be compared directly with the 
        thresholds at the end of the sampling interval.  If the 
        value of this object is deltaValue(2), the value of the 
        selected variable at the last sample will be subtracted from 
        the current value, and the difference compared with the 
        thresholds. 
        
        If the associated cHcAlarmVariable instance could not be 
        obtained at the previous sample interval, then a delta 
        sample is not possible, and the value of the associated 
        cHcAlarmValueStatus object for this interval will be 
        valueNotAvailable(1). 
        
        This object may not be modified if the associated 
        cHcAlarmStatus object is equal to active(1)."
    ::= { cHcAlarmEntry 4 }

cHcAlarmAbsValue OBJECT-TYPE
    SYNTAX --?? syntax is not convertable to SMIv1
           CounterBasedGauge64
--    Rsyntax Counter64
    ACCESS read-only
    STATUS mandatory
    DESCRIPTION
        "The absolute value (i.e. unsigned value) of the 
        cHcAlarmVariable statistic during the last sampling period. 
        The value during the current sampling period is not made 
        available until the period is completed. 
        
        To obtain the true value for this sampling interval, the 
        associated instance of cHcAlarmValueStatus must be checked, 
        and the value of this object adjusted as necessary. 
        
        If the MIB instance could not be accessed during the 
        sampling interval, then this object will have a value of 
        zero and the associated instance of cHcAlarmValueStatus will 
        be set to 'valueNotAvailable(1)'."
    ::= { cHcAlarmEntry 5 }

cHcAlarmValueStatus OBJECT-TYPE
    SYNTAX CHcValueStatus
--    Rsyntax INTEGER {
--        valueNotAvailable(1),
--        valuePositive(2),
--        valueNegative(3)
--        }
    ACCESS read-only
    STATUS mandatory
    DESCRIPTION
        "This object indicates the validity and sign of the data for 
        the cHcAlarmAbsValue object, as described in the 
        CHcValueStatus textual convention."
    ::= { cHcAlarmEntry 6 }

cHcAlarmStartupAlarm OBJECT-TYPE
    SYNTAX INTEGER {
        risingAlarm(1),
        fallingAlarm(2),
        risingOrFallingAlarm(3)
        }
    ACCESS read-write
    STATUS mandatory
    DESCRIPTION
        "The alarm that may be sent when this entry is first set to 
        active.  If the first sample after this entry becomes active 
        is greater than or equal to the rising threshold and this 
        object is equal to risingAlarm(1) or 
        risingOrFallingAlarm(3), then a single rising alarm will be 
        generated.  If the first sample after this entry becomes 
        valid is less than or equal to the falling threshold and 
        this object is equal to fallingAlarm(2) or 
        risingOrFallingAlarm(3), then a single falling alarm will be 
        generated. 
        
        This object may not be modified if the associated 
        cHcAlarmStatus object is equal to active(1)."
    ::= { cHcAlarmEntry 7 }

cHcAlarmRisingThreshAbsValueLo OBJECT-TYPE
    SYNTAX Gauge
    ACCESS read-write
    STATUS mandatory
    DESCRIPTION
        "The lower 32 bits of the absolute value for threshold for 
        the sampled statistic.  The actual threshold value is 
        determined by the associated instances of the 
        cHcAlarmRisingThreshAbsValueHi and 
        cHcAlarmRisingThresholdValStatus objects, as follows: 
        
           ABS(threshold) = cHcAlarmRisingThreshAbsValueLo + 
                 (cHcAlarmRisingThreshAbsValueHi * 2^^32) 
        
        The absolute value of the threshold is adjusted as required, 
        as described in the CHcValueStatus textual convention. These 
        three object instances are conceptually combined to 
        represent the rising threshold for this entry. 
        
        When the current sampled value is greater than or equal to 
        this threshold, and the value at the last sampling interval 
        was less than this threshold, a single event will be 
        generated.  A single event will also be generated if the 
        first sample after this entry becomes valid is greater than 
        or equal to this threshold and the associated 
        cHcAlarmStartupAlarm is equal to risingAlarm(1) or 
        risingOrFallingAlarm(3). 
        
        After a rising event is generated, another such event will 
        not be generated until the sampled value falls below this 
        threshold and reaches the threshold identified by the 
        cHcAlarmFallingThreshAbsValueLo, 
        cHcAlarmFallingThreshAbsValueHi, and 
        cHcAlarmFallingThrsholdValStatus objects. 
        
        This object may not be modified if the associated 
        cHcAlarmStatus object is equal to active(1)."
    ::= { cHcAlarmEntry 8 }

cHcAlarmRisingThreshAbsValueHi OBJECT-TYPE
    SYNTAX Gauge
    ACCESS read-write
    STATUS mandatory
    DESCRIPTION
        "The upper 32 bits of the absolute value for threshold for 
        the sampled statistic.  The actual threshold value is 
        determined by the associated instances of the 
        cHcAlarmRisingThreshAbsValueLo and 
        cHcAlarmRisingThresholdValStatus objects, as follows: 
        
           ABS(threshold) = cHcAlarmRisingThreshAbsValueLo + 
                 (cHcAlarmRisingThreshAbsValueHi * 2^^32) 
        
        The absolute value of the threshold is adjusted as required, 
        as described in the CHcValueStatus textual convention. These 
        three object instances are conceptually combined to 
        represent the rising threshold for this entry. 
        
        When the current sampled value is greater than or equal to 
        this threshold, and the value at the last sampling interval 
        was less than this threshold, a single event will be 
        generated.  A single event will also be generated if the 
        first sample after this entry becomes valid is greater than 
        or equal to this threshold and the associated 
        cHcAlarmStartupAlarm is equal to risingAlarm(1) or 
        risingOrFallingAlarm(3). 
        
        After a rising event is generated, another such event will 
        not be generated until the sampled value falls below this 
        threshold and reaches the threshold identified by the 
        cHcAlarmFallingThreshAbsValueLo, 
        cHcAlarmFallingThreshAbsValueHi, and 
        cHcAlarmFallingThrsholdValStatus objects. 
        
        This object may not be modified if the associated 
        cHcAlarmStatus object is equal to active(1)."
    ::= { cHcAlarmEntry 9 }

cHcAlarmRisingThresholdValStatus OBJECT-TYPE
    SYNTAX CHcValueStatus
--    Rsyntax INTEGER {
--        valueNotAvailable(1),
--        valuePositive(2),
--        valueNegative(3)
--        }
    ACCESS read-write
    STATUS mandatory
    DESCRIPTION
        "This object indicates the sign of the data for the rising 
        threshold, as defined by the cHcAlarmRisingThresAbsValueLo 
        and cHcAlarmRisingThresAbsValueHi objects, as described in 
        the CHcValueStatus textual convention. 
        
        The enumeration 'valueNotAvailable(1)' is not allowed, and 
        the associated cHcAlarmStatus object cannot be equal to 
        'active(1)' if this object is set to this value. 
        
        This object may not be modified if the associated 
        cHcAlarmStatus object is equal to active(1)."
    ::= { cHcAlarmEntry 10 }

cHcAlarmFallingThreshAbsValueLo OBJECT-TYPE
    SYNTAX Gauge
    ACCESS read-write
    STATUS mandatory
    DESCRIPTION
        "The lower 32 bits of the absolute value for threshold for 
        the sampled statistic.  The actual threshold value is 
        determined by the associated instances of the 
        cHcAlarmFallingThreshAbsValueHi and 
        cHcAlarmFallingThrsholdValStatus objects, as follows: 
        
           ABS(threshold) = cHcAlarmFallingThreshAbsValueLo + 
                 (cHcAlarmFallingThreshAbsValueHi * 2^^32) 
        
        The absolute value of the threshold is adjusted as required, 
        as described in the CHcValueStatus textual convention. These 
        three object instances are conceptually combined to 
        represent the falling threshold for this entry. 
        
        When the current sampled value is less than or equal to this 
        threshold, and the value at the last sampling interval was 
        greater than this threshold, a single event will be 
        generated.  A single event will also be generated if the 
        first sample after this entry becomes valid is less than or 
        equal to this threshold and the associated 
        cHcAlarmStartupAlarm is equal to fallingAlarm(2) or 
        risingOrFallingAlarm(3). 
        
        After a falling event is generated, another such event will 
        not be generated until the sampled value rises above this 
        threshold and reaches the threshold identified by the 
        cHcAlarmRisingThreshAbsValueLo, 
        cHcAlarmRisingThreshAbsValueHi, and 
        cHcAlarmRisingThresholdValStatus objects. 
        
        This object may not be modified if the associated 
        cHcAlarmStatus object is equal to active(1)."
    ::= { cHcAlarmEntry 11 }

cHcAlarmFallingThreshAbsValueHi OBJECT-TYPE
    SYNTAX Gauge
    ACCESS read-write
    STATUS mandatory
    DESCRIPTION
        "The upper 32 bits of the absolute value for threshold for 
        the sampled statistic.  The actual threshold value is 
        determined by the associated instances of the 
        cHcAlarmFallingThreshAbsValueLo and 
        cHcAlarmFallingThrsholdValStatus objects, as follows: 
        
           ABS(threshold) = cHcAlarmFallingThreshAbsValueLo + 
                 (cHcAlarmFallingThreshAbsValueHi * 2^^32) 
        
        The absolute value of the threshold is adjusted as required, 
        as described in the CHcValueStatus textual convention. These 
        three object instances are conceptually combined to 
        represent the falling threshold for this entry. 
        
        When the current sampled value is less than or equal to this 
        threshold, and the value at the last sampling interval was 
        greater than this threshold, a single event will be 
        generated.  A single event will also be generated if the 
        first sample after this entry becomes valid is less than or 
        equal to this threshold and the associated 
        cHcAlarmStartupAlarm is equal to fallingAlarm(2) or 
        risingOrFallingAlarm(3). 
        
        After a falling event is generated, another such event will 
        not be generated until the sampled value rises above this 
        threshold and reaches the threshold identified by the 
        cHcAlarmRisingThreshAbsValueLo, 
        cHcAlarmRisingThreshAbsValueHi, and 
        cHcAlarmRisingThresholdValStatus objects. 
        
        This object may not be modified if the associated 
        cHcAlarmStatus object is equal to active(1)."
    ::= { cHcAlarmEntry 12 }

cHcAlarmFallingThrsholdValStatus OBJECT-TYPE
    SYNTAX CHcValueStatus
--    Rsyntax INTEGER {
--        valueNotAvailable(1),
--        valuePositive(2),
--        valueNegative(3)
--        }
    ACCESS read-write
    STATUS mandatory
    DESCRIPTION
        "This object indicates the sign of the data for the falling 
        threshold, as defined by the cHcAlarmFallingThreshAbsValueLo 
        and cHcAlarmFallingThreshAbsValueHi objects, as described in 
        the CHcValueStatus textual convention. 
        
        The enumeration 'valueNotAvailable(1)' is not allowed, and 
        the associated cHcAlarmStatus object cannot be equal to 
        'active(1)' if this object is set to this value. 
        
        This object may not be modified if the associated 
        cHcAlarmStatus object is equal to active(1)."
    ::= { cHcAlarmEntry 13 }

cHcAlarmRisingEventIndex OBJECT-TYPE
    SYNTAX INTEGER(0..65535)
    ACCESS read-write
    STATUS mandatory
    DESCRIPTION
        "The index of the eventEntry that is used when a rising 
        threshold is crossed.  The eventEntry identified by a 
        particular value of this index is the same as identified by 
        the same value of the eventIndex object.  If there is no 
        corresponding entry in the eventTable, then no association 
        exists.  In particular, if this value is zero, no associated 
        event will be generated, as zero is not a valid event index. 
        
        This object may not be modified if the associated 
        cHcAlarmStatus object is equal to active(1)."
    ::= { cHcAlarmEntry 14 }

cHcAlarmFallingEventIndex OBJECT-TYPE
    SYNTAX INTEGER(0..65535)
    ACCESS read-write
    STATUS mandatory
    DESCRIPTION
        "The index of the eventEntry that is used when a falling 
        threshold is crossed.  The eventEntry identified by a 
        particular value of this index is the same as identified by 
        the same value of the eventIndex object.  If there is no 
        corresponding entry in the eventTable, then no association 
        exists.  In particular, if this value is zero, no associated 
        event will be generated, as zero is not a valid event index. 
        
        This object may not be modified if the associated 
        cHcAlarmStatus object is equal to active(1)."
    ::= { cHcAlarmEntry 15 }

cHcAlarmValueFailedAttempts OBJECT-TYPE
    SYNTAX Counter
    ACCESS read-only
    STATUS mandatory
    DESCRIPTION
        "The number of times the associated cHcAlarmVariable  
        instance was polled on behalf of this cHcAlarmEntry, (while 
        in the active state) and the value was not available. This  
        counter may experience a discontinuity if the agent  
        restarts, indicated by the value of sysUpTime."
    ::= { cHcAlarmEntry 16 }

cHcAlarmOwner OBJECT-TYPE
    SYNTAX OwnerString
--    Rsyntax OCTET STRING(SIZE(0..127))
    ACCESS read-write
    STATUS mandatory
    DESCRIPTION
        "The entity that configured this entry and is therefore 
        using the resources assigned to it."
    ::= { cHcAlarmEntry 17 }

cHcAlarmStorageType OBJECT-TYPE
    SYNTAX StorageType
--    Rsyntax INTEGER {
--        other(1),
--        volatile(2),
--        nonVolatile(3),
--        permanent(4),
--        readOnly(5)
--        }
    ACCESS read-write
    STATUS mandatory
    DESCRIPTION
        "The type of non-volatile storage configured for this entry. 
        If this object is equal to 'permanent(4)', then the 
        associated cHcAlarmRisingEventIndex and 
        cHcAlarmFallingEventIndex objects must be writable."
    ::= { cHcAlarmEntry 18 }

cHcAlarmStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this row. 
        
        An entry MUST NOT exist in the active state unless all 
        objects in the entry have an appropriate value, as described 
        in the description clause for each writable object. 
        
        The cHcAlarmStatus object may be modified if the associated 
        instance of this object is equal to active(1), 
        notInService(2), or notReady(3).  All other writable objects 
        may be modified if the associated instance of this object is 
        equal to notInService(2) or notReady(3)."
    ::= { cHcAlarmEntry 19 }

cHcAlarmCapabilities OBJECT-TYPE
    SYNTAX OCTET STRING(SIZE(1..2))
        -- BITS are:
        --   cHcAlarmCreation(0)
        --   cHcAlarmNvStorage(1)
    ACCESS read-only
    STATUS mandatory
    DESCRIPTION
        "An indication of the high capacity alarm capabilities 
        supported by this agent. 
        
        If the 'cHcAlarmCreation' BIT is set, then this agent allows 
        NMS applications to create entries in the cHcAlarmTable. 
        
        If the 'cHcAlarmNvStorage' BIT is set, then this agent  
        allows entries in the cHcAlarmTable which will be recreated 
        after a system restart, as controlled by the  
        cHcAlarmStorageType object."
    ::= { cHcAlarmCapabilitiesObjects 1 }

cHcRisingAlarm TRAP-TYPE
-- Reverse mappable trap
    ENTERPRISE cHcAlarmNotifications
    VARIABLES {
        cHcAlarmVariable, cHcAlarmSampleType, cHcAlarmAbsValue, 
        cHcAlarmValueStatus, cHcAlarmRisingThreshAbsValueLo, 
        cHcAlarmRisingThreshAbsValueHi, 
        cHcAlarmRisingThresholdValStatus, cHcAlarmRisingEventIndex }
--  Status
--    mandatory
    DESCRIPTION
        "The SNMP notification that is generated when a high 
        capacity alarm entry crosses its rising threshold and 
        generates an event that is configured for sending SNMP 
        traps. 
        
        The cHcAlarmEntry object instances identified in the OBJECTS 
        clause are from the entry that causes this notification to 
        be generated."
    ::= 1

cHcFallingAlarm TRAP-TYPE
-- Reverse mappable trap
    ENTERPRISE cHcAlarmNotifications
    VARIABLES {
        cHcAlarmVariable, cHcAlarmSampleType, cHcAlarmAbsValue, 
        cHcAlarmValueStatus, cHcAlarmFallingThreshAbsValueLo, 
        cHcAlarmFallingThreshAbsValueHi, 
        cHcAlarmFallingThrsholdValStatus, cHcAlarmFallingEventIndex }
--  Status
--    mandatory
    DESCRIPTION
        "The SNMP notification that is generated when a high 
        capacity alarm entry crosses its falling threshold and 
        generates an event that is configured for sending SNMP 
        traps. 
        
        The cHcAlarmEntry object instances identified in the OBJECTS 
        clause are from the entry that causes this notification to 
        be generated."
    ::= 2

cHcAlarmControlGroup OBJECT IDENTIFIER ::= { cHcAlarmGroups 1 }
-- OBJECT-GROUP
--  Status
--    mandatory
--  Descr
--    A collection of objects used to configure entries for high 
--    capacity alarm threshold monitoring purposes.
--  objects
--    cHcAlarmInterval, cHcAlarmVariable, cHcAlarmSampleType, 
--    cHcAlarmAbsValue, cHcAlarmValueStatus, cHcAlarmStartupAlarm, 
--    cHcAlarmRisingThreshAbsValueLo, 
--    cHcAlarmRisingThreshAbsValueHi, 
--    cHcAlarmRisingThresholdValStatus, 
--    cHcAlarmFallingThreshAbsValueLo, 
--    cHcAlarmFallingThreshAbsValueHi, 
--    cHcAlarmFallingThrsholdValStatus, cHcAlarmRisingEventIndex, 
--    cHcAlarmFallingEventIndex, cHcAlarmValueFailedAttempts, 
--    cHcAlarmOwner, cHcAlarmStorageType, cHcAlarmStatus

cHcAlarmCapabilitiesGroup OBJECT IDENTIFIER ::= { cHcAlarmGroups 2 }
-- OBJECT-GROUP
--  Status
--    mandatory
--  Descr
--    A collection of objects used to indicate an agent's high 
--    capacity alarm threshold monitoring capabilities.
--  objects
--    cHcAlarmCapabilities

cHcAlarmNotificationsGroup OBJECT IDENTIFIER ::= { cHcAlarmGroups 3 }
-- NOTIFICATION-GROUP
--  Status
--    mandatory
--  Descr
--    A collection of notifications to deliver information 
--    related to a high capacity rising or falling threshold event 
--    to a management application.
--  notifications
--    cHcRisingAlarm, cHcFallingAlarm

cHcAlarmCompliance OBJECT IDENTIFIER ::= { cHcAlarmCompliances 1 }
-- MODULE-COMPLIANCE
--  Status
--    mandatory
--  Descr
--    Describes the requirements for conformance to the High 
--    Capacity Alarm MIB.
--  Module
--    >>current<<
--   MandGroup
--    cHcAlarmControlGroup
--   MandGroup
--    cHcAlarmCapabilitiesGroup
--   MandGroup
--    cHcAlarmNotificationsGroup
--  Module
--    RMON-MIB
--   MandGroup
--    rmonEventGroup


END
