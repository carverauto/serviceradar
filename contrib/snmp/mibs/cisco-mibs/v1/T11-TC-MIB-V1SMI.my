-- MIB file created 21-Sep-2009 18:07:45, by
--   SMICng version 2.2.11-beta(PRO)(Solaris), January 20, 2001. Enterprise key cisco.com

T11-TC-MIB DEFINITIONS ::= BEGIN

-- From file: "T11-TC-MIB.my"
-- Compile options "4 7 F H N O W 03 06 0B 0G 0N 0T"

IMPORTS
    mib-2
            FROM SNMPv2-SMI-v1
    Gauge
            FROM RFC1155-SMI;

t11TcMIB OBJECT IDENTIFIER ::= { mib-2 136 }
-- MODULE-IDENTITY
--  LastUpdated
--    200603020000Z
--  OrgName
--    T11
--  ContactInfo
--         Claudio DeSanti
--          Cisco Systems, Inc.
--          170 West Tasman Drive
--          San Jose, CA 95134 USA
--          Phone: +1 408 853-9172
--          EMail: cds@cisco.com
--    
--          Keith McCloghrie
--          Cisco Systems, Inc.
--          170 West Tasman Drive
--          San Jose, CA USA 95134
--          Phone: +1 408-526-5260
--          EMail: kzm@cisco.com
--  Descr
--    This module defines textual conventions used in T11 MIBs.
--    
--    Copyright (C) The Internet Society (2006).  This version
--    of this MIB module is part of RFC 4439;  see the RFC
--    itself for full legal notices.
--  RevDate
--    200603020000Z
--  RevDescr
--    Initial version of this MIB module, published as RFC 4439.

T11FabricIndex ::= Gauge(0..4095)
-- TEXTUAL-CONVENTION
--  DspHint
--    d
--  Status
--    mandatory
--  Descr
--    A Fabric Index that is used as a unique
--    index value to identify a particular Fabric within
--    one (or more) physical infrastructures.
--    
--    In an environment that is conformant to FC-SW-3, where
--    
--    there is always exactly one Fabric in a single physical
--    infrastructure, the value of this Fabric Index will
--    always be 1.
--    
--    However, the current standard, FC-SW-4, defines
--    how multiple Fabrics, each with its own management
--    instrumentation, could operate within one (or more)
--    physical infrastructures.  When such multiple Fabrics
--    are in use, this index value is used to uniquely
--    identify a particular Fabric within a physical
--    infrastructure.
--    
--    Note that the value of this textual convention has a
--    range of (0..4095) so as to be consistent with FC-SW-4,
--    which says that a 'VF_ID Bitmap' is 512 bytes long, with
--    the high-order bit representing VF_ID zero, and the
--    low-order bit representing 4095.
--  Refer
--    Fibre Channel - Switch Fabric - 4 (FC-SW-4),
--     ANSI INCITS 418-2006, section 6.1.27.2.4.


END
