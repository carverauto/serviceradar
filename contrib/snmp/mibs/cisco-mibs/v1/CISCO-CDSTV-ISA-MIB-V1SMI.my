-- MIB file created 03-Apr-2012 11:36:25, by
--   SMICng version 2.2.11-beta(PRO)(Solaris), January 20, 2001. Enterprise key cisco.com

CISCO-CDSTV-ISA-MIB DEFINITIONS ::= BEGIN

-- From file: "CISCO-CDSTV-ISA-MIB.my"
-- Compile options "4 7 F H N W 03 06 0B 0G 0N 0T"

IMPORTS
    SnmpAdminString
            FROM SNMP-FRAMEWORK-MIB
    InetAddressType, InetAddress, InetPortNumber
            FROM INET-ADDRESS-MIB
    TruthValue
            FROM SNMPv2-TC-v1
    TimeIntervalSec
            FROM CISCO-TC
    ciscoMgmt
            FROM CISCO-SMI
    Gauge
            FROM RFC1155-SMI
    OBJECT-TYPE
            FROM RFC-1212;

ciscoCdstvIsaMIB OBJECT IDENTIFIER ::= { ciscoMgmt 755 }
-- MODULE-IDENTITY
--  LastUpdated
--    201203130000Z
--  OrgName
--    Cisco Systems, Inc.
--  ContactInfo
--    Cisco Systems
--    Customer Service
--    
--    
--    Postal: 170 W Tasman Drive
--    
--    San Jose, CA  95134
--    
--    USA
--    
--    
--    Tel: +1 800 553-NETS
--    
--    
--    E-mail: cs-cds@cisco.com
--  Descr
--    This MIB module defines ISA configuration objects that
--    faciliate the management of the Cisco Content Delivery System
--    for TV (CDS-TV) product family.
--    
--    CDS-TV is a suite of products and software applications
--    providing ingest, storage, caching, streaming, playout and
--    on-demand delivery of video to television or set-top-box
--    clients.
--    
--    Abbreviations:
--    
--    ASI     Asynchronous Serial Interface
--    CDS     Content Delivery System
--    CORBA   Common Object Request Broker Architecture
--    ISA     Interactive Services Architecture
--    ISV     Integrated Streamer-Vault
--    FSI     File Service Interface
--    FTP     File Transfer Protocol
--    MPEG    Motion Picture Experts Group
--    MSA     Managed Services Architecture
--    LSCP    Lightweight Stream Control Protocol
--    RTI     Roome Telecommunications, Inc
--    RTSP    Real-Time Streaming Protocol
--    STB     Set-Top Box
--    TTV     Tampereen Tietoverkko, Finland
--    
--    Common terms:
--    
--    Catcher: Device responsible for receiving content (typically via
--    satellite dishes and antennae) from content providers or from a
--    Headend-In-The-Sky. 
--    
--    Content Ingest: Acquisition of content from a source such as a
--    catcher or an FTP server for storing it locally and making it
--    available to streamers as needed.
--    
--    Vault: Content delivery application responsible for ingesting
--    and storing video content and making it available to streamers.
--    
--    Streamer: Content delivery application responsible for streaming
--    video out to STB's.
--    
--    CorbaLoc: Corba Location (CorbaLoc) refers to a string object
--    reference for a CORBA object that looks similar to a URL and
--    provides a human readable and editable way to specify a location
--    where an IOR (Interoperable Object Reference) can be obtained.
--    An example of a corbaloc URL is:
--    'corbaloc::160.45.110.41:38693/StandardNS/NameServer-POA/_root'
--    
--    ISA: Time Warner Cable's Interactive Services Architecture is a
--    CORBA-based framework specifying interfaces for communication
--    between various applications and servers in a cable
--    video-on-demand ecosystem, including back-office, billing,
--    subscriber management and streaming.
--  RevDate
--    201203130000Z
--  RevDescr
--    CDS-TV 3.0 version of this MIB module
--  RevDate
--    201008100000Z
--  RevDescr
--    Initial version of this MIB module.

ciscoCdstvIsaMIBNotifs OBJECT IDENTIFIER ::= { ciscoCdstvIsaMIB 0 }
ciscoCdstvIsaMIBObjects OBJECT IDENTIFIER ::= { ciscoCdstvIsaMIB 1 }
ciscoCdstvIsaMIBConform OBJECT IDENTIFIER ::= { ciscoCdstvIsaMIB 2 }
cdstvISAConfigGeneral OBJECT IDENTIFIER ::= { ciscoCdstvIsaMIBObjects 1 }
cdstvISAConfigContentService OBJECT IDENTIFIER ::= { ciscoCdstvIsaMIBObjects 2 }
cdstvISAConfigStreamService OBJECT IDENTIFIER ::= { ciscoCdstvIsaMIBObjects 3 }
cdstvISAConfigNamingService OBJECT IDENTIFIER ::= { ciscoCdstvIsaMIBObjects 4 }
cdstvISAConfigNotifyService OBJECT IDENTIFIER ::= { ciscoCdstvIsaMIBObjects 5 }
cdstvISAConfigContentStore OBJECT IDENTIFIER ::= { ciscoCdstvIsaMIBObjects 6 }
cdstvISAConfigFactory OBJECT IDENTIFIER ::= { ciscoCdstvIsaMIBObjects 7 }
cdstvISAConfigContentFactory OBJECT IDENTIFIER ::= { ciscoCdstvIsaMIBObjects 8 }
cdstvISAConfigContentChannel OBJECT IDENTIFIER ::= { ciscoCdstvIsaMIBObjects 9 }
cdstvISAConfigStreamChannel OBJECT IDENTIFIER ::= { ciscoCdstvIsaMIBObjects 10 }
cdstvISAConfigEventChannel OBJECT IDENTIFIER ::= { ciscoCdstvIsaMIBObjects 11 }
cdstvISAConfigFTP OBJECT IDENTIFIER ::= { ciscoCdstvIsaMIBObjects 12 }
cdstvISAConfigLSCP OBJECT IDENTIFIER ::= { ciscoCdstvIsaMIBObjects 13 }
ciscoCdstvIsaMIBCompliances OBJECT IDENTIFIER ::= { ciscoCdstvIsaMIBConform 1 }
ciscoCdstvIsaMIBGroups OBJECT IDENTIFIER ::= { ciscoCdstvIsaMIBConform 2 }

cdstvISAConfigFileName OBJECT-TYPE
    SYNTAX SnmpAdminString
--    Rsyntax OCTET STRING(SIZE(0..255))
    ACCESS read-write
    STATUS mandatory
    DESCRIPTION
        "This object specifies the name of the file that stores the ISA
        configuration settings."
    ::= { cdstvISAConfigGeneral 1 }

cdstvISAConfigWebServicePort OBJECT-TYPE
    SYNTAX InetPortNumber
--    Rsyntax Gauge(0..65535)
    ACCESS read-write
    STATUS mandatory
    DESCRIPTION
        "This object specifies the port number used by web service
        processes listening on this server."
    ::= { cdstvISAConfigGeneral 2 }

cdstvISAConfigMSAEnabled OBJECT-TYPE
    SYNTAX TruthValue
--    Rsyntax INTEGER {
--        true(1),
--        false(2)
--        }
    ACCESS read-write
    STATUS mandatory
    DESCRIPTION
        "This object specifies whether Managed Services Architecture
        (MSA) is enabled or disabled.
        'true'  - MSA is enabled.
        'false' - MSA is disabled."
    ::= { cdstvISAConfigGeneral 3 }

cdstvISAConfigTmeEnabled OBJECT-TYPE
    SYNTAX TruthValue
--    Rsyntax INTEGER {
--        true(1),
--        false(2)
--        }
    ACCESS read-write
    STATUS deprecated
    DESCRIPTION
        "This object specifies whether Trick Mode Event (TME)
        enhancements are enabled.
        'true'  - TME enhancements enabled.
        'false' - TME enhancements disabled.
        cdstvISAConfigTmeEnabled object is superseded by cdstvISAConfigTmeStatus."
    ::= { cdstvISAConfigGeneral 4 }

cdstvISAConfigLoadQueryInterval OBJECT-TYPE
    SYNTAX TimeIntervalSec
--    Rsyntax Gauge
    ACCESS read-write
    STATUS mandatory
    DESCRIPTION
        "This object specifies the time interval (in seconds) between
        ISA process queries to the CDS database and other internal
        sources that aid in determining the management and distribution
        of streams and ingests."
    ::= { cdstvISAConfigGeneral 5 }

cdstvISAConfigPlayNumThreads OBJECT-TYPE
    SYNTAX Gauge
    ACCESS read-write
    STATUS mandatory
    DESCRIPTION
        "This object specifies the Lightweight Stream Control Protocol
        (LSCP) number of threads."
    ::= { cdstvISAConfigGeneral 6 }

cdstvISAConfigResourceMgrServiceName OBJECT-TYPE
    SYNTAX SnmpAdminString
--    Rsyntax OCTET STRING(SIZE(0..255))
    ACCESS read-write
    STATUS mandatory
    DESCRIPTION
        "This object specifies the name of the CDS Resource Service
        Manager that monitors orphan sessions."
    ::= { cdstvISAConfigGeneral 7 }

cdstvISAConfigServicePollTime OBJECT-TYPE
    SYNTAX TimeIntervalSec
--    Rsyntax Gauge
    ACCESS read-write
    STATUS mandatory
    DESCRIPTION
        "This object specifies the time interval (seconds) between
        polling for orphan sessions."
    ::= { cdstvISAConfigGeneral 8 }

cdstvISAConfigPreEncryptionEnabled OBJECT-TYPE
    SYNTAX TruthValue
--    Rsyntax INTEGER {
--        true(1),
--        false(2)
--        }
    ACCESS read-write
    STATUS mandatory
    DESCRIPTION
        "This object specifies whether pre-encryption support
        is enabled or disabled.
        'true' - Pre-encryption support is enabled.
        'false' - Pre-encryption support is disabled."
    ::= { cdstvISAConfigGeneral 9 }

cdstvISAConfigSessionGatewayTable OBJECT-TYPE
    SYNTAX SEQUENCE OF CdstvISAConfigSessionGatewayEntry
    ACCESS not-accessible
    STATUS mandatory
    DESCRIPTION
        "This table lists the Session Gateways Identifiers. This table
        is supported only for server roles 'streamer' and 'ISV',
        indicated by the object 'cdstvServerRole' in
        CISCO-CDSTV-SERVER-MIB."
    ::= { cdstvISAConfigGeneral 10 }

cdstvISAConfigSessionGatewayEntry OBJECT-TYPE
    SYNTAX CdstvISAConfigSessionGatewayEntry
    ACCESS not-accessible
    STATUS mandatory
    DESCRIPTION
        "An entry in the cdstvISAConfigSessionGatewayTable. A new row is
        created/destroyed in the cdstvISAConfigSessionGatewayTable
        whenever session gateway ID's are configured/unconfigured."
    INDEX { cdstvISAConfigSessionGatewayIndex }
    ::= { cdstvISAConfigSessionGatewayTable 1 }

CdstvISAConfigSessionGatewayEntry ::= SEQUENCE {
    cdstvISAConfigSessionGatewayIndex Gauge,
    cdstvISAConfigSessionGatewayID SnmpAdminString
    }

cdstvISAConfigSessionGatewayIndex OBJECT-TYPE
    SYNTAX Gauge
    ACCESS not-accessible
    STATUS mandatory
    DESCRIPTION
        "An index into the table containing Session Gateway
        ID's."
    ::= { cdstvISAConfigSessionGatewayEntry 1 }

cdstvISAConfigSessionGatewayID OBJECT-TYPE
    SYNTAX SnmpAdminString
--    Rsyntax OCTET STRING(SIZE(0..255))
    ACCESS read-write
    STATUS mandatory
    DESCRIPTION
        "This object specifies the Session Gateway ID used by the
        backoffice Session Gateway service for registering with the
        Name
        Service."
    ::= { cdstvISAConfigSessionGatewayEntry 2 }

cdstvISAConfigTmeStatus OBJECT-TYPE
    SYNTAX INTEGER {
        enableForOpenStream(1),
        enableForMystroMDN(2),
        disabled(3)
        }
    ACCESS read-write
    STATUS mandatory
    DESCRIPTION
        "This object specifies whether Trick Mode Event (TME)
        enhancements are Enabled or Disabled.
        enableForOpenStream(1) - Enable for OpenStream
        enableForMystroMDN(2) - Enable for MystroMDN
        disabled(3) - Disabled"
    ::= { cdstvISAConfigGeneral 11 }

cdstvISAConfigContentServiceMasterIpType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object specifies the type of the master IP address of the
        Content Service, which is specified by
        cdstvISAConfigContentServiceMasterIp."
    ::= { cdstvISAConfigContentService 1 }

cdstvISAConfigContentServiceMasterIp OBJECT-TYPE
    SYNTAX InetAddress
--    Rsyntax OCTET STRING(SIZE(0..255))
    ACCESS read-write
    STATUS mandatory
    DESCRIPTION
        "This object specifies the master IP address of the Content
        Service, which is the same for all Vault servers in an array.
        The type of the IP address is specified by
        cdstvISAConfigContentServiceMasterIpType."
    ::= { cdstvISAConfigContentService 2 }

cdstvISAConfigContentServiceMasterPort OBJECT-TYPE
    SYNTAX InetPortNumber
--    Rsyntax Gauge(0..65535)
    ACCESS read-write
    STATUS mandatory
    DESCRIPTION
        "This object specifies the port used by the master Content
        Service for controlling content."
    ::= { cdstvISAConfigContentService 3 }

cdstvISAConfigStreamServiceMasterIpType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object specifies the type of the configured IP address for
        the Stream Service Master, specified by
        cdstvISAConfigStreamServiceMasterIp."
    ::= { cdstvISAConfigStreamService 1 }

cdstvISAConfigStreamServiceMasterIp OBJECT-TYPE
    SYNTAX InetAddress
--    Rsyntax OCTET STRING(SIZE(0..255))
    ACCESS read-write
    STATUS mandatory
    DESCRIPTION
        "This object specifies the configured IP address for the Stream
        Service Master. The type of the IP address is specified by
        cdstvISAConfigStreamServiceMasterIpType."
    ::= { cdstvISAConfigStreamService 2 }

cdstvISAConfigStreamServiceMasterPort OBJECT-TYPE
    SYNTAX InetPortNumber
--    Rsyntax Gauge(0..65535)
    ACCESS read-write
    STATUS mandatory
    DESCRIPTION
        "This object specifies the port used by the Stream
        Service Master for controlling streams."
    ::= { cdstvISAConfigStreamService 3 }

cdstvISAConfigStreamServiceId OBJECT-TYPE
    SYNTAX SnmpAdminString
--    Rsyntax OCTET STRING(SIZE(0..255))
    ACCESS read-write
    STATUS mandatory
    DESCRIPTION
        "This object specifies the name of the Stream Service object
        that is registered with the OpenStream system."
    ::= { cdstvISAConfigStreamService 4 }

cdstvISAConfigStreamServiceKind OBJECT-TYPE
    SYNTAX SnmpAdminString
--    Rsyntax OCTET STRING(SIZE(0..255))
    ACCESS read-write
    STATUS mandatory
    DESCRIPTION
        "This object specifies the Service ID extension."
    ::= { cdstvISAConfigStreamService 5 }

cdstvISAConfigMasterNumThreads OBJECT-TYPE
    SYNTAX Gauge
    ACCESS read-write
    STATUS mandatory
    DESCRIPTION
        "This object specifies the stream service master number of
        threads."
    ::= { cdstvISAConfigStreamService 6 }

cdstvISAConfigStreamSourceIPConfig OBJECT-TYPE
    SYNTAX INTEGER {
        none(1),
        controlIp(2),
        defaultStreamSourceIp(3),
        streamInterfaceIp(4)
        }
    ACCESS read-write
    STATUS mandatory
    DESCRIPTION
        "This object specifies the type of the source IP address that is
        included in the session setup header. Possible values are: 
        none(1)                   - No IP address included in session
                                    setup header            
        controlIp(2)              - Control IP. 
        defaultStreamSourceIp(3)  - Default Stream Source IP. 
        streamInterfaceIp(4)      - Stream Interface IP."
    ::= { cdstvISAConfigStreamService 7 }

cdstvISAConfigStreamSourcePort OBJECT-TYPE
    SYNTAX InetPortNumber
--    Rsyntax Gauge(0..65535)
    ACCESS read-write
    STATUS mandatory
    DESCRIPTION
        "This object specifies the Streamer port used for streaming."
    ::= { cdstvISAConfigStreamService 8 }

cdstvISAConfigStreamingMode OBJECT-TYPE
    SYNTAX INTEGER {
        asi(1),
        gige(2)
        }
    ACCESS read-write
    STATUS mandatory
    DESCRIPTION
        "This object specifies the mode expected by the next device in
        the network. Possible options are: 
        asi(1)  - ASI mode.
        gige(2) - GigE mode."
    ::= { cdstvISAConfigStreamService 9 }

cdstvISAConfigStreamHeadendIdType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object specifies the type of the Headend ID for the
        Streaming Service, specified by cdstvISAConfigStreamHeadendId."
    ::= { cdstvISAConfigStreamService 10 }

cdstvISAConfigStreamHeadendId OBJECT-TYPE
    SYNTAX InetAddress
--    Rsyntax OCTET STRING(SIZE(0..255))
    ACCESS read-write
    STATUS mandatory
    DESCRIPTION
        "This object specifies the Headend ID for the Streaming
        Service. The address type of the Headend ID is specified by
        cdstvISAConfigStreamHeadendIdType."
    ::= { cdstvISAConfigStreamService 11 }

cdstvISAConfigStreamTimeout OBJECT-TYPE
    SYNTAX TimeIntervalSec
--    Rsyntax Gauge
    ACCESS read-write
    STATUS mandatory
    DESCRIPTION
        "This object specifies the maximum time allowed (seconds) before
        a stream object is played."
    ::= { cdstvISAConfigStreamService 12 }

cdstvISAConfigNamingServiceIpType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object specifies the type of the IP address of the CORBA
        Naming Service used by the OpenStream system. The IP address is
        specified by cdstvISAConfigNamingServiceIp."
    ::= { cdstvISAConfigNamingService 1 }

cdstvISAConfigNamingServiceIp OBJECT-TYPE
    SYNTAX InetAddress
--    Rsyntax OCTET STRING(SIZE(0..255))
    ACCESS read-write
    STATUS mandatory
    DESCRIPTION
        "This object specifies the IP address of the CORBA Naming
        Service used by the OpenStream system. The type of the address
        is specified by cdstvISAConfigNamingServiceIpType."
    ::= { cdstvISAConfigNamingService 2 }

cdstvISAConfigNamingServicePort OBJECT-TYPE
    SYNTAX InetPortNumber
--    Rsyntax Gauge(0..65535)
    ACCESS read-write
    STATUS mandatory
    DESCRIPTION
        "This object specifies the port of the Naming Service used by
        the OpenStream system."
    ::= { cdstvISAConfigNamingService 3 }

cdstvISAConfigNotifyServiceIpType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object specifies the type of the IP address of the CORBA
        Notification Service used by the OpenStream system. The IP
        address is specified by cdstvISAConfigNotifyServiceIp."
    ::= { cdstvISAConfigNotifyService 1 }

cdstvISAConfigNotifyServiceIp OBJECT-TYPE
    SYNTAX InetAddress
--    Rsyntax OCTET STRING(SIZE(0..255))
    ACCESS read-write
    STATUS mandatory
    DESCRIPTION
        "This object specifies the IP address of the CORBA Notification
        Service used by the OpenStream system. The type of this address
        is specified by cdstvISAConfigNotifyServiceIpType."
    ::= { cdstvISAConfigNotifyService 2 }

cdstvISAConfigNotifyServicePort OBJECT-TYPE
    SYNTAX InetPortNumber
--    Rsyntax Gauge(0..65535)
    ACCESS read-write
    STATUS mandatory
    DESCRIPTION
        "The port of the Notification Service used by the
        OpenStream system."
    ::= { cdstvISAConfigNotifyService 3 }

cdstvISAConfigNotifyServiceFactory OBJECT-TYPE
    SYNTAX SnmpAdminString
--    Rsyntax OCTET STRING(SIZE(0..255))
    ACCESS read-write
    STATUS mandatory
    DESCRIPTION
        "This object specifies the name used to locate the Notify
        Service through the 'corbaloc' protocol."
    ::= { cdstvISAConfigNotifyService 4 }

cdstvISAConfigContentStoreName OBJECT-TYPE
    SYNTAX SnmpAdminString
--    Rsyntax OCTET STRING(SIZE(0..255))
    ACCESS read-write
    STATUS mandatory
    DESCRIPTION
        "This object specifies the name of the CDS Content Store object
        that is registered with the OpenStream system."
    ::= { cdstvISAConfigContentStore 1 }

cdstvISAConfigContentStoreKind OBJECT-TYPE
    SYNTAX SnmpAdminString
--    Rsyntax OCTET STRING(SIZE(0..255))
    ACCESS read-write
    STATUS mandatory
    DESCRIPTION
        "This object specifies the content store ID extension."
    ::= { cdstvISAConfigContentStore 2 }

cdstvISAConfigContentNumThreads OBJECT-TYPE
    SYNTAX Gauge
    ACCESS read-write
    STATUS mandatory
    DESCRIPTION
        "This object specifies the content store number of threads."
    ::= { cdstvISAConfigContentStore 3 }

cdstvISAConfigFactoryId OBJECT-TYPE
    SYNTAX SnmpAdminString
--    Rsyntax OCTET STRING(SIZE(0..255))
    ACCESS read-write
    STATUS mandatory
    DESCRIPTION
        "This object specifies a name that identifies the root
        directory of the ISA factories where all factories need to
        register."
    ::= { cdstvISAConfigFactory 1 }

cdstvISAConfigFactoryKind OBJECT-TYPE
    SYNTAX SnmpAdminString
--    Rsyntax OCTET STRING(SIZE(0..255))
    ACCESS read-write
    STATUS mandatory
    DESCRIPTION
        "This object specifies the Factories ID extension."
    ::= { cdstvISAConfigFactory 2 }

cdstvISAConfigContentFactoryId OBJECT-TYPE
    SYNTAX SnmpAdminString
--    Rsyntax OCTET STRING(SIZE(0..255))
    ACCESS read-write
    STATUS mandatory
    DESCRIPTION
        "This object specifies the name of the CDS Content Store Factory
        that is registered with the OpenStream system."
    ::= { cdstvISAConfigContentFactory 1 }

cdstvISAConfigContentFactoryKind OBJECT-TYPE
    SYNTAX SnmpAdminString
--    Rsyntax OCTET STRING(SIZE(0..255))
    ACCESS read-write
    STATUS mandatory
    DESCRIPTION
        "This object specifies the content store factory ID extension."
    ::= { cdstvISAConfigContentFactory 2 }

cdstvISAConfigContentChannelId OBJECT-TYPE
    SYNTAX SnmpAdminString
--    Rsyntax OCTET STRING(SIZE(0..255))
    ACCESS read-write
    STATUS mandatory
    DESCRIPTION
        "This object specifies a name that identifies the Content
        Event Channel where all events concerning content objects are
        published."
    ::= { cdstvISAConfigContentChannel 1 }

cdstvISAConfigContentChannelKind OBJECT-TYPE
    SYNTAX SnmpAdminString
--    Rsyntax OCTET STRING(SIZE(0..255))
    ACCESS read-write
    STATUS mandatory
    DESCRIPTION
        "This object specifies the Event Channel Content ID extension."
    ::= { cdstvISAConfigContentChannel 2 }

cdstvISAConfigStreamChannelId OBJECT-TYPE
    SYNTAX SnmpAdminString
--    Rsyntax OCTET STRING(SIZE(0..255))
    ACCESS read-write
    STATUS mandatory
    DESCRIPTION
        "This object specifies a name that identifies the Stream
        Event Channel where all events concerning stream objects are
        published."
    ::= { cdstvISAConfigStreamChannel 1 }

cdstvISAConfigStreamChannelKind OBJECT-TYPE
    SYNTAX SnmpAdminString
--    Rsyntax OCTET STRING(SIZE(0..255))
    ACCESS read-write
    STATUS mandatory
    DESCRIPTION
        "This object specifies the Event Channel Stream ID extension."
    ::= { cdstvISAConfigStreamChannel 2 }

cdstvISAConfigEventChannelId OBJECT-TYPE
    SYNTAX SnmpAdminString
--    Rsyntax OCTET STRING(SIZE(0..255))
    ACCESS read-write
    STATUS mandatory
    DESCRIPTION
        "This object specifies a name that identifies the root
        directory of the Event Channel where all event channels need to
        register."
    ::= { cdstvISAConfigEventChannel 1 }

cdstvISAConfigEventChannelKind OBJECT-TYPE
    SYNTAX SnmpAdminString
--    Rsyntax OCTET STRING(SIZE(0..255))
    ACCESS read-write
    STATUS mandatory
    DESCRIPTION
        "This object specifies the directory extension of the Event
        Channel ID."
    ::= { cdstvISAConfigEventChannel 2 }

cdstvISAConfigEventChannelFactory OBJECT-TYPE
    SYNTAX SnmpAdminString
--    Rsyntax OCTET STRING(SIZE(0..255))
    ACCESS read-write
    STATUS mandatory
    DESCRIPTION
        "This object specifies a name that identifies the Event
        Channel Factory which is used to create event channels, and
        resolves the Notification Service name."
    ::= { cdstvISAConfigEventChannel 3 }

cdstvISAConfigFTPClientPort OBJECT-TYPE
    SYNTAX InetPortNumber
--    Rsyntax Gauge(0..65535)
    ACCESS read-write
    STATUS mandatory
    DESCRIPTION
        "This object specifies the port used when the Vault receives a
        request from the OpenStream system to act as an FTP client and
        sends an FTP get command to the content provider acting as an
        FTP server."
    ::= { cdstvISAConfigFTP 1 }

cdstvISAConfigFTPServerPort OBJECT-TYPE
    SYNTAX InetPortNumber
--    Rsyntax Gauge(0..65535)
    ACCESS read-write
    STATUS mandatory
    DESCRIPTION
        "This object specifies the port used when the Vault receives a
        request from the OpenStream system to act as an FTP server and 
        receives an FTP put command from the content provider  acting as
        an FTP client."
    ::= { cdstvISAConfigFTP 2 }

cdstvISAConfigFTPServerOutPort OBJECT-TYPE
    SYNTAX InetPortNumber
--    Rsyntax Gauge(0..65535)
    ACCESS read-write
    STATUS mandatory
    DESCRIPTION
        "This object specifies the configured ISA FTP Server Out Port."
    ::= { cdstvISAConfigFTP 3 }

cdstvISAConfigFTPClientNumAttempts OBJECT-TYPE
    SYNTAX Gauge
    ACCESS read-write
    STATUS mandatory
    DESCRIPTION
        "This object specifies the number of times the FTP client
        attempts to transfer the content file."
    ::= { cdstvISAConfigFTP 4 }

cdstvISAConfigFTPPollTimeout OBJECT-TYPE
    SYNTAX TimeIntervalSec
--    Rsyntax Gauge
    ACCESS read-write
    STATUS mandatory
    DESCRIPTION
        "This object specifies the idle seconds allowed before an FTP
        download is disconnected."
    ::= { cdstvISAConfigFTP 5 }

cdstvISAConfigLscpServerPort OBJECT-TYPE
    SYNTAX InetPortNumber
--    Rsyntax Gauge(0..65535)
    ACCESS read-write
    STATUS mandatory
    DESCRIPTION
        "This object specifies the port on the Streamer that is
        listening for LSCP commands from the set-top box."
    ::= { cdstvISAConfigLSCP 1 }

cdstvISAConfigLscpResponsePadding OBJECT-TYPE
    SYNTAX TruthValue
--    Rsyntax INTEGER {
--        true(1),
--        false(2)
--        }
    ACCESS read-write
    STATUS mandatory
    DESCRIPTION
        "This object specifies whether LSCP response padding is enabled.
        When enabled, three blank bytes are added to the end of the LSCP
        response.
        'true' - LSCP response padding is enabled.
        'false' - LSCP response padding is disabled."
    ::= { cdstvISAConfigLSCP 2 }

cdstvISAConfigfMsaLscpClientProto OBJECT-TYPE
    SYNTAX INTEGER {
        tvguide(1),
        rti(2),
        vodlink(3),
        cv(4),
        cisco(5),
        ttv(6),
        lscppauseateos(7)
        }
    ACCESS read-write
    STATUS mandatory
    DESCRIPTION
        "This object specifies the way LSCP clients communicate with the
        Streamer. Possible options are:
        tvguide(1) -  TV Guide
        rti(2)     -  RTI
        vodlink(3) -  VOD Link
        cv(4)      -  CableVision
        cisco(5)   -  Cisco
        ttv(6)     -  TTV
        lscppauseateos(7) - LSCP Pause at EOS"
    ::= { cdstvISAConfigLSCP 3 }

ciscoCdstvIsaGeneralGroup OBJECT IDENTIFIER ::= { ciscoCdstvIsaMIBGroups 1 }
-- OBJECT-GROUP
--  Status
--    deprecated
--  Descr
--    A collection of objects that provide general ISA configuration
--    information.
--    ciscoCdstvIsaGeneralGroup object is superseded by ciscoCdstvIsaGeneralGroup2.
--  objects
--    cdstvISAConfigFileName, cdstvISAConfigWebServicePort, 
--    cdstvISAConfigMSAEnabled, cdstvISAConfigTmeEnabled, 
--    cdstvISAConfigLoadQueryInterval, cdstvISAConfigPlayNumThreads, 
--    cdstvISAConfigResourceMgrServiceName, 
--    cdstvISAConfigServicePollTime, 
--    cdstvISAConfigPreEncryptionEnabled, 
--    cdstvISAConfigSessionGatewayID

ciscoCdstvIsaContentServiceGroup OBJECT IDENTIFIER ::= { ciscoCdstvIsaMIBGroups 2 }
-- OBJECT-GROUP
--  Status
--    mandatory
--  Descr
--    A collection of objects that provide ISA Content Service
--    configuration information.
--  objects
--    cdstvISAConfigContentServiceMasterIpType, 
--    cdstvISAConfigContentServiceMasterIp, 
--    cdstvISAConfigContentServiceMasterPort

ciscoCdstvIsaStreamServiceGroup OBJECT IDENTIFIER ::= { ciscoCdstvIsaMIBGroups 3 }
-- OBJECT-GROUP
--  Status
--    mandatory
--  Descr
--    A collection of objects that provide ISA Stream Service
--    configuration information.
--  objects
--    cdstvISAConfigStreamServiceMasterIpType, 
--    cdstvISAConfigStreamServiceMasterIp, 
--    cdstvISAConfigStreamServiceMasterPort, 
--    cdstvISAConfigStreamServiceId, 
--    cdstvISAConfigStreamServiceKind, 
--    cdstvISAConfigMasterNumThreads, 
--    cdstvISAConfigStreamSourceIPConfig, 
--    cdstvISAConfigStreamSourcePort, cdstvISAConfigStreamingMode, 
--    cdstvISAConfigStreamHeadendIdType, 
--    cdstvISAConfigStreamHeadendId, cdstvISAConfigStreamTimeout

ciscoCdstvIsaNamingServiceGroup OBJECT IDENTIFIER ::= { ciscoCdstvIsaMIBGroups 4 }
-- OBJECT-GROUP
--  Status
--    mandatory
--  Descr
--    A collection of objects that provide ISA Naming Service
--    configuration information.
--  objects
--    cdstvISAConfigNamingServiceIpType, 
--    cdstvISAConfigNamingServiceIp, 
--    cdstvISAConfigNamingServicePort

ciscoCdstvIsaNotifyServiceGroup OBJECT IDENTIFIER ::= { ciscoCdstvIsaMIBGroups 5 }
-- OBJECT-GROUP
--  Status
--    mandatory
--  Descr
--    A collection of objects that provide ISA Notify Service
--    configuration information.
--  objects
--    cdstvISAConfigNotifyServiceIpType, 
--    cdstvISAConfigNotifyServiceIp, 
--    cdstvISAConfigNotifyServicePort, 
--    cdstvISAConfigNotifyServiceFactory

ciscoCdstvIsaContentStoreGroup OBJECT IDENTIFIER ::= { ciscoCdstvIsaMIBGroups 6 }
-- OBJECT-GROUP
--  Status
--    mandatory
--  Descr
--    A collection of objects that provide ISA Content Store
--    configuration information.
--  objects
--    cdstvISAConfigContentStoreName, 
--    cdstvISAConfigContentStoreKind, 
--    cdstvISAConfigContentNumThreads

ciscoCdstvIsaFactoryGroup OBJECT IDENTIFIER ::= { ciscoCdstvIsaMIBGroups 7 }
-- OBJECT-GROUP
--  Status
--    mandatory
--  Descr
--    A collection of objects that provide ISA factory configuration
--    information.
--  objects
--    cdstvISAConfigFactoryId, cdstvISAConfigFactoryKind

ciscoCdstvIsaContentFactoryGroup OBJECT IDENTIFIER ::= { ciscoCdstvIsaMIBGroups 8 }
-- OBJECT-GROUP
--  Status
--    mandatory
--  Descr
--    A collection of objects that provide ISA Content Factory
--    configuration information.
--  objects
--    cdstvISAConfigContentFactoryId, 
--    cdstvISAConfigContentFactoryKind

ciscoCdstvIsaContentChannelGroup OBJECT IDENTIFIER ::= { ciscoCdstvIsaMIBGroups 9 }
-- OBJECT-GROUP
--  Status
--    mandatory
--  Descr
--    A collection of objects that provide ISA Content Channel
--    configuration information.
--  objects
--    cdstvISAConfigContentChannelId, 
--    cdstvISAConfigContentChannelKind

ciscoCdstvIsaStreamChannelGroup OBJECT IDENTIFIER ::= { ciscoCdstvIsaMIBGroups 10 }
-- OBJECT-GROUP
--  Status
--    mandatory
--  Descr
--    A collection of objects that provide ISA Stream Channel
--    configuration information.
--  objects
--    cdstvISAConfigStreamChannelId, 
--    cdstvISAConfigStreamChannelKind

ciscoCdstvIsaEventChannelGroup OBJECT IDENTIFIER ::= { ciscoCdstvIsaMIBGroups 11 }
-- OBJECT-GROUP
--  Status
--    mandatory
--  Descr
--    A collection of objects that provide ISA Event Channel
--    configuration information.
--  objects
--    cdstvISAConfigEventChannelId, cdstvISAConfigEventChannelKind, 
--    cdstvISAConfigEventChannelFactory

ciscoCdstvIsaFtpGroup OBJECT IDENTIFIER ::= { ciscoCdstvIsaMIBGroups 12 }
-- OBJECT-GROUP
--  Status
--    mandatory
--  Descr
--    A collection of objects that provide ISA FTP configuration
--    information.
--  objects
--    cdstvISAConfigFTPClientPort, cdstvISAConfigFTPServerPort, 
--    cdstvISAConfigFTPServerOutPort, 
--    cdstvISAConfigFTPClientNumAttempts, 
--    cdstvISAConfigFTPPollTimeout

ciscoCdstvIsaLscpGroup OBJECT IDENTIFIER ::= { ciscoCdstvIsaMIBGroups 13 }
-- OBJECT-GROUP
--  Status
--    mandatory
--  Descr
--    A collection of objects that provide ISA LSCP configuration
--    information.
--  objects
--    cdstvISAConfigLscpServerPort, 
--    cdstvISAConfigLscpResponsePadding, 
--    cdstvISAConfigfMsaLscpClientProto

ciscoCdstvIsaGeneralGroup2 OBJECT IDENTIFIER ::= { ciscoCdstvIsaMIBGroups 14 }
-- OBJECT-GROUP
--  Status
--    mandatory
--  Descr
--    A collection of objects that provide general ISA configuration
--    information.
--  objects
--    cdstvISAConfigFileName, cdstvISAConfigWebServicePort, 
--    cdstvISAConfigMSAEnabled, cdstvISAConfigLoadQueryInterval, 
--    cdstvISAConfigPlayNumThreads, 
--    cdstvISAConfigResourceMgrServiceName, 
--    cdstvISAConfigServicePollTime, 
--    cdstvISAConfigPreEncryptionEnabled, 
--    cdstvISAConfigSessionGatewayID, cdstvISAConfigTmeStatus

ciscoCdstvIsaMIBCompliance OBJECT IDENTIFIER ::= { ciscoCdstvIsaMIBCompliances 1 }
-- MODULE-COMPLIANCE
--  Status
--    deprecated
--  Descr
--    The compliance statement for the entities which
--    implement the Cisco CDS TV ISA MIB.
--  Module
--    >>current<<
--   MandGroup
--    ciscoCdstvIsaGeneralGroup
--   MandGroup
--    ciscoCdstvIsaContentServiceGroup
--   MandGroup
--    ciscoCdstvIsaStreamServiceGroup
--   MandGroup
--    ciscoCdstvIsaNamingServiceGroup
--   MandGroup
--    ciscoCdstvIsaNotifyServiceGroup
--   MandGroup
--    ciscoCdstvIsaContentStoreGroup
--   MandGroup
--    ciscoCdstvIsaFactoryGroup
--   MandGroup
--    ciscoCdstvIsaContentFactoryGroup
--   MandGroup
--    ciscoCdstvIsaContentChannelGroup
--   MandGroup
--    ciscoCdstvIsaStreamChannelGroup
--   MandGroup
--    ciscoCdstvIsaEventChannelGroup
--   MandGroup
--    ciscoCdstvIsaFtpGroup
--   MandGroup
--    ciscoCdstvIsaLscpGroup
--   ObjVar
--    cdstvISAConfigContentServiceMasterIpType
--   ObjVar
--    cdstvISAConfigContentServiceMasterIp
--   ObjVar
--    cdstvISAConfigContentServiceMasterPort
--   ObjVar
--    cdstvISAConfigStreamServiceMasterIpType
--   ObjVar
--    cdstvISAConfigStreamServiceMasterIp
--   ObjVar
--    cdstvISAConfigStreamServiceMasterPort
--   ObjVar
--    cdstvISAConfigStreamSourceIPConfig
--   ObjVar
--    cdstvISAConfigStreamingMode
--   ObjVar
--    cdstvISAConfigStreamHeadendIdType
--   ObjVar
--    cdstvISAConfigStreamHeadendId
--   ObjVar
--    cdstvISAConfigFileName
--   ObjVar
--    cdstvISAConfigWebServicePort
--   ObjVar
--    cdstvISAConfigFTPServerOutPort
--   ObjVar
--    cdstvISAConfigMSAEnabled
--   ObjVar
--    cdstvISAConfigTmeEnabled
--   ObjVar
--    cdstvISAConfigNamingServiceIpType
--   ObjVar
--    cdstvISAConfigNamingServiceIp
--   ObjVar
--    cdstvISAConfigNamingServicePort
--   ObjVar
--    cdstvISAConfigNotifyServiceIpType
--   ObjVar
--    cdstvISAConfigNotifyServiceIp
--   ObjVar
--    cdstvISAConfigNotifyServicePort
--   ObjVar
--    cdstvISAConfigNotifyServiceFactory
--   ObjVar
--    cdstvISAConfigEventChannelId
--   ObjVar
--    cdstvISAConfigEventChannelKind
--   ObjVar
--    cdstvISAConfigContentChannelId
--   ObjVar
--    cdstvISAConfigContentChannelKind
--   ObjVar
--    cdstvISAConfigStreamChannelId
--   ObjVar
--    cdstvISAConfigFactoryKind
--   ObjVar
--    cdstvISAConfigStreamChannelKind
--   ObjVar
--    cdstvISAConfigFactoryId
--   ObjVar
--    cdstvISAConfigEventChannelFactory
--   ObjVar
--    cdstvISAConfigLoadQueryInterval
--   ObjVar
--    cdstvISAConfigContentStoreName
--   ObjVar
--    cdstvISAConfigContentStoreKind
--   ObjVar
--    cdstvISAConfigContentFactoryId
--   ObjVar
--    cdstvISAConfigContentFactoryKind
--   ObjVar
--    cdstvISAConfigContentNumThreads
--   ObjVar
--    cdstvISAConfigFTPClientPort
--   ObjVar
--    cdstvISAConfigPreEncryptionEnabled
--   ObjVar
--    cdstvISAConfigFTPServerPort
--   ObjVar
--    cdstvISAConfigFTPClientNumAttempts
--   ObjVar
--    cdstvISAConfigFTPPollTimeout
--   ObjVar
--    cdstvISAConfigStreamServiceId
--   ObjVar
--    cdstvISAConfigStreamServiceKind
--   ObjVar
--    cdstvISAConfigMasterNumThreads
--   ObjVar
--    cdstvISAConfigPlayNumThreads
--   ObjVar
--    cdstvISAConfigLscpServerPort
--   ObjVar
--    cdstvISAConfigLscpResponsePadding
--   ObjVar
--    cdstvISAConfigfMsaLscpClientProto
--   ObjVar
--    cdstvISAConfigResourceMgrServiceName
--   ObjVar
--    cdstvISAConfigServicePollTime
--   ObjVar
--    cdstvISAConfigStreamTimeout
--   ObjVar
--    cdstvISAConfigStreamSourcePort
--   ObjVar
--    cdstvISAConfigSessionGatewayID

ciscoCdstvIsaMIBCompliance2 OBJECT IDENTIFIER ::= { ciscoCdstvIsaMIBCompliances 2 }
-- MODULE-COMPLIANCE
--  Status
--    mandatory
--  Descr
--    The compliance statement for the entities which
--    implement the Cisco CDS TV ISA MIB.
--  Module
--    >>current<<
--   MandGroup
--    ciscoCdstvIsaContentServiceGroup
--   MandGroup
--    ciscoCdstvIsaStreamServiceGroup
--   MandGroup
--    ciscoCdstvIsaNamingServiceGroup
--   MandGroup
--    ciscoCdstvIsaNotifyServiceGroup
--   MandGroup
--    ciscoCdstvIsaContentStoreGroup
--   MandGroup
--    ciscoCdstvIsaFactoryGroup
--   MandGroup
--    ciscoCdstvIsaContentFactoryGroup
--   MandGroup
--    ciscoCdstvIsaContentChannelGroup
--   MandGroup
--    ciscoCdstvIsaStreamChannelGroup
--   MandGroup
--    ciscoCdstvIsaEventChannelGroup
--   MandGroup
--    ciscoCdstvIsaFtpGroup
--   MandGroup
--    ciscoCdstvIsaLscpGroup
--   MandGroup
--    ciscoCdstvIsaGeneralGroup2
--   ObjVar
--    cdstvISAConfigContentServiceMasterIpType
--   ObjVar
--    cdstvISAConfigContentServiceMasterIp
--   ObjVar
--    cdstvISAConfigContentServiceMasterPort
--   ObjVar
--    cdstvISAConfigStreamServiceMasterIpType
--   ObjVar
--    cdstvISAConfigStreamServiceMasterIp
--   ObjVar
--    cdstvISAConfigStreamServiceMasterPort
--   ObjVar
--    cdstvISAConfigStreamSourceIPConfig
--   ObjVar
--    cdstvISAConfigStreamingMode
--   ObjVar
--    cdstvISAConfigStreamHeadendIdType
--   ObjVar
--    cdstvISAConfigStreamHeadendId
--   ObjVar
--    cdstvISAConfigFileName
--   ObjVar
--    cdstvISAConfigWebServicePort
--   ObjVar
--    cdstvISAConfigFTPServerOutPort
--   ObjVar
--    cdstvISAConfigMSAEnabled
--   ObjVar
--    cdstvISAConfigTmeStatus
--   ObjVar
--    cdstvISAConfigNamingServiceIpType
--   ObjVar
--    cdstvISAConfigNamingServiceIp
--   ObjVar
--    cdstvISAConfigNamingServicePort
--   ObjVar
--    cdstvISAConfigNotifyServiceIpType
--   ObjVar
--    cdstvISAConfigNotifyServiceIp
--   ObjVar
--    cdstvISAConfigNotifyServicePort
--   ObjVar
--    cdstvISAConfigNotifyServiceFactory
--   ObjVar
--    cdstvISAConfigEventChannelId
--   ObjVar
--    cdstvISAConfigEventChannelKind
--   ObjVar
--    cdstvISAConfigContentChannelId
--   ObjVar
--    cdstvISAConfigContentChannelKind
--   ObjVar
--    cdstvISAConfigStreamChannelId
--   ObjVar
--    cdstvISAConfigFactoryKind
--   ObjVar
--    cdstvISAConfigStreamChannelKind
--   ObjVar
--    cdstvISAConfigFactoryId
--   ObjVar
--    cdstvISAConfigEventChannelFactory
--   ObjVar
--    cdstvISAConfigLoadQueryInterval
--   ObjVar
--    cdstvISAConfigContentStoreName
--   ObjVar
--    cdstvISAConfigContentStoreKind
--   ObjVar
--    cdstvISAConfigContentFactoryId
--   ObjVar
--    cdstvISAConfigContentFactoryKind
--   ObjVar
--    cdstvISAConfigContentNumThreads
--   ObjVar
--    cdstvISAConfigFTPClientPort
--   ObjVar
--    cdstvISAConfigPreEncryptionEnabled
--   ObjVar
--    cdstvISAConfigFTPServerPort
--   ObjVar
--    cdstvISAConfigFTPClientNumAttempts
--   ObjVar
--    cdstvISAConfigFTPPollTimeout
--   ObjVar
--    cdstvISAConfigStreamServiceId
--   ObjVar
--    cdstvISAConfigStreamServiceKind
--   ObjVar
--    cdstvISAConfigMasterNumThreads
--   ObjVar
--    cdstvISAConfigPlayNumThreads
--   ObjVar
--    cdstvISAConfigLscpServerPort
--   ObjVar
--    cdstvISAConfigLscpResponsePadding
--   ObjVar
--    cdstvISAConfigfMsaLscpClientProto
--   ObjVar
--    cdstvISAConfigResourceMgrServiceName
--   ObjVar
--    cdstvISAConfigServicePollTime
--   ObjVar
--    cdstvISAConfigStreamTimeout
--   ObjVar
--    cdstvISAConfigStreamSourcePort
--   ObjVar
--    cdstvISAConfigSessionGatewayID


END
