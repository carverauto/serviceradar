-- MIB file created 18-Sep-2014 07:14:32, by
--   SMICng version 2.2.11-beta(PRO)(Solaris), January 20, 2001. Enterprise key cisco.com

CISCO-ENTITY-QFP-MIB DEFINITIONS ::= BEGIN

-- From file: "CISCO-ENTITY-QFP-MIB.my"
-- Compile options "4 7 F H N W 03 06 0B 0G 0N 0T"

IMPORTS
    DateAndTime, TruthValue
            FROM SNMPv2-TC-v1
    entPhysicalIndex
            FROM ENTITY-MIB
    CounterBasedGauge64
            FROM HCNUM-TC
    ciscoMgmt
            FROM CISCO-SMI
    Counter, Gauge
            FROM RFC1155-SMI
    OBJECT-TYPE
            FROM RFC-1212
    TRAP-TYPE
            FROM RFC-1215;

ciscoEntityQfpMIB OBJECT IDENTIFIER ::= { ciscoMgmt 715 }
-- MODULE-IDENTITY
--  LastUpdated
--    201406180000Z
--  OrgName
--    Cisco Systems, Inc.
--  ContactInfo
--    Cisco Systems
--    Customer Service
--    
--    
--    Postal: 170 W Tasman Drive
--    
--    San Jose, CA  95134
--    
--    USA
--    
--    
--    Tel: +1 800 553-NETS
--    
--    
--    E-mail: cs-snmp@cisco.com
--  Descr
--    This MIB module defines managed objects that facilitate the
--    management of Quantum Flow Processors (QFP), which are listed
--    in the ENTITY-MIB (RFC 4133) entPhysicalTable as an
--    entPhysicalClass of 'cpu'.
--    
--    The Quantum Flow Processors (QFP) technology is an architecture
--    family developed by Cisco, which has fully integrated and
--    programmable networking chip set that controls different
--    functions of a system such as packet forwarding.
--    
--    This module contains objects to monitor various QFP
--    statistics such as system, utilization, memory, etc.
--    
--    The utilization statistics can be used for future capacity
--    planning. The calculation of this statistics may vary by
--    devices which host QFPs, hence the user must refer to the
--    specific device document of interest for the exact method
--    of calculation. The utilization statistics have the following
--    terminology.
--    
--    o Input - Communication channel where packets arrive on the
--              QFP.
--    
--    o Output - Communication channel where packets leave the QFP.
--    
--    o Priority - A classification applied to packets indicating
--                 they should be treated with greater urgency.
--    
--    o Non-Priority - A classification applied to packets indicating
--                     they should be treated with lesser urgency.
--    
--    o Processing Load - The percentage of time over some interval
--                        that the QFP has spent forwarding packets,
--                        relative to the total time spent both 
--                        forwarding packets and being idle.
--  RevDate
--    201406180000Z
--  RevDescr
--    Added the following objects to the MIB.
--    
--    ceqfpThroughputLicensedBW, ceqfpThroughputLevel,
--    ceqfpThroughputInterval, ceqfpThroughputThreshold,
--    ceqfpThroughputAvgRate to ceqfpThroughputTable.
--    
--    Added ceqfpThroughputNotifEnabled to ciscoEntityQfpNotif group.
--    
--    Added ceqfpThroughputNotif as a new notification to the MIB.
--    
--    Added a new MIB conform group, ceqfpThroughputGroup for the new
--    objects.
--    
--    Also modified the ciscoEntityQfpMIBComplianceRev2 to add the new
--    group ceqfpThroughputGroup.
--  RevDate
--    201206060000Z
--  RevDescr
--    Added the following new objects to the
--    ceqfpMemoryResourceTable.
--    ceqfpMemoryResTotalOvrflw, ceqfpMemoryHCResTotal,
--    ceqfpMemoryResInUseOvrflw, ceqfpMemoryHCResInUse,
--    ceqfpMemoryResFreeOvrflw,ceqfpMemoryHCResFree,
--    ceqfpMemoryResLowFreeWatermarkOvrflw,
--    ceqfpMemoryHCResLowFreeWatermark.
--    
--    Added following new compliance groups.
--    ciscoEntityQfpMemoryResourceOvrflwGroup,
--    ciscoEntityQfpMemoryHCResourceGroup.
--    
--    Added new compliance ciscoEntityQfpMIBComplianceRev2 which
--    deprecates ciscoEntityQfpMIBComplianceRev1.
--  RevDate
--    200912020000Z
--  RevDescr
--    Initial version of this MIB module.

ciscoEntityQfpMIBNotifs OBJECT IDENTIFIER ::= { ciscoEntityQfpMIB 0 }
ciscoEntityQfpMIBObjects OBJECT IDENTIFIER ::= { ciscoEntityQfpMIB 1 }
ciscoEntityQfpMIBConform OBJECT IDENTIFIER ::= { ciscoEntityQfpMIB 2 }
ciscoEntityQfp  OBJECT IDENTIFIER ::= { ciscoEntityQfpMIBObjects 1 }
ciscoEntityQfpNotif OBJECT IDENTIFIER ::= { ciscoEntityQfpMIBObjects 2 }
ciscoEntityQfpMIBCompliances OBJECT IDENTIFIER ::= { ciscoEntityQfpMIBConform 1 }
ciscoEntityQfpMIBGroups OBJECT IDENTIFIER ::= { ciscoEntityQfpMIBConform 2 }

CiscoQfpPacketRate ::= --?? syntax is not convertable to SMIv1
        Counter
-- TEXTUAL-CONVENTION
--  DspHint
--    d
--  Status
--    mandatory
--  Descr
--    An estimate of throughput in units of packets per second.
--    
--    The CiscoQfpPacketRate type represents a non-negative integer,
--    which may increase or decrease, but shall never exceed a 
--    maximum value, nor fall below a minimum value of Counter.
--    The Counter syntax is used for encoding rules.

CiscoQfpBitRate ::= --?? syntax is not convertable to SMIv1
        Counter
-- TEXTUAL-CONVENTION
--  DspHint
--    d
--  Status
--    mandatory
--  Descr
--    An estimate of throughput in units of bits per second.
--    
--    The CiscoQfpBitRate type represents a non-negative integer,
--    which may increase or decrease, but shall never exceed a 
--    maximum value, nor fall below a minimum value of Counter.
--    The Counter syntax is used for encoding rules.

CiscoQfpTimeInterval ::= INTEGER {
        fiveSeconds(1),
        oneMinute(2),
        fiveMinutes(3),
        sixtyMinutes(4)
        }
-- TEXTUAL-CONVENTION
--  Status
--    mandatory
--  Descr
--    An enumerated integer-value describing the available interval
--    values for which the periodic statistics are to be collected.
--    
--    fiveSeconds (1)   - Interval to collect last 5 seconds       
--                        statistics
--    oneMinute(2)      - Interval to collect last 1 minute
--                        statistics
--    fiveMinutes(3)    - Interval to collect last 5 minutes       
--                        statistics
--    sixtyMinutes(4)   - Interval to collect last 60 minutes       
--                        statistics

CiscoQfpMemoryResource ::= INTEGER {
        dram(1)
        }
-- TEXTUAL-CONVENTION
--  Status
--    mandatory
--  Descr
--    An enumerated integer-value describing various memory resources
--    used by the QFP.
--    
--    dram (1) - Dynamic Random Access Memory (DRAM) memory resource

ceqfpSystemTable OBJECT-TYPE
    SYNTAX SEQUENCE OF CeqfpSystemEntry
    ACCESS not-accessible
    STATUS mandatory
    DESCRIPTION
        "This table maintains the QFP system information for each QFP
        physical entity.
        
        An agent creates a conceptual row to this table corresponding
        to a QFP physical entity upon detection of a physical entity
        supporting the QFP system information.
        
        An agent destroys a conceptual row from this table       
        corresponding to a QFP physical entity upon removal
        of the QFP host physical entity."
    ::= { ciscoEntityQfp 1 }

ceqfpSystemEntry OBJECT-TYPE
    SYNTAX CeqfpSystemEntry
    ACCESS not-accessible
    STATUS mandatory
    DESCRIPTION
        "A conceptual row in the ceqfpSystemTable. There is an entry
        in this table for each QFP entity, as defined by a value of
        entPhysicalIndex."
    INDEX { entPhysicalIndex }
    ::= { ceqfpSystemTable 1 }

CeqfpSystemEntry ::= SEQUENCE {
    ceqfpSystemTrafficDirection INTEGER,
    ceqfpSystemState INTEGER,
    ceqfpNumberSystemLoads Counter,
    ceqfpSystemLastLoadTime DateAndTime
    }

ceqfpSystemTrafficDirection OBJECT-TYPE
    SYNTAX INTEGER {
        none(1),
        ingress(2),
        egress(3),
        both(4)
        }
    ACCESS read-only
    STATUS mandatory
    DESCRIPTION
        "This object represents the traffic direction that this QFP is
        assigned to process. The enumerated values are described below.
        
        none (1)    - The QFP is not assigned to processes any traffic
                      yet
        ingress (2) - The QFP processes inbound traffic
        egress (3)  - The QFP processes outbound traffic
        both (4)    - The QFP processes both inbound and outbound
                      traffic"
    ::= { ceqfpSystemEntry 1 }

ceqfpSystemState OBJECT-TYPE
    SYNTAX INTEGER {
        unknown(1),
        reset(2),
        init(3),
        active(4),
        activeSolo(5),
        standby(6),
        hotStandby(7)
        }
    ACCESS read-only
    STATUS mandatory
    DESCRIPTION
        "This object represents the current QFP state. The enumerated
        values are described below.
        
        unknown (1)    - The state of the QFP is unknown
        reset (2)      - The QFP is reset
        init (3)       - The QFP is being initialized
        active (4)     - The QFP is active in a system with redundant
                         QFP
        activeSolo (5) - The QFP is active and there is no redundant
                         QFP in the system
        standby (6)    - The QFP is standby in a redundant system.
        hotStandby (7) - The QFP is standby and synchronized with
                         active, so that a switchover in this state
                         will preserve state of the active. Stateful 
                         datapath features are synchronized between the
                         active QFP and standby QFP"
    ::= { ceqfpSystemEntry 2 }

ceqfpNumberSystemLoads OBJECT-TYPE
    SYNTAX Counter
    ACCESS read-only
    STATUS mandatory
    DESCRIPTION
        "This object represents the number of times the QFP is loaded,
        since the QFP host is up."
    ::= { ceqfpSystemEntry 3 }

ceqfpSystemLastLoadTime OBJECT-TYPE
    SYNTAX DateAndTime
--    Rsyntax OCTET STRING(SIZE(8|11))
    ACCESS read-only
    STATUS mandatory
    DESCRIPTION
        "This object represents the QFP last load time."
    ::= { ceqfpSystemEntry 4 }

ceqfpFiveSecondUtilAlgo OBJECT-TYPE
    SYNTAX INTEGER {
        unknown(1),
        fiveSecSample(2)
        }
    ACCESS read-only
    STATUS mandatory
    DESCRIPTION
        "This objects represents the method used to calculate 5 Second
        interval utilization data. The enumerated values are described
        below.
        
        unknown       (1) - The calculation method is unknown
        fiveSecSample (2) - The value is calculated based on the last
                            5 second sampling period of utilization
                            data."
    ::= { ciscoEntityQfp 2 }

ceqfpOneMinuteUtilAlgo OBJECT-TYPE
    SYNTAX INTEGER {
        unknown(1),
        fiveSecSMA(2)
        }
    ACCESS read-only
    STATUS mandatory
    DESCRIPTION
        "This objects represents the method used to calculate 1 Minute
        interval utilization data. The enumerated values are described
        below.
        
        unknown    (1) - The calculation method is unknown
        fiveSecSMA (2) - The value is calculated using Simple Moving  
                         Average of last 12 five seconds utilization
                         data."
    ::= { ciscoEntityQfp 3 }

ceqfpFiveMinutesUtilAlgo OBJECT-TYPE
    SYNTAX INTEGER {
        unknown(1),
        fiveSecSMA(2)
        }
    ACCESS read-only
    STATUS mandatory
    DESCRIPTION
        "This objects represents the method used to calculate 5 Minutes
        interval utilization data. The enumerated values are described
        below.
        
        unknown    (1) - The calculation method is unknown
        fiveSecSMA (2) - The value is calculated using Simple Moving  
                         Average of last 60 five seconds utilization
                         data."
    ::= { ciscoEntityQfp 4 }

ceqfpSixtyMinutesUtilAlgo OBJECT-TYPE
    SYNTAX INTEGER {
        unknown(1),
        fiveSecSMA(2)
        }
    ACCESS read-only
    STATUS mandatory
    DESCRIPTION
        "This objects represents the method used to calculate 60 Minutes
        interval utilization data. The enumerated values are described
        below.
        
        unknown    (1) - The calculation method is unknown
        fiveSecSMA (1) - The value is calculated using Simple Moving  
                         Average of last 720 five seconds utilization
                         data."
    ::= { ciscoEntityQfp 5 }

ceqfpUtilizationTable OBJECT-TYPE
    SYNTAX SEQUENCE OF CeqfpUtilizationEntry
    ACCESS not-accessible
    STATUS mandatory
    DESCRIPTION
        "This table maintains the utilization statistics collected
        by each QFP physical entity at various time interval such as
        last 5 seconds, 1 minute, etc.
        
        An agent creates a conceptual row to this table corresponding
        to a QFP physical entity for a time interval upon detection of
        a physical entity supporting the utilization statistics for a
        time interval.
        
        The agent destroys a conceptual row from this table       
        corresponding to a QFP physical entity for a time interval
        upon removal of the QFP host physical entity or it does not
        receive the utilization statistics update for a certain time
        period. The time period to wait before deleting an entry from
        this table would be the discretion of the supporting device."
    ::= { ciscoEntityQfp 6 }

ceqfpUtilizationEntry OBJECT-TYPE
    SYNTAX CeqfpUtilizationEntry
    ACCESS not-accessible
    STATUS mandatory
    DESCRIPTION
        "A conceptual row in the ceqfpUtilizationTable. There is
        an entry in this table for each QFP entity by a value of
        entPhysicalIndex and the supported time interval by a value 
        of ceqfpUtilTimeInterval.
        
        The method of utilization data calculation for each interval
        period can be identified through the respective interval
        scalar objects. For example the utilizaiton data calculation
        method for 'fiveSecond' interval can be identified by
        ceqfpFiveSecondUtilAlgo."
    INDEX { entPhysicalIndex, ceqfpUtilTimeInterval }
    ::= { ceqfpUtilizationTable 1 }

CeqfpUtilizationEntry ::= SEQUENCE {
    ceqfpUtilTimeInterval CiscoQfpTimeInterval,
    ceqfpUtilInputPriorityPktRate CiscoQfpPacketRate,
    ceqfpUtilInputPriorityBitRate CiscoQfpBitRate,
    ceqfpUtilInputNonPriorityPktRate CiscoQfpPacketRate,
    ceqfpUtilInputNonPriorityBitRate CiscoQfpBitRate,
    ceqfpUtilInputTotalPktRate CiscoQfpPacketRate,
    ceqfpUtilInputTotalBitRate CiscoQfpBitRate,
    ceqfpUtilOutputPriorityPktRate CiscoQfpPacketRate,
    ceqfpUtilOutputPriorityBitRate CiscoQfpBitRate,
    ceqfpUtilOutputNonPriorityPktRate CiscoQfpPacketRate,
    ceqfpUtilOutputNonPriorityBitRate CiscoQfpBitRate,
    ceqfpUtilOutputTotalPktRate CiscoQfpPacketRate,
    ceqfpUtilOutputTotalBitRate CiscoQfpBitRate,
    ceqfpUtilProcessingLoad Gauge
    }

ceqfpUtilTimeInterval OBJECT-TYPE
    SYNTAX CiscoQfpTimeInterval
--    Rsyntax INTEGER {
--        fiveSeconds(1),
--        oneMinute(2),
--        fiveMinutes(3),
--        sixtyMinutes(4)
--        }
    ACCESS not-accessible
    STATUS mandatory
    DESCRIPTION
        "This object identifies the time interval for which the
        utilization statistics being collected. The interval 
        values can be 5 second, 1 minute, etc. as specified in 
        the CiscoQfpTimeInterval."
    ::= { ceqfpUtilizationEntry 1 }

ceqfpUtilInputPriorityPktRate OBJECT-TYPE
    SYNTAX --?? syntax is not convertable to SMIv1
           CiscoQfpPacketRate
--    Rsyntax Counter
--  Units
--    packets per second
    ACCESS read-only
    STATUS mandatory
    DESCRIPTION
        "This object represents the QFP input channel priority packet
        rate during this interval."
    ::= { ceqfpUtilizationEntry 2 }

ceqfpUtilInputPriorityBitRate OBJECT-TYPE
    SYNTAX --?? syntax is not convertable to SMIv1
           CiscoQfpBitRate
--    Rsyntax Counter
--  Units
--    bits per second
    ACCESS read-only
    STATUS mandatory
    DESCRIPTION
        "This object represents the QFP input channel priority bit rate
        during this interval."
    ::= { ceqfpUtilizationEntry 3 }

ceqfpUtilInputNonPriorityPktRate OBJECT-TYPE
    SYNTAX --?? syntax is not convertable to SMIv1
           CiscoQfpPacketRate
--    Rsyntax Counter
--  Units
--    packets per second
    ACCESS read-only
    STATUS mandatory
    DESCRIPTION
        "This object represents the QFP input channel non-priority
        packet rate during this interval."
    ::= { ceqfpUtilizationEntry 4 }

ceqfpUtilInputNonPriorityBitRate OBJECT-TYPE
    SYNTAX --?? syntax is not convertable to SMIv1
           CiscoQfpBitRate
--    Rsyntax Counter
--  Units
--    bits per second
    ACCESS read-only
    STATUS mandatory
    DESCRIPTION
        "This object represents the QFP input channel non-priority
        bit rate during this interval."
    ::= { ceqfpUtilizationEntry 5 }

ceqfpUtilInputTotalPktRate OBJECT-TYPE
    SYNTAX --?? syntax is not convertable to SMIv1
           CiscoQfpPacketRate
--    Rsyntax Counter
--  Units
--    packets per second
    ACCESS read-only
    STATUS mandatory
    DESCRIPTION
        "This object represents the QFP input channel total packet rate
        during this interval, which includes both priority and
        non-priority input packet rate."
    ::= { ceqfpUtilizationEntry 6 }

ceqfpUtilInputTotalBitRate OBJECT-TYPE
    SYNTAX --?? syntax is not convertable to SMIv1
           CiscoQfpBitRate
--    Rsyntax Counter
--  Units
--    bits per second
    ACCESS read-only
    STATUS mandatory
    DESCRIPTION
        "This object represents the QFP input channel total bit rate
        during this interval, which includes both priority and
        non-priority input bit rate."
    ::= { ceqfpUtilizationEntry 7 }

ceqfpUtilOutputPriorityPktRate OBJECT-TYPE
    SYNTAX --?? syntax is not convertable to SMIv1
           CiscoQfpPacketRate
--    Rsyntax Counter
--  Units
--    packets per second
    ACCESS read-only
    STATUS mandatory
    DESCRIPTION
        "This object represents the QFP output channel priority packet
        rate during this interval."
    ::= { ceqfpUtilizationEntry 8 }

ceqfpUtilOutputPriorityBitRate OBJECT-TYPE
    SYNTAX --?? syntax is not convertable to SMIv1
           CiscoQfpBitRate
--    Rsyntax Counter
--  Units
--    bits per second
    ACCESS read-only
    STATUS mandatory
    DESCRIPTION
        "This object represents the QFP output channel priority bit
        rate during this interval."
    ::= { ceqfpUtilizationEntry 9 }

ceqfpUtilOutputNonPriorityPktRate OBJECT-TYPE
    SYNTAX --?? syntax is not convertable to SMIv1
           CiscoQfpPacketRate
--    Rsyntax Counter
--  Units
--    packets per second
    ACCESS read-only
    STATUS mandatory
    DESCRIPTION
        "This object represents the QFP output channel non-priority
        packet rate during this interval."
    ::= { ceqfpUtilizationEntry 10 }

ceqfpUtilOutputNonPriorityBitRate OBJECT-TYPE
    SYNTAX --?? syntax is not convertable to SMIv1
           CiscoQfpBitRate
--    Rsyntax Counter
--  Units
--    bits per second
    ACCESS read-only
    STATUS mandatory
    DESCRIPTION
        "This object represents the QFP output channel non-priority
        bit rate during this interval."
    ::= { ceqfpUtilizationEntry 11 }

ceqfpUtilOutputTotalPktRate OBJECT-TYPE
    SYNTAX --?? syntax is not convertable to SMIv1
           CiscoQfpPacketRate
--    Rsyntax Counter
--  Units
--    packets per second
    ACCESS read-only
    STATUS mandatory
    DESCRIPTION
        "This object represents the QFP output channel total packet rate
        during this interval, which includes both priority and
        non-priority output packet rate."
    ::= { ceqfpUtilizationEntry 12 }

ceqfpUtilOutputTotalBitRate OBJECT-TYPE
    SYNTAX --?? syntax is not convertable to SMIv1
           CiscoQfpBitRate
--    Rsyntax Counter
--  Units
--    bits per second
    ACCESS read-only
    STATUS mandatory
    DESCRIPTION
        "This object represents the QFP output channel total bit rate
        during this interval, which includes both priority and
        non-priority bit rate."
    ::= { ceqfpUtilizationEntry 13 }

ceqfpUtilProcessingLoad OBJECT-TYPE
    SYNTAX Gauge(0..100)
--  Units
--    percent
    ACCESS read-only
    STATUS mandatory
    DESCRIPTION
        "This object represents the QFP processing load during this
        interval."
    ::= { ceqfpUtilizationEntry 14 }

ceqfpMemoryResourceTable OBJECT-TYPE
    SYNTAX SEQUENCE OF CeqfpMemoryResourceEntry
    ACCESS not-accessible
    STATUS mandatory
    DESCRIPTION
        "This table maintains the memory resources statistics for
        each QFP physical entity.
        
        An agent creates a conceptual row to this table corresponding
        to a QFP physical entity and its supported memory resource type
        upon detection of a physical entity supporting the memory 
        resource statistics for a memory resource type.
        
        An agent destroys a conceptual row from this table       
        corresponding to a QFP physical entity and its supported
        memory resource type upon removal of the QFP host physical
        entity or it does not receive memory resource statistics
        update for a certain time period. The time period to wait
        before deleting an entry from this table would be the
        discretion of the supporting device."
    ::= { ciscoEntityQfp 7 }

ceqfpMemoryResourceEntry OBJECT-TYPE
    SYNTAX CeqfpMemoryResourceEntry
    ACCESS not-accessible
    STATUS mandatory
    DESCRIPTION
        "A conceptual row in the ceqfpMemoryResourceTable. There
        is an entry in this table for each QFP entity by a value 
        of entPhysicalIndex and the supported memory resource type 
        by a value of ceqfpMemoryResType."
    INDEX { entPhysicalIndex, ceqfpMemoryResType }
    ::= { ceqfpMemoryResourceTable 1 }

CeqfpMemoryResourceEntry ::= SEQUENCE {
    ceqfpMemoryResType CiscoQfpMemoryResource,
    ceqfpMemoryResTotal Gauge,
    ceqfpMemoryResInUse Gauge,
    ceqfpMemoryResFree Gauge,
    ceqfpMemoryResLowFreeWatermark Gauge,
    ceqfpMemoryResRisingThreshold Gauge,
    ceqfpMemoryResFallingThreshold Gauge,
    ceqfpMemoryResTotalOvrflw Gauge,
    ceqfpMemoryHCResTotal CounterBasedGauge64,
    ceqfpMemoryResInUseOvrflw Gauge,
    ceqfpMemoryHCResInUse CounterBasedGauge64,
    ceqfpMemoryResFreeOvrflw Gauge,
    ceqfpMemoryHCResFree CounterBasedGauge64,
    ceqfpMemoryResLowFreeWatermarkOvrflw Gauge,
    ceqfpMemoryHCResLowFreeWatermark CounterBasedGauge64
    }

ceqfpMemoryResType OBJECT-TYPE
    SYNTAX CiscoQfpMemoryResource
--    Rsyntax INTEGER {
--        dram(1)
--        }
    ACCESS not-accessible
    STATUS mandatory
    DESCRIPTION
        "This object indicates the type of the memory resource used by
        the QFP. This object is one of the indices to uniquely identify
        the QFP memory resource type."
    ::= { ceqfpMemoryResourceEntry 1 }

ceqfpMemoryResTotal OBJECT-TYPE
    SYNTAX Gauge
--  Units
--    kilo bytes
    ACCESS read-only
    STATUS mandatory
    DESCRIPTION
        "This object represents total memory available on this memory
        resource."
    ::= { ceqfpMemoryResourceEntry 2 }

ceqfpMemoryResInUse OBJECT-TYPE
    SYNTAX Gauge
--  Units
--    kilo bytes
    ACCESS read-only
    STATUS mandatory
    DESCRIPTION
        "This object represents the memory which is currently under use
        on this memory resource."
    ::= { ceqfpMemoryResourceEntry 3 }

ceqfpMemoryResFree OBJECT-TYPE
    SYNTAX Gauge
--  Units
--    kilo bytes
    ACCESS read-only
    STATUS mandatory
    DESCRIPTION
        "This object represents the memory which is currently free on
        this memory resource."
    ::= { ceqfpMemoryResourceEntry 4 }

ceqfpMemoryResLowFreeWatermark OBJECT-TYPE
    SYNTAX Gauge
--  Units
--    kilo bytes
    ACCESS read-only
    STATUS mandatory
    DESCRIPTION
        "This object represents lowest free water mark on this memory
        resource."
    ::= { ceqfpMemoryResourceEntry 5 }

ceqfpMemoryResRisingThreshold OBJECT-TYPE
    SYNTAX Gauge(0..100)
--  Units
--    percent
    ACCESS read-write
    STATUS mandatory
    DESCRIPTION
        "This object represents the rising threshold value for this
        memory resource. A value of zero means that the rising
        threshold is not supported for this memory resource.
        
        The value of this object can not be set to lower than or
        equal to ceqfpMemoryResFallingThreshold.
        
        A rising (ceqfpMemoryResRisingThreshNotif) notification
        will be generated, whenever the memory resource usage
        (ceqfpMemoryHCResInUse) is equal to or greater than this
        value.
        
        After a rising notification is generated, another such 
        notification will not be generated until the 
        ceqfpMemoryResInUse falls below this value and reaches 
        the ceqfpMemoryResFallingThreshold."
    DEFVAL { 90 }
    ::= { ceqfpMemoryResourceEntry 6 }

ceqfpMemoryResFallingThreshold OBJECT-TYPE
    SYNTAX Gauge(0..100)
--  Units
--    percent
    ACCESS read-write
    STATUS mandatory
    DESCRIPTION
        "This object represents the falling threshold value for this
        memory resource. A value of zero means that the falling
        threshold is not supported for this memory resource.
        
        The value of this object can not be set to higher than or
        equal to ceqfpMemoryResRisingThreshold.
        
        A falling (ceqfpMemoryResRisingThreshNotif) notification 
        will be generated, whenever the memory resource usage
        (ceqfpMemoryHCResInUse) is equal to or lesser than this value.
        
        After a falling notification is generated, another 
        such notification will not be generated until the 
        ceqfpMemoryResInUse rises above this value and reaches 
        the ceqfpMemoryResRisingThreshold."
    DEFVAL { 85 }
    ::= { ceqfpMemoryResourceEntry 7 }

ceqfpMemoryResTotalOvrflw OBJECT-TYPE
    SYNTAX Gauge
--  Units
--    kilo bytes
    ACCESS read-only
    STATUS mandatory
    DESCRIPTION
        "This object represents the upper 32-bit of
        ceqfpMemoryResTotal.
        This object needs to be supported only when the value of
        ceqfpMemoryResTotal exceeds 32-bit, otherwise this object value
        would be set to 0."
    ::= { ceqfpMemoryResourceEntry 8 }

ceqfpMemoryHCResTotal OBJECT-TYPE
    SYNTAX --?? syntax is not convertable to SMIv1
           CounterBasedGauge64
--    Rsyntax Counter
--  Units
--    kilo bytes
    ACCESS read-only
    STATUS mandatory
    DESCRIPTION
        "This object is a 64-bit version of ceqfpMemoryResTotal."
    ::= { ceqfpMemoryResourceEntry 9 }

ceqfpMemoryResInUseOvrflw OBJECT-TYPE
    SYNTAX Gauge
--  Units
--    kilo bytes
    ACCESS read-only
    STATUS mandatory
    DESCRIPTION
        "This object represents the upper 32-bit of
        ceqfpMemoryResInUse.
        This object needs to be supported only when the value of
        ceqfpMemoryResInUse exceeds 32-bit, otherwise this object value
        would be set to 0."
    ::= { ceqfpMemoryResourceEntry 10 }

ceqfpMemoryHCResInUse OBJECT-TYPE
    SYNTAX --?? syntax is not convertable to SMIv1
           CounterBasedGauge64
--    Rsyntax Counter
--  Units
--    kilo bytes
    ACCESS read-only
    STATUS mandatory
    DESCRIPTION
        "This object is a 64-bit version of ceqfpMemoryInRes."
    ::= { ceqfpMemoryResourceEntry 11 }

ceqfpMemoryResFreeOvrflw OBJECT-TYPE
    SYNTAX Gauge
--  Units
--    kilo bytes
    ACCESS read-only
    STATUS mandatory
    DESCRIPTION
        "This object represents the upper 32-bit of ceqfpMemoryResFree.
        This object needs to be supported only when the value of
        ceqfpMemoryResFree exceeds 32-bit, otherwise this object value
        would be set to 0."
    ::= { ceqfpMemoryResourceEntry 12 }

ceqfpMemoryHCResFree OBJECT-TYPE
    SYNTAX --?? syntax is not convertable to SMIv1
           CounterBasedGauge64
--    Rsyntax Counter
--  Units
--    kilo bytes
    ACCESS read-only
    STATUS mandatory
    DESCRIPTION
        "This object is a 64-bit version of ceqfpMemoryResFree."
    ::= { ceqfpMemoryResourceEntry 13 }

ceqfpMemoryResLowFreeWatermarkOvrflw OBJECT-TYPE
    SYNTAX Gauge
--  Units
--    kilo bytes
    ACCESS read-only
    STATUS mandatory
    DESCRIPTION
        "This object represents the upper 32-bit of
        ceqfpMemoryResLowFreeWatermark. This object needs to be
        supported only when the value of ceqfpMemoryResLowFreeWatermark
        exceeds 32-bit, otherwise this object value would be set to 0."
    ::= { ceqfpMemoryResourceEntry 14 }

ceqfpMemoryHCResLowFreeWatermark OBJECT-TYPE
    SYNTAX --?? syntax is not convertable to SMIv1
           CounterBasedGauge64
--    Rsyntax Counter
--  Units
--    kilo bytes
    ACCESS read-only
    STATUS mandatory
    DESCRIPTION
        "This object is a 64-bit version of
        ceqfpMemoryResLowFreeWatermark."
    ::= { ceqfpMemoryResourceEntry 15 }

ceqfpThroughputTable OBJECT-TYPE
    SYNTAX SEQUENCE OF CeqfpThroughputEntry
    ACCESS not-accessible
    STATUS mandatory
    DESCRIPTION
        "This table maintains the throughput information for each
        QFP physical entity.
        
                An agent creates a conceptual row to this table
        corresponding to a QFP physical entity upon detection of a
        physical entity supporting the QFP throughput information.
        
                An agent destroys a conceptual row from this table     
        
        corresponding to a QFP physical entity upon removal of the QFP
        host physical entity."
    ::= { ciscoEntityQfp 8 }

ceqfpThroughputEntry OBJECT-TYPE
    SYNTAX CeqfpThroughputEntry
    ACCESS not-accessible
    STATUS mandatory
    DESCRIPTION
        "A conceptual row in the ceqfpThroughputTable. There is an entry
        in this table for each QFP entity, as defined by a value of
        entPhysicalIndex."
    INDEX { entPhysicalIndex }
    ::= { ceqfpThroughputTable 1 }

CeqfpThroughputEntry ::= SEQUENCE {
    ceqfpThroughputLicensedBW Counter,
    ceqfpThroughputLevel INTEGER,
    ceqfpThroughputInterval INTEGER,
    ceqfpThroughputThreshold INTEGER,
    ceqfpThroughputAvgRate Counter
    }

ceqfpThroughputLicensedBW OBJECT-TYPE
    SYNTAX --?? syntax is not convertable to SMIv1
           Counter
--  Units
--    bits per second
    ACCESS read-only
    STATUS mandatory
    DESCRIPTION
        "This object represents the bandwidth for installed
        throughput license."
    ::= { ceqfpThroughputEntry 1 }

ceqfpThroughputLevel OBJECT-TYPE
    SYNTAX INTEGER {
        normal(1),
        warning(2),
        exceed(3)
        }
    ACCESS read-only
    STATUS mandatory
    DESCRIPTION
        "This object represents the current throughput level for
        installed throughput license.
        
                        normal  (1) - Throughput usage is normal
                        warning (2) - Throughput usage has crossed the
                                      configured threshold limit
                        exceed  (3) - Throughput usage has exceeded the
                                      total licensed bandwidth"
    ::= { ceqfpThroughputEntry 2 }

ceqfpThroughputInterval OBJECT-TYPE
    SYNTAX INTEGER(10..86400)
--  Units
--    seconds
    ACCESS read-write
    STATUS mandatory
    DESCRIPTION
        "The object represents the configured time interval at which the
        ceqfpThroughputLevel is checked."
    ::= { ceqfpThroughputEntry 3 }

ceqfpThroughputThreshold OBJECT-TYPE
    SYNTAX INTEGER(75..95)
--  Units
--    percent
    ACCESS read-write
    STATUS mandatory
    DESCRIPTION
        "The object represents the configured throughput threshold."
    ::= { ceqfpThroughputEntry 4 }

ceqfpThroughputAvgRate OBJECT-TYPE
    SYNTAX --?? syntax is not convertable to SMIv1
           Counter
--  Units
--    bits per second
    ACCESS read-only
    STATUS mandatory
    DESCRIPTION
        "The object represents the average throughput rate in the
        interval ceqfpThroughputInterval."
    ::= { ceqfpThroughputEntry 5 }

ceqfpMemoryResThreshNotifEnabled OBJECT-TYPE
    SYNTAX TruthValue
--    Rsyntax INTEGER {
--        true(1),
--        false(2)
--        }
    ACCESS read-write
    STATUS mandatory
    DESCRIPTION
        "This object controls memory resource rising and falling
        threshold notification.
        
        When this object contains a value 'true', then generation of
        memory resource threshold notification is enabled. If this
        object contains a value 'false', then generation of memory
        resource threshold notification is disabled."
    DEFVAL { false }
    ::= { ciscoEntityQfpNotif 1 }

ceqfpMemoryResCurrentRisingThresh OBJECT-TYPE
    SYNTAX Gauge(1..100)
--  Units
--    percent
    ACCESS not-accessible
    STATUS mandatory
    DESCRIPTION
        "This object represents the current rising threshold
        value, which triggers the rising threshold notification
        (ceqfpMemoryResRisingThreshNotif)."
    ::= { ciscoEntityQfpNotif 2 }

ceqfpMemoryResCurrentFallingThresh OBJECT-TYPE
    SYNTAX Gauge
--  Units
--    percent
    ACCESS not-accessible
    STATUS mandatory
    DESCRIPTION
        "This object represents the current falling threshold
        value, which triggers the falling threshold notification
        (ceqfpMemoryResFallingThreshNotif)."
    ::= { ciscoEntityQfpNotif 3 }

ceqfpThroughputNotifEnabled OBJECT-TYPE
    SYNTAX TruthValue
--    Rsyntax INTEGER {
--        true(1),
--        false(2)
--        }
    ACCESS read-write
    STATUS mandatory
    DESCRIPTION
        "This object controls throughput rate notification.
        
        When this object contains a value 'true', then generation of
        ceqfpThroughputNotif is enabled. If this object contains a value
        'false', then generation of ceqfpThroughputNotif is disabled."
    DEFVAL { false }
    ::= { ciscoEntityQfpNotif 4 }

ceqfpMemoryResRisingThreshNotif TRAP-TYPE
-- Reverse mappable trap
    ENTERPRISE ciscoEntityQfpMIB
    VARIABLES {
        ceqfpMemoryResInUse, ceqfpMemoryResCurrentRisingThresh }
--  Status
--    mandatory
    DESCRIPTION
        "A notification indicating that the QFP memory usage is rising
        the threshold on this memory resource.
        
        This notification will be sent, whenever the QFP memory
        usage (ceqfpMemoryResInUse) is equal to or above the 
        rising threshold (ceqfpMemoryResRisingThreshold).
        
        An agent may throttle the generation of consecutive
        ceqfpMemoryResRisingThreshNotif notification so that
        there is at least a five second (suggested default)
        gap between notification of this type."
    ::= 1

ceqfpMemoryResFallingThreshNotif TRAP-TYPE
-- Reverse mappable trap
    ENTERPRISE ciscoEntityQfpMIB
    VARIABLES {
        ceqfpMemoryResInUse, ceqfpMemoryResCurrentFallingThresh }
--  Status
--    mandatory
    DESCRIPTION
        "A notification indicating that the QFP memory usage is equal
        to or below the falling threshold on this memory resource.
        
        This notification will be sent, whenever the QFP memory
        usage (ceqfpMemoryResInUse) is equal to or below the 
        falling threshold (ceqfpMemoryResFallingThreshold).
        
        An agent may throttle the generation of consecutive
        ceqfpMemoryResFallingThreshNotif notification so that
        there is at least a five second (suggested default)
        gap between notification of this type."
    ::= 2

ceqfpThroughputNotif TRAP-TYPE
-- Reverse mappable trap
    ENTERPRISE ciscoEntityQfpMIB
    VARIABLES {
        ceqfpThroughputLicensedBW, ceqfpThroughputLevel, 
        ceqfpThroughputAvgRate }
--  Status
--    mandatory
    DESCRIPTION
        "A notification indicating that the average throughput rate for
        the configured interval has exceeded the threshold or reached
        maximum bandwidth allowed.
        
        This notification will be sent, whenever the ceqfpThroughputLevel
        object has the value warning(2) or exceed(3). The condition for
        trap generation will be checked in every
        ceqfpThroughputInterval.
        
        ceqfpThroughputNotif with ceqfpThrougputLevel as warning(2)
        indicates that average throughput rate has crossed the
        configured threshold.
        
        ceqfpThroughputNotif with ceqfpThrougputLevel as exceed(3)
        indicates that average throughput rate has reached maximum
        licensed bandwidth."
    ::= 3

ciscoEntityQfpSystemGroup OBJECT IDENTIFIER ::= { ciscoEntityQfpMIBGroups 1 }
-- OBJECT-GROUP
--  Status
--    mandatory
--  Descr
--    This group contains collection of QFP system information.
--  objects
--    ceqfpSystemTrafficDirection, ceqfpSystemState, 
--    ceqfpNumberSystemLoads, ceqfpSystemLastLoadTime

ciscoEntityQfpUtilizationAlgoGroup OBJECT IDENTIFIER ::= { ciscoEntityQfpMIBGroups 2 }
-- OBJECT-GROUP
--  Status
--    mandatory
--  Descr
--    This group contains collection of QFP utilization algorithm
--    objects.
--  objects
--    ceqfpFiveSecondUtilAlgo, ceqfpOneMinuteUtilAlgo, 
--    ceqfpFiveMinutesUtilAlgo, ceqfpSixtyMinutesUtilAlgo

ciscoEntityQfpUtilizationGroup OBJECT IDENTIFIER ::= { ciscoEntityQfpMIBGroups 3 }
-- OBJECT-GROUP
--  Status
--    mandatory
--  Descr
--    This group contains collection of QFP utilization information.
--  objects
--    ceqfpUtilInputPriorityPktRate, ceqfpUtilInputPriorityBitRate, 
--    ceqfpUtilInputNonPriorityPktRate, 
--    ceqfpUtilInputNonPriorityBitRate, ceqfpUtilInputTotalPktRate, 
--    ceqfpUtilInputTotalBitRate, ceqfpUtilOutputPriorityPktRate, 
--    ceqfpUtilOutputPriorityBitRate, 
--    ceqfpUtilOutputNonPriorityPktRate, 
--    ceqfpUtilOutputNonPriorityBitRate, 
--    ceqfpUtilOutputTotalPktRate, ceqfpUtilOutputTotalBitRate, 
--    ceqfpUtilProcessingLoad

ciscoEntityQfpMemoryResourceGroup OBJECT IDENTIFIER ::= { ciscoEntityQfpMIBGroups 4 }
-- OBJECT-GROUP
--  Status
--    mandatory
--  Descr
--    This group contains collection of QFP memory resource
--    information.
--  objects
--    ceqfpMemoryResTotal, ceqfpMemoryResInUse, ceqfpMemoryResFree, 
--    ceqfpMemoryResLowFreeWatermark, ceqfpMemoryResRisingThreshold, 
--    ceqfpMemoryResFallingThreshold

ciscoEntityQfpMemoryResNotifGroup OBJECT IDENTIFIER ::= { ciscoEntityQfpMIBGroups 6 }
-- OBJECT-GROUP
--  Status
--    mandatory
--  Descr
--    This group contains memory resource notification control
--    objects.
--  objects
--    ceqfpMemoryResThreshNotifEnabled, 
--    ceqfpMemoryResCurrentRisingThresh, 
--    ceqfpMemoryResCurrentFallingThresh

ciscoEntityQfpMemoryResourceOvrflwGroup OBJECT IDENTIFIER ::= { ciscoEntityQfpMIBGroups 7 }
-- OBJECT-GROUP
--  Status
--    mandatory
--  Descr
--    This group contains collection of upper 32-bit QFP memory
--    resource
--    information.
--  objects
--    ceqfpMemoryResTotalOvrflw, ceqfpMemoryResInUseOvrflw, 
--    ceqfpMemoryResFreeOvrflw, 
--    ceqfpMemoryResLowFreeWatermarkOvrflw

ciscoEntityQfpMemoryHCResourceGroup OBJECT IDENTIFIER ::= { ciscoEntityQfpMIBGroups 8 }
-- OBJECT-GROUP
--  Status
--    mandatory
--  Descr
--    This group contains collection of high capacity(HC) objects of
--    QFP memory resource information.
--  objects
--    ceqfpMemoryHCResTotal, ceqfpMemoryHCResInUse, 
--    ceqfpMemoryHCResFree, ceqfpMemoryHCResLowFreeWatermark

ceqfpThroughputGroup OBJECT IDENTIFIER ::= { ciscoEntityQfpMIBGroups 9 }
-- OBJECT-GROUP
--  Status
--    mandatory
--  Descr
--    This group contains collection of throughput rate information.
--  objects
--    ceqfpThroughputLicensedBW, ceqfpThroughputLevel, 
--    ceqfpThroughputInterval, ceqfpThroughputThreshold, 
--    ceqfpThroughputAvgRate, ceqfpThroughputNotifEnabled

ciscoEntityQfpNotifGroup OBJECT IDENTIFIER ::= { ciscoEntityQfpMIBGroups 5 }
-- NOTIFICATION-GROUP
--  Status
--    mandatory
--  Descr
--    This group contains collection of QFP notifications.
--  notifications
--    ceqfpMemoryResRisingThreshNotif, 
--    ceqfpMemoryResFallingThreshNotif, ceqfpThroughputNotif

ciscoEntityQfpMIBComplianceRev1 OBJECT IDENTIFIER ::= { ciscoEntityQfpMIBCompliances 1 }
-- MODULE-COMPLIANCE
--  Status
--    deprecated
--  Descr
--    The compliance statement for CISCO-ENTITY-QFP-MIB
--  Module
--    >>current<<
--   MandGroup
--    ciscoEntityQfpSystemGroup
--   MandGroup
--    ciscoEntityQfpUtilizationGroup
--   MandGroup
--    ciscoEntityQfpUtilizationAlgoGroup
--   OptGroup
--    ciscoEntityQfpMemoryResourceGroup
--   OptGroup
--    ciscoEntityQfpMemoryResNotifGroup
--   OptGroup
--    ciscoEntityQfpNotifGroup
--   ObjVar
--    ceqfpMemoryResRisingThreshold
--   ObjVar
--    ceqfpMemoryResFallingThreshold

ciscoEntityQfpMIBComplianceRev2 OBJECT IDENTIFIER ::= { ciscoEntityQfpMIBCompliances 2 }
-- MODULE-COMPLIANCE
--  Status
--    mandatory
--  Descr
--    The compliance statement for CISCO-ENTITY-QFP-MIB.
--    This compliance module deprecates
--    ciscoEntityQfpMIBComplianceRev1.
--  Module
--    >>current<<
--   MandGroup
--    ciscoEntityQfpSystemGroup
--   MandGroup
--    ciscoEntityQfpUtilizationGroup
--   MandGroup
--    ciscoEntityQfpUtilizationAlgoGroup
--   OptGroup
--    ciscoEntityQfpMemoryResourceGroup
--   OptGroup
--    ciscoEntityQfpMemoryResourceOvrflwGroup
--   OptGroup
--    ciscoEntityQfpMemoryHCResourceGroup
--   OptGroup
--    ciscoEntityQfpMemoryResNotifGroup
--   OptGroup
--    ciscoEntityQfpNotifGroup
--   OptGroup
--    ceqfpThroughputGroup
--   ObjVar
--    ceqfpMemoryResRisingThreshold
--   ObjVar
--    ceqfpMemoryResFallingThreshold


END
