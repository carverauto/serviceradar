-- MIB file created 05-Oct-2006 20:10:49, by
--   SMICng version 2.2.11-beta(PRO)(Solaris), January 20, 2001. Enterprise key cisco.com

CISCO-SSM-PROV-MIB DEFINITIONS ::= BEGIN

-- From file: "CISCO-SSM-PROV-MIB.my"
-- Compile options "4 7 F H N O W 03 06 0B 0G 0N 0T"

IMPORTS
    RowStatus, TruthValue
            FROM SNMPv2-TC-v1
    SnmpAdminString
            FROM SNMP-FRAMEWORK-MIB
    entPhysicalIndex
            FROM ENTITY-MIB
    ciscoMgmt
            FROM CISCO-SMI
    InterfaceIndex
            FROM IF-MIB
    OBJECT-TYPE
            FROM RFC-1212;

ciscoSsmProvMIB OBJECT IDENTIFIER ::= { ciscoMgmt 448 }
-- MODULE-IDENTITY
--  LastUpdated
--    200502150000Z
--  OrgName
--    Cisco Systems Inc.
--  ContactInfo
--         Cisco Systems
--          Customer Service
--    Postal: 170 W Tasman Drive
--          San Jose, CA  95134
--          USA
--    Tel: +1 800 553-NETS
--    E-mail: cs-san@cisco.com
--  Descr
--    This MIB is used to provision features
--     on a Data Path Processor (DPP) of a Storage Service
--     Module (SSM). A DPP is assigned to a contiguous 
--     set of ports.  Each DPP can run one or more 
--     features independent of other DPPs on the module.
--     Since the concept of a DPP is transparent to the 
--     network manager, ranges of ports are used to
--     configure different features. A start and an end 
--     port are specified to identify a DPP and 
--     provision a feature.
--  RevDate
--    200502150000Z
--  RevDescr
--    Initial version of this MIB.

ciscoSsmProvMIBObjects OBJECT IDENTIFIER ::= { ciscoSsmProvMIB 1 }
ciscoSsmProvMIBConform OBJECT IDENTIFIER ::= { ciscoSsmProvMIB 2 }
ssmProvConfiguration OBJECT IDENTIFIER ::= { ciscoSsmProvMIBObjects 1 }
ssmProvMIBCompliances OBJECT IDENTIFIER ::= { ciscoSsmProvMIBConform 1 }
ssmProvMIBGroups OBJECT IDENTIFIER ::= { ciscoSsmProvMIBConform 2 }

ssmProvFeatureTable OBJECT-TYPE
    SYNTAX SEQUENCE OF SsmProvFeatureEntry
    ACCESS not-accessible
    STATUS mandatory
    DESCRIPTION
        "A table containing list of features that can be
         provisioned on an SSM."
    ::= { ssmProvConfiguration 1 }

ssmProvFeatureEntry OBJECT-TYPE
    SYNTAX SsmProvFeatureEntry
    ACCESS not-accessible
    STATUS mandatory
    DESCRIPTION
        "An entry in the ssmProvFeatureTable that contains 
         information on the features that can be configured 
         on an SSM."
    INDEX { entPhysicalIndex, ssmProvFeatureName }
    ::= { ssmProvFeatureTable 1 }

SsmProvFeatureEntry ::= SEQUENCE {
    ssmProvFeatureName SnmpAdminString,
    ssmProvFeatureNeedsImage TruthValue
    }

ssmProvFeatureName OBJECT-TYPE
    SYNTAX SnmpAdminString(SIZE(1..80))
--    Rsyntax OCTET STRING(SIZE(1..80))
    ACCESS not-accessible
    STATUS mandatory
    DESCRIPTION
        "The name of the feature that can be provisioned
         on the SSM."
    ::= { ssmProvFeatureEntry 1 }

ssmProvFeatureNeedsImage OBJECT-TYPE
    SYNTAX TruthValue
--    Rsyntax INTEGER {
--        true(1),
--        false(2)
--        }
    ACCESS read-only
    STATUS mandatory
    DESCRIPTION
        "The object indicates if the feature needs an 
        image name to be specified during provisioning.
        
        If the value of this object is 'true', then an
        image needs to be specified.
        
        If the value of this object is 'false', then an
        image does not need to be specified."
    ::= { ssmProvFeatureEntry 2 }

ssmProvFeatureIfTable OBJECT-TYPE
    SYNTAX SEQUENCE OF SsmProvFeatureIfEntry
    ACCESS not-accessible
    STATUS mandatory
    DESCRIPTION
        "A table containing feature related information
        for interfaces.  This table gives a list of
        interfaces that are assigned to different features.
        The interfaces supported are of the type
        fibreChannel.
        
        If a feature is removed from ssmProvFeatureTable,
        then corresponding entries in ssmProvFeatureIfTable
        will also get removed."
    ::= { ssmProvConfiguration 2 }

ssmProvFeatureIfEntry OBJECT-TYPE
    SYNTAX SsmProvFeatureIfEntry
    ACCESS not-accessible
    STATUS mandatory
    DESCRIPTION
        "This contains information on the SSM-feature
        membership of a interface."
    INDEX { ssmProvFeatureIfStartPort, ssmProvFeatureIfEndPort, ssmProvFeatureIfFeatureName }
    ::= { ssmProvFeatureIfTable 1 }

SsmProvFeatureIfEntry ::= SEQUENCE {
    ssmProvFeatureIfStartPort InterfaceIndex,
    ssmProvFeatureIfEndPort InterfaceIndex,
    ssmProvFeatureIfFeatureName SnmpAdminString,
    ssmProvFeatureIfForceRemove INTEGER,
    ssmProvFeatureIfPartnerImageURI SnmpAdminString,
    ssmProvFeatureIfRowStatus RowStatus
    }

ssmProvFeatureIfStartPort OBJECT-TYPE
    SYNTAX InterfaceIndex
--    Rsyntax INTEGER(1..2147483647)
    ACCESS not-accessible
    STATUS mandatory
    DESCRIPTION
        "The starting interface index on the SSM card to
         which a feature is going to be assigned.  A feature
         is assigned to a DPP by specifying a starting and
         ending port."
    ::= { ssmProvFeatureIfEntry 1 }

ssmProvFeatureIfEndPort OBJECT-TYPE
    SYNTAX InterfaceIndex
--    Rsyntax INTEGER(1..2147483647)
    ACCESS not-accessible
    STATUS mandatory
    DESCRIPTION
        "The end interface index on the SSM card to
         which a feature is going to be assigned.  A
         feature is assigned to a DPP by specifying a
         start and end port."
    ::= { ssmProvFeatureIfEntry 2 }

ssmProvFeatureIfFeatureName OBJECT-TYPE
    SYNTAX SnmpAdminString(SIZE(1..80))
--    Rsyntax OCTET STRING(SIZE(1..80))
    ACCESS not-accessible
    STATUS mandatory
    DESCRIPTION
        "The SSM feature name bound to the interface. This
         must be one of the features listed in 
         ssmProvFeatureTable."
    ::= { ssmProvFeatureIfEntry 3 }

ssmProvFeatureIfForceRemove OBJECT-TYPE
    SYNTAX INTEGER {
        forceReset(1),
        noop(2)
        }
    ACCESS read-write
    STATUS mandatory
    DESCRIPTION
        "This object indicates if the provisioning should be 
         forcefully removed. The object must be set 
         concurrently with setting the corresponding instance 
         of ssmProvFeatureIfRowStatus to 'destroy'.
        
         The 'forceReset' option will cause the configuration
         to be removed and the SSM card to be reset in the 
         process.
        
         No action is taken if this object is set to 'noop'.
        
         The value of this object when read is always 'noop'."
    DEFVAL { noop }
    ::= { ssmProvFeatureIfEntry 4 }

ssmProvFeatureIfPartnerImageURI OBJECT-TYPE
    SYNTAX SnmpAdminString(SIZE(1..80))
--    Rsyntax OCTET STRING(SIZE(1..80))
    ACCESS read-write
    STATUS mandatory
    DESCRIPTION
        "The object representing the location on the local
         system, from where the partner image will be picked
         for installation. The value of this object is only
         relevant if the ssmProvFeatureNeedsImage object is
         set to 'true' for that feature in 
         ssmProvFeatureTable."
    ::= { ssmProvFeatureIfEntry 5 }

ssmProvFeatureIfRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this conceptual row."
    ::= { ssmProvFeatureIfEntry 6 }

ssmProvDppTable OBJECT-TYPE
    SYNTAX SEQUENCE OF SsmProvDppEntry
    ACCESS not-accessible
    STATUS mandatory
    DESCRIPTION
        "A table containing DPP information for interfaces.
        This table gives a list of DPPs for every interface.
        Entries get added to the table when an SSM comes 
        online and removed when it goes offline."
    ::= { ssmProvConfiguration 3 }

ssmProvDppEntry OBJECT-TYPE
    SYNTAX SsmProvDppEntry
    ACCESS not-accessible
    STATUS mandatory
    DESCRIPTION
        "This contains information on the DPP to interface
        association."
    INDEX { ssmProvDppStartPort }
    ::= { ssmProvDppTable 1 }

SsmProvDppEntry ::= SEQUENCE {
    ssmProvDppStartPort InterfaceIndex,
    ssmProvDppEndPort InterfaceIndex,
    ssmProvDppName SnmpAdminString
    }

ssmProvDppStartPort OBJECT-TYPE
    SYNTAX InterfaceIndex
--    Rsyntax INTEGER(1..2147483647)
    ACCESS not-accessible
    STATUS mandatory
    DESCRIPTION
        "The starting interface index on the SSM card 
        that corresponds to a DPP."
    ::= { ssmProvDppEntry 1 }

ssmProvDppEndPort OBJECT-TYPE
    SYNTAX InterfaceIndex
--    Rsyntax INTEGER(1..2147483647)
    ACCESS read-only
    STATUS mandatory
    DESCRIPTION
        "The ending interface index on the SSM card 
        that corresponds to a DPP."
    ::= { ssmProvDppEntry 2 }

ssmProvDppName OBJECT-TYPE
    SYNTAX SnmpAdminString(SIZE(1..80))
--    Rsyntax OCTET STRING(SIZE(1..80))
    ACCESS read-only
    STATUS mandatory
    DESCRIPTION
        "The DPP that is associated with the given
        starting and ending interface."
    ::= { ssmProvDppEntry 3 }

ssmProvFeatureGroup OBJECT IDENTIFIER ::= { ssmProvMIBGroups 1 }
-- OBJECT-GROUP
--  Status
--    mandatory
--  Descr
--    A collection of objects related to SSM features.
--  objects
--    ssmProvFeatureNeedsImage

ssmProvFeatureIfGroup OBJECT IDENTIFIER ::= { ssmProvMIBGroups 2 }
-- OBJECT-GROUP
--  Status
--    mandatory
--  Descr
--    A collection of objects related to SSM Feature to 
--     Interface mapping . 
--  objects
--    ssmProvFeatureIfForceRemove, ssmProvFeatureIfPartnerImageURI, 
--    ssmProvFeatureIfRowStatus

ssmProvDppGroup OBJECT IDENTIFIER ::= { ssmProvMIBGroups 3 }
-- OBJECT-GROUP
--  Status
--    mandatory
--  Descr
--    A collection of objects related to DPP 
--     to interface mapping.
--  objects
--    ssmProvDppEndPort, ssmProvDppName

ssmProvMIBCompliance OBJECT IDENTIFIER ::= { ssmProvMIBCompliances 1 }
-- MODULE-COMPLIANCE
--  Status
--    mandatory
--  Descr
--    The compliance statement for entities which 
--    implement this MIB.
--  Module
--    >>current<<
--   MandGroup
--    ssmProvFeatureGroup
--   MandGroup
--    ssmProvFeatureIfGroup
--   MandGroup
--    ssmProvDppGroup
--   ObjVar
--    ssmProvFeatureIfRowStatus


END
