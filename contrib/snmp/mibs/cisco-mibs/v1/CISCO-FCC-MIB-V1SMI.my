-- MIB file created 20-Oct-2004 18:58:29, by
--   SMICng version 2.2.11-beta(PRO)(Solaris), January 20, 2001. Enterprise key cisco.com

CISCO-FCC-MIB DEFINITIONS ::= BEGIN

-- From file: "CISCO-FCC-MIB.my"
-- Compile options "4 7 F H N O W 03 06 0B 0G 0N 0T"

IMPORTS
    TruthValue, TimeStamp
            FROM SNMPv2-TC-v1
    ciscoMgmt
            FROM CISCO-SMI
    ifIndex
            FROM IF-MIB
    FcAddressId, VsanIndex
            FROM CISCO-ST-TC
    Counter
            FROM RFC1155-SMI
    OBJECT-TYPE
            FROM RFC-1212
    TRAP-TYPE
            FROM RFC-1215;

ciscoFCCMIB OBJECT IDENTIFIER ::= { ciscoMgmt 365 }
-- MODULE-IDENTITY
--  LastUpdated
--    200407080000Z
--  OrgName
--    Cisco Systems, Inc.
--  ContactInfo
--           Cisco Systems
--            Customer Service
--    
--    Postal 170 W Tasman Drive
--            San Jose, CA  95134
--            USA
--    
--       Tel +1 800 553-NETS
--    
--    E-mail cs-san@cisco.com
--  Descr
--    The MIB module for the management of Fibre Channel
--     Congestion Control(FCC). FCC is a Cisco proprietary
--     flow control mechanism that alleviates congestion
--     on Fibre Channel networks. This MIB enables managers
--     to configure the FCC mechanism on the switch, provides 
--     statistics of the congestion control packets,
--     notification of congestion state changes of the 
--     FC port and monitoring of the congestion state of
--     the FC port.
--  RevDate
--    200407080000Z
--  RevDescr
--    Added the following objects to the 'cFCCPortTable' :
--      - 'cFCCLastCongestionStartTime'  and
--      - 'cFCCIsRateLimitingApplied'.
--  RevDate
--    200402250000Z
--  RevDescr
--    Changed the cFCCNotificationEnable DEFVAL to 'false'
--     instead of 1.
--  RevDate
--    200308060000Z
--  RevDescr
--    Changed cFCCCongestionSourceID and 
--     cFCCCongestionDestinationID to be FC_IDs
--     instead of WWNs and added 
--     cFCCCongestionNotifyVSANIndex
--  RevDate
--    200305260000Z
--  RevDescr
--    Initial version of this MIB.

ciscoFCCMIBNotifs OBJECT IDENTIFIER ::= { ciscoFCCMIB 0 }
ciscoFCCMIBObjects OBJECT IDENTIFIER ::= { ciscoFCCMIB 1 }
ciscoFCCMIBConformance OBJECT IDENTIFIER ::= { ciscoFCCMIB 2 }
cFCCConfig      OBJECT IDENTIFIER ::= { ciscoFCCMIBObjects 1 }
cFCCPortEntries OBJECT IDENTIFIER ::= { ciscoFCCMIBObjects 2 }
cFCCNotifObjects OBJECT IDENTIFIER ::= { ciscoFCCMIBObjects 3 }
ciscoFCCMIBCompliances OBJECT IDENTIFIER ::= { ciscoFCCMIBConformance 1 }
ciscoFCCMIBGroups OBJECT IDENTIFIER ::= { ciscoFCCMIBConformance 2 }

CiscoFCCCongestionState ::= INTEGER {
        noCongestion(1),
        congested(2),
        severelyCongested(3)
        }
-- TEXTUAL-CONVENTION
--  Status
--    mandatory
--  Descr
--    The FCC Congestion state. This is to indicate the severity
--     of the Congestion 
--    
--          noCongestion(1)       - No Congestion
--          Congested(2)          - Congested
--          SeverelyCongested(3)  - Severely Congested.

cFCCEnable OBJECT-TYPE
    SYNTAX INTEGER {
        enable(1),
        disable(2)
        }
    ACCESS read-write
    STATUS mandatory
    DESCRIPTION
        "To enable/disable FCC on the device."
    DEFVAL { disable }
    ::= { cFCCConfig 1 }

cFCCPacketPriority OBJECT-TYPE
    SYNTAX INTEGER(0..7)
    ACCESS read-write
    STATUS mandatory
    DESCRIPTION
        "The traffic Priority for the  FCC packets. The generated
         FCC quench packets should be granted high, but not
         highest priority, so that the FCC packet priority
         is higher than the normal data traffic priority but lower
         than control and critical traffic priority.  This ensures
         that the packets of the protocols guaranteeing the
         proper behavior of the fabric are not disturbed by
         quench packets.
        
         0 is the lowest priority and 7 is the highest."
    DEFVAL { 4 }
    ::= { cFCCConfig 2 }

cFCCNotificationEnable OBJECT-TYPE
    SYNTAX TruthValue
--    Rsyntax INTEGER {
--        true(1),
--        false(2)
--        }
    ACCESS read-write
    STATUS mandatory
    DESCRIPTION
        "This object specifies whether the agent should
         generate the notifications defined in this MIB
         module.
         If the value of this object is 'true', then the
         notifications are generated. 
         If the value of this object is 'false', then the
         notifications are not generated."
    DEFVAL { false }
    ::= { cFCCConfig 3 }

cFCCPortTable OBJECT-TYPE
    SYNTAX SEQUENCE OF CFCCPortEntry
    ACCESS not-accessible
    STATUS mandatory
    DESCRIPTION
        "A table providing statistics and status for FCC
         on a per FC Port basis."
    ::= { cFCCPortEntries 1 }

cFCCPortEntry OBJECT-TYPE
    SYNTAX CFCCPortEntry
    ACCESS not-accessible
    STATUS mandatory
    DESCRIPTION
        "Each entry contains the FCC statistics and 
         status for a particular FC port identified
         by the value of ifIndex."
    INDEX { ifIndex }
    ::= { cFCCPortTable 1 }

CFCCPortEntry ::= SEQUENCE {
    cFCCEdgeQuenchPktsRecd Counter,
    cFCCEdgeQuenchPktsSent Counter,
    cFCCPathQuenchPktsRecd Counter,
    cFCCPathQuenchPktsSent Counter,
    cFCCCurrentCongestionState CiscoFCCCongestionState,
    cFCCLastCongestedTime TimeStamp,
    cFCCLastCongestionStartTime TimeStamp,
    cFCCIsRateLimitingApplied TruthValue
    }

cFCCEdgeQuenchPktsRecd OBJECT-TYPE
    SYNTAX Counter
    ACCESS read-only
    STATUS mandatory
    DESCRIPTION
        "The number of Edge Quench packets received and processed
         on this Port."
    ::= { cFCCPortEntry 1 }

cFCCEdgeQuenchPktsSent OBJECT-TYPE
    SYNTAX Counter
    ACCESS read-only
    STATUS mandatory
    DESCRIPTION
        "The number of Edge Quench packets generated on this
         Port as result of congestion."
    ::= { cFCCPortEntry 2 }

cFCCPathQuenchPktsRecd OBJECT-TYPE
    SYNTAX Counter
    ACCESS read-only
    STATUS mandatory
    DESCRIPTION
        "The number of Path Quench packets recieved and processed
         on this Port."
    ::= { cFCCPortEntry 3 }

cFCCPathQuenchPktsSent OBJECT-TYPE
    SYNTAX Counter
    ACCESS read-only
    STATUS mandatory
    DESCRIPTION
        "The number of Path Quench packets generated on this
         Port as result of congestion."
    ::= { cFCCPortEntry 4 }

cFCCCurrentCongestionState OBJECT-TYPE
    SYNTAX CiscoFCCCongestionState
--    Rsyntax INTEGER {
--        noCongestion(1),
--        congested(2),
--        severelyCongested(3)
--        }
    ACCESS read-only
    STATUS mandatory
    DESCRIPTION
        "The current FCC congestion state of this Port indicating the
         severity of the congestion."
    ::= { cFCCPortEntry 5 }

cFCCLastCongestedTime OBJECT-TYPE
    SYNTAX TimeStamp
--    Rsyntax TimeTicks
    ACCESS read-only
    STATUS mandatory
    DESCRIPTION
        "The value of sysUpTime at the most recent time the
         congestion state of the Port changed to noCongestion(1) 
         from some other value.  0 if the congestion state of
         the Port has never transitioned to noCongestion(1) 
         since the last restart of the device."
    ::= { cFCCPortEntry 6 }

cFCCLastCongestionStartTime OBJECT-TYPE
    SYNTAX TimeStamp
--    Rsyntax TimeTicks
    ACCESS read-only
    STATUS mandatory
    DESCRIPTION
        "The value of sysUpTime at the most recent time the
         congestion state (value of corresponding instance of
         'cFCCCurrentCongestionState') of the Port changed from
         'noCongestion' to some other value. 0 if the congestion
         state of the Port has never transitioned from 
         'noCongestion' to  some other value  since the last 
         restart of the device."
    ::= { cFCCPortEntry 7 }

cFCCIsRateLimitingApplied OBJECT-TYPE
    SYNTAX TruthValue
--    Rsyntax INTEGER {
--        true(1),
--        false(2)
--        }
    ACCESS read-only
    STATUS mandatory
    DESCRIPTION
        "The value of this object indicates if the rate
         limiting is currently being applied on this Port.
         If the value of this object is 'true', the rate
         limiting is currently being applied on this  
         Port. If the value of this object is 'false', the 
         rate limiting is not being applied currently on 
         this Port."
    ::= { cFCCPortEntry 8 }

cFCCCongestionSourceID OBJECT-TYPE
    SYNTAX FcAddressId
--    Rsyntax OCTET STRING(SIZE(3))
    ACCESS not-accessible
    STATUS mandatory
    DESCRIPTION
        "The FC_ID associated with the Source causing
         the congestion. The value is extracted from 
         the FCC congestion quench packet."
    ::= { cFCCNotifObjects 1 }

cFCCCongestionDestinationID OBJECT-TYPE
    SYNTAX FcAddressId
--    Rsyntax OCTET STRING(SIZE(3))
    ACCESS not-accessible
    STATUS mandatory
    DESCRIPTION
        "The  FC_ID associated with the Destination that
         is part of Source-Destination Flow causing the 
         congestion. The value is extracted from the 
         FCC congestion quench packet."
    ::= { cFCCNotifObjects 2 }

cFCCCongestionNotifyVSANIndex OBJECT-TYPE
    SYNTAX VsanIndex
--    Rsyntax INTEGER(1..4094)
    ACCESS not-accessible
    STATUS mandatory
    DESCRIPTION
        "Id of the VSAN containing the Source-Destination
        flow causing the congestion. The value is extracted 
        from the FCC congestion quench packet. This along 
        with cFCCCongestionSourceID and 
        cFCCCongestionDestinationID gives the Flow causing 
        the congestion."
    ::= { cFCCNotifObjects 3 }

cFCCCongestionState OBJECT-TYPE
    SYNTAX CiscoFCCCongestionState
--    Rsyntax INTEGER {
--        noCongestion(1),
--        congested(2),
--        severelyCongested(3)
--        }
    ACCESS not-accessible
    STATUS mandatory
    DESCRIPTION
        "This is to indicate the congestion state of the port."
    ::= { cFCCNotifObjects 4 }

ciscoFCCCongestionStateChange TRAP-TYPE
-- Reverse mappable trap
    ENTERPRISE ciscoFCCMIB
    VARIABLES {
        ifIndex, cFCCCongestionState }
--  Status
--    mandatory
    DESCRIPTION
        "Notification to indicate that the congestion state of
         this port has changed. cFCCCongestionState indicates
         the new state of the port."
    ::= 1

ciscoFCCCongestionRateLimitStart TRAP-TYPE
-- Reverse mappable trap
    ENTERPRISE ciscoFCCMIB
    VARIABLES {
        ifIndex, cFCCCongestionSourceID, 
        cFCCCongestionDestinationID, cFCCCongestionNotifyVSANIndex }
--  Status
--    mandatory
    DESCRIPTION
        "Notification to indicate that the rate limiting has
         begun on this port for a source-destination pair."
    ::= 2

ciscoFCCCongestionRateLimitEnd TRAP-TYPE
-- Reverse mappable trap
    ENTERPRISE ciscoFCCMIB
    VARIABLES {
        ifIndex, cFCCCongestionSourceID, 
        cFCCCongestionDestinationID, cFCCCongestionNotifyVSANIndex }
--  Status
--    mandatory
    DESCRIPTION
        "Notification to indicate that the rate limiting has
         been stopped on this port for a source-destination
         pair."
    ::= 3

cFCCConfigurationGroup OBJECT IDENTIFIER ::= { ciscoFCCMIBGroups 1 }
-- OBJECT-GROUP
--  Status
--    mandatory
--  Descr
--    A collection of objects for FCC configuration.
--  objects
--    cFCCEnable, cFCCPacketPriority, cFCCNotificationEnable

cFCCPortEntriesGroup OBJECT IDENTIFIER ::= { ciscoFCCMIBGroups 2 }
-- OBJECT-GROUP
--  Status
--    deprecated
--  Descr
--    A collection of objects for FCC Statistics and Status.
--  objects
--    cFCCEdgeQuenchPktsRecd, cFCCEdgeQuenchPktsSent, 
--    cFCCPathQuenchPktsRecd, cFCCPathQuenchPktsSent, 
--    cFCCCurrentCongestionState, cFCCLastCongestedTime

cFCCNotificationObjectsGroup OBJECT IDENTIFIER ::= { ciscoFCCMIBGroups 3 }
-- OBJECT-GROUP
--  Status
--    mandatory
--  Descr
--    A collection of objects defined for notification only.
--  objects
--    cFCCCongestionDestinationID, cFCCCongestionSourceID, 
--    cFCCCongestionNotifyVSANIndex, cFCCCongestionState

cFCCPortEntriesGroupRev1 OBJECT IDENTIFIER ::= { ciscoFCCMIBGroups 5 }
-- OBJECT-GROUP
--  Status
--    mandatory
--  Descr
--    A collection of objects for FCC Statistics and Status.
--  objects
--    cFCCEdgeQuenchPktsRecd, cFCCEdgeQuenchPktsSent, 
--    cFCCPathQuenchPktsRecd, cFCCPathQuenchPktsSent, 
--    cFCCCurrentCongestionState, cFCCLastCongestedTime, 
--    cFCCLastCongestionStartTime, cFCCIsRateLimitingApplied

cFCCNotificationGroup OBJECT IDENTIFIER ::= { ciscoFCCMIBGroups 4 }
-- NOTIFICATION-GROUP
--  Status
--    mandatory
--  Descr
--    A collection of notifications for Congestion Monitoring.
--  notifications
--    ciscoFCCCongestionStateChange, 
--    ciscoFCCCongestionRateLimitStart, 
--    ciscoFCCCongestionRateLimitEnd

ciscoFCCMIBCompliance OBJECT IDENTIFIER ::= { ciscoFCCMIBCompliances 1 }
-- MODULE-COMPLIANCE
--  Status
--    deprecated
--  Descr
--    The compliance statement for entities which implement the
--    CISCO-FCC-MIB.
--  Module
--    >>current<<
--   MandGroup
--    cFCCConfigurationGroup
--   MandGroup
--    cFCCPortEntriesGroup
--   MandGroup
--    cFCCNotificationObjectsGroup
--   MandGroup
--    cFCCNotificationGroup

ciscoFCCMIBComplianceRev1 OBJECT IDENTIFIER ::= { ciscoFCCMIBCompliances 2 }
-- MODULE-COMPLIANCE
--  Status
--    mandatory
--  Descr
--    The compliance statement for entities which implement the
--    CISCO-FCC-MIB.
--  Module
--    >>current<<
--   MandGroup
--    cFCCConfigurationGroup
--   MandGroup
--    cFCCPortEntriesGroupRev1
--   MandGroup
--    cFCCNotificationObjectsGroup
--   MandGroup
--    cFCCNotificationGroup


END
