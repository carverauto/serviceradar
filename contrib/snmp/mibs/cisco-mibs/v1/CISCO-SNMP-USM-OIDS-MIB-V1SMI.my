-- MIB file created 28-Feb-2007 14:55:45, by
--   SMICng version 2.2.11-beta(PRO)(Solaris), January 20, 2001. Enterprise key cisco.com

CISCO-SNMP-USM-OIDS-MIB DEFINITIONS ::= BEGIN

-- From file: "CISCO-SNMP-USM-OIDS-MIB.my"
-- Compile options "4 7 F H N O W 03 06 0B 0G 0N 0T"

IMPORTS
    ciscoModules
            FROM CISCO-SMI;

ciscoSnmpUsmOidsMIB OBJECT IDENTIFIER ::= { ciscoModules 6 }
-- MODULE-IDENTITY
--  LastUpdated
--    200602280000Z
--  OrgName
--    Cisco Systems, Inc.
--  ContactInfo
--           Cisco Systems
--            Customer Service
--    
--    Postal: 170 W. Tasman Drive
--            San Jose, CA 95134
--            USA
--    
--       Tel: +1 800 553-NETS
--    
--    E-mail: cs-snmp@cisco.com
--  Descr
--    This MIB extends the OID's for SNMP-USM-MIB
--     specified in RFC 3414.
--    
--    The privacy protocol OID's specified herein 
--    are intended to be used as values  for 
--    usmUserPrivProtocol when managing SNMPv3  
--    users via the snmpUsmMIB.
--    
--    This MIB defines the OID's for the following
--    encryption options:
--    
--            * 192 bit key size AES
--            * 256 bit key size AES
--            * 168 bit key size 3DES.
--    
--    OID for 128 bit key size AES encryption is 
--    defined in SNMP-USM-AES-MIB as per the 
--    RFC 3826.
--  RevDate
--    200602280000Z
--  RevDescr
--    Initial version of this MIB module.

ciscoSnmpPrivProtocols OBJECT IDENTIFIER ::= { ciscoSnmpUsmOidsMIB 1 }
cusmAESCfb192PrivProtocol OBJECT IDENTIFIER ::= { ciscoSnmpPrivProtocols 1 }
cusmAESCfb256PrivProtocol OBJECT IDENTIFIER ::= { ciscoSnmpPrivProtocols 2 }
cusm3DES168PrivProtocol OBJECT IDENTIFIER ::= { ciscoSnmpPrivProtocols 3 }


END
