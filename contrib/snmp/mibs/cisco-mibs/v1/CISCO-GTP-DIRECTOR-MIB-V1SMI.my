-- MIB file created 09-Jan-2002 16:20:16, by
--   SMICng version 2.2.11-beta(PRO)(Solaris), January 20, 2001. Enterprise key cisco.com

CISCO-GTP-DIRECTOR-MIB DEFINITIONS ::= BEGIN

-- From file: "CISCO-GTP-DIRECTOR-MIB.my"
-- Compile options "4 7 F H N W 03 06 0B 0G 0N 0T"

IMPORTS
    TruthValue
            FROM SNMPv2-TC-v1
    ciscoMgmt
            FROM CISCO-SMI
    Counter, Gauge
            FROM RFC1155-SMI
    OBJECT-TYPE
            FROM RFC-1212
    TRAP-TYPE
            FROM RFC-1215;

ciscoGtpDirectorMIB OBJECT IDENTIFIER ::= { ciscoMgmt 9997 }
-- MODULE-IDENTITY
--  LastUpdated
--    200109131400Z
--  OrgName
--    Cisco Systems, Inc.
--  ContactInfo
--           Cisco Systems
--            Customer Service
--    
--    Postal: 170 W Tasman Drive
--            San Jose, CA  95134
--            USA
--    
--       Tel: +1 800 553-NETS
--    
--    E-mail: cs-gprs@cisco.com
--  Descr
--    This MIB module defines objects that are used to 
--     manage GTP Director Module.
--    
--     In the GPRS network, the APN is the identifier that 
--     specifies where the user is connecting. The APN 
--     identifies whether the network is a corporate network 
--     or a service provider network.  The APN comprises of 
--     two parts, the network id and the operator id.
--    
--     The Single Access point feature enables the 
--     service provider to add new access-points to the GGSN 
--     without having to provision the HLR. The requests are 
--     sent by the SGSN to the same virtual APN. A virtual 
--     APN is not associated with any actual physical 
--     network.  The GGSN processes the request and forwards 
--     the packet to the appropriate access-point that is 
--     specified in the PCO. The Single APN feature is 
--     supported only in Cisco GGSNs.
--    
--     The purpose of the GTP-Director is to provide a 
--     mechanism for service providers using non-Cisco GGSN 
--     to use the Single APN feature. This would enable the 
--     service providers to add access-point to the network 
--     without having to provision the HLR. This will be 
--     transparent to the SGSN. The mobile user initiates 
--     a connection request to the SGSN. The access-point 
--     name specified in the request is the virtual APN. 
--     The GTP-Director would resolve the access-point name 
--     and forward the request to the appropriate 
--     GGSN (real GGSN).
--    
--    +==+  +===+  +====+   ====   +===+  +====+     +===+
--    |MS|==|BSS|==|SGSN|==|PLMN|==|GDM|==|GGSN|==Gi-|PDN|
--    +==+  +===+  +====+   ====   +===+  +====+     +===+
--                                  | |
--                                  | |   +====+    
--                                  | |___|GGSN|======Gi
--                                  |     +====+       |
--                                  |                  |
--                                  |     +====+     +===+
--                                  |_____|GGSN|==Gi-|PDN|
--                                        +====+     +===+
--    
--     The GTP-Director also provides load balancing across 
--     GGSNs. The GTP-Director uses the round-robin 
--     mechanism for providing load balancing.  The 
--     Cisco GGSNs may use the GTP-Director, but is not 
--     necessary as they can use IOS-SLB ( Server Load 
--     Balancing ).
--    
--    Acronyms and terms:
--     APN    Access Point Name
--     BSS    Base Staion Subsystem
--     GDM    GTP Director Module
--     GGSN   Gateway GPRS Support Node
--     Gi     Reference point between GPRS and an external
--            packet data network
--     GPRS   General Packet Radio Service
--     HLR    Home Location Register
--     NMS    Network Management System
--     PCO    Protocol Configuration Options
--     PDN    Packet Data Network
--     PDP    Packet Data Protocol
--     PLMN   Public Land Mobile Network
--     MS     Mobile Station 
--     SGSN   Serving GPRS Support Node
--     TID    Tunnel Identifier
--     
--  RevDate
--    200109131400Z
--  RevDescr
--    Initial version of this MIB Module.

ciscoGtpDirectorMIBObjects OBJECT IDENTIFIER ::= { ciscoGtpDirectorMIB 1 }
cgdConfigurations OBJECT IDENTIFIER ::= { ciscoGtpDirectorMIBObjects 1 }
cgdStatus       OBJECT IDENTIFIER ::= { ciscoGtpDirectorMIBObjects 2 }
cgdStatistics   OBJECT IDENTIFIER ::= { ciscoGtpDirectorMIBObjects 3 }
cgdNotifMgmt    OBJECT IDENTIFIER ::= { ciscoGtpDirectorMIBObjects 4 }
ciscoGtpDirectorNotifPrefix OBJECT IDENTIFIER ::= { ciscoGtpDirectorMIB 2 }
ciscoGtpDirectorNotifications OBJECT IDENTIFIER ::= { ciscoGtpDirectorNotifPrefix 0 }
ciscoGtpDirectorMIBConformance OBJECT IDENTIFIER ::= { ciscoGtpDirectorMIB 3 }
ciscoGtpDirectorMIBCompliances OBJECT IDENTIFIER ::= { ciscoGtpDirectorMIBConformance 1 }
ciscoGtpDirectorMIBGroups OBJECT IDENTIFIER ::= { ciscoGtpDirectorMIBConformance 2 }

cgdCreatePdpRequestInfoSaveTimer OBJECT-TYPE
    SYNTAX Gauge(1..65535)
--  Units
--    seconds
    ACCESS read-write
    STATUS mandatory
    DESCRIPTION
        "When a GDM receives a request to create PDP, it processes 
        and forwards the request to the GGSN and saves the information 
        related to the request.  This object defines the time during 
        which the information is maintained by the GDM. Any subsequent
        retries by the SGSN within this time period will be forwarded
        to the same GGSN, but the timer will not be reset if a retry
        occurs before it has expired."
    DEFVAL { 30 }
    ::= { cgdConfigurations 1 }

cgdPendingPdps OBJECT-TYPE
    SYNTAX Gauge
    ACCESS read-only
    STATUS mandatory
    DESCRIPTION
        "This object gives the number of create PDP requests whose
        connection retry timer has not expired."
    ::= { cgdStatus 1 }

cgdCreatePdpRequestFwded OBJECT-TYPE
    SYNTAX Counter
    ACCESS read-only
    STATUS mandatory
    DESCRIPTION
        "This object gives the number of unique create PDP requests 
        forwarded by the GDM to GGSN.  This does not include
        the retransmissions."
    ::= { cgdStatistics 1 }

cgdTotalCreatePdpRequestFwded OBJECT-TYPE
    SYNTAX Counter
    ACCESS read-only
    STATUS mandatory
    DESCRIPTION
        "This object gives the total number of create PDP requests 
        forwarded by the GDM to GGSN.  This includes retransmissions 
        too."
    ::= { cgdStatistics 2 }

cgdCreateRequestRejected OBJECT-TYPE
    SYNTAX Counter
    ACCESS read-only
    STATUS mandatory
    DESCRIPTION
        "This object gives the total number of create PDP requests 
        rejected by the GGSN.  "
    ::= { cgdStatistics 3 }

cgdTotalUnsupportedMessages OBJECT-TYPE
    SYNTAX Counter
    ACCESS read-only
    STATUS mandatory
    DESCRIPTION
        "GDM does not support any signalling message other than 
        create PDP request.  If the GDM receives any unsupported 
        signalling message, it will not be forwarded to GGSN 
        and will be dropped.  This object gives the total number 
        of unsupported signalling messages received by the GDM."
    ::= { cgdStatistics 4 }

cgdPdpRequestDropped OBJECT-TYPE
    SYNTAX Counter
    ACCESS read-only
    STATUS mandatory
    DESCRIPTION
        "This object gives the total number of PDP requests dropped 
        by the GDM due to routing failures, which occur, if the GTP is 
        unable to pass the packet to IP.  "
    ::= { cgdStatistics 5 }

cgdNotifEnable OBJECT-TYPE
    SYNTAX TruthValue
--    Rsyntax INTEGER {
--        true(1),
--        false(2)
--        }
    ACCESS read-write
    STATUS mandatory
    DESCRIPTION
        "Indicates whether ciscoGtpDirectorNotifications notification will
         be sent when it is generated by the device.
           - 'true',  will enable the device to send the notification.
           - 'false', will prevent the device from sending out the
                      notification."
    DEFVAL { false }
    ::= { cgdNotifMgmt 1 }

cgdNotifType OBJECT-TYPE
    SYNTAX INTEGER {
        gdmServiceUp(1),
        gdmServiceDown(2)
        }
    ACCESS not-accessible
    STATUS mandatory
    DESCRIPTION
        "This object indicates the type of notification."
    ::= { cgdNotifMgmt 2 }

ciscoGtpDirectorNotification TRAP-TYPE
-- Reverse mappable trap
    ENTERPRISE ciscoGtpDirectorNotifPrefix
    VARIABLES {
        cgdNotifType }
--  Status
--    mandatory
    DESCRIPTION
        "This notification indicates the occurrence of a GDM
        related alarm. "
    ::= 1

ciscoGtpDirectorConfigurationsGroup OBJECT IDENTIFIER ::= { ciscoGtpDirectorMIBGroups 1 }
-- OBJECT-GROUP
--  Status
--    mandatory
--  Descr
--    A collection of GDM configuration objects.
--  objects
--    cgdCreatePdpRequestInfoSaveTimer

ciscoGtpDirectorStatusGroup OBJECT IDENTIFIER ::= { ciscoGtpDirectorMIBGroups 2 }
-- OBJECT-GROUP
--  Status
--    mandatory
--  Descr
--    A collection of GDM status.
--  objects
--    cgdPendingPdps

ciscoGtpDirectorStatisticsGroup OBJECT IDENTIFIER ::= { ciscoGtpDirectorMIBGroups 3 }
-- OBJECT-GROUP
--  Status
--    mandatory
--  Descr
--    A collection of GDM Statistics.
--  objects
--    cgdCreatePdpRequestFwded, cgdTotalCreatePdpRequestFwded, 
--    cgdCreateRequestRejected, cgdTotalUnsupportedMessages, 
--    cgdPdpRequestDropped

ciscoGtpDirectorNotifMgmtGroup OBJECT IDENTIFIER ::= { ciscoGtpDirectorMIBGroups 4 }
-- OBJECT-GROUP
--  Status
--    mandatory
--  Descr
--     A collection of objects related with notification
--    management on GDM.
--  objects
--    cgdNotifEnable, cgdNotifType

ciscoGtpDirectorNotifGroup OBJECT IDENTIFIER ::= { ciscoGtpDirectorMIBGroups 5 }
-- NOTIFICATION-GROUP
--  Status
--    mandatory
--  Descr
--    A collection of notifications.
--  notifications
--    ciscoGtpDirectorNotification

ciscoGtpDirectorMIBCompliance OBJECT IDENTIFIER ::= { ciscoGtpDirectorMIBCompliances 1 }
-- MODULE-COMPLIANCE
--  Status
--    mandatory
--  Descr
--    The compliance statements for entities which implement
--    CISCO-GDM-MIB.
--  Module
--    >>current<<
--   MandGroup
--    ciscoGtpDirectorConfigurationsGroup
--   MandGroup
--    ciscoGtpDirectorStatusGroup
--   MandGroup
--    ciscoGtpDirectorStatisticsGroup
--   MandGroup
--    ciscoGtpDirectorNotifMgmtGroup
--   MandGroup
--    ciscoGtpDirectorNotifGroup


END
