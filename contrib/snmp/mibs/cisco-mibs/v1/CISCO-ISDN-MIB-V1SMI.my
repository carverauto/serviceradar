-- MIB file created 09-Apr-2002 11:01:53, by
--   SMICng version 2.2.11-beta(PRO)(Solaris), January 20, 2001. Enterprise key cisco.com

CISCO-ISDN-MIB DEFINITIONS ::= BEGIN

-- From file: "CISCO-ISDN-MIB.my"
-- Compile options "4 7 F H N W 03 06 0B 0G 0N 0T"

IMPORTS
    DisplayString, TimeStamp, RowStatus
            FROM SNMPv2-TC-v1
    ciscoMgmt
            FROM CISCO-SMI
    ifIndex
            FROM IF-MIB
    isdnLapdOperStatus, isdnSignalingIndex, isdnSignalingIfIndex
            FROM ISDN-MIB
    Counter
            FROM RFC1155-SMI
    OBJECT-TYPE
            FROM RFC-1212
    TRAP-TYPE
            FROM RFC-1215;

ciscoIsdnMib OBJECT IDENTIFIER ::= { ciscoMgmt 26 }
-- MODULE-IDENTITY
--  LastUpdated
--    200102090000Z
--  OrgName
--    Cisco Systems, Inc.
--  ContactInfo
--           Cisco Systems
--     Customer Service
--    
--    Postal: 170 W Tasman Drive
--     San Jose, CA  95134
--     USA
--    
--       Tel: +1 800 553-NETS
--    
--    E-mail: cs-isdn@cisco.com
--  Descr
--    The MIB module to describe the status of the ISDN 
--     Interfaces on the routers.
--  RevDate
--    200102090000Z
--  RevDescr
--    For a call connects, demandNbrLastDuration, 
--     demandNbrClearReason, and demandNbrClearCode 
--     objects are not included in the trap.
--  RevDate
--    200003270000Z
--  RevDescr
--    Added demandNbrCNANotification when call rejected with
--     channel not available cause code
--  RevDate
--    200002230000Z
--  RevDescr
--    Removed an instantiated clause in description for 
--     ciscoCallHistoryCallingNumber.
--  RevDate
--    9905070000Z
--  RevDescr
--    Added a new trap for PRI layer 2 state changes.
--  RevDate
--    9602210000Z
--  RevDescr
--    Add a new object demandNbrCallOrigin.
--  RevDate
--    9508150000Z
--  RevDescr
--    Specify a correct (non-negative) range for an index
--    object.
--  RevDate
--    9501300000Z
--  RevDescr
--    Initial version of Cisco ISDN MIB.

ciscoIsdnMibObjects OBJECT IDENTIFIER ::= { ciscoIsdnMib 1 }
isdnNeighbor    OBJECT IDENTIFIER ::= { ciscoIsdnMibObjects 1 }
ciscoIsdnMibTrapPrefix OBJECT IDENTIFIER ::= { ciscoIsdnMib 2 }
ciscoIsdnMibTraps OBJECT IDENTIFIER ::= { ciscoIsdnMibTrapPrefix 0 }
ciscoIsdnMibConformance OBJECT IDENTIFIER ::= { ciscoIsdnMib 3 }
ciscoIsdnMibCompliances OBJECT IDENTIFIER ::= { ciscoIsdnMibConformance 1 }
ciscoIsdnMibGroups OBJECT IDENTIFIER ::= { ciscoIsdnMibConformance 2 }

demandNbrTable OBJECT-TYPE
    SYNTAX SEQUENCE OF DemandNbrEntry
    ACCESS not-accessible
    STATUS mandatory
    DESCRIPTION
        "The list of neighbors from which the router will accept calls or
        to which it will place them."
    ::= { isdnNeighbor 1 }

demandNbrEntry OBJECT-TYPE
    SYNTAX DemandNbrEntry
    ACCESS not-accessible
    STATUS mandatory
    DESCRIPTION
        "A single Neighbor. This entry is effectively permanent, and contains
        information describing the neighbor, his permissions, his last call
        attempt, and his cumulative effects."
    INDEX { demandNbrPhysIf, demandNbrId }
    ::= { demandNbrTable 1 }

DemandNbrEntry ::= SEQUENCE {
    demandNbrPhysIf INTEGER,
    demandNbrId INTEGER,
    demandNbrLogIf INTEGER,
    demandNbrName DisplayString,
    demandNbrAddress DisplayString,
    demandNbrPermission INTEGER,
    demandNbrMaxDuration INTEGER,
    demandNbrLastDuration INTEGER,
    demandNbrClearReason DisplayString,
    demandNbrClearCode OCTET STRING,
    demandNbrSuccessCalls Counter,
    demandNbrFailCalls Counter,
    demandNbrAcceptCalls Counter,
    demandNbrRefuseCalls Counter,
    demandNbrLastAttemptTime TimeStamp,
    demandNbrStatus RowStatus,
    demandNbrCallOrigin INTEGER
    }

demandNbrPhysIf OBJECT-TYPE
    SYNTAX INTEGER(1..2147483647)
    ACCESS not-accessible
    STATUS mandatory
    DESCRIPTION
        "ifIndex value of the physical interface the neighbor will be
        called on. On an ISDN interface, this is the ifIndex value of
        the D channel."
    ::= { demandNbrEntry 1 }

demandNbrId OBJECT-TYPE
    SYNTAX INTEGER(0..2147483647)
    ACCESS not-accessible
    STATUS mandatory
    DESCRIPTION
        "arbitrary sequence number associated with the neighbor."
    ::= { demandNbrEntry 2 }

demandNbrLogIf OBJECT-TYPE
    SYNTAX INTEGER(1..2147483647)
    ACCESS read-write
    STATUS mandatory
    DESCRIPTION
        "ifIndex value of virtual interface associated with the neighbor.
        This interface maintains a queue of messages holding for the neighbor
        awaiting call completion, and all statistics."
    ::= { demandNbrEntry 3 }

demandNbrName OBJECT-TYPE
    SYNTAX DisplayString
--    Rsyntax OCTET STRING(SIZE(0..255))
    ACCESS read-write
    STATUS mandatory
    DESCRIPTION
        "ASCII name of the neighbor."
    ::= { demandNbrEntry 4 }

demandNbrAddress OBJECT-TYPE
    SYNTAX DisplayString
--    Rsyntax OCTET STRING(SIZE(0..255))
    ACCESS read-write
    STATUS mandatory
    DESCRIPTION
        "Call Address  at which the neighbor should be called.
        Think of this as the set of characters following 'ATDT '
        or the 'phone number' included in a D channel call request."
    ::= { demandNbrEntry 5 }

demandNbrPermission OBJECT-TYPE
    SYNTAX INTEGER {
        iCanCallHim(1),
        heCanCallMe(2),
        weCanCallEachOther(3)
        }
    ACCESS read-write
    STATUS mandatory
    DESCRIPTION
        "applicable permissions."
    DEFVAL { weCanCallEachOther }
    ::= { demandNbrEntry 6 }

demandNbrMaxDuration OBJECT-TYPE
    SYNTAX INTEGER(1..2147483647)
--  Units
--    seconds
    ACCESS read-write
    STATUS mandatory
    DESCRIPTION
        "Maximum call duration in seconds."
    DEFVAL { 2147483647 }
    ::= { demandNbrEntry 7 }

demandNbrLastDuration OBJECT-TYPE
    SYNTAX INTEGER(1..2147483647)
--  Units
--    seconds
    ACCESS read-only
    STATUS mandatory
    DESCRIPTION
        "Duration of last call in seconds."
    ::= { demandNbrEntry 8 }

demandNbrClearReason OBJECT-TYPE
    SYNTAX DisplayString
--    Rsyntax OCTET STRING(SIZE(0..255))
    ACCESS read-only
    STATUS mandatory
    DESCRIPTION
        "ASCII reason that the last call terminated."
    ::= { demandNbrEntry 9 }

demandNbrClearCode OBJECT-TYPE
    SYNTAX OCTET STRING
    ACCESS read-only
    STATUS mandatory
    DESCRIPTION
        "encoded reason for the last call tear down."
    ::= { demandNbrEntry 10 }

demandNbrSuccessCalls OBJECT-TYPE
    SYNTAX Counter
    ACCESS read-only
    STATUS mandatory
    DESCRIPTION
        "number of completed calls to neighbor since system reset."
    ::= { demandNbrEntry 11 }

demandNbrFailCalls OBJECT-TYPE
    SYNTAX Counter
    ACCESS read-only
    STATUS mandatory
    DESCRIPTION
        "Number of call attempts that have failed."
    ::= { demandNbrEntry 12 }

demandNbrAcceptCalls OBJECT-TYPE
    SYNTAX Counter
    ACCESS read-only
    STATUS mandatory
    DESCRIPTION
        "Number of calls accepted from the neighbor."
    ::= { demandNbrEntry 13 }

demandNbrRefuseCalls OBJECT-TYPE
    SYNTAX Counter
    ACCESS read-only
    STATUS mandatory
    DESCRIPTION
        "Number of calls from neighbor that we have refused."
    ::= { demandNbrEntry 14 }

demandNbrLastAttemptTime OBJECT-TYPE
    SYNTAX TimeStamp
--    Rsyntax TimeTicks
    ACCESS read-only
    STATUS mandatory
    DESCRIPTION
        "sysUpTime of last call attempt."
    ::= { demandNbrEntry 15 }

demandNbrStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Somebody might want to manage the device using SNMP some day..."
    ::= { demandNbrEntry 16 }

demandNbrCallOrigin OBJECT-TYPE
    SYNTAX INTEGER {
        originate(1),
        answer(2),
        callback(3)
        }
    ACCESS read-only
    STATUS mandatory
    DESCRIPTION
        "Indication of outgoing or incoming call."
    ::= { demandNbrEntry 17 }

demandNbrCallInformation TRAP-TYPE
-- Reverse mappable trap
    ENTERPRISE ciscoIsdnMibTrapPrefix
    VARIABLES {
        demandNbrLogIf, demandNbrName, demandNbrAddress, 
        demandNbrLastDuration, demandNbrClearReason, 
        demandNbrClearCode }
--  Status
--    obsolete
    DESCRIPTION
        "This trap/inform is sent to the manager whenever a successful 
        call clears, or a failed call attempt is determined to have 
        ultimately failed. In the event that call retry is active, 
        then this is after all retry attempts have failed. However, 
        only one such trap is sent in between successful call
        attempts; subsequent call attempts result in no trap."
    ::= 1

demandNbrCallDetails TRAP-TYPE
-- Reverse mappable trap
    ENTERPRISE ciscoIsdnMibTrapPrefix
    VARIABLES {
        demandNbrLogIf, demandNbrName, demandNbrAddress, 
        demandNbrLastDuration, demandNbrClearReason, 
        demandNbrClearCode, demandNbrCallOrigin }
--  Status
--    mandatory
    DESCRIPTION
        "This trap/inform is sent to the manager whenever a call 
        connects, or  clears, or a failed call attempt is determined to 
        have ultimately failed. In the event that call retry is active, 
        then this is after all retry attempts have failed. However, 
        only one such trap is sent in between successful call
        attempts; subsequent call attempts result in no trap.
         
        Whenever a call connects, demandNbrLastDuration, 
        demandNbrClearReason, and demandNbrClearCode objects are not
        included in the trap."
    ::= 2

demandNbrLayer2Change TRAP-TYPE
-- Reverse mappable trap
    ENTERPRISE ciscoIsdnMibTrapPrefix
    VARIABLES {
        ifIndex, isdnLapdOperStatus }
--  Status
--    mandatory
    DESCRIPTION
        "This trap/inform is sent to the manager whenever the
        D-channel of an interface changes state."
    ::= 3

demandNbrCNANotification TRAP-TYPE
-- Reverse mappable trap
    ENTERPRISE ciscoIsdnMibTrapPrefix
    VARIABLES {
        isdnSignalingIfIndex, ifIndex }
--  Status
--    mandatory
    DESCRIPTION
        "This trap/inform is sent to the manager whenever the
         an incoming call request is rejected with cause
         'requested circuit/channel not available' (CNA),
         code number 44.
        
         isdnSignalingIfIndex is the ifIndex value of the interface
         associated with this signaling channel.
        
         ifIndex is the interface index of the requested bearer channel "
    ::= 4

ciscoIsdnMibGroup OBJECT IDENTIFIER ::= { ciscoIsdnMibGroups 1 }
-- OBJECT-GROUP
--  Status
--    mandatory
--  Descr
--    A collection of objects providing the ISDN MIB capability.
--  objects
--    demandNbrLogIf, demandNbrName, demandNbrAddress, 
--    demandNbrPermission, demandNbrMaxDuration, 
--    demandNbrLastDuration, demandNbrClearReason, 
--    demandNbrClearCode, demandNbrSuccessCalls, demandNbrFailCalls, 
--    demandNbrAcceptCalls, demandNbrRefuseCalls, 
--    demandNbrLastAttemptTime, demandNbrStatus

ciscoIsdnMibGroupRev1 OBJECT IDENTIFIER ::= { ciscoIsdnMibGroups 2 }
-- OBJECT-GROUP
--  Status
--    mandatory
--  Descr
--    A collection of objects providing the call origin capability.
--  objects
--    demandNbrLogIf, demandNbrName, demandNbrAddress, 
--    demandNbrPermission, demandNbrMaxDuration, 
--    demandNbrLastDuration, demandNbrClearReason, 
--    demandNbrClearCode, demandNbrSuccessCalls, demandNbrFailCalls, 
--    demandNbrAcceptCalls, demandNbrRefuseCalls, 
--    demandNbrLastAttemptTime, demandNbrStatus, 
--    demandNbrCallOrigin

ciscoIsdnMibCompliance OBJECT IDENTIFIER ::= { ciscoIsdnMibCompliances 1 }
-- MODULE-COMPLIANCE
--  Status
--    mandatory
--  Descr
--    The compliance statement for entities which implement
--    the Cisco ISDN MIB
--  Module
--    >>current<<
--   MandGroup
--    ciscoIsdnMibGroup

ciscoIsdnMibComplianceRev1 OBJECT IDENTIFIER ::= { ciscoIsdnMibCompliances 2 }
-- MODULE-COMPLIANCE
--  Status
--    mandatory
--  Descr
--    The compliance statement for entities which implement
--    the Cisco ISDN MIB
--  Module
--    >>current<<
--   MandGroup
--    ciscoIsdnMibGroupRev1


END
