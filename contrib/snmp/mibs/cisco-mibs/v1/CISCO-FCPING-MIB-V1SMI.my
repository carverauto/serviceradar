-- MIB file created 27-Dec-2002 14:30:01, by
--   SMICng version 2.2.11-beta(PRO)(Solaris), January 20, 2001. Enterprise key cisco.com

CISCO-FCPING-MIB DEFINITIONS ::= BEGIN

-- From file: "CISCO-FCPING-MIB.my"
-- Compile options "4 7 F H N W 03 06 0B 0G 0N 0T"

IMPORTS
    RowStatus, TruthValue
            FROM SNMPv2-TC-v1
    ciscoMgmt
            FROM CISCO-SMI
    VsanIndex, FcAddress, FcAddressType
            FROM CISCO-ST-TC
    Gauge
            FROM RFC1155-SMI
    OBJECT-TYPE
            FROM RFC-1212
    TRAP-TYPE
            FROM RFC-1215;

ciscoFcPingMIB OBJECT IDENTIFIER ::= { ciscoMgmt 295 }
-- MODULE-IDENTITY
--  LastUpdated
--    200210070000Z
--  OrgName
--    Cisco Systems Inc.
--  ContactInfo
--         Cisco Systems 
--          Customer Service 
--    Postal: 170 W Tasman Drive 
--          San Jose, CA  95134 
--          USA 
--    Tel: +1 800 553 -NETS 
--    E-mail: cs-san@cisco.com
--  Descr
--    The MIB module for the management of the 
--     Fibre Channel Ping functionality.
--  RevDate
--    200210070000Z
--  RevDescr
--    Initial version of this MIB module.

ciscoFcPingMIBObjects OBJECT IDENTIFIER ::= { ciscoFcPingMIB 1 }
fcPingMIBConformance OBJECT IDENTIFIER ::= { ciscoFcPingMIB 2 }
fcPingConfiguration OBJECT IDENTIFIER ::= { ciscoFcPingMIBObjects 1 }
fcPingStats     OBJECT IDENTIFIER ::= { ciscoFcPingMIBObjects 2 }
fcPingNotification OBJECT IDENTIFIER ::= { ciscoFcPingMIBObjects 3 }
fcPingNotifications OBJECT IDENTIFIER ::= { fcPingNotification 0 }
fcPingMIBCompliances OBJECT IDENTIFIER ::= { fcPingMIBConformance 1 }
fcPingMIBGroups OBJECT IDENTIFIER ::= { fcPingMIBConformance 2 }

FcStartOper ::= INTEGER {
        enable(1),
        disable(2)
        }
-- TEXTUAL-CONVENTION
--  Status
--    mandatory
--  Descr
--    Enable/disable an operation. 
--     enable(1) - enable the operation. 
--     disable(2) - disable the operation.

fcPingTable OBJECT-TYPE
    SYNTAX SEQUENCE OF FcPingEntry
    ACCESS not-accessible
    STATUS mandatory
    DESCRIPTION
        "A table of ping request entries. 
         This table contains a set of ping requests 
         which need to be executed at the agent."
    ::= { fcPingConfiguration 1 }

fcPingEntry OBJECT-TYPE
    SYNTAX FcPingEntry
    ACCESS not-accessible
    STATUS mandatory
    DESCRIPTION
        "A ping request entry. 
        
         A management station wishing to create an entry 
         should generate a pseudo-random number to be  
         used as an index into this table and create an  
         instance of the fcPingRowStatus object. After that,  
         the management station should set the corresponding  
         instance of fcPingAddress object with the address of  
         the destination that should be pinged and  
         fcPingVsanIndex with the desired VSAN number. 
        
         Once the appropriate instance of all the configuration 
         objects have been created, either by an explicit SNMP 
         set request or by default, the row status should be  
         set to active to initiate the ping sequence. Note that 
         this entire procedure may be initiated via a single 
         set request which specifies a row status of  
         createAndGo as well as specifies valid values for the  
         non-defaulted configuration objects.  
        
         Once the ping sequence has been initiated it can 
         be stopped by setting the corresponding instance 
         of fcPingRowStatus to 'destroy'. 
        
         The results of the ping operation are made available 
         in the fcPingStats table. For a ping entry uniquely 
         identified by fcPingIndex, an entry will be created  
         in the fcPingStats table automatically by the agent.  
        
         Once the ping sequence completes, the management  
         station should retrieve the statistics of interest  
         from the fcPingStats table and delete the entry from  
         the fcPingTable. The corresponding entry in the 
         fcPingStats table shall be deleted automatically by  
         the agent. 
        
         In order to prevent old entries from clogging the  
         table, entries will be aged out, but an entry will  
         never be deleted within fcPingAgeInterval  
         milliseconds of completing. 
        
         If the management station wishes to repeat the ping 
         sequence to a particular destination, then it will 
         need to set the corresponding instance of  
         fcPingAdminStatus to 'enable' again."
    INDEX { fcPingIndex }
    ::= { fcPingTable 1 }

FcPingEntry ::= SEQUENCE {
    fcPingIndex INTEGER,
    fcPingVsanIndex VsanIndex,
    fcPingAddressType FcAddressType,
    fcPingAddress FcAddress,
    fcPingPacketCount Gauge,
    fcPingPayloadSize Gauge,
    fcPingPacketTimeout Gauge,
    fcPingDelay Gauge,
    fcPingAgeInterval Gauge,
    fcPingUsrPriority INTEGER,
    fcPingAdminStatus FcStartOper,
    fcPingOperStatus INTEGER,
    fcPingTrapOnCompletion TruthValue,
    fcPingRowStatus RowStatus
    }

fcPingIndex OBJECT-TYPE
    SYNTAX INTEGER(1..2147483647)
    ACCESS not-accessible
    STATUS mandatory
    DESCRIPTION
        "The index of a ping entry. This object uniquely 
         identifies a ping request entry on a VSAN."
    ::= { fcPingEntry 1 }

fcPingVsanIndex OBJECT-TYPE
    SYNTAX VsanIndex
--    Rsyntax INTEGER(1..4094)
    ACCESS read-write
    STATUS mandatory
    DESCRIPTION
        "This object identifies the VSAN to which this ping 
         request belongs. This object cannot be modified 
         if the corresponding instance of fcPingOperStatus 
         object has a value of 'inProgress'."
    DEFVAL { 1 }
    ::= { fcPingEntry 2 }

fcPingAddressType OBJECT-TYPE
    SYNTAX FcAddressType
--    Rsyntax INTEGER {
--        wwn(1),
--        fcid(2)
--        }
    ACCESS read-write
    STATUS mandatory
    DESCRIPTION
        "The format of the corresponding instance of 
         fcPingAddress object."
    DEFVAL { wwn }
    ::= { fcPingEntry 3 }

fcPingAddress OBJECT-TYPE
    SYNTAX FcAddress
--    Rsyntax OCTET STRING(SIZE(3|8))
    ACCESS read-write
    STATUS mandatory
    DESCRIPTION
        "The address of the device to be pinged. 
        
         If the value of the corresponding instance of 
         fcPingAddressType object is 'wwn', then this 
         object will contain an 8 octet long WWN. 
        
         If the value of the corresponding instance of 
         fcPingAddressType object is 'fcid', then this 
         object will contain a 3 octet long FCID. 
        
         This object MUST be set to a valid value before 
         or concurrently with setting the corresponding 
         instance of fcPingRowStatus to 'active'."
    ::= { fcPingEntry 4 }

fcPingPacketCount OBJECT-TYPE
    SYNTAX Gauge(1..2147483647)
    ACCESS read-write
    STATUS mandatory
    DESCRIPTION
        "The number of ping packets to be sent to the 
         target in this sequence. This object cannot 
         be modified if the corresponding instance 
         of fcPingOperStatus object has a value of 
         'inProgress'."
    DEFVAL { 5 }
    ::= { fcPingEntry 5 }

fcPingPayloadSize OBJECT-TYPE
    SYNTAX Gauge(0..1884)
    ACCESS read-write
    STATUS mandatory
    DESCRIPTION
        "This object specifies the size of the ping packet 
         payload to be sent to the target in this sequence. 
         This object cannot be modified if the 
         corresponding instance of fcPingOperStatus object 
         has a value of 'inProgress'."
    DEFVAL { 0 }
    ::= { fcPingEntry 6 }

fcPingPacketTimeout OBJECT-TYPE
    SYNTAX Gauge(1..10)
--  Units
--    seconds
    ACCESS read-write
    STATUS mandatory
    DESCRIPTION
        "The amount of time to wait for a response to a  
         transmitted packet before declaring the packet 
         'dropped'. This object cannot be modified if 
         the corresponding instance of fcPingOperStatus 
         object has a value of 'inProgress'."
    DEFVAL { 2 }
    ::= { fcPingEntry 7 }

fcPingDelay OBJECT-TYPE
    SYNTAX Gauge(0..3600000)
--  Units
--    milliseconds
    ACCESS read-write
    STATUS mandatory
    DESCRIPTION
        "The minimum amount of time to wait before sending  
         the next packet in a sequence, after receiving a  
         response or declaring a timeout for a previously 
         transmitted packet. This object cannot be 
         modified if the corresponding instance of 
         fcPingOperStatus object has a value of 
         'inProgress'."
    DEFVAL { 0 }
    ::= { fcPingEntry 8 }

fcPingAgeInterval OBJECT-TYPE
    SYNTAX Gauge(500000..900000)
--  Units
--    milliseconds
    ACCESS read-write
    STATUS mandatory
    DESCRIPTION
        "The amount of time to wait after the ping sequence 
         completes before the ping entry is aged out. 
         This object cannot be modified if the 
         corresponding instance of fcPingOperStatus object 
         has a value of 'inProgress'."
    DEFVAL { 500000 }
    ::= { fcPingEntry 9 }

fcPingUsrPriority OBJECT-TYPE
    SYNTAX INTEGER {
        high(1),
        low(2)
        }
    ACCESS read-write
    STATUS mandatory
    DESCRIPTION
        "This object determines the queuing priority 
         and drop probability this sequence of ping 
         packets experience in the switches through 
         which they pass through. 
        
         If the value of this object is set to 'high', 
         then the corresponding sequence of packets 
         will experience high queueing priority and 
         low drop probability in the switches through 
         which they pass through. 
        
         If the value of this object is set to 'low', 
         then the corresponding sequence of packets 
         will experience low queueing priority and 
         higher drop probability in the switches  
         through which they pass through. 
         
         This object cannot be modified if the 
         corresponding instance of fcPingOperStatus 
         object has a value of 'inProgress'."
    DEFVAL { low }
    ::= { fcPingEntry 10 }

fcPingAdminStatus OBJECT-TYPE
    SYNTAX FcStartOper
--    Rsyntax INTEGER {
--        enable(1),
--        disable(2)
--        }
    ACCESS read-write
    STATUS mandatory
    DESCRIPTION
        "This object specifies the desired state that a  
         fcPingEntry should be in: 
        
         enable(1)  -  Attempt to activate the ping as  
                       defined by this entry. 
        
         disable(2) -  Deactivate the ping as defined by 
                       this entry. 
        
         The actual operational state of this test is  
         indicated by the corresponding instance of  
         fcPingOperStatus. 
        
         When the ping sequence corresponding to this entry 
         is executing, this object cannot be modified. If this 
         object is read at such a time, a value of 'enable'  
         will be returned. When the ping sequence completes,  
         the value of this object will be made 'disable'  
         automatically by the agent."
    DEFVAL { disable }
    ::= { fcPingEntry 11 }

fcPingOperStatus OBJECT-TYPE
    SYNTAX INTEGER {
        inProgress(1),
        complete(2),
        disabled(3),
        failure(4)
        }
    ACCESS read-only
    STATUS mandatory
    DESCRIPTION
        "This object indicates the operational status 
         of this fcPingEntry. 
        
         inProgress(1)  -  Indicates that the ping sequence 
                           as defined by this instance of 
                           fcPingEntry is currently running. 
        
         complete(2)    -  Indicates that the ping sequence 
                           as defined by this instance of 
                           fcPingEntry is currently  
                           complete. 
        
         disabled(3)    -  Indicates that the ping sequence 
                           as defined by this instance of 
                           fcPingEntry is currently disabled. 
        
         failure(4)     -  Indicates that the ping sequence 
                           as defined by this instance of 
                           fcPingEntry has currently failed  
                           due to resource limitations. 
        
         Initially the value of this object will be 
         'inProgress' when the ping sequence is being 
         executed. Once the ping sequence is completed, 
         the value of this object will transition to 
         'complete'. 
        
         If the value of the corresponding instance of 
         fcPingAdminStatus is 'disable', then this object 
         will have a value of 'disabled'."
    ::= { fcPingEntry 12 }

fcPingTrapOnCompletion OBJECT-TYPE
    SYNTAX TruthValue
--    Rsyntax INTEGER {
--        true(1),
--        false(2)
--        }
    ACCESS read-write
    STATUS mandatory
    DESCRIPTION
        "This specifies if fcPingCompletionNotify notification 
         should be generated or not when the corresponding 
         ping sequence completes. 
        
         If this object is set to 'true', then the  
         notification is generated. 
        
         If this object is set to 'false', then the  
         notification is not generated. 
        
         This object cannot be modified if the 
         corresponding instance of fcPingOperStatus 
         object has a value of 'inProgress'."
    DEFVAL { false }
    ::= { fcPingEntry 13 }

fcPingRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this conceptual row. 
        
         When a ping sequence is being executed, if this 
         object is set to 'destroy', then the 
         corresponding ping sequence will be stopped."
    ::= { fcPingEntry 14 }

fcPingStatsTable OBJECT-TYPE
    SYNTAX SEQUENCE OF FcPingStatsEntry
    ACCESS not-accessible
    STATUS mandatory
    DESCRIPTION
        "A table of ping statistics. 
         The statistics corresponding to the entries 
         in the fcPingTable. When an entry is deleted 
         in the fcPingTable, the corresponding entry 
         in this table is deleted automatically by 
         the agent."
    ::= { fcPingStats 1 }

fcPingStatsEntry OBJECT-TYPE
    SYNTAX FcPingStatsEntry
    ACCESS not-accessible
    STATUS mandatory
    DESCRIPTION
        "A ping statistics entry. 
        
         An entry shall be created automatically in this 
         table whenever a ping request is activated in the 
         fcPingTable by setting the fcPingRowStatus to 
         'active'. This entry shall have the same indices 
         as the entry that got activated in the fcPingTable. 
        
         An entry in this table shall be deleted by the 
         agent automatically either when the corresponding 
         entry in the fcPingTable is deleted by the 
         management station or is aged out by the agent. 
        
         This table shall be empty if there is no 'active' 
         entry in the fcPingTable."
    INDEX { fcPingIndex }
    ::= { fcPingStatsTable 1 }

FcPingStatsEntry ::= SEQUENCE {
    fcPingTxPackets Gauge,
    fcPingRxPackets Gauge,
    fcPingMinRtt INTEGER,
    fcPingAvgRtt INTEGER,
    fcPingMaxRtt INTEGER,
    fcPingNumTimeouts Gauge
    }

fcPingTxPackets OBJECT-TYPE
    SYNTAX Gauge
    ACCESS read-only
    STATUS mandatory
    DESCRIPTION
        "The number of ping packets sent to the target in  
         this sequence."
    ::= { fcPingStatsEntry 1 }

fcPingRxPackets OBJECT-TYPE
    SYNTAX Gauge
    ACCESS read-only
    STATUS mandatory
    DESCRIPTION
        "The number of ping packets received from the target 
         in this sequence."
    ::= { fcPingStatsEntry 2 }

fcPingMinRtt OBJECT-TYPE
    SYNTAX INTEGER(0..10000000)
--  Units
--    microseconds
    ACCESS read-only
    STATUS mandatory
    DESCRIPTION
        "The minimum round trip time of all the packets that 
         have been sent in this sequence."
    ::= { fcPingStatsEntry 3 }

fcPingAvgRtt OBJECT-TYPE
    SYNTAX INTEGER(0..10000000)
--  Units
--    microseconds
    ACCESS read-only
    STATUS mandatory
    DESCRIPTION
        "The average round trip time of all the packets that 
         have been sent in this sequence."
    ::= { fcPingStatsEntry 4 }

fcPingMaxRtt OBJECT-TYPE
    SYNTAX INTEGER(0..10000000)
--  Units
--    microseconds
    ACCESS read-only
    STATUS mandatory
    DESCRIPTION
        "The maximum round trip time of all the packets that 
         have been sent in this sequence."
    ::= { fcPingStatsEntry 5 }

fcPingNumTimeouts OBJECT-TYPE
    SYNTAX Gauge
    ACCESS read-only
    STATUS mandatory
    DESCRIPTION
        "The number of timeouts encountered in this sequence."
    ::= { fcPingStatsEntry 6 }

fcPingCompletionNotify TRAP-TYPE
-- Reverse mappable trap
    ENTERPRISE fcPingNotification
    VARIABLES {
        fcPingAddress, fcPingTxPackets, fcPingRxPackets }
--  Status
--    mandatory
    DESCRIPTION
        "This notification is generated whenever a sequence 
         of pings is complete and the corresponding instance 
         of fcPingTrapOnCompletion object has been set to  
         'true'."
    ::= 1

fcPingConfigGroup OBJECT IDENTIFIER ::= { fcPingMIBGroups 1 }
-- OBJECT-GROUP
--  Status
--    mandatory
--  Descr
--    A collection of objects for configuring  
--     Fibre Channel Ping.
--  objects
--    fcPingVsanIndex, fcPingAddressType, fcPingAddress, 
--    fcPingPacketCount, fcPingPayloadSize, fcPingPacketTimeout, 
--    fcPingDelay, fcPingAgeInterval, fcPingUsrPriority, 
--    fcPingAdminStatus, fcPingOperStatus, fcPingTrapOnCompletion, 
--    fcPingRowStatus

fcPingStatsGroup OBJECT IDENTIFIER ::= { fcPingMIBGroups 2 }
-- OBJECT-GROUP
--  Status
--    mandatory
--  Descr
--    A collection of objects for displaying  
--     Fibre Channel Ping statistics.
--  objects
--    fcPingTxPackets, fcPingRxPackets, fcPingMinRtt, fcPingAvgRtt, 
--    fcPingMaxRtt, fcPingNumTimeouts

fcPingNotifyGroup OBJECT IDENTIFIER ::= { fcPingMIBGroups 3 }
-- NOTIFICATION-GROUP
--  Status
--    mandatory
--  Descr
--    A collection of notification(s) for monitoring 
--     Fibre Channel Ping completion.
--  notifications
--    fcPingCompletionNotify

fcPingMIBCompliance OBJECT IDENTIFIER ::= { fcPingMIBCompliances 1 }
-- MODULE-COMPLIANCE
--  Status
--    mandatory
--  Descr
--    The compliance statement for entities which 
--     implement the Fibre Channel Ping module.
--  Module
--    >>current<<
--   MandGroup
--    fcPingConfigGroup
--   MandGroup
--    fcPingStatsGroup
--   MandGroup
--    fcPingNotifyGroup
--   ObjVar
--    fcPingRowStatus


END
