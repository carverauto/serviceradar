-- MIB file created 25-Jun-2005 01:14:15, by
--   SMICng version 2.2.11-beta(PRO)(Solaris), January 20, 2001. Enterprise key cisco.com

CISCO-SIP-UA-MIB DEFINITIONS ::= BEGIN

-- From file: "CISCO-SIP-UA-MIB.my"
-- Compile options "4 7 F H N O W 03 06 0B 0G 0N 0T"

IMPORTS
    SnmpAdminString
            FROM SNMP-FRAMEWORK-MIB
    ciscoMgmt
            FROM CISCO-SMI
    InterfaceIndexOrZero
            FROM IF-MIB
    StorageType, TruthValue
            FROM SNMPv2-TC-v1
    Counter, Gauge
            FROM RFC1155-SMI
    OBJECT-TYPE
            FROM RFC-1212;

ciscoSipUaMIB OBJECT IDENTIFIER ::= { ciscoMgmt 152 }
-- MODULE-IDENTITY
--  LastUpdated
--    200402190000Z
--  OrgName
--    Cisco Systems, Inc.
--  ContactInfo
--           Cisco Systems
--            Customer Service
--    
--    Postal: 170 W. Tasman Drive
--            San Jose, CA  95134
--            USA
--    
--    Tel: +1 800 553-NETS
--    
--    E-mail: cs-sip@cisco.com
--  Descr
--    Cisco User Agent Session Initiation Protocol (SIP) 
--     MIB module.  SIP is an application-layer signalling
--     protocol for creating, modifying and terminating
--     multimedia sessions with one or more participants.
--     These sessions include Internet multimedia conferences
--     and Internet telephone calls.  SIP is defined in 
--     RFC 2543 (March 1999).  
--    
--     This MIB is defined for the management of SIP User 
--     Agents (UAs).  A User Agent is an application which 
--     contains both a User Agent Client (UAC) and a User 
--     Agent Server (UAS).   A UAC is an application that 
--     initiates a SIP request.  A UAS is an application that 
--     contacts the user when a SIP request is received and 
--     that returns a response on behalf of the user.  The 
--     response accepts, rejects, or redirects the request.
--    
--     A SIP transaction occurs between a client and a server 
--     and comprises all messages from the first request sent
--     from the client to the server up to a final (non-1xx) 
--     response sent from the server to the client.
--  RevDate
--    200402190000Z
--  RevDescr
--     Addition of the following objects:
--      cSipCfgSuspendResumeEnabled
--      cSipCfgTimerHold
--      cSipCfgTimerInfo
--      cSipCfgTimerConnectionAging
--      cSipCfgTimerBufferInvite
--      cSipCfgRetryInfo
--      cSipCfgRetrySubscribe
--      cSipCfgOfferCallHold
--      cSipCfgPeerSwitchTransEnabled
--      cSipCfgSwitchTransportEnabled
--      cSipCfgMaximumForwards
--      cSipCfgReasonHeaderOveride
--    
--      cSipCfgBindSourceAddrTable ->
--          cSipCfgBindSourceAddrEntry 
--          cSipCfgBindSourceAddrScope 
--          cSipCfgBindSourceAddrInterface 
--      cSipCfgVoiceServiceVoip ->
--          cSipCfgHeaderPassingEnabled
--          cSipCfgMaxSubscriptionAccept 
--          cSipCfgMaxSubscriptionOriginate
--    
--      cSipStatsRedirMovedTempsIns
--      cSipStatsRedirMovedTempsOuts
--      cSipStatsRetryInfo
--      cSipStatsRetrySubscribe
--      cSipStatsClientReqPendingIns
--      cSipStatsClientReqPendingOuts
--      cSipStatsTrafficUpdateIns
--      cSipStatsTrafficUpdateOuts
--      cSipStatsConnTCPSendFailures
--      cSipStatsConnUDPSendFailures
--      cSipStatsConnTCPRemoteClosures
--      cSipStatsConnUDPCreateFailures
--      cSipStatsConnTCPCreateFailures
--      cSipStatsConnUDPInactiveTimeouts
--      cSipStatsConnTCPInactiveTimeouts
--      cSipStatsActiveUDPConnections
--      cSipStatsActiveTCPConnections
--    
--      Deprecated the following objects:
--      cSipCfgMaxForwards
--      cSipStatsRedirMovedTemps
--      cSipCfgBindSrcAddrScope
--      cSipCfgBindSrcAddrInterface
--    
--      Addition of the following Conformance objects:
--      ciscoSipTrafficStatsGroupRev3
--      ciscoSipStatsRedirStatusCodesGroupRev2
--      ciscoSipTimerConfigGroupRev4
--      ciscoSipRetryStatsGroupRev4
--      ciscoSipBaseIOSConfigGroupRev1
--      ciscoSipStatsClientStatusCodesGroupRev4
--      ciscoSipRetryConfigGroupRev4
--      ciscoSipCfgPeerGroupRev1
--      ciscoSipCfgVoiceServiceVoipGroup
--      ciscoSipStatsConnectionGroup
--    
--      Deprecated the following Conformance objects:
--      ciscoSipTrafficStatsGroupRev2
--      ciscoSipStatsRedirStatusCodesGroupRev1
--      ciscoSipTimerConfigGroupRev3
--      ciscoSipRetryStatsGroupRev3
--      ciscoSipBaseIOSConfigGroup
--      ciscoSipStatsClientStatusCodesGroupRev3
--      ciscoSipRetryConfigGroupRev3
--      ciscoSipCfgPeerGroup
--    
--      Addition of the following Compliance object:
--      ciscoSipComplianceRev5
--    
--      Deprecated the following Compliance object:
--      ciscoSipComplianceRev4
--  RevDate
--    200205080000Z
--  RevDescr
--     Addition of the following textual conventions:
--       CSipStatusCode
--       CSipMethodStr
--    
--      Addition of the following objects:
--       cSipCfgRedirectionDisabled
--       cSipCfgTimerSessionTimer
--       cSipCfgEarlyMediaTable
--           cSipCfgEarlyMediaStatusCodeIndex
--           cSipCfgEarlyMediaCutThruDisabled
--       cSipStatsClientSTTooSmallIns
--       cSipStatsClientSTTooSmallOuts
--       cSipStatsMisc3xxMappedTo4xxRsps
--       cSipStatsSuccessOkTable
--           cSipStatsSuccessOkMethod
--           cSipStatsSuccessOkInbounds
--           cSipStatsSuccessOkOutbounds
--       cSipCfgSymNatEnabled
--       cSipCfgSymNatDirectionRole
--  RevDate
--    200110050000Z
--  RevDescr
--    Obsoleting  cSipStatsRedirSeeOthers, 
--     cSipStatsClientLengthRequiredIns and
--     cSipStatsClientLengthRequiredOuts.
--     Add cSipCfgTimerRefer, cSipCfgRetryRefer,
--     and cSipStatsRetryRefers.
--     Deprecated old-style ciscoSipUaMIBNotificationPrefix.
--  RevDate
--    200109070000Z
--  RevDescr
--    Neglected to deprecate 
--     ciscoSipStatsClientStatusCodesGroupRev1 
--     in the previous revision where 
--     ciscoSipStatsClientStatusCodesGroupRev2 
--     was made current.
--  RevDate
--    200108210000Z
--  RevDescr
--    Deprecating cSipStatsRedirSeeOthers, 
--     cSipStatsClientLengthRequiredIns and
--     cSipStatsClientLengthRequiredOuts.
--     The SIP status codes related to these
--     counters have been removed from 
--     RFC2543bis03 version of the standard.
--  RevDate
--    200108020000Z
--  RevDescr
--    Addition of the following objects:
--       cSipCfgAaaUsername
--       cSipStatsTrafficInfoIns
--       cSipStatsTrafficInfoOuts
--       cSipStatsTrafficSubscribeIns
--       cSipStatsTrafficSubscribeOuts
--       cSipStatsClientBadEventIns
--       cSipStatsClientBadEventOuts
--  RevDate
--    200106070000Z
--  RevDescr
--    Addition of the following objects:
--       cSipCfgBindSrcAddrInterface
--       cSipCfgBindSrcAddrScope
--       cSipCfgDnsSrvQueryStringFormat
--       cSipStatsTrafficReferIns
--       cSipStatsTrafficReferOuts
--       cSipStatsTrafficNotifyIns
--       cSipStatsTrafficNotifyOuts
--       cSipStatsSuccessAcceptedIns
--       cSipStatsSuccessAcceptedOuts
--       cSipCfgTimerNotify 
--       cSipCfgRetryNotify
--       cSipCfgStatusCodeIndex   
--       cSipCfgPstnCause
--       cSipCfgStatusCauseStoreStatus
--       cSipCfgPstnCauseIndex
--       cSipCfgStatusCode   
--       cSipCfgCauseStatusStoreStatus
--       cSipStatsRetryNotifys
--  RevDate
--    200103020000Z
--  RevDescr
--    Addition of the following objects:
--       cSipCfgMaxForwards
--       cSipCfgTimerPrack
--       cSipCfgTimerComet
--       cSipCfgTimerReliableRsp
--       cSipCfgRetryPrack
--       cSipCfgRetryComet
--       cSipCfgRetryReliableRsp
--       cSipCfgOutSessionTransport
--       cSipCfgReliable1xxRspStr
--       cSipCfgReliable1xxRspHdr
--       cSipCfgUrlType
--       cSipCfgPeerTable
--           cSipCfgPeerIndex
--           cSipCfgPeerOutSessionTransport
--           cSipCfgPeerReliable1xxRspStr
--           cSipCfgPeerReliable1xxRspHdr
--           cSipCfgPeerUrlType
--       cSipStatsClientReqTermIns
--       cSipStatsClientReqTermOuts
--       cSipStatsClientNoAcceptHereIns
--       cSipStatsClientNoAcceptHereOuts
--       cSipStatsServerPrecondFailureIns
--       cSipStatsServerPrecondFailureOuts
--       cSipStatsTrafficCometIns
--       cSipStatsTrafficCometOuts
--       cSipStatsTrafficPrackIns
--       cSipStatsTrafficPrackOuts
--       cSipStatsRetryPrack
--       cSipStatsRetryComets
--       cSipStatsRetryReliable1xxRsps

ciscoSipUaMIBNotifs OBJECT IDENTIFIER ::= { ciscoSipUaMIB 0 }
ciscoSipUaMIBObjects OBJECT IDENTIFIER ::= { ciscoSipUaMIB 1 }
cSipCfg         OBJECT IDENTIFIER ::= { ciscoSipUaMIBObjects 1 }
cSipCfgBase     OBJECT IDENTIFIER ::= { cSipCfg 1 }
cSipCfgTimer    OBJECT IDENTIFIER ::= { cSipCfg 2 }
cSipCfgRetry    OBJECT IDENTIFIER ::= { cSipCfg 3 }
cSipCfgPeer     OBJECT IDENTIFIER ::= { cSipCfg 4 }
cSipCfgStatusCauseMap OBJECT IDENTIFIER ::= { cSipCfg 5 }
cSipCfgAaa      OBJECT IDENTIFIER ::= { cSipCfg 6 }
cSipCfgVoiceServiceVoip OBJECT IDENTIFIER ::= { cSipCfg 7 }
cSipStats       OBJECT IDENTIFIER ::= { ciscoSipUaMIBObjects 2 }
cSipStatsInfo   OBJECT IDENTIFIER ::= { cSipStats 1 }
cSipStatsSuccess OBJECT IDENTIFIER ::= { cSipStats 2 }
cSipStatsRedirect OBJECT IDENTIFIER ::= { cSipStats 3 }
cSipStatsErrClient OBJECT IDENTIFIER ::= { cSipStats 4 }
cSipStatsErrServer OBJECT IDENTIFIER ::= { cSipStats 5 }
cSipStatsGlobalFail OBJECT IDENTIFIER ::= { cSipStats 6 }
cSipStatsTraffic OBJECT IDENTIFIER ::= { cSipStats 7 }
cSipStatsRetry  OBJECT IDENTIFIER ::= { cSipStats 8 }
cSipStatsMisc   OBJECT IDENTIFIER ::= { cSipStats 9 }
cSipStatsConnection OBJECT IDENTIFIER ::= { cSipStats 10 }
ciscoSipUaMIBConformance OBJECT IDENTIFIER ::= { ciscoSipUaMIB 3 }
ciscoSipUaMIBCompliances OBJECT IDENTIFIER ::= { ciscoSipUaMIBConformance 1 }
ciscoSipUaMIBGroups OBJECT IDENTIFIER ::= { ciscoSipUaMIBConformance 2 }

ciscoSipUaMIBNotificationPrefix OBJECT IDENTIFIER ::= { ciscoSipUaMIB 2 }
-- OBJECT-IDENTITY
--  Status
--    deprecated
--  Descr
--    Old style notification prefixing.  Being replaced by
--     ciscoSipUaMIBNotifs.

ciscoSipUaMIBNotifications OBJECT IDENTIFIER ::= { ciscoSipUaMIBNotificationPrefix 0 }
-- OBJECT-IDENTITY
--  Status
--    deprecated
--  Descr
--    Old style notification prefixing.  Being replaced by
--     ciscoSipUaMIBNotifs.

CSipStatusCode ::= INTEGER(1..2147483647)
-- TEXTUAL-CONVENTION
--  Status
--    mandatory
--  Descr
--    A textual convention reflecting a SIP 
--     response status code value.

CSipMethodStr ::= OCTET STRING(SIZE(1..32))
-- TEXTUAL-CONVENTION
--  Status
--    mandatory
--  Descr
--    A textual convention reflecting SIP methods 
--     supported by this user agent.  SIP methods 
--     are case-sensitive.  Therefore, objects using 
--     this textual convention must also have values
--     that are case-sensitive.  All SIP methods must
--     be represented as all upper case ASCII strings.  
--     For example, 'INVITE'.

cSipCfgVersion OBJECT-TYPE
    SYNTAX SnmpAdminString
--    Rsyntax OCTET STRING(SIZE(0..255))
    ACCESS read-only
    STATUS mandatory
    DESCRIPTION
        "This object will reflect the version of SIP supported by this 
         user agent.  It will follow the same format as SIP version 
         information contained in the SIP messages generated by this
         user agent.  For example, user agents supporting SIP version 2
         will return 'SIP/2.0' as dictated by RFC 2543."
    ::= { cSipCfgBase 1 }

cSipCfgTransport OBJECT-TYPE
    SYNTAX INTEGER {
        udp(1),
        tcp(2),
        udpAndTcp(3),
        disabled(4)
        }
    ACCESS read-write
    STATUS mandatory
    DESCRIPTION
        "This object specifies the transport protocol the SIP user 
         agent will use to receive SIP messages.  A value of 'disabled'
         indicates that the UA will not receive any SIP messages."
    ::= { cSipCfgBase 2 }

cSipCfgUserLocationServerAddr OBJECT-TYPE
    SYNTAX SnmpAdminString
--    Rsyntax OCTET STRING(SIZE(0..255))
    ACCESS read-write
    STATUS mandatory
    DESCRIPTION
        "This object specifies address of the User Location 
         Server (ULS) being used to resolve the location of end 
         points.  This could be a Domain Name Server (DNS) or a 
         SIP proxy/redirect server.
        
         The format of the address follows the IETF service location 
         protocol. The syntax is as follows:
        
            mapping-type:type-specific-syntax
        
         the mapping-type specifies a scheme for mapping the matching 
         dial string to a target server. The type-specific-syntax is 
         exactly that, something that the particular mapping scheme can
         understand.  For example,
            Session target           Meaning
            ipv4:171.68.13.55:1006   The session target is the IP 
                                     version 4 address of 171.68.13.55 
                                     and port 1006.
            dns:pots.cisco.com       The session target is the IP host 
                                     with dns name pots.cisco.com.
        
         The valid Mapping type definitions for the peer follow:
            ipv4  - Syntax: ipv4:w.x.y.z:port or  ipv4:w.x.y.z 
            dns   - Syntax: dns:host.domain."
    ::= { cSipCfgBase 3 }

cSipCfgMaxForwards OBJECT-TYPE
    SYNTAX INTEGER(1..15)
    ACCESS read-write
    STATUS deprecated
    DESCRIPTION
        "This object may be used with any SIP method to limit the 
         number of proxies that can forward the request to the next 
         downstream server."
    ::= { cSipCfgBase 4 }

cSipCfgBindSrcAddrInterface OBJECT-TYPE
    SYNTAX InterfaceIndexOrZero
--    Rsyntax INTEGER(0..2147483647)
    ACCESS read-write
    STATUS deprecated
    DESCRIPTION
        "This object may specify the interface where the
         source IP address used in SIP signalling or media
         packets is configured.  A value of 0 means that 
         there is no specific source address configured and 
         in this case the best local IP address will be chosen 
         by the system."
    DEFVAL { 0 }
    ::= { cSipCfgBase 5 }

cSipCfgBindSrcAddrScope OBJECT-TYPE
    SYNTAX INTEGER {
        all(1),
        control(2)
        }
    ACCESS read-write
    STATUS deprecated
    DESCRIPTION
        "This object specifies the scope of packets to
         which the source IP address of the interface 
         designated by cSipCfgBindSrcAddrInterface
         will be bound.  A value of 'all' means the IP address 
         will be bound to both SIP signalling and media packets.
         A value of 'control' means the IP address will only
         be bound to SIP signalling packets.  
         If cSipCfgBindSrcAddrInterface is set to 0,
         the value of this object has no meaning."
    DEFVAL { all }
    ::= { cSipCfgBase 6 }

cSipCfgDnsSrvQueryStringFormat OBJECT-TYPE
    SYNTAX INTEGER {
        v1(1),
        v2(2)
        }
    ACCESS read-write
    STATUS mandatory
    DESCRIPTION
        "This object specifies the format of the prefix used 
         by the system for DNS SRV queries.
        
         v1  :  RFC 2052 format - 'protocol.transport.'
         v2  :  RFC 2782 format - '_protocol._transport.'
        
         This object allows backward compatibility with systems
         only supporting RFC 2052 format."
    DEFVAL { v2 }
    ::= { cSipCfgBase 7 }

cSipCfgRedirectionDisabled OBJECT-TYPE
    SYNTAX TruthValue
--    Rsyntax INTEGER {
--        true(1),
--        false(2)
--        }
    ACCESS read-write
    STATUS mandatory
    DESCRIPTION
        "This object specifies how call redirection (3xx)
         is handled by the user agent.  
        
         If 'false', the user agent's treatment of incoming 
         3xx class response messages is as defined in RFC 2543.  
         That is, the user agent uses the Contact header(s)
         from the 3xx response to reinitiate another INVITE
         transaction to the user's new location.  The call 
         is redirected.
        
         If 'true', the user agent treats incoming 3xx 
         response messages as 4xx (client error) class 
         response messages.  In this case, the call is not
         redirected, instead it is released with the 
         appropriate PSTN cause code.
        
         The mapping of SIP 3xx response status codes to
         4xx response status codes is as follows:
          300 Multiple Choices -> 410 Gone
          301 Moved Permanently -> 410 Gone
          302 Moved Temporarily -> 480 Temporarily Unavailable
          305 User Proxy        -> 410 Gone
          380 Alternative Service -> 410 Gone
          Any other 3xx -> 410 Gone"
    DEFVAL { false }
    ::= { cSipCfgBase 8 }

cSipCfgEarlyMediaTable OBJECT-TYPE
    SYNTAX SEQUENCE OF CSipCfgEarlyMediaEntry
    ACCESS not-accessible
    STATUS mandatory
    DESCRIPTION
        "This table contains configuration for Early
         Media Cut Through.  The configuration controls
         how the SIP user agent will process 1xx
         (Provisional) SIP response messages that contain 
         Session Definition Protocol (SDP) payloads."
    ::= { cSipCfgBase 9 }

cSipCfgEarlyMediaEntry OBJECT-TYPE
    SYNTAX CSipCfgEarlyMediaEntry
    ACCESS not-accessible
    STATUS mandatory
    DESCRIPTION
        "A row in the cSipCfgEarlyMediaTable.
         A row is accessible with a Provisional (1xx)
         status code value (eg, 180) and provides
         an object for the enabling or disabling of
         the Early Media Cut Through functionality."
    INDEX { cSipCfgEarlyMediaStatusCodeIndex }
    ::= { cSipCfgEarlyMediaTable 1 }

CSipCfgEarlyMediaEntry ::= SEQUENCE {
    cSipCfgEarlyMediaStatusCodeIndex CSipStatusCode,
    cSipCfgEarlyMediaCutThruDisabled TruthValue
    }

cSipCfgEarlyMediaStatusCodeIndex OBJECT-TYPE
    SYNTAX CSipStatusCode
--    Rsyntax INTEGER(1..2147483647)
    ACCESS not-accessible
    STATUS mandatory
    DESCRIPTION
        "A unique identifier of a row in this table and
         a valid SIP status code."
    ::= { cSipCfgEarlyMediaEntry 1 }

cSipCfgEarlyMediaCutThruDisabled OBJECT-TYPE
    SYNTAX TruthValue
--    Rsyntax INTEGER {
--        true(1),
--        false(2)
--        }
    ACCESS read-write
    STATUS mandatory
    DESCRIPTION
        "This object specifies whether Early Media 
         Cut Through is enabled or disabled for the 
         SIP response messages with status codes that 
         match cSipCfgEarlyMediaStatusCodeIndex.
        
         If 'true', early media cut through is disabled,
         and the user agent will process the message as
         though it did not contain any SDP payload.
        
         If 'false', early media cut through is enabled,
         and the user agent will process the message
         similar to a 183 (Session Progress) and cut
         through for early media.  The assumption being
         that the SDP is an indication that the far end
         is going to send early media."
    DEFVAL { false }
    ::= { cSipCfgEarlyMediaEntry 2 }

cSipCfgSymNatEnabled OBJECT-TYPE
    SYNTAX TruthValue
--    Rsyntax INTEGER {
--        true(1),
--        false(2)
--        }
    ACCESS read-write
    STATUS mandatory
    DESCRIPTION
        "This object specifies whether remote media checks
         for Symmetric Network Address Translation (NAT) 
         is enabled or disabled.
        
         If 'true', remote media checks are enabled.  The
         gateway will have the ability to open a Real Time 
         Transport Protocol (RTP) session with the remote
         end and then update (modify) the existing RTP
         session's remote address/port (raddr:rport) with
         the source address and port of the actual media
         packet received.  This would be triggered for only
         those calls where the Session Description Protocol
         (SDP) received by the gateway has an indication to
         do so.
        
         If 'false', remote media checks are disabled."
    DEFVAL { false }
    ::= { cSipCfgBase 10 }

cSipCfgSymNatDirectionRole OBJECT-TYPE
    SYNTAX INTEGER {
        none(1),
        passive(2),
        active(3)
        }
    ACCESS read-write
    STATUS mandatory
    DESCRIPTION
        "This object specifies the value of the
         'a=direction:<role>' SDP attribute supported by 
         the user agent.  The direction attribute is used 
         to describe the role of the user agent (as an 
         endpoint for a connection-oriented media stream) 
         in the connection setup procedure.
         
         none    :  No role is specified.
         passive :  The user agent will advertise itself
                    as a 'passive' entity (inside the NAT)
                    in the SDP.
         active  :  The user agent will advertise itself
                    as a 'active' entity (outside the NAT)
                    in the SDP."
    DEFVAL { none }
    ::= { cSipCfgBase 11 }

cSipCfgBindSourceAddrTable OBJECT-TYPE
    SYNTAX SEQUENCE OF CSipCfgBindSourceAddrEntry
    ACCESS not-accessible
    STATUS mandatory
    DESCRIPTION
        "This table contains configuration for binding
         the scope of packets to the particular ethernet
         interface. The scope for the packets can be
         specified as either 'signalling' or 'media'
         packets. The ethernet interface shall be
         specified by the interface index. The table
         shall be indexed based on the scope."
    ::= { cSipCfgBase 12 }

cSipCfgBindSourceAddrEntry OBJECT-TYPE
    SYNTAX CSipCfgBindSourceAddrEntry
    ACCESS not-accessible
    STATUS mandatory
    DESCRIPTION
        "A row in the cSipCfgBindSourceAddrTable.
         A row is accessible with the scope of packets
         to which the source IP address of the interface
         designated by cSipCfgBindSourceAddrInterface
         will be bound."
    INDEX { cSipCfgBindSourceAddrScope }
    ::= { cSipCfgBindSourceAddrTable 1 }

CSipCfgBindSourceAddrEntry ::= SEQUENCE {
    cSipCfgBindSourceAddrScope INTEGER,
    cSipCfgBindSourceAddrInterface InterfaceIndexOrZero
    }

cSipCfgBindSourceAddrScope OBJECT-TYPE
    SYNTAX INTEGER {
        media(1),
        control(2)
        }
    ACCESS not-accessible
    STATUS mandatory
    DESCRIPTION
        "A unique identifier of a row in this table and
         specifies the scope of packets to which the
         source IP address of the interface
         designated by cSipCfgBindSourceAddrInterface
         will be bound."
    ::= { cSipCfgBindSourceAddrEntry 1 }

cSipCfgBindSourceAddrInterface OBJECT-TYPE
    SYNTAX InterfaceIndexOrZero
--    Rsyntax INTEGER(0..2147483647)
    ACCESS read-write
    STATUS mandatory
    DESCRIPTION
        "This object may specify the interface where the
         source IP address used in SIP signalling or media
         packets is configured.  A value of 0 means that
         there is no specific source address configured and
         in this case the best local IP address will be chosen
         by the system."
    DEFVAL { 0 }
    ::= { cSipCfgBindSourceAddrEntry 2 }

cSipCfgSuspendResumeEnabled OBJECT-TYPE
    SYNTAX TruthValue
--    Rsyntax INTEGER {
--        true(1),
--        false(2)
--        }
    ACCESS read-write
    STATUS mandatory
    DESCRIPTION
        "This object specifies if support for handling 
         Suspend/Resume events from the switch is enabled or not.
        
         If 'true', the user agent on getting a Suspend will
         notify the remote agent by sending it a re-invite with
         a hold SDP. Similarly, when the Gateway receives a Resume, it
         will initiate a re-invite with the original SDP and unhold the
         call.
        
         If 'false', the user agent will not initiate any re-invites
         on receiving Suspend/Resume events, basically it won't be
         putting the call on hold or off hold."
    DEFVAL { true }
    ::= { cSipCfgBase 13 }

cSipCfgOfferCallHold OBJECT-TYPE
    SYNTAX INTEGER {
        directionAttr(1),
        connAddr(2)
        }
    ACCESS read-write
    STATUS mandatory
    DESCRIPTION
        "This object specifies how the SIP gateway would initiate call
         hold requests.
         
         directionAttr: The user agent will use the direction
                         attribute such as a=sendonly or a=inactive in
                         the sdp to initiate call hold requests.
                           
         connAddr: The user agent will use 0.0.0.0 connection address
                    to specify Call Hold."
    DEFVAL { directionAttr }
    ::= { cSipCfgBase 14 }

cSipCfgReasonHeaderOveride OBJECT-TYPE
    SYNTAX TruthValue
--    Rsyntax INTEGER {
--        true(1),
--        false(2)
--        }
    ACCESS read-write
    STATUS mandatory
    DESCRIPTION
        "This object specifies that the Reason header overrides SIP 
         status code mapping table."
    DEFVAL { false }
    ::= { cSipCfgBase 15 }

cSipCfgMaximumForwards OBJECT-TYPE
    SYNTAX INTEGER(1..70)
    ACCESS read-write
    STATUS mandatory
    DESCRIPTION
        "This object may be used with any SIP method to limit the 
         number of proxies that can forward the request to the next 
         downstream server."
    DEFVAL { 70 }
    ::= { cSipCfgBase 16 }

cSipCfgTimerTrying OBJECT-TYPE
    SYNTAX INTEGER(100..1000)
--  Units
--    milliseconds
    ACCESS read-write
    STATUS mandatory
    DESCRIPTION
        "This object specifies the time a user agent will wait to 
         receive a provisional response to a INVITE before resending 
         the INVITE."
    ::= { cSipCfgTimer 1 }

cSipCfgTimerExpires OBJECT-TYPE
    SYNTAX INTEGER(60000..300000)
--  Units
--    milliseconds
    ACCESS read-write
    STATUS mandatory
    DESCRIPTION
        "This object specifies the time a user agent will wait to 
         receive a final response to a INVITE before cancelling the 
         transaction."
    ::= { cSipCfgTimer 2 }

cSipCfgTimerConnect OBJECT-TYPE
    SYNTAX INTEGER(100..1000)
--  Units
--    milliseconds
    ACCESS read-write
    STATUS mandatory
    DESCRIPTION
        "This object specifies the time a user agent will wait to 
         receive an ACK confirmation a session is established."
    ::= { cSipCfgTimer 3 }

cSipCfgTimerDisconnect OBJECT-TYPE
    SYNTAX INTEGER(100..1000)
--  Units
--    milliseconds
    ACCESS read-write
    STATUS mandatory
    DESCRIPTION
        "This object specifies the time a user agent will wait to 
         receive an BYE confirmation a session is disconnected."
    ::= { cSipCfgTimer 4 }

cSipCfgTimerPrack OBJECT-TYPE
    SYNTAX INTEGER(100..1000)
--  Units
--    milliseconds
    ACCESS read-write
    STATUS mandatory
    DESCRIPTION
        "This object specifies the time a user agent will wait for 
         a final response before retransmitting the PRACK (PRovisional
         ACKnowledgment)."
    ::= { cSipCfgTimer 5 }

cSipCfgTimerComet OBJECT-TYPE
    SYNTAX INTEGER(100..1000)
--  Units
--    milliseconds
    ACCESS read-write
    STATUS mandatory
    DESCRIPTION
        "This object specifies the time a user agent will wait 
         for a final response before retransmitting the COMET 
         (COndition MET)."
    ::= { cSipCfgTimer 6 }

cSipCfgTimerReliableRsp OBJECT-TYPE
    SYNTAX INTEGER(100..1000)
--  Units
--    milliseconds
    ACCESS read-write
    STATUS mandatory
    DESCRIPTION
        "This object specifies the amount of time to wait for a
         PRACK before retransmitting the reliable 1xx response."
    ::= { cSipCfgTimer 7 }

cSipCfgTimerNotify OBJECT-TYPE
    SYNTAX INTEGER(100..1000)
--  Units
--    milliseconds
    ACCESS read-write
    STATUS mandatory
    DESCRIPTION
        "This object specifies the amount of time to wait for a
         final response before retransmitting the Notify."
    ::= { cSipCfgTimer 8 }

cSipCfgTimerRefer OBJECT-TYPE
    SYNTAX INTEGER(100..1000)
--  Units
--    milliseconds
    ACCESS read-write
    STATUS mandatory
    DESCRIPTION
        "This object specifies the amount of time to wait for a
         final response before retransmitting the Refer."
    ::= { cSipCfgTimer 9 }

cSipCfgTimerSessionTimer OBJECT-TYPE
    SYNTAX INTEGER(60..86400)
--  Units
--    seconds
    ACCESS read-write
    STATUS mandatory
    DESCRIPTION
        "This object specifies the value of the Min-SE 
         header for INVITE messages originated by this 
         user agent and the minimum value of the 
         Session-Expires headers for INVITE messages 
         received by this user agent.
        
         Any Session-Expires headers received with a 
         value below this object's value will be rejected
         with a 422 client error response message.
        
         Setting this object to a value less than 600 is
         valid, but the possibly of excessive re-INVITES 
         and the impact of those messages should be fully 
         understood and considered an acceptable risk."
    DEFVAL { 1800 }
    ::= { cSipCfgTimer 10 }

cSipCfgTimerHold OBJECT-TYPE
    SYNTAX INTEGER(0|15..2880)
--  Units
--    minutes
    ACCESS read-write
    STATUS mandatory
    DESCRIPTION
        "This object specifies the amount of time to wait before 
         disconnecting a call already on hold. A value of 0 specifies
         that this functionality is disabled."
    DEFVAL { 2880 }
    ::= { cSipCfgTimer 11 }

cSipCfgTimerInfo OBJECT-TYPE
    SYNTAX INTEGER(100..1000)
--  Units
--    milliseconds
    ACCESS read-write
    STATUS mandatory
    DESCRIPTION
        "This object specifies the amount of time to wait for a
         200ok response before retransmitting the Info."
    DEFVAL { 500 }
    ::= { cSipCfgTimer 12 }

cSipCfgTimerConnectionAging OBJECT-TYPE
    SYNTAX INTEGER(5..30)
--  Units
--    minutes
    ACCESS read-write
    STATUS mandatory
    DESCRIPTION
        "This object specifies the amount of time to wait before 
         aging out a TCP/UDP connection."
    DEFVAL { 5 }
    ::= { cSipCfgTimer 13 }

cSipCfgTimerBufferInvite OBJECT-TYPE
    SYNTAX INTEGER(0|50..5000)
--  Units
--    milliseconds
    ACCESS read-write
    STATUS mandatory
    DESCRIPTION
        "This object specifies the amount of time to buffer the INVITE 
         while waiting for display name info in the Facility.
        
         A value of 0 means that the INVITE wouldn't be buffered
         waiting for the display name info in the Facility."
    DEFVAL { 0 }
    ::= { cSipCfgTimer 14 }

cSipCfgRetryInvite OBJECT-TYPE
    SYNTAX INTEGER(1..10)
    ACCESS read-write
    STATUS mandatory
    DESCRIPTION
        "This object specifies the number of times a user agent 
         will retry sending a INVITE request."
    ::= { cSipCfgRetry 1 }

cSipCfgRetryBye OBJECT-TYPE
    SYNTAX INTEGER(1..10)
    ACCESS read-write
    STATUS mandatory
    DESCRIPTION
        "This object specifies the number of times a user agent 
         will retry sending a BYE request."
    ::= { cSipCfgRetry 2 }

cSipCfgRetryCancel OBJECT-TYPE
    SYNTAX INTEGER(1..10)
    ACCESS read-write
    STATUS mandatory
    DESCRIPTION
        "This object specifies the number of times a user agent 
         will retry sending a CANCEL request."
    ::= { cSipCfgRetry 3 }

cSipCfgRetryRegister OBJECT-TYPE
    SYNTAX INTEGER(1..10)
    ACCESS read-write
    STATUS mandatory
    DESCRIPTION
        "This object specifies the number of times a user agent 
         will retry sending a REGISTER request."
    ::= { cSipCfgRetry 4 }

cSipCfgRetryResponse OBJECT-TYPE
    SYNTAX INTEGER(1..10)
    ACCESS read-write
    STATUS mandatory
    DESCRIPTION
        "This object specifies the number of times a user agent 
         will retry sending a Response and expecting a ACK."
    ::= { cSipCfgRetry 5 }

cSipCfgRetryPrack OBJECT-TYPE
    SYNTAX INTEGER(1..10)
    ACCESS read-write
    STATUS mandatory
    DESCRIPTION
        "This object specifies the number of times a user agent 
         will retry sending a PRACK (PRovisional ACKnowledgement)."
    ::= { cSipCfgRetry 6 }

cSipCfgRetryComet OBJECT-TYPE
    SYNTAX INTEGER(1..10)
    ACCESS read-write
    STATUS mandatory
    DESCRIPTION
        "This object specifies the number of times a user agent 
         will retry sending a COMET (COndition MET)."
    ::= { cSipCfgRetry 7 }

cSipCfgRetryReliableRsp OBJECT-TYPE
    SYNTAX INTEGER(1..10)
    ACCESS read-write
    STATUS mandatory
    DESCRIPTION
        "This object specifies the number of times a user agent 
         will retry sending a reliable response."
    ::= { cSipCfgRetry 8 }

cSipCfgRetryNotify OBJECT-TYPE
    SYNTAX INTEGER(1..10)
    ACCESS read-write
    STATUS mandatory
    DESCRIPTION
        "This object specifies the number of times a user agent 
         will retry sending a Notify request."
    ::= { cSipCfgRetry 9 }

cSipCfgRetryRefer OBJECT-TYPE
    SYNTAX INTEGER(1..10)
    ACCESS read-write
    STATUS mandatory
    DESCRIPTION
        "This object specifies the number of times a user agent 
         will retry sending a Refer request."
    ::= { cSipCfgRetry 10 }

cSipCfgRetryInfo OBJECT-TYPE
    SYNTAX INTEGER(1..10)
    ACCESS read-write
    STATUS mandatory
    DESCRIPTION
        "This object specifies the number of times a user agent
         will retry sending a Info request."
    DEFVAL { 6 }
    ::= { cSipCfgRetry 11 }

cSipCfgRetrySubscribe OBJECT-TYPE
    SYNTAX INTEGER(1..10)
    ACCESS read-write
    STATUS mandatory
    DESCRIPTION
        "This object specifies the number of times a user agent
         will retry sending a Subscribe request."
    DEFVAL { 6 }
    ::= { cSipCfgRetry 12 }

cSipCfgPeerTable OBJECT-TYPE
    SYNTAX SEQUENCE OF CSipCfgPeerEntry
    ACCESS not-accessible
    STATUS mandatory
    DESCRIPTION
        "This table contains per dial-peer SIP related 
         configuration.   
        
         The table is a sparse table of dial-peer information.
         This means, it only reflects dial-peers being used 
         for SIP.  A dial-peer is being used for SIP if the 
         value of cvVoIPPeerCfgSessionProtocol 
         (CISCO-VOICE-DIAL-CONTROL-MIB) is 'sip'.
        
         Dial-peers are not created or destroyed via this
         table.  Only SIP related configuration can be 
         performed via this table once the dial-peer exists
         in the system and is visible in this table."
    ::= { cSipCfgPeer 1 }

cSipCfgPeerEntry OBJECT-TYPE
    SYNTAX CSipCfgPeerEntry
    ACCESS not-accessible
    STATUS mandatory
    DESCRIPTION
        "A row in the cSipCfgPeerTable."
    INDEX { cSipCfgPeerIndex }
    ::= { cSipCfgPeerTable 1 }

CSipCfgPeerEntry ::= SEQUENCE {
    cSipCfgPeerIndex INTEGER,
    cSipCfgPeerOutSessionTransport INTEGER,
    cSipCfgPeerReliable1xxRspStr SnmpAdminString,
    cSipCfgPeerReliable1xxRspHdr INTEGER,
    cSipCfgPeerUrlType INTEGER,
    cSipCfgPeerSwitchTransEnabled TruthValue
    }

cSipCfgPeerIndex OBJECT-TYPE
    SYNTAX INTEGER(1..2147483647)
    ACCESS not-accessible
    STATUS mandatory
    DESCRIPTION
        "An arbitrary index that uniquely identifies a 
         dial-peer configured for SIP."
    ::= { cSipCfgPeerEntry 1 }

cSipCfgPeerOutSessionTransport OBJECT-TYPE
    SYNTAX INTEGER {
        system(1),
        udp(2),
        tcp(3)
        }
    ACCESS read-write
    STATUS mandatory
    DESCRIPTION
        "This object specifies the session transport 
         protocol that will be used by this dial-peer
         for outbound SIP messages.  
        
         The value 'system' is the default and indicates 
         that this dial-peer should use the value set by 
         cSipCfgOutSessionTransport instead."
    DEFVAL { system }
    ::= { cSipCfgPeerEntry 2 }

cSipCfgPeerReliable1xxRspStr OBJECT-TYPE
    SYNTAX SnmpAdminString
--    Rsyntax OCTET STRING(SIZE(0..255))
    ACCESS read-write
    STATUS mandatory
    DESCRIPTION
        "This object specifies the string that will be 
         placed in either the Supported or Require SIP 
         header, as specified by cSipCfgPeerReliable1xxRspHdr."
    DEFVAL { "100rel" }
    ::= { cSipCfgPeerEntry 3 }

cSipCfgPeerReliable1xxRspHdr OBJECT-TYPE
    SYNTAX INTEGER {
        system(1),
        supported(2),
        require(3),
        disabled(4)
        }
    ACCESS read-write
    STATUS mandatory
    DESCRIPTION
        "This object specifies behavior with respect to
         Support or Require headers in SIP messages sent
         and received via this dial-peer.
        
         If the originating gateway is configured for 'require',
         the Require header is added to the outgoing INVITEs
         with the value of cSipCfgPeerReliable1xxStr.  This
         requires the use of reliable provisional responses by
         the terminating gateway.  Sessions will be torn down
         if this use cannot be supported by that gateway.
        
         If the originating gateway is configured for 'supported',
         the Supported header is added to the outgoing INVITEs
         with the value of cSipCfgPeerReliable1xxStr.  This 
         requires that an attempt to use reliable provisional
         responses be made, but sessions can continue without them.
        
         If the originating gateway is configured for 'disabled',
         the value of cSipCfgReliable1xxStr will NOT be added to
         either the Require or Supported headers of outgoing INVITEs.
        
         The value 'system' is the default and indicates that this 
         dial-peer should use the value of  cSipCfgReliable1xxRspHdr
         instead."
    DEFVAL { system }
    ::= { cSipCfgPeerEntry 4 }

cSipCfgPeerUrlType OBJECT-TYPE
    SYNTAX INTEGER {
        system(1),
        sip(2),
        tel(3)
        }
    ACCESS read-write
    STATUS mandatory
    DESCRIPTION
        "This object specifies the URL type sent in outbound
         INVITES generated by this device.
        
         The value 'system' is the default and indicates that this 
         dial-peer should use the value of cSipCfgUrlType instead."
    DEFVAL { system }
    ::= { cSipCfgPeerEntry 5 }

cSipCfgPeerSwitchTransEnabled OBJECT-TYPE
    SYNTAX TruthValue
--    Rsyntax INTEGER {
--        true(1),
--        false(2)
--        }
    ACCESS read-write
    STATUS mandatory
    DESCRIPTION
        "This object specifies if the functionality of switching
         between transports from UDP to TCP if the message size of a
         Request is greater than 1300 bytes is enabled or not."
    DEFVAL { false }
    ::= { cSipCfgPeerEntry 6 }

cSipCfgOutSessionTransport OBJECT-TYPE
    SYNTAX INTEGER {
        udp(1),
        tcp(2)
        }
    ACCESS read-write
    STATUS mandatory
    DESCRIPTION
        "This object specifies the session transport 
         protocol that will be used for outbound SIP 
         messages.  This configuration is applicable
         to all dial-peers in the system having 
         cSipCfgPeerOutSessionTransport set to 'system'."
    DEFVAL { udp }
    ::= { cSipCfgPeer 2 }

cSipCfgReliable1xxRspStr OBJECT-TYPE
    SYNTAX SnmpAdminString
--    Rsyntax OCTET STRING(SIZE(0..255))
    ACCESS read-write
    STATUS mandatory
    DESCRIPTION
        "This object specifies the string that will be 
         placed in either the Supported or Require SIP 
         header, as specified by cSipCfgReliable1xxRspHdr."
    DEFVAL { "100rel" }
    ::= { cSipCfgPeer 3 }

cSipCfgReliable1xxRspHdr OBJECT-TYPE
    SYNTAX INTEGER {
        supported(1),
        require(2),
        disabled(3)
        }
    ACCESS read-write
    STATUS mandatory
    DESCRIPTION
        "This object specifies behavior with respect to
         Supported or Require headers in SIP messages sent
         and received via this dial-peer.
        
         If the originating gateway is configured for 'require',
         the Require header is added to the outgoing INVITEs
         with the value of cSipCfgReliable1xxStr.  This
         requires the use of reliable provisional responses by
         the terminating gateway.  Sessions will be torn down
         if this use cannot be supported by that gateway.
        
         If the originating gateway is configured for 'supported',
         the Supported header is added to the outgoing INVITEs
         with the value of cSipCfgReliable1xxStr.  This 
         requires that an attempt to use reliable provisional
         responses be made, but sessions can continue without them.
        
         If the originating gateway is configured for 'disabled',
         the value of cSipCfgReliable1xxStr will NOT be added to
         either the Require or Supported headers of outgoing INVITEs."
    DEFVAL { supported }
    ::= { cSipCfgPeer 4 }

cSipCfgUrlType OBJECT-TYPE
    SYNTAX INTEGER {
        sip(1),
        tel(2)
        }
    ACCESS read-write
    STATUS mandatory
    DESCRIPTION
        "This object specifies the URL type sent in outbound
         INVITES generated by this device."
    DEFVAL { sip }
    ::= { cSipCfgPeer 5 }

cSipCfgStatusCauseTable OBJECT-TYPE
    SYNTAX SEQUENCE OF CSipCfgStatusCauseEntry
    ACCESS not-accessible
    STATUS mandatory
    DESCRIPTION
        "This table contains SIP status code to PSTN cause code
         mapping configuration.  Inbound SIP response messages 
         that will result in outbound PSTN signalling messages
         will have the SIP status codes transposed into the
         PSTN cause codes as prescribed by the contents of this 
         table."
    ::= { cSipCfgStatusCauseMap 1 }

cSipCfgStatusCauseEntry OBJECT-TYPE
    SYNTAX CSipCfgStatusCauseEntry
    ACCESS not-accessible
    STATUS mandatory
    DESCRIPTION
        "A row in the cSipCfgStatusCauseTable.  Entries cannot be
         created or destroyed by the actions of any NMS."
    INDEX { cSipCfgStatusCodeIndex }
    ::= { cSipCfgStatusCauseTable 1 }

CSipCfgStatusCauseEntry ::= SEQUENCE {
    cSipCfgStatusCodeIndex CSipStatusCode,
    cSipCfgPstnCause INTEGER,
    cSipCfgStatusCauseStoreStatus StorageType
    }

cSipCfgStatusCodeIndex OBJECT-TYPE
    SYNTAX CSipStatusCode
--    Rsyntax INTEGER(1..2147483647)
    ACCESS not-accessible
    STATUS mandatory
    DESCRIPTION
        "A unique identifier of a row in this table and
         a valid SIP status code."
    ::= { cSipCfgStatusCauseEntry 1 }

cSipCfgPstnCause OBJECT-TYPE
    SYNTAX INTEGER(1..2147483647)
    ACCESS read-write
    STATUS mandatory
    DESCRIPTION
        "The PSTN cause code to which the SIP status code
         given by cSipCfgStatusCodeIndex is to be mapped
         for outbound PSTN signalling messages."
    ::= { cSipCfgStatusCauseEntry 2 }

cSipCfgStatusCauseStoreStatus OBJECT-TYPE
    SYNTAX StorageType
--    Rsyntax INTEGER {
--        other(1),
--        volatile(2),
--        nonVolatile(3),
--        permanent(4),
--        readOnly(5)
--        }
    ACCESS read-only
    STATUS mandatory
    DESCRIPTION
        "This object reflects the storage status of this
         table entry.  If the value is 'volatile', then
         this entry only exists in RAM and the information
         would be lost (reverting to defaults) on system reload.  
         If the value is 'nonVolatile' then this entry has been 
         written to NVRAM and will persist across system reloads."
    ::= { cSipCfgStatusCauseEntry 3 }

cSipCfgCauseStatusTable OBJECT-TYPE
    SYNTAX SEQUENCE OF CSipCfgCauseStatusEntry
    ACCESS not-accessible
    STATUS mandatory
    DESCRIPTION
        "This table contains PSTN cause code to SIP status code
         mapping configuration.   Inbound PSTN signalling messages
         that will result in outbound SIP response messages 
         will have the PSTN cause codes transposed into the
         SIP status codes as prescribed by the contents of this 
         table."
    ::= { cSipCfgStatusCauseMap 2 }

cSipCfgCauseStatusEntry OBJECT-TYPE
    SYNTAX CSipCfgCauseStatusEntry
    ACCESS not-accessible
    STATUS mandatory
    DESCRIPTION
        "A row in the cSipCfgCauseStatusTable. Entries cannot be
         created or destroyed by the actions of any NMS."
    INDEX { cSipCfgPstnCauseIndex }
    ::= { cSipCfgCauseStatusTable 1 }

CSipCfgCauseStatusEntry ::= SEQUENCE {
    cSipCfgPstnCauseIndex INTEGER,
    cSipCfgStatusCode CSipStatusCode,
    cSipCfgCauseStatusStoreStatus StorageType
    }

cSipCfgPstnCauseIndex OBJECT-TYPE
    SYNTAX INTEGER(1..2147483647)
    ACCESS not-accessible
    STATUS mandatory
    DESCRIPTION
        "A unique identifier of a row in this table and
         a valid PSTN cause code."
    ::= { cSipCfgCauseStatusEntry 1 }

cSipCfgStatusCode OBJECT-TYPE
    SYNTAX CSipStatusCode
--    Rsyntax INTEGER(1..2147483647)
    ACCESS read-write
    STATUS mandatory
    DESCRIPTION
        "The SIP status code to which the PSTN cause code
         given by cSipCfgPstnCauseIndex is to be mapped
         for outbound SIP response messages."
    ::= { cSipCfgCauseStatusEntry 2 }

cSipCfgCauseStatusStoreStatus OBJECT-TYPE
    SYNTAX StorageType
--    Rsyntax INTEGER {
--        other(1),
--        volatile(2),
--        nonVolatile(3),
--        permanent(4),
--        readOnly(5)
--        }
    ACCESS read-only
    STATUS mandatory
    DESCRIPTION
        "This object reflects the storage status of this
         table entry.  If the value is 'volatile', then
         this entry only exists in RAM and the information
         would be lost (reverting to defaults) on system reload.  
         If the value is 'nonVolatile' then this entry has been 
         written to NVRAM and will persist across system reloads."
    ::= { cSipCfgCauseStatusEntry 3 }

cSipCfgAaaUsername OBJECT-TYPE
    SYNTAX INTEGER {
        callingNumber(1),
        proxyAuth(2)
        }
    ACCESS read-write
    STATUS mandatory
    DESCRIPTION
        "This object specifies the source of the information used to
        populate the username attribute of AAA billing records."
    DEFVAL { callingNumber }
    ::= { cSipCfgAaa 1 }

cSipCfgHeaderPassingEnabled OBJECT-TYPE
    SYNTAX TruthValue
--    Rsyntax INTEGER {
--        true(1),
--        false(2)
--        }
    ACCESS read-write
    STATUS mandatory
    DESCRIPTION
        "This object specifies if support for passing
         SIP headers from Invite, Subscribe, Notify Request to the
         application is enabled.
        
         If 'true', the headers received in a message will be passed
         to the application.
        
         If 'false', the headers received in a message will not be
         passed to the application."
    DEFVAL { false }
    ::= { cSipCfgVoiceServiceVoip 1 }

cSipCfgMaxSubscriptionAccept OBJECT-TYPE
    SYNTAX Gauge(0..4294967295)
    ACCESS read-write
    STATUS mandatory
    DESCRIPTION
        "This object specifies the maximum number of concurrent SIP
         subscriptions a SIP Gateway can accept."
    ::= { cSipCfgVoiceServiceVoip 2 }

cSipCfgMaxSubscriptionOriginate OBJECT-TYPE
    SYNTAX Gauge(0..4294967295)
    ACCESS read-write
    STATUS mandatory
    DESCRIPTION
        "This object specifies the maximum number of concurrent SIP
         subscriptions that a SIP Gateway can originate. Default is Max
         Dialpeers on platform. Maximum is 2*Max Dialpeers on
         Platform."
    ::= { cSipCfgVoiceServiceVoip 3 }

cSipCfgSwitchTransportEnabled OBJECT-TYPE
    SYNTAX TruthValue
--    Rsyntax INTEGER {
--        true(1),
--        false(2)
--        }
    ACCESS read-write
    STATUS mandatory
    DESCRIPTION
        "This object specifies if the functionality of switching
         between transports from udp to tcp if the message size of a
         Request is greater than 1300 bytes is enabled or not.
        
         This configuration is at the global level, and will only be 
         considered if there exists no voip dial-peer."
    DEFVAL { false }
    ::= { cSipCfgVoiceServiceVoip 4 }

cSipStatsInfoTryingIns OBJECT-TYPE
    SYNTAX Counter
    ACCESS read-only
    STATUS mandatory
    DESCRIPTION
        "This object reflects the total number of Trying
         (100) responses received by the user agent since system startup.  
         Trying responses indicate that some unspecified
         action is being taken on behalf of this call, but
         the user has not yet been located.  Inbound Trying
         responses indicate that outbound INVITE request 
         sent out by this system have been received and
         are processed."
    REFERENCE
        "RFC 2543, Sections 5.1.1 & 7.1.1"
    ::= { cSipStatsInfo 1 }

cSipStatsInfoTryingOuts OBJECT-TYPE
    SYNTAX Counter
    ACCESS read-only
    STATUS mandatory
    DESCRIPTION
        "This object reflects the total number of Trying
         (100) responses sent by the user agent since system startup.
         Trying responses indicate that some unspecified
         action is being taken on behalf of this call, but
         the user has not yet been located.  Outbound Trying
         responses indicate this system is successfully 
         receiving INVITE requests and processing them on 
         behalf of the system initiating the INVITE."
    REFERENCE
        "RFC 2543, Sections 5.1.1 & 7.1.1"
    ::= { cSipStatsInfo 2 }

cSipStatsInfoRingingIns OBJECT-TYPE
    SYNTAX Counter
    ACCESS read-only
    STATUS mandatory
    DESCRIPTION
        "This object reflects the total number of Ringing
         (180) responses received by the user agent since system startup.
         A inbound Ringing response indicates that the UAS
         processing a INVITE initiated by this system has 
         found a possible location where the desired end user 
         has registered recently and is trying to alert the user."
    REFERENCE
        "RFC 2543, Sections 5.1.1 & 7.1.2"
    ::= { cSipStatsInfo 3 }

cSipStatsInfoRingingOuts OBJECT-TYPE
    SYNTAX Counter
    ACCESS read-only
    STATUS mandatory
    DESCRIPTION
        "This object reflects the total number of Ringing
         (180) responses sent by the user agent since system startup.
         A outbound Ringing response indicates that this
         system has processed an INVITE for a particular
         end user and found a possible location where that
         user has registered recently.  The system is trying
         to alert the end user and is conveying that status
         to the system that originated the INVITE."
    REFERENCE
        "RFC 2543, Sections 5.1.1 & 7.1.2"
    ::= { cSipStatsInfo 4 }

cSipStatsInfoForwardedIns OBJECT-TYPE
    SYNTAX Counter
    ACCESS read-only
    STATUS mandatory
    DESCRIPTION
        "This object reflects the total number of Call Is Being
         Forwarded (181) responses received by the user agent since system startup.
         A proxy server may use a Forwarded status code to
         indicate that the call is being forwarded to a different
         set of destinations.  Inbound Forwarded responses indicate 
         to this system that forwarding actions are taking place 
         with regard to calls initiated by this system."
    REFERENCE
        "RFC 2543, Sections 5.1.1 & 7.1.3"
    ::= { cSipStatsInfo 5 }

cSipStatsInfoForwardedOuts OBJECT-TYPE
    SYNTAX Counter
    ACCESS read-only
    STATUS mandatory
    DESCRIPTION
        "This object reflects the total number of Call Is Being
         Forwarded (181) responses sent by the user agent since system startup.
         A proxy server may use a Forwarded status code to
         indicate that the call is being forwarded to a different
         set of destinations.  Outbound Forwarded responses
         indicate this system is taking some forwarding action
         for calls and conveying that status to the system that
         initiated the calls."
    REFERENCE
        "RFC 2543, Sections 5.1.1 & 7.1.3"
    ::= { cSipStatsInfo 6 }

cSipStatsInfoQueuedIns OBJECT-TYPE
    SYNTAX Counter
    ACCESS read-only
    STATUS mandatory
    DESCRIPTION
        "This object reflects the total number of Queued
         (182) responses received by the user agent since system startup.
         Inbound Queued responses indicate that the users
         this system is attempting to call are temporarily
         unavailable but the SIP agents operating on behalf
         of those users wish to queue the calls rather than
         reject them.  When the called parties become available,
         this system can expect to receive the appropriate
         final status response.  The Reason-Phrase from the
         Queued response messages Status-Line may give further
         details about the status of the call.  Multiple 
         Queued responses to update this system about the status
         of the queued call my be received."
    REFERENCE
        "RFC 2543, Sections 5.1.1 & 7.1.4"
    ::= { cSipStatsInfo 7 }

cSipStatsInfoQueuedOuts OBJECT-TYPE
    SYNTAX Counter
    ACCESS read-only
    STATUS mandatory
    DESCRIPTION
        "This object reflects the total number of Queued
         (182) responses sent by the user agent since system startup.
         Outbound Queued responses indicate this system
         has determined that the called party is temporarily
         unavailable but the call is not rejected.  Rather 
         the call is queued until the called party becomes
         available.  Queued responses messages are sent to
         the system originating the call request to convey
         the current status of a queued call."
    REFERENCE
        "RFC 2543, Sections 5.1.1 & 7.1.4"
    ::= { cSipStatsInfo 8 }

cSipStatsInfoSessionProgIns OBJECT-TYPE
    SYNTAX Counter
    ACCESS read-only
    STATUS mandatory
    DESCRIPTION
        "This object reflects the total number of Session
         Progress (183) responses received by the user agent since system startup."
    ::= { cSipStatsInfo 9 }

cSipStatsInfoSessionProgOuts OBJECT-TYPE
    SYNTAX Counter
    ACCESS read-only
    STATUS mandatory
    DESCRIPTION
        "This object reflects the total number of Session
         Progress (183) responses sent by the user agent since system startup."
    ::= { cSipStatsInfo 10 }

cSipStatsSuccessOkIns OBJECT-TYPE
    SYNTAX Counter
    ACCESS read-only
    STATUS deprecated
    DESCRIPTION
        "This object reflects the total number of Ok
         (200) responses received by the user agent since system startup.
         The meaning of inbound Ok responses depends
         on the method used in the associated request.
        
         BYE      : The Ok response means the call has 
                    been terminated.
        
         CANCEL   : The Ok response means the search for 
                    the end user has been cancelled.
        
         INVITE   : The Ok response means the called party 
                    has agreed to participate in the call.
        
         OPTIONS  : The Ok response means the called party 
                    has agreed to share its capabilities.
        
         REGISTER : The Ok response means the registration
                    has succeeded."
    REFERENCE
        "RFC 2543, Sections 5.1.1 & 7.2.1"
    ::= { cSipStatsSuccess 1 }

cSipStatsSuccessOkOuts OBJECT-TYPE
    SYNTAX Counter
    ACCESS read-only
    STATUS deprecated
    DESCRIPTION
        "This object reflects the total number of Ok
         (200) responses sent by the user agent since system startup.
         The meaning of outbound Ok responses depends
         on the method used in the associated request.
        
         BYE      : The Ok response means the call has 
                    been terminated.
        
         CANCEL   : The Ok response means the search for 
                    the end user has been cancelled.
        
         INVITE   : The Ok response means the called party 
                    has agreed to participate in the call.
        
         OPTIONS  : The Ok response means the called party 
                    has agreed to share its capabilities.
        
         REGISTER : The Ok response means the registration
                    has succeeded."
    REFERENCE
        "RFC 2543, Sections 5.1.1 & 7.2.1"
    ::= { cSipStatsSuccess 2 }

cSipStatsSuccessAcceptedIns OBJECT-TYPE
    SYNTAX Counter
    ACCESS read-only
    STATUS mandatory
    DESCRIPTION
        "This object reflects the total number of Accepted
         (202) responses received by the user agent since system startup.
         The meaning of outbound 202 Ok responses depends
         on the method used in the associated request."
    REFERENCE
        "draft-ietf-sip-cc-transfer-04.txt"
    ::= { cSipStatsSuccess 3 }

cSipStatsSuccessAcceptedOuts OBJECT-TYPE
    SYNTAX Counter
    ACCESS read-only
    STATUS mandatory
    DESCRIPTION
        "This object reflects the total number of Accepted
         (202) responses sent by the user agent since system startup.
         The meaning of outbound 202 Ok responses depends
         on the method used in the associated request."
    REFERENCE
        "draft-ietf-sip-cc-transfer-04.txt"
    ::= { cSipStatsSuccess 4 }

cSipStatsSuccessOkTable OBJECT-TYPE
    SYNTAX SEQUENCE OF CSipStatsSuccessOkEntry
    ACCESS not-accessible
    STATUS mandatory
    DESCRIPTION
        "This table contains statistics for sent and
         received 200 Ok response messages.  The 
         statistics are kept on per SIP method basis."
    ::= { cSipStatsSuccess 5 }

cSipStatsSuccessOkEntry OBJECT-TYPE
    SYNTAX CSipStatsSuccessOkEntry
    ACCESS not-accessible
    STATUS mandatory
    DESCRIPTION
        "A row in the cSipStatsSuccessOkTable.  There is 
         an entry for each SIP method for which 200 Ok 
         inbound and/or outbound statistics are kept."
    INDEX { cSipStatsSuccessOkMethod }
    ::= { cSipStatsSuccessOkTable 1 }

CSipStatsSuccessOkEntry ::= SEQUENCE {
    cSipStatsSuccessOkMethod CSipMethodStr,
    cSipStatsSuccessOkInbounds Counter,
    cSipStatsSuccessOkOutbounds Counter
    }

cSipStatsSuccessOkMethod OBJECT-TYPE
    SYNTAX CSipMethodStr
--    Rsyntax OCTET STRING(SIZE(1..32))
    ACCESS not-accessible
    STATUS mandatory
    DESCRIPTION
        "This object is used for instance identification
         of objects in this table.  The value reflects a
         SIP method."
    ::= { cSipStatsSuccessOkEntry 1 }

cSipStatsSuccessOkInbounds OBJECT-TYPE
    SYNTAX Counter
    ACCESS read-only
    STATUS mandatory
    DESCRIPTION
        "This object reflects the total number of Ok
         (200) responses sent by the user agent, since
         system startup, that were associated with the
         SIP method as specified by cSipStatsSuccessOkMethod."
    ::= { cSipStatsSuccessOkEntry 2 }

cSipStatsSuccessOkOutbounds OBJECT-TYPE
    SYNTAX Counter
    ACCESS read-only
    STATUS mandatory
    DESCRIPTION
        "This object reflects the total number of Ok
         (200) responses received by the user agent, since
         system startup, that were associated with the
         SIP method as specified by cSipStatsSuccessOkMethod."
    ::= { cSipStatsSuccessOkEntry 3 }

cSipStatsRedirMultipleChoices OBJECT-TYPE
    SYNTAX Counter
    ACCESS read-only
    STATUS mandatory
    DESCRIPTION
        "This object reflects the total number of Multiple
         Choices (300) responses received by the user agent since system startup.
         Multiple Choices responses indicate that the called
         party can be reached at several different locations
         and the server cannot or prefers not to proxy the request."
    REFERENCE
        "RFC 2543, Section 5.1.1 & 7.3.1"
    ::= { cSipStatsRedirect 1 }

cSipStatsRedirMovedPerms OBJECT-TYPE
    SYNTAX Counter
    ACCESS read-only
    STATUS mandatory
    DESCRIPTION
        "This object reflects the total number of Moved 
         Permanently (301) responses received by the user agent since system startup.
         Moved Permanently responses indicate that the called party 
         can no longer be found at the address offered in the request 
         and the requesting UAC should retry at the new address given 
         by the Contact header field of the response."
    REFERENCE
        "RFC 2543, Sections 5.1.1 & 7.3.2"
    ::= { cSipStatsRedirect 2 }

cSipStatsRedirMovedTemps OBJECT-TYPE
    SYNTAX Counter
    ACCESS read-only
    STATUS deprecated
    DESCRIPTION
        "This object reflects the total number of Moved 
         Temporarily (302) responses received by the user agent since system startup.
         Moved Temporarily responses indicate the UAC should
         retry the request directed at the new address(es)
         given by the Contact header field of the response.
         The duration of this redirection can be indicated
         through the Expires header.  If no explicit expiration
         time is given, the new address(es) are only valid
         for this call."
    REFERENCE
        "RFC 2543, Sections 5.1.1 & 7.3.3"
    ::= { cSipStatsRedirect 3 }

cSipStatsRedirSeeOthers OBJECT-TYPE
    SYNTAX Counter
    ACCESS read-only
    STATUS obsolete
    DESCRIPTION
        "This object reflects the total number of See Other 
         (303) responses received by the user agent since system startup."
    REFERENCE
        "RFC 2543, Sections 5.1.1"
    ::= { cSipStatsRedirect 4 }

cSipStatsRedirUseProxys OBJECT-TYPE
    SYNTAX Counter
    ACCESS read-only
    STATUS mandatory
    DESCRIPTION
        "This object reflects the total number of Use Proxy 
         (305) responses received by the user agent since system startup.
         See Other responses indicate that requested resources
         must be accessed through the proxy given by the 
         Contact header field of the response.  The recipient
         of this response is expected to repeat this single
         request via the proxy."
    REFERENCE
        "RFC 2543, Sections 5.1.1 & 7.3.4"
    ::= { cSipStatsRedirect 5 }

cSipStatsRedirAltServices OBJECT-TYPE
    SYNTAX Counter
    ACCESS read-only
    STATUS mandatory
    DESCRIPTION
        "This object reflects the total number of Alternative
         Service (380) responses received by the user agent since system startup.
         Alternative Service responses indicate that the call
         was not successful, but alternative services are
         possible.  Those alternative services are described
         in the message body of the response."
    REFERENCE
        "RFC 2543, Sections 5.1.1 & 7.3.5"
    ::= { cSipStatsRedirect 6 }

cSipStatsRedirMovedTempsIns OBJECT-TYPE
    SYNTAX Counter
    ACCESS read-only
    STATUS mandatory
    DESCRIPTION
        "This object reflects the total number of Moved
         Temporarily (302) responses received by the user agent since
         system startup. 
         Moved Temporarily responses indicate the UAC should
         retry the request directed at the new address(es) 
         given by the Contact header field of the response.
         The duration of this redirection can be indicated
         through the Expires header.  If no explicit expiration
         time is given, the new address(es) are only valid
         for this call."
    REFERENCE
        "RFC 3261 Section 21.3.3"
    ::= { cSipStatsRedirect 7 }

cSipStatsRedirMovedTempsOuts OBJECT-TYPE
    SYNTAX Counter
    ACCESS read-only
    STATUS mandatory
    DESCRIPTION
        "This object reflects the total number of Moved
         Temporarily (302) responses sent by the user agent since
         system startup."
    REFERENCE
        "RFC 3261, Section 21.3.3"
    ::= { cSipStatsRedirect 8 }

cSipStatsClientBadRequestIns OBJECT-TYPE
    SYNTAX Counter
    ACCESS read-only
    STATUS mandatory
    DESCRIPTION
        "This object reflects the total number of Bad Request (400) 
         responses received by the user agent since system startup.
         Inbound Bad Request responses indicate that requests issued 
         by this system could not be understood due to malformed 
         syntax."
    REFERENCE
        "RFC 2543, Sections 5.1.1 & 7.4.1"
    ::= { cSipStatsErrClient 1 }

cSipStatsClientBadRequestOuts OBJECT-TYPE
    SYNTAX Counter
    ACCESS read-only
    STATUS mandatory
    DESCRIPTION
        "This object reflects the total number of Bad Request (400) 
         responses sent by the user agent since system startup.
         Outbound Bad Request responses indicate that requests 
         received by this system could not be understood due to 
         malformed syntax."
    REFERENCE
        "RFC 2543, Sections 5.1.1 & 7.4.1"
    ::= { cSipStatsErrClient 2 }

cSipStatsClientUnauthorizedIns OBJECT-TYPE
    SYNTAX Counter
    ACCESS read-only
    STATUS mandatory
    DESCRIPTION
        "This object reflects the total number of Unauthorized (401) 
         responses received by the user agent since system startup.  
         Inbound Unauthorized responses indicate that requests issued 
         by this system require user authentication."
    REFERENCE
        "RFC 2543, Sections 5.1.1 & 7.4.2"
    ::= { cSipStatsErrClient 3 }

cSipStatsClientUnauthorizedOuts OBJECT-TYPE
    SYNTAX Counter
    ACCESS read-only
    STATUS mandatory
    DESCRIPTION
        "This object reflects the total number of Unauthorized (401) 
         responses sent by the user agent since system startup.
         Outbound Unauthorized responses indicate that requests 
         received by this system require user authentication."
    REFERENCE
        "RFC 2543, Sections 5.1.1 & 7.4.2"
    ::= { cSipStatsErrClient 4 }

cSipStatsClientPaymentReqdIns OBJECT-TYPE
    SYNTAX Counter
    ACCESS read-only
    STATUS mandatory
    DESCRIPTION
        "This object reflects the total number of Payment Required 
         (402) responses received by the user agent since system startup."
    REFERENCE
        "RFC 2543, Sections 5.1.1 & 7.4.3"
    ::= { cSipStatsErrClient 5 }

cSipStatsClientPaymentReqdOuts OBJECT-TYPE
    SYNTAX Counter
    ACCESS read-only
    STATUS mandatory
    DESCRIPTION
        "This object reflects the total number of Payment Required 
         (402) responses sent by the user agent since system startup."
    REFERENCE
        "RFC 2543, Sections 5.1.1 & 7.4.3"
    ::= { cSipStatsErrClient 6 }

cSipStatsClientForbiddenIns OBJECT-TYPE
    SYNTAX Counter
    ACCESS read-only
    STATUS mandatory
    DESCRIPTION
        "This object reflects the total number of Forbidden (403) 
         responses received by the user agent since system startup.
         Inbound Forbidden responses indicate that requests issued
         by this system are understood by the server but the server
         refuses to fulfill the request.  Authorization will not help
         and the requests should not be repeated."
    REFERENCE
        "RFC 2543, Sections 5.1.1 & 7.4.4"
    ::= { cSipStatsErrClient 7 }

cSipStatsClientForbiddenOuts OBJECT-TYPE
    SYNTAX Counter
    ACCESS read-only
    STATUS mandatory
    DESCRIPTION
        "This object reflects the total number of Forbidden (403) 
         responses sent by the user agent since system startup.
         Outbound Forbidden responses indicate that requests received
         by this system are understood but this system is refusing to
         fulfill the requests."
    REFERENCE
        "RFC 2543, Sections 5.1.1 & 7.4.4"
    ::= { cSipStatsErrClient 8 }

cSipStatsClientNotFoundIns OBJECT-TYPE
    SYNTAX Counter
    ACCESS read-only
    STATUS mandatory
    DESCRIPTION
        "This object reflects the total number of Not Found (404) 
         responses received by the user agent since system startup.
         Inbound Not Found responses indicate that the called party 
         does not exist at the domain specified in the Request-URI 
         or the domain is not handled by the recipient of the request."
    REFERENCE
        "RFC 2543, Sections 5.1.1 & 7.4.5"
    ::= { cSipStatsErrClient 9 }

cSipStatsClientNotFoundOuts OBJECT-TYPE
    SYNTAX Counter
    ACCESS read-only
    STATUS mandatory
    DESCRIPTION
        "This object reflects the total number of Not Found (404) 
         responses sent by the user agent since system startup.
         Outbound Not Found responses indicate that this system
         knows that the called party does not exist at the domain
         specified in the Request-URI or the domain is not handled
         by this system."
    REFERENCE
        "RFC 2543, Sections 5.1.1 & 7.4.5"
    ::= { cSipStatsErrClient 10 }

cSipStatsClientMethNotAllowedIns OBJECT-TYPE
    SYNTAX Counter
    ACCESS read-only
    STATUS mandatory
    DESCRIPTION
        "This object reflects the total number of Method Not Allowed 
         (405) received responses by the user agent.
         Inbound Method Not Allowed responses indicate that requests 
         issued by this system have specified a SIP method in the 
         Request-Line that is not allowed for the address identified 
         by the Request-URI."
    REFERENCE
        "RFC 2543, Sections 5.1.1 & 7.4.6"
    ::= { cSipStatsErrClient 11 }

cSipStatsClientMethNotAllowedOuts OBJECT-TYPE
    SYNTAX Counter
    ACCESS read-only
    STATUS mandatory
    DESCRIPTION
        "This object reflects the total number of Method Not Allowed 
         (405) received sent by the user agent since system startup.
         Outbound Method Not Allowed responses indicate that requests 
         received by this system have SIP methods specified in the 
         Request-Line that are not allowed for the address identified 
         by the Request-URI."
    REFERENCE
        "RFC 2543, Sections 5.1.1 & 7.4.6"
    ::= { cSipStatsErrClient 12 }

cSipStatsClientNotAcceptableIns OBJECT-TYPE
    SYNTAX Counter
    ACCESS read-only
    STATUS mandatory
    DESCRIPTION
        "This object reflects the total number of Not Acceptable 
         (406) responses received by the user agent since system startup.
         Inbound Not Acceptable responses indicate the resources 
         identified by requests issued by this system cannot generate 
         responses with content characteristics acceptable to this 
         system according to the accept headers sent in the requests."
    REFERENCE
        "RFC 2543, Sections 5.1.1 & 7.4.7"
    ::= { cSipStatsErrClient 13 }

cSipStatsClientNotAcceptableOuts OBJECT-TYPE
    SYNTAX Counter
    ACCESS read-only
    STATUS mandatory
    DESCRIPTION
        "This object reflects the total number of Not Acceptable (406) 
         responses sent by the user agent since system startup.
         Outbound Not Acceptable responses indicate that the resources
         identified by requests received by this system cannot generate
         responses with content characteristics acceptable to the 
         system sending the requests."
    REFERENCE
        "RFC 2543, Sections 5.1.1 & 7.4.7"
    ::= { cSipStatsErrClient 14 }

cSipStatsClientProxyAuthReqdIns OBJECT-TYPE
    SYNTAX Counter
    ACCESS read-only
    STATUS mandatory
    DESCRIPTION
        "This object reflects the total number of Proxy Authentication 
         Required (407) responses received by the user agent since system startup.
         Inbound Proxy Authentication Required responses indicate that 
         this system must authenticate itself with the proxy before 
         gaining access to the requested resource."
    REFERENCE
        "RFC 2543, Sections 5.1.1 & 7.4.8"
    ::= { cSipStatsErrClient 15 }

cSipStatsClientProxyAuthReqdOuts OBJECT-TYPE
    SYNTAX Counter
    ACCESS read-only
    STATUS mandatory
    DESCRIPTION
        "This object reflects the total number of Proxy Authentication 
         Required (407) responses sent by the user agent since system startup.
         Outbound Proxy Authentication Required responses indicate that
         the systems issuing requests being processed by this system 
         must authenticate themselves with this system before gaining 
         access to requested resources."
    REFERENCE
        "RFC 2543, Sections 5.1.1 & 7.4.8"
    ::= { cSipStatsErrClient 16 }

cSipStatsClientReqTimeoutIns OBJECT-TYPE
    SYNTAX Counter
    ACCESS read-only
    STATUS mandatory
    DESCRIPTION
        "This object reflects the total number of Request Timeout 
         (408) responses received by the user agent since system startup.
         Inbound Request Timeout responses indicate that requests 
         issued by this system are not being processed by the server 
         within the time indicated in the Expires header of the 
         request."
    REFERENCE
        "RFC 2543, Sections 5.1.1 & 7.4.9"
    ::= { cSipStatsErrClient 17 }

cSipStatsClientReqTimeoutOuts OBJECT-TYPE
    SYNTAX Counter
    ACCESS read-only
    STATUS mandatory
    DESCRIPTION
        "This object reflects the total number of Request Timeout 
         (408) responses sent by the user agent since system startup.
         Outbound Request Timeout responses indicate that this 
         system is not able to produce an appropriate response within 
         the time indicated in the Expires header of the request."
    REFERENCE
        "RFC 2543, Sections 5.1.1 & 7.4.9"
    ::= { cSipStatsErrClient 18 }

cSipStatsClientConflictIns OBJECT-TYPE
    SYNTAX Counter
    ACCESS read-only
    STATUS mandatory
    DESCRIPTION
        "This object reflects the total number of Conflict (409) 
         responses received by the user agent since system startup.
         Inbound Conflict responses indicate that requests issued
         by this system could not be completed due to a conflict
         with the current state of a requested resource."
    REFERENCE
        "RFC 2543, Sections 5.1.1 & 7.4.10"
    ::= { cSipStatsErrClient 19 }

cSipStatsClientConflictOuts OBJECT-TYPE
    SYNTAX Counter
    ACCESS read-only
    STATUS mandatory
    DESCRIPTION
        "This object reflects the total number of Conflict (409) 
         responses sent by the user agent since system startup.
         Outbound Conflict responses indicate that requests received
         by this system could not be completed due to a conflict
         with the current state of a requested resource."
    REFERENCE
        "RFC 2543, Sections 5.1.1 & 7.4.10"
    ::= { cSipStatsErrClient 20 }

cSipStatsClientGoneIns OBJECT-TYPE
    SYNTAX Counter
    ACCESS read-only
    STATUS mandatory
    DESCRIPTION
        "This object reflects the total number of Gone (410) 
         responses received by the user agent since system startup.
         Inbound Gone responses indicate that resources requested
         by this system are no longer available at the recipient server
         and no forwarding address is known."
    REFERENCE
        "RFC 2543, Sections 5.1.1 & 7.4.11"
    ::= { cSipStatsErrClient 21 }

cSipStatsClientGoneOuts OBJECT-TYPE
    SYNTAX Counter
    ACCESS read-only
    STATUS mandatory
    DESCRIPTION
        "This object reflects the total number of Gone (410) 
         responses sent by the user agent since system startup.
         Outbound Gone responses indicate that the requested
         resources are no longer available at this system and
         no forwarding address is known."
    REFERENCE
        "RFC 2543, Sections 5.1.1 & 7.4.11"
    ::= { cSipStatsErrClient 22 }

cSipStatsClientLengthRequiredIns OBJECT-TYPE
    SYNTAX Counter
    ACCESS read-only
    STATUS obsolete
    DESCRIPTION
        "This object reflects the total number of Length Required 
         (411) responses received by the user agent since system startup.
         Inbound Length Required responses indicate that requests 
         issued by this system are being refused by servers because 
         of no defined Content-Length header field."
    REFERENCE
        "RFC 2543, Sections 5.1.1 & 7.4.12"
    ::= { cSipStatsErrClient 23 }

cSipStatsClientLengthRequiredOuts OBJECT-TYPE
    SYNTAX Counter
    ACCESS read-only
    STATUS obsolete
    DESCRIPTION
        "This object reflects the total number of Length Required 
         (411) responses sent by the user agent since system startup.
         Outbound Length Required responses indicate that requests 
         received by this system are being refused because of no 
         defined Content-Length header field."
    REFERENCE
        "RFC 2543, Sections 5.1.1 & 7.4.12"
    ::= { cSipStatsErrClient 24 }

cSipStatsClientReqEntTooLargeIns OBJECT-TYPE
    SYNTAX Counter
    ACCESS read-only
    STATUS mandatory
    DESCRIPTION
        "This object reflects the total number of Request Entity Too 
         Large (413) responses received by the user agent since system startup.
         Inbound Request Entity Too Large responses indicate that 
         requests issued by this system are being refused because 
         the request is larger than the server is willing or able to 
         process."
    REFERENCE
        "RFC 2543, Sections 5.1.1 & 7.4.13"
    ::= { cSipStatsErrClient 25 }

cSipStatsClientReqEntTooLargeOuts OBJECT-TYPE
    SYNTAX Counter
    ACCESS read-only
    STATUS mandatory
    DESCRIPTION
        "This object reflects the total number of Request Entity Too 
         Large (413) responses sent by the user agent since system startup.
         Outbound Request Entity Too Large responses indicate that 
         requests received by this system are larger than this system 
         is willing or able to process."
    REFERENCE
        "RFC 2543, Sections 5.1.1 & 7.4.13"
    ::= { cSipStatsErrClient 26 }

cSipStatsClientReqURITooLargeIns OBJECT-TYPE
    SYNTAX Counter
    ACCESS read-only
    STATUS mandatory
    DESCRIPTION
        "This object reflects the total number of Request-URI Too 
         Large (414) responses received by the user agent since system startup.
         Inbound Request-URI Too Large responses indicate that 
         requests issued by this system are being refused because the 
         Request-URI is longer than the server is willing or able to 
         interpret."
    REFERENCE
        "RFC 2543, Sections 5.1.1 & 7.4.14"
    ::= { cSipStatsErrClient 27 }

cSipStatsClientReqURITooLargeOuts OBJECT-TYPE
    SYNTAX Counter
    ACCESS read-only
    STATUS mandatory
    DESCRIPTION
        "This object reflects the total number of Request-URI Too 
         Large (414) responses sent by the user agent since system startup.
         Outbound Request-URI Too Large responses indicate that 
         Request-URIs received by this system are longer than this 
         system is willing or able to interpret."
    REFERENCE
        "RFC 2543, Sections 5.1.1 & 7.4.14"
    ::= { cSipStatsErrClient 28 }

cSipStatsClientNoSupMediaTypeIns OBJECT-TYPE
    SYNTAX Counter
    ACCESS read-only
    STATUS mandatory
    DESCRIPTION
        "This object reflects the total number of Unsupported Media 
         Type (415) responses received by the user agent since system startup.
         Inbound Unsupported Media Type responses indicate that 
         requests issued by this system are being refused because the 
         message body of the request is in a format not supported by 
         the requested resource for the requested method."
    REFERENCE
        "RFC 2543, Sections 5.1.1 & 7.4.15"
    ::= { cSipStatsErrClient 29 }

cSipStatsClientNoSupMediaTypeOuts OBJECT-TYPE
    SYNTAX Counter
    ACCESS read-only
    STATUS mandatory
    DESCRIPTION
        "This object reflects the total number of Unsupported Media 
         Type (415) responses sent by the user agent since system startup.
         Outbound Unsupported Media Type responses indicate that the 
         body of requests received by this system are in a format not 
         supported by the requested resource for the requested method."
    REFERENCE
        "RFC 2543, Sections 5.1.1 & 7.4.15"
    ::= { cSipStatsErrClient 30 }

cSipStatsClientBadExtensionIns OBJECT-TYPE
    SYNTAX Counter
    ACCESS read-only
    STATUS mandatory
    DESCRIPTION
        "This object reflects the total number of Bad Extension (420) 
         responses received by the user agent since system startup.
         Inbound Bad Extension responses indicate that the recipient 
         did not understand the protocol extension specified in a 
         Require header field."
    REFERENCE
        "RFC 2543, Sections 5.1.1 & 7.5.16"
    ::= { cSipStatsErrClient 31 }

cSipStatsClientBadExtensionOuts OBJECT-TYPE
    SYNTAX Counter
    ACCESS read-only
    STATUS mandatory
    DESCRIPTION
        "This object reflects the total number of Bad Extension (420) 
         responses sent by the user agent since system startup.
         Outbound Bad Extension responses indicate that this system
         did not understand the protocol extension specified in a
         Require header field of requests."
    REFERENCE
        "RFC 2543, Sections 5.1.1 & 7.4.16"
    ::= { cSipStatsErrClient 32 }

cSipStatsClientTempNotAvailIns OBJECT-TYPE
    SYNTAX Counter
    ACCESS read-only
    STATUS mandatory
    DESCRIPTION
        "This object reflects the total number of Temporarily Not 
         Available (480) responses received by the user agent since system startup.
         Inbound Temporarily Not Available responses indicate that 
         the called party is currently unavailable."
    REFERENCE
        "RFC 2543, Sections 5.1.1 & 7.4.17"
    ::= { cSipStatsErrClient 33 }

cSipStatsClientTempNotAvailOuts OBJECT-TYPE
    SYNTAX Counter
    ACCESS read-only
    STATUS mandatory
    DESCRIPTION
        "This object reflects the total number of Temporarily Not 
         Available (480) responses sent by the user agent since system startup.
         Outbound Temporarily Not Available responses indicate that 
         the called party's end system was contacted successfully but 
         the called party is currently unavailable."
    REFERENCE
        "RFC 2543, Sections 5.1.1 & 7.4.17"
    ::= { cSipStatsErrClient 34 }

cSipStatsClientCallLegNoExistIns OBJECT-TYPE
    SYNTAX Counter
    ACCESS read-only
    STATUS mandatory
    DESCRIPTION
        "This object reflects the total number of Call Leg/Transaction 
         Does Not Exist (481) responses received by the user agent since system startup.
         Inbound Call Leg/Transaction Does Not Exist responses indicate
         that either BYE or CANCEL requests issued by this system were 
         received by a server and not matching call leg or transaction 
         existed."
    REFERENCE
        "RFC 2543, Sections 5.1.1 & 7.4.18"
    ::= { cSipStatsErrClient 35 }

cSipStatsClientCallLegNoExistOuts OBJECT-TYPE
    SYNTAX Counter
    ACCESS read-only
    STATUS mandatory
    DESCRIPTION
        "This object reflects the total number of Call Leg/Transaction 
         Does Not Exist (481) responses sent by the user agent since system startup.
         Outbound Call Leg/Transaction Does Not Exist responses 
         indicate that BYE or CANCEL requests have been received by 
         this system and not call leg or transaction matching that 
         request exists."
    REFERENCE
        "RFC 2543, Sections 5.1.1 & 7.4.18"
    ::= { cSipStatsErrClient 36 }

cSipStatsClientLoopDetectedIns OBJECT-TYPE
    SYNTAX Counter
    ACCESS read-only
    STATUS mandatory
    DESCRIPTION
        "This object reflects the total number of Loop Detected (482) 
         responses received by the user agent since system startup.
         Inbound Loop Detected responses indicate that requests issued
         by this system were received at servers and the server found 
         itself in the Via path more than once."
    REFERENCE
        "RFC 2543, Sections 5.1.1 & 7.4.19"
    ::= { cSipStatsErrClient 37 }

cSipStatsClientLoopDetectedOuts OBJECT-TYPE
    SYNTAX Counter
    ACCESS read-only
    STATUS mandatory
    DESCRIPTION
        "This object reflects the total number of Loop Detected (482) 
         responses sent by the user agent since system startup.
         Outbound Loop Detected responses indicate that requests 
         received by this system contain a Via path with this system 
         appearing more than once."
    REFERENCE
        "RFC 2543, Sections 5.1.1 & 7.4.19"
    ::= { cSipStatsErrClient 38 }

cSipStatsClientTooManyHopsIns OBJECT-TYPE
    SYNTAX Counter
    ACCESS read-only
    STATUS mandatory
    DESCRIPTION
        "This object reflects the total number of Too Many Hops (483) 
         responses received by the user agent since system startup.
         Inbound Too Many Hops responses indicate that requests issued
         by this system contain more Via entries (hops) than allowed by
         the Max-Forwards header field of the requests."
    REFERENCE
        "RFC 2543, Sections 5.1.1 & 7.4.20"
    ::= { cSipStatsErrClient 39 }

cSipStatsClientTooManyHopsOuts OBJECT-TYPE
    SYNTAX Counter
    ACCESS read-only
    STATUS mandatory
    DESCRIPTION
        "This object reflects the total number of Too Many Hops (483) 
         responses sent by the user agent since system startup.
         Outbound Too Many Hops responses indicate that requests
         received by this system contain more Via entries (hops) than
         are allowed by the Max-Forwards header field of the requests."
    REFERENCE
        "RFC 2543, Sections 5.1.1 & 7.4.20"
    ::= { cSipStatsErrClient 40 }

cSipStatsClientAddrIncompleteIns OBJECT-TYPE
    SYNTAX Counter
    ACCESS read-only
    STATUS mandatory
    DESCRIPTION
        "This object reflects the total number of Address Incomplete 
         (484) responses received by the user agent since system startup.
         Inbound Address Incomplete responses indicate that requests 
         issued by this system had To addresses or Request-URIs that 
         were incomplete."
    REFERENCE
        "RFC 2543, Sections 5.1.1 & 7.4.21"
    ::= { cSipStatsErrClient 41 }

cSipStatsClientAddrIncompleteOuts OBJECT-TYPE
    SYNTAX Counter
    ACCESS read-only
    STATUS mandatory
    DESCRIPTION
        "This object reflects the total number of Address Incomplete 
         (484) responses sent by the user agent since system startup.
         Outbound Address Incomplete responses indicate that requests 
         received by this system had To addresses or Request-URIs that 
         were incomplete."
    REFERENCE
        "RFC 2543, Sections 5.1.1 & 7.4.21"
    ::= { cSipStatsErrClient 42 }

cSipStatsClientAmbiguousIns OBJECT-TYPE
    SYNTAX Counter
    ACCESS read-only
    STATUS mandatory
    DESCRIPTION
        "This object reflects the total number of Ambiguous (485) 
         responses received by the user agent since system startup.
         Inbound Ambiguous responses indicate that requests issued
         by this system provided ambiguous address information."
    REFERENCE
        "RFC 2543, Sections 5.1.1 & 7.4.22"
    ::= { cSipStatsErrClient 43 }

cSipStatsClientAmbiguousOuts OBJECT-TYPE
    SYNTAX Counter
    ACCESS read-only
    STATUS mandatory
    DESCRIPTION
        "This object reflects the total number of Ambiguous (485) 
         responses sent by the user agent since system startup.
         Outbound Ambiguous responses indicate that requests received
         by this system contained ambiguous address information."
    REFERENCE
        "RFC 2543, Sections 5.1.1 & 7.4.22"
    ::= { cSipStatsErrClient 44 }

cSipStatsClientBusyHereIns OBJECT-TYPE
    SYNTAX Counter
    ACCESS read-only
    STATUS mandatory
    DESCRIPTION
        "This object reflects the total number of Busy Here (486) 
         responses received by the user agent since system startup.
         Inbound Busy Here responses indicate that the
         called party is currently not willing or not able to
         take additional calls."
    REFERENCE
        "RFC 2543, Section 5.1.1 & 7.4.23"
    ::= { cSipStatsErrClient 45 }

cSipStatsClientBusyHereOuts OBJECT-TYPE
    SYNTAX Counter
    ACCESS read-only
    STATUS mandatory
    DESCRIPTION
        "This object reflects the total number of Busy Here (486) 
         responses sent by the user agent since system startup.
         Outbound Busy Here responses indicate that the
         called party's end system was contacted successfully but the
         called party is currently not willing or able to take 
         additional calls."
    REFERENCE
        "RFC 2543, Sections 5.1.1 & 7.4.23"
    ::= { cSipStatsErrClient 46 }

cSipStatsClientReqTermIns OBJECT-TYPE
    SYNTAX Counter
    ACCESS read-only
    STATUS mandatory
    DESCRIPTION
        "This object reflects the total number of Request Terminated 
         (487) responses received by the user agent since system startup.
         Request Terminated responses are issued if the original 
         request was terminated via CANCEL or BYE."
    REFERENCE
        "draft-ietf-sip-rfc2543bis-01.txt, Section 7.4.24.487"
    ::= { cSipStatsErrClient 47 }

cSipStatsClientReqTermOuts OBJECT-TYPE
    SYNTAX Counter
    ACCESS read-only
    STATUS mandatory
    DESCRIPTION
        "This object reflects the total number of Request Terminated 
         (487) responses sent by the user agent since system startup.
         Request Terminated responses are issued if the original 
         request was terminated via CANCEL or BYE."
    REFERENCE
        "draft-ietf-sip-rfc2543bis-01.txt, Section 7.4.24.487"
    ::= { cSipStatsErrClient 48 }

cSipStatsClientNoAcceptHereIns OBJECT-TYPE
    SYNTAX Counter
    ACCESS read-only
    STATUS mandatory
    DESCRIPTION
        "This object reflects the total number of Not Acceptable Here
         (488) responses received by the user agent since system startup.
         The response has the same meaning as 606 (Not Acceptable), 
         but only applies to the specific entity addressed by the 
         Request-URI and the request may succeed elsewhere."
    REFERENCE
        "draft-ietf-sip-rfc2543bis-01.txt, Section 7.4.24.488"
    ::= { cSipStatsErrClient 49 }

cSipStatsClientNoAcceptHereOuts OBJECT-TYPE
    SYNTAX Counter
    ACCESS read-only
    STATUS mandatory
    DESCRIPTION
        "This object reflects the total number of Not Acceptable Here
         (488) responses sent by the user agent since system startup.
         The response has the same meaning as 606 (Not Acceptable), 
         but only applies to the specific entity addressed by the 
         Request-URI and the request may succeed elsewhere."
    REFERENCE
        "draft-ietf-sip-rfc2543bis-01.txt, Section 7.4.24.488"
    ::= { cSipStatsErrClient 50 }

cSipStatsClientBadEventIns OBJECT-TYPE
    SYNTAX Counter
    ACCESS read-only
    STATUS mandatory
    DESCRIPTION
        "This object reflects the total number of BadEvent (489) 
         responses received by the user agent since system startup."
    ::= { cSipStatsErrClient 51 }

cSipStatsClientBadEventOuts OBJECT-TYPE
    SYNTAX Counter
    ACCESS read-only
    STATUS mandatory
    DESCRIPTION
        "This object reflects the total number of BadEvent (489) 
         responses sent by the user agent since system startup."
    ::= { cSipStatsErrClient 52 }

cSipStatsClientSTTooSmallIns OBJECT-TYPE
    SYNTAX Counter
    ACCESS read-only
    STATUS mandatory
    DESCRIPTION
        "This object reflects the total number of SessionTimerTooSmall
         (422) responses received by the user agent since system 
         startup."
    ::= { cSipStatsErrClient 53 }

cSipStatsClientSTTooSmallOuts OBJECT-TYPE
    SYNTAX Counter
    ACCESS read-only
    STATUS mandatory
    DESCRIPTION
        "This object reflects the total number of SessionTimerTooSmall
         (422) responses sent by the user agent since system startup."
    ::= { cSipStatsErrClient 54 }

cSipStatsClientReqPendingIns OBJECT-TYPE
    SYNTAX Counter
    ACCESS read-only
    STATUS mandatory
    DESCRIPTION
        "This object reflects the total number of RequestPending
         (491) responses received by the user agent since system
         startup."
    ::= { cSipStatsErrClient 55 }

cSipStatsClientReqPendingOuts OBJECT-TYPE
    SYNTAX Counter
    ACCESS read-only
    STATUS mandatory
    DESCRIPTION
        "This object reflects the total number of RequestPending
         (491) responses sent by the user agent since system startup."
    ::= { cSipStatsErrClient 56 }

cSipStatsServerIntErrorIns OBJECT-TYPE
    SYNTAX Counter
    ACCESS read-only
    STATUS mandatory
    DESCRIPTION
        "This object reflects the total number of Internal Server Error
         (500) responses received by the user agent since system startup.
         Inbound Internal Server Error responses indicate that servers 
         to which this system is sending requests have encountered 
         unexpected conditions that prevent them from fulfilling the 
         requests."
    REFERENCE
        "RFC 2543, Sections 5.1.1 & 7.5.1"
    ::= { cSipStatsErrServer 1 }

cSipStatsServerIntErrorOuts OBJECT-TYPE
    SYNTAX Counter
    ACCESS read-only
    STATUS mandatory
    DESCRIPTION
        "This object reflects the total number of Internal Server Error
         (500) responses sent by the user agent since system startup.
         Outbound Internal Server Error responses indicate that this 
         system has encountered unexpected conditions that prevent it 
         from fulfilling received requests."
    REFERENCE
        "RFC 2543, Sections 5.1.1 & 7.5.1"
    ::= { cSipStatsErrServer 2 }

cSipStatsServerNotImplementedIns OBJECT-TYPE
    SYNTAX Counter
    ACCESS read-only
    STATUS mandatory
    DESCRIPTION
        "This object reflects the total number of Not Implemented 
         (501) responses received by the user agent since system startup.
         Inbound Not Implemented responses indicate that servers to 
         which this system is sending requests do not support the 
         functionality required to fulfill the requests."
    REFERENCE
        "RFC 2543, Sections 5.1.1 & 7.5.2"
    ::= { cSipStatsErrServer 3 }

cSipStatsServerNotImplementedOuts OBJECT-TYPE
    SYNTAX Counter
    ACCESS read-only
    STATUS mandatory
    DESCRIPTION
        "This object reflects the total number of Not Implemented 
         (501) responses sent by the user agent since system startup.
         Outbound Not Implemented responses indicate that this system
         does not support the functionality required to fulfill the 
         requests."
    REFERENCE
        "RFC 2543, Sections 5.1.1 & 7.5.2"
    ::= { cSipStatsErrServer 4 }

cSipStatsServerBadGatewayIns OBJECT-TYPE
    SYNTAX Counter
    ACCESS read-only
    STATUS mandatory
    DESCRIPTION
        "This object reflects the total number of Bad Gateway (502) 
         responses received by the user agent since system startup."
    REFERENCE
        "RFC 2543, Sections 5.1.1 & 7.5.3"
    ::= { cSipStatsErrServer 5 }

cSipStatsServerBadGatewayOuts OBJECT-TYPE
    SYNTAX Counter
    ACCESS read-only
    STATUS mandatory
    DESCRIPTION
        "This object reflects the total number of Bad Gateway (502) 
         responses sent by the user agent since system startup."
    REFERENCE
        "RFC 2543, Sections 5.1.1 & 7.5.3"
    ::= { cSipStatsErrServer 6 }

cSipStatsServerServiceUnavailIns OBJECT-TYPE
    SYNTAX Counter
    ACCESS read-only
    STATUS mandatory
    DESCRIPTION
        "This object reflects the total number of Service Unavailable 
         (503) responses received by the user agent since system startup.
         Inbound Service Unavailable responses indicate that the server
         servicing this system's request is temporarily unavailable to
         handle the request."
    REFERENCE
        "RFC 2543, Sections 5.1.1 & 7.5.4"
    ::= { cSipStatsErrServer 7 }

cSipStatsServerServiceUnavailOuts OBJECT-TYPE
    SYNTAX Counter
    ACCESS read-only
    STATUS mandatory
    DESCRIPTION
        "This object reflects the total number of Service Unavailable 
         (503) responses sent by the user agent since system startup.
         Outbound Service Unavailable responses indicate that this
         system is temporarily unable to handle received requests."
    REFERENCE
        "RFC 2543, Sections 5.1.1 & 7.5.4"
    ::= { cSipStatsErrServer 8 }

cSipStatsServerGatewayTimeoutIns OBJECT-TYPE
    SYNTAX Counter
    ACCESS read-only
    STATUS mandatory
    DESCRIPTION
        "This object reflects the total number of Gateway Time-out 
         (504) responses received by the user agent since system startup.
         Inbound Gateway Time-out responses indicate that the server
         attempting to complete this system's request did not receive
         a timely response from yet another system it was accessing to
         complete the request."
    REFERENCE
        "RFC 2543, Sections 5.1.1 & 7.5.5"
    ::= { cSipStatsErrServer 9 }

cSipStatsServerGatewayTimeoutOuts OBJECT-TYPE
    SYNTAX Counter
    ACCESS read-only
    STATUS mandatory
    DESCRIPTION
        "This object reflects the total number of Gateway Time-out 
         (504) responses sent by the user agent since system startup.
         Outbound Gateway Time-out responses indicate that this system
         did not receive a timely response from the system it had
         accessed to assist in completing a received request."
    REFERENCE
        "RFC 2543, Sections 5.1.1 & 7.5.5"
    ::= { cSipStatsErrServer 10 }

cSipStatsServerBadSipVersionIns OBJECT-TYPE
    SYNTAX Counter
    ACCESS read-only
    STATUS mandatory
    DESCRIPTION
        "This object reflects the total number of SIP Version Not 
         Supported (505) responses received by the user agent since system startup.
         Inbound SIP Version Not Supported responses indicate that 
         the server does not support, or refuses to support, the SIP 
         protocol version that was used in the request message."
    REFERENCE
        "RFC 2543, Sections 5.1.1 & 7.5.6"
    ::= { cSipStatsErrServer 11 }

cSipStatsServerBadSipVersionOuts OBJECT-TYPE
    SYNTAX Counter
    ACCESS read-only
    STATUS mandatory
    DESCRIPTION
        "This object reflects the total number of SIP Version Not 
         Supported (505) responses sent by the user agent since system startup.
         Outbound SIP Version Not Supported responses indicate that 
         this system does not support, or refuses to support, the SIP 
         protocol version used in received requests."
    REFERENCE
        "RFC 2543, Sections 5.1.1 & 7.5.6"
    ::= { cSipStatsErrServer 12 }

cSipStatsServerPrecondFailureIns OBJECT-TYPE
    SYNTAX Counter
    ACCESS read-only
    STATUS mandatory
    DESCRIPTION
        "This object reflects the total number of Precondition 
         Failure (580) responses received by the user agent since system startup.
         This response is returned by a UAS if it is unable to
         perform the mandatory preconditions for the session."
    REFERENCE
        "draft-manyfolks-sip-resource-01.txt, Section 6"
    ::= { cSipStatsErrServer 13 }

cSipStatsServerPrecondFailureOuts OBJECT-TYPE
    SYNTAX Counter
    ACCESS read-only
    STATUS mandatory
    DESCRIPTION
        "This object reflects the total number of Precondition 
         Failure (580) responses sent by the user agent since system startup.
         This response is returned by a UAS if it is unable to
         perform the mandatory preconditions for the session."
    REFERENCE
        "draft-manyfolks-sip-resource-01.txt, Section 6"
    ::= { cSipStatsErrServer 14 }

cSipStatsGlobalBusyEverywhereIns OBJECT-TYPE
    SYNTAX Counter
    ACCESS read-only
    STATUS mandatory
    DESCRIPTION
        "This object reflects the total number of Busy
         Everywhere (600) responses received by the user agent since system startup.
         Inbound Busy Everywhere responses indicate that the 
         called party's end system was contacted successfully
         but the called party is busy and does not wish to take
         the call at this time."
    REFERENCE
        "RFC 2543, Sections 5.1.1 & 7.6.1"
    ::= { cSipStatsGlobalFail 1 }

cSipStatsGlobalBusyEverywhereOuts OBJECT-TYPE
    SYNTAX Counter
    ACCESS read-only
    STATUS mandatory
    DESCRIPTION
        "This object reflects the total number of Busy
         Everywhere (600) responses sent by the user agent since system startup.
         Outbound Busy Everywhere responses indicate that 
         this system has successfully contacted a called party's
         end system and the called party does not wish to take
         the call at this time."
    REFERENCE
        "RFC 2543, Sections 5.1.1 & 7.6.1"
    ::= { cSipStatsGlobalFail 2 }

cSipStatsGlobalDeclineIns OBJECT-TYPE
    SYNTAX Counter
    ACCESS read-only
    STATUS mandatory
    DESCRIPTION
        "This object reflects the total number of Decline
         (603) responses received by the user agent since system startup.
         Decline responses indicate that the called party's end 
         system was contacted successfully but the called party 
         explicitly does not wish to, or cannot, participate."
    REFERENCE
        "RFC 2543, Sections 5.1.1 & 7.6.2"
    ::= { cSipStatsGlobalFail 3 }

cSipStatsGlobalDeclineOuts OBJECT-TYPE
    SYNTAX Counter
    ACCESS read-only
    STATUS mandatory
    DESCRIPTION
        "This object reflects the total number of Decline
         (603) responses sent by the user agent since system startup.
         Outbound Decline responses indicate that this system
         has successfully contacted a called party's end system
         and the called party explicitly does not wish to, or
         cannot, participate."
    REFERENCE
        "RFC 2543, Sections 5.1.1 & 7.6.2"
    ::= { cSipStatsGlobalFail 4 }

cSipStatsGlobalNotAnywhereIns OBJECT-TYPE
    SYNTAX Counter
    ACCESS read-only
    STATUS mandatory
    DESCRIPTION
        "This object reflects the total number of Does Not
         Exist Anywhere (604) responses received by the user agent since system startup.
         Inbound Does Not Exist Anywhere responses indicate that
         the server handling this system's request has authoritative
         information that the called party indicated in the To
         request field does not exist anywhere."
    REFERENCE
        "RFC 2543, Sections 5.1.1 & 7.6.3"
    ::= { cSipStatsGlobalFail 5 }

cSipStatsGlobalNotAnywhereOuts OBJECT-TYPE
    SYNTAX Counter
    ACCESS read-only
    STATUS mandatory
    DESCRIPTION
        "This object reflects the total number of Does Not
         Exist Anywhere (604) responses sent by the user agent since system startup.
         Outbound Does Not Exist Anywhere responses indicate that
         this system has authoritative information that the called
         party in the To field of received requests does not exist
         anywhere."
    REFERENCE
        "RFC 2543, Sections 5.1.1 & 7.6.3"
    ::= { cSipStatsGlobalFail 6 }

cSipStatsGlobalNotAcceptableIns OBJECT-TYPE
    SYNTAX Counter
    ACCESS read-only
    STATUS mandatory
    DESCRIPTION
        "This object reflects the total number of Not Acceptable
         (606) responses received by the user agent since system startup.
         Inbound Not Acceptable responses indicate that the called
         party's end system was contacted successfully but some
         aspect of the session description is not acceptable."
    REFERENCE
        "RFC 2543, Sections 5.1.1 & 7.6.4"
    ::= { cSipStatsGlobalFail 7 }

cSipStatsGlobalNotAcceptableOuts OBJECT-TYPE
    SYNTAX Counter
    ACCESS read-only
    STATUS mandatory
    DESCRIPTION
        "This object reflects the total number of Not Acceptable
         (606) responses sent by the user agent since system startup.
         Outbound Not Acceptable responses indicate that the called
         party wishes to communicate, but cannot adequately support
         the session described in the request."
    REFERENCE
        "RFC 2543, Sections 5.1.1 & 7.6.4"
    ::= { cSipStatsGlobalFail 8 }

cSipStatsTrafficInviteIns OBJECT-TYPE
    SYNTAX Counter
    ACCESS read-only
    STATUS mandatory
    DESCRIPTION
        "This object reflects the total number of INVITE requests 
         received by the user agent since system startup."
    REFERENCE
        "RFC 2543, Section 4.2.1"
    ::= { cSipStatsTraffic 1 }

cSipStatsTrafficInviteOuts OBJECT-TYPE
    SYNTAX Counter
    ACCESS read-only
    STATUS mandatory
    DESCRIPTION
        "This object reflects the total number of INVITE requests sent
         by the user agent."
    REFERENCE
        "RFC 2543, Section 4.2.1"
    ::= { cSipStatsTraffic 2 }

cSipStatsTrafficAckIns OBJECT-TYPE
    SYNTAX Counter
    ACCESS read-only
    STATUS mandatory
    DESCRIPTION
        "This object reflects the total number of ACK requests 
         received by the user agent since system startup."
    REFERENCE
        "RFC 2543, Section 4.2.2"
    ::= { cSipStatsTraffic 3 }

cSipStatsTrafficAckOuts OBJECT-TYPE
    SYNTAX Counter
    ACCESS read-only
    STATUS mandatory
    DESCRIPTION
        "This object reflects the total number of ACK requests sent
         by the user agent."
    REFERENCE
        "RFC 2543, Section 4.2.2"
    ::= { cSipStatsTraffic 4 }

cSipStatsTrafficByeIns OBJECT-TYPE
    SYNTAX Counter
    ACCESS read-only
    STATUS mandatory
    DESCRIPTION
        "This object reflects the total number of BYE requests 
         received by the user agent since system startup."
    REFERENCE
        "RFC 2543, Section 4.2.4"
    ::= { cSipStatsTraffic 5 }

cSipStatsTrafficByeOuts OBJECT-TYPE
    SYNTAX Counter
    ACCESS read-only
    STATUS mandatory
    DESCRIPTION
        "This object reflects the total number of BYE requests sent
         by the user agent."
    REFERENCE
        "RFC 2543, Section 4.2.4"
    ::= { cSipStatsTraffic 6 }

cSipStatsTrafficCancelIns OBJECT-TYPE
    SYNTAX Counter
    ACCESS read-only
    STATUS mandatory
    DESCRIPTION
        "This object reflects the total number of CANCEL requests 
         received by the user agent since system startup."
    REFERENCE
        "RFC 2543, Section 4.2.5"
    ::= { cSipStatsTraffic 7 }

cSipStatsTrafficCancelOuts OBJECT-TYPE
    SYNTAX Counter
    ACCESS read-only
    STATUS mandatory
    DESCRIPTION
        "This object reflects the total number of CANCEL requests sent
         by the user agent."
    REFERENCE
        "RFC 2543, Section 4.2.5"
    ::= { cSipStatsTraffic 8 }

cSipStatsTrafficOptionsIns OBJECT-TYPE
    SYNTAX Counter
    ACCESS read-only
    STATUS mandatory
    DESCRIPTION
        "This object reflects the total number of OPTIONS requests 
         received by the user agent since system startup."
    REFERENCE
        "RFC 2543, Section 4.2.3"
    ::= { cSipStatsTraffic 9 }

cSipStatsTrafficOptionsOuts OBJECT-TYPE
    SYNTAX Counter
    ACCESS read-only
    STATUS mandatory
    DESCRIPTION
        "This object reflects the total number of OPTIONS requests sent
         by the user agent."
    REFERENCE
        "RFC 2543, Section 4.2.3"
    ::= { cSipStatsTraffic 10 }

cSipStatsTrafficRegisterIns OBJECT-TYPE
    SYNTAX Counter
    ACCESS read-only
    STATUS mandatory
    DESCRIPTION
        "This object reflects the total number of REGISTER requests 
         received by the user agent since system startup."
    REFERENCE
        "RFC 2543, Section 4.2.6"
    ::= { cSipStatsTraffic 11 }

cSipStatsTrafficRegisterOuts OBJECT-TYPE
    SYNTAX Counter
    ACCESS read-only
    STATUS mandatory
    DESCRIPTION
        "This object reflects the total number of REGISTER requests 
         sent by the user agent since system startup."
    REFERENCE
        "RFC 2543, Section 4.2.6"
    ::= { cSipStatsTraffic 12 }

cSipStatsTrafficCometIns OBJECT-TYPE
    SYNTAX Counter
    ACCESS read-only
    STATUS mandatory
    DESCRIPTION
        "This object reflects the total number of COndition MET 
         requests received by the user agent since system startup."
    REFERENCE
        "draft-manyfolks-sip-resource-01.txt, Section 5"
    ::= { cSipStatsTraffic 13 }

cSipStatsTrafficCometOuts OBJECT-TYPE
    SYNTAX Counter
    ACCESS read-only
    STATUS mandatory
    DESCRIPTION
        "This object reflects the total number of COndition MET 
         requests sent by the user agent since system startup."
    REFERENCE
        "draft-manyfolks-sip-resource-01.txt, Section 5"
    ::= { cSipStatsTraffic 14 }

cSipStatsTrafficPrackIns OBJECT-TYPE
    SYNTAX Counter
    ACCESS read-only
    STATUS mandatory
    DESCRIPTION
        "This object reflects the total number of PRovisonal 
         ACKnowledgement requests received by the user agent since system startup."
    REFERENCE
        "draft-ietf-sip-100rel-02.txt"
    ::= { cSipStatsTraffic 15 }

cSipStatsTrafficPrackOuts OBJECT-TYPE
    SYNTAX Counter
    ACCESS read-only
    STATUS mandatory
    DESCRIPTION
        "This object reflects the total number of PRovisonal 
         ACKnowledgement requests sent by the user agent since system startup."
    REFERENCE
        "draft-ietf-sip-100rel-02.txt"
    ::= { cSipStatsTraffic 16 }

cSipStatsTrafficReferIns OBJECT-TYPE
    SYNTAX Counter
    ACCESS read-only
    STATUS mandatory
    DESCRIPTION
        "This object reflects the total number of Refer
         requests received by the user agent since system startup."
    ::= { cSipStatsTraffic 17 }

cSipStatsTrafficReferOuts OBJECT-TYPE
    SYNTAX Counter
    ACCESS read-only
    STATUS mandatory
    DESCRIPTION
        "This object reflects the total number of Refer
         requests sent by the user agent since system startup."
    ::= { cSipStatsTraffic 18 }

cSipStatsTrafficNotifyIns OBJECT-TYPE
    SYNTAX Counter
    ACCESS read-only
    STATUS mandatory
    DESCRIPTION
        "This object reflects the total number of Notify 
         requests received by the user agent since system startup."
    ::= { cSipStatsTraffic 19 }

cSipStatsTrafficNotifyOuts OBJECT-TYPE
    SYNTAX Counter
    ACCESS read-only
    STATUS mandatory
    DESCRIPTION
        "This object reflects the total number of Notify 
         requests sent by the user agent since system startup."
    ::= { cSipStatsTraffic 20 }

cSipStatsTrafficInfoIns OBJECT-TYPE
    SYNTAX Counter
    ACCESS read-only
    STATUS mandatory
    DESCRIPTION
        "This object reflects the total number of Info 
         requests received by the user agent since system startup."
    ::= { cSipStatsTraffic 21 }

cSipStatsTrafficInfoOuts OBJECT-TYPE
    SYNTAX Counter
    ACCESS read-only
    STATUS mandatory
    DESCRIPTION
        "This object reflects the total number of Info 
         requests sent by the user agent since system startup."
    ::= { cSipStatsTraffic 22 }

cSipStatsTrafficSubscribeIns OBJECT-TYPE
    SYNTAX Counter
    ACCESS read-only
    STATUS mandatory
    DESCRIPTION
        "This object reflects the total number of Subscribe
         requests received by the user agent since system startup."
    ::= { cSipStatsTraffic 23 }

cSipStatsTrafficSubscribeOuts OBJECT-TYPE
    SYNTAX Counter
    ACCESS read-only
    STATUS mandatory
    DESCRIPTION
        "This object reflects the total number of Subscribe
         requests sent by the user agent since system startup."
    ::= { cSipStatsTraffic 24 }

cSipStatsTrafficUpdateIns OBJECT-TYPE
    SYNTAX Counter
    ACCESS read-only
    STATUS mandatory
    DESCRIPTION
        "This object reflects the total number of Update
         requests received by the user agent since system startup."
    ::= { cSipStatsTraffic 25 }

cSipStatsTrafficUpdateOuts OBJECT-TYPE
    SYNTAX Counter
    ACCESS read-only
    STATUS mandatory
    DESCRIPTION
        "This object reflects the total number of Update
         requests sent by the user agent since system startup."
    ::= { cSipStatsTraffic 26 }

cSipStatsRetryInvites OBJECT-TYPE
    SYNTAX Counter
    ACCESS read-only
    STATUS mandatory
    DESCRIPTION
        "This object reflects the total number of INVITE retries that 
         have been sent by the user agent since system startup.   If the number of 'first 
         attempt' INVITES is of interest, subtract the value of this 
         object from cSipStatsTrafficInviteOut."
    ::= { cSipStatsRetry 1 }

cSipStatsRetryByes OBJECT-TYPE
    SYNTAX Counter
    ACCESS read-only
    STATUS mandatory
    DESCRIPTION
        "This object reflects the total number of BYE retries that have
         been sent by the user agent since system startup."
    ::= { cSipStatsRetry 2 }

cSipStatsRetryCancels OBJECT-TYPE
    SYNTAX Counter
    ACCESS read-only
    STATUS mandatory
    DESCRIPTION
        "This object reflects the total number of CANCEL retries that 
         have been sent by the user agent since system startup."
    ::= { cSipStatsRetry 3 }

cSipStatsRetryRegisters OBJECT-TYPE
    SYNTAX Counter
    ACCESS read-only
    STATUS mandatory
    DESCRIPTION
        "This object reflects the total number of REGISTER retries that
         have been sent by the user agent since system startup."
    ::= { cSipStatsRetry 4 }

cSipStatsRetryResponses OBJECT-TYPE
    SYNTAX Counter
    ACCESS read-only
    STATUS mandatory
    DESCRIPTION
        "This object reflects the total number of Response (while 
         expecting a ACK) retries that have been sent by the user
         agent."
    ::= { cSipStatsRetry 5 }

cSipStatsRetryPracks OBJECT-TYPE
    SYNTAX Counter
    ACCESS read-only
    STATUS mandatory
    DESCRIPTION
        "This object reflects the total number of PRovisional
         ACKnowledgement retries sent by the user agent since system startup."
    ::= { cSipStatsRetry 6 }

cSipStatsRetryComets OBJECT-TYPE
    SYNTAX Counter
    ACCESS read-only
    STATUS mandatory
    DESCRIPTION
        "This object reflects the total number of COndition
         MET retries sent by the user agent since system startup."
    ::= { cSipStatsRetry 7 }

cSipStatsRetryReliable1xxRsps OBJECT-TYPE
    SYNTAX Counter
    ACCESS read-only
    STATUS mandatory
    DESCRIPTION
        "This object reflects the total number of Reliable
         1xx Response retries sent by the user agent since system startup."
    ::= { cSipStatsRetry 8 }

cSipStatsRetryNotifys OBJECT-TYPE
    SYNTAX Counter
    ACCESS read-only
    STATUS mandatory
    DESCRIPTION
        "This object reflects the total number of Notify 
         retries that have been sent by the user agent since system startup."
    ::= { cSipStatsRetry 9 }

cSipStatsRetryRefers OBJECT-TYPE
    SYNTAX Counter
    ACCESS read-only
    STATUS mandatory
    DESCRIPTION
        "This object reflects the total number of Refer
         retries that have been sent by the user agent since system startup."
    ::= { cSipStatsRetry 10 }

cSipStatsRetryInfo OBJECT-TYPE
    SYNTAX Counter
    ACCESS read-only
    STATUS mandatory
    DESCRIPTION
        "This object reflects the total number of Info
         retries that have been sent by the user agent since system
         startup."
    ::= { cSipStatsRetry 11 }

cSipStatsRetrySubscribe OBJECT-TYPE
    SYNTAX Counter
    ACCESS read-only
    STATUS mandatory
    DESCRIPTION
        "This object reflects the total number of Subscribe
         retries that have been sent by the user agent since system
         startup."
    ::= { cSipStatsRetry 12 }

cSipStatsMisc3xxMappedTo4xxRsps OBJECT-TYPE
    SYNTAX Counter
    ACCESS read-only
    STATUS mandatory
    DESCRIPTION
        "This object reflects the total number of incoming Redirect 
         (3xx) response messages that have been mapped to Client 
         Error (4xx) response messages."
    ::= { cSipStatsMisc 1 }

cSipStatsConnTCPSendFailures OBJECT-TYPE
    SYNTAX Counter
    ACCESS read-only
    STATUS mandatory
    DESCRIPTION
        "This object reflects the total number of TCP send failures
         since system startup."
    ::= { cSipStatsConnection 1 }

cSipStatsConnUDPSendFailures OBJECT-TYPE
    SYNTAX Counter
    ACCESS read-only
    STATUS mandatory
    DESCRIPTION
        "This object reflects the total number of UDP send failures
         since system startup."
    ::= { cSipStatsConnection 2 }

cSipStatsConnTCPRemoteClosures OBJECT-TYPE
    SYNTAX Counter
    ACCESS read-only
    STATUS mandatory
    DESCRIPTION
        "This object reflects the total number of Remote Closures 
         for TCP since system startup."
    ::= { cSipStatsConnection 3 }

cSipStatsConnUDPCreateFailures OBJECT-TYPE
    SYNTAX Counter
    ACCESS read-only
    STATUS mandatory
    DESCRIPTION
        "This object reflects the total number of connection create
         failures for UDP since system startup."
    ::= { cSipStatsConnection 4 }

cSipStatsConnTCPCreateFailures OBJECT-TYPE
    SYNTAX Counter
    ACCESS read-only
    STATUS mandatory
    DESCRIPTION
        "This object reflects the total number of connection create
         failures for TCP since system startup."
    ::= { cSipStatsConnection 5 }

cSipStatsConnUDPInactiveTimeouts OBJECT-TYPE
    SYNTAX Counter
    ACCESS read-only
    STATUS mandatory
    DESCRIPTION
        "This object reflects the total number of UDP connections that 
         timed out due to inactivity since system startup."
    ::= { cSipStatsConnection 6 }

cSipStatsConnTCPInactiveTimeouts OBJECT-TYPE
    SYNTAX Counter
    ACCESS read-only
    STATUS mandatory
    DESCRIPTION
        "This object reflects the total number of TCP connections that
         timed out due to inactivity since system startup."
    ::= { cSipStatsConnection 7 }

cSipStatsActiveUDPConnections OBJECT-TYPE
    SYNTAX Gauge
    ACCESS read-only
    STATUS mandatory
    DESCRIPTION
        "This object reflects the total number of active UDP
         connections since system startup."
    ::= { cSipStatsConnection 8 }

cSipStatsActiveTCPConnections OBJECT-TYPE
    SYNTAX Gauge
    ACCESS read-only
    STATUS mandatory
    DESCRIPTION
        "This object reflects the total number of active TCP
         connections since system startup."
    ::= { cSipStatsConnection 9 }

ciscoSipBaseConfigGroup OBJECT IDENTIFIER ::= { ciscoSipUaMIBGroups 1 }
-- OBJECT-GROUP
--  Status
--    deprecated
--  Descr
--    A collection of objects providing basic SIP User Agent 
--     configuration.
--  objects
--    cSipCfgUserLocationServerAddr, cSipCfgTransport, 
--    cSipCfgVersion

ciscoSipTimerConfigGroup OBJECT IDENTIFIER ::= { ciscoSipUaMIBGroups 2 }
-- OBJECT-GROUP
--  Status
--    deprecated
--  Descr
--    A collection of objects providing basic SIP User Agent
--     timer configuration.
--  objects
--    cSipCfgTimerTrying, cSipCfgTimerExpires, cSipCfgTimerConnect, 
--    cSipCfgTimerDisconnect

ciscoSipRetryConfigGroup OBJECT IDENTIFIER ::= { ciscoSipUaMIBGroups 3 }
-- OBJECT-GROUP
--  Status
--    deprecated
--  Descr
--    A collection of objects providing basic SIP User Agent
--     retry configuration.
--  objects
--    cSipCfgRetryInvite, cSipCfgRetryBye, cSipCfgRetryCancel, 
--    cSipCfgRetryRegister, cSipCfgRetryResponse

ciscoSipStatsInfoStatusCodesGroup OBJECT IDENTIFIER ::= { ciscoSipUaMIBGroups 4 }
-- OBJECT-GROUP
--  Status
--    mandatory
--  Descr
--    A collection of objects providing basic SIP User Agent
--     Informational status code response messages statistics.
--  objects
--    cSipStatsInfoTryingIns, cSipStatsInfoTryingOuts, 
--    cSipStatsInfoRingingIns, cSipStatsInfoRingingOuts, 
--    cSipStatsInfoForwardedIns, cSipStatsInfoForwardedOuts, 
--    cSipStatsInfoQueuedIns, cSipStatsInfoQueuedOuts, 
--    cSipStatsInfoSessionProgIns, cSipStatsInfoSessionProgOuts

ciscoSipStatsSuccessStatusCodesGroup OBJECT IDENTIFIER ::= { ciscoSipUaMIBGroups 5 }
-- OBJECT-GROUP
--  Status
--    deprecated
--  Descr
--    A collection of objects providing basic SIP User Agent
--     Success status code response messages statistics.
--  objects
--    cSipStatsSuccessOkIns, cSipStatsSuccessOkOuts

ciscoSipStatsRedirStatusCodesGroup OBJECT IDENTIFIER ::= { ciscoSipUaMIBGroups 6 }
-- OBJECT-GROUP
--  Status
--    obsolete
--  Descr
--    A collection of objects providing basic SIP User Agent
--     Redirection status code response messages statistics.
--  objects
--    cSipStatsRedirMultipleChoices, cSipStatsRedirMovedPerms, 
--    cSipStatsRedirMovedTemps, cSipStatsRedirSeeOthers, 
--    cSipStatsRedirUseProxys, cSipStatsRedirAltServices

ciscoSipStatsClientStatusCodesGroup OBJECT IDENTIFIER ::= { ciscoSipUaMIBGroups 7 }
-- OBJECT-GROUP
--  Status
--    obsolete
--  Descr
--    A collection of objects providing basic SIP User Agent
--     Client Error status code response messages statistics.
--  objects
--    cSipStatsClientBadRequestIns, cSipStatsClientBadRequestOuts, 
--    cSipStatsClientUnauthorizedIns, 
--    cSipStatsClientUnauthorizedOuts, 
--    cSipStatsClientPaymentReqdIns, cSipStatsClientPaymentReqdOuts, 
--    cSipStatsClientForbiddenIns, cSipStatsClientForbiddenOuts, 
--    cSipStatsClientNotFoundIns, cSipStatsClientNotFoundOuts, 
--    cSipStatsClientMethNotAllowedIns, 
--    cSipStatsClientMethNotAllowedOuts, 
--    cSipStatsClientNotAcceptableIns, 
--    cSipStatsClientNotAcceptableOuts, 
--    cSipStatsClientProxyAuthReqdIns, 
--    cSipStatsClientProxyAuthReqdOuts, 
--    cSipStatsClientReqTimeoutIns, cSipStatsClientReqTimeoutOuts, 
--    cSipStatsClientConflictIns, cSipStatsClientConflictOuts, 
--    cSipStatsClientGoneIns, cSipStatsClientGoneOuts, 
--    cSipStatsClientLengthRequiredIns, 
--    cSipStatsClientLengthRequiredOuts, 
--    cSipStatsClientReqEntTooLargeIns, 
--    cSipStatsClientReqEntTooLargeOuts, 
--    cSipStatsClientReqURITooLargeIns, 
--    cSipStatsClientReqURITooLargeOuts, 
--    cSipStatsClientNoSupMediaTypeIns, 
--    cSipStatsClientNoSupMediaTypeOuts, 
--    cSipStatsClientBadExtensionIns, 
--    cSipStatsClientBadExtensionOuts, 
--    cSipStatsClientTempNotAvailIns, 
--    cSipStatsClientTempNotAvailOuts, 
--    cSipStatsClientCallLegNoExistIns, 
--    cSipStatsClientCallLegNoExistOuts, 
--    cSipStatsClientLoopDetectedIns, 
--    cSipStatsClientLoopDetectedOuts, 
--    cSipStatsClientTooManyHopsIns, cSipStatsClientTooManyHopsOuts, 
--    cSipStatsClientAddrIncompleteIns, 
--    cSipStatsClientAddrIncompleteOuts, 
--    cSipStatsClientAmbiguousIns, cSipStatsClientAmbiguousOuts, 
--    cSipStatsClientBusyHereIns, cSipStatsClientBusyHereOuts

ciscoSipStatsServerStatusCodesGroup OBJECT IDENTIFIER ::= { ciscoSipUaMIBGroups 8 }
-- OBJECT-GROUP
--  Status
--    deprecated
--  Descr
--    A collection of objects providing basic SIP User Agent
--     Server Error status code response messages statistics.
--  objects
--    cSipStatsServerIntErrorIns, cSipStatsServerIntErrorOuts, 
--    cSipStatsServerNotImplementedIns, 
--    cSipStatsServerNotImplementedOuts, 
--    cSipStatsServerBadGatewayIns, cSipStatsServerBadGatewayOuts, 
--    cSipStatsServerServiceUnavailIns, 
--    cSipStatsServerServiceUnavailOuts, 
--    cSipStatsServerGatewayTimeoutIns, 
--    cSipStatsServerGatewayTimeoutOuts, 
--    cSipStatsServerBadSipVersionIns, 
--    cSipStatsServerBadSipVersionOuts

ciscoSipStatsGlobalStatusCodesGroup OBJECT IDENTIFIER ::= { ciscoSipUaMIBGroups 9 }
-- OBJECT-GROUP
--  Status
--    mandatory
--  Descr
--    A collection of objects providing basic SIP User Agent
--     Global Failure status code response messages statistics.
--  objects
--    cSipStatsGlobalBusyEverywhereIns, 
--    cSipStatsGlobalBusyEverywhereOuts, cSipStatsGlobalDeclineIns, 
--    cSipStatsGlobalDeclineOuts, cSipStatsGlobalNotAnywhereIns, 
--    cSipStatsGlobalNotAnywhereOuts, 
--    cSipStatsGlobalNotAcceptableIns, 
--    cSipStatsGlobalNotAcceptableOuts

ciscoSipTrafficStatsGroup OBJECT IDENTIFIER ::= { ciscoSipUaMIBGroups 10 }
-- OBJECT-GROUP
--  Status
--    deprecated
--  Descr
--    A collection of objects providing basic SIP User Agent
--     inbound and outbound traffic statistics.
--  objects
--    cSipStatsTrafficInviteIns, cSipStatsTrafficInviteOuts, 
--    cSipStatsTrafficAckIns, cSipStatsTrafficAckOuts, 
--    cSipStatsTrafficByeIns, cSipStatsTrafficByeOuts, 
--    cSipStatsTrafficCancelIns, cSipStatsTrafficCancelOuts, 
--    cSipStatsTrafficOptionsIns, cSipStatsTrafficOptionsOuts, 
--    cSipStatsTrafficRegisterIns, cSipStatsTrafficRegisterOuts

ciscoSipRetryStatsGroup OBJECT IDENTIFIER ::= { ciscoSipUaMIBGroups 11 }
-- OBJECT-GROUP
--  Status
--    deprecated
--  Descr
--    A collection of objects providing basic SIP User Agent
--     retry statistics.
--  objects
--    cSipStatsRetryInvites, cSipStatsRetryByes, 
--    cSipStatsRetryCancels, cSipStatsRetryRegisters, 
--    cSipStatsRetryResponses

ciscoSipBaseConfigGroupRev1 OBJECT IDENTIFIER ::= { ciscoSipUaMIBGroups 12 }
-- OBJECT-GROUP
--  Status
--    deprecated
--  Descr
--    A collection of objects providing basic SIP User Agent 
--     configuration.
--  objects
--    cSipCfgUserLocationServerAddr, cSipCfgTransport, 
--    cSipCfgVersion, cSipCfgMaxForwards

ciscoSipTimerConfigGroupRev1 OBJECT IDENTIFIER ::= { ciscoSipUaMIBGroups 13 }
-- OBJECT-GROUP
--  Status
--    deprecated
--  Descr
--    A collection of objects providing basic SIP User Agent
--     timer configuration.
--  objects
--    cSipCfgTimerTrying, cSipCfgTimerExpires, cSipCfgTimerConnect, 
--    cSipCfgTimerDisconnect, cSipCfgTimerPrack, cSipCfgTimerComet, 
--    cSipCfgTimerReliableRsp

ciscoSipRetryConfigGroupRev1 OBJECT IDENTIFIER ::= { ciscoSipUaMIBGroups 14 }
-- OBJECT-GROUP
--  Status
--    deprecated
--  Descr
--    A collection of objects providing basic SIP User Agent
--     retry configuration.
--  objects
--    cSipCfgRetryInvite, cSipCfgRetryBye, cSipCfgRetryCancel, 
--    cSipCfgRetryRegister, cSipCfgRetryResponse, cSipCfgRetryPrack, 
--    cSipCfgRetryComet, cSipCfgRetryReliableRsp

ciscoSipTrafficStatsGroupRev1 OBJECT IDENTIFIER ::= { ciscoSipUaMIBGroups 15 }
-- OBJECT-GROUP
--  Status
--    deprecated
--  Descr
--    A collection of objects providing basic SIP User Agent
--     inbound and outbound traffic statistics.
--  objects
--    cSipStatsTrafficInviteIns, cSipStatsTrafficInviteOuts, 
--    cSipStatsTrafficAckIns, cSipStatsTrafficAckOuts, 
--    cSipStatsTrafficByeIns, cSipStatsTrafficByeOuts, 
--    cSipStatsTrafficCancelIns, cSipStatsTrafficCancelOuts, 
--    cSipStatsTrafficOptionsIns, cSipStatsTrafficOptionsOuts, 
--    cSipStatsTrafficRegisterIns, cSipStatsTrafficRegisterOuts, 
--    cSipStatsTrafficCometIns, cSipStatsTrafficCometOuts, 
--    cSipStatsTrafficPrackIns, cSipStatsTrafficPrackOuts

ciscoSipStatsServerStatusCodesGroupRev1 OBJECT IDENTIFIER ::= { ciscoSipUaMIBGroups 16 }
-- OBJECT-GROUP
--  Status
--    mandatory
--  Descr
--    A collection of objects providing basic SIP User Agent
--     Server Error status code response messages statistics.
--  objects
--    cSipStatsServerIntErrorIns, cSipStatsServerIntErrorOuts, 
--    cSipStatsServerNotImplementedIns, 
--    cSipStatsServerNotImplementedOuts, 
--    cSipStatsServerBadGatewayIns, cSipStatsServerBadGatewayOuts, 
--    cSipStatsServerServiceUnavailIns, 
--    cSipStatsServerServiceUnavailOuts, 
--    cSipStatsServerGatewayTimeoutIns, 
--    cSipStatsServerGatewayTimeoutOuts, 
--    cSipStatsServerBadSipVersionIns, 
--    cSipStatsServerBadSipVersionOuts, 
--    cSipStatsServerPrecondFailureIns, 
--    cSipStatsServerPrecondFailureOuts

ciscoSipRetryStatsGroupRev1 OBJECT IDENTIFIER ::= { ciscoSipUaMIBGroups 17 }
-- OBJECT-GROUP
--  Status
--    deprecated
--  Descr
--    A collection of objects providing basic SIP User Agent
--     retry statistics.
--  objects
--    cSipStatsRetryInvites, cSipStatsRetryByes, 
--    cSipStatsRetryCancels, cSipStatsRetryRegisters, 
--    cSipStatsRetryResponses, cSipStatsRetryPracks, 
--    cSipStatsRetryComets, cSipStatsRetryReliable1xxRsps

ciscoSipStatsClientStatusCodesGroupRev1 OBJECT IDENTIFIER ::= { ciscoSipUaMIBGroups 18 }
-- OBJECT-GROUP
--  Status
--    obsolete
--  Descr
--    A collection of objects providing basic SIP User Agent
--     Client Error status code response messages statistics.
--  objects
--    cSipStatsClientBadRequestIns, cSipStatsClientBadRequestOuts, 
--    cSipStatsClientUnauthorizedIns, 
--    cSipStatsClientUnauthorizedOuts, 
--    cSipStatsClientPaymentReqdIns, cSipStatsClientPaymentReqdOuts, 
--    cSipStatsClientForbiddenIns, cSipStatsClientForbiddenOuts, 
--    cSipStatsClientNotFoundIns, cSipStatsClientNotFoundOuts, 
--    cSipStatsClientMethNotAllowedIns, 
--    cSipStatsClientMethNotAllowedOuts, 
--    cSipStatsClientNotAcceptableIns, 
--    cSipStatsClientNotAcceptableOuts, 
--    cSipStatsClientProxyAuthReqdIns, 
--    cSipStatsClientProxyAuthReqdOuts, 
--    cSipStatsClientReqTimeoutIns, cSipStatsClientReqTimeoutOuts, 
--    cSipStatsClientConflictIns, cSipStatsClientConflictOuts, 
--    cSipStatsClientGoneIns, cSipStatsClientGoneOuts, 
--    cSipStatsClientLengthRequiredIns, 
--    cSipStatsClientLengthRequiredOuts, 
--    cSipStatsClientReqEntTooLargeIns, 
--    cSipStatsClientReqEntTooLargeOuts, 
--    cSipStatsClientReqURITooLargeIns, 
--    cSipStatsClientReqURITooLargeOuts, 
--    cSipStatsClientNoSupMediaTypeIns, 
--    cSipStatsClientNoSupMediaTypeOuts, 
--    cSipStatsClientBadExtensionIns, 
--    cSipStatsClientBadExtensionOuts, 
--    cSipStatsClientTempNotAvailIns, 
--    cSipStatsClientTempNotAvailOuts, 
--    cSipStatsClientCallLegNoExistIns, 
--    cSipStatsClientCallLegNoExistOuts, 
--    cSipStatsClientLoopDetectedIns, 
--    cSipStatsClientLoopDetectedOuts, 
--    cSipStatsClientTooManyHopsIns, cSipStatsClientTooManyHopsOuts, 
--    cSipStatsClientAddrIncompleteIns, 
--    cSipStatsClientAddrIncompleteOuts, 
--    cSipStatsClientAmbiguousIns, cSipStatsClientAmbiguousOuts, 
--    cSipStatsClientBusyHereIns, cSipStatsClientBusyHereOuts, 
--    cSipStatsClientReqTermIns, cSipStatsClientReqTermOuts, 
--    cSipStatsClientNoAcceptHereIns, 
--    cSipStatsClientNoAcceptHereOuts

ciscoSipCfgPeerGroup OBJECT IDENTIFIER ::= { ciscoSipUaMIBGroups 19 }
-- OBJECT-GROUP
--  Status
--    deprecated
--  Descr
--    A collection of objects providing SIP related configuration
--     of Dial Peers.
--  objects
--    cSipCfgPeerOutSessionTransport, cSipCfgPeerReliable1xxRspStr, 
--    cSipCfgPeerReliable1xxRspHdr, cSipCfgPeerUrlType, 
--    cSipCfgOutSessionTransport, cSipCfgReliable1xxRspStr, 
--    cSipCfgReliable1xxRspHdr, cSipCfgUrlType

ciscoSipBaseConfigGroupRev2 OBJECT IDENTIFIER ::= { ciscoSipUaMIBGroups 20 }
-- OBJECT-GROUP
--  Status
--    deprecated
--  Descr
--    A collection of objects providing basic SIP User Agent 
--     configuration.
--  objects
--    cSipCfgUserLocationServerAddr, cSipCfgTransport, 
--    cSipCfgVersion, cSipCfgMaxForwards, 
--    cSipCfgBindSrcAddrInterface, cSipCfgBindSrcAddrScope, 
--    cSipCfgDnsSrvQueryStringFormat

ciscoSipStatusCauseMapGroup OBJECT IDENTIFIER ::= { ciscoSipUaMIBGroups 21 }
-- OBJECT-GROUP
--  Status
--    mandatory
--  Descr
--    A collection of objects providing SIP status code to
--     PSTN cause code mapping configuration.
--  objects
--    cSipCfgPstnCause, cSipCfgStatusCauseStoreStatus, 
--    cSipCfgStatusCode, cSipCfgCauseStatusStoreStatus

ciscoSipTrafficStatsGroupRev2 OBJECT IDENTIFIER ::= { ciscoSipUaMIBGroups 22 }
-- OBJECT-GROUP
--  Status
--    deprecated
--  Descr
--    A collection of objects providing basic SIP User Agent
--     inbound and outbound traffic statistics.
--  objects
--    cSipStatsTrafficInviteIns, cSipStatsTrafficInviteOuts, 
--    cSipStatsTrafficAckIns, cSipStatsTrafficAckOuts, 
--    cSipStatsTrafficByeIns, cSipStatsTrafficByeOuts, 
--    cSipStatsTrafficCancelIns, cSipStatsTrafficCancelOuts, 
--    cSipStatsTrafficOptionsIns, cSipStatsTrafficOptionsOuts, 
--    cSipStatsTrafficRegisterIns, cSipStatsTrafficRegisterOuts, 
--    cSipStatsTrafficCometIns, cSipStatsTrafficCometOuts, 
--    cSipStatsTrafficPrackIns, cSipStatsTrafficPrackOuts, 
--    cSipStatsTrafficReferIns, cSipStatsTrafficReferOuts, 
--    cSipStatsTrafficNotifyIns, cSipStatsTrafficNotifyOuts, 
--    cSipStatsTrafficInfoIns, cSipStatsTrafficInfoOuts, 
--    cSipStatsTrafficSubscribeIns, cSipStatsTrafficSubscribeOuts

ciscoSipStatsSuccessStatusCodesGroupRev1 OBJECT IDENTIFIER ::= { ciscoSipUaMIBGroups 23 }
-- OBJECT-GROUP
--  Status
--    deprecated
--  Descr
--    A collection of objects providing basic SIP User Agent
--     Success status code response messages statistics.
--  objects
--    cSipStatsSuccessOkIns, cSipStatsSuccessOkOuts, 
--    cSipStatsSuccessAcceptedIns, cSipStatsSuccessAcceptedOuts

ciscoSipTimerConfigGroupRev2 OBJECT IDENTIFIER ::= { ciscoSipUaMIBGroups 24 }
-- OBJECT-GROUP
--  Status
--    deprecated
--  Descr
--    A collection of objects providing basic SIP User Agent
--     timer configuration.
--  objects
--    cSipCfgTimerTrying, cSipCfgTimerExpires, cSipCfgTimerConnect, 
--    cSipCfgTimerDisconnect, cSipCfgTimerPrack, cSipCfgTimerComet, 
--    cSipCfgTimerReliableRsp, cSipCfgTimerNotify

ciscoSipRetryConfigGroupRev2 OBJECT IDENTIFIER ::= { ciscoSipUaMIBGroups 25 }
-- OBJECT-GROUP
--  Status
--    deprecated
--  Descr
--    A collection of objects providing basic SIP User Agent
--     retry configuration.
--  objects
--    cSipCfgRetryInvite, cSipCfgRetryBye, cSipCfgRetryCancel, 
--    cSipCfgRetryRegister, cSipCfgRetryResponse, cSipCfgRetryPrack, 
--    cSipCfgRetryComet, cSipCfgRetryReliableRsp, 
--    cSipCfgRetryNotify

ciscoSipRetryStatsGroupRev2 OBJECT IDENTIFIER ::= { ciscoSipUaMIBGroups 26 }
-- OBJECT-GROUP
--  Status
--    deprecated
--  Descr
--    A collection of objects providing basic SIP User Agent
--     retry statistics.
--  objects
--    cSipStatsRetryInvites, cSipStatsRetryByes, 
--    cSipStatsRetryCancels, cSipStatsRetryRegisters, 
--    cSipStatsRetryResponses, cSipStatsRetryPracks, 
--    cSipStatsRetryComets, cSipStatsRetryReliable1xxRsps, 
--    cSipStatsRetryNotifys

ciscoSipCfgAaaGroup OBJECT IDENTIFIER ::= { ciscoSipUaMIBGroups 27 }
-- OBJECT-GROUP
--  Status
--    mandatory
--  Descr
--    A collection of objects providing SIP related configuration
--     for AAA.
--  objects
--    cSipCfgAaaUsername

ciscoSipStatsClientStatusCodesGroupRev2 OBJECT IDENTIFIER ::= { ciscoSipUaMIBGroups 28 }
-- OBJECT-GROUP
--  Status
--    deprecated
--  Descr
--    A collection of objects providing basic SIP User Agent
--     Client Error status code response messages statistics.
--  objects
--    cSipStatsClientBadRequestIns, cSipStatsClientBadRequestOuts, 
--    cSipStatsClientUnauthorizedIns, 
--    cSipStatsClientUnauthorizedOuts, 
--    cSipStatsClientPaymentReqdIns, cSipStatsClientPaymentReqdOuts, 
--    cSipStatsClientForbiddenIns, cSipStatsClientForbiddenOuts, 
--    cSipStatsClientNotFoundIns, cSipStatsClientNotFoundOuts, 
--    cSipStatsClientMethNotAllowedIns, 
--    cSipStatsClientMethNotAllowedOuts, 
--    cSipStatsClientNotAcceptableIns, 
--    cSipStatsClientNotAcceptableOuts, 
--    cSipStatsClientProxyAuthReqdIns, 
--    cSipStatsClientProxyAuthReqdOuts, 
--    cSipStatsClientReqTimeoutIns, cSipStatsClientReqTimeoutOuts, 
--    cSipStatsClientConflictIns, cSipStatsClientConflictOuts, 
--    cSipStatsClientGoneIns, cSipStatsClientGoneOuts, 
--    cSipStatsClientReqEntTooLargeIns, 
--    cSipStatsClientReqEntTooLargeOuts, 
--    cSipStatsClientReqURITooLargeIns, 
--    cSipStatsClientReqURITooLargeOuts, 
--    cSipStatsClientNoSupMediaTypeIns, 
--    cSipStatsClientNoSupMediaTypeOuts, 
--    cSipStatsClientBadExtensionIns, 
--    cSipStatsClientBadExtensionOuts, 
--    cSipStatsClientTempNotAvailIns, 
--    cSipStatsClientTempNotAvailOuts, 
--    cSipStatsClientCallLegNoExistIns, 
--    cSipStatsClientCallLegNoExistOuts, 
--    cSipStatsClientLoopDetectedIns, 
--    cSipStatsClientLoopDetectedOuts, 
--    cSipStatsClientTooManyHopsIns, cSipStatsClientTooManyHopsOuts, 
--    cSipStatsClientAddrIncompleteIns, 
--    cSipStatsClientAddrIncompleteOuts, 
--    cSipStatsClientAmbiguousIns, cSipStatsClientAmbiguousOuts, 
--    cSipStatsClientBusyHereIns, cSipStatsClientBusyHereOuts, 
--    cSipStatsClientReqTermIns, cSipStatsClientReqTermOuts, 
--    cSipStatsClientNoAcceptHereIns, 
--    cSipStatsClientNoAcceptHereOuts, cSipStatsClientBadEventIns, 
--    cSipStatsClientBadEventOuts

ciscoSipStatsRedirStatusCodesGroupRev1 OBJECT IDENTIFIER ::= { ciscoSipUaMIBGroups 29 }
-- OBJECT-GROUP
--  Status
--    deprecated
--  Descr
--    A collection of objects providing basic SIP User Agent
--     Redirection status code response messages statistics.
--  objects
--    cSipStatsRedirMultipleChoices, cSipStatsRedirMovedPerms, 
--    cSipStatsRedirMovedTemps, cSipStatsRedirUseProxys, 
--    cSipStatsRedirAltServices

ciscoSipTimerConfigGroupRev3 OBJECT IDENTIFIER ::= { ciscoSipUaMIBGroups 30 }
-- OBJECT-GROUP
--  Status
--    deprecated
--  Descr
--    A collection of objects providing basic SIP User Agent
--     timer configuration.
--  objects
--    cSipCfgTimerTrying, cSipCfgTimerExpires, cSipCfgTimerConnect, 
--    cSipCfgTimerDisconnect, cSipCfgTimerPrack, cSipCfgTimerComet, 
--    cSipCfgTimerReliableRsp, cSipCfgTimerNotify, 
--    cSipCfgTimerRefer

ciscoSipRetryConfigGroupRev3 OBJECT IDENTIFIER ::= { ciscoSipUaMIBGroups 31 }
-- OBJECT-GROUP
--  Status
--    deprecated
--  Descr
--    A collection of objects providing basic SIP User Agent
--     retry configuration.
--  objects
--    cSipCfgRetryInvite, cSipCfgRetryBye, cSipCfgRetryCancel, 
--    cSipCfgRetryRegister, cSipCfgRetryResponse, cSipCfgRetryPrack, 
--    cSipCfgRetryComet, cSipCfgRetryReliableRsp, 
--    cSipCfgRetryNotify, cSipCfgRetryRefer

ciscoSipRetryStatsGroupRev3 OBJECT IDENTIFIER ::= { ciscoSipUaMIBGroups 32 }
-- OBJECT-GROUP
--  Status
--    deprecated
--  Descr
--    A collection of objects providing basic SIP User Agent
--     retry statistics.
--  objects
--    cSipStatsRetryInvites, cSipStatsRetryByes, 
--    cSipStatsRetryCancels, cSipStatsRetryRegisters, 
--    cSipStatsRetryResponses, cSipStatsRetryPracks, 
--    cSipStatsRetryComets, cSipStatsRetryReliable1xxRsps, 
--    cSipStatsRetryNotifys, cSipStatsRetryRefers

ciscoSipStatsSuccessStatusCodesGroupRev2 OBJECT IDENTIFIER ::= { ciscoSipUaMIBGroups 33 }
-- OBJECT-GROUP
--  Status
--    mandatory
--  Descr
--    A collection of objects providing basic SIP User Agent
--     Success status code response messages statistics.
--  objects
--    cSipStatsSuccessAcceptedIns, cSipStatsSuccessAcceptedOuts, 
--    cSipStatsSuccessOkInbounds, cSipStatsSuccessOkOutbounds

ciscoSipBaseConfigGroupRev3 OBJECT IDENTIFIER ::= { ciscoSipUaMIBGroups 34 }
-- OBJECT-GROUP
--  Status
--    mandatory
--  Descr
--    A collection of objects providing basic SIP User Agent 
--     configuration.
--  objects
--    cSipCfgUserLocationServerAddr, cSipCfgTransport, 
--    cSipCfgVersion

ciscoSipStatsClientStatusCodesGroupRev3 OBJECT IDENTIFIER ::= { ciscoSipUaMIBGroups 35 }
-- OBJECT-GROUP
--  Status
--    deprecated
--  Descr
--    A collection of objects providing basic SIP User Agent
--     Client Error status code response messages statistics.
--  objects
--    cSipStatsClientBadRequestIns, cSipStatsClientBadRequestOuts, 
--    cSipStatsClientUnauthorizedIns, 
--    cSipStatsClientUnauthorizedOuts, 
--    cSipStatsClientPaymentReqdIns, cSipStatsClientPaymentReqdOuts, 
--    cSipStatsClientForbiddenIns, cSipStatsClientForbiddenOuts, 
--    cSipStatsClientNotFoundIns, cSipStatsClientNotFoundOuts, 
--    cSipStatsClientMethNotAllowedIns, 
--    cSipStatsClientMethNotAllowedOuts, 
--    cSipStatsClientNotAcceptableIns, 
--    cSipStatsClientNotAcceptableOuts, 
--    cSipStatsClientProxyAuthReqdIns, 
--    cSipStatsClientProxyAuthReqdOuts, 
--    cSipStatsClientReqTimeoutIns, cSipStatsClientReqTimeoutOuts, 
--    cSipStatsClientConflictIns, cSipStatsClientConflictOuts, 
--    cSipStatsClientGoneIns, cSipStatsClientGoneOuts, 
--    cSipStatsClientReqEntTooLargeIns, 
--    cSipStatsClientReqEntTooLargeOuts, 
--    cSipStatsClientReqURITooLargeIns, 
--    cSipStatsClientReqURITooLargeOuts, 
--    cSipStatsClientNoSupMediaTypeIns, 
--    cSipStatsClientNoSupMediaTypeOuts, 
--    cSipStatsClientBadExtensionIns, 
--    cSipStatsClientBadExtensionOuts, 
--    cSipStatsClientTempNotAvailIns, 
--    cSipStatsClientTempNotAvailOuts, 
--    cSipStatsClientCallLegNoExistIns, 
--    cSipStatsClientCallLegNoExistOuts, 
--    cSipStatsClientLoopDetectedIns, 
--    cSipStatsClientLoopDetectedOuts, 
--    cSipStatsClientTooManyHopsIns, cSipStatsClientTooManyHopsOuts, 
--    cSipStatsClientAddrIncompleteIns, 
--    cSipStatsClientAddrIncompleteOuts, 
--    cSipStatsClientAmbiguousIns, cSipStatsClientAmbiguousOuts, 
--    cSipStatsClientBusyHereIns, cSipStatsClientBusyHereOuts, 
--    cSipStatsClientReqTermIns, cSipStatsClientReqTermOuts, 
--    cSipStatsClientNoAcceptHereIns, 
--    cSipStatsClientNoAcceptHereOuts, cSipStatsClientBadEventIns, 
--    cSipStatsClientBadEventOuts, cSipStatsClientSTTooSmallIns, 
--    cSipStatsClientSTTooSmallOuts

ciscoSipStatsMiscGroup OBJECT IDENTIFIER ::= { ciscoSipUaMIBGroups 36 }
-- OBJECT-GROUP
--  Status
--    mandatory
--  Descr
--    A collection of objects providing miscellaneous SIP User 
--     Agent statistics.
--  objects
--    cSipStatsMisc3xxMappedTo4xxRsps

ciscoSipBaseIOSConfigGroup OBJECT IDENTIFIER ::= { ciscoSipUaMIBGroups 37 }
-- OBJECT-GROUP
--  Status
--    deprecated
--  Descr
--    A collection of objects providing basic SIP User Agent 
--     configuration for SIP user agents in IOS.
--  objects
--    cSipCfgMaxForwards, cSipCfgBindSrcAddrInterface, 
--    cSipCfgBindSrcAddrScope, cSipCfgDnsSrvQueryStringFormat, 
--    cSipCfgRedirectionDisabled, cSipCfgTimerSessionTimer, 
--    cSipCfgEarlyMediaCutThruDisabled, cSipCfgSymNatEnabled, 
--    cSipCfgSymNatDirectionRole

ciscoSipTrafficStatsGroupRev3 OBJECT IDENTIFIER ::= { ciscoSipUaMIBGroups 38 }
-- OBJECT-GROUP
--  Status
--    mandatory
--  Descr
--    A collection of objects providing basic SIP User Agent
--     inbound and outbound traffic statistics.
--  objects
--    cSipStatsTrafficInviteIns, cSipStatsTrafficInviteOuts, 
--    cSipStatsTrafficAckIns, cSipStatsTrafficAckOuts, 
--    cSipStatsTrafficByeIns, cSipStatsTrafficByeOuts, 
--    cSipStatsTrafficCancelIns, cSipStatsTrafficCancelOuts, 
--    cSipStatsTrafficOptionsIns, cSipStatsTrafficOptionsOuts, 
--    cSipStatsTrafficRegisterIns, cSipStatsTrafficRegisterOuts, 
--    cSipStatsTrafficCometIns, cSipStatsTrafficCometOuts, 
--    cSipStatsTrafficPrackIns, cSipStatsTrafficPrackOuts, 
--    cSipStatsTrafficReferIns, cSipStatsTrafficReferOuts, 
--    cSipStatsTrafficNotifyIns, cSipStatsTrafficNotifyOuts, 
--    cSipStatsTrafficInfoIns, cSipStatsTrafficInfoOuts, 
--    cSipStatsTrafficSubscribeIns, cSipStatsTrafficSubscribeOuts, 
--    cSipStatsTrafficUpdateIns, cSipStatsTrafficUpdateOuts

ciscoSipStatsRedirStatusCodesGroupRev2 OBJECT IDENTIFIER ::= { ciscoSipUaMIBGroups 39 }
-- OBJECT-GROUP
--  Status
--    mandatory
--  Descr
--    A collection of objects providing basic SIP User Agent
--     Redirection status code response messages statistics.
--  objects
--    cSipStatsRedirMultipleChoices, cSipStatsRedirMovedPerms, 
--    cSipStatsRedirUseProxys, cSipStatsRedirAltServices, 
--    cSipStatsRedirMovedTempsIns, cSipStatsRedirMovedTempsOuts

ciscoSipTimerConfigGroupRev4 OBJECT IDENTIFIER ::= { ciscoSipUaMIBGroups 40 }
-- OBJECT-GROUP
--  Status
--    mandatory
--  Descr
--    A collection of objects providing basic SIP User Agent
--     timer configuration.
--  objects
--    cSipCfgTimerTrying, cSipCfgTimerExpires, cSipCfgTimerConnect, 
--    cSipCfgTimerDisconnect, cSipCfgTimerPrack, cSipCfgTimerComet, 
--    cSipCfgTimerReliableRsp, cSipCfgTimerNotify, 
--    cSipCfgTimerRefer, cSipCfgTimerHold, cSipCfgTimerInfo, 
--    cSipCfgTimerConnectionAging, cSipCfgTimerBufferInvite

ciscoSipRetryStatsGroupRev4 OBJECT IDENTIFIER ::= { ciscoSipUaMIBGroups 41 }
-- OBJECT-GROUP
--  Status
--    mandatory
--  Descr
--    A collection of objects providing basic SIP User Agent
--     retry statistics.
--  objects
--    cSipStatsRetryInvites, cSipStatsRetryByes, 
--    cSipStatsRetryCancels, cSipStatsRetryRegisters, 
--    cSipStatsRetryResponses, cSipStatsRetryPracks, 
--    cSipStatsRetryComets, cSipStatsRetryReliable1xxRsps, 
--    cSipStatsRetryNotifys, cSipStatsRetryRefers, 
--    cSipStatsRetryInfo, cSipStatsRetrySubscribe

ciscoSipBaseIOSConfigGroupRev1 OBJECT IDENTIFIER ::= { ciscoSipUaMIBGroups 42 }
-- OBJECT-GROUP
--  Status
--    mandatory
--  Descr
--    A collection of objects providing basic SIP User Agent 
--     configuration for SIP user agents in IOS.
--  objects
--    cSipCfgMaximumForwards, cSipCfgDnsSrvQueryStringFormat, 
--    cSipCfgRedirectionDisabled, cSipCfgTimerSessionTimer, 
--    cSipCfgEarlyMediaCutThruDisabled, cSipCfgSymNatEnabled, 
--    cSipCfgSymNatDirectionRole, cSipCfgBindSourceAddrInterface, 
--    cSipCfgSuspendResumeEnabled, cSipCfgOfferCallHold, 
--    cSipCfgReasonHeaderOveride

ciscoSipStatsClientStatusCodesGroupRev4 OBJECT IDENTIFIER ::= { ciscoSipUaMIBGroups 43 }
-- OBJECT-GROUP
--  Status
--    mandatory
--  Descr
--    A collection of objects providing basic SIP User Agent
--     Client Error status code response messages statistics.
--  objects
--    cSipStatsClientBadRequestIns, cSipStatsClientBadRequestOuts, 
--    cSipStatsClientUnauthorizedIns, 
--    cSipStatsClientUnauthorizedOuts, 
--    cSipStatsClientPaymentReqdIns, cSipStatsClientPaymentReqdOuts, 
--    cSipStatsClientForbiddenIns, cSipStatsClientForbiddenOuts, 
--    cSipStatsClientNotFoundIns, cSipStatsClientNotFoundOuts, 
--    cSipStatsClientMethNotAllowedIns, 
--    cSipStatsClientMethNotAllowedOuts, 
--    cSipStatsClientNotAcceptableIns, 
--    cSipStatsClientNotAcceptableOuts, 
--    cSipStatsClientProxyAuthReqdIns, 
--    cSipStatsClientProxyAuthReqdOuts, 
--    cSipStatsClientReqTimeoutIns, cSipStatsClientReqTimeoutOuts, 
--    cSipStatsClientConflictIns, cSipStatsClientConflictOuts, 
--    cSipStatsClientGoneIns, cSipStatsClientGoneOuts, 
--    cSipStatsClientReqEntTooLargeIns, 
--    cSipStatsClientReqEntTooLargeOuts, 
--    cSipStatsClientReqURITooLargeIns, 
--    cSipStatsClientReqURITooLargeOuts, 
--    cSipStatsClientNoSupMediaTypeIns, 
--    cSipStatsClientNoSupMediaTypeOuts, 
--    cSipStatsClientBadExtensionIns, 
--    cSipStatsClientBadExtensionOuts, 
--    cSipStatsClientTempNotAvailIns, 
--    cSipStatsClientTempNotAvailOuts, 
--    cSipStatsClientCallLegNoExistIns, 
--    cSipStatsClientCallLegNoExistOuts, 
--    cSipStatsClientLoopDetectedIns, 
--    cSipStatsClientLoopDetectedOuts, 
--    cSipStatsClientTooManyHopsIns, cSipStatsClientTooManyHopsOuts, 
--    cSipStatsClientAddrIncompleteIns, 
--    cSipStatsClientAddrIncompleteOuts, 
--    cSipStatsClientAmbiguousIns, cSipStatsClientAmbiguousOuts, 
--    cSipStatsClientBusyHereIns, cSipStatsClientBusyHereOuts, 
--    cSipStatsClientReqTermIns, cSipStatsClientReqTermOuts, 
--    cSipStatsClientNoAcceptHereIns, 
--    cSipStatsClientNoAcceptHereOuts, cSipStatsClientBadEventIns, 
--    cSipStatsClientBadEventOuts, cSipStatsClientSTTooSmallIns, 
--    cSipStatsClientSTTooSmallOuts, cSipStatsClientReqPendingIns, 
--    cSipStatsClientReqPendingOuts

ciscoSipRetryConfigGroupRev4 OBJECT IDENTIFIER ::= { ciscoSipUaMIBGroups 44 }
-- OBJECT-GROUP
--  Status
--    mandatory
--  Descr
--    A collection of objects providing basic SIP User Agent
--     retry configuration.
--  objects
--    cSipCfgRetryInvite, cSipCfgRetryBye, cSipCfgRetryCancel, 
--    cSipCfgRetryRegister, cSipCfgRetryResponse, cSipCfgRetryPrack, 
--    cSipCfgRetryComet, cSipCfgRetryReliableRsp, 
--    cSipCfgRetryNotify, cSipCfgRetryRefer, cSipCfgRetryInfo, 
--    cSipCfgRetrySubscribe

ciscoSipCfgPeerGroupRev1 OBJECT IDENTIFIER ::= { ciscoSipUaMIBGroups 45 }
-- OBJECT-GROUP
--  Status
--    mandatory
--  Descr
--    A collection of objects providing SIP related configuration
--     of Dial Peers.
--  objects
--    cSipCfgPeerOutSessionTransport, cSipCfgPeerReliable1xxRspStr, 
--    cSipCfgPeerReliable1xxRspHdr, cSipCfgPeerUrlType, 
--    cSipCfgOutSessionTransport, cSipCfgReliable1xxRspStr, 
--    cSipCfgReliable1xxRspHdr, cSipCfgUrlType, 
--    cSipCfgPeerSwitchTransEnabled

ciscoSipCfgVoiceServiceVoipGroup OBJECT IDENTIFIER ::= { ciscoSipUaMIBGroups 46 }
-- OBJECT-GROUP
--  Status
--    mandatory
--  Descr
--    A collection of objects providing SIP related configuration
--     of Voice Service VoIP.
--  objects
--    cSipCfgHeaderPassingEnabled, cSipCfgMaxSubscriptionAccept, 
--    cSipCfgMaxSubscriptionOriginate, 
--    cSipCfgSwitchTransportEnabled

ciscoSipStatsConnectionGroup OBJECT IDENTIFIER ::= { ciscoSipUaMIBGroups 47 }
-- OBJECT-GROUP
--  Status
--    mandatory
--  Descr
--    A collection of objects providing basic SIP User Agent
--     Transport Connection statistics.
--  objects
--    cSipStatsConnTCPSendFailures, cSipStatsConnUDPSendFailures, 
--    cSipStatsConnTCPRemoteClosures, 
--    cSipStatsConnUDPCreateFailures, 
--    cSipStatsConnTCPCreateFailures, 
--    cSipStatsConnUDPInactiveTimeouts, 
--    cSipStatsConnTCPInactiveTimeouts, 
--    cSipStatsActiveUDPConnections, cSipStatsActiveTCPConnections

ciscoSipCompliance OBJECT IDENTIFIER ::= { ciscoSipUaMIBCompliances 1 }
-- MODULE-COMPLIANCE
--  Status
--    obsolete
--  Descr
--    The compliance statement for SIP user agent entities.
--  Module
--    >>current<<
--   MandGroup
--    ciscoSipBaseConfigGroup
--   MandGroup
--    ciscoSipStatsInfoStatusCodesGroup
--   MandGroup
--    ciscoSipStatsSuccessStatusCodesGroup
--   MandGroup
--    ciscoSipStatsGlobalStatusCodesGroup
--   MandGroup
--    ciscoSipTrafficStatsGroup
--   OptGroup
--    ciscoSipTimerConfigGroup
--   OptGroup
--    ciscoSipRetryConfigGroup
--   OptGroup
--    ciscoSipRetryStatsGroup
--   OptGroup
--    ciscoSipStatsRedirStatusCodesGroup
--   OptGroup
--    ciscoSipStatsClientStatusCodesGroup
--   OptGroup
--    ciscoSipStatsServerStatusCodesGroup
--   ObjVar
--    cSipCfgUserLocationServerAddr
--   ObjVar
--    cSipCfgTransport

ciscoSipComplianceRev1 OBJECT IDENTIFIER ::= { ciscoSipUaMIBCompliances 2 }
-- MODULE-COMPLIANCE
--  Status
--    obsolete
--  Descr
--    The compliance statement for SIP user agent entities.
--  Module
--    >>current<<
--   MandGroup
--    ciscoSipBaseConfigGroupRev1
--   MandGroup
--    ciscoSipStatsInfoStatusCodesGroup
--   MandGroup
--    ciscoSipStatsSuccessStatusCodesGroup
--   MandGroup
--    ciscoSipStatsGlobalStatusCodesGroup
--   MandGroup
--    ciscoSipTrafficStatsGroupRev1
--   OptGroup
--    ciscoSipTimerConfigGroupRev1
--   OptGroup
--    ciscoSipRetryConfigGroupRev1
--   OptGroup
--    ciscoSipRetryStatsGroupRev1
--   OptGroup
--    ciscoSipStatsRedirStatusCodesGroup
--   OptGroup
--    ciscoSipStatsClientStatusCodesGroupRev1
--   OptGroup
--    ciscoSipStatsServerStatusCodesGroupRev1
--   ObjVar
--    cSipCfgUserLocationServerAddr
--   ObjVar
--    cSipCfgTransport
--   ObjVar
--    cSipCfgMaxForwards
--   OptGroup
--    ciscoSipCfgPeerGroup

ciscoSipComplianceRev2 OBJECT IDENTIFIER ::= { ciscoSipUaMIBCompliances 3 }
-- MODULE-COMPLIANCE
--  Status
--    deprecated
--  Descr
--    The compliance statement for SIP user agent entities.
--  Module
--    >>current<<
--   MandGroup
--    ciscoSipBaseConfigGroupRev2
--   MandGroup
--    ciscoSipStatsInfoStatusCodesGroup
--   MandGroup
--    ciscoSipStatsSuccessStatusCodesGroupRev1
--   MandGroup
--    ciscoSipStatsGlobalStatusCodesGroup
--   MandGroup
--    ciscoSipTrafficStatsGroupRev2
--   OptGroup
--    ciscoSipTimerConfigGroupRev2
--   OptGroup
--    ciscoSipRetryConfigGroupRev2
--   OptGroup
--    ciscoSipRetryStatsGroupRev2
--   OptGroup
--    ciscoSipStatsRedirStatusCodesGroupRev1
--   OptGroup
--    ciscoSipStatsClientStatusCodesGroupRev2
--   OptGroup
--    ciscoSipStatsServerStatusCodesGroupRev1
--   ObjVar
--    cSipCfgUserLocationServerAddr
--   ObjVar
--    cSipCfgTransport
--   ObjVar
--    cSipCfgMaxForwards
--   OptGroup
--    ciscoSipCfgPeerGroup
--   OptGroup
--    ciscoSipCfgAaaGroup

ciscoSipComplianceRev3 OBJECT IDENTIFIER ::= { ciscoSipUaMIBCompliances 4 }
-- MODULE-COMPLIANCE
--  Status
--    deprecated
--  Descr
--    The compliance statement for SIP user agent entities.
--  Module
--    >>current<<
--   MandGroup
--    ciscoSipBaseConfigGroupRev2
--   MandGroup
--    ciscoSipStatsInfoStatusCodesGroup
--   MandGroup
--    ciscoSipStatsSuccessStatusCodesGroupRev1
--   MandGroup
--    ciscoSipStatsGlobalStatusCodesGroup
--   MandGroup
--    ciscoSipTrafficStatsGroupRev2
--   OptGroup
--    ciscoSipTimerConfigGroupRev3
--   OptGroup
--    ciscoSipRetryConfigGroupRev3
--   OptGroup
--    ciscoSipRetryStatsGroupRev3
--   OptGroup
--    ciscoSipStatsRedirStatusCodesGroupRev1
--   OptGroup
--    ciscoSipStatsClientStatusCodesGroupRev2
--   OptGroup
--    ciscoSipStatsServerStatusCodesGroupRev1
--   ObjVar
--    cSipCfgUserLocationServerAddr
--   ObjVar
--    cSipCfgTransport
--   ObjVar
--    cSipCfgMaxForwards
--   OptGroup
--    ciscoSipCfgPeerGroup
--   OptGroup
--    ciscoSipCfgAaaGroup
--   OptGroup
--    ciscoSipStatusCauseMapGroup

ciscoSipComplianceRev4 OBJECT IDENTIFIER ::= { ciscoSipUaMIBCompliances 5 }
-- MODULE-COMPLIANCE
--  Status
--    deprecated
--  Descr
--    The compliance statement for SIP user agent entities.
--  Module
--    >>current<<
--   MandGroup
--    ciscoSipBaseConfigGroupRev3
--   MandGroup
--    ciscoSipStatsInfoStatusCodesGroup
--   MandGroup
--    ciscoSipStatsSuccessStatusCodesGroupRev2
--   MandGroup
--    ciscoSipStatsGlobalStatusCodesGroup
--   MandGroup
--    ciscoSipTrafficStatsGroupRev2
--   OptGroup
--    ciscoSipTimerConfigGroupRev3
--   OptGroup
--    ciscoSipRetryConfigGroupRev3
--   OptGroup
--    ciscoSipRetryStatsGroupRev3
--   OptGroup
--    ciscoSipStatsRedirStatusCodesGroupRev1
--   OptGroup
--    ciscoSipStatsClientStatusCodesGroupRev3
--   OptGroup
--    ciscoSipStatsServerStatusCodesGroupRev1
--   ObjVar
--    cSipCfgUserLocationServerAddr
--   ObjVar
--    cSipCfgTransport
--   OptGroup
--    ciscoSipCfgPeerGroup
--   OptGroup
--    ciscoSipCfgAaaGroup
--   OptGroup
--    ciscoSipStatusCauseMapGroup
--   OptGroup
--    ciscoSipStatsMiscGroup
--   OptGroup
--    ciscoSipBaseIOSConfigGroup

ciscoSipComplianceRev5 OBJECT IDENTIFIER ::= { ciscoSipUaMIBCompliances 6 }
-- MODULE-COMPLIANCE
--  Status
--    mandatory
--  Descr
--    The compliance statement for SIP user agent entities.
--  Module
--    >>current<<
--   MandGroup
--    ciscoSipBaseConfigGroupRev3
--   MandGroup
--    ciscoSipStatsInfoStatusCodesGroup
--   MandGroup
--    ciscoSipStatsSuccessStatusCodesGroupRev2
--   MandGroup
--    ciscoSipStatsGlobalStatusCodesGroup
--   MandGroup
--    ciscoSipTrafficStatsGroupRev3
--   OptGroup
--    ciscoSipTimerConfigGroupRev4
--   OptGroup
--    ciscoSipRetryConfigGroupRev4
--   OptGroup
--    ciscoSipRetryStatsGroupRev4
--   OptGroup
--    ciscoSipStatsRedirStatusCodesGroupRev2
--   OptGroup
--    ciscoSipStatsClientStatusCodesGroupRev4
--   OptGroup
--    ciscoSipStatsServerStatusCodesGroupRev1
--   ObjVar
--    cSipCfgUserLocationServerAddr
--   ObjVar
--    cSipCfgTransport
--   OptGroup
--    ciscoSipCfgPeerGroupRev1
--   OptGroup
--    ciscoSipCfgAaaGroup
--   OptGroup
--    ciscoSipStatusCauseMapGroup
--   OptGroup
--    ciscoSipStatsMiscGroup
--   OptGroup
--    ciscoSipBaseIOSConfigGroupRev1
--   OptGroup
--    ciscoSipCfgVoiceServiceVoipGroup
--   OptGroup
--    ciscoSipStatsConnectionGroup


END
