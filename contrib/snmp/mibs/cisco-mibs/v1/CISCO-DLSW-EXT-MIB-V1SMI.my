-- MIB created 6/25/99 12:57:08, by
--   SMIC (the next generation) version 1.6.29, November 22, 1994.

CISCO-DLSW-EXT-MIB DEFINITIONS ::= BEGIN

-- From file: "CISCO-DLSW-EXT-MIB.my"

IMPORTS
    TimeTicks
            FROM SNMPv2-SMI-v1
    OBJECT-TYPE
            FROM RFC-1212
    TRAP-TYPE
            FROM RFC-1215
    TruthValue, DisplayString
            FROM SNMPv2-TC-v1
    InterfaceIndex, ifIndex
            FROM IF-MIB
    dlswTConnConfigEntry, dlswTConnOperEntry, 
    dlswTConnTcpConfigEntry, dlswIfEntry, dlswCircuitEntry, 
    dlswTConnConfigIndex, DlcType, TAddress, MacAddressNC, LFSize, 
    dlswTConnOperState, dlswCircuitState, dlswTConnOperTDomain,
    dlswTConnOperRemoteTAddr,dlswCircuitS1Mac, dlswCircuitS1Sap,
    dlswCircuitS2Mac, dlswCircuitS2Sap
            FROM DLSW-MIB
    DlciNumber
            FROM CISCO-FRAME-RELAY-MIB
    SAPType
            FROM CISCO-TC
    ciscoMgmt
            FROM CISCO-SMI;

ciscoDlswExtMIB OBJECT IDENTIFIER ::= { ciscoMgmt 74 }
-- MODULE-IDENTITY
--  LastUpdated
--    9703110000Z
--  OrgName
--    Cisco IBU Engineering Working Group
--  ContactInfo
--           Cisco Systems
--            Customer Service
--    
--    Postal: 170 W. Tasman Drive
--            San Jose, CA 95134
--            USA
--    
--            Tel: +1 800 553-NETS
--    E-mail: cs-dlsw@cisco.com
--  Descr
--    The MIB module for management of Cisco specific Data Link
--    Switching protocol enhancements.  DLSw is described in 
--    RFC 1795 and RFC 2024.
--    
--    DLSw+ Defined
--    
--    Data link switching Plus (DLSw+) is a means of transporting
--    Systems Network Architecture (SNA) and NetBIOS traffic over
--    an IP network. The end systems can attach to the network over
--    Token Ring, Ethernet, Synchronous Data Link Control
--    (SDLC) protocol, or Qualified Logical Link Control (QLLC).
--    DLSw+ switches between diverse media, and locally terminates
--    the data links, keeping acknowledgments, keepalives, and polling
--    off of the WAN. Local termination of data links also
--    eliminates data link control time-outs that can occur during
--    transient network congestion or when rerouting around failed
--    links. Finally, DLSw+ provides a mechanism for dynamically
--    searching a network for SNA or NetBIOS resources and
--    includes caching algorithms that minimize the broadcast traffic
--    required. 
--    
--    In this document, DLSw+ routers are referred to as
--    peers, or partners. The connection between two DLSw+
--    routers is referred to as a peer connection. A DLSw circuit is
--    comprised of the data link control connection between the
--    originating end system and the originating router, the connection
--    between the two routers (typically a TCP connection), and
--    the data link control connection between the target router and
--    the target end system. A single peer connection can carry
--    multiple circuits.
--    
--    The transport connection between DLSw+ routers can vary according
--    to the needs of the network and is not tied to TCP/IP
--    as the DLSw standard is. Cisco supports four different transport
--    protocols between DLSw+ routers:
--    
--    TCP/IP-for transport of SNA and NetBIOS traffic across WANs where
--    local acknowledgment is required to minimize
--    unnecessary traffic and prevent data-link control timeouts and
--    where non-disruptive rerouting around link failures is
--    critical. This transport option is required when DLSw+ is
--    operating in DLSw standards mode. 
--    
--    FST/IP-for transport across WANs with an arbitrary topology and
--    with sufficient bandwidth to accommodate SNA
--    and NetBIOS traffic. This solution allows for rerouting around
--    link failures, but recovery may be disruptive depending
--    on the time required to find an alternate path. This option does
--    not support local acknowledgment of frames. 
--    
--    Direct-encapsulation for transport across a point-to-point or
--    Frame Relay connection where the benefits of an
--    arbitrary topology are not important and where nondisruptive
--    rerouting around link failures is not required. This option
--    does not support local acknowledgment of frames. 
--    
--    DLSw Lite-also known as Logical Link Control, Type2 (LLC2)
--    encapsulation -for transport across a point-to-point
--    connection (currently only Frame Relay is supported) where
--    local acknowledgment and reliable transport are
--    important, but where nondisruptive rerouting around link
--    failures is not required. DLSw Lite uses RFC 1490
--    encapsulation of LLC2.
--  RevDate
--    9703110000Z
--  RevDescr
--    Initial version of this MIB module.

ciscoDlswExtMIBObjects OBJECT IDENTIFIER ::= { ciscoDlswExtMIB 1 }
cdeDomains      OBJECT IDENTIFIER ::= { ciscoDlswExtMIBObjects 1 }
cdeNode         OBJECT IDENTIFIER ::= { ciscoDlswExtMIBObjects 2 }
cdeTConn        OBJECT IDENTIFIER ::= { ciscoDlswExtMIBObjects 3 }
cdeInterface    OBJECT IDENTIFIER ::= { ciscoDlswExtMIBObjects 4 }
cdeCircuit      OBJECT IDENTIFIER ::= { ciscoDlswExtMIBObjects 5 }
cdeFast         OBJECT IDENTIFIER ::= { ciscoDlswExtMIBObjects 6 }
cdeTrapControl  OBJECT IDENTIFIER ::= { ciscoDlswExtMIBObjects 7 }
cdeFSTDomain    OBJECT IDENTIFIER ::= { cdeDomains 1 }
cdeDirectHdlcDomain OBJECT IDENTIFIER ::= { cdeDomains 2 }
cdeDirectFrameRelayDomain OBJECT IDENTIFIER ::= { cdeDomains 3 }
cdeLlc2Domain   OBJECT IDENTIFIER ::= { cdeDomains 4 }
cdeTConnSpecific OBJECT IDENTIFIER ::= { cdeTConn 3 }
cdeTConnTcp     OBJECT IDENTIFIER ::= { cdeTConnSpecific 1 }
cdeTConnDirect  OBJECT IDENTIFIER ::= { cdeTConnSpecific 2 }
cdeTrapsPrefix  OBJECT IDENTIFIER ::= { ciscoDlswExtMIB 2 }
cdeTraps        OBJECT IDENTIFIER ::= { cdeTrapsPrefix 0 }
cdeMIBConformance OBJECT IDENTIFIER ::= { ciscoDlswExtMIB 3 }
cdeMIBCompliances OBJECT IDENTIFIER ::= { cdeMIBConformance 1 }
cdeMIBGroups    OBJECT IDENTIFIER ::= { cdeMIBConformance 2 }

TDomainType ::= INTEGER {
        tcp(1),
        fst(2),
        directHdlc(3),
        directFrameRelay(4),
        llc2(5)
        }
-- TEXTUAL-CONVENTION
--  Status
--    mandatory
--  Descr
--    The type of DLSw encapsulation in use on this peer connection.

Cost ::= INTEGER(1..5)
-- TEXTUAL-CONVENTION
--  Status
--    mandatory
--  Descr
--    Allows a cost to be assigned to a peer.  
--     If an end station can be reached through more
--     than one peer, the cost of each peer will be considered when
--     a circuit is established.
--     A lower cost indicates that peer will be the
--     preferred choice if there is more than one path to the
--     destination.

KeepaliveInterval ::= INTEGER(0..1200)
-- TEXTUAL-CONVENTION
--  Status
--    mandatory
--  Descr
--    The keepalive parameter refers to how often DLSw peers
--     send peer keep alives to each other.  These periodic messages
--     allow DLSw to keep track of the state of all peers.
--     The keepalive interval is measured in seconds.
--     If set to zero, no keepalives are sent.

TCPQueueMax ::= INTEGER(25..2000)
-- TEXTUAL-CONVENTION
--  Status
--    mandatory
--  Descr
--    For DLSw over TCP encapsulation, packets may be queued
--     due to congestion of the TCP network.  The TCPQueueMax
--     is used to set the output queue maximum of the underlying
--     TCP connection.

cdeNodeTAddr OBJECT-TYPE
    SYNTAX TAddress
--    Rsyntax OCTET STRING(SIZE(0..255))
    ACCESS read-write
    STATUS mandatory
    DESCRIPTION
        "The local peer IP address; required for Fast-Sequenced
         Transport (FST) and TCP.  If no local peer IP address
         is configured then this object will be the empty string."
    DEFVAL { ''h }
    ::= { cdeNode 1 }

cdeNodeGroup OBJECT-TYPE
    SYNTAX INTEGER(0..255)
    ACCESS read-write
    STATUS mandatory
    DESCRIPTION
        "Peer group number for this router.
         Peer groups are arbitrary groups of routers with one or
         more designated border peers.  Border peers form peer
         connections with every router in their group and with
         border peers in other groups. The role of a border peer
         is to forward explorers on behalf of other routers. 
         A value of zero means no group has been set and the
         DLSw is not a group member."
    DEFVAL { 0 }
    ::= { cdeNode 2 }

cdeNodeBorder OBJECT-TYPE
    SYNTAX TruthValue
--    Rsyntax INTEGER {
--        true(1),
--        false(2)
--        }
    ACCESS read-write
    STATUS mandatory
    DESCRIPTION
        "This variable indicates if this DLSw is capable of
         operating as a border peer.  True indicates that it is
         capable, false indicates that it is not.
        
         Border peers form peer connections with every router in
         their group and with border peers in other groups. The
         role of a border peer is to forward explorers on behalf
         of other DLSw routers."
    DEFVAL { false }
    ::= { cdeNode 3 }

cdeNodeCost OBJECT-TYPE
    SYNTAX Cost
--    Rsyntax INTEGER(1..5)
    ACCESS read-write
    STATUS mandatory
    DESCRIPTION
        "Peer cost advertised to remote peers in the capabilities
         exchange.  If an end station can be reached through more 
         than one peer, the cost of each peer will be considered when
         a circuit is established.  
         A lower cost indicates that peer will be the 
         preferred choice if there is more than one path to the
         destination.  A value of zero means no cost has been set
         and that cost will not be considered during circuit
         establishment."
    DEFVAL { 3 }
    ::= { cdeNode 4 }

cdeNodeKeepaliveInterval OBJECT-TYPE
    SYNTAX KeepaliveInterval
--    Rsyntax INTEGER(0..1200)
--  Units
--    Seconds
    ACCESS read-write
    STATUS mandatory
    DESCRIPTION
        "Default remote peer keepalive interval in seconds.
         The keepalive parameter refers to how often DLSw peers
         send peer keep alives to each other.  These periodic messages 
         allow DLSw to keep track of the state of all peers.
         If set to zero, no keepalives are sent."
    DEFVAL { 30 }
    ::= { cdeNode 5 }

cdeNodePassiveConnect OBJECT-TYPE
    SYNTAX TruthValue
--    Rsyntax INTEGER {
--        true(1),
--        false(2)
--        }
    ACCESS read-write
    STATUS mandatory
    DESCRIPTION
        "This variable indicates if DLSw will not initiate
         remote peer connections to configured peers.  True
         indicates that it will not initiate remote peer connections,
         false indicates that it will initiate remote peer connections.
         In other words a passive peer will wait for the remote peer
         to initiate a peer connection"
    DEFVAL { false }
    ::= { cdeNode 6 }

cdeNodeBiuSegment OBJECT-TYPE
    SYNTAX TruthValue
--    Rsyntax INTEGER {
--        true(1),
--        false(2)
--        }
    ACCESS read-write
    STATUS mandatory
    DESCRIPTION
        "This variable indicates if DLSw will spoof the maximum
         receivable Basic Information Unit (frame) size in XID so that
         each end station sends the largest frame it can.  True indicates
         that it will spoof, false indicates that it will not."
    DEFVAL { false }
    ::= { cdeNode 7 }

cdeNodeInitPacingWindow OBJECT-TYPE
    SYNTAX INTEGER(1..2000)
--  Units
--    packets
    ACCESS read-write
    STATUS mandatory
    DESCRIPTION
        "Initial pacing window size.  This is the starting size of the
         pacing window.  DLSw uses an adaptive pacing
         flow control algorithm that automatically adjusts to congestion
         levels in the network.  Pacing windows are used to control
         how many packets may be sent to a peer before acknowlegement."
    DEFVAL { 20 }
    ::= { cdeNode 8 }

cdeNodeMaxPacingWindow OBJECT-TYPE
    SYNTAX INTEGER(1..2000)
--  Units
--    packets
    ACCESS read-write
    STATUS mandatory
    DESCRIPTION
        "Maximum pacing window size.  This is the largest size that
         the pacing window will grow to.  DLSw uses an adaptive pacing
         flow control algorithm that automatically adjusts to congestion
         levels in the network.  Pacing windows are used to control
         how many packets may be sent to a peer before acknowlegement."
    DEFVAL { 50 }
    ::= { cdeNode 9 }

cdeNodePromiscuous OBJECT-TYPE
    SYNTAX TruthValue
--    Rsyntax INTEGER {
--        true(1),
--        false(2)
--        }
    ACCESS read-write
    STATUS mandatory
    DESCRIPTION
        "This variable indicates if DLSw will accept connections from
         non-configured remote peers.  Promiscuous routers will
         accept peer connection requests from routers that are
         not preconfigured.  This feature allows central site routers
         to remain unchanged when branch offices are added or deleted.
         It also minimizes required coordination of configurations.
         True indicates that it will accept connections,
         false indicates that it will not."
    DEFVAL { false }
    ::= { cdeNode 10 }

cdeNodePromPeerDefaultsCost OBJECT-TYPE
    SYNTAX Cost
--    Rsyntax INTEGER(1..5)
    ACCESS read-write
    STATUS mandatory
    DESCRIPTION
        "This variable indicates the cost that will be used with
         promiscuous peers.
         If an end station can be reached through more
         than one peer, the cost of each peer will be considered when
         a circuit is established.
         A lower cost indicates that peer will be the
         preferred choice if there is more than one path to the
         destination."
    DEFVAL { 3 }
    ::= { cdeNode 11 }

cdeNodePromPeerDefaultsDestMac OBJECT-TYPE
    SYNTAX MacAddressNC
--    Rsyntax OCTET STRING(SIZE(0 | 6))
    ACCESS read-write
    STATUS mandatory
    DESCRIPTION
        "Permits the promiscuous peer connection to be established
         only when there is an explorer frame destined for the
         specified 48-bit MAC address.  If no default destination mac 
         is configured then this object will be the empty string."
    DEFVAL { ''h }
    ::= { cdeNode 12 }

cdeNodePromPeerDefaultsKeepaliveInterval OBJECT-TYPE
    SYNTAX KeepaliveInterval
--    Rsyntax INTEGER(0..1200)
--  Units
--    Seconds
    ACCESS read-write
    STATUS mandatory
    DESCRIPTION
        "Default promiscuous peer keepalive interval in seconds.
         The keepalive parameter refers to how often DLSw peers
         send peer keep alives to each other.  These periodic messages
         allow DLSw to keep track of the state of all peers.
         If set to zero, no keepalives are sent."
    DEFVAL { 30 }
    ::= { cdeNode 13 }

cdeNodePromPeerDefaultsLFSize OBJECT-TYPE
    SYNTAX LFSize
--    Rsyntax INTEGER {
--        lfs516(516),
--        lfs635(635),
--        lfs754(754),
--        lfs873(873),
--        lfs993(993),
--        lfs1112(1112),
--        lfs1231(1231),
--        lfs1350(1350),
--        lfs1470(1470),
--        lfs1542(1542),
--        lfs1615(1615),
--        lfs1688(1688),
--        lfs1761(1761),
--        lfs1833(1833),
--        lfs1906(1906),
--        lfs1979(1979),
--        lfs2052(2052),
--        lfs2345(2345),
--        lfs2638(2638),
--        lfs2932(2932),
--        lfs3225(3225),
--        lfs3518(3518),
--        lfs3812(3812),
--        lfs4105(4105),
--        lfs4399(4399),
--        lfs4865(4865),
--        lfs5331(5331),
--        lfs5798(5798),
--        lfs6264(6264),
--        lfs6730(6730),
--        lfs7197(7197),
--        lfs7663(7663),
--        lfs8130(8130),
--        lfs8539(8539),
--        lfs8949(8949),
--        lfs9358(9358),
--        lfs9768(9768),
--        lfs10178(10178),
--        lfs10587(10587),
--        lfs10997(10997),
--        lfs11407(11407),
--        lfs12199(12199),
--        lfs12992(12992),
--        lfs13785(13785),
--        lfs14578(14578),
--        lfs15370(15370),
--        lfs16163(16163),
--        lfs16956(16956),
--        lfs17749(17749),
--        lfs20730(20730),
--        lfs23711(23711),
--        lfs26693(26693),
--        lfs29674(29674),
--        lfs32655(32655),
--        lfs38618(38618),
--        lfs41600(41600),
--        lfs44591(44591),
--        lfs47583(47583),
--        lfs50575(50575),
--        lfs53567(53567),
--        lfs56559(56559),
--        lfs59551(59551),
--        lfs65535(65535)
--        }
--  Units
--    bytes
    ACCESS read-write
    STATUS mandatory
    DESCRIPTION
        "The default Largest Frame Size associated with the
         default promiscuous peer transport connection.
         In other words its the largest size of the INFO field
         (including DLC header, not including any MAC-level or framing
         octets)."
    DEFVAL { lfs17749 }
    ::= { cdeNode 14 }

cdeNodePromPeerDefaultsTCPQueueMax OBJECT-TYPE
    SYNTAX TCPQueueMax
--    Rsyntax INTEGER(25..2000)
--  Units
--    packets
    ACCESS read-write
    STATUS mandatory
    DESCRIPTION
        "Default promiscuous peer maximum output TCP queue size.
         For DLSw over TCP encapsulation, packets may be queued
         due to congestion of the TCP network.  This variable
         is used to set the output queue maximum of the underlying
         TCP connection, by default on a promiscuous
         peer transport connection."
    DEFVAL { 200 }
    ::= { cdeNode 15 }

cdeNodePeerOnDemandDefaultsCost OBJECT-TYPE
    SYNTAX Cost
--    Rsyntax INTEGER(1..5)
    ACCESS read-write
    STATUS mandatory
    DESCRIPTION
        "This variable indicates the cost that will be used with
         peer on demand peers.
         If an end station can be reached through more
         than one peer, the cost of each peer will be considered when
         a circuit is established.
         A lower cost indicates that peer will be the
         preferred choice if there is more than one path to the
         destination."
    DEFVAL { 3 }
    ::= { cdeNode 16 }

cdeNodePeerOnDemandDefaultsFst OBJECT-TYPE
    SYNTAX TruthValue
--    Rsyntax INTEGER {
--        true(1),
--        false(2)
--        }
    ACCESS read-write
    STATUS mandatory
    DESCRIPTION
        "This variable indicates if Fast-Sequenced Transport (FST)
         will be for peer on demand peers.  True indicates that
         FST will be used, false indicates that it will not."
    DEFVAL { false }
    ::= { cdeNode 17 }

cdeNodePeerOnDemandDefaultsInactivityInterval OBJECT-TYPE
    SYNTAX INTEGER(0..1440)
--  Units
--    Minutes
    ACCESS read-write
    STATUS mandatory
    DESCRIPTION
        "This variable indicates the length of time a peer on demand 
         connection can be idle before shutting down this peer
         on demand connection.  If set to zero, the peer on demand 
         connection will not be closed due to inactivity."
    DEFVAL { 10 }
    ::= { cdeNode 18 }

cdeNodePeerOnDemandDefaultsKeepaliveInterval OBJECT-TYPE
    SYNTAX KeepaliveInterval
--    Rsyntax INTEGER(0..1200)
--  Units
--    Seconds
    ACCESS read-write
    STATUS mandatory
    DESCRIPTION
        "Default peer on demand keepalive interval in seconds.
         The keepalive parameter refers to how often DLSw peers
         send peer keep alives to each other.  These periodic messages
         allow DLSw to keep track of the state of all peers.
         If set to zero, no keepalives are sent."
    DEFVAL { 30 }
    ::= { cdeNode 19 }

cdeNodePeerOnDemandDefaultsLFSize OBJECT-TYPE
    SYNTAX LFSize
--    Rsyntax INTEGER {
--        lfs516(516),
--        lfs635(635),
--        lfs754(754),
--        lfs873(873),
--        lfs993(993),
--        lfs1112(1112),
--        lfs1231(1231),
--        lfs1350(1350),
--        lfs1470(1470),
--        lfs1542(1542),
--        lfs1615(1615),
--        lfs1688(1688),
--        lfs1761(1761),
--        lfs1833(1833),
--        lfs1906(1906),
--        lfs1979(1979),
--        lfs2052(2052),
--        lfs2345(2345),
--        lfs2638(2638),
--        lfs2932(2932),
--        lfs3225(3225),
--        lfs3518(3518),
--        lfs3812(3812),
--        lfs4105(4105),
--        lfs4399(4399),
--        lfs4865(4865),
--        lfs5331(5331),
--        lfs5798(5798),
--        lfs6264(6264),
--        lfs6730(6730),
--        lfs7197(7197),
--        lfs7663(7663),
--        lfs8130(8130),
--        lfs8539(8539),
--        lfs8949(8949),
--        lfs9358(9358),
--        lfs9768(9768),
--        lfs10178(10178),
--        lfs10587(10587),
--        lfs10997(10997),
--        lfs11407(11407),
--        lfs12199(12199),
--        lfs12992(12992),
--        lfs13785(13785),
--        lfs14578(14578),
--        lfs15370(15370),
--        lfs16163(16163),
--        lfs16956(16956),
--        lfs17749(17749),
--        lfs20730(20730),
--        lfs23711(23711),
--        lfs26693(26693),
--        lfs29674(29674),
--        lfs32655(32655),
--        lfs38618(38618),
--        lfs41600(41600),
--        lfs44591(44591),
--        lfs47583(47583),
--        lfs50575(50575),
--        lfs53567(53567),
--        lfs56559(56559),
--        lfs59551(59551),
--        lfs65535(65535)
--        }
    ACCESS read-write
    STATUS mandatory
    DESCRIPTION
        "The default Largest Frame Size associated with the
         default peer on demand transport connections.
         In other words its the largest size of the INFO field
         (including DLC header, not including any MAC-level or framing
         octets)."
    DEFVAL { lfs17749 }
    ::= { cdeNode 20 }

cdeNodePeerOnDemandDefaultsPriority OBJECT-TYPE
    SYNTAX TruthValue
--    Rsyntax INTEGER {
--        true(1),
--        false(2)
--        }
    ACCESS read-write
    STATUS mandatory
    DESCRIPTION
        "This variable indicates if circuit prioritization will be used
         for peer-on-demand peers.  True indicates that circuit
         prioritization specified by the dlswCircuitPriority object
         in the DLSW-MIB (RFC 2024) will be used, false indicates that
         there will be no circuit prioritization."
    DEFVAL { false }
    ::= { cdeNode 21 }

cdeNodePeerOnDemandDefaultsTCPQueueMax OBJECT-TYPE
    SYNTAX TCPQueueMax
--    Rsyntax INTEGER(25..2000)
--  Units
--    packets
    ACCESS read-write
    STATUS mandatory
    DESCRIPTION
        "Default peer-on-demand Maximum output TCP queue size.
         For DLSw over TCP encapsulation, packets may be queued
         due to congestion of the TCP network.  This variable
         is used to set the output queue maximum of the underlying
         TCP connection, by default on a peer on demand 
         transport connection."
    DEFVAL { 200 }
    ::= { cdeNode 22 }

cdeTConnConfigTable OBJECT-TYPE
    SYNTAX SEQUENCE OF CdeTConnConfigEntry
    ACCESS not-accessible
    STATUS mandatory
    DESCRIPTION
        "This table defines the peer transport connections
         that will be initiated or accepted by this
         DLSw.  Structure of masks allows wildcard
         definition for a collection of transport
         connections by a conceptual row.  For a
         specific transport connection, there may
         be multiple conceptual rows that match the
         transport address.  The `best' match will be
         the one to determine the characteristics
         of the transport connection.
             
         This table augments dlswTConnConfigTable."
    ::= { cdeTConn 1 }

cdeTConnConfigEntry OBJECT-TYPE
    SYNTAX CdeTConnConfigEntry
    ACCESS not-accessible
    STATUS mandatory
    DESCRIPTION
        "A list of objects that define specific configuration for
         a DLSw peer transport connection."
    INDEX { dlswTConnConfigIndex }
-- Augments dlswTConnConfigEntry FROM DLSW-MIB
    ::= { cdeTConnConfigTable 1 }

CdeTConnConfigEntry ::= SEQUENCE {
    cdeTConnConfigTDomainType TDomainType,
    cdeTConnConfigLocalAck TruthValue,
    cdeTConnConfigCost Cost,
    cdeTConnConfigLFSize LFSize,
    cdeTConnConfigKeepaliveInterval KeepaliveInterval,
    cdeTConnConfigBackup TruthValue,
    cdeTConnConfigBackupTAddr TAddress,
    cdeTConnConfigBackupLinger TruthValue,
    cdeTConnConfigBackupLingerInterval INTEGER,
    cdeTConnConfigPriority TruthValue,
    cdeTConnConfigDestMac MacAddressNC,
    cdeTConnConfigDynamic TruthValue,
    cdeTConnConfigDynamicNoLlc INTEGER,
    cdeTConnConfigDynamicInactivityInterval INTEGER
    }

cdeTConnConfigTDomainType OBJECT-TYPE
    SYNTAX TDomainType
--    Rsyntax INTEGER {
--        tcp(1),
--        fst(2),
--        directHdlc(3),
--        directFrameRelay(4),
--        llc2(5)
--        }
    ACCESS read-write
    STATUS mandatory
    DESCRIPTION
        "The type of DLSw encapsulation in use on this peer connection."
    DEFVAL { tcp }
    ::= { cdeTConnConfigEntry 1 }

cdeTConnConfigLocalAck OBJECT-TYPE
    SYNTAX TruthValue
--    Rsyntax INTEGER {
--        true(1),
--        false(2)
--        }
    ACCESS read-write
    STATUS mandatory
    DESCRIPTION
        "Reflects whether the peer connection is locally acknowledged.
         Locally acknoledgement means terminating the DLC connections
         at the router, eliminating the requirement for link-layer
         acknowledgements and keepalive messages to flow across the
         WAN.  In addition because link-layer frames are acknowledged
         locally, link-layer time-outs should not occur.
        
         In general ciscoDlswTConnConfigLocalAck will be true when the
         domain type is tcp, false when the domain type is fst,
         direct-hdlc, or direct-frame-relay.
        
         Configuring the remote-peer as pass-thru, the remote peer
         will not use local acknowlegement."
    DEFVAL { true }
    ::= { cdeTConnConfigEntry 2 }

cdeTConnConfigCost OBJECT-TYPE
    SYNTAX Cost
--    Rsyntax INTEGER(1..5)
    ACCESS read-write
    STATUS mandatory
    DESCRIPTION
        "The cost associated with the transport connection,
         assigned to this conceptual row representing a peer.
         If an end station can be reached through more
         than one peer, the cost of each peer will be considered when
         a circuit is established.
         A lower cost indicates that peer will be the
         preferred choice if there is more than one path to the
         destination."
    DEFVAL { 3 }
    ::= { cdeTConnConfigEntry 3 }

cdeTConnConfigLFSize OBJECT-TYPE
    SYNTAX LFSize
--    Rsyntax INTEGER {
--        lfs516(516),
--        lfs635(635),
--        lfs754(754),
--        lfs873(873),
--        lfs993(993),
--        lfs1112(1112),
--        lfs1231(1231),
--        lfs1350(1350),
--        lfs1470(1470),
--        lfs1542(1542),
--        lfs1615(1615),
--        lfs1688(1688),
--        lfs1761(1761),
--        lfs1833(1833),
--        lfs1906(1906),
--        lfs1979(1979),
--        lfs2052(2052),
--        lfs2345(2345),
--        lfs2638(2638),
--        lfs2932(2932),
--        lfs3225(3225),
--        lfs3518(3518),
--        lfs3812(3812),
--        lfs4105(4105),
--        lfs4399(4399),
--        lfs4865(4865),
--        lfs5331(5331),
--        lfs5798(5798),
--        lfs6264(6264),
--        lfs6730(6730),
--        lfs7197(7197),
--        lfs7663(7663),
--        lfs8130(8130),
--        lfs8539(8539),
--        lfs8949(8949),
--        lfs9358(9358),
--        lfs9768(9768),
--        lfs10178(10178),
--        lfs10587(10587),
--        lfs10997(10997),
--        lfs11407(11407),
--        lfs12199(12199),
--        lfs12992(12992),
--        lfs13785(13785),
--        lfs14578(14578),
--        lfs15370(15370),
--        lfs16163(16163),
--        lfs16956(16956),
--        lfs17749(17749),
--        lfs20730(20730),
--        lfs23711(23711),
--        lfs26693(26693),
--        lfs29674(29674),
--        lfs32655(32655),
--        lfs38618(38618),
--        lfs41600(41600),
--        lfs44591(44591),
--        lfs47583(47583),
--        lfs50575(50575),
--        lfs53567(53567),
--        lfs56559(56559),
--        lfs59551(59551),
--        lfs65535(65535)
--        }
    ACCESS read-write
    STATUS mandatory
    DESCRIPTION
        "The Largest Frame Size associated with the transport connection.
         In other words its the largest size of the INFO field
         (including DLC header, not including any MAC-level or framing
         octets)."
    DEFVAL { lfs17749 }
    ::= { cdeTConnConfigEntry 4 }

cdeTConnConfigKeepaliveInterval OBJECT-TYPE
    SYNTAX KeepaliveInterval
--    Rsyntax INTEGER(0..1200)
--  Units
--    Seconds
    ACCESS read-write
    STATUS mandatory
    DESCRIPTION
        "The amount of time between keepalive messages on a transport
         connection.
         The keepalive parameter refers to how often DLSw peers
         send peer keep alives to each other.  These periodic messages
         allow DLSw to keep track of the state of all peers.
         If set to zero, no keepalives are sent."
    DEFVAL { 30 }
    ::= { cdeTConnConfigEntry 5 }

cdeTConnConfigBackup OBJECT-TYPE
    SYNTAX TruthValue
--    Rsyntax INTEGER {
--        true(1),
--        false(2)
--        }
    ACCESS read-write
    STATUS mandatory
    DESCRIPTION
        "This variable indicates if this peer is defined
         as a backup to an existing peer.  A backup peer is used
         to provide an alternate path in case an existing peer becomes
         unavailable.  A backup peer will not enter the connected
         state until the primary peer that it backs up becomes
         disconnected.
         True indicates that this conecptual row is a backup peer
         to a pre-existing peer, false indicates this peer is not
         a backup peer."
    DEFVAL { false }
    ::= { cdeTConnConfigEntry 6 }

cdeTConnConfigBackupTAddr OBJECT-TYPE
    SYNTAX TAddress
--    Rsyntax OCTET STRING(SIZE(0..255))
    ACCESS read-write
    STATUS mandatory
    DESCRIPTION
        "The primary peer's IP address that this entry backs up.
         Valid only when ciscoDlswTConnConfigBackup is true."
    DEFVAL { ''h }
    ::= { cdeTConnConfigEntry 7 }

cdeTConnConfigBackupLinger OBJECT-TYPE
    SYNTAX TruthValue
--    Rsyntax INTEGER {
--        true(1),
--        false(2)
--        }
    ACCESS read-write
    STATUS mandatory
    DESCRIPTION
        "This variable indicates whether the backup peer will
         remain connected after the primary peer connection has
         been re-established.
         True indicates that the backup peer will remain connected after
         the primary peer connection has been re-established, for the
         length of time specified in cdeTConnConfigBackupLingerInterval.
         False indicates that the backup peer will remain connected until
         all circuits on the backup peer connection have been disconnected."
    DEFVAL { false }
    ::= { cdeTConnConfigEntry 8 }

cdeTConnConfigBackupLingerInterval OBJECT-TYPE
    SYNTAX INTEGER(0..1440)
--  Units
--    Minutes
    ACCESS read-write
    STATUS mandatory
    DESCRIPTION
        "This variable indicates the length of time the backup peer
         remains connected after the primary peer connection has
         been re-established.  If this variable is zero, the backup peer
         will be disconnected immediately after the primary peer connection
         has been re-established.  If greater than zero the backup will 
         stay connected for the number of minutes indicated by this variable,
         after the primary peer connection has been re-established.
         Note that the linger interval is only used when
         cdeTConnConfigBackupLinger is true."
    DEFVAL { 0 }
    ::= { cdeTConnConfigEntry 9 }

cdeTConnConfigPriority OBJECT-TYPE
    SYNTAX TruthValue
--    Rsyntax INTEGER {
--        true(1),
--        false(2)
--        }
    ACCESS read-write
    STATUS mandatory
    DESCRIPTION
        "Indicator of whether this peer connection supports priority.
         When priority is configured for the remote peer,
         DLSw+ will automatically activate four TCP connections to that
         remote peer (ports 2065, 1981, 1982, and 1983). Priority only
         needs to be configured if you need to prioritize between SNA
         and NetBIOS, or within SNA by LOCADDR or MAC/SAP pair
         (known as SAP prioritization). In addition, this granular packet
         classification is only possible when TCP encapsulation is selected
         for a specific remote peer. By default DLSw+ assigns certain
         traffic to specific TCP ports."
    DEFVAL { false }
    ::= { cdeTConnConfigEntry 10 }

cdeTConnConfigDestMac OBJECT-TYPE
    SYNTAX MacAddressNC
--    Rsyntax OCTET STRING(SIZE(0 | 6))
    ACCESS read-write
    STATUS mandatory
    DESCRIPTION
        "Permits the peer connection to be established only when there is an
         explorer frame destined for the specified 48-bit MAC address.
         
         If no expolorer traffic with a destination address of 
         cdeTConnConfigDestMac is received by DLSw, 
         the peer reprented by this conceptual row will not be connected."
    DEFVAL { ''h }
    ::= { cdeTConnConfigEntry 11 }

cdeTConnConfigDynamic OBJECT-TYPE
    SYNTAX TruthValue
--    Rsyntax INTEGER {
--        true(1),
--        false(2)
--        }
    ACCESS read-write
    STATUS mandatory
    DESCRIPTION
        "Indicates the peer connection is to be established only
         when there is DLSw+ data to send."
    DEFVAL { false }
    ::= { cdeTConnConfigEntry 12 }

cdeTConnConfigDynamicNoLlc OBJECT-TYPE
    SYNTAX INTEGER(1..300)
--  Units
--    Minutes
    ACCESS read-write
    STATUS mandatory
    DESCRIPTION
        "This variable indicates the length of time a dynamic peer
         remains connected after all LLC2 circuits are gone."
    DEFVAL { 5 }
    ::= { cdeTConnConfigEntry 13 }

cdeTConnConfigDynamicInactivityInterval OBJECT-TYPE
    SYNTAX INTEGER(0..300)
--  Units
--    Minutes
    ACCESS read-write
    STATUS mandatory
    DESCRIPTION
        "Indicates the length of time a connection can be idle before
         closing the dynamic peer connection.  If set to zero, the dynamic 
         peer connection will not be closed due to inactivity."
    DEFVAL { 0 }
    ::= { cdeTConnConfigEntry 14 }

cdeTConnOperTable OBJECT-TYPE
    SYNTAX SEQUENCE OF CdeTConnOperEntry
    ACCESS not-accessible
    STATUS mandatory
    DESCRIPTION
        "A list of peer transport connections.
         Each connected peer will create a conceptual row in the table.
         When the peer disconnects, the row will be deleted from the table.
         This table augments dlswTConnOperTable."
    ::= { cdeTConn 2 }

cdeTConnOperEntry OBJECT-TYPE
    SYNTAX CdeTConnOperEntry
    ACCESS not-accessible
    STATUS mandatory
    DESCRIPTION
        "A list of objects that contain spefific operational 
         information for a DLSw peer transport connection."
    INDEX { dlswTConnOperTDomain, dlswTConnOperRemoteTAddr }
-- Augments dlswTConnOperEntry FROM DLSW-MIB
    ::= { cdeTConnOperTable 1 }

CdeTConnOperEntry ::= SEQUENCE {
    cdeTConnOperPartnerCost Cost,
    cdeTConnOperPartnerPriority TruthValue,
    cdeTConnOperPartnerBorderPeer TruthValue,
    cdeTConnOperPartnerGroupNum INTEGER,
    cdeTConnOperTDomainType TDomainType
    }

cdeTConnOperPartnerCost OBJECT-TYPE
    SYNTAX Cost
--    Rsyntax INTEGER(1..5)
    ACCESS read-only
    STATUS mandatory
    DESCRIPTION
        "The partner's cost on this peer connection, as received
         through capabilities exchange.
         If an end station can be reached through more
         than one peer, the cost of each peer will be considered when
         a circuit is established.
         A lower cost indicates that peer will be the
         preferred choice if there is more than one path to the
         destination."
    DEFVAL { 3 }
    ::= { cdeTConnOperEntry 1 }

cdeTConnOperPartnerPriority OBJECT-TYPE
    SYNTAX TruthValue
--    Rsyntax INTEGER {
--        true(1),
--        false(2)
--        }
    ACCESS read-only
    STATUS mandatory
    DESCRIPTION
        "The partner's priority setting on this peer connection,
         as received through capabilities exchange.
         When priority is enabled for the remote peer,
         DLSw+ will automatically activate four TCP connections to that
         remote peer (ports 2065, 1981, 1982, and 1983). Priority only
         needs to be configured if you need to prioritize between SNA
         and NetBIOS, or within SNA by LOCADDR or MAC/SAP pair
         (known as SAP prioritization). In addition, this granular packet
         classification is only possible when TCP encapsulation is selected
         for a specific remote peer. By default DLSw+ assigns certain
         traffic to specific TCP ports."
    ::= { cdeTConnOperEntry 2 }

cdeTConnOperPartnerBorderPeer OBJECT-TYPE
    SYNTAX TruthValue
--    Rsyntax INTEGER {
--        true(1),
--        false(2)
--        }
    ACCESS read-only
    STATUS mandatory
    DESCRIPTION
        "This variable indicates if the partner DLSw is capable of
         operating as a border peer, as received through capabilities
         exchange.  True indicates that it is
         capable, false indicates that it is not.
        
         Border peers form peer connections with every router in
         their group and with border peers in other groups. The
         role of a border peer is to forward explorers on behalf
         of other DLSw routers."
    ::= { cdeTConnOperEntry 3 }

cdeTConnOperPartnerGroupNum OBJECT-TYPE
    SYNTAX INTEGER(0..255)
    ACCESS read-only
    STATUS mandatory
    DESCRIPTION
        "This variable indicates the partner's group number, as
         received through capabilities exchange.
         Peer groups are arbitrary groups of routers with one or
         more designated border peers.  Border peers form peer
         connections with every router in their group and with
         border peers in other groups. The role of a border peer
         is to forward explorers on behalf of other routers.
         A value of zero means no group has been set and the
         DLSw is not a group member."
    ::= { cdeTConnOperEntry 4 }

cdeTConnOperTDomainType OBJECT-TYPE
    SYNTAX TDomainType
--    Rsyntax INTEGER {
--        tcp(1),
--        fst(2),
--        directHdlc(3),
--        directFrameRelay(4),
--        llc2(5)
--        }
    ACCESS read-only
    STATUS mandatory
    DESCRIPTION
        "The type of DLSw encapsulation in use on this peer connection."
    ::= { cdeTConnOperEntry 5 }

cdeTConnTcpConfigTable OBJECT-TYPE
    SYNTAX SEQUENCE OF CdeTConnTcpConfigEntry
    ACCESS not-accessible
    STATUS mandatory
    DESCRIPTION
        "This table defines the TCP transport connections that
         will be either initiated by or accepted by this DSLw.
         It augments the entries in dlswTConnConfigTable whose
         domain is dlswTCPDomain.  In other words for each conceptual row
         in the dlswTConnConfigTable, if the dlswTConnConfigTDomain is
         dlswTCPDomain, that conceptual row will be augmented by this
         table.
        
         dlswTCPDomain, dlswTConnConfigTable, and dlswTConnConfigTDomain
         are all imported from DLSW-MIB (RFC 2024).
        
         This table augments dlswTConnTcpConfigTable."
    ::= { cdeTConnTcp 1 }

cdeTConnTcpConfigEntry OBJECT-TYPE
    SYNTAX CdeTConnTcpConfigEntry
    ACCESS not-accessible
    STATUS mandatory
    DESCRIPTION
        "A list of objects that define spefific configuration for
         a DLSw peer transport connection within the dlswTCPDomain.
         dlswTCPDomain is imported from DLSW-MIB (RFC 2024)."
    INDEX { dlswTConnConfigIndex }
-- Augments dlswTConnTcpConfigEntry FROM DLSW-MIB
    ::= { cdeTConnTcpConfigTable 1 }

CdeTConnTcpConfigEntry ::= SEQUENCE {
    cdeTConnTcpConfigQueueMax TCPQueueMax
    }

cdeTConnTcpConfigQueueMax OBJECT-TYPE
    SYNTAX TCPQueueMax
--    Rsyntax INTEGER(25..2000)
--  Units
--    packets
    ACCESS read-write
    STATUS mandatory
    DESCRIPTION
        "Maximum output TCP queue size for this remote peer.
         For DLSw over TCP encapsulation, packets may be queued
         due to congestion of the TCP network.  This variable
         is used to set the output queue maximum of the underlying
         TCP connection for the peer represented by the conceptual row."
    DEFVAL { 200 }
    ::= { cdeTConnTcpConfigEntry 1 }

cdeTConnDirectConfigTable OBJECT-TYPE
    SYNTAX SEQUENCE OF CdeTConnDirectConfigEntry
    ACCESS not-accessible
    STATUS mandatory
    DESCRIPTION
        "This table contains direct peer media-specific
         configuration information. 
         An entry is maintained for every peer in the 
         cdeTConnConfigTable whose domain is either cdeDirectHdlcDomain,
         cdeDirectFrameRelayDomain, or cdeLlc2Domain.
        
         In other words, for each conceptual row
         in the dlswTConnConfigTable, if the dlswTConnConfigTDomain is
         either cdeDirectHdlcDomain, cdeDirectFrameRelayDomain, or
         cdeLlc2Domain, there will be an entry in this table.
        
         dlswTConnConfigTable, and dlswTConnConfigTDomain
         are imported from DLSW-MIB (RFC 2024)."
    ::= { cdeTConnDirect 1 }

cdeTConnDirectConfigEntry OBJECT-TYPE
    SYNTAX CdeTConnDirectConfigEntry
    ACCESS not-accessible
    STATUS mandatory
    DESCRIPTION
        "Each conceptual row defines parameters that are
         specific to peer transport connections whose domain is
         either cdeDirectHdlcDomain, cdeDirectFrameRelayDomain, or
         cdeLlc2Domain."
    INDEX { dlswTConnConfigIndex }
    ::= { cdeTConnDirectConfigTable 1 }

CdeTConnDirectConfigEntry ::= SEQUENCE {
    cdeTConnDirectConfigIfIndex InterfaceIndex,
    cdeTConnDirectConfigMediaEncap INTEGER,
    cdeTConnDirectConfigFrameRelayDlci DlciNumber
    }

cdeTConnDirectConfigIfIndex OBJECT-TYPE
    SYNTAX InterfaceIndex
--    Rsyntax Integer32
    ACCESS read-write
    STATUS mandatory
    DESCRIPTION
        "The IfEntry index of the local interface,
         on which the direct peer can be reached."
    ::= { cdeTConnDirectConfigEntry 1 }

cdeTConnDirectConfigMediaEncap OBJECT-TYPE
    SYNTAX INTEGER {
        directHdlc(1),
        directFrameRelay(2),
        llc2(3)
        }
    ACCESS read-write
    STATUS mandatory
    DESCRIPTION
        "The type of media encapsulation to be used on this 
         peer connection.  When using DLSw Direct-encapsulation or
         DLSw Lite (Frame Relay) encapsulation, the peer transport
         connection is defined as either directHdlc or directFrameRelay,
         respectively.
        
         Hdlc peer transport encapsulation does not support
         local acknowledgment of frames.
        
         Logical Link Control, Type2 (LLC2) peer transport
         encapsulation -for transport across a point-to-point
         connection (currently only Frame Relay is supported) provides
         local acknowledgment and reliable transport."
    DEFVAL { directHdlc }
    ::= { cdeTConnDirectConfigEntry 2 }

cdeTConnDirectConfigFrameRelayDlci OBJECT-TYPE
    SYNTAX DlciNumber
--    Rsyntax INTEGER(0..1023)
    ACCESS read-write
    STATUS mandatory
    DESCRIPTION
        "The Data Link Connection Identifier for the virtual
         circuit on this interface.  This object will only
         be valid if the value of
         cdeTConnDirectConfigMediaEncap is llc2."
    DEFVAL { 0 }
    ::= { cdeTConnDirectConfigEntry 3 }

cdeIfTable OBJECT-TYPE
    SYNTAX SEQUENCE OF CdeIfEntry
    ACCESS not-accessible
    STATUS mandatory
    DESCRIPTION
        "The list of interfaces on which DLSw is active.
        
         This table augments dlswIfTable."
    ::= { cdeInterface 1 }

cdeIfEntry OBJECT-TYPE
    SYNTAX CdeIfEntry
    ACCESS not-accessible
    STATUS mandatory
    DESCRIPTION
        "Each conceptual row represents an interface."
    INDEX { ifIndex }
-- Augments dlswIfEntry FROM DLSW-MIB
    ::= { cdeIfTable 1 }

CdeIfEntry ::= SEQUENCE {
    cdeIfType DlcType
    }

cdeIfType OBJECT-TYPE
    SYNTAX DlcType
--    Rsyntax INTEGER {
--        other(1),
--        na(2),
--        llc(3),
--        sdlc(4),
--        qllc(5)
--        }
    ACCESS read-only
    STATUS mandatory
    DESCRIPTION
        "The DLC protocol in use on this DLSw interface."
    ::= { cdeIfEntry 1 }

cdeCircuitTable OBJECT-TYPE
    SYNTAX SEQUENCE OF CdeCircuitEntry
    ACCESS not-accessible
    STATUS mandatory
    DESCRIPTION
        "A list of circuits.  Each new circuit will create a conceptual row 
         in the table.
         When the circuit disconnects, the row will be deleted from the table.
         End station 1 (S1) and End station 2 (S2) are used to
         represent the two end stations of the circuit.
         S1 is always an end station which is locally attached.
         S2 may be locally attached or remote.  
        
         This table augments the dlswCircuitTable."
    ::= { cdeCircuit 1 }

cdeCircuitEntry OBJECT-TYPE
    SYNTAX CdeCircuitEntry
    ACCESS not-accessible
    STATUS mandatory
    DESCRIPTION
        "A list of objects that contain specific 
         information for a DLSw circuit."
    INDEX { dlswCircuitS1Mac, dlswCircuitS1Sap, dlswCircuitS2Mac, dlswCircuitS2Sap }
-- Augments dlswCircuitEntry FROM DLSW-MIB
    ::= { cdeCircuitTable 1 }

CdeCircuitEntry ::= SEQUENCE {
    cdeCircuitS1Name DisplayString(SIZE(0..17)),
    cdeCircuitS2Name DisplayString(SIZE(0..17)),
    cdeCircuitS1IdBlock DisplayString(SIZE(0..3)),
    cdeCircuitS1IdNum DisplayString(SIZE(0..5))
    }

cdeCircuitS1Name OBJECT-TYPE
    SYNTAX DisplayString(SIZE(0..17))
--    Rsyntax OCTET STRING(SIZE(0..17))
    ACCESS read-only
    STATUS mandatory
    DESCRIPTION
        "Represents the PU Name of End Station 1 (S1), if available."
    ::= { cdeCircuitEntry 1 }

cdeCircuitS2Name OBJECT-TYPE
    SYNTAX DisplayString(SIZE(0..17))
--    Rsyntax OCTET STRING(SIZE(0..17))
    ACCESS read-only
    STATUS mandatory
    DESCRIPTION
        "Represents the PU Name of End Station 2 (S2), if available."
    ::= { cdeCircuitEntry 2 }

cdeCircuitS1IdBlock OBJECT-TYPE
    SYNTAX DisplayString(SIZE(0..3))
--    Rsyntax OCTET STRING(SIZE(0..3))
    ACCESS read-only
    STATUS mandatory
    DESCRIPTION
        "The block number is the first three digits of the SNA Node id of
         End Station 1 (S1), if available.  These 3 hexadecimal digits
         identify the product."
    ::= { cdeCircuitEntry 3 }

cdeCircuitS1IdNum OBJECT-TYPE
    SYNTAX DisplayString(SIZE(0..5))
--    Rsyntax OCTET STRING(SIZE(0..5))
    ACCESS read-only
    STATUS mandatory
    DESCRIPTION
        "The ID number is the last 5 digits of the SNA Node id of End
         Station 1 (S1), if available.  These 5 hexadecimal digits are
         administratively defined and combined with the 3 digit
         block number form the Node id.  This Node id is used to
         identify the local node and is included in SNA XIDs."
    ::= { cdeCircuitEntry 4 }

cdeFastTable OBJECT-TYPE
    SYNTAX SEQUENCE OF CdeFastEntry
    ACCESS not-accessible
    STATUS mandatory
    DESCRIPTION
        "A table containing fast cache entries.
         The table contains cache information for FST peers or
         direct encapsulation peers (without local acknowledgement enabled).
        
         When using these encapsulation types, a fast-switching
         cache must be built. The first frame between two end
         stations will be process switched, and during this
         process an entry will be made in the fast-switching
         cache so that subsequent frames between those end
         stations may be fast switched.
        
         End station 1 (S1) and End station 2 (S2) are used to
         represent the two end stations of the faat cache entry.
         S1 is always an end station which is locally attached.
         S2 is always an end station which is remote."
    ::= { cdeFast 1 }

cdeFastEntry OBJECT-TYPE
    SYNTAX CdeFastEntry
    ACCESS not-accessible
    STATUS mandatory
    DESCRIPTION
        "A list of objects that define specific information
         for a DLSw fast cache entry."
    INDEX { cdeFastS1Mac, cdeFastS1Sap, cdeFastS2Mac, cdeFastS2Sap }
    ::= { cdeFastTable 1 }

CdeFastEntry ::= SEQUENCE {
    cdeFastS1Mac MacAddressNC,
    cdeFastS1Sap SAPType,
    cdeFastS2Mac MacAddressNC,
    cdeFastS2Sap SAPType,
    cdeFastS1IfIndex InterfaceIndex,
    cdeFastS1RouteInfo OCTET STRING,
    cdeFastS1CacheId OCTET STRING,
    cdeFastS2TDomain OBJECT IDENTIFIER,
    cdeFastS2TAddress TAddress,
    cdeFastS2CacheId OCTET STRING,
    cdeFastOrigin INTEGER,
    cdeFastTimeToLive TimeTicks
    }

cdeFastS1Mac OBJECT-TYPE
    SYNTAX MacAddressNC
--    Rsyntax OCTET STRING(SIZE(0 | 6))
    ACCESS not-accessible
    STATUS mandatory
    DESCRIPTION
        "The MAC Address of End Station 1 (S1) used for this cache entry."
    ::= { cdeFastEntry 1 }

cdeFastS1Sap OBJECT-TYPE
    SYNTAX SAPType
--    Rsyntax Integer32(0..254)
    ACCESS not-accessible
    STATUS mandatory
    DESCRIPTION
        "The SAP at End Station 1 (S1) used for this cache entry."
    ::= { cdeFastEntry 2 }

cdeFastS2Mac OBJECT-TYPE
    SYNTAX MacAddressNC
--    Rsyntax OCTET STRING(SIZE(0 | 6))
    ACCESS not-accessible
    STATUS mandatory
    DESCRIPTION
        "The MAC Address of End Station 2 (S2) used for this cache entry."
    ::= { cdeFastEntry 3 }

cdeFastS2Sap OBJECT-TYPE
    SYNTAX SAPType
--    Rsyntax Integer32(0..254)
    ACCESS not-accessible
    STATUS mandatory
    DESCRIPTION
        "The SAP at End Station 2 (S2) used for this cache entry."
    ::= { cdeFastEntry 4 }

cdeFastS1IfIndex OBJECT-TYPE
    SYNTAX InterfaceIndex
--    Rsyntax Integer32
    ACCESS read-only
    STATUS mandatory
    DESCRIPTION
        "The ifEntry index of the local interface through which S1
         can be reached."
    ::= { cdeFastEntry 5 }

cdeFastS1RouteInfo OBJECT-TYPE
    SYNTAX OCTET STRING(SIZE(0..30))
    ACCESS read-only
    STATUS mandatory
    DESCRIPTION
        "If source-route bridging is in use between the DLSw
         and S1, this is the routing information field
         describing the path between the two devices.
         Otherwise the value will be an OCTET STRING of
         zero length."
    ::= { cdeFastEntry 6 }

cdeFastS1CacheId OBJECT-TYPE
    SYNTAX OCTET STRING(SIZE(8))
    ACCESS read-only
    STATUS mandatory
    DESCRIPTION
        "The Cache ID assigned by this DLSw to this fast cache entry.
         Every Fast cache entry will have a unique id.
         A management station could use this object by periodically
         polling this table, and determine whether the same cache 
         entries were present or absent."
    ::= { cdeFastEntry 7 }

cdeFastS2TDomain OBJECT-TYPE
    SYNTAX OBJECT IDENTIFIER
    ACCESS read-only
    STATUS mandatory
    DESCRIPTION
        "This object contains the transport domain of the peer
         transport protocol that the fast cache entry is running
         over."
    ::= { cdeFastEntry 8 }

cdeFastS2TAddress OBJECT-TYPE
    SYNTAX TAddress
--    Rsyntax OCTET STRING(SIZE(0..255))
    ACCESS read-only
    STATUS mandatory
    DESCRIPTION
        "This object contains the transport address of the partner DLSw."
    ::= { cdeFastEntry 9 }

cdeFastS2CacheId OBJECT-TYPE
    SYNTAX OCTET STRING(SIZE(8))
    ACCESS read-only
    STATUS mandatory
    DESCRIPTION
        "The Cache ID assigned to this fast cache entry by the partner
         DLSw.
         Every Fast cache entry will have a unique id.
         A management station could use this object by periodically
         polling this table, and determine whether the same cache
         entries were present or absent."
    ::= { cdeFastEntry 10 }

cdeFastOrigin OBJECT-TYPE
    SYNTAX INTEGER {
        s1(1),
        s2(2)
        }
    ACCESS read-only
    STATUS mandatory
    DESCRIPTION
        "This object specifies which of the two end stations
         initiated the establishment of this circuit."
    ::= { cdeFastEntry 11 }

cdeFastTimeToLive OBJECT-TYPE
    SYNTAX TimeTicks
--  Units
--    hundredths of a second
    ACCESS read-only
    STATUS mandatory
    DESCRIPTION
        "The amount of time (in hundredths of a second) remaining
         before this fast cache entry will be removed from the table.
         After 5 minutes of inactivity, the fast cache entry will be
         deleted."
    ::= { cdeFastEntry 12 }

cdeTrapCntlTConn OBJECT-TYPE
    SYNTAX TruthValue
--    Rsyntax INTEGER {
--        true(1),
--        false(2)
--        }
    ACCESS read-write
    STATUS mandatory
    DESCRIPTION
        "Indicates whether DLSw is permitted to emit transport
         connection up and down traps.  With the value of `true'
         DLSw will emit traps when connections enter `connected'
         and `disconnected' states.  With the value of `false'
         DLSw will not emit traps when connections enter
         `connected' and `disconnected' states.
         The changes take effect immediately."
    DEFVAL { false }
    ::= { cdeTrapControl 1 }

cdeTrapCntlCircuit OBJECT-TYPE
    SYNTAX TruthValue
--    Rsyntax INTEGER {
--        true(1),
--        false(2)
--        }
    ACCESS read-write
    STATUS mandatory
    DESCRIPTION
        "Indicates whether the DLSw is permitted to generate
         circuit up and down traps.  With the value of `true'
         the DLSw will emit traps when circuits enter `connected'
         and `disconnected' states.  With the value of `false'
         the DLSw will not emit traps when circuits enter
         `connected' and `disconnected' states.
         The changes take effect immediately."
    DEFVAL { false }
    ::= { cdeTrapControl 2 }

cdeTrapTConnUpDown TRAP-TYPE
-- Reverse mappable trap
    ENTERPRISE cdeTrapsPrefix
    VARIABLES {
        dlswTConnOperState }
--  Status
--    mandatory
    DESCRIPTION
        "This trap is sent each time a transport connection
         changes state to `connected' or `disconnected'.
         The emission of this trap
         is controlled by cdeTrapCntlTConn."
    ::= 1

cdeTrapCircuitUpDown TRAP-TYPE
-- Reverse mappable trap
    ENTERPRISE cdeTrapsPrefix
    VARIABLES {
        dlswCircuitState }
--  Status
--    mandatory
    DESCRIPTION
        "This trap is sent each time a circuit changes 
         state to `connected' or `disconnected'.
         the emission of this trap is controlled by
         cdeTrapCntlCircuit."
    ::= 2

cdeMIBNodeGroup OBJECT IDENTIFIER ::= { cdeMIBGroups 1 }
-- OBJECT-GROUP
--  Status
--    mandatory
--  Descr
--    Conformance group for DLSw Node general information.
--  objects
--    cdeNodeTAddr, cdeNodeGroup, cdeNodeBorder, cdeNodeCost, 
--    cdeNodeKeepaliveInterval, cdeNodePassiveConnect, 
--    cdeNodeBiuSegment, cdeNodeInitPacingWindow, 
--    cdeNodeMaxPacingWindow, cdeNodePromiscuous, 
--    cdeNodePromPeerDefaultsCost, cdeNodePromPeerDefaultsDestMac, 
--    cdeNodePromPeerDefaultsKeepaliveInterval, 
--    cdeNodePromPeerDefaultsLFSize, 
--    cdeNodePromPeerDefaultsTCPQueueMax, 
--    cdeNodePeerOnDemandDefaultsCost, 
--    cdeNodePeerOnDemandDefaultsFst, 
--    cdeNodePeerOnDemandDefaultsInactivityInterval, 
--    cdeNodePeerOnDemandDefaultsKeepaliveInterval, 
--    cdeNodePeerOnDemandDefaultsLFSize, 
--    cdeNodePeerOnDemandDefaultsPriority, 
--    cdeNodePeerOnDemandDefaultsTCPQueueMax

cdeMIBTConnConfigGroup OBJECT IDENTIFIER ::= { cdeMIBGroups 2 }
-- OBJECT-GROUP
--  Status
--    mandatory
--  Descr
--    Conformance group for the configuration of
--     transport connections.
--  objects
--    cdeTConnConfigTDomainType, cdeTConnConfigLocalAck, 
--    cdeTConnConfigCost, cdeTConnConfigLFSize, 
--    cdeTConnConfigKeepaliveInterval, cdeTConnConfigBackup, 
--    cdeTConnConfigBackupTAddr, cdeTConnConfigBackupLinger, 
--    cdeTConnConfigBackupLingerInterval, cdeTConnConfigPriority, 
--    cdeTConnConfigDestMac, cdeTConnConfigDynamic, 
--    cdeTConnConfigDynamicNoLlc, 
--    cdeTConnConfigDynamicInactivityInterval

cdeMIBTConnOperGroup OBJECT IDENTIFIER ::= { cdeMIBGroups 3 }
-- OBJECT-GROUP
--  Status
--    mandatory
--  Descr
--    Conformance group for operation information for
--     transport connections.
--  objects
--    cdeTConnOperPartnerCost, cdeTConnOperPartnerPriority, 
--    cdeTConnOperPartnerBorderPeer, cdeTConnOperPartnerGroupNum, 
--    cdeTConnOperTDomainType

cdeMIBTConnTcpConfigGroup OBJECT IDENTIFIER ::= { cdeMIBGroups 4 }
-- OBJECT-GROUP
--  Status
--    mandatory
--  Descr
--    Conformance group for configuration information for
--     transport connections using TCP.
--  objects
--    cdeTConnTcpConfigQueueMax

cdeMIBTConnDirectConfigGroup OBJECT IDENTIFIER ::= { cdeMIBGroups 5 }
-- OBJECT-GROUP
--  Status
--    mandatory
--  Descr
--    Conformance group for configuration information for
--     transport connections using Direct or FST.
--  objects
--    cdeTConnDirectConfigIfIndex, cdeTConnDirectConfigMediaEncap, 
--    cdeTConnDirectConfigFrameRelayDlci

cdeMIBInterfaceGroup OBJECT IDENTIFIER ::= { cdeMIBGroups 6 }
-- OBJECT-GROUP
--  Status
--    mandatory
--  Descr
--    Conformance group for DLSw interfaces.
--  objects
--    cdeIfType

cdeMIBCircuitGroup OBJECT IDENTIFIER ::= { cdeMIBGroups 7 }
-- OBJECT-GROUP
--  Status
--    mandatory
--  Descr
--    Conformance group for DLSw circuits.
--  objects
--    cdeCircuitS1Name, cdeCircuitS2Name, cdeCircuitS1IdBlock, 
--    cdeCircuitS1IdNum

cdeMIBFastGroup OBJECT IDENTIFIER ::= { cdeMIBGroups 8 }
-- OBJECT-GROUP
--  Status
--    mandatory
--  Descr
--    Conformance group for DLSw Fast Cache entries.
--  objects
--    cdeFastS1IfIndex, cdeFastS1RouteInfo, cdeFastS1CacheId, 
--    cdeFastS2TDomain, cdeFastS2TAddress, cdeFastS2CacheId, 
--    cdeFastOrigin, cdeFastTimeToLive

cdeTrapControlGroup OBJECT IDENTIFIER ::= { cdeMIBGroups 9 }
-- OBJECT-GROUP
--  Status
--    mandatory
--  Descr
--    Conformance group for DLSw Trap Control.
--  objects
--    cdeTrapCntlTConn, cdeTrapCntlCircuit

cdeMIBCompliance OBJECT IDENTIFIER ::= { cdeMIBCompliances 1 }
-- MODULE-COMPLIANCE
--  Status
--    mandatory
--  Descr
--    The compliance statement for all Cisco DLSw+
--                   implementations.
--  Module
--    >>current<<
--   MandGroup
--    cdeMIBNodeGroup
--   MandGroup
--    cdeMIBTConnConfigGroup
--   MandGroup
--    cdeMIBTConnOperGroup
--   MandGroup
--    cdeMIBTConnTcpConfigGroup
--   MandGroup
--    cdeMIBTConnDirectConfigGroup
--   MandGroup
--    cdeMIBInterfaceGroup
--   MandGroup
--    cdeMIBCircuitGroup
--   MandGroup
--    cdeMIBFastGroup
--   MandGroup
--    cdeTrapControlGroup
--   ObjVar
--    cdeNodeTAddr
--   ObjVar
--    cdeNodeGroup
--   ObjVar
--    cdeNodeBorder
--   ObjVar
--    cdeNodeCost
--   ObjVar
--    cdeNodeKeepaliveInterval
--   ObjVar
--    cdeNodePassiveConnect
--   ObjVar
--    cdeNodeBiuSegment
--   ObjVar
--    cdeNodeInitPacingWindow
--   ObjVar
--    cdeNodeMaxPacingWindow
--   ObjVar
--    cdeNodePromiscuous
--   ObjVar
--    cdeNodePromPeerDefaultsCost
--   ObjVar
--    cdeNodePromPeerDefaultsDestMac
--   ObjVar
--    cdeNodePromPeerDefaultsKeepaliveInterval
--   ObjVar
--    cdeNodePromPeerDefaultsLFSize
--   ObjVar
--    cdeNodePromPeerDefaultsTCPQueueMax
--   ObjVar
--    cdeNodePeerOnDemandDefaultsCost
--   ObjVar
--    cdeNodePeerOnDemandDefaultsFst
--   ObjVar
--    cdeNodePeerOnDemandDefaultsInactivityInterval
--   ObjVar
--    cdeNodePeerOnDemandDefaultsKeepaliveInterval
--   ObjVar
--    cdeNodePeerOnDemandDefaultsLFSize
--   ObjVar
--    cdeNodePeerOnDemandDefaultsPriority
--   ObjVar
--    cdeNodePeerOnDemandDefaultsTCPQueueMax
--   ObjVar
--    cdeTConnConfigTDomainType
--   ObjVar
--    cdeTConnConfigLocalAck
--   ObjVar
--    cdeTConnConfigCost
--   ObjVar
--    cdeTConnConfigLFSize
--   ObjVar
--    cdeTConnConfigKeepaliveInterval
--   ObjVar
--    cdeTConnConfigBackup
--   ObjVar
--    cdeTConnConfigBackupTAddr
--   ObjVar
--    cdeTConnConfigBackupLinger
--   ObjVar
--    cdeTConnConfigBackupLingerInterval
--   ObjVar
--    cdeTConnConfigPriority
--   ObjVar
--    cdeTConnConfigDestMac
--   ObjVar
--    cdeTConnConfigDynamic
--   ObjVar
--    cdeTConnConfigDynamicNoLlc
--   ObjVar
--    cdeTConnConfigDynamicInactivityInterval
--   ObjVar
--    cdeTConnTcpConfigQueueMax
--   ObjVar
--    cdeTConnDirectConfigIfIndex
--   ObjVar
--    cdeTConnDirectConfigMediaEncap
--   ObjVar
--    cdeTConnDirectConfigFrameRelayDlci
--   ObjVar
--    cdeTrapCntlTConn
--   ObjVar
--    cdeTrapCntlCircuit


END
