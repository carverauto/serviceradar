-- MIB file created 16-Dec-2004 10:43:18, by
--   SMICng version 2.2.11-beta(PRO)(Solaris), January 20, 2001. Enterprise key cisco.com

CISCO-POE-PD-MIB DEFINITIONS ::= BEGIN

-- From file: "CISCO-POE-PD-MIB.my"
-- Compile options "4 7 F H N O W 03 06 0B 0G 0N 0T"

IMPORTS
    SnmpAdminString
            FROM SNMP-FRAMEWORK-MIB
    ciscoMgmt
            FROM CISCO-SMI
    Gauge
            FROM RFC1155-SMI
    OBJECT-TYPE
            FROM RFC-1212;

ciscoPoePdMIB OBJECT IDENTIFIER ::= { ciscoMgmt 414 }
-- MODULE-IDENTITY
--  LastUpdated
--    200405050000Z
--  OrgName
--    Cisco Systems Inc.
--  ContactInfo
--            Cisco Systems,
--             Customer Service
--             Postal: 170 West Tasman Drive
--    San Jose, CA  95134
--    USA
--             Tel: +1 800 553-NETS                 
--    
--     E-mail: cs-poe@cisco.com
--  Descr
--    This MIB is intended for devices powered by 
--    external power sources, in particular Power 
--    Over Ethernet (PoE or formerly called inline 
--    power), to provide power usage configuration 
--    and information for NMS.  For example, PoE 
--    supplies DC power over standard Category 5 
--    unshielded twisted-pair (UTP) cable.  Instead 
--    of requiring wall power, powered devices such 
--    as IP telephones can utilize power provided
--    from power source equipments.  By using Cisco
--    Discovery Protocol (CDP),  powered devices 
--    can negotiated with power source equipment to
--    obtain optimum power supply. 
--      
--     
--                      GLOSSARY
--    
--    Midspan Injector
--        The midspan PSE sends out a signal tone down
--        one of the unused pairs of the standard 
--        Category 5 cable and detects tone on the 
--        other unused pair when the PD loops this tone
--        back to it through a loopback transformer.  
--        Once the midspan PSE detects this tone, it 
--        begins to provide power down the cable using 
--        the unused pairs.  The midspan PSE provide no 
--        physical layer capability. 
--    
--    Powered Device ( PD )
--        These are devices powered by external electrical
--        power sources.  They are, for example, IP 
--        telephones and wireless Access Points or bridges. 
--    
--    Power Source Equipment ( PSE )
--        These are devices supplying electrical power to  
--        other equipments.  They are, for example, inline 
--        power switches and power patch panels.
--  RevDate
--    200405050000Z
--  RevDescr
--    Initial version of this MIB module.

cpoePdMIBNotifications OBJECT IDENTIFIER ::= { ciscoPoePdMIB 0 }
cpoePdMIBObjects OBJECT IDENTIFIER ::= { ciscoPoePdMIB 1 }
cpoePdMIBConformance OBJECT IDENTIFIER ::= { ciscoPoePdMIB 2 }
cpoePdInformation OBJECT IDENTIFIER ::= { cpoePdMIBObjects 1 }
cpoePdMIBCompliances OBJECT IDENTIFIER ::= { cpoePdMIBConformance 1 }
cpoePdMIBGroups OBJECT IDENTIFIER ::= { cpoePdMIBConformance 2 }

CpoePdPowerSourceType ::= INTEGER {
        pending(1),
        acAdaptor(2),
        thirdParty(3),
        classic(4),
        midspan(5),
        cdpNegotiated(6),
        highPowerClassic(7)
        }
-- TEXTUAL-CONVENTION
--  Status
--    mandatory
--  Descr
--    This is the type of power source equipment supplying
--    DC power to the PD.
--        pending   == power source is not yet determined.
--        acAdaptor == power is supplied by an AC adapter
--        thirdParty  == power is supplied by a PSE not 
--                       supporting Cisco CDP 
--        classic   == power is supplied and limited by 
--                     a classic Cisco PSE
--        midspan   == power is supplied by a midspan 
--                     injector
--        cdpNegotiated  == power is negotiated using Cisco
--                          CDP
--        highPowerClassic == power is supplied by Cisco
--                            PSE without negotiation.

cpoePdCurrentPowerLevel OBJECT-TYPE
    SYNTAX Gauge(1..65535)
    ACCESS read-only
    STATUS mandatory
    DESCRIPTION
        "This identifies the currently how much power 
        is consummed by the device at which this agent
        is running.  The level shall be one of the
        cpoePdSupportedPowerLevel in the  
        cpoePdSupportedPowerTable."
    ::= { cpoePdInformation 1 }

cpoePdCurrentPowerSource OBJECT-TYPE
    SYNTAX CpoePdPowerSourceType
--    Rsyntax INTEGER {
--        pending(1),
--        acAdaptor(2),
--        thirdParty(3),
--        classic(4),
--        midspan(5),
--        cdpNegotiated(6),
--        highPowerClassic(7)
--        }
    ACCESS read-only
    STATUS mandatory
    DESCRIPTION
        "This is the current power source type 
        obtained from device power source detection."
    ::= { cpoePdInformation 2 }

cpoePdSupportedPowerLevelTable OBJECT-TYPE
    SYNTAX SEQUENCE OF CpoePdSupportedPowerLevelEntry
    ACCESS not-accessible
    STATUS mandatory
    DESCRIPTION
        "This table shows all the supported electrical
        power consumption levels of this agent and the
        corresponding modes of operation at those power
        levels.  The mode of operation and the device 
        capability changes as the supplied power level
        varies.  The number of supported levels is 
        platform and implementation dependent."
    ::= { cpoePdInformation 3 }

cpoePdSupportedPowerLevelEntry OBJECT-TYPE
    SYNTAX CpoePdSupportedPowerLevelEntry
    ACCESS not-accessible
    STATUS mandatory
    DESCRIPTION
        "Each entry shows a supported power level 
        and the corresponding mode of operation."
    INDEX { cpoePdSupportedPowerLevel }
    ::= { cpoePdSupportedPowerLevelTable 1 }

CpoePdSupportedPowerLevelEntry ::= SEQUENCE {
    cpoePdSupportedPowerLevel Gauge,
    cpoePdSupportedPower Gauge,
    cpoePdSupportedPowerMode SnmpAdminString
    }

cpoePdSupportedPowerLevel OBJECT-TYPE
    SYNTAX Gauge(1..65535)
    ACCESS not-accessible
    STATUS mandatory
    DESCRIPTION
        "This index uniquely identifies the supported 
        power consumption level."
    ::= { cpoePdSupportedPowerLevelEntry 1 }

cpoePdSupportedPower OBJECT-TYPE
    SYNTAX Gauge(1..65535)
--  Units
--    milliwatts
    ACCESS read-only
    STATUS mandatory
    DESCRIPTION
        "This is the electrical power consummed by
        the device operating at this supported power
        consumption level."
    ::= { cpoePdSupportedPowerLevelEntry 2 }

cpoePdSupportedPowerMode OBJECT-TYPE
    SYNTAX SnmpAdminString
--    Rsyntax OCTET STRING(SIZE(0..255))
    ACCESS read-only
    STATUS mandatory
    DESCRIPTION
        "This is a text string describing the mode of
        operation or capability of the device at the
        power consumption level.  For example, the 
        comsumption level and corresponding mode should
        look like these:
            1  'Full power mode'
            2  'Low power mode - dot11radio 0 disabled'
            3  'Low power mode - dot11radio 1 disabled'
            4  'Low power mode - dot11 radios disabled'."
    ::= { cpoePdSupportedPowerLevelEntry 3 }

cpoePdInformationGroup OBJECT IDENTIFIER ::= { cpoePdMIBGroups 1 }
-- OBJECT-GROUP
--  Status
--    mandatory
--  Descr
--    This collection of objects provide information about
--    the supported electrical power level, current power
--    consumption, and mode of operation of this agent.
--  objects
--    cpoePdCurrentPowerLevel, cpoePdCurrentPowerSource, 
--    cpoePdSupportedPower, cpoePdSupportedPowerMode

cpoePdMIBCompliance OBJECT IDENTIFIER ::= { cpoePdMIBCompliances 1 }
-- MODULE-COMPLIANCE
--  Status
--    mandatory
--  Descr
--    The compliance statement for the SNMP entities that
--     implement the ciscoPoePdMIB module.
--  Module
--    >>current<<
--   MandGroup
--    cpoePdInformationGroup


END
