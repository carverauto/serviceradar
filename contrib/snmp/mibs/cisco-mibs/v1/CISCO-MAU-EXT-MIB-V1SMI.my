-- MIB file created 19-Mar-2008 09:04:37, by
--   SMICng version 2.2.11-beta(PRO)(Solaris), January 20, 2001. Enterprise key cisco.com

CISCO-MAU-EXT-MIB DEFINITIONS ::= BEGIN

-- From file: "CISCO-MAU-EXT-MIB.my"
-- Compile options "4 7 F H N O W 03 06 0B 0G 0N 0T"

IMPORTS
    TruthValue
            FROM SNMPv2-TC-v1
    ifJackIndex, ifMauIfIndex, ifMauIndex
            FROM MAU-MIB
    ciscoMgmt
            FROM CISCO-SMI
    OBJECT-TYPE
            FROM RFC-1212;

ciscoMauExtMIB OBJECT IDENTIFIER ::= { ciscoMgmt 398 }
-- MODULE-IDENTITY
--  LastUpdated
--    200803050000Z
--  OrgName
--    Cisco Systems, Inc.
--  ContactInfo
--    Cisco Systems
--    Customer Service
--    
--    Postal: 170 W Tasman Drive
--    San Jose, CA  95134
--    USA
--    
--    Tel: +1 800 553-NETS
--    
--    E-mail: cs-lan-switch-snmp@cisco.com
--  Descr
--    A MIB module for extending the MAU-MIB (RFC 3636)
--    to add objects which provide additional management
--    information about MAU or Jack not available in 
--    MAU-MIB.
--  RevDate
--    200803050000Z
--  RevDescr
--    Added cmExtIfMauTrafficTable
--    Added cmExtIfMauTrafficGroup OBJECT-GROUP
--    Deprecated cmExtMIBCompliance2 MODULE-COMPLIANCE
--    Added cmExtMIBCompliance3 MODULE-COMPLIANCE
--  RevDate
--    200404210000Z
--  RevDescr
--    Initial version of this MIB module.

cmExtMIBNotifs  OBJECT IDENTIFIER ::= { ciscoMauExtMIB 0 }
cmExtMIBObjects OBJECT IDENTIFIER ::= { ciscoMauExtMIB 1 }
cmExtMIBConformance OBJECT IDENTIFIER ::= { ciscoMauExtMIB 2 }
cmExtMauConfig  OBJECT IDENTIFIER ::= { cmExtMIBObjects 1 }
cmExtAutoMdixConfig OBJECT IDENTIFIER ::= { cmExtMIBObjects 2 }
cmExtIfMau      OBJECT IDENTIFIER ::= { cmExtMIBObjects 3 }
cmExtMIBCompliances OBJECT IDENTIFIER ::= { cmExtMIBConformance 1 }
cmExtMIBGroups  OBJECT IDENTIFIER ::= { cmExtMIBConformance 2 }

cmExtJackConfigTable OBJECT-TYPE
    SYNTAX SEQUENCE OF CmExtJackConfigEntry
    ACCESS not-accessible
    STATUS mandatory
    DESCRIPTION
        "This table contains management information about MAUs
        attached to interfaces with managed jacks.  The 
        objects in this table are in addition to the objects
        in the ifJackTable."
    REFERENCE
        "Reference RFC 3636, ifJackTable."
    ::= { cmExtMauConfig 1 }

cmExtJackConfigEntry OBJECT-TYPE
    SYNTAX CmExtJackConfigEntry
    ACCESS not-accessible
    STATUS mandatory
    DESCRIPTION
        "An entry containing additional management information
        for a particular jack."
    REFERENCE
        "Reference RFC 3636, ifJackEntry"
    INDEX { ifMauIfIndex, ifMauIndex, ifJackIndex }
-- Augments ifJackEntry FROM MAU-MIB
    ::= { cmExtJackConfigTable 1 }

CmExtJackConfigEntry ::= SEQUENCE {
    cmExtJackState INTEGER
    }

cmExtJackState OBJECT-TYPE
    SYNTAX INTEGER {
        active(1),
        inactive(2)
        }
    ACCESS read-write
    STATUS mandatory
    DESCRIPTION
        "Indicates the state of a particular jack.
        
        Within a particular MAU, setting this to 'active' on
        a jack which is not the current active jack will 
        deactivate the current active jack. 
        
        Setting the current active jack to 'active' has no 
        effect.
        
        A value of inactive(2) indicates that the jack is
        currently deactiveated.  Setting this to 'inactive' 
        has no effect.  Of all the jacks connected to a MAU,
        at least one must be active at all times."
    ::= { cmExtJackConfigEntry 1 }

cmExtIfAutoMdixConfigTable OBJECT-TYPE
    SYNTAX SEQUENCE OF CmExtIfAutoMdixConfigEntry
    ACCESS not-accessible
    STATUS mandatory
    DESCRIPTION
        "This table contains Auto-MDIX configuration
        information for MAUs attached to interfaces in the
        device. An entry appears in this table for each 
        active Auto-MDIX capable MAU connected to 
        interfaces in the device."
    ::= { cmExtAutoMdixConfig 1 }

cmExtIfAutoMdixConfigEntry OBJECT-TYPE
    SYNTAX CmExtIfAutoMdixConfigEntry
    ACCESS not-accessible
    STATUS mandatory
    DESCRIPTION
        "An entry containing Auto-MDIX configuration
        information for a MAU connected to the interface."
    INDEX { ifMauIfIndex, ifMauIndex }
    ::= { cmExtIfAutoMdixConfigTable 1 }

CmExtIfAutoMdixConfigEntry ::= SEQUENCE {
    cmExtIfAutoMdixEnabled TruthValue
    }

cmExtIfAutoMdixEnabled OBJECT-TYPE
    SYNTAX TruthValue
--    Rsyntax INTEGER {
--        true(1),
--        false(2)
--        }
    ACCESS read-write
    STATUS mandatory
    DESCRIPTION
        "Specifies if Auto-MDIX feature is enabled on
        the MAU."
    ::= { cmExtIfAutoMdixConfigEntry 1 }

cmExtIfMauTrafficTable OBJECT-TYPE
    SYNTAX SEQUENCE OF CmExtIfMauTrafficEntry
    ACCESS not-accessible
    STATUS mandatory
    DESCRIPTION
        "The (conceptual) table that identifies the type of traffic
        carried by the interfaces associated with the MAUs in the device.
        This table is sparse dependant on ifMauTable."
    REFERENCE
        "ifMauTable defined in MAU-MIB [RFC 4836]."
    ::= { cmExtIfMau 1 }

cmExtIfMauTrafficEntry OBJECT-TYPE
    SYNTAX CmExtIfMauTrafficEntry
    ACCESS not-accessible
    STATUS mandatory
    DESCRIPTION
        "An entry (conceptual row) in the cmExtIfMauTrafficEntry. Each
        entry contains the type of traffic carried by the interface
        associated with the MAU identified by the indices."
    REFERENCE
        "ifMauTable defined in MAU-MIB [RFC 4836]."
    INDEX { ifMauIfIndex, ifMauIndex }
    ::= { cmExtIfMauTrafficTable 1 }

CmExtIfMauTrafficEntry ::= SEQUENCE {
    cmExtIfMauTrafficType INTEGER
    }

cmExtIfMauTrafficType OBJECT-TYPE
    SYNTAX INTEGER {
        other(1),
        adminControl(2),
        user(3)
        }
    ACCESS read-only
    STATUS mandatory
    DESCRIPTION
        "This object is used to identify the type of traffic carried
        by the MAU. This object can take the following values
        other(1)        - The traffic type is other than anything
                          defined below
        adminControl(2) - This interface carries administrative
                          and control traffic that is internal to 
                          the device
        user(3)         - This interface carries the user data
                          traffic"
    DEFVAL { user }
    ::= { cmExtIfMauTrafficEntry 1 }

cmExtJackConfigGroup OBJECT IDENTIFIER ::= { cmExtMIBGroups 1 }
-- OBJECT-GROUP
--  Status
--    mandatory
--  Descr
--    A collection of objects providing the configuration
--    information about MAUs attached to interfaces with
--    managed jacks.
--  objects
--    cmExtJackState

cmExtIfAutoMdixConfigGroup OBJECT IDENTIFIER ::= { cmExtMIBGroups 2 }
-- OBJECT-GROUP
--  Status
--    mandatory
--  Descr
--    A collection of objects providing the configuration
--    information of Auto-MDIX feature in the device.
--  objects
--    cmExtIfAutoMdixEnabled

cmExtIfMauTrafficGroup OBJECT IDENTIFIER ::= { cmExtMIBGroups 3 }
-- OBJECT-GROUP
--  Status
--    mandatory
--  Descr
--    Object that provides the type of traffic carried by MAUs in
--    devices having admin or control traffic internal to the device.
--  objects
--    cmExtIfMauTrafficType

cmExtMIBCompliance OBJECT IDENTIFIER ::= { cmExtMIBCompliances 1 }
-- MODULE-COMPLIANCE
--  Status
--    deprecated
--  Descr
--    The compliance statement for entities which implement
--    the Cisco MAU extension MIB.
--  Module
--    >>current<<
--   MandGroup
--    cmExtJackConfigGroup

cmExtMIBCompliance2 OBJECT IDENTIFIER ::= { cmExtMIBCompliances 2 }
-- MODULE-COMPLIANCE
--  Status
--    deprecated
--  Descr
--    The compliance statement for entities which implement
--    the Cisco MAU extension MIB.
--  Module
--    >>current<<
--   OptGroup
--    cmExtJackConfigGroup
--   OptGroup
--    cmExtIfAutoMdixConfigGroup

cmExtMIBCompliance3 OBJECT IDENTIFIER ::= { cmExtMIBCompliances 3 }
-- MODULE-COMPLIANCE
--  Status
--    mandatory
--  Descr
--    The compliance statement for entities which implement
--    the Cisco MAU extension MIB.
--  Module
--    >>current<<
--   OptGroup
--    cmExtJackConfigGroup
--   OptGroup
--    cmExtIfAutoMdixConfigGroup
--   OptGroup
--    cmExtIfMauTrafficGroup


END
