-- MIB file created 12-Sep-2012 13:43:24, by
--   SMICng version 2.2.11-beta(PRO)(Solaris), January 20, 2001. Enterprise key cisco.com

CISCO-INTERFACETOPN-EXT-MIB DEFINITIONS ::= BEGIN

-- From file: "CISCO-INTERFACETOPN-EXT-MIB.my"
-- Compile options "4 7 F H N W 03 06 0B 0G 0N 0T"

IMPORTS
    ciscoMgmt
            FROM CISCO-SMI
    interfaceTopNControlIndex
            FROM INTERFACETOPN-MIB
    VlanIndex
            FROM Q-BRIDGE-MIB
    OBJECT-TYPE
            FROM RFC-1212;

ciscoInterfaceTopNExtMIB OBJECT IDENTIFIER ::= { ciscoMgmt 482 }
-- MODULE-IDENTITY
--  LastUpdated
--    201010190000Z
--  OrgName
--    Cisco Systems, Inc.
--  ContactInfo
--    Cisco Systems
--    Customer Service
--    
--    Postal: 170 W Tasman Drive
--    San Jose, CA  95134
--    USA
--    
--    Tel: +1 800 553-NETS
--    
--    E-mail: cs-lan-switch-snmp@cisco.com
--  Descr
--    This MIB module is an extension to INTERFACETOPN-MIB.
--    It provides additional management information for
--    sorting device interfaces.
--  RevDate
--    201010190000Z
--  RevDescr
--    Add fortyGigaEthernet
--    in citneInterfaceTopNInterfaceType
--  RevDate
--    200801150000Z
--  RevDescr
--    Modified the object descriptions of
--    citneInterfaceTopNCounterType,
--    citneInterfaceTopNInterfaceType 
--    and citneInterfaceTopNVlanNumber.
--  RevDate
--    200603150000Z
--  RevDescr
--    Initial version of this MIB module.

ciscoInterfaceTopNExtMIBNotifs OBJECT IDENTIFIER ::= { ciscoInterfaceTopNExtMIB 0 }
ciscoInterfaceTopNExtMIBObjects OBJECT IDENTIFIER ::= { ciscoInterfaceTopNExtMIB 1 }
ciscoInterfaceTopNExtMIBConform OBJECT IDENTIFIER ::= { ciscoInterfaceTopNExtMIB 2 }
ciscoIfTopNExtMIBCompliances OBJECT IDENTIFIER ::= { ciscoInterfaceTopNExtMIBConform 1 }
ciscoIfTopNExtMIBGroups OBJECT IDENTIFIER ::= { ciscoInterfaceTopNExtMIBConform 2 }

citneInterfaceTopNCaps OBJECT-TYPE
    SYNTAX OCTET STRING(SIZE(1..2))
        -- BITS are:
        --   utilization(0)
        --   bytes(1)
        --   packets(2)
        --   broadcast(3)
        --   multicast(4)
        --   overflow(5)
    ACCESS read-only
    STATUS mandatory
    DESCRIPTION
        "The type of interface counters the system is capable to
        do sorting on, as an extension to the interfaceTopNCaps 
        defined in INTERFACETOPN-MIB. 
        
        utilization --  The interface bandwidth utilization in 
                        32-bit version. The utilization on 
                        ethernet interface is computed in the 
                        following methods:
        
          Ethernet utilization: (for full duplex interface, 
                                 divide by 2)
        
          10 Mbps         I/O-pkts * (9.6 + 6.4) + (0.8 * I/O-Bytes)
          Ethernet Util = -----------------------------------------
                          Interval * 10,000
        
                          where 9.6 is interframe gap of Ethernet
                          6.4 is preamble of Ethernet
                          10,000 is 10Mbps
        
          100 Mbps        I/O-pkts * (96 + 64) + (8 * I/O-Bytes)
          Ethernet Util = --------------------------------------
                          Interval * 1,000,000
        
          1000 Mbps       I/O-pkts * (96 + 64) + (8 * I/O-Bytes)
          Ethernet Util = --------------------------------------
                          Interval * 10,000,000
        
          10000Mbps       I/O-pkts * (96 + 64) + (8 * I/O-Bytes)
          Ethernet Util = --------------------------------------
                          Interval * 100,000,000
        
          All other       I/O-pkts * (9.6 + 6.4) + (0.8 * I/O-Bytes)
          Ethernet Util = ------------------------------------------
                          Interval * N * 1,000
                          (where N is N Mbps)
        
        bytes -- the total number of bytes received and transmitted 
                 on the interface in 64-bit version.  
        
        packets -- the total number of packets received and 
                 transmitted on  the interface in 64-bit version.
        
        broadcast -- the total number of broadcast packets received 
                 and transmitted on the interface in 64-bit version.
        
        multicast -- the total number of multicast packets received 
                 and transmitted on the interface in 64-bit version.
        
        overflow -- the total number of transmitted buffer overflow 
                 errors on the interface in 32-bit version."
    ::= { ciscoInterfaceTopNExtMIBObjects 1 }

citneInterfaceTopNControlTable OBJECT-TYPE
    SYNTAX SEQUENCE OF CitneInterfaceTopNControlEntry
    ACCESS not-accessible
    STATUS mandatory
    DESCRIPTION
        "A table providing supplemental parameter information
        for interfaceTopNControlTable as defined in 
        INTERFACETOPN-MIB."
    ::= { ciscoInterfaceTopNExtMIBObjects 2 }

citneInterfaceTopNControlEntry OBJECT-TYPE
    SYNTAX CitneInterfaceTopNControlEntry
    ACCESS not-accessible
    STATUS mandatory
    DESCRIPTION
        "An entry providing supplemental parameter information
        that control the creation of a report of the top 
        N ports according to several metrics."
    INDEX { interfaceTopNControlIndex }
-- Augments interfaceTopNControlEntry FROM INTERFACETOPN-MIB
    ::= { citneInterfaceTopNControlTable 1 }

CitneInterfaceTopNControlEntry ::= SEQUENCE {
    citneInterfaceTopNCounterType INTEGER,
    citneInterfaceTopNInterfaceType INTEGER,
    citneInterfaceTopNVlanNumber VlanIndex
    }

citneInterfaceTopNCounterType OBJECT-TYPE
    SYNTAX INTEGER {
        none(1),
        utilization(2),
        bytes(3),
        packets(4),
        broadcast(5),
        multicast(6),
        overflow(7)
        }
    ACCESS read-write
    STATUS mandatory
    DESCRIPTION
        "The particular counter type to be sampled, as
        an extension to the interfaceTopNObjectVariable
        defined in INTERFACETOPN-MIB.
        
        Setting this object to the value of 'none' indicates
        that the TopN sampling is based on the counter type 
        as specified by the corresponding 
        interfaceTopNObjectVariable for the same entry
        in interfaceTopNControlTable; Setting this object 
        to a value other than 'none' indicates that the 
        TopN sampling is based on the counter type as 
        specified by this object instead of the 
        counter type as specified by the 
        corresponding interfaceTopNObjectVariable for 
        the same entry in interfaceTopNControlTable.    
        
        For entries in the interfaceTopNTable in the 
        INTERFACETOPN-MIB reported for counter type as specified 
        by this citneInterfaceTopNCounterType: 
        (1) The corresponding interfaceTopNDataSourceIndex will 
            point to the ifIndex of the sorted interfaces; 
        (2) If the sampled counter type is one of the following
            32 bit counters: 
                   'utilization',
                   'overflow', 
            the interfaceTopNValue object is used in 
            the corresponding entries in interfaceTopNTable.
        
            If the sampled counter type is one of the following
            64 bit counters: 
                   'bytes', 
                   'packets',
                   'broadcast',
                   'multicast',
            the interfaceTopNValue64 object is used 
            in the corresponding entries in interfaceTopNTable. 
        
        This object may not be modified if the associated
        interfaceTopNRowStatus object is equal to 'active'."
    DEFVAL { none }
    ::= { citneInterfaceTopNControlEntry 1 }

citneInterfaceTopNInterfaceType OBJECT-TYPE
    SYNTAX INTEGER {
        all(1),
        ethernet(2),
        fastEthernet(3),
        gigaEthernet(4),
        tenGigaEthernet(5),
        portChannel(6),
        layer2(7),
        layer3(8),
        fortyGigaEthernet(9)
        }
    ACCESS read-write
    STATUS mandatory
    DESCRIPTION
        "Specifies the interface type for the TopN sampling.
        
        all -- all applicable interfaces in the system.
        
        ethernet -- all Ethernet interfaces in the system.        
        
        fastEthernet -- all FastEthernet interfaces in the system.
        
        gigaEthernet -- all GigabitEthernet interfaces in the 
                        system. 
        
        tenGigaEthernet -- all TenGigabitEthernet interfaces 
                           in the system.
        
        portChannel -- all Port-channel interfaces in the system. 
        
        layer2 -- all layer-2 interfaces in the system. 
        
        layer3 -- all layer-3 interfaces in the system.  
        
        fortyGigaEthernet -- all FortyGigabitEthernet interfaces 
                           in the system.
        
        This object may not be modified if the associated
        interfaceTopNRowStatus object is equal to 'active'."
    DEFVAL { all }
    ::= { citneInterfaceTopNControlEntry 2 }

citneInterfaceTopNVlanNumber OBJECT-TYPE
    SYNTAX VlanIndex
--    Rsyntax Gauge
    ACCESS read-write
    STATUS mandatory
    DESCRIPTION
        "Specifies the Vlan number for the layer-2 interfaces when
        the object value of citneInterfaceTopNInterfaceType 
        for the same entry is 'layer2'. If the object value
        of citneInterfaceTopNVlanNumber is other than zero and 
        the corresponding citneInterfaceTopNInterfaceType is 
        'layer2' for the same entry, then it indicates all 
        layer-2 interfaces in that VLAN is sampled.  If the 
        object value of citneInterfaceTopNVlanNumber is zero 
        and the corresponding citneInterfaceTopNInterfaceType 
        is 'layer2' for the same entry, then it indicates all 
        layer-2 interfaces in the system regardless of their 
        Vlan number is sampled. If the object value of 
        citneInterfaceTopNInterfaceType is other than 
        'layer2', then citneInterfaceTopNVlanNumber has to take
        the value of 0.
        
        This object may not be modified if the associated
        interfaceTopNRowStatus object is equal to 'active'."
    DEFVAL { 0 }
    ::= { citneInterfaceTopNControlEntry 3 }

ciscoIfTopNExtCapsGroup OBJECT IDENTIFIER ::= { ciscoIfTopNExtMIBGroups 1 }
-- OBJECT-GROUP
--  Status
--    mandatory
--  Descr
--    A collection of objects providing capability information
--    about supplemental counter type supported by the system.
--  objects
--    citneInterfaceTopNCaps

ciscoIfTopNExtControlGroup OBJECT IDENTIFIER ::= { ciscoIfTopNExtMIBGroups 2 }
-- OBJECT-GROUP
--  Status
--    mandatory
--  Descr
--    A collection of objects providing information about
--    supplemental parameters for the 
--    interfaceTopNControlTable.
--  objects
--    citneInterfaceTopNCounterType, 
--    citneInterfaceTopNInterfaceType

ciscoIfTopNExtCtrlVlanGroup OBJECT IDENTIFIER ::= { ciscoIfTopNExtMIBGroups 3 }
-- OBJECT-GROUP
--  Status
--    mandatory
--  Descr
--    A collection of objects providing information about
--    supplemental vlan parameters for the
--    interfaceTopNControlTable.
--  objects
--    citneInterfaceTopNVlanNumber

ciscoIfTopNExtMIBCompliance OBJECT IDENTIFIER ::= { ciscoIfTopNExtMIBCompliances 1 }
-- MODULE-COMPLIANCE
--  Status
--    mandatory
--  Descr
--    Describes the requirements for conformance to the
--    Cisco InterfaceTopN Extention MIB.
--  Module
--    >>current<<
--   MandGroup
--    ciscoIfTopNExtCapsGroup
--   OptGroup
--    ciscoIfTopNExtControlGroup
--   OptGroup
--    ciscoIfTopNExtCtrlVlanGroup


END
