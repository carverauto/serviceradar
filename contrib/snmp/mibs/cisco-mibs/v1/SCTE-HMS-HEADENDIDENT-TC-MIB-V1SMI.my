-- MIB file created 06-Mar-2014 01:13:17, by
--   SMICng version 2.2.11-beta(PRO)(Solaris), January 20, 2001. Enterprise key cisco.com

SCTE-HMS-HEADENDIDENT-TC-MIB DEFINITIONS ::= BEGIN

-- From file: "SCTE-HMS-HEADENDIDENT-TC-MIB.my"
-- Compile options "4 7 F H N W 03 06 0B 0G 0N 0T"

IMPORTS
    enterprises
            FROM SNMPv2-SMI-v1
    Gauge
            FROM RFC1155-SMI;

hmsTextualConventionMIB OBJECT IDENTIFIER ::= { enterprises scteRoot(5591) scteHmsTree(1) insidePlantIdent(11) heDigital(5) 1 }
-- MODULE-IDENTITY
--  LastUpdated
--    200807231300Z
--  OrgName
--    SCTE HMS Working Group
--  ContactInfo
--    SCTE HMS Subcommittee, Chairman 
--     mail to:  standards@scte.org 
--  Descr
--    The MIB module is for representing general information
--    about HeadEnd Digital equipment present(or indoor)
--    and is supported by an SNMP agent.
--  RevDate
--    200807231300Z
--  RevDescr
--    Changed enumeration for QAMChannelInterleaveMode.
--  RevDate
--    200807121300Z
--  RevDescr
--    Modifications due to Comment Resolution Phase 2
--    1. Un-Commented out HeAlarmControl, HeTrapRegenerate to add Alarm Processing
--    back into the HMS-154 mib files. 
--    2. Added support for Alarm Processing.
--    3. Removed enumerations that were not used under the heDigital tree (heLaserType).
--    4. Modified QAMChannelModulationFormat.
--    5. Removed Display String from IMPORTS
--    6. Removed HeLaserType
--    7. Added enumeration QAMChannelInterleaveMode
--  RevDate
--    200801161300Z
--  RevDescr
--    Modifications due to Comment Resolution Meeting
--    1. Commented out HeAlarmControl, HeTrapRegenerate, HeDigitalRedundancyStatus
--    per Comment Resolution meeting for formal release of the Mib File. 
--    2. Added comments to HeDigitalAlarmSeverity and HeDigitalAlarmType that they 
--    are not used per Comment Resolution meeting for formal release of the Mib File, 
--    and commented out the enumerations so no-one uses them until they are needed in
--    case they will have to change.
--    3. Added the enumeration other to HeDigitalAlarmType so it would be universal.
--  RevDate
--    200712170000Z
--  RevDescr
--    Modifications due to voting comments
--    1. Changed syntax errors for capitalized words.
--    2. Changed mib to have the -MIB extention

VideoInputFrameRateType ::= INTEGER {
        other(1),
        autoSelect(2),
        f24Hz(3),
        f25Hz(4),
        f29Hz97(5),
        f30Hz(6),
        f29or30Hz(7),
        f48Hz(8),
        f50Hz(9),
        f59Hz94(10),
        f60Hz(11),
        f59or60Hz(12)
        }
-- TEXTUAL-CONVENTION
--  Status
--    mandatory
--  Descr
--     This value defines the types of MPEG Video Input Frame Rate that is
--    supported by QAM devices.

QAMChannelModulationFormat ::= INTEGER {
        unknown(1),
        other(2),
        qam64(3),
        qam256(4),
        qam128(5),
        qam512(6),
        qam1024(7)
        }
-- TEXTUAL-CONVENTION
--  Status
--    mandatory
--  Descr
--     This value defines the types of QAM Channel Modulation that is
--    supported by QAM devices.

QAMChannelInterleaveMode ::= INTEGER {
        unknown(1),
        other(2),
        fecI8J16(3),
        fecI16J8(4),
        fecI32J4(5),
        fecI64J2(6),
        fecI128J1(7),
        fecI12J17(8),
        fecI128J2(9),
        fecI128J3(10),
        fecI128J4(11),
        fecI128J5(12),
        fecI128J6(13),
        fecI128J7(14),
        fecI128J8(15)
        }
-- TEXTUAL-CONVENTION
--  Status
--    mandatory
--  Descr
--     This value defines the types of QAM Interleave Mode 
--    which follows the value of docsIfDownChannelInterleave. This
--    value is supported by HMS QAM devices.

ProgDataType ::= INTEGER {
        video(1),
        audio(2),
        data(3),
        other(4)
        }
-- TEXTUAL-CONVENTION
--  Status
--    mandatory
--  Descr
--    This value defines the types of data that can be contained in 
--         Programs and program streams.

DeviceEnableDisableValues ::= INTEGER {
        disabled(1),
        enabled(2),
        notSupported(3)
        }
-- TEXTUAL-CONVENTION
--  Status
--    mandatory
--  Descr
--    This data type represents whether the object is disabled(1) or 
--    enabled(2), or the object is not supported (3) by the current
--           configuration or this device's hardware.

MpegErrorStatus ::= INTEGER {
        good(1),
        errors(2),
        notSupported(3)
        }
-- TEXTUAL-CONVENTION
--  Status
--    mandatory
--  Descr
--    This data type represents whether the object is good(1) or has 
--    errors(2), or the object is not supported (3) by the current
--           configuration or this device's hardware.

HePIDValue ::= Gauge(0..8191|65535)
-- TEXTUAL-CONVENTION
--  DspHint
--    d
--  Status
--    mandatory
--  Descr
--    This data type represents a packet identifier (PID)
--           value which ranges from 0 to (2^13 - 1). The value of
--           65535 indicates that either the PID is invalid or does
--           not exist.

HeClockSource ::= INTEGER {
        unknown(1),
        other(2),
        internal(3),
        external(4),
        ntp(5),
        none(6)
        }
-- TEXTUAL-CONVENTION
--  Status
--    mandatory
--  Descr
--    An enumerated value that provides the location where the
--    value for the clock on the module is coming from.
--    internal - this value is being derived internally from the local 
--    module timing source.
--    external - an source that is external to the module, such as a 
--    controller card is providing a signal to calculate the real time clock.
--    ntp - this module is running the ntp protocol and can sync up to a 
--    master ntp clock source.
--    other - the real time clock source does not fit into the existing values. 

HeResetValue ::= INTEGER {
        reset(1),
        running(2),
        resetting(3)
        }
-- TEXTUAL-CONVENTION
--  Status
--    mandatory
--  Descr
--    Configured reset value for a specific device. 
--          reset - the value of reset is SET at the device and the device
--          will reset.
--          running - the normal value of the device is running when an SNMP
--          GET of the reset value is sent.
--          resetting - The value resetting shall be returned if an SNMP GET of 
--          the device is performed after a reset SET command is sent and before
--          the device can actually perform the reset. A second reset SET command
--          should not interrupt the reset sequence. If a second SET is sent, it 
--          will be ignored.
--          

HeTenthVolt ::= INTEGER
-- TEXTUAL-CONVENTION
--  DspHint
--    d-1
--  Status
--    mandatory
--  Descr
--    This data type represents voltage levels that are normally
--     expressed in volts. Units are in tenths of a volt;
--     for example, -48.1 volts will be represented as -481.

HeTenthdBm ::= INTEGER
-- TEXTUAL-CONVENTION
--  DspHint
--    d-1
--  Status
--    mandatory
--  Descr
--    This data type represents power levels 
--     that are normally expressed in dBm. Units 
--     are in tenths of a dBm;
--     for example, -5.1 dBm will be represented as -51.

HeTenthdBmV ::= INTEGER
-- TEXTUAL-CONVENTION
--  DspHint
--    d-1
--  Status
--    mandatory
--  Descr
--    This data type represents power levels 
--     that are normally expressed in dBmV. Units 
--     are in tenths of a dBmV;
--     for example, -5.1 dBmV will be represented as -51.

HeTenthCentigrade ::= INTEGER
-- TEXTUAL-CONVENTION
--  DspHint
--    d-1
--  Status
--    mandatory
--  Descr
--    This data type represents temperature values that
--     are normally expressed in Centigrade. Units are in
--     tenths of a Centigrade;
--     for example, -5.1 Centigrade will be represented as -51.

HeHundredthNanoMeter ::= Gauge
-- TEXTUAL-CONVENTION
--  DspHint
--    d-2
--  Status
--    mandatory
--  Descr
--    This data type represents wavelength values that
--     are normally expressed in nano meters. Units are in
--     hundredths of a NanoMeter;
--     for example, 1550.56 nm will be represented as 155056.

HeTenthdB ::= INTEGER
-- TEXTUAL-CONVENTION
--  DspHint
--    d-1
--  Status
--    mandatory
--  Descr
--    This data type represents power levels 
--    that are normally expressed in dB. Units 
--    are in tenths of a dB;
--    for example, -5.1 dB will be represented as -51.

HeOnOffControl ::= INTEGER {
        off(1),
        on(2),
        meaningless(3)
        }
-- TEXTUAL-CONVENTION
--  Status
--    mandatory
--  Descr
--    An enumerated value that provides a control of a particular
--    hardware or software parameter that usually represent
--    some sort of switch.
--    
--    A SET request with a value off(1) will cause the switch
--    to be shut off. 
--    
--    A SET request with a value on(2) will cause the switch
--    to be turned on.
--    
--    A value meaningless(3) will be implemented by the
--    variables that represent a switch with write-only access.
--    A GET request for the value of the write-only variable
--    shall return a value meaningless(3). 
--    
--    A SET request with a value meaningless(3) for the variable
--    with write access shall have no effect and no exception is
--    generated.
--    
--    A value may be used by the variables with both read-write
--    and write-only access.
--    
--    The variables with read-only access shall be defined with 
--    the textual convention HeOnOffStatus.

HeOnOffStatus ::= INTEGER {
        off(1),
        on(2)
        }
-- TEXTUAL-CONVENTION
--  Status
--    mandatory
--  Descr
--    An enumerated value that provides a status of a particular
--    hardware or software parameter that usually represent
--    some sort of switch.
--    
--    A value off(1) indicates the switch is off. 
--    
--    A value on(2) indicates the switch is on.

HeAlarmControl ::= INTEGER {
        alarmEnabled(1),
        alarmDisabled(2)
        }
-- TEXTUAL-CONVENTION
--  Status
--    mandatory
--  Descr
--    Alarm Control value for a specific device. This object is used to control sending
--          traps related to this headend entity or enabling disabling of raising an alarm
--          condition for a specific entity.

HeTrapRegenerate ::= INTEGER {
        trapRegenerate(1),
        trapNormal(2)
        }
-- TEXTUAL-CONVENTION
--  Status
--    mandatory
--  Descr
--     This value tells the SNMP Agent to send the Trap Regenerate Trap for
--     all values of Current alarms for this entity. The device can provide
--     for a means to send ALL current alarms, not just one specific entity.

HeDigitalAlarmSeverity ::= INTEGER {
        critical(1),
        major(2),
        minor(3),
        warning(4),
        status(5),
        clear(6),
        information(7)
        }
-- TEXTUAL-CONVENTION
--  Status
--    mandatory
--  Descr
--     The alarm severity that is determined by the device and sent over in the trap message.

HeDigitalAlarmType ::= INTEGER {
        communication(1),
        process(2),
        session(3),
        capacity(4),
        maintenance(5),
        provisioning(6),
        programMgmt(7),
        redundancy(8),
        other(9)
        }
-- TEXTUAL-CONVENTION
--  Status
--    mandatory
--  Descr
--     The alarm type that describes the Event that caused the alarm.

HeFaultStatus ::= INTEGER {
        normal(1),
        fault(2)
        }
-- TEXTUAL-CONVENTION
--  Status
--    mandatory
--  Descr
--    An enumerated value that provides a fault status of
--    a particular hardware or software parameter that
--    usually represent some sort of condition.
--    
--    A value normal(1) indicates the normal condition. 
--    
--    A value fault(2) indicates the fault condition.

HeMilliAmp ::= Gauge
-- TEXTUAL-CONVENTION
--  DspHint
--    d-3
--  Status
--    mandatory
--  Descr
--    This data type represents current levels that are normally
--     expressed in amperes. Units are in milliamperes;
--     for example, 2.1 Amperes would be expressed as 2100.

HeHundredthWatts ::= Gauge
-- TEXTUAL-CONVENTION
--  DspHint
--    d-2
--  Status
--    mandatory
--  Descr
--    This data type represents power values that
--     are normally expressed in watts. Units are in
--     hundredths of a watt;
--     for example, 420 watts will be represented as 42000.


END
