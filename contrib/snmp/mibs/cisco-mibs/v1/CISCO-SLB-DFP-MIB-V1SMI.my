-- MIB file created 10-Jun-2009 11:47:58, by
--   SMICng version 2.2.11-beta(PRO)(Solaris), January 20, 2001. Enterprise key cisco.com

CISCO-SLB-DFP-MIB DEFINITIONS ::= BEGIN

-- From file: "CISCO-SLB-DFP-MIB.my"
-- Compile options "4 7 F H N O W 03 06 0B 0G 0N 0T"

IMPORTS
    SnmpAdminString
            FROM SNMP-FRAMEWORK-MIB
    EntPhysicalIndexOrZero
            FROM CISCO-TC
    ciscoMgmt
            FROM CISCO-SMI
    Gauge
            FROM RFC1155-SMI
    OBJECT-TYPE
            FROM RFC-1212
    TRAP-TYPE
            FROM RFC-1215;

ciscoSlbDfpMIB OBJECT IDENTIFIER ::= { ciscoMgmt 689 }
-- MODULE-IDENTITY
--  LastUpdated
--    200901290000Z
--  OrgName
--    Cisco Systems, Inc.
--  ContactInfo
--    Cisco Systems 
--    Customer Service 
--    
--    
--    Postal:170 W. Tasman Drive 
--    
--    San Jose, CA  95134 
--    
--    USA 
--    
--    
--    Tel:+1 800 553-NETS 
--    
--    
--    E-mail:cs-asngw@cisco.com
--  Descr
--    This MIB reports the congestion status of the real server. 
--    A server can be in congested state due to high memory 
--    consumption, high CPU utilization or high number of clients 
--    being served by it. Congestion can cause delay in server 
--    response time. 
--    DFP (Dynamic Feedback Protocol) weight values are used as a 
--    metric to monitor the congestion of the server. 
--    
--    This MIB generates notifications when congestion state 
--    is detected on the real server.    
--    DFP weight is calculated as follows 
--    
--    BindingWeight=(Maxbindings-numberOfBindings)/Maxbindings 
--    
--    CPUMemWeight=(cpu + mem)/32 
--    
--    Weight = BindingWeight*CPUMemWeight*dfp_max_weight 
--    
--    Here, 
--     - Maxbindings is the maximum number of bindings allowed on the 
--    server. 
--     - dfp_max_weight is the maximum possible value of DFP weight 
--    (24). 
--     - numberOfBindings is the number of mobile bindings currently 
--    present with the server. 
--    
--    The DFP weight at which congestion is detected is configurable. 
--     If the DFP weight of the system falls below this value, then 
--    the system is treated as congested and notification is 
--    generated.
--  RevDate
--    200901290000Z
--  RevDescr
--    Initial version of this MIB module.

ciscoSlbDfpMIBNotifs OBJECT IDENTIFIER ::= { ciscoSlbDfpMIB 0 }
ciscoSlbDfpMIBObjects OBJECT IDENTIFIER ::= { ciscoSlbDfpMIB 1 }
ciscoSlbDfpMIBConform OBJECT IDENTIFIER ::= { ciscoSlbDfpMIB 2 }
ciscoSlbDfpMIBCompliances OBJECT IDENTIFIER ::= { ciscoSlbDfpMIBConform 1 }
ciscoSlbDfpMIBGroups OBJECT IDENTIFIER ::= { ciscoSlbDfpMIBConform 2 }

CslbcDfpValue ::= Gauge(0..65535)
-- TEXTUAL-CONVENTION
--  DspHint
--    d
--  Status
--    mandatory
--  Descr
--    This textual convention defines valid ranges DFP values 
--    similar to slbDfpRealWeight object defined in CISCO-SLB-MIB.

cslbcDfpCongestionOnsetThreshold OBJECT-TYPE
    SYNTAX CslbcDfpValue
--    Rsyntax Gauge(0..65535)
--  Units
--    DFP weight
    ACCESS read-write
    STATUS mandatory
    DESCRIPTION
        "This object specifes when congestion occurs.  When the DFP 
        level of the system drops below this value, the system is 
        marked as congested.  This value is same for all the 
        processors."
    DEFVAL { 0 }
    ::= { ciscoSlbDfpMIBObjects 1 }

cslbcDfpCongestionAbateThreshold OBJECT-TYPE
    SYNTAX CslbcDfpValue
--    Rsyntax Gauge(0..65535)
--  Units
--    DFP weight
    ACCESS read-write
    STATUS mandatory
    DESCRIPTION
        "This object specifies when decongestion occurs.  When the DFP 
        level of the system rises above this value, the system is 
        marked as decongested.  This value is same for all processors."
    DEFVAL { 0 }
    ::= { ciscoSlbDfpMIBObjects 2 }

cslbcDfpCongestionThresholdType OBJECT-TYPE
    SYNTAX INTEGER {
        reject(1),
        abort(2),
        redirect(3),
        drop(4)
        }
    ACCESS not-accessible
    STATUS mandatory
    DESCRIPTION
        "This object specifies the action taken when the congestion 
        threshold is reached. 
        The valid congestion action type are 
        o reject - Incoming registration requests will be rejected when 
        this congestion type is configured. 
        o abort - Registration request being processed will be aborted 
        when this congestion type is configured. 
        o redirect - Incoming registration requests will be redirected 
        to another Home Agent when this congestion type is configured. 
        o drop - Existing idle mobile IP bindings will be dropped when 
        this congestion type is configured. 
        
        A mobile IP binding is a record present with the server that  
        associates the home address given to the mobile node by its 
        home network with the care of address granted to it by the 
        foreign network while it is roaming.   
        The Home Agent is a real server that maintains mobile  
        bindings."
    ::= { ciscoSlbDfpMIBObjects 3 }

cslbcProcessorDfpValTable OBJECT-TYPE
    SYNTAX SEQUENCE OF CslbcProcessorDfpValEntry
    ACCESS not-accessible
    STATUS mandatory
    DESCRIPTION
        "This table lists the DFP status for each processor for which 
        DFP weights are monitored."
    ::= { ciscoSlbDfpMIBObjects 4 }

cslbcProcessorDfpValEntry OBJECT-TYPE
    SYNTAX CslbcProcessorDfpValEntry
    ACCESS not-accessible
    STATUS mandatory
    DESCRIPTION
        "The entry contains DFP value for one processor. 
        A row is added to this table when congestion needs to be 
        monitored on a processor. Row is deleted when congestion no 
        longer needs to be monitored."
    INDEX { cslbcProcessorDfpValPhysicalIndex }
    ::= { cslbcProcessorDfpValTable 1 }

CslbcProcessorDfpValEntry ::= SEQUENCE {
    cslbcProcessorDfpValPhysicalIndex EntPhysicalIndexOrZero,
    cslbcProcessorDfpValDescription SnmpAdminString,
    cslbcProcessorDfpValDfpValue CslbcDfpValue
    }

cslbcProcessorDfpValPhysicalIndex OBJECT-TYPE
    SYNTAX EntPhysicalIndexOrZero
--    Rsyntax INTEGER(0..2147483647)
    ACCESS not-accessible
    STATUS mandatory
    DESCRIPTION
        "This element contains the index of the physical entity or 
        identifier of the processor for which the DFP value is 
        maintained."
    ::= { cslbcProcessorDfpValEntry 1 }

cslbcProcessorDfpValDescription OBJECT-TYPE
    SYNTAX SnmpAdminString
--    Rsyntax OCTET STRING(SIZE(0..255))
    ACCESS read-only
    STATUS mandatory
    DESCRIPTION
        "This element contains the description for the congestion 
        configured on for processor."
    ::= { cslbcProcessorDfpValEntry 2 }

cslbcProcessorDfpValDfpValue OBJECT-TYPE
    SYNTAX CslbcDfpValue
--    Rsyntax Gauge(0..65535)
    ACCESS read-only
    STATUS mandatory
    DESCRIPTION
        "This object indicates DFP value for the processor."
    ::= { cslbcProcessorDfpValEntry 3 }

cslbcSlbDfpCongestionOnset TRAP-TYPE
-- Reverse mappable trap
    ENTERPRISE ciscoSlbDfpMIB
    VARIABLES {
        cslbcProcessorDfpValDescription, 
        cslbcProcessorDfpValDfpValue, 
        cslbcDfpCongestionThresholdType, 
        cslbcDfpCongestionOnsetThreshold }
--  Status
--    mandatory
    DESCRIPTION
        "The server generates this notification when value of 
        cslbcInstanceDfpValue object drops below the threshold 
        indicated 
        by the cslbcDfpCongestionOnsetThreshold object."
    ::= 1

cslbcSlbDfpCongestionAbate TRAP-TYPE
-- Reverse mappable trap
    ENTERPRISE ciscoSlbDfpMIB
    VARIABLES {
        cslbcProcessorDfpValDescription, 
        cslbcProcessorDfpValDfpValue, 
        cslbcDfpCongestionAbateThreshold, 
        cslbcDfpCongestionThresholdType }
--  Status
--    mandatory
    DESCRIPTION
        "The server generates this notification when value of 
        cslbcInstanceDfpValue object rises above the threshold 
        indicated 
        by the cslbcDfpCongestionAbateThreshold object."
    ::= 2

ciscoSlbDfpInstanceGroup OBJECT IDENTIFIER ::= { ciscoSlbDfpMIBGroups 1 }
-- OBJECT-GROUP
--  Status
--    mandatory
--  Descr
--    This group represents the fields that identifies the processor 
--    and associated DFP value.
--  objects
--    cslbcProcessorDfpValDescription, cslbcProcessorDfpValDfpValue

cslbcSlbDfpScalarsGroup OBJECT IDENTIFIER ::= { ciscoSlbDfpMIBGroups 2 }
-- OBJECT-GROUP
--  Status
--    mandatory
--  Descr
--    This group represents the set of thresholds against which the 
--    DFP value is compared.
--  objects
--    cslbcDfpCongestionOnsetThreshold, 
--    cslbcDfpCongestionAbateThreshold, 
--    cslbcDfpCongestionThresholdType

cslbcSlbDfpCongestionGroup OBJECT IDENTIFIER ::= { ciscoSlbDfpMIBGroups 3 }
-- NOTIFICATION-GROUP
--  Status
--    mandatory
--  Descr
--    This groutp represents the group of notifications on Home 
--    Agent.
--  notifications
--    cslbcSlbDfpCongestionOnset, cslbcSlbDfpCongestionAbate

ciscoSlbDfpMIBCompliance OBJECT IDENTIFIER ::= { ciscoSlbDfpMIBCompliances 1 }
-- MODULE-COMPLIANCE
--  Status
--    mandatory
--  Descr
--    The compliance statement for entities which implement 
--    ciscoSlbDfp MIB module.
--  Module
--    >>current<<
--   MandGroup
--    ciscoSlbDfpInstanceGroup
--   MandGroup
--    cslbcSlbDfpScalarsGroup
--   MandGroup
--    cslbcSlbDfpCongestionGroup


END
