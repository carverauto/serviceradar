-- MIB created 6/25/99 12:57:12, by
--   SMIC (the next generation) version 1.6.29, November 22, 1994.

CISCO-DS0BUNDLE-MIB DEFINITIONS ::= BEGIN

-- From file: "CISCO-DS0BUNDLE-MIB.my"

IMPORTS
    OBJECT-TYPE
            FROM RFC-1212
    RowStatus, TestAndIncr
            FROM SNMPv2-TC-v1
    ciscoExperiment
            FROM CISCO-SMI
    InterfaceIndex
            FROM IF-MIB;

ds0Bundle OBJECT IDENTIFIER ::= { ciscoExperiment 32 }
-- MODULE-IDENTITY
--  LastUpdated
--    9805242010Z
--  OrgName
--    Cisco Systems, Inc.
--  ContactInfo
--            Cisco Systems
--             Customer Service
--    
--    Postal: 170 W Tasman Drive
--           San Jose, CA  95134
--           USA
--    
--     Tel: +1 800 553-NETS
--    
--    E-mail: cs-snmp@cisco.com
--  Descr
--    The MIB module to describe DS0 Bundle interfaces
--    objects.
--    
--    
--    Note: This contains a subset of the MIB objects
--    defined in DS0BUNDLE-MIB of
--    draft-ietf-trunkmib-ds0-mib-06.txt, section 6; it does
--    not include the DS0 Bonding group.

ds0BundleConformance OBJECT IDENTIFIER ::= { ds0Bundle 4 }
ds0BundleGroups OBJECT IDENTIFIER ::= { ds0BundleConformance 1 }
ds0BundleCompliances OBJECT IDENTIFIER ::= { ds0BundleConformance 2 }

dsx0BundleNextIndex OBJECT-TYPE
    SYNTAX TestAndIncr
--    Rsyntax INTEGER(0..2147483647)
    ACCESS read-write
    STATUS mandatory
    DESCRIPTION
        "This object is used to assist the manager in
                      selecting a value for dsx0BundleIndex.  Because
                      this object is of syntax TestAndIncr (see the
                      SNMPv2-TC document, RFC1903) it can also be used to
                      avoid race conditions with multiple managers trying to
                      create rows in the table. 
        
        If the result of the SET for dsx0BundleNextIndex is
        not success, this means the value has been changed
        from index (i.e. another manager used the value), so a
        new value is required.
        
        The algorithm is:
        done = false
                      while done == false 
                            index = GET (dsx0BundleNextIndex.0) 
                            SET (dsx0BundleNextIndex.0=index)
              if (set failed)
         done = false
              else
         SET(dsx0BundleRowStatus.index=createAndGo) 
         if (set failed)
           done = false
         else
                                done = true 
                                other error handling"
    ::= { ds0Bundle 2 }

dsx0BundleTable OBJECT-TYPE
    SYNTAX SEQUENCE OF Dsx0BundleEntry
    ACCESS not-accessible
    STATUS mandatory
    DESCRIPTION
        "There is a row in this table for each ds0Bundle in
        the system.  This table can be used to (indirectly)
        create rows in the ifTable with ifType =
        'ds0Bundle(82)'."
    ::= { ds0Bundle 3 }

dsx0BundleEntry OBJECT-TYPE
    SYNTAX Dsx0BundleEntry
    ACCESS not-accessible
    STATUS mandatory
    DESCRIPTION
        "There is a row in this table for each ds0Bundle
        interface."
    INDEX { dsx0BundleIndex }
    ::= { dsx0BundleTable 1 }

Dsx0BundleEntry ::= SEQUENCE {
    dsx0BundleIndex INTEGER,
    dsx0BundleIfIndex InterfaceIndex,
    dsx0BundleRowStatus RowStatus
    }

dsx0BundleIndex OBJECT-TYPE
    SYNTAX INTEGER(0..2147483647)
    ACCESS not-accessible
    STATUS mandatory
    DESCRIPTION
        "A unique identifier for a ds0Bundle. This is not the
        same value as ifIndex. This table is not indexed by
        ifIndex because the manager has to choose the index in
        a createable row and the agent must be allowed to
        select ifIndex values."
    ::= { dsx0BundleEntry 1 }

dsx0BundleIfIndex OBJECT-TYPE
    SYNTAX InterfaceIndex
--    Rsyntax Integer32
    ACCESS read-only
    STATUS mandatory
    DESCRIPTION
        "The ifIndex value the agent selected for the (new) 
                      ds0Bundle interface."
    ::= { dsx0BundleEntry 2 }

dsx0BundleRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create and delete rows in 
                      this table."
    ::= { dsx0BundleEntry 3 }

ds0BundleConfigGroup OBJECT IDENTIFIER ::= { ds0BundleGroups 2 }
-- OBJECT-GROUP
--  Status
--    mandatory
--  Descr
--    A collection of objects providing the ability to 
--    create a new ds0Bundle in the ifTable.
--  objects
--    dsx0BundleNextIndex, dsx0BundleIfIndex, dsx0BundleRowStatus

ds0BundleCompliance OBJECT IDENTIFIER ::= { ds0BundleCompliances 1 }
-- MODULE-COMPLIANCE
--  Status
--    mandatory
--  Descr
--    The compliance statement for DS0Bundle interfaces.
--  Module
--    >>current<<
--   MandGroup
--    ds0BundleConfigGroup


END
