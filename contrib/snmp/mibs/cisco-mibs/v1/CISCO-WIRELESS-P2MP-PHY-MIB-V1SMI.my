-- MIB created 1/08/101 14:56:51, by
--   SMIC (the next generation) version 1.6.29, November 22, 1994.

CISCO-WIRELESS-P2MP-PHY-MIB DEFINITIONS ::= BEGIN

-- From file: "CISCO-WIRELESS-P2MP-PHY-MIB.my"

IMPORTS
    Integer32
            FROM SNMPv2-SMI-v1
    OBJECT-TYPE
            FROM RFC-1212
    TRAP-TYPE
            FROM RFC-1215
    DisplayString, TruthValue
            FROM SNMPv2-TC-v1
    ifIndex
            FROM IF-MIB
    CwrOscState, CwrRfType, CwrRfFreqRange
            FROM CISCO-WIRELESS-TC-MIB
    Unsigned32
            FROM CISCO-TC
    entPhysicalIndex
            FROM ENTITY-MIB
    ciscoMgmt
            FROM CISCO-SMI;

ciscoWirelessPhyMIB OBJECT IDENTIFIER ::= { ciscoMgmt 170 }
-- MODULE-IDENTITY
--  LastUpdated
--    200010221910Z
--  OrgName
--    Cisco Systems Inc.
--  ContactInfo
--     Cisco Systems
--    Customer Service
--    
--    Postal: 170 W Tasman Drive
--     San Jose, CA  95134
--     USA
--    
--     Tel: +1 800 553-NETS
--            E-mail: wireless-nms@cisco.com
--  Descr
--    This is the MIB Module for the Cisco Wireless Radio 
--            Point to MultiPoint interface.
--  RevDate
--    200010221910Z
--  RevDescr
--    Changed propWirelessDocsMAC to 
--     propDocsWirelessMaclayer
--  RevDate
--    200010041910Z
--  RevDescr
--    Fixed minor typo in spelling of Duplexer
--     Changed valid range for p2mpSuMeasuredPower
--  RevDate
--    200007211910Z
--  RevDescr
--    Redefined p2mpDenyService 
--     Redefined p2mpLoopbackTable
--     Added a second index for p2mpSuPowerScanTable

p2mpRadioObjects OBJECT IDENTIFIER ::= { ciscoWirelessPhyMIB 1 }
p2mpRadioBaseObjects OBJECT IDENTIFIER ::= { p2mpRadioObjects 1 }
p2mpRadioSuObjects OBJECT IDENTIFIER ::= { p2mpRadioObjects 2 }
p2mpRadioHeObjects OBJECT IDENTIFIER ::= { p2mpRadioObjects 3 }
p2mpPhyConfigGroup OBJECT IDENTIFIER ::= { p2mpRadioBaseObjects 1 }
p2mpFreqResourceGroup OBJECT IDENTIFIER ::= { p2mpRadioBaseObjects 2 }
p2mpRadioTestGroup OBJECT IDENTIFIER ::= { p2mpRadioBaseObjects 3 }
p2mpLedGroup    OBJECT IDENTIFIER ::= { p2mpRadioBaseObjects 4 }
p2mpPhyMIBNotificationPrefix OBJECT IDENTIFIER ::= { ciscoWirelessPhyMIB 2 }
p2mpPhyMIBNotification OBJECT IDENTIFIER ::= { p2mpPhyMIBNotificationPrefix 0 }
p2mpRadioPhyConformance OBJECT IDENTIFIER ::= { p2mpRadioObjects 4 }
p2mpRadioPhyCompliances OBJECT IDENTIFIER ::= { p2mpRadioPhyConformance 1 }
p2mpRadioPhyGroups OBJECT IDENTIFIER ::= { p2mpRadioPhyConformance 2 }

p2mpRadioPhyTable OBJECT-TYPE
    SYNTAX SEQUENCE OF P2mpRadioPhyEntry
    ACCESS not-accessible
    STATUS mandatory
    DESCRIPTION
        "This table provides facilities to configure the physical
        layer characteristics of the radio link.
               The objects in this table are supported on the head end and 
               at the subscriber unit."
    ::= { p2mpPhyConfigGroup 1 }

p2mpRadioPhyEntry OBJECT-TYPE
    SYNTAX P2mpRadioPhyEntry
    ACCESS not-accessible
    STATUS mandatory
    DESCRIPTION
        "The entry of this table is created when the managed system
        detects a propDocsWirelessMaclayer interface. The entry 
        is removed when the associated propDocsWirelessMaclayer 
        interface is deleted from the ifTable."
    INDEX { ifIndex }
    ::= { p2mpRadioPhyTable 1 }

P2mpRadioPhyEntry ::= SEQUENCE {
    p2mpSelfTest TruthValue,
    p2mpDiversityAntennaPresent TruthValue,
    p2mpCableLoss Unsigned32,
    p2mpCableLossDiversity Unsigned32,
    p2mpClockRefExt TruthValue,
    p2mpDenyService TruthValue,
    p2mpCommonTrapEnable TruthValue,
    p2mpLastPhyFailureType INTEGER,
    p2mpLastPhyFailureReason DisplayString
    }

p2mpSelfTest OBJECT-TYPE
    SYNTAX TruthValue
--    Rsyntax INTEGER {
--        true(1),
--        false(2)
--        }
    ACCESS read-write
    STATUS mandatory
    DESCRIPTION
        "This object is used to enable/disable self test.  When set to 
        true(1), the software tests the memory and hardware integrity
        shortly after the router powers up."
    ::= { p2mpRadioPhyEntry 1 }

p2mpDiversityAntennaPresent OBJECT-TYPE
    SYNTAX TruthValue
--    Rsyntax INTEGER {
--        true(1),
--        false(2)
--        }
    ACCESS read-write
    STATUS mandatory
    DESCRIPTION
        "When true(1), this object indicates that a diversity
        antenna is being used to receive the wireless transmissions.
        When false(2), the radio system is using a single antenna
        to transmit and receive."
    ::= { p2mpRadioPhyEntry 2 }

p2mpCableLoss OBJECT-TYPE
    SYNTAX Unsigned32(0..15)
--    Rsyntax Gauge32(0..15)
--  Units
--    dB
    ACCESS read-write
    STATUS mandatory
    DESCRIPTION
        "This object indicates the measured signal power loss in dB
        due to the cable connecting the radio to the main antenna.
        The hardware compensates for this cable loss by adjusting the
        receive and transmit gain appropriately.  A value of 0 
        indicates no degradation in the signal due to the cable.  The 
        radio hardware can compensate for a cable loss of no more 
        than 15 db.
        This cable loss applies to the main antenna only."
    ::= { p2mpRadioPhyEntry 3 }

p2mpCableLossDiversity OBJECT-TYPE
    SYNTAX Unsigned32(0..15)
--    Rsyntax Gauge32(0..15)
--  Units
--    dB
    ACCESS read-write
    STATUS mandatory
    DESCRIPTION
        "This object indicates the measured signal power loss in dB 
        due to the cable connecting the radio to the diversity 
        antenna.  The hardware compensates for this loss by adjusting 
        the receive and transmit gain appropriately.  A value of 0 
        indicates no degradation in the signal due to the cable.  The 
        radio hardware can compensate for a cable loss of no more 
        than 15 dB. 
        This cable loss applies to the diversity antenna only."
    ::= { p2mpRadioPhyEntry 4 }

p2mpDenyService OBJECT-TYPE
    SYNTAX TruthValue
--    Rsyntax INTEGER {
--        true(1),
--        false(2)
--        }
    ACCESS read-only
    STATUS mandatory
    DESCRIPTION
        "Indicates if the service is disabled in the unit.
        For Head-end unit, if this object has the value of 
        'true', the link is in loopback mode; otherwise the 
        link is enabled for transmitting / receiving data.
        For Subscriber unit, if this object has the value of 
        'true', the subscriber unit service is disabled; 
        otherwise, the subscriber unit is enabled for 
        transmitting / receiving data"
    ::= { p2mpRadioPhyEntry 5 }

p2mpClockRefExt OBJECT-TYPE
    SYNTAX TruthValue
--    Rsyntax INTEGER {
--        true(1),
--        false(2)
--        }
    ACCESS read-write
    STATUS mandatory
    DESCRIPTION
        "This object controls the use of external reference 
        clock for IF module as follows:
        'true(1)'  - an external reference clock is used
        'false(2)' - an internal reference clock is used."
    ::= { p2mpRadioPhyEntry 6 }

p2mpCommonTrapEnable OBJECT-TYPE
    SYNTAX TruthValue
--    Rsyntax INTEGER {
--        true(1),
--        false(2)
--        }
    ACCESS read-write
    STATUS mandatory
    DESCRIPTION
        "When set to true(1), the notifications common to the head end 
        and subscriber unit are enabled.  When set to false(2), these 
        notifications are disabled.
        The notification controlled by this object are: 
          - p2mpRadioPhyFailNotification
          - p2mpTrapRfSupplyVoltage
          - p2mpTrapRfRxOsc
          - p2mpTrapRfTxOsc
          - p2mpTrapRfTemp
          - p2mpTrapRfCommLinkError
          - p2mpTrapTxPower
          - p2mpTrapRfStatusChange"
    DEFVAL { true }
    ::= { p2mpRadioPhyEntry 7 }

p2mpLastPhyFailureType OBJECT-TYPE
    SYNTAX INTEGER {
        none(1),
        p2mpHwConfigUnsupported(2),
        p2mpHwConfigMismatch(3),
        p2mpHwInitFailure(4),
        p2mpHostIfCommLinkError(5),
        p2mpAutoCableCompFailure(6)
        }
    ACCESS read-only
    STATUS mandatory
    DESCRIPTION
        "This object indicates the last physical link failure that 
        resulted in a p2mpRadioPhyFailNotification trap.
        
            none(1) - no failure
        
            p2mpHwConfigUnsupported(2) - The radio subsystem has 
               detected that the configuration requested is not 
               supported by the hardware.  The p2mpLastPhyFailureReason
               variable will indicate which configuration parameter is
               not supported.
        
            p2mpHwConfigMismatch(3) - The radio subsystem has detected 
               that the combination of the configuration parameters 
               requested is inconsistent and cannot be supported.
               The p2mpLastPhyFailReason variable will indicate the 
               configuration parameter that causes the mismatch.
        
            p2mpHwInitFailure(4) - The radio subsystem has failed to 
               initialize the hardware. This implies that there is a 
               critical error condition in the associated hardware. 
               The p2mpLastPhyFailReason specifies the reason why the 
               init failed.
        
            p2mpHostIfCommLinkError(5) - The host could not communicate 
               with the IF module.
        
            p2mpAutoCableCompFailure(6) - Failed to achieve automatic 
               cable compensation due to loss of Tx signal."
    ::= { p2mpRadioPhyEntry 8 }

p2mpLastPhyFailureReason OBJECT-TYPE
    SYNTAX DisplayString(SIZE(0..255))
--    Rsyntax OCTET STRING(SIZE(0..255))
    ACCESS read-only
    STATUS mandatory
    DESCRIPTION
        "This is a text string that describes the last physical link
               failure identified by p2mpLastPhyFailureType."
    ::= { p2mpRadioPhyEntry 9 }

p2mpRfTable OBJECT-TYPE
    SYNTAX SEQUENCE OF P2mpRfEntry
    ACCESS not-accessible
    STATUS mandatory
    DESCRIPTION
        "This table contains information about the state of the radio 
        frequency resources used by the radio system.
        
        Physically each RF resource may be realized by one antenna and 
        its associated control hardware. A single antenna and its 
        associated electronics may act as more than 1 RF resource. When
        an RF resource acts as both a transmit and receive resource,
        the transmit and receive frequency ranges may overlap."
    ::= { p2mpFreqResourceGroup 1 }

p2mpRfEntry OBJECT-TYPE
    SYNTAX P2mpRfEntry
    ACCESS not-accessible
    STATUS mandatory
    DESCRIPTION
        "This represents one entry in the p2mpRfTable.  
        
        An entry is created in this table when the managed system 
        detects a RF resource. The entry is removed when the RF 
        resource is removed from the wireless system."
    INDEX { ifIndex, p2mpRfIndex }
    ::= { p2mpRfTable 1 }

P2mpRfEntry ::= SEQUENCE {
    p2mpRfIndex Integer32,
    p2mpRfType CwrRfType,
    p2mpRfOpMode INTEGER,
    p2mpTxFreqRangeMin CwrRfFreqRange,
    p2mpTxFreqRangeMax CwrRfFreqRange,
    p2mpRxFreqRangeMin CwrRfFreqRange,
    p2mpRxFreqRangeMax CwrRfFreqRange,
    p2mpMinTxPower Integer32,
    p2mpMaxTxPower Integer32,
    p2mpRfTemperature Integer32,
    p2mpRfTxOscState CwrOscState,
    p2mpRfRxOscState CwrOscState,
    p2mpRfSupplyVoltageState INTEGER,
    p2mpRfStatus INTEGER,
    p2mpRfLoopbackSupported TruthValue
    }

p2mpRfIndex OBJECT-TYPE
    SYNTAX Integer32(1..100)
    ACCESS not-accessible
    STATUS mandatory
    DESCRIPTION
        "This object, along with the ifIndex of the MAC layer, 
               represents the index of this entry in the p2mpRfTable. 
               Each entry in the table provides details on the state of  
               the RF resources available in the system."
    ::= { p2mpRfEntry 1 }

p2mpRfType OBJECT-TYPE
    SYNTAX CwrRfType
--    Rsyntax INTEGER {
--        main(0),
--        diversity(1)
--        }
    ACCESS read-only
    STATUS mandatory
    DESCRIPTION
        "This object identifies the RF resource."
    ::= { p2mpRfEntry 2 }

p2mpRfOpMode OBJECT-TYPE
    SYNTAX INTEGER {
        receiveOnly(1),
        transmitOnly(2),
        transmitAndReceive(3)
        }
    ACCESS read-only
    STATUS mandatory
    DESCRIPTION
        "This object specifies whether this RF resource can either
               transmit, receive, or do both."
    ::= { p2mpRfEntry 3 }

p2mpTxFreqRangeMin OBJECT-TYPE
    SYNTAX CwrRfFreqRange
--    Rsyntax Integer32(0..60000000)
--  Units
--    KHz
    ACCESS read-only
    STATUS mandatory
    DESCRIPTION
        "This object represents the minimum frequency at which this RF 
        resource can transmit."
    ::= { p2mpRfEntry 4 }

p2mpTxFreqRangeMax OBJECT-TYPE
    SYNTAX CwrRfFreqRange
--    Rsyntax Integer32(0..60000000)
--  Units
--    KHz
    ACCESS read-only
    STATUS mandatory
    DESCRIPTION
        "This object represents the maximum frequency at which this RF 
        resource can transmit."
    ::= { p2mpRfEntry 5 }

p2mpRxFreqRangeMin OBJECT-TYPE
    SYNTAX CwrRfFreqRange
--    Rsyntax Integer32(0..60000000)
--  Units
--    KHz
    ACCESS read-only
    STATUS mandatory
    DESCRIPTION
        "This object represents the lowest transmission frequency this 
        RF resource can receive. "
    ::= { p2mpRfEntry 6 }

p2mpRxFreqRangeMax OBJECT-TYPE
    SYNTAX CwrRfFreqRange
--    Rsyntax Integer32(0..60000000)
--  Units
--    KHz
    ACCESS read-only
    STATUS mandatory
    DESCRIPTION
        "This object represents the highest transmission frequency that 
        this RF resource can receive."
    ::= { p2mpRfEntry 7 }

p2mpMinTxPower OBJECT-TYPE
    SYNTAX Integer32(-80..50)
--  Units
--    dBm
    ACCESS read-only
    STATUS mandatory
    DESCRIPTION
        "This object represents the minimum power that the RF subsystem
        can supply the antenna. "
    ::= { p2mpRfEntry 8 }

p2mpMaxTxPower OBJECT-TYPE
    SYNTAX Integer32(-80..50)
--  Units
--    dBm
    ACCESS read-only
    STATUS mandatory
    DESCRIPTION
        "This object represents the maximum power that the RF subsystem
        can supply the antenna."
    ::= { p2mpRfEntry 9 }

p2mpRfTemperature OBJECT-TYPE
    SYNTAX Integer32(-40..100)
--  Units
--    Degrees Centigrade
    ACCESS read-only
    STATUS mandatory
    DESCRIPTION
        "This object represents the current temperature of the RF unit"
    ::= { p2mpRfEntry 10 }

p2mpRfTxOscState OBJECT-TYPE
    SYNTAX CwrOscState
--    Rsyntax INTEGER {
--        oscillatorOk(1),
--        osccillatorBad(2)
--        }
    ACCESS read-only
    STATUS mandatory
    DESCRIPTION
        "This object represents the state of the transmit oscillator. 
        The oscillator must be in oscillatorOk(1) state for the system 
               to function properly."
    ::= { p2mpRfEntry 11 }

p2mpRfRxOscState OBJECT-TYPE
    SYNTAX CwrOscState
--    Rsyntax INTEGER {
--        oscillatorOk(1),
--        osccillatorBad(2)
--        }
    ACCESS read-only
    STATUS mandatory
    DESCRIPTION
        "This object represents the state of the receive oscillator. 
        The oscillator must be in oscillatorOk(1) state for the system
        to function properly."
    ::= { p2mpRfEntry 12 }

p2mpRfSupplyVoltageState OBJECT-TYPE
    SYNTAX INTEGER {
        withinSpecification(1),
        outsideSpecification(2)
        }
    ACCESS read-only
    STATUS mandatory
    DESCRIPTION
        "This object specifies whether the voltage supply to the RF 
             unit is within specifications or not.  Voltage specifications
               are hardware dependent."
    ::= { p2mpRfEntry 13 }

p2mpRfStatus OBJECT-TYPE
    SYNTAX INTEGER {
        online(1),
        offline(2)
        }
    ACCESS read-only
    STATUS mandatory
    DESCRIPTION
        "This object specifies whether the RF resource is functioning 
        properly. If it is functioning properly then it will be 
               online(1), else offline(2).
               At the Subscriber Unit, this object will reflect offline(2) 
               if p2mpTxMuteEnable in the p2mpSuRadioPhyTable is true(1)."
    ::= { p2mpRfEntry 14 }

p2mpRfLoopbackSupported OBJECT-TYPE
    SYNTAX TruthValue
--    Rsyntax INTEGER {
--        true(1),
--        false(2)
--        }
    ACCESS read-only
    STATUS mandatory
    DESCRIPTION
        "This object indicates if the RF unit supports loopback.
               When true(1), the user can configure loopback using the 
               objects in p2mpLoopbackTable. When false(2), any attempt
               to configure RF loopback will fail. "
    ::= { p2mpRfEntry 15 }

p2mpDuplexerTable OBJECT-TYPE
    SYNTAX SEQUENCE OF P2mpDuplexerEntry
    ACCESS not-accessible
    STATUS mandatory
    DESCRIPTION
        "This table contains information about the Duplexers
        available for use on the system.
        
        A Duplexer is a mechanical device, that acts as a band 
        pass filter when installed in an RF resource.
        
        Normally a RF resource is capable of operating over a wide
        frequency range. To operate at restricted frequencies, the user
        has to own that part of the frequency spectrum.  Since the user
        may not own parts of the frequency spectrum over which the RF
        resource may operate, a duplexer is installed at the RF.
        This restricts the RF resource to operate in the passband
        defined by the duplexer."
    ::= { p2mpFreqResourceGroup 2 }

p2mpDuplexerEntry OBJECT-TYPE
    SYNTAX P2mpDuplexerEntry
    ACCESS not-accessible
    STATUS mandatory
    DESCRIPTION
        "This represents one entry in the p2mpDuplexerTable. 
        Each entry contains information about the duplexers 
        capabilities and the associated RF resource.
        
        An entry is created in this table when the managed system
        detects a RF resource. The entry is removed when the RF
        resource is removed from the wireless system."
    INDEX { ifIndex, p2mpDuplexerIndex }
    ::= { p2mpDuplexerTable 1 }

P2mpDuplexerEntry ::= SEQUENCE {
    p2mpDuplexerIndex Integer32,
    p2mpDuplexerRF CwrRfType,
    p2mpDuplexerLoPassbandMinFreq CwrRfFreqRange,
    p2mpDuplexerLoPassbandMaxFreq CwrRfFreqRange,
    p2mpDuplexerHiPassbandMinFreq CwrRfFreqRange,
    p2mpDuplexerHiPassbandMaxFreq CwrRfFreqRange,
    p2mpDuplexerReceivePassband INTEGER,
    p2mpDuplexerTxInsertionLoss Integer32,
    p2mpDuplexerBurnDate DisplayString
    }

p2mpDuplexerIndex OBJECT-TYPE
    SYNTAX Integer32(1..100)
    ACCESS not-accessible
    STATUS mandatory
    DESCRIPTION
        "This object, along with ifIndex, uniquely identifies 
        an entry in this table.  Each entry contains 
        information about the duplexer's capabilities and also 
        identifies the associated RF resource."
    ::= { p2mpDuplexerEntry 1 }

p2mpDuplexerRF OBJECT-TYPE
    SYNTAX CwrRfType
--    Rsyntax INTEGER {
--        main(0),
--        diversity(1)
--        }
    ACCESS read-only
    STATUS mandatory
    DESCRIPTION
        "This object identifies the RF resource associated with this
        duplexer."
    ::= { p2mpDuplexerEntry 2 }

p2mpDuplexerLoPassbandMinFreq OBJECT-TYPE
    SYNTAX CwrRfFreqRange
--    Rsyntax Integer32(0..60000000)
--  Units
--    MHz
    ACCESS read-only
    STATUS mandatory
    DESCRIPTION
        "This object identifies the minimum frequency in the low
        passband that this duplexer will pass through without 
        attenuation."
    ::= { p2mpDuplexerEntry 3 }

p2mpDuplexerLoPassbandMaxFreq OBJECT-TYPE
    SYNTAX CwrRfFreqRange
--    Rsyntax Integer32(0..60000000)
--  Units
--    MHz
    ACCESS read-only
    STATUS mandatory
    DESCRIPTION
        "This object identifies the maximum frequency in the low
        passband that this duplexer will pass through without 
        attenuation."
    ::= { p2mpDuplexerEntry 4 }

p2mpDuplexerHiPassbandMinFreq OBJECT-TYPE
    SYNTAX CwrRfFreqRange
--    Rsyntax Integer32(0..60000000)
--  Units
--    MHz
    ACCESS read-only
    STATUS mandatory
    DESCRIPTION
        "This object identifies the minimum frequency in the high
        passband that this duplexer will pass through without 
        attenuation."
    ::= { p2mpDuplexerEntry 5 }

p2mpDuplexerHiPassbandMaxFreq OBJECT-TYPE
    SYNTAX CwrRfFreqRange
--    Rsyntax Integer32(0..60000000)
--  Units
--    MHz
    ACCESS read-only
    STATUS mandatory
    DESCRIPTION
        "This object identifies the maximum frequency in the high
        passband that this duplexer will pass through without 
        attenuation."
    ::= { p2mpDuplexerEntry 6 }

p2mpDuplexerReceivePassband OBJECT-TYPE
    SYNTAX INTEGER {
        loPassband(1),
        hiPassband(2)
        }
    ACCESS read-only
    STATUS mandatory
    DESCRIPTION
        "This object indicates which of the two passbands are being used
         to receive transmissions.  The RF Resource can receive on
         either of the duplexer passbands.
        
         loPassband(1) - The RF Resource is receiving on a frequency
                         in the low passband.
         hiPassband(2) - The RF Resource is receiving on a frequency
                         in the high passband."
    ::= { p2mpDuplexerEntry 7 }

p2mpDuplexerTxInsertionLoss OBJECT-TYPE
    SYNTAX Integer32
--  Units
--    dB
    ACCESS read-only
    STATUS mandatory
    DESCRIPTION
        "This object represents the loss in 'dB' that would result in 
        the transmission path due to the duplexer."
    ::= { p2mpDuplexerEntry 8 }

p2mpDuplexerBurnDate OBJECT-TYPE
    SYNTAX DisplayString
--    Rsyntax OCTET STRING(SIZE(0..255))
    ACCESS read-only
    STATUS mandatory
    DESCRIPTION
        "This object indicates the date when the revision information
        was programmed into non-volatile memory."
    ::= { p2mpDuplexerEntry 9 }

p2mpAntennaTable OBJECT-TYPE
    SYNTAX SEQUENCE OF P2mpAntennaEntry
    ACCESS not-accessible
    STATUS mandatory
    DESCRIPTION
        "This table contains information about the antennas available 
        in the system."
    ::= { p2mpFreqResourceGroup 3 }

p2mpAntennaEntry OBJECT-TYPE
    SYNTAX P2mpAntennaEntry
    ACCESS not-accessible
    STATUS mandatory
    DESCRIPTION
        "An entry is created in this table when the managed system 
        detects a RF resource. The entry is removed when the RF 
        resource is removed from the wireless system."
    INDEX { ifIndex, p2mpAntennaIndex }
    ::= { p2mpAntennaTable 1 }

P2mpAntennaEntry ::= SEQUENCE {
    p2mpAntennaIndex Unsigned32,
    p2mpRfResource CwrRfType,
    p2mpAntennaXDim Unsigned32,
    p2mpAntennaYDim Unsigned32,
    p2mpAntennaType DisplayString,
    p2mpAntennaDescr DisplayString,
    p2mpAntennaGain Unsigned32,
    p2mpAntennaPolarization INTEGER
    }

p2mpAntennaIndex OBJECT-TYPE
    SYNTAX Unsigned32
--    Rsyntax Gauge32
    ACCESS not-accessible
    STATUS mandatory
    DESCRIPTION
        "This object, along with ifIndex, represents the index of this 
               entry in the p2mpAntennaTable."
    ::= { p2mpAntennaEntry 1 }

p2mpRfResource OBJECT-TYPE
    SYNTAX CwrRfType
--    Rsyntax INTEGER {
--        main(0),
--        diversity(1)
--        }
    ACCESS read-only
    STATUS mandatory
    DESCRIPTION
        "This object identifies if the antenna is connected to the main
        or the diversity RF resource."
    ::= { p2mpAntennaEntry 2 }

p2mpAntennaXDim OBJECT-TYPE
    SYNTAX Unsigned32(1..96)
--    Rsyntax Gauge32(1..96)
--  Units
--    Inches
    ACCESS read-write
    STATUS mandatory
    DESCRIPTION
        "This object represents the dimension of the antenna in the
               X direction."
    ::= { p2mpAntennaEntry 3 }

p2mpAntennaYDim OBJECT-TYPE
    SYNTAX Unsigned32(1..96)
--    Rsyntax Gauge32(1..96)
--  Units
--    Inches
    ACCESS read-write
    STATUS mandatory
    DESCRIPTION
        "This object represents the dimension of the antenna in the
               Y direction."
    ::= { p2mpAntennaEntry 4 }

p2mpAntennaType OBJECT-TYPE
    SYNTAX DisplayString(SIZE(0..64))
--    Rsyntax OCTET STRING(SIZE(0..64))
    ACCESS read-write
    STATUS mandatory
    DESCRIPTION
        "This object represents the antenna type. For example, 
               'dish-antenna'."
    ::= { p2mpAntennaEntry 5 }

p2mpAntennaDescr OBJECT-TYPE
    SYNTAX DisplayString(SIZE(0..64))
--    Rsyntax OCTET STRING(SIZE(0..64))
    ACCESS read-write
    STATUS mandatory
    DESCRIPTION
        "This object is used to describe the antenna.  For example,
               it could be used to identify the manufacturer like in
               'Manufactured by Watkins Johnson'."
    ::= { p2mpAntennaEntry 6 }

p2mpAntennaGain OBJECT-TYPE
    SYNTAX Unsigned32(0..60)
--    Rsyntax Gauge32(0..60)
--  Units
--    dBi : decibel Isotropic
    ACCESS read-write
    STATUS mandatory
    DESCRIPTION
        "This object represents the receive and transmit gain 
                of this antenna."
    ::= { p2mpAntennaEntry 7 }

p2mpAntennaPolarization OBJECT-TYPE
    SYNTAX INTEGER {
        vertical(1),
        horizontal(2)
        }
    ACCESS read-only
    STATUS mandatory
    DESCRIPTION
        "This object represents the polarization of the antanna."
    ::= { p2mpAntennaEntry 8 }

p2mpLoopbackTable OBJECT-TYPE
    SYNTAX SEQUENCE OF P2mpLoopbackEntry
    ACCESS not-accessible
    STATUS mandatory
    DESCRIPTION
        "This table provides facilities to establish loopback points to
        exercise various sections of the hardware."
    ::= { p2mpRadioTestGroup 1 }

p2mpLoopbackEntry OBJECT-TYPE
    SYNTAX P2mpLoopbackEntry
    ACCESS not-accessible
    STATUS mandatory
    DESCRIPTION
        "This represents one entry in the p2mpLoopbackTable.  It
        is created when the managed system detects a 
        propDocsWirelessMaclayer interface. The entry is removed
        when the associated propDocsWirelessMaclayer interface 
        is deleted from the ifTable."
    INDEX { ifIndex }
    ::= { p2mpLoopbackTable 1 }

P2mpLoopbackEntry ::= SEQUENCE {
    p2mpLocalLoopbackMode INTEGER,
    p2mpLocalLoopbackAntenna CwrRfType,
    p2mpLocalLoopbackChannel Unsigned32
    }

p2mpLocalLoopbackMode OBJECT-TYPE
    SYNTAX INTEGER {
        noLoopback(1),
        fir(2),
        if(3),
        rf(4)
        }
    ACCESS read-write
    STATUS mandatory
    DESCRIPTION
        "This object is used to configure the system in loopback mode 
        prior to executing some system diagnostic tests.  The user 
        selects the point in the system where the data signal should be
        looped back.  The diagnostic tests outlined in the user manual
        have to be manually executed to determine success or failure.  
        Once all the tests are completed, normal operation is restored
        by setting this object to noLoopback(1).
        
        noLoopback(1)  - no loopback
        fir(2)         - loopback at the Finite Impulse 
                         Response (FIR) module.
        if(3)          - loopback at the IF module.  This 
                         exercises the FIR, and IF modules.
        rf(4)          - loopback at the RF unit. This 
                         exercises the FIR, IF, and RF modules.
                         This mode is supported only when
                         p2mpRfLoopbackSupported is true(1)."
    DEFVAL { noLoopback }
    ::= { p2mpLoopbackEntry 1 }

p2mpLocalLoopbackAntenna OBJECT-TYPE
    SYNTAX CwrRfType
--    Rsyntax INTEGER {
--        main(0),
--        diversity(1)
--        }
    ACCESS read-write
    STATUS mandatory
    DESCRIPTION
        "This object identifies the RF resource used for 
        loopback testing.  This object is not applicable for 
        loopback testing when p2mpLocalLoopbackMode has a 
        value of 'noLoopback(1)'."
    ::= { p2mpLoopbackEntry 2 }

p2mpLocalLoopbackChannel OBJECT-TYPE
    SYNTAX Unsigned32(1..7)
--    Rsyntax Gauge32(1..7)
    ACCESS read-write
    STATUS mandatory
    DESCRIPTION
        "This object identifies the channel being used to  
        loopback the data.  This object is not applicable 
        for loopback testing when p2mpLocalLoopbackMode has 
        a value of 'noLoopback(1)'."
    ::= { p2mpLoopbackEntry 3 }

p2mpLedTable OBJECT-TYPE
    SYNTAX SEQUENCE OF P2mpLedEntry
    ACCESS not-accessible
    STATUS mandatory
    DESCRIPTION
        "Entity (Light emitting diode) LED information.  For each LED on
        the entity, an entry will exist in this table, describing the
        location and current status of that LED."
    ::= { p2mpLedGroup 1 }

p2mpLedEntry OBJECT-TYPE
    SYNTAX P2mpLedEntry
    ACCESS not-accessible
    STATUS mandatory
    DESCRIPTION
        "An entry in the table, containing the LED information.
        The entPhysicalIndex identifies the entity on which the LED's
        are present."
    INDEX { entPhysicalIndex, p2mpLedIndex }
    ::= { p2mpLedTable 1 }

P2mpLedEntry ::= SEQUENCE {
    p2mpLedIndex Integer32,
    p2mpLedType INTEGER,
    p2mpLedState INTEGER
    }

p2mpLedIndex OBJECT-TYPE
    SYNTAX Integer32(1..16)
    ACCESS not-accessible
    STATUS mandatory
    DESCRIPTION
        "For a given entPhysicalIndex, this index value uniquely
        identifies an entry in the p2mpLedTable."
    ::= { p2mpLedEntry 1 }

p2mpLedType OBJECT-TYPE
    SYNTAX INTEGER {
--        interfaceEnable(0),
        majorAlarm(1),
        minorAlarm(2),
        outOfService(3),
        carrier(4),
        transmitData(5),
        receiveData(6)
        }
    ACCESS read-only
    STATUS mandatory
    DESCRIPTION
        "Indicates the type or label of the LED."
    ::= { p2mpLedEntry 2 }

p2mpLedState OBJECT-TYPE
    SYNTAX INTEGER {
--        off(0),
        green(1),
        yellow(2)
        }
    ACCESS read-only
    STATUS mandatory
    DESCRIPTION
        "Indicates the state of the LED."
    ::= { p2mpLedEntry 3 }

p2mpSuRadioPhyTable OBJECT-TYPE
    SYNTAX SEQUENCE OF P2mpSuRadioPhyEntry
    ACCESS not-accessible
    STATUS mandatory
    DESCRIPTION
        "This table contains information about the currently configured
        physical layer interfaces in the subscriber unit."
    ::= { p2mpRadioSuObjects 1 }

p2mpSuRadioPhyEntry OBJECT-TYPE
    SYNTAX P2mpSuRadioPhyEntry
    ACCESS not-accessible
    STATUS mandatory
    DESCRIPTION
        "An entry containing the radio configuration information
         of the propDocsWirelessMaclayer interface in the 
         subscriber unit.
        
         The entry is created when a propDocsWirelessMaclayer
         interface is detected in the subscriber unit. The entry
         is deleted when the associated propDocsWirelessMaclayer
         interface is removed."
    INDEX { ifIndex }
    ::= { p2mpSuRadioPhyTable 1 }

P2mpSuRadioPhyEntry ::= SEQUENCE {
    p2mpSuTxMuteEnable TruthValue,
    p2mpSuTxMuteDuration Unsigned32
    }

p2mpSuTxMuteEnable OBJECT-TYPE
    SYNTAX TruthValue
--    Rsyntax INTEGER {
--        true(1),
--        false(2)
--        }
    ACCESS read-only
    STATUS mandatory
    DESCRIPTION
        "When true(1), this object indicates the subscriber unit 
        transmission has been turned off for a duration indicated by
        p2mpSuTxMuteDuration.  When false(2), this object indicates 
        that the subscriber unit is transmitting."
    ::= { p2mpSuRadioPhyEntry 1 }

p2mpSuTxMuteDuration OBJECT-TYPE
    SYNTAX Unsigned32(1..65535)
--    Rsyntax Gauge32(1..65535)
--  Units
--    minutes
    ACCESS read-write
    STATUS mandatory
    DESCRIPTION
        " This object indicates the duration of time (in minutes) 
        for which the subscriber transmission will be turned off. "
    ::= { p2mpSuRadioPhyEntry 2 }

p2mpSuPowerScanTable OBJECT-TYPE
    SYNTAX SEQUENCE OF P2mpSuPowerScanEntry
    ACCESS not-accessible
    STATUS mandatory
    DESCRIPTION
        "This table contains information about the receive power 
        measured at the different possible center frequencies."
    ::= { p2mpRadioSuObjects 2 }

p2mpSuPowerScanEntry OBJECT-TYPE
    SYNTAX P2mpSuPowerScanEntry
    ACCESS not-accessible
    STATUS mandatory
    DESCRIPTION
        "An entry containing the power related status 
        information of the propDocsWirelessMaclayer 
        interface in the subscriber unit.
        
        The entry is created when a propDocsWirelessMaclayer 
        interface is detected in the subscriber unit. The entry 
        is deleted after the associated propDocsWirelessMaylayer
        interface is removed."
    INDEX { ifIndex, p2mpSuPowerScanIndex }
    ::= { p2mpSuPowerScanTable 1 }

P2mpSuPowerScanEntry ::= SEQUENCE {
    p2mpSuPowerScanIndex Integer32,
    p2mpSuCenterFrequency CwrRfFreqRange,
    p2mpSuMeasuredPower Integer32
    }

p2mpSuPowerScanIndex OBJECT-TYPE
    SYNTAX Integer32(1..20)
    ACCESS not-accessible
    STATUS mandatory
    DESCRIPTION
        "For a given ifIndex, this index value uniquely
        identifies an entry in the p2mpSuPowerScanTable."
    ::= { p2mpSuPowerScanEntry 1 }

p2mpSuCenterFrequency OBJECT-TYPE
    SYNTAX CwrRfFreqRange
--    Rsyntax Integer32(0..60000000)
--  Units
--    KHz
    ACCESS read-only
    STATUS mandatory
    DESCRIPTION
        "This object indicates the frequency at which the receive power
        at the subscriber unit was measured."
    ::= { p2mpSuPowerScanEntry 2 }

p2mpSuMeasuredPower OBJECT-TYPE
    SYNTAX Integer32(-127..50)
--  Units
--    dBm
    ACCESS read-only
    STATUS mandatory
    DESCRIPTION
        "This object represents the power measured at the frequency 
        indicated by p2mpSuCenterFrequency."
    ::= { p2mpSuPowerScanEntry 3 }

p2mpHeAlcTable OBJECT-TYPE
    SYNTAX SEQUENCE OF P2mpHeAlcEntry
    ACCESS not-accessible
    STATUS mandatory
    DESCRIPTION
        "This table contains Automatic Line Control (ALC) configuration 
        information.  It is supported at the head end only."
    ::= { p2mpRadioHeObjects 1 }

p2mpHeAlcEntry OBJECT-TYPE
    SYNTAX P2mpHeAlcEntry
    ACCESS not-accessible
    STATUS mandatory
    DESCRIPTION
        "An entry containing the ALC configuration information 
        the propDocsWirelessMaylayer interface at the head end.
        
        The entry is created when a propDocsWirelessMaclayer 
        interface is detected in the head end unit. The entry is
        deleted after the associated propDocsWirelessMaclayer 
        interface is removed."
    INDEX { ifIndex }
    ::= { p2mpHeAlcTable 1 }

P2mpHeAlcEntry ::= SEQUENCE {
    p2mpHeAlcEnable TruthValue,
    p2mpHeAlcInterval Unsigned32,
    p2mpHeAlcNumMiniSlots Unsigned32
    }

p2mpHeAlcEnable OBJECT-TYPE
    SYNTAX TruthValue
--    Rsyntax INTEGER {
--        true(1),
--        false(2)
--        }
    ACCESS read-write
    STATUS mandatory
    DESCRIPTION
        "This object is used to enable/disable ALC at the Head End.  A
        value of true(1), indicates that ALC is enabled."
    ::= { p2mpHeAlcEntry 1 }

p2mpHeAlcInterval OBJECT-TYPE
    SYNTAX Unsigned32(32..1024)
--    Rsyntax Gauge32(32..1024)
--  Units
--    milliseconds
    ACCESS read-write
    STATUS mandatory
    DESCRIPTION
        "This object represents the scheduling interval.  It is the
        regular interval at which the ALC grant in Map is transmitted 
        to the SU's"
    ::= { p2mpHeAlcEntry 2 }

p2mpHeAlcNumMiniSlots OBJECT-TYPE
    SYNTAX Unsigned32(1..4)
--    Rsyntax Gauge32(1..4)
    ACCESS read-write
    STATUS mandatory
    DESCRIPTION
        "This indicates the number of minislots within each grant."
    ::= { p2mpHeAlcEntry 3 }

p2mpHeIntFreqTable OBJECT-TYPE
    SYNTAX SEQUENCE OF P2mpHeIntFreqEntry
    ACCESS not-accessible
    STATUS mandatory
    DESCRIPTION
        "This table contains information about the state of the 
        intermediate frequency subsystem in the radio system.  This
        table is supported at the head end only."
    ::= { p2mpRadioHeObjects 2 }

p2mpHeIntFreqEntry OBJECT-TYPE
    SYNTAX P2mpHeIntFreqEntry
    ACCESS not-accessible
    STATUS mandatory
    DESCRIPTION
        "The entry of this table is created when the managed system 
        detects a propDocsWirelessMaclayer interface in the head
        end unit. 
        The entry is deleted when the associated 
        propDocsWirelessMaclayer interface is removed."
    INDEX { ifIndex }
    ::= { p2mpHeIntFreqTable 1 }

P2mpHeIntFreqEntry ::= SEQUENCE {
    p2mpHeIfTxOscState CwrOscState,
    p2mpHeIfRxOscState CwrOscState,
    p2mpHeIfRefOscState CwrOscState,
    p2mpHeIfInpFreq Unsigned32,
    p2mpHeIfOutFreq Unsigned32,
    p2mpHeTrapEnable TruthValue
    }

p2mpHeIfTxOscState OBJECT-TYPE
    SYNTAX CwrOscState
--    Rsyntax INTEGER {
--        oscillatorOk(1),
--        osccillatorBad(2)
--        }
    ACCESS read-only
    STATUS mandatory
    DESCRIPTION
        "This object indicates the state of the IF transmit oscillator.
        The oscillator must be in oscillatorOk(1) state for the system 
               to function properly."
    ::= { p2mpHeIntFreqEntry 1 }

p2mpHeIfRxOscState OBJECT-TYPE
    SYNTAX CwrOscState
--    Rsyntax INTEGER {
--        oscillatorOk(1),
--        osccillatorBad(2)
--        }
    ACCESS read-only
    STATUS mandatory
    DESCRIPTION
        "This object indicates the state of the IF receive oscillator. 
        The oscillator must be in oscillatorOk(1) state for the system 
               to function properly."
    ::= { p2mpHeIntFreqEntry 2 }

p2mpHeIfRefOscState OBJECT-TYPE
    SYNTAX CwrOscState
--    Rsyntax INTEGER {
--        oscillatorOk(1),
--        osccillatorBad(2)
--        }
    ACCESS read-only
    STATUS mandatory
    DESCRIPTION
        "This object indicates the state of the IF reference oscillator.
        The oscillator must be in oscillatorOk(1) state for the system 
        to function properly."
    ::= { p2mpHeIntFreqEntry 3 }

p2mpHeIfInpFreq OBJECT-TYPE
    SYNTAX Unsigned32(1000..500000)
--    Rsyntax Gauge32(1000..500000)
--  Units
--    KHz
    ACCESS read-only
    STATUS mandatory
    DESCRIPTION
        "This object represents the IF input frequency."
    ::= { p2mpHeIntFreqEntry 4 }

p2mpHeIfOutFreq OBJECT-TYPE
    SYNTAX Unsigned32(1000..500000)
--    Rsyntax Gauge32(1000..500000)
--  Units
--    KHz
    ACCESS read-only
    STATUS mandatory
    DESCRIPTION
        "This object represents the IF output frequency."
    ::= { p2mpHeIntFreqEntry 5 }

p2mpHeTrapEnable OBJECT-TYPE
    SYNTAX TruthValue
--    Rsyntax INTEGER {
--        true(1),
--        false(2)
--        }
    ACCESS read-write
    STATUS mandatory
    DESCRIPTION
        "When set to true(1), this enables the notifications
        that are specific to the head end. When set to false(2), 
        these notifications are disabled."
    DEFVAL { true }
    ::= { p2mpHeIntFreqEntry 6 }

p2mpRadioPhyFailNotification TRAP-TYPE
-- Reverse mappable trap
    ENTERPRISE p2mpPhyMIBNotificationPrefix
    VARIABLES {
        p2mpLastPhyFailureType, p2mpLastPhyFailureReason }
--  Status
--    mandatory
    DESCRIPTION
        "A p2mpRadioPhyFailNotification is sent if the value of
        p2mpLastPhyFailureType changes due to the new failure 
        being detected in the Radio interface."
    ::= 1

p2mpTrapRfSupplyVoltage TRAP-TYPE
-- Reverse mappable trap
    ENTERPRISE p2mpPhyMIBNotificationPrefix
    VARIABLES {
        p2mpRfSupplyVoltageState }
--  Status
--    mandatory
    DESCRIPTION
        "The supply voltage to the RF resource has changed. 
        The p2mpRfSupplyVoltageState specifies whether the supply 
        voltage is in spec or not."
    ::= 2

p2mpTrapRfRxOsc TRAP-TYPE
-- Reverse mappable trap
    ENTERPRISE p2mpPhyMIBNotificationPrefix
    VARIABLES {
        p2mpRfRxOscState }
--  Status
--    mandatory
    DESCRIPTION
        "The RF receive frequency oscillator has changed state.
        The p2mpRfRxOscState specifies the current state of 
               the oscillator."
    ::= 3

p2mpTrapRfTxOsc TRAP-TYPE
-- Reverse mappable trap
    ENTERPRISE p2mpPhyMIBNotificationPrefix
    VARIABLES {
        p2mpRfTxOscState }
--  Status
--    mandatory
    DESCRIPTION
        "The RF transmit frequency oscillator has changed state.
        The p2mpRfRxOscState specifies the state of the 
        oscillator."
    ::= 4

p2mpTrapRfTemp TRAP-TYPE
-- Reverse mappable trap
    ENTERPRISE p2mpPhyMIBNotificationPrefix
    VARIABLES {
        p2mpRfTemperature }
--  Status
--    mandatory
    DESCRIPTION
        "The temperature of the RF module identified by p2mpRfIndex
        has exceeded a defined reference."
    ::= 5

p2mpTrapRfCommLinkError TRAP-TYPE
-- Reverse mappable trap
    ENTERPRISE p2mpPhyMIBNotificationPrefix
    VARIABLES {
        p2mpRfType }
--  Status
--    mandatory
    DESCRIPTION
        "This trap indicates that the host and the IF module cannot 
        communicate with the RF resource identified by p2mpRfType."
    ::= 6

p2mpTrapTxPower TRAP-TYPE
-- Reverse mappable trap
    ENTERPRISE p2mpPhyMIBNotificationPrefix
    VARIABLES {
        p2mpRfType }
--  Status
--    mandatory
    DESCRIPTION
        "This trap indicates that the transmit power for the RF resource 
        identified by p2mpRfType exceeded a predefined threshold."
    ::= 7

p2mpTrapRfStatusChange TRAP-TYPE
-- Reverse mappable trap
    ENTERPRISE p2mpPhyMIBNotificationPrefix
    VARIABLES {
        p2mpRfStatus }
--  Status
--    mandatory
    DESCRIPTION
        "This trap indicates that the RF resource either came online(1)
        or went offline(2)."
    ::= 8

p2mpTrapHeIfRxOsc TRAP-TYPE
-- Reverse mappable trap
    ENTERPRISE p2mpPhyMIBNotificationPrefix
    VARIABLES {
        p2mpHeIfRxOscState }
--  Status
--    mandatory
    DESCRIPTION
        "The IF receive frequency oscillator has changed state."
    ::= 9

p2mpTrapHeIfTxOsc TRAP-TYPE
-- Reverse mappable trap
    ENTERPRISE p2mpPhyMIBNotificationPrefix
    VARIABLES {
        p2mpHeIfTxOscState }
--  Status
--    mandatory
    DESCRIPTION
        "The IF transmit frequency oscillator has changed state."
    ::= 10

p2mpTrapHeIfExtRefOsc TRAP-TYPE
-- Reverse mappable trap
    ENTERPRISE p2mpPhyMIBNotificationPrefix
    VARIABLES {
        p2mpHeIfRefOscState }
--  Status
--    mandatory
    DESCRIPTION
        "The IF Reference Frequency oscillator has changed state."
    ::= 11

p2mpCommonRadioGroup OBJECT IDENTIFIER ::= { p2mpRadioPhyGroups 1 }
-- OBJECT-GROUP
--  Status
--    mandatory
--  Descr
--    Mandatory group of objects implemented to configure a 
--     point to multipoint wireless radio.
--  objects
--    p2mpSelfTest, p2mpDiversityAntennaPresent, p2mpCableLoss, 
--    p2mpCableLossDiversity, p2mpDenyService, p2mpClockRefExt, 
--    p2mpCommonTrapEnable, p2mpLastPhyFailureType, 
--    p2mpLastPhyFailureReason, p2mpLedType, p2mpLedState

p2mpCommonRfGroup OBJECT IDENTIFIER ::= { p2mpRadioPhyGroups 2 }
-- OBJECT-GROUP
--  Status
--    mandatory
--  Descr
--    Mandatory group of objects implemented to tune the phy quality 
--    in a point to multipoint wireless radio.
--  objects
--    p2mpRfType, p2mpRfOpMode, p2mpTxFreqRangeMin, 
--    p2mpTxFreqRangeMax, p2mpRxFreqRangeMin, p2mpRxFreqRangeMax, 
--    p2mpMinTxPower, p2mpMaxTxPower, p2mpRfTxOscState, 
--    p2mpRfRxOscState, p2mpRfTemperature, p2mpRfSupplyVoltageState, 
--    p2mpRfStatus, p2mpRfLoopbackSupported, p2mpDuplexerRF, 
--    p2mpDuplexerLoPassbandMinFreq, p2mpDuplexerLoPassbandMaxFreq, 
--    p2mpDuplexerHiPassbandMinFreq, p2mpDuplexerHiPassbandMaxFreq, 
--    p2mpDuplexerReceivePassband, p2mpDuplexerTxInsertionLoss, 
--    p2mpDuplexerBurnDate

p2mpCommonTestGroup OBJECT IDENTIFIER ::= { p2mpRadioPhyGroups 3 }
-- OBJECT-GROUP
--  Status
--    mandatory
--  Descr
--    Mandatory group of objects implemented in the point to 
--     multi point wireless system for Testing the link.
--  objects
--    p2mpLocalLoopbackMode, p2mpLocalLoopbackAntenna, 
--    p2mpLocalLoopbackChannel

p2mpRadioSuGroup OBJECT IDENTIFIER ::= { p2mpRadioPhyGroups 5 }
-- OBJECT-GROUP
--  Status
--    mandatory
--  Descr
--    Group of objects implemented at the Subscriber unit.
--  objects
--    p2mpSuTxMuteEnable, p2mpSuTxMuteDuration, 
--    p2mpSuCenterFrequency, p2mpSuMeasuredPower

p2mpRadioHeGroup OBJECT IDENTIFIER ::= { p2mpRadioPhyGroups 6 }
-- OBJECT-GROUP
--  Status
--    mandatory
--  Descr
--    Group of objects implemented at the Head End.
--  objects
--    p2mpHeAlcEnable, p2mpHeAlcInterval, p2mpHeAlcNumMiniSlots, 
--    p2mpHeIfTxOscState, p2mpHeIfRxOscState, p2mpHeIfRefOscState, 
--    p2mpHeIfInpFreq, p2mpHeIfOutFreq, p2mpHeTrapEnable

p2mpRadioAntennaGroup OBJECT IDENTIFIER ::= { p2mpRadioPhyGroups 8 }
-- OBJECT-GROUP
--  Status
--    mandatory
--  Descr
--    Group of objects implemented in the point to multi point wireless
--     system for managing the antennas available in the system.
--  objects
--    p2mpRfResource, p2mpAntennaXDim, p2mpAntennaYDim, 
--    p2mpAntennaType, p2mpAntennaDescr, p2mpAntennaGain, 
--    p2mpAntennaPolarization

p2mpRadioPhyCompliance OBJECT IDENTIFIER ::= { p2mpRadioPhyCompliances 1 }
-- MODULE-COMPLIANCE
--  Status
--    mandatory
--  Descr
--    The compliance statement for devices that implement Point to 
--    Multipoint wireless interfaces compliant with the Cisco Systems 
--    Inc. specification.
--  Module
--    >>current<<
--   MandGroup
--    p2mpCommonRadioGroup
--   MandGroup
--    p2mpCommonRfGroup
--   MandGroup
--    p2mpCommonTestGroup
--   OptGroup
--    p2mpRadioSuGroup
--   OptGroup
--    p2mpRadioHeGroup
--   OptGroup
--    p2mpRadioAntennaGroup


END
