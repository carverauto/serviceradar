-- MIB created 2/10/100 21:29:13, by
--   SMIC (the next generation) version 1.6.29, November 22, 1994.

CISCO-RTTMON-MIB DEFINITIONS ::= BEGIN

-- From file: "CISCO-RTTMON-MIB-120_5_T.my"

IMPORTS
    Integer32, Counter32, Gauge32, TimeTicks
            FROM SNMPv2-SMI-v1
    OBJECT-TYPE
            FROM RFC-1212
    TRAP-TYPE
            FROM RFC-1215
    DisplayString, TruthValue, RowStatus, TimeInterval, TimeStamp
            FROM SNMPv2-TC-v1
    ciscoMgmt
            FROM CISCO-SMI
    OwnerString
            FROM IF-MIB;

ciscoRttMonMIB OBJECT IDENTIFIER ::= { ciscoMgmt 42 }
-- MODULE-IDENTITY
--  LastUpdated
--    9903110000Z
--  OrgName
--    Cisco IBU Engineering Working Group
--  ContactInfo
--    Cisco Systems, Inc.
--    Customer Service 
--    
--    Postal: 170 W Tasman Drive
--    San Jose, CA 95134
--    
--    Tel: +1 800 553 NETS
--    
--    rangers-rtr@cisco.com
--  Descr
--    This module defines a MIB for Round Trip Time 
--    (RTT) monitoring of a list of targets, using a 
--    variety of protocols.
--    
--    The table structure overview is a follows (t: 
--     indicates a table, at:  indicates an augmented 
--     table, and it:  indicates table with the same 
--     indices/control as parent table):
--    
--    RTTMON MIB
--    |=== Application Group
--    |    |=== Application Identity
--    |    |=== Application Capabilities
--    |    |=== Application Reset
--    |    |t== Supported RTT Types
--    |         |=== Truth Value
--    |    |t== Supported Protocols
--    |         |=== Truth Value
--    |    |t== Application Preconfigured
--    |         |=== Script Names
--    |         |=== File Paths
--    |
--    |=== Overall Control Group
--    |    |t== Master Definitions Table
--    |    |    |=== Global Configuration Definitions
--    |    |         |=== Config for a single RTT Life
--    |    |    |it- Echo Specific Configuration
--    |    |    |it- Echo Path Hop Address Configuration
--    |    |    |it- File I/O Specific Configuration
--    |    |    |it- Script Specific Configuration
--    |    |    |at- Schedule Configuration
--    |    |    |at- Reaction Specific Config
--    |    |    |at- Statistics Capture Configuration
--    |    |    |at- History Collection Configuration
--    |    |    |at- Monitoring Operational State
--    |    |    |at- Last RTT operation
--    |    |
--    |    |t== Reaction Trigger Table
--    |         |at- Reaction Trigger Operational State
--    |
--    |=== Statistics Collection Group
--    |    |t== Statistics Capture Table
--    |         |=== Captured Statistics
--    |              |=== Path Information
--    |              |=== Distribution Capture 
--    |              |=== Mean and Deviation Capture
--    |         |it- Statistics Collection Table
--    |    |it- Statistics Totals Table
--    |    |t== HTTP Stats Table
--    |    |t== Jitter Stats Table
--    |
--    |=== History Collection Group
--    |    |t== History Collection Table
--    |         |== Path Information
--    |         |== Completion Information per operation
--    |
--    |=== Latest Operation Group
--    |    |t== Latest HTTP Oper Table
--    |    |t== Latest Jitter Oper Table
--    
--    DEFINITIONS:
--      conceptual RTT control row - 
--              This is a row in the 'Overall Control 
--              Group'.  This row is indexed via the 
--              rttMonCtrlAdminIndex object.  This row 
--              is spread across multiple real tables 
--              in the 'Overall Control Group'.
--      probe -
--              This is the entity that executes via a 
--              conceptual RTT control row and populates
--              a conceptual statistics row and a 
--              conceptual history row.
--      Rtt operation -
--              This is a single operation performed by
--              a probe.  This operation can be a single
--              Rtt attempt/completion or a group of Rtt
--              attempts/completions that produce one
--              operation table entry.
--              
--    ARR Protocol Definition:
--    
--    The format of the RTT Asymmetric Request/Responses 
--     (ARR) protocol is as follows:
--    
--      The ARR Header (total of 12 octets): 
--    
--      4 octet -> eyecatcher: 'WxYz'
--      1 octet -> version   : 0x01 - protocol version
--      1 octet -> command   : 0x01 - logoff request
--                             0x02 - echo request
--                             0x03 - echo response
--                             0x04 - software version request
--                             0x05 - software version response
--      2 octet -> sequence number (Network Byte Order)
--      4 octet -> response data size (Network Byte Order)
--    
--      The ARR Data:
--    
--      n octets -> request/response data
--                            : 'AB..ZAB..ZAB..' 
--    
--      For software version request/response the 
--       protocol version octet will contain the version
--       number of the responder.  Thus the sequence 
--       number, etc will not be included.
--    
--      For snaLU0EchoAppl and snaLU2EchoAppl all character 
--       fields will be in EBCDIC.
--    
--      The response data should be appended to the 
--       origin request data.  This allows data  
--       verification to check the data that flows in 
--       both directions.  If the response data size is
--       smaller than the request data size the original
--       request data will be truncated.  
--    
--      An example would be:
--        Request:        /       Response:
--        'WxYz'          /       'WxYz'
--        0x01            /       0x01
--        0x02            /       0x03
--        0x0001          /       0x0001
--        0x00000008      /       0x00000008
--        'ABCDEF'        /       'ABCDEFGH'
--    
--      NOTE: We requested 8 bytes in the response and 
--            the response had 8 bytes.  The size of the
--            request data has no correlation to the
--            size of the response data.
--    
--    NOTE:  For native RTT request/response (i.e. 
--           ipIcmpecho) operations both the 'Header' 
--           and 'Data' will be included.  Only the 
--           'sequence number' in the Header will be 
--           valid.
--    
--    NOTE:  For non-connection oriented protocol the 
--           initial RTT request/response operation will
--           be preceded with an RTT request/response 
--           operation to the target address to force 
--           path exploration and to prove 
--           connectivity.  The History collection table
--           will contain these responses, but the 
--           Statistics capture table will omit them to
--           prevent skewed results.
--  RevDate
--    9903110000Z
--  RevDescr
--    the following modifications are done in the MIB
--    (a) new tables created
--    - rttMonLatestHTTPOperTable
--    - rttMonLatestJitterOperTable
--    - rttMonHTTPStatsTable
--    - rttMonJitterStatsTable
--    (b) some columns added to rttMonEchoAdminTable and
--    (c) some objects obsoleted

ciscoRttMonObjects OBJECT IDENTIFIER ::= { ciscoRttMonMIB 1 }
rttMonAppl      OBJECT IDENTIFIER ::= { ciscoRttMonObjects 1 }
rttMonCtrl      OBJECT IDENTIFIER ::= { ciscoRttMonObjects 2 }
rttMonStats     OBJECT IDENTIFIER ::= { ciscoRttMonObjects 3 }
rttMonHistory   OBJECT IDENTIFIER ::= { ciscoRttMonObjects 4 }
rttMonLatestOper OBJECT IDENTIFIER ::= { ciscoRttMonObjects 5 }
rttMonNotificationsPrefix OBJECT IDENTIFIER ::= { ciscoRttMonMIB 2 }
rttMonNotifications OBJECT IDENTIFIER ::= { rttMonNotificationsPrefix 0 }
ciscoRttMonMibConformance OBJECT IDENTIFIER ::= { ciscoRttMonMIB 3 }
ciscoRttMonMibCompliances OBJECT IDENTIFIER ::= { ciscoRttMonMibConformance 1 }
ciscoRttMonMibGroups OBJECT IDENTIFIER ::= { ciscoRttMonMibConformance 2 }

RttReset ::= INTEGER {
        ready(1),
        reset(2)
        }
-- TEXTUAL-CONVENTION
--  Status
--    mandatory
--  Descr
--    Represents the reset control object.
--    
--    When this object is set to reset, the defined
--    reset operation will take place.
--    
--    When this object is read (with a get), during the
--    the reset operation the value 'reset' will be
--    returned.  At all other times the value 'ready'
--    will be returned.

RttMonOperation ::= INTEGER {
        httpGet(1),
        httpRaw(2)
        }
-- TEXTUAL-CONVENTION
--  Status
--    mandatory
--  Descr
--    The following are specific RTT operations for a 
--    particular probe type:
--    httpGet(1)            - HTTP get request
--    httpRaw(2)            - HTTP request with user defined payload

RttResponseSense ::= INTEGER {
        ok(1),
        disconnected(2),
        overThreshold(3),
        timeout(4),
        busy(5),
        notConnected(6),
        dropped(7),
        sequenceError(8),
        verifyError(9),
        applicationSpecific(10),
        dnsServerTimeout(11),
        tcpConnectTimeout(12),
        httpTransactionTimeout(13),
        dnsQueryError(14),
        httpError(15),
        error(16)
        }
-- TEXTUAL-CONVENTION
--  Status
--    mandatory
--  Descr
--    These are the defined values for a completion status
--    of a RTT operation.  
--    
--    ok(1)            - a valid completion occurred and
--                        timed successfully
--    disconnected(2)  - the operation did not occur because
--                        the connection to the target
--                        was lost
--    overThreshold(3) - a valid completion was received but
--                        the completion time exceeded a
--                        threshold value
--    timeout(4)       - an operation timed out; no completion
--                        time recorded
--    busy(5)          - the operation did not occur because a
--                        previous operation is still
--                        outstanding
--    notConnected(6)  - the operation did not occur because no
--                        connection (session) exists with the
--                        target
--    dropped(7)       - the operation did not occur due to lack
--                        of internal resource
--    sequenceError(8) - a completed operation did not contain 
--                        the correct sequence id; no completion
--                        time recorded
--    verifyError(9)   - a completed operation was received, but
--                        the data it contained did not match
--                        the expected data; no completion time 
--                        recorded
--    applicationSpecific(10) 
--                     - the application generating the operation
--                        had a specific error
--    dnsServerTimeout(11) 
--    - DNS Server Timeout
--    tcpConnectTimeout(12)
--    - TCP Connect Timeout
--    httpTransactionTimeout(13)
--    - HTTP Transaction Timeout
--    dnsQueryError(14)
--    - DNS Query error (because of unknown address 
--    etc.,)
--    httpError(15)
--    - HTTP Response StatusCode is not OK (200) then
--    HTTP error is set. 
--    error(16)
--    - if there are socket failures or some other 
--    errors not relavant to the actual probe, they 
--    are recorded under this error

RttMonRttType ::= INTEGER {
        echo(1),
        pathEcho(2),
        fileIO(3),
        script(4),
        udpEcho(5),
        tcpConnect(6),
        http(7),
        dns(8),
        jitter(9),
        dlsw(10),
        dhcp(11)
        }
-- TEXTUAL-CONVENTION
--  Status
--    mandatory
--  Descr
--    Specifies the type of RTT operation to be performed.
--    
--    The value 'echo' will cause the RTT application to
--    perform a timed echo request/response operation directed
--    at the 'RttMonTargetAddress'.
--    
--    The value 'pathEcho' will cause the RTT application
--    to perform path discovery to the 'RttMonTargetAddress', 
--    then it will perform a timed echo request/response 
--    operation directed at the each hop along the path.  
--    This operation will provide two types of information, 
--    first the path and second the time delay along the path.
--    
--    NOTE:  The 'pathEcho' time delay operation is a heuristic
--           measurement because an intermediate hop may forward
--           the different echo request/response at different
--           rates.  Thus the time delay difference between two
--           hops along a path may contain very little 'true'
--           statistical meaning. 
--    
--    The value 'fileIO' will cause the RTT application to 
--    write, read, or write/read a file to a preconfigured 
--    file server.
--    
--    The value 'script' will cause the RTT application to
--    execute a preconfigured script.
--    
--    The value 'udpEcho' will cause the RTT application
--    to perform a timed udp packet send/receive operation 
--    directed at the 'RttMonTargetAddress'.
--    
--    The value 'tcpConnect' will cause the RTT application
--    to perform a timed tcp connect operation directed at the 
--    'RttMonTargetAddress'.
--    
--    The value 'http' will cause the RTT application
--    to perform a download of the object specified in the URL.
--    
--    The value 'dns' will cause the RTT application
--    to perform a name lookup of an IP Address or a hostname.
--    
--    The value 'jitter' will cause the RTT application
--    to perform delay variance analysis.
--    
--    The value 'dlsw' will cause the RTT application
--    to perform a keepalive operation to measure the response 
--    time of a DLSw peer.
--    
--    The value 'dhcp' will cause the RTT application
--    to perform a IP Address lease request/teardown operation.

RttMonProtocol ::= INTEGER {
        notApplicable(1),
        ipIcmpEcho(2),
        ipUdpEchoAppl(3),
        snaRUEcho(4),
        snaLU0EchoAppl(5),
        snaLU2EchoAppl(6),
        snaLU62Echo(7),
        snaLU62EchoAppl(8),
        appleTalkEcho(9),
        appleTalkEchoAppl(10),
        decNetEcho(11),
        decNetEchoAppl(12),
        ipxEcho(13),
        ipxEchoAppl(14),
        isoClnsEcho(15),
        isoClnsEchoAppl(16),
        vinesEcho(17),
        vinesEchoAppl(18),
        xnsEcho(19),
        xnsEchoAppl(20),
        apolloEcho(21),
        apolloEchoAppl(22),
        netbiosEchoAppl(23),
        ipTcpConn(24),
        httpAppl(25),
        dnsAppl(26),
        jitterAppl(27),
        dlswAppl(28),
        dhcpAppl(29)
        }
-- TEXTUAL-CONVENTION
--  Status
--    mandatory
--  Descr
--    Specifies the protocol to be used to perform the timed
--    echo request/response.  The following protocols are
--    defined:
--    
--    NOTE: All protocols that end in 'Appl' will support
--          the asymetric request/response (ARR) protocol.  
--          See the DESCRIPTION for ciscoRttMonMIB for a
--          complete description of the asymetric 
--          request/response protocol.
--    
--    notApplicable     - no protocol is defined
--    ipIcmpEcho        - uses Echo Request/Reply as defined
--                         in RFC792 for Internet Protocol
--                         networks
--    ipUdpEchoAppl     - uses the UDP based echo server
--    snaRUEcho         - uses the REQECHO and ECHOTEST RU's
--                         to an SSCP over an SNA LU-SSCP
--                         session
--    snaLU0EchoAppl    - uses test RU's sent to the Echo 
--                         Server over an SNA LU0-LU0 session
--    snaLU2EchoAppl    - uses test RU's sent to the Echo 
--                         Server over an SNA LU2-LU2 session
--    snaLU62Echo       - uses the native appn ping ie. aping 
--    snaLU62EchoAppl   - uses test RU's sent to the ARR
--                         Echo Server over an SNA LU6.2-LU6.2
--                         session
--    appleTalkEcho     - uses Echo Request/Reply as defined
--                         for appleTalk networks
--    appleTalkEchoAppl - uses the appleTalk based echo
--                         server
--    decNetEcho        - uses Echo Request/Reply as defined
--                         for DECNet networks
--    decNetEchoAppl    - uses the DECnet based echo server
--    ipxEcho           - uses Echo Request/Reply as defined
--                         for Novell IPX networks
--    ipxEchoAppl       - uses the Novel IPX based echo
--                         server
--    isoClnsEcho       - uses Echo Request/Reply as defined
--                         for ISO CLNS networks
--    isoClnsEchoAppl   - uses the ISO CLNS based echo
--                         server
--    vinesEcho         - uses Echo Request/Reply as defined
--                         for VINES networks
--    vinesEchoAppl     - uses the VINES based echo server
--    xnsEcho           - uses Echo Request/Reply as defined
--                         for XNS networks
--    xnsEchoAppl       - uses the XNS based echo server
--    apolloEcho        - uses Echo Request/Reply as defined
--                         for APOLLO networks
--    apolloEchoAppl    - uses the APOLLO based echo
--                         server
--    netbiosEchoAppl   - uses the netbios based echo
--                         server
--    ipTcpConn         - uses the tcp's connect mechanism
--    httpAppl          - uses udp for name resolution, 
--    tcp connect and tcp data transfer
--    mechanisms for HTTP data download
--    from a particular HTTP Server
--    dnsAppl           - uses udp for name resolution
--    jitterAppl        - uses udp for packet transfers
--    dlswAppl          - uses tcp for sending keepalives
--    dhcpAppl          - uses udp for sending dhcp requests

RttMonTargetAddress ::= OCTET STRING
-- TEXTUAL-CONVENTION
--  Status
--    mandatory
--  Descr
--    A string which specifies the address of the target for 
--    the RTT operation; a value of RttMonTargetAddress
--    which corresponds to a 'broadcast' address is disallowed.
--    
--    The interpretation of this string depends on the type of
--    RTT operation selected, as specified by RttMonProtocol; 
--    consequently, this object cannot be created until 
--    RttMonProtocol has been created (or must be in the same 
--    PDU).
--    
--    SNA addresses will be provided in ASCII, but will be
--    converted to EBCDIC
--    
--    It is interpreted as follows, for the specified values of
--    RttMonProtocol:
--    
--    ipIcmpEcho, ipUdpEchoAppl, ipTcpConn, jitterAppl, dlswAppl,
--    dnsAppl, httpAppl, and dhcpAppl
--         - 4 octets
--    snaRUEcho
--         - N octets, containing the value of the sna
--            HOSTNAME of which the SSCP LU will be used
--            for the operation.  For many systems this value
--            can be empty, and the system will use the
--            implied SSCP LU.  For example 'NSPECHO'.
--    snaLU0EchoAppl and snaLU2EchoAppl 
--         - N octets, the first x octets are the HOSTNAME
--            (Alternatively, this could be a PU name defined
--            to transport to the desired HOST), the second
--            y octets are the APPLID, and the last z octets 
--            are the MODENAME of the Echo Server (blank 
--            for a MODENAME default). The address will be 
--            encoded with a size byte preceding each of 
--            the x y and z called s. For example sxsysz 
--            as in '0x06CWBC060x07NSPECHO0x00' where 
--            HOSTNAME = CWBC06, APPLID = NSPECHO, and 
--            MODENAME is defaulted to 8 blanks.  
--            NOTE: MODENAME is either size 0 or 8.
--    snaLU62Echo and snaLU62EchoAppl
--         - N octets, the first x octets are the LU-NAME,
--            the second y octets are the TP-NAME, and the 
--            last z octets are the MODENAME of the Echo 
--            Server.  The address will be encoded with a size
--            byte preceding each of the x y and z called s.
--            For example sxsysz (zero size before z for a
--            MODENAME default).  The LU-NAME is composed of
--            8 bytes '.' 8 bytes.  The Transaction Program
--            name (TP-NAME) is 1-64 bytes.  The MODENAME
--            is 8 bytes.
--    appleTalkEcho, appleTalkEchoAppl
--    decNetEcho, decNetEchoAppl
--    ipxEcho, ipxEchoAppl
--    isoClnsEcho, isoClnsEchoAppl
--    vinesEcho, vinesEchoAppl
--    xnsEcho, xnsEchoAppl
--    apolloEcho, apolloEchoAppl
--    netbiosEchoAppl
--            - unsupported protocols.

rttMonApplVersion OBJECT-TYPE
    SYNTAX DisplayString
--    Rsyntax OCTET STRING(SIZE(0..255))
    ACCESS read-only
    STATUS mandatory
    DESCRIPTION
        "Round Trip Time monitoring application version 
        string.
        
        The format will be:
        
        'Version.Release.Patch-Level: Textual-Description'
         
        For example:  '1.0.0: Initial RTT Application'"
    ::= { rttMonAppl 1 }

rttMonApplMaxPacketDataSize OBJECT-TYPE
    SYNTAX INTEGER(0..16384)
--  Units
--    octets
    ACCESS read-only
    STATUS mandatory
    DESCRIPTION
        "The maximum size of the data portion an echo
        packet supported by this RTT application.  This is
        the maximum value that can be specified by
        (rttMonEchoAdminPktDataRequestSize + ARR Header)
        or 
        (rttMonEchoAdminPktDataResponseSize + ARR Header)
        in the rttMonCtrlAdminTable.
        
        This object is undefined for conceptual RTT 
        control rows when the RttMonRttType object is set
        to 'fileIO' or 'script'."
    ::= { rttMonAppl 2 }

rttMonApplTimeOfLastSet OBJECT-TYPE
    SYNTAX TimeStamp
--    Rsyntax TimeTicks
    ACCESS read-only
    STATUS mandatory
    DESCRIPTION
        "The last time at which a set operation occurred 
        on any of the objects in this MIB.  The managing 
        application can inspect this value in order to 
        determine whether changes have been made without 
        retrieving the entire Administration portion of
        this MIB.
        
        This object applies to all settable objects in this
        MIB, including the 'Reset' objects that could clear
        saved history/statistics."
    ::= { rttMonAppl 3 }

rttMonApplNumCtrlAdminEntry OBJECT-TYPE
    SYNTAX Integer32(1..500)
    ACCESS read-only
    STATUS mandatory
    DESCRIPTION
        "This object defines the maximum number of entries
         that can be added to the rttMonCtrlAdminTable. It
         is calculated at the system init time. The value
         is impacted when rttMonApplFreeMemLowWaterMark is changed."
    ::= { rttMonAppl 4 }

rttMonApplReset OBJECT-TYPE
    SYNTAX RttReset
--    Rsyntax INTEGER {
--        ready(1),
--        reset(2)
--        }
    ACCESS read-write
    STATUS mandatory
    DESCRIPTION
        "When set to 'reset' the entire RTT application 
        goes through a reset sequence, making a best 
        effort to revert to its startup condition.  Any 
        and all rows in the Overall Control Group will be
        immediately deleted, together with any associated
        rows in the Statistics Collection Group, and 
        History Collection Group.  All open connections 
        will also be closed.  Finally the 
        rttMonApplPreConfigedTable will reset (see 
        rttMonApplPreConfigedReset)."
    ::= { rttMonAppl 5 }

rttMonApplPreConfigedReset OBJECT-TYPE
    SYNTAX RttReset
--    Rsyntax INTEGER {
--        ready(1),
--        reset(2)
--        }
    ACCESS read-write
    STATUS obsolete
    DESCRIPTION
        "When set to 'reset' the RTT application will 
        reset the Application Preconfigured MIB section.
        
        This will force the RTT application to delete all
        entries in the rttMonApplPreConfigedTable and then
        to repopulate the table with the current configuration.
        
        This provides a mechanism to load and unload user
        scripts and file paths."
    ::= { rttMonAppl 6 }

rttMonApplSupportedRttTypesTable OBJECT-TYPE
    SYNTAX SEQUENCE OF RttMonApplSupportedRttTypesEntry
    ACCESS not-accessible
    STATUS mandatory
    DESCRIPTION
        "A table of which contains the supported Rtt
        Monitor Types.
        
        See the RttMonRttType textual convention for
        the definition of each type."
    ::= { rttMonAppl 7 }

rttMonApplSupportedRttTypesEntry OBJECT-TYPE
    SYNTAX RttMonApplSupportedRttTypesEntry
    ACCESS not-accessible
    STATUS mandatory
    DESCRIPTION
        "A list that presents the valid Rtt Monitor
        Types."
    INDEX { rttMonApplSupportedRttTypes }
    ::= { rttMonApplSupportedRttTypesTable 1 }

RttMonApplSupportedRttTypesEntry ::= SEQUENCE {
    rttMonApplSupportedRttTypes RttMonRttType,
    rttMonApplSupportedRttTypesValid TruthValue
    }

rttMonApplSupportedRttTypes OBJECT-TYPE
    SYNTAX RttMonRttType
--    Rsyntax INTEGER {
--        echo(1),
--        pathEcho(2),
--        fileIO(3),
--        script(4),
--        udpEcho(5),
--        tcpConnect(6),
--        http(7),
--        dns(8),
--        jitter(9),
--        dlsw(10),
--        dhcp(11)
--        }
    ACCESS not-accessible
    STATUS mandatory
    DESCRIPTION
        "This object indexes the supported
        'RttMonRttType' types."
    ::= { rttMonApplSupportedRttTypesEntry 1 }

rttMonApplSupportedRttTypesValid OBJECT-TYPE
    SYNTAX TruthValue
--    Rsyntax INTEGER {
--        true(1),
--        false(2)
--        }
    ACCESS read-only
    STATUS mandatory
    DESCRIPTION
        "This object defines the supported 
        'RttMonRttType' types."
    ::= { rttMonApplSupportedRttTypesEntry 2 }

rttMonApplSupportedProtocolsTable OBJECT-TYPE
    SYNTAX SEQUENCE OF RttMonApplSupportedProtocolsEntry
    ACCESS not-accessible
    STATUS mandatory
    DESCRIPTION
        "A table of which contains the supported Rtt
        Monitor Protocols.
        
        See the RttMonProtocol textual convention 
        for the definition of each protocol."
    ::= { rttMonAppl 8 }

rttMonApplSupportedProtocolsEntry OBJECT-TYPE
    SYNTAX RttMonApplSupportedProtocolsEntry
    ACCESS not-accessible
    STATUS mandatory
    DESCRIPTION
        "A list that presents the valid Rtt Monitor
        Protocols."
    INDEX { rttMonApplSupportedProtocols }
    ::= { rttMonApplSupportedProtocolsTable 1 }

RttMonApplSupportedProtocolsEntry ::= SEQUENCE {
    rttMonApplSupportedProtocols RttMonProtocol,
    rttMonApplSupportedProtocolsValid TruthValue
    }

rttMonApplSupportedProtocols OBJECT-TYPE
    SYNTAX RttMonProtocol
--    Rsyntax INTEGER {
--        notApplicable(1),
--        ipIcmpEcho(2),
--        ipUdpEchoAppl(3),
--        snaRUEcho(4),
--        snaLU0EchoAppl(5),
--        snaLU2EchoAppl(6),
--        snaLU62Echo(7),
--        snaLU62EchoAppl(8),
--        appleTalkEcho(9),
--        appleTalkEchoAppl(10),
--        decNetEcho(11),
--        decNetEchoAppl(12),
--        ipxEcho(13),
--        ipxEchoAppl(14),
--        isoClnsEcho(15),
--        isoClnsEchoAppl(16),
--        vinesEcho(17),
--        vinesEchoAppl(18),
--        xnsEcho(19),
--        xnsEchoAppl(20),
--        apolloEcho(21),
--        apolloEchoAppl(22),
--        netbiosEchoAppl(23),
--        ipTcpConn(24),
--        httpAppl(25),
--        dnsAppl(26),
--        jitterAppl(27),
--        dlswAppl(28),
--        dhcpAppl(29)
--        }
    ACCESS not-accessible
    STATUS mandatory
    DESCRIPTION
        "This object indexes the supported 
        'RttMonProtocol' protocols."
    ::= { rttMonApplSupportedProtocolsEntry 1 }

rttMonApplSupportedProtocolsValid OBJECT-TYPE
    SYNTAX TruthValue
--    Rsyntax INTEGER {
--        true(1),
--        false(2)
--        }
    ACCESS read-only
    STATUS mandatory
    DESCRIPTION
        "This object defines the supported 
        'RttMonProtocol' protocols."
    ::= { rttMonApplSupportedProtocolsEntry 2 }

rttMonApplPreConfigedTable OBJECT-TYPE
    SYNTAX SEQUENCE OF RttMonApplPreConfigedEntry
    ACCESS not-accessible
    STATUS obsolete
    DESCRIPTION
        "A table of which contains the previously
        configured Script Names and File IO targets.
        
        These Script Names and File IO targets are installed
        via a different mechanism than this application, and
        are specific to each platform."
    ::= { rttMonAppl 9 }

rttMonApplPreConfigedEntry OBJECT-TYPE
    SYNTAX RttMonApplPreConfigedEntry
    ACCESS not-accessible
    STATUS obsolete
    DESCRIPTION
        "A list of objects that describe the previously
        configured Script Names and File IO targets."
    INDEX { rttMonApplPreConfigedType, rttMonApplPreConfigedName }
    ::= { rttMonApplPreConfigedTable 1 }

RttMonApplPreConfigedEntry ::= SEQUENCE {
    rttMonApplPreConfigedType INTEGER,
    rttMonApplPreConfigedName DisplayString,
    rttMonApplPreConfigedValid TruthValue
    }

rttMonApplPreConfigedType OBJECT-TYPE
    SYNTAX INTEGER {
        filePath(1),
        scriptName(2)
        }
    ACCESS not-accessible
    STATUS obsolete
    DESCRIPTION
        "This is the type of value being stored in the
        rttMonApplPreConfigedName object."
    ::= { rttMonApplPreConfigedEntry 2 }

rttMonApplPreConfigedName OBJECT-TYPE
    SYNTAX DisplayString
--    Rsyntax OCTET STRING(SIZE(0..255))
    ACCESS not-accessible
    STATUS obsolete
    DESCRIPTION
        "This is either one of the following depending on the
        value of the rttMonApplPreConfigedType object:
        
         - The file path to a server.  One of these file paths 
           must be used when defining an entry in the 
           rttMonFileIOAdminTable table with 'fileIO' as the 
           value of the rttMonCtrlAdminRttType object.
        
         - The script name to be used when generating RTT 
           operations.  One of these script names must be used 
           when defining an entry in the rttMonScriptAdminTable 
           table with 'script' as the value of the 
           rttMonCtrlAdminRttType object.
        
        NOTE:  For script names, command line parameters 
               can follow these names in the 
               rttMonScriptAdminTable table."
    ::= { rttMonApplPreConfigedEntry 3 }

rttMonApplPreConfigedValid OBJECT-TYPE
    SYNTAX TruthValue
--    Rsyntax INTEGER {
--        true(1),
--        false(2)
--        }
    ACCESS read-only
    STATUS obsolete
    DESCRIPTION
        "When this row exists, this value will be 'true'.  
        This object exists only to create a valid row in this 
        table."
    ::= { rttMonApplPreConfigedEntry 4 }

rttMonApplProbeCapacity OBJECT-TYPE
    SYNTAX Integer32(1..1000)
    ACCESS read-only
    STATUS mandatory
    DESCRIPTION
        "This object defines the number of probes that can be 
         configured on a router. The number depends on the value 
         of rttMonApplFreeMemLowWaterMark & free bytes
         available on the router or the system configured
         rttMonCtrlAdminEntry number."
    ::= { rttMonAppl 10 }

rttMonApplFreeMemLowWaterMark OBJECT-TYPE
    SYNTAX Integer32(0..2147483647)
    ACCESS read-write
    STATUS mandatory
    DESCRIPTION
        "This object defines the amount of free memory a router must
         have in order to configure RTR. If RTR found out that the
         memory is falling below this mark, it will not allow new
         probes to be configured.
        
         This value should not be set higher (or very close to) than 
         the free bytes available on the router."
    ::= { rttMonAppl 11 }

rttMonApplLatestSetError OBJECT-TYPE
    SYNTAX DisplayString
--    Rsyntax OCTET STRING(SIZE(0..255))
    ACCESS read-only
    STATUS mandatory
    DESCRIPTION
        "An error description for the last error message caused
         by set.
        
         Currently, it includes set error caused due to setting
         rttMonApplFreeMemLowWaterMark greater than the available
         free memory on the router or not enough memory left to
         create new probes."
    ::= { rttMonAppl 12 }

rttMonCtrlAdminTable OBJECT-TYPE
    SYNTAX SEQUENCE OF RttMonCtrlAdminEntry
    ACCESS not-accessible
    STATUS mandatory
    DESCRIPTION
        "A table of Round Trip Time (RTT) monitoring definitions.
        
        The RTT administration control is in multiple tables.  
        This first table, is used to create a conceptual RTT 
        control row.  The following tables contain objects which 
        configure scheduling, information gathering, and 
        notification/trigger generation.  All of these tables 
        will create the same conceptual RTT control row as this 
        table using this tables' index as their own index. 
        
        This table is limited in size by the agent 
        implementation.  The object rttMonApplNumCtrlAdminEntry
        will reflect this tables maximum number of entries."
    ::= { rttMonCtrl 1 }

rttMonCtrlAdminEntry OBJECT-TYPE
    SYNTAX RttMonCtrlAdminEntry
    ACCESS not-accessible
    STATUS mandatory
    DESCRIPTION
        "A base list of objects that define a conceptual RTT 
        control row."
    INDEX { rttMonCtrlAdminIndex }
    ::= { rttMonCtrlAdminTable 1 }

RttMonCtrlAdminEntry ::= SEQUENCE {
    rttMonCtrlAdminIndex Integer32,
    rttMonCtrlAdminOwner OwnerString,
    rttMonCtrlAdminTag DisplayString,
    rttMonCtrlAdminRttType RttMonRttType,
    rttMonCtrlAdminThreshold Integer32,
    rttMonCtrlAdminFrequency Integer32,
    rttMonCtrlAdminTimeout Integer32,
    rttMonCtrlAdminVerifyData TruthValue,
    rttMonCtrlAdminStatus RowStatus,
    rttMonCtrlAdminNvgen TruthValue
    }

rttMonCtrlAdminIndex OBJECT-TYPE
    SYNTAX Integer32(1..2147483647)
    ACCESS not-accessible
    STATUS mandatory
    DESCRIPTION
        "Uniquely identifies a row in the rttMonCtrlAdminTable.
        
        This is a pseudo-random number selected by the management 
        station when creating a row via the rttMonCtrlAdminStatus
        object.  If the pseudo-random number is already in use an 
        'inconsistentValue' return code will be returned when
        set operation is attempted."
    ::= { rttMonCtrlAdminEntry 1 }

rttMonCtrlAdminOwner OBJECT-TYPE
    SYNTAX OwnerString
--    Rsyntax OCTET STRING(SIZE(0..255))
    ACCESS read-write
    STATUS mandatory
    DESCRIPTION
        "Identifies the entity that created this table row."
    DEFVAL { "" }
    ::= { rttMonCtrlAdminEntry 2 }

rttMonCtrlAdminTag OBJECT-TYPE
    SYNTAX DisplayString(SIZE(0..16))
--    Rsyntax OCTET STRING(SIZE(0..16))
    ACCESS read-write
    STATUS mandatory
    DESCRIPTION
        "A string which is used by a managing application to 
        identify the RTT target.  This string is inserted into trap
        notifications, but has no other significance to the 
        agent."
    DEFVAL { "" }
    ::= { rttMonCtrlAdminEntry 3 }

rttMonCtrlAdminRttType OBJECT-TYPE
    SYNTAX RttMonRttType
--    Rsyntax INTEGER {
--        echo(1),
--        pathEcho(2),
--        fileIO(3),
--        script(4),
--        udpEcho(5),
--        tcpConnect(6),
--        http(7),
--        dns(8),
--        jitter(9),
--        dlsw(10),
--        dhcp(11)
--        }
    ACCESS read-write
    STATUS mandatory
    DESCRIPTION
        "The type of RTT operation to be performed.  This value
        must be set in the same PDU or before setting any type
        specific configuration."
    DEFVAL { echo }
    ::= { rttMonCtrlAdminEntry 4 }

rttMonCtrlAdminThreshold OBJECT-TYPE
    SYNTAX Integer32(0..2147483647)
--  Units
--    milliseconds
    ACCESS read-write
    STATUS mandatory
    DESCRIPTION
        "This object defines an administrative threshold limit. If the RTT 
        operation time exceeds this limit and if the conditions
        specified in rttMonReactAdminThresholdType or 
        rttMonHistoryAdminFilter are satisfied, a
        threshold is generated."
    DEFVAL { 5000 }
    ::= { rttMonCtrlAdminEntry 5 }

rttMonCtrlAdminFrequency OBJECT-TYPE
    SYNTAX Integer32(0..604800)
--  Units
--    seconds
    ACCESS read-write
    STATUS mandatory
    DESCRIPTION
        "Specifies the duration between initiating each RTT 
        operation. 
        
        This object cannot be set to a value which would be a 
        shorter duration than rttMonCtrlAdminTimeout.
        
        When the RttMonRttType specifies an operation that is
        synchronous in nature, it may happen that the next RTT 
        operation is blocked by a RTT operation which has not
        yet completed.  In this case, the value of a counter
        (rttMonStatsCollectBusies) in rttMonStatsCaptureTable is
        incremented in lieu of initiating a RTT operation, and 
        the next attempt will occur at the next
        rttMonCtrlAdminFrequency expiration. 
        
        NOTE:  When the rttMonCtrlAdminRttType object is defined 
               to be 'pathEcho', setting this value to a small
               value for your network size may cause an operation
               attempt (or multiple attempts) to be started 
               before the previous operation has finished.  In 
               this situation the rttMonStatsCollectBusies object
               will be incremented in lieu of initiating a new 
               RTT operation, and the next attempt will occur at
               the next rttMonCtrlAdminFrequency expiration.
        
        When the rttMonCtrlAdminRttType object is defined
        to be 'pathEcho', the suggested value for this object 
        is greater than rttMonCtrlAdminTimeout times the 
        maximum number of expected hops to the target.
        
        NOTE:  When the rttMonCtrlAdminRttType object is defined 
               to be 'dhcp', the minimum allowed value for this
               object is 10 seconds.  This restriction is due to
               protocol limitations described in RFC 2131."
    DEFVAL { 60 }
    ::= { rttMonCtrlAdminEntry 6 }

rttMonCtrlAdminTimeout OBJECT-TYPE
    SYNTAX Integer32(0..604800000)
--  Units
--    milliseconds
    ACCESS read-write
    STATUS mandatory
    DESCRIPTION
        "Specifies the duration to wait for a RTT operation 
        completion.  The value of this object cannot be set to 
        a value which would specify a duration exceeding 
        rttMonCtrlAdminFrequency.
        
        For connection oriented protocols, this may cause the
        connection to be closed by the probe.  Once closed, it
        will be assumed that the connection reestablishment
        will be performed.  To prevent unwanted closure of
        connections, be sure to set this value to a realistic
        connection timeout."
    DEFVAL { 5000 }
    ::= { rttMonCtrlAdminEntry 7 }

rttMonCtrlAdminVerifyData OBJECT-TYPE
    SYNTAX TruthValue
--    Rsyntax INTEGER {
--        true(1),
--        false(2)
--        }
    ACCESS read-write
    STATUS mandatory
    DESCRIPTION
        "When set to true, the resulting data in each RTT 
        operation is compared with the expected data.  This
        includes checking header information (if possible) and
        exact packet size.  Any mismatch will be recorded in the
        rttMonStatsCollectVerifyErrors object.
        
        Some RttMonRttTypes may not support this option.  When
        a type does not support this option, the agent will 
        transition this object to false.  It is the management
        applications responsibility to check for this 
        transition. This object is only applicable to SNA protocols."
    DEFVAL { false }
    ::= { rttMonCtrlAdminEntry 8 }

rttMonCtrlAdminStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of the conceptual RTT control row. 
        
        In order for this object to become active, the following 
        row objects must be defined:  
        - rttMonCtrlAdminRttType
        Additionally:
         - for echo, pathEcho and dlsw probes
            rttMonEchoAdminProtocol and 
            rttMonEchoAdminTargetAddress;
         - for udpEcho, tcpConnect and jitter probes
            rttMonEchoAdminTargetAddress and
        rttMonEchoAdminTargetPort
         - for http probe
            rttMonEchoAdminURL 
         - for dns probe
            rttMonEchoAdminTargetAddressString 
            rttMonEchoAdminNameServer 
         - dhcp probe doesn't require any additional objects
        
        All other objects can assume default values. The 
        conceptual Rtt control row will be placed into a 
        'pending' state (via the rttMonCtrlOperState object)
        if rttMonScheduleAdminRttStartTime is not specified.
        
        Most conceptual Rtt control row objects cannot be 
        modified once this conceptual Rtt control row has been 
        created.  The objects that can change are the following:
        
         - Objects in the rttMonReactAdminTable can be modified
           as needed without setting this object to 
           'notInService'.
         - Objects in the rttMonScheduleAdminTable can be 
           modified only when this object has the value of
           'notInService'.
         - The rttMonCtrlOperState can be modified to control
           the state of the probe.
        
        Once this object is in 'active' status, it cannot be 
        set to 'notInService' while the rttMonCtrlOperState
        is in 'active' state.  Thus the rttMonCtrlOperState 
        object must be transitioned first. 
        
        This object can be set to 'destroy' from any value
        at any time."
    ::= { rttMonCtrlAdminEntry 9 }

rttMonCtrlAdminNvgen OBJECT-TYPE
    SYNTAX TruthValue
--    Rsyntax INTEGER {
--        true(1),
--        false(2)
--        }
    ACCESS read-write
    STATUS mandatory
    DESCRIPTION
        "When set to true, this entry will be shown in 
         'show running' command and can be saved into
         Non-volatile memory."
    DEFVAL { false }
    ::= { rttMonCtrlAdminEntry 10 }

rttMonEchoAdminTable OBJECT-TYPE
    SYNTAX SEQUENCE OF RttMonEchoAdminEntry
    ACCESS not-accessible
    STATUS mandatory
    DESCRIPTION
        "A table that contains Round Trip Time (RTT) specific 
        definitions.
        
        This table is controlled via the 
        rttMonCtrlAdminTable.  Entries in this table are
        created via the rttMonCtrlAdminStatus object."
    ::= { rttMonCtrl 2 }

rttMonEchoAdminEntry OBJECT-TYPE
    SYNTAX RttMonEchoAdminEntry
    ACCESS not-accessible
    STATUS mandatory
    DESCRIPTION
        "A list of objects that define specific configuration for
        RttMonRttType conceptual Rtt control rows."
    INDEX { rttMonCtrlAdminIndex }
    ::= { rttMonEchoAdminTable 1 }

RttMonEchoAdminEntry ::= SEQUENCE {
    rttMonEchoAdminProtocol RttMonProtocol,
    rttMonEchoAdminTargetAddress RttMonTargetAddress,
    rttMonEchoAdminPktDataRequestSize Integer32,
    rttMonEchoAdminPktDataResponseSize Integer32,
    rttMonEchoAdminTargetPort Integer32,
    rttMonEchoAdminSourceAddress RttMonTargetAddress,
    rttMonEchoAdminSourcePort Integer32,
    rttMonEchoAdminControlEnable TruthValue,
    rttMonEchoAdminTOS Integer32,
    rttMonEchoAdminLSREnable TruthValue,
    rttMonEchoAdminTargetAddressString DisplayString,
    rttMonEchoAdminNameServer RttMonTargetAddress,
    rttMonEchoAdminOperation RttMonOperation,
    rttMonEchoAdminHTTPVersion DisplayString,
    rttMonEchoAdminURL DisplayString,
    rttMonEchoAdminCache TruthValue,
    rttMonEchoAdminInterval Integer32,
    rttMonEchoAdminNumPackets Integer32,
    rttMonEchoAdminProxy DisplayString,
    rttMonEchoAdminString1 DisplayString,
    rttMonEchoAdminString2 DisplayString,
    rttMonEchoAdminString3 DisplayString,
    rttMonEchoAdminString4 DisplayString,
    rttMonEchoAdminString5 DisplayString
    }

rttMonEchoAdminProtocol OBJECT-TYPE
    SYNTAX RttMonProtocol
--    Rsyntax INTEGER {
--        notApplicable(1),
--        ipIcmpEcho(2),
--        ipUdpEchoAppl(3),
--        snaRUEcho(4),
--        snaLU0EchoAppl(5),
--        snaLU2EchoAppl(6),
--        snaLU62Echo(7),
--        snaLU62EchoAppl(8),
--        appleTalkEcho(9),
--        appleTalkEchoAppl(10),
--        decNetEcho(11),
--        decNetEchoAppl(12),
--        ipxEcho(13),
--        ipxEchoAppl(14),
--        isoClnsEcho(15),
--        isoClnsEchoAppl(16),
--        vinesEcho(17),
--        vinesEchoAppl(18),
--        xnsEcho(19),
--        xnsEchoAppl(20),
--        apolloEcho(21),
--        apolloEchoAppl(22),
--        netbiosEchoAppl(23),
--        ipTcpConn(24),
--        httpAppl(25),
--        dnsAppl(26),
--        jitterAppl(27),
--        dlswAppl(28),
--        dhcpAppl(29)
--        }
    ACCESS read-write
    STATUS mandatory
    DESCRIPTION
        "Specifies the protocol to be used to perform the RTT
        operation. The following list defines what protocol 
        should be used for each probe type:
        
        echo, pathEcho   - ipIcmpEcho
        udpEcho          - ipUdpEchoAppl
        tcpConnect       - ipTcpConn
        http             - httpAppl
        jitter           - jitterAppl
        dlsw             - dlswAppl
        dhcp             - dhcpAppl
        
        When this protocol does not support the type, a 'badValue'
        error will be returned."
    DEFVAL { notApplicable }
    ::= { rttMonEchoAdminEntry 1 }

rttMonEchoAdminTargetAddress OBJECT-TYPE
    SYNTAX RttMonTargetAddress
--    Rsyntax OCTET STRING
    ACCESS read-write
    STATUS mandatory
    DESCRIPTION
        "A string which specifies the address of the target."
    DEFVAL { "" }
    ::= { rttMonEchoAdminEntry 2 }

rttMonEchoAdminPktDataRequestSize OBJECT-TYPE
    SYNTAX Integer32(0..16384)
--  Units
--    octets
    ACCESS read-write
    STATUS mandatory
    DESCRIPTION
        "This object represents the number of octets to be
        placed into the ARR Data portion of the request 
        message, when using SNA protocols.
        
        For non-ARR protocols' RTT request/responses, 
        this value represents the native payload size.
        
        REMEMBER:  The ARR Header overhead is not included 
                   in this value.
        
        For echo probes the total packet size = (IP header(20) + 
        ICMP header(8) + 8 (internal timestamps) + request size).
        
        For echo and pathEcho default request size is 28.
        For udp probe, default request size is 16 and for jitter 
        probe it is 32. For dlsw probes default request size is 0.
        
        The minimum request size for echo and pathEcho is 28 bytes,
        for udp it is 4 and for jitter it is 16.
        For udp and jitter probes the maximum request size is 1500."
    DEFVAL { 1 }
    ::= { rttMonEchoAdminEntry 3 }

rttMonEchoAdminPktDataResponseSize OBJECT-TYPE
    SYNTAX Integer32(0..16384)
    ACCESS read-write
    STATUS mandatory
    DESCRIPTION
        "This object represents the number of octets to be
        placed into the ARR Data portion of the response message.
        This value is passed to the RTT Echo Server via a
        field in the ARR Header.
        
        For non-ARR RTT request/response (i.e. ipIcmpecho)
        this value will be set by the agent to match the
        size of rttMonEchoAdminPktDataRequestSize, when
        native payloads are supported.
        
        REMEMBER:  The ARR Header overhead is not included 
                   in this value.
        
        This object is only supported by SNA protocols."
    DEFVAL { 0 }
    ::= { rttMonEchoAdminEntry 4 }

rttMonEchoAdminTargetPort OBJECT-TYPE
    SYNTAX Integer32(0..65536)
    ACCESS read-write
    STATUS mandatory
    DESCRIPTION
        "This object represents the target's port number. This
        object is applicable to udpEcho, tcpConnect and jitter probes."
    DEFVAL { 0 }
    ::= { rttMonEchoAdminEntry 5 }

rttMonEchoAdminSourceAddress OBJECT-TYPE
    SYNTAX RttMonTargetAddress
--    Rsyntax OCTET STRING
    ACCESS read-write
    STATUS mandatory
    DESCRIPTION
        "A string which specifies the IP address of the source.
        This object is applicable to all probes except dns, dlsw 
        and sna."
    DEFVAL { "" }
    ::= { rttMonEchoAdminEntry 6 }

rttMonEchoAdminSourcePort OBJECT-TYPE
    SYNTAX Integer32(0..65536)
    ACCESS read-write
    STATUS mandatory
    DESCRIPTION
        "This object represents the source's port number. If this 
        object is not specified, the application will get a 
        port allocated by the system. This object is applicable 
        to all probes except dns, dlsw and sna."
    DEFVAL { 0 }
    ::= { rttMonEchoAdminEntry 7 }

rttMonEchoAdminControlEnable OBJECT-TYPE
    SYNTAX TruthValue
--    Rsyntax INTEGER {
--        true(1),
--        false(2)
--        }
    ACCESS read-write
    STATUS mandatory
    DESCRIPTION
        "If this object is enabled, then the RTR application
        will send control messages to a responder, residing on the 
        target router to respond to the data request packets being 
        sent by the source router. This object is not applicable to 
        echo, pathEcho, dns and http probes."
    DEFVAL { true }
    ::= { rttMonEchoAdminEntry 8 }

rttMonEchoAdminTOS OBJECT-TYPE
    SYNTAX Integer32(0..255)
    ACCESS read-write
    STATUS mandatory
    DESCRIPTION
        "This object represents the type of service octet in an 
        IP header. This object is not applicable to dhcp and dns."
    REFERENCE
        "Refer to the following documents for TOS definition.
        RFC791/1349  for IPv4, IPv6, draft-ietf-diffserv-header-02.txt"
    DEFVAL { 0 }
    ::= { rttMonEchoAdminEntry 9 }

rttMonEchoAdminLSREnable OBJECT-TYPE
    SYNTAX TruthValue
--    Rsyntax INTEGER {
--        true(1),
--        false(2)
--        }
    ACCESS read-only
    STATUS mandatory
    DESCRIPTION
        "If this object is enabled then it means that the application
        calculates response time for a specific path, defined in
        rttMonEchoPathAdminEntry. This object is applicable to echo 
        probe only."
    DEFVAL { false }
    ::= { rttMonEchoAdminEntry 10 }

rttMonEchoAdminTargetAddressString OBJECT-TYPE
    SYNTAX DisplayString
--    Rsyntax OCTET STRING(SIZE(0..255))
    ACCESS read-write
    STATUS mandatory
    DESCRIPTION
        "A string which specifies the address of the target. This string
        can be in IP address format or a hostname. This object
        is applicable to dns probe only."
    DEFVAL { "" }
    ::= { rttMonEchoAdminEntry 11 }

rttMonEchoAdminNameServer OBJECT-TYPE
    SYNTAX RttMonTargetAddress
--    Rsyntax OCTET STRING
    ACCESS read-write
    STATUS mandatory
    DESCRIPTION
        "A string which specifies the ip address of the name-server.
        This object is applicable to dns probe only."
    DEFVAL { "" }
    ::= { rttMonEchoAdminEntry 12 }

rttMonEchoAdminOperation OBJECT-TYPE
    SYNTAX RttMonOperation
--    Rsyntax INTEGER {
--        httpGet(1),
--        httpRaw(2)
--        }
    ACCESS read-write
    STATUS mandatory
    DESCRIPTION
        "A code that represents the specific type of RTT operation.
        This object is applicable to http probe only."
    DEFVAL { httpGet }
    ::= { rttMonEchoAdminEntry 13 }

rttMonEchoAdminHTTPVersion OBJECT-TYPE
    SYNTAX DisplayString(SIZE(3..10))
--    Rsyntax OCTET STRING(SIZE(3..10))
    ACCESS read-write
    STATUS mandatory
    DESCRIPTION
        "A string which specifies the version number of the HTTP Server.
        The syntax for the version string is <major number>.<minor number>
        An example would be 1.0, 1.1 etc.,.  This object is applicable to 
        http probe only."
    DEFVAL { "1.0" }
    ::= { rttMonEchoAdminEntry 14 }

rttMonEchoAdminURL OBJECT-TYPE
    SYNTAX DisplayString
--    Rsyntax OCTET STRING(SIZE(0..255))
    ACCESS read-write
    STATUS mandatory
    DESCRIPTION
        "A string which represents the URL to which a HTTP probe should 
        communicate with. This object is applicable to http probe only."
    DEFVAL { "" }
    ::= { rttMonEchoAdminEntry 15 }

rttMonEchoAdminCache OBJECT-TYPE
    SYNTAX TruthValue
--    Rsyntax INTEGER {
--        true(1),
--        false(2)
--        }
    ACCESS read-write
    STATUS mandatory
    DESCRIPTION
        "If this object is false then it means that HTTP request should 
        not download cached pages. This means that the request should 
        be forwarded to the origin server. This object is applicable
        to http probe only."
    DEFVAL { true }
    ::= { rttMonEchoAdminEntry 16 }

rttMonEchoAdminInterval OBJECT-TYPE
    SYNTAX Integer32(0..60000)
--  Units
--    milliseconds
    ACCESS read-write
    STATUS mandatory
    DESCRIPTION
        "This value represents the inter-packet delay between packets
        and is in milliseconds. This value is currently used for 
        Jitter probe. This object is applicable to jitter probe only."
    DEFVAL { 20 }
    ::= { rttMonEchoAdminEntry 17 }

rttMonEchoAdminNumPackets OBJECT-TYPE
    SYNTAX Integer32
    ACCESS read-write
    STATUS mandatory
    DESCRIPTION
        "This value represents the number of packets that need to be 
        transmitted. This value is currently used for Jitter probe. 
        This object is applicable to jitter probe only."
    DEFVAL { 10 }
    ::= { rttMonEchoAdminEntry 18 }

rttMonEchoAdminProxy OBJECT-TYPE
    SYNTAX DisplayString
--    Rsyntax OCTET STRING(SIZE(0..255))
    ACCESS read-write
    STATUS mandatory
    DESCRIPTION
        "This string represents the proxy server information.
        This object is applicable to http probe only."
    DEFVAL { "" }
    ::= { rttMonEchoAdminEntry 19 }

rttMonEchoAdminString1 OBJECT-TYPE
    SYNTAX DisplayString
--    Rsyntax OCTET STRING(SIZE(0..255))
    ACCESS read-write
    STATUS mandatory
    DESCRIPTION
        "This string stores the content of HTTP raw request.
        If the request cannot fit into String1 then it should 
        be split and put in Strings 1 through 5.
        This object is applicable to http probe only."
    DEFVAL { "" }
    ::= { rttMonEchoAdminEntry 20 }

rttMonEchoAdminString2 OBJECT-TYPE
    SYNTAX DisplayString
--    Rsyntax OCTET STRING(SIZE(0..255))
    ACCESS read-write
    STATUS mandatory
    DESCRIPTION
        "This string stores the content of HTTP raw request.
        rttMonEchoAdminString1-5 are concatenated to 
        form the HTTP raw request used in the RTT operation.
        This object is applicable to http probe only."
    DEFVAL { "" }
    ::= { rttMonEchoAdminEntry 21 }

rttMonEchoAdminString3 OBJECT-TYPE
    SYNTAX DisplayString
--    Rsyntax OCTET STRING(SIZE(0..255))
    ACCESS read-write
    STATUS mandatory
    DESCRIPTION
        "This string stores the content of HTTP raw request.
        rttMonEchoAdminString1-5 are concatenated to 
        form the HTTP raw request used in the RTT operation.
        This object is applicable to http probe only."
    DEFVAL { "" }
    ::= { rttMonEchoAdminEntry 22 }

rttMonEchoAdminString4 OBJECT-TYPE
    SYNTAX DisplayString
--    Rsyntax OCTET STRING(SIZE(0..255))
    ACCESS read-write
    STATUS mandatory
    DESCRIPTION
        "This string stores the content of HTTP raw request.
        rttMonEchoAdminString1-5 are concatenated to 
        form the HTTP raw request used in the RTT operation.
        This object is applicable to http probe only."
    DEFVAL { "" }
    ::= { rttMonEchoAdminEntry 23 }

rttMonEchoAdminString5 OBJECT-TYPE
    SYNTAX DisplayString
--    Rsyntax OCTET STRING(SIZE(0..255))
    ACCESS read-write
    STATUS mandatory
    DESCRIPTION
        "This string stores the content of HTTP raw request.
        rttMonEchoAdminString1-5 are concatenated to 
        form the HTTP raw request used in the RTT operation.
        This object is applicable to http probe only."
    DEFVAL { "" }
    ::= { rttMonEchoAdminEntry 24 }

rttMonFileIOAdminTable OBJECT-TYPE
    SYNTAX SEQUENCE OF RttMonFileIOAdminEntry
    ACCESS not-accessible
    STATUS obsolete
    DESCRIPTION
        "A table of Round Trip Time (RTT) monitoring 'fileIO'
        specific definitions.
        
        When the RttMonRttType is not 'fileIO' this table is
        not valid.
        
        This table is controlled via the 
        rttMonCtrlAdminTable.  Entries in this table are
        created via the rttMonCtrlAdminStatus object."
    ::= { rttMonCtrl 3 }

rttMonFileIOAdminEntry OBJECT-TYPE
    SYNTAX RttMonFileIOAdminEntry
    ACCESS not-accessible
    STATUS obsolete
    DESCRIPTION
        "A list of objects that define specific configuration for
        'fileIO' RttMonRttType conceptual Rtt control rows."
    INDEX { rttMonCtrlAdminIndex }
    ::= { rttMonFileIOAdminTable 1 }

RttMonFileIOAdminEntry ::= SEQUENCE {
    rttMonFileIOAdminFilePath DisplayString,
    rttMonFileIOAdminSize INTEGER,
    rttMonFileIOAdminAction INTEGER
    }

rttMonFileIOAdminFilePath OBJECT-TYPE
    SYNTAX DisplayString
--    Rsyntax OCTET STRING(SIZE(0..255))
    ACCESS read-write
    STATUS obsolete
    DESCRIPTION
        "The fully qualified file path that will be the target 
        of the RTT operation.
        
        This value must match one of the rttMonApplPreConfigedName
        entries."
    DEFVAL { "" }
    ::= { rttMonFileIOAdminEntry 1 }

rttMonFileIOAdminSize OBJECT-TYPE
    SYNTAX INTEGER {
        n256(1),
        n1k(2),
        n64k(3),
        n128k(4),
        n256k(5)
        }
--  Units
--    bytes
    ACCESS read-write
    STATUS obsolete
    DESCRIPTION
        "The size of the file to write/read from the File
        Server."
    DEFVAL { n256 }
    ::= { rttMonFileIOAdminEntry 2 }

rttMonFileIOAdminAction OBJECT-TYPE
    SYNTAX INTEGER {
        write(1),
        read(2),
        writeRead(3)
        }
    ACCESS read-write
    STATUS obsolete
    DESCRIPTION
        "The File I/O action to be performed."
    DEFVAL { read }
    ::= { rttMonFileIOAdminEntry 3 }

rttMonScriptAdminTable OBJECT-TYPE
    SYNTAX SEQUENCE OF RttMonScriptAdminEntry
    ACCESS not-accessible
    STATUS obsolete
    DESCRIPTION
        "A table of Round Trip Time (RTT) monitoring 'script'
        specific definitions.
        
        When the RttMonRttType is not 'script' this table is
        not valid.
        
        This table is controlled via the
        rttMonCtrlAdminTable.  Entries in this table are
        created via the rttMonCtrlAdminStatus object."
    ::= { rttMonCtrl 4 }

rttMonScriptAdminEntry OBJECT-TYPE
    SYNTAX RttMonScriptAdminEntry
    ACCESS not-accessible
    STATUS obsolete
    DESCRIPTION
        "A list of objects that define specific configuration for
        'script' RttMonRttType conceptual Rtt control rows."
    INDEX { rttMonCtrlAdminIndex }
    ::= { rttMonScriptAdminTable 1 }

RttMonScriptAdminEntry ::= SEQUENCE {
    rttMonScriptAdminName DisplayString,
    rttMonScriptAdminCmdLineParams DisplayString
    }

rttMonScriptAdminName OBJECT-TYPE
    SYNTAX DisplayString
--    Rsyntax OCTET STRING(SIZE(0..255))
    ACCESS read-write
    STATUS obsolete
    DESCRIPTION
        "This will be the Name of the Script that will be used to 
        generate RTT operations.  
        
        This object must match one of the 
        rttMonApplPreConfigedName entries."
    DEFVAL { "" }
    ::= { rttMonScriptAdminEntry 1 }

rttMonScriptAdminCmdLineParams OBJECT-TYPE
    SYNTAX DisplayString
--    Rsyntax OCTET STRING(SIZE(0..255))
    ACCESS read-write
    STATUS obsolete
    DESCRIPTION
        "This will be the actual command line parameters
        passed to the rttMonScriptAdminName when being
        executed."
    DEFVAL { "" }
    ::= { rttMonScriptAdminEntry 2 }

rttMonScheduleAdminTable OBJECT-TYPE
    SYNTAX SEQUENCE OF RttMonScheduleAdminEntry
    ACCESS not-accessible
    STATUS mandatory
    DESCRIPTION
        "A table of Round Trip Time (RTT) monitoring scheduling
        specific definitions.
        
        This table is controlled via the
        rttMonCtrlAdminTable.  Entries in this table are
        created via the rttMonCtrlAdminStatus object."
    ::= { rttMonCtrl 5 }

rttMonScheduleAdminEntry OBJECT-TYPE
    SYNTAX RttMonScheduleAdminEntry
    ACCESS not-accessible
    STATUS mandatory
    DESCRIPTION
        "A list of objects that define specific configuration for
        the scheduling of RTT operations."
    INDEX { rttMonCtrlAdminIndex }
-- Augments rttMonCtrlAdminEntry
    ::= { rttMonScheduleAdminTable 1 }

RttMonScheduleAdminEntry ::= SEQUENCE {
    rttMonScheduleAdminRttLife Integer32,
    rttMonScheduleAdminRttStartTime TimeTicks,
    rttMonScheduleAdminConceptRowAgeout Integer32
    }

rttMonScheduleAdminRttLife OBJECT-TYPE
    SYNTAX Integer32(0..2147483647)
--  Units
--    seconds
    ACCESS read-write
    STATUS mandatory
    DESCRIPTION
        "This object value will be placed into the 
        rttMonCtrlOperRttLife object when the rttMonCtrlOperState
        object transitions to 'active' or 'pending'.
        
        The value 2147483647 has a special meaning.  When
        this object is set to 2147483647, the 
        rttMonCtrlOperRttLife object will not decrement.  
        And thus the life time will never end."
    DEFVAL { 3600 }
    ::= { rttMonScheduleAdminEntry 1 }

rttMonScheduleAdminRttStartTime OBJECT-TYPE
    SYNTAX TimeTicks
    ACCESS read-write
    STATUS mandatory
    DESCRIPTION
        "This is the time when this conceptional row will 
        activate.  
        
        This is the value of MIB-II's sysUpTime in the future.
        When sysUpTime equals this value this object will 
        cause the activation of a conceptual Rtt row.
        
        When an agent has the capability to determine date and 
        time, the agent should store this object as DateAndTime.
        This allows the agent to completely reset (restart) and
        still be able to start conceptual Rtt rows at the 
        intended time.  If the agent cannot keep date and time
        and the agent resets, all entries should take on one of
        the special value defined below.
        
        The first special value allows this conceptual Rtt 
        control row to immediately transition the 
        rttMonCtrlOperState object into 'active' state when the
        rttMonCtrlAdminStatus  object transitions to active.
        This special value is defined to be a value of this
        object that, when initially set, is 1.
        
        The second special value allows this conceptual Rtt 
        control row to immediately transition the 
        rttMonCtrlOperState object into 'pending' state when 
        the rttMonCtrlAdminStatus object transitions to active.  
        Also, when the rttMonCtrlOperRttLife counts down to zero 
        (and not when set to zero), this special value causes 
        this conceptual Rtt control row to  retransition the 
        rttMonCtrlOperState object into 'pending' state.  This 
        special value is defined to be a value of this object 
        that, when initially set, is smaller than the current
        sysUpTime. (With the exception of one, as defined in
        the previous paragraph)"
    DEFVAL { 0 }
    ::= { rttMonScheduleAdminEntry 2 }

rttMonScheduleAdminConceptRowAgeout OBJECT-TYPE
    SYNTAX Integer32(0..2073600)
--  Units
--    seconds
    ACCESS read-write
    STATUS mandatory
    DESCRIPTION
        "The amount of time this conceptual Rtt control row will 
         exist when not in an 'active' rttMonCtrlOperState.
        
         When this conceptual Rtt control row enters an 'active' 
         state, this timer will be reset and suspended.  When 
         this conceptual RTT control row enters a state other 
         than 'active', the timer will be restarted.
        
         NOTE:  When a conceptual Rtt control row ages out, the 
                agent needs to remove the associated entries in 
                the rttMonReactTriggerAdminTable and 
                rttMonReactTriggerOperTable.
        
         When this value is set to zero, this entry will
         never be aged out."
    DEFVAL { 3600 }
    ::= { rttMonScheduleAdminEntry 3 }

rttMonReactAdminTable OBJECT-TYPE
    SYNTAX SEQUENCE OF RttMonReactAdminEntry
    ACCESS not-accessible
    STATUS mandatory
    DESCRIPTION
        "A table of Round Trip Time (RTT) monitoring Notification
        and Trigger definitions.
        
        All Notification/Reactions are applied to all RTT 
        End-to-End operations.  Thus, they do not apply to hops
        along a path to the target, when RttMonRttType is 
        'pathEcho'.
        
        The format and content of SNA NMVT's are not defined 
        within this module.  
        
        It can be noted, however, that there are Alert NMVT's,
        and traps which are sent when an abnormal
        condition occurs, i.e. when one of 
        rttMonCtrlOperConnectionLostOccurred,
        rttMonCtrlOperTimeoutOccurred or
        rttMonCtrlOperOverThresholdOccurred are changed to true,
        and Resolution NMVT's, and Resolution traps which are 
        sent when that condition clears, i.e. when one of
        rttMonCtrlOperConnectionLostOccurred,
        rttMonCtrlOperTimeoutOccurred or
        rttMonCtrlOperOverThresholdOccurred is changed back to 
        false.
        
        When rttMonReactAdminActionType is set to one of the 
        following:
          -  triggerOnly
          -  trapAndTrigger
          -  nmvtAndTrigger
          -  trapNmvtAndTrigger
        The corresponding rows in the 
        rttMonReactTriggerAdminTable defined via the 
        rttMonCtrlAdminIndex will become active.
        
        This table augments the rttMonCtrlAdminTable."
    ::= { rttMonCtrl 6 }

rttMonReactAdminEntry OBJECT-TYPE
    SYNTAX RttMonReactAdminEntry
    ACCESS not-accessible
    STATUS mandatory
    DESCRIPTION
        "A list of objects that define RTT reaction operations."
    INDEX { rttMonCtrlAdminIndex }
-- Augments rttMonCtrlAdminEntry
    ::= { rttMonReactAdminTable 1 }

RttMonReactAdminEntry ::= SEQUENCE {
    rttMonReactAdminConnectionEnable TruthValue,
    rttMonReactAdminTimeoutEnable TruthValue,
    rttMonReactAdminThresholdType INTEGER,
    rttMonReactAdminThresholdFalling Integer32,
    rttMonReactAdminThresholdCount Integer32,
    rttMonReactAdminThresholdCount2 Integer32,
    rttMonReactAdminActionType INTEGER
    }

rttMonReactAdminConnectionEnable OBJECT-TYPE
    SYNTAX TruthValue
--    Rsyntax INTEGER {
--        true(1),
--        false(2)
--        }
    ACCESS read-write
    STATUS mandatory
    DESCRIPTION
        "If true, a reaction is generated when a RTT 
        operation to a rttMonEchoAdminTargetAddress
        (echo type) causes 
        rttMonCtrlOperConnectionLostOccurred to change its 
        value.  Thus connections to intermediate hops will 
        not cause this value to change."
    DEFVAL { false }
    ::= { rttMonReactAdminEntry 1 }

rttMonReactAdminTimeoutEnable OBJECT-TYPE
    SYNTAX TruthValue
--    Rsyntax INTEGER {
--        true(1),
--        false(2)
--        }
    ACCESS read-write
    STATUS mandatory
    DESCRIPTION
        "If true, a reaction is generated when a RTT
        operation causes rttMonCtrlOperTimeoutOccurred 
        to change its value.  
        
        When the RttMonRttType is 'pathEcho' timeouts to 
        intermediate hops will not cause 
        rttMonCtrlOperTimeoutOccurred to change its value."
    DEFVAL { false }
    ::= { rttMonReactAdminEntry 2 }

rttMonReactAdminThresholdType OBJECT-TYPE
    SYNTAX INTEGER {
        never(1),
        immediate(2),
        consecutive(3),
        xOfy(4),
        average(5)
        }
    ACCESS read-write
    STATUS mandatory
    DESCRIPTION
        "This object specifies the conditions under which 
        rttMonCtrlOperOverThresholdOccurred is changed:
        
        NOTE:  When the RttMonRttType is 'pathEcho' this 
               objects' value and all associated 
               object values are only valid when RTT 
               'echo' operations are to the
               rttMonEchoAdminTargetAddress object address.  Thus
               'pathEcho' operations to intermediate
               hops will not cause this object to change.
        
        never       - rttMonCtrlOperOverThresholdOccurred is 
                       never set
        immediate   - rttMonCtrlOperOverThresholdOccurred is set 
                       to true when an operation completion time 
                       exceeds rttMonCtrlAdminThreshold; 
                       conversely 
                       rttMonCtrlOperOverThresholdOccurred is set 
                       to false when an operation completion time 
                       falls below 
                       rttMonReactAdminThresholdFalling 
        consecutive - rttMonCtrlOperOverThresholdOccurred is set 
                       to true when an operation completion time 
                       exceeds rttMonCtrlAdminThreshold on 
                       rttMonReactAdminThresholdCount consecutive 
                       RTT operations; conversely, 
                       rttMonCtrlOperOverThresholdOccurred is set 
                       to false when an operation completion time
                       falls under the 
                       rttMonReactAdminThresholdFalling 
                       for the same number of consecutive 
                       operations 
        xOfy        - rttMonCtrlOperOverThresholdOccurred is set 
                       to true when x (as specified by 
                       rttMonReactAdminThresholdCount) out of the 
                       last y (as specified by 
                       rttMonReactAdminThresholdCount2) 
                       operation completion time exceeds 
                       rttMonCtrlAdminThreshold; 
                       conversely, it is set to false when x, 
                       out of the last y operation completion
                       time fall below
                       rttMonReactAdminThresholdFalling
                       NOTE: When x > y, the probe will never
                             generate a reaction.
        average     - rttMonCtrlOperOverThresholdOccurred is set 
                       to true when the running average of the 
                       previous rttMonReactAdminThresholdCount 
                       operation completion times exceed 
                       rttMonCtrlAdminThreshold; conversely, it 
                       is set to false when the running average 
                       falls below the 
                       rttMonReactAdminThresholdFalling
        
        If this value is changed by a management station, 
        rttMonCtrlOperOverThresholdOccurred is set to false, but 
        no reaction is generated if the prior value of 
        rttMonCtrlOperOverThresholdOccurred was true."
    DEFVAL { never }
    ::= { rttMonReactAdminEntry 3 }

rttMonReactAdminThresholdFalling OBJECT-TYPE
    SYNTAX Integer32(0..2147483647)
--  Units
--    milliseconds
    ACCESS read-write
    STATUS mandatory
    DESCRIPTION
        "This object defines a threshold limit. If the RTT 
        operation time falls below this limit and if the conditions
        specified in rttMonReactAdminThresholdType are satisfied, an 
        threshold is generated."
    DEFVAL { 3000 }
    ::= { rttMonReactAdminEntry 4 }

rttMonReactAdminThresholdCount OBJECT-TYPE
    SYNTAX Integer32(1..16)
    ACCESS read-write
    STATUS mandatory
    DESCRIPTION
        "This object defines the 'x' value of the xOfy condition
        specified in rttMonReactAdminThresholdType."
    DEFVAL { 5 }
    ::= { rttMonReactAdminEntry 5 }

rttMonReactAdminThresholdCount2 OBJECT-TYPE
    SYNTAX Integer32(1..16)
    ACCESS read-write
    STATUS mandatory
    DESCRIPTION
        "This object defines the 'y' value of the xOfy condition
        specified in rttMonReactAdminThresholdType."
    DEFVAL { 5 }
    ::= { rttMonReactAdminEntry 6 }

rttMonReactAdminActionType OBJECT-TYPE
    SYNTAX INTEGER {
        none(1),
        trapOnly(2),
        nmvtOnly(3),
        triggerOnly(4),
        trapAndNmvt(5),
        trapAndTrigger(6),
        nmvtAndTrigger(7),
        trapNmvtAndTrigger(8)
        }
    ACCESS read-write
    STATUS mandatory
    DESCRIPTION
        "Specifies what type(s), if any, of reaction(s) to 
        generate if an operation violates one of the watched 
        conditions:
        
        none               - no reaction is generated
        trapOnly           - a trap is generated
        nmvtOnly           - an SNA NMVT is generated
        triggerOnly        - all trigger actions defined for this 
                              entry are initiated
        trapAndNmvt        - both a trap and an SNA NMVT are 
                              generated
        trapAndTrigger     - both a trap and all trigger actions 
                              are initiated 
        nmvtAndTrigger     - both a NMVT and all trigger actions 
                              are initiated
        trapNmvtAndTrigger - a NMVT, trap, and all trigger actions
                              are initiated
        
        A trigger action is defined via the 
        rttMonReactTriggerAdminTable."
    DEFVAL { none }
    ::= { rttMonReactAdminEntry 7 }

rttMonStatisticsAdminTable OBJECT-TYPE
    SYNTAX SEQUENCE OF RttMonStatisticsAdminEntry
    ACCESS not-accessible
    STATUS mandatory
    DESCRIPTION
        "A table of Round Trip Time (RTT) monitoring statistics 
        definitions. 
        
        The definitions in this table control what and how many
        entries will be placed into the rttMonStatsCaptureTable.
        
        The statistics capture table is a rollover table.  When 
        the rttMonStatisticsAdminNumHourGroups index value 
        exceeds its value defined in this table, the oldest 
        corresponding group will be deleted and will be replaced 
        with the new group.  All other indices will only fill to 
        there maximum size.
        
        NOTE:  The maximum size of this table is defined to be
               the product of the rttMonCtrlAdminIndex times
               rttMonStatisticsAdminNumHourGroups times
               rttMonStatisticsAdminNumPaths times
               rttMonStatisticsAdminNumHops times
               rttMonStatisticsAdminNumDistBuckets. 
        
        NOTE WELL:  Each of the 'Num' objects values in this 
                    have a special behavior.  When one of the
                    objects is set to a value larger than the
                    Rtt application can support the set will
                    succeed, but the resultant value will
                    be set to the applications maximum value. 
                    The setting management station must reread
                    this object to verify the actual value.
        
        This table augments the rttMonCtrlAdminTable."
    ::= { rttMonCtrl 7 }

rttMonStatisticsAdminEntry OBJECT-TYPE
    SYNTAX RttMonStatisticsAdminEntry
    ACCESS not-accessible
    STATUS mandatory
    DESCRIPTION
        "A list of objects that define RTT statistics 
        capture operations."
    INDEX { rttMonCtrlAdminIndex }
-- Augments rttMonCtrlAdminEntry
    ::= { rttMonStatisticsAdminTable 1 }

RttMonStatisticsAdminEntry ::= SEQUENCE {
    rttMonStatisticsAdminNumHourGroups Integer32,
    rttMonStatisticsAdminNumPaths Integer32,
    rttMonStatisticsAdminNumHops Integer32,
    rttMonStatisticsAdminNumDistBuckets Integer32,
    rttMonStatisticsAdminDistInterval Integer32
    }

rttMonStatisticsAdminNumHourGroups OBJECT-TYPE
    SYNTAX Integer32(0..25)
    ACCESS read-write
    STATUS mandatory
    DESCRIPTION
        "The maximum number of groups of paths to record.
        Specifically this is the number of hourly groups 
        to keep before rolling over.  
        
        The value of one is not advisable because the 
        group will close and immediately be deleted before
        the network management station will have the 
        opportunity to retrieve the statistics. 
        
        The value used in the rttMonStatsCaptureTable to 
        uniquely identify this group is the 
        rttMonStatsCaptureStartTimeIndex.
        
        HTTP and Jitter probes store only two hours of data.
        
        When this object is set to the value of zero all 
        rttMonStatsCaptureTable data capturing will be shut off."
    DEFVAL { 2 }
    ::= { rttMonStatisticsAdminEntry 1 }

rttMonStatisticsAdminNumPaths OBJECT-TYPE
    SYNTAX Integer32(1..128)
    ACCESS read-write
    STATUS mandatory
    DESCRIPTION
        "When RttMonRttType is 'pathEcho' this is the maximum 
        number of statistics paths to record per hourly group.  
        This value directly represents the path to a target.  
        For all other RttMonRttTypes this value will be 
        forced to one by the agent.
        
        NOTE: For 'pathEcho' a source to target path will be 
              created to to hold all errors that occur when a 
              specific path or connection has not be found/setup. 
              Thus, it is advised to set this value greater
              than one.
        
        Since this index does not rollover, only the first
        rttMonStatisticsAdminNumPaths will be kept."
    DEFVAL { 5 }
    ::= { rttMonStatisticsAdminEntry 2 }

rttMonStatisticsAdminNumHops OBJECT-TYPE
    SYNTAX Integer32(1..30)
    ACCESS read-write
    STATUS mandatory
    DESCRIPTION
        "When RttMonRttType is 'pathEcho' this is the maximum 
        number of statistics hops to record per path group.  
        This value directly represents the number of hops along 
        a path to a target, thus we can only support 30 hops.  
        For all other RttMonRttTypes this value will be 
        forced to one by the agent.
        
        Since this index does not rollover, only the first
        rttMonStatisticsAdminNumHops will be kept. This object 
        is applicable to pathEcho probes only."
    DEFVAL { 16 }
    ::= { rttMonStatisticsAdminEntry 3 }

rttMonStatisticsAdminNumDistBuckets OBJECT-TYPE
    SYNTAX Integer32(1..20)
    ACCESS read-write
    STATUS mandatory
    DESCRIPTION
        "The maximum number of statistical distribution
        Buckets to accumulate.
        
        Since this index does not rollover, only the first
        rttMonStatisticsAdminNumDistBuckets will be kept.
        
        The last rttMonStatisticsAdminNumDistBucket will
        contain all entries from its distribution interval
        start point to infinity. This object is not applicable 
        to http and jitter probes."
    DEFVAL { 1 }
    ::= { rttMonStatisticsAdminEntry 4 }

rttMonStatisticsAdminDistInterval OBJECT-TYPE
    SYNTAX Integer32(1..100)
--  Units
--    milliseconds
    ACCESS read-write
    STATUS mandatory
    DESCRIPTION
        "The statistical distribution buckets interval.
        
        Distribution Bucket Example:
        
        rttMonStatisticsAdminNumDistBuckets = 5 buckets
        rttMonStatisticsAdminDistInterval = 10 milliseconds
        
        | Bucket 1 | Bucket 2 | Bucket 3 | Bucket 4 | Bucket 5  |
        |  0-9 ms  | 10-19 ms | 20-29 ms | 30-39 ms | 40-Inf ms |
        
        Odd Example:
        
        rttMonStatisticsAdminNumDistBuckets = 1 buckets
        rttMonStatisticsAdminDistInterval = 10 milliseconds
        
        | Bucket 1  |
        |  0-Inf ms |
        
        Thus, this odd example shows that the value of 
        rttMonStatisticsAdminDistInterval does not apply when
        rttMonStatisticsAdminNumDistBuckets is one.
        This object is not applicable to http and jitter probes."
    DEFVAL { 20 }
    ::= { rttMonStatisticsAdminEntry 5 }

rttMonHistoryAdminTable OBJECT-TYPE
    SYNTAX SEQUENCE OF RttMonHistoryAdminEntry
    ACCESS not-accessible
    STATUS mandatory
    DESCRIPTION
        "A table of Round Trip Time (RTT) monitoring history 
        definitions.
        
        The definitions in this table control what and how many
        entries will be placed into the 
        rttMonHistoryCollectionTable.
        
        The history collection table is a rollover table.  When 
        the rttMonHistoryAdminNumLives index value exceeds its 
        value defined in this table, the oldest corresponding 
        'lives' group will be deleted and will be replaced with 
        the new 'lives' group.  All other indices will only fill
        to their maximum size.
        
        NOTE:  The maximum size of this table is defined to be
               the product of the rttMonCtrlAdminIndex times
               rttMonHistoryAdminNumLives times
               rttMonHistoryAdminNumBuckets times
               rttMonHistoryAdminNumSamples.
        
        NOTE WELL:  Each of the 'Num' objects values in this 
                    have a special behavior.  When one of the
                    objects is set to a value larger than the
                    Rtt application can support the set will
                    succeed, but the resultant value will
                    be set to the applications maximum value. 
                    The setting management station must reread
                    this object to verify the actual value.
        
        NOTE: this table is not applicable to http and jitter 
              probes"
    ::= { rttMonCtrl 8 }

rttMonHistoryAdminEntry OBJECT-TYPE
    SYNTAX RttMonHistoryAdminEntry
    ACCESS not-accessible
    STATUS mandatory
    DESCRIPTION
        "A list of objects that define RTT history collection 
        operations."
    INDEX { rttMonCtrlAdminIndex }
-- Augments rttMonCtrlAdminEntry
    ::= { rttMonHistoryAdminTable 1 }

RttMonHistoryAdminEntry ::= SEQUENCE {
    rttMonHistoryAdminNumLives Integer32,
    rttMonHistoryAdminNumBuckets Integer32,
    rttMonHistoryAdminNumSamples Integer32,
    rttMonHistoryAdminFilter INTEGER
    }

rttMonHistoryAdminNumLives OBJECT-TYPE
    SYNTAX Integer32(0..2)
    ACCESS read-write
    STATUS mandatory
    DESCRIPTION
        "The maximum number of history lives to record.  A life
        is defined by the countdown (or transition) to zero 
        by the rttMonCtrlOperRttLife object.  A new life is
        created when the same conceptual RTT control row is
        restarted via the transition of the 
        rttMonCtrlOperRttLife object and its subsequent 
        countdown.
        
        The value of zero will shut off all 
        rttMonHistoryAdminTable data collection."
    DEFVAL { 0 }
    ::= { rttMonHistoryAdminEntry 1 }

rttMonHistoryAdminNumBuckets OBJECT-TYPE
    SYNTAX Integer32(1..60)
    ACCESS read-write
    STATUS mandatory
    DESCRIPTION
        "The maximum number of history buckets to record.  When
        the RttMonRttType is 'pathEcho'  this value directly 
        represents a path to a target.  For all other 
        RttMonRttTypes this value should be set to the number 
        of operations to keep per lifetime.
        
        After rttMonHistoryAdminNumBuckets are filled, the 
        and the oldest entries are deleted and the most recent
        rttMonHistoryAdminNumBuckets buckets are retained."
    DEFVAL { 15 }
    ::= { rttMonHistoryAdminEntry 2 }

rttMonHistoryAdminNumSamples OBJECT-TYPE
    SYNTAX Integer32(1..30)
    ACCESS read-write
    STATUS mandatory
    DESCRIPTION
        "The maximum number of history samples to record per 
        bucket.  When the RttMonRttType is 'pathEcho' this 
        value directly represents the number of hops along a 
        path to a target, thus we can only support 30 hops.
        For all other RttMonRttTypes this value will be 
        forced to one by the agent."
    DEFVAL { 16 }
    ::= { rttMonHistoryAdminEntry 3 }

rttMonHistoryAdminFilter OBJECT-TYPE
    SYNTAX INTEGER {
        none(1),
        all(2),
        overThreshold(3),
        failures(4)
        }
    ACCESS read-write
    STATUS mandatory
    DESCRIPTION
        "Defines a filter for adding RTT results to the history 
        buffer:
        
        none          - no history is recorded
        all           - the results of all completion times 
                         and failed completions are recorded
        overThreshold - the results of completion times
                         over rttMonCtrlAdminThreshold are 
                         recorded.
        failures      - the results of failed operations (only) 
                         are recorded."
    DEFVAL { none }
    ::= { rttMonHistoryAdminEntry 4 }

rttMonCtrlOperTable OBJECT-TYPE
    SYNTAX SEQUENCE OF RttMonCtrlOperEntry
    ACCESS not-accessible
    STATUS mandatory
    DESCRIPTION
        "A table of which contains the Operational values for the
        probe, and the conceptual RTT control row. 
        
        This table augments the rttMonCtrlAdminTable."
    ::= { rttMonCtrl 9 }

rttMonCtrlOperEntry OBJECT-TYPE
    SYNTAX RttMonCtrlOperEntry
    ACCESS not-accessible
    STATUS mandatory
    DESCRIPTION
        "A list of objects that describe the current state
        of probe, and the conceptual RTT control row. "
    INDEX { rttMonCtrlAdminIndex }
-- Augments rttMonCtrlAdminEntry
    ::= { rttMonCtrlOperTable 1 }

RttMonCtrlOperEntry ::= SEQUENCE {
    rttMonCtrlOperModificationTime TimeStamp,
    rttMonCtrlOperDiagText DisplayString,
    rttMonCtrlOperResetTime TimeStamp,
    rttMonCtrlOperOctetsInUse Gauge32,
    rttMonCtrlOperConnectionLostOccurred TruthValue,
    rttMonCtrlOperTimeoutOccurred TruthValue,
    rttMonCtrlOperOverThresholdOccurred TruthValue,
    rttMonCtrlOperNumRtts Integer32,
    rttMonCtrlOperRttLife Integer32,
    rttMonCtrlOperState INTEGER
    }

rttMonCtrlOperModificationTime OBJECT-TYPE
    SYNTAX TimeStamp
--    Rsyntax TimeTicks
    ACCESS read-only
    STATUS mandatory
    DESCRIPTION
        "This object is updated whenever an object in 
        the conceptual RTT control row is changed or
        updated."
    ::= { rttMonCtrlOperEntry 1 }

rttMonCtrlOperDiagText OBJECT-TYPE
    SYNTAX DisplayString(SIZE(0..51))
--    Rsyntax OCTET STRING(SIZE(0..51))
    ACCESS read-only
    STATUS mandatory
    DESCRIPTION
        "A string which can be used as an aid in tracing problems. 
        The content of this field will depend on the type of 
        target (rttMonEchoAdminProtocol). 
        
        When rttMonEchoAdminProtocol is one of snaLU0EchoAppl, or 
        snaLU2EchoAppl this object contains the name of the 
        Logical Unit (LU) being used for this RTT session (from
        the HOST's point of view), once the session has been 
        established; this can then be used to correlate this 
        name to the connection information stored in the 
        Mainframe Host.
        
        When rttMonEchoAdminProtocol is snaLU62EchoAppl, this 
        object contains the Logical Unit (LU) name being used for
        this RTT session, once the session has been established.  
        This name can be used by the management application to 
        correlate this objects value to the connection 
        information stored at this SNMP Agent via the APPC or 
        APPN mib.
        
        When rttMonEchoAdminProtocol is not one of the 
        previously mentioned values, this value will be null.
        
        It is primarily intended that this object contains 
        information which has significance to a human operator."
    DEFVAL { "" }
    ::= { rttMonCtrlOperEntry 2 }

rttMonCtrlOperResetTime OBJECT-TYPE
    SYNTAX TimeStamp
--    Rsyntax TimeTicks
    ACCESS read-only
    STATUS mandatory
    DESCRIPTION
        "This object is set when the rttMonCtrlOperState is set
        to reset."
    ::= { rttMonCtrlOperEntry 3 }

rttMonCtrlOperOctetsInUse OBJECT-TYPE
    SYNTAX Gauge32
    ACCESS read-only
    STATUS mandatory
    DESCRIPTION
        "This object is the number of octets currently in use
        by this composite conceptual RTT row.  A composite
        conceptual row include the control, statistics, and 
        history conceptual rows combined.  (All octets that
        are addressed via the rttMonCtrlAdminIndex in this
        mib.)"
    ::= { rttMonCtrlOperEntry 4 }

rttMonCtrlOperConnectionLostOccurred OBJECT-TYPE
    SYNTAX TruthValue
--    Rsyntax INTEGER {
--        true(1),
--        false(2)
--        }
    ACCESS read-only
    STATUS mandatory
    DESCRIPTION
        "This object will only change its value when the
        RttMonRttType is 'echo' or 'pathEcho'.
        
        This object is set to true when the RTT connection fails 
        to be established or is lost, and set to false when a 
        connection is reestablished.  When the RttMonRttType
        is 'pathEcho', connection loss applies only to the
        rttMonEchoAdminTargetAddress and not to intermediate
        hops to the Target.
        
        When this value changes and 
        rttMonReactAdminConnectionEnable is true, a reaction 
        will occur. 
        
        If a trap is sent it is a 
        rttMonConnectionChangeNotification."
    DEFVAL { false }
    ::= { rttMonCtrlOperEntry 5 }

rttMonCtrlOperTimeoutOccurred OBJECT-TYPE
    SYNTAX TruthValue
--    Rsyntax INTEGER {
--        true(1),
--        false(2)
--        }
    ACCESS read-only
    STATUS mandatory
    DESCRIPTION
        "This object will change its value for all
        RttMonRttTypes.
        
        This object is set to true when an operation times out, 
        and set to false when an operation completes under 
        rttMonCtrlAdminTimeout.  When this value changes, a 
        reaction may occur, as defined by 
        rttMonReactAdminTimeoutEnable. 
        
        When the RttMonRttType is 'pathEcho', this timeout
        applies only to the rttMonEchoAdminTargetAddress and
        not to intermediate hops to the Target.
        
        If a trap is sent it is a rttMonTimeoutNotification."
    DEFVAL { false }
    ::= { rttMonCtrlOperEntry 6 }

rttMonCtrlOperOverThresholdOccurred OBJECT-TYPE
    SYNTAX TruthValue
--    Rsyntax INTEGER {
--        true(1),
--        false(2)
--        }
    ACCESS read-only
    STATUS mandatory
    DESCRIPTION
        "This object will change its value for all 
        RttMonRttTypes.
        
        This object is changed by operation completion times over
        threshold, as defined by rttMonReactAdminThresholdType.  
        When this value changes, a reaction may occur, as defined 
        by rttMonReactAdminThresholdType. 
        
        If a trap is sent it is a rttMonThresholdNotification."
    DEFVAL { false }
    ::= { rttMonCtrlOperEntry 7 }

rttMonCtrlOperNumRtts OBJECT-TYPE
    SYNTAX Integer32(0..2147483647)
    ACCESS read-only
    STATUS mandatory
    DESCRIPTION
        "This is the total number of probe operations that have 
        been attempted.   
        
        This value is incremented for each start of an RTT 
        operation.  Thus when rttMonCtrlAdminRttType is set to 
        'pathEcho' this value will be incremented by one and 
        not for very every hop along the path.
        
        This object has the special behavior as defined by the
        ROLLOVER NOTE in the DESCRIPTION of the ciscoRttMonMIB
        object.
        
        This value is not effected by the rollover of a statistics
        hourly group."
    ::= { rttMonCtrlOperEntry 8 }

rttMonCtrlOperRttLife OBJECT-TYPE
    SYNTAX Integer32(0..2147483647)
--  Units
--    seconds
    ACCESS read-only
    STATUS mandatory
    DESCRIPTION
        "This object is decremented every second, until it 
        reaches zero.  When the value of this object is zero
        RTT operations for this row are suspended.  This 
        object will either reach zero by a countdown or 
        it will transition to zero via setting the
        rttMonCtrlOperState.
        
        When this object reaches zero the agent needs to 
        transition the rttMonCtrlOperState to 'inactive'.
        
        REMEMBER:  The value 2147483647 has a special 
                   meaning.  When this object has the
                   value 2147483647, this object will
                   not decrement.  And thus the life 
                   time will never.
        
        When the rttMonCtrlOperState object is 'active' and 
        the rttMonReactTriggerOperState object transitions to 
        'active' this object will not be updated with the 
        current value of rttMonCrtlAdminRttLife object."
    ::= { rttMonCtrlOperEntry 9 }

rttMonCtrlOperState OBJECT-TYPE
    SYNTAX INTEGER {
        reset(1),
        orderlyStop(2),
        immediateStop(3),
        pending(4),
        inactive(5),
        active(6),
        restart(7)
        }
    ACCESS read-write
    STATUS mandatory
    DESCRIPTION
        "The RttMonOperStatus object is used to
        manage the 'state' of the probe that is implementing 
        conceptual RTT control row.
        
        This status object has six defined values:
        
        reset(1)          - reset this entry, transition
                            to 'pending'
        orderlyStop(2)    - shutdown this entry at the end
                             of the next RTT operation attempt, 
                             transition to 'inactive'
        immediateStop(3)  - shutdown this entry immediately
                             (if possible), transition to 
                             'inactive'
        pending(4)        - this value is not settable and
                             this conceptual RTT control row is 
                             waiting for further control either 
                             via the rttMonScheduleAdminTable 
                             or the rttMonReactAdminTable/
                             rttMonReactTriggerAdminTable;
                             This object can transition to this
                             value via two mechanisms, first by
                             reseting this object, and second
                             by creating a conceptual Rtt control
                             row with the 
                             rttMonScheduleAdminRttStartTime
                             object with the its special value
        inactive(5)       - this value is not settable and
                             this conceptual RTT control row is 
                             waiting for further control via
                             the rttMonScheduleAdminTable;
                             This object can transition to this
                             value via two mechanisms, first by
                             setting this object to 'orderlyStop'
                             or 'immediateStop', second by 
                             the rttMonCtrlOperRttLife object
                             reaching zero
        active(6)         - this value is not settable and
                             this conceptual RTT control row is
                             currently active
        restart(7)        - this value is only settable when the
                             state is active. It clears the data
                             of this entry and remain on active state.
        
        The probes action when this object is set to 'reset':
          -  all rows in rttMonStatsCaptureTable that relate to 
              this conceptual RTT control row are destroyed and 
              the indices are set to 1
          -  if rttMonStatisticsAdminNumHourGroups is not zero, a 
              single new rttMonStatsCaptureTable row is created
          -  all rows in rttMonHistoryCaptureTable that relate 
              to this RTT definition are destroyed and the indices
              are set to 1
          -  implied history used for timeout or threshold
              notification (see rttMonReactAdminThresholdType)
              is purged
          -  rttMonCtrlOperRttLife is set to 
              rttMonScheduleAdminRttLife
          -  rttMonCtrlOperNumRtts is set to zero
          -  rttMonCtrlOperTimeoutOccurred, 
              rttMonCtrlOperOverThresholdOccurred, and 
              rttMonCtrlOperConnectionLostOccurred are set to 
              false; if this causes a change in the value of 
              either of these objects, resolution notifications 
              will not occur
          -  the next RTT operation is controlled by the objects
              in the rttMonScheduleAdminTable or the 
              rttMonReactAdminTable/rttMonReactTriggerAdminTable
          -  if the rttMonReactTriggerOperState is 'active', it 
              will transition to 'pending'
          -  all rttMonReactTriggerAdminEntries pointing to
              this conceptual entry with their 
              rttMonReactTriggerOperState object 'active', 
              will transition their OperState to 'pending'
          -  all open connections must be maintained
        
        This can be used to synchronize various RTT 
        definitions, so that the RTT requests occur 
        simultaneously, or as simultaneously as possible.
        
        The probes action when this object transitions to 
          'inactive' (via setting this object to 'orderlyStop' 
          or 'immediateStop' or by rttMonCtrlOperRttLife 
          reaching zero):
          -  all statistics and history collection information
              table entries will be closed and kept
          -  implied history used for timeout or threshold
              notification (see rttMonReactAdminThresholdType)
              is purged
          -  rttMonCtrlOperTimeoutOccurred, 
              rttMonCtrlOperOverThresholdOccurred, and 
              rttMonCtrlOperConnectionLostOccurred are set to 
              false; if this causes a change in the value of 
              either of these objects, resolution notifications 
              will not occur.
          -  the next RTT request is controlled by the objects
              in the rttMonScheduleAdminTable
          -  if the rttMonReactTriggerOperState is 'active', it 
              will transition to 'pending' (this denotes that
              the Trigger will be ready the next time this
              object goes active)
          -  all rttMonReactTriggerAdminEntries pointing to
              this conceptual entry with their 
              rttMonReactTriggerOperState object 'active', 
              will transition their OperState to 'pending'
          -  all open connections are to be closed and cleanup.
        
                     rttMonCtrlOperState
                            STATE
                  +-------------------------------------------+
                  |      A       |       B      |      C      |
        ACTION       |  'pending'   |  'inactive'  |   'active'  |
        +----------------+--------------+--------------+-------------+
        | OperState set  |    noError   |inconsistent- |   noError   |
        |  to 'reset'    |              | Value        |             |
        |                |    -> A      |              |   -> A      |
        +----------------+--------------+--------------+-------------+
        | OperState set  |    noError   |    noError   |   noError   |
        |to 'orderlyStop'|    -> B      |    -> B      |   -> B      |
        |     or to      |              |              |             |
        |'immediateStop' |              |              |             |
        +----------------+--------------+--------------+-------------+
        |  Event causes  |    -> C      |    -> B      |   -> C      |
        | Trigger State  |              |              |   see (3)   |
        | to transition  |              |              |             |
        | to 'active'    |              |              |             |
        +----------------+--------------+--------------+-------------+
        | AdminStatus    |    -> C      |    -> C      |   see (1)   |
        | transitions to |              |              |             |
        | 'active' &     |              |              |             |
        | RttStartTime is|              |              |             |
        | special value  |              |              |             |
        | of one.        |              |              |             |
        +----------------+--------------+--------------+-------------+
        | AdminStatus    |    -> A      |    -> A      |   see (1)   |
        | transitions to |              |              |             |
        | 'active' &     |              |              |             |
        | RttStartTime is|              |              |             |
        | special value  |              |              |             |
        | of less than   |              |              |             |
        | current time,  |              |              |             |
        | excluding one. |              |              |             |
        +----------------+--------------+--------------+-------------+
        | AdminStatus    |    -> A      |    -> B      |   see (2)   |
        | transitions to |              |              |             |
        | 'notInService' |              |              |             |
        +----------------+--------------+--------------+-------------+
        | AdminStatus    |    -> B      |    -> B      |   -> B      |
        | transitions to |              |              |             |
        | 'delete'       |              |              |             |
        +----------------+--------------+--------------+-------------+
        | AdminStatus is |    -> C      |    -> C      |   -> C      |
        | 'active' & the |              |              |   see (3)   |
        | RttStartTime   |              |              |             |
        | arrives        |              |              |             |
        +----------------+--------------+--------------+-------------+
        |   RowAgeout    |    -> B      |    -> B      |   -> B      |
        |    expires     |              |              |             |
        +----------------+--------------+--------------+-------------+
        |  OperRttLife   |    N/A       |    N/A       |   -> B      |
        | counts down to |              |              |             |
        | zero           |              |              |             |
        +----------------+--------------+--------------+-------------+
        
        (1) - rttMonCtrlOperState must have transitioned to 'inactive'
        or 'pending' before the rttMonCtrlAdminStatus can
        transition to 'active'.  See (2).
        (2) - rttMonCtrlAdminStatus cannot transition to 'notInService'
        unless rttMonCtrlOperState has been previously forced
        to 'inactive' or 'pending'.
        (3) - when this happens the rttMonCtrlOperRttLife will not
        be updated with the rttMonCtrlAdminRttLife.
        
        NOTE:  In order for all objects in a PDU to be set
               at the same time, this object can not be
               part of a multi-bound PDU."
    ::= { rttMonCtrlOperEntry 10 }

rttMonLatestRttOperTable OBJECT-TYPE
    SYNTAX SEQUENCE OF RttMonLatestRttOperEntry
    ACCESS not-accessible
    STATUS mandatory
    DESCRIPTION
        "A table of which contains the status of latest RTT 
        operation. 
        
        When the RttMonRttType is 'pathEcho', operations 
        performed to the hops along the path will be recorded
        in this table.
        
        This table augments the RTT definition table, 
        rttMonCtrlAdminTable."
    ::= { rttMonCtrl 10 }

rttMonLatestRttOperEntry OBJECT-TYPE
    SYNTAX RttMonLatestRttOperEntry
    ACCESS not-accessible
    STATUS mandatory
    DESCRIPTION
        "A list of objects that record the latest RTT operation. "
    INDEX { rttMonCtrlAdminIndex }
-- Augments rttMonCtrlAdminEntry
    ::= { rttMonLatestRttOperTable 1 }

RttMonLatestRttOperEntry ::= SEQUENCE {
    rttMonLatestRttOperCompletionTime Gauge32,
    rttMonLatestRttOperSense RttResponseSense,
    rttMonLatestRttOperApplSpecificSense Integer32,
    rttMonLatestRttOperSenseDescription DisplayString,
    rttMonLatestRttOperTime TimeStamp,
    rttMonLatestRttOperAddress RttMonTargetAddress
    }

rttMonLatestRttOperCompletionTime OBJECT-TYPE
    SYNTAX Gauge32
--  Units
--    milliseconds
    ACCESS read-only
    STATUS mandatory
    DESCRIPTION
        "The completion time of the latest RTT operation
        successfully completed."
    ::= { rttMonLatestRttOperEntry 1 }

rttMonLatestRttOperSense OBJECT-TYPE
    SYNTAX RttResponseSense
--    Rsyntax INTEGER {
--        ok(1),
--        disconnected(2),
--        overThreshold(3),
--        timeout(4),
--        busy(5),
--        notConnected(6),
--        dropped(7),
--        sequenceError(8),
--        verifyError(9),
--        applicationSpecific(10),
--        dnsServerTimeout(11),
--        tcpConnectTimeout(12),
--        httpTransactionTimeout(13),
--        dnsQueryError(14),
--        httpError(15),
--        error(16)
--        }
    ACCESS read-only
    STATUS mandatory
    DESCRIPTION
        "A sense code for the completion status of the latest 
        RTT operation."
    ::= { rttMonLatestRttOperEntry 2 }

rttMonLatestRttOperApplSpecificSense OBJECT-TYPE
    SYNTAX Integer32(1001..2147483647)
    ACCESS read-only
    STATUS mandatory
    DESCRIPTION
        "An application specific sense code for the 
        completion status of the latest RTT operation.  This 
        object will only be valid when the 
        rttMonLatestRttOperSense object is set to 
        'applicationSpecific'.  Otherwise, this object's 
        value is not valid."
    ::= { rttMonLatestRttOperEntry 3 }

rttMonLatestRttOperSenseDescription OBJECT-TYPE
    SYNTAX DisplayString
--    Rsyntax OCTET STRING(SIZE(0..255))
    ACCESS read-only
    STATUS mandatory
    DESCRIPTION
        "A sense description for the completion status of
        the latest RTT operation when the 
        rttMonLatestRttOperSense object is set to 
        'applicationSpecific'."
    ::= { rttMonLatestRttOperEntry 4 }

rttMonLatestRttOperTime OBJECT-TYPE
    SYNTAX TimeStamp
--    Rsyntax TimeTicks
    ACCESS read-only
    STATUS mandatory
    DESCRIPTION
        "The value of the agent system time at the time of the 
        latest RTT operation."
    ::= { rttMonLatestRttOperEntry 5 }

rttMonLatestRttOperAddress OBJECT-TYPE
    SYNTAX RttMonTargetAddress
--    Rsyntax OCTET STRING
    ACCESS read-only
    STATUS mandatory
    DESCRIPTION
        "When the RttMonRttType is 'echo', 'pathEcho', 'udpEcho',
        'tcpConnect', 'dns' and 'dlsw' this is a string which specifies 
        the address of the target for this RTT operation.  When the 
        RttMonRttType is not one of these types this object will 
        be null.
        
        This address will be the address of the hop along the
        path to the rttMonEchoAdminTargetAddress address,
        including rttMonEchoAdminTargetAddress address, or just
        the rttMonEchoAdminTargetAddress address, when the
        path information is not collected.  This behavior is
        defined by the rttMonCtrlAdminRttType object.
        
        The interpretation of this string depends on the type
        of RTT operation selected, as specified by the
        rttMonEchoAdminProtocol object.
        
        See rttMonEchoAdminTargetAddress for a complete
        description."
    ::= { rttMonLatestRttOperEntry 6 }

rttMonLatestHTTPOperTable OBJECT-TYPE
    SYNTAX SEQUENCE OF RttMonLatestHTTPOperEntry
    ACCESS not-accessible
    STATUS mandatory
    DESCRIPTION
        "A table which contains the status of latest HTTP RTT
        operation."
    ::= { rttMonLatestOper 1 }

rttMonLatestHTTPOperEntry OBJECT-TYPE
    SYNTAX RttMonLatestHTTPOperEntry
    ACCESS not-accessible
    STATUS mandatory
    DESCRIPTION
        "A list of objects that record the latest HTTP RTT 
        operation. This entry is created automatically after the 
        rttMonCtrlAdminEntry is created. Also the entry is 
        automatically deleted when rttMonCtrlAdminEntry is deleted."
    INDEX { rttMonCtrlAdminIndex }
    ::= { rttMonLatestHTTPOperTable 1 }

RttMonLatestHTTPOperEntry ::= SEQUENCE {
    rttMonLatestHTTPOperRTT Gauge32,
    rttMonLatestHTTPOperDNSRTT Gauge32,
    rttMonLatestHTTPOperTCPConnectRTT Gauge32,
    rttMonLatestHTTPOperTransactionRTT Gauge32,
    rttMonLatestHTTPOperMessageBodyOctets Gauge32,
    rttMonLatestHTTPOperSense RttResponseSense,
    rttMonLatestHTTPErrorSenseDescription DisplayString
    }

rttMonLatestHTTPOperRTT OBJECT-TYPE
    SYNTAX Gauge32
    ACCESS read-only
    STATUS mandatory
    DESCRIPTION
        "Round Trip Time taken to perform HTTP operation. This value 
        is the sum of DNSRTT, TCPConnectRTT and TransactionRTT."
    ::= { rttMonLatestHTTPOperEntry 1 }

rttMonLatestHTTPOperDNSRTT OBJECT-TYPE
    SYNTAX Gauge32
    ACCESS read-only
    STATUS mandatory
    DESCRIPTION
        "Round Trip Time taken to perform DNS query within the 
        HTTP operation. If an IP Address is specified in the URL, 
        then DNSRTT is 0."
    ::= { rttMonLatestHTTPOperEntry 2 }

rttMonLatestHTTPOperTCPConnectRTT OBJECT-TYPE
    SYNTAX Gauge32
    ACCESS read-only
    STATUS mandatory
    DESCRIPTION
        "Round Trip Time taken to connect to the HTTP server."
    ::= { rttMonLatestHTTPOperEntry 3 }

rttMonLatestHTTPOperTransactionRTT OBJECT-TYPE
    SYNTAX Gauge32
    ACCESS read-only
    STATUS mandatory
    DESCRIPTION
        "Round Trip Time taken to download the object specified by 
        the URL."
    ::= { rttMonLatestHTTPOperEntry 4 }

rttMonLatestHTTPOperMessageBodyOctets OBJECT-TYPE
    SYNTAX Gauge32
    ACCESS read-only
    STATUS mandatory
    DESCRIPTION
        "The size of the message body received as a response to 
        the HTTP request."
    ::= { rttMonLatestHTTPOperEntry 5 }

rttMonLatestHTTPOperSense OBJECT-TYPE
    SYNTAX RttResponseSense
--    Rsyntax INTEGER {
--        ok(1),
--        disconnected(2),
--        overThreshold(3),
--        timeout(4),
--        busy(5),
--        notConnected(6),
--        dropped(7),
--        sequenceError(8),
--        verifyError(9),
--        applicationSpecific(10),
--        dnsServerTimeout(11),
--        tcpConnectTimeout(12),
--        httpTransactionTimeout(13),
--        dnsQueryError(14),
--        httpError(15),
--        error(16)
--        }
    ACCESS read-only
    STATUS mandatory
    DESCRIPTION
        "An application specific sense code for the completion status
        of the latest RTT operation."
    ::= { rttMonLatestHTTPOperEntry 6 }

rttMonLatestHTTPErrorSenseDescription OBJECT-TYPE
    SYNTAX DisplayString
--    Rsyntax OCTET STRING(SIZE(0..255))
    ACCESS read-only
    STATUS mandatory
    DESCRIPTION
        "An sense description for the completion status
        of the latest RTT operation."
    ::= { rttMonLatestHTTPOperEntry 7 }

rttMonLatestJitterOperTable OBJECT-TYPE
    SYNTAX SEQUENCE OF RttMonLatestJitterOperEntry
    ACCESS not-accessible
    STATUS mandatory
    DESCRIPTION
        "A table which contains the status of latest Jitter 
        operation."
    ::= { rttMonLatestOper 2 }

rttMonLatestJitterOperEntry OBJECT-TYPE
    SYNTAX RttMonLatestJitterOperEntry
    ACCESS not-accessible
    STATUS mandatory
    DESCRIPTION
        "A list of objects that record the latest Jitter 
        operation."
    INDEX { rttMonCtrlAdminIndex }
    ::= { rttMonLatestJitterOperTable 1 }

RttMonLatestJitterOperEntry ::= SEQUENCE {
    rttMonLatestJitterOperNumOfRTT Gauge32,
    rttMonLatestJitterOperRTTSum Gauge32,
    rttMonLatestJitterOperRTTSum2 Gauge32,
    rttMonLatestJitterOperRTTMin Gauge32,
    rttMonLatestJitterOperRTTMax Gauge32,
    rttMonLatestJitterOperMinOfPositivesSD Gauge32,
    rttMonLatestJitterOperMaxOfPositivesSD Gauge32,
    rttMonLatestJitterOperNumOfPositivesSD Gauge32,
    rttMonLatestJitterOperSumOfPositivesSD Gauge32,
    rttMonLatestJitterOperSum2PositivesSD Gauge32,
    rttMonLatestJitterOperMinOfNegativesSD Gauge32,
    rttMonLatestJitterOperMaxOfNegativesSD Gauge32,
    rttMonLatestJitterOperNumOfNegativesSD Gauge32,
    rttMonLatestJitterOperSumOfNegativesSD Gauge32,
    rttMonLatestJitterOperSum2NegativesSD Gauge32,
    rttMonLatestJitterOperMinOfPositivesDS Gauge32,
    rttMonLatestJitterOperMaxOfPositivesDS Gauge32,
    rttMonLatestJitterOperNumOfPositivesDS Gauge32,
    rttMonLatestJitterOperSumOfPositivesDS Gauge32,
    rttMonLatestJitterOperSum2PositivesDS Gauge32,
    rttMonLatestJitterOperMinOfNegativesDS Gauge32,
    rttMonLatestJitterOperMaxOfNegativesDS Gauge32,
    rttMonLatestJitterOperNumOfNegativesDS Gauge32,
    rttMonLatestJitterOperSumOfNegativesDS Gauge32,
    rttMonLatestJitterOperSum2NegativesDS Gauge32,
    rttMonLatestJitterOperPacketLossSD Gauge32,
    rttMonLatestJitterOperPacketLossDS Gauge32,
    rttMonLatestJitterOperPacketOutOfSequence Gauge32,
    rttMonLatestJitterOperPacketMIA Gauge32,
    rttMonLatestJitterOperPacketLateArrival Gauge32,
    rttMonLatestJitterOperSense RttResponseSense,
    rttMonLatestJitterErrorSenseDescription DisplayString
    }

rttMonLatestJitterOperNumOfRTT OBJECT-TYPE
    SYNTAX Gauge32
    ACCESS read-only
    STATUS mandatory
    DESCRIPTION
        "The number of RTT's that were successfully measured."
    ::= { rttMonLatestJitterOperEntry 1 }

rttMonLatestJitterOperRTTSum OBJECT-TYPE
    SYNTAX Gauge32
    ACCESS read-only
    STATUS mandatory
    DESCRIPTION
        "The sum of Jitter RTT's that are successfully measured."
    ::= { rttMonLatestJitterOperEntry 2 }

rttMonLatestJitterOperRTTSum2 OBJECT-TYPE
    SYNTAX Gauge32
    ACCESS read-only
    STATUS mandatory
    DESCRIPTION
        "The sum of squares of RTT's that are successfully measured."
    ::= { rttMonLatestJitterOperEntry 3 }

rttMonLatestJitterOperRTTMin OBJECT-TYPE
    SYNTAX Gauge32
    ACCESS read-only
    STATUS mandatory
    DESCRIPTION
        "The minimum of RTT's that were successfully measured."
    ::= { rttMonLatestJitterOperEntry 4 }

rttMonLatestJitterOperRTTMax OBJECT-TYPE
    SYNTAX Gauge32
    ACCESS read-only
    STATUS mandatory
    DESCRIPTION
        "The maximum of RTT's that were successfully measured."
    ::= { rttMonLatestJitterOperEntry 5 }

rttMonLatestJitterOperMinOfPositivesSD OBJECT-TYPE
    SYNTAX Gauge32
    ACCESS read-only
    STATUS mandatory
    DESCRIPTION
        "The minimum of all positive jitter values from packets sent
        from source to destination."
    ::= { rttMonLatestJitterOperEntry 6 }

rttMonLatestJitterOperMaxOfPositivesSD OBJECT-TYPE
    SYNTAX Gauge32
    ACCESS read-only
    STATUS mandatory
    DESCRIPTION
        "The maximum of all positive jitter values from packets sent
        from source to destination."
    ::= { rttMonLatestJitterOperEntry 7 }

rttMonLatestJitterOperNumOfPositivesSD OBJECT-TYPE
    SYNTAX Gauge32
    ACCESS read-only
    STATUS mandatory
    DESCRIPTION
        "The sum of number of all positive jitter values from packets
        sent from source to destination."
    ::= { rttMonLatestJitterOperEntry 8 }

rttMonLatestJitterOperSumOfPositivesSD OBJECT-TYPE
    SYNTAX Gauge32
    ACCESS read-only
    STATUS mandatory
    DESCRIPTION
        "The sum of RTT's of all positive jitter values from packets
        sent from source to destination."
    ::= { rttMonLatestJitterOperEntry 9 }

rttMonLatestJitterOperSum2PositivesSD OBJECT-TYPE
    SYNTAX Gauge32
    ACCESS read-only
    STATUS mandatory
    DESCRIPTION
        "The sum of square of RTT's of all positive jitter values from
        packets sent from source to destination."
    ::= { rttMonLatestJitterOperEntry 10 }

rttMonLatestJitterOperMinOfNegativesSD OBJECT-TYPE
    SYNTAX Gauge32
    ACCESS read-only
    STATUS mandatory
    DESCRIPTION
        "The minimum of absolute values of all negative jitter values 
        from packets sent from source to destination."
    ::= { rttMonLatestJitterOperEntry 11 }

rttMonLatestJitterOperMaxOfNegativesSD OBJECT-TYPE
    SYNTAX Gauge32
    ACCESS read-only
    STATUS mandatory
    DESCRIPTION
        "The maximum of absolute values of all negative jitter values 
        from packets sent from source to destination."
    ::= { rttMonLatestJitterOperEntry 12 }

rttMonLatestJitterOperNumOfNegativesSD OBJECT-TYPE
    SYNTAX Gauge32
    ACCESS read-only
    STATUS mandatory
    DESCRIPTION
        "The sum of number of all negative jitter values from packets
        sent from source to destination."
    ::= { rttMonLatestJitterOperEntry 13 }

rttMonLatestJitterOperSumOfNegativesSD OBJECT-TYPE
    SYNTAX Gauge32
    ACCESS read-only
    STATUS mandatory
    DESCRIPTION
        "The sum of all negative jitter values from packets
        sent from source to destination."
    ::= { rttMonLatestJitterOperEntry 14 }

rttMonLatestJitterOperSum2NegativesSD OBJECT-TYPE
    SYNTAX Gauge32
    ACCESS read-only
    STATUS mandatory
    DESCRIPTION
        "The sum of square of RTT's of all negative jitter values from
        packets sent from source to destination."
    ::= { rttMonLatestJitterOperEntry 15 }

rttMonLatestJitterOperMinOfPositivesDS OBJECT-TYPE
    SYNTAX Gauge32
    ACCESS read-only
    STATUS mandatory
    DESCRIPTION
        "The minimum of all positive jitter values from packets sent
        from destination to source."
    ::= { rttMonLatestJitterOperEntry 16 }

rttMonLatestJitterOperMaxOfPositivesDS OBJECT-TYPE
    SYNTAX Gauge32
    ACCESS read-only
    STATUS mandatory
    DESCRIPTION
        "The maximum of all positive jitter values from packets sent
        from destination to source."
    ::= { rttMonLatestJitterOperEntry 17 }

rttMonLatestJitterOperNumOfPositivesDS OBJECT-TYPE
    SYNTAX Gauge32
    ACCESS read-only
    STATUS mandatory
    DESCRIPTION
        "The sum of number of all positive jitter values from packets
        sent from destination to source."
    ::= { rttMonLatestJitterOperEntry 18 }

rttMonLatestJitterOperSumOfPositivesDS OBJECT-TYPE
    SYNTAX Gauge32
    ACCESS read-only
    STATUS mandatory
    DESCRIPTION
        "The sum of RTT's of all positive jitter values from packets
        sent from destination to source."
    ::= { rttMonLatestJitterOperEntry 19 }

rttMonLatestJitterOperSum2PositivesDS OBJECT-TYPE
    SYNTAX Gauge32
    ACCESS read-only
    STATUS mandatory
    DESCRIPTION
        "The sum of squares of RTT's of all positive jitter values from
        packets sent from destination to source."
    ::= { rttMonLatestJitterOperEntry 20 }

rttMonLatestJitterOperMinOfNegativesDS OBJECT-TYPE
    SYNTAX Gauge32
    ACCESS read-only
    STATUS mandatory
    DESCRIPTION
        "The minimum of all negative jitter values from packets sent
        from destination to source."
    ::= { rttMonLatestJitterOperEntry 21 }

rttMonLatestJitterOperMaxOfNegativesDS OBJECT-TYPE
    SYNTAX Gauge32
    ACCESS read-only
    STATUS mandatory
    DESCRIPTION
        "The maximum of all negative jitter values from packets sent
        from destination to source."
    ::= { rttMonLatestJitterOperEntry 22 }

rttMonLatestJitterOperNumOfNegativesDS OBJECT-TYPE
    SYNTAX Gauge32
    ACCESS read-only
    STATUS mandatory
    DESCRIPTION
        "The sum of number of all negative jitter values from packets
        sent from destination to source."
    ::= { rttMonLatestJitterOperEntry 23 }

rttMonLatestJitterOperSumOfNegativesDS OBJECT-TYPE
    SYNTAX Gauge32
    ACCESS read-only
    STATUS mandatory
    DESCRIPTION
        "The sum of RTT's of all negative jitter values from packets
        sent from destination to source."
    ::= { rttMonLatestJitterOperEntry 24 }

rttMonLatestJitterOperSum2NegativesDS OBJECT-TYPE
    SYNTAX Gauge32
    ACCESS read-only
    STATUS mandatory
    DESCRIPTION
        "The sum of squares of RTT's of all negative jitter values from
        packets sent from destination to source."
    ::= { rttMonLatestJitterOperEntry 25 }

rttMonLatestJitterOperPacketLossSD OBJECT-TYPE
    SYNTAX Gauge32
    ACCESS read-only
    STATUS mandatory
    DESCRIPTION
        "The number of packets lost when sent from source to destination."
    ::= { rttMonLatestJitterOperEntry 26 }

rttMonLatestJitterOperPacketLossDS OBJECT-TYPE
    SYNTAX Gauge32
    ACCESS read-only
    STATUS mandatory
    DESCRIPTION
        "The number of packets lost when sent from destination to source."
    ::= { rttMonLatestJitterOperEntry 27 }

rttMonLatestJitterOperPacketOutOfSequence OBJECT-TYPE
    SYNTAX Gauge32
    ACCESS read-only
    STATUS mandatory
    DESCRIPTION
        "The number of packets arrived out of sequence."
    ::= { rttMonLatestJitterOperEntry 28 }

rttMonLatestJitterOperPacketMIA OBJECT-TYPE
    SYNTAX Gauge32
    ACCESS read-only
    STATUS mandatory
    DESCRIPTION
        "The number of packets that are lost for which we cannot determine
        the direction."
    ::= { rttMonLatestJitterOperEntry 29 }

rttMonLatestJitterOperPacketLateArrival OBJECT-TYPE
    SYNTAX Gauge32
    ACCESS read-only
    STATUS mandatory
    DESCRIPTION
        "The number of packets that arrived after the timeout."
    ::= { rttMonLatestJitterOperEntry 30 }

rttMonLatestJitterOperSense OBJECT-TYPE
    SYNTAX RttResponseSense
--    Rsyntax INTEGER {
--        ok(1),
--        disconnected(2),
--        overThreshold(3),
--        timeout(4),
--        busy(5),
--        notConnected(6),
--        dropped(7),
--        sequenceError(8),
--        verifyError(9),
--        applicationSpecific(10),
--        dnsServerTimeout(11),
--        tcpConnectTimeout(12),
--        httpTransactionTimeout(13),
--        dnsQueryError(14),
--        httpError(15),
--        error(16)
--        }
    ACCESS read-only
    STATUS mandatory
    DESCRIPTION
        "An application specific sense code for the completion status
        of the latest Jitter RTT operation."
    ::= { rttMonLatestJitterOperEntry 31 }

rttMonLatestJitterErrorSenseDescription OBJECT-TYPE
    SYNTAX DisplayString
--    Rsyntax OCTET STRING(SIZE(0..255))
    ACCESS read-only
    STATUS mandatory
    DESCRIPTION
        "An sense description for the completion status
        of the latest Jitter RTT operation."
    ::= { rttMonLatestJitterOperEntry 32 }

rttMonReactTriggerAdminTable OBJECT-TYPE
    SYNTAX SEQUENCE OF RttMonReactTriggerAdminEntry
    ACCESS not-accessible
    STATUS mandatory
    DESCRIPTION
        "A table of which contains the list of conceptual RTT
        control rows that will start to collect data when a 
        reaction condition is violated and when 
        rttMonReactAdminActionType is set to one of the 
        following:
          -  triggerOnly
          -  trapAndTrigger
          -  nmvtAndTrigger
          -  trapNmvtAndTrigger
        
        The goal of this table is to define one or more 
        additional conceptual RTT control rows that will become
        active and start to collect additional history and
        statistics (depending on the rows configuration values),
        when a problem has been detected.
        
        If the conceptual RTT control row is undefined, and a 
        trigger occurs, no action will take place.  
        
        If the conceptual RTT control row is scheduled to start 
        at a later time, triggering that row will have no effect.
        
        If the conceptual RTT control row is currently active, 
        triggering that row will have no effect on that row, but 
        the rttMonReactTriggerOperState object will transition to 
        'active'.
        
        An entry in this table can only be triggered when
        it is not currently in a triggered state.  The
        object rttMonReactTriggerOperState will 
        reflect the state of each entry in this table."
    ::= { rttMonCtrl 11 }

rttMonReactTriggerAdminEntry OBJECT-TYPE
    SYNTAX RttMonReactTriggerAdminEntry
    ACCESS not-accessible
    STATUS mandatory
    DESCRIPTION
        "A list of objects that will be triggered when
        a reaction condition is violated."
    INDEX { rttMonCtrlAdminIndex, rttMonReactTriggerAdminRttMonCtrlAdminIndex }
    ::= { rttMonReactTriggerAdminTable 1 }

RttMonReactTriggerAdminEntry ::= SEQUENCE {
    rttMonReactTriggerAdminRttMonCtrlAdminIndex Integer32,
    rttMonReactTriggerAdminStatus RowStatus
    }

rttMonReactTriggerAdminRttMonCtrlAdminIndex OBJECT-TYPE
    SYNTAX Integer32(1..2147483647)
    ACCESS not-accessible
    STATUS mandatory
    DESCRIPTION
        "This object points to a single conceptual Rtt control 
        row.  If this row does not exist and this value is 
        triggered no action will result.
        
        The conceptual Rtt control row will be triggered for the 
        rttMonCtrlOperRttLife length.  If this conceptual Rtt
        control row is already active, rttMonCtrlOperRttLife will
        not be updated, and its life will continue as previously 
        defined."
    ::= { rttMonReactTriggerAdminEntry 1 }

rttMonReactTriggerAdminStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create Trigger entries."
    DEFVAL { createAndGo }
    ::= { rttMonReactTriggerAdminEntry 2 }

rttMonReactTriggerOperTable OBJECT-TYPE
    SYNTAX SEQUENCE OF RttMonReactTriggerOperEntry
    ACCESS not-accessible
    STATUS mandatory
    DESCRIPTION
        "A table of which contains the operational state
        of each entry in the 
        rttMonReactTriggerAdminTable.
        
        This table augments the RTT trigger 
        definition table, rttMonReactTriggerAdminTable."
    ::= { rttMonCtrl 12 }

rttMonReactTriggerOperEntry OBJECT-TYPE
    SYNTAX RttMonReactTriggerOperEntry
    ACCESS not-accessible
    STATUS mandatory
    DESCRIPTION
        "A list of state objects for the 
        rttMonReactTriggerAdminTable."
    INDEX { rttMonCtrlAdminIndex, rttMonReactTriggerAdminRttMonCtrlAdminIndex }
-- Augments rttMonReactTriggerAdminEntry
    ::= { rttMonReactTriggerOperTable 1 }

RttMonReactTriggerOperEntry ::= SEQUENCE {
    rttMonReactTriggerOperState INTEGER
    }

rttMonReactTriggerOperState OBJECT-TYPE
    SYNTAX INTEGER {
        active(1),
        pending(2)
        }
    ACCESS read-only
    STATUS mandatory
    DESCRIPTION
        "This object takes on the value active
        when its associated entry in the 
        rttMonReactTriggerAdminTable has been
        triggered.
        
        When the associated entry in the
        rttMonReactTriggerAdminTable is not under
        a trigger state, this object will be
        pending.
        
        When this object is in the active state
        this entry can not be retriggered."
    ::= { rttMonReactTriggerOperEntry 1 }

rttMonEchoPathAdminTable OBJECT-TYPE
    SYNTAX SEQUENCE OF RttMonEchoPathAdminEntry
    ACCESS not-accessible
    STATUS mandatory
    DESCRIPTION
        "A table to store the hop addresses in a Loose Source Routing 
        path. Response times are computed along the specified path using 
        ping.
        
        This maximum table size is limited by the size of the 
        maximum number of hop addresses that can fit in an IP header,
        which is 8. The object rttMonEchoPathAdminEntry will reflect 
        this tables maximum number of entries.
        
        This table is coupled with rttMonCtrlAdminStatus."
    ::= { rttMonCtrl 13 }

rttMonEchoPathAdminEntry OBJECT-TYPE
    SYNTAX RttMonEchoPathAdminEntry
    ACCESS not-accessible
    STATUS mandatory
    DESCRIPTION
        "A list of objects that define intermediate hop's IP Address.
        
        This entry can be added only if the rttMonCtrlAdminRttType is
        'echo'. The entry gets deleted when the corresponding RTR entry,
        which has an index of rttMonCtrlAdminIndex, is deleted."
    INDEX { rttMonCtrlAdminIndex, rttMonEchoPathAdminHopIndex }
    ::= { rttMonEchoPathAdminTable 1 }

RttMonEchoPathAdminEntry ::= SEQUENCE {
    rttMonEchoPathAdminHopIndex Integer32,
    rttMonEchoPathAdminHopAddress RttMonTargetAddress
    }

rttMonEchoPathAdminHopIndex OBJECT-TYPE
    SYNTAX Integer32(1..8)
    ACCESS not-accessible
    STATUS mandatory
    DESCRIPTION
        "Uniquely identifies a row in the rttMonEchoPathAdminTable.
        This number represents the hop address number in a specific 
        ping path. All the indicies should start from 1 and must be 
        contiguous ie., entries should be (say rttMonCtrlAdminIndex = 1) 
        1.1, 1.2, 1.3, they cannot be 1.1, 1.2, 1.4"
    ::= { rttMonEchoPathAdminEntry 1 }

rttMonEchoPathAdminHopAddress OBJECT-TYPE
    SYNTAX RttMonTargetAddress
--    Rsyntax OCTET STRING
    ACCESS read-write
    STATUS mandatory
    DESCRIPTION
        "A string which specifies the address of an intermediate hop's
        IP Address for a RTT 'echo' operation"
    ::= { rttMonEchoPathAdminEntry 2 }

rttMonStatsCaptureTable OBJECT-TYPE
    SYNTAX SEQUENCE OF RttMonStatsCaptureEntry
    ACCESS not-accessible
    STATUS mandatory
    DESCRIPTION
        "The statistics capture database.
        
        The statistics capture table contains summarized 
        information of the results for a conceptual RTT control 
        row.  A rolling accumulated history of this information 
        is maintained in a series of hourly 'group(s)'.  Each 
        'group' contains a series of 'path(s)', each 'path' 
        contains a series of 'hop(s)', each 'hop' contains a 
        series of 'statistics distribution bucket(s)'.
        
        Each conceptual statistics row has a current hourly 
        group, into which RTT results are accumulated.  At the 
        end of each hour a new hourly group is created which 
        then becomes current.  The counters and accumulators in 
        the new group are initialized to zero.  The previous 
        group(s) is kept in the table until the table contains 
        rttMonStatisticsAdminNumHourGroups groups for the 
        conceptual statistics row;  at this point, the oldest 
        group is discarded and is replaced by the newly created 
        one.  The hourly group is uniquely identified by the 
        rttMonStatsCaptureStartTimeIndex object.
        
        If the activity for a conceptual RTT control row ceases 
        because the rttMonCtrlOperState object transitions to 
        'inactive', the corresponding current hourly group in 
        this table is 'frozen', and a new hourly group is 
        created when activity is resumed.
        
        If the activity for a conceptual RTT control row ceases 
        because the rttMonCtrlOperState object transitions to 
        'pending' this whole table will be cleared and reset to 
        its initial state.
        
        When the RttMonRttType is 'pathEcho', the path 
        exploration RTT requests' statistics will not be 
        accumulated in this table.
        
        NOTE: When the RttMonRttType is 'pathEcho', a source to 
              target rttMonStatsCapturePathIndex path will be 
              created for each rttMonStatsCaptureStartTimeIndex 
              to hold all errors that occur when a specific path
              had not been found or connection has not be setup.
        
        Using this rttMonStatsCaptureTable, a managing 
        application can retrieve summarized data from accurately 
        measured periods, which is synchronized across multiple 
        conceptual RTT control rows.  With the new hourly group
        creation being performed on a 60 minute period, the 
        managing station has plenty of time to collect the data, 
        and need not be concerned with the vagaries of network 
        delays and lost PDU's when trying to get matching data.  
        Also, the managing station can spread the data gathering 
        over a longer period, which removes the need for a flood 
        of get requests in a short period which otherwise would 
        occur."
    ::= { rttMonStats 1 }

rttMonStatsCaptureEntry OBJECT-TYPE
    SYNTAX RttMonStatsCaptureEntry
    ACCESS not-accessible
    STATUS mandatory
    DESCRIPTION
        "A list of objects which accumulate the results of a 
        series of RTT operations over a 60 minute time period.
        
        The statistics capture table is a rollover table.  When
        rttMonStatsCaptureStartTimeIndex groups exceeds the 
        rttMonStatisticsAdminNumHourGroups value, the oldest 
        corresponding hourly group will be deleted and will be 
        replaced with the new rttMonStatsCaptureStartTimeIndex
        hourly group.  
        
        All other indices will fill to there maximum size. 
        
        The statistics capture table has five indices.  Each
        described as follows:
        
          -  The first index correlates its entries to a
              conceptual RTT control row via the 
              rttMonCtrlAdminIndex object.
          -  The second index is a rollover group and it 
              uniquely identifies a 60 minute group. (The 
              rttMonStatsCaptureStartTimeIndex object
              is used to make this value unique.)
          -  When the RttMonRttType is 'pathEcho', the third 
              index uniquely identifies the paths in a 
              statistics period.  (The period is 60
              minutes.)  A path will be created for each
              unique path through the network.  Note:  A
              path that does not contain the target is
              considered a different path than one which
              uses the exact same path, but does contain the
              target.  For all other values of RttMonRttType
              this index will be one.
          -  When the RttMonRttType is 'pathEcho', the fourth 
              index uniquely identifies the hops in each path, 
              as grouped by the third index.  This index does 
              imply the order of the hops along the path to a 
              target.  For all other values of RttMonRttType
              this index will be one.
          -  The fifth index uniquely creates a statistical
              distribution bucket."
    INDEX { rttMonCtrlAdminIndex, rttMonStatsCaptureStartTimeIndex, rttMonStatsCapturePathIndex, rttMonStatsCaptureHopIndex, rttMonStatsCaptureDistIndex }
    ::= { rttMonStatsCaptureTable 1 }

RttMonStatsCaptureEntry ::= SEQUENCE {
    rttMonStatsCaptureStartTimeIndex TimeStamp,
    rttMonStatsCapturePathIndex Integer32,
    rttMonStatsCaptureHopIndex Integer32,
    rttMonStatsCaptureDistIndex Integer32,
    rttMonStatsCaptureCompletions Integer32,
    rttMonStatsCaptureOverThresholds Integer32,
    rttMonStatsCaptureSumCompletionTime Gauge32,
    rttMonStatsCaptureSumCompletionTime2Low Gauge32,
    rttMonStatsCaptureSumCompletionTime2High Gauge32,
    rttMonStatsCaptureCompletionTimeMax Gauge32,
    rttMonStatsCaptureCompletionTimeMin Gauge32
    }

rttMonStatsCaptureStartTimeIndex OBJECT-TYPE
    SYNTAX TimeStamp
--    Rsyntax TimeTicks
    ACCESS not-accessible
    STATUS mandatory
    DESCRIPTION
        "The time when this row was created. 
        
        This object is the second index of the 
        rttMonStatsCaptureTable Table.
        
        The the number of rttMonStatsCaptureStartTimeIndex  
        groups exceeds the rttMonStatisticsAdminNumHourGroups
        value, the oldest rttMonStatsCaptureStartTimeIndex 
        group will be removed and replaced with the new entry.
        
        When the RttMonRttType is 'pathEcho', this object also 
        uniquely defines a group of paths.  See the 
        rttMonStatsCaptureEntry object."
    ::= { rttMonStatsCaptureEntry 1 }

rttMonStatsCapturePathIndex OBJECT-TYPE
    SYNTAX Integer32(1..128)
    ACCESS not-accessible
    STATUS mandatory
    DESCRIPTION
        "When the RttMonRttType is 'pathEcho', this object 
        uniquely defines a path for a given value of 
        rttMonStatsCaptureStartTimeIndex.  For all other values
        of RttMonRttType, this object will be one.
        
        For a particular value of 
        rttMonStatsCaptureStartTimeIndex, the agent assigns the
        first instance of a path a value of 1, then second 
        instance a value of 2, and so on.  The sequence keeps 
        incrementing until the number of paths equals 
        rttMonStatisticsAdminNumPaths value, then no new paths 
        are kept for the current rttMonStatsCaptureStartTimeIndex 
        group.
        
        NOTE: A source to target rttMonStatsCapturePathIndex
              path will be created for each 
              rttMonStatsCaptureStartTimeIndex to hold all 
              errors that occur when a specific path or 
              connection has not be setup.
        
        This value directly represents the path to
        a target. We can only support 128 paths."
    ::= { rttMonStatsCaptureEntry 2 }

rttMonStatsCaptureHopIndex OBJECT-TYPE
    SYNTAX Integer32(1..30)
    ACCESS not-accessible
    STATUS mandatory
    DESCRIPTION
        "When the RttMonRttType is 'pathEcho', this object 
        uniquely defines a hop for a given value of 
        rttMonStatsCapturePathIndex.  For all other values of
        RttMonRttType, this object will be one.
        
        For a particular value of rttMonStatsCapturePathIndex,
        the agent assigns the first instance of a hop
        a value of 1, then second instance a value of 2, and so
        on.  The sequence keeps incrementing until the number of 
        hops equals rttMonStatisticsAdminNumHops value, then
        no new hops are kept for the current
        rttMonStatsCapturePathIndex.
        
        This value directly represents a hop along the path to
        a target, thus we can only support 30 hops.
        
        This value shows the order along the path to a target."
    ::= { rttMonStatsCaptureEntry 3 }

rttMonStatsCaptureDistIndex OBJECT-TYPE
    SYNTAX Integer32(1..20)
    ACCESS not-accessible
    STATUS mandatory
    DESCRIPTION
        "This object uniquely defines a statistical distribution
        bucket for a given value of rttMonStatsCaptureHopIndex.
        
        For a particular value of rttMonStatsCaptureHopIndex,
        the agent assigns the first instance of a distribution
        a value of 1, then second instance a value of 2, and so
        on.  The sequence keeps incrementing until the number of 
        statistics distribution intervals equals 
        rttMonStatisticsAdminNumDistBuckets value, then
        all values that fall above the last interval will
        be placed into the last interval.
        
        Each of these Statistics Distribution Buckets contain 
        the results of each completion as defined by 
        rttMonStatisticsAdminDistInterval object."
    ::= { rttMonStatsCaptureEntry 4 }

rttMonStatsCaptureCompletions OBJECT-TYPE
    SYNTAX Integer32(0..2147483647)
    ACCESS read-only
    STATUS mandatory
    DESCRIPTION
        "The number of RTT operations that have completed without
        an error and without timing out.
        
        This object has the special behavior as defined by the
        ROLLOVER NOTE in the DESCRIPTION of the ciscoRttMonMIB
        object."
    ::= { rttMonStatsCaptureEntry 5 }

rttMonStatsCaptureOverThresholds OBJECT-TYPE
    SYNTAX Integer32(0..2147483647)
    ACCESS read-only
    STATUS mandatory
    DESCRIPTION
        "The number of RTT operations successfully completed, but 
        in excess of rttMonCtrlAdminThreshold.  This number is a
        subset of the accumulation of all 
        rttMonStatsCaptureCompletions.  The operation time 
        of these completed operations will be accumulated.
        
        This object has the special behavior as defined by the
        ROLLOVER NOTE in the DESCRIPTION of the ciscoRttMonMIB
        object."
    ::= { rttMonStatsCaptureEntry 6 }

rttMonStatsCaptureSumCompletionTime OBJECT-TYPE
    SYNTAX Gauge32
--  Units
--    milliseconds
    ACCESS read-only
    STATUS mandatory
    DESCRIPTION
        "The accumulated completion time of RTT operations which 
        complete successfully."
    ::= { rttMonStatsCaptureEntry 7 }

rttMonStatsCaptureSumCompletionTime2Low OBJECT-TYPE
    SYNTAX Gauge32
    ACCESS read-only
    STATUS mandatory
    DESCRIPTION
        "The low order 32 bits of the accumulated squares 
        of completion times (in milliseconds) of RTT 
        operations which complete successfully.
        
        Low/High order is defined where the binary number
        will look as follows:
        -------------------------------------------------
        | High order 32 bits    | Low order 32 bits     |
        -------------------------------------------------
        For example the number 4294967296 would have all
        Low order bits as '0' and the rightmost High
        order bit will be 1 (zeros,1)."
    ::= { rttMonStatsCaptureEntry 8 }

rttMonStatsCaptureSumCompletionTime2High OBJECT-TYPE
    SYNTAX Gauge32
    ACCESS read-only
    STATUS mandatory
    DESCRIPTION
        "The high order 32 bits of the accumulated squares 
        of completion times (in milliseconds) of RTT 
        operations which complete successfully.
        
        See the rttMonStatsCaptureSumCompletionTime2Low object
        for a definition of Low/High Order."
    ::= { rttMonStatsCaptureEntry 9 }

rttMonStatsCaptureCompletionTimeMax OBJECT-TYPE
    SYNTAX Gauge32
--  Units
--    milliseconds
    ACCESS read-only
    STATUS mandatory
    DESCRIPTION
        "The maximum completion time of any RTT operation which 
        completes successfully."
    ::= { rttMonStatsCaptureEntry 10 }

rttMonStatsCaptureCompletionTimeMin OBJECT-TYPE
    SYNTAX Gauge32
--  Units
--    milliseconds
    ACCESS read-only
    STATUS mandatory
    DESCRIPTION
        "The minimum completion time of any RTT operation which 
        completes successfully."
    ::= { rttMonStatsCaptureEntry 11 }

rttMonStatsCollectTable OBJECT-TYPE
    SYNTAX SEQUENCE OF RttMonStatsCollectEntry
    ACCESS not-accessible
    STATUS mandatory
    DESCRIPTION
        "The statistics collection database.
        
        This table has the exact same behavior as the
        rttMonStatsCaptureTable, except it does not keep
        statistical distribution information.
        
        For a complete table description see
        the rttMonStatsCaptureTable object."
    ::= { rttMonStats 2 }

rttMonStatsCollectEntry OBJECT-TYPE
    SYNTAX RttMonStatsCollectEntry
    ACCESS not-accessible
    STATUS mandatory
    DESCRIPTION
        "A list of objects which accumulate the results of a
        series of RTT operations over a 60 minute time period.
        
        This entry has the exact same behavior as the 
        rttMonStatsCaptureEntry, except it does not keep
        statistical distribution information.
        
        For a complete entry description see
        the rttMonStatsCaptureEntry object."
    INDEX { rttMonCtrlAdminIndex, rttMonStatsCaptureStartTimeIndex, rttMonStatsCapturePathIndex, rttMonStatsCaptureHopIndex }
    ::= { rttMonStatsCollectTable 1 }

RttMonStatsCollectEntry ::= SEQUENCE {
    rttMonStatsCollectNumDisconnects Integer32,
    rttMonStatsCollectTimeouts Integer32,
    rttMonStatsCollectBusies Integer32,
    rttMonStatsCollectNoConnections Integer32,
    rttMonStatsCollectDrops Integer32,
    rttMonStatsCollectSequenceErrors Integer32,
    rttMonStatsCollectVerifyErrors Integer32,
    rttMonStatsCollectAddress RttMonTargetAddress
    }

rttMonStatsCollectNumDisconnects OBJECT-TYPE
    SYNTAX Integer32(0..2147483647)
    ACCESS read-only
    STATUS mandatory
    DESCRIPTION
        "When the RttMonRttType is 'echo' or pathEcho', this 
        object represents the number of times that the target or 
        hop along the path to a target became disconnected.  For
        all other values of RttMonRttType, this object will
        remain zero.
        
        For connectionless protocols this has no meaning,
        and will consequently remain 0.  When
        rttMonEchoAdminProtocol is one of snaRUEcho, this is
        the number of times that an LU-SSCP session was lost, 
        for snaLU0EchoAppl, snaLU2EchoAppl, snaLu62Echo, and for 
        snaLU62EchoAppl, this is the number of times that LU-LU 
        session was lost.
        
        Since this error does not indicate any information about
        the failure of an RTT operation, no response time 
        information for this instance will be recorded in the 
        appropriate objects.
        
        If this error occurs and the rttMonStatsCapturePathIndex 
        cannot be determined, this error will be accumulated in 
        the source to target path, that will always exist.
        
        This object has the special behavior as defined by the
        ROLLOVER NOTE in the DESCRIPTION of the ciscoRttMonMIB
        object."
    ::= { rttMonStatsCollectEntry 1 }

rttMonStatsCollectTimeouts OBJECT-TYPE
    SYNTAX Integer32(0..2147483647)
    ACCESS read-only
    STATUS mandatory
    DESCRIPTION
        "The number of occasions when a RTT operation was not
        completed before a timeout occurred, i.e.
        rttMonCtrlAdminTimeout was exceeded.
        
        Since the RTT operation was never completed, the 
        completion time of these operations are not accumulated,
        nor do they increment rttMonStatsCaptureCompletions (in 
        any of the statistics distribution buckets).
        
        This object has the special behavior as defined by the
        ROLLOVER NOTE in the DESCRIPTION of the ciscoRttMonMIB
        object."
    ::= { rttMonStatsCollectEntry 2 }

rttMonStatsCollectBusies OBJECT-TYPE
    SYNTAX Integer32(0..2147483647)
    ACCESS read-only
    STATUS mandatory
    DESCRIPTION
        "The number of occasions when a RTT operation could not
        be initiated because a previous RTT operation has not 
        been completed.
        
        When the RttMonRttType is 'pathEcho' this can occur for
        both connection oriented protocols and connectionless
        protocols.
        
        When the RttMonRttType is 'echo' this can only occur for
        connection oriented protocols such as SNA. 
        
        When the initiation of a new operation cannot be started,
        this object will be incremented and the operation will be
        omitted.  (The next operation will start at the next 
        Frequency).  Since, a RTT operation was never initiated, 
        the completion time of these operations is not 
        accumulated, nor do they increment 
        rttMonStatsCaptureCompletions.
        
        When the RttMonRttType is 'pathEcho', and this error 
        occurs and the rttMonStatsCapturePathIndex cannot be 
        determined, this error will be accumulated in the source 
        to target path, that will always exist.
        
        This object has the special behavior as defined by the
        ROLLOVER NOTE in the DESCRIPTION of the ciscoRttMonMIB
        object."
    ::= { rttMonStatsCollectEntry 3 }

rttMonStatsCollectNoConnections OBJECT-TYPE
    SYNTAX Integer32(0..2147483647)
    ACCESS read-only
    STATUS mandatory
    DESCRIPTION
        "When the RttMonRttType is 'echo' or 'pathEcho' this is
        the number of occasions when a RTT operation could not be
        initiated because the connection to the target has not 
        been established.  For all other RttMonRttTypes this
        object will remain zero.
        
        This cannot occur for connectionless protocols, but may
        occur for connection oriented protocols, such as SNA.
        
        Since a RTT operation was never initiated, the completion
        time of these operations are not accumulated, nor do they
        increment rttMonStatsCaptureCompletions. 
        
        If this error occurs and the rttMonStatsCapturePathIndex
        cannot be determined, this error will be accumulated
        in the source to target path, that will always exist.
        
        This object has the special behavior as defined by the
        ROLLOVER NOTE in the DESCRIPTION of the ciscoRttMonMIB
        object."
    ::= { rttMonStatsCollectEntry 4 }

rttMonStatsCollectDrops OBJECT-TYPE
    SYNTAX Integer32(0..2147483647)
    ACCESS read-only
    STATUS mandatory
    DESCRIPTION
        "The number of occasions when a RTT operation could not 
        be initiated because some necessary internal resource 
        (for example memory, or SNA subsystem) was not available,
        or the operation completion could not be recognized.
        
        Since a RTT operation was never initiated or was not
        recognized, the completion time of these operations 
        are not accumulated, nor do they increment 
        rttMonStatsCaptureCompletions (in the expected 
        Distribution Bucket).
        
        When the RttMonRttType is 'pathEcho', and this error 
        occurs and the rttMonStatsCapturePathIndex cannot be 
        determined, this error will be accumulated in the 
        source to target path, that will always exist.
        
        This object has the special behavior as defined by the
        ROLLOVER NOTE in the DESCRIPTION of the ciscoRttMonMIB
        object."
    ::= { rttMonStatsCollectEntry 5 }

rttMonStatsCollectSequenceErrors OBJECT-TYPE
    SYNTAX Integer32(0..2147483647)
    ACCESS read-only
    STATUS mandatory
    DESCRIPTION
        "When the RttMonRttType is 'echo' of 'pathEcho' this is 
        the number of RTT operation completions received with 
        an unexpected sequence identifier.  For all other values
        of RttMonRttType this object will remain zero.
        
        When this has occurred some of the possible reasons may
        be:  
           - a duplicate packet was received
           - a response was received after it had timed-out
           - a corrupted packet was received and was not detected
        
        The completion time of these operations are not 
        accumulated, nor do they increment 
        rttMonStatsCaptureCompletions (in the expected
        Distribution Bucket).
        
        This object has the special behavior as defined by the
        ROLLOVER NOTE in the DESCRIPTION of the ciscoRttMonMIB
        object."
    ::= { rttMonStatsCollectEntry 6 }

rttMonStatsCollectVerifyErrors OBJECT-TYPE
    SYNTAX Integer32(0..2147483647)
    ACCESS read-only
    STATUS mandatory
    DESCRIPTION
        "The number of RTT operation completions received with 
        data that does not compare with the expected data.  The 
        completion time of these operations are not accumulated, 
        nor do they increment rttMonStatsCaptureCompletions (in
        the expected Distribution Bucket).
        
        This object has the special behavior as defined by the
        ROLLOVER NOTE in the DESCRIPTION of the ciscoRttMonMIB
        object."
    ::= { rttMonStatsCollectEntry 7 }

rttMonStatsCollectAddress OBJECT-TYPE
    SYNTAX RttMonTargetAddress
--    Rsyntax OCTET STRING
    ACCESS read-only
    STATUS mandatory
    DESCRIPTION
        "This object only applies when the RttMonRttType is 
        'echo', 'pathEcho', 'dlsw', 'udpEcho', 'tcpConnect'.  
        For all other values of the RttMonRttType, this will be 
        null. 
        
        The object is a string which specifies the address of 
        the target for the this RTT operation.
        
        This address will be the address of the hop along the 
        path to the rttMonEchoAdminTargetAddress address, 
        including rttMonEchoAdminTargetAddress address, or just 
        the rttMonEchoAdminTargetAddress address, when the 
        path information is not collected.  This behavior is
        defined by the rttMonCtrlAdminRttType object.
        
        The interpretation of this string depends on the type 
        of RTT operation selected, as specified by the 
        rttMonEchoAdminProtocol object."
    ::= { rttMonStatsCollectEntry 8 }

rttMonStatsTotalsTable OBJECT-TYPE
    SYNTAX SEQUENCE OF RttMonStatsTotalsEntry
    ACCESS not-accessible
    STATUS mandatory
    DESCRIPTION
        "The statistics totals database.
        
        This table has the exact same behavior as the
        rttMonStatsCaptureTable, except it only keeps
        60 minute group values.
        
        For a complete table description see
        the rttMonStatsCaptureTable object."
    ::= { rttMonStats 3 }

rttMonStatsTotalsEntry OBJECT-TYPE
    SYNTAX RttMonStatsTotalsEntry
    ACCESS not-accessible
    STATUS mandatory
    DESCRIPTION
        "A list of objects which accumulate the results of a
        series of RTT operations over a 60 minute time period.
        
        This entry has the exact same behavior as the 
        rttMonStatsCaptureEntry, except it only keeps
        60 minute group values.
        
        For a complete entry description see
        the rttMonStatsCaptureEntry object."
    INDEX { rttMonCtrlAdminIndex, rttMonStatsCaptureStartTimeIndex }
    ::= { rttMonStatsTotalsTable 1 }

RttMonStatsTotalsEntry ::= SEQUENCE {
    rttMonStatsTotalsElapsedTime TimeInterval,
    rttMonStatsTotalsInitiations Integer32
    }

rttMonStatsTotalsElapsedTime OBJECT-TYPE
    SYNTAX TimeInterval
--    Rsyntax INTEGER(0..2147483647)
    ACCESS read-only
    STATUS mandatory
    DESCRIPTION
        "The length of time since this conceptual statistics row 
        was created."
    ::= { rttMonStatsTotalsEntry 1 }

rttMonStatsTotalsInitiations OBJECT-TYPE
    SYNTAX Integer32(0..2147483647)
    ACCESS read-only
    STATUS mandatory
    DESCRIPTION
        "The number of RTT operations that have been initiated.  
        
        This number includes all RTT operations which succeed 
        or fail for whatever reason.
        
        This object has the special behavior as defined by the
        ROLLOVER NOTE in the DESCRIPTION of the ciscoRttMonMIB
        object."
    ::= { rttMonStatsTotalsEntry 2 }

rttMonHTTPStatsTable OBJECT-TYPE
    SYNTAX SEQUENCE OF RttMonHTTPStatsEntry
    ACCESS not-accessible
    STATUS mandatory
    DESCRIPTION
        "The HTTP statistics collection database.
        
        The HTTP statistics table contains summarized information of
        the results for a conceptual RTT control row. A rolling
        accumulated history of this information is maintained in a 
        series of hourly 'group(s)'.
        
        The operation of this table is same as that of 
        rttMonStatsCaptureTable, except that this table can only 
        store a maximum of 2 hours of data."
    ::= { rttMonStats 4 }

rttMonHTTPStatsEntry OBJECT-TYPE
    SYNTAX RttMonHTTPStatsEntry
    ACCESS not-accessible
    STATUS mandatory
    DESCRIPTION
        "A list of objects which accumulate the results of a
        series of RTT operations over a 60 minute time period.
        
        This entry is created only if the rttMonCtrlAdminRttType 
        is http. The operation of this table is same as that of
        rttMonStatsCaptureTable."
    INDEX { rttMonCtrlAdminIndex, rttMonHTTPStatsStartTimeIndex }
    ::= { rttMonHTTPStatsTable 1 }

RttMonHTTPStatsEntry ::= SEQUENCE {
    rttMonHTTPStatsStartTimeIndex TimeStamp,
    rttMonHTTPStatsCompletions Counter32,
    rttMonHTTPStatsOverThresholds Counter32,
    rttMonHTTPStatsRTTSum Counter32,
    rttMonHTTPStatsRTTSum2Low Counter32,
    rttMonHTTPStatsRTTSum2High Counter32,
    rttMonHTTPStatsRTTMin Gauge32,
    rttMonHTTPStatsRTTMax Gauge32,
    rttMonHTTPStatsDNSRTTSum Counter32,
    rttMonHTTPStatsTCPConnectRTTSum Counter32,
    rttMonHTTPStatsTransactionRTTSum Counter32,
    rttMonHTTPStatsMessageBodyOctetsSum Counter32,
    rttMonHTTPStatsDNSServerTimeout Counter32,
    rttMonHTTPStatsTCPConnectTimeout Counter32,
    rttMonHTTPStatsTransactionTimeout Counter32,
    rttMonHTTPStatsDNSQueryError Counter32,
    rttMonHTTPStatsHTTPError Counter32,
    rttMonHTTPStatsError Counter32,
    rttMonHTTPStatsBusies Counter32
    }

rttMonHTTPStatsStartTimeIndex OBJECT-TYPE
    SYNTAX TimeStamp
--    Rsyntax TimeTicks
    ACCESS not-accessible
    STATUS mandatory
    DESCRIPTION
        "This is the time when this row was created. This index 
        uniquely identifies a HTTP Stats row in the 
        rttMonHTTPStatsTable."
    ::= { rttMonHTTPStatsEntry 1 }

rttMonHTTPStatsCompletions OBJECT-TYPE
    SYNTAX Counter32
    ACCESS read-only
    STATUS mandatory
    DESCRIPTION
        "The number of HTTP operations that have completed 
        successfully."
    ::= { rttMonHTTPStatsEntry 2 }

rttMonHTTPStatsOverThresholds OBJECT-TYPE
    SYNTAX Counter32
    ACCESS read-only
    STATUS mandatory
    DESCRIPTION
        "The number of HTTP operations that violate threshold."
    ::= { rttMonHTTPStatsEntry 3 }

rttMonHTTPStatsRTTSum OBJECT-TYPE
    SYNTAX Counter32
    ACCESS read-only
    STATUS mandatory
    DESCRIPTION
        "The sum of HTTP operations that are successfully measured."
    ::= { rttMonHTTPStatsEntry 4 }

rttMonHTTPStatsRTTSum2Low OBJECT-TYPE
    SYNTAX Counter32
    ACCESS read-only
    STATUS mandatory
    DESCRIPTION
        "The sum of squares of the RTT's that are successfully 
        measured (low order 32 bits)."
    ::= { rttMonHTTPStatsEntry 5 }

rttMonHTTPStatsRTTSum2High OBJECT-TYPE
    SYNTAX Counter32
    ACCESS read-only
    STATUS mandatory
    DESCRIPTION
        "The sum of squares of the RTT's that are successfully 
        measured (high order 32 bits)."
    ::= { rttMonHTTPStatsEntry 6 }

rttMonHTTPStatsRTTMin OBJECT-TYPE
    SYNTAX Gauge32
    ACCESS read-only
    STATUS mandatory
    DESCRIPTION
        "The minimum RTT taken to perform HTTP operation."
    ::= { rttMonHTTPStatsEntry 7 }

rttMonHTTPStatsRTTMax OBJECT-TYPE
    SYNTAX Gauge32
    ACCESS read-only
    STATUS mandatory
    DESCRIPTION
        "The minimum RTT taken to perform HTTP operation."
    ::= { rttMonHTTPStatsEntry 8 }

rttMonHTTPStatsDNSRTTSum OBJECT-TYPE
    SYNTAX Counter32
    ACCESS read-only
    STATUS mandatory
    DESCRIPTION
        "The sum of RTT taken to perform DNS query within the 
        HTTP operation."
    ::= { rttMonHTTPStatsEntry 9 }

rttMonHTTPStatsTCPConnectRTTSum OBJECT-TYPE
    SYNTAX Counter32
    ACCESS read-only
    STATUS mandatory
    DESCRIPTION
        "The sum of RTT taken to connect to the HTTP server."
    ::= { rttMonHTTPStatsEntry 10 }

rttMonHTTPStatsTransactionRTTSum OBJECT-TYPE
    SYNTAX Counter32
    ACCESS read-only
    STATUS mandatory
    DESCRIPTION
        "The sum of RTT taken to download the object specified by URL."
    ::= { rttMonHTTPStatsEntry 11 }

rttMonHTTPStatsMessageBodyOctetsSum OBJECT-TYPE
    SYNTAX Counter32
    ACCESS read-only
    STATUS mandatory
    DESCRIPTION
        "The sum of the size of the message body received as a 
        response to the HTTP request."
    ::= { rttMonHTTPStatsEntry 12 }

rttMonHTTPStatsDNSServerTimeout OBJECT-TYPE
    SYNTAX Counter32
    ACCESS read-only
    STATUS mandatory
    DESCRIPTION
        "The number of requests that could not connect to the 
        DNS Server."
    ::= { rttMonHTTPStatsEntry 13 }

rttMonHTTPStatsTCPConnectTimeout OBJECT-TYPE
    SYNTAX Counter32
    ACCESS read-only
    STATUS mandatory
    DESCRIPTION
        "The number of requests that could not connect to the 
        the HTTP Server."
    ::= { rttMonHTTPStatsEntry 14 }

rttMonHTTPStatsTransactionTimeout OBJECT-TYPE
    SYNTAX Counter32
    ACCESS read-only
    STATUS mandatory
    DESCRIPTION
        "The number of requests that timed out during HTTP 
        transaction."
    ::= { rttMonHTTPStatsEntry 15 }

rttMonHTTPStatsDNSQueryError OBJECT-TYPE
    SYNTAX Counter32
    ACCESS read-only
    STATUS mandatory
    DESCRIPTION
        "The number of requests that had DNS Query errors."
    ::= { rttMonHTTPStatsEntry 16 }

rttMonHTTPStatsHTTPError OBJECT-TYPE
    SYNTAX Counter32
    ACCESS read-only
    STATUS mandatory
    DESCRIPTION
        "The number of requests that had HTTP errors while 
        downloading the base page."
    ::= { rttMonHTTPStatsEntry 17 }

rttMonHTTPStatsError OBJECT-TYPE
    SYNTAX Counter32
    ACCESS read-only
    STATUS mandatory
    DESCRIPTION
        "The number of occasions when a HTTP operation could not
        be initiated because an internal error"
    ::= { rttMonHTTPStatsEntry 18 }

rttMonHTTPStatsBusies OBJECT-TYPE
    SYNTAX Counter32
    ACCESS read-only
    STATUS mandatory
    DESCRIPTION
        "The number of occasions when an HTTP operation could not
        be initiated because a previous HTTP operation has not
        been completed."
    ::= { rttMonHTTPStatsEntry 19 }

rttMonJitterStatsTable OBJECT-TYPE
    SYNTAX SEQUENCE OF RttMonJitterStatsEntry
    ACCESS not-accessible
    STATUS mandatory
    DESCRIPTION
        "The Jitter statistics collection database.
        
        The Jitter statistics table contains summarized information of
        the results for a conceptual RTT control row. A rolling
        accumulated history of this information is maintained in a 
        series of hourly 'group(s)'.
        
        The operation of this table is same as that of 
        rttMonStatsCaptureTable, except that this table will store 
        2 hours of data."
    ::= { rttMonStats 5 }

rttMonJitterStatsEntry OBJECT-TYPE
    SYNTAX RttMonJitterStatsEntry
    ACCESS not-accessible
    STATUS mandatory
    DESCRIPTION
        "A list of objects which accumulate the results of a
        series of RTT operations over a 60 minute time period.
        
        This entry is created only if the rttMonCtrlAdminRttType 
        is jitter. The operation of this table is same as that of
        rttMonStatsCaptureTable."
    INDEX { rttMonCtrlAdminIndex, rttMonJitterStatsStartTimeIndex }
    ::= { rttMonJitterStatsTable 1 }

RttMonJitterStatsEntry ::= SEQUENCE {
    rttMonJitterStatsStartTimeIndex TimeStamp,
    rttMonJitterStatsCompletions Counter32,
    rttMonJitterStatsOverThresholds Counter32,
    rttMonJitterStatsNumOfRTT Counter32,
    rttMonJitterStatsRTTSum Counter32,
    rttMonJitterStatsRTTSum2Low Counter32,
    rttMonJitterStatsRTTSum2High Counter32,
    rttMonJitterStatsRTTMin Gauge32,
    rttMonJitterStatsRTTMax Gauge32,
    rttMonJitterStatsMinOfPositivesSD Gauge32,
    rttMonJitterStatsMaxOfPositivesSD Gauge32,
    rttMonJitterStatsNumOfPositivesSD Counter32,
    rttMonJitterStatsSumOfPositivesSD Counter32,
    rttMonJitterStatsSum2PositivesSDLow Counter32,
    rttMonJitterStatsSum2PositivesSDHigh Counter32,
    rttMonJitterStatsMinOfNegativesSD Gauge32,
    rttMonJitterStatsMaxOfNegativesSD Gauge32,
    rttMonJitterStatsNumOfNegativesSD Counter32,
    rttMonJitterStatsSumOfNegativesSD Counter32,
    rttMonJitterStatsSum2NegativesSDLow Counter32,
    rttMonJitterStatsSum2NegativesSDHigh Counter32,
    rttMonJitterStatsMinOfPositivesDS Gauge32,
    rttMonJitterStatsMaxOfPositivesDS Gauge32,
    rttMonJitterStatsNumOfPositivesDS Counter32,
    rttMonJitterStatsSumOfPositivesDS Counter32,
    rttMonJitterStatsSum2PositivesDSLow Counter32,
    rttMonJitterStatsSum2PositivesDSHigh Counter32,
    rttMonJitterStatsMinOfNegativesDS Gauge32,
    rttMonJitterStatsMaxOfNegativesDS Gauge32,
    rttMonJitterStatsNumOfNegativesDS Counter32,
    rttMonJitterStatsSumOfNegativesDS Counter32,
    rttMonJitterStatsSum2NegativesDSLow Counter32,
    rttMonJitterStatsSum2NegativesDSHigh Counter32,
    rttMonJitterStatsPacketLossSD Counter32,
    rttMonJitterStatsPacketLossDS Counter32,
    rttMonJitterStatsPacketOutOfSequence Counter32,
    rttMonJitterStatsPacketMIA Counter32,
    rttMonJitterStatsPacketLateArrival Counter32,
    rttMonJitterStatsError Counter32,
    rttMonJitterStatsBusies Counter32
    }

rttMonJitterStatsStartTimeIndex OBJECT-TYPE
    SYNTAX TimeStamp
--    Rsyntax TimeTicks
    ACCESS not-accessible
    STATUS mandatory
    DESCRIPTION
        "The time when this row was created."
    ::= { rttMonJitterStatsEntry 1 }

rttMonJitterStatsCompletions OBJECT-TYPE
    SYNTAX Counter32
    ACCESS read-only
    STATUS mandatory
    DESCRIPTION
        "The number of jitter operation that have completed 
        successfully."
    ::= { rttMonJitterStatsEntry 2 }

rttMonJitterStatsOverThresholds OBJECT-TYPE
    SYNTAX Counter32
    ACCESS read-only
    STATUS mandatory
    DESCRIPTION
        "The number of jitter operations that violate threshold."
    ::= { rttMonJitterStatsEntry 3 }

rttMonJitterStatsNumOfRTT OBJECT-TYPE
    SYNTAX Counter32
    ACCESS read-only
    STATUS mandatory
    DESCRIPTION
        "The number of RTT's that are successfully measured."
    ::= { rttMonJitterStatsEntry 4 }

rttMonJitterStatsRTTSum OBJECT-TYPE
    SYNTAX Counter32
    ACCESS read-only
    STATUS mandatory
    DESCRIPTION
        "The sum of RTT's that are successfully measured."
    ::= { rttMonJitterStatsEntry 5 }

rttMonJitterStatsRTTSum2Low OBJECT-TYPE
    SYNTAX Counter32
    ACCESS read-only
    STATUS mandatory
    DESCRIPTION
        "The sum of squares of RTT's that are successfully measured
        (low order 32 bits)."
    ::= { rttMonJitterStatsEntry 6 }

rttMonJitterStatsRTTSum2High OBJECT-TYPE
    SYNTAX Counter32
    ACCESS read-only
    STATUS mandatory
    DESCRIPTION
        "The sum of squares of RTT's that are successfully measured
        (high order 32 bits)."
    ::= { rttMonJitterStatsEntry 7 }

rttMonJitterStatsRTTMin OBJECT-TYPE
    SYNTAX Gauge32
    ACCESS read-only
    STATUS mandatory
    DESCRIPTION
        "The minimum of RTT's that were successfully measured"
    ::= { rttMonJitterStatsEntry 8 }

rttMonJitterStatsRTTMax OBJECT-TYPE
    SYNTAX Gauge32
    ACCESS read-only
    STATUS mandatory
    DESCRIPTION
        "The maximum of RTT's that were successfully measured"
    ::= { rttMonJitterStatsEntry 9 }

rttMonJitterStatsMinOfPositivesSD OBJECT-TYPE
    SYNTAX Gauge32
    ACCESS read-only
    STATUS mandatory
    DESCRIPTION
        "The minimum of absolute values of all positive jitter values 
        from packets sent from source to destination."
    ::= { rttMonJitterStatsEntry 10 }

rttMonJitterStatsMaxOfPositivesSD OBJECT-TYPE
    SYNTAX Gauge32
    ACCESS read-only
    STATUS mandatory
    DESCRIPTION
        "The maximum of absolute values of all positive jitter values 
        from packets sent from source to destination."
    ::= { rttMonJitterStatsEntry 11 }

rttMonJitterStatsNumOfPositivesSD OBJECT-TYPE
    SYNTAX Counter32
    ACCESS read-only
    STATUS mandatory
    DESCRIPTION
        "The sum of number of all positive jitter values from packets 
        sent from source to destination."
    ::= { rttMonJitterStatsEntry 12 }

rttMonJitterStatsSumOfPositivesSD OBJECT-TYPE
    SYNTAX Counter32
    ACCESS read-only
    STATUS mandatory
    DESCRIPTION
        "The sum of all positive jitter values from packets 
        sent from source to destination."
    ::= { rttMonJitterStatsEntry 13 }

rttMonJitterStatsSum2PositivesSDLow OBJECT-TYPE
    SYNTAX Counter32
    ACCESS read-only
    STATUS mandatory
    DESCRIPTION
        "The sum of square of RTT's of all positive jitter values from 
        packets sent from source to destination (low order 32 bits)."
    ::= { rttMonJitterStatsEntry 14 }

rttMonJitterStatsSum2PositivesSDHigh OBJECT-TYPE
    SYNTAX Counter32
    ACCESS read-only
    STATUS mandatory
    DESCRIPTION
        "The sum of square of RTT's of all positive jitter values from 
        packets sent from source to destination (high order 32 bits)."
    ::= { rttMonJitterStatsEntry 15 }

rttMonJitterStatsMinOfNegativesSD OBJECT-TYPE
    SYNTAX Gauge32
    ACCESS read-only
    STATUS mandatory
    DESCRIPTION
        "The minimum of all negative jitter values from packets sent
        from source to destination."
    ::= { rttMonJitterStatsEntry 16 }

rttMonJitterStatsMaxOfNegativesSD OBJECT-TYPE
    SYNTAX Gauge32
    ACCESS read-only
    STATUS mandatory
    DESCRIPTION
        "The maximum of all negative jitter values from packets sent
        from source to destination."
    ::= { rttMonJitterStatsEntry 17 }

rttMonJitterStatsNumOfNegativesSD OBJECT-TYPE
    SYNTAX Counter32
    ACCESS read-only
    STATUS mandatory
    DESCRIPTION
        "The sum of number of all negative jitter values from packets
        sent from source to destination."
    ::= { rttMonJitterStatsEntry 18 }

rttMonJitterStatsSumOfNegativesSD OBJECT-TYPE
    SYNTAX Counter32
    ACCESS read-only
    STATUS mandatory
    DESCRIPTION
        "The sum of RTT's of all negative jitter values from packets
        sent from source to destination."
    ::= { rttMonJitterStatsEntry 19 }

rttMonJitterStatsSum2NegativesSDLow OBJECT-TYPE
    SYNTAX Counter32
    ACCESS read-only
    STATUS mandatory
    DESCRIPTION
        "The sum of square of RTT's of all negative jitter values from
        packets sent from source to destination (low order 32 bits)."
    ::= { rttMonJitterStatsEntry 20 }

rttMonJitterStatsSum2NegativesSDHigh OBJECT-TYPE
    SYNTAX Counter32
    ACCESS read-only
    STATUS mandatory
    DESCRIPTION
        "The sum of square of RTT's of all negative jitter values from
        packets sent from source to destination (high order 32 bits)."
    ::= { rttMonJitterStatsEntry 21 }

rttMonJitterStatsMinOfPositivesDS OBJECT-TYPE
    SYNTAX Gauge32
    ACCESS read-only
    STATUS mandatory
    DESCRIPTION
        "The minimum of all positive jitter values from packets sent
        from destination to source."
    ::= { rttMonJitterStatsEntry 22 }

rttMonJitterStatsMaxOfPositivesDS OBJECT-TYPE
    SYNTAX Gauge32
    ACCESS read-only
    STATUS mandatory
    DESCRIPTION
        "The maximum of all positive jitter values from packets sent
        from destination to source."
    ::= { rttMonJitterStatsEntry 23 }

rttMonJitterStatsNumOfPositivesDS OBJECT-TYPE
    SYNTAX Counter32
    ACCESS read-only
    STATUS mandatory
    DESCRIPTION
        "The sum of number of all positive jitter values from packets
        sent from destination to source."
    ::= { rttMonJitterStatsEntry 24 }

rttMonJitterStatsSumOfPositivesDS OBJECT-TYPE
    SYNTAX Counter32
    ACCESS read-only
    STATUS mandatory
    DESCRIPTION
        "The sum of RTT's of all positive jitter values from packets
        sent from destination to source."
    ::= { rttMonJitterStatsEntry 25 }

rttMonJitterStatsSum2PositivesDSLow OBJECT-TYPE
    SYNTAX Counter32
    ACCESS read-only
    STATUS mandatory
    DESCRIPTION
        "The sum of squares of RTT's of all positive jitter values from 
        packets sent from destination to source (low order 32 bits)."
    ::= { rttMonJitterStatsEntry 26 }

rttMonJitterStatsSum2PositivesDSHigh OBJECT-TYPE
    SYNTAX Counter32
    ACCESS read-only
    STATUS mandatory
    DESCRIPTION
        "The sum of squares of RTT's of all positive jitter values from 
        packets sent from destination to source (high order 32 bits)."
    ::= { rttMonJitterStatsEntry 27 }

rttMonJitterStatsMinOfNegativesDS OBJECT-TYPE
    SYNTAX Gauge32
    ACCESS read-only
    STATUS mandatory
    DESCRIPTION
        "The minimum of all negative jitter values from packets sent
        from destination to source."
    ::= { rttMonJitterStatsEntry 28 }

rttMonJitterStatsMaxOfNegativesDS OBJECT-TYPE
    SYNTAX Gauge32
    ACCESS read-only
    STATUS mandatory
    DESCRIPTION
        "The maximum of all negative jitter values from packets sent
        from destination to source."
    ::= { rttMonJitterStatsEntry 29 }

rttMonJitterStatsNumOfNegativesDS OBJECT-TYPE
    SYNTAX Counter32
    ACCESS read-only
    STATUS mandatory
    DESCRIPTION
        "The sum of number of all negative jitter values from packets
        sent from destination to source."
    ::= { rttMonJitterStatsEntry 30 }

rttMonJitterStatsSumOfNegativesDS OBJECT-TYPE
    SYNTAX Counter32
    ACCESS read-only
    STATUS mandatory
    DESCRIPTION
        "The sum of RTT's of all negative jitter values from packets
        sent from destination to source."
    ::= { rttMonJitterStatsEntry 31 }

rttMonJitterStatsSum2NegativesDSLow OBJECT-TYPE
    SYNTAX Counter32
    ACCESS read-only
    STATUS mandatory
    DESCRIPTION
        "The sum of squares of RTT's of all negative jitter values from 
        packets sent from destination to source (low order 32 bits)."
    ::= { rttMonJitterStatsEntry 32 }

rttMonJitterStatsSum2NegativesDSHigh OBJECT-TYPE
    SYNTAX Counter32
    ACCESS read-only
    STATUS mandatory
    DESCRIPTION
        "The sum of squares of RTT's of all negative jitter values from 
        packets sent from destination to source (high order 32 bits)."
    ::= { rttMonJitterStatsEntry 33 }

rttMonJitterStatsPacketLossSD OBJECT-TYPE
    SYNTAX Counter32
    ACCESS read-only
    STATUS mandatory
    DESCRIPTION
        "The number of packets lost when sent from source to destination."
    ::= { rttMonJitterStatsEntry 34 }

rttMonJitterStatsPacketLossDS OBJECT-TYPE
    SYNTAX Counter32
    ACCESS read-only
    STATUS mandatory
    DESCRIPTION
        "The number of packets lost when sent from destination to source."
    ::= { rttMonJitterStatsEntry 35 }

rttMonJitterStatsPacketOutOfSequence OBJECT-TYPE
    SYNTAX Counter32
    ACCESS read-only
    STATUS mandatory
    DESCRIPTION
        "The number of packets arrived out of sequence."
    ::= { rttMonJitterStatsEntry 36 }

rttMonJitterStatsPacketMIA OBJECT-TYPE
    SYNTAX Counter32
    ACCESS read-only
    STATUS mandatory
    DESCRIPTION
        "The number of packets that are lost for which we cannot determine
        the direction."
    ::= { rttMonJitterStatsEntry 37 }

rttMonJitterStatsPacketLateArrival OBJECT-TYPE
    SYNTAX Counter32
    ACCESS read-only
    STATUS mandatory
    DESCRIPTION
        "The number of packets that arrived after the timeout."
    ::= { rttMonJitterStatsEntry 38 }

rttMonJitterStatsError OBJECT-TYPE
    SYNTAX Counter32
    ACCESS read-only
    STATUS mandatory
    DESCRIPTION
        "The number of occasions when a jitter operation could not
        be initiated because an internal error"
    ::= { rttMonJitterStatsEntry 39 }

rttMonJitterStatsBusies OBJECT-TYPE
    SYNTAX Counter32
    ACCESS read-only
    STATUS mandatory
    DESCRIPTION
        "The number of occasions when a jitter operation could not
        be initiated because a previous jitter operation has not
        been completed."
    ::= { rttMonJitterStatsEntry 40 }

rttMonHistoryCollectionTable OBJECT-TYPE
    SYNTAX SEQUENCE OF RttMonHistoryCollectionEntry
    ACCESS not-accessible
    STATUS mandatory
    DESCRIPTION
        "The history collection database.
        
        The history table contains a point by point rolling 
        history of the most recent RTT operations for each 
        conceptual RTT control row.  The rolling history of this 
        information is maintained in a series of 'live(s)', each
        containing a series of 'bucket(s)', each 'bucket' 
        contains a series of 'sample(s)'.
        
        Each conceptual history row can have lives.  A life is 
        defined by the rttMonCtrlOperRttLife object.  A new life 
        will be created when rttMonCtrlOperState transitions
        'active'.  When the number of lives become greater 
        than rttMonHistoryAdminNumLives the oldest life will be 
        discarded and a new life will be created by incrementing
        the index.
        
        The path exploration RTT operation will be kept as an
        entry in this table."
    ::= { rttMonHistory 1 }

rttMonHistoryCollectionEntry OBJECT-TYPE
    SYNTAX RttMonHistoryCollectionEntry
    ACCESS not-accessible
    STATUS mandatory
    DESCRIPTION
        "A list of history objects that are recorded for each 
        RTT operation.
        
        The history collection table has four indices.  Each 
        described as follows:
          -  The first index correlates its entries to a 
              conceptual RTT control row via the 
              rttMonCtrlAdminIndex object.  
          -  The second index uniquely identifies the results 
              of each 'life' as defined by the 
              rttMonCtrlOperRttLife object.  
          -  The third index uniquely identifies the number of 
              buckets in a life.  A bucket will contain one 
              sample per bucket if the rttMonCtrlAdminRttType 
              object is set to any value
              other than 'pathEcho'.  If the 
              rttMonCtrlAdminRttType object is set to 
              'pathEcho', a bucket will contain one sample per 
              hop along a path to the target (including the 
              target).  
          -  The fourth index uniquely identifies the number of 
              samples in a bucket.   Again, if the 
              rttMonCtrlAdminRttType object is set to 
              'pathEcho', this value is associated with each 
              hop in an ascending order, thus for the 
              first hop on a path, this index will be 1, the 
              second will be 2 and so on.   For all other values
              of rttMonCtrlAdminRttType this will be 1."
    INDEX { rttMonCtrlAdminIndex, rttMonHistoryCollectionLifeIndex, rttMonHistoryCollectionBucketIndex, rttMonHistoryCollectionSampleIndex }
    ::= { rttMonHistoryCollectionTable 1 }

RttMonHistoryCollectionEntry ::= SEQUENCE {
    rttMonHistoryCollectionLifeIndex Integer32,
    rttMonHistoryCollectionBucketIndex Integer32,
    rttMonHistoryCollectionSampleIndex Integer32,
    rttMonHistoryCollectionSampleTime TimeStamp,
    rttMonHistoryCollectionAddress RttMonTargetAddress,
    rttMonHistoryCollectionCompletionTime Gauge32,
    rttMonHistoryCollectionSense RttResponseSense,
    rttMonHistoryCollectionApplSpecificSense Integer32,
    rttMonHistoryCollectionSenseDescription DisplayString
    }

rttMonHistoryCollectionLifeIndex OBJECT-TYPE
    SYNTAX Integer32(1..2147483647)
    ACCESS not-accessible
    STATUS mandatory
    DESCRIPTION
        "This uniquely defines a life for a conceptual history 
        row.
        
        For a particular value of rttMonHistoryCollectionLifeIndex,
        the agent assigns the first value of 1, the second value 
        of 2, and so on.  The sequence keeps incrementing, 
        despite older (lower) values being removed from the 
        table."
    ::= { rttMonHistoryCollectionEntry 1 }

rttMonHistoryCollectionBucketIndex OBJECT-TYPE
    SYNTAX Integer32(1..2147483647)
    ACCESS not-accessible
    STATUS mandatory
    DESCRIPTION
        "When the RttMonRttType is 'pathEcho', this uniquely 
        defines a bucket for a given value of 
        rttMonHistoryCollectionLifeIndex.  For all other 
        RttMonRttType this value will be the number of
        operations per a lifetime.  Thus, this object 
        increments on each operation attempt.
        
        For a particular value of 
        rttMonHistoryCollectionLifeIndex, the agent assigns 
        the first value of 1, the second value of 2, and so 
        on.  The sequence keeps incrementing until the number
        of buckets equals rttMonHistoryAdminNumBuckets, after
        which the most recent rttMonHistoryAdminNumBuckets 
        buckets are retained (the index is incremented though)."
    ::= { rttMonHistoryCollectionEntry 2 }

rttMonHistoryCollectionSampleIndex OBJECT-TYPE
    SYNTAX Integer32(1..512)
    ACCESS not-accessible
    STATUS mandatory
    DESCRIPTION
        "This uniquely defines a row for a given value of 
        rttMonHistoryCollectionBucketIndex.  This object
        represents a hop along a path to the Target.
        
        For a particular value of 
        rttMonHistoryCollectionBucketIndex, the agent assigns 
        the first value of 1, the second value of 2, and so on.
        The sequence keeps incrementing until the number of 
        samples equals rttMonHistoryAdminNumSamples, then no 
        new samples are created for the current 
        rttMonHistoryCollectionBucketIndex.
        
        When the RttMonRttType is 'pathEcho', this value 
        directly represents the number of hops along a 
        path to a target, thus we can only support 512 hops.
        For all other values of RttMonRttType this object
        will be one."
    ::= { rttMonHistoryCollectionEntry 3 }

rttMonHistoryCollectionSampleTime OBJECT-TYPE
    SYNTAX TimeStamp
--    Rsyntax TimeTicks
    ACCESS read-only
    STATUS mandatory
    DESCRIPTION
        "The time that the RTT operation was initiated."
    ::= { rttMonHistoryCollectionEntry 4 }

rttMonHistoryCollectionAddress OBJECT-TYPE
    SYNTAX RttMonTargetAddress
--    Rsyntax OCTET STRING
    ACCESS read-only
    STATUS mandatory
    DESCRIPTION
        "When the RttMonRttType is 'echo' or 'pathEcho' this
        is a string which specifies the address of the target for
        the this RTT operation.  For all other values of
        RttMonRttType this string will be null.
        
        This address will be the address of the hop along the
        path to the rttMonEchoAdminTargetAddress address,
        including rttMonEchoAdminTargetAddress address, or just
        the rttMonEchoAdminTargetAddress address, when the
        path information is not collected.  This behavior is
        defined by the rttMonCtrlAdminRttType object.
        
        The interpretation of this string depends on the type
        of RTT operation selected, as specified by the
        rttMonEchoAdminProtocol object.
        
        See rttMonEchoAdminTargetAddress for a complete
        description."
    ::= { rttMonHistoryCollectionEntry 5 }

rttMonHistoryCollectionCompletionTime OBJECT-TYPE
    SYNTAX Gauge32
--  Units
--    milliseconds
    ACCESS read-only
    STATUS mandatory
    DESCRIPTION
        "This is the operation completion time of the RTT 
        operation.  If the RTT operation fails 
        (rttMonHistoryCollectionSense is any 
        value other than ok), this has a value of 0."
    ::= { rttMonHistoryCollectionEntry 6 }

rttMonHistoryCollectionSense OBJECT-TYPE
    SYNTAX RttResponseSense
--    Rsyntax INTEGER {
--        ok(1),
--        disconnected(2),
--        overThreshold(3),
--        timeout(4),
--        busy(5),
--        notConnected(6),
--        dropped(7),
--        sequenceError(8),
--        verifyError(9),
--        applicationSpecific(10),
--        dnsServerTimeout(11),
--        tcpConnectTimeout(12),
--        httpTransactionTimeout(13),
--        dnsQueryError(14),
--        httpError(15),
--        error(16)
--        }
    ACCESS read-only
    STATUS mandatory
    DESCRIPTION
        "A sense code for the completion status of the RTT 
        operation."
    ::= { rttMonHistoryCollectionEntry 7 }

rttMonHistoryCollectionApplSpecificSense OBJECT-TYPE
    SYNTAX Integer32(1001..2147483647)
    ACCESS read-only
    STATUS mandatory
    DESCRIPTION
        "An application specific sense code for the 
        completion status of the last RTT operation.  This 
        object will only be valid when the 
        rttMonHistoryCollectionSense object is set to 
        'applicationSpecific'.  Otherwise, this object's 
        value is not valid."
    ::= { rttMonHistoryCollectionEntry 8 }

rttMonHistoryCollectionSenseDescription OBJECT-TYPE
    SYNTAX DisplayString
--    Rsyntax OCTET STRING(SIZE(0..255))
    ACCESS read-only
    STATUS mandatory
    DESCRIPTION
        "A sense description for the completion status of 
        the last RTT operation when the 
        rttMonHistoryCollectionSense object is set to 
        'applicationSpecific'."
    ::= { rttMonHistoryCollectionEntry 9 }

rttMonConnectionChangeNotification TRAP-TYPE
-- Reverse mappable trap
    ENTERPRISE rttMonNotificationsPrefix
    VARIABLES {
        rttMonCtrlAdminTag, rttMonHistoryCollectionAddress, 
        rttMonCtrlOperConnectionLostOccurred }
--  Status
--    mandatory
    DESCRIPTION
        "This notification is only valid when the RttMonRttType
        is 'echo' or 'pathEcho'.
        
        A rttMonConnectionChangeNotification indicates that a
        connection to a target (not to a hop along the path
        to a target) has either failed on establishment or 
        been lost and when reestablished.  Precisely, this
        has resulted in rttMonCtrlOperConnectionLostOccurred
        changing value.
        
        If History is not being collected, the instance values 
        for the rttMonHistoryCollectionAddress object will not 
        be valid.  When RttMonRttType is not 'echo' or 'pathEcho'
        the rttMonHistoryCollectionAddress object will be null."
    ::= 1

rttMonTimeoutNotification TRAP-TYPE
-- Reverse mappable trap
    ENTERPRISE rttMonNotificationsPrefix
    VARIABLES {
        rttMonCtrlAdminTag, rttMonHistoryCollectionAddress, 
        rttMonCtrlOperTimeoutOccurred }
--  Status
--    mandatory
    DESCRIPTION
        "A rttMonTimeoutNotification indicates the occurrence of 
        a timeout for a RTT operation, and it indicates the 
        clearing of such a condition by a subsequent RTT 
        operation. Precisely, this has resulted in 
        rttMonCtrlOperTimeoutOccurred changing value. 
        
        When the RttMonRttType is 'pathEcho', this 
        notification will only be sent when the timeout 
        occurs during an operation to the target and not to
        a hop along the path to the target.  This also 
        applies to the clearing of the timeout. 
        
        If History is not being collected, the instance values 
        for the rttMonHistoryCollectionAddress object will not 
        be valid.  When RttMonRttType is not 'echo' or 'pathEcho'
        the rttMonHistoryCollectionAddress object will be null."
    ::= 2

rttMonThresholdNotification TRAP-TYPE
-- Reverse mappable trap
    ENTERPRISE rttMonNotificationsPrefix
    VARIABLES {
        rttMonCtrlAdminTag, rttMonHistoryCollectionAddress, 
        rttMonCtrlOperOverThresholdOccurred }
--  Status
--    mandatory
    DESCRIPTION
        "A rttMonThresholdNotification indicates the 
        occurrence of a threshold violation for a RTT operation,
        and it indicates the previous violation has subsided for
        a subsequent RTT operation.  Precisely, this has resulted
        in rttMonCtrlOperOverThresholdOccurred changing value.  
        
        When the RttMonRttType is 'pathEcho', this 
        notification will only be sent when the threshold
        violation occurs during an operation to the target and
        not to a hop along the path to the target.  This also
        applies to the subsiding of a threshold condition.
        
        If History is not being collected, the instance values 
        for the rttMonHistoryCollectionAddress object will not 
        be valid.  When RttMonRttType is not 'echo' or 'pathEcho'
        the rttMonHistoryCollectionAddress object will be null."
    ::= 3

ciscoApplGroup OBJECT IDENTIFIER ::= { ciscoRttMonMibGroups 1 }
-- OBJECT-GROUP
--  Status
--    obsolete
--  Descr
--    A collection of objects providing the RTT Monitoring
--    Application defaults.
--    
--    This group of information is provided to the agent when
--    the Application starts.
--  objects
--    rttMonApplVersion, rttMonApplMaxPacketDataSize, 
--    rttMonApplTimeOfLastSet, rttMonApplSupportedRttTypesValid, 
--    rttMonApplSupportedProtocolsValid, 
--    rttMonApplNumCtrlAdminEntry, rttMonApplReset, 
--    rttMonApplPreConfigedReset, rttMonApplPreConfigedValid, 
--    rttMonApplProbeCapacity, rttMonApplFreeMemLowWaterMark, 
--    rttMonApplLatestSetError

ciscoCtrlGroup OBJECT IDENTIFIER ::= { ciscoRttMonMibGroups 2 }
-- OBJECT-GROUP
--  Status
--    obsolete
--  Descr
--    A collection of objects providing the Administration,
--    Operational, Last Statistical values for the RTT
--    Monitoring Application.
--  objects
--    rttMonCtrlAdminOwner, rttMonCtrlAdminTag, 
--    rttMonCtrlAdminRttType, rttMonCtrlAdminThreshold, 
--    rttMonCtrlAdminFrequency, rttMonCtrlAdminTimeout, 
--    rttMonCtrlAdminVerifyData, rttMonCtrlAdminStatus, 
--    rttMonEchoAdminProtocol, rttMonEchoAdminTargetAddress, 
--    rttMonEchoAdminPktDataRequestSize, 
--    rttMonEchoAdminPktDataResponseSize, rttMonFileIOAdminFilePath, 
--    rttMonFileIOAdminSize, rttMonFileIOAdminAction, 
--    rttMonScriptAdminName, rttMonScriptAdminCmdLineParams, 
--    rttMonScheduleAdminRttLife, rttMonScheduleAdminRttStartTime, 
--    rttMonScheduleAdminConceptRowAgeout, 
--    rttMonReactAdminConnectionEnable, 
--    rttMonReactAdminTimeoutEnable, rttMonReactAdminThresholdType, 
--    rttMonReactAdminThresholdFalling, 
--    rttMonReactAdminThresholdCount, 
--    rttMonReactAdminThresholdCount2, rttMonReactAdminActionType, 
--    rttMonStatisticsAdminNumHourGroups, 
--    rttMonStatisticsAdminNumPaths, rttMonStatisticsAdminNumHops, 
--    rttMonStatisticsAdminNumDistBuckets, 
--    rttMonStatisticsAdminDistInterval, rttMonHistoryAdminNumLives, 
--    rttMonHistoryAdminNumBuckets, rttMonHistoryAdminNumSamples, 
--    rttMonHistoryAdminFilter, rttMonCtrlOperModificationTime, 
--    rttMonCtrlOperDiagText, rttMonCtrlOperResetTime, 
--    rttMonCtrlOperOctetsInUse, 
--    rttMonCtrlOperConnectionLostOccurred, 
--    rttMonCtrlOperTimeoutOccurred, 
--    rttMonCtrlOperOverThresholdOccurred, rttMonCtrlOperNumRtts, 
--    rttMonCtrlOperRttLife, rttMonCtrlOperState, 
--    rttMonLatestRttOperCompletionTime, rttMonLatestRttOperSense, 
--    rttMonLatestRttOperApplSpecificSense, 
--    rttMonLatestRttOperSenseDescription, rttMonLatestRttOperTime, 
--    rttMonLatestRttOperAddress, rttMonReactTriggerAdminStatus, 
--    rttMonReactTriggerOperState

ciscoStatsGroup OBJECT IDENTIFIER ::= { ciscoRttMonMibGroups 3 }
-- OBJECT-GROUP
--  Status
--    mandatory
--  Descr
--    A collection of objects providing accumulated statistical 
--    history.
--  objects
--    rttMonStatsCaptureCompletions, 
--    rttMonStatsCaptureOverThresholds, 
--    rttMonStatsCaptureSumCompletionTime, 
--    rttMonStatsCaptureSumCompletionTime2Low, 
--    rttMonStatsCaptureSumCompletionTime2High, 
--    rttMonStatsCaptureCompletionTimeMax, 
--    rttMonStatsCaptureCompletionTimeMin, 
--    rttMonStatsCollectNumDisconnects, rttMonStatsCollectTimeouts, 
--    rttMonStatsCollectBusies, rttMonStatsCollectNoConnections, 
--    rttMonStatsCollectDrops, rttMonStatsCollectSequenceErrors, 
--    rttMonStatsCollectVerifyErrors, rttMonStatsCollectAddress, 
--    rttMonStatsTotalsElapsedTime, rttMonStatsTotalsInitiations

ciscoHistoryGroup OBJECT IDENTIFIER ::= { ciscoRttMonMibGroups 4 }
-- OBJECT-GROUP
--  Status
--    mandatory
--  Descr
--    A collection of objects providing point by point
--    history of each RTT operation.
--  objects
--    rttMonHistoryCollectionSampleTime, 
--    rttMonHistoryCollectionAddress, 
--    rttMonHistoryCollectionCompletionTime, 
--    rttMonHistoryCollectionSense, 
--    rttMonHistoryCollectionApplSpecificSense, 
--    rttMonHistoryCollectionSenseDescription

ciscoCtrlGroupRev1 OBJECT IDENTIFIER ::= { ciscoRttMonMibGroups 5 }
-- OBJECT-GROUP
--  Status
--    mandatory
--  Descr
--    A collection of objects that were added to enhance the 
--    functionality of the RTT application.
--  objects
--    rttMonEchoAdminTargetPort, rttMonEchoAdminSourceAddress, 
--    rttMonEchoAdminSourcePort, rttMonEchoAdminControlEnable, 
--    rttMonEchoAdminTOS, rttMonEchoAdminLSREnable, 
--    rttMonEchoPathAdminHopAddress

ciscoCtrlGroupRev2 OBJECT IDENTIFIER ::= { ciscoRttMonMibGroups 6 }
-- OBJECT-GROUP
--  Status
--    mandatory
--  Descr
--    A collection of objects that were added to enhance the 
--    functionality of the RTT application to configure HTTP, DNS and 
--    Jitter probes.
--  objects
--    rttMonEchoAdminTargetAddressString, rttMonEchoAdminNameServer, 
--    rttMonEchoAdminOperation, rttMonEchoAdminHTTPVersion, 
--    rttMonEchoAdminURL, rttMonEchoAdminCache, 
--    rttMonEchoAdminInterval, rttMonEchoAdminNumPackets, 
--    rttMonEchoAdminProxy, rttMonEchoAdminString1, 
--    rttMonEchoAdminString2, rttMonEchoAdminString3, 
--    rttMonEchoAdminString4, rttMonEchoAdminString5

ciscoLatestOperGroupRev1 OBJECT IDENTIFIER ::= { ciscoRttMonMibGroups 7 }
-- OBJECT-GROUP
--  Status
--    mandatory
--  Descr
--    A collection of objects that were added to store the latest 
--    operational results for HTTP, DNS and Jitter probes.
--  objects
--    rttMonLatestHTTPOperRTT, rttMonLatestHTTPOperDNSRTT, 
--    rttMonLatestHTTPOperTCPConnectRTT, 
--    rttMonLatestHTTPOperTransactionRTT, 
--    rttMonLatestHTTPOperMessageBodyOctets, 
--    rttMonLatestHTTPOperSense, 
--    rttMonLatestHTTPErrorSenseDescription, 
--    rttMonLatestJitterOperNumOfRTT, rttMonLatestJitterOperRTTSum, 
--    rttMonLatestJitterOperRTTSum2, rttMonLatestJitterOperRTTMin, 
--    rttMonLatestJitterOperRTTMax, 
--    rttMonLatestJitterOperMinOfPositivesSD, 
--    rttMonLatestJitterOperMaxOfPositivesSD, 
--    rttMonLatestJitterOperNumOfPositivesSD, 
--    rttMonLatestJitterOperSumOfPositivesSD, 
--    rttMonLatestJitterOperSum2PositivesSD, 
--    rttMonLatestJitterOperMinOfNegativesSD, 
--    rttMonLatestJitterOperMaxOfNegativesSD, 
--    rttMonLatestJitterOperNumOfNegativesSD, 
--    rttMonLatestJitterOperSumOfNegativesSD, 
--    rttMonLatestJitterOperSum2NegativesSD, 
--    rttMonLatestJitterOperMinOfPositivesDS, 
--    rttMonLatestJitterOperMaxOfPositivesDS, 
--    rttMonLatestJitterOperNumOfPositivesDS, 
--    rttMonLatestJitterOperSumOfPositivesDS, 
--    rttMonLatestJitterOperSum2PositivesDS, 
--    rttMonLatestJitterOperMinOfNegativesDS, 
--    rttMonLatestJitterOperMaxOfNegativesDS, 
--    rttMonLatestJitterOperNumOfNegativesDS, 
--    rttMonLatestJitterOperSumOfNegativesDS, 
--    rttMonLatestJitterOperSum2NegativesDS, 
--    rttMonLatestJitterOperPacketLossSD, 
--    rttMonLatestJitterOperPacketLossDS, 
--    rttMonLatestJitterOperPacketOutOfSequence, 
--    rttMonLatestJitterOperPacketMIA, 
--    rttMonLatestJitterOperPacketLateArrival, 
--    rttMonLatestJitterOperSense, 
--    rttMonLatestJitterErrorSenseDescription

ciscoStatsGroupRev1 OBJECT IDENTIFIER ::= { ciscoRttMonMibGroups 8 }
-- OBJECT-GROUP
--  Status
--    mandatory
--  Descr
--    A collection of objects that were added to enhance the 
--    functionality of the RTT application to store 'HTTP' and 
--    'Jitter' probes statistics.
--  objects
--    rttMonHTTPStatsCompletions, rttMonHTTPStatsOverThresholds, 
--    rttMonHTTPStatsRTTSum, rttMonHTTPStatsRTTSum2Low, 
--    rttMonHTTPStatsRTTSum2High, rttMonHTTPStatsRTTMin, 
--    rttMonHTTPStatsRTTMax, rttMonHTTPStatsDNSRTTSum, 
--    rttMonHTTPStatsTCPConnectRTTSum, 
--    rttMonHTTPStatsTransactionRTTSum, 
--    rttMonHTTPStatsMessageBodyOctetsSum, 
--    rttMonHTTPStatsDNSServerTimeout, 
--    rttMonHTTPStatsTCPConnectTimeout, 
--    rttMonHTTPStatsTransactionTimeout, 
--    rttMonHTTPStatsDNSQueryError, rttMonHTTPStatsHTTPError, 
--    rttMonHTTPStatsError, rttMonHTTPStatsBusies, 
--    rttMonJitterStatsCompletions, rttMonJitterStatsOverThresholds, 
--    rttMonJitterStatsNumOfRTT, rttMonJitterStatsRTTSum, 
--    rttMonJitterStatsRTTSum2Low, rttMonJitterStatsRTTSum2High, 
--    rttMonJitterStatsRTTMin, rttMonJitterStatsRTTMax, 
--    rttMonJitterStatsMinOfPositivesSD, 
--    rttMonJitterStatsMaxOfPositivesSD, 
--    rttMonJitterStatsNumOfPositivesSD, 
--    rttMonJitterStatsSumOfPositivesSD, 
--    rttMonJitterStatsSum2PositivesSDLow, 
--    rttMonJitterStatsSum2PositivesSDHigh, 
--    rttMonJitterStatsMinOfNegativesSD, 
--    rttMonJitterStatsMaxOfNegativesSD, 
--    rttMonJitterStatsNumOfNegativesSD, 
--    rttMonJitterStatsSumOfNegativesSD, 
--    rttMonJitterStatsSum2NegativesSDLow, 
--    rttMonJitterStatsSum2NegativesSDHigh, 
--    rttMonJitterStatsMinOfPositivesDS, 
--    rttMonJitterStatsMaxOfPositivesDS, 
--    rttMonJitterStatsNumOfPositivesDS, 
--    rttMonJitterStatsSumOfPositivesDS, 
--    rttMonJitterStatsSum2PositivesDSLow, 
--    rttMonJitterStatsSum2PositivesDSHigh, 
--    rttMonJitterStatsMinOfNegativesDS, 
--    rttMonJitterStatsMaxOfNegativesDS, 
--    rttMonJitterStatsNumOfNegativesDS, 
--    rttMonJitterStatsSumOfNegativesDS, 
--    rttMonJitterStatsSum2NegativesDSLow, 
--    rttMonJitterStatsSum2NegativesDSHigh, 
--    rttMonJitterStatsPacketLossSD, rttMonJitterStatsPacketLossDS, 
--    rttMonJitterStatsPacketOutOfSequence, 
--    rttMonJitterStatsPacketMIA, 
--    rttMonJitterStatsPacketLateArrival, rttMonJitterStatsError, 
--    rttMonJitterStatsBusies

ciscoApplGroupRev1 OBJECT IDENTIFIER ::= { ciscoRttMonMibGroups 9 }
-- OBJECT-GROUP
--  Status
--    mandatory
--  Descr
--    A collection of objects providing the RTT Monitoring
--    Application defaults.
--    
--    This group of information is provided to the agent when
--    the Application starts.
--  objects
--    rttMonApplVersion, rttMonApplMaxPacketDataSize, 
--    rttMonApplTimeOfLastSet, rttMonApplSupportedRttTypesValid, 
--    rttMonApplSupportedProtocolsValid, 
--    rttMonApplNumCtrlAdminEntry, rttMonApplReset

ciscoCtrlGroupRev3 OBJECT IDENTIFIER ::= { ciscoRttMonMibGroups 10 }
-- OBJECT-GROUP
--  Status
--    mandatory
--  Descr
--    A collection of objects providing the Administration,
--    Operational, Last Statistical values for the RTT
--    Monitoring Application.
--  objects
--    rttMonCtrlAdminOwner, rttMonCtrlAdminTag, 
--    rttMonCtrlAdminRttType, rttMonCtrlAdminThreshold, 
--    rttMonCtrlAdminFrequency, rttMonCtrlAdminTimeout, 
--    rttMonCtrlAdminVerifyData, rttMonCtrlAdminStatus, 
--    rttMonCtrlAdminNvgen, rttMonEchoAdminProtocol, 
--    rttMonEchoAdminTargetAddress, 
--    rttMonEchoAdminPktDataRequestSize, 
--    rttMonEchoAdminPktDataResponseSize, 
--    rttMonScheduleAdminRttLife, rttMonScheduleAdminRttStartTime, 
--    rttMonScheduleAdminConceptRowAgeout, 
--    rttMonReactAdminConnectionEnable, 
--    rttMonReactAdminTimeoutEnable, rttMonReactAdminThresholdType, 
--    rttMonReactAdminThresholdFalling, 
--    rttMonReactAdminThresholdCount, 
--    rttMonReactAdminThresholdCount2, rttMonReactAdminActionType, 
--    rttMonStatisticsAdminNumHourGroups, 
--    rttMonStatisticsAdminNumPaths, rttMonStatisticsAdminNumHops, 
--    rttMonStatisticsAdminNumDistBuckets, 
--    rttMonStatisticsAdminDistInterval, rttMonHistoryAdminNumLives, 
--    rttMonHistoryAdminNumBuckets, rttMonHistoryAdminNumSamples, 
--    rttMonHistoryAdminFilter, rttMonCtrlOperModificationTime, 
--    rttMonCtrlOperDiagText, rttMonCtrlOperResetTime, 
--    rttMonCtrlOperOctetsInUse, 
--    rttMonCtrlOperConnectionLostOccurred, 
--    rttMonCtrlOperTimeoutOccurred, 
--    rttMonCtrlOperOverThresholdOccurred, rttMonCtrlOperNumRtts, 
--    rttMonCtrlOperRttLife, rttMonCtrlOperState, 
--    rttMonLatestRttOperCompletionTime, rttMonLatestRttOperSense, 
--    rttMonLatestRttOperApplSpecificSense, 
--    rttMonLatestRttOperSenseDescription, rttMonLatestRttOperTime, 
--    rttMonLatestRttOperAddress, rttMonReactTriggerAdminStatus, 
--    rttMonReactTriggerOperState

ciscoRttMonMibCompliance OBJECT IDENTIFIER ::= { ciscoRttMonMibCompliances 1 }
-- MODULE-COMPLIANCE
--  Status
--    obsolete
--  Descr
--    The compliance statement for the Round Trip Time (RTT)
--     Monitoring Application Architecture.
--  Module
--    >>current<<
--   MandGroup
--    ciscoApplGroup
--   MandGroup
--    ciscoCtrlGroup
--   MandGroup
--    ciscoStatsGroup
--   MandGroup
--    ciscoHistoryGroup

ciscoRttMonMibComplianceRev1 OBJECT IDENTIFIER ::= { ciscoRttMonMibCompliances 2 }
-- MODULE-COMPLIANCE
--  Status
--    obsolete
--  Descr
--    The compliance statement for new MIB extensions for 'udpEcho' and
--    'tcpConnect'
--  Module
--    >>current<<
--   MandGroup
--    ciscoApplGroup
--   MandGroup
--    ciscoCtrlGroup
--   MandGroup
--    ciscoStatsGroup
--   MandGroup
--    ciscoHistoryGroup
--   MandGroup
--    ciscoCtrlGroupRev1

ciscoRttMonMibComplianceRev2 OBJECT IDENTIFIER ::= { ciscoRttMonMibCompliances 3 }
-- MODULE-COMPLIANCE
--  Status
--    obsolete
--  Descr
--    The compliance statement for new MIB extensions for 'HTTP', 'DNS' 
--    and 'Jitter' probes
--  Module
--    >>current<<
--   MandGroup
--    ciscoApplGroup
--   MandGroup
--    ciscoCtrlGroup
--   MandGroup
--    ciscoStatsGroup
--   MandGroup
--    ciscoHistoryGroup
--   MandGroup
--    ciscoCtrlGroupRev1
--   MandGroup
--    ciscoCtrlGroupRev2
--   MandGroup
--    ciscoLatestOperGroupRev1
--   MandGroup
--    ciscoStatsGroupRev1

ciscoRttMonMibComplianceRev3 OBJECT IDENTIFIER ::= { ciscoRttMonMibCompliances 4 }
-- MODULE-COMPLIANCE
--  Status
--    mandatory
--  Descr
--    The compliance statement for new MIB extensions without the obsolete
--    items
--  Module
--    >>current<<
--   MandGroup
--    ciscoApplGroupRev1
--   MandGroup
--    ciscoCtrlGroupRev3
--   MandGroup
--    ciscoStatsGroup
--   MandGroup
--    ciscoHistoryGroup
--   MandGroup
--    ciscoCtrlGroupRev1
--   MandGroup
--    ciscoCtrlGroupRev2
--   MandGroup
--    ciscoLatestOperGroupRev1
--   MandGroup
--    ciscoStatsGroupRev1


END
