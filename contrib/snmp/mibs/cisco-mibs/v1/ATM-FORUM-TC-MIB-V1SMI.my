-- MIB created 6/25/99 12:56:38, by
--   SMIC (the next generation) version 1.6.29, November 22, 1994.

ATM-FORUM-TC-MIB DEFINITIONS ::= BEGIN

-- From file: "ATM-FORUM-TC-MIB.my"

IMPORTS
    enterprises
            FROM RFC1155-SMI;

atmForum        OBJECT IDENTIFIER ::= { enterprises 353 }
atmForumAdmin   OBJECT IDENTIFIER ::= { atmForum 1 }
atmfTransmissionTypes OBJECT IDENTIFIER ::= { atmForumAdmin 2 }
atmfMediaTypes  OBJECT IDENTIFIER ::= { atmForumAdmin 3 }
atmfTrafficDescrTypes OBJECT IDENTIFIER ::= { atmForumAdmin 4 }
atmfSrvcRegTypes OBJECT IDENTIFIER ::= { atmForumAdmin 5 }
atmForumUni     OBJECT IDENTIFIER ::= { atmForum 2 }
atmfPhysicalGroup OBJECT IDENTIFIER ::= { atmForumUni 1 }
atmfAtmLayerGroup OBJECT IDENTIFIER ::= { atmForumUni 2 }
atmfAtmStatsGroup OBJECT IDENTIFIER ::= { atmForumUni 3 }
atmfVpcGroup    OBJECT IDENTIFIER ::= { atmForumUni 4 }
atmfVccGroup    OBJECT IDENTIFIER ::= { atmForumUni 5 }
atmfAddressGroup OBJECT IDENTIFIER ::= { atmForumUni 6 }
atmfNetPrefixGroup OBJECT IDENTIFIER ::= { atmForumUni 7 }
atmfSrvcRegistryGroup OBJECT IDENTIFIER ::= { atmForumUni 8 }
atmfVpcAbrGroup OBJECT IDENTIFIER ::= { atmForumUni 9 }
atmfVccAbrGroup OBJECT IDENTIFIER ::= { atmForumUni 10 }
atmfAddressRegistrationAdminGroup OBJECT IDENTIFIER ::= { atmForumUni 11 }
atmfUnknownType OBJECT IDENTIFIER ::= { atmfTransmissionTypes 1 }
atmfSonetSTS3c  OBJECT IDENTIFIER ::= { atmfTransmissionTypes 2 }
atmfDs3         OBJECT IDENTIFIER ::= { atmfTransmissionTypes 3 }
atmf4B5B        OBJECT IDENTIFIER ::= { atmfTransmissionTypes 4 }
atmf8B10B       OBJECT IDENTIFIER ::= { atmfTransmissionTypes 5 }
atmfSonetSTS12c OBJECT IDENTIFIER ::= { atmfTransmissionTypes 6 }
atmfE3          OBJECT IDENTIFIER ::= { atmfTransmissionTypes 7 }
atmfT1          OBJECT IDENTIFIER ::= { atmfTransmissionTypes 8 }
atmfE1          OBJECT IDENTIFIER ::= { atmfTransmissionTypes 9 }
atmfMediaUnknownType OBJECT IDENTIFIER ::= { atmfMediaTypes 1 }
atmfMediaCoaxCable OBJECT IDENTIFIER ::= { atmfMediaTypes 2 }
atmfMediaSingleMode OBJECT IDENTIFIER ::= { atmfMediaTypes 3 }
atmfMediaMultiMode OBJECT IDENTIFIER ::= { atmfMediaTypes 4 }
atmfMediaStp    OBJECT IDENTIFIER ::= { atmfMediaTypes 5 }
atmfMediaUtp    OBJECT IDENTIFIER ::= { atmfMediaTypes 6 }
atmfNoDescriptor OBJECT IDENTIFIER ::= { atmfTrafficDescrTypes 1 }
atmfPeakRate    OBJECT IDENTIFIER ::= { atmfTrafficDescrTypes 2 }
atmfNoClpNoScr  OBJECT IDENTIFIER ::= { atmfTrafficDescrTypes 3 }
atmfClpNoTaggingNoScr OBJECT IDENTIFIER ::= { atmfTrafficDescrTypes 4 }
atmfClpTaggingNoScr OBJECT IDENTIFIER ::= { atmfTrafficDescrTypes 5 }
atmfNoClpScr    OBJECT IDENTIFIER ::= { atmfTrafficDescrTypes 6 }
atmfClpNoTaggingScr OBJECT IDENTIFIER ::= { atmfTrafficDescrTypes 7 }
atmfClpTaggingScr OBJECT IDENTIFIER ::= { atmfTrafficDescrTypes 8 }
atmfClpNoTaggingMcr OBJECT IDENTIFIER ::= { atmfTrafficDescrTypes 9 }

TruthValue ::= INTEGER {
        true(1),
        false(2)
        }
-- TEXTUAL-CONVENTION
--  Status
--    mandatory
--  Descr
--    Boolean values use this data type from RFC-1903

ClnpAddress ::= OCTET STRING(SIZE(1..21))
-- TEXTUAL-CONVENTION
--  Status
--    mandatory
--  Descr
--    CLNP address values use this data type from RFC-1238

AtmServiceCategory ::= INTEGER {
        other(1),
        cbr(2),
        rtVbr(3),
        nrtVbr(4),
        abr(5),
        ubr(6)
        }
-- TEXTUAL-CONVENTION
--  Status
--    mandatory
--  Descr
--    ATM Service Categories use this data type

AtmAddress ::= OCTET STRING(SIZE(8 | 20))
-- TEXTUAL-CONVENTION
--  Status
--    mandatory
--  Descr
--    ATM End-System Addresses

NetPrefix ::= OCTET STRING(SIZE(8 | 13))
-- TEXTUAL-CONVENTION
--  Status
--    mandatory
--  Descr
--    ATM End-System Addresses


END
