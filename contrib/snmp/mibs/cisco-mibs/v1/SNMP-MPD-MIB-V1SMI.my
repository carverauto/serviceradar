-- MIB file created 28-Jun-2001 22:14:18, by
--   SMICng version 2.2.11-beta(PRO)(Solaris), January 20, 2001. Enterprise key cisco.com

SNMP-MPD-MIB DEFINITIONS ::= BEGIN

-- From file: "SNMP-MPD-MIB.my"
-- Compile options "4 7 F H N W 03 06 0B 0G 0N 0T"

IMPORTS
    snmpModules
            FROM SNMPv2-SMI-v1
    Counter
            FROM RFC1155-SMI
    OBJECT-TYPE
            FROM RFC-1212;

snmpMPDMIB OBJECT IDENTIFIER ::= { snmpModules 11 }
-- MODULE-IDENTITY
--  LastUpdated
--    9905041636Z
--  OrgName
--    SNMPv3 Working Group
--  ContactInfo
--    WG-EMail:   snmpv3@lists.tislabs.com
--     Subscribe:  majordomo@lists.tislabs.com
--                 In message body:  subscribe snmpv3
--    
--     Chair:      Russ Mundy
--                 TIS Labs at Network Associates
--     postal:     3060 Washington Road
--                 Glenwood, MD 21738
--                 USA
--     EMail:      mundy@tislabs.com
--     phone:      +1 301-854-6889
--    
--    
--    
--    
--    
--    
--     Co-editor:  Jeffrey Case
--                 SNMP Research, Inc.
--     postal:     3001 Kimberlin Heights Road
--                 Knoxville, TN 37920-9716
--                 USA
--     EMail:      case@snmp.com
--     phone:      +1 423-573-1434
--    
--     Co-editor   Dave Harrington
--                 Cabletron Systems, Inc.
--     postal:     Post Office Box 5005
--                 MailStop: Durham
--                 35 Industrial Way
--                 Rochester, NH 03867-5005
--                 USA
--     EMail:      dbh@ctron.com
--     phone:      +1 603-337-7357
--    
--     Co-editor:  Randy Presuhn
--                 BMC Software, Inc.
--     postal:     965 Stewart Drive
--                 Sunnyvale, CA 94086
--                 USA
--     EMail:      randy_presuhn@bmc.com
--     phone:      +1 408-616-3100
--    
--     Co-editor:  Bert Wijnen
--                 IBM T. J. Watson Research
--     postal:     Schagen 33
--                 3461 GL Linschoten
--                 Netherlands
--     EMail:      wijnen@vnet.ibm.com
--     phone:      +31 348-432-794
--    
--  Descr
--    The MIB for Message Processing and Dispatching
--  RevDate
--    9905041636Z
--  RevDescr
--    Updated addresses, published as RFC 2572.
--  RevDate
--    9709300000Z
--  RevDescr
--    Original version, published as RFC 2272.

snmpMPDAdmin    OBJECT IDENTIFIER ::= { snmpMPDMIB 1 }
snmpMPDMIBObjects OBJECT IDENTIFIER ::= { snmpMPDMIB 2 }
snmpMPDMIBConformance OBJECT IDENTIFIER ::= { snmpMPDMIB 3 }
snmpMPDStats    OBJECT IDENTIFIER ::= { snmpMPDMIBObjects 1 }
snmpMPDMIBCompliances OBJECT IDENTIFIER ::= { snmpMPDMIBConformance 1 }
snmpMPDMIBGroups OBJECT IDENTIFIER ::= { snmpMPDMIBConformance 2 }

snmpUnknownSecurityModels OBJECT-TYPE
    SYNTAX Counter
    ACCESS read-only
    STATUS mandatory
    DESCRIPTION
        "The total number of packets received by the SNMP
         engine which were dropped because they referenced a
         securityModel that was not known to or supported by
         the SNMP engine."
    ::= { snmpMPDStats 1 }

snmpInvalidMsgs OBJECT-TYPE
    SYNTAX Counter
    ACCESS read-only
    STATUS mandatory
    DESCRIPTION
        "The total number of packets received by the SNMP
         engine which were dropped because there were invalid
         or inconsistent components in the SNMP message."
    ::= { snmpMPDStats 2 }

snmpUnknownPDUHandlers OBJECT-TYPE
    SYNTAX Counter
    ACCESS read-only
    STATUS mandatory
    DESCRIPTION
        "The total number of packets received by the SNMP
         engine which were dropped because the PDU contained
         in the packet could not be passed to an application
         responsible for handling the pduType, e.g. no SNMP
         application had registered for the proper
         combination of the contextEngineID and the pduType."
    ::= { snmpMPDStats 3 }

snmpMPDGroup OBJECT IDENTIFIER ::= { snmpMPDMIBGroups 1 }
-- OBJECT-GROUP
--  Status
--    mandatory
--  Descr
--    A collection of objects providing for remote
--     monitoring of the SNMP Message Processing and
--     Dispatching process.
--  objects
--    snmpUnknownSecurityModels, snmpInvalidMsgs, 
--    snmpUnknownPDUHandlers

snmpMPDCompliance OBJECT IDENTIFIER ::= { snmpMPDMIBCompliances 1 }
-- MODULE-COMPLIANCE
--  Status
--    mandatory
--  Descr
--    The compliance statement for SNMP entities which
--    
--    
--    
--    
--    
--     implement the SNMP-MPD-MIB.
--  Module
--    >>current<<
--   MandGroup
--    snmpMPDGroup


END
