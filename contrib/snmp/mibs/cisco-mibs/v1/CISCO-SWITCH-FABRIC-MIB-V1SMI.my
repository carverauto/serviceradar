-- MIB file created 07-Aug-2014 11:55:32, by
--   SMICng version 2.2.11-beta(PRO)(Solaris), January 20, 2001. Enterprise key cisco.com

CISCO-SWITCH-FABRIC-MIB DEFINITIONS ::= BEGIN

-- From file: "CISCO-SWITCH-FABRIC-MIB.my"
-- Compile options "4 7 F H N W 03 06 0B 0G 0N 0T"

IMPORTS
    TruthValue, DateAndTime
            FROM SNMPv2-TC-v1
    SnmpAdminString
            FROM SNMP-FRAMEWORK-MIB
    entPhysicalIndex, PhysicalIndex
            FROM ENTITY-MIB
    ciscoMgmt
            FROM CISCO-SMI
    Gauge
            FROM RFC1155-SMI
    OBJECT-TYPE
            FROM RFC-1212
    TRAP-TYPE
            FROM RFC-1215;

ciscoSwitchFabricMIB OBJECT IDENTIFIER ::= { ciscoMgmt 803 }
-- MODULE-IDENTITY
--  LastUpdated
--    201407300000Z
--  OrgName
--    Cisco Systems, Inc.
--  ContactInfo
--    Cisco Systems
--    Customer Service
--    Postal: 170 W Tasman Drive
--    San Jose, CA  95134
--    USA
--    Tel: +1 800 553-NETS
--    
--    E-mail: cs-lan-switch-snmp@cisco.com
--  Descr
--    This MIB module defined managed objects that
--    facilitates the management of switching fabric
--    information in a Cisco switch.
--  RevDate
--    201407300000Z
--  RevDescr
--    Added the following OBJECT-GROUP
--     - csfFabricCrcErrorNotifsControlGroup 
--     - csfFabricCrcErrorNotifsInfoGroup 
--     - csfFabricCrcErrorNotifsGroup.
--     Added new compliance csfSwitchFabricMIBCompliance1.
--  RevDate
--    201206120000Z
--  RevDescr
--    Initial version of this MIB module.

ciscoSwitchFabricMIBNotifs OBJECT IDENTIFIER ::= { ciscoSwitchFabricMIB 0 }
ciscoSwitchFabricMIBObjects OBJECT IDENTIFIER ::= { ciscoSwitchFabricMIB 1 }
ciscoSwitchFabricMIBConform OBJECT IDENTIFIER ::= { ciscoSwitchFabricMIB 2 }
csfFabricStatistics OBJECT IDENTIFIER ::= { ciscoSwitchFabricMIBObjects 1 }
csfNotifsControl OBJECT IDENTIFIER ::= { ciscoSwitchFabricMIBObjects 2 }
csfNotifsOnlyInfo OBJECT IDENTIFIER ::= { ciscoSwitchFabricMIBObjects 3 }
csfSwitchFabricMIBCompliances OBJECT IDENTIFIER ::= { ciscoSwitchFabricMIBConform 1 }
csfSwitchFabricMIBGroups OBJECT IDENTIFIER ::= { ciscoSwitchFabricMIBConform 2 }

CsfFabricLinkType ::= INTEGER {
        other(1),
        qEngineFacingLcXbarLink(2),
        fabricXbarLink(3),
        fabricFacingLcXbarLink(4),
        lcXbarInterLink(5),
        fabricXbarInterLink(6),
        centralXbarLink(7)
        }
-- TEXTUAL-CONVENTION
--  Status
--    mandatory
--  Descr
--    The type of fabric link.
--    
--    other                       - none of the following
--    qEngineFacingLcXbarLink     - queue engine facing linecard 
--                                  crossbar link 
--    fabricXbarLink              - fabric module crossbar link
--    fabricFacingLcXbarLink      - fabric module facing linecard 
--                                  crossbar link
--    lcXbarInterLink             - linecard crossbar interlink
--    fabricXbarInterLink         - fabric module crossbar interlink
--    centralXbarLink             - central fabric link

CsfPercentOrMinusOne ::= INTEGER(-1|0..100)
-- TEXTUAL-CONVENTION
--  DspHint
--    d
--  Status
--    mandatory
--  Descr
--    An integer that is in the range of a percent value.
--    
--    A value of -1 means that the percentage is not available.

csfFabricUtilTable OBJECT-TYPE
    SYNTAX SEQUENCE OF CsfFabricUtilEntry
    ACCESS not-accessible
    STATUS mandatory
    DESCRIPTION
        "A table containing fabric utilization information."
    ::= { csfFabricStatistics 1 }

csfFabricUtilEntry OBJECT-TYPE
    SYNTAX CsfFabricUtilEntry
    ACCESS not-accessible
    STATUS mandatory
    DESCRIPTION
        "A conceptual row containing the fabric utilization
        information for a particular type of traffic utilization
        of a fabric entity.
        
        An entry of this table is created if a traffic utilization
        on a fabric entity is detected by the managed system.
        
        An entry of this table is deleted when the removal of fabric
        entity."
    INDEX { entPhysicalIndex, csfFabricUtilLinkType, csfFabricUtilIndex }
    ::= { csfFabricUtilTable 1 }

CsfFabricUtilEntry ::= SEQUENCE {
    csfFabricUtilLinkType CsfFabricLinkType,
    csfFabricUtilIndex Gauge,
    csfFabricUtilDescr SnmpAdminString,
    csfFabricUtilBandwidth Gauge,
    csfFabricUtilIn CsfPercentOrMinusOne,
    csfFabricUtilInPeak CsfPercentOrMinusOne,
    csfFabricUtilInPeakTime DateAndTime,
    csfFabricUtilOut CsfPercentOrMinusOne,
    csfFabricUtilOutPeak CsfPercentOrMinusOne,
    csfFabricUtilOutPeakTime DateAndTime
    }

csfFabricUtilLinkType OBJECT-TYPE
    SYNTAX CsfFabricLinkType
--    Rsyntax INTEGER {
--        other(1),
--        qEngineFacingLcXbarLink(2),
--        fabricXbarLink(3),
--        fabricFacingLcXbarLink(4),
--        lcXbarInterLink(5),
--        fabricXbarInterLink(6),
--        centralXbarLink(7)
--        }
    ACCESS not-accessible
    STATUS mandatory
    DESCRIPTION
        "This object indicates the type of fabric link on which 
        fabric traffic utilization is monitored."
    ::= { csfFabricUtilEntry 1 }

csfFabricUtilIndex OBJECT-TYPE
    SYNTAX Gauge
    ACCESS not-accessible
    STATUS mandatory
    DESCRIPTION
        "This object indicates an arbitrary integer value which
        uniquely identifies the type of traffic utilization."
    ::= { csfFabricUtilEntry 2 }

csfFabricUtilDescr OBJECT-TYPE
    SYNTAX SnmpAdminString
--    Rsyntax OCTET STRING(SIZE(0..255))
    ACCESS read-only
    STATUS mandatory
    DESCRIPTION
        "This object indicates the human-readable description of
        the type of fabric traffic utilization."
    ::= { csfFabricUtilEntry 3 }

csfFabricUtilBandwidth OBJECT-TYPE
    SYNTAX Gauge
--  Units
--    gigabits per second
    ACCESS read-only
    STATUS mandatory
    DESCRIPTION
        "This object indicates the bandwidth of the fabric link."
    ::= { csfFabricUtilEntry 4 }

csfFabricUtilIn OBJECT-TYPE
    SYNTAX CsfPercentOrMinusOne
--    Rsyntax INTEGER(-1|0..100)
    ACCESS read-only
    STATUS mandatory
    DESCRIPTION
        "This object indicates the utilization on the
        fabric link input."
    ::= { csfFabricUtilEntry 5 }

csfFabricUtilInPeak OBJECT-TYPE
    SYNTAX CsfPercentOrMinusOne
--    Rsyntax INTEGER(-1|0..100)
    ACCESS read-only
    STATUS mandatory
    DESCRIPTION
        "This object indicates the peak utilization on the
        fabric link input."
    ::= { csfFabricUtilEntry 6 }

csfFabricUtilInPeakTime OBJECT-TYPE
    SYNTAX DateAndTime
--    Rsyntax OCTET STRING(SIZE(8|11))
    ACCESS read-only
    STATUS mandatory
    DESCRIPTION
        "This object indicates the time of the most recent change in
        the corresponding instance value of csfFabricUtilInPeak.
        
        This object contains value 0x0000010100000000 when the
        corresponding instance value of csfFabricUtilInPeak is
        '0 or '-1'."
    ::= { csfFabricUtilEntry 7 }

csfFabricUtilOut OBJECT-TYPE
    SYNTAX CsfPercentOrMinusOne
--    Rsyntax INTEGER(-1|0..100)
    ACCESS read-only
    STATUS mandatory
    DESCRIPTION
        "This object indicates the utilization on the
        fabric link output."
    ::= { csfFabricUtilEntry 8 }

csfFabricUtilOutPeak OBJECT-TYPE
    SYNTAX CsfPercentOrMinusOne
--    Rsyntax INTEGER(-1|0..100)
    ACCESS read-only
    STATUS mandatory
    DESCRIPTION
        "This object indicates the peak utilization on the
        fabric link output."
    ::= { csfFabricUtilEntry 9 }

csfFabricUtilOutPeakTime OBJECT-TYPE
    SYNTAX DateAndTime
--    Rsyntax OCTET STRING(SIZE(8|11))
    ACCESS read-only
    STATUS mandatory
    DESCRIPTION
        "This object indicates the time of the most recent change in
        the corresponding instance value of csfFabricUtilOutPeak.
        
        This object contains value 0x0000010100000000 when the
        corresponding instance value of csfFabricUtilInPeak is
        '0 or '-1'."
    ::= { csfFabricUtilEntry 10 }

csfFabricCrcErrorNotifEnable OBJECT-TYPE
    SYNTAX TruthValue
--    Rsyntax INTEGER {
--        true(1),
--        false(2)
--        }
    ACCESS read-write
    STATUS mandatory
    DESCRIPTION
        "This object specifies whether the system generates the
        cfsFabricCrcErrorNotif.
        
        A value of 'false' will prevent cfsFabricCrcErrorNotif
        notifications from being generated by this system."
    ::= { csfNotifsControl 1 }

csfFabricCrcErrorEntPhysicalIndex OBJECT-TYPE
    SYNTAX PhysicalIndex
--    Rsyntax INTEGER(1..2147483647)
    ACCESS not-accessible
    STATUS mandatory
    DESCRIPTION
        "This object indicates the entPhysicalIndex of the fabric
        entity on which fabric CRC error happens."
    ::= { csfNotifsOnlyInfo 1 }

csfFabricCrcErrorDescr OBJECT-TYPE
    SYNTAX SnmpAdminString
--    Rsyntax OCTET STRING(SIZE(0..255))
    ACCESS not-accessible
    STATUS mandatory
    DESCRIPTION
        "This object indicates the fabric CRC error description.
        A zero-length string indicates that the error description
        is not available."
    ::= { csfNotifsOnlyInfo 2 }

csfFabricCrcErrorNotif TRAP-TYPE
-- Reverse mappable trap
    ENTERPRISE ciscoSwitchFabricMIB
    VARIABLES {
        csfFabricCrcErrorEntPhysicalIndex, csfFabricCrcErrorDescr }
--  Status
--    mandatory
    DESCRIPTION
        "A cfsFabricCrcErrorNotif is generated when
        fabric CRC errors are detected by the managed system."
    ::= 1

csfFabricUtilGroup OBJECT IDENTIFIER ::= { csfSwitchFabricMIBGroups 1 }
-- OBJECT-GROUP
--  Status
--    mandatory
--  Descr
--    A collection of objects providing the information
--    about utilization on the fabric link.
--  objects
--    csfFabricUtilDescr, csfFabricUtilBandwidth, csfFabricUtilIn, 
--    csfFabricUtilInPeak, csfFabricUtilInPeakTime, 
--    csfFabricUtilOut, csfFabricUtilOutPeak, 
--    csfFabricUtilOutPeakTime

csfFabricCrcErrorNotifsControlGroup OBJECT IDENTIFIER ::= { csfSwitchFabricMIBGroups 2 }
-- OBJECT-GROUP
--  Status
--    mandatory
--  Descr
--    A collection of objects providing notification 
--    control for csfFabricCrcErrorNotif.
--  objects
--    csfFabricCrcErrorNotifEnable

csfFabricCrcErrorNotifsInfoGroup OBJECT IDENTIFIER ::= { csfSwitchFabricMIBGroups 3 }
-- OBJECT-GROUP
--  Status
--    mandatory
--  Descr
--    A collection of object(s) providing the variable binding  
--    for csfFabricCrcErrorNotif.
--  objects
--    csfFabricCrcErrorEntPhysicalIndex, csfFabricCrcErrorDescr

csfFabricCrcErrorNotifsGroup OBJECT IDENTIFIER ::= { csfSwitchFabricMIBGroups 4 }
-- NOTIFICATION-GROUP
--  Status
--    mandatory
--  Descr
--    A collection of Fabric CRC Error notifications for 
--    CISCO-SWITCH-FABRIC-MIB.
--  notifications
--    csfFabricCrcErrorNotif

csfSwitchFabricMIBCompliance OBJECT IDENTIFIER ::= { csfSwitchFabricMIBCompliances 1 }
-- MODULE-COMPLIANCE
--  Status
--    deprecated
--  Descr
--    The compliance statement for
--    the CISCO-SWITCH-FABRIC-MIB.
--  Module
--    >>current<<
--   MandGroup
--    csfFabricUtilGroup

csfSwitchFabricMIBCompliance1 OBJECT IDENTIFIER ::= { csfSwitchFabricMIBCompliances 2 }
-- MODULE-COMPLIANCE
--  Status
--    mandatory
--  Descr
--    The compliance statement for
--    the CISCO-SWITCH-FABRIC-MIB.
--  Module
--    >>current<<
--   MandGroup
--    csfFabricUtilGroup
--   OptGroup
--    csfFabricCrcErrorNotifsControlGroup
--   OptGroup
--    csfFabricCrcErrorNotifsInfoGroup
--   OptGroup
--    csfFabricCrcErrorNotifsGroup
--   ObjVar
--    csfFabricCrcErrorNotifEnable


END
