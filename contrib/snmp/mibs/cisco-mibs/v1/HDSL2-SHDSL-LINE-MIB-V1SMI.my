-- MIB file created 21-Dec-2011 05:00:22, by
--   SMICng version 2.2.11-beta(PRO)(Solaris), January 20, 2001. Enterprise key cisco.com

HDSL2-SHDSL-LINE-MIB DEFINITIONS ::= BEGIN

-- From file: "HDSL2-SHDSL-LINE-MIB.my"
-- Compile options "4 7 F H N W 03 06 0B 0G 0N 0T"

IMPORTS
    transmission
            FROM SNMPv2-SMI-v1
    RowStatus
            FROM SNMPv2-TC-v1
    ifIndex
            FROM IF-MIB
    PerfCurrentCount, PerfIntervalCount
            FROM PerfHist-TC-MIB
    SnmpAdminString
            FROM SNMP-FRAMEWORK-MIB
    Counter, Gauge
            FROM RFC1155-SMI
    OBJECT-TYPE
            FROM RFC-1212
    TRAP-TYPE
            FROM RFC-1215;

hdsl2ShdslMIB OBJECT IDENTIFIER ::= { transmission 48 }
-- MODULE-IDENTITY
--  LastUpdated
--    201112210000Z
--  OrgName
--    ADSLMIB Working Group
--  ContactInfo
--    WG-email:  adslmib@ietf.org
--    WG-URL:
--       http://www.ietf.org/html.charters/adslmib-charter.html
--    Info:       https://www1.ietf.org/mailman/listinfo/adslmib
--    Chair:      Mike Sneed
--                Sand Channel Systems
--    Postal:     1210-203 Westview Ln
--                Raleigh NC 27605  USA
--    Email:      sneedmike@hotmail.com
--    Phone:     +1 206 600 7022
--    
--    Co-Chair    Bob Ray
--                PESA Switching Systems, Inc.
--    
--    Postal      330-A Wynn Drive
--                Huntsville, AL 35805 USA
--    Phone       +1 256 726 9200 ext. 142
--    
--    Co-editor:  Clay Sikes
--                Zhone Technologies, Inc.
--    Postal:     8545 126th Ave. N.
--                Largo, FL 33772 USA
--    Email:      csikes@zhone.com
--    Phone:      +1 727 530 8257
--    
--    Co-editor:  Bob Ray
--                PESA Switching Systems, Inc.
--    Postal:     330-A Wynn Drive
--                Huntsville, AL 35805 USA
--    Email:      rray@pesa.com
--    Phone:      +1 256 726 9200 ext. 142
--    
--    Co-editor:  Rajesh Abbi
--                Alcatel USA
--    Postal:     2301 Sugar Bush Road
--                Raleigh, NC 27612-3339 USA
--    
--    Email:      Rajesh.Abbi@alcatel.com
--    Phone:      +1 919 850 6194
--  Descr
--    This MIB module defines a collection of objects for managing
--    HDSL2/SHDSL lines.  An agent may reside at either end of the
--    line; however, the MIB module is designed to require no
--    management communication between the modems beyond that
--    inherent in the low-level EOC line protocol as defined in
--    ANSI T1E1.4/2000-006 (for HDSL2 lines) or in ITU G.991.2
--    (for SHDSL lines).
--    
--    Copyright (C) The Internet Society (2005).  This version of
--    this MIB module is part of RFC 4319; see the RFC itself for
--    full legal notices.
--  RevDate
--    201112210000Z
--  RevDescr
--    addressed comment: defval missing, added region1 as def val as
--    per RFC
--  RevDate
--    200512070000Z
--  RevDescr
--    This version, published as RFC 4319.
--    The following changes have been made in this version:
--      1.  Added a 3rd and 4th wire pair.
--      2.  Modified all rates such that their rates are only
--          constrained by an unsigned 32-bit value and not by
--          what today's perceived technology limitations are.
--      3.  Clarified that the rates from RFC 3276 include
--          payload and any applicable framing and added
--          objects for payload-only rates.
--      4.  Added an object to indicate whether the
--          tip and ring are reversed on a wire pair.
--      5.  Added an object to display the activation state
--          of a wire pair.
--      6.  Added references as necessary for clarification.
--      7.  Added display hints to textual conventions as
--          necessary.
--      8.  Updated conformance statements as necessary.
--      9.  Some changes were due to IETF requirements and
--          RFC generation tools.
--  RevDate
--    200205090000Z
--  RevDescr
--    Initial version, published as RFC 3276.

hdsl2ShdslMibObjects OBJECT IDENTIFIER ::= { hdsl2ShdslMIB 1 }
hdsl2ShdslNotifications OBJECT IDENTIFIER ::= { hdsl2ShdslMIB 0 }
hdsl2ShdslConformance OBJECT IDENTIFIER ::= { hdsl2ShdslMIB 3 }
hdsl2ShdslGroups OBJECT IDENTIFIER ::= { hdsl2ShdslConformance 1 }
hdsl2ShdslCompliances OBJECT IDENTIFIER ::= { hdsl2ShdslConformance 2 }

Hdsl2ShdslPerfCurrDayCount ::= Gauge
-- TEXTUAL-CONVENTION
--  DspHint
--    d
--  Status
--    mandatory
--  Descr
--    A gauge associated with interface performance measurements in
--    a current 1-day (24 hour) measurement interval.
--    
--    The value of this gauge starts at zero at the beginning of an
--    interval and is increased when associated events occur, until
--    the end of the 1-day interval.  At that time, the value of the
--    gauge is stored in the previous 1-day history interval, as
--    defined in a companion object of type
--    Hdsl2Shdsl1DayIntevalCount, and the current interval gauge
--    is restarted at zero.
--    
--    In the case where the agent has no valid data available for
--    this interval, the corresponding object instance is not
--    available, and upon a retrieval request, a corresponding error
--    message shall be returned to indicate that this instance does
--    not exist.  Please note that zero is a valid value.

Hdsl2Shdsl1DayIntervalCount ::= Gauge
-- TEXTUAL-CONVENTION
--  DspHint
--    d
--  Status
--    mandatory
--  Descr
--    A counter associated with interface performance measurements
--    during the most previous 1-day (24 hour) measurement interval.
--    The value of this gauge is equal to the value of the current
--    day gauge, as defined in a companion object of type
--    Hdsl2ShdslPerfCurrDayCount, at the end of its most recent
--    interval.
--    
--    In the case where the agent has no valid data available for
--    this interval, the corresponding object instance is not
--    available, and upon a retrieval request, a corresponding error
--    message shall be returned to indicate that this instance does
--    not exist.

Hdsl2ShdslPerfTimeElapsed ::= Gauge(0..86399)
-- TEXTUAL-CONVENTION
--  DspHint
--    d
--  Status
--    mandatory
--  Descr
--    The number of seconds that have elapsed since the beginning of
--    the current measurement period.  If, for some reason, such as
--    an adjustment in the system's time-of-day clock or the addition
--    of a leap second, the current interval exceeds the maximum
--    value, the agent will return the maximum value.
--    
--    For 15-minute intervals, the range is limited to (0..899).
--    For 24-hour intervals, the range is limited to (0..86399).

Hdsl2ShdslPerfIntervalThreshold ::= Gauge(0..900)
-- TEXTUAL-CONVENTION
--  DspHint
--    d
--  Status
--    mandatory
--  Descr
--    This convention defines a range of values that may be set in
--    a fault threshold alarm control.  As the number of seconds in
--    a 15-minute interval numbers at most 900, objects of this type
--    may have a range of 0...900, where the value of 0 disables the
--    alarm.

Hdsl2ShdslUnitId ::= INTEGER {
        xtuC(1),
        xtuR(2),
        xru1(3),
        xru2(4),
        xru3(5),
        xru4(6),
        xru5(7),
        xru6(8),
        xru7(9),
        xru8(10)
        }
-- TEXTUAL-CONVENTION
--  Status
--    mandatory
--  Descr
--    This is the unique identification for all units in an
--    HDSL2/SHDSL span.  It is based on the EOC unit addressing
--    scheme with reference to the xtuC.

Hdsl2ShdslUnitSide ::= INTEGER {
        networkSide(1),
        customerSide(2)
        }
-- TEXTUAL-CONVENTION
--  Status
--    mandatory
--  Descr
--    This is the referenced side of an HDSL2/SHDSL unit - Network
--    or Customer side.  The side facing the Network is the Network
--    side, while the side facing the Customer is the Customer side.

Hdsl2ShdslWirePair ::= INTEGER {
        wirePair1(1),
        wirePair2(2),
        wirePair3(3),
        wirePair4(4)
        }
-- TEXTUAL-CONVENTION
--  Status
--    mandatory
--  Descr
--    This is the referenced pair of wires in an HDSL2/SHDSL segment.
--    HDSL2 only supports a single pair (wirePair1 or two wire),
--    SHDSL lines support an optional second pair (wirePair2 or four
--    wire), and G.shdsl.bis support an optional third pair
--    (wirePair3 or six wire) and an optional fourth pair
--    (wirePair4 or eight wire).

Hdsl2ShdslTransmissionModeType ::= OCTET STRING(SIZE(1..2))
        -- BITS are:
        --   region1(0)
        --   region2(1)
-- TEXTUAL-CONVENTION
--  Status
--    mandatory
--  Descr
--    Contains the regional setting of the HDSL2/SHDSL span,
--    represented as a bit-map of possible settings.  The various
--    bit positions are as follows:
--    Bit   Meaning      Description
--    1     region 1     Indicates ITU-T G.991.2 Annex A.
--    2     region 2     Indicates ITU-T G.991.2 Annex B.

Hdsl2ShdslClockReferenceType ::= INTEGER {
        localClk(1),
        networkClk(2),
        dataOrNetworkClk(3),
        dataClk(4)
        }
-- TEXTUAL-CONVENTION
--  Status
--    mandatory
--  Descr
--    The various STU-C symbol clock references for the
--    HDSL2/SHDSL span, represented as an enumeration.

hdsl2ShdslSpanConfTable OBJECT-TYPE
    SYNTAX SEQUENCE OF Hdsl2ShdslSpanConfEntry
    ACCESS not-accessible
    STATUS mandatory
    DESCRIPTION
        "This table supports overall configuration of HDSL2/SHDSL
        spans.  Entries in this table MUST be maintained in a
        persistent manner."
    ::= { hdsl2ShdslMibObjects 1 }

hdsl2ShdslSpanConfEntry OBJECT-TYPE
    SYNTAX Hdsl2ShdslSpanConfEntry
    ACCESS not-accessible
    STATUS mandatory
    DESCRIPTION
        "An entry in the hdsl2ShdslSpanConfTable.  Each entry
        represents the complete span in a single HDSL2/SHDSL line.
        It is indexed by the ifIndex of the associated HDSL2/SHDSL
        line."
    INDEX { ifIndex }
    ::= { hdsl2ShdslSpanConfTable 1 }

Hdsl2ShdslSpanConfEntry ::= SEQUENCE {
    hdsl2ShdslSpanConfNumRepeaters Gauge,
    hdsl2ShdslSpanConfProfile SnmpAdminString,
    hdsl2ShdslSpanConfAlarmProfile SnmpAdminString
    }

hdsl2ShdslSpanConfNumRepeaters OBJECT-TYPE
    SYNTAX Gauge(0..8)
--  Units
--    repeaters
    ACCESS read-write
    STATUS mandatory
    DESCRIPTION
        "This object provisions the number of repeaters/regenerators
        in this HDSL2/SHDSL span."
    ::= { hdsl2ShdslSpanConfEntry 1 }

hdsl2ShdslSpanConfProfile OBJECT-TYPE
    SYNTAX SnmpAdminString(SIZE(1..32))
--    Rsyntax OCTET STRING(SIZE(1..32))
    ACCESS read-write
    STATUS mandatory
    DESCRIPTION
        "This object is a pointer to a span configuration profile in
        the hdsl2ShdslSpanConfProfileTable, which applies to this
        span.  The value of this object is the index of the referenced
        profile in the hdsl2ShdslSpanConfProfileTable.  Note that span
        configuration profiles are only applicable to SHDSL lines.
        
        HDSL2 lines MUST reference the default profile, 'DEFVAL'.
        By default, this object will have the value 'DEFVAL'
        (the index of the default profile).
        
        Any attempt to set this object to a value that is not the value
        of the index for an active entry in the profile table,
        hdsl2ShdslSpanConfProfileTable, MUST be rejected."
    ::= { hdsl2ShdslSpanConfEntry 2 }

hdsl2ShdslSpanConfAlarmProfile OBJECT-TYPE
    SYNTAX SnmpAdminString(SIZE(1..32))
--    Rsyntax OCTET STRING(SIZE(1..32))
    ACCESS read-write
    STATUS mandatory
    DESCRIPTION
        "This object is a pointer to an alarm configuration profile in
        the hdsl2ShdslEndpointAlarmConfProfileTable.  The value of
        this object is the index of the referenced profile in the
        hdsl2ShdslEndpointAlarmConfProfileTable.  The alarm
        threshold configuration in the referenced profile will be
        used by default for all segment endpoints in this span.
        Individual endpoints may override this profile by explicitly
        specifying some other profile in the
        hdsl2ShdslEndpointConfTable.  By default, this object will
        have the value 'DEFVAL' (the index of the default
        profile).
        
        Any attempt to set this object to a value that is not the value
        of the index for an active entry in the profile table,
        hdsl2ShdslEndpointAlarmConfProfileTable, MUST be rejected."
    ::= { hdsl2ShdslSpanConfEntry 3 }

hdsl2ShdslSpanStatusTable OBJECT-TYPE
    SYNTAX SEQUENCE OF Hdsl2ShdslSpanStatusEntry
    ACCESS not-accessible
    STATUS mandatory
    DESCRIPTION
        "This table provides overall status information of
        HDSL2/SHDSL spans.  This table contains live data from
        equipment.  As such, it is NOT persistent."
    ::= { hdsl2ShdslMibObjects 2 }

hdsl2ShdslSpanStatusEntry OBJECT-TYPE
    SYNTAX Hdsl2ShdslSpanStatusEntry
    ACCESS not-accessible
    STATUS mandatory
    DESCRIPTION
        "An entry in the hdsl2ShdslSpanStatusTable.  Each entry
        represents the complete span in a single HDSL2/SHDSL line.
        It is indexed by the ifIndex of the associated HDSL2/SHDSL
        line."
    INDEX { ifIndex }
    ::= { hdsl2ShdslSpanStatusTable 1 }

Hdsl2ShdslSpanStatusEntry ::= SEQUENCE {
    hdsl2ShdslStatusNumAvailRepeaters Gauge,
    hdsl2ShdslStatusMaxAttainableLineRate Gauge,
    hdsl2ShdslStatusActualLineRate Gauge,
    hdsl2ShdslStatusTransmissionModeCurrent Hdsl2ShdslTransmissionModeType,
    hdsl2ShdslStatusMaxAttainablePayloadRate Gauge,
    hdsl2ShdslStatusActualPayloadRate Gauge
    }

hdsl2ShdslStatusNumAvailRepeaters OBJECT-TYPE
    SYNTAX Gauge(0..8)
    ACCESS read-only
    STATUS mandatory
    DESCRIPTION
        "Contains the actual number of repeaters/regenerators
        discovered in this HDSL2/SHDSL span."
    ::= { hdsl2ShdslSpanStatusEntry 1 }

hdsl2ShdslStatusMaxAttainableLineRate OBJECT-TYPE
    SYNTAX Gauge(0..4294967295)
--  Units
--    bps
    ACCESS read-only
    STATUS mandatory
    DESCRIPTION
        "Contains the maximum attainable line rate in this HDSL2/SHDSL
        span.  This object provides the maximum rate the line is
        capable of achieving.  This is based upon measurements made
        during line probing.  This rate includes payload (user data)
        and any applicable framing overhead."
    ::= { hdsl2ShdslSpanStatusEntry 2 }

hdsl2ShdslStatusActualLineRate OBJECT-TYPE
    SYNTAX Gauge(0..4294967295)
--  Units
--    bps
    ACCESS read-only
    STATUS mandatory
    DESCRIPTION
        "Contains the actual line rate in this HDSL2/SHDSL span.  This
        SHOULD equal ifSpeed.  This rate includes payload (user data)
        and any applicable framing overhead"
    ::= { hdsl2ShdslSpanStatusEntry 3 }

hdsl2ShdslStatusTransmissionModeCurrent OBJECT-TYPE
    SYNTAX Hdsl2ShdslTransmissionModeType
--    Rsyntax OCTET STRING(SIZE(1..2))
--         BITS are:
--           region1(0)
--           region2(1)
    ACCESS read-only
    STATUS mandatory
    DESCRIPTION
        "Contains the current Power Spectral Density (PSD) regional
        setting of the HDSL2/SHDSL span."
    ::= { hdsl2ShdslSpanStatusEntry 4 }

hdsl2ShdslStatusMaxAttainablePayloadRate OBJECT-TYPE
    SYNTAX Gauge(0..4294967295)
--  Units
--    bps
    ACCESS read-only
    STATUS mandatory
    DESCRIPTION
        "Contains the maximum attainable payload (user data)
        line rate in this HDSL2/SHDSL span.  This object provides
        the maximum rate the line is capable of achieving.  This
        is based upon measurements made during line probing.  Any
        framing overhead is not included."
    ::= { hdsl2ShdslSpanStatusEntry 5 }

hdsl2ShdslStatusActualPayloadRate OBJECT-TYPE
    SYNTAX Gauge(0..4294967295)
--  Units
--    bps
    ACCESS read-only
    STATUS mandatory
    DESCRIPTION
        "Contains the actual line rate in this HDSL2/SHDSL span.  Any
        framing overhead is not included."
    ::= { hdsl2ShdslSpanStatusEntry 6 }

hdsl2ShdslInventoryTable OBJECT-TYPE
    SYNTAX SEQUENCE OF Hdsl2ShdslInventoryEntry
    ACCESS not-accessible
    STATUS mandatory
    DESCRIPTION
        "This table supports retrieval of unit inventory information
        available via the EOC from units in an HDSL2/SHDSL line.
        
        Entries in this table are dynamically created during the
        line discovery process.  The life cycle for these entries
        is as follows:
        
           - xtu discovers a device, either a far-end xtu or an xru
           - an inventory table entry is created for the device
           - the line goes down for whatever reason
           - inventory table entries for unreachable devices are
             destroyed
        
        As these entries are created/destroyed dynamically, they
        are NOT persistent."
    ::= { hdsl2ShdslMibObjects 3 }

hdsl2ShdslInventoryEntry OBJECT-TYPE
    SYNTAX Hdsl2ShdslInventoryEntry
    ACCESS not-accessible
    STATUS mandatory
    DESCRIPTION
        "An entry in the hdsl2ShdslInventoryTable.  Each entry
        represents inventory information for a single unit in an
        HDSL2/SHDSL line.  It is indexed by the ifIndex of the
        HDSL2/SHDSL line and the Hdsl2ShdslUnitId of the
        associated unit."
    INDEX { ifIndex, hdsl2ShdslInvIndex }
    ::= { hdsl2ShdslInventoryTable 1 }

Hdsl2ShdslInventoryEntry ::= SEQUENCE {
    hdsl2ShdslInvIndex Hdsl2ShdslUnitId,
    hdsl2ShdslInvVendorID OCTET STRING,
    hdsl2ShdslInvVendorModelNumber OCTET STRING,
    hdsl2ShdslInvVendorSerialNumber OCTET STRING,
    hdsl2ShdslInvVendorEOCSoftwareVersion INTEGER,
    hdsl2ShdslInvStandardVersion INTEGER,
    hdsl2ShdslInvVendorListNumber OCTET STRING,
    hdsl2ShdslInvVendorIssueNumber OCTET STRING,
    hdsl2ShdslInvVendorSoftwareVersion OCTET STRING,
    hdsl2ShdslInvEquipmentCode OCTET STRING,
    hdsl2ShdslInvVendorOther OCTET STRING,
    hdsl2ShdslInvTransmissionModeCapability Hdsl2ShdslTransmissionModeType
    }

hdsl2ShdslInvIndex OBJECT-TYPE
    SYNTAX Hdsl2ShdslUnitId
--    Rsyntax INTEGER {
--        xtuC(1),
--        xtuR(2),
--        xru1(3),
--        xru2(4),
--        xru3(5),
--        xru4(6),
--        xru5(7),
--        xru6(8),
--        xru7(9),
--        xru8(10)
--        }
    ACCESS not-accessible
    STATUS mandatory
    DESCRIPTION
        "Each entry in this table corresponds to a physical element
        in an HDSL2/SHDSL span.  It is based on the EOC unit addressing
        scheme with reference to the xtuC."
    ::= { hdsl2ShdslInventoryEntry 1 }

hdsl2ShdslInvVendorID OBJECT-TYPE
    SYNTAX OCTET STRING(SIZE(8))
    ACCESS read-only
    STATUS mandatory
    DESCRIPTION
        "Vendor ID as reported in an Inventory Response message."
    REFERENCE
        "G.991.2, Section 9.5.5.7.4, Inventory response - Message ID
         130, Octets 25-32."
    ::= { hdsl2ShdslInventoryEntry 2 }

hdsl2ShdslInvVendorModelNumber OBJECT-TYPE
    SYNTAX OCTET STRING(SIZE(12))
    ACCESS read-only
    STATUS mandatory
    DESCRIPTION
        "Vendor model number as reported in an Inventory Response
        message."
    REFERENCE
        "G.991.2, Section 9.5.5.7.4, Inventory response - Message ID
         130, Octets 33-44."
    ::= { hdsl2ShdslInventoryEntry 3 }

hdsl2ShdslInvVendorSerialNumber OBJECT-TYPE
    SYNTAX OCTET STRING(SIZE(12))
    ACCESS read-only
    STATUS mandatory
    DESCRIPTION
        "Vendor serial number as reported in an Inventory Response
        message."
    REFERENCE
        "G.991.2, Section 9.5.5.7.4, Inventory response - Message ID
         130, Octets 45-56."
    ::= { hdsl2ShdslInventoryEntry 4 }

hdsl2ShdslInvVendorEOCSoftwareVersion OBJECT-TYPE
    SYNTAX INTEGER
    ACCESS read-only
    STATUS mandatory
    DESCRIPTION
        "Vendor EOC version as reported in a Discovery Response
        message."
    REFERENCE
        "G.991.2, Section 9.5.5.7.2, Discovery response - Message ID
         129, Octet 12."
    ::= { hdsl2ShdslInventoryEntry 5 }

hdsl2ShdslInvStandardVersion OBJECT-TYPE
    SYNTAX INTEGER
    ACCESS read-only
    STATUS mandatory
    DESCRIPTION
        "Version of the HDSL2/SHDSL standard implemented, as reported
        in an Inventory Response message."
    REFERENCE
        "G.991.2, Section 9.5.5.7.4, Inventory response - Message ID
         130, Octet 2."
    ::= { hdsl2ShdslInventoryEntry 6 }

hdsl2ShdslInvVendorListNumber OBJECT-TYPE
    SYNTAX OCTET STRING(SIZE(3))
    ACCESS read-only
    STATUS mandatory
    DESCRIPTION
        "Vendor list number as reported in an Inventory Response
        message."
    REFERENCE
        "G.991.2, Section 9.5.5.7.4, Inventory response - Message ID
         130, Octets 3-5."
    ::= { hdsl2ShdslInventoryEntry 7 }

hdsl2ShdslInvVendorIssueNumber OBJECT-TYPE
    SYNTAX OCTET STRING(SIZE(2))
    ACCESS read-only
    STATUS mandatory
    DESCRIPTION
        "Vendor issue number as reported in an Inventory Response
        message."
    REFERENCE
        "G.991.2, Section 9.5.5.7.4, Inventory response - Message ID
         130, Octets 6-7."
    ::= { hdsl2ShdslInventoryEntry 8 }

hdsl2ShdslInvVendorSoftwareVersion OBJECT-TYPE
    SYNTAX OCTET STRING(SIZE(6))
    ACCESS read-only
    STATUS mandatory
    DESCRIPTION
        "Vendor software version as reported in an Inventory Response
        message."
    REFERENCE
        "G.991.2, Section 9.5.5.7.4, Inventory response - Message ID
         130, Octets 8-13."
    ::= { hdsl2ShdslInventoryEntry 9 }

hdsl2ShdslInvEquipmentCode OBJECT-TYPE
    SYNTAX OCTET STRING(SIZE(10))
    ACCESS read-only
    STATUS mandatory
    DESCRIPTION
        "Equipment code conforming to ANSI T1.213, Coded Identification
        of Equipment Entities."
    REFERENCE
        "G.991.2, Section 9.5.5.7.4, Inventory response - Message ID
         130, Octets 14-23."
    ::= { hdsl2ShdslInventoryEntry 10 }

hdsl2ShdslInvVendorOther OBJECT-TYPE
    SYNTAX OCTET STRING(SIZE(12))
    ACCESS read-only
    STATUS mandatory
    DESCRIPTION
        "Other vendor information as reported in an Inventory Response
        message."
    REFERENCE
        "G.991.2, Section 9.5.5.7.4, Inventory response - Message ID
         130, Octets 57-68."
    ::= { hdsl2ShdslInventoryEntry 11 }

hdsl2ShdslInvTransmissionModeCapability OBJECT-TYPE
    SYNTAX Hdsl2ShdslTransmissionModeType
--    Rsyntax OCTET STRING(SIZE(1..2))
--         BITS are:
--           region1(0)
--           region2(1)
    ACCESS read-only
    STATUS mandatory
    DESCRIPTION
        "Contains the transmission mode capability of the SHDSL unit."
    ::= { hdsl2ShdslInventoryEntry 12 }

hdsl2ShdslEndpointConfTable OBJECT-TYPE
    SYNTAX SEQUENCE OF Hdsl2ShdslEndpointConfEntry
    ACCESS not-accessible
    STATUS mandatory
    DESCRIPTION
        "This table supports configuration parameters for segment
        endpoints in an HDSL2/SHDSL line.  As this table is indexed
        by ifIndex, it MUST be maintained in a persistent manner."
    ::= { hdsl2ShdslMibObjects 4 }

hdsl2ShdslEndpointConfEntry OBJECT-TYPE
    SYNTAX Hdsl2ShdslEndpointConfEntry
    ACCESS not-accessible
    STATUS mandatory
    DESCRIPTION
        "An entry in the hdsl2ShdslEndpointConfTable.  Each entry
        represents a single segment endpoint in an HDSL2/SHDSL line.
        It is indexed by the ifIndex of the HDSL2/SHDSL line, the
        UnitId of the associated unit, the side of the unit, and the
        wire pair of the associated modem."
    INDEX { ifIndex, hdsl2ShdslInvIndex, hdsl2ShdslEndpointSide, hdsl2ShdslEndpointWirePair }
    ::= { hdsl2ShdslEndpointConfTable 1 }

Hdsl2ShdslEndpointConfEntry ::= SEQUENCE {
    hdsl2ShdslEndpointSide Hdsl2ShdslUnitSide,
    hdsl2ShdslEndpointWirePair Hdsl2ShdslWirePair,
    hdsl2ShdslEndpointAlarmConfProfile SnmpAdminString
    }

hdsl2ShdslEndpointSide OBJECT-TYPE
    SYNTAX Hdsl2ShdslUnitSide
--    Rsyntax INTEGER {
--        networkSide(1),
--        customerSide(2)
--        }
    ACCESS not-accessible
    STATUS mandatory
    DESCRIPTION
        "The side of the unit associated with this segment endpoint --
        Network/Customer side -- as per the Hdsl2ShdslUnitSide textual
        convention."
    ::= { hdsl2ShdslEndpointConfEntry 1 }

hdsl2ShdslEndpointWirePair OBJECT-TYPE
    SYNTAX Hdsl2ShdslWirePair
--    Rsyntax INTEGER {
--        wirePair1(1),
--        wirePair2(2),
--        wirePair3(3),
--        wirePair4(4)
--        }
    ACCESS not-accessible
    STATUS mandatory
    DESCRIPTION
        "The wire pair of the modem associated with this segment
        endpoint as per the Hdsl2ShdslWirePair textual convention."
    ::= { hdsl2ShdslEndpointConfEntry 2 }

hdsl2ShdslEndpointAlarmConfProfile OBJECT-TYPE
    SYNTAX SnmpAdminString(SIZE(0..32))
--    Rsyntax OCTET STRING(SIZE(0..32))
    ACCESS read-write
    STATUS mandatory
    DESCRIPTION
        "This object configures the alarm threshold values to be used
        for this segment endpoint.  The values are obtained from the
        alarm configuration profile referenced by this object.  The
        value of this object is the index of the referenced profile in
        the hdsl2ShdslEndpointAlarmConfProfileTable, or NULL (a
        zero-length SnmpAdminString).  If the value is a zero-length
        SnmpAdminString, the endpoint uses the default Alarm
        Configuration Profile for the associated span as per the
        hdsl2ShdslSpanConfAlarmProfile object in the
        hdsl2ShdslSpanConfTable.  The default value of this object is
        a zero-length SnmpAdminString.
        
        Any attempt to set this object to a value that is not the value
        of the index for an active entry in the profile table,
        hdsl2ShdslEndpointAlarmConfProfileTable, MUST be rejected."
    ::= { hdsl2ShdslEndpointConfEntry 3 }

hdsl2ShdslEndpointCurrTable OBJECT-TYPE
    SYNTAX SEQUENCE OF Hdsl2ShdslEndpointCurrEntry
    ACCESS not-accessible
    STATUS mandatory
    DESCRIPTION
        "This table contains current status and performance information
        for segment endpoints in HDSL2/SHDSL lines.  As with other
        tables in this MIB module indexed by ifIndex, entries in this
        table MUST be maintained in a persistent manner."
    ::= { hdsl2ShdslMibObjects 5 }

hdsl2ShdslEndpointCurrEntry OBJECT-TYPE
    SYNTAX Hdsl2ShdslEndpointCurrEntry
    ACCESS not-accessible
    STATUS mandatory
    DESCRIPTION
        "An entry in the hdsl2ShdslEndpointCurrTable.  Each entry
        contains status and performance information relating to a
        single segment endpoint.  It is indexed by the ifIndex of the
        HDSL2/SHDSL line, the UnitId of the associated unit, the side
        of the unit, and the wire pair of the associated modem."
    INDEX { ifIndex, hdsl2ShdslInvIndex, hdsl2ShdslEndpointSide, hdsl2ShdslEndpointWirePair }
    ::= { hdsl2ShdslEndpointCurrTable 1 }

Hdsl2ShdslEndpointCurrEntry ::= SEQUENCE {
    hdsl2ShdslEndpointCurrAtn INTEGER,
    hdsl2ShdslEndpointCurrSnrMgn INTEGER,
    hdsl2ShdslEndpointCurrStatus OCTET STRING,
    hdsl2ShdslEndpointES Counter,
    hdsl2ShdslEndpointSES Counter,
    hdsl2ShdslEndpointCRCanomalies Counter,
    hdsl2ShdslEndpointLOSWS Counter,
    hdsl2ShdslEndpointUAS Counter,
    hdsl2ShdslEndpointCurr15MinTimeElapsed Hdsl2ShdslPerfTimeElapsed,
    hdsl2ShdslEndpointCurr15MinES PerfCurrentCount,
    hdsl2ShdslEndpointCurr15MinSES PerfCurrentCount,
    hdsl2ShdslEndpointCurr15MinCRCanomalies PerfCurrentCount,
    hdsl2ShdslEndpointCurr15MinLOSWS PerfCurrentCount,
    hdsl2ShdslEndpointCurr15MinUAS PerfCurrentCount,
    hdsl2ShdslEndpointCurr1DayTimeElapsed Hdsl2ShdslPerfTimeElapsed,
    hdsl2ShdslEndpointCurr1DayES Hdsl2ShdslPerfCurrDayCount,
    hdsl2ShdslEndpointCurr1DaySES Hdsl2ShdslPerfCurrDayCount,
    hdsl2ShdslEndpointCurr1DayCRCanomalies Hdsl2ShdslPerfCurrDayCount,
    hdsl2ShdslEndpointCurr1DayLOSWS Hdsl2ShdslPerfCurrDayCount,
    hdsl2ShdslEndpointCurr1DayUAS Hdsl2ShdslPerfCurrDayCount,
    hdsl2ShdslEndpointCurrTipRingReversal INTEGER,
    hdsl2ShdslEndpointCurrActivationState INTEGER
    }

hdsl2ShdslEndpointCurrAtn OBJECT-TYPE
    SYNTAX INTEGER(-127..128)
--  Units
--    dB
    ACCESS read-only
    STATUS mandatory
    DESCRIPTION
        "The current loop attenuation for this endpoint as reported in
        a Network or Customer Side Performance Status message."
    REFERENCE
        "HDSL2 Section 7.5.3.7; SHDSL Section 9.5.5.7"
    ::= { hdsl2ShdslEndpointCurrEntry 1 }

hdsl2ShdslEndpointCurrSnrMgn OBJECT-TYPE
    SYNTAX INTEGER(-127..128)
--  Units
--    dB
    ACCESS read-only
    STATUS mandatory
    DESCRIPTION
        "The current SNR margin for this endpoint as reported in a
        Status Response/SNR message."
    REFERENCE
        "HDSL2 Section 7.5.3.7; SHDSL Section 9.5.5.7"
    ::= { hdsl2ShdslEndpointCurrEntry 2 }

hdsl2ShdslEndpointCurrStatus OBJECT-TYPE
    SYNTAX OCTET STRING(SIZE(1..2))
        -- BITS are:
        --   noDefect(0)
        --   powerBackoff(1)
        --   deviceFault(2)
        --   dcContinuityFault(3)
        --   snrMarginAlarm(4)
        --   loopAttenuationAlarm(5)
        --   loswFailureAlarm(6)
        --   configInitFailure(7)
        --   protocolInitFailure(8)
        --   noNeighborPresent(9)
        --   loopbackActive(10)
    ACCESS read-only
    STATUS mandatory
    DESCRIPTION
        "Contains the current state of the endpoint.  This is a
        bit-map of possible conditions.  The various bit positions
        are as follows:
        
        noDefect               There are no defects on the line.
        
        powerBackoff           Indicates enhanced Power Backoff.
        
        deviceFault            Indicates that a vendor-dependent
                               diagnostic or self-test fault
                               has been detected.
        
        dcContinuityFault      Indicates vendor-dependent
                               conditions that interfere with
                               span powering such as short and
                               open circuits.
        
        snrMarginAlarm         Indicates that the SNR margin
                               has dropped below the alarm threshold.
        
        loopAttenuationAlarm   Indicates that the loop attenuation
                               exceeds the alarm threshold.
        
        loswFailureAlarm       Indicates a forward LOSW alarm.
        
        configInitFailure      Endpoint failure during initialization
                               due to paired endpoint not able to
                               support requested configuration.
        
        protocolInitFailure    Endpoint failure during initialization
                               due to incompatible protocol used by
                               the paired endpoint.
        
        noNeighborPresent      Endpoint failure during initialization
                               due to no activation sequence detected
                               from paired endpoint.
        
        loopbackActive         A loopback is currently active at this
                               segment endpoint.
        
        This is intended to supplement ifOperStatus.  Note that there
        is a 1:1 relationship between the status bits defined in this
        object and the notification thresholds defined elsewhere in
        this MIB module."
    REFERENCE
        "HDSL2 Section 7.5.3.7; SHDSL Section 9.5.5.7"
    ::= { hdsl2ShdslEndpointCurrEntry 3 }

hdsl2ShdslEndpointES OBJECT-TYPE
    SYNTAX Counter
--  Units
--    seconds
    ACCESS read-only
    STATUS mandatory
    DESCRIPTION
        "Count of Errored Seconds (ES) on this endpoint since the xU
        was last restarted."
    REFERENCE
        "HDSL2 Section 7.5.3.7; SHDSL Section 9.5.5.7"
    ::= { hdsl2ShdslEndpointCurrEntry 4 }

hdsl2ShdslEndpointSES OBJECT-TYPE
    SYNTAX Counter
--  Units
--    seconds
    ACCESS read-only
    STATUS mandatory
    DESCRIPTION
        "Count of Severely Errored Seconds (SES) on this endpoint
        since the xU was last restarted."
    REFERENCE
        "HDSL2 Section 7.5.3.7; SHDSL Section 9.5.5.7"
    ::= { hdsl2ShdslEndpointCurrEntry 5 }

hdsl2ShdslEndpointCRCanomalies OBJECT-TYPE
    SYNTAX Counter
--  Units
--    detected CRC Anomalies
    ACCESS read-only
    STATUS mandatory
    DESCRIPTION
        "Count of CRC anomalies on this endpoint since the xU was
        last restarted."
    REFERENCE
        "HDSL2 Section 7.5.3.7; SHDSL Section 9.5.5.7"
    ::= { hdsl2ShdslEndpointCurrEntry 6 }

hdsl2ShdslEndpointLOSWS OBJECT-TYPE
    SYNTAX Counter
--  Units
--    seconds
    ACCESS read-only
    STATUS mandatory
    DESCRIPTION
        "Count of Loss of Sync Word (LOSW) Seconds on this endpoint
        since the xU was last restarted."
    REFERENCE
        "HDSL2 Section 7.5.3.7; SHDSL Section 9.5.5.7"
    ::= { hdsl2ShdslEndpointCurrEntry 7 }

hdsl2ShdslEndpointUAS OBJECT-TYPE
    SYNTAX Counter
--  Units
--    seconds
    ACCESS read-only
    STATUS mandatory
    DESCRIPTION
        "Count of Unavailable Seconds (UAS) on this endpoint since
        the xU was last restarted."
    REFERENCE
        "HDSL2 Section 7.5.3.7; SHDSL Section 9.5.5.7"
    ::= { hdsl2ShdslEndpointCurrEntry 8 }

hdsl2ShdslEndpointCurr15MinTimeElapsed OBJECT-TYPE
    SYNTAX Hdsl2ShdslPerfTimeElapsed
--    Rsyntax Gauge(0..86399)
--  Units
--    seconds
    ACCESS read-only
    STATUS mandatory
    DESCRIPTION
        "Total elapsed seconds in the current 15-minute interval."
    ::= { hdsl2ShdslEndpointCurrEntry 9 }

hdsl2ShdslEndpointCurr15MinES OBJECT-TYPE
    SYNTAX PerfCurrentCount
--    Rsyntax Gauge
--  Units
--    seconds
    ACCESS read-only
    STATUS mandatory
    DESCRIPTION
        "Count of Errored Seconds (ES) in the current 15-minute
        interval."
    REFERENCE
        "HDSL2 Section 7.5.3.7; SHDSL Section 9.5.5.7"
    ::= { hdsl2ShdslEndpointCurrEntry 10 }

hdsl2ShdslEndpointCurr15MinSES OBJECT-TYPE
    SYNTAX PerfCurrentCount
--    Rsyntax Gauge
--  Units
--    seconds
    ACCESS read-only
    STATUS mandatory
    DESCRIPTION
        "Count of Severely Errored Seconds (SES) in the current
        15-minute interval."
    REFERENCE
        "HDSL2 Section 7.5.3.7; SHDSL Section 9.5.5.7"
    ::= { hdsl2ShdslEndpointCurrEntry 11 }

hdsl2ShdslEndpointCurr15MinCRCanomalies OBJECT-TYPE
    SYNTAX PerfCurrentCount
--    Rsyntax Gauge
--  Units
--    detected CRC Anomalies
    ACCESS read-only
    STATUS mandatory
    DESCRIPTION
        "Count of CRC anomalies in the current 15-minute interval."
    REFERENCE
        "HDSL2 Section 7.5.3.7; SHDSL Section 9.5.5.7"
    ::= { hdsl2ShdslEndpointCurrEntry 12 }

hdsl2ShdslEndpointCurr15MinLOSWS OBJECT-TYPE
    SYNTAX PerfCurrentCount
--    Rsyntax Gauge
--  Units
--    seconds
    ACCESS read-only
    STATUS mandatory
    DESCRIPTION
        "Count of Loss of Sync Word (LOSW) Seconds in the current
        15-minute interval."
    REFERENCE
        "HDSL2 Section 7.5.3.7; SHDSL Section 9.5.5.7"
    ::= { hdsl2ShdslEndpointCurrEntry 13 }

hdsl2ShdslEndpointCurr15MinUAS OBJECT-TYPE
    SYNTAX PerfCurrentCount
--    Rsyntax Gauge
--  Units
--    seconds
    ACCESS read-only
    STATUS mandatory
    DESCRIPTION
        "Count of Unavailable Seconds (UAS) in the current 15-minute
        interval."
    REFERENCE
        "HDSL2 Section 7.5.3.7; SHDSL Section 9.5.5.7"
    ::= { hdsl2ShdslEndpointCurrEntry 14 }

hdsl2ShdslEndpointCurr1DayTimeElapsed OBJECT-TYPE
    SYNTAX Hdsl2ShdslPerfTimeElapsed
--    Rsyntax Gauge(0..86399)
--  Units
--    seconds
    ACCESS read-only
    STATUS mandatory
    DESCRIPTION
        "Number of seconds that have elapsed since the beginning of
        the current 1-day interval."
    ::= { hdsl2ShdslEndpointCurrEntry 15 }

hdsl2ShdslEndpointCurr1DayES OBJECT-TYPE
    SYNTAX Hdsl2ShdslPerfCurrDayCount
--    Rsyntax Gauge
--  Units
--    seconds
    ACCESS read-only
    STATUS mandatory
    DESCRIPTION
        "Count of Errored Seconds (ES) during the current day as
        measured by hdsl2ShdslEndpointCurr1DayTimeElapsed."
    REFERENCE
        "HDSL2 Section 7.5.3.7; SHDSL Section 9.5.5.7"
    ::= { hdsl2ShdslEndpointCurrEntry 16 }

hdsl2ShdslEndpointCurr1DaySES OBJECT-TYPE
    SYNTAX Hdsl2ShdslPerfCurrDayCount
--    Rsyntax Gauge
--  Units
--    seconds
    ACCESS read-only
    STATUS mandatory
    DESCRIPTION
        "Count of Severely Errored Seconds (SES) during the current
        day as measured by hdsl2ShdslEndpointCurr1DayTimeElapsed."
    REFERENCE
        "HDSL2 Section 7.5.3.7; SHDSL Section 9.5.5.7"
    ::= { hdsl2ShdslEndpointCurrEntry 17 }

hdsl2ShdslEndpointCurr1DayCRCanomalies OBJECT-TYPE
    SYNTAX Hdsl2ShdslPerfCurrDayCount
--    Rsyntax Gauge
--  Units
--    detected CRC Anomalies
    ACCESS read-only
    STATUS mandatory
    DESCRIPTION
        "Count of CRC anomalies during the current day as measured
        by hdsl2ShdslEndpointCurr1DayTimeElapsed."
    REFERENCE
        "HDSL2 Section 7.5.3.7; SHDSL Section 9.5.5.7"
    ::= { hdsl2ShdslEndpointCurrEntry 18 }

hdsl2ShdslEndpointCurr1DayLOSWS OBJECT-TYPE
    SYNTAX Hdsl2ShdslPerfCurrDayCount
--    Rsyntax Gauge
--  Units
--    seconds
    ACCESS read-only
    STATUS mandatory
    DESCRIPTION
        "Count of Loss of Sync Word (LOSW) Seconds during the current
        day as measured by hdsl2ShdslEndpointCurr1DayTimeElapsed."
    REFERENCE
        "HDSL2 Section 7.5.3.7; SHDSL Section 9.5.5.7"
    ::= { hdsl2ShdslEndpointCurrEntry 19 }

hdsl2ShdslEndpointCurr1DayUAS OBJECT-TYPE
    SYNTAX Hdsl2ShdslPerfCurrDayCount
--    Rsyntax Gauge
--  Units
--    seconds
    ACCESS read-only
    STATUS mandatory
    DESCRIPTION
        "Count of Unavailable Seconds (UAS) during the current day as
        measured by hdsl2ShdslEndpointCurr1DayTimeElapsed."
    REFERENCE
        "HDSL2 Section 7.5.3.7; SHDSL Section 9.5.5.7"
    ::= { hdsl2ShdslEndpointCurrEntry 20 }

hdsl2ShdslEndpointCurrTipRingReversal OBJECT-TYPE
    SYNTAX INTEGER {
        normal(1),
        reversed(2)
        }
    ACCESS read-only
    STATUS mandatory
    DESCRIPTION
        "This object indicates the state of the tip/ring for the
        wire pair."
    ::= { hdsl2ShdslEndpointCurrEntry 21 }

hdsl2ShdslEndpointCurrActivationState OBJECT-TYPE
    SYNTAX INTEGER {
        preActivation(1),
        activation(2),
        data(3)
        }
    ACCESS read-only
    STATUS mandatory
    DESCRIPTION
        "This object indicates the activation or training state of
        the wire pair."
    REFERENCE
        "ITU-T G.991.2, Section 6.2 PMD Activation Sequence"
    ::= { hdsl2ShdslEndpointCurrEntry 22 }

hdsl2Shdsl15MinIntervalTable OBJECT-TYPE
    SYNTAX SEQUENCE OF Hdsl2Shdsl15MinIntervalEntry
    ACCESS not-accessible
    STATUS mandatory
    DESCRIPTION
        "This table provides one row for each HDSL2/SHDSL endpoint
        performance data collection interval.  This table contains
        live data from equipment.  As such, it is NOT persistent."
    ::= { hdsl2ShdslMibObjects 6 }

hdsl2Shdsl15MinIntervalEntry OBJECT-TYPE
    SYNTAX Hdsl2Shdsl15MinIntervalEntry
    ACCESS not-accessible
    STATUS mandatory
    DESCRIPTION
        "An entry in the hdsl2Shdsl15MinIntervalTable."
    INDEX { ifIndex, hdsl2ShdslInvIndex, hdsl2ShdslEndpointSide, hdsl2ShdslEndpointWirePair, hdsl2Shdsl15MinIntervalNumber }
    ::= { hdsl2Shdsl15MinIntervalTable 1 }

Hdsl2Shdsl15MinIntervalEntry ::= SEQUENCE {
    hdsl2Shdsl15MinIntervalNumber Gauge,
    hdsl2Shdsl15MinIntervalES PerfIntervalCount,
    hdsl2Shdsl15MinIntervalSES PerfIntervalCount,
    hdsl2Shdsl15MinIntervalCRCanomalies PerfIntervalCount,
    hdsl2Shdsl15MinIntervalLOSWS PerfIntervalCount,
    hdsl2Shdsl15MinIntervalUAS PerfIntervalCount
    }

hdsl2Shdsl15MinIntervalNumber OBJECT-TYPE
    SYNTAX Gauge(1..96)
    ACCESS not-accessible
    STATUS mandatory
    DESCRIPTION
        "Performance Data Interval number.  Interval 1 is the most
        recent previous interval; interval 96 is 24 hours ago.
        Intervals 2..96 are optional."
    ::= { hdsl2Shdsl15MinIntervalEntry 1 }

hdsl2Shdsl15MinIntervalES OBJECT-TYPE
    SYNTAX PerfIntervalCount
--    Rsyntax Gauge
--  Units
--    seconds
    ACCESS read-only
    STATUS mandatory
    DESCRIPTION
        "Count of Errored Seconds (ES) during the interval."
    REFERENCE
        "HDSL2 Section 7.5.3.7; SHDSL Section 9.5.5.7"
    ::= { hdsl2Shdsl15MinIntervalEntry 2 }

hdsl2Shdsl15MinIntervalSES OBJECT-TYPE
    SYNTAX PerfIntervalCount
--    Rsyntax Gauge
--  Units
--    seconds
    ACCESS read-only
    STATUS mandatory
    DESCRIPTION
        "Count of Severely Errored Seconds (SES) during the interval."
    REFERENCE
        "HDSL2 Section 7.5.3.7; SHDSL Section 9.5.5.7"
    ::= { hdsl2Shdsl15MinIntervalEntry 3 }

hdsl2Shdsl15MinIntervalCRCanomalies OBJECT-TYPE
    SYNTAX PerfIntervalCount
--    Rsyntax Gauge
--  Units
--    detected CRC Anomalies
    ACCESS read-only
    STATUS mandatory
    DESCRIPTION
        "Count of CRC anomalies during the interval."
    REFERENCE
        "HDSL2 Section 7.5.3.7; SHDSL Section 9.5.5.7"
    ::= { hdsl2Shdsl15MinIntervalEntry 4 }

hdsl2Shdsl15MinIntervalLOSWS OBJECT-TYPE
    SYNTAX PerfIntervalCount
--    Rsyntax Gauge
--  Units
--    seconds
    ACCESS read-only
    STATUS mandatory
    DESCRIPTION
        "Count of Loss of Sync Word (LOSW) Seconds during the
        interval."
    REFERENCE
        "HDSL2 Section 7.5.3.7; SHDSL Section 9.5.5.7"
    ::= { hdsl2Shdsl15MinIntervalEntry 5 }

hdsl2Shdsl15MinIntervalUAS OBJECT-TYPE
    SYNTAX PerfIntervalCount
--    Rsyntax Gauge
--  Units
--    seconds
    ACCESS read-only
    STATUS mandatory
    DESCRIPTION
        "Count of Unavailable Seconds (UAS) during the interval."
    REFERENCE
        "HDSL2 Section 7.5.3.7; SHDSL Section 9.5.5.7"
    ::= { hdsl2Shdsl15MinIntervalEntry 6 }

hdsl2Shdsl1DayIntervalTable OBJECT-TYPE
    SYNTAX SEQUENCE OF Hdsl2Shdsl1DayIntervalEntry
    ACCESS not-accessible
    STATUS mandatory
    DESCRIPTION
        "This table provides one row for each HDSL2/SHDSL endpoint
        performance data collection interval.  This table contains
        live data from equipment.  As such, it is NOT persistent."
    ::= { hdsl2ShdslMibObjects 7 }

hdsl2Shdsl1DayIntervalEntry OBJECT-TYPE
    SYNTAX Hdsl2Shdsl1DayIntervalEntry
    ACCESS not-accessible
    STATUS mandatory
    DESCRIPTION
        "An entry in the hdsl2Shdsl1DayIntervalTable."
    INDEX { ifIndex, hdsl2ShdslInvIndex, hdsl2ShdslEndpointSide, hdsl2ShdslEndpointWirePair, hdsl2Shdsl1DayIntervalNumber }
    ::= { hdsl2Shdsl1DayIntervalTable 1 }

Hdsl2Shdsl1DayIntervalEntry ::= SEQUENCE {
    hdsl2Shdsl1DayIntervalNumber Gauge,
    hdsl2Shdsl1DayIntervalMoniSecs Hdsl2ShdslPerfTimeElapsed,
    hdsl2Shdsl1DayIntervalES Hdsl2Shdsl1DayIntervalCount,
    hdsl2Shdsl1DayIntervalSES Hdsl2Shdsl1DayIntervalCount,
    hdsl2Shdsl1DayIntervalCRCanomalies Hdsl2Shdsl1DayIntervalCount,
    hdsl2Shdsl1DayIntervalLOSWS Hdsl2Shdsl1DayIntervalCount,
    hdsl2Shdsl1DayIntervalUAS Hdsl2Shdsl1DayIntervalCount
    }

hdsl2Shdsl1DayIntervalNumber OBJECT-TYPE
    SYNTAX Gauge(1..30)
    ACCESS not-accessible
    STATUS mandatory
    DESCRIPTION
        "History Data Interval number.  Interval 1 is the most
        recent previous day; interval 30 is 30 days ago.  Intervals
        2..30 are optional."
    ::= { hdsl2Shdsl1DayIntervalEntry 1 }

hdsl2Shdsl1DayIntervalMoniSecs OBJECT-TYPE
    SYNTAX Hdsl2ShdslPerfTimeElapsed
--    Rsyntax Gauge(0..86399)
--  Units
--    seconds
    ACCESS read-only
    STATUS mandatory
    DESCRIPTION
        "The amount of time in the 1-day interval over which the
        performance monitoring information is actually counted.
        This value will be the same as the interval duration except
        in a situation where performance monitoring data could not
        be collected for any reason."
    ::= { hdsl2Shdsl1DayIntervalEntry 2 }

hdsl2Shdsl1DayIntervalES OBJECT-TYPE
    SYNTAX Hdsl2Shdsl1DayIntervalCount
--    Rsyntax Gauge
--  Units
--    seconds
    ACCESS read-only
    STATUS mandatory
    DESCRIPTION
        "Count of Errored Seconds (ES) during the 1-day interval as
        measured by hdsl2Shdsl1DayIntervalMoniSecs."
    REFERENCE
        "HDSL2 Section 7.5.3.7; SHDSL Section 9.5.5.7"
    ::= { hdsl2Shdsl1DayIntervalEntry 3 }

hdsl2Shdsl1DayIntervalSES OBJECT-TYPE
    SYNTAX Hdsl2Shdsl1DayIntervalCount
--    Rsyntax Gauge
--  Units
--    seconds
    ACCESS read-only
    STATUS mandatory
    DESCRIPTION
        "Count of Severely Errored Seconds (SES) during the 1-day
        interval as measured by hdsl2Shdsl1DayIntervalMoniSecs."
    REFERENCE
        "HDSL2 Section 7.5.3.7; SHDSL Section 9.5.5.7"
    ::= { hdsl2Shdsl1DayIntervalEntry 4 }

hdsl2Shdsl1DayIntervalCRCanomalies OBJECT-TYPE
    SYNTAX Hdsl2Shdsl1DayIntervalCount
--    Rsyntax Gauge
--  Units
--    detected CRC Anomalies
    ACCESS read-only
    STATUS mandatory
    DESCRIPTION
        "Count of CRC anomalies during the 1-day interval as
        measured by hdsl2Shdsl1DayIntervalMoniSecs."
    REFERENCE
        "HDSL2 Section 7.5.3.7; SHDSL Section 9.5.5.7"
    ::= { hdsl2Shdsl1DayIntervalEntry 5 }

hdsl2Shdsl1DayIntervalLOSWS OBJECT-TYPE
    SYNTAX Hdsl2Shdsl1DayIntervalCount
--    Rsyntax Gauge
--  Units
--    seconds
    ACCESS read-only
    STATUS mandatory
    DESCRIPTION
        "Count of Loss of Sync Word (LOSW) Seconds during the 1-day
        interval as measured by hdsl2Shdsl1DayIntervalMoniSecs."
    REFERENCE
        "HDSL2 Section 7.5.3.7; SHDSL Section 9.5.5.7"
    ::= { hdsl2Shdsl1DayIntervalEntry 6 }

hdsl2Shdsl1DayIntervalUAS OBJECT-TYPE
    SYNTAX Hdsl2Shdsl1DayIntervalCount
--    Rsyntax Gauge
--  Units
--    seconds
    ACCESS read-only
    STATUS mandatory
    DESCRIPTION
        "Count of Unavailable Seconds (UAS) during the 1-day interval
        as measured by hdsl2Shdsl1DayIntervalMoniSecs."
    REFERENCE
        "HDSL2 Section 7.5.3.7; SHDSL Section 9.5.5.7"
    ::= { hdsl2Shdsl1DayIntervalEntry 7 }

hdsl2ShdslEndpointMaintTable OBJECT-TYPE
    SYNTAX SEQUENCE OF Hdsl2ShdslEndpointMaintEntry
    ACCESS not-accessible
    STATUS mandatory
    DESCRIPTION
        "This table supports maintenance operations (e.g., loopbacks)
        to be performed on HDSL2/SHDSL segment endpoints.  This table
        contains live data from equipment.  As such, it is NOT
        persistent."
    ::= { hdsl2ShdslMibObjects 8 }

hdsl2ShdslEndpointMaintEntry OBJECT-TYPE
    SYNTAX Hdsl2ShdslEndpointMaintEntry
    ACCESS not-accessible
    STATUS mandatory
    DESCRIPTION
        "An entry in the hdsl2ShdslEndpointMaintTable.  Each entry
        corresponds to a single segment endpoint and is indexed by the
        ifIndex of the HDSL2/SHDSL line, the UnitId of the associated
        unit, and the side of the unit."
    INDEX { ifIndex, hdsl2ShdslInvIndex, hdsl2ShdslEndpointSide }
    ::= { hdsl2ShdslEndpointMaintTable 1 }

Hdsl2ShdslEndpointMaintEntry ::= SEQUENCE {
    hdsl2ShdslMaintLoopbackConfig INTEGER,
    hdsl2ShdslMaintTipRingReversal INTEGER,
    hdsl2ShdslMaintPowerBackOff INTEGER,
    hdsl2ShdslMaintSoftRestart INTEGER
    }

hdsl2ShdslMaintLoopbackConfig OBJECT-TYPE
    SYNTAX INTEGER {
        noLoopback(1),
        normalLoopback(2),
        specialLoopback(3)
        }
    ACCESS read-write
    STATUS mandatory
    DESCRIPTION
        "This object controls configuration of loopbacks for the
        associated segment endpoint.  The status of the loopback
        is obtained via the hdsl2ShdslEndpointCurrStatus object."
    ::= { hdsl2ShdslEndpointMaintEntry 1 }

hdsl2ShdslMaintTipRingReversal OBJECT-TYPE
    SYNTAX INTEGER {
        normal(1),
        reversed(2)
        }
    ACCESS read-only
    STATUS mandatory
    DESCRIPTION
        "This object indicates the state of the tip/ring pair at the
        associated segment endpoint."
    ::= { hdsl2ShdslEndpointMaintEntry 2 }

hdsl2ShdslMaintPowerBackOff OBJECT-TYPE
    SYNTAX INTEGER {
        default(1),
        enhanced(2)
        }
    ACCESS read-write
    STATUS mandatory
    DESCRIPTION
        "This object configures the receiver at the associated
        segment endpoint to operate in default or enhanced power
        backoff mode."
    ::= { hdsl2ShdslEndpointMaintEntry 3 }

hdsl2ShdslMaintSoftRestart OBJECT-TYPE
    SYNTAX INTEGER {
        ready(1),
        restart(2)
        }
    ACCESS read-write
    STATUS mandatory
    DESCRIPTION
        "This object enables the manager to trigger a soft restart
        of the modem at the associated segment endpoint.  The
        manager may only set this object to the 'restart(2)'
        value, which initiates a restart.  The agent will perform a
        restart after approximately 5 seconds.  Following the 5 second
        period, the agent will restore the object to the 'ready(1)'
        state."
    ::= { hdsl2ShdslEndpointMaintEntry 4 }

hdsl2ShdslUnitMaintTable OBJECT-TYPE
    SYNTAX SEQUENCE OF Hdsl2ShdslUnitMaintEntry
    ACCESS not-accessible
    STATUS mandatory
    DESCRIPTION
        "This table supports maintenance operations for units in a
        HDSL2/SHDSL line.  Entries in this table MUST be maintained
        in a persistent manner."
    ::= { hdsl2ShdslMibObjects 9 }

hdsl2ShdslUnitMaintEntry OBJECT-TYPE
    SYNTAX Hdsl2ShdslUnitMaintEntry
    ACCESS not-accessible
    STATUS mandatory
    DESCRIPTION
        "An entry in the hdsl2ShdslUnitMaintTable.  Each entry
        corresponds to a single unit and is indexed by the
        ifIndex of the HDSL2/SHDSL line and the UnitId of the
        associated unit."
    INDEX { ifIndex, hdsl2ShdslInvIndex }
    ::= { hdsl2ShdslUnitMaintTable 1 }

Hdsl2ShdslUnitMaintEntry ::= SEQUENCE {
    hdsl2ShdslMaintLoopbackTimeout INTEGER,
    hdsl2ShdslMaintUnitPowerSource INTEGER
    }

hdsl2ShdslMaintLoopbackTimeout OBJECT-TYPE
    SYNTAX INTEGER(0..4095)
--  Units
--    minutes
    ACCESS read-write
    STATUS mandatory
    DESCRIPTION
        "This object configures the timeout value for loopbacks
        initiated at segments endpoints contained in the associated
        unit.  A value of 0 disables the timeout."
    ::= { hdsl2ShdslUnitMaintEntry 1 }

hdsl2ShdslMaintUnitPowerSource OBJECT-TYPE
    SYNTAX INTEGER {
        local(1),
        span(2)
        }
    ACCESS read-only
    STATUS mandatory
    DESCRIPTION
        "This object indicates the DC power source being used by the
        associated unit."
    ::= { hdsl2ShdslUnitMaintEntry 2 }

hdsl2ShdslSpanConfProfileTable OBJECT-TYPE
    SYNTAX SEQUENCE OF Hdsl2ShdslSpanConfProfileEntry
    ACCESS not-accessible
    STATUS mandatory
    DESCRIPTION
        "This table supports definitions of span configuration
        profiles for SHDSL lines.  HDSL2 does not support these
        configuration options.  This table MUST be maintained
        in a persistent manner."
    ::= { hdsl2ShdslMibObjects 10 }

hdsl2ShdslSpanConfProfileEntry OBJECT-TYPE
    SYNTAX Hdsl2ShdslSpanConfProfileEntry
    ACCESS not-accessible
    STATUS mandatory
    DESCRIPTION
        "Each entry corresponds to a single span configuration
        profile.  Each profile contains a set of span configuration
        parameters.  The configuration parameters in a profile are
        applied to those lines referencing that profile (see the
        hdsl2ShdslSpanConfProfile object).  Profiles may be
        created/deleted using the row creation/deletion mechanism
        via hdsl2ShdslSpanConfProfileRowStatus.  If an active
        entry is referenced in hdsl2ShdslSpanConfProfile, the
        entry MUST remain active until all references are removed."
    INDEX { --?? IMPLIED may cause problems
            IMPLIED hdsl2ShdslSpanConfProfileName }
    ::= { hdsl2ShdslSpanConfProfileTable 1 }

Hdsl2ShdslSpanConfProfileEntry ::= SEQUENCE {
    hdsl2ShdslSpanConfProfileName SnmpAdminString,
    hdsl2ShdslSpanConfWireInterface INTEGER,
    hdsl2ShdslSpanConfMinLineRate Gauge,
    hdsl2ShdslSpanConfMaxLineRate Gauge,
    hdsl2ShdslSpanConfPSD INTEGER,
    hdsl2ShdslSpanConfTransmissionMode Hdsl2ShdslTransmissionModeType,
    hdsl2ShdslSpanConfRemoteEnabled INTEGER,
    hdsl2ShdslSpanConfPowerFeeding INTEGER,
    hdsl2ShdslSpanConfCurrCondTargetMarginDown INTEGER,
    hdsl2ShdslSpanConfWorstCaseTargetMarginDown INTEGER,
    hdsl2ShdslSpanConfCurrCondTargetMarginUp INTEGER,
    hdsl2ShdslSpanConfWorstCaseTargetMarginUp INTEGER,
    hdsl2ShdslSpanConfUsedTargetMargins OCTET STRING,
    hdsl2ShdslSpanConfReferenceClock Hdsl2ShdslClockReferenceType,
    hdsl2ShdslSpanConfLineProbeEnable INTEGER,
    hdsl2ShdslSpanConfProfileRowStatus RowStatus
    }

hdsl2ShdslSpanConfProfileName OBJECT-TYPE
    SYNTAX SnmpAdminString(SIZE(1..32))
--    Rsyntax OCTET STRING(SIZE(1..32))
    ACCESS not-accessible
    STATUS mandatory
    DESCRIPTION
        "This object is the unique index associated with this profile.
        Entries in this table are referenced via the object
        hdsl2ShdslSpanConfProfile in Hdsl2ShdslSpanConfEntry."
    ::= { hdsl2ShdslSpanConfProfileEntry 1 }

hdsl2ShdslSpanConfWireInterface OBJECT-TYPE
    SYNTAX INTEGER {
        twoWire(1),
        fourWire(2),
        sixWire(3),
        eightWire(4)
        }
    ACCESS read-write
    STATUS mandatory
    DESCRIPTION
        "This object configures the two-wire or optional four-wire,
        six-wire, or eight-wire operation for SHDSL lines."
    DEFVAL { twoWire }
    ::= { hdsl2ShdslSpanConfProfileEntry 2 }

hdsl2ShdslSpanConfMinLineRate OBJECT-TYPE
    SYNTAX Gauge(0..4294967295)
--  Units
--    bps
    ACCESS read-write
    STATUS mandatory
    DESCRIPTION
        "This object configures the minimum transmission rate for
        the associated SHDSL Line in bits-per-second (bps) and includes
        both payload (user data) and any applicable framing overhead.
        If the minimum line rate equals the maximum line rate
        (hdsl2ShdslSpanMaxLineRate), the line rate is considered
        'fixed'.  If the minimum line rate is less than the
        maximum line rate, the line rate is considered
        'rate-adaptive'."
    DEFVAL { 1552000 }
    ::= { hdsl2ShdslSpanConfProfileEntry 3 }

hdsl2ShdslSpanConfMaxLineRate OBJECT-TYPE
    SYNTAX Gauge(0..4294967295)
--  Units
--    bps
    ACCESS read-write
    STATUS mandatory
    DESCRIPTION
        "This object configures the maximum transmission rate for
        the associated SHDSL Line in bits-per-second (bps) and includes
        both payload (user data) and any applicable framing overhead.
        If the minimum line rate equals the maximum line rate
        (hdsl2ShdslSpanMaxLineRate), the line rate is considered
        'fixed'.  If the minimum line rate is less than the
        maximum line rate, the line rate is considered
        'rate-adaptive'."
    DEFVAL { 1552000 }
    ::= { hdsl2ShdslSpanConfProfileEntry 4 }

hdsl2ShdslSpanConfPSD OBJECT-TYPE
    SYNTAX INTEGER {
        symmetric(1),
        asymmetric(2)
        }
    ACCESS read-write
    STATUS mandatory
    DESCRIPTION
        "This object configures use of symmetric/asymmetric PSD (Power
        Spectral Density) Mask for the associated SHDSL Line.  Support
        for symmetric PSD is mandatory for all supported data rates.
        Support for asymmetric PSD is optional."
    DEFVAL { symmetric }
    ::= { hdsl2ShdslSpanConfProfileEntry 5 }

hdsl2ShdslSpanConfTransmissionMode OBJECT-TYPE
    SYNTAX Hdsl2ShdslTransmissionModeType
--    Rsyntax OCTET STRING(SIZE(1..2))
--         BITS are:
--           region1(0)
--           region2(1)
    ACCESS read-write
    STATUS mandatory
    DESCRIPTION
        "This object specifies the regional setting for the SHDSL
        line."
    DEFVAL { '80'h }
    ::= { hdsl2ShdslSpanConfProfileEntry 6 }

hdsl2ShdslSpanConfRemoteEnabled OBJECT-TYPE
    SYNTAX INTEGER {
        enabled(1),
        disabled(2)
        }
    ACCESS read-write
    STATUS mandatory
    DESCRIPTION
        "This object enables/disables support for remote management
        of the units in an SHDSL line from the STU-R via the EOC."
    DEFVAL { enabled }
    ::= { hdsl2ShdslSpanConfProfileEntry 7 }

hdsl2ShdslSpanConfPowerFeeding OBJECT-TYPE
    SYNTAX INTEGER {
        noPower(1),
        powerFeed(2),
        wettingCurrent(3)
        }
    ACCESS read-write
    STATUS mandatory
    DESCRIPTION
        "This object enables/disables support for optional power
        feeding in an SHDSL line."
    DEFVAL { noPower }
    ::= { hdsl2ShdslSpanConfProfileEntry 8 }

hdsl2ShdslSpanConfCurrCondTargetMarginDown OBJECT-TYPE
    SYNTAX INTEGER(-10..21)
--  Units
--    dB
    ACCESS read-write
    STATUS mandatory
    DESCRIPTION
        "This object specifies the downstream current condition target
        SNR margin for an SHDSL line.  The SNR margin is the difference
        between the desired SNR and the actual SNR.  Target SNR margin
        is the desired SNR margin for a unit."
    DEFVAL { 0 }
    ::= { hdsl2ShdslSpanConfProfileEntry 9 }

hdsl2ShdslSpanConfWorstCaseTargetMarginDown OBJECT-TYPE
    SYNTAX INTEGER(-10..21)
--  Units
--    dB
    ACCESS read-write
    STATUS mandatory
    DESCRIPTION
        "This object specifies the downstream worst-case target SNR
        margin for an SHDSL line.  The SNR margin is the difference
        between the desired SNR and the actual SNR.  Target SNR
        margin is the desired SNR margin for a unit."
    DEFVAL { 0 }
    ::= { hdsl2ShdslSpanConfProfileEntry 10 }

hdsl2ShdslSpanConfCurrCondTargetMarginUp OBJECT-TYPE
    SYNTAX INTEGER(-10..21)
--  Units
--    dB
    ACCESS read-write
    STATUS mandatory
    DESCRIPTION
        "This object specifies the upstream current-condition target
        SNR margin for an SHDSL line.  The SNR margin is the difference
        between the desired SNR and the actual SNR.  Target SNR margin
        is the desired SNR margin for a unit."
    DEFVAL { 0 }
    ::= { hdsl2ShdslSpanConfProfileEntry 11 }

hdsl2ShdslSpanConfWorstCaseTargetMarginUp OBJECT-TYPE
    SYNTAX INTEGER(-10..21)
--  Units
--    dB
    ACCESS read-write
    STATUS mandatory
    DESCRIPTION
        "This object specifies the upstream worst-case target SNR
        margin for an SHDSL line.  The SNR margin is the difference
        between the desired SNR and the actual SNR.  Target SNR margin
        is the desired SNR margin for a unit."
    DEFVAL { 0 }
    ::= { hdsl2ShdslSpanConfProfileEntry 12 }

hdsl2ShdslSpanConfUsedTargetMargins OBJECT-TYPE
    SYNTAX OCTET STRING(SIZE(1..2))
        -- BITS are:
        --   currCondDown(0)
        --   worstCaseDown(1)
        --   currCondUp(2)
        --   worstCaseUp(3)
    ACCESS read-write
    STATUS mandatory
    DESCRIPTION
        "Indicates whether a target SNR margin is enabled or
        disabled.  This is a bit-map of possible settings.  The
        various bit positions are as follows:
        
        currCondDown   - current-condition downstream target SNR
                         margin enabled
        
        worstCaseDown  - worst-case downstream target SNR margin
                         enabled
        
        currCondUp     - current-condition upstream target SNR
                         margin enabled
        
        worstCaseUp    - worst-case upstream target SNR margin
                         enabled."
    DEFVAL { '80'h }
    ::= { hdsl2ShdslSpanConfProfileEntry 13 }

hdsl2ShdslSpanConfReferenceClock OBJECT-TYPE
    SYNTAX Hdsl2ShdslClockReferenceType
--    Rsyntax INTEGER {
--        localClk(1),
--        networkClk(2),
--        dataOrNetworkClk(3),
--        dataClk(4)
--        }
    ACCESS read-write
    STATUS mandatory
    DESCRIPTION
        "This object configures the clock reference for the STU-C
        in an SHDSL Line."
    DEFVAL { localClk }
    ::= { hdsl2ShdslSpanConfProfileEntry 14 }

hdsl2ShdslSpanConfLineProbeEnable OBJECT-TYPE
    SYNTAX INTEGER {
        disable(1),
        enable(2)
        }
    ACCESS read-write
    STATUS mandatory
    DESCRIPTION
        "This object enables/disables support for Line Probe of
        the units in an SHDSL line.  When Line Probe is enabled, the
        system performs Line Probing to find the best possible
        rate.  If Line Probe is disabled, the rate adaptation phase
        is skipped to shorten set up time."
    DEFVAL { disable }
    ::= { hdsl2ShdslSpanConfProfileEntry 15 }

hdsl2ShdslSpanConfProfileRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object controls creation/deletion of the associated
        entry in this table per the semantics of RowStatus.  If an
        active entry is referenced in hdsl2ShdslSpanConfProfile, the
        entry MUST remain active until all references are removed."
    ::= { hdsl2ShdslSpanConfProfileEntry 16 }

hdsl2ShdslEndpointAlarmConfProfileTable OBJECT-TYPE
    SYNTAX SEQUENCE OF Hdsl2ShdslEndpointAlarmConfProfileEntry
    ACCESS not-accessible
    STATUS mandatory
    DESCRIPTION
        "This table supports definitions of alarm configuration
        profiles for HDSL2/SHDSL segment endpoints.  This table
        MUST be maintained in a persistent manner."
    ::= { hdsl2ShdslMibObjects 11 }

hdsl2ShdslEndpointAlarmConfProfileEntry OBJECT-TYPE
    SYNTAX Hdsl2ShdslEndpointAlarmConfProfileEntry
    ACCESS not-accessible
    STATUS mandatory
    DESCRIPTION
        "Each entry corresponds to a single alarm configuration profile.
        Each profile contains a set of parameters for setting alarm
        thresholds for various performance attributes monitored at
        HDSL2/SHDSL segment endpoints.  Profiles may be created/deleted
        using the row creation/deletion mechanism via
        hdsl2ShdslEndpointAlarmConfProfileRowStatus.  If an active
        entry is referenced in either hdsl2ShdslSpanConfAlarmProfile
        or hdsl2ShdslEndpointAlarmConfProfile, the entry MUST remain
        active until all references are removed."
    INDEX { --?? IMPLIED may cause problems
            IMPLIED hdsl2ShdslEndpointAlarmConfProfileName }
    ::= { hdsl2ShdslEndpointAlarmConfProfileTable 1 }

Hdsl2ShdslEndpointAlarmConfProfileEntry ::= SEQUENCE {
    hdsl2ShdslEndpointAlarmConfProfileName SnmpAdminString,
    hdsl2ShdslEndpointThreshLoopAttenuation INTEGER,
    hdsl2ShdslEndpointThreshSNRMargin INTEGER,
    hdsl2ShdslEndpointThreshES Hdsl2ShdslPerfIntervalThreshold,
    hdsl2ShdslEndpointThreshSES Hdsl2ShdslPerfIntervalThreshold,
    hdsl2ShdslEndpointThreshCRCanomalies INTEGER,
    hdsl2ShdslEndpointThreshLOSWS Hdsl2ShdslPerfIntervalThreshold,
    hdsl2ShdslEndpointThreshUAS Hdsl2ShdslPerfIntervalThreshold,
    hdsl2ShdslEndpointAlarmConfProfileRowStatus RowStatus
    }

hdsl2ShdslEndpointAlarmConfProfileName OBJECT-TYPE
    SYNTAX SnmpAdminString(SIZE(1..32))
--    Rsyntax OCTET STRING(SIZE(1..32))
    ACCESS not-accessible
    STATUS mandatory
    DESCRIPTION
        "This object is the unique index associated with this profile."
    ::= { hdsl2ShdslEndpointAlarmConfProfileEntry 1 }

hdsl2ShdslEndpointThreshLoopAttenuation OBJECT-TYPE
    SYNTAX INTEGER(-127..128)
--  Units
--    dB
    ACCESS read-write
    STATUS mandatory
    DESCRIPTION
        "This object configures the loop attenuation alarm threshold.
        When the current value of hdsl2ShdslEndpointCurrAtn reaches
        or exceeds this threshold, an hdsl2ShdslLoopAttenCrossing
        MAY be generated."
    DEFVAL { 0 }
    ::= { hdsl2ShdslEndpointAlarmConfProfileEntry 2 }

hdsl2ShdslEndpointThreshSNRMargin OBJECT-TYPE
    SYNTAX INTEGER(-127..128)
--  Units
--    dB
    ACCESS read-write
    STATUS mandatory
    DESCRIPTION
        "This object configures the SNR margin alarm threshold.
        When the current value of hdsl2ShdslEndpointCurrSnrMgn
        reaches or drops below this threshold, a
        hdsl2ShdslSNRMarginCrossing MAY be generated."
    DEFVAL { 0 }
    ::= { hdsl2ShdslEndpointAlarmConfProfileEntry 3 }

hdsl2ShdslEndpointThreshES OBJECT-TYPE
    SYNTAX Hdsl2ShdslPerfIntervalThreshold
--    Rsyntax Gauge(0..900)
--  Units
--    seconds
    ACCESS read-write
    STATUS mandatory
    DESCRIPTION
        "This object configures the threshold for the number of
        Errored Seconds (ES) within any given 15-minute performance
        data collection interval.  If the value of Errored Seconds
        in a particular 15-minute collection interval reaches/
        exceeds this value, an hdsl2ShdslPerfESThresh MAY be
        generated.  At most, one notification will be sent per
        interval per endpoint."
    DEFVAL { 0 }
    ::= { hdsl2ShdslEndpointAlarmConfProfileEntry 4 }

hdsl2ShdslEndpointThreshSES OBJECT-TYPE
    SYNTAX Hdsl2ShdslPerfIntervalThreshold
--    Rsyntax Gauge(0..900)
--  Units
--    seconds
    ACCESS read-write
    STATUS mandatory
    DESCRIPTION
        "This object configures the threshold for the number of
        Severely Errored Seconds (SES) within any given 15-minute
        performance data collection interval.  If the value of
        Severely Errored Seconds in a particular 15-minute collection
        interval reaches/exceeds this value, an hdsl2ShdslPerfSESThresh
        MAY be generated.  At most, one notification will be sent per
        interval per endpoint."
    DEFVAL { 0 }
    ::= { hdsl2ShdslEndpointAlarmConfProfileEntry 5 }

hdsl2ShdslEndpointThreshCRCanomalies OBJECT-TYPE
    SYNTAX INTEGER
--  Units
--    detected CRC Anomalies
    ACCESS read-write
    STATUS mandatory
    DESCRIPTION
        "This object configures the threshold for the number of
        CRC anomalies within any given 15-minute performance data
        collection interval.  If the value of CRC anomalies in a
        particular 15-minute collection interval reaches/exceeds
        this value, an hdsl2ShdslPerfCRCanomaliesThresh MAY be
        generated.  At most, one notification will be sent per
        interval per endpoint."
    DEFVAL { 0 }
    ::= { hdsl2ShdslEndpointAlarmConfProfileEntry 6 }

hdsl2ShdslEndpointThreshLOSWS OBJECT-TYPE
    SYNTAX Hdsl2ShdslPerfIntervalThreshold
--    Rsyntax Gauge(0..900)
--  Units
--    seconds
    ACCESS read-write
    STATUS mandatory
    DESCRIPTION
        "This object configures the threshold for the number of
        Loss of Sync Word (LOSW) Seconds within any given 15-minute
        performance data collection interval.  If the value of LOSW
        in a particular 15-minute collection interval reaches/exceeds
        this value, an hdsl2ShdslPerfLOSWSThresh MAY be generated.
        At most, one notification will be sent per interval per
        endpoint."
    DEFVAL { 0 }
    ::= { hdsl2ShdslEndpointAlarmConfProfileEntry 7 }

hdsl2ShdslEndpointThreshUAS OBJECT-TYPE
    SYNTAX Hdsl2ShdslPerfIntervalThreshold
--    Rsyntax Gauge(0..900)
--  Units
--    seconds
    ACCESS read-write
    STATUS mandatory
    DESCRIPTION
        "This object configures the threshold for the number of
        Unavailable Seconds (UAS) within any given 15-minute
        performance data collection interval.  If the value of UAS
        in a particular 15-minute collection interval reaches/exceeds
        this value, an hdsl2ShdslPerfUASThresh MAY be generated.
        At most, one notification will be sent per interval per
        endpoint."
    DEFVAL { 0 }
    ::= { hdsl2ShdslEndpointAlarmConfProfileEntry 8 }

hdsl2ShdslEndpointAlarmConfProfileRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object controls creation/deletion of the associated
        entry in this table as per the semantics of RowStatus.
        If an active entry is referenced in either
        hdsl2ShdslSpanConfAlarmProfile or
        hdsl2ShdslEndpointAlarmConfProfile, the entry MUST remain
        active until all references are removed."
    ::= { hdsl2ShdslEndpointAlarmConfProfileEntry 9 }

hdsl2ShdslLoopAttenCrossing TRAP-TYPE
-- Reverse mappable trap
    ENTERPRISE hdsl2ShdslMIB
    VARIABLES {
        hdsl2ShdslEndpointCurrAtn, 
        hdsl2ShdslEndpointThreshLoopAttenuation }
--  Status
--    mandatory
    DESCRIPTION
        "This notification indicates that the loop attenuation
        threshold (as per the hdsl2ShdslEndpointThreshLoopAttenuation
        value) has been reached/exceeded for the HDSL2/SHDSL segment
        endpoint."
    ::= 1

hdsl2ShdslSNRMarginCrossing TRAP-TYPE
-- Reverse mappable trap
    ENTERPRISE hdsl2ShdslMIB
    VARIABLES {
        hdsl2ShdslEndpointCurrSnrMgn, 
        hdsl2ShdslEndpointThreshSNRMargin }
--  Status
--    mandatory
    DESCRIPTION
        "This notification indicates that the SNR margin threshold (as
        per the hdsl2ShdslEndpointThreshSNRMargin value) has been
        reached/exceeded for the HDSL2/SHDSL segment endpoint."
    ::= 2

hdsl2ShdslPerfESThresh TRAP-TYPE
-- Reverse mappable trap
    ENTERPRISE hdsl2ShdslMIB
    VARIABLES {
        hdsl2ShdslEndpointCurr15MinES, hdsl2ShdslEndpointThreshES }
--  Status
--    mandatory
    DESCRIPTION
        "This notification indicates that the errored seconds
        threshold (as per the hdsl2ShdslEndpointThreshES value)
        has been reached/exceeded for the HDSL2/SHDSL segment
        endpoint."
    ::= 3

hdsl2ShdslPerfSESThresh TRAP-TYPE
-- Reverse mappable trap
    ENTERPRISE hdsl2ShdslMIB
    VARIABLES {
        hdsl2ShdslEndpointCurr15MinSES, hdsl2ShdslEndpointThreshSES }
--  Status
--    mandatory
    DESCRIPTION
        "This notification indicates that the severely errored seconds
        threshold (as per the hdsl2ShdslEndpointThreshSES value) has
        been reached/exceeded for the HDSL2/SHDSL segment endpoint."
    ::= 4

hdsl2ShdslPerfCRCanomaliesThresh TRAP-TYPE
-- Reverse mappable trap
    ENTERPRISE hdsl2ShdslMIB
    VARIABLES {
        hdsl2ShdslEndpointCurr15MinCRCanomalies, 
        hdsl2ShdslEndpointThreshCRCanomalies }
--  Status
--    mandatory
    DESCRIPTION
        "This notification indicates that the CRC anomalies threshold
        (as per the hdsl2ShdslEndpointThreshCRCanomalies value) has
        been reached/exceeded for the HDSL2/SHDSL segment endpoint."
    ::= 5

hdsl2ShdslPerfLOSWSThresh TRAP-TYPE
-- Reverse mappable trap
    ENTERPRISE hdsl2ShdslMIB
    VARIABLES {
        hdsl2ShdslEndpointCurr15MinLOSWS, 
        hdsl2ShdslEndpointThreshLOSWS }
--  Status
--    mandatory
    DESCRIPTION
        "This notification indicates that the LOSW Seconds threshold
        (as per the hdsl2ShdslEndpointThreshLOSWS value) has been
        reached/exceeded for the HDSL2/SHDSL segment endpoint."
    ::= 6

hdsl2ShdslPerfUASThresh TRAP-TYPE
-- Reverse mappable trap
    ENTERPRISE hdsl2ShdslMIB
    VARIABLES {
        hdsl2ShdslEndpointCurr15MinUAS, hdsl2ShdslEndpointThreshUAS }
--  Status
--    mandatory
    DESCRIPTION
        "This notification indicates that the unavailable seconds
        threshold (as per the hdsl2ShdslEndpointThreshUAS value) has
        been reached/exceeded for the HDSL2/SHDSL segment endpoint."
    ::= 7

hdsl2ShdslSpanInvalidNumRepeaters TRAP-TYPE
-- Reverse mappable trap
    ENTERPRISE hdsl2ShdslMIB
    VARIABLES {
        hdsl2ShdslSpanConfNumRepeaters }
--  Status
--    mandatory
    DESCRIPTION
        "This notification indicates that a mismatch has been detected
        between the number of repeater/regenerator units configured
        for an HDSL2/SHDSL line via the hdsl2ShdslSpanConfNumRepeaters
        object and the actual number of repeater/regenerator units
        discovered via the EOC."
    ::= 8

hdsl2ShdslLoopbackFailure TRAP-TYPE
-- Reverse mappable trap
    ENTERPRISE hdsl2ShdslMIB
    VARIABLES {
        hdsl2ShdslMaintLoopbackConfig }
--  Status
--    mandatory
    DESCRIPTION
        "This notification indicates that an endpoint maintenance
        loopback command failed for an HDSL2/SHDSL segment."
    ::= 9

hdsl2ShdslpowerBackoff TRAP-TYPE
-- Reverse mappable trap
    ENTERPRISE hdsl2ShdslMIB
    VARIABLES {
        hdsl2ShdslEndpointCurrStatus }
--  Status
--    mandatory
    DESCRIPTION
        "This notification indicates that the bit setting for
        powerBackoff in the hdsl2ShdslEndpointCurrStatus object for
        this endpoint has changed."
    ::= 10

hdsl2ShdsldeviceFault TRAP-TYPE
-- Reverse mappable trap
    ENTERPRISE hdsl2ShdslMIB
    VARIABLES {
        hdsl2ShdslEndpointCurrStatus }
--  Status
--    mandatory
    DESCRIPTION
        "This notification indicates that the bit setting for
        deviceFault in the hdsl2ShdslEndpointCurrStatus object for
        this endpoint has changed."
    ::= 11

hdsl2ShdsldcContinuityFault TRAP-TYPE
-- Reverse mappable trap
    ENTERPRISE hdsl2ShdslMIB
    VARIABLES {
        hdsl2ShdslEndpointCurrStatus }
--  Status
--    mandatory
    DESCRIPTION
        "This notification indicates that the bit setting for
        dcContinuityFault in the hdsl2ShdslEndpointCurrStatus object
        for this endpoint has changed."
    ::= 12

hdsl2ShdslconfigInitFailure TRAP-TYPE
-- Reverse mappable trap
    ENTERPRISE hdsl2ShdslMIB
    VARIABLES {
        hdsl2ShdslEndpointCurrStatus }
--  Status
--    mandatory
    DESCRIPTION
        "This notification indicates that the bit setting for
        configInitFailure in the hdsl2ShdslEndpointCurrStatus object
        for this endpoint has changed."
    ::= 13

hdsl2ShdslprotocolInitFailure TRAP-TYPE
-- Reverse mappable trap
    ENTERPRISE hdsl2ShdslMIB
    VARIABLES {
        hdsl2ShdslEndpointCurrStatus }
--  Status
--    mandatory
    DESCRIPTION
        "This notification indicates that the bit setting for
        protocolInitFailure in the hdsl2ShdslEndpointCurrStatus
        object for this endpoint has changed."
    ::= 14

hdsl2ShdslnoNeighborPresent TRAP-TYPE
-- Reverse mappable trap
    ENTERPRISE hdsl2ShdslMIB
    VARIABLES {
        hdsl2ShdslEndpointCurrStatus }
--  Status
--    mandatory
    DESCRIPTION
        "This notification indicates that the bit setting for
        noNeighborPresent in the hdsl2ShdslEndpointCurrStatus object
        for this endpoint has changed."
    ::= 15

hdsl2ShdslLocalPowerLoss TRAP-TYPE
-- Reverse mappable trap
    ENTERPRISE hdsl2ShdslMIB
    VARIABLES {
        hdsl2ShdslInvVendorID }
--  Status
--    mandatory
    DESCRIPTION
        "This notification indicates impending unit failure due to
        loss of local power (last gasp)."
    ::= 16

hdsl2ShdslSpanConfGroup OBJECT IDENTIFIER ::= { hdsl2ShdslGroups 1 }
-- OBJECT-GROUP
--  Status
--    mandatory
--  Descr
--    This group supports objects for configuring span-related
--    parameters for HDSL2/SHDSL lines.
--  objects
--    hdsl2ShdslSpanConfNumRepeaters, hdsl2ShdslSpanConfProfile, 
--    hdsl2ShdslSpanConfAlarmProfile

hdsl2ShdslSpanStatusGroup OBJECT IDENTIFIER ::= { hdsl2ShdslGroups 2 }
-- OBJECT-GROUP
--  Status
--    mandatory
--  Descr
--    This group supports objects for retrieving span-related
--    status for HDSL2/SHDSL lines.
--  objects
--    hdsl2ShdslStatusNumAvailRepeaters

hdsl2ShdslInventoryShdslGroup OBJECT IDENTIFIER ::= { hdsl2ShdslGroups 3 }
-- OBJECT-GROUP
--  Status
--    mandatory
--  Descr
--    This group supports objects for retrieving SHDSL-specific
--    inventory information.
--  objects
--    hdsl2ShdslInvTransmissionModeCapability

hdsl2ShdslSpanShdslStatusGroup OBJECT IDENTIFIER ::= { hdsl2ShdslGroups 4 }
-- OBJECT-GROUP
--  Status
--    mandatory
--  Descr
--    This group supports objects for retrieving SHDSL-specific
--    span-related status.
--  objects
--    hdsl2ShdslStatusMaxAttainableLineRate, 
--    hdsl2ShdslStatusActualLineRate, 
--    hdsl2ShdslStatusTransmissionModeCurrent

hdsl2ShdslInventoryGroup OBJECT IDENTIFIER ::= { hdsl2ShdslGroups 5 }
-- OBJECT-GROUP
--  Status
--    mandatory
--  Descr
--    This group supports objects that provide unit inventory
--    information about the units in HDSL2/SHDSL lines.
--  objects
--    hdsl2ShdslInvVendorID, hdsl2ShdslInvVendorModelNumber, 
--    hdsl2ShdslInvVendorSerialNumber, 
--    hdsl2ShdslInvVendorEOCSoftwareVersion, 
--    hdsl2ShdslInvStandardVersion, hdsl2ShdslInvVendorListNumber, 
--    hdsl2ShdslInvVendorIssueNumber, 
--    hdsl2ShdslInvVendorSoftwareVersion, 
--    hdsl2ShdslInvEquipmentCode, hdsl2ShdslInvVendorOther

hdsl2ShdslEndpointConfGroup OBJECT IDENTIFIER ::= { hdsl2ShdslGroups 6 }
-- OBJECT-GROUP
--  Status
--    mandatory
--  Descr
--    This group supports objects for configuring parameters for
--    segment endpoints in HDSL2/SHDSL lines.
--  objects
--    hdsl2ShdslEndpointCurrAtn

hdsl2ShdslEndpointCurrGroup OBJECT IDENTIFIER ::= { hdsl2ShdslGroups 7 }
-- OBJECT-GROUP
--  Status
--    mandatory
--  Descr
--    This group supports objects that provide current status and
--    performance measurements relating to segment endpoints in
--    HDSL2/SHDSL lines.
--  objects
--    hdsl2ShdslEndpointCurrAtn, hdsl2ShdslEndpointCurrSnrMgn, 
--    hdsl2ShdslEndpointCurrStatus, hdsl2ShdslEndpointES, 
--    hdsl2ShdslEndpointSES, hdsl2ShdslEndpointCRCanomalies, 
--    hdsl2ShdslEndpointLOSWS, hdsl2ShdslEndpointUAS, 
--    hdsl2ShdslEndpointCurr15MinTimeElapsed, 
--    hdsl2ShdslEndpointCurr15MinES, hdsl2ShdslEndpointCurr15MinSES, 
--    hdsl2ShdslEndpointCurr15MinCRCanomalies, 
--    hdsl2ShdslEndpointCurr15MinLOSWS, 
--    hdsl2ShdslEndpointCurr15MinUAS, 
--    hdsl2ShdslEndpointCurr1DayTimeElapsed, 
--    hdsl2ShdslEndpointCurr1DayES, hdsl2ShdslEndpointCurr1DaySES, 
--    hdsl2ShdslEndpointCurr1DayCRCanomalies, 
--    hdsl2ShdslEndpointCurr1DayLOSWS, 
--    hdsl2ShdslEndpointCurr1DayUAS

hdsl2Shdsl15MinIntervalGroup OBJECT IDENTIFIER ::= { hdsl2ShdslGroups 8 }
-- OBJECT-GROUP
--  Status
--    mandatory
--  Descr
--    This group supports objects that maintain historic
--    performance measurements relating to segment endpoints in
--    HDSL2/SHDSL lines in 15-minute intervals.
--  objects
--    hdsl2Shdsl15MinIntervalES, hdsl2Shdsl15MinIntervalSES, 
--    hdsl2Shdsl15MinIntervalCRCanomalies, 
--    hdsl2Shdsl15MinIntervalLOSWS, hdsl2Shdsl15MinIntervalUAS

hdsl2Shdsl1DayIntervalGroup OBJECT IDENTIFIER ::= { hdsl2ShdslGroups 9 }
-- OBJECT-GROUP
--  Status
--    mandatory
--  Descr
--    This group supports objects that maintain historic
--    performance measurements relating to segment endpoints in
--    HDSL2/SHDSL lines in 1-day intervals.
--  objects
--    hdsl2Shdsl1DayIntervalMoniSecs, hdsl2Shdsl1DayIntervalES, 
--    hdsl2Shdsl1DayIntervalSES, hdsl2Shdsl1DayIntervalCRCanomalies, 
--    hdsl2Shdsl1DayIntervalLOSWS, hdsl2Shdsl1DayIntervalUAS

hdsl2ShdslMaintenanceGroup OBJECT IDENTIFIER ::= { hdsl2ShdslGroups 10 }
-- OBJECT-GROUP
--  Status
--    mandatory
--  Descr
--    This group supports objects that provide support for
--    maintenance actions for HDSL2/SHDSL lines.
--  objects
--    hdsl2ShdslMaintLoopbackConfig, hdsl2ShdslMaintTipRingReversal, 
--    hdsl2ShdslMaintPowerBackOff, hdsl2ShdslMaintSoftRestart, 
--    hdsl2ShdslMaintLoopbackTimeout, 
--    hdsl2ShdslMaintUnitPowerSource

hdsl2ShdslEndpointAlarmConfGroup OBJECT IDENTIFIER ::= { hdsl2ShdslGroups 11 }
-- OBJECT-GROUP
--  Status
--    mandatory
--  Descr
--    This group supports objects that allow configuration of alarm
--    thresholds for various performance parameters for HDSL2/SHDSL
--    lines.
--  objects
--    hdsl2ShdslEndpointAlarmConfProfile, 
--    hdsl2ShdslEndpointThreshLoopAttenuation, 
--    hdsl2ShdslEndpointThreshSNRMargin, hdsl2ShdslEndpointThreshES, 
--    hdsl2ShdslEndpointThreshSES, 
--    hdsl2ShdslEndpointThreshCRCanomalies, 
--    hdsl2ShdslEndpointThreshLOSWS, hdsl2ShdslEndpointThreshUAS, 
--    hdsl2ShdslEndpointAlarmConfProfileRowStatus

hdsl2ShdslSpanConfProfileGroup OBJECT IDENTIFIER ::= { hdsl2ShdslGroups 13 }
-- OBJECT-GROUP
--  Status
--    mandatory
--  Descr
--    This group supports objects that constitute configuration
--    profiles for configuring span-related parameters in SHDSL
--    lines.
--  objects
--    hdsl2ShdslSpanConfWireInterface, 
--    hdsl2ShdslSpanConfMinLineRate, hdsl2ShdslSpanConfMaxLineRate, 
--    hdsl2ShdslSpanConfPSD, hdsl2ShdslSpanConfTransmissionMode, 
--    hdsl2ShdslSpanConfRemoteEnabled, 
--    hdsl2ShdslSpanConfPowerFeeding, 
--    hdsl2ShdslSpanConfCurrCondTargetMarginDown, 
--    hdsl2ShdslSpanConfWorstCaseTargetMarginDown, 
--    hdsl2ShdslSpanConfCurrCondTargetMarginUp, 
--    hdsl2ShdslSpanConfWorstCaseTargetMarginUp, 
--    hdsl2ShdslSpanConfUsedTargetMargins, 
--    hdsl2ShdslSpanConfReferenceClock, 
--    hdsl2ShdslSpanConfLineProbeEnable, 
--    hdsl2ShdslSpanConfProfileRowStatus

hdsl2ShdslWirePairGroup OBJECT IDENTIFIER ::= { hdsl2ShdslGroups 14 }
-- OBJECT-GROUP
--  Status
--    mandatory
--  Descr
--    This group supports objects that provide the status
--    of SHDSL-specific wire pairs.
--  objects
--    hdsl2ShdslEndpointCurrTipRingReversal, 
--    hdsl2ShdslEndpointCurrActivationState

hdsl2ShdslPayloadRateGroup OBJECT IDENTIFIER ::= { hdsl2ShdslGroups 15 }
-- OBJECT-GROUP
--  Status
--    mandatory
--  Descr
--    This group supports objects for retrieving payload rates
--    that exclude any framing overhead.
--  objects
--    hdsl2ShdslStatusMaxAttainablePayloadRate, 
--    hdsl2ShdslStatusActualPayloadRate

hdsl2ShdslNotificationGroup OBJECT IDENTIFIER ::= { hdsl2ShdslGroups 12 }
-- NOTIFICATION-GROUP
--  Status
--    mandatory
--  Descr
--    This group supports notifications of significant conditions
--    associated with HDSL2/SHDSL lines.
--  notifications
--    hdsl2ShdslLoopAttenCrossing, hdsl2ShdslSNRMarginCrossing, 
--    hdsl2ShdslPerfESThresh, hdsl2ShdslPerfSESThresh, 
--    hdsl2ShdslPerfCRCanomaliesThresh, hdsl2ShdslPerfLOSWSThresh, 
--    hdsl2ShdslPerfUASThresh, hdsl2ShdslSpanInvalidNumRepeaters, 
--    hdsl2ShdslLoopbackFailure, hdsl2ShdslpowerBackoff, 
--    hdsl2ShdsldeviceFault, hdsl2ShdsldcContinuityFault, 
--    hdsl2ShdslconfigInitFailure, hdsl2ShdslprotocolInitFailure, 
--    hdsl2ShdslnoNeighborPresent, hdsl2ShdslLocalPowerLoss

hdsl2ShdslLineMibCompliance OBJECT IDENTIFIER ::= { hdsl2ShdslCompliances 1 }
-- MODULE-COMPLIANCE
--  Status
--    deprecated
--  Descr
--    The compliance statement for SNMP entities that implement
--    HDSL2 and SHDSL.  The version of SHDSL supported in this
--    compliance statement is g.shdsl.
--    
--    **** This compliance statement is deprecated. ****
--  Module
--    >>current<<
--   MandGroup
--    hdsl2ShdslSpanConfGroup
--   MandGroup
--    hdsl2ShdslSpanStatusGroup
--   MandGroup
--    hdsl2ShdslInventoryGroup
--   MandGroup
--    hdsl2ShdslEndpointConfGroup
--   MandGroup
--    hdsl2ShdslEndpointCurrGroup
--   MandGroup
--    hdsl2Shdsl15MinIntervalGroup
--   MandGroup
--    hdsl2Shdsl1DayIntervalGroup
--   MandGroup
--    hdsl2ShdslMaintenanceGroup
--   MandGroup
--    hdsl2ShdslEndpointAlarmConfGroup
--   MandGroup
--    hdsl2ShdslNotificationGroup
--   OptGroup
--    hdsl2ShdslInventoryShdslGroup
--   OptGroup
--    hdsl2ShdslSpanShdslStatusGroup
--   OptGroup
--    hdsl2ShdslSpanConfProfileGroup
--   ObjVar
--    hdsl2ShdslSpanConfWireInterface
--   ObjVar
--    hdsl2ShdslStatusMaxAttainableLineRate
--   ObjVar
--    hdsl2ShdslStatusActualLineRate
--   ObjVar
--    hdsl2ShdslSpanConfMinLineRate
--   ObjVar
--    hdsl2ShdslSpanConfMaxLineRate

hdsl2GshdslbisLineMibCompliance OBJECT IDENTIFIER ::= { hdsl2ShdslCompliances 2 }
-- MODULE-COMPLIANCE
--  Status
--    mandatory
--  Descr
--    The compliance statement for SNMP entities that implement
--    HDSL2 and SHDSL.  The version of SHDSL supported in this
--    compliance statement is g.shdsl.bis.
--  Module
--    >>current<<
--   MandGroup
--    hdsl2ShdslSpanConfGroup
--   MandGroup
--    hdsl2ShdslSpanStatusGroup
--   MandGroup
--    hdsl2ShdslInventoryGroup
--   MandGroup
--    hdsl2ShdslEndpointConfGroup
--   MandGroup
--    hdsl2ShdslEndpointCurrGroup
--   MandGroup
--    hdsl2Shdsl15MinIntervalGroup
--   MandGroup
--    hdsl2Shdsl1DayIntervalGroup
--   MandGroup
--    hdsl2ShdslMaintenanceGroup
--   MandGroup
--    hdsl2ShdslEndpointAlarmConfGroup
--   MandGroup
--    hdsl2ShdslNotificationGroup
--   OptGroup
--    hdsl2ShdslInventoryShdslGroup
--   OptGroup
--    hdsl2ShdslSpanShdslStatusGroup
--   OptGroup
--    hdsl2ShdslSpanConfProfileGroup
--   OptGroup
--    hdsl2ShdslWirePairGroup
--   OptGroup
--    hdsl2ShdslPayloadRateGroup


END
