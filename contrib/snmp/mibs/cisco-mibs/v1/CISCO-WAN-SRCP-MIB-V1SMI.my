-- MIB file created 25-Mar-2004 13:44:20, by
--   SMICng version 2.2.11-beta(PRO)(Solaris), January 20, 2001. Enterprise key cisco.com

CISCO-WAN-SRCP-MIB DEFINITIONS ::= BEGIN

-- From file: "CISCO-WAN-SRCP-MIB.my"
-- Compile options "4 7 F H N W 03 06 0B 0G 0N 0T"

IMPORTS
    DisplayString
            FROM SNMPv2-TC-v1
    ciscoWan
            FROM CISCOWAN-SMI
    mgcRedundancyGrpNum
            FROM CISCO-WAN-MGC-REDUN-MIB
    Counter, IpAddress
            FROM RFC1155-SMI
    OBJECT-TYPE
            FROM RFC-1212;

ciscoWanSrcpMIB OBJECT IDENTIFIER ::= { ciscoWan 11 }
-- MODULE-IDENTITY
--  LastUpdated
--    200401300000Z
--  OrgName
--    Cisco Systems, Inc.
--  ContactInfo
--           Cisco Systems 
--            Customer Service 
--    
--        Postal: 170 W Tasman Drive 
--                San Jose, CA 95134 
--                USA 
--    
--                Tel: +1 800 553-NETS 
--    
--        E-mail: cs-wanatm@cisco.com
--  Descr
--    The MIB module for managing SRCP(Simple Resource 
--     Coordination Protocol) implementations. SRCP 
--     is a resource coordination protocol used 
--     between a MGC(Media Gateway Controller) and 
--     a MG(Media Gateway). SRCP MIB is applicable 
--     to both controllers (SRCP clients) and gateways 
--     (SRCP servers). 
--      
--     MGMIB: This is the short name used for  
--            CISCO-WAN-MG-MIB in this MIB.
--  RevDate
--    200401300000Z
--  RevDescr
--    Update descriptions in the MIB. 
--  RevDate
--    200012260000Z
--  RevDescr
--    Changed description of srcpRequestMaxTimeout which 
--     had a reference to an object srcpRequestMinTimeout 
--     which should actually be srcpRequestTimeout. 
--  RevDate
--    200008310000Z
--  RevDescr
--    moved srcpRequestMinTimeout, srcpRequestRetries 
--     and srcpRequestMaxTimeout objects to new subgroup 
--     srcpAdminRetyObject         
--  RevDate
--    200007210000Z
--  RevDescr
--    Added following new objects for exponential retry 
--     srcpRequestTimeOut , srcpRequestRetries,  
--     srcpRequestMaxTimeout 
--  RevDate
--    200005280000Z
--  RevDescr
--    Moved some objects from the srcpPeerTable to the  
--     srcpPeerGrpTable for the implementation of the  
--     MGC Redundancy Feature. 
--  RevDate
--    200005240000Z
--  RevDescr
--    added srcpRequestMinTimeout, srcpRequestRetries and  
--     srcpRequestMaxTimeout objects 
--  RevDate
--    199911230000Z
--  RevDescr
--    Added DEFVAL clause for srcpPeerHeartbeatInterval,  
--     srcpPeerMaxPduSize. 
--  RevDate
--    199911010000Z
--  RevDescr
--    Changed the description of srcpPeerHeartbeatInterval 
--     to say that value less than 100 (except 0) is not 
--     allowed. 
--  RevDate
--    199910210000Z
--  RevDescr
--    Changed the description of TimeSinceHeartbeat as it  
--     was saying return -1 if in locked state or unassociated  
--     state. But -1 is not a valid value as per the specified  
--     range. Changed it to return 0. 
--  RevDate
--    199906230000Z
--  RevDescr
--    Added definition for srcpStatsPeerName & changed  
--     srcpPeerName to read-only. 
--  RevDate
--    199906070000Z
--  RevDescr
--    Added DEFVAL clause for srcpPortNumber and  
--     srcpPeerPortNumber 
--  RevDate
--    199904290000Z
--  RevDescr
--    Initial version of the MIB. 

srcpObjects     OBJECT IDENTIFIER ::= { ciscoWanSrcpMIB 1 }
srcpAdminObjects OBJECT IDENTIFIER ::= { srcpObjects 1 }
srcpStatsObjects OBJECT IDENTIFIER ::= { srcpObjects 2 }
srcpAdminRetyObjects OBJECT IDENTIFIER ::= { srcpObjects 3 }
srcpMIBConformance OBJECT IDENTIFIER ::= { ciscoWanSrcpMIB 3 }
srcpMIBCompliances OBJECT IDENTIFIER ::= { srcpMIBConformance 1 }
srcpMIBGroups   OBJECT IDENTIFIER ::= { srcpMIBConformance 2 }

srcpVersion OBJECT-TYPE
    SYNTAX DisplayString(SIZE(1..64))
--    Rsyntax OCTET STRING(SIZE(1..64))
    ACCESS read-only
    STATUS mandatory
    DESCRIPTION
        "The name of the SRCP protocol version for 
         exmaple SRCP 1.0.2.  If MGMIB is supported, 
         this name corresponds to mgProtocolName 
         (defined in CISCO-WAN-MG-MIB MIB) in an 
         entry to mgSupportedProtocolTable. "
    ::= { srcpAdminObjects 1 }

srcpPortNumber OBJECT-TYPE
    SYNTAX INTEGER(1025..65535)
    ACCESS read-write
    STATUS mandatory
    DESCRIPTION
        "This object is used to configure the UDP port used  
            for SRCP on the system (local UDP port). It is 
            configurable only if the system is in a locked or 
            disabled state (i.e If MGMIB Is supported, 
            mgAdministrativeState(defined in CISCO-WAN-MG-MIB MIB) 
            should be 'locked' before the UDP port can be configured). 
           "
    DEFVAL { 2428 }
    ::= { srcpAdminObjects 2 }

srcpPeerTable OBJECT-TYPE
    SYNTAX SEQUENCE OF SrcpPeerEntry
    ACCESS not-accessible
    STATUS mandatory
    DESCRIPTION
        "This is a table which is used to provision peer-specific 
         SRCP configuration and administration information.  
         Each table entry corresponds to an SRCP peer as  
         identified by its domain name(srcpPeerName). "
    ::= { srcpAdminObjects 3 }

srcpPeerEntry OBJECT-TYPE
    SYNTAX SrcpPeerEntry
    ACCESS not-accessible
    STATUS mandatory
    DESCRIPTION
        "Represents an individual table entry in srcpPeerTable. 
        Each row corresponds to an SRCP peer and is identified 
        by its domain name (srcpPeerName).  
        
        Entries in this table are implicitly created by the agent.  
        
        If the agent supports MGMIB, this occurs as follows: 
        An entry shall be created when an entry is created in the  
        mgcRedundancyGrpProtocolTable(defined in 
        CISCO-WAN-MGC-REDUN-MIB MIB) and when 
        mgProtocolNumber (defined in CISCO-WAN-MG-MIB MIB) 
        refers to SRCP as supported protocol. An entry will 
        be made for all MGC(Media Gateway Controller) in 
        that MGC Redundancy Group. Accordingly, an entry 
        shall be deleted if the corresponding entry in 
        the mgcRedundancyGrpProtocolTable is deleted. 
        
        If the agent does not support MGMIB, entry creation 
        might occur when the first SRCP communication with 
        an IP address/domain  name occurs. 
        
        if MGC Redundacy feature is supported the following objects: 
        srcpPeerHeartbeatInterval, srcpPeerTimeSinceHeartbeat 
        rcpPeerMaxPduSize are not meaningful here. These objects 
        are defined per MGC Redundancy Group rather than per MGC. "
    INDEX { srcpPeerId }
    ::= { srcpPeerTable 1 }

SrcpPeerEntry ::= SEQUENCE {
    srcpPeerId INTEGER,
    srcpPeerName DisplayString,
    srcpPeerPortNumber INTEGER,
    srcpPeerHeartbeatInterval INTEGER,
    srcpPeerTimeSinceHeartbeat INTEGER,
    srcpPeerMaxPduSize INTEGER
    }

srcpPeerId OBJECT-TYPE
    SYNTAX INTEGER(1..65535)
    ACCESS not-accessible
    STATUS mandatory
    DESCRIPTION
        "This object identifies the SRCP peer and serves 
         as index to this table. If MGMIB is supported,  
         this is the same as the mgcNumber(defined 
         in CISCO-WAN-MG-MIB MIB) from the mgcTable. "
    ::= { srcpPeerEntry 1 }

srcpPeerName OBJECT-TYPE
    SYNTAX DisplayString(SIZE(1..64))
--    Rsyntax OCTET STRING(SIZE(1..64))
    ACCESS read-only
    STATUS mandatory
    DESCRIPTION
        "This object identifies the name of the SRCP peer.  
         If MGMIB is supported, this is the same as the  
         mgcName from the mgcTable.  "
    ::= { srcpPeerEntry 2 }

srcpPeerPortNumber OBJECT-TYPE
    SYNTAX INTEGER(1025..65535)
    ACCESS read-write
    STATUS mandatory
    DESCRIPTION
        "This object is used to configure the UDP port of  
        the SRCP peer. "
    DEFVAL { 2428 }
    ::= { srcpPeerEntry 3 }

srcpPeerHeartbeatInterval OBJECT-TYPE
    SYNTAX INTEGER(0..65535)
--  Units
--    milliseconds
    ACCESS read-write
    STATUS deprecated
    DESCRIPTION
        "This object is used to configure the length of the  
         heartbeat interval, in milliseconds. The heartbeat 
         interval indicate when the GW(Gateway) is expected to 
         receive a heartbeat from a specific peer or MGC group. 
         If value is 0, heartbeat for this peer is not 
         monitored.  The heartbeat interval less than 100 is 
         not allowed (except 0). 
        
         If MGC Redundancy is supported, this object is not  
         effective. Instead, the user should use 
         srcpPeerGrpHeartbeatInterval.  "
    DEFVAL { 0 }
    ::= { srcpPeerEntry 4 }

srcpPeerTimeSinceHeartbeat OBJECT-TYPE
    SYNTAX INTEGER(0..2147483647)
--  Units
--    milliseconds
    ACCESS read-only
    STATUS deprecated
    DESCRIPTION
        "The time since the last heartbeat was received, in 
         milliseconds.  This represents the difference between 
         the current time and the last time an SRCP command was 
         received.  
        
         A value of 0 shall be returned if the heartbeat is not 
         monitored.  Even if the heartbeat is monitored, a value 
         of 0 shall be returned if any of the following is true: 
        
         i)  The system is locked or disabled (as indicated by  
             mgAdministrativeState).  
         ii) The srcpPeer is unassociated as indicated by 
             mgcAssociationState(defined in CISCO-WAN-MG-MIB MIB). 
        
         If MGC Redundancy is supported, this object is not 
         effective. Instead, the user should use 
         srcpPeerGrpTimeSinceHeartbeat. "
    ::= { srcpPeerEntry 5 }

srcpPeerMaxPduSize OBJECT-TYPE
    SYNTAX INTEGER(4095..65535)
--  Units
--    octets
    ACCESS read-write
    STATUS deprecated
    DESCRIPTION
        "This object is used to configure the maximum UDP 
         PDU(Protocol Data Unit) size, in octets, that may 
         be used for SRCP communications with the peer.  
        
         This value may not be configurable for all agents. 
        
         If MGC Redundancy is supported, this object is not 
         effective. Instead, the user should use 
         srcpPeerGrpMaxPduSize. "
    DEFVAL { 16384 }
    ::= { srcpPeerEntry 6 }

srcpPeerGrpParamTable OBJECT-TYPE
    SYNTAX SEQUENCE OF SrcpPeerGrpParamEntry
    ACCESS not-accessible
    STATUS mandatory
    DESCRIPTION
        "This table is used to provision SRCP parameters for 
         an MGC Redundancy group. MGCs can be configured as part 
         of MGC Redundancy groups. This feature allows for 
         redundant call agents. 
        
         Each table entry corresponds to an SRCP peer entry that is 
         identified by the MGC Redundancy group number. "
    ::= { srcpAdminObjects 4 }

srcpPeerGrpParamEntry OBJECT-TYPE
    SYNTAX SrcpPeerGrpParamEntry
    ACCESS not-accessible
    STATUS mandatory
    DESCRIPTION
        "Represents an individual table entry in the 
         srcpPeerGrpParamTable. Each row corresponds to  
         an MGC Redundancy Group and is identified by the 
         MGC Redundancy Group Number. 
              
         Entries are implicitly created when the SRCP protocol  
         is added for an MGC Redundancy Group. The entry will 
         be removed if the SRCP protocol is removed for an MGC  
         Redundancy Group. "
    INDEX { mgcRedundancyGrpNum }
    ::= { srcpPeerGrpParamTable 1 }

SrcpPeerGrpParamEntry ::= SEQUENCE {
    srcpPeerGrpHeartbeatInterval INTEGER,
    srcpPeerGrpTimeSinceHeartbeat INTEGER,
    srcpPeerGrpMaxPduSize INTEGER
    }

srcpPeerGrpHeartbeatInterval OBJECT-TYPE
    SYNTAX INTEGER(0..65535)
--  Units
--    milliseconds
    ACCESS read-write
    STATUS mandatory
    DESCRIPTION
        "This object is used to configure the length of the 
         heartbeat interval, in milliseconds. If 0, heartbeat  
         for this peer Group is not monitored. The heartbeat 
         interval less than 100 is not allowed (except 0). "
    DEFVAL { 0 }
    ::= { srcpPeerGrpParamEntry 1 }

srcpPeerGrpTimeSinceHeartbeat OBJECT-TYPE
    SYNTAX INTEGER(0..2147483647)
--  Units
--    milliseconds
    ACCESS read-only
    STATUS mandatory
    DESCRIPTION
        "The time since the last heartbeat was received, 
        in milliseconds. This represents the difference 
        between the current time and the last time an SRCP  
        command was received. 
        
        A value of 0 shall be returned if the heartbeat is not 
        monitored.  Even if the heartbeat is monitored, a value  
        of 0 shall be returned if any of the following is true: 
        
        i)  The system is locked or disabled (as indicated by 
            mgAdministrativeState). 
        ii) The stateChangeNtfy flag is disabled for the srcpPeer 
            Group (as indicated by mgcRedundancyGrpStateChangeNtfy 
            of CISCO-WAN-MGC-REDUN-MIB). "
    DEFVAL { 0 }
    ::= { srcpPeerGrpParamEntry 2 }

srcpPeerGrpMaxPduSize OBJECT-TYPE
    SYNTAX INTEGER(4095..65535)
--  Units
--    octets
    ACCESS read-write
    STATUS mandatory
    DESCRIPTION
        "This object is used to configure the maximum UDP PDU size, 
         in octets, that may be used for SRCP communications with  
         the peer. This value may not be configurable for all agents. "
    DEFVAL { 16384 }
    ::= { srcpPeerGrpParamEntry 3 }

srcpRequestTimeOut OBJECT-TYPE
    SYNTAX INTEGER(1..10000)
--  Units
--    milliseconds
    ACCESS read-write
    STATUS mandatory
    DESCRIPTION
        "This object specifies the minimum timeout value. 
        
         This value along with srcpRequestMaxTimeout and 
         srcpRequestRetries is used to determine the exponential 
         retry interval for retransmitting unacknowledged SRCP 
         messages. 
        
         It is the responsibility of the requesting entity to 
         provide suitable timeouts for all outstanding commands, 
         and to retry commands when timeouts exceeded. 
        
         The default value of this object is 500 milliseconds. 
        
         When the value of this object changes srcpAdminObjects 
         group changed trap will be sent as specify by 
         vismConfigChangeTypeBitMap in CISCO-VISM-MODULE-MIB. "
    ::= { srcpAdminRetyObjects 1 }

srcpRequestRetries OBJECT-TYPE
    SYNTAX INTEGER(0..10)
    ACCESS read-write
    STATUS mandatory
    DESCRIPTION
        "This object specifies the number of retries for a SRCP  
         request that exceeds timeout. It is the responsibility  
         of the requesting entity to provide suitable timeouts for  
         all outstanding commands, and to retry when times out. 
        
         The default value of this object is 3. 
        
         When the value of this object changes srcpAdminObjects 
         group changed trap will be sent as specify by 
         vismConfigChangeTypeBitMap in CISCO-VISM-MODULE-MIB. "
    ::= { srcpAdminRetyObjects 2 }

srcpRequestMaxTimeout OBJECT-TYPE
    SYNTAX INTEGER(1..10000)
--  Units
--    milliseconds
    ACCESS read-write
    STATUS mandatory
    DESCRIPTION
        "This object specifies the maximum timeout value. 
        
         This timer value is used along with srcpRequestTimeOut and 
         srcpRequestRetries to determine the exponential retry 
         interval for retransmitting unacknowledged SRCP messages. 
        
         The value of this timer has to be greater than or equal to 
         srcpRequestTimeOut. 
        
         The default value of this object is 500 milliseconds. 
        
         When the value of this object changes srcpAdminObjects 
         group changed trap will be sent as specify by 
         vismConfigChangeTypeBitMap in CISCO-VISM-MODULE-MIB. "
    ::= { srcpAdminRetyObjects 3 }

srcpPeerStatsTable OBJECT-TYPE
    SYNTAX SEQUENCE OF SrcpPeerStatsEntry
    ACCESS not-accessible
    STATUS mandatory
    DESCRIPTION
        "This table contains SRCP statistics information since 
         reset. SRCP statistics are kept in this table, with 
         each table entry containing the statistics of SRCP 
         messages that communicated with a peer at a specific 
         IP address of the peer. 
        
         It differs from the SRCP peer table which maintains 
         information on a per call agent basis as identified 
         by their domain names. "
    ::= { srcpStatsObjects 1 }

srcpPeerStatsEntry OBJECT-TYPE
    SYNTAX SrcpPeerStatsEntry
    ACCESS not-accessible
    STATUS mandatory
    DESCRIPTION
        "The row of the srcpPeerStatsTable contains information about  
         SRCP message statistics per IP address of the MGC. 
        
         An entry is implicitly created and deleted by the agent.  
        
         There can be two cases: 
        
         1. Case of Internal address resolution : In this case IP 
            addresses of all SRCP peers are resolved internally. 
            If the agent supports the MGMIB, the following 
            referential integrity rules apply: 
        
         When an entry is added to mgcResolutionTable defined in 
         CISCO-WAN-MG-MIB with a specific IP address, an entry  
         is created in this srcpPeerStatsTable for that IP address.  
         When an entry is deleted from mgcResolutionTable, 
         the row with the corresponding IP address in this table 
         will be deleted. 
             
         2. Case of External address resolution : If there is at 
            least one Call agent whose IP address is resolved 
            externally, an entry is created whenever SRCP 
            communication occurs with a new IP address. Table 
            entries are never deleted, but must be  
            nonpersistent in agent implementations, i.e. must be 
            purged in case of a system shutdown/restart. "
    INDEX { srcpStatsPeerIpAddress }
    ::= { srcpPeerStatsTable 1 }

SrcpPeerStatsEntry ::= SEQUENCE {
    srcpStatsPeerIpAddress IpAddress,
    srcpStatsPeerName DisplayString,
    packetsDiscardedCnts Counter,
    augwCnts Counter,
    augwFailCnts Counter,
    aulnCnts Counter,
    aulnFailCnts Counter,
    ntfyCnts Counter,
    ntfyFailCnts Counter,
    rqntCnts Counter,
    rqntFailCnts Counter
    }

srcpStatsPeerIpAddress OBJECT-TYPE
    SYNTAX IpAddress
    ACCESS not-accessible
    STATUS mandatory
    DESCRIPTION
        "This object specifies the IP address of the   
         SRCP peer and serves as index to the table. "
    ::= { srcpPeerStatsEntry 1 }

srcpStatsPeerName OBJECT-TYPE
    SYNTAX DisplayString(SIZE(1..64))
--    Rsyntax OCTET STRING(SIZE(1..64))
    ACCESS read-only
    STATUS mandatory
    DESCRIPTION
        "Denotes the name of the SRCP peer. This is the 
         same as the mgcName from the mgcTable. It is provided 
         here as a read-only parameter as a convinience feature. "
    ::= { srcpPeerStatsEntry 2 }

packetsDiscardedCnts OBJECT-TYPE
    SYNTAX Counter
    ACCESS read-only
    STATUS mandatory
    DESCRIPTION
        "The number of packets that were received and discarded.  
         The packets may get discarded because of indecipherable  
         PDUs like bad protocol version, bad command verb etc, or  
         because of unknown transaction IDs (in case of SRCP clients). "
    ::= { srcpPeerStatsEntry 3 }

augwCnts OBJECT-TYPE
    SYNTAX Counter
    ACCESS read-only
    STATUS mandatory
    DESCRIPTION
        "The total number of AUGW(Audit Gateway) commands received 
         from the peer on this IP address."
    ::= { srcpPeerStatsEntry 4 }

aulnCnts OBJECT-TYPE
    SYNTAX Counter
    ACCESS read-only
    STATUS mandatory
    DESCRIPTION
        "The total number of AULN(Audit Line) commands received from  
         or sent to the peer on this IP address. "
    ::= { srcpPeerStatsEntry 5 }

rqntCnts OBJECT-TYPE
    SYNTAX Counter
    ACCESS read-only
    STATUS mandatory
    DESCRIPTION
        "The total number of RQNT(Notification Request) commands 
         received from or sent to the peer on this IP address. "
    ::= { srcpPeerStatsEntry 6 }

ntfyCnts OBJECT-TYPE
    SYNTAX Counter
    ACCESS read-only
    STATUS mandatory
    DESCRIPTION
        "The total number of NTFY(Notify) commands received from  
         or sent to the peer on this IP address. "
    ::= { srcpPeerStatsEntry 7 }

augwFailCnts OBJECT-TYPE
    SYNTAX Counter
    ACCESS read-only
    STATUS mandatory
    DESCRIPTION
        "For MG : The total number of AUGW commands  
         received that were responded to with a failure  
         return code. 
        
         For MGC : The total number of AUGW commands sent which 
         were timed out without a response or for which a response 
         with failure return code was received. "
    ::= { srcpPeerStatsEntry 8 }

aulnFailCnts OBJECT-TYPE
    SYNTAX Counter
    ACCESS read-only
    STATUS mandatory
    DESCRIPTION
        "Media gateway : The total number of AULN commands  
         received that were responded to with a failure  
         return code. 
        
         Media gateway controller : The total number of AULN 
         commands sent which were timed out without a response or  
         For which a response with failure return code 
         was received. "
    ::= { srcpPeerStatsEntry 9 }

rqntFailCnts OBJECT-TYPE
    SYNTAX Counter
    ACCESS read-only
    STATUS mandatory
    DESCRIPTION
        "Media gateway : The total number of RQNT commands  
         received that were responded to with a failure return  
         code. 
        
         Media gateway controller : The total number of RQNT  
         commands sent which were timed out without a response  
         or for which a response with failure return code was  
         received. "
    ::= { srcpPeerStatsEntry 10 }

ntfyFailCnts OBJECT-TYPE
    SYNTAX Counter
    ACCESS read-only
    STATUS mandatory
    DESCRIPTION
        "Media gateway : The total number of NTFY commands sent  
         which were timed out without a response or for which a 
         response with failure return code was received. 
        
         Media gateway controller: The total number of NTFY commands  
         received that were responded to with a failure return code. "
    ::= { srcpPeerStatsEntry 11 }

srcpConfigurationGroup OBJECT IDENTIFIER ::= { srcpMIBGroups 1 }
-- OBJECT-GROUP
--  Status
--    deprecated
--  Descr
--    This group contains objects related to configuration  
--    of SRCP.  Min Access of read only is permissible for  
--    system providing only a fixed SRCP port.
--  objects
--    srcpVersion, srcpPortNumber, srcpPeerName, srcpPeerPortNumber, 
--    srcpPeerHeartbeatInterval, srcpPeerTimeSinceHeartbeat, 
--    srcpPeerMaxPduSize

srcpStatisticsGroup OBJECT IDENTIFIER ::= { srcpMIBGroups 2 }
-- OBJECT-GROUP
--  Status
--    deprecated
--  Descr
--    This group contains the statistics per SRCP peer.
--  objects
--    srcpStatsPeerName, packetsDiscardedCnts, augwCnts, aulnCnts, 
--    rqntCnts, ntfyCnts, augwFailCnts, aulnFailCnts, rqntFailCnts, 
--    ntfyFailCnts

srcpConfigurationGroup2 OBJECT IDENTIFIER ::= { srcpMIBGroups 3 }
-- OBJECT-GROUP
--  Status
--    deprecated
--  Descr
--    This group contains objects related to configuration  
--    of SRCP. Min Access of read only is permissible for  
--    system providing only a fixed SRCP port.
--  objects
--    srcpVersion, srcpPortNumber, srcpPeerName, srcpPeerPortNumber, 
--    srcpPeerHeartbeatInterval, srcpPeerTimeSinceHeartbeat, 
--    srcpPeerMaxPduSize, srcpRequestTimeOut, srcpRequestRetries, 
--    srcpRequestMaxTimeout

srcpConfigurationGroup3 OBJECT IDENTIFIER ::= { srcpMIBGroups 5 }
-- OBJECT-GROUP
--  Status
--    mandatory
--  Descr
--    This group contains objects related to configuration  
--    of SRCP.  Min Access of read only is permissible for  
--    system providing only a fixed SRCP port.
--  objects
--    srcpVersion, srcpPortNumber, srcpPeerName, srcpPeerPortNumber, 
--    srcpPeerGrpHeartbeatInterval, srcpPeerGrpTimeSinceHeartbeat, 
--    srcpPeerGrpMaxPduSize, srcpRequestTimeOut, srcpRequestRetries, 
--    srcpRequestMaxTimeout

srcpStatisticsGroup2 OBJECT IDENTIFIER ::= { srcpMIBGroups 4 }
-- OBJECT-GROUP
--  Status
--    mandatory
--  Descr
--    This group contains the statistics per SRCP peer.
--  objects
--    srcpStatsPeerName, packetsDiscardedCnts, augwCnts, aulnCnts, 
--    rqntCnts, ntfyCnts, augwFailCnts, aulnFailCnts, rqntFailCnts, 
--    ntfyFailCnts

srcpMIBCompliance OBJECT IDENTIFIER ::= { srcpMIBCompliances 1 }
-- MODULE-COMPLIANCE
--  Status
--    deprecated
--  Descr
--    The compliance statement for the SNMPv2 entities  
--     which implement SRCP MIB.
--  Module
--    >>current<<
--   MandGroup
--    srcpConfigurationGroup
--   MandGroup
--    srcpStatisticsGroup

srcpMIBComplaince2 OBJECT IDENTIFIER ::= { srcpMIBCompliances 2 }
-- MODULE-COMPLIANCE
--  Status
--    deprecated
--  Descr
--     The compliance  statement for the SNMPv2 entities 
--      which implement SRCP MIB.
--  Module
--    >>current<<
--   MandGroup
--    srcpConfigurationGroup2
--   MandGroup
--    srcpStatisticsGroup2

srcpMIBComplaince3 OBJECT IDENTIFIER ::= { srcpMIBCompliances 3 }
-- MODULE-COMPLIANCE
--  Status
--    mandatory
--  Descr
--    The compliance  statement for the SNMPv2 entities 
--     which implement SRCP MIB.
--  Module
--    >>current<<
--   MandGroup
--    srcpConfigurationGroup3
--   MandGroup
--    srcpStatisticsGroup2


END
