-- MIB file created 29-Mar-2006 19:59:20, by
--   SMICng version 2.2.11-beta(PRO)(Solaris), January 20, 2001. Enterprise key cisco.com

CISCO-WWNMGR-MIB DEFINITIONS ::= BEGIN

-- From file: "CISCO-WWNMGR-MIB.my"
-- Compile options "4 7 F H N O W 03 06 0B 0G 0N 0T"

IMPORTS
    MacAddress, StorageType, RowStatus
            FROM SNMPv2-TC-v1
    FcNameId
            FROM CISCO-ST-TC
    vsanIndex
            FROM CISCO-VSAN-MIB
    ciscoMgmt
            FROM CISCO-SMI
    Gauge
            FROM RFC1155-SMI
    OBJECT-TYPE
            FROM RFC-1212
    TRAP-TYPE
            FROM RFC-1215;

ciscoWwnmgrMIB OBJECT IDENTIFIER ::= { ciscoMgmt 286 }
-- MODULE-IDENTITY
--  LastUpdated
--    200602060000Z
--  OrgName
--    Cisco Systems Inc. 
--  ContactInfo
--         Cisco Systems
--          Customer Service
--    Postal: 170 W Tasman Drive
--          San Jose, CA  95134
--          USA
--    Tel: +1 800 553 -NETS
--    E-mail: cs-san@cisco.com
--  Descr
--    The World Wide Name (WWN) in the fibre channel networking 
--     technology is equivalent to the MAC address in Ethernet. 
--     There are six different types of WWNs defined in ANSI 
--     Standard for Fibre Channel Framing and Signalling (FC-FS) 
--     Spec Rev 1.4. 
--    
--     This mib provides the mechanism to configure and report
--     WWNs for the fibre channel devices connected to a
--     fibre channel switch.
--    
--     GLOSSARY :
--     NAA   Network Address Authority (NAA) address formats 
--           for WWN.
--    
--     OUI   Organization Unique Identifier.
--     
--     VSAN  Virtual Storage Area Network, 
--           similar to a VLAN.
--  RevDate
--    200602060000Z
--  RevDescr
--    Added a new table 'wwnmVsanWwnTable'
--     to configure user specific WWN for VSANs.
--  RevDate
--    200210010000Z
--  RevDescr
--    Initial version of this MIB module.

ciscoWwnmMIBObjects OBJECT IDENTIFIER ::= { ciscoWwnmgrMIB 1 }
wwnmConfigurationGroup OBJECT IDENTIFIER ::= { ciscoWwnmMIBObjects 1 }
wwnmNotificationGroup OBJECT IDENTIFIER ::= { ciscoWwnmMIBObjects 2 }
wwnmNotification OBJECT IDENTIFIER ::= { wwnmNotificationGroup 1 }
wwnmNotificationPrefix OBJECT IDENTIFIER ::= { wwnmNotification 0 }
ciscoWwnmMIBConformance OBJECT IDENTIFIER ::= { ciscoWwnmgrMIB 2 }
ciscoWwnmMIBCompliances OBJECT IDENTIFIER ::= { ciscoWwnmMIBConformance 1 }
ciscoWwnmMIBGroups OBJECT IDENTIFIER ::= { ciscoWwnmMIBConformance 2 }

wwnmSecondaryBaseMacAddress OBJECT-TYPE
    SYNTAX MacAddress
--    Rsyntax OCTET STRING(SIZE(6))
    ACCESS read-write
    STATUS mandatory
    DESCRIPTION
        "The first MAC address used for generating World Wide
        Names (WWNs) when the default range of WWNs generated 
        from supervisor MAC address are exhausted."
    DEFVAL { '000000000000'H }
    ::= { wwnmConfigurationGroup 1 }

wwnmSecondaryMacAddressRange OBJECT-TYPE
    SYNTAX Gauge(0..4294967295)
    ACCESS read-write
    STATUS mandatory
    DESCRIPTION
        "The number of secondary MAC Addresses starting from 
        and including the wwnmSecondayBaseMacAddress."
    DEFVAL { 0 }
    ::= { wwnmConfigurationGroup 2 }

wwnmType1MaxWwns OBJECT-TYPE
    SYNTAX Gauge(0..4294967295)
    ACCESS read-only
    STATUS mandatory
    DESCRIPTION
        "Maximum number of NAA Type 1 WWNs that are available
        for assignment to internal entities."
    REFERENCE
        "FC-FS-2 Rev 1.70, Section 14 Name Identifier Formats."
    ::= { wwnmConfigurationGroup 3 }

wwnmType1AvailableWwns OBJECT-TYPE
    SYNTAX Gauge
    ACCESS read-only
    STATUS mandatory
    DESCRIPTION
        "Number of NAA Type 1 WWNs that are currently 
        available for assignment to internal entities."
    REFERENCE
        "FC-FS-2 Rev 1.70, Section 14 Name Identifier Formats."
    ::= { wwnmConfigurationGroup 4 }

wwnmTypeOtherMaxWwns OBJECT-TYPE
    SYNTAX Gauge(0..4294967295)
    ACCESS read-only
    STATUS mandatory
    DESCRIPTION
        "Maximum number of total WWNs of types NAA Type 2 
        and Type 5 WWNs available for assignment to  internal
        entities."
    REFERENCE
        "FC-FS-2 Rev 1.70, Section 14 Name Identifier Formats."
    ::= { wwnmConfigurationGroup 5 }

wwnmTypeOtherAvailableWwns OBJECT-TYPE
    SYNTAX Gauge
    ACCESS read-only
    STATUS mandatory
    DESCRIPTION
        "Sum of number of NAA Type 2 and Type 5 WWNs currently
        available for assignment to the internal entities."
    REFERENCE
        "FC-FS-2 Rev 1.70, Section 14 Name Identifier Formats."
    ::= { wwnmConfigurationGroup 6 }

wwnmType1ReservedWwns OBJECT-TYPE
    SYNTAX Gauge(0..4294967295)
    ACCESS read-only
    STATUS mandatory
    DESCRIPTION
        "Number of NAA Type 1 WWNs that are reserved
        for internal purposes."
    REFERENCE
        "FC-FS-2 Rev 1.70, Section 14 Name Identifier Formats."
    ::= { wwnmConfigurationGroup 7 }

wwnmTypeOtherReservedWwns OBJECT-TYPE
    SYNTAX Gauge(0..4294967295)
    ACCESS read-only
    STATUS mandatory
    DESCRIPTION
        "Number of total WWNs of types NAA Type 2 
        and Type 5 WWNs reserved for internal purposes."
    REFERENCE
        "FC-FS-2 Rev 1.70, Section 14 Name Identifier Formats."
    ::= { wwnmConfigurationGroup 8 }

wwnmVsanWwnTable OBJECT-TYPE
    SYNTAX SEQUENCE OF WwnmVsanWwnEntry
    ACCESS not-accessible
    STATUS mandatory
    DESCRIPTION
        "This table provides an option to configure
        user specified WWN for the VSANs. 
        
        To enable the fibre channel switch to interoperate
        with other vendor switches on a VSAN, user 
        needs to configure a WWN (based on the other 
        vendor switch OUI) for the corresponding VSAN. 
        
        To create a new entry in this table for a VSAN,
        a corresponding entry for that VSAN should exists in
        the vsanTable. Also, the value of the corresponding 
        instance of vsanAdminState should be in 'suspended' 
        state and the VSAN should interoperate in mode 4 
        (represented by vsanInterOperValue '4'). 
        
        An entry from this table can be removed by any one
        of the following ways, 
        a. Setting the corresponding instance 
           wwnmVsanWwnRowStatus value to 'destroy'. 
        b. Deleting the corresponding VSAN from vsanTable.
        c. Changing the corresponding VSAN configuration 
           from interoperate mode 4 (represented by 
           vsanInterOperValue '4') to any other value."
    REFERENCE
        "vsanTable, vsanAdminState, vsanInterOperValue in 
         CISCO-VSAN-MIB"
    ::= { wwnmConfigurationGroup 9 }

wwnmVsanWwnEntry OBJECT-TYPE
    SYNTAX WwnmVsanWwnEntry
    ACCESS not-accessible
    STATUS mandatory
    DESCRIPTION
        "An entry (conceptual row) in this table.
        Each entry of this table represents the 
        WWN configuration set for a VSAN."
    INDEX { vsanIndex }
    ::= { wwnmVsanWwnTable 1 }

WwnmVsanWwnEntry ::= SEQUENCE {
    wwnmVsanWwn FcNameId,
    wwnmVsanWwnStorageType StorageType,
    wwnmVsanWwnRowStatus RowStatus
    }

wwnmVsanWwn OBJECT-TYPE
    SYNTAX FcNameId
--    Rsyntax OCTET STRING(SIZE(8))
    ACCESS read-write
    STATUS mandatory
    DESCRIPTION
        "The user configurable WWN for a VSAN.
        
        For row creation, it is mandatory to set
        the value of this object to a valid value."
    ::= { wwnmVsanWwnEntry 1 }

wwnmVsanWwnStorageType OBJECT-TYPE
    SYNTAX StorageType
--    Rsyntax INTEGER {
--        other(1),
--        volatile(2),
--        nonVolatile(3),
--        permanent(4),
--        readOnly(5)
--        }
    ACCESS read-only
    STATUS mandatory
    DESCRIPTION
        "The storage type for this conceptual row.
        Conceptual rows having the value 'permanent' need
        not allow write-access to any columnar objects in
        the row."
    DEFVAL { nonVolatile }
    ::= { wwnmVsanWwnEntry 2 }

wwnmVsanWwnRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this conceptual row. 
        
        The value of this object cannot be 'active' 
        unless the value of the corresponding instance
        of 'wwnmVsanWwn' is set to a valid value."
    ::= { wwnmVsanWwnEntry 3 }

wwnmType1WwnShortageNotify TRAP-TYPE
-- Reverse mappable trap
    ENTERPRISE wwnmNotification
    VARIABLES {
        wwnmType1AvailableWwns }
--  Status
--    mandatory
    DESCRIPTION
        "A WWN shortage notification is generated whenever the 
        number of available Type 1 WWNs 'wwnmType1AvailableWwns'
        reduces to either 20% or 10% or 0% of the maximum number
        of Type 1 WWNs 'wwnmType1MaxWwns'.
        After a shortage event is generated for a threshhold
        (say 20%), another such event will not be generated until
        after an availability event (see 
        wwnmType1WwnAvailableNotify) is generated for the same 
        threshold."
    ::= 1

wwnmType1WwnAvailableNotify TRAP-TYPE
-- Reverse mappable trap
    ENTERPRISE wwnmNotification
    VARIABLES {
        wwnmType1AvailableWwns }
--  Status
--    mandatory
    DESCRIPTION
        "An availability notification is generated whenever
        the number of available Type 1 WWNs 
        (wwnmType1AvailableWwns) increases to either 25% or 15% 
        or 5% of the maximum number of Type 1 WWNs 
        (wwnmType1MaxWwns) after a wwnmType1WwnShortageNotify
        notification has been generated for either 20% or 10%
        or 5% respectively."
    ::= 2

wwnmTypeOtherWwnShortageNotify TRAP-TYPE
-- Reverse mappable trap
    ENTERPRISE wwnmNotification
    VARIABLES {
        wwnmTypeOtherAvailableWwns }
--  Status
--    mandatory
    DESCRIPTION
        "A WWN shortage notification is generated whenever the 
        number of available Type Other WWNs 
        'wwnmTypeOtherAvailableWwns' reduces to either 20% or 
        10% or 0% of the maximum number of Type Other WWNs 
        'wwnmTypeOtherMaxWwns'.
        After a shortage event is generated for a threshhold 
        (say 20%), another such event will not be generated until
        after an availability event (see 
        wwnmType1WwnAvailableNotify) is generated for the same 
        threshold."
    ::= 3

wwnmTypeOtherWwnAvailableNotify TRAP-TYPE
-- Reverse mappable trap
    ENTERPRISE wwnmNotification
    VARIABLES {
        wwnmTypeOtherAvailableWwns }
--  Status
--    mandatory
    DESCRIPTION
        "An availability notification is generated whenever
        the number of available Type Other WWNs
        (wwnmTypeOtherAvailableWwns) increases to either 25% 
        or 15% or 5% of the maximum number of Type Other WWNs
        (wwnmTypeOtherMaxWwns) after a 
        wwnmTypeOtherWwnShortageNotify notification has been 
        generated for either 20% or 10% or 5% respectively."
    ::= 4

cwmWwnmConfigurationGroup OBJECT IDENTIFIER ::= { ciscoWwnmMIBGroups 6 }
-- OBJECT-GROUP
--  Status
--    mandatory
--  Descr
--    A collection of objects for WWN Manager.
--  objects
--    wwnmSecondaryBaseMacAddress, wwnmSecondaryMacAddressRange, 
--    wwnmType1MaxWwns, wwnmType1AvailableWwns, 
--    wwnmTypeOtherMaxWwns, wwnmTypeOtherAvailableWwns, 
--    wwnmType1ReservedWwns, wwnmTypeOtherReservedWwns

cwmWwnmVsanWwnGroup OBJECT IDENTIFIER ::= { ciscoWwnmMIBGroups 9 }
-- OBJECT-GROUP
--  Status
--    mandatory
--  Descr
--    A collection of objects to represent the configured 
--     WWN for the VSANs.
--  objects
--    wwnmVsanWwn, wwnmVsanWwnStorageType, wwnmVsanWwnRowStatus

cwmWwnmNotificationGroup OBJECT IDENTIFIER ::= { ciscoWwnmMIBGroups 8 }
-- NOTIFICATION-GROUP
--  Status
--    mandatory
--  Descr
--    A collection of notifications for the 
--    WWN assignment.
--  notifications
--    wwnmType1WwnShortageNotify, wwnmType1WwnAvailableNotify, 
--    wwnmTypeOtherWwnShortageNotify, 
--    wwnmTypeOtherWwnAvailableNotify

ciscoWwnmMIBCompliance OBJECT IDENTIFIER ::= { ciscoWwnmMIBCompliances 1 }
-- MODULE-COMPLIANCE
--  Status
--    deprecated
--  Descr
--    The compliance statement for entities which
--     implement the CISCO-WWNMGR-MIB.
--  Module
--    >>current<<
--   MandGroup
--    cwmWwnmConfigurationGroup
--   MandGroup
--    cwmWwnmNotificationGroup

ciscoWwnmMIBCompliance1 OBJECT IDENTIFIER ::= { ciscoWwnmMIBCompliances 2 }
-- MODULE-COMPLIANCE
--  Status
--    mandatory
--  Descr
--    The compliance statement for entities which
--     implement the CISCO-WWNMGR-MIB.
--  Module
--    >>current<<
--   MandGroup
--    cwmWwnmConfigurationGroup
--   MandGroup
--    cwmWwnmVsanWwnGroup
--   MandGroup
--    cwmWwnmNotificationGroup
--   ObjVar
--    wwnmVsanWwnRowStatus


END
