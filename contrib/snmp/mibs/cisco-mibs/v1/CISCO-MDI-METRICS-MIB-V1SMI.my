-- MIB file created 03-Jan-2011 18:12:40, by
--   SMICng version 2.2.11-beta(PRO)(Solaris), January 20, 2001. Enterprise key cisco.com

CISCO-MDI-METRICS-MIB DEFINITIONS ::= BEGIN

-- From file: "CISCO-MDI-METRICS-MIB.my"
-- Compile options "4 7 F H N O W 03 06 0B 0G 0N 0T"

IMPORTS
    TimeStamp
            FROM SNMPv2-TC-v1
    ReportIntervalCount
            FROM CISCO-REPORT-INTERVAL-TC-MIB
    FlowCfgRateType, FlowBitRateUnits, FlowMetricScale, 
    FlowMetricPrecision, FlowMetricValue
            FROM CISCO-FLOW-MONITOR-TC-MIB
    cfmFlowMonitorId, cfmFlowId, cfmFlowMetricsIntNumber
            FROM CISCO-FLOW-MONITOR-MIB
    TimeIntervalMin
            FROM CISCO-TC
    ciscoMgmt
            FROM CISCO-SMI
    Gauge, Counter
            FROM RFC1155-SMI
    OBJECT-TYPE
            FROM RFC-1212;

ciscoMdiMetricsMIB OBJECT IDENTIFIER ::= { ciscoMgmt 699 }
-- MODULE-IDENTITY
--  LastUpdated
--    200911020000Z
--  OrgName
--    Cisco Systems, Inc.
--  ContactInfo
--    Cisco Systems
--    Customer Service
--    
--    Postal:  170 W Tasman Drive
--    San Jose, CA 95134
--    
--    Tel:  +1 800 553-NETS
--    
--    E-mail:  cs-snmp@cisco.com
--  Descr
--    This MIB module defines objects that describe the Media
--    Delivery Index (MDI).  The MDI [RFC4445] measurement describes
--    the quality indicator of a network intended to delivery
--    applications such as streaming media, MPEG video, VoIP, or other
--    information sensitive to arrival time and packet loss.
--    
--    GLOSSARY
--    ============
--    
--    Delay Factor - the maximum observed value of the flow rate
--        imbalance over a measurement interval.
--    
--    DF - Delay Factor.
--    
--    Flow Monitor - a hardware or software entity that classifies
--        traffic flows, collects flow data, and periodically
--        computes flow metrics.
--    
--    Flow Metric - a measurement that reflects the quality of a
--        traffic flow.
--    
--    Measurement Interval - the length of time over which a flow
--        monitor collects data related to a traffic flow, after which
--        the flow monitor computes flow metrics using the collected
--        data.
--    
--    Media Loss Rate - the number of lost or out-of-order packets
--        over a measurement interval.
--    
--    Media Rate - the effective bit rate of the media content carried
--    by a traffic flow.
--    
--    MLR - Media Loss Rate.
--    
--    MR - Media Rate.
--    
--    Traffic Flow - a unidirectional stream of packets conforming to
--        a classifier.  For example, packets having a particular 
--        source IP address, destination IP address, protocol type,
--        source port number, and destination port number.
--    
--    VB - Virtual Buffer.
--    
--    Virtual Buffer - a virtual buffer is a construct used to
--        simulate a real buffer used by a media application for the
--        purpose of storing media packets until the application can
--        render their content.
--    
--    REFERENCES
--    ==============
--    
--    [RFC4445]   J. Welch and J. Clark, 'A Proposed Media Delivery
--                Index (MDI)', RFC-4445, April 2006.
--  RevDate
--    200911020000Z
--  RevDescr
--    Added the objects cfmMdiMetricsMdc, cfmMdiMetricsIntMdc.
--    Modified the objects cfmMdiMetricsValid and
--    cfmMdiMetricsIntValid with values to support the above object
--    additions. Added cfmeMdiCumulativeMdc and cfmeMdiMdc to
--    cfmMdiMonitoredElements.
--  RevDate
--    200906050000Z
--  RevDescr
--    The initial version of the MIB module.

ciscoMdiMetricsMIBNotifs OBJECT IDENTIFIER ::= { ciscoMdiMetricsMIB 0 }
ciscoMdiMetricsMIBObjects OBJECT IDENTIFIER ::= { ciscoMdiMetricsMIB 1 }
ciscoMdiMetricsMIBConform OBJECT IDENTIFIER ::= { ciscoMdiMetricsMIB 2 }
ciscoMdiMetricsMIBIds OBJECT IDENTIFIER ::= { ciscoMdiMetricsMIB 3 }
cfmMdiMetrics   OBJECT IDENTIFIER ::= { ciscoMdiMetricsMIBObjects 1 }
cfmMdiMonitoredElements OBJECT IDENTIFIER ::= { ciscoMdiMetricsMIBIds 1 }
ciscoMdiMetricsMIBCompliances OBJECT IDENTIFIER ::= { ciscoMdiMetricsMIBConform 1 }
ciscoMdiMetricsMIBGroups OBJECT IDENTIFIER ::= { ciscoMdiMetricsMIBConform 2 }

cfmeMdiCumulativeLostPkts OBJECT IDENTIFIER ::= { cfmMdiMonitoredElements 1 }
-- OBJECT-IDENTITY
--  Status
--    mandatory
--  Descr
--    This object identifier represents the monitored element
--    describing the cumulative number of lost packets for a traffic
--    flow (cfmMdiMetricsLostPkts).

cfmeMdiCumulativeMlr OBJECT IDENTIFIER ::= { cfmMdiMonitoredElements 2 }
-- OBJECT-IDENTITY
--  Status
--    mandatory
--  Descr
--    This object identifier represents the monitored element
--    describing the MDI MLR for a traffic flow (cfmMdiMetricsMlr).

cfmeMdiCumulativeMdc OBJECT IDENTIFIER ::= { cfmMdiMonitoredElements 3 }
-- OBJECT-IDENTITY
--  Status
--    mandatory
--  Descr
--    This object identifier represents the monitored element
--    describing the MDI MDC for a traffic flow (cfmMdiMetricsMdc).

cfmeMdiLostPkts OBJECT IDENTIFIER ::= { cfmMdiMonitoredElements 4 }
-- OBJECT-IDENTITY
--  Status
--    mandatory
--  Descr
--    This object identifier represents the monitored element
--    describing the number of lost packets for a traffic flow during
--    the last measurement interval (cfmMdiMetricsIntLostPkts).

cfmeMdiDf OBJECT IDENTIFIER ::= { cfmMdiMonitoredElements 5 }
-- OBJECT-IDENTITY
--  Status
--    mandatory
--  Descr
--    This object identifier represents the monitored element
--    describing the MDI DF for a traffic flow during the last
--    measurement interval (cfmMdiMetricsIntDf).

cfmeMdiMlr OBJECT IDENTIFIER ::= { cfmMdiMonitoredElements 6 }
-- OBJECT-IDENTITY
--  Status
--    mandatory
--  Descr
--    This object identifier represents the monitored element
--    describing the MDI MLR for a traffic flow during the last
--    measurement interval (cfmMdiMetricsIntMlr).

cfmeMdiMdc OBJECT IDENTIFIER ::= { cfmMdiMonitoredElements 7 }
-- OBJECT-IDENTITY
--  Status
--    mandatory
--  Descr
--    This object identifier represents the monitored element
--    describing the MDI MDC for a traffic flow during the last
--    measurement interval (cfmMdiMetricsIntMdc).

cfmMdiMetricsTable OBJECT-TYPE
    SYNTAX SEQUENCE OF CfmMdiMetricsEntry
    ACCESS not-accessible
    STATUS mandatory
    DESCRIPTION
        "This table contains aggregate data maintained by a flow
        monitor for traffic flows for which it is computing MDI
        metrics.
        
        This table has an sparse dependent relationship on the
        cfmFlowMetricsTable (defined by the CISCO-FLOW-MONITOR-MIB),
        containing a row for each row in the cfmFlowMetricsTable having
        a corresponding instance of cfmFlowMetricsCollected with the
        'mdi' bit set to one."
    ::= { cfmMdiMetrics 1 }

cfmMdiMetricsEntry OBJECT-TYPE
    SYNTAX CfmMdiMetricsEntry
    ACCESS not-accessible
    STATUS mandatory
    DESCRIPTION
        "An entry describes cumulative and aggregate MDI metrics for a
        single traffic flow.
        
        The devices creates a row in the cfmMdiMetricsTable when a flow
        monitor starts monitoring a traffic flow and has been configured
        to compute MDI metrics for the same traffic flow. Likewise, the
        device destroys a row in the cfmMdiMetricsMetricsTable when the
        corresponding flow monitor has ceased monitoring the traffic
        flow (e.g., when a traffic flow has timed out)."
    INDEX { cfmFlowMonitorId, cfmFlowId }
    ::= { cfmMdiMetricsTable 1 }

CfmMdiMetricsEntry ::= SEQUENCE {
    cfmMdiMetricsCfgRateType FlowCfgRateType,
    cfmMdiMetricsCfgBitRate FlowBitRateUnits,
    cfmMdiMetricsCfgRate Gauge,
    cfmMdiMetricsCfgMediaPktSize Gauge,
    cfmMdiMetricsValid OCTET STRING,
    cfmMdiMetricsLostPkts Counter,
    cfmMdiMetricsMlrScale FlowMetricScale,
    cfmMdiMetricsMlrPrecision FlowMetricPrecision,
    cfmMdiMetricsMlr FlowMetricValue,
    cfmMdiMetricsMdc Counter
    }

cfmMdiMetricsCfgRateType OBJECT-TYPE
    SYNTAX FlowCfgRateType
--    Rsyntax INTEGER {
--        auto(1),
--        ipPktRate(2),
--        ipBitRate(3),
--        mediaRate(4)
--        }
    ACCESS read-only
    STATUS mandatory
    DESCRIPTION
        "This object indicates how the corresponding flow monitor
        computes the DF for the traffic flow."
    ::= { cfmMdiMetricsEntry 1 }

cfmMdiMetricsCfgBitRate OBJECT-TYPE
    SYNTAX FlowBitRateUnits
--    Rsyntax INTEGER {
--        bps(1),
--        kbps(2),
--        mbps(3),
--        gbps(4)
--        }
    ACCESS read-only
    STATUS mandatory
    DESCRIPTION
        "This object indicates the units for the corresponding instance
        of cfmMdiMetricsCfgRate.  The value of this column only has
        relevance if the corresponding instance of
        cfmMdiMetricsCfgRateType is 'ipBitRate' or 'mediaRate'."
    ::= { cfmMdiMetricsEntry 2 }

cfmMdiMetricsCfgRate OBJECT-TYPE
    SYNTAX Gauge(1..4294967295)
    ACCESS read-only
    STATUS mandatory
    DESCRIPTION
        "This object indicates the configured bit rate used by the flow
        monitor to compute the DF for the traffic flow.  The value of
        this column only has relevance if the corresponding instance of
        cfmMdiMetricsCfgRateType is 'ipBitRate' or 'mediaRate'."
    ::= { cfmMdiMetricsEntry 3 }

cfmMdiMetricsCfgMediaPktSize OBJECT-TYPE
    SYNTAX Gauge(64..65535)
--  Units
--    octets
    ACCESS read-only
    STATUS mandatory
    DESCRIPTION
        "This object indicates the configured media packet size used by
        the flow monitor to compute the DF for the traffic flow.  The
        value of this column only has relevance if the corresponding
        instance of cfmMdiMetricsCfgRateType is 'mediaRate'."
    ::= { cfmMdiMetricsEntry 4 }

cfmMdiMetricsValid OBJECT-TYPE
    SYNTAX OCTET STRING(SIZE(1..2))
        -- BITS are:
        --   lostPkts(0)
        --   mediaLossRate(1)
        --   mediaDiscontinuityCount(2)
    ACCESS read-only
    STATUS mandatory
    DESCRIPTION
        "This object indicates which metrics are valid for the traffic
        flow:
        
            'lostPkts'
                If this bit is set to '1', then the corresponding
                instance of cfmMdiMetricsLostPkts is valid.
        
            'mediaLossRate'
                If this bit is set to '1', then the corresponding
                instances of cfmMdiMetricsMlrScale,
                cfmMdiMetricsMlrPrecision, and cfmMdiMetricsMlr are
                valid.
        
            'mediaDiscontinuityCount'
                If this bit is set to '1', then the corresponding
                instance of cfmMdiMetricsMdc is valid."
    ::= { cfmMdiMetricsEntry 5 }

cfmMdiMetricsLostPkts OBJECT-TYPE
    SYNTAX --?? syntax is not convertable to SMIv1
           Counter
--  Units
--    packets
    ACCESS read-only
    STATUS mandatory
    DESCRIPTION
        "This object indicates the number of packets lost for the
        traffic flow.
        
        The value of this column is valid if and only if the 'lostPkts'
        bit in the corresponding instance of cfmMdiMetricsValid is set
        to '1'."
    ::= { cfmMdiMetricsEntry 6 }

cfmMdiMetricsMlrScale OBJECT-TYPE
    SYNTAX FlowMetricScale
--    Rsyntax INTEGER {
--        yocto(1),
--        zepto(2),
--        atto(3),
--        femto(4),
--        pico(5),
--        nano(6),
--        micro(7),
--        milli(8),
--        units(9),
--        kilo(10),
--        mega(11),
--        giga(12),
--        tera(13),
--        exa(14),
--        peta(15),
--        zetta(16),
--        yotta(17)
--        }
    ACCESS read-only
    STATUS mandatory
    DESCRIPTION
        "This object indicates the scale factor for the corresponding
        instance of cfmMdiMetricsMlr.
        
        The value of this column is valid if and only if the
        'mediaLossRate' bit in the corresponding instance of
        cfmMdiMetricsValid is set to '1'."
    ::= { cfmMdiMetricsEntry 7 }

cfmMdiMetricsMlrPrecision OBJECT-TYPE
    SYNTAX FlowMetricPrecision
--    Rsyntax INTEGER(-8..-1|1..9)
    ACCESS read-only
    STATUS mandatory
    DESCRIPTION
        "This object indicates the precision for the corresponding
        instance of cfmMdiMetricsMlr.
        
        The value of this column is valid if and only if the
        'mediaLossRate' bit in the corresponding instance of
        cfmMdiMetricsValid is set to '1'."
    ::= { cfmMdiMetricsEntry 8 }

cfmMdiMetricsMlr OBJECT-TYPE
    SYNTAX FlowMetricValue
--    Rsyntax INTEGER(-1000000000..1000000000)
--  Units
--    packets per second
    ACCESS read-only
    STATUS mandatory
    DESCRIPTION
        "This object indicates the MLR for the traffic flow since the
        flow monitor started collecting data for the traffic flow.
        
        The value of this column is valid if and only if the
        'mediaLossRate' bit in the corresponding instance of
        cfmMdiMetricsValid is set to '1'."
    ::= { cfmMdiMetricsEntry 9 }

cfmMdiMetricsMdc OBJECT-TYPE
    SYNTAX --?? syntax is not convertable to SMIv1
           Counter
--  Units
--    Events
    ACCESS read-only
    STATUS mandatory
    DESCRIPTION
        "This object indicates the media discontinuity events count for
        the traffic flow since the flow monitor started collecting data
        for the traffic flow.
        
        The value of this column is valid if and only if the
        'mediaDiscontinuityCount' bit in the corresponding instance of
        cfmMdiMetricsValid is set to '1'."
    ::= { cfmMdiMetricsEntry 10 }

cfmMdiMetricsTableChanged OBJECT-TYPE
    SYNTAX TimeStamp
--    Rsyntax TimeTicks
    ACCESS read-only
    STATUS mandatory
    DESCRIPTION
        "This object indicates the value of sysUpTime the last time the
        device created/destroyed a row in the cfmMdiMetricsTable."
    ::= { cfmMdiMetrics 2 }

cfmMdiMetricsIntTable OBJECT-TYPE
    SYNTAX SEQUENCE OF CfmMdiMetricsIntEntry
    ACCESS not-accessible
    STATUS mandatory
    DESCRIPTION
        "This table contains historic MDI metrics for the traffic flows
        monitored by each of the flow monitors supported by the device.
        
        This table has an sparse dependent relationship on the
        cfmFlowMetricsIntTable (defined by the CISCO-FLOW-MONITOR-MIB),
        containing a row for each row in the cfmFlowMetricsIntTable
        having a corresponding instance of cfmFlowMetricsCollected with
        the 'mdi' bit set to one."
    ::= { cfmMdiMetrics 3 }

cfmMdiMetricsIntEntry OBJECT-TYPE
    SYNTAX CfmMdiMetricsIntEntry
    ACCESS not-accessible
    STATUS mandatory
    DESCRIPTION
        "An entry describes MDI metrics collected for a previous
        measurement interval for a corresponding traffic flow."
    INDEX { cfmFlowMonitorId, cfmFlowId, cfmFlowMetricsIntNumber }
    ::= { cfmMdiMetricsIntTable 1 }

CfmMdiMetricsIntEntry ::= SEQUENCE {
    cfmMdiMetricsIntValid OCTET STRING,
    cfmMdiMetricsIntLostPkts ReportIntervalCount,
    cfmMdiMetricsIntVbMin ReportIntervalCount,
    cfmMdiMetricsIntVbMax ReportIntervalCount,
    cfmMdiMetricsIntMrUnits FlowBitRateUnits,
    cfmMdiMetricsIntMr ReportIntervalCount,
    cfmMdiMetricsIntDfScale FlowMetricScale,
    cfmMdiMetricsIntDfPrecision FlowMetricPrecision,
    cfmMdiMetricsIntDf FlowMetricValue,
    cfmMdiMetricsIntMlrScale FlowMetricScale,
    cfmMdiMetricsIntMlrPrecision FlowMetricPrecision,
    cfmMdiMetricsIntMlr FlowMetricValue,
    cfmMdiMetricsIntMdc ReportIntervalCount
    }

cfmMdiMetricsIntValid OBJECT-TYPE
    SYNTAX OCTET STRING(SIZE(1..2))
        -- BITS are:
        --   lostPkts(0)
        --   vbMin(1)
        --   vbMax(2)
        --   mediaRate(3)
        --   delayFactor(4)
        --   mediaLossRate(5)
        --   mediaDiscontinuityCount(6)
    ACCESS read-only
    STATUS mandatory
    DESCRIPTION
        "This object indicates which metrics are valid for the
        measurement interval:
        
            'lostPkts'
                If this bit is set to '1', then the corresponding
                instance of cfmMdiMetricsIntLostPkts is valid.
        
            'vbMin'
                If this bit is set to '1', then the corresponding
                instance of cfmMdiMetricsIntVbMin is valid.
        
            'vbMax'
                If this bit is set to '1', then the corresponding
                instance of cfmMdiMetricsIntVbMax is valid.
        
            'mediaRate'
                If this bit is set to '1', then the corresponding
                instances of cfmMdiMetricsIntMrUnits and
                cfmMdiMetricsIntMr are valid.
        
            'delayFactor'
                If this bit is set to '1', then the corresponding
                instances of cfmMdiMetricsIntDfScale,
                cfmMdiMetricsIntDfPrecision, and cfmMdiMetricsIntDf are
                valid.
        
            'mediaLossRate'
                If this bit is set to '1', then the corresponding
                instances of cfmMdiMetricsIntMlrScale,
                cfmMdiMetricsIntMlrPrecision, and cfmMdiMetricsIntMlr
                are valid.
        
            'mediaDiscontinuityCount'
                If this bit is set to '1', then the corresponding
                instance of cfmMdiMetricsIntMdc is valid."
    ::= { cfmMdiMetricsIntEntry 1 }

cfmMdiMetricsIntLostPkts OBJECT-TYPE
    SYNTAX ReportIntervalCount
--    Rsyntax Gauge
--  Units
--    packets
    ACCESS read-only
    STATUS mandatory
    DESCRIPTION
        "This object indicates the number of packets lost for the
        traffic flow during the measurement interval.
        
        The value of this column is valid if and only if the 'lostPkts'
        bit in the corresponding instance of cfmMdiMetricsValid is set
        to '1'."
    ::= { cfmMdiMetricsIntEntry 2 }

cfmMdiMetricsIntVbMin OBJECT-TYPE
    SYNTAX ReportIntervalCount
--    Rsyntax Gauge
--  Units
--    bytes
    ACCESS read-only
    STATUS mandatory
    DESCRIPTION
        "This object indicates the minimum virtual buffer size computed
        for the traffic flow over the course of the measurement
        interval.
        
        The value of this column is valid if and only if the 'vbMin'
        bit in the corresponding instance of cfmMdiMetricsValid is set
        to '1'."
    ::= { cfmMdiMetricsIntEntry 3 }

cfmMdiMetricsIntVbMax OBJECT-TYPE
    SYNTAX ReportIntervalCount
--    Rsyntax Gauge
--  Units
--    bytes
    ACCESS read-only
    STATUS mandatory
    DESCRIPTION
        "This object indicates the maximum virtual buffer size computed
        for the traffic flow over the course of the measurement
        interval.
        
        The value of this column is valid if and only if the 'vbMax' bit
        in the corresponding instance of cfmMdiMetricsIntValid is set to
        '1'."
    ::= { cfmMdiMetricsIntEntry 4 }

cfmMdiMetricsIntMrUnits OBJECT-TYPE
    SYNTAX FlowBitRateUnits
--    Rsyntax INTEGER {
--        bps(1),
--        kbps(2),
--        mbps(3),
--        gbps(4)
--        }
    ACCESS read-only
    STATUS mandatory
    DESCRIPTION
        "This object indicates the units for the corresponding instance
        of cfmMdiMetricsIntMr.
        
        The value of this column is valid if and only if the 'mediaRate'
        bit in the corresponding instance of cfmMdiMetricsIntValid is
        set to '1'."
    ::= { cfmMdiMetricsIntEntry 5 }

cfmMdiMetricsIntMr OBJECT-TYPE
    SYNTAX ReportIntervalCount
--    Rsyntax Gauge
    ACCESS read-only
    STATUS mandatory
    DESCRIPTION
        "This object indicates the media rate used by the flow monitor
        to compute the DF for the traffic flow.  If the corresponding
        instance of cfmMdiMetricsCfgRateType is 'auto', then the value
        of this column indicates the MR for the traffic flow during the
        measurement interval.  Otherwise, the value  of this column
        reflects the configure MR.
        
        The value of this column is valid if and only if the 'mediaRate'
        bit in the corresponding instance of cfmMdiMetricsIntValid is
        set to '1'."
    ::= { cfmMdiMetricsIntEntry 6 }

cfmMdiMetricsIntDfScale OBJECT-TYPE
    SYNTAX FlowMetricScale
--    Rsyntax INTEGER {
--        yocto(1),
--        zepto(2),
--        atto(3),
--        femto(4),
--        pico(5),
--        nano(6),
--        micro(7),
--        milli(8),
--        units(9),
--        kilo(10),
--        mega(11),
--        giga(12),
--        tera(13),
--        exa(14),
--        peta(15),
--        zetta(16),
--        yotta(17)
--        }
    ACCESS read-only
    STATUS mandatory
    DESCRIPTION
        "This object indicates the scaling factor for the corresponding
        instance of cfmMdiMetricsIntDf.
        
        The value of this column is valid if and only if the
        'delayFactor' bit in the corresponding instance of
        cfmMdiMetricsIntValid is set to '1'."
    ::= { cfmMdiMetricsIntEntry 7 }

cfmMdiMetricsIntDfPrecision OBJECT-TYPE
    SYNTAX FlowMetricPrecision
--    Rsyntax INTEGER(-8..-1|1..9)
    ACCESS read-only
    STATUS mandatory
    DESCRIPTION
        "This object indicates the precision for the corresponding
        instance of cfmMdiMetricsIntDf.
        
        The value of this column is valid if and only if the
        'delayFactor' bit in the corresponding instance of
        cfmMdiMetricsIntValid is set to '1'."
    ::= { cfmMdiMetricsIntEntry 8 }

cfmMdiMetricsIntDf OBJECT-TYPE
    SYNTAX FlowMetricValue
--    Rsyntax INTEGER(-1000000000..1000000000)
    ACCESS read-only
    STATUS mandatory
    DESCRIPTION
        "This object indicates the DF for the traffic flow during the
        measurement interval.
        
        The value of this column is valid if and only if the
        'delayFactor' bit in the corresponding instance of
        cfmMdiMetricsIntValid is set to '1'."
    ::= { cfmMdiMetricsIntEntry 9 }

cfmMdiMetricsIntMlrScale OBJECT-TYPE
    SYNTAX FlowMetricScale
--    Rsyntax INTEGER {
--        yocto(1),
--        zepto(2),
--        atto(3),
--        femto(4),
--        pico(5),
--        nano(6),
--        micro(7),
--        milli(8),
--        units(9),
--        kilo(10),
--        mega(11),
--        giga(12),
--        tera(13),
--        exa(14),
--        peta(15),
--        zetta(16),
--        yotta(17)
--        }
    ACCESS read-only
    STATUS mandatory
    DESCRIPTION
        "This object indicates the scaling factor for the corresponding
        instance of cfmMdiMetricsIntMlr.
        
        The value of this column is valid if and only if the
        'mediaLossRate' bit in the corresponding instance of
        cfmMdiMetricsIntValid is set to '1'."
    ::= { cfmMdiMetricsIntEntry 10 }

cfmMdiMetricsIntMlrPrecision OBJECT-TYPE
    SYNTAX FlowMetricPrecision
--    Rsyntax INTEGER(-8..-1|1..9)
    ACCESS read-only
    STATUS mandatory
    DESCRIPTION
        "This object indicates the precision for the corresponding
        instance of cfmMdiMetricsIntMlr.
        
        The value of this column is valid if and only if the
        'mediaLossRate' bit in the corresponding instance of
        cfmMdiMetricsIntValid is set to '1'."
    ::= { cfmMdiMetricsIntEntry 11 }

cfmMdiMetricsIntMlr OBJECT-TYPE
    SYNTAX FlowMetricValue
--    Rsyntax INTEGER(-1000000000..1000000000)
--  Units
--    packets per second
    ACCESS read-only
    STATUS mandatory
    DESCRIPTION
        "This object indicates the MLR for the traffic flow during the
        measurement interval.
        
        The value of this column is valid if and only if the
        'mediaLossRate' bit in the corresponding instance of
        cfmMdiMetricsIntValid is set to '1'."
    ::= { cfmMdiMetricsIntEntry 12 }

cfmMdiMetricsIntMdc OBJECT-TYPE
    SYNTAX ReportIntervalCount
--    Rsyntax Gauge
--  Units
--    Events
    ACCESS read-only
    STATUS mandatory
    DESCRIPTION
        "This object indicates the media discontinuity events count for
        the traffic flow during the measurement interval.
        
        The value of this column is valid if and only if the
        'mediaDiscontinuityCount' bit in the corresponding instance of
        cfmMdiMetricsIntValid is set to '1'."
    ::= { cfmMdiMetricsIntEntry 13 }

cfmMdiMetricsGroup OBJECT IDENTIFIER ::= { ciscoMdiMetricsMIBGroups 1 }
-- OBJECT-GROUP
--  Status
--    mandatory
--  Descr
--    This group contains objects that describe MDI metrics.
--  objects
--    cfmMdiMetricsCfgRateType, cfmMdiMetricsCfgBitRate, 
--    cfmMdiMetricsCfgRate, cfmMdiMetricsCfgMediaPktSize, 
--    cfmMdiMetricsValid, cfmMdiMetricsLostPkts, 
--    cfmMdiMetricsMlrScale, cfmMdiMetricsMlrPrecision, 
--    cfmMdiMetricsMlr, cfmMdiMetricsMdc, cfmMdiMetricsTableChanged, 
--    cfmMdiMetricsIntValid, cfmMdiMetricsIntLostPkts, 
--    cfmMdiMetricsIntVbMin, cfmMdiMetricsIntVbMax, 
--    cfmMdiMetricsIntMrUnits, cfmMdiMetricsIntMr, 
--    cfmMdiMetricsIntDfScale, cfmMdiMetricsIntDfPrecision, 
--    cfmMdiMetricsIntDf, cfmMdiMetricsIntMlrScale, 
--    cfmMdiMetricsIntMlrPrecision, cfmMdiMetricsIntMlr, 
--    cfmMdiMetricsIntMdc

ciscoMdiMetricsCompliance01 OBJECT IDENTIFIER ::= { ciscoMdiMetricsMIBCompliances 1 }
-- MODULE-COMPLIANCE
--  Status
--    mandatory
--  Descr
--    This compliance statement specifies the minimal requirements an
--    implementation must meet in order to claim full compliance with
--    the definition of the CISCO-MDI-METRICS-MIB.
--  Module
--    >>current<<
--   MandGroup
--    cfmMdiMetricsGroup


END
