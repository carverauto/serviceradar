-- MIB created 4/14/100 12:26:48, by
--   SMIC (the next generation) version 1.6.29, November 22, 1994.

CISCO-ENTITY-PROVISIONING-MIB DEFINITIONS ::= BEGIN

-- From file: "CISCO-ENTITY-PROVISIONING-MIB.my"

IMPORTS
    OBJECT-TYPE
            FROM RFC-1212
    AutonomousType
            FROM SNMPv2-TC-v1
    ciscoMgmt
            FROM CISCO-SMI
    entPhysicalIndex
            FROM ENTITY-MIB;

ciscoEntityProvMIB OBJECT IDENTIFIER ::= { ciscoMgmt 139 }
-- MODULE-IDENTITY
--  LastUpdated
--    9907082052Z
--  OrgName
--    Cisco Systems, Inc.
--  ContactInfo
--    Cisco Systems
--     Customer Service
--    
--     Postal: 170 W Tasman Drive
--     San Jose, CA 95134
--    
--     Tel: +1 800 553-NETS
--    
--     E-mail: cs-dslam@cisco.com
--  Descr
--    This MIB module defines the objects that support provisioning
--    of 'container' class physical entities.  Provisioning sets up
--    a 'container' to hold a specified physical entity.  This allows
--    a management client to configure the specified physical entity,
--    including all of its subordinates physical entities, before
--    installation.
--    
--    Consider a network manager of a CLEC (Competitive Local Exchange
--    Carrier) planning for the installation of the hardware necessary
--    to support several new subscribers.  This network manager wants
--    to pre-configure the ADSL (Asymmetric Digital Subscriber Loop)
--    modems that will support these subscribers, thereby reducing the
--    bring-up time once they arrive.  Under normal circumstances this
--    would not be possible.  However, provisioning allows the network
--    manager to 'create' the physical entities that represent the new
--    modems.  In essence, the device simulates the installation of
--    the new modules into the system.  This has the effect of creating
--    all conceptual rows in all the necessary tables that support the
--    physical entity and all its subordinate physical entities (e.g.,
--    entPhysicalTable, entAliasMappingTable, and ifTable).

ciscoEntityProvMIBObjects OBJECT IDENTIFIER ::= { ciscoEntityProvMIB 1 }
ceProvMIBNotificationsPrefix OBJECT IDENTIFIER ::= { ciscoEntityProvMIB 2 }
ceProvMIBNotifications OBJECT IDENTIFIER ::= { ceProvMIBNotificationsPrefix 0 }
ceProvMIBConformance OBJECT IDENTIFIER ::= { ciscoEntityProvMIB 3 }
ceProvMIBCompliances OBJECT IDENTIFIER ::= { ceProvMIBConformance 1 }
ceProvMIBGroups OBJECT IDENTIFIER ::= { ceProvMIBConformance 2 }

ceProvContainerTable OBJECT-TYPE
    SYNTAX SEQUENCE OF CeProvContainerEntry
    ACCESS not-accessible
    STATUS mandatory
    DESCRIPTION
        "This table extends some entries in the entPhysicalTable
        (see ENTITY-MIB for further details).  A entry appears in
        this table for a physical entity matching the following
        criteria:
        
        1)  Its entPhysicalClass object has a value of 'container';
        
        2)  It can contain one (but not multiple) physical entity;
            and,
        
        3)  It supports provisioning."
    ::= { ciscoEntityProvMIBObjects 1 }

ceProvContainerEntry OBJECT-TYPE
    SYNTAX CeProvContainerEntry
    ACCESS not-accessible
    STATUS mandatory
    DESCRIPTION
        "The attributes that support the provisioning of a physical
        entity of the 'container' class (i.e., a physical entity
        having an entPhysicalClass of 'container')."
    INDEX { entPhysicalIndex }
    ::= { ceProvContainerTable 1 }

CeProvContainerEntry ::= SEQUENCE {
    ceProvContainerStatus INTEGER,
    ceProvContainerEquipped AutonomousType,
    ceProvContainerDetected AutonomousType
    }

ceProvContainerStatus OBJECT-TYPE
    SYNTAX INTEGER {
        unequipped(1),
        provisioned(2),
        mismatched(3),
        invalid(4),
        equipped(5),
        failed(6)
        }
    ACCESS read-only
    STATUS mandatory
    DESCRIPTION
        "This object represents the equipment status of the container:
        
        'unequipped'    The container neither holds a physical entity,
                        nor has it been provisioned to hold a physical
                        entity.
        
        'provisioned'   The container does not hold a physical entity
                        However, it has been provisioned to hold a
                        physical entity of a particular type.  This
                        physical entity appears in the entPhysicalTable
                        as a child of the container.
        
        'mismatched'    The container holds a valid physical entity that
                        does not match the type of physical entity for
                        which the container has been previously
                        provisioned.
        
        'invalid'       The container holds a recognized physical entity
                        that the container is not capable of supporting,
                        or the container holds an unrecognized physical
                        entity.
        
        'equipped'      The container holds a valid physical entity for
                        which the container has been previously
                        provisioned to hold.
        
        'failed'        The container holds a valid physical entity that
                        has become totally inoperable and incapable of
                        providing service."
    ::= { ceProvContainerEntry 1 }

ceProvContainerEquipped OBJECT-TYPE
    SYNTAX AutonomousType
--    Rsyntax OBJECT IDENTIFIER
    ACCESS read-write
    STATUS mandatory
    DESCRIPTION
        "This object specifies the vendor type of the physical entity
        for which this container has been provisioned to hold.  If the
        container has no provisioning, then the value of this object
        is { 0 0 }.
        
        For more information concerning 'vendor type', see the
        definition of the entPhysicalVendorType object in the
        ENTITY-MIB."
    ::= { ceProvContainerEntry 2 }

ceProvContainerDetected OBJECT-TYPE
    SYNTAX AutonomousType
--    Rsyntax OBJECT IDENTIFIER
    ACCESS read-only
    STATUS mandatory
    DESCRIPTION
        "This object specifies the vendor type of the physical entity
        held by the container.  If the container does not hold a
        physical entity, then the value of this object is { 0 0 }.
        
        For more information concerning 'vendor type', see the
        definition of the entPhysicalVendorType object in the
        ENTITY-MIB."
    ::= { ceProvContainerEntry 3 }

ceProvContainerGroup OBJECT IDENTIFIER ::= { ceProvMIBGroups 1 }
-- OBJECT-GROUP
--  Status
--    mandatory
--  Descr
--    A collection of attributes that support provisioning of a
--    physical entity of the 'container' class.
--  objects
--    ceProvContainerStatus, ceProvContainerEquipped, 
--    ceProvContainerDetected

ceProvMIBCompliance OBJECT IDENTIFIER ::= { ceProvMIBCompliances 1 }
-- MODULE-COMPLIANCE
--  Status
--    mandatory
--  Descr
--    The compliance statement for entities that implement the
--    CISCO-ENTITY-PROVISIONING-MIB.  Implementation of this MIB
--    is strongly recommended for any platform targeted for a
--    carrier-class environment.
--  Module
--    >>current<<
--   MandGroup
--    ceProvContainerGroup


END
