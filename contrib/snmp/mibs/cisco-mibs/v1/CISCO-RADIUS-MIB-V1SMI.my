-- MIB file created 10-Jun-2009 11:47:57, by
--   SMICng version 2.2.11-beta(PRO)(Solaris), January 20, 2001. Enterprise key cisco.com

CISCO-RADIUS-MIB DEFINITIONS ::= BEGIN

-- From file: "CISCO-RADIUS-MIB.my"
-- Compile options "4 7 F H N O W 03 06 0B 0G 0N 0T"

IMPORTS
    RowStatus, TruthValue
            FROM SNMPv2-TC-v1
    InetAddressType, InetAddress
            FROM INET-ADDRESS-MIB
    SnmpAdminString
            FROM SNMP-FRAMEWORK-MIB
    TimeIntervalMin, TimeIntervalSec, CiscoPort
            FROM CISCO-TC
    ciscoMgmt
            FROM CISCO-SMI
    Gauge
            FROM RFC1155-SMI
    OBJECT-TYPE
            FROM RFC-1212
    TRAP-TYPE
            FROM RFC-1215;

ciscoRadiusMIB OBJECT IDENTIFIER ::= { ciscoMgmt 288 }
-- MODULE-IDENTITY
--  LastUpdated
--    200902060000Z
--  OrgName
--    Cisco Systems Inc.
--  ContactInfo
--    Cisco Systems 
--    Customer Service 
--    Postal: 170 W Tasman Drive 
--    San Jose, CA  95134 
--    USA 
--    Tel: +1 800 553 -NETS 
--    E-mail: cs-san@cisco.com
--  Descr
--    MIB module for monitoring and configuring 
--    authentication and logging services using RADIUS 
--    (Remote Authentication Dial In User Service) related  
--    objects. 
--    
--    The RADIUS (RFC2865) framework consists of clients and  
--    servers. A client is responsible for passing user  
--    information to designated RADIUS servers, and then  
--    acting on the response which is returned. 
--    
--    RADIUS server is responsible for receiving user  
--    connection requests, authenticating the user, and then 
--    returning all configuration information necessary for  
--    the client to deliver service to the user. 
--    
--    This MIB module also contains objects for  
--    enabling/disabling telnet and SSH (Secure Shell)  
--    authentication. Secure Shell is program which is used  
--    to log into another machine over a secured session.
--  RevDate
--    200902060000Z
--  RevDescr
--    The following objects have been added 
--    [1] crRadiusServerRTTThldNorm 
--    [2] crRadiusServerRTTThldHi 
--    [3] crRadiusServerRetransThldNorm 
--    [4] crRadiusServerRetransThldHi 
--    [5] crRadiusServerRTTNormNotifEnable 
--    [6] crRadiusServerRTTHiNotifEnable 
--    [7] crRadiusServerRetransNormNotifEnable 
--    [8] crRadiusServerRetransHiNotifEnable 
--    
--    The following notifications have been added 
--    [1] crRadiusServerRTTNormNotif 
--    [2] crRadiusServerRTTHiNotif 
--    [3] crRadiusServerRetransNormNotif 
--    [4] crRadiusServerRetransHiNotif 
--    
--    The following object-groups have been added 
--    [1] crmRadiusServerNotifGroup 
--    [2] crmNotificationControlGroup 
--    [3] crmRadiusServerNotifCntlGroup 
--    
--    The compliance statement ciscoRadiusMIBCompliance3 has been 
--    deprecated by ciscoRadiusMIBCompliance4.
--  RevDate
--    200707220000Z
--  RevDescr
--    Added support of crmRadiusKeepAliveUserGroup.
--  RevDate
--    200701030000Z
--  RevDescr
--    Added support of 
--    crmKeepAliveGroup, 
--    crmAutoInitializeConfigGroup, and 
--    crmAttributesGroup2.
--  RevDate
--    200403030000Z
--  RevDescr
--    Added support of 
--    crRadiusFramedIpAddrIncluded, 
--    crRadiusVlanAssignmentEnabled, 
--    crVlanGroupTable. 
--    
--    Added http(2) bit to crRadiusLoginAuthentication.
--  RevDate
--    200211090000Z
--  RevDescr
--    Removed the TC CiscoRadiusAuthKeyType. 
--    Added new TC CiscoRadiusAuthKey. 
--    Removed the objects crRadiusAuthKeyType and  
--    crRadiusServerKeyType. 
--    Changed the SYNTAX of objects crRadiusAuthKey and  
--    crRadiusServerKey.
--  RevDate
--    200210080000Z
--  RevDescr
--    Initial version of this MIB module.

ciscoRadiusMIBObjects OBJECT IDENTIFIER ::= { ciscoRadiusMIB 1 }
ciscoRadiusMIBConformance OBJECT IDENTIFIER ::= { ciscoRadiusMIB 2 }
crRadiusGenericConfig OBJECT IDENTIFIER ::= { ciscoRadiusMIBObjects 1 }
crRadiusServerConfig OBJECT IDENTIFIER ::= { ciscoRadiusMIBObjects 2 }
crRadiusAttributesConfig OBJECT IDENTIFIER ::= { ciscoRadiusMIBObjects 3 }
crRadiusVlanConfigGroup OBJECT IDENTIFIER ::= { ciscoRadiusMIBObjects 4 }
crRadiusKeepAliveConfig OBJECT IDENTIFIER ::= { ciscoRadiusMIBObjects 5 }
crRadiusServerNotifCntl OBJECT IDENTIFIER ::= { ciscoRadiusMIBObjects 6 }
ciscoRadiusMIBNotifications OBJECT IDENTIFIER ::= { ciscoRadiusMIB 3 }
ciscoRadiusMIBCompliances OBJECT IDENTIFIER ::= { ciscoRadiusMIBConformance 1 }
ciscoRadiusMIBGroups OBJECT IDENTIFIER ::= { ciscoRadiusMIBConformance 2 }

CiscoRadiusAuthKey ::= OCTET STRING(SIZE(0..65))
-- TEXTUAL-CONVENTION
--  Status
--    mandatory
--  Descr
--    The authentication key of a radius server. 
--    The first octet of this object contains the the type of key. 
--    The octets following the first octet contain the key. 
--    If the value of the first object is ascii value 'p', then the 
--    key is in plain text. 
--    If the value of first object is ascii value 'e', the key is  
--    encrypted. 
--    Note that this object has same format as TC DisplayString.

CiscoRadiusRoundTripTimePercent ::= Gauge(1..100)
-- TEXTUAL-CONVENTION
--  DspHint
--    d-2
--  Status
--    mandatory
--  Descr
--    This textual convention represents a round-trip time per 
--    session expressed as a percent of the round-trip time 
--    configured for the RADIUS server.

CiscoRadiusRetransPercent ::= Gauge(1..100)
-- TEXTUAL-CONVENTION
--  DspHint
--    d-2
--  Status
--    mandatory
--  Descr
--    This textual convention represents the number of retransmisions 
--    per session expressed as a percent of the retransmissions 
--    configured for the RADIUS server.

crRadiusLoginAuthentication OBJECT-TYPE
    SYNTAX OCTET STRING(SIZE(1..2))
        -- BITS are:
        --   telnet(0)
        --   console(1)
        --   http(2)
    ACCESS read-write
    STATUS mandatory
    DESCRIPTION
        "The login authentication using RADIUS feature is enabled for 
        telnet/SSH sessions if the 'telnet (0) ' bit is set, and  
        disabled if this bit is reset. 
        
        The login authentication using RADIUS feature is enabled for 
        console sessions if the 'console (1) ' bit is set, and  
        disabled if this bit is reset. 
        
        The login authentication using RADIUS feature is enabled for 
        remote web sessions if the 'http (2) ' bit is set, and  
        disabled if this bit is reset."
    DEFVAL { '00'h }
    ::= { crRadiusGenericConfig 1 }

crRadiusDeadtime OBJECT-TYPE
    SYNTAX TimeIntervalMin(0..1440)
--    Rsyntax Gauge(0..1440)
--  Units
--    minutes
    ACCESS read-write
    STATUS mandatory
    DESCRIPTION
        "Indicates the length of time in minutes that the system will 
        mark the server dead when a RADIUS server does not respond to 
        an authentication request.  During the interval of the dead  
        time, any authentication request that comes up would not be  
        sent to that RADIUS server that was marked as dead. The  
        default value of 0 means that the RADIUS servers will not be 
        marked dead if they do not respond."
    DEFVAL { 0 }
    ::= { crRadiusGenericConfig 2 }

crRadiusAuthKey OBJECT-TYPE
    SYNTAX CiscoRadiusAuthKey
--    Rsyntax OCTET STRING(SIZE(0..65))
    ACCESS read-write
    STATUS mandatory
    DESCRIPTION
        "The key used in encrypting the packets passed between the 
        RADIUS server and the client. This key must match the one  
        configured on the server. 
        
        A zero-length string is always returned when this object is  
        read."
    ::= { crRadiusGenericConfig 3 }

crRadiusTimeout OBJECT-TYPE
    SYNTAX TimeIntervalSec(1..1000)
--    Rsyntax Gauge(1..1000)
--  Units
--    seconds
    ACCESS read-write
    STATUS mandatory
    DESCRIPTION
        "This is the time in seconds between retransmissions to 
        the RADIUS server."
    DEFVAL { 1 }
    ::= { crRadiusGenericConfig 4 }

crRadiusRetransmits OBJECT-TYPE
    SYNTAX Gauge(0..100)
--  Units
--    retransmits
    ACCESS read-write
    STATUS mandatory
    DESCRIPTION
        "The additional number of times the RADIUS server should be 
        tried by the RADIUS client before giving up on the server."
    DEFVAL { 1 }
    ::= { crRadiusGenericConfig 5 }

crRadiusAccountingLogMaxSize OBJECT-TYPE
    SYNTAX Gauge(0..30000)
--  Units
--    bytes
    ACCESS read-write
    STATUS mandatory
    DESCRIPTION
        "The maximum size of the accounting log file in bytes. 
        The log file is stored on local persistent storage at the 
        device. If the size is set to a smaller value than the  
        existing one, then smaller log will be available for view  
        by the user."
    DEFVAL { 30000 }
    ::= { crRadiusGenericConfig 6 }

crRadiusAccountingMethod OBJECT-TYPE
    SYNTAX OCTET STRING(SIZE(1..2))
        -- BITS are:
        --   radius(0)
        --   local(1)
    ACCESS read-write
    STATUS mandatory
    DESCRIPTION
        "The accounting method on the device. If bit 0 
        is set, the accounting method is RADIUS. If bit 1 
        is set, then the accounting method is local. It is 
        possible for the user to set both the bits so that 
        both the RADIUS as well as local accounting methods 
        are used. It is also possible to set none of the  
        methods; in this case the switch will not do any 
        accounting."
    ::= { crRadiusGenericConfig 7 }

crRadiusFramedIpAddrIncluded OBJECT-TYPE
    SYNTAX TruthValue
--    Rsyntax INTEGER {
--        true(1),
--        false(2)
--        }
    ACCESS read-write
    STATUS mandatory
    DESCRIPTION
        "Specifies if Access-Request packets will include 
        Framed-IP-Address attributes."
    ::= { crRadiusAttributesConfig 1 }

crRadiusFramedMtu OBJECT-TYPE
    SYNTAX Gauge
    ACCESS read-write
    STATUS mandatory
    DESCRIPTION
        "Specifies the Framed-MTU attribute value to be sent to 
        the RADIUS server."
    REFERENCE
        "RFC2865: Section 5.12"
    ::= { crRadiusAttributesConfig 2 }

crRadiusServerTableMaxEntries OBJECT-TYPE
    SYNTAX Gauge(0..65536)
    ACCESS read-only
    STATUS mandatory
    DESCRIPTION
        "The maximum number of entries that the agent supports in the 
        crRadiusServerTable."
    ::= { crRadiusServerConfig 1 }

crRadiusServerTable OBJECT-TYPE
    SYNTAX SEQUENCE OF CrRadiusServerEntry
    ACCESS not-accessible
    STATUS mandatory
    DESCRIPTION
        "This table lists RADIUS servers."
    ::= { crRadiusServerConfig 2 }

crRadiusServerEntry OBJECT-TYPE
    SYNTAX CrRadiusServerEntry
    ACCESS not-accessible
    STATUS mandatory
    DESCRIPTION
        "A RADIUS server table entry. 
        
        Users can add/delete entries in this table using object 
        'crRadiusServerRowStatus'.  
        
        An entry cannot be created until following objects are  
        instantiated : 
        - crRadiusServerAddrType 
        - crRadiusServerAddr 
        
        Also, following objects cannot be modified when  
        'crRadiusServerRowStatus' is 'active' : 
        - crRadiusServerAddrType 
        - crRadiusServerAddr 
        
        To modify above objects, the entry must be deleted and  
        re-created with new values of above objects. 
        
        If 'crRadiusServerKey' is not instantiated or is a  
        zero-length string, then value of the object  
        'crRadiusAuthkey' is used as the key to communicate with the 
        corresponding RADIUS server."
    INDEX { crRadiusServerIndex }
    ::= { crRadiusServerTable 1 }

CrRadiusServerEntry ::= SEQUENCE {
    crRadiusServerIndex Gauge,
    crRadiusServerAddrType InetAddressType,
    crRadiusServerAddr InetAddress,
    crRadiusServerAuthPort CiscoPort,
    crRadiusServerAcctPort CiscoPort,
    crRadiusServerKey CiscoRadiusAuthKey,
    crRadiusServerType INTEGER,
    crRadiusServerMode INTEGER,
    crRadiusServerRowStatus RowStatus,
    crRadiusServerRTTThldNorm CiscoRadiusRoundTripTimePercent,
    crRadiusServerRTTThldHi CiscoRadiusRoundTripTimePercent,
    crRadiusServerRetransThldNorm CiscoRadiusRetransPercent,
    crRadiusServerRetransThldHi CiscoRadiusRetransPercent
    }

crRadiusServerIndex OBJECT-TYPE
    SYNTAX Gauge(1..4294967295)
    ACCESS not-accessible
    STATUS mandatory
    DESCRIPTION
        "An arbitrary integer value, greater than zero, and less than 
        and equal to crRadiusServerTableMaxEntries, which identifies 
        a RADIUS Server in this table. 
        The value of this object must be persistent across  
        reboots/reinitialization of the device."
    ::= { crRadiusServerEntry 1 }

crRadiusServerAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "The type of address of the RADIUS Server as specified by 
        object 'crRadiusServerAddr'."
    DEFVAL { ipv4 }
    ::= { crRadiusServerEntry 2 }

crRadiusServerAddr OBJECT-TYPE
    SYNTAX InetAddress
--    Rsyntax OCTET STRING(SIZE(0..255))
    ACCESS read-write
    STATUS mandatory
    DESCRIPTION
        "The address of the RADIUS Server."
    ::= { crRadiusServerEntry 3 }

crRadiusServerAuthPort OBJECT-TYPE
    SYNTAX CiscoPort
--    Rsyntax INTEGER(0..65535)
    ACCESS read-write
    STATUS mandatory
    DESCRIPTION
        "This is the destination UDP port number to which RADIUS 
        authentication messages should be sent. The RADIUS server  
        will not be used for authentication if this port number is  
        0."
    DEFVAL { 1812 }
    ::= { crRadiusServerEntry 4 }

crRadiusServerAcctPort OBJECT-TYPE
    SYNTAX CiscoPort
--    Rsyntax INTEGER(0..65535)
    ACCESS read-write
    STATUS mandatory
    DESCRIPTION
        "This is the destination UDP port number to which RADIUS 
        accounting messages should be sent."
    DEFVAL { 1813 }
    ::= { crRadiusServerEntry 5 }

crRadiusServerKey OBJECT-TYPE
    SYNTAX CiscoRadiusAuthKey
--    Rsyntax OCTET STRING(SIZE(0..65))
    ACCESS read-write
    STATUS mandatory
    DESCRIPTION
        "The key used in encrypting the packets passed between the 
        RADIUS server and the client. This key must match the one  
        configured on the server. 
        
        A zero-length string is always returned when this object is  
        read. 
        
        Note that if this object is a zero length string, then  
        'crRadiusAuthKey' is used as the key for this server."
    DEFVAL { '00000000'H }
    ::= { crRadiusServerEntry 6 }

crRadiusServerType OBJECT-TYPE
    SYNTAX INTEGER {
        other(1),
        primary(2)
        }
    ACCESS read-write
    STATUS mandatory
    DESCRIPTION
        "Type of the RADIUS server. 
        other (1),  - a lower priority server 
        primary (2) - the primary server which is tried first 
                       by the RADIUS client."
    DEFVAL { other }
    ::= { crRadiusServerEntry 7 }

crRadiusServerMode OBJECT-TYPE
    SYNTAX INTEGER {
        none(1),
        authAndAcct(2),
        authOnly(3),
        acctOnly(4)
        }
    ACCESS read-write
    STATUS mandatory
    DESCRIPTION
        "Mode of the RADIUS server. 
        none (1)        - neither authentication nor 
                          accounting  
        authAndAcct (2) - both authentication and  
                          accounting 
        authOnly (3)    - only for authentication 
        acctOnly (4)    - only for accounting."
    DEFVAL { authAndAcct }
    ::= { crRadiusServerEntry 8 }

crRadiusServerRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Status of this row."
    ::= { crRadiusServerEntry 9 }

crRadiusServerRTTThldNorm OBJECT-TYPE
    SYNTAX CiscoRadiusRoundTripTimePercent
--    Rsyntax Gauge(1..100)
--  Units
--    percent
    ACCESS read-write
    STATUS mandatory
    DESCRIPTION
        "This object represents the normal threshold on the 
        round-trip time of RADIUS authentication messages. This is 
        measured as a percentage of configured round-trip time as per 
        RFC-2865. If the round-trip time is less than or equal to this 
        threshold, the agent generates the crRadiusServerRTTNormNotif 
        notification. The value configured through this object should 
        never be greater than that configured through 
        crRadiusServerRTTThldHi."
    ::= { crRadiusServerEntry 10 }

crRadiusServerRTTThldHi OBJECT-TYPE
    SYNTAX CiscoRadiusRoundTripTimePercent
--    Rsyntax Gauge(1..100)
--  Units
--    percent
    ACCESS read-write
    STATUS mandatory
    DESCRIPTION
        "This object represents the high threshold on the round-trip 
        time of RADIUS authentication messages. This is measured as a 
        percentage of configured round-trip time as per RFC-2865. If the 
        round-trip time is greater than or equal to this threshold, the 
        agent generates the crRadiusServerRTTHiNotif notification. The 
        value configured through this object should never be smaller 
        than that configured through crRadiusServerRTTThldNorm."
    ::= { crRadiusServerEntry 11 }

crRadiusServerRetransThldNorm OBJECT-TYPE
    SYNTAX CiscoRadiusRetransPercent
--    Rsyntax Gauge(1..100)
--  Units
--    percent
    ACCESS read-write
    STATUS mandatory
    DESCRIPTION
        "This object represents the normal threshold on the 
        retransmitted RADIUS authentication messages per session. This 
        is measured as a percentage of crRadiusRetransmits. If the 
        number of retransmits is less than or equal to this threshold, 
        the agent generates the crRadiusServerRetransNormNotif 
        notification. The value configured through this object should 
        never be greater than that configured through 
        crRadiusServerRetransThldHi."
    ::= { crRadiusServerEntry 12 }

crRadiusServerRetransThldHi OBJECT-TYPE
    SYNTAX CiscoRadiusRetransPercent
--    Rsyntax Gauge(1..100)
--  Units
--    percent
    ACCESS read-write
    STATUS mandatory
    DESCRIPTION
        "This object represents the high threshold on the retransmitted 
        RADIUS authentication messages per session. This is measured as 
        a percentage of crRadiusRetransmits. If the number of 
        retransmits is greater than or equal to this threshold, the 
        agent generates the crRadiusServerRetransHiNotif notification. 
        The value configured through this object should never be smaller 
        than that configured through crRadiusServerRetransThldNorm."
    ::= { crRadiusServerEntry 13 }

crRadiusVlanAssignmentEnabled OBJECT-TYPE
    SYNTAX TruthValue
--    Rsyntax INTEGER {
--        true(1),
--        false(2)
--        }
    ACCESS read-write
    STATUS mandatory
    DESCRIPTION
        "Specifies if VLANs will be assigned by RADIUS server 
        via the tunnel attribute during the authentication."
    ::= { crRadiusVlanConfigGroup 1 }

crVlanGroupTable OBJECT-TYPE
    SYNTAX SEQUENCE OF CrVlanGroupEntry
    ACCESS not-accessible
    STATUS mandatory
    DESCRIPTION
        "A table containing VLAN Group Mapping information for the 
        purpose of distributing users across multiple VLANs which 
        have the same group name."
    ::= { crRadiusVlanConfigGroup 2 }

crVlanGroupEntry OBJECT-TYPE
    SYNTAX CrVlanGroupEntry
    ACCESS not-accessible
    STATUS mandatory
    DESCRIPTION
        "An entry containing an VLAN Group Mapping information 
        applicable to a particular VLAN. Entries in this table can 
        be created or deleted using cpaeVlanGroupRowStatus object."
    INDEX { crVlanGroupName }
    ::= { crVlanGroupTable 1 }

CrVlanGroupEntry ::= SEQUENCE {
    crVlanGroupName SnmpAdminString,
    crVlanGroupVlansLow OCTET STRING,
    crVlanGroupVlansHigh OCTET STRING,
    crVlanGroupRowStatus RowStatus
    }

crVlanGroupName OBJECT-TYPE
    SYNTAX SnmpAdminString
--    Rsyntax OCTET STRING(SIZE(0..255))
    ACCESS not-accessible
    STATUS mandatory
    DESCRIPTION
        "Specifies the name of the VLAN group."
    ::= { crVlanGroupEntry 1 }

crVlanGroupVlansLow OBJECT-TYPE
    SYNTAX OCTET STRING(SIZE(0..256))
    ACCESS read-write
    STATUS mandatory
    DESCRIPTION
        "A string of octets containing one bit per VLAN for VLANs 
        with VlanIndex value of 0 to 2047.  
        
        Each octet within this value specifies a set of eight 
        VLANs, with the first octet specifying VLANs 0 through 
        7, the second octet specifying VLANs 8 through 15, etc. 
        Within each octet, the most significant bit represents 
        the lowest numbered VLAN, and the least significant bit 
        represents the highest numbered VLAN. Thus, each VLAN 
        of the device is represented by a single bit within 
        the value of this object. If that bit has a value of 
        '1' then that VLAN is included in the group; the VLAN 
        is not mapped to the group if its bit has a value of 
        '0'."
    ::= { crVlanGroupEntry 2 }

crVlanGroupVlansHigh OBJECT-TYPE
    SYNTAX OCTET STRING(SIZE(0..256))
    ACCESS read-write
    STATUS mandatory
    DESCRIPTION
        "A string of octets containing one bit per VLAN for VLANs 
        with VlanIndex value of 2048 to 4095.  
        
        Each octet within this value specifies a set of eight 
        VLANs, with the first octet specifying VLANs 2048 through 
        2055, the second octet specifying VLANs 2056 through 2063, 
        etc. Within each octet, the most significant bit represents 
        the lowest numbered VLAN, and the least significant bit 
        represents the highest numbered VLAN. Thus, each VLAN 
        of the device is represented by a single bit within 
        the value of this object. If that bit has a value of 
        '1' then that VLAN is included in the group; the VLAN 
        is not mapped to the group if its bit has a value of 
        '0'."
    ::= { crVlanGroupEntry 3 }

crVlanGroupRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to manage the creation and deletion 
        of rows in this table. 
        
        The only way to create an entry is by setting the value 
        createAndGo(4), and the only way to delete an entry is by 
        setting the value destroy(6) to this object."
    ::= { crVlanGroupEntry 4 }

crRadiusKeepAliveEnabled OBJECT-TYPE
    SYNTAX TruthValue
--    Rsyntax INTEGER {
--        true(1),
--        false(2)
--        }
    ACCESS read-write
    STATUS mandatory
    DESCRIPTION
        "Specifies whether RADIUS keep-alive feature is 
        enabled or not."
    ::= { crRadiusKeepAliveConfig 1 }

crRadiusKeepAliveInterval OBJECT-TYPE
    SYNTAX Gauge
--  Units
--    seconds
    ACCESS read-write
    STATUS mandatory
    DESCRIPTION
        "Specifies the RADIUS keep-alive interval value. When the 
        object value of crRadiusKeepAliveEnabled is 'true', 
        a tracking message is sent to every configured RADIUS 
        server at the interval of crRadiusKeepAliveInterval to 
        query the status of the server."
    ::= { crRadiusKeepAliveConfig 2 }

crRadiusKeepAliveServerTable OBJECT-TYPE
    SYNTAX SEQUENCE OF CrRadiusKeepAliveServerEntry
    ACCESS not-accessible
    STATUS mandatory
    DESCRIPTION
        "This table contains the keep-alive information on 
        every RADIUS server configured on the system."
    ::= { crRadiusKeepAliveConfig 3 }

crRadiusKeepAliveServerEntry OBJECT-TYPE
    SYNTAX CrRadiusKeepAliveServerEntry
    ACCESS not-accessible
    STATUS mandatory
    DESCRIPTION
        "An entry containing keep-alive information of a 
        corresponding RADIUS server configured in 
        crRadiusServerTable."
    INDEX { crRadiusServerIndex }
    ::= { crRadiusKeepAliveServerTable 1 }

CrRadiusKeepAliveServerEntry ::= SEQUENCE {
    crRadiusKeepAliveServerStatus INTEGER
    }

crRadiusKeepAliveServerStatus OBJECT-TYPE
    SYNTAX INTEGER {
        other(1),
        init(2),
        active(3),
        checkup(4),
        dead(5)
        }
    ACCESS read-only
    STATUS mandatory
    DESCRIPTION
        "Indicates the current keep-alive status of the RADIUS server. 
        
        other  : none of the following. 
        init   : the server is in init state. 
        active : the server is in active state. 
        checkup: the server is in checkup state. 
        dead   : the server is in dead state. 
        
        This object is only instantiated when the corresponding  
        instance value of crRadiusServerRowStatus is 'active' and  
        the object value of crRadiusKeepAliveEnabled is 'true'."
    ::= { crRadiusKeepAliveServerEntry 1 }

crRadiusPortAutoInitialize OBJECT-TYPE
    SYNTAX TruthValue
--    Rsyntax INTEGER {
--        true(1),
--        false(2)
--        }
    ACCESS read-write
    STATUS mandatory
    DESCRIPTION
        "Specifies whether a port's state machines will be re- 
        initialized if their state machines are in 'aaaFail'  
        when a RADIUS server becomes available."
    ::= { crRadiusKeepAliveConfig 4 }

crRadiusKeepAliveUserName OBJECT-TYPE
    SYNTAX SnmpAdminString
--    Rsyntax OCTET STRING(SIZE(0..255))
    ACCESS read-write
    STATUS mandatory
    DESCRIPTION
        "Specifies the user name used in keep-alive communication 
        with RADIUS server."
    ::= { crRadiusKeepAliveConfig 5 }

crRadiusServerRTTNormNotifEnable OBJECT-TYPE
    SYNTAX TruthValue
--    Rsyntax INTEGER {
--        true(1),
--        false(2)
--        }
    ACCESS read-write
    STATUS mandatory
    DESCRIPTION
        "This object is used to control the generation of 
        crRadiusServerRTTNormNotif notification.  A value of 'true' 
        indicates that the notification will be generated when the 
        current server round-trip time is less than or equal to 
        crRadiusServerRTTThldNorm."
    DEFVAL { false }
    ::= { crRadiusServerNotifCntl 1 }

crRadiusServerRTTHiNotifEnable OBJECT-TYPE
    SYNTAX TruthValue
--    Rsyntax INTEGER {
--        true(1),
--        false(2)
--        }
    ACCESS read-write
    STATUS mandatory
    DESCRIPTION
        "This object is used to control the generation of 
        crRadiusServerRTTHiNotif notification.  A value of 'true' 
        indicates that the notification will be generated when the 
        current server round-trip time is greater than or equal to 
        crRadiusServerRTTThldHi."
    DEFVAL { false }
    ::= { crRadiusServerNotifCntl 2 }

crRadiusServerRetransNormNotifEnable OBJECT-TYPE
    SYNTAX TruthValue
--    Rsyntax INTEGER {
--        true(1),
--        false(2)
--        }
    ACCESS read-write
    STATUS mandatory
    DESCRIPTION
        "This object is used to control the generation of 
        crRadiusServerRetransNormNotif notification.  A value of 'true' 
        indicates that the notification will be generated when the 
        current number of server retransmissions are less than or 
        equal to crRadiusServerRetransThldNorm."
    DEFVAL { false }
    ::= { crRadiusServerNotifCntl 3 }

crRadiusServerRetransHiNotifEnable OBJECT-TYPE
    SYNTAX TruthValue
--    Rsyntax INTEGER {
--        true(1),
--        false(2)
--        }
    ACCESS read-write
    STATUS mandatory
    DESCRIPTION
        "This object is used to control the generation of 
        crRadiusServerRetransHiNotif notification.  A value of 'true' 
        indicates that the notification will be generated when the 
        current number of server retransmissions are greater than or 
        equal to crRadiusServerRetransThldHi."
    DEFVAL { false }
    ::= { crRadiusServerNotifCntl 4 }

crRadiusServerRTTNormNotif TRAP-TYPE
--?? Non-reverse mappable trap
    ENTERPRISE ciscoRadiusMIBNotifications
    VARIABLES {
        crRadiusServerRTTThldNorm, crRadiusServerAddr, 
        crRadiusServerAuthPort }
--  Status
--    mandatory
    DESCRIPTION
        "This notification indicates that the current server round-trip 
        time is less than or equal to crRadiusServerRTTThldNorm. Once 
        sent, this notification will be disarmed until the round-trip 
        time exceeds the value configured through 
        crRadiusServerRTTThldHi."
    ::= 1

crRadiusServerRTTHiNotif TRAP-TYPE
--?? Non-reverse mappable trap
    ENTERPRISE ciscoRadiusMIBNotifications
    VARIABLES {
        crRadiusServerRTTThldHi, crRadiusServerAddr, 
        crRadiusServerAuthPort }
--  Status
--    mandatory
    DESCRIPTION
        "This notification indicates that the current server round-trip 
        time is greater than or equal to crRadiusServerRTTThldHi. Once 
        sent, this notification will be disarmed until the round-trip 
        time falls below the value configured through 
        crRadiusServerRTTThldNorm."
    ::= 2

crRadiusServerRetransNormNotif TRAP-TYPE
--?? Non-reverse mappable trap
    ENTERPRISE ciscoRadiusMIBNotifications
    VARIABLES {
        crRadiusServerRetransThldNorm, crRadiusServerAddr, 
        crRadiusServerAuthPort }
--  Status
--    mandatory
    DESCRIPTION
        "This notification indicates that the current number of server 
        retransmissions are less than or equal to 
        crRadiusServerRetransThldNorm. Once sent, this notification will 
        be disarmed until the number of retransmissions exceed the value 
        configured through crRadiusServerRetransThldHi."
    ::= 3

crRadiusServerRetransHiNotif TRAP-TYPE
--?? Non-reverse mappable trap
    ENTERPRISE ciscoRadiusMIBNotifications
    VARIABLES {
        crRadiusServerRetransThldHi, crRadiusServerAddr, 
        crRadiusServerAuthPort }
--  Status
--    mandatory
    DESCRIPTION
        "This notification indicates that the current number of server 
        retransmissions are greater than or equal to 
        crRadiusServerRetransThldHi. Once sent, this notification will 
        be disarmed until the number of retransmissions falls below the 
        value configured through crRadiusServerRetransThldNorm."
    ::= 4

crmConfigurationGroup OBJECT IDENTIFIER ::= { ciscoRadiusMIBGroups 1 }
-- OBJECT-GROUP
--  Status
--    mandatory
--  Descr
--    A collection of objects for RADIUS configuration.
--  objects
--    crRadiusLoginAuthentication, crRadiusAuthKey, crRadiusTimeout, 
--    crRadiusRetransmits, crRadiusDeadtime, 
--    crRadiusAccountingLogMaxSize, crRadiusAccountingMethod, 
--    crRadiusServerTableMaxEntries, crRadiusServerAddrType, 
--    crRadiusServerAddr, crRadiusServerAuthPort, 
--    crRadiusServerAcctPort, crRadiusServerKey, crRadiusServerType, 
--    crRadiusServerMode, crRadiusServerRowStatus

crmAttributesGroup OBJECT IDENTIFIER ::= { ciscoRadiusMIBGroups 2 }
-- OBJECT-GROUP
--  Status
--    mandatory
--  Descr
--    A collection of objects for RADIUS attributes 
--    configuration.
--  objects
--    crRadiusFramedIpAddrIncluded

crmVlanConfigGroup OBJECT IDENTIFIER ::= { ciscoRadiusMIBGroups 3 }
-- OBJECT-GROUP
--  Status
--    mandatory
--  Descr
--    A collection of objects for RADIUS Vlans assignment 
--    configuration.
--  objects
--    crRadiusVlanAssignmentEnabled, crVlanGroupVlansLow, 
--    crVlanGroupVlansHigh, crVlanGroupRowStatus

crmKeepAliveGroup OBJECT IDENTIFIER ::= { ciscoRadiusMIBGroups 4 }
-- OBJECT-GROUP
--  Status
--    mandatory
--  Descr
--    A collection of objects for RADIUS keep-alive 
--    information.
--  objects
--    crRadiusKeepAliveEnabled, crRadiusKeepAliveInterval, 
--    crRadiusKeepAliveServerStatus

crmAutoInitializeConfigGroup OBJECT IDENTIFIER ::= { ciscoRadiusMIBGroups 5 }
-- OBJECT-GROUP
--  Status
--    mandatory
--  Descr
--    A collection of objects for RADIUS auto initialize 
--    configuration.
--  objects
--    crRadiusPortAutoInitialize

crmAttributesGroup2 OBJECT IDENTIFIER ::= { ciscoRadiusMIBGroups 6 }
-- OBJECT-GROUP
--  Status
--    mandatory
--  Descr
--    A collection of additional objects for RADIUS 
--    attributes configuration.
--  objects
--    crRadiusFramedMtu

crmRadiusKeepAliveUserGroup OBJECT IDENTIFIER ::= { ciscoRadiusMIBGroups 7 }
-- OBJECT-GROUP
--  Status
--    mandatory
--  Descr
--    A collection of objects for RADIUS keep-alive 
--    user configuration.
--  objects
--    crRadiusKeepAliveUserName

crmConfigurationGroupSup1 OBJECT IDENTIFIER ::= { ciscoRadiusMIBGroups 9 }
-- OBJECT-GROUP
--  Status
--    mandatory
--  Descr
--    This group supplements crmConfigurationGroup, to 
--    configure the thresholds on the round-trip times and 
--    retransmission counts.
--  objects
--    crRadiusServerRTTThldNorm, crRadiusServerRTTThldHi, 
--    crRadiusServerRetransThldNorm, crRadiusServerRetransThldHi

crmRadiusServerNotifCntlGroup OBJECT IDENTIFIER ::= { ciscoRadiusMIBGroups 10 }
-- OBJECT-GROUP
--  Status
--    mandatory
--  Descr
--    This collection of objects control the generation of 
--    notifications related to RADIUS server.
--  objects
--    crRadiusServerRTTNormNotifEnable, 
--    crRadiusServerRTTHiNotifEnable, 
--    crRadiusServerRetransNormNotifEnable, 
--    crRadiusServerRetransHiNotifEnable

crmRadiusServerNotifGroup OBJECT IDENTIFIER ::= { ciscoRadiusMIBGroups 8 }
-- NOTIFICATION-GROUP
--  Status
--    mandatory
--  Descr
--    This collection of notifications is used to monitor the 
--    responsiveness of the RADIUS server.
--  notifications
--    crRadiusServerRTTNormNotif, crRadiusServerRTTHiNotif, 
--    crRadiusServerRetransNormNotif, crRadiusServerRetransHiNotif

ciscoRadiusMIBCompliance OBJECT IDENTIFIER ::= { ciscoRadiusMIBCompliances 1 }
-- MODULE-COMPLIANCE
--  Status
--    deprecated
--  Descr
--    The compliance statement for entities which implement the 
--    CISCO-RADIUS-MIB.
--  Module
--    >>current<<
--   MandGroup
--    crmConfigurationGroup
--   ObjVar
--    crRadiusTimeout
--   ObjVar
--    crRadiusRetransmits
--   ObjVar
--    crRadiusServerAddrType
--   ObjVar
--    crRadiusServerRowStatus
--   ObjVar
--    crRadiusDeadtime

ciscoRadiusMIBCompliance2 OBJECT IDENTIFIER ::= { ciscoRadiusMIBCompliances 2 }
-- MODULE-COMPLIANCE
--  Status
--    deprecated
--  Descr
--    The compliance statement for entities which implement the 
--    CISCO-RADIUS-MIB.
--  Module
--    >>current<<
--   MandGroup
--    crmConfigurationGroup
--   OptGroup
--    crmAttributesGroup
--   OptGroup
--    crmKeepAliveGroup
--   OptGroup
--    crmAutoInitializeConfigGroup
--   OptGroup
--    crmAttributesGroup2
--   ObjVar
--    crRadiusTimeout
--   ObjVar
--    crRadiusRetransmits
--   ObjVar
--    crRadiusServerAddrType
--   ObjVar
--    crRadiusServerRowStatus
--   ObjVar
--    crRadiusDeadtime

ciscoRadiusMIBCompliance3 OBJECT IDENTIFIER ::= { ciscoRadiusMIBCompliances 3 }
-- MODULE-COMPLIANCE
--  Status
--    deprecated
--  Descr
--    The compliance statement for entities which implement the 
--    CISCO-RADIUS-MIB.
--  Module
--    >>current<<
--   MandGroup
--    crmConfigurationGroup
--   OptGroup
--    crmAttributesGroup
--   OptGroup
--    crmKeepAliveGroup
--   OptGroup
--    crmAutoInitializeConfigGroup
--   OptGroup
--    crmAttributesGroup2
--   OptGroup
--    crmVlanConfigGroup
--   OptGroup
--    crmRadiusKeepAliveUserGroup
--   ObjVar
--    crRadiusTimeout
--   ObjVar
--    crRadiusRetransmits
--   ObjVar
--    crRadiusServerAddrType
--   ObjVar
--    crRadiusServerRowStatus
--   ObjVar
--    crRadiusDeadtime

ciscoRadiusMIBCompliance4 OBJECT IDENTIFIER ::= { ciscoRadiusMIBCompliances 4 }
-- MODULE-COMPLIANCE
--  Status
--    mandatory
--  Descr
--    The compliance statement for entities which implement the 
--    CISCO-RADIUS-MIB.
--  Module
--    >>current<<
--   MandGroup
--    crmConfigurationGroup
--   MandGroup
--    crmConfigurationGroupSup1
--   MandGroup
--    crmRadiusServerNotifGroup
--   MandGroup
--    crmRadiusServerNotifCntlGroup
--   OptGroup
--    crmAttributesGroup
--   OptGroup
--    crmKeepAliveGroup
--   OptGroup
--    crmAutoInitializeConfigGroup
--   OptGroup
--    crmAttributesGroup2
--   OptGroup
--    crmVlanConfigGroup
--   OptGroup
--    crmRadiusKeepAliveUserGroup
--   ObjVar
--    crRadiusTimeout
--   ObjVar
--    crRadiusRetransmits
--   ObjVar
--    crRadiusServerAddrType
--   ObjVar
--    crRadiusServerRowStatus
--   ObjVar
--    crRadiusDeadtime


END
