-- MIB file created 20-Jun-2007 17:13:15, by
--   SMICng version 2.2.11-beta(PRO)(Solaris), January 20, 2001. Enterprise key cisco.com

CISCO-LWAPP-DOT11-CLIENT-CCX-TC-MIB DEFINITIONS ::= BEGIN

-- From file: "CISCO-LWAPP-DOT11-CLIENT-CCX-TC-MIB.my"
-- Compile options "4 7 F H N O W 03 06 0B 0G 0N 0T"

IMPORTS
    ciscoMgmt
            FROM CISCO-SMI;

ciscoLwappDot11ClientCCXTextualConventions OBJECT IDENTIFIER ::= { ciscoMgmt 611 }
-- MODULE-IDENTITY
--  LastUpdated
--    200703220000Z
--  OrgName
--    Cisco Systems Inc.
--  ContactInfo
--    Cisco Systems,
--    Customer Service
--    
--    Postal: 170 West Tasman Drive
--    San Jose, CA  95134
--    USA
--    
--    Tel: +1 800 553-NETS
--    
--    Email: cs-wnbu-snmp@cisco.com
--  Descr
--    This module defines the textual conventions used
--    throughout the Cisco enterprise MIBs designed for
--    implementation on Central Controllers (CC) that
--    terminate the Light Weight Access Point Protocol
--    tunnel from Light-weight LWAPP Access Points, 
--    specifically for the functions of the Cisco Client 
--    Extensions (CCX) program.
--    
--    This MIB provides textual conventions used in the
--    configuration and status information mibs
--    about the CCX clients that the controller is aware of.
--    
--    
--             GLOSSARY
--    
--    Light Weight Access Point Protocol ( LWAPP )
--    
--    This is a generic protocol that defines the
--    communication between the Access Points and the
--    Central Controller.
--    
--    Mobile Node ( MN )
--    
--    A roaming 802.11 wireless device in a wireless
--    network associated with an access point. Mobile Node,
--    Mobile Station(Ms) and client are used
--    interchangeably.
--    
--    Cisco Client eXtentions (CCX)
--    The Cisco Client Extensions (CCX) Program is a 
--    program of working through silicon providers to 
--    embed Cisco client technology in wireless client 
--    reference designs, and to promote compliant and 
--    interoperable third-party clients with Cisco's 
--    infrastructure, thus further driving wireless adoption 
--    in the market.  
--    
--    Extensible Authentication Protocol (EAP) 
--    
--    The Extensible Authentication Protocol (EAP) is an 
--    Internet Engineering Task Force (IETF) standard that 
--    provides an infrastructure for network access clients and 
--    authentication servers to host plug-in modules for current
--    and future authentication methods and technologies.
--    
--    Wired Equivalent Privacy (WEP) 
--    
--    A security method defined by 802.11. WEP uses a  
--    symmetric key stream cipher called RC4 to encrypt the data
--    packets. 
--    
--    
--    
--    REFERENCE
--    
--    [1] Part 11 Wireless LAN Medium Access Control ( MAC )
--    and Physical Layer ( PHY ) Specifications.
--    
--    [2] Draft-obara-capwap-lwapp-00.txt, IETF Light 
--    Weight Access Point Protocol. 
--    
--    [3] Cisco Compatible Extensions for WLAN Devices
--    Version 5.0.11
--  RevDate
--    200703220000Z
--  RevDescr
--    Added 2 more radio types to CiscoLwappDot11ClientRadioType.
--  RevDate
--    200702220000Z
--  RevDescr
--    Reverted some of the enum names to be in line with the CCXV5
--    spec.
--  RevDate
--    200702190000Z
--  RevDescr
--    Incorporated review comments.
--  RevDate
--    200701300000Z
--  RevDescr
--    Initial version of this  mib module.

CiscoLwappDot11ClientReqStatus ::= INTEGER {
        initiate(1),
        inProgress(2),
        success(3),
        failure(4),
        requestNotProcessedByClient(5)
        }
-- TEXTUAL-CONVENTION
--  Status
--    mandatory
--  Descr
--    This field indicates the status of current request.The values
--    used can be one of the following:
--    
--        initiate - this will be used to trigger a request to get 
--        some parameters from a CCX client.
--    
--        inProgress - this indicates that the request to get the 
--        details from the client is still in progress.
--    
--        success - indicates that the query was executed 
--        successfully. 
--    
--        failed -  this indicates that the request to get some 
--        parameters from a CCX client failed.
--    
--        requestNotProcessedByClient - indicates that the CCX client
--        did not honour this request.

CiscoLwappDot11ClientSSId ::= OCTET STRING(SIZE(1..32))
-- TEXTUAL-CONVENTION
--  Status
--    mandatory
--  Descr
--    This represents the Service Set Identifier assigned
--    to WLAN.

CiscoLwappDot11ClientAuthMethod ::= INTEGER {
        --?? enum value of zero may cause problems
        none(0),
        preSharedKey(1),
        eap(2),
        unknown(255)
        }
-- TEXTUAL-CONVENTION
--  Status
--    mandatory
--  Descr
--    This is the authentication method used by the client.
--    The possible values are:
--       none - this indicates that no authentication method is
--       used
--    
--       preSharedKey - this refers to the method of using pre
--       shared key for authentication
--    
--       eap - this is Extensible Authentication Protocol 
--    
--       unknown - this indicates an authentication protocol other
--       than the ones defined above

CiscoLwappDot11ClientEAPMethod ::= INTEGER {
        --?? enum value of zero may cause problems
        leap(0),
        eapFast(1),
        eapTls(2),
        eapTtls(3),
        peap0EapMschap2(4),
        peap1EapGtc(5),
        eapMd5(6),
        eapSim(7),
        preSharedKey(8),
        unknown(255)
        }
-- TEXTUAL-CONVENTION
--  Status
--    mandatory
--  Descr
--    This identifies the Extensible Authentication Protocol(EAP)
--    method used. The possible values are:
--    
--       leap - this is Lightweight Extensible Authentication 
--       Protocol
--    
--       eapFast - this is Extensible Authentication 
--       Protocol with Flexible Authentication via Secure Tunneling
--    
--       eapTls - this is Extensible Authentication
--       Protocol with Transport Layer Security
--    
--       eapTtls - this is Extensible Authentication Protocol with
--       Tunneled Transport Layer Security
--    
--       peap0EapMschap2 - this refers to Protected Extensible 
--       Authentication Protocol Version 0 with Microsoft 
--       Challenge Handshake Authentication Protocol version 2
--    
--       peap1EapGtc - this refers to Protected Extensible 
--       Authentication Protocol Version 1 with Generic Token Card
--    
--       eapMd5 - this is Extensible Authentication Protocol with
--       Message-Digest algorithm 5
--    
--       eapSim - this is Extensible Authentication Protocol using 
--       the Global System for Mobile Communications (GSM) 
--       Subscriber Identity Module (SIM)
--    
--       preSharedKey - this refers to the method of using pre
--       shared key for authentication
--    
--       unknown - this indicates an EAP method other
--       than the ones defined above

CiscoLwappDot11ClientKeyMgmtMethod ::= INTEGER {
        --?? enum value of zero may cause problems
        none(0),
        staticWep(1),
        dynamicWep(2),
        wpa(3),
        wpaCckm(4),
        wpa2(5),
        wpa2Cckm(6),
        cckm(7),
        unknown(255)
        }
-- TEXTUAL-CONVENTION
--  Status
--    mandatory
--  Descr
--    This is the key management method used by the client.
--    The possible values are:
--    
--       staticWep - this is Wired Equivalent Privacy with a static
--       key defined
--    
--       dynamicWep - this is Wired Equivalent Privacy with a 
--       dynamic key
--    
--       wpa - this indicates wifi protected access
--    
--       wpaCckm - this is wifi protected access with 
--       Cisco Centralized Key Management
--    
--       wpa2 - this indicates version 2 of wifi protected access
--    
--       wpa2Cckm - this is wifi protected access  
--       version 2 with Cisco Centralized Key Management
--    
--       cckm - this indicates Cisco Centralized Key 
--       Management
--    
--       unknown - this indicates a key management method other
--       than the ones defined above

CiscoLwappDot11ClientEncryptionMethod ::= INTEGER {
        --?? enum value of zero may cause problems
        none(0),
        wep40(1),
        wep104(2),
        tkip(3),
        ckip(4),
        aesCcmp(5),
        unknown(255)
        }
-- TEXTUAL-CONVENTION
--  Status
--    mandatory
--  Descr
--    This is the encryption method used  by the client.
--    The possible values are:
--    
--       none - no encryption is used
--    
--       wep40 - this is Wired Equivalent Privacy with a 40 bit 
--       secret key
--    
--       wep104 - this is Wired Equivalent Privacy with a 104 bit
--       secret key
--    
--       tkip - this indicates Temporal Key Integrity
--       Protocol
--    
--       ckip - this is Cisco Key Integrity Protocol
--    
--       aesCcmp - this is Advanced Encryption Standard 
--       - Counter Mode Cipher Block Chaining-Message Authentication 
--       Code Protocol
--    
--       unknown - this indicates an encryption method other
--       than the ones defined above

CiscoLwappDot11ClientCredentialType ::= INTEGER {
        --?? enum value of zero may cause problems
        localSaved(0),
        manuallyPrompted(1),
        hostOsLogin(2),
        unknown(255)
        }
-- TEXTUAL-CONVENTION
--  Status
--    mandatory
--  Descr
--    This indicates how the 802.11 credentials are configured for
--    the client.
--    The possible values are:
--    
--       localSaved - credentials are locally saved
--    
--       manuallyPrompted - client is prompted for the credentials
--    
--       hostOsLogin - this means the host operating system's login
--       credentials will be used
--    
--       unknown - this indicates a credential method other
--       than the ones defined above

CiscoLwappDot11ClientPowerSaveMode ::= INTEGER {
        --?? enum value of zero may cause problems
        awake(0),
        normal(1),
        maxPower(2),
        uApsd(3),
        sApsd(4),
        unknown(255)
        }
-- TEXTUAL-CONVENTION
--  Status
--    mandatory
--  Descr
--    This is the type of power save mode configured on the
--    client. The possible values are:
--    
--       awake - this indicates that the client is constantly awake
--    
--       normal - this indicates normal power save mode
--    
--       maxPower - this indicates maximum power save mode
--    
--       uApsd - this indicates Unsolicited Automatic  
--       Power Save Delivery
--    
--       sApsd - this indicates Solicited Automatic Power  
--       Save Delivery
--    
--       unknown - this indicates a power save mode other
--       than the ones defined above

CiscoLwappDot11ClientTxPowerMode ::= INTEGER {
        --?? enum value of zero may cause problems
        fixed(0),
        automatic(1)
        }
-- TEXTUAL-CONVENTION
--  Status
--    mandatory
--  Descr
--    This field identifies the transmit power mode of the
--    client. The possible values are:
--    
--       fixed - this indicates that the client is operating at a
--       fixed power mode
--    
--       automatic - this indicates that the client power will be
--       determined automatically

CiscoLwappDot11ClientRadioType ::= INTEGER {
        --?? enum value of zero may cause problems
        unused(0),
        fhss(1),
        dsss(2),
        irBaseband(3),
        oFdm(4),
        highRateDsss(5),
        erp(6),
        draft11n2point4Ghz(7),
        draft11n5Ghz(8)
        }
-- TEXTUAL-CONVENTION
--  Status
--    mandatory
--  Descr
--    This is the radio type of the client. The possible values
--    are:
--        unused - this is currently a reserved radio type and is 
--        not used
--    
--        fhss - this is Frequency-hopping spread spectrum based
--        radio
--    
--        dsss - this is Direct Sequence spread spectrum based
--        radio
--    
--        infraRedBaseband - this is infrared baseband based radio
--    
--        oFdm - this is orthogonal frequency division 
--        multiplexing based radio
--    
--        highRateDsss - this is high rate direct sequence spread 
--        spectrum based radio
--    
--        erp - this indicates effective radiated power based radio
--    
--        draft11n2point4Ghz - this indicates a 2.4 Ghz band radio
--        as defined in draft 802.11n
--    
--        draft11n5Ghz - this indicates a 5 Ghz band radio
--        as defined in draft 802.11n

CiscoLwappDot11ClientDataRates ::= OCTET STRING(SIZE(1..2))
        -- BITS are:
        --   mhz1(0)
        --   mhz2(1)
        --   mhz5point5(2)
        --   mhz6(3)
        --   mhz9(4)
        --   mhz11(5)
        --   mhz12(6)
        --   mhz18(7)
        --   mhz24(8)
        --   mhz36(9)
        --   mhz48(10)
        --   mhz54(11)
-- TEXTUAL-CONVENTION
--  Status
--    mandatory
--  Descr
--    This field indicates the data rates supported by a
--    client.  If a data rate is supported by a client, the 
--    corresponding bit is set to 1 else it is 
--    set to 0.  The different data rates (in Mhz) are 1, 2,
--    5.5, 6, 9, 11, 12, 18, 24, 36, 48, 54.


END
