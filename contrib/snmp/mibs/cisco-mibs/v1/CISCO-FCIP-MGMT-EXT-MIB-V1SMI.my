-- MIB file created 05-Apr-2006 13:46:19, by
--   SMICng version 2.2.11-beta(PRO)(Solaris), January 20, 2001. Enterprise key cisco.com

CISCO-FCIP-MGMT-EXT-MIB DEFINITIONS ::= BEGIN

-- From file: "CISCO-FCIP-MGMT-EXT-MIB.my"
-- Compile options "4 7 F H N O W 03 06 0B 0G 0N 0T"

IMPORTS
    SnmpAdminString
            FROM SNMP-FRAMEWORK-MIB
    TruthValue
            FROM SNMPv2-TC-v1
    ciscoMgmt
            FROM CISCO-SMI
    cfmFcipEntityId, cfmFcipEntityId, cfmFcipLinkIndex
            FROM CISCO-FCIP-MGMT-MIB
    CiscoPort
            FROM CISCO-TC
    InetPortNumber
            FROM INET-ADDRESS-MIB
    InterfaceIndex
            FROM IF-MIB
    FcList
            FROM CISCO-ZS-MIB
    Gauge
            FROM RFC1155-SMI
    OBJECT-TYPE
            FROM RFC-1212;

ciscoFcipMgmtExtMIB OBJECT IDENTIFIER ::= { ciscoMgmt 329 }
-- MODULE-IDENTITY
--  LastUpdated
--    200510120000Z
--  OrgName
--    Cisco Systems Inc.
--  ContactInfo
--         Cisco Systems
--          Customer Service
--    Postal: 170 W Tasman Drive
--          San Jose, CA  95134
--          USA
--    Tel: +1 800 553 -NETS
--    E-mail: cs-san@cisco.com
--  Descr
--    A MIB module for extending the CISCO-FCIP-MGMT-MIB
--     to add objects which provide additional information
--     about FCIP interfaces not available in other MIBS. 
--  RevDate
--    200510120000Z
--  RevDescr
--    Added the following objects in cfmFcipLinkExtTable:
--        - cfmFcipLinkExtTapeReadAccOper
--        - cfmFcipLinkExtFiconTAVsanL2k
--        - cfmFcipLinkExtFiconTAVsanL4k
--        - cfmFcipLinkExtFiconTAVsanLOper2k
--        - cfmFcipLinkExtFiconTAVsanLOper4k
--  RevDate
--    200506070000Z
--  RevDescr
--    Added the following objects in cfmFcipLinkExtTable:
--         cfmFcipLinkExtPhyIfIndex,
--         cfmFcipLinkExtWriteAccOper, and
--         cfmFcipLinkExtTapeAccOper.
--     Also added a new table cfmFcipLinkExtStatsTable with
--     objects:
--         cfmFcipLinkStatsRxIPCompRatio and
--         cfmFcipLinkStatsTxIPCompRatio. 
--  RevDate
--    200505140000Z
--  RevDescr
--    Added following objects in cfmFcipLinkExtTable.
--        cfmFcipLinkExtIPSec
--     Added cfmFcipLinkExtGroupRev2Sup1.
--    
--     Added following object in cfmFcipEntityExtTable.
--        cfmFcipEntityExtTcpLocalPort.
--        cfmFcipEntityExtTcpMaxJitter.
--        cfmFcipEntityExtTcpSACKEnable.
--    
--     Added cfmFcipEntityExtGroupSup1.
--    
--     Added cfmFcipExtCompliance4.
--  RevDate
--    200409230000Z
--  RevDescr
--    Added following objects in cfmFcipLinkExtTable.
--        cfmFcipLinkExtTapeAccelerator,
--        cfmFcipLinkExtFlowCtrlBurstSize. 
--    
--     Added cfmFcipLinkMapTable. 
--  RevDate
--    200403100000Z
--  RevDescr
--    Added following objects in cfmFcipEntityExtTable.
--        cfmFcipEntityExtCWMEnable,
--        cfmFcipEntityExtCWMBurstSize. 
--  RevDate
--    200311050000Z
--  RevDescr
--    Removed cfmFcipLinkExtIPCompAlgorithm and renamed
--    object cfmFcipLinkExtIPCompPerf to cfmFcipLinkExtIPComp
--    Added compliance statement for
--    cfmFcipLinkExtTimestampTolerance.
--  RevDate
--    200309190000Z
--  RevDescr
--    Added: cfmFcipLinkExtEthIfIndex,
--     cfmFcipLinkExtWriteAccelerator,
--     cfmFcipLinkExtIPCompAlgorithm,cfmFcipLinkExtIPCompPerf.
--     Updated the Compliance statement. 
--  RevDate
--    200305060000Z
--  RevDescr
--    Modified ranges and added DEFVAL clause to objects: 
--     cfmFcipEntityExtTcpSendBufSize,cfmFcipEntityExtTcpMaxBW,
--     cfmFcipEntityExtTcpMinAvailBW,
--     cfmFcipEntityExtTcpRndTrpTimeEst. 
--  RevDate
--    200303250000Z
--  RevDescr
--    Modified objects: cfmFcipEntityExtTcpKeepAliveTO.
--     Replaced: cfmFcipLinkExtLocalEntityMode with
--     cfmFcipLinkExtLocalBPortEnable. cfmFcipEntityExtTcpInitRTO 
--     with cfmFcipEntityExtTcpMinRTO.
--     Added: cfmFcipEntityExtTcpSendBufSize,
--     cfmFcipEntityExtTcpMaxBW,cfmFcipEntityExtTcpMinAvailBW,
--     cfmFcipEntityExtTcpRndTrpTimeEst,cfmFcipLinkExtCntrlQOSField,
--     cfmFcipLinkExtDataQOSField.
--     Removed cfmFcipEntityExtWindowSize.
--  RevDate
--    200301070000Z
--  RevDescr
--    Added objects cfmFcipLinkExtSpecialFrameEnable,
--     cfmFcipLinkExtBPortKAEnable.
--     Modified the range values for some objects. 
--  RevDate
--    200212060000Z
--  RevDescr
--    Initial version of this MIB module.

ciscoFcipMgmtExtMIBNotifs OBJECT IDENTIFIER ::= { ciscoFcipMgmtExtMIB 0 }
ciscoFcipMgmtExtMIBObjects OBJECT IDENTIFIER ::= { ciscoFcipMgmtExtMIB 1 }
ciscoFcipMgmtExtMIBConform OBJECT IDENTIFIER ::= { ciscoFcipMgmtExtMIB 2 }
cfmFcipMgmtExtConfig OBJECT IDENTIFIER ::= { ciscoFcipMgmtExtMIBObjects 1 }
cfmFcipMgmtExtStats OBJECT IDENTIFIER ::= { ciscoFcipMgmtExtMIBObjects 2 }
cfmFcipExtCompliances OBJECT IDENTIFIER ::= { ciscoFcipMgmtExtMIBConform 1 }
cfmFcipExtGroups OBJECT IDENTIFIER ::= { ciscoFcipMgmtExtMIBConform 2 }

cfmFcipEntityExtTable OBJECT-TYPE
    SYNTAX SEQUENCE OF CfmFcipEntityExtEntry
    ACCESS not-accessible
    STATUS mandatory
    DESCRIPTION
        "A table contains objects which provide more information
         of FCIP entity which is not available in
         CISCO-FCIP-MGMT-MIB. "
    ::= { cfmFcipMgmtExtConfig 1 }

cfmFcipEntityExtEntry OBJECT-TYPE
    SYNTAX CfmFcipEntityExtEntry
    ACCESS not-accessible
    STATUS mandatory
    DESCRIPTION
        "A entry into the cfmFcipEntityExtTable. Each entry
         contains attributes associated with an FCIP entity. "
    INDEX { cfmFcipEntityId }
-- Augments cfmFcipEntityInstanceEntry FROM CISCO-FCIP-MGMT-MIB
    ::= { cfmFcipEntityExtTable 1 }

CfmFcipEntityExtEntry ::= SEQUENCE {
    cfmFcipEntityExtTcpKeepAliveTO Gauge,
    cfmFcipEntityExtTcpMaxReTx Gauge,
    cfmFcipEntityExtPMTUEnable TruthValue,
    cfmFcipEntityExtPMTUResetTO Gauge,
    cfmFcipEntityExtTcpMinRTO Gauge,
    cfmFcipEntityExtTcpSendBufSize Gauge,
    cfmFcipEntityExtTcpMaxBW Gauge,
    cfmFcipEntityExtTcpMinAvailBW Gauge,
    cfmFcipEntityExtTcpRndTrpTimeEst Gauge,
    cfmFcipEntityExtCWMEnable TruthValue,
    cfmFcipEntityExtCWMBurstSize Gauge,
    cfmFcipEntityExtTcpSACKEnable TruthValue,
    cfmFcipEntityExtTcpLocalPort InetPortNumber,
    cfmFcipEntityExtTcpMaxJitter Gauge
    }

cfmFcipEntityExtTcpKeepAliveTO OBJECT-TYPE
    SYNTAX Gauge(1..7200)
--  Units
--    seconds
    ACCESS read-write
    STATUS mandatory
    DESCRIPTION
        "The TCP Keep alive timeout for all links within this
         entity. "
    DEFVAL { 60 }
    ::= { cfmFcipEntityExtEntry 1 }

cfmFcipEntityExtTcpMaxReTx OBJECT-TYPE
    SYNTAX Gauge(1..8)
    ACCESS read-write
    STATUS mandatory
    DESCRIPTION
        "The Maximum number of times that the same item of data
         will be retransmitted over a TCP connection. If delivery
         is not acknowledged after this number of retransmissions
         then the TCP connection is terminated. "
    DEFVAL { 4 }
    ::= { cfmFcipEntityExtEntry 2 }

cfmFcipEntityExtPMTUEnable OBJECT-TYPE
    SYNTAX TruthValue
--    Rsyntax INTEGER {
--        true(1),
--        false(2)
--        }
    ACCESS read-write
    STATUS mandatory
    DESCRIPTION
        "The path MTU discovery is enabled if the value of
        this object is true(1), else it is disabled, and
        has the value false(2). "
    REFERENCE
        "RFC 1191 - Path MTU Discovery"
    DEFVAL { true }
    ::= { cfmFcipEntityExtEntry 3 }

cfmFcipEntityExtPMTUResetTO OBJECT-TYPE
    SYNTAX Gauge(60..3600)
--  Units
--    seconds
    ACCESS read-write
    STATUS mandatory
    DESCRIPTION
        "The time interval for which the discovered pathMTU
        is valid, before MSS reverts back to the negotiated
        TCP value. This object is writeble only if
        cfmFcipEntityExtPMTUEnable is 'true'. "
    DEFVAL { 3600 }
    ::= { cfmFcipEntityExtEntry 4 }

cfmFcipEntityExtTcpMinRTO OBJECT-TYPE
    SYNTAX Gauge(100..5000)
--  Units
--    milliseconds
    ACCESS read-write
    STATUS mandatory
    DESCRIPTION
        "The TCP minimum retransmit timeout for all the links on
         this entity. "
    DEFVAL { 100 }
    ::= { cfmFcipEntityExtEntry 5 }

cfmFcipEntityExtTcpSendBufSize OBJECT-TYPE
    SYNTAX Gauge(0..8192)
--  Units
--    kilobytes
    ACCESS read-write
    STATUS mandatory
    DESCRIPTION
        "The aggregate TCP send window for all TCP connections on all
         Links within this entity. This value is used for Egress
         Flow Control. When the aggregate of the data queued
         on all connections within this entity reaches this value,
         the sender is flow controlled. "
    DEFVAL { 0 }
    ::= { cfmFcipEntityExtEntry 6 }

cfmFcipEntityExtTcpMaxBW OBJECT-TYPE
    SYNTAX Gauge(1000..1000000)
--  Units
--    kilobits
    ACCESS read-write
    STATUS mandatory
    DESCRIPTION
        "This is an estimate of the Bandwidth of the network pipe
        used for the B-D product computation, which lets us derive
        the TCP receive window to advertise.
        The cfmFcipEntityExtTcpMaxBW,cfmFcipEntityExtTcpMinAvailBW,
        cfmFcipEntityExtTcpRndTrpTimeEst must be set in the same
        SNMP set request. SET operation would fail if this object
        is set individually."
    DEFVAL { 1000000 }
    ::= { cfmFcipEntityExtEntry 7 }

cfmFcipEntityExtTcpMinAvailBW OBJECT-TYPE
    SYNTAX Gauge(1000..1000000)
--  Units
--    kilobits
    ACCESS read-write
    STATUS mandatory
    DESCRIPTION
        "The minimum available bandwidth for the TCP connections
        on the Links within this entity.
        The cfmFcipEntityExtTcpMaxBW,cfmFcipEntityExtTcpMinAvailBW,
        cfmFcipEntityExtTcpRndTrpTimeEst must be set in the same
        SNMP set request. SET operation would fail if this object
        is set individually. "
    DEFVAL { 15000 }
    ::= { cfmFcipEntityExtEntry 8 }

cfmFcipEntityExtTcpRndTrpTimeEst OBJECT-TYPE
    SYNTAX Gauge(0..300000)
--  Units
--    microseconds
    ACCESS read-write
    STATUS mandatory
    DESCRIPTION
        "This is an estimate of the round trip delay of the network
         pipe used for the B-D product computation, which lets us
         derive the TCP receive window to advertise.
         The cfmFcipEntityExtTcpMaxBW,cfmFcipEntityExtTcpMinAvailBW,
         cfmFcipEntityExtTcpRndTrpTimeEst must be set in the same
         SNMP set request. SET operation would fail if this object
         is set individually. "
    DEFVAL { 1000 }
    ::= { cfmFcipEntityExtEntry 9 }

cfmFcipEntityExtCWMEnable OBJECT-TYPE
    SYNTAX TruthValue
--    Rsyntax INTEGER {
--        true(1),
--        false(2)
--        }
    ACCESS read-write
    STATUS mandatory
    DESCRIPTION
        "This object is used for enabling/disabling the congestion
         window monitoring. If the value of this object is true(1),
         it is enabled. It is disabled if the value is false(2). "
    REFERENCE
        "Congestion Window Monitoring (Hughes, Touch, and Heidemann)"
    DEFVAL { true }
    ::= { cfmFcipEntityExtEntry 10 }

cfmFcipEntityExtCWMBurstSize OBJECT-TYPE
    SYNTAX Gauge(10..100)
--  Units
--    kilobytes
    ACCESS read-write
    STATUS mandatory
    DESCRIPTION
        "The maximum burst sent after a tcp sender idle
         period. This object is writeble only if
         cfmFcipEntityExtCWMEnable is 'true'. "
    DEFVAL { 50 }
    ::= { cfmFcipEntityExtEntry 11 }

cfmFcipEntityExtTcpSACKEnable OBJECT-TYPE
    SYNTAX TruthValue
--    Rsyntax INTEGER {
--        true(1),
--        false(2)
--        }
    ACCESS read-write
    STATUS mandatory
    DESCRIPTION
        "Setting the value to 'True', enables the Selective
         Acknowledgement (SACK) on this link."
    ::= { cfmFcipEntityExtEntry 12 }

cfmFcipEntityExtTcpLocalPort OBJECT-TYPE
    SYNTAX InetPortNumber
--    Rsyntax Gauge(0..65535)
    ACCESS read-write
    STATUS mandatory
    DESCRIPTION
        "The local TCP port to which the local FCIP entity will
        connect if and when it initiates a TCP connection setup
        for this link."
    ::= { cfmFcipEntityExtEntry 13 }

cfmFcipEntityExtTcpMaxJitter OBJECT-TYPE
    SYNTAX Gauge(0..65535)
--  Units
--    milliseconds
    ACCESS read-write
    STATUS mandatory
    DESCRIPTION
        "The maximum delay variation that is not due to
         congestion that can be experienced by TCP
         connections for all links on this entity."
    DEFVAL { 1 }
    ::= { cfmFcipEntityExtEntry 14 }

cfmFcipLinkExtTable OBJECT-TYPE
    SYNTAX SEQUENCE OF CfmFcipLinkExtEntry
    ACCESS not-accessible
    STATUS mandatory
    DESCRIPTION
        "A table contains objects which provide more information
        of FCIP link which is not available in CISCO-FCIP-MGMT-MIB."
    ::= { cfmFcipMgmtExtConfig 2 }

cfmFcipLinkExtEntry OBJECT-TYPE
    SYNTAX CfmFcipLinkExtEntry
    ACCESS not-accessible
    STATUS mandatory
    DESCRIPTION
        "A entry into cfmFcipLinkExtTable. Each entry
         contains attributes associated with an FCIP Link. "
    INDEX { cfmFcipEntityId, cfmFcipLinkIndex }
-- Augments cfmFcipLinkEntry FROM CISCO-FCIP-MGMT-MIB
    ::= { cfmFcipLinkExtTable 1 }

CfmFcipLinkExtEntry ::= SEQUENCE {
    cfmFcipLinkExtPassiveMode TruthValue,
    cfmFcipLinkExtNumTcpConn Gauge,
    cfmFcipLinkExtCheckTimestamp TruthValue,
    cfmFcipLinkExtTimestampTolerance Gauge,
    cfmFcipLinkExtTcpRemPort CiscoPort,
    cfmFcipLinkExtLocalBPortEnable TruthValue,
    cfmFcipLinkExtSpecialFrameEnable TruthValue,
    cfmFcipLinkExtBPortKAEnable TruthValue,
    cfmFcipLinkExtCntrlQOSField Gauge,
    cfmFcipLinkExtDataQOSField Gauge,
    cfmFcipLinkExtEthIfIndex InterfaceIndex,
    cfmFcipLinkExtWriteAccelerator TruthValue,
    cfmFcipLinkExtIPComp INTEGER,
    cfmFcipLinkExtTapeAccelerator TruthValue,
    cfmFcipLinkExtFlowCtrlBufSize Gauge,
    cfmFcipLinkExtIPSec TruthValue,
    cfmFcipLinkExtPhyIfIndex InterfaceIndex,
    cfmFcipLinkExtWriteAccOper TruthValue,
    cfmFcipLinkExtTapeAccOper TruthValue,
    cfmFcipLinkExtTapeReadAccOper TruthValue,
    cfmFcipLinkExtFiconTAVsanL2k FcList,
    cfmFcipLinkExtFiconTAVsanL4k FcList,
    cfmFcipLinkExtFiconTAVsanLOper2k FcList,
    cfmFcipLinkExtFiconTAVsanLOper4k FcList
    }

cfmFcipLinkExtPassiveMode OBJECT-TYPE
    SYNTAX TruthValue
--    Rsyntax INTEGER {
--        true(1),
--        false(2)
--        }
    ACCESS read-write
    STATUS mandatory
    DESCRIPTION
        "If the value is set to 'false' this link endpoint actively
        tries to connect to the peer. If it is set to 'true' the link
        endpoint waits for the peer to connect to it. "
    DEFVAL { false }
    ::= { cfmFcipLinkExtEntry 1 }

cfmFcipLinkExtNumTcpConn OBJECT-TYPE
    SYNTAX Gauge(1..100)
--  Units
--    tcp connections
    ACCESS read-write
    STATUS mandatory
    DESCRIPTION
        "The maximum number of TCP connections allowed on this
        link. "
    DEFVAL { 2 }
    ::= { cfmFcipLinkExtEntry 2 }

cfmFcipLinkExtCheckTimestamp OBJECT-TYPE
    SYNTAX TruthValue
--    Rsyntax INTEGER {
--        true(1),
--        false(2)
--        }
    ACCESS read-write
    STATUS mandatory
    DESCRIPTION
        "The value is 'true', if the timestamp in FCIP header
        is to checked. If 'false' the timestamp is ignored. "
    DEFVAL { false }
    ::= { cfmFcipLinkExtEntry 3 }

cfmFcipLinkExtTimestampTolerance OBJECT-TYPE
    SYNTAX Gauge(100..10000)
--  Units
--    milliseconds
    ACCESS read-write
    STATUS mandatory
    DESCRIPTION
        "The accepted time difference between the local time
        and the timestamp value received in the FCIP header.
        By default this value will be EDTOV/2. EDTOV is the
        Error_Detect_Timeout Value used for Fibre channel Ports
        as the timeout value for detecting an error condition."
    REFERENCE
        "Section 29.2.1.2 E_D_TOV in FC-PH (Fibre Channel -
         Physical and Signaling Interface) Rev 4.3."
    ::= { cfmFcipLinkExtEntry 4 }

cfmFcipLinkExtTcpRemPort OBJECT-TYPE
    SYNTAX CiscoPort(1..65535)
--    Rsyntax INTEGER(1..65535)
    ACCESS read-write
    STATUS mandatory
    DESCRIPTION
        "The remote TCP port to which the local FCIP entity will
        connect if and when it initiates a TCP connection setup
        for this link. "
    ::= { cfmFcipLinkExtEntry 5 }

cfmFcipLinkExtLocalBPortEnable OBJECT-TYPE
    SYNTAX TruthValue
--    Rsyntax INTEGER {
--        true(1),
--        false(2)
--        }
    ACCESS read-write
    STATUS mandatory
    DESCRIPTION
        "If the value is set to 'true', the B port mode is enabled
         on the local FCIP link. If set to 'false' the B port mode
         is disabled. "
    DEFVAL { false }
    ::= { cfmFcipLinkExtEntry 6 }

cfmFcipLinkExtSpecialFrameEnable OBJECT-TYPE
    SYNTAX TruthValue
--    Rsyntax INTEGER {
--        true(1),
--        false(2)
--        }
    ACCESS read-write
    STATUS mandatory
    DESCRIPTION
        "If the value is set to 'true', the TCP active opener
         initiates FCIP special frames and the TCP passive
         opener responds to the FCIP special frames.
         If it is set to 'false', the FCIP special frames are
         neither generated nor responded to. "
    REFERENCE
        "Section 8 in draft-ietf-ips-fcovertcpip-12.txt."
    DEFVAL { false }
    ::= { cfmFcipLinkExtEntry 7 }

cfmFcipLinkExtBPortKAEnable OBJECT-TYPE
    SYNTAX TruthValue
--    Rsyntax INTEGER {
--        true(1),
--        false(2)
--        }
    ACCESS read-write
    STATUS mandatory
    DESCRIPTION
        "If the value is set to 'true', a message is
         sent in response to a (Fibre Channel) ELS Echo
         frame received from the peer. Some B Port
         implementations use ELS Echo request/response frames
         as Link Keep Alive.
         If it is set to 'false', this response is not
         generated.
         This object is valid only if the
         cfmFcipLinkExtLocalBPortEnable is  'true'. "
    REFERENCE
        "Section 15.5.4 Echo in FC-FS (Fibre Channel -
         Framing and Signaling ) Rev 0.50."
    DEFVAL { false }
    ::= { cfmFcipLinkExtEntry 8 }

cfmFcipLinkExtCntrlQOSField OBJECT-TYPE
    SYNTAX Gauge(0..63)
    ACCESS read-write
    STATUS mandatory
    DESCRIPTION
        "The value to be set for the TOS field in IP header
        for the TCP control connection.
        The cfmFcipLinkExtCntrlQOSField,cfmFcipLinkExtDataQOSField
        must be set in the same SNMP set request. SET operation would
        fail if this object is set individually. "
    DEFVAL { 0 }
    ::= { cfmFcipLinkExtEntry 9 }

cfmFcipLinkExtDataQOSField OBJECT-TYPE
    SYNTAX Gauge(0..63)
    ACCESS read-write
    STATUS mandatory
    DESCRIPTION
        "The value to be set for the TOS field in IP header
        for the TCP Data connection.
        The cfmFcipLinkExtCntrlQOSField,cfmFcipLinkExtDataQOSField
        must be set in the same SNMP set request. SET operation would
        fail if this object is set individually. "
    DEFVAL { 0 }
    ::= { cfmFcipLinkExtEntry 10 }

cfmFcipLinkExtEthIfIndex OBJECT-TYPE
    SYNTAX InterfaceIndex
--    Rsyntax INTEGER(1..2147483647)
    ACCESS read-only
    STATUS mandatory
    DESCRIPTION
        "The ifIndex of the interface on which this FCIP link was
        initiated. "
    ::= { cfmFcipLinkExtEntry 11 }

cfmFcipLinkExtWriteAccelerator OBJECT-TYPE
    SYNTAX TruthValue
--    Rsyntax INTEGER {
--        true(1),
--        false(2)
--        }
    ACCESS read-write
    STATUS mandatory
    DESCRIPTION
        "The Write accelerator allows for enhancing SCSI write
        performance.
        If 'true', the FCIP Write accelerator is enabled on this link
        If 'false' it is disabled."
    DEFVAL { false }
    ::= { cfmFcipLinkExtEntry 12 }

cfmFcipLinkExtIPComp OBJECT-TYPE
    SYNTAX INTEGER {
        none(1),
        highCompressionRatio(2),
        highThroughput(3),
        auto(4),
        mode1(5),
        mode2(6),
        mode3(7)
        }
    ACCESS read-write
    STATUS mandatory
    DESCRIPTION
        "The configuration for the IP compression.
         'none'                 - ip compression is disabled.
        
         'highCompressionRatio' - indicates better compression
                                  performance at the cost of lower
                                  throughput.
        
         'highThroughput'       - indicates better throughput at
                                  the cost of lower compression
                                  performance.
        
         'auto'                 - indicates that an appropriate
                                  mode wll be picked based on
                                  the bandwidth and data.
        
         'mode1'                - fast compression mode for high
                                  bandwidth WAN links with bandwidth
                                  greater than 30 Mbps.
        
         'mode2'                - high compression mode for
                                  moderately low bandwidth WAN links,
                                  i.e. bandwidth between 15 and 30
                                  Mbps.
        
         'mode3'                - high compression mode for
                                  low bandwidth WAN links,
                                  i.e. banwidth less than 15 Mbps.
        "
    DEFVAL { none }
    ::= { cfmFcipLinkExtEntry 13 }

cfmFcipLinkExtTapeAccelerator OBJECT-TYPE
    SYNTAX TruthValue
--    Rsyntax INTEGER {
--        true(1),
--        false(2)
--        }
    ACCESS read-write
    STATUS mandatory
    DESCRIPTION
        "The Tape accelerator allows for enhancing Tape write
        performance.
        If 'true', the FCIP Tape accelerator is enabled on this link
        If 'false' it is disabled."
    DEFVAL { false }
    ::= { cfmFcipLinkExtEntry 14 }

cfmFcipLinkExtFlowCtrlBufSize OBJECT-TYPE
    SYNTAX Gauge(0..12288)
--  Units
--    bytes
    ACCESS read-write
    STATUS mandatory
    DESCRIPTION
        "The flow control buffer size."
    DEFVAL { 256 }
    ::= { cfmFcipLinkExtEntry 15 }

cfmFcipLinkExtIPSec OBJECT-TYPE
    SYNTAX TruthValue
--    Rsyntax INTEGER {
--        true(1),
--        false(2)
--        }
    ACCESS read-only
    STATUS mandatory
    DESCRIPTION
        "Indicates whether the IP Security has been turned on or
         off on this link."
    DEFVAL { false }
    ::= { cfmFcipLinkExtEntry 16 }

cfmFcipLinkExtPhyIfIndex OBJECT-TYPE
    SYNTAX InterfaceIndex
--    Rsyntax INTEGER(1..2147483647)
    ACCESS read-only
    STATUS mandatory
    DESCRIPTION
        "The physical ifIndex of the interface on which this FCIP link
        is currently bound. "
    ::= { cfmFcipLinkExtEntry 17 }

cfmFcipLinkExtWriteAccOper OBJECT-TYPE
    SYNTAX TruthValue
--    Rsyntax INTEGER {
--        true(1),
--        false(2)
--        }
    ACCESS read-only
    STATUS mandatory
    DESCRIPTION
        "When Write Acceleration is operationally off for the FCIP
        link, the value of this object will be set to 'false'.
        When Write Acceleration is operationally on for the FCIP
        link, the value of this object will be set to 'true'. "
    DEFVAL { false }
    ::= { cfmFcipLinkExtEntry 18 }

cfmFcipLinkExtTapeAccOper OBJECT-TYPE
    SYNTAX TruthValue
--    Rsyntax INTEGER {
--        true(1),
--        false(2)
--        }
    ACCESS read-only
    STATUS mandatory
    DESCRIPTION
        "When Tape Acceleration is operationally off for the FCIP
        link, the value of this object will be set to 'false'.
        When Tape Acceleration is operationally on for the FCIP
        link, the value of this object will be set to 'true'. "
    DEFVAL { false }
    ::= { cfmFcipLinkExtEntry 19 }

cfmFcipLinkExtTapeReadAccOper OBJECT-TYPE
    SYNTAX TruthValue
--    Rsyntax INTEGER {
--        true(1),
--        false(2)
--        }
    ACCESS read-only
    STATUS mandatory
    DESCRIPTION
        "This object represents the state of the Tape Read
        Acceleration for an FCIP link.  Tape Read Acceleration
        is automatically operational when Tape Acceleration is
        operational (cfmFcipLinkExtTapeAccOper) and both sides 
        of the FCIP link support Tape Read Acceleration. 
        When Tape Read Acceleration is operationally off for 
        the FCIP link, the value of this object is 'false'. 
        When Tape Read Acceleration is operationally on for 
        the FCIP link, the value of this object is 'true'. "
    DEFVAL { false }
    ::= { cfmFcipLinkExtEntry 20 }

cfmFcipLinkExtFiconTAVsanL2k OBJECT-TYPE
    SYNTAX FcList
--    Rsyntax OCTET STRING(SIZE(0..256))
    ACCESS read-write
    STATUS mandatory
    DESCRIPTION
        "The list of VSANs (in the range 1 through 2047)
         for which Ficon Tape Acceleration is configured.
         Only VSANs with a cficonVsanEntry of CISCO-FICON-MIB
         present can be configured for Ficon Tape Acceleration."
    DEFVAL { ''H }
    ::= { cfmFcipLinkExtEntry 21 }

cfmFcipLinkExtFiconTAVsanL4k OBJECT-TYPE
    SYNTAX FcList
--    Rsyntax OCTET STRING(SIZE(0..256))
    ACCESS read-write
    STATUS mandatory
    DESCRIPTION
        "The list of VSANs (in the range 2048 through 4096)
         for which Ficon Tape Acceleration is configured.
         Only VSANs with a cficonVsanEntry of CISCO-FICON-MIB
         present can be configured for Ficon Tape Acceleration."
    DEFVAL { ''H }
    ::= { cfmFcipLinkExtEntry 22 }

cfmFcipLinkExtFiconTAVsanLOper2k OBJECT-TYPE
    SYNTAX FcList
--    Rsyntax OCTET STRING(SIZE(0..256))
    ACCESS read-only
    STATUS mandatory
    DESCRIPTION
        "The list of VSANs (in the range 1 through 2047)
         for which Ficon Tape Acceleration is operationally
         ON."
    ::= { cfmFcipLinkExtEntry 23 }

cfmFcipLinkExtFiconTAVsanLOper4k OBJECT-TYPE
    SYNTAX FcList
--    Rsyntax OCTET STRING(SIZE(0..256))
    ACCESS read-only
    STATUS mandatory
    DESCRIPTION
        "The list of VSANs (in the range 2048 through 4096)
         for which Ficon Tape Acceleration is operationally
         ON."
    ::= { cfmFcipLinkExtEntry 24 }

cfmFcipLinkMapTable OBJECT-TYPE
    SYNTAX SEQUENCE OF CfmFcipLinkMapEntry
    ACCESS not-accessible
    STATUS mandatory
    DESCRIPTION
        "A table containing FCIP link index to
         Entity Identifier mapping for a FCIP link."
    ::= { cfmFcipMgmtExtConfig 3 }

cfmFcipLinkMapEntry OBJECT-TYPE
    SYNTAX CfmFcipLinkMapEntry
    ACCESS not-accessible
    STATUS mandatory
    DESCRIPTION
        "A conceptual row of the FCIP link map table
         mapping the fcip link index to FCIP Entity
         Identifier. "
    INDEX { cfmFcipLinkMapIndex }
    ::= { cfmFcipLinkMapTable 1 }

CfmFcipLinkMapEntry ::= SEQUENCE {
    cfmFcipLinkMapIndex Gauge,
    cfmFcipMapEntityId Gauge
    }

cfmFcipLinkMapIndex OBJECT-TYPE
    SYNTAX Gauge
    ACCESS not-accessible
    STATUS mandatory
    DESCRIPTION
        "An arbitrary integer which uniquely identifies one FCIP link
         within a FCIP entity. "
    ::= { cfmFcipLinkMapEntry 1 }

cfmFcipMapEntityId OBJECT-TYPE
    SYNTAX Gauge
    ACCESS read-only
    STATUS mandatory
    DESCRIPTION
        "The FCIP entity Identifier corresponding to the instance
         of cfmFcipLinkMapIndex."
    ::= { cfmFcipLinkMapEntry 2 }

cfmFcipLinkExtStatsTable OBJECT-TYPE
    SYNTAX SEQUENCE OF CfmFcipLinkExtStatsEntry
    ACCESS not-accessible
    STATUS mandatory
    DESCRIPTION
        "A table containing objects which provide status information
        of the FCIP link for the cfmFcipLinkExtTable configured
        information. "
    ::= { cfmFcipMgmtExtStats 1 }

cfmFcipLinkExtStatsEntry OBJECT-TYPE
    SYNTAX CfmFcipLinkExtStatsEntry
    ACCESS not-accessible
    STATUS mandatory
    DESCRIPTION
        "An entry into cfmFcipLinkExtStatsTable. Each entry
         contains attributes associated with an FCIP Link. "
    INDEX { cfmFcipEntityId, cfmFcipLinkIndex }
-- Augments cfmFcipLinkEntry FROM CISCO-FCIP-MGMT-MIB
    ::= { cfmFcipLinkExtStatsTable 1 }

CfmFcipLinkExtStatsEntry ::= SEQUENCE {
    cfmFcipLinkStatsRxIPCompRatio SnmpAdminString,
    cfmFcipLinkStatsTxIPCompRatio SnmpAdminString
    }

cfmFcipLinkStatsRxIPCompRatio OBJECT-TYPE
    SYNTAX SnmpAdminString
--    Rsyntax OCTET STRING(SIZE(0..255))
    ACCESS read-only
    STATUS mandatory
    DESCRIPTION
        "The IP Copmression ratio for received packets on
        the FCIP device.  The value of this object will be
        presented as a floating point number with two digits
        after the decimal point. "
    ::= { cfmFcipLinkExtStatsEntry 1 }

cfmFcipLinkStatsTxIPCompRatio OBJECT-TYPE
    SYNTAX SnmpAdminString
--    Rsyntax OCTET STRING(SIZE(0..255))
    ACCESS read-only
    STATUS mandatory
    DESCRIPTION
        "The IP Copmression ratio for transmitted packets on
        the FCIP device.  The value of this object will be
        presented as a floating point number with two digits
        after the decimal point. "
    ::= { cfmFcipLinkExtStatsEntry 2 }

cfmFcipEntityExtGroup OBJECT IDENTIFIER ::= { cfmFcipExtGroups 1 }
-- OBJECT-GROUP
--  Status
--    mandatory
--  Descr
--    A collection of objects providing information about FCIP
--     Entity. 
--  objects
--    cfmFcipEntityExtTcpKeepAliveTO, cfmFcipEntityExtTcpMaxReTx, 
--    cfmFcipEntityExtPMTUEnable, cfmFcipEntityExtPMTUResetTO, 
--    cfmFcipEntityExtTcpMinRTO, cfmFcipEntityExtTcpSendBufSize, 
--    cfmFcipEntityExtTcpMaxBW, cfmFcipEntityExtTcpMinAvailBW, 
--    cfmFcipEntityExtTcpRndTrpTimeEst

cfmFcipLinkExtGroup OBJECT IDENTIFIER ::= { cfmFcipExtGroups 2 }
-- OBJECT-GROUP
--  Status
--    mandatory
--  Descr
--    A collection of objects providing information about FCIP
--     Links. 
--  objects
--    cfmFcipLinkExtPassiveMode, cfmFcipLinkExtNumTcpConn, 
--    cfmFcipLinkExtCheckTimestamp, 
--    cfmFcipLinkExtTimestampTolerance, cfmFcipLinkExtTcpRemPort, 
--    cfmFcipLinkExtLocalBPortEnable, 
--    cfmFcipLinkExtSpecialFrameEnable, cfmFcipLinkExtBPortKAEnable, 
--    cfmFcipLinkExtCntrlQOSField, cfmFcipLinkExtDataQOSField

cfmFcipLinkExtGroupRev1 OBJECT IDENTIFIER ::= { cfmFcipExtGroups 3 }
-- OBJECT-GROUP
--  Status
--    mandatory
--  Descr
--    A collection of objects providing information about FCIP
--     Links. 
--  objects
--    cfmFcipLinkExtEthIfIndex, cfmFcipLinkExtWriteAccelerator, 
--    cfmFcipLinkExtIPComp

cfmFcipEntityExtCWMGroup OBJECT IDENTIFIER ::= { cfmFcipExtGroups 4 }
-- OBJECT-GROUP
--  Status
--    mandatory
--  Descr
--    A collection of objects providing information on Congestion
--    Window Monitoring of a FCIP Entity. 
--  objects
--    cfmFcipEntityExtCWMEnable, cfmFcipEntityExtCWMBurstSize, 
--    cfmFcipEntityExtTcpSACKEnable, cfmFcipEntityExtTcpLocalPort

cfmFcipLinkExtGroupRev2 OBJECT IDENTIFIER ::= { cfmFcipExtGroups 5 }
-- OBJECT-GROUP
--  Status
--    mandatory
--  Descr
--    A collection of objects providing information about FCIP
--     Links, especially about the tape acceleration. 
--  objects
--    cfmFcipLinkExtTapeAccelerator, cfmFcipLinkExtFlowCtrlBufSize

cfmFcipLinkExtMapGroup OBJECT IDENTIFIER ::= { cfmFcipExtGroups 6 }
-- OBJECT-GROUP
--  Status
--    mandatory
--  Descr
--    A collection of objects providing mapping between FCIP
--     Links and their enrity Identifiers 
--  objects
--    cfmFcipMapEntityId

cfmFcipEntityExtGroupSup1 OBJECT IDENTIFIER ::= { cfmFcipExtGroups 7 }
-- OBJECT-GROUP
--  Status
--    mandatory
--  Descr
--    A collection of objects providing information about FCIP
--     Entity. 
--  objects
--    cfmFcipEntityExtTcpMaxJitter

cfmFcipLinkExtGroupRev2Sup1 OBJECT IDENTIFIER ::= { cfmFcipExtGroups 8 }
-- OBJECT-GROUP
--  Status
--    mandatory
--  Descr
--    A collection of objects providing information about FCIP
--     Links, especially about the tape acceleration and IP
--     Security. 
--  objects
--    cfmFcipLinkExtIPSec

cfmFcipLinkExtGroupRev2Sup2 OBJECT IDENTIFIER ::= { cfmFcipExtGroups 9 }
-- OBJECT-GROUP
--  Status
--    mandatory
--  Descr
--    A collection of objects providing information about FCIP
--     Link Operational state.
--  objects
--    cfmFcipLinkExtPhyIfIndex, cfmFcipLinkExtWriteAccOper, 
--    cfmFcipLinkExtTapeAccOper

cfmFcipLinkExtStatsGroup OBJECT IDENTIFIER ::= { cfmFcipExtGroups 10 }
-- OBJECT-GROUP
--  Status
--    mandatory
--  Descr
--    A collection of objects providing information about FCIP
--     statistics. 
--  objects
--    cfmFcipLinkStatsRxIPCompRatio, cfmFcipLinkStatsTxIPCompRatio

cfmFcipLinkExtGroupRev2Sup3 OBJECT IDENTIFIER ::= { cfmFcipExtGroups 11 }
-- OBJECT-GROUP
--  Status
--    mandatory
--  Descr
--    A collection of objects providing information about FCIP
--     Link Tape Read and Ficon Tape Acceleration Configuration
--     and Operational status. 
--  objects
--    cfmFcipLinkExtTapeReadAccOper, cfmFcipLinkExtFiconTAVsanL2k, 
--    cfmFcipLinkExtFiconTAVsanL4k, 
--    cfmFcipLinkExtFiconTAVsanLOper2k, 
--    cfmFcipLinkExtFiconTAVsanLOper4k

cfmFcipExtCompliance OBJECT IDENTIFIER ::= { cfmFcipExtCompliances 1 }
-- MODULE-COMPLIANCE
--  Status
--    deprecated
--  Descr
--    Compliance statement for FCIP Extension MIB. 
--  Module
--    >>current<<
--   MandGroup
--    cfmFcipEntityExtGroup
--   MandGroup
--    cfmFcipLinkExtGroup
--   ObjVar
--    cfmFcipLinkExtNumTcpConn

cfmFcipExtCompliance1 OBJECT IDENTIFIER ::= { cfmFcipExtCompliances 2 }
-- MODULE-COMPLIANCE
--  Status
--    deprecated
--  Descr
--    Compliance statement for FCIP Extension MIB. 
--  Module
--    >>current<<
--   MandGroup
--    cfmFcipEntityExtGroup
--   MandGroup
--    cfmFcipLinkExtGroup
--   MandGroup
--    cfmFcipLinkExtGroupRev1
--   ObjVar
--    cfmFcipLinkExtNumTcpConn
--   ObjVar
--    cfmFcipLinkExtTimestampTolerance

cfmFcipExtCompliance2 OBJECT IDENTIFIER ::= { cfmFcipExtCompliances 3 }
-- MODULE-COMPLIANCE
--  Status
--    deprecated
--  Descr
--    Compliance statement for FCIP Extension MIB. 
--  Module
--    >>current<<
--   MandGroup
--    cfmFcipEntityExtGroup
--   MandGroup
--    cfmFcipLinkExtGroup
--   MandGroup
--    cfmFcipLinkExtGroupRev1
--   MandGroup
--    cfmFcipEntityExtCWMGroup
--   ObjVar
--    cfmFcipLinkExtNumTcpConn
--   ObjVar
--    cfmFcipLinkExtTimestampTolerance
--   ObjVar
--    cfmFcipEntityExtCWMBurstSize

cfmFcipExtCompliance3 OBJECT IDENTIFIER ::= { cfmFcipExtCompliances 4 }
-- MODULE-COMPLIANCE
--  Status
--    deprecated
--  Descr
--    Compliance statement for FCIP Extension MIB. 
--  Module
--    >>current<<
--   MandGroup
--    cfmFcipEntityExtGroup
--   MandGroup
--    cfmFcipLinkExtGroup
--   MandGroup
--    cfmFcipLinkExtGroupRev1
--   MandGroup
--    cfmFcipEntityExtCWMGroup
--   MandGroup
--    cfmFcipLinkExtGroupRev2
--   MandGroup
--    cfmFcipLinkExtMapGroup
--   ObjVar
--    cfmFcipLinkExtNumTcpConn
--   ObjVar
--    cfmFcipLinkExtTimestampTolerance
--   ObjVar
--    cfmFcipEntityExtCWMBurstSize

cfmFcipExtCompliance4 OBJECT IDENTIFIER ::= { cfmFcipExtCompliances 5 }
-- MODULE-COMPLIANCE
--  Status
--    deprecated
--  Descr
--    Compliance statement for FCIP Extension MIB. 
--  Module
--    >>current<<
--   MandGroup
--    cfmFcipEntityExtGroup
--   MandGroup
--    cfmFcipEntityExtGroupSup1
--   MandGroup
--    cfmFcipLinkExtGroup
--   MandGroup
--    cfmFcipLinkExtGroupRev1
--   MandGroup
--    cfmFcipEntityExtCWMGroup
--   MandGroup
--    cfmFcipLinkExtGroupRev2
--   MandGroup
--    cfmFcipLinkExtGroupRev2Sup1
--   MandGroup
--    cfmFcipLinkExtMapGroup
--   ObjVar
--    cfmFcipLinkExtNumTcpConn
--   ObjVar
--    cfmFcipLinkExtTimestampTolerance
--   ObjVar
--    cfmFcipEntityExtCWMBurstSize

cfmFcipExtCompliance5 OBJECT IDENTIFIER ::= { cfmFcipExtCompliances 6 }
-- MODULE-COMPLIANCE
--  Status
--    deprecated
--  Descr
--    Compliance statement for FCIP Extension MIB. 
--  Module
--    >>current<<
--   MandGroup
--    cfmFcipEntityExtGroup
--   MandGroup
--    cfmFcipLinkExtGroup
--   MandGroup
--    cfmFcipLinkExtGroupRev1
--   MandGroup
--    cfmFcipEntityExtCWMGroup
--   MandGroup
--    cfmFcipLinkExtGroupRev2
--   MandGroup
--    cfmFcipLinkExtGroupRev2Sup1
--   MandGroup
--    cfmFcipLinkExtGroupRev2Sup2
--   MandGroup
--    cfmFcipLinkExtStatsGroup
--   ObjVar
--    cfmFcipLinkExtNumTcpConn
--   ObjVar
--    cfmFcipLinkExtTimestampTolerance
--   ObjVar
--    cfmFcipEntityExtCWMBurstSize

cfmFcipExtCompliance6 OBJECT IDENTIFIER ::= { cfmFcipExtCompliances 7 }
-- MODULE-COMPLIANCE
--  Status
--    mandatory
--  Descr
--    Compliance statement for FCIP Extension MIB. 
--  Module
--    >>current<<
--   MandGroup
--    cfmFcipEntityExtGroup
--   MandGroup
--    cfmFcipLinkExtGroup
--   MandGroup
--    cfmFcipLinkExtGroupRev1
--   MandGroup
--    cfmFcipEntityExtCWMGroup
--   MandGroup
--    cfmFcipLinkExtGroupRev2
--   MandGroup
--    cfmFcipLinkExtGroupRev2Sup1
--   MandGroup
--    cfmFcipLinkExtGroupRev2Sup2
--   MandGroup
--    cfmFcipLinkExtStatsGroup
--   MandGroup
--    cfmFcipLinkExtGroupRev2Sup3
--   ObjVar
--    cfmFcipLinkExtNumTcpConn
--   ObjVar
--    cfmFcipLinkExtTimestampTolerance
--   ObjVar
--    cfmFcipEntityExtCWMBurstSize


END
