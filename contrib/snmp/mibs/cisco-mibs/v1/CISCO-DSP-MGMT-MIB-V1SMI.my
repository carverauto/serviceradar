-- MIB file created 17-Feb-2011 16:32:43, by
--   SMICng version 2.2.11-beta(PRO)(Solaris), January 20, 2001. Enterprise key cisco.com

CISCO-DSP-MGMT-MIB DEFINITIONS ::= BEGIN

-- From file: "CISCO-DSP-MGMT-MIB.my"
-- Compile options "4 7 F H N W 03 06 0B 0G 0N 0T"

IMPORTS
    TimeStamp, TruthValue, DisplayString, RowStatus
            FROM SNMPv2-TC-v1
    entPhysicalIndex, entPhysicalName
            FROM ENTITY-MIB
    Percent
            FROM CISCO-QOS-PIB-MIB
    ciscoMgmt
            FROM CISCO-SMI
    Counter, Gauge
            FROM RFC1155-SMI
    OBJECT-TYPE
            FROM RFC-1212
    TRAP-TYPE
            FROM RFC-1215;

ciscoDspMgmtMIB OBJECT IDENTIFIER ::= { ciscoMgmt 86 }
-- MODULE-IDENTITY
--  LastUpdated
--    201102170000Z
--  OrgName
--    Cisco Systems, Inc.
--  ContactInfo
--    Cisco Systems
--    Customer Service
--    
--    Postal: 170 W. Tasman Drive
--    San Jose, CA  95134
--    USA
--    
--    Tel: +1 800 553-NETS
--    
--    E-mail: cs-voice@cisco.com
--  Descr
--    Digital Signal Processing (DSP) Management MIB module.
--    The MIB module monitors the DSP resource and status.
--    
--    Acronyms & Terms 
--    ================
--    
--    DTMF - Dual Tone Multi-Frequency.
--           DTMF uses two frequencies, the high frequency
--           omponent and the low frequency component,
--           to generate digit signals.
--    DSPFarm - DSPFarm ia a logical name given to a functionality
--           which groups the DSP resources to provide certain
--           service like transcoding and conferencing using DSP.
--    DSPFarm profile - A DSPFarm profile logically groups the DSP
--           to perform service like transcoding and conferencing.
--           It is uniquely identified by a profile number.
--    MTP  - Media Termination Point. RTP packet received by
--           MTP in the incoming call leg will be regenerated
--           and send out through the outgoing call leg.
--    transcode - Translating codec. transcoder is used to do
--           codec translation. If incoming call leg negotiates
--           codec-A and outgoing call leg negotiates codec-B
--           then transcoder will convert received RTP packet
--           from codec-A to codec-B or codec-B to codec-A.
--    MTP hardware session - Media termination functionality 
--           with using DSP.
--    MTP software session - Media termination functionality
--           without using DSP.
--    RTP  - Real-time Transport protocol.
--    Video Pool - A group of DSP resources dedicated to providing 
--           video services.
--  RevDate
--    201102170000Z
--  RevDescr
--    1. Added cdspCardVideoPoolUtilization and
--    cdspCardVideoPoolUtilizationThreshold to cdspCardStatusTable.
--    
--    2. Added cdspVideoUsageNotificationEnable and
--    cdspVideoOutOfResourceNotificationEnable to
--    cdspMIBNotificationEnables.
--    
--    4. Added 2 new notifications: cdspVideoUsageNotification and
--    cdspVideoOutOfResourceNotification.
--    
--    5. Deprecated cdspMgmtComplianceRev10 and added
--    cdspMgmtComplianceRev11.
--    
--    7. Added cdspMgmtVideoInfoGroup and
--    cdspMgmtVideoNotificationsGroup.
--  RevDate
--    200904090000Z
--  RevDescr
--    1. Added the following new OBJECT IDENTIFIERs:
--    cdspDspfarmObjects, 
--    cdspDspfarmUtilObjects.
--    2. Added the following objects to cdspDspfarmObjects: 
--    cdspGlobMaxConfTranscodeSess,
--    cdspGlobMaxAvailTranscodeSess.
--    3. Added cdspTranscodeProfileTable.
--    4. Added cdspMtpProfileTable.
--    5. Added the following objects to cdspDspfarmUtilObjects:
--    cdspTotAvailTranscodeSess,
--    cdspTotUnusedTranscodeSess,
--    cdspTotAvailMtpSess,
--    cdspTotUnusedMtpSess.
--    6. Added OBJECT-GROUP cdspDspfarmInfoGroup. 
--    7. Deprecated MODULE-COMPLIANCE cdspMgmtComplianceRev9.
--    8. Added MODULE-COMPLIANCE cdspMgmtComplianceRev10.
--  RevDate
--    200709030005Z
--  RevDescr
--    Added cdspUtilTable to have MIB support for utilised and free
--    DSP channels corresponding to codec pools available in codec
--    template currently active on VXSM.
--  RevDate
--    200706250000Z
--  RevDescr
--    Added two values to object cdspCodecTemplateSupported to
--    support TGW2 and FMC codec templates.
--  RevDate
--    200706200000Z
--  RevDescr
--    1. Added cdspVoiceModeIpIp object in cdspVoiceParamTable.
--    2. Deprecated cdspTransparentIpIp.
--  RevDate
--    200604140000Z
--  RevDescr
--    Added following objects in cdspVoiceParamTable:
--    cdspTransparentIpIp
--  RevDate
--    200511020000Z
--  RevDescr
--    Added following objects in cdspVoiceParamTable:
--    cdspVqmThreshSES   
--    Modified the following objects in cdspVoiceParamTable:
--            cdspVqmControl
--  RevDate
--    200508170000Z
--  RevDescr
--    Added following objects to cdspVoiceParamTable:
--    cdspPktLossConcealment
--  RevDate
--    200508040000Z
--  RevDescr
--    Added following objects to cdspVoiceParamTable:
--    cdspVqmControl
--    cdspRtcpXrControl
--    cdspRtcpXrTransMultiplier
--    cdspRtcpXrGminDefault
--    cdspRtcpXrExtRfactor
--  RevDate
--    200506200000Z
--  RevDescr
--    Added entPhysicalName to the OBJECTS clause of
--    cdspOperStateNotification.
--  RevDate
--    200505180000Z
--  RevDescr
--    Added object cdspEnableOperStateNotification
--    to enable cdspOperStateNotification.
--    Added cdspOperStateNotification to reflect
--    cdspOperState in 'normal' or 'shutdown' state.
--  RevDate
--    200504180000Z
--  RevDescr
--    Added object cdspCodecTemplateSupported to
--    cdspCardStatusTable.
--  RevDate
--    200410210000Z
--  RevDescr
--    Added object cdspRtcpTimerControl to
--    cdspVoiceParamTable.
--  RevDate
--    200310100000Z
--  RevDescr
--    Added object cdspDspNum to cdspStatusTable.
--  RevDate
--    200308200000Z
--  RevDescr
--    Changing the DESCRIPTION of
--    cdspMIBCardStateNotification 
--    to notify Manager whenever
--    cdspCardState enters normal.
--  RevDate
--    200308140000Z
--  RevDescr
--    (1) Added following objects to cdspCardStatusTable:
--    cdspTotalDsp
--    cdspFailedDsp
--    cdspCongestedDsp  
--    cdspNormalDsp       
--    cdspNx64Dsp
--    cdspDspSwitchOverThreshold
--    (2) Added cdspVoiceParamTable 
--    (3) Added following objects to cdspStatusTable:
--    cdspSigBearerChannelSplit
--    cdspNumCongestionOccurrence
--    (4) Added following enumerations to cdspOperState:
--    congested (3)
--    failed    (4)
--    (5) Added cdspStatusXTable
--  RevDate
--    200008140000Z
--  RevDescr
--    Fix typo in the DESCRIPTION clause of
--    cdspMIBEnableCardStatusNotification object;
--    change 'cdspFatalNotification' to 
--    'cdspMIBCardStateNotification'.
--  RevDate
--    9810170000Z
--  RevDescr
--    Add new objects to support channelized DSP features.

cdspMgmtNotifications OBJECT IDENTIFIER ::= { ciscoDspMgmtMIB 0 }
cdspMgmtObjects OBJECT IDENTIFIER ::= { ciscoDspMgmtMIB 1 }
cdspCardObjects OBJECT IDENTIFIER ::= { cdspMgmtObjects 1 }
cdspObjects     OBJECT IDENTIFIER ::= { cdspMgmtObjects 2 }
cdspMIBNotificationEnables OBJECT IDENTIFIER ::= { cdspMgmtObjects 3 }
cdspVoiceObjects OBJECT IDENTIFIER ::= { cdspMgmtObjects 4 }
cdspUtilObjects OBJECT IDENTIFIER ::= { cdspMgmtObjects 5 }
cdspDspfarmObjects OBJECT IDENTIFIER ::= { cdspMgmtObjects 6 }
cdspDspfarmUtilObjects OBJECT IDENTIFIER ::= { cdspMgmtObjects 7 }
cdspMIBNotificationPrefix OBJECT IDENTIFIER ::= { ciscoDspMgmtMIB 2 }
cdspMIBNotifications OBJECT IDENTIFIER ::= { cdspMIBNotificationPrefix 0 }
cdspMgmtConformance OBJECT IDENTIFIER ::= { ciscoDspMgmtMIB 3 }
cdspMgmtCompliances OBJECT IDENTIFIER ::= { cdspMgmtConformance 1 }
cdspMgmtGroups  OBJECT IDENTIFIER ::= { cdspMgmtConformance 2 }

cdspCardStatusTable OBJECT-TYPE
    SYNTAX SEQUENCE OF CdspCardStatusEntry
    ACCESS not-accessible
    STATUS mandatory
    DESCRIPTION
        "The DSP Card Table. It contains status information of the
        DSP cards present within the router."
    ::= { cdspCardObjects 1 }

cdspCardStatusEntry OBJECT-TYPE
    SYNTAX CdspCardStatusEntry
    ACCESS not-accessible
    STATUS mandatory
    DESCRIPTION
        "An entry in the DSP card table indicates the
        DSP card state, resource utilization.
        Each entry is created when a DSP software is detected
        on a DSP card. The entry is deleted when the DSP card is 
        deleted."
    INDEX { entPhysicalIndex }
    ::= { cdspCardStatusTable 1 }

CdspCardStatusEntry ::= SEQUENCE {
    cdspCardIndex INTEGER,
    cdspCardState INTEGER,
    cdspCardResourceUtilization Gauge,
    cdspCardLastHiWaterUtilization Gauge,
    cdspCardLastResetTime TimeStamp,
    cdspCardMaxChanPerDSP Gauge,
    cdspTotalDsp Gauge,
    cdspFailedDsp Gauge,
    cdspDspSwitchOverThreshold Gauge,
    cdspCongestedDsp Gauge,
    cdspNormalDsp Gauge,
    cdspNx64Dsp Gauge,
    cdspCodecTemplateSupported INTEGER,
    cdspCardVideoPoolUtilization Percent,
    cdspCardVideoPoolUtilizationThreshold Gauge
    }

cdspCardIndex OBJECT-TYPE
    SYNTAX INTEGER
    ACCESS read-only
    STATUS mandatory
    DESCRIPTION
        "The object corresponds to cardIndex in the chassis mib.
        If value of this object is 0, then the entry is not
        associated to cardIndex of the chassis mib."
    ::= { cdspCardStatusEntry 1 }

cdspCardState OBJECT-TYPE
    SYNTAX INTEGER {
        normal(1),
        warning(2),
        critical(3),
        fatal(4),
        offLine(5)
        }
    ACCESS read-only
    STATUS mandatory
    DESCRIPTION
        "The object indicates the current state of
        DSP card being monitored.
        normal   - DSP card in normal condition.
        warning  - DSP card has some problem and need attention.
        critical - DSP card has a major alarm.
        fatal    - DSP card is not functional.
                   DSP subsystem might reset DSP card to 
                   recover it from the fatal error condition.
                   After the DSP card is reset successfully,
                   the object cdspCardResourceUtilization and
                   cdspCardLastHiWaterUtilization are reset to
                   0.
                   If the fatal error is persistent in this object
                   after card is reset, the card should be replaced. 
        offLine  - DSP card is in off-line maintenance state."
    ::= { cdspCardStatusEntry 2 }

cdspCardResourceUtilization OBJECT-TYPE
    SYNTAX Gauge(0..100)
--  Units
--    percent
    ACCESS read-only
    STATUS mandatory
    DESCRIPTION
        "The object indicates the percentage of current DSP
        resource utilization of the card. The utilization is a 
        ratio of number of busy DSP resources (for handling calls, 
        transcoding, voice compression,...) to the total available 
        DSP resources."
    ::= { cdspCardStatusEntry 3 }

cdspCardLastHiWaterUtilization OBJECT-TYPE
    SYNTAX Gauge(0..100)
--  Units
--    percent
    ACCESS read-only
    STATUS mandatory
    DESCRIPTION
        "The object indicates the last high water mark of DSP
        resource utilization. This object is reset to 0 after
        DSP card is reset."
    ::= { cdspCardStatusEntry 4 }

cdspCardLastResetTime OBJECT-TYPE
    SYNTAX TimeStamp
--    Rsyntax TimeTicks
    ACCESS read-only
    STATUS mandatory
    DESCRIPTION
        "The value of sysUpTime when the last DSP card reset
        occurred."
    ::= { cdspCardStatusEntry 5 }

cdspCardMaxChanPerDSP OBJECT-TYPE
    SYNTAX Gauge
--  Units
--    channels
    ACCESS read-only
    STATUS mandatory
    DESCRIPTION
        "The maximum number of channels allowed in each DSP.
        The value is chosen in an implementation-dependent
        manner by the DSP functionality.
        The value of 0 in this object indicates Channelized
        DSP mode is turned off."
    ::= { cdspCardStatusEntry 6 }

cdspTotalDsp OBJECT-TYPE
    SYNTAX Gauge(1..2048)
    ACCESS read-only
    STATUS mandatory
    DESCRIPTION
        "The total number of DSPs in the card."
    ::= { cdspCardStatusEntry 7 }

cdspFailedDsp OBJECT-TYPE
    SYNTAX Gauge(0..2048)
    ACCESS read-only
    STATUS mandatory
    DESCRIPTION
        "The number of DSPs in the failed state (i.e
        cdspOperstate is 'failed')"
    ::= { cdspCardStatusEntry 8 }

cdspDspSwitchOverThreshold OBJECT-TYPE
    SYNTAX Gauge(1..2048)
    ACCESS read-write
    STATUS mandatory
    DESCRIPTION
        "This object specifies the threshold of DSP failures.
        When 'cdspFailedDsp' reaches the value of this object,
        the voice gateway switchover will occur.          
        The maximum value of this object can not be more than 
        the value in 'cdspTotalDsp'"
    ::= { cdspCardStatusEntry 9 }

cdspCongestedDsp OBJECT-TYPE
    SYNTAX Gauge(0..2048)
    ACCESS read-only
    STATUS mandatory
    DESCRIPTION
        "The number of DSPs in the congested state (i.e
        cdspOperstate is 'congested')."
    ::= { cdspCardStatusEntry 10 }

cdspNormalDsp OBJECT-TYPE
    SYNTAX Gauge(0..2048)
    ACCESS read-only
    STATUS mandatory
    DESCRIPTION
        "The number of DSPs in the normal state (i.e
        cdspOperstate is 'normal')."
    ::= { cdspCardStatusEntry 11 }

cdspNx64Dsp OBJECT-TYPE
    SYNTAX Gauge(0..2048)
    ACCESS read-write
    STATUS mandatory
    DESCRIPTION
        "This object specifies the number of DSPs that need to be set
        aside for making Nx64 calls. 
        The max value of this object is limited to the value of the
        object 'cdspTotalDsp'. 
        
        If this value is 0, it is not allowed to make any 
        Nx64 call. The default value of this object is 0."
    ::= { cdspCardStatusEntry 12 }

cdspCodecTemplateSupported OBJECT-TYPE
    SYNTAX INTEGER {
        tgw(1),
        cable(2),
        umts3G(3),
        cdma3G(4),
        tgw2(5),
        fmc(6)
        }
    ACCESS read-only
    STATUS mandatory
    DESCRIPTION
        "This object indicates the codec template supported in DSP
        image. The codec template can be:
           tgw    - Codec template for wireline used in 
                    Trunking GateWay application.
           cable  - Codec template for AES (Advanced Encryption
                    Standard) encryption used in cable 
                    application.
           umts3G - Codec template for AMR (Adaptive Multi-Rate) 
                    codecs used in 3G UMTS (Universal Mobile 
                    Telecommunication System) application.
           cdma3G - Codec template for EVRC (Enhanced Variable 
                    Rate Codec) used in 3G CDMA (Code Division 
                    Multiple Access) application.
           tgw2   - Codec template for iLBC (Internet Low Bandwidth Codec)
                    codec used in Tandem Gateway application.
           fmc    - Codec template for AMR (Adaptive Multi-Rate)
                    codec used in Fixed Mobile Convergence (FMC)
                    application."
    ::= { cdspCardStatusEntry 13 }

cdspCardVideoPoolUtilization OBJECT-TYPE
    SYNTAX Percent
--    Rsyntax INTEGER(0..100)
    ACCESS read-only
    STATUS mandatory
    DESCRIPTION
        "The object indicates the percentage of current DSP video
        resource pool utilization of the card."
    ::= { cdspCardStatusEntry 14 }

cdspCardVideoPoolUtilizationThreshold OBJECT-TYPE
    SYNTAX Gauge(1..100)
    ACCESS read-write
    STATUS mandatory
    DESCRIPTION
        "This object specifies the threshold of DSP video pool resource
        usage.  
        
        When cdspCardVideoPoolUtilization crosses the value of this
        threshold in the rising direction, cdspVideoUsageNotification is
        generated.  
        
        If cdspCardVideoPoolUtilization stays above the value of this
        threshold, cdspVideoUsageNotification is generated whenever the
        value of cdspCardVideoPoolUtilization increases, but no
        notification is sent if when the value of
        cdspCardVideoPoolUtilization decreases.  
        
        No notification is sent if cdspCardVideoPoolUtilization crosses
        the value of this threshold in the falling direction."
    ::= { cdspCardStatusEntry 15 }

cdspStatusTable OBJECT-TYPE
    SYNTAX SEQUENCE OF CdspStatusEntry
    ACCESS not-accessible
    STATUS mandatory
    DESCRIPTION
        "Status information for the DSPs.
        This status table is used for tracking dangling DSP 
        resources. The dangling DSP channel means that the DSP 
        channel is reserved for serving calls but the channel 
        is not used by active calls. The number of the dangling 
        DSP channels can be computed by 
        'cdspInUseChannels - cdspActiveChannels'."
    ::= { cdspObjects 1 }

cdspStatusEntry OBJECT-TYPE
    SYNTAX CdspStatusEntry
    ACCESS not-accessible
    STATUS mandatory
    DESCRIPTION
        "An entry in cdspStatusTable indicates the DSP state and
        alarm conditions. Each entry is created when a DSP is 
        detected on a DSP card. The entry is deleted when the DSP 
        card is deleted. 
        The 'entPhysicalIndex' represents a DSP entity, and the
        'entPhysicalClass' is 'other(1)'."
    INDEX { entPhysicalIndex }
    ::= { cdspStatusTable 1 }

CdspStatusEntry ::= SEQUENCE {
    cdspOperState INTEGER,
    cdspAlarms Counter,
    cdspLastAlarmCause INTEGER,
    cdspLastAlarmCauseText DisplayString,
    cdspLastAlarmTime TimeStamp,
    cdspTotalChannels Gauge,
    cdspInUseChannels Gauge,
    cdspActiveChannels Gauge,
    cdspSigBearerChannelSplit TruthValue,
    cdspNumCongestionOccurrence Counter,
    cdspDspNum Gauge
    }

cdspOperState OBJECT-TYPE
    SYNTAX INTEGER {
        normal(1),
        shutdown(2),
        congested(3),
        failed(4)
        }
    ACCESS read-only
    STATUS mandatory
    DESCRIPTION
        "The current operational state of the DSP.
        normal    - DSP operates normally 
        shutdown  - DSP is shutdown due to fatal error
        congested - DSP does not accept call because 
                    the DSP buffer is full
        failed    - DSP failed"
    ::= { cdspStatusEntry 1 }

cdspAlarms OBJECT-TYPE
    SYNTAX Counter
    ACCESS read-only
    STATUS mandatory
    DESCRIPTION
        "The object indicates the accumulated number of DSP
        Alarms."
    ::= { cdspStatusEntry 2 }

cdspLastAlarmCause OBJECT-TYPE
    SYNTAX INTEGER {
        other(1),
        noAlarm(2),
        dspFatalError(3),
        dspMemoryError(4),
        dspBufferError(5),
        dspDownloadError(6)
        }
    ACCESS read-only
    STATUS mandatory
    DESCRIPTION
        "The object indicates the current or last alarm state of
        DSP.
        other            - none of the following
        noAlarm          - alarm condition had not been detected
        dspFatalError    - DSP fatal error 
        dspMemoryError   - DSP memory error is detected
        dspBufferError   - DSP buffer error
        dspDownloadError - Failed to download software to DSP. 
        The cdspOperState will be set to 'shutdown(2) if the
        alarm condition of DSP is persistent."
    ::= { cdspStatusEntry 3 }

cdspLastAlarmCauseText OBJECT-TYPE
    SYNTAX DisplayString
--    Rsyntax OCTET STRING(SIZE(0..255))
    ACCESS read-only
    STATUS mandatory
    DESCRIPTION
        "The object indicates the failure reason for the current
        or last DSP Alarm.
        It should be used only for direct, human-readable display 
        and only if a management station is unable to
        decode the value of cdspLastAlarmCause."
    ::= { cdspStatusEntry 4 }

cdspLastAlarmTime OBJECT-TYPE
    SYNTAX TimeStamp
--    Rsyntax TimeTicks
    ACCESS read-only
    STATUS mandatory
    DESCRIPTION
        "The value of sysUpTime when the last DSP Alarm
        occurred. The value of this object is 0 if the value of
        cdspLastAlarmCause object is 'noAlarm'."
    ::= { cdspStatusEntry 5 }

cdspTotalChannels OBJECT-TYPE
    SYNTAX Gauge
--  Units
--    channels
    ACCESS read-only
    STATUS mandatory
    DESCRIPTION
        "The total number of channels in the DSP. This value is
        predetermined by the DSP functionality upon initialization.
        The value of 0 in this object indicates Channelized DSP 
        mode is turned off."
    ::= { cdspStatusEntry 6 }

cdspInUseChannels OBJECT-TYPE
    SYNTAX Gauge
--  Units
--    channels
    ACCESS read-only
    STATUS mandatory
    DESCRIPTION
        "The number of channels that are reserved for
        serving calls. The value is incremented when the
        DSP channel is reserved for call setup and
        is decremented after the DSP channel is free
        due to call disconnection."
    ::= { cdspStatusEntry 7 }

cdspActiveChannels OBJECT-TYPE
    SYNTAX Gauge
--  Units
--    channels
    ACCESS read-only
    STATUS mandatory
    DESCRIPTION
        "The number of channels that are used by
        active calls to process media stream.
        The value is incremented after the reserved DSP
        channel enters call connection state and is decremented
        after the call is disconnected."
    ::= { cdspStatusEntry 8 }

cdspSigBearerChannelSplit OBJECT-TYPE
    SYNTAX TruthValue
--    Rsyntax INTEGER {
--        true(1),
--        false(2)
--        }
    ACCESS read-only
    STATUS mandatory
    DESCRIPTION
        "This object indicates if the DSP channels are splitted
        for signaling call and bearer call.
        If the value of this object is 'true' which
        means that signaling call and bearer call cannot share
        any DSP channel. 
        This object is not applicable when Channelized DSP 
        mode is turned off."
    ::= { cdspStatusEntry 9 }

cdspNumCongestionOccurrence OBJECT-TYPE
    SYNTAX Counter
    ACCESS read-only
    STATUS mandatory
    DESCRIPTION
        "The number of congestion occurred on the DSP.
        This value is set to 0 when system is reset."
    ::= { cdspStatusEntry 10 }

cdspDspNum OBJECT-TYPE
    SYNTAX Gauge(1..252)
    ACCESS read-only
    STATUS mandatory
    DESCRIPTION
        "This object identifies the DSP number associated with
        this DSP entity."
    ::= { cdspStatusEntry 11 }

cdspStatusXTable OBJECT-TYPE
    SYNTAX SEQUENCE OF CdspStatusXEntry
    ACCESS not-accessible
    STATUS mandatory
    DESCRIPTION
        "This table provides the additional detailed
        state and statistics information for a DSP 
        that supports the splitted signalling and 
        bearer channels."
    ::= { cdspObjects 2 }

cdspStatusXEntry OBJECT-TYPE
    SYNTAX CdspStatusXEntry
    ACCESS not-accessible
    STATUS mandatory
    DESCRIPTION
        "An entry of this table is created when its associated
        entry in cdspStatusTable is created and the value of
        cdspSigBearerChannelSplit object  is 'true'."
    INDEX { entPhysicalIndex }
-- Augments cdspStatusEntry
    ::= { cdspStatusXTable 1 }

CdspStatusXEntry ::= SEQUENCE {
    cdspXNumberOfBearerCalls Gauge,
    cdspXNumberOfSigCalls Gauge,
    cdspXAvailableBearerBandwidth Gauge,
    cdspXAvailableSigBandwidth Gauge
    }

cdspXNumberOfBearerCalls OBJECT-TYPE
    SYNTAX Gauge
--  Units
--    calls
    ACCESS read-only
    STATUS mandatory
    DESCRIPTION
        "The current number of bearer calls on the DSP."
    ::= { cdspStatusXEntry 1 }

cdspXNumberOfSigCalls OBJECT-TYPE
    SYNTAX Gauge
--  Units
--    calls
    ACCESS read-only
    STATUS mandatory
    DESCRIPTION
        "The current number of signaling calls on the DSP."
    ::= { cdspStatusXEntry 2 }

cdspXAvailableBearerBandwidth OBJECT-TYPE
    SYNTAX Gauge
--  Units
--    percent
    ACCESS read-only
    STATUS mandatory
    DESCRIPTION
        "The percentage of channels on the DSP currently
        available for bearer calls."
    ::= { cdspStatusXEntry 3 }

cdspXAvailableSigBandwidth OBJECT-TYPE
    SYNTAX Gauge
--  Units
--    percent
    ACCESS read-only
    STATUS mandatory
    DESCRIPTION
        "The percentage of channels on the DSP currently
        available for signaling calls."
    ::= { cdspStatusXEntry 4 }

cdspVoiceParamTable OBJECT-TYPE
    SYNTAX SEQUENCE OF CdspVoiceParamEntry
    ACCESS not-accessible
    STATUS mandatory
    DESCRIPTION
        "This table contains information on voice call setup
        related parameters for DSP resource."
    ::= { cdspVoiceObjects 1 }

cdspVoiceParamEntry OBJECT-TYPE
    SYNTAX CdspVoiceParamEntry
    ACCESS not-accessible
    STATUS mandatory
    DESCRIPTION
        "An entry in the DSP table contains information
        regarding a single DSP resource associated voice 
        call setup parameters.
        
        An entry in this table is created when a DSP is
        detected and the DSP resource can be used by voice
        applications. 
        
        An entry in this table is deleted when the DSP
        associated card/module is removed from the system. 
        
        The 'entPhysicalClass' for the entry is 'other'."
    INDEX { entPhysicalIndex }
    ::= { cdspVoiceParamTable 1 }

CdspVoiceParamEntry ::= SEQUENCE {
    cdspRtpSidPayloadType INTEGER,
    cdspRtcpControl TruthValue,
    cdspRtcpTransInterval Gauge,
    cdspRtcpRecvMultiplier Gauge,
    cdspVadAdaptive TruthValue,
    cdspDtmfPowerLevel INTEGER,
    cdspDtmfPowerTwist INTEGER,
    cdspRtcpTimerControl INTEGER,
    cdspVqmControl INTEGER,
    cdspRtcpXrControl TruthValue,
    cdspRtcpXrTransMultiplier Gauge,
    cdspRtcpXrGminDefault Gauge,
    cdspRtcpXrExtRfactor Gauge,
    cdspPktLossConcealment INTEGER,
    cdspVqmThreshSES Gauge,
    cdspTransparentIpIp TruthValue,
    cdspVoiceModeIpIp INTEGER
    }

cdspRtpSidPayloadType OBJECT-TYPE
    SYNTAX INTEGER {
        decimal(13),
        hexadecimal(19)
        }
    ACCESS read-write
    STATUS mandatory
    DESCRIPTION
        "This object specifies the RTP (Real Time Protocol) payload
        type of the SID (Silence Insertion Descriptor) packet 
        that is sent to the remote endpoint at the onset 
        of silence suppression."
    REFERENCE
        "Section 5.1 of RFC2833"
    DEFVAL { decimal }
    ::= { cdspVoiceParamEntry 1 }

cdspRtcpControl OBJECT-TYPE
    SYNTAX TruthValue
--    Rsyntax INTEGER {
--        true(1),
--        false(2)
--        }
    ACCESS read-write
    STATUS mandatory
    DESCRIPTION
        "This objects controls if RTCP (Real Time Control Protocol)
        will be enabled.
        If this object is set to 'true', both transmission and 
        reception of RTCP packets are enabled; otherwise, 
        transmission of RTCP packets is disabled while any 
        received RTCP packets are ignored."
    REFERENCE
        "Appendix A.7 of RFC1889"
    DEFVAL { true }
    ::= { cdspVoiceParamEntry 2 }

cdspRtcpTransInterval OBJECT-TYPE
    SYNTAX Gauge(5000..65535)
--  Units
--    milliseconds
    ACCESS read-write
    STATUS mandatory
    DESCRIPTION
        "This attribute specifies the RTCP report interval (defined
        in RFC1889). It indicates the interval in which the RTCP 
        reports should be sent to the participating members. 
        
        RTCP reports is sent out in a random interval computed
        by using 'cdspRtcpTransInterval' and a random number
        that is between 0.5 and 1.5. 
        
        This interval timer also serves the purpose 
        of RTP packets receive timer. At every interval 
        multiplier times this interval, where a check is made on 
        a VoIP connection (which is in SENDRECV or RECVONLY xGCP 
        modes) to see if any RTP packets have been received. If 
        not, gateway-initiated DLCX should be sent to the 
        Call Agent. 
        
        This object is applicable only if 'cdspRtcpControl' is
        set to 'true'."
    REFERENCE
        "Appendix A.7 of RFC1889"
    DEFVAL { 5000 }
    ::= { cdspVoiceParamEntry 3 }

cdspRtcpRecvMultiplier OBJECT-TYPE
    SYNTAX Gauge(1..60)
    ACCESS read-write
    STATUS mandatory
    DESCRIPTION
        "This object specifies an approximate RTCP report interval
        (defined in RFC 1889) in milliseconds in which the RTCP 
        reports should be sent to the participating members.
        
        It specifies how many times the RTCP reports may fail  
        before exception condition activity may be done.
        In the time elapse of value of this MIB object times the 
        RTCP Report Interval specified by 'cdspRtcpTransInterval', 
        a check will be done on a VoIP connection (which is in   
        SENDRECV or RECVONLY xGCP modes) to see if any RTP packets 
        have been received. If not, gateway-initiated DLCX should 
        be sent to the Call Agent.
        
        This object is applicable only if 'cdspRtcpControl' is
        set to 'true'."
    REFERENCE
        "Section 6.2.1 of RFC1889"
    DEFVAL { 5 }
    ::= { cdspVoiceParamEntry 4 }

cdspVadAdaptive OBJECT-TYPE
    SYNTAX TruthValue
--    Rsyntax INTEGER {
--        true(1),
--        false(2)
--        }
    ACCESS read-write
    STATUS mandatory
    DESCRIPTION
        "This attribute is used to enable or disable the Adaptive
        VAD knob of the VAD algorithm. 
        Adaptive VAD works in conjunction with VAD Threshold
        (cvifcfgMusicOnHoldThreshold from CISCO-VOICE-IF-MIB). 
        When this object set to 'true', VAD Threshold is ignored 
        and the DSP adjusts the threshold automatically according 
        to the background noise level. 
        When the adaptive VAD configuration is 'false', VAD 
        threshold is used directly. The VAD configuration is 
        ignored for all CODECs that contain their own VAD 
        (G.729AB, G.723.1A and GSM-EFR).
        Likewise, when a channel is configured in ClearChannel 
        mode (Clear Channel is Non-Compression CODEC channel), 
        VAD will automatically be disabled irrespective of 
        the configuration."
    DEFVAL { false }
    ::= { cdspVoiceParamEntry 5 }

cdspDtmfPowerLevel OBJECT-TYPE
    SYNTAX INTEGER(-250..30)
--  Units
--    0.1 dBm
    ACCESS read-write
    STATUS mandatory
    DESCRIPTION
        "This object specifies the power level of the low
        frequency component of DTMF. The power level of the high 
        frequency component of DTMF is relative above or below
        the value specified in object cdspDtmfPowerTwist.
        If the value of cdspDtmfPowerTwist is 0, the power
        level of the high frequency component as well as the low 
        frequency component is specified by this object."
    REFERENCE
        "Q.23, Q.24, EIA/TIA-464"
    DEFVAL { -120 }
    ::= { cdspVoiceParamEntry 6 }

cdspDtmfPowerTwist OBJECT-TYPE
    SYNTAX INTEGER(-100..100)
--  Units
--    0.1 dB
    ACCESS read-write
    STATUS mandatory
    DESCRIPTION
        "This object specifies the relative power level of the
        high frequency component of DTMF.
        The low frequency group is always fixed to the value
        specified by cdspDtmfPowerLevel. 
        When this object is set to 0, the power level of both
        frequency components is set to the same level.
        When this object is set to a positive value, the power
        level of the high frequency component is set to 
        relatively higher specified in this object than the 
        low frequency component. 
        For example if cdspDtmfPowerLevel is set to -120(-12 dBm)
        and this object is set to 50, the power level of the 
        high frequency component becomes -70(-7 dBm).
        When this object is set to a negative value, the power
        level of the high frequency component is set to 
        relatively lower specified in this object than the low
        frequency component. For example if cdspDtmfPowerLevel is 
        set to -120(-12 dBm) and this object is set to -100, 
        the power level of the high frequency component becomes 
        -220(-22 dBm).
        The power level of the high frequency component has to be
        in the data range specified in cdspDtmfPowerLevel. 
        For example if cdspDtmfPowerLevel is set to -200(-20 dBm)
        and this object is set to -100, the power level
        of the high frequency component will become -300(-30 dBm)
        which is out of the range (-250..30) of data specified in
        cdspDtmfPowerLevel, so -100 is illegitimate for
        this setting."
    REFERENCE
        "Q.23, Q.24, EIA/TIA-464"
    DEFVAL { 0 }
    ::= { cdspVoiceParamEntry 7 }

cdspRtcpTimerControl OBJECT-TYPE
    SYNTAX INTEGER {
        disabled(1),
        startImmediately(2),
        startRtpOrRtcpPktRcvd(3),
        startRtcpPktRcvd(4)
        }
    ACCESS read-write
    STATUS mandatory
    DESCRIPTION
        "This object specifies when the RTCP receive timer
        is started.
        
        disabled              - timer is disabled
        startImmediately      - timer starts immediately 
                                as soon as RTCP is enabled
                                on the call
        startRtpOrRtcpPktRcvd - timer starts upon reception of
                                the first RTP or RTCP packet
        startRtcpPktRcvd      - timer starts upon reception of 
                                the first RTCP packet"
    DEFVAL { startRtcpPktRcvd }
    ::= { cdspVoiceParamEntry 8 }

cdspVqmControl OBJECT-TYPE
    SYNTAX INTEGER {
        disable(1),
        rfc3611Vqm(2),
        xnq(3)
        }
    ACCESS read-write
    STATUS mandatory
    DESCRIPTION
        "This object is used to disable VQM or enable either
        RFC 3611 RTCPXR or Extended Network Quality Metrics VQM.
        
        disable - VQM is disabled.
        rfc3611Vqm -  RFC 3611 RTCPXR. RTCPXR packet uses 
                      extended report block type as defined 
                      in RFC3611.
        xnq - Extended Network Quality Metrics.
        
        The difference between RFC 3611 RTCPXR and 
        Extended Network Quality Metrics is the extended 
        report block type used in RTCPXR packets.  
        RFC 3611 RTCPXR uses voip-metrics block type as defined
        in RFC3611.  Extended Network Quality Metrics 
        uses a proprietary block type.
        
        If this object is set to 'disabled', the RTP terminations 
        (object cmedxTermTypePkgIds in CISCO-MEGACO-EXT-MIB)
        on the card cannot be provisioned with the related packages, 
        rtcpxr or pkgXnq, respectively.
        
        If this object is set to 'rfc3611Vqm', the RTP
        terminations (object cmedxTermTypePkgIds in
        CISCO-MEGACO-EXT-MIB) on the card 
        can include package ID 'rtcpxr (27)' and/or 'xrbm (28)',
        but can not include package ID 'pkgXnq (32)'.
        
        If this object is set to 'xnq', the RTP
        terminations (object cmedxTermTypePkgIds in
        CISCO-MEGACO-EXT-MIB) on the card 
        can include package ID 'pkgXnq (32)', but can not
        include 'rtcpxr (27)' or 'xrbm (28)'."
    REFERENCE
        "RFC 3611"
    DEFVAL { disable }
    ::= { cdspVoiceParamEntry 9 }

cdspRtcpXrControl OBJECT-TYPE
    SYNTAX TruthValue
--    Rsyntax INTEGER {
--        true(1),
--        false(2)
--        }
    ACCESS read-write
    STATUS mandatory
    DESCRIPTION
        "This object controls if RTCPXR
        (Real Time Control Protocol Extended Report) is enabled.
        If this object is set to 'true', both transmission and 
        reception of RTCPXR packets are enabled; otherwise, 
        transmission of RTCPXR packets is disabled while any 
        received RTCPXR packets are ignored. 
        If object cdspVqmControl is set to 'xnq (3)', this
        object is read-only with the value of 'true'."
    DEFVAL { true }
    ::= { cdspVoiceParamEntry 10 }

cdspRtcpXrTransMultiplier OBJECT-TYPE
    SYNTAX Gauge(1..5)
    ACCESS read-write
    STATUS mandatory
    DESCRIPTION
        "This object is used to configure the RTCPXR report
        frequency. i.e. how many RTCP packets during the interval
        of every RTCPXR packet.
        The RTCPXR report is sent every 'cdspRtcpXrTransMultiplier'
        of RTCP packet.
        Example:
           If RTCP packet is sent every 10 ms(frequency of RTCP
        packet = 10 ms), and 'cdspRtcpXrTransMultiplier' is set
        to 3, then RTCPXR is sent every 3x10 ms = 30 ms(frequency
        of RTCPXR packet = 30 ms). 
        
        This object is applicable only if 'cdspRtcpXrControl' is
        set to 'true'.
        
        If object cdspVqmControl is set to 'xnq (3)', this
        object is read-only with the value of '1'."
    DEFVAL { 1 }
    ::= { cdspVoiceParamEntry 11 }

cdspRtcpXrGminDefault OBJECT-TYPE
    SYNTAX Gauge(1..255)
    ACCESS read-write
    STATUS mandatory
    DESCRIPTION
        "This object is the default minimum gap value configured
        for the IP stream.
        
        This object is applicable only if 'cdspVqmControl' is
        set to 'rfc3611Vqm'."
    REFERENCE
        "RFC3611"
    DEFVAL { 16 }
    ::= { cdspVoiceParamEntry 12 }

cdspRtcpXrExtRfactor OBJECT-TYPE
    SYNTAX Gauge(0..65535)
    ACCESS read-write
    STATUS mandatory
    DESCRIPTION
        "This object is the external R factor metric value.
        The value 127 means it is not applicable.
        
        This object is applicable only if 'cdspVqmControl' is
        set to 'rfc3611Vqm'.  
        When 'cdspVqmControl' is not 'rfc3611Vqm', this object
        is set to 127."
    DEFVAL { 127 }
    ::= { cdspVoiceParamEntry 13 }

cdspPktLossConcealment OBJECT-TYPE
    SYNTAX INTEGER {
        none(1),
        simple(2),
        g711A1(3)
        }
    ACCESS read-write
    STATUS mandatory
    DESCRIPTION
        "This object specifies the packet loss concealment:
        
        (1) none: No packet loss concealment applied
        (2) simple: Cisco Proprietary packet loss concealment
        (3) g711A1: ITU G.711 Appendix I compliant"
    REFERENCE
        "ITU G.711 Appendix 1"
    DEFVAL { simple }
    ::= { cdspVoiceParamEntry 14 }

cdspVqmThreshSES OBJECT-TYPE
    SYNTAX Gauge(10..1000)
--  Units
--    milliseconds
    ACCESS read-write
    STATUS mandatory
    DESCRIPTION
        "This attribute specifies the threshold for
        Severely Errored Second on VQM.  If the total 
        number of milliseconds sampled as bad voice quality
        in one second period exceeds threshold, then 
        this second is considered a 'severely errored second'.
        
        This object is applicable only if 'cdspVqmControl' is
        set to 'xnq'."
    DEFVAL { 50 }
    ::= { cdspVoiceParamEntry 15 }

cdspTransparentIpIp OBJECT-TYPE
    SYNTAX TruthValue
--    Rsyntax INTEGER {
--        true(1),
--        false(2)
--        }
    ACCESS read-write
    STATUS deprecated
    DESCRIPTION
        "This attribute is used to enable or disable the transparent
        mode when establishing a non-transcoding IP-IP connection.
        The attribute does not apply for the transcoding IP-IP
        connections.
        A non-transcoding connection is one where the codec and
        packetization period are the same between the two IP
        terminations.
        When this object is set to 'true', the non-transcoding IP-IP
        connection is established in such a way that the bearer stream
        is not interrupted by the gateway.
        When this object is set to 'false', the non-transcoding IP-IP
        connection is established in a way the gateway terminates the
        bearer stream at one leg, and regenerates the bearer stream at
        the other leg."
    DEFVAL { false }
    ::= { cdspVoiceParamEntry 16 }

cdspVoiceModeIpIp OBJECT-TYPE
    SYNTAX INTEGER {
        normal(1),
        fastRoute(2),
        transparent(3)
        }
    ACCESS read-write
    STATUS mandatory
    DESCRIPTION
        "This object specifies the voice mode for IP IP connections.
        normal     : A normal Mode is a transcoding mode for IP-IP 
                     connections where the bearer properties will 
                     be different on two ends of a call.
        fastRoute : A voice call will be esatblished in this mode 
                     when the codec is same on two ends of a call 
                     but packetization period is different.
        tranparent : A voice call will be established in transparent
                     mode when the all the bearer properties for a 
                     voice call are same on the two ends of a call."
    DEFVAL { normal }
    ::= { cdspVoiceParamEntry 17 }

cdspUtilTable OBJECT-TYPE
    SYNTAX SEQUENCE OF CdspUtilEntry
    ACCESS not-accessible
    STATUS mandatory
    DESCRIPTION
        "This table contains DSP utilization information for all the codec
        families available in codec template currently active on VXSM."
    ::= { cdspUtilObjects 1 }

cdspUtilEntry OBJECT-TYPE
    SYNTAX CdspUtilEntry
    ACCESS not-accessible
    STATUS mandatory
    DESCRIPTION
        "An entry (conceptual row) in cdspUtilTable indicates the
        DSP capacity usage.
        Each entry maps to a codec pool family , uniquely identified
        by cdspCodecPoolIndex, and displays corresponding
        utilized and available DSP channels.
        The entry is derived based on the codec families supported
        (DSP channels consumed by them) in the current codec template
        i.e the instance of cdspCodecTemplateSupported at start up 
        time by the system."
    INDEX { entPhysicalIndex, cdspCodecPoolIndex }
    ::= { cdspUtilTable 1 }

CdspUtilEntry ::= SEQUENCE {
    cdspCodecPoolIndex Gauge,
    cdspCurrentUtilCap Gauge,
    cdspCurrentAvlbCap Gauge
    }

cdspCodecPoolIndex OBJECT-TYPE
    SYNTAX Gauge(1..64)
    ACCESS not-accessible
    STATUS mandatory
    DESCRIPTION
        "This object identifies a row. Pool index is corresponding
        to the number of DSP channels utilized. The instance 
        identifier value of this object depends on the codec 
        template supported on this module as indicated by the
        value of corresponding instance of 'cdspCodecTemplateSupported' 
        of cdspCardStatusTable table. A pool index will map to
        codec family utilizing pool index number of DSP channels,
        codecs consuming same number of DSP channels will be part 
        of one family.
        
        Based on the value of the corresponding instance of
        'cdspCodecTemplateSupported', the possible instance 
        identifier values of 'cdspCodecPollIndex' specific
        set of codec families:
        Codec Template  Pool Index  Codec family
        tgw             1           G.711 family/HDLC/CCD
                        3           G.729/G.726/T.38 family
                        4           G.723 family
        cable           1           G.711 family/HDLC/T.38
                        3           iLBC family
        tgw2            1           G.711 family/HDLC/T.38
                        3           G.729/G.726/T.38 family
                        4           iLBC family
        fmc             1           G.711 family/HDLC/T.38
                        2           G.729/G.726/T.38 family
                        3           AMR/EFR family"
    ::= { cdspUtilEntry 1 }

cdspCurrentUtilCap OBJECT-TYPE
    SYNTAX Gauge
    ACCESS read-only
    STATUS mandatory
    DESCRIPTION
        "This object indicates the number of DSP channels which are
        currently being utilized corresponding to active calls on
        VXSM segregated on the basis of codec families."
    DEFVAL { 0 }
    ::= { cdspUtilEntry 2 }

cdspCurrentAvlbCap OBJECT-TYPE
    SYNTAX Gauge
    ACCESS read-only
    STATUS mandatory
    DESCRIPTION
        "This object indicates the number of DSP channels which are
        currently available on VXSM corresponding to a codec family."
    DEFVAL { 0 }
    ::= { cdspUtilEntry 3 }

cdspGlobMaxConfTranscodeSess OBJECT-TYPE
    SYNTAX Gauge(0..4294967295)
    ACCESS read-write
    STATUS mandatory
    DESCRIPTION
        "This object indicates the maximum transcode sessions
        configured globally for the voice gateway."
    ::= { cdspDspfarmObjects 1 }

cdspGlobMaxAvailTranscodeSess OBJECT-TYPE
    SYNTAX Gauge(0..4294967295)
    ACCESS read-only
    STATUS mandatory
    DESCRIPTION
        "This object indicates the total number of available sessions
        from the maximum transcode sessions configured globally for
        the voice gateway."
    ::= { cdspDspfarmObjects 2 }

cdspTranscodeProfileTable OBJECT-TYPE
    SYNTAX SEQUENCE OF CdspTranscodeProfileEntry
    ACCESS not-accessible
    STATUS mandatory
    DESCRIPTION
        "This table contains information about each transcode
        DSPFarm profile. It gives the maximum number of transcode
        sessions configured and the number of available
        sessions per profile."
    ::= { cdspDspfarmObjects 3 }

cdspTranscodeProfileEntry OBJECT-TYPE
    SYNTAX CdspTranscodeProfileEntry
    ACCESS not-accessible
    STATUS mandatory
    DESCRIPTION
        "An entry in cdspTranscodeProfileTable indicates the transcode
        DSPFarm profile maximum configured sessions and available
        sessions. Each DSPFarm transcode profile configured in the 
        voice gateway forms a new entry to this table. The entry is
        deleted when the transcode DSPFarm profile is deleted.
        
        A new entry to this table can be created and an existing
        entry can be deleted using object cdspTranscodeProfileRowStatus
        indexed with a profile number."
    INDEX { cdspTranscodeProfileId }
    ::= { cdspTranscodeProfileTable 1 }

CdspTranscodeProfileEntry ::= SEQUENCE {
    cdspTranscodeProfileId Gauge,
    cdspTranscodeProfileMaxConfSess Gauge,
    cdspTranscodeProfileMaxAvailSess Gauge,
    cdspTranscodeProfileRowStatus RowStatus
    }

cdspTranscodeProfileId OBJECT-TYPE
    SYNTAX Gauge(1..4294967295)
    ACCESS not-accessible
    STATUS mandatory
    DESCRIPTION
        "This object indicates the profile number
        of the DSPFarm transcode profile."
    ::= { cdspTranscodeProfileEntry 1 }

cdspTranscodeProfileMaxConfSess OBJECT-TYPE
    SYNTAX Gauge(0..4294967295)
    ACCESS read-write
    STATUS mandatory
    DESCRIPTION
        "This object indicates the maximum transcode sessions
        configured on the DSPFarm transcode profile for the
        voice gateway."
    ::= { cdspTranscodeProfileEntry 2 }

cdspTranscodeProfileMaxAvailSess OBJECT-TYPE
    SYNTAX Gauge(0..4294967295)
    ACCESS read-only
    STATUS mandatory
    DESCRIPTION
        "This object indicates the total number of available
        transcode sessions per transcode profile from the 
        configured maximum transcode sessions per transcode 
        profile for the voice gateway."
    ::= { cdspTranscodeProfileEntry 3 }

cdspTranscodeProfileRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create a new entry or delete
        an existing entry in cdspTranscodeProfileTable.
        
        The storage type for all the entries created would 
        be volatile. To retain the configured entries. One must
        write the configuration to memory in the voice gateway."
    ::= { cdspTranscodeProfileEntry 4 }

cdspMtpProfileTable OBJECT-TYPE
    SYNTAX SEQUENCE OF CdspMtpProfileEntry
    ACCESS not-accessible
    STATUS mandatory
    DESCRIPTION
        "This table contains information about each MTP
        DSPFarm profile. It gives the maximum number of MTP
        sessions configured and the number of available
        sessions per profile."
    ::= { cdspDspfarmObjects 4 }

cdspMtpProfileEntry OBJECT-TYPE
    SYNTAX CdspMtpProfileEntry
    ACCESS not-accessible
    STATUS mandatory
    DESCRIPTION
        "An entry in cdspMtpProfileTable indicates the MTP
        DSPFarm profile maximum configured sessions and available
        sessions. Each DSPFarm MTP profile configured in the 
        voice gateway forms a new entry to this table. The entry is
        deleted when the MTP DSPFarm profile is deleted. 
        
        A new entry to this table can be created and an existing
        entry can be deleted using object cdspMtpProfileRowStatus
        indexed with a profile number."
    INDEX { cdspMtpProfileId }
    ::= { cdspMtpProfileTable 1 }

CdspMtpProfileEntry ::= SEQUENCE {
    cdspMtpProfileId Gauge,
    cdspMtpProfileMaxConfSoftSess Gauge,
    cdspMtpProfileMaxConfHardSess Gauge,
    cdspMtpProfileMaxAvailHardSess Gauge,
    cdspMtpProfileRowStatus RowStatus
    }

cdspMtpProfileId OBJECT-TYPE
    SYNTAX Gauge(1..4294967295)
    ACCESS not-accessible
    STATUS mandatory
    DESCRIPTION
        "This object indicates the profile number
        of the DSPFarm MTP profile."
    ::= { cdspMtpProfileEntry 1 }

cdspMtpProfileMaxConfSoftSess OBJECT-TYPE
    SYNTAX Gauge(0..4294967295)
    ACCESS read-write
    STATUS mandatory
    DESCRIPTION
        "This object indicates the maximum MTP software
        sessions configured per DSPFarm MTP profile for the 
        voice gateway."
    ::= { cdspMtpProfileEntry 2 }

cdspMtpProfileMaxConfHardSess OBJECT-TYPE
    SYNTAX Gauge(0..4294967295)
    ACCESS read-write
    STATUS mandatory
    DESCRIPTION
        "This object indicates the maximum MTP hardware
        sessions configured per DSPFarm MTP profile for the
        voice gateway."
    ::= { cdspMtpProfileEntry 3 }

cdspMtpProfileMaxAvailHardSess OBJECT-TYPE
    SYNTAX Gauge(0..4294967295)
    ACCESS read-only
    STATUS mandatory
    DESCRIPTION
        "This object indicates the total number of available
        MTP sessions per MTP profile from the configured
        maximum MTP sessions per MTP profile for the voice
        gateway."
    ::= { cdspMtpProfileEntry 4 }

cdspMtpProfileRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create a new entry or delete
        an existing entry in cdspMtpProfileTable.
        
        The storage type for all the entries created would 
        be volatile. To retain the configured entries. One must
        write the configuration to memory in the voice gateway."
    ::= { cdspMtpProfileEntry 5 }

cdspTotAvailTranscodeSess OBJECT-TYPE
    SYNTAX Gauge(0..4294967295)
    ACCESS read-only
    STATUS mandatory
    DESCRIPTION
        "This object indicates the total number of transcode
        sessions available for the voice gateway. The value
        is equal to summation of all the values returned by
        transcode profile object cdspTranscodeProfileMaxAvailSess."
    ::= { cdspDspfarmUtilObjects 1 }

cdspTotUnusedTranscodeSess OBJECT-TYPE
    SYNTAX Gauge(0..4294967295)
    ACCESS read-only
    STATUS mandatory
    DESCRIPTION
        "This object indicates the total number of unused
        transcode sessions."
    ::= { cdspDspfarmUtilObjects 2 }

cdspTotAvailMtpSess OBJECT-TYPE
    SYNTAX Gauge(0..4294967295)
    ACCESS read-only
    STATUS mandatory
    DESCRIPTION
        "This object indicates the total number of MTP sessions
        available for the voice gateway. The value is equal to
        summation of all the values returned by MTP profile
        object cdspMtpProfileMaxAvailHardSess."
    ::= { cdspDspfarmUtilObjects 3 }

cdspTotUnusedMtpSess OBJECT-TYPE
    SYNTAX Gauge(0..4294967295)
    ACCESS read-only
    STATUS mandatory
    DESCRIPTION
        "This object indicates the total number of unused MTP
        sessions."
    ::= { cdspDspfarmUtilObjects 4 }

cdspMIBEnableCardStatusNotification OBJECT-TYPE
    SYNTAX TruthValue
--    Rsyntax INTEGER {
--        true(1),
--        false(2)
--        }
    ACCESS read-write
    STATUS mandatory
    DESCRIPTION
        "This variable controls whether the system
        produces the cdspMIBCardStateNotification.  A false
        value will prevent DSP card fatal notifications
        from being generated by this system."
    DEFVAL { false }
    ::= { cdspMIBNotificationEnables 1 }

cdspEnableOperStateNotification OBJECT-TYPE
    SYNTAX TruthValue
--    Rsyntax INTEGER {
--        true(1),
--        false(2)
--        }
    ACCESS read-write
    STATUS mandatory
    DESCRIPTION
        "This variable controls whether the system
        produces the cdspOperStateNotification. A false
        value will prevent a DSP operational state
        notification from being generated by this system."
    DEFVAL { false }
    ::= { cdspMIBNotificationEnables 2 }

cdspVideoUsageNotificationEnable OBJECT-TYPE
    SYNTAX TruthValue
--    Rsyntax INTEGER {
--        true(1),
--        false(2)
--        }
    ACCESS read-write
    STATUS mandatory
    DESCRIPTION
        "This object specifies whether the system produces
        cdspVideoUsageNotification. 
        
        'true': Video usage notification is generated by this system.
        'false': Video usage notification is not generated by this
        system."
    ::= { cdspMIBNotificationEnables 3 }

cdspVideoOutOfResourceNotificationEnable OBJECT-TYPE
    SYNTAX TruthValue
--    Rsyntax INTEGER {
--        true(1),
--        false(2)
--        }
    ACCESS read-write
    STATUS mandatory
    DESCRIPTION
        "This object specifies whether the system produces
        cdspVideoOutOfResourceNotification. 
        
        'true': Video out-of-resource notification is generated by this
        system.
        'false': Video out-of-resource notification is not generated by
        this system."
    ::= { cdspMIBNotificationEnables 4 }

cdspMIBCardStateNotification TRAP-TYPE
-- Reverse mappable trap
    ENTERPRISE cdspMIBNotificationPrefix
    VARIABLES {
        cdspCardState }
--  Status
--    mandatory
    DESCRIPTION
        "A cdspMIBCardStateNotification is sent when the cdspCardState
        enters into normal(1) state and enters into or exits from
        fatal(4) state."
    ::= 1

cdspOperStateNotification TRAP-TYPE
-- Reverse mappable trap
    ENTERPRISE cdspMIBNotificationPrefix
    VARIABLES {
        cdspOperState, entPhysicalName }
--  Status
--    mandatory
    DESCRIPTION
        "A cdspOperStateNotification is sent when the cdspOperState
        enters into normal(1) state or shutdown(2) state.
        The value of entPhysicalName contains the name of the
        DSP."
    ::= 2

cdspVideoUsageNotification TRAP-TYPE
-- Reverse mappable trap
    ENTERPRISE cdspMIBNotificationPrefix
    VARIABLES {
        cdspCardVideoPoolUtilization, 
        cdspCardVideoPoolUtilizationThreshold }
--  Status
--    mandatory
    DESCRIPTION
        "This notification is sent when cdspCardVideoPoolUtilization
        reaches the specified threshold 
        (cdspCardVideoPoolUtilizationThreshold).
        
        cdspCardVideoPoolUtilization indicates the DSP video pool usage
        at the time this notification is sent.
        cdspCardVideoPoolUtilizationThreshold indicates the threshold
        configured to trigger this notification.
        
        DSP video pool resource usage (cdspCardVideoPoolUtilization) is
        updated and compared against the threshold
        (cdspCardVideoPoolUtilizationThreshold) in the events below:
            1.  A call that requires DSP video resource connects.
            2.  A call that requires DSP video resource disconnects.
            3.  DSPFarm profile for video resource is enabled.
            4.  DSPFarm profile for video resource is disabled.
        During comparison, if usage is larger than threshold, this 
        notification is generated."
    ::= 3

cdspVideoOutOfResourceNotification TRAP-TYPE
-- Reverse mappable trap
    ENTERPRISE cdspMIBNotificationPrefix
    VARIABLES {
        cdspCardVideoPoolUtilization, 
        cdspCardVideoPoolUtilizationThreshold }
--  Status
--    mandatory
    DESCRIPTION
        "A cdspVideoOutOfResourceNotification is sent when there is not
        enough DSP resource in the video pool of the system for video
        services.
        
        cdspCardVideoPoolUtilization indicates the DSP video pool usage
        at the time this notification is sent.
        cdspCardVideoPoolUtilizationThreshold indicates the threshold
        configured to trigger this notification.
        
        DSP video resources required is computed for each incoming call
        that requires DSP video resources.  If there is not enough
        video resource, this call will not have any video capabilities
        and is treated as audio-only; and this notification is
        generated."
    ::= 4

cdspMgmtGeneralInfoGroup OBJECT IDENTIFIER ::= { cdspMgmtGroups 1 }
-- OBJECT-GROUP
--  Status
--    deprecated
--  Descr
--    A collection of objects providing the Digital Signal
--    Processing related information.
--  objects
--    cdspCardIndex, cdspCardState, cdspCardResourceUtilization, 
--    cdspCardLastHiWaterUtilization, cdspCardLastResetTime, 
--    cdspOperState, cdspAlarms, cdspLastAlarmCause, 
--    cdspLastAlarmCauseText, cdspLastAlarmTime, 
--    cdspMIBEnableCardStatusNotification

cdspChannelGroup OBJECT IDENTIFIER ::= { cdspMgmtGroups 2 }
-- OBJECT-GROUP
--  Status
--    mandatory
--  Descr
--    A collection of objects providing information
--    specific for multiple channels per DSP.
--  objects
--    cdspCardMaxChanPerDSP, cdspTotalChannels, cdspInUseChannels, 
--    cdspActiveChannels

cdspMgmtExtGeneralInfoGroup OBJECT IDENTIFIER ::= { cdspMgmtGroups 3 }
-- OBJECT-GROUP
--  Status
--    deprecated
--  Descr
--    A collection of objects providing information for DSP.
--  objects
--    cdspTotalDsp, cdspFailedDsp, cdspCongestedDsp, cdspNormalDsp, 
--    cdspDspSwitchOverThreshold, cdspNx64Dsp, cdspDspNum

cdspVoiceInfoGroup OBJECT IDENTIFIER ::= { cdspMgmtGroups 4 }
-- OBJECT-GROUP
--  Status
--    deprecated
--  Descr
--    A collection of objects providing DSP voice
--    application parameters.
--  objects
--    cdspRtpSidPayloadType, cdspRtcpControl, cdspRtcpTransInterval, 
--    cdspRtcpRecvMultiplier, cdspVadAdaptive, cdspDtmfPowerLevel, 
--    cdspDtmfPowerTwist

cdspChannelExtGroup OBJECT IDENTIFIER ::= { cdspMgmtGroups 6 }
-- OBJECT-GROUP
--  Status
--    mandatory
--  Descr
--    A collection of objects providing DSP channels
--    splitting information.
--  objects
--    cdspSigBearerChannelSplit, cdspNumCongestionOccurrence, 
--    cdspXNumberOfBearerCalls, cdspXNumberOfSigCalls, 
--    cdspXAvailableBearerBandwidth, cdspXAvailableSigBandwidth

cdspVoiceInfoGroupRev1 OBJECT IDENTIFIER ::= { cdspMgmtGroups 7 }
-- OBJECT-GROUP
--  Status
--    deprecated
--  Descr
--    A collection of objects providing DSP voice
--    application parameters.
--  objects
--    cdspRtpSidPayloadType, cdspRtcpControl, cdspRtcpTransInterval, 
--    cdspRtcpRecvMultiplier, cdspVadAdaptive, cdspDtmfPowerLevel, 
--    cdspDtmfPowerTwist, cdspRtcpTimerControl

cdspMgmtExtGeneralInfoGroupRev1 OBJECT IDENTIFIER ::= { cdspMgmtGroups 8 }
-- OBJECT-GROUP
--  Status
--    mandatory
--  Descr
--    This group replaces cdspMgmtExtGeneralInfoGroup.
--    A collection of objects providing information for DSP.
--  objects
--    cdspTotalDsp, cdspFailedDsp, cdspCongestedDsp, cdspNormalDsp, 
--    cdspDspSwitchOverThreshold, cdspNx64Dsp, cdspDspNum, 
--    cdspCodecTemplateSupported

cdspMgmtGeneralInfoGroupRev1 OBJECT IDENTIFIER ::= { cdspMgmtGroups 9 }
-- OBJECT-GROUP
--  Status
--    mandatory
--  Descr
--    A collection of objects providing the Digital Signal
--    Processing related information.
--  objects
--    cdspCardIndex, cdspCardState, cdspCardResourceUtilization, 
--    cdspCardLastHiWaterUtilization, cdspCardLastResetTime, 
--    cdspOperState, cdspAlarms, cdspLastAlarmCause, 
--    cdspLastAlarmCauseText, cdspLastAlarmTime, 
--    cdspMIBEnableCardStatusNotification, 
--    cdspEnableOperStateNotification

cdspVQMGroup OBJECT IDENTIFIER ::= { cdspMgmtGroups 11 }
-- OBJECT-GROUP
--  Status
--    mandatory
--  Descr
--    This group includs VQM (Voice Quality Monitor)
--    related information. It is mandatory only if
--    VQM is supported.
--  objects
--    cdspVqmControl, cdspRtcpXrControl, cdspRtcpXrTransMultiplier, 
--    cdspRtcpXrGminDefault, cdspRtcpXrExtRfactor, cdspVqmThreshSES

cdspVoiceInfoGroupRev2 OBJECT IDENTIFIER ::= { cdspMgmtGroups 12 }
-- OBJECT-GROUP
--  Status
--    mandatory
--  Descr
--    A collection of objects providing DSP voice
--    application parameters.
--  objects
--    cdspRtpSidPayloadType, cdspRtcpControl, cdspRtcpTransInterval, 
--    cdspRtcpRecvMultiplier, cdspVadAdaptive, cdspDtmfPowerLevel, 
--    cdspDtmfPowerTwist, cdspRtcpTimerControl, 
--    cdspPktLossConcealment

cdspTransCodingGroup OBJECT IDENTIFIER ::= { cdspMgmtGroups 13 }
-- OBJECT-GROUP
--  Status
--    deprecated
--  Descr
--    A collection of objects providing DSP
--    transcoding related parameters.
--  objects
--    cdspTransparentIpIp

cdspTransCodingGroup1 OBJECT IDENTIFIER ::= { cdspMgmtGroups 14 }
-- OBJECT-GROUP
--  Status
--    mandatory
--  Descr
--    A collection of objects providing DSP
--    transcoding related parameters for voice.
--  objects
--    cdspVoiceModeIpIp

cdspUtilInfoGroup OBJECT IDENTIFIER ::= { cdspMgmtGroups 15 }
-- OBJECT-GROUP
--  Status
--    mandatory
--  Descr
--    A collection of objects providing DSP
--    codec capacity usage .
--  objects
--    cdspCurrentUtilCap, cdspCurrentAvlbCap

cdspDspfarmInfoGroup OBJECT IDENTIFIER ::= { cdspMgmtGroups 16 }
-- OBJECT-GROUP
--  Status
--    mandatory
--  Descr
--    A collection of objects providing DSPFarm
--    session configuration, availability and 
--    utilization.
--  objects
--    cdspGlobMaxConfTranscodeSess, cdspGlobMaxAvailTranscodeSess, 
--    cdspTranscodeProfileRowStatus, 
--    cdspTranscodeProfileMaxConfSess, 
--    cdspTranscodeProfileMaxAvailSess, cdspMtpProfileRowStatus, 
--    cdspMtpProfileMaxConfSoftSess, cdspMtpProfileMaxConfHardSess, 
--    cdspMtpProfileMaxAvailHardSess, cdspTotAvailTranscodeSess, 
--    cdspTotUnusedTranscodeSess, cdspTotAvailMtpSess, 
--    cdspTotUnusedMtpSess

cdspMgmtVideoInfoGroup OBJECT IDENTIFIER ::= { cdspMgmtGroups 18 }
-- OBJECT-GROUP
--  Status
--    mandatory
--  Descr
--    A collection of objects related to DSP video resource.
--  objects
--    cdspCardVideoPoolUtilization, 
--    cdspCardVideoPoolUtilizationThreshold, 
--    cdspVideoUsageNotificationEnable, 
--    cdspVideoOutOfResourceNotificationEnable

cdspMgmtNotificationsGroup OBJECT IDENTIFIER ::= { cdspMgmtGroups 5 }
-- NOTIFICATION-GROUP
--  Status
--    deprecated
--  Descr
--    The notifications which a DSP Management entity is
--    required to implement.
--  notifications
--    cdspMIBCardStateNotification

cdspMgmtNotificationsGroupRev1 OBJECT IDENTIFIER ::= { cdspMgmtGroups 10 }
-- NOTIFICATION-GROUP
--  Status
--    mandatory
--  Descr
--    The notifications which a DSP Management entity is
--    required to implement.
--  notifications
--    cdspMIBCardStateNotification, cdspOperStateNotification

cdspMgmtVideoNotificationsGroup OBJECT IDENTIFIER ::= { cdspMgmtGroups 17 }
-- NOTIFICATION-GROUP
--  Status
--    mandatory
--  Descr
--    A collection of notifications related to DSP video resource.
--  notifications
--    cdspVideoUsageNotification, 
--    cdspVideoOutOfResourceNotification

cdspMgmtCompliance OBJECT IDENTIFIER ::= { cdspMgmtCompliances 1 }
-- MODULE-COMPLIANCE
--  Status
--    deprecated
--  Descr
--    The compliance statement for systems that contain a
--    Cisco DSP card and its associated DSPs.
--  Module
--    >>current<<
--   MandGroup
--    cdspMgmtGeneralInfoGroup

cdspMgmtComplianceRev1 OBJECT IDENTIFIER ::= { cdspMgmtCompliances 2 }
-- MODULE-COMPLIANCE
--  Status
--    deprecated
--  Descr
--    The compliance statement for systems that contain a
--    Cisco DSP card and its associated DSPs.
--  Module
--    >>current<<
--   MandGroup
--    cdspMgmtGeneralInfoGroup
--   OptGroup
--    cdspChannelGroup

cdspMgmtComplianceRev2 OBJECT IDENTIFIER ::= { cdspMgmtCompliances 3 }
-- MODULE-COMPLIANCE
--  Status
--    deprecated
--  Descr
--    The compliance statement for systems that contain a
--    Cisco DSP card and its associated DSPs.
--  Module
--    >>current<<
--   MandGroup
--    cdspMgmtGeneralInfoGroup
--   MandGroup
--    cdspMgmtNotificationsGroup
--   OptGroup
--    cdspMgmtExtGeneralInfoGroup
--   OptGroup
--    cdspChannelGroup
--   OptGroup
--    cdspChannelExtGroup
--   OptGroup
--    cdspVoiceInfoGroup

cdspMgmtComplianceRev3 OBJECT IDENTIFIER ::= { cdspMgmtCompliances 4 }
-- MODULE-COMPLIANCE
--  Status
--    deprecated
--  Descr
--    The compliance statement for systems that contain a
--    Cisco DSP card and its associated DSPs.
--  Module
--    >>current<<
--   MandGroup
--    cdspMgmtGeneralInfoGroup
--   MandGroup
--    cdspMgmtNotificationsGroup
--   OptGroup
--    cdspMgmtExtGeneralInfoGroup
--   OptGroup
--    cdspChannelGroup
--   OptGroup
--    cdspChannelExtGroup
--   OptGroup
--    cdspVoiceInfoGroupRev1

cdspMgmtComplianceRev4 OBJECT IDENTIFIER ::= { cdspMgmtCompliances 5 }
-- MODULE-COMPLIANCE
--  Status
--    deprecated
--  Descr
--    The compliance statement for systems that contain a
--    Cisco DSP card and its associated DSPs.
--    This replaces cdspMgmtComplianceRev3.
--  Module
--    >>current<<
--   OptGroup
--    cdspMgmtExtGeneralInfoGroupRev1
--   OptGroup
--    cdspChannelGroup
--   OptGroup
--    cdspChannelExtGroup
--   OptGroup
--    cdspVoiceInfoGroupRev1

cdspMgmtComplianceRev5 OBJECT IDENTIFIER ::= { cdspMgmtCompliances 6 }
-- MODULE-COMPLIANCE
--  Status
--    deprecated
--  Descr
--    The compliance statement for systems that contain a
--    Cisco DSP card and its associated DSPs.
--    This replaces cdspMgmtComplianceRev4.
--  Module
--    >>current<<
--   MandGroup
--    cdspMgmtGeneralInfoGroupRev1
--   MandGroup
--    cdspMgmtNotificationsGroupRev1
--   OptGroup
--    cdspMgmtExtGeneralInfoGroupRev1
--   OptGroup
--    cdspChannelGroup
--   OptGroup
--    cdspChannelExtGroup
--   OptGroup
--    cdspVoiceInfoGroupRev1
--   OptGroup
--    cdspVQMGroup

cdspMgmtComplianceRev6 OBJECT IDENTIFIER ::= { cdspMgmtCompliances 7 }
-- MODULE-COMPLIANCE
--  Status
--    deprecated
--  Descr
--    The compliance statement for systems that contain a
--    Cisco DSP card and its associated DSPs.
--    This replaces cdspMgmtComplianceRev5.
--  Module
--    >>current<<
--   MandGroup
--    cdspMgmtGeneralInfoGroupRev1
--   MandGroup
--    cdspMgmtNotificationsGroupRev1
--   OptGroup
--    cdspMgmtExtGeneralInfoGroupRev1
--   OptGroup
--    cdspChannelGroup
--   OptGroup
--    cdspChannelExtGroup
--   OptGroup
--    cdspVQMGroup
--   OptGroup
--    cdspVoiceInfoGroupRev2

cdspMgmtComplianceRev7 OBJECT IDENTIFIER ::= { cdspMgmtCompliances 8 }
-- MODULE-COMPLIANCE
--  Status
--    deprecated
--  Descr
--    The compliance statement for systems that contain a
--    Cisco DSP card and its associated DSPs.
--    This replaces cdspMgmtComplianceRev5.
--  Module
--    >>current<<
--   MandGroup
--    cdspMgmtGeneralInfoGroupRev1
--   MandGroup
--    cdspMgmtNotificationsGroupRev1
--   OptGroup
--    cdspMgmtExtGeneralInfoGroupRev1
--   OptGroup
--    cdspChannelGroup
--   OptGroup
--    cdspChannelExtGroup
--   OptGroup
--    cdspVQMGroup
--   OptGroup
--    cdspVoiceInfoGroupRev2
--   OptGroup
--    cdspTransCodingGroup

cdspMgmtComplianceRev8 OBJECT IDENTIFIER ::= { cdspMgmtCompliances 9 }
-- MODULE-COMPLIANCE
--  Status
--    deprecated
--  Descr
--    The compliance statement for systems that contain a
--    Cisco DSP card and its associated DSPs.
--  Module
--    >>current<<
--   MandGroup
--    cdspMgmtGeneralInfoGroupRev1
--   MandGroup
--    cdspMgmtNotificationsGroupRev1
--   OptGroup
--    cdspMgmtExtGeneralInfoGroupRev1
--   OptGroup
--    cdspChannelGroup
--   OptGroup
--    cdspChannelExtGroup
--   OptGroup
--    cdspVQMGroup
--   OptGroup
--    cdspVoiceInfoGroupRev2
--   OptGroup
--    cdspTransCodingGroup1

cdspMgmtComplianceRev9 OBJECT IDENTIFIER ::= { cdspMgmtCompliances 10 }
-- MODULE-COMPLIANCE
--  Status
--    deprecated
--  Descr
--    The compliance statement for systems that contain a
--    Cisco DSP card and its associated DSPs.
--  Module
--    >>current<<
--   MandGroup
--    cdspMgmtGeneralInfoGroupRev1
--   MandGroup
--    cdspMgmtNotificationsGroupRev1
--   OptGroup
--    cdspMgmtExtGeneralInfoGroupRev1
--   OptGroup
--    cdspChannelGroup
--   OptGroup
--    cdspChannelExtGroup
--   OptGroup
--    cdspVQMGroup
--   OptGroup
--    cdspVoiceInfoGroupRev2
--   OptGroup
--    cdspTransCodingGroup1
--   OptGroup
--    cdspUtilInfoGroup

cdspMgmtComplianceRev10 OBJECT IDENTIFIER ::= { cdspMgmtCompliances 11 }
-- MODULE-COMPLIANCE
--  Status
--    deprecated
--  Descr
--    The compliance statement for systems that contain a
--    Cisco DSP card and its associated DSPs.
--  Module
--    >>current<<
--   MandGroup
--    cdspMgmtGeneralInfoGroupRev1
--   MandGroup
--    cdspMgmtNotificationsGroupRev1
--   OptGroup
--    cdspMgmtExtGeneralInfoGroupRev1
--   OptGroup
--    cdspChannelGroup
--   OptGroup
--    cdspChannelExtGroup
--   OptGroup
--    cdspVQMGroup
--   OptGroup
--    cdspVoiceInfoGroupRev2
--   OptGroup
--    cdspTransCodingGroup1
--   OptGroup
--    cdspUtilInfoGroup
--   OptGroup
--    cdspDspfarmInfoGroup

cdspMgmtComplianceRev11 OBJECT IDENTIFIER ::= { cdspMgmtCompliances 12 }
-- MODULE-COMPLIANCE
--  Status
--    mandatory
--  Descr
--    The compliance statement for systems that contain a
--    Cisco DSP card and its associated DSPs.
--  Module
--    >>current<<
--   MandGroup
--    cdspMgmtGeneralInfoGroupRev1
--   MandGroup
--    cdspMgmtNotificationsGroupRev1
--   OptGroup
--    cdspMgmtExtGeneralInfoGroupRev1
--   OptGroup
--    cdspChannelGroup
--   OptGroup
--    cdspChannelExtGroup
--   OptGroup
--    cdspVQMGroup
--   OptGroup
--    cdspVoiceInfoGroupRev2
--   OptGroup
--    cdspTransCodingGroup1
--   OptGroup
--    cdspUtilInfoGroup
--   OptGroup
--    cdspDspfarmInfoGroup
--   OptGroup
--    cdspMgmtVideoInfoGroup
--   OptGroup
--    cdspMgmtVideoNotificationsGroup
--   ObjVar
--    cdspVideoUsageNotificationEnable
--   ObjVar
--    cdspVideoOutOfResourceNotificationEnable
--   ObjVar
--    cdspCardVideoPoolUtilizationThreshold


END
