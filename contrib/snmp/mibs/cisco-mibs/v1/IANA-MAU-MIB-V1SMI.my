-- MIB file created 21-May-2010 19:13:12, by
--   SMICng version 2.2.11-beta(PRO)(Solaris), January 20, 2001. Enterprise key cisco.com

IANA-MAU-MIB DEFINITIONS ::= BEGIN

-- From file: "IANA-MAU-MIB.my"
-- Compile options "4 7 F H N W 03 06 0B 0G 0N 0T"

IMPORTS
    mib-2
            FROM SNMPv2-SMI-v1;

ianaMauMIB OBJECT IDENTIFIER ::= { mib-2 154 }
-- MODULE-IDENTITY
--  LastUpdated
--    201002230000Z
--  OrgName
--    IANA
--  ContactInfo
--            Internet Assigned Numbers Authority
--    
--     Postal: ICANN
--             4676 Admiralty Way, Suite 330
--             Marina del Rey, CA 90292
--    
--        Tel: +1-310-823-9358
--      EMail: iana&iana.org
--  Descr
--    This MIB module defines dot3MauType OBJECT-IDENTITIES and
--    IANAifMauListBits, IANAifMauMediaAvailable,
--    IANAifMauAutoNegCapBits, and IANAifJackType
--    
--    TEXTUAL-CONVENTIONs, specifying enumerated values of the
--    ifMauTypeListBits, ifMauMediaAvailable / rpMauMediaAvailable,
--    ifMauAutoNegCapabilityBits / ifMauAutoNegCapAdvertisedBits /
--    ifMauAutoNegCapReceivedBits and ifJackType / rpJackType objects
--    respectively, defined in the MAU-MIB.
--    
--    It is intended that each new MAU type, Media Availability
--    state, Auto Negotiation capability and/or Jack type defined by
--    the IEEE 802.3 working group and approved for publication in a
--    revision of IEEE Std 802.3 will be added to this MIB module,
--    provided that it is suitable for being managed by the base
--    objects in the MAU-MIB.  An Expert Review, as defined in
--    RFC 2434 [RFC2434], is REQUIRED for such additions.
--    
--    The following reference is used throughout this MIB module:
--    
--    [IEEE802.3] refers to:
--       IEEE Std 802.3, 2005 Edition: 'IEEE Standard for
--       Information technology - Telecommunications and information
--       exchange between systems - Local and metropolitan area
--       networks - Specific requirements -
--       Part 3: Carrier sense multiple access with collision
--       detection (CSMA/CD) access method and physical layer
--       specifications'.
--    
--    This reference should be updated as appropriate when new
--    MAU types, Media Availability states, Auto Negotiation
--    capabilities, and/or Jack types are added to this MIB module.
--    
--    Copyright (C) The IETF Trust (2007).
--    The initial version of this MIB module was published in
--    RFC 4836; for full legal notices see the RFC itself.
--    Supplementary information may be available at:
--    http://www.ietf.org/copyrights/ianamib.html
--  RevDate
--    201002230000Z
--  RevDescr
--    Added assignments that will be included in 
--     Clause 14 of IEEE P802.3.1.
--  RevDate
--    200704210000Z
--  RevDescr
--    Initial version of this MIB as published in
--     RFC 4836.

dot3MauType     OBJECT IDENTIFIER ::= { mib-2 snmpDot3MauMgt(26) 4 }

dot3MauTypeAUI OBJECT IDENTIFIER ::= { dot3MauType 1 }
-- OBJECT-IDENTITY
--  Status
--    mandatory
--  Descr
--    no internal MAU, view from AUI
--  Refer
--    [IEEE802.3], Section 7

dot3MauType10Base5 OBJECT IDENTIFIER ::= { dot3MauType 2 }
-- OBJECT-IDENTITY
--  Status
--    mandatory
--  Descr
--    thick coax MAU
--  Refer
--    [IEEE802.3], Section 7

dot3MauTypeFoirl OBJECT IDENTIFIER ::= { dot3MauType 3 }
-- OBJECT-IDENTITY
--  Status
--    mandatory
--  Descr
--    FOIRL MAU
--  Refer
--    [IEEE802.3], Section 9.9

dot3MauType10Base2 OBJECT IDENTIFIER ::= { dot3MauType 4 }
-- OBJECT-IDENTITY
--  Status
--    mandatory
--  Descr
--    thin coax MAU
--  Refer
--    [IEEE802.3], Section 10

dot3MauType10BaseT OBJECT IDENTIFIER ::= { dot3MauType 5 }
-- OBJECT-IDENTITY
--  Status
--    mandatory
--  Descr
--    UTP MAU.
--    Note that it is strongly recommended that
--    agents return either dot3MauType10BaseTHD or
--    dot3MauType10BaseTFD if the duplex mode is
--    known.  However, management applications should
--    be prepared to receive this MAU type value from
--    older agent implementations.
--  Refer
--    [IEEE802.3], Section 14

dot3MauType10BaseFP OBJECT IDENTIFIER ::= { dot3MauType 6 }
-- OBJECT-IDENTITY
--  Status
--    mandatory
--  Descr
--    passive fiber MAU
--  Refer
--    [IEEE802.3], Section 16

dot3MauType10BaseFB OBJECT IDENTIFIER ::= { dot3MauType 7 }
-- OBJECT-IDENTITY
--  Status
--    mandatory
--  Descr
--    sync fiber MAU
--  Refer
--    [IEEE802.3], Section 17

dot3MauType10BaseFL OBJECT IDENTIFIER ::= { dot3MauType 8 }
-- OBJECT-IDENTITY
--  Status
--    mandatory
--  Descr
--    async fiber MAU.
--    Note that it is strongly recommended that
--    agents return either dot3MauType10BaseFLHD or
--    dot3MauType10BaseFLFD if the duplex mode is
--    known.  However, management applications should
--    be prepared to receive this MAU type value from
--    older agent implementations.
--  Refer
--    [IEEE802.3], Section 18

dot3MauType10Broad36 OBJECT IDENTIFIER ::= { dot3MauType 9 }
-- OBJECT-IDENTITY
--  Status
--    mandatory
--  Descr
--    broadband DTE MAU.
--    Note that 10BROAD36 MAUs can be attached to
--    interfaces but not to repeaters.
--  Refer
--    [IEEE802.3], Section 11

dot3MauType10BaseTHD OBJECT IDENTIFIER ::= { dot3MauType 10 }
-- OBJECT-IDENTITY
--  Status
--    mandatory
--  Descr
--    UTP MAU, half duplex mode
--  Refer
--    [IEEE802.3], Section 14

dot3MauType10BaseTFD OBJECT IDENTIFIER ::= { dot3MauType 11 }
-- OBJECT-IDENTITY
--  Status
--    mandatory
--  Descr
--    UTP MAU, full duplex mode
--  Refer
--    [IEEE802.3], Section 14

dot3MauType10BaseFLHD OBJECT IDENTIFIER ::= { dot3MauType 12 }
-- OBJECT-IDENTITY
--  Status
--    mandatory
--  Descr
--    async fiber MAU, half duplex mode
--  Refer
--    [IEEE802.3], Section 18

dot3MauType10BaseFLFD OBJECT IDENTIFIER ::= { dot3MauType 13 }
-- OBJECT-IDENTITY
--  Status
--    mandatory
--  Descr
--    async fiber MAU, full duplex mode
--  Refer
--    [IEEE802.3], Section 18

dot3MauType100BaseT4 OBJECT IDENTIFIER ::= { dot3MauType 14 }
-- OBJECT-IDENTITY
--  Status
--    mandatory
--  Descr
--    4 pair category 3 UTP
--  Refer
--    [IEEE802.3], Section 23

dot3MauType100BaseTXHD OBJECT IDENTIFIER ::= { dot3MauType 15 }
-- OBJECT-IDENTITY
--  Status
--    mandatory
--  Descr
--    2 pair category 5 UTP, half duplex mode
--  Refer
--    [IEEE802.3], Section 25

dot3MauType100BaseTXFD OBJECT IDENTIFIER ::= { dot3MauType 16 }
-- OBJECT-IDENTITY
--  Status
--    mandatory
--  Descr
--    2 pair category 5 UTP, full duplex mode
--  Refer
--    [IEEE802.3], Section 25

dot3MauType100BaseFXHD OBJECT IDENTIFIER ::= { dot3MauType 17 }
-- OBJECT-IDENTITY
--  Status
--    mandatory
--  Descr
--    X fiber over PMT, half duplex mode
--  Refer
--    [IEEE802.3], Section 26

dot3MauType100BaseFXFD OBJECT IDENTIFIER ::= { dot3MauType 18 }
-- OBJECT-IDENTITY
--  Status
--    mandatory
--  Descr
--    X fiber over PMT, full duplex mode
--  Refer
--    [IEEE802.3], Section 26

dot3MauType100BaseT2HD OBJECT IDENTIFIER ::= { dot3MauType 19 }
-- OBJECT-IDENTITY
--  Status
--    mandatory
--  Descr
--    2 pair category 3 UTP, half duplex mode
--  Refer
--    [IEEE802.3], Section 32

dot3MauType100BaseT2FD OBJECT IDENTIFIER ::= { dot3MauType 20 }
-- OBJECT-IDENTITY
--  Status
--    mandatory
--  Descr
--    2 pair category 3 UTP, full duplex mode
--  Refer
--    [IEEE802.3], Section 32

dot3MauType1000BaseXHD OBJECT IDENTIFIER ::= { dot3MauType 21 }
-- OBJECT-IDENTITY
--  Status
--    mandatory
--  Descr
--    PCS/PMA, unknown PMD, half duplex mode
--  Refer
--    [IEEE802.3], Section 36

dot3MauType1000BaseXFD OBJECT IDENTIFIER ::= { dot3MauType 22 }
-- OBJECT-IDENTITY
--  Status
--    mandatory
--  Descr
--    PCS/PMA, unknown PMD, full duplex mode
--  Refer
--    [IEEE802.3], Section 36

dot3MauType1000BaseLXHD OBJECT IDENTIFIER ::= { dot3MauType 23 }
-- OBJECT-IDENTITY
--  Status
--    mandatory
--  Descr
--    Fiber over long-wavelength laser, half duplex
--    mode
--  Refer
--    [IEEE802.3], Section 38

dot3MauType1000BaseLXFD OBJECT IDENTIFIER ::= { dot3MauType 24 }
-- OBJECT-IDENTITY
--  Status
--    mandatory
--  Descr
--    Fiber over long-wavelength laser, full duplex
--    mode
--  Refer
--    [IEEE802.3], Section 38

dot3MauType1000BaseSXHD OBJECT IDENTIFIER ::= { dot3MauType 25 }
-- OBJECT-IDENTITY
--  Status
--    mandatory
--  Descr
--    Fiber over short-wavelength laser, half
--    duplex mode
--  Refer
--    [IEEE802.3], Section 38

dot3MauType1000BaseSXFD OBJECT IDENTIFIER ::= { dot3MauType 26 }
-- OBJECT-IDENTITY
--  Status
--    mandatory
--  Descr
--    Fiber over short-wavelength laser, full
--    duplex mode
--  Refer
--    [IEEE802.3], Section 38

dot3MauType1000BaseCXHD OBJECT IDENTIFIER ::= { dot3MauType 27 }
-- OBJECT-IDENTITY
--  Status
--    mandatory
--  Descr
--    Copper over 150-Ohm balanced cable, half
--    duplex mode
--  Refer
--    [IEEE802.3], Section 39

dot3MauType1000BaseCXFD OBJECT IDENTIFIER ::= { dot3MauType 28 }
-- OBJECT-IDENTITY
--  Status
--    mandatory
--  Descr
--    Copper over 150-Ohm balanced cable, full
--    
--    duplex mode
--  Refer
--    [IEEE802.3], Section 39

dot3MauType1000BaseTHD OBJECT IDENTIFIER ::= { dot3MauType 29 }
-- OBJECT-IDENTITY
--  Status
--    mandatory
--  Descr
--    Four-pair Category 5 UTP, half duplex mode
--  Refer
--    [IEEE802.3], Section 40

dot3MauType1000BaseTFD OBJECT IDENTIFIER ::= { dot3MauType 30 }
-- OBJECT-IDENTITY
--  Status
--    mandatory
--  Descr
--    Four-pair Category 5 UTP, full duplex mode
--  Refer
--    [IEEE802.3], Section 40

dot3MauType10GigBaseX OBJECT IDENTIFIER ::= { dot3MauType 31 }
-- OBJECT-IDENTITY
--  Status
--    mandatory
--  Descr
--    X PCS/PMA, unknown PMD.
--  Refer
--    [IEEE802.3], Section 48

dot3MauType10GigBaseLX4 OBJECT IDENTIFIER ::= { dot3MauType 32 }
-- OBJECT-IDENTITY
--  Status
--    mandatory
--  Descr
--    X fiber over WWDM optics
--  Refer
--    [IEEE802.3], Section 53

dot3MauType10GigBaseR OBJECT IDENTIFIER ::= { dot3MauType 33 }
-- OBJECT-IDENTITY
--  Status
--    mandatory
--  Descr
--    R PCS/PMA, unknown PMD.
--  Refer
--    [IEEE802.3], Section 49

dot3MauType10GigBaseER OBJECT IDENTIFIER ::= { dot3MauType 34 }
-- OBJECT-IDENTITY
--  Status
--    mandatory
--  Descr
--    R fiber over 1550 nm optics
--  Refer
--    [IEEE802.3], Section 52

dot3MauType10GigBaseLR OBJECT IDENTIFIER ::= { dot3MauType 35 }
-- OBJECT-IDENTITY
--  Status
--    mandatory
--  Descr
--    R fiber over 1310 nm optics
--  Refer
--    [IEEE802.3], Section 52

dot3MauType10GigBaseSR OBJECT IDENTIFIER ::= { dot3MauType 36 }
-- OBJECT-IDENTITY
--  Status
--    mandatory
--  Descr
--    R fiber over 850 nm optics
--  Refer
--    [IEEE802.3], Section 52

dot3MauType10GigBaseW OBJECT IDENTIFIER ::= { dot3MauType 37 }
-- OBJECT-IDENTITY
--  Status
--    mandatory
--  Descr
--    W PCS/PMA, unknown PMD.
--  Refer
--    [IEEE802.3], Section 49 and 50

dot3MauType10GigBaseEW OBJECT IDENTIFIER ::= { dot3MauType 38 }
-- OBJECT-IDENTITY
--  Status
--    mandatory
--  Descr
--    W fiber over 1550 nm optics
--  Refer
--    [IEEE802.3], Section 52

dot3MauType10GigBaseLW OBJECT IDENTIFIER ::= { dot3MauType 39 }
-- OBJECT-IDENTITY
--  Status
--    mandatory
--  Descr
--    W fiber over 1310 nm optics
--  Refer
--    [IEEE802.3], Section 52

dot3MauType10GigBaseSW OBJECT IDENTIFIER ::= { dot3MauType 40 }
-- OBJECT-IDENTITY
--  Status
--    mandatory
--  Descr
--    W fiber over 850 nm optics
--  Refer
--    [IEEE802.3], Section 52

dot3MauType10GigBaseCX4 OBJECT IDENTIFIER ::= { dot3MauType 41 }
-- OBJECT-IDENTITY
--  Status
--    mandatory
--  Descr
--    X copper over 8 pair 100-Ohm balanced cable
--  Refer
--    [IEEE802.3], Section 54

dot3MauType2BaseTL OBJECT IDENTIFIER ::= { dot3MauType 42 }
-- OBJECT-IDENTITY
--  Status
--    mandatory
--  Descr
--    Voice grade UTP copper, up to 2700m, optional PAF
--  Refer
--    [IEEE802.3], Sections 61 and 63

dot3MauType10PassTS OBJECT IDENTIFIER ::= { dot3MauType 43 }
-- OBJECT-IDENTITY
--  Status
--    mandatory
--  Descr
--    Voice grade UTP copper, up to 750m, optional PAF
--  Refer
--    [IEEE802.3], Sections 61 and 62

dot3MauType100BaseBX10D OBJECT IDENTIFIER ::= { dot3MauType 44 }
-- OBJECT-IDENTITY
--  Status
--    mandatory
--  Descr
--    One single-mode fiber OLT, long wavelength, 10km
--  Refer
--    [IEEE802.3], Section 58

dot3MauType100BaseBX10U OBJECT IDENTIFIER ::= { dot3MauType 45 }
-- OBJECT-IDENTITY
--  Status
--    mandatory
--  Descr
--    One single-mode fiber ONU, long wavelength, 10km
--  Refer
--    [IEEE802.3], Section 58

dot3MauType100BaseLX10 OBJECT IDENTIFIER ::= { dot3MauType 46 }
-- OBJECT-IDENTITY
--  Status
--    mandatory
--  Descr
--    Two single-mode fibers, long wavelength, 10km
--  Refer
--    [IEEE802.3], Section 58

dot3MauType1000BaseBX10D OBJECT IDENTIFIER ::= { dot3MauType 47 }
-- OBJECT-IDENTITY
--  Status
--    mandatory
--  Descr
--    One single-mode fiber OLT, long wavelength, 10km
--  Refer
--    [IEEE802.3], Section 59

dot3MauType1000BaseBX10U OBJECT IDENTIFIER ::= { dot3MauType 48 }
-- OBJECT-IDENTITY
--  Status
--    mandatory
--  Descr
--    One single-mode fiber ONU, long wavelength, 10km
--  Refer
--    [IEEE802.3], Section 59

dot3MauType1000BaseLX10 OBJECT IDENTIFIER ::= { dot3MauType 49 }
-- OBJECT-IDENTITY
--  Status
--    mandatory
--  Descr
--    Two sigle-mode fiber, long wavelength, 10km
--  Refer
--    [IEEE802.3], Section 59

dot3MauType1000BasePX10D OBJECT IDENTIFIER ::= { dot3MauType 50 }
-- OBJECT-IDENTITY
--  Status
--    mandatory
--  Descr
--    One single-mode fiber EPON OLT, 10km
--  Refer
--    [IEEE802.3], Section 60

dot3MauType1000BasePX10U OBJECT IDENTIFIER ::= { dot3MauType 51 }
-- OBJECT-IDENTITY
--  Status
--    mandatory
--  Descr
--    One single-mode fiber EPON ONU, 10km
--  Refer
--    [IEEE802.3], Section 60

dot3MauType1000BasePX20D OBJECT IDENTIFIER ::= { dot3MauType 52 }
-- OBJECT-IDENTITY
--  Status
--    mandatory
--  Descr
--    One single-mode fiber EPON OLT, 20km
--  Refer
--    [IEEE802.3], Section 60

dot3MauType1000BasePX20U OBJECT IDENTIFIER ::= { dot3MauType 53 }
-- OBJECT-IDENTITY
--  Status
--    mandatory
--  Descr
--    One single-mode fiber EPON ONU, 20km
--  Refer
--    [IEEE802.3], Section 60

dot3MauType10GbaseT OBJECT IDENTIFIER ::= { dot3MauType 54 }
-- OBJECT-IDENTITY
--  Status
--    mandatory
--  Descr
--    Four-pair Category 6A or better, full duplex mode only
--  Refer
--    IEEE Std 802.3, Clause 55

dot3MauType10GbaseLRM OBJECT IDENTIFIER ::= { dot3MauType 55 }
-- OBJECT-IDENTITY
--  Status
--    mandatory
--  Descr
--    R multimode fiber over 1310 nm optics
--  Refer
--    IEEE Std 802.3, Clause 68

dot3MauType1000baseKX OBJECT IDENTIFIER ::= { dot3MauType 56 }
-- OBJECT-IDENTITY
--  Status
--    mandatory
--  Descr
--    X backplane, full duplex mode only
--  Refer
--    IEEE Std 802.3, Clause 70

dot3MauType10GbaseKX4 OBJECT IDENTIFIER ::= { dot3MauType 57 }
-- OBJECT-IDENTITY
--  Status
--    mandatory
--  Descr
--    4 lane X backplane, full duplex mode only
--  Refer
--    IEEE Std 802.3, Clause 71

dot3MauType10GbaseKR OBJECT IDENTIFIER ::= { dot3MauType 58 }
-- OBJECT-IDENTITY
--  Status
--    mandatory
--  Descr
--    R backplane, full duplex mode only
--  Refer
--    IEEE Std 802.3, Clause 72

dot3MauType10G1GbasePRXD1 OBJECT IDENTIFIER ::= { dot3MauType 59 }
-- OBJECT-IDENTITY
--  Status
--    mandatory
--  Descr
--    One single-mode fiber asymmetric-rate EPON OLT, supporting low
--     power budget (PRX10)
--  Refer
--    IEEE Std 802.3, Clause 75

dot3MauType10G1GbasePRXD2 OBJECT IDENTIFIER ::= { dot3MauType 60 }
-- OBJECT-IDENTITY
--  Status
--    mandatory
--  Descr
--    One single-mode fiber asymmetric-rate EPON OLT, supporting
--    medium power budget (PRX20)
--  Refer
--    IEEE Std 802.3, Clause 75

dot3MauType10G1GbasePRXD3 OBJECT IDENTIFIER ::= { dot3MauType 61 }
-- OBJECT-IDENTITY
--  Status
--    mandatory
--  Descr
--    One single-mode fiber asymmetric-rate EPON OLT, supporting high
--    power budget (PRX30)
--  Refer
--    IEEE Std 802.3, Clause 75

dot3MauType10G1GbasePRXU1 OBJECT IDENTIFIER ::= { dot3MauType 62 }
-- OBJECT-IDENTITY
--  Status
--    mandatory
--  Descr
--    One single-mode fiber asymmetric-rate EPON ONU, supporting low
--    power budget (PRX10)
--  Refer
--    IEEE Std 802.3, Clause 75

dot3MauType10G1GbasePRXU2 OBJECT IDENTIFIER ::= { dot3MauType 63 }
-- OBJECT-IDENTITY
--  Status
--    mandatory
--  Descr
--    One single-mode fiber asymmetric-rate EPON ONU, supporting
--    medium power budget (PRX20)
--  Refer
--    IEEE Std 802.3, Clause 75

dot3MauType10G1GbasePRXU3 OBJECT IDENTIFIER ::= { dot3MauType 64 }
-- OBJECT-IDENTITY
--  Status
--    mandatory
--  Descr
--    One single-mode fiber asymmetric-rate EPON ONU, supporting high
--    power budget (PRX30)
--  Refer
--    IEEE Std 802.3, Clause 75

dot3MauType10GbasePRD1 OBJECT IDENTIFIER ::= { dot3MauType 65 }
-- OBJECT-IDENTITY
--  Status
--    mandatory
--  Descr
--    One single-mode fiber symmetric-rate EPON OLT, supporting low
--    power budget (PR10)
--  Refer
--    IEEE Std 802.3, Clause 75

dot3MauType10GbasePRD2 OBJECT IDENTIFIER ::= { dot3MauType 66 }
-- OBJECT-IDENTITY
--  Status
--    mandatory
--  Descr
--    One single-mode fiber symmetric-rate EPON OLT, supporting
--    medium power budget (PR20)
--  Refer
--    IEEE Std 802.3, Clause 75

dot3MauType10GbasePRD3 OBJECT IDENTIFIER ::= { dot3MauType 67 }
-- OBJECT-IDENTITY
--  Status
--    mandatory
--  Descr
--    One single-mode fiber symmetric-rate EPON OLT, supporting high
--    power budget (PR30)
--  Refer
--    IEEE Std 802.3, Clause 75

dot3MauType10GbasePRU1 OBJECT IDENTIFIER ::= { dot3MauType 68 }
-- OBJECT-IDENTITY
--  Status
--    mandatory
--  Descr
--    One single-mode fiber symmetric-rate EPON ONU, supporting
--    low and medium power budget (PR10 and PR20)
--  Refer
--    IEEE Std 802.3, Clause 75

dot3MauType10GbasePRU3 OBJECT IDENTIFIER ::= { dot3MauType 69 }
-- OBJECT-IDENTITY
--  Status
--    mandatory
--  Descr
--    One single-mode fiber symmetric-rate EPON ONU, supporting high
--    power budget (PR30)
--  Refer
--    IEEE Std 802.3, Clause 75

IANAifMauTypeListBits ::= OCTET STRING(SIZE(1..9))
        -- BITS are:
        --   bOther(0)
        --   bAUI(1)
        --   b10base5(2)
        --   bFoirl(3)
        --   b10base2(4)
        --   b10baseT(5)
        --   b10baseFP(6)
        --   b10baseFB(7)
        --   b10baseFL(8)
        --   b10broad36(9)
        --   b10baseTHD(10)
        --   b10baseTFD(11)
        --   b10baseFLHD(12)
        --   b10baseFLFD(13)
        --   b100baseT4(14)
        --   b100baseTXHD(15)
        --   b100baseTXFD(16)
        --   b100baseFXHD(17)
        --   b100baseFXFD(18)
        --   b100baseT2HD(19)
        --   b100baseT2FD(20)
        --   b1000baseXHD(21)
        --   b1000baseXFD(22)
        --   b1000baseLXHD(23)
        --   b1000baseLXFD(24)
        --   b1000baseSXHD(25)
        --   b1000baseSXFD(26)
        --   b1000baseCXHD(27)
        --   b1000baseCXFD(28)
        --   b1000baseTHD(29)
        --   b1000baseTFD(30)
        --   b10GbaseX(31)
        --   b10GbaseLX4(32)
        --   b10GbaseR(33)
        --   b10GbaseER(34)
        --   b10GbaseLR(35)
        --   b10GbaseSR(36)
        --   b10GbaseW(37)
        --   b10GbaseEW(38)
        --   b10GbaseLW(39)
        --   b10GbaseSW(40)
        --   b10GbaseCX4(41)
        --   b2BaseTL(42)
        --   b10PassTS(43)
        --   b100BaseBX10D(44)
        --   b100BaseBX10U(45)
        --   b100BaseLX10(46)
        --   b1000BaseBX10D(47)
        --   b1000BaseBX10U(48)
        --   b1000BaseLX10(49)
        --   b1000BasePX10D(50)
        --   b1000BasePX10U(51)
        --   b1000BasePX20D(52)
        --   b1000BasePX20U(53)
        --   b10GbaseT(54)
        --   b10GbaseLRM(55)
        --   b1000baseKX(56)
        --   b10GbaseKX4(57)
        --   b10GbaseKR(58)
        --   b10G1GbasePRXD1(59)
        --   b10G1GbasePRXD2(60)
        --   b10G1GbasePRXD3(61)
        --   b10G1GbasePRXU1(62)
        --   b10G1GbasePRXU2(63)
        --   b10G1GbasePRXU3(64)
        --   b10GbasePRD1(65)
        --   b10GbasePRD2(66)
        --   b10GbasePRD3(67)
        --   b10GbasePRU1(68)
        --   b10GbasePRU3(69)
-- TEXTUAL-CONVENTION
--  Status
--    mandatory
--  Descr
--    This data type is used as the syntax of the ifMauTypeListBits
--    object in the (updated) definition of MAU-MIB's ifMauTable.
--    
--    The most recent version of this textual convention is available
--    in the online version of this MIB module on the IANA web site.
--    
--    Requests for new values should be made to IANA via email
--    (iana&iana.org).
--    
--    Note that changes in this textual convention SHALL be
--    synchronized with relevant changes in the dot3MauType
--    OBJECT-IDENTITIES.
--  Refer
--    [IEEE802.3], Section 30.5.1.1.2

IANAifMauMediaAvailable ::= INTEGER {
        other(1),
        unknown(2),
        available(3),
        notAvailable(4),
        remoteFault(5),
        invalidSignal(6),
        remoteJabber(7),
        remoteLinkLoss(8),
        remoteTest(9),
        offline(10),
        autoNegError(11),
        pmdLinkFault(12),
        wisFrameLoss(13),
        wisSignalLoss(14),
        pcsLinkFault(15),
        excessiveBER(16),
        dxsLinkFault(17),
        pxsLinkFault(18),
        availableReduced(19),
        ready(20)
        }
-- TEXTUAL-CONVENTION
--  Status
--    mandatory
--  Descr
--    This data type is used as the syntax of the
--    ifMauMediaAvailable and rpMauMediaAvailable objects in the
--    (updated) definition of MAU-MIB's ifMauTable and rpMauTable
--    respectively.
--    
--    Possible values are:
--      other(1)             - undefined (not listed below)
--      unknown(2)           - MAU's true state is unknown; e.g.,
--                             during initialization
--      available(3)         - link, light, or loopback is normal
--      notAvailable(4)      - link loss, low light, or no loopback
--      remoteFault(5)       - a fault has been detected at the
--                             remote end of the link.  This value
--                             applies to 10BASE-FB, 100BASE-T4 Far
--                             End Fault Indication and non-specified
--                             remote faults from a system running
--                             auto-negotiation
--      invalidSignal(6)     - invalid signal has been received from
--                             the other end of the link, 10BASE-FB
--                             only
--      remoteJabber(7)      - remote fault, due to jabber
--    
--      remoteLinkLoss(8)    - remote fault, due to link loss
--      remoteTest(9)        - remote fault, due to test
--      offline(10)          - offline, Clause 37 Auto-Negotiation
--                             only
--      autoNegError(11)     - Auto-Negotiation Error, Clause 37
--                             Auto-Negotiation only
--      pmdLinkFault(12)     - PMA/PMD receive link fault.  In case
--                             of PAF (2BASE-TL / 10PASS-TS PHYs),
--                             all PMEs in the aggregation group have
--                             detected a link fault
--      wisFrameLoss(13)     - WIS loss of frame, 10GBASE-W only
--      wisSignalLoss(14)    - WIS loss of signal, 10GBASE-W only
--      pcsLinkFault(15)     - PCS receive link fault
--      excessiveBER(16)     - PCS Bit Error Ratio monitor
--                             reporting excessive error ratio
--      dxsLinkFault(17)     - DTE XGXS receive link fault, XAUI only
--      pxsLinkFault(18)     - PHY XGXS receive link fault, XAUI only
--      availableReduced(19) - link normal, reduced bandwidth,
--                             2BASE-TL / 10PASS-TS only
--      ready(20)            - at least one PME in the aggregation
--                             group is detecting handshake tones,
--                             2BASE-TL / 10PASS-TS only
--    
--    If the MAU is a 10M b/s link or fiber type (FOIRL, 10BASE-T,
--    10BASE-F), then this is equivalent to the link test fail
--    state/low light function.  For an AUI, 10BASE2, 10BASE5, or
--    10BROAD36 MAU, this indicates whether loopback is detected on
--    the DI circuit.  The value of this attribute persists between
--    packets for MAU types AUI, 10BASE5, 10BASE2, 10BROAD36, and
--    10BASEFP.
--    
--    At power-up or following a reset, the Media Available state
--    will be unknown(2) for AUI, 10BASE5, 10BASE2, 10BROAD36, and
--    10BASE-FP MAUs.  For these MAUs loopback will be tested on each
--    transmission during which no collision is detected.
--    If DI is receiving input when DO returns to IDL after a
--    transmission and there has been no collision during the
--    transmission, then loopback will be detected.  The Media
--    Available state will only change during noncollided
--    transmissions for AUI, 10BASE2, 10BASE5, 10BROAD36, and
--    10BASE-FP MAUs.
--    
--    For 100BASE-T2, 100BASE-T4, 100BASE-TX, 100BASE-FX,
--    100BASE-LX10, and 100BASE-BX10 PHYs the enumerations match the
--    states within the link integrity state diagram.
--    Any MAU that implements management of [IEEE802.3] Clause
--    28 Auto-Negotiation, will map remote fault indication to
--    remoteFault(5).
--    
--    Any MAU that implements management of Clause 37
--    Auto-Negotiation, will map the received RF1 and RF2 bits as
--    follows: Offline maps to offline(10), Link_Failure maps to
--    remoteFault(5), and Auto-Negotiation Error maps to
--    autoNegError(11).
--    
--    The value remoteFault(5) applies to 10BASE-FB remote
--    fault indication, the 100BASE-X far-end fault indication, and
--    nonspecified remote faults from a system running Clause 28
--    Auto-Negotiation.
--    
--    The value remoteJabber(7), remoteLink loss(8), or remoteTest(9)
--    SHOULD be used instead of remoteFault(5) where the reason for
--    remote fault is identified in the remote signaling protocol.
--    Where a Clause 22 MII or Clause 35 GMII is present, a logic
--    one in the remote fault bit maps to the value remoteFault(5),
--    a logic zero in the link status bit maps to the enumeration
--    notAvailable(4).  The value notAvailable(4) takes precedence
--    over remoteFault(5).
--    
--    For 2BASE-TL and 10PASS-TS PHYs, the value unknown(2) maps to
--    the condition where the PHY (PCS with connected PMEs) is
--    initializing, the value ready(20) maps to the condition where
--    the interface is down and at least one PME in the aggregation
--    group is ready for handshake, the value available(3) maps to
--    the condition where all the PMEs in the aggregation group are
--    up, the value notAvailable(4) maps to the condition where all
--    the PMEs in the aggregation group are down and no handshake
--    tones are detected, the value availableReduced(19) maps to the
--    condition where the interface is up, a link fault is detected
--    at the receive direction by one or more PMEs in the
--    aggregation group, but at least one PME is up and the
--    enumeration pmdLinkFault(12) maps to the condition where a link
--    fault is detected at the receive direction by all of the PMEs
--    in the aggregation group.
--    
--    For 10 Gb/s the enumerations map to value of the link_fault
--    variable within the Link Fault Signaling state diagram
--    as follows: the value OK maps to the value available(3),
--    the value Local Fault maps to the value notAvailable(4),
--    and the value Remote Fault maps to the value remoteFault(5).
--    The value pmdLinkFault(12), wisFrameLoss(13),
--    wisSignalLoss(14), pcsLinkFault(15), excessiveBER(16), or
--    dxsLinkFault(17) SHOULD be used instead of the value
--    notAvailable(4), where the reason for the Local Fault state can
--    be identified through the use of the Clause 45 MDIO Interface.
--    Where multiple reasons for the Local Fault state can be
--    identified, only the highest precedence error SHOULD be
--    
--    reported.  This precedence in descending order is as follows:
--    
--      pxsLinkFault
--      pmdLinkFault
--      wisFrameLoss
--      wisSignalLoss
--      pcsLinkFault
--      excessiveBER
--      dxsLinkFault.
--    
--    Where a Clause 45 MDIO interface is present a logic zero in
--    the PMA/PMD Receive link status bit ([IEEE802.3]
--    Section 45.2.1.2.2) maps to the value pmdLinkFault(12),
--    logic one in the LOF status bit (Section 45.2.2.10.4) maps
--    to the value wisFrameLoss(13), a logic one in the LOS
--    status bit (Section 45.2.2.10.5) maps to the value
--    wisSignalLoss, a logic zero in the PCS Receive
--    link status bit (Section 45.2.3.2.2) maps to the value
--    pcsLinkFault(15), a logic one in the 10GBASE-R PCS Latched
--    high BER status bit (Section 45.2.3.12.2) maps to the value
--    excessiveBER, a logic zero in the DTE XS receive link status
--    bit (Section 45.2.5.2.2) maps to the value dxsLinkFault(17)
--    and a logic zero in the PHY XS transmit link status bit
--    (Section 45.2.4.2.2) maps to the value pxsLinkFault(18).
--    
--    The most recent version of this textual convention is available
--    in the online version of this MIB module on the IANA web site.
--    
--    Requests for new values should be made to IANA via email
--    (iana&iana.org).
--  Refer
--    [IEEE802.3], Section 30.5.1.1.4

IANAifMauAutoNegCapBits ::= OCTET STRING(SIZE(1..3))
        -- BITS are:
        --   bOther(0)
        --   b10baseT(1)
        --   b10baseTFD(2)
        --   b100baseT4(3)
        --   b100baseTX(4)
        --   b100baseTXFD(5)
        --   b100baseT2(6)
        --   b100baseT2FD(7)
        --   bFdxPause(8)
        --   bFdxAPause(9)
        --   bFdxSPause(10)
        --   bFdxBPause(11)
        --   b1000baseX(12)
        --   b1000baseXFD(13)
        --   b1000baseT(14)
        --   b1000baseTFD(15)
        --   b10GbaseT(16)
        --   b1000baseKX(17)
        --   b10GbaseKX4(18)
        --   b10GbaseKR(19)
-- TEXTUAL-CONVENTION
--  Status
--    mandatory
--  Descr
--    This data type is used as the syntax of the
--    ifMauAutoNegCapabilityBits, ifMauAutoNegCapAdvertisedBits, and
--    ifMauAutoNegCapReceivedBits objects in the (updated) definition
--    of MAU-MIB's ifMauAutoNegTable.
--    
--    The most recent version of this textual convention is available
--    in the online version of this MIB module on the IANA web site.
--    
--    Requests for new values should be made to IANA via email
--    (iana&iana.org).
--  Refer
--    [IEEE802.3], Section 30.6.1.1.5

IANAifJackType ::= INTEGER {
        other(1),
        rj45(2),
        rj45S(3),
        db9(4),
        bnc(5),
        fAUI(6),
        mAUI(7),
        fiberSC(8),
        fiberMIC(9),
        fiberST(10),
        telco(11),
        mtrj(12),
        hssdc(13),
        fiberLC(14),
        cx4(15)
        }
-- TEXTUAL-CONVENTION
--  Status
--    mandatory
--  Descr
--    Common enumeration values for repeater and interface MAU
--    jack types.  This data type is used as the syntax of the
--    ifJackType and rpJackType objects in the (updated) definition
--    of MAU-MIB's ifJackTable and rpJackTable respectively.
--    
--    Possible values are:
--         other(1)          - undefined or unknown
--         rj45(2)           - RJ45
--         rj45S(3)          - RJ45 shielded
--         db9(4)            - DB9
--         bnc(5)            - BNC
--         fAUI(6)           - AUI female
--         mAUI(7)           - AUI male
--         fiberSC(8)        - SC fiber
--         fiberMIC(9)       - MIC fiber
--         fiberST(10)       - ST fiber
--         telco(11)         - Telco
--         mtrj(12)          - MT-RJ fiber
--         hssdc(13)         - fiber channel style-2
--         fiberLC(14)       - LC fiber
--         cx4(15)           - IB4X for 10GBASE-CX4
--    
--    The most recent version of this textual convention is available
--    in the online version of this MIB module on the IANA web site.
--    
--    Requests for new values should be made to IANA via email
--    (iana&iana.org).


END
