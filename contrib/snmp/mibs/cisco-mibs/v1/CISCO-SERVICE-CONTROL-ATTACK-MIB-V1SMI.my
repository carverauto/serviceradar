-- MIB file created 04-Sep-2013 02:19:48, by
--   SMICng version 2.2.11-beta(PRO)(Solaris), January 20, 2001. Enterprise key cisco.com

CISCO-SERVICE-CONTROL-ATTACK-MIB DEFINITIONS ::= BEGIN

-- From file: "CISCO-SERVICE-CONTROL-ATTACK-MIB.my"
-- Compile options "4 7 F H N W 03 06 0B 0G 0N 0T"

IMPORTS
    entPhysicalIndex, entPhysicalName
            FROM ENTITY-MIB
    InetAddressType, InetAddress, InetPortNumber
            FROM INET-ADDRESS-MIB
    TruthValue, TimeStamp, TimeInterval, AutonomousType
            FROM SNMPv2-TC-v1
    ciscoMgmt
            FROM CISCO-SMI
    Counter, Gauge
            FROM RFC1155-SMI
    OBJECT-TYPE
            FROM RFC-1212
    TRAP-TYPE
            FROM RFC-1215;

ciscoServiceControlAttackMIB OBJECT IDENTIFIER ::= { ciscoMgmt 693 }
-- MODULE-IDENTITY
--  LastUpdated
--    201308160000Z
--  OrgName
--    Cisco Systems, Inc.
--  ContactInfo
--    Cisco Systems
--    Customer Service
--    
--    Postal: 170 W Tasman Drive
--    San Jose, CA  95134
--    USA
--    
--    Tel: +1 800 553-NETS
--    
--    E-mail: cs-excelsior-dev@cisco.com
--  Descr
--    This MIB provides data related to different types of
--    attacks detected by a service control entity.
--    
--    A service control entity is a network device which monitors and
--    controls traffic.  The service control entity is used as a
--    platform for different service control applications which may
--    perform monitoring operations beyond packet counting and delve 
--    
--    deeper into the contents of network traffic.  It provides
--    programmable stateful inspection of bidirectional
--    traffic flows and maps these flows with user/subscriber
--    ownership.
--    
--    An attack is a malicious network activity with certain traffic
--    characteristics and which is targeted on a certain network
--    entity.  An attack can be identified by its type, direction,
--    source address, destination address and ports.
--    
--    Once an attack is detected, an attack filter is activated based
--    on the type of the attack and corresponding actions are taken
--    in
--    the monitored network - this is referred to as attack start. 
--    For example the attack filter can drop the attacking traffic. 
--    When the attack detector identifies that the attack
--    characteristics are no longer exist, it ends the mitigation
--    action - what is referred to as attack end.  The attack
--    mitigation action is also referred to as attack filtering in
--    this MIB.
--    
--    The time duration of attack filtering between attack start to
--    attack end along with the direction (upstream, downstream) is
--    also maintained by the service control entity.  Attack
--    filtering
--    can be applied from the subscriber side to the network side, in
--    the upstream direction.  The downstream attack filtering is
--    done
--    from the network side to the subscriber side.
--    
--    This MIB also defines notifications generated by the service
--    control entity when an attack is detected on a monitored
--    network.
--  RevDate
--    201308160000Z
--  RevDescr
--    Updates to support traps for global attacks. For this
--    1. A new trap is introduced: cscaGlobalAttackFilterChange.
--    2. A new object is introduced: cscaGlobalAtackType to describe
--    the type of global attack.
--    3. A 3 groups are introduced: 
--            a. cscaMIBNotificationGroupRev1, deprecating
--    cscaMIBNotificationGroup.
--            b. cscaFilterObjectGroupRev1, deprecating
--    cscaFilterObjectGroup.
--            c. cscaMIBNotifControlGroupRev1, deprecating
--    cscaMIBNotifControlGroup
--    4. A new compliance is introduced:
--    cscaMIBComplianceRev1, deprecating cscaMIBCompliance.
--  RevDate
--    200905050000Z
--  RevDescr
--    Initial version of this MIB module.

ciscoServiceControlAttackMIBNotifs OBJECT IDENTIFIER ::= { ciscoServiceControlAttackMIB 0 }
ciscoServiceControlAttackMIBObjects OBJECT IDENTIFIER ::= { ciscoServiceControlAttackMIB 1 }
ciscoServiceControlAttackMIBConform OBJECT IDENTIFIER ::= { ciscoServiceControlAttackMIB 2 }
cscaFilterMIBObjects OBJECT IDENTIFIER ::= { ciscoServiceControlAttackMIBObjects 1 }
cscaMIBCompliances OBJECT IDENTIFIER ::= { ciscoServiceControlAttackMIBConform 1 }
cscaMIBGroups   OBJECT IDENTIFIER ::= { ciscoServiceControlAttackMIBConform 2 }

CscaAttackType ::= INTEGER
-- TEXTUAL-CONVENTION
--  DspHint
--    d
--  Status
--    mandatory
--  Descr
--    A value which identifies the various attack types which may be
--    detected by the service control entity.

cscaTypeTable OBJECT-TYPE
    SYNTAX SEQUENCE OF CscaTypeEntry
    ACCESS not-accessible
    STATUS mandatory
    DESCRIPTION
        "This table lists the aggregated statistics for each detected
        attack in a network controlled by a service control entity."
    ::= { ciscoServiceControlAttackMIBObjects 2 }

cscaTypeEntry OBJECT-TYPE
    SYNTAX CscaTypeEntry
    ACCESS not-accessible
    STATUS mandatory
    DESCRIPTION
        "This entry contains information for an attack detected by the
        service control entity.
        
        The service control entity can report a number of attack types,
        the cscaTypeTable is created during the initialization of the
        service control entity and is valid while the service control
        entity is operational."
    INDEX { entPhysicalIndex, cscaTypeIndex }
    ::= { cscaTypeTable 1 }

CscaTypeEntry ::= SEQUENCE {
    cscaTypeIndex CscaAttackType,
    cscaTypeCurrentNumAttacks Gauge,
    cscaTypeTotalNumAttacks Counter,
    cscaTypeTotalNumFlows Counter,
    cscaTypeTotalNumSeconds Counter,
    cscaTypeOriginatedByNetworkSide TruthValue,
    cscaTypeProtocol INTEGER,
    cscaTypeIsPortSpecific TruthValue,
    cscaTypeIPsDetected INTEGER
    }

cscaTypeIndex OBJECT-TYPE
    SYNTAX CscaAttackType (1..64)
--    Rsyntax INTEGER(1..64)
    ACCESS not-accessible
    STATUS mandatory
    DESCRIPTION
        "This object uniquely identifies the attack type."
    ::= { cscaTypeEntry 1 }

cscaTypeCurrentNumAttacks OBJECT-TYPE
    SYNTAX Gauge
--  Units
--    attacks
    ACCESS read-only
    STATUS mandatory
    DESCRIPTION
        "This object indicates the current number of ongoing attacks of
        this type, that the service control entity has detected in the
        network."
    ::= { cscaTypeEntry 2 }

cscaTypeTotalNumAttacks OBJECT-TYPE
    SYNTAX Counter
--  Units
--    attacks
    ACCESS read-only
    STATUS mandatory
    DESCRIPTION
        "This object indicates the total number of attacks of this type
        since the last discontinuity."
    ::= { cscaTypeEntry 3 }

cscaTypeTotalNumFlows OBJECT-TYPE
    SYNTAX --?? syntax is not convertable to SMIv1
           Counter
--  Units
--    IP flows
    ACCESS read-only
    STATUS mandatory
    DESCRIPTION
        "This object indicates the total number of IP flows on which
        this type of attack has been detected, since the last
        discontinuity."
    ::= { cscaTypeEntry 4 }

cscaTypeTotalNumSeconds OBJECT-TYPE
    SYNTAX Counter
--  Units
--    seconds
    ACCESS read-only
    STATUS mandatory
    DESCRIPTION
        "This object indicates the accumulated duration in seconds
        belonging to this attack type, since the last discontinuity."
    ::= { cscaTypeEntry 5 }

cscaTypeOriginatedByNetworkSide OBJECT-TYPE
    SYNTAX TruthValue
--    Rsyntax INTEGER {
--        true(1),
--        false(2)
--        }
    ACCESS read-only
    STATUS mandatory
    DESCRIPTION
        "This object indicates whether this attack type is originated
        from the Network side or from the Subscriber side."
    ::= { cscaTypeEntry 6 }

cscaTypeProtocol OBJECT-TYPE
    SYNTAX INTEGER
    ACCESS read-only
    STATUS mandatory
    DESCRIPTION
        "This enumerated object indicates the protocol type for this
        type of attack (TCP/UDP/ICMP/etc).  The values for this object
        are:
        
        (1) TCP
        (2) UDP
        (3) ICMP
        (4) Other"
    ::= { cscaTypeEntry 7 }

cscaTypeIsPortSpecific OBJECT-TYPE
    SYNTAX TruthValue
--    Rsyntax INTEGER {
--        true(1),
--        false(2)
--        }
    ACCESS read-only
    STATUS mandatory
    DESCRIPTION
        "This object indicates whether the attack type is port-specific
        or not."
    ::= { cscaTypeEntry 8 }

cscaTypeIPsDetected OBJECT-TYPE
    SYNTAX INTEGER
    ACCESS read-only
    STATUS mandatory
    DESCRIPTION
        "This object indicates which IPs are detected in this type of
        attack. The enumerated values are:
        (1) Originating Side IP is detected.
        (2) Attacked Side IP is detected.
        (3) Both side IPs are detected."
    ::= { cscaTypeEntry 9 }

cscaInfoTable OBJECT-TYPE
    SYNTAX SEQUENCE OF CscaInfoEntry
    ACCESS not-accessible
    STATUS mandatory
    DESCRIPTION
        "This table lists information for attack mitigation, also
        referred to as attack filtering, done by a service control
        entity in the monitored network."
    ::= { ciscoServiceControlAttackMIBObjects 3 }

cscaInfoEntry OBJECT-TYPE
    SYNTAX CscaInfoEntry
    ACCESS not-accessible
    STATUS mandatory
    DESCRIPTION
        "This entry contains information about attack mitigation done by
        a physical service control entity, for attacks which it has
        detected."
    INDEX { entPhysicalIndex }
    ::= { cscaInfoTable 1 }

CscaInfoEntry ::= SEQUENCE {
    cscaInfoUpStreamAttackFilteringTime Counter,
    cscaInfoUpStreamLastAttackFilteringTime TimeInterval,
    cscaInfoDownStreamAttackFilteringTime Counter,
    cscaInfoDownStreamLastAttackFilteringTime TimeInterval
    }

cscaInfoUpStreamAttackFilteringTime OBJECT-TYPE
    SYNTAX Counter
--  Units
--    seconds
    ACCESS read-only
    STATUS mandatory
    DESCRIPTION
        "This object indicates the cumulative time during which attacks
        in the up-stream direction were filtered."
    ::= { cscaInfoEntry 1 }

cscaInfoUpStreamLastAttackFilteringTime OBJECT-TYPE
    SYNTAX TimeInterval
--    Rsyntax INTEGER(0..2147483647)
    ACCESS read-only
    STATUS mandatory
    DESCRIPTION
        "This object indicates the time since the previous attack in the
        upstream direction has ended.  Attack end is reached when the
        service control entity attack detector identifies that the
        attack characteristics (like high flow rate) no longer exist,
        and the attack is suppressed in the up-stream traffic."
    ::= { cscaInfoEntry 2 }

cscaInfoDownStreamAttackFilteringTime OBJECT-TYPE
    SYNTAX Counter
--  Units
--    seconds
    ACCESS read-only
    STATUS mandatory
    DESCRIPTION
        "This object indicates the cumulative time during which attacks
        in the down-stream direction were filtered."
    ::= { cscaInfoEntry 3 }

cscaInfoDownStreamLastAttackFilteringTime OBJECT-TYPE
    SYNTAX TimeInterval
--    Rsyntax INTEGER(0..2147483647)
    ACCESS read-only
    STATUS mandatory
    DESCRIPTION
        "This object indicates the time since the previous attack in the
        downstream direction has ended.  Attack end is reached when the
        service control entity attack detector identifies that the
        attack characteristics (like high flow rate) no longer exist,
        and the attack is suppressed in the down-stream traffic."
    ::= { cscaInfoEntry 4 }

cscaType OBJECT-TYPE
    SYNTAX CscaAttackType
--    Rsyntax INTEGER
    ACCESS not-accessible
    STATUS mandatory
    DESCRIPTION
        "This object indicates the type of an attack detected and
        reported by the service control entity.
        
        There are numerous attack types, based on the service control
        entity's definition.  The service control entity monitors and
        mitigates a predefined set of attack type.  The value of this
        object should be used as index to table cscaTypeTable in order
        to query for information regarding this attack type, such as
        its
        name and other statistics."
    ::= { cscaFilterMIBObjects 1 }

cscaSourceAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS not-accessible
    STATUS mandatory
    DESCRIPTION
        "This object indicates the address type for cscaSourceAddress."
    ::= { cscaFilterMIBObjects 2 }

cscaSourceAddress OBJECT-TYPE
    SYNTAX InetAddress
--    Rsyntax OCTET STRING(SIZE(0..255))
    ACCESS not-accessible
    STATUS mandatory
    DESCRIPTION
        "This object indicates the network address that is the source
        end point of this attack."
    ::= { cscaFilterMIBObjects 3 }

cscaDestinationAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS not-accessible
    STATUS mandatory
    DESCRIPTION
        "This object indicates the address type for
        cscaDestinationAddress."
    ::= { cscaFilterMIBObjects 4 }

cscaDestinationAddress OBJECT-TYPE
    SYNTAX InetAddress
--    Rsyntax OCTET STRING(SIZE(0..255))
    ACCESS not-accessible
    STATUS mandatory
    DESCRIPTION
        "This object indicates the network address that is the
        destination end point of this attack."
    ::= { cscaFilterMIBObjects 5 }

cscaAttackedPort OBJECT-TYPE
    SYNTAX InetPortNumber
--    Rsyntax Gauge(0..65535)
    ACCESS not-accessible
    STATUS mandatory
    DESCRIPTION
        "This object indicates the port on which this attack occurs, if
        relevant for this type of attack."
    ::= { cscaFilterMIBObjects 6 }

cscaFilterStatus OBJECT-TYPE
    SYNTAX INTEGER {
        activated(1),
        deactivated(2)
        }
    ACCESS not-accessible
    STATUS mandatory
    DESCRIPTION
        "This object indicates the status of the filter for this attack.
        The values for this object are '1' (activated) and '2'
        (de-activated)."
    ::= { cscaFilterMIBObjects 7 }

cscaNotifsEnabled OBJECT-TYPE
    SYNTAX TruthValue
--    Rsyntax INTEGER {
--        true(1),
--        false(2)
--        }
    ACCESS read-write
    STATUS mandatory
    DESCRIPTION
        "This object specifies whether the system generates the
        cscaFilterChange notification."
    ::= { cscaFilterMIBObjects 8 }

cscaLastDiscontinuityTimeStamp OBJECT-TYPE
    SYNTAX TimeStamp
--    Rsyntax TimeTicks
    ACCESS read-only
    STATUS mandatory
    DESCRIPTION
        "This object indicates the value of sysUpTime when the last
        discontinuity occurred."
    ::= { cscaFilterMIBObjects 9 }

cscaGlobalAttackType OBJECT-TYPE
    SYNTAX INTEGER {
        icmpAttack(1),
        udpAttack(2),
        udpFragmentAttack(3),
        tcpSynAttack(4),
        tcpRstAttack(5),
        tcpFragmentAttack(6),
        tcpNonSynAttack(7)
        }
    ACCESS read-only
    STATUS mandatory
    DESCRIPTION
        "This object indicates the type of a global attack detected and
        reported by the service control entity.
        
        The list of the various global attack are:
          ICMP attack(1)
          UDP attack(2)
          UDP fragment attack(3)
          TCP SYN Attack(4)
          TCP RST Attack(5)
          TCP fragment Attack(6)
          TCP NON-SYN Attack(7)"
    ::= { cscaFilterMIBObjects 10 }

cscaGlobalAttackNotifsEnabled OBJECT-TYPE
    SYNTAX TruthValue
--    Rsyntax INTEGER {
--        true(1),
--        false(2)
--        }
    ACCESS read-write
    STATUS mandatory
    DESCRIPTION
        "This object specifies whether the system generates the
        cscaGlobalAttackFilterChange notification.
        
        Setting this object value to 'true' will enable generation of
        cscaGlobalAttackFilterChange notification.
        
        Setting this object value to 'false' will disable generation of
        cscaGlobalAttackFilterChange notification."
    ::= { cscaFilterMIBObjects 11 }

cscaFilterChange TRAP-TYPE
-- Reverse mappable trap
    ENTERPRISE ciscoServiceControlAttackMIB
    VARIABLES {
        entPhysicalName, cscaType, cscaSourceAddressType, 
        cscaSourceAddress, cscaDestinationAddressType, 
        cscaDestinationAddress, cscaAttackedPort, cscaFilterStatus }
--  Status
--    mandatory
    DESCRIPTION
        "The system generates this notification to indicate that the
        cscaFilterStatus of the attack filter for cscaType has changed
        due to the reason determined by cscaDescription.  The system
        limits the generation of this notifications for the same
        cscaType to a five-second interval."
    ::= 1

cscaGlobalAttackFilterChange TRAP-TYPE
-- Reverse mappable trap
    ENTERPRISE ciscoServiceControlAttackMIB
    VARIABLES {
        entPhysicalName, cscaGlobalAttackType, cscaFilterStatus, 
        cscaTypeOriginatedByNetworkSide }
--  Status
--    mandatory
    DESCRIPTION
        "The notification is generated when a start or end of a global
        attack is detected in the system. 
        
        Below fields are sent with the trap:
        entPhysicalName indicates the name of the 
        originating physical entity.
        cscaGlobalAttackType indicates the type of the global
        attack.
        cscaFilterStatus indicates whether the global attack is
        started or ended ie. the attack filter status is activated or
        deactivated.
        cscaTypeOriginatedByNetworkSide indicates the origin/source
        of the attack, whether it originated from network or subscriber
        side."
    ::= 2

cscaMIBAttackTypeObjectGroup OBJECT IDENTIFIER ::= { cscaMIBGroups 1 }
-- OBJECT-GROUP
--  Status
--    mandatory
--  Descr
--    A collection of objects which provides attack information.
--  objects
--    cscaTypeCurrentNumAttacks, cscaTypeTotalNumAttacks, 
--    cscaTypeTotalNumFlows, cscaTypeTotalNumSeconds, 
--    cscaTypeOriginatedByNetworkSide, cscaTypeProtocol, 
--    cscaTypeIsPortSpecific, cscaTypeIPsDetected

cscaMIBAttackInfoObjectGroup OBJECT IDENTIFIER ::= { cscaMIBGroups 2 }
-- OBJECT-GROUP
--  Status
--    mandatory
--  Descr
--    A collection of objects which provides attack filtering times
--    for upstream and down stream attacks.
--  objects
--    cscaInfoUpStreamAttackFilteringTime, 
--    cscaInfoUpStreamLastAttackFilteringTime, 
--    cscaInfoDownStreamAttackFilteringTime, 
--    cscaInfoDownStreamLastAttackFilteringTime

cscaFilterObjectGroup OBJECT IDENTIFIER ::= { cscaMIBGroups 4 }
-- OBJECT-GROUP
--  Status
--    deprecated
--  Descr
--    A collection of objects which define each attack filter and
--    its status.
--    cscaFilterObjectGroup object is superseded by
--    cscaFilterObjectGroupRev1.
--  objects
--    cscaType, cscaSourceAddressType, cscaSourceAddress, 
--    cscaDestinationAddressType, cscaDestinationAddress, 
--    cscaAttackedPort, cscaFilterStatus, 
--    cscaLastDiscontinuityTimeStamp

cscaMIBNotifControlGroup OBJECT IDENTIFIER ::= { cscaMIBGroups 5 }
-- OBJECT-GROUP
--  Status
--    deprecated
--  Descr
--    A collection of object(s) to control the enable/disable
--    state of notification generation.
--    cscaMIBNotifControlGroup object is superseded by
--    cscaMIBNotifControlGroupRev1.
--  objects
--    cscaNotifsEnabled

cscaFilterObjectGroupRev1 OBJECT IDENTIFIER ::= { cscaMIBGroups 7 }
-- OBJECT-GROUP
--  Status
--    mandatory
--  Descr
--    A collection of objects which define each attack filter and
--    its status.
--  objects
--    cscaType, cscaSourceAddressType, cscaSourceAddress, 
--    cscaDestinationAddressType, cscaDestinationAddress, 
--    cscaAttackedPort, cscaFilterStatus, 
--    cscaLastDiscontinuityTimeStamp, cscaGlobalAttackType

cscaMIBNotifControlGroupRev1 OBJECT IDENTIFIER ::= { cscaMIBGroups 8 }
-- OBJECT-GROUP
--  Status
--    mandatory
--  Descr
--    A collection of object(s) to control the enable/disable
--    state of notification generation.
--  objects
--    cscaNotifsEnabled, cscaGlobalAttackNotifsEnabled

cscaMIBNotificationGroup OBJECT IDENTIFIER ::= { cscaMIBGroups 3 }
-- NOTIFICATION-GROUP
--  Status
--    deprecated
--  Descr
--    A collection of notification which provides status change
--    information for attack filters.
--    cscaMIBNotificationGroup object is superseded by
--    cscaMIBNotificationGroupRev1.
--  notifications
--    cscaFilterChange

cscaMIBNotificationGroupRev1 OBJECT IDENTIFIER ::= { cscaMIBGroups 6 }
-- NOTIFICATION-GROUP
--  Status
--    mandatory
--  Descr
--    A collection of notification which provides status change
--    information for both specific IP and global attack filters.
--  notifications
--    cscaFilterChange, cscaGlobalAttackFilterChange

cscaMIBCompliance OBJECT IDENTIFIER ::= { cscaMIBCompliances 1 }
-- MODULE-COMPLIANCE
--  Status
--    deprecated
--  Descr
--    The compliance statement for SNMP Agents which implement this
--    MIB.
--  Module
--    >>current<<
--   MandGroup
--    cscaMIBAttackTypeObjectGroup
--   MandGroup
--    cscaMIBNotificationGroup
--   MandGroup
--    cscaMIBAttackInfoObjectGroup
--   MandGroup
--    cscaFilterObjectGroup
--   MandGroup
--    cscaMIBNotifControlGroup

cscaMIBComplianceRev1 OBJECT IDENTIFIER ::= { cscaMIBCompliances 2 }
-- MODULE-COMPLIANCE
--  Status
--    mandatory
--  Descr
--    The compliance statement for SNMP Agents which implement this
--    generic filter (both Specific IP and global attack) MIB.
--  Module
--    >>current<<
--   MandGroup
--    cscaMIBAttackTypeObjectGroup
--   MandGroup
--    cscaMIBNotificationGroupRev1
--   MandGroup
--    cscaMIBAttackInfoObjectGroup
--   MandGroup
--    cscaFilterObjectGroupRev1
--   MandGroup
--    cscaMIBNotifControlGroupRev1


END
