-- MIB created 6/25/99 12:56:45, by
--   SMIC (the next generation) version 1.6.29, November 22, 1994.

CISCO-ATM-ACCESS-LIST-MIB DEFINITIONS ::= BEGIN

-- From file: "CISCO-ATM-ACCESS-LIST-MIB.my"

IMPORTS
    OBJECT-TYPE
            FROM RFC-1212
    DisplayString, RowStatus
            FROM SNMPv2-TC-v1
    ifIndex
            FROM IF-MIB
    ciscoMgmt
            FROM CISCO-SMI;

ciscoAtmAccessListMIB OBJECT IDENTIFIER ::= { ciscoMgmt 67 }
-- MODULE-IDENTITY
--  LastUpdated
--    9611100000Z
--  OrgName
--    Cisco Systems, Inc.
--  ContactInfo
--           Cisco Systems
--     Customer Service
--    
--    Postal: 170 W Tasman Drive
--     San Jose, CA  95134
--     USA
--    
--       Tel: +1 800 553-NETS
--    
--    E-mail: cs-atm@cisco.com
--  Descr
--    A cisco ATM access list mib module.
--  RevDate
--    9611180000Z
--  RevDescr
--    Initial Version of this MIB module.

ciscoAtmAccessListMIBObjects OBJECT IDENTIFIER ::= { ciscoAtmAccessListMIB 1 }
ciscoAtmAddressTemplate OBJECT IDENTIFIER ::= { ciscoAtmAccessListMIBObjects 1 }
ciscoAtmAddressFilter OBJECT IDENTIFIER ::= { ciscoAtmAccessListMIBObjects 2 }
ciscoAtmAccessGroup OBJECT IDENTIFIER ::= { ciscoAtmAccessListMIBObjects 3 }
ciscoAtmAccessListMIBConformance OBJECT IDENTIFIER ::= { ciscoAtmAccessListMIB 3 }
ciscoAtmAccessListMIBCompliances OBJECT IDENTIFIER ::= { ciscoAtmAccessListMIBConformance 1 }
ciscoAtmAccessListMIBGroups OBJECT IDENTIFIER ::= { ciscoAtmAccessListMIBConformance 2 }

CiscoAtmAddressTemplate ::= DisplayString(SIZE(1..70))
-- Rsyntax OCTET STRING(SIZE(1..70))
-- TEXTUAL-CONVENTION
--  Status
--    mandatory
--  Descr
--    A NSAP address or address template string. If it only contains
--     hexadecimal digits, 20-octet long, it represents a single 
--     NSAP address.
--     For example,
--     47.0091.8100.0000.0060.3e5b.7201.4000.0c    is an NSAP address
--     with no wild cards.
--    
--     If it contains one or more wild-card characters, it then 
--     represents multiple NSAP addresses as follows. An 
--     ellipsis ... matches any number of leading or trailing
--     hexadecimal digits.  
--     For example,
--     12.8344... will match any address that starts with 12.8344 and
--     ...0201.01 will match any address that ends with 0201.01.
--    
--     An asterisk * can be used to match any single 4-bit nibble 
--     in an address string.  
--     For example, in
--     47.8*9*1200000000603E5B7201.00603E5B7201.00 the 2nd nibble of
--     the 2nd most significant byte and 2nd nibble of 3rd most 
--     significant byte will match any 4bit nibble value. 
--     
--     An asterisk (*) enclosed by a pair of parentheses, can also 
--     be used to match any binary bit (0 or 1) in a 4-bit nibble.
--     For example, in
--     ...92(1*0*)8.01  the asterisk within parentheses will match
--     either binary values 0 and 1.

ciscoAtmAddressTemplateTable OBJECT-TYPE
    SYNTAX SEQUENCE OF CiscoAtmAddressTemplateEntry
    ACCESS not-accessible
    STATUS mandatory
    DESCRIPTION
        "The ATM address template alias Table.  Entries in this table can be
         created and deleted by setting the atmAddressTemplateRowStatus object
         to appropriate values.  Existing rows can be modified when the row is
         active.  Entries in this table can be created/modified/ deleted through 
         the commands provided by CLI also."
    ::= { ciscoAtmAddressTemplate 1 }

ciscoAtmAddressTemplateEntry OBJECT-TYPE
    SYNTAX CiscoAtmAddressTemplateEntry
    ACCESS not-accessible
    STATUS mandatory
    DESCRIPTION
        " An entry in the address template table."
    INDEX { atmAddressAliasName }
    ::= { ciscoAtmAddressTemplateTable 1 }

CiscoAtmAddressTemplateEntry ::= SEQUENCE {
    atmAddressAliasName DisplayString,
    atmAddressTemplate CiscoAtmAddressTemplate,
    atmAddressTemplateRowStatus RowStatus
    }

atmAddressAliasName OBJECT-TYPE
    SYNTAX DisplayString(SIZE(1..30))
--    Rsyntax OCTET STRING(SIZE(1..30))
    ACCESS not-accessible
    STATUS mandatory
    DESCRIPTION
        "The alias name for an ATM address template."
    ::= { ciscoAtmAddressTemplateEntry 1 }

atmAddressTemplate OBJECT-TYPE
    SYNTAX CiscoAtmAddressTemplate
--    Rsyntax OCTET STRING(SIZE(1..70))
    ACCESS read-write
    STATUS mandatory
    DESCRIPTION
        "The Address Template to be aliased."
    ::= { ciscoAtmAddressTemplateEntry 2 }

atmAddressTemplateRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "To create, delete, read and write a row. Entries in this table can be
         modified on the fly.  For example, value of atmAddressTemplateObject 
         can be changed even when the corresponding atmAddressTemplateRowStatus 
         object indicates that the row is active."
    ::= { ciscoAtmAddressTemplateEntry 3 }

ciscoAtmAddressFilterSetTable OBJECT-TYPE
    SYNTAX SEQUENCE OF CiscoAtmAddressFilterSetEntry
    ACCESS not-accessible
    STATUS mandatory
    DESCRIPTION
        "The ATM address filter set Table.  Entries in this table can be 
         created/deleted by setting the atmAddressFilterSetRowStatus object
         to appropriate values.  Existing entries in this table can be modified
         on the fly.  Entries in this table can be created/modified/deleted
         through the commands provided by the CLI also."
    ::= { ciscoAtmAddressFilter 1 }

ciscoAtmAddressFilterSetEntry OBJECT-TYPE
    SYNTAX CiscoAtmAddressFilterSetEntry
    ACCESS not-accessible
    STATUS mandatory
    DESCRIPTION
        " An entry in the address filter set table."
    INDEX { atmAddressFilterSetName, atmAddressFilterSetIndex }
    ::= { ciscoAtmAddressFilterSetTable 1 }

CiscoAtmAddressFilterSetEntry ::= SEQUENCE {
    atmAddressFilterSetName DisplayString,
    atmAddressFilterSetIndex INTEGER,
    atmAddressFilterSetType INTEGER,
    atmAddressFilterSetTemplate DisplayString,
    atmAddressFilterSetStartHour INTEGER,
    atmAddressFilterSetStartMinute INTEGER,
    atmAddressFilterSetEndHour INTEGER,
    atmAddressFilterSetEndMinute INTEGER,
    atmAddressFilterSetPermission INTEGER,
    atmAddressFilterSetRowStatus RowStatus
    }

atmAddressFilterSetName OBJECT-TYPE
    SYNTAX DisplayString(SIZE(1..30))
--    Rsyntax OCTET STRING(SIZE(1..30))
    ACCESS not-accessible
    STATUS mandatory
    DESCRIPTION
        "The name for an ATM address filter set."
    ::= { ciscoAtmAddressFilterSetEntry 1 }

atmAddressFilterSetIndex OBJECT-TYPE
    SYNTAX INTEGER(1..65535)
    ACCESS not-accessible
    STATUS mandatory
    DESCRIPTION
        "The Index for a Filter in an ATM address filter set. The filters are 
        matched in the ascending order of atmAddressFilterSetIndex.  A filter
        with a lower atmAddressFilterSetIndex value is matched prior to a 
        filter with a higher atmAddressFilterSetIndex value.  The only 
        exception to this rule are those address filters that specify all 
        20-bytes without using wildcards.  These filters are matched before 
         any other wildcard filter in a filter-set irrespective of the 
         atmAddressFilterSetIndex value."
    ::= { ciscoAtmAddressFilterSetEntry 2 }

atmAddressFilterSetType OBJECT-TYPE
    SYNTAX INTEGER {
        addressFilter(1),
        timeOfDayFilter(2)
        }
    ACCESS read-write
    STATUS mandatory
    DESCRIPTION
        "Indicates the type of a filter whether atm Address filter or a 
         Time-of-day filter. If the value of this object is addressFilter(1) 
         then the objects atmAddressFilterSetStartHour,
         atmAddressFilterSetStartMinute, atmAddressFilterSetEndHour and 
         atmAddressFilterSetEndMinute shall contain only the default values and 
         cannot be set to any other value. If the value of this object is 
         timeOfDayFilter(2) then the object atmAddressFilterSetTemplate shall 
         contain only the default value and cannot be set to any other value.  
         If the value of this object is modified to timeOfDayFilter(2),
         for an existing addressFilter row, the corresponding 
         atmAddressFilterSetTemplate object will be set to its default value 
         automatically.  If the value of this object is modified to 
         addressFilter(1) for an existing timeOfDayFilter row, the corresponding 
         objects atmAddressFilterSetStartHour, atmAddressFilterSetStartMinute,
         atmAddressFilterSetEndHour and atmAddressFilterSetEndMinute
         will be set to their default values automatically."
    DEFVAL { addressFilter }
    ::= { ciscoAtmAddressFilterSetEntry 3 }

atmAddressFilterSetTemplate OBJECT-TYPE
    SYNTAX DisplayString(SIZE(1..70))
--    Rsyntax OCTET STRING(SIZE(1..70))
    ACCESS read-write
    STATUS mandatory
    DESCRIPTION
        "This is either an existing atmAddressAliasName, or an ATM address 
         template, as described in the CiscoAtmAddressTemplate.  If the value 
         of this object matches an atmAddressAliasName in the
         ciscoAtmAddressTemplateTable, then the value of the corresponding 
         atmAddressTemplate object will be used.  And subsequent attempts to 
         read this object will return the address-template instead of the alias 
         name. Only if a such a match is not found in ciscoAtmAddressTemplateTable,
         an attempt can be made to interpret this object as a 
         CiscoAtmAddressTemplate. The value of this object shall be '...' and 
         cannot be set to any other value if a filter is of the type 
         timeOfDayFilter"
    DEFVAL { "..." }
    ::= { ciscoAtmAddressFilterSetEntry 4 }

atmAddressFilterSetStartHour OBJECT-TYPE
    SYNTAX INTEGER(0..23)
    ACCESS read-write
    STATUS mandatory
    DESCRIPTION
        "Indicates the Hours portion of the Start time of a Time-of-day
         filter.  If the value of atmAddressFilterSetType object is 
         addressFilter, then this object cannot be set and shall only 
         contain the default value"
    DEFVAL { 0 }
    ::= { ciscoAtmAddressFilterSetEntry 5 }

atmAddressFilterSetStartMinute OBJECT-TYPE
    SYNTAX INTEGER(0..59)
    ACCESS read-write
    STATUS mandatory
    DESCRIPTION
        "Indicates the Minutes portion of the Start time of a Time-of-day
         filter. If the value of atmAddressFilterSetType object is 
         addressFilter, then this object cannot be set and shall only 
         contain the default value"
    DEFVAL { 0 }
    ::= { ciscoAtmAddressFilterSetEntry 6 }

atmAddressFilterSetEndHour OBJECT-TYPE
    SYNTAX INTEGER(0..23)
    ACCESS read-write
    STATUS mandatory
    DESCRIPTION
        "Indicates the Hours portion of the End time of a Time-of-day
         filter.  If the value of atmAddressFilterSetType object is 
         addressFilter, then this object cannot be set and shall only 
         contain the default value"
    DEFVAL { 0 }
    ::= { ciscoAtmAddressFilterSetEntry 7 }

atmAddressFilterSetEndMinute OBJECT-TYPE
    SYNTAX INTEGER(0..59)
    ACCESS read-write
    STATUS mandatory
    DESCRIPTION
        "Indicates the Minutes portion of the End time of a Time-of-day
         filter. If the value of atmAddressFilterSetType object is 
         addressFilter, then this object cannot be set and shall only 
         contain the default value"
    DEFVAL { 0 }
    ::= { ciscoAtmAddressFilterSetEntry 8 }

atmAddressFilterSetPermission OBJECT-TYPE
    SYNTAX INTEGER {
        permit(1),
        deny(2)
        }
    ACCESS read-write
    STATUS mandatory
    DESCRIPTION
        "Indicates the action of a filter set (either permit or deny), when
         a specific ATM address matches with the atmAddressFilterSetTemplate
         defined in this address filter set in case of an addressFilter or 
         when the current time falls in the interval specified by the  
         atmAddressFilterSetStartHour, atmAddressFiltersetStartMinute,
         atmAddressFilterSetEndHour and atmAddressFiltersetEndMinute objects
         in case of a timeOfDayFilter."
    DEFVAL { permit }
    ::= { ciscoAtmAddressFilterSetEntry 9 }

atmAddressFilterSetRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "To create, delete, read and write a row. Entries in this table can be
         modified on the fly.  For exmaple, atmAddressFilterSetTemplate object 
         of an existing addressFilter can be modified even if the value of the
         corresponding atmAddressFilterSetRowStatus object indicates that the
         row is active."
    ::= { ciscoAtmAddressFilterSetEntry 10 }

ciscoAtmAddressFilterExpressionTable OBJECT-TYPE
    SYNTAX SEQUENCE OF CiscoAtmAddressFilterExpressionEntry
    ACCESS not-accessible
    STATUS mandatory
    DESCRIPTION
        "The ATM address filter expression table. Entries in this table can be
         created/deleted by setting the atmAddressFilterExpressionRowStatus
         object to appropriate values. Existing entries in this table cannot be
         modified on the fly.  Before an existing active entry can be modified, 
         it has to be brought to notInService by setting the corresponding 
         atmAddressFilterExpressionRowStatus object to notInService.  Entries
         in this table can also be created/modified/deleted through the commands
         provided by the CLI."
    ::= { ciscoAtmAddressFilter 2 }

ciscoAtmAddressFilterExpressionEntry OBJECT-TYPE
    SYNTAX CiscoAtmAddressFilterExpressionEntry
    ACCESS not-accessible
    STATUS mandatory
    DESCRIPTION
        " An entry in the address filter expression table."
    INDEX { atmAddressFilterExpressionName }
    ::= { ciscoAtmAddressFilterExpressionTable 1 }

CiscoAtmAddressFilterExpressionEntry ::= SEQUENCE {
    atmAddressFilterExpressionName DisplayString,
    atmAddressFilterExpressionQualifier1 INTEGER,
    atmAddressFilterExpressionTerm1 DisplayString,
    atmAddressFilterExpressionQualifier2 INTEGER,
    atmAddressFilterExpressionTerm2 DisplayString,
    atmAddressFilterExpressionOperator INTEGER,
    atmAddressFilterExpressionRowStatus RowStatus
    }

atmAddressFilterExpressionName OBJECT-TYPE
    SYNTAX DisplayString(SIZE(1..30))
--    Rsyntax OCTET STRING(SIZE(1..30))
    ACCESS not-accessible
    STATUS mandatory
    DESCRIPTION
        "The name for an ATM address filter expression."
    ::= { ciscoAtmAddressFilterExpressionEntry 1 }

atmAddressFilterExpressionQualifier1 OBJECT-TYPE
    SYNTAX INTEGER {
        source(1),
        destination(2),
        none(3)
        }
    ACCESS read-write
    STATUS mandatory
    DESCRIPTION
        "This object indicates the ATM filter set specified by the 
         atmAddressFilterExpressionTerm1 should be  applied to either the
         source (calling party) or destination (called party) ATM address.
         atmAddressFilterExpressionQualifier1 shall be none(3) if 
         atmAddressFilterExpressionTerm1 is a Filter Expression or a
         timeOfDayFilter.  The value of this object can be modified for 
         an existing row only after placing that row notInService by setting
         the corresponding atmAddressFilterExpressionRowStatus object to
         notInService(2)."
    DEFVAL { destination }
    ::= { ciscoAtmAddressFilterExpressionEntry 2 }

atmAddressFilterExpressionTerm1 OBJECT-TYPE
    SYNTAX DisplayString(SIZE(1..30))
--    Rsyntax OCTET STRING(SIZE(1..30))
    ACCESS read-write
    STATUS mandatory
    DESCRIPTION
        "This object is the name of the first ATM address filter set or ATM 
         address filter expression used in the logical expression. The 
         value of this object can only be either an already existing 
         atmAddressFilterSetName whose row is already active in the 
         ciscoAtmAddressFilterSetTable or an atmAddressFilterExpressionName 
         whose row is already active in the ciscoAtmAddressFilterExpressionTable. 
         When the reference that this object is pointing to gets deleted out from 
         under it, this object may have a value that does not exist in both
         ciscoAtmAddressFilterSetTable and ciscoAtmAddressFilterExpressionTable 
         and the expression will be evaluated as if the deleted filter resulted 
         in a match with a permission of 'permit'. The value of this object can 
         be modified for an existing row only after placing that row notInService
         by setting the corresponding atmAddressFilterExpressionRowStatus object 
         to notInService."
    ::= { ciscoAtmAddressFilterExpressionEntry 3 }

atmAddressFilterExpressionQualifier2 OBJECT-TYPE
    SYNTAX INTEGER {
        source(1),
        destination(2),
        none(3)
        }
    ACCESS read-write
    STATUS mandatory
    DESCRIPTION
        "Indicates the ATM filter set or filter expression specified by the
         atmAddressFilterExpressionTerm2 should be applied to either the
         source (calling party) or destination (called party) ATM address.
         It is not used if the logical operator is NOT. 
         atmAddressFilterExpressionQualifier2 shall be none(3) if 
         atmAddressFilterExpressionTerm2 is a Filter Expression or 
         timeOfDayFilter.  The value of this object can be modified for an
         existing row only after placing the row notInService by setting
         the corresponding atmAddressFilterExpressionRowStatus object to
         notInService(2)."
    DEFVAL { destination }
    ::= { ciscoAtmAddressFilterExpressionEntry 4 }

atmAddressFilterExpressionTerm2 OBJECT-TYPE
    SYNTAX DisplayString(SIZE(0..30))
--    Rsyntax OCTET STRING(SIZE(0..30))
    ACCESS read-write
    STATUS mandatory
    DESCRIPTION
        "The name of the second ATM address filter set or ATM address filter 
         expression used in the logical expression. The value of this object 
         can only be either an existing atmAddressFilterSetName whose row is 
         already active in the ciscoAtmAddressFilterSetTable or an existing 
         atmAddressFilterExpressionName whose row is already active in the 
         ciscoAtmAddressFilterExpressionTable.  The value of this object shall 
         be null if the value of corresponding atmAddressFilterExpressionOperator
         object is not(4) or none(5).  When the reference that this object is 
         pointing to gets deleted out from under it, this object may have a value 
         that does not exist in both ciscoAtmAddressFilterExpressionTable and 
         ciscoAtmAddressFilterSetTable and the expression will be evaluated 
         as if the deleted filter resulted in a match with a permission of 
         'permit'.  The value of this object can be modified for an existing 
         row only after placing that row notInService by setting the respective 
         atmAddressFilterExpressionRowStatus object to the value notInService."
    ::= { ciscoAtmAddressFilterExpressionEntry 5 }

atmAddressFilterExpressionOperator OBJECT-TYPE
    SYNTAX INTEGER {
        and(1),
        or(2),
        xor(3),
        not(4),
        none(5)
        }
    ACCESS read-write
    STATUS mandatory
    DESCRIPTION
        "The logical operator to be applied to the associated ATM address
         filter logical expression.  The value of this object can be modified
         for an existing row only after placing that row notInService by setting 
         the corresponding atmAddressFilterExpressionRowStatus object to the 
         value notInService."
    ::= { ciscoAtmAddressFilterExpressionEntry 6 }

atmAddressFilterExpressionRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "To create, delete, read and write a row.  Existing entries in this table
         that are active cannot be modified on the fly. Before an existing entry 
         in this table that is active can be modified, the corresponding 
         atmAddressFilterExpressionRowStatus object has to be set to notInService."
    ::= { ciscoAtmAddressFilterExpressionEntry 7 }

ciscoAtmAccessGroupTable OBJECT-TYPE
    SYNTAX SEQUENCE OF CiscoAtmAccessGroupEntry
    ACCESS not-accessible
    STATUS mandatory
    DESCRIPTION
        "The ATM access group Table.  This table shall only include interfaces 
         whose ifType is atm(37) or logicalAtm(80).  Entries in this table can 
         be modified through the commands provided by the CLI also."
    ::= { ciscoAtmAccessGroup 1 }

ciscoAtmAccessGroupEntry OBJECT-TYPE
    SYNTAX CiscoAtmAccessGroupEntry
    ACCESS not-accessible
    STATUS mandatory
    DESCRIPTION
        "An entry in the ATM access group table.  This table shall only 
         include interfaces whose ifType is atm(37) or logicalAtm(80)"
    INDEX { ifIndex }
    ::= { ciscoAtmAccessGroupTable 1 }

CiscoAtmAccessGroupEntry ::= SEQUENCE {
    atmInboundAccessGroupName DisplayString,
    atmOutboundAccessGroupName DisplayString
    }

atmInboundAccessGroupName OBJECT-TYPE
    SYNTAX DisplayString(SIZE(0..30))
--    Rsyntax OCTET STRING(SIZE(0..30))
    ACCESS read-write
    STATUS mandatory
    DESCRIPTION
        "The name of an ATM address filter set or expression used for access
         control for inbound call on the associated interface."
    ::= { ciscoAtmAccessGroupEntry 1 }

atmOutboundAccessGroupName OBJECT-TYPE
    SYNTAX DisplayString(SIZE(0..30))
--    Rsyntax OCTET STRING(SIZE(0..30))
    ACCESS read-write
    STATUS mandatory
    DESCRIPTION
        "The name of an ATM address filter set or expression used for access
         control for outbound call on the associated interface."
    ::= { ciscoAtmAccessGroupEntry 2 }

ciscoAtmAccessListMIBGroup OBJECT IDENTIFIER ::= { ciscoAtmAccessListMIBGroups 1 }
-- OBJECT-GROUP
--  Status
--    mandatory
--  objects
--    atmAddressTemplate, atmAddressTemplateRowStatus, 
--    atmAddressFilterSetType, atmAddressFilterSetTemplate, 
--    atmAddressFilterSetStartHour, atmAddressFilterSetStartMinute, 
--    atmAddressFilterSetEndHour, atmAddressFilterSetEndMinute, 
--    atmAddressFilterSetPermission, atmAddressFilterSetRowStatus, 
--    atmAddressFilterExpressionQualifier1, 
--    atmAddressFilterExpressionTerm1, 
--    atmAddressFilterExpressionQualifier2, 
--    atmAddressFilterExpressionTerm2, 
--    atmAddressFilterExpressionOperator, 
--    atmAddressFilterExpressionRowStatus, 
--    atmInboundAccessGroupName, atmOutboundAccessGroupName

ciscoAtmAccessListMIBCompliance OBJECT IDENTIFIER ::= { ciscoAtmAccessListMIBCompliances 1 }
-- MODULE-COMPLIANCE
--  Status
--    mandatory
--  Descr
--    The compliance statement for the Cisco ATM access list group.
--  Module
--    >>current<<
--   MandGroup
--    ciscoAtmAccessListMIBGroup


END
