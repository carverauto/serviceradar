-- MIB file created 15-Jan-2004 18:25:18, by
--   SMICng version 2.2.11-beta(PRO)(Solaris), January 20, 2001. Enterprise key cisco.com

CISCO-WAN-ATM-COSB-MIB DEFINITIONS ::= BEGIN

-- From file: "CISCO-WAN-ATM-COSB-MIB.my"
-- Compile options "4 7 F H N W 03 06 0B 0G 0N 0T"

IMPORTS
    ifIndex
            FROM IF-MIB
    ciscoWan
            FROM CISCOWAN-SMI
    Counter
            FROM RFC1155-SMI
    OBJECT-TYPE
            FROM RFC-1212;

ciscoWanAtmCosbMIB OBJECT IDENTIFIER ::= { ciscoWan 16 }
-- MODULE-IDENTITY
--  LastUpdated
--    200303210000Z
--  OrgName
--    Cisco Systems, Inc.
--  ContactInfo
--           Cisco Systems
--            Customer Service
--    
--    Postal: 170 W Tasman Drive
--            San Jose, CA  95134
--            USA
--    
--       Tel: +1 800 553-NETS
--    
--    E-mail: cs-wanatm@cisco.com
--  Descr
--    The MIB to manage CoS(Class of Service) queue/buffer 
--     related parameters. 
--     One or more virtual interfaces may exist on a physical 
--     interface  or a channelized interface. Every virtual 
--     interface has certain number (e.g. 16) of CoS queues. 
--     These queues are also known as Class Of Service Buffers. 
--     Every COS queue maps to an ATM trafiic type such as CBR, 
--     VBR-rt, ABR etc. These COS queues are used to provide 
--     QOS (quality of service), depending on the corresponding
--     ATM trafiic  type.  This MIB provides management 
--     functionality such as Threshold Crossing Alarms(TCA) for
--     cell discards and interval statistics for these COS 
--     queues.
--  RevDate
--    200303210000Z
--  RevDescr
--    Descriptions have been clarified for few objects or 
--     tables.
--  RevDate
--    200206100000Z
--  RevDescr
--    1. Added following objects to cwacIntervalTable, 
--      as upper 32-bits for counters which are 
--      64-bit wide:
--      cwacHighIntCellArrivals, cwacHighIntCellDiscards,
--      cwacHighIntCellDeparts.
--     2. Added following 64-bit objects to 
--      cwacIntervalTable for 64-bit counter support:
--      cwacHCIntCellArrivals, cwacHCIntCellDiscards,
--      cwacHCIntCellDeparts
--  RevDate
--    200004170000Z
--  RevDescr
--    Initial version of this MIB module.

ciscoWanAtmCosbMIBObjects OBJECT IDENTIFIER ::= { ciscoWanAtmCosbMIB 1 }
cwacConfig      OBJECT IDENTIFIER ::= { ciscoWanAtmCosbMIBObjects 1 }
cwacStatistics  OBJECT IDENTIFIER ::= { ciscoWanAtmCosbMIBObjects 2 }
ciscoWanAtmCosbMIBConformance OBJECT IDENTIFIER ::= { ciscoWanAtmCosbMIB 2 }
ciscoWanAtmCosbMIBCompliances OBJECT IDENTIFIER ::= { ciscoWanAtmCosbMIBConformance 1 }
ciscoWanAtmCosbMIBGroups OBJECT IDENTIFIER ::= { ciscoWanAtmCosbMIBConformance 2 }

cwacStatsAlarmConfgTable OBJECT-TYPE
    SYNTAX SEQUENCE OF CwacStatsAlarmConfgEntry
    ACCESS not-accessible
    STATUS mandatory
    DESCRIPTION
        "This table contains alarm configuration parameters 
         related to CoS queue. Entries in this table are 
         automatically created when a new virtual interface 
         is added."
    ::= { cwacStatistics 1 }

cwacStatsAlarmConfgEntry OBJECT-TYPE
    SYNTAX CwacStatsAlarmConfgEntry
    ACCESS not-accessible
    STATUS mandatory
    DESCRIPTION
        "An entry in CoS queue alarm configuration table. 
         This table is indexed by ifIndex, that belongs to 
         the ifTable entry with ifType value atmVirtual(149), 
         and cwacCosbIndex."
    INDEX { ifIndex, cwacCosbIndex }
    ::= { cwacStatsAlarmConfgTable 1 }

CwacStatsAlarmConfgEntry ::= SEQUENCE {
    cwacCosbIndex INTEGER,
    cwacCosbCurrentCellsDiscThres INTEGER,
    cwacStatsAlarmStatus INTEGER,
    cwacValidIntervals INTEGER
    }

cwacCosbIndex OBJECT-TYPE
    SYNTAX INTEGER(1..32)
    ACCESS not-accessible
    STATUS mandatory
    DESCRIPTION
        "This is the CoS queue number to which this entry belongs."
    ::= { cwacStatsAlarmConfgEntry 1 }

cwacCosbCurrentCellsDiscThres OBJECT-TYPE
    SYNTAX INTEGER(0..2147483647)
    ACCESS read-write
    STATUS mandatory
    DESCRIPTION
        "This object indicates the threshold for cell discards
         for the current 15-min interval, above which alarm is 
         generated."
    ::= { cwacStatsAlarmConfgEntry 2 }

cwacStatsAlarmStatus OBJECT-TYPE
    SYNTAX INTEGER(0..2147483647)
    ACCESS read-only
    STATUS mandatory
    DESCRIPTION
        "This is a bitmap that shows the status of TCA(Threshold 
         Crossing Alarm) of current queue. This bitmap is sent as
         part of the trap that is generated as part of TCA being 
         raised.
        
         Bit assignmed is as follows:
         ----------------------------
             1       Cell discard 15 minute threshold was exceeded.
         "
    ::= { cwacStatsAlarmConfgEntry 3 }

cwacValidIntervals OBJECT-TYPE
    SYNTAX INTEGER(0..96)
    ACCESS read-only
    STATUS mandatory
    DESCRIPTION
        "The number of previous intervals for which valid
         data has been stored."
    ::= { cwacStatsAlarmConfgEntry 4 }

cwacIntervalTable OBJECT-TYPE
    SYNTAX SEQUENCE OF CwacIntervalEntry
    ACCESS not-accessible
    STATUS mandatory
    DESCRIPTION
        "This table reflects interval statistics associated with
         each of the CoS queues. Entries in this table are 
         automatically created when a new virtual interface 
         is added."
    ::= { cwacStatistics 2 }

cwacIntervalEntry OBJECT-TYPE
    SYNTAX CwacIntervalEntry
    ACCESS not-accessible
    STATUS mandatory
    DESCRIPTION
        "An entry for per virtual interface CoS queue interval 
         statistics. In addition to the current 15-minute 
         interval bucket, the previous 24 hours worth of 
         15-minute interval buckets are collected for each 
         vitual interface. This table is indexed by ifIndex, 
         that belongs to the ifTable entry with ifType value 
         atmVirtual(149), cwacCosbIndex and 
         cwacIntervalNumber."
    INDEX { ifIndex, cwacCosbIndex, cwacIntervalNumber }
    ::= { cwacIntervalTable 1 }

CwacIntervalEntry ::= SEQUENCE {
    cwacIntervalNumber INTEGER,
    cwacIntCellArrivals Counter,
    cwacIntCellDiscards Counter,
    cwacIntCellDeparts Counter,
    cwacHighIntCellArrivals Counter,
    cwacHighIntCellDiscards Counter,
    cwacHighIntCellDeparts Counter,
    cwacHCIntCellArrivals Counter,
    cwacHCIntCellDiscards Counter,
    cwacHCIntCellDeparts Counter
    }

cwacIntervalNumber OBJECT-TYPE
    SYNTAX INTEGER(0..96)
    ACCESS not-accessible
    STATUS mandatory
    DESCRIPTION
        "A number used to uniquely identify per virtual interface CoS
         queue interval statistics. 0 is used to identify the current
         15-minute interval. 1-96 identify the previous 24 hours
         of 15-minute interval buckets."
    ::= { cwacIntervalEntry 1 }

cwacIntCellArrivals OBJECT-TYPE
    SYNTAX Counter
    ACCESS read-only
    STATUS mandatory
    DESCRIPTION
        "The number of cells arrived at the queue during 
         a particular 15 minute interval."
    ::= { cwacIntervalEntry 2 }

cwacIntCellDiscards OBJECT-TYPE
    SYNTAX Counter
    ACCESS read-only
    STATUS mandatory
    DESCRIPTION
        "The number of cells discarded due to congestion
         during a particular 15 minute interval."
    ::= { cwacIntervalEntry 3 }

cwacIntCellDeparts OBJECT-TYPE
    SYNTAX Counter
    ACCESS read-only
    STATUS mandatory
    DESCRIPTION
        "The number of cells that left the QBIN
         during a particular 15 minute interval."
    ::= { cwacIntervalEntry 4 }

cwacHighIntCellArrivals OBJECT-TYPE
    SYNTAX Counter
    ACCESS read-only
    STATUS mandatory
    DESCRIPTION
        "The upper 32-bits of the number of cells arrived 
         at the queue during a particular 15-minute interval."
    ::= { cwacIntervalEntry 5 }

cwacHighIntCellDiscards OBJECT-TYPE
    SYNTAX Counter
    ACCESS read-only
    STATUS mandatory
    DESCRIPTION
        "The upper 32-bits of the number of cells discarded 
         due to congestion during a particular 15-minute 
         interval."
    ::= { cwacIntervalEntry 6 }

cwacHighIntCellDeparts OBJECT-TYPE
    SYNTAX Counter
    ACCESS read-only
    STATUS mandatory
    DESCRIPTION
        "The upper 32-bits of the number of cells that left the QBIN
         during a particular 15-minute interval."
    ::= { cwacIntervalEntry 7 }

cwacHCIntCellArrivals OBJECT-TYPE
    SYNTAX --?? syntax is not convertable to SMIv1
           Counter
    ACCESS read-only
    STATUS mandatory
    DESCRIPTION
        "The 64 bit value of the number of cells arriving at 
         the queue during a particular 15-minute interval."
    ::= { cwacIntervalEntry 8 }

cwacHCIntCellDiscards OBJECT-TYPE
    SYNTAX --?? syntax is not convertable to SMIv1
           Counter
    ACCESS read-only
    STATUS mandatory
    DESCRIPTION
        "The 64 bit value of the number of cells discarded 
         due to congestion during a particular 15-minute 
         interval."
    ::= { cwacIntervalEntry 9 }

cwacHCIntCellDeparts OBJECT-TYPE
    SYNTAX --?? syntax is not convertable to SMIv1
           Counter
    ACCESS read-only
    STATUS mandatory
    DESCRIPTION
        "The 64 bit value of the number of cells that left the QBIN
         during a particular 15-minute interval."
    ::= { cwacIntervalEntry 10 }

ciscoWanAtmCosbAlarmMIBGroup OBJECT IDENTIFIER ::= { ciscoWanAtmCosbMIBGroups 1 }
-- OBJECT-GROUP
--  Status
--    deprecated
--  Descr
--    The statistical per virtual interface CoS queue alarm group.
--  objects
--    cwacCosbCurrentCellsDiscThres, cwacStatsAlarmStatus, 
--    cwacValidIntervals, cwacIntCellArrivals, cwacIntCellDiscards, 
--    cwacIntCellDeparts

ciscoWanAtmCosbAlarmMIBGroup1 OBJECT IDENTIFIER ::= { ciscoWanAtmCosbMIBGroups 2 }
-- OBJECT-GROUP
--  Status
--    mandatory
--  Descr
--    The statistical per virtual interface CoS queue alarm group.
--  objects
--    cwacCosbCurrentCellsDiscThres, cwacStatsAlarmStatus, 
--    cwacValidIntervals, cwacIntCellArrivals, cwacIntCellDiscards, 
--    cwacIntCellDeparts, cwacHighIntCellArrivals, 
--    cwacHighIntCellDiscards, cwacHighIntCellDeparts

ciscoHCWanAtmCosbAlarmMIBGroup OBJECT IDENTIFIER ::= { ciscoWanAtmCosbMIBGroups 3 }
-- OBJECT-GROUP
--  Status
--    mandatory
--  Descr
--    The statistical per virtual interface CoS queue alarm group.
--  objects
--    cwacHCIntCellArrivals, cwacHCIntCellDiscards, 
--    cwacHCIntCellDeparts

ciscoWanAtmCosbMIBCompliance OBJECT IDENTIFIER ::= { ciscoWanAtmCosbMIBCompliances 1 }
-- MODULE-COMPLIANCE
--  Status
--    deprecated
--  Descr
--    The Compliance statement for CoS queue configuration group.
--  Module
--    >>current<<
--   MandGroup
--    ciscoWanAtmCosbAlarmMIBGroup
--   ObjVar
--    cwacCosbCurrentCellsDiscThres

ciscoWanAtmCosbMIBCompliance1 OBJECT IDENTIFIER ::= { ciscoWanAtmCosbMIBCompliances 2 }
-- MODULE-COMPLIANCE
--  Status
--    mandatory
--  Descr
--    The Compliance statement for CoS queue configuration group.
--  Module
--    >>current<<
--   MandGroup
--    ciscoWanAtmCosbAlarmMIBGroup1
--   ObjVar
--    cwacCosbCurrentCellsDiscThres
--   OptGroup
--    ciscoHCWanAtmCosbAlarmMIBGroup


END
