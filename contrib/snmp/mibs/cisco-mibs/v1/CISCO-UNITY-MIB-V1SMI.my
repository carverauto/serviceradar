-- MIB file created 08-Jul-2009 12:00:17, by
--   SMICng version 2.2.11-beta(PRO)(Solaris), January 20, 2001. Enterprise key cisco.com

CISCO-UNITY-MIB DEFINITIONS ::= BEGIN

-- From file: "CISCO-UNITY-MIB.my"
-- Compile options "4 7 F H N O W 03 06 0B 0G 0N 0T"

IMPORTS
    DateAndTime, TruthValue
            FROM SNMPv2-TC-v1
    SnmpAdminString
            FROM SNMP-FRAMEWORK-MIB
    ciscoMgmt
            FROM CISCO-SMI
    Gauge
            FROM RFC1155-SMI
    OBJECT-TYPE
            FROM RFC-1212
    TRAP-TYPE
            FROM RFC-1215;

ciscoUnityMIB OBJECT IDENTIFIER ::= { ciscoMgmt 385 }
-- MODULE-IDENTITY
--  LastUpdated
--    200512120000Z
--  OrgName
--    Cisco Systems, Inc.
--  ContactInfo
--           Cisco Systems 
--            Customer Service 
--    
--    Postal: 170 W Tasman Drive 
--            San Jose, CA  95134 
--            USA 
--    
--       Tel: +1 800 553-NETS 
--    
--    E-mail: cs-unity@cisco.com
--  Descr
--    The MIB Module for the management of Cisco Unity server. 
--    Cisco Unity is a Unified Communications solution that provides  
--    advanced, convergence-based communication services. The MIB 
--    presents provision and statistics information. 
--    
--            ACRONYMS  
--    
--    AMIS 
--        Analog Messaging Interface Standard 
--    MWI 
--        Message Waiting Indicator 
--    TRAP 
--        Telephone Record and Playback 
--    TTS 
--        Text-To-Speech 
--    UM 
--        Unified Messaging 
--    VMI 
--        Visual Messaging Interface 
--    VPIM 
--        Voice Profile for Internet Mail
--  RevDate
--    200512120000Z
--  RevDescr
--    Added these objects: 
--        ciscoUnityLicLanguagesMax, 
--        ciscoUnityLicTTSSessionsMax, 
--        ciscoUnityLicSubscribersMax, 
--        ciscoUnityLicUMSubscribersMax, 
--        ciscoUnityLicVMISubscribersMax, 
--        ciscoUnityLicVoicePortsMax, 
--        ciscoUnityLicBridgeSessionsMax, 
--        ciscoUnityLicAMISIsLicensed, 
--        ciscoUnityLicMaxMsgRecLenIsLic, 
--        ciscoUnityLicPoolingIsEnabled, 
--        ciscoUnityLicVPIMIsLicensed, 
--        ciscoUnityLicPrimaryServerIsLic, 
--        ciscoUnityLicSecondServerIsLic, 
--        ciscoUnityLicUtilSecondServer, 
--        ciscoUnityLicUtilSubs, 
--        ciscoUnityLicUtilVMISubs, 
--        ciscoUnityPortActivity, 
--        ciscoUnityPortObjectId
--  RevDate
--    200401060000Z
--  RevDescr
--    The initial version of this MIB module.

ciscoUnityMIBNotifs OBJECT IDENTIFIER ::= { ciscoUnityMIB 0 }
ciscoUnityMIBObjects OBJECT IDENTIFIER ::= { ciscoUnityMIB 1 }
ciscoUnityMIBConform OBJECT IDENTIFIER ::= { ciscoUnityMIB 2 }
ciscoUnityGeneralInfo OBJECT IDENTIFIER ::= { ciscoUnityMIBObjects 1 }
ciscoUnityGlobalInfo OBJECT IDENTIFIER ::= { ciscoUnityMIBObjects 2 }
ciscoUnityNotificationsInfo OBJECT IDENTIFIER ::= { ciscoUnityMIBObjects 3 }
ciscoUnityMIBCompliances OBJECT IDENTIFIER ::= { ciscoUnityMIBConform 1 }
ciscoUnityMIBGroups OBJECT IDENTIFIER ::= { ciscoUnityMIBConform 2 }

CiscoUnityIndex ::= Gauge(1..2147483647)
-- TEXTUAL-CONVENTION
--  Status
--    mandatory
--  Descr
--    This textual convention is used as the Index into a table. 
--    A positive value is used to identify a unique entry in 
--    the table.

CiscoUnityServerStatus ::= INTEGER {
        stopped(1),
        starting(2),
        running(3),
        stopping(4)
        }
-- TEXTUAL-CONVENTION
--  Status
--    mandatory
--  Descr
--    This textual convention is used to indicate the current 
--    status of the local Unity server. 
--    stopped(1)          The main Cisco Unity process is stopped 
--    starting(2)         The main Cisco Unity process is starting 
--    running(3)          The main Cisco Unity process is in normal 
--                            operational mode 
--    stopping(4)         The main Cisco Unity process is shutting 
--                            down

ciscoUnityTable OBJECT-TYPE
    SYNTAX SEQUENCE OF CiscoUnityEntry
    ACCESS not-accessible
    STATUS mandatory
    DESCRIPTION
        "The table containing information about all the Unity servers 
        on the network visible to the local Unity server."
    ::= { ciscoUnityGeneralInfo 1 }

ciscoUnityEntry OBJECT-TYPE
    SYNTAX CiscoUnityEntry
    ACCESS not-accessible
    STATUS mandatory
    DESCRIPTION
        "An entry (conceptual row) in the Unity table, containing 
        the information about a Unity server."
    INDEX { ciscoUnityIndex }
    ::= { ciscoUnityTable 1 }

CiscoUnityEntry ::= SEQUENCE {
    ciscoUnityIndex CiscoUnityIndex,
    ciscoUnityName SnmpAdminString,
    ciscoUnityVersion SnmpAdminString
    }

ciscoUnityIndex OBJECT-TYPE
    SYNTAX CiscoUnityIndex
--    Rsyntax Gauge(1..2147483647)
    ACCESS not-accessible
    STATUS mandatory
    DESCRIPTION
        "An arbitrary integer, selected by the local Unity, which 
        uniquely identifies a Unity server on the network."
    ::= { ciscoUnityEntry 1 }

ciscoUnityName OBJECT-TYPE
    SYNTAX SnmpAdminString
--    Rsyntax OCTET STRING(SIZE(0..255))
    ACCESS read-only
    STATUS mandatory
    DESCRIPTION
        "The host name of the Unity server."
    ::= { ciscoUnityEntry 2 }

ciscoUnityVersion OBJECT-TYPE
    SYNTAX SnmpAdminString(SIZE(0..128))
--    Rsyntax OCTET STRING(SIZE(0..128))
    ACCESS read-only
    STATUS mandatory
    DESCRIPTION
        "The version number of the Unity server software."
    ::= { ciscoUnityEntry 3 }

ciscoUnityPortTable OBJECT-TYPE
    SYNTAX SEQUENCE OF CiscoUnityPortEntry
    ACCESS not-accessible
    STATUS mandatory
    DESCRIPTION
        "The table containing information about the configuration of 
        ports on the local Unity server."
    ::= { ciscoUnityGeneralInfo 2 }

ciscoUnityPortEntry OBJECT-TYPE
    SYNTAX CiscoUnityPortEntry
    ACCESS not-accessible
    STATUS mandatory
    DESCRIPTION
        "An entry (conceptual row) in the Port table, containing 
        the information about the port configuration on the local 
        Unity server."
    INDEX { ciscoUnityPortIndex }
    ::= { ciscoUnityPortTable 1 }

CiscoUnityPortEntry ::= SEQUENCE {
    ciscoUnityPortIndex CiscoUnityIndex,
    ciscoUnityPortNumber Gauge,
    ciscoUnityPortIntegration SnmpAdminString,
    ciscoUnityPortExtension SnmpAdminString,
    ciscoUnityPortEnabled TruthValue,
    ciscoUnityPortAnswerCalls TruthValue,
    ciscoUnityPortMessageNotif TruthValue,
    ciscoUnityPortDialoutMWI TruthValue,
    ciscoUnityPortAMISDelivery TruthValue,
    ciscoUnityPortTRAPConnection TruthValue,
    ciscoUnityPortActivity SnmpAdminString,
    ciscoUnityPortObjectId SnmpAdminString
    }

ciscoUnityPortIndex OBJECT-TYPE
    SYNTAX CiscoUnityIndex
--    Rsyntax Gauge(1..2147483647)
    ACCESS not-accessible
    STATUS mandatory
    DESCRIPTION
        "An arbitrary integer, selected by the local Unity, which 
        uniquely identifies a port on the local Unity server."
    ::= { ciscoUnityPortEntry 1 }

ciscoUnityPortNumber OBJECT-TYPE
    SYNTAX Gauge(0..255)
    ACCESS read-only
    STATUS mandatory
    DESCRIPTION
        "The Unity voice messaging port number."
    ::= { ciscoUnityPortEntry 2 }

ciscoUnityPortIntegration OBJECT-TYPE
    SYNTAX SnmpAdminString(SIZE(0..128))
--    Rsyntax OCTET STRING(SIZE(0..128))
    ACCESS read-only
    STATUS mandatory
    DESCRIPTION
        "The phone system integration to which this port belongs.   
        This could be Cisco CallManager or a traditional PBX."
    ::= { ciscoUnityPortEntry 3 }

ciscoUnityPortExtension OBJECT-TYPE
    SYNTAX SnmpAdminString(SIZE(0..128))
--    Rsyntax OCTET STRING(SIZE(0..128))
    ACCESS read-only
    STATUS mandatory
    DESCRIPTION
        "The extension for the port as assigned on the phone system."
    ::= { ciscoUnityPortEntry 4 }

ciscoUnityPortEnabled OBJECT-TYPE
    SYNTAX TruthValue
--    Rsyntax INTEGER {
--        true(1),
--        false(2)
--        }
    ACCESS read-only
    STATUS mandatory
    DESCRIPTION
        "This indicates whether this port is enabled on the local 
        Unity server."
    ::= { ciscoUnityPortEntry 5 }

ciscoUnityPortAnswerCalls OBJECT-TYPE
    SYNTAX TruthValue
--    Rsyntax INTEGER {
--        true(1),
--        false(2)
--        }
    ACCESS read-only
    STATUS mandatory
    DESCRIPTION
        "This indicates whether this port is designated to answer 
        incoming calls."
    ::= { ciscoUnityPortEntry 6 }

ciscoUnityPortMessageNotif OBJECT-TYPE
    SYNTAX TruthValue
--    Rsyntax INTEGER {
--        true(1),
--        false(2)
--        }
    ACCESS read-only
    STATUS mandatory
    DESCRIPTION
        "This indicates whether this port is designated for notifying 
        subscribers of messages."
    ::= { ciscoUnityPortEntry 7 }

ciscoUnityPortDialoutMWI OBJECT-TYPE
    SYNTAX TruthValue
--    Rsyntax INTEGER {
--        true(1),
--        false(2)
--        }
    ACCESS read-only
    STATUS mandatory
    DESCRIPTION
        "This indicates whether this port is designated for turning 
        MWIs on and off."
    ::= { ciscoUnityPortEntry 8 }

ciscoUnityPortAMISDelivery OBJECT-TYPE
    SYNTAX TruthValue
--    Rsyntax INTEGER {
--        true(1),
--        false(2)
--        }
    ACCESS read-only
    STATUS mandatory
    DESCRIPTION
        "This indicates whether this port is designated for making 
        outbound AMIS calls to deliver voice messages from Unity 
        subscribers to users on another voice messaging system."
    ::= { ciscoUnityPortEntry 9 }

ciscoUnityPortTRAPConnection OBJECT-TYPE
    SYNTAX TruthValue
--    Rsyntax INTEGER {
--        true(1),
--        false(2)
--        }
    ACCESS read-only
    STATUS mandatory
    DESCRIPTION
        "This indicates whether this port is designated for use by 
        subscribers as a Telephone Recording And Playback (TRAP) 
        device in Unity web applications and e-mail clients."
    ::= { ciscoUnityPortEntry 10 }

ciscoUnityPortActivity OBJECT-TYPE
    SYNTAX SnmpAdminString
--    Rsyntax OCTET STRING(SIZE(0..255))
    ACCESS read-only
    STATUS mandatory
    DESCRIPTION
        "The port activity of the voice mail port.  This value 
        is available to monitor port activity over time.  The specific 
        value of this object is not as useful as monitoring for the  
        changing of this value.  During normal operation this value 
        should change several times during a call.  You can use this 
        value to watch for abnormal operation that might indicate a 
        problem with this voice mail port.  For example, if you  
        monitor this value and do not detect a change in value for 
        a long time (like 60 minutes) it could be an indication of 
        a problem with that voice mail port.  There are other  
        explanations as well so more investigation on the server 
        should be conducted before taking any action with the voice 
        mail port."
    ::= { ciscoUnityPortEntry 11 }

ciscoUnityPortObjectId OBJECT-TYPE
    SYNTAX SnmpAdminString(SIZE(0..38))
--    Rsyntax OCTET STRING(SIZE(0..38))
    ACCESS read-only
    STATUS mandatory
    DESCRIPTION
        "A globally unique, system-generated identifier for a port 
        object.  The ObjectId (UUID or GUID) uniquely identifies the  
        port for the lifetime of this port.  A UUID is 128 bits long,  
        and can guarantee uniqueness across space and time."
    REFERENCE
        "RFC-4122 A Universally Unique IDentifier (UUID) URN  
        Namespace."
    ::= { ciscoUnityPortEntry 12 }

ciscoUnityServerState OBJECT-TYPE
    SYNTAX CiscoUnityServerStatus
--    Rsyntax INTEGER {
--        stopped(1),
--        starting(2),
--        running(3),
--        stopping(4)
--        }
    ACCESS read-only
    STATUS mandatory
    DESCRIPTION
        "The current state of the local Unity server."
    ::= { ciscoUnityGlobalInfo 1 }

ciscoUnityPorts OBJECT-TYPE
    SYNTAX Gauge(0..255)
    ACCESS read-only
    STATUS mandatory
    DESCRIPTION
        "The total number of ports on the local Unity server."
    ::= { ciscoUnityGlobalInfo 2 }

ciscoUnityPortsActive OBJECT-TYPE
    SYNTAX Gauge(0..255)
    ACCESS read-only
    STATUS mandatory
    DESCRIPTION
        "The total number of ports that are currently active with 
        calls."
    ::= { ciscoUnityGlobalInfo 3 }

ciscoUnityPortsInbound OBJECT-TYPE
    SYNTAX Gauge(0..255)
    ACCESS read-only
    STATUS mandatory
    DESCRIPTION
        "The total number of ports that are designated to answer 
        incoming calls."
    ::= { ciscoUnityGlobalInfo 4 }

ciscoUnityPortsInboundActive OBJECT-TYPE
    SYNTAX Gauge(0..255)
    ACCESS read-only
    STATUS mandatory
    DESCRIPTION
        "The number of inbound ports that are currently active with 
        calls."
    ::= { ciscoUnityGlobalInfo 5 }

ciscoUnityPortsOutbound OBJECT-TYPE
    SYNTAX Gauge(0..255)
    ACCESS read-only
    STATUS mandatory
    DESCRIPTION
        "The total number of ports that are designated for outbound 
        calls (includes message notification, MWI dialout and AMIS 
        delivery)."
    ::= { ciscoUnityGlobalInfo 6 }

ciscoUnityPortsOutboundActive OBJECT-TYPE
    SYNTAX Gauge(0..255)
    ACCESS read-only
    STATUS mandatory
    DESCRIPTION
        "The number of outbound ports that are currently active with 
        calls."
    ::= { ciscoUnityGlobalInfo 7 }

ciscoUnityLicLanguagesMax OBJECT-TYPE
    SYNTAX Gauge(0..255)
    ACCESS read-only
    STATUS mandatory
    DESCRIPTION
        "The number of languages that Unity may use concurrently."
    ::= { ciscoUnityGlobalInfo 8 }

ciscoUnityLicTTSSessionsMax OBJECT-TYPE
    SYNTAX Gauge(0..255)
    ACCESS read-only
    STATUS mandatory
    DESCRIPTION
        "The maximum number of ports licensed for Text-to-Speech 
        operations."
    ::= { ciscoUnityGlobalInfo 9 }

ciscoUnityLicSubscribersMax OBJECT-TYPE
    SYNTAX Gauge(0..2147483647)
    ACCESS read-only
    STATUS mandatory
    DESCRIPTION
        "The maximum number of subscribers licensed."
    ::= { ciscoUnityGlobalInfo 10 }

ciscoUnityLicUMSubscribersMax OBJECT-TYPE
    SYNTAX Gauge(0..2147483647)
    ACCESS read-only
    STATUS mandatory
    DESCRIPTION
        "The maximum number of subscribers licensed for unified  
        messaging."
    ::= { ciscoUnityGlobalInfo 11 }

ciscoUnityLicVMISubscribersMax OBJECT-TYPE
    SYNTAX Gauge(0..2147483647)
    ACCESS read-only
    STATUS mandatory
    DESCRIPTION
        "The maximum number of subscribers licensed for Visual 
        Messaging Interface (VMI)."
    ::= { ciscoUnityGlobalInfo 12 }

ciscoUnityLicVoicePortsMax OBJECT-TYPE
    SYNTAX Gauge(0..255)
    ACCESS read-only
    STATUS mandatory
    DESCRIPTION
        "The maximum number of voice ports licensed."
    ::= { ciscoUnityGlobalInfo 13 }

ciscoUnityLicBridgeSessionsMax OBJECT-TYPE
    SYNTAX Gauge(0..255)
    ACCESS read-only
    STATUS mandatory
    DESCRIPTION
        "The maximum number of sessions licensed for Unity Bridge 
        on the server."
    ::= { ciscoUnityGlobalInfo 14 }

ciscoUnityLicAMISIsLicensed OBJECT-TYPE
    SYNTAX TruthValue
--    Rsyntax INTEGER {
--        true(1),
--        false(2)
--        }
    ACCESS read-only
    STATUS mandatory
    DESCRIPTION
        "This indicates whether or not AMIS is licensed 
        for this server."
    ::= { ciscoUnityGlobalInfo 15 }

ciscoUnityLicMaxMsgRecLenIsLic OBJECT-TYPE
    SYNTAX TruthValue
--    Rsyntax INTEGER {
--        true(1),
--        false(2)
--        }
    ACCESS read-only
    STATUS mandatory
    DESCRIPTION
        "This indicates whether or not this server is 
        licensed to record voice mail messages of any length."
    ::= { ciscoUnityGlobalInfo 16 }

ciscoUnityLicPoolingIsEnabled OBJECT-TYPE
    SYNTAX TruthValue
--    Rsyntax INTEGER {
--        true(1),
--        false(2)
--        }
    ACCESS read-only
    STATUS mandatory
    DESCRIPTION
        "This indicates whether or not license pooling 
        is enabled for this server."
    ::= { ciscoUnityGlobalInfo 17 }

ciscoUnityLicVPIMIsLicensed OBJECT-TYPE
    SYNTAX TruthValue
--    Rsyntax INTEGER {
--        true(1),
--        false(2)
--        }
    ACCESS read-only
    STATUS mandatory
    DESCRIPTION
        "This indicates whether or not VPIM is licensed 
        for this server."
    ::= { ciscoUnityGlobalInfo 18 }

ciscoUnityLicPrimaryServerIsLic OBJECT-TYPE
    SYNTAX TruthValue
--    Rsyntax INTEGER {
--        true(1),
--        false(2)
--        }
    ACCESS read-only
    STATUS mandatory
    DESCRIPTION
        "This indicates whether or not this server 
        is licensed to run as a primary/stand-alone Unity server."
    ::= { ciscoUnityGlobalInfo 19 }

ciscoUnityLicSecondServerIsLic OBJECT-TYPE
    SYNTAX TruthValue
--    Rsyntax INTEGER {
--        true(1),
--        false(2)
--        }
    ACCESS read-only
    STATUS mandatory
    DESCRIPTION
        "This indicates whether or not a secondary 
        (failover) server is licensed."
    ::= { ciscoUnityGlobalInfo 20 }

ciscoUnityLicUtilSecondServer OBJECT-TYPE
    SYNTAX Gauge(0..1)
    ACCESS read-only
    STATUS mandatory
    DESCRIPTION
        "This indicates the current number of licensed secondary  
        servers."
    ::= { ciscoUnityGlobalInfo 21 }

ciscoUnityLicUtilSubs OBJECT-TYPE
    SYNTAX Gauge(0..2147483647)
    ACCESS read-only
    STATUS mandatory
    DESCRIPTION
        "This indicates the current number of licensed subscribers."
    ::= { ciscoUnityGlobalInfo 22 }

ciscoUnityLicUtilVMISubs OBJECT-TYPE
    SYNTAX Gauge(0..2147483647)
    ACCESS read-only
    STATUS mandatory
    DESCRIPTION
        "This indicates the current number of subscribers that are 
        licensed for VMI."
    ::= { ciscoUnityGlobalInfo 23 }

ciscoUnityEventType OBJECT-TYPE
    SYNTAX INTEGER {
        error(1),
        warning(2),
        informational(3)
        }
    ACCESS not-accessible
    STATUS mandatory
    DESCRIPTION
        "The classification on the event severity. 
        error(1)            Error events indicate significant  
                            problems that the user should know about 
        warning(2)          Warning events indicate problems that are 
                            not immediately significant, but that may 
                            indicate conditions that could cause 
                            future problems. 
        informational(3)    Information events indicate infrequent 
                            but significant successful operations."
    ::= { ciscoUnityNotificationsInfo 1 }

ciscoUnityEventSource OBJECT-TYPE
    SYNTAX SnmpAdminString
--    Rsyntax OCTET STRING(SIZE(0..255))
    ACCESS not-accessible
    STATUS mandatory
    DESCRIPTION
        "The software that logged the event, which can be either a 
        program name, a component of the system, or a component of 
        a large program."
    ::= { ciscoUnityNotificationsInfo 2 }

ciscoUnityEventCategory OBJECT-TYPE
    SYNTAX SnmpAdminString
--    Rsyntax OCTET STRING(SIZE(0..255))
    ACCESS not-accessible
    STATUS mandatory
    DESCRIPTION
        "A classification of the event by the event source."
    ::= { ciscoUnityNotificationsInfo 3 }

ciscoUnityEventId OBJECT-TYPE
    SYNTAX Gauge(0..2147483647)
    ACCESS not-accessible
    STATUS mandatory
    DESCRIPTION
        "A number identifying the particular event type.  The EventID 
        and EventSource can be used to troubleshoot system problems."
    ::= { ciscoUnityNotificationsInfo 4 }

ciscoUnityEventDate OBJECT-TYPE
    SYNTAX DateAndTime
--    Rsyntax OCTET STRING(SIZE(8|11))
    ACCESS not-accessible
    STATUS mandatory
    DESCRIPTION
        "The date and time the event occurred."
    ::= { ciscoUnityNotificationsInfo 5 }

ciscoUnityEventUser OBJECT-TYPE
    SYNTAX SnmpAdminString
--    Rsyntax OCTET STRING(SIZE(0..255))
    ACCESS not-accessible
    STATUS mandatory
    DESCRIPTION
        "The user name of the user on whose behalf the event occurred. 
        This name is the client ID if the event was actually caused by  
        a server process, or the primary ID if impersonation is not  
        taking place."
    ::= { ciscoUnityNotificationsInfo 6 }

ciscoUnityEventComputer OBJECT-TYPE
    SYNTAX SnmpAdminString
--    Rsyntax OCTET STRING(SIZE(0..255))
    ACCESS not-accessible
    STATUS mandatory
    DESCRIPTION
        "The name of the computer where the event occurred."
    ::= { ciscoUnityNotificationsInfo 7 }

ciscoUnityEventDescription OBJECT-TYPE
    SYNTAX SnmpAdminString
--    Rsyntax OCTET STRING(SIZE(0..255))
    ACCESS not-accessible
    STATUS mandatory
    DESCRIPTION
        "The event description indicates what happened or the  
        significance of the event."
    ::= { ciscoUnityNotificationsInfo 8 }

ciscoUnityEventEMSNotes OBJECT-TYPE
    SYNTAX SnmpAdminString
--    Rsyntax OCTET STRING(SIZE(0..255))
    ACCESS not-accessible
    STATUS mandatory
    DESCRIPTION
        "The contents of the notes field as entered into the EMS for 
        this monitored event."
    ::= { ciscoUnityNotificationsInfo 9 }

ciscoUnityMonitoredEvent TRAP-TYPE
-- Reverse mappable trap
    ENTERPRISE ciscoUnityMIB
    VARIABLES {
        ciscoUnityEventType, ciscoUnityEventSource, 
        ciscoUnityEventCategory, ciscoUnityEventId, 
        ciscoUnityEventDate, ciscoUnityEventUser, 
        ciscoUnityEventComputer, ciscoUnityEventDescription, 
        ciscoUnityEventEMSNotes }
--  Status
--    mandatory
    DESCRIPTION
        "This Notification contains information from the Windows Event  
        Log concerning an event that the Event Monitoring Service is 
        configured to monitor."
    ::= 1

ciscoUnityInfoGroup OBJECT IDENTIFIER ::= { ciscoUnityMIBGroups 1 }
-- OBJECT-GROUP
--  Status
--    mandatory
--  Descr
--    A collection of objects which provide info about the local 
--    Unity server.
--  objects
--    ciscoUnityName, ciscoUnityVersion, ciscoUnityServerState, 
--    ciscoUnityPorts, ciscoUnityPortsActive, 
--    ciscoUnityPortsInbound, ciscoUnityPortsInboundActive, 
--    ciscoUnityPortsOutbound, ciscoUnityPortsOutboundActive

ciscoUnityPortInfoGroup OBJECT IDENTIFIER ::= { ciscoUnityMIBGroups 2 }
-- OBJECT-GROUP
--  Status
--    mandatory
--  Descr
--    A collection of objects which provide info about the port 
--    configuration of a Unity server.
--  objects
--    ciscoUnityPortNumber, ciscoUnityPortIntegration, 
--    ciscoUnityPortExtension, ciscoUnityPortEnabled, 
--    ciscoUnityPortAnswerCalls, ciscoUnityPortMessageNotif, 
--    ciscoUnityPortDialoutMWI, ciscoUnityPortAMISDelivery, 
--    ciscoUnityPortTRAPConnection

ciscoUnityNotificationsInfoGroup OBJECT IDENTIFIER ::= { ciscoUnityMIBGroups 3 }
-- OBJECT-GROUP
--  Status
--    mandatory
--  Descr
--    A collection of objects which provide info about all the 
--    Notifications generated by the Cisco Unity Agent.
--  objects
--    ciscoUnityEventType, ciscoUnityEventSource, 
--    ciscoUnityEventCategory, ciscoUnityEventId, 
--    ciscoUnityEventDate, ciscoUnityEventUser, 
--    ciscoUnityEventComputer, ciscoUnityEventDescription, 
--    ciscoUnityEventEMSNotes

ciscoUnityLicInfoGroup OBJECT IDENTIFIER ::= { ciscoUnityMIBGroups 5 }
-- OBJECT-GROUP
--  Status
--    mandatory
--  Descr
--    A collection of objects which provide info about the local 
--    Unity server.
--  objects
--    ciscoUnityLicLanguagesMax, ciscoUnityLicTTSSessionsMax, 
--    ciscoUnityLicSubscribersMax, ciscoUnityLicUMSubscribersMax, 
--    ciscoUnityLicVMISubscribersMax, ciscoUnityLicVoicePortsMax, 
--    ciscoUnityLicBridgeSessionsMax, ciscoUnityLicAMISIsLicensed, 
--    ciscoUnityLicMaxMsgRecLenIsLic, ciscoUnityLicPoolingIsEnabled, 
--    ciscoUnityLicVPIMIsLicensed, ciscoUnityLicPrimaryServerIsLic, 
--    ciscoUnityLicSecondServerIsLic, ciscoUnityLicUtilSecondServer, 
--    ciscoUnityLicUtilSubs, ciscoUnityLicUtilVMISubs

ciscoUnityPortInfoGroup2 OBJECT IDENTIFIER ::= { ciscoUnityMIBGroups 6 }
-- OBJECT-GROUP
--  Status
--    mandatory
--  Descr
--    A collection of objects which provide info about the port 
--    configuration of a Unity Connection server.
--  objects
--    ciscoUnityPortActivity

ciscoUnityPortInfoGroup3 OBJECT IDENTIFIER ::= { ciscoUnityMIBGroups 7 }
-- OBJECT-GROUP
--  Status
--    mandatory
--  Descr
--    A collection of objects which provide info about the port 
--    configuration of a Unity Connection server. This object group 
--    is only implemented on Cisco Unity Connection.
--  objects
--    ciscoUnityPortObjectId

ciscoUnityNotificationsGroup OBJECT IDENTIFIER ::= { ciscoUnityMIBGroups 4 }
-- NOTIFICATION-GROUP
--  Status
--    mandatory
--  Descr
--    A collection of notifications that are generated by the 
--    CISCO UNITY MIB Agent.
--  notifications
--    ciscoUnityMonitoredEvent

ciscoUnityMIBCompliance OBJECT IDENTIFIER ::= { ciscoUnityMIBCompliances 1 }
-- MODULE-COMPLIANCE
--  Status
--    deprecated
--  Descr
--    The compliance statement for entities which implement 
--    the Cisco Unity MIB
--  Module
--    >>current<<
--   MandGroup
--    ciscoUnityInfoGroup
--   MandGroup
--    ciscoUnityNotificationsInfoGroup
--   MandGroup
--    ciscoUnityNotificationsGroup
--   OptGroup
--    ciscoUnityPortInfoGroup

ciscoUnityMIBComplianceRev1 OBJECT IDENTIFIER ::= { ciscoUnityMIBCompliances 2 }
-- MODULE-COMPLIANCE
--  Status
--    mandatory
--  Descr
--    The compliance statement for entities which implement 
--    the Cisco Unity MIB
--  Module
--    >>current<<
--   MandGroup
--    ciscoUnityInfoGroup
--   MandGroup
--    ciscoUnityNotificationsInfoGroup
--   MandGroup
--    ciscoUnityNotificationsGroup
--   MandGroup
--    ciscoUnityLicInfoGroup
--   OptGroup
--    ciscoUnityPortInfoGroup
--   OptGroup
--    ciscoUnityPortInfoGroup2
--   OptGroup
--    ciscoUnityPortInfoGroup3


END
