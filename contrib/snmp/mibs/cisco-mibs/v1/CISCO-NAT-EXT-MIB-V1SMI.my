-- MIB file created 20-Jun-2007 15:24:36, by
--   SMICng version 2.2.11-beta(PRO)(Solaris), January 20, 2001. Enterprise key cisco.com

CISCO-NAT-EXT-MIB DEFINITIONS ::= BEGIN

-- From file: "CISCO-NAT-EXT-MIB.my"
-- Compile options "4 7 F H N O W 03 06 0B 0G 0N 0T"

IMPORTS
    entPhysicalIndex
            FROM ENTITY-MIB
    ciscoMgmt
            FROM CISCO-SMI
    Gauge
            FROM RFC1155-SMI
    OBJECT-TYPE
            FROM RFC-1212;

ciscoNATExtMIB OBJECT IDENTIFIER ::= { ciscoMgmt 532 }
-- MODULE-IDENTITY
--  LastUpdated
--    200606050000Z
--  OrgName
--    Cisco Systems, Inc.
--  ContactInfo
--           Cisco Systems
--            Customer Service
--            
--    Postal: 170 W Tasman Drive
--            San Jose, CA  95134
--            USA
--            
--       Tel: +1 800 553-NETS
--       
--    E-mail:  cs-l4l7security@cisco.com
--  Descr
--    This MIB is an extension to the NAT-MIB.
--     This MIB module includes objects for
--     providing the NAT related statistics.
--     
--     Acronyms:
--     
--     NAT    Network Address Translation.
--  RevDate
--    200606050000Z
--  RevDescr
--    Initial version of this MIB.

ciscoNatExtMIBNotifs OBJECT IDENTIFIER ::= { ciscoNATExtMIB 0 }
ciscoNatExtMIBObjects OBJECT IDENTIFIER ::= { ciscoNATExtMIB 1 }
ciscoNatExtMIBConformance OBJECT IDENTIFIER ::= { ciscoNATExtMIB 2 }
ciscoNatExtMIBCompliances OBJECT IDENTIFIER ::= { ciscoNatExtMIBConformance 1 }
ciscoNatExtMIBGroups OBJECT IDENTIFIER ::= { ciscoNatExtMIBConformance 2 }

cneAddrTranslationStatsTable OBJECT-TYPE
    SYNTAX SEQUENCE OF CneAddrTranslationStatsEntry
    ACCESS not-accessible
    STATUS mandatory
    DESCRIPTION
        "A table of NAT statistics in a managed system."
    ::= { ciscoNatExtMIBObjects 1 }

cneAddrTranslationStatsEntry OBJECT-TYPE
    SYNTAX CneAddrTranslationStatsEntry
    ACCESS not-accessible
    STATUS mandatory
    DESCRIPTION
        "An entry in the cneAddrTranslationStatsTable.
         This contains information about the NAT related
         statistics pertaining to a module.
         The entPhysicalIndex specifies the entry in 
         entPhysicalTable with entPhysicalClass='module'."
    INDEX { entPhysicalIndex }
    ::= { cneAddrTranslationStatsTable 1 }

CneAddrTranslationStatsEntry ::= SEQUENCE {
    cneAddrTranslationNumActive Gauge,
    cneAddrTranslationNumPeak Gauge,
    cneAddrTranslation1min Gauge,
    cneAddrTranslation5min Gauge
    }

cneAddrTranslationNumActive OBJECT-TYPE
    SYNTAX Gauge
--  Units
--    Number of address translation entries
    ACCESS read-only
    STATUS mandatory
    DESCRIPTION
        "The total number of address translation entries that
         are currently available in the NAT device. This indicates
         the aggregate of the translation entries created from 
         both the static and dynamic address translation 
         mechanisms."
    REFERENCE
        "This object is an aggregate of the objects 
         natAddrBindNumberOfEntries and
         natAddrPortBindNumberOfEntries defined in the 
         RFC 4008, NAT-MIB [RFC4008].                "
    ::= { cneAddrTranslationStatsEntry 1 }

cneAddrTranslationNumPeak OBJECT-TYPE
    SYNTAX Gauge
--  Units
--    Number of address translation entries
    ACCESS read-only
    STATUS mandatory
    DESCRIPTION
        "The maximum number of address translation entries
         that are active at any one time since the system
         startup. This indicates the high watermark of
         address translation entries that are active at any
         one time since the system startup.
         
         This object includes the translation entries created
         from both the static and dynamic address translation
         mechanisms."
    ::= { cneAddrTranslationStatsEntry 2 }

cneAddrTranslation1min OBJECT-TYPE
    SYNTAX Gauge
--  Units
--    Address translation entries per second
    ACCESS read-only
    STATUS mandatory
    DESCRIPTION
        "The averaged number of address translation entries 
         which the NAT device establishing per second, averaged
         over the last 1 minute.
         
         This object includes the translation entries created
        from both the static and dynamic address translation
         mechanisms."
    ::= { cneAddrTranslationStatsEntry 3 }

cneAddrTranslation5min OBJECT-TYPE
    SYNTAX Gauge
--  Units
--    Address translation entries per second
    ACCESS read-only
    STATUS mandatory
    DESCRIPTION
        "The averaged number of address translation entries which
        the NAT device establishing per second, averaged over
         the last 5 minutes.
         
        This object includes the translation entries created
        from both the static and dynamic address translation
         mechanisms."
    ::= { cneAddrTranslationStatsEntry 4 }

ciscoNatExtAddrTransStatsGroup OBJECT IDENTIFIER ::= { ciscoNatExtMIBGroups 1 }
-- OBJECT-GROUP
--  Status
--    mandatory
--  Descr
--    This group contains the objects for NAT address translation 
--     related statistics.
--  objects
--    cneAddrTranslationNumActive, cneAddrTranslationNumPeak, 
--    cneAddrTranslation1min, cneAddrTranslation5min

ciscoNatExtMIBCompliance OBJECT IDENTIFIER ::= { ciscoNatExtMIBCompliances 1 }
-- MODULE-COMPLIANCE
--  Status
--    mandatory
--  Descr
--    The compliance statement for entities which implement the 
--     CISCO-NAT-EXT-MIB.
--  Module
--    >>current<<
--   MandGroup
--    ciscoNatExtAddrTransStatsGroup


END
