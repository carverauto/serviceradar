-- MIB file created 18-Nov-2010 15:50:14, by
--   SMICng version 2.2.11-beta(PRO)(Solaris), January 20, 2001. Enterprise key cisco.com

CISCO-CABLE-DSG-IF-MIB DEFINITIONS ::= BEGIN

-- From file: "CISCO-CABLE-DSG-IF-MIB.my"
-- Compile options "4 7 F H N W 03 06 0B 0G 0N 0T"

IMPORTS
    MacAddress, RowStatus
            FROM SNMPv2-TC-v1
    InetAddressType, InetAddress
            FROM INET-ADDRESS-MIB
    SnmpAdminString
            FROM SNMP-FRAMEWORK-MIB
    InterfaceIndex
            FROM IF-MIB
    ciscoExperiment
            FROM CISCO-SMI
    Gauge
            FROM RFC1155-SMI
    OBJECT-TYPE
            FROM RFC-1212;

ciscoCableDsgIfMIB OBJECT IDENTIFIER ::= { ciscoExperiment 999 }
-- MODULE-IDENTITY
--  LastUpdated
--    200403290000Z
--  OrgName
--    Cisco Systems, Inc.
--  ContactInfo
--               Cisco Systems 
--                     Customer Service 
--    
--    Postal: 170 West Tasman Dr  
--            San Jose, CA 95134 
--            U.S.A.  
--    Phone: +1 800 553-NETS 
--    E-mail: cs-ubr@cisco.com
--  Descr
--    This is the MIB Module for the DOCSIS Set-top Gateway 
--    (DSG). The DSG provides a one-way IP datagram transport  
--    for Out-Of-Band (OOB) messaging to cable set-top terminals. 
--    The one-way IP datagram transport is called a DSG Tunnel. 
--    A DSG Tunnel is a multicast IP datagram stream originating 
--    at the DOCSIS Set-top Gateway and carrying Out-Of-Band  
--    messages intended for set-top terminals. It is carried over 
--    one or more downstream DOCSIS channels and is identified by 
--    a well know Ethernet unicast MAC address. The well-known 
--    Ethernet unicast MAC address is reserved and published 
--    by the Conditional Access/Point Of Deployment (CA/POD) 
--    provider. A CA/POD provider is limited to eight DSG Tunnels 
--    to transport their OOB Messaging. Multiple DSG Tunnels may  
--    exist on a single downstream DOCSIS channel.  
--    This MIB is implemented as 3 groups, the CA Vendor Table,  
--    the DSG Tunnel Table and the Downstream Table. 
--     
--    1) The DSG CA Vendor Table associates a CA Vendor Name with 
--       a CA Vendor Index and the current count of tunnels  
--       carrying this CA OOB  
--    2) The DSG Tunnel Table associates an input IP Address and 
--       an output MAC Address with a CA Vendor Index. 
--    3) The DSG Downstream Table associates a tunnel Index with a 
--       DOCSIS downstream channel interface index (ifIndex). 
--    
--    These tables are all dynamic in nature. Individual rows can 
--    be created or deleted as necessary. In general, the DSG is 
--    configured once per CA system.
--  RevDate
--    200403290000Z
--  RevDescr
--    Initial revision, extracted from DOCSIS Set-top  
--    Gateway Specification.

ccdsgIfCaVendor OBJECT IDENTIFIER ::= { ciscoCableDsgIfMIB 1 }
ccdsgIfTunnel   OBJECT IDENTIFIER ::= { ciscoCableDsgIfMIB 2 }
ccdsgIfDownstream OBJECT IDENTIFIER ::= { ciscoCableDsgIfMIB 3 }
ciscoCableDsgIfConformance OBJECT IDENTIFIER ::= { ciscoCableDsgIfMIB 4 }
ciscoCableDsgIfCompliances OBJECT IDENTIFIER ::= { ciscoCableDsgIfConformance 1 }
ciscoCableDsgIfGroups OBJECT IDENTIFIER ::= { ciscoCableDsgIfConformance 2 }

ccdsgIfCaVendorTable OBJECT-TYPE
    SYNTAX SEQUENCE OF CcdsgIfCaVendorEntry
    ACCESS not-accessible
    STATUS mandatory
    DESCRIPTION
        "The DSG CA Vendor Table associates a CA Vendor Index 
        with the CA Vendor Name and the number of tunnels 
        that carry the CA Vendor's OOB Messaging."
    ::= { ccdsgIfCaVendor 1 }

ccdsgIfCaVendorEntry OBJECT-TYPE
    SYNTAX CcdsgIfCaVendorEntry
    ACCESS not-accessible
    STATUS mandatory
    DESCRIPTION
        "An entry in the CA Vendor Table. Rows are created  
        by an SNMP SET request setting the value of  
        ccdsgifCaVendorRowStatus to 'createAndGo' or  
        'createAndWait'. Rows are deleted by an SNMP SET  
        request setting the value of ccdsgifCaVendorRowStatus to  
        'destroy'. Active CA (that are associated to the tunnel) 
        cannot be detroyed till association is removed."
    INDEX { ccdsgIfCaVendorIndex }
    ::= { ccdsgIfCaVendorTable 1 }

CcdsgIfCaVendorEntry ::= SEQUENCE {
    ccdsgIfCaVendorIndex Gauge,
    ccdsgIfCaVendorName SnmpAdminString,
    ccdsgIfCaVendorTunnelCnt INTEGER,
    ccdsgIfCaVendorRowStatus RowStatus
    }

ccdsgIfCaVendorIndex OBJECT-TYPE
    SYNTAX Gauge(1..65535)
    ACCESS not-accessible
    STATUS mandatory
    DESCRIPTION
        "The row index into the CA Vendor Table"
    ::= { ccdsgIfCaVendorEntry 1 }

ccdsgIfCaVendorName OBJECT-TYPE
    SYNTAX SnmpAdminString(SIZE(1..20))
--    Rsyntax OCTET STRING(SIZE(1..20))
    ACCESS read-write
    STATUS mandatory
    DESCRIPTION
        "The name of the CA Vendor."
    ::= { ccdsgIfCaVendorEntry 2 }

ccdsgIfCaVendorTunnelCnt OBJECT-TYPE
    SYNTAX INTEGER(0..8)
    ACCESS read-only
    STATUS mandatory
    DESCRIPTION
        "The total count of Tunnel(s) configured for 
        the CA vendor.  
        The value 0 implies that no tunnel is currently  
        configured for this CA vendor."
    ::= { ccdsgIfCaVendorEntry 3 }

ccdsgIfCaVendorRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of the row.  A value of active(1)  
        indicates that DSG forwards OOB messages onto the 
        DSG Tunnel."
    ::= { ccdsgIfCaVendorEntry 4 }

ccdsgIfTunnelTable OBJECT-TYPE
    SYNTAX SEQUENCE OF CcdsgIfTunnelEntry
    ACCESS not-accessible
    STATUS mandatory
    DESCRIPTION
        "The DSG Tunnel Table associates an input IP Address and  
        an output MAC Address with a CA Vendor Index."
    ::= { ccdsgIfTunnel 1 }

ccdsgIfTunnelEntry OBJECT-TYPE
    SYNTAX CcdsgIfTunnelEntry
    ACCESS not-accessible
    STATUS mandatory
    DESCRIPTION
        "An entry in the DSG Tunnel Table. Rows are created by 
        an SNMP SET request setting the value of 
        ccdsgIfTunnelRowStatus to 'createAndGo' or 'createAndWait'. 
        Rows are deleted by an SNMP SET request setting the 
        value of ccdsgIfTunnelRowStatus to 'destroy'."
    INDEX { ccdsgIfTunnelIndex }
    ::= { ccdsgIfTunnelTable 1 }

CcdsgIfTunnelEntry ::= SEQUENCE {
    ccdsgIfTunnelIndex Gauge,
    ccdsgIfTunnelInAddressType InetAddressType,
    ccdsgIfTunnelInIpAddress InetAddress,
    ccdsgIfTunnelMacAddress MacAddress,
    ccdsgIfTunnelCaVendorIndex Gauge,
    ccdsgIfTunnelRowStatus RowStatus
    }

ccdsgIfTunnelIndex OBJECT-TYPE
    SYNTAX Gauge(1..65535)
    ACCESS not-accessible
    STATUS mandatory
    DESCRIPTION
        "The row index into the DSG Tunnel table."
    ::= { ccdsgIfTunnelEntry 1 }

ccdsgIfTunnelInAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "The type of internet address of ccdsgIfTunnelInIpAddress.  
        Cannot be changed if the value of ccdsgIfTunnelRowStatus  
        is active."
    ::= { ccdsgIfTunnelEntry 2 }

ccdsgIfTunnelInIpAddress OBJECT-TYPE
    SYNTAX InetAddress
--    Rsyntax OCTET STRING(SIZE(0..255))
    ACCESS read-write
    STATUS mandatory
    DESCRIPTION
        "The DSG Tunnel Input IP address. Cannot be changed  
        if the value of ccdsgIfTunnelRowStatus is active."
    ::= { ccdsgIfTunnelEntry 3 }

ccdsgIfTunnelMacAddress OBJECT-TYPE
    SYNTAX MacAddress
--    Rsyntax OCTET STRING(SIZE(6))
    ACCESS read-write
    STATUS mandatory
    DESCRIPTION
        "The the DSG Tunnel Output MAC address. Cannot be  
        changed if the value of ccdsgTunnelRowStatus is active."
    ::= { ccdsgIfTunnelEntry 4 }

ccdsgIfTunnelCaVendorIndex OBJECT-TYPE
    SYNTAX Gauge(0..65535)
    ACCESS read-write
    STATUS mandatory
    DESCRIPTION
        "The index in ccdsgIfCaVendorTable describing the vendor 
        information associated with this particular tunnel. 
        If no associated entry in ccdsgIfCaVendorTable exists, 
        this object should be zero."
    ::= { ccdsgIfTunnelEntry 5 }

ccdsgIfTunnelRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of the row."
    ::= { ccdsgIfTunnelEntry 6 }

ccdsgIfDownstreamTable OBJECT-TYPE
    SYNTAX SEQUENCE OF CcdsgIfDownstreamEntry
    ACCESS not-accessible
    STATUS mandatory
    DESCRIPTION
        "The DSG Downstream Table associates a Tunnel Index 
        with a DOCSIS downstream channel interface index  
        (ifIndex). It could have a same tunnel associated to 
        multiple downstream channel and vise versa."
    ::= { ccdsgIfDownstream 1 }

ccdsgIfDownstreamEntry OBJECT-TYPE
    SYNTAX CcdsgIfDownstreamEntry
    ACCESS not-accessible
    STATUS mandatory
    DESCRIPTION
        "An entry in the DSG Downstream Table. Rows are   
        created by an SNMP SET request setting the value   
        of ccdsgIfDownRowStatus to 'createAndGo' or  
        'createAndWait'. Rows are deleted by an SNMP SET  
        request setting the value of ccdsgIfDownRowStatus  
        to 'destroy'."
    INDEX { ccdsgIfDownDsgIndex }
    ::= { ccdsgIfDownstreamTable 1 }

CcdsgIfDownstreamEntry ::= SEQUENCE {
    ccdsgIfDownDsgIndex Gauge,
    ccdsgIfDownTunnelIndex Gauge,
    ccdsgIfDownIfIndex InterfaceIndex,
    ccdsgIfDownRowStatus RowStatus
    }

ccdsgIfDownDsgIndex OBJECT-TYPE
    SYNTAX Gauge(1..65535)
    ACCESS not-accessible
    STATUS mandatory
    DESCRIPTION
        "The row index into the the downstream DSG table."
    ::= { ccdsgIfDownstreamEntry 1 }

ccdsgIfDownTunnelIndex OBJECT-TYPE
    SYNTAX Gauge(1..65535)
    ACCESS read-write
    STATUS mandatory
    DESCRIPTION
        "The index in ccdsgIfTunnelTable (ccdsgIfTunnelIndex) 
        describing the Tunnel information associated with 
        particular downstream(s)."
    ::= { ccdsgIfDownstreamEntry 2 }

ccdsgIfDownIfIndex OBJECT-TYPE
    SYNTAX InterfaceIndex
--    Rsyntax INTEGER(1..2147483647)
    ACCESS read-write
    STATUS mandatory
    DESCRIPTION
        "The interface index (ifIndex) of this downstream."
    ::= { ccdsgIfDownstreamEntry 3 }

ccdsgIfDownRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of the row."
    ::= { ccdsgIfDownstreamEntry 4 }

ccdsgIfCaVendorGroup OBJECT IDENTIFIER ::= { ciscoCableDsgIfGroups 1 }
-- OBJECT-GROUP
--  Status
--    mandatory
--  Descr
--    A collection of objects providing CA Vendor 
--    configuration.
--  objects
--    ccdsgIfCaVendorName, ccdsgIfCaVendorTunnelCnt, 
--    ccdsgIfCaVendorRowStatus

ccdsgIfTunnelGroup OBJECT IDENTIFIER ::= { ciscoCableDsgIfGroups 2 }
-- OBJECT-GROUP
--  Status
--    mandatory
--  Descr
--    A collection of objects providing DSG Tunnel  
--    configuration.
--  objects
--    ccdsgIfTunnelInAddressType, ccdsgIfTunnelInIpAddress, 
--    ccdsgIfTunnelMacAddress, ccdsgIfTunnelCaVendorIndex, 
--    ccdsgIfTunnelRowStatus

ccdsgIfDownstreamGroup OBJECT IDENTIFIER ::= { ciscoCableDsgIfGroups 3 }
-- OBJECT-GROUP
--  Status
--    mandatory
--  Descr
--    A collection of objects providing DSG Downstream  
--    configuration.
--  objects
--    ccdsgIfDownTunnelIndex, ccdsgIfDownIfIndex, 
--    ccdsgIfDownRowStatus

ccdsgIfBasicCompliance OBJECT IDENTIFIER ::= { ciscoCableDsgIfCompliances 1 }
-- MODULE-COMPLIANCE
--  Status
--    mandatory
--  Descr
--    The compliance statement for DOCSIS Set-top Gateway  
--    systems.
--  Module
--    >>current<<
--   MandGroup
--    ccdsgIfCaVendorGroup
--   MandGroup
--    ccdsgIfTunnelGroup
--   MandGroup
--    ccdsgIfDownstreamGroup


END
