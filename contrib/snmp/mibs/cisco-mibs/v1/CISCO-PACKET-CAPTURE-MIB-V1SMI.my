-- MIB file created 12-Nov-2008 15:14:53, by
--   SMICng version 2.2.11-beta(PRO)(Solaris), January 20, 2001. Enterprise key cisco.com

CISCO-PACKET-CAPTURE-MIB DEFINITIONS ::= BEGIN

-- From file: "CISCO-PACKET-CAPTURE-MIB.my"
-- Compile options "4 7 F H N O W 03 06 0B 0G 0N 0T"

IMPORTS
    DateAndTime, RowStatus, MacAddress
            FROM SNMPv2-TC-v1
    InetAddress, InetAddressType, InetAddressPrefixLength
            FROM INET-ADDRESS-MIB
    SnmpAdminString
            FROM SNMP-FRAMEWORK-MIB
    ifIndex
            FROM IF-MIB
    VlanIndex
            FROM CISCO-VTP-MIB
    ciscoMgmt
            FROM CISCO-SMI
    Gauge
            FROM RFC1155-SMI
    OBJECT-TYPE
            FROM RFC-1212;

ciscoPacketCaptureMIB OBJECT IDENTIFIER ::= { ciscoMgmt 602 }
-- MODULE-IDENTITY
--  LastUpdated
--    200807070000Z
--  OrgName
--    Cisco System, Inc.
--  ContactInfo
--    Cisco Systems
--    Customer Service
--    
--    Postal: 170 W Tasman Drive
--    San Jose, CA  95134
--    USA
--    
--    Tel: +1 800 553-NETS
--    
--    E-mail: cs-lan-switch-snmp@cisco.com
--  Descr
--    The MIB module for the management of packet capture
--    feature.
--  RevDate
--    200807070000Z
--  RevDescr
--    Added cpcPacketLengthFilterConfigGroup,
--     cpcEthertypeFilterConfigGroup,
--     cpcVlanFilterConfigGroup,
--     cpcAccessGroupFilterConfigGroup,
--     cpcBufferConfigGroup,
--     cpcScheduleConfigGroup,
--     cpcSessionStatsGroup,
--     cpcMaxMacFilterConfigGroup,
--     cpcMaxIpFilterConfigGroup,
--     cpcSessionDescrGroup,
--     cpcSessionPacketRateLimitGroup.
--  RevDate
--    200701030000Z
--  RevDescr
--    Initial version of this MIB module.

cpcMIBNotification OBJECT IDENTIFIER ::= { ciscoPacketCaptureMIB 0 }
cpcMIBObjects   OBJECT IDENTIFIER ::= { ciscoPacketCaptureMIB 1 }
cpcMIBConformance OBJECT IDENTIFIER ::= { ciscoPacketCaptureMIB 2 }
cpcGenericConfig OBJECT IDENTIFIER ::= { cpcMIBObjects 1 }
cpcFilterConfig OBJECT IDENTIFIER ::= { cpcMIBObjects 2 }
cpcBufferConfig OBJECT IDENTIFIER ::= { cpcMIBObjects 3 }
cpcScheduleConfig OBJECT IDENTIFIER ::= { cpcMIBObjects 4 }
cpcSessionStats OBJECT IDENTIFIER ::= { cpcMIBObjects 5 }
cpcMIBCompliances OBJECT IDENTIFIER ::= { cpcMIBConformance 1 }
cpcMIBGroups    OBJECT IDENTIFIER ::= { cpcMIBConformance 2 }

CiscoPacketCaptureFilterCriteria ::= INTEGER {
        source(1),
        dest(2)
        }
-- TEXTUAL-CONVENTION
--  Status
--    mandatory
--  Descr
--    Filter criteria to specify if packets will be captured
--    based on source or destination addresses.
--    
--    source: packets will be captured based on source
--            address.
--    
--    dest  : packets will be captured based on destination
--            address.

cpcMaxSessionAllowed OBJECT-TYPE
    SYNTAX Gauge
    ACCESS read-only
    STATUS mandatory
    DESCRIPTION
        "The maximum number of packet capture sessions
        allowed in cpcSessionConfigTable. A value of zero
        indicates no limitation on the number of
        configurable sessions."
    ::= { cpcGenericConfig 1 }

cpcSessionConfigTable OBJECT-TYPE
    SYNTAX SEQUENCE OF CpcSessionConfigEntry
    ACCESS not-accessible
    STATUS mandatory
    DESCRIPTION
        "A table of configuration to be used in the packet
        capture sessions. This entry may be modified if value
        of corresponding instance of cpcSessionConfigStatus
        is 'active'."
    ::= { cpcGenericConfig 2 }

cpcSessionConfigEntry OBJECT-TYPE
    SYNTAX CpcSessionConfigEntry
    ACCESS not-accessible
    STATUS mandatory
    DESCRIPTION
        "An entry containing management information of a packet
        capture session."
    INDEX { cpcSessionId }
    ::= { cpcSessionConfigTable 1 }

CpcSessionConfigEntry ::= SEQUENCE {
    cpcSessionId Gauge,
    cpcSessionOperStatus INTEGER,
    cpcSessionDestFileName SnmpAdminString,
    cpcSessionPacketLength Gauge,
    cpcSessionPacketLimits Gauge,
    cpcSessionAction INTEGER,
    cpcSessionConfigStatus RowStatus,
    cpcSessionPacketRateLimit Gauge,
    cpcSessionDescr SnmpAdminString
    }

cpcSessionId OBJECT-TYPE
    SYNTAX Gauge(1..4294967295)
    ACCESS not-accessible
    STATUS mandatory
    DESCRIPTION
        "An unique number which represents a session."
    ::= { cpcSessionConfigEntry 1 }

cpcSessionOperStatus OBJECT-TYPE
    SYNTAX INTEGER {
        other(1),
        inProgress(2),
        completed(3),
        stopped(4),
        storageFull(5),
        bufferFull(6)
        }
    ACCESS read-only
    STATUS mandatory
    DESCRIPTION
        "Operational status of a packet capture session.
        
        other      : none of the following.
        inProgress : packet capture session is in progress.
        completed  : number of captured frames has reached
                     the value of corresponding instance of
                     cpcSessionPacketLimits.
        stopped    : packet capture session was administratively
                     stopped.
        storageFull: storage device is full.
        bufferFull : storage buffer is full."
    ::= { cpcSessionConfigEntry 2 }

cpcSessionDestFileName OBJECT-TYPE
    SYNTAX SnmpAdminString
--    Rsyntax OCTET STRING(SIZE(0..255))
    ACCESS read-write
    STATUS mandatory
    DESCRIPTION
        "The destination file name used to store the captured frames.
        Value of this object must be specified in the format
        of <device>:<filename> for local location, or
        <protocol>://<server>/<filename> for network location.
        
        This object may not be modified if value of the corresponding
        instance of cpcSessionOperStatus is 'inProgress' or the value
        of cpcBufferOperStatus of an instance entry with same
        cpcSessionId in cpcBufferConfigEntry is 'exporting'."
    ::= { cpcSessionConfigEntry 3 }

cpcSessionPacketLength OBJECT-TYPE
    SYNTAX Gauge
--  Units
--    octets
    ACCESS read-write
    STATUS mandatory
    DESCRIPTION
        "The length of packet to be captured by this session. If the
        length of an actual packet is greater than the value of this
        object, the session will only capture the first number of
        bytes specified by this object. A value zero for this object
        indicates that the entire packet will be captured.
        
        This object may not be modified if value of the corresponding
        instance of cpcSessionOperStatus is 'inProgress'."
    DEFVAL { 0 }
    ::= { cpcSessionConfigEntry 4 }

cpcSessionPacketLimits OBJECT-TYPE
    SYNTAX Gauge
--  Units
--    packets
    ACCESS read-write
    STATUS mandatory
    DESCRIPTION
        "The number of packets to be captured by this
        session. A value of zero for this object
        indicates that there is no limitation. When
        the value of this object is zero, the session
        remains 'inProgress' until it is administratively
        stopped or the storage is full.
        
        This object may not be modified if value of the
        corresponding instance of cpcSessionOperStatus is
        'inProgress'."
    DEFVAL { 0 }
    ::= { cpcSessionConfigEntry 5 }

cpcSessionAction OBJECT-TYPE
    SYNTAX INTEGER {
        start(1),
        stop(2)
        }
    ACCESS read-write
    STATUS mandatory
    DESCRIPTION
        "The action control for this capture session.
        Setting this object to 'start' causes the capture 
        session to be started if it is not running. 
        Setting this object to 'stop' terminates the 
        capturing session if it is running. 
        
        The value of this object will be changed to 'stop' 
        when value of the corresponding instance of 
        cpcSessionOperStatus leaves from 'inProgress' to 
        other status. 
        
        This object may only be set when the corresponding 
        instance value of cpcSessionConfigStatus is 'active'."
    DEFVAL { stop }
    ::= { cpcSessionConfigEntry 6 }

cpcSessionConfigStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this conceptual row."
    ::= { cpcSessionConfigEntry 7 }

cpcSessionPacketRateLimit OBJECT-TYPE
    SYNTAX Gauge
--  Units
--    packets per second
    ACCESS read-write
    STATUS mandatory
    DESCRIPTION
        "Rate limit for this session. Only packets within the
        rate may be captured. A value of zero for this object
        indicates that there is no rate limitation.
        
        This object may not be modified if value of the
        corresponding instance of cpcSessionOperStatus is
        'inProgress'."
    DEFVAL { 10000 }
    ::= { cpcSessionConfigEntry 8 }

cpcSessionDescr OBJECT-TYPE
    SYNTAX SnmpAdminString
--    Rsyntax OCTET STRING(SIZE(0..255))
    ACCESS read-write
    STATUS mandatory
    DESCRIPTION
        "Provides description of this session."
    DEFVAL { "" }
    ::= { cpcSessionConfigEntry 9 }

cpcSessionMaxSources OBJECT-TYPE
    SYNTAX Gauge
    ACCESS read-only
    STATUS mandatory
    DESCRIPTION
        "The maximum number of entries allowed in
        cpcCaptureSourceIfTable for a packet capture session.
        A value of zero indicates no limitation on the
        number of configurable sources."
    ::= { cpcGenericConfig 3 }

cpcCaptureSourceIfTable OBJECT-TYPE
    SYNTAX SEQUENCE OF CpcCaptureSourceIfEntry
    ACCESS not-accessible
    STATUS mandatory
    DESCRIPTION
        "A table of interface information to be used in
        the packet capture session."
    ::= { cpcGenericConfig 4 }

cpcCaptureSourceIfEntry OBJECT-TYPE
    SYNTAX CpcCaptureSourceIfEntry
    ACCESS not-accessible
    STATUS mandatory
    DESCRIPTION
        "An entry containing interface related management
        information for a packet capture session. 
        
        The entry is created and deleted by using 
        cpcCaptureSourceIfStatus object. 
        
        The entry may not be modified, added or deleted when
        the corresponding value of cpcSessionOperStatus is
        'inProgress'."
    INDEX { cpcSessionId, ifIndex }
    ::= { cpcCaptureSourceIfTable 1 }

CpcCaptureSourceIfEntry ::= SEQUENCE {
    cpcCaptureSourceIfDirection INTEGER,
    cpcCaptureSourceIfStatus RowStatus
    }

cpcCaptureSourceIfDirection OBJECT-TYPE
    SYNTAX INTEGER {
        rx(1),
        tx(2),
        both(3)
        }
    ACCESS read-write
    STATUS mandatory
    DESCRIPTION
        "The direction of traffic to be captured.
        
        rx  : Only ingress traffic will be captured.
        
        tx  : Only egress traffic will be captured.
        
        both: Traffic from both directions will be
              captured.
        
        This object may be modified if value of the
        corresponding instance of cpcCaptureSourceIfStatus
        is 'active'."
    DEFVAL { rx }
    ::= { cpcCaptureSourceIfEntry 1 }

cpcCaptureSourceIfStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this conceptual row."
    ::= { cpcCaptureSourceIfEntry 2 }

cpcMaxFilterAllowed OBJECT-TYPE
    SYNTAX Gauge
    ACCESS read-only
    STATUS mandatory
    DESCRIPTION
        "The maximum number of filters allowed in a packet
        capture session. Value of zero indicates that there
        is no limitation."
    ::= { cpcFilterConfig 1 }

cpcMacFilterTable OBJECT-TYPE
    SYNTAX SEQUENCE OF CpcMacFilterEntry
    ACCESS not-accessible
    STATUS mandatory
    DESCRIPTION
        "A table of MAC filter information to be used in
        the packet capture session."
    ::= { cpcFilterConfig 2 }

cpcMacFilterEntry OBJECT-TYPE
    SYNTAX CpcMacFilterEntry
    ACCESS not-accessible
    STATUS mandatory
    DESCRIPTION
        "An entry containing management information about
        a packet capture filter based on MAC address.
        The entry is created or deleted by using
        cpcMacFilterRowStatus object.
        
        The entry may not be modified, created or deleted
        when the corresponding value of cpcSessionOperStatus is
        'inProgress'."
    INDEX { cpcSessionId, cpcMacFilterMacAddress, cpcMacFilterCriteria }
    ::= { cpcMacFilterTable 1 }

CpcMacFilterEntry ::= SEQUENCE {
    cpcMacFilterMacAddress MacAddress,
    cpcMacFilterCriteria CiscoPacketCaptureFilterCriteria,
    cpcMacFilterRowStatus RowStatus
    }

cpcMacFilterMacAddress OBJECT-TYPE
    SYNTAX MacAddress
--    Rsyntax OCTET STRING(SIZE(6))
    ACCESS not-accessible
    STATUS mandatory
    DESCRIPTION
        "The filtered MAC address. Incorporated with the
        corresponding instance value of crcMacFilterCriteria,
        packet capture will capture packets sending from or to
        the address specified by this object."
    ::= { cpcMacFilterEntry 1 }

cpcMacFilterCriteria OBJECT-TYPE
    SYNTAX CiscoPacketCaptureFilterCriteria
--    Rsyntax INTEGER {
--        source(1),
--        dest(2)
--        }
    ACCESS not-accessible
    STATUS mandatory
    DESCRIPTION
        "The filter criteria of the entry."
    ::= { cpcMacFilterEntry 2 }

cpcMacFilterRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this conceptual row."
    ::= { cpcMacFilterEntry 3 }

cpcIpFilterTable OBJECT-TYPE
    SYNTAX SEQUENCE OF CpcIpFilterEntry
    ACCESS not-accessible
    STATUS mandatory
    DESCRIPTION
        "A table of IP filter information to be used in
        the packet capture session."
    ::= { cpcFilterConfig 3 }

cpcIpFilterEntry OBJECT-TYPE
    SYNTAX CpcIpFilterEntry
    ACCESS not-accessible
    STATUS mandatory
    DESCRIPTION
        "An entry containing management information if IP based
        packet capture filter for the packet capture session. 
        
        The entry can be created or deleted by using 
        cpcIpFilterRowStatus object. 
        
        The entry may not be modified, created or deleted when
        value of the corresponding instance of cpcSessionOperStatus
        is 'inProgress'."
    INDEX { cpcSessionId, cpcIpFilterAddressType, cpcIpFilterAddress, cpcIpFilterCriteria }
    ::= { cpcIpFilterTable 1 }

CpcIpFilterEntry ::= SEQUENCE {
    cpcIpFilterAddressType InetAddressType,
    cpcIpFilterAddress InetAddress,
    cpcIpFilterCriteria CiscoPacketCaptureFilterCriteria,
    cpcIpFilterMask InetAddressPrefixLength,
    cpcIpFilterRowStatus RowStatus
    }

cpcIpFilterAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS not-accessible
    STATUS mandatory
    DESCRIPTION
        "The type of Internet address is configured in this
        packet capture filter."
    ::= { cpcIpFilterEntry 1 }

cpcIpFilterAddress OBJECT-TYPE
    SYNTAX InetAddress(SIZE(1..64))
--    Rsyntax OCTET STRING(SIZE(1..64))
    ACCESS not-accessible
    STATUS mandatory
    DESCRIPTION
        "The Internet address for the filter. The type of
        this address is determined by the value of the
        cpcIpFilterAddressType object. The cpcIpFilterAddress
        may not be empty due to the SIZE restriction.
        
        Incorporated with the corresponding instance value
        of cpcIpFilterCriteria, packet capture will capture
        packets sending to or from the address specified by
        this object."
    ::= { cpcIpFilterEntry 2 }

cpcIpFilterCriteria OBJECT-TYPE
    SYNTAX CiscoPacketCaptureFilterCriteria
--    Rsyntax INTEGER {
--        source(1),
--        dest(2)
--        }
    ACCESS not-accessible
    STATUS mandatory
    DESCRIPTION
        "The filter criteria of the entry."
    ::= { cpcIpFilterEntry 3 }

cpcIpFilterMask OBJECT-TYPE
    SYNTAX InetAddressPrefixLength
--    Rsyntax Gauge(0..2040)
    ACCESS read-write
    STATUS mandatory
    DESCRIPTION
        "The prefix length value associated with the corresponding
        cpcIpFilterAddress. The value of zero indicates that no IP 
        mask is associated with the corresponding cpcIpFilterAddress. 
        
        This object may be modified while value of the corresponding
        instance of cpcIpFilterRowStatus is 'active'."
    ::= { cpcIpFilterEntry 4 }

cpcIpFilterRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this conceptual row."
    ::= { cpcIpFilterEntry 5 }

cpcMaxMacFilterAllowed OBJECT-TYPE
    SYNTAX Gauge
    ACCESS read-only
    STATUS mandatory
    DESCRIPTION
        "The maximum number of filters allowed in cpcMacFilterTable
        for each packet capture session. Once the number of entries
        in cpcMacFilterTable reaches the value of this object, if
        users need to create a new entry in cpcMacFilteTable, an
        existing entry must be removed first.  Value of zero
        indicates that there is no limitation."
    ::= { cpcFilterConfig 4 }

cpcMaxIpFilterAllowed OBJECT-TYPE
    SYNTAX Gauge
    ACCESS read-only
    STATUS mandatory
    DESCRIPTION
        "The maximum number of IP filter allowed in cpcIpFilterTable
        for each packet capture session. Once the number of entries
        in cpcIpFilterTable reaches the value of this object, if
        users need to create a new entry in cpcIpFilterTable, an
        existing entry must be removed first. Value of zero
        indicates that there is no limitation."
    ::= { cpcFilterConfig 5 }

cpcPacketLengthFilterTable OBJECT-TYPE
    SYNTAX SEQUENCE OF CpcPacketLengthFilterEntry
    ACCESS not-accessible
    STATUS mandatory
    DESCRIPTION
        "A table of packet length filter configuration
        to be used in the packet capture sessions."
    ::= { cpcFilterConfig 6 }

cpcPacketLengthFilterEntry OBJECT-TYPE
    SYNTAX CpcPacketLengthFilterEntry
    ACCESS not-accessible
    STATUS mandatory
    DESCRIPTION
        "An entry contains management information about a packet
        capture filter based on packet length. A row is created
        for each entry in cpcSessionConfigTable.
        
        This entry may not be modified if value of the corresponding
        instance of cpcSessionOperStatus is 'inProgress'."
    INDEX { cpcSessionId }
    ::= { cpcPacketLengthFilterTable 1 }

CpcPacketLengthFilterEntry ::= SEQUENCE {
    cpcPacketLengthFilterMin Gauge,
    cpcPacketLengthFilterMax Gauge
    }

cpcPacketLengthFilterMin OBJECT-TYPE
    SYNTAX Gauge
--  Units
--    bytes
    ACCESS read-write
    STATUS mandatory
    DESCRIPTION
        "This object specifies the minimum length of the packet to be
         captured. Packets having length smaller than this value will
         not be captured.  A zero value means there is no minimum
         length limit. The value of cpcPacketLengthFilterMax object
         should not be less than that of cpcPacketLengthFilterMin
         object in the same row when both values are non zero."
    ::= { cpcPacketLengthFilterEntry 1 }

cpcPacketLengthFilterMax OBJECT-TYPE
    SYNTAX Gauge
--  Units
--    bytes
    ACCESS read-write
    STATUS mandatory
    DESCRIPTION
        "This object specifies the maximum length of the packet to be
         captured. Packets having length bigger than this value will
         not be captured.  A zero value means there is no maximum
         length limit. The value of cpcPacketLengthFilterMax object
         should not be less than that of cpcPacketLengthFilterMin
         object in the same row when both values are non zero."
    ::= { cpcPacketLengthFilterEntry 2 }

cpcMaxEthertypeFilterAllowed OBJECT-TYPE
    SYNTAX Gauge
    ACCESS read-only
    STATUS mandatory
    DESCRIPTION
        "The maximum number of filters allowed in
        cpcEthertypeFilterTable for each packet capture session.
        Value of zero indicates that there is no limitation."
    ::= { cpcFilterConfig 7 }

cpcEthertypeFilterTable OBJECT-TYPE
    SYNTAX SEQUENCE OF CpcEthertypeFilterEntry
    ACCESS not-accessible
    STATUS mandatory
    DESCRIPTION
        "This table lists Ethertype filter configuration
        to be used in the packet capture sessions."
    ::= { cpcFilterConfig 8 }

cpcEthertypeFilterEntry OBJECT-TYPE
    SYNTAX CpcEthertypeFilterEntry
    ACCESS not-accessible
    STATUS mandatory
    DESCRIPTION
        "An entry contains management information about
        a packet capture filter based on Ethertype.
        
        This entry may not be modified if value of the 
        corresponding instance of cpcSessionOperStatus is 
        'inProgress'."
    INDEX { cpcSessionId, cpcEthertypeFilterValue }
    ::= { cpcEthertypeFilterTable 1 }

CpcEthertypeFilterEntry ::= SEQUENCE {
    cpcEthertypeFilterValue INTEGER,
    cpcEthertypeFilterStatus RowStatus
    }

cpcEthertypeFilterValue OBJECT-TYPE
    SYNTAX INTEGER(0..65535)
    ACCESS not-accessible
    STATUS mandatory
    DESCRIPTION
        "The ethertype value to indicate which packet to
        be captured."
    ::= { cpcEthertypeFilterEntry 1 }

cpcEthertypeFilterStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object specifies the status of this conceptual row and
        is used to manage creation, and deletion of entries in this
        table. Whenever the current number of rows is equal to the
        value of cpcMaxEthertypeFilterAllowed, setting RowStatus of a 
        new row to 'createAndGo' or 'createAndWait' should fail with
        an 'inconsistentValue' error. That is, to create another row,
        an existing row must be deleted via either setting its
        RowStatus object to 'destroy' or alternatively via the CLI."
    ::= { cpcEthertypeFilterEntry 2 }

cpcMaxVlanFilterAllowed OBJECT-TYPE
    SYNTAX Gauge
    ACCESS read-only
    STATUS mandatory
    DESCRIPTION
        "The maximum number of filters allowed in
        cpcVlanFilterTable for each packet capture session.
        Value of zero indicates that there is no limitation."
    ::= { cpcFilterConfig 9 }

cpcVlanFilterTable OBJECT-TYPE
    SYNTAX SEQUENCE OF CpcVlanFilterEntry
    ACCESS not-accessible
    STATUS mandatory
    DESCRIPTION
        "A table of VLAN filter information to be used
         in packet capture sessions."
    ::= { cpcFilterConfig 10 }

cpcVlanFilterEntry OBJECT-TYPE
    SYNTAX CpcVlanFilterEntry
    ACCESS not-accessible
    STATUS mandatory
    DESCRIPTION
        "An entry contains management information about
         a packet capture filter based on VLAN. The entry
         is created or deleted using cpcVlanFilterRowStatus
         object.
        
        This entry may not be modified if value of the 
        corresponding instance of cpcSessionOperStatus is 
        'inProgress'."
    INDEX { cpcSessionId, cpcVlanFilterVlanIndex }
    ::= { cpcVlanFilterTable 1 }

CpcVlanFilterEntry ::= SEQUENCE {
    cpcVlanFilterVlanIndex VlanIndex,
    cpcVlanFilterRowStatus RowStatus
    }

cpcVlanFilterVlanIndex OBJECT-TYPE
    SYNTAX VlanIndex
--    Rsyntax INTEGER(0..4095)
    ACCESS not-accessible
    STATUS mandatory
    DESCRIPTION
        "The VLAN index value of this filter."
    ::= { cpcVlanFilterEntry 1 }

cpcVlanFilterRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object specifies the status of this conceptual row and
        is used to manage creation, and deletion of entries in this
        table.  Whenever the current number of rows is equal to the
        value of cpcMaxVlanFilterAllowed, setting RowStatus of a
        new row to 'createAndGo' or 'createAndWait' should fail with
        an 'inconsistentValue' error. That is, to create another row,
        an existing row must be deleted via either setting its
        RowStatus object to 'destroy' or alternatively via the CLI."
    ::= { cpcVlanFilterEntry 2 }

cpcMaxAccessGroupFilterAllowed OBJECT-TYPE
    SYNTAX Gauge
    ACCESS read-only
    STATUS mandatory
    DESCRIPTION
        "The maximum number of filters allowed in
        cpcAccessGroupFilterTable for each packet capture
        session. Value of zero indicates that there is no
        limitation."
    ::= { cpcFilterConfig 11 }

cpcAccessGroupFilterTable OBJECT-TYPE
    SYNTAX SEQUENCE OF CpcAccessGroupFilterEntry
    ACCESS not-accessible
    STATUS mandatory
    DESCRIPTION
        "A table of Access-Group filter information to be
         used in packet capture sessions."
    ::= { cpcFilterConfig 12 }

cpcAccessGroupFilterEntry OBJECT-TYPE
    SYNTAX CpcAccessGroupFilterEntry
    ACCESS not-accessible
    STATUS mandatory
    DESCRIPTION
        "An entry contains management information about
         a packet capture filter based on Access-Group number
         or name. The entry is created or deleted using 
         cpcAccessGroupFilterStatus object. 
        
        This entry may not be modified if value of the corresponding
        instance of cpcSessionOperStatus is 'inProgress'."
    INDEX { cpcSessionId, cpcAccessGroupFilterType, --?? IMPLIED may cause problems
            IMPLIED cpcAccessGroupFilterName }
    ::= { cpcAccessGroupFilterTable 1 }

CpcAccessGroupFilterEntry ::= SEQUENCE {
    cpcAccessGroupFilterType INTEGER,
    cpcAccessGroupFilterName SnmpAdminString,
    cpcAccessGroupFilterStatus RowStatus
    }

cpcAccessGroupFilterType OBJECT-TYPE
    SYNTAX INTEGER {
        hardware(1),
        software(2)
        }
    ACCESS not-accessible
    STATUS mandatory
    DESCRIPTION
        "The way the ACL denoted by cpcAccessGroupFilterName
        is applied to the packets.
           hardware:  hardware based
           software:  software based."
    ::= { cpcAccessGroupFilterEntry 1 }

cpcAccessGroupFilterName OBJECT-TYPE
    SYNTAX SnmpAdminString(SIZE(1..99))
--    Rsyntax OCTET STRING(SIZE(1..99))
    ACCESS not-accessible
    STATUS mandatory
    DESCRIPTION
        "The ACL name or ACL number used in this package capture filter."
    ::= { cpcAccessGroupFilterEntry 2 }

cpcAccessGroupFilterStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object specifies the status of this conceptual row and
        is used to manage creation, and deletion of entries in this
        table. Whenever the current number of rows is equal to the
        value of cpcMaxAccessGroupFilterAllowed, setting RowStatus of
        a new row to 'createAndGo' or 'createAndWait' should fail
        with an 'inconsistentValue' error. That is, to create another
        row, an existing row must be deleted via either setting its
        RowStatus object to 'destroy' or alternatively via the CLI."
    ::= { cpcAccessGroupFilterEntry 3 }

cpcBufferConfigTable OBJECT-TYPE
    SYNTAX SEQUENCE OF CpcBufferConfigEntry
    ACCESS not-accessible
    STATUS mandatory
    DESCRIPTION
        "A table of buffer configuration and controls for
        packet capture sessions."
    ::= { cpcBufferConfig 1 }

cpcBufferConfigEntry OBJECT-TYPE
    SYNTAX CpcBufferConfigEntry
    ACCESS not-accessible
    STATUS mandatory
    DESCRIPTION
        "An entry contains management information for a packet capture
         session's buffer. An entry is created corresponding to each entry
         in cpcSessionConfigTable.
        
        This entry may not be modified if value of the corresponding
        instance of cpcSessionOperStatus is 'inProgress'."
    INDEX { cpcSessionId }
    ::= { cpcBufferConfigTable 1 }

CpcBufferConfigEntry ::= SEQUENCE {
    cpcBufferType INTEGER,
    cpcBufferSize Gauge,
    cpcBufferAction INTEGER,
    cpcBufferOperStatus INTEGER
    }

cpcBufferType OBJECT-TYPE
    SYNTAX INTEGER {
        linear(1),
        circular(2)
        }
    ACCESS read-write
    STATUS mandatory
    DESCRIPTION
        "Type of the buffer for a packet capture session.
        
         linear  : captured packets will be kept in the buffer one after the
                   other. If there is no available space in the buffer, packet
                   capture session will stop and value of the corresponding
                   instance of cpcSessionOperStatus is set to 'bufferFull'.
        
         circular: If there is no space to store a captured packet completely,
                   the oldest packet in the buffer will be overwritten."
    ::= { cpcBufferConfigEntry 1 }

cpcBufferSize OBJECT-TYPE
    SYNTAX Gauge
--  Units
--    Kilo-bytes
    ACCESS read-write
    STATUS mandatory
    DESCRIPTION
        "Size of the buffer for a packet capture session. A value zero for 
         this object indicates that there is no limitation."
    ::= { cpcBufferConfigEntry 2 }

cpcBufferAction OBJECT-TYPE
    SYNTAX INTEGER {
        noAction(1),
        clear(2),
        export(3)
        }
    ACCESS read-write
    STATUS mandatory
    DESCRIPTION
        "The action control for this packet capture session buffer.
         noAction:  no action (do nothing).
         clear:     clear this capture buffer.
         export:    exporting the buffer contents to the storage
                    specified by cpcSessionDestFileName of
                    cpcSessionConfigEntry with the same cpcSessionId value.
        
        When the value is set to 'noAction', no operation is performed.
        When read, the value 'noAction' is always returned."
    ::= { cpcBufferConfigEntry 3 }

cpcBufferOperStatus OBJECT-TYPE
    SYNTAX INTEGER {
        other(1),
        exporting(2)
        }
    ACCESS read-only
    STATUS mandatory
    DESCRIPTION
        "Operational status of a packet capture buffer.
        
        other      : none of the following.
        exporting  : buffer is being exported to the storage 
                     denoted by cpcSessionDestFileName from 
                     cpcSessionConfigEntry indexed by the
                     same cpcSessionId."
    ::= { cpcBufferConfigEntry 4 }

cpcScheduleConfigTable OBJECT-TYPE
    SYNTAX SEQUENCE OF CpcScheduleConfigEntry
    ACCESS not-accessible
    STATUS mandatory
    DESCRIPTION
        "A table of schedule configuration and information for packet
        capture sessions."
    ::= { cpcScheduleConfig 1 }

cpcScheduleConfigEntry OBJECT-TYPE
    SYNTAX CpcScheduleConfigEntry
    ACCESS not-accessible
    STATUS mandatory
    DESCRIPTION
        "An entry containing schedule configuration and information
         for a packet capture session. An entry is created corresponding
         to each entry in cpcSessionConfigTable if scheduled operation
         is required for a packet capture session.
        
         This entry may not be modified if value of the corresponding
         instance of cpcSessionOperStatus is 'inProgress'."
    INDEX { cpcSessionId }
    ::= { cpcScheduleConfigTable 1 }

CpcScheduleConfigEntry ::= SEQUENCE {
    cpcScheduleStartTime DateAndTime,
    cpcScheduleCapturePeriod Gauge
    }

cpcScheduleStartTime OBJECT-TYPE
    SYNTAX DateAndTime
--    Rsyntax OCTET STRING(SIZE(8|11))
    ACCESS read-write
    STATUS mandatory
    DESCRIPTION
        "The date and time this packet capture session will be
        started. A value of all zero with length of eight indicates
        either the scheduled time has expired or none is scheduled."
    ::= { cpcScheduleConfigEntry 1 }

cpcScheduleCapturePeriod OBJECT-TYPE
    SYNTAX Gauge
--  Units
--    seconds
    ACCESS read-write
    STATUS mandatory
    DESCRIPTION
        "The length of time, in seconds, that this packet capture
         session will be running. Value of zero indicates that there
         is no restriction on the capture period."
    ::= { cpcScheduleConfigEntry 2 }

cpcSessionStatsTable OBJECT-TYPE
    SYNTAX SEQUENCE OF CpcSessionStatsEntry
    ACCESS not-accessible
    STATUS mandatory
    DESCRIPTION
        "A table of statistic information for packet capture
        sessions."
    ::= { cpcSessionStats 1 }

cpcSessionStatsEntry OBJECT-TYPE
    SYNTAX CpcSessionStatsEntry
    ACCESS not-accessible
    STATUS mandatory
    DESCRIPTION
        "An entry contains statistic information of a 
         packet capture session."
    INDEX { cpcSessionId }
    ::= { cpcSessionStatsTable 1 }

CpcSessionStatsEntry ::= SEQUENCE {
    cpcSessionPacketsReceived Gauge,
    cpcSessionPacketsCaptured Gauge,
    cpcSessionPacketsDropped Gauge
    }

cpcSessionPacketsReceived OBJECT-TYPE
    SYNTAX Gauge
    ACCESS read-only
    STATUS mandatory
    DESCRIPTION
        "Indicates the number of packets received in this
         sessions."
    ::= { cpcSessionStatsEntry 1 }

cpcSessionPacketsCaptured OBJECT-TYPE
    SYNTAX Gauge
    ACCESS read-only
    STATUS mandatory
    DESCRIPTION
        "Indicates the number of packets captured in this 
         session."
    ::= { cpcSessionStatsEntry 2 }

cpcSessionPacketsDropped OBJECT-TYPE
    SYNTAX Gauge
    ACCESS read-only
    STATUS mandatory
    DESCRIPTION
        "Indicates the number of packets dropped in this
         session."
    ::= { cpcSessionStatsEntry 3 }

cpcGenericConfigGroup OBJECT IDENTIFIER ::= { cpcMIBGroups 1 }
-- OBJECT-GROUP
--  Status
--    mandatory
--  Descr
--    A collection of object(s) that provides the generic
--    configuration for packet capture feature.
--  objects
--    cpcMaxSessionAllowed, cpcSessionOperStatus, 
--    cpcSessionMaxSources, cpcSessionPacketLength, 
--    cpcSessionPacketLimits, cpcSessionAction, 
--    cpcSessionConfigStatus, cpcCaptureSourceIfDirection, 
--    cpcCaptureSourceIfStatus

cpcFilterConfigGroup OBJECT IDENTIFIER ::= { cpcMIBGroups 2 }
-- OBJECT-GROUP
--  Status
--    mandatory
--  Descr
--    A collection of object(s) that provides general
--    filter configuration for packet capture feature.
--  objects
--    cpcMaxFilterAllowed

cpcMacFilterConfigGroup OBJECT IDENTIFIER ::= { cpcMIBGroups 3 }
-- OBJECT-GROUP
--  Status
--    mandatory
--  Descr
--    A collection of object(s) that provides the MAC
--    address filter configuration for packet capture
--    feature.
--  objects
--    cpcMacFilterRowStatus

cpcIpFilterConfigGroup OBJECT IDENTIFIER ::= { cpcMIBGroups 4 }
-- OBJECT-GROUP
--  Status
--    mandatory
--  Descr
--    A collection of object(s) that provides the IP
--    address filter configuration for packet capture
--    feature.
--  objects
--    cpcIpFilterMask, cpcIpFilterRowStatus

cpcDestFileNameConfigGroup OBJECT IDENTIFIER ::= { cpcMIBGroups 5 }
-- OBJECT-GROUP
--  Status
--    mandatory
--  Descr
--    A collection of object(s) that provides configuration
--    for destination file for packet capture feature.
--  objects
--    cpcSessionDestFileName

cpcPacketLengthFilterConfigGroup OBJECT IDENTIFIER ::= { cpcMIBGroups 6 }
-- OBJECT-GROUP
--  Status
--    mandatory
--  Descr
--    A collection of object(s) that provides packet
--    length filter configuration for packet capture
--    feature.
--  objects
--    cpcPacketLengthFilterMin, cpcPacketLengthFilterMax

cpcEthertypeFilterConfigGroup OBJECT IDENTIFIER ::= { cpcMIBGroups 7 }
-- OBJECT-GROUP
--  Status
--    mandatory
--  Descr
--    A collection of object(s) that provides Ethertype
--    filter configuration for packet capture feature.
--  objects
--    cpcMaxEthertypeFilterAllowed, cpcEthertypeFilterStatus

cpcVlanFilterConfigGroup OBJECT IDENTIFIER ::= { cpcMIBGroups 8 }
-- OBJECT-GROUP
--  Status
--    mandatory
--  Descr
--    A collection of object(s) that provides VLAN
--     filter configuration for packet capture feature.
--  objects
--    cpcMaxVlanFilterAllowed, cpcVlanFilterRowStatus

cpcAccessGroupFilterConfigGroup OBJECT IDENTIFIER ::= { cpcMIBGroups 9 }
-- OBJECT-GROUP
--  Status
--    mandatory
--  Descr
--    A collection of object(s) that provides Access
--    Group filter configuration for packet capture
--    feature.
--  objects
--    cpcMaxAccessGroupFilterAllowed, cpcAccessGroupFilterStatus

cpcBufferConfigGroup OBJECT IDENTIFIER ::= { cpcMIBGroups 10 }
-- OBJECT-GROUP
--  Status
--    mandatory
--  Descr
--    A collection of object(s) that provides buffer
--     configuration for packet capture feature.
--  objects
--    cpcBufferType, cpcBufferSize, cpcBufferAction, 
--    cpcBufferOperStatus

cpcScheduleConfigGroup OBJECT IDENTIFIER ::= { cpcMIBGroups 11 }
-- OBJECT-GROUP
--  Status
--    mandatory
--  Descr
--    A collection of object(s) that provides schedule
--     configuration for packet capture feature.
--  objects
--    cpcScheduleStartTime, cpcScheduleCapturePeriod

cpcSessionStatsGroup OBJECT IDENTIFIER ::= { cpcMIBGroups 12 }
-- OBJECT-GROUP
--  Status
--    mandatory
--  Descr
--    A collection of object(s) that provides statistic
--     information for packet capture feature.
--  objects
--    cpcSessionPacketsReceived, cpcSessionPacketsCaptured, 
--    cpcSessionPacketsDropped

cpcMaxMacFilterConfigGroup OBJECT IDENTIFIER ::= { cpcMIBGroups 13 }
-- OBJECT-GROUP
--  Status
--    mandatory
--  Descr
--    A collection of object(s) that provides information on
--    the maximum MAC address filter allowed for each packet
--    capture session.
--  objects
--    cpcMaxMacFilterAllowed

cpcMaxIpFilterConfigGroup OBJECT IDENTIFIER ::= { cpcMIBGroups 14 }
-- OBJECT-GROUP
--  Status
--    mandatory
--  Descr
--    A collection of object(s) that provides information on
--    the maximum IP address filter allowed for each packet
--    capture session.
--  objects
--    cpcMaxIpFilterAllowed

cpcSessionPacketRateLimitGroup OBJECT IDENTIFIER ::= { cpcMIBGroups 15 }
-- OBJECT-GROUP
--  Status
--    mandatory
--  Descr
--    A collection of object(s) that provides rate limit
--    configuration for packet capture feature.
--  objects
--    cpcSessionPacketRateLimit

cpcSessionDescrGroup OBJECT IDENTIFIER ::= { cpcMIBGroups 16 }
-- OBJECT-GROUP
--  Status
--    mandatory
--  Descr
--    A collection of object(s) that provides session 
--    description configuration for packet capture feature.
--  objects
--    cpcSessionDescr

cpcCompliance OBJECT IDENTIFIER ::= { cpcMIBCompliances 1 }
-- MODULE-COMPLIANCE
--  Status
--    deprecated
--  Descr
--    The compliance statement for devices that implement
--    CISCO-PACKET-CAPTURE-MIB.
--  Module
--    >>current<<
--   MandGroup
--    cpcGenericConfigGroup
--   OptGroup
--    cpcFilterConfigGroup
--   OptGroup
--    cpcMacFilterConfigGroup
--   OptGroup
--    cpcIpFilterConfigGroup
--   OptGroup
--    cpcDestFileNameConfigGroup
--   ObjVar
--    cpcSessionConfigStatus
--   ObjVar
--    cpcCaptureSourceIfStatus
--   ObjVar
--    cpcMacFilterRowStatus
--   ObjVar
--    cpcIpFilterRowStatus

cpcComplianceRev1 OBJECT IDENTIFIER ::= { cpcMIBCompliances 2 }
-- MODULE-COMPLIANCE
--  Status
--    mandatory
--  Descr
--    The compliance statement for devices that implement
--    CISCO-PACKET-CAPTURE-MIB.
--  Module
--    >>current<<
--   MandGroup
--    cpcGenericConfigGroup
--   OptGroup
--    cpcFilterConfigGroup
--   OptGroup
--    cpcMacFilterConfigGroup
--   OptGroup
--    cpcIpFilterConfigGroup
--   OptGroup
--    cpcDestFileNameConfigGroup
--   OptGroup
--    cpcPacketLengthFilterConfigGroup
--   OptGroup
--    cpcEthertypeFilterConfigGroup
--   OptGroup
--    cpcVlanFilterConfigGroup
--   OptGroup
--    cpcAccessGroupFilterConfigGroup
--   OptGroup
--    cpcBufferConfigGroup
--   OptGroup
--    cpcScheduleConfigGroup
--   OptGroup
--    cpcSessionStatsGroup
--   OptGroup
--    cpcMaxMacFilterConfigGroup
--   OptGroup
--    cpcMaxIpFilterConfigGroup
--   OptGroup
--    cpcSessionPacketRateLimitGroup
--   OptGroup
--    cpcSessionDescrGroup
--   ObjVar
--    cpcSessionConfigStatus
--   ObjVar
--    cpcCaptureSourceIfStatus
--   ObjVar
--    cpcMacFilterRowStatus
--   ObjVar
--    cpcIpFilterRowStatus


END
