-- MIB file created 23-Aug-2013 11:03:25, by
--   SMICng version 2.2.11-beta(PRO)(Solaris), January 20, 2001. Enterprise key cisco.com

CISCO-AUTH-FRAMEWORK-MIB DEFINITIONS ::= BEGIN

-- From file: "CISCO-AUTH-FRAMEWORK-MIB.my"
-- Compile options "4 7 F H N W 03 06 0B 0G 0N 0T"

IMPORTS
    MacAddress, TruthValue
            FROM SNMPv2-TC-v1
    SnmpAdminString
            FROM SNMP-FRAMEWORK-MIB
    InetAddress, InetAddressType
            FROM INET-ADDRESS-MIB
    ifIndex, ifName
            FROM IF-MIB
    VlanIndexOrZero
            FROM CISCO-PRIVATE-VLAN-MIB
    CnnEouPostureTokenString
            FROM CISCO-NAC-TC-MIB
    ciscoMgmt
            FROM CISCO-SMI
    Gauge
            FROM RFC1155-SMI
    OBJECT-TYPE
            FROM RFC-1212
    TRAP-TYPE
            FROM RFC-1215;

ciscoAuthFrameworkMIB OBJECT IDENTIFIER ::= { ciscoMgmt 656 }
-- MODULE-IDENTITY
--  LastUpdated
--    201308230000Z
--  OrgName
--    Cisco Systems Inc.
--  ContactInfo
--    Cisco Systems
--    Customer Service
--    Postal: 170 W Tasman Drive
--    San Jose, CA  95134
--    USA
--    Tel: +1 800 553 -NETS
--    E-mail: cs-ibns@cisco.com,
--            cs-lan-switch-snmp@cisco.com
--  Descr
--    MIB module for Authentication Framework in the system.
--    
--    Authentication Framework provides generic configurations
--    for authentication methods in the system and manage the
--    failover sequence of these methods in a flexible manner.
--  RevDate
--    201308230000Z
--  RevDescr
--    Added notification cafAuthFailNotif.
--    Added new objects cafAuthFailNotifEnable and
--    cafAuthFailClient.
--    Added new groups cafAuthFailNotifGroup,
--    cafAuthFailNotifEnableGroup and cafAuthFailClientGroup.
--    A new compliance ciscoAuthFrameworkMIBCompliance4 is added
--    which deprecates ciscoAuthFrameworkMIBCompliance3.
--  RevDate
--    201011170000Z
--  RevDescr
--    Added cafMacMoveConfigGroup and cafCoACommandConfigGroup
--    groups.
--  RevDate
--    201004010000Z
--  RevDescr
--    Added value 'replace' to cafPortViolationAction.
--  RevDate
--    200904200000Z
--  RevDescr
--    Added cafSessionVlanGroupNameGroup.
--  RevDate
--    200810240000Z
--  RevDescr
--    Added value 'protect' to cafPortViolationAction.
--  RevDate
--    200808250000Z
--  RevDescr
--    Initial version of this MIB module.

ciscoAuthFrameworkMIBNotifs OBJECT IDENTIFIER ::= { ciscoAuthFrameworkMIB 0 }
ciscoAuthFrameworkMIBObjects OBJECT IDENTIFIER ::= { ciscoAuthFrameworkMIB 1 }
ciscoAuthFrameworkMIBConform OBJECT IDENTIFIER ::= { ciscoAuthFrameworkMIB 2 }
ciscoAuthFrameworkSystem OBJECT IDENTIFIER ::= { ciscoAuthFrameworkMIBObjects 1 }
ciscoAuthFrwkAuthenticator OBJECT IDENTIFIER ::= { ciscoAuthFrameworkMIBObjects 2 }
ciscoAuthFrameworkEvent OBJECT IDENTIFIER ::= { ciscoAuthFrameworkMIBObjects 3 }
ciscoAuthFrameworkSession OBJECT IDENTIFIER ::= { ciscoAuthFrameworkMIBObjects 4 }
ciscoAuthFrwkNotifControl OBJECT IDENTIFIER ::= { ciscoAuthFrameworkMIBObjects 5 }
ciscoAuthFrwkNotifInfo OBJECT IDENTIFIER ::= { ciscoAuthFrameworkMIBObjects 6 }
ciscoAuthFrameworkMIBCompliances OBJECT IDENTIFIER ::= { ciscoAuthFrameworkMIBConform 1 }
ciscoAuthFrameworkMIBGroups OBJECT IDENTIFIER ::= { ciscoAuthFrameworkMIBConform 2 }

CiscoAuthControlledDirections ::= INTEGER {
        --?? enum value of zero may cause problems
--        both(0),
        in(1)
        }
-- TEXTUAL-CONVENTION
--  Status
--    mandatory
--  Descr
--    The controlled direction values for capable ports in
--    Authentication Framework.
--    
--    both: control is required to be exerted over both
--          incoming and outgoing traffic through the
--          controlled port.
--    
--    in  : control is required to be exerted over the
--          incoming traffic through the controlled port.

CiscoAuthControlledPortControl ::= INTEGER {
        forceUnauthorized(1),
        auto(2),
        forceAuthorized(3)
        }
-- TEXTUAL-CONVENTION
--  Status
--    mandatory
--  Descr
--    The authorization control values of Authentication
--    Framework on a controlled port.
--    
--    forceUnauthorized: the controlled port is forced to
--                     be unauthorized unconditionally.
--    
--    auto             : authorization of the controlled
--                     port will be determined by an
--                     authentication process.
--    
--    forceAuthorized  : The controlled port is forced to
--                     be authorized unconditionally.

CiscoAuthMethod ::= INTEGER {
        other(1),
        dot1x(2),
        macAuthBypass(3),
        webAuth(4)
        }
-- TEXTUAL-CONVENTION
--  Status
--    mandatory
--  Descr
--    The authentication methods and protocols supported in
--    Authentication Framework.
--    
--    other        : none of the below.
--    
--    dot1x        : 802.1x Protocol.
--    
--    macAuthBypass: MAC Authentication Bypass. 
--    
--    webAuth      : Web-Proxy Authentication.
--    
--    'other' is a read only value which can not be used in
--    set operation.

CiscoAuthMethodList ::= OCTET STRING
-- TEXTUAL-CONVENTION
--  Status
--    mandatory
--  Descr
--    The list of authentication methods provided within
--    Authentication Framework.
--    
--    Each octet represents an authentication method which
--    is defined in CiscoAuthMethod.
--    
--    The DESCRIPTION clause of CiscoAuthMethodList objects
--    must fully describe the relationship between methods.

CiscoAuthHostMode ::= INTEGER {
        singleHost(1),
        multiHost(2),
        multiAuth(3),
        multiDomain(4)
        }
-- TEXTUAL-CONVENTION
--  Status
--    mandatory
--  Descr
--    The authentication mode of a controlled port.
--    
--    singleHost: port allows one host to connect and authenticate
--                in a single domain.
--    
--    multiHost : port allows multiple hosts to connect. Once
--              a host is authenticated, all remaining hosts are
--              also authenticated in a single domain.
--    
--    multiAuth : port allows multiple hosts to connect. Each host
--              is authenticated separately in a single domain.
--    
--    multiDomain: port allows multiple domains to be authenticated.

cafAaaNoRespRecoveryDelay OBJECT-TYPE
    SYNTAX Gauge
--  Units
--    milliseconds
    ACCESS read-write
    STATUS mandatory
    DESCRIPTION
        "Specifies the AAA recovery delay for authentication methods
        registered in Authentication Framework when AAA server becomes
        active again after being inactive. A value of zero indicates
        that AAA recovery delay is disabled in the system."
    ::= { ciscoAuthFrameworkSystem 1 }

cafAuthMethodRegTable OBJECT-TYPE
    SYNTAX SEQUENCE OF CafAuthMethodRegEntry
    ACCESS not-accessible
    STATUS mandatory
    DESCRIPTION
        "A list of authentication methods which are currrently
        registered with Authentication Framework. 
        
        An entry is created by the agent when an authentication method 
        has successfully registered with Authentication Framework. 
        
        An entry is deleted by the agent upon de-registration of the 
        authentication method."
    ::= { ciscoAuthFrameworkSystem 2 }

cafAuthMethodRegEntry OBJECT-TYPE
    SYNTAX CafAuthMethodRegEntry
    ACCESS not-accessible
    STATUS mandatory
    DESCRIPTION
        "An entry containing registration information of a particular
        authentication method with Authentication Framework."
    INDEX { cafAuthMethod }
    ::= { cafAuthMethodRegTable 1 }

CafAuthMethodRegEntry ::= SEQUENCE {
    cafAuthMethod CiscoAuthMethod,
    cafAuthMethodDefaultPriority Gauge,
    cafAuthMethodDefaultExecOrder Gauge
    }

cafAuthMethod OBJECT-TYPE
    SYNTAX CiscoAuthMethod
--    Rsyntax INTEGER {
--        other(1),
--        dot1x(2),
--        macAuthBypass(3),
--        webAuth(4)
--        }
    ACCESS not-accessible
    STATUS mandatory
    DESCRIPTION
        "The authentication method registered with Authentication
        Framework."
    ::= { cafAuthMethodRegEntry 1 }

cafAuthMethodDefaultPriority OBJECT-TYPE
    SYNTAX Gauge
    ACCESS read-only
    STATUS mandatory
    DESCRIPTION
        "A unique number which indicates the default priority of a
        authentication method.
        
        The default priority is assigned by Authentication Framework 
        during method registration.  The method with smallest value 
        has highest priority."
    ::= { cafAuthMethodRegEntry 2 }

cafAuthMethodDefaultExecOrder OBJECT-TYPE
    SYNTAX Gauge
    ACCESS read-only
    STATUS mandatory
    DESCRIPTION
        "A unique number which indicates the default execution order
        of a authentication method. 
        
        The default execution order is assigned by Authentication
        Framework during method registration.  The method with
        smallest value will be execute first."
    ::= { cafAuthMethodRegEntry 3 }

cafMacMoveMode OBJECT-TYPE
    SYNTAX INTEGER {
        deny(1),
        permit(2)
        }
    ACCESS read-write
    STATUS mandatory
    DESCRIPTION
        "This object specifies the MAC Move configuration for
        Authentication Framework. 
        
        deny : When a host is authenticated on one port, 
              that address is not allowed on another 
              authenticated manager-enabled port of the device. 
        
        permit: Authenticated hosts are allowed to move from one 
               port to another on the same device. When a host moves to 
               a new port, the authenticated session on the original 
               port is deleted, and the host is reauthenticated on the 
               new port."
    ::= { ciscoAuthFrameworkSystem 3 }

cafCoABouncePortCommandIgnoreEnabled OBJECT-TYPE
    SYNTAX TruthValue
--    Rsyntax INTEGER {
--        true(1),
--        false(2)
--        }
    ACCESS read-write
    STATUS mandatory
    DESCRIPTION
        "This object specifies whether the device ignores the bounce
        port command that sent from RADIUS via Change-of-Authorization
        (CoA) packets."
    ::= { ciscoAuthFrameworkSystem 4 }

cafCoADisablePortCommandIgnoreEnabled OBJECT-TYPE
    SYNTAX TruthValue
--    Rsyntax INTEGER {
--        true(1),
--        false(2)
--        }
    ACCESS read-write
    STATUS mandatory
    DESCRIPTION
        "This object specifies whether the device ingores the
        disable port command that sent from RADIUS via
        Change-of-Authorization (CoA) packets."
    ::= { ciscoAuthFrameworkSystem 5 }

cafPortConfigTable OBJECT-TYPE
    SYNTAX SEQUENCE OF CafPortConfigEntry
    ACCESS not-accessible
    STATUS mandatory
    DESCRIPTION
        "A list of port entries.  An entry will exist for each
        interface which support Authentication Framework feature."
    ::= { ciscoAuthFrwkAuthenticator 1 }

cafPortConfigEntry OBJECT-TYPE
    SYNTAX CafPortConfigEntry
    ACCESS not-accessible
    STATUS mandatory
    DESCRIPTION
        "An entry containing management information of Authentication
        Framework applicable to a particular port."
    INDEX { ifIndex }
    ::= { cafPortConfigTable 1 }

CafPortConfigEntry ::= SEQUENCE {
    cafPortControlledDirection CiscoAuthControlledDirections,
    cafPortFallBackProfile SnmpAdminString,
    cafPortAuthHostMode CiscoAuthHostMode,
    cafPortPreAuthOpenAccess TruthValue,
    cafPortAuthorizeControl CiscoAuthControlledPortControl,
    cafPortReauthEnabled TruthValue,
    cafPortReauthInterval Gauge,
    cafPortRestartInterval Gauge,
    cafPortInactivityTimeout INTEGER,
    cafPortViolationAction INTEGER
    }

cafPortControlledDirection OBJECT-TYPE
    SYNTAX CiscoAuthControlledDirections
--    Rsyntax INTEGER {
--        ?? enum value of zero may cause problems
--        both(0),
--        in(1)
--        }
    ACCESS read-write
    STATUS mandatory
    DESCRIPTION
        "Specifies the controlled direction of this port."
    ::= { cafPortConfigEntry 1 }

cafPortFallBackProfile OBJECT-TYPE
    SYNTAX SnmpAdminString
--    Rsyntax OCTET STRING(SIZE(0..255))
    ACCESS read-write
    STATUS mandatory
    DESCRIPTION
        "Specifies the name of the fallback profile to be used when
        failing over to Web Proxy Authentication.  A zero length
        string indicates that fallback mechanism to Web Proxy
        Authentication is disabled in Authentication Framework."
    ::= { cafPortConfigEntry 2 }

cafPortAuthHostMode OBJECT-TYPE
    SYNTAX CiscoAuthHostMode
--    Rsyntax INTEGER {
--        singleHost(1),
--        multiHost(2),
--        multiAuth(3),
--        multiDomain(4)
--        }
    ACCESS read-write
    STATUS mandatory
    DESCRIPTION
        "Specifies the authentication host mode for this port."
    ::= { cafPortConfigEntry 3 }

cafPortPreAuthOpenAccess OBJECT-TYPE
    SYNTAX TruthValue
--    Rsyntax INTEGER {
--        true(1),
--        false(2)
--        }
    ACCESS read-write
    STATUS mandatory
    DESCRIPTION
        "Specifies if the Pre-Authentication Open Access feature
        allows clients/devices to gain network access before 
        authentication is performed. 
        
        A value of 'true' for this object indicates that client/device 
        is able to gain network access before authentication is 
        performed."
    ::= { cafPortConfigEntry 4 }

cafPortAuthorizeControl OBJECT-TYPE
    SYNTAX CiscoAuthControlledPortControl
--    Rsyntax INTEGER {
--        forceUnauthorized(1),
--        auto(2),
--        forceAuthorized(3)
--        }
    ACCESS read-write
    STATUS mandatory
    DESCRIPTION
        "Specifies the authorization control for this port."
    ::= { cafPortConfigEntry 5 }

cafPortReauthEnabled OBJECT-TYPE
    SYNTAX TruthValue
--    Rsyntax INTEGER {
--        true(1),
--        false(2)
--        }
    ACCESS read-write
    STATUS mandatory
    DESCRIPTION
        "Specifies if reauthentication is enabled for this port."
    ::= { cafPortConfigEntry 6 }

cafPortReauthInterval OBJECT-TYPE
    SYNTAX Gauge
--  Units
--    seconds
    ACCESS read-write
    STATUS mandatory
    DESCRIPTION
        "Specifies the reauthentication interval, after which the port
        will be reauthenticated if value of the corresponding instance
        of cafPortReauthEnabled is 'true'.
        
        A value of zero indicates that the reauthentication interval
        is downloaded from AAA server when this port is authenticated."
    ::= { cafPortConfigEntry 7 }

cafPortRestartInterval OBJECT-TYPE
    SYNTAX Gauge
--  Units
--    seconds
    ACCESS read-write
    STATUS mandatory
    DESCRIPTION
        "Specifies the interval after which a further authentication
        attempt should be made to this port if it is not authorized.
        
        A value of zero indicates that no further authentication attempt
        will be made if this port is unauthorized."
    ::= { cafPortConfigEntry 8 }

cafPortInactivityTimeout OBJECT-TYPE
    SYNTAX INTEGER(-1|0|1..65535)
--  Units
--    seconds
    ACCESS read-write
    STATUS mandatory
    DESCRIPTION
        "Specifies the period of time that a client associating with
        this
        port is allowed to be inactive before being terminated.
        
        A value of zero indicates that inactivity timeout is disabled on
        
        this port.
        
        A value of -1 indicates that inactivity timeout is downloaded
        from the AAA server when this port is authenticated."
    ::= { cafPortConfigEntry 9 }

cafPortViolationAction OBJECT-TYPE
    SYNTAX INTEGER {
        restrict(1),
        shutdown(2),
        protect(3),
        replace(4)
        }
    ACCESS read-write
    STATUS mandatory
    DESCRIPTION
        "Specifies the action to be taken due to a security violation
        occurs on this port.
        
              restrict: This port will be moved to restricted state.
        
              shutdown: This port will be shutdown from Authentication
                        Framework perspective.
        
              protect : This port will be moved to protected state.
        
              replace : The current authentication session on this
                        port will be terminated and replaced by a new
                        authentication session, upon the detection of
                        security violation on the current authentication
                        session on the port."
    ::= { cafPortConfigEntry 10 }

cafPortMethodTable OBJECT-TYPE
    SYNTAX SEQUENCE OF CafPortMethodEntry
    ACCESS not-accessible
    STATUS mandatory
    DESCRIPTION
        "The table contains a list of port entries.  An entry will exist
        for each port which supports Authentication Framework feature."
    ::= { ciscoAuthFrwkAuthenticator 2 }

cafPortMethodEntry OBJECT-TYPE
    SYNTAX CafPortMethodEntry
    ACCESS not-accessible
    STATUS mandatory
    DESCRIPTION
        "Entry containing configuration and information of
        authentication methods for a particular port."
    INDEX { ifIndex }
    ::= { cafPortMethodTable 1 }

CafPortMethodEntry ::= SEQUENCE {
    cafPortMethodAdminExecOrder CiscoAuthMethodList,
    cafPortMethodAdminPriority CiscoAuthMethodList,
    cafPortMethodAvailable CiscoAuthMethodList,
    cafPortMethodOperExecOrder CiscoAuthMethodList,
    cafPortMethodOperPriority CiscoAuthMethodList
    }

cafPortMethodAdminExecOrder OBJECT-TYPE
    SYNTAX CiscoAuthMethodList
--    Rsyntax OCTET STRING
    ACCESS read-write
    STATUS mandatory
    DESCRIPTION
        "This object specifies the administrative execution order of
        authentication methods on the port.  Methods are executed in
        the order as specified in the method list.
        
        Method which is at the beginning of the method list will be
        executed first.  Method which is at the end of method list
        will be executed last.
        
        A zero length string of this object indicates that no per
        port execution order configuration has been specified on
        this port. The actual execution order is based on the value
        of cafAuthMethodDefaultExecOrder in cafAuthMethodRegTable."
    ::= { cafPortMethodEntry 1 }

cafPortMethodAdminPriority OBJECT-TYPE
    SYNTAX CiscoAuthMethodList
--    Rsyntax OCTET STRING
    ACCESS read-write
    STATUS mandatory
    DESCRIPTION
        "This object specifies the administrative priority of
        authentication methods on the port.  The priority of
        each method is assigned based on the method list.
        
        Method which is at the beginning of the method list has
        highest priority.  Method which is at the end of method list
        has lowest priority.
        
        A zero length string of this object indicates that no per
        port method priority configuration has been specified on
        this port.  The actual execution order is based on the value 
        of cafAuthMethodDefaultExecOrder in cafAuthMethodRegTable."
    ::= { cafPortMethodEntry 2 }

cafPortMethodAvailable OBJECT-TYPE
    SYNTAX CiscoAuthMethodList
--    Rsyntax OCTET STRING
    ACCESS read-only
    STATUS mandatory
    DESCRIPTION
        "This object indicates the authentication methods currently
        available on this port."
    ::= { cafPortMethodEntry 3 }

cafPortMethodOperExecOrder OBJECT-TYPE
    SYNTAX CiscoAuthMethodList
--    Rsyntax OCTET STRING
    ACCESS read-only
    STATUS mandatory
    DESCRIPTION
        "This object indicates the operational execution order of
        authentication methods on this port.  Methods are executed in
        the order as specified in the method list.
        
        Method which is at the beginning of the method list will be
        executed first.  Method which is at the end of method list
        will be executed last."
    ::= { cafPortMethodEntry 4 }

cafPortMethodOperPriority OBJECT-TYPE
    SYNTAX CiscoAuthMethodList
--    Rsyntax OCTET STRING
    ACCESS read-only
    STATUS mandatory
    DESCRIPTION
        "This object indicates the operational priority of
        authentication methods on this port.  Methods have the
        priority as specified in the method list.
        
        Method which is at the beginning of the method list has
        highest priority.  Method which is at the end of method list
        has lowest priority."
    ::= { cafPortMethodEntry 5 }

cafAuthFailedEventPortTable OBJECT-TYPE
    SYNTAX SEQUENCE OF CafAuthFailedEventPortEntry
    ACCESS not-accessible
    STATUS mandatory
    DESCRIPTION
        "The table contains a list of port entries.
        
        An entry will exist for each port which supports Authentication
        Fail event within the Authentication Framework."
    ::= { ciscoAuthFrameworkEvent 1 }

cafAuthFailedEventPortEntry OBJECT-TYPE
    SYNTAX CafAuthFailedEventPortEntry
    ACCESS not-accessible
    STATUS mandatory
    DESCRIPTION
        "Entry containing management information of Authentication
        Fail event for a particular port."
    INDEX { ifIndex }
    ::= { cafAuthFailedEventPortTable 1 }

CafAuthFailedEventPortEntry ::= SEQUENCE {
    cafAuthFailedMaxRetry Gauge,
    cafAuthFailedNoActionEnabled TruthValue,
    cafAuthFailedAuthorizedVlan INTEGER,
    cafAuthFailedNextMethodEnabled TruthValue
    }

cafAuthFailedMaxRetry OBJECT-TYPE
    SYNTAX Gauge
    ACCESS read-write
    STATUS mandatory
    DESCRIPTION
        "This object specifies the maximum number of retry should be
        performed before generating Authentication Fail event.
        
        A value of zero indicates that Authentication Fail event will
        be generated upon authentication fail without any retry."
    ::= { cafAuthFailedEventPortEntry 1 }

cafAuthFailedNoActionEnabled OBJECT-TYPE
    SYNTAX TruthValue
--    Rsyntax INTEGER {
--        true(1),
--        false(2)
--        }
    ACCESS read-write
    STATUS mandatory
    DESCRIPTION
        "This object specifies whether no action will be performed
        when an Authentication Fail event occurs.
        
        Setting 'true' on this object indicates that no action will
        be performed when Authentication Fail event occurs.
        
        The read-only value 'false' indicates that an action will
        be performed when an Authentication Fail event occurs."
    ::= { cafAuthFailedEventPortEntry 2 }

cafAuthFailedAuthorizedVlan OBJECT-TYPE
    SYNTAX INTEGER(-1|0|1..2147483647)
    ACCESS read-write
    STATUS mandatory
    DESCRIPTION
        "This object specifies the Authentication Failed VLAN number.
        
        The read-only value of -1 indicates that this object is not
        applicable on this port.
        
        The read-only value of zero indicates that this port will not be
        authorized to any VLAN when Authentication Failed event occurs.
        
        Setting a non-zero value on this object indicates that this port
        will be authorized to the VLAN as specified by this object
        value, when Authentication Fail event occurs."
    ::= { cafAuthFailedEventPortEntry 3 }

cafAuthFailedNextMethodEnabled OBJECT-TYPE
    SYNTAX TruthValue
--    Rsyntax INTEGER {
--        true(1),
--        false(2)
--        }
    ACCESS read-write
    STATUS mandatory
    DESCRIPTION
        "This object specifies whether the next authentication method
        will be used if an Authentication Fail event is generated by the
        current authentication method.
        
        Setting this object to 'true' indicates that the next available
        authentication method will be used when Authentication Fail 
        event occurs.
        
        The read-only value 'false' indicates that the next available
        authentication method will not be used when Authentication Fail
        event occurs."
    ::= { cafAuthFailedEventPortEntry 4 }

cafSecurityViolationClient OBJECT-TYPE
    SYNTAX MacAddress
--    Rsyntax OCTET STRING(SIZE(6))
    ACCESS not-accessible
    STATUS mandatory
    DESCRIPTION
        "The MAC address included in the notification currently being
        sent, indicating the client who triggered the security violation
        notification."
    ::= { ciscoAuthFrwkNotifInfo 1 }

cafAuthFailClient OBJECT-TYPE
    SYNTAX MacAddress
--    Rsyntax OCTET STRING(SIZE(6))
    ACCESS not-accessible
    STATUS mandatory
    DESCRIPTION
        "The MAC address included in the cafAuthFailNotif being
        sent, indicating the client which failed to authenticate."
    ::= { ciscoAuthFrwkNotifInfo 2 }

cafClientNoRespEventPortTable OBJECT-TYPE
    SYNTAX SEQUENCE OF CafClientNoRespEventPortEntry
    ACCESS not-accessible
    STATUS mandatory
    DESCRIPTION
        "The table contains a list of port entries.
        
        An entry exists for each port which supports No Response
        event within the Authentication Framework."
    ::= { ciscoAuthFrameworkEvent 2 }

cafClientNoRespEventPortEntry OBJECT-TYPE
    SYNTAX CafClientNoRespEventPortEntry
    ACCESS not-accessible
    STATUS mandatory
    DESCRIPTION
        "Entry containing management information of No Response
        event for a particular port."
    INDEX { ifIndex }
    ::= { cafClientNoRespEventPortTable 1 }

CafClientNoRespEventPortEntry ::= SEQUENCE {
    cafClientNoRespNoActionEnabled TruthValue,
    cafClientNoRespAuthorizedVlan INTEGER
    }

cafClientNoRespNoActionEnabled OBJECT-TYPE
    SYNTAX TruthValue
--    Rsyntax INTEGER {
--        true(1),
--        false(2)
--        }
    ACCESS read-write
    STATUS mandatory
    DESCRIPTION
        "This object specifies whether an action is performed when No
        Response event occurs.
        
        Setting 'true' on this object indicates that no action will
        be performed when No Response event occurs.
        
        The read-only value 'false' of this object indicates that an
        action will be performed when No Response event occurs."
    ::= { cafClientNoRespEventPortEntry 1 }

cafClientNoRespAuthorizedVlan OBJECT-TYPE
    SYNTAX INTEGER(-1|0|1..2147483647)
    ACCESS read-write
    STATUS mandatory
    DESCRIPTION
        "This object specifies the No Response Authorized VLAN number.
        
        The read-only value of -1 indicates that this object is not
        applicable on this port.
        
        The read-only value of zero indicates that this port will not be
        authorized to any VLAN when No Response event occurs.
        
        Setting a non-zero value on this object indicates that this port
        will be authorized to the VLAN as specified by this object
        value, when No Response event occurs."
    ::= { cafClientNoRespEventPortEntry 2 }

cafServerEventPortTable OBJECT-TYPE
    SYNTAX SEQUENCE OF CafServerEventPortEntry
    ACCESS not-accessible
    STATUS mandatory
    DESCRIPTION
        "The table contains a list of port entries.
        
        An entry exists for each port which supports AAA Server
        Reachability event within the Authentication Framework."
    ::= { ciscoAuthFrameworkEvent 3 }

cafServerEventPortEntry OBJECT-TYPE
    SYNTAX CafServerEventPortEntry
    ACCESS not-accessible
    STATUS mandatory
    DESCRIPTION
        "Entry containing management information of AAA Server
        Reachability event for a particular port."
    INDEX { ifIndex }
    ::= { cafServerEventPortTable 1 }

CafServerEventPortEntry ::= SEQUENCE {
    cafServerDeadNoActionEnabled TruthValue,
    cafServerDeadRemainAuthorized TruthValue,
    cafServerDeadAuthorizedVlan INTEGER,
    cafServerAliveAction INTEGER
    }

cafServerDeadNoActionEnabled OBJECT-TYPE
    SYNTAX TruthValue
--    Rsyntax INTEGER {
--        true(1),
--        false(2)
--        }
    ACCESS read-write
    STATUS mandatory
    DESCRIPTION
        "This object indicates whether an action is performed if an
        AAA Server Reachability event occurs.
        
        Setting 'true' on this object indicates that no action
        will be performed when AAA Server Reachability event occurs.
        
        The read-only value 'false' indicates that an action will
        be performed when AAA Server Reachability event occurs."
    ::= { cafServerEventPortEntry 1 }

cafServerDeadRemainAuthorized OBJECT-TYPE
    SYNTAX TruthValue
--    Rsyntax INTEGER {
--        true(1),
--        false(2)
--        }
    ACCESS read-write
    STATUS mandatory
    DESCRIPTION
        "This object specifies if current authorization will remain
        unchanged for the port when AAA Server Reachability event
        occurs.
        
        Setting 'true' on this object indicates that current
        authorization will remain unchanged for the port when AAA
        Server Reachability event occurs.
        
        The read-only value 'false' indicates that the current
        authorization will not be retained for the port when
        AAA Server Reachability event occurs."
    ::= { cafServerEventPortEntry 2 }

cafServerDeadAuthorizedVlan OBJECT-TYPE
    SYNTAX INTEGER(-1|0|1..2147483647)
    ACCESS read-write
    STATUS mandatory
    DESCRIPTION
        "This object specifies the AAA Server Reachability
        Authorized VLAN number.
        
        The read-only value of -1 indicates that this object is not
        applicable on this port.
        
        The read-only value of zero indicates that this port will not
        be authorized to any VLAN when AAA Server Reachability event
        occurs.
        
        Setting a non-zero value on this object indicates that this port
        will be authorized to the VLAN as specified by this object
        value, when AAA Server Reachability event occurs."
    ::= { cafServerEventPortEntry 3 }

cafServerAliveAction OBJECT-TYPE
    SYNTAX INTEGER {
        none(1),
        reinitialize(2)
        }
    ACCESS read-write
    STATUS mandatory
    DESCRIPTION
        "This object specifies the action applied to the port upon AAA
        recovery.
        
        none        : no action will be applied.
        reinitialize: the port will be reinitialized with the current
                     authentication method."
    ::= { cafServerEventPortEntry 4 }

cafSessionTable OBJECT-TYPE
    SYNTAX SEQUENCE OF CafSessionEntry
    ACCESS not-accessible
    STATUS mandatory
    DESCRIPTION
        "The table contains a list of authentication session.
        
        An entry is created when an authentication session has
        successfully created within Authentication Framework.
        
        An entry is deleted when an authentication session has been
        removed."
    ::= { ciscoAuthFrameworkSession 1 }

cafSessionEntry OBJECT-TYPE
    SYNTAX CafSessionEntry
    ACCESS not-accessible
    STATUS mandatory
    DESCRIPTION
        "Entry containing management information for a particular
        authentication session."
    INDEX { ifIndex, --?? IMPLIED may cause problems
            IMPLIED cafSessionId }
    ::= { cafSessionTable 1 }

CafSessionEntry ::= SEQUENCE {
    cafSessionId OCTET STRING,
    cafSessionClientMacAddress MacAddress,
    cafSessionClientAddrType InetAddressType,
    cafSessionClientAddress InetAddress,
    cafSessionStatus INTEGER,
    cafSessionDomain INTEGER,
    cafSessionAuthHostMode CiscoAuthHostMode,
    cafSessionControlledDirection CiscoAuthControlledDirections,
    cafSessionPostureToken CnnEouPostureTokenString,
    cafSessionAuthUserName SnmpAdminString,
    cafSessionClientFramedIpPool SnmpAdminString,
    cafSessionAuthorizedBy SnmpAdminString,
    cafSessionCriticalTimeLeft Gauge,
    cafSessionAuthVlan VlanIndexOrZero,
    cafSessionTimeout Gauge,
    cafSessionTimeLeft Gauge,
    cafSessionTimeoutAction INTEGER,
    cafSessionInactivityTimeout Gauge,
    cafSessionInactivityTimeLeft Gauge,
    cafSessionReauth TruthValue,
    cafSessionTerminate TruthValue,
    cafSessionVlanGroupName SnmpAdminString
    }

cafSessionId OBJECT-TYPE
    SYNTAX OCTET STRING(SIZE(1..64))
    ACCESS not-accessible
    STATUS mandatory
    DESCRIPTION
        "A unique identifier of the authentication session."
    ::= { cafSessionEntry 1 }

cafSessionClientMacAddress OBJECT-TYPE
    SYNTAX MacAddress
--    Rsyntax OCTET STRING(SIZE(6))
    ACCESS read-only
    STATUS mandatory
    DESCRIPTION
        "Indicates the MAC address of the device associates with the
        authentication session."
    ::= { cafSessionEntry 2 }

cafSessionClientAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "Indicates the type of Internet address of the client
        associates with the authentication session."
    ::= { cafSessionEntry 3 }

cafSessionClientAddress OBJECT-TYPE
    SYNTAX InetAddress
--    Rsyntax OCTET STRING(SIZE(0..255))
    ACCESS read-only
    STATUS mandatory
    DESCRIPTION
        "Indicates the Internet address of the client associates with
        the authentication session. The type of this address is
        determined by the value of cafSessionClientAddrType object."
    ::= { cafSessionEntry 4 }

cafSessionStatus OBJECT-TYPE
    SYNTAX INTEGER {
        idle(1),
        running(2),
        noMethod(3),
        authenticationSuccess(4),
        authenticationFailed(5),
        authorizationSuccess(6),
        authorizationFailed(7)
        }
    ACCESS read-only
    STATUS mandatory
    DESCRIPTION
        "Indicates the current status of the authentication session.
        
        idle        : the session has been initialized and no
                    method has run yet.
        
        running     : an authentication method is running for
                    this session.
        
        noMethod    : no authentication method has provided a
                    result for this session.
        
        authenticationSuccess: an authentication method has resulted
                    in authentication success for this session.
        
        authenticationFailed: an authentication method has resulted
                    in authentication failed for this session.
        
        authorizationSuccess: authorization is successful for this
                    session.
        
        authorizationFailed : authorization is failed for this
                    session."
    ::= { cafSessionEntry 5 }

cafSessionDomain OBJECT-TYPE
    SYNTAX INTEGER {
        other(1),
        data(2),
        voice(3)
        }
    ACCESS read-only
    STATUS mandatory
    DESCRIPTION
        "Indicates the type of domain that the authentication session
        belongs to.
        
        other  : none of the below.
        
        data : indicates the data domain.
        
        voice: indicates the voice domain."
    ::= { cafSessionEntry 6 }

cafSessionAuthHostMode OBJECT-TYPE
    SYNTAX CiscoAuthHostMode
--    Rsyntax INTEGER {
--        singleHost(1),
--        multiHost(2),
--        multiAuth(3),
--        multiDomain(4)
--        }
    ACCESS read-only
    STATUS mandatory
    DESCRIPTION
        "Indicates the authentication host mode of the port in the
        authentication session."
    ::= { cafSessionEntry 7 }

cafSessionControlledDirection OBJECT-TYPE
    SYNTAX CiscoAuthControlledDirections
--    Rsyntax INTEGER {
--        ?? enum value of zero may cause problems
--        both(0),
--        in(1)
--        }
    ACCESS read-only
    STATUS mandatory
    DESCRIPTION
        "Indicates the operational controlled directions parameter
        for this port in the authentication session."
    ::= { cafSessionEntry 8 }

cafSessionPostureToken OBJECT-TYPE
    SYNTAX CnnEouPostureTokenString
--    Rsyntax OCTET STRING(SIZE(0..255))
    ACCESS read-only
    STATUS mandatory
    DESCRIPTION
        "Indicates the posture token associates with the authentication
        session."
    ::= { cafSessionEntry 9 }

cafSessionAuthUserName OBJECT-TYPE
    SYNTAX SnmpAdminString
--    Rsyntax OCTET STRING(SIZE(0..255))
    ACCESS read-only
    STATUS mandatory
    DESCRIPTION
        "Indicates the name of the authenticated user for the
        authentication session."
    ::= { cafSessionEntry 10 }

cafSessionClientFramedIpPool OBJECT-TYPE
    SYNTAX SnmpAdminString
--    Rsyntax OCTET STRING(SIZE(0..255))
    ACCESS read-only
    STATUS mandatory
    DESCRIPTION
        "Indicates the name of the address pool from which the
        session's client IP address is assigned."
    ::= { cafSessionEntry 11 }

cafSessionAuthorizedBy OBJECT-TYPE
    SYNTAX SnmpAdminString
--    Rsyntax OCTET STRING(SIZE(0..255))
    ACCESS read-only
    STATUS mandatory
    DESCRIPTION
        "Indicates the name of the feature which authorizes the
        authentication session."
    ::= { cafSessionEntry 12 }

cafSessionCriticalTimeLeft OBJECT-TYPE
    SYNTAX Gauge
--  Units
--    seconds
    ACCESS read-only
    STATUS mandatory
    DESCRIPTION
        "Indicates the leftover time before the next authentication
        attempt for the authentication session after Server Reachability
        event occurred.  Value zero indicates that this session is
        currently being authenticated or it is not applicable."
    ::= { cafSessionEntry 13 }

cafSessionAuthVlan OBJECT-TYPE
    SYNTAX VlanIndexOrZero
--    Rsyntax INTEGER(0..4095)
    ACCESS read-only
    STATUS mandatory
    DESCRIPTION
        "Indicates the authorized VLAN applied to the authentication
        session. Value zero indicates that no authorized VLAN has been
        applied, or it is not applicable."
    ::= { cafSessionEntry 14 }

cafSessionTimeout OBJECT-TYPE
    SYNTAX Gauge
--  Units
--    seconds
    ACCESS read-only
    STATUS mandatory
    DESCRIPTION
        "Indicates the session timeout used by Authentication
        Framework in the authentication session."
    ::= { cafSessionEntry 15 }

cafSessionTimeLeft OBJECT-TYPE
    SYNTAX Gauge
--  Units
--    seconds
    ACCESS read-only
    STATUS mandatory
    DESCRIPTION
        "Indicates the leftover time of the current authentication
        session."
    ::= { cafSessionEntry 16 }

cafSessionTimeoutAction OBJECT-TYPE
    SYNTAX INTEGER {
        unknown(1),
        terminate(2),
        reauthenticate(3)
        }
    ACCESS read-only
    STATUS mandatory
    DESCRIPTION
        "Indicates the timeout action on the authentication session,
        when value of the corresponding instance of cafSessionTimeLeft
        reaches zero. 
        
         unknown       : None of the below.
        
         terminate     : Session will be terminated.
        
         reauthenticate: Session will be reauthenticated."
    ::= { cafSessionEntry 17 }

cafSessionInactivityTimeout OBJECT-TYPE
    SYNTAX Gauge
--  Units
--    seconds
    ACCESS read-only
    STATUS mandatory
    DESCRIPTION
        "Indicates the inactivity timeout used by Authentication
        Framework in the authentication session."
    ::= { cafSessionEntry 18 }

cafSessionInactivityTimeLeft OBJECT-TYPE
    SYNTAX Gauge
--  Units
--    seconds
    ACCESS read-only
    STATUS mandatory
    DESCRIPTION
        "Indicates the leftover time of the inactivity timer of
        the authentication session."
    ::= { cafSessionEntry 19 }

cafSessionReauth OBJECT-TYPE
    SYNTAX TruthValue
--    Rsyntax INTEGER {
--        true(1),
--        false(2)
--        }
    ACCESS read-write
    STATUS mandatory
    DESCRIPTION
        "The reauthentication control for the authentication session.
        Setting this object to 'true' cause the current authenticated
        session to reauthenticate the authenticated client. Setting
        this object to 'false' has no effect.
        
        This object always returns 'false' when being read."
    ::= { cafSessionEntry 20 }

cafSessionTerminate OBJECT-TYPE
    SYNTAX TruthValue
--    Rsyntax INTEGER {
--        true(1),
--        false(2)
--        }
    ACCESS read-write
    STATUS mandatory
    DESCRIPTION
        "The termination request control for the authentication session.
        Setting this object to 'true' terminates the current session.
        Setting this object to 'false' has no effect.
        
        This object always returns 'false' when being read."
    ::= { cafSessionEntry 21 }

cafSessionVlanGroupName OBJECT-TYPE
    SYNTAX SnmpAdminString
--    Rsyntax OCTET STRING(SIZE(0..255))
    ACCESS read-only
    STATUS mandatory
    DESCRIPTION
        "The name of the VLAN group that has been used during VLAN
        assignment for this session. 
        
        A zero length string indicates that there is no VLAN group been
        used during VLAN assignment."
    ::= { cafSessionEntry 22 }

cafSessionMethodsInfoTable OBJECT-TYPE
    SYNTAX SEQUENCE OF CafSessionMethodsInfoEntry
    ACCESS not-accessible
    STATUS mandatory
    DESCRIPTION
        "The table contains a list of authentication method for every
        authentication session.
        
        An entry exists for each authentication method that can
        authenticate an authentication session within
        Authentication Framework."
    ::= { ciscoAuthFrameworkSession 2 }

cafSessionMethodsInfoEntry OBJECT-TYPE
    SYNTAX CafSessionMethodsInfoEntry
    ACCESS not-accessible
    STATUS mandatory
    DESCRIPTION
        "Entry containing method information for a particular runnable
        authentication methods which is associated with a session for 
        an Authentication Framework managed port."
    INDEX { ifIndex, cafSessionId, cafSessionMethod }
    ::= { cafSessionMethodsInfoTable 1 }

CafSessionMethodsInfoEntry ::= SEQUENCE {
    cafSessionMethod CiscoAuthMethod,
    cafSessionMethodState INTEGER
    }

cafSessionMethod OBJECT-TYPE
    SYNTAX CiscoAuthMethod
--    Rsyntax INTEGER {
--        other(1),
--        dot1x(2),
--        macAuthBypass(3),
--        webAuth(4)
--        }
    ACCESS not-accessible
    STATUS mandatory
    DESCRIPTION
        "Indicates this authentication method."
    ::= { cafSessionMethodsInfoEntry 1 }

cafSessionMethodState OBJECT-TYPE
    SYNTAX INTEGER {
        notRun(1),
        running(2),
        failedOver(3),
        authcSuccess(4),
        authcFailed(5)
        }
    ACCESS read-only
    STATUS mandatory
    DESCRIPTION
        "Indicates the state of this authentication method.
        
        notRun      : The method has not run for this session.
        
        running     : The method is running for this session.
        
        failedOver  : The method has failed and the next method is
                    expected to provide a result.
        
        authcSuccess: The method has provided a successful
                     authentication result for this session.
        
        authcFailed : The method has provided a failed authentication
                     result for this session."
    ::= { cafSessionMethodsInfoEntry 2 }

cafSecurityViolationNotifEnable OBJECT-TYPE
    SYNTAX TruthValue
--    Rsyntax INTEGER {
--        true(1),
--        false(2)
--        }
    ACCESS read-write
    STATUS mandatory
    DESCRIPTION
        "This variable indicates whether the system produces
        the cafSecurityViolationNotif.
        
        A 'false' value will prevent cafSecurityViolationNotif 
        from being generated by this system."
    ::= { ciscoAuthFrwkNotifControl 1 }

cafAuthFailNotifEnable OBJECT-TYPE
    SYNTAX TruthValue
--    Rsyntax INTEGER {
--        true(1),
--        false(2)
--        }
    ACCESS read-write
    STATUS mandatory
    DESCRIPTION
        "This object specifies whether the system produces
        the cafAuthFailNotif.
        
        A 'true' value will cause cafAuthFailNotif to be generated by
        this system when an authentication failure happens.
        
        A 'false' value will prevent cafAuthFailNotif 
        from being generated by this system."
    ::= { ciscoAuthFrwkNotifControl 2 }

cafSecurityViolationNotif TRAP-TYPE
-- Reverse mappable trap
    ENTERPRISE ciscoAuthFrameworkMIB
    VARIABLES {
        ifIndex, ifName, cafSecurityViolationClient }
--  Status
--    mandatory
    DESCRIPTION
        "A cafSecurityViolationNotif is sent if a security violation
        is detected on a port, and the instance value of 
        cafSecurityViolationNotifEnable is 'true'."
    ::= 1

cafAuthFailNotif TRAP-TYPE
-- Reverse mappable trap
    ENTERPRISE ciscoAuthFrameworkMIB
    VARIABLES {
        ifName, cafAuthFailClient }
--  Status
--    mandatory
    DESCRIPTION
        "A cafAuthFailNotif is sent if an authentication failure is
        detected on a port, and the instance value of 
        cafAuthFailNotifEnable is 'true'.
        
        ifName contains the name of the interface where the
        authentication failure happened.
        
        cafAuthFailClient contains the mac address of the client which
        failed to authenticate."
    ::= 2

cafAuthMethodRegGroup OBJECT IDENTIFIER ::= { ciscoAuthFrameworkMIBGroups 1 }
-- OBJECT-GROUP
--  Status
--    mandatory
--  Descr
--    A collection of objects that provides registration
--    information of authentication methods in Authentication
--    Framework.
--  objects
--    cafAuthMethodDefaultPriority, cafAuthMethodDefaultExecOrder

cafAaaNoRespRecoveryDelayGroup OBJECT IDENTIFIER ::= { ciscoAuthFrameworkMIBGroups 2 }
-- OBJECT-GROUP
--  Status
--    mandatory
--  Descr
--    A collection of objects that provides AAA recovery delay
--    configuration for Authentication Framework in the system.
--  objects
--    cafAaaNoRespRecoveryDelay

cafAuthPortConfigGroup OBJECT IDENTIFIER ::= { ciscoAuthFrameworkMIBGroups 3 }
-- OBJECT-GROUP
--  Status
--    mandatory
--  Descr
--    A collection of objects that provides configuration of
--    Authentication Framework for capable ports in the system.
--  objects
--    cafPortControlledDirection, cafPortFallBackProfile, 
--    cafPortAuthHostMode, cafPortPreAuthOpenAccess, 
--    cafPortAuthorizeControl, cafPortReauthEnabled, 
--    cafPortReauthInterval, cafPortRestartInterval, 
--    cafPortInactivityTimeout, cafPortViolationAction

cafPortMethodGroup OBJECT IDENTIFIER ::= { ciscoAuthFrameworkMIBGroups 4 }
-- OBJECT-GROUP
--  Status
--    mandatory
--  Descr
--    A collection of objects that provides configuration and
--    information of authentication methods within Authentication
--    Framework for capable ports in the system.
--  objects
--    cafPortMethodAdminExecOrder, cafPortMethodAdminPriority, 
--    cafPortMethodAvailable, cafPortMethodOperExecOrder, 
--    cafPortMethodOperPriority

cafAuthFailedEventGroup OBJECT IDENTIFIER ::= { ciscoAuthFrameworkMIBGroups 5 }
-- OBJECT-GROUP
--  Status
--    mandatory
--  Descr
--    A collection of objects that provides configuration of
--    Auth-Failed behaviour of Authentication Framework for
--    ports in the system.
--  objects
--    cafAuthFailedMaxRetry, cafAuthFailedNoActionEnabled, 
--    cafAuthFailedAuthorizedVlan, cafAuthFailedNextMethodEnabled

cafClientNoRespEventGroup OBJECT IDENTIFIER ::= { ciscoAuthFrameworkMIBGroups 6 }
-- OBJECT-GROUP
--  Status
--    mandatory
--  Descr
--    A collection of objects that provides configuration of
--    Authentication Framework when no-responsive client is detected
--    on a port in the system.
--  objects
--    cafClientNoRespNoActionEnabled, cafClientNoRespAuthorizedVlan

cafServerEventGroup OBJECT IDENTIFIER ::= { ciscoAuthFrameworkMIBGroups 7 }
-- OBJECT-GROUP
--  Status
--    mandatory
--  Descr
--    A collection of objects that provides configuration of
--    Authentication Framework when AAA Server Reachability event
--    occurs.
--  objects
--    cafServerDeadNoActionEnabled, cafServerDeadRemainAuthorized, 
--    cafServerDeadAuthorizedVlan, cafServerAliveAction

cafSessionGroup OBJECT IDENTIFIER ::= { ciscoAuthFrameworkMIBGroups 8 }
-- OBJECT-GROUP
--  Status
--    mandatory
--  Descr
--    A collection of objects that provides authentication session
--    management information for Authentication Framework.
--  objects
--    cafSessionClientMacAddress, cafSessionClientAddrType, 
--    cafSessionClientAddress, cafSessionDomain, cafSessionStatus, 
--    cafSessionAuthHostMode, cafSessionControlledDirection, 
--    cafSessionPostureToken, cafSessionAuthUserName, 
--    cafSessionClientFramedIpPool, cafSessionAuthorizedBy, 
--    cafSessionCriticalTimeLeft, cafSessionAuthVlan, 
--    cafSessionTimeout, cafSessionTimeLeft, 
--    cafSessionTimeoutAction, cafSessionInactivityTimeout, 
--    cafSessionInactivityTimeLeft, cafSessionReauth, 
--    cafSessionTerminate

cafSessionMethodInfoGroup OBJECT IDENTIFIER ::= { ciscoAuthFrameworkMIBGroups 9 }
-- OBJECT-GROUP
--  Status
--    mandatory
--  Descr
--    A collection of objects that provides information about
--    authentication methods associate with Authentication Framework
--    's authentication sessions in the system.
--  objects
--    cafSessionMethodState

cafSecViolationNotifEnableGroup OBJECT IDENTIFIER ::= { ciscoAuthFrameworkMIBGroups 10 }
-- OBJECT-GROUP
--  Status
--    mandatory
--  Descr
--    A collection of objects that provides control over
--    security violation notification for Authentication
--    Framework in the system.
--  objects
--    cafSecurityViolationNotifEnable

cafSecurityViolationClientGroup OBJECT IDENTIFIER ::= { ciscoAuthFrameworkMIBGroups 12 }
-- OBJECT-GROUP
--  Status
--    mandatory
--  Descr
--    A collection of objects providing MAC address of the offending
--    client in the security violation notification.
--  objects
--    cafSecurityViolationClient

cafSessionVlanGroupNameGroup OBJECT IDENTIFIER ::= { ciscoAuthFrameworkMIBGroups 13 }
-- OBJECT-GROUP
--  Status
--    mandatory
--  Descr
--    A collection of objects providing VLAN group information of
--    authenticated session in Authentication Framework.
--  objects
--    cafSessionVlanGroupName

cafMacMoveConfigGroup OBJECT IDENTIFIER ::= { ciscoAuthFrameworkMIBGroups 14 }
-- OBJECT-GROUP
--  Status
--    mandatory
--  Descr
--    A collection of objects providing MAC move cofiguration
--    information for Authentication Framework on the device.
--  objects
--    cafMacMoveMode

cafCoACommandConfigGroup OBJECT IDENTIFIER ::= { ciscoAuthFrameworkMIBGroups 15 }
-- OBJECT-GROUP
--  Status
--    mandatory
--  Descr
--    A collection of objects providing configuration information
--    for the device's behaviour on CoA commands.
--  objects
--    cafCoABouncePortCommandIgnoreEnabled, 
--    cafCoADisablePortCommandIgnoreEnabled

cafAuthFailNotifEnableGroup OBJECT IDENTIFIER ::= { ciscoAuthFrameworkMIBGroups 17 }
-- OBJECT-GROUP
--  Status
--    mandatory
--  Descr
--    A collection of objects that provides control over
--    authentication failure notification for Authentication
--    Framework in the system.
--  objects
--    cafAuthFailNotifEnable

cafAuthFailClientGroup OBJECT IDENTIFIER ::= { ciscoAuthFrameworkMIBGroups 18 }
-- OBJECT-GROUP
--  Status
--    mandatory
--  Descr
--    A collection of objects providing MAC address of the failed
--    client in the authentication failure notification.
--  objects
--    cafAuthFailClient

cafSecurityViolationNotifGroup OBJECT IDENTIFIER ::= { ciscoAuthFrameworkMIBGroups 11 }
-- NOTIFICATION-GROUP
--  Status
--    mandatory
--  Descr
--    A collection of notification providing information
--    about port's security violation in Authentication
--    Framework.
--  notifications
--    cafSecurityViolationNotif

cafAuthFailNotifGroup OBJECT IDENTIFIER ::= { ciscoAuthFrameworkMIBGroups 16 }
-- NOTIFICATION-GROUP
--  Status
--    mandatory
--  Descr
--    A collection of notification providing information
--    about port's authentication failure in Authentication
--    Framework.
--  notifications
--    cafAuthFailNotif

ciscoAuthFrameworkMIBCompliance OBJECT IDENTIFIER ::= { ciscoAuthFrameworkMIBCompliances 1 }
-- MODULE-COMPLIANCE
--  Status
--    deprecated
--  Descr
--    The compliance statement for entities which implement
--    CISCO-AUTH-FRAMEWORK-MIB.
--  Module
--    >>current<<
--   MandGroup
--    cafAuthMethodRegGroup
--   MandGroup
--    cafAuthPortConfigGroup
--   MandGroup
--    cafPortMethodGroup
--   MandGroup
--    cafSessionGroup
--   MandGroup
--    cafSessionMethodInfoGroup
--   OptGroup
--    cafAaaNoRespRecoveryDelayGroup
--   OptGroup
--    cafAuthFailedEventGroup
--   OptGroup
--    cafClientNoRespEventGroup
--   OptGroup
--    cafServerEventGroup
--   OptGroup
--    cafSecViolationNotifEnableGroup
--   OptGroup
--    cafSecurityViolationNotifGroup
--   OptGroup
--    cafSecurityViolationClientGroup
--   ObjVar
--    cafAaaNoRespRecoveryDelay
--   ObjVar
--    cafPortControlledDirection
--   ObjVar
--    cafPortFallBackProfile
--   ObjVar
--    cafPortAuthHostMode
--   ObjVar
--    cafPortPreAuthOpenAccess
--   ObjVar
--    cafPortAuthorizeControl
--   ObjVar
--    cafPortReauthEnabled
--   ObjVar
--    cafPortReauthInterval
--   ObjVar
--    cafPortRestartInterval
--   ObjVar
--    cafPortInactivityTimeout
--   ObjVar
--    cafPortViolationAction
--   ObjVar
--    cafPortMethodAdminExecOrder
--   ObjVar
--    cafPortMethodAdminPriority
--   ObjVar
--    cafAuthFailedMaxRetry
--   ObjVar
--    cafAuthFailedNoActionEnabled
--   ObjVar
--    cafAuthFailedAuthorizedVlan
--   ObjVar
--    cafAuthFailedNextMethodEnabled
--   ObjVar
--    cafClientNoRespNoActionEnabled
--   ObjVar
--    cafClientNoRespAuthorizedVlan
--   ObjVar
--    cafServerDeadNoActionEnabled
--   ObjVar
--    cafServerDeadRemainAuthorized
--   ObjVar
--    cafServerDeadAuthorizedVlan
--   ObjVar
--    cafServerAliveAction
--   ObjVar
--    cafSessionReauth
--   ObjVar
--    cafSessionTerminate
--   ObjVar
--    cafSecurityViolationNotifEnable

ciscoAuthFrameworkMIBCompliance2 OBJECT IDENTIFIER ::= { ciscoAuthFrameworkMIBCompliances 2 }
-- MODULE-COMPLIANCE
--  Status
--    deprecated
--  Descr
--    The compliance statement for entities which implement
--    CISCO-AUTH-FRAMEWORK-MIB.
--  Module
--    >>current<<
--   MandGroup
--    cafAuthMethodRegGroup
--   MandGroup
--    cafAuthPortConfigGroup
--   MandGroup
--    cafPortMethodGroup
--   MandGroup
--    cafSessionGroup
--   MandGroup
--    cafSessionMethodInfoGroup
--   OptGroup
--    cafAaaNoRespRecoveryDelayGroup
--   OptGroup
--    cafAuthFailedEventGroup
--   OptGroup
--    cafClientNoRespEventGroup
--   OptGroup
--    cafServerEventGroup
--   OptGroup
--    cafSecViolationNotifEnableGroup
--   OptGroup
--    cafSecurityViolationNotifGroup
--   OptGroup
--    cafSecurityViolationClientGroup
--   OptGroup
--    cafSessionVlanGroupNameGroup
--   ObjVar
--    cafAaaNoRespRecoveryDelay
--   ObjVar
--    cafPortControlledDirection
--   ObjVar
--    cafPortFallBackProfile
--   ObjVar
--    cafPortAuthHostMode
--   ObjVar
--    cafPortPreAuthOpenAccess
--   ObjVar
--    cafPortAuthorizeControl
--   ObjVar
--    cafPortReauthEnabled
--   ObjVar
--    cafPortReauthInterval
--   ObjVar
--    cafPortRestartInterval
--   ObjVar
--    cafPortInactivityTimeout
--   ObjVar
--    cafPortViolationAction
--   ObjVar
--    cafPortMethodAdminExecOrder
--   ObjVar
--    cafPortMethodAdminPriority
--   ObjVar
--    cafAuthFailedMaxRetry
--   ObjVar
--    cafAuthFailedNoActionEnabled
--   ObjVar
--    cafAuthFailedAuthorizedVlan
--   ObjVar
--    cafAuthFailedNextMethodEnabled
--   ObjVar
--    cafClientNoRespNoActionEnabled
--   ObjVar
--    cafClientNoRespAuthorizedVlan
--   ObjVar
--    cafServerDeadNoActionEnabled
--   ObjVar
--    cafServerDeadRemainAuthorized
--   ObjVar
--    cafServerDeadAuthorizedVlan
--   ObjVar
--    cafServerAliveAction
--   ObjVar
--    cafSessionReauth
--   ObjVar
--    cafSessionTerminate
--   ObjVar
--    cafSecurityViolationNotifEnable

ciscoAuthFrameworkMIBCompliance3 OBJECT IDENTIFIER ::= { ciscoAuthFrameworkMIBCompliances 3 }
-- MODULE-COMPLIANCE
--  Status
--    deprecated
--  Descr
--    The compliance statement for entities which implement
--    CISCO-AUTH-FRAMEWORK-MIB.
--  Module
--    >>current<<
--   MandGroup
--    cafAuthMethodRegGroup
--   MandGroup
--    cafAuthPortConfigGroup
--   MandGroup
--    cafPortMethodGroup
--   MandGroup
--    cafSessionGroup
--   MandGroup
--    cafSessionMethodInfoGroup
--   OptGroup
--    cafAaaNoRespRecoveryDelayGroup
--   OptGroup
--    cafAuthFailedEventGroup
--   OptGroup
--    cafClientNoRespEventGroup
--   OptGroup
--    cafServerEventGroup
--   OptGroup
--    cafSecViolationNotifEnableGroup
--   OptGroup
--    cafSecurityViolationNotifGroup
--   OptGroup
--    cafSecurityViolationClientGroup
--   OptGroup
--    cafSessionVlanGroupNameGroup
--   OptGroup
--    cafMacMoveConfigGroup
--   OptGroup
--    cafCoACommandConfigGroup
--   ObjVar
--    cafAaaNoRespRecoveryDelay
--   ObjVar
--    cafPortControlledDirection
--   ObjVar
--    cafPortFallBackProfile
--   ObjVar
--    cafPortAuthHostMode
--   ObjVar
--    cafPortPreAuthOpenAccess
--   ObjVar
--    cafPortAuthorizeControl
--   ObjVar
--    cafPortReauthEnabled
--   ObjVar
--    cafPortReauthInterval
--   ObjVar
--    cafPortRestartInterval
--   ObjVar
--    cafPortInactivityTimeout
--   ObjVar
--    cafPortViolationAction
--   ObjVar
--    cafPortMethodAdminExecOrder
--   ObjVar
--    cafPortMethodAdminPriority
--   ObjVar
--    cafAuthFailedMaxRetry
--   ObjVar
--    cafAuthFailedNoActionEnabled
--   ObjVar
--    cafAuthFailedAuthorizedVlan
--   ObjVar
--    cafAuthFailedNextMethodEnabled
--   ObjVar
--    cafClientNoRespNoActionEnabled
--   ObjVar
--    cafClientNoRespAuthorizedVlan
--   ObjVar
--    cafServerDeadNoActionEnabled
--   ObjVar
--    cafServerDeadRemainAuthorized
--   ObjVar
--    cafServerDeadAuthorizedVlan
--   ObjVar
--    cafServerAliveAction
--   ObjVar
--    cafSessionReauth
--   ObjVar
--    cafSessionTerminate
--   ObjVar
--    cafSecurityViolationNotifEnable
--   ObjVar
--    cafMacMoveMode
--   ObjVar
--    cafCoABouncePortCommandIgnoreEnabled
--   ObjVar
--    cafCoADisablePortCommandIgnoreEnabled

ciscoAuthFrameworkMIBCompliance4 OBJECT IDENTIFIER ::= { ciscoAuthFrameworkMIBCompliances 4 }
-- MODULE-COMPLIANCE
--  Status
--    mandatory
--  Descr
--    The compliance statement for entities which implement
--    CISCO-AUTH-FRAMEWORK-MIB.
--  Module
--    >>current<<
--   MandGroup
--    cafAuthMethodRegGroup
--   MandGroup
--    cafAuthPortConfigGroup
--   MandGroup
--    cafPortMethodGroup
--   MandGroup
--    cafSessionGroup
--   MandGroup
--    cafSessionMethodInfoGroup
--   OptGroup
--    cafAaaNoRespRecoveryDelayGroup
--   OptGroup
--    cafAuthFailedEventGroup
--   OptGroup
--    cafClientNoRespEventGroup
--   OptGroup
--    cafServerEventGroup
--   OptGroup
--    cafSecViolationNotifEnableGroup
--   OptGroup
--    cafSecurityViolationNotifGroup
--   OptGroup
--    cafSecurityViolationClientGroup
--   OptGroup
--    cafSessionVlanGroupNameGroup
--   OptGroup
--    cafMacMoveConfigGroup
--   OptGroup
--    cafCoACommandConfigGroup
--   OptGroup
--    cafAuthFailNotifGroup
--   OptGroup
--    cafAuthFailNotifEnableGroup
--   OptGroup
--    cafAuthFailClientGroup
--   ObjVar
--    cafAaaNoRespRecoveryDelay
--   ObjVar
--    cafPortControlledDirection
--   ObjVar
--    cafPortFallBackProfile
--   ObjVar
--    cafPortAuthHostMode
--   ObjVar
--    cafPortPreAuthOpenAccess
--   ObjVar
--    cafPortAuthorizeControl
--   ObjVar
--    cafPortReauthEnabled
--   ObjVar
--    cafPortReauthInterval
--   ObjVar
--    cafPortRestartInterval
--   ObjVar
--    cafPortInactivityTimeout
--   ObjVar
--    cafPortViolationAction
--   ObjVar
--    cafPortMethodAdminExecOrder
--   ObjVar
--    cafPortMethodAdminPriority
--   ObjVar
--    cafAuthFailedMaxRetry
--   ObjVar
--    cafAuthFailedNoActionEnabled
--   ObjVar
--    cafAuthFailedAuthorizedVlan
--   ObjVar
--    cafAuthFailedNextMethodEnabled
--   ObjVar
--    cafClientNoRespNoActionEnabled
--   ObjVar
--    cafClientNoRespAuthorizedVlan
--   ObjVar
--    cafServerDeadNoActionEnabled
--   ObjVar
--    cafServerDeadRemainAuthorized
--   ObjVar
--    cafServerDeadAuthorizedVlan
--   ObjVar
--    cafServerAliveAction
--   ObjVar
--    cafSessionReauth
--   ObjVar
--    cafSessionTerminate
--   ObjVar
--    cafSecurityViolationNotifEnable
--   ObjVar
--    cafMacMoveMode
--   ObjVar
--    cafCoABouncePortCommandIgnoreEnabled
--   ObjVar
--    cafCoADisablePortCommandIgnoreEnabled


END
