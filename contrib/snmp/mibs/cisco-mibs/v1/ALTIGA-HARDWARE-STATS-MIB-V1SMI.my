-- MIB file created 25-Apr-2003 16:22:10, by
--   SMICng version 2.2.11-beta(PRO)(Solaris), January 20, 2001. Enterprise key cisco.com

ALTIGA-HARDWARE-STATS-MIB DEFINITIONS ::= BEGIN

-- From file: "ALTIGA-HARDWARE-STATS-MIB.my"
-- Compile options "4 7 F H N W 03 06 0B 0G 0N 0T"

IMPORTS
    DisplayString, TruthValue
            FROM SNMPv2-TC-v1
    alStatsHardware, alHardwareGroup
            FROM ALTIGA-MIB
    alHardwareMibModule
            FROM ALTIGA-GLOBAL-REG
    Counter, Gauge, TimeTicks
            FROM RFC1155-SMI
    OBJECT-TYPE
            FROM RFC-1212;

altigaHardwareStatsMibModule OBJECT IDENTIFIER ::= { alHardwareMibModule 2 }
-- MODULE-IDENTITY
--  LastUpdated
--    200303271300Z
--  OrgName
--    Cisco Systems, Inc.
--  ContactInfo
--    Cisco Systems 
--     170 W Tasman Drive 
--     San Jose, CA  95134 
--     USA 
--    
--     Tel: +1 800 553-NETS 
--     E-mail: cs-cvpn3000@cisco.com
--  Descr
--    The Altiga Hardware Statistics MIB models counters and objects that 
--     are of management interest for the hardware. 
--     
--     Acronyms 
--     The following acronyms are used in this document: 
--    
--       CPU:        Central Processing Unit 
--    
--       MB:         Megabyte 
--    
--       MIB:        Management Information Base 
--    
--       PS:         Power Supply 
--    
--       RPM:        Revolutions Per Minute 
--    
--       SEP:        Scalable Encryption Processor 
--    
--       WAN:        Wide Area Network 
--    
--  RevDate
--    200303271300Z
--  RevDescr
--    Added new emun to ConcentratorCard.
--  RevDate
--    200209051300Z
--  RevDescr
--    Added module compliance.
--  RevDate
--    200207100000Z
--  RevDescr
--    Updated with new header

alStatsHardwareGlobal OBJECT IDENTIFIER ::= { alStatsHardware 1 }
altigaHardwareStatsMibConformance OBJECT IDENTIFIER ::= { altigaHardwareStatsMibModule 1 }
altigaHardwareStatsMibCompliances OBJECT IDENTIFIER ::= { altigaHardwareStatsMibConformance 1 }

ConcentratorCard ::= INTEGER {
        none(1),
        sep(2),
        dualT1Wan(3),
        sepE(4)
        }
-- TEXTUAL-CONVENTION
--  Status
--    mandatory
--  Descr
--    Concentrator Card Type.

ConcentratorType ::= INTEGER {
        cxx(1),
        c5(2),
        c1(3)
        }
-- TEXTUAL-CONVENTION
--  Status
--    mandatory
--  Descr
--    Concentrator Type indicates the chassis type.

alHardwareCpuVoltage OBJECT-TYPE
    SYNTAX Gauge
--  Units
--    centivolts
    ACCESS read-only
    STATUS mandatory
    DESCRIPTION
        "The current CPU voltage in centivolts."
    ::= { alStatsHardwareGlobal 1 }

alHardwareCpuVoltageAlarm OBJECT-TYPE
    SYNTAX TruthValue
--    Rsyntax INTEGER {
--        true(1),
--        false(2)
--        }
    ACCESS read-only
    STATUS mandatory
    DESCRIPTION
        "The alarm status for CPU voltage.  This alarm will fired when the CPU 
         voltage is detected out of configured range."
    ::= { alStatsHardwareGlobal 2 }

alHardwareCpuVoltageCount OBJECT-TYPE
    SYNTAX Counter
    ACCESS read-only
    STATUS mandatory
    DESCRIPTION
        "The number of alarm events for CPU voltage."
    ::= { alStatsHardwareGlobal 3 }

alHardwareCpuVoltageTime OBJECT-TYPE
    SYNTAX TimeTicks
    ACCESS read-only
    STATUS mandatory
    DESCRIPTION
        "The sysUptime at the time of the last change of alarm status for CPU 
         voltage."
    ::= { alStatsHardwareGlobal 4 }

alHardwarePs1Voltage3v OBJECT-TYPE
    SYNTAX Gauge
--  Units
--    centivolts
    ACCESS read-only
    STATUS mandatory
    DESCRIPTION
        "The current 3V voltage of Power Supply 1 in centivolts."
    ::= { alStatsHardwareGlobal 5 }

alHardwarePs1Voltage3vAlarm OBJECT-TYPE
    SYNTAX TruthValue
--    Rsyntax INTEGER {
--        true(1),
--        false(2)
--        }
    ACCESS read-only
    STATUS mandatory
    DESCRIPTION
        "The alarm status for PS1 3v voltage.  This alarm will fired when the 
         3v power supply 1 voltage is detected out of configured range."
    ::= { alStatsHardwareGlobal 6 }

alHardwarePs1Voltage3vCount OBJECT-TYPE
    SYNTAX Counter
    ACCESS read-only
    STATUS mandatory
    DESCRIPTION
        "The number of alarm events for PS1 3v voltage."
    ::= { alStatsHardwareGlobal 7 }

alHardwarePs1Voltage3vTime OBJECT-TYPE
    SYNTAX TimeTicks
    ACCESS read-only
    STATUS mandatory
    DESCRIPTION
        "The sysUptime at the time of the last change of alarm status for PS1  
         3v voltage."
    ::= { alStatsHardwareGlobal 8 }

alHardwarePs1Voltage5v OBJECT-TYPE
    SYNTAX Gauge
--  Units
--    centivolts
    ACCESS read-only
    STATUS mandatory
    DESCRIPTION
        "The current 5V voltage of Power Supply 1 in centivolts."
    ::= { alStatsHardwareGlobal 9 }

alHardwarePs1Voltage5vAlarm OBJECT-TYPE
    SYNTAX TruthValue
--    Rsyntax INTEGER {
--        true(1),
--        false(2)
--        }
    ACCESS read-only
    STATUS mandatory
    DESCRIPTION
        "The alarm status for PS1 5v voltage.  This alarm will fired when the 
         5v power supply 1 voltage is detected out of configured range."
    ::= { alStatsHardwareGlobal 10 }

alHardwarePs1Voltage5vCount OBJECT-TYPE
    SYNTAX Counter
    ACCESS read-only
    STATUS mandatory
    DESCRIPTION
        "The number of alarm events for PS1 5v voltage."
    ::= { alStatsHardwareGlobal 11 }

alHardwarePs1Voltage5vTime OBJECT-TYPE
    SYNTAX TimeTicks
    ACCESS read-only
    STATUS mandatory
    DESCRIPTION
        "The sysUptime at the time of the last change of alarm status for PS1 
         5v voltage."
    ::= { alStatsHardwareGlobal 12 }

alHardwarePs2Voltage3v OBJECT-TYPE
    SYNTAX Gauge
--  Units
--    centivolts
    ACCESS read-only
    STATUS mandatory
    DESCRIPTION
        "The current 3V voltage of Power Supply 2 in centivolts."
    ::= { alStatsHardwareGlobal 13 }

alHardwarePs2Voltage3vAlarm OBJECT-TYPE
    SYNTAX TruthValue
--    Rsyntax INTEGER {
--        true(1),
--        false(2)
--        }
    ACCESS read-only
    STATUS mandatory
    DESCRIPTION
        "The alarm status for PS2 3v voltage.  This alarm will fired when the 
         3v power supply 2 voltage is detected out of configured range."
    ::= { alStatsHardwareGlobal 14 }

alHardwarePs2Voltage3vCount OBJECT-TYPE
    SYNTAX Counter
    ACCESS read-only
    STATUS mandatory
    DESCRIPTION
        "The number of alarm events for PS2 3v voltage."
    ::= { alStatsHardwareGlobal 15 }

alHardwarePs2Voltage3vTime OBJECT-TYPE
    SYNTAX TimeTicks
    ACCESS read-only
    STATUS mandatory
    DESCRIPTION
        "The sysUptime at the time of the last change of alarm status for PS2 
         3v voltage."
    ::= { alStatsHardwareGlobal 16 }

alHardwarePs2Voltage5v OBJECT-TYPE
    SYNTAX Gauge
--  Units
--    centivolts
    ACCESS read-only
    STATUS mandatory
    DESCRIPTION
        "The current 5V voltage of Power Supply 2 in centivolts."
    ::= { alStatsHardwareGlobal 17 }

alHardwarePs2Voltage5vAlarm OBJECT-TYPE
    SYNTAX TruthValue
--    Rsyntax INTEGER {
--        true(1),
--        false(2)
--        }
    ACCESS read-only
    STATUS mandatory
    DESCRIPTION
        "The alarm status for PS2 5v voltage.  This alarm will fired when the 
         5v power supply 2 voltage is detected out of configured range."
    ::= { alStatsHardwareGlobal 18 }

alHardwarePs2Voltage5vCount OBJECT-TYPE
    SYNTAX Counter
    ACCESS read-only
    STATUS mandatory
    DESCRIPTION
        "The number of alarm events for PS2 5v voltage."
    ::= { alStatsHardwareGlobal 19 }

alHardwarePs2Voltage5vTime OBJECT-TYPE
    SYNTAX TimeTicks
    ACCESS read-only
    STATUS mandatory
    DESCRIPTION
        "The sysUptime at the time of the last change of alarm status for PS2 
         5v voltage."
    ::= { alStatsHardwareGlobal 20 }

alHardwareBoardVoltage3v OBJECT-TYPE
    SYNTAX Gauge
--  Units
--    centivolts
    ACCESS read-only
    STATUS mandatory
    DESCRIPTION
        "The current 3V voltage of the mainboard in centivolts."
    ::= { alStatsHardwareGlobal 21 }

alHardwareBoardVoltage3vAlarm OBJECT-TYPE
    SYNTAX TruthValue
--    Rsyntax INTEGER {
--        true(1),
--        false(2)
--        }
    ACCESS read-only
    STATUS mandatory
    DESCRIPTION
        "The alarm status for the mainboard 3v voltage.  This alarm will fired 
         when the 3v mainboard voltage is detected out of configured range."
    ::= { alStatsHardwareGlobal 22 }

alHardwareBoardVoltage3vCount OBJECT-TYPE
    SYNTAX Counter
    ACCESS read-only
    STATUS mandatory
    DESCRIPTION
        "The number of alarm events for the mainboard 3v voltage."
    ::= { alStatsHardwareGlobal 23 }

alHardwareBoardVoltage3vTime OBJECT-TYPE
    SYNTAX TimeTicks
    ACCESS read-only
    STATUS mandatory
    DESCRIPTION
        "The sysUptime at the time of the last change of alarm status for the 
         mainboard 3v voltage."
    ::= { alStatsHardwareGlobal 24 }

alHardwareBoardVoltage5v OBJECT-TYPE
    SYNTAX Gauge
--  Units
--    centivolts
    ACCESS read-only
    STATUS mandatory
    DESCRIPTION
        "The current 5V voltage of the mainboard in centivolts."
    ::= { alStatsHardwareGlobal 25 }

alHardwareBoardVoltage5vAlarm OBJECT-TYPE
    SYNTAX TruthValue
--    Rsyntax INTEGER {
--        true(1),
--        false(2)
--        }
    ACCESS read-only
    STATUS mandatory
    DESCRIPTION
        "The alarm status for the mainboard 5v voltage.  This alarm will fired 
         when the 5v mainboard voltage is detected out of configured range."
    ::= { alStatsHardwareGlobal 26 }

alHardwareBoardVoltage5vCount OBJECT-TYPE
    SYNTAX Counter
    ACCESS read-only
    STATUS mandatory
    DESCRIPTION
        "The number of alarm events for the mainboard 5v voltage."
    ::= { alStatsHardwareGlobal 27 }

alHardwareBoardVoltage5vTime OBJECT-TYPE
    SYNTAX TimeTicks
    ACCESS read-only
    STATUS mandatory
    DESCRIPTION
        "The sysUptime at the time of the last change of alarm status for the 
         mainboard 5v voltage."
    ::= { alStatsHardwareGlobal 28 }

alHardwareCpuTemp OBJECT-TYPE
    SYNTAX INTEGER(-40..120)
--  Units
--    degrees Celsius
    ACCESS read-only
    STATUS mandatory
    DESCRIPTION
        "The current CPU temperature in degrees C."
    ::= { alStatsHardwareGlobal 29 }

alHardwareCpuTempAlarm OBJECT-TYPE
    SYNTAX TruthValue
--    Rsyntax INTEGER {
--        true(1),
--        false(2)
--        }
    ACCESS read-only
    STATUS mandatory
    DESCRIPTION
        "The alarm status for the CPU temperature.  This alarm will fired 
         when the CPU temperature is detected out of configured range."
    ::= { alStatsHardwareGlobal 30 }

alHardwareCpuTempCount OBJECT-TYPE
    SYNTAX Counter
    ACCESS read-only
    STATUS mandatory
    DESCRIPTION
        "The number of alarm events for the CPU temperature."
    ::= { alStatsHardwareGlobal 31 }

alHardwareCpuTempTime OBJECT-TYPE
    SYNTAX TimeTicks
    ACCESS read-only
    STATUS mandatory
    DESCRIPTION
        "The sysUptime at the time of the last change of alarm status for the 
         CPU temperature."
    ::= { alStatsHardwareGlobal 32 }

alHardwareCageTemp OBJECT-TYPE
    SYNTAX INTEGER(-40..120)
--  Units
--    degrees Celsius
    ACCESS read-only
    STATUS mandatory
    DESCRIPTION
        "The current cage temperature in degrees C."
    ::= { alStatsHardwareGlobal 33 }

alHardwareCageTempAlarm OBJECT-TYPE
    SYNTAX TruthValue
--    Rsyntax INTEGER {
--        true(1),
--        false(2)
--        }
    ACCESS read-only
    STATUS mandatory
    DESCRIPTION
        "The alarm status for the cage temperature.  This alarm will fired 
         when the cage temperature is detected out of configured range."
    ::= { alStatsHardwareGlobal 34 }

alHardwareCageTempCount OBJECT-TYPE
    SYNTAX Counter
    ACCESS read-only
    STATUS mandatory
    DESCRIPTION
        "The number of alarm events for the cage temperature."
    ::= { alStatsHardwareGlobal 35 }

alHardwareCageTempTime OBJECT-TYPE
    SYNTAX TimeTicks
    ACCESS read-only
    STATUS mandatory
    DESCRIPTION
        "The sysUptime at the time of the last change of alarm status for the 
         cage temperature."
    ::= { alStatsHardwareGlobal 36 }

alHardwareFan1Rpm OBJECT-TYPE
    SYNTAX Gauge
--  Units
--    RPM
    ACCESS read-only
    STATUS mandatory
    DESCRIPTION
        "The current speed of fan 1 in RPM."
    ::= { alStatsHardwareGlobal 37 }

alHardwareFan1RpmAlarm OBJECT-TYPE
    SYNTAX TruthValue
--    Rsyntax INTEGER {
--        true(1),
--        false(2)
--        }
    ACCESS read-only
    STATUS mandatory
    DESCRIPTION
        "The alarm status for fan 1 RPM.  This alarm will fired when fan 1 RPM 
         is detected out of configured range."
    ::= { alStatsHardwareGlobal 38 }

alHardwareFan1RpmCount OBJECT-TYPE
    SYNTAX Counter
    ACCESS read-only
    STATUS mandatory
    DESCRIPTION
        "The number of alarm events for fan 1 RPM."
    ::= { alStatsHardwareGlobal 39 }

alHardwareFan1RpmTime OBJECT-TYPE
    SYNTAX TimeTicks
    ACCESS read-only
    STATUS mandatory
    DESCRIPTION
        "The sysUptime at the time of the last change of alarm status for 
         fan 1 RPM."
    ::= { alStatsHardwareGlobal 40 }

alHardwareFan2Rpm OBJECT-TYPE
    SYNTAX Gauge
--  Units
--    RPM
    ACCESS read-only
    STATUS mandatory
    DESCRIPTION
        "The current speed of fan 2 in RPM."
    ::= { alStatsHardwareGlobal 41 }

alHardwareFan2RpmAlarm OBJECT-TYPE
    SYNTAX TruthValue
--    Rsyntax INTEGER {
--        true(1),
--        false(2)
--        }
    ACCESS read-only
    STATUS mandatory
    DESCRIPTION
        "The alarm status for fan 2 RPM.  This alarm will fired when fan 2 RPM 
         is detected out of configured range."
    ::= { alStatsHardwareGlobal 42 }

alHardwareFan2RpmCount OBJECT-TYPE
    SYNTAX Counter
    ACCESS read-only
    STATUS mandatory
    DESCRIPTION
        "The number of alarm events for fan 2 RPM."
    ::= { alStatsHardwareGlobal 43 }

alHardwareFan2RpmTime OBJECT-TYPE
    SYNTAX TimeTicks
    ACCESS read-only
    STATUS mandatory
    DESCRIPTION
        "The sysUptime at the time of the last change of alarm status for 
         fan 2 RPM."
    ::= { alStatsHardwareGlobal 44 }

alHardwareFan3Rpm OBJECT-TYPE
    SYNTAX Gauge
--  Units
--    RPM
    ACCESS read-only
    STATUS mandatory
    DESCRIPTION
        "The current speed of fan 3 in RPM."
    ::= { alStatsHardwareGlobal 45 }

alHardwareFan3RpmAlarm OBJECT-TYPE
    SYNTAX TruthValue
--    Rsyntax INTEGER {
--        true(1),
--        false(2)
--        }
    ACCESS read-only
    STATUS mandatory
    DESCRIPTION
        "The alarm status for fan 3 RPM.  This alarm will fired when fan 3 RPM 
         is detected out of configured range."
    ::= { alStatsHardwareGlobal 46 }

alHardwareFan3RpmCount OBJECT-TYPE
    SYNTAX Counter
    ACCESS read-only
    STATUS mandatory
    DESCRIPTION
        "The number of alarm events for fan 3 RPM."
    ::= { alStatsHardwareGlobal 47 }

alHardwareFan3RpmTime OBJECT-TYPE
    SYNTAX TimeTicks
    ACCESS read-only
    STATUS mandatory
    DESCRIPTION
        "The sysUptime at the time of the last change of alarm status for 
         fan 3 RPM."
    ::= { alStatsHardwareGlobal 48 }

alHardwarePs1Type OBJECT-TYPE
    SYNTAX INTEGER {
        none(1),
        ac(2)
        }
    ACCESS read-only
    STATUS mandatory
    DESCRIPTION
        "The type of power supply for Power Supply slot 1."
    ::= { alStatsHardwareGlobal 49 }

alHardwarePs2Type OBJECT-TYPE
    SYNTAX INTEGER {
        none(1),
        ac(2)
        }
    ACCESS read-only
    STATUS mandatory
    DESCRIPTION
        "The type of power supply for Power Supply slot 2."
    ::= { alStatsHardwareGlobal 50 }

alHardwareSlot1Card OBJECT-TYPE
    SYNTAX ConcentratorCard
--    Rsyntax INTEGER {
--        none(1),
--        sep(2),
--        dualT1Wan(3),
--        sepE(4)
--        }
    ACCESS read-only
    STATUS mandatory
    DESCRIPTION
        "The type of card in slot 1."
    ::= { alStatsHardwareGlobal 51 }

alHardwareSlot2Card OBJECT-TYPE
    SYNTAX ConcentratorCard
--    Rsyntax INTEGER {
--        none(1),
--        sep(2),
--        dualT1Wan(3),
--        sepE(4)
--        }
    ACCESS read-only
    STATUS mandatory
    DESCRIPTION
        "The type of card in slot 2."
    ::= { alStatsHardwareGlobal 52 }

alHardwareSlot3Card OBJECT-TYPE
    SYNTAX ConcentratorCard
--    Rsyntax INTEGER {
--        none(1),
--        sep(2),
--        dualT1Wan(3),
--        sepE(4)
--        }
    ACCESS read-only
    STATUS mandatory
    DESCRIPTION
        "The type of card in slot 3."
    ::= { alStatsHardwareGlobal 53 }

alHardwareSlot4Card OBJECT-TYPE
    SYNTAX ConcentratorCard
--    Rsyntax INTEGER {
--        none(1),
--        sep(2),
--        dualT1Wan(3),
--        sepE(4)
--        }
    ACCESS read-only
    STATUS mandatory
    DESCRIPTION
        "The type of card in slot 4."
    ::= { alStatsHardwareGlobal 54 }

alHardwareSlot1Operational OBJECT-TYPE
    SYNTAX TruthValue
--    Rsyntax INTEGER {
--        true(1),
--        false(2)
--        }
    ACCESS read-only
    STATUS mandatory
    DESCRIPTION
        "The operational status of card in slot 1."
    ::= { alStatsHardwareGlobal 55 }

alHardwareSlot2Operational OBJECT-TYPE
    SYNTAX TruthValue
--    Rsyntax INTEGER {
--        true(1),
--        false(2)
--        }
    ACCESS read-only
    STATUS mandatory
    DESCRIPTION
        "The operational status of card in slot 2."
    ::= { alStatsHardwareGlobal 56 }

alHardwareSlot3Operational OBJECT-TYPE
    SYNTAX TruthValue
--    Rsyntax INTEGER {
--        true(1),
--        false(2)
--        }
    ACCESS read-only
    STATUS mandatory
    DESCRIPTION
        "The operational status of card in slot 3."
    ::= { alStatsHardwareGlobal 57 }

alHardwareSlot4Operational OBJECT-TYPE
    SYNTAX TruthValue
--    Rsyntax INTEGER {
--        true(1),
--        false(2)
--        }
    ACCESS read-only
    STATUS mandatory
    DESCRIPTION
        "The operational status of card in slot 4."
    ::= { alStatsHardwareGlobal 58 }

alHardwareRamSize OBJECT-TYPE
    SYNTAX Gauge
--  Units
--    MB
    ACCESS read-only
    STATUS mandatory
    DESCRIPTION
        "The amount of memory, in MB on the concentrator."
    ::= { alStatsHardwareGlobal 59 }

alHardwareChassis OBJECT-TYPE
    SYNTAX ConcentratorType
--    Rsyntax INTEGER {
--        cxx(1),
--        c5(2),
--        c1(3)
--        }
    ACCESS read-only
    STATUS mandatory
    DESCRIPTION
        "The type of VPN Concentrator this is."
    ::= { alStatsHardwareGlobal 60 }

alHardwareCpuVoltageNominal OBJECT-TYPE
    SYNTAX Gauge
--  Units
--    centivolts
    ACCESS read-only
    STATUS mandatory
    DESCRIPTION
        "The nominal CPU voltage in centivolts for the concentrator."
    ::= { alStatsHardwareGlobal 61 }

alHardwareClientEthPrivSwitch OBJECT-TYPE
    SYNTAX TruthValue
--    Rsyntax INTEGER {
--        true(1),
--        false(2)
--        }
    ACCESS read-only
    STATUS mandatory
    DESCRIPTION
        "Whether or not the 3002 Hardware Client has an Ethernet Switch for 
         the private interface."
    ::= { alStatsHardwareGlobal 62 }

alHardwareSerialNumber OBJECT-TYPE
    SYNTAX DisplayString
--    Rsyntax OCTET STRING(SIZE(0..255))
    ACCESS read-only
    STATUS mandatory
    DESCRIPTION
        "Unit serial number."
    ::= { alStatsHardwareGlobal 63 }

altigaHardwareStatsGroup OBJECT IDENTIFIER ::= { alHardwareGroup 2 }
-- OBJECT-GROUP
--  Status
--    mandatory
--  Descr
--    The objects for Hardware statistics.
--  objects
--    alHardwareCpuVoltage, alHardwareCpuVoltageAlarm, 
--    alHardwareCpuVoltageCount, alHardwareCpuVoltageTime, 
--    alHardwarePs1Voltage3v, alHardwarePs1Voltage3vAlarm, 
--    alHardwarePs1Voltage3vCount, alHardwarePs1Voltage3vTime, 
--    alHardwarePs1Voltage5v, alHardwarePs1Voltage5vAlarm, 
--    alHardwarePs1Voltage5vCount, alHardwarePs1Voltage5vTime, 
--    alHardwarePs2Voltage3v, alHardwarePs2Voltage3vAlarm, 
--    alHardwarePs2Voltage3vCount, alHardwarePs2Voltage3vTime, 
--    alHardwarePs2Voltage5v, alHardwarePs2Voltage5vAlarm, 
--    alHardwarePs2Voltage5vCount, alHardwarePs2Voltage5vTime, 
--    alHardwareBoardVoltage3v, alHardwareBoardVoltage3vAlarm, 
--    alHardwareBoardVoltage3vCount, alHardwareBoardVoltage3vTime, 
--    alHardwareBoardVoltage5v, alHardwareBoardVoltage5vAlarm, 
--    alHardwareBoardVoltage5vCount, alHardwareBoardVoltage5vTime, 
--    alHardwareCpuTemp, alHardwareCpuTempAlarm, 
--    alHardwareCpuTempCount, alHardwareCpuTempTime, 
--    alHardwareCageTemp, alHardwareCageTempAlarm, 
--    alHardwareCageTempCount, alHardwareCageTempTime, 
--    alHardwareFan1Rpm, alHardwareFan1RpmAlarm, 
--    alHardwareFan1RpmCount, alHardwareFan1RpmTime, 
--    alHardwareFan2Rpm, alHardwareFan2RpmAlarm, 
--    alHardwareFan2RpmCount, alHardwareFan2RpmTime, 
--    alHardwareFan3Rpm, alHardwareFan3RpmAlarm, 
--    alHardwareFan3RpmCount, alHardwareFan3RpmTime, 
--    alHardwarePs1Type, alHardwarePs2Type, alHardwareSlot1Card, 
--    alHardwareSlot2Card, alHardwareSlot3Card, alHardwareSlot4Card, 
--    alHardwareSlot1Operational, alHardwareSlot2Operational, 
--    alHardwareSlot3Operational, alHardwareSlot4Operational, 
--    alHardwareRamSize, alHardwareChassis, 
--    alHardwareCpuVoltageNominal, alHardwareClientEthPrivSwitch, 
--    alHardwareSerialNumber

altigaHardwareStatsMibCompliance OBJECT IDENTIFIER ::= { altigaHardwareStatsMibCompliances 1 }
-- MODULE-COMPLIANCE
--  Status
--    mandatory
--  Descr
--    The compliance statement for agents which  
--     implement the Altiga Hardware Statistics MIB.
--  Module
--    >>current<<
--   MandGroup
--    altigaHardwareStatsGroup


END
