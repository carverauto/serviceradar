-- MIB file created 22-Apr-2003 14:21:38, by
--   SMICng version 2.2.11-beta(PRO)(Solaris), January 20, 2001. Enterprise key cisco.com

CISCO-MGX82XX-ENVMON-MIB DEFINITIONS ::= BEGIN

-- From file: "CISCO-MGX82XX-ENVMON-MIB.my"
-- Compile options "4 7 F H N W 03 06 0B 0G 0N 0T"

IMPORTS
    basisAsm
            FROM BASIS-MIB
    ciscoWan
            FROM CISCOWAN-SMI
    OBJECT-TYPE
            FROM RFC-1212;

ciscoMgx82xxEnvmonMIB OBJECT IDENTIFIER ::= { ciscoWan 70 }
-- MODULE-IDENTITY
--  LastUpdated
--    200304170000Z
--  OrgName
--    Cisco Systems, Inc.
--  ContactInfo
--           Cisco Systems
--            Customer Service
--    
--    Postal: 170 W Tasman Drive
--            San Jose, CA  95134
--            USA
--    
--            Tel: +1 800 553-NETS
--    
--    E-mail: cs-wanatm@cisco.com
--  Descr
--    The MIB module to describe the status of the 
--    Environmental Monitoring devices in
--    MGX82xx products.
--  RevDate
--    200304170000Z
--  RevDescr
--    Initial version of the MIB.
--    
--    The content of this MIB was originally available
--    in CISCO-WAN-AXIPOP-MIB defined using SMIv1.
--    The applicable objects from CISCO-WAN-AXIPOP-MIB
--    are defined using SMIv2 in this MIB. Also the
--    descriptions of some of the objects have been 
--    modified.

cmEnvmonMIBConformance OBJECT IDENTIFIER ::= { ciscoMgx82xxEnvmonMIB 2 }
cmEnvmonMIBGroups OBJECT IDENTIFIER ::= { cmEnvmonMIBConformance 1 }
cmEnvmonMIBCompliances OBJECT IDENTIFIER ::= { cmEnvmonMIBConformance 2 }

asmAlarmTable OBJECT-TYPE
    SYNTAX SEQUENCE OF AsmAlarmEntry
    ACCESS not-accessible
    STATUS mandatory
    DESCRIPTION
        "The ASM Alarm table. The table size is
        given by the value of ASMNumOfValidEntries."
    ::= { basisAsm 1 }

asmAlarmEntry OBJECT-TYPE
    SYNTAX AsmAlarmEntry
    ACCESS not-accessible
    STATUS mandatory
    DESCRIPTION
        "An entry in the Basis ASM Alarm Table."
    INDEX { asmAlarmNum }
    ::= { asmAlarmTable 1 }

AsmAlarmEntry ::= SEQUENCE {
    asmAlarmNum INTEGER,
    asmAlarmType INTEGER,
    asmAlarmUnitNum INTEGER,
    asmAlarmThreshold INTEGER,
    asmAlarmSeverity INTEGER,
    asmUnitMeasurable INTEGER,
    asmUnitMeasuredValue INTEGER,
    asmPhysicalAlarmState INTEGER,
    asmClrButton INTEGER
    }

asmAlarmNum OBJECT-TYPE
    SYNTAX INTEGER(1..100)
    ACCESS read-only
    STATUS mandatory
    DESCRIPTION
        "This object is the identifier of a ASM alarm
        entry. The Alarm is further identified by the 
        objects ASMAlarmType & ASMAlarmUnitNum."
    ::= { asmAlarmEntry 1 }

asmAlarmType OBJECT-TYPE
    SYNTAX INTEGER {
        alarmOther(1),
        alarmTemperature(2),
        alarmPSU(3),
        alarmDCLevel(4),
        alarmFanUnit(5)
        }
    ACCESS read-only
    STATUS mandatory
    DESCRIPTION
        "The value for this object indicates the type
        of device for which alarm is applicable.
        
        The possible values are :
        
         alarmOther      (1) : Other than specified below
         alarmTemperature(2) : Temperature sensor
         alarmPSU        (3) : Power Supply Unit
         alarmDCLevel    (4) : DC Level Sensor
         alarmFanUnit    (5) : FAN speed sensor."
    ::= { asmAlarmEntry 2 }

asmAlarmUnitNum OBJECT-TYPE
    SYNTAX INTEGER(1..16)
    ACCESS read-only
    STATUS mandatory
    DESCRIPTION
        "This object identifies one unit among a number of
        identical units represented in this table having the
        same asmAlarmType."
    ::= { asmAlarmEntry 3 }

asmAlarmThreshold OBJECT-TYPE
    SYNTAX INTEGER(1..2147483647)
    ACCESS read-only
    STATUS mandatory
    DESCRIPTION
        "This object specifies the threshold beyond which
        the alarmable unit is said to be in an abnormal state."
    ::= { asmAlarmEntry 4 }

asmAlarmSeverity OBJECT-TYPE
    SYNTAX INTEGER {
        alarmMinor(1),
        alarmMajor(2)
        }
    ACCESS read-only
    STATUS mandatory
    DESCRIPTION
        "This variable specifies the severity of the alarm
        to be declared when the asmAlarmThreshold specified is
        exceeded."
    ::= { asmAlarmEntry 5 }

asmUnitMeasurable OBJECT-TYPE
    SYNTAX INTEGER {
        no(1),
        yes(2)
        }
    ACCESS read-only
    STATUS mandatory
    DESCRIPTION
        "This object indicates if the alarm unit is measurable
        by the switch/system."
    ::= { asmAlarmEntry 6 }

asmUnitMeasuredValue OBJECT-TYPE
    SYNTAX INTEGER(0..2147483647)
    ACCESS read-only
    STATUS mandatory
    DESCRIPTION
        "This object gives the measured value of the entity
        addressed by asmAlarmNum. The value in this object
        is valid only if asmUnitMeasurable is set to 'yes'.
        This object contains value zero for asmUnitMeasurable
        value of 'no'."
    ::= { asmAlarmEntry 7 }

asmPhysicalAlarmState OBJECT-TYPE
    SYNTAX INTEGER(0..2147483647)
    ACCESS read-only
    STATUS mandatory
    DESCRIPTION
        "This object indicates the status of the ASM alarm
        represented in this entry. It is a bitmap where a
        set bit indicates an abnormal condition. A reset bit
        signifies normal operation."
    ::= { asmAlarmEntry 8 }

asmClrButton OBJECT-TYPE
    SYNTAX INTEGER {
        asmAlarmNoAction(1),
        asmAlarmClear(2)
        }
    ACCESS read-write
    STATUS mandatory
    DESCRIPTION
        "This object when set to asmAlarmClear(2),causes the
        alarm to be cleared."
    ::= { asmAlarmEntry 9 }

asmNumOfValidEntries OBJECT-TYPE
    SYNTAX INTEGER(0..100)
    ACCESS read-only
    STATUS mandatory
    DESCRIPTION
        "The number of valid asmAlarmTable entries (regardless
        of how many are actually configured) in the table."
    ::= { basisAsm 2 }

asmShelfAlarmState OBJECT-TYPE
    SYNTAX INTEGER {
        alarmOff(1),
        alarmOn(2)
        }
    ACCESS read-only
    STATUS mandatory
    DESCRIPTION
        "This object indicates whether any Shelf/Node Alarm has been 
        declared in the system."
    ::= { basisAsm 3 }

cmEnvmonInfoGroup OBJECT IDENTIFIER ::= { cmEnvmonMIBGroups 1 }
-- OBJECT-GROUP
--  Status
--    mandatory
--  Descr
--    The collection of objects which are used for
--    providing information on environmental monitoring
--    devices.
--  objects
--    asmAlarmNum, asmAlarmType, asmAlarmUnitNum, asmAlarmThreshold, 
--    asmAlarmSeverity, asmUnitMeasurable, asmUnitMeasuredValue, 
--    asmPhysicalAlarmState, asmClrButton

cmEnvmonGeneralGroup OBJECT IDENTIFIER ::= { cmEnvmonMIBGroups 2 }
-- OBJECT-GROUP
--  Status
--    mandatory
--  Descr
--    The collection of objects which are used for
--    providing information on shelf level objects
--    related to environmental monitoring devices.
--  objects
--    asmNumOfValidEntries, asmShelfAlarmState

cmEnvmonCompliance OBJECT IDENTIFIER ::= { cmEnvmonMIBCompliances 1 }
-- MODULE-COMPLIANCE
--  Status
--    mandatory
--  Descr
--    The compliance statement for objects related
--    to MGX82xx Environmental monitoring MIB.
--  Module
--    >>current<<
--   MandGroup
--    cmEnvmonInfoGroup
--   MandGroup
--    cmEnvmonGeneralGroup


END
