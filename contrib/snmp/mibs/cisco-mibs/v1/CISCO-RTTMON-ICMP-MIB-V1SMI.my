-- MIB file created 02-Dec-2005 11:38:59, by
--   SMICng version 2.2.11-beta(PRO)(Solaris), January 20, 2001. Enterprise key cisco.com

CISCO-RTTMON-ICMP-MIB DEFINITIONS ::= BEGIN

-- From file: "CISCO-RTTMON-ICMP-MIB.my"
-- Compile options "4 7 F H N O W 03 06 0B 0G 0N 0T"

IMPORTS
    TimeStamp
            FROM SNMPv2-TC-v1
    rttMonLatestOper, rttMonCtrlAdminIndex, rttMonStats
            FROM CISCO-RTTMON-MIB
    RttResponseSense
            FROM CISCO-RTTMON-TC-MIB
    ciscoMgmt
            FROM CISCO-SMI
    Counter, Gauge
            FROM RFC1155-SMI
    OBJECT-TYPE
            FROM RFC-1212;

ciscoRttMonIcmpMIB OBJECT IDENTIFIER ::= { ciscoMgmt 486 }
-- MODULE-IDENTITY
--  LastUpdated
--    200508090000Z
--  OrgName
--    Cisco Systems, Inc.
--  ContactInfo
--    Cisco Systems, Inc.
--    Customer Service 
--    
--    Postal: 170 W Tasman Drive
--    San Jose, CA 95134
--    
--    Tel: +1 800 553 NETS
--    Email: cs-ipsla@cisco.com
--  Descr
--    An extension to the CISCO-RTTMON-MIB for ICMP 
--     operations. The ICMP Jitter operation provides capability 
--     to measure metrics such as RTT (Round Trip Time), Jitter, 
--     packet loss, one-way latency by sending ICMP TIMESTAMP 
--     stream to the destination devices.
--  RevDate
--    200508090000Z
--  RevDescr
--    Initial version of this MIB module.

ciscoRttMonIcmpMIBNotifs OBJECT IDENTIFIER ::= { ciscoRttMonIcmpMIB 0 }
ciscoRttMonIcmpMIBObjects OBJECT IDENTIFIER ::= { ciscoRttMonIcmpMIB 1 }
ciscoRttMonIcmpMIBConform OBJECT IDENTIFIER ::= { ciscoRttMonIcmpMIB 2 }
ciscoRttMonIcmpCompliances OBJECT IDENTIFIER ::= { ciscoRttMonIcmpMIBConform 1 }
ciscoRttMonIcmpMIBGroups OBJECT IDENTIFIER ::= { ciscoRttMonIcmpMIBConform 2 }

rttMonLatestIcmpJitterOperTable OBJECT-TYPE
    SYNTAX SEQUENCE OF RttMonLatestIcmpJitterOperEntry
    ACCESS not-accessible
    STATUS mandatory
    DESCRIPTION
        "A table which contains the status of latest ICMP Jitter 
        operation.
        
        Each conceptual row corresponds to a ICMP jitter probe 
        defined in rttMonCtrlAdminTable and has same index as
        rttMonCtrlAdminTable. 
        
        An entry in this table is created only if the 
        rttMonCtrlAdminRttType is 'icmpJitter', the 
        rttMonEchoAdminProtocol is 'icmpJitterAppl' and valid 
        rttMonEchoAdminTargetAddress is configured. The entry will 
        start to collect data when rttMonCtrlAdminStatus from 
        rttMonCtrlAdminStatus is in 'active' state. The entry 
        will be removed when the rttMonCtrlAdminStatus is in 
        'destroy' state."
    REFERENCE
        "rttMonCtrlAdminTable           from CISCO-RTTMON-MIB
         rttMonEchoAdminProtocol        from CISCO-RTTMON-MIB
         rttMonCtrlAdminRttType         from CISCO-RTTMON-MIB
         rttMonEchoAdminTargetAddress   from CISCO-RTTMON-MIB"
    ::= { rttMonLatestOper 4 }

rttMonLatestIcmpJitterOperEntry OBJECT-TYPE
    SYNTAX RttMonLatestIcmpJitterOperEntry
    ACCESS not-accessible
    STATUS mandatory
    DESCRIPTION
        "A list of objects that record the latest
        ICMP jitter operation."
    INDEX { rttMonCtrlAdminIndex }
    ::= { rttMonLatestIcmpJitterOperTable 1 }

RttMonLatestIcmpJitterOperEntry ::= SEQUENCE {
    rttMonLatestIcmpJitterNumRTT Gauge,
    rttMonLatestIcmpJitterRTTSum Gauge,
    rttMonLatestIcmpJitterRTTSum2 Gauge,
    rttMonLatestIcmpJitterRTTMin Gauge,
    rttMonLatestIcmpJitterRTTMax Gauge,
    rttMonLatestIcmpJitterMinPosSD Gauge,
    rttMonLatestIcmpJitterMaxPosSD Gauge,
    rttMonLatestIcmpJitterNumPosSD Gauge,
    rttMonLatestIcmpJitterSumPosSD Gauge,
    rttMonLatestIcmpJitterSum2PosSD Gauge,
    rttMonLatestIcmpJitterMinNegSD Gauge,
    rttMonLatestIcmpJitterMaxNegSD Gauge,
    rttMonLatestIcmpJitterNumNegSD Gauge,
    rttMonLatestIcmpJitterSumNegSD Gauge,
    rttMonLatestIcmpJitterSum2NegSD Gauge,
    rttMonLatestIcmpJitterMinPosDS Gauge,
    rttMonLatestIcmpJitterMaxPosDS Gauge,
    rttMonLatestIcmpJitterNumPosDS Gauge,
    rttMonLatestIcmpJitterSumPosDS Gauge,
    rttMonLatestIcmpJitterSum2PosDS Gauge,
    rttMonLatestIcmpJitterMinNegDS Gauge,
    rttMonLatestIcmpJitterMaxNegDS Gauge,
    rttMonLatestIcmpJitterNumNegDS Gauge,
    rttMonLatestIcmpJitterSumNegDS Gauge,
    rttMonLatestIcmpJitterSum2NegDS Gauge,
    rttMonLatestIcmpJitterPktLoss Gauge,
    rttMonLatestIcmpJPktOutSeqBoth Gauge,
    rttMonLatestIcmpJPktOutSeqSD Gauge,
    rttMonLatestIcmpJPktOutSeqDS Gauge,
    rttMonLatestIcmpJitterPktSkipped Gauge,
    rttMonLatestIcmpJitterSense RttResponseSense,
    rttMonLatestIcmpJitterPktLateA Gauge,
    rttMonLatestIcmpJitterMinSucPktL Gauge,
    rttMonLatestIcmpJitterMaxSucPktL Gauge,
    rttMonLatestIcmpJitterOWSumSD Gauge,
    rttMonLatestIcmpJitterOWSum2SD Gauge,
    rttMonLatestIcmpJitterOWMinSD Gauge,
    rttMonLatestIcmpJitterOWMaxSD Gauge,
    rttMonLatestIcmpJitterOWSumDS Gauge,
    rttMonLatestIcmpJitterOWSum2DS Gauge,
    rttMonLatestIcmpJitterOWMinDS Gauge,
    rttMonLatestIcmpJitterOWMaxDS Gauge,
    rttMonLatestIcmpJitterNumOW Gauge,
    rttMonLatestIcmpJitterAvgJitter Gauge,
    rttMonLatestIcmpJitterAvgSDJ Gauge,
    rttMonLatestIcmpJitterAvgDSJ Gauge,
    rttMonLatestIcmpJitterOWAvgSD Gauge,
    rttMonLatestIcmpJitterOWAvgDS Gauge,
    rttMonLatestIcmpJitterIAJOut Gauge,
    rttMonLatestIcmpJitterIAJIn Gauge
    }

rttMonLatestIcmpJitterNumRTT OBJECT-TYPE
    SYNTAX Gauge
--  Units
--    packets
    ACCESS read-only
    STATUS mandatory
    DESCRIPTION
        "The number of RTT's that were successfully measured."
    ::= { rttMonLatestIcmpJitterOperEntry 1 }

rttMonLatestIcmpJitterRTTSum OBJECT-TYPE
    SYNTAX Gauge
--  Units
--    milliseconds
    ACCESS read-only
    STATUS mandatory
    DESCRIPTION
        "The sum of RTT's that are successfully measured.
        The number of successfully measured RTT is 
        stored in rttMonLatestIcmpJitterNumRTT."
    ::= { rttMonLatestIcmpJitterOperEntry 2 }

rttMonLatestIcmpJitterRTTSum2 OBJECT-TYPE
    SYNTAX Gauge
--  Units
--    milliseconds
    ACCESS read-only
    STATUS mandatory
    DESCRIPTION
        "The sum of squares of RTT's that are successfully measured."
    ::= { rttMonLatestIcmpJitterOperEntry 3 }

rttMonLatestIcmpJitterRTTMin OBJECT-TYPE
    SYNTAX Gauge
--  Units
--    milliseconds
    ACCESS read-only
    STATUS mandatory
    DESCRIPTION
        "The minimum of RTT's that were successfully measured."
    ::= { rttMonLatestIcmpJitterOperEntry 4 }

rttMonLatestIcmpJitterRTTMax OBJECT-TYPE
    SYNTAX Gauge
--  Units
--    milliseconds
    ACCESS read-only
    STATUS mandatory
    DESCRIPTION
        "The maximum of RTT's that were successfully measured."
    ::= { rttMonLatestIcmpJitterOperEntry 5 }

rttMonLatestIcmpJitterMinPosSD OBJECT-TYPE
    SYNTAX Gauge
--  Units
--    milliseconds
    ACCESS read-only
    STATUS mandatory
    DESCRIPTION
        "The minimum of all positive jitter values for packets sent
        from source to destination."
    ::= { rttMonLatestIcmpJitterOperEntry 6 }

rttMonLatestIcmpJitterMaxPosSD OBJECT-TYPE
    SYNTAX Gauge
--  Units
--    milliseconds
    ACCESS read-only
    STATUS mandatory
    DESCRIPTION
        "The maximum of all positive jitter values for packets sent
        from source to destination."
    ::= { rttMonLatestIcmpJitterOperEntry 7 }

rttMonLatestIcmpJitterNumPosSD OBJECT-TYPE
    SYNTAX Gauge
--  Units
--    occurrences
    ACCESS read-only
    STATUS mandatory
    DESCRIPTION
        "The number of all positive jitter values for packets
        sent from source to destination."
    ::= { rttMonLatestIcmpJitterOperEntry 8 }

rttMonLatestIcmpJitterSumPosSD OBJECT-TYPE
    SYNTAX Gauge
--  Units
--    milliseconds
    ACCESS read-only
    STATUS mandatory
    DESCRIPTION
        "The sum of all positive jitter values for packets sent
         source to destination. The number of such values
        is stored in rttMonLatestIcmpJitterNumPosSD."
    ::= { rttMonLatestIcmpJitterOperEntry 9 }

rttMonLatestIcmpJitterSum2PosSD OBJECT-TYPE
    SYNTAX Gauge
--  Units
--    milliseconds
    ACCESS read-only
    STATUS mandatory
    DESCRIPTION
        "The sum of square of all positive jitter values for
        packets sent from source to destination."
    ::= { rttMonLatestIcmpJitterOperEntry 10 }

rttMonLatestIcmpJitterMinNegSD OBJECT-TYPE
    SYNTAX Gauge
--  Units
--    milliseconds
    ACCESS read-only
    STATUS mandatory
    DESCRIPTION
        "The minimum of absolute values of all negative jitter values
        for packets sent from source to destination."
    ::= { rttMonLatestIcmpJitterOperEntry 11 }

rttMonLatestIcmpJitterMaxNegSD OBJECT-TYPE
    SYNTAX Gauge
--  Units
--    milliseconds
    ACCESS read-only
    STATUS mandatory
    DESCRIPTION
        "The maximum of absolute values of all negative jitter values
        for packets sent from source to destination."
    ::= { rttMonLatestIcmpJitterOperEntry 12 }

rttMonLatestIcmpJitterNumNegSD OBJECT-TYPE
    SYNTAX Gauge
--  Units
--    occurrences
    ACCESS read-only
    STATUS mandatory
    DESCRIPTION
        "The number of all negative jitter values for packets
        sent from source to destination."
    ::= { rttMonLatestIcmpJitterOperEntry 13 }

rttMonLatestIcmpJitterSumNegSD OBJECT-TYPE
    SYNTAX Gauge
--  Units
--    milliseconds
    ACCESS read-only
    STATUS mandatory
    DESCRIPTION
        "The sum of all negative jitter values for packets sent
        from source to destination. The number of such values
        is stored in rttMonLatestIcmpJitterNumNegSD."
    ::= { rttMonLatestIcmpJitterOperEntry 14 }

rttMonLatestIcmpJitterSum2NegSD OBJECT-TYPE
    SYNTAX Gauge
--  Units
--    milliseconds
    ACCESS read-only
    STATUS mandatory
    DESCRIPTION
        "The sum of square of all negative jitter values for
        packets sent from source to destination."
    ::= { rttMonLatestIcmpJitterOperEntry 15 }

rttMonLatestIcmpJitterMinPosDS OBJECT-TYPE
    SYNTAX Gauge
--  Units
--    milliseconds
    ACCESS read-only
    STATUS mandatory
    DESCRIPTION
        "The minimum of all positive jitter values for packets sent
        from destination to source."
    ::= { rttMonLatestIcmpJitterOperEntry 16 }

rttMonLatestIcmpJitterMaxPosDS OBJECT-TYPE
    SYNTAX Gauge
--  Units
--    milliseconds
    ACCESS read-only
    STATUS mandatory
    DESCRIPTION
        "The maximum of all positive jitter values for packets sent
        from destination to source."
    ::= { rttMonLatestIcmpJitterOperEntry 17 }

rttMonLatestIcmpJitterNumPosDS OBJECT-TYPE
    SYNTAX Gauge
--  Units
--    occurrences
    ACCESS read-only
    STATUS mandatory
    DESCRIPTION
        "The number of all positive jitter values for packets
        sent from destination to source."
    ::= { rttMonLatestIcmpJitterOperEntry 18 }

rttMonLatestIcmpJitterSumPosDS OBJECT-TYPE
    SYNTAX Gauge
--  Units
--    milliseconds
    ACCESS read-only
    STATUS mandatory
    DESCRIPTION
        "The sum of all positive jitter values for packets sent
        from destination to source. The number of such values
        is stored in rttMonLatestIcmpJitterNumPosDS."
    ::= { rttMonLatestIcmpJitterOperEntry 19 }

rttMonLatestIcmpJitterSum2PosDS OBJECT-TYPE
    SYNTAX Gauge
--  Units
--    milliseconds
    ACCESS read-only
    STATUS mandatory
    DESCRIPTION
        "The sum of squares of all positive jitter values for
        packets sent from destination to source."
    ::= { rttMonLatestIcmpJitterOperEntry 20 }

rttMonLatestIcmpJitterMinNegDS OBJECT-TYPE
    SYNTAX Gauge
--  Units
--    milliseconds
    ACCESS read-only
    STATUS mandatory
    DESCRIPTION
        "The minimum of all negative jitter values for packets sent
        from destination to source."
    ::= { rttMonLatestIcmpJitterOperEntry 21 }

rttMonLatestIcmpJitterMaxNegDS OBJECT-TYPE
    SYNTAX Gauge
--  Units
--    milliseconds
    ACCESS read-only
    STATUS mandatory
    DESCRIPTION
        "The maximum of all negative jitter values for packets sent
        from destination to source."
    ::= { rttMonLatestIcmpJitterOperEntry 22 }

rttMonLatestIcmpJitterNumNegDS OBJECT-TYPE
    SYNTAX Gauge
--  Units
--    occurrences
    ACCESS read-only
    STATUS mandatory
    DESCRIPTION
        "The number of all negative jitter values for packets
        sent from destination to source."
    ::= { rttMonLatestIcmpJitterOperEntry 23 }

rttMonLatestIcmpJitterSumNegDS OBJECT-TYPE
    SYNTAX Gauge
--  Units
--    milliseconds
    ACCESS read-only
    STATUS mandatory
    DESCRIPTION
        "The sum of all negative jitter values for packets sent
        from destination to source. The number of such values
        is stored in rttMonLatestIcmpJitterNumNegDS."
    ::= { rttMonLatestIcmpJitterOperEntry 24 }

rttMonLatestIcmpJitterSum2NegDS OBJECT-TYPE
    SYNTAX Gauge
--  Units
--    milliseconds
    ACCESS read-only
    STATUS mandatory
    DESCRIPTION
        "The sum of squares of all negative jitter values for
         packets sent from destination to source."
    ::= { rttMonLatestIcmpJitterOperEntry 25 }

rttMonLatestIcmpJitterPktLoss OBJECT-TYPE
    SYNTAX Gauge
--  Units
--    packets
    ACCESS read-only
    STATUS mandatory
    DESCRIPTION
        "The number of packets lost."
    ::= { rttMonLatestIcmpJitterOperEntry 26 }

rttMonLatestIcmpJPktOutSeqBoth OBJECT-TYPE
    SYNTAX Gauge
--  Units
--    packets
    ACCESS read-only
    STATUS mandatory
    DESCRIPTION
        "The number of packets arrived out of sequence in both
        source-to-destination and destination-to-source direction."
    ::= { rttMonLatestIcmpJitterOperEntry 27 }

rttMonLatestIcmpJPktOutSeqSD OBJECT-TYPE
    SYNTAX Gauge
--  Units
--    packets
    ACCESS read-only
    STATUS mandatory
    DESCRIPTION
        "The number of packets arrived out of sequence in the 
        direction of source-to-destination."
    ::= { rttMonLatestIcmpJitterOperEntry 28 }

rttMonLatestIcmpJPktOutSeqDS OBJECT-TYPE
    SYNTAX Gauge
--  Units
--    packets
    ACCESS read-only
    STATUS mandatory
    DESCRIPTION
        "The number of packets arrived out of sequence in the
        direction of destination-to-source."
    ::= { rttMonLatestIcmpJitterOperEntry 29 }

rttMonLatestIcmpJitterPktSkipped OBJECT-TYPE
    SYNTAX Gauge
--  Units
--    packets
    ACCESS read-only
    STATUS mandatory
    DESCRIPTION
        "The number of packets in the operation that could not be 
         initiated due to an internal error."
    ::= { rttMonLatestIcmpJitterOperEntry 30 }

rttMonLatestIcmpJitterSense OBJECT-TYPE
    SYNTAX RttResponseSense
--    Rsyntax INTEGER {
--        ?? enum value of zero may cause problems
--        other(0),
--        ok(1),
--        disconnected(2),
--        overThreshold(3),
--        timeout(4),
--        busy(5),
--        notConnected(6),
--        dropped(7),
--        sequenceError(8),
--        verifyError(9),
--        applicationSpecific(10),
--        dnsServerTimeout(11),
--        tcpConnectTimeout(12),
--        httpTransactionTimeout(13),
--        dnsQueryError(14),
--        httpError(15),
--        error(16),
--        mplsLspEchoTxError(17),
--        mplsLspUnreachable(18),
--        mplsLspMalformedReq(19),
--        mplsLspReachButNotFEC(20)
--        }
    ACCESS read-only
    STATUS mandatory
    DESCRIPTION
        "An application specific sense code for the completion status."
    ::= { rttMonLatestIcmpJitterOperEntry 31 }

rttMonLatestIcmpJitterPktLateA OBJECT-TYPE
    SYNTAX Gauge
--  Units
--    packets
    ACCESS read-only
    STATUS mandatory
    DESCRIPTION
        "The number of packets that arrived after the timeout."
    ::= { rttMonLatestIcmpJitterOperEntry 32 }

rttMonLatestIcmpJitterMinSucPktL OBJECT-TYPE
    SYNTAX Gauge
--  Units
--    packets
    ACCESS read-only
    STATUS mandatory
    DESCRIPTION
        "The minimum number of packets that are dropped
         successively."
    ::= { rttMonLatestIcmpJitterOperEntry 33 }

rttMonLatestIcmpJitterMaxSucPktL OBJECT-TYPE
    SYNTAX Gauge
--  Units
--    packets
    ACCESS read-only
    STATUS mandatory
    DESCRIPTION
        "The maximum number of packets that are dropped
         successively."
    ::= { rttMonLatestIcmpJitterOperEntry 34 }

rttMonLatestIcmpJitterOWSumSD OBJECT-TYPE
    SYNTAX Gauge
--  Units
--    milliseconds
    ACCESS read-only
    STATUS mandatory
    DESCRIPTION
        "The sum of one way trip time from source to destination."
    ::= { rttMonLatestIcmpJitterOperEntry 35 }

rttMonLatestIcmpJitterOWSum2SD OBJECT-TYPE
    SYNTAX Gauge
--  Units
--    milliseconds
    ACCESS read-only
    STATUS mandatory
    DESCRIPTION
        "The sum of squares of one way trip time from source to
        destination."
    ::= { rttMonLatestIcmpJitterOperEntry 36 }

rttMonLatestIcmpJitterOWMinSD OBJECT-TYPE
    SYNTAX Gauge
--  Units
--    milliseconds
    ACCESS read-only
    STATUS mandatory
    DESCRIPTION
        "The minimum of all one way trip time from 
        source to destination."
    ::= { rttMonLatestIcmpJitterOperEntry 37 }

rttMonLatestIcmpJitterOWMaxSD OBJECT-TYPE
    SYNTAX Gauge
--  Units
--    milliseconds
    ACCESS read-only
    STATUS mandatory
    DESCRIPTION
        "The maximum of all one way trip time from 
        source to destination."
    ::= { rttMonLatestIcmpJitterOperEntry 38 }

rttMonLatestIcmpJitterOWSumDS OBJECT-TYPE
    SYNTAX Gauge
--  Units
--    milliseconds
    ACCESS read-only
    STATUS mandatory
    DESCRIPTION
        "The sum of one way trip time from destination to source."
    ::= { rttMonLatestIcmpJitterOperEntry 39 }

rttMonLatestIcmpJitterOWSum2DS OBJECT-TYPE
    SYNTAX Gauge
--  Units
--    milliseconds
    ACCESS read-only
    STATUS mandatory
    DESCRIPTION
        "The sum of squares of one way trip time from 
        destination to source."
    ::= { rttMonLatestIcmpJitterOperEntry 40 }

rttMonLatestIcmpJitterOWMinDS OBJECT-TYPE
    SYNTAX Gauge
--  Units
--    milliseconds
    ACCESS read-only
    STATUS mandatory
    DESCRIPTION
        "The minimum of all one way trip time from 
        destination to source."
    ::= { rttMonLatestIcmpJitterOperEntry 41 }

rttMonLatestIcmpJitterOWMaxDS OBJECT-TYPE
    SYNTAX Gauge
--  Units
--    milliseconds
    ACCESS read-only
    STATUS mandatory
    DESCRIPTION
        "The maximum of all one way trip time from 
        destination to source."
    ::= { rttMonLatestIcmpJitterOperEntry 42 }

rttMonLatestIcmpJitterNumOW OBJECT-TYPE
    SYNTAX Gauge
--  Units
--    packets
    ACCESS read-only
    STATUS mandatory
    DESCRIPTION
        "The number of successful one way trip time measurements."
    ::= { rttMonLatestIcmpJitterOperEntry 43 }

rttMonLatestIcmpJitterAvgJitter OBJECT-TYPE
    SYNTAX Gauge
--  Units
--    milliseconds
    ACCESS read-only
    STATUS mandatory
    DESCRIPTION
        "The average of positive and negative jitter values
        in Source-to-Destionation and Destination-to-Source
        direction."
    ::= { rttMonLatestIcmpJitterOperEntry 44 }

rttMonLatestIcmpJitterAvgSDJ OBJECT-TYPE
    SYNTAX Gauge
--  Units
--    milliseconds
    ACCESS read-only
    STATUS mandatory
    DESCRIPTION
        "The average of positive and negative jitter values
         from source to destination."
    ::= { rttMonLatestIcmpJitterOperEntry 45 }

rttMonLatestIcmpJitterAvgDSJ OBJECT-TYPE
    SYNTAX Gauge
--  Units
--    milliseconds
    ACCESS read-only
    STATUS mandatory
    DESCRIPTION
        "The average of positive and negative jitter values
         from destination to source."
    ::= { rttMonLatestIcmpJitterOperEntry 46 }

rttMonLatestIcmpJitterOWAvgSD OBJECT-TYPE
    SYNTAX Gauge
--  Units
--    milliseconds
    ACCESS read-only
    STATUS mandatory
    DESCRIPTION
        "The average one way trip time from source to destination."
    ::= { rttMonLatestIcmpJitterOperEntry 47 }

rttMonLatestIcmpJitterOWAvgDS OBJECT-TYPE
    SYNTAX Gauge
--  Units
--    milliseconds
    ACCESS read-only
    STATUS mandatory
    DESCRIPTION
        "The average one way trip time from destination to source."
    ::= { rttMonLatestIcmpJitterOperEntry 48 }

rttMonLatestIcmpJitterIAJOut OBJECT-TYPE
    SYNTAX Gauge
--  Units
--    milliseconds
    ACCESS read-only
    STATUS mandatory
    DESCRIPTION
        "Inter-arrival jitter (RFC 1889) at responder."
    REFERENCE
        "Refer to the following documents for the definition: 
        RFC 1889, Section 6.3.1"
    ::= { rttMonLatestIcmpJitterOperEntry 49 }

rttMonLatestIcmpJitterIAJIn OBJECT-TYPE
    SYNTAX Gauge
--  Units
--    milliseconds
    ACCESS read-only
    STATUS mandatory
    DESCRIPTION
        "Inter-arrival jitter (RFC 1889) at source."
    REFERENCE
        "Refer to the following documents for the definition: 
        RFC 1889, Section 6.3.1"
    ::= { rttMonLatestIcmpJitterOperEntry 50 }

rttMonIcmpJitterStatsTable OBJECT-TYPE
    SYNTAX SEQUENCE OF RttMonIcmpJitterStatsEntry
    ACCESS not-accessible
    STATUS mandatory
    DESCRIPTION
        "The ICMP Jitter statistics table contains summarized 
        information of the results for a conceptual RTT control 
        row. A rolling accumulated history of this information 
        is maintained in a series of hourly 'group(s)'.
        
        When rttMonIcmpJitterStatsStartTimeId groups exceeds 
        the rttMonStatisticsAdminNumHourGroups value, the 
        oldest corresponding hourly group will be deleted and will 
        be replaced with the new rttMonIcmpJitterStatsStartTimeId 
        hourly group.
        
        The table is created only if the rttMonCtrlAdminRttType
        is 'icmpJitter' and the rttMonEchoAdminProtocol is 
        'icmpJitterAppl'. It will be removed when the corresponding 
        conceptual RTT control row is destroyed."
    ::= { rttMonStats 8 }

rttMonIcmpJitterStatsEntry OBJECT-TYPE
    SYNTAX RttMonIcmpJitterStatsEntry
    ACCESS not-accessible
    STATUS mandatory
    DESCRIPTION
        "An entry in ICMP jitter stats table. Each entry contains the 
         objects which accumulate the results of a series of RTT 
         operations over a 60 minute time period or a time period 
         stored in rttMonScheduleAdminRttLife, whichever is smaller."
    INDEX { rttMonCtrlAdminIndex, rttMonIcmpJitterStatsStartTimeId }
    ::= { rttMonIcmpJitterStatsTable 1 }

RttMonIcmpJitterStatsEntry ::= SEQUENCE {
    rttMonIcmpJitterStatsStartTimeId TimeStamp,
    rttMonIcmpJitterStatsCompletions Counter,
    rttMonIcmpJStatsOverThresholds Counter,
    rttMonIcmpJitterStatsNumRTTs Counter,
    rttMonIcmpJitterStatsRTTSums Counter,
    rttMonIcmpJStatsRTTSum2Lows Counter,
    rttMonIcmpJStatsRTTSum2Highs Counter,
    rttMonIcmpJitterStatsRTTMin Gauge,
    rttMonIcmpJitterStatsRTTMax Gauge,
    rttMonIcmpJitterStatsMinPosSD Gauge,
    rttMonIcmpJitterStatsMaxPosSD Gauge,
    rttMonIcmpJitterStatsNumPosSDs Counter,
    rttMonIcmpJitterStatsSumPosSDs Counter,
    rttMonIcmpJStatsSum2PosSDLows Counter,
    rttMonIcmpJStatsSum2PosSDHighs Counter,
    rttMonIcmpJitterStatsMinNegSD Gauge,
    rttMonIcmpJitterStatsMaxNegSD Gauge,
    rttMonIcmpJitterStatsNumNegSDs Counter,
    rttMonIcmpJitterStatsSumNegSDs Counter,
    rttMonIcmpJStatsSum2NegSDLows Counter,
    rttMonIcmpJStatsSum2NegSDHighs Counter,
    rttMonIcmpJitterStatsMinPosDS Gauge,
    rttMonIcmpJitterStatsMaxPosDS Gauge,
    rttMonIcmpJitterStatsNumPosDSes Counter,
    rttMonIcmpJitterStatsSumPosDSes Counter,
    rttMonIcmpJStatsSum2PosDSLows Counter,
    rttMonIcmpJStatsSum2PosDSHighs Counter,
    rttMonIcmpJitterStatsMinNegDS Gauge,
    rttMonIcmpJitterStatsMaxNegDS Gauge,
    rttMonIcmpJitterStatsNumNegDSes Counter,
    rttMonIcmpJitterStatsSumNegDSes Counter,
    rttMonIcmpJStatsSum2NegDSLows Counter,
    rttMonIcmpJStatsSum2NegDSHighs Counter,
    rttMonIcmpJitterStatsPktLosses Counter,
    rttMonIcmpJStatsPktOutSeqBoth Counter,
    rttMonIcmpJStatsPktOutSeqSDs Counter,
    rttMonIcmpJStatsPktOutSeqDSes Counter,
    rttMonIcmpJitterStatsPktSkippeds Counter,
    rttMonIcmpJitterStatsErrors Counter,
    rttMonIcmpJitterStatsBusies Counter,
    rttMonIcmpJitterStatsOWSumSDs Counter,
    rttMonIcmpJStatsOWSum2SDLows Counter,
    rttMonIcmpJStatsOWSum2SDHighs Counter,
    rttMonIcmpJitterStatsOWMinSD Gauge,
    rttMonIcmpJitterStatsOWMaxSD Gauge,
    rttMonIcmpJitterStatsOWSumDSes Counter,
    rttMonIcmpJStatsOWSum2DSLows Counter,
    rttMonIcmpJStatsOWSum2DSHighs Counter,
    rttMonIcmpJitterStatsOWMinDS Gauge,
    rttMonIcmpJitterStatsOWMaxDS Gauge,
    rttMonIcmpJitterStatsNumOWs Counter,
    rttMonIcmpJitterStatsAvgJ Gauge,
    rttMonIcmpJitterStatsAvgJSD Gauge,
    rttMonIcmpJitterStatsAvgJDS Gauge,
    rttMonIcmpJitterMinSucPktLoss Gauge,
    rttMonIcmpJitterMaxSucPktLoss Gauge,
    rttMonIcmpJitterStatsIAJOut Gauge,
    rttMonIcmpJitterStatsIAJIn Gauge,
    rttMonIcmpJitterStatsPktLateAs Counter
    }

rttMonIcmpJitterStatsStartTimeId OBJECT-TYPE
    SYNTAX TimeStamp
--    Rsyntax TimeTicks
    ACCESS not-accessible
    STATUS mandatory
    DESCRIPTION
        "The value of sysUpTime at the time when this 
        row was created."
    ::= { rttMonIcmpJitterStatsEntry 1 }

rttMonIcmpJitterStatsCompletions OBJECT-TYPE
    SYNTAX Counter
--  Units
--    completions
    ACCESS read-only
    STATUS mandatory
    DESCRIPTION
        "The number of ICMP jitter operation that have completed 
        successfully."
    ::= { rttMonIcmpJitterStatsEntry 2 }

rttMonIcmpJStatsOverThresholds OBJECT-TYPE
    SYNTAX Counter
--  Units
--    operations
    ACCESS read-only
    STATUS mandatory
    DESCRIPTION
        "The number of ICMP jitter operations that violate 
        jitterAvg threshold which is defined in RttMonReactVar."
    ::= { rttMonIcmpJitterStatsEntry 3 }

rttMonIcmpJitterStatsNumRTTs OBJECT-TYPE
    SYNTAX Counter
--  Units
--    packets
    ACCESS read-only
    STATUS mandatory
    DESCRIPTION
        "The number of RTT's that are successfully measured."
    ::= { rttMonIcmpJitterStatsEntry 4 }

rttMonIcmpJitterStatsRTTSums OBJECT-TYPE
    SYNTAX Counter
--  Units
--    milliseconds
    ACCESS read-only
    STATUS mandatory
    DESCRIPTION
        "The sum of RTT's that are successfully measured for this
        rttMonIcmpJitterStatsStartTimeId hourly group. The number
        of the successfully measured RTT is stored in the
        rttMonIcmpJitterStatsNumRTT."
    ::= { rttMonIcmpJitterStatsEntry 5 }

rttMonIcmpJStatsRTTSum2Lows OBJECT-TYPE
    SYNTAX Counter
--  Units
--    milliseconds
    ACCESS read-only
    STATUS mandatory
    DESCRIPTION
        "The sum of squares of RTT's that are successfully measured
        (low order 32 bits)."
    ::= { rttMonIcmpJitterStatsEntry 6 }

rttMonIcmpJStatsRTTSum2Highs OBJECT-TYPE
    SYNTAX Counter
--  Units
--    milliseconds
    ACCESS read-only
    STATUS mandatory
    DESCRIPTION
        "The sum of squares of RTT's that are successfully measured
        (high order 32 bits)."
    ::= { rttMonIcmpJitterStatsEntry 7 }

rttMonIcmpJitterStatsRTTMin OBJECT-TYPE
    SYNTAX Gauge
--  Units
--    milliseconds
    ACCESS read-only
    STATUS mandatory
    DESCRIPTION
        "The minimum of RTT's that were successfully measured."
    ::= { rttMonIcmpJitterStatsEntry 8 }

rttMonIcmpJitterStatsRTTMax OBJECT-TYPE
    SYNTAX Gauge
--  Units
--    milliseconds
    ACCESS read-only
    STATUS mandatory
    DESCRIPTION
        "The maximum of RTT's that were successfully measured."
    ::= { rttMonIcmpJitterStatsEntry 9 }

rttMonIcmpJitterStatsMinPosSD OBJECT-TYPE
    SYNTAX Gauge
--  Units
--    milliseconds
    ACCESS read-only
    STATUS mandatory
    DESCRIPTION
        "The minimum of absolute values of all positive jitter values
        for packets sent from source to destination."
    ::= { rttMonIcmpJitterStatsEntry 10 }

rttMonIcmpJitterStatsMaxPosSD OBJECT-TYPE
    SYNTAX Gauge
--  Units
--    milliseconds
    ACCESS read-only
    STATUS mandatory
    DESCRIPTION
        "The maximum of absolute values of all positive jitter values
        for packets sent from source to destination."
    ::= { rttMonIcmpJitterStatsEntry 11 }

rttMonIcmpJitterStatsNumPosSDs OBJECT-TYPE
    SYNTAX Counter
--  Units
--    occurrences
    ACCESS read-only
    STATUS mandatory
    DESCRIPTION
        "The number of all positive jitter values for packets
        sent from source to destination."
    ::= { rttMonIcmpJitterStatsEntry 12 }

rttMonIcmpJitterStatsSumPosSDs OBJECT-TYPE
    SYNTAX Counter
--  Units
--    milliseconds
    ACCESS read-only
    STATUS mandatory
    DESCRIPTION
        "The sum of all positive jitter values for packets sent
        from source to destination. The number of such values
        is stored in rttMonIcmpJitterStatsNumPosSD."
    ::= { rttMonIcmpJitterStatsEntry 13 }

rttMonIcmpJStatsSum2PosSDLows OBJECT-TYPE
    SYNTAX Counter
--  Units
--    milliseconds
    ACCESS read-only
    STATUS mandatory
    DESCRIPTION
        "The sum of square of all positive jitter values for packets
         sent from source to destination (low order 32 bits)."
    ::= { rttMonIcmpJitterStatsEntry 14 }

rttMonIcmpJStatsSum2PosSDHighs OBJECT-TYPE
    SYNTAX Counter
--  Units
--    milliseconds
    ACCESS read-only
    STATUS mandatory
    DESCRIPTION
        "The sum of square of all positive jitter values for packets
         sent from source to destination (high order 32 bits)."
    ::= { rttMonIcmpJitterStatsEntry 15 }

rttMonIcmpJitterStatsMinNegSD OBJECT-TYPE
    SYNTAX Gauge
--  Units
--    milliseconds
    ACCESS read-only
    STATUS mandatory
    DESCRIPTION
        "The minimum of all negative jitter values for packets sent
        from source to destination."
    ::= { rttMonIcmpJitterStatsEntry 16 }

rttMonIcmpJitterStatsMaxNegSD OBJECT-TYPE
    SYNTAX Gauge
--  Units
--    milliseconds
    ACCESS read-only
    STATUS mandatory
    DESCRIPTION
        "The maximum of all negative jitter values for packets sent
        from source to destination."
    ::= { rttMonIcmpJitterStatsEntry 17 }

rttMonIcmpJitterStatsNumNegSDs OBJECT-TYPE
    SYNTAX Counter
--  Units
--    occurrences
    ACCESS read-only
    STATUS mandatory
    DESCRIPTION
        "The number of all negative jitter values for packets
        sent from source to destination."
    ::= { rttMonIcmpJitterStatsEntry 18 }

rttMonIcmpJitterStatsSumNegSDs OBJECT-TYPE
    SYNTAX Counter
--  Units
--    milliseconds
    ACCESS read-only
    STATUS mandatory
    DESCRIPTION
        "The sum of all negative jitter values for packets sent
        from source to destination. The number of such values
        is stored in rttMonIcmpJitterStatsNumNegSD."
    ::= { rttMonIcmpJitterStatsEntry 19 }

rttMonIcmpJStatsSum2NegSDLows OBJECT-TYPE
    SYNTAX Counter
--  Units
--    milliseconds
    ACCESS read-only
    STATUS mandatory
    DESCRIPTION
        "The sum of square of all negative jitter values for
        packets sent from source to destination (low order 32 bits)."
    ::= { rttMonIcmpJitterStatsEntry 20 }

rttMonIcmpJStatsSum2NegSDHighs OBJECT-TYPE
    SYNTAX Counter
--  Units
--    milliseconds
    ACCESS read-only
    STATUS mandatory
    DESCRIPTION
        "The sum of square of all negative jitter values for
        packets sent from source to destination (high order 32 bits)."
    ::= { rttMonIcmpJitterStatsEntry 21 }

rttMonIcmpJitterStatsMinPosDS OBJECT-TYPE
    SYNTAX Gauge
--  Units
--    milliseconds
    ACCESS read-only
    STATUS mandatory
    DESCRIPTION
        "The minimum of all positive jitter values for packets sent
        from destination to source."
    ::= { rttMonIcmpJitterStatsEntry 22 }

rttMonIcmpJitterStatsMaxPosDS OBJECT-TYPE
    SYNTAX Gauge
--  Units
--    milliseconds
    ACCESS read-only
    STATUS mandatory
    DESCRIPTION
        "The maximum of all positive jitter values for packets sent
        from destination to source."
    ::= { rttMonIcmpJitterStatsEntry 23 }

rttMonIcmpJitterStatsNumPosDSes OBJECT-TYPE
    SYNTAX Counter
--  Units
--    occurrences
    ACCESS read-only
    STATUS mandatory
    DESCRIPTION
        "The number of all positive jitter values for packets 
        sent from destination to source."
    ::= { rttMonIcmpJitterStatsEntry 24 }

rttMonIcmpJitterStatsSumPosDSes OBJECT-TYPE
    SYNTAX Counter
--  Units
--    milliseconds
    ACCESS read-only
    STATUS mandatory
    DESCRIPTION
        "The sum of all positive jitter values for packets sent
        from destination to source. The number of such values
        is stored in rttMonIcmpJitterStatsNumPosDS."
    ::= { rttMonIcmpJitterStatsEntry 25 }

rttMonIcmpJStatsSum2PosDSLows OBJECT-TYPE
    SYNTAX Counter
--  Units
--    milliseconds
    ACCESS read-only
    STATUS mandatory
    DESCRIPTION
        "The sum of squares of all positive jitter values for
        packets sent from destination to source (low order 32 bits)."
    ::= { rttMonIcmpJitterStatsEntry 26 }

rttMonIcmpJStatsSum2PosDSHighs OBJECT-TYPE
    SYNTAX Counter
--  Units
--    milliseconds
    ACCESS read-only
    STATUS mandatory
    DESCRIPTION
        "The sum of squares of all positive jitter values for
        packets sent from destination to source (high order 32 bits)."
    ::= { rttMonIcmpJitterStatsEntry 27 }

rttMonIcmpJitterStatsMinNegDS OBJECT-TYPE
    SYNTAX Gauge
--  Units
--    milliseconds
    ACCESS read-only
    STATUS mandatory
    DESCRIPTION
        "The minimum of all negative jitter values for packets sent
        from destination to source."
    ::= { rttMonIcmpJitterStatsEntry 28 }

rttMonIcmpJitterStatsMaxNegDS OBJECT-TYPE
    SYNTAX Gauge
--  Units
--    milliseconds
    ACCESS read-only
    STATUS mandatory
    DESCRIPTION
        "The maximum of all negative jitter values for packets sent
        from destination to source."
    ::= { rttMonIcmpJitterStatsEntry 29 }

rttMonIcmpJitterStatsNumNegDSes OBJECT-TYPE
    SYNTAX Counter
--  Units
--    occurrences
    ACCESS read-only
    STATUS mandatory
    DESCRIPTION
        "The number of all negative jitter values for packets
        sent from destination to source."
    ::= { rttMonIcmpJitterStatsEntry 30 }

rttMonIcmpJitterStatsSumNegDSes OBJECT-TYPE
    SYNTAX Counter
--  Units
--    milliseconds
    ACCESS read-only
    STATUS mandatory
    DESCRIPTION
        "The sum of all negative jitter values for packets sent
        from destination to source. The number of such values
        is stored in rttMonIcmpJitterStatsNumNegDS."
    ::= { rttMonIcmpJitterStatsEntry 31 }

rttMonIcmpJStatsSum2NegDSLows OBJECT-TYPE
    SYNTAX Counter
--  Units
--    milliseconds
    ACCESS read-only
    STATUS mandatory
    DESCRIPTION
        "The sum of squares of all negative jitter values for
        packets sent from destination to source (low order 32 bits)."
    ::= { rttMonIcmpJitterStatsEntry 32 }

rttMonIcmpJStatsSum2NegDSHighs OBJECT-TYPE
    SYNTAX Counter
--  Units
--    milliseconds
    ACCESS read-only
    STATUS mandatory
    DESCRIPTION
        "The sum of squares of all negative jitter values for
        packets sent from destination to source (high order 32 bits)."
    ::= { rttMonIcmpJitterStatsEntry 33 }

rttMonIcmpJitterStatsPktLosses OBJECT-TYPE
    SYNTAX Counter
--  Units
--    packets
    ACCESS read-only
    STATUS mandatory
    DESCRIPTION
        "The number of lost packets"
    ::= { rttMonIcmpJitterStatsEntry 34 }

rttMonIcmpJStatsPktOutSeqBoth OBJECT-TYPE
    SYNTAX Counter
--  Units
--    packets
    ACCESS read-only
    STATUS mandatory
    DESCRIPTION
        "The number of packets arrived out of sequence in both
        source-to-destination and destination-to-source direction."
    ::= { rttMonIcmpJitterStatsEntry 35 }

rttMonIcmpJStatsPktOutSeqSDs OBJECT-TYPE
    SYNTAX Counter
--  Units
--    packets
    ACCESS read-only
    STATUS mandatory
    DESCRIPTION
        "The number of packets arrived out of sequence in the 
        direction of source-to-destination."
    ::= { rttMonIcmpJitterStatsEntry 36 }

rttMonIcmpJStatsPktOutSeqDSes OBJECT-TYPE
    SYNTAX Counter
--  Units
--    packets
    ACCESS read-only
    STATUS mandatory
    DESCRIPTION
        "The number of packets arrived out of sequence in the
        direction of destination-to-source."
    ::= { rttMonIcmpJitterStatsEntry 37 }

rttMonIcmpJitterStatsPktSkippeds OBJECT-TYPE
    SYNTAX Counter
--  Units
--    packets
    ACCESS read-only
    STATUS mandatory
    DESCRIPTION
        "The number of packets that are skipped per operation because 
        the router could not send the packet out."
    ::= { rttMonIcmpJitterStatsEntry 38 }

rttMonIcmpJitterStatsErrors OBJECT-TYPE
    SYNTAX Counter
--  Units
--    errors
    ACCESS read-only
    STATUS mandatory
    DESCRIPTION
        "The number of occasions when a ICMP jitter operation could not
        be initiated because of an internal error"
    ::= { rttMonIcmpJitterStatsEntry 39 }

rttMonIcmpJitterStatsBusies OBJECT-TYPE
    SYNTAX Counter
--  Units
--    busies
    ACCESS read-only
    STATUS mandatory
    DESCRIPTION
        "The number of occasions when a ICMP jitter operation could not
        be initiated because a previous ICMP jitter operation has not
        been completed."
    ::= { rttMonIcmpJitterStatsEntry 40 }

rttMonIcmpJitterStatsOWSumSDs OBJECT-TYPE
    SYNTAX Counter
--  Units
--    milliseconds
    ACCESS read-only
    STATUS mandatory
    DESCRIPTION
        "The sum of one way trip time from source to destination."
    ::= { rttMonIcmpJitterStatsEntry 41 }

rttMonIcmpJStatsOWSum2SDLows OBJECT-TYPE
    SYNTAX Counter
--  Units
--    milliseconds
    ACCESS read-only
    STATUS mandatory
    DESCRIPTION
        "The sum of squares of one way trip time from source to 
        destination (low order 32 bits)."
    ::= { rttMonIcmpJitterStatsEntry 42 }

rttMonIcmpJStatsOWSum2SDHighs OBJECT-TYPE
    SYNTAX Counter
--  Units
--    milliseconds
    ACCESS read-only
    STATUS mandatory
    DESCRIPTION
        "The sum of squares of one way trip time from source to 
        destination (high order 32 bits)."
    ::= { rttMonIcmpJitterStatsEntry 43 }

rttMonIcmpJitterStatsOWMinSD OBJECT-TYPE
    SYNTAX Gauge
--  Units
--    milliseconds
    ACCESS read-only
    STATUS mandatory
    DESCRIPTION
        "The minimum of all one way trip time from source to 
        destination."
    ::= { rttMonIcmpJitterStatsEntry 44 }

rttMonIcmpJitterStatsOWMaxSD OBJECT-TYPE
    SYNTAX Gauge
--  Units
--    milliseconds
    ACCESS read-only
    STATUS mandatory
    DESCRIPTION
        "The maximum of all one way trip time from source to 
        destination."
    ::= { rttMonIcmpJitterStatsEntry 45 }

rttMonIcmpJitterStatsOWSumDSes OBJECT-TYPE
    SYNTAX Counter
--  Units
--    milliseconds
    ACCESS read-only
    STATUS mandatory
    DESCRIPTION
        "The sum of one way trip time from destination to source."
    ::= { rttMonIcmpJitterStatsEntry 46 }

rttMonIcmpJStatsOWSum2DSLows OBJECT-TYPE
    SYNTAX Counter
--  Units
--    milliseconds
    ACCESS read-only
    STATUS mandatory
    DESCRIPTION
        "The sum of squares of one way trip time from destination 
        to source (low order 32 bits)."
    ::= { rttMonIcmpJitterStatsEntry 47 }

rttMonIcmpJStatsOWSum2DSHighs OBJECT-TYPE
    SYNTAX Counter
--  Units
--    milliseconds
    ACCESS read-only
    STATUS mandatory
    DESCRIPTION
        "The sum of squares of one way trip time from destination 
        to source (high order 32 bits)."
    ::= { rttMonIcmpJitterStatsEntry 48 }

rttMonIcmpJitterStatsOWMinDS OBJECT-TYPE
    SYNTAX Gauge
--  Units
--    milliseconds
    ACCESS read-only
    STATUS mandatory
    DESCRIPTION
        "The minimum of all one way trip time from destination 
        to source."
    ::= { rttMonIcmpJitterStatsEntry 49 }

rttMonIcmpJitterStatsOWMaxDS OBJECT-TYPE
    SYNTAX Gauge
--  Units
--    milliseconds
    ACCESS read-only
    STATUS mandatory
    DESCRIPTION
        "The maximum of all one way trip time from destination 
        to source."
    ::= { rttMonIcmpJitterStatsEntry 50 }

rttMonIcmpJitterStatsNumOWs OBJECT-TYPE
    SYNTAX Counter
--  Units
--    packets
    ACCESS read-only
    STATUS mandatory
    DESCRIPTION
        "The number of one way trip time that are successfully 
         measured."
    ::= { rttMonIcmpJitterStatsEntry 51 }

rttMonIcmpJitterStatsAvgJ OBJECT-TYPE
    SYNTAX Gauge
--  Units
--    milliseconds
    ACCESS read-only
    STATUS mandatory
    DESCRIPTION
        "The average of positive and negative jitter
        values for source-to-destination and 
        destination-to-source direction."
    ::= { rttMonIcmpJitterStatsEntry 52 }

rttMonIcmpJitterStatsAvgJSD OBJECT-TYPE
    SYNTAX Gauge
--  Units
--    milliseconds
    ACCESS read-only
    STATUS mandatory
    DESCRIPTION
        "The average of positive and negative jitter
         values in source-to-destination direction."
    ::= { rttMonIcmpJitterStatsEntry 53 }

rttMonIcmpJitterStatsAvgJDS OBJECT-TYPE
    SYNTAX Gauge
--  Units
--    milliseconds
    ACCESS read-only
    STATUS mandatory
    DESCRIPTION
        "The average of positive and negative jitter
         values in destination-to-source direction."
    ::= { rttMonIcmpJitterStatsEntry 54 }

rttMonIcmpJitterMinSucPktLoss OBJECT-TYPE
    SYNTAX Gauge
--  Units
--    packets
    ACCESS read-only
    STATUS mandatory
    DESCRIPTION
        "The minimum number of packets that are dropped 
         successively."
    ::= { rttMonIcmpJitterStatsEntry 55 }

rttMonIcmpJitterMaxSucPktLoss OBJECT-TYPE
    SYNTAX Gauge
--  Units
--    packets
    ACCESS read-only
    STATUS mandatory
    DESCRIPTION
        "The maximum number of packets that are dropped
         successively."
    ::= { rttMonIcmpJitterStatsEntry 56 }

rttMonIcmpJitterStatsIAJOut OBJECT-TYPE
    SYNTAX Gauge
--  Units
--    milliseconds
    ACCESS read-only
    STATUS mandatory
    DESCRIPTION
        "Inter-arrival jitter (RFC 1889) at responder"
    REFERENCE
        "Refer to the following documents for the definition: 
        RFC 1889, Section 6.3.1"
    ::= { rttMonIcmpJitterStatsEntry 57 }

rttMonIcmpJitterStatsIAJIn OBJECT-TYPE
    SYNTAX Gauge
--  Units
--    milliseconds
    ACCESS read-only
    STATUS mandatory
    DESCRIPTION
        "Inter-arrival jitter (RFC 1889) at sender"
    REFERENCE
        "Refer to the following documents for the definition: 
        RFC 1889, Section 6.3.1"
    ::= { rttMonIcmpJitterStatsEntry 58 }

rttMonIcmpJitterStatsPktLateAs OBJECT-TYPE
    SYNTAX Counter
--  Units
--    packets
    ACCESS read-only
    STATUS mandatory
    DESCRIPTION
        "The number of packets that arrived after the timeout."
    ::= { rttMonIcmpJitterStatsEntry 59 }

ciscoRttMonIcmpJitterGroup OBJECT IDENTIFIER ::= { ciscoRttMonIcmpMIBGroups 1 }
-- OBJECT-GROUP
--  Status
--    mandatory
--  Descr
--    A collection of statistics objects related to
--     ICMP Jitter Probe.
--  objects
--    rttMonLatestIcmpJitterNumRTT, rttMonLatestIcmpJitterRTTSum, 
--    rttMonLatestIcmpJitterRTTSum2, rttMonLatestIcmpJitterRTTMin, 
--    rttMonLatestIcmpJitterRTTMax, rttMonLatestIcmpJitterMinPosSD, 
--    rttMonLatestIcmpJitterMaxPosSD, 
--    rttMonLatestIcmpJitterNumPosSD, 
--    rttMonLatestIcmpJitterSumPosSD, 
--    rttMonLatestIcmpJitterSum2PosSD, 
--    rttMonLatestIcmpJitterMinNegSD, 
--    rttMonLatestIcmpJitterMaxNegSD, 
--    rttMonLatestIcmpJitterNumNegSD, 
--    rttMonLatestIcmpJitterSumNegSD, 
--    rttMonLatestIcmpJitterSum2NegSD, 
--    rttMonLatestIcmpJitterMinPosDS, 
--    rttMonLatestIcmpJitterMaxPosDS, 
--    rttMonLatestIcmpJitterNumPosDS, 
--    rttMonLatestIcmpJitterSumPosDS, 
--    rttMonLatestIcmpJitterSum2PosDS, 
--    rttMonLatestIcmpJitterMinNegDS, 
--    rttMonLatestIcmpJitterMaxNegDS, 
--    rttMonLatestIcmpJitterNumNegDS, 
--    rttMonLatestIcmpJitterSumNegDS, 
--    rttMonLatestIcmpJitterSum2NegDS, 
--    rttMonLatestIcmpJitterPktLoss, rttMonLatestIcmpJPktOutSeqBoth, 
--    rttMonLatestIcmpJPktOutSeqSD, rttMonLatestIcmpJPktOutSeqDS, 
--    rttMonLatestIcmpJitterPktSkipped, rttMonLatestIcmpJitterSense, 
--    rttMonLatestIcmpJitterPktLateA, 
--    rttMonLatestIcmpJitterMinSucPktL, 
--    rttMonLatestIcmpJitterMaxSucPktL, 
--    rttMonLatestIcmpJitterOWSumSD, rttMonLatestIcmpJitterOWSum2SD, 
--    rttMonLatestIcmpJitterOWMinSD, rttMonLatestIcmpJitterOWMaxSD, 
--    rttMonLatestIcmpJitterOWSumDS, rttMonLatestIcmpJitterOWSum2DS, 
--    rttMonLatestIcmpJitterOWMinDS, rttMonLatestIcmpJitterOWMaxDS, 
--    rttMonLatestIcmpJitterNumOW, rttMonLatestIcmpJitterAvgJitter, 
--    rttMonLatestIcmpJitterAvgSDJ, rttMonLatestIcmpJitterAvgDSJ, 
--    rttMonLatestIcmpJitterOWAvgSD, rttMonLatestIcmpJitterOWAvgDS, 
--    rttMonLatestIcmpJitterIAJOut, rttMonLatestIcmpJitterIAJIn, 
--    rttMonIcmpJitterStatsCompletions, 
--    rttMonIcmpJStatsOverThresholds, rttMonIcmpJitterStatsNumRTTs, 
--    rttMonIcmpJitterStatsRTTSums, rttMonIcmpJStatsRTTSum2Lows, 
--    rttMonIcmpJStatsRTTSum2Highs, rttMonIcmpJitterStatsRTTMin, 
--    rttMonIcmpJitterStatsRTTMax, rttMonIcmpJitterStatsMinPosSD, 
--    rttMonIcmpJitterStatsMaxPosSD, rttMonIcmpJitterStatsNumPosSDs, 
--    rttMonIcmpJitterStatsSumPosSDs, rttMonIcmpJStatsSum2PosSDLows, 
--    rttMonIcmpJStatsSum2PosSDHighs, rttMonIcmpJitterStatsMinNegSD, 
--    rttMonIcmpJitterStatsMaxNegSD, rttMonIcmpJitterStatsNumNegSDs, 
--    rttMonIcmpJitterStatsSumNegSDs, rttMonIcmpJStatsSum2NegSDLows, 
--    rttMonIcmpJStatsSum2NegSDHighs, rttMonIcmpJitterStatsMinPosDS, 
--    rttMonIcmpJitterStatsMaxPosDS, 
--    rttMonIcmpJitterStatsNumPosDSes, 
--    rttMonIcmpJitterStatsSumPosDSes, 
--    rttMonIcmpJStatsSum2PosDSLows, rttMonIcmpJStatsSum2PosDSHighs, 
--    rttMonIcmpJitterStatsMinNegDS, rttMonIcmpJitterStatsMaxNegDS, 
--    rttMonIcmpJitterStatsNumNegDSes, 
--    rttMonIcmpJitterStatsSumNegDSes, 
--    rttMonIcmpJStatsSum2NegDSLows, rttMonIcmpJStatsSum2NegDSHighs, 
--    rttMonIcmpJitterStatsPktLosses, rttMonIcmpJStatsPktOutSeqBoth, 
--    rttMonIcmpJStatsPktOutSeqSDs, rttMonIcmpJStatsPktOutSeqDSes, 
--    rttMonIcmpJitterStatsPktSkippeds, rttMonIcmpJitterStatsErrors, 
--    rttMonIcmpJitterStatsBusies, rttMonIcmpJitterStatsOWSumSDs, 
--    rttMonIcmpJStatsOWSum2SDLows, rttMonIcmpJStatsOWSum2SDHighs, 
--    rttMonIcmpJitterStatsOWMinSD, rttMonIcmpJitterStatsOWMaxSD, 
--    rttMonIcmpJitterStatsOWSumDSes, rttMonIcmpJStatsOWSum2DSLows, 
--    rttMonIcmpJStatsOWSum2DSHighs, rttMonIcmpJitterStatsOWMinDS, 
--    rttMonIcmpJitterStatsOWMaxDS, rttMonIcmpJitterStatsNumOWs, 
--    rttMonIcmpJitterStatsAvgJ, rttMonIcmpJitterStatsAvgJSD, 
--    rttMonIcmpJitterStatsAvgJDS, rttMonIcmpJitterMinSucPktLoss, 
--    rttMonIcmpJitterMaxSucPktLoss, rttMonIcmpJitterStatsIAJOut, 
--    rttMonIcmpJitterStatsIAJIn, rttMonIcmpJitterStatsPktLateAs

ciscoRttMonIcmpJitterCompliance OBJECT IDENTIFIER ::= { ciscoRttMonIcmpCompliances 1 }
-- MODULE-COMPLIANCE
--  Status
--    mandatory
--  Descr
--    The compliance statement for
--    (1) ICMP Jitter operation and statistics
--  Module
--    >>current<<
--   MandGroup
--    ciscoRttMonIcmpJitterGroup


END
