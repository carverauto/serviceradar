-- MIB file created 05-Mar-2014 15:16:48, by
--   SMICng version 2.2.11-beta(PRO)(Solaris), January 20, 2001. Enterprise key cisco.com

CISCO-WAN-CELL-EXT-MIB DEFINITIONS ::= BEGIN

-- From file: "CISCO-WAN-CELL-EXT-MIB.my"
-- Compile options "4 7 F H N W 03 06 0B 0G 0N 0T"

IMPORTS
    entPhysicalIndex, entPhysicalName
            FROM ENTITY-MIB
    ifIndex
            FROM IF-MIB
    RowStatus, StorageType
            FROM SNMPv2-TC-v1
    SnmpAdminString
            FROM SNMP-FRAMEWORK-MIB
    InetAddressType, InetAddress
            FROM INET-ADDRESS-MIB
    C3gServiceCapability
            FROM CISCO-WAN-3G-MIB
    ciscoMgmt
            FROM CISCO-SMI
    Gauge, Counter
            FROM RFC1155-SMI
    OBJECT-TYPE
            FROM RFC-1212
    TRAP-TYPE
            FROM RFC-1215;

ciscoWanCellExtMIB OBJECT IDENTIFIER ::= { ciscoMgmt 817 }
-- MODULE-IDENTITY
--  LastUpdated
--    201403050000Z
--  OrgName
--    Cisco Systems, Inc.
--  ContactInfo
--    Cisco Systems
--    Customer Service
--    
--    Postal: 170 W Tasman Drive
--    San Jose, CA  95134
--    USA
--    
--    Tel: +1 800 553-NETS
--    
--    E-mail: cs-3g@cisco.com
--            cs-4g@cisco.com
--  Descr
--    This MIB module is an extension of
--    CISCO-WAN-3G-MIB.my, and it provides
--    network management support for Cisco cellular
--    WAN 4G/LTE products.
--    
--    *** ABBREVIATIONS, ACRONYMS, AND SYMBOLS ***
--    
--    AMBR         -   Aggregate Maximum Bit Rate
--    APN          -   Access Point Name
--    ARP          -   Allocation and Retention Priority
--    CQI          -   Channel Quality Indicator
--    eNodeB       -   Evolved Node B
--    EPS          -   Evolved Packet System
--    E-UTRAN      -   Evolved Universal Terrestrial Radio Access
--    GBR          -   Guaranteed Bit Rate
--    LTE          -   Long Term Evolution
--    MBR          -   Maximum Bit Rate
--    PCRF         -   Policy and Charging Rules Function
--    PDN          -   Packet Data Network
--    QCI          -   QoS Class Identifier
--    QOS          -   Quality of Service
--    RF           -   Radio Frequency
--    RSRP         -   Reference Signal Receive Power
--    RSRQ         -   Reference Signal Receive Quality
--    SINR         -   Signal-to-Interference plus Noise Ratio
--    SNR          -   Signal-to-Noise Ratio
--    UE           -   User Equipment
--  RevDate
--    201403050000Z
--  RevDescr
--    Initial version of this MIB module.

ciscoWanCellExtMIBNotifs OBJECT IDENTIFIER ::= { ciscoWanCellExtMIB 0 }
ciscoWanCellExtMIBObjects OBJECT IDENTIFIER ::= { ciscoWanCellExtMIB 1 }
ciscoWanCellExtMIBConform OBJECT IDENTIFIER ::= { ciscoWanCellExtMIB 2 }
ciscoWanCellExtLte OBJECT IDENTIFIER ::= { ciscoWanCellExtMIBObjects 1 }
cwceLteRadio    OBJECT IDENTIFIER ::= { ciscoWanCellExtLte 1 }
cwceLteProfile  OBJECT IDENTIFIER ::= { ciscoWanCellExtLte 2 }
cwceLteRadioHistory OBJECT IDENTIFIER ::= { cwceLteRadio 2 }
ciscoWanCellExtMIBCompliances OBJECT IDENTIFIER ::= { ciscoWanCellExtMIBConform 1 }
ciscoWanCellExtMIBGroups OBJECT IDENTIFIER ::= { ciscoWanCellExtMIBConform 2 }

CiscoWanCellExtProtocolType ::= INTEGER {
        unknown(1),
        ipv4(2),
        ppp(3),
        ipv6(4),
        ipv4V6(5)
        }
-- TEXTUAL-CONVENTION
--  Status
--    mandatory
--  Descr
--    Generic PDN type.

CiscoWanCellExtRsrp ::= INTEGER
-- TEXTUAL-CONVENTION
--  DspHint
--    d
--  Status
--    mandatory
--  Descr
--    Reference signal received power (RSRP) is
--    defined as the linear average over the power 
--    contributions and measured in dBm. The reporting 
--    range of RSRP is defined per LTE standard 
--    with 1 dBm resolution.

CiscoWanCellExtRsrq ::= INTEGER
-- TEXTUAL-CONVENTION
--  DspHint
--    d-1
--  Status
--    mandatory
--  Descr
--    Reference Signal Received Quality (RSRQ) is
--    defined as the ratio NxRSRP over (E-UTRAN carrier RSSI) 
--    and measured in dB. The reporting range of 
--    RSRQ is defined per LTE standard with 0.5 dB
--    resolution.

CiscoWanCellExtCqiIndex ::= Gauge
-- TEXTUAL-CONVENTION
--  DspHint
--    d
--  Status
--    mandatory
--  Descr
--    Channel Quality indicator reported to eNodeB
--    which directly translates to Modulation Coding
--    Scheme selected.

CiscoWanCellExtSNR ::= INTEGER
-- TEXTUAL-CONVENTION
--  DspHint
--    d-1
--  Status
--    mandatory
--  Descr
--    Signal-to-Noise power Ratio (SNR)
--    is defined as the ratio of signal
--    power to the noise power, measured
--    in dB. It determines the downlink
--    throughput for the UE.

CiscoWanCellExtSINR ::= INTEGER
-- TEXTUAL-CONVENTION
--  DspHint
--    d-1
--  Status
--    mandatory
--  Descr
--    Signal to Interference plus Noise Ratio is
--    the power at the receiver due to the required
--    signal, divided by the power due to noise and
--    interference measured in dB. It is used as a
--    measure of signal quality.

cwceLteRadioTable OBJECT-TYPE
    SYNTAX SEQUENCE OF CwceLteRadioEntry
    ACCESS not-accessible
    STATUS mandatory
    DESCRIPTION
        "This table contains entPhysicalTable entries which
        are capable of providing operational Cellular 4G/LTE
        Radio signal parameters and administrative notification
        information."
    ::= { cwceLteRadio 1 }

cwceLteRadioEntry OBJECT-TYPE
    SYNTAX CwceLteRadioEntry
    ACCESS not-accessible
    STATUS mandatory
    DESCRIPTION
        "An entry contains management information of Cellular
        4G/LTE Radio signal parameters and  notification
        information.
        
        An entry of this table is created if an entity capable
        of providing operational Cellular 4G/LTE Radio signal
        parameters and administrative notification information
        is detected by the agent.
        
        An entry of this table is deleted by the agent if the
        corresponding entry in entPhysicalTable is removed."
    INDEX { entPhysicalIndex }
    ::= { cwceLteRadioTable 1 }

CwceLteRadioEntry ::= SEQUENCE {
    cwceLteCurrRsrp CiscoWanCellExtRsrp,
    cwceLteCurrRsrq CiscoWanCellExtRsrq,
    cwceLteCurrSnr CiscoWanCellExtSNR,
    cwceLteCurrSinr CiscoWanCellExtSINR,
    cwceLteCurrCqiIndex CiscoWanCellExtCqiIndex,
    cwceLteCurrOperatingBand Gauge,
    cwceLteNotifRsrp CiscoWanCellExtRsrp,
    cwceLteNotifRsrq CiscoWanCellExtRsrq,
    cwceLteRsrpOnsetNotifThreshold CiscoWanCellExtRsrp,
    cwceLteRsrpAbateNotifThreshold CiscoWanCellExtRsrp,
    cwceLteRsrqOnsetNotifThreshold CiscoWanCellExtRsrq,
    cwceLteRsrqAbateNotifThreshold CiscoWanCellExtRsrq,
    cwceLteRsrpOnsetNotifFlag C3gServiceCapability,
    cwceLteRsrpAbateNotifFlag C3gServiceCapability,
    cwceLteRsrqOnsetNotifFlag C3gServiceCapability,
    cwceLteRsrqAbateNotifFlag C3gServiceCapability
    }

cwceLteCurrRsrp OBJECT-TYPE
    SYNTAX CiscoWanCellExtRsrp
--    Rsyntax INTEGER
--  Units
--    dBm
    ACCESS read-only
    STATUS mandatory
    DESCRIPTION
        "This object indicates the LTE RSRP value reported by 
        the modem."
    ::= { cwceLteRadioEntry 1 }

cwceLteCurrRsrq OBJECT-TYPE
    SYNTAX CiscoWanCellExtRsrq
--    Rsyntax INTEGER
--  Units
--    dB
    ACCESS read-only
    STATUS mandatory
    DESCRIPTION
        "This object indicates the LTE RSRQ value reported by 
        the modem."
    ::= { cwceLteRadioEntry 2 }

cwceLteCurrSnr OBJECT-TYPE
    SYNTAX CiscoWanCellExtSNR
--    Rsyntax INTEGER
--  Units
--    dB
    ACCESS read-only
    STATUS mandatory
    DESCRIPTION
        "This object indicates the LTE SNR value reported by 
        the modem."
    ::= { cwceLteRadioEntry 3 }

cwceLteCurrSinr OBJECT-TYPE
    SYNTAX CiscoWanCellExtSINR
--    Rsyntax INTEGER
--  Units
--    dB
    ACCESS read-only
    STATUS mandatory
    DESCRIPTION
        "This object indicates the LTE SINR value measured in
        decibels (dB) reported by the modem."
    ::= { cwceLteRadioEntry 4 }

cwceLteCurrCqiIndex OBJECT-TYPE
    SYNTAX CiscoWanCellExtCqiIndex
--    Rsyntax Gauge
    ACCESS read-only
    STATUS mandatory
    DESCRIPTION
        "This object indicates he LTE CQI Index reported by
        the modem."
    ::= { cwceLteRadioEntry 5 }

cwceLteCurrOperatingBand OBJECT-TYPE
    SYNTAX Gauge
    ACCESS read-only
    STATUS mandatory
    DESCRIPTION
        "This object indicates the E-UTRAN Operating Band reported 
        by the modem."
    ::= { cwceLteRadioEntry 6 }

cwceLteNotifRsrp OBJECT-TYPE
    SYNTAX CiscoWanCellExtRsrp
--    Rsyntax INTEGER
    ACCESS read-only
    STATUS mandatory
    DESCRIPTION
        "This object indicates the LTE RSRP value reported by
        the modem which triggered the most recent
        cwceLteRsrpOnsetNotif or cwceLteRsrpAbateNotif
        notification."
    ::= { cwceLteRadioEntry 7 }

cwceLteNotifRsrq OBJECT-TYPE
    SYNTAX CiscoWanCellExtRsrq
--    Rsyntax INTEGER
    ACCESS read-only
    STATUS mandatory
    DESCRIPTION
        "This object indicates the LTE RSRP value reported by
        the modem which triggered the most recent
        cwceLteRsrqOnsetNotif or cwceLteRsrqAbateNotif
        notification."
    ::= { cwceLteRadioEntry 8 }

cwceLteRsrpOnsetNotifThreshold OBJECT-TYPE
    SYNTAX CiscoWanCellExtRsrp
--    Rsyntax INTEGER
--  Units
--    dBm
    ACCESS read-write
    STATUS mandatory
    DESCRIPTION
        "This object specifies the RSRP onset threshold
        value.  If the value of cwceLteCurrRsrp goes
        below the threshold and the service bit in
        cwceLteRsrpOnsetNotifFlag is set, the
        cwceLteRsrqOnsetNotif notification for that
        service will be sent.  The absolute value of
        cwceLteRsrpAbateNotifThreshold should be less
        than or equal to the absolute value of
        cwceLteRsrpOnsetNotifThreshold
        (|cwceLteRsrpAbateNotifThreshold| <=
        |cwceLteRsrpOnsetNotifThreshold|)."
    ::= { cwceLteRadioEntry 9 }

cwceLteRsrpAbateNotifThreshold OBJECT-TYPE
    SYNTAX CiscoWanCellExtRsrp
--    Rsyntax INTEGER
--  Units
--    dBm
    ACCESS read-write
    STATUS mandatory
    DESCRIPTION
        "This object specifies the RSRP abate
        threshold value. If the value of
        cwceLteCurrRsrp goes above the threshold
        and the service bit in cwceLteRsrpOnsetNotifFlag
        is set, the cwceLteRsrpAbateNotif notification
        for that service will be sent. The absolute
        value of cwceLteRsrpAbateNotifThreshold should
        be less than or equal to the absolute value of
        cwceLteRsrpOnsetNotifThreshold
        (|cwceLteRsrpAbateNotifThreshold| <=
        |cwceLteRsrpOnsetNotifThreshold|)."
    ::= { cwceLteRadioEntry 10 }

cwceLteRsrqOnsetNotifThreshold OBJECT-TYPE
    SYNTAX CiscoWanCellExtRsrq
--    Rsyntax INTEGER
--  Units
--    dB
    ACCESS read-write
    STATUS mandatory
    DESCRIPTION
        "This object specifies the RSRQ onset threshold
        value. If the value of cwceLteCurrRsrq goes below
        the threshold and the service bit in
        cwceLteRsrqOnsetNotifFlag is set, the
        cwceLteRsrqOnsetNotif notification for that
        service will be sent.  The absolute value of
        cwceLteRsrqAbateNotifThreshold should be
        less than or equal to the absolute value of
        cwceLteRsrqOnsetNotifThreshold
        (|cwceLteRsrqAbateNotifThreshold| <=
        |cwceLteRsrqOnsetNotifThreshold|)."
    ::= { cwceLteRadioEntry 11 }

cwceLteRsrqAbateNotifThreshold OBJECT-TYPE
    SYNTAX CiscoWanCellExtRsrq
--    Rsyntax INTEGER
--  Units
--    dB
    ACCESS read-write
    STATUS mandatory
    DESCRIPTION
        "This object specifies the RSRQ abate
        threshold value.  If the value of
        cwceLteCurrRsrq goes above the threshold
        and the service bit in
        cwceLteRsrqOnsetNotifFlag is set, the
        cwceLteRsrqAbateNotif notification for that
        service will be sent.  The absolute value of
        cwceLteRsrqAbateNotifThreshold should be
        less than or equal to the absolute value of
        cwceLteRsrqOnsetNotifThreshold
        (|cwceLteRsrqAbateNotifThreshold| <=
        |cwceLteRsrqOnsetNotifThreshold|)."
    ::= { cwceLteRadioEntry 12 }

cwceLteRsrpOnsetNotifFlag OBJECT-TYPE
    SYNTAX C3gServiceCapability
--    Rsyntax OCTET STRING(SIZE(1..2))
--         BITS are:
--           oneXRtt(0)
--           evDoRel0(1)
--           evDoRelA(2)
--           evDoRelB(3)
--           gprs(4)
--           edge(5)
--           umtsWcdma(6)
--           hsdpa(7)
--           hsupa(8)
--           hspa(9)
--           hspaPlus(10)
--           lteTdd(11)
--           lteFdd(12)
    ACCESS read-write
    STATUS mandatory
    DESCRIPTION
        "This object specifies the flag bitmap to control
        the generation of notification cwceLteRsrpOnsetNotif.
        Each bit represents a service as defined in
        C3gServiceCapability, set the bit value to 1
        to enable (and 0 to disable) the generation of
        notification cwceLteRsrpOnsetNotif for that service.
        The default value of this object is all bits are 0.
        Notifications are not generated in technology modes
        where RSRP is not relevant."
    ::= { cwceLteRadioEntry 13 }

cwceLteRsrpAbateNotifFlag OBJECT-TYPE
    SYNTAX C3gServiceCapability
--    Rsyntax OCTET STRING(SIZE(1..2))
--         BITS are:
--           oneXRtt(0)
--           evDoRel0(1)
--           evDoRelA(2)
--           evDoRelB(3)
--           gprs(4)
--           edge(5)
--           umtsWcdma(6)
--           hsdpa(7)
--           hsupa(8)
--           hspa(9)
--           hspaPlus(10)
--           lteTdd(11)
--           lteFdd(12)
    ACCESS read-write
    STATUS mandatory
    DESCRIPTION
        "This object specifies the flag bitmap to control the generation
        of notification cwceLteRsrpAbateNotif. Each bit
        represents a service as defined in C3gServiceCapability,
        set the bit value to 1 to enable (and 0 to disable) the
        generation of notification cwceLteRsrpAbateNotif
        for that service.  The default value of this object is
        all bits are 0. Notifications are not generated in
        technology modes where RSRP is not relevant."
    ::= { cwceLteRadioEntry 14 }

cwceLteRsrqOnsetNotifFlag OBJECT-TYPE
    SYNTAX C3gServiceCapability
--    Rsyntax OCTET STRING(SIZE(1..2))
--         BITS are:
--           oneXRtt(0)
--           evDoRel0(1)
--           evDoRelA(2)
--           evDoRelB(3)
--           gprs(4)
--           edge(5)
--           umtsWcdma(6)
--           hsdpa(7)
--           hsupa(8)
--           hspa(9)
--           hspaPlus(10)
--           lteTdd(11)
--           lteFdd(12)
    ACCESS read-write
    STATUS mandatory
    DESCRIPTION
        "This object specifies the flag bitmap to control the generation
        of notification cwceLteRsrqOnsetNotif. Each bit
        represents a service as defined in C3gServiceCapability,
        set the bit value to 1 to enable (and 0 to disable) the
        generation of notification cwceLteRsrqOnsetNotif
        for that service.  The default value of this object is
        all bits are 0. Notifications are not generated in
        technology modes where RSRQ is not relevant."
    ::= { cwceLteRadioEntry 15 }

cwceLteRsrqAbateNotifFlag OBJECT-TYPE
    SYNTAX C3gServiceCapability
--    Rsyntax OCTET STRING(SIZE(1..2))
--         BITS are:
--           oneXRtt(0)
--           evDoRel0(1)
--           evDoRelA(2)
--           evDoRelB(3)
--           gprs(4)
--           edge(5)
--           umtsWcdma(6)
--           hsdpa(7)
--           hsupa(8)
--           hspa(9)
--           hspaPlus(10)
--           lteTdd(11)
--           lteFdd(12)
    ACCESS read-write
    STATUS mandatory
    DESCRIPTION
        "This object specifies the flag bitmap to control the generation
        of notification cwceLteRsrqAbateNotif. Each bit
        represents a service as defined in C3gServiceCapability,
        set the bit value to 1 to enable (and 0 to disable) the
        generation of notification cwceLteRsrqAbateNotif
        for that service.  The default value of this object is
        all bits are 0. Notifications are not generated in
        technology modes where RSRQ is not relevant."
    ::= { cwceLteRadioEntry 16 }

cwceLteRadioHistoryRsrpTable OBJECT-TYPE
    SYNTAX SEQUENCE OF CwceLteRadioHistoryRsrpEntry
    ACCESS not-accessible
    STATUS mandatory
    DESCRIPTION
        "This table contains Cellular 4G/LTE RSRP history.
        The history of RSRP are carried in an octet of string.
        Each octet in the octet string has a value from 40 to
        140 and the 150 value is reserved to indicate an
        uninitialized (Invalid) value.  The format of
        the octet string with n octets is as following:
           [ octet 0 is latest,
             octet 1 is latest-1,
             .
             .
             octet n-2 is oldest-1,
             octet n-1 is oldest ]
        
        To convert the provided value into dBm the following formula
        should be used:
           dBm = (-1)*value"
    ::= { cwceLteRadioHistory 1 }

cwceLteRadioHistoryRsrpEntry OBJECT-TYPE
    SYNTAX CwceLteRadioHistoryRsrpEntry
    ACCESS not-accessible
    STATUS mandatory
    DESCRIPTION
        "An entry contains management information of Cellular 
        4G/LTE RSRP Radio history parameters.
        
        An entry of this table is created if an entity capable
        of providing operational Cellular 4G/LTE RSRP Radio
        history is detected by the agent.
        
        An entry of this table is deleted by the agent if the
        corresponding entry in entPhysicalTable is removed."
    INDEX { entPhysicalIndex }
    ::= { cwceLteRadioHistoryRsrpTable 1 }

CwceLteRadioHistoryRsrpEntry ::= SEQUENCE {
    cwceLteRadioHistoryRsrpPerSecond OCTET STRING,
    cwceLteRadioHistoryRsrpPerMinute OCTET STRING,
    cwceLteRadioHistoryRsrpPerHour OCTET STRING
    }

cwceLteRadioHistoryRsrpPerSecond OBJECT-TYPE
    SYNTAX OCTET STRING(SIZE(60))
--  Units
--    -dBm
    ACCESS read-only
    STATUS mandatory
    DESCRIPTION
        "This object indicates per-second RSRP history.  
        It contains a per-second history of RSRP values
        for the last 60 seconds."
    ::= { cwceLteRadioHistoryRsrpEntry 1 }

cwceLteRadioHistoryRsrpPerMinute OBJECT-TYPE
    SYNTAX OCTET STRING(SIZE(60))
--  Units
--    -dBm
    ACCESS read-only
    STATUS mandatory
    DESCRIPTION
        "This object indicates per-minute weakest RSRP value history.  
        It contains a per-minute history of weakest RSRP values for
        the last 60 minutes. The octet in the string is the weakest 
        RSRP value measured in a minute interval."
    ::= { cwceLteRadioHistoryRsrpEntry 2 }

cwceLteRadioHistoryRsrpPerHour OBJECT-TYPE
    SYNTAX OCTET STRING(SIZE(72))
--  Units
--    -dBm
    ACCESS read-only
    STATUS mandatory
    DESCRIPTION
        "This object indicates per-hour weakest RSRP value history.  
        It contains a per-hour history of weakest RSRP values for 
        the last 72 hours.  The octet in the string is the weakest 
        RSRP value measured in an hour interval."
    ::= { cwceLteRadioHistoryRsrpEntry 3 }

cwceLteRadioHistoryRsrqTable OBJECT-TYPE
    SYNTAX SEQUENCE OF CwceLteRadioHistoryRsrqEntry
    ACCESS not-accessible
    STATUS mandatory
    DESCRIPTION
        "This table contains Cellular 4G/LTE RSRQ history.
        The history of RSRQ are carried in an octet of string.
        Each octet in the octet string has a value from 3 to 20
        and the 25 value is reserved to indicate an uninitialized
        (Invalid) value.  The format of the octet string with n
        octets is as following:
           [ octet 0 is latest,
             octet 1 is latest-1,
             .
             .
             octet n-2 is oldest-1,
             octet n-1 is oldest ]
        
        To convert the provided value into dB the following formula
        should be used:
           dB = (-1)*value"
    ::= { cwceLteRadioHistory 2 }

cwceLteRadioHistoryRsrqEntry OBJECT-TYPE
    SYNTAX CwceLteRadioHistoryRsrqEntry
    ACCESS not-accessible
    STATUS mandatory
    DESCRIPTION
        "An entry contains management information of Cellular 
        4G/LTE RSRQ Radio history parameters.
        
        An entry of this table is created if an entity capable
        of providing operational Cellular 4G/LTE RSRQ Radio
        history is detected by the agent.
        
        An entry of this table is deleted by the agent if the
        corresponding entry in entPhysicalTable is removed."
    INDEX { entPhysicalIndex }
    ::= { cwceLteRadioHistoryRsrqTable 1 }

CwceLteRadioHistoryRsrqEntry ::= SEQUENCE {
    cwceLteRadioHistoryRsrqPerSecond OCTET STRING,
    cwceLteRadioHistoryRsrqPerMinute OCTET STRING,
    cwceLteRadioHistoryRsrqPerHour OCTET STRING
    }

cwceLteRadioHistoryRsrqPerSecond OBJECT-TYPE
    SYNTAX OCTET STRING(SIZE(60))
--  Units
--    -dB
    ACCESS read-only
    STATUS mandatory
    DESCRIPTION
        "This object indicates per-second RSRQ history.  
        It contains a per-second history of RSRQ values for 
        the last 60 seconds."
    ::= { cwceLteRadioHistoryRsrqEntry 1 }

cwceLteRadioHistoryRsrqPerMinute OBJECT-TYPE
    SYNTAX OCTET STRING(SIZE(60))
--  Units
--    -dB
    ACCESS read-only
    STATUS mandatory
    DESCRIPTION
        "This object indicates per-minute weakest RSRQ value history.  
        It contains a per-minute history of weakest RSRQ values
        for the last 60 minutes.  The octet in the string is the 
        weakest RSRQ value measured in a minute interval."
    ::= { cwceLteRadioHistoryRsrqEntry 2 }

cwceLteRadioHistoryRsrqPerHour OBJECT-TYPE
    SYNTAX OCTET STRING(SIZE(72))
--  Units
--    -dB
    ACCESS read-only
    STATUS mandatory
    DESCRIPTION
        "This object indicates per-hour weakest RSRQ value history.  
        It contains a per-hour history of weakest RSRQ values
        for the last 72 hours.  The octet in the string is
        the weakest RSRQ value measured in an hour interval."
    ::= { cwceLteRadioHistoryRsrqEntry 3 }

cwceLteIpv4AddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "The object indicates the type of Internet address for
        IPv4 addresses used by profiles and PDNs.
        
        The valid value for this object is ipv4(1)."
    ::= { cwceLteProfile 1 }

cwceLteIpv6AddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "The object indicates the type of Internet address for
        IPv6 addresses used by profiles and PDNs.
        
        The valid value for this object is ipv6(2)."
    ::= { cwceLteProfile 2 }

cwceLteProfileTable OBJECT-TYPE
    SYNTAX SEQUENCE OF CwceLteProfileEntry
    ACCESS not-accessible
    STATUS mandatory
    DESCRIPTION
        "This table contains Cellular LTE PDN profiles.  
        Cellular device contains multiple profile entries which can 
        be used to establish cellular data connections (PDN contexts).
        Users can choose any of available PDN profiles to establish 
        data connections. Data connections are described in 
        cwcePacketLteSessionTable.
        
        This table is valid only in 4G/LTE Technology mode."
    ::= { cwceLteProfile 3 }

cwceLteProfileEntry OBJECT-TYPE
    SYNTAX CwceLteProfileEntry
    ACCESS not-accessible
    STATUS mandatory
    DESCRIPTION
        "An entry contains management information of Cellular 
        4G/LTE profile parameters.
        
        Entries in this table can be created or deleted using
        cwceLteProfileRowStatus object.
        
        An entry of this table is deleted by the agent if the
        corresponding entry in entPhysicalTable is removed."
    INDEX { entPhysicalIndex, cwceLteProfileIndex }
    ::= { cwceLteProfileTable 1 }

CwceLteProfileEntry ::= SEQUENCE {
    cwceLteProfileIndex Gauge,
    cwceLteProfileType CiscoWanCellExtProtocolType,
    cwceLteProfileIPv4Addr InetAddress,
    cwceLteProfileIPv6Addr InetAddress,
    cwceLteProfileApn SnmpAdminString,
    cwceLteProfileApnAmbr Gauge,
    cwceLteProfileStorage StorageType,
    cwceLteProfileRowStatus RowStatus
    }

cwceLteProfileIndex OBJECT-TYPE
    SYNTAX Gauge(1..4294967295)
    ACCESS not-accessible
    STATUS mandatory
    DESCRIPTION
        "This object specifies profile index, combined with 
        entPhysicalIndex to access profile table."
    ::= { cwceLteProfileEntry 1 }

cwceLteProfileType OBJECT-TYPE
    SYNTAX CiscoWanCellExtProtocolType
--    Rsyntax INTEGER {
--        unknown(1),
--        ipv4(2),
--        ppp(3),
--        ipv6(4),
--        ipv4V6(5)
--        }
    ACCESS read-write
    STATUS mandatory
    DESCRIPTION
        "This object specifies the configured EPS Bearer type."
    ::= { cwceLteProfileEntry 2 }

cwceLteProfileIPv4Addr OBJECT-TYPE
    SYNTAX InetAddress
--    Rsyntax OCTET STRING(SIZE(0..255))
    ACCESS read-write
    STATUS mandatory
    DESCRIPTION
        "This object specifies the configured EPS Bearer IPv4 address.
        The type of this address is determined by the value of the
        cwceLteIpv4AddrType object.
        
        This object is valid only if the corresponding instance value
        of cwceLteProfileType is either 'ipv4' or 'ipv4V6'."
    ::= { cwceLteProfileEntry 3 }

cwceLteProfileIPv6Addr OBJECT-TYPE
    SYNTAX InetAddress
--    Rsyntax OCTET STRING(SIZE(0..255))
    ACCESS read-write
    STATUS mandatory
    DESCRIPTION
        "This object specifies the configured EPS Bearer IPv6 address.
        The type of this address is determined by the value of the
        cwceLteIpv6AddrType object.
        
        This object is valid only if the corresponding instance value
        of cwceLteProfileType is either 'ipv6' or 'ipv4V6'."
    ::= { cwceLteProfileEntry 4 }

cwceLteProfileApn OBJECT-TYPE
    SYNTAX SnmpAdminString(SIZE(0..64))
--    Rsyntax OCTET STRING(SIZE(0..64))
    ACCESS read-write
    STATUS mandatory
    DESCRIPTION
        "This object specifies configured profile of Access Point
        Name (APN).  The value of this object should be provided
        by the APN service provider."
    ::= { cwceLteProfileEntry 5 }

cwceLteProfileApnAmbr OBJECT-TYPE
    SYNTAX Gauge
    ACCESS read-write
    STATUS mandatory
    DESCRIPTION
        "This object specifies the profile APN-AMBR.
        APN-AMBR is aggregate bit rate across all Non-GBR bearers
        and across all PDN connections of the same APN. The value
        APN-AMBR is a parameter which is defined as part of a user's
        subscription, but may be overridden by the PCRF."
    ::= { cwceLteProfileEntry 6 }

cwceLteProfileStorage OBJECT-TYPE
    SYNTAX StorageType
--    Rsyntax INTEGER {
--        other(1),
--        volatile(2),
--        nonVolatile(3),
--        permanent(4),
--        readOnly(5)
--        }
    ACCESS read-write
    STATUS mandatory
    DESCRIPTION
        "This object specifies the storage type for this
        conceptual row."
    ::= { cwceLteProfileEntry 7 }

cwceLteProfileRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object specifies the status of the conceptual row.
        It's used to manage creation, modification and deletion
        of rows in this table.
        
        When a row is active, user cannot modify the value of the 
        objects in that row. All objects in this row need to have 
        valid value before the row can be active."
    ::= { cwceLteProfileEntry 8 }

cwceLtePdnTable OBJECT-TYPE
    SYNTAX SEQUENCE OF CwceLtePdnEntry
    ACCESS not-accessible
    STATUS mandatory
    DESCRIPTION
        "This table contains Cellular 4G/LTE Packet Data Network(PDN)
        information of all the PDN capable interfaces in the system."
    ::= { cwceLteProfile 4 }

cwceLtePdnEntry OBJECT-TYPE
    SYNTAX CwceLtePdnEntry
    ACCESS not-accessible
    STATUS mandatory
    DESCRIPTION
        "An entry contains management information of Cellular 
        4G/LTE PDN parameters.
        
        An entry of this table is created if an interface capable
        of providing operational Cellular 4G/LTE PDN parameters
        is detected by the agent.
        
        An entry of this table is deleted by the agent if the
        corresponding entry in ifTable is removed."
    INDEX { ifIndex }
    ::= { cwceLtePdnTable 1 }

CwceLtePdnEntry ::= SEQUENCE {
    cwceLtePdnProfileUsed Gauge,
    cwceLtePdnConnStatus INTEGER,
    cwceLtePdnType CiscoWanCellExtProtocolType,
    cwceLtePdnIpv4Addr InetAddress,
    cwceLtePdnIpv6Addr InetAddress,
    cwceLtePdnPriDnsIpv4Addr InetAddress,
    cwceLtePdnSecDnsIpv4Addr InetAddress,
    cwceLtePdnPriDnsIpv6Addr InetAddress,
    cwceLtePdnSecDnsIpv6Addr InetAddress
    }

cwceLtePdnProfileUsed OBJECT-TYPE
    SYNTAX Gauge
    ACCESS read-only
    STATUS mandatory
    DESCRIPTION
        "This object indicates the cwceLteProfileIndex of
        the profile used by current EPS bearer to
        establish data connection."
    ::= { cwceLtePdnEntry 2 }

cwceLtePdnConnStatus OBJECT-TYPE
    SYNTAX INTEGER {
        unknown(1),
        active(2),
        inactive(3)
        }
    ACCESS read-only
    STATUS mandatory
    DESCRIPTION
        "This object indicates PDN session status
        of the profile. This is active when the call is
        established and PDN context has become active."
    DEFVAL { inactive }
    ::= { cwceLtePdnEntry 3 }

cwceLtePdnType OBJECT-TYPE
    SYNTAX CiscoWanCellExtProtocolType
--    Rsyntax INTEGER {
--        unknown(1),
--        ipv4(2),
--        ppp(3),
--        ipv6(4),
--        ipv4V6(5)
--        }
    ACCESS read-only
    STATUS mandatory
    DESCRIPTION
        "This object indicates current session PDN type."
    ::= { cwceLtePdnEntry 4 }

cwceLtePdnIpv4Addr OBJECT-TYPE
    SYNTAX InetAddress
--    Rsyntax OCTET STRING(SIZE(0..255))
    ACCESS read-only
    STATUS mandatory
    DESCRIPTION
        "This object indicates current session
        EPS Bearer IPv4 address.
        The type of this address is determined by
        the value of the cwceLteIpv4AddrType object."
    ::= { cwceLtePdnEntry 5 }

cwceLtePdnIpv6Addr OBJECT-TYPE
    SYNTAX InetAddress
--    Rsyntax OCTET STRING(SIZE(0..255))
    ACCESS read-only
    STATUS mandatory
    DESCRIPTION
        "This object indicates current session
        EPS Bearer IPv6 address.
        The type of this address is determined by
        the value of the cwceLteIpv6AddrType object."
    ::= { cwceLtePdnEntry 6 }

cwceLtePdnPriDnsIpv4Addr OBJECT-TYPE
    SYNTAX InetAddress
--    Rsyntax OCTET STRING(SIZE(0..255))
    ACCESS read-only
    STATUS mandatory
    DESCRIPTION
        "This object indicates current session
        EPS Bearer Primary DNS IPv4 address.
        The type of this address is determined by
        the value of the cwceLteIpv4AddrType object."
    ::= { cwceLtePdnEntry 7 }

cwceLtePdnSecDnsIpv4Addr OBJECT-TYPE
    SYNTAX InetAddress
--    Rsyntax OCTET STRING(SIZE(0..255))
    ACCESS read-only
    STATUS mandatory
    DESCRIPTION
        "This object indicates current session
        EPS Bearer Secondary DNS IPv4 address.
        The type of this address is determined by
        the value of the cwceLteIpv4AddrType object."
    ::= { cwceLtePdnEntry 8 }

cwceLtePdnPriDnsIpv6Addr OBJECT-TYPE
    SYNTAX InetAddress
--    Rsyntax OCTET STRING(SIZE(0..255))
    ACCESS read-only
    STATUS mandatory
    DESCRIPTION
        "This object indicates current session
        EPS Bearer Primary DNS IPv6 address.
        The type of this address is determined by
        the value of the cwceLteIpv6AddrType object."
    ::= { cwceLtePdnEntry 9 }

cwceLtePdnSecDnsIpv6Addr OBJECT-TYPE
    SYNTAX InetAddress
--    Rsyntax OCTET STRING(SIZE(0..255))
    ACCESS read-only
    STATUS mandatory
    DESCRIPTION
        "This object indicates current session
        EPS Bearer Secondary DNS IPv6 address.
        The type of this address is determined by
        the value of the cwceLteIpv6AddrType object."
    ::= { cwceLtePdnEntry 10 }

cwceLteEpsBearerQosTable OBJECT-TYPE
    SYNTAX SEQUENCE OF CwceLteEpsBearerQosEntry
    ACCESS not-accessible
    STATUS mandatory
    DESCRIPTION
        "This table contains 4G/LTE QoS parameters
        requested by modem to the cellular network 
        via PDN Context Activation Request message."
    ::= { cwceLteProfile 5 }

cwceLteEpsBearerQosEntry OBJECT-TYPE
    SYNTAX CwceLteEpsBearerQosEntry
    ACCESS not-accessible
    STATUS mandatory
    DESCRIPTION
        "An entry contains management information of Cellular 
        4G/LTE QoS parameters.
        
        An entry of this table is created if an interface
        capable of providing operational Cellular 4G/LTE
        QoS parameters is detected by the agent.
        
        An entry of this table is deleted by the agent
        if the corresponding entry in ifTable is removed."
    INDEX { ifIndex, cwceLteEpsBearerId }
    ::= { cwceLteEpsBearerQosTable 1 }

CwceLteEpsBearerQosEntry ::= SEQUENCE {
    cwceLteEpsBearerId Gauge,
    cwceLteEpsBearerType INTEGER,
    cwceLteEpsQCI Gauge,
    cwceLteEpsArp Gauge,
    cwceLteEpsBearerResType INTEGER,
    cwceLteEpsGbr Gauge,
    cwceLteEpsMbr Gauge,
    cwceLteEpsAmbr Gauge,
    cwceLteEpsTotalBytesTx Counter,
    cwceLteEpsTotalBytesRx Counter,
    cwceLteEpsPacketsTx Counter,
    cwceLteEpsPacketsRx Counter
    }

cwceLteEpsBearerId OBJECT-TYPE
    SYNTAX Gauge(1..4294967295)
    ACCESS not-accessible
    STATUS mandatory
    DESCRIPTION
        "This object indicates the EPS Bearer Identity which is
        allocated by the Mobility Management Entity (MME)."
    ::= { cwceLteEpsBearerQosEntry 1 }

cwceLteEpsBearerType OBJECT-TYPE
    SYNTAX INTEGER {
        gbr(1),
        nonGbr(2),
        unknown(3)
        }
    ACCESS read-only
    STATUS mandatory
    DESCRIPTION
        "This object indicates the type of bearers.
        
        gbr     - Guaranteed Bit Rate(GBR).
                  GBR bearer has a minimum amount of bandwidth that
                  is reserved by the network, and these resources are
                  always consumed in a radio base station regardless
                  of whether it is used or not.
        
        nonGbr  - non-Guaranteed Bit Rate(Non-GBR).
                  Non-GBR bearers are for best-effort services and do
                  not consume any network
                  resources.
        
        unknown - the type of bearers is unknown."
    ::= { cwceLteEpsBearerQosEntry 2 }

cwceLteEpsQCI OBJECT-TYPE
    SYNTAX Gauge
    ACCESS read-only
    STATUS mandatory
    DESCRIPTION
        "This object indicates the QoS Class Identifier(QCI).
        The QCI along with the ARP characterizes the QoS of
        the bearer."
    ::= { cwceLteEpsBearerQosEntry 3 }

cwceLteEpsArp OBJECT-TYPE
    SYNTAX Gauge
    ACCESS read-only
    STATUS mandatory
    DESCRIPTION
        "This object indicates the Allocation and Retention
        Priority(ARP).
        ARP is a QoS parameter designed to facilitate decisions
        as to whether a bearer establishment/modification request
        can be accepted."
    ::= { cwceLteEpsBearerQosEntry 4 }

cwceLteEpsBearerResType OBJECT-TYPE
    SYNTAX INTEGER {
        defaultBearer(1),
        dedicatedBearer(2),
        unknown(3)
        }
    ACCESS read-only
    STATUS mandatory
    DESCRIPTION
        "This object indicates the Bearer resource type."
    ::= { cwceLteEpsBearerQosEntry 5 }

cwceLteEpsGbr OBJECT-TYPE
    SYNTAX Gauge
    ACCESS read-only
    STATUS mandatory
    DESCRIPTION
        "This object indicates the Guaranteed Bit Rate(GBR) which
        determines the resource reservation to guarantee a
        given data rate."
    ::= { cwceLteEpsBearerQosEntry 6 }

cwceLteEpsMbr OBJECT-TYPE
    SYNTAX Gauge
    ACCESS read-only
    STATUS mandatory
    DESCRIPTION
        "This object indicates the Maximum Bit Rate(MBR) which is
        used for policing the user traffic."
    ::= { cwceLteEpsBearerQosEntry 7 }

cwceLteEpsAmbr OBJECT-TYPE
    SYNTAX Gauge
    ACCESS read-only
    STATUS mandatory
    DESCRIPTION
        "This object indicates the Aggregated Maximum Bit Rate.
        This object is valid only if the value of the corresponding
        cwceLteEpsBearerResType is 'defaultBearer'."
    ::= { cwceLteEpsBearerQosEntry 8 }

cwceLteEpsTotalBytesTx OBJECT-TYPE
    SYNTAX --?? syntax is not convertable to SMIv1
           Counter
--  Units
--    bytes
    ACCESS read-only
    STATUS mandatory
    DESCRIPTION
        "This object indicates the total data bytes transmitted
        by this bearer."
    ::= { cwceLteEpsBearerQosEntry 9 }

cwceLteEpsTotalBytesRx OBJECT-TYPE
    SYNTAX --?? syntax is not convertable to SMIv1
           Counter
--  Units
--    bytes
    ACCESS read-only
    STATUS mandatory
    DESCRIPTION
        "This object indicates the total data bytes received
        by this bearer."
    ::= { cwceLteEpsBearerQosEntry 10 }

cwceLteEpsPacketsTx OBJECT-TYPE
    SYNTAX --?? syntax is not convertable to SMIv1
           Counter
--  Units
--    packets
    ACCESS read-only
    STATUS mandatory
    DESCRIPTION
        "This object indicates the number of packets transmitted
        by this bearer."
    ::= { cwceLteEpsBearerQosEntry 11 }

cwceLteEpsPacketsRx OBJECT-TYPE
    SYNTAX --?? syntax is not convertable to SMIv1
           Counter
--  Units
--    packets
    ACCESS read-only
    STATUS mandatory
    DESCRIPTION
        "This object indicates the number of packets received
        by this bearer."
    ::= { cwceLteEpsBearerQosEntry 12 }

cwceLteRsrqOnsetNotif TRAP-TYPE
-- Reverse mappable trap
    ENTERPRISE ciscoWanCellExtMIB
    VARIABLES {
        entPhysicalName, cwceLteRsrqOnsetNotifFlag, 
        cwceLteNotifRsrq, cwceLteRsrqOnsetNotifThreshold }
--  Status
--    mandatory
    DESCRIPTION
        "If RSRQ goes below cwceLteRsrqOnsetNotifThreshold
        and the service bit in cwceLteRsrqOnsetNotifFlag
        is set, this notification will be generated. Object
        cwceLteRsrqOnsetNotifFlag will indicate which service
        generates this notification and the associated RSRQ
        will be reported in cwceLteNotifRsrq. Please note
        that cwceLteNotifRsrq is used to indicate the
        RSRQ value that triggers the notification, user
        should go to the corresponding radio table to
        get the current RSRQ value."
    ::= 1

cwceLteRsrqAbateNotif TRAP-TYPE
-- Reverse mappable trap
    ENTERPRISE ciscoWanCellExtMIB
    VARIABLES {
        entPhysicalName, cwceLteRsrqAbateNotifFlag, 
        cwceLteNotifRsrq, cwceLteRsrqAbateNotifThreshold }
--  Status
--    mandatory
    DESCRIPTION
        "If RSRQ goes above cwceLteRsrqAbateNotifThreshold
        and the service bit in cwceLteRsrqOnsetNotifFlag
        is set, this notification will be generated. Object
        cwceLteRsrqAbateNotifFlag will indicate which service
        generates this notification and the associated RSRQ
        will be reported in cwceLteNotifRsrq. Please
        note that cwceLteNotifRsrq is used to indicate
        the RSRQ value that triggers the notification,
        user should go to the corresponding radio table to
        get the current RSRQ value."
    ::= 2

cwceLteRsrpOnsetNotif TRAP-TYPE
-- Reverse mappable trap
    ENTERPRISE ciscoWanCellExtMIB
    VARIABLES {
        entPhysicalName, cwceLteRsrpOnsetNotifFlag, 
        cwceLteNotifRsrp, cwceLteRsrpOnsetNotifThreshold }
--  Status
--    mandatory
    DESCRIPTION
        "If RSRP goes below cwceLteRsrpOnsetNotifThreshold
        and the service bit in cwceLteRsrpOnsetNotifFlag
        is set, this notification will be generated. Object
        cwceLteRsrpOnsetNotifFlag will indicate which service
        generates this notification and the associated RSRP
        will be reported in cwceLteNotifRsrp. Please
        note that cwceLteNotifRsrp is used to indicate
        the RSRP value that triggers the notification,
        user should go to the
        corresponding radio table to get the current RSRP
        value."
    ::= 3

cwceLteRsrpAbateNotif TRAP-TYPE
-- Reverse mappable trap
    ENTERPRISE ciscoWanCellExtMIB
    VARIABLES {
        entPhysicalName, cwceLteRsrpAbateNotifFlag, 
        cwceLteNotifRsrp, cwceLteRsrpAbateNotifThreshold }
--  Status
--    mandatory
    DESCRIPTION
        "If RSRP goes above cwceLteRsrqAbateNotifThreshold
        and the service bit in cwceLteRsrpOnsetNotifFlag
        is set, this notification will be generated. Object
        cwceLteRsrpAbateNotifFlag will indicate which service
        generates this notification and the associated RSRP
        will be reported in cwceLteNotifRsrp. Please
        note that cwceLteNotifRsrp is used to indicate
        the RSRP value that triggers the notification,
        user should go to the corresponding radio table to
        get the current RSRP value."
    ::= 4

ciscoWanCellExtMIBLteObjectGroup OBJECT IDENTIFIER ::= { ciscoWanCellExtMIBGroups 1 }
-- OBJECT-GROUP
--  Status
--    mandatory
--  Descr
--    A collection of objects for Cellular 4G/LTE.
--  objects
--    cwceLteCurrRsrp, cwceLteCurrRsrq, cwceLteCurrSnr, 
--    cwceLteCurrSinr, cwceLteCurrCqiIndex, cwceLteNotifRsrp, 
--    cwceLteNotifRsrq, cwceLteRsrpOnsetNotifThreshold, 
--    cwceLteRsrpAbateNotifThreshold, 
--    cwceLteRsrqOnsetNotifThreshold, 
--    cwceLteRsrqAbateNotifThreshold, cwceLteRsrpOnsetNotifFlag, 
--    cwceLteRsrpAbateNotifFlag, cwceLteRsrqOnsetNotifFlag, 
--    cwceLteRsrqAbateNotifFlag, cwceLteCurrOperatingBand, 
--    cwceLteRadioHistoryRsrpPerSecond, 
--    cwceLteRadioHistoryRsrpPerMinute, 
--    cwceLteRadioHistoryRsrpPerHour, 
--    cwceLteRadioHistoryRsrqPerSecond, 
--    cwceLteRadioHistoryRsrqPerMinute, 
--    cwceLteRadioHistoryRsrqPerHour, cwceLteIpv4AddrType, 
--    cwceLteIpv6AddrType, cwceLteProfileType, 
--    cwceLteProfileIPv4Addr, cwceLteProfileIPv6Addr, 
--    cwceLteProfileApn, cwceLteProfileApnAmbr, 
--    cwceLteProfileStorage, cwceLteProfileRowStatus, 
--    cwceLtePdnProfileUsed, cwceLtePdnConnStatus, cwceLtePdnType, 
--    cwceLtePdnIpv4Addr, cwceLtePdnIpv6Addr, 
--    cwceLtePdnPriDnsIpv4Addr, cwceLtePdnSecDnsIpv4Addr, 
--    cwceLtePdnPriDnsIpv6Addr, cwceLtePdnSecDnsIpv6Addr, 
--    cwceLteEpsBearerType, cwceLteEpsArp, cwceLteEpsQCI, 
--    cwceLteEpsBearerResType, cwceLteEpsGbr, cwceLteEpsMbr, 
--    cwceLteEpsAmbr, cwceLteEpsTotalBytesTx, 
--    cwceLteEpsTotalBytesRx, cwceLteEpsPacketsTx, 
--    cwceLteEpsPacketsRx

ciscoWanCellExtMIBNotificationGroup OBJECT IDENTIFIER ::= { ciscoWanCellExtMIBGroups 2 }
-- NOTIFICATION-GROUP
--  Status
--    mandatory
--  Descr
--    A collection of objects for Cellular WAN
--    notifications.
--  notifications
--    cwceLteRsrqOnsetNotif, cwceLteRsrqAbateNotif, 
--    cwceLteRsrpOnsetNotif, cwceLteRsrpAbateNotif

ciscoWanCellExtMIBCompliance OBJECT IDENTIFIER ::= { ciscoWanCellExtMIBCompliances 1 }
-- MODULE-COMPLIANCE
--  Status
--    mandatory
--  Descr
--    The compliance statement for the
--    CISCO-WAN-CELL-EXT-MIB.
--  Module
--    >>current<<
--   MandGroup
--    ciscoWanCellExtMIBNotificationGroup
--   MandGroup
--    ciscoWanCellExtMIBLteObjectGroup
--   ObjVar
--    cwceLteRsrpOnsetNotifThreshold
--   ObjVar
--    cwceLteRsrpAbateNotifThreshold
--   ObjVar
--    cwceLteRsrqOnsetNotifThreshold
--   ObjVar
--    cwceLteRsrqAbateNotifThreshold
--   ObjVar
--    cwceLteRsrpOnsetNotifFlag
--   ObjVar
--    cwceLteRsrpAbateNotifFlag
--   ObjVar
--    cwceLteRsrqOnsetNotifFlag
--   ObjVar
--    cwceLteRsrqAbateNotifFlag
--   ObjVar
--    cwceLteProfileType
--   ObjVar
--    cwceLteProfileIPv4Addr
--   ObjVar
--    cwceLteProfileIPv6Addr
--   ObjVar
--    cwceLteProfileApn
--   ObjVar
--    cwceLteProfileApnAmbr
--   ObjVar
--    cwceLteProfileStorage
--   ObjVar
--    cwceLteProfileRowStatus


END
