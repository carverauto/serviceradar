-- MIB file created 30-Aug-2004 15:51:07, by
--   SMICng version 2.2.11-beta(PRO)(Solaris), January 20, 2001. Enterprise key cisco.com

CISCO-MGX8800-IF-MAPPING-MIB DEFINITIONS ::= BEGIN

-- From file: "CISCO-MGX8800-IF-MAPPING-MIB.my"
-- Compile options "4 7 F H N W 03 06 0B 0G 0N 0T"

IMPORTS
    InterfaceIndex
            FROM IF-MIB
    ciscoWan
            FROM CISCOWAN-SMI
    Gauge
            FROM RFC1155-SMI
    OBJECT-TYPE
            FROM RFC-1212;

ciscoMGX8800IfMappingMIB OBJECT IDENTIFIER ::= { ciscoWan 7 }
-- MODULE-IDENTITY
--  LastUpdated
--    200405250000Z
--  OrgName
--    Cisco Systems, Inc.
--  ContactInfo
--               Cisco Systems
--                Customer Service
--    
--        Postal: 170 W Tasman Drive
--                San Jose, CA  95134
--                USA
--    
--           Tel: +1 800 553-NETS
--    
--        E-mail: cs-wanatm@cisco.com
--  Descr
--    This MIB module is used for getting the ifIndex values 
--     given physical location and/or logical information.
--     The physical information includes the slot, back-card
--     and physical line, IMA group ID, MFR (Multilink Frame Relay)
--     bundle etc. The logical information includes the logical 
--     interface or virtual interface number.
--    
--     In this MIB back card, bay, line module are used to
--     refer to the back card.
--  RevDate
--    200405250000Z
--  RevDescr
--    Added following enums to CmimIfType:
--        lapd(24). 
--  RevDate
--    200404300000Z
--  RevDescr
--    Added following enums to CmimIfType:
--        ppplink(22), pppMultilinkBundle(23), 
--  RevDate
--    200312040000Z
--  RevDescr
--    Added new enum mfrBundle(21) to CmimIfType.
--  RevDate
--    200303200000Z
--  RevDescr
--    Fixed alignments and descriptions.
--  RevDate
--    200210210000Z
--  RevDescr
--    1. Added following enums to CmimIfType:
--        ds1VTPath(18), ds1Ds3SonetPath(19) and atmVciEndPt(20)
--     2. Modified description for cmimModuleIndex, CmimIfType
--        and cmimIfNumber to describe the rules to form a
--        query to obtain ifIndex for ds1VTPath, ds1Ds3SonetPath
--        and atmVciEndPt.
--  RevDate
--    200210160000Z
--  RevDescr
--    1. Added following enums to CmimIfType:
--        frameRelayPort(16), ces(17).
--     2. Modified description for cmimModuleIndex, CmimIfType
--        and cmimIfNumber to describe the rules to form a
--        query to obtain ifIndex for frame relay and ces 
--        interfaces.
--  RevDate
--    200205210000Z
--  RevDescr
--    1. Added following enums to CmimIfType:
--        sonetPath(12), ds3SonetPath(13),
--        atmSonetPath(14), atmDs3SonetPath(15).
--     2. Modified description for cmimModuleIndex, CmimIfType
--        and cmimIfNumber to describe the rules to form a
--        query to obtain ifIndex for SONET Path, ds3 path on 
--        a SONET path and corresponding ATM Cell layers.
--     3. Imported Unsigned32 from SNMPv2-SMI instead of 
--        CISCO-TC.
--  RevDate
--    200202170000Z
--  RevDescr
--    Added enums srmBertLine(10) and srmBertPort(11) to CmimIfType
--     and modified descriptions of cmimIfNumber and CmimIfType, 
--     explaining how to discover the interface indexes of  
--     physical lines and logical ports of narrow-band service 
--     modules (NBSM) that obtain BERT service through Service 
--     Resource Module (SRM).
--  RevDate
--    200110160000Z
--  RevDescr
--    Added enum sonetVT(8) and imaGrpAtmPhy(9) for CmimIfType,
--     and modified descriptions for cmimIfNumber and CmimIfType.
--  RevDate
--    200107080000Z
--  RevDescr
--    Added following enumerations to Textual-convention CmimIfType:
--     adjCardApsLine(6), propAtm(7).
--  RevDate
--    200002120000Z
--  RevDescr
--    Initial version of this MIB Module

cmimMappingObjects OBJECT IDENTIFIER ::= { ciscoMGX8800IfMappingMIB 1 }
cmimPhysToIf    OBJECT IDENTIFIER ::= { cmimMappingObjects 1 }
cmimPhysToIfMIBConformance OBJECT IDENTIFIER ::= { ciscoMGX8800IfMappingMIB 3 }
cmimPhysToIfMIBCompliances OBJECT IDENTIFIER ::= { cmimPhysToIfMIBConformance 1 }
cmimPhysToIfMIBGroups OBJECT IDENTIFIER ::= { cmimPhysToIfMIBConformance 2 }

CmimIfType ::= INTEGER {
        physicalLine(1),
        atmIma(2),
        atm(3),
        atmVirtual(4),
        ds1Inds3(5),
        adjCardApsLine(6),
        propAtm(7),
        sonetVT(8),
        imaGrpAtmPhy(9),
        srmBertLine(10),
        srmBertPort(11),
        sonetPath(12),
        ds3SonetPath(13),
        atmSonetPath(14),
        atmDs3SonetPath(15),
        frameRelayPort(16),
        ces(17),
        ds1VTPath(18),
        ds1Ds3SonetPath(19),
        atmVciEndPt(20),
        mfrBundle(21),
        ppplink(22),
        pppMpbundle(23),
        lapd(24)
        }
-- TEXTUAL-CONVENTION
--  Status
--    mandatory
--  Descr
--    The interface types.

cmimPhysToIfTable OBJECT-TYPE
    SYNTAX SEQUENCE OF CmimPhysToIfEntry
    ACCESS not-accessible
    STATUS mandatory
    DESCRIPTION
        "This table contains one or more rows, representing 
         mappings of physical or logical interfaces to ifIndex
         values."
    ::= { cmimPhysToIf 1 }

cmimPhysToIfEntry OBJECT-TYPE
    SYNTAX CmimPhysToIfEntry
    ACCESS not-accessible
    STATUS mandatory
    DESCRIPTION
        "Information about a particular physical interface or 
         logical interface."
    INDEX { cmimModuleIndex, cmimIfNumber, cmimIfType }
    ::= { cmimPhysToIfTable 1 }

CmimPhysToIfEntry ::= SEQUENCE {
    cmimModuleIndex Gauge,
    cmimIfNumber Gauge,
    cmimIfType CmimIfType,
    cmimIfIndex InterfaceIndex
    }

cmimModuleIndex OBJECT-TYPE
    SYNTAX Gauge
    ACCESS not-accessible
    STATUS mandatory
    DESCRIPTION
        "An index value that uniquely identifies the location 
         of the module or a physical line.
         It has the information on slot number, back card
         and physical line number. Following is the mapping 
         used for this object.
        
         Mapping used when cmimIfType is physicalLine(1), atm(3),
         adjCardApsLine(6), imaGrpAtmPhy(9) and mfrBundle(21)
        
          Bits 0-7   : Ignored
          Bits 8-15  : Back Card Number (0 - Ignored, 1-Top Back card
                                         2 - Bottom Back card)
          Bits 16-23 : Logical slot number
          Bits 24-31 : Shelf number
                       (1 - Currently, only value 1 is supported)
        
          Mapping used when cmimIfType is set to ds1Inds3(5),
          sonetVT(8), sonetPath(12), ds3SonetPath(13), 
          atmSonetPath(14), atmDs3SonetPath(15), ds1VTPath(18),
          ds1Ds3SonetPath(19) and lapd(24)
        
          Bits 0-7   : DS3/E3/Sonet/Sdh physical line number
          Bits 8-15  : Back Card Number (0 - Ignored, 1-Top Back card
                                         2 - Bottom Back card.
          Bits 16-23 : Logical slot number
          Bits 24-31 : Shelf number 
                       (1 - Currently, only value 1 is supported)
        
          Mapping used when cmimIfType is set to propAtm(7),
          frameRelayPort(16), ces(17), atmVciEndPt(20), ppplink(22)
          and pppMpbundle(23).
        
          Bits 0-7   : 0  Ignored
          Bits 8-15  : 0  Ignored
          Bits 16-23 : Logical slot number
          Bits 24-31 : Shelf number (1 - only value 1 is supported)
        
          Mapping used when cmimIfType is set to srmBertLine(10) or
          srmBertPort(11) 
        
          Bits 0-7   : 0  Ignored
          Bits 8-15  : Logical slot number of NBSM
          Bits 16-23 : Logical slot number of SRM
          Bits 24-31 : Shelf number (1 - only value 1 is supported)"
    ::= { cmimPhysToIfEntry 1 }

cmimIfNumber OBJECT-TYPE
    SYNTAX Gauge
    ACCESS not-accessible
    STATUS mandatory
    DESCRIPTION
        "An index value uniquely identifies the interface
         number (physical, logical) of the module. The 
         value specified depends on the value specified in 
         cmimIfType.
        
         cmimIfType             cmimIfNumber
         ----------              ------------
        
         physicalLine(1)         physical line number
         atm(3)                  physical line number for atm phy 
                                 number
         ds1Inds3(5)             DS1/E1 line number in a DS3/E3
         adjCardApsLine(6)       adjacent card APS line number
         propAtm(7)              set to 1, this is the only value
                                 supported at this time
         sonetVT(8)              DSxN tributary in a sonet/sdh line
         imaGrpAtmPhy(9)         atm ima group for atm phy number
         srmBertLine(10)         physical line number of NBSM
         srmBertPort(11)         logical port number of NBSM.
         sonetPath(12)           STS-1/AU-3 Path Number
         atmSonetPath(14)        STS-1/AU-3 Path Number   
         ds3SonetPath(13)        Bits 0..15 : STS-1/AU-3 Path Number
                                 Bits 16..31: 1 for STS-1/AU-3 
                                 or DS3 Number within AU-4 
         atmDs3SonetPath(15)     Bits 0..15 : STS-1/AU-3 Path Number
                                 Bits 16..31: 1 for STS-1/AU-3 
                                 or DS3 Number within AU-4
         frameRelayPort(16)      logical port number for frame 
                                 interface
         ces(17)                 logical port number of circuit
                                 emulation service interface
         ds1InVT(18)             Bits 0..7 :  VT Number
                                 Bits 8..15:  VT group number
                                 Bits 16..31: STS-1/AU-3 Path Number
         ds1Ds3SonetPath(19)     Bits 0..7 :  ds1 Number
                                 Bits 8..15:  ds3 Number
                                 Bits 16..31: STS Path Number
         atmVciEndPt(20)         Bits 0..15 : VCI 
                                 Bits 16..27: VPI 
                                 Bits 28..31: Port(ATM)
         mfrBundle(21)           Multilink Frame Relay bundle number
         ppplink(22)             ppp index of the ppp interface
         pppMpbundle(23)         mpbundle index of the mpbundle 
                                 interface 
         lapd(24)                Bits 0..7  : ds0 number
                                 Bits 8..15 : VT number or ds1 number
                                 Bits 16..23: VT group (DS3 ignore it) 
                                 Bits 24..31: STS or DS3 path"
    ::= { cmimPhysToIfEntry 2 }

cmimIfType OBJECT-TYPE
    SYNTAX CmimIfType
--    Rsyntax INTEGER {
--        physicalLine(1),
--        atmIma(2),
--        atm(3),
--        atmVirtual(4),
--        ds1Inds3(5),
--        adjCardApsLine(6),
--        propAtm(7),
--        sonetVT(8),
--        imaGrpAtmPhy(9),
--        srmBertLine(10),
--        srmBertPort(11),
--        sonetPath(12),
--        ds3SonetPath(13),
--        atmSonetPath(14),
--        atmDs3SonetPath(15),
--        frameRelayPort(16),
--        ces(17),
--        ds1VTPath(18),
--        ds1Ds3SonetPath(19),
--        atmVciEndPt(20),
--        mfrBundle(21),
--        ppplink(22),
--        pppMpbundle(23),
--        lapd(24)
--        }
    ACCESS not-accessible
    STATUS mandatory
    DESCRIPTION
        "The type of interface specified by cmimIfNumber."
    ::= { cmimPhysToIfEntry 3 }

cmimIfIndex OBJECT-TYPE
    SYNTAX InterfaceIndex
--    Rsyntax INTEGER(1..2147483647)
    ACCESS read-only
    STATUS mandatory
    DESCRIPTION
        "The value of the instance of the ifIndex object,
         defined in MIB-II, for the interface corresponding
         to the INDEXes specified in the table.
        
         Note that the values returned for cmimIfType=srmBertLine(10) 
         and cmimIfType=srmBertPort(11) will not have any entries 
         in the IF-TABLE."
    ::= { cmimPhysToIfEntry 4 }

cmimPhysToIfMIBGroup OBJECT IDENTIFIER ::= { cmimPhysToIfMIBGroups 1 }
-- OBJECT-GROUP
--  Status
--    mandatory
--  Descr
--    This group has to be implemented on all MGX8800 
--     series products.
--  objects
--    cmimIfIndex

cmimPhysToIfMIBCompliance OBJECT IDENTIFIER ::= { cmimPhysToIfMIBCompliances 1 }
-- MODULE-COMPLIANCE
--  Status
--    mandatory
--  Descr
--    The compliance statement for cmimPhystoIfTable.
--  Module
--    >>current<<
--   MandGroup
--    cmimPhysToIfMIBGroup


END
