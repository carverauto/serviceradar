-- MIB file created 31-May-2006 16:39:47, by
--   SMICng version 2.2.11-beta(PRO)(Solaris), January 20, 2001. Enterprise key cisco.com

PCUBE-SMI DEFINITIONS ::= BEGIN

-- From file: "PCUBE-SMI.my"
-- Compile options "4 7 F H N O W 03 06 0B 0G 0N 0T"

IMPORTS
    enterprises
            FROM SNMPv2-SMI-v1;

pcube OBJECT IDENTIFIER ::= { enterprises 5655 }
-- MODULE-IDENTITY
--  LastUpdated
--    200201142000Z
--  OrgName
--    Cisco Systems, Inc.
--  ContactInfo
--    Cisco Systems 
--     Customer Service 
--    
--    Postal: 170 W Tasman Drive 
--            San Jose, CA  95134 
--            USA 
--    
--    Tel: +1 800 553-NETS 
--    
--    E-mail: cs-sce@cisco.com
--  Descr
--    The Structure of Management Information for the 
--    Pcube enterprise.
--  RevDate
--    200201142000Z
--  RevDescr
--    Initial version of this MIB module.

pcubeProducts OBJECT IDENTIFIER ::= { pcube 1 }
-- OBJECT-IDENTITY
--  Status
--    mandatory
--  Descr
--    pcubeProducts is the root OBJECT IDENTIFIER from 
--    which sysObjectID values are assigned.  Actual 
--    values are defined in PCUBE-PRODUCTS-MIB.

pcubeModules OBJECT IDENTIFIER ::= { pcube 2 }
-- OBJECT-IDENTITY
--  Status
--    mandatory
--  Descr
--    pcubeModules provides a root object identifier 
--    from which MODULE-IDENTITY values may be assigned.

pcubeMgmt OBJECT IDENTIFIER ::= { pcube 3 }
-- OBJECT-IDENTITY
--  Status
--    mandatory
--  Descr
--    pcubeMgmt is the main subtree for new MIB development.

pcubeWorkgroup OBJECT IDENTIFIER ::= { pcube 4 }
-- OBJECT-IDENTITY
--  Status
--    mandatory
--  Descr
--    pcubeWorkgroup is the main subtree for objects and events of 
--    P-Cube's products.


END
