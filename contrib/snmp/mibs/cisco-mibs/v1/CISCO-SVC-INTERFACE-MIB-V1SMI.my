-- MIB file created 30-Jun-2005 00:30:14, by
--   SMICng version 2.2.11-beta(PRO)(Solaris), January 20, 2001. Enterprise key cisco.com

CISCO-SVC-INTERFACE-MIB DEFINITIONS ::= BEGIN

-- From file: "CISCO-SVC-INTERFACE-MIB.my"
-- Compile options "4 7 F H N O W 03 06 0B 0G 0N 0T"

IMPORTS
    RowStatus
            FROM SNMPv2-TC-v1
    SnmpAdminString
            FROM SNMP-FRAMEWORK-MIB
    FcNameId, VsanIndex
            FROM CISCO-ST-TC
    InterfaceIndex
            FROM IF-MIB
    ciscoMgmt
            FROM CISCO-SMI
    Counter, Gauge
            FROM RFC1155-SMI
    OBJECT-TYPE
            FROM RFC-1212
    TRAP-TYPE
            FROM RFC-1215;

ciscoSvcInterfaceMIB OBJECT IDENTIFIER ::= { ciscoMgmt 378 }
-- MODULE-IDENTITY
--  LastUpdated
--    200409210000Z
--  OrgName
--    Cisco Systems Inc. 
--  ContactInfo
--    Cisco Systems
--     Postal: 170 W Tasman Drive
--     San Jose, CA  95134
--     USA
--     Tel: +1 800 553 -NETS
--     E-mail: cs-san@cisco.com
--  Descr
--    MIB module for displaying and configuring 
--        SVC (SAN Volume Controller) related features 
--        in the Storage Area Network (SAN) switches.
--    
--        SVC is the SAN Volume Controller that implements 
--        the specialized virtualization and caching
--        features for storage attached to a SAN.
--  RevDate
--    200409210000Z
--  RevDescr
--    Initial version of this MIB module.

ciscoSvcInterfaceMIBObjects OBJECT IDENTIFIER ::= { ciscoSvcInterfaceMIB 1 }
ciscoSvcInterfaceMIBTrapPrefix OBJECT IDENTIFIER ::= { ciscoSvcInterfaceMIB 2 }
cSvcInterfaceConfiguration OBJECT IDENTIFIER ::= { ciscoSvcInterfaceMIBObjects 1 }
cSvcInterfaceTrapObjects OBJECT IDENTIFIER ::= { ciscoSvcInterfaceMIBObjects 2 }
csiMIBTraps     OBJECT IDENTIFIER ::= { ciscoSvcInterfaceMIBTrapPrefix 0 }
ciscoSvcMIBConformance OBJECT IDENTIFIER ::= { ciscoSvcInterfaceMIB 3 }
ciscoSvcMIBCompliances OBJECT IDENTIFIER ::= { ciscoSvcMIBConformance 1 }
ciscoSvcMIBGroups OBJECT IDENTIFIER ::= { ciscoSvcMIBConformance 2 }

NportType ::= INTEGER(1..3)
-- TEXTUAL-CONVENTION
--  Status
--    mandatory
--  Descr
--    Type of the virtual N-port. 
--    
--    The types are 
--    
--    1 = Initiator
--    2 = Target
--    3 = Mgmt 

csiNportTable OBJECT-TYPE
    SYNTAX SEQUENCE OF CsiNportEntry
    ACCESS not-accessible
    STATUS mandatory
    DESCRIPTION
        "A table that lets the user configure 
         and monitor the virtual N-ports. 
        
         A virtual N-port is a logical entity within an SVC 
         line card that simulates a real Fibre Channel
         N-port."
    ::= { cSvcInterfaceConfiguration 1 }

csiNportEntry OBJECT-TYPE
    SYNTAX CsiNportEntry
    ACCESS not-accessible
    STATUS mandatory
    DESCRIPTION
        "An entry in the csiNportTable, that describes a virtual 
         N-port. Each virtual N-port is identified by the
         ifIndex of the SVC interface on the SVC line card,
         the type of N-port and the VSAN id of the VSAN it
         belongs to.
        
         Each virtual N-port also has a Fibre Channel Identifier,
         operational state and a WWN (Worldwide Name)."
    INDEX { csiNportIfIndex, csiNportType, csiNportVsanId }
    ::= { csiNportTable 1 }

CsiNportEntry ::= SEQUENCE {
    csiNportIfIndex InterfaceIndex,
    csiNportType NportType,
    csiNportVsanId VsanIndex,
    csiNportPwwn FcNameId,
    csiNportFcid INTEGER,
    csiNportState INTEGER,
    csiNportDownReason INTEGER,
    csiNportRowStatus RowStatus
    }

csiNportIfIndex OBJECT-TYPE
    SYNTAX InterfaceIndex
--    Rsyntax INTEGER(1..2147483647)
    ACCESS not-accessible
    STATUS mandatory
    DESCRIPTION
        "The ifIndex of the SVC interface to which this Nport
         belongs to. 
        
         A SVC interface is a FC interface that implements 
         virtualization and caching. Note that the ifType of
         this interface is fiberChannel (56)."
    ::= { csiNportEntry 1 }

csiNportType OBJECT-TYPE
    SYNTAX NportType
--    Rsyntax INTEGER(1..3)
    ACCESS not-accessible
    STATUS mandatory
    DESCRIPTION
        "The type of this N-port.
        
         There are 3 types of Nport -
        
         initiator - Initiates communication with SCSI 
                     (Small Computer Systems Interface)
                     targets.
        
         target    - Responds to the communication from the 
                     FC-SCSI initiators.
        
         mgmt      - Communicates with other SVC interfaces."
    ::= { csiNportEntry 2 }

csiNportVsanId OBJECT-TYPE
    SYNTAX VsanIndex
--    Rsyntax INTEGER(1..4094)
    ACCESS not-accessible
    STATUS mandatory
    DESCRIPTION
        "The VSAN identifier  of the virtual N-port."
    ::= { csiNportEntry 3 }

csiNportPwwn OBJECT-TYPE
    SYNTAX FcNameId
--    Rsyntax OCTET STRING(SIZE(8))
    ACCESS read-write
    STATUS mandatory
    DESCRIPTION
        "The WWN (Worldwide Name) of the virtual N-port."
    ::= { csiNportEntry 4 }

csiNportFcid OBJECT-TYPE
    SYNTAX INTEGER(1..16777215)
    ACCESS read-only
    STATUS mandatory
    DESCRIPTION
        "Fibre Channel Identifier of the virtual N-port."
    ::= { csiNportEntry 5 }

csiNportState OBJECT-TYPE
    SYNTAX INTEGER {
        up(1),
        down(2)
        }
    ACCESS read-only
    STATUS mandatory
    DESCRIPTION
        "The operational state of the virtual N-port."
    ::= { csiNportEntry 6 }

csiNportDownReason OBJECT-TYPE
    SYNTAX INTEGER {
        none(1),
        adminDown(2),
        ifSoftwareDown(3),
        lineCardSwDown(4),
        vsanDown(5),
        inRemovalState(6),
        ifHardwareDown(7),
        uninitialized(8)
        }
    ACCESS read-only
    STATUS mandatory
    DESCRIPTION
        "If the state of the N-port is 'down' as depicted 
         by the instance of csiNportState, this objects 
         denotes the reason why this N-port is 'down'. 
        
         When the N-port is 'up' the value returned by
         this object is 'none'. 
        
         adminDown - The user has configured the SVC interface
                     that contains this N-port as down.
        
         ifSoftwareDown - Virtualization software is down.
        
         lineCardSwDown - Line card software is down.
        
         vsanDown - The VSAN that this N-port belongs to
                    (instance of csiNportVsanId), is down.
        
         inRemovalState - The SVC interface that this N-port
                    belongs to, is in the process of 
                    going down.
        
         ifHardwareDown - The line card hardware is down.
        
         uninitialized  - Port is being initialized.
         "
    ::= { csiNportEntry 7 }

csiNportRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Status of this row."
    ::= { csiNportEntry 8 }

csiSessionTable OBJECT-TYPE
    SYNTAX SEQUENCE OF CsiSessionEntry
    ACCESS not-accessible
    STATUS mandatory
    DESCRIPTION
        "A table of SVC sessions.   
        
         A SVC session is a FC session between a virtual
         N-port and any other N-port within a FC fabric."
    ::= { cSvcInterfaceConfiguration 2 }

csiSessionEntry OBJECT-TYPE
    SYNTAX CsiSessionEntry
    ACCESS not-accessible
    STATUS mandatory
    DESCRIPTION
        "An entry in the csiSessionTable.
        
         An entry in the session table is identified by a 
         virtual N-port and a session Identifier.  
        
         Each N-port is identified by the ifIndex, 
         Nport type and the VSAN id as described above 
         in the csiNportEntry.
        
         The combination of the N-port and the sessionId
         uniquely identifies a session.
        
         Each session has the local N-port's WWN, remote
         N-port's WWN and remote node's WWN as well as
         remote N-port's FcId."
    INDEX { csiSessionIfIndex, csiSessionType, csiSessionVsanId, csiSessionId }
    ::= { csiSessionTable 1 }

CsiSessionEntry ::= SEQUENCE {
    csiSessionIfIndex InterfaceIndex,
    csiSessionType NportType,
    csiSessionVsanId VsanIndex,
    csiSessionId INTEGER,
    csiSessionNportPwwn FcNameId,
    csiSessionPeerPwwn FcNameId,
    csiSessionPeerNwwn FcNameId,
    csiSessionPeerFcid INTEGER
    }

csiSessionIfIndex OBJECT-TYPE
    SYNTAX InterfaceIndex
--    Rsyntax INTEGER(1..2147483647)
    ACCESS not-accessible
    STATUS mandatory
    DESCRIPTION
        "The ifIndex of the SVC interface to which this N-port
         belongs to. "
    ::= { csiSessionEntry 1 }

csiSessionType OBJECT-TYPE
    SYNTAX NportType
--    Rsyntax INTEGER(1..3)
    ACCESS not-accessible
    STATUS mandatory
    DESCRIPTION
        "The type of the N-port for this session. "
    ::= { csiSessionEntry 2 }

csiSessionVsanId OBJECT-TYPE
    SYNTAX VsanIndex
--    Rsyntax INTEGER(1..4094)
    ACCESS not-accessible
    STATUS mandatory
    DESCRIPTION
        "The VSAN identifier of the N-port for this session. "
    ::= { csiSessionEntry 3 }

csiSessionId OBJECT-TYPE
    SYNTAX INTEGER(1..2147483647)
    ACCESS not-accessible
    STATUS mandatory
    DESCRIPTION
        "The session identifier of this session. "
    ::= { csiSessionEntry 4 }

csiSessionNportPwwn OBJECT-TYPE
    SYNTAX FcNameId
--    Rsyntax OCTET STRING(SIZE(8))
    ACCESS read-only
    STATUS mandatory
    DESCRIPTION
        "The WWN of the N-port that belongs to this session."
    ::= { csiSessionEntry 5 }

csiSessionPeerPwwn OBJECT-TYPE
    SYNTAX FcNameId
--    Rsyntax OCTET STRING(SIZE(8))
    ACCESS read-only
    STATUS mandatory
    DESCRIPTION
        "The WWN of the remote N-port for this session."
    ::= { csiSessionEntry 6 }

csiSessionPeerNwwn OBJECT-TYPE
    SYNTAX FcNameId
--    Rsyntax OCTET STRING(SIZE(8))
    ACCESS read-only
    STATUS mandatory
    DESCRIPTION
        "The WWN of the remote node for this session."
    ::= { csiSessionEntry 7 }

csiSessionPeerFcid OBJECT-TYPE
    SYNTAX INTEGER(1..16777215)
    ACCESS read-only
    STATUS mandatory
    DESCRIPTION
        "Fibre Channel Identifier of the remote port 
         for this session. "
    ::= { csiSessionEntry 8 }

csiInterfaceStatsTable OBJECT-TYPE
    SYNTAX SEQUENCE OF CsiInterfaceStatsEntry
    ACCESS not-accessible
    STATUS mandatory
    DESCRIPTION
        "A table that lists various statistics for each SVC
         interface. "
    ::= { cSvcInterfaceConfiguration 3 }

csiInterfaceStatsEntry OBJECT-TYPE
    SYNTAX CsiInterfaceStatsEntry
    ACCESS not-accessible
    STATUS mandatory
    DESCRIPTION
        "An entry in the csiInterfaceStatsTable,
         indexed by the N-port ifIndex and containing
         interface statistics such as the input and output
         frames, bytes and rates."
    INDEX { csiNportIfIndex }
    ::= { csiInterfaceStatsTable 1 }

CsiInterfaceStatsEntry ::= SEQUENCE {
    csiInterfaceInFrames Counter,
    csiInterfaceInFrameRate Gauge,
    csiInterfaceInBytes Counter,
    csiInterfaceInBytesRate Gauge,
    csiInterfaceOutFrames Counter,
    csiInterfaceOutFrameRate Gauge,
    csiInterfaceOutBytes Counter,
    csiInterfaceOutBytesRate Gauge
    }

csiInterfaceInFrames OBJECT-TYPE
    SYNTAX Counter
    ACCESS read-only
    STATUS mandatory
    DESCRIPTION
        "Number of incoming frames on this interface."
    ::= { csiInterfaceStatsEntry 1 }

csiInterfaceInFrameRate OBJECT-TYPE
    SYNTAX Gauge
    ACCESS read-only
    STATUS mandatory
    DESCRIPTION
        "Number of incoming frames per second on 
         this interface."
    ::= { csiInterfaceStatsEntry 2 }

csiInterfaceInBytes OBJECT-TYPE
    SYNTAX Counter
    ACCESS read-only
    STATUS mandatory
    DESCRIPTION
        "Number of incoming bytes on this interface."
    ::= { csiInterfaceStatsEntry 3 }

csiInterfaceInBytesRate OBJECT-TYPE
    SYNTAX Gauge
    ACCESS read-only
    STATUS mandatory
    DESCRIPTION
        "Number of incoming bytes per second on 
         this interface."
    ::= { csiInterfaceStatsEntry 4 }

csiInterfaceOutFrames OBJECT-TYPE
    SYNTAX Counter
    ACCESS read-only
    STATUS mandatory
    DESCRIPTION
        "Number of outgoing frames on this interface."
    ::= { csiInterfaceStatsEntry 5 }

csiInterfaceOutFrameRate OBJECT-TYPE
    SYNTAX Gauge
    ACCESS read-only
    STATUS mandatory
    DESCRIPTION
        "Number of outgoing frames per second on 
         this interface."
    ::= { csiInterfaceStatsEntry 6 }

csiInterfaceOutBytes OBJECT-TYPE
    SYNTAX Counter
    ACCESS read-only
    STATUS mandatory
    DESCRIPTION
        "Number of outgoing bytes on this interface."
    ::= { csiInterfaceStatsEntry 7 }

csiInterfaceOutBytesRate OBJECT-TYPE
    SYNTAX Gauge
    ACCESS read-only
    STATUS mandatory
    DESCRIPTION
        "Number of outgoing bytes per second on 
         this interface."
    ::= { csiInterfaceStatsEntry 8 }

csiNportStatsTable OBJECT-TYPE
    SYNTAX SEQUENCE OF CsiNportStatsEntry
    ACCESS not-accessible
    STATUS mandatory
    DESCRIPTION
        "A table of N-port statistics."
    ::= { cSvcInterfaceConfiguration 4 }

csiNportStatsEntry OBJECT-TYPE
    SYNTAX CsiNportStatsEntry
    ACCESS not-accessible
    STATUS mandatory
    DESCRIPTION
        "An entry in the csiNportStatsTable. "
    INDEX { csiNportIfIndex, csiNportType, csiNportVsanId }
    ::= { csiNportStatsTable 1 }

CsiNportStatsEntry ::= SEQUENCE {
    csiNportSessions Counter,
    csiNportInFrames Counter,
    csiNportInFrameRate Gauge,
    csiNportInBytes Counter,
    csiNportInBytesRate Gauge,
    csiNportOutFrames Counter,
    csiNportOutFrameRate Gauge,
    csiNportOutBytes Counter,
    csiNportOutBytesRate Gauge
    }

csiNportSessions OBJECT-TYPE
    SYNTAX Counter
    ACCESS read-only
    STATUS mandatory
    DESCRIPTION
        "Number of pen sessions on this virtual N-port."
    ::= { csiNportStatsEntry 1 }

csiNportInFrames OBJECT-TYPE
    SYNTAX Counter
    ACCESS read-only
    STATUS mandatory
    DESCRIPTION
        "Number of incoming frames on this virtual N-port."
    ::= { csiNportStatsEntry 2 }

csiNportInFrameRate OBJECT-TYPE
    SYNTAX Gauge
    ACCESS read-only
    STATUS mandatory
    DESCRIPTION
        "Number of incoming frames per second on 
         this virtual N-port."
    ::= { csiNportStatsEntry 3 }

csiNportInBytes OBJECT-TYPE
    SYNTAX Counter
    ACCESS read-only
    STATUS mandatory
    DESCRIPTION
        "Number of incoming bytes on this virtual N-port."
    ::= { csiNportStatsEntry 4 }

csiNportInBytesRate OBJECT-TYPE
    SYNTAX Gauge
    ACCESS read-only
    STATUS mandatory
    DESCRIPTION
        "Number of incoming bytes per second on 
         this virtual N-port."
    ::= { csiNportStatsEntry 5 }

csiNportOutFrames OBJECT-TYPE
    SYNTAX Counter
    ACCESS read-only
    STATUS mandatory
    DESCRIPTION
        "Number of outgoing frames on this virtual N-port."
    ::= { csiNportStatsEntry 6 }

csiNportOutFrameRate OBJECT-TYPE
    SYNTAX Gauge
    ACCESS read-only
    STATUS mandatory
    DESCRIPTION
        "Number of outgoing frames per second on 
         this virtual N-port."
    ::= { csiNportStatsEntry 7 }

csiNportOutBytes OBJECT-TYPE
    SYNTAX Counter
    ACCESS read-only
    STATUS mandatory
    DESCRIPTION
        "Number of outgoing bytes on this virtual N-port."
    ::= { csiNportStatsEntry 8 }

csiNportOutBytesRate OBJECT-TYPE
    SYNTAX Gauge
    ACCESS read-only
    STATUS mandatory
    DESCRIPTION
        "Number of outgoing bytes per second on 
         this virtual N-port."
    ::= { csiNportStatsEntry 9 }

csiSessionStatsTable OBJECT-TYPE
    SYNTAX SEQUENCE OF CsiSessionStatsEntry
    ACCESS not-accessible
    STATUS mandatory
    DESCRIPTION
        "A table of session statistics."
    ::= { cSvcInterfaceConfiguration 5 }

csiSessionStatsEntry OBJECT-TYPE
    SYNTAX CsiSessionStatsEntry
    ACCESS not-accessible
    STATUS mandatory
    DESCRIPTION
        "An entry in the csiSessionStatsEntry."
    INDEX { csiSessionIfIndex, csiSessionType, csiSessionVsanId, csiSessionId }
    ::= { csiSessionStatsTable 1 }

CsiSessionStatsEntry ::= SEQUENCE {
    csiSessionInELSFrames Counter,
    csiSessionInBLSFrames Counter,
    csiSessionInFCPCmds Counter,
    csiSessionInFCPXferRdys Counter,
    csiSessionInFCPDataFrames Counter,
    csiSessionInFCPStatus Counter,
    csiSessionInFCPDataBytes Counter,
    csiSessionInFCPOverRuns Counter,
    csiSessionInFCPUnderRuns Counter,
    csiSessionInAborts Counter,
    csiSessionOutELSFrames Counter,
    csiSessionOutBLSFrames Counter,
    csiSessionOutFCPCmds Counter,
    csiSessionOutFCPXferRdys Counter,
    csiSessionOutFCPDataFrames Counter,
    csiSessionOutFCPStatus Counter,
    csiSessionOutFCPDataBytes Counter,
    csiSessionOutFCPOverRuns Counter,
    csiSessionOutFCPUnderRuns Counter,
    csiSessionOutAborts Counter,
    csiSessionOpenXchanges Counter,
    csiSessionInBadFc2Drops Counter,
    csiSessionInBadFcPDrops Counter,
    csiSessionInFCPDataExcess Counter
    }

csiSessionInELSFrames OBJECT-TYPE
    SYNTAX Counter
    ACCESS read-only
    STATUS mandatory
    DESCRIPTION
        "Number of incoming Extended Link Service frames 
         in this session."
    ::= { csiSessionStatsEntry 1 }

csiSessionInBLSFrames OBJECT-TYPE
    SYNTAX Counter
    ACCESS read-only
    STATUS mandatory
    DESCRIPTION
        "Number of incoming Basic Link Service frames
         in this session."
    ::= { csiSessionStatsEntry 2 }

csiSessionInFCPCmds OBJECT-TYPE
    SYNTAX Counter
    ACCESS read-only
    STATUS mandatory
    DESCRIPTION
        "Number of incoming FCP Command frames 
         in this session. Note that FCP stands for
         Fibre Channel Protocol."
    ::= { csiSessionStatsEntry 3 }

csiSessionInFCPXferRdys OBJECT-TYPE
    SYNTAX Counter
    ACCESS read-only
    STATUS mandatory
    DESCRIPTION
        "Number of incoming FCP Transfer Ready 
         frames in this session."
    ::= { csiSessionStatsEntry 4 }

csiSessionInFCPDataFrames OBJECT-TYPE
    SYNTAX Counter
    ACCESS read-only
    STATUS mandatory
    DESCRIPTION
        "Number of incoming FCP Data frames."
    ::= { csiSessionStatsEntry 5 }

csiSessionInFCPStatus OBJECT-TYPE
    SYNTAX Counter
    ACCESS read-only
    STATUS mandatory
    DESCRIPTION
        "Number of incoming FCP Status frames."
    ::= { csiSessionStatsEntry 6 }

csiSessionInFCPDataBytes OBJECT-TYPE
    SYNTAX Counter
    ACCESS read-only
    STATUS mandatory
    DESCRIPTION
        "Number of incoming FCP Data bytes."
    ::= { csiSessionStatsEntry 7 }

csiSessionInFCPOverRuns OBJECT-TYPE
    SYNTAX Counter
    ACCESS read-only
    STATUS mandatory
    DESCRIPTION
        "Number of incoming FCP Overrun frames."
    ::= { csiSessionStatsEntry 8 }

csiSessionInFCPUnderRuns OBJECT-TYPE
    SYNTAX Counter
    ACCESS read-only
    STATUS mandatory
    DESCRIPTION
        "Number of incoming FCP Underrun frames."
    ::= { csiSessionStatsEntry 9 }

csiSessionInAborts OBJECT-TYPE
    SYNTAX Counter
    ACCESS read-only
    STATUS mandatory
    DESCRIPTION
        "Number of incoming aborted frames."
    ::= { csiSessionStatsEntry 10 }

csiSessionOutELSFrames OBJECT-TYPE
    SYNTAX Counter
    ACCESS read-only
    STATUS mandatory
    DESCRIPTION
        "Number of outgoing Extended Link Service frames 
         in this session."
    ::= { csiSessionStatsEntry 11 }

csiSessionOutBLSFrames OBJECT-TYPE
    SYNTAX Counter
    ACCESS read-only
    STATUS mandatory
    DESCRIPTION
        "Number of outgoing Basic Link Service frames 
         in this session."
    ::= { csiSessionStatsEntry 12 }

csiSessionOutFCPCmds OBJECT-TYPE
    SYNTAX Counter
    ACCESS read-only
    STATUS mandatory
    DESCRIPTION
        "Number of outgoing FCP Command frames 
         in this session."
    ::= { csiSessionStatsEntry 13 }

csiSessionOutFCPXferRdys OBJECT-TYPE
    SYNTAX Counter
    ACCESS read-only
    STATUS mandatory
    DESCRIPTION
        "Number of outgoing FCP Transfer Ready frames 
         in this session."
    ::= { csiSessionStatsEntry 14 }

csiSessionOutFCPDataFrames OBJECT-TYPE
    SYNTAX Counter
    ACCESS read-only
    STATUS mandatory
    DESCRIPTION
        "Number of outgoing FCP Data frames 
         in this session."
    ::= { csiSessionStatsEntry 15 }

csiSessionOutFCPStatus OBJECT-TYPE
    SYNTAX Counter
    ACCESS read-only
    STATUS mandatory
    DESCRIPTION
        "Number of outgoing FCP Status frames 
         in this session."
    ::= { csiSessionStatsEntry 16 }

csiSessionOutFCPDataBytes OBJECT-TYPE
    SYNTAX Counter
    ACCESS read-only
    STATUS mandatory
    DESCRIPTION
        "Number of outgoing FCP Data bytes 
         in this session."
    ::= { csiSessionStatsEntry 17 }

csiSessionOutFCPOverRuns OBJECT-TYPE
    SYNTAX Counter
    ACCESS read-only
    STATUS mandatory
    DESCRIPTION
        "Number of outgoing FCP Overrun frames 
         in this session."
    ::= { csiSessionStatsEntry 18 }

csiSessionOutFCPUnderRuns OBJECT-TYPE
    SYNTAX Counter
    ACCESS read-only
    STATUS mandatory
    DESCRIPTION
        "Number of outgoing FCP Underrun frames 
         in this session."
    ::= { csiSessionStatsEntry 19 }

csiSessionOutAborts OBJECT-TYPE
    SYNTAX Counter
    ACCESS read-only
    STATUS mandatory
    DESCRIPTION
        "Number of outgoing aborted frames
         in this session."
    ::= { csiSessionStatsEntry 20 }

csiSessionOpenXchanges OBJECT-TYPE
    SYNTAX Counter
    ACCESS read-only
    STATUS mandatory
    DESCRIPTION
        "Number of Open Exchanges in this session."
    ::= { csiSessionStatsEntry 21 }

csiSessionInBadFc2Drops OBJECT-TYPE
    SYNTAX Counter
    ACCESS read-only
    STATUS mandatory
    DESCRIPTION
        "Number of FC2 dropped frames in this
         session."
    ::= { csiSessionStatsEntry 22 }

csiSessionInBadFcPDrops OBJECT-TYPE
    SYNTAX Counter
    ACCESS read-only
    STATUS mandatory
    DESCRIPTION
        "Number of FCP dropped frames."
    ::= { csiSessionStatsEntry 23 }

csiSessionInFCPDataExcess OBJECT-TYPE
    SYNTAX Counter
    ACCESS read-only
    STATUS mandatory
    DESCRIPTION
        "Number of FCP Data  Excess frames in 
         this session."
    ::= { csiSessionStatsEntry 24 }

csiInterfaceNwwnTable OBJECT-TYPE
    SYNTAX SEQUENCE OF CsiInterfaceNwwnEntry
    ACCESS not-accessible
    STATUS mandatory
    DESCRIPTION
        "A table that lists Nwwn for SVC
         interfaces. "
    ::= { cSvcInterfaceConfiguration 6 }

csiInterfaceNwwnEntry OBJECT-TYPE
    SYNTAX CsiInterfaceNwwnEntry
    ACCESS not-accessible
    STATUS mandatory
    DESCRIPTION
        "An entry in the csiInterfaceNwwnTable,
         indexed by the N-port ifIndex and containing
         interface Nwwn and a description of the
         cause if that interface is down."
    INDEX { csiNportIfIndex }
    ::= { csiInterfaceNwwnTable 1 }

CsiInterfaceNwwnEntry ::= SEQUENCE {
    csiInterfaceNwwn FcNameId,
    csiInterfaceOperStateCause SnmpAdminString
    }

csiInterfaceNwwn OBJECT-TYPE
    SYNTAX FcNameId
--    Rsyntax OCTET STRING(SIZE(8))
    ACCESS read-write
    STATUS mandatory
    DESCRIPTION
        "Nwwn of this interface."
    ::= { csiInterfaceNwwnEntry 1 }

csiInterfaceOperStateCause OBJECT-TYPE
    SYNTAX SnmpAdminString(SIZE(1..64))
--    Rsyntax OCTET STRING(SIZE(1..64))
    ACCESS read-only
    STATUS mandatory
    DESCRIPTION
        "A description of the cause that the interface
         is down."
    ::= { csiInterfaceNwwnEntry 2 }

csiErrorId OBJECT-TYPE
    SYNTAX INTEGER(0..2147483647)
    ACCESS not-accessible
    STATUS mandatory
    DESCRIPTION
        "Error Id"
    ::= { cSvcInterfaceTrapObjects 1 }

csiErrorSeqNumber OBJECT-TYPE
    SYNTAX INTEGER(0..2147483647)
    ACCESS not-accessible
    STATUS mandatory
    DESCRIPTION
        "Error Sequence Number"
    ::= { cSvcInterfaceTrapObjects 2 }

csiSlotNumber OBJECT-TYPE
    SYNTAX INTEGER(0..2147483647)
    ACCESS not-accessible
    STATUS mandatory
    DESCRIPTION
        "Slot Number of the slot from where the
         notification is being generated."
    ::= { cSvcInterfaceTrapObjects 3 }

csiPortNumber OBJECT-TYPE
    SYNTAX INTEGER(0..2147483647)
    ACCESS not-accessible
    STATUS mandatory
    DESCRIPTION
        "Port Number of the port from where the
         notification is being generated."
    ::= { cSvcInterfaceTrapObjects 4 }

csiObjName OBJECT-TYPE
    SYNTAX SnmpAdminString
--    Rsyntax OCTET STRING(SIZE(0..255))
    ACCESS not-accessible
    STATUS mandatory
    DESCRIPTION
        "User configured name of an object.
         e.g. vDisk1, where the user has 
         named  the virtual disk 1 as vDisk1."
    ::= { cSvcInterfaceTrapObjects 5 }

csiErrorText OBJECT-TYPE
    SYNTAX SnmpAdminString
--    Rsyntax OCTET STRING(SIZE(0..255))
    ACCESS not-accessible
    STATUS mandatory
    DESCRIPTION
        " Full text string describing the Error."
    ::= { cSvcInterfaceTrapObjects 6 }

csiMachineType OBJECT-TYPE
    SYNTAX SnmpAdminString
--    Rsyntax OCTET STRING(SIZE(0..255))
    ACCESS not-accessible
    STATUS mandatory
    DESCRIPTION
        "Machine Type in which the SVC software is
         running. This could be the vendor product
         identifier. e.g MDS9000"
    ::= { cSvcInterfaceTrapObjects 7 }

csiCardSerialNo OBJECT-TYPE
    SYNTAX SnmpAdminString
--    Rsyntax OCTET STRING(SIZE(0..255))
    ACCESS not-accessible
    STATUS mandatory
    DESCRIPTION
        "The serial number of the card from where 
         the notification is being generated."
    ::= { cSvcInterfaceTrapObjects 8 }

csiSwVersion OBJECT-TYPE
    SYNTAX SnmpAdminString
--    Rsyntax OCTET STRING(SIZE(0..255))
    ACCESS not-accessible
    STATUS mandatory
    DESCRIPTION
        "The SVC software version."
    ::= { cSvcInterfaceTrapObjects 9 }

csiSwitchName OBJECT-TYPE
    SYNTAX SnmpAdminString
--    Rsyntax OCTET STRING(SIZE(0..255))
    ACCESS not-accessible
    STATUS mandatory
    DESCRIPTION
        "The user configured name of the
         switch that is running the SVC
         software."
    ::= { cSvcInterfaceTrapObjects 10 }

csiClusterName OBJECT-TYPE
    SYNTAX SnmpAdminString
--    Rsyntax OCTET STRING(SIZE(0..255))
    ACCESS not-accessible
    STATUS mandatory
    DESCRIPTION
        "The user configured name of the
         cluster."
    ::= { cSvcInterfaceTrapObjects 11 }

csiNodeName OBJECT-TYPE
    SYNTAX SnmpAdminString
--    Rsyntax OCTET STRING(SIZE(0..255))
    ACCESS not-accessible
    STATUS mandatory
    DESCRIPTION
        "The user configured name of the SVC 
         node."
    ::= { cSvcInterfaceTrapObjects 12 }

csiErrorTrap TRAP-TYPE
-- Reverse mappable trap
    ENTERPRISE ciscoSvcInterfaceMIBTrapPrefix
    VARIABLES {
        csiErrorId, csiErrorSeqNumber, csiSlotNumber, csiPortNumber, 
        csiObjName, csiErrorText, csiMachineType, csiCardSerialNo, 
        csiSwVersion, csiSwitchName, csiClusterName, csiNodeName }
--  Status
--    mandatory
    DESCRIPTION
        "SVC error trap.
        
         The objects within this trap convey the information
         about things such as the port number, slot number
         machine type etc for which the error occurred.
        
         This notification will be generated when there is
         an error condition in any of the SVC operations."
    ::= 1

csiWarningTrap TRAP-TYPE
-- Reverse mappable trap
    ENTERPRISE ciscoSvcInterfaceMIBTrapPrefix
    VARIABLES {
        csiErrorId, csiErrorSeqNumber, csiSlotNumber, csiPortNumber, 
        csiObjName, csiErrorText, csiMachineType, csiCardSerialNo, 
        csiSwVersion, csiSwitchName, csiClusterName, csiNodeName }
--  Status
--    mandatory
    DESCRIPTION
        "SVC warning trap
        
         The objects within this trap convey the information
         about things such as the port number, slot number
         machine type etc for which the error occurred.
        
         This notification will be generated when there is
         an warning condition in any of the SVC operations."
    ::= 2

csiInformationTrap TRAP-TYPE
-- Reverse mappable trap
    ENTERPRISE ciscoSvcInterfaceMIBTrapPrefix
    VARIABLES {
        csiErrorId, csiErrorSeqNumber, csiSlotNumber, csiPortNumber, 
        csiObjName, csiErrorText, csiMachineType, csiCardSerialNo, 
        csiSwVersion, csiSwitchName, csiClusterName, csiNodeName }
--  Status
--    mandatory
    DESCRIPTION
        "SVC information trap
        
         The objects within this trap convey the information
         about things such as the port number, slot number
         machine type etc for which the information needs
         to be conveyed.
        
         This notification will be generated when there is
         an information needs to be conveyed in any of the 
         SVC operations."
    ::= 3

csiNportGroup OBJECT IDENTIFIER ::= { ciscoSvcMIBGroups 1 }
-- OBJECT-GROUP
--  Status
--    mandatory
--  Descr
--    A collection of objects for Nport configuration.
--  objects
--    csiNportPwwn, csiNportFcid, csiNportState, csiNportDownReason, 
--    csiNportRowStatus

csiSessionGroup OBJECT IDENTIFIER ::= { ciscoSvcMIBGroups 2 }
-- OBJECT-GROUP
--  Status
--    mandatory
--  Descr
--    A collection of objects for session configuration.
--  objects
--    csiSessionNportPwwn, csiSessionPeerPwwn, csiSessionPeerNwwn, 
--    csiSessionPeerFcid

csiInterfaceStatsGroup OBJECT IDENTIFIER ::= { ciscoSvcMIBGroups 3 }
-- OBJECT-GROUP
--  Status
--    mandatory
--  Descr
--    A collection of objects for interface statistics.
--  objects
--    csiInterfaceInFrames, csiInterfaceInFrameRate, 
--    csiInterfaceInBytes, csiInterfaceInBytesRate, 
--    csiInterfaceOutFrames, csiInterfaceOutFrameRate, 
--    csiInterfaceOutBytes, csiInterfaceOutBytesRate

csiNportStatsGroup OBJECT IDENTIFIER ::= { ciscoSvcMIBGroups 4 }
-- OBJECT-GROUP
--  Status
--    mandatory
--  Descr
--    A collection of objects for N-port statistics.
--  objects
--    csiNportSessions, csiNportInFrames, csiNportInFrameRate, 
--    csiNportInBytes, csiNportInBytesRate, csiNportOutFrames, 
--    csiNportOutFrameRate, csiNportOutBytes, csiNportOutBytesRate

csiSessionStatsGroup OBJECT IDENTIFIER ::= { ciscoSvcMIBGroups 5 }
-- OBJECT-GROUP
--  Status
--    mandatory
--  Descr
--    A collection of objects for Session statistics.
--  objects
--    csiSessionInELSFrames, csiSessionInBLSFrames, 
--    csiSessionInFCPCmds, csiSessionInFCPXferRdys, 
--    csiSessionInFCPDataFrames, csiSessionInFCPStatus, 
--    csiSessionInFCPDataBytes, csiSessionInFCPOverRuns, 
--    csiSessionInFCPUnderRuns, csiSessionInAborts, 
--    csiSessionOutELSFrames, csiSessionOutBLSFrames, 
--    csiSessionOutFCPCmds, csiSessionOutFCPXferRdys, 
--    csiSessionOutFCPDataFrames, csiSessionOutFCPStatus, 
--    csiSessionOutFCPDataBytes, csiSessionOutFCPOverRuns, 
--    csiSessionOutFCPUnderRuns, csiSessionOutAborts, 
--    csiSessionOpenXchanges, csiSessionInBadFc2Drops, 
--    csiSessionInBadFcPDrops, csiSessionInFCPDataExcess

csiInterfaceNwwnGroup OBJECT IDENTIFIER ::= { ciscoSvcMIBGroups 6 }
-- OBJECT-GROUP
--  Status
--    mandatory
--  Descr
--    A collection of objects for Interface nwwn.
--  objects
--    csiInterfaceNwwn, csiInterfaceOperStateCause

csiNotifObjectsGroup OBJECT IDENTIFIER ::= { ciscoSvcMIBGroups 7 }
-- OBJECT-GROUP
--  Status
--    mandatory
--  Descr
--    A collection of objects for sending notifications.
--  objects
--    csiErrorId, csiErrorSeqNumber, csiSlotNumber, csiPortNumber, 
--    csiObjName, csiErrorText, csiMachineType, csiCardSerialNo, 
--    csiSwVersion, csiSwitchName, csiClusterName, csiNodeName

cefcMgmtNotificationsGroup OBJECT IDENTIFIER ::= { ciscoSvcMIBGroups 8 }
-- NOTIFICATION-GROUP
--  Status
--    mandatory
--  Descr
--    The notifications which a SVC Management entity is
--     required to implement.
--  notifications
--    csiErrorTrap, csiWarningTrap, csiInformationTrap

ciscoSvcMIBCompliance OBJECT IDENTIFIER ::= { ciscoSvcMIBCompliances 1 }
-- MODULE-COMPLIANCE
--  Status
--    mandatory
--  Descr
--    The compliance statement for entities which
--     implement the CISCO-SVC-INERFACE-MIB.
--  Module
--    >>current<<
--   MandGroup
--    csiNportGroup
--   MandGroup
--    csiSessionGroup
--   MandGroup
--    csiInterfaceStatsGroup
--   MandGroup
--    csiNportStatsGroup
--   MandGroup
--    csiSessionStatsGroup
--   MandGroup
--    csiInterfaceNwwnGroup
--   MandGroup
--    csiNotifObjectsGroup
--   MandGroup
--    cefcMgmtNotificationsGroup
--   ObjVar
--    csiNportRowStatus


END
