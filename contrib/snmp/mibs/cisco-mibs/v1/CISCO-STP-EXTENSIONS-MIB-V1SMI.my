-- MIB file created 18-Mar-2013 16:17:05, by
--   SMICng version 2.2.11-beta(PRO)(Solaris), January 20, 2001. Enterprise key cisco.com

CISCO-STP-EXTENSIONS-MIB DEFINITIONS ::= BEGIN

-- From file: "CISCO-STP-EXTENSIONS-MIB.my"
-- Compile options "4 7 F H N W 03 06 0B 0G 0N 0T"

IMPORTS
    TruthValue, TimeStamp, DisplayString, RowStatus
            FROM SNMPv2-TC-v1
    vlanTrunkPortIfIndex, VlanIndex, managementDomainIndex, 
    vtpVlanIndex, managementDomainIndex, vtpVlanEditIndex
            FROM CISCO-VTP-MIB
    dot1dStpPort
            FROM BRIDGE-MIB
    ciscoMgmt
            FROM CISCO-SMI
    Counter, Gauge
            FROM RFC1155-SMI
    OBJECT-TYPE
            FROM RFC-1212
    TRAP-TYPE
            FROM RFC-1215;

ciscoStpExtensionsMIB OBJECT IDENTIFIER ::= { ciscoMgmt 82 }
-- MODULE-IDENTITY
--  LastUpdated
--    201303070000Z
--  OrgName
--    Cisco Systems, Inc.
--  ContactInfo
--           Cisco Systems
--            Customer Service
--    
--    Postal: 170 W Tasman Drive
--            San Jose, CA  95134
--            USA
--    
--       Tel: +1 800 553-NETS
--    
--    E-mail: cs-wbu@cisco.com
--  Descr
--    The MIB module for managing Cisco extensions to
--    the 802.1D Spanning Tree Protocol (STP).
--  RevDate
--    201303070000Z
--  RevDescr
--    Added one new value network(5) to stpxFastStartPortMode.
--  RevDate
--    200512200000Z
--  RevDescr
--    Added bit value rstp(5) to stpxSMSTPortStatus and
--    dispute(4) to stpxRPVSTPortStatus.
--  RevDate
--    200504120000Z
--  RevDescr
--    Changed the description clauses of stpxMSTMaxHopCount
--    and stpxMSTInstanceRemainingHopCount.
--    Added StpxMSTConfigurationDigest textual convention.
--    Deprecated stpxMSTGroup3 and added the following groups: 
--        stpxRSTPTransmitHoldCountGroup,
--        stpxSMSTPortMSTModeGroup, stpxSMSTMaxHopCountGroup,
--        stpxSMSTConfigDigestGroup and stpxMSTGroup4.
--    Added bit dispute(4) into the BITS syntax of
--    stpxSMSTPortStatus.
--    Deprecated stpxMIBCompliance11 and added 
--    stpxMIBCompliance12.
--  RevDate
--    200407210000Z
--  RevDescr
--    Added stpxPathCostOperModeGroup
--     and changed the decription of 
--     stpxSpanningTreePathCostMode.
--  RevDate
--    200404080000Z
--  RevDescr
--    Added stpxSMSTInstanceCISTGroup.
--    Added 3 new bit values into the BITS syntax
--    of stpxNotificationEnable: 
--    inconsistency(2), rootInconsistency(3), 
--    and loopInconsistency(4).
--  RevDate
--    200401140000Z
--  RevDescr
--    Deprecated stpxMSTGroup2 and 
--    stpxPreferredMSTInstancesGroup.
--    Added stpxMSTGroup3, stpxSMSTGroup, 
--    stpxSMSTInstanceGroup, stpxSMSTInstanceEditGroup,
--    stpxSMSTPortStatusGroup, stpxSMSTPortHelloTimeGroup. 
--    Added one new value master(7) to stpxMSTPortRoleValue
--    and stpxRSTPPortRoleValue. Added 2 new unused bit 
--    value into the BITS syntax of stpxRPVSTPortStatus.
--  RevDate
--    200310230000Z
--  RevDescr
--    Added stpxExtendedSysIDGroup,  
--    stpxNotificationEnableGroup, and 
--    stpxFastStartOperModeGroup.
--  RevDate
--    200207110000Z
--  RevDescr
--    Added Rapid Spanning Tree Protocol support.
--    Added stpxUplinkFastOperEnabled and
--    stpxBackboneFastOperEnabled objects.
--    Replaced stpxMSTPortAdminLinkType, 
--    stpxMSTPortOperLinkType, 
--    stpxMSTPortProtocolMigration 
--    with stpxRSTPPortAdminLinkType,
--    stpxRSTPPortOperLinkType and 
--    stpxRSTPPortProtocolMigration
--    defined in stpxRSTPPortTable.
--    Replaced stpxMSTPortRoleTable with
--    stpxRSTPPortRoleTable. Added stpxRPVSTPortTable.
--  RevDate
--    200112060000Z
--  RevDescr
--    Added per port Bpdu Guard and Bpdu Filter 
--    mode configuration support. Modified the
--    description of stpxUplinkFastEnabled and
--    stpxUplinkStationLearningGenRate for MST
--    support. 
--  RevDate
--    200109140000Z
--  RevDescr
--    Added MST support, Loop Guard Global Default mode
--    support and Fast Start Global Default mode support.
--    Deprecated stpxFastStartPortEnable and 
--    stpxLoopGuardConfigEnabled objects. Changed description
--    of stpxUplinkFastEnabled, stpxUplinkFastTransitions,
--    stpxUplinkStationLearningGenRate, 
--    stpxUplinkStationLearningFrames objects for MST support.
--  RevDate
--    200106200000Z
--  RevDescr
--    Added BPDU Skewing feature support and modified
--    the SYNTAX clause of stpxUplinkStationLearningGenRate.
--  RevDate
--    200104120000Z
--  RevDescr
--    Added PVST+ VLAN Configuration, MISTP to VLAN mapping,
--    Loopguard, and Port Fast Start support.
--  RevDate
--    200005230000Z
--  RevDescr
--    Added Long Spanning Tree Path Cost Mode support.
--  RevDate
--    200003210000Z
--  RevDescr
--    Added Rootguard, 4k VLAN and MISTP support.
--  RevDate
--    9711101200Z
--  RevDescr
--    Additional objects to support SSTP.
--  RevDate
--    9708191200Z
--  RevDescr
--    Initial version of this MIB module.

stpxObjects     OBJECT IDENTIFIER ::= { ciscoStpExtensionsMIB 1 }
stpxUplinkFastObjects OBJECT IDENTIFIER ::= { stpxObjects 1 }
stpxVlanObjects OBJECT IDENTIFIER ::= { stpxObjects 2 }
stpxInconsistencyObjects OBJECT IDENTIFIER ::= { stpxObjects 3 }
stpxBackboneFastObjects OBJECT IDENTIFIER ::= { stpxObjects 4 }
stpxRootGuardObjects OBJECT IDENTIFIER ::= { stpxObjects 5 }
stpxSpanningTreeObjects OBJECT IDENTIFIER ::= { stpxObjects 6 }
stpxMISTPObjects OBJECT IDENTIFIER ::= { stpxObjects 7 }
stpxLoopGuardObjects OBJECT IDENTIFIER ::= { stpxObjects 8 }
stpxFastStartObjects OBJECT IDENTIFIER ::= { stpxObjects 9 }
stpxBpduSkewingObjects OBJECT IDENTIFIER ::= { stpxObjects 10 }
stpxMSTObjects  OBJECT IDENTIFIER ::= { stpxObjects 11 }
stpxRSTPObjects OBJECT IDENTIFIER ::= { stpxObjects 12 }
stpxRPVSTObjects OBJECT IDENTIFIER ::= { stpxObjects 13 }
stpxSMSTObjects OBJECT IDENTIFIER ::= { stpxObjects 14 }
stpxNotifications OBJECT IDENTIFIER ::= { ciscoStpExtensionsMIB 2 }
stpxNotificationsPrefix OBJECT IDENTIFIER ::= { stpxNotifications 0 }
stpxMIBConformance OBJECT IDENTIFIER ::= { ciscoStpExtensionsMIB 3 }
stpxMIBCompliances OBJECT IDENTIFIER ::= { stpxMIBConformance 1 }
stpxMIBGroups   OBJECT IDENTIFIER ::= { stpxMIBConformance 2 }

StpxMSTConfigurationDigest ::= OCTET STRING(SIZE(16))
-- TEXTUAL-CONVENTION
--  DspHint
--    1x
--  Status
--    mandatory
--  Descr
--    Represents an MST configuration digest.

stpxUplinkFastEnabled OBJECT-TYPE
    SYNTAX TruthValue
--    Rsyntax INTEGER {
--        true(1),
--        false(2)
--        }
    ACCESS read-write
    STATUS mandatory
    DESCRIPTION
        "An indication of whether the UplinkFast capability is
         administratively enabled on the device.
        
         If the platform does not support configuration of this
         object when the object value of stpxSpanningTreeType is 
         mst(4), then this object is not instantiated."
    ::= { stpxUplinkFastObjects 1 }

stpxUplinkFastTransitions OBJECT-TYPE
    SYNTAX Counter
--  Units
--    transitions
    ACCESS read-only
    STATUS mandatory
    DESCRIPTION
        "The cumulative number of UplinkFast transitions (from
        the STP 'Blocking' state directly to the STP 'Forwarding'
        state).  All transitions are included in this counter,
        irrespective of the instance of the Spanning Tree 
        Protocol on which they occur.
        
        If the platform supports the stpxUplinkFastOperEnabled 
        object, then this object is not instantiated when the 
        object value of stpxUplinkFastOperEnabled is false(2).
        If the platform does not support the 
        stpxUplinkFastOperEnabled object, then this object is 
        not instantiated when the object value of 
        stpxSpanningTreeType is mst(4)."
    ::= { stpxUplinkFastObjects 2 }

stpxUplinkStationLearningGenRate OBJECT-TYPE
    SYNTAX INTEGER(0..32000)
--  Units
--    frames
    ACCESS read-write
    STATUS mandatory
    DESCRIPTION
        "The maximum number of station-learning frames that this
        device will generate in each 100 milli-second period after
        a UplinkFast transition.  By configuring this object, the
        network administrator can limit the rate at which
        station-learning frames are generated.  
        
        If the platform does not support configuration of this
        object when the object value of stpxSpanningTreeType is
        mst(4), then this object is not instantiated."
    ::= { stpxUplinkFastObjects 3 }

stpxUplinkStationLearningFrames OBJECT-TYPE
    SYNTAX Counter
--  Units
--    frames
    ACCESS read-only
    STATUS mandatory
    DESCRIPTION
        "The cumulative number of station-learning frames generated
        due to UplinkFast transitions.  All generated
        station-learning frames are included in this counter,
        irrespective of the instance of the Spanning Tree Protocol
        on which the UplinkFast transition occurred.
        
        If the platform supports the stpxUplinkFastOperEnabled 
        object, then this object is not instantiated when the 
        object value of stpxUplinkFastOperEnabled is false(2).
        If the platform does not support the 
        stpxUplinkFastOperEnabled object, then this object is 
        not instantiated when the object value of 
        stpxSpanningTreeType is mst(4)."
    ::= { stpxUplinkFastObjects 4 }

stpxUplinkFastOperEnabled OBJECT-TYPE
    SYNTAX TruthValue
--    Rsyntax INTEGER {
--        true(1),
--        false(2)
--        }
    ACCESS read-only
    STATUS mandatory
    DESCRIPTION
        "An indication of whether the UplinkFast capability is 
        operationally enabled on the device."
    ::= { stpxUplinkFastObjects 5 }

stpxPreferredVlansTable OBJECT-TYPE
    SYNTAX SEQUENCE OF StpxPreferredVlansEntry
    ACCESS not-accessible
    STATUS mandatory
    DESCRIPTION
        "The table containing indications of which VLANs are
        preferred on which VLAN trunk ports.  The preferred
        VLANs on a trunk port have a lower Path Cost value
        compared with the VLANs on the trunk not in the
        preferred list. If the value of stpxSpanningTreeType 
        is neither pvstPlus(1) nor rapidPvstPlus(5), the 
        configuration in this table has no effect. "
    ::= { stpxVlanObjects 1 }

stpxPreferredVlansEntry OBJECT-TYPE
    SYNTAX StpxPreferredVlansEntry
    ACCESS not-accessible
    STATUS mandatory
    DESCRIPTION
        "An entry indicating which VLANs are preferred on a
        specific VLAN trunk port."
    INDEX { vlanTrunkPortIfIndex }
-- Augments vlanTrunkPortEntry FROM CISCO-VTP-MIB
    ::= { stpxPreferredVlansTable 1 }

StpxPreferredVlansEntry ::= SEQUENCE {
    stpxPreferredVlansMap OCTET STRING,
    stpxPreferredVlansMap2k OCTET STRING,
    stpxPreferredVlansMap3k OCTET STRING,
    stpxPreferredVlansMap4k OCTET STRING
    }

stpxPreferredVlansMap OBJECT-TYPE
    SYNTAX OCTET STRING(SIZE(128))
    ACCESS read-write
    STATUS mandatory
    DESCRIPTION
        "A string of octets containing one bit per VLAN in the
        management domain on this trunk port.  The first octet
        corresponds to VLANs with VlanIndex values of 0 through 7;
        the second octet to VLANs 8 through 15; etc.  The most
        significant bit of each octet corresponds to the lowest
        value VlanIndex in that octet.
        
        For each VLAN, if it is preferred on this trunk port, then
        the bit corresponding to that VLAN is set to '1'.
        The default value is 128 bytes of zeros.
        
        To avoid conflicts between overlapping partial updates by
        multiple managers, i.e., updates which modify only a portion
        of an instance of this object (e.g., enable/disable a single
        VLAN on the trunk port), any SNMP Set operation accessing an
        instance of this object should also write the value of
        vlanTrunkPortSetSerialNo."
    ::= { stpxPreferredVlansEntry 1 }

stpxPreferredVlansMap2k OBJECT-TYPE
    SYNTAX OCTET STRING(SIZE(0..128))
    ACCESS read-write
    STATUS mandatory
    DESCRIPTION
        "A string of octets containing one bit per VLAN for VLANS 
        with VlanIndex values of 1024 through 2047 in the management
        domain on this trunk port.  The first octet corresponds to 
        VLANs with VlanIndex values of 1024 through 1031; 
        the second octet to VLANs 1032 through 1039; etc. 
        The most significant bit of each octet corresponds to the 
        lowest value VlanIndex in that octet. 
        
        For each VLAN, if it is preferred on this trunk port, then 
        the bit corresponding to that VLAN is set to '1'. 
        The default value is 128 bytes of zeros. 
        
        To avoid conflicts between overlapping partial updates by 
        multiple managers, i.e., updates which modify only a portion
        of an instance of this object (e.g., enable/disable a single
        VLAN on the trunk port), any SNMP Set operation accessing an
        instance of this object should also write the value of 
        vlanTrunkPortSetSerialNo."
    ::= { stpxPreferredVlansEntry 2 }

stpxPreferredVlansMap3k OBJECT-TYPE
    SYNTAX OCTET STRING(SIZE(0..128))
    ACCESS read-write
    STATUS mandatory
    DESCRIPTION
        "A string of octets containing one bit per VLAN for VLANS 
        with VlanIndex values of 2048 through 3071 in the management
        domain on this trunk port.  The first octet corresponds to 
        VLANs with VlanIndex values of 2048 through 2055; 
        the second octet to VLANs 2056 through 2063; etc. 
        The most significant bit of each octet corresponds to the 
        lowest value VlanIndex in that octet. 
        
        For each VLAN, if it is preferred on this trunk port, then 
        the bit corresponding to that VLAN is set to '1'. 
        The default value is 128 bytes of zeros. 
        
        To avoid conflicts between overlapping partial updates by 
        multiple managers, i.e., updates which modify only a portion
        of an instance of this object (e.g., enable/disable a single
        VLAN on the trunk port), any SNMP Set operation accessing an
        instance of this object should also write the value of 
        vlanTrunkPortSetSerialNo."
    ::= { stpxPreferredVlansEntry 3 }

stpxPreferredVlansMap4k OBJECT-TYPE
    SYNTAX OCTET STRING(SIZE(0..128))
    ACCESS read-write
    STATUS mandatory
    DESCRIPTION
        "A string of octets containing one bit per VLAN for VLANS 
        with VlanIndex values of 3072 through 4095 in the management
        domain on this trunk port.  The first octet corresponds to 
        VLANs with VlanIndex values of 3072 through 3079; 
        the second octet to VLANs 3080 through 3087; etc. 
        The most significant bit of each octet corresponds to the 
        lowest value VlanIndex in that octet. 
        
        For each VLAN, if it is preferred on this trunk port, then 
        the bit corresponding to that VLAN is set to '1'. 
        The default value is 128 bytes of zeros. 
        
        To avoid conflicts between overlapping partial updates by 
        multiple managers, i.e., updates which modify only a portion
        of an instance of this object (e.g., enable/disable a single
        VLAN on the trunk port), any SNMP Set operation accessing an
        instance of this object should also write the value of 
        vlanTrunkPortSetSerialNo."
    ::= { stpxPreferredVlansEntry 4 }

stpxPVSTVlanTable OBJECT-TYPE
    SYNTAX SEQUENCE OF StpxPVSTVlanEntry
    ACCESS not-accessible
    STATUS mandatory
    DESCRIPTION
        "A list of Virtual LAN entries containing
        information for Spanning Tree PVST+ protocol. 
        An entry will exist for each VLAN existing on 
        the device."
    ::= { stpxVlanObjects 2 }

stpxPVSTVlanEntry OBJECT-TYPE
    SYNTAX StpxPVSTVlanEntry
    ACCESS not-accessible
    STATUS mandatory
    DESCRIPTION
        "An entry containing Spanning Tree PVST+ Protocol 
        information for a particular Virtual LAN."
    INDEX { stpxPVSTVlanIndex }
    ::= { stpxPVSTVlanTable 1 }

StpxPVSTVlanEntry ::= SEQUENCE {
    stpxPVSTVlanIndex VlanIndex,
    stpxPVSTVlanEnable INTEGER
    }

stpxPVSTVlanIndex OBJECT-TYPE
    SYNTAX VlanIndex
--    Rsyntax INTEGER(0..4095)
    ACCESS not-accessible
    STATUS mandatory
    DESCRIPTION
        "An index value that uniquely identifies the
        Virtual LAN associated with this information."
    ::= { stpxPVSTVlanEntry 1 }

stpxPVSTVlanEnable OBJECT-TYPE
    SYNTAX INTEGER {
        enabled(1),
        disabled(2),
        notApplicable(3)
        }
    ACCESS read-write
    STATUS mandatory
    DESCRIPTION
        "Indicates whether Spanning Tree PVST+  
        Protocol is enabled for this Virtual LAN. If 
        Spanning Tree PVST+ Protocol is not supported 
        on this VLAN, then notApplicable(3) will be 
        returned while retrieving the object value for 
        this VLAN.
        
        If the device only supports a single global
        Spanning Tree PVST+ Protocol enable/disable 
        for all the existing VLANs, then the object 
        value assigned to this VLAN will be applied
        to the object values of all the instances
        in this table which do not have the value
        of notApplicable(3).
        
        If the value of stpxSpanningTreeType is neither 
        pvstPlus(1) nor rapidPvstPlus(5), then the value 
        of stpxPVSTVlanEnable for this VLAN can not be 
        changed."
    DEFVAL { enabled }
    ::= { stpxPVSTVlanEntry 2 }

stpxInconsistencyTable OBJECT-TYPE
    SYNTAX SEQUENCE OF StpxInconsistencyEntry
    ACCESS not-accessible
    STATUS mandatory
    DESCRIPTION
        "A table containing a list of the ports for which
        a particular VLAN's Spanning Tree has been found to
        have an inconsistency.  Two types of inconsistency
        are discovered: 1) an inconsistency where two different
        port types have been plugged together; and 2) an
        inconsistency where different switches have different
        PVIDs for the same link."
    ::= { stpxInconsistencyObjects 1 }

stpxInconsistencyEntry OBJECT-TYPE
    SYNTAX StpxInconsistencyEntry
    ACCESS not-accessible
    STATUS mandatory
    DESCRIPTION
        "A VLAN on a particular port for which a Spanning Tree
        inconsistency is currently in effect."
    INDEX { stpxVlanIndex, stpxPortIndex }
    ::= { stpxInconsistencyTable 1 }

StpxInconsistencyEntry ::= SEQUENCE {
    stpxVlanIndex VlanIndex,
    stpxPortIndex INTEGER,
    stpxInconsistentState OCTET STRING
    }

stpxVlanIndex OBJECT-TYPE
    SYNTAX VlanIndex
--    Rsyntax INTEGER(0..4095)
    ACCESS not-accessible
    STATUS mandatory
    DESCRIPTION
        "The VLAN id of the VLAN."
    ::= { stpxInconsistencyEntry 1 }

stpxPortIndex OBJECT-TYPE
    SYNTAX INTEGER(1..65535)
    ACCESS not-accessible
    STATUS mandatory
    DESCRIPTION
        "The value of dot1dBasePort (i.e. dot1dBridge.1.4)
         for the bridge port."
    REFERENCE
        "dot1dBasePort is defined in RFC1493."
    ::= { stpxInconsistencyEntry 2 }

stpxInconsistentState OBJECT-TYPE
    SYNTAX OCTET STRING(SIZE(1..2))
        -- BITS are:
        --   typeInconsistent(0)
        --   pvidInconsistent(1)
    ACCESS read-only
    STATUS mandatory
    DESCRIPTION
        "The types of inconsistency which have been discovered on
         this port for this VLAN's Spanning Tree.
        
         When this object exists, the value of the corresponding
         instance of the Bridge MIB's dot1dStpPortState object will
         be 'broken(6)'."
    REFERENCE
        "dot1dStpPortState is defined in RFC-1493."
    ::= { stpxInconsistencyEntry 3 }

stpxBackboneFastEnabled OBJECT-TYPE
    SYNTAX TruthValue
--    Rsyntax INTEGER {
--        true(1),
--        false(2)
--        }
    ACCESS read-write
    STATUS mandatory
    DESCRIPTION
        "An indication of whether the BackboneFast capability is
         administratively enabled on the device."
    ::= { stpxBackboneFastObjects 1 }

stpxBackboneFastInInferiorBPDUs OBJECT-TYPE
    SYNTAX Counter
    ACCESS read-only
    STATUS mandatory
    DESCRIPTION
        "The number of inferior BPDUs received by the switch 
         since the stpxBackboneFastOperEnabled has
         become true(1). If the value of 
         stpxBackboneFastOperEnabled is false(2), then this 
         mib object will have a value of 0."
    ::= { stpxBackboneFastObjects 2 }

stpxBackboneFastInRLQRequestPDUs OBJECT-TYPE
    SYNTAX Counter
    ACCESS read-only
    STATUS mandatory
    DESCRIPTION
        "The number of Root Link Query request PDUs received by the
         switch since the stpxBackboneFastOperEnabled has become
         true(1). If the value of stpxBackboneFastOperEnabled is
         false(2), then this mib object will have a value of 0."
    ::= { stpxBackboneFastObjects 3 }

stpxBackboneFastInRLQResponsePDUs OBJECT-TYPE
    SYNTAX Counter
    ACCESS read-only
    STATUS mandatory
    DESCRIPTION
        "The number of Root Link Query response PDUs received by the
         switch since the stpxBackboneFastOperEnabled has become
         true(1). If the value of stpxBackboneFastOperEnabled is
         false(2), then this mib object will have a value of 0."
    ::= { stpxBackboneFastObjects 4 }

stpxBackboneFastOutRLQRequestPDUs OBJECT-TYPE
    SYNTAX Counter
    ACCESS read-only
    STATUS mandatory
    DESCRIPTION
        "The number of Root Link Query request PDUs transmitted by
         the switch since the stpxBackboneFastOperEnabled has become
         true(1). If the value of stpxBackboneFastOperEnabled is
         false(2), then this mib object will have a value of 0."
    ::= { stpxBackboneFastObjects 5 }

stpxBackboneFastOutRLQResponsePDUs OBJECT-TYPE
    SYNTAX Counter
    ACCESS read-only
    STATUS mandatory
    DESCRIPTION
        "The number of Root Link Query response PDUs transmitted by
         the switch since the stpxBackboneFastOperEnabled has become
         true(1). If the value of stpxBackboneFastOperEnabled is
         false(2), then this mib object will have a value of 0."
    ::= { stpxBackboneFastObjects 6 }

stpxBackboneFastOperEnabled OBJECT-TYPE
    SYNTAX TruthValue
--    Rsyntax INTEGER {
--        true(1),
--        false(2)
--        }
    ACCESS read-only
    STATUS mandatory
    DESCRIPTION
        "An indication of whether the BackboneFast capability is
        operationally enabled on the device."
    ::= { stpxBackboneFastObjects 7 }

stpxRootGuardConfigTable OBJECT-TYPE
    SYNTAX SEQUENCE OF StpxRootGuardConfigEntry
    ACCESS not-accessible
    STATUS mandatory
    DESCRIPTION
        "A table containing a list of the bridge ports for which
        Spanning Tree RootGuard capability can be configured."
    ::= { stpxRootGuardObjects 1 }

stpxRootGuardConfigEntry OBJECT-TYPE
    SYNTAX StpxRootGuardConfigEntry
    ACCESS not-accessible
    STATUS mandatory
    DESCRIPTION
        "A bridge port for which Spanning Tree RootGuard
        capability can be configured."
    INDEX { stpxRootGuardConfigPortIndex }
    ::= { stpxRootGuardConfigTable 1 }

StpxRootGuardConfigEntry ::= SEQUENCE {
    stpxRootGuardConfigPortIndex INTEGER,
    stpxRootGuardConfigEnabled TruthValue
    }

stpxRootGuardConfigPortIndex OBJECT-TYPE
    SYNTAX INTEGER(1..65535)
    ACCESS not-accessible
    STATUS mandatory
    DESCRIPTION
        "The value of dot1dBasePort (i.e. dot1dBridge.1.4)
         for the bridge port."
    REFERENCE
        "dot1dBasePort is defined in RFC1493."
    ::= { stpxRootGuardConfigEntry 1 }

stpxRootGuardConfigEnabled OBJECT-TYPE
    SYNTAX TruthValue
--    Rsyntax INTEGER {
--        true(1),
--        false(2)
--        }
    ACCESS read-write
    STATUS mandatory
    DESCRIPTION
        "An indication of whether the RootGuard capability is 
        enabled on this port or not. This configuration will be
        applied to all Spanning Tree instances in which this port 
        exists."
    DEFVAL { false }
    ::= { stpxRootGuardConfigEntry 2 }

stpxRootInconsistencyTable OBJECT-TYPE
    SYNTAX SEQUENCE OF StpxRootInconsistencyEntry
    ACCESS not-accessible
    STATUS mandatory
    DESCRIPTION
        "A table containing a list of the bridge ports for which
        a particular Spanning Tree instance has been found 
        to have an root-inconsistency. The agent creates a new 
        entry in this table whenever it detects a new 
        root-inconsistency, and deletes entries 
        when/soon after the inconsistency is no longer present."
    ::= { stpxRootGuardObjects 2 }

stpxRootInconsistencyEntry OBJECT-TYPE
    SYNTAX StpxRootInconsistencyEntry
    ACCESS not-accessible
    STATUS mandatory
    DESCRIPTION
        "A Spanning Tree instance on a particular port for 
        which a Spanning Tree root-inconsistency is currently 
        in effect."
    INDEX { stpxRootInconsistencyIndex, stpxRootInconsistencyPortIndex }
    ::= { stpxRootInconsistencyTable 1 }

StpxRootInconsistencyEntry ::= SEQUENCE {
    stpxRootInconsistencyIndex INTEGER,
    stpxRootInconsistencyPortIndex INTEGER,
    stpxRootInconsistencyState TruthValue
    }

stpxRootInconsistencyIndex OBJECT-TYPE
    SYNTAX INTEGER(0..65535)
    ACCESS not-accessible
    STATUS mandatory
    DESCRIPTION
        "The Spanning Tree instance id, such as the VLAN id
        of the VLAN if the object value of stpxSpanningTreeType
        is pvstPlus(1) or rapidPvstPlus(5)."
    ::= { stpxRootInconsistencyEntry 1 }

stpxRootInconsistencyPortIndex OBJECT-TYPE
    SYNTAX INTEGER(1..65535)
    ACCESS not-accessible
    STATUS mandatory
    DESCRIPTION
        "The value of dot1dBasePort (i.e. dot1dBridge.1.4)
         for the bridge port."
    REFERENCE
        "dot1dBasePort is defined in RFC1493."
    ::= { stpxRootInconsistencyEntry 2 }

stpxRootInconsistencyState OBJECT-TYPE
    SYNTAX TruthValue
--    Rsyntax INTEGER {
--        true(1),
--        false(2)
--        }
    ACCESS read-only
    STATUS mandatory
    DESCRIPTION
        "Indicates whether the port on a particular Spanning 
         Tree instance is currently in root-inconsistent 
         state or not."
    ::= { stpxRootInconsistencyEntry 3 }

stpxSpanningTreeType OBJECT-TYPE
    SYNTAX INTEGER {
        pvstPlus(1),
        mistp(2),
        mistpPvstPlus(3),
        mst(4),
        rapidPvstPlus(5)
        }
    ACCESS read-write
    STATUS mandatory
    DESCRIPTION
        "The actual mode of spanning tree protocol runs
        on the  device. It can be one of the following:
        
        pvstPlus -- PVST+ (Per VLAN Spanning Tree+ Protocol).
        
        mistp -- MISTP (Multi Instance Spanning Tree Protocol).
        
        mistpPvstPlus --  MISTP with the tunneling scheme
                             enabled for PVST+.
        
        mst -- IEEE 802.1s Multiple Spanning Tree (MST)
               with IEEE 802.1w Rapid Spanning Tree Protocol
               (RSTP).
        
        rapidPvstPlus -- IEEE 802.1w Rapid Spanning Tree 
                Protocol (RSTP) for all vlans in PVST+.
        
        When the value of this MIB object gets changed, the 
        network connectivity would be affected and the 
        connectivity to this device would also be lost 
        temporarily."
    DEFVAL { pvstPlus }
    ::= { stpxSpanningTreeObjects 1 }

stpxSpanningTreePathCostMode OBJECT-TYPE
    SYNTAX INTEGER {
        short(1),
        long(2)
        }
    ACCESS read-write
    STATUS mandatory
    DESCRIPTION
        "Indicates the administrative  spanning tree path cost mode 
         configured on device."
    DEFVAL { short }
    ::= { stpxSpanningTreeObjects 2 }

stpxLongStpPortPathCostTable OBJECT-TYPE
    SYNTAX SEQUENCE OF StpxLongStpPortPathCostEntry
    ACCESS not-accessible
    STATUS mandatory
    DESCRIPTION
        "A table containing the spanning tree port path cost
        configuration when stpxSpanningTreePathCostOperMode is
        long(2).
        
        If the value of stpxSpanningTreePathCostOperMode is 
        short(1), this table is not instantiated."
    ::= { stpxSpanningTreeObjects 3 }

stpxLongStpPortPathCostEntry OBJECT-TYPE
    SYNTAX StpxLongStpPortPathCostEntry
    ACCESS not-accessible
    STATUS mandatory
    DESCRIPTION
        "A conceptual row containing the spanning tree port path cost
         configuration."
    INDEX { dot1dStpPort }
-- Augments dot1dStpPortEntry FROM BRIDGE-MIB
    ::= { stpxLongStpPortPathCostTable 1 }

StpxLongStpPortPathCostEntry ::= SEQUENCE {
    stpxLongStpPortPathCost Gauge
    }

stpxLongStpPortPathCost OBJECT-TYPE
    SYNTAX Gauge
    ACCESS read-write
    STATUS mandatory
    DESCRIPTION
        "The contribution of this port to the path cost (in 32
         bits value) of paths towards the spanning tree root which
         include this port.
        
         This object is used to configure the spanning tree port
         path cost in 32 bits value range when the
         stpxSpanningTreePathCostOperMode is long(2).
        
         If the stpxSpanningTreePathCostOperMode is short(1), this 
         MIB object is not instantiated."
    ::= { stpxLongStpPortPathCostEntry 1 }

stpxExtendedSysIDAdminEnabled OBJECT-TYPE
    SYNTAX TruthValue
--    Rsyntax INTEGER {
--        true(1),
--        false(2)
--        }
    ACCESS read-write
    STATUS mandatory
    DESCRIPTION
        "Indicates whether Extended System ID feature 
         is administratively enabled on the device or not."
    REFERENCE
        "IEEE 802.1t."
    ::= { stpxSpanningTreeObjects 4 }

stpxExtendedSysIDOperEnabled OBJECT-TYPE
    SYNTAX TruthValue
--    Rsyntax INTEGER {
--        true(1),
--        false(2)
--        }
    ACCESS read-only
    STATUS mandatory
    DESCRIPTION
        "Indicates whether Extended System ID feature 
         is operationaly enabled on the device or not.
        
         If the value of this object is true(1), then
         the accepted values for dot1dStpPriority
         in BRIDGE-MIB should be multiples of 4096 plus
         bridge instance ID, such as VlanIndex. Changing
         this object value might cause the values of
         dot1dBaseBridgeAddress and dot1dStpPriority
         in BRIDGE-MIB to be changed also."
    REFERENCE
        "IEEE 802.1t."
    ::= { stpxSpanningTreeObjects 5 }

stpxNotificationEnable OBJECT-TYPE
    SYNTAX OCTET STRING(SIZE(1..2))
        -- BITS are:
        --   newRoot(0)
        --   topologyChange(1)
        --   inconsistency(2)
        --   rootInconsistency(3)
        --   loopInconsistency(4)
    ACCESS read-write
    STATUS mandatory
    DESCRIPTION
        "Indicates whether a specified notification is enabled or not.
        If a bit corresponding to a notification is set to 1, then 
        the specified notification can be generated.
        
        newRoot -- the newRoot notification as defined in BRIDGE-MIB.
        
        topologyChange -- the topologyChange notification as
                          defined in BRIDGE-MIB.
        
        inconsistency -- the stpxInconsistencyUpdate notification.
        
        rootInconsistency -- the stpxRootInconsistencyUpdate 
                             notification.
        
        loopInconsistency -- the stpxLoopInconsistencyUpdate 
                             notification."
    ::= { stpxSpanningTreeObjects 6 }

stpxSpanningTreePathCostOperMode OBJECT-TYPE
    SYNTAX INTEGER {
        short(1),
        long(2)
        }
    ACCESS read-only
    STATUS mandatory
    DESCRIPTION
        "Indicate the operational spanning tree path cost mode
        on device. This mode applies to all instances of the Spanning
        Tree protocol running on the device. 
        
        When the value of this MIB object gets changed, the path cost
        of all ports will be reassigned to the default path cost
        values based on the new spanning tree path cost mode and the
        ports' speed.
        
        When the value of this MIB object is long(2),
        the stpxLongStpPortPathCost MIB object must be used in order
        to retrieve/configure the spanning tree port path cost as a
        32 bits value. The set operation on dot1dStpPortPathCost in
        BRIDGE-MIB will be rejected. While retrieving the value of
        dot1dStpPortPathCost, the maximum value of 65535 will be
        returned if the value of stpxLongStpPortPathCost for the same
        instance exceeds 65535.
        
        When the value of this MIB object is short(1),
        the dot1dStpPortPathCost in BRIDGE-MIB must be used."
    ::= { stpxSpanningTreeObjects 7 }

stpxMISTPInstanceNumber OBJECT-TYPE
    SYNTAX INTEGER(1..256)
    ACCESS read-only
    STATUS mandatory
    DESCRIPTION
        "The number of MISTP instances, that are supported by the device 
        when the value of stpxSpanningTreeType is either mistp(2)
        or mistpPvstPlus(3)."
    ::= { stpxMISTPObjects 1 }

stpxMISTPInstanceTable OBJECT-TYPE
    SYNTAX SEQUENCE OF StpxMISTPInstanceEntry
    ACCESS not-accessible
    STATUS mandatory
    DESCRIPTION
        "This table contains one entry for each instance of MISTP and 
        it contains stpxMISTPInstanceNumber entries, numbered from 1
        to stpxMISTPInstanceNumber.
        
        This table is only instantiated when the value of 
        stpxSpanningTreeType is mistp(2) or mistpPvstPlus(3)."
    ::= { stpxMISTPObjects 2 }

stpxMISTPInstanceEntry OBJECT-TYPE
    SYNTAX StpxMISTPInstanceEntry
    ACCESS not-accessible
    STATUS mandatory
    DESCRIPTION
        "A conceptual row containing the status of the MISTP 
        instance."
    INDEX { stpxMISTPInstanceIndex }
    ::= { stpxMISTPInstanceTable 1 }

StpxMISTPInstanceEntry ::= SEQUENCE {
    stpxMISTPInstanceIndex INTEGER,
    stpxMISTPInstanceEnable TruthValue,
    stpxMISTPInstanceVlansMapped OCTET STRING,
    stpxMISTPInstanceVlansMapped2k OCTET STRING,
    stpxMISTPInstanceVlansMapped3k OCTET STRING,
    stpxMISTPInstanceVlansMapped4k OCTET STRING
    }

stpxMISTPInstanceIndex OBJECT-TYPE
    SYNTAX INTEGER(1..256)
    ACCESS not-accessible
    STATUS mandatory
    DESCRIPTION
        "An arbitrary integer within the range from 1 to the value of
        stpxMISTPInstanceNumber that uniquely identifies an instance."
    ::= { stpxMISTPInstanceEntry 1 }

stpxMISTPInstanceEnable OBJECT-TYPE
    SYNTAX TruthValue
--    Rsyntax INTEGER {
--        true(1),
--        false(2)
--        }
    ACCESS read-write
    STATUS mandatory
    DESCRIPTION
        "This object indicates whether the MISTP protocol is currently
        enabled on the MISTP instance.
        
        If this object is set to
           'true'    - the MISTP protocol will run on this instance.
                      
           'false'   - the MISTP protocol will stop running on this 
                       instance."
    DEFVAL { true }
    ::= { stpxMISTPInstanceEntry 2 }

stpxMISTPInstanceVlansMapped OBJECT-TYPE
    SYNTAX OCTET STRING(SIZE(0..128))
    ACCESS read-only
    STATUS mandatory
    DESCRIPTION
        "A string of octets containing one bit per VLAN. The
        first octet corresponds to VLANs with VlanIndex values
        of 0 through 7; the second octet to VLANs 8 through
        15; etc.  The most significant bit of each octet
        corresponds to the lowest value VlanIndex in that octet.
        
        For each VLAN, if it is mapped to this MISTP instance,
        then the bit corresponding to that VLAN is set to '1'."
    ::= { stpxMISTPInstanceEntry 3 }

stpxMISTPInstanceVlansMapped2k OBJECT-TYPE
    SYNTAX OCTET STRING(SIZE(0..128))
    ACCESS read-only
    STATUS mandatory
    DESCRIPTION
        "A string of octets containing one bit per VLAN for
        VLANS with VlanIndex values of 1024 through 2047. The
        first octet corresponds to VLANs with VlanIndex values
        of 1024 through 1031; the second octet to VLANs 1032
        through 1039; etc.  The most significant bit of each
        octet corresponds to the lowest value VlanIndex in that
        octet.
        
        For each VLAN, if it is mapped to this MISTP instance,
        then the bit corresponding to that VLAN is set to '1'.
        
        This object is only instantiated on devices with 
        support for VlanIndex up to 4095."
    ::= { stpxMISTPInstanceEntry 4 }

stpxMISTPInstanceVlansMapped3k OBJECT-TYPE
    SYNTAX OCTET STRING(SIZE(0..128))
    ACCESS read-only
    STATUS mandatory
    DESCRIPTION
        "A string of octets containing one bit per VLAN for
        VLANS with VlanIndex values of 2048 through 3071. The
        first octet corresponds to VLANs with VlanIndex values
        of 2048 through 2055; the second octet to VLANs 2056
        through 2063; etc.  The most significant bit of each
        octet corresponds to the lowest value VlanIndex in that
        octet.
        
        For each VLAN, if it is mapped to this MISTP instance,
        then the bit corresponding to that VLAN is set to '1'.
        
        This object is only instantiated on devices with 
        support for VlanIndex up to 4095."
    ::= { stpxMISTPInstanceEntry 5 }

stpxMISTPInstanceVlansMapped4k OBJECT-TYPE
    SYNTAX OCTET STRING(SIZE(0..128))
    ACCESS read-only
    STATUS mandatory
    DESCRIPTION
        "A string of octets containing one bit per VLAN for
        VLANS with VlanIndex values of 3072 through 4095. The
        first octet corresponds to VLANs with VlanIndex values
        of 3072 through 3079; the second octet to VLANs 3080
        through 3087; etc.  The most significant bit of each
        octet corresponds to the lowest value VlanIndex in that
        octet.
        
        For each VLAN, if it is mapped to this MISTP instance,
        then the bit corresponding to that VLAN is set to '1'.
        
        This object is only instantiated on devices with 
        support for VlanIndex up to 4095."
    ::= { stpxMISTPInstanceEntry 6 }

stpxVlanMISTPInstMapTable OBJECT-TYPE
    SYNTAX SEQUENCE OF StpxVlanMISTPInstMapEntry
    ACCESS not-accessible
    STATUS mandatory
    DESCRIPTION
        "A table containing the MISTP Instance Index of the VLANs for a
        particular management domain. 
        
        This table is only instantiated when the value of  
        stpxSpanningTreeType is mistp(2) or mistpPvstPlus(3)."
    ::= { stpxMISTPObjects 3 }

stpxVlanMISTPInstMapEntry OBJECT-TYPE
    SYNTAX StpxVlanMISTPInstMapEntry
    ACCESS not-accessible
    STATUS mandatory
    DESCRIPTION
        "A conceptual row containing the MISTP Instance Index of the 
        VLAN for a particular management domain."
    INDEX { managementDomainIndex, vtpVlanIndex }
-- Augments vtpVlanEntry FROM CISCO-VTP-MIB
    ::= { stpxVlanMISTPInstMapTable 1 }

StpxVlanMISTPInstMapEntry ::= SEQUENCE {
    stpxVlanMISTPInstMapInstIndex INTEGER
    }

stpxVlanMISTPInstMapInstIndex OBJECT-TYPE
    SYNTAX INTEGER(0..256)
    ACCESS read-only
    STATUS mandatory
    DESCRIPTION
        "The MISTP instance, to which the corresponding vlan is mapped.
        If this value of this mib object is 0,  the corresponding vlan 
        is not configured to be mapped to any MISTP instance and all
        the ports under this VLAN remain in blocking state."
    ::= { stpxVlanMISTPInstMapEntry 1 }

stpxVlanMISTPInstMapEditTable OBJECT-TYPE
    SYNTAX SEQUENCE OF StpxVlanMISTPInstMapEditEntry
    ACCESS not-accessible
    STATUS mandatory
    DESCRIPTION
        "A table containing the MISTP related information for the VLANs 
        in the Edit Buffers for a particular management domain.
        
        This table is only instantiated when when the value of
        stpxSpanningTreeType is mistp(2) or mistpPvstPlus(3)."
    ::= { stpxMISTPObjects 4 }

stpxVlanMISTPInstMapEditEntry OBJECT-TYPE
    SYNTAX StpxVlanMISTPInstMapEditEntry
    ACCESS not-accessible
    STATUS mandatory
    DESCRIPTION
        "Information about one VLAN mapping to one instance 
        in the Edit Buffer for a particular management domain."
    INDEX { managementDomainIndex, vtpVlanEditIndex }
-- Augments vtpVlanEditEntry FROM CISCO-VTP-MIB
    ::= { stpxVlanMISTPInstMapEditTable 1 }

StpxVlanMISTPInstMapEditEntry ::= SEQUENCE {
    stpxVlanMISTPInstMapEditInstIndex INTEGER
    }

stpxVlanMISTPInstMapEditInstIndex OBJECT-TYPE
    SYNTAX INTEGER(0..256)
    ACCESS read-write
    STATUS mandatory
    DESCRIPTION
        "The MISTP instance, to which the corresponding vlan would be 
         mapped. The value of this mib object is from 0 to the value of
         stpxMISTPInstanceNumber. If setting the value of this object
         to 0, the corresponding vlan will not be mapped to a MISTP 
         instance and all the ports under this VLAN will be moved into
         the blocking state."
    ::= { stpxVlanMISTPInstMapEditEntry 1 }

stpxPreferredMISTPInstancesTable OBJECT-TYPE
    SYNTAX SEQUENCE OF StpxPreferredMISTPInstancesEntry
    ACCESS not-accessible
    STATUS mandatory
    DESCRIPTION
        "The table containing indications of which MISTP instances
        are preferred on which  trunk ports.  The preferred
        MISTP instances on a trunk port have a lower Path Cost value
        compared with the MISTP instances on the trunk not in the
        preferred list. 
        
        This table is only instantiated when the value of
        stpxSpanningTreeType is mistp(2) or mistpPvstPlus(3)."
    ::= { stpxMISTPObjects 5 }

stpxPreferredMISTPInstancesEntry OBJECT-TYPE
    SYNTAX StpxPreferredMISTPInstancesEntry
    ACCESS not-accessible
    STATUS mandatory
    DESCRIPTION
        "An entry indicating which MISTP instances are preferred on
        a specific trunk port."
    INDEX { vlanTrunkPortIfIndex }
-- Augments vlanTrunkPortEntry FROM CISCO-VTP-MIB
    ::= { stpxPreferredMISTPInstancesTable 1 }

StpxPreferredMISTPInstancesEntry ::= SEQUENCE {
    stpxPreferredMISTPInstancesMap OCTET STRING
    }

stpxPreferredMISTPInstancesMap OBJECT-TYPE
    SYNTAX OCTET STRING(SIZE(1..32))
    ACCESS read-write
    STATUS mandatory
    DESCRIPTION
        "A string of octets containing one bit per MISTP instances 
        in the management domain on this trunk port. The first octet
        corresponds to MISTP instances with InstIndex values of 1 
        through 8; the second octet to MISTP instances 9 through 16;
        etc. The most significant bit of each octet corresponds to 
        the lowest value instanceIndex in that octet. The number of 
        bits for this mib object will be determined by the value of 
        stpxMISTPInstanceNumber.
        
        For each instance, if it is preferred on this trunk port,
        then the bit corresponding to that instance is set to '1'.
        
        
        To avoid conflicts between overlapping partial updates by
        multiple managers, i.e., updates which modify only a portion
        of an instance of this object (e.g., enable/disable a single
        instance on the trunk port), any SNMP Set operation 
        accessing an instance of this object should also write the 
        value of vlanTrunkPortSetSerialNo."
    ::= { stpxPreferredMISTPInstancesEntry 1 }

stpxLoopGuardConfigTable OBJECT-TYPE
    SYNTAX SEQUENCE OF StpxLoopGuardConfigEntry
    ACCESS not-accessible
    STATUS mandatory
    DESCRIPTION
        "A table containing a list of the bridge ports for which
        Spanning Tree LoopGuard capability can be configured."
    ::= { stpxLoopGuardObjects 1 }

stpxLoopGuardConfigEntry OBJECT-TYPE
    SYNTAX StpxLoopGuardConfigEntry
    ACCESS not-accessible
    STATUS mandatory
    DESCRIPTION
        "A bridge port for which Spanning Tree LoopGuard 
        capability can be configured."
    INDEX { stpxLoopGuardConfigPortIndex }
    ::= { stpxLoopGuardConfigTable 1 }

StpxLoopGuardConfigEntry ::= SEQUENCE {
    stpxLoopGuardConfigPortIndex INTEGER,
    stpxLoopGuardConfigEnabled TruthValue,
    stpxLoopGuardConfigMode INTEGER
    }

stpxLoopGuardConfigPortIndex OBJECT-TYPE
    SYNTAX INTEGER(1..65535)
    ACCESS not-accessible
    STATUS mandatory
    DESCRIPTION
        "The value of dot1dBasePort (i.e. dot1dBridge.1.4)
         for the bridge port."
    REFERENCE
        "dot1dBasePort is defined in RFC1493."
    ::= { stpxLoopGuardConfigEntry 1 }

stpxLoopGuardConfigEnabled OBJECT-TYPE
    SYNTAX TruthValue
--    Rsyntax INTEGER {
--        true(1),
--        false(2)
--        }
    ACCESS read-write
    STATUS deprecated
    DESCRIPTION
        "An indication of whether the LoopGuard capability is 
        enabled on this port or not. This configuration will be
        applied to all the Spanning Tree instances in which this 
        port exists.
        
        In order to support additional Loop Guard config mode
        (default) as defined in stpxLoopGuardConfigMode other 
        than enable (true(1)) or disable (false(2)) as defined 
        in this object, stpxLoopGuardConfigMode object needs to 
        be used.
        
        When the stpxLoopGuardConfigMode object has the value of
        enable(1), the value of stpxLoopGuardConfigEnabled for 
        the same instance will be true(1). When the 
        stpxLoopGuardConfigMode object has the value of disable(2), 
        the value of stpxLoopGuardConfigEnabled for the same 
        instance will be false(2). When the stpxLoopGuardConfigMode 
        object has the value of default(3), the value of 
        stpxLoopGuardConfigEnabled for the same instance will 
        depend on the object value of 
        stpxLoopGuardGlobalDefaultMode."
    DEFVAL { false }
    ::= { stpxLoopGuardConfigEntry 2 }

stpxLoopGuardConfigMode OBJECT-TYPE
    SYNTAX INTEGER {
        enable(1),
        disable(2),
        default(3)
        }
    ACCESS read-write
    STATUS mandatory
    DESCRIPTION
        "Indicates the mode of Loop Guard Feature on this 
        port. This configuration will be applied to all 
        the Spanning Tree instances in which this port 
        exists.
        
        enable -- the Loop Guard feature is enabled on this 
                  port. 
        
        disable -- the Loop Guard feature is disabled on this 
                  port.  
        
        default -- whether the Loop Guard feature is enabled
                   or not on this port depends on the object 
                   value of stpxLoopGuardGlobalDefaultMode."
    ::= { stpxLoopGuardConfigEntry 3 }

stpxLoopInconsistencyTable OBJECT-TYPE
    SYNTAX SEQUENCE OF StpxLoopInconsistencyEntry
    ACCESS not-accessible
    STATUS mandatory
    DESCRIPTION
        "A table containing a list of the bridge ports for which
        a particular Spanning Tree instance has been found
        to have a loop-inconsistency. The agent creates a new
        entry in this table whenever it detects a new
        loop-inconsistency, and deletes entries
        when/soon after the inconsistency is no longer present."
    ::= { stpxLoopGuardObjects 2 }

stpxLoopInconsistencyEntry OBJECT-TYPE
    SYNTAX StpxLoopInconsistencyEntry
    ACCESS not-accessible
    STATUS mandatory
    DESCRIPTION
        "A Spanning Tree instance on a particular port for
        which a Spanning Tree loop-inconsistency is currently
        in effect."
    INDEX { stpxLoopInconsistencyIndex, stpxLoopInconsistencyPortIndex }
    ::= { stpxLoopInconsistencyTable 1 }

StpxLoopInconsistencyEntry ::= SEQUENCE {
    stpxLoopInconsistencyIndex INTEGER,
    stpxLoopInconsistencyPortIndex INTEGER,
    stpxLoopInconsistencyState TruthValue
    }

stpxLoopInconsistencyIndex OBJECT-TYPE
    SYNTAX INTEGER(0..65535)
    ACCESS not-accessible
    STATUS mandatory
    DESCRIPTION
        "The Spanning Tree instance id, such as the VLAN id
         of the VLAN if the object value of stpxSpanningTreeType
         is pvstPlus(1) or rapidPvstPlus(5)."
    ::= { stpxLoopInconsistencyEntry 1 }

stpxLoopInconsistencyPortIndex OBJECT-TYPE
    SYNTAX INTEGER(1..65535)
    ACCESS not-accessible
    STATUS mandatory
    DESCRIPTION
        "The value of dot1dBasePort (i.e. dot1dBridge.1.4)
         for the bridge port."
    REFERENCE
        "dot1dBasePort is defined in RFC1493."
    ::= { stpxLoopInconsistencyEntry 2 }

stpxLoopInconsistencyState OBJECT-TYPE
    SYNTAX TruthValue
--    Rsyntax INTEGER {
--        true(1),
--        false(2)
--        }
    ACCESS read-only
    STATUS mandatory
    DESCRIPTION
        "Indicates whether the port on a particular Spanning 
         Tree instance is currently in loop-inconsistent 
         state or not."
    ::= { stpxLoopInconsistencyEntry 3 }

stpxLoopGuardGlobalDefaultMode OBJECT-TYPE
    SYNTAX INTEGER {
        enable(1),
        disable(2)
        }
    ACCESS read-write
    STATUS mandatory
    DESCRIPTION
        "Indicates the global default config mode of LoopGuard 
        feature on the device."
    ::= { stpxLoopGuardObjects 3 }

stpxFastStartBpduGuardEnable OBJECT-TYPE
    SYNTAX TruthValue
--    Rsyntax INTEGER {
--        true(1),
--        false(2)
--        }
    ACCESS read-write
    STATUS mandatory
    DESCRIPTION
        "Indicates the global default mode of the Bpdu
        Guard feature on the device.
        
        On platforms that does not support per port 
        Bpdu Guard configuration as indicated by
        the object stpxFastStartPortBpduGuardMode,
        if  the value of this object is set to true(1), 
        and the Fast Start Feature is operationally 
        enabled on a port, then that port will be 
        immediately disabled when the system receives
        a BPDU from that port."
    DEFVAL { false }
    ::= { stpxFastStartObjects 1 }

stpxFastStartBpduFilterEnable OBJECT-TYPE
    SYNTAX TruthValue
--    Rsyntax INTEGER {
--        true(1),
--        false(2)
--        }
    ACCESS read-write
    STATUS mandatory
    DESCRIPTION
        "Indicates the global default mode of the Bpdu 
        Filter feature on the device.
        
        On platforms that does not support per port 
        Bpdu Filter configuration as indicated by
        the object stpxFastStartPortBpduFilterMode,
        if  the value of this object is set to true(1), 
        and the Fast Start Feature is operationally 
        enabled on a port, then no BPDUs will be 
        transmitted on this port."
    DEFVAL { false }
    ::= { stpxFastStartObjects 2 }

stpxFastStartPortTable OBJECT-TYPE
    SYNTAX SEQUENCE OF StpxFastStartPortEntry
    ACCESS not-accessible
    STATUS mandatory
    DESCRIPTION
        "A table containing a list of the bridge ports for
        which Spanning Tree Port Fast Start can be
        configured."
    ::= { stpxFastStartObjects 3 }

stpxFastStartPortEntry OBJECT-TYPE
    SYNTAX StpxFastStartPortEntry
    ACCESS not-accessible
    STATUS mandatory
    DESCRIPTION
        "A bridge port for which Spanning Tree Port Fast
        Start can be configured."
    INDEX { stpxFastStartPortIndex }
    ::= { stpxFastStartPortTable 1 }

StpxFastStartPortEntry ::= SEQUENCE {
    stpxFastStartPortIndex INTEGER,
    stpxFastStartPortEnable TruthValue,
    stpxFastStartPortMode INTEGER,
    stpxFastStartPortBpduGuardMode INTEGER,
    stpxFastStartPortBpduFilterMode INTEGER
    }

stpxFastStartPortIndex OBJECT-TYPE
    SYNTAX INTEGER(1..65535)
    ACCESS not-accessible
    STATUS mandatory
    DESCRIPTION
        "The value of dot1dBasePort (i.e. dot1dBridge.1.4)
         for the bridge port."
    REFERENCE
        "dot1dBasePort is defined in RFC1493."
    ::= { stpxFastStartPortEntry 1 }

stpxFastStartPortEnable OBJECT-TYPE
    SYNTAX TruthValue
--    Rsyntax INTEGER {
--        true(1),
--        false(2)
--        }
    ACCESS read-write
    STATUS deprecated
    DESCRIPTION
        "Indicates whether the port is operating in spantree
        fast start mode.  A port with fast start enabled is
        immediately put in spanning tree forwarding state when
        that port is detected by the Spanning Tree, rather 
        than starting in blocking state which is the normal 
        operation.
        
        In order to support additional Fast Start enable mode
        (enableForTrunk and default) as defined in
        stpxFastStartPortMode other than enable (true(1))
        or disable (false(2)) as defined in this object,
        stpxFastStartPortMode object needs to be used.
        
        When the stpxFastStartPortMode has the value of
        enable(1) or enableForTrunk(3), the value of
        stpxFastStartPortEnable for the same instance
        will be true(1). When the stpxFastStartPortMode
        has the value of disable(2), the value of 
        stpxFastStartPortEnable for the same instance will be 
        false(2). When the stpxFastStartPortMode has the value 
        of default(4), the value of stpxFastStartPortEnable for 
        the same instance depends on the object value of 
        stpxFastStartGlobalDefaultMode."
    DEFVAL { false }
    ::= { stpxFastStartPortEntry 2 }

stpxFastStartPortMode OBJECT-TYPE
    SYNTAX INTEGER {
        enable(1),
        disable(2),
        enableForTrunk(3),
        default(4),
        network(5)
        }
    ACCESS read-write
    STATUS mandatory
    DESCRIPTION
        "Indicates the mode of Fast Start Feature on the 
        port. A port with fast start enabled is immediately 
        put in spanning tree forwarding state when the port
        is detected by the Spanning Tree, rather than 
        starting in blocking state which is the normal 
        operation.
        
        enable -- the fast start feature is enabled on this 
                  port but will only take effect when the 
                  object value of its 
                  vlanTrunkPortDynamicStatus as specified 
                  in CISCO-VTP-MIB is notTrunking(2).
        
        disable -- the fast start feature is disabled on this 
                  port.  
        
        enableForTrunk -- the fast start feature is enabled 
                  on this port and will take effect 
                  regardless of the object value of 
                  its vlanTrunkPortDynamicStatus.
        
        default -- whether the fast start feature is enabled
                   or not on this port depends on the object 
                   value of stpxFastStartGlobalDefaultMode.
        
        network -- the fast start network mode is enabled on 
                   this port."
    ::= { stpxFastStartPortEntry 3 }

stpxFastStartPortBpduGuardMode OBJECT-TYPE
    SYNTAX INTEGER {
        enable(1),
        disable(2),
        default(3)
        }
    ACCESS read-write
    STATUS mandatory
    DESCRIPTION
        "Indicates the mode of Bpdu Guard Feature on the
        port. A port with Bpdu Guard enabled is 
        immediately disabled when the system 
        receives a BPDU from that port. 
        
        enable -- the Bpdu Guard feature is enabled on this
                  port. 
        
        disable -- the Bpdu Guard feature is disabled on this
                  port.
        
        default -- whether the Bpdu Guard feature is enabled
                   or not on this port depends on the object
                   value of stpxFastStartBpduGuardEnable. If 
                   the value of stpxFastStartBpduGuardEnable
                   is true(1) and Fast Start feature is also 
                   enabled operationally on this port, then
                   this port is immediately disabled when 
                   the system receives a BPDU from this port."
    DEFVAL { default }
    ::= { stpxFastStartPortEntry 4 }

stpxFastStartPortBpduFilterMode OBJECT-TYPE
    SYNTAX INTEGER {
        enable(1),
        disable(2),
        default(3)
        }
    ACCESS read-write
    STATUS mandatory
    DESCRIPTION
        "Indicates the mode of Bpdu Filter Feature on the
        port. The system will not transmit BPDUs on a port 
        with Bpdu Filter feature enabled.
        
        enable -- the Bpdu Filter feature is enabled on this 
                  port. 
        
        disable -- the Bpdu Filter feature is disabled on this
                   port.
        
        default -- whether the Bpdu Filter feature is enabled
                   or not on this port depends on the object
                   value of stpxFastStartBpduFilterEnable. If
                   the value of stpxFastStartBpduFilterEnable
                   is true(1) and Fast Start feature is also
                   enabled operationally on this port, then
                   no BPDUs will be transmitted on this port."
    DEFVAL { default }
    ::= { stpxFastStartPortEntry 5 }

stpxFastStartGlobalDefaultMode OBJECT-TYPE
    SYNTAX INTEGER {
        enable(1),
        disable(2)
        }
    ACCESS read-write
    STATUS mandatory
    DESCRIPTION
        "Indicates the global default mode of the Fast 
        Start feature on the device."
    DEFVAL { disable }
    ::= { stpxFastStartObjects 4 }

stpxFastStartOperModeTable OBJECT-TYPE
    SYNTAX SEQUENCE OF StpxFastStartOperModeEntry
    ACCESS not-accessible
    STATUS mandatory
    DESCRIPTION
        "A table containing a list of the bridge ports 
        for a particular Spanning Tree Instance."
    ::= { stpxFastStartObjects 5 }

stpxFastStartOperModeEntry OBJECT-TYPE
    SYNTAX StpxFastStartOperModeEntry
    ACCESS not-accessible
    STATUS mandatory
    DESCRIPTION
        "An entry with port fast start oper mode 
        information on a bridge port for a particular 
        Spanning Tree Instance."
    INDEX { stpxFastStartOperModeInstIndex, stpxFastStartOperModePortIndex }
    ::= { stpxFastStartOperModeTable 1 }

StpxFastStartOperModeEntry ::= SEQUENCE {
    stpxFastStartOperModeInstIndex INTEGER,
    stpxFastStartOperModePortIndex INTEGER,
    stpxFastStartOperMode INTEGER
    }

stpxFastStartOperModeInstIndex OBJECT-TYPE
    SYNTAX INTEGER(0..65535)
    ACCESS not-accessible
    STATUS mandatory
    DESCRIPTION
        "The Spanning Tree instance id, such as the VLAN id 
        of the VLAN if the object value of stpxSpanningTreeType
        is pvstPlus(1)."
    ::= { stpxFastStartOperModeEntry 1 }

stpxFastStartOperModePortIndex OBJECT-TYPE
    SYNTAX INTEGER(1..65535)
    ACCESS not-accessible
    STATUS mandatory
    DESCRIPTION
        "The value of dot1dBasePort (i.e. dot1dBridge.1.4)
        for the bridge port."
    REFERENCE
        "dot1dBasePort is defined in RFC1493."
    ::= { stpxFastStartOperModeEntry 2 }

stpxFastStartOperMode OBJECT-TYPE
    SYNTAX INTEGER {
        enabled(1),
        disabled(2)
        }
    ACCESS read-only
    STATUS mandatory
    DESCRIPTION
        "Indicates the fast start operational status of the 
        port on a particular Spanning Tree Instance."
    ::= { stpxFastStartOperModeEntry 3 }

stpxBpduSkewingDetectionEnable OBJECT-TYPE
    SYNTAX TruthValue
--    Rsyntax INTEGER {
--        true(1),
--        false(2)
--        }
    ACCESS read-write
    STATUS mandatory
    DESCRIPTION
        "Indicates whether BPDU skewing detection feature
        is enabled or not on the system. If this object has
        the value of true(1), then the system will detect
        whether BPDUs received by any port on any Spanning 
        Tree instance are processed at an interval longer
        than the object value of dot1dStpHelloTime in the
        BIRDGE-MIB of the Spanning Tree instance."
    DEFVAL { false }
    ::= { stpxBpduSkewingObjects 1 }

stpxBpduSkewingTable OBJECT-TYPE
    SYNTAX SEQUENCE OF StpxBpduSkewingEntry
    ACCESS not-accessible
    STATUS mandatory
    DESCRIPTION
        "A table containing a list of the bridge ports for 
        which a particular Spanning Tree instance has been 
        detected to have BPDU skewing occurred since the 
        object value of stpxBpduSkewingDetectionEnable was
        last changed to true(1).
        
        The agent creates a new entry in this table whenever
        a port in a particular Spanning Tree instance is 
        detected to be BPDU skewed since the object value of 
        stpxBpduSkewingDetectionEnable object is changed to 
        true(1). The agent deletes all the entries in this 
        table when the object value of 
        stpxBpduSkewingDetectionEnable is changed to false(2)
        or the object value of stpxSpanningTreeType is 
        changed."
    ::= { stpxBpduSkewingObjects 2 }

stpxBpduSkewingEntry OBJECT-TYPE
    SYNTAX StpxBpduSkewingEntry
    ACCESS not-accessible
    STATUS mandatory
    DESCRIPTION
        "A Spanning Tree instance on a particular port for
        which BPDU skewing has been detected."
    INDEX { stpxBpduSkewingInstanceIndex, stpxBpduSkewingPortIndex }
    ::= { stpxBpduSkewingTable 1 }

StpxBpduSkewingEntry ::= SEQUENCE {
    stpxBpduSkewingInstanceIndex INTEGER,
    stpxBpduSkewingPortIndex INTEGER,
    stpxBpduSkewingLastSkewDuration Gauge,
    stpxBpduSkewingWorstSkewDuration Gauge,
    stpxBpduSkewingWorstSkewTime TimeStamp
    }

stpxBpduSkewingInstanceIndex OBJECT-TYPE
    SYNTAX INTEGER(0..65535)
    ACCESS not-accessible
    STATUS mandatory
    DESCRIPTION
        "The Spanning Tree instance id, such as the VLAN id 
        of the VLAN if the object value of stpxSpanningTreeType 
        is pvstPlus(1)."
    ::= { stpxBpduSkewingEntry 1 }

stpxBpduSkewingPortIndex OBJECT-TYPE
    SYNTAX INTEGER(1..65535)
    ACCESS not-accessible
    STATUS mandatory
    DESCRIPTION
        "The value of dot1dBasePort (i.e. dot1dBridge.1.4)
         for the bridge port."
    REFERENCE
        "dot1dBasePort is defined in RFC1493."
    ::= { stpxBpduSkewingEntry 2 }

stpxBpduSkewingLastSkewDuration OBJECT-TYPE
    SYNTAX Gauge
--  Units
--    milliseconds
    ACCESS read-only
    STATUS mandatory
    DESCRIPTION
        "Indicates the skew duration in milliseconds of the
        last BPDU skewing detected."
    ::= { stpxBpduSkewingEntry 3 }

stpxBpduSkewingWorstSkewDuration OBJECT-TYPE
    SYNTAX Gauge
--  Units
--    milliseconds
    ACCESS read-only
    STATUS mandatory
    DESCRIPTION
        "Indicates the skew duration in milliseconds of the
        worst BPDU skewing detected."
    ::= { stpxBpduSkewingEntry 4 }

stpxBpduSkewingWorstSkewTime OBJECT-TYPE
    SYNTAX TimeStamp
--    Rsyntax TimeTicks
    ACCESS read-only
    STATUS mandatory
    DESCRIPTION
        "Indicates the value of sysUpTime when the worst
        BPDU skewing was detected."
    ::= { stpxBpduSkewingEntry 5 }

stpxMSTMaxInstanceNumber OBJECT-TYPE
    SYNTAX INTEGER(1..256)
    ACCESS read-only
    STATUS deprecated
    DESCRIPTION
        "The maximum MST (Multiple Spanning Tree) instance id, 
        that can be supported by the device for Cisco proprietary
        implementation of the MST Protocol.
        
        This object is deprecated and replaced by 
        stpxSMSTMaxInstanceID."
    ::= { stpxMSTObjects 1 }

stpxMSTRegionName OBJECT-TYPE
    SYNTAX DisplayString(SIZE(0..32))
--    Rsyntax OCTET STRING(SIZE(0..32))
    ACCESS read-only
    STATUS mandatory
    DESCRIPTION
        "The operational MST region name."
    ::= { stpxMSTObjects 2 }

stpxMSTRegionRevision OBJECT-TYPE
    SYNTAX INTEGER(1..65535)
    ACCESS read-only
    STATUS deprecated
    DESCRIPTION
        "The operational MST region version.
        
        This object is deprecated and replaced by 
        stpxSMSTRegionRevision."
    ::= { stpxMSTObjects 3 }

stpxMSTInstanceTable OBJECT-TYPE
    SYNTAX SEQUENCE OF StpxMSTInstanceEntry
    ACCESS not-accessible
    STATUS deprecated
    DESCRIPTION
        "This table contains MST instance information with
        one entry for an MST instance within the range of 
        0 to the object value of stpxMSTMaxInstanceNumber. 
        
        This table is deprecated and replaced by 
        stpxSMSTInstanceTable."
    ::= { stpxMSTObjects 4 }

stpxMSTInstanceEntry OBJECT-TYPE
    SYNTAX StpxMSTInstanceEntry
    ACCESS not-accessible
    STATUS deprecated
    DESCRIPTION
        "A conceptual row containing the MST instance 
        information."
    INDEX { stpxMSTInstanceIndex }
    ::= { stpxMSTInstanceTable 1 }

StpxMSTInstanceEntry ::= SEQUENCE {
    stpxMSTInstanceIndex INTEGER,
    stpxMSTInstanceVlansMapped OCTET STRING,
    stpxMSTInstanceVlansMapped2k OCTET STRING,
    stpxMSTInstanceVlansMapped3k OCTET STRING,
    stpxMSTInstanceVlansMapped4k OCTET STRING,
    stpxMSTInstanceRemainingHopCount INTEGER
    }

stpxMSTInstanceIndex OBJECT-TYPE
    SYNTAX INTEGER(0..256)
    ACCESS not-accessible
    STATUS deprecated
    DESCRIPTION
        "An integer that uniquely identifies an MST instance 
        within the range of 0 to the object value of
        stpxMSTMaxInstanceNumber.
        
        This object is deprecated and replaced by 
        stpxSMSTInstanceIndex."
    ::= { stpxMSTInstanceEntry 1 }

stpxMSTInstanceVlansMapped OBJECT-TYPE
    SYNTAX OCTET STRING(SIZE(0..128))
    ACCESS read-only
    STATUS deprecated
    DESCRIPTION
        "A string of octets containing one bit per VLAN. The
        first octet corresponds to VLANs with VlanIndex values
        of 0 through 7; the second octet to VLANs 8 through
        15; etc.  The most significant bit of each octet
        corresponds to the lowest value VlanIndex in that octet.
        
        For each VLAN, if it is mapped to this MST instance, 
        then the bit corresponding to that VLAN is set to '1'.
        
        This object is deprecated and replaced by 
        stpxSMSTInstanceVlansMapped1k2k."
    ::= { stpxMSTInstanceEntry 2 }

stpxMSTInstanceVlansMapped2k OBJECT-TYPE
    SYNTAX OCTET STRING(SIZE(0..128))
    ACCESS read-only
    STATUS deprecated
    DESCRIPTION
        "A string of octets containing one bit per VLAN for
         VLANS with VlanIndex values of 1024 through 2047. The
         first octet corresponds to VLANs with VlanIndex values
         of 1024 through 1031; the second octet to VLANs 1032
         through 1039; etc.  The most significant bit of each
         octet corresponds to the lowest value VlanIndex in that
         octet.
        
         For each VLAN, if it is mapped to this MST instance, 
         then the bit corresponding to that VLAN is set to '1'.
        
         This object is deprecated and replaced by 
        stpxSMSTInstanceVlansMapped1k2k."
    ::= { stpxMSTInstanceEntry 3 }

stpxMSTInstanceVlansMapped3k OBJECT-TYPE
    SYNTAX OCTET STRING(SIZE(0..128))
    ACCESS read-only
    STATUS deprecated
    DESCRIPTION
        "A string of octets containing one bit per VLAN for
        VLANS with VlanIndex values of 2048 through 3071. The
        first octet corresponds to VLANs with VlanIndex values
        of 2048 through 2055; the second octet to VLANs 2056
        through 2063; etc.  The most significant bit of each
        octet corresponds to the lowest value VlanIndex in that
        octet.
        
        For each VLAN, if it is mapped to this MST instance, 
        then the bit corresponding to that VLAN is set to '1'.
        
        This object is deprecated and replaced by 
        stpxSMSTInstanceVlansMapped3k4k."
    ::= { stpxMSTInstanceEntry 4 }

stpxMSTInstanceVlansMapped4k OBJECT-TYPE
    SYNTAX OCTET STRING(SIZE(0..128))
    ACCESS read-only
    STATUS deprecated
    DESCRIPTION
        "A string of octets containing one bit per VLAN for
        VLANS with VlanIndex values of 3072 through 4095. The
        first octet corresponds to VLANs with VlanIndex values
        of 3072 through 3079; the second octet to VLANs 3080
        through 3087; etc.  The most significant bit of each
        octet corresponds to the lowest value VlanIndex in that
        octet.
        
        For each VLAN, if it is mapped to this MST instance, 
        then the bit corresponding to that VLAN is set to '1'.
        
        This object is deprecated and replaced by
        stpxSMSTInstanceVlansMapped3k4k."
    ::= { stpxMSTInstanceEntry 5 }

stpxMSTInstanceRemainingHopCount OBJECT-TYPE
    SYNTAX INTEGER(0..40)
    ACCESS read-only
    STATUS deprecated
    DESCRIPTION
        "The remaining hop count for this MST instance.
        
        This object will take on value of 40 if the object value
        of stpxSMSTInstanceRemainingHopCount is greater than 40.
        
        This object is only instantiated when the object value of
        stpxSpanningTreeType is mst(4).
        
        This object is deprecated and replaced by 
        stpxSMSTInstanceRemainingHopCount."
    ::= { stpxMSTInstanceEntry 6 }

stpxMSTRegionEditBufferStatus OBJECT-TYPE
    SYNTAX INTEGER {
        released(1),
        acquiredBySnmp(2),
        acquiredByNonSnmp(3)
        }
    ACCESS read-only
    STATUS mandatory
    DESCRIPTION
        "Indicates the current ownership status of the unique 
         Region Config Edit Buffer. 
        
         released -- the Edit Buffer can be acquired by any of 
                     the SNMP management stations. 
        
         acquiredBySnmp -- the Edit Buffer is acquired by
                     any of the SNMP management stations. 
        
         acquiredByNonSnmp -- the Edit Buffer is acquired by the 
                     non-SNMP users managing the device."
    ::= { stpxMSTObjects 5 }

stpxMSTRegionEditBufferOperation OBJECT-TYPE
    SYNTAX INTEGER {
        other(1),
        acquire(2),
        releaseWithForce(3),
        commit(4),
        rollBack(5)
        }
    ACCESS read-write
    STATUS mandatory
    DESCRIPTION
        "Indicates the operation that is performed on the Region 
        Config Edit Buffer.
        
        other --   none of the following operations.  
        
        acquire -- acquire the Edit Buffer. This operation can 
                   only be performed when the object 
                   stpxMSTRegionEditBufferStatus has the value of
                   released(1). After the successful operation of 
                   this action, the stpxMSTRegionEditBufferStatus
                   will be changed to acquiredBySnmp(2). 
                    
        releaseWithForce -- release the Edit Buffer acquired by
                   non-SNMP users with force and discard the changes
                   in the Edit Buffer. This operation can only be 
                   performed when the object 
                   stpxMSTRegionEditBufferStatus has the value of 
                   acquiredByNonSnmp(2).
        
        commit --  commit the changes in the Edit Buffer
                   and release the Edit Buffer. The successful 
                   operation of this action will make the changes
                   in the Edit Buffer effective on the device.
                   This operation can only be performed when the 
                   object stpxMSTRegionEditBufferStatus has the 
                   value of acquiredBySnmp(3).
         
        rollBack -- discard the changes in the Edit Buffer
                   and release the Edit Buffer. This operation can 
                   only be performed when the object 
                   stpxMSTRegionEditBufferStatus has the value 
                   of acquiredBySnmp(3).
        
        This object always returns other(1) when it is read."
    ::= { stpxMSTObjects 6 }

stpxMSTRegionEditName OBJECT-TYPE
    SYNTAX DisplayString(SIZE(0..32))
--    Rsyntax OCTET STRING(SIZE(0..32))
    ACCESS read-write
    STATUS mandatory
    DESCRIPTION
        "The MST region name in the Edit Buffer. 
        
        This object is only instantiated when the 
        stpxMSTRegionEditBufferStatus has the value of 
        acquiredBySnmp(2)."
    ::= { stpxMSTObjects 7 }

stpxMSTRegionEditRevision OBJECT-TYPE
    SYNTAX INTEGER(1..65535)
    ACCESS read-write
    STATUS deprecated
    DESCRIPTION
        "The MST region version in the Edit Buffer. This object is
        only instantiated when the stpxMSTRegionEditBufferStatus 
        has the value of acquiredBySnmp(2).
        
        This object is deprecated and replaced by
        stpxSMSTRegionEditRevision."
    ::= { stpxMSTObjects 8 }

stpxMSTInstanceEditTable OBJECT-TYPE
    SYNTAX SEQUENCE OF StpxMSTInstanceEditEntry
    ACCESS not-accessible
    STATUS deprecated
    DESCRIPTION
        "This table contains MST instance information in the 
        Edit Buffer with one entry for each MST
        instance numbered from 0 to stpxMSTMaxInstanceNumber. 
        
        This table is only instantiated when the 
        stpxMSTRegionEditBufferStatus has the value of
        acquiredBySnmp(2).
        
        This table is deprecated and replaced by 
        stpxSMSTInstanceEditTable."
    ::= { stpxMSTObjects 9 }

stpxMSTInstanceEditEntry OBJECT-TYPE
    SYNTAX StpxMSTInstanceEditEntry
    ACCESS not-accessible
    STATUS deprecated
    DESCRIPTION
        "A conceptual row containing MST instance information 
        in the Edit Buffer."
    INDEX { stpxMSTInstanceEditIndex }
    ::= { stpxMSTInstanceEditTable 1 }

StpxMSTInstanceEditEntry ::= SEQUENCE {
    stpxMSTInstanceEditIndex INTEGER,
    stpxMSTInstanceEditVlansMap OCTET STRING,
    stpxMSTInstanceEditVlansMap2k OCTET STRING,
    stpxMSTInstanceEditVlansMap3k OCTET STRING,
    stpxMSTInstanceEditVlansMap4k OCTET STRING
    }

stpxMSTInstanceEditIndex OBJECT-TYPE
    SYNTAX INTEGER(0..256)
    ACCESS not-accessible
    STATUS deprecated
    DESCRIPTION
        "An integer that uniquely identifies an MST instance 
        from 0 to the object value of stpxMSTMaxInstanceNumber.
        
        The instances of this table entry with 
        stpxMSTInstanceEditIndex of zero can not be 
        modified.
        
        This object is deprecated and replaced by 
        stpxSMSTInstanceEditIndex."
    ::= { stpxMSTInstanceEditEntry 1 }

stpxMSTInstanceEditVlansMap OBJECT-TYPE
    SYNTAX OCTET STRING(SIZE(0..128))
    ACCESS read-write
    STATUS deprecated
    DESCRIPTION
        "A string of octets containing one bit per VLAN. The
        first octet corresponds to VLANs with VlanIndex values
        of 0 through 7; the second octet to VLANs 8 through
        15; etc.  The most significant bit of each octet
        corresponds to the lowest value VlanIndex in that octet.
        
        For each VLAN, if it is mapped to this MST instance, 
        then the bit corresponding to that VLAN is set to 
        '1'. Each VLAN can only be mapped to one unique MST 
        instance in the range from 1 to stpxMSTMaxInstanceNumber.
        If the bit corresponding to a VLAN is changed from '1' 
        to '0', then that VLAN will be automatically mapped to 
        MST instance 0 by the device.
        
        This object is deprecated and replaced by 
        stpxSMSTInstanceEditVlansMap1k2k."
    ::= { stpxMSTInstanceEditEntry 2 }

stpxMSTInstanceEditVlansMap2k OBJECT-TYPE
    SYNTAX OCTET STRING(SIZE(0..128))
    ACCESS read-write
    STATUS deprecated
    DESCRIPTION
        "A string of octets containing one bit per VLAN for
        VLANS with VlanIndex values of 1024 through 2047. The
        first octet corresponds to VLANs with VlanIndex values
        of 1024 through 1031; the second octet to VLANs 1032
        through 1039; etc.  The most significant bit of each
        octet corresponds to the lowest value VlanIndex in that
        octet.
        
        For each VLAN, if it is mapped to this MST instance,
        then the bit corresponding to that VLAN is set to
        '1'. Each VLAN can only be mapped to one unique MST
        instance in the range from 1 to stpxMSTMaxInstanceNumber.
        If the bit corresponding to a VLAN is changed from '1' 
        to '0', then that VLAN will be automatically mapped to 
        MST instance 0 by the device.
        
        This object is deprecated and replaced by 
        stpxSMSTInstanceEditVlansMap1k2k."
    ::= { stpxMSTInstanceEditEntry 3 }

stpxMSTInstanceEditVlansMap3k OBJECT-TYPE
    SYNTAX OCTET STRING(SIZE(0..128))
    ACCESS read-write
    STATUS deprecated
    DESCRIPTION
        "A string of octets containing one bit per VLAN for
         VLANS with VlanIndex values of 2048 through 3071. The
         first octet corresponds to VLANs with VlanIndex values
         of 2048 through 2055; the second octet to VLANs 2056
         through 2063; etc.  The most significant bit of each
         octet corresponds to the lowest value VlanIndex in that
         octet.
        
         For each VLAN, if it is mapped to this MST instance,
         then the bit corresponding to that VLAN is set to
         '1'. Each VLAN can only be mapped to one unique MST
         instance in the range from 1 to stpxMSTMaxInstanceNumber.
         If the bit corresponding to a VLAN is changed from '1' 
         to '0', then that VLAN will be automatically mapped to 
         MST instance 0 by the device.
        
         This object is deprecated and replaced by 
         stpxSMSTInstanceEditVlansMap3k4k."
    ::= { stpxMSTInstanceEditEntry 4 }

stpxMSTInstanceEditVlansMap4k OBJECT-TYPE
    SYNTAX OCTET STRING(SIZE(0..128))
    ACCESS read-write
    STATUS deprecated
    DESCRIPTION
        "A string of octets containing one bit per VLAN for
        VLANS with VlanIndex values of 3072 through 4095. The
        first octet corresponds to VLANs with VlanIndex values
        of 3072 through 3079; the second octet to VLANs 3080
        through 3087; etc.  The most significant bit of each
        octet corresponds to the lowest value VlanIndex in that
        octet.
        
        For each VLAN, if it is mapped to this MST instance,
        then the bit corresponding to that VLAN is set to
        '1'. Each VLAN can only be mapped to one unique MST
        instance in the range from 1 to stpxMSTMaxInstanceNumber.
        If the bit corresponding to a VLAN is changed from '1' 
        to '0', then that VLAN will be automatically mapped to 
        MST instance 0 by the device.
        
        This object is deprecated and replaced by
        stpxSMSTInstanceEditVlansMap3k4k."
    ::= { stpxMSTInstanceEditEntry 5 }

stpxPreferredMSTInstancesTable OBJECT-TYPE
    SYNTAX SEQUENCE OF StpxPreferredMSTInstancesEntry
    ACCESS not-accessible
    STATUS deprecated
    DESCRIPTION
        "The table containing indications of which MST instances 
        are preferred on which  trunk ports.  The preferred
        MST instances on a trunk port have a lower Path Cost value
        compared with the MST instances on the trunk not in the
        preferred list."
    ::= { stpxMSTObjects 10 }

stpxPreferredMSTInstancesEntry OBJECT-TYPE
    SYNTAX StpxPreferredMSTInstancesEntry
    ACCESS not-accessible
    STATUS deprecated
    DESCRIPTION
        "An entry indicating which MST instances are preferred on 
        a specific trunk port."
    INDEX { vlanTrunkPortIfIndex }
-- Augments vlanTrunkPortEntry FROM CISCO-VTP-MIB
    ::= { stpxPreferredMSTInstancesTable 1 }

StpxPreferredMSTInstancesEntry ::= SEQUENCE {
    stpxPreferredMSTInstancesMap OCTET STRING
    }

stpxPreferredMSTInstancesMap OBJECT-TYPE
    SYNTAX OCTET STRING(SIZE(1..32))
    ACCESS read-write
    STATUS deprecated
    DESCRIPTION
        "A string of octets containing one bit per MST instances 
        on this trunk port.  The first octet corresponds to MST 
        instances of 0 through 7; the second octet to MST instances 
        8 through 15; etc. The most significant bit of each octet 
        corresponds to the lowest MST instance value in that octet. 
        The number of bits for this mib object will be determined 
        by the value of stpxMSTMaxInstanceNumber.
        
        For each instance, if it is preferred on this trunk port, 
        then the bit corresponding to that instance is set to '1'."
    ::= { stpxPreferredMSTInstancesEntry 1 }

stpxMSTPortTable OBJECT-TYPE
    SYNTAX SEQUENCE OF StpxMSTPortEntry
    ACCESS not-accessible
    STATUS deprecated
    DESCRIPTION
        "A table containing port information for the MST 
         Protocol on all the bridge ports existing on the 
         system."
    ::= { stpxMSTObjects 11 }

stpxMSTPortEntry OBJECT-TYPE
    SYNTAX StpxMSTPortEntry
    ACCESS not-accessible
    STATUS deprecated
    DESCRIPTION
        "An entry with port information for the MST Protocol
        on a bridge port."
    INDEX { stpxMSTPortIndex }
    ::= { stpxMSTPortTable 1 }

StpxMSTPortEntry ::= SEQUENCE {
    stpxMSTPortIndex INTEGER,
    stpxMSTPortAdminLinkType INTEGER,
    stpxMSTPortOperLinkType INTEGER,
    stpxMSTPortProtocolMigration TruthValue,
    stpxMSTPortStatus OCTET STRING
    }

stpxMSTPortIndex OBJECT-TYPE
    SYNTAX INTEGER(1..65535)
    ACCESS not-accessible
    STATUS deprecated
    DESCRIPTION
        "The value of dot1dBasePort (i.e. dot1dBridge.1.4)
         for the bridge port."
    REFERENCE
        "dot1dBasePort is defined in RFC1493."
    ::= { stpxMSTPortEntry 1 }

stpxMSTPortAdminLinkType OBJECT-TYPE
    SYNTAX INTEGER {
        pointToPoint(1),
        shared(2),
        auto(3)
        }
    ACCESS read-write
    STATUS deprecated
    DESCRIPTION
        "Indicates the administrative link type configuration of 
        a bridge port for the MST protocol. 
        
        pointToPoint -- the port is administratively configured to
                be connected to a point-to-point link.
        
        shared -- the port is administratively configured to be
                connected to a shared medium. 
        
        auto -- the administrative configuration of the port's 
                link type depends on link duplex of the port.
                If the port link is full-duplex, the administrative 
                link type configuration on this port will be taken 
                as pointTopoint(1). If the port link is half-duplex, 
                the administrative link type configuration on this
                port will be taken as shared(2).
        
        This configuration of this object only takes effect when the
        stpxSpanningTreeType is mst(4) or rapidPvstPlus(5).
        stpxMSTPortAdminLinkType is deprecated and replaced 
        with stpxRSTPPortAdminLinkType."
    DEFVAL { auto }
    ::= { stpxMSTPortEntry 2 }

stpxMSTPortOperLinkType OBJECT-TYPE
    SYNTAX INTEGER {
        pointToPoint(1),
        shared(2),
        other(3)
        }
    ACCESS read-only
    STATUS deprecated
    DESCRIPTION
        "Indicates the operational link type of a bridge port
        for the MST protocol.
        
        pointToPoint -- the port is operationally connected to
                a point-to-point link.
        
        shared -- the port is operationally connected to 
                a shared medium.
        
        other -- none of the above.
        
        This object is only instantiated when the object value of
        stpxSpanningTreeType is mst(4).  stpxMSTPortOperLinkType 
        is deprecated and replaced with stpxRSTPPortOperLinkType."
    ::= { stpxMSTPortEntry 3 }

stpxMSTPortProtocolMigration OBJECT-TYPE
    SYNTAX TruthValue
--    Rsyntax INTEGER {
--        true(1),
--        false(2)
--        }
    ACCESS read-write
    STATUS deprecated
    DESCRIPTION
        "The protocol migration control on this port. When the 
        object value of  stpxSpanningTreeType is mst(4) or 
        rapidPvstPlus(5), setting true(1) to this object forces 
        the device to try using version 2 BPDUs on this port. 
        When the object value of stpxSpanningTreeType is neither 
        mst(4) nor rapidPvstPlus(5), setting true(1) to this 
        object has no effect. Setting false(2) to this object has 
        no effect. This object always returns false(2) when read.
        stpxMSTPortProtocolMigration is deprecated and 
        replaced with stpxRSTPPortProtocolMigration."
    REFERENCE
        "IEEE 802.1w clause 14.8.2.4, 17.26."
    ::= { stpxMSTPortEntry 4 }

stpxMSTPortStatus OBJECT-TYPE
    SYNTAX OCTET STRING(SIZE(1..2))
        -- BITS are:
        --   edge(0)
        --   boundary(1)
        --   pvst(2)
        --   stp(3)
    ACCESS read-only
    STATUS deprecated
    DESCRIPTION
        "Indicates the operational status of the port for the 
        MST protocol. 
        
        edge -- this port is an edge port for the MST region.
        
        boundary -- this port is a boundary port for the 
                MST region.
        
        pvst --  this port is connected to a PVST/PVST+ bridge.   
        
        stp -- this port is connected to a Single Spanning
                Tree bridge. 
        
        This object is only instantiated when the object value
        of stpxSpanningTreeType is mst(4).
        
        This object is deprecated and replaced by 
        stpxSMSTPortStatus."
    ::= { stpxMSTPortEntry 5 }

stpxMSTPortRoleTable OBJECT-TYPE
    SYNTAX SEQUENCE OF StpxMSTPortRoleEntry
    ACCESS not-accessible
    STATUS deprecated
    DESCRIPTION
        "A table containing a list of the bridge ports for a 
        particular MST instance.  This table is only instantiated 
        when the stpxSpanningTreeType is mst(4). 
        
        This table is deprecated and replaced with 
        stpxRSTPPortRoleTable."
    ::= { stpxMSTObjects 12 }

stpxMSTPortRoleEntry OBJECT-TYPE
    SYNTAX StpxMSTPortRoleEntry
    ACCESS not-accessible
    STATUS deprecated
    DESCRIPTION
        "An entry containing the port role information for the MST
        protocol on a port for a particular MST instance existing
        on the system."
    INDEX { stpxMSTPortRoleInstanceIndex, stpxMSTPortRolePortIndex }
    ::= { stpxMSTPortRoleTable 1 }

StpxMSTPortRoleEntry ::= SEQUENCE {
    stpxMSTPortRoleInstanceIndex INTEGER,
    stpxMSTPortRolePortIndex INTEGER,
    stpxMSTPortRoleValue INTEGER
    }

stpxMSTPortRoleInstanceIndex OBJECT-TYPE
    SYNTAX INTEGER(0..256)
    ACCESS not-accessible
    STATUS deprecated
    DESCRIPTION
        "The MST instance id within the range of 0 to
        stpxMSTMaxInstanceNumber."
    ::= { stpxMSTPortRoleEntry 1 }

stpxMSTPortRolePortIndex OBJECT-TYPE
    SYNTAX INTEGER(1..65535)
    ACCESS not-accessible
    STATUS deprecated
    DESCRIPTION
        "The value of dot1dBasePort (i.e. dot1dBridge.1.4)
        for the bridge port."
    REFERENCE
        "dot1dBasePort is defined in RFC1493."
    ::= { stpxMSTPortRoleEntry 2 }

stpxMSTPortRoleValue OBJECT-TYPE
    SYNTAX INTEGER {
        disabled(1),
        root(2),
        designated(3),
        alternate(4),
        backUp(5),
        boundary(6),
        master(7)
        }
    ACCESS read-only
    STATUS deprecated
    DESCRIPTION
        "Indicates the port role on a particular MST instance
        for the MST protocol. 
        
        disabled --  this port has no role on this MST instance. 
        
        root -- this port has the role of root port on this MST
                    instance. 
        
        designated -- this port has the role of designated 
                    port on this MST instance.
        
        alternate -- this port has the role of alternate port
                    on this MST instance.
        
        backUp -- this port has the role of backup port on this  
                    MST instance.
        
        boundary -- this port has the role of boundary port on 
                    this MST instance.
        
        master -- this port has the role of master port on
                  this MST instance."
    ::= { stpxMSTPortRoleEntry 3 }

stpxMSTMaxHopCount OBJECT-TYPE
    SYNTAX INTEGER(1..40)
    ACCESS read-write
    STATUS deprecated
    DESCRIPTION
        "The maximum number of hops for the MST region. 
        
        This object will take on value of 40 if the object value
        of stpxSMSTMaxHopCount is greater than 40.
        
        This object is deprecated and replaced by
        stpxSMSTMaxHopCount."
    DEFVAL { 20 }
    ::= { stpxMSTObjects 13 }

stpxRSTPPortTable OBJECT-TYPE
    SYNTAX SEQUENCE OF StpxRSTPPortEntry
    ACCESS not-accessible
    STATUS mandatory
    DESCRIPTION
        "A table containing port information for the RSTP 
         Protocol on all the bridge ports existing in the 
         system."
    ::= { stpxRSTPObjects 1 }

stpxRSTPPortEntry OBJECT-TYPE
    SYNTAX StpxRSTPPortEntry
    ACCESS not-accessible
    STATUS mandatory
    DESCRIPTION
        "An entry with port information for the RSTP Protocol
        on a bridge port."
    INDEX { stpxRSTPPortIndex }
    ::= { stpxRSTPPortTable 1 }

StpxRSTPPortEntry ::= SEQUENCE {
    stpxRSTPPortIndex INTEGER,
    stpxRSTPPortAdminLinkType INTEGER,
    stpxRSTPPortOperLinkType INTEGER,
    stpxRSTPPortProtocolMigration TruthValue
    }

stpxRSTPPortIndex OBJECT-TYPE
    SYNTAX INTEGER(1..65535)
    ACCESS not-accessible
    STATUS mandatory
    DESCRIPTION
        "The value of dot1dBasePort (i.e. dot1dBridge.1.4)
         for the bridge port."
    REFERENCE
        "dot1dBasePort is defined in RFC1493."
    ::= { stpxRSTPPortEntry 1 }

stpxRSTPPortAdminLinkType OBJECT-TYPE
    SYNTAX INTEGER {
        pointToPoint(1),
        shared(2),
        auto(3)
        }
    ACCESS read-write
    STATUS mandatory
    DESCRIPTION
        "Indicates the administrative link type configuration of 
        a bridge port for the RSTP protocol. 
        
        pointToPoint -- the port is administratively configured to
                be connected to a point-to-point link.
        
        shared -- the port is administratively configured to be
                connected to a shared medium. 
        
        auto -- the administrative configuration of the port's 
                link type depends on link duplex of the port.
                If the port link is full-duplex, the administrative 
                link type configuration on this port will be taken 
                as pointTopoint(1). If the port link is half-duplex, 
                the administrative link type configuration on this
                port will be taken as shared(2).
        
        This configuration of this object only takes effect when the
        stpxSpanningTreeType is mst(4) or rapidPvstPlus(5)."
    DEFVAL { auto }
    ::= { stpxRSTPPortEntry 2 }

stpxRSTPPortOperLinkType OBJECT-TYPE
    SYNTAX INTEGER {
        pointToPoint(1),
        shared(2),
        other(3)
        }
    ACCESS read-only
    STATUS mandatory
    DESCRIPTION
        "Indicates the operational link type of a bridge port
        for the RSTP protocol.
        
        pointToPoint -- the port is operationally connected to
                a point-to-point link.
        
        shared -- the port is operationally connected to 
                a shared medium.
        
        other -- none of the above.
        
        This object is only instantiated when the object value of
        stpxSpanningTreeType is mst(4) or rapidPvstPlus(5)."
    ::= { stpxRSTPPortEntry 3 }

stpxRSTPPortProtocolMigration OBJECT-TYPE
    SYNTAX TruthValue
--    Rsyntax INTEGER {
--        true(1),
--        false(2)
--        }
    ACCESS read-write
    STATUS mandatory
    DESCRIPTION
        "The protocol migration control on this port. When the 
        object value of  stpxSpanningTreeType is mst(4) or 
        rapidPvstPlus(5), setting true(1) to this object forces 
        the device to try using version 2 BPDUs on this port. 
        When the object value of stpxSpanningTreeType is neither 
        mst(4) nor rapidPvstPlus(5), setting true(1) to 
        this object has no effect. Setting false(2) to this 
        object has no effect. This object always returns 
        false(2) when read."
    REFERENCE
        "IEEE 802.1w clause 14.8.2.4, 17.26."
    ::= { stpxRSTPPortEntry 4 }

stpxRSTPPortRoleTable OBJECT-TYPE
    SYNTAX SEQUENCE OF StpxRSTPPortRoleEntry
    ACCESS not-accessible
    STATUS mandatory
    DESCRIPTION
        "A table containing a list of the bridge ports for a 
        particular Spanning Tree instance.  This table is 
        only instantiated when the stpxSpanningTreeType is mst(4) 
        or rapidPvstPlus(5)."
    ::= { stpxRSTPObjects 2 }

stpxRSTPPortRoleEntry OBJECT-TYPE
    SYNTAX StpxRSTPPortRoleEntry
    ACCESS not-accessible
    STATUS mandatory
    DESCRIPTION
        "An entry containing the port role information for the RSTP
        protocol on a port for a particular Spanning Tree instance."
    INDEX { stpxRSTPPortRoleInstanceIndex, stpxRSTPPortRolePortIndex }
    ::= { stpxRSTPPortRoleTable 1 }

StpxRSTPPortRoleEntry ::= SEQUENCE {
    stpxRSTPPortRoleInstanceIndex INTEGER,
    stpxRSTPPortRolePortIndex INTEGER,
    stpxRSTPPortRoleValue INTEGER
    }

stpxRSTPPortRoleInstanceIndex OBJECT-TYPE
    SYNTAX INTEGER(0..4095)
    ACCESS not-accessible
    STATUS mandatory
    DESCRIPTION
        "The Spanning Tree instance id, it can either be a 
        VLAN number if the stpxSpanningTreeType is rapidPvstPlus(5) 
        or an MST instance id if the stpxSpanningTreeType is mst(4)."
    ::= { stpxRSTPPortRoleEntry 1 }

stpxRSTPPortRolePortIndex OBJECT-TYPE
    SYNTAX INTEGER(1..65535)
    ACCESS not-accessible
    STATUS mandatory
    DESCRIPTION
        "The value of dot1dBasePort (i.e. dot1dBridge.1.4)
        for the bridge port."
    REFERENCE
        "dot1dBasePort is defined in RFC1493."
    ::= { stpxRSTPPortRoleEntry 2 }

stpxRSTPPortRoleValue OBJECT-TYPE
    SYNTAX INTEGER {
        disabled(1),
        root(2),
        designated(3),
        alternate(4),
        backUp(5),
        boundary(6),
        master(7)
        }
    ACCESS read-only
    STATUS mandatory
    DESCRIPTION
        "Indicates the port role on a particular Spanning Tree 
        instance for the RSTP protocol. 
        
        disabled --  this port has no role in this Spanning
                    Tree instance. 
        
        root -- this port has the role of root port in this
                    Spanning Tree instance. 
        
        designated -- this port has the role of designated 
                    port in this Spanning Tree instance.
        
        alternate -- this port has the role of alternate port
                    in this Spanning Tree instance.
        
        backUp -- this port has the role of backup port in this  
                    Spanning Tree instance.
        
        boundary -- this port has the role of boundary port in 
                    this Spanning Tree instance.
        
        master -- this port has the role of master port in
                    this Spanning Tree instance.
        
        This object could have a value of 'boundary' or 'master'
        only when the object value of stpxSpanningTreeType is mst(4)."
    ::= { stpxRSTPPortRoleEntry 3 }

stpxRSTPTransmitHoldCount OBJECT-TYPE
    SYNTAX Gauge
    ACCESS read-write
    STATUS mandatory
    DESCRIPTION
        "The Transmit Hold Count."
    ::= { stpxRSTPObjects 3 }

stpxRPVSTPortTable OBJECT-TYPE
    SYNTAX SEQUENCE OF StpxRPVSTPortEntry
    ACCESS not-accessible
    STATUS mandatory
    DESCRIPTION
        "A table containing a list of the bridge ports 
         for a particular Spanning Tree Instance.
         This table is only instantiated when the object value
         of stpxSpanningTreeType is rapidPvstPlus(5)."
    ::= { stpxRPVSTObjects 1 }

stpxRPVSTPortEntry OBJECT-TYPE
    SYNTAX StpxRPVSTPortEntry
    ACCESS not-accessible
    STATUS mandatory
    DESCRIPTION
        "An entry with port status information on a 
         bridge port for a particular Spanning Tree 
         Instance."
    INDEX { stpxRPVSTPortVlanIndex, stpxRPVSTPortIndex }
    ::= { stpxRPVSTPortTable 1 }

StpxRPVSTPortEntry ::= SEQUENCE {
    stpxRPVSTPortVlanIndex VlanIndex,
    stpxRPVSTPortIndex INTEGER,
    stpxRPVSTPortStatus OCTET STRING
    }

stpxRPVSTPortVlanIndex OBJECT-TYPE
    SYNTAX VlanIndex
--    Rsyntax INTEGER(0..4095)
    ACCESS not-accessible
    STATUS mandatory
    DESCRIPTION
        "The VLAN id of the VLAN."
    ::= { stpxRPVSTPortEntry 1 }

stpxRPVSTPortIndex OBJECT-TYPE
    SYNTAX INTEGER(1..65535)
    ACCESS not-accessible
    STATUS mandatory
    DESCRIPTION
        "The value of dot1dBasePort (i.e. dot1dBridge.1.4)
         for the bridge port."
    REFERENCE
        "dot1dBasePort is defined in RFC1493."
    ::= { stpxRPVSTPortEntry 2 }

stpxRPVSTPortStatus OBJECT-TYPE
    SYNTAX OCTET STRING(SIZE(1..2))
        -- BITS are:
        --   edge(0)
        --   unused1(1)
        --   unused2(2)
        --   stp(3)
        --   dispute(4)
    ACCESS read-only
    STATUS mandatory
    DESCRIPTION
        "Indicates the operational status of the port for the 
         Rapid PVST+ protocol.
        
        edge -- this port is an edge port for the RST region.
        
        unused1 -- unused bit 1.
        
        unused2 -- unused bit 2.
        
        stp -- this port is connected to a Single Spanning
                Tree/PVST+ bridge.
        
        dispute -- this port, as a designated port, received an
                inferior BPDU with a designated role and the
                learning bit being set."
    ::= { stpxRPVSTPortEntry 3 }

stpxSMSTMaxInstances OBJECT-TYPE
    SYNTAX Gauge
    ACCESS read-only
    STATUS mandatory
    DESCRIPTION
        "The maximum number of MST instances that can be 
        supported by the device for IEEE MST."
    ::= { stpxSMSTObjects 1 }

stpxSMSTMaxInstanceID OBJECT-TYPE
    SYNTAX Gauge
    ACCESS read-only
    STATUS mandatory
    DESCRIPTION
        "The maximum MST instance ID that can be supported 
        by the device for IEEE MST."
    ::= { stpxSMSTObjects 2 }

stpxSMSTRegionRevision OBJECT-TYPE
    SYNTAX Gauge
    ACCESS read-only
    STATUS mandatory
    DESCRIPTION
        "The operational region version for IEEE MST."
    ::= { stpxSMSTObjects 3 }

stpxSMSTRegionEditRevision OBJECT-TYPE
    SYNTAX Gauge
    ACCESS read-write
    STATUS mandatory
    DESCRIPTION
        "The MST region version in the Edit Buffer for IEEE 
        MST.
        
        This object is only instantiated when the 
        stpxMSTRegionEditBufferStatus has the value of 
        acquiredBySnmp(2)."
    ::= { stpxSMSTObjects 4 }

stpxSMSTInstanceTable OBJECT-TYPE
    SYNTAX SEQUENCE OF StpxSMSTInstanceEntry
    ACCESS not-accessible
    STATUS mandatory
    DESCRIPTION
        "This table contains MST instance information
        for IEEE MST."
    ::= { stpxSMSTObjects 5 }

stpxSMSTInstanceEntry OBJECT-TYPE
    SYNTAX StpxSMSTInstanceEntry
    ACCESS not-accessible
    STATUS mandatory
    DESCRIPTION
        "A conceptual row containing the MST instance 
        information for IEEE MST."
    INDEX { stpxSMSTInstanceIndex }
    ::= { stpxSMSTInstanceTable 1 }

StpxSMSTInstanceEntry ::= SEQUENCE {
    stpxSMSTInstanceIndex Gauge,
    stpxSMSTInstanceVlansMapped1k2k OCTET STRING,
    stpxSMSTInstanceVlansMapped3k4k OCTET STRING,
    stpxSMSTInstanceRemainingHopCount INTEGER,
    stpxSMSTInstanceCISTRegionalRoot OCTET STRING,
    stpxSMSTInstanceCISTIntRootCost Gauge
    }

stpxSMSTInstanceIndex OBJECT-TYPE
    SYNTAX Gauge
    ACCESS not-accessible
    STATUS mandatory
    DESCRIPTION
        "The MST instance ID, the value of which is in the range 
        from 0 to stpxSMSTMaxInstanceID."
    ::= { stpxSMSTInstanceEntry 1 }

stpxSMSTInstanceVlansMapped1k2k OBJECT-TYPE
    SYNTAX OCTET STRING(SIZE(0..256))
    ACCESS read-only
    STATUS mandatory
    DESCRIPTION
        "A string of octets containing one bit per VLAN for
        VLANS with VlanIndex values of 0 through 2047. The
        first octet corresponds to VLANs with VlanIndex values
        of 0 through 7; the second octet to VLANs 8 through
        15; etc.  The most significant bit of each octet
        corresponds to the lowest value VlanIndex in that octet.
        
        For each VLAN, if it is mapped to this MST instance,
        then the bit corresponding to that VLAN is set to '1'.
        If the length of this string is less than 256 octets,
        any 'missing' octets are assumed to contain the value 
        of zero."
    ::= { stpxSMSTInstanceEntry 2 }

stpxSMSTInstanceVlansMapped3k4k OBJECT-TYPE
    SYNTAX OCTET STRING(SIZE(0..256))
    ACCESS read-only
    STATUS mandatory
    DESCRIPTION
        "A string of octets containing one bit per VLAN for
        VLANS with VlanIndex values of 2048 through 4095. The
        first octet corresponds to VLANs with VlanIndex values
        of 2048 through 2055; the second octet to VLANs 2056
        through 2063; etc.  The most significant bit of each
        octet corresponds to the lowest value VlanIndex in that
        octet.
        
        For each VLAN, if it is mapped to this MST instance,
        then the bit corresponding to that VLAN is set to '1'.
        If the length of this string is less than 256 octets,
        any 'missing' octets are assumed to contain the value 
        of zero."
    ::= { stpxSMSTInstanceEntry 3 }

stpxSMSTInstanceRemainingHopCount OBJECT-TYPE
    SYNTAX INTEGER(-1..2147483647)
    ACCESS read-only
    STATUS mandatory
    DESCRIPTION
        "The remaining hop count for this MST instance. If this object
        value is not applicable on an MST instance, then the value
        retrieved for this object for that MST instance will be -1. 
        
        This object is only instantiated when the object value of
        stpxSpanningTreeType is mst(4)."
    ::= { stpxSMSTInstanceEntry 4 }

stpxSMSTInstanceCISTRegionalRoot OBJECT-TYPE
    SYNTAX OCTET STRING(SIZE(8))
    ACCESS read-only
    STATUS mandatory
    DESCRIPTION
        "Indicates the Bridge Identifier (refer to BridgeId 
        defined in BRIDGE-MIB) of CIST (Common and Internal 
        Spanning Tree) Regional Root for the MST region.
        
        This object is only instantiated when the object value of
        stpxSpanningTreeType is mst(4) and stpxSMSTInstanceIndex
        is 0."
    REFERENCE
        "IEEE 802.1S-2002: Section 13.9."
    ::= { stpxSMSTInstanceEntry 5 }

stpxSMSTInstanceCISTIntRootCost OBJECT-TYPE
    SYNTAX Gauge
    ACCESS read-only
    STATUS mandatory
    DESCRIPTION
        "Indicates the CIST Internal Root Path Cost, i.e., the
        path cost to the CIST Regional Root as specified by the
        corresponding stpxSMSTInstanceCISTRegionalRoot for the 
        MST region.
        
        This object is only instantiated when the object value of
        stpxSpanningTreeType is mst(4) and stpxSMSTInstanceIndex
        is 0."
    REFERENCE
        "IEEE 802.1S-2002: Section 13.9."
    ::= { stpxSMSTInstanceEntry 6 }

stpxSMSTInstanceEditTable OBJECT-TYPE
    SYNTAX SEQUENCE OF StpxSMSTInstanceEditEntry
    ACCESS not-accessible
    STATUS mandatory
    DESCRIPTION
        "This table contains MST instance information in the 
        Edit Buffer. 
        
        This table is only instantiated when the object value
        of  stpxMSTRegionEditBufferStatus has the value of
        acquiredBySnmp(2)."
    ::= { stpxSMSTObjects 6 }

stpxSMSTInstanceEditEntry OBJECT-TYPE
    SYNTAX StpxSMSTInstanceEditEntry
    ACCESS not-accessible
    STATUS mandatory
    DESCRIPTION
        "A conceptual row containing MST instance information 
        in the Edit Buffer.
        
        The total number of entries in this table has to be 
        less than or equal to the object value of stpxSMSTMaxInstances."
    INDEX { stpxSMSTInstanceEditIndex }
    ::= { stpxSMSTInstanceEditTable 1 }

StpxSMSTInstanceEditEntry ::= SEQUENCE {
    stpxSMSTInstanceEditIndex Gauge,
    stpxSMSTInstanceEditVlansMap1k2k OCTET STRING,
    stpxSMSTInstanceEditVlansMap3k4k OCTET STRING,
    stpxSMSTInstanceEditRowStatus RowStatus
    }

stpxSMSTInstanceEditIndex OBJECT-TYPE
    SYNTAX Gauge
    ACCESS not-accessible
    STATUS mandatory
    DESCRIPTION
        "The MST instance ID, the value of which is in the range from
        0 to stpxSMSTMaxInstanceID. 
        
        The instances of this table entry with 
        stpxSMSTInstanceEditIndex of zero is automatically
        created by the device and can not modified."
    ::= { stpxSMSTInstanceEditEntry 1 }

stpxSMSTInstanceEditVlansMap1k2k OBJECT-TYPE
    SYNTAX OCTET STRING(SIZE(0..256))
    ACCESS read-write
    STATUS mandatory
    DESCRIPTION
        "A string of octets containing one bit per VLAN for
        VLANS with VlanIndex values of 0 through 2047. The
        first octet corresponds to VLANs with VlanIndex values
        of 0 through 7; the second octet to VLANs 8 through
        15; etc.  The most significant bit of each octet
        corresponds to the lowest value VlanIndex in that octet.
        
        For each VLAN, if it is mapped to this MST instance, 
        then the bit corresponding to that VLAN is set to 
        '1'. Each VLAN can only be mapped to one unique MST 
        instance with the range from 0 to stpxSMSTMaxInstanceNumber.
        If the bit corresponding to a VLAN is changed from '1' 
        to '0', then that VLAN will be automatically mapped to 
        SMST instance 0 by the device. If the bit corresponding 
        to a VLAN is changed from '0' to '1', then that VLAN will 
        be automatically removed from the MST instance this VLAN was 
        previously mapped to. If the length of this string is 
        less than 256 octets, any 'missing' octets are assumed to 
        contain the value of zero."
    ::= { stpxSMSTInstanceEditEntry 2 }

stpxSMSTInstanceEditVlansMap3k4k OBJECT-TYPE
    SYNTAX OCTET STRING(SIZE(0..256))
    ACCESS read-write
    STATUS mandatory
    DESCRIPTION
        "A string of octets containing one bit per VLAN for
        VLANS with VlanIndex values of 2048 through 4095. The
        first octet corresponds to VLANs with VlanIndex values
        of 2048 through 2055; the second octet to VLANs 2056 through
        2063; etc.  The most significant bit of each octet
        corresponds to the lowest value VlanIndex in that octet.
        
        For each VLAN, if it is mapped to this MST instance,
        then the bit corresponding to that VLAN is set to
        '1'. Each VLAN can only be mapped to one unique MST
        instance with the range from 0 to stpxSMSTMaxInstanceNumber.
        If the bit corresponding to a VLAN is changed from '1'
        to '0', then that VLAN will be automatically mapped to
        SMST instance 0 by the device. If the bit corresponding
        to a VLAN is changed from '0' to '1', then that VLAN will
        be automatically removed from the MST instance this VLAN was
        previously mapped to. If the length of this string is 
        less than 256 octets, any 'missing' octets are assumed to 
        contain the value of zero."
    ::= { stpxSMSTInstanceEditEntry 3 }

stpxSMSTInstanceEditRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object controls the creation and deletion of a row 
        in stpxSMSTInstanceEditTable.
        
        When creating an entry in this table, 'createAndGo' method
        is used and the value of this object is set to 'active'.
        Deactivation of an 'active' entry is not allowed.  When 
        deleting an entry in this table, 'destroy' method is used. 
        Once a row becomes active, value in any other column 
        within such a row may be modified. When a row is active, 
        setting the instance of stpxSMSTInstanceEditVlansMap1k2k
        stpxSMSTInstanceEditVlansMap3k4k for the same MST instance
        both to the value of zero length can not be allowed."
    ::= { stpxSMSTInstanceEditEntry 4 }

stpxSMSTPortTable OBJECT-TYPE
    SYNTAX SEQUENCE OF StpxSMSTPortEntry
    ACCESS not-accessible
    STATUS mandatory
    DESCRIPTION
        "A table containing port information for the MST 
        Protocol on all the bridge ports existing on the 
        system.
        
        This table is only instantiated when the object 
        value of stpxSpanningTreeType is mst(4)"
    ::= { stpxSMSTObjects 7 }

stpxSMSTPortEntry OBJECT-TYPE
    SYNTAX StpxSMSTPortEntry
    ACCESS not-accessible
    STATUS mandatory
    DESCRIPTION
        "An entry with port information for the MST protocol
        on a bridge port."
    INDEX { stpxSMSTPortIndex }
    ::= { stpxSMSTPortTable 1 }

StpxSMSTPortEntry ::= SEQUENCE {
    stpxSMSTPortIndex INTEGER,
    stpxSMSTPortStatus OCTET STRING,
    stpxSMSTPortAdminHelloTime Gauge,
    stpxSMSTPortConfigedHelloTime Gauge,
    stpxSMSTPortOperHelloTime INTEGER,
    stpxSMSTPortAdminMSTMode INTEGER,
    stpxSMSTPortOperMSTMode INTEGER
    }

stpxSMSTPortIndex OBJECT-TYPE
    SYNTAX INTEGER(1..65535)
    ACCESS not-accessible
    STATUS mandatory
    DESCRIPTION
        "The value of dot1dBasePort (i.e. dot1dBridge.1.4)
         for the bridge port."
    REFERENCE
        "dot1dBasePort is defined in RFC1493."
    ::= { stpxSMSTPortEntry 1 }

stpxSMSTPortStatus OBJECT-TYPE
    SYNTAX OCTET STRING(SIZE(1..2))
        -- BITS are:
        --   edge(0)
        --   boundary(1)
        --   pvst(2)
        --   stp(3)
        --   dispute(4)
        --   rstp(5)
    ACCESS read-only
    STATUS mandatory
    DESCRIPTION
        "Indicates the operational status of the port for the 
        MST protocol. 
        
        edge -- this port is an edge port for the MST region.
        
        boundary -- this port is a boundary port for the 
                MST region.
        
        pvst --  this port is connected to a PVST/PVST+ bridge.   
        
        stp -- this port is connected to a Single Spanning
                Tree bridge.
        
        dispute -- this port, as a designated port, received an
                inferior BPDU with a designated role and the
                learning bit being set.
        
        rstp -- this port is connected to a RSTP bridge or an 
                MST bridge in a different MST region."
    ::= { stpxSMSTPortEntry 2 }

stpxSMSTPortAdminHelloTime OBJECT-TYPE
    SYNTAX Gauge
--  Units
--    hundredth of seconds
    ACCESS read-write
    STATUS mandatory
    DESCRIPTION
        "The adminitratively configured hello time in hundredth 
        of seconds on a port for IEEE MST. The granularity 
        of this timer is 1 second. An agent may return a badValue 
        error if a set is attempted to a value which is not a 
        whole number of seconds. This object value of zero
        means the hello time is not specifically configured on 
        this port and object value of stpxSMSTPortConfigedHelloTime
        retrieved for this port will take on the value of 
        dot1dStpBridgeHelloTime defined in BRIDGE-MIB."
    ::= { stpxSMSTPortEntry 3 }

stpxSMSTPortConfigedHelloTime OBJECT-TYPE
    SYNTAX Gauge
--  Units
--    hundredth of seconds
    ACCESS read-only
    STATUS mandatory
    DESCRIPTION
        "Indicates the effective configuration of the hello time on 
        a port."
    ::= { stpxSMSTPortEntry 4 }

stpxSMSTPortOperHelloTime OBJECT-TYPE
    SYNTAX INTEGER(-1..2147483647)
--  Units
--    hundredth of seconds
    ACCESS read-only
    STATUS mandatory
    DESCRIPTION
        "The operational hello time in hundredth of seconds on a 
        port for IEEE MST. If this object value is not
        applicable on a port, then the value retrieved on that
        port will be -1."
    ::= { stpxSMSTPortEntry 5 }

stpxSMSTPortAdminMSTMode OBJECT-TYPE
    SYNTAX INTEGER {
        preStandard(1),
        auto(2)
        }
    ACCESS read-write
    STATUS mandatory
    DESCRIPTION
        "The desired MST mode of this port.
        
        preStandard -- this port is administratively configured to
            transmit pre-standard, i.e. pre IEEE MST, BPDUs.
        
        auto -- the BPDU transmission mode of this port is based 
            on automatic detection of neighbor ports."
    ::= { stpxSMSTPortEntry 6 }

stpxSMSTPortOperMSTMode OBJECT-TYPE
    SYNTAX INTEGER {
        unknown(1),
        preStandard(2),
        standard(3)
        }
    ACCESS read-only
    STATUS mandatory
    DESCRIPTION
        "Indicates the current operational MST mode of this port.
        
        unknown -- the operational mode is currently unknown.
        
        preStandard -- this port is currently operating in 
            pre-standard MSTP BPDU transmission mode.
        
        standard -- this port is currently operating in IEEE MST 
            BPDU transmission mode."
    ::= { stpxSMSTPortEntry 7 }

stpxSMSTMaxHopCount OBJECT-TYPE
    SYNTAX Gauge
    ACCESS read-write
    STATUS mandatory
    DESCRIPTION
        "The maximum number of hops for the IEEE MST region."
    ::= { stpxSMSTObjects 8 }

stpxSMSTConfigDigest OBJECT-TYPE
    SYNTAX StpxMSTConfigurationDigest
--    Rsyntax OCTET STRING(SIZE(16))
    ACCESS read-only
    STATUS mandatory
    DESCRIPTION
        "The IEEE MST region configuration digest."
    REFERENCE
        "IEEE 802.1Q-2003 Section 13.7."
    ::= { stpxSMSTObjects 9 }

stpxSMSTConfigPreStandardDigest OBJECT-TYPE
    SYNTAX StpxMSTConfigurationDigest
--    Rsyntax OCTET STRING(SIZE(16))
    ACCESS read-only
    STATUS mandatory
    DESCRIPTION
        "The pre-standard MST region configuration digest."
    ::= { stpxSMSTObjects 10 }

stpxInconsistencyUpdate TRAP-TYPE
-- Reverse mappable trap
    ENTERPRISE stpxNotifications
    VARIABLES {
        stpxInconsistentState }
--  Status
--    mandatory
    DESCRIPTION
        "A stpxPortInconsistencyUpdate notification is sent by a
         bridge when an instance of stpxInconsistentState is 
         created or destroyed.  That is, when an inconsistency is
         discovered in the VLAN's Spanning Tree for a particular 
         port, or when such an inconsistency disappears.  Note 
         that the trap is not sent if the port transitions between
         different types of inconsistency.
        
         The stpxInconsistentState value indicates the type of
         inconsistency which now exists/no longer exists for the 
         relevant VLAN on the relevant port."
    ::= 1

stpxRootInconsistencyUpdate TRAP-TYPE
-- Reverse mappable trap
    ENTERPRISE stpxNotifications
    VARIABLES {
        stpxRootInconsistencyState, stpxSpanningTreeType }
--  Status
--    mandatory
    DESCRIPTION
        "A stpxRootInconsistencyUpdate notification is sent by a
         bridge when an instance of stpxRootInconsistencyState
         is created or destroyed. That is, when an
         root-inconsistency is discovered in the VLAN's or 
         instance's Spanning Tree for a particular port, or when 
         such an root-inconsistency disappears. For creation, the 
         value of stpxRootInconsistencyState in the notification is
         true(1); for deletion, the value is false(2).
        
         The object value of stpxSpanningTreeType indicates
         which Spanning Tree protocol is running when an instance 
         of stpxRootInconsistencyState is created or destroyed.  "
    ::= 2

stpxLoopInconsistencyUpdate TRAP-TYPE
-- Reverse mappable trap
    ENTERPRISE stpxNotifications
    VARIABLES {
        stpxLoopInconsistencyState, stpxSpanningTreeType }
--  Status
--    mandatory
    DESCRIPTION
        "A stpxLoopInconsistencyUpdate notification is sent by a
         bridge when an instance of stpxLoopInconsistencyState
         is created or destroyed. That is, when an
         loop-inconsistency is discovered in the VLAN's or 
         instance's Spanning Tree for a particular port, or when 
         such an loop-inconsistency disappears. For creation, 
         the value of stpxLoopInconsistencyState in the 
         notification is true(1); for deletion, the value is 
         false(2).
        
         The object value of stpxSpanningTreeType indicates
         which Spanning Tree protocol is running when an instance
         of stpxLoopInconsistencyState is created or 
         destroyed."
    ::= 3

stpxUplinkGroup OBJECT IDENTIFIER ::= { stpxMIBGroups 1 }
-- OBJECT-GROUP
--  Status
--    mandatory
--  Descr
--    A collection of objects for managing the UplinkFast
--    capability.
--  objects
--    stpxUplinkFastEnabled, stpxUplinkFastTransitions, 
--    stpxUplinkStationLearningGenRate, 
--    stpxUplinkStationLearningFrames

stpxPreferredVlansGroup OBJECT IDENTIFIER ::= { stpxMIBGroups 2 }
-- OBJECT-GROUP
--  Status
--    mandatory
--  Descr
--    A collection of objects for indicating preferred VLANs.
--  objects
--    stpxPreferredVlansMap

stpxSstpGroup OBJECT IDENTIFIER ::= { stpxMIBGroups 3 }
-- OBJECT-GROUP
--  Status
--    mandatory
--  Descr
--    A collection of objects to support Cisco's Shared Spanning
--    Tree Protocol (SSTP).
--  objects
--    stpxInconsistentState

stpxBackboneGroup OBJECT IDENTIFIER ::= { stpxMIBGroups 5 }
-- OBJECT-GROUP
--  Status
--    mandatory
--  Descr
--    A collection of objects for managing the BackboneFast
--    capability.
--  objects
--    stpxBackboneFastEnabled, stpxBackboneFastInInferiorBPDUs, 
--    stpxBackboneFastInRLQRequestPDUs, 
--    stpxBackboneFastInRLQResponsePDUs, 
--    stpxBackboneFastOutRLQRequestPDUs, 
--    stpxBackboneFastOutRLQResponsePDUs

stpxRootGuardGroup OBJECT IDENTIFIER ::= { stpxMIBGroups 6 }
-- OBJECT-GROUP
--  Status
--    mandatory
--  Descr
--    A collection of objects to support root guard
--    capabilities.
--  objects
--    stpxRootGuardConfigEnabled, stpxRootInconsistencyState

stpx4kVlanGroup OBJECT IDENTIFIER ::= { stpxMIBGroups 8 }
-- OBJECT-GROUP
--  Status
--    mandatory
--  Descr
--    A collection of objects providing information
--    for VLANS with VlanIndex from 1024 to 4095.
--  objects
--    stpxPreferredVlansMap2k, stpxPreferredVlansMap3k, 
--    stpxPreferredVlansMap4k

stpxSpanningTreeGroup OBJECT IDENTIFIER ::= { stpxMIBGroups 9 }
-- OBJECT-GROUP
--  Status
--    mandatory
--  Descr
--    An object selecting what kind of spanning tree protocol.
--  objects
--    stpxSpanningTreeType

stpxMISTPGroup OBJECT IDENTIFIER ::= { stpxMIBGroups 10 }
-- OBJECT-GROUP
--  Status
--    mandatory
--  Descr
--    A collection objects managing the information of
--     MISTP feature.
--  objects
--    stpxMISTPInstanceNumber, stpxMISTPInstanceEnable, 
--    stpxVlanMISTPInstMapInstIndex, 
--    stpxVlanMISTPInstMapEditInstIndex, 
--    stpxPreferredMISTPInstancesMap

stpxLongPathCostModeGroup OBJECT IDENTIFIER ::= { stpxMIBGroups 11 }
-- OBJECT-GROUP
--  Status
--    mandatory
--  Descr
--    A collection objects managing the information of
--    spanning tree path cost in 32 bits value.
--  objects
--    stpxSpanningTreePathCostMode, stpxLongStpPortPathCost

stpxPVSTVlanGroup OBJECT IDENTIFIER ::= { stpxMIBGroups 12 }
-- OBJECT-GROUP
--  Status
--    mandatory
--  Descr
--    A collection of objects managing the information 
--    of Spanning Tree PVST+ protocol VLAN configuration.
--  objects
--    stpxPVSTVlanEnable

stpxMISTPGroup2 OBJECT IDENTIFIER ::= { stpxMIBGroups 13 }
-- OBJECT-GROUP
--  Status
--    mandatory
--  Descr
--    A collection objects managing the information of
--    MISTP instances to VLAN mapping with the range of
--    VlanIndex up to 4095.
--  objects
--    stpxMISTPInstanceVlansMapped, stpxMISTPInstanceVlansMapped2k, 
--    stpxMISTPInstanceVlansMapped3k, 
--    stpxMISTPInstanceVlansMapped4k

stpxLoopGuardGroup OBJECT IDENTIFIER ::= { stpxMIBGroups 14 }
-- OBJECT-GROUP
--  Status
--    deprecated
--  Descr
--    A collection of objects to support LoopGuard 
--    capabilities.
--  objects
--    stpxLoopGuardConfigEnabled, stpxLoopInconsistencyState

stpxFastStartGroup OBJECT IDENTIFIER ::= { stpxMIBGroups 16 }
-- OBJECT-GROUP
--  Status
--    deprecated
--  Descr
--    A collection of objects to support Spanning Tree Port
--    Fast Start feature.
--  objects
--    stpxFastStartBpduGuardEnable, stpxFastStartBpduFilterEnable, 
--    stpxFastStartPortEnable

stpxBpduSkewingGroup OBJECT IDENTIFIER ::= { stpxMIBGroups 17 }
-- OBJECT-GROUP
--  Status
--    mandatory
--  Descr
--    This is an optional group with a collection of
--    objects to support Spanning Tree BPDU Skewing feature.
--  objects
--    stpxBpduSkewingDetectionEnable, 
--    stpxBpduSkewingLastSkewDuration, 
--    stpxBpduSkewingWorstSkewDuration, 
--    stpxBpduSkewingWorstSkewTime

stpxFastStartGroup2 OBJECT IDENTIFIER ::= { stpxMIBGroups 18 }
-- OBJECT-GROUP
--  Status
--    mandatory
--  Descr
--    An optional group with a collection of objects to 
--    support Fast Start global default mode on the device.
--  objects
--    stpxFastStartBpduGuardEnable, stpxFastStartBpduFilterEnable, 
--    stpxFastStartPortMode, stpxFastStartGlobalDefaultMode

stpxLoopGuardGroup2 OBJECT IDENTIFIER ::= { stpxMIBGroups 19 }
-- OBJECT-GROUP
--  Status
--    mandatory
--  Descr
--    An optional group with a collection of objects to 
--    support Loop Guard global default mode on the device.
--  objects
--    stpxLoopInconsistencyState, stpxLoopGuardConfigMode, 
--    stpxLoopGuardGlobalDefaultMode

stpxMSTGroup OBJECT IDENTIFIER ::= { stpxMIBGroups 20 }
-- OBJECT-GROUP
--  Status
--    deprecated
--  Descr
--    An optional group with a collection of objects to 
--    support Multiple Spanning Tree Protocol on the device.
--  objects
--    stpxMSTMaxInstanceNumber, stpxMSTRegionName, 
--    stpxMSTRegionRevision, stpxMSTInstanceVlansMapped, 
--    stpxMSTInstanceVlansMapped2k, stpxMSTInstanceVlansMapped3k, 
--    stpxMSTInstanceVlansMapped4k, 
--    stpxMSTInstanceRemainingHopCount, 
--    stpxMSTRegionEditBufferStatus, 
--    stpxMSTRegionEditBufferOperation, stpxMSTRegionEditName, 
--    stpxMSTRegionEditRevision, stpxMSTInstanceEditVlansMap, 
--    stpxMSTInstanceEditVlansMap2k, stpxMSTInstanceEditVlansMap3k, 
--    stpxMSTInstanceEditVlansMap4k, stpxMSTPortAdminLinkType, 
--    stpxMSTPortOperLinkType, stpxMSTPortProtocolMigration, 
--    stpxMSTPortStatus, stpxMSTPortRoleValue, stpxMSTMaxHopCount

stpxPreferredMSTInstancesGroup OBJECT IDENTIFIER ::= { stpxMIBGroups 21 }
-- OBJECT-GROUP
--  Status
--    deprecated
--  Descr
--    An optional group with a collection of objects to
--    support Preferred MST Instance Map feature for Multiple 
--    Spanning Tree Protocol on the device.
--  objects
--    stpxPreferredMSTInstancesMap

stpxFastStartGroup3 OBJECT IDENTIFIER ::= { stpxMIBGroups 22 }
-- OBJECT-GROUP
--  Status
--    mandatory
--  Descr
--    An optional group with a collection of objects to
--    support per port Bpdu Guard and Bpdu Filter mode 
--    configuration on the device.
--  objects
--    stpxFastStartPortBpduGuardMode, 
--    stpxFastStartPortBpduFilterMode

stpxUplinkGroup2 OBJECT IDENTIFIER ::= { stpxMIBGroups 23 }
-- OBJECT-GROUP
--  Status
--    mandatory
--  Descr
--    An optional group with a collection of objects to
--    manage the UplinkFast capability.
--  objects
--    stpxUplinkFastOperEnabled

stpxBackboneGroup2 OBJECT IDENTIFIER ::= { stpxMIBGroups 24 }
-- OBJECT-GROUP
--  Status
--    mandatory
--  Descr
--    An optional group with a collection of objects to 
--    manage the BackboneFast capability.
--  objects
--    stpxBackboneFastOperEnabled

stpxMSTGroup2 OBJECT IDENTIFIER ::= { stpxMIBGroups 25 }
-- OBJECT-GROUP
--  Status
--    deprecated
--  Descr
--    An optional group with a collection of objects to 
--    support Multiple Spanning Tree Protocol on the device.
--  objects
--    stpxMSTMaxInstanceNumber, stpxMSTRegionName, 
--    stpxMSTRegionRevision, stpxMSTInstanceVlansMapped, 
--    stpxMSTInstanceVlansMapped2k, stpxMSTInstanceVlansMapped3k, 
--    stpxMSTInstanceVlansMapped4k, 
--    stpxMSTInstanceRemainingHopCount, 
--    stpxMSTRegionEditBufferStatus, 
--    stpxMSTRegionEditBufferOperation, stpxMSTRegionEditName, 
--    stpxMSTRegionEditRevision, stpxMSTInstanceEditVlansMap, 
--    stpxMSTInstanceEditVlansMap2k, stpxMSTInstanceEditVlansMap3k, 
--    stpxMSTInstanceEditVlansMap4k, stpxMSTPortStatus, 
--    stpxMSTMaxHopCount

stpxRSTPGroup OBJECT IDENTIFIER ::= { stpxMIBGroups 26 }
-- OBJECT-GROUP
--  Status
--    mandatory
--  Descr
--    An optional group with a collection of objects to
--    support Rapid Spanning Tree Protocol on the device.
--  objects
--    stpxRSTPPortAdminLinkType, stpxRSTPPortOperLinkType, 
--    stpxRSTPPortProtocolMigration, stpxRSTPPortRoleValue

stpxRPVSTGroup OBJECT IDENTIFIER ::= { stpxMIBGroups 27 }
-- OBJECT-GROUP
--  Status
--    mandatory
--  Descr
--    An optional group with a collection of objects to
--    support Rapid PVST+ on the device.
--  objects
--    stpxRPVSTPortStatus

stpxExtendedSysIDGroup OBJECT IDENTIFIER ::= { stpxMIBGroups 28 }
-- OBJECT-GROUP
--  Status
--    mandatory
--  Descr
--    A collection of objects to manage the 
--    Extended System ID capability.
--  objects
--    stpxExtendedSysIDAdminEnabled, stpxExtendedSysIDOperEnabled

stpxNotificationEnableGroup OBJECT IDENTIFIER ::= { stpxMIBGroups 29 }
-- OBJECT-GROUP
--  Status
--    mandatory
--  Descr
--    A collection of objects providing control on the 
--    generation of Spanning Tree notifications.
--  objects
--    stpxNotificationEnable

stpxFastStartOperModeGroup OBJECT IDENTIFIER ::= { stpxMIBGroups 30 }
-- OBJECT-GROUP
--  Status
--    mandatory
--  Descr
--    A collection of objects providing Spanning Tree 
--    Port Fast Start Operatioanl information on a port.
--  objects
--    stpxFastStartOperMode

stpxMSTGroup3 OBJECT IDENTIFIER ::= { stpxMIBGroups 31 }
-- OBJECT-GROUP
--  Status
--    deprecated
--  Descr
--    A collection of objects providing support 
--    for Multiple Spanning Tree Protocol on the device.
--  objects
--    stpxMSTRegionName, stpxMSTRegionEditBufferStatus, 
--    stpxMSTRegionEditBufferOperation, stpxMSTRegionEditName, 
--    stpxMSTMaxHopCount

stpxSMSTGroup OBJECT IDENTIFIER ::= { stpxMIBGroups 32 }
-- OBJECT-GROUP
--  Status
--    mandatory
--  Descr
--    A collection of objects providing support for
--    IEEE MST on the device.
--  objects
--    stpxSMSTMaxInstances, stpxSMSTMaxInstanceID, 
--    stpxSMSTRegionRevision, stpxSMSTRegionEditRevision

stpxSMSTInstanceGroup OBJECT IDENTIFIER ::= { stpxMIBGroups 33 }
-- OBJECT-GROUP
--  Status
--    mandatory
--  Descr
--    A collection of objects providing support for 
--    MST instance information for IEEE MST on the device.
--  objects
--    stpxSMSTInstanceVlansMapped1k2k, 
--    stpxSMSTInstanceVlansMapped3k4k, 
--    stpxSMSTInstanceRemainingHopCount

stpxSMSTInstanceEditGroup OBJECT IDENTIFIER ::= { stpxMIBGroups 34 }
-- OBJECT-GROUP
--  Status
--    mandatory
--  Descr
--    A collection of objects providing support for MST 
--    instance edit information for IEEE MST on the device.
--  objects
--    stpxSMSTInstanceEditVlansMap1k2k, 
--    stpxSMSTInstanceEditVlansMap3k4k, 
--    stpxSMSTInstanceEditRowStatus

stpxSMSTPortStatusGroup OBJECT IDENTIFIER ::= { stpxMIBGroups 35 }
-- OBJECT-GROUP
--  Status
--    mandatory
--  Descr
--    A collection of objects providing support for  
--    port status information for MST Protocol on the
--    device.
--  objects
--    stpxSMSTPortStatus

stpxSMSTPortHelloTimeGroup OBJECT IDENTIFIER ::= { stpxMIBGroups 36 }
-- OBJECT-GROUP
--  Status
--    mandatory
--  Descr
--    A collection of objects providing support for per 
--    port hello time information for IEEE MST on the device.
--  objects
--    stpxSMSTPortAdminHelloTime, stpxSMSTPortConfigedHelloTime, 
--    stpxSMSTPortOperHelloTime

stpxSMSTInstanceCISTGroup OBJECT IDENTIFIER ::= { stpxMIBGroups 37 }
-- OBJECT-GROUP
--  Status
--    mandatory
--  Descr
--    A collection of objects providing information about 
--    Common and Internal Spanning Tree (CIST) for IEEE 
--    MST on the device.
--  objects
--    stpxSMSTInstanceCISTRegionalRoot, 
--    stpxSMSTInstanceCISTIntRootCost

stpxPathCostOperModeGroup OBJECT IDENTIFIER ::= { stpxMIBGroups 38 }
-- OBJECT-GROUP
--  Status
--    mandatory
--  Descr
--    A collection of objects providing information about 
--     operational spanning tree path cost mode.
--  objects
--    stpxSpanningTreePathCostOperMode

stpxRSTPTransmitHoldCountGroup OBJECT IDENTIFIER ::= { stpxMIBGroups 39 }
-- OBJECT-GROUP
--  Status
--    mandatory
--  Descr
--    A collection of objects providing information for
--    configuration of transmit hold count for Rapid Spanning
--    Tree Protocol.
--  objects
--    stpxRSTPTransmitHoldCount

stpxSMSTPortMSTModeGroup OBJECT IDENTIFIER ::= { stpxMIBGroups 40 }
-- OBJECT-GROUP
--  Status
--    mandatory
--  Descr
--    A collection of objects providing information for port 
--    MST mode configuration on the device.
--  objects
--    stpxSMSTPortAdminMSTMode, stpxSMSTPortOperMSTMode

stpxSMSTMaxHopCountGroup OBJECT IDENTIFIER ::= { stpxMIBGroups 41 }
-- OBJECT-GROUP
--  Status
--    mandatory
--  Descr
--    A collection of objects providing information for 
--    configuration of IEEE MST maximum hop count.
--  objects
--    stpxSMSTMaxHopCount

stpxSMSTConfigDigestGroup OBJECT IDENTIFIER ::= { stpxMIBGroups 42 }
-- OBJECT-GROUP
--  Status
--    mandatory
--  Descr
--    A collection of objects providing information for
--    MST configuration digests on the device.
--  objects
--    stpxSMSTConfigDigest, stpxSMSTConfigPreStandardDigest

stpxMSTGroup4 OBJECT IDENTIFIER ::= { stpxMIBGroups 43 }
-- OBJECT-GROUP
--  Status
--    mandatory
--  Descr
--    A collection of objects providing support 
--    for Multiple Spanning Tree Protocol on the device.
--  objects
--    stpxMSTRegionName, stpxMSTRegionEditBufferStatus, 
--    stpxMSTRegionEditBufferOperation, stpxMSTRegionEditName

stpxNotificationsGroup OBJECT IDENTIFIER ::= { stpxMIBGroups 4 }
-- NOTIFICATION-GROUP
--  Status
--    mandatory
--  Descr
--    The notifications which a STP extension implementation is
--     required to implement.
--  notifications
--    stpxInconsistencyUpdate

stpxRootInconsistencyNotificationsGroup OBJECT IDENTIFIER ::= { stpxMIBGroups 7 }
-- NOTIFICATION-GROUP
--  Status
--    mandatory
--  Descr
--    The notifications which a STP root guard 
--      implementation is required to implement.
--  notifications
--    stpxRootInconsistencyUpdate

stpxLoopInconsistencyNotificationsGroup OBJECT IDENTIFIER ::= { stpxMIBGroups 15 }
-- NOTIFICATION-GROUP
--  Status
--    mandatory
--  Descr
--    The notifications which a STP LoopGuard 
--      implementation is required to implement.
--  notifications
--    stpxLoopInconsistencyUpdate

stpxMIBCompliance OBJECT IDENTIFIER ::= { stpxMIBCompliances 1 }
-- MODULE-COMPLIANCE
--  Status
--    deprecated
--  Descr
--    The compliance statement for entities which implement
--    Cisco STP Extensions MIB.
--  Module
--    >>current<<
--   OptGroup
--    stpxUplinkGroup
--   OptGroup
--    stpxPreferredVlansGroup
--   OptGroup
--    stpxNotificationsGroup

stpxMIBCompliance2 OBJECT IDENTIFIER ::= { stpxMIBCompliances 2 }
-- MODULE-COMPLIANCE
--  Status
--    deprecated
--  Descr
--    The compliance statement for entities which implement
--    Cisco STP Extensions MIB.
--  Module
--    >>current<<
--   OptGroup
--    stpxUplinkGroup
--   OptGroup
--    stpxPreferredVlansGroup
--   OptGroup
--    stpxNotificationsGroup
--   OptGroup
--    stpxBackboneGroup

stpxMIBCompliance3 OBJECT IDENTIFIER ::= { stpxMIBCompliances 3 }
-- MODULE-COMPLIANCE
--  Status
--    deprecated
--  Descr
--    The compliance statement for entities which implement
--    Cisco STP Extensions MIB.
--  Module
--    >>current<<
--   OptGroup
--    stpxUplinkGroup
--   OptGroup
--    stpxPreferredVlansGroup
--   OptGroup
--    stpxNotificationsGroup
--   OptGroup
--    stpxBackboneGroup
--   OptGroup
--    stpxRootGuardGroup
--   OptGroup
--    stpxRootInconsistencyNotificationsGroup
--   OptGroup
--    stpx4kVlanGroup
--   OptGroup
--    stpxSpanningTreeGroup
--   OptGroup
--    stpxMISTPGroup

stpxMIBCompliance4 OBJECT IDENTIFIER ::= { stpxMIBCompliances 4 }
-- MODULE-COMPLIANCE
--  Status
--    deprecated
--  Descr
--    The compliance statement for entities which implement
--    Cisco STP Extensions MIB.
--  Module
--    >>current<<
--   OptGroup
--    stpxUplinkGroup
--   OptGroup
--    stpxPreferredVlansGroup
--   OptGroup
--    stpxNotificationsGroup
--   OptGroup
--    stpxBackboneGroup
--   OptGroup
--    stpxRootGuardGroup
--   OptGroup
--    stpxRootInconsistencyNotificationsGroup
--   OptGroup
--    stpx4kVlanGroup
--   OptGroup
--    stpxSpanningTreeGroup
--   OptGroup
--    stpxMISTPGroup
--   OptGroup
--    stpxLongPathCostModeGroup

stpxMIBCompliance5 OBJECT IDENTIFIER ::= { stpxMIBCompliances 5 }
-- MODULE-COMPLIANCE
--  Status
--    deprecated
--  Descr
--    The compliance statement for entities which implement
--    Cisco STP Extensions MIB.
--  Module
--    >>current<<
--   OptGroup
--    stpxUplinkGroup
--   OptGroup
--    stpxPreferredVlansGroup
--   OptGroup
--    stpxNotificationsGroup
--   OptGroup
--    stpxBackboneGroup
--   OptGroup
--    stpxRootGuardGroup
--   OptGroup
--    stpxRootInconsistencyNotificationsGroup
--   OptGroup
--    stpx4kVlanGroup
--   OptGroup
--    stpxSpanningTreeGroup
--   OptGroup
--    stpxMISTPGroup
--   OptGroup
--    stpxLongPathCostModeGroup
--   OptGroup
--    stpxPVSTVlanGroup
--   OptGroup
--    stpxMISTPGroup2
--   OptGroup
--    stpxLoopGuardGroup
--   OptGroup
--    stpxLoopInconsistencyNotificationsGroup
--   OptGroup
--    stpxFastStartGroup

stpxMIBCompliance6 OBJECT IDENTIFIER ::= { stpxMIBCompliances 6 }
-- MODULE-COMPLIANCE
--  Status
--    deprecated
--  Descr
--    The compliance statement for entities which implement
--    Cisco STP Extensions MIB.
--  Module
--    >>current<<
--   OptGroup
--    stpxUplinkGroup
--   OptGroup
--    stpxSstpGroup
--   OptGroup
--    stpxPreferredVlansGroup
--   OptGroup
--    stpxNotificationsGroup
--   OptGroup
--    stpxBackboneGroup
--   OptGroup
--    stpxRootGuardGroup
--   OptGroup
--    stpxRootInconsistencyNotificationsGroup
--   OptGroup
--    stpx4kVlanGroup
--   OptGroup
--    stpxSpanningTreeGroup
--   OptGroup
--    stpxMISTPGroup
--   OptGroup
--    stpxLongPathCostModeGroup
--   OptGroup
--    stpxPVSTVlanGroup
--   OptGroup
--    stpxMISTPGroup2
--   OptGroup
--    stpxLoopInconsistencyNotificationsGroup
--   OptGroup
--    stpxBpduSkewingGroup
--   OptGroup
--    stpxFastStartGroup2
--   OptGroup
--    stpxLoopGuardGroup2
--   OptGroup
--    stpxMSTGroup
--   OptGroup
--    stpxPreferredMSTInstancesGroup

stpxMIBCompliance7 OBJECT IDENTIFIER ::= { stpxMIBCompliances 7 }
-- MODULE-COMPLIANCE
--  Status
--    deprecated
--  Descr
--    The compliance statement for entities which implement
--    Cisco STP Extensions MIB.
--  Module
--    >>current<<
--   OptGroup
--    stpxUplinkGroup
--   OptGroup
--    stpxSstpGroup
--   OptGroup
--    stpxPreferredVlansGroup
--   OptGroup
--    stpxNotificationsGroup
--   OptGroup
--    stpxBackboneGroup
--   OptGroup
--    stpxRootGuardGroup
--   OptGroup
--    stpxRootInconsistencyNotificationsGroup
--   OptGroup
--    stpx4kVlanGroup
--   OptGroup
--    stpxSpanningTreeGroup
--   OptGroup
--    stpxMISTPGroup
--   OptGroup
--    stpxLongPathCostModeGroup
--   OptGroup
--    stpxPVSTVlanGroup
--   OptGroup
--    stpxMISTPGroup2
--   OptGroup
--    stpxLoopInconsistencyNotificationsGroup
--   OptGroup
--    stpxBpduSkewingGroup
--   OptGroup
--    stpxFastStartGroup2
--   OptGroup
--    stpxLoopGuardGroup2
--   OptGroup
--    stpxPreferredMSTInstancesGroup
--   OptGroup
--    stpxFastStartGroup3
--   OptGroup
--    stpxUplinkGroup2
--   OptGroup
--    stpxBackboneGroup2
--   OptGroup
--    stpxMSTGroup2
--   OptGroup
--    stpxRSTPGroup
--   OptGroup
--    stpxRPVSTGroup

stpxMIBCompliance8 OBJECT IDENTIFIER ::= { stpxMIBCompliances 8 }
-- MODULE-COMPLIANCE
--  Status
--    deprecated
--  Descr
--    The compliance statement for entities which implement
--    Cisco STP Extensions MIB.
--  Module
--    >>current<<
--   OptGroup
--    stpxUplinkGroup
--   OptGroup
--    stpxSstpGroup
--   OptGroup
--    stpxPreferredVlansGroup
--   OptGroup
--    stpxNotificationsGroup
--   OptGroup
--    stpxBackboneGroup
--   OptGroup
--    stpxRootGuardGroup
--   OptGroup
--    stpxRootInconsistencyNotificationsGroup
--   OptGroup
--    stpx4kVlanGroup
--   OptGroup
--    stpxSpanningTreeGroup
--   OptGroup
--    stpxMISTPGroup
--   OptGroup
--    stpxLongPathCostModeGroup
--   OptGroup
--    stpxPVSTVlanGroup
--   OptGroup
--    stpxMISTPGroup2
--   OptGroup
--    stpxLoopInconsistencyNotificationsGroup
--   OptGroup
--    stpxBpduSkewingGroup
--   OptGroup
--    stpxFastStartGroup2
--   OptGroup
--    stpxLoopGuardGroup2
--   OptGroup
--    stpxPreferredMSTInstancesGroup
--   OptGroup
--    stpxFastStartGroup3
--   OptGroup
--    stpxUplinkGroup2
--   OptGroup
--    stpxBackboneGroup2
--   OptGroup
--    stpxMSTGroup2
--   OptGroup
--    stpxRSTPGroup
--   OptGroup
--    stpxRPVSTGroup
--   OptGroup
--    stpxExtendedSysIDGroup
--   OptGroup
--    stpxNotificationEnableGroup
--   OptGroup
--    stpxFastStartOperModeGroup

stpxMIBCompliance9 OBJECT IDENTIFIER ::= { stpxMIBCompliances 9 }
-- MODULE-COMPLIANCE
--  Status
--    deprecated
--  Descr
--    The compliance statement for entities which implement
--    Cisco STP Extensions MIB.
--  Module
--    >>current<<
--   OptGroup
--    stpxUplinkGroup
--   OptGroup
--    stpxSstpGroup
--   OptGroup
--    stpxPreferredVlansGroup
--   OptGroup
--    stpxNotificationsGroup
--   OptGroup
--    stpxBackboneGroup
--   OptGroup
--    stpxRootGuardGroup
--   OptGroup
--    stpxRootInconsistencyNotificationsGroup
--   OptGroup
--    stpx4kVlanGroup
--   OptGroup
--    stpxSpanningTreeGroup
--   OptGroup
--    stpxMISTPGroup
--   OptGroup
--    stpxLongPathCostModeGroup
--   OptGroup
--    stpxPVSTVlanGroup
--   OptGroup
--    stpxMISTPGroup2
--   OptGroup
--    stpxLoopInconsistencyNotificationsGroup
--   OptGroup
--    stpxBpduSkewingGroup
--   OptGroup
--    stpxFastStartGroup2
--   OptGroup
--    stpxLoopGuardGroup2
--   OptGroup
--    stpxFastStartGroup3
--   OptGroup
--    stpxUplinkGroup2
--   OptGroup
--    stpxBackboneGroup2
--   OptGroup
--    stpxRSTPGroup
--   OptGroup
--    stpxRPVSTGroup
--   OptGroup
--    stpxExtendedSysIDGroup
--   OptGroup
--    stpxNotificationEnableGroup
--   OptGroup
--    stpxFastStartOperModeGroup
--   OptGroup
--    stpxMSTGroup3
--   OptGroup
--    stpxSMSTGroup
--   OptGroup
--    stpxSMSTInstanceGroup
--   OptGroup
--    stpxSMSTInstanceEditGroup
--   OptGroup
--    stpxSMSTPortStatusGroup
--   OptGroup
--    stpxSMSTPortHelloTimeGroup

stpxMIBCompliance10 OBJECT IDENTIFIER ::= { stpxMIBCompliances 10 }
-- MODULE-COMPLIANCE
--  Status
--    deprecated
--  Descr
--    The compliance statement for entities which implement
--    Cisco STP Extensions MIB.
--  Module
--    >>current<<
--   OptGroup
--    stpxUplinkGroup
--   OptGroup
--    stpxSstpGroup
--   OptGroup
--    stpxPreferredVlansGroup
--   OptGroup
--    stpxNotificationsGroup
--   OptGroup
--    stpxBackboneGroup
--   OptGroup
--    stpxRootGuardGroup
--   OptGroup
--    stpxRootInconsistencyNotificationsGroup
--   OptGroup
--    stpx4kVlanGroup
--   OptGroup
--    stpxSpanningTreeGroup
--   OptGroup
--    stpxMISTPGroup
--   OptGroup
--    stpxLongPathCostModeGroup
--   OptGroup
--    stpxPVSTVlanGroup
--   OptGroup
--    stpxMISTPGroup2
--   OptGroup
--    stpxLoopInconsistencyNotificationsGroup
--   OptGroup
--    stpxBpduSkewingGroup
--   OptGroup
--    stpxFastStartGroup2
--   OptGroup
--    stpxLoopGuardGroup2
--   OptGroup
--    stpxFastStartGroup3
--   OptGroup
--    stpxUplinkGroup2
--   OptGroup
--    stpxBackboneGroup2
--   OptGroup
--    stpxRSTPGroup
--   OptGroup
--    stpxRPVSTGroup
--   OptGroup
--    stpxExtendedSysIDGroup
--   OptGroup
--    stpxNotificationEnableGroup
--   OptGroup
--    stpxFastStartOperModeGroup
--   OptGroup
--    stpxMSTGroup3
--   OptGroup
--    stpxSMSTGroup
--   OptGroup
--    stpxSMSTInstanceGroup
--   OptGroup
--    stpxSMSTInstanceEditGroup
--   OptGroup
--    stpxSMSTPortStatusGroup
--   OptGroup
--    stpxSMSTPortHelloTimeGroup
--   OptGroup
--    stpxSMSTInstanceCISTGroup

stpxMIBCompliance11 OBJECT IDENTIFIER ::= { stpxMIBCompliances 11 }
-- MODULE-COMPLIANCE
--  Status
--    deprecated
--  Descr
--    The compliance statement for entities which implement
--    Cisco STP Extensions MIB.
--  Module
--    >>current<<
--   OptGroup
--    stpxUplinkGroup
--   OptGroup
--    stpxSstpGroup
--   OptGroup
--    stpxPreferredVlansGroup
--   OptGroup
--    stpxNotificationsGroup
--   OptGroup
--    stpxBackboneGroup
--   OptGroup
--    stpxRootGuardGroup
--   OptGroup
--    stpxRootInconsistencyNotificationsGroup
--   OptGroup
--    stpx4kVlanGroup
--   OptGroup
--    stpxSpanningTreeGroup
--   OptGroup
--    stpxMISTPGroup
--   OptGroup
--    stpxLongPathCostModeGroup
--   OptGroup
--    stpxPVSTVlanGroup
--   OptGroup
--    stpxMISTPGroup2
--   OptGroup
--    stpxLoopInconsistencyNotificationsGroup
--   OptGroup
--    stpxBpduSkewingGroup
--   OptGroup
--    stpxFastStartGroup2
--   OptGroup
--    stpxLoopGuardGroup2
--   OptGroup
--    stpxFastStartGroup3
--   OptGroup
--    stpxUplinkGroup2
--   OptGroup
--    stpxBackboneGroup2
--   OptGroup
--    stpxRSTPGroup
--   OptGroup
--    stpxRPVSTGroup
--   OptGroup
--    stpxExtendedSysIDGroup
--   OptGroup
--    stpxNotificationEnableGroup
--   OptGroup
--    stpxFastStartOperModeGroup
--   OptGroup
--    stpxMSTGroup3
--   OptGroup
--    stpxSMSTGroup
--   OptGroup
--    stpxSMSTInstanceGroup
--   OptGroup
--    stpxSMSTInstanceEditGroup
--   OptGroup
--    stpxSMSTPortStatusGroup
--   OptGroup
--    stpxSMSTPortHelloTimeGroup
--   OptGroup
--    stpxSMSTInstanceCISTGroup
--   OptGroup
--    stpxPathCostOperModeGroup

stpxMIBCompliance12 OBJECT IDENTIFIER ::= { stpxMIBCompliances 12 }
-- MODULE-COMPLIANCE
--  Status
--    mandatory
--  Descr
--    The compliance statement for entities which implement
--    Cisco STP Extensions MIB.
--  Module
--    >>current<<
--   OptGroup
--    stpxUplinkGroup
--   OptGroup
--    stpxSstpGroup
--   OptGroup
--    stpxPreferredVlansGroup
--   OptGroup
--    stpxNotificationsGroup
--   OptGroup
--    stpxBackboneGroup
--   OptGroup
--    stpxRootGuardGroup
--   OptGroup
--    stpxRootInconsistencyNotificationsGroup
--   OptGroup
--    stpx4kVlanGroup
--   OptGroup
--    stpxSpanningTreeGroup
--   OptGroup
--    stpxMISTPGroup
--   OptGroup
--    stpxLongPathCostModeGroup
--   OptGroup
--    stpxPVSTVlanGroup
--   OptGroup
--    stpxMISTPGroup2
--   OptGroup
--    stpxLoopInconsistencyNotificationsGroup
--   OptGroup
--    stpxBpduSkewingGroup
--   OptGroup
--    stpxFastStartGroup2
--   OptGroup
--    stpxLoopGuardGroup2
--   OptGroup
--    stpxFastStartGroup3
--   OptGroup
--    stpxUplinkGroup2
--   OptGroup
--    stpxBackboneGroup2
--   OptGroup
--    stpxRSTPGroup
--   OptGroup
--    stpxRSTPTransmitHoldCountGroup
--   OptGroup
--    stpxRPVSTGroup
--   OptGroup
--    stpxExtendedSysIDGroup
--   OptGroup
--    stpxNotificationEnableGroup
--   OptGroup
--    stpxFastStartOperModeGroup
--   OptGroup
--    stpxMSTGroup4
--   OptGroup
--    stpxSMSTGroup
--   OptGroup
--    stpxSMSTMaxHopCountGroup
--   OptGroup
--    stpxSMSTInstanceGroup
--   OptGroup
--    stpxSMSTInstanceEditGroup
--   OptGroup
--    stpxSMSTPortStatusGroup
--   OptGroup
--    stpxSMSTPortHelloTimeGroup
--   OptGroup
--    stpxSMSTInstanceCISTGroup
--   OptGroup
--    stpxPathCostOperModeGroup
--   OptGroup
--    stpxSMSTPortMSTModeGroup
--   OptGroup
--    stpxSMSTConfigDigestGroup


END
