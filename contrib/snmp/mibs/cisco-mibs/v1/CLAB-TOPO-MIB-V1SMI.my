-- MIB file created 10-Apr-2009 13:22:37, by
--   SMICng version 2.2.11-beta(PRO)(Solaris), January 20, 2001. Enterprise key cisco.com

CLAB-TOPO-MIB DEFINITIONS ::= BEGIN

-- From file: "CLAB-TOPO-MIB.my"
-- Compile options "4 7 F H N O W 03 06 0B 0G 0N 0T"

IMPORTS
    RowStatus
            FROM SNMPv2-TC-v1
    SnmpAdminString
            FROM SNMP-FRAMEWORK-MIB
    InterfaceIndex
            FROM IF-MIB
    clabCommonMibs
            FROM CLAB-DEF-MIB
    OBJECT-TYPE
            FROM RFC-1212;

clabTopoMib OBJECT IDENTIFIER ::= { clabCommonMibs 2 }
-- MODULE-IDENTITY
--  LastUpdated
--    200612071700Z
--  OrgName
--    Cable Television Laboratories, Inc.
--  ContactInfo
--    
--    Postal: Cable Television Laboratories, Inc.
--    858 Coal Creek Circle
--    Louisville, Colorado 80027-9750
--    U.S.A.
--    Phone: +1 303-661-9100
--    Fax: +1 303-661-9199
--    E-mail: mibs@cablelabs.com
--  Descr
--    This MIB module contains the management objects for the
--    management of fiber nodes in the Cable plant.
--  RevDate
--    200612071700Z
--  RevDescr
--    Initial version, published as part of the CableLabs
--    OSSIv3.0 specification CM-SP-OSSIv3.0-I01-061207
--    Copyright 1999-2006 Cable Television Laboratories, Inc.
--    All rights reserved.

clabTopoMibObjects OBJECT IDENTIFIER ::= { clabTopoMib 1 }
clabTopoMibConformance OBJECT IDENTIFIER ::= { clabTopoMib 2 }
clabTopoMibCompliances OBJECT IDENTIFIER ::= { clabTopoMibConformance 1 }
clabTopoMibGroups OBJECT IDENTIFIER ::= { clabTopoMibConformance 2 }

NodeName ::= OCTET STRING(SIZE(0..16))
-- TEXTUAL-CONVENTION
--  Status
--    mandatory
--  Descr
--    This data type is a human readable string that represents
--    the name of a fiber node. Internationalization is supported
--    by conforming to the SNMP textual convention SnmpAdminString.
--  Refer
--    RFC 3411.

clabTopoFiberNodeCfgTable OBJECT-TYPE
    SYNTAX SEQUENCE OF ClabTopoFiberNodeCfgEntry
    ACCESS not-accessible
    STATUS mandatory
    DESCRIPTION
        "This object defines the cable HFC plant Fiber Nodes
        known at a CMTS.
        This object supports the creation and deletion of multiple
        instances."
    ::= { clabTopoMibObjects 1 }

clabTopoFiberNodeCfgEntry OBJECT-TYPE
    SYNTAX ClabTopoFiberNodeCfgEntry
    ACCESS not-accessible
    STATUS mandatory
    DESCRIPTION
        "The conceptual row of clabTopoFiberNodeCfg.
        The CMTS persists all instances of FiberNodeCfg
        across reinitializations."
    INDEX { clabTopoFiberNodeCfgNodeName }
    ::= { clabTopoFiberNodeCfgTable 1 }

ClabTopoFiberNodeCfgEntry ::= SEQUENCE {
    clabTopoFiberNodeCfgNodeName NodeName,
    clabTopoFiberNodeCfgNodeDescr SnmpAdminString,
    clabTopoFiberNodeCfgRowStatus RowStatus
    }

clabTopoFiberNodeCfgNodeName OBJECT-TYPE
    SYNTAX NodeName(SIZE(1..16))
--    Rsyntax OCTET STRING(SIZE(1..16))
    ACCESS not-accessible
    STATUS mandatory
    DESCRIPTION
        "This key represents a human-readable name for a fiber
        node."
    REFERENCE
        "DOCSIS 3.0 MAC and Upper Layer Protocols Interface
        Specification CM-SP-MULPIv3.0-I01-060804, RF Topology 
        Configuration section."
    ::= { clabTopoFiberNodeCfgEntry 1 }

clabTopoFiberNodeCfgNodeDescr OBJECT-TYPE
    SYNTAX SnmpAdminString
--    Rsyntax OCTET STRING(SIZE(0..255))
    ACCESS read-write
    STATUS mandatory
    DESCRIPTION
        "Administratively configured human-readable description
        of the fiber node"
    DEFVAL { ''H }
    ::= { clabTopoFiberNodeCfgEntry 2 }

clabTopoFiberNodeCfgRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this instance."
    ::= { clabTopoFiberNodeCfgEntry 3 }

clabTopoChFnCfgTable OBJECT-TYPE
    SYNTAX SEQUENCE OF ClabTopoChFnCfgEntry
    ACCESS not-accessible
    STATUS mandatory
    DESCRIPTION
        "This object defines the RF topology by defining the
        connectivity of a CMTS's downstream and upstream channels
        to the fiber nodes. Each instance of this object
        describes connectivity of one downstream or upstream
        channel with a single fiber node.
        This object supports the creation and deletion of multiple
        instances."
    ::= { clabTopoMibObjects 2 }

clabTopoChFnCfgEntry OBJECT-TYPE
    SYNTAX ClabTopoChFnCfgEntry
    ACCESS not-accessible
    STATUS mandatory
    DESCRIPTION
        "The conceptual row of clabTopoChFnCfg.
        The CMTS persists all instances of ChFnCfg
        across reinitializations."
    INDEX { clabTopoFiberNodeCfgNodeName, clabTopoChFnCfgChIfIndex }
    ::= { clabTopoChFnCfgTable 1 }

ClabTopoChFnCfgEntry ::= SEQUENCE {
    clabTopoChFnCfgChIfIndex InterfaceIndex,
    clabTopoChFnCfgRowStatus RowStatus
    }

clabTopoChFnCfgChIfIndex OBJECT-TYPE
    SYNTAX InterfaceIndex
--    Rsyntax INTEGER(1..2147483647)
    ACCESS not-accessible
    STATUS mandatory
    DESCRIPTION
        "This key represents the interface index of an upstream
        or downstream channel associated with this fiber
        node. In the upstream direction, only ifIndices
        docsCableUpstream channels are reflected."
    ::= { clabTopoChFnCfgEntry 1 }

clabTopoChFnCfgRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this instance."
    ::= { clabTopoChFnCfgEntry 2 }

clabTopoGroup OBJECT IDENTIFIER ::= { clabTopoMibGroups 1 }
-- OBJECT-GROUP
--  Status
--    mandatory
--  Descr
--    Group of objects implemented in the CMTS.
--  objects
--    clabTopoFiberNodeCfgNodeDescr, clabTopoFiberNodeCfgRowStatus, 
--    clabTopoChFnCfgRowStatus

clabTopoCompliance OBJECT IDENTIFIER ::= { clabTopoMibCompliances 1 }
-- MODULE-COMPLIANCE
--  Status
--    mandatory
--  Descr
--    The compliance statement for devices that implement the
--    CableLabs Topology MIB.
--  Module
--    >>current<<
--   MandGroup
--    clabTopoGroup


END
