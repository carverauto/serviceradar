module viptela-security {
  namespace "http://viptela.com/security";
  prefix viptela-security;

  import ietf-inet-types {
    prefix inet;
  }
  import ietf-yang-types {
    prefix yang;
  }
  import viptela-common {
    prefix viptela;
  }
    prefix tailf;
  }
  import viptela-system {
    prefix viptela-system;
  }

  organization "Viptela, Inc.";
  contact
    "Viptela, Inc.
     Email:support@viptela.com";
  description
    "This module defines data model for Viptela security management";

  revision 2019-08-15 {
    description
      "Release version: 19.2";
  }
  revision 2018-11-01 {
    description
      "Release version: 18.4";
  }
  revision 2018-08-20 {
    description
      "Release version: 18.3.1";
  }
  revision 2018-06-25 {
    description
      "Release version: 18.3";
  }
  revision 2018-04-25 {
    description
      "Release version: 18.2";
  }
  revision 2018-03-15 {
    description
      "Release version: 18.1.1";
  }
  revision 2018-01-16 {
    description
      "Release version: 17.2.3";
  }
  revision 2017-11-01 {
    description
      "Release version: 17.2.1";
  }
  revision 2017-08-01 {
    description
      "Release version: 17.2";
  }
  revision 2017-05-25 {
    description
      "Release version: 17.1.1";
  }
  revision 2017-04-06 {
    description
      "Release version: 17.1";
  }
  revision 2017-02-15 {
    description
      "Release version: 16.3.2";
  }
  revision 2017-02-06 {
    description
      "Release version: 16.3.1";
  }
  revision 2016-11-16 {
    description
      "Release version: 16.3";
  }
  revision 2016-10-25 {
    description
      "Release version: 16.2.10";
  }
  revision 2016-10-24 {
    description
      "Release version: 16.2.4";
  }
  revision 2016-08-10 {
    description
      "Release version: 16.2.2";
  }
  revision 2016-08-01 {
    description
      "Release version: 16.2.1";
  }
  revision 2016-06-09 {
    description
      "Release version: 16.2";
  }
  revision 2016-04-22 {
    description
      "Release version: 16.1.1";
  }
  revision 2016-03-15 {
    description
      "Release version: 16.1";
  }
  revision 2016-01-30 {
    description
      "Release version: 15.4.3";
  }
  revision 2015-12-28 {
    description
      "Release version: 15.4.1";
  }
  revision 2015-12-01 {
    description
      "Release version: 15.4.0";
  }
  revision 2015-10-31 {
    description
      "Release version: 15.3.5";
  }
  revision 2015-09-27 {
    description
      "Release version: 15.3.3";
  }
  revision 2015-09-01 {
    description
      "Release version: 15.3.1";
  }
  revision 2015-07-01 {
    description
      "Release version: 15.3";
  }
  revision 2015-06-01 {
    description
      "Release version: 15.2.8";
  }
  revision 2015-05-01 {
    description
      "Release version: 15.2";
  }
  revision 2015-02-01 {
    description
      "Release version: 15.1";
  }
  revision 2014-12-01 {
    description
      "Release version: 14.3";
  }
  revision 2014-07-01 {
    description
      "Release version: 14.2";
  }
  revision 2013-02-12 {
    description
      "Initial revision";
  }

  typedef session-state {
    description "Session state";
    type enumeration {
      enum "down";
      enum "connect";
      enum "handshake";
      enum "trying";
      enum "challenge";
      enum "challenge_resp";
      enum "challenge_ack";
      enum "up";
      enum "tear_down";
    }
  }

  typedef state-enum {
    description "State";
    type enumeration {
      enum "unknown";
      enum "up";
      enum "down";
    }
  }

  typedef authentication-enum {
    type enumeration {
      enum "none" {
        value 0;
      }
      enum "sha1-hmac" {
        value 3;
      }
      enum "ah-sha1-hmac" {
        value 4;
      }
      enum "ah-no-id" {
        value 5;
      }
    }
  }

  typedef conn-flag-enum {
    description "Connection error flags";
    type enumeration {
      enum "NOERR";
      enum "ACSRREJ";
      enum "STENTRY";
      enum "HSFAIL";
      enum "DCERTFL";
      enum "NLCERT";
      enum "LISFD";
      enum "SNOCHECK";
      enum "IP_TOS";
      enum "TMRALC";
      enum "DCONFAIL";
      enum "WRKRTO";
      enum "VS_TMO";
      enum "VB_TMO";
      enum "VM_TMO";
      enum "VP_TMO";
      enum "DISTLOC";
      enum "RMGSPR";
      enum "PRCHAL";
      enum "SYSPRCH";
      enum "RECLEN0";
      enum "TXCHTOBD";
      enum "RDSIGFBD";
      enum "SSLNFAIL";
      enum "DHSTMO";
      enum "NOVS";
      enum "NOACTVB";
      enum "ORPTMO";
      enum "DEVALC";
      enum "TUNALC";
      enum "CRTREJSER";
      enum "VBDEST";
      enum "CRTREV";
      enum "RXTRDWN";
      enum "XTVSTRDN";
      enum "NOSLPRCRT";
      enum "DUPSER";
      enum "SERNTPRES";
      enum "CRTVERFL";
      enum "BIDNTPR";
      enum "BIDNTVRFD";
      enum "BDSGVERFL";
      enum "MEMALCFL";
      enum "UNMSGBDRG";
      enum "VSCRTREV";
      enum "VECRTREV";
      enum "UNAUTHEL";
      enum "DISCVBD";
      enum "CTORGNMMIS";
      enum "NOZTPEN";
      enum "NOVMCFG";
      enum "CHVERFAIL";
      enum "DUPCLHELO";
      enum "CERTEXPRD";
      enum "SYSIPCHNG";
      enum "XTVMTRDN";
      enum "MGRTBLCKD";
      enum "NONCGN";
      enum "XTMOS";
      enum "IPTMISS";
      enum "OPERDOWN";
      enum "NTPRVMINT";
      enum "STNMODETD";
      enum "LRNTPEER";
      enum "CGNIDCHNGD";
      enum "DUPSYSIPDEL";
      enum "BIDSIG";
      enum "IDREQDECFAIL";
      enum "VEYIDBNDFAIL";
      enum "CREDFAIL";
      enum "RECCABLOBFAIL";
      enum "EMBARGOFAIL";
      enum "NEWVBNOVMNG";
      enum "HWCERTREN";
      enum "HWCERTREV";
    }
  }

  container security {
    description "Security information";
    when "/viptela-system:system/viptela-system:personality != 'vcontainer'";
    container ipsec {
      description "Configure IPsec parameters";
      when "/viptela-system:system/viptela-system:personality = 'vedge'";
      must
        "(replay-window = 64)   or (replay-window = 128)  or (replay-window = 256)  or 
         (replay-window = 512)  or (replay-window = 1024) or (replay-window = 2048) or 
         (replay-window = 4096) or (replay-window = 8192)" {
        error-message "Invalid replay-window (Should be power of 2 Range 64..4096)";
      }
      leaf rekey {
        description "Time interval between rekeying";
        type uint32 {
          description "10..1209600 seconds";
          range "10..1209600";
        }
        default "86400";
      }
      leaf replay-window {
        description "Replay window size";
        type uint32 {
          description "64..4096 (must be a power of 2)";
        }
        default "512";
      }
      leaf-list authentication-type {
        description "List of authentication types";
        ordered-by user;
        type authentication-enum;
      }
      leaf pairwise-keying {
        description "Enable IPsec pairwise-keying";
        type boolean;
      }
    }
    container control {
      description "Configure control related properties";
      when
        "(/viptela-system:system/viptela-system:personality = 'vsmart') or
         (/viptela-system:system/viptela-system:personality = 'vmanage')";
      leaf protocol {
        description "DTLS or TLS";
        type viptela:control-protocol-enum;
        default "dtls";
      }
      leaf tls-port {
        when "(../protocol != 'dtls')";
        description "Control TLS port";
        type uint32 {
          description "1025..65535";
          range "1025..65535";
        }
        default "23456";
      }
    }
    container umbrella {
      description "Configure Umbrella service related security properties";
      presence "Is umbrella redirection enabled";
      when "/viptela-system:system/viptela-system:personality = 'vedge'";
      leaf token {
        description "Umbrella service registration token";
        type string {
          length "1..64";
        }
      }
      leaf dnscrypt {
        description "Enable DNScrypt while redirecting DNS requests to Umbrella";
        type boolean;
        default "true";
      }
    }
  }
  container control {
    description "Display control information";
    when "/viptela-system:system/viptela-system:personality != 'vcontainer'";
    container connections-info {
      description "Display configured control connection rate, in PPS";
      when "/viptela-system:system/viptela-system:personality = 'vedge'";
      config false;
      leaf rate {
        type string;
      }
    }
    list connections {
      description "Display control connections information";
      config false;
      key "instance peer-type site-id domain-id local-private-ip local-private-port public-ip public-port";
      leaf instance {
        description "vdaemon instance ID";
        type uint32;
      }
      leaf peer-type {
        description "Connection type";
        type viptela:personality-enum-oper;
      }
      leaf site-id {
        description "Site ID";
        type uint32;
      }
      leaf domain-id {
        description "Domain ID";
        type uint32;
      }
      leaf local-private-ip {
        description "Private IP address";
        type inet:ip-address;
      }
      leaf local-private-port {
        description "Private port number";
        type uint32;
      }
      leaf public-ip {
        description "Public IP address";
        type inet:ip-address;
      }
      leaf public-port {
        description "Public port number";
        type uint32;
      }
      leaf system-ip {
        description "System IP address";
        type inet:ip-address;
      }
      leaf protocol {
        description "Protocol";
        type viptela:control-protocol-enum;
      }
      leaf local-color {
        description "Local color";
        type viptela:color-enum;
      }
      leaf remote-color {
        description "Remote color";
        type viptela:color-enum;
      }
      leaf private-ip {
        description "Private IP address";
        type inet:ip-address;
      }
      leaf private-port {
        description "Private port";
        type uint32;
      }
      leaf state {
        description "State";
        type session-state;
      }
      leaf local_enum {
        description "Local error reason";
        type conn-flag-enum;
      }
      leaf remote_enum {
        description "Remote error reason";
        type conn-flag-enum;
      }
      leaf local-state-info {
        description "Local state information";
        type string;
      }
      leaf remote-state-info {
        description "Remote state information";
        type string;
      }
      leaf uptime {
        description "Uptime";
        type string;
      }
      leaf controller-group-id {
        description "Controller group ID";
        type uint16;
      }
      leaf tx_hello {
        description "Tx hello";
        type uint32;
      }
      leaf tx_connects {
        description "Tx connects";
        type uint32;
      }
      leaf tx_registers {
        description "Tx registers";
        type uint32;
      }
      leaf tx_register_replies {
        description "Tx register replies";
        type uint32;
      }
      leaf tx_challenge {
        description "Tx challenge";
        type uint32;
      }
      leaf tx_challenge_resp {
        description "Tx challenge response";
        type uint32;
      }
      leaf tx_challenge_ack {
        description "Tx challenge ack";
        type uint32;
      }
      leaf tx_teardown {
        description "Tx teardown";
        type uint32;
      }
      leaf tx_teardown_all {
        description "Tx teardown all connections";
        type uint32;
      }
      leaf tx_vm_to_peer {
        description "Tx vManage to peer";
        type uint32;
      }
      leaf tx_register_to_vm {
        description "Tx register to vManage";
        type uint32;
      }
      leaf rx_hello {
        description "Rx hello";
        type uint32;
      }
      leaf rx_connects {
        description "Rx connects";
        type uint32;
      }
      leaf rx_registers {
        description "Rx registers";
        type uint32;
      }
      leaf rx_register_replies {
        description "Rx register replies";
        type uint32;
      }
      leaf rx_challenge {
        description "Rx challenge";
        type uint32;
      }
      leaf rx_challenge_resp {
        description "Rx challenge response";
        type uint32;
      }
      leaf rx_challenge_ack {
        description "Rx challenge ack";
        type uint32;
      }
      leaf rx_teardown {
        description "Rx teardown";
        type uint32;
      }
      leaf rx_vm_to_peer {
        description "Rx vManage to peer";
        type uint32;
      }
      leaf rx_register_to_vm {
        description "Rx register to vManage";
        type uint32;
      }
      leaf negotiated_hello_interval {
        description "Negotiated hello interval";
        type uint32;
      }
      leaf negotiated_hello_tolerance {
        description "Negotiated hello tolerance";
        type uint32;
      }
      leaf cfg-system-ip {
        description "Configured System IP address";
        type inet:ip-address;
      }
      leaf v-org-name {
        description "Organization Name";
        type string;
      }
      leaf tx_create_cert {
        description "Tx create certificate to vManage";
        type uint32;
      }
      leaf rx_create_cert {
        description "Rx create certificate from vBond";
        type uint32;
      }
      leaf tx_create_cert_reply {
        description "Tx create certificate reply to vBond";
        type uint32;
      }
      leaf rx_create_cert_reply {
        description "Rx create certificate reply from vManage";
        type uint32;
      }
      leaf behind-proxy {
        description "Whether controller is behind proxy";
        type string;
      }
    }
    list connections-history {
      description "Display control connections history";
      config false;
      key "instance index";
      leaf instance {
        description "vdaemon instance ID";
        type uint32;
      }
      leaf index {
        description "History index";
        type uint32;
      }
      leaf peer-type {
        description "Connection type";
        type viptela:personality-enum-oper;
      }
      leaf site-id {
        description "Site ID";
        type viptela:site-id;
      }
      leaf domain-id {
        description "Domain ID";
        type uint32;
      }
      leaf private-ip {
        description "Private IP address";
        type inet:ip-address;
      }
      leaf private-port {
        description "Private port number";
        type uint32;
      }
      leaf public-ip {
        description "Public IP address";
        type inet:ip-address;
      }
      leaf public-port {
        description "Public port number";
        type uint32;
      }
      leaf system-ip {
        description "System IP address";
        type inet:ip-address;
      }
      leaf protocol {
        description "Protocol";
        type viptela:control-protocol-enum;
      }
      leaf local-color {
        description "Local color";
        type viptela:color-enum;
      }
      leaf remote-color {
        description "Remote color";
        type viptela:color-enum;
      }
      leaf state {
        description "State";
        type session-state;
      }
      leaf local_enum {
        description "Local error reason";
        type conn-flag-enum;
      }
      leaf remote_enum {
        description "Remote Error Reason";
        type conn-flag-enum;
      }
      leaf local-state-info {
        description "Local state information";
        type string;
      }
      leaf remote-state-info {
        description "Remote state information";
        type string;
      }
      leaf downtime {
        description "Downtime";
        type string;
      }
      leaf tx_hello {
        description "Tx hello";
        type uint32;
      }
      leaf tx_connects {
        description "Tx connects";
        type uint32;
      }
      leaf tx_registers {
        description "Tx registers";
        type uint32;
      }
      leaf tx_register_replies {
        description "Tx register replies";
        type uint32;
      }
      leaf tx_challenge {
        description "Tx challenge";
        type uint32;
      }
      leaf tx_challenge_resp {
        description "Tx challenge response";
        type uint32;
      }
      leaf tx_challenge_ack {
        description "Tx challenge ack";
        type uint32;
      }
      leaf tx_teardown {
        description "Tx teardown";
        type uint32;
      }
      leaf tx_teardown_all {
        description "Tx teardown all connections";
        type uint32;
      }
      leaf tx_vm_to_peer {
        description "Tx vManage to peer";
        type uint32;
      }
      leaf tx_register_to_vm {
        description "Tx register to vManage";
        type uint32;
      }
      leaf rx_hello {
        description "Rx hello";
        type uint32;
      }
      leaf rx_connects {
        description "Rx connects";
        type uint32;
      }
      leaf rx_registers {
        description "Rx registers";
        type uint32;
      }
      leaf rx_register_replies {
        description "Rx register replies";
        type uint32;
      }
      leaf rx_challenge {
        description "Rx challenge";
        type uint32;
      }
      leaf rx_challenge_resp {
        description "Rx challenge response";
        type uint32;
      }
      leaf rx_challenge_ack {
        description "Rx challenge ack";
        type uint32;
      }
      leaf rx_teardown {
        description "Rx teardown";
        type uint32;
      }
      leaf rx_vm_to_peer {
        description "Rx vManage to peer";
        type uint32;
      }
      leaf rx_register_to_vm {
        description "Rx register to vManage";
        type uint32;
      }
      leaf rep-count {
        description "Repeat count";
        type uint32;
      }
      leaf prev-downtime {
        description "Previous downtime";
        type string;
      }
      leaf cfg-system-ip {
        description "Configured System IP address";
        type inet:ip-address;
      }
      leaf vh-org-name {
        description "Organization Name";
        type string;
      }
      leaf uuid {
        description "Peer's unique device identifier";
        type string;
      }
      leaf tx_create_cert {
        description "Tx create certificate to vManage";
        type uint32;
      }
      leaf rx_create_cert {
        description "Rx create certificate from vBond";
        type uint32;
      }
      leaf tx_create_cert_reply {
        description "Tx create certificate reply to vBond";
        type uint32;
      }
      leaf rx_create_cert_reply {
        description "Rx create certificate reply from vManage";
        type uint32;
      }
    }
    container statistics {
      description "Display control statistics";
      config false;
      leaf tx_pkts {
        description "Tx packets";
        type yang:counter64;
      }
      leaf tx_octets {
        description "Tx octets";
        type uint32;
      }
      leaf tx_error {
        description "Tx error";
        type uint32;
      }
      leaf tx_blocked {
        description "Tx blocked";
        type uint32;
      }
      leaf tx_hello {
        description "Tx hello";
        type yang:counter64;
      }
      leaf tx_connects {
        description "Tx connects";
        type uint32;
      }
      leaf tx_registers {
        description "Tx registers";
        type uint32;
      }
      leaf tx_register_replies {
        description "Tx register replies";
        type uint32;
      }
      leaf tx_dtls_handshake {
        description "Tx DTLS handshake";
        type uint32;
      }
      leaf tx_dtls_handshake_failures {
        description "Tx DTLS handshake failures";
        type uint32;
      }
      leaf tx_dtls_handshake_done {
        description "Tx DTLS handshake done";
        type uint32;
      }
      leaf tx_challenge {
        description "Tx challenge";
        type uint32;
      }
      leaf tx_challenge_resp {
        description "Tx challenge response";
        type uint32;
      }
      leaf tx_challenge_ack {
        description "Tx challenge ack";
        type uint32;
      }
      leaf tx_challenge_error {
        description "Tx challenge error";
        type uint32;
      }
      leaf tx_challenge_resp_error {
        description "Tx challenge response error";
        type uint32;
      }
      leaf tx_challenge_ack_error {
        description "Tx challenge ack error";
        type uint32;
      }
      leaf tx_challenge_gen_error {
        description "Tx challenge general errors";
        type uint32;
      }
      leaf tx_vmanage_to_peer {
        description "Tx vManage to peer";
        type uint32;
      }
      leaf tx_register_to_vmanage {
        description "Tx register to vmanage";
        type uint32;
      }
      leaf rx_pkts {
        description "Rx packets";
        type yang:counter64;
      }
      leaf rx_octets {
        description "Rx octets";
        type uint32;
      }
      leaf rx_error {
        description "Rx error";
        type uint32;
      }
      leaf rx_hello {
        description "Rx hello";
        type yang:counter64;
      }
      leaf rx_connects {
        description "Rx connects";
        type uint32;
      }
      leaf rx_registers {
        description "Rx registers";
        type uint32;
      }
      leaf rx_register_replies {
        description "Rx register replies";
        type uint32;
      }
      leaf rx_dtls_handshake {
        description "Rx DTLS handshake";
        type uint32;
      }
      leaf rx_dtls_handshake_failures {
        description "Rx DTLS handshake failures";
        type uint32;
      }
      leaf rx_dtls_handshake_done {
        description "Rx DTLS handshake done";
        type uint32;
      }
      leaf rx_challenge {
        description "Rx challenge";
        type uint32;
      }
      leaf rx_challenge_resp {
        description "Rx challenge response";
        type uint32;
      }
      leaf rx_challenge_ack {
        description "Rx challenge ack";
        type uint32;
      }
      leaf challenge_failures {
        description "Challenge failures";
        type uint32;
      }
      leaf rx_vmanage_to_peer {
        description "Rx vManage to peer";
        type uint32;
      }
      leaf rx_register_to_vmanage {
        description "Rx register to vmanage";
        type uint32;
      }
      leaf bid_failures_needing_reset {
        description "Board ID reset count";
        type uint32;
      }
    }
    container local-properties {
      description "Display local control properties";
      config false;
      leaf device-type {
        description "Personality";
        type viptela:personality-enum-oper;
      }
      leaf organization-name {
        description "Organization name";
        type viptela:organization-name;
      }
      leaf certificate-status {
        description "Certificate status";
        type string;
      }
      leaf root-ca-chain-status {
        description "Root CA chain status";
        type string;
      }
      leaf certificate-validity {
        description "Certificate validity";
        type string;
      }
      leaf certificate-not-valid-before {
        description "Certificate not valid before";
        type string;
      }
      leaf certificate-not-valid-after {
        description "Certificate not valid after";
        type string;
      }
      leaf dns-name {
        description "DNS name";
        type string;
      }
      leaf site-id {
        description "Site ID";
        type viptela:site-id;
      }
      leaf domain-id {
        description "Domain ID";
        type uint32;
      }
      leaf protocol {
        description "Protocol";
        type viptela:control-protocol-enum;
      }
      leaf tls-port {
        description "TLS port";
        type uint32;
      }
      leaf system-ip {
        description "System IP address";
        type inet:ip-address;
      }
      leaf uuid {
        description "Unique device identifier";
        type string;
      }
      leaf board-serial {
        description "Board ID serial number";
        type viptela:serial-number;
      }
      leaf register-interval {
        description "Register interval - Deprecated in 15.4";
        type string;
        status deprecated;
      }
      leaf retry-interval {
        description "Retry interval";
        type string;
      }
      leaf no-activity {
        description "No activity expiry interval";
        type string;
      }
      leaf dns-cache-flush-interval {
        description "DNS cache time to live";
        type string;
      }
      leaf port-hopped {
        description "Device changed port";
        type string;
      }
      leaf time-since-port-hop {
        description "Time since last port hop";
        type string;
      }
      leaf max-controllers {
        description "Maximum number of controllers";
        type uint8;
        default "2";
      }
      leaf keygen-interval {
        description "Key generation interval";
        type string;
      }
      list ip-address-list {
        description "List of IP addresses";
        config false;
        key "index";
        leaf index {
          description "IP index";
          type uint32;
        }
        leaf ip {
          description "IP";
          type inet:ip-address;
        }
        leaf port {
          description "Port";
          type uint32;
        }
      }
      leaf number-vbond-peers {
        description "Number of vBond peers";
        type uint32;
      }
      list vbond-address-list {
        description "List of vBond peers";
        config false;
        key "index";
        leaf index {
          description "IP index";
          type uint32;
        }
        leaf ip {
          description "IP address";
          type inet:ip-address;
        }
        leaf port {
          description "Port";
          type uint32;
        }
      }
      leaf number-active-wan-interfaces {
        description "Number of WAN interfaces";
        type uint32;
      }
      list wan-interface-list {
        description "List of WAN interfaces";
        config false;
        key "instance index";
        leaf instance {
          description "vdaemon instance ID";
          type uint32;
        }
        leaf index {
          description "WAN index";
          type uint32;
        }
        leaf interface {
          description "Interface name";
          type viptela:named-type;
        }
        leaf public-ip {
          description "Public IP address";
          type inet:ip-address;
        }
        leaf public-port {
          description "Public port";
          type uint32;
        }
        leaf private-ip {
          description "Private IP";
          type inet:ip-address;
        }
        leaf private-port {
          description "Private port";
          type uint32;
        }
        leaf num-vsmarts {
          description "Number of vSmarts";
          type uint32;
        }
        leaf num-vmanages {
          description "Number of vManages";
          type uint32;
        }
        leaf weight {
          description "Weight";
          type uint32;
          when "/viptela-system:system/viptela-system:personality = 'vedge'";
        }
        leaf color {
          description "Color";
          type viptela:color-enum;
        }
        leaf carrier {
          description "Carrier";
          type viptela:carrier-enum;
        }
        leaf preference {
          description "Preference";
          type uint32;
          when "/viptela-system:system/viptela-system:personality = 'vedge'";
        }
        leaf admin-state {
          description "Administrative state";
          type state-enum;
        }
        leaf operation-state {
          description "Operational state";
          type state-enum;
        }
        leaf last-conn-time {
          description "Time since last connection";
          type string;
        }
        leaf restrict-str {
          description "Restrict";
          type string;
        }
        leaf control-str {
          description "Control connections required";
          type string;
        }
        leaf per-wan-max-controllers {
          description "Maximum number of controllers on this WAN interface";
          type uint8;
        }
        leaf private-ipv6 {
          description "Private IPv6 address";
          type inet:ip-address;
        }
        leaf spi-change {
          description "Time left until SPI change";
          type string;
        }
        leaf last-resort {
          description "Last-resort Interface";
          type string;
        }
        leaf wan-port-hopped {
          description "Interface changed port";
          type string;
        }
        leaf wan-time-since-port-hop {
          description "Time since last port hop";
          type string;
        }
        leaf vbond-as-stun-server {
          description "vbond as a stun server";
          type string;
        }
        leaf vmanage-connection-preference {
          description "Interface preference for control connection to vManage";
          type uint8;
        }
        leaf low-bandwidth-link {
          description "Low bandwith interface";
          type string;
        }
        leaf nat-type {
          description "NAT type";
          type string;
        }
      }
      leaf vedge-list-version {
        description "vEdge list version number";
        type yang:counter64;
      }
      leaf vsmart-list-version {
        description "vSmart list version number";
        type yang:counter64;
      }
      leaf sp-organization-name {
        description "SP Organization name";
        type viptela:organization-name;
      }
      leaf token {
        description "Token information";
        type viptela:serial-number;
      }
      leaf cloud-hosted {
        description "vManage is hosted in the Cisco cloud";
        type string;
      }
      leaf embargo-check {
        description "Embargo check status";
        type string;
      }
      leaf enterprise-serial {
        description "Enterprise certificate serial number";
        type viptela:serial-number;
      }
      leaf enterprise-certificate-status {
        description "Enterprise certificate status";
        type string;
      }
      leaf enterprise-certificate-validity {
        description "Enterprise certificate validity";
        type string;
      }
      leaf enterprise-certificate-not-valid-before {
        description "Enterprise certificate not valid before";
        type string;
      }
      leaf enterprise-certificate-not-valid-after {
        description "Enterprise certificate not valid after";
        type string;
      }
      leaf pairwise-keying {
        description "Pairwise keying enabled";
        type string;
      }
    }
    container affinity {
      description "Display control affinity";
      when "(/viptela-system:system/viptela-system:personality = 'vedge')";
      list config {
        description "Display control affinity configuration";
        config false;
        key "affc-index";
        leaf affc-index {
          description "WAN index";
          type uint32;
        }
        leaf affc-interface {
          description "Interface name";
          type viptela:named-type;
        }
        leaf affc-ervc {
          description "Effective required vSmart count";
          type uint32;
        }
        leaf affc-ecl {
          description "Effective controller group id list";
          type string;
        }
        leaf affc-ccl {
          description "Current controller group ID list";
          type string;
        }
        leaf affc-equil {
          description "Equilibrium";
          type string;
        }
        leaf affc-last-resort {
          description "Last-resort Interface";
          type string;
        }
      }
      list status {
        description "Display control affinity status";
        config false;
        key "affs-index";
        leaf affs-index {
          description "WAN index";
          type uint32;
        }
        leaf affs-interface {
          description "Interface name";
          type viptela:named-type;
        }
        leaf affs-acc {
          description "Assigned connected controllers";
          type string;
        }
        leaf affs-ucc {
          description "Unassigned connected controllers";
          type string;
        }
        leaf affs-ac {
          description "Assigned controllers";
          type string;
        }
      }
    }
    list valid-vsmarts {
      description "Display valid vSmarts";
      config false;
      key "serial-number org";
      leaf serial-number {
        description "Serial number of the device";
        type viptela:serial-number;
      }
      leaf org {
        description "Organization that the controller belongs to";
        type string;
      }
    }
    list valid-vedges {
      when
        "(/viptela-system:system/viptela-system:personality != 'vedge')or
         (/viptela-system:system/viptela-system:vbond/viptela-system:local)";
      description "Display valid vEdges";
      config false;
      key "chassis-number";
      leaf chassis-number {
        description "Chassis number of the device";
        type viptela:chassis-number;
      }
      leaf serial-number {
        description "Serial number of the device";
        type viptela:serial-number;
      }
      leaf validity {
        description "Device valid or staging";
        type viptela:validity-enum;
      }
      leaf org {
        description "Organization that the vedge belongs to";
        type string;
      }
      leaf hardware-installed-serial-number {
        description "Installed serial number of the device";
        type viptela:serial-number;
      }
    }
    list summary {
      description "Display control summary";
      config false;
      key "instance";
      leaf instance {
        description "vdaemon instance ID";
        type uint32;
      }
      leaf vbond_counts {
        type uint16;
      }
      leaf vmanage_counts {
        type uint16;
      }
      leaf vsmart_counts {
        type uint16;
      }
      leaf vedge_counts {
        type uint16;
        when "/viptela-system:system/viptela-system:personality != 'vedge'";
      }
      leaf protocol {
        type viptela:control-protocol-enum;
        when "/viptela-system:system/viptela-system:personality != 'vedge'";
      }
      leaf listening_ip {
        type inet:ip-address;
        when "/viptela-system:system/viptela-system:personality != 'vedge'";
      }
      leaf listening_ipv6 {
        type inet:ip-address;
        when "/viptela-system:system/viptela-system:personality != 'vedge'";
      }
      leaf listening_port {
        type inet:port-number;
        when "/viptela-system:system/viptela-system:personality != 'vedge'";
      }
    }
    list valid-vmanage-id {
      description "Display valid vManage certificate authority UUID";
      when "(/viptela-system:system/viptela-system:personality = 'vedge')";
      config false;
      key "chassis-number";
      leaf chassis-number {
        description "Chassis number of the device";
        type viptela:chassis-number;
      }
    }
  }
  container orchestrator {
    description "Display orchestrator information";
    when
      "(/viptela-system:system/viptela-system:vbond/viptela-system:local)
       and (/viptela-system:system/viptela-system:vbond/viptela-system:remote)";
    list connections {
      description "Display orchestrator connection information";
      config false;
      key "instance peer-type site-id domain-id local-private-ip local-private-port public-ip public-port";
      leaf instance {
        description "vdaemon instance ID";
        type uint32;
      }
      leaf peer-type {
        description "Connection type";
        type viptela:personality-enum-oper;
      }
      leaf site-id {
        description "Site ID";
        type viptela:site-id;
      }
      leaf domain-id {
        description "Domain ID";
        type uint32;
      }
      leaf protocol {
        description "Protocol";
        type viptela:control-protocol-enum;
      }
      leaf local-private-ip {
        description "Private IP address";
        type inet:ip-address;
      }
      leaf local-private-port {
        description "Private port number";
        type uint32;
      }
      leaf public-ip {
        description "Public IP address";
        type inet:ip-address;
      }
      leaf public-port {
        description "Public port number";
        type uint32;
      }
      leaf system-ip {
        description "System IP address";
        type inet:ip-address;
      }
      leaf local-color {
        description "Local color";
        type viptela:color-enum;
      }
      leaf remote-color {
        description "Remote color";
        type viptela:color-enum;
      }
      leaf private-ip {
        description "Private IP address";
        type inet:ip-address;
      }
      leaf private-port {
        description "Private port";
        type uint32;
      }
      leaf state {
        description "State";
        type session-state;
      }
      leaf local_enum {
        description "Local error reason";
        type conn-flag-enum;
      }
      leaf remote_enum {
        description "Remote error reason";
        type conn-flag-enum;
      }
      leaf local-state-info {
        description "Local state information";
        type string;
      }
      leaf remote-state-info {
        description "Remote state information";
        type string;
      }
      leaf uptime {
        description "Uptime";
        type string;
      }
      leaf tx_hello {
        description "Tx hello";
        type uint32;
      }
      leaf tx_connects {
        description "Tx connects";
        type uint32;
      }
      leaf tx_registers {
        description "Tx registers";
        type uint32;
      }
      leaf tx_register_replies {
        description "Tx register replies";
        type uint32;
      }
      leaf tx_challenge {
        description "Tx challenge";
        type uint32;
      }
      leaf tx_challenge_resp {
        description "Tx challenge response";
        type uint32;
      }
      leaf tx_challenge_ack {
        description "Tx challenge ack";
        type uint32;
      }
      leaf tx_teardown {
        description "Tx teardown";
        type uint32;
      }
      leaf tx_teardown_all {
        description "Tx teardown all connections";
        type uint32;
      }
      leaf tx_vm_to_peer {
        description "Tx vManage to peer";
        type uint32;
      }
      leaf tx_register_to_vm {
        description "Tx register to vManage";
        type uint32;
      }
      leaf rx_hello {
        description "Rx hello";
        type uint32;
      }
      leaf rx_connects {
        description "Rx connects";
        type uint32;
      }
      leaf rx_registers {
        description "Rx registers";
        type uint32;
      }
      leaf rx_register_replies {
        description "Rx register replies";
        type uint32;
      }
      leaf rx_challenge {
        description "Rx challenge";
        type uint32;
      }
      leaf rx_challenge_resp {
        description "Rx challenge response";
        type uint32;
      }
      leaf rx_challenge_ack {
        description "Rx challenge ack";
        type uint32;
      }
      leaf rx_teardown {
        description "Rx teardown";
        type uint32;
      }
      leaf rx_vm_to_peer {
        description "Rx vManage to peer";
        type uint32;
      }
      leaf rx_register_to_vm {
        description "Rx register to vManage";
        type uint32;
      }
      leaf negotiated_hello_interval {
        description "Negotiated hello interval";
        type uint32;
      }
      leaf negotiated_hello_tolerance {
        description "Negotiated hello tolerance";
        type uint32;
      }
      leaf orgname {
        description "Peer's organization name";
        type string;
      }
      leaf sporgname {
        description "Peer's SP organization name";
        type string;
      }
      leaf tx_create_cert {
        description "Tx create certificate to vManage";
        type uint32;
      }
      leaf rx_create_cert {
        description "Rx create certificate from vBond";
        type uint32;
      }
      leaf tx_create_cert_reply {
        description "Tx create certificate reply from vBond";
        type uint32;
      }
      leaf rx_create_cert_reply {
        description "Rx create certificate reply from vManage";
        type uint32;
      }
      leaf cloud-hosted {
        description "Controller hosted in Cisco cloud";
        type boolean;
      }
    }
    list connections-history {
      description "Display orchestrator connection history";
      config false;
      key "instance index";
      leaf instance {
        description "vdaemon instance ID";
        type uint32;
      }
      leaf index {
        description "History index";
        type uint32;
      }
      leaf peer-type {
        description "Connection type";
        type viptela:personality-enum-oper;
      }
      leaf site-id {
        description "Site ID";
        type viptela:site-id;
      }
      leaf domain-id {
        description "Domain ID";
        type uint32;
      }
      leaf protocol {
        description "Protocol";
        type viptela:control-protocol-enum;
      }
      leaf private-ip {
        description "Private IP address";
        type inet:ip-address;
      }
      leaf private-port {
        description "Private port number";
        type uint32;
      }
      leaf public-ip {
        description "Public IP address";
        type inet:ip-address;
      }
      leaf public-port {
        description "Public port number";
        type uint32;
      }
      leaf system-ip {
        description "System IP address";
        type inet:ip-address;
      }
      leaf local-color {
        description "Local color";
        type viptela:color-enum;
      }
      leaf remote-color {
        description "Remote color";
        type viptela:color-enum;
      }
      leaf state {
        description "State";
        type session-state;
      }
      leaf local_enum {
        description "Local error reason";
        type conn-flag-enum;
      }
      leaf remote_enum {
        description "Remote error reason";
        type conn-flag-enum;
      }
      leaf local-state-info {
        description "Local state information";
        type string;
      }
      leaf remote-state-info {
        description "Remote state information";
        type string;
      }
      leaf local-private-ip {
        description "Private IP address";
        type inet:ip-address;
      }
      leaf local-private-port {
        description "Private port";
        type uint32;
      }
      leaf downtime {
        description "Downtime";
        type string;
      }
      leaf tx_hello {
        description "Tx hello";
        type uint32;
      }
      leaf tx_connects {
        description "Tx connects";
        type uint32;
      }
      leaf tx_registers {
        description "Tx registers";
        type uint32;
      }
      leaf tx_register_replies {
        description "Tx register replies";
        type uint32;
      }
      leaf tx_challenge {
        description "Tx challenge";
        type uint32;
      }
      leaf tx_challenge_resp {
        description "Tx challenge response";
        type uint32;
      }
      leaf tx_challenge_ack {
        description "Tx challenge ack";
        type uint32;
      }
      leaf tx_teardown {
        description "Tx teardown";
        type uint32;
      }
      leaf tx_teardown_all {
        description "Tx teardown all connections";
        type uint32;
      }
      leaf tx_vm_to_peer {
        description "Tx vManage to peer";
        type uint32;
      }
      leaf tx_register_to_vm {
        description "Tx register to vManage";
        type uint32;
      }
      leaf rx_hello {
        description "Rx hello";
        type uint32;
      }
      leaf rx_connects {
        description "Rx connects";
        type uint32;
      }
      leaf rx_registers {
        description "Rx registers";
        type uint32;
      }
      leaf rx_register_replies {
        description "Rx register replies";
        type uint32;
      }
      leaf rx_challenge {
        description "Rx challenge";
        type uint32;
      }
      leaf rx_challenge_resp {
        description "Rx challenge response";
        type uint32;
      }
      leaf rx_challenge_ack {
        description "Rx challenge ack";
        type uint32;
      }
      leaf rx_teardown {
        description "Rx teardown";
        type uint32;
      }
      leaf rx_vm_to_peer {
        description "Rx vManage to peer";
        type uint32;
      }
      leaf rx_register_to_vm {
        description "Rx register to vManage";
        type uint32;
      }
      leaf rep-count {
        description "Repeat count";
        type uint32;
      }
      leaf prev-downtime {
        description "Previous downtime";
        type string;
      }
      leaf h-orgname {
        description "Peer's organization name";
        type string;
      }
      leaf h-sporgname {
        description "Peer's SP organization name";
        type string;
      }
      leaf uuid {
        description "Peer's unique device identifier";
        type string;
      }
      leaf tx_create_cert {
        description "Tx create certificate to vManage";
        type uint32;
      }
      leaf rx_create_cert {
        description "Rx create certificate from vBond";
        type uint32;
      }
      leaf tx_create_cert_reply {
        description "Tx create certificate reply to vBond";
        type uint32;
      }
      leaf rx_create_cert_reply {
        description "Rx create certificate reply from vManage";
        type uint32;
      }
    }
    container statistics {
      description "Display orchestrator statistics";
      config false;
      leaf tx_pkts {
        description "Tx packets";
        type uint64;
      }
      leaf tx_octets {
        description "Tx octets";
        type uint32;
      }
      leaf tx_error {
        description "Tx error";
        type uint32;
      }
      leaf tx_blocked {
        description "Tx blocked";
        type uint32;
      }
      leaf tx_connects {
        description "Tx connects";
        type uint32;
      }
      leaf tx_registers {
        description "Tx registers";
        type uint32;
      }
      leaf tx_register_replies {
        description "Tx register replies";
        type uint32;
      }
      leaf tx_dtls_handshake {
        description "Tx DTLS handshake";
        type uint32;
      }
      leaf tx_dtls_handshake_failures {
        description "Tx DTLS handshake failures";
        type uint32;
      }
      leaf tx_dtls_handshake_done {
        description "Tx DTLS handshake done";
        type uint32;
      }
      leaf tx_challenge {
        description "Tx challenge";
        type uint32;
      }
      leaf tx_challenge_resp {
        description "Tx challenge response";
        type uint32;
      }
      leaf tx_challenge_ack {
        description "Tx challenge ack";
        type uint32;
      }
      leaf tx_challenge_error {
        description "Tx challenge error";
        type uint32;
      }
      leaf tx_challenge_resp_error {
        description "Tx Challenge response error";
        type uint32;
      }
      leaf tx_challenge_ack_error {
        description "Tx Challenge ack error";
        type uint32;
      }
      leaf tx_challenge_gen_error {
        description "Tx Challenge general errors";
        type uint32;
      }
      leaf rx_pkts {
        description "Rx packets";
        type uint64;
      }
      leaf rx_octets {
        description "Rx octets";
        type uint32;
      }
      leaf rx_error {
        description "Rx error";
        type uint32;
      }
      leaf rx_connects {
        description "Rx connects";
        type uint32;
      }
      leaf rx_registers {
        description "Rx registers";
        type uint32;
      }
      leaf rx_register_replies {
        description "Rx register replies";
        type uint32;
      }
      leaf rx_dtls_handshake {
        description "Rx DTLS handshake";
        type uint32;
      }
      leaf rx_dtls_handshake_failures {
        description "Rx DTLS handshake failures";
        type uint32;
      }
      leaf rx_dtls_handshake_done {
        description "Rx DTLS handshake done";
        type uint32;
      }
      leaf rx_challenge {
        description "Rx challenge";
        type uint32;
      }
      leaf rx_challenge_resp {
        description "Rx challenge response";
        type uint32;
      }
      leaf rx_challenge_ack {
        description "Rx challenge ack";
        type uint32;
      }
      leaf challenge_failures {
        description "Challenge failures";
        type uint32;
      }
    }
    container local-properties {
      description "Display local control properties";
      config false;
      leaf device-type {
        description "Personality";
        type viptela:personality-enum-oper;
      }
      leaf organization-name {
        description "Organization name";
        type viptela:organization-name;
      }
      leaf certificate-status {
        description "Certificate status";
        type string;
      }
      leaf root-ca-chain-status {
        description "Root CA chain status";
        type string;
      }
      leaf certificate-validity {
        description "Certificate validity";
        type string;
      }
      leaf certificate-not-valid-before {
        description "Certificate not valid before";
        type string;
      }
      leaf certificate-not-valid-after {
        description "Certificate not valid after";
        type string;
      }
      leaf uuid {
        description "Unique device identifier";
        type string;
      }
      leaf board-serial {
        description "Board ID serial number";
        type viptela:serial-number;
      }
      leaf number-active-wan-interfaces {
        description "Number of WAN interfaces";
        type uint32;
      }
      leaf protocol {
        description "Protocol";
        type viptela:control-protocol-enum;
      }
      list wan-interface-list {
        description "List of WAN interfaces";
        config false;
        key "instance index";
        leaf instance {
          description "vdaemon instance ID";
          type uint32;
        }
        leaf index {
          description "WAN index";
          type uint32;
        }
        leaf ip {
          description "IP address";
          type inet:ip-address;
        }
        leaf port {
          description "Port";
          type uint32;
        }
        leaf num-vsmarts {
          description "Number of vSmarts";
          type uint32;
        }
        leaf num-vmanages {
          description "Number of vManages";
          type uint32;
        }
        leaf admin-state {
          description "Administrative state";
          type state-enum;
        }
        leaf operation-state {
          description "Operational state";
          type state-enum;
        }
        leaf last-conn-time {
          description "Time since last connection";
          type string;
        }
      }
      leaf system-ip {
        description "System IP address";
        type inet:ip-address;
      }
      leaf vedge-list-version {
        description "vEdge list version number";
        type yang:counter64;
      }
      leaf vsmart-list-version {
        description "vSmart list version number";
        type yang:counter64;
      }
      leaf sp-organization-name {
        description "SP Organization name";
        type viptela:organization-name;
      }
    }
    list valid-vsmarts {
      description "Display valid vSmarts";
      config false;
      key "serial-number org";
      leaf serial-number {
        description "Serial number of the device";
        type viptela:serial-number;
      }
      leaf org {
        description "Organization that the controller belongs to";
        type string;
      }
    }
    list valid-vedges {
      description "Display valid vedges";
      config false;
      key "chassis-number";
      leaf chassis-number {
        description "Chassis number of the device";
        type viptela:chassis-number;
      }
      leaf serial-number {
        description "Serial number of the device";
        type viptela:serial-number;
      }
      leaf validity {
        description "Device valid or staging";
        type viptela:validity-enum;
      }
      leaf org {
        description "Organization that the vedge belongs to";
        type string;
      }
      leaf hardware-installed-serial-number {
        description "Installed serial number of the device";
        type viptela:serial-number;
      }
    }
    list summary {
      description "Display orchestrator summary";
      config false;
      key "instance";
      leaf instance {
        description "vdaemon instance ID";
        type uint32;
      }
      leaf vmanage_counts {
        type uint16;
      }
      leaf vsmart_counts {
        type uint16;
      }
      leaf vedge_counts {
        type uint16;
      }
      leaf protocol {
        type viptela:control-protocol-enum;
      }
      leaf listening_ip {
        type inet:ip-address;
      }
      leaf listening_ipv6 {
        type inet:ip-address;
      }
      leaf listening_port {
        type inet:port-number;
      }
    }
    list valid-vmanage-id {
      description "Display valid vManage certificate authority UUID";
      config false;
      key "chassis-number";
      leaf chassis-number {
        description "Chassis number of the device";
        type viptela:chassis-number;
      }
    }
    list reverse-proxy-mapping {
      description "Display reverse proxy mapping";
      config false;
      key "uuid private-ip private-port";
      leaf uuid {
        description "UUID of vSmart or vManage";
        type string;
      }
      leaf private-ip {
        description "Private IP address of vSmart or vManage";
        type inet:ip-address;
      }
      leaf private-port {
        description "Private port of vSmart or vManage";
        type inet:port-number;
      }
      leaf proxy-ip {
        description "Proxy IP address mapping this vSmart or vManage";
        type inet:ip-address;
      }
      leaf proxy-port {
        description "Proxy port mapping this vSmart or vManage";
        type inet:port-number;
      }
    }
  }
  container ipsec {
    description "Display IPsec information";
    when "/viptela-system:system/viptela-system:personality = 'vedge'";
    list local-sa {
      description "Display IPsec local SA";
      config false;
      key "tloc-address tloc-color spi tloc-index";
      leaf tloc-address {
        description "TLOC address";
        type inet:ip-address;
      }
      leaf tloc-color {
        description "Color";
        type viptela:color-enum;
      }
      leaf spi {
        description "SPI";
        type uint32;
      }
      leaf tloc-index {
        description "TLOC index";
        type uint32;
      }
      leaf ip {
        description "IP address";
        type inet:ip-address;
      }
      leaf port {
        description "Port number";
        type uint32;
      }
      leaf encrypt-key-hash {
        description "Encryption key hash";
        type string;
      }
      leaf auth-key-hash {
        description "Authentication key hash";
        type string;
      }
      leaf ipv6 {
        description "IPv6 address";
        type inet:ip-address;
      }
    }
    list inbound-connections {
      description "Display IPsec inbound connections";
      config false;
      key "local-tloc-address local-tloc-color remote-tloc-address remote-tloc-color local-tloc-index remote-tloc-index";
      leaf local-tloc-address {
        description "Local TLOC address";
        type inet:ip-address;
      }
      leaf local-tloc-color {
        description "Local color";
        type viptela:color-enum;
      }
      leaf remote-tloc-address {
        description "Remote TLOC address";
        type inet:ip-address;
      }
      leaf remote-tloc-color {
        description "Remote color";
        type viptela:color-enum;
      }
      leaf local-tloc-index {
        description "Local TLOC Index";
        type uint32;
      }
      leaf remote-tloc-index {
        description "Remote TLOC Index";
        type uint32;
      }
      leaf source-ip {
        description "Source IP address";
        type inet:ip-address;
      }
      leaf source-port {
        description "Source port number";
        type uint32;
      }
      leaf dest-ip {
        description "Destination IP address";
        type inet:ip-address;
      }
      leaf dest-port {
        description "Destination port number";
        type uint32;
      }
      leaf negotiated-encryption-algo {
        description "Negotiated encryption algorithm";
        type string;
      }
      leaf tc-spi-per-tun {
        description "Traffic Control SPIs per Tunnel";
        type uint32;
      }
      leaf pkey-hash {
        description "Peer pairwise key hash";
        type string;
      }
      leaf peer-spi {
        description "Peer negotiated IPsec tunnel SPI";
        type string;
      }
    }
    list outbound-connections {
      description "Display IPsec outbound connections";
      config false;
      key "source-ip source-port dest-ip dest-port spi tloc-index";
      leaf source-ip {
        description "Source IP address";
        type inet:ip-address;
      }
      leaf source-port {
        description "Source port number";
        type uint32;
      }
      leaf dest-ip {
        description "Destination IP address";
        type inet:ip-address;
      }
      leaf dest-port {
        description "Destination port number";
        type uint32;
      }
      leaf spi {
        description "SPI";
        type uint32;
      }
      leaf tloc-index {
        description "TLOC index";
        type uint32;
      }
      leaf tunnel-mtu {
        description "Tunnel MTU";
        type uint32;
      }
      leaf remote-tloc-address {
        description "Remote TLOC address";
        type inet:ip-address;
      }
      leaf remote-tloc-color {
        description "Remote color";
        type viptela:color-enum;
      }
      leaf authentication-used {
        description "Authentication used";
        type string;
      }
      leaf encrypt-key-hash {
        description "Encryption key hash";
        type string;
      }
      leaf auth-key-hash {
        description "Authentication key hash";
        type string;
      }
      leaf negotiated-algo {
        description "Negotiated encryption algorithm";
        type string;
      }
      leaf tc-spi-per-tun {
        description "Traffic Control SPIs per Tunnel";
        type uint32;
      }
      leaf pkey-hash {
        description "Peer pairwise key hash";
        type string;
      }
      leaf peer-spi {
        description "Peer pairwise key SPI";
        type string;
      }
      leaf local-tloc-address {
        description "Local TLOC address";
        type inet:ip-address;
      }
      leaf local-tloc-color {
        description "Local color";
        type viptela:color-enum;
      }
    }
    container ike {
      description "Display IPsec information for IKE sessions";
      when "/viptela-system:system/viptela-system:personality = 'vedge'";
      list inbound-connections {
        description "Display IPsec-IKE inbound connections";
        config false;
        key "source-ip source-port dest-ip dest-port";
        leaf source-ip {
          description "Source IP address";
          type inet:ip-address;
        }
        leaf source-port {
          description "Source port number";
          type uint32;
        }
        leaf dest-ip {
          description "Destination IP address";
          type inet:ip-address;
        }
        leaf dest-port {
          description "Destination port number";
          type uint32;
        }
        leaf new-spi {
          description "New SPI";
          type uint32;
        }
        leaf old-spi {
          description "Old SPI";
          type uint32;
        }
        leaf cipher-suite {
          description "Encryption and integrity Suite";
          type string;
        }
        leaf new-key-hash {
          description "New Key Hash";
          type string;
        }
        leaf old-key-hash {
          description "Old Key Hash";
          type string;
        }
        leaf ext-seq {
          description "Extended Sequence Numbers";
          type string;
        }
      }
      list outbound-connections {
        description "Display IPsec-IKE outbound connections";
        config false;
        key "source-ip source-port dest-ip dest-port spi";
        leaf source-ip {
          description "Source IP address";
          type inet:ip-address;
        }
        leaf source-port {
          description "Source port number";
          type uint32;
        }
        leaf dest-ip {
          description "Destination IP address";
          type inet:ip-address;
        }
        leaf dest-port {
          description "Destination port number";
          type uint32;
        }
        leaf spi {
          description "SPI";
          type uint32;
        }
        leaf cipher-suite {
          description "Encryption and integrity Suite";
          type string;
        }
        leaf key-hash {
          description "Key Hash";
          type string;
        }
        leaf tunnel-mtu {
          description "Tunnel MTU";
          type uint32;
        }
        leaf ext-seq {
          description "Extended Sequence Numbers";
          type string;
        }
      }
      list sessions {
        description "Display IPsec-IKE sessions";
        config false;
        key "vpn-id if-name";
        leaf vpn-id {
          description "VPN ID";
          type viptela:vpn-id;
        }
        leaf if-name {
          description "IPsec interface name";
          type string;
        }
        leaf version {
          description "IKE version";
          type uint8;
        }
        leaf source-ip {
          description "Source IP address";
          type inet:ip-address;
        }
        leaf source-port {
          description "Source port number";
          type uint32;
        }
        leaf dest-ip {
          description "Destination IP address";
          type inet:ip-address;
        }
        leaf dest-port {
          description "Destination port number";
          type uint32;
        }
        leaf initiator-spi {
          description "Initiator SPI";
          type string;
        }
        leaf responder-spi {
          description "Responder SPI";
          type string;
        }
        leaf cipher-suite {
          description "Negotiated cipher suite";
          type string;
        }
        leaf dh-group {
          description "Negotiated Diffie-Hellman group";
          type string;
        }
        leaf state {
          description "IKE SA state";
          type string;
        }
        leaf uptime {
          description "IKE sessions uptime";
          type string;
        }
        leaf tunnel-uptime {
          description "IPsec tunnel uptime";
          type string;
        }
      }
    }
  }
  container tunnel {
    description "Display tunnel information";
    when "/viptela-system:system/viptela-system:personality = 'vedge'";
    list stats {
      description "Display tunnel forwarding statistics";
      config false;
      key "tunnel-protocol source-ip dest-ip source-port dest-port";
      leaf tunnel-protocol {
        description "Tunnel encapsulation protocol type";
        type viptela:encap-enum;
      }
      leaf source-ip {
        description "Source IP address";
        type inet:ip-address;
      }
      leaf dest-ip {
        description "Destination IP address";
        type inet:ip-address;
      }
      leaf source-port {
        description "Source port number";
        type uint32;
      }
      leaf dest-port {
        description "Destination port number";
        type uint32;
      }
      leaf system-ip {
        description "Remote system IP address";
        type inet:ip-address;
      }
      leaf local-color {
        description "Local color";
        type viptela:color-enum;
      }
      leaf remote-color {
        description "Remote color";
        type viptela:color-enum;
      }
      leaf tunnel-mtu {
        description "Tunnel MTU size";
        type uint32;
      }
      leaf tx_pkts {
        description "Number of packets transmitted";
        type yang:counter64;
      }
      leaf tx_octets {
        description "Number of octets transmitted";
        type yang:counter64;
      }
      leaf rx_pkts {
        description "Number of packets received";
        type yang:counter64;
      }
      leaf rx_octets {
        description "Number of octets received";
        type yang:counter64;
      }
      leaf ipsec-decrypt-inbound {
        description "Received IPsec packets that were decrypted";
        type yang:counter64;
      }
      leaf ipsec-rx-auth-failures {
        description "Authentication failures for received IPsec packets";
        type yang:counter64;
      }
      leaf ipsec-rx-failures {
        description "Other failures for received IPsec packets";
        type yang:counter64;
      }
      leaf ipsec-encrypt-outbound {
        description "Transmitted IPsec packets that were encrypted";
        type yang:counter64;
      }
      leaf ipsec-tx-auth-failures {
        description "Authentication failures for transmitted IPsec packets";
        type yang:counter64;
      }
      leaf ipsec-tx-failures {
        description "Other failures for transmitted IPsec packets";
        type yang:counter64;
      }
      leaf tcp-mss-adjust {
        description "Effective TCP MSS adjust used";
        type uint32;
      }
      leaf bfd-echo-tx-pkts {
        description "BFD echo packets sent";
        type yang:counter64;
      }
      leaf bfd-echo-rx-pkts {
        description "BFD echo packets received";
        type yang:counter64;
      }
      leaf bfd-echo-tx-octets {
        description "BFD echo octets sent";
        type yang:counter64;
      }
      leaf bfd-echo-rx-octets {
        description "BFD hello octets received";
        type yang:counter64;
      }
      leaf bfd-pmtu-tx-pkts {
        description "BFD PMTU packets sent";
        type yang:counter64;
      }
      leaf bfd-pmtu-rx-pkts {
        description "BFD PMTU packets received";
        type yang:counter64;
      }
      leaf bfd-pmtu-tx-octets {
        description "BFD PMTU octets sent";
        type yang:counter64;
      }
      leaf bfd-pmtu-rx-octets {
        description "BFD PMTU octets received";
        type yang:counter64;
      }
      leaf fec-rx-data-pkts {
        description "Total FEC data packets received";
        type uint32;
      }
      leaf fec-rx-parity-pkts {
        description "Total FEC parity packets received";
        type uint32;
      }
      leaf fec-tx-data-pkts {
        description "Total FEC data packets transmitted";
        type uint32;
      }
      leaf fec-tx-parity-pkts {
        description "Total FEC parity packets transmitted";
        type uint32;
      }
      leaf fec-reconstruct-pkts {
        description "Total FEC packets reconstructed";
        type uint32;
      }
      leaf fec-capable {
        description "Is tunnel FEC capable";
        type boolean;
      }
      leaf fec-dynamic {
        description "Is tunnel subjected to dynamic FEC";
        type boolean;
      }
      leaf pktdup-rx {
        description "Total PKT-DUP RX packets";
        type uint32;
      }
      leaf pktdup-rx-other {
        description "Total PKT-DUP RX for other tunnel";
        type uint32;
      }
      leaf pktdup-rx-this {
        description "Total PKT-DUP RX for this tunnel";
        type uint32;
      }
      leaf pktdup-tx {
        description "Total PKT-DUP TX packets";
        type uint32;
      }
      leaf pktdup-tx-other {
        description "Total PKT-DUP TX for other tunnel";
        type uint32;
      }
      leaf pktdup-capable {
        description "Is tunnel PKT-DUP capable";
        type boolean;
      }
    }
    list gre-keepalives {
      description "GRE tunnel keepalive state";
      config false;
      key "vpn-id if-name";
      leaf vpn-id {
        description "VPN ID";
        type viptela:vpn-id;
      }
      leaf if-name {
        description "GRE Interface Name";
        type string;
      }
      leaf source-ip {
        description "Source IP address";
        type inet:ip-address;
      }
      leaf dest-ip {
        description "Destination IP address";
        type inet:ip-address;
      }
      leaf admin-state {
        description "GRE tunnel admin state";
        type viptela:gre-tunnel-state-enum;
      }
      leaf oper-state {
        description "GRE tunnel operational state";
        type viptela:gre-tunnel-ka-state-enum;
      }
      leaf ka-enabled {
        description "Keepalive enabled";
        type boolean;
      }
      leaf base-if-oper-status {
        description "Underlay interface operational status";
        type viptela:if-oper-status-type;
      }
      leaf remote-tx-packets {
        description "Number of remote GRE packets transmitted";
        type yang:counter64;
      }
      leaf remote-rx-packets {
        description "Number of remote GRE packets received";
        type yang:counter64;
      }
      leaf tx-packets {
        description "Number of packets transmitted";
        type yang:counter64;
      }
      leaf rx-packets {
        description "Number of packets received";
        type yang:counter64;
      }
      leaf tx-errors {
        description "Number of transmit errors";
        type yang:counter32;
      }
      leaf rx-errors {
        description "Number of receive errors";
        type yang:counter32;
      }
      leaf transitions {
        description "Gre tunnel state transitions";
        type yang:counter32;
      }
    }
  }
  container security-info {
    description "Display configured security parameters";
    when "/viptela-system:system/viptela-system:personality = 'vedge'";
    config false;
    leaf authentication-type {
      type string;
    }
    leaf rekey {
      type uint32;
    }
    leaf replay-window {
      type uint32;
    }
    leaf encryption-supported {
      type string;
    }
    leaf fips-mode {
      type string;
    }
    leaf pairwise-keying {
      type string;
    }
  }
  container ztp {
    description "Display entries in the ZTP database";
    when
      "(/viptela-system:system/viptela-system:vbond/viptela-system:local) and 
       (/viptela-system:system/viptela-system:vbond/viptela-system:ztp-server)";
    config false;
    list entries {
      description "Display vEdges in the ZTP database";
      key "index";
      leaf index {
        description "Row index";
        type uint32;
      }
      leaf chassis-number {
        description "Chassis number of the device";
        type viptela:chassis-number;
      }
      leaf serial-number {
        description "Serial number of the device";
        type viptela:serial-number;
      }
      leaf validity {
        description "Device chassis number validity status";
        type string {
          length "1..8";
        }
      }
      leaf vbond-ip {
        description "Enterprise vBond public IP address";
        type union {
          type inet:ip-address {
            description "IP address";
          }
          type string {
            description "DNS name";
            length "1..128";
          }
        }
      }
      leaf vbond-port {
        description "Enterprise vBond public port number";
        type inet:port-number;
      }
      leaf organization-name {
        description "Enterprise organization name";
        type viptela:organization-name;
      }
      leaf root-cert-path {
        description "Enterprise root certificate path";
        type string {
          length "1..128";
        }
      }
    }
  }
  notification control-connection-state-change {
    uses viptela:common-notification-header;
    leaf personality {
      type viptela:personality-enum-oper;
    }
    leaf peer-type {
      type viptela:personality-enum-oper;
    }
    leaf peer-system-ip {
      type inet:ip-address;
    }
    leaf peer-vmanage-system-ip {
      type inet:ip-address;
    }
    leaf public-ip {
      type inet:ip-address;
    }
    leaf public-port {
      type uint32;
    }
    leaf src-color {
      type viptela:color-enum;
    }
    leaf remote-color {
      type viptela:color-enum;
    }
    leaf uptime {
      type string;
    }
    leaf new-state {
      type viptela:oper-state;
    }
  }
  notification control-connection-auth-fail {
    uses viptela:common-notification-header;
    leaf personality {
      type viptela:personality-enum-oper;
    }
    leaf peer-type {
      type viptela:personality-enum-oper;
    }
    leaf peer-system-ip {
      type inet:ip-address;
    }
    leaf local-system-ip {
      type inet:ip-address;
    }
    leaf local-color {
      type viptela:color-enum;
    }
    leaf remote-color {
      type viptela:color-enum;
    }
    leaf reason {
      type string;
    }
  }
  notification control-vbond-state-change {
    uses viptela:common-notification-header;
    leaf personality {
      type viptela:personality-enum-oper;
    }
    leaf new-state {
      type viptela:oper-state;
    }
  }
  notification control-connection-tloc-ip-change {
    uses viptela:common-notification-header;
    leaf personality {
      type viptela:personality-enum-oper;
    }
    leaf old-public-ip {
      type inet:ip-address;
    }
    leaf old-public-port {
      type uint32;
    }
    leaf new-public-ip {
      type inet:ip-address;
    }
    leaf new-public-port {
      type uint32;
    }
  }
  notification control-no-active-vsmart {
    uses viptela:common-notification-header;
    leaf personality {
      type viptela:personality-enum-oper;
    }
  }
  notification control-no-active-vbond {
    uses viptela:common-notification-header;
    leaf personality {
      type viptela:personality-enum-oper;
    }
  }
  notification tunnel-ipsec-rekey {
    uses viptela:common-notification-header;
    leaf personality {
      type viptela:personality-enum-oper;
    }
    leaf color {
      type viptela:color-enum;
    }
  }
  notification tunnel-ipsec-manual-rekey {
    uses viptela:common-notification-header;
    leaf personality {
      type viptela:personality-enum-oper;
    }
    leaf color {
      type viptela:color-enum;
    }
  }
  notification security-root-cert-chain-installed {
    uses viptela:common-notification-header;
  }
  notification security-certificate-installed {
    uses viptela:common-notification-header;
  }
  notification security-new-csr-generated {
    uses viptela:common-notification-header;
  }
  notification security-root-cert-chain-uninstalled {
    uses viptela:common-notification-header;
  }
  notification security-clear-installed-certificate {
    uses viptela:common-notification-header;
  }
  notification security-vedge-serial-file-uploaded {
    uses viptela:common-notification-header;
  }
  notification security-vsmart-serial-file-uploaded {
    uses viptela:common-notification-header;
  }
  notification security-vedge-entry-added {
    uses viptela:common-notification-header;
    leaf uuid {
      type string;
    }
    leaf serial {
      type viptela:serial-number;
    }
  }
  notification security-vedge-entry-removed {
    uses viptela:common-notification-header;
    leaf uuid {
      type string;
    }
  }
  notification security-vsmart-entry-added {
    uses viptela:common-notification-header;
    leaf serial {
      type viptela:serial-number;
    }
  }
  notification security-vsmart-entry-removed {
    uses viptela:common-notification-header;
    leaf serial {
      type viptela:serial-number;
    }
  }
  notification security-certificate-expired {
    uses viptela:common-notification-header;
  }
  notification control-vedge-list-request {
    uses viptela:common-notification-header;
    leaf peer-type {
      type viptela:personality-enum-oper;
    }
    leaf peer-system-ip {
      type inet:ip-address;
    }
    leaf uuid {
      type string;
    }
  }
  notification service-gre-state-update {
    uses viptela:common-notification-header;
    leaf old-oper-state {
      type viptela:oper-state;
    }
    leaf new-oper-state {
      type viptela:oper-state;
    }
    leaf gre-ifname {
      type string;
    }
    leaf vpn-id {
      type viptela:vpn-id;
    }
    leaf tunnel-source {
      type inet:ip-address;
    }
    leaf tunnel-destination {
      type inet:ip-address;
    }
    leaf gre-ip {
      type string;
    }
  }
  notification vmanage-connection-preference-changed {
    uses viptela:common-notification-header;
    leaf color {
      type viptela:color-enum;
    }
    leaf vmanage-connection-preference {
      type uint8;
    }
  }
  notification vbond-reject-vedge-connection {
    uses viptela:common-notification-header;
    leaf uuid {
      type string;
    }
    leaf organization-name {
      type viptela:organization-name;
    }
    leaf sp-organization-name {
      type viptela:organization-name;
    }
    leaf reason {
      type string;
    }
  }
  notification device-template-missing {
    uses viptela:common-notification-header;
    leaf uuid {
      type string;
    }
    leaf peer-type {
      type viptela:personality-enum-oper;
    }
  }
  notification device-template-attached-during-ztp {
    uses viptela:common-notification-header;
    leaf uuid {
      type string;
    }
    leaf peer-type {
      type viptela:personality-enum-oper;
    }
  }
}
