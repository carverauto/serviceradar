module viptela-hardware {
  namespace "http://viptela.com/hardware";
  prefix viptela-hardware;

    prefix tailf;
  }
  import viptela-common {
    prefix viptela;
  }
  import viptela-system {
    prefix viptela-system;
  }

  organization "Viptela, Inc.";
  contact
    "Viptela, Inc.
     Email:support@viptela.com";
  description
    "This module defines the data model for hardware operational data";

  revision 2019-08-15 {
    description
      "Release version: 19.2";
  }
  revision 2018-11-01 {
    description
      "Release version: 18.4";
  }
  revision 2018-08-20 {
    description
      "Release version: 18.3.1";
  }
  revision 2018-06-25 {
    description
      "Release version: 18.3";
  }
  revision 2018-04-25 {
    description
      "Release version: 18.2";
  }
  revision 2018-03-15 {
    description
      "Release version: 18.1.1";
  }
  revision 2018-01-16 {
    description
      "Release version: 17.2.3";
  }
  revision 2017-11-01 {
    description
      "Release version: 17.2.1";
  }
  revision 2017-08-01 {
    description
      "Release version: 17.2";
  }
  revision 2017-05-25 {
    description
      "Release version: 17.1.1";
  }
  revision 2017-04-06 {
    description
      "Release version: 17.1";
  }
  revision 2017-02-15 {
    description
      "Release version: 16.3.2";
  }
  revision 2017-02-06 {
    description
      "Release version: 16.3.1";
  }
  revision 2016-11-16 {
    description
      "Release version: 16.3";
  }
  revision 2016-10-25 {
    description
      "Release version: 16.2.10";
  }
  revision 2016-10-24 {
    description
      "Release version: 16.2.4";
  }
  revision 2016-08-10 {
    description
      "Release version: 16.2.2";
  }
  revision 2016-08-01 {
    description
      "Release version: 16.2.1";
  }
  revision 2016-06-09 {
    description
      "Release version: 16.2";
  }
  revision 2016-04-22 {
    description
      "Release version: 16.1.1";
  }
  revision 2016-03-15 {
    description
      "Release version: 16.1";
  }
  revision 2016-01-30 {
    description
      "Release version: 15.4.3";
  }
  revision 2015-12-28 {
    description
      "Release version: 15.4.1";
  }
  revision 2015-12-01 {
    description
      "Release version: 15.4.0";
  }
  revision 2015-10-31 {
    description
      "Release version: 15.3.5";
  }
  revision 2015-09-27 {
    description
      "Release version: 15.3.3";
  }
  revision 2015-09-01 {
    description
      "Release version: 15.3.1";
  }
  revision 2015-07-01 {
    description
      "Release version: 15.3";
  }
  revision 2015-06-01 {
    description
      "Release version: 15.2.8";
  }
  revision 2015-05-01 {
    description
      "Release version: 15.2";
  }
  revision 2015-02-01 {
    description
      "Release version: 15.1";
  }
  revision 2014-12-01 {
    description
      "Release version: 14.3";
  }
  revision 2014-07-01 {
    description
      "Release version: 14.2";
  }
  revision 2013-02-12 {
    description
      "Initial revision";
  }

  typedef module-state-enum {
    type enumeration {
      enum "Inserted";
      enum "Removed";
    }
  }

  typedef failure-state-enum {
    type enumeration {
      enum "OK";
      enum "Failed";
    }
  }

  typedef sensor-state-enum {
    type enumeration {
      enum "Green";
      enum "Yellow";
      enum "Red";
    }
  }

  typedef hw-sensor-type-enum {
    type enumeration {
      enum "Board";
      enum "CPU Junction";
      enum "DRAM";
      enum "PIM";
    }
  }

  typedef hw-type-enum {
    type enumeration {
      enum "Unknown" {
        value 0;
      }
      enum "Chassis" {
        value 1;
      }
      enum "CPU";
      enum "DRAM";
      enum "Flash";
      enum "eMMC";
      enum "SDCard";
      enum "USB";
      enum "PIM";
      enum "Transceiver";
      enum "FanTray";
      enum "PEM";
      enum "NIM";
    }
  }

  typedef hw-poe-class-enum {
    description
      "PoE PD Class";
    type enumeration {
      enum "Unknown";
      enum "Class 1";
      enum "Class 2";
      enum "Class 3";
      enum "Class 4";
      enum "Reserved";
      enum "Class 0";
      enum "Over Current";
    }
  }

  container hardware {
    description "Display hardware information";
    when "/viptela-system:system/viptela-system:personality = 'vedge'";
    list inventory {
      description "Display hardware inventory";
      config false;
      key "hw-type hw-dev-index";
      leaf hw-type {
        description "Hardware type";
        type hw-type-enum;
      }
      leaf hw-dev-index {
        description "Hardware device index";
        type uint32;
      }
      leaf version {
        description "Version";
        type viptela:named-type;
      }
      leaf part-number {
        description "Part number";
        type viptela:named-type;
      }
      leaf serial-number {
        description "Serial number";
        type viptela:named-type;
      }
      leaf hw-description {
        description "Description";
        type string {
          length "1..128";
        }
      }
    }
    list environment {
      description "Display hardware environment status";
      config false;
      key "hw-class hw-item hw-dev-index";
      leaf hw-class {
        description "Hardware class";
        type enumeration {
          enum "Temperature Sensors";
          enum "Fans";
          enum "PEM";
          enum "PIM";
          enum "USB";
          enum "LED";
          enum "NIM";
        }
      }
      leaf hw-item {
        description "Item";
        type viptela:named-type;
      }
      leaf hw-dev-index {
        description "Device index";
        type uint32;
      }
      leaf status {
        description "Status";
        type enumeration {
          enum "OK";
          enum "Down";
          enum "Failed";
        }
      }
      leaf measurement {
        description "Measurement";
        type string {
          length "1..256";
        }
      }
    }
    list alarms {
      description "Display hardware alarms";
      config false;
      key "alarm-id alarm-instance";
      leaf alarm-id {
        description "Alarm ID";
        type uint32;
      }
      leaf alarm-name {
        description "Name";
        type viptela:named-type;
      }
      leaf alarm-instance {
        description "Alarm instance";
        type uint32;
      }
      leaf alarm-time {
        description "Alarm time";
        type viptela:named-type;
      }
      leaf alarm-category {
        description "Category";
        type enumeration {
          enum "Critical";
          enum "Major";
          enum "Minor";
        }
      }
      leaf alarm-description {
        description "Description";
        type string {
          length "1..128";
        }
      }
    }
    list temperature-thresholds {
      description "Display hardware temperature thresholds";
      config false;
      key "hw-sensor-type hw-dev-index";
      leaf hw-sensor-type {
        description "Temperature sensor type";
        type hw-sensor-type-enum;
      }
      leaf hw-dev-index {
        description "Index";
        type uint32;
      }
      leaf fan-speed-normal {
        description "No alarm below this threshold when fans at normal speed";
        when
          "/viptela-system:system/viptela-system:device-model != 'vedge-ISR1100-4G' and
           /viptela-system:system/viptela-system:device-model != 'vedge-ISR1100-4GLTE' and
           /viptela-system:system/viptela-system:device-model != 'vedge-ISR1100-6G'";
        type uint32;
      }
      leaf yellow-alarm-normal {
        description "Yellow alarm threshold when fans at normal speed, in degrees Celsius";
        type uint32;
      }
      leaf yellow-alarm-bad-fan {
        description "Yellow alarm threshold when one or more fans has failed, in degrees Celsius";
        when
          "/viptela-system:system/viptela-system:device-model != 'vedge-ISR1100-4G' and
           /viptela-system:system/viptela-system:device-model != 'vedge-ISR1100-4GLTE' and
           /viptela-system:system/viptela-system:device-model != 'vedge-ISR1100-6G'";
        type uint32;
      }
      leaf red-alarm-normal {
        description "Red alarm threshold when fans at normal speed, in degrees Celsius";
        type uint32;
      }
      leaf red-alarm-bad-fan {
        description "Red alarm threshold when one or more fans has failed, in degrees Celsius";
        when
          "/viptela-system:system/viptela-system:device-model != 'vedge-ISR1100-4G' and
           /viptela-system:system/viptela-system:device-model != 'vedge-ISR1100-4GLTE' and
           /viptela-system:system/viptela-system:device-model != 'vedge-ISR1100-6G'";
        type uint32;
      }
    }
    list poe {
      description "Display PoE information";
      when
        "(/viptela-system:system/viptela-system:personality = 'vedge') and
         (/viptela-system:system/viptela-system:device-model = 'vedge-100' or
         /viptela-system:system/viptela-system:device-model = 'vedge-100-W2' or
         /viptela-system:system/viptela-system:device-model = 'vedge-100-WM' or
         /viptela-system:system/viptela-system:device-model = 'vedge-100-M2' or
         /viptela-system:system/viptela-system:device-model = 'vedge-100-M')";
      config false;
      key "poe-ifname";
      leaf poe-ifname {
        description "Interface name";
        type viptela:named-type;
      }
      leaf poe-if-status {
        description "Interface administrative status";
        type string {
          length "1..16";
        }
      }
      leaf poe-status {
        description "Interface PoE status";
        type string {
          length "1..16";
        }
      }
      leaf poe-max-power {
        description "Max Power (Watts)";
        type decimal64 {
          fraction-digits 1;
        }
      }
      leaf poe-used-power {
        description "Used Power (Watts)";
        type decimal64 {
          fraction-digits 1;
        }
      }
      leaf poe-pd-class {
        description "Device Class";
        type hw-poe-class-enum;
      }
    }
  }
  container viptela-devices {
    description "System object IDs for viptela devices";
    container vsmart;
    container vmanage;
    container vbond-software;
    container vedge-1000-AC;
    container vedge-2000-AC;
    container vedge-100-AC;
    container vedge-100-W2-AC;
    container vedge-100-WM-AC;
    container vedge-100-M2-AC;
    container vedge-100-M-AC;
    container vedge-100-B-AC;
    container vedge-cloud;
    container vcontainer;
    container vedge-5000-AC;
    container vedge-101-B-AC;
    container vedge-1001-AC;
    container vedge-101-M-AC;
    container vedge-ISR1100-4G-AC;
    container vedge-ISR1100-6G-AC;
    container vedge-ISR1100-4GLTE-AC;
  }
  notification flash-fault {
    uses viptela:common-notification-header;
    leaf new-state {
      type failure-state-enum;
    }
  }
  notification emmc-fault {
    uses viptela:common-notification-header;
    leaf new-state {
      type failure-state-enum;
    }
  }
  notification sdcard-fault {
    uses viptela:common-notification-header;
    leaf new-state {
      type failure-state-enum;
    }
  }
  notification tempsensor-fault {
    uses viptela:common-notification-header;
    leaf hw-sensor-type {
      type hw-sensor-type-enum;
    }
    leaf hw-dev-index {
      type uint32;
    }
    leaf name {
      type string;
    }
    leaf new-state {
      type failure-state-enum;
    }
  }
  notification tempsensor-state {
    uses viptela:common-notification-header;
    leaf hw-sensor-type {
      type hw-sensor-type-enum;
    }
    leaf hw-dev-index {
      type uint32;
    }
    leaf name {
      type string;
    }
    leaf temp {
      type uint32;
    }
    leaf sensor-new-state {
      type sensor-state-enum;
    }
  }
  notification fan-fault {
    uses viptela:common-notification-header;
    leaf fantray-id {
      type uint32;
    }
    leaf fan-id {
      type uint32;
    }
    leaf new-state {
      type failure-state-enum;
    }
  }
  notification fantray-fault {
    uses viptela:common-notification-header;
    leaf fantray-id {
      type uint32;
    }
    leaf new-state {
      type module-state-enum;
    }
  }
  notification pem-fault {
    uses viptela:common-notification-header;
    leaf pem-id {
      type uint32;
    }
    leaf new-state {
      type failure-state-enum;
    }
  }
  notification pem-state-change {
    uses viptela:common-notification-header;
    leaf pem-id {
      type uint32;
    }
    leaf new-state {
      type module-state-enum;
    }
  }
  notification pim-fault {
    uses viptela:common-notification-header;
    leaf pim-id {
      type uint32;
    }
    leaf new-state {
      type failure-state-enum;
    }
  }
  notification pim-state-change {
    uses viptela:common-notification-header;
    leaf pim-id {
      type uint32;
    }
    leaf new-state {
      type module-state-enum;
    }
  }
  notification sfp-state-change {
    uses viptela:common-notification-header;
    leaf sfp-name {
      type string;
    }
    leaf new-state {
      type module-state-enum;
    }
  }
  notification sfp-support-state {
    uses viptela:common-notification-header;
    leaf sfp-name {
      type string;
    }
    leaf new-state {
      type module-state-enum;
    }
  }
  notification usb-state-change {
    uses viptela:common-notification-header;
    leaf usb-slot {
      type uint32;
    }
    leaf new-state {
      type module-state-enum;
    }
  }
}
