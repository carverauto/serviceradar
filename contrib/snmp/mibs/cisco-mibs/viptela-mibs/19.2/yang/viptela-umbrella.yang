module viptela-umbrella {
  namespace "http://viptela.com/umbrella";
  prefix viptela-umbrella;

  import ietf-inet-types {
    prefix inet;
  }
  import ietf-yang-types {
    prefix yang;
  }
  import viptela-common {
    prefix viptela;
  }
    prefix tailf;
  }
  import viptela-system {
    prefix viptela-system;
  }

  organization "Viptela, Inc.";
  contact
    "Viptela, Inc.
     Email:support@viptela.com";
  description
    "This module defines data model for Viptela Umbrella management";

  revision 2019-08-15 {
    description
      "Release version: 19.2";
  }
  revision 2018-11-01 {
    description
      "Release version: 18.4";
  }

  container umbrella {
    description "Display Umbrella information";
    when "/viptela-system:system/viptela-system:personality = 'vedge'";
    container config-state {
      description "Display Umbrella configuration";
      config false;
      leaf token {
        description "Token for device registration";
        type string;
      }
      leaf DNSCrypt {
        description "DNSCrypt enabled/disabled";
        type string;
      }
      leaf public-key {
        description "Public key";
        type string;
      }
      leaf resolver-address {
        description "List of resolver address";
        type string;
      }
      leaf vpn-id {
        description "List of Umbrella VPNs";
        type string;
      }
      leaf ldb-vpn {
        description "List of local domain bypass VPNs";
        type string;
      }
      leaf ldb-status {
        description "Display local domain regex status";
        type string;
      }
      leaf intf-list {
        description "List of NATed WAN interfaces";
        type string;
      }
    }
    list device-id {
      description "Display device registration information";
      config false;
      key "vpn-id";
      leaf vpn-id {
        description "VPN ID";
        type viptela:vpn-id;
      }
      leaf intf-name {
        description "Umbrella interfaces";
        type string;
      }
      leaf state {
        description "Registration states";
        type string;
      }
      leaf deviceID {
        description "unique device-id per vpn";
        type string;
      }
      leaf org-id {
        description "Organization ID";
        type uint32;
      }
      leaf retry-count {
        description "Registration retry counts";
        type uint32;
      }
      leaf tag {
        description "Tag for VPN";
        type string;
      }
      leaf label {
        description "Label for VPN";
        type string;
      }
      leaf http-response-code {
        description "HTTP response code";
        type uint16;
      }
      leaf http-response-text {
        description "HTTP response text";
        type string;
      }
      leaf last-error {
        description "Last error received for registration request";
        type string;
      }
      leaf last-code {
        description "Last code received for registration request";
        type string;
      }
      leaf last-code-text {
        description "Last code text received for registration request";
        type string;
      }
    }
    list dnscrypt {
      description "Display DNScrypt information";
      config false;
      key "index";
      leaf index {
        description "DNS server index";
        type uint32;
      }
      leaf resolver-address {
        description "Resolver address";
        type inet:ip-address;
      }
      leaf certificate-validity {
        description "Certificate validity";
        type string;
      }
      leaf certificate-state {
        description "Certificate state";
        type string;
      }
      leaf intf-name {
        description "NATed WAN interface";
        type string;
      }
      leaf resolver-public-key {
        description "Resolver public key";
        type string;
      }
      leaf client-public-key {
        description "Client public key";
        type string;
      }
      leaf certificate-valid-from {
        description "Certificate validity start date";
        type string;
      }
      leaf certificate-valid-till {
        description "Certificate validity end date";
        type string;
      }
      leaf certificate-last-refresh-time {
        description "Certificate last refresh time";
        type string;
      }
      leaf certificate-next-refresh-time {
        description "Certificate next refresh time";
        type string;
      }
      leaf serial-num {
        description "Certificate serial number";
        type uint32;
      }
      leaf client-magic {
        description "Client magic";
        type string;
      }
      leaf error-msg {
        description "Error message";
        type string;
      }
    }
  }
}
