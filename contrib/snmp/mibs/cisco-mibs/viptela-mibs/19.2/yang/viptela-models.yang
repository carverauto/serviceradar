submodule viptela-models {
  belongs-to viptela-common {
    prefix viptela;
  }

    prefix tailf;
  }

  typedef device-model-enum {
    description "Device Hardware";
    type enumeration {
      enum "vsmart" {
        value 1;
      }
      enum "vmanage" {
        value 2;
      }
      enum "vbond-software" {
        value 3;
      }
      enum "vedge-1000" {
        value 4;
      }
      enum "vedge-2000" {
        value 5;
      }
      enum "vedge-100" {
        value 6;
      }
      enum "vedge-100-W2" {
        value 7;
      }
      enum "vedge-100-WM" {
        value 8;
      }
      enum "vedge-100-M2" {
        value 9;
      }
      enum "vedge-100-M" {
        value 10;
      }
      enum "vedge-100-B" {
        value 11;
      }
      enum "vedge-cloud" {
        value 12;
      }
      enum "vcontainer" {
        value 13;
      }
      enum "vedge-5000" {
        value 14;
      }
      enum "vedge-CSR-1000v" {
        value 15;
      }
      enum "vedge-ISR-4331" {
        value 16;
      }
      enum "vedge-ISR-4321" {
        value 17;
      }
      enum "vedge-ISR-4351" {
        value 18;
      }
      enum "vedge-ISR-4221" {
        value 19;
      }
      enum "vedge-ASR-1001-X" {
        value 20;
      }
      enum "vedge-ASR-1001-HX" {
        value 21;
      }
      enum "vedge-ASR-1002-X" {
        value 22;
      }
      enum "vedge-ASR-1002-HX" {
        value 23;
      }
      enum "vedge-C1111-8PLTEEA" {
        value 24;
      }
      enum "vedge-C1111-8PLTELA" {
        value 25;
      }
      enum "vedge-C1117-4PLTEEA" {
        value 26;
      }
      enum "vedge-C1117-4PLTELA" {
        value 27;
      }
      enum "vedge-C1116-4PLTEEA" {
        value 28;
      }
      enum "vedge-C1116-4PLTELA" {
        value 29;
      }
      enum "vedge-ISRv" {
        value 30;
      }
      enum "vedge-C1111-8P" {
        value 31;
      }
      enum "vedge-C1111-4PLTEEA" {
        value 32;
      }
      enum "vedge-C1111-4PLTELA" {
        value 33;
      }
      enum "vedge-C1117-4PMLTEEA" {
        value 34;
      }
      enum "vedge-C1111-4P" {
        value 35;
      }
      enum "vedge-C1116-4P" {
        value 36;
      }
      enum "vedge-C1117-4P" {
        value 37;
      }
      enum "vedge-C1117-4PM" {
        value 38;
      }
      enum "vedge-C1101-4P" {
        value 39;
      }
      enum "vedge-C1101-4PLTEP" {
        value 40;
      }
      enum "vedge-C1111X-8P" {
        value 41;
      }
      enum "vedge-C1111-8PLTEEAW" {
        value 42;
      }
      enum "vedge-C1111-8PW" {
        value 43;
      }
      enum "vedge-ISR-4431" {
        value 44;
      }
      enum "vedge-ISR-4451-X" {
        value 45;
      }
      enum "vedge-ISR-4221X" {
        value 46;
      }
      enum "vedge-ISR-4461" {
        value 47;
      }
      enum "vedge-C8300-1N1S-6G" {
        value 48;
      }
      enum "vedge-C8300-1N1S-4G2X" {
        value 49;
      }
      enum "vedge-CE-9515" {
        value 54;
      }
      enum "vedge-CE-9511" {
        value 55;
      }
      enum "vedge-IR-1101" {
        value 56;
      }
      enum "vedge-C1121X-8PLTEPWB" {
        value 57;
      }
      enum "vedge-C1121X-8PLTEPWE" {
        value 58;
      }
      enum "vedge-C1121X-8PLTEPWZ" {
        value 59;
      }
      enum "vedge-C1161X-8P" {
        value 60;
      }
      enum "vedge-C1161X-8PLTEP" {
        value 61;
      }
      enum "vedge-C1111-8PLTEAEAWA" {
        value 62;
      }
      enum "vedge-C1121-8P" {
        value 63;
      }
      enum "vedge-C1121-8PLTEP" {
        value 64;
      }
      enum "vedge-C1121X-8PLTEPWA" {
        value 65;
      }
      enum "vedge-C1127X-8PMLTEP" {
        value 66;
      }
      enum "vedge-C1111-8PLTEEAWA" {
        value 67;
      }
      enum "vedge-C1109-4PLTE2P" {
        value 68;
      }
      enum "vedge-C1101-4PLTEPW" {
        value 69;
      }
      enum "vedge-C1109-4PLTE2PW" {
        value 70;
      }
      enum "vedge-C1111-8PLTELAW" {
        value 71;
      }
      enum "vedge-C1121X-8P" {
        value 72;
      }
      enum "vedge-C1121X-8PLTEP" {
        value 73;
      }
      enum "vedge-C1126X-8PLTEP" {
        value 74;
      }
      enum "vedge-C1127X-8PLTEP" {
        value 75;
      }
      enum "vedge-C8500-12X4QC" {
        value 76;
      }
      enum "vedge-C8500-12X" {
        value 77;
      }
      enum "vedge-C1121-8PLTEPW" {
        value 78;
      }
      enum "vedge-C1113-8PMLTEEA" {
        value 79;
      }
      enum "vedge-ISR1100-4G" {
        value 80;
      }
      enum "vedge-ISR1100-4GLTE" {
        value 81;
      }
      enum "vedge-ISR1100-6G" {
        value 82;
      }
      enum "vedge-sim" {
        value 100;
      }
      enum "vedge-nfvis-ENCS5100" {
        value 200;
      }
      enum "vedge-nfvis-ENCS5400" {
        value 201;
      }
      enum "vedge-nfvis-UCSC-M5" {
        value 202;
      }
      enum "vedge-nfvis-UCSC-E" {
        value 203;
      }
      enum "vedge-nfvis-CSP2100" {
        value 204;
      }
      enum "vedge-nfvis-CSP2100-X1" {
        value 205;
      }
      enum "vedge-nfvis-CSP2100-X2" {
        value 206;
      }
      enum "vedge-nfvis-CSP-5444" {
        value 207;
      }
    }
  }
}
