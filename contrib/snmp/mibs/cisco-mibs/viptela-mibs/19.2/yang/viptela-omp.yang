module viptela-omp {
  namespace "http://viptela.com/omp";
  prefix viptela-omp;

  import ietf-inet-types {
    prefix inet;
  }
  import ietf-yang-types {
    prefix yang;
  }
    prefix tailf;
  }
  import viptela-common {
    prefix viptela;
  }
  import viptela-system {
    prefix viptela-system;
  }
  import viptela-security {
    prefix viptela-security;
  }

  organization "Viptela, Inc.";
  contact
    "Viptela, Inc.
     Email:support@viptela.com";
  description
    "This module defines the data model for OMP management";

  revision 2019-08-15 {
    description
      "Release version: 19.2";
  }
  revision 2018-11-01 {
    description
      "Release version: 18.4";
  }
  revision 2018-08-20 {
    description
      "Release version: 18.3.1";
  }
  revision 2018-06-25 {
    description
      "Release version: 18.3";
  }
  revision 2018-04-25 {
    description
      "Release version: 18.2";
  }
  revision 2018-03-15 {
    description
      "Release version: 18.1.1";
  }
  revision 2018-01-16 {
    description
      "Release version: 17.2.3";
  }
  revision 2017-11-01 {
    description
      "Release version: 17.2.1";
  }
  revision 2017-08-01 {
    description
      "Release version: 17.2";
  }
  revision 2017-05-25 {
    description
      "Release version: 17.1.1";
  }
  revision 2017-04-06 {
    description
      "Release version: 17.1";
  }
  revision 2017-02-15 {
    description
      "Release version: 16.3.2";
  }
  revision 2017-02-06 {
    description
      "Release version: 16.3.1";
  }
  revision 2016-11-16 {
    description
      "Release version: 16.3";
  }
  revision 2016-10-25 {
    description
      "Release version: 16.2.10";
  }
  revision 2016-10-24 {
    description
      "Release version: 16.2.4";
  }
  revision 2016-08-10 {
    description
      "Release version: 16.2.2";
  }
  revision 2016-08-01 {
    description
      "Release version: 16.2.1";
  }
  revision 2016-06-09 {
    description
      "Release version: 16.2";
  }
  revision 2016-04-22 {
    description
      "Release version: 16.1.1";
  }
  revision 2016-03-15 {
    description
      "Release version: 16.1";
  }
  revision 2016-01-30 {
    description
      "Release version: 15.4.3";
  }
  revision 2015-12-28 {
    description
      "Release version: 15.4.1";
  }
  revision 2015-12-01 {
    description
      "Release version: 15.4.0";
  }
  revision 2015-10-31 {
    description
      "Release version: 15.3.5";
  }
  revision 2015-09-27 {
    description
      "Release version: 15.3.3";
  }
  revision 2015-09-01 {
    description
      "Release version: 15.3.1";
  }
  revision 2015-07-01 {
    description
      "Release version: 15.3";
  }
  revision 2015-06-01 {
    description
      "Release version: 15.2.8";
  }
  revision 2015-05-01 {
    description
      "Release version: 15.2";
  }
  revision 2015-02-01 {
    description
      "Release version: 15.1";
  }
  revision 2014-12-01 {
    description
      "Release version: 14.3";
  }
  revision 2014-07-01 {
    description
      "Release version: 14.2";
  }
  revision 2013-02-12 {
    description
      "Initial revision";
  }

  typedef attribute-type-enum {
    type enumeration {
      enum "original";
      enum "installed";
    }
  }

  typedef addr-family-enum {
    type enumeration {
      enum "ipv4";
      enum "ipv6";
    }
  }

  typedef bfd-status-enum {
    type enumeration {
      enum "up";
      enum "down";
    }
  }

  typedef path-status-enum {
    type enumeration {
      enum "chosen";
      enum "backup";
    }
  }

  typedef af-type-enum {
    type enumeration {
      enum "tloc-ipv4";
      enum "tloc-ipv6";
      enum "service";
      enum "route-ipv4";
      enum "route-ipv6";
      enum "mcast-ipv4";
      enum "mcast-ipv6";
      enum "service-ipv6";
    }
  }

  typedef rib-in-status-type {
    type bits {
      bit C {
        description
          "chosen";
      }
      bit I {
        description
          "installed";
      }
      bit Red {
        description
          "redistributed";
      }
      bit Rej {
        description
          "rejected";
      }
      bit L {
        description
          "looped";
      }
      bit R {
        description
          "resolved";
      }
      bit S {
        description
          "stale";
      }
      bit Ext {
        description
          "extranet";
      }
      bit Inv {
        description
          "invalid";
      }
      bit U {
        description
          "TLOC Unresolved";
      }
      bit Stg {
        description
          "staged";
      }
    }
  }

  typedef loss-reason-enum {
    description "Best-path loss reason";
    type enumeration {
      enum "none" {
        value 0;
      }
      enum "invalid";
      enum "personality";
      enum "distance";
      enum "preference";
      enum "tloc-preference";
      enum "origin-protocol";
      enum "origin-protocol-subtype";
      enum "origin-metric";
      enum "peer-id";
      enum "tloc-id";
      enum "ultimate-tloc-id";
      enum "stale-entry";
      enum "site-id";
      enum "omp-version";
      enum "tloc-gen-id";
      enum "tloc-spi";
      enum "tloc-action";
    }
  }

  typedef mcast-route-enum {
    description "Multicast route type";
    type enumeration {
      enum "(*,G)";
      enum "(S,G)";
    }
  }

  container omp {
    description "OMP information";
    when
      "(/viptela-system:system/viptela-system:personality = 'vsmart') or
       (/viptela-system:system/viptela-system:personality = 'vedge')";
    leaf shutdown {
      description "Enable/disable OMP";
      type boolean;
      default "false";
    }
    leaf overlay-as {
      description "Overlay AS number <1..4294967295> or <XX.YY>";
      when "(/viptela-system:system/viptela-system:personality = 'vedge')";
      type viptela:asnum-type;
    }
    leaf send-path-limit {
      description "Maximum number of paths sent for a prefix";
      type uint8 {
        description "<1..16>";
        range "1..16";
      }
      default "4";
    }
    leaf send-backup-paths {
      description "Enable/Disable transmission of backup paths";
      when "/viptela-system:system/viptela-system:personality = 'vsmart'";
      type boolean;
      default "false";
    }
    leaf discard-rejected {
      description "Enable/Disable storage of information rejected by policy";
      when "/viptela-system:system/viptela-system:personality = 'vsmart'";
      type boolean;
      default "false";
    }
    leaf ecmp-limit {
      description "Maximum paths installed in RTM for a prefix";
      when "/viptela-system:system/viptela-system:personality != 'vsmart'";
      type uint8 {
        description "<1..16>";
        range "1..16";
      }
      default "4";
    }
    leaf graceful-restart {
      description "Enable/Disable graceful restart";
      type boolean;
      default "true";
    }
    leaf multithreading {
      description "Enable/Disable multithreading for OMP operations";
      type boolean;
      default "true";
    }
    container timers {
      description "Set timers";
      leaf holdtime {
        description "Hold time";
        type uint32 {
          description "<0..65535>";
          range "0..65535";
        }
        default "60";
        must "((../holdtime = 0) or (../holdtime >= 3))" {
          error-message "Holdtime should be greater than 3 seconds";
        }
      }
      leaf advertisement-interval {
        description "Advertisement interval";
        type uint32 {
          description "<0..65535>";
          range "0..65535";
        }
        default "1";
      }
      leaf graceful-restart-timer {
        description "Graceful restart timer, in seconds";
        type uint32 {
          description "<1..604800> seconds";
          range "1..604800";
        }
        default "43200";
        must
          "(/viptela-system:system/viptela-system:personality != 'vedge') or
           (((/viptela-system:system/viptela-system:personality = 'vedge') and
           (/viptela-system:system/viptela-system:device-model = 'vedge-100-M' or
           /viptela-system:system/viptela-system:device-model = 'vedge-1000' or
           /viptela-system:system/viptela-system:device-model = 'vedge-100-WM' or
           /viptela-system:system/viptela-system:device-model = 'vedge-100-M2' or
           /viptela-system:system/viptela-system:device-model = 'vedge-1000' or
           /viptela-system:system/viptela-system:device-model = 'vedge-2000' or
           /viptela-system:system/viptela-system:device-model = 'vedge-100' or
           /viptela-system:system/viptela-system:device-model = 'vedge-100-W2' or
           /viptela-system:system/viptela-system:device-model = 'vedge-100-B' or
           /viptela-system:system/viptela-system:device-model = 'vedge-cloud' or
           /viptela-system:system/viptela-system:device-model = 'vedge-sim' or
           /viptela-system:system/viptela-system:device-model = 'vedge-ISR1100-4G' or
           /viptela-system:system/viptela-system:device-model = 'vedge-ISR1100-4GLTE' or
           /viptela-system:system/viptela-system:device-model = 'vedge-ISR1100-6G')) and
           ((2 * .) <= (/viptela-security:security/viptela-security:ipsec/viptela-security:rekey))) or
           ((/viptela-system:system/viptela-system:personality = 'vedge') and
           (/viptela-system:system/viptela-system:device-model != 'vedge-100-M' or
           /viptela-system:system/viptela-system:device-model != 'vedge-1000' or
           /viptela-system:system/viptela-system:device-model != 'vedge-100-WM' or
           /viptela-system:system/viptela-system:device-model != 'vedge-100-M2' or
           /viptela-system:system/viptela-system:device-model != 'vedge-1000' or
           /viptela-system:system/viptela-system:device-model != 'vedge-2000' or
           /viptela-system:system/viptela-system:device-model != 'vedge-100' or
           /viptela-system:system/viptela-system:device-model != 'vedge-100-W2' or
           /viptela-system:system/viptela-system:device-model != 'vedge-100-B' or
           /viptela-system:system/viptela-system:device-model != 'vedge-cloud' or
           /viptela-system:system/viptela-system:device-model = 'vedge-sim' or
           /viptela-system:system/viptela-system:device-model = 'vedge-ISR1100-4G' or
           /viptela-system:system/viptela-system:device-model = 'vedge-ISR1100-4GLTE' or
           /viptela-system:system/viptela-system:device-model != 'vedge-ISR1100-6G'))" {
          error-message "IPSec Rekey timer is configured. Rekey timer should be atleast 2 times the Graceful-restart timer";
        }
      }
      leaf eor-timer {
        description "End of RIB timer, in seconds";
        type uint32 {
          description "<1..3600> seconds";
          range "1..3600";
        }
        default "300";
      }
      leaf multithreading-high-timer {
        description "Multithreading high priority timer";
        default "400";
        type uint32 {
          description "<0..65535>";
          range "0..65535";
        }
      }
      leaf multithreading-low-timer {
        description "Multithreading low priority timer";
        default "1";
        type uint32 {
          description "<0..65535>";
          range "0..65535";
        }
      }
    }
    list advertise {
      description "Advertise routes";
      when "/viptela-system:system/viptela-system:personality = 'vedge'";
      key "protocol";
      must
        "(protocol != 'ospf') or
         ((protocol = 'ospf') and (count(route) = 1))" {
        error-message "route-type missing";
      }
      leaf protocol {
        type enumeration {
          enum "bgp";
          enum "ospf";
          enum "connected";
          enum "static";
          enum "eigrp";
          enum "lisp";
          enum "isis";
        }
      }
      leaf-list route {
        when "../protocol = 'ospf'";
        type enumeration {
          enum "external";
        }
      }
    }
    container summary {
      config false;
      description "Display OMP summary";
      leaf operstate {
        description "Operational state";
        type viptela:state-enum;
      }
      leaf adminstate {
        description "Administration state";
        type viptela:state-enum;
      }
      leaf devicetype {
        description "Device personality";
        type viptela:personality-enum-oper;
      }
      leaf ompuptime {
        description "OMP uptime";
        type string;
      }
      leaf ompdowntime {
        description "OMP downtime";
        type string;
      }
      leaf routes-received {
        description "Routes received";
        type uint32;
      }
      leaf routes-installed {
        description "Routes installed";
        type uint32;
      }
      leaf routes-sent {
        description "Routes sent";
        type uint32;
      }
      leaf tlocs-received {
        description "TLOCs received";
        type uint32;
      }
      leaf tlocs-installed {
        description "TLOCs installed";
        type uint32;
      }
      leaf tlocs-sent {
        description "TLOCs sent";
        type uint32;
      }
      leaf services-received {
        description "Services received";
        type uint32;
      }
      leaf services-installed {
        description "Services installed";
        type uint32;
      }
      leaf services-sent {
        description "Services sent";
        type uint32;
      }
      leaf mcast-routes-received {
        description "Multicast routes received";
        type uint32;
      }
      leaf mcast-routes-installed {
        description "Multicast routes installed";
        type uint32;
      }
      leaf mcast-routes-sent {
        description "Multicast routes sent";
        type uint32;
      }
      leaf hello-received {
        description "Hello packets received";
        type uint32;
      }
      leaf hello-sent {
        description "Hello packets sent";
        type uint32;
      }
      leaf handshake-received {
        description "Handshake packets received";
        type uint32;
      }
      leaf handshake-sent {
        description "Handshake packets sent";
        type uint32;
      }
      leaf alert-received {
        description "Alert packets received";
        type uint32;
      }
      leaf alert-sent {
        description "Alert packets sent";
        type uint32;
      }
      leaf inform-received {
        description "Inform packets received";
        type uint32;
      }
      leaf inform-sent {
        description "Inform packets sent";
        type uint32;
      }
      leaf update-received {
        description "Update packets received";
        type uint32;
      }
      leaf update-sent {
        description "Update packets sent";
        type uint32;
      }
      leaf policy-received {
        description "Policy packets received";
        type uint32;
      }
      leaf policy-sent {
        description "Policy packets sent";
        type uint32;
      }
      leaf packets-received {
        description "Total OMP packets received";
        type uint32;
      }
      leaf packets-sent {
        description "Total OMP packets sent";
        type uint32;
      }
      leaf vsmart-peers {
        description "Number of vSmart peers in up state";
        type uint32;
      }
      leaf vedge-peers {
        when "/viptela-system:system/viptela-system:personality = 'vsmart'";
        description "Number of vEdge peers in up state";
        type uint32;
      }
      list peers {
        description "Display OMP peers";
        key "peer";
        leaf peer {
          description "Peer address";
          type inet:ip-address;
        }
        leaf type {
          description "Peer personality";
          type viptela:personality-enum-oper;
        }
        leaf domain-id {
          description "Domain ID";
          type viptela:oper-domain-id;
        }
        leaf site-id {
          description "Site ID";
          type viptela:site-id;
        }
        leaf state {
          description "State";
          type viptela:peer-state;
        }
        leaf version {
          type uint8;
        }
        leaf legit {
          description "Legitimate";
          type enumeration {
            enum "no";
            enum "yes";
          }
        }
        leaf upcount {
          description "Up count";
          type uint32;
        }
        leaf downcount {
          description "Down count";
          type uint32;
        }
        leaf lastuptime {
          description "Last uptime";
          type yang:date-and-time;
        }
        leaf lastdowntime {
          description "Last downtime";
          type yang:date-and-time;
        }
        leaf up-time {
          description "Uptime";
          type string;
        }
        leaf down-time {
          description "Downtime";
          type string;
        }
        leaf holdtime {
          description "Negotiated holdtime";
          type uint32;
        }
        leaf sitepolicy {
          description "Site policy";
          type string;
        }
        leaf policyin {
          description "Inbound policy";
          type string;
        }
        leaf policyout {
          description "Outbound policy";
          type string;
        }
        leaf graceful-restart {
          description "Graceful restart status";
          type enumeration {
            enum "supported";
            enum "not-supported";
            enum "in-progress";
          }
        }
        leaf graceful-restart-interval {
          description "Graceful restart interval";
          type uint32;
        }
        leaf hello-received {
          description "Hello packets received";
          type uint32;
        }
        leaf hello-sent {
          description "Hello packets sent";
          type uint32;
        }
        leaf handshake-received {
          description "Handshake packets received";
          type uint32;
        }
        leaf handshake-sent {
          description "Handshake packets sent";
          type uint32;
        }
        leaf alert-received {
          description "Alert packets received";
          type uint32;
        }
        leaf alert-sent {
          description "Alert packets sent";
          type uint32;
        }
        leaf inform-received {
          description "Inform packets received";
          type uint32;
        }
        leaf inform-sent {
          description "Inform packets sent";
          type uint32;
        }
        leaf update-received {
          description "Update packets received";
          type uint32;
        }
        leaf update-sent {
          description "Update packets sent";
          type uint32;
        }
        leaf policy-received {
          description "Policy packets received";
          type uint32;
        }
        leaf policy-sent {
          description "Policy packets sent";
          type uint32;
        }
        leaf packets-received {
          description "Total OMP packets received";
          type uint32;
        }
        leaf packets-sent {
          description "Total OMP packets sent";
          type uint32;
        }
        leaf routes-received {
          description "Routes received";
          type uint32;
        }
        leaf routes-installed {
          description "Routes installed";
          type uint32;
        }
        leaf routes-sent {
          description "Routes sent";
          type uint32;
        }
        leaf tlocs-received {
          description "TLOCs received";
          type uint32;
        }
        leaf tlocs-installed {
          description "TLOCs installed";
          type uint32;
        }
        leaf tlocs-sent {
          description "TLOCs sent";
          type uint32;
        }
        leaf services-received {
          description "Services received";
          type uint32;
        }
        leaf services-installed {
          description "Services installed";
          type uint32;
        }
        leaf services-sent {
          description "Services sent";
          type uint32;
        }
        leaf mcast-routes-received {
          description "Multicast routes received";
          type uint32;
        }
        leaf mcast-routes-installed {
          description "Multicast routes installed";
          type uint32;
        }
        leaf mcast-routes-sent {
          description "Multicast routes sent";
          type uint32;
        }
        leaf control-up {
          description "Control connection UP";
          type enumeration {
            enum "no";
            enum "yes";
          }
        }
        leaf staging {
          description "Device under staging";
          type enumeration {
            enum "no";
            enum "yes";
          }
        }
        leaf refresh {
          description "Refresh status";
          type enumeration {
            enum "supported";
            enum "not-supported";
          }
        }
        leaf overlay-id {
          description "Overlay ID";
          type viptela:oper-domain-id;
        }
        leaf routes-received-ipv6 {
          description "Routes received IPv6";
          type uint32;
        }
        leaf routes-installed-ipv6 {
          description "Routes installed IPv6";
          type uint32;
        }
        leaf routes-sent-ipv6 {
          description "Routes sent IPv6";
          type uint32;
        }
        leaf routes-received-total {
          description "Total Routes Received";
          type uint32;
        }
        leaf routes-installed-total {
          description "Total Routes Installed";
          type uint32;
        }
        leaf routes-sent-total {
          description "Total Routes Sent";
          type uint32;
        }
        leaf services-received-ipv6 {
          description "Services IPv6 received";
          type uint32;
        }
        leaf services-installed-ipv6 {
          description "Services IPv6 installed";
          type uint32;
        }
        leaf services-sent-ipv6 {
          description "Services IPv6 sent";
          type uint32;
        }
      }
    }
    container snmp-summary {
      config false;
    }
    container routes-table {
      description "Display routes";
      list family {
        config false;
        key "address-family";
        leaf address-family {
          type addr-family-enum;
        }
        list entries {
          key "vpn-id prefix";
          leaf vpn-id {
            type viptela:vpn-id;
          }
          leaf prefix {
            type inet:ip-prefix;
          }
          list received {
            key "from-peer path-id";
            leaf from-peer {
              type inet:ip-address;
            }
            leaf path-id {
              type uint32;
            }
            leaf label {
              type uint32;
            }
            leaf status {
              description "RIB-in status";
              type rib-in-status-type;
            }
            leaf loss-reason {
              type loss-reason-enum;
            }
            leaf lost-to-peer {
              type inet:ip-address;
            }
            leaf lost-to-path-id {
              type uint32;
            }
            list attributes {
              key "attribute-type";
              leaf attribute-type {
                type attribute-type-enum;
              }
              container tloc {
                uses viptela:tloc-group {
                  refine "ip";
                  refine "color";
                  refine "encap";
                }
              }
              container origin {
                uses viptela:origin-group {
                  refine "protocol";
                  refine "metric";
                }
              }
              leaf domain-id {
                type viptela:oper-domain-id;
              }
              leaf site-id {
                type viptela:site-id;
              }
              leaf preference {
                type viptela:route-preference;
              }
              leaf tag {
                type viptela:route-tag;
              }
              leaf unknown-attribute-len {
                type uint16;
              }
              leaf originator {
                type inet:ipv4-address;
              }
              container ultimate-tloc {
                uses viptela:tloc-group {
                  refine "ip";
                  refine "color";
                  refine "encap";
                }
              }
              leaf ultimate-tloc-action {
                type viptela:ultimate-tloc-enum;
              }
              leaf overlay-id {
                type viptela:oper-domain-id;
              }
              leaf as-path {
                type string;
              }
            }
          }
          list advertised {
            key "to-peer";
            leaf to-peer {
              type inet:ip-address;
            }
            list paths {
              key "advertise-id";
              leaf advertise-id {
                type uint32;
              }
              list attributes {
                key "path-id";
                leaf path-id {
                  type uint32;
                }
                leaf label {
                  type uint32;
                }
                container tloc {
                  uses viptela:tloc-group {
                    refine "ip";
                    refine "color";
                    refine "encap";
                  }
                }
                container origin {
                  uses viptela:origin-group {
                    refine "protocol";
                    refine "metric";
                  }
                }
                leaf domain-id {
                  type viptela:oper-domain-id;
                }
                leaf site-id {
                  type viptela:site-id;
                }
                leaf preference {
                  type viptela:route-preference;
                }
                leaf tag {
                  type viptela:route-tag;
                }
                leaf unknown-attribute-len {
                  type uint16;
                }
                leaf originator {
                  type inet:ipv4-address;
                }
                container ultimate-tloc {
                  uses viptela:tloc-group {
                    refine "ip";
                    refine "color";
                    refine "encap";
                  }
                }
                leaf ultimate-tloc-action {
                  type viptela:ultimate-tloc-enum;
                }
                leaf overlay-id {
                  type viptela:oper-domain-id;
                }
                leaf as-path {
                  type string;
                }
              }
            }
          }
        }
      }
    }
    container best-match-route {
      description "Display best-match route";
      list family {
        config false;
        key "address-family";
        leaf address-family {
          type addr-family-enum;
        }
        list entries {
          key "vpn-id route-addr";
          leaf vpn-id {
            type viptela:vpn-id;
          }
          leaf route-addr {
            type inet:ip-address;
          }
          leaf prefix {
            type inet:ip-prefix;
          }
          list received {
            key "from-peer path-id";
            leaf from-peer {
              type inet:ip-address;
            }
            leaf path-id {
              type uint32;
            }
            leaf label {
              type uint32;
            }
            leaf status {
              description "RIB-in status";
              type rib-in-status-type;
            }
            leaf loss-reason {
              type loss-reason-enum;
            }
            leaf lost-to-peer {
              type inet:ip-address;
            }
            leaf lost-to-path-id {
              type uint32;
            }
            list attributes {
              key "pseudo-key";
              leaf pseudo-key {
                type uint32;
              }
              leaf attribute-type {
                type attribute-type-enum;
              }
              container tloc {
                uses viptela:tloc-group {
                  refine "ip";
                  refine "color";
                  refine "encap";
                }
              }
              container origin {
                uses viptela:origin-group {
                  refine "protocol";
                  refine "metric";
                }
              }
              leaf domain-id {
                type viptela:oper-domain-id;
              }
              leaf site-id {
                type viptela:site-id;
              }
              leaf preference {
                type viptela:route-preference;
              }
              leaf tag {
                type viptela:route-tag;
              }
              leaf unknown-attribute-len {
                type uint16;
              }
              leaf originator {
                type inet:ipv4-address;
              }
              leaf overlay-id {
                type viptela:oper-domain-id;
              }
              leaf as-path {
                type string;
              }
            }
          }
          list advertised {
            key "to-peer";
            leaf to-peer {
              type inet:ip-address;
            }
            list paths {
              key "advertise-id";
              leaf advertise-id {
                type uint32;
              }
              list attributes {
                key "path-id";
                leaf path-id {
                  type uint32;
                }
                leaf label {
                  type uint32;
                }
                container tloc {
                  uses viptela:tloc-group {
                    refine "ip";
                    refine "color";
                    refine "encap";
                  }
                }
                container origin {
                  uses viptela:origin-group {
                    refine "protocol";
                    refine "metric";
                  }
                }
                leaf domain-id {
                  type viptela:oper-domain-id;
                }
                leaf site-id {
                  type viptela:site-id;
                }
                leaf preference {
                  type viptela:route-preference;
                }
                leaf tag {
                  type viptela:route-tag;
                }
                leaf unknown-attribute-len {
                  type uint16;
                }
                leaf originator {
                  type inet:ipv4-address;
                }
                leaf overlay-id {
                  type viptela:oper-domain-id;
                }
                leaf as-path {
                  type string;
                }
              }
            }
          }
        }
      }
    }
    container tloc-paths {
      config false;
      description "Display TLOC paths";
      list entries {
        key "ip color encap";
        uses viptela:tloc-group {
          refine "ip";
          refine "color";
          refine "encap";
        }
        list paths {
          when "/viptela-system:system/viptela-system:personality != 'vsmart'";
          key "index";
          leaf index {
            type uint32;
          }
          leaf preference {
            type viptela:route-preference;
          }
          leaf mtu {
            type uint32;
          }
          leaf bfd-status {
            type bfd-status-enum;
          }
          list links {
            when "/viptela-system:system/viptela-system:personality != 'vsmart'";
            key "link-index";
            leaf link-index {
              type uint32;
            }
            container from-tloc {
              uses viptela:tloc-group {
                refine "ip";
                refine "color";
                refine "encap";
              }
            }
            container to-tloc {
              uses viptela:tloc-group {
                refine "ip";
                refine "color";
                refine "encap";
              }
            }
            leaf label {
              type uint32;
            }
          }
          leaf path-status {
            type path-status-enum;
          }
          leaf stale {
            type boolean;
          }
        }
      }
    }
    container omp-tlocs {
      description "Display TLOCs";
      list family {
        config false;
        key "address-family";
        leaf address-family {
          type addr-family-enum;
        }
        list entries {
          key "ip color encap";
          uses viptela:tloc-group {
            refine "ip";
            refine "color";
            refine "encap";
          }
          list received {
            key "from-peer";
            leaf from-peer {
              type inet:ip-address;
            }
            leaf status {
              description "RIB-in status";
              type rib-in-status-type;
            }
            leaf loss-reason {
              type loss-reason-enum;
            }
            leaf lost-to-peer {
              type inet:ip-address;
            }
            leaf lost-to-path-id {
              type uint32;
            }
            list attributes {
              key "pseudo-key";
              leaf pseudo-key {
                type uint32;
              }
              leaf attribute-type {
                type attribute-type-enum;
              }
              container tloc-encap {
                uses viptela:tloc-encap-group {
                  refine "key";
                  refine "proto";
                  refine "spi";
                  refine "auth-type";
                  refine "encrypt-type";
                }
              }
              container tloc-map-public {
                uses viptela:tloc-map-group {
                  refine "ip";
                  refine "port";
                }
              }
              container tloc-map-private {
                uses viptela:tloc-map-group {
                  refine "ip";
                  refine "port";
                }
              }
              container tloc-map-v6-public {
                uses viptela:tloc-map-group {
                  refine "ip";
                  refine "port";
                }
              }
              container tloc-map-v6-private {
                uses viptela:tloc-map-group {
                  refine "ip";
                  refine "port";
                }
              }
              leaf bfd-status {
                when "/viptela-system:system/viptela-system:personality != 'vsmart'";
                type bfd-status-enum;
              }
              leaf domain-id {
                type viptela:oper-domain-id;
              }
              leaf site-id {
                type viptela:site-id;
              }
              leaf preference {
                type viptela:route-preference;
              }
              leaf tag {
                type viptela:route-tag;
              }
              leaf stale {
                type uint8;
              }
              leaf carrier {
                type viptela:carrier-enum;
              }
              leaf-list groups {
                type viptela:group-id;
              }
              leaf border {
                type uint8;
              }
              leaf unknown-attribute-len {
                type uint16;
              }
              leaf weight {
                type uint32;
              }
              leaf gen-id {
                type uint32;
              }
              leaf version {
                type uint32;
              }
              leaf originator {
                type inet:ipv4-address;
              }
              leaf restrict {
                type uint8;
              }
              leaf overlay-id {
                type viptela:oper-domain-id;
              }
            }
          }
          list advertised {
            key "to-peer";
            leaf to-peer {
              type inet:ip-address;
            }
            list attributes {
              key "attribute-id";
              leaf attribute-id {
                type uint32;
              }
              container tloc-encap {
                uses viptela:tloc-encap-group {
                  refine "key";
                  refine "proto";
                  refine "spi";
                  refine "auth-type";
                  refine "encrypt-type";
                }
              }
              container tloc-map-public {
                uses viptela:tloc-map-group {
                  refine "ip";
                  refine "port";
                }
              }
              container tloc-map-private {
                uses viptela:tloc-map-group {
                  refine "ip";
                  refine "port";
                }
              }
              container tloc-map-v6-public {
                uses viptela:tloc-map-group {
                  refine "ip";
                  refine "port";
                }
              }
              container tloc-map-v6-private {
                uses viptela:tloc-map-group {
                  refine "ip";
                  refine "port";
                }
              }
              leaf domain-id {
                type viptela:oper-domain-id;
              }
              leaf site-id {
                type viptela:site-id;
              }
              leaf preference {
                type viptela:route-preference;
              }
              leaf tag {
                type viptela:route-tag;
              }
              leaf stale {
                type uint8;
              }
              leaf carrier {
                type viptela:carrier-enum;
              }
              leaf-list groups {
                type viptela:group-id;
              }
              leaf border {
                type uint8;
              }
              leaf unknown-attribute-len {
                type uint16;
              }
              leaf weight {
                type uint32;
              }
              leaf gen-id {
                type uint32;
              }
              leaf version {
                type uint32;
              }
              leaf originator {
                type inet:ipv4-address;
              }
              leaf restrict {
                type uint8;
              }
              leaf overlay-id {
                type viptela:oper-domain-id;
              }
            }
          }
        }
      }
    }
    container services {
      description "Display services";
      list family {
        config false;
        key "address-family";
        leaf address-family {
          type addr-family-enum;
        }
        list entries {
          config false;
          key "vpn-id service originator";
          uses viptela:service-oper-group {
            refine "vpn-id";
            refine "service";
            refine "originator";
          }
          list received {
            key "from-peer path-id";
            leaf from-peer {
              type inet:ip-address;
            }
            leaf path-id {
              type uint32;
            }
            leaf label {
              type uint32;
            }
            leaf status {
              description "RIB-in status";
              type rib-in-status-type;
            }
            leaf loss-reason {
              type loss-reason-enum;
            }
            leaf lost-to-peer {
              type inet:ip-address;
            }
            leaf lost-to-path-id {
              type uint32;
            }
          }
          list advertised {
            key "to-peer";
            leaf to-peer {
              type inet:ip-address;
            }
          }
        }
      }
    }
    container multicast-auto-discover {
      description "Display autodiscovered multicast routes";
      list family {
        config false;
        key "address-family";
        leaf address-family {
          type addr-family-enum;
        }
        list entries {
          key "vpn-id source-originator";
          leaf vpn-id {
            type viptela:vpn-id;
          }
          leaf source-originator {
            type inet:ipv4-address;
          }
          list received {
            key "from-peer";
            leaf from-peer {
              type inet:ip-address;
            }
            leaf status {
              description "RIB-in status";
              type rib-in-status-type;
            }
            leaf loss-reason {
              type loss-reason-enum;
            }
          }
          list advertised {
            key "to-peer";
            leaf to-peer {
              type inet:ip-address;
            }
          }
        }
      }
    }
    container multicast-routes {
      description "Display multicast Joins";
      list family {
        config false;
        key "address-family";
        leaf address-family {
          type addr-family-enum;
        }
        list entries {
          key "type vpn-id source-originator destination group source";
          leaf type {
            type mcast-route-enum;
          }
          leaf vpn-id {
            type viptela:vpn-id;
          }
          leaf source-originator {
            type inet:ipv4-address;
          }
          leaf destination {
            type inet:ipv4-address;
          }
          leaf group {
            type inet:ipv4-address;
          }
          leaf source {
            type inet:ipv4-address;
          }
          list received {
            key "from-peer";
            leaf from-peer {
              type inet:ip-address;
            }
            leaf rp {
              type inet:ipv4-address;
            }
            leaf-list received-prunes {
              type inet:ipv4-address;
            }
            leaf status {
              description "RIB-in status";
              type rib-in-status-type;
            }
            leaf loss-reason {
              type loss-reason-enum;
            }
          }
          list advertised {
            key "to-peer";
            leaf to-peer {
              type inet:ip-address;
            }
            leaf rp {
              type inet:ipv4-address;
            }
            leaf-list advertised-prunes {
              type inet:ipv4-address;
            }
          }
        }
      }
    }
    container cloudexpress {
      description "Display cloudexpress gateway application routes";
      list entries {
        config false;
        key "vpn-id originator app-id";
        leaf vpn-id {
          type viptela:vpn-id;
        }
        leaf originator {
          type inet:ipv4-address;
        }
        leaf app-id {
          type uint32;
        }
        leaf app-name {
          type viptela:named-type;
        }
        list received {
          key "from-peer";
          leaf from-peer {
            type inet:ip-address;
          }
          leaf status {
            description "RIB-in status";
            type rib-in-status-type;
          }
          leaf loss-reason {
            type loss-reason-enum;
          }
          leaf latency {
            type uint32;
          }
          leaf loss {
            type uint32;
          }
        }
        list advertised {
          key "to-peer";
          leaf to-peer {
            type inet:ip-address;
          }
          leaf latency {
            type uint32;
          }
          leaf loss {
            type uint32;
          }
        }
      }
    }
  }
  notification omp-number-of-vsmarts-change {
    uses viptela:common-notification-header;
    leaf number-of-vsmarts {
      type uint32;
    }
  }
  notification omp-state-change {
    uses viptela:common-notification-header;
    leaf new-state {
      type viptela:oper-state;
    }
  }
  notification omp-peer-state-change {
    uses viptela:common-notification-header;
    leaf peer {
      type inet:ip-address;
    }
    leaf peer-new-state {
      type viptela:peer-state;
    }
  }
  notification omp-tloc-state-change {
    uses viptela:common-notification-header;
    leaf omp-address-family {
      type af-type-enum;
    }
    container tloc {
      uses viptela:tloc-group;
    }
    leaf new-state {
      type viptela:oper-state;
    }
  }
  notification omp-policy {
    uses viptela:common-notification-header;
    leaf policy {
      type enumeration {
        enum "add";
        enum "delete";
      }
    }
    leaf vsmart-peer {
      type inet:ip-address;
    }
  }
  notification omp-data-policy {
    uses viptela:common-notification-header;
    leaf policy {
      type enumeration {
        enum "add";
        enum "delete";
      }
    }
    leaf vsmart-peer {
      type inet:ip-address;
    }
  }
}
