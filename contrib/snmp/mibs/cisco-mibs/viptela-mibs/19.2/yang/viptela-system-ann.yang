module viptela-system-ann {
  namespace "http://viptela.com/system-ann";
  prefix viptela-system-ann;

  import viptela-system {
    prefix system;
  }

  organization "Viptela, Inc.";
  contact
    "Viptela, Inc.
     Email:support@viptela.com";
  description
    "Defines annotations for system module";
}
