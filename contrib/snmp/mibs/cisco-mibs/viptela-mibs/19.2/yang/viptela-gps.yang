module viptela-gps {
  namespace "http://viptela.com/gps";
  prefix viptela-gps;

  import ietf-inet-types {
    prefix inet;
  }
  import viptela-common {
    prefix viptela;
  }
  import viptela-system {
    prefix viptela-system;
  }
  import ietf-yang-types {
    prefix yang;
  }

  organization "Viptela, Inc.";
  contact
    "Viptela, Inc.
     Email:yang.model@viptela.com";
  description
    "This module defines the data model for GPS management";

  revision 2019-08-15 {
    description
      "Release version: 19.2";
  }
  revision 2018-11-01 {
    description
      "Release version: 18.4";
  }
  revision 2018-08-20 {
    description
      "Release version: 18.3.1";
  }
  revision 2018-06-25 {
    description
      "Release version: 18.3";
  }
  revision 2018-04-25 {
    description
      "Release version: 18.2";
  }
  revision 2018-03-15 {
    description
      "Release version: 18.1.1";
  }
  revision 2018-01-16 {
    description
      "Release version: 17.2.3";
  }
  revision 2017-11-01 {
    description
      "Release version: 17.2.1";
  }
  revision 2017-08-01 {
    description
      "Release version: 17.2";
  }

  typedef gps-fix {
    description
      "GPS fix";
    type enumeration {
      enum "Invalid" {
        value 0;
      }
      enum "Valid" {
        value 1;
      }
    }
  }
}
