module viptela-global {
  namespace "http://viptela.com/viptela-global";
  prefix viptela-global;

  organization "Viptela, Inc.";
  contact
    "Viptela, Inc.
     Email:support@viptela.com";
  description
    "This module defines global Viptela definitions";

  revision 2019-08-15 {
    description
      "Release version: 19.2";
  }
  revision 2018-11-01 {
    description
      "Release version: 18.4";
  }
  revision 2018-08-20 {
    description
      "Release version: 18.3.1";
  }
  revision 2018-06-25 {
    description
      "Release version: 18.3";
  }
  revision 2018-04-25 {
    description
      "Release version: 18.2";
  }
  revision 2018-03-15 {
    description
      "Release version: 18.1.1";
  }
  revision 2018-01-16 {
    description
      "Release version: 17.2.3";
  }
  revision 2017-11-01 {
    description
      "Release version: 17.2.1";
  }
  revision 2017-08-01 {
    description
      "Release version: 17.2";
  }
  revision 2017-05-25 {
    description
      "Release version: 17.1.1";
  }
  revision 2017-04-06 {
    description
      "Release version: 17.1";
  }
  revision 2017-02-15 {
    description
      "Release version: 16.3.2";
  }
  revision 2017-02-06 {
    description
      "Release version: 16.3.1";
  }
  revision 2016-11-16 {
    description
      "Release version: 16.3";
  }
  revision 2016-10-25 {
    description
      "Release version: 16.2.10";
  }
  revision 2016-10-24 {
    description
      "Release version: 16.2.4";
  }
  revision 2016-08-10 {
    description
      "Release version: 16.2.2";
  }
  revision 2016-08-01 {
    description
      "Release version: 16.2.1";
  }
  revision 2016-06-09 {
    description
      "Release version: 16.2";
  }
  revision 2016-04-22 {
    description
      "Release version: 16.1.1";
  }
  revision 2016-03-15 {
    description
      "Release version: 16.1";
  }
  revision 2016-01-30 {
    description
      "Release version: 15.4.3";
  }
  revision 2015-12-28 {
    description
      "Release version: 15.4.1";
  }
  revision 2015-12-01 {
    description
      "Release version: 15.4.0";
  }
  revision 2015-10-31 {
    description
      "Release version: 15.3.5";
  }
  revision 2015-09-27 {
    description
      "Release version: 15.3.3";
  }
  revision 2015-09-01 {
    description
      "Release version: 15.3.1";
  }
}
