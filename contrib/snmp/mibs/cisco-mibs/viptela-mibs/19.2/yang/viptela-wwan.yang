module viptela-wwan {
  namespace "http://viptela.com/wwan";
  prefix viptela-wwan;

    prefix tailf;
  }
  import ietf-inet-types {
    prefix inet;
  }
  import viptela-common {
    prefix viptela;
  }
  import viptela-system {
    prefix viptela-system;
  }
  import ietf-yang-types {
    prefix yang;
  }

  organization "Viptela, Inc.";
  contact
    "Viptela, Inc.
     Email:yang.model@viptela.com";
  description
    "This module defines the data model for  cellular management";

  revision 2019-08-15 {
    description
      "Release version: 19.2";
  }
  revision 2018-11-01 {
    description
      "Release version: 18.4";
  }
  revision 2018-08-20 {
    description
      "Release version: 18.3.1";
  }
  revision 2018-06-25 {
    description
      "Release version: 18.3";
  }
  revision 2018-04-25 {
    description
      "Release version: 18.2";
  }
  revision 2018-03-15 {
    description
      "Release version: 18.1.1";
  }
  revision 2018-01-16 {
    description
      "Release version: 17.2.3";
  }
  revision 2017-11-01 {
    description
      "Release version: 17.2.1";
  }
  revision 2017-08-01 {
    description
      "Release version: 17.2";
  }
  revision 2017-05-25 {
    description
      "Release version: 17.1.1";
  }
  revision 2017-04-06 {
    description
      "Release version: 17.1";
  }
  revision 2017-02-15 {
    description
      "Release version: 16.3.2";
  }
  revision 2017-02-06 {
    description
      "Release version: 16.3.1";
  }
  revision 2016-11-16 {
    description
      "Release version: 16.3";
  }
  revision 2016-10-25 {
    description
      "Release version: 16.2.10";
  }
  revision 2016-10-24 {
    description
      "Release version: 16.2.4";
  }
  revision 2016-08-10 {
    description
      "Release version: 16.2.2";
  }
  revision 2016-08-01 {
    description
      "Release version: 16.2.1";
  }
  revision 2016-06-09 {
    description
      "Release version: 16.2";
  }
  revision 2016-04-22 {
    description
      "Release version: 16.1.1";
  }
  revision 2016-03-15 {
    description
      "Release version: 16.1";
  }
  revision 2016-01-30 {
    description
      "Release version: 15.4.3";
  }
  revision 2015-12-28 {
    description
      "Release version: 15.4.1";
  }
  revision 2015-12-01 {
    description
      "Release version: 15.4.0";
  }
  revision 2015-10-31 {
    description
      "Release version: 15.3.5";
  }
  revision 2015-09-27 {
    description
      "Release version: 15.3.3";
  }
  revision 2015-09-01 {
    description
      "Release version: 15.3.1";
  }
  revision 2015-07-01 {
    description
      "Release version: 15.3";
  }

  typedef wwan-registration-status {
    description
      "Registration status";
    type enumeration {
      enum "Not registered";
      enum "Registered";
      enum "Searching";
      enum "Registration denied";
      enum "Unknown";
    }
  }

  typedef wwan-pdn-type {
    description
      "Packet data network type";
    type enumeration {
      enum "ipv4" {
        value 0;
      }
      enum "ipv6" {
        value 2;
      }
      enum "ipv46" {
        value 3;
      }
    }
  }

  typedef wwan-auth-type {
    description
      "Authentication";
    type enumeration {
      enum "None";
      enum "PAP";
      enum "CHAP";
      enum "PAP/CHAP";
    }
  }

  typedef wwan-radio-enum {
    description
      "Radio mode";
    type enumeration {
      enum "No Service";
      enum "AMPS";
      enum "CDMA";
      enum "GSM";
      enum "HDR";
      enum "WCDMA";
      enum "GPS";
      enum "Not Used";
      enum "WLAN";
      enum "LTE";
    }
  }

  typedef wwan-sim-enum {
    description
      "SIM Status";
    type enumeration {
      enum "Not Present";
      enum "Present";
      enum "Error";
    }
  }

  typedef wwan-activation-enum {
    description
      "Activation Status";
    type enumeration {
      enum "Not activated";
      enum "Activated";
      enum "Not applicable";
    }
  }

  typedef wwan-domain-enum {
    description
      "Packet-switched domain state";
    type enumeration {
      enum "Unknown" {
        value 0;
      }
      enum "Attached" {
        value 1;
      }
      enum "Detached" {
        value 2;
      }
    }
  }

  typedef wwan-bearer-enum {
    description
      "Data bearer technology";
    type enumeration {
      enum "Unknown" {
        value 0;
      }
      enum "CDMA 1x" {
        value 1;
      }
      enum "CDMA 1xEV-DO Rev 0" {
        value 2;
      }
      enum "GPRS" {
        value 3;
      }
      enum "UMTS" {
        value 4;
      }
      enum "CDMA 1xEV-DO Rev A" {
        value 5;
      }
      enum "EDGE" {
        value 6;
      }
      enum "HSDPA AND WCDMA" {
        value 7;
      }
      enum "WCDMA AND HSUPA" {
        value 8;
      }
      enum "HSDPA AND HSUPA" {
        value 9;
      }
      enum "LTE" {
        value 10;
      }
      enum "CDMA EHRPD" {
        value 11;
      }
      enum "HSDPA+ and WCDMA" {
        value 12;
      }
      enum "HSDPA+ and HSUPA" {
        value 13;
      }
      enum "DC-HSDPA+ and WCDMA" {
        value 14;
      }
      enum "DC-HSDPA+ and HSUPA" {
        value 15;
      }
      enum "HSDPA+ and 64QAM" {
        value 16;
      }
      enum "HSDPA+, 64QAM and HSUPA" {
        value 17;
      }
      enum "TDSCDMA" {
        value 18;
      }
      enum "TDSCDMA and HSDPA" {
        value 19;
      }
    }
  }

  typedef wwan-qos-enum {
    description
      "QoS flow state";
    type enumeration {
      enum "Activated" {
        value 1;
      }
      enum "Modified" {
        value 2;
      }
      enum "Deleted" {
        value 3;
      }
      enum "Suspended" {
        value 4;
      }
      enum "Enabled" {
        value 5;
      }
      enum "Disabled" {
        value 6;
      }
    }
  }

  typedef wwan-status-enum {
    description
      "Status";
    type enumeration {
      enum "Inactive";
      enum "Active";
    }
  }

  container cellular {
    description "Configure cellular";
    when
      "(/viptela-system:system/viptela-system:personality = 'vedge') and 
       (/viptela-system:system/viptela-system:device-model = 'vedge-1000' or
        /viptela-system:system/viptela-system:device-model = 'vedge-100-M' or 
        /viptela-system:system/viptela-system:device-model = 'vedge-100-WM' or 
        /viptela-system:system/viptela-system:device-model = 'vedge-100-M2' or
        /viptela-system:system/viptela-system:device-model = 'vedge-ISR1100-4G' or
        /viptela-system:system/viptela-system:device-model = 'vedge-ISR1100-4GLTE' or
        /viptela-system:system/viptela-system:device-model = 'vedge-ISR1100-6G')";
    list cellular-instance {
      description "List of cellular radios";
      key "if-name";
      leaf if-name {
        description "Interface name";
        type viptela:named-type;
      }
      list profile {
        description "Add, modify, or delete profile";
        key "profile-id";
        leaf profile-id {
          description "Profile ID";
          type uint8 {
            range "1..16";
          }
        }
        leaf pdn-type {
          description "Packet data network type";
          type wwan-pdn-type;
        }
        leaf apn {
          description "Access point name";
          type string {
            length "1..32";
          }
        }
        leaf name {
          description "Profile name";
          type string {
            length "1..14";
          }
        }
        leaf auth {
          description "Authentication";
          type wwan-auth-type;
        }
        leaf ip-addr {
          description "Assigned IP address";
          type inet:ipv4-address;
        }
        leaf primary-dns {
          description "Primary DNS address";
          type inet:ipv4-address;
        }
        leaf secondary-dns {
          description "Secondary DNS address";
          type inet:ipv4-address;
        }
        leaf user-name {
          description "Profile username";
          type string {
            length "1..32";
          }
        }
        leaf user-pass {
          description "Profile password";
          type aes-cfb-128-encrypted-string {
            description "Cleartext or AES encrypted key";
          }
        }
      }
    }
    list radio {
      description "Display cellular radio information";
      config false;
      key "if-name";
      leaf if-name {
        description "Interface name";
        type viptela:named-type;
      }
      leaf band {
        description "Frequency band";
        type uint8;
      }
      leaf bandwidth {
        description "Bandwidth";
        type decimal64 {
          fraction-digits 1;
        }
      }
      leaf tx-channel {
        description "Transmit channel";
        type uint16;
      }
      leaf rx-channel {
        description "Receive channel";
        type uint16;
      }
      leaf rssi {
        description "Received signal strength indicator";
        type int8;
      }
      leaf rsrp {
        description "Reference signal receive power";
        type int16;
      }
      leaf rsrp-comment {
        description "RSRP value classification";
        type string {
          length "1..16";
        }
      }
      leaf rsrq {
        description "Reference signal receive quality";
        type int8;
      }
      leaf rsrq-comment {
        description "RSRQ value classification";
        type string {
          length "1..16";
        }
      }
      leaf snr {
        description "Signal-to-noise ratio";
        type decimal64 {
          fraction-digits 2;
        }
      }
      leaf snr-comment {
        description "SNR value classification";
        type string {
          length "1..16";
        }
      }
      leaf ecio {
        description "EC/IO";
        type decimal64 {
          fraction-digits 2;
        }
      }
      leaf sinr {
        description "SINR";
        type decimal64 {
          fraction-digits 2;
        }
      }
      leaf io {
        description "Received IO";
        type int32;
      }
      leaf mode {
        description "Radio mode";
        type wwan-radio-enum;
      }
      leaf band-class {
        description "Band class";
        type string {
          length "1..64";
        }
      }
      leaf channel {
        description "Active channel";
        type uint16;
      }
    }
    list sessions {
      description "Display cellular data session information";
      config false;
      key "if-name session-id";
      leaf if-name {
        description "Interface name";
        type viptela:named-type;
      }
      leaf session-id {
        description "Session ID";
        type uint8;
      }
      leaf data-bearer {
        description "Data bearer technology";
        type string {
          length "1..32";
        }
      }
      leaf dormancy-state {
        description "Dormancy state";
        type string {
          length "1..16";
        }
      }
      leaf active-profile {
        description "Active profile";
        type uint8 {
          range "1..16";
        }
      }
      leaf rx-packets {
        description "Receive packets ";
        type yang:counter64;
      }
      leaf rx-drops {
        description "Receive drops";
        type yang:counter64;
      }
      leaf rx-errors {
        description "Receive errors";
        type yang:counter64;
      }
      leaf rx-overflows {
        description "Receive overflows";
        type yang:counter64;
      }
      leaf tx-packets {
        description "Transmit packets ";
        type yang:counter64;
      }
      leaf tx-drops {
        description "Transmit drops";
        type yang:counter64;
      }
      leaf tx-errors {
        description "Transmit errors";
        type yang:counter64;
      }
      leaf tx-overflows {
        description "Transmit overflows";
        type yang:counter64;
      }
      leaf rx-octets {
        description "Receive octets";
        type yang:counter64;
      }
      leaf tx-octets {
        description "Transmit octets";
        type yang:counter64;
      }
      leaf ipv4-addr {
        description "IPv4 address";
        type inet:ipv4-address;
      }
      leaf ipv4-mask {
        description "IPv4 mask length";
        type uint8;
      }
      leaf ipv4-gw {
        description "IPv4 gateway";
        type inet:ipv4-address;
      }
      leaf ipv4-dns-pri {
        description "Primary IPv4 DNS server";
        type inet:ipv4-address;
      }
      leaf ipv4-dns-sec {
        description "Secondary IPv4 DNS server";
        type inet:ipv4-address;
      }
      leaf uptime {
        description "Session uptime";
        type string;
      }
      leaf ip-proto {
        description "IP protocol version";
        type enumeration {
          enum "IPv4 only" {
            value 4;
          }
          enum "IPv6 only" {
            value 6;
          }
          enum "IPv4 and IPv6" {
            value 7;
          }
        }
      }
      leaf ipv6-prefix {
        description "IPv6 prefix";
        type inet:ipv6-address;
      }
      leaf ipv6-prefix-len {
        description "IPv6 prefix length";
        type uint8;
      }
      leaf ipv6-gw-prefix {
        description "IPv6 gateway prefix";
        type inet:ipv6-address;
      }
      leaf ipv6-gw-prefix-len {
        description "IPv6 gateway prefix length";
        type uint8;
      }
      leaf ipv6-dns-pri {
        description "Primary IPv6 DNS server";
        type inet:ipv6-address;
      }
      leaf ipv6-dns-sec {
        description "Secondary IPv6 DNS server";
        type inet:ipv6-address;
      }
      leaf v6-rx-packets {
        description "Receive packets ";
        type yang:counter64;
      }
      leaf v6-rx-drops {
        description "Receive drops";
        type yang:counter64;
      }
      leaf v6-rx-errors {
        description "Receive errors";
        type yang:counter64;
      }
      leaf v6-rx-overflows {
        description "Receive overflows";
        type yang:counter64;
      }
      leaf v6-tx-packets {
        description "Transmit packets ";
        type yang:counter64;
      }
      leaf v6-tx-drops {
        description "Transmit drops";
        type yang:counter64;
      }
      leaf v6-tx-errors {
        description "Transmit errors";
        type yang:counter64;
      }
      leaf v6-tx-overflows {
        description "Transmit overflows";
        type yang:counter64;
      }
      leaf v6-rx-octets {
        description "Receive octets";
        type yang:counter64;
      }
      leaf v6-tx-octets {
        description "Transmit octets";
        type yang:counter64;
      }
    }
    list network {
      description "Display cellular network information";
      config false;
      key "if-name";
      leaf if-name {
        description "Interface name";
        type viptela:named-type;
      }
      leaf reg-status {
        description "Registration status";
        type wwan-registration-status;
      }
      leaf roam-status {
        description "Roaming status";
        type string {
          length "1..128";
        }
      }
      leaf domain-status {
        description "Packet-switched domain state";
        type string {
          length "1..128";
        }
      }
      leaf mcc {
        description "Mobile country code (MCC)";
        type uint16;
      }
      leaf mnc {
        description "Mobile network code (MNC)";
        type uint16;
      }
      leaf nw-name {
        description "Network name";
        type string {
          length "1..128";
        }
      }
      leaf emm-state {
        description "EPS mobility management (EMM) state";
        type string {
          length "1..128";
        }
      }
      leaf emm-substate {
        description "EPS mobility management (EMM) substate";
        type string {
          length "1..128";
        }
      }
      leaf emm-connstate {
        description "EPS mobility management (EMM) connection state";
        type string {
          length "1..128";
        }
      }
      leaf cellid {
        description "Cell ID";
        type uint64;
      }
      leaf tac {
        description "Tracking area code (TAC)";
        type uint16;
      }
      leaf lac {
        description "Location area code (LAC)";
        type uint16;
      }
      leaf radio-mode {
        description "Radio mode";
        type wwan-radio-enum;
      }
      leaf bsic {
        description "Base station identity code (BSIC)";
        type uint8;
      }
      leaf psc {
        description "Primary scrambling code (PSC)";
        type uint16;
      }
      leaf sid {
        description "System ID (SID)";
        type uint16;
      }
      leaf nid {
        description "Network ID (NID)";
        type uint16;
      }
      leaf bid {
        description "Base statation ID (BID)";
        type uint16;
      }
    }
    list modem {
      description "Display cellular modem information";
      config false;
      key "if-name";
      leaf if-name {
        description "Interface name";
        type viptela:named-type;
      }
      leaf model {
        description "Model number";
        type string {
          length "1..128";
        }
      }
      leaf fw-version {
        description "Firmware version";
        type string {
          length "1..128";
        }
      }
      leaf fw-date {
        description "Firmware release date";
        type string {
          length "1..128";
        }
      }
      leaf fw-time {
        description "Firmware release time";
        type string {
          length "1..128";
        }
      }
      leaf fw-pkg-ver {
        description "Firmware package version";
        type string {
          length "1..16";
        }
      }
      leaf fw-pkg-carrier {
        description "Firmware package carrier";
        type string {
          length "1..16";
        }
      }
      leaf fw-pkg-pri {
        description "Firmware package PRI version";
        type string {
          length "1..16";
        }
      }
      leaf fw-pkg-subver {
        description "Firmware package subversion";
        type string {
          length "1..16";
        }
      }
      leaf hw-version {
        description "Hardware version";
        type string {
          length "1..128";
        }
      }
      leaf modem-status {
        description "Modem status";
        type string {
          length "1..128";
        }
      }
      leaf temperature {
        description "Modem temperature, in degrees C";
        type int8;
      }
      leaf imsi {
        description "International mobile subscriber identity (IMSI)";
        type string {
          length "1..128";
        }
      }
      leaf imei {
        description "International mobile equipment identity (IMEI)";
        type string {
          length "1..128";
        }
      }
      leaf iccid {
        description "Integrated circuit card ID (ICCID)";
        type string {
          length "1..128";
        }
      }
      leaf msisdn {
        description "Mobile subscriber ISDN (MSISDN)";
        type string {
          length "1..128";
        }
      }
      leaf esn {
        description "Electronic serial number (ESN)";
        type string {
          length "1..128";
        }
      }
    }
    list status {
      description "Display cellular status";
      config false;
      key "if-name";
      leaf if-name {
        description "Interface name";
        type viptela:named-type;
      }
      leaf modem-status {
        description "Modem status";
        type string {
          length "1..128";
        }
      }
      leaf sim-status {
        description "SIM status";
        type string {
          length "1..128";
        }
      }
      leaf radio-mode {
        description "Radio mode";
        type wwan-radio-enum;
      }
      leaf signal-strength {
        description "Signal Strength";
        type string {
          length "1..128";
        }
      }
      leaf network-status {
        description "Network registration status";
        type wwan-registration-status;
      }
      leaf last-seen-error {
        description "Last seen error";
        type string {
          length "1..200";
        }
      }
      leaf activation-status {
        description "Activation status";
        type wwan-activation-enum;
      }
    }
    list profiles {
      description "Display cellular profile information";
      config false;
      key "if-name profile-id";
      leaf if-name {
        description "Interface name";
        type viptela:named-type;
      }
      leaf profile-id {
        description "Profile ID";
        type uint8;
      }
      leaf pdn-type {
        description "Packet data network type";
        type wwan-pdn-type;
      }
      leaf apn {
        description "Access point name";
        type string {
          length "1..104";
        }
      }
      leaf name {
        description "Profile name";
        type string {
          length "1..17";
        }
      }
      leaf auth {
        description "Authentication";
        type wwan-auth-type;
      }
      leaf ip-addr {
        description "Assigned IP address";
        type inet:ipv4-address;
      }
      leaf primary-dns {
        description "Assigned primary DNS address";
        type inet:ipv4-address;
      }
      leaf secondary-dns {
        description "Assigned secondary DNS address";
        type inet:ipv4-address;
      }
      leaf user-name {
        description "Profile username";
        type string {
          length "1..129";
        }
      }
    }
    list qos {
      description "Display cellular qos";
      config false;
      key "if-name";
      leaf if-name {
        description "Interface name";
        type viptela:named-type;
      }
      leaf flow-id {
        description "QoS Flow Identifier";
        type uint32;
      }
      leaf bearer-id {
        description "Bearer Identifier";
        type uint8;
      }
      leaf qci {
        description "QoS Class Identifier";
        type uint8;
      }
      leaf bearer-status {
        description "QoS State";
        type wwan-qos-enum;
      }
    }
    list firmware {
      description "Display cellular firmware information";
      config false;
      key "if-name image-index";
      leaf if-name {
        description "Interface name";
        type viptela:named-type;
      }
      leaf image-index {
        description "Image index";
        type uint8;
      }
      leaf carrier {
        description "Carrier name";
        type string {
          length "1..16";
        }
      }
      leaf version {
        description "Firmware version";
        type string {
          length "1..16";
        }
      }
      leaf pri-version {
        description "PRI version";
        type string {
          length "1..16";
        }
      }
      leaf image-status {
        description "Status";
        type wwan-status-enum;
      }
    }
  }
  notification sim-state-change {
    uses viptela:common-notification-header;
    leaf sim-slot {
      type uint32;
    }
    leaf sim-state {
      type wwan-sim-enum;
    }
  }
  notification domain-state-change {
    uses viptela:common-notification-header;
    leaf if-name {
      type viptela:named-type;
    }
    leaf domain-state {
      type wwan-domain-enum;
    }
  }
  notification reg-state-change {
    uses viptela:common-notification-header;
    leaf if-name {
      type viptela:named-type;
    }
    leaf reg-state {
      type wwan-registration-status;
    }
  }
  notification bearer-change {
    uses viptela:common-notification-header;
    leaf if-name {
      type viptela:named-type;
    }
    leaf bearer {
      type wwan-bearer-enum;
    }
  }
  notification qos-state-change {
    uses viptela:common-notification-header;
    leaf if-name {
      type viptela:named-type;
    }
    leaf qos-state {
      type wwan-qos-enum;
    }
  }

  typedef aes-cfb-128-encrypted-string {
    type string;
    description
      "The aes-cfb-128-encrypted-string works exactly like
       des3-cbc-encrypted-string but AES/128bits in CFB mode is used to
       encrypt the string.  The prefix for encrypted values is '$8$'.";
  }
}
