module viptela-oper-vpn {
  namespace "http://viptela.com/oper-vpn";
  prefix viptela-oper-vpn;

  import ietf-inet-types {
    prefix inet;
  }
  import ietf-yang-types {
    prefix yang;
  }
    prefix tailf;
  }
  import tailf-xsd-types {
    prefix xs;
  }
  import viptela-common {
    prefix viptela;
  }
  import viptela-system {
    prefix viptela-system;
  }

  organization "Viptela, Inc.";
  contact
    "Viptela, Inc.
     Email:support@viptela.com";
  description
    "This module defines the data model for VPN operational data";

  revision 2019-08-15 {
    description
      "Release version: 19.2";
  }
  revision 2018-11-01 {
    description
      "Release version: 18.4";
  }
  revision 2018-08-20 {
    description
      "Release version: 18.3.1";
  }
  revision 2018-06-25 {
    description
      "Release version: 18.3";
  }
  revision 2018-04-25 {
    description
      "Release version: 18.2";
  }
  revision 2018-03-15 {
    description
      "Release version: 18.1.1";
  }
  revision 2018-01-16 {
    description
      "Release version: 17.2.3";
  }
  revision 2017-11-01 {
    description
      "Release version: 17.2.1";
  }
  revision 2017-08-01 {
    description
      "Release version: 17.2";
  }
  revision 2017-05-25 {
    description
      "Release version: 17.1.1";
  }
  revision 2017-04-06 {
    description
      "Release version: 17.1";
  }
  revision 2017-02-15 {
    description
      "Release version: 16.3.2";
  }
  revision 2017-02-06 {
    description
      "Release version: 16.3.1";
  }
  revision 2016-11-16 {
    description
      "Release version: 16.3";
  }
  revision 2016-10-25 {
    description
      "Release version: 16.2.10";
  }
  revision 2016-10-24 {
    description
      "Release version: 16.2.4";
  }
  revision 2016-08-10 {
    description
      "Release version: 16.2.2";
  }
  revision 2016-08-01 {
    description
      "Release version: 16.2.1";
  }
  revision 2016-06-09 {
    description
      "Release version: 16.2";
  }
  revision 2016-04-22 {
    description
      "Release version: 16.1.1";
  }
  revision 2016-03-15 {
    description
      "Release version: 16.1";
  }
  revision 2016-01-30 {
    description
      "Release version: 15.4.3";
  }
  revision 2015-12-28 {
    description
      "Release version: 15.4.1";
  }
  revision 2015-12-01 {
    description
      "Release version: 15.4.0";
  }
  revision 2015-10-31 {
    description
      "Release version: 15.3.5";
  }
  revision 2015-09-27 {
    description
      "Release version: 15.3.3";
  }
  revision 2015-09-01 {
    description
      "Release version: 15.3.1";
  }
  revision 2015-07-01 {
    description
      "Release version: 15.3";
  }
  revision 2015-06-01 {
    description
      "Release version: 15.2.8";
  }
  revision 2015-05-01 {
    description
      "Release version: 15.2";
  }
  revision 2015-02-01 {
    description
      "Release version: 15.1";
  }
  revision 2014-12-01 {
    description
      "Release version: 14.3";
  }
  revision 2014-07-01 {
    description
      "Release version: 14.2";
  }
  revision 2013-02-12 {
    description
      "Initial revision";
  }

  typedef route-status-type {
    type bits {
      bit B {
        description
          "blackhole";
      }
      bit F {
        description
          "fib";
      }
      bit I {
        description
          "inactive";
      }
      bit S {
        description
          "selected";
      }
      bit R {
        description
          "recursive";
      }
    }
  }

  typedef vpn-if-flags-type {
    type bits {
      bit Inactive;
      bit Detect;
      bit Pseudo;
    }
  }

  typedef vpn-if-pause-type {
    type bits {
      bit tx_pause;
      bit rx_pause;
    }
  }

  typedef arp-entry-type {
    type enumeration {
      enum "static";
      enum "dynamic";
      enum "invalid";
    }
  }

  typedef if-address-type-enum {
    description
      "A type describing the nature of the primary IP address used on the interface";
    description "Interface address type";
    type enumeration {
      enum "invalid" {
        value 0;
      }
      enum "ipv4-static" {
        value 1;
      }
      enum "ipv4-dhcp" {
        value 2;
      }
      enum "ipv6-static" {
        value 3;
      }
      enum "ipv6-dhcp" {
        value 4;
      }
      enum "ipv6-ra" {
        value 5;
      }
      enum "ipv6-link-local" {
        value 6;
      }
    }
  }

  typedef sfp-physical-identifier-enum {
    description
      "A type defining the physical SFP identifying characteristics. The
       enumerations provided include common decodes for the SFP MSA
       Physical Identifier field as defined in SFP specification SFF-8024.";
    description "SFP physical identifer type";
    type enumeration {
      enum "Unknown/unspecified" {
        value 0;
      }
      enum "GBIC" {
        value 1;
      }
      enum "SFF" {
        value 2;
      }
      enum "SFP/SFP+" {
        value 3;
      }
      enum "Unknown" {
        value 256;
      }
    }
  }

  typedef sfp-connector-type-enum {
    description
      "A type indicating the connector style presented by an SFP. The decoded
       enumerations are take from the SFP specification SFF-8042.";
    description "SFP connector types";
    type enumeration {
      enum "Unknown/unspecified" {
        value 0;
      }
      enum "SC (Subscriber connector)" {
        value 1;
      }
      enum "Fiber channel style 1 copper connector" {
        value 2;
      }
      enum "Fiber channel style 2 copper connector" {
        value 3;
      }
      enum "BNC/TNC connector" {
        value 4;
      }
      enum "Fiber channel coax headers" {
        value 5;
      }
      enum "Fiber jack" {
        value 6;
      }
      enum "LC (Lucent connector)" {
        value 7;
      }
      enum "MT-RJ" {
        value 8;
      }
      enum "MU (Multiple optical)" {
        value 9;
      }
      enum "SG" {
        value 10;
      }
      enum "Optical pigtail" {
        value 11;
      }
      enum "MPO 1x12 (Multifiber)" {
        value 12;
      }
      enum "MPO 2x16 (Multifiber)" {
        value 13;
      }
      enum "HSSDC II" {
        value 32;
      }
      enum "Copper pigtail" {
        value 33;
      }
      enum "RJ45 (Registered jack)" {
        value 34;
      }
      enum "No separable connector" {
        value 35;
      }
      enum "MXC 2x16" {
        value 36;
      }
      enum "Unknown" {
        value 256;
      }
    }
  }

  typedef sfp-transceiver-compliance-enum {
    description
      "A type indicating the supported SFP compliances. The decoded
       enumerations are taken from the SFP specification SFF-8042.";
    description "SFP transceiver compliance types";
    type enumeration {
      enum "Unexpected" {
        value 0;
      }
      enum "10G Base-ER" {
        value 1;
      }
      enum "10G Base-LRM" {
        value 2;
      }
      enum "10G Base-SR" {
        value 3;
      }
      enum "10G Base-LR" {
        value 4;
      }
      enum "1000 Base-T" {
        value 5;
      }
      enum "1000 Base-CX" {
        value 6;
      }
      enum "1000 Base-LX" {
        value 7;
      }
      enum "1000 Base-SX" {
        value 8;
      }
    }
  }

  typedef sfp-encoding-enum {
    description
      "A type indicating the supported SFP encoding types. The decoded
       enumerations are taken from the SFP specification SFF-8042.";
    description "SFP encoding types";
    type enumeration {
      enum "Unspecified" {
        value 0;
      }
      enum "8b/10b" {
        value 1;
      }
      enum "4b/5b" {
        value 2;
      }
      enum "NRZ" {
        value 3;
      }
      enum "Manchester" {
        value 4;
      }
      enum "SONET scrambled" {
        value 5;
      }
      enum "64b/66b" {
        value 6;
      }
      enum "256b/257b" {
        value 7;
      }
      enum "PAM4" {
        value 8;
      }
      enum "Reserved" {
        value 255;
      }
    }
  }

  typedef sfp-rate-select-enum {
    description
      "A standardized set of pre-canned rate selection options";
    description "SFP rate selection type";
    type enumeration {
      enum "Unspecified" {
        value 0;
      }
      enum "4/2/1G Rate_Select and AS0/AS1" {
        value 1;
      }
      enum "8/4/2G Rx Rate_Select only" {
        value 2;
      }
      enum "8/4/2G Tx Rate_Select only" {
        value 4;
      }
      enum "8/4/2G Independent Rx & Tx Rate_Select" {
        value 6;
      }
      enum "16/8/4G Rx Rate_Select only" {
        value 8;
      }
      enum "16/8/4G Independent Rx & Tx Rate_Select" {
        value 10;
      }
      enum "32/16/8G Independent Rx & Tx Rate_Select" {
        value 12;
      }
      enum "10/8G Independent Rx & Tx Rate_Select" {
        value 14;
      }
      enum "Reserved" {
        value 256;
      }
      enum "Unallocated value" {
        value 257;
      }
    }
  }

  typedef sfp-calibration-type {
    description
      "An enumeration indicating the types of SFP calibration possible.
       External calibration decodes are not supported.";
    description "SFP calibration type";
    type enumeration {
      enum "None" {
        value 0;
      }
      enum "Internal" {
        value 1;
      }
      enum "External (not supported)" {
        value 2;
      }
    }
  }

  typedef sfp-power-type {
    description
      "An enumeration indicating the basis for SFP optical power
       measurements.";
    description "SFP optical power measurement basis";
    type enumeration {
      enum "Average input power" {
        value 0;
      }
      enum "OMA (optical modulation amplitude)" {
        value 1;
      }
    }
  }

  typedef sfp-timing-type {
    description
      "A set of enumerated values indicating the type of clock timing
       used.";
    description "SFP clock timing type";
    type enumeration {
      enum "Internal retimer" {
        value 0;
      }
      enum "CDR" {
        value 1;
      }
    }
  }

  typedef sfp-hex-bytes {
    description
      "A hexadecimal string with octets represented as hex digits
       separated by spaces or '-'.";
    description "Hexadecimal octet array type";
    type string {
      pattern "([0-9a-fA-F]{2}([ \\-][0-9a-fA-F]{2})*)?";
    }
  }

  typedef yesno {
    description
      "A type similar to 'boolean' that provides a more friendly
       Yes or No value output than the 'boolean' type.";
    description "Friendly boolean type";
    type enumeration {
      enum "No" {
        value 0;
      }
      enum "Yes" {
        value 1;
      }
    }
  }

  list arp {
    description "Display ARP table";
    config false;
    key "vpn-id if-name ip";
    leaf vpn-id {
      description "VPN ID";
      type viptela:vpn-id;
    }
    leaf if-name {
      description "Interface name";
      type viptela:named-type;
    }
    leaf ip {
      description "IP address";
      type inet:ip-address;
    }
    leaf mac {
      description "MAC address";
      type viptela:mac-address;
    }
    leaf state {
      description "State";
      type arp-entry-type;
    }
    leaf idle-timer {
      description "Time before expiration, in seconds";
      type string;
    }
    leaf uptime {
      description "How long this ARP entry has been active, in seconds";
      type string;
    }
  }
  list nd6 {
    description "Display IPv6 neighbor table";
    config false;
    key "vpn-id if-name ip";
    leaf vpn-id {
      description "VPN ID";
      type viptela:vpn-id;
    }
    leaf if-name {
      description "Interface name";
      type viptela:named-type;
    }
    leaf ip {
      description "IP address";
      type inet:ip-address;
    }
    leaf mac {
      description "MAC address";
      type viptela:mac-address;
    }
    leaf state {
      description "State";
      type enumeration {
        enum "static";
        enum "dynamic";
        enum "invalid";
      }
    }
    leaf idle-timer {
      description "Time before expiration, in seconds";
      type string;
    }
    leaf uptime {
      description "How long this neighbor entry has been active, in seconds";
      type string;
    }
  }
  list interface {
    description "Display interface";
    config false;
    key "vpn-id ifname af-type";
    leaf vpn-id {
      description "VPN ID";
      type viptela:vpn-id;
    }
    leaf ifname {
      description "Interface name";
      type viptela:named-type;
    }
    leaf af-type {
      description "Interface AF type";
      type viptela:afi-enum;
    }
    leaf ip-address {
      description "Address";
      type viptela:ipv4-ucast-addr-prefix;
    }
    leaf ipv6-address {
      description "IPv6 Address";
      type viptela:ipv6-ucast-addr-prefix;
    }
    leaf if-admin-status {
      description "Interface administrative status";
      type viptela:if-admin-status-type;
    }
    leaf if-oper-status {
      description "Interface operational status";
      type viptela:if-oper-status-type;
    }
    leaf if-tracker-status {
      description "Interface Tracker Status";
      type viptela:if-tracker-status-type;
    }
    leaf desc {
      description "Interface description";
      type viptela:named-type;
    }
    list if-addr {
      description "List of interface addresses";
      key "addr-id";
      leaf addr-id {
        type uint32;
      }
      leaf ip-address {
        description "IP address";
        type viptela:ipv4-ucast-addr-prefix;
      }
      leaf broadcast-addr {
        description "Broadcast address";
        type inet:ipv4-address;
      }
      leaf secondary {
        description "Secondary";
        type boolean;
      }
    }
    list if-addrv6 {
      description "List of interface addresses";
      leaf ipv6-address {
        description "Address";
        type viptela:ipv6-ucast-addr-prefix;
      }
      leaf broadcast-v6addr {
        description "Broadcast address";
        type inet:ipv6-address;
      }
      leaf secondary-v6 {
        description "Secondary";
        type boolean;
      }
      leaf link-local {
        description "Link Local";
        type boolean;
      }
    }
    leaf encap-type {
      description "Encapsulation type";
      type viptela:encapsulation;
    }
    leaf port-type {
      description "Port type";
      type enumeration {
        enum "service";
        enum "transport";
        enum "loopback";
        enum "mgmt";
      }
    }
    leaf ifindex {
      description "SNMP interface index";
      type uint32;
    }
    leaf mtu {
      description "MTU";
      type uint32;
    }
    leaf hwaddr {
      description "Hardware address";
      type viptela:named-type;
    }
    leaf speed-mbps {
      description "Speed";
      type uint32;
    }
    leaf duplex {
      description "Duplex mode";
      type enumeration {
        enum "full";
        enum "half";
        enum "NA";
      }
    }
    leaf auto-neg {
      description "Autonegotiation";
      type boolean;
    }
    leaf pause-type {
      description "Pause parameters type";
      type vpn-if-pause-type;
    }
    leaf tcp-mss-adjust {
      description "TCP MSS on SYN packets, in bytes";
      type uint16;
    }
    leaf uptime {
      description "Interface uptime";
      type string;
    }
    leaf allow-service {
      description "Which services are allowed on this interface (only for WAN interfaces)";
      when "/viptela-system:system/viptela-system:personality = 'vedge'";
      type bits {
        bit dhcp;
        bit dns;
        bit icmp;
        bit sshd;
        bit ntp;
        bit stun;
        bit all;
        bit bgp;
        bit ospf;
        bit netconf;
        bit https;
      }
    }
    leaf rx-packets {
      type yang:counter64;
    }
    leaf rx-octets {
      type yang:counter64;
    }
    leaf rx-errors {
      type yang:counter64;
    }
    leaf rx-drops {
      type yang:counter64;
    }
    leaf tx-packets {
      type yang:counter64;
    }
    leaf tx-octets {
      type yang:counter64;
    }
    leaf tx-errors {
      type yang:counter64;
    }
    leaf tx-drops {
      type yang:counter64;
    }
    leaf rx-pps {
      type yang:counter64;
    }
    leaf rx-kbps {
      type yang:counter64;
    }
    leaf tx-pps {
      type yang:counter64;
    }
    leaf tx-kbps {
      type yang:counter64;
    }
    leaf rx-arp-requests {
      type yang:counter64;
      when "/viptela-system:system/viptela-system:personality = 'vedge'";
    }
    leaf tx-arp-replies {
      type yang:counter64;
      when "/viptela-system:system/viptela-system:personality = 'vedge'";
    }
    leaf tx-arp-requests {
      type yang:counter64;
      when "/viptela-system:system/viptela-system:personality = 'vedge'";
    }
    leaf rx-arp-replies {
      type yang:counter64;
      when "/viptela-system:system/viptela-system:personality = 'vedge'";
    }
    leaf arp-add-fails {
      type yang:counter64;
      when "/viptela-system:system/viptela-system:personality = 'vedge'";
    }
    leaf rx-arp-reply-drops {
      type yang:counter64;
      when "/viptela-system:system/viptela-system:personality = 'vedge'";
    }
    leaf rx-arp-rate-limit-drops {
      type yang:counter64;
      when "/viptela-system:system/viptela-system:personality = 'vedge'";
    }
    leaf tx-arp-rate-limit-drops {
      type yang:counter64;
      when "/viptela-system:system/viptela-system:personality = 'vedge'";
    }
    leaf rx-arp-non-local-drops {
      type yang:counter64;
      when "/viptela-system:system/viptela-system:personality = 'vedge'";
    }
    leaf tx-arp-request-fail {
      type yang:counter64;
      when "/viptela-system:system/viptela-system:personality = 'vedge'";
    }
    leaf tx-no-arp-drops {
      type yang:counter64;
      when "/viptela-system:system/viptela-system:personality = 'vedge'";
    }
    leaf rx-ip-ttl-expired {
      type yang:counter64;
      when "/viptela-system:system/viptela-system:personality = 'vedge'";
    }
    leaf rx-ip-errors {
      type yang:counter64;
      when "/viptela-system:system/viptela-system:personality = 'vedge'";
    }
    leaf interface-disabled {
      type yang:counter64;
      when "/viptela-system:system/viptela-system:personality = 'vedge'";
    }
    leaf rx-policer-drops {
      type yang:counter64;
      when "/viptela-system:system/viptela-system:personality = 'vedge'";
    }
    leaf rx-non-ip-drops {
      type yang:counter64;
      when "/viptela-system:system/viptela-system:personality = 'vedge'";
    }
    leaf filter-drops {
      type yang:counter64;
      when "/viptela-system:system/viptela-system:personality = 'vedge'";
    }
    leaf mirror-drops {
      type yang:counter64;
      when "/viptela-system:system/viptela-system:personality = 'vedge'";
    }
    leaf cpu-policer-drops {
      type yang:counter64;
      when "/viptela-system:system/viptela-system:personality = 'vedge'";
    }
    leaf tx-icmp-policer-drops {
      type yang:counter64;
      when "/viptela-system:system/viptela-system:personality = 'vedge'";
    }
    leaf tx-icmp-mirrored-drops {
      type yang:counter64;
      when "/viptela-system:system/viptela-system:personality = 'vedge'";
    }
    leaf split-horizon-drops {
      type yang:counter64;
      when "/viptela-system:system/viptela-system:personality = 'vedge'";
    }
    leaf route-lookup-fail {
      type yang:counter64;
      when "/viptela-system:system/viptela-system:personality = 'vedge'";
    }
    leaf bad-label {
      type yang:counter64;
      when "/viptela-system:system/viptela-system:personality = 'vedge'";
    }
    leaf tx-interface-disabled {
      type yang:counter64;
      when "/viptela-system:system/viptela-system:personality = 'vedge'";
    }
    leaf rx-multicast-pkts {
      type yang:counter64;
      when "/viptela-system:system/viptela-system:personality = 'vedge'";
    }
    leaf rx-broadcast-pkts {
      type yang:counter64;
      when "/viptela-system:system/viptela-system:personality = 'vedge'";
    }
    leaf tx-multicast-pkts {
      type yang:counter64;
      when "/viptela-system:system/viptela-system:personality = 'vedge'";
    }
    leaf tx-broadcast-pkts {
      type yang:counter64;
      when "/viptela-system:system/viptela-system:personality = 'vedge'";
    }
    leaf rx-pause-pkts {
      type yang:counter64;
      when "/viptela-system:system/viptela-system:personality = 'vedge'";
    }
    leaf rx-dmac-filter-drops {
      type yang:counter64;
      when "/viptela-system:system/viptela-system:personality = 'vedge'";
    }
    leaf rx-wred-drops {
      type yang:counter64;
      when "/viptela-system:system/viptela-system:personality = 'vedge'";
    }
    leaf rx-interface-not-found {
      type yang:counter64;
      when "/viptela-system:system/viptela-system:personality = 'vedge'";
    }
    leaf rx-inb-errors {
      type yang:counter64;
      when "/viptela-system:system/viptela-system:personality = 'vedge'";
    }
    leaf rx-oversize-errors {
      type yang:counter64;
      when "/viptela-system:system/viptela-system:personality = 'vedge'";
    }
    leaf rx-fcs-align-errors {
      type yang:counter64;
      when "/viptela-system:system/viptela-system:personality = 'vedge'";
    }
    leaf rx-undersize-errors {
      type yang:counter64;
      when "/viptela-system:system/viptela-system:personality = 'vedge'";
    }
    leaf tx-underflow-pkts {
      type yang:counter64;
      when "/viptela-system:system/viptela-system:personality = 'vedge'";
    }
    leaf tx-collision-drops {
      type yang:counter64;
      when "/viptela-system:system/viptela-system:personality = 'vedge'";
    }
    leaf tx-pause-pkts {
      type yang:counter64;
      when "/viptela-system:system/viptela-system:personality = 'vedge'";
    }
    leaf tx-fragments-needed {
      type yang:counter64;
      when "/viptela-system:system/viptela-system:personality = 'vedge'";
    }
    leaf tx-fragments {
      type yang:counter64;
      when "/viptela-system:system/viptela-system:personality = 'vedge'";
    }
    leaf tx-fragment-drops {
      type yang:counter64;
      when "/viptela-system:system/viptela-system:personality = 'vedge'";
    }
    leaf tx-tail-red-drops {
      type yang:counter64;
      when "/viptela-system:system/viptela-system:personality = 'vedge'";
    }
    leaf llq-drops {
      type yang:counter64;
      when "/viptela-system:system/viptela-system:personality = 'vedge'";
    }
    leaf rx-pkt-size-64 {
      type yang:counter64;
      when "/viptela-system:system/viptela-system:personality = 'vedge'";
    }
    leaf rx-pkt-size-lt-64 {
      type yang:counter64;
      when "/viptela-system:system/viptela-system:personality = 'vedge'";
    }
    leaf rx-pkt-size-65-127 {
      type yang:counter64;
      when "/viptela-system:system/viptela-system:personality = 'vedge'";
    }
    leaf rx-pkt-size-128-255 {
      type yang:counter64;
      when "/viptela-system:system/viptela-system:personality = 'vedge'";
    }
    leaf rx-pkt-size-256-511 {
      type yang:counter64;
      when "/viptela-system:system/viptela-system:personality = 'vedge'";
    }
    leaf rx-pkt-size-512-1023 {
      type yang:counter64;
      when "/viptela-system:system/viptela-system:personality = 'vedge'";
    }
    leaf rx-pkt-size-1024-1518 {
      type yang:counter64;
      when "/viptela-system:system/viptela-system:personality = 'vedge'";
    }
    leaf rx-pkt-size-gt-1518 {
      type yang:counter64;
      when "/viptela-system:system/viptela-system:personality = 'vedge'";
    }
    leaf tx-pkt-size-64 {
      type yang:counter64;
      when "/viptela-system:system/viptela-system:personality = 'vedge'";
    }
    leaf tx-pkt-size-lt-64 {
      type yang:counter64;
      when "/viptela-system:system/viptela-system:personality = 'vedge'";
    }
    leaf tx-pkt-size-65-127 {
      type yang:counter64;
      when "/viptela-system:system/viptela-system:personality = 'vedge'";
    }
    leaf tx-pkt-size-128-255 {
      type yang:counter64;
      when "/viptela-system:system/viptela-system:personality = 'vedge'";
    }
    leaf tx-pkt-size-256-511 {
      type yang:counter64;
      when "/viptela-system:system/viptela-system:personality = 'vedge'";
    }
    leaf tx-pkt-size-512-1023 {
      type yang:counter64;
      when "/viptela-system:system/viptela-system:personality = 'vedge'";
    }
    leaf tx-pkt-size-1024-1518 {
      type yang:counter64;
      when "/viptela-system:system/viptela-system:personality = 'vedge'";
    }
    leaf tx-pkt-size-gt-1518 {
      type yang:counter64;
      when "/viptela-system:system/viptela-system:personality = 'vedge'";
    }
    leaf num-flaps {
      description "Number of interface flaps since last boot";
      type uint32;
      when "/viptela-system:system/viptela-system:personality = 'vedge'";
    }
    leaf pppoe-enabled-interface {
      description "PPPoE-enabled interface";
      type viptela:named-type;
      when "/viptela-system:system/viptela-system:personality = 'vedge'";
    }
    leaf pppoe-tx-pkts {
      description "PPPoE Tx packets";
      type yang:counter64;
      when "/viptela-system:system/viptela-system:personality = 'vedge'";
    }
    leaf pppoe-rx-pkts {
      description "PPPoE Rx packets";
      type yang:counter64;
      when "/viptela-system:system/viptela-system:personality = 'vedge'";
    }
    leaf bandwidth-upstream {
      description "Interface upstream bandwidth capacity, in kbps";
      type uint32;
      when "/viptela-system:system/viptela-system:personality = 'vedge'";
    }
    leaf bandwidth-downstream {
      description "Interface downstream bandwidth capacity, in kbps";
      type uint32;
      when "/viptela-system:system/viptela-system:personality = 'vedge'";
    }
    leaf shaping-rate {
      description "Interface shaping rate in kbps";
      type yang:counter64;
      when "/viptela-system:system/viptela-system:personality = 'vedge'";
    }
    leaf dot1x-tx-pkts {
      description "Dot1x Tx packets";
      type yang:counter64;
      when "/viptela-system:system/viptela-system:personality = 'vedge'";
    }
    leaf dot1x-rx-pkts {
      description "Dot1x Rx packets";
      type yang:counter64;
      when "/viptela-system:system/viptela-system:personality = 'vedge'";
    }
    leaf rx-policer-remark {
      type yang:counter64;
      when "/viptela-system:system/viptela-system:personality = 'vedge'";
    }
    leaf addr-type {
      description "Interface primary address type";
      type if-address-type-enum;
    }
    leaf icmp-redirect-tx-drops {
      description "icmp redirect tx drops";
      type yang:counter64;
      when "/viptela-system:system/viptela-system:personality = 'vedge'";
    }
    leaf icmp-redirect-rx-drops {
      description "icmp redirect rx drops";
      type yang:counter64;
      when "/viptela-system:system/viptela-system:personality = 'vedge'";
    }
    list queue {
      when "/viptela-system:system/viptela-system:personality = 'vedge'";
      description "Queue statistics";
      key "qnum";
      leaf qnum {
        description "Queue number";
        type uint8 {
          description "<0..7>";
          range "0..7";
        }
      }
      leaf queued-packets {
        type yang:counter64;
      }
      leaf queued-bytes {
        type yang:counter64;
      }
      leaf tail-drop-packets {
        type yang:counter64;
      }
      leaf tail-drop-bytes {
        type yang:counter64;
      }
      leaf red-drop-packets {
        type yang:counter64;
      }
      leaf red-drop-bytes {
        type yang:counter64;
      }
      leaf tx-packets {
        type yang:counter64;
      }
      leaf tx-bytes {
        type yang:counter64;
      }
      leaf queue-depth {
        type yang:counter64;
      }
      leaf max-depth {
        type yang:counter64;
      }
      leaf avg-queue {
        type yang:counter64;
      }
      leaf queue-pps {
        type yang:counter64;
      }
      leaf queue-drop-pps {
        type yang:counter64;
      }
    }
    leaf link-local-address {
      description "Link Local Address";
      type viptela:ipv6-ucast-addr-prefix;
    }
  }
  container app {
    when
      "(/viptela-system:system/viptela-system:personality = 'vedge') or
       (/viptela-system:system/viptela-system:personality = 'vsmart') or
       (/viptela-system:system/viptela-system:personality = 'vmanage')";
    description "Application-specific information";
    config false;
    container cflowd {
      description "Cflowd specific information";
      when "/viptela-system:system/viptela-system:personality = 'vedge'";
      list flows {
        description "Display cflowd flows";
        key "vpn-id src-ip dest-ip src-port dest-port dscp ip-proto";
        leaf vpn-id {
          description "VPN ID";
          type viptela:vpn-id;
        }
        leaf src-ip {
          description "Source IP Address";
          type inet:ip-address;
        }
        leaf dest-ip {
          description "Destination IP Address";
          type inet:ip-address;
        }
        leaf src-port {
          description "Source Port";
          type uint16;
        }
        leaf dest-port {
          description "Destination Port";
          type uint16;
        }
        leaf dscp {
          description "DSCP bits";
          type uint8;
        }
        leaf ip-proto {
          description "IP protocol number";
          type uint8;
        }
        leaf tcp-cntrl-bits {
          description "TCP control bits";
          type uint8;
        }
        leaf icmp-opcode {
          description "256*ICMP-type + code";
          type uint16;
        }
        leaf nhop-ip {
          description "Next-Hop IP address";
          type inet:ip-address;
        }
        leaf egress-intf {
          description "Egress interface id - Deprecated in 15.4";
          type uint32;
          status deprecated;
        }
        leaf ingress-intf {
          description "Ingress interface id - Deprecated in 15.4";
          type uint32;
          status deprecated;
        }
        leaf total-pkts {
          description "Total number of packets";
          type yang:counter64;
        }
        leaf total-bytes {
          description "Total number of bytes";
          type yang:counter64;
        }
        leaf min-len {
          description "Minimum packet length, in bytes";
          type uint16;
        }
        leaf max-len {
          description "Maximum packet length, in bytes";
          type uint16;
        }
        leaf start-time {
          description "Start time";
          type string;
        }
        leaf time-to-expire {
          description "Time left until flow expires, in seconds";
          type uint32;
        }
        leaf egress-intf-name {
          description "Egress interface name";
          type viptela:named-type;
        }
        leaf ingress-intf-name {
          description "Ingress interface name";
          type viptela:named-type;
        }
        leaf app-id {
          description "app id";
          type uint32;
        }
      }
      list collector {
        description "Display cflowd collector information";
        key "vpn-id ip-address port proto";
        leaf vpn-id {
          description "Collector VPN ID";
          type viptela:vpn-id;
        }
        leaf ip-address {
          description "Collector IP address";
          type inet:ip-address;
        }
        leaf port {
          description "Collector port";
          type inet:port-number;
        }
        leaf proto {
          description "Transport protocol";
          type enumeration {
            enum "icmp" {
              value 1;
            }
            enum "tcp" {
              value 6;
            }
            enum "udp" {
              value 17;
            }
          }
        }
        leaf connection-up {
          description "Connection state";
          type boolean;
        }
        leaf ipfix {
          description "IPFix version";
          type uint8;
        }
        leaf connection-retry {
          description "Number of connection retry attempts";
          type uint16;
        }
        leaf template-packets {
          description "Number of IPFIX template pkts transmitted";
          type yang:counter64;
        }
        leaf data-packets {
          description "Number of IPFIX data pkts transmitted";
          type yang:counter64;
        }
        leaf dropped-packets {
          description "Number of IPFIX pkts dropped on TCP connection";
          type yang:counter64;
        }
        leaf source-interface {
          description "Source interface used to export IPFIX records";
          type viptela:named-type;
        }
      }
      container statistics {
        description "Display cflowd statistics information";
        leaf data-packets {
          description "Number of IPFIX data record packets created";
          type yang:counter64;
        }
        leaf template-packets {
          description "Number of IPFIX template packets created";
          type yang:counter64;
        }
        leaf total-packets {
          description "Number of IPFIX packets transmitted";
          type yang:counter64;
        }
        leaf flow-refresh {
          description "Number of flow active timeouts to be reported";
          type yang:counter64;
        }
        leaf flow-ageout {
          description "Number of flow idle timeouts to be reported";
          type yang:counter64;
        }
        leaf flow-end-detected {
          description "Number of flows whose end was detected by fastpath";
          type yang:counter64;
        }
        leaf flow-end-forced {
          description "Number of flow that were forcibly removed";
          type yang:counter64;
        }
      }
      container template {
        description "Display cflowd template information";
        leaf name {
          description "cflowd template name";
          type string;
        }
        leaf flow-active-timeout {
          description "Timeout value for active flows in secs";
          type uint32;
        }
        leaf flow-inactive-timeout {
          description "Timeout value for inactive flows in secs";
          type uint32;
        }
        leaf template-refresh {
          description "Refresh value for template in secs";
          type uint32;
        }
      }
      list flow-count {
        description "Display cflowd flow count";
        config false;
        key "vpn-id";
        leaf vpn-id {
          description "Flow count";
          type viptela:vpn-id;
        }
        leaf count {
          description "Flow count";
          type uint32;
        }
      }
    }
    container dpi {
      description "DPI specific information";
      list applications {
        description "Display applications";
        key "vpn-id application";
        when "/viptela-system:system/viptela-system:personality = 'vedge'";
        leaf vpn-id {
          description "VPN ID";
          type viptela:vpn-id;
        }
        leaf src-ip {
          description "Source IP Address - Deprecated in 17.2";
          type inet:ip-address;
          status deprecated;
        }
        leaf application {
          description "Application";
          type string {
            length "1..128";
          }
        }
        leaf family {
          description "Family";
          type string;
        }
        leaf total-flows {
          description "Tot Flows - Deprecated in 17.2";
          type uint32;
          status deprecated;
        }
        leaf expired-flows {
          description "Exp Flows";
          type uint32;
        }
        leaf last-seen {
          description "Last seen";
          type yang:date-and-time;
        }
        leaf packets {
          description "Packet count for the application";
          type uint32;
        }
        leaf octets {
          description "Octet count for the application";
          type yang:counter64;
        }
      }
      list flows {
        description "Display flows";
        key "vpn-id src-ip dst-ip src-port dst-port proto";
        when "/viptela-system:system/viptela-system:personality = 'vedge'";
        leaf vpn-id {
          description "VPN ID";
          type viptela:vpn-id;
        }
        leaf src-ip {
          description "Source IP Address";
          type inet:ip-address;
        }
        leaf dst-ip {
          description "Destination IP Address";
          type inet:ip-address;
        }
        leaf src-port {
          description "Source port";
          type inet:port-number;
        }
        leaf dst-port {
          description "Destination port";
          type inet:port-number;
        }
        leaf proto {
          description "Transport protocol";
          type viptela:ip-proto;
        }
        leaf application {
          description "Application";
          type string;
        }
        leaf family {
          description "Family";
          type string;
        }
        leaf active-since {
          description "Time since active";
          type yang:date-and-time;
        }
        leaf packets {
          description "Packet count for the flow";
          type uint32;
        }
        leaf octets {
          description "Octet count for the flow";
          type yang:counter64;
        }
        list tunnels-in {
          description "Tunnels taken for overlay traffic to remote vedge";
          key "index";
          when "/viptela-system:system/viptela-system:personality = 'vedge'";
          leaf index {
            description "Tunnel index";
            type uint32;
          }
          container local-tloc {
            uses viptela:tloc-group {
              refine "ip";
              refine "color";
              refine "encap";
            }
          }
          container remote-tloc {
            uses viptela:tloc-group {
              refine "ip";
              refine "color";
              refine "encap";
            }
          }
          leaf packets {
            description "Packet count for the tunnel";
            type uint32;
          }
          leaf octets {
            description "Octet count for the tunnel";
            type yang:counter64;
          }
          leaf start-time {
            description "Time when flow started using this tunnel";
            type yang:date-and-time;
          }
        }
        list tunnels-out {
          description "Tunnels taken by overlay traffic from remote vedge";
          key "index";
          when "/viptela-system:system/viptela-system:personality = 'vedge'";
          leaf index {
            description "Tunnel index";
            type uint32;
          }
          container local-tloc {
            uses viptela:tloc-group {
              refine "ip";
              refine "color";
              refine "encap";
            }
          }
          container remote-tloc {
            uses viptela:tloc-group {
              refine "ip";
              refine "color";
              refine "encap";
            }
          }
          leaf packets {
            description "Packet count for the tunnel";
            type uint32;
          }
          leaf octets {
            description "Octet count for the tunnel";
            type yang:counter64;
          }
          leaf start-time {
            description "Time when flow started using this tunnel";
            type yang:date-and-time;
          }
        }
      }
      list supported-applications {
        description "Display list of supported applications";
        key "application";
        leaf application {
          description "Application";
          type string {
            length "1..128";
          }
        }
        leaf family {
          description "Family";
          type string;
        }
        leaf application-long-name {
          description "Application Long Name";
          type string;
        }
        leaf family-long-name {
          description "Family Long Name";
          type string;
        }
        leaf app-id {
          description "App ID";
          type uint32;
        }
      }
      container summary {
        config false;
        description "Display DPI summary";
        when "/viptela-system:system/viptela-system:personality = 'vedge'";
        leaf status {
          description "Dpi status";
          type viptela:admin-state-enum;
        }
        leaf flows-created {
          description "Flows created";
          type uint64;
        }
        leaf flows-expired {
          description "Flows expired";
          type uint64;
        }
        leaf current-flows {
          description "Current flows";
          type uint64;
        }
        leaf peak-flows {
          description "Peak flows";
          type uint64;
        }
        leaf current-rate {
          description "Current rate";
          type uint32;
        }
        leaf peak-rate {
          description "Peak rate";
          type uint32;
        }
      }
    }
    container log {
      description "Flow logging specific information";
      when "/viptela-system:system/viptela-system:personality = 'vedge'";
      list flows {
        description "Display logged flows";
        key "vpn-id src-ip dest-ip src-port dest-port dscp ip-proto";
        leaf vpn-id {
          description "Flow VPN";
          type viptela:vpn-id;
        }
        leaf src-ip {
          description "Source IP address";
          type inet:ip-address;
        }
        leaf dest-ip {
          description "Destination IP address";
          type inet:ip-address;
        }
        leaf src-port {
          description "Source port";
          type uint16;
        }
        leaf dest-port {
          description "Destination port";
          type uint16;
        }
        leaf dscp {
          description "DSCP bits";
          type uint8;
        }
        leaf ip-proto {
          description "IP protocol number";
          type uint8;
        }
        leaf tcp-cntrl-bits {
          description "TCP control bits";
          type uint8;
        }
        leaf icmp-opcode {
          description "(ICMP type number * 256) + (ICMP code type)";
          type uint16;
        }
        leaf nhop-ip {
          description "Next-hop IP address";
          type inet:ip-address;
        }
        leaf total-pkts {
          description "Total packets";
          type yang:counter64;
        }
        leaf total-bytes {
          description "Total bytes";
          type yang:counter64;
        }
        leaf start-time {
          description "Start time";
          type string;
        }
        leaf time-to-expire {
          description "Time left until flow expires, in seconds";
          type uint32;
        }
        leaf egress-intf-name {
          description "Egress interface name";
          type viptela:named-type;
        }
        leaf ingress-intf-name {
          description "Ingress interface name";
          type viptela:named-type;
        }
        leaf policy-name {
          description "Policy name";
          type viptela:named-type;
        }
        leaf policy-action {
          description "Policy action";
          type viptela:named-type;
        }
        leaf policy-direction {
          description "Policy direction";
          type viptela:named-type;
        }
      }
      list flow-count {
        description "Display log flow count";
        config false;
        key "vpn-id";
        leaf vpn-id {
          description "Flow VPN";
          type viptela:vpn-id;
        }
        leaf count {
          description "Flow count";
          type uint32;
        }
      }
    }
    container tcp-opt {
      description "TCP flow information";
      when "/viptela-system:system/viptela-system:personality = 'vedge'";
      list active-flows {
        description "Display active TCP-optimized flows";
        key "vpn-id src-ip dest-ip src-port dest-port";
        leaf vpn-id {
          description "Flow VPN";
          type viptela:vpn-id;
        }
        leaf src-ip {
          description "Source IP address";
          type inet:ip-address;
        }
        leaf dest-ip {
          description "Destination IP address";
          type inet:ip-address;
        }
        leaf src-port {
          description "Source port";
          type uint16;
        }
        leaf dest-port {
          description "Destination port";
          type uint16;
        }
        leaf start-time {
          description "Start time";
          type viptela:named-type;
        }
        leaf egress-intf-name {
          description "Egress interface name";
          type viptela:named-type;
        }
        leaf ingress-intf-name {
          description "Ingress interface name";
          type viptela:named-type;
        }
        leaf tx-bytes {
          description "Transmitted Bytes";
          type yang:counter64;
        }
        leaf rx-bytes {
          description "Received Bytes";
          type yang:counter64;
        }
        leaf tcp-state {
          description "Optimization state";
          type viptela:named-type;
        }
        leaf unopt-reason {
          description "Reason why flow is unoptimized";
          type viptela:named-type;
        }
        leaf proxy-identity {
          description "Proxy identity";
          type viptela:named-type;
        }
      }
      list expired-flows {
        description "Display expired TCP-optimized flows";
        key "timestamp vpn-id src-ip dest-ip src-port dest-port";
        leaf timestamp {
          description "Timestamp";
          type uint64;
        }
        leaf vpn-id {
          description "Flow VPN";
          type viptela:vpn-id;
        }
        leaf src-ip {
          description "Source IP address";
          type inet:ip-address;
        }
        leaf dest-ip {
          description "Destination IP address";
          type inet:ip-address;
        }
        leaf src-port {
          description "Source port";
          type uint16;
        }
        leaf dest-port {
          description "Destination port";
          type uint16;
        }
        leaf start-time {
          description "Start time";
          type viptela:named-type;
        }
        leaf end-time {
          description "End time";
          type viptela:named-type;
        }
        leaf tx-bytes {
          description "Transmitted Bytes";
          type yang:counter64;
        }
        leaf rx-bytes {
          description "Received Bytes";
          type yang:counter64;
        }
        leaf tcp-state {
          description "Optimization state";
          type viptela:named-type;
        }
        leaf unopt-reason {
          description "Reason why flow was unoptimized";
          type viptela:named-type;
        }
        leaf proxy-identity {
          description "Proxy identity";
          type viptela:named-type;
        }
        leaf delete-reason {
          description "Reason why flow was deleted";
          type viptela:named-type;
        }
      }
      container summary {
        description "TCP optimized flow summary";
        config false;
        leaf flows-optimized {
          description "Number of optimized TCP flows";
          type uint32;
        }
        leaf flows-passthrough {
          description "Number of passthrough TCP flows";
          type uint32;
        }
        leaf flows-in-progress {
          description "Number of in-progress TCP flows";
          type uint32;
        }
        leaf flows-expired {
          description "Number of expired TCP flows";
          type uint32;
        }
        leaf flows-close-wait {
          description "Number of expired TCP flows";
          type uint32;
        }
      }
    }
  }
  container ip {
    description "IP information";
    list routes-table {
      description "List of routes";
      config false;
      key "vpn-id address-family prefix path-id";
      leaf vpn-id {
        description "VPN ID";
        type viptela:vpn-id;
      }
      leaf address-family {
        description "Address Family";
        type viptela:afi-enum;
      }
      leaf prefix {
        description "Route";
        type inet:ip-prefix;
      }
      leaf path-id {
        description "Path identifier";
        type uint32 {
          description "<0..4294967295>";
        }
      }
      leaf protocol {
        description "Protocol";
        type enumeration {
          enum "connected" {
            description
              "connected";
          }
          enum "static" {
            description
              "static";
          }
          enum "ospf" {
            description
              "ospf";
          }
          enum "bgp" {
            description
              "bgp";
          }
          enum "omp" {
            description
              "omp";
          }
          enum "nat" {
            description
              "nat";
          }
          enum "gre" {
            description
              "gre";
          }
          enum "natpool-inside";
          enum "natpool-outside";
          enum "std-ipsec" {
            description
              "std ipsec";
          }
        }
      }
      leaf protocol-sub-type {
        description "Subtype";
        type enumeration {
          enum "IA" {
            description
              "ospf-intra-area";
            value 1;
          }
          enum "IE" {
            description
              "ospf-inter-area";
            value 2;
          }
          enum "E1" {
            description
              "ospf-external1";
            value 3;
          }
          enum "E2" {
            description
              "ospf-external2";
            value 4;
          }
          enum "N1" {
            description
              "ospf-nssa-external1";
            value 5;
          }
          enum "N2" {
            description
              "ospf-nssa-external2";
            value 6;
          }
          enum "e" {
            description
              "bgp-external";
            value 7;
          }
          enum "i" {
            description
              "bgp-internal";
            value 8;
          }
        }
      }
      leaf distance {
        description "Distance";
        type uint32;
      }
      leaf metric {
        description "Metric";
        type uint32;
      }
      leaf uptime {
        description "Uptime (Days:Hours:Minutes:Seconds)";
        type string;
      }
      leaf path-flags {
        description "Path flags";
        type uint32;
      }
      leaf nexthop-flags {
        description "Next-hop flags";
        type uint32;
      }
      leaf nexthop-type {
        description "Next-hop type";
        type viptela:nexthop-enum;
      }
      leaf nexthop-ifname {
        description "Next-hop interface name";
        type viptela:named-type;
      }
      leaf nexthop-addr {
        description "Next-hop address";
        type inet:ip-address;
      }
      leaf nexthop-rtype {
        description "Recursive lookup next-hop type";
        type viptela:nexthop-enum;
      }
      leaf nexthop-rifname {
        description "Recursive lookup next-hop interface name";
        type viptela:named-type;
      }
      leaf nexthop-raddr {
        description "Recursive lookup next-hop address";
        type inet:ip-address;
      }
      leaf nexthop-rsrc {
        description "Recursive lookup next-hop source";
        type inet:ip-address;
      }
      leaf ip {
        description "IP address";
        type inet:ip-address;
      }
      leaf color {
        description "Color";
        type viptela:color-enum;
      }
      leaf encap {
        description "Encapsulation";
        type viptela:encap-enum;
      }
      leaf nexthop-vpn {
        description "Next-hop VPN";
        type viptela:vpn-id;
      }
      leaf nexthop-label {
        description "Next-hop label";
        type uint32;
      }
      leaf rstatus {
        description "Path status (fib/selected/blackhole/inactive/recursive)";
        type route-status-type;
      }
      leaf omp-tag {
        description "OMP Tag";
        type uint32;
      }
      leaf ospf-tag {
        description "OSPF Tag";
        type uint32;
      }
    }
    list longer-routes-table {
      description "List of longer routes";
      config false;
      key "vpn-id address-family prefix longer-prefix path-id";
      leaf vpn-id {
        description "VPN ID";
        type viptela:vpn-id;
        mandatory true;
      }
      leaf address-family {
        description "Address Family";
        type viptela:afi-enum;
      }
      leaf prefix {
        description "Route";
        type inet:ip-prefix;
        mandatory true;
      }
      leaf longer-prefix {
        description "Longer route";
        type inet:ip-prefix;
      }
      leaf path-id {
        description "Path identifier";
        type uint32 {
          description "<0..4294967295>";
        }
      }
      leaf protocol {
        description "Protocol";
        type enumeration {
          enum "connected" {
            description
              "connected";
          }
          enum "static" {
            description
              "static";
          }
          enum "ospf" {
            description
              "ospf";
          }
          enum "bgp" {
            description
              "bgp";
          }
          enum "omp" {
            description
              "omp";
          }
          enum "nat" {
            description
              "nat";
          }
          enum "gre" {
            description
              "gre";
          }
          enum "natpool-inside";
          enum "natpool-outside";
        }
      }
      leaf protocol-sub-type {
        description "Subtype";
        type enumeration {
          enum "IA" {
            description
              "ospf-intra-area";
            value 1;
          }
          enum "IE" {
            description
              "ospf-inter-area";
            value 2;
          }
          enum "E1" {
            description
              "ospf-external1";
            value 3;
          }
          enum "E2" {
            description
              "ospf-external2";
            value 4;
          }
          enum "N1" {
            description
              "ospf-nssa-external1";
            value 5;
          }
          enum "N2" {
            description
              "ospf-nssa-external2";
            value 6;
          }
          enum "e" {
            description
              "bgp-external";
            value 7;
          }
          enum "i" {
            description
              "bgp-internal";
            value 8;
          }
        }
      }
      leaf distance {
        description "Distance";
        type uint32;
      }
      leaf metric {
        description "Metric";
        type uint32;
      }
      leaf uptime {
        description "Uptime (Days:Hours:Minutes:Seconds)";
        type string;
      }
      leaf path-flags {
        description "Path flags";
        type uint32;
      }
      leaf nexthop-flags {
        description "Next-hop flags";
        type uint32;
      }
      leaf nexthop-type {
        description "Next-hop type";
        type viptela:nexthop-enum;
      }
      leaf nexthop-ifname {
        description "Next-hop interface name";
        type viptela:named-type;
      }
      leaf nexthop-addr {
        description "Next-hop address";
        type inet:ip-address;
      }
      leaf nexthop-rtype {
        description "Recursive lookup next-hop type";
        type viptela:nexthop-enum;
      }
      leaf nexthop-rifname {
        description "Recursive lookup next-hop interface name";
        type viptela:named-type;
      }
      leaf nexthop-raddr {
        description "Recursive lookup next-hop address";
        type inet:ip-address;
      }
      leaf nexthop-rsrc {
        description "Recursive lookup next-hop source";
        type inet:ip-address;
      }
      container tloc {
        uses viptela:tloc-group {
          refine "ip";
          refine "color";
          refine "encap";
        }
      }
      leaf nexthop-vpn {
        description "Next-hop VPN";
        type viptela:vpn-id;
      }
      leaf nexthop-label {
        description "Next-hop label";
        type uint32;
      }
      leaf rstatus {
        description "Path status (fib/selected/blackhole/inactive/recursive)";
        type route-status-type;
      }
      leaf tag {
        description "Route tag";
        type uint32;
      }
    }
    list best-match-route {
      description "Best matching route";
      config false;
      key "vpn-id address-family destination path-id";
      leaf vpn-id {
        description "VPN ID";
        type viptela:vpn-id;
      }
      leaf address-family {
        description "Address Family";
        type viptela:afi-enum;
      }
      leaf destination {
        description "Destination address";
        type inet:ip-address;
      }
      leaf path-id {
        description "Path identifier";
        type uint32 {
          description "<0..4294967295>";
        }
      }
      leaf prefix {
        description "Route";
        type inet:ip-prefix;
      }
      leaf protocol {
        description "Protocol";
        type enumeration {
          enum "connected" {
            description
              "connected";
          }
          enum "static" {
            description
              "static";
          }
          enum "ospf" {
            description
              "ospf";
          }
          enum "bgp" {
            description
              "bgp";
          }
          enum "omp" {
            description
              "omp";
          }
          enum "nat" {
            description
              "nat";
          }
          enum "gre" {
            description
              "gre";
          }
          enum "natpool-inside";
          enum "natpool-outside";
        }
      }
      leaf protocol-sub-type {
        description "Subtype";
        type enumeration {
          enum "IA" {
            description
              "ospf-intra-area";
            value 1;
          }
          enum "IE" {
            description
              "ospf-inter-area";
            value 2;
          }
          enum "E1" {
            description
              "ospf-external1";
            value 3;
          }
          enum "E2" {
            description
              "ospf-external2";
            value 4;
          }
          enum "N1" {
            description
              "ospf-nssa-external1";
            value 5;
          }
          enum "N2" {
            description
              "ospf-nssa-external2";
            value 6;
          }
          enum "e" {
            description
              "bgp-external";
            value 7;
          }
          enum "i" {
            description
              "bgp-internal";
            value 8;
          }
        }
      }
      leaf distance {
        description "Distance";
        type uint32;
      }
      leaf metric {
        description "Metric";
        type uint32;
      }
      leaf uptime {
        description "Uptime (Days:Hours:Minutes:Seconds)";
        type string;
      }
      leaf path-flags {
        description "Path flags";
        type uint32;
      }
      leaf nexthop-flags {
        description "Next-hop flags";
        type uint32;
      }
      leaf nexthop-type {
        description "Next-hop type";
        type viptela:nexthop-enum;
      }
      leaf nexthop-ifname {
        description "Next-hop interface name";
        type viptela:named-type;
      }
      leaf nexthop-addr {
        description "Next-hop address";
        type inet:ip-address;
      }
      leaf nexthop-rtype {
        description "Recursive lookup next-hop type";
        type viptela:nexthop-enum;
      }
      leaf nexthop-rifname {
        description "Recursive lookup next-hop interface name";
        type viptela:named-type;
      }
      leaf nexthop-raddr {
        description "Recursive lookup next-hop address";
        type inet:ip-address;
      }
      leaf nexthop-rsrc {
        description "Recursive lookup next-hop source";
        type inet:ip-address;
      }
      container tloc {
        uses viptela:tloc-group {
          refine "ip";
          refine "color";
          refine "encap";
        }
      }
      leaf nexthop-label {
        description "Next-hop label";
        type uint32;
      }
      leaf rstatus {
        description "Path status (fib/selected/blackhole/inactive/recursive)";
        type route-status-type;
      }
      leaf tag {
        description "Route tag";
        type uint32;
      }
      leaf nexthop-vpn {
        description "Next-hop VPN";
        type viptela:vpn-id;
      }
    }
    container mfib {
      description "MFIB commands";
      when "/viptela-system:system/viptela-system:personality = 'vedge'";
      list summary {
        description "Summary of MFIB entries";
        config false;
        key "vpn-id group source";
        leaf vpn-id {
          description "VPN";
          type viptela:vpn-id;
        }
        leaf group {
          description "Group address";
          type inet:ip-address;
        }
        leaf source {
          description "Source address";
          type inet:ip-address;
        }
        leaf upstream-if {
          description "RPF interface";
          type viptela:named-type;
        }
        leaf upstream-tunnel {
          description "RPF remote system IP address";
          type inet:ip-address;
        }
        leaf num-service-oils {
          description "Number of service-side output interfaces";
          type uint32;
        }
        leaf num-tunnel-oils {
          description "Number of tunnel-side output interfaces";
          type uint32;
        }
      }
      list oil {
        description "Multicast OIL database";
        when "/viptela-system:system/viptela-system:personality = 'vedge'";
        config false;
        key "vpn-id group source";
        leaf vpn-id {
          description "VPN";
          type viptela:vpn-id;
        }
        leaf group {
          description "Group address";
          type inet:ip-address;
        }
        leaf source {
          description "Source address";
          type inet:ip-address;
        }
        list mcast-oil-list {
          description "List of OILs for the multicast group";
          key "index";
          leaf index {
            description "OIL index";
            type uint32 {
              description "<0..4294967295>";
            }
          }
          leaf oil-interface {
            description "OIL interface";
            type viptela:named-type;
          }
          leaf oil-remote-system {
            description "OIL remote system";
            type inet:ip-address;
          }
        }
      }
      list stats {
        description "Display statistics associated with a MFIB";
        when "/viptela-system:system/viptela-system:personality = 'vedge'";
        config false;
        key "vpn-id group source";
        leaf vpn-id {
          description "VPN";
          type viptela:vpn-id;
        }
        leaf group {
          description "Group address";
          type inet:ip-address;
        }
        leaf source {
          description "Source address";
          type inet:ip-address;
        }
        leaf rx-pkts {
          description "Rx packets";
          type yang:counter64;
        }
        leaf rx-octets {
          description "Rx octets";
          type yang:counter64;
        }
        leaf tx-pkts {
          description "Tx packets";
          type yang:counter64;
        }
        leaf tx-octets {
          description "Tx octets";
          type yang:counter64;
        }
        leaf tx-to-pim-pkts {
          description "Tx To PIM Pkts";
          type yang:counter64;
        }
        leaf rx-packet-rate {
          description "Rx packet rate";
          type yang:counter64;
        }
        leaf rx-octet-rate {
          description "Rx octet rate";
          type yang:counter64;
        }
        leaf tx-packet-rate {
          description "Tx packet rate";
          type yang:counter64;
        }
        leaf tx-octet-rate {
          description "Tx octet rate";
          type yang:counter64;
        }
        leaf avg_replication {
          description "Average packet replication";
          type string {
            length "1..32";
          }
        }
        leaf rpf-failure {
          description "RPF check failure";
          type uint32;
        }
        leaf rx-policy-drop {
          description "Rx policy drop";
          type uint32;
        }
        leaf tx-policy-drop {
          description "Tx policy drop";
          type uint32;
        }
        leaf tx-invalid-oil-failure {
          description "Attempt to transmit on invalid OIL";
          type uint32;
        }
        leaf tx-failure {
          description "Transmit failure";
          type uint32;
        }
      }
    }
    list fib-routes {
      description "List of routes in FIB";
      when "/viptela-system:system/viptela-system:personality = 'vedge'";
      config false;
      key "vpn-id address-family prefix path-id";
      leaf vpn-id {
        description "VPN ID";
        type viptela:vpn-id;
      }
      leaf prefix {
        description "Route";
        type inet:ip-prefix;
      }
      leaf path-id {
        description "Path ID";
        type uint32 {
          description "<0..4294967295>";
        }
      }
      leaf out-ifname {
        description "Next-hop interface name";
        type viptela:named-type;
      }
      leaf nexthop-address {
        description "Next-hop address";
        type inet:ip-address;
      }
      leaf nexthop-label {
        description "Next-hop label";
        type uint32;
      }
      leaf sa-index {
        description "Outbound SA index";
        type uint32;
      }
      leaf ip {
        description "IP address";
        type inet:ip-address;
      }
      leaf color {
        description "Color";
        type viptela:color-enum;
      }
      leaf address-family {
        description "Address Family";
        type viptela:afi-enum;
      }
    }
    container nat {
      description "Display NAT information";
      when "/viptela-system:system/viptela-system:personality = 'vedge'";
      list interface {
        description "Interfaces on which NAT is enabled";
        config false;
        key "vpn-id ifname";
        leaf vpn-id {
          description "VPN ID";
          type viptela:vpn-id;
        }
        leaf ifname {
          description "NAT interface name";
          type viptela:named-type;
        }
        leaf mapping-type {
          description "NAT mapping type";
          type viptela:nat-map-type-enum;
        }
        leaf filter-type {
          description "NAT filter type";
          type viptela:nat-filter-type-enum;
        }
        leaf filter-count {
          description "Number of NAT filter entries in the control plane";
          type uint32;
        }
        leaf fib-filter-count {
          description "Number of NAT filter entries in the FIB";
          type uint32;
        }
        leaf ip {
          description "IP address";
          type inet:ip-prefix;
        }
        leaf number-ip-pools {
          description "Number of IP addresses in the pool";
          type uint32;
        }
      }
      list interface-statistics {
        description "Display NAT interface statistics";
        config false;
        when "/viptela-system:system/viptela-system:personality = 'vedge'";
        key "vpn-id ifname";
        leaf vpn-id {
          description "VPN ID";
          type viptela:vpn-id;
        }
        leaf ifname {
          description "NAT interface name";
          type viptela:named-type;
        }
        leaf nat-outbound-packets {
          description "Number of packets sent through NAT from the private realm";
          type yang:counter64;
        }
        leaf nat-inbound-packets {
          description "Number of packets received through NAT from the public realm";
          type yang:counter64;
        }
        leaf nat-encode-fail {
          description "NAT translation encoding failed either in outbound or inbound direction";
          type yang:counter64;
        }
        leaf nat-decode-fail {
          description "NAT translation decode failed (typically, ICMP error payload) either in outbound or inbound direction";
          type yang:counter64;
        }
        leaf nat-map-add-fail {
          description "Could not add new NAT-mapping entry (insufficient resources)";
          type yang:counter64;
        }
        leaf nat-filter-add-fail {
          description "Could not add new NAT filter entry (insufficient resources)";
          type yang:counter64;
        }
        leaf nat-filter-lookup-fail {
          description "Could not find NAT filter entry for an inbound packet";
          type yang:counter64;
        }
        leaf nat-state-check-fail {
          description "Did not match TCP state check on inbound packets";
          type yang:counter64;
        }
        leaf nat-policer-drops {
          description "Drops due to policer action configured on some filters";
          type yang:counter64;
        }
        leaf outbound-icmp-error {
          description "Number of ICMP error packets sent";
          type yang:counter64;
        }
        leaf inbound-icmp-error {
          description "Number of ICMP error packets received";
          type yang:counter64;
        }
        leaf inbound-icmp-error-drops {
          description "Number of ICMP error packets received and dropped due to block-icmp-error configuration";
          type yang:counter64;
        }
        leaf nat-fragments {
          description "Number of fragmented packets forwarded in either direction";
          type yang:counter64;
        }
        leaf nat-fragments-fail {
          description "Number of fragmented packets dropped in either direction due to absence of fragment state";
          type yang:counter64;
        }
        leaf nat-unsupported-proto {
          description "Unsupport NAT protocol packets dropped";
          type yang:counter64;
        }
        leaf nat-map-no-ports {
          description "Ran out of NAT ports to map to";
          type yang:counter64;
        }
        leaf nat-map-cannot-xlate {
          description "Cannot nat translate this flow";
          type yang:counter64;
        }
        leaf nat-filter-map-mismatch {
          description "Mismatch in the filter and map records";
          type yang:counter64;
        }
        leaf nat-map-ip-pool-exhausted {
          description "Ran out of NAT ip pools to map to";
          type yang:counter64;
        }
      }
      list filter {
        description "Display NAT filter entries";
        config false;
        when "/viptela-system:system/viptela-system:personality = 'vedge'";
        key "nat-vpn-id nat-ifname private-vpn-id proto private-source-address private-dest-address private-source-port private-dest-port";
        leaf nat-vpn-id {
          description "NAT interface VPN ID";
          type viptela:vpn-id;
        }
        leaf nat-ifname {
          description "NAT interface name";
          type viptela:named-type;
        }
        leaf private-vpn-id {
          description "Private VPN ID";
          type viptela:vpn-id;
        }
        leaf proto {
          description "Protocol";
          type enumeration {
            enum "icmp" {
              value 1;
            }
            enum "tcp" {
              value 6;
            }
            enum "udp" {
              value 17;
            }
          }
        }
        leaf private-source-address {
          description "Private source IP address";
          type inet:ipv4-address;
        }
        leaf private-dest-address {
          description "Private destination IP address";
          type inet:ipv4-address;
        }
        leaf private-source-port {
          description "Private source port";
          type uint32;
        }
        leaf private-dest-port {
          description "Private destination port";
          type uint32;
        }
        leaf public-source-address {
          description "Public source IP address";
          type inet:ipv4-address;
        }
        leaf public-dest-address {
          description "Public destination IP address";
          type inet:ipv4-address;
        }
        leaf public-source-port {
          description "Public source port";
          type uint32;
        }
        leaf public-dest-port {
          description "Public destination port";
          type uint32;
        }
        leaf filter-state {
          description "Session state";
          type enumeration {
            enum "initial";
            enum "syn-sent";
            enum "syn-ack";
            enum "syn-received";
            enum "established";
            enum "fin-sent";
            enum "fin-received";
            enum "fin-acked";
            enum "closed";
            enum "reset";
          }
        }
        leaf idle-timeout {
          description "Session idle timeout";
          type string;
        }
        leaf outbound-packets {
          description "Number of outbound packets";
          type yang:counter64;
        }
        leaf outbound-octets {
          description "Number of outbound octets";
          type yang:counter64;
        }
        leaf inbound-packets {
          description "Number of inbound packets";
          type yang:counter64;
        }
        leaf inbound-octets {
          description "Number of inbound octets";
          type yang:counter64;
        }
        leaf direction {
          description "Direction of NAT translation";
          type enumeration {
            enum "inside";
            enum "outside";
          }
        }
      }
    }
    list routes-summary {
      description "Summary of routes";
      config false;
      key "vpn-id address-family route-protocol";
      leaf vpn-id {
        description "VPN ID";
        type viptela:vpn-id;
      }
      leaf address-family {
        description "Address Family";
        type viptela:afi-enum;
      }
      leaf route-protocol {
        description "Protocol";
        type enumeration {
          enum "connected" {
            description
              "connected";
          }
          enum "static" {
            description
              "static";
          }
          enum "ospf" {
            description
              "ospf";
          }
          enum "bgp" {
            description
              "bgp";
          }
          enum "omp" {
            description
              "omp";
          }
          enum "nat" {
            description
              "nat";
          }
          enum "gre" {
            description
              "gre";
          }
          enum "natpool-inside";
          enum "natpool-outside";
        }
      }
      leaf received {
        description "Number of routes received";
        type uint32;
      }
      leaf installed {
        description "Number of routes installed";
        type uint32;
      }
    }
  }
  list vrrp {
    description "Display VRRP information";
    when "/viptela-system:system/viptela-system:personality = 'vedge'";
    config false;
    key "vpn-id";
    leaf vpn-id {
      description "VPN ID";
      type viptela:vpn-id;
    }
    list interfaces {
      description "Display VRRP interfaces";
      key "if-name";
      leaf if-name {
        description "Interface name";
        type viptela:named-type;
      }
      list groups {
        description "Display VRRP group";
        key "group-id";
        leaf group-id {
          type uint8 {
            description "<1..255>";
            range "1..255";
          }
        }
        leaf virtual-ip {
          description "Virtual IP address";
          type inet:ip-address;
        }
        leaf virtual-mac {
          description "Virtual MAC address";
          type viptela:mac-address;
        }
        leaf priority {
          description "Priority";
          type uint8;
        }
        leaf vrrp-state {
          description "VRRP state";
          type enumeration {
            enum "init" {
              value 1;
            }
            enum "backup";
            enum "master";
          }
        }
        leaf omp-state {
          description "OMP state";
          type enumeration {
            enum "down";
            enum "up";
          }
        }
        leaf advertisement-timer {
          description "Advertisement interval";
          type int32;
        }
        leaf master-down-timer {
          description "Master down detection interval";
          type int32;
        }
        leaf last-state-change-time {
          description "Time when state changed last time";
          type yang:date-and-time;
        }
        leaf track-prefix-list {
          description "Prefix list to be tracked";
          type viptela:named-type;
        }
        leaf prefix-list-state {
          description "Prefix list state";
          type enumeration {
            enum "resolved";
            enum "unresolved";
          }
        }
      }
    }
  }
  container dhcp {
    description "Display DHCP information";
    list client-interface {
      description "Display DHCP client interface information";
      config false;
      key "vpn-id ifname";
      leaf vpn-id {
        description "VPN ID";
        type viptela:vpn-id;
      }
      leaf ifname {
        description "Interface name";
        type viptela:named-type;
      }
      leaf state {
        description "State";
        type enumeration {
          enum "init";
          enum "request";
          enum "bound";
          enum "renew";
          enum "rebind";
          enum "release";
          enum "dynamic-ip";
        }
      }
      leaf acquired-ip {
        description "Acquired IP address";
        type inet:ipv4-prefix;
      }
      leaf server {
        description "Server IP";
        type inet:ipv4-address;
      }
      leaf lease-time {
        description "Lease time (Days:Hours:Minutes:Seconds)";
        type string;
      }
      leaf time-remaining {
        description "Lease time remaining (Days:Hours:Minutes:Seconds)";
        type string;
      }
      leaf gateway {
        description "Default gateway";
        type inet:ipv4-address;
      }
      list dns-list {
        description "List of DNS servers";
        config false;
        key "index";
        leaf index {
          description "Index";
          type uint32;
        }
        leaf dns {
          description "DNS IP";
          type inet:ipv4-address;
        }
      }
    }
    list server {
      description "Display DHCP server information";
      when "/viptela-system:system/viptela-system:personality = 'vedge'";
      config false;
      key "vpn-id ifname";
      leaf vpn-id {
        description "VPN ID";
        type viptela:vpn-id;
      }
      leaf ifname {
        description "Interface name";
        type viptela:named-type;
      }
      list bindings {
        description "Display bindings for clients";
        config false;
        key "client-mac";
        leaf client-mac {
          description "DHCP client's mac address";
          type string {
            length "1..32";
          }
        }
        leaf client-ip {
          description "IP address leased to DHCP client";
          type inet:ipv4-address;
        }
        leaf lease-time {
          description "Lease time (Days:Hours:Minutes:Seconds)";
          type string;
        }
        leaf lease-time-remaining {
          description "Lease time remaining (Days:Hours:Minutes:Seconds)";
          type string;
        }
        leaf static-binding {
          description "Is binding static or not";
          type boolean;
        }
        leaf host-name {
          description "DHCP client's hostname";
          type string;
        }
      }
    }
  }
  container dhcpv6 {
    description "Display DHCPv6 information";
    list interface {
      description "Display DHCPv6 client interface information";
      config false;
      key "vpn-id ifname";
      leaf vpn-id {
        description "VPN ID";
        type viptela:vpn-id;
      }
      leaf ifname {
        description "Interface name";
        type viptela:named-type;
      }
      leaf state {
        description "State";
        type enumeration {
          enum "init";
          enum "request";
          enum "bound";
          enum "renew";
          enum "rebind";
          enum "release";
        }
      }
      leaf acquired-ip {
        description "Acquired IPv6 address";
        type inet:ip-prefix;
      }
      leaf server {
        description "Server ID";
        type string;
      }
      leaf lease-time {
        description "Lease time (Days:Hours:Minutes:Seconds)";
        type string;
      }
      leaf time-remaining {
        description "Lease time remaining (Days:Hours:Minutes:Seconds)";
        type string;
      }
      leaf gateway {
        description "Default IPv6 gateway";
        type inet:ipv6-address;
      }
      list dns-list {
        description "List of DNS servers";
        config false;
        key "index";
        leaf index {
          description "Index";
          type uint32;
        }
        leaf dns {
          description "DNS IPv6";
          type inet:ipv6-address;
        }
      }
    }
  }
  container pppoe {
    description "Display PPPoE information";
    when "/viptela-system:system/viptela-system:personality = 'vedge'";
    list session {
      description "Display PPPoE session information";
      config false;
      key "vpn-id ifname";
      leaf vpn-id {
        description "VPN ID";
        type viptela:vpn-id;
      }
      leaf ifname {
        description "Ethernet Interface name";
        type viptela:named-type;
      }
      leaf session-id {
        description "Session ID";
        type uint32;
      }
      leaf server-mac {
        description "Server MAC address";
        type viptela:mac-address;
      }
      leaf local-mac {
        description "Local MAC address";
        type viptela:mac-address;
      }
      leaf ppp-interface {
        description "PPP interface name";
        type viptela:named-type;
      }
      leaf ac-name {
        description "Access concentrator name";
        type viptela:named-type;
      }
      leaf service-name {
        description "Service name";
        type viptela:named-type;
      }
    }
    container statistics {
      description "PPPoE statistics";
      config false;
      leaf pppoe-tx-pkts {
        description "PPPoE tx pkts";
        type uint64;
      }
      leaf pppoe-rx-pkts {
        description "PPPoE rx pkts";
        type uint64;
      }
      leaf pppoe-tx-session-drops {
        description "PPPoE tx drops due to invalid session id";
        type uint32;
      }
      leaf pppoe-rx-session-drops {
        description "PPPoE rx drops due to invalid session id";
        type uint32;
      }
      leaf pppoe-lcp-pkts {
        description "PPPoE ppp LCP protocol pkts";
        type uint32;
      }
      leaf pppoe-ipcp-pkts {
        description "PPPoE ppp IPCP protocol pkts";
        type uint32;
      }
      leaf pppoe-ccp-pkts {
        description "PPPoE ppp CCP protocol pkts";
        type uint32;
      }
      leaf pppoe-inv-discovery-pkts {
        description "PPPoE invalid discovery packets";
        type uint32;
      }
      leaf pppoe-padi-pkts {
        description "PPPoE active discovery initiation pkts";
        type uint32;
      }
      leaf pppoe-pado-pkts {
        description "PPPoE active discovery offer pkts";
        type uint32;
      }
      leaf pppoe-padr-pkts {
        description "PPPoE active discovery response pkts";
        type uint32;
      }
      leaf pppoe-pads-pkts {
        description "PPPoE active discovery session pkts";
        type uint32;
      }
      leaf pppoe-padt-pkts {
        description "PPPoE active discovery termination pkts";
        type uint32;
      }
    }
  }
  container ppp {
    description "Display PPP interface information";
    when "/viptela-system:system/viptela-system:personality = 'vedge'";
    list interface {
      description "Display PPP interface information";
      config false;
      key "vpn-id ifname";
      leaf vpn-id {
        description "VPN ID";
        type viptela:vpn-id;
      }
      leaf ifname {
        description "Ethernet interface name";
        type viptela:named-type;
      }
      leaf pppoe-interface {
        description "PPPoE interface name";
        type viptela:named-type;
      }
      leaf interface-ip {
        description "Interface IP";
        type viptela:named-type;
      }
      leaf gateway-ip {
        description "Server's IP address";
        type viptela:named-type;
      }
      leaf primary-dns {
        description "Primary DNS IP address";
        type viptela:named-type;
      }
      leaf secondary-dns {
        description "Secondary DNS IP address";
        type viptela:named-type;
      }
      leaf mtu {
        description "MTU for PPP interface";
        type int32;
      }
      leaf auth-type {
        description "Auth type for PPP interface";
        type viptela:ppp-auth;
      }
    }
  }
  container sfp {
    description "Display SFP information";
    config false;
    when "/viptela-system:system/viptela-system:personality = 'vedge'";
    list detail {
      description
        "This list provides mechanisms for retrieving detailed SFP
         information.";
      key "ifname";
      description "Display detailed SFP information";
      when "/viptela-system:system/viptela-system:personality = 'vedge'";
      leaf ifname {
        description "Interface name";
        type viptela:named-type;
        when "/viptela-system:system/viptela-system:personality = 'vedge'";
      }
      leaf present {
        description "SFP present";
        type yesno;
        when "/viptela-system:system/viptela-system:personality = 'vedge'";
      }
      leaf physical-identifier {
        description "Physical transceiver device";
        type sfp-physical-identifier-enum;
        when
          "(/viptela-system:system/viptela-system:personality = 'vedge') and
           (../present = 'Yes')";
      }
      leaf connector-type {
        description "Connector type presented by the device";
        type sfp-connector-type-enum;
        when
          "(/viptela-system:system/viptela-system:personality = 'vedge') and
           (../present = 'Yes')";
      }
      leaf transceiver-compliance-pri {
        description "Primary supported protocol compliance";
        type sfp-transceiver-compliance-enum;
        when
          "(/viptela-system:system/viptela-system:personality = 'vedge') and
           (../present = 'Yes')";
      }
      leaf transceiver-compliance-sec {
        description "Secondary supported protocol compliance";
        type sfp-transceiver-compliance-enum;
        when
          "(/viptela-system:system/viptela-system:personality = 'vedge') and
           (../present = 'Yes')";
      }
      leaf encoding {
        description "Link encoding mechansim";
        type sfp-encoding-enum;
        when
          "(/viptela-system:system/viptela-system:personality = 'vedge') and
           (../present = 'Yes')";
      }
      leaf nominal-speed {
        description "Nominal link speed";
        type uint64;
        when
          "(/viptela-system:system/viptela-system:personality = 'vedge') and
           (../present = 'Yes')";
      }
      leaf rate-select-options {
        description "Rate selection options";
        type sfp-rate-select-enum;
        when
          "(/viptela-system:system/viptela-system:personality = 'vedge') and
           (../present = 'Yes')";
      }
      leaf length-single-mode-km {
        description "Supported length for single mode fiber";
        type uint32;
        when
          "(/viptela-system:system/viptela-system:personality = 'vedge') and
           (../present = 'Yes')";
      }
      leaf length-625um-om1 {
        description "Supported length for 62.5-um multimode OM1 fiber";
        type uint32;
        when
          "(/viptela-system:system/viptela-system:personality = 'vedge') and
           (../present = 'Yes')";
      }
      leaf length-50um-om2 {
        description "Supported length for 50-um multimode OM2 fiber";
        type uint32;
        when
          "(/viptela-system:system/viptela-system:personality = 'vedge') and
           (../present = 'Yes')";
      }
      leaf copper-min-length {
        description "Copper minimum link length";
        type uint32;
        when
          "(/viptela-system:system/viptela-system:personality = 'vedge') and
           (../present = 'Yes')";
      }
      leaf length-50um-om3 {
        description "Supported length for 50-um multimode OM3 fiber";
        type uint32;
        when
          "(/viptela-system:system/viptela-system:personality = 'vedge') and
           (../present = 'Yes')";
      }
      leaf length-50um-om4 {
        description "Supported length for 50-um multimode OM4 fiber or active cable";
        type uint32;
        when
          "(/viptela-system:system/viptela-system:personality = 'vedge') and
           (../present = 'Yes')";
      }
      leaf laser-wavelength {
        description "Laser wavelength (fiber only)";
        type uint32;
        when
          "(/viptela-system:system/viptela-system:personality = 'vedge') and
           (../present = 'Yes')";
      }
      leaf vendor-name {
        description "Vendor name";
        type string;
        when
          "(/viptela-system:system/viptela-system:personality = 'vedge') and
           (../present = 'Yes')";
      }
      leaf vendor-oui {
        description "Vendor OUI";
        type hex-list;
        when
          "(/viptela-system:system/viptela-system:personality = 'vedge') and
           (../present = 'Yes')";
      }
      leaf vendor-part-number {
        description "Vendor number";
        type string;
        when
          "(/viptela-system:system/viptela-system:personality = 'vedge') and
           (../present = 'Yes')";
      }
      leaf vendor-revision {
        description "Vendor revision";
        type string;
        when
          "(/viptela-system:system/viptela-system:personality = 'vedge') and
           (../present = 'Yes')";
      }
      leaf vendor-serial-number {
        description "Vendor serial number";
        type string;
        when
          "(/viptela-system:system/viptela-system:personality = 'vedge') and
           (../present = 'Yes')";
      }
      leaf date-code {
        description "Date code";
        type string;
        when
          "(/viptela-system:system/viptela-system:personality = 'vedge') and
           (../present = 'Yes')";
      }
      container feature-options {
        description
          "Option values equating to SFP feature options found
           in bytes 64 and 65 of the SFP MSA.";
        description "Feature options";
        when
          "(/viptela-system:system/viptela-system:personality = 'vedge') and
           (../present = 'Yes')";
        leaf loss-of-signal {
          description "Loss of signal";
          type yesno;
        }
        leaf signal-detect {
          description "Signal detect";
          type yesno;
        }
        leaf tx-fault {
          description "Tx fault";
          type yesno;
        }
        leaf tx-disable {
          description "Tx disable";
          type yesno;
        }
        leaf rate-select {
          description "Rate select";
          type yesno;
        }
        leaf tuneable-wavelength {
          description "Tunable wavelength";
          type yesno;
        }
        leaf rdt {
          description "Rx decision threshold (RDT)";
          type yesno;
        }
        leaf lro {
          description "Linear receive output";
          type yesno;
        }
        leaf power-level {
          description "Power level";
          type uint32;
        }
        leaf cooled-laser {
          description "Cooled laser";
          type yesno;
        }
        leaf timing-type {
          description "Timing type";
          type sfp-timing-type;
        }
        leaf paged-a2 {
          description "Paged A2 access";
          type yesno;
        }
      }
      container digital-diagnostics {
        description "Digital diagnostics";
        when
          "(/viptela-system:system/viptela-system:personality = 'vedge') and
           (../present = 'Yes')";
        leaf supported {
          description "Supported";
          type yesno;
        }
        leaf calibration-type {
          description "Calibration type";
          type sfp-calibration-type;
          when "(../supported = 'Yes')";
        }
        leaf power-type {
          description "Power measurement type";
          type sfp-power-type;
          when "(../supported = 'Yes')";
        }
      }
      container enhanced-options {
        description "Enhanced options";
        when
          "(/viptela-system:system/viptela-system:personality = 'vedge') and
           (../present = 'Yes')";
        leaf soft-rate-select-control {
          description "Soft rate select control";
          type yesno;
        }
        leaf app-select-control {
          description "Application select control";
          type yesno;
        }
        leaf soft-rate-select-control-monitor {
          description "Soft rate select control/monitor";
          type yesno;
        }
        leaf soft-rx-los-monitor {
          description "Soft Rx loss of signal monitor";
          type yesno;
        }
        leaf soft-tx-fault-monitor {
          description "Soft Tx fault monitor";
          type yesno;
        }
        leaf soft-tx-disable-control-monitor {
          description "Soft Tx disable control/monitor";
          type yesno;
        }
        leaf all-alarm-warning-flags {
          description "Supports all alarms/warning flags";
          type yesno;
        }
      }
    }
    list diagnostic {
      description
        "This list provides SFP digital diagnostic information.";
      key "ifname";
      description "Display diagnostic SFP information";
      when "(/viptela-system:system/viptela-system:personality = 'vedge')";
      leaf ifname {
        description "Interface name";
        type viptela:named-type;
        when "(/viptela-system:system/viptela-system:personality = 'vedge')";
      }
      leaf present {
        description "SFP present";
        type yesno;
        when "(/viptela-system:system/viptela-system:personality = 'vedge')";
      }
      leaf supported {
        description "Diagnostics supported";
        type yesno;
        when
          "(/viptela-system:system/viptela-system:personality = 'vedge') and
           (../present = 'Yes')";
      }
      container control-status {
        description "SFP control/status";
        when
          "(/viptela-system:system/viptela-system:personality = 'vedge') and
           (../present = 'Yes') and (../supported = 'Yes')";
        leaf data-ready-state {
          description "Data ready";
          type yesno;
        }
        leaf rx-los-state {
          description "Rx loss of signal";
          type yesno;
        }
        leaf tx-fault-state {
          description "Tx fault";
          type yesno;
        }
        leaf soft-rate-select0-state {
          description "Soft rate select 0";
          type yesno;
        }
        leaf soft-rate-select1-state {
          description "Soft rate select 1";
          type yesno;
        }
        leaf rate-select0-state {
          description "Rate select 0";
          type yesno;
        }
        leaf rate-select1-state {
          description "Rate select 1";
          type yesno;
        }
        leaf soft-tx-disable-state {
          description "Soft Tx disable";
          type yesno;
        }
        leaf tx-disable-state {
          description "Tx disable";
          type yesno;
        }
      }
      list measurement-value {
        description "Measurement";
        key "measurement";
        when
          "(/viptela-system:system/viptela-system:personality = 'vedge') and
           (../present = 'Yes') and (../supported = 'Yes')";
        leaf measurement {
          description "Measurement";
          type string;
        }
        leaf unit-value {
          description "Unit";
          type string;
        }
        leaf low-alarm-value {
          description "Low alarm";
          type xs:float;
        }
        leaf low-warning-value {
          description "Low warning";
          type xs:float;
        }
        leaf high-warning-value {
          description "High warning";
          type xs:float;
        }
        leaf high-alarm-value {
          description "High alarm";
          type xs:float;
        }
        leaf current-value {
          description "Current value";
          type xs:float;
        }
      }
      list measurement-alarm {
        description "Measurement";
        key "measurement";
        when
          "(/viptela-system:system/viptela-system:personality = 'vedge') and
           (../present = 'Yes') and (../supported = 'Yes')";
        leaf measurement {
          description "Measurement";
          type string;
        }
        leaf low-alarm-alarm {
          description "Low alarm";
          type string;
        }
        leaf low-warning-alarm {
          description "Low warning";
          type string;
        }
        leaf high-warning-alarm {
          description "High warning";
          type string;
        }
        leaf high-alarm-alarm {
          description "High alarm";
          type string;
        }
      }
    }
    list raw-a0 {
      description
        "This list provides all items for retrieving SFP raw A0 data.";
      description "(HIDDEN) Display SFP raw page A0 data";
      key "ifname";
      when "(/viptela-system:system/viptela-system:personality = 'vedge')";
      leaf ifname {
        description "Interface name";
        type viptela:named-type;
        when "(/viptela-system:system/viptela-system:personality = 'vedge')";
      }
      leaf present {
        description "SFP present";
        type yesno;
        when "(/viptela-system:system/viptela-system:personality = 'vedge')";
      }
      leaf row-0 {
        description "Row 0 data";
        type sfp-hex-bytes;
        when
          "(/viptela-system:system/viptela-system:personality = 'vedge') and
           (../present = 'Yes')";
      }
      leaf row-1 {
        description "Row 1 data";
        type sfp-hex-bytes;
        when
          "(/viptela-system:system/viptela-system:personality = 'vedge') and
           (../present = 'Yes')";
      }
      leaf row-2 {
        description "Row 2 data";
        type sfp-hex-bytes;
        when
          "(/viptela-system:system/viptela-system:personality = 'vedge') and
           (../present = 'Yes')";
      }
      leaf row-3 {
        description "Row 3 data";
        type sfp-hex-bytes;
        when
          "(/viptela-system:system/viptela-system:personality = 'vedge') and
           (../present = 'Yes')";
      }
      leaf row-4 {
        description "Row 4 data";
        type sfp-hex-bytes;
        when
          "(/viptela-system:system/viptela-system:personality = 'vedge') and
           (../present = 'Yes')";
      }
      leaf row-5 {
        description "Row 5 data";
        type sfp-hex-bytes;
        when
          "(/viptela-system:system/viptela-system:personality = 'vedge') and
           (../present = 'Yes')";
      }
      leaf row-6 {
        description "Row 6 data";
        type sfp-hex-bytes;
        when
          "(/viptela-system:system/viptela-system:personality = 'vedge') and
           (../present = 'Yes')";
      }
      leaf row-7 {
        description "Row 7 data";
        type sfp-hex-bytes;
        when
          "(/viptela-system:system/viptela-system:personality = 'vedge') and
           (../present = 'Yes')";
      }
      leaf row-8 {
        description "Row 8 data";
        type sfp-hex-bytes;
        when
          "(/viptela-system:system/viptela-system:personality = 'vedge') and
           (../present = 'Yes')";
      }
      leaf row-9 {
        description "Row 9 data";
        type sfp-hex-bytes;
        when
          "(/viptela-system:system/viptela-system:personality = 'vedge') and
           (../present = 'Yes')";
      }
      leaf row-A {
        description "Row 10 data";
        type sfp-hex-bytes;
        when
          "(/viptela-system:system/viptela-system:personality = 'vedge') and
           (../present = 'Yes')";
      }
      leaf row-B {
        description "Row 11 data";
        type sfp-hex-bytes;
        when
          "(/viptela-system:system/viptela-system:personality = 'vedge') and
           (../present = 'Yes')";
      }
      leaf row-C {
        description "Row 12 data";
        type sfp-hex-bytes;
        when
          "(/viptela-system:system/viptela-system:personality = 'vedge') and
           (../present = 'Yes')";
      }
      leaf row-D {
        description "Row 13 data";
        type sfp-hex-bytes;
        when
          "(/viptela-system:system/viptela-system:personality = 'vedge') and
           (../present = 'Yes')";
      }
      leaf row-E {
        description "Row 14 data";
        type sfp-hex-bytes;
        when
          "(/viptela-system:system/viptela-system:personality = 'vedge') and
           (../present = 'Yes')";
      }
      leaf row-F {
        description "Row 15 data";
        type sfp-hex-bytes;
        when
          "(/viptela-system:system/viptela-system:personality = 'vedge') and
           (../present = 'Yes')";
      }
    }
    list raw-a2 {
      description
        "This list provides all items for retrieving SFP raw A2 data.";
      description "(HIDDEN) Display SFP raw page A2 data";
      key "ifname";
      when "(/viptela-system:system/viptela-system:personality = 'vedge')";
      leaf ifname {
        description "Interface name";
        type viptela:named-type;
        when "(/viptela-system:system/viptela-system:personality = 'vedge')";
      }
      leaf present {
        description "SFP present";
        type yesno;
        when "(/viptela-system:system/viptela-system:personality = 'vedge')";
      }
      leaf supported {
        description "Diagnostics supported";
        type yesno;
        when
          "(/viptela-system:system/viptela-system:personality = 'vedge') and
           (../present = 'Yes')";
      }
      leaf row-0 {
        description "Row 0 data";
        type sfp-hex-bytes;
        when
          "(/viptela-system:system/viptela-system:personality = 'vedge') and
           (../present = 'Yes') and (../supported = 'Yes')";
      }
      leaf row-1 {
        description "Row 1 data";
        type sfp-hex-bytes;
        when
          "(/viptela-system:system/viptela-system:personality = 'vedge') and
           (../present = 'Yes') and (../supported = 'Yes')";
      }
      leaf row-2 {
        description "Row 2 data";
        type sfp-hex-bytes;
        when
          "(/viptela-system:system/viptela-system:personality = 'vedge') and
           (../present = 'Yes') and (../supported = 'Yes')";
      }
      leaf row-3 {
        description "Row 3 data";
        type sfp-hex-bytes;
        when
          "(/viptela-system:system/viptela-system:personality = 'vedge') and
           (../present = 'Yes') and (../supported = 'Yes')";
      }
      leaf row-4 {
        description "Row 4 data";
        type sfp-hex-bytes;
        when
          "(/viptela-system:system/viptela-system:personality = 'vedge') and
           (../present = 'Yes') and (../supported = 'Yes')";
      }
      leaf row-5 {
        description "Row 5 data";
        type sfp-hex-bytes;
        when
          "(/viptela-system:system/viptela-system:personality = 'vedge') and
           (../present = 'Yes') and (../supported = 'Yes')";
      }
      leaf row-6 {
        description "Row 6 data";
        type sfp-hex-bytes;
        when
          "(/viptela-system:system/viptela-system:personality = 'vedge') and
           (../present = 'Yes') and (../supported = 'Yes')";
      }
      leaf row-7 {
        description "Row 7 data";
        type sfp-hex-bytes;
        when
          "(/viptela-system:system/viptela-system:personality = 'vedge') and
           (../present = 'Yes') and (../supported = 'Yes')";
      }
      leaf row-8 {
        description "Row 8 data";
        type sfp-hex-bytes;
        when
          "(/viptela-system:system/viptela-system:personality = 'vedge') and
           (../present = 'Yes') and (../supported = 'Yes')";
      }
      leaf row-9 {
        description "Row 9 data";
        type sfp-hex-bytes;
        when
          "(/viptela-system:system/viptela-system:personality = 'vedge') and
           (../present = 'Yes') and (../supported = 'Yes')";
      }
      leaf row-A {
        description "Row 10 data";
        type sfp-hex-bytes;
        when
          "(/viptela-system:system/viptela-system:personality = 'vedge') and
           (../present = 'Yes') and (../supported = 'Yes')";
      }
      leaf row-B {
        description "Row 11 data";
        type sfp-hex-bytes;
        when
          "(/viptela-system:system/viptela-system:personality = 'vedge') and
           (../present = 'Yes') and (../supported = 'Yes')";
      }
      leaf row-C {
        description "Row 12 data";
        type sfp-hex-bytes;
        when
          "(/viptela-system:system/viptela-system:personality = 'vedge') and
           (../present = 'Yes') and (../supported = 'Yes')";
      }
      leaf row-D {
        description "Row 13 data";
        type sfp-hex-bytes;
        when
          "(/viptela-system:system/viptela-system:personality = 'vedge') and
           (../present = 'Yes') and (../supported = 'Yes')";
      }
      leaf row-E {
        description "Row 14 data";
        type sfp-hex-bytes;
        when
          "(/viptela-system:system/viptela-system:personality = 'vedge') and
           (../present = 'Yes') and (../supported = 'Yes')";
      }
      leaf row-F {
        description "Row 15 data";
        type sfp-hex-bytes;
        when
          "(/viptela-system:system/viptela-system:personality = 'vedge') and
           (../present = 'Yes') and (../supported = 'Yes')";
      }
    }
  }
  container cloudexpress {
    description "cloudExpress specific information";
    config false;
    when "/viptela-system:system/viptela-system:personality = 'vedge'";
    list applications {
      description "Display applications";
      key "vpn-id application";
      when "/viptela-system:system/viptela-system:personality = 'vedge'";
      leaf vpn-id {
        description "VPN ID";
        type viptela:vpn-id;
      }
      leaf application {
        description "Application";
        type viptela:cloudexpress-app-type;
      }
      leaf exit-type {
        description "Exit type for the application";
        type viptela:cloudexpress-exit-type;
      }
      leaf gateway-system-ip {
        description "Remote gateway system IP";
        type inet:ip-address;
      }
      leaf interface {
        description "Interface name for direct internet access from client";
        type viptela:named-type;
      }
      leaf latency {
        description "Average latency for the application";
        type uint32;
      }
      leaf loss {
        description "Average loss for the application";
        type uint32;
      }
      leaf local-color {
        description "Local color of tunnel for gateway exit";
        type viptela:color-enum;
      }
      leaf remote-color {
        description "Remote color of tunnel for gateway exit";
        type viptela:color-enum;
      }
    }
    list local-exits {
      description "Display all local exits";
      key "vpn-id application interface";
      when "/viptela-system:system/viptela-system:personality = 'vedge'";
      leaf vpn-id {
        description "VPN ID";
        type viptela:vpn-id;
      }
      leaf application {
        description "Application";
        type viptela:cloudexpress-app-type;
      }
      leaf interface {
        description "Interface name for direct internet access from client";
        type viptela:named-type;
      }
      leaf latency {
        description "Average latency for the application";
        type uint32;
      }
      leaf loss {
        description "Average loss for the application";
        type uint32;
      }
    }
    list gateway-exits {
      description "Display all gateway exits";
      key "vpn-id application gateway-ip";
      when "/viptela-system:system/viptela-system:personality = 'vedge'";
      leaf vpn-id {
        description "VPN ID";
        type viptela:vpn-id;
      }
      leaf application {
        description "Application";
        type viptela:cloudexpress-app-type;
      }
      leaf gateway-ip {
        description "Gateway system IP for appliction exit";
        type inet:ip-address;
      }
      leaf latency {
        description "Average latency for the application";
        type uint32;
      }
      leaf loss {
        description "Average loss for the application";
        type uint32;
      }
      leaf local-color {
        description "Local color of tunnel for gateway exit";
        type viptela:color-enum;
      }
      leaf remote-color {
        description "Remote color of tunnel for gateway exit";
        type viptela:color-enum;
      }
    }
  }

  typedef hex-list {
    type string {
      pattern "(([0-9a-fA-F]){2}(:([0-9a-fA-F]){2})*)?";
    }
    status deprecated;
    description
      "DEPRECATED: Use yang:hex-string instead.  There are no plans to remove
       tailf:hex-list.
       
       A list of colon-separated hexa-decimal octets e.g. '4F:4C:41:71'.
       
       The statement tailf:value-length can be used to restrict the number
       of octets.  Note that using the 'length' restriction limits the
       number of characters in the lexical representation.";
  }
}
