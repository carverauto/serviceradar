module viptela-oper-multicast {
  namespace "http://viptela.com/oper-multicast";
  prefix viptela-oper-multicast;

  import ietf-inet-types {
    prefix inet;
  }
  import ietf-yang-types {
    prefix yang;
  }
    prefix tailf;
  }
  import viptela-common {
    prefix viptela;
  }
  import viptela-system {
    prefix viptela-system;
  }

  organization "Viptela, Inc.";
  contact
    "Viptela, Inc.
     Email:support@viptela.com";
  description
    "This module defines the data model for PIM operational data";

  revision 2019-08-15 {
    description
      "Release version: 19.2";
  }
  revision 2018-11-01 {
    description
      "Release version: 18.4";
  }
  revision 2018-08-20 {
    description
      "Release version: 18.3.1";
  }
  revision 2018-06-25 {
    description
      "Release version: 18.3";
  }
  revision 2018-04-25 {
    description
      "Release version: 18.2";
  }
  revision 2018-03-15 {
    description
      "Release version: 18.1.1";
  }
  revision 2018-01-16 {
    description
      "Release version: 17.2.3";
  }
  revision 2017-11-01 {
    description
      "Release version: 17.2.1";
  }
  revision 2017-08-01 {
    description
      "Release version: 17.2";
  }
  revision 2017-05-25 {
    description
      "Release version: 17.1.1";
  }
  revision 2017-04-06 {
    description
      "Release version: 17.1";
  }
  revision 2017-02-15 {
    description
      "Release version: 16.3.2";
  }
  revision 2017-02-06 {
    description
      "Release version: 16.3.1";
  }
  revision 2016-11-16 {
    description
      "Release version: 16.3";
  }
  revision 2016-10-25 {
    description
      "Release version: 16.2.10";
  }
  revision 2016-10-24 {
    description
      "Release version: 16.2.4";
  }
  revision 2016-08-10 {
    description
      "Release version: 16.2.2";
  }
  revision 2016-08-01 {
    description
      "Release version: 16.2.1";
  }
  revision 2016-06-09 {
    description
      "Release version: 16.2";
  }
  revision 2016-04-22 {
    description
      "Release version: 16.1.1";
  }
  revision 2016-03-15 {
    description
      "Release version: 16.1";
  }
  revision 2016-01-30 {
    description
      "Release version: 15.4.3";
  }
  revision 2015-12-28 {
    description
      "Release version: 15.4.1";
  }
  revision 2015-12-01 {
    description
      "Release version: 15.4.0";
  }
  revision 2015-10-31 {
    description
      "Release version: 15.3.5";
  }
  revision 2015-09-27 {
    description
      "Release version: 15.3.3";
  }
  revision 2015-09-01 {
    description
      "Release version: 15.3.1";
  }
  revision 2015-07-01 {
    description
      "Release version: 15.3";
  }
  revision 2015-06-01 {
    description
      "Release version: 15.2.8";
  }
  revision 2015-05-01 {
    description
      "Release version: 15.2";
  }
  revision 2015-02-01 {
    description
      "Release version: 15.1";
  }
  revision 2014-12-01 {
    description
      "Release version: 14.3";
  }
  revision 2014-07-01 {
    description
      "Release version: 14.2";
  }
  revision 2013-02-12 {
    description
      "Initial revision";
  }

  typedef rpf-status-enum {
    type enumeration {
      enum "resolved";
      enum "not-resolved";
    }
  }

  typedef join-type-enum {
    type enumeration {
      enum "invalid";
      enum "(*,*,RP)";
      enum "(*,G)";
      enum "(S,G)";
      enum "(S,G,RPT)";
      enum "Auto-RP";
    }
  }

  typedef upstream-state-enum {
    type enumeration {
      enum "invalid";
      enum "not-joined";
      enum "joined";
      enum "not-pruned";
      enum "pruned";
    }
  }

  typedef replicator-status-enum {
    type enumeration {
      enum "yes";
      enum "no";
    }
  }

  typedef igmp-if-state-enum {
    type enumeration {
      enum "init";
      enum "querier";
      enum "non-querier";
    }
  }

  typedef igmp-if-event-enum {
    type enumeration {
      enum "init-event";
      enum "query-timer-expiry";
      enum "query-from-lower-ip";
      enum "other-querier-present";
    }
  }

  typedef igmp-group-state-enum {
    type enumeration {
      enum "no-members-present";
      enum "members-present";
      enum "v1-members-present";
      enum "checking-membership";
    }
  }

  typedef igmp-group-event-enum {
    type enumeration {
      enum "init-event";
      enum "membership-report";
      enum "v1-membership-report";
      enum "leave";
      enum "query-timer-expired";
      enum "retransmit-timer-expired";
      enum "v1-host-timer-expired";
    }
  }

  typedef multicast-flags {
    description "Multicast flags";
    type bits {
      bit S;
    }
  }

  typedef multicast-oif-flags {
    description "Multicast OIF flags";
    type bits {
      bit A;
    }
  }

  container multicast {
    description "Multicast information";
    when "/viptela-system:system/viptela-system:personality = 'vedge'";
    config false;
    list rpf {
      description "List of RPF entries";
      key "vpn-id rpf-address";
      leaf vpn-id {
        description "VPN ID";
        type viptela:vpn-id;
      }
      leaf rpf-address {
        description "Address";
        type inet:ip-address;
      }
      leaf rpf-status {
        description "RPF status";
        type rpf-status-enum;
      }
      leaf nexthop-count {
        description "Next-hop count";
        type uint32;
      }
      list rpf-nexthops {
        description "List of next hops";
        key "index";
        leaf index {
          description "Index";
          type uint32;
        }
        leaf rpf-nbr-addr {
          description "RPF neighbor address";
          type inet:ip-address;
        }
        leaf rpf-if-name {
          description "Interface";
          type viptela:named-type;
        }
        leaf rpf-tunnel {
          description "Tunnel end point";
          type inet:ip-address;
        }
        leaf rpf-tunnel-color {
          description "Tunnel end point color";
          type viptela:color-enum;
        }
        leaf rpf-tunnel-encap {
          description "Tunnel end point encapsulation";
          type viptela:encap-enum;
        }
      }
    }
    list topology {
      description "PIM topology database";
      key "vpn-id group source join-type";
      leaf vpn-id {
        description "VPN ID";
        type viptela:vpn-id;
      }
      leaf group {
        description "Group address";
        type inet:ip-address;
      }
      leaf source {
        description "Source address";
        type inet:ip-address;
      }
      leaf join-type {
        description "Type of join";
        type join-type-enum;
      }
      leaf Flags {
        description "Topology flags";
        type multicast-flags;
      }
      leaf rp-address {
        description "RP address";
        type inet:ip-address;
      }
      leaf replicator {
        description "Multicast replicator";
        type inet:ip-address;
      }
      leaf upstream-neighbor {
        description "Upstream neighbor";
        type inet:ip-address;
      }
      leaf upstream-state {
        description "Upstream neighbor";
        type upstream-state-enum;
      }
      leaf upstream-interface {
        description "RPF interface";
        type viptela:named-type;
      }
      leaf up-time {
        description "Uptime (Days:Hours:Minutes:Seconds)";
        type string;
      }
      leaf expires {
        description "Expires (Days:Hours:Minutes:Seconds)";
        type string;
      }
      list topology-oil {
        description "List of outgoing interfaces";
        key "index";
        leaf index {
          description "Index";
          type uint32;
        }
        leaf oif-name {
          description "Outgoing interface name";
          type viptela:named-type;
        }
        leaf oif-flags {
          description "Outgoing interface flag";
          type multicast-oif-flags;
        }
        leaf oif-tunnel {
          description "Outgoing tunnel end point";
          type inet:ip-address;
        }
      }
    }
    list replicator {
      description "List of replicators";
      key "vpn-id replicator-address";
      leaf vpn-id {
        description "VPN ID";
        type viptela:vpn-id;
      }
      leaf replicator-address {
        description "Address";
        type inet:ip-address;
      }
      leaf replicator-status {
        description "Replicator status";
        type viptela:state-enum;
      }
      leaf load-percent {
        description "Load percentage for VPN";
        type uint32;
      }
    }
    list tunnel {
      description "List of tunnels";
      key "vpn-id tunnel-address";
      leaf vpn-id {
        description "VPN ID";
        type viptela:vpn-id;
      }
      leaf tunnel-address {
        description "Tunnel end point";
        type inet:ip-address;
      }
      leaf tunnel-status {
        description "Tunnel status";
        type viptela:state-enum;
      }
      leaf replicator {
        description "Replicator status";
        type replicator-status-enum;
      }
    }
  }
  container pim {
    description "PIM information";
    when "/viptela-system:system/viptela-system:personality = 'vedge'";
    config false;
    list interface {
      description "List of interfaces";
      key "vpn-id if-name";
      leaf vpn-id {
        description "VPN ID";
        type viptela:vpn-id;
      }
      leaf if-name {
        description "Interface";
        type viptela:named-type;
      }
      leaf if-addr {
        description "Address";
        type inet:ip-prefix;
      }
      leaf neighbor-count {
        description "Neighbor count";
        type uint32;
      }
      leaf hello-interval {
        description "Hello interval";
        type uint32;
      }
      leaf priority {
        description "DR priority";
        type uint32;
      }
      leaf dr-address {
        description "DR address";
        type inet:ip-address;
      }
      leaf join-prune-interval {
        description "Join prune interval";
        type uint32;
      }
    }
    list rp-mapping {
      description "List of RP mapping entries";
      key "vpn-id type group";
      leaf vpn-id {
        description "VPN ID";
        type viptela:vpn-id;
      }
      leaf type {
        description "Mapping source type";
        type enumeration {
          enum "Auto-RP";
        }
      }
      leaf group {
        description "Group prefix";
        type inet:ip-prefix;
      }
      leaf rp-address {
        description "RP address";
        type inet:ip-address;
      }
    }
    list neighbor {
      description "List of neighbors";
      key "vpn-id if-name nbr-addr";
      leaf vpn-id {
        description "VPN ID";
        type viptela:vpn-id;
      }
      leaf if-name {
        description "Interface";
        type viptela:named-type;
      }
      leaf nbr-addr {
        description "Neighbor address";
        type inet:ip-address;
      }
      leaf up-time {
        description "Uptime (Days:Hours:Minutes:Seconds)";
        type string;
      }
      leaf expires {
        description "Expires (Days:Hours:Minutes:Seconds)";
        type string;
      }
      leaf priority {
        description "DR priority";
        type uint32;
      }
      leaf hold-time {
        description "Neighbor's advertised hold time";
        type uint32;
      }
      leaf dr-address {
        description "DR address";
        type inet:ip-address;
      }
    }
    list statistics {
      description "Packet statistics";
      key "vpn-id";
      leaf vpn-id {
        description "VPN ID";
        type viptela:vpn-id;
      }
      leaf hello-rx {
        description "Hello packets received";
        type uint32;
      }
      leaf join-prune-rx {
        description "Join-prune packets received";
        type uint32;
      }
      leaf assert-rx {
        description "Assert packets received";
        type uint32;
      }
      leaf auto-rp-announce-rx {
        description "Auto-RP announce packets received";
        type uint32;
      }
      leaf auto-rp-mapping-rx {
        description "Auto-RP mapping packets received";
        type uint32;
      }
      leaf unsupported-rx {
        description "Unsupported packets received";
        type uint32;
      }
      leaf unknown-rx {
        description "Unknown packets received";
        type uint32;
      }
      leaf bad-rx {
        description "Bad packets received";
        type uint32;
      }
      leaf hello-tx {
        description "Hello packets transmitted";
        type uint32;
      }
      leaf join-prune-tx {
        description "Join-prune packets transmitted";
        type uint32;
      }
      leaf assert-tx {
        description "Assert packets transmitted";
        type uint32;
      }
    }
  }
  container igmp {
    description "IGMP information";
    when "/viptela-system:system/viptela-system:personality = 'vedge'";
    config false;
    container summary {
      description "Summary of various variables";
      leaf version {
        description "Version";
        type uint32;
      }
      leaf query-interval {
        description "Query Interval, in seconds";
        type uint32;
      }
      leaf query-response-time {
        description "Query Response Time, in seconds";
        type uint32;
      }
      leaf last-member-query-response-time {
        description "Last member query response time, in seconds";
        type uint32;
      }
      leaf last-member-query-count {
        description "Last member query count time";
        type uint32;
      }
      leaf querier-timeout {
        description "Other Querier timeout, in seconds";
        type uint32;
      }
    }
    list interface {
      description "List of interfaces";
      key "vpn-id if-name";
      leaf vpn-id {
        description "VPN ID";
        type viptela:vpn-id;
      }
      leaf if-name {
        description "Interface";
        type viptela:named-type;
      }
      leaf if-addr {
        description "Address";
        type inet:ip-prefix;
      }
      leaf group-count {
        description "Number of groups for this interface";
        type uint32;
      }
      leaf querier {
        description "Querier state on this interface";
        type boolean;
      }
      leaf querier-ip {
        description "Querier IP";
        type inet:ip-address;
      }
      leaf query-interval {
        description "Expiration of the other querier, in seconds";
        type string;
      }
      leaf state {
        description "Interface state for this interface";
        type igmp-if-state-enum;
      }
      leaf other-querier-expiry {
        description "Expiration of the other querier, in seconds";
        type string;
      }
      leaf event {
        description "Last interface event";
        type igmp-if-event-enum;
      }
    }
    list groups {
      description "List of groups";
      key "vpn-id if-name group";
      leaf vpn-id {
        description "VPN ID";
        type viptela:vpn-id;
      }
      leaf if-name {
        description "Interface name";
        type viptela:named-type;
      }
      leaf group {
        description "Group Address";
        type inet:ip-address;
      }
      leaf v1-members-present {
        description "Whether IGMPv1 members are present";
        type boolean;
      }
      leaf state {
        description "IGMP Group State";
        type igmp-group-state-enum;
      }
      leaf uptime {
        description "How long the group has been up";
        type string;
      }
      leaf expires {
        description "Expiration of the group, in seconds";
        type string;
      }
      leaf v1-expires {
        description "Time to expiration of IGMPv1 host timer, in seconds";
        type string;
      }
      leaf event {
        description "Last group event";
        type igmp-group-event-enum;
      }
    }
    list statistics {
      description "Packet statistics";
      key "vpn-id";
      leaf vpn-id {
        description "VPN ID";
        type viptela:vpn-id;
      }
      leaf rx_general_query {
        description "Rx General Query";
        type yang:counter64;
      }
      leaf rx_group_query {
        description "Rx Group Query";
        type yang:counter64;
      }
      leaf rx_v1_report {
        description "Rx V1 Report";
        type yang:counter64;
      }
      leaf rx_v2_report {
        description "Rx V2 Report";
        type yang:counter64;
      }
      leaf rx_leave {
        description "Rx Leave";
        type yang:counter64;
      }
      leaf rx_unknown {
        description "Rx Unknown";
        type yang:counter64;
      }
      leaf rx_error {
        description "Rx Error";
        type yang:counter64;
      }
      leaf tx_general_query {
        description "Tx General Query";
        type yang:counter64;
      }
      leaf tx_group_query {
        description "Tx Group Query";
        type yang:counter64;
      }
      leaf tx_error {
        description "Tx Error";
        type yang:counter64;
      }
    }
  }
}
