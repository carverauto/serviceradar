module viptela-oper-bgp {
  namespace "http://viptela.com/oper-bgp";
  prefix viptela-oper-bgp;

  import ietf-inet-types {
    prefix inet;
  }
    prefix tailf;
  }
  import viptela-common {
    prefix viptela;
  }
  import viptela-system {
    prefix viptela-system;
  }

  organization "Viptela, Inc.";
  contact
    "Viptela, Inc.
     Email:support@viptela.com";
  description
    "This module defines the data model for BGP operational data";

  revision 2019-08-15 {
    description
      "Release version: 19.2";
  }
  revision 2018-11-01 {
    description
      "Release version: 18.4";
  }
  revision 2018-08-20 {
    description
      "Release version: 18.3.1";
  }
  revision 2018-06-25 {
    description
      "Release version: 18.3";
  }
  revision 2018-04-25 {
    description
      "Release version: 18.2";
  }
  revision 2018-03-15 {
    description
      "Release version: 18.1.1";
  }
  revision 2018-01-16 {
    description
      "Release version: 17.2.3";
  }
  revision 2017-11-01 {
    description
      "Release version: 17.2.1";
  }
  revision 2017-08-01 {
    description
      "Release version: 17.2";
  }
  revision 2017-05-25 {
    description
      "Release version: 17.1.1";
  }
  revision 2017-04-06 {
    description
      "Release version: 17.1";
  }
  revision 2017-02-15 {
    description
      "Release version: 16.3.2";
  }
  revision 2017-02-06 {
    description
      "Release version: 16.3.1";
  }
  revision 2016-11-16 {
    description
      "Release version: 16.3";
  }
  revision 2016-10-25 {
    description
      "Release version: 16.2.10";
  }
  revision 2016-10-24 {
    description
      "Release version: 16.2.4";
  }
  revision 2016-08-10 {
    description
      "Release version: 16.2.2";
  }
  revision 2016-08-01 {
    description
      "Release version: 16.2.1";
  }
  revision 2016-06-09 {
    description
      "Release version: 16.2";
  }
  revision 2016-04-22 {
    description
      "Release version: 16.1.1";
  }
  revision 2016-03-15 {
    description
      "Release version: 16.1";
  }
  revision 2016-01-30 {
    description
      "Release version: 15.4.3";
  }
  revision 2015-12-28 {
    description
      "Release version: 15.4.1";
  }
  revision 2015-12-01 {
    description
      "Release version: 15.4.0";
  }
  revision 2015-10-31 {
    description
      "Release version: 15.3.5";
  }
  revision 2015-09-27 {
    description
      "Release version: 15.3.3";
  }
  revision 2015-09-01 {
    description
      "Release version: 15.3.1";
  }
  revision 2015-07-01 {
    description
      "Release version: 15.3";
  }
  revision 2015-06-01 {
    description
      "Release version: 15.2.8";
  }
  revision 2015-05-01 {
    description
      "Release version: 15.2";
  }
  revision 2015-02-01 {
    description
      "Release version: 15.1";
  }
  revision 2014-12-01 {
    description
      "Release version: 14.3";
  }
  revision 2014-07-01 {
    description
      "Release version: 14.2";
  }
  revision 2013-02-12 {
    description
      "Initial revision";
  }

  typedef bgp-rib-status-type {
    type bits {
      bit valid;
      bit best;
      bit internal;
      bit external;
      bit removed;
      bit stale;
      bit history;
      bit damped;
      bit inaccessible;
      bit multipath;
    }
  }

  container bgp {
    description "Display BGP information";
    when "/viptela-system:system/viptela-system:personality = 'vedge'";
    list bgp-summary {
      description "BGP summary";
      config false;
      key "vpn-id";
      leaf vpn-id {
        description "VPN ID";
        type viptela:vpn-id;
      }
      leaf bgp-router-identifier {
        description "Router ID";
        type inet:ipv4-address;
      }
      leaf local-as {
        description "Local AS number";
        type uint32;
      }
      leaf rib-entries {
        description "RIB count";
        type uint32;
      }
      leaf rib-memory {
        description "RIB memory usage, in bytes";
        type uint32;
      }
      leaf total-peers {
        description "Total number of BGP neighbors";
        type uint32;
      }
      leaf peer-memory {
        description "Neighbor memory usage, in bytes";
        type uint32;
      }
      leaf local-site-of-origin {
        description "Local site-of-origin extended community added to OMP routes in BGP";
        type string;
      }
      leaf ignore-site-of-origin {
        description "Ignore site-of-origin value in BGP";
        type boolean;
      }
      list neighbor {
        description "List of neighbors";
        key "peer-addr";
        leaf peer-addr {
          description "Neighbor address";
          type inet:ipv4-address;
        }
        leaf as {
          description "Neighbor AS number";
          type uint32;
        }
        leaf msg-rcvd {
          description "Number of messages received";
          type uint32;
        }
        leaf msg-sent {
          description "Number of messages sent";
          type uint32;
        }
        leaf outQ {
          description "Outbound queue";
          type uint32;
        }
        leaf prefix-rcvd {
          description "Number of routes received";
          type uint32;
        }
        leaf prefix-valid {
          description "Number of valid routes";
          type uint32;
        }
        leaf prefix-installed {
          description "Number of installed routes";
          type uint32;
        }
        leaf up-time {
          description "Uptime (Days:Hours:Minutes:Seconds)";
          type string;
        }
        leaf state {
          description "State";
          type viptela:bgp-state;
        }
        leaf last-up-time {
          description "Last uptime (Days:Hours:Minutes:Seconds)";
          type string;
        }
      }
    }
    list routes-table {
      description "List of routes";
      config false;
      key "vpn-id prefix";
      leaf vpn-id {
        description "VPN ID";
        type viptela:vpn-id;
      }
      leaf prefix {
        description "Route prefix";
        type inet:ipv4-prefix;
      }
      leaf best-path {
        description "Best path";
        type uint32;
      }
      leaf suppressed {
        description "Advertisements suppressed";
        type boolean;
      }
      leaf no-advertise {
        description "Not advertised to any peer";
        type boolean;
      }
      leaf no-export {
        description "Not advertised to EBGP peer";
        type boolean;
      }
      leaf no-local-as {
        description "Not advertised outside local AS";
        type boolean;
      }
      list advertised-peers {
        description "List of peers";
        key "peer-index";
        leaf peer-index {
          description "Peer address";
          type uint32;
        }
        leaf peer-addr {
          description "Peer address";
          type inet:ipv4-address;
        }
      }
      list info {
        key "info-id";
        description "Route information";
        leaf info-id {
          description "Route information index";
          type uint32;
        }
        leaf nexthop {
          description "Next-hop IP address";
          type inet:ipv4-address;
        }
        leaf metric {
          description "Metric";
          type uint32;
        }
        leaf local-pref {
          description "Local preference";
          type uint32;
        }
        leaf weight {
          description "Weight";
          type uint32;
        }
        leaf origin {
          description "Origin";
          type enumeration {
            enum "igp";
            enum "egp";
            enum "incomplete";
          }
        }
        leaf as-path {
          description "AS path";
          type string;
        }
        leaf rr-client {
          description "Received from a route reflector client";
          type boolean;
        }
        leaf history {
          description "History entry";
          type boolean;
        }
        leaf aggregator {
          description "Aggregated";
          type boolean;
        }
        leaf aggregator-as {
          description "Aggregator AS number";
          type uint32;
        }
        leaf aggregator-ip {
          description "Aggregator IP address";
          type inet:ipv4-address;
        }
        leaf ri-peer {
          description "Peer address";
          type inet:ipv4-address;
        }
        leaf ri-routerid {
          description "Router ID";
          type inet:ipv4-address;
        }
        leaf igp-metric {
          description "IGP metric";
          type uint32;
        }
        leaf confed-external {
          description "EBGP confederation";
          type boolean;
        }
        leaf aggregated {
          description "Aggregated";
          type boolean;
        }
        leaf local {
          description "Local";
          type boolean;
        }
        leaf sourced {
          description "Sourced";
          type boolean;
        }
        leaf multipath {
          status obsolete;
          description "Multipath";
          type boolean;
        }
        leaf community {
          description "Community";
          type viptela:named-type;
        }
        leaf ext-community {
          description "Extended community";
          type viptela:named-type;
        }
        leaf originator {
          description "Attribute originator ID";
          type inet:ipv4-address;
        }
        leaf last-update {
          description "Time";
          type viptela:named-type;
        }
        leaf cluster-list {
          description "Cluster list";
          type string;
        }
        leaf path-status {
          description "BGP path status";
          type bgp-rib-status-type;
        }
        leaf tag {
          description "Tag";
          type uint32;
        }
      }
    }
    list best-match-route {
      description "List of routes";
      config false;
      key "vpn-id route-addr";
      leaf vpn-id {
        description "VPN ID";
        type viptela:vpn-id;
      }
      leaf route-addr {
        type inet:ipv4-address;
      }
      leaf prefix {
        description "Route prefix";
        type inet:ipv4-prefix;
      }
      leaf best-path {
        description "Best path";
        type uint32;
      }
      leaf suppressed {
        description "Advertisements suppressed";
        type boolean;
      }
      leaf no-advertise {
        description "Not advertised to any peer";
        type boolean;
      }
      leaf no-export {
        description "Not advertised to EBGP peer";
        type boolean;
      }
      leaf no-local-as {
        description "Not advertised outside local AS";
        type boolean;
      }
      list advertised-peers {
        description "List of peers";
        leaf peer-addr {
          description "Peer address";
          type inet:ipv4-address;
        }
      }
      list info {
        key "info-id";
        description "Route information";
        leaf info-id {
          description "Route information index";
          type uint32;
        }
        leaf nexthop {
          description "Next-hop IP address";
          type inet:ipv4-address;
        }
        leaf metric {
          description "Metric";
          type uint32;
        }
        leaf local-pref {
          description "Local preference";
          type uint32;
        }
        leaf weight {
          description "Weight";
          type uint32;
        }
        leaf origin {
          description "Origin";
          type enumeration {
            enum "igp";
            enum "egp";
            enum "incomplete";
          }
        }
        leaf as-path {
          description "AS path";
          type string;
        }
        leaf rr-client {
          description "Received from a route reflector client";
          type boolean;
        }
        leaf history {
          description "History entry";
          type boolean;
        }
        leaf aggregator {
          description "Aggregated";
          type boolean;
        }
        leaf aggregator-as {
          description "Aggregator AS number";
          type uint32;
        }
        leaf aggregator-ip {
          description "Aggregator IP address";
          type inet:ipv4-address;
        }
        leaf ri-peer {
          description "Peer address";
          type inet:ipv4-address;
        }
        leaf ri-routerid {
          description "Router ID";
          type inet:ipv4-address;
        }
        leaf igp-metric {
          description "IGP metric";
          type uint32;
        }
        leaf confed-external {
          description "EBGP confederation";
          type boolean;
        }
        leaf aggregated {
          description "Aggregated";
          type boolean;
        }
        leaf local {
          description "Local";
          type boolean;
        }
        leaf sourced {
          description "Sourced";
          type boolean;
        }
        leaf multipath {
          status obsolete;
          description "Multipath";
          type boolean;
        }
        leaf community {
          description "Community";
          type viptela:named-type;
        }
        leaf ext-community {
          description "Extended community";
          type viptela:named-type;
        }
        leaf originator {
          description "Attribute originator ID";
          type inet:ipv4-address;
        }
        leaf last-update {
          description "Time";
          type viptela:named-type;
        }
        leaf cluster-list {
          description "Cluster list";
          type string;
        }
        leaf path-status {
          description "BGP path status";
          type bgp-rib-status-type;
        }
        leaf tag {
          description "Tag";
          type uint32;
        }
      }
    }
    list bgp-neighbor {
      description "List of neighbors";
      config false;
      key "vpn-id peer-addr";
      leaf vpn-id {
        description "VPN ID";
        type viptela:vpn-id;
      }
      leaf peer-addr {
        description "Neighbor address";
        type inet:ipv4-address;
      }
      leaf as {
        description "Neighbor AS number";
        type uint32;
      }
      leaf local-as-num {
        description "Local AS number";
        type uint32;
      }
      leaf change-local-as-num {
        description "Change local AS number";
        type boolean;
      }
      leaf flags {
        description "Flags";
        type uint32;
      }
      leaf desc {
        description "Description";
        type viptela:named-type;
      }
      leaf remote-router-id {
        description "Remote router ID";
        type inet:ipv4-address;
      }
      leaf common-admin {
        description "Common administrator";
        type boolean;
      }
      leaf last-read {
        description "Last read time, in seconds";
        type uint32;
      }
      leaf keepalive {
        description "Keepalive time";
        type uint32;
      }
      leaf holdtime {
        description "Hold time";
        type uint32;
      }
      leaf cfg-keepalive {
        description "Configured keepalive time";
        type uint32;
      }
      leaf cfg-holdtime {
        description "Configured holdtime";
        type uint32;
      }
      leaf adv-4byte-as-cap {
        description "Advertised 4-byte AS capability";
        type boolean;
      }
      leaf rec-4byte-as-cap {
        description "Received 4-byte AS capability";
        type boolean;
      }
      leaf adv-dynamic-cap {
        description "Advertised dynamic capability";
        type boolean;
      }
      leaf rec-dynamic-cap {
        description "Received dynamic capability";
        type boolean;
      }
      leaf adv-refresh-cap {
        description "Advertised route refresh capability";
        type boolean;
      }
      leaf rec-refresh-cap {
        description "Received route refresh capability";
        type boolean;
      }
      leaf adv-new-refresh-cap {
        description "Advertised new route refresh capability";
        type boolean;
      }
      leaf rec-new-refresh-cap {
        description "Received new route refresh capability";
        type boolean;
      }
      leaf adv-ipv4-unicast-addr-family {
        description "Advertised IPv4 unicast address family";
        type boolean;
      }
      leaf rec-ipv4-unicast-addr-family {
        description "Received IPv4 unicast address family";
        type boolean;
      }
      leaf restart-time-left {
        description "Restart time remaining, in seconds";
        type uint32;
      }
      leaf stalepath-time-left {
        description "Stale path time remaining, in seconds";
        type uint32;
      }
      leaf msg-rcvd {
        description "Total messages input count";
        type uint32;
      }
      leaf msg-sent {
        description "Total messages output count";
        type uint32;
      }
      leaf prefix-rcvd {
        description "Number of routes received";
        type uint32;
      }
      leaf prefix-valid {
        description "Number of valid routes";
        type uint32;
      }
      leaf prefix-installed {
        description "Number of installed routes";
        type uint32;
      }
      leaf outQ {
        description "Output queue depth";
        type uint32;
      }
      leaf uptime {
        description "Uptime (Days:Hours:Minutes:Seconds)";
        type string;
      }
      leaf state {
        description "State";
        type viptela:bgp-state;
      }
      leaf open-in-count {
        description "Open message input count";
        type uint32;
      }
      leaf open-out-count {
        description "Open message output count";
        type uint32;
      }
      leaf notify-in-count {
        description "Notify input count";
        type uint32;
      }
      leaf notify-out-count {
        description "Notify output count";
        type uint32;
      }
      leaf update-in-count {
        description "Update message input count";
        type uint32;
      }
      leaf update-out-count {
        description "Update message output count";
        type uint32;
      }
      leaf keepalive-in-count {
        description "Keepalive message input count";
        type uint32;
      }
      leaf keepalive-out-count {
        description "Keepalive message output count";
        type uint32;
      }
      leaf refresh-in-count {
        description "Route refresh message input count";
        type uint32;
      }
      leaf refresh-out-count {
        description "Route refresh message output count";
        type uint32;
      }
      leaf dynamic-in-count {
        description "Dynamic capability message input count";
        type uint32;
      }
      leaf dynamic-out-count {
        description "Dynamic capability message output count";
        type uint32;
      }
      leaf adv-interval {
        description "Time between advertisements, in seconds";
        type uint32;
      }
      leaf update-source {
        description "Update source";
        type inet:ipv4-address;
      }
      leaf update-if {
        description "Update interface";
        type viptela:named-type;
      }
      leaf weight {
        description "Weight";
        type uint32;
      }
      leaf conn-established {
        description "Connections established";
        type uint32;
      }
      leaf conn-dropped {
        description "Connections dropped";
        type uint32;
      }
      leaf last-reset-time {
        description "Last reset time";
        type uint32;
      }
      leaf last-reset-reason {
        description "Last reset reason";
        type viptela:named-type;
      }
      leaf max-prefix-restart-time {
        description "Restart time after maximum prefix reached";
        type uint32;
      }
      leaf ext-peer-hops {
        description "EBGP neighbor hops";
        type uint32;
      }
      leaf local-host {
        description "Local host";
        type inet:ipv4-address;
      }
      leaf local-port {
        description "Local port";
        type uint16;
      }
      leaf remote-host {
        description "Remote host";
        type inet:ipv4-address;
      }
      leaf remote-port {
        description "Remote port";
        type inet:port-number;
      }
      leaf next-hop {
        description "Next hop";
        type inet:ipv4-address;
      }
      leaf next-start-timer {
        description "Next start timer";
        type uint32;
      }
      leaf next-connect-timer {
        description "Next connect timer";
        type uint32;
      }
      leaf read-thread-on {
        description "Read thread on";
        type boolean;
      }
      leaf write-thread-on {
        description "Write thread on";
        type boolean;
      }
      leaf password {
        description "MD5 key (hashed)";
        type viptela:named-type;
      }
      leaf last-uptime {
        description "Last uptime (Days:Hours:Minutes:Seconds)";
        type string;
      }
      list address-family {
        key "afi-id";
        description "Address family information";
        leaf afi-id {
          description "Address family Index";
          type uint32;
        }
        leaf afi {
          description "Address family";
          type viptela:bgp-afi-type;
        }
        leaf route-reflector-client {
          description "Route reflector client";
          type boolean;
        }
        leaf inbound-soft-reconfig {
          description "Inbound soft reconfiguration allowed";
          type boolean;
        }
        leaf private-as {
          description "Private AS number removed";
          type boolean;
        }
        leaf nexthop-self {
          description "Next hop is this router";
          type boolean;
        }
        leaf as-path-unchanged {
          description "AS path propogated unchanged";
          type boolean;
        }
        leaf nexthop-unchanged {
          description "Next hop unchanged";
          type boolean;
        }
        leaf med-unchanged {
          description "MED propogated unchanged";
          type boolean;
        }
        leaf sent-community {
          description "Sent community attribute";
          type boolean;
        }
        leaf def-originate-routemap {
          description "Default originate route map";
          type viptela:named-type;
        }
        leaf sent-def-originate {
          description "Default originate sent";
          type boolean;
        }
        leaf policy-in {
          description "Inbound path policy configured";
          type boolean;
        }
        leaf policy-out {
          description "Outbound path policy configured";
          type boolean;
        }
        leaf accepted-prefix-count {
          description "Accepted prefix count";
          type uint32;
        }
        leaf maximum-prefix-count {
          description "Maximum prefix count";
          type uint32;
        }
        leaf max-prefix-warning-only {
          description "Warning only";
          type boolean;
        }
        leaf max-prefix-threshold-warning {
          description "Threshold for warning";
          type uint32;
        }
        leaf max-prefix-restart-interval {
          description "Threshold for restart interval";
          type uint32;
        }
      }
    }
  }
}
