module viptela-traps {
  namespace "http://tail-f.com/ns/mibs/VIPTELA-TRAPS/201502150000Z";
  prefix VIPTELA_TRAPS;

  import ietf-yang-types {
    prefix yang;
  }
  import viptela-common {
    prefix viptela;
  }

  revision 2019-08-15 {
    description
      "Release version: 19.2";
  }
  revision 2018-11-01 {
    description
      "Release version: 18.4";
  }
  revision 2018-08-20 {
    description
      "Release version: 18.3.1";
  }
  revision 2018-06-25 {
    description
      "Release version: 18.3";
  }
  revision 2018-04-25 {
    description
      "Release version: 18.2";
  }
  revision 2018-03-15 {
    description
      "Release version: 18.1.1";
  }
  revision 2018-01-16 {
    description
      "Release version: 17.2.3";
  }
  revision 2017-11-01 {
    description
      "Release version: 17.2.1";
  }
  revision 2017-08-01 {
    description
      "Release version: 17.2";
  }
  revision 2017-05-25 {
    description
      "Release version: 17.1.1";
  }
  revision 2017-04-06 {
    description
      "Release version: 17.1";
  }
  revision 2017-02-15 {
    description
      "Release version: 16.3.2";
  }
  revision 2017-02-06 {
    description
      "Release version: 16.3.1";
  }
  revision 2016-11-16 {
    description
      "Release version: 16.3";
  }
  revision 2016-10-25 {
    description
      "Release version: 16.2.10";
  }
  revision 2016-10-24 {
    description
      "Release version: 16.2.4";
  }
  revision 2016-08-10 {
    description
      "Release version: 16.2.2";
  }
  revision 2016-08-01 {
    description
      "Release version: 16.2.1";
  }
  revision 2016-06-09 {
    description
      "Release version: 16.2";
  }
  revision 2016-04-22 {
    description
      "Release version: 16.1.1";
  }
  revision 2016-03-15 {
    description
      "Release version: 16.1";
  }
  revision 2016-01-30 {
    description
      "Release version: 15.4.3";
  }
  revision 2015-12-28 {
    description
      "Release version: 15.4.1";
  }
  revision 2015-12-01 {
    description
      "Release version: 15.4.0";
  }
  revision 2015-10-31 {
    description
      "Release version: 15.3.5";
  }
  revision 2015-09-27 {
    description
      "Release version: 15.3.3";
  }
  revision 2015-09-01 {
    description
      "Release version: 15.3.1";
  }
  revision 2015-07-01 {
    description
      "Release version: 15.3";
  }
  revision 2015-06-01 {
    description
      "Release version: 15.2.8";
  }
  revision 2015-05-01 {
    description
      "Release version: 15.2";
  }

  container VIPTELA-TRAPS {
    container fields {
      config false;
      leaf eventTime {
        type yang:date-and-time;
        config false;
      }
      leaf netconfNotificationSeverity {
        type NetconfNotificationSeverity;
        config false;
      }
      leaf viptelaActionsRebootReason {
        type hex-list;
        config false;
      }
      leaf viptelaBfdSrcIp {
        type ViptelaIpAddress;
        config false;
      }
      leaf viptelaBfdDstIp {
        type ViptelaIpAddress;
        config false;
      }
      leaf viptelaBfdProto {
        type EncapEnum;
        config false;
      }
      leaf viptelaBfdSrcPort {
        type uint32;
        config false;
      }
      leaf viptelaBfdDstPort {
        type uint32;
        config false;
      }
      leaf viptelaBfdLocalSystemIp {
        type ViptelaIpAddress;
        config false;
      }
      leaf viptelaBfdLocalColor {
        type hex-list;
        config false;
      }
      leaf viptelaBfdRemoteSystemIp {
        type ViptelaIpAddress;
        config false;
      }
      leaf viptelaBfdRemoteColor {
        type hex-list;
        config false;
      }
      leaf viptelaBfdNewState {
        type OperState;
        config false;
      }
      leaf viptelaHardwareNewState {
        type FailureStateEnum;
        config false;
      }
      leaf viptelaHardwareHwSensorType {
        type HwSensorTypeEnum;
        config false;
      }
      leaf viptelaHardwareHwDevIndex {
        type uint32;
        config false;
      }
      leaf viptelaHardwareName {
        type hex-list;
        config false;
      }
      leaf viptelaHardwareTemp {
        type uint32;
        config false;
      }
      leaf viptelaHardwareFantrayId {
        type uint32;
        config false;
      }
      leaf viptelaHardwareFanId {
        type uint32;
        config false;
      }
      leaf viptelaHardwarePemId {
        type uint32;
        config false;
      }
      leaf viptelaHardwarePimId {
        type uint32;
        config false;
      }
      leaf viptelaHardwareSfpName {
        type hex-list;
        config false;
      }
      leaf viptelaHardwareUsbSlot {
        type uint32;
        config false;
      }
      leaf viptelaOmpNumberOfVsmarts {
        type uint32;
        config false;
      }
      leaf viptelaOmpNewState {
        type OperState;
        config false;
      }
      leaf viptelaOmpPeer {
        type ViptelaIpAddress;
        config false;
      }
      leaf viptelaOmpPeerNewState {
        type PeerState;
        config false;
      }
      leaf viptelaOmpOmpAddressFamily {
        type AfTypeEnum;
        config false;
      }
      leaf viptelaOmpPolicy {
        type OmpPolicyState;
        config false;
      }
      leaf viptelaOmpVsmartPeer {
        type ViptelaIpAddress;
        config false;
      }
      leaf viptelaSecurityPeerType {
        type PersonalityEnumOper;
        config false;
      }
      leaf viptelaSecurityPeerSystemIp {
        type ViptelaIpAddress;
        config false;
      }
      leaf viptelaSecurityPublicIp {
        type ViptelaIpAddress;
        config false;
      }
      leaf viptelaSecurityPublicPort {
        type uint32;
        config false;
      }
      leaf viptelaSecuritySrcColor {
        type ColorEnum;
        config false;
      }
      leaf viptelaSecurityRemoteColor {
        type ColorEnum;
        config false;
      }
      leaf viptelaSecurityUptime {
        type hex-list;
        config false;
      }
      leaf viptelaSecurityNewState {
        type OperState;
        config false;
      }
      leaf viptelaSecurityLocalSystemIp {
        type ViptelaIpAddress;
        config false;
      }
      leaf viptelaSecurityLocalColor {
        type ColorEnum;
        config false;
      }
      leaf viptelaSecurityReason {
        type hex-list;
        config false;
      }
      leaf viptelaSecurityOldPublicIp {
        type ViptelaIpAddress;
        config false;
      }
      leaf viptelaSecurityOldPublicPort {
        type uint32;
        config false;
      }
      leaf viptelaSecurityNewPublicIp {
        type ViptelaIpAddress;
        config false;
      }
      leaf viptelaSecurityNewPublicPort {
        type uint32;
        config false;
      }
      leaf viptelaSecurityColor {
        type ColorEnum;
        config false;
      }
      leaf viptelaSecurityPersonality {
        type PersonalityEnumOper;
        config false;
      }
      leaf viptelaSecurityUuid {
        type hex-list;
        config false;
      }
      leaf viptelaSecuritySerial {
        type hex-list;
        config false;
      }
      leaf viptelaSystemProcessName {
        type hex-list;
        config false;
      }
      leaf viptelaSystemProcessId {
        type uint32;
        config false;
      }
      leaf viptelaSystemReason {
        type hex-list;
        config false;
      }
      leaf viptelaSystemWarning {
        type hex-list;
        config false;
      }
      leaf viptelaSystemTotalMb {
        type uint32;
        config false;
      }
      leaf viptelaSystemFreeMb {
        type uint32;
        config false;
      }
      leaf viptelaSystemOldSiteId {
        type SiteId;
        config false;
      }
      leaf viptelaSystemNewSiteId {
        type SiteId;
        config false;
      }
      leaf viptelaSystemOldDomainId {
        type DomainId;
        config false;
      }
      leaf viptelaSystemNewDomainId {
        type DomainId;
        config false;
      }
      leaf viptelaSystemOldSystemIp {
        type ViptelaIpAddress;
        config false;
      }
      leaf viptelaSystemNewSystemIp {
        type ViptelaIpAddress;
        config false;
      }
      leaf viptelaSystemOldOrganizationName {
        type hex-list;
        config false;
      }
      leaf viptelaSystemNewOrganizationName {
        type hex-list;
        config false;
      }
      leaf viptelaSystemUserName {
        type hex-list;
        config false;
      }
      leaf viptelaSystemUserId {
        type int32;
        config false;
      }
      leaf viptelaVpnVpnId {
        type VpnId;
        config false;
      }
      leaf viptelaVpnPeer {
        type ViptelaIpAddress;
        config false;
      }
      leaf viptelaVpnBgpNewState {
        type BgpState;
        config false;
      }
      leaf viptelaVpnLocalAddress {
        type ViptelaIpAddress;
        config false;
      }
      leaf viptelaVpnLocalRouterid {
        type ViptelaIpAddress;
        config false;
      }
      leaf viptelaVpnPeerRouterid {
        type ViptelaIpAddress;
        config false;
      }
      leaf viptelaVpnIfName {
        type hex-list;
        config false;
      }
      leaf viptelaVpnNewState {
        type OperState;
        config false;
      }
      leaf viptelaVpnGrpId {
        type uint32;
        config false;
      }
      leaf viptelaVpnIpPrefix {
        type viptelaVpnIpPrefixType;
        config false;
      }
      leaf viptelaVpnFailureReason {
        type hex-list;
        config false;
      }
      leaf viptelaVpnFarEndSystemIp {
        type ViptelaIpAddress;
        config false;
      }
      leaf viptelaVpnFarEndColor {
        type ColorEnum;
        config false;
      }
      leaf viptelaVpnClientMac {
        type hex-list;
        config false;
      }
      leaf viptelaVpnIp {
        type ViptelaIpAddress;
        config false;
      }
      leaf viptelaVpnReason {
        type hex-list;
        config false;
      }
      leaf viptelaVpnState {
        type Enumeration;
        config false;
      }
      leaf viptelaVpnNeighbor {
        type ViptelaIpAddress;
        config false;
      }
      leaf viptelaVpnPimNewState {
        type StateEnum;
        config false;
      }
      leaf viptelaVpnInterface {
        type hex-list;
        config false;
      }
      leaf viptelaVpnTunnelAddress {
        type ViptelaIpAddress;
        config false;
      }
      leaf viptelaVpnRouterId {
        type ViptelaIpAddress;
        config false;
      }
      leaf viptelaVpnOspfNewState {
        type OspfStateEnum;
        config false;
      }
      leaf viptelaVpnIfAddr {
        type Ipv4UcastAddrPrefix;
        config false;
      }
      leaf viptelaVpnOspfInterfaceNewState {
        type OspfIfStateEnum;
        config false;
      }
      leaf viptelaVpnVrrpGroupState {
        type VrrpGroupStateEnum;
        config false;
      }
      leaf viptelaSystemStatusStr {
        type hex-list;
        config false;
      }
      leaf viptelaAppRouteSrcIp {
        type ViptelaIpAddress;
        config false;
      }
      leaf viptelaAppRouteDstIp {
        type ViptelaIpAddress;
        config false;
      }
      leaf viptelaAppRouteProto {
        type EncapEnum;
        config false;
      }
      leaf viptelaAppRouteSrcPort {
        type uint32;
        config false;
      }
      leaf viptelaAppRouteDstPort {
        type uint32;
        config false;
      }
      leaf viptelaAppRouteLocalSystemIp {
        type ViptelaIpAddress;
        config false;
      }
      leaf viptelaAppRouteLocalColor {
        type hex-list;
        config false;
      }
      leaf viptelaAppRouteRemoteSystemIp {
        type ViptelaIpAddress;
        config false;
      }
      leaf viptelaAppRouteRemoteColor {
        type hex-list;
        config false;
      }
      leaf viptelaAppRouteMeanLoss {
        type uint8;
        config false;
      }
      leaf viptelaAppRouteMeanLatency {
        type uint32;
        config false;
      }
      leaf viptelaAppRouteSlaClasses {
        type hex-list;
        config false;
      }
      leaf viptelaActionsStatus {
        type InstallationStatus;
        config false;
      }
      leaf viptelaActionsInstallId {
        type hex-list;
        config false;
      }
      leaf viptelaActionsMessage {
        type hex-list;
        config false;
      }
      leaf viptelaVpnOperState {
        type StateEnum;
        config false;
      }
      leaf viptelaVpnAdminState {
        type AdminStateEnum;
        config false;
      }
      leaf viptelaVpnAddressFamilyType {
        type AddressFamilyEnum;
        config false;
      }
      leaf viptelaVpnFibLastUpdateTime {
        type yang:date-and-time;
        config false;
      }
      leaf viptelaBridgeId {
        type BridgeId;
        config false;
      }
      leaf viptelaNumMacs {
        type NumMacs;
        config false;
      }
      leaf viptelaPolicyVpnId {
        type VpnId;
        config false;
      }
      leaf viptelaPolicyApplication {
        type hex-list;
        config false;
      }
      leaf viptelaPolicySourceIp {
        type ViptelaIpAddress;
        config false;
      }
      leaf viptelaPolicySourcePort {
        type uint32;
        config false;
      }
      leaf viptelaPolicyDestinationIp {
        type ViptelaIpAddress;
        config false;
      }
      leaf viptelaPolicyDestinationPort {
        type uint32;
        config false;
      }
      leaf viptelaPolicyProtocol {
        type uint32;
        config false;
      }
      leaf viptelaPolicyDscp {
        type uint32;
        config false;
      }
      leaf viptelaPolicySlaInformation {
        type hex-list;
        config false;
      }
      leaf viptelaPolicySlaStatus {
        type hex-list;
        config false;
      }
      leaf viptelaSystemDpiOutOfMemoryState {
        type boolean;
        config false;
      }
      leaf viptelaBfdDeleted {
        type BoolEnum;
        config false;
      }
      leaf viptelaSecurityGreOldOperState {
        type OperState;
        config false;
      }
      leaf viptelaSecurityGreNewOperState {
        type OperState;
        config false;
      }
      leaf viptelaSecurityGreIfName {
        type hex-list;
        config false;
      }
      leaf viptelaSecurityGreVpnId {
        type VpnId;
        config false;
      }
      leaf viptelaSecurityGreTunnelSource {
        type ViptelaIpAddress;
        config false;
      }
      leaf viptelaSecurityGreTunnelDestination {
        type ViptelaIpAddress;
        config false;
      }
      leaf viptelaSecurityGreGreIp {
        type hex-list;
        config false;
      }
      leaf viptelaVpnIfCfgBwKbps {
        type uint32;
        config false;
      }
      leaf viptelaVpnTrafficDirection {
        type TrafficDirectionEnum;
        config false;
      }
      leaf viptelaVpnDuration {
        type uint32;
        config false;
      }
      leaf viptelaAppRouteMeanJitter {
        type uint32;
        config false;
      }
      leaf viptelaVpnPimEnabled {
        type boolean;
        config false;
      }
      leaf viptelaSystemRemoteHost {
        type string;
        config false;
      }
      leaf viptelaPolicyVpnListName {
        type hex-list;
        config false;
      }
      leaf viptelaPolicyName {
        type hex-list;
        config false;
      }
      leaf viptelaPolicyAccessListName {
        type hex-list;
        config false;
      }
      leaf viptelaPolicyStatus {
        type hex-list;
        config false;
      }
      leaf viptelaSecurityVmanageConnectionPreference {
        type uint8;
        config false;
      }
      leaf viptelaHardwareSensorNewState {
        type SensorStateEnum;
        config false;
      }
      leaf viptelaCloudExpressApplication {
        type CloudAppEnum;
        config false;
      }
      leaf viptelaCloudExpressExitType {
        type CloudExitEnum;
        config false;
      }
      leaf viptelaGatewayIp {
        type ViptelaIpAddress;
        config false;
      }
      leaf viptelaAppLatency {
        type uint32;
        config false;
      }
      leaf viptelaAppLoss {
        type uint32;
        config false;
      }
      leaf viptelaWwanSimSlot {
        type uint32;
        config false;
      }
      leaf viptelaWwanSimState {
        type SimStateEnum;
        config false;
      }
      leaf viptelaAppRouteOldSlaClasses {
        type hex-list;
        config false;
      }
      leaf viptelaVpnNewAdminState {
        type AdminState;
        config false;
      }
      leaf viptelaWwanDomainState {
        type DomainStateEnum;
        config false;
      }
      leaf viptelaWwanRegState {
        type RegStateEnum;
        config false;
      }
      leaf viptelaWwanBearer {
        type BearerEnum;
        config false;
      }
      leaf viptelaActionsReason {
        type hex-list;
        config false;
      }
      leaf viptelaWwanIfname {
        type hex-list;
        config false;
      }
      leaf viptelaExitLocalColor {
        type hex-list;
        config false;
      }
      leaf viptelaExitRemoteColor {
        type hex-list;
        config false;
      }
      leaf viptelaSecurityOrganizationName {
        type hex-list;
        config false;
      }
      leaf viptelaSecuritySpOrganizationName {
        type hex-list;
        config false;
      }
      leaf viptelaBfdFlapReason {
        type BfdFlapReasonEnum;
        config false;
      }
      leaf viptelaSecurityPeerVmanageSystemIp {
        type ViptelaIpAddress;
        config false;
      }
      leaf viptelaPolicySvcVpnId {
        type VpnId;
        config false;
      }
      leaf viptelaPolicySvcZonePair {
        type string;
        config false;
      }
      leaf viptelaPolicySourceVpn {
        type VpnId;
        config false;
      }
      leaf viptelaPolicyDestinationVpn {
        type VpnId;
        config false;
      }
      leaf viptelaPolicyState {
        type string;
        config false;
      }
      leaf viptelaPolicyCurrFlows {
        type uint32;
        config false;
      }
      leaf viptelaPolicyHthreshFlows {
        type uint32;
        config false;
      }
      leaf viptelaPolicyLthreshFlows {
        type uint32;
        config false;
      }
      leaf viptelaPolicyMaxFlows {
        type uint32;
        config false;
      }
      leaf viptelaPolicyAction {
        type string;
        config false;
      }
      leaf viptelaPolicyCurrHalfOpenFlows {
        type uint32;
        config false;
      }
      leaf viptelaPolicyHthreshHalfOpenFlows {
        type uint32;
        config false;
      }
      leaf viptelaPolicyMaxHalfOpenFlows {
        type uint32;
        config false;
      }
      leaf viptelaPolicyLthreshHalfOpenFlows {
        type uint32;
        config false;
      }
      leaf viptelaPolicySlaName {
        type hex-list;
        config false;
      }
      leaf viptelaPolicySlaOperation {
        type hex-list;
        config false;
      }
      leaf viptelaPolicySlaLoss {
        type uint8;
        config false;
      }
      leaf viptelaPolicySlaLatency {
        type uint32;
        config false;
      }
      leaf viptelaPolicySlaJitter {
        type uint32;
        config false;
      }
      leaf viptelaWwanQosState {
        type QosStateEnum;
        config false;
      }
    }
  }

  typedef NetconfNotificationSeverity {
    type enumeration {
      enum "critical" {
        value 1;
      }
      enum "major" {
        value 2;
      }
      enum "minor" {
        value 3;
      }
    }
  }

  typedef DomainId {
    type uint32 {
      range "0 .. 4294967295";
    }
  }

  typedef BoolEnum {
    type enumeration {
      enum "false" {
        value 0;
      }
      enum "true" {
        value 1;
      }
    }
  }

  typedef BfdFlapReasonEnum {
    type enumeration {
      enum "bfd-deleted" {
        value 1;
      }
      enum "remote-down" {
        value 2;
      }
      enum "timeout" {
        value 3;
      }
      enum "na" {
        value 4;
      }
      enum "not-known" {
        value 5;
      }
    }
  }

  typedef ColorEnum {
    type enumeration {
      enum "default" {
        value 1;
      }
      enum "mpls" {
        value 2;
      }
      enum "metro-ethernet" {
        value 3;
      }
      enum "biz-internet" {
        value 4;
      }
      enum "public-internet" {
        value 5;
      }
      enum "lte" {
        value 6;
      }
      enum "threeG" {
        value 7;
      }
      enum "red" {
        value 8;
      }
      enum "green" {
        value 9;
      }
      enum "blue" {
        value 10;
      }
      enum "gold" {
        value 11;
      }
      enum "silver" {
        value 12;
      }
      enum "bronze" {
        value 13;
      }
      enum "custom1" {
        value 14;
      }
      enum "custom2" {
        value 15;
      }
      enum "custom3" {
        value 16;
      }
      enum "private1" {
        value 17;
      }
      enum "private2" {
        value 18;
      }
      enum "private3" {
        value 19;
      }
      enum "private4" {
        value 20;
      }
      enum "private5" {
        value 21;
      }
      enum "private6" {
        value 22;
      }
    }
  }

  typedef VpnId {
    type uint32 {
      range "0 .. 65530";
    }
  }

  typedef FailureStateEnum {
    type enumeration {
      enum "oK" {
        value 0;
      }
      enum "failed" {
        value 1;
      }
    }
  }

  typedef SensorStateEnum {
    type enumeration {
      enum "Green" {
        value 0;
      }
      enum "Yellow" {
        value 1;
      }
      enum "Red" {
        value 2;
      }
    }
  }

  typedef AfTypeEnum {
    type enumeration {
      enum "tloc-ipv4" {
        value 0;
      }
      enum "tloc-ipv6" {
        value 1;
      }
      enum "service" {
        value 2;
      }
      enum "route-ipv4" {
        value 3;
      }
      enum "route-ipv6" {
        value 4;
      }
      enum "mcast-ipv4" {
        value 5;
      }
      enum "mcast-ipv6" {
        value 6;
      }
    }
  }

  typedef OperState {
    type enumeration {
      enum "up" {
        value 0;
      }
      enum "down" {
        value 1;
      }
    }
  }

  typedef AdminState {
    type enumeration {
      enum "up" {
        value 0;
      }
      enum "down" {
        value 1;
      }
    }
  }

  typedef SiteId {
    type uint32 {
      range "0 .. 4294967295";
    }
  }

  typedef BgpState {
    type enumeration {
      enum "idle" {
        value 0;
      }
      enum "connect" {
        value 1;
      }
      enum "active" {
        value 2;
      }
      enum "opensent" {
        value 3;
      }
      enum "openconfirm" {
        value 4;
      }
      enum "established" {
        value 5;
      }
      enum "clearing" {
        value 6;
      }
      enum "deleted" {
        value 7;
      }
    }
  }

  typedef HwSensorTypeEnum {
    type enumeration {
      enum "board" {
        value 0;
      }
      enum "cPU-Junction" {
        value 1;
      }
      enum "dRAM" {
        value 2;
      }
      enum "pIM" {
        value 3;
      }
    }
  }

  typedef TunnelEnum {
    type enumeration {
      enum "add" {
        value 1;
      }
      enum "delete" {
        value 2;
      }
    }
  }

  typedef PersonalityEnumOper {
    type enumeration {
      enum "unknown" {
        value 0;
      }
      enum "vedge" {
        value 1;
      }
      enum "vhub" {
        value 2;
      }
      enum "vsmart" {
        value 3;
      }
      enum "vbond" {
        value 4;
      }
      enum "vmanage" {
        value 5;
      }
      enum "ztp" {
        value 6;
      }
      enum "vcontainer" {
        value 7;
      }
    }
  }

  typedef Ipv4UcastAddrPrefix {
    type string;
  }

  typedef EncapEnum {
    type enumeration {
      enum "gre" {
        value 1;
      }
      enum "ipsec" {
        value 2;
      }
    }
  }

  typedef Enumeration {
    type enumeration {
      enum "up" {
        value 0;
      }
      enum "down" {
        value 1;
      }
    }
  }

  typedef ViptelaIpAddress {
    type string;
  }

  typedef OspfIfStateEnum {
    type enumeration {
      enum "if-depend-upon" {
        value 0;
      }
      enum "if-down" {
        value 1;
      }
      enum "if-loopback" {
        value 2;
      }
      enum "if-waiting" {
        value 3;
      }
      enum "if-point-to-point" {
        value 4;
      }
      enum "if-dr-other" {
        value 5;
      }
      enum "if-backup" {
        value 6;
      }
      enum "if-dr" {
        value 7;
      }
    }
  }

  typedef OspfStateEnum {
    type enumeration {
      enum "full" {
        value 0;
      }
      enum "deleted" {
        value 1;
      }
      enum "depend-upon" {
        value 2;
      }
      enum "down" {
        value 3;
      }
      enum "attempt" {
        value 4;
      }
      enum "init" {
        value 5;
      }
      enum "two-way" {
        value 6;
      }
      enum "exstart" {
        value 7;
      }
      enum "exchange" {
        value 8;
      }
      enum "loading" {
        value 9;
      }
    }
  }

  typedef StateEnum {
    type enumeration {
      enum "dOWN" {
        value 1;
      }
      enum "uP" {
        value 2;
      }
    }
  }

  typedef PeerState {
    type enumeration {
      enum "invalid" {
        value 0;
      }
      enum "init" {
        value 1;
      }
      enum "handshake" {
        value 2;
      }
      enum "up" {
        value 3;
      }
      enum "down" {
        value 4;
      }
    }
  }

  typedef VrrpGroupStateEnum {
    type enumeration {
      enum "init" {
        value 1;
      }
      enum "backup" {
        value 2;
      }
      enum "master" {
        value 3;
      }
    }
  }

  typedef viptelaVpnIpPrefixType {
    type hex-list;
  }

  typedef InstallationStatus {
    type enumeration {
      enum "download-start" {
        value 2;
      }
      enum "download-complete" {
        value 3;
      }
      enum "verification-complete" {
        value 4;
      }
      enum "upgrade-apply-complete" {
        value 5;
      }
      enum "sync-partition-start" {
        value 6;
      }
      enum "sync-partition-complete" {
        value 7;
      }
      enum "install-complete" {
        value 8;
      }
      enum "install-fail" {
        value 9;
      }
      enum "reboot" {
        value 10;
      }
    }
  }

  typedef OmpPolicyState {
    type enumeration {
      enum "add";
      enum "delete";
    }
  }

  typedef AdminStateEnum {
    type enumeration {
      enum "disable" {
        value 1;
      }
      enum "enable" {
        value 2;
      }
    }
  }

  typedef AddressFamilyEnum {
    type enumeration {
      enum "ipv4";
      enum "ipv6";
    }
  }

  typedef TrafficDirectionEnum {
    type enumeration {
      enum "downstream";
      enum "upstream";
    }
  }

  typedef BridgeId {
    type uint32 {
      range "1..63";
    }
  }

  typedef NumMacs {
    type uint32 {
      range "0..65535";
    }
  }

  typedef SimStateEnum {
    type enumeration {
      enum "Not Present" {
        value 0;
      }
      enum "Present" {
        value 1;
      }
      enum "Error" {
        value 2;
      }
    }
  }

  typedef DomainStateEnum {
    type enumeration {
      enum "Unknown" {
        value 0;
      }
      enum "Attached" {
        value 1;
      }
      enum "Detached" {
        value 2;
      }
    }
  }

  typedef RegStateEnum {
    type enumeration {
      enum "Not Registered" {
        value 0;
      }
      enum "Registered" {
        value 1;
      }
      enum "Searching" {
        value 2;
      }
      enum "Registration denied" {
        value 3;
      }
      enum "Unknown" {
        value 4;
      }
    }
  }

  typedef BearerEnum {
    type enumeration {
      enum "Unknown" {
        value 0;
      }
      enum "CDMA 1x" {
        value 1;
      }
      enum "CDMA 1xEV-DO Rev 0" {
        value 2;
      }
      enum "GPRS" {
        value 3;
      }
      enum "UMTS" {
        value 4;
      }
      enum "CDMA 1xEV-DO Rev A" {
        value 5;
      }
      enum "EDGE" {
        value 6;
      }
      enum "HSDPA AND WCDMA" {
        value 7;
      }
      enum "WCDMA AND HSUPA" {
        value 8;
      }
      enum "HSDPA AND HSUPA" {
        value 9;
      }
      enum "LTE" {
        value 10;
      }
      enum "CDMA EHRPD" {
        value 11;
      }
      enum "HSDPA+ and WCDMA" {
        value 12;
      }
      enum "HSDPA+ and HSUPA" {
        value 13;
      }
      enum "DC-HSDPA+ and WCDMA" {
        value 14;
      }
      enum "DC-HSDPA+ and HSUPA" {
        value 15;
      }
      enum "HSDPA+ and 64QAM" {
        value 16;
      }
      enum "HSDPA+, 64QAM and HSUPA" {
        value 17;
      }
      enum "TDSCDMA" {
        value 18;
      }
      enum "TDSCDMA and HSDPA" {
        value 19;
      }
    }
  }

  typedef CloudAppEnum {
    type enumeration {
      enum "salesforce" {
        value 1;
      }
      enum "office365" {
        value 2;
      }
      enum "amazonAws" {
        value 3;
      }
      enum "oracle" {
        value 4;
      }
      enum "boxNet" {
        value 6;
      }
      enum "dropbox" {
        value 7;
      }
      enum "intuit" {
        value 9;
      }
      enum "concur" {
        value 10;
      }
      enum "sugarCrm" {
        value 11;
      }
      enum "zohoCrm" {
        value 12;
      }
      enum "zendesk" {
        value 13;
      }
      enum "gotomeeting" {
        value 14;
      }
      enum "googleApps" {
        value 16;
      }
    }
  }

  typedef CloudExitEnum {
    type enumeration {
      enum "gateway" {
        value 1;
      }
      enum "office365" {
        value 2;
      }
      enum "amazonAws" {
        value 3;
      }
      enum "oracle" {
        value 4;
      }
    }
  }

  typedef QosStateEnum {
    description
      "QoS flow state";
    type enumeration {
      enum "Activated" {
        value 1;
      }
      enum "Modified" {
        value 2;
      }
      enum "Deleted" {
        value 3;
      }
      enum "Suspended" {
        value 4;
      }
      enum "Enabled" {
        value 5;
      }
      enum "Disabled" {
        value 6;
      }
    }
  }

  typedef hex-list {
    type string {
      pattern "(([0-9a-fA-F]){2}(:([0-9a-fA-F]){2})*)?";
    }
    status deprecated;
    description
      "DEPRECATED: Use yang:hex-string instead.  There are no plans to remove
       tailf:hex-list.
       
       A list of colon-separated hexa-decimal octets e.g. '4F:4C:41:71'.
       
       The statement tailf:value-length can be used to restrict the number
       of octets.  Note that using the 'length' restriction limits the
       number of characters in the lexical representation.";
  }
}
