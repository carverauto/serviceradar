module viptela-clear {
  namespace "http://viptela.com/clear";
  prefix viptela-clear;

  import ietf-inet-types {
    prefix inet;
  }
    prefix tailf;
  }
  import viptela-common {
    prefix viptela;
  }
  import viptela-system {
    prefix viptela-system;
  }

  organization "Viptela, Inc.";
  contact
    "Viptela, Inc.
     Email:support@viptela.com";
  description
    "This module defines the data model for clear operations";

  revision 2019-08-15 {
    description
      "Release version: 19.2";
  }
  revision 2018-11-01 {
    description
      "Release version: 18.4";
  }
  revision 2018-08-20 {
    description
      "Release version: 18.3.1";
  }
  revision 2018-06-25 {
    description
      "Release version: 18.3";
  }
  revision 2018-04-25 {
    description
      "Release version: 18.2";
  }
  revision 2018-03-15 {
    description
      "Release version: 18.1.1";
  }
  revision 2018-01-16 {
    description
      "Release version: 17.2.3";
  }
  revision 2017-11-01 {
    description
      "Release version: 17.2.1";
  }
  revision 2017-08-01 {
    description
      "Release version: 17.2";
  }
  revision 2017-05-25 {
    description
      "Release version: 17.1.1";
  }
  revision 2017-04-06 {
    description
      "Release version: 17.1";
  }
  revision 2017-02-15 {
    description
      "Release version: 16.3.2";
  }
  revision 2017-02-06 {
    description
      "Release version: 16.3.1";
  }
  revision 2016-11-16 {
    description
      "Release version: 16.3";
  }
  revision 2016-10-25 {
    description
      "Release version: 16.2.10";
  }
  revision 2016-10-24 {
    description
      "Release version: 16.2.4";
  }
  revision 2016-08-10 {
    description
      "Release version: 16.2.2";
  }
  revision 2016-08-01 {
    description
      "Release version: 16.2.1";
  }
  revision 2016-06-09 {
    description
      "Release version: 16.2";
  }
  revision 2016-04-22 {
    description
      "Release version: 16.1.1";
  }
  revision 2016-03-15 {
    description
      "Release version: 16.1";
  }
  revision 2016-01-30 {
    description
      "Release version: 15.4.3";
  }
  revision 2015-12-28 {
    description
      "Release version: 15.4.1";
  }
  revision 2015-12-01 {
    description
      "Release version: 15.4.0";
  }
  revision 2015-10-31 {
    description
      "Release version: 15.3.5";
  }
  revision 2015-09-27 {
    description
      "Release version: 15.3.3";
  }
  revision 2015-09-01 {
    description
      "Release version: 15.3.1";
  }
  revision 2015-07-01 {
    description
      "Release version: 15.3";
  }
  revision 2015-06-01 {
    description
      "Release version: 15.2.8";
  }
  revision 2015-05-01 {
    description
      "Release version: 15.2";
  }
  revision 2015-02-01 {
    description
      "Release version: 15.1";
  }
  revision 2014-12-01 {
    description
      "Release version: 14.3";
  }
  revision 2014-07-01 {
    description
      "Release version: 14.2";
  }
  revision 2013-02-12 {
    description
      "Initial revision";
  }

  container clear {
    description "Clear parameter";
    viptela:action "notification" {
      description "Clear notifications";
      input {
        leaf stream {
          description "Notification stream";
          mandatory true;
          type enumeration {
            enum "viptela";
          }
        }
      }
    }
    container bridge {
      description "Clear bridge related information";
      when "/viptela-system:system/viptela-system:personality = 'vedge'";
      viptela:action "statistics" {
        description "Clear all bridge statistics";
        input {
          leaf bridge-id {
            description "Allowed values: <0..63>";
            type viptela:bridge-id;
          }
        }
      }
      viptela:action "mac" {
        description "Flush all bridge mac tables";
        input {
          leaf bridge-id {
            description "Allowed values: <0..63>";
            type viptela:bridge-id;
          }
        }
      }
    }
    container ip {
      description "Clear IP information";
      when "/viptela-system:system/viptela-system:personality = 'vedge'";
      container mfib {
        description "Clear MFIB entries";
        when "/viptela-system:system/viptela-system:personality = 'vedge'";
        viptela:action "stats" {
          description "Clear MFIB statistics for all groups";
        }
        viptela:action "record" {
          description "Clear MFIB statistics for a specific group";
          input {
            leaf vpn {
              description "VPN ID";
              type viptela:vpn-id;
              mandatory true;
            }
            leaf group {
              description "IPv4 group address";
              type inet:ipv4-address;
              mandatory true;
            }
            leaf source {
              description "IPv4 source address";
              type inet:ipv4-address;
              mandatory true;
            }
            leaf upstream-iif {
              description "Incoming interface name";
              type viptela:named-type;
              mandatory false;
            }
            leaf upstream-tunnel {
              description "IPv4 address of tunnel remote system";
              type inet:ipv4-address;
              mandatory false;
            }
          }
        }
      }
      container nat {
        description "Clear NAT states and statistics";
        when "/viptela-system:system/viptela-system:personality = 'vedge'";
        viptela:action "filter" {
          description "Clear NAT filter entries";
          input {
            leaf nat-vpn-id {
              description "NAT VPN ID";
              type viptela:vpn-id;
            }
            leaf nat-ifname {
              description "Name of NAT interface";
              type viptela:named-type;
            }
            leaf private-vpn-id {
              description "Private VPN ID";
              type viptela:vpn-id;
            }
            leaf proto {
              description "Protocol";
              type enumeration {
                enum "tcp";
                enum "udp";
                enum "icmp";
              }
            }
            leaf private-source-address {
              description "Private source IP address";
              type inet:ipv4-address;
            }
            leaf private-dest-address {
              description "Private destination IP address";
              type inet:ipv4-address;
            }
            leaf private-source-port {
              description "Private source port";
              type inet:port-number {
                description "<0..65535>";
              }
            }
            leaf private-dest-port {
              description "Private destination port";
              type inet:port-number {
                description "<0..65535>";
              }
            }
          }
        }
        viptela:action "statistics" {
          description "Clear NAT statistics";
          input {
            leaf vpn-id {
              description "VPN ID";
              type viptela:vpn-id;
            }
            leaf interface {
              description "Name of NAT interface";
              type viptela:named-type;
            }
          }
        }
      }
    }
    container omp {
      description "Clear OMP";
      when
        "(/viptela-system:system/viptela-system:personality = 'vedge') or
         (/viptela-system:system/viptela-system:personality = 'vsmart')";
      viptela:action "peer" {
        description "Clear a specific OMP peer";
        input {
          leaf address {
            description "IPv4 address of peer";
            type inet:ipv4-address;
            mandatory true;
          }
          leaf soft {
            description "Re-evaluate peer information";
            type enumeration {
              enum "in";
              enum "out";
            }
          }
        }
      }
      viptela:action "routes" {
        description "Re-install routes into route table";
      }
      viptela:action "tlocs" {
        description "Re-install TLOCs into tunnel table";
      }
      viptela:action "all" {
        description "Restart OMP";
      }
    }
    container bfd {
      description "Clear BFD information";
      when "/viptela-system:system/viptela-system:personality = 'vedge'";
      viptela:action "transitions" {
        description "Clear all BFD transition counters";
      }
    }
    container reverse-proxy {
      description "Clear reverse-proxy";
      when "/viptela-system:system/viptela-system:personality = 'vedge'";
      viptela:action "context" {
        description "Clear installed reverse proxy certificate and resets control connections";
      }
    }
    container pppoe {
      description "Clear PPPoE";
      when "/viptela-system:system/viptela-system:personality = 'vedge'";
      viptela:action "statistics" {
        description "Clear PPPoE related statistics";
      }
    }
    container certificate {
      description "Clear certificate";
      when
        "(/viptela-system:system/viptela-system:personality = 'vsmart') or
         (/viptela-system:system/viptela-system:personality = 'vmanage') or
         (/viptela-system:system/viptela-system:vbond/viptela-system:local)";
      viptela:action "installed" {
        description "Clear the installed certificate";
        output {
          leaf status {
            type enumeration {
              enum "success";
              enum "failure";
            }
          }
        }
      }
    }
    container bgp {
      description "Clear BGP";
      when "/viptela-system:system/viptela-system:personality = 'vedge'";
      viptela:action "neighbor" {
        description "Clear a specific BGP neighbor";
        input {
          leaf address {
            description "IPv4 address of neighbor";
            type inet:ipv4-address;
            mandatory true;
          }
          leaf soft {
            description "Re-evaluate neighbor information";
            type enumeration {
              enum "in";
              enum "out";
            }
          }
          leaf vpn {
            description "VPN ID";
            type viptela:vpn-id;
            mandatory true;
          }
        }
      }
      viptela:action "all" {
        description "Reset all BGP neighbors";
        input {
          leaf vpn {
            description "VPN ID";
            type viptela:vpn-id;
            mandatory true;
          }
        }
      }
    }
    container ospf {
      description "Clear OSPF information";
      when "/viptela-system:system/viptela-system:personality = 'vedge'";
      viptela:action "all" {
        description "Reset all OSPF neighbors";
        input {
          leaf vpn {
            description "VPN ID";
            type viptela:vpn-id;
            mandatory true;
          }
        }
      }
      viptela:action "database" {
        description "Clear all received LSAs";
        input {
          leaf vpn {
            description "VPN ID";
            type viptela:vpn-id;
            mandatory true;
          }
        }
      }
    }
    container ipv6 {
      description "Clear IPv6 information";
      viptela:action "neighbor" {
        description "Clear IPv6 Neighbor information";
        input {
          leaf vpn {
            description "VPN ID";
            type viptela:vpn-id;
          }
          leaf interface {
            description "Interface name";
            type viptela:named-type {
              description "Interface name: 1..32 characters";
            }
          }
          leaf ipv6 {
            description "IPv6 address";
            type inet:ipv6-address;
          }
        }
      }
      container policy {
        description "Clear IPv6 policy counters";
        when "/viptela-system:system/viptela-system:personality = 'vedge'";
        viptela:action "access-list" {
          input {
            leaf name {
              description "Name of access list";
              type viptela:named-type-127;
            }
          }
        }
      }
      container dhcp {
        description "Clear DHCPv6 information";
        viptela:action "state" {
          description "Clear DHCPv6 state";
          input {
            leaf vpn {
              description "VPN ID";
              type viptela:vpn-id;
            }
            leaf interface {
              description "Interface name";
              type viptela:named-type {
                description "Interface name: 1..32 characters";
              }
            }
          }
        }
      }
    }
    viptela:action "arp" {
      description "Clear ARP information";
      input {
        leaf vpn {
          description "VPN ID";
          type viptela:vpn-id;
        }
        leaf interface {
          description "Interface name";
          type viptela:named-type {
            description "Interface name: 1..32 characters";
          }
        }
        leaf ip {
          description "IPv4 address";
          type inet:ipv4-address;
        }
      }
    }
    container policy {
      description "Clear policy counters";
      when "/viptela-system:system/viptela-system:personality = 'vedge'";
      viptela:action "access-list" {
        input {
          leaf name {
            description "Name of access list";
            type viptela:named-type-127;
          }
        }
      }
      viptela:action "data-policy" {
        input {
          leaf name {
            description "Name of data policy";
            type viptela:named-type-127;
          }
        }
      }
      viptela:action "app-route-policy" {
        input {
          leaf name {
            description "Name of application-aware routing policy";
            type viptela:named-type-127;
          }
        }
      }
      container zbfw {
        description "Clear inspect session data for a given zone-pair";
        when "/viptela-system:system/viptela-system:personality = 'vedge'";
        viptela:action "sessions" {
          input {
            leaf name {
              description "Name of the zone-pair";
              type viptela:named-type;
            }
          }
        }
        viptela:action "filter-statistics" {
          input {
            leaf name {
              description "Name of the zone-pair policy";
              type viptela:named-type-127;
            }
          }
        }
        viptela:action "global-statistics" {
          description "Clear zone pair statistics";
        }
      }
    }
    container policer {
      description "Clear Policer statistics";
      when "/viptela-system:system/viptela-system:personality = 'vedge'";
      viptela:action "statistics" {
        description "Clear policer statistics";
        input {
          leaf name {
            description "Name of policer";
            type viptela:named-type;
          }
        }
      }
    }
    container interface {
      description "Clear interface information";
      viptela:action "statistics" {
        description "Clear interface forwarding statistics";
        input {
          leaf vpn {
            description "VPN ID";
            type viptela:vpn-id;
          }
          leaf interface {
            description "Interface name";
            type viptela:named-type {
              description "Interface name (1..32 characters)";
            }
          }
          leaf queue {
            description "Queue number";
            type uint8 {
              description "<0..7>";
              range "0..7";
            }
          }
        }
      }
    }
    container system {
      description "Clear system information";
      when "/viptela-system:system/viptela-system:personality = 'vedge'";
      viptela:action "statistics" {
        description "Clear system forwarding statistics";
      }
    }
    container tunnel {
      description "Clear tunnel information";
      when "/viptela-system:system/viptela-system:personality = 'vedge'";
      viptela:action "statistics" {
        description "Clear tunnel forwarding statistics";
      }
      viptela:action "gre-keepalives" {
        description "Clear tunnel gre keepalives";
      }
    }
    container app-route {
      when "/viptela-system:system/viptela-system:personality = 'vedge'";
      description "Clear application-aware routing policy information";
      viptela:action "statistics";
    }
    container dhcp {
      description "Clear DHCP information";
      viptela:action "state" {
        description "Clear DHCP state";
        input {
          leaf vpn {
            description "VPN ID";
            type viptela:vpn-id;
          }
          leaf interface {
            description "Interface name";
            type viptela:named-type {
              description "Interface name: 1..32 characters";
            }
          }
        }
      }
      viptela:action "server-bindings" {
        description "Clear DHCP server bindings";
        input {
          leaf vpn {
            description "VPN ID";
            type viptela:vpn-id;
            mandatory true;
          }
          leaf interface {
            description "Interface name";
            type viptela:named-type {
              description "Interface name: 1..32 characters";
            }
            mandatory true;
          }
          leaf client-mac {
            description "DHCP client's MAC address";
            type string;
          }
        }
      }
      viptela:action "server-declined-addresses" {
        description "Clear DHCP server declined addresses";
        input {
          leaf vpn {
            description "VPN ID";
            type viptela:vpn-id;
            mandatory true;
          }
          leaf interface {
            description "Interface name";
            type viptela:named-type {
              description "Interface name: 1..32 characters";
            }
            mandatory true;
          }
          leaf address {
            description "IPv4 address";
            type inet:ipv4-address;
          }
        }
      }
      viptela:action "server-packet-stats" {
        description "Clear DHCP server bindings";
        input {
          leaf vpn {
            description "VPN ID";
            type viptela:vpn-id;
            mandatory true;
          }
          leaf interface {
            description "Interface name";
            type viptela:named-type {
              description "Interface name: 1..32 characters";
            }
            mandatory true;
          }
        }
      }
      viptela:action "autoip" {
        description "Clear DHCP autoip helper state";
      }
    }
    container cloudexpress {
      description "Clear cloudexpress information";
      when "/viptela-system:system/viptela-system:personality = 'vedge'";
      viptela:action "computations" {
        description "Clear cloudexpress computations for applications";
        input {
          leaf application {
            description "applications";
            type viptela:cloudexpress-app-type;
          }
        }
      }
    }
    container app {
      description "Clear app related information";
      when "/viptela-system:system/viptela-system:personality = 'vedge'";
      container cflowd {
        description "Clear cflowd flow information";
        viptela:action "flows" {
          description "Clear per-VPN cflowd flows";
          input {
            leaf vpn {
              description "VPN ID";
              type viptela:vpn-id;
              mandatory true;
            }
            leaf dest-ip {
              description "Destination IP prefix";
              type inet:ipv4-prefix;
            }
            leaf src-ip {
              description "Source IP prefix";
              type inet:ipv4-prefix;
            }
            leaf ip-proto {
              description "IP protocol";
              type uint8 {
                description "<0..255>";
              }
            }
            leaf src-port {
              description "Source transport port ";
              type inet:port-number {
                description "<1..65335>";
                range "1..65335";
              }
            }
            leaf dest-port {
              description "Destination transport port ";
              type inet:port-number {
                description "<1..65335>";
                range "1..65335";
              }
            }
          }
        }
        viptela:action "flow-all" {
          description "Clear all cflowd flows in the system";
        }
        viptela:action "statistics" {
          description "Clear all cflowd statistics";
        }
      }
      container dpi {
        description "Clear DPI flow information";
        viptela:action "flows" {
          description "Clear per VPN DPI flows";
          input {
            leaf vpn {
              description "VPN ID";
              type viptela:vpn-id;
              mandatory true;
            }
            leaf destination-prefix {
              description "Destination IP prefix";
              type inet:ipv4-prefix;
            }
            leaf source-prefix {
              description "Source IP prefix";
              type inet:ipv4-prefix;
            }
            leaf ip-protocol {
              description "IP protocol";
              type uint8 {
                description "<0..255>";
              }
            }
            leaf source-port {
              description "Source transport port ";
              type inet:port-number;
            }
            leaf destination-port {
              description "Destination transport port ";
              type inet:port-number;
            }
          }
        }
        viptela:action "apps" {
          description "Clear per VPN DPI apps";
          input {
            leaf vpn {
              description "VPN ID";
              type viptela:vpn-id;
              mandatory true;
            }
            leaf application {
              description "Application ";
              type viptela:named-type {
                description "Application name: 1..32 characters";
              }
            }
          }
        }
        viptela:action "all" {
          description "Clear all dpi flows in the system";
        }
        viptela:action "protocol-hits" {
          description "Clear all protocol hits on the system";
        }
        container summary {
          description "Clear DPI summary";
          viptela:action "statistics" {
            description "Clear DPI statistics";
          }
        }
        container cache {
          description "Clear DPI cache";
          viptela:action "table" {
            description "Clear DPI cache table";
          }
        }
      }
      container log {
        description "Clear log flow information";
        viptela:action "flows" {
          description "Clear per-VPN log flows";
          input {
            leaf vpn {
              description "VPN ID";
              type viptela:vpn-id;
              mandatory true;
            }
            leaf dest-ip {
              description "Destination IP prefix";
              type inet:ip-prefix;
            }
            leaf src-ip {
              description "Source IP prefix";
              type inet:ip-prefix;
            }
            leaf ip-proto {
              description "IP protocol";
              type uint8 {
                description "<0..255>";
              }
            }
            leaf src-port {
              description "Source transport port ";
              type inet:port-number {
                description "<1..65335>";
                range "1..65335";
              }
            }
            leaf dest-port {
              description "Destination transport port ";
              type inet:port-number {
                description "<1..65335>";
                range "1..65335";
              }
            }
          }
        }
        viptela:action "flow-all" {
          description "Clear all logged flows in the system";
        }
      }
      container tcp-opt {
        description "Clear tcp-opt related information";
        viptela:action "expired-flows" {
          description "Clear tcp-opt expired flow table";
        }
      }
    }
    container pim {
      description "Clear PIM information";
      when "/viptela-system:system/viptela-system:personality = 'vedge'";
      viptela:action "neighbor" {
        description "Clear a specific PIM neighbor";
        input {
          leaf address {
            description "IPv4 address of neighbor";
            type inet:ipv4-address;
          }
          leaf vpn {
            description "VPN ID";
            type viptela:service-vpn-id;
            mandatory true;
          }
        }
      }
      viptela:action "interface" {
        description "Clear a specific PIM interface";
        input {
          leaf interface {
            description "Interface name";
            type viptela:named-type {
              description "Interface name: 1..32 characters";
            }
          }
          leaf vpn {
            description "VPN ID";
            type viptela:service-vpn-id;
            mandatory true;
          }
        }
      }
      viptela:action "protocol" {
        description "Clear all PIM state";
        input {
          leaf vpn {
            description "VPN ID";
            type viptela:service-vpn-id;
            mandatory true;
          }
        }
      }
      viptela:action "statistics" {
        description "Clear PIM statistics";
        input {
          leaf vpn {
            description "VPN ID";
            type viptela:service-vpn-id;
          }
        }
      }
      viptela:action "rp-mapping" {
        description "Clear PIM RP mapping";
        input {
          leaf vpn {
            description "VPN ID";
            type viptela:service-vpn-id;
          }
        }
      }
    }
    container igmp {
      description "Clear IGMP information";
      when "/viptela-system:system/viptela-system:personality = 'vedge'";
      viptela:action "protocol" {
        description "Clear all IGMP state";
        input {
          leaf vpn {
            description "VPN ID";
            type viptela:service-vpn-id;
            mandatory true;
          }
        }
      }
      viptela:action "interface" {
        description "Clear an IGMP interface";
        input {
          leaf interface {
            description "Interface name";
            type viptela:named-type {
              description "Interface name: 1..32 characters";
            }
            mandatory true;
          }
          leaf vpn {
            description "VPN ID";
            type viptela:service-vpn-id;
            mandatory true;
          }
        }
      }
      viptela:action "statistics" {
        description "Clear IGMP statistics";
        input {
          leaf vpn {
            description "VPN ID";
            type viptela:service-vpn-id;
          }
        }
      }
    }
    container cellular {
      description "Clear cellular information";
      when
        "(/viptela-system:system/viptela-system:personality = 'vedge') and 
         (/viptela-system:system/viptela-system:device-model = 'vedge-1000' or
         /viptela-system:system/viptela-system:device-model = 'vedge-100-M' or 
         /viptela-system:system/viptela-system:device-model = 'vedge-100-WM' or 
         /viptela-system:system/viptela-system:device-model = 'vedge-100-M2' or
         /viptela-system:system/viptela-system:device-model = 'vedge-ISR1100-4G' or
         /viptela-system:system/viptela-system:device-model = 'vedge-ISR1100-4GLTE' or
         /viptela-system:system/viptela-system:device-model = 'vedge-ISR1100-6G')";
      viptela:action "statistics" {
        description "Clear cellular session statistics";
        input {
          leaf interface {
            description "Interface name";
            type viptela:named-type {
              description "Interface name: 1..32 characters";
            }
            default "cellular0";
          }
        }
      }
      viptela:action "errors" {
        description "Clear cellular errors";
        input {
          leaf interface {
            description "Interface name";
            type viptela:named-type {
              description "Interface name: 1..32 characters";
            }
            default "cellular0";
          }
        }
      }
    }
    container wlan {
      description "Clear WLAN information";
      when
        "(/viptela-system:system/viptela-system:personality = 'vedge') and 
         (/viptela-system:system/viptela-system:device-model = 'vedge-100-WM' or 
         /viptela-system:system/viptela-system:device-model = 'vedge-100-W2')";
      viptela:action "client" {
        description "Disassociate WLAN client";
        input {
          leaf mac {
            description "Client MAC address in aa:bb:cc:dd:ee:ff format";
            type string {
              length "1..18";
              description "<1..18> characters";
            }
          }
        }
      }
      viptela:action "radius-stats" {
        description "Clear WLAN RADIUS statistics";
        input {
          leaf vap-ifname {
            type viptela:vap-iftype;
            mandatory true;
          }
        }
      }
    }
    container control {
      description "Clear control connections";
      when
        "(/viptela-system:system/viptela-system:personality = 'vsmart') or
         (/viptela-system:system/viptela-system:personality = 'vmanage') or
         (/viptela-system:system/viptela-system:personality = 'vedge')";
      viptela:action "connections" {
        description "Clear all control connections";
      }
      viptela:action "reverse-proxy-connections" {
        description "Clear all reverse proxy control connections";
      }
      viptela:action "connections-history" {
        description "Clear control connections history";
      }
      viptela:action "port-index" {
        description "Clear the port-hopping bucket index";
      }
    }
    container orchestrator {
      description "Clear orchestrator connections";
      when
        "(/viptela-system:system/viptela-system:vbond/viptela-system:local) and
         (/viptela-system:system/viptela-system:personality = 'vedge')";
      viptela:action "connections" {
        description "Clear all control connections";
      }
      viptela:action "connections-history" {
        description "Clear control connections history";
      }
    }
    container pseudo-commit {
      description "Clear the pseudo commit lock and stop the timer";
      viptela:action "lock" {
        description "Clear the pseudo commit lock and stop the timer";
      }
    }
    container dns {
      description "Clear the dns cache";
      viptela:action "cache" {
        description "Clear the cached dns entries";
      }
    }
    container cloudinit {
      description "Clear cloudinit data";
      viptela:action "data" {
        description "Clear all vEdge Cloud initialization data";
      }
    }
    container ztp {
      description "Clear ZTP information";
      when
        "(/viptela-system:system/viptela-system:vbond/viptela-system:local) and
         (/viptela-system:system/viptela-system:vbond/viptela-system:ztp-server)";
      viptela:action "entries" {
        description "Clear all entries from the ZTP database";
      }
    }
  }
}
