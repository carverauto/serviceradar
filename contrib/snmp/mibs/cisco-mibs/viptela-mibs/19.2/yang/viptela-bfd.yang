module viptela-bfd {
  namespace "http://viptela.com/bfd";
  prefix viptela-bfd;

    prefix tailf;
  }
  import ietf-inet-types {
    prefix inet;
  }
  import ietf-yang-types {
    prefix yang;
  }
  import viptela-common {
    prefix viptela;
  }
  import viptela-system {
    prefix viptela-system;
  }

  organization "Viptela, Inc.";
  contact
    "Viptela, Inc.
     Email:support@viptela.com";
  description
    "This module defines data model for BFD";

  revision 2019-08-15 {
    description
      "Release version: 19.2";
  }
  revision 2018-11-01 {
    description
      "Release version: 18.4";
  }
  revision 2018-08-20 {
    description
      "Release version: 18.3.1";
  }
  revision 2018-06-25 {
    description
      "Release version: 18.3";
  }
  revision 2018-04-25 {
    description
      "Release version: 18.2";
  }
  revision 2018-03-15 {
    description
      "Release version: 18.1.1";
  }
  revision 2018-01-16 {
    description
      "Release version: 17.2.3";
  }
  revision 2017-11-01 {
    description
      "Release version: 17.2.1";
  }
  revision 2017-08-01 {
    description
      "Release version: 17.2";
  }
  revision 2017-05-25 {
    description
      "Release version: 17.1.1";
  }
  revision 2017-04-06 {
    description
      "Release version: 17.1";
  }
  revision 2017-02-15 {
    description
      "Release version: 16.3.2";
  }
  revision 2017-02-06 {
    description
      "Release version: 16.3.1";
  }
  revision 2016-11-16 {
    description
      "Release version: 16.3";
  }
  revision 2016-10-25 {
    description
      "Release version: 16.2.10";
  }
  revision 2016-10-24 {
    description
      "Release version: 16.2.4";
  }
  revision 2016-08-10 {
    description
      "Release version: 16.2.2";
  }
  revision 2016-08-01 {
    description
      "Release version: 16.2.1";
  }
  revision 2016-06-09 {
    description
      "Release version: 16.2";
  }
  revision 2016-04-22 {
    description
      "Release version: 16.1.1";
  }
  revision 2016-03-15 {
    description
      "Release version: 16.1";
  }
  revision 2016-01-30 {
    description
      "Release version: 15.4.3";
  }
  revision 2015-12-28 {
    description
      "Release version: 15.4.1";
  }
  revision 2015-12-01 {
    description
      "Release version: 15.4.0";
  }
  revision 2015-10-31 {
    description
      "Release version: 15.3.5";
  }
  revision 2015-09-27 {
    description
      "Release version: 15.3.3";
  }
  revision 2015-09-01 {
    description
      "Release version: 15.3.1";
  }
  revision 2015-07-01 {
    description
      "Release version: 15.3";
  }
  revision 2015-06-01 {
    description
      "Release version: 15.2.8";
  }
  revision 2015-05-01 {
    description
      "Release version: 15.2";
  }
  revision 2015-02-01 {
    description
      "Release version: 15.1";
  }
  revision 2014-12-01 {
    description
      "Release version: 14.3";
  }
  revision 2014-07-01 {
    description
      "Release version: 14.2";
  }
  revision 2013-02-12 {
    description
      "Initial revision";
  }

  typedef bfdmgr-state-enum {
    type enumeration {
      enum "admin-down" {
        value 0;
      }
      enum "down";
      enum "init";
      enum "up";
      enum "invalid";
    }
  }

  typedef bfd-flap-reason-enum {
    type enumeration {
      enum "bfd-deleted" {
        value 1;
      }
      enum "remote-down";
      enum "timeout";
      enum "na";
      enum "not-known";
    }
  }

  typedef bool-enum {
    type enumeration {
      enum "false" {
        value 0;
      }
      enum "true" {
        value 1;
      }
    }
  }

  container bfd {
    description "BFD information";
    when "/viptela-system:system/viptela-system:personality = 'vedge'";
    list sessions-list {
      description "BFD sessions";
      config false;
      key "src-ip dst-ip proto src-port dst-port";
      leaf src-ip {
        description "Local TLOC IP address";
        type inet:ip-address;
      }
      leaf dst-ip {
        description "Remote TLOC IP address";
        type inet:ip-address;
      }
      leaf proto {
        type viptela:encap-enum;
      }
      leaf src-port {
        description "Local port number";
        type uint16;
      }
      leaf dst-port {
        description "Remote port number";
        type uint16;
      }
      leaf system-ip {
        description "System IP address";
        type inet:ip-address;
      }
      leaf site-id {
        description "Site ID";
        type uint32;
      }
      leaf local-color {
        description "Color";
        type viptela:color-enum;
      }
      leaf color {
        description "Color";
        type viptela:color-enum;
      }
      leaf state {
        description "State";
        type bfdmgr-state-enum;
      }
      leaf detect-multiplier {
        type uint8;
      }
      leaf tx-interval {
        type uint32;
      }
      leaf uptime {
        type string;
      }
      leaf transitions {
        type int32;
      }
    }
    list history-list {
      description "BFD session history";
      config false;
      key "src-ip dst-ip proto src-port dst-port index";
      leaf src-ip {
        description "Local TLOC IP address";
        type inet:ip-address;
      }
      leaf dst-ip {
        description "Remote TLOC IP address";
        type inet:ip-address;
      }
      leaf proto {
        type viptela:encap-enum;
      }
      leaf src-port {
        description "Local port number";
        type uint16;
      }
      leaf dst-port {
        description "Remote port number";
        type uint16;
      }
      leaf index {
        description "History index";
        type uint32;
      }
      leaf system-ip {
        description "System IP address";
        type inet:ip-address;
      }
      leaf site-id {
        description "Site ID";
        type uint32;
      }
      leaf color {
        description "Color";
        type viptela:color-enum;
      }
      leaf state {
        description "State";
        type bfdmgr-state-enum;
      }
      leaf time {
        type string;
      }
      leaf rx-pkts {
        type yang:counter64;
      }
      leaf tx-pkts {
        type yang:counter64;
      }
      leaf del {
        type uint8;
      }
    }
    list color {
      key "color";
      leaf color {
        description "Set BFD color parameter";
        type viptela:color-enum;
      }
      leaf hello-interval {
        description "Hello interval, in milliseconds";
        type uint32 {
          description "<100..300000> milliseconds";
          range "100..300000";
        }
        default "1000";
      }
      leaf pmtu-discovery {
        description "Automatically discover path MTU";
        type boolean;
        default "true";
      }
      leaf multiplier {
        description "Maximum number of attempts";
        type uint8 {
          description "<1..60>";
          range "1..60";
        }
        default "7";
      }
    }
    container probe-path {
      description "Probe-Path information";
      when
        "((/viptela-system:system/viptela-system:personality != 'vbond' and 
         /viptela-system:system/viptela-system:personality != 'vsmart' and
         /viptela-system:system/viptela-system:device-model != 'vedge-100-M' and
         /viptela-system:system/viptela-system:device-model != 'vedge-1000' and
         /viptela-system:system/viptela-system:device-model != 'vedge-100-WM' and
         /viptela-system:system/viptela-system:device-model != 'vedge-100-M2' and
         /viptela-system:system/viptela-system:device-model != 'vedge-1000' and
         /viptela-system:system/viptela-system:device-model != 'vedge-2000' and
         /viptela-system:system/viptela-system:device-model != 'vedge-100' and
         /viptela-system:system/viptela-system:device-model != 'vedge-100-W2' and
         /viptela-system:system/viptela-system:device-model != 'vedge-100-B' and
         /viptela-system:system/viptela-system:device-model != 'vedge-cloud' and
         /viptela-system:system/viptela-system:device-model != 'vedge-sim'
         ))";
      choice all-or-specific-tlocs {
        case all {
          leaf all-tlocs {
            description "Start probes all TLOCs";
            type boolean;
            default "false";
          }
        }
        case tloc-list {
          leaf-list color-list {
            description "Local color list";
            type viptela:color-enum;
          }
        }
      }
      choice event-or-periodic {
        case event {
          leaf trigger-on-change {
            description "Start event / On-Change based probe-paths";
            type boolean;
            default "false";
          }
        }
        case periodic {
          leaf trigger-periodic {
            description "Period (secs) + on-change for the probe path";
            type uint32 {
              description "<1..4294967295> seconds";
              range "1..4294967295";
            }
            default "3600";
          }
        }
      }
    }
    container app-route {
      leaf multiplier {
        description "Number of polling intervals used to determine tunnel SLA class";
        type uint8 {
          description "<1..6>";
          range "1..6";
        }
        default "6";
      }
      leaf poll-interval {
        description "Polling interval, in milliseconds";
        type uint32 {
          description "<1..4294967295> milliseconds";
          range "1..4294967295";
        }
        default "600000";
      }
      leaf keepalive-interval {
        description "Session keepalive interval, in milliseconds";
        type uint32 {
          description "<1..4294967295> milliseconds";
          range "1..4294967295";
        }
        default "86400000";
      }
      leaf flush-interval {
        description "Time after which statistics are flushed to disk, in hours";
        type uint32 {
          description "<1..24> hours";
          range "1..24";
        }
        default "24";
      }
    }
    container summary {
      description "BFD summary";
      config false;
      leaf bfd-sessions-total {
        description "Current number of BFD sessions";
        type uint32;
      }
      leaf bfd-sessions-up {
        description "Number of BFD sessions currently in Up state";
        type uint32;
      }
      leaf bfd-sessions-max {
        description "Maximum number of BFD sessions seen since bootup";
        type uint32;
      }
      leaf bfd-sessions-flap {
        description "Number of BFD session flaps (transitions out of Up state)";
        type uint32;
      }
      leaf poll-interval {
        description "App route poll interval";
        type uint32;
      }
    }
    list tloc-summary-list {
      description "Per-TLOC BFD summary";
      config false;
      key "if-name encap";
      leaf if-name {
        description "Interface name";
        type viptela:named-type;
      }
      leaf encap {
        description "Encapsulation index";
        type viptela:encap-enum;
      }
      leaf sessions-total {
        description "Current number of BFD sessions";
        type uint32;
      }
      leaf sessions-up {
        description "Number of BFD sessions currently in Up state";
        type uint32;
      }
      leaf sessions-flap {
        description "Number of BFD session flaps (transitions out of Up state)";
        type uint32;
      }
    }
  }
  notification bfd-state-change {
    uses viptela:common-notification-header;
    leaf src-ip {
      type inet:ip-address;
    }
    leaf dst-ip {
      type inet:ip-address;
    }
    leaf proto {
      type viptela:encap-enum;
    }
    leaf src-port {
      type uint16;
    }
    leaf dst-port {
      type uint16;
    }
    leaf local-system-ip {
      type inet:ip-address;
    }
    leaf local-color {
      type string;
    }
    leaf remote-system-ip {
      type inet:ip-address;
    }
    leaf remote-color {
      type string;
    }
    leaf new-state {
      type viptela:oper-state;
    }
    leaf deleted {
      type bool-enum;
    }
    leaf flap-reason {
      type bfd-flap-reason-enum;
    }
  }
}
