module viptela-vpn-ann {
  namespace "http://viptela.com/vpn-ann";
  prefix viptela-vpn-ann;

  import viptela-vpn {
    prefix vpn;
  }

  organization "Viptela, Inc.";
  contact
    "Viptela, Inc.
     Email:support@viptela.com";
  description
    "Defines annotations for vpn module";
}
