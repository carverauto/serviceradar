module viptela-bridge {
  namespace "http://viptela.com/bridge";
  prefix viptela-bridge;

    prefix tailf;
  }
  import viptela-common {
    prefix viptela;
  }
  import viptela-system {
    prefix viptela-system;
  }
  import ietf-yang-types {
    prefix yang;
  }

  organization "Viptela, Inc.";
  contact
    "Viptela, Inc.
     Email:support@viptela.com";
  description
    "This module defines the data model for Bridge management";

  revision 2019-08-15 {
    description
      "Release version: 19.2";
  }
  revision 2018-11-01 {
    description
      "Release version: 18.4";
  }
  revision 2018-08-20 {
    description
      "Release version: 18.3.1";
  }
  revision 2018-06-25 {
    description
      "Release version: 18.3";
  }
  revision 2018-04-25 {
    description
      "Release version: 18.2";
  }
  revision 2018-03-15 {
    description
      "Release version: 18.1.1";
  }
  revision 2018-01-16 {
    description
      "Release version: 17.2.3";
  }
  revision 2017-11-01 {
    description
      "Release version: 17.2.1";
  }
  revision 2017-08-01 {
    description
      "Release version: 17.2";
  }
  revision 2017-05-25 {
    description
      "Release version: 17.1.1";
  }
  revision 2017-04-06 {
    description
      "Release version: 17.1";
  }
  revision 2017-02-15 {
    description
      "Release version: 16.3.2";
  }
  revision 2017-02-06 {
    description
      "Release version: 16.3.1";
  }
  revision 2016-11-16 {
    description
      "Release version: 16.3";
  }
  revision 2016-10-25 {
    description
      "Release version: 16.2.10";
  }
  revision 2016-10-24 {
    description
      "Release version: 16.2.4";
  }
  revision 2016-08-10 {
    description
      "Release version: 16.2.2";
  }
  revision 2016-08-01 {
    description
      "Release version: 16.2.1";
  }
  revision 2016-06-09 {
    description
      "Release version: 16.2";
  }
  revision 2016-04-22 {
    description
      "Release version: 16.1.1";
  }
  revision 2016-03-15 {
    description
      "Release version: 16.1";
  }
  revision 2016-01-30 {
    description
      "Release version: 15.4.3";
  }
  revision 2015-12-28 {
    description
      "Release version: 15.4.1";
  }
  revision 2015-12-01 {
    description
      "Release version: 15.4.0";
  }
  revision 2015-10-31 {
    description
      "Release version: 15.3.5";
  }
  revision 2015-09-27 {
    description
      "Release version: 15.3.3";
  }
  revision 2015-09-01 {
    description
      "Release version: 15.3.1";
  }
  revision 2015-07-01 {
    description
      "Release version: 15.3";
  }
  revision 2015-06-01 {
    description
      "Release version: 15.2.8";
  }
  revision 2015-05-01 {
    description
      "Release version: 15.2";
  }
  revision 2015-02-01 {
    description
      "Release version: 15.1";
  }
  revision 2014-12-01 {
    description
      "Release version: 14.3";
  }
  revision 2014-07-01 {
    description
      "Release version: 14.2";
  }
  revision 2013-02-12 {
    description
      "Initial revision";
  }

  container bridge {
    description "Bridge instance information";
    when "/viptela-system:system/viptela-system:personality = 'vedge'";
    must "(count(bridge-instance) <= 64)" {
      error-message "Maximum limit for configured Bridges is 64";
    }
    list bridge-instance {
      description "List of Bridging instances";
      key "bridge-id";
      leaf bridge-id {
        description "Allowed values: <1..63>";
        type viptela:bridge-id;
      }
      leaf name {
        description "Bridge description";
        type viptela:named-type;
      }
      leaf vlan {
        description "VLAN ID associated with the bridge";
        type uint16 {
          description "<1..4095>";
          range "1..4095";
        }
      }
      leaf max-macs {
        description "Maximum number of MACs the bridge can learn";
        type uint32 {
          description "<0..4096>";
          range "0..4096";
        }
        default "1024";
      }
      leaf num-macs {
        description "Number of MACs the bridge has learnt";
        type uint32;
      }
      leaf age-time {
        description "MAC table aging time in seconds";
        type uint32 {
          description "<10 - 4096>";
          range "10..4096";
        }
        default "300";
      }
      list interface {
        description "Interface to bind to the bridge";
        key "if-name";
        leaf if-name {
          description "Interface name: ge0/<0-..>  when present";
          type string {
            length "1..32";
            description "Interface name: ge0/<0-..>  when present";
          }
        }
        leaf description {
          description "Description";
          type viptela:named-type;
        }
        leaf native-vlan {
          description "Support native VLAN handling";
          type boolean;
          default "false";
        }
        leaf shutdown {
          description "Administrative state";
          type boolean;
          default "true";
        }
        list static-mac-address {
          description "Static MAC Address";
          key "macaddr";
          leaf macaddr {
            description "<MAC address>";
            type viptela:mac-address;
          }
        }
        leaf mtu {
          description "IP MTU, in bytes";
          type uint16 {
            description "Interface MTU <576..2000, PPP: 576..1492>";
            range "576..2000";
          }
          default "1500";
        }
      }
    }
    list table {
      description "Display bridge table";
      config false;
      key "bridge-id";
      leaf bridge-id {
        description "BRIDGE ID";
        type viptela:bridge-id;
      }
      leaf name {
        type string {
          length "0..32";
        }
      }
      leaf vlan {
        type uint16;
      }
      leaf routing-interface {
        type viptela:named-type;
      }
      leaf max-macs {
        type uint32;
      }
      leaf num-macs {
        description "Number of MACs the bridge has learnt";
        type uint32;
      }
      leaf age-time {
        type uint32;
      }
      leaf rx-packets {
        type yang:counter64;
      }
      leaf rx-octets {
        type yang:counter64;
      }
      leaf tx-packets {
        type yang:counter64;
      }
      leaf tx-octets {
        type yang:counter64;
      }
      leaf flood-packets {
        type yang:counter64;
      }
      leaf flood-octets {
        type yang:counter64;
      }
      leaf rx-routed-packets {
        type yang:counter64;
      }
      leaf tx-routed-packets {
        type yang:counter64;
      }
      leaf learn {
        type uint32;
      }
      leaf age {
        type uint32;
      }
      leaf move {
        type uint32;
      }
    }
    list interface {
      description "Display bridge interface information";
      config false;
      key "bridge-id if-name";
      leaf bridge-id {
        description "BRIDGE ID";
        type viptela:bridge-id;
      }
      leaf if-name {
        description "Interface Name";
        type viptela:named-type;
      }
      leaf vlan {
        description "VLAN ID associated with the bridge";
        type uint16;
      }
      leaf native-vlan {
        description "Is native vlan enabled";
        type string;
      }
      leaf admin-status {
        description "Interface Administrative Status";
        type viptela:if-admin-status-type;
      }
      leaf oper-status {
        description "Interface Operational Status";
        type viptela:if-oper-status-type;
      }
      leaf encap-type {
        description "Encapsulation type";
        type viptela:encapsulation;
      }
      leaf ifindex {
        description "Interface index";
        type uint32;
      }
      leaf mtu {
        description "MTU";
        type uint32;
      }
      leaf rx-packets {
        description "Number of packets received";
        type yang:counter64;
      }
      leaf rx-octets {
        description "Number of octets received";
        type yang:counter64;
      }
      leaf rx-errors {
        type yang:counter64;
      }
      leaf rx-drops {
        type yang:counter64;
      }
      leaf tx-packets {
        description "Number of packets transmitted";
        type yang:counter64;
      }
      leaf tx-octets {
        description "Number of octets transmitted";
        type yang:counter64;
      }
      leaf tx-errors {
        type yang:counter64;
      }
      leaf tx-drops {
        type yang:counter64;
      }
      leaf rx-pps {
        type yang:counter64;
      }
      leaf rx-kbps {
        type yang:counter64;
      }
      leaf tx-pps {
        type yang:counter64;
      }
      leaf tx-kbps {
        type yang:counter64;
      }
      leaf rx-arp-requests {
        type yang:counter64;
      }
      leaf tx-arp-replies {
        type yang:counter64;
      }
      leaf tx-arp-requests {
        type yang:counter64;
      }
      leaf rx-arp-replies {
        type yang:counter64;
      }
      leaf arp-add-fails {
        type yang:counter64;
      }
      leaf rx-arp-reply-drops {
        type yang:counter64;
      }
      leaf rx-arp-rate-limit-drops {
        type yang:counter64;
      }
      leaf tx-arp-rate-limit-drops {
        type yang:counter64;
      }
      leaf rx-arp-non-local-drops {
        type yang:counter64;
      }
      leaf tx-arp-request-fail {
        type yang:counter64;
      }
      leaf tx-no-arp-drops {
        type yang:counter64;
      }
      leaf rx-ip-ttl-expired {
        type yang:counter64;
      }
      leaf rx-ip-errors {
        type yang:counter64;
      }
      leaf interface-disabled {
        type yang:counter64;
      }
      leaf rx-policer-drops {
        type yang:counter64;
      }
      leaf rx-non-ip-drops {
        type yang:counter64;
      }
      leaf filter-drops {
        type yang:counter64;
      }
      leaf mirror-drops {
        type yang:counter64;
      }
      leaf cpu-policer-drops {
        type yang:counter64;
      }
      leaf tx-icmp-policer-drops {
        type yang:counter64;
      }
      leaf tx-icmp-mirrored-drops {
        type yang:counter64;
      }
      leaf split-horizon-drops {
        type yang:counter64;
      }
      leaf route-lookup-fail {
        type yang:counter64;
      }
      leaf bad-label {
        type yang:counter64;
      }
      leaf tx-interface-disabled {
        type yang:counter64;
      }
      leaf rx-multicast-pkts {
        type yang:counter64;
      }
      leaf rx-broadcast-pkts {
        type yang:counter64;
      }
      leaf tx-multicast-pkts {
        type yang:counter64;
      }
      leaf tx-broadcast-pkts {
        type yang:counter64;
      }
      leaf rx-pause-pkts {
        type yang:counter64;
      }
      leaf rx-dmac-filter-drops {
        type yang:counter64;
      }
      leaf rx-wred-drops {
        type yang:counter64;
      }
      leaf rx-interface-not-found {
        type yang:counter64;
      }
      leaf rx-inb-errors {
        type yang:counter64;
      }
      leaf rx-oversize-errors {
        type yang:counter64;
      }
      leaf rx-fcs-align-errors {
        type yang:counter64;
      }
      leaf rx-undersize-errors {
        type yang:counter64;
      }
      leaf tx-underflow-pkts {
        type yang:counter64;
      }
      leaf tx-collision-drops {
        type yang:counter64;
      }
      leaf tx-pause-pkts {
        type yang:counter64;
      }
      leaf tx-fragments-needed {
        type yang:counter64;
      }
      leaf tx-fragments {
        type yang:counter64;
      }
      leaf tx-fragment-drops {
        type yang:counter64;
      }
      leaf tx-tail-red-drops {
        type yang:counter64;
      }
      leaf llq-drops {
        type yang:counter64;
      }
      leaf rx-pkt-size-64 {
        type yang:counter64;
      }
      leaf rx-pkt-size-lt-64 {
        type yang:counter64;
      }
      leaf rx-pkt-size-65-127 {
        type yang:counter64;
      }
      leaf rx-pkt-size-128-255 {
        type yang:counter64;
      }
      leaf rx-pkt-size-256-511 {
        type yang:counter64;
      }
      leaf rx-pkt-size-512-1023 {
        type yang:counter64;
      }
      leaf rx-pkt-size-1024-1518 {
        type yang:counter64;
      }
      leaf rx-pkt-size-gt-1518 {
        type yang:counter64;
      }
      leaf tx-pkt-size-64 {
        type yang:counter64;
      }
      leaf tx-pkt-size-lt-64 {
        type yang:counter64;
      }
      leaf tx-pkt-size-65-127 {
        type yang:counter64;
      }
      leaf tx-pkt-size-128-255 {
        type yang:counter64;
      }
      leaf tx-pkt-size-256-511 {
        type yang:counter64;
      }
      leaf tx-pkt-size-512-1023 {
        type yang:counter64;
      }
      leaf tx-pkt-size-1024-1518 {
        type yang:counter64;
      }
      leaf tx-pkt-size-gt-1518 {
        type yang:counter64;
      }
      leaf rx-policer-remark {
        type yang:counter64;
      }
    }
    list mac {
      description "Display MAC addresses";
      config false;
      key "bridge-id if-name mac-address";
      leaf bridge-id {
        description "BRIDGE ID";
        type viptela:bridge-id;
      }
      leaf if-name {
        description "Interface Name";
        type viptela:named-type;
      }
      leaf mac-address {
        description "Hardware Address";
        type viptela:named-type;
      }
      leaf type {
        description "MAC address type: static/dynamic";
        type string;
      }
      leaf expiry-time {
        description "Time left for the entry to be aged out.";
        type string;
      }
      leaf rx-packets {
        type yang:counter64;
      }
      leaf rx-octets {
        type yang:counter64;
      }
      leaf tx-packets {
        type yang:counter64;
      }
      leaf tx-octets {
        type yang:counter64;
      }
    }
  }
  notification bridge-creation {
    uses viptela:common-notification-header;
    leaf bridge-id {
      type viptela:bridge-id;
    }
  }
  notification bridge-deletion {
    uses viptela:common-notification-header;
    leaf bridge-id {
      type viptela:bridge-id;
    }
  }
  notification bridge-interface-state-change {
    uses viptela:common-notification-header;
    leaf bridge-id {
      type viptela:bridge-id;
    }
    leaf if-name {
      type viptela:named-type;
    }
    leaf new-state {
      type viptela:oper-state;
    }
  }
  notification bridge-max-mac-reached {
    uses viptela:common-notification-header;
    leaf bridge-id {
      type viptela:bridge-id;
    }
    leaf num-macs {
      type uint32;
    }
  }
}
