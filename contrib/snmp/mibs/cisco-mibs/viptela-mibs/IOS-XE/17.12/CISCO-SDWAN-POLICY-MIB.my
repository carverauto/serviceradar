-- *****************************************************************
-- CISCO-SDWAN-POLICY-MIB.my:
-- OID assignments for Cisco sdwan policy

-- Feb 2021, Michelle Ng

-- Copyright (c) 2020-2022 by Cisco Systems, Inc.
-- All rights reserved.
-- *****************************************************************

CISCO-SDWAN-POLICY-MIB DEFINITIONS ::= BEGIN
IMPORTS
    MODULE-IDENTITY,
    OBJECT-TYPE,
    NOTIFICATION-TYPE,
    Unsigned32,
    Counter64
        FROM SNMPv2-SMI
    MODULE-COMPLIANCE,
    OBJECT-GROUP,
    NOTIFICATION-GROUP
        FROM SNMPv2-CONF
    TEXTUAL-CONVENTION,
    TruthValue
        FROM SNMPv2-TC
    ciscoMgmt
        FROM CISCO-SMI;

ciscoSdwanPolicyMIB MODULE-IDENTITY
    LAST-UPDATED "202103010000Z"
    ORGANIZATION    "Cisco Systems Inc."
    CONTACT-INFO
            "Cisco Systems,
            Customer Service

            Postal: 170 West Tasman Drive
            San Jose, CA  95134
            USA

            Tel: +1 800 553-NETS

            Email: cs-snmp@cisco.com"
    DESCRIPTION "This module defines the data model for route
                 and forwarding policy management"
    REVISION "202103010000Z"
    DESCRIPTION "Cisco SDWAN Policy Revision 0"
    ::= { ciscoMgmt 1005 }

UnsignedByte ::= TEXTUAL-CONVENTION
    DISPLAY-HINT "d"
    STATUS      current
    DESCRIPTION "xs:unsignedByte"
    SYNTAX      Unsigned32 (0 .. 255)

UnsignedShort ::= TEXTUAL-CONVENTION
    DISPLAY-HINT "d"
    STATUS      current
    DESCRIPTION "xs:unsignedShort"
    SYNTAX      Unsigned32 (0 .. 65535)

Ipv4Prefix ::= TEXTUAL-CONVENTION
    DISPLAY-HINT "1d.1d.1d.1d/1d"
    STATUS      current
    DESCRIPTION "confd:ipv4Prefix"
    SYNTAX      OCTET STRING (SIZE (5))

InetAddressIP ::= TEXTUAL-CONVENTION
    STATUS      current
    DESCRIPTION "confd:inetAddressIP"
    SYNTAX      OCTET STRING (SIZE (4|16))

String ::= TEXTUAL-CONVENTION
    DISPLAY-HINT "1t"
    STATUS      current
    DESCRIPTION "xs:string"
    SYNTAX      OCTET STRING

DestinationIp ::= TEXTUAL-CONVENTION
    DISPLAY-HINT "1t"
    STATUS      current
    DESCRIPTION "destination ip"
    SYNTAX      OCTET STRING

SourceIp ::= TEXTUAL-CONVENTION
    DISPLAY-HINT "1t"
    STATUS      current
    DESCRIPTION "source ip"
    SYNTAX      OCTET STRING

TcpFlags ::= TEXTUAL-CONVENTION
    STATUS      current
    DESCRIPTION "TCP flags"
    SYNTAX      BITS {syn(0)}

DataPolicyDirectionEnum ::= TEXTUAL-CONVENTION
    STATUS      current
    DESCRIPTION "Policy direction"
    SYNTAX      INTEGER {from-service(0),
                         from-tunnel(1),
                         all(2)}

DirectionEnum ::= TEXTUAL-CONVENTION
    STATUS      current
    DESCRIPTION "direction enum"
    SYNTAX      INTEGER {in(0),
                         out(1)}
TransportProtocol ::= TEXTUAL-CONVENTION
    STATUS      current
    DESCRIPTION "Transport protocol"
    SYNTAX      INTEGER {transport-tcp(0),
                         transport-udp(1)}

ActionDataEnum ::= TEXTUAL-CONVENTION
    STATUS      current
    DESCRIPTION "Action"
    SYNTAX      INTEGER {accept(0),
                         drop(1)}

EncapsulationList ::= TEXTUAL-CONVENTION
     DISPLAY-HINT "1t"
     STATUS      current
     DESCRIPTION "Encapsulation list"
     SYNTAX      OCTET STRING

FnfMonitorEnum ::= TEXTUAL-CONVENTION
    STATUS      current
    DESCRIPTION "Fnf monitor"
    SYNTAX      INTEGER {ipv4(0),
                         ipv6(1),
                         both(2)}

ColorList ::= TEXTUAL-CONVENTION
     DISPLAY-HINT "1t"
     STATUS      current
     DESCRIPTION "Color list"
     SYNTAX      OCTET STRING

-- Notification type definitions
NotificationSeverity ::= TEXTUAL-CONVENTION
    STATUS      current
    DESCRIPTION "Netconf notification severity level"
    SYNTAX      INTEGER {critical(1),
                         major(2),
			 minor(3)}

VpnId ::= TEXTUAL-CONVENTION
    DISPLAY-HINT "d"
    STATUS      current
    DESCRIPTION "<0..65530>"
    SYNTAX      Unsigned32 (0 .. 65530)

-- MIB Objects, Notification Objects, Notification and Conform
ciscoSdwanPolicyMIBNotifs OBJECT IDENTIFIER
    ::= { ciscoSdwanPolicyMIB 0 }

ciscoSdwanPolicyMIBObjects OBJECT IDENTIFIER
    ::= { ciscoSdwanPolicyMIB 1 }

ciscoSdwanPolicyMIBNotifObjects OBJECT IDENTIFIER
    ::= { ciscoSdwanPolicyMIB 2 }

ciscoSdwanPolicyMIBConform OBJECT IDENTIFIER
    ::= { ciscoSdwanPolicyMIB 3 }

-- tagpath /policy/snmp-policy
policy OBJECT IDENTIFIER ::= { ciscoSdwanPolicyMIBObjects 4 }

-- tagpath /policy/snmp-policy/data-policy
policyDataPolicyFilter OBJECT IDENTIFIER ::= { policy 1 }

-- tagpath /policy/snmp-policy/app-route-policy
policyAppRoutePolicy OBJECT IDENTIFIER ::= { policy 2 }

-- tagpath /policy/snmp-policy/access-list-names
policyAccessListNames OBJECT IDENTIFIER ::= { policy 3 }

-- tagpath /policy/snmp-policy/access-list-counters
policyAccessListCounters OBJECT IDENTIFIER ::= { policy 4 }

-- tagpath /policy/snmp-policy/access-list-policers
policyAccessListPolicers OBJECT IDENTIFIER ::= { policy 5 }

-- tagpath /policy/snmp-policy/access-list-associations
policyAccessListAssociations OBJECT IDENTIFIER ::= { policy 8 }

-- tagpath /policy/snmp-policy/rewrite-associations
policyRewriteAssociations OBJECT IDENTIFIER ::= { policy 9 }

-- tagpath /policy/from-vsmart
policyFromVsmart OBJECT IDENTIFIER ::= { policy 10 }

-- tagpath /policy/data-policy-filter
policyDataPolicyFilterTable OBJECT-TYPE
    SYNTAX      SEQUENCE OF PolicyDataPolicyFilterEntry
    MAX-ACCESS  not-accessible
    STATUS      current
    DESCRIPTION "Data policy filters"
    ::= { policyDataPolicyFilter 1 }

-- tagpath /policy/data-policy-filter
policyDataPolicyFilterEntry OBJECT-TYPE
    SYNTAX      PolicyDataPolicyFilterEntry
    MAX-ACCESS  not-accessible
    STATUS      current
    DESCRIPTION "data polcy filter entry"
    INDEX { policyDataPolicyFilterName }
        ::= { policyDataPolicyFilterTable 1 }

PolicyDataPolicyFilterEntry ::=
    SEQUENCE {
        policyDataPolicyFilterName String
    }

-- tagpath /policy/data-policy-filter/name
policyDataPolicyFilterName OBJECT-TYPE
    SYNTAX      String (SIZE (1 .. 127))
    MAX-ACCESS  read-only
    STATUS      current
    DESCRIPTION "Data policy name"
    ::= { policyDataPolicyFilterEntry 1 }

-- tagpath /policy/data-policy-filter/data-policy-vpnlist
policyDataPolicyFilterVpnlistTable OBJECT-TYPE
    SYNTAX      SEQUENCE OF PolicyDataPolicyFilterVpnlistEntry
    MAX-ACCESS  not-accessible
    STATUS      current
    DESCRIPTION "Filter VPN list"
    ::= { policyDataPolicyFilter 2 }

-- tagpath /policy/data-policy-filter/data-policy-vpnlist
policyDataPolicyFilterVpnlistEntry OBJECT-TYPE
    SYNTAX      PolicyDataPolicyFilterVpnlistEntry
    MAX-ACCESS  not-accessible
    STATUS      current
    DESCRIPTION "data policy filter vpn list entry"
    INDEX { policyDataPolicyFilterName,
            policyDataPolicyFilterVpnlistName }
        ::= { policyDataPolicyFilterVpnlistTable 1 }

PolicyDataPolicyFilterVpnlistEntry ::=
    SEQUENCE {
        policyDataPolicyFilterVpnlistName String
    }

-- tagpath /policy/data-policy-filter/data-policy-vpnlist/name
policyDataPolicyFilterVpnlistName OBJECT-TYPE
    SYNTAX      String (SIZE (1 .. 32))
    MAX-ACCESS  read-only
    STATUS      current
    DESCRIPTION "VPN list name"
    ::= { policyDataPolicyFilterVpnlistEntry 1 }

-- tagpath
-- /policy/data-policy-filter/data-policy-vpnlist/data-policy-counter
policyDataPolicyFilterVpnlistCounterTable OBJECT-TYPE
    SYNTAX      SEQUENCE OF PolicyDataPolicyFilterVpnlistCounterEntry
    MAX-ACCESS  not-accessible
    STATUS      current
    DESCRIPTION "Filter counters"
    ::= { policyDataPolicyFilter 3 }

-- tagpath
-- /policy/data-policy-filter/data-policy-vpnlist/data-policy-counter
policyDataPolicyFilterVpnlistCounterEntry OBJECT-TYPE
    SYNTAX      PolicyDataPolicyFilterVpnlistCounterEntry
    MAX-ACCESS  not-accessible
    STATUS      current
    DESCRIPTION "data policy filter vpn list counter entry"
    INDEX { policyDataPolicyFilterName,
            policyDataPolicyFilterVpnlistName,
	    policyDataPolicyFilterVpnlistCounterName }
        ::= { policyDataPolicyFilterVpnlistCounterTable 1 }

PolicyDataPolicyFilterVpnlistCounterEntry ::=
    SEQUENCE {
        policyDataPolicyFilterVpnlistCounterName String,
        policyDataPolicyFilterVpnlistCounterPackets Counter64,
        policyDataPolicyFilterVpnlistCounterBytes Counter64
    }

-- tagpath
-- /policy/data-policy-filter/data-policy-vpnlist
-- /data-policy-counter/counter-name
policyDataPolicyFilterVpnlistCounterName OBJECT-TYPE
    SYNTAX      String (SIZE (1 .. 32))
    MAX-ACCESS  not-accessible
    STATUS      current
    DESCRIPTION "Counter name"
    ::= { policyDataPolicyFilterVpnlistCounterEntry 1 }

-- tagpath
-- /policy/data-policy-filter/data-policy-vpnlist
-- /data-policy-counter/packets
policyDataPolicyFilterVpnlistCounterPackets OBJECT-TYPE
    SYNTAX      Counter64
    MAX-ACCESS  read-only
    STATUS      current
    DESCRIPTION "data policy filter vpn list counter in packets"
    ::= { policyDataPolicyFilterVpnlistCounterEntry 2 }

-- tagpath
-- /policy/data-policy-filter/data-policy-vpnlist
-- /data-policy-counter/bytes
policyDataPolicyFilterVpnlistCounterBytes OBJECT-TYPE
    SYNTAX      Counter64
    MAX-ACCESS  read-only
    STATUS      current
    DESCRIPTION "data policy filter vpn list counter in bytes"
    ::= { policyDataPolicyFilterVpnlistCounterEntry 3 }

-- tagpath
-- /policy/data-policy-filter/data-policy-vpnlist/data-policy-policer
policyDataPolicyFilterVpnlistPolicerTable OBJECT-TYPE
    SYNTAX      SEQUENCE OF PolicyDataPolicyFilterVpnlistPolicerEntry
    MAX-ACCESS  not-accessible
    STATUS      current
    DESCRIPTION "Filter policers"
    ::= { policyDataPolicyFilter 4 }

-- tagpath
-- /policy/data-policy-filter/data-policy-vpnlist/data-policy-policer
policyDataPolicyFilterVpnlistPolicerEntry OBJECT-TYPE
    SYNTAX      PolicyDataPolicyFilterVpnlistPolicerEntry
    MAX-ACCESS  not-accessible
    STATUS      current
    DESCRIPTION "data policy filter vpn list policer entry"
    INDEX { policyDataPolicyFilterName,
            policyDataPolicyFilterVpnlistName,
	    policyDataPolicyFilterVpnlistPolicerName }
        ::= { policyDataPolicyFilterVpnlistPolicerTable 1 }

PolicyDataPolicyFilterVpnlistPolicerEntry ::=
    SEQUENCE {
        policyDataPolicyFilterVpnlistPolicerName String,
        policyDataPolicyFilterVpnlistPolicerOosPackets Counter64,
        policyDataPolicyFilterVpnlistPolicerOosBytes Counter64
    }

-- tagpath
-- /policy/data-policy-filter/data-policy-vpnlist
-- /data-policy-policer/policer-name
policyDataPolicyFilterVpnlistPolicerName OBJECT-TYPE
    SYNTAX      String (SIZE (1 .. 128))
    MAX-ACCESS  not-accessible
    STATUS      current
    DESCRIPTION "Policer name"
    ::= { policyDataPolicyFilterVpnlistPolicerEntry 1 }

-- tagpath
-- /policy/data-policy-filter/data-policy-vpnlist
-- /data-policy-policer/oos-packets
policyDataPolicyFilterVpnlistPolicerOosPackets OBJECT-TYPE
    SYNTAX      Counter64
    MAX-ACCESS  read-only
    STATUS      current
    DESCRIPTION "data policy filter vpn list policer oos in packets"
    ::= { policyDataPolicyFilterVpnlistPolicerEntry 2 }

-- tagpath
-- /policy/data-policy-filter/data-policy-vpnlist
-- /data-policy-policer/oos-bytes
policyDataPolicyFilterVpnlistPolicerOosBytes OBJECT-TYPE
    SYNTAX      Counter64
    MAX-ACCESS  read-only
    STATUS      current
    DESCRIPTION "data policy filter vpn list policer oos in bytes"
    ::= { policyDataPolicyFilterVpnlistPolicerEntry 3 }

-- tagpath /policy/app-route-policy-filter
policyAppRoutePolicyFilterTable OBJECT-TYPE
    SYNTAX      SEQUENCE OF PolicyAppRoutePolicyFilterEntry
    MAX-ACCESS  not-accessible
    STATUS      current
    DESCRIPTION "Application-aware routing policy filters"
    ::= { policyAppRoutePolicy 1 }

-- tagpath /policy/app-route-policy-filter
policyAppRoutePolicyFilterEntry OBJECT-TYPE
    SYNTAX      PolicyAppRoutePolicyFilterEntry
    MAX-ACCESS  not-accessible
    STATUS      current
    DESCRIPTION "app route policy filter entry"
    INDEX { policyAppRoutePolicyFilterName }
        ::= { policyAppRoutePolicyFilterTable 1 }

PolicyAppRoutePolicyFilterEntry ::=
    SEQUENCE {
        policyAppRoutePolicyFilterName String
    }

-- tagpath /policy/app-route-policy-filter/name
policyAppRoutePolicyFilterName OBJECT-TYPE
    SYNTAX      String (SIZE (1 .. 127))
    MAX-ACCESS  read-only
    STATUS      current
    DESCRIPTION "Application-aware routing policy name"
    ::= { policyAppRoutePolicyFilterEntry 1 }

-- tagpath /policy/app-route-policy-filter/app-route-policy-vpnlist
policyAppRoutePolicyFilterVpnlistTable OBJECT-TYPE
    SYNTAX      SEQUENCE OF PolicyAppRoutePolicyFilterVpnlistEntry
    MAX-ACCESS  not-accessible
    STATUS      current
    DESCRIPTION "Filter VPN list"
    ::= { policyAppRoutePolicy 2 }

-- tagpath /policy/app-route-policy-filter/app-route-policy-vpnlist
policyAppRoutePolicyFilterVpnlistEntry OBJECT-TYPE
    SYNTAX      PolicyAppRoutePolicyFilterVpnlistEntry
    MAX-ACCESS  not-accessible
    STATUS      current
    DESCRIPTION "app route policy filter vpn list entry"
    INDEX { policyAppRoutePolicyFilterName,
            policyAppRoutePolicyFilterVpnlistName }
        ::= { policyAppRoutePolicyFilterVpnlistTable 1 }

PolicyAppRoutePolicyFilterVpnlistEntry ::=
    SEQUENCE {
        policyAppRoutePolicyFilterVpnlistName String
    }

-- tagpath /policy/app-route-policy-filter/app-route-policy-vpnlist/name
policyAppRoutePolicyFilterVpnlistName OBJECT-TYPE
    SYNTAX      String (SIZE (1 .. 32))
    MAX-ACCESS  read-only
    STATUS      current
    DESCRIPTION "VPN list name"
    ::= { policyAppRoutePolicyFilterVpnlistEntry 1 }

-- tagpath
-- /policy/app-route-policy-filter/app-route-policy-vpnlist
-- /app-route-policy-counter
policyAppRoutePolicyFilterVpnlistCounterTable OBJECT-TYPE
    SYNTAX      SEQUENCE OF
                   PolicyAppRoutePolicyFilterVpnlistCounterEntry
    MAX-ACCESS  not-accessible
    STATUS      current
    DESCRIPTION "Filter counters"
    ::= { policyAppRoutePolicy 3 }

-- tagpath
-- /policy/app-route-policy-filter/app-route-policy-vpnlist
-- /app-route-policy-counter
policyAppRoutePolicyFilterVpnlistCounterEntry OBJECT-TYPE
    SYNTAX      PolicyAppRoutePolicyFilterVpnlistCounterEntry
    MAX-ACCESS  not-accessible
    STATUS      current
    DESCRIPTION "app route policy filter vpn list counter entry"
    INDEX { policyAppRoutePolicyFilterName,
            policyAppRoutePolicyFilterVpnlistName,
	    policyAppRoutePolicyFilterVpnlistCounterName }
        ::= { policyAppRoutePolicyFilterVpnlistCounterTable 1 }

PolicyAppRoutePolicyFilterVpnlistCounterEntry ::=
    SEQUENCE {
        policyAppRoutePolicyFilterVpnlistCounterName String,
        policyAppRoutePolicyFilterVpnlistCounterPackets Counter64,
        policyAppRoutePolicyFilterVpnlistCounterBytes Counter64
    }

-- tagpath
-- /policy/app-route-policy-filter/app-route-policy-vpnlist
-- /app-route-policy-counter/counter-name
policyAppRoutePolicyFilterVpnlistCounterName OBJECT-TYPE
    SYNTAX      String (SIZE (1 .. 32))
    MAX-ACCESS  not-accessible
    STATUS      current
    DESCRIPTION "Counter name"
    ::= { policyAppRoutePolicyFilterVpnlistCounterEntry 1 }

-- tagpath
-- /policy/app-route-policy-filter/app-route-policy-vpnlist
-- /app-route-policy-counter/packets
policyAppRoutePolicyFilterVpnlistCounterPackets OBJECT-TYPE
    SYNTAX      Counter64
    MAX-ACCESS  read-only
    STATUS      current
    DESCRIPTION "app route policy filter vpn list counter in packets"
    ::= { policyAppRoutePolicyFilterVpnlistCounterEntry 2 }

-- tagpath
-- /policy/app-route-policy-filter/app-route-policy-vpnlist
-- /app-route-policy-counter/bytes
policyAppRoutePolicyFilterVpnlistCounterBytes OBJECT-TYPE
    SYNTAX      Counter64
    MAX-ACCESS  read-only
    STATUS      current
    DESCRIPTION "app route policy filter vpn list counter in bytes"
    ::= { policyAppRoutePolicyFilterVpnlistCounterEntry 3 }

-- tagpath /policy/access-list-names
policyAccessListNamesTable OBJECT-TYPE
    SYNTAX      SEQUENCE OF PolicyAccessListNamesEntry
    MAX-ACCESS  not-accessible
    STATUS      current
    DESCRIPTION "ACL names"
    ::= { policyAccessListNames 1 }

-- tagpath /policy/access-list-names
policyAccessListNamesEntry OBJECT-TYPE
    SYNTAX      PolicyAccessListNamesEntry
    MAX-ACCESS  not-accessible
    STATUS      current
    DESCRIPTION "access list names entry"
    INDEX { policyAccessListNamesName }
        ::= { policyAccessListNamesTable 1 }

PolicyAccessListNamesEntry ::=
    SEQUENCE {
        policyAccessListNamesName String
    }

-- tagpath /policy/access-list-names/name
policyAccessListNamesName OBJECT-TYPE
    SYNTAX      String (SIZE (1 .. 127))
    MAX-ACCESS  read-only
    STATUS      current
    DESCRIPTION "ACL name"
    ::= { policyAccessListNamesEntry 1 }

-- tagpath /policy/access-list-counters
policyAccessListCountersTable OBJECT-TYPE
    SYNTAX      SEQUENCE OF PolicyAccessListCountersEntry
    MAX-ACCESS  not-accessible
    STATUS      current
    DESCRIPTION "ACL counters"
    ::= { policyAccessListCounters 1 }

-- tagpath /policy/access-list-counters
policyAccessListCountersEntry OBJECT-TYPE
    SYNTAX      PolicyAccessListCountersEntry
    MAX-ACCESS  not-accessible
    STATUS      current
    DESCRIPTION "access list counters entry"
    INDEX { policyAccessListCountersName }
        ::= { policyAccessListCountersTable 1 }

PolicyAccessListCountersEntry ::=
    SEQUENCE {
        policyAccessListCountersName String
    }

-- tagpath /policy/access-list-counters/name
policyAccessListCountersName OBJECT-TYPE
    SYNTAX      String (SIZE (1 .. 127))
    MAX-ACCESS  read-only
    STATUS      current
    DESCRIPTION "ACL name"
    ::= { policyAccessListCountersEntry 1 }

-- tagpath /policy/access-list-counters/access-policy-counter-list
policyAccessListCountersAccessPolicyCounterListTable OBJECT-TYPE
    SYNTAX      SEQUENCE OF
                 PolicyAccessListCountersAccessPolicyCounterListEntry
    MAX-ACCESS  not-accessible
    STATUS      current
    DESCRIPTION "Access policy counter list"
    ::= { policyAccessListCounters 2 }

-- tagpath /policy/access-list-counters/access-policy-counter-list
policyAccessListCountersAccessPolicyCounterListEntry OBJECT-TYPE
    SYNTAX      PolicyAccessListCountersAccessPolicyCounterListEntry
    MAX-ACCESS  not-accessible
    STATUS      current
    DESCRIPTION "access list counters access policy counter list entry"
    INDEX { policyAccessListCountersName,
            policyAccessListCountersAccessPolicyCounterListCounterName }
        ::= { policyAccessListCountersAccessPolicyCounterListTable 1 }

PolicyAccessListCountersAccessPolicyCounterListEntry ::=
    SEQUENCE {
     policyAccessListCountersAccessPolicyCounterListCounterName String,
     policyAccessListCountersAccessPolicyCounterListPackets Counter64,
     policyAccessListCountersAccessPolicyCounterListBytes Counter64
    }

-- tagpath
-- /policy/access-list-counters/access-policy-counter-list/counter-name
policyAccessListCountersAccessPolicyCounterListCounterName OBJECT-TYPE
    SYNTAX      String (SIZE (1 .. 32))
    MAX-ACCESS  not-accessible
    STATUS      current
    DESCRIPTION "Counter name"
    ::= { policyAccessListCountersAccessPolicyCounterListEntry 1 }

-- tagpath
-- /policy/access-list-counters/access-policy-counter-list/packets
policyAccessListCountersAccessPolicyCounterListPackets OBJECT-TYPE
    SYNTAX      Counter64
    MAX-ACCESS  read-only
    STATUS      current
    DESCRIPTION "access list counter access policy
                 counter list in packets"
    ::= { policyAccessListCountersAccessPolicyCounterListEntry 2 }

-- tagpath /policy/access-list-counters/access-policy-counter-list/bytes
policyAccessListCountersAccessPolicyCounterListBytes OBJECT-TYPE
    SYNTAX      Counter64
    MAX-ACCESS  read-only
    STATUS      current
    DESCRIPTION "access list counters access policy
                 counter list in bytes"
    ::= { policyAccessListCountersAccessPolicyCounterListEntry 3 }

-- tagpath /policy/access-list-policers
policyAccessListPolicersTable OBJECT-TYPE
    SYNTAX      SEQUENCE OF PolicyAccessListPolicersEntry
    MAX-ACCESS  not-accessible
    STATUS      current
    DESCRIPTION "ACL policer"
    ::= { policyAccessListPolicers 1 }

-- tagpath /policy/access-list-policers
policyAccessListPolicersEntry OBJECT-TYPE
    SYNTAX      PolicyAccessListPolicersEntry
    MAX-ACCESS  not-accessible
    STATUS      current
    DESCRIPTION "access list policers entry"
    INDEX { policyAccessListPolicersName }
        ::= { policyAccessListPolicersTable 1 }

PolicyAccessListPolicersEntry ::=
    SEQUENCE {
        policyAccessListPolicersName String
    }

-- tagpath /policy/access-list-policers/name
policyAccessListPolicersName OBJECT-TYPE
    SYNTAX      String (SIZE (1 .. 127))
    MAX-ACCESS  read-only
    STATUS      current
    DESCRIPTION "Access policy name"
    ::= { policyAccessListPolicersEntry 1 }

-- tagpath /policy/access-list-policers/access-policy-policer-list
policyAccessListPolicersAccessPolicyPolicerListTable OBJECT-TYPE
    SYNTAX      SEQUENCE OF
                 PolicyAccessListPolicersAccessPolicyPolicerListEntry
    MAX-ACCESS  not-accessible
    STATUS      current
    DESCRIPTION "Access policy policer list"
    ::= { policyAccessListPolicers 2 }

-- tagpath /policy/access-list-policers/access-policy-policer-list
policyAccessListPolicersAccessPolicyPolicerListEntry OBJECT-TYPE
    SYNTAX      PolicyAccessListPolicersAccessPolicyPolicerListEntry
    MAX-ACCESS  not-accessible
    STATUS      current
    DESCRIPTION "access list policers access policy policer list entry"
    INDEX { policyAccessListPolicersName,
            policyAccessListPolicersAccessPolicyPolicerListPolicerName }
        ::= { policyAccessListPolicersAccessPolicyPolicerListTable 1 }

PolicyAccessListPolicersAccessPolicyPolicerListEntry ::=
    SEQUENCE {
   policyAccessListPolicersAccessPolicyPolicerListPolicerName String,
   policyAccessListPolicersAccessPolicyPolicerListOosPackets Counter64,
   policyAccessListPolicersAccessPolicyPolicerListOosBytes Counter64
    }

-- tagpath
-- /policy/access-list-policers/access-policy-policer-list/policer-name
policyAccessListPolicersAccessPolicyPolicerListPolicerName OBJECT-TYPE
    SYNTAX      String (SIZE (1 .. 128))
    MAX-ACCESS  not-accessible
    STATUS      current
    DESCRIPTION "Policer name"
    ::= { policyAccessListPolicersAccessPolicyPolicerListEntry 1 }

-- tagpath
-- /policy/access-list-policers/access-policy-policer-list/oos-packets
policyAccessListPolicersAccessPolicyPolicerListOosPackets OBJECT-TYPE
    SYNTAX      Counter64
    MAX-ACCESS  read-only
    STATUS      current
    DESCRIPTION "access list policers access policy
                 policer list oos in packets"
    ::= { policyAccessListPolicersAccessPolicyPolicerListEntry 2 }

-- tagpath
-- /policy/access-list-policers/access-policy-policer-list/oos-bytes
policyAccessListPolicersAccessPolicyPolicerListOosBytes OBJECT-TYPE
    SYNTAX      Counter64
    MAX-ACCESS  read-only
    STATUS      current
    DESCRIPTION "access list policers access policy
                 policer list oos in bytes"
    ::= { policyAccessListPolicersAccessPolicyPolicerListEntry 3 }

-- tagpath /policy/access-list-associations
policyAccessListAssociationsTable OBJECT-TYPE
    SYNTAX      SEQUENCE OF PolicyAccessListAssociationsEntry
    MAX-ACCESS  not-accessible
    STATUS      current
    DESCRIPTION "Access policy interfaces"
    ::= { policyAccessListAssociations 1 }

-- tagpath /policy/access-list-associations
policyAccessListAssociationsEntry OBJECT-TYPE
    SYNTAX      PolicyAccessListAssociationsEntry
    MAX-ACCESS  not-accessible
    STATUS      current
    DESCRIPTION "access list associations entry"
    INDEX { policyAccessListAssociationsName }
        ::= { policyAccessListAssociationsTable 1 }

PolicyAccessListAssociationsEntry ::=
    SEQUENCE {
        policyAccessListAssociationsName String
    }

-- tagpath /policy/access-list-associations/name
policyAccessListAssociationsName OBJECT-TYPE
    SYNTAX      String (SIZE (1 .. 127))
    MAX-ACCESS  read-only
    STATUS      current
    DESCRIPTION "Access policy name"
    ::= { policyAccessListAssociationsEntry 1 }

-- tagpath /policy/access-list-associations/access-policy-interface-list
policyAccessListAssociationsAccessPolicyInterfaceListTable OBJECT-TYPE
    SYNTAX      SEQUENCE OF
             PolicyAccessListAssociationsAccessPolicyInterfaceListEntry
    MAX-ACCESS  not-accessible
    STATUS      current
    DESCRIPTION "Access policy interface association"
    ::= { policyAccessListAssociations 2 }

-- tagpath /policy/access-list-associations/access-policy-interface-list
policyAccessListAssociationsAccessPolicyInterfaceListEntry OBJECT-TYPE
    SYNTAX  PolicyAccessListAssociationsAccessPolicyInterfaceListEntry
    MAX-ACCESS  not-accessible
    STATUS      current
    DESCRIPTION "access list associations access policy
                 interface list entry"
    INDEX {
        policyAccessListAssociationsName,
        policyAccessListAssociationsAccessPolicyInterfaceListIntName,
        policyAccessListAssociationsAccessPolicyInterfaceListIntDir }
    ::= { policyAccessListAssociationsAccessPolicyInterfaceListTable 1 }

PolicyAccessListAssociationsAccessPolicyInterfaceListEntry ::=
    SEQUENCE {
  policyAccessListAssociationsAccessPolicyInterfaceListIntName String,
  policyAccessListAssociationsAccessPolicyInterfaceListIntDir
                                                        DirectionEnum
    }

-- tagpath
-- /policy/access-list-associations/access-policy-interface-list
-- /interface-name
policyAccessListAssociationsAccessPolicyInterfaceListIntName OBJECT-TYPE
    SYNTAX      String (SIZE (1 .. 32))
    MAX-ACCESS  read-only
    STATUS      current
    DESCRIPTION "Interface name"
    ::= { policyAccessListAssociationsAccessPolicyInterfaceListEntry 1 }

-- tagpath
-- /policy/access-list-associations/access-policy-interface-list
-- /interface-direction
policyAccessListAssociationsAccessPolicyInterfaceListIntDir OBJECT-TYPE
    SYNTAX      DirectionEnum
    MAX-ACCESS  read-only
    STATUS      current
    DESCRIPTION "Interface direction"
    ::= { policyAccessListAssociationsAccessPolicyInterfaceListEntry 2 }

-- tagpath /policy/rewrite-associations
policyRewriteAssociationsTable OBJECT-TYPE
    SYNTAX      SEQUENCE OF PolicyRewriteAssociationsEntry
    MAX-ACCESS  not-accessible
    STATUS      current
    DESCRIPTION "Rewrite rule to interface bindings"
    ::= { policyRewriteAssociations 1 }

-- tagpath /policy/rewrite-associations
policyRewriteAssociationsEntry OBJECT-TYPE
    SYNTAX      PolicyRewriteAssociationsEntry
    MAX-ACCESS  not-accessible
    STATUS      current
    DESCRIPTION "rewrite assocations entry"
    INDEX { policyRewriteAssociationsName }
        ::= { policyRewriteAssociationsTable 1 }

PolicyRewriteAssociationsEntry ::=
    SEQUENCE {
        policyRewriteAssociationsName String
    }

-- tagpath /policy/rewrite-associations/name
policyRewriteAssociationsName OBJECT-TYPE
    SYNTAX      String (SIZE (1 .. 127))
    MAX-ACCESS  read-only
    STATUS      current
    DESCRIPTION "Name of rewrite rule"
    ::= { policyRewriteAssociationsEntry 1 }

-- tagpath /policy/rewrite-associations/rewrite-interface-list
policyRewriteAssociationsRewriteInterfaceListTable OBJECT-TYPE
    SYNTAX      SEQUENCE OF
                 PolicyRewriteAssociationsRewriteInterfaceListEntry
    MAX-ACCESS  not-accessible
    STATUS      current
    DESCRIPTION "Rewrite rule to interface association"
    ::= { policyRewriteAssociations 2 }

-- tagpath /policy/rewrite-associations/rewrite-interface-list
policyRewriteAssociationsRewriteInterfaceListEntry OBJECT-TYPE
    SYNTAX      PolicyRewriteAssociationsRewriteInterfaceListEntry
    MAX-ACCESS  not-accessible
    STATUS      current
    DESCRIPTION "rewrite assocations rewrite interface list entry"
    INDEX { policyRewriteAssociationsName,
            policyRewriteAssociationsRewriteInterfaceListInterfaceName }
        ::= { policyRewriteAssociationsRewriteInterfaceListTable 1 }

PolicyRewriteAssociationsRewriteInterfaceListEntry ::=
    SEQUENCE {
     policyRewriteAssociationsRewriteInterfaceListInterfaceName String
    }

-- tagpath
-- /policy/rewrite-associations/rewrite-interface-list/interface-name
policyRewriteAssociationsRewriteInterfaceListInterfaceName OBJECT-TYPE
    SYNTAX      String (SIZE (1 .. 32))
    MAX-ACCESS  read-only
    STATUS      current
    DESCRIPTION "Interface name"
    ::= { policyRewriteAssociationsRewriteInterfaceListEntry 1 }

-- tagpath /policy/from-vsmart/sla-class
policyFromVsmartSlaClassTable OBJECT-TYPE
    SYNTAX      SEQUENCE OF PolicyFromVsmartSlaClassEntry
    MAX-ACCESS  not-accessible
    STATUS      current
    DESCRIPTION "Configure SLA classes for application-aware routing"
    ::= { policyFromVsmart 2 }

-- tagpath /policy/from-vsmart/sla-class
policyFromVsmartSlaClassEntry OBJECT-TYPE
    SYNTAX      PolicyFromVsmartSlaClassEntry
    MAX-ACCESS  not-accessible
    STATUS      current
    DESCRIPTION "policy from vsmart sla class entry"
    INDEX { IMPLIED policyFromVsmartSlaClassName }
        ::= { policyFromVsmartSlaClassTable 1 }

PolicyFromVsmartSlaClassEntry ::=
    SEQUENCE {
        policyFromVsmartSlaClassName String,
        policyFromVsmartSlaClassLoss UnsignedByte,
        policyFromVsmartSlaClassLatency UnsignedShort,
        policyFromVsmartSlaClassJitter  UnsignedShort,
        policyFromVsmartSlaClassAppProbeClass String
    }

-- tagpath /policy/from-vsmart/sla-class/name
policyFromVsmartSlaClassName OBJECT-TYPE
    SYNTAX      String (SIZE (1 .. 32))
    MAX-ACCESS  not-accessible
    STATUS      current
    DESCRIPTION "Name of SLA class"
    ::= { policyFromVsmartSlaClassEntry 1 }

-- tagpath /policy/from-vsmart/sla-class/loss
policyFromVsmartSlaClassLoss OBJECT-TYPE
    SYNTAX      UnsignedByte (0 .. 100)
    MAX-ACCESS  read-only
    STATUS      current
    DESCRIPTION "Loss percentage"
    ::= { policyFromVsmartSlaClassEntry 2 }

-- tagpath /policy/from-vsmart/sla-class/latency
policyFromVsmartSlaClassLatency OBJECT-TYPE
    SYNTAX      UnsignedShort (1 .. 1000)
    MAX-ACCESS  read-only
    STATUS      current
    DESCRIPTION "Latency, in milliseconds"
    ::= { policyFromVsmartSlaClassEntry 3 }

-- tagpath /policy/from-vsmart/sla-class/jitter
policyFromVsmartSlaClassJitter OBJECT-TYPE
    SYNTAX      UnsignedShort (1 .. 1000)
    MAX-ACCESS  read-only
    STATUS      current
    DESCRIPTION "Jitter, in milliseconds"
    ::= { policyFromVsmartSlaClassEntry 4 }

-- tagpath /policy/from-vsmart/sla-class/app-probe-class
policyFromVsmartSlaClassAppProbeClass OBJECT-TYPE
    SYNTAX      String (SIZE (1 .. 32))
    MAX-ACCESS  read-only
    STATUS      current
    DESCRIPTION "App Probe Class Name"
    ::= { policyFromVsmartSlaClassEntry 5 }

-- tagpath /policy/from-vsmart/data-policy
policyFromVsmartDataPolicyTable OBJECT-TYPE
    SYNTAX      SEQUENCE OF PolicyFromVsmartDataPolicyEntry
    MAX-ACCESS  not-accessible
    STATUS      current
    DESCRIPTION "Display data policy"
    ::= { policyFromVsmart 3 }

-- tagpath /policy/from-vsmart/data-policy
policyFromVsmartDataPolicyEntry OBJECT-TYPE
    SYNTAX      PolicyFromVsmartDataPolicyEntry
    MAX-ACCESS  not-accessible
    STATUS      current
    DESCRIPTION "Data Policy"
    INDEX { IMPLIED policyFromVsmartDataPolicyName }
        ::= { policyFromVsmartDataPolicyTable 1 }

PolicyFromVsmartDataPolicyEntry ::=
    SEQUENCE {
        policyFromVsmartDataPolicyName String,
        policyFromVsmartDataPolicyDirection DataPolicyDirectionEnum
    }

-- tagpath /policy/from-vsmart/data-policy/name
policyFromVsmartDataPolicyName OBJECT-TYPE
    SYNTAX      String (SIZE (1 .. 127))
    MAX-ACCESS  not-accessible
    STATUS      current
    DESCRIPTION "Data policy name"
    ::= { policyFromVsmartDataPolicyEntry 1 }

-- tagpath /policy/from-vsmart/data-policy/direction
policyFromVsmartDataPolicyDirection OBJECT-TYPE
    SYNTAX      DataPolicyDirectionEnum
    MAX-ACCESS  read-only
    STATUS      current
    DESCRIPTION "Data policy direction"
    ::= { policyFromVsmartDataPolicyEntry 2 }

-- tagpath /policy/from-vsmart/data-policy/vpn-list
policyFromVsmartDataPolicyVpnListTable OBJECT-TYPE
    SYNTAX      SEQUENCE OF PolicyFromVsmartDataPolicyVpnListEntry
    MAX-ACCESS  not-accessible
    STATUS      current
    DESCRIPTION "Name of VPN list"
    ::= { policyFromVsmart 4 }

-- tagpath /policy/from-vsmart/data-policy/vpn-list
policyFromVsmartDataPolicyVpnListEntry OBJECT-TYPE
    SYNTAX      PolicyFromVsmartDataPolicyVpnListEntry
    MAX-ACCESS  not-accessible
    STATUS      current
    DESCRIPTION "Date policy vpn list"
    INDEX { policyFromVsmartDataPolicyName,
            IMPLIED policyFromVsmartDataPolicyVpnListName }
        ::= { policyFromVsmartDataPolicyVpnListTable 1 }

PolicyFromVsmartDataPolicyVpnListEntry ::=
    SEQUENCE {
        policyFromVsmartDataPolicyVpnListName String,
        policyFromVsmartDataPolicyVpnListDefaultAction ActionDataEnum
    }

-- tagpath /policy/from-vsmart/data-policy/vpn-list/name
policyFromVsmartDataPolicyVpnListName OBJECT-TYPE
    SYNTAX      String (SIZE (1 .. 32))
    MAX-ACCESS  not-accessible
    STATUS      current
    DESCRIPTION "VPN list name"
    ::= { policyFromVsmartDataPolicyVpnListEntry 1 }

-- tagpath /policy/from-vsmart/data-policy/vpn-list/default-action
policyFromVsmartDataPolicyVpnListDefaultAction OBJECT-TYPE
    SYNTAX      ActionDataEnum
    MAX-ACCESS  read-only
    STATUS      current
    DESCRIPTION "Accept or drop"
    DEFVAL { drop }
    ::= { policyFromVsmartDataPolicyVpnListEntry 2 }

-- tagpath /policy/from-vsmart/data-policy/vpn-list/sequence
policyFromVsmartDataPolicyVpnListSequenceTable OBJECT-TYPE
    SYNTAX      SEQUENCE OF
                   PolicyFromVsmartDataPolicyVpnListSequenceEntry
    MAX-ACCESS  not-accessible
    STATUS      current
    DESCRIPTION "List of sequences"
    ::= { policyFromVsmart 5 }

-- tagpath /policy/from-vsmart/data-policy/vpn-list/sequence
policyFromVsmartDataPolicyVpnListSequenceEntry OBJECT-TYPE
    SYNTAX      PolicyFromVsmartDataPolicyVpnListSequenceEntry
    MAX-ACCESS  not-accessible
    STATUS      current
    DESCRIPTION "Data policy vpn list sequence"
    INDEX { policyFromVsmartDataPolicyName,
            policyFromVsmartDataPolicyVpnListName,
	    policyFromVsmartDataPolicyVpnListSequenceSeqValue }
        ::= { policyFromVsmartDataPolicyVpnListSequenceTable 1 }

PolicyFromVsmartDataPolicyVpnListSequenceEntry ::=
    SEQUENCE {
policyFromVsmartDataPolicyVpnListSequenceSeqValue
                                             UnsignedShort,
policyFromVsmartDataPolicyVpnListSequenceMatchSrcDataPrLst
                                             String,
policyFromVsmartDataPolicyVpnListSequenceMatchSrcDataV6PrLst
                                             String,
policyFromVsmartDataPolicyVpnListSequenceMatchDestDataPrLst
                                             String,
policyFromVsmartDataPolicyVpnListSequenceMatchDestDataV6PrLst
                                             String,
policyFromVsmartDataPolicyVpnListSequenceMatchTcp
                                             TcpFlags,
policyFromVsmartDataPolicyVpnListSequenceActionActionValue
                                             ActionDataEnum,
policyFromVsmartDataPolicyVpnListSequenceActionCount
                                             String,
policyFromVsmartDataPolicyVpnListSequenceActionNatUseVpn
                                             Unsigned32,
policyFromVsmartDataPolicyVpnListSequenceActionCflowd
                                             TruthValue,
policyFromVsmartDataPolicyVpnListSequenceActionSetLocalTlocColor
                                             INTEGER,
policyFromVsmartDataPolicyVpnListSequenceActionSetLocalTlocEncap
                                             INTEGER,
policyFromVsmartDataPolicyVpnListSequenceActionSetNextHop
                                             String,
policyFromVsmartDataPolicyVpnListSequenceActionSetPolicer
                                             String,
policyFromVsmartDataPolicyVpnListSequenceActionSetVpn
                                             Unsigned32,
policyFromVsmartDataPolicyVpnListSequenceActionSetVpnLabel
                                             Unsigned32,
policyFromVsmartDataPolicyVpnListSequenceActionSetTlocIp
                                             InetAddressIP,
policyFromVsmartDataPolicyVpnListSequenceActionSetTlocColor
                                             INTEGER,
policyFromVsmartDataPolicyVpnListSequenceActionSetTlocList
                                             String,
policyFromVsmartDataPolicyVpnListSequenceActionSetServiceSvcType
                                             INTEGER,
policyFromVsmartDataPolicyVpnListSequenceActionSetServiceVpn
                                             Unsigned32,
policyFromVsmartDataPolicyVpnListSequenceActionSetServiceTlocIp
                                             InetAddressIP,
policyFromVsmartDataPolicyVpnListSequenceActionSetSvcTlocClr
                                             INTEGER,
policyFromVsmartDataPolicyVpnListSequencActionSetSvcTlocLst
                                             String,
policyFromVsmartDataPolicyVpnListSequenceActionSetServiceLocal
                                             TruthValue,
policyFromVsmartDataPolicyVpnListSeqActSetServiceRestrict
                                             TruthValue,
policyFromVsmartDataPolicyVpnListSequenceActionLog
                                             TruthValue,
policyFromVsmartDataPolicyVpnListSeqActSetLocalTlocListColor
                                             ColorList,
policyFromVsmartDataPolicyVpnListSeqActSetLocalTlocListEncap
                                             EncapsulationList,
policyFromVsmartDataPolicyVpnListSeqActSetLocalTlocListRestrict
                                             TruthValue,
policyFromVsmartDataPolicyVpnListSequenceActionTcpOptimization
                                             TruthValue,
policyFromVsmartDataPolicyVpnListSequenceActionSetNextHopIpv6
                                             String,
policyFromVsmartDataPolicyVpnListSequenceActionSig
                                             TruthValue,
policyFromVsmartDataPolicyVpnListSequenceActionSetNextHopLoose
                                             TruthValue,
policyFromVsmartDataPolicyVpnListSeqActSigFallbackToRoute
                                             TruthValue
    }

-- tagpath /policy/from-vsmart/data-policy/vpn-list/sequence/seq-value
policyFromVsmartDataPolicyVpnListSequenceSeqValue OBJECT-TYPE
    SYNTAX      UnsignedShort (0 .. 65530)
    MAX-ACCESS  not-accessible
    STATUS      current
    DESCRIPTION "Data policy vpn list sequence seq value"
    ::= { policyFromVsmartDataPolicyVpnListSequenceEntry 1 }

-- tagpath /policy/from-vsmart/data-policy/vpn-list/sequence/match
-- /source-data-prefix-list
policyFromVsmartDataPolicyVpnListSequenceMatchSrcDataPrLst OBJECT-TYPE
    SYNTAX      String (SIZE (1 .. 32))
    MAX-ACCESS  read-only
    STATUS      current
    DESCRIPTION "Source prefix list"
    ::= { policyFromVsmartDataPolicyVpnListSequenceEntry 4 }

-- tagpath /policy/from-vsmart/data-policy/vpn-list/sequence
-- /match/source-data-ipv6-prefix-list
policyFromVsmartDataPolicyVpnListSequenceMatchSrcDataV6PrLst
                                                     OBJECT-TYPE
    SYNTAX      String (SIZE (1 .. 32))
    MAX-ACCESS  read-only
    STATUS      current
    DESCRIPTION "Source IPv6 prefix list"
    ::= { policyFromVsmartDataPolicyVpnListSequenceEntry 5 }

-- tagpath /policy/from-vsmart/data-policy/vpn-list/sequence/match
-- /destination-data-prefix-list
policyFromVsmartDataPolicyVpnListSequenceMatchDestDataPrLst OBJECT-TYPE
    SYNTAX      String (SIZE (1 .. 32))
    MAX-ACCESS  read-only
    STATUS      current
    DESCRIPTION "Destination prefix list"
    ::= { policyFromVsmartDataPolicyVpnListSequenceEntry 7 }

-- tagpath /policy/from-vsmart/data-policy/vpn-list/sequence/match
-- /destination-data-ipv6-prefix-list
policyFromVsmartDataPolicyVpnListSequenceMatchDestDataV6PrLst
                                                       OBJECT-TYPE
    SYNTAX      String (SIZE (1 .. 32))
    MAX-ACCESS  read-only
    STATUS      current
    DESCRIPTION "Destination IPv6 prefix list"
    ::= { policyFromVsmartDataPolicyVpnListSequenceEntry 8 }

-- tagpath /policy/from-vsmart/data-policy/vpn-list/sequence/match/tcp
policyFromVsmartDataPolicyVpnListSequenceMatchTcp OBJECT-TYPE
    SYNTAX      TcpFlags
    MAX-ACCESS  read-only
    STATUS      current
    DESCRIPTION "TCP flags"
    ::= { policyFromVsmartDataPolicyVpnListSequenceEntry 10 }

-- tagpath /policy/from-vsmart/data-policy/vpn-list/sequence/action
-- /action-value
policyFromVsmartDataPolicyVpnListSequenceActionActionValue OBJECT-TYPE
    SYNTAX      ActionDataEnum
    MAX-ACCESS  read-only
    STATUS      current
    DESCRIPTION "Action value"
    DEFVAL { drop }
    ::= { policyFromVsmartDataPolicyVpnListSequenceEntry 11 }

-- tagpath /policy/from-vsmart/data-policy/vpn-list/sequence/action
-- /count
policyFromVsmartDataPolicyVpnListSequenceActionCount OBJECT-TYPE
    SYNTAX      String (SIZE (1 .. 32))
    MAX-ACCESS  read-only
    STATUS      current
    DESCRIPTION "Count packets/bytes matching this rule"
    ::= { policyFromVsmartDataPolicyVpnListSequenceEntry 12 }

-- tagpath /policy/from-vsmart/data-policy/vpn-list/sequence/action
-- /nat/use-vpn
policyFromVsmartDataPolicyVpnListSequenceActionNatUseVpn OBJECT-TYPE
    SYNTAX      Unsigned32
    MAX-ACCESS  read-only
    STATUS      current
    DESCRIPTION "VPN ID (only 0 is allowed)"
    ::= { policyFromVsmartDataPolicyVpnListSequenceEntry 13 }

-- tagpath /policy/from-vsmart/data-policy/vpn-list/sequence/action
-- /cflowd
policyFromVsmartDataPolicyVpnListSequenceActionCflowd OBJECT-TYPE
    SYNTAX      TruthValue
    MAX-ACCESS  read-only
    STATUS      current
    DESCRIPTION "Apply cflowd"
    ::= { policyFromVsmartDataPolicyVpnListSequenceEntry 14 }

-- tagpath /policy/from-vsmart/data-policy/vpn-list/sequence/action
-- /set/local-tloc/color
policyFromVsmartDataPolicyVpnListSequenceActionSetLocalTlocColor
                                                       OBJECT-TYPE
    SYNTAX      INTEGER {default(1),
                         mpls(2),
			 metro-ethernet(3),
			 biz-internet(4),
			 public-internet(5),
			 lte(6),
			 threeG(7),
			 red(8),
			 green(9),
			 blue(10),
			 gold(11),
			 silver(12),
			 bronze(13),
			 custom1(14),
			 custom2(15),
			 custom3(16),
			 private1(17),
			 private2(18),
			 private3(19),
			 private4(20),
			 private5(21),
			 private6(22)}
    MAX-ACCESS  read-only
    STATUS      current
    DESCRIPTION "Color"
    ::= { policyFromVsmartDataPolicyVpnListSequenceEntry 15 }

-- tagpath /policy/from-vsmart/data-policy/vpn-list/sequence/action
-- /set/local-tloc/encap
policyFromVsmartDataPolicyVpnListSequenceActionSetLocalTlocEncap
                                                        OBJECT-TYPE
    SYNTAX      INTEGER {gre(1),
                         ipsec(2)}
    MAX-ACCESS  read-only
    STATUS      current
    DESCRIPTION "Encapsulation"
    ::= { policyFromVsmartDataPolicyVpnListSequenceEntry 16 }

-- tagpath /policy/from-vsmart/data-policy/vpn-list/sequence/action
-- /set/next-hop
policyFromVsmartDataPolicyVpnListSequenceActionSetNextHop OBJECT-TYPE
    SYNTAX      String
    MAX-ACCESS  read-only
    STATUS      current
    DESCRIPTION "Next-hop address"
    ::= { policyFromVsmartDataPolicyVpnListSequenceEntry 17 }

-- tagpath /policy/from-vsmart/data-policy/vpn-list/sequence/action
-- /set/policer
policyFromVsmartDataPolicyVpnListSequenceActionSetPolicer OBJECT-TYPE
    SYNTAX      String (SIZE (1 .. 32))
    MAX-ACCESS  read-only
    STATUS      current
    DESCRIPTION "Policer"
    ::= { policyFromVsmartDataPolicyVpnListSequenceEntry 18 }

-- tagpath /policy/from-vsmart/data-policy/vpn-list/sequence/action
-- /set/vpn
policyFromVsmartDataPolicyVpnListSequenceActionSetVpn OBJECT-TYPE
    SYNTAX      Unsigned32 (0 .. 65530)
    MAX-ACCESS  read-only
    STATUS      current
    DESCRIPTION "VPN ID"
    ::= { policyFromVsmartDataPolicyVpnListSequenceEntry 19 }

-- tagpath /policy/from-vsmart/data-policy/vpn-list/sequence/action
-- /set/vpn-label
policyFromVsmartDataPolicyVpnListSequenceActionSetVpnLabel OBJECT-TYPE
    SYNTAX      Unsigned32
    MAX-ACCESS  read-only
    STATUS      current
    DESCRIPTION "VPN label"
    ::= { policyFromVsmartDataPolicyVpnListSequenceEntry 20 }

-- tagpath /policy/from-vsmart/data-policy/vpn-list/sequence/action
-- /set/tloc/ip
policyFromVsmartDataPolicyVpnListSequenceActionSetTlocIp OBJECT-TYPE
    SYNTAX      InetAddressIP
    MAX-ACCESS  read-only
    STATUS      current
    DESCRIPTION "IP address"
    ::= { policyFromVsmartDataPolicyVpnListSequenceEntry 21 }

-- tagpath /policy/from-vsmart/data-policy/vpn-list/sequence/action
-- /set/tloc/color
policyFromVsmartDataPolicyVpnListSequenceActionSetTlocColor OBJECT-TYPE
    SYNTAX      INTEGER {default(1),
                         mpls(2),
			 metro-ethernet(3),
			 biz-internet(4),
			 public-internet(5),
			 lte(6),
			 threeG(7),
			 red(8),
			 green(9),
			 blue(10),
			 gold(11),
			 silver(12),
			 bronze(13),
			 custom1(14),
			 custom2(15),
			 custom3(16),
			 private1(17),
			 private2(18),
			 private3(19),
			 private4(20),
			 private5(21),
			 private6(22)}
    MAX-ACCESS  read-only
    STATUS      current
    DESCRIPTION "Color"
    ::= { policyFromVsmartDataPolicyVpnListSequenceEntry 22 }

-- tagpath /policy/from-vsmart/data-policy/vpn-list/sequence/action
-- /set/tloc-list
policyFromVsmartDataPolicyVpnListSequenceActionSetTlocList OBJECT-TYPE
    SYNTAX      String (SIZE (1 .. 32))
    MAX-ACCESS  read-only
    STATUS      current
    DESCRIPTION "Name of TLOC list"
    ::= { policyFromVsmartDataPolicyVpnListSequenceEntry 23 }

-- tagpath /policy/from-vsmart/data-policy/vpn-list/sequence/action
-- /set/service/svc-type
policyFromVsmartDataPolicyVpnListSequenceActionSetServiceSvcType
                                                        OBJECT-TYPE
    SYNTAX      INTEGER {fW(1),
                         iDS(2),
			 iDP(3),
			 netsvc1(4),
			 netsvc2(5),
			 netsvc3(6),
			 netsvc4(7)}
    MAX-ACCESS  read-only
    STATUS      current
    DESCRIPTION "Service type"
    ::= { policyFromVsmartDataPolicyVpnListSequenceEntry 24 }

-- tagpath /policy/from-vsmart/data-policy/vpn-list/sequence/action
-- /set/service/vpn
policyFromVsmartDataPolicyVpnListSequenceActionSetServiceVpn
                                                    OBJECT-TYPE
    SYNTAX      Unsigned32 (0 .. 65530)
    MAX-ACCESS  read-only
    STATUS      current
    DESCRIPTION "VPN ID"
    ::= { policyFromVsmartDataPolicyVpnListSequenceEntry 25 }

-- tagpath /policy/from-vsmart/data-policy/vpn-list/sequence/action
-- /set/service/tloc/ip
policyFromVsmartDataPolicyVpnListSequenceActionSetServiceTlocIp
                                                       OBJECT-TYPE
    SYNTAX      InetAddressIP
    MAX-ACCESS  read-only
    STATUS      current
    DESCRIPTION "IP address"
    ::= { policyFromVsmartDataPolicyVpnListSequenceEntry 26 }

-- tagpath /policy/from-vsmart/data-policy/vpn-list/sequence/action
-- /set/service/tloc/color
policyFromVsmartDataPolicyVpnListSequenceActionSetSvcTlocClr
                                                     OBJECT-TYPE
    SYNTAX      INTEGER {default(1),
                         mpls(2),
			 metro-ethernet(3),
			 biz-internet(4),
			 public-internet(5),
			 lte(6),
			 threeG(7),
			 red(8),
			 green(9),
			 blue(10),
			 gold(11),
			 silver(12),
			 bronze(13),
			 custom1(14),
			 custom2(15),
			 custom3(16),
			 private1(17),
			 private2(18),
			 private3(19),
			 private4(20),
			 private5(21),
			 private6(22)}
    MAX-ACCESS  read-only
    STATUS      current
    DESCRIPTION "Color"
    ::= { policyFromVsmartDataPolicyVpnListSequenceEntry 27 }

-- tagpath /policy/from-vsmart/data-policy/vpn-list/sequence/action
-- /set/service/tloc-list
policyFromVsmartDataPolicyVpnListSequencActionSetSvcTlocLst OBJECT-TYPE
    SYNTAX      String (SIZE (1 .. 32))
    MAX-ACCESS  read-only
    STATUS      current
    DESCRIPTION "Name of TLOC list"
    ::= { policyFromVsmartDataPolicyVpnListSequenceEntry 28 }

-- tagpath /policy/from-vsmart/data-policy/vpn-list/sequence/action
-- /set/service/local
policyFromVsmartDataPolicyVpnListSequenceActionSetServiceLocal
                                                      OBJECT-TYPE
    SYNTAX      TruthValue
    MAX-ACCESS  read-only
    STATUS      current
    DESCRIPTION "Local service"
    ::= { policyFromVsmartDataPolicyVpnListSequenceEntry 29 }

-- tagpath /policy/from-vsmart/data-policy/vpn-list/sequence/action
-- /set/service/restrict
policyFromVsmartDataPolicyVpnListSeqActSetServiceRestrict
                                                          OBJECT-TYPE
    SYNTAX      TruthValue
    MAX-ACCESS  read-only
    STATUS      current
    DESCRIPTION "Drop packet if local service unreachable"
    ::= { policyFromVsmartDataPolicyVpnListSequenceEntry 30 }

-- tagpath /policy/from-vsmart/data-policy/vpn-list/sequence/action/log
policyFromVsmartDataPolicyVpnListSequenceActionLog OBJECT-TYPE
    SYNTAX      TruthValue
    MAX-ACCESS  read-only
    STATUS      current
    DESCRIPTION "Log this packet header"
    ::= { policyFromVsmartDataPolicyVpnListSequenceEntry 31 }

-- tagpath /policy/from-vsmart/data-policy/vpn-list/sequence/action/set
-- /local-tloc-list/color
policyFromVsmartDataPolicyVpnListSeqActSetLocalTlocListColor OBJECT-TYPE
    SYNTAX      ColorList
    MAX-ACCESS  read-only
    STATUS      current
    DESCRIPTION "Local color list"
    ::= { policyFromVsmartDataPolicyVpnListSequenceEntry 32 }

-- tagpath /policy/from-vsmart/data-policy/vpn-list/sequence/action/set
-- /local-tloc-list/encap
policyFromVsmartDataPolicyVpnListSeqActSetLocalTlocListEncap OBJECT-TYPE
    SYNTAX      EncapsulationList
    MAX-ACCESS  read-only
    STATUS      current
    DESCRIPTION "Local encapsulation list"
    ::= { policyFromVsmartDataPolicyVpnListSequenceEntry 33 }

-- tagpath /policy/from-vsmart/data-policy/vpn-list/sequence/action
-- /set/local-tloc-list/restrict
policyFromVsmartDataPolicyVpnListSeqActSetLocalTlocListRestrict
                                                            OBJECT-TYPE
    SYNTAX      TruthValue
    MAX-ACCESS  read-only
    STATUS      current
    DESCRIPTION "Drop packet if local color or encapsulation
                 is not found"
    ::= { policyFromVsmartDataPolicyVpnListSequenceEntry 34 }

-- tagpath /policy/from-vsmart/data-policy/vpn-list/sequence/action
-- /tcp-optimization
policyFromVsmartDataPolicyVpnListSequenceActionTcpOptimization
                                                        OBJECT-TYPE
    SYNTAX      TruthValue
    MAX-ACCESS  read-only
    STATUS      current
    DESCRIPTION "Send TCP traffic for optimization"
    ::= { policyFromVsmartDataPolicyVpnListSequenceEntry 35 }

-- tagpath /policy/from-vsmart/data-policy/vpn-list/sequence/action
-- /set/next-hop-ipv6
policyFromVsmartDataPolicyVpnListSequenceActionSetNextHopIpv6
                                                       OBJECT-TYPE
    SYNTAX      String
    MAX-ACCESS  read-only
    STATUS      current
    DESCRIPTION "Next-hop IPv6 address"
    ::= { policyFromVsmartDataPolicyVpnListSequenceEntry 37 }

-- tagpath /policy/from-vsmart/data-policy/vpn-list/sequence/action/sig
policyFromVsmartDataPolicyVpnListSequenceActionSig OBJECT-TYPE
    SYNTAX      TruthValue
    MAX-ACCESS  read-only
    STATUS      current
    DESCRIPTION "Packet redirect to SIG (Secure Internet Gateway)"
    ::= { policyFromVsmartDataPolicyVpnListSequenceEntry 38 }

-- tagpath /policy/from-vsmart/data-policy/vpn-list/sequence/action
-- /set/next-hop-loose
policyFromVsmartDataPolicyVpnListSequenceActionSetNextHopLoose
                                                       OBJECT-TYPE
    SYNTAX      TruthValue
    MAX-ACCESS  read-only
    STATUS      current
    DESCRIPTION "Forward packet if next-hop is not routable"
    ::= { policyFromVsmartDataPolicyVpnListSequenceEntry 39 }

-- tagpath /policy/from-vsmart/data-policy/vpn-list/sequence/action
-- /sig-action/fallback-to-route
policyFromVsmartDataPolicyVpnListSeqActSigFallbackToRoute
                                                       OBJECT-TYPE
    SYNTAX      TruthValue
    MAX-ACCESS  read-only
    STATUS      current
    DESCRIPTION "Fallback to routing if SIG is DOWN"
    ::= { policyFromVsmartDataPolicyVpnListSequenceEntry 41 }


-- tagpath /policy/from-vsmart/data-policy/vpn-list/sequence/action
-- /set/vip-tloc-pref-list
policyFromVsmartDataPolicyVpnListSeqActSetVipTlocPrLstTable OBJECT-TYPE
    SYNTAX      SEQUENCE OF
             PolicyFromVsmartDataPolicyVpnListSeqActSetVipTlocPrLstEntry
    MAX-ACCESS  not-accessible
    STATUS      current
    DESCRIPTION "Data policy vpn list seq act set vip tloc pr list"
    ::= { policyFromVsmart 6 }

-- tagpath /policy/from-vsmart/data-policy/vpn-list/sequence/action
-- /set/vip-tloc-pref-list
policyFromVsmartDataPolicyVpnListSeqActSetVipTlocPrLstEntry OBJECT-TYPE
  SYNTAX  PolicyFromVsmartDataPolicyVpnListSeqActSetVipTlocPrLstEntry
  MAX-ACCESS  not-accessible
  STATUS      current
  DESCRIPTION "Data policy vpn list seq act set vip tloc pr list"
  INDEX {
  policyFromVsmartDataPolicyName,
  policyFromVsmartDataPolicyVpnListName,
  policyFromVsmartDataPolicyVpnListSequenceSeqValue,
  policyFromVsmartDataPolicyVpnListSeqActSetVipTlocPrLstListNum }
  ::= { policyFromVsmartDataPolicyVpnListSeqActSetVipTlocPrLstTable 1 }

PolicyFromVsmartDataPolicyVpnListSeqActSetVipTlocPrLstEntry ::=
    SEQUENCE {
        policyFromVsmartDataPolicyVpnListSeqActSetVipTlocPrLstListNum
	                                                   Unsigned32,
        policyFromVsmartDataPolicyVpnListSeqActSetVipTlocPrLstTlocLbl
	                                                   Unsigned32,
        policyFromVsmartDataPolicyVpnListSeqActSetVipTlocPrLstTlocIp
	                                                 InetAddressIP,
        policyFromVsmartDataPolicyVpnListSeqActSetVipTlocPrLstTlocClr
	                                                   INTEGER,
        policyFromVsmartDataPolicyVpnListSeqActSetVipTlocPrLstTlocEn
	                                                   INTEGER,
        policyFromVsmartDataPolicyVpnListSeqActSetVipTlocPrLstTlocPrf
	                                                   Unsigned32
    }

-- tagpath /policy/from-vsmart/data-policy/vpn-list/sequence/action
-- /set/vip-tloc-pref-list/list-num
policyFromVsmartDataPolicyVpnListSeqActSetVipTlocPrLstListNum
                                                       OBJECT-TYPE
    SYNTAX      Unsigned32 (0 .. 100)
    MAX-ACCESS  not-accessible
    STATUS      current
    DESCRIPTION "Data policy vpn list sdwq act set vip tloc pr lst
                 list num"
  ::= { policyFromVsmartDataPolicyVpnListSeqActSetVipTlocPrLstEntry 1 }

-- tagpath /policy/from-vsmart/data-policy/vpn-list/sequence/action
-- /set/vip-tloc-pref-list/tloc-label
policyFromVsmartDataPolicyVpnListSeqActSetVipTlocPrLstTlocLbl
                                                        OBJECT-TYPE
    SYNTAX      Unsigned32
    MAX-ACCESS  read-only
    STATUS      current
    DESCRIPTION "VPN label"
  ::= { policyFromVsmartDataPolicyVpnListSeqActSetVipTlocPrLstEntry 2 }

-- tagpath /policy/from-vsmart/data-policy/vpn-list/sequence/action
-- /set/vip-tloc-pref-list/tloc-ip
policyFromVsmartDataPolicyVpnListSeqActSetVipTlocPrLstTlocIp OBJECT-TYPE
    SYNTAX      InetAddressIP
    MAX-ACCESS  read-only
    STATUS      current
    DESCRIPTION "IP address"
  ::= { policyFromVsmartDataPolicyVpnListSeqActSetVipTlocPrLstEntry 3 }

-- tagpath /policy/from-vsmart/data-policy/vpn-list/sequence/action
-- /set/vip-tloc-pref-list/tloc-color
policyFromVsmartDataPolicyVpnListSeqActSetVipTlocPrLstTlocClr
                                                       OBJECT-TYPE
    SYNTAX      INTEGER {default(1),
                         mpls(2),
			 metro-ethernet(3),
			 biz-internet(4),
			 public-internet(5),
			 lte(6),
			 threeG(7),
			 red(8),
			 green(9),
			 blue(10),
			 gold(11),
			 silver(12),
			 bronze(13),
			 custom1(14),
			 custom2(15),
			 custom3(16),
			 private1(17),
			 private2(18),
			 private3(19),
			 private4(20),
			 private5(21),
			 private6(22)}
    MAX-ACCESS  read-only
    STATUS      current
    DESCRIPTION "Color"
  ::= { policyFromVsmartDataPolicyVpnListSeqActSetVipTlocPrLstEntry 4 }

-- tagpath /policy/from-vsmart/data-policy/vpn-list/sequence/action
-- /set/vip-tloc-pref-list/tloc-encap
policyFromVsmartDataPolicyVpnListSeqActSetVipTlocPrLstTlocEn OBJECT-TYPE
    SYNTAX      INTEGER {gre(1),ipsec(2)}
    MAX-ACCESS  read-only
    STATUS      current
    DESCRIPTION "Encapsulation"
  ::= { policyFromVsmartDataPolicyVpnListSeqActSetVipTlocPrLstEntry 5 }

-- tagpath /policy/from-vsmart/data-policy/vpn-list/sequence/action
-- /set/vip-tloc-pref-list/tloc-preference
policyFromVsmartDataPolicyVpnListSeqActSetVipTlocPrLstTlocPrf
                                                      OBJECT-TYPE
    SYNTAX      Unsigned32
    MAX-ACCESS  read-only
    STATUS      current
    DESCRIPTION "Preference"
  ::= { policyFromVsmartDataPolicyVpnListSeqActSetVipTlocPrLstEntry 6 }

-- tagpath /policy/from-vsmart/cflowd-template
policyFromVsmartCflowdTemplate OBJECT IDENTIFIER
    ::= { policyFromVsmart 7 }

-- tagpath /policy/from-vsmart/cflowd-template/name
policyFromVsmartCflowdTemplateName OBJECT-TYPE
    SYNTAX      String (SIZE (1 .. 127))
    MAX-ACCESS  read-only
    STATUS      current
    DESCRIPTION "Name of cflowd"
    ::= { policyFromVsmartCflowdTemplate 1 }

-- tagpath /policy/from-vsmart/cflowd-template/flow-active-timeout
policyFromVsmartCflowdTemplateFlowActiveTimeout OBJECT-TYPE
    SYNTAX      Unsigned32 (30 .. 3600)
    MAX-ACCESS  read-only
    STATUS      current
    DESCRIPTION "Timeout value for active flows"
    DEFVAL { 30 }
    ::= { policyFromVsmartCflowdTemplate 2 }

-- tagpath /policy/from-vsmart/cflowd-template/flow-inactive-timeout
policyFromVsmartCflowdTemplateFlowInactiveTimeout OBJECT-TYPE
    SYNTAX      Unsigned32 (1 .. 3600)
    MAX-ACCESS  read-only
    STATUS      current
    DESCRIPTION "Timeout value for inactive flows"
    DEFVAL { 30 }
    ::= { policyFromVsmartCflowdTemplate 3 }

-- tagpath /policy/from-vsmart/cflowd-template/template-refresh
policyFromVsmartCflowdTemplateTemplateRefresh OBJECT-TYPE
    SYNTAX      Unsigned32 (60 .. 86400)
    MAX-ACCESS  read-only
    STATUS      current
    DESCRIPTION "Refresh value for template"
    DEFVAL { 600 }
    ::= { policyFromVsmartCflowdTemplate 4 }

-- tagpath /policy/from-vsmart/cflowd-template/flow-sampling-interval
policyFromVsmartCflowdTemplateFlowSamplingInterval OBJECT-TYPE
    SYNTAX      Unsigned32 (1 .. 65536)
    MAX-ACCESS  read-only
    STATUS      current
    DESCRIPTION "Flow sampling interval"
    DEFVAL { 1024 }
    ::= { policyFromVsmartCflowdTemplate 5 }

-- tagpath /policy/from-vsmart/cflowd-template/protocol
policyFromVsmartCflowdTemplateProtocol OBJECT-TYPE
    SYNTAX      FnfMonitorEnum
    MAX-ACCESS  read-only
    STATUS      current
    DESCRIPTION "Traffic type for FNF"
    DEFVAL { ipv4 }
    ::= { policyFromVsmartCflowdTemplate 6 }

-- tagpath /policy/from-vsmart/cflowd-template/collector
policyFromVsmartCflowdTemplateCollectorTable OBJECT-TYPE
    SYNTAX      SEQUENCE OF PolicyFromVsmartCflowdTemplateCollectorEntry
    MAX-ACCESS  not-accessible
    STATUS      current
    DESCRIPTION "Cflowd collector"
    ::= { policyFromVsmart 8 }

-- tagpath /policy/from-vsmart/cflowd-template/collector
policyFromVsmartCflowdTemplateCollectorEntry OBJECT-TYPE
    SYNTAX      PolicyFromVsmartCflowdTemplateCollectorEntry
    MAX-ACCESS  not-accessible
    STATUS      current
    DESCRIPTION "Cflowd template collector"
    INDEX { policyFromVsmartCflowdTemplateCollectorVpn,
	    policyFromVsmartCflowdTemplateCollectorAddress,
	    policyFromVsmartCflowdTemplateCollectorPort,
	    policyFromVsmartCflowdTemplateCollectorTransport }
        ::= { policyFromVsmartCflowdTemplateCollectorTable 1 }

PolicyFromVsmartCflowdTemplateCollectorEntry ::=
    SEQUENCE {
        policyFromVsmartCflowdTemplateCollectorVpn Unsigned32,
        policyFromVsmartCflowdTemplateCollectorAddress InetAddressIP,
        policyFromVsmartCflowdTemplateCollectorPort UnsignedShort,
        policyFromVsmartCflowdTemplateCollectorTransport
	                                           TransportProtocol,
        policyFromVsmartCflowdTemplateCollectorSourceInterface String,
        policyFromVsmartCflowdTemplateCollectorExportSpreadEnable TruthValue,
        policyFromVsmartCflowdTemplateCollectorExportSpreadAppTables Unsigned32,
        policyFromVsmartCflowdTemplateCollectorExportSpreadTlocTables Unsigned32,
        policyFromVsmartCflowdTemplateCollectorExportSpreadOtherTables Unsigned32,
        policyFromVsmartCflowdTemplateCollectorBFDMetricsExport TruthValue,
        policyFromVsmartCflowdTemplateCollectorBFDExportInterval Unsigned32
    }

-- tagpath /policy/from-vsmart/cflowd-template/collector/vpn
policyFromVsmartCflowdTemplateCollectorVpn OBJECT-TYPE
    SYNTAX      Unsigned32 (0 .. 65531)
    MAX-ACCESS  not-accessible
    STATUS      current
    DESCRIPTION "VPN ID"
    ::= { policyFromVsmartCflowdTemplateCollectorEntry 1 }

-- tagpath /policy/from-vsmart/cflowd-template/collector/address
policyFromVsmartCflowdTemplateCollectorAddress OBJECT-TYPE
    SYNTAX      InetAddressIP
    MAX-ACCESS  not-accessible
    STATUS      current
    DESCRIPTION "IP address"
    ::= { policyFromVsmartCflowdTemplateCollectorEntry 2 }

-- tagpath /policy/from-vsmart/cflowd-template/collector/port
policyFromVsmartCflowdTemplateCollectorPort OBJECT-TYPE
    SYNTAX      UnsignedShort (1024 .. 65535)
    MAX-ACCESS  not-accessible
    STATUS      current
    DESCRIPTION "Port"
    ::= { policyFromVsmartCflowdTemplateCollectorEntry 3 }

-- tagpath /policy/from-vsmart/cflowd-template/collector/transport
policyFromVsmartCflowdTemplateCollectorTransport OBJECT-TYPE
    SYNTAX      TransportProtocol
    MAX-ACCESS  not-accessible
    STATUS      current
    DESCRIPTION "Transport Protocol type"
    ::= { policyFromVsmartCflowdTemplateCollectorEntry 4 }

-- tagpath /policy/from-vsmart/cflowd-template/collector
-- /source-interface
policyFromVsmartCflowdTemplateCollectorSourceInterface OBJECT-TYPE
    SYNTAX      String (SIZE (1 .. 32))
    MAX-ACCESS  read-only
    STATUS      current
    DESCRIPTION "IPFIX Source Interface"
    ::= { policyFromVsmartCflowdTemplateCollectorEntry 5 }

-- tagpath /policy/from-vsmart/cflowd-template/collector
-- /export-spread/enable
policyFromVsmartCflowdTemplateCollectorExportSpreadEnable OBJECT-TYPE
    SYNTAX      TruthValue
    MAX-ACCESS  read-only
    STATUS      current
    DESCRIPTION "Exporter Spreading enable"
    ::= { policyFromVsmartCflowdTemplateCollectorEntry 6 }

-- tagpath /policy/from-vsmart/cflowd-template/collector
-- /export-spread/app-tables
policyFromVsmartCflowdTemplateCollectorExportSpreadAppTables OBJECT-TYPE
    SYNTAX      Unsigned32 (0 .. 65535)
    MAX-ACCESS  read-only
    STATUS      current
    DESCRIPTION "Exporter Spreading application tables"
    ::= { policyFromVsmartCflowdTemplateCollectorEntry 7 }

-- tagpath /policy/from-vsmart/cflowd-template/collector
-- /export-spread/tloc-tables
policyFromVsmartCflowdTemplateCollectorExportSpreadTlocTables OBJECT-TYPE
    SYNTAX      Unsigned32 (0 .. 65535)
    MAX-ACCESS  read-only
    STATUS      current
    DESCRIPTION "Exporter Spreading application tables"
    ::= { policyFromVsmartCflowdTemplateCollectorEntry 8 }

-- tagpath /policy/from-vsmart/cflowd-template/collector
-- /export-spread/other-tables
policyFromVsmartCflowdTemplateCollectorExportSpreadOtherTables OBJECT-TYPE
    SYNTAX      Unsigned32 (0 .. 65535)
    MAX-ACCESS  read-only
    STATUS      current
    DESCRIPTION "Exporter Spreading application tables"
    ::= { policyFromVsmartCflowdTemplateCollectorEntry 9 }

-- tagpath /policy/from-vsmart/cflowd-template/collector
-- /bfd-metrics-export
policyFromVsmartCflowdTemplateCollectorBfdMetricsExport OBJECT-TYPE
    SYNTAX      TruthValue
    MAX-ACCESS  read-only
    STATUS      current
    DESCRIPTION "Export BFD Metrcis Settings"
    ::= { policyFromVsmartCflowdTemplateCollectorEntry 10 }

-- tagpath /policy/from-vsmart/cflowd-template/collector
-- /bfd-metrics-export/export-interval
policyFromVsmartCflowdTemplateCollectorBFDExportInterval OBJECT-TYPE
    SYNTAX      Unsigned32 (1 .. 86400)
    MAX-ACCESS  read-only
    STATUS      current
    DESCRIPTION "Export BFD Metrcis Interval"
    ::= { policyFromVsmartCflowdTemplateCollectorEntry 11 }

-- tagpath /policy/from-vsmart/app-route-policy
policyFromVsmartAppRoutePolicyTable OBJECT-TYPE
    SYNTAX      SEQUENCE OF PolicyFromVsmartAppRoutePolicyEntry
    MAX-ACCESS  not-accessible
    STATUS      current
    DESCRIPTION "Configure application-aware routing policy"
    ::= { policyFromVsmart 9 }

-- tagpath /policy/from-vsmart/app-route-policy
policyFromVsmartAppRoutePolicyEntry OBJECT-TYPE
    SYNTAX      PolicyFromVsmartAppRoutePolicyEntry
    MAX-ACCESS  not-accessible
    STATUS      current
    DESCRIPTION "App route policy"
    INDEX { IMPLIED policyFromVsmartAppRoutePolicyName }
        ::= { policyFromVsmartAppRoutePolicyTable 1 }

PolicyFromVsmartAppRoutePolicyEntry ::=
    SEQUENCE {
        policyFromVsmartAppRoutePolicyName String
    }

-- tagpath /policy/from-vsmart/app-route-policy/name
policyFromVsmartAppRoutePolicyName OBJECT-TYPE
    SYNTAX      String (SIZE (1 .. 127))
    MAX-ACCESS  read-only
    STATUS      current
    DESCRIPTION "Name of application-aware routing policy"
    ::= { policyFromVsmartAppRoutePolicyEntry 1 }

-- tagpath /policy/from-vsmart/app-route-policy/vpn-list
policyFromVsmartAppRoutePolicyVpnListTable OBJECT-TYPE
    SYNTAX      SEQUENCE OF PolicyFromVsmartAppRoutePolicyVpnListEntry
    MAX-ACCESS  not-accessible
    STATUS      current
    DESCRIPTION "Name of VPN list"
    ::= { policyFromVsmart 10 }

-- tagpath /policy/from-vsmart/app-route-policy/vpn-list
policyFromVsmartAppRoutePolicyVpnListEntry OBJECT-TYPE
    SYNTAX      PolicyFromVsmartAppRoutePolicyVpnListEntry
    MAX-ACCESS  not-accessible
    STATUS      current
    DESCRIPTION "App route policy vpn list"
    INDEX { policyFromVsmartAppRoutePolicyName,
            IMPLIED policyFromVsmartAppRoutePolicyVpnListName }
        ::= { policyFromVsmartAppRoutePolicyVpnListTable 1 }

PolicyFromVsmartAppRoutePolicyVpnListEntry ::=
    SEQUENCE {
        policyFromVsmartAppRoutePolicyVpnListName String,
        policyFromVsmartAppRoutePolicyVpnListDefActSlaClassName String
    }

-- tagpath /policy/from-vsmart/app-route-policy/vpn-list/name
policyFromVsmartAppRoutePolicyVpnListName OBJECT-TYPE
    SYNTAX      String (SIZE (1 .. 32))
    MAX-ACCESS  not-accessible
    STATUS      current
    DESCRIPTION "VPN list name"
    ::= { policyFromVsmartAppRoutePolicyVpnListEntry 1 }

-- tagpath /policy/from-vsmart/app-route-policy/vpn-list/default-action
-- /sla-class/sla-class-name
policyFromVsmartAppRoutePolicyVpnListDefActSlaClassName OBJECT-TYPE
    SYNTAX      String (SIZE (1 .. 32))
    MAX-ACCESS  read-only
    STATUS      current
    DESCRIPTION "VPN list default action sla class name"
    ::= { policyFromVsmartAppRoutePolicyVpnListEntry 13 }

-- tagpath /policy/from-vsmart/app-route-policy/vpn-list/sequence
policyFromVsmartAppRoutePolicyVpnListSequenceTable OBJECT-TYPE
    SYNTAX      SEQUENCE OF
             PolicyFromVsmartAppRoutePolicyVpnListSequenceEntry
    MAX-ACCESS  not-accessible
    STATUS      current
    DESCRIPTION "List of sequences"
    ::= { policyFromVsmart 11 }

-- tagpath /policy/from-vsmart/app-route-policy/vpn-list/sequence
policyFromVsmartAppRoutePolicyVpnListSequenceEntry OBJECT-TYPE
    SYNTAX      PolicyFromVsmartAppRoutePolicyVpnListSequenceEntry
    MAX-ACCESS  not-accessible
    STATUS      current
    DESCRIPTION "App route policy vpn list sequence"
    INDEX { policyFromVsmartAppRoutePolicyName,
            policyFromVsmartAppRoutePolicyVpnListName,
	    policyFromVsmartAppRoutePolicyVpnListSequenceSeqValue }
        ::= { policyFromVsmartAppRoutePolicyVpnListSequenceTable 1 }

PolicyFromVsmartAppRoutePolicyVpnListSequenceEntry ::=
    SEQUENCE {
        policyFromVsmartAppRoutePolicyVpnListSequenceSeqValue
	                                            UnsignedShort,
        policyFromVsmartAppRoutePolicyVpnListSequenceMatchSrcDtPrLst
	                                            String,
        policyFromVsmartAppRoutePolicyVpnListSequenceMatchSrcDtV6PrLst
	                                            String,
        policyFromVsmartAppRoutePolicyVpnListSequenceMatchDestDtPrLst
	                                            String,
        policyFromVsmartAppRoutePolicyVpnListSequenceMatchDestDtV6PrLst
	                                            String,
        policyFromVsmartAppRoutePolicyVpnListSequenceActionCount
                                                    String,
        policyFromVsmartAppRoutePolicyVpnListSequenceActionSlaClName
                                                    String,
        policyFromVsmartAppRoutePolicyVpnListSequenceActionSlaClStrict
	                                            TruthValue,
        policyFromVsmartAppRoutePolicyVpnListSequenceActionSlaClPrefClr
                                                    ColorList,
        policyFromVsmartAppRoutePolicyVpnListSequenceActionLog
	                                            TruthValue,
        policyFromVsmartAppRoutePolicyVpnListSeqActBackupSlaPrefClr
                                                    ColorList,
        policyFromVsmartAppRoutePolicyVpnListSequenceActionSlaClFallback
	                                            TruthValue
    }

-- tagpath /policy/from-vsmart/app-route-policy/vpn-list/sequence
-- /seq-value
policyFromVsmartAppRoutePolicyVpnListSequenceSeqValue OBJECT-TYPE
    SYNTAX      UnsignedShort (1 .. 65530)
    MAX-ACCESS  not-accessible
    STATUS      current
    DESCRIPTION "Sequence value"
    ::= { policyFromVsmartAppRoutePolicyVpnListSequenceEntry 1 }

-- tagpath /policy/from-vsmart/app-route-policy/vpn-list/sequence/match
-- /source-data-prefix-list
policyFromVsmartAppRoutePolicyVpnListSequenceMatchSrcDtPrLst OBJECT-TYPE
    SYNTAX      String (SIZE (1 .. 32))
    MAX-ACCESS  read-only
    STATUS      current
    DESCRIPTION "Source prefix list"
    ::= { policyFromVsmartAppRoutePolicyVpnListSequenceEntry 4 }

-- tagpath /policy/from-vsmart/app-route-policy/vpn-list/sequence/match
-- /source-data-ipv6-prefix-list
policyFromVsmartAppRoutePolicyVpnListSequenceMatchSrcDtV6PrLst
                                                        OBJECT-TYPE
    SYNTAX      String (SIZE (1 .. 32))
    MAX-ACCESS  read-only
    STATUS      current
    DESCRIPTION "Source prefix IPv6 list"
    ::= { policyFromVsmartAppRoutePolicyVpnListSequenceEntry 5 }

-- tagpath /policy/from-vsmart/app-route-policy/vpn-list/sequence/match
-- /destination-data-prefix-list
policyFromVsmartAppRoutePolicyVpnListSequenceMatchDestDtPrLst
                                                       OBJECT-TYPE
    SYNTAX      String (SIZE (1 .. 32))
    MAX-ACCESS  read-only
    STATUS      current
    DESCRIPTION "Destination prefix list"
    ::= { policyFromVsmartAppRoutePolicyVpnListSequenceEntry 7 }

-- tagpath /policy/from-vsmart/app-route-policy/vpn-list/sequence/match
-- /destination-data-ipv6-prefix-list
policyFromVsmartAppRoutePolicyVpnListSequenceMatchDestDtV6PrLst
                                                        OBJECT-TYPE
    SYNTAX      String (SIZE (1 .. 32))
    MAX-ACCESS  read-only
    STATUS      current
    DESCRIPTION "Destination prefix Ipv6 list"
    ::= { policyFromVsmartAppRoutePolicyVpnListSequenceEntry 8 }

-- tagpath /policy/from-vsmart/app-route-policy/vpn-list/sequence
-- /action/count
policyFromVsmartAppRoutePolicyVpnListSequenceActionCount OBJECT-TYPE
    SYNTAX      String (SIZE (1 .. 32))
    MAX-ACCESS  read-only
    STATUS      current
    DESCRIPTION "Count packets/bytes matching this rule"
    ::= { policyFromVsmartAppRoutePolicyVpnListSequenceEntry 10 }

-- tagpath /policy/from-vsmart/app-route-policy/vpn-list/sequence
-- /action/sla-class/sla-class-name
policyFromVsmartAppRoutePolicyVpnListSequenceActionSlaClName OBJECT-TYPE
    SYNTAX      String (SIZE (1 .. 32))
    MAX-ACCESS  read-only
    STATUS      current
    DESCRIPTION "SLA class name"
    ::= { policyFromVsmartAppRoutePolicyVpnListSequenceEntry 11 }

-- tagpath /policy/from-vsmart/app-route-policy/vpn-list/sequence
-- /action/sla-class/strict
policyFromVsmartAppRoutePolicyVpnListSequenceActionSlaClStrict
                                                         OBJECT-TYPE
    SYNTAX      TruthValue
    MAX-ACCESS  read-only
    STATUS      current
    DESCRIPTION "Drop traffic if preferred SLA class is unavailable"
    ::= { policyFromVsmartAppRoutePolicyVpnListSequenceEntry 12 }

-- tagpath /policy/from-vsmart/app-route-policy/vpn-list/sequence
-- /action/sla-class/preferred-color
policyFromVsmartAppRoutePolicyVpnListSequenceActionSlaClPrefClr 
                                                       OBJECT-TYPE
    SYNTAX      ColorList
    MAX-ACCESS  not-accessible
    STATUS      current
    DESCRIPTION "List of preferred colors when SLA is met"
    ::= { policyFromVsmartAppRoutePolicyVpnListSequenceEntry 14 }

-- tagpath /policy/from-vsmart/app-route-policy/vpn-list/sequence
-- /action/log
policyFromVsmartAppRoutePolicyVpnListSequenceActionLog OBJECT-TYPE
    SYNTAX      TruthValue
    MAX-ACCESS  read-only
    STATUS      current
    DESCRIPTION "Syslog a sampled set of packets matching this rule
                 with SLA-class information"
    ::= { policyFromVsmartAppRoutePolicyVpnListSequenceEntry 15 }

-- tagpath /policy/from-vsmart/app-route-policy/vpn-list/sequence
-- /action/sla-class/backup-preferred-color
policyFromVsmartAppRoutePolicyVpnListSeqActBackupSlaPrefClr OBJECT-TYPE
    SYNTAX      ColorList
    MAX-ACCESS  not-accessible
    STATUS      current
    DESCRIPTION "List of preferred colors for ECMP 
                 when primary SLA is not met"
    ::= { policyFromVsmartAppRoutePolicyVpnListSequenceEntry 16 }

-- tagpath /policy/from-vsmart/app-route-policy/vpn-list/sequence
-- /action/sla-class/fallback-to-best-path
policyFromVsmartAppRoutePolicyVpnListSequenceActionSlaClFallback
                                                        OBJECT-TYPE
    SYNTAX      TruthValue
    MAX-ACCESS  read-only
    STATUS      current
    DESCRIPTION "Fallback to best path when SLA is not met"
    ::= { policyFromVsmartAppRoutePolicyVpnListSequenceEntry 17 }

-- tagpath /policy/from-vsmart/policer
policyFromVsmartPolicerTable OBJECT-TYPE
    SYNTAX      SEQUENCE OF PolicyFromVsmartPolicerEntry
    MAX-ACCESS  not-accessible
    STATUS      current
    DESCRIPTION "Configure policer"
    ::= { policyFromVsmart 12 }

-- tagpath /policy/from-vsmart/policer
policyFromVsmartPolicerEntry OBJECT-TYPE
    SYNTAX      PolicyFromVsmartPolicerEntry
    MAX-ACCESS  not-accessible
    STATUS      current
    DESCRIPTION "Policer"
    INDEX { IMPLIED policyFromVsmartPolicerName }
        ::= { policyFromVsmartPolicerTable 1 }

PolicyFromVsmartPolicerEntry ::=
    SEQUENCE {
        policyFromVsmartPolicerName String,
        policyFromVsmartPolicerRate Counter64,
        policyFromVsmartPolicerBurst Unsigned32,
        policyFromVsmartPolicerExceed INTEGER
    }

-- tagpath /policy/from-vsmart/policer/name
policyFromVsmartPolicerName OBJECT-TYPE
    SYNTAX      String (SIZE (1 .. 32))
    MAX-ACCESS  not-accessible
    STATUS      current
    DESCRIPTION "Name of policer"
    ::= { policyFromVsmartPolicerEntry 1 }

-- tagpath /policy/from-vsmart/policer/rate
policyFromVsmartPolicerRate OBJECT-TYPE
    SYNTAX      Counter64
    MAX-ACCESS  read-only
    STATUS      current
    DESCRIPTION "Bandwidth for 1g interfaces: <8..1000000000>bps;
  for 10g interfaces: <8..10000000000>bps"
    ::= { policyFromVsmartPolicerEntry 2 }

-- tagpath /policy/from-vsmart/policer/burst
policyFromVsmartPolicerBurst OBJECT-TYPE
    SYNTAX      Unsigned32 (15000 .. 10000000)
    MAX-ACCESS  read-only
    STATUS      current
    DESCRIPTION "Burst rate, in bytes"
    ::= { policyFromVsmartPolicerEntry 3 }

-- tagpath /policy/from-vsmart/policer/exceed
policyFromVsmartPolicerExceed OBJECT-TYPE
    SYNTAX      INTEGER {drop(0),
                         remark(1)}
    MAX-ACCESS  read-only
    STATUS      current
    DESCRIPTION "Action for nonconforming packets"
    ::= { policyFromVsmartPolicerEntry 4 }

-- tagpath /policy/from-vsmart/lists/vpn-list
policyFromVsmartListsVpnListTable OBJECT-TYPE
    SYNTAX      SEQUENCE OF PolicyFromVsmartListsVpnListEntry
    MAX-ACCESS  not-accessible
    STATUS      current
    DESCRIPTION "List of VPN IDs"
    ::= { policyFromVsmart 13 }

-- tagpath /policy/from-vsmart/lists/vpn-list
policyFromVsmartListsVpnListEntry OBJECT-TYPE
    SYNTAX      PolicyFromVsmartListsVpnListEntry
    MAX-ACCESS  not-accessible
    STATUS      current
    DESCRIPTION "policy from vsmart vpn list entry"
    INDEX { IMPLIED policyFromVsmartListsVpnListName }
        ::= { policyFromVsmartListsVpnListTable 1 }

PolicyFromVsmartListsVpnListEntry ::=
    SEQUENCE {
        policyFromVsmartListsVpnListName String
    }

-- tagpath /policy/from-vsmart/lists/vpn-list/name
policyFromVsmartListsVpnListName OBJECT-TYPE
    SYNTAX      String (SIZE (1 .. 32))
    MAX-ACCESS  read-only
    STATUS      current
    DESCRIPTION "Name of VPN list"
    ::= { policyFromVsmartListsVpnListEntry 1 }

-- tagpath /policy/from-vsmart/lists/vpn-list/vpn
policyFromVsmartListsVpnListVpnTable OBJECT-TYPE
    SYNTAX      SEQUENCE OF PolicyFromVsmartListsVpnListVpnEntry
    MAX-ACCESS  not-accessible
    STATUS      current
    DESCRIPTION "VPN ID"
    ::= { policyFromVsmart 14 }

-- tagpath /policy/from-vsmart/lists/vpn-list/vpn
policyFromVsmartListsVpnListVpnEntry OBJECT-TYPE
    SYNTAX      PolicyFromVsmartListsVpnListVpnEntry
    MAX-ACCESS  not-accessible
    STATUS      current
    DESCRIPTION "policy from vsmart lists of vpn list vpn entry"
    INDEX { policyFromVsmartListsVpnListName,
           IMPLIED policyFromVsmartListsVpnListVpnId }
        ::= { policyFromVsmartListsVpnListVpnTable 1 }

PolicyFromVsmartListsVpnListVpnEntry ::=
    SEQUENCE {
        policyFromVsmartListsVpnListVpnId String
    }

-- tagpath /policy/from-vsmart/lists/vpn-list/vpn/id
policyFromVsmartListsVpnListVpnId OBJECT-TYPE
    SYNTAX      String (SIZE (1 .. 32))
    MAX-ACCESS  read-only
    STATUS      current
    DESCRIPTION "policy from vsmart lists of vpn list of vpn id"
    ::= { policyFromVsmartListsVpnListVpnEntry 1 }

-- tagpath /policy/from-vsmart/lists/data-prefix-list
policyFromVsmartListsDataPrefixListTable OBJECT-TYPE
    SYNTAX      SEQUENCE OF PolicyFromVsmartListsDataPrefixListEntry
    MAX-ACCESS  not-accessible
    STATUS      current
    DESCRIPTION "List of prefixes"
    ::= { policyFromVsmart 15 }

-- tagpath /policy/from-vsmart/lists/data-prefix-list
policyFromVsmartListsDataPrefixListEntry OBJECT-TYPE
    SYNTAX      PolicyFromVsmartListsDataPrefixListEntry
    MAX-ACCESS  not-accessible
    STATUS      current
    DESCRIPTION "List of prefix table entry"
    INDEX { IMPLIED policyFromVsmartListsDataPrefixListName }
        ::= { policyFromVsmartListsDataPrefixListTable 1 }

PolicyFromVsmartListsDataPrefixListEntry ::=
    SEQUENCE {
        policyFromVsmartListsDataPrefixListName String
    }

-- tagpath /policy/from-vsmart/lists/data-prefix-list/name
policyFromVsmartListsDataPrefixListName OBJECT-TYPE
    SYNTAX      String (SIZE (1 .. 32))
    MAX-ACCESS  read-only
    STATUS      current
    DESCRIPTION "Name of prefix list"
    ::= { policyFromVsmartListsDataPrefixListEntry 1 }

-- tagpath /policy/from-vsmart/lists/data-prefix-list/ip-prefix
policyFromVsmartListsDataPrefixListIpPrefixTable OBJECT-TYPE
    SYNTAX      SEQUENCE OF
                PolicyFromVsmartListsDataPrefixListIpPrefixEntry
    MAX-ACCESS  not-accessible
    STATUS      current
    DESCRIPTION "Prefix"
    ::= { policyFromVsmart 16 }

-- tagpath /policy/from-vsmart/lists/data-prefix-list/ip-prefix
policyFromVsmartListsDataPrefixListIpPrefixEntry OBJECT-TYPE
    SYNTAX      PolicyFromVsmartListsDataPrefixListIpPrefixEntry
    MAX-ACCESS  not-accessible
    STATUS      current
    DESCRIPTION "Prefix entry"
    INDEX { policyFromVsmartListsDataPrefixListName,
            policyFromVsmartListsDataPrefixListIpPrefixIp }
        ::= { policyFromVsmartListsDataPrefixListIpPrefixTable 1 }

PolicyFromVsmartListsDataPrefixListIpPrefixEntry ::=
    SEQUENCE {
        policyFromVsmartListsDataPrefixListIpPrefixIp Ipv4Prefix
    }

-- tagpath /policy/from-vsmart/lists/data-prefix-list/ip-prefix/ip
policyFromVsmartListsDataPrefixListIpPrefixIp OBJECT-TYPE
    SYNTAX      Ipv4Prefix
    MAX-ACCESS  read-only
    STATUS      current
    DESCRIPTION "Prefix ip"
    ::= { policyFromVsmartListsDataPrefixListIpPrefixEntry 1 }

-- tagpath /policy/from-vsmart/lists/tloc-list
policyFromVsmartListsTlocListTable OBJECT-TYPE
    SYNTAX      SEQUENCE OF PolicyFromVsmartListsTlocListEntry
    MAX-ACCESS  not-accessible
    STATUS      current
    DESCRIPTION "List of TLOCs"
    ::= { policyFromVsmart 17 }

-- tagpath /policy/from-vsmart/lists/tloc-list
policyFromVsmartListsTlocListEntry OBJECT-TYPE
    SYNTAX      PolicyFromVsmartListsTlocListEntry
    MAX-ACCESS  not-accessible
    STATUS      current
    DESCRIPTION "policy from vsmart lists of tloc list entry"
    INDEX { IMPLIED policyFromVsmartListsTlocListName }
        ::= { policyFromVsmartListsTlocListTable 1 }

PolicyFromVsmartListsTlocListEntry ::=
    SEQUENCE {
        policyFromVsmartListsTlocListName String
    }

-- tagpath /policy/from-vsmart/lists/tloc-list/name
policyFromVsmartListsTlocListName OBJECT-TYPE
    SYNTAX      String (SIZE (1 .. 32))
    MAX-ACCESS  read-only
    STATUS      current
    DESCRIPTION "Name of TLOC list"
    ::= { policyFromVsmartListsTlocListEntry 1 }

-- tagpath /policy/from-vsmart/lists/tloc-list/tloc
policyFromVsmartListsTlocListTlocTable OBJECT-TYPE
    SYNTAX      SEQUENCE OF PolicyFromVsmartListsTlocListTlocEntry
    MAX-ACCESS  not-accessible
    STATUS      current
    DESCRIPTION "Transport location"
    ::= { policyFromVsmart 18 }

-- tagpath /policy/from-vsmart/lists/tloc-list/tloc
policyFromVsmartListsTlocListTlocEntry OBJECT-TYPE
    SYNTAX      PolicyFromVsmartListsTlocListTlocEntry
    MAX-ACCESS  not-accessible
    STATUS      current
    DESCRIPTION "policy from vsmart lists of tloc list of tloc entry"
    INDEX { policyFromVsmartListsTlocListName,
            policyFromVsmartListsTlocListTlocIp,
	    policyFromVsmartListsTlocListTlocColor,
	    policyFromVsmartListsTlocListTlocEncap }
        ::= { policyFromVsmartListsTlocListTlocTable 1 }

PolicyFromVsmartListsTlocListTlocEntry ::=
    SEQUENCE {
        policyFromVsmartListsTlocListTlocIp InetAddressIP,
        policyFromVsmartListsTlocListTlocColor INTEGER,
        policyFromVsmartListsTlocListTlocEncap INTEGER,
        policyFromVsmartListsTlocListTlocPreference Unsigned32
    }

-- tagpath /policy/from-vsmart/lists/tloc-list/tloc/ip
policyFromVsmartListsTlocListTlocIp OBJECT-TYPE
    SYNTAX      InetAddressIP
    MAX-ACCESS  not-accessible
    STATUS      current
    DESCRIPTION "IP address"
    ::= { policyFromVsmartListsTlocListTlocEntry 1 }

-- tagpath /policy/from-vsmart/lists/tloc-list/tloc/color
policyFromVsmartListsTlocListTlocColor OBJECT-TYPE
    SYNTAX      INTEGER {default(1),
                         mpls(2),
			 metro-ethernet(3),
			 biz-internet(4),
			 public-internet(5),
			 lte(6),
			 threeG(7),
			 red(8),
			 green(9),
			 blue(10),
			 gold(11),
			 silver(12),
			 bronze(13),
			 custom1(14),
			 custom2(15),
			 custom3(16),
			 private1(17),
			 private2(18),
			 private3(19),
			 private4(20),
			 private5(21),
			 private6(22)}
    MAX-ACCESS  not-accessible
    STATUS      current
    DESCRIPTION "Color"
    ::= { policyFromVsmartListsTlocListTlocEntry 2 }

-- tagpath /policy/from-vsmart/lists/tloc-list/tloc/encap
policyFromVsmartListsTlocListTlocEncap OBJECT-TYPE
    SYNTAX      INTEGER {gre(1),ipsec(2)}
    MAX-ACCESS  not-accessible
    STATUS      current
    DESCRIPTION "Encapsulation"
    ::= { policyFromVsmartListsTlocListTlocEntry 3 }

-- tagpath /policy/from-vsmart/lists/tloc-list/tloc/preference
policyFromVsmartListsTlocListTlocPreference OBJECT-TYPE
    SYNTAX      Unsigned32
    MAX-ACCESS  read-only
    STATUS      current
    DESCRIPTION "Route preference"
    ::= { policyFromVsmartListsTlocListTlocEntry 4 }

-- tagpath /policy/from-vsmart/lists/app-probe-class
policyFromVsmartListsAppProbeClassListTable OBJECT-TYPE
    SYNTAX      SEQUENCE OF PolicyFromVsmartListsAppProbeClassListEntry
    MAX-ACCESS  not-accessible
    STATUS      current
    DESCRIPTION "List of App Probe Classes"
    ::= { policyFromVsmart 21 }

-- tagpath /policy/from-vsmart/lists/app-probe-class
policyFromVsmartListsAppProbeClassListEntry OBJECT-TYPE
    SYNTAX      PolicyFromVsmartListsAppProbeClassListEntry
    MAX-ACCESS  not-accessible
    STATUS      current
    DESCRIPTION "policy from vsmart lists of app probe class list entry"
    INDEX { IMPLIED policyFromVsmartListsAppProbeClassListName }
    ::= { policyFromVsmartListsAppProbeClassListTable 1 }

    PolicyFromVsmartListsAppProbeClassListEntry ::=
    SEQUENCE {
        policyFromVsmartListsAppProbeClassListName String,
        policyFromVsmartListsAppProbeClassListForwardingClass String
    }

-- tagpath /policy/from-vsmart/lists/app-probe-class/name
policyFromVsmartListsAppProbeClassListName OBJECT-TYPE
    SYNTAX      String (SIZE (1 .. 32))
    MAX-ACCESS  not-accessible
    STATUS      current
    DESCRIPTION "Name of app probe class list"
    ::= { policyFromVsmartListsAppProbeClassListEntry 1 }

-- tagpath /policy/from-vsmart/lists/app-probe-class/forwarding-class
policyFromVsmartListsAppProbeClassListForwardingClass OBJECT-TYPE
    SYNTAX      String (SIZE (1 .. 32))
    MAX-ACCESS  read-only
    STATUS      current
    DESCRIPTION "Name of forwarding class list"
    ::= { policyFromVsmartListsAppProbeClassListEntry 2 }

-- tagpath /policy/from-vsmart/lists/app-probe-class/color
policyFromVsmartListsAppProbeClassColorTable OBJECT-TYPE
    SYNTAX      SEQUENCE OF PolicyFromVsmartListsAppProbeClassColorEntry
    MAX-ACCESS  not-accessible
    STATUS      current
    DESCRIPTION "Color"
    ::= { policyFromVsmart 22 }

-- tagpath /policy/from-vsmart/lists/app-probe-class/color
policyFromVsmartListsAppProbeClassColorEntry OBJECT-TYPE
    SYNTAX      PolicyFromVsmartListsAppProbeClassColorEntry
    MAX-ACCESS  not-accessible
    STATUS      current
    DESCRIPTION "policy from vsmart lists of
                 app probe class of color entry"
    INDEX {policyFromVsmartListsAppProbeClassListName,
           policyFromVsmartListsAppProbeClassColorName}
    ::= { policyFromVsmartListsAppProbeClassColorTable 1 }

PolicyFromVsmartListsAppProbeClassColorEntry ::=
    SEQUENCE {
        policyFromVsmartListsAppProbeClassColorName INTEGER,
	policyFromVsmartListsAppProbeClassColorDscp Unsigned32
    }

-- tagpath /policy/from-vsmart/lists/app-probe-class/color/color-name
policyFromVsmartListsAppProbeClassColorName OBJECT-TYPE
    SYNTAX	INTEGER {default(1),
                         mpls(2),
			 metro-ethernet(3),
			 biz-internet(4),
			 public-internet(5),
			 lte(6),
			 threeG(7),
			 red(8),
			 green(9),
			 blue(10),
			 gold(11),
			 silver(12),
			 bronze(13),
			 custom1(14),
			 custom2(15),
			 custom3(16),
			 private1(17),
			 private2(18),
			 private3(19),
			 private4(20),
			 private5(21),
			 private6(22)}
    MAX-ACCESS  not-accessible
    STATUS      current
    DESCRIPTION "policy from vsmart lists of
                 app probe class of color name"
    ::= { policyFromVsmartListsAppProbeClassColorEntry 1 }

-- tagpath /policy/from-vsmart/lists/app-probe-class/color/dscp
policyFromVsmartListsAppProbeClassColorDscp OBJECT-TYPE
    SYNTAX      Unsigned32 (0 .. 63)
    MAX-ACCESS  read-only
    STATUS      current
    DESCRIPTION "policy from vsmart lists of
                 app probe class of colo dscp"
    ::= { policyFromVsmartListsAppProbeClassColorEntry 2 }

-- ********************************************************************
-- *  Notification Objects
-- ********************************************************************

netconfNotificationSeverity OBJECT-TYPE
    SYNTAX      NotificationSeverity
    MAX-ACCESS  read-only
    STATUS      current
    DESCRIPTION "Netconf notification severity level"
    ::= { ciscoSdwanPolicyMIBNotifObjects 2 }

ciscoSdwanPolicyVpnId OBJECT-TYPE
    SYNTAX      VpnId
    MAX-ACCESS  read-only
    STATUS      current
    DESCRIPTION "VPN id"
    ::= { ciscoSdwanPolicyMIBNotifObjects 3 }

ciscoSdwanPolicyApplication OBJECT-TYPE
    SYNTAX      OCTET STRING
    MAX-ACCESS  read-only
    STATUS      current
    DESCRIPTION "Policy application"
    ::= { ciscoSdwanPolicyMIBNotifObjects 4 }

ciscoSdwanPolicySourceIp OBJECT-TYPE
    SYNTAX      SourceIp
    MAX-ACCESS  read-only
    STATUS      current
    DESCRIPTION "Source ip"
    ::= { ciscoSdwanPolicyMIBNotifObjects 5 }

ciscoSdwanPolicySourcePort OBJECT-TYPE
    SYNTAX      Unsigned32
    MAX-ACCESS  read-only
    STATUS      current
    DESCRIPTION "Source port"
    ::= { ciscoSdwanPolicyMIBNotifObjects 6 }

ciscoSdwanPolicyDestinationIp OBJECT-TYPE
    SYNTAX      DestinationIp
    MAX-ACCESS  read-only
    STATUS      current
    DESCRIPTION "Destination ip"
    ::= { ciscoSdwanPolicyMIBNotifObjects 7 }

ciscoSdwanPolicyDestinationPort OBJECT-TYPE
    SYNTAX      Unsigned32
    MAX-ACCESS  read-only
    STATUS      current
    DESCRIPTION "Destination port"
    ::= { ciscoSdwanPolicyMIBNotifObjects 8 }

ciscoSdwanPolicyProtocol OBJECT-TYPE
    SYNTAX      Unsigned32
    MAX-ACCESS  read-only
    STATUS      current
    DESCRIPTION "Protocol"
    ::= { ciscoSdwanPolicyMIBNotifObjects 9 }

ciscoSdwanPolicyDscp OBJECT-TYPE
    SYNTAX      Unsigned32
    MAX-ACCESS  read-only
    STATUS      current
    DESCRIPTION "DSCP"
    ::= { ciscoSdwanPolicyMIBNotifObjects 10 }

ciscoSdwanPolicySlaInformation OBJECT-TYPE
    SYNTAX      OCTET STRING
    MAX-ACCESS  read-only
    STATUS      current
    DESCRIPTION "SLA information"
    ::= { ciscoSdwanPolicyMIBNotifObjects 11 }

ciscoSdwanPolicySlaStatus OBJECT-TYPE
    SYNTAX      OCTET STRING
    MAX-ACCESS  read-only
    STATUS      current
    DESCRIPTION "SLA status"
    ::= { ciscoSdwanPolicyMIBNotifObjects 12 }

ciscoSdwanPolicyVpnListName OBJECT-TYPE
    SYNTAX      OCTET STRING
    MAX-ACCESS  read-only
    STATUS      current
    DESCRIPTION "VPN list name"
    ::= { ciscoSdwanPolicyMIBNotifObjects 13 }

ciscoSdwanPolicyName OBJECT-TYPE
    SYNTAX      OCTET STRING
    MAX-ACCESS  read-only
    STATUS      current
    DESCRIPTION "Policy name"
    ::= { ciscoSdwanPolicyMIBNotifObjects 14 }

ciscoSdwanPolicyAccessListName OBJECT-TYPE
    SYNTAX      OCTET STRING
    MAX-ACCESS  read-only
    STATUS      current
    DESCRIPTION "ACL name"
    ::= { ciscoSdwanPolicyMIBNotifObjects 15 }

ciscoSdwanPolicyStatus OBJECT-TYPE
    SYNTAX      OCTET STRING
    MAX-ACCESS  read-only
    STATUS      current
    DESCRIPTION "Policy status"
    ::= { ciscoSdwanPolicyMIBNotifObjects 16 }

-- ********************************************************************
-- *  Notifications
-- ********************************************************************

ciscoSdwanPolicySlaViolation NOTIFICATION-TYPE
    OBJECTS {
        netconfNotificationSeverity,
        ciscoSdwanPolicyVpnId,
        ciscoSdwanPolicyApplication,
        ciscoSdwanPolicySourceIp,
        ciscoSdwanPolicySourcePort,
        ciscoSdwanPolicyDestinationIp,
        ciscoSdwanPolicyDestinationPort,
        ciscoSdwanPolicyProtocol,
        ciscoSdwanPolicyDscp,
        ciscoSdwanPolicySlaInformation,
        ciscoSdwanPolicySlaStatus
    }
    STATUS current
    DESCRIPTION "Cisco SDWAN trap from policy"
    ::= { ciscoSdwanPolicyMIBNotifs 1 }

ciscoSdwanPolicySlaViolationPktDrop NOTIFICATION-TYPE
    OBJECTS {
        netconfNotificationSeverity,
        ciscoSdwanPolicyVpnId,
        ciscoSdwanPolicyApplication,
        ciscoSdwanPolicySourceIp,
        ciscoSdwanPolicySourcePort,
        ciscoSdwanPolicyDestinationIp,
        ciscoSdwanPolicyDestinationPort,
        ciscoSdwanPolicyProtocol,
        ciscoSdwanPolicyDscp,
        ciscoSdwanPolicySlaInformation,
        ciscoSdwanPolicySlaStatus
    }
    STATUS current
    DESCRIPTION "Cisco SDWAN trap from policy"
    ::= { ciscoSdwanPolicyMIBNotifs 2 }

ciscoSdwanPolicyDataPolicyAssociationStatus NOTIFICATION-TYPE
    OBJECTS {
        netconfNotificationSeverity,
        ciscoSdwanPolicyVpnListName,
        ciscoSdwanPolicyName,
        ciscoSdwanPolicyStatus
    }
    STATUS current
    DESCRIPTION "Cisco SDWAN trap from policy"
    ::= { ciscoSdwanPolicyMIBNotifs 3 }

ciscoSdwanPolicyAccessListAssociationStatus NOTIFICATION-TYPE
    OBJECTS {
        netconfNotificationSeverity,
        ciscoSdwanPolicyAccessListName,
        ciscoSdwanPolicyStatus
    }
    STATUS current
    DESCRIPTION "Cisco SDWAN trap from policyy"
    ::= { ciscoSdwanPolicyMIBNotifs 4 }

-- ********************************************************************
-- *    Compliance statements
-- ********************************************************************

ciscoSdwanPolicyMIBCompliances OBJECT IDENTIFIER
    ::= { ciscoSdwanPolicyMIBConform 1 }

ciscoSdwanPolicyMIBGroups OBJECT IDENTIFIER
    ::= { ciscoSdwanPolicyMIBConform 2 }

ciscoSdwanPolicyMIBCompliance MODULE-COMPLIANCE
    STATUS            current
    DESCRIPTION
        "The compliance statement for the SNMP entities
         that implement the ciscoSdwanPolicyMIB module."
    MODULE          -- this module
    MANDATORY-GROUPS {
     cSdwanPolicyDataPolicyFilterGroup,
     cSdwanPolicyDataPolicyFilterVpnlistGroup,
     cSdwanPolicyDataPolicyFilterVpnlistCounterGroup,
     cSdwanPolicyDataPolicyFilterVpnlistPolicerGroup,
     cSdwanPolicyAppRoutePolicyFilterGroup,
     cSdwanPolicyAppRoutePolicyFilterVpnlistGroup,
     cSdwanPolicyAppRoutePolicyFilterVpnlistCounterGroup,
     cSdwanPolicyAccessListNamesGroup,
     cSdwanPolicyAccessListCountersGroup,
     cSdwanPolicyAccessListCountersAccessPolicyCounterListGroup,
     cSdwanPolicyAccessListPolicersGroup,
     cSdwanPolicyAccessListPolicersAccessPolicyPolicerListGroup,
     cSdwanPolicyAccessListAssociationsGroup,
     cSdwanPolicyAccessListAssociationsAccessPolicyInterfaceListGroup,
     cSdwanPolicyRewriteAssociationsGroup,
     cSdwanPolicyRewriteAssociationsRewriteInterfaceListGroup,
     cSdwanPolicyFromVsmartSlaClassGroup,
     cSdwanPolicyFromVsmartListsVpnListGroup,
     cSdwanPolicyFromVsmartListsVpnListVpnGroup,
     cSdwanPolicyFromVsmartListsDataPrefixListGroup,
     cSdwanPolicyFromVsmartListsDataPrefixListIpPrefixGroup,
     cSdwanPolicyFromVsmartListsTlocListGroup,
     cSdwanPolicyFromVsmartListsTlocListTlocGroup,
     cSdwanPolicyFromVsmartListsAppProbeClassListGroup,
     cSdwanPolicyFromVsmartListsAppProbeClassColorGroup,
     cSdwanPolicyNotifObjsGroup,
     cSdwanPolicyNotifsGroup,
     cSdwanPolicyFromVsmartDataPolicyGroup,
     cSdwanPolicyFromVsmartDataPolicyVpnListGroup,
     cSdwanPolicyFromVsmartDataPolicyVpnListSequenceGroup,
     cSdwanpolicyFromVsmartDataPolVpnListSeqActSetVipTlocPrLstGroup,
     cSdwanPolicyFromVsmartCflowdTemplateGroup,
     cSdwanPolicyFromVsmartCflowdTemplateCollectorGroup,
     cSdwanPolicyFromVsmartAppRoutePolicyGroup,
     cSdwanPolicyFromVsmartAppRoutePolicyVpnListGroup,
     cSdwanPolicyFromVsmartAppRoutePolicyVpnListSequenceGroup,
     cSdwanPolicyFromVsmartPolicerGroup
    }
    ::= { ciscoSdwanPolicyMIBCompliances 1 }

-- ********************************************************************
-- *    Units of conformance
-- ********************************************************************

cSdwanPolicyDataPolicyFilterGroup OBJECT-GROUP
    OBJECTS          {
                         policyDataPolicyFilterName
                     }
    STATUS           current
    DESCRIPTION
        "This is a collection of object of data policy filter."
    ::= { ciscoSdwanPolicyMIBGroups 1 }

cSdwanPolicyDataPolicyFilterVpnlistGroup OBJECT-GROUP
    OBJECTS          {
                         policyDataPolicyFilterVpnlistName
                     }
    STATUS           current
    DESCRIPTION
        "This is a collection of objects of
	 data policy filter vpn list."
    ::= { ciscoSdwanPolicyMIBGroups 2 }

cSdwanPolicyDataPolicyFilterVpnlistCounterGroup OBJECT-GROUP
    OBJECTS          {
                         policyDataPolicyFilterVpnlistCounterPackets,
                         policyDataPolicyFilterVpnlistCounterBytes
                     }
    STATUS           current
    DESCRIPTION
        "This is a collection of object of
	  data policy filter vpn list counter. "
    ::= { ciscoSdwanPolicyMIBGroups 3 }

cSdwanPolicyDataPolicyFilterVpnlistPolicerGroup OBJECT-GROUP
    OBJECTS          {
                         policyDataPolicyFilterVpnlistPolicerOosPackets,
                         policyDataPolicyFilterVpnlistPolicerOosBytes
                     }
    STATUS           current
    DESCRIPTION
        "This is a collection of object of
	  data policy filter vpn list policer. "
    ::= { ciscoSdwanPolicyMIBGroups 4 }

cSdwanPolicyAppRoutePolicyFilterGroup OBJECT-GROUP
    OBJECTS          {
                         policyAppRoutePolicyFilterName
                     }
    STATUS           current
    DESCRIPTION
        "This is a collection of object of app route policy filter. "
    ::= { ciscoSdwanPolicyMIBGroups 5 }

cSdwanPolicyAppRoutePolicyFilterVpnlistGroup OBJECT-GROUP
    OBJECTS          {
                         policyAppRoutePolicyFilterVpnlistName
                     }
    STATUS           current
    DESCRIPTION
        "This is a collection of object of
	  app route policy filter vpn list. "
    ::= { ciscoSdwanPolicyMIBGroups 6 }

cSdwanPolicyAppRoutePolicyFilterVpnlistCounterGroup OBJECT-GROUP
    OBJECTS          {
                     policyAppRoutePolicyFilterVpnlistCounterPackets,
                     policyAppRoutePolicyFilterVpnlistCounterBytes
                     }
    STATUS           current
    DESCRIPTION
        "This is a collection of object of
	  app route policy filter vpn list counter. "
    ::= { ciscoSdwanPolicyMIBGroups 7 }

cSdwanPolicyAccessListNamesGroup OBJECT-GROUP
    OBJECTS          {
                         policyAccessListNamesName
                     }
    STATUS           current
    DESCRIPTION
        "This is a collection of object of access list names. "
    ::= { ciscoSdwanPolicyMIBGroups 8 }

cSdwanPolicyAccessListCountersGroup OBJECT-GROUP
    OBJECTS          {
                         policyAccessListCountersName
                     }
    STATUS           current
    DESCRIPTION
        "This is a collection of object of access list counters. "
    ::= { ciscoSdwanPolicyMIBGroups 9 }

cSdwanPolicyAccessListCountersAccessPolicyCounterListGroup OBJECT-GROUP
    OBJECTS          {
                policyAccessListCountersAccessPolicyCounterListPackets,
                policyAccessListCountersAccessPolicyCounterListBytes
                     }
    STATUS           current
    DESCRIPTION
        "This is a collection of object of
	  access list counters access policy counter list. "
    ::= { ciscoSdwanPolicyMIBGroups 10 }

cSdwanPolicyAccessListPolicersGroup OBJECT-GROUP
    OBJECTS          {
                         policyAccessListPolicersName
                     }
    STATUS           current
    DESCRIPTION
        "This is a collection of object of access list policers. "
    ::= { ciscoSdwanPolicyMIBGroups 11 }

cSdwanPolicyAccessListPolicersAccessPolicyPolicerListGroup OBJECT-GROUP
    OBJECTS          {
             policyAccessListPolicersAccessPolicyPolicerListOosPackets,
             policyAccessListPolicersAccessPolicyPolicerListOosBytes
                     }
    STATUS           current
    DESCRIPTION
        "This is a collection of object of
	  access list policers access policy policer list. "
    ::= { ciscoSdwanPolicyMIBGroups 12 }

cSdwanPolicyAccessListAssociationsGroup OBJECT-GROUP
    OBJECTS          {
                         policyAccessListAssociationsName
                     }
    STATUS           current
    DESCRIPTION
        "This is a collection of object of access list associations. "
    ::= { ciscoSdwanPolicyMIBGroups 13 }

cSdwanPolicyAccessListAssociationsAccessPolicyInterfaceListGroup
    OBJECT-GROUP
    OBJECTS          {
         policyAccessListAssociationsAccessPolicyInterfaceListIntName,
         policyAccessListAssociationsAccessPolicyInterfaceListIntDir
                     }
    STATUS           current
    DESCRIPTION
        "This is a collection of object of
	   access list associations access policy interface list. "
    ::= { ciscoSdwanPolicyMIBGroups 14 }

cSdwanPolicyRewriteAssociationsGroup OBJECT-GROUP
    OBJECTS          {
                         policyRewriteAssociationsName
                     }
    STATUS           current
    DESCRIPTION
        "This is a collection of object of rewrite associations. "
    ::= { ciscoSdwanPolicyMIBGroups 15 }

cSdwanPolicyRewriteAssociationsRewriteInterfaceListGroup OBJECT-GROUP
    OBJECTS          {
             policyRewriteAssociationsRewriteInterfaceListInterfaceName
                     }
    STATUS           current
    DESCRIPTION
        "This is a collection of object of
	  rewrite associations rewrite interface list. "
    ::= { ciscoSdwanPolicyMIBGroups 16 }

cSdwanPolicyFromVsmartSlaClassGroup OBJECT-GROUP
    OBJECTS          {
                         policyFromVsmartSlaClassLoss,
                         policyFromVsmartSlaClassLatency,
                         policyFromVsmartSlaClassJitter,
                         policyFromVsmartSlaClassAppProbeClass
                     }
    STATUS           current
    DESCRIPTION
        "This is a collection of object of
	  policy from vsmart sla class. "
    ::= { ciscoSdwanPolicyMIBGroups 17 }

cSdwanPolicyFromVsmartListsVpnListGroup OBJECT-GROUP
    OBJECTS          {
                         policyFromVsmartListsVpnListName
                     }
    STATUS           current
    DESCRIPTION
        "This is a collection of object of
	  policy from vsmart lists of vpn list. "
    ::= { ciscoSdwanPolicyMIBGroups 18 }

cSdwanPolicyFromVsmartListsVpnListVpnGroup OBJECT-GROUP
    OBJECTS          {
                         policyFromVsmartListsVpnListVpnId
                     }
    STATUS           current
    DESCRIPTION
        "This is a collection of object of
	  policy from vsmart lists of vpn list vpn. "
    ::= { ciscoSdwanPolicyMIBGroups 19 }

cSdwanPolicyFromVsmartListsDataPrefixListGroup OBJECT-GROUP
    OBJECTS          {
                         policyFromVsmartListsDataPrefixListName
                     }
    STATUS           current
    DESCRIPTION
        "This is a collection of object of
	  policy from vsmart lists of data prefix list. "
    ::= { ciscoSdwanPolicyMIBGroups 20 }

cSdwanPolicyFromVsmartListsDataPrefixListIpPrefixGroup OBJECT-GROUP
    OBJECTS          {
                        policyFromVsmartListsDataPrefixListIpPrefixIp
                     }
    STATUS           current
    DESCRIPTION
        "This is a collection of object of
	  policy from vsmart lists of data prefix list ip prefix. "
    ::= { ciscoSdwanPolicyMIBGroups 21 }

cSdwanPolicyFromVsmartListsTlocListGroup OBJECT-GROUP
    OBJECTS          {
                         policyFromVsmartListsTlocListName
                     }
    STATUS           current
    DESCRIPTION
        "This is a collection of object of
	  policy from vsmart lists of tloc list. "
    ::= { ciscoSdwanPolicyMIBGroups 22 }

cSdwanPolicyFromVsmartListsTlocListTlocGroup OBJECT-GROUP
    OBJECTS          {
               policyFromVsmartListsTlocListTlocPreference
                     }
    STATUS           current
    DESCRIPTION
        "This is a collection of object of
	  policy from vsmart lists of tloc list tloc details. "
    ::= { ciscoSdwanPolicyMIBGroups 23 }

cSdwanPolicyFromVsmartListsAppProbeClassListGroup OBJECT-GROUP
    OBJECTS          {
--               policyFromVsmartListsAppProbeClassListName,
               policyFromVsmartListsAppProbeClassListForwardingClass
                     }
    STATUS           current
    DESCRIPTION
        "This is a collection of object of
	  policy from vsmart lists of app probe class list. "
    ::= { ciscoSdwanPolicyMIBGroups 24 }

cSdwanPolicyFromVsmartListsAppProbeClassColorGroup OBJECT-GROUP
    OBJECTS          {
                         policyFromVsmartListsAppProbeClassColorDscp
                     }
    STATUS           current
    DESCRIPTION
        "This is a collection of object of
	  policy from vsmart lists of app probe class color. "
    ::= { ciscoSdwanPolicyMIBGroups 25 }

cSdwanPolicyNotifObjsGroup OBJECT-GROUP
    OBJECTS {
           netconfNotificationSeverity,
	       ciscoSdwanPolicyVpnId,
	       ciscoSdwanPolicyApplication,
	       ciscoSdwanPolicySourceIp,
	       ciscoSdwanPolicySourcePort,
	       ciscoSdwanPolicyDestinationIp,
	       ciscoSdwanPolicyDestinationPort,
	       ciscoSdwanPolicyProtocol,
	       ciscoSdwanPolicyDscp,
	       ciscoSdwanPolicySlaInformation,
	       ciscoSdwanPolicySlaStatus,
	       ciscoSdwanPolicyVpnListName,
	       ciscoSdwanPolicyName,
	       ciscoSdwanPolicyAccessListName,
	       ciscoSdwanPolicyStatus
            }
    STATUS          current
    DESCRIPTION
        "This is a collection of objects of
                                 policy notification objects."
    ::= { ciscoSdwanPolicyMIBGroups 26 }

cSdwanPolicyNotifsGroup NOTIFICATION-GROUP
   NOTIFICATIONS {
            ciscoSdwanPolicySlaViolation,
		    ciscoSdwanPolicySlaViolationPktDrop,
		    ciscoSdwanPolicyDataPolicyAssociationStatus,
		    ciscoSdwanPolicyAccessListAssociationStatus
                 }
    STATUS          current
    DESCRIPTION
        "This is a collection of policy notifications."
    ::= { ciscoSdwanPolicyMIBGroups 27 }

cSdwanPolicyFromVsmartDataPolicyGroup OBJECT-GROUP
    OBJECTS          {
                         policyFromVsmartDataPolicyDirection
                     }
    STATUS           current
    DESCRIPTION
        "This is a collection of object of data policy."
    ::= { ciscoSdwanPolicyMIBGroups 28 }

cSdwanPolicyFromVsmartDataPolicyVpnListGroup OBJECT-GROUP
    OBJECTS          {
                         policyFromVsmartDataPolicyVpnListDefaultAction
                     }
    STATUS           current
    DESCRIPTION
        "This is a collection of object of data policy vpn list."
    ::= { ciscoSdwanPolicyMIBGroups 29 }

cSdwanPolicyFromVsmartDataPolicyVpnListSequenceGroup OBJECT-GROUP
   OBJECTS           {
policyFromVsmartDataPolicyVpnListSequenceMatchSrcDataPrLst,
policyFromVsmartDataPolicyVpnListSequenceMatchSrcDataV6PrLst,
policyFromVsmartDataPolicyVpnListSequenceMatchDestDataPrLst,
policyFromVsmartDataPolicyVpnListSequenceMatchDestDataV6PrLst,
policyFromVsmartDataPolicyVpnListSequenceMatchTcp,
policyFromVsmartDataPolicyVpnListSequenceActionActionValue,
policyFromVsmartDataPolicyVpnListSequenceActionCount,
policyFromVsmartDataPolicyVpnListSequenceActionNatUseVpn,
policyFromVsmartDataPolicyVpnListSequenceActionCflowd,
policyFromVsmartDataPolicyVpnListSequenceActionSetLocalTlocColor,
policyFromVsmartDataPolicyVpnListSequenceActionSetLocalTlocEncap,
policyFromVsmartDataPolicyVpnListSequenceActionSetNextHop,
policyFromVsmartDataPolicyVpnListSequenceActionSetPolicer,
policyFromVsmartDataPolicyVpnListSequenceActionSetVpn,
policyFromVsmartDataPolicyVpnListSequenceActionSetVpnLabel,
policyFromVsmartDataPolicyVpnListSequenceActionSetTlocIp,
policyFromVsmartDataPolicyVpnListSequenceActionSetTlocColor,
policyFromVsmartDataPolicyVpnListSequenceActionSetTlocList,
policyFromVsmartDataPolicyVpnListSequenceActionSetServiceSvcType,
policyFromVsmartDataPolicyVpnListSequenceActionSetServiceVpn,
policyFromVsmartDataPolicyVpnListSequenceActionSetServiceTlocIp,
policyFromVsmartDataPolicyVpnListSequenceActionSetSvcTlocClr,
policyFromVsmartDataPolicyVpnListSequencActionSetSvcTlocLst,
policyFromVsmartDataPolicyVpnListSequenceActionSetServiceLocal,
policyFromVsmartDataPolicyVpnListSeqActSetServiceRestrict,
policyFromVsmartDataPolicyVpnListSequenceActionLog,
policyFromVsmartDataPolicyVpnListSeqActSetLocalTlocListColor,
policyFromVsmartDataPolicyVpnListSeqActSetLocalTlocListEncap,
policyFromVsmartDataPolicyVpnListSeqActSetLocalTlocListRestrict,
policyFromVsmartDataPolicyVpnListSequenceActionTcpOptimization,
policyFromVsmartDataPolicyVpnListSequenceActionSetNextHopIpv6,
policyFromVsmartDataPolicyVpnListSequenceActionSig,
policyFromVsmartDataPolicyVpnListSequenceActionSetNextHopLoose,
policyFromVsmartDataPolicyVpnListSeqActSigFallbackToRoute
                     }
   STATUS            current
   DESCRIPTION
       "This is a collection of object of
                 data policy vpn list sequence."
   ::= { ciscoSdwanPolicyMIBGroups 30 }

cSdwanpolicyFromVsmartDataPolVpnListSeqActSetVipTlocPrLstGroup
                                                         OBJECT-GROUP
   OBJECTS           {
      policyFromVsmartDataPolicyVpnListSeqActSetVipTlocPrLstTlocLbl,
      policyFromVsmartDataPolicyVpnListSeqActSetVipTlocPrLstTlocIp,
      policyFromVsmartDataPolicyVpnListSeqActSetVipTlocPrLstTlocClr,
      policyFromVsmartDataPolicyVpnListSeqActSetVipTlocPrLstTlocEn,
      policyFromVsmartDataPolicyVpnListSeqActSetVipTlocPrLstTlocPrf
                     }
   STATUS            current
   DESCRIPTION
       "This is a collection of object of data policy vpn list sequence
                               active set vip tloc priority list."
   ::= { ciscoSdwanPolicyMIBGroups 31 }

cSdwanPolicyFromVsmartCflowdTemplateGroup OBJECT-GROUP
   OBJECTS           {
                policyFromVsmartCflowdTemplateName,
                policyFromVsmartCflowdTemplateFlowActiveTimeout,
                policyFromVsmartCflowdTemplateFlowInactiveTimeout,
                policyFromVsmartCflowdTemplateTemplateRefresh,
                policyFromVsmartCflowdTemplateFlowSamplingInterval,
                policyFromVsmartCflowdTemplateProtocol
                     }
   STATUS            current
   DESCRIPTION
       "This is a collection of object of cflowd template."
   ::= { ciscoSdwanPolicyMIBGroups 32 }

cSdwanPolicyFromVsmartCflowdTemplateCollectorGroup OBJECT-GROUP
   OBJECTS           {
                policyFromVsmartCflowdTemplateCollectorSourceInterface,
                policyFromVsmartCflowdTemplateCollectorExportSpreadEnable,
                policyFromVsmartCflowdTemplateCollectorExportSpreadAppTables,
                policyFromVsmartCflowdTemplateCollectorExportSpreadTlocTables,
                policyFromVsmartCflowdTemplateCollectorExportSpreadOtherTables,
                policyFromVsmartCflowdTemplateCollectorBFDMetricsExport,
                policyFromVsmartCflowdTemplateCollectorBFDExportInterval
                     }
   STATUS            current
   DESCRIPTION
       "This is a collection of object of cflowd template collector."
   ::= { ciscoSdwanPolicyMIBGroups 33 }

cSdwanPolicyFromVsmartAppRoutePolicyGroup OBJECT-GROUP
   OBJECTS           {
                         policyFromVsmartAppRoutePolicyName
                     }
   STATUS            current
   DESCRIPTION
       "This is a collection of object of app route policy."
   ::= { ciscoSdwanPolicyMIBGroups 34 }

cSdwanPolicyFromVsmartAppRoutePolicyVpnListGroup OBJECT-GROUP
   OBJECTS           {
     policyFromVsmartAppRoutePolicyVpnListDefActSlaClassName
                     }
   STATUS            current
   DESCRIPTION
       "This is a collection of object of app route policy vpn list."
   ::= { ciscoSdwanPolicyMIBGroups 35 }

cSdwanPolicyFromVsmartAppRoutePolicyVpnListSequenceGroup OBJECT-GROUP
   OBJECTS           {
     policyFromVsmartAppRoutePolicyVpnListSequenceMatchSrcDtPrLst,
     policyFromVsmartAppRoutePolicyVpnListSequenceMatchSrcDtV6PrLst,
     policyFromVsmartAppRoutePolicyVpnListSequenceMatchDestDtPrLst,
     policyFromVsmartAppRoutePolicyVpnListSequenceMatchDestDtV6PrLst,
     policyFromVsmartAppRoutePolicyVpnListSequenceActionCount,
     policyFromVsmartAppRoutePolicyVpnListSequenceActionSlaClName,
     policyFromVsmartAppRoutePolicyVpnListSequenceActionSlaClStrict,
     policyFromVsmartAppRoutePolicyVpnListSequenceActionLog,
     policyFromVsmartAppRoutePolicyVpnListSequenceActionSlaClFallback
                     }
   STATUS            current
   DESCRIPTION
       "This is a collection of object of
                 app route policy vpn list sequence."
   ::= { ciscoSdwanPolicyMIBGroups 36 }

cSdwanPolicyFromVsmartPolicerGroup OBJECT-GROUP
   OBJECTS           {
                          policyFromVsmartPolicerRate,
                          policyFromVsmartPolicerBurst,
                          policyFromVsmartPolicerExceed
                     }
   STATUS            current
   DESCRIPTION
       "This is a collection of object of policer."
   ::= { ciscoSdwanPolicyMIBGroups 37 }

END
