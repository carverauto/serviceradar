-- *****************************************************************
-- CISCO-SDWAN-OMP-MIB.my:
-- OID assignments for Cisco sdwan policy

-- Feb 2021, Richard Fu

-- Copyright (c) 2020-2022 by Cisco Systems, Inc.
-- All rights reserved.
-- *****************************************************************

CISCO-SDWAN-OMP-MIB DEFINITIONS ::= BEGIN
IMPORTS
    MODULE-IDENTITY, 
    OBJECT-TYPE, 
    NOTIFICATION-TYPE,
    Unsigned32
        FROM SNMPv2-SMI
    MODULE-COMPLIANCE,
    OBJECT-GROUP,
    NOTIFICATION-GROUP
        FROM SNMPv2-CONF
    TEXTUAL-CONVENTION, 
    TruthValue
        FROM SNMPv2-TC
    ciscoMgmt
        FROM CISCO-SMI;

ciscoSdwanOmpMIB MODULE-IDENTITY
    LAST-UPDATED "202103030000Z"
    ORGANIZATION    "Cisco Systems Inc."
    CONTACT-INFO
            "Cisco Systems,
            Customer Service

            Postal: 170 West Tasman Drive
            San Jose, CA  95134
            USA

            Tel: +1 800 553-NETS

            Email: cs-snmp@cisco.com"
    DESCRIPTION "This module defines the data model for OMP"
    REVISION "202103030000Z"
    DESCRIPTION "Cisco SDWAN OMP Revision 0"
    ::= { ciscoMgmt 1003 }

UnsignedByte ::= TEXTUAL-CONVENTION
    DISPLAY-HINT "d"
    STATUS      current
    DESCRIPTION "xs:unsignedByte"
    SYNTAX      Unsigned32 (0 .. 255)

UnsignedShort ::= TEXTUAL-CONVENTION
    DISPLAY-HINT "d"
    STATUS      current
    DESCRIPTION "xs:unsignedShort"
    SYNTAX      Unsigned32 (0 .. 65535)

IpPrefix ::= TEXTUAL-CONVENTION
    DISPLAY-HINT "1x "
    STATUS       current
    DESCRIPTION  "confd:ipPrefix"
    SYNTAX       OCTET STRING (SIZE (5|17))

String ::= TEXTUAL-CONVENTION
    DISPLAY-HINT "1t"
    STATUS      current
    DESCRIPTION "xs:string"
    SYNTAX      OCTET STRING

Groups1 ::= TEXTUAL-CONVENTION
    DISPLAY-HINT "1t"
    STATUS      current
    DESCRIPTION "Groups 1"
    SYNTAX      OCTET STRING

AttributeTypeEnum ::= TEXTUAL-CONVENTION
    STATUS      current
    DESCRIPTION "Type enum"
    SYNTAX      INTEGER {original(0),
                         installed(1)}

ReceivedPrunes1 ::= TEXTUAL-CONVENTION
    DISPLAY-HINT "1t"
    STATUS      current
    DESCRIPTION "Received Prunes 1"
    SYNTAX      OCTET STRING

AdvertisedPrunes1 ::= TEXTUAL-CONVENTION
    DISPLAY-HINT "1t"
    STATUS      current
    DESCRIPTION "Advertised Prunes 1"
    SYNTAX      OCTET STRING

BfdStatusEnum ::= TEXTUAL-CONVENTION
    STATUS      current
    DESCRIPTION "Bidirectional Forwarding Detection (BFD) Status enum"
    SYNTAX      INTEGER {up(0),
                         down(1),
                         inactive(2)}

PathStatusEnum ::= TEXTUAL-CONVENTION
    STATUS      current
    DESCRIPTION "Path Status enum"
    SYNTAX      INTEGER {chosen(0),
                         backup(1)}

RibInStatusType ::= TEXTUAL-CONVENTION
    STATUS      current
    DESCRIPTION "Rib in Status type"
    SYNTAX      BITS {c(0),i(1),red(2),rej(3),l(4),r(5),s(6),
                      ext(7),inv(8),u(9),stg(10),ia(11),brr(12), 
                      tgwr(13)}

AddrFamilyEnum ::= TEXTUAL-CONVENTION
    STATUS      current
    DESCRIPTION "Address Family enum"
    SYNTAX      INTEGER {ipv4(0),
                         ipv6(1)}

LossReasonEnum ::= TEXTUAL-CONVENTION
    STATUS      current
    DESCRIPTION "Best-path loss reason"
    SYNTAX      INTEGER {none(0),
                         invalid(1),
                         personality(2),
                         distance(3),
                         preference(4),
                         tloc-preference(5),
                         origin-protocol(6),
                         origin-protocol-subtype(7),
                         origin-metric(8),
                         peer-id(9),
                         tloc-id(10),
                         stale-entry(11),
                         site-id(12),
                         omp-version(13),
                         tloc-gen-id(14),
                         tloc-spi(15),
                         ultimate-tloc-id(16),
                         tloc-action(17),
                         path-inactive(18),
                         region-id(19),
                         region-path(20),
                         transport-gateway(21),
                         affinity-group(22),
                         migration-bgp-community(23),
                         as-path-length(24),
                         migration-omp-prefer(25)}

McastRouteEnum ::= TEXTUAL-CONVENTION
    STATUS      current
    DESCRIPTION "Multicast route type"
    SYNTAX      INTEGER {starGroup(0),
                         sourceGroup(1),
                         sourceActive(2)}

TlocColorEnum ::= TEXTUAL-CONVENTION
    STATUS      current
    DESCRIPTION "TLOC color"
    SYNTAX      INTEGER {none(0),
                         default(1),
                         mpls(2),
                         metro-ethernet(3),
                         biz-internet(4),
                         public-internet(5),
                         lte(6),
                         threeG(7),
                         red(8),
                         green(9),
                         blue(10),
                         gold(11),
                         silver(12),
                         bronze(13),
                         custom1(14),
                         custom2(15),
                         custom3(16),
                         private1(17),
                         private2(18),
                         private3(19),
                         private4(20),
                         private5(21),
                         private6(22)}

TlocEncapEnum ::= TEXTUAL-CONVENTION
    STATUS      current
    DESCRIPTION "TLOC encapsulation"
    SYNTAX      INTEGER {none(0),
                         gre(1),
                         ipsec(2)}

ProtocolEnum ::= TEXTUAL-CONVENTION
    STATUS      current
    DESCRIPTION "Protocol"
    SYNTAX      INTEGER {proto-invalid(0),
                         static(1),
                         connected(2),
                         eBGP(3),
                         iBGP(4),
                         oSPF-intra-area(5),
                         oSPF-inter-area(6),
                         oSPF-external-1(7),
                         oSPF-external-2(8),
                         aggregate(9),
                         natpoolInside(10),
                         eigrp-sum(11),
                         eigrp-int(12),
                         eigrp-ext(13),
                         lisp(14),
                         isis-level-1(15),
                         isis-level-2(16),
                         oSPF-nssa-1(17),
                         oSPF-nssa-2(18),
                         oSPF-nat-dia(19),
                         rip(20)}

TlocActionEnum ::= TEXTUAL-CONVENTION
    STATUS      current
    DESCRIPTION "TLOC action"
    SYNTAX      INTEGER {none(0),
                         strict(1),
                         primary(2),
                         ecmp(3),
                         backup(4)}

EncryptType ::= TEXTUAL-CONVENTION
    STATUS      current
    DESCRIPTION "Encryption type"
    SYNTAX      BITS {null(0),
                      des(1),
                      des3(2),
                      aes128(3),
                      aes192(4),
                      aes256(5),
                      aes128Ctr(6),
                      aes192Ctr(7),
                      aes256Ctr(8),
                      aes128Gmac(9),
                      aes192Gmac(10),
                      aes256Gmac(11)}

IntegType ::= TEXTUAL-CONVENTION
    STATUS      current
    DESCRIPTION "Integrity type"
    SYNTAX      BITS {none(0),
                      esp(1),
                      ip-udp-esp(2),
                      ip-udp-esp-no-id(3)}

CarrierEnum ::= TEXTUAL-CONVENTION
    STATUS      current
    DESCRIPTION "Carrier"
    SYNTAX      INTEGER {default(1),
                         carrier1(2),
                         carrier2(3),
                         carrier3(4),
                         carrier4(5),
                         carrier5(6),
                         carrier6(7),
                         carrier7(8),
                         carrier8(9)}

-- Notification type definitions
NotificationSeverity ::= TEXTUAL-CONVENTION
    STATUS      current
    DESCRIPTION "Netconf notification severity level"
    SYNTAX      INTEGER {critical(1),
                         major(2),
                         minor(3)}

OperState ::= TEXTUAL-CONVENTION
    STATUS      current
    DESCRIPTION "Operational state"
    SYNTAX      INTEGER {up(0),
                         down(1)}

PeerState ::= TEXTUAL-CONVENTION
    STATUS      current
    DESCRIPTION "OMP peer state"
    SYNTAX      INTEGER {invalid(0),
                         init(1),
                         handshake(2),
                         up(3),
                         down(4),
                         init-in-gr(5),
                         down-in-gr(6),
                         handshake-in-gr(7),
                         up-in-gr(8)}

OmpPolicyState ::= TEXTUAL-CONVENTION
    STATUS      current
    DESCRIPTION "OMP policy state"
    SYNTAX      INTEGER {add(0),
                         delete(1)}

InetAddressIP ::= TEXTUAL-CONVENTION
    DISPLAY-HINT "1d."
    STATUS      current
    DESCRIPTION "confd:inetAddressIP"
    SYNTAX      OCTET STRING (SIZE (4|16))

-- MIB Objects, Notification Objects, Notification and Conform
ciscoSdwanOmpMIBNotifs OBJECT IDENTIFIER
    ::= { ciscoSdwanOmpMIB 0 }

ciscoSdwanOmpMIBObjects OBJECT IDENTIFIER
    ::= { ciscoSdwanOmpMIB 1 }

ciscoSdwanOmpMIBNotifObjects OBJECT IDENTIFIER
    ::= { ciscoSdwanOmpMIB 2 }

ciscoSdwanOmpMIBConform OBJECT IDENTIFIER
    ::= { ciscoSdwanOmpMIB 3 }

-- OMP information
-- tagpath /omp
omp OBJECT IDENTIFIER ::= { ciscoSdwanOmpMIBObjects 1 }

-- Display OMP summary
-- tagpath /omp/summary
ompSummaryTable OBJECT IDENTIFIER ::= { ciscoSdwanOmpMIBObjects 2 }

-- Display OMP summary
-- tagpath /omp/summary
ompSummary OBJECT IDENTIFIER ::= { ompSummaryTable 1 }

-- tagpath /omp/summary/operstate
ompSummaryOperstate OBJECT-TYPE
    SYNTAX      INTEGER {dOWN(1),uP(2)}
    MAX-ACCESS  read-only
    STATUS      current
    DESCRIPTION "Operational state"
    ::= { ompSummary 1 }

-- tagpath /omp/summary/adminstate
ompSummaryAdminstate OBJECT-TYPE
    SYNTAX      INTEGER {dOWN(1),uP(2)}
    MAX-ACCESS  read-only
    STATUS      current
    DESCRIPTION "Administration state"
    ::= { ompSummary 2 }

-- tagpath /omp/summary/devicetype
ompSummaryDevicetype OBJECT-TYPE
    SYNTAX      INTEGER {unknown(0),
                         vedge(1),
                         vhub(2),
                         vsmart(3),
                         vbond(4),
                         vmanage(5),
                         ztp(6),
                         vcontainer(7)}
    MAX-ACCESS  read-only
    STATUS      current
    DESCRIPTION "Device personality"
    ::= { ompSummary 3 }

-- tagpath /omp/summary/ompuptime-str
ompSummaryOmpuptime OBJECT-TYPE
    SYNTAX      String
    MAX-ACCESS  read-only
    STATUS      current
    DESCRIPTION "Time OMP has been up"
    ::= { ompSummary 4 }

-- tagpath /omp/summary/ompdowntime-str
ompSummaryOmpdowntime OBJECT-TYPE
    SYNTAX      String
    MAX-ACCESS  read-only
    STATUS      current
    DESCRIPTION "Time OMP has been down"
    ::= { ompSummary 5 }

-- tagpath /omp/summary/routes-received
ompSummaryRoutesReceived OBJECT-TYPE
    SYNTAX      Unsigned32
    MAX-ACCESS  read-only
    STATUS      current
    DESCRIPTION "Routes received"
    ::= { ompSummary 6 }

-- tagpath /omp/summary/routes-installed
ompSummaryRoutesInstalled OBJECT-TYPE
    SYNTAX      Unsigned32
    MAX-ACCESS  read-only
    STATUS      current
    DESCRIPTION "Routes installed"
    ::= { ompSummary 7 }

-- tagpath /omp/summary/routes-sent
ompSummaryRoutesSent OBJECT-TYPE
    SYNTAX      Unsigned32
    MAX-ACCESS  read-only
    STATUS      current
    DESCRIPTION "Routes sent"
    ::= { ompSummary 8 }

-- tagpath /omp/summary/tlocs-received
ompSummaryTlocsReceived OBJECT-TYPE
    SYNTAX      Unsigned32
    MAX-ACCESS  read-only
    STATUS      current
    DESCRIPTION "TLOCs received"
    ::= { ompSummary 9 }

-- tagpath /omp/summary/tlocs-installed
ompSummaryTlocsInstalled OBJECT-TYPE
    SYNTAX      Unsigned32
    MAX-ACCESS  read-only
    STATUS      current
    DESCRIPTION "TLOCs installed"
    ::= { ompSummary 10 }

-- tagpath /omp/summary/tlocs-sent
ompSummaryTlocsSent OBJECT-TYPE
    SYNTAX      Unsigned32
    MAX-ACCESS  read-only
    STATUS      current
    DESCRIPTION "TLOCs sent"
    ::= { ompSummary 11 }

-- tagpath /omp/summary/services-received
ompSummaryServicesReceived OBJECT-TYPE
    SYNTAX      Unsigned32
    MAX-ACCESS  read-only
    STATUS      current
    DESCRIPTION "Services received"
    ::= { ompSummary 12 }

-- tagpath /omp/summary/services-installed
ompSummaryServicesInstalled OBJECT-TYPE
    SYNTAX      Unsigned32
    MAX-ACCESS  read-only
    STATUS      current
    DESCRIPTION "Services installed"
    ::= { ompSummary 13 }

-- tagpath /omp/summary/services-sent
ompSummaryServicesSent OBJECT-TYPE
    SYNTAX      Unsigned32
    MAX-ACCESS  read-only
    STATUS      current
    DESCRIPTION "Services sent"
    ::= { ompSummary 14 }

-- tagpath /omp/summary/mcast-routes-received
ompSummaryMcastRoutesReceived OBJECT-TYPE
    SYNTAX      Unsigned32
    MAX-ACCESS  read-only
    STATUS      current
    DESCRIPTION "Multicast routes received"
    ::= { ompSummary 15 }

-- tagpath /omp/summary/mcast-routes-installed
ompSummaryMcastRoutesInstalled OBJECT-TYPE
    SYNTAX      Unsigned32
    MAX-ACCESS  read-only
    STATUS      current
    DESCRIPTION "Multicast routes installed"
    ::= { ompSummary 16 }

-- tagpath /omp/summary/mcast-routes-sent
ompSummaryMcastRoutesSent OBJECT-TYPE
    SYNTAX      Unsigned32
    MAX-ACCESS  read-only
    STATUS      current
    DESCRIPTION "Multicast routes sent"
    ::= { ompSummary 17 }

-- tagpath /omp/summary/hello-received
ompSummaryHelloReceived OBJECT-TYPE
    SYNTAX      Unsigned32
    MAX-ACCESS  read-only
    STATUS      current
    DESCRIPTION "Hello packets received"
    ::= { ompSummary 18 }

-- tagpath /omp/summary/hello-sent
ompSummaryHelloSent OBJECT-TYPE
    SYNTAX      Unsigned32
    MAX-ACCESS  read-only
    STATUS      current
    DESCRIPTION "Hello packets sent"
    ::= { ompSummary 19 }

-- tagpath /omp/summary/handshake-received
ompSummaryHandshakeReceived OBJECT-TYPE
    SYNTAX      Unsigned32
    MAX-ACCESS  read-only
    STATUS      current
    DESCRIPTION "Handshake packets received"
    ::= { ompSummary 20 }

-- tagpath /omp/summary/handshake-sent
ompSummaryHandshakeSent OBJECT-TYPE
    SYNTAX      Unsigned32
    MAX-ACCESS  read-only
    STATUS      current
    DESCRIPTION "Handshake packets sent"
    ::= { ompSummary 21 }

-- tagpath /omp/summary/alert-received
ompSummaryAlertReceived OBJECT-TYPE
    SYNTAX      Unsigned32
    MAX-ACCESS  read-only
    STATUS      current
    DESCRIPTION "Alert packets received"
    ::= { ompSummary 22 }

-- tagpath /omp/summary/alert-sent
ompSummaryAlertSent OBJECT-TYPE
    SYNTAX      Unsigned32
    MAX-ACCESS  read-only
    STATUS      current
    DESCRIPTION "Alert packets sent"
    ::= { ompSummary 23 }

-- tagpath /omp/summary/inform-received
ompSummaryInformReceived OBJECT-TYPE
    SYNTAX      Unsigned32
    MAX-ACCESS  read-only
    STATUS      current
    DESCRIPTION "Inform packets received"
    ::= { ompSummary 24 }

-- tagpath /omp/summary/inform-sent
ompSummaryInformSent OBJECT-TYPE
    SYNTAX      Unsigned32
    MAX-ACCESS  read-only
    STATUS      current
    DESCRIPTION "Inform packets sent"
    ::= { ompSummary 25 }

-- tagpath /omp/summary/update-received
ompSummaryUpdateReceived OBJECT-TYPE
    SYNTAX      Unsigned32
    MAX-ACCESS  read-only
    STATUS      current
    DESCRIPTION "Update packets received"
    ::= { ompSummary 26 }

-- tagpath /omp/summary/update-sent
ompSummaryUpdateSent OBJECT-TYPE
    SYNTAX      Unsigned32
    MAX-ACCESS  read-only
    STATUS      current
    DESCRIPTION "Update packets sent"
    ::= { ompSummary 27 }

-- tagpath /omp/summary/policy-received
ompSummaryPolicyReceived OBJECT-TYPE
    SYNTAX      Unsigned32
    MAX-ACCESS  read-only
    STATUS      current
    DESCRIPTION "Policy packets received"
    ::= { ompSummary 28 }

-- tagpath /omp/summary/policy-sent
ompSummaryPolicySent OBJECT-TYPE
    SYNTAX      Unsigned32
    MAX-ACCESS  read-only
    STATUS      current
    DESCRIPTION "Policy packets sent"
    ::= { ompSummary 29 }

-- tagpath /omp/summary/packets-received
ompSummaryPacketsReceived OBJECT-TYPE
    SYNTAX      Unsigned32
    MAX-ACCESS  read-only
    STATUS      current
    DESCRIPTION "Total OMP packets received"
    ::= { ompSummary 30 }

-- tagpath /omp/summary/packets-sent
ompSummaryPacketsSent OBJECT-TYPE
    SYNTAX      Unsigned32
    MAX-ACCESS  read-only
    STATUS      current
    DESCRIPTION "Total OMP packets sent"
    ::= { ompSummary 31 }

-- tagpath /omp/summary/vsmart-peers
ompSummaryVsmartPeers OBJECT-TYPE
    SYNTAX      Unsigned32
    MAX-ACCESS  read-only
    STATUS      current
    DESCRIPTION "Number of vSmart peers in up state"
    ::= { ompSummary 32 }

-- tagpath /omp/summary/mt-peers
ompSummaryMtPeersTable OBJECT-TYPE
    SYNTAX      SEQUENCE OF OmpSummaryMtPeersEntry
    MAX-ACCESS  not-accessible
    STATUS      current
    DESCRIPTION "Display OMP Multi Tenant peers"
    ::= { ompSummaryTable 2 }

-- tagpath /omp/summary/mt-peers
ompSummaryMtPeersEntry OBJECT-TYPE
    SYNTAX      OmpSummaryMtPeersEntry
    MAX-ACCESS  not-accessible
    STATUS      current
    DESCRIPTION "mt-peers entry"
    INDEX { ompSummaryMtPeersTenantId,
            ompSummaryMtPeersPeer }
        ::= { ompSummaryMtPeersTable 1 }

OmpSummaryMtPeersEntry ::=
    SEQUENCE {
        ompSummaryMtPeersTenantId UnsignedShort,
        ompSummaryMtPeersPeer InetAddressIP,
        ompSummaryMtPeersType INTEGER,
        ompSummaryMtPeersDomainId Unsigned32,
        ompSummaryMtPeersSiteId Unsigned32,
        ompSummaryMtPeersRegionId String,
        ompSummaryMtPeersState INTEGER,
        ompSummaryMtPeersVersion UnsignedByte,
        ompSummaryMtPeersLegit TruthValue,
        ompSummaryMtPeersUpcount Unsigned32,
        ompSummaryMtPeersDowncount Unsigned32,
        ompSummaryMtPeersLastuptime String,
        ompSummaryMtPeersLastdowntime String,
        ompSummaryMtPeersUpTime String,
        ompSummaryMtPeersDownTime String,
        ompSummaryMtPeersHoldtime Unsigned32,
        ompSummaryMtPeersSitepolicy String,
        ompSummaryMtPeersPolicyin String,
        ompSummaryMtPeersPolicyout String,
        ompSummaryMtPeersGracefulRestart INTEGER,
        ompSummaryMtPeersGracefulRestartInterval Unsigned32,
        ompSummaryMtPeersHelloReceived Unsigned32,
        ompSummaryMtPeersHelloSent Unsigned32,
        ompSummaryMtPeersHandshakeReceived Unsigned32,
        ompSummaryMtPeersHandshakeSent Unsigned32,
        ompSummaryMtPeersAlertReceived Unsigned32,
        ompSummaryMtPeersAlertSent Unsigned32,
        ompSummaryMtPeersInformReceived Unsigned32,
        ompSummaryMtPeersInformSent Unsigned32,
        ompSummaryMtPeersUpdateReceived Unsigned32,
        ompSummaryMtPeersUpdateSent Unsigned32,
        ompSummaryMtPeersPolicyReceived Unsigned32,
        ompSummaryMtPeersPolicySent Unsigned32,
        ompSummaryMtPeersPacketsReceived Unsigned32,
        ompSummaryMtPeersPacketsSent Unsigned32,
        ompSummaryMtPeersRoutesReceived Unsigned32,
        ompSummaryMtPeersRoutesInstalled Unsigned32,
        ompSummaryMtPeersRoutesSent Unsigned32,
        ompSummaryMtPeersTlocsReceived Unsigned32,
        ompSummaryMtPeersTlocsInstalled Unsigned32,
        ompSummaryMtPeersTlocsSent Unsigned32,
        ompSummaryMtPeersServicesReceived Unsigned32,
        ompSummaryMtPeersServicesInstalled Unsigned32,
        ompSummaryMtPeersServicesSent Unsigned32,
        ompSummaryMtPeersMcastRoutesReceived Unsigned32,
        ompSummaryMtPeersMcastRoutesInstalled Unsigned32,
        ompSummaryMtPeersMcastRoutesSent Unsigned32,
        ompSummaryMtPeersControlUp TruthValue,
        ompSummaryMtPeersStaging TruthValue,
        ompSummaryMtPeersRefresh INTEGER,
        ompSummaryMtPeersOverlayId Unsigned32,
        ompSummaryMtPeersRoutesReceivedIPv6 Unsigned32,
        ompSummaryMtPeersRoutesInstalledIPv6 Unsigned32,
        ompSummaryMtPeersRoutesSentIPv6 Unsigned32,
        ompSummaryMtPeersRoutesReceivedTotal Unsigned32,
        ompSummaryMtPeersRoutesInstalledTotal Unsigned32,
        ompSummaryMtPeersRoutesSentTotal Unsigned32,
        ompSummaryMtPeersServicesReceivedIPv6 Unsigned32,
        ompSummaryMtPeersServicesInstalledIPv6 Unsigned32,
        ompSummaryMtPeersServicesSentIPv6 Unsigned32
    }

-- tagpath /omp/summary/mt-peers/tenant-id
ompSummaryMtPeersTenantId OBJECT-TYPE
    SYNTAX      UnsignedShort
    MAX-ACCESS  not-accessible
    STATUS      current
    DESCRIPTION "Peer Tenant Id"
    ::= { ompSummaryMtPeersEntry 1 }

-- tagpath /omp/summary/mt-peers/peer
ompSummaryMtPeersPeer OBJECT-TYPE
    SYNTAX      InetAddressIP
    MAX-ACCESS  not-accessible
    STATUS      current
    DESCRIPTION "Peer address"
    ::= { ompSummaryMtPeersEntry 2 }

-- tagpath /omp/summary/mt-peers/type
ompSummaryMtPeersType OBJECT-TYPE
    SYNTAX      INTEGER {unknown(0),
                         vedge(1),
                         vhub(2),
                         vsmart(3),
                         vbond(4),
                         vmanage(5),
                         ztp(6),
                         vcontainer(7)}
    MAX-ACCESS  read-only
    STATUS      current
    DESCRIPTION "Peer personality"
    ::= { ompSummaryMtPeersEntry 3 }

-- tagpath /omp/summary/mt-peers/domain-id
ompSummaryMtPeersDomainId OBJECT-TYPE
    SYNTAX      Unsigned32 (0 .. 4294967295)
    MAX-ACCESS  read-only
    STATUS      current
    DESCRIPTION "Domain ID"
    ::= { ompSummaryMtPeersEntry 4 }

-- tagpath /omp/summary/mt-peers/site-id
ompSummaryMtPeersSiteId OBJECT-TYPE
    SYNTAX      Unsigned32
    MAX-ACCESS  read-only
    STATUS      current
    DESCRIPTION "Site ID"
    ::= { ompSummaryMtPeersEntry 5 }

-- tagpath /omp/summary/mt-peers/region-id
ompSummaryMtPeersRegionId OBJECT-TYPE
    SYNTAX      String
    MAX-ACCESS  read-only
    STATUS      current
    DESCRIPTION "Region ID"
    ::= { ompSummaryMtPeersEntry 6 }

-- tagpath /omp/summary/mt-peers/state
ompSummaryMtPeersState OBJECT-TYPE
    SYNTAX      INTEGER {invalid(0),
                         init(1),
                         handshake(2),
                         up(3),
                         down(4),
                         init-in-gr(5),
                         down-in-gr(6),
                         handshake-in-gr(7),
                         up-in-gr(8)}
    MAX-ACCESS  read-only
    STATUS      current
    DESCRIPTION "State"
    ::= { ompSummaryMtPeersEntry 7 }

-- tagpath /omp/summary/mt-peers/version
ompSummaryMtPeersVersion OBJECT-TYPE
    SYNTAX      UnsignedByte
    MAX-ACCESS  read-only
    STATUS      current
    DESCRIPTION "mt-peers version"
    ::= { ompSummaryMtPeersEntry 8 }

-- tagpath /omp/summary/mt-peers/legit
ompSummaryMtPeersLegit OBJECT-TYPE
    SYNTAX      TruthValue
    MAX-ACCESS  read-only
    STATUS      current
    DESCRIPTION "Legitimate"
    ::= { ompSummaryMtPeersEntry 9 }

-- tagpath /omp/summary/mt-peers/upcount
ompSummaryMtPeersUpcount OBJECT-TYPE
    SYNTAX      Unsigned32
    MAX-ACCESS  read-only
    STATUS      current
    DESCRIPTION "Up count"
    ::= { ompSummaryMtPeersEntry 10 }

-- tagpath /omp/summary/mt-peers/downcount
ompSummaryMtPeersDowncount OBJECT-TYPE
    SYNTAX      Unsigned32
    MAX-ACCESS  read-only
    STATUS      current
    DESCRIPTION "Down count"
    ::= { ompSummaryMtPeersEntry 11 }

-- tagpath /omp/summary/mt-peers/lastuptime-str
ompSummaryMtPeersLastuptime OBJECT-TYPE
    SYNTAX      String
    MAX-ACCESS  read-only
    STATUS      current
    DESCRIPTION "Last uptime"
    ::= { ompSummaryMtPeersEntry 12 }

-- tagpath /omp/summary/mt-peers/lastdowntime-str
ompSummaryMtPeersLastdowntime OBJECT-TYPE
    SYNTAX      String
    MAX-ACCESS  read-only
    STATUS      current
    DESCRIPTION "Last downtime"
    ::= { ompSummaryMtPeersEntry 13 }

-- tagpath /omp/summary/mt-peers/up-time-str
ompSummaryMtPeersUpTime OBJECT-TYPE
    SYNTAX      String
    MAX-ACCESS  read-only
    STATUS      current
    DESCRIPTION "Uptime"
    ::= { ompSummaryMtPeersEntry 14 }

-- tagpath /omp/summary/mt-peers/down-time-str
ompSummaryMtPeersDownTime OBJECT-TYPE
    SYNTAX      String
    MAX-ACCESS  read-only
    STATUS      current
    DESCRIPTION "Downtime"
    ::= { ompSummaryMtPeersEntry 15 }

-- tagpath /omp/summary/mt-peers/holdtime
ompSummaryMtPeersHoldtime OBJECT-TYPE
    SYNTAX      Unsigned32
    MAX-ACCESS  read-only
    STATUS      current
    DESCRIPTION "Negotiated holdtime"
    ::= { ompSummaryMtPeersEntry 16 }

-- tagpath /omp/summary/mt-peers/sitepolicy
ompSummaryMtPeersSitepolicy OBJECT-TYPE
    SYNTAX      String
    MAX-ACCESS  read-only
    STATUS      current
    DESCRIPTION "Site policy"
    ::= { ompSummaryMtPeersEntry 17 }

-- tagpath /omp/summary/mt-peers/policyin
ompSummaryMtPeersPolicyin OBJECT-TYPE
    SYNTAX      String
    MAX-ACCESS  read-only
    STATUS      current
    DESCRIPTION "Inbound policy"
    ::= { ompSummaryMtPeersEntry 18 }

-- tagpath /omp/summary/mt-peers/policyout
ompSummaryMtPeersPolicyout OBJECT-TYPE
    SYNTAX      String
    MAX-ACCESS  read-only
    STATUS      current
    DESCRIPTION "Outbound policy"
    ::= { ompSummaryMtPeersEntry 19 }

-- tagpath /omp/summary/mt-peers/graceful-restart
ompSummaryMtPeersGracefulRestart OBJECT-TYPE
    SYNTAX      INTEGER {supported(0),
                         not-supported(1),
                         in-progress(2)}
    MAX-ACCESS  read-only
    STATUS      current
    DESCRIPTION "Graceful restart status"
    ::= { ompSummaryMtPeersEntry 20 }

-- tagpath /omp/summary/mt-peers/graceful-restart-interval
ompSummaryMtPeersGracefulRestartInterval OBJECT-TYPE
    SYNTAX      Unsigned32
    MAX-ACCESS  read-only
    STATUS      current
    DESCRIPTION "Graceful restart interval"
    ::= { ompSummaryMtPeersEntry 21 }

-- tagpath /omp/summary/mt-peers/hello-received
ompSummaryMtPeersHelloReceived OBJECT-TYPE
    SYNTAX      Unsigned32
    MAX-ACCESS  read-only
    STATUS      current
    DESCRIPTION "Hello packets received"
    ::= { ompSummaryMtPeersEntry 22 }

-- tagpath /omp/summary/mt-peers/hello-sent
ompSummaryMtPeersHelloSent OBJECT-TYPE
    SYNTAX      Unsigned32
    MAX-ACCESS  read-only
    STATUS      current
    DESCRIPTION "Hello packets sent"
    ::= { ompSummaryMtPeersEntry 23 }

-- tagpath /omp/summary/mt-peers/handshake-received
ompSummaryMtPeersHandshakeReceived OBJECT-TYPE
    SYNTAX      Unsigned32
    MAX-ACCESS  read-only
    STATUS      current
    DESCRIPTION "Handshake packets received"
    ::= { ompSummaryMtPeersEntry 24 }

-- tagpath /omp/summary/mt-peers/handshake-sent
ompSummaryMtPeersHandshakeSent OBJECT-TYPE
    SYNTAX      Unsigned32
    MAX-ACCESS  read-only
    STATUS      current
    DESCRIPTION "Handshake packets sent"
    ::= { ompSummaryMtPeersEntry 25 }

-- tagpath /omp/summary/mt-peers/alert-received
ompSummaryMtPeersAlertReceived OBJECT-TYPE
    SYNTAX      Unsigned32
    MAX-ACCESS  read-only
    STATUS      current
    DESCRIPTION "Alert packets received"
    ::= { ompSummaryMtPeersEntry 26 }

-- tagpath /omp/summary/mt-peers/alert-sent
ompSummaryMtPeersAlertSent OBJECT-TYPE
    SYNTAX      Unsigned32
    MAX-ACCESS  read-only
    STATUS      current
    DESCRIPTION "Alert packets sent"
    ::= { ompSummaryMtPeersEntry 27 }

-- tagpath /omp/summary/mt-peers/inform-received
ompSummaryMtPeersInformReceived OBJECT-TYPE
    SYNTAX      Unsigned32
    MAX-ACCESS  read-only
    STATUS      current
    DESCRIPTION "Inform packets received"
    ::= { ompSummaryMtPeersEntry 28 }

-- tagpath /omp/summary/mt-peers/inform-sent
ompSummaryMtPeersInformSent OBJECT-TYPE
    SYNTAX      Unsigned32
    MAX-ACCESS  read-only
    STATUS      current
    DESCRIPTION "Inform packets sent"
    ::= { ompSummaryMtPeersEntry 29 }

-- tagpath /omp/summary/mt-peers/update-received
ompSummaryMtPeersUpdateReceived OBJECT-TYPE
    SYNTAX      Unsigned32
    MAX-ACCESS  read-only
    STATUS      current
    DESCRIPTION "Update packets received"
    ::= { ompSummaryMtPeersEntry 30 }

-- tagpath /omp/summary/mt-peers/update-sent
ompSummaryMtPeersUpdateSent OBJECT-TYPE
    SYNTAX      Unsigned32
    MAX-ACCESS  read-only
    STATUS      current
    DESCRIPTION "Update packets sent"
    ::= { ompSummaryMtPeersEntry 31 }

-- tagpath /omp/summary/mt-peers/policy-received
ompSummaryMtPeersPolicyReceived OBJECT-TYPE
    SYNTAX      Unsigned32
    MAX-ACCESS  read-only
    STATUS      current
    DESCRIPTION "Policy packets received"
    ::= { ompSummaryMtPeersEntry 32 }

-- tagpath /omp/summary/mt-peers/policy-sent
ompSummaryMtPeersPolicySent OBJECT-TYPE
    SYNTAX      Unsigned32
    MAX-ACCESS  read-only
    STATUS      current
    DESCRIPTION "Policy packets sent"
    ::= { ompSummaryMtPeersEntry 33 }

-- tagpath /omp/summary/mt-peers/packets-received
ompSummaryMtPeersPacketsReceived OBJECT-TYPE
    SYNTAX      Unsigned32
    MAX-ACCESS  read-only
    STATUS      current
    DESCRIPTION "Total OMP packets received"
    ::= { ompSummaryMtPeersEntry 34 }

-- tagpath /omp/summary/mt-peers/packets-sent
ompSummaryMtPeersPacketsSent OBJECT-TYPE
    SYNTAX      Unsigned32
    MAX-ACCESS  read-only
    STATUS      current
    DESCRIPTION "Total OMP packets sent"
    ::= { ompSummaryMtPeersEntry 35 }

-- tagpath /omp/summary/mt-peers/routes-received
ompSummaryMtPeersRoutesReceived OBJECT-TYPE
    SYNTAX      Unsigned32
    MAX-ACCESS  read-only
    STATUS      current
    DESCRIPTION "Routes received"
    ::= { ompSummaryMtPeersEntry 36 }

-- tagpath /omp/summary/mt-peers/routes-installed
ompSummaryMtPeersRoutesInstalled OBJECT-TYPE
    SYNTAX      Unsigned32
    MAX-ACCESS  read-only
    STATUS      current
    DESCRIPTION "Routes installed"
    ::= { ompSummaryMtPeersEntry 37 }

-- tagpath /omp/summary/mt-peers/routes-sent
ompSummaryMtPeersRoutesSent OBJECT-TYPE
    SYNTAX      Unsigned32
    MAX-ACCESS  read-only
    STATUS      current
    DESCRIPTION "Routes sent"
    ::= { ompSummaryMtPeersEntry 38 }

-- tagpath /omp/summary/mt-peers/tlocs-received
ompSummaryMtPeersTlocsReceived OBJECT-TYPE
    SYNTAX      Unsigned32
    MAX-ACCESS  read-only
    STATUS      current
    DESCRIPTION "TLOCs received"
    ::= { ompSummaryMtPeersEntry 39 }

-- tagpath /omp/summary/mt-peers/tlocs-installed
ompSummaryMtPeersTlocsInstalled OBJECT-TYPE
    SYNTAX      Unsigned32
    MAX-ACCESS  read-only
    STATUS      current
    DESCRIPTION "TLOCs installed"
    ::= { ompSummaryMtPeersEntry 40 }

-- tagpath /omp/summary/mt-peers/tlocs-sent
ompSummaryMtPeersTlocsSent OBJECT-TYPE
    SYNTAX      Unsigned32
    MAX-ACCESS  read-only
    STATUS      current
    DESCRIPTION "TLOCs sent"
    ::= { ompSummaryMtPeersEntry 41 }

-- tagpath /omp/summary/mt-peers/services-received
ompSummaryMtPeersServicesReceived OBJECT-TYPE
    SYNTAX      Unsigned32
    MAX-ACCESS  read-only
    STATUS      current
    DESCRIPTION "Services received"
    ::= { ompSummaryMtPeersEntry 42 }

-- tagpath /omp/summary/mt-peers/services-installed
ompSummaryMtPeersServicesInstalled OBJECT-TYPE
    SYNTAX      Unsigned32
    MAX-ACCESS  read-only
    STATUS      current
    DESCRIPTION "Services installed"
    ::= { ompSummaryMtPeersEntry 43 }

-- tagpath /omp/summary/mt-peers/services-sent
ompSummaryMtPeersServicesSent OBJECT-TYPE
    SYNTAX      Unsigned32
    MAX-ACCESS  read-only
    STATUS      current
    DESCRIPTION "Services sent"
    ::= { ompSummaryMtPeersEntry 44 }

-- tagpath /omp/summary/mt-peers/mcast-routes-received
ompSummaryMtPeersMcastRoutesReceived OBJECT-TYPE
    SYNTAX      Unsigned32
    MAX-ACCESS  read-only
    STATUS      current
    DESCRIPTION "Multicast routes received"
    ::= { ompSummaryMtPeersEntry 45 }

-- tagpath /omp/summary/mt-peers/mcast-routes-installed
ompSummaryMtPeersMcastRoutesInstalled OBJECT-TYPE
    SYNTAX      Unsigned32
    MAX-ACCESS  read-only
    STATUS      current
    DESCRIPTION "Multicast routes installed"
    ::= { ompSummaryMtPeersEntry 46 }

-- tagpath /omp/summary/mt-peers/mcast-routes-sent
ompSummaryMtPeersMcastRoutesSent OBJECT-TYPE
    SYNTAX      Unsigned32
    MAX-ACCESS  read-only
    STATUS      current
    DESCRIPTION "Multicast routes sent"
    ::= { ompSummaryMtPeersEntry 47 }

-- tagpath /omp/summary/mt-peers/control-up
ompSummaryMtPeersControlUp OBJECT-TYPE
    SYNTAX      TruthValue
    MAX-ACCESS  read-only
    STATUS      current
    DESCRIPTION "Control Up"
    ::= { ompSummaryMtPeersEntry 48 }

-- tagpath /omp/summary/mt-peers/staging
ompSummaryMtPeersStaging OBJECT-TYPE
    SYNTAX      TruthValue
    MAX-ACCESS  read-only
    STATUS      current
    DESCRIPTION "Device under staging"
    ::= { ompSummaryMtPeersEntry 49 }

-- tagpath /omp/summary/mt-peers/refresh
ompSummaryMtPeersRefresh OBJECT-TYPE
    SYNTAX      INTEGER {supported(0),not-supported(1)}
    MAX-ACCESS  read-only
    STATUS      current
    DESCRIPTION "Refresh status"
    ::= { ompSummaryMtPeersEntry 50 }

-- tagpath /omp/summary/mt-peers/overlay-id
ompSummaryMtPeersOverlayId OBJECT-TYPE
    SYNTAX      Unsigned32
    MAX-ACCESS  read-only
    STATUS      current
    DESCRIPTION "Overlay ID"
    ::= { ompSummaryMtPeersEntry 51 }

-- tagpath /omp/summary/mt-peers/routes-received-ipv6
ompSummaryMtPeersRoutesReceivedIPv6 OBJECT-TYPE
    SYNTAX      Unsigned32
    MAX-ACCESS  read-only
    STATUS      current
    DESCRIPTION "Routes received for IPv6"
    ::= { ompSummaryMtPeersEntry 52 }

-- tagpath /omp/summary/mt-peers/routes-installed-ipv6
ompSummaryMtPeersRoutesInstalledIPv6 OBJECT-TYPE
    SYNTAX      Unsigned32
    MAX-ACCESS  read-only
    STATUS      current
    DESCRIPTION "Routes installed for IPv6"
    ::= { ompSummaryMtPeersEntry 53 }

-- tagpath /omp/summary/mt-peers/routes-sent-ipv6
ompSummaryMtPeersRoutesSentIPv6 OBJECT-TYPE
    SYNTAX      Unsigned32
    MAX-ACCESS  read-only
    STATUS      current
    DESCRIPTION "Routes sent for IPv6"
    ::= { ompSummaryMtPeersEntry 54 }

-- tagpath /omp/summary/mt-peers/routes-received-total
ompSummaryMtPeersRoutesReceivedTotal OBJECT-TYPE
    SYNTAX      Unsigned32
    MAX-ACCESS  read-only
    STATUS      current
    DESCRIPTION "Routes received total"
    ::= { ompSummaryMtPeersEntry 55 }

-- tagpath /omp/summary/mt-peers/routes-installed-total
ompSummaryMtPeersRoutesInstalledTotal OBJECT-TYPE
    SYNTAX      Unsigned32
    MAX-ACCESS  read-only
    STATUS      current
    DESCRIPTION "Routes installed total"
    ::= { ompSummaryMtPeersEntry 56 }

-- tagpath /omp/summary/mt-peers/routes-sent-total
ompSummaryMtPeersRoutesSentTotal OBJECT-TYPE
    SYNTAX      Unsigned32
    MAX-ACCESS  read-only
    STATUS      current
    DESCRIPTION "Routes sent total"
    ::= { ompSummaryMtPeersEntry 57 }

-- tagpath /omp/summary/mt-peers/services-received-ipv6
ompSummaryMtPeersServicesReceivedIPv6 OBJECT-TYPE
    SYNTAX      Unsigned32
    MAX-ACCESS  read-only
    STATUS      current
    DESCRIPTION "Services IPv6 received"
    ::= { ompSummaryMtPeersEntry 58 }

-- tagpath /omp/summary/mt-peers/services-installed-ipv6
ompSummaryMtPeersServicesInstalledIPv6 OBJECT-TYPE
    SYNTAX      Unsigned32
    MAX-ACCESS  read-only
    STATUS      current
    DESCRIPTION "Services IPv6 installed"
    ::= { ompSummaryMtPeersEntry 59 }

-- tagpath /omp/summary/mt-peers/services-sent-ipv6
ompSummaryMtPeersServicesSentIPv6 OBJECT-TYPE
    SYNTAX      Unsigned32
    MAX-ACCESS  read-only
    STATUS      current
    DESCRIPTION "Services IPv6 sent"
    ::= { ompSummaryMtPeersEntry 60 }

-- Display routes
-- tagpath /omp/routes-table
ompRoutesTable OBJECT IDENTIFIER ::= { ciscoSdwanOmpMIBObjects 3 }

-- Display best-match route
-- tagpath /omp/best-match-route
ompBestMatchRoute OBJECT IDENTIFIER ::= { ciscoSdwanOmpMIBObjects 4 }

-- Display TLOC Paths
-- tagpath /omp/tloc-paths
ompTlocPaths OBJECT IDENTIFIER ::= { ciscoSdwanOmpMIBObjects 5 }

-- Display TLOCs
-- tagpath /omp/omp-tlocs
ompTlocs OBJECT IDENTIFIER ::= { ciscoSdwanOmpMIBObjects 6 }

-- Display services
-- tagpath /omp/services
ompServices OBJECT IDENTIFIER ::= { ciscoSdwanOmpMIBObjects 7 }

-- Display Auto-Discovered Multicast Routes
-- tagpath /omp/multicast-auto-discover
ompMulticastAutoDiscover OBJECT IDENTIFIER ::= 
                             { ciscoSdwanOmpMIBObjects 8 }

-- Display Multicast Joins
-- tagpath /omp/multicast-routes
ompMulticastRoutes OBJECT IDENTIFIER ::= { ciscoSdwanOmpMIBObjects 9 }

-- Display cloudexpress gateway applications Routes
-- tagpath /omp/cloudexpress
ompCloudexpressRoutes OBJECT IDENTIFIER ::= 
                            { ciscoSdwanOmpMIBObjects 10 }

-- tagpath /omp/routes-table/family
ompRoutesTableFamilyTable OBJECT-TYPE
    SYNTAX      SEQUENCE OF OmpRoutesTableFamilyEntry
    MAX-ACCESS  not-accessible
    STATUS      current
    DESCRIPTION "OMP route table family table"
    ::= { ompRoutesTable 1 }

-- tagpath /omp/routes-table/family
ompRoutesTableFamilyEntry OBJECT-TYPE
    SYNTAX      OmpRoutesTableFamilyEntry
    MAX-ACCESS  not-accessible
    STATUS      current
    DESCRIPTION "OMP route table family table entry"
    INDEX { ompRoutesTableFamilyAddressFamily }
        ::= { ompRoutesTableFamilyTable 1 }

OmpRoutesTableFamilyEntry ::=
    SEQUENCE {
        ompRoutesTableFamilyAddressFamily AddrFamilyEnum
    }

-- tagpath /omp/routes-table/family/address-family
ompRoutesTableFamilyAddressFamily OBJECT-TYPE
    SYNTAX      AddrFamilyEnum
    MAX-ACCESS  read-only
    STATUS      current
    DESCRIPTION "Address family"
    ::= { ompRoutesTableFamilyEntry 1 }

-- tagpath /omp/routes-table/family/entries
ompRoutesTableFamilyEntriesTable OBJECT-TYPE
    SYNTAX      SEQUENCE OF OmpRoutesTableFamilyEntriesEntry
    MAX-ACCESS  not-accessible
    STATUS      current
    DESCRIPTION "OMP route table entries table"
    ::= { ompRoutesTable 2 }

-- tagpath /omp/routes-table/family/entries
ompRoutesTableFamilyEntriesEntry OBJECT-TYPE
    SYNTAX      OmpRoutesTableFamilyEntriesEntry
    MAX-ACCESS  not-accessible
    STATUS      current
    DESCRIPTION "OMP route table entries table"
    INDEX { ompRoutesTableFamilyAddressFamily, 
            ompRoutesTableFamilyEntriesTenantId, 
            ompRoutesTableFamilyEntriesVpnId, 
            ompRoutesTableFamilyEntriesPrefix }
        ::= { ompRoutesTableFamilyEntriesTable 1 }

OmpRoutesTableFamilyEntriesEntry ::=
    SEQUENCE {
        ompRoutesTableFamilyEntriesTenantId Unsigned32,
        ompRoutesTableFamilyEntriesVpnId Unsigned32,
        ompRoutesTableFamilyEntriesPrefix IpPrefix
    }

-- tagpath /omp/routes-table/family/entries/tenant-id
ompRoutesTableFamilyEntriesTenantId OBJECT-TYPE
    SYNTAX      Unsigned32
    MAX-ACCESS  read-only
    STATUS      current
    DESCRIPTION "Tenant ID"
    ::= { ompRoutesTableFamilyEntriesEntry 1 }

-- tagpath /omp/routes-table/family/entries/vpn-id
ompRoutesTableFamilyEntriesVpnId OBJECT-TYPE
    SYNTAX      Unsigned32 (0 .. 65530)
    MAX-ACCESS  read-only
    STATUS      current
    DESCRIPTION "VPN ID"
    ::= { ompRoutesTableFamilyEntriesEntry 2 }

-- tagpath /omp/routes-table/family/entries/prefix
ompRoutesTableFamilyEntriesPrefix OBJECT-TYPE
    SYNTAX      IpPrefix
    MAX-ACCESS  read-only
    STATUS      current
    DESCRIPTION "Prefix"
    ::= { ompRoutesTableFamilyEntriesEntry 3 }

-- tagpath /omp/routes-table/family/entries/received
ompRoutesTableFamilyEntriesReceivedTable OBJECT-TYPE
    SYNTAX      SEQUENCE OF OmpRoutesTableFamilyEntriesReceivedEntry
    MAX-ACCESS  not-accessible
    STATUS      current
    DESCRIPTION "OMP received routes table"
    ::= { ompRoutesTable 3 }

-- tagpath /omp/routes-table/family/entries/received
ompRoutesTableFamilyEntriesReceivedEntry OBJECT-TYPE
    SYNTAX      OmpRoutesTableFamilyEntriesReceivedEntry
    MAX-ACCESS  not-accessible
    STATUS      current
    DESCRIPTION "OMP received routes table"
    INDEX { ompRoutesTableFamilyAddressFamily, 
            ompRoutesTableFamilyEntriesTenantId, 
            ompRoutesTableFamilyEntriesVpnId, 
            ompRoutesTableFamilyEntriesPrefix, 
            ompRoutesTableFamilyEntriesReceivedFromPeer, 
            ompRoutesTableFamilyEntriesReceivedPathId }
        ::= { ompRoutesTableFamilyEntriesReceivedTable 1 }

OmpRoutesTableFamilyEntriesReceivedEntry ::=
    SEQUENCE {
        ompRoutesTableFamilyEntriesReceivedFromPeer InetAddressIP,
        ompRoutesTableFamilyEntriesReceivedPathId Unsigned32,
        ompRoutesTableFamilyEntriesReceivedLabel Unsigned32,
        ompRoutesTableFamilyEntriesReceivedStatus RibInStatusType,
        ompRoutesTableFamilyEntriesReceivedLossReason LossReasonEnum,
        ompRoutesTableFamilyEntriesReceivedLostToPeer InetAddressIP,
        ompRoutesTableFamilyEntriesReceivedLostToPathId Unsigned32
    }

-- tagpath /omp/routes-table/family/entries/received/from-peer
ompRoutesTableFamilyEntriesReceivedFromPeer OBJECT-TYPE
    SYNTAX      InetAddressIP
    MAX-ACCESS  not-accessible
    STATUS      current
    DESCRIPTION "From peer IP"
    ::= { ompRoutesTableFamilyEntriesReceivedEntry 1 }

-- tagpath /omp/routes-table/family/entries/received/path-id
ompRoutesTableFamilyEntriesReceivedPathId OBJECT-TYPE
    SYNTAX      Unsigned32
    MAX-ACCESS  not-accessible
    STATUS      current
    DESCRIPTION "Path ID"
    ::= { ompRoutesTableFamilyEntriesReceivedEntry 2 }

-- tagpath /omp/routes-table/family/entries/received/label
ompRoutesTableFamilyEntriesReceivedLabel OBJECT-TYPE
    SYNTAX      Unsigned32
    MAX-ACCESS  read-only
    STATUS      current
    DESCRIPTION "Label"
    ::= { ompRoutesTableFamilyEntriesReceivedEntry 3 }

-- tagpath /omp/routes-table/family/entries/received/status
ompRoutesTableFamilyEntriesReceivedStatus OBJECT-TYPE
    SYNTAX      RibInStatusType
    MAX-ACCESS  read-only
    STATUS      current
    DESCRIPTION "RIB-in status"
    ::= { ompRoutesTableFamilyEntriesReceivedEntry 4 }

-- tagpath /omp/routes-table/family/entries/received/loss-reason
ompRoutesTableFamilyEntriesReceivedLossReason OBJECT-TYPE
    SYNTAX      LossReasonEnum
    MAX-ACCESS  read-only
    STATUS      current
    DESCRIPTION "Loss reason"
    ::= { ompRoutesTableFamilyEntriesReceivedEntry 5 }

-- tagpath /omp/routes-table/family/entries/received/lost-to-peer
ompRoutesTableFamilyEntriesReceivedLostToPeer OBJECT-TYPE
    SYNTAX      InetAddressIP
    MAX-ACCESS  read-only
    STATUS      current
    DESCRIPTION "Lost peer IP"
    ::= { ompRoutesTableFamilyEntriesReceivedEntry 6 }

-- tagpath /omp/routes-table/family/entries/received/lost-to-path-id
ompRoutesTableFamilyEntriesReceivedLostToPathId OBJECT-TYPE
    SYNTAX      Unsigned32
    MAX-ACCESS  read-only
    STATUS      current
    DESCRIPTION "Lost to path ID"
    ::= { ompRoutesTableFamilyEntriesReceivedEntry 7 }

-- tagpath /omp/routes-table/family/entries/received/attributes
ompRoutesTableFamilyEntriesReceivedAttributesTable OBJECT-TYPE
    SYNTAX      SEQUENCE OF 
             OmpRoutesTableFamilyEntriesReceivedAttributesEntry
    MAX-ACCESS  not-accessible
    STATUS      current
    DESCRIPTION "OMP received routes attributes table"
    ::= { ompRoutesTable 4 }

-- tagpath /omp/routes-table/family/entries/received/attributes
ompRoutesTableFamilyEntriesReceivedAttributesEntry OBJECT-TYPE
    SYNTAX      OmpRoutesTableFamilyEntriesReceivedAttributesEntry
    MAX-ACCESS  not-accessible
    STATUS      current
    DESCRIPTION "OMP received routes attributes table"
    INDEX { ompRoutesTableFamilyAddressFamily, 
            ompRoutesTableFamilyEntriesTenantId, 
            ompRoutesTableFamilyEntriesVpnId, 
            ompRoutesTableFamilyEntriesPrefix, 
            ompRoutesTableFamilyEntriesReceivedFromPeer, 
            ompRoutesTableFamilyEntriesReceivedPathId, 
            ompRoutesTableFamilyEntriesReceivedAttributesAttributeType }
        ::= { ompRoutesTableFamilyEntriesReceivedAttributesTable 1 }

OmpRoutesTableFamilyEntriesReceivedAttributesEntry ::=
    SEQUENCE {
  ompRoutesTableFamilyEntriesReceivedAttributesAttributeType 
                                                 AttributeTypeEnum,
  ompRoutesTableFamilyEntriesReceivedAttributesTlocIp 
                                                 InetAddressIP,
  ompRoutesTableFamilyEntriesReceivedAttributesTlocColor 
                                                 TlocColorEnum,
  ompRoutesTableFamilyEntriesReceivedAttributesTlocEncap 
                                                 TlocEncapEnum,
  ompRoutesTableFamilyEntriesReceivedAttributesOriginProtocol 
                                                 ProtocolEnum,
  ompRoutesTableFamilyEntriesReceivedAttributesOriginMetric 
                                                 Unsigned32,
  ompRoutesTableFamilyEntriesReceivedAttributesDomainId 
                                                 Unsigned32,
  ompRoutesTableFamilyEntriesReceivedAttributesSiteId 
                                                 Unsigned32,
  ompRoutesTableFamilyEntriesReceivedAttributesPreference 
                                                 Unsigned32,
  ompRoutesTableFamilyEntriesReceivedAttributesTag 
                                                 Unsigned32,
  ompRoutesTableFamilyEntriesReceivedAttributesUnknownAttributeLen 
                                                 UnsignedShort,
  ompRoutesTableFamilyEntriesReceivedAttributesOriginator 
                                                 InetAddressIP,
  ompRoutesTableFamilyEntriesReceivedAttributesUltimateTlocIp 
                                                 InetAddressIP,
  ompRoutesTableFamilyEntriesReceivedAttributesUltimateTlocColor 
                                                 TlocColorEnum,
  ompRoutesTableFamilyEntriesReceivedAttributesUltimateTlocEncap 
                                                 TlocEncapEnum,
  ompRoutesTableFamilyEntriesReceivedAttributesUltimateTlocAction 
                                                 TlocActionEnum,
  ompRoutesTableFamilyEntriesReceivedAttributesOverlayId 
                                                 Unsigned32,
  ompRoutesTableFamilyEntriesReceivedAttributesAsPath String,
  ompRoutesTableFamilyEntriesReceivedAttributesCommunity String,
  ompRoutesTableFamilyEntriesReceivedAttributesRegionId String,
  ompRoutesTableFamilyEntriesReceivedAttributesRegionPath String
    }

-- tagpath /omp/routes-table/family/entries/received/
-- attributes/attribute-type
ompRoutesTableFamilyEntriesReceivedAttributesAttributeType OBJECT-TYPE
    SYNTAX      AttributeTypeEnum
    MAX-ACCESS  not-accessible
    STATUS      current
    DESCRIPTION "Attribute type"
    ::= { ompRoutesTableFamilyEntriesReceivedAttributesEntry 1 }

-- tagpath /omp/routes-table/family/entries/received/attributes/tloc/ip
ompRoutesTableFamilyEntriesReceivedAttributesTlocIp OBJECT-TYPE
    SYNTAX      InetAddressIP
    MAX-ACCESS  read-only
    STATUS      current
    DESCRIPTION "TLOC IP address"
    ::= { ompRoutesTableFamilyEntriesReceivedAttributesEntry 2 }

-- tagpath /omp/routes-table/family/entries/received/attributes/
-- tloc/color
ompRoutesTableFamilyEntriesReceivedAttributesTlocColor OBJECT-TYPE
    SYNTAX      TlocColorEnum
    MAX-ACCESS  read-only
    STATUS      current
    DESCRIPTION "TLOC Color"
    ::= { ompRoutesTableFamilyEntriesReceivedAttributesEntry 3 }

-- tagpath /omp/routes-table/family/entries/received/attributes/
-- tloc/encap
ompRoutesTableFamilyEntriesReceivedAttributesTlocEncap OBJECT-TYPE
    SYNTAX      TlocEncapEnum
    MAX-ACCESS  read-only
    STATUS      current
    DESCRIPTION "TLOC Encapsulation"
    ::= { ompRoutesTableFamilyEntriesReceivedAttributesEntry 4 }

-- tagpath /omp/routes-table/family/entries/received/attributes/
-- origin/protocol
ompRoutesTableFamilyEntriesReceivedAttributesOriginProtocol OBJECT-TYPE
    SYNTAX      ProtocolEnum
    MAX-ACCESS  read-only
    STATUS      current
    DESCRIPTION "Origin protocol"
    ::= { ompRoutesTableFamilyEntriesReceivedAttributesEntry 5 }

-- tagpath /omp/routes-table/family/entries/received/attributes/
-- origin/metric
ompRoutesTableFamilyEntriesReceivedAttributesOriginMetric OBJECT-TYPE
    SYNTAX      Unsigned32
    MAX-ACCESS  read-only
    STATUS      current
    DESCRIPTION "Origin metric"
    ::= { ompRoutesTableFamilyEntriesReceivedAttributesEntry 6 }

-- tagpath /omp/routes-table/family/entries/received/attributes/
-- domain-id
ompRoutesTableFamilyEntriesReceivedAttributesDomainId OBJECT-TYPE
    SYNTAX      Unsigned32 (0 .. 4294967295)
    MAX-ACCESS  read-only
    STATUS      current
    DESCRIPTION "Domain ID"
    ::= { ompRoutesTableFamilyEntriesReceivedAttributesEntry 7 }

-- tagpath /omp/routes-table/family/entries/received/attributes/site-id
ompRoutesTableFamilyEntriesReceivedAttributesSiteId OBJECT-TYPE
    SYNTAX      Unsigned32
    MAX-ACCESS  read-only
    STATUS      current
    DESCRIPTION "Site ID"
    ::= { ompRoutesTableFamilyEntriesReceivedAttributesEntry 8 }

-- tagpath /omp/routes-table/family/entries/received/attributes/
-- preference
ompRoutesTableFamilyEntriesReceivedAttributesPreference OBJECT-TYPE
    SYNTAX      Unsigned32
    MAX-ACCESS  read-only
    STATUS      current
    DESCRIPTION "Preference"
    ::= { ompRoutesTableFamilyEntriesReceivedAttributesEntry 9 }

-- tagpath /omp/routes-table/family/entries/received/attributes/tag
ompRoutesTableFamilyEntriesReceivedAttributesTag OBJECT-TYPE
    SYNTAX      Unsigned32
    MAX-ACCESS  read-only
    STATUS      current
    DESCRIPTION "Tag"
    ::= { ompRoutesTableFamilyEntriesReceivedAttributesEntry 10 }

-- tagpath /omp/routes-table/family/entries/received/attributes/
-- unknown-attribute-len
ompRoutesTableFamilyEntriesReceivedAttributesUnknownAttributeLen 
                                                       OBJECT-TYPE
    SYNTAX      UnsignedShort
    MAX-ACCESS  read-only
    STATUS      current
    DESCRIPTION "Unknown attribute length"
    ::= { ompRoutesTableFamilyEntriesReceivedAttributesEntry 11 }

-- tagpath /omp/routes-table/family/entries/received/attributes/
-- originator
ompRoutesTableFamilyEntriesReceivedAttributesOriginator OBJECT-TYPE
    SYNTAX      InetAddressIP
    MAX-ACCESS  read-only
    STATUS      current
    DESCRIPTION "Originator"
    ::= { ompRoutesTableFamilyEntriesReceivedAttributesEntry 12 }

-- tagpath /omp/routes-table/family/entries/received/attributes/
-- ultimate-tloc/ip
ompRoutesTableFamilyEntriesReceivedAttributesUltimateTlocIp OBJECT-TYPE
    SYNTAX      InetAddressIP
    MAX-ACCESS  read-only
    STATUS      current
    DESCRIPTION "Ultimate TLOC IP address"
    ::= { ompRoutesTableFamilyEntriesReceivedAttributesEntry 13 }

-- tagpath /omp/routes-table/family/entries/received/attributes/
-- ultimate-tloc/color
ompRoutesTableFamilyEntriesReceivedAttributesUltimateTlocColor
                                                   OBJECT-TYPE
    SYNTAX      TlocColorEnum
    MAX-ACCESS  read-only
    STATUS      current
    DESCRIPTION "Ultimate TLOC color"
    ::= { ompRoutesTableFamilyEntriesReceivedAttributesEntry 14 }

-- tagpath /omp/routes-table/family/entries/received/attributes/
-- ultimate-tloc/encap
ompRoutesTableFamilyEntriesReceivedAttributesUltimateTlocEncap
                                                   OBJECT-TYPE
    SYNTAX      TlocEncapEnum
    MAX-ACCESS  read-only
    STATUS      current
    DESCRIPTION "Ultimate TLOC encapsulation"
    ::= { ompRoutesTableFamilyEntriesReceivedAttributesEntry 15 }

-- tagpath /omp/routes-table/family/entries/received/attributes/
-- ultimate-tloc-action
ompRoutesTableFamilyEntriesReceivedAttributesUltimateTlocAction
                                                    OBJECT-TYPE
    SYNTAX      TlocActionEnum
    MAX-ACCESS  read-only
    STATUS      current
    DESCRIPTION "Ultimate TLOC action to indicate if packets should be 
                 forwarded only via intermediate TLOC or fallback to 
                 ultimate TLOC"
    ::= { ompRoutesTableFamilyEntriesReceivedAttributesEntry 16 }

-- tagpath /omp/routes-table/family/entries/received/attributes/
-- overlay-id
ompRoutesTableFamilyEntriesReceivedAttributesOverlayId OBJECT-TYPE
    SYNTAX      Unsigned32
    MAX-ACCESS  read-only
    STATUS      current
    DESCRIPTION "Overlay ID"
    ::= { ompRoutesTableFamilyEntriesReceivedAttributesEntry 17 }

-- tagpath /omp/routes-table/family/entries/received/attributes/as-path
ompRoutesTableFamilyEntriesReceivedAttributesAsPath OBJECT-TYPE
    SYNTAX      String
    MAX-ACCESS  read-only
    STATUS      current
    DESCRIPTION "AS Path"
    ::= { ompRoutesTableFamilyEntriesReceivedAttributesEntry 18 }

-- tagpath /omp/routes-table/family/entries/received/attributes/
-- community
ompRoutesTableFamilyEntriesReceivedAttributesCommunity OBJECT-TYPE
    SYNTAX      String
    MAX-ACCESS  read-only
    STATUS      current
    DESCRIPTION "Community"
    ::= { ompRoutesTableFamilyEntriesReceivedAttributesEntry 19 }

-- tagpath /omp/routes-table/family/entries/received/attributes/
-- region_id
ompRoutesTableFamilyEntriesReceivedAttributesRegionId OBJECT-TYPE
    SYNTAX      String
    MAX-ACCESS  read-only
    STATUS      current
    DESCRIPTION "Region ID"
    ::= { ompRoutesTableFamilyEntriesReceivedAttributesEntry 20 }

-- tagpath /omp/routes-table/family/entries/received/attributes/
-- region_path
ompRoutesTableFamilyEntriesReceivedAttributesRegionPath OBJECT-TYPE
    SYNTAX      String
    MAX-ACCESS  read-only
    STATUS      current
    DESCRIPTION "Region path"
    ::= { ompRoutesTableFamilyEntriesReceivedAttributesEntry 21 }

-- tagpath /omp/routes-table/family/entries/advertised
ompRoutesTableFamilyEntriesAdvertisedTable OBJECT-TYPE
    SYNTAX      SEQUENCE OF OmpRoutesTableFamilyEntriesAdvertisedEntry
    MAX-ACCESS  not-accessible
    STATUS      current
    DESCRIPTION "OMP advertised routes table"
    ::= { ompRoutesTable 5 }

-- tagpath /omp/routes-table/family/entries/advertised
ompRoutesTableFamilyEntriesAdvertisedEntry OBJECT-TYPE
    SYNTAX      OmpRoutesTableFamilyEntriesAdvertisedEntry
    MAX-ACCESS  not-accessible
    STATUS      current
    DESCRIPTION "OMP advertised routes table"
    INDEX { ompRoutesTableFamilyAddressFamily, 
            ompRoutesTableFamilyEntriesTenantId, 
            ompRoutesTableFamilyEntriesVpnId, 
            ompRoutesTableFamilyEntriesPrefix, 
            ompRoutesTableFamilyEntriesAdvertisedToPeer }
        ::= { ompRoutesTableFamilyEntriesAdvertisedTable 1 }

OmpRoutesTableFamilyEntriesAdvertisedEntry ::=
    SEQUENCE {
        ompRoutesTableFamilyEntriesAdvertisedToPeer InetAddressIP
    }

-- tagpath /omp/routes-table/family/entries/advertised/to-peer
ompRoutesTableFamilyEntriesAdvertisedToPeer OBJECT-TYPE
    SYNTAX      InetAddressIP
    MAX-ACCESS  read-only
    STATUS      current
    DESCRIPTION " To peer IP"
    ::= { ompRoutesTableFamilyEntriesAdvertisedEntry 1 }

-- tagpath /omp/routes-table/family/entries/advertised/paths
ompRoutesTableFamilyEntriesAdvertisedPathsTable OBJECT-TYPE
    SYNTAX      SEQUENCE OF 
            OmpRoutesTableFamilyEntriesAdvertisedPathsEntry
    MAX-ACCESS  not-accessible
    STATUS      current
    DESCRIPTION "OMP advertised paths table"
    ::= { ompRoutesTable 6 }

-- tagpath /omp/routes-table/family/entries/advertised/paths
ompRoutesTableFamilyEntriesAdvertisedPathsEntry OBJECT-TYPE
    SYNTAX      OmpRoutesTableFamilyEntriesAdvertisedPathsEntry
    MAX-ACCESS  not-accessible
    STATUS      current
    DESCRIPTION "OMP advertised paths table"
    INDEX { ompRoutesTableFamilyAddressFamily, 
            ompRoutesTableFamilyEntriesTenantId, 
            ompRoutesTableFamilyEntriesVpnId, 
            ompRoutesTableFamilyEntriesPrefix, 
            ompRoutesTableFamilyEntriesAdvertisedToPeer, 
            ompRoutesTableFamilyEntriesAdvertisedPathsAdvertiseId }
        ::= { ompRoutesTableFamilyEntriesAdvertisedPathsTable 1 }

OmpRoutesTableFamilyEntriesAdvertisedPathsEntry ::=
    SEQUENCE {
        ompRoutesTableFamilyEntriesAdvertisedPathsAdvertiseId Unsigned32
    }

-- tagpath /omp/routes-table/family/entries/advertised/paths/
-- advertise-id
ompRoutesTableFamilyEntriesAdvertisedPathsAdvertiseId OBJECT-TYPE
    SYNTAX      Unsigned32
    MAX-ACCESS  read-only
    STATUS      current
    DESCRIPTION "Advertise ID"
    ::= { ompRoutesTableFamilyEntriesAdvertisedPathsEntry 1 }

-- tagpath /omp/routes-table/family/entries/advertised/paths/attributes
ompRoutesTableFamilyEntriesAdvertisedPathsAttributesTable OBJECT-TYPE
    SYNTAX      SEQUENCE OF 
             OmpRoutesTableFamilyEntriesAdvertisedPathsAttributesEntry
    MAX-ACCESS  not-accessible
    STATUS      current
    DESCRIPTION "OMP advertised routes attributes table"
    ::= { ompRoutesTable 7 }

-- tagpath /omp/routes-table/family/entries/advertised/paths/attributes
ompRoutesTableFamilyEntriesAdvertisedPathsAttributesEntry OBJECT-TYPE
    SYNTAX    OmpRoutesTableFamilyEntriesAdvertisedPathsAttributesEntry
    MAX-ACCESS  not-accessible
    STATUS      current
    DESCRIPTION "OMP advertised routes attributes table"
    INDEX { ompRoutesTableFamilyAddressFamily, 
            ompRoutesTableFamilyEntriesTenantId, 
            ompRoutesTableFamilyEntriesVpnId, 
            ompRoutesTableFamilyEntriesPrefix, 
            ompRoutesTableFamilyEntriesAdvertisedToPeer, 
            ompRoutesTableFamilyEntriesAdvertisedPathsAdvertiseId, 
            ompRoutesTableFamilyEntriesAdvertisedPathsAttributesPathId }
    ::= { ompRoutesTableFamilyEntriesAdvertisedPathsAttributesTable 1 }

OmpRoutesTableFamilyEntriesAdvertisedPathsAttributesEntry ::=
    SEQUENCE {
  ompRoutesTableFamilyEntriesAdvertisedPathsAttributesPathId 
                                                     Unsigned32,
  ompRoutesTableFamilyEntriesAdvertisedPathsAttributesLabel 
                                                     Unsigned32,
  ompRoutesTableFamilyEntriesAdvertisedPathsAttributesTlocIp 
                                                     InetAddressIP,
  ompRoutesTableFamilyEntriesAdvertisedPathsAttributesTlocColor 
                                                     TlocColorEnum,
  ompRoutesTableFamilyEntriesAdvertisedPathsAttributesTlocEncap 
                                                     TlocEncapEnum,
  ompRoutesTableFamilyEntriesAdvertisedPathsAttrbOrgProto 
                                                     ProtocolEnum,
  ompRoutesTableFamilyEntriesAdvertisedPathsAttributesOriginMetric 
                                                     Unsigned32,
  ompRoutesTableFamilyEntriesAdvertisedPathsAttributesDomainId 
                                                     Unsigned32,
  ompRoutesTableFamilyEntriesAdvertisedPathsAttributesSiteId 
                                                     Unsigned32,
  ompRoutesTableFamilyEntriesAdvertisedPathsAttributesPreference 
                                                     Unsigned32,
  ompRoutesTableFamilyEntriesAdvertisedPathsAttributesTag 
                                                     Unsigned32,
  ompRoutesTableFamilyEntriesAdvertisedPathsAttrbUnkAttrbLen 
                                                     UnsignedShort,
  ompRoutesTableFamilyEntriesAdvertisedPathsAttributesOriginator 
                                                     InetAddressIP,
  ompRoutesTableFamilyEntriesAdvertisedPathsAttrUltTlocIp 
                                                     InetAddressIP,
  ompRoutesTableFamilyEntriesAdvertisedPathsAttrUltTlocColor 
                                                     TlocColorEnum,
  ompRoutesTableFamilyEntriesAdvertisedPathsAttrUltTlocEncap 
                                                     TlocEncapEnum,
  ompRoutesTableFamilyEntriesAdvertisedPathsAttrUltTlocAction 
                                                     TlocActionEnum,
  ompRoutesTableFamilyEntriesAdvertisedPathsAttributesOverlayId 
                                                     Unsigned32,
  ompRoutesTableFamilyEntriesAdvertisedPathsAttributesAsPath String,
  ompRoutesTableFamilyEntriesAdvertisedPathsAttributesCommunity String,
  ompRoutesTableFamilyEntriesAdvertisedPathsAttributesRegionId String,
  ompRoutesTableFamilyEntriesAdvertisedPathsAttributesRegionPath String
    }

-- tagpath /omp/routes-table/family/entries/advertised/paths/
-- attributes/path-id
ompRoutesTableFamilyEntriesAdvertisedPathsAttributesPathId OBJECT-TYPE
    SYNTAX      Unsigned32
    MAX-ACCESS  not-accessible
    STATUS      current
    DESCRIPTION "Path ID"
    ::= { ompRoutesTableFamilyEntriesAdvertisedPathsAttributesEntry 1 }

-- tagpath /omp/routes-table/family/entries/advertised/paths/
-- attributes/label
ompRoutesTableFamilyEntriesAdvertisedPathsAttributesLabel OBJECT-TYPE
    SYNTAX      Unsigned32
    MAX-ACCESS  read-only
    STATUS      current
    DESCRIPTION "label"
    ::= { ompRoutesTableFamilyEntriesAdvertisedPathsAttributesEntry 2 }

-- tagpath /omp/routes-table/family/entries/advertised/paths/attributes/
-- tloc/ip
ompRoutesTableFamilyEntriesAdvertisedPathsAttributesTlocIp OBJECT-TYPE
    SYNTAX      InetAddressIP
    MAX-ACCESS  read-only
    STATUS      current
    DESCRIPTION "TLOC IP address"
    ::= { ompRoutesTableFamilyEntriesAdvertisedPathsAttributesEntry 3 }

-- tagpath /omp/routes-table/family/entries/advertised/paths/attributes/
-- tloc/color
ompRoutesTableFamilyEntriesAdvertisedPathsAttributesTlocColor 
                                                  OBJECT-TYPE
    SYNTAX      TlocColorEnum
    MAX-ACCESS  read-only
    STATUS      current
    DESCRIPTION "TLOC color"
    ::= { ompRoutesTableFamilyEntriesAdvertisedPathsAttributesEntry 4 }

-- tagpath /omp/routes-table/family/entries/advertised/paths/attributes/
-- tloc/encap
ompRoutesTableFamilyEntriesAdvertisedPathsAttributesTlocEncap 
                                                  OBJECT-TYPE
    SYNTAX      TlocEncapEnum
    MAX-ACCESS  read-only
    STATUS      current
    DESCRIPTION "TLOC encapsulation"
    ::= { ompRoutesTableFamilyEntriesAdvertisedPathsAttributesEntry 5 }

-- tagpath /omp/routes-table/family/entries/advertised/paths/attributes/
-- origin/protocol
ompRoutesTableFamilyEntriesAdvertisedPathsAttrbOrgProto OBJECT-TYPE
    SYNTAX      ProtocolEnum
    MAX-ACCESS  read-only
    STATUS      current
    DESCRIPTION "Origin protocol"
    ::= { ompRoutesTableFamilyEntriesAdvertisedPathsAttributesEntry 6 }

-- tagpath /omp/routes-table/family/entries/advertised/paths/attributes/
-- origin/metric
ompRoutesTableFamilyEntriesAdvertisedPathsAttributesOriginMetric 
                                                     OBJECT-TYPE
    SYNTAX      Unsigned32
    MAX-ACCESS  read-only
    STATUS      current
    DESCRIPTION "Origin metric"
    ::= { ompRoutesTableFamilyEntriesAdvertisedPathsAttributesEntry 7 }

-- tagpath /omp/routes-table/family/entries/advertised/paths/attributes/
-- domain-id
ompRoutesTableFamilyEntriesAdvertisedPathsAttributesDomainId OBJECT-TYPE
    SYNTAX      Unsigned32 (0 .. 4294967295)
    MAX-ACCESS  read-only
    STATUS      current
    DESCRIPTION "Domain ID"
    ::= { ompRoutesTableFamilyEntriesAdvertisedPathsAttributesEntry 8 }

-- tagpath /omp/routes-table/family/entries/advertised/paths/attributes/
-- site-id
ompRoutesTableFamilyEntriesAdvertisedPathsAttributesSiteId OBJECT-TYPE
    SYNTAX      Unsigned32
    MAX-ACCESS  read-only
    STATUS      current
    DESCRIPTION "Site ID"
    ::= { ompRoutesTableFamilyEntriesAdvertisedPathsAttributesEntry 9 }

-- tagpath /omp/routes-table/family/entries/advertised/paths/attributes/
-- preference
ompRoutesTableFamilyEntriesAdvertisedPathsAttributesPreference 
                                                   OBJECT-TYPE
    SYNTAX      Unsigned32
    MAX-ACCESS  read-only
    STATUS      current
    DESCRIPTION "Preference"
    ::= { ompRoutesTableFamilyEntriesAdvertisedPathsAttributesEntry 10 }

-- tagpath /omp/routes-table/family/entries/advertised/paths/attributes/
-- tag
ompRoutesTableFamilyEntriesAdvertisedPathsAttributesTag OBJECT-TYPE
    SYNTAX      Unsigned32
    MAX-ACCESS  read-only
    STATUS      current
    DESCRIPTION "Tag"
    ::= { ompRoutesTableFamilyEntriesAdvertisedPathsAttributesEntry 11 }

-- tagpath /omp/routes-table/family/entries/advertised/paths/attributes/
-- unknown-attribute-len
ompRoutesTableFamilyEntriesAdvertisedPathsAttrbUnkAttrbLen OBJECT-TYPE
    SYNTAX      UnsignedShort
    MAX-ACCESS  read-only
    STATUS      current
    DESCRIPTION "Unkonwn attribute length"
    ::= { ompRoutesTableFamilyEntriesAdvertisedPathsAttributesEntry 12 }

-- tagpath /omp/routes-table/family/entries/advertised/paths/attributes/
-- originator
ompRoutesTableFamilyEntriesAdvertisedPathsAttributesOriginator 
                                                   OBJECT-TYPE
    SYNTAX      InetAddressIP
    MAX-ACCESS  read-only
    STATUS      current
    DESCRIPTION "Originator"
    ::= { ompRoutesTableFamilyEntriesAdvertisedPathsAttributesEntry 13 }

-- tagpath /omp/routes-table/family/entries/advertised/paths/attributes/
-- ultimate-tloc/ip
ompRoutesTableFamilyEntriesAdvertisedPathsAttrUltTlocIp OBJECT-TYPE
    SYNTAX      InetAddressIP
    MAX-ACCESS  read-only
    STATUS      current
    DESCRIPTION "TLOC IP address"
    ::= { ompRoutesTableFamilyEntriesAdvertisedPathsAttributesEntry 14 }

-- tagpath /omp/routes-table/family/entries/advertised/paths/attributes/
-- ultimate-tloc/color
ompRoutesTableFamilyEntriesAdvertisedPathsAttrUltTlocColor OBJECT-TYPE
    SYNTAX      TlocColorEnum
    MAX-ACCESS  read-only
    STATUS      current
    DESCRIPTION "TLOC color"
    ::= { ompRoutesTableFamilyEntriesAdvertisedPathsAttributesEntry 15 }

-- tagpath /omp/routes-table/family/entries/advertised/paths/attributes/
-- ultimate-tloc/encap
ompRoutesTableFamilyEntriesAdvertisedPathsAttrUltTlocEncap OBJECT-TYPE
    SYNTAX      TlocEncapEnum
    MAX-ACCESS  read-only
    STATUS      current
    DESCRIPTION "TLOC encapsulation"
    ::= { ompRoutesTableFamilyEntriesAdvertisedPathsAttributesEntry 16 }

-- tagpath /omp/routes-table/family/entries/advertised/paths/attributes/
-- ultimate-tloc-action
ompRoutesTableFamilyEntriesAdvertisedPathsAttrUltTlocAction OBJECT-TYPE
    SYNTAX      TlocActionEnum
    MAX-ACCESS  read-only
    STATUS      current
    DESCRIPTION "Ultimate TLOC action to indicate if packets should be
                 forwarded only via intermediate TLOC or fallback to 
                 ultimate TLOC"
    ::= { ompRoutesTableFamilyEntriesAdvertisedPathsAttributesEntry 17 }

-- tagpath /omp/routes-table/family/entries/advertised/paths/attributes/
-- overlay-id
ompRoutesTableFamilyEntriesAdvertisedPathsAttributesOverlayId 
                                                  OBJECT-TYPE
    SYNTAX      Unsigned32
    MAX-ACCESS  read-only
    STATUS      current
    DESCRIPTION "Overlay ID"
    ::= { ompRoutesTableFamilyEntriesAdvertisedPathsAttributesEntry 18 }

-- tagpath /omp/routes-table/family/entries/advertised/paths/attributes/
-- as-path
ompRoutesTableFamilyEntriesAdvertisedPathsAttributesAsPath OBJECT-TYPE
    SYNTAX      String
    MAX-ACCESS  read-only
    STATUS      current
    DESCRIPTION "As path"
    ::= { ompRoutesTableFamilyEntriesAdvertisedPathsAttributesEntry 19 }

-- tagpath /omp/routes-table/family/entries/advertised/paths/attributes/
-- community
ompRoutesTableFamilyEntriesAdvertisedPathsAttributesCommunity 
                                                  OBJECT-TYPE
    SYNTAX      String
    MAX-ACCESS  read-only
    STATUS      current
    DESCRIPTION "Community"
    ::= { ompRoutesTableFamilyEntriesAdvertisedPathsAttributesEntry 20 }

-- tagpath /omp/routes-table/family/entries/advertised/paths/attributes/
-- region_id
ompRoutesTableFamilyEntriesAdvertisedPathsAttributesRegionId 
                                                 OBJECT-TYPE
    SYNTAX      String
    MAX-ACCESS  read-only
    STATUS      current
    DESCRIPTION "Region ID"
    ::= { ompRoutesTableFamilyEntriesAdvertisedPathsAttributesEntry 21 }

-- tagpath /omp/routes-table/family/entries/advertised/paths/attributes/
-- region_path
ompRoutesTableFamilyEntriesAdvertisedPathsAttributesRegionPath 
                                                   OBJECT-TYPE
    SYNTAX      String
    MAX-ACCESS  read-only
    STATUS      current
    DESCRIPTION "Region path"
    ::= { ompRoutesTableFamilyEntriesAdvertisedPathsAttributesEntry 22 }

-- tagpath /omp/tloc-paths/entries
ompTlocPathsEntriesTable OBJECT-TYPE
    SYNTAX      SEQUENCE OF OmpTlocPathsEntriesEntry
    MAX-ACCESS  not-accessible
    STATUS      current
    DESCRIPTION "OMP TLOC paths table"
    ::= { ompTlocPaths 1 }

-- tagpath /omp/tloc-paths/entries
ompTlocPathsEntriesEntry OBJECT-TYPE
    SYNTAX      OmpTlocPathsEntriesEntry
    MAX-ACCESS  not-accessible
    STATUS      current
    DESCRIPTION "OMP TLOC paths table"
    INDEX { ompTlocPathsEntriesIp, 
            ompTlocPathsEntriesColor, 
            ompTlocPathsEntriesEncap }
        ::= { ompTlocPathsEntriesTable 1 }

OmpTlocPathsEntriesEntry ::=
    SEQUENCE {
        ompTlocPathsEntriesIp InetAddressIP,
        ompTlocPathsEntriesColor TlocColorEnum,
        ompTlocPathsEntriesEncap TlocEncapEnum
    }

-- tagpath /omp/tloc-paths/entries/ip
ompTlocPathsEntriesIp OBJECT-TYPE
    SYNTAX      InetAddressIP
    MAX-ACCESS  read-only
    STATUS      current
    DESCRIPTION "IP address"
    ::= { ompTlocPathsEntriesEntry 1 }

-- tagpath /omp/tloc-paths/entries/color
ompTlocPathsEntriesColor OBJECT-TYPE
    SYNTAX      TlocColorEnum
    MAX-ACCESS  read-only
    STATUS      current
    DESCRIPTION "Color"
    ::= { ompTlocPathsEntriesEntry 2 }

-- tagpath /omp/tloc-paths/entries/encap
ompTlocPathsEntriesEncap OBJECT-TYPE
    SYNTAX      TlocEncapEnum
    MAX-ACCESS  read-only
    STATUS      current
    DESCRIPTION "Encapsulation"
    ::= { ompTlocPathsEntriesEntry 3 }

-- tagpath /omp/tloc-paths/entries/paths
ompTlocPathsEntriesPathsTable OBJECT-TYPE
    SYNTAX      SEQUENCE OF OmpTlocPathsEntriesPathsEntry
    MAX-ACCESS  not-accessible
    STATUS      current
    DESCRIPTION "OMP TLOC paths table"
    ::= { ompTlocPaths 2 }

-- tagpath /omp/tloc-paths/entries/paths
ompTlocPathsEntriesPathsEntry OBJECT-TYPE
    SYNTAX      OmpTlocPathsEntriesPathsEntry
    MAX-ACCESS  not-accessible
    STATUS      current
    DESCRIPTION "OMP TLOC paths table"
    INDEX { ompTlocPathsEntriesIp, 
            ompTlocPathsEntriesColor, 
            ompTlocPathsEntriesEncap, 
            ompTlocPathsEntriesPathsIndex }
        ::= { ompTlocPathsEntriesPathsTable 1 }

OmpTlocPathsEntriesPathsEntry ::=
    SEQUENCE {
        ompTlocPathsEntriesPathsIndex Unsigned32,
        ompTlocPathsEntriesPathsPreference Unsigned32,
        ompTlocPathsEntriesPathsMtu Unsigned32,
        ompTlocPathsEntriesPathsBfdStatus BfdStatusEnum,
        ompTlocPathsEntriesPathsStatus PathStatusEnum,
        ompTlocPathsEntriesPathsStale TruthValue
    }

-- tagpath /omp/tloc-paths/entries/paths/index
ompTlocPathsEntriesPathsIndex OBJECT-TYPE
    SYNTAX      Unsigned32
    MAX-ACCESS  not-accessible
    STATUS      current
    DESCRIPTION "Index"
    ::= { ompTlocPathsEntriesPathsEntry 1 }

-- tagpath /omp/tloc-paths/entries/paths/preference
ompTlocPathsEntriesPathsPreference OBJECT-TYPE
    SYNTAX      Unsigned32
    MAX-ACCESS  read-only
    STATUS      current
    DESCRIPTION "Preference"
    ::= { ompTlocPathsEntriesPathsEntry 2 }

-- tagpath /omp/tloc-paths/entries/paths/mtu
ompTlocPathsEntriesPathsMtu OBJECT-TYPE
    SYNTAX      Unsigned32
    MAX-ACCESS  read-only
    STATUS      current
    DESCRIPTION "MTU"
    ::= { ompTlocPathsEntriesPathsEntry 3 }

-- tagpath /omp/tloc-paths/entries/paths/bfd-status
ompTlocPathsEntriesPathsBfdStatus OBJECT-TYPE
    SYNTAX      BfdStatusEnum
    MAX-ACCESS  read-only
    STATUS      current
    DESCRIPTION "BFD status"
    ::= { ompTlocPathsEntriesPathsEntry 4 }

-- tagpath /omp/tloc-paths/entries/paths/path-status
ompTlocPathsEntriesPathsStatus OBJECT-TYPE
    SYNTAX      PathStatusEnum
    MAX-ACCESS  read-only
    STATUS      current
    DESCRIPTION "Status"
    ::= { ompTlocPathsEntriesPathsEntry 6 }

-- tagpath /omp/tloc-paths/entries/paths/stale
ompTlocPathsEntriesPathsStale OBJECT-TYPE
    SYNTAX      TruthValue
    MAX-ACCESS  read-only
    STATUS      current
    DESCRIPTION "Stale"
    ::= { ompTlocPathsEntriesPathsEntry 7 }

-- tagpath /omp/tloc-paths/entries/paths/links
ompTlocPathsEntriesPathsLinksTable OBJECT-TYPE
    SYNTAX      SEQUENCE OF OmpTlocPathsEntriesPathsLinksEntry
    MAX-ACCESS  not-accessible
    STATUS      current
    DESCRIPTION "OMP TLOC paths links table"
    ::= { ompTlocPaths 3 }

-- tagpath /omp/tloc-paths/entries/paths/links
ompTlocPathsEntriesPathsLinksEntry OBJECT-TYPE
    SYNTAX      OmpTlocPathsEntriesPathsLinksEntry
    MAX-ACCESS  not-accessible
    STATUS      current
    DESCRIPTION "OMP TLOC paths links table"
    INDEX { ompTlocPathsEntriesIp, 
            ompTlocPathsEntriesColor, 
            ompTlocPathsEntriesEncap, 
            ompTlocPathsEntriesPathsIndex, 
            ompTlocPathsEntriesPathsLinksLinkIndex }
        ::= { ompTlocPathsEntriesPathsLinksTable 1 }

OmpTlocPathsEntriesPathsLinksEntry ::=
    SEQUENCE {
        ompTlocPathsEntriesPathsLinksLinkIndex Unsigned32,
        ompTlocPathsEntriesPathsLinksFromTlocIp InetAddressIP,
        ompTlocPathsEntriesPathsLinksFromTlocColor TlocColorEnum,
        ompTlocPathsEntriesPathsLinksFromTlocEncap TlocEncapEnum,
        ompTlocPathsEntriesPathsLinksToTlocIp InetAddressIP,
        ompTlocPathsEntriesPathsLinksToTlocColor TlocColorEnum,
        ompTlocPathsEntriesPathsLinksToTlocEncap TlocEncapEnum,
        ompTlocPathsEntriesPathsLinksLabel Unsigned32
    }

-- tagpath /omp/tloc-paths/entries/paths/links/link-index
ompTlocPathsEntriesPathsLinksLinkIndex OBJECT-TYPE
    SYNTAX      Unsigned32
    MAX-ACCESS  not-accessible
    STATUS      current
    DESCRIPTION "Link index"
    ::= { ompTlocPathsEntriesPathsLinksEntry 1 }

-- tagpath /omp/tloc-paths/entries/paths/links/from-tloc/ip
ompTlocPathsEntriesPathsLinksFromTlocIp OBJECT-TYPE
    SYNTAX      InetAddressIP
    MAX-ACCESS  read-only
    STATUS      current
    DESCRIPTION "TLOC IP address"
    ::= { ompTlocPathsEntriesPathsLinksEntry 2 }

-- tagpath /omp/tloc-paths/entries/paths/links/from-tloc/color
ompTlocPathsEntriesPathsLinksFromTlocColor OBJECT-TYPE
    SYNTAX      TlocColorEnum
    MAX-ACCESS  read-only
    STATUS      current
    DESCRIPTION "TLOC color"
    ::= { ompTlocPathsEntriesPathsLinksEntry 3 }

-- tagpath /omp/tloc-paths/entries/paths/links/from-tloc/encap
ompTlocPathsEntriesPathsLinksFromTlocEncap OBJECT-TYPE
    SYNTAX      TlocEncapEnum
    MAX-ACCESS  read-only
    STATUS      current
    DESCRIPTION "TLOC encapsulation"
    ::= { ompTlocPathsEntriesPathsLinksEntry 4 }

-- tagpath /omp/tloc-paths/entries/paths/links/to-tloc/ip
ompTlocPathsEntriesPathsLinksToTlocIp OBJECT-TYPE
    SYNTAX      InetAddressIP
    MAX-ACCESS  read-only
    STATUS      current
    DESCRIPTION "To TLOC IP address"
    ::= { ompTlocPathsEntriesPathsLinksEntry 5 }

-- tagpath /omp/tloc-paths/entries/paths/links/to-tloc/color
ompTlocPathsEntriesPathsLinksToTlocColor OBJECT-TYPE
    SYNTAX      TlocColorEnum
    MAX-ACCESS  read-only
    STATUS      current
    DESCRIPTION "To TLOC Color"
    ::= { ompTlocPathsEntriesPathsLinksEntry 6 }

-- tagpath /omp/tloc-paths/entries/paths/links/to-tloc/encap
ompTlocPathsEntriesPathsLinksToTlocEncap OBJECT-TYPE
    SYNTAX      TlocEncapEnum
    MAX-ACCESS  read-only
    STATUS      current
    DESCRIPTION "To TLOC encapsulation"
    ::= { ompTlocPathsEntriesPathsLinksEntry 7 }

-- tagpath /omp/tloc-paths/entries/paths/links/label
ompTlocPathsEntriesPathsLinksLabel OBJECT-TYPE
    SYNTAX      Unsigned32
    MAX-ACCESS  read-only
    STATUS      current
    DESCRIPTION "Label"
    ::= { ompTlocPathsEntriesPathsLinksEntry 8 }

-- tagpath /omp/omp-tlocs/family
ompTlocsFamilyTable OBJECT-TYPE
    SYNTAX      SEQUENCE OF OmpTlocsFamilyEntry
    MAX-ACCESS  not-accessible
    STATUS      current
    DESCRIPTION "OMP TLOCs family table"
    ::= { ompTlocs 1 }

-- tagpath /omp/omp-tlocs/family
ompTlocsFamilyEntry OBJECT-TYPE
    SYNTAX      OmpTlocsFamilyEntry
    MAX-ACCESS  not-accessible
    STATUS      current
    DESCRIPTION "OMP TLOCs family table"
    INDEX { ompTlocsFamilyAddressFamily }
        ::= { ompTlocsFamilyTable 1 }

OmpTlocsFamilyEntry ::=
    SEQUENCE {
        ompTlocsFamilyAddressFamily AddrFamilyEnum
    }

-- tagpath /omp/omp-tlocs/family/address-family
ompTlocsFamilyAddressFamily OBJECT-TYPE
    SYNTAX      AddrFamilyEnum
    MAX-ACCESS  read-only
    STATUS      current
    DESCRIPTION "Address family"
    ::= { ompTlocsFamilyEntry 1 }

-- tagpath /omp/omp-tlocs/family/entries
ompTlocsFamilyEntriesTable OBJECT-TYPE
    SYNTAX      SEQUENCE OF OmpTlocsFamilyEntriesEntry
    MAX-ACCESS  not-accessible
    STATUS      current
    DESCRIPTION "OMP TLOCs entries table"
    ::= { ompTlocs 2 }

-- tagpath /omp/omp-tlocs/family/entries
ompTlocsFamilyEntriesEntry OBJECT-TYPE
    SYNTAX      OmpTlocsFamilyEntriesEntry
    MAX-ACCESS  not-accessible
    STATUS      current
    DESCRIPTION "OMP TLOCs entries table"
    INDEX { ompTlocsFamilyAddressFamily, 
            ompTlocsFamilyEntriesIp, 
            ompTlocsFamilyEntriesColor, 
            ompTlocsFamilyEntriesEncap }
        ::= { ompTlocsFamilyEntriesTable 1 }

OmpTlocsFamilyEntriesEntry ::=
    SEQUENCE {
        ompTlocsFamilyEntriesIp InetAddressIP,
        ompTlocsFamilyEntriesColor TlocColorEnum,
        ompTlocsFamilyEntriesEncap TlocEncapEnum
    }

-- tagpath /omp/omp-tlocs/family/entries/ip
ompTlocsFamilyEntriesIp OBJECT-TYPE
    SYNTAX      InetAddressIP
    MAX-ACCESS  read-only
    STATUS      current
    DESCRIPTION "IP address"
    ::= { ompTlocsFamilyEntriesEntry 1 }

-- tagpath /omp/omp-tlocs/family/entries/color
ompTlocsFamilyEntriesColor OBJECT-TYPE
    SYNTAX      TlocColorEnum
    MAX-ACCESS  read-only
    STATUS      current
    DESCRIPTION "Color"
    ::= { ompTlocsFamilyEntriesEntry 2 }

-- tagpath /omp/omp-tlocs/family/entries/encap
ompTlocsFamilyEntriesEncap OBJECT-TYPE
    SYNTAX      TlocEncapEnum
    MAX-ACCESS  read-only
    STATUS      current
    DESCRIPTION "Encapsulation"
    ::= { ompTlocsFamilyEntriesEntry 3 }

-- tagpath /omp/omp-tlocs/family/entries/received
ompTlocsFamilyEntriesReceivedTable OBJECT-TYPE
    SYNTAX      SEQUENCE OF OmpTlocsFamilyEntriesReceivedEntry
    MAX-ACCESS  not-accessible
    STATUS      current
    DESCRIPTION "OMP TLOCs entries received table"
    ::= { ompTlocs 5 }

-- tagpath /omp/omp-tlocs/family/entries/received
ompTlocsFamilyEntriesReceivedEntry OBJECT-TYPE
    SYNTAX      OmpTlocsFamilyEntriesReceivedEntry
    MAX-ACCESS  not-accessible
    STATUS      current
    DESCRIPTION "OMP TLOCs entries received table"
    INDEX { ompTlocsFamilyAddressFamily, 
            ompTlocsFamilyEntriesIp, 
            ompTlocsFamilyEntriesColor, 
            ompTlocsFamilyEntriesEncap, 
            ompTlocsFamilyEntriesReceivedTenantId, 
            ompTlocsFamilyEntriesReceivedFromPeer }
        ::= { ompTlocsFamilyEntriesReceivedTable 1 }

OmpTlocsFamilyEntriesReceivedEntry ::=
    SEQUENCE {
        ompTlocsFamilyEntriesReceivedTenantId Unsigned32,
        ompTlocsFamilyEntriesReceivedFromPeer InetAddressIP,
        ompTlocsFamilyEntriesReceivedStatus RibInStatusType,
        ompTlocsFamilyEntriesReceivedLossReason LossReasonEnum,
        ompTlocsFamilyEntriesReceivedLostToPeer InetAddressIP,
        ompTlocsFamilyEntriesReceivedLostToPathId Unsigned32
    }

-- tagpath /omp/omp-tlocs/family/entries/received/tenant-id
ompTlocsFamilyEntriesReceivedTenantId OBJECT-TYPE
    SYNTAX      Unsigned32
    MAX-ACCESS  not-accessible
    STATUS      current
    DESCRIPTION "Tenant ID"
    ::= { ompTlocsFamilyEntriesReceivedEntry 1 }

-- tagpath /omp/omp-tlocs/family/entries/received/from-peer
ompTlocsFamilyEntriesReceivedFromPeer OBJECT-TYPE
    SYNTAX      InetAddressIP
    MAX-ACCESS  not-accessible
    STATUS      current
    DESCRIPTION "From peer IP"
    ::= { ompTlocsFamilyEntriesReceivedEntry 2 }

-- tagpath /omp/omp-tlocs/family/entries/received/status
ompTlocsFamilyEntriesReceivedStatus OBJECT-TYPE
    SYNTAX      RibInStatusType
    MAX-ACCESS  read-only
    STATUS      current
    DESCRIPTION "RIB-in status"
    ::= { ompTlocsFamilyEntriesReceivedEntry 3 }

-- tagpath /omp/omp-tlocs/family/entries/received/loss-reason
ompTlocsFamilyEntriesReceivedLossReason OBJECT-TYPE
    SYNTAX      LossReasonEnum
    MAX-ACCESS  read-only
    STATUS      current
    DESCRIPTION "Loss reason"
    ::= { ompTlocsFamilyEntriesReceivedEntry 4 }

-- tagpath /omp/omp-tlocs/family/entries/received/lost-to-peer
ompTlocsFamilyEntriesReceivedLostToPeer OBJECT-TYPE
    SYNTAX      InetAddressIP
    MAX-ACCESS  read-only
    STATUS      current
    DESCRIPTION "Lost to peer IP"
    ::= { ompTlocsFamilyEntriesReceivedEntry 5 }

-- tagpath /omp/omp-tlocs/family/entries/received/lost-to-path-id
ompTlocsFamilyEntriesReceivedLostToPathId OBJECT-TYPE
    SYNTAX      Unsigned32
    MAX-ACCESS  read-only
    STATUS      current
    DESCRIPTION "Lost to path ID"
    ::= { ompTlocsFamilyEntriesReceivedEntry 6 }

-- tagpath /omp/omp-tlocs/family/entries/received/attributes
ompTlocsFamilyEntriesReceivedAttributesTable OBJECT-TYPE
    SYNTAX      SEQUENCE OF OmpTlocsFamilyEntriesReceivedAttributesEntry
    MAX-ACCESS  not-accessible
    STATUS      current
    DESCRIPTION "OMP TLOCs received attributes table"
    ::= { ompTlocs 6 }

-- tagpath /omp/omp-tlocs/family/entries/received/attributes
ompTlocsFamilyEntriesReceivedAttributesEntry OBJECT-TYPE
    SYNTAX      OmpTlocsFamilyEntriesReceivedAttributesEntry
    MAX-ACCESS  not-accessible
    STATUS      current
    DESCRIPTION "OMP TLOCs received attributes table"
    INDEX { ompTlocsFamilyAddressFamily, 
            ompTlocsFamilyEntriesIp, 
            ompTlocsFamilyEntriesColor, 
            ompTlocsFamilyEntriesEncap, 
            ompTlocsFamilyEntriesReceivedTenantId, 
            ompTlocsFamilyEntriesReceivedFromPeer, 
            ompTlocsFamilyEntriesReceivedAttributesPseudoKey }
        ::= { ompTlocsFamilyEntriesReceivedAttributesTable 1 }

OmpTlocsFamilyEntriesReceivedAttributesEntry ::=
    SEQUENCE {
    ompTlocsFamilyEntriesReceivedAttributesPseudoKey Unsigned32,
    ompTlocsFamilyEntriesReceivedAttributesAttributeType 
                                            AttributeTypeEnum,
    ompTlocsFamilyEntriesReceivedAttributesTlocEncapKey Unsigned32,
    ompTlocsFamilyEntriesReceivedAttributesTlocEncapProto Unsigned32,
    ompTlocsFamilyEntriesReceivedAttributesTlocEncapSpi Unsigned32,
    ompTlocsFamilyEntriesReceivedAttributesTlocEncapEncryptType 
                                                          EncryptType,
    ompTlocsFamilyEntriesReceivedAttributesTlocEncapIntegType IntegType,
    ompTlocsFamilyEntriesReceivedAttributesTlocMapPublicIp 
                                            InetAddressIP,
    ompTlocsFamilyEntriesReceivedAttributesTlocMapPublicPort 
                                            UnsignedShort,
    ompTlocsFamilyEntriesReceivedAttributesTlocMapPrivateIp 
                                            InetAddressIP,
    ompTlocsFamilyEntriesReceivedAttributesTlocMapPrivatePort 
                                            UnsignedShort,
    ompTlocsFamilyEntriesReceivedAttributesTlocMapV6PublicIp 
                                            InetAddressIP,
    ompTlocsFamilyEntriesReceivedAttributesTlocMapV6PublicPort 
                                            UnsignedShort,
    ompTlocsFamilyEntriesReceivedAttributesTlocMapV6PrivateIp 
                                            InetAddressIP,
    ompTlocsFamilyEntriesReceivedAttributesTlocMapV6PrivatePort 
                                            UnsignedShort,
    ompTlocsFamilyEntriesReceivedAttributesBfdStatus BfdStatusEnum,
    ompTlocsFamilyEntriesReceivedAttributesDomainId Unsigned32,
    ompTlocsFamilyEntriesReceivedAttributesSiteId Unsigned32,
    ompTlocsFamilyEntriesReceivedAttributesPreference Unsigned32,
    ompTlocsFamilyEntriesReceivedAttributesTag Unsigned32,
    ompTlocsFamilyEntriesReceivedAttributesStale UnsignedByte,
    ompTlocsFamilyEntriesReceivedAttributesCarrier CarrierEnum,
    ompTlocsFamilyEntriesReceivedAttributesGroups Groups1,
    ompTlocsFamilyEntriesReceivedAttributesUnknownAttributeLen 
                                            UnsignedShort,
    ompTlocsFamilyEntriesReceivedAttributesWeight Unsigned32,
    ompTlocsFamilyEntriesReceivedAttributesGenId Unsigned32,
    ompTlocsFamilyEntriesReceivedAttributesVersion Unsigned32,
    ompTlocsFamilyEntriesReceivedAttributesOriginator InetAddressIP,
    ompTlocsFamilyEntriesReceivedAttributesRestrict UnsignedByte,
    ompTlocsFamilyEntriesReceivedAttributesOverlayId Unsigned32,
    ompTlocsFamilyEntriesReceivedAttributesBandwidth Unsigned32,
    ompTlocsFamilyEntriesReceivedAttributesQosGroup String,
    ompTlocsFamilyEntriesReceivedAttributesOnDemand UnsignedByte,
    ompTlocsFamilyEntriesReceivedAttributesBandwidthDmin Unsigned32,
    ompTlocsFamilyEntriesReceivedAttributesBandwidthDown Unsigned32,
    ompTlocsFamilyEntriesReceivedAttributesBandwidthDmax Unsigned32,
    ompTlocsFamilyEntriesReceivedAttributesAdaptQosPeriod Unsigned32,
    ompTlocsFamilyEntriesReceivedAttributesAdaptQosUp UnsignedByte
    }

-- tagpath /omp/omp-tlocs/family/entries/received/attributes/pseudo-key
ompTlocsFamilyEntriesReceivedAttributesPseudoKey OBJECT-TYPE
    SYNTAX      Unsigned32
    MAX-ACCESS  not-accessible
    STATUS      current
    DESCRIPTION "Pseudo key"
    ::= { ompTlocsFamilyEntriesReceivedAttributesEntry 1 }

-- tagpath /omp/omp-tlocs/family/entries/received/attributes/
-- attribute-type
ompTlocsFamilyEntriesReceivedAttributesAttributeType OBJECT-TYPE
    SYNTAX      AttributeTypeEnum
    MAX-ACCESS  read-only
    STATUS      current
    DESCRIPTION "Attribute type"
    ::= { ompTlocsFamilyEntriesReceivedAttributesEntry 2 }

-- tagpath /omp/omp-tlocs/family/entries/received/attributes/
-- tloc-encap/key
ompTlocsFamilyEntriesReceivedAttributesTlocEncapKey OBJECT-TYPE
    SYNTAX      Unsigned32
    MAX-ACCESS  read-only
    STATUS      current
    DESCRIPTION "GRE key"
    ::= { ompTlocsFamilyEntriesReceivedAttributesEntry 3 }

-- tagpath /omp/omp-tlocs/family/entries/received/attributes/
-- tloc-encap/proto
ompTlocsFamilyEntriesReceivedAttributesTlocEncapProto OBJECT-TYPE
    SYNTAX      Unsigned32
    MAX-ACCESS  read-only
    STATUS      current
    DESCRIPTION "Protocol"
    ::= { ompTlocsFamilyEntriesReceivedAttributesEntry 4 }

-- tagpath /omp/omp-tlocs/family/entries/received/attributes/
--tloc-encap/spi
ompTlocsFamilyEntriesReceivedAttributesTlocEncapSpi OBJECT-TYPE
    SYNTAX      Unsigned32
    MAX-ACCESS  read-only
    STATUS      current
    DESCRIPTION "SPI"
    ::= { ompTlocsFamilyEntriesReceivedAttributesEntry 5 }

-- tagpath /omp/omp-tlocs/family/entries/received/attributes/
-- tloc-encap/encrypt-type
ompTlocsFamilyEntriesReceivedAttributesTlocEncapEncryptType OBJECT-TYPE
    SYNTAX      EncryptType
    MAX-ACCESS  read-only
    STATUS      current
    DESCRIPTION "Encryption"
    ::= { ompTlocsFamilyEntriesReceivedAttributesEntry 6 }

-- tagpath /omp/omp-tlocs/family/entries/received/attributes/
-- tloc-encap/integ-type
ompTlocsFamilyEntriesReceivedAttributesTlocEncapIntegType OBJECT-TYPE
    SYNTAX      IntegType
    MAX-ACCESS  read-only
    STATUS      current
    DESCRIPTION "Integrity"
    ::= { ompTlocsFamilyEntriesReceivedAttributesEntry 7 }

-- tagpath /omp/omp-tlocs/family/entries/received/attributes/
-- tloc-map-public/ip
ompTlocsFamilyEntriesReceivedAttributesTlocMapPublicIp OBJECT-TYPE
    SYNTAX      InetAddressIP
    MAX-ACCESS  read-only
    STATUS      current
    DESCRIPTION "IP address"
    ::= { ompTlocsFamilyEntriesReceivedAttributesEntry 8 }

-- tagpath /omp/omp-tlocs/family/entries/received/attributes/
-- tloc-map-public/port
ompTlocsFamilyEntriesReceivedAttributesTlocMapPublicPort OBJECT-TYPE
    SYNTAX      UnsignedShort
    MAX-ACCESS  read-only
    STATUS      current
    DESCRIPTION "Port number"
    ::= { ompTlocsFamilyEntriesReceivedAttributesEntry 9 }

-- tagpath /omp/omp-tlocs/family/entries/received/attributes/
-- tloc-map-private/ip
ompTlocsFamilyEntriesReceivedAttributesTlocMapPrivateIp OBJECT-TYPE
    SYNTAX      InetAddressIP
    MAX-ACCESS  read-only
    STATUS      current
    DESCRIPTION "IP address"
    ::= { ompTlocsFamilyEntriesReceivedAttributesEntry 10 }

-- tagpath /omp/omp-tlocs/family/entries/received/attributes/
-- tloc-map-private/port
ompTlocsFamilyEntriesReceivedAttributesTlocMapPrivatePort OBJECT-TYPE
    SYNTAX      UnsignedShort
    MAX-ACCESS  read-only
    STATUS      current
    DESCRIPTION "Port number"
    ::= { ompTlocsFamilyEntriesReceivedAttributesEntry 11 }

-- tagpath /omp/omp-tlocs/family/entries/received/attributes/
-- tloc-map-v6-public/ip
ompTlocsFamilyEntriesReceivedAttributesTlocMapV6PublicIp OBJECT-TYPE
    SYNTAX      InetAddressIP
    MAX-ACCESS  read-only
    STATUS      current
    DESCRIPTION "IP address"
    ::= { ompTlocsFamilyEntriesReceivedAttributesEntry 12 }

-- tagpath /omp/omp-tlocs/family/entries/received/attributes/
-- tloc-map-v6-public/port
ompTlocsFamilyEntriesReceivedAttributesTlocMapV6PublicPort OBJECT-TYPE
    SYNTAX      UnsignedShort
    MAX-ACCESS  read-only
    STATUS      current
    DESCRIPTION "Port number"
    ::= { ompTlocsFamilyEntriesReceivedAttributesEntry 13 }

-- tagpath /omp/omp-tlocs/family/entries/received/attributes/
-- tloc-map-v6-private/ip
ompTlocsFamilyEntriesReceivedAttributesTlocMapV6PrivateIp OBJECT-TYPE
    SYNTAX      InetAddressIP
    MAX-ACCESS  read-only
    STATUS      current
    DESCRIPTION "IP address"
    ::= { ompTlocsFamilyEntriesReceivedAttributesEntry 14 }

-- tagpath /omp/omp-tlocs/family/entries/received/attributes/
-- tloc-map-v6-private/port
ompTlocsFamilyEntriesReceivedAttributesTlocMapV6PrivatePort OBJECT-TYPE
    SYNTAX      UnsignedShort
    MAX-ACCESS  read-only
    STATUS      current
    DESCRIPTION "Port number"
    ::= { ompTlocsFamilyEntriesReceivedAttributesEntry 15 }

-- tagpath /omp/omp-tlocs/family/entries/received/attributes/bfd-status
ompTlocsFamilyEntriesReceivedAttributesBfdStatus OBJECT-TYPE
    SYNTAX      BfdStatusEnum
    MAX-ACCESS  read-only
    STATUS      current
    DESCRIPTION "BFD status"
    ::= { ompTlocsFamilyEntriesReceivedAttributesEntry 16 }

-- tagpath /omp/omp-tlocs/family/entries/received/attributes/domain-id
ompTlocsFamilyEntriesReceivedAttributesDomainId OBJECT-TYPE
    SYNTAX      Unsigned32 (0 .. 4294967295)
    MAX-ACCESS  read-only
    STATUS      current
    DESCRIPTION "Domain ID"
    ::= { ompTlocsFamilyEntriesReceivedAttributesEntry 17 }

-- tagpath /omp/omp-tlocs/family/entries/received/attributes/site-id
ompTlocsFamilyEntriesReceivedAttributesSiteId OBJECT-TYPE
    SYNTAX      Unsigned32
    MAX-ACCESS  read-only
    STATUS      current
    DESCRIPTION "Site ID"
    ::= { ompTlocsFamilyEntriesReceivedAttributesEntry 18 }

-- tagpath /omp/omp-tlocs/family/entries/received/attributes/preference
ompTlocsFamilyEntriesReceivedAttributesPreference OBJECT-TYPE
    SYNTAX      Unsigned32
    MAX-ACCESS  read-only
    STATUS      current
    DESCRIPTION "Preference"
    ::= { ompTlocsFamilyEntriesReceivedAttributesEntry 19 }

-- tagpath /omp/omp-tlocs/family/entries/received/attributes/tag
ompTlocsFamilyEntriesReceivedAttributesTag OBJECT-TYPE
    SYNTAX      Unsigned32
    MAX-ACCESS  read-only
    STATUS      current
    DESCRIPTION "Tag"
    ::= { ompTlocsFamilyEntriesReceivedAttributesEntry 20 }

-- tagpath /omp/omp-tlocs/family/entries/received/attributes/stale
ompTlocsFamilyEntriesReceivedAttributesStale OBJECT-TYPE
    SYNTAX      UnsignedByte
    MAX-ACCESS  read-only
    STATUS      current
    DESCRIPTION "Stale"
    ::= { ompTlocsFamilyEntriesReceivedAttributesEntry 21 }

-- tagpath /omp/omp-tlocs/family/entries/received/attributes/carrier
ompTlocsFamilyEntriesReceivedAttributesCarrier OBJECT-TYPE
    SYNTAX      CarrierEnum
    MAX-ACCESS  read-only
    STATUS      current
    DESCRIPTION "Carrier"
    ::= { ompTlocsFamilyEntriesReceivedAttributesEntry 22 }

-- tagpath /omp/omp-tlocs/family/entries/received/attributes/groups
ompTlocsFamilyEntriesReceivedAttributesGroups OBJECT-TYPE
    SYNTAX      Groups1
    MAX-ACCESS  read-only
    STATUS      current
    DESCRIPTION "Groups"
    ::= { ompTlocsFamilyEntriesReceivedAttributesEntry 23 }

-- tagpath /omp/omp-tlocs/family/entries/received/attributes/
-- unknown-attribute-len
ompTlocsFamilyEntriesReceivedAttributesUnknownAttributeLen OBJECT-TYPE
    SYNTAX      UnsignedShort
    MAX-ACCESS  read-only
    STATUS      current
    DESCRIPTION "Unknown attribute length"
    ::= { ompTlocsFamilyEntriesReceivedAttributesEntry 24 }

-- tagpath /omp/omp-tlocs/family/entries/received/attributes/weight
ompTlocsFamilyEntriesReceivedAttributesWeight OBJECT-TYPE
    SYNTAX      Unsigned32
    MAX-ACCESS  read-only
    STATUS      current
    DESCRIPTION "Weight"
    ::= { ompTlocsFamilyEntriesReceivedAttributesEntry 25 }

-- tagpath /omp/omp-tlocs/family/entries/received/attributes/gen-id
ompTlocsFamilyEntriesReceivedAttributesGenId OBJECT-TYPE
    SYNTAX      Unsigned32
    MAX-ACCESS  read-only
    STATUS      current
    DESCRIPTION "Gen ID"
    ::= { ompTlocsFamilyEntriesReceivedAttributesEntry 26 }

-- tagpath /omp/omp-tlocs/family/entries/received/attributes/version
ompTlocsFamilyEntriesReceivedAttributesVersion OBJECT-TYPE
    SYNTAX      Unsigned32
    MAX-ACCESS  read-only
    STATUS      current
    DESCRIPTION "Version"
    ::= { ompTlocsFamilyEntriesReceivedAttributesEntry 27 }

-- tagpath /omp/omp-tlocs/family/entries/received/attributes/originator
ompTlocsFamilyEntriesReceivedAttributesOriginator OBJECT-TYPE
    SYNTAX      InetAddressIP
    MAX-ACCESS  read-only
    STATUS      current
    DESCRIPTION "Originator"
    ::= { ompTlocsFamilyEntriesReceivedAttributesEntry 28 }

-- tagpath /omp/omp-tlocs/family/entries/received/attributes/restrict
ompTlocsFamilyEntriesReceivedAttributesRestrict OBJECT-TYPE
    SYNTAX      UnsignedByte
    MAX-ACCESS  read-only
    STATUS      current
    DESCRIPTION "Restrict"
    ::= { ompTlocsFamilyEntriesReceivedAttributesEntry 29 }

-- tagpath /omp/omp-tlocs/family/entries/received/attributes/overlay-id
ompTlocsFamilyEntriesReceivedAttributesOverlayId OBJECT-TYPE
    SYNTAX      Unsigned32
    MAX-ACCESS  read-only
    STATUS      current
    DESCRIPTION "Overlay ID"
    ::= { ompTlocsFamilyEntriesReceivedAttributesEntry 30 }

-- tagpath /omp/omp-tlocs/family/entries/received/attributes/bandwidth
ompTlocsFamilyEntriesReceivedAttributesBandwidth OBJECT-TYPE
    SYNTAX      Unsigned32
    MAX-ACCESS  read-only
    STATUS      current
    DESCRIPTION "Bandwidth"
    ::= { ompTlocsFamilyEntriesReceivedAttributesEntry 31 }

-- tagpath /omp/omp-tlocs/family/entries/received/attributes/qos-group
ompTlocsFamilyEntriesReceivedAttributesQosGroup OBJECT-TYPE
    SYNTAX      String
    MAX-ACCESS  read-only
    STATUS      current
    DESCRIPTION "QoS group"
    ::= { ompTlocsFamilyEntriesReceivedAttributesEntry 32 }

-- tagpath /omp/omp-tlocs/family/entries/received/attributes/on-demand
ompTlocsFamilyEntriesReceivedAttributesOnDemand OBJECT-TYPE
    SYNTAX      UnsignedByte
    MAX-ACCESS  read-only
    STATUS      current
    DESCRIPTION "On demand"
    ::= { ompTlocsFamilyEntriesReceivedAttributesEntry 33 }
 
-- tagpath /omp/omp-tlocs/family/entries/received/attributes/
-- bandwidth-dmin
ompTlocsFamilyEntriesReceivedAttributesBandwidthDmin OBJECT-TYPE
    SYNTAX      Unsigned32
    MAX-ACCESS  read-only
    STATUS      current
    DESCRIPTION "Minimum downstream bandwidth"
    ::= { ompTlocsFamilyEntriesReceivedAttributesEntry 34 }

-- tagpath /omp/omp-tlocs/family/entries/received/attributes/
-- bandwidth-down
ompTlocsFamilyEntriesReceivedAttributesBandwidthDown OBJECT-TYPE
    SYNTAX      Unsigned32
    MAX-ACCESS  read-only
    STATUS      current
    DESCRIPTION "Downstream bandwidth"
    ::= { ompTlocsFamilyEntriesReceivedAttributesEntry 35 }
-- tagpath /omp/omp-tlocs/family/entries/received/attributes/
-- bandwidth-dmax
ompTlocsFamilyEntriesReceivedAttributesBandwidthDmax OBJECT-TYPE
    SYNTAX      Unsigned32
    MAX-ACCESS  read-only
    STATUS      current
    DESCRIPTION "Maximum downstream bandwidth"
    ::= { ompTlocsFamilyEntriesReceivedAttributesEntry 36 }

-- tagpath /omp/omp-tlocs/family/entries/received/attributes/
-- adapt-qos-period
ompTlocsFamilyEntriesReceivedAttributesAdaptQosPeriod OBJECT-TYPE
    SYNTAX      Unsigned32
    MAX-ACCESS  read-only
    STATUS      current
    DESCRIPTION "Adapt QoS period"
    ::= { ompTlocsFamilyEntriesReceivedAttributesEntry 37 }

-- tagpath /omp/omp-tlocs/family/entries/received/attributes/
-- adapt-qos-up
ompTlocsFamilyEntriesReceivedAttributesAdaptQosUp OBJECT-TYPE
    SYNTAX      UnsignedByte
    MAX-ACCESS  read-only
    STATUS      current
    DESCRIPTION "Adapt QoS up"
    ::= { ompTlocsFamilyEntriesReceivedAttributesEntry 38 }


-- tagpath /omp/omp-tlocs/family/entries/advertised
ompTlocsFamilyEntriesAdvertisedTable OBJECT-TYPE
    SYNTAX      SEQUENCE OF OmpTlocsFamilyEntriesAdvertisedEntry
    MAX-ACCESS  not-accessible
    STATUS      current
    DESCRIPTION "OMP TLOCs advertised table"
    ::= { ompTlocs 7 }

-- tagpath /omp/omp-tlocs/family/entries/advertised
ompTlocsFamilyEntriesAdvertisedEntry OBJECT-TYPE
    SYNTAX      OmpTlocsFamilyEntriesAdvertisedEntry
    MAX-ACCESS  not-accessible
    STATUS      current
    DESCRIPTION "OMP TLOCs advertised table"
    INDEX { ompTlocsFamilyAddressFamily, 
            ompTlocsFamilyEntriesIp, 
            ompTlocsFamilyEntriesColor, 
            ompTlocsFamilyEntriesEncap, 
            ompTlocsFamilyEntriesAdvertisedTenantId, 
            ompTlocsFamilyEntriesAdvertisedToPeer }
        ::= { ompTlocsFamilyEntriesAdvertisedTable 1 }

OmpTlocsFamilyEntriesAdvertisedEntry ::=
    SEQUENCE {
        ompTlocsFamilyEntriesAdvertisedTenantId Unsigned32,
        ompTlocsFamilyEntriesAdvertisedToPeer InetAddressIP
    }

-- tagpath /omp/omp-tlocs/family/entries/advertised/tenant-id
ompTlocsFamilyEntriesAdvertisedTenantId OBJECT-TYPE
    SYNTAX      Unsigned32
    MAX-ACCESS  read-only
    STATUS      current
    DESCRIPTION "Tenant ID"
    ::= { ompTlocsFamilyEntriesAdvertisedEntry 1 }

-- tagpath /omp/omp-tlocs/family/entries/advertised/to-peer
ompTlocsFamilyEntriesAdvertisedToPeer OBJECT-TYPE
    SYNTAX      InetAddressIP
    MAX-ACCESS  read-only
    STATUS      current
    DESCRIPTION "To peer IP"
    ::= { ompTlocsFamilyEntriesAdvertisedEntry 2 }

-- tagpath /omp/omp-tlocs/family/entries/advertised/attributes
ompTlocsFamilyEntriesAdvertisedAttributesTable OBJECT-TYPE
    SYNTAX      SEQUENCE OF 
                OmpTlocsFamilyEntriesAdvertisedAttributesEntry
    MAX-ACCESS  not-accessible
    STATUS      current
    DESCRIPTION "OMP TLOCs advertised attributes table"
    ::= { ompTlocs 8 }

-- tagpath /omp/omp-tlocs/family/entries/advertised/attributes
ompTlocsFamilyEntriesAdvertisedAttributesEntry OBJECT-TYPE
    SYNTAX      OmpTlocsFamilyEntriesAdvertisedAttributesEntry
    MAX-ACCESS  not-accessible
    STATUS      current
    DESCRIPTION "OMP TLOCs advertised attributes table"
    INDEX { ompTlocsFamilyAddressFamily, 
            ompTlocsFamilyEntriesIp, 
            ompTlocsFamilyEntriesColor, 
            ompTlocsFamilyEntriesEncap, 
            ompTlocsFamilyEntriesAdvertisedTenantId, 
            ompTlocsFamilyEntriesAdvertisedToPeer, 
            ompTlocsFamilyEntriesAdvertisedAttributesAttributeId }
        ::= { ompTlocsFamilyEntriesAdvertisedAttributesTable 1 }

OmpTlocsFamilyEntriesAdvertisedAttributesEntry ::=
    SEQUENCE {
    ompTlocsFamilyEntriesAdvertisedAttributesAttributeId Unsigned32,
    ompTlocsFamilyEntriesAdvertisedAttributesTlocEncapKey Unsigned32,
    ompTlocsFamilyEntriesAdvertisedAttributesTlocEncapProto Unsigned32,
    ompTlocsFamilyEntriesAdvertisedAttributesTlocEncapSpi Unsigned32,
    ompTlocsFamilyEntriesAdvertisedAttributesTlocEncapEncryptType 
                                                          EncryptType,
    ompTlocsFamilyEntriesAdvertisedAttributesTlocEncapIntegType 
                                                          IntegType,
    ompTlocsFamilyEntriesAdvertisedAttributesTlocMapPublicIp 
                                                        InetAddressIP,
    ompTlocsFamilyEntriesAdvertisedAttributesTlocMapPublicPort 
                                                        UnsignedShort,
    ompTlocsFamilyEntriesAdvertisedAttributesTlocMapPrivateIp 
                                                        InetAddressIP,
    ompTlocsFamilyEntriesAdvertisedAttributesTlocMapPrivatePort 
                                                        UnsignedShort,
    ompTlocsFamilyEntriesAdvertisedAttributesTlocMapV6PublicIp 
                                                        InetAddressIP,
    ompTlocsFamilyEntriesAdvertisedAttributesTlocMapV6PublicPort 
                                                        UnsignedShort,
    ompTlocsFamilyEntriesAdvertisedAttributesTlocMapV6PrivateIp 
                                                        InetAddressIP,
    ompTlocsFamilyEntriesAdvertisedAttributesTlocMapV6PrivatePort 
                                                        UnsignedShort,
    ompTlocsFamilyEntriesAdvertisedAttributesDomainId Unsigned32,
    ompTlocsFamilyEntriesAdvertisedAttributesSiteId Unsigned32,
    ompTlocsFamilyEntriesAdvertisedAttributesPreference Unsigned32,
    ompTlocsFamilyEntriesAdvertisedAttributesTag Unsigned32,
    ompTlocsFamilyEntriesAdvertisedAttributesStale UnsignedByte,
    ompTlocsFamilyEntriesAdvertisedAttributesCarrier CarrierEnum,
    ompTlocsFamilyEntriesAdvertisedAttributesGroups Groups1,
    ompTlocsFamilyEntriesAdvertisedAttributesUnknownAttributeLen 
                                                        UnsignedShort,
    ompTlocsFamilyEntriesAdvertisedAttributesWeight Unsigned32,
    ompTlocsFamilyEntriesAdvertisedAttributesGenId Unsigned32,
    ompTlocsFamilyEntriesAdvertisedAttributesVersion Unsigned32,
    ompTlocsFamilyEntriesAdvertisedAttributesOriginator InetAddressIP,
    ompTlocsFamilyEntriesAdvertisedAttributesRestrict UnsignedByte,
    ompTlocsFamilyEntriesAdvertisedAttributesOverlayId Unsigned32,
    ompTlocsFamilyEntriesAdvertisedAttributesBandwidth Unsigned32,
    ompTlocsFamilyEntriesAdvertisedAttributesQosGroup String,
    ompTlocsFamilyEntriesAdvertisedAttributesBandwidthDmin Unsigned32,
    ompTlocsFamilyEntriesAdvertisedAttributesBandwidthDown Unsigned32,
    ompTlocsFamilyEntriesAdvertisedAttributesBandwidthDmax Unsigned32,
    ompTlocsFamilyEntriesAdvertisedAttributesAdaptQosPeriod Unsigned32,
    ompTlocsFamilyEntriesAdvertisedAttributesAdaptQosUp Unsigned32,
    ompTlocsFamilyEntriesAdvertisedAttributesOnDemand UnsignedByte
    }

-- tagpath /omp/omp-tlocs/family/entries/advertised/attributes/
-- attribute-id
ompTlocsFamilyEntriesAdvertisedAttributesAttributeId OBJECT-TYPE
    SYNTAX      Unsigned32
    MAX-ACCESS  not-accessible
    STATUS      current
    DESCRIPTION "Attribute ID"
    ::= { ompTlocsFamilyEntriesAdvertisedAttributesEntry 1 }

-- tagpath /omp/omp-tlocs/family/entries/advertised/attributes/
-- tloc-encap/key
ompTlocsFamilyEntriesAdvertisedAttributesTlocEncapKey OBJECT-TYPE
    SYNTAX      Unsigned32
    MAX-ACCESS  read-only
    STATUS      current
    DESCRIPTION "GRE key"
    ::= { ompTlocsFamilyEntriesAdvertisedAttributesEntry 2 }

-- tagpath /omp/omp-tlocs/family/entries/advertised/attributes/
-- tloc-encap/proto
ompTlocsFamilyEntriesAdvertisedAttributesTlocEncapProto OBJECT-TYPE
    SYNTAX      Unsigned32
    MAX-ACCESS  read-only
    STATUS      current
    DESCRIPTION "Protocol"
    ::= { ompTlocsFamilyEntriesAdvertisedAttributesEntry 3 }

-- tagpath /omp/omp-tlocs/family/entries/advertised/attributes/
-- tloc-encap/spi
ompTlocsFamilyEntriesAdvertisedAttributesTlocEncapSpi OBJECT-TYPE
    SYNTAX      Unsigned32
    MAX-ACCESS  read-only
    STATUS      current
    DESCRIPTION "SPI"
    ::= { ompTlocsFamilyEntriesAdvertisedAttributesEntry 4 }

-- tagpath /omp/omp-tlocs/family/entries/advertised/attributes/
-- tloc-encap/encrypt-type
ompTlocsFamilyEntriesAdvertisedAttributesTlocEncapEncryptType 
                                                    OBJECT-TYPE
    SYNTAX      EncryptType
    MAX-ACCESS  read-only
    STATUS      current
    DESCRIPTION "Encryption"
    ::= { ompTlocsFamilyEntriesAdvertisedAttributesEntry 5 }

-- tagpath /omp/omp-tlocs/family/entries/advertised/attributes/
-- tloc-encap/integ-type
ompTlocsFamilyEntriesAdvertisedAttributesTlocEncapIntegType OBJECT-TYPE
    SYNTAX      IntegType
    MAX-ACCESS  read-only
    STATUS      current
    DESCRIPTION "Integrity"
    ::= { ompTlocsFamilyEntriesAdvertisedAttributesEntry 6 }

-- tagpath /omp/omp-tlocs/family/entries/advertised/attributes/
-- tloc-map-public/ip
ompTlocsFamilyEntriesAdvertisedAttributesTlocMapPublicIp OBJECT-TYPE
    SYNTAX      InetAddressIP
    MAX-ACCESS  read-only
    STATUS      current
    DESCRIPTION "IP address"
    ::= { ompTlocsFamilyEntriesAdvertisedAttributesEntry 7 }

-- tagpath /omp/omp-tlocs/family/entries/advertised/attributes/
-- tloc-map-public/port
ompTlocsFamilyEntriesAdvertisedAttributesTlocMapPublicPort OBJECT-TYPE
    SYNTAX      UnsignedShort
    MAX-ACCESS  read-only
    STATUS      current
    DESCRIPTION "Port number"
    ::= { ompTlocsFamilyEntriesAdvertisedAttributesEntry 8 }

-- tagpath /omp/omp-tlocs/family/entries/advertised/attributes/
-- tloc-map-private/ip
ompTlocsFamilyEntriesAdvertisedAttributesTlocMapPrivateIp OBJECT-TYPE
    SYNTAX      InetAddressIP
    MAX-ACCESS  read-only
    STATUS      current
    DESCRIPTION "IP address"
    ::= { ompTlocsFamilyEntriesAdvertisedAttributesEntry 9 }

-- tagpath /omp/omp-tlocs/family/entries/advertised/attributes/
-- tloc-map-private/port
ompTlocsFamilyEntriesAdvertisedAttributesTlocMapPrivatePort OBJECT-TYPE
    SYNTAX      UnsignedShort
    MAX-ACCESS  read-only
    STATUS      current
    DESCRIPTION "Port number"
    ::= { ompTlocsFamilyEntriesAdvertisedAttributesEntry 10 }

-- tagpath /omp/omp-tlocs/family/entries/advertised/attributes/
-- tloc-map-v6-public/ip
ompTlocsFamilyEntriesAdvertisedAttributesTlocMapV6PublicIp OBJECT-TYPE
    SYNTAX      InetAddressIP
    MAX-ACCESS  read-only
    STATUS      current
    DESCRIPTION "IP address"
    ::= { ompTlocsFamilyEntriesAdvertisedAttributesEntry 11 }

-- tagpath /omp/omp-tlocs/family/entries/advertised/attributes/
-- tloc-map-v6-public/port
ompTlocsFamilyEntriesAdvertisedAttributesTlocMapV6PublicPort OBJECT-TYPE
    SYNTAX      UnsignedShort
    MAX-ACCESS  read-only
    STATUS      current
    DESCRIPTION "Port number"
    ::= { ompTlocsFamilyEntriesAdvertisedAttributesEntry 12 }

-- tagpath /omp/omp-tlocs/family/entries/advertised/attributes/
-- tloc-map-v6-private/ip
ompTlocsFamilyEntriesAdvertisedAttributesTlocMapV6PrivateIp OBJECT-TYPE
    SYNTAX      InetAddressIP
    MAX-ACCESS  read-only
    STATUS      current
    DESCRIPTION "IP address"
    ::= { ompTlocsFamilyEntriesAdvertisedAttributesEntry 13 }

-- tagpath /omp/omp-tlocs/family/entries/advertised/attributes/
-- tloc-map-v6-private/port
ompTlocsFamilyEntriesAdvertisedAttributesTlocMapV6PrivatePort 
                                                    OBJECT-TYPE
    SYNTAX      UnsignedShort
    MAX-ACCESS  read-only
    STATUS      current
    DESCRIPTION "Port number"
    ::= { ompTlocsFamilyEntriesAdvertisedAttributesEntry 14 }

-- tagpath /omp/omp-tlocs/family/entries/advertised/attributes/domain-id
ompTlocsFamilyEntriesAdvertisedAttributesDomainId OBJECT-TYPE
    SYNTAX      Unsigned32 (0 .. 4294967295)
    MAX-ACCESS  read-only
    STATUS      current
    DESCRIPTION "Domain ID"
    ::= { ompTlocsFamilyEntriesAdvertisedAttributesEntry 15 }

-- tagpath /omp/omp-tlocs/family/entries/advertised/attributes/site-id
ompTlocsFamilyEntriesAdvertisedAttributesSiteId OBJECT-TYPE
    SYNTAX      Unsigned32
    MAX-ACCESS  read-only
    STATUS      current
    DESCRIPTION "Site ID"
    ::= { ompTlocsFamilyEntriesAdvertisedAttributesEntry 16 }

-- tagpath /omp/omp-tlocs/family/entries/advertised/attributes/
-- preference
ompTlocsFamilyEntriesAdvertisedAttributesPreference OBJECT-TYPE
    SYNTAX      Unsigned32
    MAX-ACCESS  read-only
    STATUS      current
    DESCRIPTION "Preference"
    ::= { ompTlocsFamilyEntriesAdvertisedAttributesEntry 17 }

-- tagpath /omp/omp-tlocs/family/entries/advertised/attributes/tag
ompTlocsFamilyEntriesAdvertisedAttributesTag OBJECT-TYPE
    SYNTAX      Unsigned32
    MAX-ACCESS  read-only
    STATUS      current
    DESCRIPTION "Tag"
    ::= { ompTlocsFamilyEntriesAdvertisedAttributesEntry 18 }

-- tagpath /omp/omp-tlocs/family/entries/advertised/attributes/stale
ompTlocsFamilyEntriesAdvertisedAttributesStale OBJECT-TYPE
    SYNTAX      UnsignedByte
    MAX-ACCESS  read-only
    STATUS      current
    DESCRIPTION "Stale"
    ::= { ompTlocsFamilyEntriesAdvertisedAttributesEntry 19 }

-- tagpath /omp/omp-tlocs/family/entries/advertised/attributes/carrier
ompTlocsFamilyEntriesAdvertisedAttributesCarrier OBJECT-TYPE
    SYNTAX      CarrierEnum
    MAX-ACCESS  read-only
    STATUS      current
    DESCRIPTION "Carrier"
    ::= { ompTlocsFamilyEntriesAdvertisedAttributesEntry 20 }

-- tagpath /omp/omp-tlocs/family/entries/advertised/attributes/groups
ompTlocsFamilyEntriesAdvertisedAttributesGroups OBJECT-TYPE
    SYNTAX      Groups1
    MAX-ACCESS  read-only
    STATUS      current
    DESCRIPTION "Groups"
    ::= { ompTlocsFamilyEntriesAdvertisedAttributesEntry 21 }

-- tagpath /omp/omp-tlocs/family/entries/advertised/attributes/
-- unknown-attribute-len
ompTlocsFamilyEntriesAdvertisedAttributesUnknownAttributeLen OBJECT-TYPE
    SYNTAX      UnsignedShort
    MAX-ACCESS  read-only
    STATUS      current
    DESCRIPTION "Unknown attribute length"
    ::= { ompTlocsFamilyEntriesAdvertisedAttributesEntry 22 }

-- tagpath /omp/omp-tlocs/family/entries/advertised/attributes/weight
ompTlocsFamilyEntriesAdvertisedAttributesWeight OBJECT-TYPE
    SYNTAX      Unsigned32
    MAX-ACCESS  read-only
    STATUS      current
    DESCRIPTION "Weight"
    ::= { ompTlocsFamilyEntriesAdvertisedAttributesEntry 23 }

-- tagpath /omp/omp-tlocs/family/entries/advertised/attributes/gen-id
ompTlocsFamilyEntriesAdvertisedAttributesGenId OBJECT-TYPE
    SYNTAX      Unsigned32
    MAX-ACCESS  read-only
    STATUS      current
    DESCRIPTION "Gen ID"
    ::= { ompTlocsFamilyEntriesAdvertisedAttributesEntry 24 }

-- tagpath /omp/omp-tlocs/family/entries/advertised/attributes/version
ompTlocsFamilyEntriesAdvertisedAttributesVersion OBJECT-TYPE
    SYNTAX      Unsigned32
    MAX-ACCESS  read-only
    STATUS      current
    DESCRIPTION "Version"
    ::= { ompTlocsFamilyEntriesAdvertisedAttributesEntry 25 }

-- tagpath /omp/omp-tlocs/family/entries/advertised/attributes/
-- originator
ompTlocsFamilyEntriesAdvertisedAttributesOriginator OBJECT-TYPE
    SYNTAX      InetAddressIP
    MAX-ACCESS  read-only
    STATUS      current
    DESCRIPTION "Originator"
    ::= { ompTlocsFamilyEntriesAdvertisedAttributesEntry 26 }

-- tagpath /omp/omp-tlocs/family/entries/advertised/attributes/restrict
ompTlocsFamilyEntriesAdvertisedAttributesRestrict OBJECT-TYPE
    SYNTAX      UnsignedByte
    MAX-ACCESS  read-only
    STATUS      current
    DESCRIPTION "Restrict"
    ::= { ompTlocsFamilyEntriesAdvertisedAttributesEntry 27 }

-- tagpath /omp/omp-tlocs/family/entries/advertised/attributes/
-- overlay-id
ompTlocsFamilyEntriesAdvertisedAttributesOverlayId OBJECT-TYPE
    SYNTAX      Unsigned32
    MAX-ACCESS  read-only
    STATUS      current
    DESCRIPTION "Overlay ID"
    ::= { ompTlocsFamilyEntriesAdvertisedAttributesEntry 28 }

-- tagpath /omp/omp-tlocs/family/entries/advertised/attributes/bandwidth
ompTlocsFamilyEntriesAdvertisedAttributesBandwidth OBJECT-TYPE
    SYNTAX      Unsigned32
    MAX-ACCESS  read-only
    STATUS      current
    DESCRIPTION "Bandwidth"
    ::= { ompTlocsFamilyEntriesAdvertisedAttributesEntry 29 }

-- tagpath /omp/omp-tlocs/family/entries/advertised/attributes/qos-group
ompTlocsFamilyEntriesAdvertisedAttributesQosGroup OBJECT-TYPE
    SYNTAX      String
    MAX-ACCESS  read-only
    STATUS      current
    DESCRIPTION "QoS group"
    ::= { ompTlocsFamilyEntriesAdvertisedAttributesEntry 30 }

-- tagpath /omp/omp-tlocs/family/entries/advertised/attributes/
-- bandwidth-dmin
ompTlocsFamilyEntriesAdvertisedAttributesBandwidthDmin OBJECT-TYPE
    SYNTAX      Unsigned32
    MAX-ACCESS  read-only
    STATUS      current
    DESCRIPTION "Minimum downstream bandwidth"
    ::= { ompTlocsFamilyEntriesAdvertisedAttributesEntry 31 }

-- tagpath /omp/omp-tlocs/family/entries/advertised/attributes/
-- bandwidth-down
ompTlocsFamilyEntriesAdvertisedAttributesBandwidthDown OBJECT-TYPE
    SYNTAX      Unsigned32
    MAX-ACCESS  read-only
    STATUS      current
    DESCRIPTION "Downstream bandwidth"
    ::= { ompTlocsFamilyEntriesAdvertisedAttributesEntry 32 }

-- tagpath /omp/omp-tlocs/family/entries/advertised/attributes/
-- bandwidth-dmax
ompTlocsFamilyEntriesAdvertisedAttributesBandwidthDmax OBJECT-TYPE
    SYNTAX      Unsigned32
    MAX-ACCESS  read-only
    STATUS      current
    DESCRIPTION "Maximum downstream bandwidth"
    ::= { ompTlocsFamilyEntriesAdvertisedAttributesEntry 33 }

-- tagpath /omp/omp-tlocs/family/entries/advertised/attributes/
-- adapt-qos-period
ompTlocsFamilyEntriesAdvertisedAttributesAdaptQosPeriod OBJECT-TYPE
    SYNTAX      Unsigned32
    MAX-ACCESS  read-only
    STATUS      current
    DESCRIPTION "Adapt QoS period"
    ::= { ompTlocsFamilyEntriesAdvertisedAttributesEntry 34 }

-- tagpath /omp/omp-tlocs/family/entries/advertised/attributes/
-- adapt-qos-up
ompTlocsFamilyEntriesAdvertisedAttributesAdaptQosUp OBJECT-TYPE
    SYNTAX      Unsigned32
    MAX-ACCESS  read-only
    STATUS      current
    DESCRIPTION "Adapt QoS up"
    ::= { ompTlocsFamilyEntriesAdvertisedAttributesEntry 35 }

-- tagpath /omp/omp-tlocs/family/entries/advertised/attributes/on-demand
ompTlocsFamilyEntriesAdvertisedAttributesOnDemand OBJECT-TYPE
    SYNTAX      UnsignedByte
    MAX-ACCESS  read-only
    STATUS      current
    DESCRIPTION "On demand"
    ::= { ompTlocsFamilyEntriesAdvertisedAttributesEntry 36 }

-- tagpath /omp/services/family
ompServicesFamilyTable OBJECT-TYPE
    SYNTAX      SEQUENCE OF OmpServicesFamilyEntry
    MAX-ACCESS  not-accessible
    STATUS      current
    DESCRIPTION "OMP services family table"
    ::= { ompServices 1 }

-- tagpath /omp/services/family
ompServicesFamilyEntry OBJECT-TYPE
    SYNTAX      OmpServicesFamilyEntry
    MAX-ACCESS  not-accessible
    STATUS      current
    DESCRIPTION "OMP services family table"
    INDEX { ompServicesFamilyAddressFamily }
        ::= { ompServicesFamilyTable 1 }

OmpServicesFamilyEntry ::=
    SEQUENCE {
        ompServicesFamilyAddressFamily AddrFamilyEnum
    }

-- tagpath /omp/services/family/address-family
ompServicesFamilyAddressFamily OBJECT-TYPE
    SYNTAX      AddrFamilyEnum
    MAX-ACCESS  read-only
    STATUS      current
    DESCRIPTION "Address family"
    ::= { ompServicesFamilyEntry 1 }

-- tagpath /omp/services/family/entries
ompServicesFamilyEntriesTable OBJECT-TYPE
    SYNTAX      SEQUENCE OF OmpServicesFamilyEntriesEntry
    MAX-ACCESS  not-accessible
    STATUS      current
    DESCRIPTION "OMP services entries table"
    ::= { ompServices 2 }

-- tagpath /omp/services/family/entries
ompServicesFamilyEntriesEntry OBJECT-TYPE
    SYNTAX      OmpServicesFamilyEntriesEntry
    MAX-ACCESS  not-accessible
    STATUS      current
    DESCRIPTION "OMP services entries table"
    INDEX { ompServicesFamilyAddressFamily, 
            ompServicesFamilyEntriesTenantId, 
            ompServicesFamilyEntriesVpnId, 
            ompServicesFamilyEntriesService,
            ompServicesFamilyEntriesOriginator }
        ::= { ompServicesFamilyEntriesTable 1 }

OmpServicesFamilyEntriesEntry ::=
    SEQUENCE {
        ompServicesFamilyEntriesTenantId Unsigned32,
        ompServicesFamilyEntriesVpnId Unsigned32,
        ompServicesFamilyEntriesService INTEGER,
        ompServicesFamilyEntriesOriginator InetAddressIP
    }

-- tagpath /omp/services/family/entries/tenant-id
ompServicesFamilyEntriesTenantId OBJECT-TYPE
    SYNTAX      Unsigned32
    MAX-ACCESS  read-only
    STATUS      current
    DESCRIPTION "Tenant ID"
    ::= { ompServicesFamilyEntriesEntry 1 }

-- tagpath /omp/services/family/entries/vpn-id
ompServicesFamilyEntriesVpnId OBJECT-TYPE
    SYNTAX      Unsigned32 (0 .. 65530)
    MAX-ACCESS  read-only
    STATUS      current
    DESCRIPTION "VPN ID"
    ::= { ompServicesFamilyEntriesEntry 2 }

-- tagpath /omp/services/family/entries/service
ompServicesFamilyEntriesService OBJECT-TYPE
    SYNTAX      INTEGER {vPN(0),
                         fW(1),
                         iDS(2),
                         iDP(3),
                         netsvc1(4),
                         netsvc2(5),
                         netsvc3(6),
                         netsvc4(7),
                         tE(8),
                         sig(9),
                         appqoe(10)}
    MAX-ACCESS  read-only
    STATUS      current
    DESCRIPTION "Service type"
    ::= { ompServicesFamilyEntriesEntry 3 }

-- tagpath /omp/services/family/entries/originator
ompServicesFamilyEntriesOriginator OBJECT-TYPE
    SYNTAX      InetAddressIP
    MAX-ACCESS  read-only
    STATUS      current
    DESCRIPTION "Source originator"
    ::= { ompServicesFamilyEntriesEntry 4 }

-- tagpath /omp/services/family/entries/received
ompServicesFamilyEntriesReceivedTable OBJECT-TYPE
    SYNTAX      SEQUENCE OF OmpServicesFamilyEntriesReceivedEntry
    MAX-ACCESS  not-accessible
    STATUS      current
    DESCRIPTION "OMP services entries received table"
    ::= { ompServices 3 }

-- tagpath /omp/services/family/entries/received
ompServicesFamilyEntriesReceivedEntry OBJECT-TYPE
    SYNTAX      OmpServicesFamilyEntriesReceivedEntry
    MAX-ACCESS  not-accessible
    STATUS      current
    DESCRIPTION "OMP services entries received table"
    INDEX { ompServicesFamilyAddressFamily, 
            ompServicesFamilyEntriesTenantId, 
            ompServicesFamilyEntriesVpnId, 
            ompServicesFamilyEntriesService,
            ompServicesFamilyEntriesOriginator, 
            ompServicesFamilyEntriesReceivedFromPeer,
            ompServicesFamilyEntriesReceivedPathId }
        ::= { ompServicesFamilyEntriesReceivedTable 1 }

OmpServicesFamilyEntriesReceivedEntry ::=
    SEQUENCE {
        ompServicesFamilyEntriesReceivedFromPeer InetAddressIP,
        ompServicesFamilyEntriesReceivedPathId Unsigned32,
        ompServicesFamilyEntriesReceivedRegionId String,
        ompServicesFamilyEntriesReceivedLabel Unsigned32,
        ompServicesFamilyEntriesReceivedStatus RibInStatusType,
        ompServicesFamilyEntriesReceivedLossReason LossReasonEnum,
        ompServicesFamilyEntriesReceivedLostToPeer InetAddressIP,
        ompServicesFamilyEntriesReceivedLostToPathId Unsigned32,
        ompServicesFamilyEntriesReceivedVrfId Unsigned32
    }

-- tagpath /omp/services/family/entries/received/from-peer
ompServicesFamilyEntriesReceivedFromPeer OBJECT-TYPE
    SYNTAX      InetAddressIP
    MAX-ACCESS  not-accessible
    STATUS      current
    DESCRIPTION "From peer IP"
    ::= { ompServicesFamilyEntriesReceivedEntry 1 }

-- tagpath /omp/services/family/entries/received/path-id
ompServicesFamilyEntriesReceivedPathId OBJECT-TYPE
    SYNTAX      Unsigned32
    MAX-ACCESS  not-accessible
    STATUS      current
    DESCRIPTION "Path Id"
    ::= { ompServicesFamilyEntriesReceivedEntry 2 }

-- tagpath /omp/services/family/entries/received/region-id
ompServicesFamilyEntriesReceivedRegionId OBJECT-TYPE
    SYNTAX      String
    MAX-ACCESS  read-only
    STATUS      current
    DESCRIPTION "Region Id"
    ::= { ompServicesFamilyEntriesReceivedEntry 3 }

-- tagpath /omp/services/family/entries/received/label
ompServicesFamilyEntriesReceivedLabel OBJECT-TYPE
    SYNTAX      Unsigned32
    MAX-ACCESS  read-only
    STATUS      current
    DESCRIPTION "Label"
    ::= { ompServicesFamilyEntriesReceivedEntry 4 }

-- tagpath /omp/services/family/entries/received/status
ompServicesFamilyEntriesReceivedStatus OBJECT-TYPE
    SYNTAX      RibInStatusType
    MAX-ACCESS  read-only
    STATUS      current
    DESCRIPTION "RIB-in status"
    ::= { ompServicesFamilyEntriesReceivedEntry 5 }

-- tagpath /omp/services/family/entries/received/loss-reason
ompServicesFamilyEntriesReceivedLossReason OBJECT-TYPE
    SYNTAX      LossReasonEnum
    MAX-ACCESS  read-only
    STATUS      current
    DESCRIPTION "Loss reason"
    ::= { ompServicesFamilyEntriesReceivedEntry 6 }

-- tagpath /omp/services/family/entries/received/lost-to-peer
ompServicesFamilyEntriesReceivedLostToPeer OBJECT-TYPE
    SYNTAX      InetAddressIP
    MAX-ACCESS  read-only
    STATUS      current
    DESCRIPTION "Lost to Peer"
    ::= { ompServicesFamilyEntriesReceivedEntry 7 }

-- tagpath /omp/services/family/entries/received/lost-to-path-id
ompServicesFamilyEntriesReceivedLostToPathId OBJECT-TYPE
    SYNTAX      Unsigned32
    MAX-ACCESS  read-only
    STATUS      current
    DESCRIPTION "Lost to Path Id"
    ::= { ompServicesFamilyEntriesReceivedEntry 8 }

-- tagpath /omp/services/family/entries/received/vrf-id
ompServicesFamilyEntriesReceivedVrfId OBJECT-TYPE
    SYNTAX      Unsigned32
    MAX-ACCESS  read-only
    STATUS      current
    DESCRIPTION "Vrf Id"
    ::= { ompServicesFamilyEntriesReceivedEntry 9 }

-- tagpath /omp/services/family/entries/advertised
ompServicesFamilyEntriesAdvertisedTable OBJECT-TYPE
    SYNTAX      SEQUENCE OF OmpServicesFamilyEntriesAdvertisedEntry
    MAX-ACCESS  not-accessible
    STATUS      current
    DESCRIPTION "OMP services entries advertised table"
    ::= { ompServices 4 }

-- tagpath /omp/services/family/entries/advertised
ompServicesFamilyEntriesAdvertisedEntry OBJECT-TYPE
    SYNTAX      OmpServicesFamilyEntriesAdvertisedEntry
    MAX-ACCESS  not-accessible
    STATUS      current
    DESCRIPTION "OMP services entries advertised table"
    INDEX { ompServicesFamilyAddressFamily, 
            ompServicesFamilyEntriesTenantId, 
            ompServicesFamilyEntriesVpnId, 
            ompServicesFamilyEntriesService,
            ompServicesFamilyEntriesOriginator,
            ompServicesFamilyEntriesAdvertisedToPeer }
        ::= { ompServicesFamilyEntriesAdvertisedTable 1 }

OmpServicesFamilyEntriesAdvertisedEntry ::=
    SEQUENCE {
        ompServicesFamilyEntriesAdvertisedToPeer InetAddressIP
    }

-- tagpath /omp/services/family/entries/advertised/to-peer
ompServicesFamilyEntriesAdvertisedToPeer OBJECT-TYPE
    SYNTAX      InetAddressIP
    MAX-ACCESS  read-only
    STATUS      current
    DESCRIPTION "To peer IP"
    ::= { ompServicesFamilyEntriesAdvertisedEntry 1 }

-- tagpath /omp/multicast-auto-discover/family
ompMulticastAutoDiscoverFamilyTable OBJECT-TYPE
    SYNTAX      SEQUENCE OF OmpMulticastAutoDiscoverFamilyEntry
    MAX-ACCESS  not-accessible
    STATUS      current
    DESCRIPTION "OMP multicast auto discovery family table"
    ::= { ompMulticastAutoDiscover 1 }

-- tagpath /omp/multicast-auto-discover/family
ompMulticastAutoDiscoverFamilyEntry OBJECT-TYPE
    SYNTAX      OmpMulticastAutoDiscoverFamilyEntry
    MAX-ACCESS  not-accessible
    STATUS      current
    DESCRIPTION "OMP multicast auto discovery family table"
    INDEX { ompMulticastAutoDiscoverFamilyAddressFamily }
        ::= { ompMulticastAutoDiscoverFamilyTable 1 }

OmpMulticastAutoDiscoverFamilyEntry ::=
    SEQUENCE {
        ompMulticastAutoDiscoverFamilyAddressFamily AddrFamilyEnum
    }

-- tagpath /omp/multicast-auto-discover/family/address-family
ompMulticastAutoDiscoverFamilyAddressFamily OBJECT-TYPE
    SYNTAX      AddrFamilyEnum
    MAX-ACCESS  read-only
    STATUS      current
    DESCRIPTION "Address family"
    ::= { ompMulticastAutoDiscoverFamilyEntry 1 }

-- tagpath /omp/multicast-auto-discover/family/entries
ompMulticastAutoDiscoverFamilyEntriesTable OBJECT-TYPE
    SYNTAX      SEQUENCE OF OmpMulticastAutoDiscoverFamilyEntriesEntry
    MAX-ACCESS  not-accessible
    STATUS      current
    DESCRIPTION "OMP multicast auto discovery entries table"
    ::= { ompMulticastAutoDiscover 2 }

-- tagpath /omp/multicast-auto-discover/family/entries
ompMulticastAutoDiscoverFamilyEntriesEntry OBJECT-TYPE
    SYNTAX      OmpMulticastAutoDiscoverFamilyEntriesEntry
    MAX-ACCESS  not-accessible
    STATUS      current
    DESCRIPTION "OMP multicast auto discovery entries table"
    INDEX { ompMulticastAutoDiscoverFamilyAddressFamily, 
            ompMulticastAutoDiscoverFamilyEntriesTenantId, 
            ompMulticastAutoDiscoverFamilyEntriesVpnId, 
            ompMulticastAutoDiscoverFamilyEntriesSourceOriginator }
        ::= { ompMulticastAutoDiscoverFamilyEntriesTable 1 }

OmpMulticastAutoDiscoverFamilyEntriesEntry ::=
    SEQUENCE {
        ompMulticastAutoDiscoverFamilyEntriesTenantId Unsigned32,
        ompMulticastAutoDiscoverFamilyEntriesVpnId Unsigned32,
        ompMulticastAutoDiscoverFamilyEntriesSourceOriginator 
                                                   InetAddressIP
    }

-- tagpath /omp/multicast-auto-discover/family/entries/tenant-id
ompMulticastAutoDiscoverFamilyEntriesTenantId OBJECT-TYPE
    SYNTAX      Unsigned32
    MAX-ACCESS  read-only
    STATUS      current
    DESCRIPTION "Tenant ID"
    ::= { ompMulticastAutoDiscoverFamilyEntriesEntry 1 }

-- tagpath /omp/multicast-auto-discover/family/entries/vpn-id
ompMulticastAutoDiscoverFamilyEntriesVpnId OBJECT-TYPE
    SYNTAX      Unsigned32 (0 .. 65530)
    MAX-ACCESS  read-only
    STATUS      current
    DESCRIPTION "VPN ID"
    ::= { ompMulticastAutoDiscoverFamilyEntriesEntry 2 }

-- tagpath /omp/multicast-auto-discover/family/entries/source-originator
ompMulticastAutoDiscoverFamilyEntriesSourceOriginator OBJECT-TYPE
    SYNTAX      InetAddressIP
    MAX-ACCESS  read-only
    STATUS      current
    DESCRIPTION "Source originator"
    ::= { ompMulticastAutoDiscoverFamilyEntriesEntry 3 }

-- tagpath /omp/multicast-auto-discover/family/entries/received
ompMulticastAutoDiscoverFamilyEntriesReceivedTable OBJECT-TYPE
    SYNTAX      SEQUENCE OF 
              OmpMulticastAutoDiscoverFamilyEntriesReceivedEntry
    MAX-ACCESS  not-accessible
    STATUS      current
    DESCRIPTION "OMP multicast auto discovery entries received table"
    ::= { ompMulticastAutoDiscover 3 }

-- tagpath /omp/multicast-auto-discover/family/entries/received
ompMulticastAutoDiscoverFamilyEntriesReceivedEntry OBJECT-TYPE
    SYNTAX      OmpMulticastAutoDiscoverFamilyEntriesReceivedEntry
    MAX-ACCESS  not-accessible
    STATUS      current
    DESCRIPTION "OMP multicast auto discovery entries received table"
    INDEX { ompMulticastAutoDiscoverFamilyAddressFamily, 
            ompMulticastAutoDiscoverFamilyEntriesTenantId, 
            ompMulticastAutoDiscoverFamilyEntriesVpnId, 
            ompMulticastAutoDiscoverFamilyEntriesSourceOriginator, 
            ompMulticastAutoDiscoverFamilyEntriesReceivedFromPeer }
        ::= { ompMulticastAutoDiscoverFamilyEntriesReceivedTable 1 }

OmpMulticastAutoDiscoverFamilyEntriesReceivedEntry ::=
    SEQUENCE {
        ompMulticastAutoDiscoverFamilyEntriesReceivedFromPeer 
                                                    InetAddressIP,
        ompMulticastAutoDiscoverFamilyEntriesReceivedStatus 
                                                    RibInStatusType,
        ompMulticastAutoDiscoverFamilyEntriesReceivedLossReason 
                                                    LossReasonEnum
    }

-- tagpath /omp/multicast-auto-discover/family/entries/received/
-- from-peer
ompMulticastAutoDiscoverFamilyEntriesReceivedFromPeer OBJECT-TYPE
    SYNTAX      InetAddressIP
    MAX-ACCESS  not-accessible
    STATUS      current
    DESCRIPTION "From peer IP"
    ::= { ompMulticastAutoDiscoverFamilyEntriesReceivedEntry 1 }

-- tagpath /omp/multicast-auto-discover/family/entries/received/status
ompMulticastAutoDiscoverFamilyEntriesReceivedStatus OBJECT-TYPE
    SYNTAX      RibInStatusType
    MAX-ACCESS  read-only
    STATUS      current
    DESCRIPTION "RIB-in status"
    ::= { ompMulticastAutoDiscoverFamilyEntriesReceivedEntry 2 }

-- tagpath /omp/multicast-auto-discover/family/entries/received/
-- loss-reason
ompMulticastAutoDiscoverFamilyEntriesReceivedLossReason OBJECT-TYPE
    SYNTAX      LossReasonEnum
    MAX-ACCESS  read-only
    STATUS      current
    DESCRIPTION "Loss reason"
    ::= { ompMulticastAutoDiscoverFamilyEntriesReceivedEntry 3 }

-- tagpath /omp/multicast-auto-discover/family/entries/advertised
ompMulticastAutoDiscoverFamilyEntriesAdvertisedTable OBJECT-TYPE
    SYNTAX      SEQUENCE OF 
              OmpMulticastAutoDiscoverFamilyEntriesAdvertisedEntry
    MAX-ACCESS  not-accessible
    STATUS      current
    DESCRIPTION "OMP multicast auto discovery entries advertised table"
    ::= { ompMulticastAutoDiscover 4 }

-- tagpath /omp/multicast-auto-discover/family/entries/advertised
ompMulticastAutoDiscoverFamilyEntriesAdvertisedEntry OBJECT-TYPE
    SYNTAX      OmpMulticastAutoDiscoverFamilyEntriesAdvertisedEntry
    MAX-ACCESS  not-accessible
    STATUS      current
    DESCRIPTION "OMP multicast auto discovery entries advertised table"
    INDEX { ompMulticastAutoDiscoverFamilyAddressFamily, 
            ompMulticastAutoDiscoverFamilyEntriesTenantId,
            ompMulticastAutoDiscoverFamilyEntriesVpnId, 
            ompMulticastAutoDiscoverFamilyEntriesSourceOriginator, 
            ompMulticastAutoDiscoverFamilyEntriesAdvertisedToPeer }
        ::= { ompMulticastAutoDiscoverFamilyEntriesAdvertisedTable 1 }

OmpMulticastAutoDiscoverFamilyEntriesAdvertisedEntry ::=
    SEQUENCE {
        ompMulticastAutoDiscoverFamilyEntriesAdvertisedToPeer 
                                                      InetAddressIP
    }

-- tagpath /omp/multicast-auto-discover/family/entries/advertised/
-- to-peer
ompMulticastAutoDiscoverFamilyEntriesAdvertisedToPeer OBJECT-TYPE
    SYNTAX      InetAddressIP
    MAX-ACCESS  read-only
    STATUS      current
    DESCRIPTION "To peer IP"
    ::= { ompMulticastAutoDiscoverFamilyEntriesAdvertisedEntry 1 }

-- tagpath /omp/multicast-routes/family
ompMulticastRoutesFamilyTable OBJECT-TYPE
    SYNTAX      SEQUENCE OF OmpMulticastRoutesFamilyEntry
    MAX-ACCESS  not-accessible
    STATUS      current
    DESCRIPTION "OMP multicast routes family table"
    ::= { ompMulticastRoutes 1 }

-- tagpath /omp/multicast-routes/family
ompMulticastRoutesFamilyEntry OBJECT-TYPE
    SYNTAX      OmpMulticastRoutesFamilyEntry
    MAX-ACCESS  not-accessible
    STATUS      current
    DESCRIPTION "OMP multicast routes family table"
    INDEX { ompMulticastRoutesFamilyAddressFamily }
        ::= { ompMulticastRoutesFamilyTable 1 }

OmpMulticastRoutesFamilyEntry ::=
    SEQUENCE {
        ompMulticastRoutesFamilyAddressFamily AddrFamilyEnum
    }

-- tagpath /omp/multicast-routes/family/address-family
ompMulticastRoutesFamilyAddressFamily OBJECT-TYPE
    SYNTAX      AddrFamilyEnum
    MAX-ACCESS  read-only
    STATUS      current
    DESCRIPTION "Address family"
    ::= { ompMulticastRoutesFamilyEntry 1 }

-- tagpath /omp/multicast-routes/family/entries
ompMulticastRoutesFamilyEntriesTable OBJECT-TYPE
    SYNTAX      SEQUENCE OF OmpMulticastRoutesFamilyEntriesEntry
    MAX-ACCESS  not-accessible
    STATUS      current
    DESCRIPTION "OMP multicast routes entries table"
    ::= { ompMulticastRoutes 2 }

-- tagpath /omp/multicast-routes/family/entries
ompMulticastRoutesFamilyEntriesEntry OBJECT-TYPE
    SYNTAX      OmpMulticastRoutesFamilyEntriesEntry
    MAX-ACCESS  not-accessible
    STATUS      current
    DESCRIPTION "OMP multicast routes entries table"
    INDEX { ompMulticastRoutesFamilyAddressFamily, 
            ompMulticastRoutesFamilyEntriesTenantId, 
            ompMulticastRoutesFamilyEntriesType, 
            ompMulticastRoutesFamilyEntriesVpnId, 
            ompMulticastRoutesFamilyEntriesDestination, 
            ompMulticastRoutesFamilyEntriesGroup, 
            ompMulticastRoutesFamilyEntriesSource,
            ompMulticastRoutesFamilyEntriesSourceOriginator }
        ::= { ompMulticastRoutesFamilyEntriesTable 1 }

OmpMulticastRoutesFamilyEntriesEntry ::=
    SEQUENCE {
        ompMulticastRoutesFamilyEntriesTenantId Unsigned32,
        ompMulticastRoutesFamilyEntriesType McastRouteEnum,
        ompMulticastRoutesFamilyEntriesVpnId Unsigned32,
        ompMulticastRoutesFamilyEntriesDestination InetAddressIP,
        ompMulticastRoutesFamilyEntriesGroup InetAddressIP,
        ompMulticastRoutesFamilyEntriesSource InetAddressIP,
        ompMulticastRoutesFamilyEntriesSourceOriginator InetAddressIP
    }

-- tagpath /omp/multicast-routes/family/entries/type
ompMulticastRoutesFamilyEntriesTenantId OBJECT-TYPE
    SYNTAX      Unsigned32
    MAX-ACCESS  read-only
    STATUS      current
    DESCRIPTION "Tenant ID"
    ::= { ompMulticastRoutesFamilyEntriesEntry 1 }

-- tagpath /omp/multicast-routes/family/entries/type
ompMulticastRoutesFamilyEntriesType OBJECT-TYPE
    SYNTAX      McastRouteEnum
    MAX-ACCESS  read-only
    STATUS      current
    DESCRIPTION "Multicast route type"
    ::= { ompMulticastRoutesFamilyEntriesEntry 2 }

-- tagpath /omp/multicast-routes/family/entries/vpn-id
ompMulticastRoutesFamilyEntriesVpnId OBJECT-TYPE
    SYNTAX      Unsigned32 (0 .. 65530)
    MAX-ACCESS  read-only
    STATUS      current
    DESCRIPTION "VPN ID"
    ::= { ompMulticastRoutesFamilyEntriesEntry 3 }

-- tagpath /omp/multicast-routes/family/entries/destination
ompMulticastRoutesFamilyEntriesDestination OBJECT-TYPE
    SYNTAX      InetAddressIP
    MAX-ACCESS  read-only
    STATUS      current
    DESCRIPTION "Destination"
    ::= { ompMulticastRoutesFamilyEntriesEntry 4 }

-- tagpath /omp/multicast-routes/family/entries/group
ompMulticastRoutesFamilyEntriesGroup OBJECT-TYPE
    SYNTAX      InetAddressIP
    MAX-ACCESS  read-only
    STATUS      current
    DESCRIPTION "Multicast group"
    ::= { ompMulticastRoutesFamilyEntriesEntry 5 }

-- tagpath /omp/multicast-routes/family/entries/source
ompMulticastRoutesFamilyEntriesSource OBJECT-TYPE
    SYNTAX      InetAddressIP
    MAX-ACCESS  read-only
    STATUS      current
    DESCRIPTION "Source"
    ::= { ompMulticastRoutesFamilyEntriesEntry 6 }

-- tagpath /omp/multicast-routes/family/entries/source-originator
ompMulticastRoutesFamilyEntriesSourceOriginator OBJECT-TYPE
    SYNTAX      InetAddressIP
    MAX-ACCESS  read-only
    STATUS      current
    DESCRIPTION "Source originator"
    ::= { ompMulticastRoutesFamilyEntriesEntry 7 }

-- tagpath /omp/multicast-routes/family/entries/received
ompMulticastRoutesFamilyEntriesReceivedTable OBJECT-TYPE
    SYNTAX      SEQUENCE OF OmpMulticastRoutesFamilyEntriesReceivedEntry
    MAX-ACCESS  not-accessible
    STATUS      current
    DESCRIPTION "OMP multicast routes entries received table"
    ::= { ompMulticastRoutes 3 }

-- tagpath /omp/multicast-routes/family/entries/received
ompMulticastRoutesFamilyEntriesReceivedEntry OBJECT-TYPE
    SYNTAX      OmpMulticastRoutesFamilyEntriesReceivedEntry
    MAX-ACCESS  not-accessible
    STATUS      current
    DESCRIPTION "OMP multicast routes entries received table"
    INDEX { ompMulticastRoutesFamilyAddressFamily, 
            ompMulticastRoutesFamilyEntriesTenantId, 
            ompMulticastRoutesFamilyEntriesType, 
            ompMulticastRoutesFamilyEntriesVpnId, 
            ompMulticastRoutesFamilyEntriesDestination, 
            ompMulticastRoutesFamilyEntriesGroup, 
            ompMulticastRoutesFamilyEntriesSource, 
            ompMulticastRoutesFamilyEntriesSourceOriginator, 
            ompMulticastRoutesFamilyEntriesReceivedFromPeer }
        ::= { ompMulticastRoutesFamilyEntriesReceivedTable 1 }

OmpMulticastRoutesFamilyEntriesReceivedEntry ::=
    SEQUENCE {
        ompMulticastRoutesFamilyEntriesReceivedFromPeer InetAddressIP,
        ompMulticastRoutesFamilyEntriesReceivedRp InetAddressIP,
        ompMulticastRoutesFamilyEntriesReceivedReceivedPrunes 
                                                       ReceivedPrunes1,
        ompMulticastRoutesFamilyEntriesReceivedStatus RibInStatusType,
        ompMulticastRoutesFamilyEntriesReceivedLossReason LossReasonEnum
    }

-- tagpath /omp/multicast-routes/family/entries/received/from-peer
ompMulticastRoutesFamilyEntriesReceivedFromPeer OBJECT-TYPE
    SYNTAX      InetAddressIP
    MAX-ACCESS  not-accessible
    STATUS      current
    DESCRIPTION "From peer IP"
    ::= { ompMulticastRoutesFamilyEntriesReceivedEntry 1 }

-- tagpath /omp/multicast-routes/family/entries/received/rp
ompMulticastRoutesFamilyEntriesReceivedRp OBJECT-TYPE
    SYNTAX      InetAddressIP
    MAX-ACCESS  read-only
    STATUS      current
    DESCRIPTION "Rp"
    ::= { ompMulticastRoutesFamilyEntriesReceivedEntry 2 }

-- tagpath /omp/multicast-routes/family/entries/received/received-prunes
ompMulticastRoutesFamilyEntriesReceivedReceivedPrunes OBJECT-TYPE
    SYNTAX      ReceivedPrunes1
    MAX-ACCESS  read-only
    STATUS      current
    DESCRIPTION "Prunes"
    ::= { ompMulticastRoutesFamilyEntriesReceivedEntry 3 }

-- tagpath /omp/multicast-routes/family/entries/received/status
ompMulticastRoutesFamilyEntriesReceivedStatus OBJECT-TYPE
    SYNTAX      RibInStatusType
    MAX-ACCESS  read-only
    STATUS      current
    DESCRIPTION "RIB-in status"
    ::= { ompMulticastRoutesFamilyEntriesReceivedEntry 4 }

-- tagpath /omp/multicast-routes/family/entries/received/loss-reason
ompMulticastRoutesFamilyEntriesReceivedLossReason OBJECT-TYPE
    SYNTAX      LossReasonEnum
    MAX-ACCESS  read-only
    STATUS      current
    DESCRIPTION "Loss reason"
    ::= { ompMulticastRoutesFamilyEntriesReceivedEntry 5 }

-- tagpath /omp/multicast-routes/family/entries/advertised
ompMulticastRoutesFamilyEntriesAdvertisedTable OBJECT-TYPE
    SYNTAX      SEQUENCE OF 
                OmpMulticastRoutesFamilyEntriesAdvertisedEntry
    MAX-ACCESS  not-accessible
    STATUS      current
    DESCRIPTION "OMP multicast routes entries advertised table"
    ::= { ompMulticastRoutes 4 }

-- tagpath /omp/multicast-routes/family/entries/advertised
ompMulticastRoutesFamilyEntriesAdvertisedEntry OBJECT-TYPE
    SYNTAX      OmpMulticastRoutesFamilyEntriesAdvertisedEntry
    MAX-ACCESS  not-accessible
    STATUS      current
    DESCRIPTION "OMP multicast routes entries advertised table"
    INDEX { ompMulticastRoutesFamilyAddressFamily, 
            ompMulticastRoutesFamilyEntriesTenantId, 
            ompMulticastRoutesFamilyEntriesType, 
            ompMulticastRoutesFamilyEntriesVpnId, 
            ompMulticastRoutesFamilyEntriesDestination, 
            ompMulticastRoutesFamilyEntriesGroup, 
            ompMulticastRoutesFamilyEntriesSource, 
            ompMulticastRoutesFamilyEntriesSourceOriginator, 
            ompMulticastRoutesFamilyEntriesAdvertisedToPeer }
        ::= { ompMulticastRoutesFamilyEntriesAdvertisedTable 1 }

OmpMulticastRoutesFamilyEntriesAdvertisedEntry ::=
    SEQUENCE {
        ompMulticastRoutesFamilyEntriesAdvertisedToPeer InetAddressIP,
        ompMulticastRoutesFamilyEntriesAdvertisedRp InetAddressIP,
        ompMulticastRoutesFamilyEntriesAdvertisedAdvertisedPrunes 
                                                     AdvertisedPrunes1
    }

-- tagpath /omp/multicast-routes/family/entries/advertised/to-peer
ompMulticastRoutesFamilyEntriesAdvertisedToPeer OBJECT-TYPE
    SYNTAX      InetAddressIP
    MAX-ACCESS  not-accessible
    STATUS      current
    DESCRIPTION "To peer IP"
    ::= { ompMulticastRoutesFamilyEntriesAdvertisedEntry 1 }

-- tagpath /omp/multicast-routes/family/entries/advertised/rp
ompMulticastRoutesFamilyEntriesAdvertisedRp OBJECT-TYPE
    SYNTAX      InetAddressIP
    MAX-ACCESS  read-only
    STATUS      current
    DESCRIPTION "Rp"
    ::= { ompMulticastRoutesFamilyEntriesAdvertisedEntry 2 }

-- tagpath /omp/multicast-routes/family/entries/advertised/
-- advertised-prunes
ompMulticastRoutesFamilyEntriesAdvertisedAdvertisedPrunes OBJECT-TYPE
    SYNTAX      AdvertisedPrunes1
    MAX-ACCESS  read-only
    STATUS      current
    DESCRIPTION "Prunes"
    ::= { ompMulticastRoutesFamilyEntriesAdvertisedEntry 3 }

-- tagpath /omp/cloudexpress/entries
ompCloudexpressEntriesTable OBJECT-TYPE
    SYNTAX      SEQUENCE OF OmpCloudexpressEntriesEntry
    MAX-ACCESS  not-accessible
    STATUS      current
    DESCRIPTION "Cloudexpress entries table"
    ::= { ompCloudexpressRoutes 1 }

-- tagpath /omp/cloudexpress/entries
ompCloudexpressEntriesEntry OBJECT-TYPE
    SYNTAX      OmpCloudexpressEntriesEntry
    MAX-ACCESS  not-accessible
    STATUS      current
    DESCRIPTION "Cloudexpress entries table"
    INDEX { ompCloudexpressEntriesTenantId, 
            ompCloudexpressEntriesVpnId, 
            ompCloudexpressEntriesOriginator, 
            ompCloudexpressEntriesAppId, 
            ompCloudexpressEntriesAppType, 
            ompCloudexpressEntriesSubAppId}
        ::= { ompCloudexpressEntriesTable 1 }

OmpCloudexpressEntriesEntry ::=
    SEQUENCE {
        ompCloudexpressEntriesTenantId Unsigned32,
        ompCloudexpressEntriesVpnId Unsigned32,
        ompCloudexpressEntriesOriginator InetAddressIP,
        ompCloudexpressEntriesAppId Unsigned32,
        ompCloudexpressEntriesAppType UnsignedByte,
        ompCloudexpressEntriesSubAppId Unsigned32,
        ompCloudexpressEntriesAppName String
    }

-- tagpath /omp/cloudexpress/entries/tenant-id
ompCloudexpressEntriesTenantId OBJECT-TYPE
    SYNTAX      Unsigned32
    MAX-ACCESS  not-accessible
    STATUS      current
    DESCRIPTION "Tenant ID"
    ::= { ompCloudexpressEntriesEntry 1 }

-- tagpath /omp/cloudexpress/entries/vpn-id
ompCloudexpressEntriesVpnId OBJECT-TYPE
    SYNTAX      Unsigned32 (0 .. 65530)
    MAX-ACCESS  not-accessible
    STATUS      current
    DESCRIPTION "VPN ID"
    ::= { ompCloudexpressEntriesEntry 2 }

-- tagpath /omp/cloudexpress/entries/originator
ompCloudexpressEntriesOriginator OBJECT-TYPE
    SYNTAX      InetAddressIP
    MAX-ACCESS  not-accessible
    STATUS      current
    DESCRIPTION "Originator"
    ::= { ompCloudexpressEntriesEntry 3 }

-- tagpath /omp/cloudexpress/entries/app_id
ompCloudexpressEntriesAppId OBJECT-TYPE
    SYNTAX      Unsigned32
    MAX-ACCESS  not-accessible
    STATUS      current
    DESCRIPTION "App ID"
    ::= { ompCloudexpressEntriesEntry 4 }

-- tagpath /omp/cloudexpress/entries/app_type
ompCloudexpressEntriesAppType OBJECT-TYPE
    SYNTAX      UnsignedByte
    MAX-ACCESS  not-accessible
    STATUS      current
    DESCRIPTION "App type"
    ::= { ompCloudexpressEntriesEntry 5 }

-- tagpath /omp/cloudexpress/entries/subapp_id
ompCloudexpressEntriesSubAppId OBJECT-TYPE
    SYNTAX      Unsigned32
    MAX-ACCESS  not-accessible
    STATUS      current
    DESCRIPTION "Subapp ID"
    ::= { ompCloudexpressEntriesEntry 6 }

-- tagpath /omp/cloudexpress/entries/appname
ompCloudexpressEntriesAppName OBJECT-TYPE
    SYNTAX      String
    MAX-ACCESS  read-only
    STATUS      current
    DESCRIPTION "App name"
    ::= { ompCloudexpressEntriesEntry 7 }

-- tagpath /omp/cloudexpress/entries/received
ompCloudexpressEntriesReceivedTable OBJECT-TYPE
    SYNTAX      SEQUENCE OF OmpCloudexpressFamilyEntriesReceivedEntry
    MAX-ACCESS  not-accessible
    STATUS      current
    DESCRIPTION "Cloudexpress entries received table"
    ::= { ompCloudexpressRoutes 2 }

-- tagpath /omp/cloudexpress/entries/received
ompCloudexpressEntriesReceivedEntry OBJECT-TYPE
    SYNTAX      OmpCloudexpressFamilyEntriesReceivedEntry
    MAX-ACCESS  not-accessible
    STATUS      current
    DESCRIPTION "Cloudexpress entries received table"
    INDEX { ompCloudexpressEntriesTenantId, 
            ompCloudexpressEntriesVpnId, 
            ompCloudexpressEntriesOriginator, 
            ompCloudexpressEntriesAppId, 
            ompCloudexpressEntriesAppType, 
            ompCloudexpressEntriesSubAppId, 
            ompCloudexpressEntriesReceivedFromPeer }
        ::= { ompCloudexpressEntriesReceivedTable 1 }

OmpCloudexpressFamilyEntriesReceivedEntry ::=
    SEQUENCE {
        ompCloudexpressEntriesReceivedFromPeer InetAddressIP,
        ompCloudexpressEntriesReceivedStatus RibInStatusType,
        ompCloudexpressEntriesReceivedLossReason LossReasonEnum,
        ompCloudexpressEntriesReceivedLatency Unsigned32,
        ompCloudexpressEntriesReceivedLoss Unsigned32
    }

-- tagpath /omp/cloudexpress/entries/received/from-peer
ompCloudexpressEntriesReceivedFromPeer OBJECT-TYPE
    SYNTAX      InetAddressIP
    MAX-ACCESS  not-accessible
    STATUS      current
    DESCRIPTION "From peer IP"
    ::= { ompCloudexpressEntriesReceivedEntry 1 }

-- tagpath /omp/cloudexpress/entries/received/status
ompCloudexpressEntriesReceivedStatus OBJECT-TYPE
    SYNTAX      RibInStatusType
    MAX-ACCESS  read-only
    STATUS      current
    DESCRIPTION "RIB-in status"
    ::= { ompCloudexpressEntriesReceivedEntry 2 }

-- tagpath /omp/cloudexpress/entries/received/loss-reason
ompCloudexpressEntriesReceivedLossReason OBJECT-TYPE
    SYNTAX      LossReasonEnum
    MAX-ACCESS  read-only
    STATUS      current
    DESCRIPTION "Loss reason"
    ::= { ompCloudexpressEntriesReceivedEntry 3 }

-- tagpath /omp/cloudexpress/entries/received/latency
ompCloudexpressEntriesReceivedLatency OBJECT-TYPE
    SYNTAX      Unsigned32
    MAX-ACCESS  read-only
    STATUS      current
    DESCRIPTION "Latency"
    ::= { ompCloudexpressEntriesReceivedEntry 4 }

-- tagpath /omp/cloudexpress/entries/received/loss
ompCloudexpressEntriesReceivedLoss OBJECT-TYPE
    SYNTAX      Unsigned32
    MAX-ACCESS  read-only
    STATUS      current
    DESCRIPTION "Loss"
    ::= { ompCloudexpressEntriesReceivedEntry 5 }

-- tagpath /omp/cloudexpress/entries/advertised
ompCloudexpressEntriesAdvertisedTable OBJECT-TYPE
    SYNTAX      SEQUENCE OF OmpCloudexpressEntriesAdvertisedEntry
    MAX-ACCESS  not-accessible
    STATUS      current
    DESCRIPTION "Cloudexpress entries advertised table"
    ::= { ompCloudexpressRoutes 3 }

-- tagpath /omp/cloudexpress/entries/advertised
ompCloudexpressEntriesAdvertisedEntry OBJECT-TYPE
    SYNTAX      OmpCloudexpressEntriesAdvertisedEntry
    MAX-ACCESS  not-accessible
    STATUS      current
    DESCRIPTION "Cloudexpress entries advertised table"
    INDEX { ompCloudexpressEntriesTenantId, 
            ompCloudexpressEntriesVpnId, 
            ompCloudexpressEntriesOriginator, 
            ompCloudexpressEntriesAppId, 
            ompCloudexpressEntriesAppType, 
            ompCloudexpressEntriesSubAppId, 
            ompCloudexpressEntriesAdvertisedToPeer }
        ::= { ompCloudexpressEntriesAdvertisedTable 1 }

OmpCloudexpressEntriesAdvertisedEntry ::=
    SEQUENCE {
        ompCloudexpressEntriesAdvertisedToPeer InetAddressIP,
        ompCloudexpressEntriesAdvertisedLatency Unsigned32,
        ompCloudexpressEntriesAdvertisedLoss Unsigned32
    }

-- tagpath /omp/cloudexpress/entries/advertised/to-peer
ompCloudexpressEntriesAdvertisedToPeer OBJECT-TYPE
    SYNTAX      InetAddressIP
    MAX-ACCESS  not-accessible
    STATUS      current
    DESCRIPTION "To peer IP"
    ::= { ompCloudexpressEntriesAdvertisedEntry 1 }

-- tagpath /omp/cloudexpress/entries/advertised/latency
ompCloudexpressEntriesAdvertisedLatency OBJECT-TYPE
    SYNTAX      Unsigned32
    MAX-ACCESS  read-only
    STATUS      current
    DESCRIPTION "Latency"
    ::= { ompCloudexpressEntriesAdvertisedEntry 2 }

-- tagpath /omp/cloudexpress/entries/advertised/loss
ompCloudexpressEntriesAdvertisedLoss OBJECT-TYPE
    SYNTAX      Unsigned32
    MAX-ACCESS  read-only
    STATUS      current
    DESCRIPTION "Loss"
    ::= { ompCloudexpressEntriesAdvertisedEntry 3 }

-- ********************************************************************
-- *  Notification Objects
-- ********************************************************************

netconfNotificationSeverity OBJECT-TYPE
    SYNTAX      NotificationSeverity
    MAX-ACCESS  read-only
    STATUS      current
    DESCRIPTION "Netconf notification severity level"
    ::= { ciscoSdwanOmpMIBNotifObjects 2 }

ciscoSdwanOmpNumberOfVsmarts OBJECT-TYPE
    SYNTAX      Unsigned32
    MAX-ACCESS  read-only
    STATUS      current
    DESCRIPTION "Number of vsmarts"
    ::= { ciscoSdwanOmpMIBNotifObjects 3 }

ciscoSdwanOmpNewState OBJECT-TYPE
    SYNTAX      OperState
    MAX-ACCESS  read-only
    STATUS      current
    DESCRIPTION "OMP new state"
    ::= { ciscoSdwanOmpMIBNotifObjects 4 }

ciscoSdwanOmpPeer OBJECT-TYPE
    SYNTAX      InetAddressIP
    MAX-ACCESS  read-only
    STATUS      current
    DESCRIPTION "OMP peer"
    ::= { ciscoSdwanOmpMIBNotifObjects 5 }

ciscoSdwanOmpPeerNewState OBJECT-TYPE
    SYNTAX      PeerState
    MAX-ACCESS  read-only
    STATUS      current
    DESCRIPTION "Peer state"
    ::= { ciscoSdwanOmpMIBNotifObjects 6 }

ciscoSdwanOmpPolicy OBJECT-TYPE
    SYNTAX      OmpPolicyState
    MAX-ACCESS  read-only
    STATUS      current
    DESCRIPTION "OMP policy state"
    ::= { ciscoSdwanOmpMIBNotifObjects 7 }

ciscoSdwanOmpVsmartPeer OBJECT-TYPE
    SYNTAX      InetAddressIP
    MAX-ACCESS  read-only
    STATUS      current
    DESCRIPTION "Peer vsmart"
    ::= { ciscoSdwanOmpMIBNotifObjects 8 }

-- ********************************************************************
-- *  Notifications
-- ********************************************************************
ciscoSdwanOmpOmpNumberOfVsmartsChange NOTIFICATION-TYPE
        OBJECTS {
                netconfNotificationSeverity,
                ciscoSdwanOmpNumberOfVsmarts
        }
        STATUS current
        DESCRIPTION "Cisco SDWAN trap from omp"
        ::= { ciscoSdwanOmpMIBNotifs 1 }

ciscoSdwanOmpOmpStateChange NOTIFICATION-TYPE
        OBJECTS {
                netconfNotificationSeverity,
                ciscoSdwanOmpNewState
        }
        STATUS current
        DESCRIPTION "Cisco SDWAN trap from omp"
        ::= { ciscoSdwanOmpMIBNotifs 2 }

ciscoSdwanOmpOmpPeerStateChange NOTIFICATION-TYPE
        OBJECTS {
                netconfNotificationSeverity,
                ciscoSdwanOmpPeer,
                ciscoSdwanOmpPeerNewState
        }
        STATUS current
        DESCRIPTION "Cisco SDWAN trap from omp"
        ::= { ciscoSdwanOmpMIBNotifs 3 }

ciscoSdwanOmpOmpPolicy NOTIFICATION-TYPE
        OBJECTS {
                netconfNotificationSeverity,
                ciscoSdwanOmpPolicy,
                ciscoSdwanOmpVsmartPeer
        }
        STATUS current
        DESCRIPTION "Cisco SDWAN trap from omp"
        ::= { ciscoSdwanOmpMIBNotifs 4 }

-- ********************************************************************
-- *    Compliance statements
-- ********************************************************************

ciscoSdwanOmpMIBCompliances OBJECT IDENTIFIER
    ::= { ciscoSdwanOmpMIBConform 1 }

ciscoSdwanOmpMIBGroups OBJECT IDENTIFIER
    ::= { ciscoSdwanOmpMIBConform 2 }

ciscoSdwanOmpMIBCompliance MODULE-COMPLIANCE
    STATUS            current
    DESCRIPTION
        "The compliance statement for the SNMP entities
         that implement the ciscoSdwanOmpMIB module."
    MODULE          -- this module
    MANDATORY-GROUPS {
          cSdwanOmpNotifObjsGroup,
          cSdwanOmpNotifsGroup,
          cSdwanOmpSummaryObjsGroup,
          cSdwanOmpSummaryMtPeersObjsGroup,
          cSdwanOmpRoutesObjsGroup,
          cSdwanOmpTlocPathsObjsGroup,
          cSdwanOmpTlocsObjsGroup,
          cSdwanOmpServicesObjsGroup,
          cSdwanOmpMulticastAutoDiscoverObjsGroup,
          cSdwanOmpMulticastRoutesObjsGroup,
          cSdwanOmpCloudexpressRoutesObjsGroup
    }
    ::= { ciscoSdwanOmpMIBCompliances 1 }

-- ********************************************************************
-- *    Units of conformance
-- ********************************************************************
cSdwanOmpNotifObjsGroup OBJECT-GROUP
    OBJECTS {
               netconfNotificationSeverity,
               ciscoSdwanOmpNumberOfVsmarts,
               ciscoSdwanOmpNewState,
               ciscoSdwanOmpPeer,
               ciscoSdwanOmpPeerNewState,
               ciscoSdwanOmpPolicy,
               ciscoSdwanOmpVsmartPeer
            }
    STATUS          current
    DESCRIPTION
        "This is a collection of objects of
         OMP notification objects."
    ::= { ciscoSdwanOmpMIBGroups 1 }

cSdwanOmpNotifsGroup NOTIFICATION-GROUP
   NOTIFICATIONS {
                    ciscoSdwanOmpOmpNumberOfVsmartsChange,
                    ciscoSdwanOmpOmpStateChange,
                    ciscoSdwanOmpOmpPeerStateChange,
                    ciscoSdwanOmpOmpPolicy
                 }
    STATUS          current
    DESCRIPTION
        "This is a collection of OMP notifications."
    ::= { ciscoSdwanOmpMIBGroups 2 }

cSdwanOmpSummaryObjsGroup OBJECT-GROUP
    OBJECTS {
    ompSummaryOperstate,
    ompSummaryAdminstate,
    ompSummaryDevicetype,
    ompSummaryOmpuptime,
    ompSummaryOmpdowntime,
    ompSummaryRoutesReceived,
    ompSummaryRoutesInstalled,
    ompSummaryRoutesSent,
    ompSummaryTlocsReceived,
    ompSummaryTlocsInstalled,
    ompSummaryTlocsSent,
    ompSummaryServicesReceived,
    ompSummaryServicesInstalled,
    ompSummaryServicesSent,
    ompSummaryMcastRoutesReceived,
    ompSummaryMcastRoutesInstalled,
    ompSummaryMcastRoutesSent,
    ompSummaryHelloReceived,
    ompSummaryHelloSent,
    ompSummaryHandshakeReceived,
    ompSummaryHandshakeSent,
    ompSummaryAlertReceived,
    ompSummaryAlertSent,
    ompSummaryInformReceived,
    ompSummaryInformSent,
    ompSummaryUpdateReceived,
    ompSummaryUpdateSent,
    ompSummaryPolicyReceived,
    ompSummaryPolicySent,
    ompSummaryPacketsReceived,
    ompSummaryPacketsSent,
    ompSummaryVsmartPeers
                 }
    STATUS          current
    DESCRIPTION
        "This is a collection of OMP Summary objects."
    ::= { ciscoSdwanOmpMIBGroups 3 }

cSdwanOmpSummaryMtPeersObjsGroup OBJECT-GROUP
    OBJECTS {
        ompSummaryMtPeersType,
        ompSummaryMtPeersDomainId,
        ompSummaryMtPeersSiteId,
        ompSummaryMtPeersRegionId,
        ompSummaryMtPeersState,
        ompSummaryMtPeersVersion,
        ompSummaryMtPeersLegit,
        ompSummaryMtPeersUpcount,
        ompSummaryMtPeersDowncount,
        ompSummaryMtPeersLastuptime,
        ompSummaryMtPeersLastdowntime,
        ompSummaryMtPeersUpTime,
        ompSummaryMtPeersDownTime,
        ompSummaryMtPeersHoldtime,
        ompSummaryMtPeersSitepolicy,
        ompSummaryMtPeersPolicyin,
        ompSummaryMtPeersPolicyout,
        ompSummaryMtPeersGracefulRestart,
        ompSummaryMtPeersGracefulRestartInterval,
        ompSummaryMtPeersHelloReceived,
        ompSummaryMtPeersHelloSent,
        ompSummaryMtPeersHandshakeReceived,
        ompSummaryMtPeersHandshakeSent,
        ompSummaryMtPeersAlertReceived,
        ompSummaryMtPeersAlertSent,
        ompSummaryMtPeersInformReceived,
        ompSummaryMtPeersInformSent,
        ompSummaryMtPeersUpdateReceived,
        ompSummaryMtPeersUpdateSent,
        ompSummaryMtPeersPolicyReceived,
        ompSummaryMtPeersPolicySent,
        ompSummaryMtPeersPacketsReceived,
        ompSummaryMtPeersPacketsSent,
        ompSummaryMtPeersRoutesReceived,
        ompSummaryMtPeersRoutesInstalled,
        ompSummaryMtPeersRoutesSent,
        ompSummaryMtPeersTlocsReceived,
        ompSummaryMtPeersTlocsInstalled,
        ompSummaryMtPeersTlocsSent,
        ompSummaryMtPeersServicesReceived,
        ompSummaryMtPeersServicesInstalled,
        ompSummaryMtPeersServicesSent,
        ompSummaryMtPeersMcastRoutesReceived,
        ompSummaryMtPeersMcastRoutesInstalled,
        ompSummaryMtPeersMcastRoutesSent,
        ompSummaryMtPeersControlUp,
        ompSummaryMtPeersStaging,
        ompSummaryMtPeersRefresh,
        ompSummaryMtPeersOverlayId,
        ompSummaryMtPeersRoutesReceivedIPv6,
        ompSummaryMtPeersRoutesInstalledIPv6,
        ompSummaryMtPeersRoutesSentIPv6,
        ompSummaryMtPeersRoutesReceivedTotal,
        ompSummaryMtPeersRoutesInstalledTotal,
        ompSummaryMtPeersRoutesSentTotal,
        ompSummaryMtPeersServicesReceivedIPv6,
        ompSummaryMtPeersServicesInstalledIPv6,
        ompSummaryMtPeersServicesSentIPv6
                 }
    STATUS          current
    DESCRIPTION
        "This is a collection of OMP Summary 
         multi-tenant peers objects."
    ::= { ciscoSdwanOmpMIBGroups 4 }

cSdwanOmpRoutesObjsGroup OBJECT-GROUP
    OBJECTS {
    ompRoutesTableFamilyAddressFamily,
    ompRoutesTableFamilyEntriesTenantId,
    ompRoutesTableFamilyEntriesVpnId,
    ompRoutesTableFamilyEntriesPrefix,
    ompRoutesTableFamilyEntriesReceivedLabel,
    ompRoutesTableFamilyEntriesReceivedStatus,
    ompRoutesTableFamilyEntriesReceivedLossReason,
    ompRoutesTableFamilyEntriesReceivedLostToPeer,
    ompRoutesTableFamilyEntriesReceivedLostToPathId,
    ompRoutesTableFamilyEntriesReceivedAttributesTlocIp,
    ompRoutesTableFamilyEntriesReceivedAttributesTlocColor,
    ompRoutesTableFamilyEntriesReceivedAttributesTlocEncap,
    ompRoutesTableFamilyEntriesReceivedAttributesOriginProtocol,
    ompRoutesTableFamilyEntriesReceivedAttributesOriginMetric,
    ompRoutesTableFamilyEntriesReceivedAttributesDomainId,
    ompRoutesTableFamilyEntriesReceivedAttributesSiteId,
    ompRoutesTableFamilyEntriesReceivedAttributesPreference,
    ompRoutesTableFamilyEntriesReceivedAttributesTag,
    ompRoutesTableFamilyEntriesReceivedAttributesUnknownAttributeLen,
    ompRoutesTableFamilyEntriesReceivedAttributesOriginator,
    ompRoutesTableFamilyEntriesReceivedAttributesUltimateTlocIp,
    ompRoutesTableFamilyEntriesReceivedAttributesUltimateTlocColor,
    ompRoutesTableFamilyEntriesReceivedAttributesUltimateTlocEncap,
    ompRoutesTableFamilyEntriesReceivedAttributesUltimateTlocAction,
    ompRoutesTableFamilyEntriesReceivedAttributesOverlayId,
    ompRoutesTableFamilyEntriesReceivedAttributesAsPath,
    ompRoutesTableFamilyEntriesReceivedAttributesCommunity,
    ompRoutesTableFamilyEntriesReceivedAttributesRegionId,
    ompRoutesTableFamilyEntriesReceivedAttributesRegionPath,
    ompRoutesTableFamilyEntriesAdvertisedToPeer,
    ompRoutesTableFamilyEntriesAdvertisedPathsAdvertiseId,
    ompRoutesTableFamilyEntriesAdvertisedPathsAttributesLabel,
    ompRoutesTableFamilyEntriesAdvertisedPathsAttributesTlocIp,
    ompRoutesTableFamilyEntriesAdvertisedPathsAttributesTlocColor,
    ompRoutesTableFamilyEntriesAdvertisedPathsAttributesTlocEncap,
    ompRoutesTableFamilyEntriesAdvertisedPathsAttrbOrgProto,
    ompRoutesTableFamilyEntriesAdvertisedPathsAttributesOriginMetric,
    ompRoutesTableFamilyEntriesAdvertisedPathsAttributesDomainId,
    ompRoutesTableFamilyEntriesAdvertisedPathsAttributesSiteId,
    ompRoutesTableFamilyEntriesAdvertisedPathsAttributesPreference,
    ompRoutesTableFamilyEntriesAdvertisedPathsAttributesTag,
    ompRoutesTableFamilyEntriesAdvertisedPathsAttrbUnkAttrbLen,
    ompRoutesTableFamilyEntriesAdvertisedPathsAttributesOriginator,
    ompRoutesTableFamilyEntriesAdvertisedPathsAttrUltTlocIp,
    ompRoutesTableFamilyEntriesAdvertisedPathsAttrUltTlocColor,
    ompRoutesTableFamilyEntriesAdvertisedPathsAttrUltTlocEncap,
    ompRoutesTableFamilyEntriesAdvertisedPathsAttrUltTlocAction,
    ompRoutesTableFamilyEntriesAdvertisedPathsAttributesOverlayId,
    ompRoutesTableFamilyEntriesAdvertisedPathsAttributesAsPath,
    ompRoutesTableFamilyEntriesAdvertisedPathsAttributesCommunity,
    ompRoutesTableFamilyEntriesAdvertisedPathsAttributesRegionId,
    ompRoutesTableFamilyEntriesAdvertisedPathsAttributesRegionPath
            }
    STATUS          current
    DESCRIPTION
        "This is a collection of objects of
         OMP route table objects."
    ::= { ciscoSdwanOmpMIBGroups 5 }

cSdwanOmpTlocPathsObjsGroup OBJECT-GROUP
    OBJECTS {
    ompTlocPathsEntriesIp,
    ompTlocPathsEntriesColor,
    ompTlocPathsEntriesEncap,
    ompTlocPathsEntriesPathsPreference,
    ompTlocPathsEntriesPathsMtu,
    ompTlocPathsEntriesPathsBfdStatus,
    ompTlocPathsEntriesPathsStatus,
    ompTlocPathsEntriesPathsStale,
    ompTlocPathsEntriesPathsLinksFromTlocIp,
    ompTlocPathsEntriesPathsLinksFromTlocColor,
    ompTlocPathsEntriesPathsLinksFromTlocEncap,
    ompTlocPathsEntriesPathsLinksToTlocIp,
    ompTlocPathsEntriesPathsLinksToTlocColor,
    ompTlocPathsEntriesPathsLinksToTlocEncap,
    ompTlocPathsEntriesPathsLinksLabel
            }
    STATUS          current
    DESCRIPTION
        "This is a collection of objects of
         OMP TLOC paths table objects."
    ::= { ciscoSdwanOmpMIBGroups 6 }

cSdwanOmpTlocsObjsGroup OBJECT-GROUP
    OBJECTS {
    ompTlocsFamilyAddressFamily,
    ompTlocsFamilyEntriesIp,
    ompTlocsFamilyEntriesColor,
    ompTlocsFamilyEntriesEncap,
    ompTlocsFamilyEntriesReceivedStatus,
    ompTlocsFamilyEntriesReceivedLossReason,
    ompTlocsFamilyEntriesReceivedLostToPeer,
    ompTlocsFamilyEntriesReceivedLostToPathId,
    ompTlocsFamilyEntriesReceivedAttributesAttributeType,
    ompTlocsFamilyEntriesReceivedAttributesTlocEncapKey,
    ompTlocsFamilyEntriesReceivedAttributesTlocEncapProto,
    ompTlocsFamilyEntriesReceivedAttributesTlocEncapSpi,
    ompTlocsFamilyEntriesReceivedAttributesTlocEncapEncryptType,
    ompTlocsFamilyEntriesReceivedAttributesTlocEncapIntegType,
    ompTlocsFamilyEntriesReceivedAttributesTlocMapPublicIp,
    ompTlocsFamilyEntriesReceivedAttributesTlocMapPublicPort,
    ompTlocsFamilyEntriesReceivedAttributesTlocMapPrivateIp,
    ompTlocsFamilyEntriesReceivedAttributesTlocMapPrivatePort,
    ompTlocsFamilyEntriesReceivedAttributesTlocMapV6PublicIp,
    ompTlocsFamilyEntriesReceivedAttributesTlocMapV6PublicPort,
    ompTlocsFamilyEntriesReceivedAttributesTlocMapV6PrivateIp,
    ompTlocsFamilyEntriesReceivedAttributesTlocMapV6PrivatePort,
    ompTlocsFamilyEntriesReceivedAttributesBfdStatus,
    ompTlocsFamilyEntriesReceivedAttributesDomainId,
    ompTlocsFamilyEntriesReceivedAttributesSiteId,
    ompTlocsFamilyEntriesReceivedAttributesPreference,
    ompTlocsFamilyEntriesReceivedAttributesTag,
    ompTlocsFamilyEntriesReceivedAttributesStale,
    ompTlocsFamilyEntriesReceivedAttributesCarrier,
    ompTlocsFamilyEntriesReceivedAttributesGroups,
    ompTlocsFamilyEntriesReceivedAttributesUnknownAttributeLen,
    ompTlocsFamilyEntriesReceivedAttributesWeight,
    ompTlocsFamilyEntriesReceivedAttributesGenId,
    ompTlocsFamilyEntriesReceivedAttributesVersion,
    ompTlocsFamilyEntriesReceivedAttributesOriginator,
    ompTlocsFamilyEntriesReceivedAttributesRestrict,
    ompTlocsFamilyEntriesReceivedAttributesOverlayId,
    ompTlocsFamilyEntriesReceivedAttributesBandwidth,
    ompTlocsFamilyEntriesReceivedAttributesQosGroup,
    ompTlocsFamilyEntriesReceivedAttributesBandwidthDmin,
    ompTlocsFamilyEntriesReceivedAttributesBandwidthDown,
    ompTlocsFamilyEntriesReceivedAttributesBandwidthDmax,
    ompTlocsFamilyEntriesReceivedAttributesAdaptQosPeriod,
    ompTlocsFamilyEntriesReceivedAttributesAdaptQosUp,
    ompTlocsFamilyEntriesReceivedAttributesOnDemand,
    ompTlocsFamilyEntriesAdvertisedTenantId,
    ompTlocsFamilyEntriesAdvertisedToPeer,
    ompTlocsFamilyEntriesAdvertisedAttributesTlocEncapKey,
    ompTlocsFamilyEntriesAdvertisedAttributesTlocEncapProto,
    ompTlocsFamilyEntriesAdvertisedAttributesTlocEncapSpi,
    ompTlocsFamilyEntriesAdvertisedAttributesTlocEncapEncryptType,
    ompTlocsFamilyEntriesAdvertisedAttributesTlocEncapIntegType,
    ompTlocsFamilyEntriesAdvertisedAttributesTlocMapPublicIp,
    ompTlocsFamilyEntriesAdvertisedAttributesTlocMapPublicPort,
    ompTlocsFamilyEntriesAdvertisedAttributesTlocMapPrivateIp,
    ompTlocsFamilyEntriesAdvertisedAttributesTlocMapPrivatePort,
    ompTlocsFamilyEntriesAdvertisedAttributesTlocMapV6PublicIp,
    ompTlocsFamilyEntriesAdvertisedAttributesTlocMapV6PublicPort,
    ompTlocsFamilyEntriesAdvertisedAttributesTlocMapV6PrivateIp,
    ompTlocsFamilyEntriesAdvertisedAttributesTlocMapV6PrivatePort,
    ompTlocsFamilyEntriesAdvertisedAttributesDomainId,
    ompTlocsFamilyEntriesAdvertisedAttributesSiteId,
    ompTlocsFamilyEntriesAdvertisedAttributesPreference,
    ompTlocsFamilyEntriesAdvertisedAttributesTag,
    ompTlocsFamilyEntriesAdvertisedAttributesStale,
    ompTlocsFamilyEntriesAdvertisedAttributesCarrier,
    ompTlocsFamilyEntriesAdvertisedAttributesGroups,
    ompTlocsFamilyEntriesAdvertisedAttributesUnknownAttributeLen,
    ompTlocsFamilyEntriesAdvertisedAttributesWeight,
    ompTlocsFamilyEntriesAdvertisedAttributesGenId,
    ompTlocsFamilyEntriesAdvertisedAttributesVersion,
    ompTlocsFamilyEntriesAdvertisedAttributesOriginator,
    ompTlocsFamilyEntriesAdvertisedAttributesRestrict,
    ompTlocsFamilyEntriesAdvertisedAttributesOverlayId,
    ompTlocsFamilyEntriesAdvertisedAttributesBandwidth,
    ompTlocsFamilyEntriesAdvertisedAttributesBandwidthDmin,
    ompTlocsFamilyEntriesAdvertisedAttributesBandwidthDown,
    ompTlocsFamilyEntriesAdvertisedAttributesBandwidthDmax,
    ompTlocsFamilyEntriesAdvertisedAttributesAdaptQosPeriod,
    ompTlocsFamilyEntriesAdvertisedAttributesAdaptQosUp,
    ompTlocsFamilyEntriesAdvertisedAttributesQosGroup,
    ompTlocsFamilyEntriesAdvertisedAttributesOnDemand
            }
    STATUS          current
    DESCRIPTION
        "This is a collection of objects of
         OMP TLOCs objects."
    ::= { ciscoSdwanOmpMIBGroups 7 }

cSdwanOmpServicesObjsGroup OBJECT-GROUP
    OBJECTS {
    ompServicesFamilyAddressFamily,
    ompServicesFamilyEntriesTenantId,
    ompServicesFamilyEntriesVpnId,
    ompServicesFamilyEntriesService,
    ompServicesFamilyEntriesOriginator,
    ompServicesFamilyEntriesReceivedRegionId,
    ompServicesFamilyEntriesReceivedLabel,
    ompServicesFamilyEntriesReceivedStatus,
    ompServicesFamilyEntriesReceivedLossReason,
    ompServicesFamilyEntriesReceivedLostToPeer,
    ompServicesFamilyEntriesReceivedLostToPathId,
    ompServicesFamilyEntriesReceivedVrfId,
    ompServicesFamilyEntriesAdvertisedToPeer
            }
    STATUS          current
    DESCRIPTION
        "This is a collection of objects of
         OMP Services objects."
    ::= { ciscoSdwanOmpMIBGroups 8 }

cSdwanOmpMulticastAutoDiscoverObjsGroup OBJECT-GROUP
    OBJECTS {
    ompMulticastAutoDiscoverFamilyAddressFamily,
    ompMulticastAutoDiscoverFamilyEntriesTenantId,
    ompMulticastAutoDiscoverFamilyEntriesVpnId,
    ompMulticastAutoDiscoverFamilyEntriesSourceOriginator,
    ompMulticastAutoDiscoverFamilyEntriesReceivedStatus,
    ompMulticastAutoDiscoverFamilyEntriesReceivedLossReason,
    ompMulticastAutoDiscoverFamilyEntriesAdvertisedToPeer
            }
    STATUS          current
    DESCRIPTION
        "This is a collection of objects of
         OMP multicast autodiscover objects."
    ::= { ciscoSdwanOmpMIBGroups 9 }

cSdwanOmpMulticastRoutesObjsGroup OBJECT-GROUP
    OBJECTS {
    ompMulticastRoutesFamilyAddressFamily,
    ompMulticastRoutesFamilyEntriesTenantId,
    ompMulticastRoutesFamilyEntriesType,
    ompMulticastRoutesFamilyEntriesVpnId,
    ompMulticastRoutesFamilyEntriesDestination,
    ompMulticastRoutesFamilyEntriesGroup,
    ompMulticastRoutesFamilyEntriesSource,
    ompMulticastRoutesFamilyEntriesSourceOriginator,
    ompMulticastRoutesFamilyEntriesReceivedRp,
    ompMulticastRoutesFamilyEntriesReceivedReceivedPrunes,
    ompMulticastRoutesFamilyEntriesReceivedStatus,
    ompMulticastRoutesFamilyEntriesReceivedLossReason,
    ompMulticastRoutesFamilyEntriesAdvertisedRp,
    ompMulticastRoutesFamilyEntriesAdvertisedAdvertisedPrunes
            }
    STATUS          current
    DESCRIPTION
        "This is a collection of objects of
         OMP multicast routes  objects."
    ::= { ciscoSdwanOmpMIBGroups 10 }

cSdwanOmpCloudexpressRoutesObjsGroup OBJECT-GROUP
    OBJECTS {
    ompCloudexpressEntriesAppName,
    ompCloudexpressEntriesReceivedStatus,
    ompCloudexpressEntriesReceivedLossReason,
    ompCloudexpressEntriesReceivedLatency,
    ompCloudexpressEntriesReceivedLoss,
    ompCloudexpressEntriesAdvertisedLatency,
    ompCloudexpressEntriesAdvertisedLoss
            }
    STATUS          current
    DESCRIPTION
        "This is a collection of objects of
         OMP cloudexpress routes  objects."
    ::= { ciscoSdwanOmpMIBGroups 11 }

END
