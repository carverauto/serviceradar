-- *****************************************************************
-- CISCO-FABRICPATH-TOPOLOGY-CAPABILITY.my:
-- Cisco CISCO-FABRICPATH-TOPOLOGY-MIB AGENT-CAPABILITIES
--   
-- July 2013,  Liwei Wang
--
-- Copyright (c) 2013 by Cisco Systems, Inc.
-- All rights reserved.
-- *****************************************************************

CISCO-FABRICPATH-TOPOLOGY-CAPABILITY DEFINITIONS ::= BEGIN

IMPORTS
    MODULE-IDENTITY
        FROM SNMPv2-SMI
    AGENT-CAPABILITIES
        FROM SNMPv2-CONF
    ciscoAgentCapability
        FROM CISCO-SMI;

ciscoFabricPathTopologyCapability MODULE-IDENTITY
    LAST-UPDATED    "201307161200Z"
    ORGANIZATION    "Cisco Systems, Inc."
    CONTACT-INFO
            "Cisco Systems
            Customer Service

            Postal: 170 West Tasman Drive
            San Jose, CA  95134
            USA

            Tel: +1 800 553-NETS

            E-mail: cs-lan-switch-snmp@cisco.com"
    DESCRIPTION
        "The capabilities description of
        CISCO-FABRICPATH-TOPOLOGY-MIB."
    REVISION        "201307161200Z"
    DESCRIPTION
        "Initial version of this MIB module."
    ::= { ciscoAgentCapability 620 }

ciscoFabricPathTopologyCapNxOSV06R0202PN7k AGENT-CAPABILITIES
    PRODUCT-RELEASE "Cisco NX-OS 6.2(2) on Nexus 7000 series devices."
    STATUS          current
    DESCRIPTION
        "CISCO-FABRICPATH-TOPOLOGY-MIB capabilities."
    SUPPORTS        CISCO-FABRICPATH-TOPOLOGY-MIB
    INCLUDES        {
                        cfptTopologyGroup,
                        cfptTopologyIfGroup,
                        cfptTopologyIfVlanGroup,
                        cfptTopologyTreeGroup
                    }
    VARIATION       cfptTopologyDescr 
    ACCESS          read-only
    DESCRIPTION
        "Write access is not supported."
    VARIATION       cfptTopologyVlansFirst2K 
    ACCESS          read-only
    DESCRIPTION
        "Write access is not supported."
    VARIATION       cfptTopologyVlansSecond2K 
    ACCESS          read-only
    DESCRIPTION
        "Write access is not supported."
    VARIATION       cfptTopologyStorageType 
    ACCESS          read-only
    DESCRIPTION
        "Write access is not supported."
    VARIATION       cfptTopologyRowStatus 
    ACCESS          read-only
    DESCRIPTION
        "Write access is not supported."
    VARIATION       cfptTopologyIfStorageType 
    ACCESS          read-only
    DESCRIPTION
        "Write access is not supported."
    VARIATION       cfptTopologyIfRowStatus 
    ACCESS          read-only
    DESCRIPTION
        "Write access is not supported."


    ::= { ciscoFabricPathTopologyCapability 1 }

END
