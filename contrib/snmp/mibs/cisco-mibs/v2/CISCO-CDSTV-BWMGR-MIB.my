-- *****************************************************************
-- CISCO-CDSTV-BWMGR-MIB: Cisco CDS-TV Bandwidth Manager Management
-- Information Base
--   
-- June 2010, Rajat Ahuja.
--   
-- Copyright (c) 2010 by Cisco Systems, Inc.
--   
-- All rights reserved.
--   
-- *****************************************************************

CISCO-CDSTV-BWMGR-MIB DEFINITIONS ::= BEGIN

IMPORTS
    MODULE-IDENTITY,
    OBJECT-TYPE,
    Unsigned32
        FROM SNMPv2-SMI
    MODULE-COMPLIANCE,
    OBJECT-GROUP
        FROM SNMPv2-CONF
    InetPortNumber,
    InetAddressType,
    InetAddress
        FROM INET-ADDRESS-MIB
    TimeIntervalSec
        FROM CISCO-TC
    ciscoMgmt
        FROM CISCO-SMI;


ciscoCdstvBwmgrMIB MODULE-IDENTITY
    LAST-UPDATED    "201006240000Z"
    ORGANIZATION    "Cisco Systems, Inc."
    CONTACT-INFO
            "Cisco Systems
            Customer Service

            Postal: 170 W Tasman Drive
            San Jose, CA  95134
            USA

            Tel: +1 800 553-NETS

            E-mail: cs-cds@cisco.com"
    DESCRIPTION
        "This MIB module defines Bandwidth Manager configuration objects
        that facilitate the management of the Cisco Content Delivery
        System for TV (CDS-TV) product family.

        CDS-TV is a suite of products and software applications
        providing ingest, storage, caching, streaming, playout and
        on-demand delivery of video to television or set-top-box
        clients.

        The Bandwidth Manager runs on the master streamer and keeps
        track of allocated streams and VOD network resources.

        Abbreviations:

        CCP     Cache Control Protocol
        CDS     Content Delivery System
        CORBA   Common Object Request Broker Architecture 
        ISA     Interactive Services Architecture
        ISV     Integrated Streamer-Vault
        FSI     File Service Interface
        FTP     File Transfer Protocol
        MPEG    Motion Picture Experts Group
        MSA     Managed Services Architecture
        RTSP    Real-Time Streaming Protocol
        SOAP    Simple Object Access Protocol
        STB     Set-Top Box
        VOD     Video On-Demand

        Common terms:

        Catcher: Device responsible for receiving content (typically via
        satellite dishes and antennae) from content providers or from a
        Headend-In-The-Sky. 

        Content Ingest: Acquisition of content from a source such as a
        catcher or an FTP server for storing it locally and making it
        available to streamers as needed.

        Device Roles:

        Vault: Content delivery application responsible for ingesting
        and storing video content and making it available to streamers
        and/or caching nodes.

        Caching Nodes: Content delivery application responsible for
        caching content from vault (using CCP) and then streaming
        content out to streamers over HTTP or CCP.

        Streamer: Content delivery application responsible for streaming
        video out to STB's.

        ISV: Content delivery application capable of acting as both a
        vault and as a streamer in a single device."
    REVISION        "201006240000Z"
    DESCRIPTION
        "Initial version of this MIB module."
    ::= { ciscoMgmt 749 }


-- Textual Conventions definition will be defined before this line

ciscoCdstvBWMgrMIBNotifs  OBJECT IDENTIFIER
    ::= { ciscoCdstvBwmgrMIB 0 }

ciscoCdstvBWMgrMIBObjects  OBJECT IDENTIFIER
    ::= { ciscoCdstvBwmgrMIB 1 }

ciscoCdstvBWMgrMIBConform  OBJECT IDENTIFIER
    ::= { ciscoCdstvBwmgrMIB 2 }

ciscoCdstvBWMgrMIBCompliances  OBJECT IDENTIFIER
    ::= { ciscoCdstvBWMgrMIBConform 1 }


cdstvBWMgrAddressType OBJECT-TYPE
    SYNTAX          InetAddressType
    MAX-ACCESS      read-write
    STATUS          current
    DESCRIPTION
        "This object specifies the type of address used by the Bandwidth
        Manager. 

        The address is specified by cdstvBWMgrAddress." 
    ::= { ciscoCdstvBWMgrMIBObjects 1 }

cdstvBWMgrAddress OBJECT-TYPE
    SYNTAX          InetAddress
    MAX-ACCESS      read-write
    STATUS          current
    DESCRIPTION
        "This object specifies the address used by the Bandwidth
        Manager. The type of the address is specified by
        cdstvBWMgrAddressType." 
    ::= { ciscoCdstvBWMgrMIBObjects 2 }

cdstvBWMgrPort OBJECT-TYPE
    SYNTAX          InetPortNumber (0..65535)
    MAX-ACCESS      read-write
    STATUS          current
    DESCRIPTION
        "This object specifies the port number to listen on for incoming
        connections from the RTSP server."
    DEFVAL          { 7791 } 
    ::= { ciscoCdstvBWMgrMIBObjects 3 }

cdstvBWMgrDatabaseThreadPool OBJECT-TYPE
    SYNTAX          Unsigned32 (1..10000)
    MAX-ACCESS      read-write
    STATUS          current
    DESCRIPTION
        "This object specifies the maximum number of threads in the
        database connection pool."
    DEFVAL          { 10 } 
    ::= { ciscoCdstvBWMgrMIBObjects 4 }

cdstvBWMgrServerThreadPool OBJECT-TYPE
    SYNTAX          Unsigned32 (1..10000)
    MAX-ACCESS      read-write
    STATUS          current
    DESCRIPTION
        "This object specifies the maximum number of threads in the
        Bandwidth Manager server pool that are used to process RTSP
        requests for the duration of the connection."
    DEFVAL          { 5 } 
    ::= { ciscoCdstvBWMgrMIBObjects 5 }

cdstvBWMgrSyncThreadPool OBJECT-TYPE
    SYNTAX          Unsigned32 (1..10000)
    MAX-ACCESS      read-write
    STATUS          current
    DESCRIPTION
        "This object specifies the maximum number of threads available
        to synchronize sessions with the RTSP during a synchronization
        operation." 
    ::= { ciscoCdstvBWMgrMIBObjects 6 }

cdstvBWMgrSyncAlarm OBJECT-TYPE
    SYNTAX          TimeIntervalSec (2400..4294967295)
    UNITS           "seconds"
    MAX-ACCESS      read-write
    STATUS          current
    DESCRIPTION
        "This object specifies how often the synchronization alarm is
        triggered. The alarm is generated if the synchronization between
        RTSP client and server (typically, streamer and back-office, but
        varies by CDS deployment environment) fails. Note that this does
        not generate an SNMP notification."
    DEFVAL          { 864000 } 
    ::= { ciscoCdstvBWMgrMIBObjects 7 }
ciscoCdstvBWMgrMIBGroups  OBJECT IDENTIFIER
    ::= { ciscoCdstvBWMgrMIBConform 2 }


ciscoCdstvBWMgrMIBCompliance MODULE-COMPLIANCE
    STATUS          current
    DESCRIPTION
        "The compliance statement for the entities which
        implement the Cisco CDS TV Bandwidth Manager MIB."
    MODULE          -- this module
    MANDATORY-GROUPS { ciscoCdstvBWMgrMIBMainObjectGroup }

    OBJECT          cdstvBWMgrAddressType
    MIN-ACCESS      read-only
    DESCRIPTION
        "Write access is not required."

    OBJECT          cdstvBWMgrAddress
    MIN-ACCESS      read-only
    DESCRIPTION
        "Write access is not required."

    OBJECT          cdstvBWMgrPort
    MIN-ACCESS      read-only
    DESCRIPTION
        "Write access is not required."

    OBJECT          cdstvBWMgrDatabaseThreadPool
    MIN-ACCESS      read-only
    DESCRIPTION
        "Write access is not required."

    OBJECT          cdstvBWMgrServerThreadPool
    MIN-ACCESS      read-only
    DESCRIPTION
        "Write access is not required."

    OBJECT          cdstvBWMgrSyncThreadPool
    MIN-ACCESS      read-only
    DESCRIPTION
        "Write access is not required."

    OBJECT          cdstvBWMgrSyncAlarm
    MIN-ACCESS      read-only
    DESCRIPTION
        "Write access is not required."
    ::= { ciscoCdstvBWMgrMIBCompliances 1 }

-- Units of Conformance

ciscoCdstvBWMgrMIBMainObjectGroup OBJECT-GROUP
    OBJECTS         {
                        cdstvBWMgrAddress,
                        cdstvBWMgrPort,
                        cdstvBWMgrDatabaseThreadPool,
                        cdstvBWMgrServerThreadPool,
                        cdstvBWMgrSyncThreadPool,
                        cdstvBWMgrSyncAlarm,
                        cdstvBWMgrAddressType
                    }
    STATUS          current
    DESCRIPTION
        "A collection of objects that provide status of bandwidth
        manager configuration."
    ::= { ciscoCdstvBWMgrMIBGroups 1 }

END
