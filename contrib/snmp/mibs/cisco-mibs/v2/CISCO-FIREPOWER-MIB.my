-- ********************************************************************
-- CISCO-FIREPOWER-MIB.my
-- 
-- Cisco Firepower MIB Module
-- 
-- Copyright (c) 2005-2024 Cisco Systems, Inc. All rights reserved.
-- ********************************************************************

CISCO-FIREPOWER-MIB DEFINITIONS ::= BEGIN

IMPORTS
        Unsigned32,
        Counter32,
        OBJECT-TYPE,
        MODULE-IDENTITY,
        NOTIFICATION-TYPE
                FROM SNMPv2-SMI
        MODULE-COMPLIANCE,
        OBJECT-GROUP,
        NOTIFICATION-GROUP
                FROM SNMPv2-CONF
        SnmpAdminString
                FROM SNMP-FRAMEWORK-MIB
        RowPointer,                
        DateAndTime,
        TEXTUAL-CONVENTION
                FROM SNMPv2-TC
        ciscoMgmt
                FROM CISCO-SMI;

ciscoFirepowerMIB MODULE-IDENTITY
        LAST-UPDATED  "201001290000Z" 
        ORGANIZATION  "Cisco"
        CONTACT-INFO
            "Cisco Systems
            Customer Service

            Postal: 170 West Tasman Drive
            San Jose, CA  95134
            USA

            Tel: +1 800 553-NETS

            E-mail: firepower-mibs@cisco.com"
      DESCRIPTION
         "This MIB module defines the managed objects for
         Firepower (FPR) Manager.
                
         Cisco FPR Manager provides centralized management
         capabilities, creates a unified management domain, and
         serves as the central nervous system for Cisco Firepower.
         
         FPR configuration is comprised of operational and
         administrative settings. The data is organized hierarchically
         in a tree structure, starts from the top (root) and contains
         children and parent nodes. Each node in the tree is a managed
         object and each object in Firepower has a unique Distinguished
         Name (DN) that describes the object and its place in the tree.
         Every managed object is also identified through a
         CfprManagedObjectId of type integer.
         
         Managed objects are abstractions of real world resources,
         they represent the physical and logical components of Firepower,
         for example, switch, chassis, blades, and so on. Properties on
         the Managed Objects (MO) are characterized as configurations
         and operations.
         Configuration Policies are the majority of the policies in the
         system and are used to describe configurations of different
         components of Firepower. Policies determine how the system
         behaves under specific circumstances. Certain MOs are not
         created by users, but are automatically created by Firepower,
         power supply objects and fan objects are examples of
         automatically created MOs.
         "
      REVISION "201001290000Z" 
      DESCRIPTION
         "Initial version of this MIB module."
  ::= { ciscoMgmt 826 }

-- *********************************************************************
-- Textual Conventions
-- *********************************************************************

CfprManagedObjectId ::= TEXTUAL-CONVENTION
        DISPLAY-HINT "d"
        STATUS current
        DESCRIPTION
            "A unique identifier for this managed object.
            Objects in FPR Manager are stored in a Management
            Information Tree (MIT). The MIT is a repository of all
            Managed Object (MO) instances, indexed by their
            Distinguished Name (DN).
            The MIT somewhat resembles a file structure - going from
            main folder to the next lowest folder, and so on, until
            the full path to a MO is established.
            
            Every object in FPR Manager has two unique identifiers:
            1) A distinguished name (DN). A DN provides a
            fully-qualified path from the top of the object tree.
            It is built as an ordered sequence of relative names
            separated by the '/' character.
            The DN is used to identify objects in the XML API.
            
            2) A CfprManagedObjectId, which is an integer uniquely
            identifying an object. 
            The CfprManagedObjectId is used to identify objects and
            traverse tables when using the SNMP protocol. 
            
            For example, an object representing a network adaptor
            on a blade might be identified with its DN set
            to 'sys/chassis-5/blade-2/adaptor-1' and its
            CfprManagedObjectId set to '13203'."
        SYNTAX         Unsigned32

CfprManagedObjectDn ::= TEXTUAL-CONVENTION
        STATUS current
        DESCRIPTION
            "An immutable property of all Managed Objects (MO) that
            provides a fully qualified and unambiguous name for the MO.
            A DN provides a fully-qualified path from the top of the
            object tree.
            It is built as an ordered sequence of relative names
            separated by the '/' character.
            
            For example, an object representing a network adaptor
            on a blade might be identified with its DN set
            to 'sys/chassis-5/blade-2/adaptor-1'.
            "
        SYNTAX         OCTET STRING

-- Faults per Managed Object:
-- The information below is organized as follows:
-- MO Name
    -- List of DNs under which the MO can be instantiated in the MIT
        -- List of faults that can be instantiated for this MO

-- equipment:BeaconLed
    -- sys/chassis-[id]/blade-[slotId]/beacon
    -- sys/rack-unit-[id]/beacon
    -- sys/chassis-[id]/beacon
    -- sys/rack-unit-[id]/fan-module-[tray]-[id]/beacon
    -- sys/chassis-[id]/fan-module-[tray]-[id]/beacon
    -- sys/switch-[id]/fan-module-[tray]-[id]/beacon
    -- sys/fex-[id]/beacon
    -- sys/chassis-[id]/slot-[id]/beacon
    -- sys/fex-[id]/slot-[id]/beacon
    -- sys/rack-unit-[id]/psu-[id]/beacon
    -- sys/chassis-[id]/psu-[id]/beacon
    -- sys/fex-[id]/psu-[id]/beacon
    -- sys/switch-[id]/psu-[id]/beacon
    -- sys/switch-[id]/slot-[id]/beacon
        -- fsmStFailEquipmentBeaconLedIlluminate:ExecuteA
        -- fsmStFailEquipmentBeaconLedIlluminate:ExecuteB
        -- fsmRmtErrEquipmentBeaconLedIlluminate:ExecuteA
        -- fsmRmtErrEquipmentBeaconLedIlluminate:ExecuteB
        -- fsmFailEquipmentBeaconLedIlluminate

-- firmware:BootUnit
    -- sys/chassis-[id]/blade-[slotId]/adaptor-[id]/host-eth-[id]/fw-boot-def/bootunit-[type]
    -- sys/rack-unit-[id]/adaptor-[id]/host-eth-[id]/fw-boot-def/bootunit-[type]
    -- sys/chassis-[id]/blade-[slotId]/adaptor-[id]/host-fc-[id]/fw-boot-def/bootunit-[type]
    -- sys/rack-unit-[id]/adaptor-[id]/host-fc-[id]/fw-boot-def/bootunit-[type]
    -- sys/chassis-[id]/blade-[slotId]/ext-board-[id]/bios/fw-boot-def/bootunit-[type]
    -- sys/rack-unit-[id]/ext-board-[id]/bios/fw-boot-def/bootunit-[type]
    -- sys/chassis-[id]/blade-[slotId]/bios/fw-boot-def/bootunit-[type]
    -- sys/rack-unit-[id]/bios/fw-boot-def/bootunit-[type]
    -- capabilities/fw-boot-def/bootunit-[type]
    -- capabilities/ep/mgmt-ext/fw-boot-def/bootunit-[type]
    -- sys/chassis-[id]/epmfpga-[slot]/fw-boot-def/bootunit-[type]
    -- sys/chassis-[id]/fpga/fw-boot-def/bootunit-[type]
    -- sys/chassis-[id]/rommon/fw-boot-def/bootunit-[type]
    -- sys/chassis-[id]/Ssd/fw-boot-def/bootunit-[type]
    -- sys/chassis-[id]/blade-[slotId]/board/graphics-card-[id]/fw-boot-def/bootunit-[type]
    -- sys/rack-unit-[id]/board/graphics-card-[id]/fw-boot-def/bootunit-[type]
    -- sys/chassis-[id]/blade-[slotId]/adaptor-[id]/mgmt/fw-boot-def/bootunit-[type]
    -- sys/rack-unit-[id]/adaptor-[id]/mgmt/fw-boot-def/bootunit-[type]
    -- sys/chassis-[id]/blade-[slotId]/ext-board-[id]/boardController/mgmt/fw-boot-def/bootunit-[type]
    -- sys/rack-unit-[id]/ext-board-[id]/boardController/mgmt/fw-boot-def/bootunit-[type]
    -- sys/chassis-[id]/blade-[slotId]/boardController/mgmt/fw-boot-def/bootunit-[type]
    -- sys/rack-unit-[id]/boardController/mgmt/fw-boot-def/bootunit-[type]
    -- sys/chassis-[id]/blade-[slotId]/ext-board-[id]/mgmt/fw-boot-def/bootunit-[type]
    -- sys/rack-unit-[id]/ext-board-[id]/mgmt/fw-boot-def/bootunit-[type]
    -- sys/chassis-[id]/blade-[slotId]/mgmt/fw-boot-def/bootunit-[type]
    -- sys/rack-unit-[id]/mgmt/fw-boot-def/bootunit-[type]
    -- sys/fex-[id]/mgmt/fw-boot-def/bootunit-[type]
    -- sys/chassis-[id]/slot-[id]/mgmt/fw-boot-def/bootunit-[type]
    -- sys/fex-[id]/slot-[id]/mgmt/fw-boot-def/bootunit-[type]
    -- sys/chassis-[id]/sw-slot-[id]/mgmt/fw-boot-def/bootunit-[type]
    -- sys/switch-[id]/mgmt/fw-boot-def/bootunit-[type]
    -- sys/mgmt/fw-boot-def/bootunit-[type]
    -- sys/chassis-[id]/blade-[slotId]/os-ctrl/fw-boot-def/bootunit-[type]
    -- sys/chassis-[id]/blade-[slotId]/os-ctrl/fw-boot-def/bootunit-[type]
    -- sys/rack-unit-[id]/os-ctrl/fw-boot-def/bootunit-[type]
    -- sys/os-ctrl/fw-boot-def/bootunit-[type]
    -- sys/chassis-[id]/blade-[slotId]/board/storage-[type]-[id]/fw-boot-def/bootunit-[type]
    -- sys/rack-unit-[id]/board/storage-[type]-[id]/fw-boot-def/bootunit-[type]
    -- sys/chassis-[id]/blade-[slotId]/board/storage-[type]-[id]/disk-[id]/fw-boot-def/bootunit-[type]
    -- sys/rack-unit-[id]/board/storage-[type]-[id]/disk-[id]/fw-boot-def/bootunit-[type]
        -- fltFirmwareBootUnitCantBoot
        -- fltFirmwareBootUnitActivateStatusFailed
        -- fltFirmwareBootUnitPowerCycleRequired

-- equipment:SwitchCard
    -- sys/switch-[id]/slot-[id]
        -- fltEquipmentSwitchCardAct2LiteFail

-- sm:AppInstance2
    -- sec-svc/slot-[slotId]/app-inst-[appName]-[identifier]
        -- fltSmAppInstance2AppNotResponding
        -- fltSmAppInstance2AppInstallFailed
        -- fltSmAppInstance2AppStartFailed
        -- fltSmAppInstance2AppUpdateFailed
        -- fltSmAppInstance2AppStopFailed
        -- fltSmAppInstance2AppNotInstalled
        -- fltSmAppInstance2AppInstanceError
        -- fltSmAppInstance2AppInstanceUnsupported
        -- fltSmAppInstance2SoftwareIncompatible
        -- fltSmAppInstance2AppFaultState
        -- fsmStFailSmAppInstance2ResetApplication:StartApp
        -- fsmStFailSmAppInstance2ResetApplication:StopApp
        -- fsmStFailSmAppInstance2ResetApplication:WaitForStopApp
        -- fsmRmtErrSmAppInstance2ResetApplication:StartApp
        -- fsmRmtErrSmAppInstance2ResetApplication:StopApp
        -- fsmRmtErrSmAppInstance2ResetApplication:WaitForStopApp
        -- fsmFailSmAppInstance2ResetApplication

-- extvmm:SwitchDelTask
    -- sys/extvm-mgmt/vsw-deltask-[swIntId]
        -- fsmStFailExtvmmSwitchDelTaskRemoveProvider:RemoveLocal
        -- fsmRmtErrExtvmmSwitchDelTaskRemoveProvider:RemoveLocal
        -- fsmFailExtvmmSwitchDelTaskRemoveProvider

-- extmgmt:NdiscTargets
    -- sys/extmgmt-intf-monitor-policy/ndisc-target-policy
        -- fltExtmgmtNdiscTargetsNdiscTargetsNotValid

-- sysdebug:MEpLog
    -- sys/chassis-[id]/blade-[slotId]/adaptor-[id]/mgmt/log-[type]-[id]
    -- sys/rack-unit-[id]/adaptor-[id]/mgmt/log-[type]-[id]
    -- sys/chassis-[id]/blade-[slotId]/ext-board-[id]/boardController/mgmt/log-[type]-[id]
    -- sys/rack-unit-[id]/ext-board-[id]/boardController/mgmt/log-[type]-[id]
    -- sys/chassis-[id]/blade-[slotId]/boardController/mgmt/log-[type]-[id]
    -- sys/rack-unit-[id]/boardController/mgmt/log-[type]-[id]
    -- sys/chassis-[id]/blade-[slotId]/ext-board-[id]/mgmt/log-[type]-[id]
    -- sys/rack-unit-[id]/ext-board-[id]/mgmt/log-[type]-[id]
    -- sys/chassis-[id]/blade-[slotId]/mgmt/log-[type]-[id]
    -- sys/rack-unit-[id]/mgmt/log-[type]-[id]
    -- sys/fex-[id]/mgmt/log-[type]-[id]
    -- sys/chassis-[id]/slot-[id]/mgmt/log-[type]-[id]
    -- sys/fex-[id]/slot-[id]/mgmt/log-[type]-[id]
    -- sys/chassis-[id]/sw-slot-[id]/mgmt/log-[type]-[id]
    -- sys/switch-[id]/mgmt/log-[type]-[id]
    -- sys/mgmt/log-[type]-[id]
        -- fltSysdebugMEpLogMEpLogLog
        -- fltSysdebugMEpLogMEpLogVeryLow
        -- fltSysdebugMEpLogMEpLogFull
        -- fltSysdebugMEpLogTransferError

-- power:Group
    -- sys/power-ep/group-[name]
        -- fltPowerGroupPowerGroupInsufficientBudget
        -- fltPowerGroupPowerGroupBudgetIncorrect

-- pool:Element
        -- fltPoolElementDuplicatedAssigned

-- capability:Catalogue
    -- capabilities
        -- fltCapabilityCatalogueLoadErrors
        -- fsmStFailCapabilityCatalogueDeployCatalogue:SyncBladeAGLocal
        -- fsmStFailCapabilityCatalogueDeployCatalogue:SyncBladeAGRemote
        -- fsmStFailCapabilityCatalogueDeployCatalogue:SyncHostagentAGLocal
        -- fsmStFailCapabilityCatalogueDeployCatalogue:SyncHostagentAGRemote
        -- fsmStFailCapabilityCatalogueDeployCatalogue:SyncNicAGLocal
        -- fsmStFailCapabilityCatalogueDeployCatalogue:SyncNicAGRemote
        -- fsmStFailCapabilityCatalogueDeployCatalogue:SyncPortAGLocal
        -- fsmStFailCapabilityCatalogueDeployCatalogue:SyncPortAGRemote
        -- fsmStFailCapabilityCatalogueDeployCatalogue:finalize
        -- fsmStFailCapabilityCatalogueActivateCatalog:ApplyCatalog
        -- fsmStFailCapabilityCatalogueActivateCatalog:CopyCatFromRep
        -- fsmStFailCapabilityCatalogueActivateCatalog:CopyExternalRepToRemote
        -- fsmStFailCapabilityCatalogueActivateCatalog:CopyRemote
        -- fsmStFailCapabilityCatalogueActivateCatalog:EvaluateStatus
        -- fsmStFailCapabilityCatalogueActivateCatalog:RescanImages
        -- fsmStFailCapabilityCatalogueActivateCatalog:UnpackLocal
        -- fsmRmtErrCapabilityCatalogueDeployCatalogue:SyncBladeAGLocal
        -- fsmRmtErrCapabilityCatalogueDeployCatalogue:SyncBladeAGRemote
        -- fsmRmtErrCapabilityCatalogueDeployCatalogue:SyncHostagentAGLocal
        -- fsmRmtErrCapabilityCatalogueDeployCatalogue:SyncHostagentAGRemote
        -- fsmRmtErrCapabilityCatalogueDeployCatalogue:SyncNicAGLocal
        -- fsmRmtErrCapabilityCatalogueDeployCatalogue:SyncNicAGRemote
        -- fsmRmtErrCapabilityCatalogueDeployCatalogue:SyncPortAGLocal
        -- fsmRmtErrCapabilityCatalogueDeployCatalogue:SyncPortAGRemote
        -- fsmRmtErrCapabilityCatalogueDeployCatalogue:finalize
        -- fsmRmtErrCapabilityCatalogueActivateCatalog:ApplyCatalog
        -- fsmRmtErrCapabilityCatalogueActivateCatalog:CopyCatFromRep
        -- fsmRmtErrCapabilityCatalogueActivateCatalog:CopyExternalRepToRemote
        -- fsmRmtErrCapabilityCatalogueActivateCatalog:CopyRemote
        -- fsmRmtErrCapabilityCatalogueActivateCatalog:EvaluateStatus
        -- fsmRmtErrCapabilityCatalogueActivateCatalog:RescanImages
        -- fsmRmtErrCapabilityCatalogueActivateCatalog:UnpackLocal
        -- fsmFailCapabilityCatalogueDeployCatalogue
        -- fsmFailCapabilityCatalogueActivateCatalog

-- fabric:EthLanPcEp
    -- fabric/lan/[id]/pc-[portId]/ep-slot-[slotId]-port-[portId]
    -- fabric/server/sw-[id]/slot-[slotId]-aggr-port-[aggrPortId]/ep-slot-[slotId]-port-[portId]
    -- fabric/server/sw-[id]/pc-[portId]/slot-[slotId]-aggr-port-[aggrPortId]/ep-slot-[slotId]-port-[portId]
    -- fabric/eth-estc/[id]/slot-[slotId]-aggr-port-[aggrPortId]/ep-slot-[slotId]-port-[portId]
    -- fabric/eth-estc/[id]/pc-[portId]/slot-[slotId]-aggr-port-[aggrPortId]/ep-slot-[slotId]-port-[portId]
    -- fabric/lan/[id]/slot-[slotId]-aggr-port-[aggrPortId]/ep-slot-[slotId]-port-[portId]
    -- fabric/lan/[id]/pc-[portId]/slot-[slotId]-aggr-port-[aggrPortId]/ep-slot-[slotId]-port-[portId]
    -- fabric/lanmon/[id]/eth-mon-[name]/slot-[slotId]-aggr-port-[aggrPortId]/ep-slot-[slotId]-port-[portId]
    -- fabric/san/[id]/slot-[slotId]-aggr-port-[aggrPortId]/ep-slot-[slotId]-port-[portId]
    -- fabric/san/[id]/fcoesanpc-[portId]/slot-[slotId]-aggr-port-[aggrPortId]/ep-slot-[slotId]-port-[portId]
        -- fltFabricEthLanPcEpDown
        -- fltFabricEthLanPcEpUdldLinkDown

-- sm:LogicalDevice
    -- sec-svc/ld-[name]
        -- fltSmLogicalDeviceIncompleteConfig
        -- fltSmLogicalDeviceLogicalDeviceError
        -- fsmStFailSmLogicalDeviceConfigure:ApplyConfig
        -- fsmStFailSmLogicalDeviceConfigure:AutoConfig
        -- fsmStFailSmLogicalDeviceConfigure:CheckConfigIssues
        -- fsmStFailSmLogicalDeviceConfigure:ResolvePolicy
        -- fsmStFailSmLogicalDeviceConfigure:ValidateLDConfig
        -- fsmRmtErrSmLogicalDeviceConfigure:ApplyConfig
        -- fsmRmtErrSmLogicalDeviceConfigure:AutoConfig
        -- fsmRmtErrSmLogicalDeviceConfigure:CheckConfigIssues
        -- fsmRmtErrSmLogicalDeviceConfigure:ResolvePolicy
        -- fsmRmtErrSmLogicalDeviceConfigure:ValidateLDConfig
        -- fsmFailSmLogicalDeviceConfigure

-- ether:SwitchIntFIo
    -- sys/chassis-[id]/slot-[id]/[type]/port-[portId]
    -- sys/fex-[id]/slot-[id]/[type]/port-[portId]
    -- sys/switch-[id]/slot-[id]/[type]/port-[portId]
    -- sys/chassis-[id]/sw-slot-[id]/[type]/port-[portId]
        -- fltEtherSwitchIntFIoSatellite-connection-absent
        -- fltEtherSwitchIntFIoSatellite-wiring-problem
        -- fltEtherSwitchIntFIoSatellite-wiring-numbers-unexpected

-- sysdebug:LogExportPolicy
    -- sys/sysdebug/log-export-policy
        -- fsmStFailSysdebugLogExportPolicyConfigure:Local
        -- fsmStFailSysdebugLogExportPolicyConfigure:Peer
        -- fsmRmtErrSysdebugLogExportPolicyConfigure:Local
        -- fsmRmtErrSysdebugLogExportPolicyConfigure:Peer
        -- fsmFailSysdebugLogExportPolicyConfigure

-- storage:MezzFlashLife
    -- sys/chassis-[id]/blade-[slotId]/board/storage-[type]-[id]/flash-life-
    -- sys/rack-unit-[id]/board/storage-[type]-[id]/flash-life-
        -- fltStorageMezzFlashLifeConfiguration-error
        -- fltStorageMezzFlashLifeDegraded

-- sysdebug:MemoryHead
    -- sys/sysdebug/mem-overall
        -- fsmStFailSysdebugMemoryHeadDeploy:ApplyConfig
        -- fsmRmtErrSysdebugMemoryHeadDeploy:ApplyConfig
        -- fsmFailSysdebugMemoryHeadDeploy

-- sd:ExternalLduLink
    -- sys-secsvc/slot-[slotId]/app-inst-[appInstId]/ldu-[slotId]/ext-ldulink-[slotId]-[aggrPortId]-[portId]-[appName]
    -- sys-secsvc/ld-[name]/ldu-[slotId]/ext-ldulink-[slotId]-[aggrPortId]-[portId]-[appName]
        -- fltSdExternalLduLinkExternalLduLinkVnicConfigFail

-- vm:LifeCyclePolicy
    -- org-[name]/vm-lc-policy
        -- fsmStFailVmLifeCyclePolicyConfig:Local
        -- fsmStFailVmLifeCyclePolicyConfig:Peer
        -- fsmRmtErrVmLifeCyclePolicyConfig:Local
        -- fsmRmtErrVmLifeCyclePolicyConfig:Peer
        -- fsmFailVmLifeCyclePolicyConfig

-- ipsec:Authority
    -- sys/ipsec-ext/author-[tpName]
        -- fltIpsecAuthorityIpsecAuthorInvalidTp

-- firmware:SupFirmware
    -- sys/fw-supfirmware
        -- fltFirmwareSupFirmwareFWUpgradeInProgress
        -- fsmStFailFirmwareSupFirmwareDeploy:ActivateFirmwarePack
        -- fsmStFailFirmwareSupFirmwareDeploy:CheckUpgradeStatus
        -- fsmStFailFirmwareSupFirmwareDeploy:CompleteFirmwareUpgrade
        -- fsmStFailFirmwareSupFirmwareDeploy:DebundlePort
        -- fsmStFailFirmwareSupFirmwareDeploy:PollActivateOfFirmwarePack
        -- fsmStFailFirmwareSupFirmwareDeploy:PollDebundlePort
        -- fsmStFailFirmwareSupFirmwareDeploy:UpdateImageVersion
        -- fsmStFailFirmwareSupFirmwareDeploy:UpdatePackageVersion
        -- fsmStFailFirmwareSupFirmwareDeploy:ValidateFirmwarePack
        -- fsmStFailFirmwareSupFirmwareDeploy:WaitForDeploy
        -- fsmStFailFirmwareSupFirmwareDeploy:WaitForFirmwareVersionUpdate
        -- fsmStFailFirmwareSupFirmwareDeploy:resetChassis
        -- fsmRmtErrFirmwareSupFirmwareDeploy:ActivateFirmwarePack
        -- fsmRmtErrFirmwareSupFirmwareDeploy:CheckUpgradeStatus
        -- fsmRmtErrFirmwareSupFirmwareDeploy:CompleteFirmwareUpgrade
        -- fsmRmtErrFirmwareSupFirmwareDeploy:DebundlePort
        -- fsmRmtErrFirmwareSupFirmwareDeploy:PollActivateOfFirmwarePack
        -- fsmRmtErrFirmwareSupFirmwareDeploy:PollDebundlePort
        -- fsmRmtErrFirmwareSupFirmwareDeploy:UpdateImageVersion
        -- fsmRmtErrFirmwareSupFirmwareDeploy:UpdatePackageVersion
        -- fsmRmtErrFirmwareSupFirmwareDeploy:ValidateFirmwarePack
        -- fsmRmtErrFirmwareSupFirmwareDeploy:WaitForDeploy
        -- fsmRmtErrFirmwareSupFirmwareDeploy:WaitForFirmwareVersionUpdate
        -- fsmRmtErrFirmwareSupFirmwareDeploy:resetChassis
        -- fsmFailFirmwareSupFirmwareDeploy

-- cimcvmedia:ActualMountEntry
    -- sys/chassis-[id]/blade-[slotId]/adaptor-[id]/mgmt/actual-mount-list/actual-mount-entry-[virtualDiskId]
    -- sys/rack-unit-[id]/adaptor-[id]/mgmt/actual-mount-list/actual-mount-entry-[virtualDiskId]
    -- sys/chassis-[id]/blade-[slotId]/ext-board-[id]/boardController/mgmt/actual-mount-list/actual-mount-entry-[virtualDiskId]
    -- sys/rack-unit-[id]/ext-board-[id]/boardController/mgmt/actual-mount-list/actual-mount-entry-[virtualDiskId]
    -- sys/chassis-[id]/blade-[slotId]/boardController/mgmt/actual-mount-list/actual-mount-entry-[virtualDiskId]
    -- sys/rack-unit-[id]/boardController/mgmt/actual-mount-list/actual-mount-entry-[virtualDiskId]
    -- sys/chassis-[id]/blade-[slotId]/ext-board-[id]/mgmt/actual-mount-list/actual-mount-entry-[virtualDiskId]
    -- sys/rack-unit-[id]/ext-board-[id]/mgmt/actual-mount-list/actual-mount-entry-[virtualDiskId]
    -- sys/chassis-[id]/blade-[slotId]/mgmt/actual-mount-list/actual-mount-entry-[virtualDiskId]
    -- sys/rack-unit-[id]/mgmt/actual-mount-list/actual-mount-entry-[virtualDiskId]
    -- sys/fex-[id]/mgmt/actual-mount-list/actual-mount-entry-[virtualDiskId]
    -- sys/chassis-[id]/slot-[id]/mgmt/actual-mount-list/actual-mount-entry-[virtualDiskId]
    -- sys/fex-[id]/slot-[id]/mgmt/actual-mount-list/actual-mount-entry-[virtualDiskId]
    -- sys/chassis-[id]/sw-slot-[id]/mgmt/actual-mount-list/actual-mount-entry-[virtualDiskId]
    -- sys/switch-[id]/mgmt/actual-mount-list/actual-mount-entry-[virtualDiskId]
    -- sys/mgmt/actual-mount-list/actual-mount-entry-[virtualDiskId]
        -- fltCimcvmediaActualMountEntryVmediaMountFailed

-- capability:Updater
    -- capabilities/ep/updater-[fileName]
        -- fsmStFailCapabilityUpdaterUpdater:Apply
        -- fsmStFailCapabilityUpdaterUpdater:CopyRemote
        -- fsmStFailCapabilityUpdaterUpdater:DeleteLocal
        -- fsmStFailCapabilityUpdaterUpdater:EvaluateStatus
        -- fsmStFailCapabilityUpdaterUpdater:Local
        -- fsmStFailCapabilityUpdaterUpdater:RescanImages
        -- fsmStFailCapabilityUpdaterUpdater:UnpackLocal
        -- fsmRmtErrCapabilityUpdaterUpdater:Apply
        -- fsmRmtErrCapabilityUpdaterUpdater:CopyRemote
        -- fsmRmtErrCapabilityUpdaterUpdater:DeleteLocal
        -- fsmRmtErrCapabilityUpdaterUpdater:EvaluateStatus
        -- fsmRmtErrCapabilityUpdaterUpdater:Local
        -- fsmRmtErrCapabilityUpdaterUpdater:RescanImages
        -- fsmRmtErrCapabilityUpdaterUpdater:UnpackLocal
        -- fsmFailCapabilityUpdaterUpdater

-- adaptor:HostIf
        -- fltAdaptorHostIfLink-down

-- equipment:Xcvr
    -- sys/chassis-[id]/slot-[id]/[type]/port-[portId]/transceiver
    -- sys/fex-[id]/slot-[id]/[type]/port-[portId]/transceiver
    -- sys/switch-[id]/slot-[id]/[type]/port-[portId]/transceiver
    -- sys/chassis-[id]/sw-slot-[id]/[type]/port-[portId]/transceiver
    -- sys/chassis-[id]/slot-[id]/[type]/aggr-port-[aggrPortId]/port-[portId]/transceiver
    -- sys/fex-[id]/slot-[id]/[type]/aggr-port-[aggrPortId]/port-[portId]/transceiver
    -- sys/switch-[id]/slot-[id]/[type]/aggr-port-[aggrPortId]/port-[portId]/transceiver
    -- sys/chassis-[id]/sw-slot-[id]/[type]/aggr-port-[aggrPortId]/port-[portId]/transceiver
    -- sys/chassis-[id]/slot-[id]/[type]/port-[portId]/transceiver
    -- sys/fex-[id]/slot-[id]/[type]/port-[portId]/transceiver
    -- sys/switch-[id]/slot-[id]/[type]/port-[portId]/transceiver
    -- sys/chassis-[id]/sw-slot-[id]/[type]/port-[portId]/transceiver
    -- sys/chassis-[id]/slot-[id]/[type]/aggr-port-[aggrPortId]/port-[portId]/transceiver
    -- sys/fex-[id]/slot-[id]/[type]/aggr-port-[aggrPortId]/port-[portId]/transceiver
    -- sys/switch-[id]/slot-[id]/[type]/aggr-port-[aggrPortId]/port-[portId]/transceiver
    -- sys/chassis-[id]/sw-slot-[id]/[type]/aggr-port-[aggrPortId]/port-[portId]/transceiver
    -- sys/chassis-[id]/slot-[id]/[type]/port-[portId]/transceiver
    -- sys/fex-[id]/slot-[id]/[type]/port-[portId]/transceiver
    -- sys/switch-[id]/slot-[id]/[type]/port-[portId]/transceiver
    -- sys/chassis-[id]/sw-slot-[id]/[type]/port-[portId]/transceiver
    -- sys/chassis-[id]/slot-[id]/[type]/aggr-port-[aggrPortId]/port-[portId]/transceiver
    -- sys/fex-[id]/slot-[id]/[type]/aggr-port-[aggrPortId]/port-[portId]/transceiver
    -- sys/switch-[id]/slot-[id]/[type]/aggr-port-[aggrPortId]/port-[portId]/transceiver
    -- sys/chassis-[id]/sw-slot-[id]/[type]/aggr-port-[aggrPortId]/port-[portId]/transceiver
    -- sys/chassis-[id]/slot-[id]/[type]/port-[portId]/transceiver
    -- sys/fex-[id]/slot-[id]/[type]/port-[portId]/transceiver
    -- sys/switch-[id]/slot-[id]/[type]/port-[portId]/transceiver
    -- sys/chassis-[id]/sw-slot-[id]/[type]/port-[portId]/transceiver
    -- sys/chassis-[id]/slot-[id]/[type]/port-[portId]/transceiver
    -- sys/fex-[id]/slot-[id]/[type]/port-[portId]/transceiver
    -- sys/switch-[id]/slot-[id]/[type]/port-[portId]/transceiver
    -- sys/chassis-[id]/sw-slot-[id]/[type]/port-[portId]/transceiver
    -- sys/chassis-[id]/blade-[slotId]/diag/port-[portId]/transceiver
    -- sys/rack-unit-[id]/diag/port-[portId]/transceiver
    -- sys/chassis-[id]/slot-[id]/[type]/port-[portId]/transceiver
    -- sys/fex-[id]/slot-[id]/[type]/port-[portId]/transceiver
    -- sys/switch-[id]/slot-[id]/[type]/port-[portId]/transceiver
    -- sys/chassis-[id]/sw-slot-[id]/[type]/port-[portId]/transceiver
    -- sys/chassis-[id]/slot-[id]/[type]/port-[portId]/transceiver
    -- sys/fex-[id]/slot-[id]/[type]/port-[portId]/transceiver
    -- sys/switch-[id]/slot-[id]/[type]/port-[portId]/transceiver
    -- sys/chassis-[id]/sw-slot-[id]/[type]/port-[portId]/transceiver
        -- fltEquipmentXcvrNonSupportedXcvr

-- storage:RaidBattery
    -- sys/chassis-[id]/blade-[slotId]/board/storage-[type]-[id]/raid-battery
    -- sys/rack-unit-[id]/board/storage-[type]-[id]/raid-battery
        -- fltStorageRaidBatteryInoperable
        -- fltStorageRaidBatteryDegraded
        -- fltStorageRaidBatteryRelearnAborted
        -- fltStorageRaidBatteryRelearnFailed

-- equipment:IOCardBase
        -- fsmStFailEquipmentIOCardBaseFePresence:CheckLicense
        -- fsmStFailEquipmentIOCardBaseFePresence:ConfigChassisId
        -- fsmStFailEquipmentIOCardBaseFePresence:Identify
        -- fsmStFailEquipmentIOCardBaseFeConn:ConfigureEndPoint
        -- fsmStFailEquipmentIOCardBaseFeConn:ConfigureSwMgmtEndPoint
        -- fsmStFailEquipmentIOCardBaseFeConn:ConfigureVifNs
        -- fsmStFailEquipmentIOCardBaseFeConn:DiscoverChassis
        -- fsmStFailEquipmentIOCardBaseFeConn:EnableChassis
        -- fsmStFailEquipmentIOCardBaseFeConn:ResetBlades
        -- fsmRmtErrEquipmentIOCardBaseFePresence:CheckLicense
        -- fsmRmtErrEquipmentIOCardBaseFePresence:ConfigChassisId
        -- fsmRmtErrEquipmentIOCardBaseFePresence:Identify
        -- fsmRmtErrEquipmentIOCardBaseFeConn:ConfigureEndPoint
        -- fsmRmtErrEquipmentIOCardBaseFeConn:ConfigureSwMgmtEndPoint
        -- fsmRmtErrEquipmentIOCardBaseFeConn:ConfigureVifNs
        -- fsmRmtErrEquipmentIOCardBaseFeConn:DiscoverChassis
        -- fsmRmtErrEquipmentIOCardBaseFeConn:EnableChassis
        -- fsmRmtErrEquipmentIOCardBaseFeConn:ResetBlades
        -- fsmFailEquipmentIOCardBaseFePresence
        -- fsmFailEquipmentIOCardBaseFeConn

-- storage:FlexFlashVirtualDrive
    -- sys/chassis-[id]/blade-[slotId]/board/storage-flexflash-[id]/vd-[id]
    -- sys/rack-unit-[id]/board/storage-flexflash-[id]/vd-[id]
        -- fltStorageFlexFlashVirtualDriveDegraded
        -- fltStorageFlexFlashVirtualDriveInoperable

-- sm:AppInstance
    -- sec-svc/slot-[slotId]/app-inst-[appName]
        -- fltSmAppInstanceFailedConversion

-- fabric:InternalPc
        -- fltFabricInternalPcDown

-- ident:IdentRequest
    -- metaverse/metasys/IdentQ-[id]
        -- fsmStFailIdentIdentRequestUpdateIdent:Execute
        -- fsmRmtErrIdentIdentRequestUpdateIdent:Execute
        -- fsmFailIdentIdentRequestUpdateIdent

-- equipment:Psu
    -- sys/rack-unit-[id]/psu-[id]
    -- sys/chassis-[id]/psu-[id]
    -- sys/fex-[id]/psu-[id]
    -- sys/switch-[id]/psu-[id]
        -- fltEquipmentPsuPowerSupplyProblem
        -- fltEquipmentPsuInoperable
        -- fltEquipmentPsuMissing
        -- fltEquipmentPsuThermalThresholdNonCritical
        -- fltEquipmentPsuThermalThresholdCritical
        -- fltEquipmentPsuThermalThresholdNonRecoverable
        -- fltEquipmentPsuVoltageThresholdNonCritical
        -- fltEquipmentPsuVoltageThresholdCritical
        -- fltEquipmentPsuVoltageThresholdNonRecoverable
        -- fltEquipmentPsuPerfThresholdNonCritical
        -- fltEquipmentPsuPerfThresholdCritical
        -- fltEquipmentPsuPerfThresholdNonRecoverable
        -- fltEquipmentPsuIdentity
        -- fltEquipmentPsuOffline
        -- fltEquipmentPsuPowerSupplyShutdown
        -- fltEquipmentPsuPowerThreshold
        -- fltEquipmentPsuInputError

-- qosclass:Definition
    -- fabric/lan/classes
        -- fsmStFailQosclassDefinitionConfigGlobalQoS:SetLocal
        -- fsmStFailQosclassDefinitionConfigGlobalQoS:SetPeer
        -- fsmRmtErrQosclassDefinitionConfigGlobalQoS:SetLocal
        -- fsmRmtErrQosclassDefinitionConfigGlobalQoS:SetPeer
        -- fsmFailQosclassDefinitionConfigGlobalQoS

-- storage:Controller
    -- sys/chassis-[id]/blade-[slotId]/board/storage-[type]-[id]
    -- sys/rack-unit-[id]/board/storage-[type]-[id]
        -- fltStorageControllerPatrolReadFailed
        -- fltStorageControllerInoperable

-- mgmt:Importer
    -- sys/import-config-[hostname]
        -- fltMgmtImporterConfiguration import failed
        -- fsmStFailMgmtImporterImport:cleanUp
        -- fsmStFailMgmtImporterImport:config
        -- fsmStFailMgmtImporterImport:configBreakout
        -- fsmStFailMgmtImporterImport:downloadLocal
        -- fsmStFailMgmtImporterImport:reportResults
        -- fsmStFailMgmtImporterImport:verifyKey
        -- fsmStFailMgmtImporterImport:waitForSwitch
        -- fsmRmtErrMgmtImporterImport:cleanUp
        -- fsmRmtErrMgmtImporterImport:config
        -- fsmRmtErrMgmtImporterImport:configBreakout
        -- fsmRmtErrMgmtImporterImport:downloadLocal
        -- fsmRmtErrMgmtImporterImport:reportResults
        -- fsmRmtErrMgmtImporterImport:verifyKey
        -- fsmRmtErrMgmtImporterImport:waitForSwitch
        -- fsmFailMgmtImporterImport

-- compute:Board
    -- sys/chassis-[id]/blade-[slotId]/board
    -- sys/rack-unit-[id]/board
        -- fltComputeBoardPowerError
        -- fltComputeBoardCmosVoltageThresholdCritical
        -- fltComputeBoardCmosVoltageThresholdNonRecoverable
        -- fltComputeBoardPowerFail

-- sm:Slot
    -- sec-svc/slot-[slotId]
        -- fltSmSlotSmaHeartbeat
        -- fltSmSlotBladeNotWorking
        -- fltSmSlotDiskFormatFailed
        -- fltSmSlotBladeSwap
        -- fltSmSlotAdapter2NotResponding
        -- fltSmSlotPlatformNotSupported
        -- fltSmSlotModuleNotSupported

-- aaa:Realm
    -- sys/
        -- fsmStFailAaaRealmUpdateRealm:SetRealmLocal
        -- fsmStFailAaaRealmUpdateRealm:SetRealmPeer
        -- fsmRmtErrAaaRealmUpdateRealm:SetRealmLocal
        -- fsmRmtErrAaaRealmUpdateRealm:SetRealmPeer
        -- fsmFailAaaRealmUpdateRealm

-- sd:CspMetaCtrl
    -- sys-secsvc/slot-[slotId]/app-inst-[appInstId]/csp-meta-ctrl
        -- fsmStFailSdCspMetaCtrlRetrieveCSPMeta:Retrieve
        -- fsmRmtErrSdCspMetaCtrlRetrieveCSPMeta:Retrieve
        -- fsmFailSdCspMetaCtrlRetrieveCSPMeta

-- sw:EthLanBorder
    -- sys/switch-[id]/border-eth
    -- sys/tbh/border-eth
        -- fsmStFailSwEthLanBorderDeploy:UpdateConnectivity
        -- fsmStFailSwEthLanBorderDeploy:UpdateVlanGroups
        -- fsmRmtErrSwEthLanBorderDeploy:UpdateConnectivity
        -- fsmRmtErrSwEthLanBorderDeploy:UpdateVlanGroups
        -- fsmFailSwEthLanBorderDeploy

-- mgmt:Entity
    -- sys/mgmt-entity-[id]
        -- fltMgmtEntityDegraded
        -- fltMgmtEntityDown
        -- fltMgmtEntityElection-failure
        -- fltMgmtEntityHa-not-ready
        -- fltMgmtEntityVersion-incompatible
        -- fltMgmtEntityManagement-services-failure
        -- fltMgmtEntityManagement-services-unresponsive
        -- fltMgmtEntityDevice-1-shared-storage-error
        -- fltMgmtEntityDevice-2-shared-storage error
        -- fltMgmtEntityDevice-3-shared-storage error
        -- fltMgmtEntityHa-ssh-keys-mismatched

-- storage:LocalDiskSlotEp
    -- sys/chassis-[id]/blade-[slotId]/board/disk-[id]
    -- sys/rack-unit-[id]/board/disk-[id]
        -- fltStorageLocalDiskSlotEpUnusable

-- ether:ServerIntFIo
    -- sys/chassis-[id]/blade-[slotId]/diag/port-[portId]
    -- sys/rack-unit-[id]/diag/port-[portId]
    -- sys/chassis-[id]/slot-[id]/[type]/port-[portId]
    -- sys/fex-[id]/slot-[id]/[type]/port-[portId]
    -- sys/switch-[id]/slot-[id]/[type]/port-[portId]
    -- sys/chassis-[id]/sw-slot-[id]/[type]/port-[portId]
        -- fltEtherServerIntFIoHardware-failure
        -- fsmStFailEtherServerIntFIoConfigSpeed:Configure
        -- fsmRmtErrEtherServerIntFIoConfigSpeed:Configure
        -- fsmFailEtherServerIntFIoConfigSpeed

-- fabric:VlanReq
    -- org-[name]/vlan-req-[name]
        -- fltFabricVlanReqVlanPermitUnresolved

-- equipment:LocatorLed
    -- sys/chassis-[id]/blade-[slotId]/ext-board-[id]/locator-led
    -- sys/rack-unit-[id]/ext-board-[id]/locator-led
    -- sys/chassis-[id]/blade-[slotId]/locator-led
    -- sys/rack-unit-[id]/locator-led
    -- sys/chassis-[id]/locator-led
    -- sys/rack-unit-[id]/fan-module-[tray]-[id]/locator-led
    -- sys/chassis-[id]/fan-module-[tray]-[id]/locator-led
    -- sys/switch-[id]/fan-module-[tray]-[id]/locator-led
    -- sys/fex-[id]/locator-led
    -- sys/chassis-[id]/slot-[id]/locator-led
    -- sys/fex-[id]/slot-[id]/locator-led
    -- sys/rack-unit-[id]/psu-[id]/locator-led
    -- sys/chassis-[id]/psu-[id]/locator-led
    -- sys/fex-[id]/psu-[id]/locator-led
    -- sys/switch-[id]/psu-[id]/locator-led
    -- sys/switch-[id]/locator-led
        -- fsmStFailEquipmentLocatorLedSetLocatorLed:Execute
        -- fsmStFailEquipmentLocatorLedSetFeLocatorLed:Execute
        -- fsmStFailEquipmentLocatorLedSetFiLocatorLed:Execute
        -- fsmRmtErrEquipmentLocatorLedSetLocatorLed:Execute
        -- fsmRmtErrEquipmentLocatorLedSetFeLocatorLed:Execute
        -- fsmRmtErrEquipmentLocatorLedSetFiLocatorLed:Execute
        -- fsmFailEquipmentLocatorLedSetLocatorLed
        -- fsmFailEquipmentLocatorLedSetFeLocatorLed
        -- fsmFailEquipmentLocatorLedSetFiLocatorLed

-- adaptor:ExtIf
        -- fltAdaptorExtIfLink-down

-- compute:Physical
        -- fltComputePhysicalInsufficientlyEquipped
        -- fltComputePhysicalIdentityUnestablishable
        -- fltComputePhysicalPowerProblem
        -- fltComputePhysicalThermalProblem
        -- fltComputePhysicalBiosPostTimeout
        -- fltComputePhysicalDiscoveryFailed
        -- fltComputePhysicalAssociationFailed
        -- fltComputePhysicalInoperable
        -- fltComputePhysicalUnassignedMissing
        -- fltComputePhysicalAssignedMissing
        -- fltComputePhysicalUnidentified
        -- fltComputePhysicalUnassignedInaccessible
        -- fltComputePhysicalAssignedInaccessible
        -- fltComputePhysicalPost-failure
        -- fltComputePhysicalDisassociationFailed
        -- fltComputePhysicalNetworkMisconfigured
        -- fltComputePhysicalAdapterMismatch
        -- fsmStFailComputePhysicalAssociate:ActivateBios
        -- fsmStFailComputePhysicalAssociate:BiosImgUpdate
        -- fsmStFailComputePhysicalAssociate:BiosPostCompletion
        -- fsmStFailComputePhysicalAssociate:BladePowerOff
        -- fsmStFailComputePhysicalAssociate:BmcConfigPnuOS
        -- fsmStFailComputePhysicalAssociate:BmcPreconfigPnuOSLocal
        -- fsmStFailComputePhysicalAssociate:BmcPreconfigPnuOSPeer
        -- fsmStFailComputePhysicalAssociate:BmcUnconfigPnuOS
        -- fsmStFailComputePhysicalAssociate:BootHost
        -- fsmStFailComputePhysicalAssociate:BootPnuos
        -- fsmStFailComputePhysicalAssociate:BootWait
        -- fsmStFailComputePhysicalAssociate:CheckPowerAvailability
        -- fsmStFailComputePhysicalAssociate:ClearBiosUpdate
        -- fsmStFailComputePhysicalAssociate:ConfigCimcVMedia
        -- fsmStFailComputePhysicalAssociate:ConfigExtMgmtGw
        -- fsmStFailComputePhysicalAssociate:ConfigExtMgmtRules
        -- fsmStFailComputePhysicalAssociate:ConfigFlexFlash
        -- fsmStFailComputePhysicalAssociate:ConfigSoL
        -- fsmStFailComputePhysicalAssociate:ConfigUserAccess
        -- fsmStFailComputePhysicalAssociate:ConfigUuid
        -- fsmStFailComputePhysicalAssociate:DeassertResetBypass
        -- fsmStFailComputePhysicalAssociate:DeleteCurlDownloadedImages
        -- fsmStFailComputePhysicalAssociate:GraphicsImageUpdate
        -- fsmStFailComputePhysicalAssociate:HbaImgUpdate
        -- fsmStFailComputePhysicalAssociate:HostOSConfig
        -- fsmStFailComputePhysicalAssociate:HostOSIdent
        -- fsmStFailComputePhysicalAssociate:HostOSPolicy
        -- fsmStFailComputePhysicalAssociate:HostOSValidate
        -- fsmStFailComputePhysicalAssociate:LocalDiskFwUpdate
        -- fsmStFailComputePhysicalAssociate:MarkAdapterForReboot
        -- fsmStFailComputePhysicalAssociate:NicConfigHostOSLocal
        -- fsmStFailComputePhysicalAssociate:NicConfigHostOSPeer
        -- fsmStFailComputePhysicalAssociate:NicConfigPnuOSLocal
        -- fsmStFailComputePhysicalAssociate:NicConfigPnuOSPeer
        -- fsmStFailComputePhysicalAssociate:NicConfigServiceInfraLocal
        -- fsmStFailComputePhysicalAssociate:NicConfigServiceInfraPeer
        -- fsmStFailComputePhysicalAssociate:NicImgUpdate
        -- fsmStFailComputePhysicalAssociate:NicUnconfigPnuOSLocal
        -- fsmStFailComputePhysicalAssociate:NicUnconfigPnuOSPeer
        -- fsmStFailComputePhysicalAssociate:OobStorageInventory
        -- fsmStFailComputePhysicalAssociate:PnuOSCatalog
        -- fsmStFailComputePhysicalAssociate:PnuOSConfig
        -- fsmStFailComputePhysicalAssociate:PnuOSIdent
        -- fsmStFailComputePhysicalAssociate:PnuOSInventory
        -- fsmStFailComputePhysicalAssociate:PnuOSLocalDiskConfig
        -- fsmStFailComputePhysicalAssociate:PnuOSPolicy
        -- fsmStFailComputePhysicalAssociate:PnuOSSelfTest
        -- fsmStFailComputePhysicalAssociate:PnuOSUnloadDrivers
        -- fsmStFailComputePhysicalAssociate:PnuOSValidate
        -- fsmStFailComputePhysicalAssociate:PollBiosActivateStatus
        -- fsmStFailComputePhysicalAssociate:PollBiosUpdateStatus
        -- fsmStFailComputePhysicalAssociate:PollBoardCtrlUpdateStatus
        -- fsmStFailComputePhysicalAssociate:PollClearBiosUpdateStatus
        -- fsmStFailComputePhysicalAssociate:PowerDeployWait
        -- fsmStFailComputePhysicalAssociate:PowerOn
        -- fsmStFailComputePhysicalAssociate:PowerOnPreConfig
        -- fsmStFailComputePhysicalAssociate:PreSanitize
        -- fsmStFailComputePhysicalAssociate:PrepareForBoot
        -- fsmStFailComputePhysicalAssociate:PrepareKeyFile
        -- fsmStFailComputePhysicalAssociate:Sanitize
        -- fsmStFailComputePhysicalAssociate:SolRedirectDisable
        -- fsmStFailComputePhysicalAssociate:SolRedirectEnable
        -- fsmStFailComputePhysicalAssociate:StorageCtlrImgUpdate
        -- fsmStFailComputePhysicalAssociate:SwConfigHostOSLocal
        -- fsmStFailComputePhysicalAssociate:SwConfigHostOSPeer
        -- fsmStFailComputePhysicalAssociate:SwConfigPnuOSLocal
        -- fsmStFailComputePhysicalAssociate:SwConfigPnuOSPeer
        -- fsmStFailComputePhysicalAssociate:SwConfigPortNivLocal
        -- fsmStFailComputePhysicalAssociate:SwConfigPortNivPeer
        -- fsmStFailComputePhysicalAssociate:SwConfigServiceInfraLocal
        -- fsmStFailComputePhysicalAssociate:SwConfigServiceInfraPeer
        -- fsmStFailComputePhysicalAssociate:SwUnconfigPnuOSLocal
        -- fsmStFailComputePhysicalAssociate:SwUnconfigPnuOSPeer
        -- fsmStFailComputePhysicalAssociate:SyncPowerState
        -- fsmStFailComputePhysicalAssociate:UnconfigCimcVMedia
        -- fsmStFailComputePhysicalAssociate:UnconfigExtMgmtGw
        -- fsmStFailComputePhysicalAssociate:UnconfigExtMgmtRules
        -- fsmStFailComputePhysicalAssociate:UpdateBiosRequest
        -- fsmStFailComputePhysicalAssociate:UpdateBoardCtrlRequest
        -- fsmStFailComputePhysicalAssociate:VerifyFcZoneConfig
        -- fsmStFailComputePhysicalAssociate:activateAdaptorNwFwLocal
        -- fsmStFailComputePhysicalAssociate:activateAdaptorNwFwPeer
        -- fsmStFailComputePhysicalAssociate:activateIBMCFw
        -- fsmStFailComputePhysicalAssociate:copyRemote
        -- fsmStFailComputePhysicalAssociate:downloadImages
        -- fsmStFailComputePhysicalAssociate:hagHostOSConnect
        -- fsmStFailComputePhysicalAssociate:hagPnuOSConnect
        -- fsmStFailComputePhysicalAssociate:hagPnuOSDisconnect
        -- fsmStFailComputePhysicalAssociate:resetIBMC
        -- fsmStFailComputePhysicalAssociate:serialDebugPnuOSConnect
        -- fsmStFailComputePhysicalAssociate:serialDebugPnuOSDisconnect
        -- fsmStFailComputePhysicalAssociate:sspUpdateHostPreBoot
        -- fsmStFailComputePhysicalAssociate:updateAdaptorNwFwLocal
        -- fsmStFailComputePhysicalAssociate:updateAdaptorNwFwPeer
        -- fsmStFailComputePhysicalAssociate:updateIBMCFw
        -- fsmStFailComputePhysicalAssociate:updateSspOsSoftware
        -- fsmStFailComputePhysicalAssociate:waitForAdaptorNwFwUpdateLocal
        -- fsmStFailComputePhysicalAssociate:waitForAdaptorNwFwUpdatePeer
        -- fsmStFailComputePhysicalAssociate:waitForIBMCFwUpdate
        -- fsmStFailComputePhysicalAssociate:waitForSspOsUpdateComplete
        -- fsmStFailComputePhysicalDisassociate:BiosPostCompletion
        -- fsmStFailComputePhysicalDisassociate:BmcConfigPnuOS
        -- fsmStFailComputePhysicalDisassociate:BmcPreconfigPnuOSLocal
        -- fsmStFailComputePhysicalDisassociate:BmcPreconfigPnuOSPeer
        -- fsmStFailComputePhysicalDisassociate:BmcUnconfigPnuOS
        -- fsmStFailComputePhysicalDisassociate:BootPnuos
        -- fsmStFailComputePhysicalDisassociate:BootWait
        -- fsmStFailComputePhysicalDisassociate:CheckPowerAvailability
        -- fsmStFailComputePhysicalDisassociate:ConfigBios
        -- fsmStFailComputePhysicalDisassociate:ConfigFlexFlashScrub
        -- fsmStFailComputePhysicalDisassociate:ConfigKvmMgmtDefaultSetting
        -- fsmStFailComputePhysicalDisassociate:ConfigUserAccess
        -- fsmStFailComputePhysicalDisassociate:DeassertResetBypass
        -- fsmStFailComputePhysicalDisassociate:HandlePooling
        -- fsmStFailComputePhysicalDisassociate:NicConfigPnuOSLocal
        -- fsmStFailComputePhysicalDisassociate:NicConfigPnuOSPeer
        -- fsmStFailComputePhysicalDisassociate:NicUnconfigHostOSLocal
        -- fsmStFailComputePhysicalDisassociate:NicUnconfigHostOSPeer
        -- fsmStFailComputePhysicalDisassociate:NicUnconfigPnuOSLocal
        -- fsmStFailComputePhysicalDisassociate:NicUnconfigPnuOSPeer
        -- fsmStFailComputePhysicalDisassociate:NicUnconfigServiceInfraLocal
        -- fsmStFailComputePhysicalDisassociate:NicUnconfigServiceInfraPeer
        -- fsmStFailComputePhysicalDisassociate:PnuOSCatalog
        -- fsmStFailComputePhysicalDisassociate:PnuOSIdent
        -- fsmStFailComputePhysicalDisassociate:PnuOSPolicy
        -- fsmStFailComputePhysicalDisassociate:PnuOSScrub
        -- fsmStFailComputePhysicalDisassociate:PnuOSSelfTest
        -- fsmStFailComputePhysicalDisassociate:PnuOSUnconfig
        -- fsmStFailComputePhysicalDisassociate:PnuOSValidate
        -- fsmStFailComputePhysicalDisassociate:PowerDeployWait
        -- fsmStFailComputePhysicalDisassociate:PowerOn
        -- fsmStFailComputePhysicalDisassociate:PreSanitize
        -- fsmStFailComputePhysicalDisassociate:ResetSecureBootConfig
        -- fsmStFailComputePhysicalDisassociate:Sanitize
        -- fsmStFailComputePhysicalDisassociate:Shutdown
        -- fsmStFailComputePhysicalDisassociate:SolRedirectDisable
        -- fsmStFailComputePhysicalDisassociate:SolRedirectEnable
        -- fsmStFailComputePhysicalDisassociate:SwConfigPnuOSLocal
        -- fsmStFailComputePhysicalDisassociate:SwConfigPnuOSPeer
        -- fsmStFailComputePhysicalDisassociate:SwConfigPortNivLocal
        -- fsmStFailComputePhysicalDisassociate:SwConfigPortNivPeer
        -- fsmStFailComputePhysicalDisassociate:SwUnconfigHostOSLocal
        -- fsmStFailComputePhysicalDisassociate:SwUnconfigHostOSPeer
        -- fsmStFailComputePhysicalDisassociate:SwUnconfigPnuOSLocal
        -- fsmStFailComputePhysicalDisassociate:SwUnconfigPnuOSPeer
        -- fsmStFailComputePhysicalDisassociate:UnconfigBios
        -- fsmStFailComputePhysicalDisassociate:UnconfigCimcVMedia
        -- fsmStFailComputePhysicalDisassociate:UnconfigExtMgmtGw
        -- fsmStFailComputePhysicalDisassociate:UnconfigExtMgmtRules
        -- fsmStFailComputePhysicalDisassociate:UnconfigFlexFlash
        -- fsmStFailComputePhysicalDisassociate:UnconfigSoL
        -- fsmStFailComputePhysicalDisassociate:UnconfigUuid
        -- fsmStFailComputePhysicalDisassociate:VerifyFcZoneConfig
        -- fsmStFailComputePhysicalDisassociate:hagPnuOSConnect
        -- fsmStFailComputePhysicalDisassociate:hagPnuOSDisconnect
        -- fsmStFailComputePhysicalDisassociate:serialDebugPnuOSConnect
        -- fsmStFailComputePhysicalDisassociate:serialDebugPnuOSDisconnect
        -- fsmStFailComputePhysicalPowerCap:Config
        -- fsmStFailComputePhysicalDecommission:CleanupCIMC
        -- fsmStFailComputePhysicalDecommission:CleanupPortConfigLocal
        -- fsmStFailComputePhysicalDecommission:CleanupPortConfigPeer
        -- fsmStFailComputePhysicalDecommission:Execute
        -- fsmStFailComputePhysicalDecommission:StopVMediaLocal
        -- fsmStFailComputePhysicalDecommission:StopVMediaPeer
        -- fsmStFailComputePhysicalDecommission:UnconfigExtMgmtGw
        -- fsmStFailComputePhysicalDecommission:UnconfigExtMgmtRules
        -- fsmStFailComputePhysicalSoftShutdown:Execute
        -- fsmStFailComputePhysicalHardShutdown:Execute
        -- fsmStFailComputePhysicalTurnup:Execute
        -- fsmStFailComputePhysicalPowercycle:Execute
        -- fsmStFailComputePhysicalPowercycle:PreSanitize
        -- fsmStFailComputePhysicalPowercycle:Sanitize
        -- fsmStFailComputePhysicalHardreset:Execute
        -- fsmStFailComputePhysicalHardreset:PreSanitize
        -- fsmStFailComputePhysicalHardreset:Sanitize
        -- fsmStFailComputePhysicalSoftreset:Execute
        -- fsmStFailComputePhysicalSoftreset:PreSanitize
        -- fsmStFailComputePhysicalSoftreset:Sanitize
        -- fsmStFailComputePhysicalSwConnUpd:A
        -- fsmStFailComputePhysicalSwConnUpd:B
        -- fsmStFailComputePhysicalBiosRecovery:Cleanup
        -- fsmStFailComputePhysicalBiosRecovery:PreSanitize
        -- fsmStFailComputePhysicalBiosRecovery:Reset
        -- fsmStFailComputePhysicalBiosRecovery:Sanitize
        -- fsmStFailComputePhysicalBiosRecovery:SetupVmediaLocal
        -- fsmStFailComputePhysicalBiosRecovery:SetupVmediaPeer
        -- fsmStFailComputePhysicalBiosRecovery:Shutdown
        -- fsmStFailComputePhysicalBiosRecovery:Start
        -- fsmStFailComputePhysicalBiosRecovery:StopVMediaLocal
        -- fsmStFailComputePhysicalBiosRecovery:StopVMediaPeer
        -- fsmStFailComputePhysicalBiosRecovery:TeardownVmediaLocal
        -- fsmStFailComputePhysicalBiosRecovery:TeardownVmediaPeer
        -- fsmStFailComputePhysicalBiosRecovery:Wait
        -- fsmStFailComputePhysicalCmosReset:BladePowerOn
        -- fsmStFailComputePhysicalCmosReset:Execute
        -- fsmStFailComputePhysicalCmosReset:PreSanitize
        -- fsmStFailComputePhysicalCmosReset:ReconfigBios
        -- fsmStFailComputePhysicalCmosReset:ReconfigUuid
        -- fsmStFailComputePhysicalCmosReset:Sanitize
        -- fsmStFailComputePhysicalResetBmc:Execute
        -- fsmStFailComputePhysicalUpdateExtUsers:Deploy
        -- fsmStFailComputePhysicalUpdateAdaptor:CheckPowerAvailability
        -- fsmStFailComputePhysicalUpdateAdaptor:PollUpdateStatusLocal
        -- fsmStFailComputePhysicalUpdateAdaptor:PollUpdateStatusPeer
        -- fsmStFailComputePhysicalUpdateAdaptor:PowerDeployWait
        -- fsmStFailComputePhysicalUpdateAdaptor:PowerOff
        -- fsmStFailComputePhysicalUpdateAdaptor:PowerOn
        -- fsmStFailComputePhysicalUpdateAdaptor:UpdateRequestLocal
        -- fsmStFailComputePhysicalUpdateAdaptor:UpdateRequestPeer
        -- fsmStFailComputePhysicalActivateAdaptor:ActivateLocal
        -- fsmStFailComputePhysicalActivateAdaptor:ActivatePeer
        -- fsmStFailComputePhysicalActivateAdaptor:CheckPowerAvailability
        -- fsmStFailComputePhysicalActivateAdaptor:DeassertResetBypass
        -- fsmStFailComputePhysicalActivateAdaptor:PowerDeployWait
        -- fsmStFailComputePhysicalActivateAdaptor:PowerOn
        -- fsmStFailComputePhysicalActivateAdaptor:Reset
        -- fsmStFailComputePhysicalConfigSoL:Execute
        -- fsmStFailComputePhysicalUnconfigSoL:Execute
        -- fsmStFailComputePhysicalDiagnosticInterrupt:Execute
        -- fsmStFailComputePhysicalResetKvm:Execute
        -- fsmStFailComputePhysicalUpdateBIOS:Clear
        -- fsmStFailComputePhysicalUpdateBIOS:PollClearStatus
        -- fsmStFailComputePhysicalUpdateBIOS:PollUpdateStatus
        -- fsmStFailComputePhysicalUpdateBIOS:UpdateRequest
        -- fsmStFailComputePhysicalActivateBIOS:Activate
        -- fsmStFailComputePhysicalActivateBIOS:Clear
        -- fsmStFailComputePhysicalActivateBIOS:PollActivateStatus
        -- fsmStFailComputePhysicalActivateBIOS:PollClearStatus
        -- fsmStFailComputePhysicalActivateBIOS:PowerOff
        -- fsmStFailComputePhysicalActivateBIOS:PowerOn
        -- fsmStFailComputePhysicalActivateBIOS:UpdateTokens
        -- fsmStFailComputePhysicalResetIpmi:Execute
        -- fsmStFailComputePhysicalFwUpgrade:ActivateBios
        -- fsmStFailComputePhysicalFwUpgrade:BiosImgUpdate
        -- fsmStFailComputePhysicalFwUpgrade:BiosPostCompletion
        -- fsmStFailComputePhysicalFwUpgrade:BladePowerOff
        -- fsmStFailComputePhysicalFwUpgrade:BmcConfigPnuOS
        -- fsmStFailComputePhysicalFwUpgrade:BmcPreconfigPnuOSLocal
        -- fsmStFailComputePhysicalFwUpgrade:BmcPreconfigPnuOSPeer
        -- fsmStFailComputePhysicalFwUpgrade:BmcUnconfigPnuOS
        -- fsmStFailComputePhysicalFwUpgrade:BootPnuos
        -- fsmStFailComputePhysicalFwUpgrade:BootWait
        -- fsmStFailComputePhysicalFwUpgrade:CheckPowerAvailability
        -- fsmStFailComputePhysicalFwUpgrade:ClearBiosUpdate
        -- fsmStFailComputePhysicalFwUpgrade:DeassertResetBypass
        -- fsmStFailComputePhysicalFwUpgrade:DeleteCurlDownloadedImages
        -- fsmStFailComputePhysicalFwUpgrade:GraphicsImageUpdate
        -- fsmStFailComputePhysicalFwUpgrade:HbaImgUpdate
        -- fsmStFailComputePhysicalFwUpgrade:LocalDiskFwUpdate
        -- fsmStFailComputePhysicalFwUpgrade:NicConfigPnuOSLocal
        -- fsmStFailComputePhysicalFwUpgrade:NicConfigPnuOSPeer
        -- fsmStFailComputePhysicalFwUpgrade:NicImgUpdate
        -- fsmStFailComputePhysicalFwUpgrade:NicUnconfigPnuOSLocal
        -- fsmStFailComputePhysicalFwUpgrade:NicUnconfigPnuOSPeer
        -- fsmStFailComputePhysicalFwUpgrade:PnuOSCatalog
        -- fsmStFailComputePhysicalFwUpgrade:PnuOSConfig
        -- fsmStFailComputePhysicalFwUpgrade:PnuOSIdent
        -- fsmStFailComputePhysicalFwUpgrade:PnuOSInventory
        -- fsmStFailComputePhysicalFwUpgrade:PnuOSPolicy
        -- fsmStFailComputePhysicalFwUpgrade:PnuOSSelfTest
        -- fsmStFailComputePhysicalFwUpgrade:PnuOSUnloadDrivers
        -- fsmStFailComputePhysicalFwUpgrade:PnuOSValidate
        -- fsmStFailComputePhysicalFwUpgrade:PollBiosActivateStatus
        -- fsmStFailComputePhysicalFwUpgrade:PollBiosUpdateStatus
        -- fsmStFailComputePhysicalFwUpgrade:PollBoardCtrlUpdateStatus
        -- fsmStFailComputePhysicalFwUpgrade:PollClearBiosUpdateStatus
        -- fsmStFailComputePhysicalFwUpgrade:PowerDeployWait
        -- fsmStFailComputePhysicalFwUpgrade:PowerOn
        -- fsmStFailComputePhysicalFwUpgrade:PreSanitize
        -- fsmStFailComputePhysicalFwUpgrade:Sanitize
        -- fsmStFailComputePhysicalFwUpgrade:Shutdown
        -- fsmStFailComputePhysicalFwUpgrade:SolRedirectDisable
        -- fsmStFailComputePhysicalFwUpgrade:SolRedirectEnable
        -- fsmStFailComputePhysicalFwUpgrade:StorageCtlrImgUpdate
        -- fsmStFailComputePhysicalFwUpgrade:SwConfigPnuOSLocal
        -- fsmStFailComputePhysicalFwUpgrade:SwConfigPnuOSPeer
        -- fsmStFailComputePhysicalFwUpgrade:SwConfigPortNivLocal
        -- fsmStFailComputePhysicalFwUpgrade:SwConfigPortNivPeer
        -- fsmStFailComputePhysicalFwUpgrade:SwUnconfigPnuOSLocal
        -- fsmStFailComputePhysicalFwUpgrade:SwUnconfigPnuOSPeer
        -- fsmStFailComputePhysicalFwUpgrade:UnconfigCimcVMedia
        -- fsmStFailComputePhysicalFwUpgrade:UnconfigExtMgmtGw
        -- fsmStFailComputePhysicalFwUpgrade:UnconfigExtMgmtRules
        -- fsmStFailComputePhysicalFwUpgrade:UpdateBiosRequest
        -- fsmStFailComputePhysicalFwUpgrade:UpdateBoardCtrlRequest
        -- fsmStFailComputePhysicalFwUpgrade:activateAdaptorNwFwLocal
        -- fsmStFailComputePhysicalFwUpgrade:activateAdaptorNwFwPeer
        -- fsmStFailComputePhysicalFwUpgrade:activateIBMCFw
        -- fsmStFailComputePhysicalFwUpgrade:copyRemote
        -- fsmStFailComputePhysicalFwUpgrade:downloadImages
        -- fsmStFailComputePhysicalFwUpgrade:hagPnuOSConnect
        -- fsmStFailComputePhysicalFwUpgrade:hagPnuOSDisconnect
        -- fsmStFailComputePhysicalFwUpgrade:resetIBMC
        -- fsmStFailComputePhysicalFwUpgrade:serialDebugPnuOSConnect
        -- fsmStFailComputePhysicalFwUpgrade:serialDebugPnuOSDisconnect
        -- fsmStFailComputePhysicalFwUpgrade:updateAdaptorNwFwLocal
        -- fsmStFailComputePhysicalFwUpgrade:updateAdaptorNwFwPeer
        -- fsmStFailComputePhysicalFwUpgrade:updateIBMCFw
        -- fsmStFailComputePhysicalFwUpgrade:waitForAdaptorNwFwUpdateLocal
        -- fsmStFailComputePhysicalFwUpgrade:waitForAdaptorNwFwUpdatePeer
        -- fsmStFailComputePhysicalFwUpgrade:waitForIBMCFwUpdate
        -- fsmStFailComputePhysicalCimcSessionDelete:Execute
        -- fsmStFailComputePhysicalUpdateBoardController:PollUpdateStatus
        -- fsmStFailComputePhysicalUpdateBoardController:PrepareForUpdate
        -- fsmStFailComputePhysicalUpdateBoardController:ServerPowerOff
        -- fsmStFailComputePhysicalUpdateBoardController:ServerPowerOn
        -- fsmStFailComputePhysicalUpdateBoardController:UpdateRequest
        -- fsmStFailComputePhysicalConfigBoard:ConfigMemoryPolicy
        -- fsmStFailComputePhysicalResetMemoryErrors:Execute
        -- fsmStFailComputePhysicalServiceInfraDeploy:NicConfigLocal
        -- fsmStFailComputePhysicalServiceInfraDeploy:NicConfigPeer
        -- fsmStFailComputePhysicalServiceInfraDeploy:SwConfigLocal
        -- fsmStFailComputePhysicalServiceInfraDeploy:SwConfigPeer
        -- fsmStFailComputePhysicalServiceInfraWithdraw:NicUnConfigLocal
        -- fsmStFailComputePhysicalServiceInfraWithdraw:NicUnConfigPeer
        -- fsmStFailComputePhysicalServiceInfraWithdraw:SwUnConfigLocal
        -- fsmStFailComputePhysicalServiceInfraWithdraw:SwUnConfigPeer
        -- fsmStFailComputePhysicalFlashController:UpdateFlashLife
        -- fsmStFailComputePhysicalEnableCimcSecureBoot:Activate
        -- fsmStFailComputePhysicalEnableCimcSecureBoot:PollUpdateStatus
        -- fsmStFailComputePhysicalEnableCimcSecureBoot:Reset
        -- fsmStFailComputePhysicalEnableCimcSecureBoot:UpdateRequest
        -- fsmStFailComputePhysicalUpdateAdaptorBoot:CheckPowerAvailability
        -- fsmStFailComputePhysicalUpdateAdaptorBoot:PollUpdateStatusLocal
        -- fsmStFailComputePhysicalUpdateAdaptorBoot:PollUpdateStatusPeer
        -- fsmStFailComputePhysicalUpdateAdaptorBoot:PowerDeployWait
        -- fsmStFailComputePhysicalUpdateAdaptorBoot:PowerOff
        -- fsmStFailComputePhysicalUpdateAdaptorBoot:PowerOn
        -- fsmStFailComputePhysicalUpdateAdaptorBoot:UpdateRequestLocal
        -- fsmStFailComputePhysicalUpdateAdaptorBoot:UpdateRequestPeer
        -- fsmStFailComputePhysicalHardPowercycle:Execute
        -- fsmRmtErrComputePhysicalAssociate:ActivateBios
        -- fsmRmtErrComputePhysicalAssociate:BiosImgUpdate
        -- fsmRmtErrComputePhysicalAssociate:BiosPostCompletion
        -- fsmRmtErrComputePhysicalAssociate:BladePowerOff
        -- fsmRmtErrComputePhysicalAssociate:BmcConfigPnuOS
        -- fsmRmtErrComputePhysicalAssociate:BmcPreconfigPnuOSLocal
        -- fsmRmtErrComputePhysicalAssociate:BmcPreconfigPnuOSPeer
        -- fsmRmtErrComputePhysicalAssociate:BmcUnconfigPnuOS
        -- fsmRmtErrComputePhysicalAssociate:BootHost
        -- fsmRmtErrComputePhysicalAssociate:BootPnuos
        -- fsmRmtErrComputePhysicalAssociate:BootWait
        -- fsmRmtErrComputePhysicalAssociate:CheckPowerAvailability
        -- fsmRmtErrComputePhysicalAssociate:ClearBiosUpdate
        -- fsmRmtErrComputePhysicalAssociate:ConfigCimcVMedia
        -- fsmRmtErrComputePhysicalAssociate:ConfigExtMgmtGw
        -- fsmRmtErrComputePhysicalAssociate:ConfigExtMgmtRules
        -- fsmRmtErrComputePhysicalAssociate:ConfigFlexFlash
        -- fsmRmtErrComputePhysicalAssociate:ConfigSoL
        -- fsmRmtErrComputePhysicalAssociate:ConfigUserAccess
        -- fsmRmtErrComputePhysicalAssociate:ConfigUuid
        -- fsmRmtErrComputePhysicalAssociate:DeassertResetBypass
        -- fsmRmtErrComputePhysicalAssociate:DeleteCurlDownloadedImages
        -- fsmRmtErrComputePhysicalAssociate:GraphicsImageUpdate
        -- fsmRmtErrComputePhysicalAssociate:HbaImgUpdate
        -- fsmRmtErrComputePhysicalAssociate:HostOSConfig
        -- fsmRmtErrComputePhysicalAssociate:HostOSIdent
        -- fsmRmtErrComputePhysicalAssociate:HostOSPolicy
        -- fsmRmtErrComputePhysicalAssociate:HostOSValidate
        -- fsmRmtErrComputePhysicalAssociate:LocalDiskFwUpdate
        -- fsmRmtErrComputePhysicalAssociate:MarkAdapterForReboot
        -- fsmRmtErrComputePhysicalAssociate:NicConfigHostOSLocal
        -- fsmRmtErrComputePhysicalAssociate:NicConfigHostOSPeer
        -- fsmRmtErrComputePhysicalAssociate:NicConfigPnuOSLocal
        -- fsmRmtErrComputePhysicalAssociate:NicConfigPnuOSPeer
        -- fsmRmtErrComputePhysicalAssociate:NicConfigServiceInfraLocal
        -- fsmRmtErrComputePhysicalAssociate:NicConfigServiceInfraPeer
        -- fsmRmtErrComputePhysicalAssociate:NicImgUpdate
        -- fsmRmtErrComputePhysicalAssociate:NicUnconfigPnuOSLocal
        -- fsmRmtErrComputePhysicalAssociate:NicUnconfigPnuOSPeer
        -- fsmRmtErrComputePhysicalAssociate:OobStorageInventory
        -- fsmRmtErrComputePhysicalAssociate:PnuOSCatalog
        -- fsmRmtErrComputePhysicalAssociate:PnuOSConfig
        -- fsmRmtErrComputePhysicalAssociate:PnuOSIdent
        -- fsmRmtErrComputePhysicalAssociate:PnuOSInventory
        -- fsmRmtErrComputePhysicalAssociate:PnuOSLocalDiskConfig
        -- fsmRmtErrComputePhysicalAssociate:PnuOSPolicy
        -- fsmRmtErrComputePhysicalAssociate:PnuOSSelfTest
        -- fsmRmtErrComputePhysicalAssociate:PnuOSUnloadDrivers
        -- fsmRmtErrComputePhysicalAssociate:PnuOSValidate
        -- fsmRmtErrComputePhysicalAssociate:PollBiosActivateStatus
        -- fsmRmtErrComputePhysicalAssociate:PollBiosUpdateStatus
        -- fsmRmtErrComputePhysicalAssociate:PollBoardCtrlUpdateStatus
        -- fsmRmtErrComputePhysicalAssociate:PollClearBiosUpdateStatus
        -- fsmRmtErrComputePhysicalAssociate:PowerDeployWait
        -- fsmRmtErrComputePhysicalAssociate:PowerOn
        -- fsmRmtErrComputePhysicalAssociate:PowerOnPreConfig
        -- fsmRmtErrComputePhysicalAssociate:PreSanitize
        -- fsmRmtErrComputePhysicalAssociate:PrepareForBoot
        -- fsmRmtErrComputePhysicalAssociate:PrepareKeyFile
        -- fsmRmtErrComputePhysicalAssociate:Sanitize
        -- fsmRmtErrComputePhysicalAssociate:SolRedirectDisable
        -- fsmRmtErrComputePhysicalAssociate:SolRedirectEnable
        -- fsmRmtErrComputePhysicalAssociate:StorageCtlrImgUpdate
        -- fsmRmtErrComputePhysicalAssociate:SwConfigHostOSLocal
        -- fsmRmtErrComputePhysicalAssociate:SwConfigHostOSPeer
        -- fsmRmtErrComputePhysicalAssociate:SwConfigPnuOSLocal
        -- fsmRmtErrComputePhysicalAssociate:SwConfigPnuOSPeer
        -- fsmRmtErrComputePhysicalAssociate:SwConfigPortNivLocal
        -- fsmRmtErrComputePhysicalAssociate:SwConfigPortNivPeer
        -- fsmRmtErrComputePhysicalAssociate:SwConfigServiceInfraLocal
        -- fsmRmtErrComputePhysicalAssociate:SwConfigServiceInfraPeer
        -- fsmRmtErrComputePhysicalAssociate:SwUnconfigPnuOSLocal
        -- fsmRmtErrComputePhysicalAssociate:SwUnconfigPnuOSPeer
        -- fsmRmtErrComputePhysicalAssociate:SyncPowerState
        -- fsmRmtErrComputePhysicalAssociate:UnconfigCimcVMedia
        -- fsmRmtErrComputePhysicalAssociate:UnconfigExtMgmtGw
        -- fsmRmtErrComputePhysicalAssociate:UnconfigExtMgmtRules
        -- fsmRmtErrComputePhysicalAssociate:UpdateBiosRequest
        -- fsmRmtErrComputePhysicalAssociate:UpdateBoardCtrlRequest
        -- fsmRmtErrComputePhysicalAssociate:VerifyFcZoneConfig
        -- fsmRmtErrComputePhysicalAssociate:activateAdaptorNwFwLocal
        -- fsmRmtErrComputePhysicalAssociate:activateAdaptorNwFwPeer
        -- fsmRmtErrComputePhysicalAssociate:activateIBMCFw
        -- fsmRmtErrComputePhysicalAssociate:copyRemote
        -- fsmRmtErrComputePhysicalAssociate:downloadImages
        -- fsmRmtErrComputePhysicalAssociate:hagHostOSConnect
        -- fsmRmtErrComputePhysicalAssociate:hagPnuOSConnect
        -- fsmRmtErrComputePhysicalAssociate:hagPnuOSDisconnect
        -- fsmRmtErrComputePhysicalAssociate:resetIBMC
        -- fsmRmtErrComputePhysicalAssociate:serialDebugPnuOSConnect
        -- fsmRmtErrComputePhysicalAssociate:serialDebugPnuOSDisconnect
        -- fsmRmtErrComputePhysicalAssociate:sspUpdateHostPreBoot
        -- fsmRmtErrComputePhysicalAssociate:updateAdaptorNwFwLocal
        -- fsmRmtErrComputePhysicalAssociate:updateAdaptorNwFwPeer
        -- fsmRmtErrComputePhysicalAssociate:updateIBMCFw
        -- fsmRmtErrComputePhysicalAssociate:updateSspOsSoftware
        -- fsmRmtErrComputePhysicalAssociate:waitForAdaptorNwFwUpdateLocal
        -- fsmRmtErrComputePhysicalAssociate:waitForAdaptorNwFwUpdatePeer
        -- fsmRmtErrComputePhysicalAssociate:waitForIBMCFwUpdate
        -- fsmRmtErrComputePhysicalAssociate:waitForSspOsUpdateComplete
        -- fsmRmtErrComputePhysicalDisassociate:BiosPostCompletion
        -- fsmRmtErrComputePhysicalDisassociate:BmcConfigPnuOS
        -- fsmRmtErrComputePhysicalDisassociate:BmcPreconfigPnuOSLocal
        -- fsmRmtErrComputePhysicalDisassociate:BmcPreconfigPnuOSPeer
        -- fsmRmtErrComputePhysicalDisassociate:BmcUnconfigPnuOS
        -- fsmRmtErrComputePhysicalDisassociate:BootPnuos
        -- fsmRmtErrComputePhysicalDisassociate:BootWait
        -- fsmRmtErrComputePhysicalDisassociate:CheckPowerAvailability
        -- fsmRmtErrComputePhysicalDisassociate:ConfigBios
        -- fsmRmtErrComputePhysicalDisassociate:ConfigFlexFlashScrub
        -- fsmRmtErrComputePhysicalDisassociate:ConfigKvmMgmtDefaultSetting
        -- fsmRmtErrComputePhysicalDisassociate:ConfigUserAccess
        -- fsmRmtErrComputePhysicalDisassociate:DeassertResetBypass
        -- fsmRmtErrComputePhysicalDisassociate:HandlePooling
        -- fsmRmtErrComputePhysicalDisassociate:NicConfigPnuOSLocal
        -- fsmRmtErrComputePhysicalDisassociate:NicConfigPnuOSPeer
        -- fsmRmtErrComputePhysicalDisassociate:NicUnconfigHostOSLocal
        -- fsmRmtErrComputePhysicalDisassociate:NicUnconfigHostOSPeer
        -- fsmRmtErrComputePhysicalDisassociate:NicUnconfigPnuOSLocal
        -- fsmRmtErrComputePhysicalDisassociate:NicUnconfigPnuOSPeer
        -- fsmRmtErrComputePhysicalDisassociate:NicUnconfigServiceInfraLocal
        -- fsmRmtErrComputePhysicalDisassociate:NicUnconfigServiceInfraPeer
        -- fsmRmtErrComputePhysicalDisassociate:PnuOSCatalog
        -- fsmRmtErrComputePhysicalDisassociate:PnuOSIdent
        -- fsmRmtErrComputePhysicalDisassociate:PnuOSPolicy
        -- fsmRmtErrComputePhysicalDisassociate:PnuOSScrub
        -- fsmRmtErrComputePhysicalDisassociate:PnuOSSelfTest
        -- fsmRmtErrComputePhysicalDisassociate:PnuOSUnconfig
        -- fsmRmtErrComputePhysicalDisassociate:PnuOSValidate
        -- fsmRmtErrComputePhysicalDisassociate:PowerDeployWait
        -- fsmRmtErrComputePhysicalDisassociate:PowerOn
        -- fsmRmtErrComputePhysicalDisassociate:PreSanitize
        -- fsmRmtErrComputePhysicalDisassociate:ResetSecureBootConfig
        -- fsmRmtErrComputePhysicalDisassociate:Sanitize
        -- fsmRmtErrComputePhysicalDisassociate:Shutdown
        -- fsmRmtErrComputePhysicalDisassociate:SolRedirectDisable
        -- fsmRmtErrComputePhysicalDisassociate:SolRedirectEnable
        -- fsmRmtErrComputePhysicalDisassociate:SwConfigPnuOSLocal
        -- fsmRmtErrComputePhysicalDisassociate:SwConfigPnuOSPeer
        -- fsmRmtErrComputePhysicalDisassociate:SwConfigPortNivLocal
        -- fsmRmtErrComputePhysicalDisassociate:SwConfigPortNivPeer
        -- fsmRmtErrComputePhysicalDisassociate:SwUnconfigHostOSLocal
        -- fsmRmtErrComputePhysicalDisassociate:SwUnconfigHostOSPeer
        -- fsmRmtErrComputePhysicalDisassociate:SwUnconfigPnuOSLocal
        -- fsmRmtErrComputePhysicalDisassociate:SwUnconfigPnuOSPeer
        -- fsmRmtErrComputePhysicalDisassociate:UnconfigBios
        -- fsmRmtErrComputePhysicalDisassociate:UnconfigCimcVMedia
        -- fsmRmtErrComputePhysicalDisassociate:UnconfigExtMgmtGw
        -- fsmRmtErrComputePhysicalDisassociate:UnconfigExtMgmtRules
        -- fsmRmtErrComputePhysicalDisassociate:UnconfigFlexFlash
        -- fsmRmtErrComputePhysicalDisassociate:UnconfigSoL
        -- fsmRmtErrComputePhysicalDisassociate:UnconfigUuid
        -- fsmRmtErrComputePhysicalDisassociate:VerifyFcZoneConfig
        -- fsmRmtErrComputePhysicalDisassociate:hagPnuOSConnect
        -- fsmRmtErrComputePhysicalDisassociate:hagPnuOSDisconnect
        -- fsmRmtErrComputePhysicalDisassociate:serialDebugPnuOSConnect
        -- fsmRmtErrComputePhysicalDisassociate:serialDebugPnuOSDisconnect
        -- fsmRmtErrComputePhysicalPowerCap:Config
        -- fsmRmtErrComputePhysicalDecommission:CleanupCIMC
        -- fsmRmtErrComputePhysicalDecommission:CleanupPortConfigLocal
        -- fsmRmtErrComputePhysicalDecommission:CleanupPortConfigPeer
        -- fsmRmtErrComputePhysicalDecommission:Execute
        -- fsmRmtErrComputePhysicalDecommission:StopVMediaLocal
        -- fsmRmtErrComputePhysicalDecommission:StopVMediaPeer
        -- fsmRmtErrComputePhysicalDecommission:UnconfigExtMgmtGw
        -- fsmRmtErrComputePhysicalDecommission:UnconfigExtMgmtRules
        -- fsmRmtErrComputePhysicalSoftShutdown:Execute
        -- fsmRmtErrComputePhysicalHardShutdown:Execute
        -- fsmRmtErrComputePhysicalTurnup:Execute
        -- fsmRmtErrComputePhysicalPowercycle:Execute
        -- fsmRmtErrComputePhysicalPowercycle:PreSanitize
        -- fsmRmtErrComputePhysicalPowercycle:Sanitize
        -- fsmRmtErrComputePhysicalHardreset:Execute
        -- fsmRmtErrComputePhysicalHardreset:PreSanitize
        -- fsmRmtErrComputePhysicalHardreset:Sanitize
        -- fsmRmtErrComputePhysicalSoftreset:Execute
        -- fsmRmtErrComputePhysicalSoftreset:PreSanitize
        -- fsmRmtErrComputePhysicalSoftreset:Sanitize
        -- fsmRmtErrComputePhysicalSwConnUpd:A
        -- fsmRmtErrComputePhysicalSwConnUpd:B
        -- fsmRmtErrComputePhysicalBiosRecovery:Cleanup
        -- fsmRmtErrComputePhysicalBiosRecovery:PreSanitize
        -- fsmRmtErrComputePhysicalBiosRecovery:Reset
        -- fsmRmtErrComputePhysicalBiosRecovery:Sanitize
        -- fsmRmtErrComputePhysicalBiosRecovery:SetupVmediaLocal
        -- fsmRmtErrComputePhysicalBiosRecovery:SetupVmediaPeer
        -- fsmRmtErrComputePhysicalBiosRecovery:Shutdown
        -- fsmRmtErrComputePhysicalBiosRecovery:Start
        -- fsmRmtErrComputePhysicalBiosRecovery:StopVMediaLocal
        -- fsmRmtErrComputePhysicalBiosRecovery:StopVMediaPeer
        -- fsmRmtErrComputePhysicalBiosRecovery:TeardownVmediaLocal
        -- fsmRmtErrComputePhysicalBiosRecovery:TeardownVmediaPeer
        -- fsmRmtErrComputePhysicalBiosRecovery:Wait
        -- fsmRmtErrComputePhysicalCmosReset:BladePowerOn
        -- fsmRmtErrComputePhysicalCmosReset:Execute
        -- fsmRmtErrComputePhysicalCmosReset:PreSanitize
        -- fsmRmtErrComputePhysicalCmosReset:ReconfigBios
        -- fsmRmtErrComputePhysicalCmosReset:ReconfigUuid
        -- fsmRmtErrComputePhysicalCmosReset:Sanitize
        -- fsmRmtErrComputePhysicalResetBmc:Execute
        -- fsmRmtErrComputePhysicalUpdateExtUsers:Deploy
        -- fsmRmtErrComputePhysicalUpdateAdaptor:CheckPowerAvailability
        -- fsmRmtErrComputePhysicalUpdateAdaptor:PollUpdateStatusLocal
        -- fsmRmtErrComputePhysicalUpdateAdaptor:PollUpdateStatusPeer
        -- fsmRmtErrComputePhysicalUpdateAdaptor:PowerDeployWait
        -- fsmRmtErrComputePhysicalUpdateAdaptor:PowerOff
        -- fsmRmtErrComputePhysicalUpdateAdaptor:PowerOn
        -- fsmRmtErrComputePhysicalUpdateAdaptor:UpdateRequestLocal
        -- fsmRmtErrComputePhysicalUpdateAdaptor:UpdateRequestPeer
        -- fsmRmtErrComputePhysicalActivateAdaptor:ActivateLocal
        -- fsmRmtErrComputePhysicalActivateAdaptor:ActivatePeer
        -- fsmRmtErrComputePhysicalActivateAdaptor:CheckPowerAvailability
        -- fsmRmtErrComputePhysicalActivateAdaptor:DeassertResetBypass
        -- fsmRmtErrComputePhysicalActivateAdaptor:PowerDeployWait
        -- fsmRmtErrComputePhysicalActivateAdaptor:PowerOn
        -- fsmRmtErrComputePhysicalActivateAdaptor:Reset
        -- fsmRmtErrComputePhysicalConfigSoL:Execute
        -- fsmRmtErrComputePhysicalUnconfigSoL:Execute
        -- fsmRmtErrComputePhysicalDiagnosticInterrupt:Execute
        -- fsmRmtErrComputePhysicalResetKvm:Execute
        -- fsmRmtErrComputePhysicalUpdateBIOS:Clear
        -- fsmRmtErrComputePhysicalUpdateBIOS:PollClearStatus
        -- fsmRmtErrComputePhysicalUpdateBIOS:PollUpdateStatus
        -- fsmRmtErrComputePhysicalUpdateBIOS:UpdateRequest
        -- fsmRmtErrComputePhysicalActivateBIOS:Activate
        -- fsmRmtErrComputePhysicalActivateBIOS:Clear
        -- fsmRmtErrComputePhysicalActivateBIOS:PollActivateStatus
        -- fsmRmtErrComputePhysicalActivateBIOS:PollClearStatus
        -- fsmRmtErrComputePhysicalActivateBIOS:PowerOff
        -- fsmRmtErrComputePhysicalActivateBIOS:PowerOn
        -- fsmRmtErrComputePhysicalActivateBIOS:UpdateTokens
        -- fsmRmtErrComputePhysicalResetIpmi:Execute
        -- fsmRmtErrComputePhysicalFwUpgrade:ActivateBios
        -- fsmRmtErrComputePhysicalFwUpgrade:BiosImgUpdate
        -- fsmRmtErrComputePhysicalFwUpgrade:BiosPostCompletion
        -- fsmRmtErrComputePhysicalFwUpgrade:BladePowerOff
        -- fsmRmtErrComputePhysicalFwUpgrade:BmcConfigPnuOS
        -- fsmRmtErrComputePhysicalFwUpgrade:BmcPreconfigPnuOSLocal
        -- fsmRmtErrComputePhysicalFwUpgrade:BmcPreconfigPnuOSPeer
        -- fsmRmtErrComputePhysicalFwUpgrade:BmcUnconfigPnuOS
        -- fsmRmtErrComputePhysicalFwUpgrade:BootPnuos
        -- fsmRmtErrComputePhysicalFwUpgrade:BootWait
        -- fsmRmtErrComputePhysicalFwUpgrade:CheckPowerAvailability
        -- fsmRmtErrComputePhysicalFwUpgrade:ClearBiosUpdate
        -- fsmRmtErrComputePhysicalFwUpgrade:DeassertResetBypass
        -- fsmRmtErrComputePhysicalFwUpgrade:DeleteCurlDownloadedImages
        -- fsmRmtErrComputePhysicalFwUpgrade:GraphicsImageUpdate
        -- fsmRmtErrComputePhysicalFwUpgrade:HbaImgUpdate
        -- fsmRmtErrComputePhysicalFwUpgrade:LocalDiskFwUpdate
        -- fsmRmtErrComputePhysicalFwUpgrade:NicConfigPnuOSLocal
        -- fsmRmtErrComputePhysicalFwUpgrade:NicConfigPnuOSPeer
        -- fsmRmtErrComputePhysicalFwUpgrade:NicImgUpdate
        -- fsmRmtErrComputePhysicalFwUpgrade:NicUnconfigPnuOSLocal
        -- fsmRmtErrComputePhysicalFwUpgrade:NicUnconfigPnuOSPeer
        -- fsmRmtErrComputePhysicalFwUpgrade:PnuOSCatalog
        -- fsmRmtErrComputePhysicalFwUpgrade:PnuOSConfig
        -- fsmRmtErrComputePhysicalFwUpgrade:PnuOSIdent
        -- fsmRmtErrComputePhysicalFwUpgrade:PnuOSInventory
        -- fsmRmtErrComputePhysicalFwUpgrade:PnuOSPolicy
        -- fsmRmtErrComputePhysicalFwUpgrade:PnuOSSelfTest
        -- fsmRmtErrComputePhysicalFwUpgrade:PnuOSUnloadDrivers
        -- fsmRmtErrComputePhysicalFwUpgrade:PnuOSValidate
        -- fsmRmtErrComputePhysicalFwUpgrade:PollBiosActivateStatus
        -- fsmRmtErrComputePhysicalFwUpgrade:PollBiosUpdateStatus
        -- fsmRmtErrComputePhysicalFwUpgrade:PollBoardCtrlUpdateStatus
        -- fsmRmtErrComputePhysicalFwUpgrade:PollClearBiosUpdateStatus
        -- fsmRmtErrComputePhysicalFwUpgrade:PowerDeployWait
        -- fsmRmtErrComputePhysicalFwUpgrade:PowerOn
        -- fsmRmtErrComputePhysicalFwUpgrade:PreSanitize
        -- fsmRmtErrComputePhysicalFwUpgrade:Sanitize
        -- fsmRmtErrComputePhysicalFwUpgrade:Shutdown
        -- fsmRmtErrComputePhysicalFwUpgrade:SolRedirectDisable
        -- fsmRmtErrComputePhysicalFwUpgrade:SolRedirectEnable
        -- fsmRmtErrComputePhysicalFwUpgrade:StorageCtlrImgUpdate
        -- fsmRmtErrComputePhysicalFwUpgrade:SwConfigPnuOSLocal
        -- fsmRmtErrComputePhysicalFwUpgrade:SwConfigPnuOSPeer
        -- fsmRmtErrComputePhysicalFwUpgrade:SwConfigPortNivLocal
        -- fsmRmtErrComputePhysicalFwUpgrade:SwConfigPortNivPeer
        -- fsmRmtErrComputePhysicalFwUpgrade:SwUnconfigPnuOSLocal
        -- fsmRmtErrComputePhysicalFwUpgrade:SwUnconfigPnuOSPeer
        -- fsmRmtErrComputePhysicalFwUpgrade:UnconfigCimcVMedia
        -- fsmRmtErrComputePhysicalFwUpgrade:UnconfigExtMgmtGw
        -- fsmRmtErrComputePhysicalFwUpgrade:UnconfigExtMgmtRules
        -- fsmRmtErrComputePhysicalFwUpgrade:UpdateBiosRequest
        -- fsmRmtErrComputePhysicalFwUpgrade:UpdateBoardCtrlRequest
        -- fsmRmtErrComputePhysicalFwUpgrade:activateAdaptorNwFwLocal
        -- fsmRmtErrComputePhysicalFwUpgrade:activateAdaptorNwFwPeer
        -- fsmRmtErrComputePhysicalFwUpgrade:activateIBMCFw
        -- fsmRmtErrComputePhysicalFwUpgrade:copyRemote
        -- fsmRmtErrComputePhysicalFwUpgrade:downloadImages
        -- fsmRmtErrComputePhysicalFwUpgrade:hagPnuOSConnect
        -- fsmRmtErrComputePhysicalFwUpgrade:hagPnuOSDisconnect
        -- fsmRmtErrComputePhysicalFwUpgrade:resetIBMC
        -- fsmRmtErrComputePhysicalFwUpgrade:serialDebugPnuOSConnect
        -- fsmRmtErrComputePhysicalFwUpgrade:serialDebugPnuOSDisconnect
        -- fsmRmtErrComputePhysicalFwUpgrade:updateAdaptorNwFwLocal
        -- fsmRmtErrComputePhysicalFwUpgrade:updateAdaptorNwFwPeer
        -- fsmRmtErrComputePhysicalFwUpgrade:updateIBMCFw
        -- fsmRmtErrComputePhysicalFwUpgrade:waitForAdaptorNwFwUpdateLocal
        -- fsmRmtErrComputePhysicalFwUpgrade:waitForAdaptorNwFwUpdatePeer
        -- fsmRmtErrComputePhysicalFwUpgrade:waitForIBMCFwUpdate
        -- fsmRmtErrComputePhysicalCimcSessionDelete:Execute
        -- fsmRmtErrComputePhysicalUpdateBoardController:PollUpdateStatus
        -- fsmRmtErrComputePhysicalUpdateBoardController:PrepareForUpdate
        -- fsmRmtErrComputePhysicalUpdateBoardController:ServerPowerOff
        -- fsmRmtErrComputePhysicalUpdateBoardController:ServerPowerOn
        -- fsmRmtErrComputePhysicalUpdateBoardController:UpdateRequest
        -- fsmRmtErrComputePhysicalConfigBoard:ConfigMemoryPolicy
        -- fsmRmtErrComputePhysicalResetMemoryErrors:Execute
        -- fsmRmtErrComputePhysicalServiceInfraDeploy:NicConfigLocal
        -- fsmRmtErrComputePhysicalServiceInfraDeploy:NicConfigPeer
        -- fsmRmtErrComputePhysicalServiceInfraDeploy:SwConfigLocal
        -- fsmRmtErrComputePhysicalServiceInfraDeploy:SwConfigPeer
        -- fsmRmtErrComputePhysicalServiceInfraWithdraw:NicUnConfigLocal
        -- fsmRmtErrComputePhysicalServiceInfraWithdraw:NicUnConfigPeer
        -- fsmRmtErrComputePhysicalServiceInfraWithdraw:SwUnConfigLocal
        -- fsmRmtErrComputePhysicalServiceInfraWithdraw:SwUnConfigPeer
        -- fsmRmtErrComputePhysicalFlashController:UpdateFlashLife
        -- fsmRmtErrComputePhysicalEnableCimcSecureBoot:Activate
        -- fsmRmtErrComputePhysicalEnableCimcSecureBoot:PollUpdateStatus
        -- fsmRmtErrComputePhysicalEnableCimcSecureBoot:Reset
        -- fsmRmtErrComputePhysicalEnableCimcSecureBoot:UpdateRequest
        -- fsmRmtErrComputePhysicalUpdateAdaptorBoot:CheckPowerAvailability
        -- fsmRmtErrComputePhysicalUpdateAdaptorBoot:PollUpdateStatusLocal
        -- fsmRmtErrComputePhysicalUpdateAdaptorBoot:PollUpdateStatusPeer
        -- fsmRmtErrComputePhysicalUpdateAdaptorBoot:PowerDeployWait
        -- fsmRmtErrComputePhysicalUpdateAdaptorBoot:PowerOff
        -- fsmRmtErrComputePhysicalUpdateAdaptorBoot:PowerOn
        -- fsmRmtErrComputePhysicalUpdateAdaptorBoot:UpdateRequestLocal
        -- fsmRmtErrComputePhysicalUpdateAdaptorBoot:UpdateRequestPeer
        -- fsmRmtErrComputePhysicalHardPowercycle:Execute
        -- fsmFailComputePhysicalAssociate
        -- fsmFailComputePhysicalDisassociate
        -- fsmFailComputePhysicalPowerCap
        -- fsmFailComputePhysicalDecommission
        -- fsmFailComputePhysicalSoftShutdown
        -- fsmFailComputePhysicalHardShutdown
        -- fsmFailComputePhysicalTurnup
        -- fsmFailComputePhysicalPowercycle
        -- fsmFailComputePhysicalHardreset
        -- fsmFailComputePhysicalSoftreset
        -- fsmFailComputePhysicalSwConnUpd
        -- fsmFailComputePhysicalBiosRecovery
        -- fsmFailComputePhysicalCmosReset
        -- fsmFailComputePhysicalResetBmc
        -- fsmFailComputePhysicalUpdateExtUsers
        -- fsmFailComputePhysicalUpdateAdaptor
        -- fsmFailComputePhysicalActivateAdaptor
        -- fsmFailComputePhysicalConfigSoL
        -- fsmFailComputePhysicalUnconfigSoL
        -- fsmFailComputePhysicalDiagnosticInterrupt
        -- fsmFailComputePhysicalResetKvm
        -- fsmFailComputePhysicalUpdateBIOS
        -- fsmFailComputePhysicalActivateBIOS
        -- fsmFailComputePhysicalResetIpmi
        -- fsmFailComputePhysicalFwUpgrade
        -- fsmFailComputePhysicalCimcSessionDelete
        -- fsmFailComputePhysicalUpdateBoardController
        -- fsmFailComputePhysicalConfigBoard
        -- fsmFailComputePhysicalResetMemoryErrors
        -- fsmFailComputePhysicalServiceInfraDeploy
        -- fsmFailComputePhysicalServiceInfraWithdraw
        -- fsmFailComputePhysicalFlashController
        -- fsmFailComputePhysicalEnableCimcSecureBoot
        -- fsmFailComputePhysicalUpdateAdaptorBoot
        -- fsmFailComputePhysicalHardPowercycle

-- aaa:Config
        -- fltAaaConfigServergroup

-- firmware:ValidationStatus
    -- sys/fw-catalogue/distrib-[name]/validation
        -- fsmStFailFirmwareValidationStatusValidate:CheckReadiness
        -- fsmStFailFirmwareValidationStatusValidate:Complete
        -- fsmStFailFirmwareValidationStatusValidate:PlatformPack
        -- fsmRmtErrFirmwareValidationStatusValidate:CheckReadiness
        -- fsmRmtErrFirmwareValidationStatusValidate:Complete
        -- fsmRmtErrFirmwareValidationStatusValidate:PlatformPack
        -- fsmFailFirmwareValidationStatusValidate

-- sm:ConfigIssue
    -- sec-svc/ld-[name]/config-issue-[moKey]
        -- fltSmConfigIssueLogicalDeviceConfigError

-- fabric:EpMgr
    -- fabric/[id]
        -- fltFabricEpMgrEpTransModeFail
        -- fsmStFailFabricEpMgrConfigure:ApplyConfig
        -- fsmStFailFabricEpMgrConfigure:ApplyPhysical
        -- fsmStFailFabricEpMgrConfigure:ValidateConfiguration
        -- fsmStFailFabricEpMgrConfigure:WaitOnPhys
        -- fsmRmtErrFabricEpMgrConfigure:ApplyConfig
        -- fsmRmtErrFabricEpMgrConfigure:ApplyPhysical
        -- fsmRmtErrFabricEpMgrConfigure:ValidateConfiguration
        -- fsmRmtErrFabricEpMgrConfigure:WaitOnPhys
        -- fsmFailFabricEpMgrConfigure

-- sysdebug:LogExportStatus
    -- sys/sysdebug/log-export-policy/log-export-status-[switchId]
        -- fltSysdebugLogExportStatusLogExportFailure

-- sd:NetMgmtBootstrap
    -- sys-secsvc/slot-[slotId]/app-inst-[appInstId]/net-mgmt-bootstrap
        -- fsmStFailSdNetMgmtBootstrapUpdateNetMgmtBootstrap:SendUpdate
        -- fsmRmtErrSdNetMgmtBootstrapUpdateNetMgmtBootstrap:SendUpdate
        -- fsmFailSdNetMgmtBootstrapUpdateNetMgmtBootstrap

-- firmware:VersionIssue
    -- sys/chassis-[id]/blade-[slotId]/adaptor-[id]/host-eth-[id]/fw-[deployment]/version-issue
    -- sys/rack-unit-[id]/adaptor-[id]/host-eth-[id]/fw-[deployment]/version-issue
    -- sys/chassis-[id]/blade-[slotId]/adaptor-[id]/host-fc-[id]/fw-[deployment]/version-issue
    -- sys/rack-unit-[id]/adaptor-[id]/host-fc-[id]/fw-[deployment]/version-issue
    -- sys/chassis-[id]/blade-[slotId]/ext-board-[id]/bios/fw-[deployment]/version-issue
    -- sys/rack-unit-[id]/ext-board-[id]/bios/fw-[deployment]/version-issue
    -- sys/chassis-[id]/blade-[slotId]/bios/fw-[deployment]/version-issue
    -- sys/rack-unit-[id]/bios/fw-[deployment]/version-issue
    -- capabilities/fw-[deployment]/version-issue
    -- capabilities/ep/mgmt-ext/fw-[deployment]/version-issue
    -- sys/chassis-[id]/epmfpga-[slot]/fw-[deployment]/version-issue
    -- sys/chassis-[id]/fpga/fw-[deployment]/version-issue
    -- sys/chassis-[id]/rommon/fw-[deployment]/version-issue
    -- sys/chassis-[id]/Ssd/fw-[deployment]/version-issue
    -- sys/chassis-[id]/blade-[slotId]/board/graphics-card-[id]/fw-[deployment]/version-issue
    -- sys/rack-unit-[id]/board/graphics-card-[id]/fw-[deployment]/version-issue
    -- sys/chassis-[id]/blade-[slotId]/adaptor-[id]/mgmt/fw-[deployment]/version-issue
    -- sys/rack-unit-[id]/adaptor-[id]/mgmt/fw-[deployment]/version-issue
    -- sys/chassis-[id]/blade-[slotId]/ext-board-[id]/boardController/mgmt/fw-[deployment]/version-issue
    -- sys/rack-unit-[id]/ext-board-[id]/boardController/mgmt/fw-[deployment]/version-issue
    -- sys/chassis-[id]/blade-[slotId]/boardController/mgmt/fw-[deployment]/version-issue
    -- sys/rack-unit-[id]/boardController/mgmt/fw-[deployment]/version-issue
    -- sys/chassis-[id]/blade-[slotId]/ext-board-[id]/mgmt/fw-[deployment]/version-issue
    -- sys/rack-unit-[id]/ext-board-[id]/mgmt/fw-[deployment]/version-issue
    -- sys/chassis-[id]/blade-[slotId]/mgmt/fw-[deployment]/version-issue
    -- sys/rack-unit-[id]/mgmt/fw-[deployment]/version-issue
    -- sys/fex-[id]/mgmt/fw-[deployment]/version-issue
    -- sys/chassis-[id]/slot-[id]/mgmt/fw-[deployment]/version-issue
    -- sys/fex-[id]/slot-[id]/mgmt/fw-[deployment]/version-issue
    -- sys/chassis-[id]/sw-slot-[id]/mgmt/fw-[deployment]/version-issue
    -- sys/switch-[id]/mgmt/fw-[deployment]/version-issue
    -- sys/mgmt/fw-[deployment]/version-issue
    -- sys/chassis-[id]/blade-[slotId]/os-ctrl/fw-[deployment]/version-issue
    -- sys/chassis-[id]/blade-[slotId]/os-ctrl/fw-[deployment]/version-issue
    -- sys/rack-unit-[id]/os-ctrl/fw-[deployment]/version-issue
    -- sys/os-ctrl/fw-[deployment]/version-issue
    -- sys/chassis-[id]/blade-[slotId]/board/storage-[type]-[id]/fw-[deployment]/version-issue
    -- sys/rack-unit-[id]/board/storage-[type]-[id]/fw-[deployment]/version-issue
    -- sys/chassis-[id]/blade-[slotId]/board/storage-flexflash-[id]/fw-[deployment]/version-issue
    -- sys/rack-unit-[id]/board/storage-flexflash-[id]/fw-[deployment]/version-issue
    -- sys/chassis-[id]/blade-[slotId]/board/storage-[type]-[id]/disk-[id]/fw-[deployment]/version-issue
    -- sys/rack-unit-[id]/board/storage-[type]-[id]/disk-[id]/fw-[deployment]/version-issue
        -- fltFirmwareVersionIssueImageVersionMismatch

-- firmware:Downloader
    -- sys/fw-catalogue/dnld-[fileName]
    -- sys/pki-ext/tp-[name]/certrevoke/dnld-[fileName]
    -- sys/pki-ext/tpAutoImport-/dnld-[fileName]
        -- fsmStFailFirmwareDownloaderDownload:CopyRemote
        -- fsmStFailFirmwareDownloaderDownload:DeleteLocal
        -- fsmStFailFirmwareDownloaderDownload:Local
        -- fsmStFailFirmwareDownloaderDownload:UnpackLocal
        -- fsmRmtErrFirmwareDownloaderDownload:CopyRemote
        -- fsmRmtErrFirmwareDownloaderDownload:DeleteLocal
        -- fsmRmtErrFirmwareDownloaderDownload:Local
        -- fsmRmtErrFirmwareDownloaderDownload:UnpackLocal
        -- fsmFailFirmwareDownloaderDownload

-- policy:PolicyScope
    -- extpol/reg/clients/client-[id]/scope-cont-[appType]/context-[name]/scope-[policyType]-[resolveType]-[policyName]
    -- extpol/reg/controllers/contro-[id]/scope-cont-[appType]/context-[name]/scope-[policyType]-[resolveType]-[policyName]
    -- extpol/reg/providers/prov-[type]/scope-cont-[appType]/context-[name]/scope-[policyType]-[resolveType]-[policyName]
    -- extpol/reg/scope-cont-[appType]/context-[name]/scope-[policyType]-[resolveType]-[policyName]
    -- policy-ep/scope-cont-[appType]/context-[name]/scope-[policyType]-[resolveType]-[policyName]
        -- fsmStFailPolicyPolicyScopeReleasePolicyFsm:Release
        -- fsmStFailPolicyPolicyScopeReleaseOperationFsm:Release
        -- fsmStFailPolicyPolicyScopeReleaseStorageFsm:Release
        -- fsmStFailPolicyPolicyScopeResolveManyPolicyFsm:ResolveMany
        -- fsmStFailPolicyPolicyScopeResolveManyOperationFsm:ResolveMany
        -- fsmStFailPolicyPolicyScopeResolveManyStorageFsm:ResolveMany
        -- fsmStFailPolicyPolicyScopeReleaseManyPolicyFsm:ReleaseMany
        -- fsmStFailPolicyPolicyScopeReleaseManyOperationFsm:ReleaseMany
        -- fsmStFailPolicyPolicyScopeReleaseManyStorageFsm:ReleaseMany
        -- fsmStFailPolicyPolicyScopeResolveAllPolicyFsm:ResolveAll
        -- fsmStFailPolicyPolicyScopeResolveAllOperationFsm:ResolveAll
        -- fsmStFailPolicyPolicyScopeResolveAllStorageFsm:ResolveAll
        -- fsmStFailPolicyPolicyScopeReleaseAllPolicyFsm:ReleaseAll
        -- fsmStFailPolicyPolicyScopeReleaseAllOperationFsm:ReleaseAll
        -- fsmStFailPolicyPolicyScopeReleaseAllStorageFsm:ReleaseAll
        -- fsmRmtErrPolicyPolicyScopeReleasePolicyFsm:Release
        -- fsmRmtErrPolicyPolicyScopeReleaseOperationFsm:Release
        -- fsmRmtErrPolicyPolicyScopeReleaseStorageFsm:Release
        -- fsmRmtErrPolicyPolicyScopeResolveManyPolicyFsm:ResolveMany
        -- fsmRmtErrPolicyPolicyScopeResolveManyOperationFsm:ResolveMany
        -- fsmRmtErrPolicyPolicyScopeResolveManyStorageFsm:ResolveMany
        -- fsmRmtErrPolicyPolicyScopeReleaseManyPolicyFsm:ReleaseMany
        -- fsmRmtErrPolicyPolicyScopeReleaseManyOperationFsm:ReleaseMany
        -- fsmRmtErrPolicyPolicyScopeReleaseManyStorageFsm:ReleaseMany
        -- fsmRmtErrPolicyPolicyScopeResolveAllPolicyFsm:ResolveAll
        -- fsmRmtErrPolicyPolicyScopeResolveAllOperationFsm:ResolveAll
        -- fsmRmtErrPolicyPolicyScopeResolveAllStorageFsm:ResolveAll
        -- fsmRmtErrPolicyPolicyScopeReleaseAllPolicyFsm:ReleaseAll
        -- fsmRmtErrPolicyPolicyScopeReleaseAllOperationFsm:ReleaseAll
        -- fsmRmtErrPolicyPolicyScopeReleaseAllStorageFsm:ReleaseAll
        -- fsmFailPolicyPolicyScopeReleasePolicyFsm
        -- fsmFailPolicyPolicyScopeReleaseOperationFsm
        -- fsmFailPolicyPolicyScopeReleaseStorageFsm
        -- fsmFailPolicyPolicyScopeResolveManyPolicyFsm
        -- fsmFailPolicyPolicyScopeResolveManyOperationFsm
        -- fsmFailPolicyPolicyScopeResolveManyStorageFsm
        -- fsmFailPolicyPolicyScopeReleaseManyPolicyFsm
        -- fsmFailPolicyPolicyScopeReleaseManyOperationFsm
        -- fsmFailPolicyPolicyScopeReleaseManyStorageFsm
        -- fsmFailPolicyPolicyScopeResolveAllPolicyFsm
        -- fsmFailPolicyPolicyScopeResolveAllOperationFsm
        -- fsmFailPolicyPolicyScopeResolveAllStorageFsm
        -- fsmFailPolicyPolicyScopeReleaseAllPolicyFsm
        -- fsmFailPolicyPolicyScopeReleaseAllOperationFsm
        -- fsmFailPolicyPolicyScopeReleaseAllStorageFsm

-- extpol:Registry
    -- extpol/reg
        -- fsmStFailExtpolRegistryCrossDomainConfig:SetLocal
        -- fsmStFailExtpolRegistryCrossDomainConfig:SetPeer
        -- fsmStFailExtpolRegistryCrossDomainDelete:SetLocal
        -- fsmStFailExtpolRegistryCrossDomainDelete:SetPeer
        -- fsmRmtErrExtpolRegistryCrossDomainConfig:SetLocal
        -- fsmRmtErrExtpolRegistryCrossDomainConfig:SetPeer
        -- fsmRmtErrExtpolRegistryCrossDomainDelete:SetLocal
        -- fsmRmtErrExtpolRegistryCrossDomainDelete:SetPeer
        -- fsmFailExtpolRegistryCrossDomainConfig
        -- fsmFailExtpolRegistryCrossDomainDelete

-- adaptor:HostFcIf
    -- sys/chassis-[id]/blade-[slotId]/adaptor-[id]/host-fc-[id]
    -- sys/rack-unit-[id]/adaptor-[id]/host-fc-[id]
        -- fsmStFailAdaptorHostFcIfResetFcPersBinding:ExecuteLocal
        -- fsmStFailAdaptorHostFcIfResetFcPersBinding:ExecutePeer
        -- fsmStFailAdaptorHostFcIfCircuitReset:DisableA
        -- fsmStFailAdaptorHostFcIfCircuitReset:DisableB
        -- fsmStFailAdaptorHostFcIfCircuitReset:EnableA
        -- fsmStFailAdaptorHostFcIfCircuitReset:EnableB
        -- fsmRmtErrAdaptorHostFcIfResetFcPersBinding:ExecuteLocal
        -- fsmRmtErrAdaptorHostFcIfResetFcPersBinding:ExecutePeer
        -- fsmRmtErrAdaptorHostFcIfCircuitReset:DisableA
        -- fsmRmtErrAdaptorHostFcIfCircuitReset:DisableB
        -- fsmRmtErrAdaptorHostFcIfCircuitReset:EnableA
        -- fsmRmtErrAdaptorHostFcIfCircuitReset:EnableB
        -- fsmFailAdaptorHostFcIfResetFcPersBinding
        -- fsmFailAdaptorHostFcIfCircuitReset

-- fabric:SanCloud
    -- fabric/san
        -- fsmStFailFabricSanCloudSwitchMode:SwConfigLocal
        -- fsmStFailFabricSanCloudSwitchMode:SwConfigPeer
        -- fsmRmtErrFabricSanCloudSwitchMode:SwConfigLocal
        -- fsmRmtErrFabricSanCloudSwitchMode:SwConfigPeer
        -- fsmFailFabricSanCloudSwitchMode

-- fabric:DceSwSrvPcEp
    -- fabric/server/sw-[id]/pc-[portId]/ep-slot-[slotId]-port-[portId]
    -- fabric/server/sw-[id]/slot-[slotId]-aggr-port-[aggrPortId]/ep-slot-[slotId]-port-[portId]
    -- fabric/server/sw-[id]/pc-[portId]/slot-[slotId]-aggr-port-[aggrPortId]/ep-slot-[slotId]-port-[portId]
    -- fabric/eth-estc/[id]/slot-[slotId]-aggr-port-[aggrPortId]/ep-slot-[slotId]-port-[portId]
    -- fabric/eth-estc/[id]/pc-[portId]/slot-[slotId]-aggr-port-[aggrPortId]/ep-slot-[slotId]-port-[portId]
    -- fabric/lan/[id]/slot-[slotId]-aggr-port-[aggrPortId]/ep-slot-[slotId]-port-[portId]
    -- fabric/lan/[id]/pc-[portId]/slot-[slotId]-aggr-port-[aggrPortId]/ep-slot-[slotId]-port-[portId]
    -- fabric/lanmon/[id]/eth-mon-[name]/slot-[slotId]-aggr-port-[aggrPortId]/ep-slot-[slotId]-port-[portId]
    -- fabric/san/[id]/slot-[slotId]-aggr-port-[aggrPortId]/ep-slot-[slotId]-port-[portId]
    -- fabric/san/[id]/fcoesanpc-[portId]/slot-[slotId]-aggr-port-[aggrPortId]/ep-slot-[slotId]-port-[portId]
        -- fltFabricDceSwSrvPcEpDown

-- vnic:IScsi
    -- org-[name]/tier-[name]/ls-[name]/iscsi-[name]
    -- org-[name]/ls-[name]/iscsi-[name]
        -- fltVnicIScsiConfig-failed

-- sm:HwCrypto
    -- sys-secsvc/slot-[slotId]/app-inst-[appInstId]/hwCrypto
    -- sec-svc/slot-[slotId]/app-inst-[appName]-[identifier]/hwCrypto
        -- fltSmHwCryptoHwCryptoNotOperable

-- comm:NtpProvider
    -- sys/svc-ext/datetime-svc/ntp-[name]
        -- fltCommNtpProviderCommNtpStratumCheckFailed

-- fabric:EthLanEp
    -- fabric/lan/[id]/phys-slot-[slotId]-port-[portId]
    -- fabric/server/sw-[id]/slot-[slotId]-aggr-port-[aggrPortId]/phys-slot-[slotId]-port-[portId]
    -- fabric/server/sw-[id]/pc-[portId]/slot-[slotId]-aggr-port-[aggrPortId]/phys-slot-[slotId]-port-[portId]
    -- fabric/eth-estc/[id]/slot-[slotId]-aggr-port-[aggrPortId]/phys-slot-[slotId]-port-[portId]
    -- fabric/eth-estc/[id]/pc-[portId]/slot-[slotId]-aggr-port-[aggrPortId]/phys-slot-[slotId]-port-[portId]
    -- fabric/lan/[id]/slot-[slotId]-aggr-port-[aggrPortId]/phys-slot-[slotId]-port-[portId]
    -- fabric/lan/[id]/pc-[portId]/slot-[slotId]-aggr-port-[aggrPortId]/phys-slot-[slotId]-port-[portId]
    -- fabric/lanmon/[id]/eth-mon-[name]/slot-[slotId]-aggr-port-[aggrPortId]/phys-slot-[slotId]-port-[portId]
    -- fabric/san/[id]/slot-[slotId]-aggr-port-[aggrPortId]/phys-slot-[slotId]-port-[portId]
    -- fabric/san/[id]/fcoesanpc-[portId]/slot-[slotId]-aggr-port-[aggrPortId]/phys-slot-[slotId]-port-[portId]
        -- fltFabricEthLanEpMissingPrimaryVlan
        -- fltFabricEthLanEpOverlapping-vlan
        -- fltFabricEthLanEpUdldLinkDown

-- aaa:Locale
    -- sys/user-ext/locale-[name]
        -- fltAaaLocaleLocaleNotDeployed

-- synthetic:FsObj
    -- sys/file-[name]
        -- fsmStFailSyntheticFsObjCreate:createLocal
        -- fsmStFailSyntheticFsObjCreate:createRemote
        -- fsmRmtErrSyntheticFsObjCreate:createLocal
        -- fsmRmtErrSyntheticFsObjCreate:createRemote
        -- fsmFailSyntheticFsObjCreate

-- mgmt:Controller
    -- sys/chassis-[id]/blade-[slotId]/adaptor-[id]/mgmt
    -- sys/rack-unit-[id]/adaptor-[id]/mgmt
    -- sys/chassis-[id]/blade-[slotId]/ext-board-[id]/boardController/mgmt
    -- sys/rack-unit-[id]/ext-board-[id]/boardController/mgmt
    -- sys/chassis-[id]/blade-[slotId]/boardController/mgmt
    -- sys/rack-unit-[id]/boardController/mgmt
    -- sys/chassis-[id]/blade-[slotId]/ext-board-[id]/mgmt
    -- sys/rack-unit-[id]/ext-board-[id]/mgmt
    -- sys/chassis-[id]/blade-[slotId]/mgmt
    -- sys/rack-unit-[id]/mgmt
    -- sys/fex-[id]/mgmt
    -- sys/chassis-[id]/slot-[id]/mgmt
    -- sys/fex-[id]/slot-[id]/mgmt
    -- sys/chassis-[id]/sw-slot-[id]/mgmt
    -- sys/switch-[id]/mgmt
    -- sys/mgmt
        -- fltMgmtControllerUnsupportedDimmBlacklisting
        -- fsmStFailMgmtControllerExtMgmtIfConfig:Primary
        -- fsmStFailMgmtControllerExtMgmtIfConfig:Secondary
        -- fsmStFailMgmtControllerUpdateSwitch:UpdateManager
        -- fsmStFailMgmtControllerUpdateSwitch:copyToLocal
        -- fsmStFailMgmtControllerUpdateSwitch:copyToPeer
        -- fsmStFailMgmtControllerUpdateSwitch:resetLocal
        -- fsmStFailMgmtControllerUpdateSwitch:resetRemote
        -- fsmStFailMgmtControllerUpdateSwitch:updateLocal
        -- fsmStFailMgmtControllerUpdateSwitch:updateRemote
        -- fsmStFailMgmtControllerUpdateSwitch:verifyLocal
        -- fsmStFailMgmtControllerUpdateSwitch:verifyRemote
        -- fsmStFailMgmtControllerUpdateIOM:CopyIOMImgToSub
        -- fsmStFailMgmtControllerUpdateIOM:CopyImgFromRep
        -- fsmStFailMgmtControllerUpdateIOM:PollUpdateStatus
        -- fsmStFailMgmtControllerUpdateIOM:UpdateRequest
        -- fsmStFailMgmtControllerActivateIOM:Activate
        -- fsmStFailMgmtControllerActivateIOM:Reset
        -- fsmStFailMgmtControllerUpdateBMC:PollUpdateStatus
        -- fsmStFailMgmtControllerUpdateBMC:UpdateRequest
        -- fsmStFailMgmtControllerActivateBMC:Activate
        -- fsmStFailMgmtControllerActivateBMC:Reset
        -- fsmStFailMgmtControllerUpdateFPRManager:copyExtToLocal
        -- fsmStFailMgmtControllerUpdateFPRManager:copyExtToPeer
        -- fsmStFailMgmtControllerUpdateFPRManager:execute
        -- fsmStFailMgmtControllerUpdateFPRManager:start
        -- fsmStFailMgmtControllerSysConfig:Primary
        -- fsmStFailMgmtControllerSysConfig:Secondary
        -- fsmStFailMgmtControllerOnline:BmcConfigureConnLocal
        -- fsmStFailMgmtControllerOnline:BmcConfigureConnPeer
        -- fsmStFailMgmtControllerOnline:SwConfigureConnLocal
        -- fsmStFailMgmtControllerOnline:SwConfigureConnPeer
        -- fsmStFailMgmtControllerRegistryConfig:Remove
        -- fsmStFailMgmtControllerExtMgmtInterfaceConfig:Active
        -- fsmStFailMgmtControllerExtMgmtInterfaceConfig:CIMCVlanCfgLocal
        -- fsmStFailMgmtControllerExtMgmtInterfaceConfig:CIMCVlanCfgPeer
        -- fsmStFailMgmtControllerExtMgmtInterfaceConfig:CMCVlanCfg
        -- fsmStFailMgmtControllerExtMgmtInterfaceConfig:CMCVlanCfgPeer
        -- fsmStFailMgmtControllerLockConfig:PowerButtonLockConfig
        -- fsmRmtErrMgmtControllerExtMgmtIfConfig:Primary
        -- fsmRmtErrMgmtControllerExtMgmtIfConfig:Secondary
        -- fsmRmtErrMgmtControllerUpdateSwitch:UpdateManager
        -- fsmRmtErrMgmtControllerUpdateSwitch:copyToLocal
        -- fsmRmtErrMgmtControllerUpdateSwitch:copyToPeer
        -- fsmRmtErrMgmtControllerUpdateSwitch:resetLocal
        -- fsmRmtErrMgmtControllerUpdateSwitch:resetRemote
        -- fsmRmtErrMgmtControllerUpdateSwitch:updateLocal
        -- fsmRmtErrMgmtControllerUpdateSwitch:updateRemote
        -- fsmRmtErrMgmtControllerUpdateSwitch:verifyLocal
        -- fsmRmtErrMgmtControllerUpdateSwitch:verifyRemote
        -- fsmRmtErrMgmtControllerUpdateIOM:CopyIOMImgToSub
        -- fsmRmtErrMgmtControllerUpdateIOM:CopyImgFromRep
        -- fsmRmtErrMgmtControllerUpdateIOM:PollUpdateStatus
        -- fsmRmtErrMgmtControllerUpdateIOM:UpdateRequest
        -- fsmRmtErrMgmtControllerActivateIOM:Activate
        -- fsmRmtErrMgmtControllerActivateIOM:Reset
        -- fsmRmtErrMgmtControllerUpdateBMC:PollUpdateStatus
        -- fsmRmtErrMgmtControllerUpdateBMC:UpdateRequest
        -- fsmRmtErrMgmtControllerActivateBMC:Activate
        -- fsmRmtErrMgmtControllerActivateBMC:Reset
        -- fsmRmtErrMgmtControllerUpdateFPRManager:copyExtToLocal
        -- fsmRmtErrMgmtControllerUpdateFPRManager:copyExtToPeer
        -- fsmRmtErrMgmtControllerUpdateFPRManager:execute
        -- fsmRmtErrMgmtControllerUpdateFPRManager:start
        -- fsmRmtErrMgmtControllerSysConfig:Primary
        -- fsmRmtErrMgmtControllerSysConfig:Secondary
        -- fsmRmtErrMgmtControllerOnline:BmcConfigureConnLocal
        -- fsmRmtErrMgmtControllerOnline:BmcConfigureConnPeer
        -- fsmRmtErrMgmtControllerOnline:SwConfigureConnLocal
        -- fsmRmtErrMgmtControllerOnline:SwConfigureConnPeer
        -- fsmRmtErrMgmtControllerRegistryConfig:Remove
        -- fsmRmtErrMgmtControllerExtMgmtInterfaceConfig:Active
        -- fsmRmtErrMgmtControllerExtMgmtInterfaceConfig:CIMCVlanCfgLocal
        -- fsmRmtErrMgmtControllerExtMgmtInterfaceConfig:CIMCVlanCfgPeer
        -- fsmRmtErrMgmtControllerExtMgmtInterfaceConfig:CMCVlanCfg
        -- fsmRmtErrMgmtControllerExtMgmtInterfaceConfig:CMCVlanCfgPeer
        -- fsmRmtErrMgmtControllerLockConfig:PowerButtonLockConfig
        -- fsmFailMgmtControllerExtMgmtIfConfig
        -- fsmFailMgmtControllerUpdateSwitch
        -- fsmFailMgmtControllerUpdateIOM
        -- fsmFailMgmtControllerActivateIOM
        -- fsmFailMgmtControllerUpdateBMC
        -- fsmFailMgmtControllerActivateBMC
        -- fsmFailMgmtControllerUpdateFPRManager
        -- fsmFailMgmtControllerSysConfig
        -- fsmFailMgmtControllerOnline
        -- fsmFailMgmtControllerRegistryConfig
        -- fsmFailMgmtControllerExtMgmtInterfaceConfig
        -- fsmFailMgmtControllerLockConfig

-- mgmt:Interface
    -- org-[name]/tier-[name]/ls-[name]/iface-[mode]
    -- org-[name]/ls-[name]/iface-[mode]
    -- sys/chassis-[id]/blade-[slotId]/adaptor-[id]/mgmt/iface-[mode]
    -- sys/rack-unit-[id]/adaptor-[id]/mgmt/iface-[mode]
    -- sys/chassis-[id]/blade-[slotId]/ext-board-[id]/boardController/mgmt/iface-[mode]
    -- sys/rack-unit-[id]/ext-board-[id]/boardController/mgmt/iface-[mode]
    -- sys/chassis-[id]/blade-[slotId]/boardController/mgmt/iface-[mode]
    -- sys/rack-unit-[id]/boardController/mgmt/iface-[mode]
    -- sys/chassis-[id]/blade-[slotId]/ext-board-[id]/mgmt/iface-[mode]
    -- sys/rack-unit-[id]/ext-board-[id]/mgmt/iface-[mode]
    -- sys/chassis-[id]/blade-[slotId]/mgmt/iface-[mode]
    -- sys/rack-unit-[id]/mgmt/iface-[mode]
    -- sys/fex-[id]/mgmt/iface-[mode]
    -- sys/chassis-[id]/slot-[id]/mgmt/iface-[mode]
    -- sys/fex-[id]/slot-[id]/mgmt/iface-[mode]
    -- sys/chassis-[id]/sw-slot-[id]/mgmt/iface-[mode]
    -- sys/switch-[id]/mgmt/iface-[mode]
    -- sys/mgmt/iface-[mode]
        -- fltMgmtInterfaceNamedInbandVlanUnresolved
        -- fltMgmtInterfaceInbandUnsupportedServer
        -- fltMgmtInterfaceInbandUnsupportedFirmware

-- sd:InternalMgmtBootstrap
    -- sys-secsvc/slot-[slotId]/app-inst-[appInstId]/internal-mgmt-bootstrap
        -- fltSdInternalMgmtBootstrapInternalMgmtVnicConfigFail

-- fabric:VnetEpSyncEp
    -- extpol/reg/providers/prov-[type]/syncEp
        -- fsmStFailFabricVnetEpSyncEpPushVnetEpDeletion:Sync
        -- fsmRmtErrFabricVnetEpSyncEpPushVnetEpDeletion:Sync
        -- fsmFailFabricVnetEpSyncEpPushVnetEpDeletion

-- sysdebug:LogControlEp
    -- sys/sysdebug/logcontrol
        -- fsmStFailSysdebugLogControlEpLogControlPersist:Local
        -- fsmStFailSysdebugLogControlEpLogControlPersist:Peer
        -- fsmRmtErrSysdebugLogControlEpLogControlPersist:Local
        -- fsmRmtErrSysdebugLogControlEpLogControlPersist:Peer
        -- fsmFailSysdebugLogControlEpLogControlPersist

-- pki:KeyRing
    -- sys/pki-ext/keyring-[name]
        -- fltPkiKeyRingStatus
        -- fltPkiKeyRingKeyRingNotDeployed
        -- fltPkiKeyRingModulus
        -- fltPkiKeyRingEc

-- compute:Blade
    -- sys/chassis-[id]/blade-[slotId]
        -- fsmStFailComputeBladeDiscover:BiosPostCompletion
        -- fsmStFailComputeBladeDiscover:BladeBootPnuos
        -- fsmStFailComputeBladeDiscover:BladeBootWait
        -- fsmStFailComputeBladeDiscover:BladePowerOn
        -- fsmStFailComputeBladeDiscover:BladeReadSmbios
        -- fsmStFailComputeBladeDiscover:BmcConfigPnuOS
        -- fsmStFailComputeBladeDiscover:BmcInventory
        -- fsmStFailComputeBladeDiscover:BmcPreConfigPnuOSLocal
        -- fsmStFailComputeBladeDiscover:BmcPreConfigPnuOSPeer
        -- fsmStFailComputeBladeDiscover:BmcPresence
        -- fsmStFailComputeBladeDiscover:BmcShutdownDiscovered
        -- fsmStFailComputeBladeDiscover:CheckPowerAvailability
        -- fsmStFailComputeBladeDiscover:ConfigBMCPowerParams
        -- fsmStFailComputeBladeDiscover:ConfigFeLocal
        -- fsmStFailComputeBladeDiscover:ConfigFePeer
        -- fsmStFailComputeBladeDiscover:ConfigFlexFlashScrub
        -- fsmStFailComputeBladeDiscover:ConfigUserAccess
        -- fsmStFailComputeBladeDiscover:HandlePooling
        -- fsmStFailComputeBladeDiscover:NicConfigPnuOSLocal
        -- fsmStFailComputeBladeDiscover:NicConfigPnuOSPeer
        -- fsmStFailComputeBladeDiscover:NicPresenceLocal
        -- fsmStFailComputeBladeDiscover:NicPresencePeer
        -- fsmStFailComputeBladeDiscover:NicUnconfigPnuOSLocal
        -- fsmStFailComputeBladeDiscover:NicUnconfigPnuOSPeer
        -- fsmStFailComputeBladeDiscover:OobStorageInventory
        -- fsmStFailComputeBladeDiscover:PnuOSCatalog
        -- fsmStFailComputeBladeDiscover:PnuOSIdent
        -- fsmStFailComputeBladeDiscover:PnuOSInventory
        -- fsmStFailComputeBladeDiscover:PnuOSPolicy
        -- fsmStFailComputeBladeDiscover:PnuOSPowerProfiling
        -- fsmStFailComputeBladeDiscover:PnuOSScrub
        -- fsmStFailComputeBladeDiscover:PnuOSSelfTest
        -- fsmStFailComputeBladeDiscover:PowerDeployWait
        -- fsmStFailComputeBladeDiscover:PreSanitize
        -- fsmStFailComputeBladeDiscover:PrepareKeyFile
        -- fsmStFailComputeBladeDiscover:Sanitize
        -- fsmStFailComputeBladeDiscover:SendBmcProfilingDone
        -- fsmStFailComputeBladeDiscover:SendBmcProfilingInit
        -- fsmStFailComputeBladeDiscover:SetupVmediaLocal
        -- fsmStFailComputeBladeDiscover:SetupVmediaPeer
        -- fsmStFailComputeBladeDiscover:SolRedirectDisable
        -- fsmStFailComputeBladeDiscover:SolRedirectEnable
        -- fsmStFailComputeBladeDiscover:SwConfigPnuOSLocal
        -- fsmStFailComputeBladeDiscover:SwConfigPnuOSPeer
        -- fsmStFailComputeBladeDiscover:SwUnconfigPnuOSLocal
        -- fsmStFailComputeBladeDiscover:SwUnconfigPnuOSPeer
        -- fsmStFailComputeBladeDiscover:TeardownVmediaLocal
        -- fsmStFailComputeBladeDiscover:TeardownVmediaPeer
        -- fsmStFailComputeBladeDiscover:UnconfigCimcVMedia
        -- fsmStFailComputeBladeDiscover:UnconfigExtMgmtGw
        -- fsmStFailComputeBladeDiscover:UnconfigExtMgmtRules
        -- fsmStFailComputeBladeDiscover:hagConnect
        -- fsmStFailComputeBladeDiscover:hagDisconnect
        -- fsmStFailComputeBladeDiscover:serialDebugConnect
        -- fsmStFailComputeBladeDiscover:serialDebugDisconnect
        -- fsmStFailComputeBladeDiag:BiosPostCompletion
        -- fsmStFailComputeBladeDiag:BladeBoot
        -- fsmStFailComputeBladeDiag:BladeBootWait
        -- fsmStFailComputeBladeDiag:BladePowerOn
        -- fsmStFailComputeBladeDiag:BladeReadSmbios
        -- fsmStFailComputeBladeDiag:BmcConfigPnuOS
        -- fsmStFailComputeBladeDiag:BmcInventory
        -- fsmStFailComputeBladeDiag:BmcPresence
        -- fsmStFailComputeBladeDiag:BmcShutdownDiagCompleted
        -- fsmStFailComputeBladeDiag:CleanupServerConnSwA
        -- fsmStFailComputeBladeDiag:CleanupServerConnSwB
        -- fsmStFailComputeBladeDiag:ConfigFeLocal
        -- fsmStFailComputeBladeDiag:ConfigFePeer
        -- fsmStFailComputeBladeDiag:ConfigUserAccess
        -- fsmStFailComputeBladeDiag:DebugWait
        -- fsmStFailComputeBladeDiag:DeriveConfig
        -- fsmStFailComputeBladeDiag:DisableServerConnSwA
        -- fsmStFailComputeBladeDiag:DisableServerConnSwB
        -- fsmStFailComputeBladeDiag:EnableServerConnSwA
        -- fsmStFailComputeBladeDiag:EnableServerConnSwB
        -- fsmStFailComputeBladeDiag:EvaluateStatus
        -- fsmStFailComputeBladeDiag:FabricATrafficTestStatus
        -- fsmStFailComputeBladeDiag:FabricBTrafficTestStatus
        -- fsmStFailComputeBladeDiag:GenerateLogWait
        -- fsmStFailComputeBladeDiag:GenerateReport
        -- fsmStFailComputeBladeDiag:HostCatalog
        -- fsmStFailComputeBladeDiag:HostConnect
        -- fsmStFailComputeBladeDiag:HostDisconnect
        -- fsmStFailComputeBladeDiag:HostIdent
        -- fsmStFailComputeBladeDiag:HostInventory
        -- fsmStFailComputeBladeDiag:HostPolicy
        -- fsmStFailComputeBladeDiag:HostServerDiag
        -- fsmStFailComputeBladeDiag:HostServerDiagStatus
        -- fsmStFailComputeBladeDiag:NicConfigLocal
        -- fsmStFailComputeBladeDiag:NicConfigPeer
        -- fsmStFailComputeBladeDiag:NicInventoryLocal
        -- fsmStFailComputeBladeDiag:NicInventoryPeer
        -- fsmStFailComputeBladeDiag:NicPresenceLocal
        -- fsmStFailComputeBladeDiag:NicPresencePeer
        -- fsmStFailComputeBladeDiag:NicUnconfigLocal
        -- fsmStFailComputeBladeDiag:NicUnconfigPeer
        -- fsmStFailComputeBladeDiag:RemoveConfig
        -- fsmStFailComputeBladeDiag:RemoveVMediaLocal
        -- fsmStFailComputeBladeDiag:RemoveVMediaPeer
        -- fsmStFailComputeBladeDiag:RestoreConfigFeLocal
        -- fsmStFailComputeBladeDiag:RestoreConfigFePeer
        -- fsmStFailComputeBladeDiag:SetDiagUser
        -- fsmStFailComputeBladeDiag:SetupVMediaLocal
        -- fsmStFailComputeBladeDiag:SetupVMediaPeer
        -- fsmStFailComputeBladeDiag:SolRedirectDisable
        -- fsmStFailComputeBladeDiag:SolRedirectEnable
        -- fsmStFailComputeBladeDiag:StartFabricATrafficTest
        -- fsmStFailComputeBladeDiag:StartFabricBTrafficTest
        -- fsmStFailComputeBladeDiag:StopVMediaLocal
        -- fsmStFailComputeBladeDiag:StopVMediaPeer
        -- fsmStFailComputeBladeDiag:SwConfigLocal
        -- fsmStFailComputeBladeDiag:SwConfigPeer
        -- fsmStFailComputeBladeDiag:SwUnconfigLocal
        -- fsmStFailComputeBladeDiag:SwUnconfigPeer
        -- fsmStFailComputeBladeDiag:UnconfigUserAccess
        -- fsmStFailComputeBladeDiag:serialDebugConnect
        -- fsmStFailComputeBladeDiag:serialDebugDisconnect
        -- fsmRmtErrComputeBladeDiscover:BiosPostCompletion
        -- fsmRmtErrComputeBladeDiscover:BladeBootPnuos
        -- fsmRmtErrComputeBladeDiscover:BladeBootWait
        -- fsmRmtErrComputeBladeDiscover:BladePowerOn
        -- fsmRmtErrComputeBladeDiscover:BladeReadSmbios
        -- fsmRmtErrComputeBladeDiscover:BmcConfigPnuOS
        -- fsmRmtErrComputeBladeDiscover:BmcInventory
        -- fsmRmtErrComputeBladeDiscover:BmcPreConfigPnuOSLocal
        -- fsmRmtErrComputeBladeDiscover:BmcPreConfigPnuOSPeer
        -- fsmRmtErrComputeBladeDiscover:BmcPresence
        -- fsmRmtErrComputeBladeDiscover:BmcShutdownDiscovered
        -- fsmRmtErrComputeBladeDiscover:CheckPowerAvailability
        -- fsmRmtErrComputeBladeDiscover:ConfigBMCPowerParams
        -- fsmRmtErrComputeBladeDiscover:ConfigFeLocal
        -- fsmRmtErrComputeBladeDiscover:ConfigFePeer
        -- fsmRmtErrComputeBladeDiscover:ConfigFlexFlashScrub
        -- fsmRmtErrComputeBladeDiscover:ConfigUserAccess
        -- fsmRmtErrComputeBladeDiscover:HandlePooling
        -- fsmRmtErrComputeBladeDiscover:NicConfigPnuOSLocal
        -- fsmRmtErrComputeBladeDiscover:NicConfigPnuOSPeer
        -- fsmRmtErrComputeBladeDiscover:NicPresenceLocal
        -- fsmRmtErrComputeBladeDiscover:NicPresencePeer
        -- fsmRmtErrComputeBladeDiscover:NicUnconfigPnuOSLocal
        -- fsmRmtErrComputeBladeDiscover:NicUnconfigPnuOSPeer
        -- fsmRmtErrComputeBladeDiscover:OobStorageInventory
        -- fsmRmtErrComputeBladeDiscover:PnuOSCatalog
        -- fsmRmtErrComputeBladeDiscover:PnuOSIdent
        -- fsmRmtErrComputeBladeDiscover:PnuOSInventory
        -- fsmRmtErrComputeBladeDiscover:PnuOSPolicy
        -- fsmRmtErrComputeBladeDiscover:PnuOSPowerProfiling
        -- fsmRmtErrComputeBladeDiscover:PnuOSScrub
        -- fsmRmtErrComputeBladeDiscover:PnuOSSelfTest
        -- fsmRmtErrComputeBladeDiscover:PowerDeployWait
        -- fsmRmtErrComputeBladeDiscover:PreSanitize
        -- fsmRmtErrComputeBladeDiscover:PrepareKeyFile
        -- fsmRmtErrComputeBladeDiscover:Sanitize
        -- fsmRmtErrComputeBladeDiscover:SendBmcProfilingDone
        -- fsmRmtErrComputeBladeDiscover:SendBmcProfilingInit
        -- fsmRmtErrComputeBladeDiscover:SetupVmediaLocal
        -- fsmRmtErrComputeBladeDiscover:SetupVmediaPeer
        -- fsmRmtErrComputeBladeDiscover:SolRedirectDisable
        -- fsmRmtErrComputeBladeDiscover:SolRedirectEnable
        -- fsmRmtErrComputeBladeDiscover:SwConfigPnuOSLocal
        -- fsmRmtErrComputeBladeDiscover:SwConfigPnuOSPeer
        -- fsmRmtErrComputeBladeDiscover:SwUnconfigPnuOSLocal
        -- fsmRmtErrComputeBladeDiscover:SwUnconfigPnuOSPeer
        -- fsmRmtErrComputeBladeDiscover:TeardownVmediaLocal
        -- fsmRmtErrComputeBladeDiscover:TeardownVmediaPeer
        -- fsmRmtErrComputeBladeDiscover:UnconfigCimcVMedia
        -- fsmRmtErrComputeBladeDiscover:UnconfigExtMgmtGw
        -- fsmRmtErrComputeBladeDiscover:UnconfigExtMgmtRules
        -- fsmRmtErrComputeBladeDiscover:hagConnect
        -- fsmRmtErrComputeBladeDiscover:hagDisconnect
        -- fsmRmtErrComputeBladeDiscover:serialDebugConnect
        -- fsmRmtErrComputeBladeDiscover:serialDebugDisconnect
        -- fsmRmtErrComputeBladeDiag:BiosPostCompletion
        -- fsmRmtErrComputeBladeDiag:BladeBoot
        -- fsmRmtErrComputeBladeDiag:BladeBootWait
        -- fsmRmtErrComputeBladeDiag:BladePowerOn
        -- fsmRmtErrComputeBladeDiag:BladeReadSmbios
        -- fsmRmtErrComputeBladeDiag:BmcConfigPnuOS
        -- fsmRmtErrComputeBladeDiag:BmcInventory
        -- fsmRmtErrComputeBladeDiag:BmcPresence
        -- fsmRmtErrComputeBladeDiag:BmcShutdownDiagCompleted
        -- fsmRmtErrComputeBladeDiag:CleanupServerConnSwA
        -- fsmRmtErrComputeBladeDiag:CleanupServerConnSwB
        -- fsmRmtErrComputeBladeDiag:ConfigFeLocal
        -- fsmRmtErrComputeBladeDiag:ConfigFePeer
        -- fsmRmtErrComputeBladeDiag:ConfigUserAccess
        -- fsmRmtErrComputeBladeDiag:DebugWait
        -- fsmRmtErrComputeBladeDiag:DeriveConfig
        -- fsmRmtErrComputeBladeDiag:DisableServerConnSwA
        -- fsmRmtErrComputeBladeDiag:DisableServerConnSwB
        -- fsmRmtErrComputeBladeDiag:EnableServerConnSwA
        -- fsmRmtErrComputeBladeDiag:EnableServerConnSwB
        -- fsmRmtErrComputeBladeDiag:EvaluateStatus
        -- fsmRmtErrComputeBladeDiag:FabricATrafficTestStatus
        -- fsmRmtErrComputeBladeDiag:FabricBTrafficTestStatus
        -- fsmRmtErrComputeBladeDiag:GenerateLogWait
        -- fsmRmtErrComputeBladeDiag:GenerateReport
        -- fsmRmtErrComputeBladeDiag:HostCatalog
        -- fsmRmtErrComputeBladeDiag:HostConnect
        -- fsmRmtErrComputeBladeDiag:HostDisconnect
        -- fsmRmtErrComputeBladeDiag:HostIdent
        -- fsmRmtErrComputeBladeDiag:HostInventory
        -- fsmRmtErrComputeBladeDiag:HostPolicy
        -- fsmRmtErrComputeBladeDiag:HostServerDiag
        -- fsmRmtErrComputeBladeDiag:HostServerDiagStatus
        -- fsmRmtErrComputeBladeDiag:NicConfigLocal
        -- fsmRmtErrComputeBladeDiag:NicConfigPeer
        -- fsmRmtErrComputeBladeDiag:NicInventoryLocal
        -- fsmRmtErrComputeBladeDiag:NicInventoryPeer
        -- fsmRmtErrComputeBladeDiag:NicPresenceLocal
        -- fsmRmtErrComputeBladeDiag:NicPresencePeer
        -- fsmRmtErrComputeBladeDiag:NicUnconfigLocal
        -- fsmRmtErrComputeBladeDiag:NicUnconfigPeer
        -- fsmRmtErrComputeBladeDiag:RemoveConfig
        -- fsmRmtErrComputeBladeDiag:RemoveVMediaLocal
        -- fsmRmtErrComputeBladeDiag:RemoveVMediaPeer
        -- fsmRmtErrComputeBladeDiag:RestoreConfigFeLocal
        -- fsmRmtErrComputeBladeDiag:RestoreConfigFePeer
        -- fsmRmtErrComputeBladeDiag:SetDiagUser
        -- fsmRmtErrComputeBladeDiag:SetupVMediaLocal
        -- fsmRmtErrComputeBladeDiag:SetupVMediaPeer
        -- fsmRmtErrComputeBladeDiag:SolRedirectDisable
        -- fsmRmtErrComputeBladeDiag:SolRedirectEnable
        -- fsmRmtErrComputeBladeDiag:StartFabricATrafficTest
        -- fsmRmtErrComputeBladeDiag:StartFabricBTrafficTest
        -- fsmRmtErrComputeBladeDiag:StopVMediaLocal
        -- fsmRmtErrComputeBladeDiag:StopVMediaPeer
        -- fsmRmtErrComputeBladeDiag:SwConfigLocal
        -- fsmRmtErrComputeBladeDiag:SwConfigPeer
        -- fsmRmtErrComputeBladeDiag:SwUnconfigLocal
        -- fsmRmtErrComputeBladeDiag:SwUnconfigPeer
        -- fsmRmtErrComputeBladeDiag:UnconfigUserAccess
        -- fsmRmtErrComputeBladeDiag:serialDebugConnect
        -- fsmRmtErrComputeBladeDiag:serialDebugDisconnect
        -- fsmFailComputeBladeDiscover
        -- fsmFailComputeBladeDiag

-- storage:System
    -- storage-ep/system
        -- fsmStFailStorageSystemSync:Execute
        -- fsmRmtErrStorageSystemSync:Execute
        -- fsmFailStorageSystemSync

-- extvmm:Provider
    -- sys/extvm-mgmt/vm-[name]
        -- fsmStFailExtvmmProviderConfig:GetVersion
        -- fsmStFailExtvmmProviderConfig:SetLocal
        -- fsmStFailExtvmmProviderConfig:SetPeer
        -- fsmRmtErrExtvmmProviderConfig:GetVersion
        -- fsmRmtErrExtvmmProviderConfig:SetLocal
        -- fsmRmtErrExtvmmProviderConfig:SetPeer
        -- fsmFailExtvmmProviderConfig

-- sd:AppInstSettingsTask
    -- sys-secsvc/slot-[slotId]/app-inst-[appInstId]/app-inst-sett
        -- fsmStFailSdAppInstSettingsTaskSendAppInstSettings:UpdateSettings
        -- fsmRmtErrSdAppInstSettingsTaskSendAppInstSettings:UpdateSettings
        -- fsmFailSdAppInstSettingsTaskSendAppInstSettings

-- comm:Snmp
    -- sys/svc-ext/snmp-svc
        -- fltCommSnmpSyscontactEmpty

-- fabric:PinTarget
        -- fltFabricPinTargetDown

-- storage:LocalDisk
    -- sys/chassis-[id]/blade-[slotId]/board/storage-[type]-[id]/disk-[id]
    -- sys/rack-unit-[id]/board/storage-[type]-[id]/disk-[id]
        -- fltStorageLocalDiskInoperable
        -- fltStorageLocalDiskDegraded
        -- fltStorageLocalDiskRebuildFailed
        -- fltStorageLocalDiskCopybackFailed
        -- fltStorageLocalDiskMissing

-- sw:EthMon
    -- sys/switch-[id]/lanmon-eth/mon-[name]
        -- fsmStFailSwEthMonDeploy:UpdateEthMon
        -- fsmRmtErrSwEthMonDeploy:UpdateEthMon
        -- fsmFailSwEthMonDeploy

-- extmgmt:ArpTargets
    -- sys/extmgmt-intf-monitor-policy/arp-target-policy
        -- fltExtmgmtArpTargetsArpTargetsNotValid

-- sm:LicenseFile
    -- sec-svc/lic-[name]
        -- fsmStFailSmLicenseFileDelete:Local
        -- fsmRmtErrSmLicenseFileDelete:Local
        -- fsmFailSmLicenseFileDelete

-- callhome:Ep
    -- call-home
        -- fltCallhomeEpNoSnmpPolicyForCallhome
        -- fsmStFailCallhomeEpConfigCallhome:SetLocal
        -- fsmStFailCallhomeEpConfigCallhome:SetPeer
        -- fsmRmtErrCallhomeEpConfigCallhome:SetLocal
        -- fsmRmtErrCallhomeEpConfigCallhome:SetPeer
        -- fsmFailCallhomeEpConfigCallhome

-- fabric:PIoEp
        -- fltFabricPIoEpErrorMisconfigured

-- extvmm:VMNDRef
    -- fabric/lan/vm-network-sets/vm-network-[name]/vm-network-def-ref[name]
        -- fltExtvmmVMNDRefVmNetworkReferenceIncorrect

-- aaa:UserLocale
    -- sys/ldap-ext/ldapgroup-[name]/locale-[name]
    -- sys/user-ext/remoteuser-[name]/locale-[name]
    -- sys/user-ext/user-[name]/locale-[name]
        -- fltAaaUserLocaleUserLocaleNotDeployed

-- aaa:User
    -- sys/user-ext/user-[name]
        -- fltAaaUserLocalUserNotDeployed

-- fabric:LanCloud
    -- fabric/lan
        -- fsmStFailFabricLanCloudSwitchMode:SwConfigLocal
        -- fsmStFailFabricLanCloudSwitchMode:SwConfigPeer
        -- fsmRmtErrFabricLanCloudSwitchMode:SwConfigLocal
        -- fsmRmtErrFabricLanCloudSwitchMode:SwConfigPeer
        -- fsmFailFabricLanCloudSwitchMode

-- storage:Item
    -- sys/switch-[id]/stor-part-[name]
        -- fltStorageItemCapacityExceeded
        -- fltStorageItemCapacityWarning
        -- fltStorageItemFilesystemIssues

-- sw:UtilityDomain
    -- sys/switch-[id]/utility-eth
        -- fsmStFailSwUtilityDomainDeploy:UpdateConnectivity
        -- fsmRmtErrSwUtilityDomainDeploy:UpdateConnectivity
        -- fsmFailSwUtilityDomainDeploy

-- sm:ExternalPortLink
    -- sec-svc/ld-[name]/ext-portlink-[name]
        -- fltSmExternalPortLinkConflictConfig

-- mgmt:Backup
    -- sys/backup-[hostname]
        -- fsmStFailMgmtBackupBackup:backupLocal
        -- fsmStFailMgmtBackupBackup:upload
        -- fsmRmtErrMgmtBackupBackup:backupLocal
        -- fsmRmtErrMgmtBackupBackup:upload
        -- fsmFailMgmtBackupBackup

-- ipsec:Ep
    -- sys/ipsec-ext
        -- fsmStFailIpsecEpUpdateEp:ApplyConfig
        -- fsmRmtErrIpsecEpUpdateEp:ApplyConfig
        -- fsmFailIpsecEpUpdateEp

-- equipment:SwitchIOCard
    -- sys/chassis-[id]/sw-slot-[id]
        -- fltEquipmentSwitchIOCardRemoved
        -- fltEquipmentSwitchIOCardThermalProblem
        -- fltEquipmentSwitchIOCardThermalThresholdNonCritical
        -- fltEquipmentSwitchIOCardThermalThresholdCritical
        -- fltEquipmentSwitchIOCardThermalThresholdNonRecoverable
        -- fltEquipmentSwitchIOCardIdentity
        -- fltEquipmentSwitchIOCardCpuThermalThresholdCritical

-- sm:Error
    -- sec-svc/slot-[slotId]/app-inst-[appName]/error-[moKey]
    -- sec-svc/slot-[slotId]/app-inst-[appName]-[identifier]/error-[moKey]
        -- fltSmErrorError0
        -- fltSmErrorError1

-- fabric:PooledVlan
    -- fabric/lan/[id]/net-group-[name]/net-[name]
    -- fabric/lan/net-group-[name]/net-[name]
        -- fltFabricPooledVlanNamedVlanUnresolved

-- ident:MetaSystem
    -- metaverse/metasys
        -- fsmStFailIdentMetaSystemSync:Execute
        -- fsmStFailIdentMetaSystemSync:Ping
        -- fsmStFailIdentMetaSystemFprcUnivSync:Execute
        -- fsmRmtErrIdentMetaSystemSync:Execute
        -- fsmRmtErrIdentMetaSystemSync:Ping
        -- fsmRmtErrIdentMetaSystemFprcUnivSync:Execute
        -- fsmFailIdentMetaSystemSync
        -- fsmFailIdentMetaSystemFprcUnivSync

-- sysdebug:Core
    -- sys/corefiles/file-[name]|[switchId]
        -- fsmStFailSysdebugCoreDownload:CopyPrimary
        -- fsmStFailSysdebugCoreDownload:CopySub
        -- fsmStFailSysdebugCoreDownload:DeletePrimary
        -- fsmStFailSysdebugCoreDownload:DeleteSub
        -- fsmRmtErrSysdebugCoreDownload:CopyPrimary
        -- fsmRmtErrSysdebugCoreDownload:CopySub
        -- fsmRmtErrSysdebugCoreDownload:DeletePrimary
        -- fsmRmtErrSysdebugCoreDownload:DeleteSub
        -- fsmFailSysdebugCoreDownload

-- sd:UpgradeTask
    -- sys-secsvc/slot-[slotId]/app-inst-[appInstId]/upgrade-task
        -- fsmStFailSdUpgradeTaskStopUpgradeStartApp:StartApp
        -- fsmStFailSdUpgradeTaskStopUpgradeStartApp:StopApp
        -- fsmStFailSdUpgradeTaskStopUpgradeStartApp:UpgradeApp
        -- fsmStFailSdUpgradeTaskStopUpgradeStartApp:WaitForBladeReboot
        -- fsmStFailSdUpgradeTaskStopUpgradeStartApp:WaitForStopApp
        -- fsmStFailSdUpgradeTaskStopUpgradeStartApp:WaitForUpgradeApp
        -- fsmRmtErrSdUpgradeTaskStopUpgradeStartApp:StartApp
        -- fsmRmtErrSdUpgradeTaskStopUpgradeStartApp:StopApp
        -- fsmRmtErrSdUpgradeTaskStopUpgradeStartApp:UpgradeApp
        -- fsmRmtErrSdUpgradeTaskStopUpgradeStartApp:WaitForBladeReboot
        -- fsmRmtErrSdUpgradeTaskStopUpgradeStartApp:WaitForStopApp
        -- fsmRmtErrSdUpgradeTaskStopUpgradeStartApp:WaitForUpgradeApp
        -- fsmFailSdUpgradeTaskStopUpgradeStartApp

-- firmware:AutoSyncPolicy
    -- org-[name]/fw-auto-sync
        -- fltFirmwareAutoSyncPolicyDefaultHostPackageMissing

-- mgmt:If
    -- sys/chassis-[id]/blade-[slotId]/adaptor-[id]/host-eth-[id]/if-[id]
    -- sys/rack-unit-[id]/adaptor-[id]/host-eth-[id]/if-[id]
    -- sys/chassis-[id]/blade-[slotId]/adaptor-[id]/mgmt/if-[id]
    -- sys/rack-unit-[id]/adaptor-[id]/mgmt/if-[id]
    -- sys/chassis-[id]/blade-[slotId]/ext-board-[id]/boardController/mgmt/if-[id]
    -- sys/rack-unit-[id]/ext-board-[id]/boardController/mgmt/if-[id]
    -- sys/chassis-[id]/blade-[slotId]/boardController/mgmt/if-[id]
    -- sys/rack-unit-[id]/boardController/mgmt/if-[id]
    -- sys/chassis-[id]/blade-[slotId]/ext-board-[id]/mgmt/if-[id]
    -- sys/rack-unit-[id]/ext-board-[id]/mgmt/if-[id]
    -- sys/chassis-[id]/blade-[slotId]/mgmt/if-[id]
    -- sys/rack-unit-[id]/mgmt/if-[id]
    -- sys/fex-[id]/mgmt/if-[id]
    -- sys/chassis-[id]/slot-[id]/mgmt/if-[id]
    -- sys/fex-[id]/slot-[id]/mgmt/if-[id]
    -- sys/chassis-[id]/sw-slot-[id]/mgmt/if-[id]
    -- sys/switch-[id]/mgmt/if-[id]
    -- sys/mgmt/if-[id]
        -- fltMgmtIfMisConnect
        -- fltMgmtIfMissing
        -- fltMgmtIfNew
        -- fsmStFailMgmtIfSwMgmtOobIfConfig:Switch
        -- fsmStFailMgmtIfSwMgmtInbandIfConfig:Switch
        -- fsmStFailMgmtIfVirtualIfConfig:Local
        -- fsmStFailMgmtIfVirtualIfConfig:Remote
        -- fsmStFailMgmtIfEnableVip:Local
        -- fsmStFailMgmtIfDisableVip:Peer
        -- fsmStFailMgmtIfEnableHA:Local
        -- fsmRmtErrMgmtIfSwMgmtOobIfConfig:Switch
        -- fsmRmtErrMgmtIfSwMgmtInbandIfConfig:Switch
        -- fsmRmtErrMgmtIfVirtualIfConfig:Local
        -- fsmRmtErrMgmtIfVirtualIfConfig:Remote
        -- fsmRmtErrMgmtIfEnableVip:Local
        -- fsmRmtErrMgmtIfDisableVip:Peer
        -- fsmRmtErrMgmtIfEnableHA:Local
        -- fsmFailMgmtIfSwMgmtOobIfConfig
        -- fsmFailMgmtIfSwMgmtInbandIfConfig
        -- fsmFailMgmtIfVirtualIfConfig
        -- fsmFailMgmtIfEnableVip
        -- fsmFailMgmtIfDisableVip
        -- fsmFailMgmtIfEnableHA

-- nfs:MountDef
    -- nfs-ep/nfs-mount-def-[name]
        -- fsmStFailNfsMountDefReportNfsMountSuspend:Report
        -- fsmRmtErrNfsMountDefReportNfsMountSuspend:Report
        -- fsmFailNfsMountDefReportNfsMountSuspend

-- sysdebug:ManualCoreFileExportTarget
    -- sys/corefiles/file-[name]|[switchId]/export-to-[hostname]
        -- fsmStFailSysdebugManualCoreFileExportTargetExport:Execute
        -- fsmRmtErrSysdebugManualCoreFileExportTargetExport:Execute
        -- fsmFailSysdebugManualCoreFileExportTargetExport

-- memory:BufferUnit
    -- sys/chassis-[id]/blade-[slotId]/board/sensor-unit-[id]
    -- sys/rack-unit-[id]/board/sensor-unit-[id]
        -- fltMemoryBufferUnitThermalThresholdNonCritical
        -- fltMemoryBufferUnitThermalThresholdCritical
        -- fltMemoryBufferUnitThermalThresholdNonRecoverable

-- license:Downloader
    -- sys/license/dnld-[fileName]
        -- fsmStFailLicenseDownloaderDownload:CopyRemote
        -- fsmStFailLicenseDownloaderDownload:DeleteLocal
        -- fsmStFailLicenseDownloaderDownload:DeleteRemote
        -- fsmStFailLicenseDownloaderDownload:Local
        -- fsmStFailLicenseDownloaderDownload:ValidateLocal
        -- fsmStFailLicenseDownloaderDownload:ValidateRemote
        -- fsmRmtErrLicenseDownloaderDownload:CopyRemote
        -- fsmRmtErrLicenseDownloaderDownload:DeleteLocal
        -- fsmRmtErrLicenseDownloaderDownload:DeleteRemote
        -- fsmRmtErrLicenseDownloaderDownload:Local
        -- fsmRmtErrLicenseDownloaderDownload:ValidateLocal
        -- fsmRmtErrLicenseDownloaderDownload:ValidateRemote
        -- fsmFailLicenseDownloaderDownload

-- sm:UnsignedCspLicense
    -- sec-svc/unsigned-csp-license
        -- fltSmUnsignedCspLicenseUnsignedCSPLicenseInstalled
        -- fsmStFailSmUnsignedCspLicenseDeploy:OnBlades
        -- fsmStFailSmUnsignedCspLicenseDeploy:OnChassis
        -- fsmStFailSmUnsignedCspLicenseDeploy:RebootSystem
        -- fsmStFailSmUnsignedCspLicenseDeploy:WaitForCompletion
        -- fsmStFailSmUnsignedCspLicenseDeploy:WaitForReady
        -- fsmRmtErrSmUnsignedCspLicenseDeploy:OnBlades
        -- fsmRmtErrSmUnsignedCspLicenseDeploy:OnChassis
        -- fsmRmtErrSmUnsignedCspLicenseDeploy:RebootSystem
        -- fsmRmtErrSmUnsignedCspLicenseDeploy:WaitForCompletion
        -- fsmRmtErrSmUnsignedCspLicenseDeploy:WaitForReady
        -- fsmFailSmUnsignedCspLicenseDeploy

-- fabric:LanPinGroup
    -- fabric/lan/lan-pin-group-[name]
        -- fltFabricLanPinGroupEmpty

-- sw:ExtUtility
    -- sys/switch-[id]/ext
        -- fsmStFailSwExtUtilityConfPortBreakout:ConfigSwA
        -- fsmStFailSwExtUtilityConfPortBreakout:ConfigSwB
        -- fsmStFailSwExtUtilityConfPortBreakout:PortInventorySwA
        -- fsmStFailSwExtUtilityConfPortBreakout:PortInventorySwB
        -- fsmStFailSwExtUtilityConfPortBreakout:VerifyBreakoutConfig
        -- fsmRmtErrSwExtUtilityConfPortBreakout:ConfigSwA
        -- fsmRmtErrSwExtUtilityConfPortBreakout:ConfigSwB
        -- fsmRmtErrSwExtUtilityConfPortBreakout:PortInventorySwA
        -- fsmRmtErrSwExtUtilityConfPortBreakout:PortInventorySwB
        -- fsmRmtErrSwExtUtilityConfPortBreakout:VerifyBreakoutConfig
        -- fsmFailSwExtUtilityConfPortBreakout

-- license:File
    -- sys/license/file-[scope]:[id]
        -- fsmStFailLicenseFileInstall:Local
        -- fsmStFailLicenseFileInstall:Remote
        -- fsmStFailLicenseFileClear:Local
        -- fsmStFailLicenseFileClear:Remote
        -- fsmRmtErrLicenseFileInstall:Local
        -- fsmRmtErrLicenseFileInstall:Remote
        -- fsmRmtErrLicenseFileClear:Local
        -- fsmRmtErrLicenseFileClear:Remote
        -- fsmFailLicenseFileInstall
        -- fsmFailLicenseFileClear

-- comm:Telemetry
    -- sys/svc-ext/telemetry
        -- fltCommTelemetryTelemetryRegistrationFailed
        -- fltCommTelemetryTelemetryUnregistrationFailed
        -- fltCommTelemetryTelemetryGetDataFailed
        -- fltCommTelemetryTelemetrySendDataFailed
        -- fsmStFailCommTelemetryDataExchSeq:GetTelemetryData
        -- fsmStFailCommTelemetryDataExchSeq:RegisterforTelemetry
        -- fsmStFailCommTelemetryDataExchSeq:SendTelemetryData
        -- fsmStFailCommTelemetryEnableDisableTelemetry:SendChassisConfig
        -- fsmStFailCommTelemetryEnableDisableTelemetry:UnRegister
        -- fsmRmtErrCommTelemetryDataExchSeq:GetTelemetryData
        -- fsmRmtErrCommTelemetryDataExchSeq:RegisterforTelemetry
        -- fsmRmtErrCommTelemetryDataExchSeq:SendTelemetryData
        -- fsmRmtErrCommTelemetryEnableDisableTelemetry:SendChassisConfig
        -- fsmRmtErrCommTelemetryEnableDisableTelemetry:UnRegister
        -- fsmFailCommTelemetryDataExchSeq
        -- fsmFailCommTelemetryEnableDisableTelemetry

-- equipment:Fan
    -- sys/rack-unit-[id]/fan-module-[tray]-[id]/fan-[id]
    -- sys/chassis-[id]/fan-module-[tray]-[id]/fan-[id]
    -- sys/switch-[id]/fan-module-[tray]-[id]/fan-[id]
    -- sys/fex-[id]/fan-[id]
    -- sys/switch-[id]/fan-[id]
        -- fltEquipmentFanDegraded
        -- fltEquipmentFanInoperable
        -- fltEquipmentFanPerfThresholdNonCritical
        -- fltEquipmentFanPerfThresholdCritical
        -- fltEquipmentFanPerfThresholdNonRecoverable
        -- fltEquipmentFanMissing
        -- fltEquipmentFanPerfThresholdLowerNonRecoverable

-- fabric:ExternalPc
        -- fltFabricExternalPcDown

-- compute:IOHub
    -- sys/chassis-[id]/blade-[slotId]/board/iohub
    -- sys/rack-unit-[id]/board/iohub
        -- fltComputeIOHubThermalNonCritical
        -- fltComputeIOHubThermalThresholdCritical
        -- fltComputeIOHubThermalThresholdNonRecoverable

-- ipsec:Connection
    -- sys/ipsec-ext/conn-[name]
        -- fltIpsecConnectionIpsecConnInvalidKey
        -- fltIpsecConnectionIpsecConnInvalidCert

-- fabric:EthLanPc
    -- fabric/lan/[id]/pc-[portId]
        -- fltFabricEthLanPcMissingPrimaryVlan
        -- fltFabricEthLanPcOverlapping-vlan

-- compute:RackUnit
    -- sys/rack-unit-[id]
        -- fsmStFailComputeRackUnitDiscover:BiosPostCompletion
        -- fsmStFailComputeRackUnitDiscover:BladePowerOff
        -- fsmStFailComputeRackUnitDiscover:BmcConfigPnuOS
        -- fsmStFailComputeRackUnitDiscover:BmcConfigureConnLocal
        -- fsmStFailComputeRackUnitDiscover:BmcConfigureConnPeer
        -- fsmStFailComputeRackUnitDiscover:BmcInventory
        -- fsmStFailComputeRackUnitDiscover:BmcPreconfigPnuOSLocal
        -- fsmStFailComputeRackUnitDiscover:BmcPreconfigPnuOSPeer
        -- fsmStFailComputeRackUnitDiscover:BmcPresence
        -- fsmStFailComputeRackUnitDiscover:BmcShutdownDiscovered
        -- fsmStFailComputeRackUnitDiscover:BmcUnconfigPnuOS
        -- fsmStFailComputeRackUnitDiscover:BootPnuos
        -- fsmStFailComputeRackUnitDiscover:BootWait
        -- fsmStFailComputeRackUnitDiscover:ConfigDiscoveryMode
        -- fsmStFailComputeRackUnitDiscover:ConfigFlexFlashScrub
        -- fsmStFailComputeRackUnitDiscover:ConfigNivMode
        -- fsmStFailComputeRackUnitDiscover:ConfigUserAccess
        -- fsmStFailComputeRackUnitDiscover:HandlePooling
        -- fsmStFailComputeRackUnitDiscover:NicConfigPnuOSLocal
        -- fsmStFailComputeRackUnitDiscover:NicConfigPnuOSPeer
        -- fsmStFailComputeRackUnitDiscover:NicInventoryLocal
        -- fsmStFailComputeRackUnitDiscover:NicInventoryPeer
        -- fsmStFailComputeRackUnitDiscover:OobStorageInventory
        -- fsmStFailComputeRackUnitDiscover:PnuOSCatalog
        -- fsmStFailComputeRackUnitDiscover:PnuOSConnStatus
        -- fsmStFailComputeRackUnitDiscover:PnuOSConnectivity
        -- fsmStFailComputeRackUnitDiscover:PnuOSIdent
        -- fsmStFailComputeRackUnitDiscover:PnuOSInventory
        -- fsmStFailComputeRackUnitDiscover:PnuOSPolicy
        -- fsmStFailComputeRackUnitDiscover:PnuOSScrub
        -- fsmStFailComputeRackUnitDiscover:PnuOSSelfTest
        -- fsmStFailComputeRackUnitDiscover:PreSanitize
        -- fsmStFailComputeRackUnitDiscover:ReadSmbios
        -- fsmStFailComputeRackUnitDiscover:Sanitize
        -- fsmStFailComputeRackUnitDiscover:SolRedirectDisable
        -- fsmStFailComputeRackUnitDiscover:SolRedirectEnable
        -- fsmStFailComputeRackUnitDiscover:SwConfigPnuOSLocal
        -- fsmStFailComputeRackUnitDiscover:SwConfigPnuOSPeer
        -- fsmStFailComputeRackUnitDiscover:SwConfigPortNivLocal
        -- fsmStFailComputeRackUnitDiscover:SwConfigPortNivPeer
        -- fsmStFailComputeRackUnitDiscover:SwConfigureConnLocal
        -- fsmStFailComputeRackUnitDiscover:SwConfigureConnPeer
        -- fsmStFailComputeRackUnitDiscover:SwPnuOSConnectivityLocal
        -- fsmStFailComputeRackUnitDiscover:SwPnuOSConnectivityPeer
        -- fsmStFailComputeRackUnitDiscover:SwUnconfigPortNivLocal
        -- fsmStFailComputeRackUnitDiscover:SwUnconfigPortNivPeer
        -- fsmStFailComputeRackUnitDiscover:UnconfigCimcVMedia
        -- fsmStFailComputeRackUnitDiscover:UnconfigExtMgmtGw
        -- fsmStFailComputeRackUnitDiscover:UnconfigExtMgmtRules
        -- fsmStFailComputeRackUnitDiscover:hagConnect
        -- fsmStFailComputeRackUnitDiscover:hagDisconnect
        -- fsmStFailComputeRackUnitDiscover:serialDebugConnect
        -- fsmStFailComputeRackUnitDiscover:serialDebugDisconnect
        -- fsmStFailComputeRackUnitDiscover:waitForConnReady
        -- fsmStFailComputeRackUnitOffline:CleanupLocal
        -- fsmStFailComputeRackUnitOffline:CleanupPeer
        -- fsmStFailComputeRackUnitOffline:SwUnconfigureLocal
        -- fsmStFailComputeRackUnitOffline:SwUnconfigurePeer
        -- fsmStFailComputeRackUnitAdapterReset:DeassertResetBypass
        -- fsmStFailComputeRackUnitAdapterReset:PowerCycle
        -- fsmStFailComputeRackUnitAdapterReset:PreSanitize
        -- fsmStFailComputeRackUnitAdapterReset:Sanitize
        -- fsmStFailComputeRackUnitCreateDhcpEntry:ExecuteLocal
        -- fsmStFailComputeRackUnitCreateDhcpEntry:ExecutePeer
        -- fsmRmtErrComputeRackUnitDiscover:BiosPostCompletion
        -- fsmRmtErrComputeRackUnitDiscover:BladePowerOff
        -- fsmRmtErrComputeRackUnitDiscover:BmcConfigPnuOS
        -- fsmRmtErrComputeRackUnitDiscover:BmcConfigureConnLocal
        -- fsmRmtErrComputeRackUnitDiscover:BmcConfigureConnPeer
        -- fsmRmtErrComputeRackUnitDiscover:BmcInventory
        -- fsmRmtErrComputeRackUnitDiscover:BmcPreconfigPnuOSLocal
        -- fsmRmtErrComputeRackUnitDiscover:BmcPreconfigPnuOSPeer
        -- fsmRmtErrComputeRackUnitDiscover:BmcPresence
        -- fsmRmtErrComputeRackUnitDiscover:BmcShutdownDiscovered
        -- fsmRmtErrComputeRackUnitDiscover:BmcUnconfigPnuOS
        -- fsmRmtErrComputeRackUnitDiscover:BootPnuos
        -- fsmRmtErrComputeRackUnitDiscover:BootWait
        -- fsmRmtErrComputeRackUnitDiscover:ConfigDiscoveryMode
        -- fsmRmtErrComputeRackUnitDiscover:ConfigFlexFlashScrub
        -- fsmRmtErrComputeRackUnitDiscover:ConfigNivMode
        -- fsmRmtErrComputeRackUnitDiscover:ConfigUserAccess
        -- fsmRmtErrComputeRackUnitDiscover:HandlePooling
        -- fsmRmtErrComputeRackUnitDiscover:NicConfigPnuOSLocal
        -- fsmRmtErrComputeRackUnitDiscover:NicConfigPnuOSPeer
        -- fsmRmtErrComputeRackUnitDiscover:NicInventoryLocal
        -- fsmRmtErrComputeRackUnitDiscover:NicInventoryPeer
        -- fsmRmtErrComputeRackUnitDiscover:OobStorageInventory
        -- fsmRmtErrComputeRackUnitDiscover:PnuOSCatalog
        -- fsmRmtErrComputeRackUnitDiscover:PnuOSConnStatus
        -- fsmRmtErrComputeRackUnitDiscover:PnuOSConnectivity
        -- fsmRmtErrComputeRackUnitDiscover:PnuOSIdent
        -- fsmRmtErrComputeRackUnitDiscover:PnuOSInventory
        -- fsmRmtErrComputeRackUnitDiscover:PnuOSPolicy
        -- fsmRmtErrComputeRackUnitDiscover:PnuOSScrub
        -- fsmRmtErrComputeRackUnitDiscover:PnuOSSelfTest
        -- fsmRmtErrComputeRackUnitDiscover:PreSanitize
        -- fsmRmtErrComputeRackUnitDiscover:ReadSmbios
        -- fsmRmtErrComputeRackUnitDiscover:Sanitize
        -- fsmRmtErrComputeRackUnitDiscover:SolRedirectDisable
        -- fsmRmtErrComputeRackUnitDiscover:SolRedirectEnable
        -- fsmRmtErrComputeRackUnitDiscover:SwConfigPnuOSLocal
        -- fsmRmtErrComputeRackUnitDiscover:SwConfigPnuOSPeer
        -- fsmRmtErrComputeRackUnitDiscover:SwConfigPortNivLocal
        -- fsmRmtErrComputeRackUnitDiscover:SwConfigPortNivPeer
        -- fsmRmtErrComputeRackUnitDiscover:SwConfigureConnLocal
        -- fsmRmtErrComputeRackUnitDiscover:SwConfigureConnPeer
        -- fsmRmtErrComputeRackUnitDiscover:SwPnuOSConnectivityLocal
        -- fsmRmtErrComputeRackUnitDiscover:SwPnuOSConnectivityPeer
        -- fsmRmtErrComputeRackUnitDiscover:SwUnconfigPortNivLocal
        -- fsmRmtErrComputeRackUnitDiscover:SwUnconfigPortNivPeer
        -- fsmRmtErrComputeRackUnitDiscover:UnconfigCimcVMedia
        -- fsmRmtErrComputeRackUnitDiscover:UnconfigExtMgmtGw
        -- fsmRmtErrComputeRackUnitDiscover:UnconfigExtMgmtRules
        -- fsmRmtErrComputeRackUnitDiscover:hagConnect
        -- fsmRmtErrComputeRackUnitDiscover:hagDisconnect
        -- fsmRmtErrComputeRackUnitDiscover:serialDebugConnect
        -- fsmRmtErrComputeRackUnitDiscover:serialDebugDisconnect
        -- fsmRmtErrComputeRackUnitDiscover:waitForConnReady
        -- fsmRmtErrComputeRackUnitOffline:CleanupLocal
        -- fsmRmtErrComputeRackUnitOffline:CleanupPeer
        -- fsmRmtErrComputeRackUnitOffline:SwUnconfigureLocal
        -- fsmRmtErrComputeRackUnitOffline:SwUnconfigurePeer
        -- fsmRmtErrComputeRackUnitAdapterReset:DeassertResetBypass
        -- fsmRmtErrComputeRackUnitAdapterReset:PowerCycle
        -- fsmRmtErrComputeRackUnitAdapterReset:PreSanitize
        -- fsmRmtErrComputeRackUnitAdapterReset:Sanitize
        -- fsmRmtErrComputeRackUnitCreateDhcpEntry:ExecuteLocal
        -- fsmRmtErrComputeRackUnitCreateDhcpEntry:ExecutePeer
        -- fsmFailComputeRackUnitDiscover
        -- fsmFailComputeRackUnitOffline
        -- fsmFailComputeRackUnitAdapterReset
        -- fsmFailComputeRackUnitCreateDhcpEntry

-- sysfile:Mutation
    -- sys/corefiles/file-[name]|[switchId]/mutation
    -- sys/corefiles/mutation
        -- fsmStFailSysfileMutationSingle:Execute
        -- fsmStFailSysfileMutationGlobal:Local
        -- fsmStFailSysfileMutationGlobal:Peer
        -- fsmRmtErrSysfileMutationSingle:Execute
        -- fsmRmtErrSysfileMutationGlobal:Local
        -- fsmRmtErrSysfileMutationGlobal:Peer
        -- fsmFailSysfileMutationSingle
        -- fsmFailSysfileMutationGlobal

-- mgmt:Connection
    -- sys/chassis-[id]/blade-[slotId]/adaptor-[id]/mgmt/mgmt-connection-[type]
    -- sys/rack-unit-[id]/adaptor-[id]/mgmt/mgmt-connection-[type]
    -- sys/chassis-[id]/blade-[slotId]/ext-board-[id]/boardController/mgmt/mgmt-connection-[type]
    -- sys/rack-unit-[id]/ext-board-[id]/boardController/mgmt/mgmt-connection-[type]
    -- sys/chassis-[id]/blade-[slotId]/boardController/mgmt/mgmt-connection-[type]
    -- sys/rack-unit-[id]/boardController/mgmt/mgmt-connection-[type]
    -- sys/chassis-[id]/blade-[slotId]/ext-board-[id]/mgmt/mgmt-connection-[type]
    -- sys/rack-unit-[id]/ext-board-[id]/mgmt/mgmt-connection-[type]
    -- sys/chassis-[id]/blade-[slotId]/mgmt/mgmt-connection-[type]
    -- sys/rack-unit-[id]/mgmt/mgmt-connection-[type]
    -- sys/fex-[id]/mgmt/mgmt-connection-[type]
    -- sys/chassis-[id]/slot-[id]/mgmt/mgmt-connection-[type]
    -- sys/fex-[id]/slot-[id]/mgmt/mgmt-connection-[type]
    -- sys/chassis-[id]/sw-slot-[id]/mgmt/mgmt-connection-[type]
    -- sys/switch-[id]/mgmt/mgmt-connection-[type]
    -- sys/mgmt/mgmt-connection-[type]
        -- fltMgmtConnectionDisabled
        -- fltMgmtConnectionUnused
        -- fltMgmtConnectionUnsupportedConnectivity

-- aaa:Org
    -- sys/user-ext/locale-[name]/org-[name]
        -- fltAaaOrgLocaleOrgNotPresent

-- adaptor:UnitExtn
    -- sys/chassis-[id]/blade-[slotId]/adaptor-[id]/adaptor-extn-[id]
    -- sys/rack-unit-[id]/adaptor-[id]/adaptor-extn-[id]
        -- fltAdaptorUnitExtnUnidentifiable-fru
        -- fltAdaptorUnitExtnMissing

-- aaa:Role
    -- sys/user-ext/role-[name]
        -- fltAaaRoleRoleNotDeployed

-- vnic:EtherIf
    -- fabric/lan/network-sets/fabric-network-[name]/fabric-network-def-[name]/vm-network-def-[name]/if-[name]
    -- org-[name]/tier-[name]/ls-[name]/if-[name]
    -- org-[name]/ls-[name]/if-[name]
    -- org-[name]/tier-[name]/ls-[name]/ether-[name]/if-[name]
    -- org-[name]/ls-[name]/ether-[name]/if-[name]
    -- org-[name]/lan-conn-pol-[name]/ether-[name]/if-[name]
    -- org-[name]/tier-[name]/ls-[name]/ipc-[name]/if-[name]
    -- org-[name]/ls-[name]/ipc-[name]/if-[name]
    -- org-[name]/lan-conn-templ-[name]/if-[name]
    -- fabric/lan/profiles/vnic-[name]/if-[name]
        -- fltVnicEtherIfVlanAccessFault
        -- fltVnicEtherIfVlanUnresolvable
        -- fltVnicEtherIfInvalidVlan
        -- fltVnicEtherIfRemoteVlanUnresolvable

-- comm:Sshc
    -- sys/svc-ext/sshc-svc
        -- fltCommSshcSshc3desUsageNotRecommended

-- processor:Unit
    -- sys/chassis-[id]/blade-[slotId]/board/cpu-[id]
    -- sys/rack-unit-[id]/board/cpu-[id]
        -- fltProcessorUnitInoperable
        -- fltProcessorUnitThermalNonCritical
        -- fltProcessorUnitThermalThresholdCritical
        -- fltProcessorUnitThermalThresholdNonRecoverable
        -- fltProcessorUnitVoltageThresholdNonCritical
        -- fltProcessorUnitVoltageThresholdCritical
        -- fltProcessorUnitVoltageThresholdNonRecoverable
        -- fltProcessorUnitIdentity-unestablishable
        -- fltProcessorUnitDisabled

-- ls:ComputeBinding
    -- org-[name]/tier-[name]/ls-[name]/
    -- org-[name]/ls-[name]/
        -- fltLsComputeBindingAssignmentRequirementsNotMet

-- aaa:UserEp
    -- sys/user-ext
        -- fltAaaUserEpPasswordEncryptionKeyNotSet
        -- fsmStFailAaaUserEpUpdateUserEp:SetUserLocal
        -- fsmStFailAaaUserEpUpdateUserEp:SetUserPeer
        -- fsmRmtErrAaaUserEpUpdateUserEp:SetUserLocal
        -- fsmRmtErrAaaUserEpUpdateUserEp:SetUserPeer
        -- fsmFailAaaUserEpUpdateUserEp

-- memory:Unit
    -- sys/chassis-[id]/blade-[slotId]/board/memarray-[id]/mem-[id]
    -- sys/rack-unit-[id]/board/memarray-[id]/mem-[id]
        -- fltMemoryUnitDegraded
        -- fltMemoryUnitInoperable
        -- fltMemoryUnitThermalThresholdNonCritical
        -- fltMemoryUnitThermalThresholdCritical
        -- fltMemoryUnitThermalThresholdNonRecoverable
        -- fltMemoryUnitDisabled

-- extvmm:Ep
    -- sys/extvm-mgmt
        -- fsmStFailExtvmmEpClusterRole:SetLocal
        -- fsmStFailExtvmmEpClusterRole:SetPeer
        -- fsmRmtErrExtvmmEpClusterRole:SetLocal
        -- fsmRmtErrExtvmmEpClusterRole:SetPeer
        -- fsmFailExtvmmEpClusterRole

-- storage:Initiator
    -- org-[name]/tier-[name]/ls-[name]/grp-[name]/ini-[name]
    -- org-[name]/ls-[name]/grp-[name]/ini-[name]
    -- org-[name]/san-conn-pol-[name]/grp-[name]/ini-[name]
        -- fltStorageInitiatorConfiguration-error

-- storage:FlexFlashCard
    -- sys/chassis-[id]/blade-[slotId]/board/storage-flexflash-[id]/card-[slotNumber]
    -- sys/rack-unit-[id]/board/storage-flexflash-[id]/card-[slotNumber]
        -- fltStorageFlexFlashCardInoperable
        -- fltStorageFlexFlashCardMissing
        -- fltStorageFlexFlashCardUnhealthy

-- nwctrl:CardConfig
    -- sys/switch-[id]/card-[slotId]
        -- fltNwctrlCardConfigOffline
        -- fltNwctrlCardConfigFailed
        -- fltNwctrlCardConfigError
        -- fltNwctrlCardConfigOirFailed
        -- fltNwctrlCardConfigOirInvalid
        -- fltNwctrlCardConfigRemoval
        -- fltNwctrlCardConfigMismatch
        -- fltNwctrlCardConfigSupriseRemoval

-- fabric:EthEstcPcEp
    -- fabric/eth-estc/[id]/pc-[portId]/ep-slot-[slotId]-port-[portId]
    -- fabric/server/sw-[id]/slot-[slotId]-aggr-port-[aggrPortId]/ep-slot-[slotId]-port-[portId]
    -- fabric/server/sw-[id]/pc-[portId]/slot-[slotId]-aggr-port-[aggrPortId]/ep-slot-[slotId]-port-[portId]
    -- fabric/eth-estc/[id]/slot-[slotId]-aggr-port-[aggrPortId]/ep-slot-[slotId]-port-[portId]
    -- fabric/eth-estc/[id]/pc-[portId]/slot-[slotId]-aggr-port-[aggrPortId]/ep-slot-[slotId]-port-[portId]
    -- fabric/lan/[id]/slot-[slotId]-aggr-port-[aggrPortId]/ep-slot-[slotId]-port-[portId]
    -- fabric/lan/[id]/pc-[portId]/slot-[slotId]-aggr-port-[aggrPortId]/ep-slot-[slotId]-port-[portId]
    -- fabric/lanmon/[id]/eth-mon-[name]/slot-[slotId]-aggr-port-[aggrPortId]/ep-slot-[slotId]-port-[portId]
    -- fabric/san/[id]/slot-[slotId]-aggr-port-[aggrPortId]/ep-slot-[slotId]-port-[portId]
    -- fabric/san/[id]/fcoesanpc-[portId]/slot-[slotId]-aggr-port-[aggrPortId]/ep-slot-[slotId]-port-[portId]
        -- fltFabricEthEstcPcEpDown

-- sysdebug:MemoryOverall
    -- sys/sysdebug/mem-overall/mem-usage
        -- fltSysdebugMemoryOverallHighSystemMemoryUsage

-- firmware:System
    -- sys/fw-system
        -- fsmStFailFirmwareSystemDeploy:ActivateIOM
        -- fsmStFailFirmwareSystemDeploy:ActivateLocalFI
        -- fsmStFailFirmwareSystemDeploy:ActivateMgmtExt
        -- fsmStFailFirmwareSystemDeploy:ActivateRemoteFI
        -- fsmStFailFirmwareSystemDeploy:ActivateFPRM
        -- fsmStFailFirmwareSystemDeploy:DebundlePort
        -- fsmStFailFirmwareSystemDeploy:ImageInventory
        -- fsmStFailFirmwareSystemDeploy:PollActivateOfIOM
        -- fsmStFailFirmwareSystemDeploy:PollActivateOfLocalFI
        -- fsmStFailFirmwareSystemDeploy:PollActivateOfMgmtExt
        -- fsmStFailFirmwareSystemDeploy:PollActivateOfRemoteFI
        -- fsmStFailFirmwareSystemDeploy:PollActivateOfFPRM
        -- fsmStFailFirmwareSystemDeploy:PollDebundlePort
        -- fsmStFailFirmwareSystemDeploy:PollUpdateOfIOM
        -- fsmStFailFirmwareSystemDeploy:ResolveDistributable
        -- fsmStFailFirmwareSystemDeploy:ResolveDistributableNames
        -- fsmStFailFirmwareSystemDeploy:ResolveImages
        -- fsmStFailFirmwareSystemDeploy:UnpackFirmware
        -- fsmStFailFirmwareSystemDeploy:UpdateIOM
        -- fsmStFailFirmwareSystemDeploy:UpgradeFirmware
        -- fsmStFailFirmwareSystemDeploy:ValidatePlatformPack
        -- fsmStFailFirmwareSystemDeploy:WaitForDeploy
        -- fsmStFailFirmwareSystemDeploy:WaitForUserAck
        -- fsmStFailFirmwareSystemApplyCatalogPack:ActivateCatalog
        -- fsmStFailFirmwareSystemApplyCatalogPack:ResolveDistributable
        -- fsmStFailFirmwareSystemApplyCatalogPack:ResolveDistributableNames
        -- fsmStFailFirmwareSystemApplyCatalogPack:ResolveImages
        -- fsmRmtErrFirmwareSystemDeploy:ActivateIOM
        -- fsmRmtErrFirmwareSystemDeploy:ActivateLocalFI
        -- fsmRmtErrFirmwareSystemDeploy:ActivateMgmtExt
        -- fsmRmtErrFirmwareSystemDeploy:ActivateRemoteFI
        -- fsmRmtErrFirmwareSystemDeploy:ActivateFPRM
        -- fsmRmtErrFirmwareSystemDeploy:DebundlePort
        -- fsmRmtErrFirmwareSystemDeploy:ImageInventory
        -- fsmRmtErrFirmwareSystemDeploy:PollActivateOfIOM
        -- fsmRmtErrFirmwareSystemDeploy:PollActivateOfLocalFI
        -- fsmRmtErrFirmwareSystemDeploy:PollActivateOfMgmtExt
        -- fsmRmtErrFirmwareSystemDeploy:PollActivateOfRemoteFI
        -- fsmRmtErrFirmwareSystemDeploy:PollActivateOfFPRM
        -- fsmRmtErrFirmwareSystemDeploy:PollDebundlePort
        -- fsmRmtErrFirmwareSystemDeploy:PollUpdateOfIOM
        -- fsmRmtErrFirmwareSystemDeploy:ResolveDistributable
        -- fsmRmtErrFirmwareSystemDeploy:ResolveDistributableNames
        -- fsmRmtErrFirmwareSystemDeploy:ResolveImages
        -- fsmRmtErrFirmwareSystemDeploy:UnpackFirmware
        -- fsmRmtErrFirmwareSystemDeploy:UpdateIOM
        -- fsmRmtErrFirmwareSystemDeploy:UpgradeFirmware
        -- fsmRmtErrFirmwareSystemDeploy:ValidatePlatformPack
        -- fsmRmtErrFirmwareSystemDeploy:WaitForDeploy
        -- fsmRmtErrFirmwareSystemDeploy:WaitForUserAck
        -- fsmRmtErrFirmwareSystemApplyCatalogPack:ActivateCatalog
        -- fsmRmtErrFirmwareSystemApplyCatalogPack:ResolveDistributable
        -- fsmRmtErrFirmwareSystemApplyCatalogPack:ResolveDistributableNames
        -- fsmRmtErrFirmwareSystemApplyCatalogPack:ResolveImages
        -- fsmFailFirmwareSystemDeploy
        -- fsmFailFirmwareSystemApplyCatalogPack

-- os:Controller
    -- sys/chassis-[id]/blade-[slotId]/os-ctrl
    -- sys/chassis-[id]/blade-[slotId]/os-ctrl
    -- sys/rack-unit-[id]/os-ctrl
    -- sys/os-ctrl
        -- fltOsControllerFailedBladeBootup
        -- fltOsControllerFailedBootupRecovery
        -- fsmStFailOsControllerDeployOS:HostCheckImageValidationStatus
        -- fsmStFailOsControllerDeployOS:HostCheckRommonReady
        -- fsmStFailOsControllerDeployOS:HostCheckUpgradeImageStatus
        -- fsmStFailOsControllerDeployOS:HostPrepareBoot
        -- fsmStFailOsControllerDeployOS:HostPrepareKeyFile
        -- fsmStFailOsControllerDeployOS:HostWaitForRommonReady
        -- fsmStFailOsControllerDeployOS:HostWaitForRommonValidateImage
        -- fsmStFailOsControllerDeployOS:HostWaitForSspOsRunning
        -- fsmStFailOsControllerUpgradeOS:HostWaitForUpgradeComplete
        -- fsmStFailOsControllerUpgradeOS:RebootHostAfterUpgrade
        -- fsmStFailOsControllerUpgradeOS:RequestToUpgrade
        -- fsmStFailOsControllerInitOS:HostPrepareBoot
        -- fsmStFailOsControllerInitOS:HostWaitForLicInstalledComplete
        -- fsmStFailOsControllerInitOS:HostWaitForUpgradeComplete
        -- fsmStFailOsControllerInitOS:RebootHostAfterUpgrade
        -- fsmStFailOsControllerInitOS:RequestToInstallLicense
        -- fsmStFailOsControllerInitOS:RequestToUpgrade
        -- fsmStFailOsControllerInstallLicense:RequestToInstallLicense
        -- fsmStFailOsControllerInstallLicense:RequestToUninstallLicense
        -- fsmStFailOsControllerInstallLicense:WaitForLicInstalledComplete
        -- fsmRmtErrOsControllerDeployOS:HostCheckImageValidationStatus
        -- fsmRmtErrOsControllerDeployOS:HostCheckRommonReady
        -- fsmRmtErrOsControllerDeployOS:HostCheckUpgradeImageStatus
        -- fsmRmtErrOsControllerDeployOS:HostPrepareBoot
        -- fsmRmtErrOsControllerDeployOS:HostPrepareKeyFile
        -- fsmRmtErrOsControllerDeployOS:HostWaitForRommonReady
        -- fsmRmtErrOsControllerDeployOS:HostWaitForRommonValidateImage
        -- fsmRmtErrOsControllerDeployOS:HostWaitForSspOsRunning
        -- fsmRmtErrOsControllerUpgradeOS:HostWaitForUpgradeComplete
        -- fsmRmtErrOsControllerUpgradeOS:RebootHostAfterUpgrade
        -- fsmRmtErrOsControllerUpgradeOS:RequestToUpgrade
        -- fsmRmtErrOsControllerInitOS:HostPrepareBoot
        -- fsmRmtErrOsControllerInitOS:HostWaitForLicInstalledComplete
        -- fsmRmtErrOsControllerInitOS:HostWaitForUpgradeComplete
        -- fsmRmtErrOsControllerInitOS:RebootHostAfterUpgrade
        -- fsmRmtErrOsControllerInitOS:RequestToInstallLicense
        -- fsmRmtErrOsControllerInitOS:RequestToUpgrade
        -- fsmRmtErrOsControllerInstallLicense:RequestToInstallLicense
        -- fsmRmtErrOsControllerInstallLicense:RequestToUninstallLicense
        -- fsmRmtErrOsControllerInstallLicense:WaitForLicInstalledComplete
        -- fsmFailOsControllerDeployOS
        -- fsmFailOsControllerUpgradeOS
        -- fsmFailOsControllerInitOS
        -- fsmFailOsControllerInstallLicense

-- compute:RtcBattery
    -- sys/chassis-[id]/blade-[slotId]/board/rtc-battery
    -- sys/rack-unit-[id]/board/rtc-battery
        -- fltComputeRtcBatteryInoperable

-- storage:FlexFlashController
    -- sys/chassis-[id]/blade-[slotId]/board/storage-flexflash-[id]
    -- sys/rack-unit-[id]/board/storage-flexflash-[id]
        -- fltStorageFlexFlashControllerInoperable
        -- fltStorageFlexFlashControllerMismatch
        -- fsmStFailStorageFlexFlashControllerMOpsReset:Reset
        -- fsmStFailStorageFlexFlashControllerMOpsFormat:Format
        -- fsmStFailStorageFlexFlashControllerMOpsPair:Pair
        -- fsmRmtErrStorageFlexFlashControllerMOpsReset:Reset
        -- fsmRmtErrStorageFlexFlashControllerMOpsFormat:Format
        -- fsmRmtErrStorageFlexFlashControllerMOpsPair:Pair
        -- fsmFailStorageFlexFlashControllerMOpsReset
        -- fsmFailStorageFlexFlashControllerMOpsFormat
        -- fsmFailStorageFlexFlashControllerMOpsPair

-- ether:FtwPortPair
    -- sys/switch-[id]/fail-to-wire/ftw-port-[slotId]-[aggrPortId]-[portId]-port-[peerSlotId]-[peerAggrPortId]-[peerPortId]
        -- fltEtherFtwPortPairBypass
        -- fltEtherFtwPortPairPhyBypass
        -- fltEtherFtwPortPairPhyBypassErr
        -- fsmStFailEtherFtwPortPairConfigFtw:Configure
        -- fsmRmtErrEtherFtwPortPairConfigFtw:Configure
        -- fsmFailEtherFtwPortPairConfigFtw

-- sm:App
    -- sys-secsvc/slot-[slotId]/app-inst-[appInstId]/app-[name]-[version]
    -- sec-svc/app-[name]-[version]
        -- fltSmAppAppImageCorrupted
        -- fsmStFailSmAppDelete:Local
        -- fsmStFailSmAppVerifyApplication:CheckReadiness
        -- fsmStFailSmAppVerifyApplication:Verify
        -- fsmRmtErrSmAppDelete:Local
        -- fsmRmtErrSmAppVerifyApplication:CheckReadiness
        -- fsmRmtErrSmAppVerifyApplication:Verify
        -- fsmFailSmAppDelete
        -- fsmFailSmAppVerifyApplication

-- sd:PortsBundle
    -- sys-secsvc/slot-[slotId]/app-inst-[appInstId]/ports-bundle
        -- fsmStFailSdPortsBundleBundleDataPorts:ConfigureLinks
        -- fsmStFailSdPortsBundleBundleDataPorts:SendBundleStatus
        -- fsmStFailSdPortsBundleBundleDataPorts:UpdateBundleStatus
        -- fsmStFailSdPortsBundleBundleDataPorts:WaitForConfigCompletion
        -- fsmRmtErrSdPortsBundleBundleDataPorts:ConfigureLinks
        -- fsmRmtErrSdPortsBundleBundleDataPorts:SendBundleStatus
        -- fsmRmtErrSdPortsBundleBundleDataPorts:UpdateBundleStatus
        -- fsmRmtErrSdPortsBundleBundleDataPorts:WaitForConfigCompletion
        -- fsmFailSdPortsBundleBundleDataPorts

-- adaptor:ExtEthIf
    -- sys/chassis-[id]/blade-[slotId]/adaptor-[id]/ext-eth-[id]
    -- sys/rack-unit-[id]/adaptor-[id]/ext-eth-[id]
        -- fltAdaptorExtEthIfMisConnect
        -- fltAdaptorExtEthIfMissing
        -- fsmStFailAdaptorExtEthIfPathReset:Disable
        -- fsmStFailAdaptorExtEthIfPathReset:Enable
        -- fsmRmtErrAdaptorExtEthIfPathReset:Disable
        -- fsmRmtErrAdaptorExtEthIfPathReset:Enable
        -- fsmFailAdaptorExtEthIfPathReset

-- network:OperLevel
    -- sys/switch-[id]/oper-level
        -- fltNetworkOperLevelExtraprimaryvlans
        -- fltNetworkOperLevelExtrasecondaryvlans

-- lsmaint:MaintPolicy
    -- org-[name]/maint-[name]
        -- fltLsmaintMaintPolicyUnresolvableScheduler

-- dcx:Ns
    -- sys/chassis-[id]/blade-[slotId]/adaptor-[id]/dcxns-[switchId]
    -- sys/rack-unit-[id]/adaptor-[id]/dcxns-[switchId]
        -- fltDcxNsFailed

-- ls:Server
    -- org-[name]/tier-[name]/ls-[name]
    -- org-[name]/ls-[name]
        -- fltLsServerFailed
        -- fltLsServerDiscoveryFailed
        -- fltLsServerConfigFailure
        -- fltLsServerMaintenanceFailed
        -- fltLsServerRemoved
        -- fltLsServerInaccessible
        -- fltLsServerAssociationFailed
        -- fltLsServerUnassociated
        -- fltLsServerServer-unfulfilled
        -- fltLsServerSvnicNotPresent
        -- fsmStFailLsServerConfigure:AnalyzeImpact
        -- fsmStFailLsServerConfigure:ApplyConfig
        -- fsmStFailLsServerConfigure:ApplyDefaultIdentifiers
        -- fsmStFailLsServerConfigure:ApplyIdentifiers
        -- fsmStFailLsServerConfigure:ApplyPolicies
        -- fsmStFailLsServerConfigure:ApplyTemplate
        -- fsmStFailLsServerConfigure:CommitStorage
        -- fsmStFailLsServerConfigure:EvaluateAssociation
        -- fsmStFailLsServerConfigure:ProvisionStorage
        -- fsmStFailLsServerConfigure:ResolveBootConfig
        -- fsmStFailLsServerConfigure:ResolveDefaultIdentifiers
        -- fsmStFailLsServerConfigure:ResolveDistributable
        -- fsmStFailLsServerConfigure:ResolveDistributableNames
        -- fsmStFailLsServerConfigure:ResolveIdentifiers
        -- fsmStFailLsServerConfigure:ResolveImages
        -- fsmStFailLsServerConfigure:ResolveNetworkPolicies
        -- fsmStFailLsServerConfigure:ResolveNetworkTemplates
        -- fsmStFailLsServerConfigure:ResolvePolicies
        -- fsmStFailLsServerConfigure:ResolveSchedule
        -- fsmStFailLsServerConfigure:ValidatePolicyOwnership
        -- fsmStFailLsServerConfigure:WaitForAssocCompletion
        -- fsmStFailLsServerConfigure:WaitForCommitStorage
        -- fsmStFailLsServerConfigure:WaitForMaintPermission
        -- fsmStFailLsServerConfigure:WaitForMaintWindow
        -- fsmStFailLsServerConfigure:WaitForStorageProvision
        -- fsmStFailLsServerConfigure:checkAssignedDefaultIdentifiersForDup
        -- fsmStFailLsServerConfigure:checkAssignedIdentifiersForDup
        -- fsmRmtErrLsServerConfigure:AnalyzeImpact
        -- fsmRmtErrLsServerConfigure:ApplyConfig
        -- fsmRmtErrLsServerConfigure:ApplyDefaultIdentifiers
        -- fsmRmtErrLsServerConfigure:ApplyIdentifiers
        -- fsmRmtErrLsServerConfigure:ApplyPolicies
        -- fsmRmtErrLsServerConfigure:ApplyTemplate
        -- fsmRmtErrLsServerConfigure:CommitStorage
        -- fsmRmtErrLsServerConfigure:EvaluateAssociation
        -- fsmRmtErrLsServerConfigure:ProvisionStorage
        -- fsmRmtErrLsServerConfigure:ResolveBootConfig
        -- fsmRmtErrLsServerConfigure:ResolveDefaultIdentifiers
        -- fsmRmtErrLsServerConfigure:ResolveDistributable
        -- fsmRmtErrLsServerConfigure:ResolveDistributableNames
        -- fsmRmtErrLsServerConfigure:ResolveIdentifiers
        -- fsmRmtErrLsServerConfigure:ResolveImages
        -- fsmRmtErrLsServerConfigure:ResolveNetworkPolicies
        -- fsmRmtErrLsServerConfigure:ResolveNetworkTemplates
        -- fsmRmtErrLsServerConfigure:ResolvePolicies
        -- fsmRmtErrLsServerConfigure:ResolveSchedule
        -- fsmRmtErrLsServerConfigure:ValidatePolicyOwnership
        -- fsmRmtErrLsServerConfigure:WaitForAssocCompletion
        -- fsmRmtErrLsServerConfigure:WaitForCommitStorage
        -- fsmRmtErrLsServerConfigure:WaitForMaintPermission
        -- fsmRmtErrLsServerConfigure:WaitForMaintWindow
        -- fsmRmtErrLsServerConfigure:WaitForStorageProvision
        -- fsmRmtErrLsServerConfigure:checkAssignedDefaultIdentifiersForDup
        -- fsmRmtErrLsServerConfigure:checkAssignedIdentifiersForDup
        -- fsmFailLsServerConfigure

-- sysdebug:TechSupport
    -- sys/tech-support-files/tech-support-[creationTS]
        -- fsmStFailSysdebugTechSupportInitiate:Local
        -- fsmStFailSysdebugTechSupportDeleteTechSupFile:Local
        -- fsmStFailSysdebugTechSupportDeleteTechSupFile:peer
        -- fsmStFailSysdebugTechSupportDownload:CopyPrimary
        -- fsmStFailSysdebugTechSupportDownload:CopySub
        -- fsmStFailSysdebugTechSupportDownload:DeletePrimary
        -- fsmStFailSysdebugTechSupportDownload:DeleteSub
        -- fsmRmtErrSysdebugTechSupportInitiate:Local
        -- fsmRmtErrSysdebugTechSupportDeleteTechSupFile:Local
        -- fsmRmtErrSysdebugTechSupportDeleteTechSupFile:peer
        -- fsmRmtErrSysdebugTechSupportDownload:CopyPrimary
        -- fsmRmtErrSysdebugTechSupportDownload:CopySub
        -- fsmRmtErrSysdebugTechSupportDownload:DeletePrimary
        -- fsmRmtErrSysdebugTechSupportDownload:DeleteSub
        -- fsmFailSysdebugTechSupportInitiate
        -- fsmFailSysdebugTechSupportDeleteTechSupFile
        -- fsmFailSysdebugTechSupportDownload

-- firmware:Image
    -- sys/fw-catalogue/image-[name]
    -- sys/fw-catalogue/distrib-[name]/image-[name]
        -- fsmStFailFirmwareImageDelete:Local
        -- fsmStFailFirmwareImageDelete:Remote
        -- fsmRmtErrFirmwareImageDelete:Local
        -- fsmRmtErrFirmwareImageDelete:Remote
        -- fsmFailFirmwareImageDelete

-- sd:Ldu
    -- sys-secsvc/slot-[slotId]/app-inst-[appInstId]/ldu-[slotId]
    -- sys-secsvc/ld-[name]/ldu-[slotId]
        -- fsmStFailSdLduProvisionLDU:CheckBladeReadiness
        -- fsmStFailSdLduProvisionLDU:StartApps
        -- fsmStFailSdLduProvisionLDU:WaitForAppsInstallation
        -- fsmStFailSdLduProvisionLDU:WaitForLinkConfiguration
        -- fsmStFailSdLduUpdateInterfaceStatus:SendStatus
        -- fsmRmtErrSdLduProvisionLDU:CheckBladeReadiness
        -- fsmRmtErrSdLduProvisionLDU:StartApps
        -- fsmRmtErrSdLduProvisionLDU:WaitForAppsInstallation
        -- fsmRmtErrSdLduProvisionLDU:WaitForLinkConfiguration
        -- fsmRmtErrSdLduUpdateInterfaceStatus:SendStatus
        -- fsmFailSdLduProvisionLDU
        -- fsmFailSdLduUpdateInterfaceStatus

-- equipment:HealthLed
    -- sys/chassis-[id]/blade-[slotId]/health-led
    -- sys/chassis-[id]/blade-[slotId]/ext-board-[id]/health-led
    -- sys/rack-unit-[id]/ext-board-[id]/health-led
    -- sys/chassis-[id]/blade-[slotId]/health-led
    -- sys/rack-unit-[id]/health-led
    -- sys/rack-unit-[id]/health-led
    -- sys/chassis-[id]/health-led
    -- sys/rack-unit-[id]/fan-module-[tray]-[id]/health-led
    -- sys/chassis-[id]/fan-module-[tray]-[id]/health-led
    -- sys/switch-[id]/fan-module-[tray]-[id]/health-led
    -- sys/fex-[id]/health-led
    -- sys/chassis-[id]/slot-[id]/health-led
    -- sys/fex-[id]/slot-[id]/health-led
    -- sys/rack-unit-[id]/psu-[id]/health-led
    -- sys/chassis-[id]/psu-[id]/health-led
    -- sys/fex-[id]/psu-[id]/health-led
    -- sys/switch-[id]/psu-[id]/health-led
        -- fltEquipmentHealthLedCriticalError
        -- fltEquipmentHealthLedMinorError

-- capability:MgmtExtension
    -- capabilities/ep/mgmt-ext
        -- fsmStFailCapabilityMgmtExtensionActivateMgmtExt:ApplyCatalog
        -- fsmStFailCapabilityMgmtExtensionActivateMgmtExt:CopyRemote
        -- fsmStFailCapabilityMgmtExtensionActivateMgmtExt:EvaluateStatus
        -- fsmStFailCapabilityMgmtExtensionActivateMgmtExt:RescanImages
        -- fsmStFailCapabilityMgmtExtensionActivateMgmtExt:UnpackLocal
        -- fsmRmtErrCapabilityMgmtExtensionActivateMgmtExt:ApplyCatalog
        -- fsmRmtErrCapabilityMgmtExtensionActivateMgmtExt:CopyRemote
        -- fsmRmtErrCapabilityMgmtExtensionActivateMgmtExt:EvaluateStatus
        -- fsmRmtErrCapabilityMgmtExtensionActivateMgmtExt:RescanImages
        -- fsmRmtErrCapabilityMgmtExtensionActivateMgmtExt:UnpackLocal
        -- fsmFailCapabilityMgmtExtensionActivateMgmtExt

-- sd:AppInstance
    -- sys-secsvc/slot-[slotId]/app-inst-[appInstId]
        -- fsmStFailSdAppInstanceInstallApplication:Install
        -- fsmStFailSdAppInstanceInstallApplication:UpdateAppInstance
        -- fsmStFailSdAppInstanceStartApplication:DebundlePorts
        -- fsmStFailSdAppInstanceStartApplication:GracefulStopApp
        -- fsmStFailSdAppInstanceStartApplication:Start
        -- fsmStFailSdAppInstanceStartApplication:UpdateAppInstance
        -- fsmStFailSdAppInstanceUpgradeApplication:DebundlePorts
        -- fsmStFailSdAppInstanceUpgradeApplication:UpdateAppInstance
        -- fsmStFailSdAppInstanceUpgradeApplication:Upgrade
        -- fsmStFailSdAppInstanceStopApplication:DebundlePorts
        -- fsmStFailSdAppInstanceStopApplication:Deregister
        -- fsmStFailSdAppInstanceStopApplication:GracefulStopApp
        -- fsmStFailSdAppInstanceStopApplication:ReleaseAppLicense
        -- fsmStFailSdAppInstanceStopApplication:Stop
        -- fsmStFailSdAppInstanceStopApplication:UpdateAppInstance
        -- fsmStFailSdAppInstanceUninstallApplication:ReleaseAppLicense
        -- fsmStFailSdAppInstanceUninstallApplication:Uninstall
        -- fsmStFailSdAppInstanceGracefulStopApp:Apply
        -- fsmRmtErrSdAppInstanceInstallApplication:Install
        -- fsmRmtErrSdAppInstanceInstallApplication:UpdateAppInstance
        -- fsmRmtErrSdAppInstanceStartApplication:DebundlePorts
        -- fsmRmtErrSdAppInstanceStartApplication:GracefulStopApp
        -- fsmRmtErrSdAppInstanceStartApplication:Start
        -- fsmRmtErrSdAppInstanceStartApplication:UpdateAppInstance
        -- fsmRmtErrSdAppInstanceUpgradeApplication:DebundlePorts
        -- fsmRmtErrSdAppInstanceUpgradeApplication:UpdateAppInstance
        -- fsmRmtErrSdAppInstanceUpgradeApplication:Upgrade
        -- fsmRmtErrSdAppInstanceStopApplication:DebundlePorts
        -- fsmRmtErrSdAppInstanceStopApplication:Deregister
        -- fsmRmtErrSdAppInstanceStopApplication:GracefulStopApp
        -- fsmRmtErrSdAppInstanceStopApplication:ReleaseAppLicense
        -- fsmRmtErrSdAppInstanceStopApplication:Stop
        -- fsmRmtErrSdAppInstanceStopApplication:UpdateAppInstance
        -- fsmRmtErrSdAppInstanceUninstallApplication:ReleaseAppLicense
        -- fsmRmtErrSdAppInstanceUninstallApplication:Uninstall
        -- fsmRmtErrSdAppInstanceGracefulStopApp:Apply
        -- fsmFailSdAppInstanceInstallApplication
        -- fsmFailSdAppInstanceStartApplication
        -- fsmFailSdAppInstanceUpgradeApplication
        -- fsmFailSdAppInstanceStopApplication
        -- fsmFailSdAppInstanceUninstallApplication
        -- fsmFailSdAppInstanceGracefulStopApp

-- compute:ServerDiscPolicy
    -- org-[name]/server-discovery
        -- fsmStFailComputeServerDiscPolicyResolveScrubPolicy:Resolve
        -- fsmRmtErrComputeServerDiscPolicyResolveScrubPolicy:Resolve
        -- fsmFailComputeServerDiscPolicyResolveScrubPolicy

-- port:PIo
    -- sys/chassis-[id]/slot-[id]/[type]/port-[portId]
    -- sys/fex-[id]/slot-[id]/[type]/port-[portId]
    -- sys/switch-[id]/slot-[id]/[type]/port-[portId]
    -- sys/chassis-[id]/sw-slot-[id]/[type]/port-[portId]
    -- sys/chassis-[id]/slot-[id]/[type]/aggr-port-[aggrPortId]/port-[portId]
    -- sys/fex-[id]/slot-[id]/[type]/aggr-port-[aggrPortId]/port-[portId]
    -- sys/switch-[id]/slot-[id]/[type]/aggr-port-[aggrPortId]/port-[portId]
    -- sys/chassis-[id]/sw-slot-[id]/[type]/aggr-port-[aggrPortId]/port-[portId]
        -- fltPortPIoLink-down
        -- fltPortPIoFailed
        -- fltPortPIoHardware-failure
        -- fltPortPIoSfp-not-present
        -- fltPortPIoInvalid-sfp
        -- fsmStFailPortPIoInCompatSfpPresence:Shutdown
        -- fsmStFailPortPIoInCompatSfpReplaced:EnablePort
        -- fsmRmtErrPortPIoInCompatSfpPresence:Shutdown
        -- fsmRmtErrPortPIoInCompatSfpReplaced:EnablePort
        -- fsmFailPortPIoInCompatSfpPresence
        -- fsmFailPortPIoInCompatSfpReplaced

-- gmeta:Holder
    -- gmeta/category-[category]-provider-[provider]
        -- fsmStFailGmetaHolderInventory:CheckInventoryStatus
        -- fsmStFailGmetaHolderInventory:ReportFullInventory
        -- fsmRmtErrGmetaHolderInventory:CheckInventoryStatus
        -- fsmRmtErrGmetaHolderInventory:ReportFullInventory
        -- fsmFailGmetaHolderInventory

-- license:Instance
    -- sys/license/feature-[name]-[vendor]-[version]/inst-[scope]
        -- fsmStFailLicenseInstanceUpdateFlexlm:Local
        -- fsmStFailLicenseInstanceUpdateFlexlm:Remote
        -- fsmRmtErrLicenseInstanceUpdateFlexlm:Local
        -- fsmRmtErrLicenseInstanceUpdateFlexlm:Remote
        -- fsmFailLicenseInstanceUpdateFlexlm

-- power:Budget
    -- sys/chassis-[id]/blade-[slotId]/ext-board-[id]/budget
    -- sys/rack-unit-[id]/ext-board-[id]/budget
    -- sys/chassis-[id]/blade-[slotId]/budget
    -- sys/rack-unit-[id]/budget
    -- sys/chassis-[id]/budget
        -- fltPowerBudgetPowerBudgetCmcProblem
        -- fltPowerBudgetPowerBudgetBmcProblem
        -- fltPowerBudgetPowerBudgetDiscFail
        -- fltPowerBudgetPowerCapReachedCommit
        -- fltPowerBudgetChassisPsuInsufficient
        -- fltPowerBudgetTStateTransition
        -- fltPowerBudgetChassisPsuMixedMode

-- ls:Issues
    -- org-[name]/tier-[name]/ls-[name]/config-issue
    -- org-[name]/ls-[name]/config-issue
        -- fltLsIssuesIscsi-config-failed
        -- fltLsIssuesKvmPolicyUnsupported

-- power:Policy
    -- org-[name]/power-policy-[name]
        -- fltPowerPolicyPowerPolicyApplicationFail

-- sysdebug:AutoCoreFileExportTarget
    -- sys/sysdebug/file-export
        -- fltSysdebugAutoCoreFileExportTargetAutoCoreTransferFailure
        -- fsmStFailSysdebugAutoCoreFileExportTargetConfigure:Local
        -- fsmStFailSysdebugAutoCoreFileExportTargetConfigure:Peer
        -- fsmRmtErrSysdebugAutoCoreFileExportTargetConfigure:Local
        -- fsmRmtErrSysdebugAutoCoreFileExportTargetConfigure:Peer
        -- fsmFailSysdebugAutoCoreFileExportTargetConfigure

-- storage:FlexFlashDrive
    -- sys/chassis-[id]/blade-[slotId]/board/storage-flexflash-[id]/card-[slotNumber]/drive-[name]
    -- sys/rack-unit-[id]/board/storage-flexflash-[id]/card-[slotNumber]/drive-[name]
        -- fltStorageFlexFlashDriveUnhealthy

-- sw:Vlan
    -- sys/chassis-[id]/blade-[slotId]/fabric-[switchId]/vc-[id]/vlan-[id]
    -- sys/chassis-[id]/blade-[slotId]/fabric-[switchId]/vc-[id]/vlan-[id]
    -- sys/rack-unit-[id]/fabric-[switchId]/vc-[id]/vlan-[id]
    -- sys/chassis-[id]/fabric-[switchId]/vc-[id]/vlan-[id]
    -- sys/fex-[id]/fabric-[switchId]/vc-[id]/vlan-[id]
    -- sys/chassis-[id]/blade-[slotId]/adaptor-[id]/mgmt/fabric-[switchId]/vc-[id]/vlan-[id]
    -- sys/rack-unit-[id]/adaptor-[id]/mgmt/fabric-[switchId]/vc-[id]/vlan-[id]
    -- sys/chassis-[id]/blade-[slotId]/ext-board-[id]/boardController/mgmt/fabric-[switchId]/vc-[id]/vlan-[id]
    -- sys/rack-unit-[id]/ext-board-[id]/boardController/mgmt/fabric-[switchId]/vc-[id]/vlan-[id]
    -- sys/chassis-[id]/blade-[slotId]/boardController/mgmt/fabric-[switchId]/vc-[id]/vlan-[id]
    -- sys/rack-unit-[id]/boardController/mgmt/fabric-[switchId]/vc-[id]/vlan-[id]
    -- sys/chassis-[id]/blade-[slotId]/ext-board-[id]/mgmt/fabric-[switchId]/vc-[id]/vlan-[id]
    -- sys/rack-unit-[id]/ext-board-[id]/mgmt/fabric-[switchId]/vc-[id]/vlan-[id]
    -- sys/chassis-[id]/blade-[slotId]/mgmt/fabric-[switchId]/vc-[id]/vlan-[id]
    -- sys/rack-unit-[id]/mgmt/fabric-[switchId]/vc-[id]/vlan-[id]
    -- sys/fex-[id]/mgmt/fabric-[switchId]/vc-[id]/vlan-[id]
    -- sys/chassis-[id]/slot-[id]/mgmt/fabric-[switchId]/vc-[id]/vlan-[id]
    -- sys/fex-[id]/slot-[id]/mgmt/fabric-[switchId]/vc-[id]/vlan-[id]
    -- sys/chassis-[id]/sw-slot-[id]/mgmt/fabric-[switchId]/vc-[id]/vlan-[id]
    -- sys/switch-[id]/mgmt/fabric-[switchId]/vc-[id]/vlan-[id]
    -- sys/mgmt/fabric-[switchId]/vc-[id]/vlan-[id]
    -- sys/chassis-[id]/blade-[slotId]/fabric-[switchId]/path-[id]/vc-[id]/vlan-[id]
    -- sys/chassis-[id]/blade-[slotId]/fabric-[switchId]/path-[id]/vc-[id]/vlan-[id]
    -- sys/rack-unit-[id]/fabric-[switchId]/path-[id]/vc-[id]/vlan-[id]
    -- sys/chassis-[id]/fabric-[switchId]/path-[id]/vc-[id]/vlan-[id]
    -- sys/fex-[id]/fabric-[switchId]/path-[id]/vc-[id]/vlan-[id]
    -- sys/chassis-[id]/blade-[slotId]/adaptor-[id]/mgmt/fabric-[switchId]/path-[id]/vc-[id]/vlan-[id]
    -- sys/rack-unit-[id]/adaptor-[id]/mgmt/fabric-[switchId]/path-[id]/vc-[id]/vlan-[id]
    -- sys/chassis-[id]/blade-[slotId]/ext-board-[id]/boardController/mgmt/fabric-[switchId]/path-[id]/vc-[id]/vlan-[id]
    -- sys/rack-unit-[id]/ext-board-[id]/boardController/mgmt/fabric-[switchId]/path-[id]/vc-[id]/vlan-[id]
    -- sys/chassis-[id]/blade-[slotId]/boardController/mgmt/fabric-[switchId]/path-[id]/vc-[id]/vlan-[id]
    -- sys/rack-unit-[id]/boardController/mgmt/fabric-[switchId]/path-[id]/vc-[id]/vlan-[id]
    -- sys/chassis-[id]/blade-[slotId]/ext-board-[id]/mgmt/fabric-[switchId]/path-[id]/vc-[id]/vlan-[id]
    -- sys/rack-unit-[id]/ext-board-[id]/mgmt/fabric-[switchId]/path-[id]/vc-[id]/vlan-[id]
    -- sys/chassis-[id]/blade-[slotId]/mgmt/fabric-[switchId]/path-[id]/vc-[id]/vlan-[id]
    -- sys/rack-unit-[id]/mgmt/fabric-[switchId]/path-[id]/vc-[id]/vlan-[id]
    -- sys/fex-[id]/mgmt/fabric-[switchId]/path-[id]/vc-[id]/vlan-[id]
    -- sys/chassis-[id]/slot-[id]/mgmt/fabric-[switchId]/path-[id]/vc-[id]/vlan-[id]
    -- sys/fex-[id]/slot-[id]/mgmt/fabric-[switchId]/path-[id]/vc-[id]/vlan-[id]
    -- sys/chassis-[id]/sw-slot-[id]/mgmt/fabric-[switchId]/path-[id]/vc-[id]/vlan-[id]
    -- sys/switch-[id]/mgmt/fabric-[switchId]/path-[id]/vc-[id]/vlan-[id]
    -- sys/mgmt/fabric-[switchId]/path-[id]/vc-[id]/vlan-[id]
    -- sys/switch-[id]/lanmon-eth/mon-[name]/vc-[id]/vlan-[id]
    -- sys/switch-[id]/border-eth/ethestc-ep-slot-[slotId]port-[portId]/vlan-[id]
    -- sys/tbh/border-eth/ethestc-ep-slot-[slotId]port-[portId]/vlan-[id]
    -- sys/switch-[id]/access-eth/slot-[slotId]-aggr-port-[aggrPortId]/ethestc-ep-slot-[slotId]port-[portId]/vlan-[id]
    -- sys/switch-[id]/border-eth/slot-[slotId]-aggr-port-[aggrPortId]/ethestc-ep-slot-[slotId]port-[portId]/vlan-[id]
    -- sys/tbh/border-eth/slot-[slotId]-aggr-port-[aggrPortId]/ethestc-ep-slot-[slotId]port-[portId]/vlan-[id]
    -- sys/switch-[id]/lanmon-eth/mon-[name]/slot-[slotId]-aggr-port-[aggrPortId]/ethestc-ep-slot-[slotId]port-[portId]/vlan-[id]
    -- sys/switch-[id]/border-fc/slot-[slotId]-aggr-port-[aggrPortId]/ethestc-ep-slot-[slotId]port-[portId]/vlan-[id]
    -- sys/switch-[id]/phys/slot-[slotId]-aggr-port-[aggrPortId]/ethestc-ep-slot-[slotId]port-[portId]/vlan-[id]
    -- sys/switch-[id]/ssp-lanmon-eth/ssp-mon-session[name]/slot-[slotId]-aggr-port-[aggrPortId]/ethestc-ep-slot-[slotId]port-[portId]/vlan-[id]
    -- sys/switch-[id]/border-eth/pc-[portId]/vlan-[id]
    -- sys/tbh/border-eth/pc-[portId]/vlan-[id]
    -- sys/switch-[id]/lanmon-eth/mon-[name]/pc-[portId]/vlan-[id]
    -- sys/switch-[id]/border-eth/vlan-[id]
    -- sys/tbh/border-eth/vlan-[id]
    -- sys/switch-[id]/border-eth/ep-slot-[slotId]port-[portId]/vlan-[id]
    -- sys/tbh/border-eth/ep-slot-[slotId]port-[portId]/vlan-[id]
    -- sys/switch-[id]/access-eth/slot-[slotId]-aggr-port-[aggrPortId]/ep-slot-[slotId]port-[portId]/vlan-[id]
    -- sys/switch-[id]/border-eth/slot-[slotId]-aggr-port-[aggrPortId]/ep-slot-[slotId]port-[portId]/vlan-[id]
    -- sys/tbh/border-eth/slot-[slotId]-aggr-port-[aggrPortId]/ep-slot-[slotId]port-[portId]/vlan-[id]
    -- sys/switch-[id]/lanmon-eth/mon-[name]/slot-[slotId]-aggr-port-[aggrPortId]/ep-slot-[slotId]port-[portId]/vlan-[id]
    -- sys/switch-[id]/border-fc/slot-[slotId]-aggr-port-[aggrPortId]/ep-slot-[slotId]port-[portId]/vlan-[id]
    -- sys/switch-[id]/phys/slot-[slotId]-aggr-port-[aggrPortId]/ep-slot-[slotId]port-[portId]/vlan-[id]
    -- sys/switch-[id]/ssp-lanmon-eth/ssp-mon-session[name]/slot-[slotId]-aggr-port-[aggrPortId]/ep-slot-[slotId]port-[portId]/vlan-[id]
    -- sys/switch-[id]/border-eth/pc-[portId]/vlan-[id]
    -- sys/tbh/border-eth/pc-[portId]/vlan-[id]
    -- sys/switch-[id]/lanmon-eth/mon-[name]/pc-[portId]/vlan-[id]
    -- sys/switch-[id]/lanmon-eth/mon-[name]/vlan-[id]
    -- sys/switch-[id]/border-fc/vlan-[id]
    -- sys/switch-[id]/border-fc/fcoesan-ep-slot-[slotId]port-[portId]/vlan-[id]
    -- sys/switch-[id]/access-eth/slot-[slotId]-aggr-port-[aggrPortId]/fcoesan-ep-slot-[slotId]port-[portId]/vlan-[id]
    -- sys/switch-[id]/border-eth/slot-[slotId]-aggr-port-[aggrPortId]/fcoesan-ep-slot-[slotId]port-[portId]/vlan-[id]
    -- sys/tbh/border-eth/slot-[slotId]-aggr-port-[aggrPortId]/fcoesan-ep-slot-[slotId]port-[portId]/vlan-[id]
    -- sys/switch-[id]/lanmon-eth/mon-[name]/slot-[slotId]-aggr-port-[aggrPortId]/fcoesan-ep-slot-[slotId]port-[portId]/vlan-[id]
    -- sys/switch-[id]/border-fc/slot-[slotId]-aggr-port-[aggrPortId]/fcoesan-ep-slot-[slotId]port-[portId]/vlan-[id]
    -- sys/switch-[id]/phys/slot-[slotId]-aggr-port-[aggrPortId]/fcoesan-ep-slot-[slotId]port-[portId]/vlan-[id]
    -- sys/switch-[id]/ssp-lanmon-eth/ssp-mon-session[name]/slot-[slotId]-aggr-port-[aggrPortId]/fcoesan-ep-slot-[slotId]port-[portId]/vlan-[id]
    -- sys/switch-[id]/border-fc/fcoesan-pc-[portId]/vlan-[id]
    -- fabric/lan/profiles/vnic-[name]/vlan-[id]
        -- fltSwVlanExtrasecondaryvlansperprimary

-- sm:Hotfix
    -- sec-svc/slot-[slotId]/app-inst-[appName]/hotfix-[version]
    -- sec-svc/slot-[slotId]/app-inst-[appName]-[identifier]/hotfix-[version]
        -- fltSmHotfixHotfixInstallFailed
        -- fltSmHotfixHotfixError

-- firmware:Runnable
    -- sys/chassis-[id]/blade-[slotId]/adaptor-[id]/mgmt/fw-runnable
    -- sys/rack-unit-[id]/adaptor-[id]/mgmt/fw-runnable
    -- sys/chassis-[id]/blade-[slotId]/ext-board-[id]/boardController/mgmt/fw-runnable
    -- sys/rack-unit-[id]/ext-board-[id]/boardController/mgmt/fw-runnable
    -- sys/chassis-[id]/blade-[slotId]/boardController/mgmt/fw-runnable
    -- sys/rack-unit-[id]/boardController/mgmt/fw-runnable
    -- sys/chassis-[id]/blade-[slotId]/ext-board-[id]/mgmt/fw-runnable
    -- sys/rack-unit-[id]/ext-board-[id]/mgmt/fw-runnable
    -- sys/chassis-[id]/blade-[slotId]/mgmt/fw-runnable
    -- sys/rack-unit-[id]/mgmt/fw-runnable
    -- sys/fex-[id]/mgmt/fw-runnable
    -- sys/chassis-[id]/slot-[id]/mgmt/fw-runnable
    -- sys/fex-[id]/slot-[id]/mgmt/fw-runnable
    -- sys/chassis-[id]/sw-slot-[id]/mgmt/fw-runnable
    -- sys/switch-[id]/mgmt/fw-runnable
    -- sys/mgmt/fw-runnable
        -- fltFirmwareRunnableAdapterUpgradeRequired

-- uuidpool:Pool
    -- org-[name]/uuid-pool-[name]
        -- fltUuidpoolPoolEmpty

-- vnic:Profile
    -- fabric/lan/profiles/vnic-[name]
        -- fltVnicProfileProfileConfigIncorrect

-- dcx:VIf
    -- sys/chassis-[id]/blade-[slotId]/adaptor-[id]/ext-eth-[id]/vif-[id]
    -- sys/rack-unit-[id]/adaptor-[id]/ext-eth-[id]/vif-[id]
    -- sys/chassis-[id]/blade-[slotId]/adaptor-[id]/host-eth-[id]/fcoe/vif-[id]
    -- sys/rack-unit-[id]/adaptor-[id]/host-eth-[id]/fcoe/vif-[id]
    -- sys/chassis-[id]/blade-[slotId]/adaptor-[id]/host-fc-[id]/fcoe/vif-[id]
    -- sys/rack-unit-[id]/adaptor-[id]/host-fc-[id]/fcoe/vif-[id]
    -- sys/chassis-[id]/blade-[slotId]/adaptor-[id]/host-eth-[id]/vif-[id]
    -- sys/rack-unit-[id]/adaptor-[id]/host-eth-[id]/vif-[id]
    -- sys/chassis-[id]/blade-[slotId]/adaptor-[id]/host-fc-[id]/vif-[id]
    -- sys/rack-unit-[id]/adaptor-[id]/host-fc-[id]/vif-[id]
    -- sys/chassis-[id]/blade-[slotId]/adaptor-[id]/host-service-eth-[id]/vif-[id]
    -- sys/rack-unit-[id]/adaptor-[id]/host-service-eth-[id]/vif-[id]
        -- fltDcxVIfLinkState

-- policy:ControlEp
    -- sys/control-ep-[type]
        -- fltPolicyControlEpSuspendModeActive
        -- fsmStFailPolicyControlEpOperate:Resolve
        -- fsmRmtErrPolicyControlEpOperate:Resolve
        -- fsmFailPolicyControlEpOperate

-- compute:ABoard
        -- fltComputeABoardThermalProblem
        -- fltComputeABoardPowerUsageProblem
        -- fltComputeABoardMotherBoardVoltageThresholdUpperNonRecoverable
        -- fltComputeABoardMotherBoardVoltageThresholdLowerNonRecoverable
        -- fltComputeABoardMotherBoardVoltageUpperThresholdCritical
        -- fltComputeABoardMotherBoardVoltageLowerThresholdCritical

-- comm:Ssh
    -- sys/svc-ext/ssh-svc
        -- fltCommSshSSh3desUsageNotRecommended

-- sw:SspEthMon
    -- sys/switch-[id]/ssp-lanmon-eth/ssp-mon-session[name]
        -- fsmStFailSwSspEthMonDeploy:ReenableSspEthMon
        -- fsmStFailSwSspEthMonDeploy:UpdateSspEthMon
        -- fsmRmtErrSwSspEthMonDeploy:ReenableSspEthMon
        -- fsmRmtErrSwSspEthMonDeploy:UpdateSspEthMon
        -- fsmFailSwSspEthMonDeploy

-- extpol:Client
    -- extpol/reg/clients/client-[id]
        -- fltExtpolClientClientLostConnectivity
        -- fltExtpolClientGracePeriodWarning
        -- fltExtpolClientGracePeriodWarning2
        -- fltExtpolClientGracePeriodWarning3
        -- fltExtpolClientGracePeriodWarning4
        -- fltExtpolClientGracePeriodWarning5
        -- fltExtpolClientGracePeriodWarning6
        -- fltExtpolClientGracePeriodWarning7
        -- fltExtpolClientGracePeriodWarning1

-- extvmm:KeyStore
    -- sys/extvm-mgmt/key-store
        -- fsmStFailExtvmmKeyStoreCertInstall:SetLocal
        -- fsmStFailExtvmmKeyStoreCertInstall:SetPeer
        -- fsmRmtErrExtvmmKeyStoreCertInstall:SetLocal
        -- fsmRmtErrExtvmmKeyStoreCertInstall:SetPeer
        -- fsmFailExtvmmKeyStoreCertInstall

-- equipment:Tpm
    -- sys/chassis-[id]/blade-[slotId]/board/Tpm-[id]
    -- sys/rack-unit-[id]/board/Tpm-[id]
        -- fltEquipmentTpmSlaveTpm

-- comm:DeviceManager
    -- sys/device-manager-[name]
        -- fltCommDeviceManagerCommDeviceRegistrationPending
        -- fltCommDeviceManagerCommDeviceRegistrationFailed
        -- fltCommDeviceManagerCommDeviceUnRegistrationFailed
        -- fltCommDeviceManagerCommDeviceSftunnelDown
        -- fltCommDeviceManagerCommDeviceSfipproxyDown
        -- fltCommDeviceManagerCommDeviceManagerNotReachable

-- epqos:DefinitionDelTask
    -- org-[name]/ep-qos-deletion-[defIntId]
        -- fsmStFailEpqosDefinitionDelTaskRemove:Local
        -- fsmStFailEpqosDefinitionDelTaskRemove:Peer
        -- fsmRmtErrEpqosDefinitionDelTaskRemove:Local
        -- fsmRmtErrEpqosDefinitionDelTaskRemove:Peer
        -- fsmFailEpqosDefinitionDelTaskRemove

-- sd:Link
    -- sys-secsvc/slot-[slotId]/app-inst-[appInstId]/ldu-[slotId]/
    -- sys-secsvc/ld-[name]/ldu-[slotId]/
        -- fltSdLinkVnicConfigFail
        -- fsmStFailSdLinkUpdateInterfaceStatus:SendStatus
        -- fsmRmtErrSdLinkUpdateInterfaceStatus:SendStatus
        -- fsmFailSdLinkUpdateInterfaceStatus

-- sw:Phys
    -- sys/switch-[id]/phys
        -- fsmStFailSwPhysConfPhysical:ConfigSwA
        -- fsmStFailSwPhysConfPhysical:ConfigSwB
        -- fsmStFailSwPhysConfPhysical:PortInventorySwA
        -- fsmStFailSwPhysConfPhysical:PortInventorySwB
        -- fsmStFailSwPhysConfPhysical:VerifyPhysConfig
        -- fsmRmtErrSwPhysConfPhysical:ConfigSwA
        -- fsmRmtErrSwPhysConfPhysical:ConfigSwB
        -- fsmRmtErrSwPhysConfPhysical:PortInventorySwA
        -- fsmRmtErrSwPhysConfPhysical:PortInventorySwB
        -- fsmRmtErrSwPhysConfPhysical:VerifyPhysConfig
        -- fsmFailSwPhysConfPhysical

-- macpool:Pool
    -- org-[name]/mac-pool-[name]
        -- fltMacpoolPoolEmpty

-- compute:Pool
    -- org-[name]/compute-pool-[name]
        -- fltComputePoolEmpty

-- aaa:Ep
    -- sys/
        -- fsmStFailAaaEpUpdateEp:SetEpLocal
        -- fsmStFailAaaEpUpdateEp:SetEpPeer
        -- fsmRmtErrAaaEpUpdateEp:SetEpLocal
        -- fsmRmtErrAaaEpUpdateEp:SetEpPeer
        -- fsmFailAaaEpUpdateEp

-- sd:PreAllocatedVnic
    -- sys-secsvc/slot-[slotId]/app-inst-[appInstId]/pre-allocated-vnic-[portType]-[mgmtSubType]
        -- fltSdPreAllocatedVnicVnicPreAllocationFail

-- sd:AppAttributeCtrl
    -- sys-secsvc/slot-[slotId]/app-inst-[appInstId]/app-attribute-ctrl
        -- fsmStFailSdAppAttributeCtrlGetAppAttributes:GetAttributes
        -- fsmRmtErrSdAppAttributeCtrlGetAppAttributes:GetAttributes
        -- fsmFailSdAppAttributeCtrlGetAppAttributes

-- extvmm:MasterExtKey
    -- sys/extvm-mgmt/ext-key
        -- fsmStFailExtvmmMasterExtKeyConfig:SetLocal
        -- fsmStFailExtvmmMasterExtKeyConfig:SetPeer
        -- fsmRmtErrExtvmmMasterExtKeyConfig:SetLocal
        -- fsmRmtErrExtvmmMasterExtKeyConfig:SetPeer
        -- fsmFailExtvmmMasterExtKeyConfig

-- mgmt:PmonEntry
    -- sys/mgmt-entity-[id]/[name]
        -- fltMgmtPmonEntryFPRM process failure
        -- fltMgmtPmonEntryProcessRestarted

-- sysdebug:MemoryProcess
    -- sys/sysdebug/mem-overall/process-[process]-[pid]
        -- fltSysdebugMemoryProcessProcessStackMemoryHigh
        -- fltSysdebugMemoryProcessProcessHeapMemoryHigh

-- firmware:ActivateIssue
    -- sys/chassis-[id]/blade-[slotId]/adaptor-[id]/host-eth-[id]/fw-[deployment]/activation-issue
    -- sys/rack-unit-[id]/adaptor-[id]/host-eth-[id]/fw-[deployment]/activation-issue
    -- sys/chassis-[id]/blade-[slotId]/adaptor-[id]/host-fc-[id]/fw-[deployment]/activation-issue
    -- sys/rack-unit-[id]/adaptor-[id]/host-fc-[id]/fw-[deployment]/activation-issue
    -- sys/chassis-[id]/blade-[slotId]/ext-board-[id]/bios/fw-[deployment]/activation-issue
    -- sys/rack-unit-[id]/ext-board-[id]/bios/fw-[deployment]/activation-issue
    -- sys/chassis-[id]/blade-[slotId]/bios/fw-[deployment]/activation-issue
    -- sys/rack-unit-[id]/bios/fw-[deployment]/activation-issue
    -- capabilities/fw-[deployment]/activation-issue
    -- capabilities/ep/mgmt-ext/fw-[deployment]/activation-issue
    -- sys/chassis-[id]/epmfpga-[slot]/fw-[deployment]/activation-issue
    -- sys/chassis-[id]/fpga/fw-[deployment]/activation-issue
    -- sys/chassis-[id]/rommon/fw-[deployment]/activation-issue
    -- sys/chassis-[id]/Ssd/fw-[deployment]/activation-issue
    -- sys/chassis-[id]/blade-[slotId]/board/graphics-card-[id]/fw-[deployment]/activation-issue
    -- sys/rack-unit-[id]/board/graphics-card-[id]/fw-[deployment]/activation-issue
    -- sys/chassis-[id]/blade-[slotId]/adaptor-[id]/mgmt/fw-[deployment]/activation-issue
    -- sys/rack-unit-[id]/adaptor-[id]/mgmt/fw-[deployment]/activation-issue
    -- sys/chassis-[id]/blade-[slotId]/ext-board-[id]/boardController/mgmt/fw-[deployment]/activation-issue
    -- sys/rack-unit-[id]/ext-board-[id]/boardController/mgmt/fw-[deployment]/activation-issue
    -- sys/chassis-[id]/blade-[slotId]/boardController/mgmt/fw-[deployment]/activation-issue
    -- sys/rack-unit-[id]/boardController/mgmt/fw-[deployment]/activation-issue
    -- sys/chassis-[id]/blade-[slotId]/ext-board-[id]/mgmt/fw-[deployment]/activation-issue
    -- sys/rack-unit-[id]/ext-board-[id]/mgmt/fw-[deployment]/activation-issue
    -- sys/chassis-[id]/blade-[slotId]/mgmt/fw-[deployment]/activation-issue
    -- sys/rack-unit-[id]/mgmt/fw-[deployment]/activation-issue
    -- sys/fex-[id]/mgmt/fw-[deployment]/activation-issue
    -- sys/chassis-[id]/slot-[id]/mgmt/fw-[deployment]/activation-issue
    -- sys/fex-[id]/slot-[id]/mgmt/fw-[deployment]/activation-issue
    -- sys/chassis-[id]/sw-slot-[id]/mgmt/fw-[deployment]/activation-issue
    -- sys/switch-[id]/mgmt/fw-[deployment]/activation-issue
    -- sys/mgmt/fw-[deployment]/activation-issue
    -- sys/chassis-[id]/blade-[slotId]/os-ctrl/fw-[deployment]/activation-issue
    -- sys/chassis-[id]/blade-[slotId]/os-ctrl/fw-[deployment]/activation-issue
    -- sys/rack-unit-[id]/os-ctrl/fw-[deployment]/activation-issue
    -- sys/os-ctrl/fw-[deployment]/activation-issue
    -- sys/chassis-[id]/blade-[slotId]/board/storage-[type]-[id]/fw-[deployment]/activation-issue
    -- sys/rack-unit-[id]/board/storage-[type]-[id]/fw-[deployment]/activation-issue
    -- sys/chassis-[id]/blade-[slotId]/board/storage-flexflash-[id]/fw-[deployment]/activation-issue
    -- sys/rack-unit-[id]/board/storage-flexflash-[id]/fw-[deployment]/activation-issue
    -- sys/chassis-[id]/blade-[slotId]/board/storage-[type]-[id]/disk-[id]/fw-[deployment]/activation-issue
    -- sys/rack-unit-[id]/board/storage-[type]-[id]/disk-[id]/fw-[deployment]/activation-issue
        -- fltFirmwareActivateIssueImageVersionMismatch

-- stats:CollectionPolicy
    -- stats/coll-policy-[name]
        -- fsmStFailStatsCollectionPolicyUpdateEp:SetEpA
        -- fsmStFailStatsCollectionPolicyUpdateEp:SetEpB
        -- fsmRmtErrStatsCollectionPolicyUpdateEp:SetEpA
        -- fsmRmtErrStatsCollectionPolicyUpdateEp:SetEpB
        -- fsmFailStatsCollectionPolicyUpdateEp

-- aaa:ProviderGroup
    -- sys/ldap-ext/providergroup-[name]
    -- sys/radius-ext/providergroup-[name]
    -- sys/tacacs-ext/providergroup-[name]
        -- fltAaaProviderGroupProvidergroup
        -- fltAaaProviderGroupProvidergroupsize

-- firmware:PackItem
    -- org-[name]/pack-image-[hwVendor]|[hwModel]|[type]
    -- org-[name]/fw-catalog-pack-[name]/pack-image-[hwVendor]|[hwModel]|[type]
    -- org-[name]/pack-image-[hwVendor]|[hwModel]|[type]
    -- org-[name]/fw-infra-pack-[name]/pack-image-[hwVendor]|[hwModel]|[type]
    -- org-[name]/fw-platform-pack-[name]/pack-image-[hwVendor]|[hwModel]|[type]
    -- org-[name]/fw-host-pack-[name]/pack-image-[hwVendor]|[hwModel]|[type]
    -- org-[name]/fw-mgmt-pack-[name]/pack-image-[hwVendor]|[hwModel]|[type]
        -- fltFirmwarePackItemImageMissing

-- sd:Hotfix
    -- sys-secsvc/slot-[slotId]/app-inst-[appInstId]/hotfix-[hotfixId]
        -- fsmStFailSdHotfixInstallHotfix:Install
        -- fsmStFailSdHotfixInstallHotfix:UpdateHotfix
        -- fsmStFailSdHotfixUninstallHotfix:Uninstall
        -- fsmStFailSdHotfixUninstallHotfix:UpdateHotfix
        -- fsmRmtErrSdHotfixInstallHotfix:Install
        -- fsmRmtErrSdHotfixInstallHotfix:UpdateHotfix
        -- fsmRmtErrSdHotfixUninstallHotfix:Uninstall
        -- fsmRmtErrSdHotfixUninstallHotfix:UpdateHotfix
        -- fsmFailSdHotfixInstallHotfix
        -- fsmFailSdHotfixUninstallHotfix

-- application:Downloader
    -- sys/app-catalogue/dnld-[fileName]
        -- fsmStFailApplicationDownloaderDownload:Local
        -- fsmStFailApplicationDownloaderDownload:UnpackLocal
        -- fsmStFailApplicationDownloaderDownload:Verify
        -- fsmRmtErrApplicationDownloaderDownload:Local
        -- fsmRmtErrApplicationDownloaderDownload:UnpackLocal
        -- fsmRmtErrApplicationDownloaderDownload:Verify
        -- fsmFailApplicationDownloaderDownload

-- policy:ControlledType
    -- sys/control-ep-[type]/ctrlled-type-[type]
    -- sys/control-ep-[type]/comm-ctrl/ctrlled-type-[type]
    -- sys/control-ep-[type]/cfg-backup-ctrl/ctrlled-type-[type]
    -- sys/control-ep-[type]/datetime-ctrl/ctrlled-type-[type]
    -- sys/control-ep-[type]/discovery-ctrl/ctrlled-type-[type]
    -- sys/control-ep-[type]/dns-ctrl/ctrlled-type-[type]
    -- sys/control-ep-[type]/fault-ctrl/ctrlled-type-[type]
    -- sys/control-ep-[type]/fabric-fw-ctrl/ctrlled-type-[type]
    -- sys/control-ep-[type]/mep-ctrl/ctrlled-type-[type]
    -- sys/control-ep-[type]/monitoring-ctrl/ctrlled-type-[type]
    -- sys/control-ep-[type]/powermgmt-ctrl/ctrlled-type-[type]
    -- sys/control-ep-[type]/psu-ctrl/ctrlled-type-[type]
    -- sys/control-ep-[type]/security-ctrl/ctrlled-type-[type]
        -- fsmStFailPolicyControlledTypeOperate:ResolveAll
        -- fsmRmtErrPolicyControlledTypeOperate:ResolveAll
        -- fsmFailPolicyControlledTypeOperate

-- fabric:Mon
        -- fltFabricMonSpanConfigFail

-- power:ChassisMember
    -- sys/power-ep/group-[name]/ch-member-[id]
        -- fltPowerChassisMemberPowerGroupCapInsufficient
        -- fltPowerChassisMemberChassisFirmwareProblem
        -- fltPowerChassisMemberChassisPsuInsufficient
        -- fltPowerChassisMemberChassisPsuRedundanceFailure

-- fabric:ComputeSlotEp
    -- fabric/server/chassis-[chassisId]/slot-[slotId]
        -- fltFabricComputeSlotEpMisplacedInChassisSlot
        -- fltFabricComputeSlotEpServerIdentificationProblem
        -- fltFabricComputeSlotEpBladeDecommissionFail
        -- fsmStFailFabricComputeSlotEpIdentify:ExecuteLocal
        -- fsmStFailFabricComputeSlotEpIdentify:ExecutePeer
        -- fsmRmtErrFabricComputeSlotEpIdentify:ExecuteLocal
        -- fsmRmtErrFabricComputeSlotEpIdentify:ExecutePeer
        -- fsmFailFabricComputeSlotEpIdentify

-- fabric:SspEthMon
    -- fabric/ssppktcapmon/ssp-mon-[name]
        -- fltFabricSspEthMonDelAllSessEnabled

-- memory:Array
    -- sys/chassis-[id]/blade-[slotId]/board/memarray-[id]
    -- sys/rack-unit-[id]/board/memarray-[id]
        -- fltMemoryArrayVoltageThresholdNonCritical
        -- fltMemoryArrayVoltageThresholdCritical
        -- fltMemoryArrayVoltageThresholdNonRecoverable
        -- fltMemoryArrayServer-bad-memorry

-- pki:TpAutoImport
    -- sys/pki-ext/tpAutoImport-
        -- fltPkiTpAutoImportTp-auto-import-failure
        -- fltPkiTpAutoImportTp-auto-import-attempt

-- sd:ClusterBootstrap
    -- sys-secsvc/slot-[slotId]/app-inst-[appInstId]/cluster-bootstrap
    -- sys-secsvc/ld-[name]/cluster-bootstrap
        -- fsmStFailSdClusterBootstrapUpdateClusterConfiguration:SendConfig
        -- fsmRmtErrSdClusterBootstrapUpdateClusterConfiguration:SendConfig
        -- fsmFailSdClusterBootstrapUpdateClusterConfiguration

-- fcpool:Initiators
    -- org-[name]/wwn-pool-[name]
        -- fltFcpoolInitiatorsEmpty

-- sd:AppLduLink
    -- sys-secsvc/slot-[slotId]/app-inst-[appInstId]/ldu-[slotId]/app-ldulink-[name]-[endpoint1AppInstId]-[endpoint2AppInstId]
    -- sys-secsvc/ld-[name]/ldu-[slotId]/app-ldulink-[name]-[endpoint1AppInstId]-[endpoint2AppInstId]
        -- fltSdAppLduLinkAppLduLinkEndpoint1VnicConfigFail
        -- fltSdAppLduLinkAppLduLinkEndpoint2VnicConfigFail

-- ippool:Pool
    -- fabric/lan/network-sets/ip-pool-[name]
    -- org-[name]/ip-pool-[name]
        -- fltIppoolPoolEmpty

-- sw:FcSanBorder
    -- sys/switch-[id]/border-fc
        -- fsmStFailSwFcSanBorderDeploy:UpdateConnectivity
        -- fsmStFailSwFcSanBorderActivateZoneSet:UpdateZones
        -- fsmRmtErrSwFcSanBorderDeploy:UpdateConnectivity
        -- fsmRmtErrSwFcSanBorderActivateZoneSet:UpdateZones
        -- fsmFailSwFcSanBorderDeploy
        -- fsmFailSwFcSanBorderActivateZoneSet

-- comm:SnmpUser
    -- sys/svc-ext/snmp-svc/snmpv3-user-[name]
        -- fltCommSnmpUserSnmpUserNotDeployed

-- nh:TableHolder
    -- sys/tbh
        -- fsmStFailNhTableHolderConfigureLinks:ApplyConfig
        -- fsmStFailNhTableHolderConfigureLinks:VerifyLinkConfig
        -- fsmStFailNhTableHolderBootstrapLinks:ApplyConfig
        -- fsmRmtErrNhTableHolderConfigureLinks:ApplyConfig
        -- fsmRmtErrNhTableHolderConfigureLinks:VerifyLinkConfig
        -- fsmRmtErrNhTableHolderBootstrapLinks:ApplyConfig
        -- fsmFailNhTableHolderConfigureLinks
        -- fsmFailNhTableHolderBootstrapLinks

-- storage:VirtualDrive
    -- sys/chassis-[id]/blade-[slotId]/board/storage-[type]-[id]/vd-[id]
    -- sys/rack-unit-[id]/board/storage-[type]-[id]/vd-[id]
        -- fltStorageVirtualDriveInoperable
        -- fltStorageVirtualDriveDegraded
        -- fltStorageVirtualDriveReconstructionFailed
        -- fltStorageVirtualDriveConsistencyCheckFailed

-- license:SmartConfig
    -- sys/license/license-config-[operation]
        -- fsmStFailLicenseSmartConfigSetConfig:Local
        -- fsmRmtErrLicenseSmartConfigSetConfig:Local
        -- fsmFailLicenseSmartConfigSetConfig

-- pki:TP
    -- sys/pki-ext/tp-[name]
        -- fltPkiTPStatus

-- vnic:ProfileSet
    -- fabric/lan/profiles
        -- fsmStFailVnicProfileSetDeploy:Local
        -- fsmStFailVnicProfileSetDeploy:Peer
        -- fsmStFailVnicProfileSetDeployAlias:Local
        -- fsmStFailVnicProfileSetDeployAlias:Peer
        -- fsmRmtErrVnicProfileSetDeploy:Local
        -- fsmRmtErrVnicProfileSetDeploy:Peer
        -- fsmRmtErrVnicProfileSetDeployAlias:Local
        -- fsmRmtErrVnicProfileSetDeployAlias:Peer
        -- fsmFailVnicProfileSetDeploy
        -- fsmFailVnicProfileSetDeployAlias

-- fabric:Vlan
    -- fabric/eth-estc/[id]/net-[name]
    -- fabric/eth-estc/net-[name]
    -- fabric/lan/[id]/net-[name]
    -- fabric/lan/net-[name]
        -- fltFabricVlanVlanConflictPermit
        -- fltFabricVlanMisconfigured-mcast-policy
        -- fltFabricVlanPrimaryVlanMissingForIsolated
        -- fltFabricVlanPrimaryVlanMissingForCommunity
        -- fltFabricVlanMismatch-a
        -- fltFabricVlanMismatch-b
        -- fltFabricVlanErrorAssocPrimary

-- nfs:MountInst
    -- sys/switch-[id]/nfs-mount-inst-[name]
        -- fsmStFailNfsMountInstMount:MountLocal
        -- fsmStFailNfsMountInstMount:MountPeer
        -- fsmStFailNfsMountInstMount:RegisterClient
        -- fsmStFailNfsMountInstMount:VerifyRegistration
        -- fsmStFailNfsMountInstUnmount:UnmountLocal
        -- fsmStFailNfsMountInstUnmount:UnmountPeer
        -- fsmRmtErrNfsMountInstMount:MountLocal
        -- fsmRmtErrNfsMountInstMount:MountPeer
        -- fsmRmtErrNfsMountInstMount:RegisterClient
        -- fsmRmtErrNfsMountInstMount:VerifyRegistration
        -- fsmRmtErrNfsMountInstUnmount:UnmountLocal
        -- fsmRmtErrNfsMountInstUnmount:UnmountPeer
        -- fsmFailNfsMountInstMount
        -- fsmFailNfsMountInstUnmount

-- firmware:Updatable
    -- sys/chassis-[id]/blade-[slotId]/ext-board-[id]/bios/fw-updatable
    -- sys/rack-unit-[id]/ext-board-[id]/bios/fw-updatable
    -- sys/chassis-[id]/blade-[slotId]/bios/fw-updatable
    -- sys/rack-unit-[id]/bios/fw-updatable
    -- sys/chassis-[id]/epmfpga-[slot]/fw-updatable
    -- sys/chassis-[id]/fpga/fw-updatable
    -- sys/chassis-[id]/rommon/fw-updatable
    -- sys/chassis-[id]/Ssd/fw-updatable
    -- sys/chassis-[id]/blade-[slotId]/adaptor-[id]/mgmt/fw-updatable
    -- sys/rack-unit-[id]/adaptor-[id]/mgmt/fw-updatable
    -- sys/chassis-[id]/blade-[slotId]/ext-board-[id]/boardController/mgmt/fw-updatable
    -- sys/rack-unit-[id]/ext-board-[id]/boardController/mgmt/fw-updatable
    -- sys/chassis-[id]/blade-[slotId]/boardController/mgmt/fw-updatable
    -- sys/rack-unit-[id]/boardController/mgmt/fw-updatable
    -- sys/chassis-[id]/blade-[slotId]/ext-board-[id]/mgmt/fw-updatable
    -- sys/rack-unit-[id]/ext-board-[id]/mgmt/fw-updatable
    -- sys/chassis-[id]/blade-[slotId]/mgmt/fw-updatable
    -- sys/rack-unit-[id]/mgmt/fw-updatable
    -- sys/fex-[id]/mgmt/fw-updatable
    -- sys/chassis-[id]/slot-[id]/mgmt/fw-updatable
    -- sys/fex-[id]/slot-[id]/mgmt/fw-updatable
    -- sys/chassis-[id]/sw-slot-[id]/mgmt/fw-updatable
    -- sys/switch-[id]/mgmt/fw-updatable
    -- sys/mgmt/fw-updatable
    -- sys/chassis-[id]/blade-[slotId]/os-ctrl/fw-updatable
    -- sys/chassis-[id]/blade-[slotId]/os-ctrl/fw-updatable
    -- sys/rack-unit-[id]/os-ctrl/fw-updatable
    -- sys/os-ctrl/fw-updatable
        -- fltFirmwareUpdatableImageUnusable

-- adaptor:Unit
    -- sys/chassis-[id]/blade-[slotId]/adaptor-[id]
    -- sys/rack-unit-[id]/adaptor-[id]
        -- fltAdaptorUnitUnidentifiable-fru
        -- fltAdaptorUnitMissing
        -- fltAdaptorUnitAdaptorReachability

-- fabric:VlanGroupReq
    -- org-[name]/vlan-group-req-[name]
        -- fltFabricVlanGroupReqVlanGroupPermitUnresolved

-- firmware:PlatformPack
    -- org-[name]/fw-platform-pack-[name]
        -- fltFirmwarePlatformPackBundleVersionMissing
        -- fsmStFailFirmwarePlatformPackPlatformVersion:Restore
        -- fsmStFailFirmwarePlatformPackPlatformVersion:WaitForReady
        -- fsmRmtErrFirmwarePlatformPackPlatformVersion:Restore
        -- fsmRmtErrFirmwarePlatformPackPlatformVersion:WaitForReady
        -- fsmFailFirmwarePlatformPackPlatformVersion

-- equipment:Fpga
    -- sys/chassis-[id]/fpga
        -- fltEquipmentFpgaFpgaUpgradeRequired

-- comm:DateTime
    -- sys/svc-ext/datetime-svc
        -- fltCommDateTimeCommTimeZoneInvalid
        -- fltCommDateTimeCommNtpConfigurationFailed

-- observe:Observed
    -- extpol/reg/clients/client-[id]/observed-[dataSrcSysId]-[id]
    -- extpol/reg/controllers/contro-[id]/observed-[dataSrcSysId]-[id]
    -- extpol/reg/providers/prov-[type]/observed-[dataSrcSysId]-[id]
    -- extpol/reg/observed-[dataSrcSysId]-[id]
    -- observe/observed-[dataSrcSysId]-[id]
        -- fsmStFailObserveObservedResolvePolicyFsm:Execute
        -- fsmStFailObserveObservedResolveResourceFsm:Execute
        -- fsmStFailObserveObservedResolveVMFsm:Execute
        -- fsmStFailObserveObservedResolveControllerFsm:Execute
        -- fsmRmtErrObserveObservedResolvePolicyFsm:Execute
        -- fsmRmtErrObserveObservedResolveResourceFsm:Execute
        -- fsmRmtErrObserveObservedResolveVMFsm:Execute
        -- fsmRmtErrObserveObservedResolveControllerFsm:Execute
        -- fsmFailObserveObservedResolvePolicyFsm
        -- fsmFailObserveObservedResolveResourceFsm
        -- fsmFailObserveObservedResolveVMFsm
        -- fsmFailObserveObservedResolveControllerFsm

-- network:Element
    -- sys/switch-[id]
        -- fltNetworkElementInoperable
        -- fltNetworkElementInventoryFailed
        -- fltNetworkElementThermalThresholdCritical
        -- fltNetworkElementRemoved
        -- fltNetworkElementMemoryerror
        -- fltNetworkElementSamconfig

-- sw:AccessDomain
    -- sys/switch-[id]/access-eth
        -- fsmStFailSwAccessDomainDeploy:UpdateConnectivity
        -- fsmRmtErrSwAccessDomainDeploy:UpdateConnectivity
        -- fsmFailSwAccessDomainDeploy

-- equipment:IOCard
    -- sys/chassis-[id]/slot-[id]
    -- sys/fex-[id]/slot-[id]
        -- fltEquipmentIOCardRemoved
        -- fltEquipmentIOCardThermalProblem
        -- fltEquipmentIOCardFirmwareUpgrade
        -- fltEquipmentIOCardUnsupportedConnectivity
        -- fltEquipmentIOCardUnacknowledged
        -- fltEquipmentIOCardPeerDisconnected
        -- fltEquipmentIOCardIdentity
        -- fltEquipmentIOCardAutoUpgradingFirmware
        -- fltEquipmentIOCardInaccessible
        -- fltEquipmentIOCardPost-failure
        -- fltEquipmentIOCardThermalThresholdNonCritical
        -- fltEquipmentIOCardThermalThresholdCritical
        -- fltEquipmentIOCardThermalThresholdNonRecoverable
        -- fsmStFailEquipmentIOCardResetCmc:Execute
        -- fsmStFailEquipmentIOCardMuxOffline:CleanupEntries
        -- fsmStFailEquipmentIOCardResetIom:Execute
        -- fsmRmtErrEquipmentIOCardResetCmc:Execute
        -- fsmRmtErrEquipmentIOCardMuxOffline:CleanupEntries
        -- fsmRmtErrEquipmentIOCardResetIom:Execute
        -- fsmFailEquipmentIOCardResetCmc
        -- fsmFailEquipmentIOCardMuxOffline
        -- fsmFailEquipmentIOCardResetIom

-- firmware:Status
    -- sys/chassis-[id]/blade-[slotId]/fw-status
    -- sys/rack-unit-[id]/fw-status
    -- sys/chassis-[id]/slot-[id]/fw-status
    -- sys/fex-[id]/slot-[id]/fw-status
    -- sys/switch-[id]/fw-status
    -- sys/fw-status
        -- fltFirmwareStatusCimcFirmwareMismatch
        -- fltFirmwareStatusPldFirmwareMismatch

-- sd:MgmtInfo
    -- sys-secsvc/slot-[slotId]/app-inst-[appInstId]/mgmt-info
        -- fsmStFailSdMgmtInfoUpdateMgmtInfo:SendUpdate
        -- fsmRmtErrSdMgmtInfoUpdateMgmtInfo:SendUpdate
        -- fsmFailSdMgmtInfoUpdateMgmtInfo

-- sm:SecSvc
    -- sec-svc
        -- fltSmSecSvcSwitchConfigFail

-- comm:SvcEp
    -- sys/svc-ext
        -- fltCommSvcEpCommSvcNotDeployed
        -- fsmStFailCommSvcEpUpdateSvcEp:InitIptablesLocal
        -- fsmStFailCommSvcEpUpdateSvcEp:InitIptablesPeer
        -- fsmStFailCommSvcEpUpdateSvcEp:PropogateEpSettings
        -- fsmStFailCommSvcEpUpdateSvcEp:PropogateEpTimeZoneSettingsLocal
        -- fsmStFailCommSvcEpUpdateSvcEp:PropogateEpTimeZoneSettingsPeer
        -- fsmStFailCommSvcEpUpdateSvcEp:PropogateEpTimeZoneSettingsToAdaptorsLocal
        -- fsmStFailCommSvcEpUpdateSvcEp:PropogateEpTimeZoneSettingsToAdaptorsPeer
        -- fsmStFailCommSvcEpUpdateSvcEp:PropogateEpTimeZoneSettingsToFexIomLocal
        -- fsmStFailCommSvcEpUpdateSvcEp:PropogateEpTimeZoneSettingsToFexIomPeer
        -- fsmStFailCommSvcEpUpdateSvcEp:SetEpLocal
        -- fsmStFailCommSvcEpUpdateSvcEp:SetEpPeer
        -- fsmStFailCommSvcEpRestartWebSvc:local
        -- fsmStFailCommSvcEpRestartWebSvc:peer
        -- fsmRmtErrCommSvcEpUpdateSvcEp:InitIptablesLocal
        -- fsmRmtErrCommSvcEpUpdateSvcEp:InitIptablesPeer
        -- fsmRmtErrCommSvcEpUpdateSvcEp:PropogateEpSettings
        -- fsmRmtErrCommSvcEpUpdateSvcEp:PropogateEpTimeZoneSettingsLocal
        -- fsmRmtErrCommSvcEpUpdateSvcEp:PropogateEpTimeZoneSettingsPeer
        -- fsmRmtErrCommSvcEpUpdateSvcEp:PropogateEpTimeZoneSettingsToAdaptorsLocal
        -- fsmRmtErrCommSvcEpUpdateSvcEp:PropogateEpTimeZoneSettingsToAdaptorsPeer
        -- fsmRmtErrCommSvcEpUpdateSvcEp:PropogateEpTimeZoneSettingsToFexIomLocal
        -- fsmRmtErrCommSvcEpUpdateSvcEp:PropogateEpTimeZoneSettingsToFexIomPeer
        -- fsmRmtErrCommSvcEpUpdateSvcEp:SetEpLocal
        -- fsmRmtErrCommSvcEpUpdateSvcEp:SetEpPeer
        -- fsmRmtErrCommSvcEpRestartWebSvc:local
        -- fsmRmtErrCommSvcEpRestartWebSvc:peer
        -- fsmFailCommSvcEpUpdateSvcEp
        -- fsmFailCommSvcEpRestartWebSvc

-- sm:ClusterBootstrap
    -- sec-svc/ld-[name]/cluster-bootstrap
        -- fltSmClusterBootstrapCclSubnetNotSupported

-- sysdebug:CpuOverall
    -- sys/sysdebug/overall-cpu-usage/cpu-[cpu]
        -- fltSysdebugCpuOverallCpuUsageHigh

-- sd:LogicalDevice
    -- sys-secsvc/ld-[name]
        -- fltSdLogicalDeviceDifferentResourcesInProfile
        -- fsmStFailSdLogicalDeviceConfigureLinks:ConfigureSwitch
        -- fsmStFailSdLogicalDeviceConfigureLinks:SendInterfaces
        -- fsmStFailSdLogicalDeviceConfigureLinks:UnconfigureLinks
        -- fsmStFailSdLogicalDeviceConfigureLinks:UnconfigureLogicalDevice
        -- fsmStFailSdLogicalDeviceConfigureLinks:WaitForSwitchConfig
        -- fsmStFailSdLogicalDeviceConfigureUserMacs:ConfigureSwitch
        -- fsmStFailSdLogicalDeviceConfigureUserMacs:WaitForSwitchConfig
        -- fsmStFailSdLogicalDeviceConfigureMacs:ConfigureSwitch
        -- fsmStFailSdLogicalDeviceConfigureMacs:SendInterfaceAdding
        -- fsmStFailSdLogicalDeviceConfigureMacs:SendInterfaceDeleting
        -- fsmStFailSdLogicalDeviceConfigureMacs:WaitForSwitchConfig
        -- fsmRmtErrSdLogicalDeviceConfigureLinks:ConfigureSwitch
        -- fsmRmtErrSdLogicalDeviceConfigureLinks:SendInterfaces
        -- fsmRmtErrSdLogicalDeviceConfigureLinks:UnconfigureLinks
        -- fsmRmtErrSdLogicalDeviceConfigureLinks:UnconfigureLogicalDevice
        -- fsmRmtErrSdLogicalDeviceConfigureLinks:WaitForSwitchConfig
        -- fsmRmtErrSdLogicalDeviceConfigureUserMacs:ConfigureSwitch
        -- fsmRmtErrSdLogicalDeviceConfigureUserMacs:WaitForSwitchConfig
        -- fsmRmtErrSdLogicalDeviceConfigureMacs:ConfigureSwitch
        -- fsmRmtErrSdLogicalDeviceConfigureMacs:SendInterfaceAdding
        -- fsmRmtErrSdLogicalDeviceConfigureMacs:SendInterfaceDeleting
        -- fsmRmtErrSdLogicalDeviceConfigureMacs:WaitForSwitchConfig
        -- fsmFailSdLogicalDeviceConfigureLinks
        -- fsmFailSdLogicalDeviceConfigureUserMacs
        -- fsmFailSdLogicalDeviceConfigureMacs

-- equipment:Chassis
    -- sys/chassis-[id]
        -- fltEquipmentChassisUnsupportedConnectivity
        -- fltEquipmentChassisUnacknowledged
        -- fltEquipmentChassisIdentity
        -- fltEquipmentChassisPowerProblem
        -- fltEquipmentChassisThermalThresholdCritical
        -- fltEquipmentChassisThermalThresholdNonRecoverable
        -- fltEquipmentChassisInoperable
        -- fltEquipmentChassisIdentity-unestablishable
        -- fltEquipmentChassisSeeprom-inoperable
        -- fltEquipmentChassisInvalid-fru
        -- fsmStFailEquipmentChassisRemoveChassis:DisableEndPoint
        -- fsmStFailEquipmentChassisRemoveChassis:UnIdentifyLocal
        -- fsmStFailEquipmentChassisRemoveChassis:UnIdentifyPeer
        -- fsmStFailEquipmentChassisRemoveChassis:Wait
        -- fsmStFailEquipmentChassisRemoveChassis:decomission
        -- fsmStFailEquipmentChassisPsuPolicyConfig:Execute
        -- fsmStFailEquipmentChassisPowerCap:Config
        -- fsmStFailEquipmentChassisDynamicReallocation:Config
        -- fsmStFailEquipmentChassisShutdownChassis:ApplyShutdown
        -- fsmStFailEquipmentChassisShutdownChassis:DebundlePort
        -- fsmStFailEquipmentChassisShutdownChassis:PollDebundlePort
        -- fsmStFailEquipmentChassisShutdownChassis:ShutdownBlade
        -- fsmStFailEquipmentChassisShutdownChassis:WaitForBladeShutdown
        -- fsmStFailEquipmentChassisRebootChassis:ApplyReboot
        -- fsmStFailEquipmentChassisRebootChassis:DebundlePort
        -- fsmStFailEquipmentChassisRebootChassis:PollDebundlePort
        -- fsmStFailEquipmentChassisRebootChassis:ShutdownBlade
        -- fsmStFailEquipmentChassisRebootChassis:WaitForBladeShutdown
        -- fsmRmtErrEquipmentChassisRemoveChassis:DisableEndPoint
        -- fsmRmtErrEquipmentChassisRemoveChassis:UnIdentifyLocal
        -- fsmRmtErrEquipmentChassisRemoveChassis:UnIdentifyPeer
        -- fsmRmtErrEquipmentChassisRemoveChassis:Wait
        -- fsmRmtErrEquipmentChassisRemoveChassis:decomission
        -- fsmRmtErrEquipmentChassisPsuPolicyConfig:Execute
        -- fsmRmtErrEquipmentChassisPowerCap:Config
        -- fsmRmtErrEquipmentChassisDynamicReallocation:Config
        -- fsmRmtErrEquipmentChassisShutdownChassis:ApplyShutdown
        -- fsmRmtErrEquipmentChassisShutdownChassis:DebundlePort
        -- fsmRmtErrEquipmentChassisShutdownChassis:PollDebundlePort
        -- fsmRmtErrEquipmentChassisShutdownChassis:ShutdownBlade
        -- fsmRmtErrEquipmentChassisShutdownChassis:WaitForBladeShutdown
        -- fsmRmtErrEquipmentChassisRebootChassis:ApplyReboot
        -- fsmRmtErrEquipmentChassisRebootChassis:DebundlePort
        -- fsmRmtErrEquipmentChassisRebootChassis:PollDebundlePort
        -- fsmRmtErrEquipmentChassisRebootChassis:ShutdownBlade
        -- fsmRmtErrEquipmentChassisRebootChassis:WaitForBladeShutdown
        -- fsmFailEquipmentChassisRemoveChassis
        -- fsmFailEquipmentChassisPsuPolicyConfig
        -- fsmFailEquipmentChassisPowerCap
        -- fsmFailEquipmentChassisDynamicReallocation
        -- fsmFailEquipmentChassisShutdownChassis
        -- fsmFailEquipmentChassisRebootChassis

-- mgmt:IPv6IfAddr
    -- sys/chassis-[id]/blade-[slotId]/adaptor-[id]/host-eth-[id]/if-[id]/ifConfig-ipv6/if-ipv6
    -- sys/rack-unit-[id]/adaptor-[id]/host-eth-[id]/if-[id]/ifConfig-ipv6/if-ipv6
    -- sys/chassis-[id]/blade-[slotId]/adaptor-[id]/mgmt/if-[id]/ifConfig-ipv6/if-ipv6
    -- sys/rack-unit-[id]/adaptor-[id]/mgmt/if-[id]/ifConfig-ipv6/if-ipv6
    -- sys/chassis-[id]/blade-[slotId]/ext-board-[id]/boardController/mgmt/if-[id]/ifConfig-ipv6/if-ipv6
    -- sys/rack-unit-[id]/ext-board-[id]/boardController/mgmt/if-[id]/ifConfig-ipv6/if-ipv6
    -- sys/chassis-[id]/blade-[slotId]/boardController/mgmt/if-[id]/ifConfig-ipv6/if-ipv6
    -- sys/rack-unit-[id]/boardController/mgmt/if-[id]/ifConfig-ipv6/if-ipv6
    -- sys/chassis-[id]/blade-[slotId]/ext-board-[id]/mgmt/if-[id]/ifConfig-ipv6/if-ipv6
    -- sys/rack-unit-[id]/ext-board-[id]/mgmt/if-[id]/ifConfig-ipv6/if-ipv6
    -- sys/chassis-[id]/blade-[slotId]/mgmt/if-[id]/ifConfig-ipv6/if-ipv6
    -- sys/rack-unit-[id]/mgmt/if-[id]/ifConfig-ipv6/if-ipv6
    -- sys/fex-[id]/mgmt/if-[id]/ifConfig-ipv6/if-ipv6
    -- sys/chassis-[id]/slot-[id]/mgmt/if-[id]/ifConfig-ipv6/if-ipv6
    -- sys/fex-[id]/slot-[id]/mgmt/if-[id]/ifConfig-ipv6/if-ipv6
    -- sys/chassis-[id]/sw-slot-[id]/mgmt/if-[id]/ifConfig-ipv6/if-ipv6
    -- sys/switch-[id]/mgmt/if-[id]/ifConfig-ipv6/if-ipv6
    -- sys/mgmt/if-[id]/ifConfig-ipv6/if-ipv6
    -- sys/switch-[id]/ifConfig-ipv6/if-ipv6
        -- fsmStFailMgmtIPv6IfAddrSwMgmtOobIpv6IfConfig:Switch
        -- fsmRmtErrMgmtIPv6IfAddrSwMgmtOobIpv6IfConfig:Switch
        -- fsmFailMgmtIPv6IfAddrSwMgmtOobIpv6IfConfig

-- mgmt:ExportPolicy
    -- org-[name]/
        -- fsmStFailMgmtExportPolicyReportConfigCopy:Report
        -- fsmRmtErrMgmtExportPolicyReportConfigCopy:Report
        -- fsmFailMgmtExportPolicyReportConfigCopy

-- sw:VlanPortNs
    -- sys/switch-[id]/vlan-port-ns
        -- fltSwVlanPortNsResourceStatus
        -- fltSwVlanPortNsVLANCompNotSupport
        -- fltSwVlanPortNsResourceStatusWarning

-- iqnpool:Pool
    -- org-[name]/iqn-pool-[name]
        -- fltIqnpoolPoolEmpty

-- extmgmt:If
    -- sys/switch-[id]/extmgmt-intf
        -- fltExtmgmtIfMgmtifdown

-- equipment:FanModule
    -- sys/rack-unit-[id]/fan-module-[tray]-[id]
    -- sys/chassis-[id]/fan-module-[tray]-[id]
    -- sys/switch-[id]/fan-module-[tray]-[id]
        -- fltEquipmentFanModuleMissing
        -- fltEquipmentFanModuleThermalThresholdNonCritical
        -- fltEquipmentFanModuleThermalThresholdCritical
        -- fltEquipmentFanModuleThermalThresholdNonRecoverable
        -- fltEquipmentFanModuleIdentity
        -- fltEquipmentFanModuleDegraded
        -- fltEquipmentFanModuleInoperable

-- vnic:Ether
    -- org-[name]/tier-[name]/ls-[name]/ether-[name]
    -- org-[name]/ls-[name]/ether-[name]
    -- org-[name]/lan-conn-pol-[name]/ether-[name]
        -- fltVnicEtherConfig-failed
        -- fltVnicEtherPinningMismatch
        -- fltVnicEtherPinningMisconfig
        -- fltVnicEtherVirtualization-conflict
        -- fltVnicEtherVirtualization-netflow-conflict

-- mgmt:BackupPolicyConfig
    -- sys/bkup-policy-cfg
        -- fltMgmtBackupPolicyConfigConfiguration backup outdated

-- firmware:MgrVersionMismatch
    -- sys/chassis-[id]/blade-[slotId]/adaptor-[id]/host-eth-[id]/fw-[deployment]/mgrversion-issue
    -- sys/rack-unit-[id]/adaptor-[id]/host-eth-[id]/fw-[deployment]/mgrversion-issue
    -- sys/chassis-[id]/blade-[slotId]/adaptor-[id]/host-fc-[id]/fw-[deployment]/mgrversion-issue
    -- sys/rack-unit-[id]/adaptor-[id]/host-fc-[id]/fw-[deployment]/mgrversion-issue
    -- sys/chassis-[id]/blade-[slotId]/ext-board-[id]/bios/fw-[deployment]/mgrversion-issue
    -- sys/rack-unit-[id]/ext-board-[id]/bios/fw-[deployment]/mgrversion-issue
    -- sys/chassis-[id]/blade-[slotId]/bios/fw-[deployment]/mgrversion-issue
    -- sys/rack-unit-[id]/bios/fw-[deployment]/mgrversion-issue
    -- capabilities/fw-[deployment]/mgrversion-issue
    -- capabilities/ep/mgmt-ext/fw-[deployment]/mgrversion-issue
    -- sys/chassis-[id]/epmfpga-[slot]/fw-[deployment]/mgrversion-issue
    -- sys/chassis-[id]/fpga/fw-[deployment]/mgrversion-issue
    -- sys/chassis-[id]/rommon/fw-[deployment]/mgrversion-issue
    -- sys/chassis-[id]/Ssd/fw-[deployment]/mgrversion-issue
    -- sys/chassis-[id]/blade-[slotId]/board/graphics-card-[id]/fw-[deployment]/mgrversion-issue
    -- sys/rack-unit-[id]/board/graphics-card-[id]/fw-[deployment]/mgrversion-issue
    -- sys/chassis-[id]/blade-[slotId]/adaptor-[id]/mgmt/fw-[deployment]/mgrversion-issue
    -- sys/rack-unit-[id]/adaptor-[id]/mgmt/fw-[deployment]/mgrversion-issue
    -- sys/chassis-[id]/blade-[slotId]/ext-board-[id]/boardController/mgmt/fw-[deployment]/mgrversion-issue
    -- sys/rack-unit-[id]/ext-board-[id]/boardController/mgmt/fw-[deployment]/mgrversion-issue
    -- sys/chassis-[id]/blade-[slotId]/boardController/mgmt/fw-[deployment]/mgrversion-issue
    -- sys/rack-unit-[id]/boardController/mgmt/fw-[deployment]/mgrversion-issue
    -- sys/chassis-[id]/blade-[slotId]/ext-board-[id]/mgmt/fw-[deployment]/mgrversion-issue
    -- sys/rack-unit-[id]/ext-board-[id]/mgmt/fw-[deployment]/mgrversion-issue
    -- sys/chassis-[id]/blade-[slotId]/mgmt/fw-[deployment]/mgrversion-issue
    -- sys/rack-unit-[id]/mgmt/fw-[deployment]/mgrversion-issue
    -- sys/fex-[id]/mgmt/fw-[deployment]/mgrversion-issue
    -- sys/chassis-[id]/slot-[id]/mgmt/fw-[deployment]/mgrversion-issue
    -- sys/fex-[id]/slot-[id]/mgmt/fw-[deployment]/mgrversion-issue
    -- sys/chassis-[id]/sw-slot-[id]/mgmt/fw-[deployment]/mgrversion-issue
    -- sys/switch-[id]/mgmt/fw-[deployment]/mgrversion-issue
    -- sys/mgmt/fw-[deployment]/mgrversion-issue
    -- sys/chassis-[id]/blade-[slotId]/os-ctrl/fw-[deployment]/mgrversion-issue
    -- sys/chassis-[id]/blade-[slotId]/os-ctrl/fw-[deployment]/mgrversion-issue
    -- sys/rack-unit-[id]/os-ctrl/fw-[deployment]/mgrversion-issue
    -- sys/os-ctrl/fw-[deployment]/mgrversion-issue
    -- sys/chassis-[id]/blade-[slotId]/board/storage-[type]-[id]/fw-[deployment]/mgrversion-issue
    -- sys/rack-unit-[id]/board/storage-[type]-[id]/fw-[deployment]/mgrversion-issue
    -- sys/chassis-[id]/blade-[slotId]/board/storage-flexflash-[id]/fw-[deployment]/mgrversion-issue
    -- sys/rack-unit-[id]/board/storage-flexflash-[id]/fw-[deployment]/mgrversion-issue
    -- sys/chassis-[id]/blade-[slotId]/board/storage-[type]-[id]/disk-[id]/fw-[deployment]/mgrversion-issue
    -- sys/rack-unit-[id]/board/storage-[type]-[id]/disk-[id]/fw-[deployment]/mgrversion-issue
        -- fltFirmwareMgrVersionMismatchImageVersionMismatch

-- sm:CloudConnector
    -- sys/cloud-connector
        -- fltSmCloudConnectorCloudRegistrationFailed
        -- fltSmCloudConnectorCloudUnregistrationFailed
        -- fsmStFailSmCloudConnectorRegisterCloudConnector:Register
        -- fsmStFailSmCloudConnectorUnRegisterCloudConnector:UnRegister
        -- fsmRmtErrSmCloudConnectorRegisterCloudConnector:Register
        -- fsmRmtErrSmCloudConnectorUnRegisterCloudConnector:UnRegister
        -- fsmFailSmCloudConnectorRegisterCloudConnector
        -- fsmFailSmCloudConnectorUnRegisterCloudConnector

-- firmware:Distributable
    -- sys/fw-catalogue/distrib-[name]
        -- fsmStFailFirmwareDistributableDelete:Local
        -- fsmStFailFirmwareDistributableDelete:Remote
        -- fsmRmtErrFirmwareDistributableDelete:Local
        -- fsmRmtErrFirmwareDistributableDelete:Remote
        -- fsmFailFirmwareDistributableDelete

-- equipment:Fex
    -- sys/fex-[id]
        -- fltEquipmentFexPost-failure
        -- fltEquipmentFexIdentity
        -- fltEquipmentFexIdentity-unestablishable
        -- fltEquipmentFexFex-unsupported
        -- fsmStFailEquipmentFexRemoveFex:CleanupEntries
        -- fsmStFailEquipmentFexRemoveFex:UnIdentifyLocal
        -- fsmStFailEquipmentFexRemoveFex:Wait
        -- fsmStFailEquipmentFexRemoveFex:decomission
        -- fsmRmtErrEquipmentFexRemoveFex:CleanupEntries
        -- fsmRmtErrEquipmentFexRemoveFex:UnIdentifyLocal
        -- fsmRmtErrEquipmentFexRemoveFex:Wait
        -- fsmRmtErrEquipmentFexRemoveFex:decomission
        -- fsmFailEquipmentFexRemoveFex

-- sd:Slot
    -- sys-secsvc/slot-[slotId]
        -- fsmStFailSdSlotChangePlatformLogLevel:SendCommand
        -- fsmStFailSdSlotFormatDisk:CheckBladeReadiness
        -- fsmStFailSdSlotFormatDisk:DecommissionBlade
        -- fsmStFailSdSlotFormatDisk:ResetBladePower
        -- fsmStFailSdSlotFormatDisk:StartDiskFormat
        -- fsmStFailSdSlotFormatDisk:WaitForDiskFormatComplete
        -- fsmStFailSdSlotFormatDisk:WaitForDiskFormatSecureComplete
        -- fsmStFailSdSlotFormatDisk:WaitforDecommissionComplete
        -- fsmStFailSdSlotSynchTimeZone:UpdateTimeZone
        -- fsmRmtErrSdSlotChangePlatformLogLevel:SendCommand
        -- fsmRmtErrSdSlotFormatDisk:CheckBladeReadiness
        -- fsmRmtErrSdSlotFormatDisk:DecommissionBlade
        -- fsmRmtErrSdSlotFormatDisk:ResetBladePower
        -- fsmRmtErrSdSlotFormatDisk:StartDiskFormat
        -- fsmRmtErrSdSlotFormatDisk:WaitForDiskFormatComplete
        -- fsmRmtErrSdSlotFormatDisk:WaitForDiskFormatSecureComplete
        -- fsmRmtErrSdSlotFormatDisk:WaitforDecommissionComplete
        -- fsmRmtErrSdSlotSynchTimeZone:UpdateTimeZone
        -- fsmFailSdSlotChangePlatformLogLevel
        -- fsmFailSdSlotFormatDisk
        -- fsmFailSdSlotSynchTimeZone

-- dcx:Vc
    -- sys/chassis-[id]/blade-[slotId]/fabric-[switchId]/vc-[id]
    -- sys/chassis-[id]/blade-[slotId]/fabric-[switchId]/vc-[id]
    -- sys/rack-unit-[id]/fabric-[switchId]/vc-[id]
    -- sys/chassis-[id]/fabric-[switchId]/vc-[id]
    -- sys/fex-[id]/fabric-[switchId]/vc-[id]
    -- sys/chassis-[id]/blade-[slotId]/adaptor-[id]/mgmt/fabric-[switchId]/vc-[id]
    -- sys/rack-unit-[id]/adaptor-[id]/mgmt/fabric-[switchId]/vc-[id]
    -- sys/chassis-[id]/blade-[slotId]/ext-board-[id]/boardController/mgmt/fabric-[switchId]/vc-[id]
    -- sys/rack-unit-[id]/ext-board-[id]/boardController/mgmt/fabric-[switchId]/vc-[id]
    -- sys/chassis-[id]/blade-[slotId]/boardController/mgmt/fabric-[switchId]/vc-[id]
    -- sys/rack-unit-[id]/boardController/mgmt/fabric-[switchId]/vc-[id]
    -- sys/chassis-[id]/blade-[slotId]/ext-board-[id]/mgmt/fabric-[switchId]/vc-[id]
    -- sys/rack-unit-[id]/ext-board-[id]/mgmt/fabric-[switchId]/vc-[id]
    -- sys/chassis-[id]/blade-[slotId]/mgmt/fabric-[switchId]/vc-[id]
    -- sys/rack-unit-[id]/mgmt/fabric-[switchId]/vc-[id]
    -- sys/fex-[id]/mgmt/fabric-[switchId]/vc-[id]
    -- sys/chassis-[id]/slot-[id]/mgmt/fabric-[switchId]/vc-[id]
    -- sys/fex-[id]/slot-[id]/mgmt/fabric-[switchId]/vc-[id]
    -- sys/chassis-[id]/sw-slot-[id]/mgmt/fabric-[switchId]/vc-[id]
    -- sys/switch-[id]/mgmt/fabric-[switchId]/vc-[id]
    -- sys/mgmt/fabric-[switchId]/vc-[id]
    -- sys/chassis-[id]/blade-[slotId]/fabric-[switchId]/path-[id]/vc-[id]
    -- sys/chassis-[id]/blade-[slotId]/fabric-[switchId]/path-[id]/vc-[id]
    -- sys/rack-unit-[id]/fabric-[switchId]/path-[id]/vc-[id]
    -- sys/chassis-[id]/fabric-[switchId]/path-[id]/vc-[id]
    -- sys/fex-[id]/fabric-[switchId]/path-[id]/vc-[id]
    -- sys/chassis-[id]/blade-[slotId]/adaptor-[id]/mgmt/fabric-[switchId]/path-[id]/vc-[id]
    -- sys/rack-unit-[id]/adaptor-[id]/mgmt/fabric-[switchId]/path-[id]/vc-[id]
    -- sys/chassis-[id]/blade-[slotId]/ext-board-[id]/boardController/mgmt/fabric-[switchId]/path-[id]/vc-[id]
    -- sys/rack-unit-[id]/ext-board-[id]/boardController/mgmt/fabric-[switchId]/path-[id]/vc-[id]
    -- sys/chassis-[id]/blade-[slotId]/boardController/mgmt/fabric-[switchId]/path-[id]/vc-[id]
    -- sys/rack-unit-[id]/boardController/mgmt/fabric-[switchId]/path-[id]/vc-[id]
    -- sys/chassis-[id]/blade-[slotId]/ext-board-[id]/mgmt/fabric-[switchId]/path-[id]/vc-[id]
    -- sys/rack-unit-[id]/ext-board-[id]/mgmt/fabric-[switchId]/path-[id]/vc-[id]
    -- sys/chassis-[id]/blade-[slotId]/mgmt/fabric-[switchId]/path-[id]/vc-[id]
    -- sys/rack-unit-[id]/mgmt/fabric-[switchId]/path-[id]/vc-[id]
    -- sys/fex-[id]/mgmt/fabric-[switchId]/path-[id]/vc-[id]
    -- sys/chassis-[id]/slot-[id]/mgmt/fabric-[switchId]/path-[id]/vc-[id]
    -- sys/fex-[id]/slot-[id]/mgmt/fabric-[switchId]/path-[id]/vc-[id]
    -- sys/chassis-[id]/sw-slot-[id]/mgmt/fabric-[switchId]/path-[id]/vc-[id]
    -- sys/switch-[id]/mgmt/fabric-[switchId]/path-[id]/vc-[id]
    -- sys/mgmt/fabric-[switchId]/path-[id]/vc-[id]
    -- sys/switch-[id]/lanmon-eth/mon-[name]/vc-[id]
        -- fltDcxVcDown
        -- fltDcxVcMgmt-vif-down

-- adaptor:HostEthIf
    -- sys/chassis-[id]/blade-[slotId]/adaptor-[id]/host-eth-[id]
    -- sys/rack-unit-[id]/adaptor-[id]/host-eth-[id]
        -- fltAdaptorHostEthIfMisConnect
        -- fltAdaptorHostEthIfMissing
        -- fsmStFailAdaptorHostEthIfCircuitReset:DisableA
        -- fsmStFailAdaptorHostEthIfCircuitReset:DisableB
        -- fsmStFailAdaptorHostEthIfCircuitReset:EnableA
        -- fsmStFailAdaptorHostEthIfCircuitReset:EnableB
        -- fsmRmtErrAdaptorHostEthIfCircuitReset:DisableA
        -- fsmRmtErrAdaptorHostEthIfCircuitReset:DisableB
        -- fsmRmtErrAdaptorHostEthIfCircuitReset:EnableA
        -- fsmRmtErrAdaptorHostEthIfCircuitReset:EnableB
        -- fsmFailAdaptorHostEthIfCircuitReset

-- sw:SspEthMonSrcPhyEp
    -- sys/switch-[id]/ssp-lanmon-eth/ssp-mon-session[name]/ssp-mon-src-phy-[chassisId]-slot-[slotId]-port-[portId]-aggr-[aggrPortId]
        -- fsmStFailSwSspEthMonSrcPhyEpDelete:DeletePcapFile
        -- fsmRmtErrSwSspEthMonSrcPhyEpDelete:DeletePcapFile
        -- fsmFailSwSspEthMonSrcPhyEpDelete

-- epqos:Definition
    -- org-[name]/ep-qos-[name]
        -- fsmStFailEpqosDefinitionDeploy:Local
        -- fsmStFailEpqosDefinitionDeploy:Peer
        -- fsmRmtErrEpqosDefinitionDeploy:Local
        -- fsmRmtErrEpqosDefinitionDeploy:Peer
        -- fsmFailEpqosDefinitionDeploy

-- extpol:Provider
    -- extpol/reg/providers/prov-[type]
        -- fsmStFailExtpolProviderReportConfigImport:Report
        -- fsmRmtErrExtpolProviderReportConfigImport:Report
        -- fsmFailExtpolProviderReportConfigImport

-- aaa:UserRole
    -- sys/ldap-ext/ldapgroup-[name]/role-[name]
    -- sys/user-ext/remoteuser-[name]/role-[name]
    -- sys/user-ext/user-[name]/role-[name]
        -- fltAaaUserRoleUserRoleNotDeployed

-- sysdebug:CpuOverallHead
    -- sys/sysdebug/overall-cpu-usage
        -- fsmStFailSysdebugCpuOverallHeadDeploy:ApplyConfig
        -- fsmRmtErrSysdebugCpuOverallHeadDeploy:ApplyConfig
        -- fsmFailSysdebugCpuOverallHeadDeploy

-- extvmm:NetworkSets
    -- fabric/lan/network-sets
        -- fsmStFailExtvmmNetworkSetsDeploy:Local
        -- fsmStFailExtvmmNetworkSetsDeploy:Peer
        -- fsmRmtErrExtvmmNetworkSetsDeploy:Local
        -- fsmRmtErrExtvmmNetworkSetsDeploy:Peer
        -- fsmFailExtvmmNetworkSetsDeploy

-- extpol:Ep
    -- extpol
        -- fsmStFailExtpolEpRegisterFsm:Execute
        -- fsmStFailExtpolEpRepairCert:cleanOldData
        -- fsmStFailExtpolEpRepairCert:request
        -- fsmStFailExtpolEpRepairCert:unregister
        -- fsmStFailExtpolEpRepairCert:verify
        -- fsmStFailExtpolEpRepairCert:verifyGuid
        -- fsmRmtErrExtpolEpRegisterFsm:Execute
        -- fsmRmtErrExtpolEpRepairCert:cleanOldData
        -- fsmRmtErrExtpolEpRepairCert:request
        -- fsmRmtErrExtpolEpRepairCert:unregister
        -- fsmRmtErrExtpolEpRepairCert:verify
        -- fsmRmtErrExtpolEpRepairCert:verifyGuid
        -- fsmFailExtpolEpRegisterFsm
        -- fsmFailExtpolEpRepairCert

-- pki:Ep
    -- sys/pki-ext
        -- fsmStFailPkiEpUpdateEp:PostSetKeyRingLocal
        -- fsmStFailPkiEpUpdateEp:PostSetKeyRingPeer
        -- fsmStFailPkiEpUpdateEp:SetKeyRingLocal
        -- fsmStFailPkiEpUpdateEp:SetKeyRingPeer
        -- fsmRmtErrPkiEpUpdateEp:PostSetKeyRingLocal
        -- fsmRmtErrPkiEpUpdateEp:PostSetKeyRingPeer
        -- fsmRmtErrPkiEpUpdateEp:SetKeyRingLocal
        -- fsmRmtErrPkiEpUpdateEp:SetKeyRingPeer
        -- fsmFailPkiEpUpdateEp

-- vm:Vif
    -- vmm/computeEp-[uuid]/nic-[name]/sw-[phSwitchId]vif-[vifId]
    -- vmm/hv-[uuid]/nic-[name]/sw-[phSwitchId]vif-[vifId]
    -- vmm/vm-[uuid]/nic-[name]/sw-[phSwitchId]vif-[vifId]
        -- fltVmVifLinkState

CfprFaultCode ::= TEXTUAL-CONVENTION
        STATUS       current
        DESCRIPTION
       "A code identifying a class of fault."
        SYNTAX INTEGER {
    fltFabricComputeSlotEpMisplacedInChassisSlot(156),
    fltFabricComputeSlotEpServerIdentificationProblem(157),
    fltVnicEtherConfigFailed(169),
    fltProcessorUnitInoperable(174),
    fltProcessorUnitThermalNonCritical(175),
    fltProcessorUnitThermalThresholdCritical(176),
    fltProcessorUnitThermalThresholdNonRecoverable(177),
    fltProcessorUnitVoltageThresholdNonCritical(178),
    fltProcessorUnitVoltageThresholdCritical(179),
    fltProcessorUnitVoltageThresholdNonRecoverable(180),
    fltStorageLocalDiskInoperable(181),
    fltStorageItemCapacityExceeded(182),
    fltStorageItemCapacityWarning(183),
    fltMemoryUnitDegraded(184),
    fltMemoryUnitInoperable(185),
    fltMemoryUnitThermalThresholdNonCritical(186),
    fltMemoryUnitThermalThresholdCritical(187),
    fltMemoryUnitThermalThresholdNonRecoverable(188),
    fltMemoryArrayVoltageThresholdNonCritical(189),
    fltMemoryArrayVoltageThresholdCritical(190),
    fltMemoryArrayVoltageThresholdNonRecoverable(191),
    fltAdaptorUnitUnidentifiableFru(200),
    fltAdaptorUnitMissing(203),
    fltAdaptorUnitAdaptorReachability(206),
    fltAdaptorHostIfLinkDown(207),
    fltAdaptorExtIfLinkDown(209),
    fltPortPIoLinkDown(276),
    fltPortPIoFailed(277),
    fltPortPIoHardwareFailure(278),
    fltPortPIoSfpNotPresent(279),
    fltFabricExternalPcDown(282),
    fltDcxVcDown(283),
    fltNetworkElementInoperable(291),
    fltMgmtEntityDegraded(293),
    fltMgmtEntityDown(294),
    fltDcxNsFailed(304),
    fltComputePhysicalInsufficientlyEquipped(305),
    fltComputePhysicalIdentityUnestablishable(306),
    fltComputeBoardPowerError(310),
    fltComputePhysicalPowerProblem(311),
    fltComputePhysicalThermalProblem(312),
    fltComputePhysicalBiosPostTimeout(313),
    fltComputePhysicalDiscoveryFailed(314),
    fltComputePhysicalAssociationFailed(315),
    fltComputePhysicalInoperable(317),
    fltComputePhysicalUnassignedMissing(318),
    fltComputePhysicalAssignedMissing(319),
    fltComputePhysicalUnidentified(320),
    fltComputePhysicalUnassignedInaccessible(321),
    fltComputePhysicalAssignedInaccessible(322),
    fltLsServerFailed(324),
    fltLsServerDiscoveryFailed(326),
    fltLsServerConfigFailure(327),
    fltLsServerMaintenanceFailed(329),
    fltLsServerRemoved(330),
    fltLsServerInaccessible(331),
    fltLsServerAssociationFailed(332),
    fltLsServerUnassociated(334),
    fltLsServerServerUnfulfilled(337),
    fltEtherSwitchIntFIoSatelliteConnectionAbsent(367),
    fltEtherSwitchIntFIoSatelliteWiringProblem(368),
    fltEquipmentPsuPowerSupplyProblem(369),
    fltEquipmentFanDegraded(371),
    fltEquipmentFanInoperable(373),
    fltEquipmentPsuInoperable(374),
    fltEquipmentIOCardRemoved(376),
    fltEquipmentFanModuleMissing(377),
    fltEquipmentPsuMissing(378),
    fltEquipmentIOCardThermalProblem(379),
    fltEquipmentFanModuleThermalThresholdNonCritical(380),
    fltEquipmentPsuThermalThresholdNonCritical(381),
    fltEquipmentFanModuleThermalThresholdCritical(382),
    fltEquipmentPsuThermalThresholdCritical(383),
    fltEquipmentFanModuleThermalThresholdNonRecoverable(384),
    fltEquipmentPsuThermalThresholdNonRecoverable(385),
    fltEquipmentPsuVoltageThresholdNonCritical(387),
    fltEquipmentPsuVoltageThresholdCritical(389),
    fltEquipmentPsuVoltageThresholdNonRecoverable(391),
    fltEquipmentPsuPerfThresholdNonCritical(392),
    fltEquipmentPsuPerfThresholdCritical(393),
    fltEquipmentPsuPerfThresholdNonRecoverable(394),
    fltEquipmentFanPerfThresholdNonCritical(395),
    fltEquipmentFanPerfThresholdCritical(396),
    fltEquipmentFanPerfThresholdNonRecoverable(397),
    fltEquipmentIOCardFirmwareUpgrade(398),
    fltEquipmentChassisUnsupportedConnectivity(399),
    fltEquipmentChassisUnacknowledged(400),
    fltEquipmentIOCardUnsupportedConnectivity(401),
    fltEquipmentIOCardUnacknowledged(402),
    fltEquipmentIOCardPeerDisconnected(403),
    fltEquipmentChassisIdentity(404),
    fltEquipmentIOCardIdentity(405),
    fltEquipmentFanModuleIdentity(406),
    fltEquipmentPsuIdentity(407),
    fltEquipmentChassisPowerProblem(408),
    fltEquipmentChassisThermalThresholdCritical(409),
    fltEquipmentChassisThermalThresholdNonRecoverable(411),
    fltComputeBoardCmosVoltageThresholdCritical(424),
    fltComputeBoardCmosVoltageThresholdNonRecoverable(425),
    fltMgmtEntityElectionFailure(428),
    fltMgmtEntityHaNotReady(429),
    fltMgmtEntityVersionIncompatible(430),
    fltEquipmentFanMissing(434),
    fltEquipmentIOCardAutoUpgradingFirmware(435),
    fltFirmwarePackItemImageMissing(436),
    fltEtherSwitchIntFIoSatelliteWiringNumbersUnexpected(440),
    fltMgmtEntityManagementServicesFailure(451),
    fltMgmtEntityManagementServicesUnresponsive(452),
    fltEquipmentChassisInoperable(456),
    fltEtherServerIntFIoHardwareFailure(458),
    fltDcxVcMgmtVifDown(459),
    fltSysdebugMEpLogMEpLogLog(460),
    fltSysdebugMEpLogMEpLogVeryLow(461),
    fltSysdebugMEpLogMEpLogFull(462),
    fltComputePoolEmpty(463),
    fltUuidpoolPoolEmpty(464),
    fltIppoolPoolEmpty(465),
    fltMacpoolPoolEmpty(466),
    fltFirmwareUpdatableImageUnusable(470),
    fltFirmwareBootUnitCantBoot(471),
    fltFcpoolInitiatorsEmpty(476),
    fltEquipmentIOCardInaccessible(478),
    fltDcxVIfLinkState(479),
    fltEquipmentFanModuleDegraded(480),
    fltEquipmentIOCardPostFailure(481),
    fltEquipmentFanPerfThresholdLowerNonRecoverable(484),
    fltComputePhysicalPostFailure(517),
    fltEquipmentPsuOffline(528),
    fltStorageRaidBatteryInoperable(531),
    fltSysdebugMEpLogTransferError(532),
    fltComputeRtcBatteryInoperable(533),
    fltMemoryBufferUnitThermalThresholdNonCritical(535),
    fltMemoryBufferUnitThermalThresholdCritical(536),
    fltMemoryBufferUnitThermalThresholdNonRecoverable(537),
    fltComputeIOHubThermalNonCritical(538),
    fltComputeIOHubThermalThresholdCritical(539),
    fltComputeIOHubThermalThresholdNonRecoverable(540),
    fltEquipmentChassisIdentityUnestablishable(543),
    fltSwVlanPortNsResourceStatus(549),
    fltFabricLanPinGroupEmpty(621),
    fltAdaptorExtEthIfMisConnect(625),
    fltAdaptorHostEthIfMisConnect(626),
    fltPowerBudgetPowerBudgetCmcProblem(635),
    fltPowerBudgetPowerBudgetBmcProblem(637),
    fltPowerBudgetPowerBudgetDiscFail(640),
    fltPowerGroupPowerGroupInsufficientBudget(642),
    fltPowerGroupPowerGroupBudgetIncorrect(643),
    fltMgmtIfMisConnect(688),
    fltLsComputeBindingAssignmentRequirementsNotMet(689),
    fltEquipmentFexPostFailure(702),
    fltEquipmentFexIdentity(703),
    fltAdaptorHostEthIfMissing(708),
    fltPortPIoInvalidSfp(713),
    fltMgmtIfMissing(717),
    fltFabricEthLanPcEpDown(727),
    fltEquipmentIOCardThermalThresholdNonCritical(729),
    fltEquipmentIOCardThermalThresholdCritical(730),
    fltEquipmentIOCardThermalThresholdNonRecoverable(731),
    fltEquipmentChassisSeepromInoperable(733),
    fltExtmgmtIfMgmtifdown(736),
    fltPowerChassisMemberPowerGroupCapInsufficient(740),
    fltPowerChassisMemberChassisFirmwareProblem(741),
    fltPowerChassisMemberChassisPsuInsufficient(742),
    fltPowerChassisMemberChassisPsuRedundanceFailure(743),
    fltPowerBudgetPowerCapReachedCommit(744),
    fltSysdebugAutoCoreFileExportTargetAutoCoreTransferFailure(747),
    fltFabricMonSpanConfigFail(757),
    fltPowerBudgetChassisPsuInsufficient(764),
    fltPowerBudgetTStateTransition(765),
    fltPowerPolicyPowerPolicyApplicationFail(766),
    fltMgmtIfNew(772),
    fltAdaptorExtEthIfMissing(775),
    fltStorageLocalDiskSlotEpUnusable(776),
    fltFabricEthEstcPcEpDown(777),
    fltEquipmentFexIdentityUnestablishable(778),
    fltEquipmentFanModuleInoperable(794),
    fltLsmaintMaintPolicyUnresolvableScheduler(795),
    fltProcessorUnitIdentityUnestablishable(801),
    fltIqnpoolPoolEmpty(821),
    fltFabricDceSwSrvPcEpDown(831),
    fltFabricEpMgrEpTransModeFail(832),
    fltFabricPIoEpErrorMisconfigured(834),
    fltFabricEthLanEpMissingPrimaryVlan(835),
    fltFabricEthLanPcMissingPrimaryVlan(836),
    fltVnicEtherPinningMismatch(840),
    fltVnicEtherPinningMisconfig(841),
    fltProcessorUnitDisabled(842),
    fltMemoryUnitDisabled(844),
    fltFirmwareBootUnitActivateStatusFailed(856),
    fltFabricInternalPcDown(858),
    fltMgmtEntityDevice1SharedStorageError(863),
    fltMgmtEntityDevice2SharedStorageError(864),
    fltMgmtEntityDevice3SharedStorageError(865),
    fltMgmtEntityHaSshKeysMismatched(866),
    fltComputeBoardPowerFail(868),
    fltVmVifLinkState(876),
    fltEquipmentPsuPowerSupplyShutdown(881),
    fltEquipmentPsuPowerThreshold(882),
    fltEquipmentPsuInputError(883),
    fltNetworkElementInventoryFailed(885),
    fltAdaptorUnitExtnUnidentifiableFru(900),
    fltAdaptorUnitExtnMissing(901),
    fltEquipmentFexFexUnsupported(902),
    fltVnicIScsiConfigFailed(903),
    fltPkiKeyRingStatus(909),
    fltPkiTPStatus(910),
    fltComputePhysicalDisassociationFailed(915),
    fltComputePhysicalNetworkMisconfigured(916),
    fltVnicProfileProfileConfigIncorrect(917),
    fltVnicEtherIfVlanAccessFault(932),
    fltVnicEtherIfVlanUnresolvable(933),
    fltVnicEtherIfInvalidVlan(934),
    fltFabricVlanVlanConflictPermit(935),
    fltFabricVlanReqVlanPermitUnresolved(936),
    fltFabricVlanGroupReqVlanGroupPermitUnresolved(937),
    fltExtpolClientClientLostConnectivity(988),
    fltStorageLocalDiskDegraded(996),
    fltStorageRaidBatteryDegraded(997),
    fltStorageRaidBatteryRelearnAborted(998),
    fltStorageRaidBatteryRelearnFailed(999),
    fltStorageInitiatorConfigurationError(1001),
    fltStorageControllerPatrolReadFailed(1003),
    fltStorageControllerInoperable(1004),
    fltStorageLocalDiskRebuildFailed(1005),
    fltStorageLocalDiskCopybackFailed(1006),
    fltStorageVirtualDriveInoperable(1007),
    fltStorageVirtualDriveDegraded(1008),
    fltStorageVirtualDriveReconstructionFailed(1009),
    fltStorageVirtualDriveConsistencyCheckFailed(1010),
    fltAaaProviderGroupProvidergroup(1026),
    fltAaaConfigServergroup(1027),
    fltAaaRoleRoleNotDeployed(1028),
    fltAaaLocaleLocaleNotDeployed(1029),
    fltAaaUserRoleUserRoleNotDeployed(1030),
    fltAaaUserLocaleUserLocaleNotDeployed(1031),
    fltPkiKeyRingKeyRingNotDeployed(1032),
    fltCommSnmpSyscontactEmpty(1033),
    fltCommDateTimeCommTimeZoneInvalid(1034),
    fltAaaUserLocalUserNotDeployed(1035),
    fltCommSnmpUserSnmpUserNotDeployed(1036),
    fltCommSvcEpCommSvcNotDeployed(1037),
    fltSwVlanPortNsVLANCompNotSupport(1056),
    fltPolicyControlEpSuspendModeActive(1057),
    fltNetworkElementThermalThresholdCritical(1080),
    fltFabricPinTargetDown(1088),
    fltFabricEthLanEpOverlappingVlan(1090),
    fltFabricEthLanPcOverlappingVlan(1091),
    fltFabricVlanMisconfiguredMcastPolicy(1095),
    fltMgmtConnectionDisabled(1097),
    fltMgmtConnectionUnused(1098),
    fltMgmtConnectionUnsupportedConnectivity(1099),
    fltCallhomeEpNoSnmpPolicyForCallhome(1102),
    fltCapabilityCatalogueLoadErrors(1103),
    fltExtmgmtArpTargetsArpTargetsNotValid(1114),
    fltExtpolClientGracePeriodWarning(1211),
    fltExtpolClientGracePeriodWarning2(1212),
    fltExtpolClientGracePeriodWarning3(1213),
    fltExtpolClientGracePeriodWarning4(1214),
    fltExtpolClientGracePeriodWarning5(1215),
    fltExtpolClientGracePeriodWarning6(1216),
    fltExtpolClientGracePeriodWarning7(1217),
    fltExtpolClientGracePeriodWarning1(1218),
    fltStorageItemFilesystemIssues(1219),
    fltPkiKeyRingModulus(1222),
    fltAaaOrgLocaleOrgNotPresent(1223),
    fltNetworkOperLevelExtraprimaryvlans(1229),
    fltEquipmentHealthLedCriticalError(1236),
    fltEquipmentHealthLedMinorError(1237),
    fltVnicEtherIfRemoteVlanUnresolvable(1249),
    fltVnicEtherVirtualizationConflict(1251),
    fltLsIssuesIscsiConfigFailed(1252),
    fltStorageLocalDiskMissing(1256),
    fltStorageFlexFlashControllerInoperable(1257),
    fltStorageFlexFlashCardInoperable(1258),
    fltStorageFlexFlashCardMissing(1259),
    fltStorageFlexFlashVirtualDriveDegraded(1260),
    fltStorageFlexFlashVirtualDriveInoperable(1261),
    fltAaaProviderGroupProvidergroupsize(1279),
    fltFirmwareAutoSyncPolicyDefaultHostPackageMissing(1284),
    fltFabricPooledVlanNamedVlanUnresolved(1306),
    fltExtvmmVMNDRefVmNetworkReferenceIncorrect(1320),
    fltExtmgmtNdiscTargetsNdiscTargetsNotValid(1321),
    fltFirmwareBootUnitPowerCycleRequired(1325),
    fltMgmtControllerUnsupportedDimmBlacklisting(1328),
    fltFabricEthLanEpUdldLinkDown(1358),
    fltFabricEthLanPcEpUdldLinkDown(1359),
    fltEquipmentChassisInvalidFru(1407),
    fltEquipmentSwitchIOCardRemoved(1408),
    fltEquipmentSwitchIOCardThermalProblem(1409),
    fltEquipmentSwitchIOCardThermalThresholdNonCritical(1410),
    fltEquipmentSwitchIOCardThermalThresholdCritical(1411),
    fltEquipmentSwitchIOCardThermalThresholdNonRecoverable(1412),
    fltEquipmentSwitchIOCardIdentity(1414),
    fltEquipmentSwitchIOCardCpuThermalThresholdCritical(1415),
    fltPowerBudgetChassisPsuMixedMode(1421),
    fltNetworkElementRemoved(1426),
    fltNetworkOperLevelExtrasecondaryvlans(1432),
    fltSwVlanExtrasecondaryvlansperprimary(1433),
    fltMgmtBackupPolicyConfigConfigurationBackupOutdated(1437),
    fltFirmwareStatusCimcFirmwareMismatch(1441),
    fltFirmwareStatusPldFirmwareMismatch(1442),
    fltVnicEtherVirtualizationNetflowConflict(1443),
    fltSysdebugLogExportStatusLogExportFailure(1444),
    fltLsServerSvnicNotPresent(1459),
    fltLsIssuesKvmPolicyUnsupported(1460),
    fltComputeABoardThermalProblem(1461),
    fltComputeABoardPowerUsageProblem(1462),
    fltComputeABoardMotherBoardVoltageThresholdUpperNonRecoverable(1463),
    fltComputeABoardMotherBoardVoltageThresholdLowerNonRecoverable(1464),
    fltComputeABoardMotherBoardVoltageUpperThresholdCritical(1465),
    fltComputeABoardMotherBoardVoltageLowerThresholdCritical(1466),
    fltCimcvmediaActualMountEntryVmediaMountFailed(1467),
    fltFabricVlanPrimaryVlanMissingForIsolated(1468),
    fltFabricVlanPrimaryVlanMissingForCommunity(1469),
    fltFabricVlanMismatchA(1470),
    fltFabricVlanMismatchB(1471),
    fltFabricVlanErrorAssocPrimary(1472),
    fltStorageMezzFlashLifeConfigurationError(1494),
    fltStorageMezzFlashLifeDegraded(1495),
    fltStorageFlexFlashControllerMismatch(1496),
    fltStorageFlexFlashDriveUnhealthy(1497),
    fltStorageFlexFlashCardUnhealthy(1498),
    fltMgmtInterfaceNamedInbandVlanUnresolved(1506),
    fltMgmtInterfaceInbandUnsupportedServer(1507),
    fltMgmtInterfaceInbandUnsupportedFirmware(1508),
    fltComputePhysicalAdapterMismatch(1509),
    fltEquipmentSwitchCardAct2LiteFail(1510),
    fltEquipmentTpmSlaveTpm(1511),
    fltPoolElementDuplicatedAssigned(1512),
    fltSwVlanPortNsResourceStatusWarning(1519),
    fltNetworkElementMemoryerror(1520),
    fltMgmtPmonEntryFPRMProcessFailure(1541),
    fltSmSlotSmaHeartbeat(1545),
    fltSmSlotBladeNotWorking(1546),
    fltSmSlotDiskFormatFailed(1547),
    fltSmSlotBladeSwap(1548),
    fltOsControllerFailedBladeBootup(1568),
    fltOsControllerFailedBootupRecovery(1569),
    fltFirmwarePlatformPackBundleVersionMissing(1595),
    fltSmSecSvcSwitchConfigFail(1626),
    fltSmLogicalDeviceIncompleteConfig(1628),
    fltSmLogicalDeviceLogicalDeviceError(1629),
    fltEtherFtwPortPairBypass(1638),
    fltCommDateTimeCommNtpConfigurationFailed(1661),
    fltSmConfigIssueLogicalDeviceConfigError(1671),
    fltSmAppAppImageCorrupted(1673),
    fltEquipmentXcvrNonSupportedXcvr(1677),
    fltFabricSspEthMonDelAllSessEnabled(1679),
    fltIpsecConnectionIpsecConnInvalidKey(1681),
    fltIpsecConnectionIpsecConnInvalidCert(1682),
    fltIpsecAuthorityIpsecAuthorInvalidTp(1683),
    fltSmHotfixHotfixInstallFailed(1691),
    fltSmHotfixHotfixError(1692),
    fltSmCloudConnectorCloudRegistrationFailed(1694),
    fltSmCloudConnectorCloudUnregistrationFailed(1695),
    fltSmUnsignedCspLicenseUnsignedCSPLicenseInstalled(1716),
    fltSdLinkVnicConfigFail(1717),
    fltNwctrlCardConfigOffline(1718),
    fltNwctrlCardConfigFailed(1719),
    fltNwctrlCardConfigError(1720),
    fltNwctrlCardConfigOirFailed(1721),
    fltNwctrlCardConfigOirInvalid(1722),
    fltNwctrlCardConfigRemoval(1723),
    fltNwctrlCardConfigMismatch(1724),
    fltNwctrlCardConfigSupriseRemoval(1725),
    fltFirmwareRunnableAdapterUpgradeRequired(1729),
    fltSmClusterBootstrapCclSubnetNotSupported(1732),
    fltSmAppInstanceFailedConversion(1735),
    fltSmAppInstance2AppNotResponding(1736),
    fltSmAppInstance2AppInstallFailed(1737),
    fltSmAppInstance2AppStartFailed(1738),
    fltSmAppInstance2AppUpdateFailed(1739),
    fltSmAppInstance2AppStopFailed(1740),
    fltSmAppInstance2AppNotInstalled(1741),
    fltSmAppInstance2AppInstanceError(1742),
    fltSmAppInstance2AppInstanceUnsupported(1743),
    fltSmAppInstance2SoftwareIncompatible(1744),
    fltNetworkElementSamconfig(1750),
    fltSmAppInstance2AppFaultState(1757),
    fltSmExternalPortLinkConflictConfig(1758),
    fltFabricComputeSlotEpBladeDecommissionFail(1760),
    fltMemoryArrayServerBadMemorry(1761),
    fltFirmwareVersionIssueImageVersionMismatch(1767),
    fltFirmwareActivateIssueImageVersionMismatch(1768),
    fltFirmwareMgrVersionMismatchImageVersionMismatch(1769),
    fltFirmwareSupFirmwareFWUpgradeInProgress(1770),
    fltSysdebugMemoryOverallHighSystemMemoryUsage(1771),
    fltSysdebugMemoryProcessProcessStackMemoryHigh(1772),
    fltSysdebugMemoryProcessProcessHeapMemoryHigh(1773),
    fltSysdebugCpuOverallCpuUsageHigh(1774),
    fltSdInternalMgmtBootstrapInternalMgmtVnicConfigFail(1784),
    fltSdExternalLduLinkExternalLduLinkVnicConfigFail(1785),
    fltSdAppLduLinkAppLduLinkEndpoint1VnicConfigFail(1786),
    fltSdAppLduLinkAppLduLinkEndpoint2VnicConfigFail(1787),
    fltSdPreAllocatedVnicVnicPreAllocationFail(1788),
    fltSdLogicalDeviceDifferentResourcesInProfile(1789),
    fltEquipmentFpgaFpgaUpgradeRequired(1792),
    fltSmSlotAdapter2NotResponding(1793),
    fltSmSlotPlatformNotSupported(1794),
    fltSmSlotModuleNotSupported(1795),
    fltSmHwCryptoHwCryptoNotOperable(1796),
    fltSmErrorError0(1797),
    fltSmErrorError1(1798),
    fltEtherFtwPortPairPhyBypass(1799),
    fltEtherFtwPortPairPhyBypassErr(1800),
    fltPkiTpAutoImportTpAutoImportFailure(1803),
    fltPkiTpAutoImportTpAutoImportAttempt(1804),
    fltPkiKeyRingEc(1805),
    fltCommTelemetryTelemetryRegistrationFailed(1806),
    fltCommTelemetryTelemetryUnregistrationFailed(1807),
    fltCommTelemetryTelemetryGetDataFailed(1808),
    fltCommTelemetryTelemetrySendDataFailed(1809),
    fltCommNtpProviderCommNtpStratumCheckFailed(1810),
    fltAaaUserEpPasswordEncryptionKeyNotSet(1811),
    fltCommSshSSh3desUsageNotRecommended(1812),
    fltCommSshcSshc3desUsageNotRecommended(1813),
    fltCommDeviceManagerCommDeviceRegistrationPending(1814),
    fltCommDeviceManagerCommDeviceRegistrationFailed(1815),
    fltCommDeviceManagerCommDeviceUnRegistrationFailed(1816),
    fltCommDeviceManagerCommDeviceSftunnelDown(1817),
    fltCommDeviceManagerCommDeviceSfipproxyDown(1818),
    fltCommDeviceManagerCommDeviceManagerNotReachable(1819),
    fltMgmtImporterConfigurationImportFailed(1820),
    fltMgmtPmonEntryProcessRestarted(1821),
    fsmStFailEquipmentChassisRemoveChassisDecomission(16407),
    fsmStFailEquipmentLocatorLedSetLocatorLedExecute(16408),
    fsmStFailMgmtControllerExtMgmtIfConfigSecondary(16518),
    fsmStFailFabricComputeSlotEpIdentifyExecutePeer(16519),
    fsmStFailComputeBladeDiscoverSerialDebugDisconnect(16520),
    fsmStFailEquipmentChassisPsuPolicyConfigExecute(16533),
    fsmStFailAdaptorHostFcIfResetFcPersBindingExecutePeer(16534),
    fsmStFailComputeBladeDiagSerialDebugDisconnect(16535),
    fsmStFailFabricLanCloudSwitchModeSwConfigPeer(16539),
    fsmStFailVnicProfileSetDeployPeer(16550),
    fsmStFailCommSvcEpUpdateSvcEpSetEpPeer(16576),
    fsmStFailCommSvcEpRestartWebSvcPeer(16577),
    fsmStFailAaaEpUpdateEpSetEpPeer(16579),
    fsmStFailAaaRealmUpdateRealmSetRealmPeer(16580),
    fsmStFailAaaUserEpUpdateUserEpSetUserPeer(16581),
    fsmStFailPkiEpUpdateEpSetKeyRingPeer(16582),
    fsmStFailSysfileMutationSingleExecute(16600),
    fsmStFailSysfileMutationGlobalPeer(16601),
    fsmStFailSysdebugManualCoreFileExportTargetExportExecute(16604),
    fsmStFailSysdebugAutoCoreFileExportTargetConfigurePeer(16605),
    fsmStFailSysdebugLogControlEpLogControlPersistPeer(16606),
    fsmStFailSwAccessDomainDeployUpdateConnectivity(16634),
    fsmStFailSwEthLanBorderDeployUpdateVlanGroups(16635),
    fsmStFailSwFcSanBorderDeployUpdateConnectivity(16636),
    fsmStFailSwUtilityDomainDeployUpdateConnectivity(16637),
    fsmStFailSyntheticFsObjCreateCreateRemote(16641),
    fsmStFailFirmwareDownloaderDownloadUnpackLocal(16650),
    fsmStFailFirmwareImageDeleteRemote(16651),
    fsmStFailMgmtControllerUpdateSwitchVerifyRemote(16653),
    fsmStFailMgmtControllerUpdateIOMUpdateRequest(16654),
    fsmStFailMgmtControllerActivateIOMReset(16655),
    fsmStFailMgmtControllerUpdateBMCUpdateRequest(16656),
    fsmStFailMgmtControllerActivateBMCReset(16657),
    fsmStFailCallhomeEpConfigCallhomeSetPeer(16670),
    fsmStFailMgmtIfSwMgmtOobIfConfigSwitch(16673),
    fsmStFailMgmtIfSwMgmtInbandIfConfigSwitch(16674),
    fsmStFailMgmtIfVirtualIfConfigRemote(16679),
    fsmStFailMgmtIfEnableVipLocal(16680),
    fsmStFailMgmtIfDisableVipPeer(16681),
    fsmStFailMgmtIfEnableHALocal(16682),
    fsmStFailMgmtBackupBackupUpload(16683),
    fsmStFailMgmtImporterImportWaitForSwitch(16684),
    fsmStFailStatsCollectionPolicyUpdateEpSetEpB(16742),
    fsmStFailQosclassDefinitionConfigGlobalQoSSetPeer(16745),
    fsmStFailEpqosDefinitionDeployPeer(16749),
    fsmStFailEpqosDefinitionDelTaskRemovePeer(16750),
    fsmStFailEquipmentIOCardResetCmcExecute(16803),
    fsmStFailMgmtControllerUpdateFPRManagerStart(16815),
    fsmStFailMgmtControllerSysConfigSecondary(16823),
    fsmStFailAdaptorExtEthIfPathResetEnable(16852),
    fsmStFailAdaptorHostEthIfCircuitResetEnableB(16857),
    fsmStFailAdaptorHostFcIfCircuitResetEnableB(16858),
    fsmStFailExtvmmProviderConfigSetPeer(16879),
    fsmStFailExtvmmKeyStoreCertInstallSetPeer(16880),
    fsmStFailExtvmmSwitchDelTaskRemoveProviderRemoveLocal(16881),
    fsmStFailExtvmmMasterExtKeyConfigSetPeer(16898),
    fsmStFailCapabilityUpdaterUpdaterUnpackLocal(16904),
    fsmStFailFirmwareDistributableDeleteRemote(16906),
    fsmStFailCapabilityCatalogueDeployCatalogueFinalize(16931),
    fsmStFailEquipmentFexRemoveFexDecomission(16942),
    fsmStFailEquipmentLocatorLedSetFeLocatorLedExecute(16943),
    fsmStFailEquipmentChassisPowerCapConfig(16944),
    fsmStFailEquipmentIOCardMuxOfflineCleanupEntries(16945),
    fsmStFailComputePhysicalAssociateWaitForSspOsUpdateComplete(16973),
    fsmStFailComputePhysicalDisassociateSerialDebugPnuOSDisconnect(16974),
    fsmStFailComputePhysicalPowerCapConfig(16975),
    fsmStFailComputePhysicalDecommissionUnconfigExtMgmtRules(16976),
    fsmStFailComputePhysicalSoftShutdownExecute(16977),
    fsmStFailComputePhysicalHardShutdownExecute(16978),
    fsmStFailComputePhysicalTurnupExecute(16979),
    fsmStFailComputePhysicalPowercycleSanitize(16980),
    fsmStFailComputePhysicalHardresetSanitize(16981),
    fsmStFailComputePhysicalSoftresetSanitize(16982),
    fsmStFailComputePhysicalSwConnUpdB(16983),
    fsmStFailComputePhysicalBiosRecoveryWait(16984),
    fsmStFailComputePhysicalCmosResetSanitize(16986),
    fsmStFailComputePhysicalResetBmcExecute(16987),
    fsmStFailEquipmentIOCardResetIomExecute(16988),
    fsmStFailComputeRackUnitDiscoverWaitForConnReady(16994),
    fsmStFailLsServerConfigureCheckAssignedIdentifiersForDup(16995),
    fsmStFailSwEthMonDeployUpdateEthMon(17000),
    fsmStFailFabricSanCloudSwitchModeSwConfigPeer(17002),
    fsmStFailComputePhysicalUpdateExtUsersDeploy(17008),
    fsmStFailSysdebugTechSupportInitiateLocal(17012),
    fsmStFailSysdebugTechSupportDeleteTechSupFilePeer(17013),
    fsmStFailSysdebugTechSupportDownloadDeleteSub(17014),
    fsmStFailComputePhysicalUpdateAdaptorUpdateRequestPeer(17043),
    fsmStFailComputePhysicalActivateAdaptorReset(17044),
    fsmStFailCapabilityCatalogueActivateCatalogUnpackLocal(17045),
    fsmStFailCapabilityMgmtExtensionActivateMgmtExtUnpackLocal(17046),
    fsmStFailLicenseDownloaderDownloadValidateRemote(17050),
    fsmStFailLicenseFileInstallRemote(17051),
    fsmStFailLicenseFileClearRemote(17052),
    fsmStFailLicenseInstanceUpdateFlexlmRemote(17053),
    fsmStFailComputePhysicalConfigSoLExecute(17083),
    fsmStFailComputePhysicalUnconfigSoLExecute(17084),
    fsmStFailPortPIoInCompatSfpPresenceShutdown(17089),
    fsmStFailComputePhysicalDiagnosticInterruptExecute(17116),
    fsmStFailSysdebugCoreDownloadDeleteSub(17133),
    fsmStFailEquipmentChassisDynamicReallocationConfig(17134),
    fsmStFailComputePhysicalResetKvmExecute(17163),
    fsmStFailMgmtControllerOnlineSwConfigureConnPeer(17169),
    fsmStFailComputeRackUnitOfflineSwUnconfigurePeer(17170),
    fsmStFailEquipmentLocatorLedSetFiLocatorLedExecute(17187),
    fsmStFailFabricEpMgrConfigureWaitOnPhys(17214),
    fsmStFailVnicProfileSetDeployAliasPeer(17223),
    fsmStFailSwPhysConfPhysicalVerifyPhysConfig(17239),
    fsmStFailExtvmmEpClusterRoleSetPeer(17254),
    fsmStFailVmLifeCyclePolicyConfigPeer(17259),
    fsmStFailEquipmentBeaconLedIlluminateExecuteB(17262),
    fsmStFailEtherServerIntFIoConfigSpeedConfigure(17271),
    fsmStFailComputePhysicalUpdateBIOSUpdateRequest(17281),
    fsmStFailComputePhysicalActivateBIOSUpdateTokens(17282),
    fsmStFailIdentIdentRequestUpdateIdentExecute(17312),
    fsmStFailIdentMetaSystemSyncPing(17313),
    fsmStFailComputePhysicalResetIpmiExecute(17326),
    fsmStFailComputePhysicalFwUpgradeWaitForIBMCFwUpdate(17327),
    fsmStFailComputeRackUnitAdapterResetSanitize(17328),
    fsmStFailPortPIoInCompatSfpReplacedEnablePort(17358),
    fsmStFailExtpolEpRegisterFsmExecute(17359),
    fsmStFailExtpolRegistryCrossDomainConfigSetPeer(17360),
    fsmStFailExtpolRegistryCrossDomainDeleteSetPeer(17361),
    fsmStFailNfsMountInstMountVerifyRegistration(17377),
    fsmStFailNfsMountInstUnmountUnmountPeer(17378),
    fsmStFailNfsMountDefReportNfsMountSuspendReport(17379),
    fsmStFailStorageSystemSyncExecute(17395),
    fsmStFailFirmwareSystemDeployWaitForUserAck(17408),
    fsmStFailFirmwareSystemApplyCatalogPackResolveImages(17409),
    fsmStFailComputeServerDiscPolicyResolveScrubPolicyResolve(17426),
    fsmStFailSwFcSanBorderActivateZoneSetUpdateZones(17439),
    fsmStFailExtpolEpRepairCertVerifyGuid(17446),
    fsmStFailPolicyControlEpOperateResolve(17447),
    fsmStFailPolicyPolicyScopeReleasePolicyFsmRelease(17448),
    fsmStFailPolicyPolicyScopeReleaseOperationFsmRelease(17449),
    fsmStFailPolicyPolicyScopeReleaseStorageFsmRelease(17450),
    fsmStFailPolicyPolicyScopeResolveManyPolicyFsmResolveMany(17451),
    fsmStFailPolicyPolicyScopeResolveManyOperationFsmResolveMany(17452),
    fsmStFailPolicyPolicyScopeResolveManyStorageFsmResolveMany(17453),
    fsmStFailPolicyPolicyScopeReleaseManyPolicyFsmReleaseMany(17454),
    fsmStFailPolicyPolicyScopeReleaseManyOperationFsmReleaseMany(17455),
    fsmStFailPolicyPolicyScopeReleaseManyStorageFsmReleaseMany(17456),
    fsmStFailPolicyPolicyScopeResolveAllPolicyFsmResolveAll(17457),
    fsmStFailPolicyPolicyScopeResolveAllOperationFsmResolveAll(17458),
    fsmStFailPolicyPolicyScopeResolveAllStorageFsmResolveAll(17459),
    fsmStFailPolicyPolicyScopeReleaseAllPolicyFsmReleaseAll(17460),
    fsmStFailPolicyPolicyScopeReleaseAllOperationFsmReleaseAll(17461),
    fsmStFailPolicyPolicyScopeReleaseAllStorageFsmReleaseAll(17462),
    fsmStFailMgmtExportPolicyReportConfigCopyReport(17484),
    fsmStFailExtpolProviderReportConfigImportReport(17485),
    fsmStFailObserveObservedResolvePolicyFsmExecute(17491),
    fsmStFailObserveObservedResolveResourceFsmExecute(17492),
    fsmStFailObserveObservedResolveVMFsmExecute(17493),
    fsmStFailObserveObservedResolveControllerFsmExecute(17494),
    fsmStFailMgmtControllerRegistryConfigRemove(17499),
    fsmStFailGmetaHolderInventoryReportFullInventory(17608),
    fsmStFailComputePhysicalCimcSessionDeleteExecute(17609),
    fsmStFailPolicyControlledTypeOperateResolveAll(17612),
    fsmStFailFabricVnetEpSyncEpPushVnetEpDeletionSync(17619),
    fsmStFailMgmtIPv6IfAddrSwMgmtOobIpv6IfConfigSwitch(17665),
    fsmStFailComputePhysicalUpdateBoardControllerUpdateRequest(17667),
    fsmStFailExtvmmNetworkSetsDeployPeer(17703),
    fsmStFailComputePhysicalConfigBoardConfigMemoryPolicy(17707),
    fsmStFailComputePhysicalResetMemoryErrorsExecute(17708),
    fsmStFailMgmtControllerExtMgmtInterfaceConfigCMCVlanCfgPeer(17714),
    fsmStFailComputeRackUnitCreateDhcpEntryExecutePeer(17715),
    fsmStFailComputePhysicalServiceInfraDeploySwConfigPeer(17716),
    fsmStFailComputePhysicalServiceInfraWithdrawSwUnConfigPeer(17717),
    fsmStFailEquipmentIOCardBaseFePresenceIdentify(17808),
    fsmStFailEquipmentIOCardBaseFeConnResetBlades(17809),
    fsmStFailMgmtControllerLockConfigPowerButtonLockConfig(17813),
    fsmStFailSdAppInstanceInstallApplicationUpdateAppInstance(17819),
    fsmStFailSysdebugLogExportPolicyConfigurePeer(17830),
    fsmStFailComputePhysicalFlashControllerUpdateFlashLife(17839),
    fsmStFailOsControllerDeployOSHostWaitForSspOsRunning(17863),
    fsmStFailNhTableHolderConfigureLinksVerifyLinkConfig(17866),
    fsmStFailStorageFlexFlashControllerMOpsResetReset(17872),
    fsmStFailStorageFlexFlashControllerMOpsFormatFormat(17873),
    fsmStFailStorageFlexFlashControllerMOpsPairPair(17874),
    fsmStFailIdentMetaSystemFprcUnivSyncExecute(17877),
    fsmStFailComputePhysicalEnableCimcSecureBootUpdateRequest(17897),
    fsmStFailSdAppInstanceStartApplicationUpdateAppInstance(17911),
    fsmStFailSdLduProvisionLDUWaitForLinkConfiguration(17912),
    fsmStFailSwExtUtilityConfPortBreakoutVerifyBreakoutConfig(17917),
    fsmStFailNhTableHolderBootstrapLinksApplyConfig(17920),
    fsmStFailLicenseSmartConfigSetConfigLocal(17922),
    fsmStFailApplicationDownloaderDownloadVerify(17928),
    fsmStFailSmAppDeleteLocal(17948),
    fsmStFailOsControllerUpgradeOSRequestToUpgrade(17964),
    fsmStFailOsControllerInitOSRequestToUpgrade(17965),
    fsmStFailSdAppInstanceUpgradeApplicationUpgrade(17966),
    fsmStFailSdAppInstanceStopApplicationUpdateAppInstance(17967),
    fsmStFailSdAppInstanceUninstallApplicationUninstall(17968),
    fsmStFailSdSlotChangePlatformLogLevelSendCommand(17969),
    fsmStFailSdLogicalDeviceConfigureLinksWaitForSwitchConfig(17971),
    fsmStFailSdSlotFormatDiskWaitforDecommissionComplete(17974),
    fsmStFailSdSlotSynchTimeZoneUpdateTimeZone(17975),
    fsmStFailSdAppAttributeCtrlGetAppAttributesGetAttributes(17976),
    fsmStFailSdMgmtInfoUpdateMgmtInfoSendUpdate(17977),
    fsmStFailSdNetMgmtBootstrapUpdateNetMgmtBootstrapSendUpdate(17978),
    fsmStFailFirmwarePlatformPackPlatformVersionWaitForReady(17984),
    fsmStFailSwSspEthMonDeployUpdateSspEthMon(18000),
    fsmStFailSdClusterBootstrapUpdateClusterConfigurationSendConfig(18003),
    fsmStFailIpsecEpUpdateEpApplyConfig(18020),
    fsmStFailEtherFtwPortPairConfigFtwConfigure(18023),
    fsmStFailSdLinkUpdateInterfaceStatusSendStatus(18024),
    fsmStFailSdUpgradeTaskStopUpgradeStartAppWaitForUpgradeApp(18025),
    fsmStFailSwSspEthMonSrcPhyEpDeleteDeletePcapFile(18034),
    fsmStFailFirmwareSupFirmwareDeployResetChassis(18035),
    fsmStFailEquipmentChassisShutdownChassisWaitForBladeShutdown(18043),
    fsmStFailSmCloudConnectorRegisterCloudConnectorRegister(18051),
    fsmStFailSmCloudConnectorUnRegisterCloudConnectorUnRegister(18052),
    fsmStFailSmAppVerifyApplicationVerify(18053),
    fsmStFailSmLogicalDeviceConfigureValidateLDConfig(18056),
    fsmStFailSdLduUpdateInterfaceStatusSendStatus(18058),
    fsmStFailSdLogicalDeviceConfigureUserMacsWaitForSwitchConfig(18059),
    fsmStFailEquipmentChassisRebootChassisWaitForBladeShutdown(18060),
    fsmStFailFirmwareValidationStatusValidatePlatformPack(18064),
    fsmStFailSdPortsBundleBundleDataPortsWaitForConfigCompletion(18081),
    fsmStFailSdHotfixInstallHotfixUpdateHotfix(18082),
    fsmStFailSdHotfixUninstallHotfixUpdateHotfix(18083),
    fsmStFailOsControllerInstallLicenseWaitForLicInstalledComplete(18092),
    fsmStFailSmUnsignedCspLicenseDeployWaitForReady(18098),
    fsmStFailSmLicenseFileDeleteLocal(18099),
    fsmStFailComputePhysicalUpdateAdaptorBootUpdateRequestPeer(18112),
    fsmStFailSmAppInstance2ResetApplicationWaitForStopApp(18129),
    fsmStFailSdLogicalDeviceConfigureMacsWaitForSwitchConfig(18135),
    fsmStFailSdAppInstSettingsTaskSendAppInstSettingsUpdateSettings(18136),
    fsmStFailComputePhysicalHardPowercycleExecute(18146),
    fsmStFailSysdebugMemoryHeadDeployApplyConfig(18159),
    fsmStFailSysdebugCpuOverallHeadDeployApplyConfig(18160),
    fsmStFailSdCspMetaCtrlRetrieveCSPMetaRetrieve(18174),
    fsmStFailSdAppInstanceGracefulStopAppApply(18175),
    fsmStFailCommTelemetryDataExchSeqSendTelemetryData(18185),
    fsmStFailCommTelemetryEnableDisableTelemetryUnRegister(18186),
    fsmRmtErrEquipmentChassisRemoveChassisDecomission(77847),
    fsmRmtErrEquipmentLocatorLedSetLocatorLedExecute(77848),
    fsmRmtErrMgmtControllerExtMgmtIfConfigSecondary(77958),
    fsmRmtErrFabricComputeSlotEpIdentifyExecutePeer(77959),
    fsmRmtErrComputeBladeDiscoverSerialDebugDisconnect(77960),
    fsmRmtErrEquipmentChassisPsuPolicyConfigExecute(77973),
    fsmRmtErrAdaptorHostFcIfResetFcPersBindingExecutePeer(77974),
    fsmRmtErrComputeBladeDiagSerialDebugDisconnect(77975),
    fsmRmtErrFabricLanCloudSwitchModeSwConfigPeer(77979),
    fsmRmtErrVnicProfileSetDeployPeer(77990),
    fsmRmtErrCommSvcEpUpdateSvcEpSetEpPeer(78016),
    fsmRmtErrCommSvcEpRestartWebSvcPeer(78017),
    fsmRmtErrAaaEpUpdateEpSetEpPeer(78019),
    fsmRmtErrAaaRealmUpdateRealmSetRealmPeer(78020),
    fsmRmtErrAaaUserEpUpdateUserEpSetUserPeer(78021),
    fsmRmtErrPkiEpUpdateEpSetKeyRingPeer(78022),
    fsmRmtErrSysfileMutationSingleExecute(78040),
    fsmRmtErrSysfileMutationGlobalPeer(78041),
    fsmRmtErrSysdebugManualCoreFileExportTargetExportExecute(78044),
    fsmRmtErrSysdebugAutoCoreFileExportTargetConfigurePeer(78045),
    fsmRmtErrSysdebugLogControlEpLogControlPersistPeer(78046),
    fsmRmtErrSwAccessDomainDeployUpdateConnectivity(78074),
    fsmRmtErrSwEthLanBorderDeployUpdateVlanGroups(78075),
    fsmRmtErrSwFcSanBorderDeployUpdateConnectivity(78076),
    fsmRmtErrSwUtilityDomainDeployUpdateConnectivity(78077),
    fsmRmtErrSyntheticFsObjCreateCreateRemote(78081),
    fsmRmtErrFirmwareDownloaderDownloadUnpackLocal(78090),
    fsmRmtErrFirmwareImageDeleteRemote(78091),
    fsmRmtErrMgmtControllerUpdateSwitchVerifyRemote(78093),
    fsmRmtErrMgmtControllerUpdateIOMUpdateRequest(78094),
    fsmRmtErrMgmtControllerActivateIOMReset(78095),
    fsmRmtErrMgmtControllerUpdateBMCUpdateRequest(78096),
    fsmRmtErrMgmtControllerActivateBMCReset(78097),
    fsmRmtErrCallhomeEpConfigCallhomeSetPeer(78110),
    fsmRmtErrMgmtIfSwMgmtOobIfConfigSwitch(78113),
    fsmRmtErrMgmtIfSwMgmtInbandIfConfigSwitch(78114),
    fsmRmtErrMgmtIfVirtualIfConfigRemote(78119),
    fsmRmtErrMgmtIfEnableVipLocal(78120),
    fsmRmtErrMgmtIfDisableVipPeer(78121),
    fsmRmtErrMgmtIfEnableHALocal(78122),
    fsmRmtErrMgmtBackupBackupUpload(78123),
    fsmRmtErrMgmtImporterImportWaitForSwitch(78124),
    fsmRmtErrStatsCollectionPolicyUpdateEpSetEpB(78182),
    fsmRmtErrQosclassDefinitionConfigGlobalQoSSetPeer(78185),
    fsmRmtErrEpqosDefinitionDeployPeer(78189),
    fsmRmtErrEpqosDefinitionDelTaskRemovePeer(78190),
    fsmRmtErrEquipmentIOCardResetCmcExecute(78243),
    fsmRmtErrMgmtControllerUpdateFPRManagerStart(78255),
    fsmRmtErrMgmtControllerSysConfigSecondary(78263),
    fsmRmtErrAdaptorExtEthIfPathResetEnable(78292),
    fsmRmtErrAdaptorHostEthIfCircuitResetEnableB(78297),
    fsmRmtErrAdaptorHostFcIfCircuitResetEnableB(78298),
    fsmRmtErrExtvmmProviderConfigSetPeer(78319),
    fsmRmtErrExtvmmKeyStoreCertInstallSetPeer(78320),
    fsmRmtErrExtvmmSwitchDelTaskRemoveProviderRemoveLocal(78321),
    fsmRmtErrExtvmmMasterExtKeyConfigSetPeer(78338),
    fsmRmtErrCapabilityUpdaterUpdaterUnpackLocal(78344),
    fsmRmtErrFirmwareDistributableDeleteRemote(78346),
    fsmRmtErrCapabilityCatalogueDeployCatalogueFinalize(78371),
    fsmRmtErrEquipmentFexRemoveFexDecomission(78382),
    fsmRmtErrEquipmentLocatorLedSetFeLocatorLedExecute(78383),
    fsmRmtErrEquipmentChassisPowerCapConfig(78384),
    fsmRmtErrEquipmentIOCardMuxOfflineCleanupEntries(78385),
    fsmRmtErrComputePhysicalAssociateWaitForSspOsUpdateComplete(78413),
    fsmRmtErrComputePhysicalDisassociateSerialDebugPnuOSDisconnect(78414),
    fsmRmtErrComputePhysicalPowerCapConfig(78415),
    fsmRmtErrComputePhysicalDecommissionUnconfigExtMgmtRules(78416),
    fsmRmtErrComputePhysicalSoftShutdownExecute(78417),
    fsmRmtErrComputePhysicalHardShutdownExecute(78418),
    fsmRmtErrComputePhysicalTurnupExecute(78419),
    fsmRmtErrComputePhysicalPowercycleSanitize(78420),
    fsmRmtErrComputePhysicalHardresetSanitize(78421),
    fsmRmtErrComputePhysicalSoftresetSanitize(78422),
    fsmRmtErrComputePhysicalSwConnUpdB(78423),
    fsmRmtErrComputePhysicalBiosRecoveryWait(78424),
    fsmRmtErrComputePhysicalCmosResetSanitize(78426),
    fsmRmtErrComputePhysicalResetBmcExecute(78427),
    fsmRmtErrEquipmentIOCardResetIomExecute(78428),
    fsmRmtErrComputeRackUnitDiscoverWaitForConnReady(78434),
    fsmRmtErrLsServerConfigureCheckAssignedIdentifiersForDup(78435),
    fsmRmtErrSwEthMonDeployUpdateEthMon(78440),
    fsmRmtErrFabricSanCloudSwitchModeSwConfigPeer(78442),
    fsmRmtErrComputePhysicalUpdateExtUsersDeploy(78448),
    fsmRmtErrSysdebugTechSupportInitiateLocal(78452),
    fsmRmtErrSysdebugTechSupportDeleteTechSupFilePeer(78453),
    fsmRmtErrSysdebugTechSupportDownloadDeleteSub(78454),
    fsmRmtErrComputePhysicalUpdateAdaptorUpdateRequestPeer(78483),
    fsmRmtErrComputePhysicalActivateAdaptorReset(78484),
    fsmRmtErrCapabilityCatalogueActivateCatalogUnpackLocal(78485),
    fsmRmtErrCapabilityMgmtExtensionActivateMgmtExtUnpackLocal(78486),
    fsmRmtErrLicenseDownloaderDownloadValidateRemote(78490),
    fsmRmtErrLicenseFileInstallRemote(78491),
    fsmRmtErrLicenseFileClearRemote(78492),
    fsmRmtErrLicenseInstanceUpdateFlexlmRemote(78493),
    fsmRmtErrComputePhysicalConfigSoLExecute(78523),
    fsmRmtErrComputePhysicalUnconfigSoLExecute(78524),
    fsmRmtErrPortPIoInCompatSfpPresenceShutdown(78529),
    fsmRmtErrComputePhysicalDiagnosticInterruptExecute(78556),
    fsmRmtErrSysdebugCoreDownloadDeleteSub(78573),
    fsmRmtErrEquipmentChassisDynamicReallocationConfig(78574),
    fsmRmtErrComputePhysicalResetKvmExecute(78603),
    fsmRmtErrMgmtControllerOnlineSwConfigureConnPeer(78609),
    fsmRmtErrComputeRackUnitOfflineSwUnconfigurePeer(78610),
    fsmRmtErrEquipmentLocatorLedSetFiLocatorLedExecute(78627),
    fsmRmtErrFabricEpMgrConfigureWaitOnPhys(78654),
    fsmRmtErrVnicProfileSetDeployAliasPeer(78663),
    fsmRmtErrSwPhysConfPhysicalVerifyPhysConfig(78679),
    fsmRmtErrExtvmmEpClusterRoleSetPeer(78694),
    fsmRmtErrVmLifeCyclePolicyConfigPeer(78699),
    fsmRmtErrEquipmentBeaconLedIlluminateExecuteB(78702),
    fsmRmtErrEtherServerIntFIoConfigSpeedConfigure(78711),
    fsmRmtErrComputePhysicalUpdateBIOSUpdateRequest(78721),
    fsmRmtErrComputePhysicalActivateBIOSUpdateTokens(78722),
    fsmRmtErrIdentIdentRequestUpdateIdentExecute(78752),
    fsmRmtErrIdentMetaSystemSyncPing(78753),
    fsmRmtErrComputePhysicalResetIpmiExecute(78766),
    fsmRmtErrComputePhysicalFwUpgradeWaitForIBMCFwUpdate(78767),
    fsmRmtErrComputeRackUnitAdapterResetSanitize(78768),
    fsmRmtErrPortPIoInCompatSfpReplacedEnablePort(78798),
    fsmRmtErrExtpolEpRegisterFsmExecute(78799),
    fsmRmtErrExtpolRegistryCrossDomainConfigSetPeer(78800),
    fsmRmtErrExtpolRegistryCrossDomainDeleteSetPeer(78801),
    fsmRmtErrNfsMountInstMountVerifyRegistration(78817),
    fsmRmtErrNfsMountInstUnmountUnmountPeer(78818),
    fsmRmtErrNfsMountDefReportNfsMountSuspendReport(78819),
    fsmRmtErrStorageSystemSyncExecute(78835),
    fsmRmtErrFirmwareSystemDeployWaitForUserAck(78848),
    fsmRmtErrFirmwareSystemApplyCatalogPackResolveImages(78849),
    fsmRmtErrComputeServerDiscPolicyResolveScrubPolicyResolve(78866),
    fsmRmtErrSwFcSanBorderActivateZoneSetUpdateZones(78879),
    fsmRmtErrExtpolEpRepairCertVerifyGuid(78886),
    fsmRmtErrPolicyControlEpOperateResolve(78887),
    fsmRmtErrPolicyPolicyScopeReleasePolicyFsmRelease(78888),
    fsmRmtErrPolicyPolicyScopeReleaseOperationFsmRelease(78889),
    fsmRmtErrPolicyPolicyScopeReleaseStorageFsmRelease(78890),
    fsmRmtErrPolicyPolicyScopeResolveManyPolicyFsmResolveMany(78891),
    fsmRmtErrPolicyPolicyScopeResolveManyOperationFsmResolveMany(78892),
    fsmRmtErrPolicyPolicyScopeResolveManyStorageFsmResolveMany(78893),
    fsmRmtErrPolicyPolicyScopeReleaseManyPolicyFsmReleaseMany(78894),
    fsmRmtErrPolicyPolicyScopeReleaseManyOperationFsmReleaseMany(78895),
    fsmRmtErrPolicyPolicyScopeReleaseManyStorageFsmReleaseMany(78896),
    fsmRmtErrPolicyPolicyScopeResolveAllPolicyFsmResolveAll(78897),
    fsmRmtErrPolicyPolicyScopeResolveAllOperationFsmResolveAll(78898),
    fsmRmtErrPolicyPolicyScopeResolveAllStorageFsmResolveAll(78899),
    fsmRmtErrPolicyPolicyScopeReleaseAllPolicyFsmReleaseAll(78900),
    fsmRmtErrPolicyPolicyScopeReleaseAllOperationFsmReleaseAll(78901),
    fsmRmtErrPolicyPolicyScopeReleaseAllStorageFsmReleaseAll(78902),
    fsmRmtErrMgmtExportPolicyReportConfigCopyReport(78924),
    fsmRmtErrExtpolProviderReportConfigImportReport(78925),
    fsmRmtErrObserveObservedResolvePolicyFsmExecute(78931),
    fsmRmtErrObserveObservedResolveResourceFsmExecute(78932),
    fsmRmtErrObserveObservedResolveVMFsmExecute(78933),
    fsmRmtErrObserveObservedResolveControllerFsmExecute(78934),
    fsmRmtErrMgmtControllerRegistryConfigRemove(78939),
    fsmRmtErrGmetaHolderInventoryReportFullInventory(79048),
    fsmRmtErrComputePhysicalCimcSessionDeleteExecute(79049),
    fsmRmtErrPolicyControlledTypeOperateResolveAll(79052),
    fsmRmtErrFabricVnetEpSyncEpPushVnetEpDeletionSync(79059),
    fsmRmtErrMgmtIPv6IfAddrSwMgmtOobIpv6IfConfigSwitch(79105),
    fsmRmtErrComputePhysicalUpdateBoardControllerUpdateRequest(79107),
    fsmRmtErrExtvmmNetworkSetsDeployPeer(79143),
    fsmRmtErrComputePhysicalConfigBoardConfigMemoryPolicy(79147),
    fsmRmtErrComputePhysicalResetMemoryErrorsExecute(79148),
    fsmRmtErrMgmtControllerExtMgmtInterfaceConfigCMCVlanCfgPeer(79154),
    fsmRmtErrComputeRackUnitCreateDhcpEntryExecutePeer(79155),
    fsmRmtErrComputePhysicalServiceInfraDeploySwConfigPeer(79156),
    fsmRmtErrComputePhysicalServiceInfraWithdrawSwUnConfigPeer(79157),
    fsmRmtErrEquipmentIOCardBaseFePresenceIdentify(79248),
    fsmRmtErrEquipmentIOCardBaseFeConnResetBlades(79249),
    fsmRmtErrMgmtControllerLockConfigPowerButtonLockConfig(79253),
    fsmRmtErrSdAppInstanceInstallApplicationUpdateAppInstance(79259),
    fsmRmtErrSysdebugLogExportPolicyConfigurePeer(79270),
    fsmRmtErrComputePhysicalFlashControllerUpdateFlashLife(79279),
    fsmRmtErrOsControllerDeployOSHostWaitForSspOsRunning(79303),
    fsmRmtErrNhTableHolderConfigureLinksVerifyLinkConfig(79306),
    fsmRmtErrStorageFlexFlashControllerMOpsResetReset(79312),
    fsmRmtErrStorageFlexFlashControllerMOpsFormatFormat(79313),
    fsmRmtErrStorageFlexFlashControllerMOpsPairPair(79314),
    fsmRmtErrIdentMetaSystemFprcUnivSyncExecute(79317),
    fsmRmtErrComputePhysicalEnableCimcSecureBootUpdateRequest(79337),
    fsmRmtErrSdAppInstanceStartApplicationUpdateAppInstance(79351),
    fsmRmtErrSdLduProvisionLDUWaitForLinkConfiguration(79352),
    fsmRmtErrSwExtUtilityConfPortBreakoutVerifyBreakoutConfig(79357),
    fsmRmtErrNhTableHolderBootstrapLinksApplyConfig(79360),
    fsmRmtErrLicenseSmartConfigSetConfigLocal(79362),
    fsmRmtErrApplicationDownloaderDownloadVerify(79368),
    fsmRmtErrSmAppDeleteLocal(79388),
    fsmRmtErrOsControllerUpgradeOSRequestToUpgrade(79404),
    fsmRmtErrOsControllerInitOSRequestToUpgrade(79405),
    fsmRmtErrSdAppInstanceUpgradeApplicationUpgrade(79406),
    fsmRmtErrSdAppInstanceStopApplicationUpdateAppInstance(79407),
    fsmRmtErrSdAppInstanceUninstallApplicationUninstall(79408),
    fsmRmtErrSdSlotChangePlatformLogLevelSendCommand(79409),
    fsmRmtErrSdLogicalDeviceConfigureLinksWaitForSwitchConfig(79411),
    fsmRmtErrSdSlotFormatDiskWaitforDecommissionComplete(79414),
    fsmRmtErrSdSlotSynchTimeZoneUpdateTimeZone(79415),
    fsmRmtErrSdAppAttributeCtrlGetAppAttributesGetAttributes(79416),
    fsmRmtErrSdMgmtInfoUpdateMgmtInfoSendUpdate(79417),
    fsmRmtErrSdNetMgmtBootstrapUpdateNetMgmtBootstrapSendUpdate(79418),
    fsmRmtErrFirmwarePlatformPackPlatformVersionWaitForReady(79424),
    fsmRmtErrSwSspEthMonDeployUpdateSspEthMon(79440),
    fsmRmtErrSdClusterBootstrapUpdateClusterConfigurationSendConfig(79443),
    fsmRmtErrIpsecEpUpdateEpApplyConfig(79460),
    fsmRmtErrEtherFtwPortPairConfigFtwConfigure(79463),
    fsmRmtErrSdLinkUpdateInterfaceStatusSendStatus(79464),
    fsmRmtErrSdUpgradeTaskStopUpgradeStartAppWaitForUpgradeApp(79465),
    fsmRmtErrSwSspEthMonSrcPhyEpDeleteDeletePcapFile(79474),
    fsmRmtErrFirmwareSupFirmwareDeployResetChassis(79475),
    fsmRmtErrEquipmentChassisShutdownChassisWaitForBladeShutdown(79483),
    fsmRmtErrSmCloudConnectorRegisterCloudConnectorRegister(79491),
    fsmRmtErrSmCloudConnectorUnRegisterCloudConnectorUnRegister(79492),
    fsmRmtErrSmAppVerifyApplicationVerify(79493),
    fsmRmtErrSmLogicalDeviceConfigureValidateLDConfig(79496),
    fsmRmtErrSdLduUpdateInterfaceStatusSendStatus(79498),
    fsmRmtErrSdLogicalDeviceConfigureUserMacsWaitForSwitchConfig(79499),
    fsmRmtErrEquipmentChassisRebootChassisWaitForBladeShutdown(79500),
    fsmRmtErrFirmwareValidationStatusValidatePlatformPack(79504),
    fsmRmtErrSdPortsBundleBundleDataPortsWaitForConfigCompletion(79521),
    fsmRmtErrSdHotfixInstallHotfixUpdateHotfix(79522),
    fsmRmtErrSdHotfixUninstallHotfixUpdateHotfix(79523),
    fsmRmtErrOsControllerInstallLicenseWaitForLicInstalledComplete(79532),
    fsmRmtErrSmUnsignedCspLicenseDeployWaitForReady(79538),
    fsmRmtErrSmLicenseFileDeleteLocal(79539),
    fsmRmtErrComputePhysicalUpdateAdaptorBootUpdateRequestPeer(79552),
    fsmRmtErrSmAppInstance2ResetApplicationWaitForStopApp(79569),
    fsmRmtErrSdLogicalDeviceConfigureMacsWaitForSwitchConfig(79575),
    fsmRmtErrSdAppInstSettingsTaskSendAppInstSettingsUpdateSettings(79576),
    fsmRmtErrComputePhysicalHardPowercycleExecute(79586),
    fsmRmtErrSysdebugMemoryHeadDeployApplyConfig(79599),
    fsmRmtErrSysdebugCpuOverallHeadDeployApplyConfig(79600),
    fsmRmtErrSdCspMetaCtrlRetrieveCSPMetaRetrieve(79614),
    fsmRmtErrSdAppInstanceGracefulStopAppApply(79615),
    fsmRmtErrCommTelemetryDataExchSeqSendTelemetryData(79625),
    fsmRmtErrCommTelemetryEnableDisableTelemetryUnRegister(79626),
    fsmFailEquipmentChassisRemoveChassis(999447),
    fsmFailEquipmentLocatorLedSetLocatorLed(999448),
    fsmFailMgmtControllerExtMgmtIfConfig(999558),
    fsmFailFabricComputeSlotEpIdentify(999559),
    fsmFailComputeBladeDiscover(999560),
    fsmFailEquipmentChassisPsuPolicyConfig(999573),
    fsmFailAdaptorHostFcIfResetFcPersBinding(999574),
    fsmFailComputeBladeDiag(999575),
    fsmFailFabricLanCloudSwitchMode(999579),
    fsmFailVnicProfileSetDeploy(999590),
    fsmFailCommSvcEpUpdateSvcEp(999616),
    fsmFailCommSvcEpRestartWebSvc(999617),
    fsmFailAaaEpUpdateEp(999619),
    fsmFailAaaRealmUpdateRealm(999620),
    fsmFailAaaUserEpUpdateUserEp(999621),
    fsmFailPkiEpUpdateEp(999622),
    fsmFailSysfileMutationSingle(999640),
    fsmFailSysfileMutationGlobal(999641),
    fsmFailSysdebugManualCoreFileExportTargetExport(999644),
    fsmFailSysdebugAutoCoreFileExportTargetConfigure(999645),
    fsmFailSysdebugLogControlEpLogControlPersist(999646),
    fsmFailSwAccessDomainDeploy(999674),
    fsmFailSwEthLanBorderDeploy(999675),
    fsmFailSwFcSanBorderDeploy(999676),
    fsmFailSwUtilityDomainDeploy(999677),
    fsmFailSyntheticFsObjCreate(999681),
    fsmFailFirmwareDownloaderDownload(999690),
    fsmFailFirmwareImageDelete(999691),
    fsmFailMgmtControllerUpdateSwitch(999693),
    fsmFailMgmtControllerUpdateIOM(999694),
    fsmFailMgmtControllerActivateIOM(999695),
    fsmFailMgmtControllerUpdateBMC(999696),
    fsmFailMgmtControllerActivateBMC(999697),
    fsmFailCallhomeEpConfigCallhome(999710),
    fsmFailMgmtIfSwMgmtOobIfConfig(999713),
    fsmFailMgmtIfSwMgmtInbandIfConfig(999714),
    fsmFailMgmtIfVirtualIfConfig(999719),
    fsmFailMgmtIfEnableVip(999720),
    fsmFailMgmtIfDisableVip(999721),
    fsmFailMgmtIfEnableHA(999722),
    fsmFailMgmtBackupBackup(999723),
    fsmFailMgmtImporterImport(999724),
    fsmFailStatsCollectionPolicyUpdateEp(999782),
    fsmFailQosclassDefinitionConfigGlobalQoS(999785),
    fsmFailEpqosDefinitionDeploy(999789),
    fsmFailEpqosDefinitionDelTaskRemove(999790),
    fsmFailEquipmentIOCardResetCmc(999843),
    fsmFailMgmtControllerUpdateFPRManager(999855),
    fsmFailMgmtControllerSysConfig(999863),
    fsmFailAdaptorExtEthIfPathReset(999892),
    fsmFailAdaptorHostEthIfCircuitReset(999897),
    fsmFailAdaptorHostFcIfCircuitReset(999898),
    fsmFailExtvmmProviderConfig(999919),
    fsmFailExtvmmKeyStoreCertInstall(999920),
    fsmFailExtvmmSwitchDelTaskRemoveProvider(999921),
    fsmFailExtvmmMasterExtKeyConfig(999938),
    fsmFailCapabilityUpdaterUpdater(999944),
    fsmFailFirmwareDistributableDelete(999946),
    fsmFailCapabilityCatalogueDeployCatalogue(999971),
    fsmFailEquipmentFexRemoveFex(999982),
    fsmFailEquipmentLocatorLedSetFeLocatorLed(999983),
    fsmFailEquipmentChassisPowerCap(999984),
    fsmFailEquipmentIOCardMuxOffline(999985),
    fsmFailComputePhysicalAssociate(1000013),
    fsmFailComputePhysicalDisassociate(1000014),
    fsmFailComputePhysicalPowerCap(1000015),
    fsmFailComputePhysicalDecommission(1000016),
    fsmFailComputePhysicalSoftShutdown(1000017),
    fsmFailComputePhysicalHardShutdown(1000018),
    fsmFailComputePhysicalTurnup(1000019),
    fsmFailComputePhysicalPowercycle(1000020),
    fsmFailComputePhysicalHardreset(1000021),
    fsmFailComputePhysicalSoftreset(1000022),
    fsmFailComputePhysicalSwConnUpd(1000023),
    fsmFailComputePhysicalBiosRecovery(1000024),
    fsmFailComputePhysicalCmosReset(1000026),
    fsmFailComputePhysicalResetBmc(1000027),
    fsmFailEquipmentIOCardResetIom(1000028),
    fsmFailComputeRackUnitDiscover(1000034),
    fsmFailLsServerConfigure(1000035),
    fsmFailSwEthMonDeploy(1000040),
    fsmFailFabricSanCloudSwitchMode(1000042),
    fsmFailComputePhysicalUpdateExtUsers(1000048),
    fsmFailSysdebugTechSupportInitiate(1000052),
    fsmFailSysdebugTechSupportDeleteTechSupFile(1000053),
    fsmFailSysdebugTechSupportDownload(1000054),
    fsmFailComputePhysicalUpdateAdaptor(1000083),
    fsmFailComputePhysicalActivateAdaptor(1000084),
    fsmFailCapabilityCatalogueActivateCatalog(1000085),
    fsmFailCapabilityMgmtExtensionActivateMgmtExt(1000086),
    fsmFailLicenseDownloaderDownload(1000090),
    fsmFailLicenseFileInstall(1000091),
    fsmFailLicenseFileClear(1000092),
    fsmFailLicenseInstanceUpdateFlexlm(1000093),
    fsmFailComputePhysicalConfigSoL(1000123),
    fsmFailComputePhysicalUnconfigSoL(1000124),
    fsmFailPortPIoInCompatSfpPresence(1000129),
    fsmFailComputePhysicalDiagnosticInterrupt(1000156),
    fsmFailSysdebugCoreDownload(1000173),
    fsmFailEquipmentChassisDynamicReallocation(1000174),
    fsmFailComputePhysicalResetKvm(1000203),
    fsmFailMgmtControllerOnline(1000209),
    fsmFailComputeRackUnitOffline(1000210),
    fsmFailEquipmentLocatorLedSetFiLocatorLed(1000227),
    fsmFailFabricEpMgrConfigure(1000254),
    fsmFailVnicProfileSetDeployAlias(1000263),
    fsmFailSwPhysConfPhysical(1000279),
    fsmFailExtvmmEpClusterRole(1000294),
    fsmFailVmLifeCyclePolicyConfig(1000299),
    fsmFailEquipmentBeaconLedIlluminate(1000302),
    fsmFailEtherServerIntFIoConfigSpeed(1000311),
    fsmFailComputePhysicalUpdateBIOS(1000321),
    fsmFailComputePhysicalActivateBIOS(1000322),
    fsmFailIdentIdentRequestUpdateIdent(1000352),
    fsmFailIdentMetaSystemSync(1000353),
    fsmFailComputePhysicalResetIpmi(1000366),
    fsmFailComputePhysicalFwUpgrade(1000367),
    fsmFailComputeRackUnitAdapterReset(1000368),
    fsmFailPortPIoInCompatSfpReplaced(1000398),
    fsmFailExtpolEpRegisterFsm(1000399),
    fsmFailExtpolRegistryCrossDomainConfig(1000400),
    fsmFailExtpolRegistryCrossDomainDelete(1000401),
    fsmFailNfsMountInstMount(1000417),
    fsmFailNfsMountInstUnmount(1000418),
    fsmFailNfsMountDefReportNfsMountSuspend(1000419),
    fsmFailStorageSystemSync(1000435),
    fsmFailFirmwareSystemDeploy(1000448),
    fsmFailFirmwareSystemApplyCatalogPack(1000449),
    fsmFailComputeServerDiscPolicyResolveScrubPolicy(1000466),
    fsmFailSwFcSanBorderActivateZoneSet(1000479),
    fsmFailExtpolEpRepairCert(1000486),
    fsmFailPolicyControlEpOperate(1000487),
    fsmFailPolicyPolicyScopeReleasePolicyFsm(1000488),
    fsmFailPolicyPolicyScopeReleaseOperationFsm(1000489),
    fsmFailPolicyPolicyScopeReleaseStorageFsm(1000490),
    fsmFailPolicyPolicyScopeResolveManyPolicyFsm(1000491),
    fsmFailPolicyPolicyScopeResolveManyOperationFsm(1000492),
    fsmFailPolicyPolicyScopeResolveManyStorageFsm(1000493),
    fsmFailPolicyPolicyScopeReleaseManyPolicyFsm(1000494),
    fsmFailPolicyPolicyScopeReleaseManyOperationFsm(1000495),
    fsmFailPolicyPolicyScopeReleaseManyStorageFsm(1000496),
    fsmFailPolicyPolicyScopeResolveAllPolicyFsm(1000497),
    fsmFailPolicyPolicyScopeResolveAllOperationFsm(1000498),
    fsmFailPolicyPolicyScopeResolveAllStorageFsm(1000499),
    fsmFailPolicyPolicyScopeReleaseAllPolicyFsm(1000500),
    fsmFailPolicyPolicyScopeReleaseAllOperationFsm(1000501),
    fsmFailPolicyPolicyScopeReleaseAllStorageFsm(1000502),
    fsmFailMgmtExportPolicyReportConfigCopy(1000524),
    fsmFailExtpolProviderReportConfigImport(1000525),
    fsmFailObserveObservedResolvePolicyFsm(1000531),
    fsmFailObserveObservedResolveResourceFsm(1000532),
    fsmFailObserveObservedResolveVMFsm(1000533),
    fsmFailObserveObservedResolveControllerFsm(1000534),
    fsmFailMgmtControllerRegistryConfig(1000539),
    fsmFailGmetaHolderInventory(1000648),
    fsmFailComputePhysicalCimcSessionDelete(1000649),
    fsmFailPolicyControlledTypeOperate(1000652),
    fsmFailFabricVnetEpSyncEpPushVnetEpDeletion(1000659),
    fsmFailMgmtIPv6IfAddrSwMgmtOobIpv6IfConfig(1000705),
    fsmFailComputePhysicalUpdateBoardController(1000707),
    fsmFailExtvmmNetworkSetsDeploy(1000743),
    fsmFailComputePhysicalConfigBoard(1000747),
    fsmFailComputePhysicalResetMemoryErrors(1000748),
    fsmFailMgmtControllerExtMgmtInterfaceConfig(1000754),
    fsmFailComputeRackUnitCreateDhcpEntry(1000755),
    fsmFailComputePhysicalServiceInfraDeploy(1000756),
    fsmFailComputePhysicalServiceInfraWithdraw(1000757),
    fsmFailEquipmentIOCardBaseFePresence(1000848),
    fsmFailEquipmentIOCardBaseFeConn(1000849),
    fsmFailMgmtControllerLockConfig(1000853),
    fsmFailSdAppInstanceInstallApplication(1000859),
    fsmFailSysdebugLogExportPolicyConfigure(1000870),
    fsmFailComputePhysicalFlashController(1000879),
    fsmFailOsControllerDeployOS(1000903),
    fsmFailNhTableHolderConfigureLinks(1000906),
    fsmFailStorageFlexFlashControllerMOpsReset(1000912),
    fsmFailStorageFlexFlashControllerMOpsFormat(1000913),
    fsmFailStorageFlexFlashControllerMOpsPair(1000914),
    fsmFailIdentMetaSystemFprcUnivSync(1000917),
    fsmFailComputePhysicalEnableCimcSecureBoot(1000937),
    fsmFailSdAppInstanceStartApplication(1000951),
    fsmFailSdLduProvisionLDU(1000952),
    fsmFailSwExtUtilityConfPortBreakout(1000957),
    fsmFailNhTableHolderBootstrapLinks(1000960),
    fsmFailLicenseSmartConfigSetConfig(1000962),
    fsmFailApplicationDownloaderDownload(1000968),
    fsmFailSmAppDelete(1000988),
    fsmFailOsControllerUpgradeOS(1001004),
    fsmFailOsControllerInitOS(1001005),
    fsmFailSdAppInstanceUpgradeApplication(1001006),
    fsmFailSdAppInstanceStopApplication(1001007),
    fsmFailSdAppInstanceUninstallApplication(1001008),
    fsmFailSdSlotChangePlatformLogLevel(1001009),
    fsmFailSdLogicalDeviceConfigureLinks(1001011),
    fsmFailSdSlotFormatDisk(1001014),
    fsmFailSdSlotSynchTimeZone(1001015),
    fsmFailSdAppAttributeCtrlGetAppAttributes(1001016),
    fsmFailSdMgmtInfoUpdateMgmtInfo(1001017),
    fsmFailSdNetMgmtBootstrapUpdateNetMgmtBootstrap(1001018),
    fsmFailFirmwarePlatformPackPlatformVersion(1001024),
    fsmFailSwSspEthMonDeploy(1001040),
    fsmFailSdClusterBootstrapUpdateClusterConfiguration(1001043),
    fsmFailIpsecEpUpdateEp(1001060),
    fsmFailEtherFtwPortPairConfigFtw(1001063),
    fsmFailSdLinkUpdateInterfaceStatus(1001064),
    fsmFailSdUpgradeTaskStopUpgradeStartApp(1001065),
    fsmFailSwSspEthMonSrcPhyEpDelete(1001074),
    fsmFailFirmwareSupFirmwareDeploy(1001075),
    fsmFailEquipmentChassisShutdownChassis(1001083),
    fsmFailSmCloudConnectorRegisterCloudConnector(1001091),
    fsmFailSmCloudConnectorUnRegisterCloudConnector(1001092),
    fsmFailSmAppVerifyApplication(1001093),
    fsmFailSmLogicalDeviceConfigure(1001096),
    fsmFailSdLduUpdateInterfaceStatus(1001098),
    fsmFailSdLogicalDeviceConfigureUserMacs(1001099),
    fsmFailEquipmentChassisRebootChassis(1001100),
    fsmFailFirmwareValidationStatusValidate(1001104),
    fsmFailSdPortsBundleBundleDataPorts(1001121),
    fsmFailSdHotfixInstallHotfix(1001122),
    fsmFailSdHotfixUninstallHotfix(1001123),
    fsmFailOsControllerInstallLicense(1001132),
    fsmFailSmUnsignedCspLicenseDeploy(1001138),
    fsmFailSmLicenseFileDelete(1001139),
    fsmFailComputePhysicalUpdateAdaptorBoot(1001152),
    fsmFailSmAppInstance2ResetApplication(1001169),
    fsmFailSdLogicalDeviceConfigureMacs(1001175),
    fsmFailSdAppInstSettingsTaskSendAppInstSettings(1001176),
    fsmFailComputePhysicalHardPowercycle(1001186),
    fsmFailSysdebugMemoryHeadDeploy(1001199),
    fsmFailSysdebugCpuOverallHeadDeploy(1001200),
    fsmFailSdCspMetaCtrlRetrieveCSPMeta(1001214),
    fsmFailSdAppInstanceGracefulStopApp(1001215),
    fsmFailCommTelemetryDataExchSeq(1001225),
    fsmFailCommTelemetryEnableDisableTelemetry(1001226)
  }

CfprFaultType  ::= TEXTUAL-CONVENTION
        STATUS       current
        DESCRIPTION
       "A code used to categorize Firepower faults"
        SYNTAX INTEGER {
    generic(0),
    fsm(1),
    equipment(2),
    network(3),
    configuration(4),
    server(5),
    management(6),
    environmental(7),
    connectivity(8),
    sysdebug(9),
    operational(10),
    security(11)
  }

CfprFaultProbableCause  ::= TEXTUAL-CONVENTION
        STATUS       current
        DESCRIPTION
       "A code used to identify the probable cause of a fault"
        SYNTAX INTEGER {
    fsmFailed(3),
    shutdownFailed(4),
    checkLicenseFailed(5),
    identifyFailed(6),
    configureSwMgmtEndPointFailed(7),
    configureVifNsFailed(8),
    configureEndPointFailed(9),
    discoverChassisFailed(10),
    enableChassisFailed(11),
    decomissionFailed(12),
    unIdentifyLocalFailed(13),
    cleanupEntriesFailed(14),
    waitFailed(15),
    disableEndPointFailed(16),
    unIdentifyPeerFailed(17),
    executeFailed(18),
    configFailed(19),
    bmcConfigureConnLocalFailed(20),
    swConfigureConnLocalFailed(21),
    bmcConfigureConnPeerFailed(22),
    swConfigureConnPeerFailed(23),
    bmcPresenceFailed(24),
    bmcInventoryFailed(25),
    preSanitizeFailed(26),
    sanitizeFailed(27),
    configUserAccessFailed(28),
    configDiscoveryModeFailed(29),
    swUnconfigPortNivLocalFailed(30),
    swUnconfigPortNivPeerFailed(31),
    swConfigPnuoslocalFailed(32),
    swConfigPnuospeerFailed(33),
    bmcPreconfigPnuoslocalFailed(34),
    bmcPreconfigPnuospeerFailed(35),
    bmcConfigPnuosFailed(36),
    bootPnuosFailed(37),
    bootWaitFailed(38),
    biosPostCompletionFailed(39),
    readSmbiosFailed(40),
    hagConnectFailed(41),
    pnuosidentFailed(42),
    pnuospolicyFailed(43),
    pnuosinventoryFailed(44),
    pnuosscrubFailed(45),
    pnuosconnectivityFailed(46),
    waitForConnReadyFailed(47),
    pnuosconnStatusFailed(48),
    swPnuosconnectivityLocalFailed(49),
    swPnuosconnectivityPeerFailed(50),
    pnuosselfTestFailed(51),
    bmcUnconfigPnuosFailed(52),
    hagDisconnectFailed(53),
    swConfigPortNivLocalFailed(54),
    swConfigPortNivPeerFailed(55),
    nicInventoryLocalFailed(56),
    nicInventoryPeerFailed(57),
    configNivModeFailed(58),
    bmcShutdownDiscoveredFailed(59),
    handlePoolingFailed(60),
    cleanupLocalFailed(63),
    cleanupPeerFailed(64),
    swUnconfigureLocalFailed(65),
    swUnconfigurePeerFailed(66),
    configFeLocalFailed(67),
    configFePeerFailed(68),
    bladePowerOnFailed(69),
    nicPresenceLocalFailed(70),
    nicPresencePeerFailed(71),
    deriveConfigFailed(72),
    swConfigLocalFailed(74),
    swConfigPeerFailed(75),
    nicConfigLocalFailed(76),
    nicConfigPeerFailed(77),
    stopvmediaLocalFailed(78),
    stopvmediaPeerFailed(79),
    setupvmediaLocalFailed(80),
    setupvmediaPeerFailed(81),
    bladeBootFailed(82),
    bladeBootWaitFailed(83),
    bladeReadSmbiosFailed(84),
    hostConnectFailed(85),
    hostIdentFailed(88),
    hostPolicyFailed(89),
    setDiagUserFailed(90),
    hostInventoryFailed(91),
    hostServerDiagFailed(92),
    hostServerDiagStatusFailed(93),
    disableServerConnSwBfailed(94),
    enableServerConnSwAfailed(95),
    startFabricatrafficTestFailed(96),
    fabricatrafficTestStatusFailed(97),
    disableServerConnSwAfailed(98),
    enableServerConnSwBfailed(99),
    startFabricbtrafficTestFailed(100),
    fabricbtrafficTestStatusFailed(101),
    cleanupServerConnSwAfailed(102),
    cleanupServerConnSwBfailed(103),
    generateReportFailed(104),
    generateLogWaitFailed(105),
    debugWaitFailed(106),
    removevmediaLocalFailed(107),
    removevmediaPeerFailed(108),
    nicUnconfigLocalFailed(109),
    nicUnconfigPeerFailed(110),
    swUnconfigLocalFailed(111),
    swUnconfigPeerFailed(112),
    removeConfigFailed(113),
    restoreConfigFeLocalFailed(114),
    restoreConfigFePeerFailed(115),
    unconfigUserAccessFailed(116),
    hostDisconnectFailed(118),
    bmcShutdownDiagCompletedFailed(119),
    evaluateStatusFailed(120),
    primaryFailed(121),
    secondaryFailed(122),
    executeLocalFailed(123),
    executePeerFailed(124),
    nicConfigPnuoslocalFailed(125),
    nicConfigPnuospeerFailed(126),
    setupVmediaLocalFailed(127),
    setupVmediaPeerFailed(128),
    bladeBootPnuosFailed(129),
    nicUnconfigPnuoslocalFailed(130),
    nicUnconfigPnuospeerFailed(131),
    swUnconfigPnuoslocalFailed(132),
    swUnconfigPnuospeerFailed(133),
    teardownVmediaLocalFailed(134),
    teardownVmediaPeerFailed(135),
    updateibmcfwFailed(136),
    waitForibmcfwUpdateFailed(137),
    activateibmcfwFailed(138),
    resetibmcFailed(139),
    bladePowerOffFailed(140),
    updateBoardCtrlRequestFailed(141),
    pollBoardCtrlUpdateStatusFailed(142),
    powerOnFailed(143),
    updateAdaptorNwFwLocalFailed(144),
    updateAdaptorNwFwPeerFailed(145),
    waitForAdaptorNwFwUpdateLocalFailed(146),
    waitForAdaptorNwFwUpdatePeerFailed(147),
    activateAdaptorNwFwLocalFailed(148),
    activateAdaptorNwFwPeerFailed(149),
    hagPnuosconnectFailed(150),
    pnuosvalidateFailed(151),
    biosImgUpdateFailed(152),
    storageCtlrImgUpdateFailed(153),
    hbaImgUpdateFailed(154),
    nicImgUpdateFailed(155),
    localDiskFwUpdateFailed(156),
    pnuosconfigFailed(157),
    pnuoslocalDiskConfigFailed(158),
    pnuosunloadDriversFailed(159),
    swConfigHostoslocalFailed(160),
    swConfigHostospeerFailed(161),
    nicConfigHostoslocalFailed(162),
    nicConfigHostospeerFailed(163),
    hagPnuosdisconnectFailed(164),
    configSoLfailed(165),
    prepareForBootFailed(166),
    configUuidFailed(167),
    bootHostFailed(168),
    hagHostosconnectFailed(169),
    hostosidentFailed(170),
    hostospolicyFailed(171),
    hostosvalidateFailed(172),
    hostosconfigFailed(173),
    nicUnconfigHostoslocalFailed(174),
    nicUnconfigHostospeerFailed(175),
    swUnconfigHostoslocalFailed(176),
    swUnconfigHostospeerFailed(177),
    configBiosFailed(178),
    pnuosunconfigFailed(179),
    unconfigUuidFailed(180),
    unconfigBiosFailed(181),
    unconfigSoLfailed(182),
    aFailed(183),
    bFailed(184),
    startFailed(185),
    cleanupFailed(186),
    resetFailed(187),
    reconfigBiosFailed(188),
    reconfigUuidFailed(189),
    applyTemplateFailed(190),
    applyIdentifiersFailed(191),
    applyPoliciesFailed(192),
    resolveBootConfigFailed(193),
    evaluateAssociationFailed(194),
    analyzeImpactFailed(195),
    waitForMaintPermissionFailed(196),
    waitForMaintWindowFailed(197),
    applyConfigFailed(198),
    mgmtifDown(199),
    updateEthMonFailed(200),
    serverMoved(202),
    serverIdentificationProblem(203),
    emptyPinGroup(205),
    membershipDown(206),
    configError(209),
    localFailed(211),
    peerFailed(212),
    configurationFailed(213),
    equipmentInoperable(214),
    thermalProblem(215),
    voltageProblem(216),
    capacityExceeded(217),
    equipmentDegraded(218),
    identityUnestablishable(219),
    setEpLocalFailed(220),
    setEpPeerFailed(221),
    propogateEpSettingsFailed(222),
    propogateEpTimeZoneSettingsLocalFailed(223),
    propogateEpTimeZoneSettingsPeerFailed(224),
    propogateEpTimeZoneSettingsToAdaptorsLocalFailed(225),
    propogateEpTimeZoneSettingsToAdaptorsPeerFailed(226),
    propogateEpTimeZoneSettingsToFexIomLocalFailed(227),
    propogateEpTimeZoneSettingsToFexIomPeerFailed(228),
    deployFailed(230),
    setRealmLocalFailed(231),
    setRealmPeerFailed(232),
    setUserLocalFailed(233),
    setUserPeerFailed(234),
    setKeyRingLocalFailed(235),
    setKeyRingPeerFailed(236),
    unidentifiableFru(237),
    equipmentMissing(238),
    connectivityProblem(239),
    linkDown(240),
    linkMisconnected(241),
    linkMissing(242),
    disableFailed(243),
    enableFailed(244),
    disableAfailed(245),
    enableAfailed(246),
    disableBfailed(247),
    enableBfailed(248),
    vifDown(249),
    tftpServerError(250),
    copySubFailed(251),
    copyPrimaryFailed(252),
    deleteSubFailed(253),
    deletePrimaryFailed(254),
    groupCapInsufficient(255),
    oldChassisComponentFirmware(256),
    psuInsufficient(258),
    psuRedundancyFail(260),
    powerCapFail(261),
    powerConsumptionHitLimit(262),
    noAckFromBios(263),
    noCapFail(264),
    updateConnectivityFailed(265),
    createLocalFailed(266),
    createRemoteFailed(267),
    unpackLocalFailed(268),
    deleteLocalFailed(269),
    copyRemoteFailed(270),
    remoteFailed(271),
    updateLocalFailed(272),
    verifyLocalFailed(273),
    resetLocalFailed(274),
    updateRemoteFailed(275),
    verifyRemoteFailed(276),
    resetRemoteFailed(277),
    updateRequestFailed(278),
    pollUpdateStatusFailed(279),
    activateFailed(280),
    updateRequestLocalFailed(281),
    updateRequestPeerFailed(282),
    pollUpdateStatusLocalFailed(283),
    pollUpdateStatusPeerFailed(284),
    powerOffFailed(285),
    activateLocalFailed(286),
    activatePeerFailed(287),
    prepareForUpdateFailed(288),
    imageDeleted(289),
    imageUnusable(290),
    imageCannotBoot(291),
    applyFailed(292),
    rescanImagesFailed(293),
    applyCatalogFailed(294),
    syncBladeaglocalFailed(295),
    syncBladeagremoteFailed(296),
    syncNicaglocalFailed(297),
    syncNicagremoteFailed(298),
    syncPortaglocalFailed(299),
    syncPortagremoteFailed(300),
    syncHostagentaglocalFailed(301),
    syncHostagentagremoteFailed(302),
    finalizeFailed(303),
    validateLocalFailed(304),
    validateRemoteFailed(305),
    deleteRemoteFailed(306),
    licenseGraceperiodEntered(307),
    licenseGraceperiod10days(308),
    licenseGraceperiod30days(309),
    licenseGraceperiod60days(310),
    licenseGraceperiod90days(311),
    licenseGraceperiod119days(312),
    licenseGraceperiodExpired(313),
    portFailed(316),
    unsupportedTransceiver(317),
    interfaceFailed(318),
    operationalStateDown(319),
    cmcVifDown(320),
    setLocalFailed(321),
    setPeerFailed(322),
    switchFailed(323),
    limitReached(324),
    emptyPool(325),
    backupLocalFailed(328),
    uploadFailed(329),
    downloadLocalFailed(330),
    reportResultsFailed(331),
    electionFailure(332),
    managementServicesFailure(333),
    managementServicesUnresponsive(334),
    haNotReady(335),
    versionIncompatible(336),
    logCapacity(338),
    fileTransferFailed(339),
    newLink(340),
    insufficientResources(342),
    insufficientlyEquipped(343),
    powerProblem(344),
    discoveryFailed(345),
    associationFailed(346),
    equipmentInaccessible(347),
    equipmentProblem(348),
    serverFailed(364),
    configurationFailure(365),
    maintenanceFailed(366),
    equipmentRemoved(367),
    serverInaccessible(368),
    assignmentFailed(369),
    unassociated(370),
    nonExistentScheduler(371),
    getVersionFailed(372),
    removeLocalFailed(373),
    setEpAfailed(374),
    setEpBfailed(375),
    satelliteConnectionAbsent(376),
    bmcPreConfigPnuospeerFailed(377),
    satelliteMisConnected(378),
    unexpectedNumberOfLinks(379),
    equipmentOffline(380),
    performanceProblem(381),
    firmwareUpgradeProblem(382),
    unsupportedConnectivityConfiguration(383),
    equipmentUnacknowledged(384),
    autoFirmwareUpgrade(385),
    equipmentDisconnected(386),
    fruProblem(387),
    validateConfigurationFailed(393),
    applyPhysicalFailed(394),
    waitOnPhysFailed(395),
    interfaceMisconfigured(402),
    missingPrimaryVlan(403),
    pinningMismatch(404),
    pinningMisconfig(405),
    equipmentDisabled(406),
    portInventorySwAfailed(419),
    portInventorySwBfailed(420),
    configSwAfailed(421),
    configSwBfailed(422),
    verifyPhysConfigFailed(423),
    activationFailed(427),
    deviceSharedStorageError(438),
    haSshKeysMismatched(439),
    executeAfailed(443),
    executeBfailed(444),
    inventoryFailed(454),
    configureFailed(455),
    clearFailed(456),
    pollClearStatusFailed(457),
    pollActivateStatusFailed(458),
    updateTokensFailed(459),
    hostCatalogFailed(460),
    pnuoscatalogFailed(461),
    clearBiosUpdateFailed(462),
    pollClearBiosUpdateStatusFailed(463),
    updateBiosRequestFailed(464),
    pollBiosUpdateStatusFailed(465),
    activateBiosFailed(466),
    pollBiosActivateStatusFailed(467),
    fexUnsupported(468),
    invalidKeyringCertificate(469),
    invalidTrustpointCertChain(470),
    disassociationFailed(471),
    vifIdsMismatch(472),
    profileConfigIncorrect(473),
    pingFailed(474),
    inaccessibleVlanReferenced(476),
    referencedVlanUnresolvable(477),
    invalidVlanInTheAllowedVlanList(478),
    vlanConflictPermit(479),
    vlanPermitUnresolved(480),
    groupPermitUnresolved(481),
    checkPowerAvailabilityFailed(482),
    markAdapterForRebootFailed(483),
    deassertResetBypassFailed(484),
    verifyFcZoneConfigFailed(485),
    cleanupPortConfigLocalFailed(486),
    cleanupPortConfigPeerFailed(487),
    powerCycleFailed(488),
    enablePortFailed(489),
    resolveIdentifiersFailed(490),
    applyDefaultIdentifiersFailed(491),
    resolveDefaultIdentifiersFailed(492),
    resolvePoliciesFailed(493),
    resolveDistributableNamesFailed(494),
    resolveDistributableFailed(495),
    resolveImagesFailed(496),
    resolveScheduleFailed(497),
    provisionStorageFailed(498),
    waitForStorageProvisionFailed(499),
    commitStorageFailed(500),
    waitForCommitStorageFailed(501),
    waitForAssocCompletionFailed(502),
    clientLostConnectivity(503),
    registerClientFailed(504),
    verifyRegistrationFailed(505),
    mountLocalFailed(506),
    mountPeerFailed(507),
    unmountLocalFailed(508),
    unmountPeerFailed(509),
    reportFailed(510),
    configurationError(511),
    operationFailed(513),
    copyExtToLocalFailed(514),
    copyExtToPeerFailed(515),
    copyToLocalFailed(516),
    copyToPeerFailed(517),
    waitForDeployFailed(518),
    activatefprmFailed(519),
    pollActivateOffprmFailed(520),
    updateiomFailed(521),
    pollUpdateOfiomFailed(522),
    activateiomFailed(523),
    pollActivateOfiomFailed(524),
    activateRemotefiFailed(525),
    pollActivateOfRemotefiFailed(526),
    waitForUserAckFailed(527),
    activateLocalfiFailed(528),
    pollActivateOfLocalfiFailed(529),
    activateCatalogFailed(530),
    providerGroupAlreadyExists(531),
    invalidServerGroup(532),
    roleConfigError(533),
    localeConfigError(534),
    userRoleConfigError(535),
    userLocaleConfigError(536),
    keyringConfigError(537),
    snmpConfigError(538),
    timezoneFileNotExists(539),
    userConfigError(540),
    snmpUserConfigError(541),
    commSvcConfigError(542),
    resolveFailed(543),
    updateVlanGroupsFailed(544),
    updateZonesFailed(545),
    noVlanOptimization(546),
    suspendModeEntered(547),
    verifyGuidFailed(548),
    unregisterFailed(549),
    cleanOldDataFailed(550),
    requestFailed(551),
    verifyFailed(552),
    releaseFailed(553),
    resolveManyFailed(554),
    releaseManyFailed(555),
    resolveAllFailed(556),
    releaseAllFailed(557),
    invalidTarget(560),
    vlanMcastPolicyMisconfigured(565),
    anotherConnectionAlreadyEnabled(566),
    connectionUnused(567),
    unsupportedConnectivity(568),
    callhomeConfigError(569),
    loadCatalogFailed(570),
    arpTargetsConfigError(572),
    removeFailed(573),
    configFlexFlashFailed(574),
    syncPowerStateFailed(575),
    unconfigFlexFlashFailed(576),
    resolveNetworkPoliciesFailed(577),
    resolveNetworkTemplatesFailed(578),
    validatePolicyOwnershipFailed(579),
    licenseInsufficient(580),
    invalidKeyringModulus(581),
    localeOrgConfigError(582),
    checkInventoryStatusFailed(583),
    reportFullInventoryFailed(584),
    extraPrimaryVlans(585),
    syncFailed(586),
    healthLedAmberBlinking(587),
    healthLedAmber(588),
    referencedRemoteVlanUnresolvable(589),
    multipleConnectionPolicies(591),
    equipmentUnhealthy(593),
    postSetKeyRingLocalFailed(594),
    postSetKeyRingPeerFailed(595),
    providerGroupSizeEmpty(596),
    serverPowerOffFailed(597),
    serverPowerOnFailed(598),
    defaultHostpackMissing(599),
    namedVlanUnresolved(601),
    vmNetworkReferenceIncorrect(602),
    ndiscTargetsConfigError(603),
    configMemoryPolicyFailed(604),
    boardCtrlUpgraded(605),
    incompatibleServerFirmware(606),
    oobStorageInventoryFailed(608),
    configFlexFlashScrubFailed(609),
    cimcvlanCfgLocalFailed(610),
    cimcvlanCfgPeerFailed(611),
    cmcvlanCfgFailed(612),
    cmcvlanCfgPeerFailed(613),
    activeFailed(614),
    swConfigServiceInfraLocalFailed(615),
    swConfigServiceInfraPeerFailed(616),
    nicConfigServiceInfraLocalFailed(617),
    nicConfigServiceInfraPeerFailed(618),
    nicUnconfigServiceInfraLocalFailed(619),
    nicUnconfigServiceInfraPeerFailed(620),
    swUnConfigLocalFailed(621),
    swUnConfigPeerFailed(622),
    nicUnConfigLocalFailed(623),
    nicUnConfigPeerFailed(624),
    powerOnPreConfigFailed(625),
    resetSecureBootConfigFailed(626),
    udldLinkDown(627),
    copyImgFromRepFailed(630),
    copyiomimgToSubFailed(631),
    copyCatFromRepFailed(632),
    copyExternalRepToRemoteFailed(633),
    psuMixedMode(634),
    configbmcpowerParamsFailed(635),
    sendBmcProfilingInitFailed(636),
    pnuospowerProfilingFailed(637),
    sendBmcProfilingDoneFailed(638),
    downloadImagesFailed(639),
    deleteCurlDownloadedImagesFailed(640),
    configChassisIdFailed(641),
    powerButtonLockConfigFailed(642),
    powerDeployWaitFailed(643),
    extraSecondaryVlans(644),
    extraSecondaryVlansPerPrimary(645),
    sendCommandFailed(646),
    updateAppInstanceFailed(648),
    configBackupOutdated(649),
    cimcFirmwareMismatch(650),
    pldFirmwareMismatch(651),
    serverError(652),
    unconfigExtMgmtRulesFailed(653),
    unconfigExtMgmtGwFailed(654),
    unconfigCimcvmediaFailed(655),
    graphicsImageUpdateFailed(656),
    configExtMgmtRulesFailed(657),
    configExtMgmtGwFailed(658),
    configCimcvmediaFailed(659),
    sspUpdateHostPreBootFailed(660),
    configKvmMgmtDefaultSettingFailed(661),
    updateFlashLifeFailed(662),
    svnicNotPresent(663),
    unsupportedCimcFirmware(664),
    vmediaMountInaccessible(665),
    primaryVlanMissingForIsolated(666),
    primaryVlanMissingForCommunity(667),
    vlanMismatch(668),
    vlanErrorAssocPrimary(669),
    hostPrepareBootFailed(670),
    hostWaitForRommonReadyFailed(671),
    hostCheckRommonReadyFailed(672),
    hostCheckUpgradeImageStatusFailed(673),
    verifyLinkConfigFailed(677),
    formatFailed(678),
    pairFailed(679),
    namedInbandVlanUnresolved(680),
    inbandUnsupportedServer(681),
    adaptorMismatch(682),
    act2Fail(683),
    tpmOnSlaveBoard(684),
    duplicatedAssigned(685),
    checkAssignedIdentifiersForDupFailed(686),
    checkAssignedDefaultIdentifiersForDupFailed(687),
    nearMaxLimit(688),
    memoryError(689),
    waitForAppsInstallationFailed(690),
    waitForLinkConfigurationFailed(691),
    startAppsFailed(692),
    verifyBreakoutConfigFailed(693),
    fprmProcessFailure(695),
    slotNotResponding(696),
    bladeNotWorking(697),
    diskFormatFailed(698),
    bladeSwap(699),
    appinstanceNotResponding(700),
    appinstanceInstallFailed(701),
    appinstanceStartFailed(702),
    appinstanceUpdateFailed(703),
    appinstanceStopFailed(704),
    restoreFailed(705),
    prepareKeyFileFailed(706),
    updateSspOsSoftwareFailed(707),
    waitForSspOsUpdateCompleteFailed(708),
    bootupFailure(709),
    hostPrepareKeyFileFailed(710),
    hostWaitForRommonValidateImageFailed(711),
    hostCheckImageValidationStatusFailed(712),
    hostWaitForSspOsRunningFailed(713),
    requestToUpgradeFailed(714),
    hostWaitForUpgradeCompleteFailed(715),
    rebootHostAfterUpgradeFailed(716),
    checkBladeReadinessFailed(717),
    releaseAppLicenseFailed(718),
    configureLinksFailed(719),
    sendBundleStatusFailed(721),
    sendInterfacesFailed(722),
    unconfigureLinksFailed(723),
    configureSwitchFailed(724),
    waitForSwitchConfigFailed(725),
    sendStatusFailed(726),
    sendConfigFailed(727),
    startDiskFormatFailed(728),
    resetBladePowerFailed(729),
    waitForDiskFormatCompleteFailed(730),
    updateTimeZoneFailed(731),
    getAttributesFailed(732),
    sendUpdateFailed(733),
    defaultPlaformVersionMissing(734),
    waitForReadyFailed(735),
    updateSspEthMonFailed(736),
    switchConfigFailed(737),
    waitForConfigCompletionFailed(738),
    updateBundleStatusFailed(739),
    resetBladesFailed(740),
    waitForBladeRebootFailed(745),
    appinstanceError(747),
    logicalDeviceIncompleteConfiguration(748),
    logicalDeviceError(749),
    appinstanceUnsupported(751),
    softwareVersionIncompatible(753),
    bypass(754),
    unconfigureLogicalDeviceFailed(755),
    stopAppFailed(756),
    waitForStopAppFailed(757),
    upgradeAppFailed(758),
    waitForUpgradeAppFailed(759),
    startAppFailed(760),
    cleanUpFailed(761),
    configBreakoutFailed(762),
    waitForSwitchFailed(763),
    deletePcapFileFailed(764),
    debundlePortFailed(765),
    pollDebundlePortFailed(766),
    activateMgmtExtFailed(767),
    pollActivateOfMgmtExtFailed(768),
    validateFirmwarePackFailed(769),
    activateFirmwarePackFailed(770),
    pollActivateOfFirmwarePackFailed(771),
    updateImageVersionFailed(772),
    waitForFirmwareVersionUpdateFailed(773),
    updatePackageVersionFailed(774),
    completeFirmwareUpgradeFailed(775),
    waitForBladeShutdownFailed(776),
    applyShutdownFailed(777),
    ntpConfigFailed(778),
    registerFailed(779),
    unRegisterFailed(780),
    checkReadinessFailed(781),
    logicalDeviceConfigError(784),
    resolvePolicyFailed(785),
    validateldconfigFailed(786),
    checkConfigIssuesFailed(787),
    autoConfigFailed(788),
    appImgCorrupted(789),
    installFailed(790),
    upgradeFailed(791),
    stopFailed(792),
    uninstallFailed(793),
    applyRebootFailed(794),
    platformPackFailed(795),
    completeFailed(796),
    checkUpgradeStatusFailed(797),
    ipsecConfigError(798),
    hotfixInstallFailed(799),
    hotfixError(800),
    genericError(801),
    cloudRegistrationFailed(802),
    cloudUnregistrationFailed(803),
    updateHotfixFailed(804),
    debundlePortsFailed(805),
    shutdownBladeFailed(806),
    validatePlatformPackFailed(807),
    requestToUninstallLicenseFailed(808),
    requestToInstallLicenseFailed(809),
    waitForLicInstalledCompleteFailed(810),
    hostWaitForLicInstalledCompleteFailed(811),
    onChassisFailed(812),
    rebootSystemFailed(813),
    onBladesFailed(814),
    waitForCompletionFailed(815),
    licenseInstalled(838),
    vnicConfigFailed(839),
    moduleOffline(840),
    moduleFailed(841),
    moduleError(842),
    moduleOirFailed(843),
    moduleOirInvalid(844),
    moduleRemoval(845),
    moduleMismatch(846),
    moduleSupriseRemoval(847),
    updateManagerFailed(848),
    adapterBootUpgradeRequired(849),
    cclSubnetNotSupported(852),
    appinstanceNotInstalled(853),
    conversionFailed(854),
    deregisterFailed(855),
    fileMissing(856),
    sendInterfaceDeletingFailed(857),
    sendInterfaceAddingFailed(858),
    updateSettingsFailed(859),
    appinstanceFaultState(862),
    externalPortLinkConflictConfiguration(863),
    reenableSspEthMonFailed(864),
    decommissionFail(865),
    badMemoryDetect(866),
    unpackFirmwareFailed(867),
    imageInventoryFailed(868),
    upgradeFirmwareFailed(869),
    resetChassisFailed(870),
    imageVersionMismatch(871),
    fwUpgradeInprogress(872),
    highSystemMemoryUsage(873),
    processStackMemoryHigh(874),
    processHeapMemoryHigh(875),
    cpuUsageHigh(876),
    internalMgmtVnicConfigFail(877),
    externalLduLinkVnicConfigFail(878),
    appLduLinkEndpoint1VnicConfigFail(879),
    appLduLinkEndpoint2VnicConfigFail(880),
    vnicPreAllocationFail(881),
    differentResourcesInProfile(882),
    gracefulStopAppFailed(883),
    waitForDiskFormatSecureCompleteFailed(884),
    decommissionBladeFailed(885),
    waitforDecommissionCompleteFailed(886),
    retrieveFailed(887),
    fpgaUpgradeRequired(888),
    adapter2NotResponding(889),
    platformNotSupported(890),
    moduleNotSupported(891),
    hardwareCryptoVersionUnsupportedOrFailure(892),
    initIptablesLocalFailed(895),
    initIptablesPeerFailed(896),
    registerforTelemetryFailed(897),
    getTelemetryDataFailed(898),
    sendTelemetryDataFailed(899),
    sendChassisConfigFailed(900),
    invalidTpAutoImport(901),
    tpAutoImport(902),
    invalidKeyringEc(903),
    telemetryRegistrationFailed(904),
    telemetryUnregistrationFailed(905),
    telemetryGetDataFailed(906),
    telemetrySendDataFailed(907),
    ntpStratumCheckFailed(908),
    passwordEncryptionKeyNotSet(909),
    ssh3desUsageNotRecommended(910),
    sshc3desUsageNotRecommended(911),
    deviceRegistrationPending(912),
    deviceRegistrationFailed(913),
    deviceUnregistrationFailed(914),
    deviceSftunnelDown(915),
    deviceManagerNotReachable(916),
    verifyKeyFailed(917),
    configImportFailed(918),
    processTerminated(919)
  }

CfprFaultSeverity  ::= TEXTUAL-CONVENTION
        STATUS       current
        DESCRIPTION
       "A code used to identify the severity of a fault"
        SYNTAX INTEGER {
    cleared(0),
    info(1),
    warning(3),
    minor(4),
    major(5),
    critical(6)
  }

-- *********************************************************************
-- Basic Firepower MIB Objects
-- *********************************************************************

ciscoFirepowerMIBObjects OBJECT IDENTIFIER
    ::= { ciscoFirepowerMIB 1 }

END
