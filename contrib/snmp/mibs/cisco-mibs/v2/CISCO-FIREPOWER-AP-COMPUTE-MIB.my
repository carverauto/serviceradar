-- *********************************************************************
-- CISCO-FIREPOWER-AP-COMPUTE-MIB.my
-- 
-- MIB representation of the Cisco Firepower
-- COMPUTE management information model package
-- 
-- Created January 2023 by Charles Bullis
-- 
-- Copyright (c) 2005-2023 Cisco Systems, Inc. All rights reserved.
-- 
-- *********************************************************************

CISCO-FIREPOWER-AP-COMPUTE-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerApMIBObjects,
    CfprApManagedObjectId,
    CfprApManagedObjectDn
        FROM CISCO-FIREPOWER-AP-MIB
    CfprApComputeABoardPower,
    CfprApComputeAdminLinkAggregation,
    CfprApComputeAdminMemoryState,
    CfprApComputeAdminPowerState,
    CfprApComputeAdminState,
    CfprApComputeAdminTrigger,
    CfprApComputeAlarmSeverity,
    CfprApComputeAssociation,
    CfprApComputeAvailability,
    CfprApComputeBlackListing,
    CfprApComputeBladeFsmCurrentFsm,
    CfprApComputeBladeFsmStageName,
    CfprApComputeBladeFsmTaskFlags,
    CfprApComputeBladeFsmTaskItem,
    CfprApComputeBladeSlotId,
    CfprApComputeChassisConnPolicyChassisId,
    CfprApComputeChassisDiscAction,
    CfprApComputeChassisQualMaxId,
    CfprApComputeChassisQualMinId,
    CfprApComputeCheckPoint,
    CfprApComputeConnectivityRebalancing,
    CfprApComputeDiscovery,
    CfprApComputeIOHubEnvStatsHistThresholded,
    CfprApComputeIOHubEnvStatsThresholded,
    CfprApComputeIssues,
    CfprApComputeLinkAggregation,
    CfprApComputeMbPowerStatsHistThresholded,
    CfprApComputeMbPowerStatsThresholded,
    CfprApComputeMbTempStatsHistThresholded,
    CfprApComputeMbTempStatsThresholded,
    CfprApComputeMemoryUnitConstraintType,
    CfprApComputeMode,
    CfprApComputeOwner,
    CfprApComputePCIeFatalCompletionStatsThresholded,
    CfprApComputePCIeFatalProtocolStatsThresholded,
    CfprApComputePCIeFatalReceiveStatsThresholded,
    CfprApComputePCIeFatalStatsThresholded,
    CfprApComputePciCapOrder,
    CfprApComputePhysicalFsmCurrentFsm,
    CfprApComputePhysicalFsmStageName,
    CfprApComputePhysicalFsmTaskItem,
    CfprApComputePhysicalLowVoltageMemory,
    CfprApComputePooledRackUnitId,
    CfprApComputePooledSlotSlotId,
    CfprApComputePsuClusterState,
    CfprApComputePsuControlRedundancy,
    CfprApComputePsuRedundancy,
    CfprApComputePsuRedundancyOperQualifier,
    CfprApComputePsuRedundancyOperState,
    CfprApComputeRackQualMaxId,
    CfprApComputeRackQualMinId,
    CfprApComputeRackUnitFsmCurrentFsm,
    CfprApComputeRackUnitFsmStageName,
    CfprApComputeRackUnitId,
    CfprApComputeRackUnitMbTempStatsHistThresholded,
    CfprApComputeRackUnitMbTempStatsThresholded,
    CfprApComputeScrubAction,
    CfprApComputeServerDiscPolicyFsmCurrentFsm,
    CfprApComputeServerDiscPolicyFsmStageName,
    CfprApComputeServerDiscPolicyFsmTaskItem,
    CfprApComputeServerMgmtDiscAction,
    CfprApComputeSlotQualMaxId,
    CfprApComputeSlotQualMinId,
    CfprApComputeUpgradeStatus,
    CfprApConditionRemoteInvRslt,
    CfprApEquipmentBoardAggregationRole,
    CfprApEquipmentBoardConnectorType,
    CfprApEquipmentConnectionStatus,
    CfprApEquipmentCpuType,
    CfprApEquipmentOperability,
    CfprApEquipmentPowerState,
    CfprApEquipmentPresence,
    CfprApEquipmentSensorThresholdStatus,
    CfprApEquipmentSlotStatus,
    CfprApFsmCompletion,
    CfprApFsmFlags,
    CfprApFsmFsmStageStatus,
    CfprApLsOperState,
    CfprApNetworkSwitchId,
    CfprApPolicyPolicyOwner,
    CfprApPoolPoolAssignmentOrder,
    CfprApTrigAckChangeDetails,
    CfprApTrigAckChanges,
    CfprApTrigAckDisr,
    CfprApTrigAckOperState,
    CfprApTrigAckPrevOperState,
    CfprApTrigAdminState
        FROM CISCO-FIREPOWER-AP-TC-MIB;

cfprApComputeObjects MODULE-IDENTITY
    LAST-UPDATED    "202301250000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        COMPUTE management information model package"
    ::= { ciscoFirepowerApMIBObjects 12 }

cfprApComputeAutoconfigPolicyTable OBJECT-TYPE
    SYNTAX           SEQUENCE OF CfprApComputeAutoconfigPolicyEntry
    MAX-ACCESS       not-accessible
    STATUS           current
    DESCRIPTION
        "Cisco Firepower compute:AutoconfigPolicy managed object table"
    ::= { cfprApComputeObjects 1 }

cfprApComputeAutoconfigPolicyEntry OBJECT-TYPE
    SYNTAX           CfprApComputeAutoconfigPolicyEntry
    MAX-ACCESS       not-accessible
    STATUS           current
    DESCRIPTION
        "Entry for the cfprApComputeAutoconfigPolicyTable table."
    INDEX { cfprApComputeAutoconfigPolicyInstanceId }
    ::= { cfprApComputeAutoconfigPolicyTable 1 }

CfprApComputeAutoconfigPolicyEntry ::= SEQUENCE {
    cfprApComputeAutoconfigPolicyInstanceId                          CfprApManagedObjectId,
    cfprApComputeAutoconfigPolicyDn                                  CfprApManagedObjectDn,
    cfprApComputeAutoconfigPolicyRn                                  SnmpAdminString,
    cfprApComputeAutoconfigPolicyDescr                               SnmpAdminString,
    cfprApComputeAutoconfigPolicyDstDn                               SnmpAdminString,
    cfprApComputeAutoconfigPolicyIntId                               SnmpAdminString,
    cfprApComputeAutoconfigPolicyName                                SnmpAdminString,
    cfprApComputeAutoconfigPolicyPolicyLevel                         Gauge32,
    cfprApComputeAutoconfigPolicyPolicyOwner                         CfprApPolicyPolicyOwner,
    cfprApComputeAutoconfigPolicyQualifier                           SnmpAdminString,
    cfprApComputeAutoconfigPolicySrcTemplName                        SnmpAdminString
}

cfprApComputeAutoconfigPolicyInstanceId OBJECT-TYPE
    SYNTAX       CfprApManagedObjectId
    MAX-ACCESS   not-accessible
    STATUS       current
    DESCRIPTION
        "Instance identifier of the managed object."
    ::= { cfprApComputeAutoconfigPolicyEntry 1 }

cfprApComputeAutoconfigPolicyDn OBJECT-TYPE
    SYNTAX       CfprApManagedObjectDn
    MAX-ACCESS   read-only
    STATUS       current
    DESCRIPTION
        "Cisco Firepower compute:AutoconfigPolicy:dn managed
        object property"
    ::= { cfprApComputeAutoconfigPolicyEntry 2 }

cfprApComputeAutoconfigPolicyRn OBJECT-TYPE
    SYNTAX       SnmpAdminString
    MAX-ACCESS   read-only
    STATUS       current
    DESCRIPTION
        "Cisco Firepower compute:AutoconfigPolicy:rn managed
        object property"
    ::= { cfprApComputeAutoconfigPolicyEntry 3 }

cfprApComputeAutoconfigPolicyDescr OBJECT-TYPE
    SYNTAX       SnmpAdminString
    MAX-ACCESS   read-only
    STATUS       current
    DESCRIPTION
        "Cisco Firepower compute:AutoconfigPolicy:descr
        managed object property"
    ::= { cfprApComputeAutoconfigPolicyEntry 4 }

cfprApComputeAutoconfigPolicyDstDn OBJECT-TYPE
    SYNTAX       SnmpAdminString
    MAX-ACCESS   read-only
    STATUS       current
    DESCRIPTION
        "Cisco Firepower compute:AutoconfigPolicy:dstDn
        managed object property"
    ::= { cfprApComputeAutoconfigPolicyEntry 5 }

cfprApComputeAutoconfigPolicyIntId OBJECT-TYPE
    SYNTAX       SnmpAdminString
    MAX-ACCESS   read-only
    STATUS       current
    DESCRIPTION
        "Cisco Firepower compute:AutoconfigPolicy:intId
        managed object property"
    ::= { cfprApComputeAutoconfigPolicyEntry 6 }

cfprApComputeAutoconfigPolicyName OBJECT-TYPE
    SYNTAX       SnmpAdminString
    MAX-ACCESS   read-only
    STATUS       current
    DESCRIPTION
        "Cisco Firepower compute:AutoconfigPolicy:name
        managed object property"
    ::= { cfprApComputeAutoconfigPolicyEntry 7 }

cfprApComputeAutoconfigPolicyPolicyLevel OBJECT-TYPE
    SYNTAX       Gauge32
    MAX-ACCESS   read-only
    STATUS       current
    DESCRIPTION
        "Cisco Firepower compute:AutoconfigPolicy:policyLevel
        managed object property"
    ::= { cfprApComputeAutoconfigPolicyEntry 8 }

cfprApComputeAutoconfigPolicyPolicyOwner OBJECT-TYPE
    SYNTAX       CfprApPolicyPolicyOwner
    MAX-ACCESS   read-only
    STATUS       current
    DESCRIPTION
        "Cisco Firepower compute:AutoconfigPolicy:policyOwner
        managed object property"
    ::= { cfprApComputeAutoconfigPolicyEntry 9 }

cfprApComputeAutoconfigPolicyQualifier OBJECT-TYPE
    SYNTAX       SnmpAdminString
    MAX-ACCESS   read-only
    STATUS       current
    DESCRIPTION
        "Cisco Firepower compute:AutoconfigPolicy:qualifier
        managed object property"
    ::= { cfprApComputeAutoconfigPolicyEntry 10 }

cfprApComputeAutoconfigPolicySrcTemplName OBJECT-TYPE
    SYNTAX       SnmpAdminString
    MAX-ACCESS   read-only
    STATUS       current
    DESCRIPTION
        "Cisco Firepower compute:AutoconfigPolicy:srcTemplName
        managed object property"
    ::= { cfprApComputeAutoconfigPolicyEntry 11 }

cfprApComputeBladeTable OBJECT-TYPE
    SYNTAX           SEQUENCE OF CfprApComputeBladeEntry
    MAX-ACCESS       not-accessible
    STATUS           current
    DESCRIPTION
        "Cisco Firepower compute:Blade managed object table"
    ::= { cfprApComputeObjects 2 }

cfprApComputeBladeEntry OBJECT-TYPE
    SYNTAX           CfprApComputeBladeEntry
    MAX-ACCESS       not-accessible
    STATUS           current
    DESCRIPTION
        "Entry for the cfprApComputeBladeTable table."
    INDEX { cfprApComputeBladeInstanceId }
    ::= { cfprApComputeBladeTable 1 }

CfprApComputeBladeEntry ::= SEQUENCE {
    cfprApComputeBladeInstanceId                                     CfprApManagedObjectId,
    cfprApComputeBladeDn                                             CfprApManagedObjectDn,
    cfprApComputeBladeRn                                             SnmpAdminString,
    cfprApComputeBladeAdminPower                                     CfprApComputeAdminPowerState,
    cfprApComputeBladeAdminState                                     CfprApComputeAdminState,
    cfprApComputeBladeAssignedToDn                                   SnmpAdminString,
    cfprApComputeBladeAssociation                                    CfprApComputeAssociation,
    cfprApComputeBladeAvailability                                   CfprApComputeAvailability,
    cfprApComputeBladeAvailableMemory                                Gauge32,
    cfprApComputeBladeChassisId                                      Gauge32,
    cfprApComputeBladeCheckPoint                                     CfprApComputeCheckPoint,
    cfprApComputeBladeConnPath                                       CfprApEquipmentConnectionStatus,
    cfprApComputeBladeConnStatus                                     CfprApEquipmentConnectionStatus,
    cfprApComputeBladeDescr                                          SnmpAdminString,
    cfprApComputeBladeDiscovery                                      CfprApComputeDiscovery,
    cfprApComputeBladeFltAggr                                        Unsigned64,
    cfprApComputeBladeFsmDescr                                       SnmpAdminString,
    cfprApComputeBladeFsmFlags                                       SnmpAdminString,
    cfprApComputeBladeFsmPrev                                        SnmpAdminString,
    cfprApComputeBladeFsmProgr                                       Gauge32,
    cfprApComputeBladeFsmRmtInvErrCode                               Gauge32,
    cfprApComputeBladeFsmRmtInvErrDescr                              SnmpAdminString,
    cfprApComputeBladeFsmRmtInvRslt                                  CfprApConditionRemoteInvRslt,
    cfprApComputeBladeFsmStageDescr                                  SnmpAdminString,
    cfprApComputeBladeFsmStamp                                       DateAndTime,
    cfprApComputeBladeFsmStatus                                      SnmpAdminString,
    cfprApComputeBladeFsmTry                                         Gauge32,
    cfprApComputeBladeIntId                                          SnmpAdminString,
    cfprApComputeBladeLc                                             CfprApComputeAdminTrigger,
    cfprApComputeBladeLcTs                                           DateAndTime,
    cfprApComputeBladeLocalId                                        SnmpAdminString,
    cfprApComputeBladeLowVoltageMemory                               CfprApComputePhysicalLowVoltageMemory,
    cfprApComputeBladeManagingInst                                   CfprApNetworkSwitchId,
    cfprApComputeBladeMemorySpeed                                    Gauge32,
    cfprApComputeBladeMfgTime                                        DateAndTime,
    cfprApComputeBladeModel                                          SnmpAdminString,
    cfprApComputeBladeName                                           SnmpAdminString,
    cfprApComputeBladeNumOfAdaptors                                  Gauge32,
    cfprApComputeBladeNumOfCores                                     Gauge32,
    cfprApComputeBladeNumOfCoresEnabled                              Gauge32,
    cfprApComputeBladeNumOfCpus                                      Gauge32,
    cfprApComputeBladeNumOfEthHostIfs                                Gauge32,
    cfprApComputeBladeNumOfFcHostIfs                                 Gauge32,
    cfprApComputeBladeNumOfThreads                                   Gauge32,
    cfprApComputeBladeOperPower                                      CfprApEquipmentPowerState,
    cfprApComputeBladeOperQualifier                                  CfprApComputeIssues,
    cfprApComputeBladeOperState                                      CfprApLsOperState,
    cfprApComputeBladeOperability                                    CfprApEquipmentOperability,
    cfprApComputeBladeOriginalUuid                                   SnmpAdminString,
    cfprApComputeBladePartNumber                                     SnmpAdminString,
    cfprApComputeBladePolicyLevel                                    Gauge32,
    cfprApComputeBladePolicyOwner                                    CfprApPolicyPolicyOwner,
    cfprApComputeBladePresence                                       CfprApEquipmentSlotStatus,
    cfprApComputeBladeRevision                                       SnmpAdminString,
    cfprApComputeBladeScaledMode                                     CfprApComputeMode,
    cfprApComputeBladeSerial                                         SnmpAdminString,
    cfprApComputeBladeServerId                                       SnmpAdminString,
    cfprApComputeBladeSlotId                                         CfprApComputeBladeSlotId,
    cfprApComputeBladeTotalMemory                                    Gauge32,
    cfprApComputeBladeUpgradeScenario                                CfprApComputeUpgradeStatus,
    cfprApComputeBladeUsrLbl                                         SnmpAdminString,
    cfprApComputeBladeUuid                                           SnmpAdminString,
    cfprApComputeBladeVendor                                         SnmpAdminString,
    cfprApComputeBladeVid                                            SnmpAdminString
}

cfprApComputeBladeInstanceId OBJECT-TYPE
    SYNTAX       CfprApManagedObjectId
    MAX-ACCESS   not-accessible
    STATUS       current
    DESCRIPTION
        "Instance identifier of the managed object."
    ::= { cfprApComputeBladeEntry 1 }

cfprApComputeBladeDn OBJECT-TYPE
    SYNTAX       CfprApManagedObjectDn
    MAX-ACCESS   read-only
    STATUS       current
    DESCRIPTION
        "Cisco Firepower compute:Blade:dn managed object property"
    ::= { cfprApComputeBladeEntry 2 }

cfprApComputeBladeRn OBJECT-TYPE
    SYNTAX       SnmpAdminString
    MAX-ACCESS   read-only
    STATUS       current
    DESCRIPTION
        "Cisco Firepower compute:Blade:rn managed object property"
    ::= { cfprApComputeBladeEntry 3 }

cfprApComputeBladeAdminPower OBJECT-TYPE
    SYNTAX       CfprApComputeAdminPowerState
    MAX-ACCESS   read-only
    STATUS       current
    DESCRIPTION
        "Cisco Firepower compute:Blade:adminPower managed object property"
    ::= { cfprApComputeBladeEntry 4 }

cfprApComputeBladeAdminState OBJECT-TYPE
    SYNTAX       CfprApComputeAdminState
    MAX-ACCESS   read-only
    STATUS       current
    DESCRIPTION
        "Cisco Firepower compute:Blade:adminState managed object property"
    ::= { cfprApComputeBladeEntry 5 }

cfprApComputeBladeAssignedToDn OBJECT-TYPE
    SYNTAX       SnmpAdminString
    MAX-ACCESS   read-only
    STATUS       current
    DESCRIPTION
        "Cisco Firepower compute:Blade:assignedToDn managed
        object property"
    ::= { cfprApComputeBladeEntry 6 }

cfprApComputeBladeAssociation OBJECT-TYPE
    SYNTAX       CfprApComputeAssociation
    MAX-ACCESS   read-only
    STATUS       current
    DESCRIPTION
        "Cisco Firepower compute:Blade:association managed
        object property"
    ::= { cfprApComputeBladeEntry 7 }

cfprApComputeBladeAvailability OBJECT-TYPE
    SYNTAX       CfprApComputeAvailability
    MAX-ACCESS   read-only
    STATUS       current
    DESCRIPTION
        "Cisco Firepower compute:Blade:availability managed
        object property"
    ::= { cfprApComputeBladeEntry 8 }

cfprApComputeBladeAvailableMemory OBJECT-TYPE
    SYNTAX       Gauge32
    MAX-ACCESS   read-only
    STATUS       current
    DESCRIPTION
        "Cisco Firepower compute:Blade:availableMemory
        managed object property"
    ::= { cfprApComputeBladeEntry 9 }

cfprApComputeBladeChassisId OBJECT-TYPE
    SYNTAX       Gauge32
    MAX-ACCESS   read-only
    STATUS       current
    DESCRIPTION
        "Cisco Firepower compute:Blade:chassisId managed object property"
    ::= { cfprApComputeBladeEntry 10 }

cfprApComputeBladeCheckPoint OBJECT-TYPE
    SYNTAX       CfprApComputeCheckPoint
    MAX-ACCESS   read-only
    STATUS       current
    DESCRIPTION
        "Cisco Firepower compute:Blade:checkPoint managed object property"
    ::= { cfprApComputeBladeEntry 11 }

cfprApComputeBladeConnPath OBJECT-TYPE
    SYNTAX       CfprApEquipmentConnectionStatus
    MAX-ACCESS   read-only
    STATUS       current
    DESCRIPTION
        "Cisco Firepower compute:Blade:connPath managed object property"
    ::= { cfprApComputeBladeEntry 12 }

cfprApComputeBladeConnStatus OBJECT-TYPE
    SYNTAX       CfprApEquipmentConnectionStatus
    MAX-ACCESS   read-only
    STATUS       current
    DESCRIPTION
        "Cisco Firepower compute:Blade:connStatus managed object property"
    ::= { cfprApComputeBladeEntry 13 }

cfprApComputeBladeDescr OBJECT-TYPE
    SYNTAX       SnmpAdminString
    MAX-ACCESS   read-only
    STATUS       current
    DESCRIPTION
        "Cisco Firepower compute:Blade:descr managed object property"
    ::= { cfprApComputeBladeEntry 14 }

cfprApComputeBladeDiscovery OBJECT-TYPE
    SYNTAX       CfprApComputeDiscovery
    MAX-ACCESS   read-only
    STATUS       current
    DESCRIPTION
        "Cisco Firepower compute:Blade:discovery managed object property"
    ::= { cfprApComputeBladeEntry 15 }

cfprApComputeBladeFltAggr OBJECT-TYPE
    SYNTAX       Unsigned64
    MAX-ACCESS   read-only
    STATUS       current
    DESCRIPTION
        "Cisco Firepower compute:Blade:fltAggr managed object property"
    ::= { cfprApComputeBladeEntry 16 }

cfprApComputeBladeFsmDescr OBJECT-TYPE
    SYNTAX       SnmpAdminString
    MAX-ACCESS   read-only
    STATUS       current
    DESCRIPTION
        "Cisco Firepower compute:Blade:fsmDescr managed object property"
    ::= { cfprApComputeBladeEntry 17 }

cfprApComputeBladeFsmFlags OBJECT-TYPE
    SYNTAX       SnmpAdminString
    MAX-ACCESS   read-only
    STATUS       current
    DESCRIPTION
        "Cisco Firepower compute:Blade:fsmFlags managed object property"
    ::= { cfprApComputeBladeEntry 18 }

cfprApComputeBladeFsmPrev OBJECT-TYPE
    SYNTAX       SnmpAdminString
    MAX-ACCESS   read-only
    STATUS       current
    DESCRIPTION
        "Cisco Firepower compute:Blade:fsmPrev managed object property"
    ::= { cfprApComputeBladeEntry 19 }

cfprApComputeBladeFsmProgr OBJECT-TYPE
    SYNTAX       Gauge32
    MAX-ACCESS   read-only
    STATUS       current
    DESCRIPTION
        "Cisco Firepower compute:Blade:fsmProgr managed object property"
    ::= { cfprApComputeBladeEntry 20 }

cfprApComputeBladeFsmRmtInvErrCode OBJECT-TYPE
    SYNTAX       Gauge32
    MAX-ACCESS   read-only
    STATUS       current
    DESCRIPTION
        "Cisco Firepower compute:Blade:fsmRmtInvErrCode
        managed object property"
    ::= { cfprApComputeBladeEntry 21 }

cfprApComputeBladeFsmRmtInvErrDescr OBJECT-TYPE
    SYNTAX       SnmpAdminString
    MAX-ACCESS   read-only
    STATUS       current
    DESCRIPTION
        "Cisco Firepower compute:Blade:fsmRmtInvErrDescr
        managed object property"
    ::= { cfprApComputeBladeEntry 22 }

cfprApComputeBladeFsmRmtInvRslt OBJECT-TYPE
    SYNTAX       CfprApConditionRemoteInvRslt
    MAX-ACCESS   read-only
    STATUS       current
    DESCRIPTION
        "Cisco Firepower compute:Blade:fsmRmtInvRslt managed
        object property"
    ::= { cfprApComputeBladeEntry 23 }

cfprApComputeBladeFsmStageDescr OBJECT-TYPE
    SYNTAX       SnmpAdminString
    MAX-ACCESS   read-only
    STATUS       current
    DESCRIPTION
        "Cisco Firepower compute:Blade:fsmStageDescr managed
        object property"
    ::= { cfprApComputeBladeEntry 24 }

cfprApComputeBladeFsmStamp OBJECT-TYPE
    SYNTAX       DateAndTime
    MAX-ACCESS   read-only
    STATUS       current
    DESCRIPTION
        "Cisco Firepower compute:Blade:fsmStamp managed object property"
    ::= { cfprApComputeBladeEntry 25 }

cfprApComputeBladeFsmStatus OBJECT-TYPE
    SYNTAX       SnmpAdminString
    MAX-ACCESS   read-only
    STATUS       current
    DESCRIPTION
        "Cisco Firepower compute:Blade:fsmStatus managed object property"
    ::= { cfprApComputeBladeEntry 26 }

cfprApComputeBladeFsmTry OBJECT-TYPE
    SYNTAX       Gauge32
    MAX-ACCESS   read-only
    STATUS       current
    DESCRIPTION
        "Cisco Firepower compute:Blade:fsmTry managed object property"
    ::= { cfprApComputeBladeEntry 27 }

cfprApComputeBladeIntId OBJECT-TYPE
    SYNTAX       SnmpAdminString
    MAX-ACCESS   read-only
    STATUS       current
    DESCRIPTION
        "Cisco Firepower compute:Blade:intId managed object property"
    ::= { cfprApComputeBladeEntry 28 }

cfprApComputeBladeLc OBJECT-TYPE
    SYNTAX       CfprApComputeAdminTrigger
    MAX-ACCESS   read-only
    STATUS       current
    DESCRIPTION
        "Cisco Firepower compute:Blade:lc managed object property"
    ::= { cfprApComputeBladeEntry 29 }

cfprApComputeBladeLcTs OBJECT-TYPE
    SYNTAX       DateAndTime
    MAX-ACCESS   read-only
    STATUS       current
    DESCRIPTION
        "Cisco Firepower compute:Blade:lcTs managed object property"
    ::= { cfprApComputeBladeEntry 30 }

cfprApComputeBladeLocalId OBJECT-TYPE
    SYNTAX       SnmpAdminString
    MAX-ACCESS   read-only
    STATUS       current
    DESCRIPTION
        "Cisco Firepower compute:Blade:localId managed object property"
    ::= { cfprApComputeBladeEntry 31 }

cfprApComputeBladeLowVoltageMemory OBJECT-TYPE
    SYNTAX       CfprApComputePhysicalLowVoltageMemory
    MAX-ACCESS   read-only
    STATUS       current
    DESCRIPTION
        "Cisco Firepower compute:Blade:lowVoltageMemory
        managed object property"
    ::= { cfprApComputeBladeEntry 32 }

cfprApComputeBladeManagingInst OBJECT-TYPE
    SYNTAX       CfprApNetworkSwitchId
    MAX-ACCESS   read-only
    STATUS       current
    DESCRIPTION
        "Cisco Firepower compute:Blade:managingInst managed
        object property"
    ::= { cfprApComputeBladeEntry 33 }

cfprApComputeBladeMemorySpeed OBJECT-TYPE
    SYNTAX       Gauge32
    MAX-ACCESS   read-only
    STATUS       current
    DESCRIPTION
        "Cisco Firepower compute:Blade:memorySpeed managed
        object property"
    ::= { cfprApComputeBladeEntry 34 }

cfprApComputeBladeMfgTime OBJECT-TYPE
    SYNTAX       DateAndTime
    MAX-ACCESS   read-only
    STATUS       current
    DESCRIPTION
        "Cisco Firepower compute:Blade:mfgTime managed object property"
    ::= { cfprApComputeBladeEntry 35 }

cfprApComputeBladeModel OBJECT-TYPE
    SYNTAX       SnmpAdminString
    MAX-ACCESS   read-only
    STATUS       current
    DESCRIPTION
        "Cisco Firepower compute:Blade:model managed object property"
    ::= { cfprApComputeBladeEntry 36 }

cfprApComputeBladeName OBJECT-TYPE
    SYNTAX       SnmpAdminString
    MAX-ACCESS   read-only
    STATUS       current
    DESCRIPTION
        "Cisco Firepower compute:Blade:name managed object property"
    ::= { cfprApComputeBladeEntry 37 }

cfprApComputeBladeNumOfAdaptors OBJECT-TYPE
    SYNTAX       Gauge32
    MAX-ACCESS   read-only
    STATUS       current
    DESCRIPTION
        "Cisco Firepower compute:Blade:numOfAdaptors managed
        object property"
    ::= { cfprApComputeBladeEntry 38 }

cfprApComputeBladeNumOfCores OBJECT-TYPE
    SYNTAX       Gauge32
    MAX-ACCESS   read-only
    STATUS       current
    DESCRIPTION
        "Cisco Firepower compute:Blade:numOfCores managed object property"
    ::= { cfprApComputeBladeEntry 39 }

cfprApComputeBladeNumOfCoresEnabled OBJECT-TYPE
    SYNTAX       Gauge32
    MAX-ACCESS   read-only
    STATUS       current
    DESCRIPTION
        "Cisco Firepower compute:Blade:numOfCoresEnabled
        managed object property"
    ::= { cfprApComputeBladeEntry 40 }

cfprApComputeBladeNumOfCpus OBJECT-TYPE
    SYNTAX       Gauge32
    MAX-ACCESS   read-only
    STATUS       current
    DESCRIPTION
        "Cisco Firepower compute:Blade:numOfCpus managed object property"
    ::= { cfprApComputeBladeEntry 41 }

cfprApComputeBladeNumOfEthHostIfs OBJECT-TYPE
    SYNTAX       Gauge32
    MAX-ACCESS   read-only
    STATUS       current
    DESCRIPTION
        "Cisco Firepower compute:Blade:numOfEthHostIfs
        managed object property"
    ::= { cfprApComputeBladeEntry 42 }

cfprApComputeBladeNumOfFcHostIfs OBJECT-TYPE
    SYNTAX       Gauge32
    MAX-ACCESS   read-only
    STATUS       current
    DESCRIPTION
        "Cisco Firepower compute:Blade:numOfFcHostIfs managed
        object property"
    ::= { cfprApComputeBladeEntry 43 }

cfprApComputeBladeNumOfThreads OBJECT-TYPE
    SYNTAX       Gauge32
    MAX-ACCESS   read-only
    STATUS       current
    DESCRIPTION
        "Cisco Firepower compute:Blade:numOfThreads managed
        object property"
    ::= { cfprApComputeBladeEntry 44 }

cfprApComputeBladeOperPower OBJECT-TYPE
    SYNTAX       CfprApEquipmentPowerState
    MAX-ACCESS   read-only
    STATUS       current
    DESCRIPTION
        "Cisco Firepower compute:Blade:operPower managed object property"
    ::= { cfprApComputeBladeEntry 45 }

cfprApComputeBladeOperQualifier OBJECT-TYPE
    SYNTAX       CfprApComputeIssues
    MAX-ACCESS   read-only
    STATUS       current
    DESCRIPTION
        "Cisco Firepower compute:Blade:operQualifier managed
        object property"
    ::= { cfprApComputeBladeEntry 46 }

cfprApComputeBladeOperState OBJECT-TYPE
    SYNTAX       CfprApLsOperState
    MAX-ACCESS   read-only
    STATUS       current
    DESCRIPTION
        "Cisco Firepower compute:Blade:operState managed object property"
    ::= { cfprApComputeBladeEntry 47 }

cfprApComputeBladeOperability OBJECT-TYPE
    SYNTAX       CfprApEquipmentOperability
    MAX-ACCESS   read-only
    STATUS       current
    DESCRIPTION
        "Cisco Firepower compute:Blade:operability managed
        object property"
    ::= { cfprApComputeBladeEntry 48 }

cfprApComputeBladeOriginalUuid OBJECT-TYPE
    SYNTAX       SnmpAdminString
    MAX-ACCESS   read-only
    STATUS       current
    DESCRIPTION
        "Cisco Firepower compute:Blade:originalUuid managed
        object property"
    ::= { cfprApComputeBladeEntry 49 }

cfprApComputeBladePartNumber OBJECT-TYPE
    SYNTAX       SnmpAdminString
    MAX-ACCESS   read-only
    STATUS       current
    DESCRIPTION
        "Cisco Firepower compute:Blade:partNumber managed object property"
    ::= { cfprApComputeBladeEntry 50 }

cfprApComputeBladePolicyLevel OBJECT-TYPE
    SYNTAX       Gauge32
    MAX-ACCESS   read-only
    STATUS       current
    DESCRIPTION
        "Cisco Firepower compute:Blade:policyLevel managed
        object property"
    ::= { cfprApComputeBladeEntry 51 }

cfprApComputeBladePolicyOwner OBJECT-TYPE
    SYNTAX       CfprApPolicyPolicyOwner
    MAX-ACCESS   read-only
    STATUS       current
    DESCRIPTION
        "Cisco Firepower compute:Blade:policyOwner managed
        object property"
    ::= { cfprApComputeBladeEntry 52 }

cfprApComputeBladePresence OBJECT-TYPE
    SYNTAX       CfprApEquipmentSlotStatus
    MAX-ACCESS   read-only
    STATUS       current
    DESCRIPTION
        "Cisco Firepower compute:Blade:presence managed object property"
    ::= { cfprApComputeBladeEntry 53 }

cfprApComputeBladeRevision OBJECT-TYPE
    SYNTAX       SnmpAdminString
    MAX-ACCESS   read-only
    STATUS       current
    DESCRIPTION
        "Cisco Firepower compute:Blade:revision managed object property"
    ::= { cfprApComputeBladeEntry 54 }

cfprApComputeBladeScaledMode OBJECT-TYPE
    SYNTAX       CfprApComputeMode
    MAX-ACCESS   read-only
    STATUS       current
    DESCRIPTION
        "Cisco Firepower compute:Blade:scaledMode managed object property"
    ::= { cfprApComputeBladeEntry 55 }

cfprApComputeBladeSerial OBJECT-TYPE
    SYNTAX       SnmpAdminString
    MAX-ACCESS   read-only
    STATUS       current
    DESCRIPTION
        "Cisco Firepower compute:Blade:serial managed object property"
    ::= { cfprApComputeBladeEntry 56 }

cfprApComputeBladeServerId OBJECT-TYPE
    SYNTAX       SnmpAdminString
    MAX-ACCESS   read-only
    STATUS       current
    DESCRIPTION
        "Cisco Firepower compute:Blade:serverId managed object property"
    ::= { cfprApComputeBladeEntry 57 }

cfprApComputeBladeSlotId OBJECT-TYPE
    SYNTAX       CfprApComputeBladeSlotId
    MAX-ACCESS   read-only
    STATUS       current
    DESCRIPTION
        "Cisco Firepower compute:Blade:slotId managed object property"
    ::= { cfprApComputeBladeEntry 58 }

cfprApComputeBladeTotalMemory OBJECT-TYPE
    SYNTAX       Gauge32
    MAX-ACCESS   read-only
    STATUS       current
    DESCRIPTION
        "Cisco Firepower compute:Blade:totalMemory managed
        object property"
    ::= { cfprApComputeBladeEntry 59 }

cfprApComputeBladeUpgradeScenario OBJECT-TYPE
    SYNTAX       CfprApComputeUpgradeStatus
    MAX-ACCESS   read-only
    STATUS       current
    DESCRIPTION
        "Cisco Firepower compute:Blade:upgradeScenario
        managed object property"
    ::= { cfprApComputeBladeEntry 60 }

cfprApComputeBladeUsrLbl OBJECT-TYPE
    SYNTAX       SnmpAdminString
    MAX-ACCESS   read-only
    STATUS       current
    DESCRIPTION
        "Cisco Firepower compute:Blade:usrLbl managed object property"
    ::= { cfprApComputeBladeEntry 61 }

cfprApComputeBladeUuid OBJECT-TYPE
    SYNTAX       SnmpAdminString
    MAX-ACCESS   read-only
    STATUS       current
    DESCRIPTION
        "Cisco Firepower compute:Blade:uuid managed object property"
    ::= { cfprApComputeBladeEntry 62 }

cfprApComputeBladeVendor OBJECT-TYPE
    SYNTAX       SnmpAdminString
    MAX-ACCESS   read-only
    STATUS       current
    DESCRIPTION
        "Cisco Firepower compute:Blade:vendor managed object property"
    ::= { cfprApComputeBladeEntry 63 }

cfprApComputeBladeVid OBJECT-TYPE
    SYNTAX       SnmpAdminString
    MAX-ACCESS   read-only
    STATUS       current
    DESCRIPTION
        "Cisco Firepower compute:Blade:vid managed object property"
    ::= { cfprApComputeBladeEntry 64 }

cfprApComputeBladeDiscPolicyTable OBJECT-TYPE
    SYNTAX           SEQUENCE OF CfprApComputeBladeDiscPolicyEntry
    MAX-ACCESS       not-accessible
    STATUS           current
    DESCRIPTION
        "Cisco Firepower compute:BladeDiscPolicy managed object table"
    ::= { cfprApComputeObjects 3 }

cfprApComputeBladeDiscPolicyEntry OBJECT-TYPE
    SYNTAX           CfprApComputeBladeDiscPolicyEntry
    MAX-ACCESS       not-accessible
    STATUS           current
    DESCRIPTION
        "Entry for the cfprApComputeBladeDiscPolicyTable table."
    INDEX { cfprApComputeBladeDiscPolicyInstanceId }
    ::= { cfprApComputeBladeDiscPolicyTable 1 }

CfprApComputeBladeDiscPolicyEntry ::= SEQUENCE {
    cfprApComputeBladeDiscPolicyInstanceId                           CfprApManagedObjectId,
    cfprApComputeBladeDiscPolicyDn                                   CfprApManagedObjectDn,
    cfprApComputeBladeDiscPolicyRn                                   SnmpAdminString,
    cfprApComputeBladeDiscPolicyAction                               SnmpAdminString,
    cfprApComputeBladeDiscPolicyDescr                                SnmpAdminString,
    cfprApComputeBladeDiscPolicyIntId                                SnmpAdminString,
    cfprApComputeBladeDiscPolicyName                                 SnmpAdminString,
    cfprApComputeBladeDiscPolicyPolicyLevel                          Gauge32,
    cfprApComputeBladeDiscPolicyPolicyOwner                          CfprApPolicyPolicyOwner,
    cfprApComputeBladeDiscPolicyQualifier                            SnmpAdminString,
    cfprApComputeBladeDiscPolicyScrubPolicyName                      SnmpAdminString
}

cfprApComputeBladeDiscPolicyInstanceId OBJECT-TYPE
    SYNTAX       CfprApManagedObjectId
    MAX-ACCESS   not-accessible
    STATUS       current
    DESCRIPTION
        "Instance identifier of the managed object."
    ::= { cfprApComputeBladeDiscPolicyEntry 1 }

cfprApComputeBladeDiscPolicyDn OBJECT-TYPE
    SYNTAX       CfprApManagedObjectDn
    MAX-ACCESS   read-only
    STATUS       current
    DESCRIPTION
        "Cisco Firepower compute:BladeDiscPolicy:dn managed
        object property"
    ::= { cfprApComputeBladeDiscPolicyEntry 2 }

cfprApComputeBladeDiscPolicyRn OBJECT-TYPE
    SYNTAX       SnmpAdminString
    MAX-ACCESS   read-only
    STATUS       current
    DESCRIPTION
        "Cisco Firepower compute:BladeDiscPolicy:rn managed
        object property"
    ::= { cfprApComputeBladeDiscPolicyEntry 3 }

cfprApComputeBladeDiscPolicyAction OBJECT-TYPE
    SYNTAX       SnmpAdminString
    MAX-ACCESS   read-only
    STATUS       current
    DESCRIPTION
        "Cisco Firepower compute:BladeDiscPolicy:action
        managed object property"
    ::= { cfprApComputeBladeDiscPolicyEntry 4 }

cfprApComputeBladeDiscPolicyDescr OBJECT-TYPE
    SYNTAX       SnmpAdminString
    MAX-ACCESS   read-only
    STATUS       current
    DESCRIPTION
        "Cisco Firepower compute:BladeDiscPolicy:descr
        managed object property"
    ::= { cfprApComputeBladeDiscPolicyEntry 5 }

cfprApComputeBladeDiscPolicyIntId OBJECT-TYPE
    SYNTAX       SnmpAdminString
    MAX-ACCESS   read-only
    STATUS       current
    DESCRIPTION
        "Cisco Firepower compute:BladeDiscPolicy:intId
        managed object property"
    ::= { cfprApComputeBladeDiscPolicyEntry 6 }

cfprApComputeBladeDiscPolicyName OBJECT-TYPE
    SYNTAX       SnmpAdminString
    MAX-ACCESS   read-only
    STATUS       current
    DESCRIPTION
        "Cisco Firepower compute:BladeDiscPolicy:name managed
        object property"
    ::= { cfprApComputeBladeDiscPolicyEntry 7 }

cfprApComputeBladeDiscPolicyPolicyLevel OBJECT-TYPE
    SYNTAX       Gauge32
    MAX-ACCESS   read-only
    STATUS       current
    DESCRIPTION
        "Cisco Firepower compute:BladeDiscPolicy:policyLevel
        managed object property"
    ::= { cfprApComputeBladeDiscPolicyEntry 8 }

cfprApComputeBladeDiscPolicyPolicyOwner OBJECT-TYPE
    SYNTAX       CfprApPolicyPolicyOwner
    MAX-ACCESS   read-only
    STATUS       current
    DESCRIPTION
        "Cisco Firepower compute:BladeDiscPolicy:policyOwner
        managed object property"
    ::= { cfprApComputeBladeDiscPolicyEntry 9 }

cfprApComputeBladeDiscPolicyQualifier OBJECT-TYPE
    SYNTAX       SnmpAdminString
    MAX-ACCESS   read-only
    STATUS       current
    DESCRIPTION
        "Cisco Firepower compute:BladeDiscPolicy:qualifier
        managed object property"
    ::= { cfprApComputeBladeDiscPolicyEntry 10 }

cfprApComputeBladeDiscPolicyScrubPolicyName OBJECT-TYPE
    SYNTAX       SnmpAdminString
    MAX-ACCESS   read-only
    STATUS       current
    DESCRIPTION
        "Cisco Firepower compute:BladeDiscPolicy:scrubPolicyName
        managed object property"
    ::= { cfprApComputeBladeDiscPolicyEntry 11 }

cfprApComputeBladeFsmTable OBJECT-TYPE
    SYNTAX           SEQUENCE OF CfprApComputeBladeFsmEntry
    MAX-ACCESS       not-accessible
    STATUS           current
    DESCRIPTION
        "Cisco Firepower compute:BladeFsm managed object table"
    ::= { cfprApComputeObjects 4 }

cfprApComputeBladeFsmEntry OBJECT-TYPE
    SYNTAX           CfprApComputeBladeFsmEntry
    MAX-ACCESS       not-accessible
    STATUS           current
    DESCRIPTION
        "Entry for the cfprApComputeBladeFsmTable table."
    INDEX { cfprApComputeBladeFsmInstanceId }
    ::= { cfprApComputeBladeFsmTable 1 }

CfprApComputeBladeFsmEntry ::= SEQUENCE {
    cfprApComputeBladeFsmInstanceId                                  CfprApManagedObjectId,
    cfprApComputeBladeFsmDn                                          CfprApManagedObjectDn,
    cfprApComputeBladeFsmRn                                          SnmpAdminString,
    cfprApComputeBladeFsmCompletionTime                              DateAndTime,
    cfprApComputeBladeFsmCurrentFsm                                  CfprApComputeBladeFsmCurrentFsm,
    cfprApComputeBladeFsmDescrData                                   SnmpAdminString,
    cfprApComputeBladeFsmFsmStatus                                   CfprApFsmFsmStageStatus,
    cfprApComputeBladeFsmProgress                                    Gauge32,
    cfprApComputeBladeFsmRmtErrCode                                  Gauge32,
    cfprApComputeBladeFsmRmtErrDescr                                 SnmpAdminString,
    cfprApComputeBladeFsmRmtRslt                                     CfprApConditionRemoteInvRslt
}

cfprApComputeBladeFsmInstanceId OBJECT-TYPE
    SYNTAX       CfprApManagedObjectId
    MAX-ACCESS   not-accessible
    STATUS       current
    DESCRIPTION
        "Instance identifier of the managed object."
    ::= { cfprApComputeBladeFsmEntry 1 }

cfprApComputeBladeFsmDn OBJECT-TYPE
    SYNTAX       CfprApManagedObjectDn
    MAX-ACCESS   read-only
    STATUS       current
    DESCRIPTION
        "Cisco Firepower compute:BladeFsm:dn managed object property"
    ::= { cfprApComputeBladeFsmEntry 2 }

cfprApComputeBladeFsmRn OBJECT-TYPE
    SYNTAX       SnmpAdminString
    MAX-ACCESS   read-only
    STATUS       current
    DESCRIPTION
        "Cisco Firepower compute:BladeFsm:rn managed object property"
    ::= { cfprApComputeBladeFsmEntry 3 }

cfprApComputeBladeFsmCompletionTime OBJECT-TYPE
    SYNTAX       DateAndTime
    MAX-ACCESS   read-only
    STATUS       current
    DESCRIPTION
        "Cisco Firepower compute:BladeFsm:completionTime
        managed object property"
    ::= { cfprApComputeBladeFsmEntry 4 }

cfprApComputeBladeFsmCurrentFsm OBJECT-TYPE
    SYNTAX       CfprApComputeBladeFsmCurrentFsm
    MAX-ACCESS   read-only
    STATUS       current
    DESCRIPTION
        "Cisco Firepower compute:BladeFsm:currentFsm managed
        object property"
    ::= { cfprApComputeBladeFsmEntry 5 }

cfprApComputeBladeFsmDescrData OBJECT-TYPE
    SYNTAX       SnmpAdminString
    MAX-ACCESS   read-only
    STATUS       current
    DESCRIPTION
        "Cisco Firepower compute:BladeFsm:descr managed object property"
    ::= { cfprApComputeBladeFsmEntry 6 }

cfprApComputeBladeFsmFsmStatus OBJECT-TYPE
    SYNTAX       CfprApFsmFsmStageStatus
    MAX-ACCESS   read-only
    STATUS       current
    DESCRIPTION
        "Cisco Firepower compute:BladeFsm:fsmStatus managed
        object property"
    ::= { cfprApComputeBladeFsmEntry 7 }

cfprApComputeBladeFsmProgress OBJECT-TYPE
    SYNTAX       Gauge32
    MAX-ACCESS   read-only
    STATUS       current
    DESCRIPTION
        "Cisco Firepower compute:BladeFsm:progress managed
        object property"
    ::= { cfprApComputeBladeFsmEntry 8 }

cfprApComputeBladeFsmRmtErrCode OBJECT-TYPE
    SYNTAX       Gauge32
    MAX-ACCESS   read-only
    STATUS       current
    DESCRIPTION
        "Cisco Firepower compute:BladeFsm:rmtErrCode managed
        object property"
    ::= { cfprApComputeBladeFsmEntry 9 }

cfprApComputeBladeFsmRmtErrDescr OBJECT-TYPE
    SYNTAX       SnmpAdminString
    MAX-ACCESS   read-only
    STATUS       current
    DESCRIPTION
        "Cisco Firepower compute:BladeFsm:rmtErrDescr managed
        object property"
    ::= { cfprApComputeBladeFsmEntry 10 }

cfprApComputeBladeFsmRmtRslt OBJECT-TYPE
    SYNTAX       CfprApConditionRemoteInvRslt
    MAX-ACCESS   read-only
    STATUS       current
    DESCRIPTION
        "Cisco Firepower compute:BladeFsm:rmtRslt managed object property"
    ::= { cfprApComputeBladeFsmEntry 11 }

cfprApComputeBladeFsmStageTable OBJECT-TYPE
    SYNTAX           SEQUENCE OF CfprApComputeBladeFsmStageEntry
    MAX-ACCESS       not-accessible
    STATUS           current
    DESCRIPTION
        "Cisco Firepower compute:BladeFsmStage managed object table"
    ::= { cfprApComputeObjects 5 }

cfprApComputeBladeFsmStageEntry OBJECT-TYPE
    SYNTAX           CfprApComputeBladeFsmStageEntry
    MAX-ACCESS       not-accessible
    STATUS           current
    DESCRIPTION
        "Entry for the cfprApComputeBladeFsmStageTable table."
    INDEX { cfprApComputeBladeFsmStageInstanceId }
    ::= { cfprApComputeBladeFsmStageTable 1 }

CfprApComputeBladeFsmStageEntry ::= SEQUENCE {
    cfprApComputeBladeFsmStageInstanceId                             CfprApManagedObjectId,
    cfprApComputeBladeFsmStageDn                                     CfprApManagedObjectDn,
    cfprApComputeBladeFsmStageRn                                     SnmpAdminString,
    cfprApComputeBladeFsmStageDescrData                              SnmpAdminString,
    cfprApComputeBladeFsmStageLastUpdateTime                         DateAndTime,
    cfprApComputeBladeFsmStageName                                   CfprApComputeBladeFsmStageName,
    cfprApComputeBladeFsmStageOrder                                  Gauge32,
    cfprApComputeBladeFsmStageRetry                                  Gauge32,
    cfprApComputeBladeFsmStageStageStatus                            CfprApFsmFsmStageStatus
}

cfprApComputeBladeFsmStageInstanceId OBJECT-TYPE
    SYNTAX       CfprApManagedObjectId
    MAX-ACCESS   not-accessible
    STATUS       current
    DESCRIPTION
        "Instance identifier of the managed object."
    ::= { cfprApComputeBladeFsmStageEntry 1 }

cfprApComputeBladeFsmStageDn OBJECT-TYPE
    SYNTAX       CfprApManagedObjectDn
    MAX-ACCESS   read-only
    STATUS       current
    DESCRIPTION
        "Cisco Firepower compute:BladeFsmStage:dn managed object property"
    ::= { cfprApComputeBladeFsmStageEntry 2 }

cfprApComputeBladeFsmStageRn OBJECT-TYPE
    SYNTAX       SnmpAdminString
    MAX-ACCESS   read-only
    STATUS       current
    DESCRIPTION
        "Cisco Firepower compute:BladeFsmStage:rn managed object property"
    ::= { cfprApComputeBladeFsmStageEntry 3 }

cfprApComputeBladeFsmStageDescrData OBJECT-TYPE
    SYNTAX       SnmpAdminString
    MAX-ACCESS   read-only
    STATUS       current
    DESCRIPTION
        "Cisco Firepower compute:BladeFsmStage:descr managed
        object property"
    ::= { cfprApComputeBladeFsmStageEntry 4 }

cfprApComputeBladeFsmStageLastUpdateTime OBJECT-TYPE
    SYNTAX       DateAndTime
    MAX-ACCESS   read-only
    STATUS       current
    DESCRIPTION
        "Cisco Firepower compute:BladeFsmStage:lastUpdateTime
        managed object property"
    ::= { cfprApComputeBladeFsmStageEntry 5 }

cfprApComputeBladeFsmStageName OBJECT-TYPE
    SYNTAX       CfprApComputeBladeFsmStageName
    MAX-ACCESS   read-only
    STATUS       current
    DESCRIPTION
        "Cisco Firepower compute:BladeFsmStage:name managed
        object property"
    ::= { cfprApComputeBladeFsmStageEntry 6 }

cfprApComputeBladeFsmStageOrder OBJECT-TYPE
    SYNTAX       Gauge32
    MAX-ACCESS   read-only
    STATUS       current
    DESCRIPTION
        "Cisco Firepower compute:BladeFsmStage:order managed
        object property"
    ::= { cfprApComputeBladeFsmStageEntry 7 }

cfprApComputeBladeFsmStageRetry OBJECT-TYPE
    SYNTAX       Gauge32
    MAX-ACCESS   read-only
    STATUS       current
    DESCRIPTION
        "Cisco Firepower compute:BladeFsmStage:retry managed
        object property"
    ::= { cfprApComputeBladeFsmStageEntry 8 }

cfprApComputeBladeFsmStageStageStatus OBJECT-TYPE
    SYNTAX       CfprApFsmFsmStageStatus
    MAX-ACCESS   read-only
    STATUS       current
    DESCRIPTION
        "Cisco Firepower compute:BladeFsmStage:stageStatus
        managed object property"
    ::= { cfprApComputeBladeFsmStageEntry 9 }

cfprApComputeBladeFsmTaskTable OBJECT-TYPE
    SYNTAX           SEQUENCE OF CfprApComputeBladeFsmTaskEntry
    MAX-ACCESS       not-accessible
    STATUS           current
    DESCRIPTION
        "Cisco Firepower compute:BladeFsmTask managed object table"
    ::= { cfprApComputeObjects 6 }

cfprApComputeBladeFsmTaskEntry OBJECT-TYPE
    SYNTAX           CfprApComputeBladeFsmTaskEntry
    MAX-ACCESS       not-accessible
    STATUS           current
    DESCRIPTION
        "Entry for the cfprApComputeBladeFsmTaskTable table."
    INDEX { cfprApComputeBladeFsmTaskInstanceId }
    ::= { cfprApComputeBladeFsmTaskTable 1 }

CfprApComputeBladeFsmTaskEntry ::= SEQUENCE {
    cfprApComputeBladeFsmTaskInstanceId                              CfprApManagedObjectId,
    cfprApComputeBladeFsmTaskDn                                      CfprApManagedObjectDn,
    cfprApComputeBladeFsmTaskRn                                      SnmpAdminString,
    cfprApComputeBladeFsmTaskCompletion                              CfprApFsmCompletion,
    cfprApComputeBladeFsmTaskFlags                                   CfprApComputeBladeFsmTaskFlags,
    cfprApComputeBladeFsmTaskItem                                    CfprApComputeBladeFsmTaskItem,
    cfprApComputeBladeFsmTaskSeqId                                   Gauge32
}

cfprApComputeBladeFsmTaskInstanceId OBJECT-TYPE
    SYNTAX       CfprApManagedObjectId
    MAX-ACCESS   not-accessible
    STATUS       current
    DESCRIPTION
        "Instance identifier of the managed object."
    ::= { cfprApComputeBladeFsmTaskEntry 1 }

cfprApComputeBladeFsmTaskDn OBJECT-TYPE
    SYNTAX       CfprApManagedObjectDn
    MAX-ACCESS   read-only
    STATUS       current
    DESCRIPTION
        "Cisco Firepower compute:BladeFsmTask:dn managed object property"
    ::= { cfprApComputeBladeFsmTaskEntry 2 }

cfprApComputeBladeFsmTaskRn OBJECT-TYPE
    SYNTAX       SnmpAdminString
    MAX-ACCESS   read-only
    STATUS       current
    DESCRIPTION
        "Cisco Firepower compute:BladeFsmTask:rn managed object property"
    ::= { cfprApComputeBladeFsmTaskEntry 3 }

cfprApComputeBladeFsmTaskCompletion OBJECT-TYPE
    SYNTAX       CfprApFsmCompletion
    MAX-ACCESS   read-only
    STATUS       current
    DESCRIPTION
        "Cisco Firepower compute:BladeFsmTask:completion
        managed object property"
    ::= { cfprApComputeBladeFsmTaskEntry 4 }

cfprApComputeBladeFsmTaskFlags OBJECT-TYPE
    SYNTAX       CfprApComputeBladeFsmTaskFlags
    MAX-ACCESS   read-only
    STATUS       current
    DESCRIPTION
        "Cisco Firepower compute:BladeFsmTask:flags managed
        object property"
    ::= { cfprApComputeBladeFsmTaskEntry 5 }

cfprApComputeBladeFsmTaskItem OBJECT-TYPE
    SYNTAX       CfprApComputeBladeFsmTaskItem
    MAX-ACCESS   read-only
    STATUS       current
    DESCRIPTION
        "Cisco Firepower compute:BladeFsmTask:item managed
        object property"
    ::= { cfprApComputeBladeFsmTaskEntry 6 }

cfprApComputeBladeFsmTaskSeqId OBJECT-TYPE
    SYNTAX       Gauge32
    MAX-ACCESS   read-only
    STATUS       current
    DESCRIPTION
        "Cisco Firepower compute:BladeFsmTask:seqId managed
        object property"
    ::= { cfprApComputeBladeFsmTaskEntry 7 }

cfprApComputeBladeInheritPolicyTable OBJECT-TYPE
    SYNTAX           SEQUENCE OF CfprApComputeBladeInheritPolicyEntry
    MAX-ACCESS       not-accessible
    STATUS           current
    DESCRIPTION
        "Cisco Firepower compute:BladeInheritPolicy managed object table"
    ::= { cfprApComputeObjects 7 }

cfprApComputeBladeInheritPolicyEntry OBJECT-TYPE
    SYNTAX           CfprApComputeBladeInheritPolicyEntry
    MAX-ACCESS       not-accessible
    STATUS           current
    DESCRIPTION
        "Entry for the cfprApComputeBladeInheritPolicyTable table."
    INDEX { cfprApComputeBladeInheritPolicyInstanceId }
    ::= { cfprApComputeBladeInheritPolicyTable 1 }

CfprApComputeBladeInheritPolicyEntry ::= SEQUENCE {
    cfprApComputeBladeInheritPolicyInstanceId                        CfprApManagedObjectId,
    cfprApComputeBladeInheritPolicyDn                                CfprApManagedObjectDn,
    cfprApComputeBladeInheritPolicyRn                                SnmpAdminString,
    cfprApComputeBladeInheritPolicyDescr                             SnmpAdminString,
    cfprApComputeBladeInheritPolicyDstDn                             SnmpAdminString,
    cfprApComputeBladeInheritPolicyIntId                             SnmpAdminString,
    cfprApComputeBladeInheritPolicyName                              SnmpAdminString,
    cfprApComputeBladeInheritPolicyPolicyLevel                       Gauge32,
    cfprApComputeBladeInheritPolicyPolicyOwner                       CfprApPolicyPolicyOwner,
    cfprApComputeBladeInheritPolicyQualifier                         SnmpAdminString
}

cfprApComputeBladeInheritPolicyInstanceId OBJECT-TYPE
    SYNTAX       CfprApManagedObjectId
    MAX-ACCESS   not-accessible
    STATUS       current
    DESCRIPTION
        "Instance identifier of the managed object."
    ::= { cfprApComputeBladeInheritPolicyEntry 1 }

cfprApComputeBladeInheritPolicyDn OBJECT-TYPE
    SYNTAX       CfprApManagedObjectDn
    MAX-ACCESS   read-only
    STATUS       current
    DESCRIPTION
        "Cisco Firepower compute:BladeInheritPolicy:dn
        managed object property"
    ::= { cfprApComputeBladeInheritPolicyEntry 2 }

cfprApComputeBladeInheritPolicyRn OBJECT-TYPE
    SYNTAX       SnmpAdminString
    MAX-ACCESS   read-only
    STATUS       current
    DESCRIPTION
        "Cisco Firepower compute:BladeInheritPolicy:rn
        managed object property"
    ::= { cfprApComputeBladeInheritPolicyEntry 3 }

cfprApComputeBladeInheritPolicyDescr OBJECT-TYPE
    SYNTAX       SnmpAdminString
    MAX-ACCESS   read-only
    STATUS       current
    DESCRIPTION
        "Cisco Firepower compute:BladeInheritPolicy:descr
        managed object property"
    ::= { cfprApComputeBladeInheritPolicyEntry 4 }

cfprApComputeBladeInheritPolicyDstDn OBJECT-TYPE
    SYNTAX       SnmpAdminString
    MAX-ACCESS   read-only
    STATUS       current
    DESCRIPTION
        "Cisco Firepower compute:BladeInheritPolicy:dstDn
        managed object property"
    ::= { cfprApComputeBladeInheritPolicyEntry 5 }

cfprApComputeBladeInheritPolicyIntId OBJECT-TYPE
    SYNTAX       SnmpAdminString
    MAX-ACCESS   read-only
    STATUS       current
    DESCRIPTION
        "Cisco Firepower compute:BladeInheritPolicy:intId
        managed object property"
    ::= { cfprApComputeBladeInheritPolicyEntry 6 }

cfprApComputeBladeInheritPolicyName OBJECT-TYPE
    SYNTAX       SnmpAdminString
    MAX-ACCESS   read-only
    STATUS       current
    DESCRIPTION
        "Cisco Firepower compute:BladeInheritPolicy:name
        managed object property"
    ::= { cfprApComputeBladeInheritPolicyEntry 7 }

cfprApComputeBladeInheritPolicyPolicyLevel OBJECT-TYPE
    SYNTAX       Gauge32
    MAX-ACCESS   read-only
    STATUS       current
    DESCRIPTION
        "Cisco Firepower compute:BladeInheritPolicy:policyLevel
        managed object property"
    ::= { cfprApComputeBladeInheritPolicyEntry 8 }

cfprApComputeBladeInheritPolicyPolicyOwner OBJECT-TYPE
    SYNTAX       CfprApPolicyPolicyOwner
    MAX-ACCESS   read-only
    STATUS       current
    DESCRIPTION
        "Cisco Firepower compute:BladeInheritPolicy:policyOwner
        managed object property"
    ::= { cfprApComputeBladeInheritPolicyEntry 9 }

cfprApComputeBladeInheritPolicyQualifier OBJECT-TYPE
    SYNTAX       SnmpAdminString
    MAX-ACCESS   read-only
    STATUS       current
    DESCRIPTION
        "Cisco Firepower compute:BladeInheritPolicy:qualifier
        managed object property"
    ::= { cfprApComputeBladeInheritPolicyEntry 10 }

cfprApComputeBoardTable OBJECT-TYPE
    SYNTAX           SEQUENCE OF CfprApComputeBoardEntry
    MAX-ACCESS       not-accessible
    STATUS           current
    DESCRIPTION
        "Cisco Firepower compute:Board managed object table"
    ::= { cfprApComputeObjects 8 }

cfprApComputeBoardEntry OBJECT-TYPE
    SYNTAX           CfprApComputeBoardEntry
    MAX-ACCESS       not-accessible
    STATUS           current
    DESCRIPTION
        "Entry for the cfprApComputeBoardTable table."
    INDEX { cfprApComputeBoardInstanceId }
    ::= { cfprApComputeBoardTable 1 }

CfprApComputeBoardEntry ::= SEQUENCE {
    cfprApComputeBoardInstanceId                                     CfprApManagedObjectId,
    cfprApComputeBoardDn                                             CfprApManagedObjectDn,
    cfprApComputeBoardRn                                             SnmpAdminString,
    cfprApComputeBoardCmosVoltage                                    CfprApEquipmentSensorThresholdStatus,
    cfprApComputeBoardCpuType                                        CfprApEquipmentCpuType,
    cfprApComputeBoardFaultQualifier                                 SnmpAdminString,
    cfprApComputeBoardId                                             Gauge32,
    cfprApComputeBoardLocationDn                                     SnmpAdminString,
    cfprApComputeBoardModel                                          SnmpAdminString,
    cfprApComputeBoardOperPower                                      CfprApEquipmentPowerState,
    cfprApComputeBoardOperQualifierReason                            SnmpAdminString,
    cfprApComputeBoardOperState                                      CfprApEquipmentOperability,
    cfprApComputeBoardOperability                                    CfprApEquipmentOperability,
    cfprApComputeBoardPerf                                           CfprApEquipmentSensorThresholdStatus,
    cfprApComputeBoardPower                                          CfprApComputeABoardPower,
    cfprApComputeBoardPowerUsage                                     CfprApEquipmentSensorThresholdStatus,
    cfprApComputeBoardPresence                                       CfprApEquipmentPresence,
    cfprApComputeBoardRevision                                       SnmpAdminString,
    cfprApComputeBoardSerial                                         SnmpAdminString,
    cfprApComputeBoardThermal                                        CfprApEquipmentSensorThresholdStatus,
    cfprApComputeBoardVendor                                         SnmpAdminString,
    cfprApComputeBoardVoltage                                        CfprApEquipmentSensorThresholdStatus
}

cfprApComputeBoardInstanceId OBJECT-TYPE
    SYNTAX       CfprApManagedObjectId
    MAX-ACCESS   not-accessible
    STATUS       current
    DESCRIPTION
        "Instance identifier of the managed object."
    ::= { cfprApComputeBoardEntry 1 }

cfprApComputeBoardDn OBJECT-TYPE
    SYNTAX       CfprApManagedObjectDn
    MAX-ACCESS   read-only
    STATUS       current
    DESCRIPTION
        "Cisco Firepower compute:Board:dn managed object property"
    ::= { cfprApComputeBoardEntry 2 }

cfprApComputeBoardRn OBJECT-TYPE
    SYNTAX       SnmpAdminString
    MAX-ACCESS   read-only
    STATUS       current
    DESCRIPTION
        "Cisco Firepower compute:Board:rn managed object property"
    ::= { cfprApComputeBoardEntry 3 }

cfprApComputeBoardCmosVoltage OBJECT-TYPE
    SYNTAX       CfprApEquipmentSensorThresholdStatus
    MAX-ACCESS   read-only
    STATUS       current
    DESCRIPTION
        "Cisco Firepower compute:Board:cmosVoltage managed
        object property"
    ::= { cfprApComputeBoardEntry 4 }

cfprApComputeBoardCpuType OBJECT-TYPE
    SYNTAX       CfprApEquipmentCpuType
    MAX-ACCESS   read-only
    STATUS       current
    DESCRIPTION
        "Cisco Firepower compute:Board:cpuType managed object property"
    ::= { cfprApComputeBoardEntry 5 }

cfprApComputeBoardFaultQualifier OBJECT-TYPE
    SYNTAX       SnmpAdminString
    MAX-ACCESS   read-only
    STATUS       current
    DESCRIPTION
        "Cisco Firepower compute:Board:faultQualifier managed
        object property"
    ::= { cfprApComputeBoardEntry 6 }

cfprApComputeBoardId OBJECT-TYPE
    SYNTAX       Gauge32
    MAX-ACCESS   read-only
    STATUS       current
    DESCRIPTION
        "Cisco Firepower compute:Board:id managed object property"
    ::= { cfprApComputeBoardEntry 7 }

cfprApComputeBoardLocationDn OBJECT-TYPE
    SYNTAX       SnmpAdminString
    MAX-ACCESS   read-only
    STATUS       current
    DESCRIPTION
        "Cisco Firepower compute:Board:locationDn managed object property"
    ::= { cfprApComputeBoardEntry 8 }

cfprApComputeBoardModel OBJECT-TYPE
    SYNTAX       SnmpAdminString
    MAX-ACCESS   read-only
    STATUS       current
    DESCRIPTION
        "Cisco Firepower compute:Board:model managed object property"
    ::= { cfprApComputeBoardEntry 9 }

cfprApComputeBoardOperPower OBJECT-TYPE
    SYNTAX       CfprApEquipmentPowerState
    MAX-ACCESS   read-only
    STATUS       current
    DESCRIPTION
        "Cisco Firepower compute:Board:operPower managed object property"
    ::= { cfprApComputeBoardEntry 10 }

cfprApComputeBoardOperQualifierReason OBJECT-TYPE
    SYNTAX       SnmpAdminString
    MAX-ACCESS   read-only
    STATUS       current
    DESCRIPTION
        "Cisco Firepower compute:Board:operQualifierReason
        managed object property"
    ::= { cfprApComputeBoardEntry 11 }

cfprApComputeBoardOperState OBJECT-TYPE
    SYNTAX       CfprApEquipmentOperability
    MAX-ACCESS   read-only
    STATUS       current
    DESCRIPTION
        "Cisco Firepower compute:Board:operState managed object property"
    ::= { cfprApComputeBoardEntry 12 }

cfprApComputeBoardOperability OBJECT-TYPE
    SYNTAX       CfprApEquipmentOperability
    MAX-ACCESS   read-only
    STATUS       current
    DESCRIPTION
        "Cisco Firepower compute:Board:operability managed
        object property"
    ::= { cfprApComputeBoardEntry 13 }

cfprApComputeBoardPerf OBJECT-TYPE
    SYNTAX       CfprApEquipmentSensorThresholdStatus
    MAX-ACCESS   read-only
    STATUS       current
    DESCRIPTION
        "Cisco Firepower compute:Board:perf managed object property"
    ::= { cfprApComputeBoardEntry 14 }

cfprApComputeBoardPower OBJECT-TYPE
    SYNTAX       CfprApComputeABoardPower
    MAX-ACCESS   read-only
    STATUS       current
    DESCRIPTION
        "Cisco Firepower compute:Board:power managed object property"
    ::= { cfprApComputeBoardEntry 15 }

cfprApComputeBoardPowerUsage OBJECT-TYPE
    SYNTAX       CfprApEquipmentSensorThresholdStatus
    MAX-ACCESS   read-only
    STATUS       current
    DESCRIPTION
        "Cisco Firepower compute:Board:powerUsage managed object property"
    ::= { cfprApComputeBoardEntry 16 }

cfprApComputeBoardPresence OBJECT-TYPE
    SYNTAX       CfprApEquipmentPresence
    MAX-ACCESS   read-only
    STATUS       current
    DESCRIPTION
        "Cisco Firepower compute:Board:presence managed object property"
    ::= { cfprApComputeBoardEntry 17 }

cfprApComputeBoardRevision OBJECT-TYPE
    SYNTAX       SnmpAdminString
    MAX-ACCESS   read-only
    STATUS       current
    DESCRIPTION
        "Cisco Firepower compute:Board:revision managed object property"
    ::= { cfprApComputeBoardEntry 18 }

cfprApComputeBoardSerial OBJECT-TYPE
    SYNTAX       SnmpAdminString
    MAX-ACCESS   read-only
    STATUS       current
    DESCRIPTION
        "Cisco Firepower compute:Board:serial managed object property"
    ::= { cfprApComputeBoardEntry 19 }

cfprApComputeBoardThermal OBJECT-TYPE
    SYNTAX       CfprApEquipmentSensorThresholdStatus
    MAX-ACCESS   read-only
    STATUS       current
    DESCRIPTION
        "Cisco Firepower compute:Board:thermal managed object property"
    ::= { cfprApComputeBoardEntry 20 }

cfprApComputeBoardVendor OBJECT-TYPE
    SYNTAX       SnmpAdminString
    MAX-ACCESS   read-only
    STATUS       current
    DESCRIPTION
        "Cisco Firepower compute:Board:vendor managed object property"
    ::= { cfprApComputeBoardEntry 21 }

cfprApComputeBoardVoltage OBJECT-TYPE
    SYNTAX       CfprApEquipmentSensorThresholdStatus
    MAX-ACCESS   read-only
    STATUS       current
    DESCRIPTION
        "Cisco Firepower compute:Board:voltage managed object property"
    ::= { cfprApComputeBoardEntry 22 }

cfprApComputeBoardConnectorTable OBJECT-TYPE
    SYNTAX           SEQUENCE OF CfprApComputeBoardConnectorEntry
    MAX-ACCESS       not-accessible
    STATUS           current
    DESCRIPTION
        "Cisco Firepower compute:BoardConnector managed object table"
    ::= { cfprApComputeObjects 9 }

cfprApComputeBoardConnectorEntry OBJECT-TYPE
    SYNTAX           CfprApComputeBoardConnectorEntry
    MAX-ACCESS       not-accessible
    STATUS           current
    DESCRIPTION
        "Entry for the cfprApComputeBoardConnectorTable table."
    INDEX { cfprApComputeBoardConnectorInstanceId }
    ::= { cfprApComputeBoardConnectorTable 1 }

CfprApComputeBoardConnectorEntry ::= SEQUENCE {
    cfprApComputeBoardConnectorInstanceId                            CfprApManagedObjectId,
    cfprApComputeBoardConnectorDn                                    CfprApManagedObjectDn,
    cfprApComputeBoardConnectorRn                                    SnmpAdminString,
    cfprApComputeBoardConnectorBoardConnectorType                    CfprApEquipmentBoardConnectorType,
    cfprApComputeBoardConnectorMasterSlotId                          Gauge32,
    cfprApComputeBoardConnectorSlaveSlotId                           Gauge32
}

cfprApComputeBoardConnectorInstanceId OBJECT-TYPE
    SYNTAX       CfprApManagedObjectId
    MAX-ACCESS   not-accessible
    STATUS       current
    DESCRIPTION
        "Instance identifier of the managed object."
    ::= { cfprApComputeBoardConnectorEntry 1 }

cfprApComputeBoardConnectorDn OBJECT-TYPE
    SYNTAX       CfprApManagedObjectDn
    MAX-ACCESS   read-only
    STATUS       current
    DESCRIPTION
        "Cisco Firepower compute:BoardConnector:dn managed
        object property"
    ::= { cfprApComputeBoardConnectorEntry 2 }

cfprApComputeBoardConnectorRn OBJECT-TYPE
    SYNTAX       SnmpAdminString
    MAX-ACCESS   read-only
    STATUS       current
    DESCRIPTION
        "Cisco Firepower compute:BoardConnector:rn managed
        object property"
    ::= { cfprApComputeBoardConnectorEntry 3 }

cfprApComputeBoardConnectorBoardConnectorType OBJECT-TYPE
    SYNTAX       CfprApEquipmentBoardConnectorType
    MAX-ACCESS   read-only
    STATUS       current
    DESCRIPTION
        "Cisco Firepower compute:BoardConnector:boardConnectorType
        managed object property"
    ::= { cfprApComputeBoardConnectorEntry 4 }

cfprApComputeBoardConnectorMasterSlotId OBJECT-TYPE
    SYNTAX       Gauge32
    MAX-ACCESS   read-only
    STATUS       current
    DESCRIPTION
        "Cisco Firepower compute:BoardConnector:masterSlotId
        managed object property"
    ::= { cfprApComputeBoardConnectorEntry 5 }

cfprApComputeBoardConnectorSlaveSlotId OBJECT-TYPE
    SYNTAX       Gauge32
    MAX-ACCESS   read-only
    STATUS       current
    DESCRIPTION
        "Cisco Firepower compute:BoardConnector:slaveSlotId
        managed object property"
    ::= { cfprApComputeBoardConnectorEntry 6 }

cfprApComputeBoardControllerTable OBJECT-TYPE
    SYNTAX           SEQUENCE OF CfprApComputeBoardControllerEntry
    MAX-ACCESS       not-accessible
    STATUS           current
    DESCRIPTION
        "Cisco Firepower compute:BoardController managed object table"
    ::= { cfprApComputeObjects 10 }

cfprApComputeBoardControllerEntry OBJECT-TYPE
    SYNTAX           CfprApComputeBoardControllerEntry
    MAX-ACCESS       not-accessible
    STATUS           current
    DESCRIPTION
        "Entry for the cfprApComputeBoardControllerTable table."
    INDEX { cfprApComputeBoardControllerInstanceId }
    ::= { cfprApComputeBoardControllerTable 1 }

CfprApComputeBoardControllerEntry ::= SEQUENCE {
    cfprApComputeBoardControllerInstanceId                           CfprApManagedObjectId,
    cfprApComputeBoardControllerDn                                   CfprApManagedObjectDn,
    cfprApComputeBoardControllerRn                                   SnmpAdminString,
    cfprApComputeBoardControllerId                                   Gauge32,
    cfprApComputeBoardControllerLocationDn                           SnmpAdminString,
    cfprApComputeBoardControllerModel                                SnmpAdminString,
    cfprApComputeBoardControllerOperQualifierReason                  SnmpAdminString,
    cfprApComputeBoardControllerOperState                            CfprApEquipmentOperability,
    cfprApComputeBoardControllerOperability                          CfprApEquipmentOperability,
    cfprApComputeBoardControllerPerf                                 CfprApEquipmentSensorThresholdStatus,
    cfprApComputeBoardControllerPower                                CfprApEquipmentPowerState,
    cfprApComputeBoardControllerPresence                             CfprApEquipmentPresence,
    cfprApComputeBoardControllerRevision                             SnmpAdminString,
    cfprApComputeBoardControllerSerial                               SnmpAdminString,
    cfprApComputeBoardControllerThermal                              CfprApEquipmentSensorThresholdStatus,
    cfprApComputeBoardControllerVendor                               SnmpAdminString,
    cfprApComputeBoardControllerVoltage                              CfprApEquipmentSensorThresholdStatus
}

cfprApComputeBoardControllerInstanceId OBJECT-TYPE
    SYNTAX       CfprApManagedObjectId
    MAX-ACCESS   not-accessible
    STATUS       current
    DESCRIPTION
        "Instance identifier of the managed object."
    ::= { cfprApComputeBoardControllerEntry 1 }

cfprApComputeBoardControllerDn OBJECT-TYPE
    SYNTAX       CfprApManagedObjectDn
    MAX-ACCESS   read-only
    STATUS       current
    DESCRIPTION
        "Cisco Firepower compute:BoardController:dn managed
        object property"
    ::= { cfprApComputeBoardControllerEntry 2 }

cfprApComputeBoardControllerRn OBJECT-TYPE
    SYNTAX       SnmpAdminString
    MAX-ACCESS   read-only
    STATUS       current
    DESCRIPTION
        "Cisco Firepower compute:BoardController:rn managed
        object property"
    ::= { cfprApComputeBoardControllerEntry 3 }

cfprApComputeBoardControllerId OBJECT-TYPE
    SYNTAX       Gauge32
    MAX-ACCESS   read-only
    STATUS       current
    DESCRIPTION
        "Cisco Firepower compute:BoardController:id managed
        object property"
    ::= { cfprApComputeBoardControllerEntry 4 }

cfprApComputeBoardControllerLocationDn OBJECT-TYPE
    SYNTAX       SnmpAdminString
    MAX-ACCESS   read-only
    STATUS       current
    DESCRIPTION
        "Cisco Firepower compute:BoardController:locationDn
        managed object property"
    ::= { cfprApComputeBoardControllerEntry 5 }

cfprApComputeBoardControllerModel OBJECT-TYPE
    SYNTAX       SnmpAdminString
    MAX-ACCESS   read-only
    STATUS       current
    DESCRIPTION
        "Cisco Firepower compute:BoardController:model
        managed object property"
    ::= { cfprApComputeBoardControllerEntry 6 }

cfprApComputeBoardControllerOperQualifierReason OBJECT-TYPE
    SYNTAX       SnmpAdminString
    MAX-ACCESS   read-only
    STATUS       current
    DESCRIPTION
        "Cisco Firepower compute:BoardController:operQualifierReason
        managed object property"
    ::= { cfprApComputeBoardControllerEntry 7 }

cfprApComputeBoardControllerOperState OBJECT-TYPE
    SYNTAX       CfprApEquipmentOperability
    MAX-ACCESS   read-only
    STATUS       current
    DESCRIPTION
        "Cisco Firepower compute:BoardController:operState
        managed object property"
    ::= { cfprApComputeBoardControllerEntry 8 }

cfprApComputeBoardControllerOperability OBJECT-TYPE
    SYNTAX       CfprApEquipmentOperability
    MAX-ACCESS   read-only
    STATUS       current
    DESCRIPTION
        "Cisco Firepower compute:BoardController:operability
        managed object property"
    ::= { cfprApComputeBoardControllerEntry 9 }

cfprApComputeBoardControllerPerf OBJECT-TYPE
    SYNTAX       CfprApEquipmentSensorThresholdStatus
    MAX-ACCESS   read-only
    STATUS       current
    DESCRIPTION
        "Cisco Firepower compute:BoardController:perf managed
        object property"
    ::= { cfprApComputeBoardControllerEntry 10 }

cfprApComputeBoardControllerPower OBJECT-TYPE
    SYNTAX       CfprApEquipmentPowerState
    MAX-ACCESS   read-only
    STATUS       current
    DESCRIPTION
        "Cisco Firepower compute:BoardController:power
        managed object property"
    ::= { cfprApComputeBoardControllerEntry 11 }

cfprApComputeBoardControllerPresence OBJECT-TYPE
    SYNTAX       CfprApEquipmentPresence
    MAX-ACCESS   read-only
    STATUS       current
    DESCRIPTION
        "Cisco Firepower compute:BoardController:presence
        managed object property"
    ::= { cfprApComputeBoardControllerEntry 12 }

cfprApComputeBoardControllerRevision OBJECT-TYPE
    SYNTAX       SnmpAdminString
    MAX-ACCESS   read-only
    STATUS       current
    DESCRIPTION
        "Cisco Firepower compute:BoardController:revision
        managed object property"
    ::= { cfprApComputeBoardControllerEntry 13 }

cfprApComputeBoardControllerSerial OBJECT-TYPE
    SYNTAX       SnmpAdminString
    MAX-ACCESS   read-only
    STATUS       current
    DESCRIPTION
        "Cisco Firepower compute:BoardController:serial
        managed object property"
    ::= { cfprApComputeBoardControllerEntry 14 }

cfprApComputeBoardControllerThermal OBJECT-TYPE
    SYNTAX       CfprApEquipmentSensorThresholdStatus
    MAX-ACCESS   read-only
    STATUS       current
    DESCRIPTION
        "Cisco Firepower compute:BoardController:thermal
        managed object property"
    ::= { cfprApComputeBoardControllerEntry 15 }

cfprApComputeBoardControllerVendor OBJECT-TYPE
    SYNTAX       SnmpAdminString
    MAX-ACCESS   read-only
    STATUS       current
    DESCRIPTION
        "Cisco Firepower compute:BoardController:vendor
        managed object property"
    ::= { cfprApComputeBoardControllerEntry 16 }

cfprApComputeBoardControllerVoltage OBJECT-TYPE
    SYNTAX       CfprApEquipmentSensorThresholdStatus
    MAX-ACCESS   read-only
    STATUS       current
    DESCRIPTION
        "Cisco Firepower compute:BoardController:voltage
        managed object property"
    ::= { cfprApComputeBoardControllerEntry 17 }

cfprApComputeChassisConnPolicyTable OBJECT-TYPE
    SYNTAX           SEQUENCE OF CfprApComputeChassisConnPolicyEntry
    MAX-ACCESS       not-accessible
    STATUS           current
    DESCRIPTION
        "Cisco Firepower compute:ChassisConnPolicy managed object table"
    ::= { cfprApComputeObjects 11 }

cfprApComputeChassisConnPolicyEntry OBJECT-TYPE
    SYNTAX           CfprApComputeChassisConnPolicyEntry
    MAX-ACCESS       not-accessible
    STATUS           current
    DESCRIPTION
        "Entry for the cfprApComputeChassisConnPolicyTable table."
    INDEX { cfprApComputeChassisConnPolicyInstanceId }
    ::= { cfprApComputeChassisConnPolicyTable 1 }

CfprApComputeChassisConnPolicyEntry ::= SEQUENCE {
    cfprApComputeChassisConnPolicyInstanceId                         CfprApManagedObjectId,
    cfprApComputeChassisConnPolicyDn                                 CfprApManagedObjectDn,
    cfprApComputeChassisConnPolicyRn                                 SnmpAdminString,
    cfprApComputeChassisConnPolicyAdminState                         CfprApComputeAdminLinkAggregation,
    cfprApComputeChassisConnPolicyChassisId                          CfprApComputeChassisConnPolicyChassisId,
    cfprApComputeChassisConnPolicyDescr                              SnmpAdminString,
    cfprApComputeChassisConnPolicyIntId                              SnmpAdminString,
    cfprApComputeChassisConnPolicyName                               SnmpAdminString,
    cfprApComputeChassisConnPolicyPolicyLevel                        Gauge32,
    cfprApComputeChassisConnPolicyPolicyOwner                        CfprApPolicyPolicyOwner,
    cfprApComputeChassisConnPolicyQualifier                          SnmpAdminString,
    cfprApComputeChassisConnPolicySwitchId                           CfprApNetworkSwitchId
}

cfprApComputeChassisConnPolicyInstanceId OBJECT-TYPE
    SYNTAX       CfprApManagedObjectId
    MAX-ACCESS   not-accessible
    STATUS       current
    DESCRIPTION
        "Instance identifier of the managed object."
    ::= { cfprApComputeChassisConnPolicyEntry 1 }

cfprApComputeChassisConnPolicyDn OBJECT-TYPE
    SYNTAX       CfprApManagedObjectDn
    MAX-ACCESS   read-only
    STATUS       current
    DESCRIPTION
        "Cisco Firepower compute:ChassisConnPolicy:dn managed
        object property"
    ::= { cfprApComputeChassisConnPolicyEntry 2 }

cfprApComputeChassisConnPolicyRn OBJECT-TYPE
    SYNTAX       SnmpAdminString
    MAX-ACCESS   read-only
    STATUS       current
    DESCRIPTION
        "Cisco Firepower compute:ChassisConnPolicy:rn managed
        object property"
    ::= { cfprApComputeChassisConnPolicyEntry 3 }

cfprApComputeChassisConnPolicyAdminState OBJECT-TYPE
    SYNTAX       CfprApComputeAdminLinkAggregation
    MAX-ACCESS   read-only
    STATUS       current
    DESCRIPTION
        "Cisco Firepower compute:ChassisConnPolicy:adminState
        managed object property"
    ::= { cfprApComputeChassisConnPolicyEntry 4 }

cfprApComputeChassisConnPolicyChassisId OBJECT-TYPE
    SYNTAX       CfprApComputeChassisConnPolicyChassisId
    MAX-ACCESS   read-only
    STATUS       current
    DESCRIPTION
        "Cisco Firepower compute:ChassisConnPolicy:chassisId
        managed object property"
    ::= { cfprApComputeChassisConnPolicyEntry 5 }

cfprApComputeChassisConnPolicyDescr OBJECT-TYPE
    SYNTAX       SnmpAdminString
    MAX-ACCESS   read-only
    STATUS       current
    DESCRIPTION
        "Cisco Firepower compute:ChassisConnPolicy:descr
        managed object property"
    ::= { cfprApComputeChassisConnPolicyEntry 6 }

cfprApComputeChassisConnPolicyIntId OBJECT-TYPE
    SYNTAX       SnmpAdminString
    MAX-ACCESS   read-only
    STATUS       current
    DESCRIPTION
        "Cisco Firepower compute:ChassisConnPolicy:intId
        managed object property"
    ::= { cfprApComputeChassisConnPolicyEntry 7 }

cfprApComputeChassisConnPolicyName OBJECT-TYPE
    SYNTAX       SnmpAdminString
    MAX-ACCESS   read-only
    STATUS       current
    DESCRIPTION
        "Cisco Firepower compute:ChassisConnPolicy:name
        managed object property"
    ::= { cfprApComputeChassisConnPolicyEntry 8 }

cfprApComputeChassisConnPolicyPolicyLevel OBJECT-TYPE
    SYNTAX       Gauge32
    MAX-ACCESS   read-only
    STATUS       current
    DESCRIPTION
        "Cisco Firepower compute:ChassisConnPolicy:policyLevel
        managed object property"
    ::= { cfprApComputeChassisConnPolicyEntry 9 }

cfprApComputeChassisConnPolicyPolicyOwner OBJECT-TYPE
    SYNTAX       CfprApPolicyPolicyOwner
    MAX-ACCESS   read-only
    STATUS       current
    DESCRIPTION
        "Cisco Firepower compute:ChassisConnPolicy:policyOwner
        managed object property"
    ::= { cfprApComputeChassisConnPolicyEntry 10 }

cfprApComputeChassisConnPolicyQualifier OBJECT-TYPE
    SYNTAX       SnmpAdminString
    MAX-ACCESS   read-only
    STATUS       current
    DESCRIPTION
        "Cisco Firepower compute:ChassisConnPolicy:qualifier
        managed object property"
    ::= { cfprApComputeChassisConnPolicyEntry 11 }

cfprApComputeChassisConnPolicySwitchId OBJECT-TYPE
    SYNTAX       CfprApNetworkSwitchId
    MAX-ACCESS   read-only
    STATUS       current
    DESCRIPTION
        "Cisco Firepower compute:ChassisConnPolicy:switchId
        managed object property"
    ::= { cfprApComputeChassisConnPolicyEntry 12 }

cfprApComputeChassisDiscPolicyTable OBJECT-TYPE
    SYNTAX           SEQUENCE OF CfprApComputeChassisDiscPolicyEntry
    MAX-ACCESS       not-accessible
    STATUS           current
    DESCRIPTION
        "Cisco Firepower compute:ChassisDiscPolicy managed object table"
    ::= { cfprApComputeObjects 12 }

cfprApComputeChassisDiscPolicyEntry OBJECT-TYPE
    SYNTAX           CfprApComputeChassisDiscPolicyEntry
    MAX-ACCESS       not-accessible
    STATUS           current
    DESCRIPTION
        "Entry for the cfprApComputeChassisDiscPolicyTable table."
    INDEX { cfprApComputeChassisDiscPolicyInstanceId }
    ::= { cfprApComputeChassisDiscPolicyTable 1 }

CfprApComputeChassisDiscPolicyEntry ::= SEQUENCE {
    cfprApComputeChassisDiscPolicyInstanceId                         CfprApManagedObjectId,
    cfprApComputeChassisDiscPolicyDn                                 CfprApManagedObjectDn,
    cfprApComputeChassisDiscPolicyRn                                 SnmpAdminString,
    cfprApComputeChassisDiscPolicyAction                             CfprApComputeChassisDiscAction,
    cfprApComputeChassisDiscPolicyDescr                              SnmpAdminString,
    cfprApComputeChassisDiscPolicyIntId                              SnmpAdminString,
    cfprApComputeChassisDiscPolicyLinkAggregationPref                CfprApComputeLinkAggregation,
    cfprApComputeChassisDiscPolicyName                               SnmpAdminString,
    cfprApComputeChassisDiscPolicyPolicyLevel                        Gauge32,
    cfprApComputeChassisDiscPolicyPolicyOwner                        CfprApPolicyPolicyOwner,
    cfprApComputeChassisDiscPolicyQualifier                          SnmpAdminString,
    cfprApComputeChassisDiscPolicyRebalance                          CfprApComputeConnectivityRebalancing
}

cfprApComputeChassisDiscPolicyInstanceId OBJECT-TYPE
    SYNTAX       CfprApManagedObjectId
    MAX-ACCESS   not-accessible
    STATUS       current
    DESCRIPTION
        "Instance identifier of the managed object."
    ::= { cfprApComputeChassisDiscPolicyEntry 1 }

cfprApComputeChassisDiscPolicyDn OBJECT-TYPE
    SYNTAX       CfprApManagedObjectDn
    MAX-ACCESS   read-only
    STATUS       current
    DESCRIPTION
        "Cisco Firepower compute:ChassisDiscPolicy:dn managed
        object property"
    ::= { cfprApComputeChassisDiscPolicyEntry 2 }

cfprApComputeChassisDiscPolicyRn OBJECT-TYPE
    SYNTAX       SnmpAdminString
    MAX-ACCESS   read-only
    STATUS       current
    DESCRIPTION
        "Cisco Firepower compute:ChassisDiscPolicy:rn managed
        object property"
    ::= { cfprApComputeChassisDiscPolicyEntry 3 }

cfprApComputeChassisDiscPolicyAction OBJECT-TYPE
    SYNTAX       CfprApComputeChassisDiscAction
    MAX-ACCESS   read-only
    STATUS       current
    DESCRIPTION
        "Cisco Firepower compute:ChassisDiscPolicy:action
        managed object property"
    ::= { cfprApComputeChassisDiscPolicyEntry 4 }

cfprApComputeChassisDiscPolicyDescr OBJECT-TYPE
    SYNTAX       SnmpAdminString
    MAX-ACCESS   read-only
    STATUS       current
    DESCRIPTION
        "Cisco Firepower compute:ChassisDiscPolicy:descr
        managed object property"
    ::= { cfprApComputeChassisDiscPolicyEntry 5 }

cfprApComputeChassisDiscPolicyIntId OBJECT-TYPE
    SYNTAX       SnmpAdminString
    MAX-ACCESS   read-only
    STATUS       current
    DESCRIPTION
        "Cisco Firepower compute:ChassisDiscPolicy:intId
        managed object property"
    ::= { cfprApComputeChassisDiscPolicyEntry 6 }

cfprApComputeChassisDiscPolicyLinkAggregationPref OBJECT-TYPE
    SYNTAX       CfprApComputeLinkAggregation
    MAX-ACCESS   read-only
    STATUS       current
    DESCRIPTION
        "Cisco Firepower compute:ChassisDiscPolicy:linkAggregationPref
        managed object property"
    ::= { cfprApComputeChassisDiscPolicyEntry 7 }

cfprApComputeChassisDiscPolicyName OBJECT-TYPE
    SYNTAX       SnmpAdminString
    MAX-ACCESS   read-only
    STATUS       current
    DESCRIPTION
        "Cisco Firepower compute:ChassisDiscPolicy:name
        managed object property"
    ::= { cfprApComputeChassisDiscPolicyEntry 8 }

cfprApComputeChassisDiscPolicyPolicyLevel OBJECT-TYPE
    SYNTAX       Gauge32
    MAX-ACCESS   read-only
    STATUS       current
    DESCRIPTION
        "Cisco Firepower compute:ChassisDiscPolicy:policyLevel
        managed object property"
    ::= { cfprApComputeChassisDiscPolicyEntry 9 }

cfprApComputeChassisDiscPolicyPolicyOwner OBJECT-TYPE
    SYNTAX       CfprApPolicyPolicyOwner
    MAX-ACCESS   read-only
    STATUS       current
    DESCRIPTION
        "Cisco Firepower compute:ChassisDiscPolicy:policyOwner
        managed object property"
    ::= { cfprApComputeChassisDiscPolicyEntry 10 }

cfprApComputeChassisDiscPolicyQualifier OBJECT-TYPE
    SYNTAX       SnmpAdminString
    MAX-ACCESS   read-only
    STATUS       current
    DESCRIPTION
        "Cisco Firepower compute:ChassisDiscPolicy:qualifier
        managed object property"
    ::= { cfprApComputeChassisDiscPolicyEntry 11 }

cfprApComputeChassisDiscPolicyRebalance OBJECT-TYPE
    SYNTAX       CfprApComputeConnectivityRebalancing
    MAX-ACCESS   read-only
    STATUS       current
    DESCRIPTION
        "Cisco Firepower compute:ChassisDiscPolicy:rebalance
        managed object property"
    ::= { cfprApComputeChassisDiscPolicyEntry 12 }

cfprApComputeChassisQualTable OBJECT-TYPE
    SYNTAX           SEQUENCE OF CfprApComputeChassisQualEntry
    MAX-ACCESS       not-accessible
    STATUS           current
    DESCRIPTION
        "Cisco Firepower compute:ChassisQual managed object table"
    ::= { cfprApComputeObjects 13 }

cfprApComputeChassisQualEntry OBJECT-TYPE
    SYNTAX           CfprApComputeChassisQualEntry
    MAX-ACCESS       not-accessible
    STATUS           current
    DESCRIPTION
        "Entry for the cfprApComputeChassisQualTable table."
    INDEX { cfprApComputeChassisQualInstanceId }
    ::= { cfprApComputeChassisQualTable 1 }

CfprApComputeChassisQualEntry ::= SEQUENCE {
    cfprApComputeChassisQualInstanceId                               CfprApManagedObjectId,
    cfprApComputeChassisQualDn                                       CfprApManagedObjectDn,
    cfprApComputeChassisQualRn                                       SnmpAdminString,
    cfprApComputeChassisQualMaxId                                    CfprApComputeChassisQualMaxId,
    cfprApComputeChassisQualMinId                                    CfprApComputeChassisQualMinId
}

cfprApComputeChassisQualInstanceId OBJECT-TYPE
    SYNTAX       CfprApManagedObjectId
    MAX-ACCESS   not-accessible
    STATUS       current
    DESCRIPTION
        "Instance identifier of the managed object."
    ::= { cfprApComputeChassisQualEntry 1 }

cfprApComputeChassisQualDn OBJECT-TYPE
    SYNTAX       CfprApManagedObjectDn
    MAX-ACCESS   read-only
    STATUS       current
    DESCRIPTION
        "Cisco Firepower compute:ChassisQual:dn managed object property"
    ::= { cfprApComputeChassisQualEntry 2 }

cfprApComputeChassisQualRn OBJECT-TYPE
    SYNTAX       SnmpAdminString
    MAX-ACCESS   read-only
    STATUS       current
    DESCRIPTION
        "Cisco Firepower compute:ChassisQual:rn managed object property"
    ::= { cfprApComputeChassisQualEntry 3 }

cfprApComputeChassisQualMaxId OBJECT-TYPE
    SYNTAX       CfprApComputeChassisQualMaxId
    MAX-ACCESS   read-only
    STATUS       current
    DESCRIPTION
        "Cisco Firepower compute:ChassisQual:maxId managed
        object property"
    ::= { cfprApComputeChassisQualEntry 4 }

cfprApComputeChassisQualMinId OBJECT-TYPE
    SYNTAX       CfprApComputeChassisQualMinId
    MAX-ACCESS   read-only
    STATUS       current
    DESCRIPTION
        "Cisco Firepower compute:ChassisQual:minId managed
        object property"
    ::= { cfprApComputeChassisQualEntry 5 }

cfprApComputeDefaultsTable OBJECT-TYPE
    SYNTAX           SEQUENCE OF CfprApComputeDefaultsEntry
    MAX-ACCESS       not-accessible
    STATUS           current
    DESCRIPTION
        "Cisco Firepower compute:Defaults managed object table"
    ::= { cfprApComputeObjects 14 }

cfprApComputeDefaultsEntry OBJECT-TYPE
    SYNTAX           CfprApComputeDefaultsEntry
    MAX-ACCESS       not-accessible
    STATUS           current
    DESCRIPTION
        "Entry for the cfprApComputeDefaultsTable table."
    INDEX { cfprApComputeDefaultsInstanceId }
    ::= { cfprApComputeDefaultsTable 1 }

CfprApComputeDefaultsEntry ::= SEQUENCE {
    cfprApComputeDefaultsInstanceId                                  CfprApManagedObjectId,
    cfprApComputeDefaultsDn                                          CfprApManagedObjectDn,
    cfprApComputeDefaultsRn                                          SnmpAdminString
}

cfprApComputeDefaultsInstanceId OBJECT-TYPE
    SYNTAX       CfprApManagedObjectId
    MAX-ACCESS   not-accessible
    STATUS       current
    DESCRIPTION
        "Instance identifier of the managed object."
    ::= { cfprApComputeDefaultsEntry 1 }

cfprApComputeDefaultsDn OBJECT-TYPE
    SYNTAX       CfprApManagedObjectDn
    MAX-ACCESS   read-only
    STATUS       current
    DESCRIPTION
        "Cisco Firepower compute:Defaults:dn managed object property"
    ::= { cfprApComputeDefaultsEntry 2 }

cfprApComputeDefaultsRn OBJECT-TYPE
    SYNTAX       SnmpAdminString
    MAX-ACCESS   read-only
    STATUS       current
    DESCRIPTION
        "Cisco Firepower compute:Defaults:rn managed object property"
    ::= { cfprApComputeDefaultsEntry 3 }

cfprApComputeExtBoardTable OBJECT-TYPE
    SYNTAX           SEQUENCE OF CfprApComputeExtBoardEntry
    MAX-ACCESS       not-accessible
    STATUS           current
    DESCRIPTION
        "Cisco Firepower compute:ExtBoard managed object table"
    ::= { cfprApComputeObjects 15 }

cfprApComputeExtBoardEntry OBJECT-TYPE
    SYNTAX           CfprApComputeExtBoardEntry
    MAX-ACCESS       not-accessible
    STATUS           current
    DESCRIPTION
        "Entry for the cfprApComputeExtBoardTable table."
    INDEX { cfprApComputeExtBoardInstanceId }
    ::= { cfprApComputeExtBoardTable 1 }

CfprApComputeExtBoardEntry ::= SEQUENCE {
    cfprApComputeExtBoardInstanceId                                  CfprApManagedObjectId,
    cfprApComputeExtBoardDn                                          CfprApManagedObjectDn,
    cfprApComputeExtBoardRn                                          SnmpAdminString,
    cfprApComputeExtBoardBoardAggregationRole                        CfprApEquipmentBoardAggregationRole,
    cfprApComputeExtBoardChassisId                                   Gauge32,
    cfprApComputeExtBoardCmosVoltage                                 CfprApEquipmentSensorThresholdStatus,
    cfprApComputeExtBoardConnPath                                    CfprApEquipmentConnectionStatus,
    cfprApComputeExtBoardConnStatus                                  CfprApEquipmentConnectionStatus,
    cfprApComputeExtBoardFaultQualifier                              SnmpAdminString,
    cfprApComputeExtBoardId                                          Gauge32,
    cfprApComputeExtBoardLocationDn                                  SnmpAdminString,
    cfprApComputeExtBoardManagingInst                                CfprApNetworkSwitchId,
    cfprApComputeExtBoardModel                                       SnmpAdminString,
    cfprApComputeExtBoardOperPower                                   CfprApEquipmentPowerState,
    cfprApComputeExtBoardOperQualifierReason                         SnmpAdminString,
    cfprApComputeExtBoardOperState                                   CfprApEquipmentOperability,
    cfprApComputeExtBoardOperability                                 CfprApEquipmentOperability,
    cfprApComputeExtBoardPerf                                        CfprApEquipmentSensorThresholdStatus,
    cfprApComputeExtBoardPower                                       CfprApComputeABoardPower,
    cfprApComputeExtBoardPowerUsage                                  CfprApEquipmentSensorThresholdStatus,
    cfprApComputeExtBoardPresence                                    CfprApEquipmentPresence,
    cfprApComputeExtBoardRevision                                    SnmpAdminString,
    cfprApComputeExtBoardSerial                                      SnmpAdminString,
    cfprApComputeExtBoardSlotId                                      Gauge32,
    cfprApComputeExtBoardThermal                                     CfprApEquipmentSensorThresholdStatus,
    cfprApComputeExtBoardVendor                                      SnmpAdminString,
    cfprApComputeExtBoardVoltage                                     CfprApEquipmentSensorThresholdStatus
}

cfprApComputeExtBoardInstanceId OBJECT-TYPE
    SYNTAX       CfprApManagedObjectId
    MAX-ACCESS   not-accessible
    STATUS       current
    DESCRIPTION
        "Instance identifier of the managed object."
    ::= { cfprApComputeExtBoardEntry 1 }

cfprApComputeExtBoardDn OBJECT-TYPE
    SYNTAX       CfprApManagedObjectDn
    MAX-ACCESS   read-only
    STATUS       current
    DESCRIPTION
        "Cisco Firepower compute:ExtBoard:dn managed object property"
    ::= { cfprApComputeExtBoardEntry 2 }

cfprApComputeExtBoardRn OBJECT-TYPE
    SYNTAX       SnmpAdminString
    MAX-ACCESS   read-only
    STATUS       current
    DESCRIPTION
        "Cisco Firepower compute:ExtBoard:rn managed object property"
    ::= { cfprApComputeExtBoardEntry 3 }

cfprApComputeExtBoardBoardAggregationRole OBJECT-TYPE
    SYNTAX       CfprApEquipmentBoardAggregationRole
    MAX-ACCESS   read-only
    STATUS       current
    DESCRIPTION
        "Cisco Firepower compute:ExtBoard:boardAggregationRole
        managed object property"
    ::= { cfprApComputeExtBoardEntry 4 }

cfprApComputeExtBoardChassisId OBJECT-TYPE
    SYNTAX       Gauge32
    MAX-ACCESS   read-only
    STATUS       current
    DESCRIPTION
        "Cisco Firepower compute:ExtBoard:chassisId managed
        object property"
    ::= { cfprApComputeExtBoardEntry 5 }

cfprApComputeExtBoardCmosVoltage OBJECT-TYPE
    SYNTAX       CfprApEquipmentSensorThresholdStatus
    MAX-ACCESS   read-only
    STATUS       current
    DESCRIPTION
        "Cisco Firepower compute:ExtBoard:cmosVoltage managed
        object property"
    ::= { cfprApComputeExtBoardEntry 6 }

cfprApComputeExtBoardConnPath OBJECT-TYPE
    SYNTAX       CfprApEquipmentConnectionStatus
    MAX-ACCESS   read-only
    STATUS       current
    DESCRIPTION
        "Cisco Firepower compute:ExtBoard:connPath managed
        object property"
    ::= { cfprApComputeExtBoardEntry 7 }

cfprApComputeExtBoardConnStatus OBJECT-TYPE
    SYNTAX       CfprApEquipmentConnectionStatus
    MAX-ACCESS   read-only
    STATUS       current
    DESCRIPTION
        "Cisco Firepower compute:ExtBoard:connStatus managed
        object property"
    ::= { cfprApComputeExtBoardEntry 8 }

cfprApComputeExtBoardFaultQualifier OBJECT-TYPE
    SYNTAX       SnmpAdminString
    MAX-ACCESS   read-only
    STATUS       current
    DESCRIPTION
        "Cisco Firepower compute:ExtBoard:faultQualifier
        managed object property"
    ::= { cfprApComputeExtBoardEntry 9 }

cfprApComputeExtBoardId OBJECT-TYPE
    SYNTAX       Gauge32
    MAX-ACCESS   read-only
    STATUS       current
    DESCRIPTION
        "Cisco Firepower compute:ExtBoard:id managed object property"
    ::= { cfprApComputeExtBoardEntry 10 }

cfprApComputeExtBoardLocationDn OBJECT-TYPE
    SYNTAX       SnmpAdminString
    MAX-ACCESS   read-only
    STATUS       current
    DESCRIPTION
        "Cisco Firepower compute:ExtBoard:locationDn managed
        object property"
    ::= { cfprApComputeExtBoardEntry 11 }

cfprApComputeExtBoardManagingInst OBJECT-TYPE
    SYNTAX       CfprApNetworkSwitchId
    MAX-ACCESS   read-only
    STATUS       current
    DESCRIPTION
        "Cisco Firepower compute:ExtBoard:managingInst
        managed object property"
    ::= { cfprApComputeExtBoardEntry 12 }

cfprApComputeExtBoardModel OBJECT-TYPE
    SYNTAX       SnmpAdminString
    MAX-ACCESS   read-only
    STATUS       current
    DESCRIPTION
        "Cisco Firepower compute:ExtBoard:model managed object property"
    ::= { cfprApComputeExtBoardEntry 13 }

cfprApComputeExtBoardOperPower OBJECT-TYPE
    SYNTAX       CfprApEquipmentPowerState
    MAX-ACCESS   read-only
    STATUS       current
    DESCRIPTION
        "Cisco Firepower compute:ExtBoard:operPower managed
        object property"
    ::= { cfprApComputeExtBoardEntry 14 }

cfprApComputeExtBoardOperQualifierReason OBJECT-TYPE
    SYNTAX       SnmpAdminString
    MAX-ACCESS   read-only
    STATUS       current
    DESCRIPTION
        "Cisco Firepower compute:ExtBoard:operQualifierReason
        managed object property"
    ::= { cfprApComputeExtBoardEntry 15 }

cfprApComputeExtBoardOperState OBJECT-TYPE
    SYNTAX       CfprApEquipmentOperability
    MAX-ACCESS   read-only
    STATUS       current
    DESCRIPTION
        "Cisco Firepower compute:ExtBoard:operState managed
        object property"
    ::= { cfprApComputeExtBoardEntry 16 }

cfprApComputeExtBoardOperability OBJECT-TYPE
    SYNTAX       CfprApEquipmentOperability
    MAX-ACCESS   read-only
    STATUS       current
    DESCRIPTION
        "Cisco Firepower compute:ExtBoard:operability managed
        object property"
    ::= { cfprApComputeExtBoardEntry 17 }

cfprApComputeExtBoardPerf OBJECT-TYPE
    SYNTAX       CfprApEquipmentSensorThresholdStatus
    MAX-ACCESS   read-only
    STATUS       current
    DESCRIPTION
        "Cisco Firepower compute:ExtBoard:perf managed object property"
    ::= { cfprApComputeExtBoardEntry 18 }

cfprApComputeExtBoardPower OBJECT-TYPE
    SYNTAX       CfprApComputeABoardPower
    MAX-ACCESS   read-only
    STATUS       current
    DESCRIPTION
        "Cisco Firepower compute:ExtBoard:power managed object property"
    ::= { cfprApComputeExtBoardEntry 19 }

cfprApComputeExtBoardPowerUsage OBJECT-TYPE
    SYNTAX       CfprApEquipmentSensorThresholdStatus
    MAX-ACCESS   read-only
    STATUS       current
    DESCRIPTION
        "Cisco Firepower compute:ExtBoard:powerUsage managed
        object property"
    ::= { cfprApComputeExtBoardEntry 20 }

cfprApComputeExtBoardPresence OBJECT-TYPE
    SYNTAX       CfprApEquipmentPresence
    MAX-ACCESS   read-only
    STATUS       current
    DESCRIPTION
        "Cisco Firepower compute:ExtBoard:presence managed
        object property"
    ::= { cfprApComputeExtBoardEntry 21 }

cfprApComputeExtBoardRevision OBJECT-TYPE
    SYNTAX       SnmpAdminString
    MAX-ACCESS   read-only
    STATUS       current
    DESCRIPTION
        "Cisco Firepower compute:ExtBoard:revision managed
        object property"
    ::= { cfprApComputeExtBoardEntry 22 }

cfprApComputeExtBoardSerial OBJECT-TYPE
    SYNTAX       SnmpAdminString
    MAX-ACCESS   read-only
    STATUS       current
    DESCRIPTION
        "Cisco Firepower compute:ExtBoard:serial managed object property"
    ::= { cfprApComputeExtBoardEntry 23 }

cfprApComputeExtBoardSlotId OBJECT-TYPE
    SYNTAX       Gauge32
    MAX-ACCESS   read-only
    STATUS       current
    DESCRIPTION
        "Cisco Firepower compute:ExtBoard:slotId managed object property"
    ::= { cfprApComputeExtBoardEntry 24 }

cfprApComputeExtBoardThermal OBJECT-TYPE
    SYNTAX       CfprApEquipmentSensorThresholdStatus
    MAX-ACCESS   read-only
    STATUS       current
    DESCRIPTION
        "Cisco Firepower compute:ExtBoard:thermal managed object property"
    ::= { cfprApComputeExtBoardEntry 25 }

cfprApComputeExtBoardVendor OBJECT-TYPE
    SYNTAX       SnmpAdminString
    MAX-ACCESS   read-only
    STATUS       current
    DESCRIPTION
        "Cisco Firepower compute:ExtBoard:vendor managed object property"
    ::= { cfprApComputeExtBoardEntry 26 }

cfprApComputeExtBoardVoltage OBJECT-TYPE
    SYNTAX       CfprApEquipmentSensorThresholdStatus
    MAX-ACCESS   read-only
    STATUS       current
    DESCRIPTION
        "Cisco Firepower compute:ExtBoard:voltage managed object property"
    ::= { cfprApComputeExtBoardEntry 27 }

cfprApComputeFwSyncAckTable OBJECT-TYPE
    SYNTAX           SEQUENCE OF CfprApComputeFwSyncAckEntry
    MAX-ACCESS       not-accessible
    STATUS           current
    DESCRIPTION
        "Cisco Firepower compute:FwSyncAck managed object table"
    ::= { cfprApComputeObjects 16 }

cfprApComputeFwSyncAckEntry OBJECT-TYPE
    SYNTAX           CfprApComputeFwSyncAckEntry
    MAX-ACCESS       not-accessible
    STATUS           current
    DESCRIPTION
        "Entry for the cfprApComputeFwSyncAckTable table."
    INDEX { cfprApComputeFwSyncAckInstanceId }
    ::= { cfprApComputeFwSyncAckTable 1 }

CfprApComputeFwSyncAckEntry ::= SEQUENCE {
    cfprApComputeFwSyncAckInstanceId                                 CfprApManagedObjectId,
    cfprApComputeFwSyncAckDn                                         CfprApManagedObjectDn,
    cfprApComputeFwSyncAckRn                                         SnmpAdminString,
    cfprApComputeFwSyncAckAcked                                      DateAndTime,
    cfprApComputeFwSyncAckAckedBy                                    SnmpAdminString,
    cfprApComputeFwSyncAckAdminState                                 CfprApTrigAdminState,
    cfprApComputeFwSyncAckAutoDelete                                 TruthValue,
    cfprApComputeFwSyncAckChangeBy                                   SnmpAdminString,
    cfprApComputeFwSyncAckChangeDetails                              CfprApTrigAckChangeDetails,
    cfprApComputeFwSyncAckChanges                                    CfprApTrigAckChanges,
    cfprApComputeFwSyncAckDescr                                      SnmpAdminString,
    cfprApComputeFwSyncAckDisr                                       CfprApTrigAckDisr,
    cfprApComputeFwSyncAckIgnoreCap                                  TruthValue,
    cfprApComputeFwSyncAckIntId                                      SnmpAdminString,
    cfprApComputeFwSyncAckModified                                   DateAndTime,
    cfprApComputeFwSyncAckName                                       SnmpAdminString,
    cfprApComputeFwSyncAckOperScheduler                              SnmpAdminString,
    cfprApComputeFwSyncAckOperState                                  CfprApTrigAckOperState,
    cfprApComputeFwSyncAckPolicyLevel                                Gauge32,
    cfprApComputeFwSyncAckPolicyOwner                                CfprApPolicyPolicyOwner,
    cfprApComputeFwSyncAckPrevOperState                              CfprApTrigAckPrevOperState,
    cfprApComputeFwSyncAckScheduler                                  SnmpAdminString
}

cfprApComputeFwSyncAckInstanceId OBJECT-TYPE
    SYNTAX       CfprApManagedObjectId
    MAX-ACCESS   not-accessible
    STATUS       current
    DESCRIPTION
        "Instance identifier of the managed object."
    ::= { cfprApComputeFwSyncAckEntry 1 }

cfprApComputeFwSyncAckDn OBJECT-TYPE
    SYNTAX       CfprApManagedObjectDn
    MAX-ACCESS   read-only
    STATUS       current
    DESCRIPTION
        "Cisco Firepower compute:FwSyncAck:dn managed object property"
    ::= { cfprApComputeFwSyncAckEntry 2 }

cfprApComputeFwSyncAckRn OBJECT-TYPE
    SYNTAX       SnmpAdminString
    MAX-ACCESS   read-only
    STATUS       current
    DESCRIPTION
        "Cisco Firepower compute:FwSyncAck:rn managed object property"
    ::= { cfprApComputeFwSyncAckEntry 3 }

cfprApComputeFwSyncAckAcked OBJECT-TYPE
    SYNTAX       DateAndTime
    MAX-ACCESS   read-only
    STATUS       current
    DESCRIPTION
        "Cisco Firepower compute:FwSyncAck:acked managed object property"
    ::= { cfprApComputeFwSyncAckEntry 4 }

cfprApComputeFwSyncAckAckedBy OBJECT-TYPE
    SYNTAX       SnmpAdminString
    MAX-ACCESS   read-only
    STATUS       current
    DESCRIPTION
        "Cisco Firepower compute:FwSyncAck:ackedBy managed
        object property"
    ::= { cfprApComputeFwSyncAckEntry 5 }

cfprApComputeFwSyncAckAdminState OBJECT-TYPE
    SYNTAX       CfprApTrigAdminState
    MAX-ACCESS   read-only
    STATUS       current
    DESCRIPTION
        "Cisco Firepower compute:FwSyncAck:adminState managed
        object property"
    ::= { cfprApComputeFwSyncAckEntry 6 }

cfprApComputeFwSyncAckAutoDelete OBJECT-TYPE
    SYNTAX       TruthValue
    MAX-ACCESS   read-only
    STATUS       current
    DESCRIPTION
        "Cisco Firepower compute:FwSyncAck:autoDelete managed
        object property"
    ::= { cfprApComputeFwSyncAckEntry 7 }

cfprApComputeFwSyncAckChangeBy OBJECT-TYPE
    SYNTAX       SnmpAdminString
    MAX-ACCESS   read-only
    STATUS       current
    DESCRIPTION
        "Cisco Firepower compute:FwSyncAck:changeBy managed
        object property"
    ::= { cfprApComputeFwSyncAckEntry 8 }

cfprApComputeFwSyncAckChangeDetails OBJECT-TYPE
    SYNTAX       CfprApTrigAckChangeDetails
    MAX-ACCESS   read-only
    STATUS       current
    DESCRIPTION
        "Cisco Firepower compute:FwSyncAck:changeDetails
        managed object property"
    ::= { cfprApComputeFwSyncAckEntry 9 }

cfprApComputeFwSyncAckChanges OBJECT-TYPE
    SYNTAX       CfprApTrigAckChanges
    MAX-ACCESS   read-only
    STATUS       current
    DESCRIPTION
        "Cisco Firepower compute:FwSyncAck:changes managed
        object property"
    ::= { cfprApComputeFwSyncAckEntry 10 }

cfprApComputeFwSyncAckDescr OBJECT-TYPE
    SYNTAX       SnmpAdminString
    MAX-ACCESS   read-only
    STATUS       current
    DESCRIPTION
        "Cisco Firepower compute:FwSyncAck:descr managed object property"
    ::= { cfprApComputeFwSyncAckEntry 11 }

cfprApComputeFwSyncAckDisr OBJECT-TYPE
    SYNTAX       CfprApTrigAckDisr
    MAX-ACCESS   read-only
    STATUS       current
    DESCRIPTION
        "Cisco Firepower compute:FwSyncAck:disr managed object property"
    ::= { cfprApComputeFwSyncAckEntry 12 }

cfprApComputeFwSyncAckIgnoreCap OBJECT-TYPE
    SYNTAX       TruthValue
    MAX-ACCESS   read-only
    STATUS       current
    DESCRIPTION
        "Cisco Firepower compute:FwSyncAck:ignoreCap managed
        object property"
    ::= { cfprApComputeFwSyncAckEntry 13 }

cfprApComputeFwSyncAckIntId OBJECT-TYPE
    SYNTAX       SnmpAdminString
    MAX-ACCESS   read-only
    STATUS       current
    DESCRIPTION
        "Cisco Firepower compute:FwSyncAck:intId managed object property"
    ::= { cfprApComputeFwSyncAckEntry 14 }

cfprApComputeFwSyncAckModified OBJECT-TYPE
    SYNTAX       DateAndTime
    MAX-ACCESS   read-only
    STATUS       current
    DESCRIPTION
        "Cisco Firepower compute:FwSyncAck:modified managed
        object property"
    ::= { cfprApComputeFwSyncAckEntry 15 }

cfprApComputeFwSyncAckName OBJECT-TYPE
    SYNTAX       SnmpAdminString
    MAX-ACCESS   read-only
    STATUS       current
    DESCRIPTION
        "Cisco Firepower compute:FwSyncAck:name managed object property"
    ::= { cfprApComputeFwSyncAckEntry 16 }

cfprApComputeFwSyncAckOperScheduler OBJECT-TYPE
    SYNTAX       SnmpAdminString
    MAX-ACCESS   read-only
    STATUS       current
    DESCRIPTION
        "Cisco Firepower compute:FwSyncAck:operScheduler
        managed object property"
    ::= { cfprApComputeFwSyncAckEntry 17 }

cfprApComputeFwSyncAckOperState OBJECT-TYPE
    SYNTAX       CfprApTrigAckOperState
    MAX-ACCESS   read-only
    STATUS       current
    DESCRIPTION
        "Cisco Firepower compute:FwSyncAck:operState managed
        object property"
    ::= { cfprApComputeFwSyncAckEntry 18 }

cfprApComputeFwSyncAckPolicyLevel OBJECT-TYPE
    SYNTAX       Gauge32
    MAX-ACCESS   read-only
    STATUS       current
    DESCRIPTION
        "Cisco Firepower compute:FwSyncAck:policyLevel
        managed object property"
    ::= { cfprApComputeFwSyncAckEntry 19 }

cfprApComputeFwSyncAckPolicyOwner OBJECT-TYPE
    SYNTAX       CfprApPolicyPolicyOwner
    MAX-ACCESS   read-only
    STATUS       current
    DESCRIPTION
        "Cisco Firepower compute:FwSyncAck:policyOwner
        managed object property"
    ::= { cfprApComputeFwSyncAckEntry 20 }

cfprApComputeFwSyncAckPrevOperState OBJECT-TYPE
    SYNTAX       CfprApTrigAckPrevOperState
    MAX-ACCESS   read-only
    STATUS       current
    DESCRIPTION
        "Cisco Firepower compute:FwSyncAck:prevOperState
        managed object property"
    ::= { cfprApComputeFwSyncAckEntry 21 }

cfprApComputeFwSyncAckScheduler OBJECT-TYPE
    SYNTAX       SnmpAdminString
    MAX-ACCESS   read-only
    STATUS       current
    DESCRIPTION
        "Cisco Firepower compute:FwSyncAck:scheduler managed
        object property"
    ::= { cfprApComputeFwSyncAckEntry 22 }

cfprApComputeHealthLedSensorAlarmTable OBJECT-TYPE
    SYNTAX           SEQUENCE OF CfprApComputeHealthLedSensorAlarmEntry
    MAX-ACCESS       not-accessible
    STATUS           current
    DESCRIPTION
        "Cisco Firepower compute:HealthLedSensorAlarm managed
        object table"
    ::= { cfprApComputeObjects 17 }

cfprApComputeHealthLedSensorAlarmEntry OBJECT-TYPE
    SYNTAX           CfprApComputeHealthLedSensorAlarmEntry
    MAX-ACCESS       not-accessible
    STATUS           current
    DESCRIPTION
        "Entry for the cfprApComputeHealthLedSensorAlarmTable table."
    INDEX { cfprApComputeHealthLedSensorAlarmInstanceId }
    ::= { cfprApComputeHealthLedSensorAlarmTable 1 }

CfprApComputeHealthLedSensorAlarmEntry ::= SEQUENCE {
    cfprApComputeHealthLedSensorAlarmInstanceId                      CfprApManagedObjectId,
    cfprApComputeHealthLedSensorAlarmDn                              CfprApManagedObjectDn,
    cfprApComputeHealthLedSensorAlarmRn                              SnmpAdminString,
    cfprApComputeHealthLedSensorAlarmAlarmDesc                       SnmpAdminString,
    cfprApComputeHealthLedSensorAlarmAlarmSeverity                   CfprApComputeAlarmSeverity,
    cfprApComputeHealthLedSensorAlarmSensorId                        Gauge32,
    cfprApComputeHealthLedSensorAlarmSensorName                      SnmpAdminString
}

cfprApComputeHealthLedSensorAlarmInstanceId OBJECT-TYPE
    SYNTAX       CfprApManagedObjectId
    MAX-ACCESS   not-accessible
    STATUS       current
    DESCRIPTION
        "Instance identifier of the managed object."
    ::= { cfprApComputeHealthLedSensorAlarmEntry 1 }

cfprApComputeHealthLedSensorAlarmDn OBJECT-TYPE
    SYNTAX       CfprApManagedObjectDn
    MAX-ACCESS   read-only
    STATUS       current
    DESCRIPTION
        "Cisco Firepower compute:HealthLedSensorAlarm:dn
        managed object property"
    ::= { cfprApComputeHealthLedSensorAlarmEntry 2 }

cfprApComputeHealthLedSensorAlarmRn OBJECT-TYPE
    SYNTAX       SnmpAdminString
    MAX-ACCESS   read-only
    STATUS       current
    DESCRIPTION
        "Cisco Firepower compute:HealthLedSensorAlarm:rn
        managed object property"
    ::= { cfprApComputeHealthLedSensorAlarmEntry 3 }

cfprApComputeHealthLedSensorAlarmAlarmDesc OBJECT-TYPE
    SYNTAX       SnmpAdminString
    MAX-ACCESS   read-only
    STATUS       current
    DESCRIPTION
        "Cisco Firepower compute:HealthLedSensorAlarm:alarmDesc
        managed object property"
    ::= { cfprApComputeHealthLedSensorAlarmEntry 4 }

cfprApComputeHealthLedSensorAlarmAlarmSeverity OBJECT-TYPE
    SYNTAX       CfprApComputeAlarmSeverity
    MAX-ACCESS   read-only
    STATUS       current
    DESCRIPTION
        "Cisco Firepower compute:HealthLedSensorAlarm:alarmSeverity
        managed object property"
    ::= { cfprApComputeHealthLedSensorAlarmEntry 5 }

cfprApComputeHealthLedSensorAlarmSensorId OBJECT-TYPE
    SYNTAX       Gauge32
    MAX-ACCESS   read-only
    STATUS       current
    DESCRIPTION
        "Cisco Firepower compute:HealthLedSensorAlarm:sensorId
        managed object property"
    ::= { cfprApComputeHealthLedSensorAlarmEntry 6 }

cfprApComputeHealthLedSensorAlarmSensorName OBJECT-TYPE
    SYNTAX       SnmpAdminString
    MAX-ACCESS   read-only
    STATUS       current
    DESCRIPTION
        "Cisco Firepower compute:HealthLedSensorAlarm:sensorName
        managed object property"
    ::= { cfprApComputeHealthLedSensorAlarmEntry 7 }

cfprApComputeIOHubTable OBJECT-TYPE
    SYNTAX           SEQUENCE OF CfprApComputeIOHubEntry
    MAX-ACCESS       not-accessible
    STATUS           current
    DESCRIPTION
        "Cisco Firepower compute:IOHub managed object table"
    ::= { cfprApComputeObjects 18 }

cfprApComputeIOHubEntry OBJECT-TYPE
    SYNTAX           CfprApComputeIOHubEntry
    MAX-ACCESS       not-accessible
    STATUS           current
    DESCRIPTION
        "Entry for the cfprApComputeIOHubTable table."
    INDEX { cfprApComputeIOHubInstanceId }
    ::= { cfprApComputeIOHubTable 1 }

CfprApComputeIOHubEntry ::= SEQUENCE {
    cfprApComputeIOHubInstanceId                                     CfprApManagedObjectId,
    cfprApComputeIOHubDn                                             CfprApManagedObjectDn,
    cfprApComputeIOHubRn                                             SnmpAdminString,
    cfprApComputeIOHubId                                             Gauge32,
    cfprApComputeIOHubLocationDn                                     SnmpAdminString,
    cfprApComputeIOHubModel                                          SnmpAdminString,
    cfprApComputeIOHubOperQualifierReason                            SnmpAdminString,
    cfprApComputeIOHubOperState                                      CfprApEquipmentOperability,
    cfprApComputeIOHubOperability                                    CfprApEquipmentOperability,
    cfprApComputeIOHubPerf                                           CfprApEquipmentSensorThresholdStatus,
    cfprApComputeIOHubPower                                          CfprApEquipmentPowerState,
    cfprApComputeIOHubPresence                                       CfprApEquipmentPresence,
    cfprApComputeIOHubRevision                                       SnmpAdminString,
    cfprApComputeIOHubSerial                                         SnmpAdminString,
    cfprApComputeIOHubThermal                                        CfprApEquipmentSensorThresholdStatus,
    cfprApComputeIOHubVendor                                         SnmpAdminString,
    cfprApComputeIOHubVoltage                                        CfprApEquipmentSensorThresholdStatus
}

cfprApComputeIOHubInstanceId OBJECT-TYPE
    SYNTAX       CfprApManagedObjectId
    MAX-ACCESS   not-accessible
    STATUS       current
    DESCRIPTION
        "Instance identifier of the managed object."
    ::= { cfprApComputeIOHubEntry 1 }

cfprApComputeIOHubDn OBJECT-TYPE
    SYNTAX       CfprApManagedObjectDn
    MAX-ACCESS   read-only
    STATUS       current
    DESCRIPTION
        "Cisco Firepower compute:IOHub:dn managed object property"
    ::= { cfprApComputeIOHubEntry 2 }

cfprApComputeIOHubRn OBJECT-TYPE
    SYNTAX       SnmpAdminString
    MAX-ACCESS   read-only
    STATUS       current
    DESCRIPTION
        "Cisco Firepower compute:IOHub:rn managed object property"
    ::= { cfprApComputeIOHubEntry 3 }

cfprApComputeIOHubId OBJECT-TYPE
    SYNTAX       Gauge32
    MAX-ACCESS   read-only
    STATUS       current
    DESCRIPTION
        "Cisco Firepower compute:IOHub:id managed object property"
    ::= { cfprApComputeIOHubEntry 4 }

cfprApComputeIOHubLocationDn OBJECT-TYPE
    SYNTAX       SnmpAdminString
    MAX-ACCESS   read-only
    STATUS       current
    DESCRIPTION
        "Cisco Firepower compute:IOHub:locationDn managed object property"
    ::= { cfprApComputeIOHubEntry 5 }

cfprApComputeIOHubModel OBJECT-TYPE
    SYNTAX       SnmpAdminString
    MAX-ACCESS   read-only
    STATUS       current
    DESCRIPTION
        "Cisco Firepower compute:IOHub:model managed object property"
    ::= { cfprApComputeIOHubEntry 6 }

cfprApComputeIOHubOperQualifierReason OBJECT-TYPE
    SYNTAX       SnmpAdminString
    MAX-ACCESS   read-only
    STATUS       current
    DESCRIPTION
        "Cisco Firepower compute:IOHub:operQualifierReason
        managed object property"
    ::= { cfprApComputeIOHubEntry 7 }

cfprApComputeIOHubOperState OBJECT-TYPE
    SYNTAX       CfprApEquipmentOperability
    MAX-ACCESS   read-only
    STATUS       current
    DESCRIPTION
        "Cisco Firepower compute:IOHub:operState managed object property"
    ::= { cfprApComputeIOHubEntry 8 }

cfprApComputeIOHubOperability OBJECT-TYPE
    SYNTAX       CfprApEquipmentOperability
    MAX-ACCESS   read-only
    STATUS       current
    DESCRIPTION
        "Cisco Firepower compute:IOHub:operability managed
        object property"
    ::= { cfprApComputeIOHubEntry 9 }

cfprApComputeIOHubPerf OBJECT-TYPE
    SYNTAX       CfprApEquipmentSensorThresholdStatus
    MAX-ACCESS   read-only
    STATUS       current
    DESCRIPTION
        "Cisco Firepower compute:IOHub:perf managed object property"
    ::= { cfprApComputeIOHubEntry 10 }

cfprApComputeIOHubPower OBJECT-TYPE
    SYNTAX       CfprApEquipmentPowerState
    MAX-ACCESS   read-only
    STATUS       current
    DESCRIPTION
        "Cisco Firepower compute:IOHub:power managed object property"
    ::= { cfprApComputeIOHubEntry 11 }

cfprApComputeIOHubPresence OBJECT-TYPE
    SYNTAX       CfprApEquipmentPresence
    MAX-ACCESS   read-only
    STATUS       current
    DESCRIPTION
        "Cisco Firepower compute:IOHub:presence managed object property"
    ::= { cfprApComputeIOHubEntry 12 }

cfprApComputeIOHubRevision OBJECT-TYPE
    SYNTAX       SnmpAdminString
    MAX-ACCESS   read-only
    STATUS       current
    DESCRIPTION
        "Cisco Firepower compute:IOHub:revision managed object property"
    ::= { cfprApComputeIOHubEntry 13 }

cfprApComputeIOHubSerial OBJECT-TYPE
    SYNTAX       SnmpAdminString
    MAX-ACCESS   read-only
    STATUS       current
    DESCRIPTION
        "Cisco Firepower compute:IOHub:serial managed object property"
    ::= { cfprApComputeIOHubEntry 14 }

cfprApComputeIOHubThermal OBJECT-TYPE
    SYNTAX       CfprApEquipmentSensorThresholdStatus
    MAX-ACCESS   read-only
    STATUS       current
    DESCRIPTION
        "Cisco Firepower compute:IOHub:thermal managed object property"
    ::= { cfprApComputeIOHubEntry 15 }

cfprApComputeIOHubVendor OBJECT-TYPE
    SYNTAX       SnmpAdminString
    MAX-ACCESS   read-only
    STATUS       current
    DESCRIPTION
        "Cisco Firepower compute:IOHub:vendor managed object property"
    ::= { cfprApComputeIOHubEntry 16 }

cfprApComputeIOHubVoltage OBJECT-TYPE
    SYNTAX       CfprApEquipmentSensorThresholdStatus
    MAX-ACCESS   read-only
    STATUS       current
    DESCRIPTION
        "Cisco Firepower compute:IOHub:voltage managed object property"
    ::= { cfprApComputeIOHubEntry 17 }

cfprApComputeIOHubEnvStatsTable OBJECT-TYPE
    SYNTAX           SEQUENCE OF CfprApComputeIOHubEnvStatsEntry
    MAX-ACCESS       not-accessible
    STATUS           current
    DESCRIPTION
        "Cisco Firepower compute:IOHubEnvStats managed object table"
    ::= { cfprApComputeObjects 19 }

cfprApComputeIOHubEnvStatsEntry OBJECT-TYPE
    SYNTAX           CfprApComputeIOHubEnvStatsEntry
    MAX-ACCESS       not-accessible
    STATUS           current
    DESCRIPTION
        "Entry for the cfprApComputeIOHubEnvStatsTable table."
    INDEX { cfprApComputeIOHubEnvStatsInstanceId }
    ::= { cfprApComputeIOHubEnvStatsTable 1 }

CfprApComputeIOHubEnvStatsEntry ::= SEQUENCE {
    cfprApComputeIOHubEnvStatsInstanceId                             CfprApManagedObjectId,
    cfprApComputeIOHubEnvStatsDn                                     CfprApManagedObjectDn,
    cfprApComputeIOHubEnvStatsRn                                     SnmpAdminString,
    cfprApComputeIOHubEnvStatsIntervals                              Gauge32,
    cfprApComputeIOHubEnvStatsSuspect                                TruthValue,
    cfprApComputeIOHubEnvStatsTemperature                            INTEGER,
    cfprApComputeIOHubEnvStatsTemperatureAvg                         INTEGER,
    cfprApComputeIOHubEnvStatsTemperatureMax                         INTEGER,
    cfprApComputeIOHubEnvStatsTemperatureMin                         INTEGER,
    cfprApComputeIOHubEnvStatsThresholded                            CfprApComputeIOHubEnvStatsThresholded,
    cfprApComputeIOHubEnvStatsTimeCollected                          DateAndTime,
    cfprApComputeIOHubEnvStatsUpdate                                 Gauge32
}

cfprApComputeIOHubEnvStatsInstanceId OBJECT-TYPE
    SYNTAX       CfprApManagedObjectId
    MAX-ACCESS   not-accessible
    STATUS       current
    DESCRIPTION
        "Instance identifier of the managed object."
    ::= { cfprApComputeIOHubEnvStatsEntry 1 }

cfprApComputeIOHubEnvStatsDn OBJECT-TYPE
    SYNTAX       CfprApManagedObjectDn
    MAX-ACCESS   read-only
    STATUS       current
    DESCRIPTION
        "Cisco Firepower compute:IOHubEnvStats:dn managed object property"
    ::= { cfprApComputeIOHubEnvStatsEntry 2 }

cfprApComputeIOHubEnvStatsRn OBJECT-TYPE
    SYNTAX       SnmpAdminString
    MAX-ACCESS   read-only
    STATUS       current
    DESCRIPTION
        "Cisco Firepower compute:IOHubEnvStats:rn managed object property"
    ::= { cfprApComputeIOHubEnvStatsEntry 3 }

cfprApComputeIOHubEnvStatsIntervals OBJECT-TYPE
    SYNTAX       Gauge32
    MAX-ACCESS   read-only
    STATUS       current
    DESCRIPTION
        "Cisco Firepower compute:IOHubEnvStats:intervals
        managed object property"
    ::= { cfprApComputeIOHubEnvStatsEntry 4 }

cfprApComputeIOHubEnvStatsSuspect OBJECT-TYPE
    SYNTAX       TruthValue
    MAX-ACCESS   read-only
    STATUS       current
    DESCRIPTION
        "Cisco Firepower compute:IOHubEnvStats:suspect
        managed object property"
    ::= { cfprApComputeIOHubEnvStatsEntry 5 }

cfprApComputeIOHubEnvStatsTemperature OBJECT-TYPE
    SYNTAX       INTEGER
    MAX-ACCESS   read-only
    STATUS       current
    DESCRIPTION
        "Cisco Firepower compute:IOHubEnvStats:temperature
        managed object property"
    ::= { cfprApComputeIOHubEnvStatsEntry 6 }

cfprApComputeIOHubEnvStatsTemperatureAvg OBJECT-TYPE
    SYNTAX       INTEGER
    MAX-ACCESS   read-only
    STATUS       current
    DESCRIPTION
        "Cisco Firepower compute:IOHubEnvStats:temperatureAvg
        managed object property"
    ::= { cfprApComputeIOHubEnvStatsEntry 7 }

cfprApComputeIOHubEnvStatsTemperatureMax OBJECT-TYPE
    SYNTAX       INTEGER
    MAX-ACCESS   read-only
    STATUS       current
    DESCRIPTION
        "Cisco Firepower compute:IOHubEnvStats:temperatureMax
        managed object property"
    ::= { cfprApComputeIOHubEnvStatsEntry 8 }

cfprApComputeIOHubEnvStatsTemperatureMin OBJECT-TYPE
    SYNTAX       INTEGER
    MAX-ACCESS   read-only
    STATUS       current
    DESCRIPTION
        "Cisco Firepower compute:IOHubEnvStats:temperatureMin
        managed object property"
    ::= { cfprApComputeIOHubEnvStatsEntry 9 }

cfprApComputeIOHubEnvStatsThresholded OBJECT-TYPE
    SYNTAX       CfprApComputeIOHubEnvStatsThresholded
    MAX-ACCESS   read-only
    STATUS       current
    DESCRIPTION
        "Cisco Firepower compute:IOHubEnvStats:thresholded
        managed object property"
    ::= { cfprApComputeIOHubEnvStatsEntry 10 }

cfprApComputeIOHubEnvStatsTimeCollected OBJECT-TYPE
    SYNTAX       DateAndTime
    MAX-ACCESS   read-only
    STATUS       current
    DESCRIPTION
        "Cisco Firepower compute:IOHubEnvStats:timeCollected
        managed object property"
    ::= { cfprApComputeIOHubEnvStatsEntry 11 }

cfprApComputeIOHubEnvStatsUpdate OBJECT-TYPE
    SYNTAX       Gauge32
    MAX-ACCESS   read-only
    STATUS       current
    DESCRIPTION
        "Cisco Firepower compute:IOHubEnvStats:update managed
        object property"
    ::= { cfprApComputeIOHubEnvStatsEntry 12 }

cfprApComputeIOHubEnvStatsHistTable OBJECT-TYPE
    SYNTAX           SEQUENCE OF CfprApComputeIOHubEnvStatsHistEntry
    MAX-ACCESS       not-accessible
    STATUS           current
    DESCRIPTION
        "Cisco Firepower compute:IOHubEnvStatsHist managed object table"
    ::= { cfprApComputeObjects 20 }

cfprApComputeIOHubEnvStatsHistEntry OBJECT-TYPE
    SYNTAX           CfprApComputeIOHubEnvStatsHistEntry
    MAX-ACCESS       not-accessible
    STATUS           current
    DESCRIPTION
        "Entry for the cfprApComputeIOHubEnvStatsHistTable table."
    INDEX { cfprApComputeIOHubEnvStatsHistInstanceId }
    ::= { cfprApComputeIOHubEnvStatsHistTable 1 }

CfprApComputeIOHubEnvStatsHistEntry ::= SEQUENCE {
    cfprApComputeIOHubEnvStatsHistInstanceId                         CfprApManagedObjectId,
    cfprApComputeIOHubEnvStatsHistDn                                 CfprApManagedObjectDn,
    cfprApComputeIOHubEnvStatsHistRn                                 SnmpAdminString,
    cfprApComputeIOHubEnvStatsHistId                                 Unsigned64,
    cfprApComputeIOHubEnvStatsHistMostRecent                         TruthValue,
    cfprApComputeIOHubEnvStatsHistSuspect                            TruthValue,
    cfprApComputeIOHubEnvStatsHistTemperature                        INTEGER,
    cfprApComputeIOHubEnvStatsHistTemperatureAvg                     INTEGER,
    cfprApComputeIOHubEnvStatsHistTemperatureMax                     INTEGER,
    cfprApComputeIOHubEnvStatsHistTemperatureMin                     INTEGER,
    cfprApComputeIOHubEnvStatsHistThresholded                        CfprApComputeIOHubEnvStatsHistThresholded,
    cfprApComputeIOHubEnvStatsHistTimeCollected                      DateAndTime
}

cfprApComputeIOHubEnvStatsHistInstanceId OBJECT-TYPE
    SYNTAX       CfprApManagedObjectId
    MAX-ACCESS   not-accessible
    STATUS       current
    DESCRIPTION
        "Instance identifier of the managed object."
    ::= { cfprApComputeIOHubEnvStatsHistEntry 1 }

cfprApComputeIOHubEnvStatsHistDn OBJECT-TYPE
    SYNTAX       CfprApManagedObjectDn
    MAX-ACCESS   read-only
    STATUS       current
    DESCRIPTION
        "Cisco Firepower compute:IOHubEnvStatsHist:dn managed
        object property"
    ::= { cfprApComputeIOHubEnvStatsHistEntry 2 }

cfprApComputeIOHubEnvStatsHistRn OBJECT-TYPE
    SYNTAX       SnmpAdminString
    MAX-ACCESS   read-only
    STATUS       current
    DESCRIPTION
        "Cisco Firepower compute:IOHubEnvStatsHist:rn managed
        object property"
    ::= { cfprApComputeIOHubEnvStatsHistEntry 3 }

cfprApComputeIOHubEnvStatsHistId OBJECT-TYPE
    SYNTAX       Unsigned64
    MAX-ACCESS   read-only
    STATUS       current
    DESCRIPTION
        "Cisco Firepower compute:IOHubEnvStatsHist:id managed
        object property"
    ::= { cfprApComputeIOHubEnvStatsHistEntry 4 }

cfprApComputeIOHubEnvStatsHistMostRecent OBJECT-TYPE
    SYNTAX       TruthValue
    MAX-ACCESS   read-only
    STATUS       current
    DESCRIPTION
        "Cisco Firepower compute:IOHubEnvStatsHist:mostRecent
        managed object property"
    ::= { cfprApComputeIOHubEnvStatsHistEntry 5 }

cfprApComputeIOHubEnvStatsHistSuspect OBJECT-TYPE
    SYNTAX       TruthValue
    MAX-ACCESS   read-only
    STATUS       current
    DESCRIPTION
        "Cisco Firepower compute:IOHubEnvStatsHist:suspect
        managed object property"
    ::= { cfprApComputeIOHubEnvStatsHistEntry 6 }

cfprApComputeIOHubEnvStatsHistTemperature OBJECT-TYPE
    SYNTAX       INTEGER
    MAX-ACCESS   read-only
    STATUS       current
    DESCRIPTION
        "Cisco Firepower compute:IOHubEnvStatsHist:temperature
        managed object property"
    ::= { cfprApComputeIOHubEnvStatsHistEntry 7 }

cfprApComputeIOHubEnvStatsHistTemperatureAvg OBJECT-TYPE
    SYNTAX       INTEGER
    MAX-ACCESS   read-only
    STATUS       current
    DESCRIPTION
        "Cisco Firepower compute:IOHubEnvStatsHist:temperatureAvg
        managed object property"
    ::= { cfprApComputeIOHubEnvStatsHistEntry 8 }

cfprApComputeIOHubEnvStatsHistTemperatureMax OBJECT-TYPE
    SYNTAX       INTEGER
    MAX-ACCESS   read-only
    STATUS       current
    DESCRIPTION
        "Cisco Firepower compute:IOHubEnvStatsHist:temperatureMax
        managed object property"
    ::= { cfprApComputeIOHubEnvStatsHistEntry 9 }

cfprApComputeIOHubEnvStatsHistTemperatureMin OBJECT-TYPE
    SYNTAX       INTEGER
    MAX-ACCESS   read-only
    STATUS       current
    DESCRIPTION
        "Cisco Firepower compute:IOHubEnvStatsHist:temperatureMin
        managed object property"
    ::= { cfprApComputeIOHubEnvStatsHistEntry 10 }

cfprApComputeIOHubEnvStatsHistThresholded OBJECT-TYPE
    SYNTAX       CfprApComputeIOHubEnvStatsHistThresholded
    MAX-ACCESS   read-only
    STATUS       current
    DESCRIPTION
        "Cisco Firepower compute:IOHubEnvStatsHist:thresholded
        managed object property"
    ::= { cfprApComputeIOHubEnvStatsHistEntry 11 }

cfprApComputeIOHubEnvStatsHistTimeCollected OBJECT-TYPE
    SYNTAX       DateAndTime
    MAX-ACCESS   read-only
    STATUS       current
    DESCRIPTION
        "Cisco Firepower compute:IOHubEnvStatsHist:timeCollected
        managed object property"
    ::= { cfprApComputeIOHubEnvStatsHistEntry 12 }

cfprApComputeMbPowerStatsTable OBJECT-TYPE
    SYNTAX           SEQUENCE OF CfprApComputeMbPowerStatsEntry
    MAX-ACCESS       not-accessible
    STATUS           current
    DESCRIPTION
        "Cisco Firepower compute:MbPowerStats managed object table"
    ::= { cfprApComputeObjects 22 }

cfprApComputeMbPowerStatsEntry OBJECT-TYPE
    SYNTAX           CfprApComputeMbPowerStatsEntry
    MAX-ACCESS       not-accessible
    STATUS           current
    DESCRIPTION
        "Entry for the cfprApComputeMbPowerStatsTable table."
    INDEX { cfprApComputeMbPowerStatsInstanceId }
    ::= { cfprApComputeMbPowerStatsTable 1 }

CfprApComputeMbPowerStatsEntry ::= SEQUENCE {
    cfprApComputeMbPowerStatsInstanceId                              CfprApManagedObjectId,
    cfprApComputeMbPowerStatsDn                                      CfprApManagedObjectDn,
    cfprApComputeMbPowerStatsRn                                      SnmpAdminString,
    cfprApComputeMbPowerStatsConsumedPower                           INTEGER,
    cfprApComputeMbPowerStatsConsumedPowerAvg                        INTEGER,
    cfprApComputeMbPowerStatsConsumedPowerMax                        INTEGER,
    cfprApComputeMbPowerStatsConsumedPowerMin                        INTEGER,
    cfprApComputeMbPowerStatsInputCurrent                            INTEGER,
    cfprApComputeMbPowerStatsInputCurrentAvg                         INTEGER,
    cfprApComputeMbPowerStatsInputCurrentMax                         INTEGER,
    cfprApComputeMbPowerStatsInputCurrentMin                         INTEGER,
    cfprApComputeMbPowerStatsInputVoltage                            INTEGER,
    cfprApComputeMbPowerStatsInputVoltageAvg                         INTEGER,
    cfprApComputeMbPowerStatsInputVoltageMax                         INTEGER,
    cfprApComputeMbPowerStatsInputVoltageMin                         INTEGER,
    cfprApComputeMbPowerStatsIntervals                               Gauge32,
    cfprApComputeMbPowerStatsSuspect                                 TruthValue,
    cfprApComputeMbPowerStatsThresholded                             CfprApComputeMbPowerStatsThresholded,
    cfprApComputeMbPowerStatsTimeCollected                           DateAndTime,
    cfprApComputeMbPowerStatsUpdate                                  Gauge32
}

cfprApComputeMbPowerStatsInstanceId OBJECT-TYPE
    SYNTAX       CfprApManagedObjectId
    MAX-ACCESS   not-accessible
    STATUS       current
    DESCRIPTION
        "Instance identifier of the managed object."
    ::= { cfprApComputeMbPowerStatsEntry 1 }

cfprApComputeMbPowerStatsDn OBJECT-TYPE
    SYNTAX       CfprApManagedObjectDn
    MAX-ACCESS   read-only
    STATUS       current
    DESCRIPTION
        "Cisco Firepower compute:MbPowerStats:dn managed object property"
    ::= { cfprApComputeMbPowerStatsEntry 2 }

cfprApComputeMbPowerStatsRn OBJECT-TYPE
    SYNTAX       SnmpAdminString
    MAX-ACCESS   read-only
    STATUS       current
    DESCRIPTION
        "Cisco Firepower compute:MbPowerStats:rn managed object property"
    ::= { cfprApComputeMbPowerStatsEntry 3 }

cfprApComputeMbPowerStatsConsumedPower OBJECT-TYPE
    SYNTAX       INTEGER
    MAX-ACCESS   read-only
    STATUS       current
    DESCRIPTION
        "Cisco Firepower compute:MbPowerStats:consumedPower
        managed object property"
    ::= { cfprApComputeMbPowerStatsEntry 4 }

cfprApComputeMbPowerStatsConsumedPowerAvg OBJECT-TYPE
    SYNTAX       INTEGER
    MAX-ACCESS   read-only
    STATUS       current
    DESCRIPTION
        "Cisco Firepower compute:MbPowerStats:consumedPowerAvg
        managed object property"
    ::= { cfprApComputeMbPowerStatsEntry 5 }

cfprApComputeMbPowerStatsConsumedPowerMax OBJECT-TYPE
    SYNTAX       INTEGER
    MAX-ACCESS   read-only
    STATUS       current
    DESCRIPTION
        "Cisco Firepower compute:MbPowerStats:consumedPowerMax
        managed object property"
    ::= { cfprApComputeMbPowerStatsEntry 6 }

cfprApComputeMbPowerStatsConsumedPowerMin OBJECT-TYPE
    SYNTAX       INTEGER
    MAX-ACCESS   read-only
    STATUS       current
    DESCRIPTION
        "Cisco Firepower compute:MbPowerStats:consumedPowerMin
        managed object property"
    ::= { cfprApComputeMbPowerStatsEntry 7 }

cfprApComputeMbPowerStatsInputCurrent OBJECT-TYPE
    SYNTAX       INTEGER
    MAX-ACCESS   read-only
    STATUS       current
    DESCRIPTION
        "Cisco Firepower compute:MbPowerStats:inputCurrent
        managed object property"
    ::= { cfprApComputeMbPowerStatsEntry 8 }

cfprApComputeMbPowerStatsInputCurrentAvg OBJECT-TYPE
    SYNTAX       INTEGER
    MAX-ACCESS   read-only
    STATUS       current
    DESCRIPTION
        "Cisco Firepower compute:MbPowerStats:inputCurrentAvg
        managed object property"
    ::= { cfprApComputeMbPowerStatsEntry 9 }

cfprApComputeMbPowerStatsInputCurrentMax OBJECT-TYPE
    SYNTAX       INTEGER
    MAX-ACCESS   read-only
    STATUS       current
    DESCRIPTION
        "Cisco Firepower compute:MbPowerStats:inputCurrentMax
        managed object property"
    ::= { cfprApComputeMbPowerStatsEntry 10 }

cfprApComputeMbPowerStatsInputCurrentMin OBJECT-TYPE
    SYNTAX       INTEGER
    MAX-ACCESS   read-only
    STATUS       current
    DESCRIPTION
        "Cisco Firepower compute:MbPowerStats:inputCurrentMin
        managed object property"
    ::= { cfprApComputeMbPowerStatsEntry 11 }

cfprApComputeMbPowerStatsInputVoltage OBJECT-TYPE
    SYNTAX       INTEGER
    MAX-ACCESS   read-only
    STATUS       current
    DESCRIPTION
        "Cisco Firepower compute:MbPowerStats:inputVoltage
        managed object property"
    ::= { cfprApComputeMbPowerStatsEntry 12 }

cfprApComputeMbPowerStatsInputVoltageAvg OBJECT-TYPE
    SYNTAX       INTEGER
    MAX-ACCESS   read-only
    STATUS       current
    DESCRIPTION
        "Cisco Firepower compute:MbPowerStats:inputVoltageAvg
        managed object property"
    ::= { cfprApComputeMbPowerStatsEntry 13 }

cfprApComputeMbPowerStatsInputVoltageMax OBJECT-TYPE
    SYNTAX       INTEGER
    MAX-ACCESS   read-only
    STATUS       current
    DESCRIPTION
        "Cisco Firepower compute:MbPowerStats:inputVoltageMax
        managed object property"
    ::= { cfprApComputeMbPowerStatsEntry 14 }

cfprApComputeMbPowerStatsInputVoltageMin OBJECT-TYPE
    SYNTAX       INTEGER
    MAX-ACCESS   read-only
    STATUS       current
    DESCRIPTION
        "Cisco Firepower compute:MbPowerStats:inputVoltageMin
        managed object property"
    ::= { cfprApComputeMbPowerStatsEntry 15 }

cfprApComputeMbPowerStatsIntervals OBJECT-TYPE
    SYNTAX       Gauge32
    MAX-ACCESS   read-only
    STATUS       current
    DESCRIPTION
        "Cisco Firepower compute:MbPowerStats:intervals
        managed object property"
    ::= { cfprApComputeMbPowerStatsEntry 16 }

cfprApComputeMbPowerStatsSuspect OBJECT-TYPE
    SYNTAX       TruthValue
    MAX-ACCESS   read-only
    STATUS       current
    DESCRIPTION
        "Cisco Firepower compute:MbPowerStats:suspect managed
        object property"
    ::= { cfprApComputeMbPowerStatsEntry 17 }

cfprApComputeMbPowerStatsThresholded OBJECT-TYPE
    SYNTAX       CfprApComputeMbPowerStatsThresholded
    MAX-ACCESS   read-only
    STATUS       current
    DESCRIPTION
        "Cisco Firepower compute:MbPowerStats:thresholded
        managed object property"
    ::= { cfprApComputeMbPowerStatsEntry 18 }

cfprApComputeMbPowerStatsTimeCollected OBJECT-TYPE
    SYNTAX       DateAndTime
    MAX-ACCESS   read-only
    STATUS       current
    DESCRIPTION
        "Cisco Firepower compute:MbPowerStats:timeCollected
        managed object property"
    ::= { cfprApComputeMbPowerStatsEntry 19 }

cfprApComputeMbPowerStatsUpdate OBJECT-TYPE
    SYNTAX       Gauge32
    MAX-ACCESS   read-only
    STATUS       current
    DESCRIPTION
        "Cisco Firepower compute:MbPowerStats:update managed
        object property"
    ::= { cfprApComputeMbPowerStatsEntry 20 }

cfprApComputeMbPowerStatsHistTable OBJECT-TYPE
    SYNTAX           SEQUENCE OF CfprApComputeMbPowerStatsHistEntry
    MAX-ACCESS       not-accessible
    STATUS           current
    DESCRIPTION
        "Cisco Firepower compute:MbPowerStatsHist managed object table"
    ::= { cfprApComputeObjects 23 }

cfprApComputeMbPowerStatsHistEntry OBJECT-TYPE
    SYNTAX           CfprApComputeMbPowerStatsHistEntry
    MAX-ACCESS       not-accessible
    STATUS           current
    DESCRIPTION
        "Entry for the cfprApComputeMbPowerStatsHistTable table."
    INDEX { cfprApComputeMbPowerStatsHistInstanceId }
    ::= { cfprApComputeMbPowerStatsHistTable 1 }

CfprApComputeMbPowerStatsHistEntry ::= SEQUENCE {
    cfprApComputeMbPowerStatsHistInstanceId                          CfprApManagedObjectId,
    cfprApComputeMbPowerStatsHistDn                                  CfprApManagedObjectDn,
    cfprApComputeMbPowerStatsHistRn                                  SnmpAdminString,
    cfprApComputeMbPowerStatsHistConsumedPower                       INTEGER,
    cfprApComputeMbPowerStatsHistConsumedPowerAvg                    INTEGER,
    cfprApComputeMbPowerStatsHistConsumedPowerMax                    INTEGER,
    cfprApComputeMbPowerStatsHistConsumedPowerMin                    INTEGER,
    cfprApComputeMbPowerStatsHistId                                  Unsigned64,
    cfprApComputeMbPowerStatsHistInputCurrent                        INTEGER,
    cfprApComputeMbPowerStatsHistInputCurrentAvg                     INTEGER,
    cfprApComputeMbPowerStatsHistInputCurrentMax                     INTEGER,
    cfprApComputeMbPowerStatsHistInputCurrentMin                     INTEGER,
    cfprApComputeMbPowerStatsHistInputVoltage                        INTEGER,
    cfprApComputeMbPowerStatsHistInputVoltageAvg                     INTEGER,
    cfprApComputeMbPowerStatsHistInputVoltageMax                     INTEGER,
    cfprApComputeMbPowerStatsHistInputVoltageMin                     INTEGER,
    cfprApComputeMbPowerStatsHistMostRecent                          TruthValue,
    cfprApComputeMbPowerStatsHistSuspect                             TruthValue,
    cfprApComputeMbPowerStatsHistThresholded                         CfprApComputeMbPowerStatsHistThresholded,
    cfprApComputeMbPowerStatsHistTimeCollected                       DateAndTime
}

cfprApComputeMbPowerStatsHistInstanceId OBJECT-TYPE
    SYNTAX       CfprApManagedObjectId
    MAX-ACCESS   not-accessible
    STATUS       current
    DESCRIPTION
        "Instance identifier of the managed object."
    ::= { cfprApComputeMbPowerStatsHistEntry 1 }

cfprApComputeMbPowerStatsHistDn OBJECT-TYPE
    SYNTAX       CfprApManagedObjectDn
    MAX-ACCESS   read-only
    STATUS       current
    DESCRIPTION
        "Cisco Firepower compute:MbPowerStatsHist:dn managed
        object property"
    ::= { cfprApComputeMbPowerStatsHistEntry 2 }

cfprApComputeMbPowerStatsHistRn OBJECT-TYPE
    SYNTAX       SnmpAdminString
    MAX-ACCESS   read-only
    STATUS       current
    DESCRIPTION
        "Cisco Firepower compute:MbPowerStatsHist:rn managed
        object property"
    ::= { cfprApComputeMbPowerStatsHistEntry 3 }

cfprApComputeMbPowerStatsHistConsumedPower OBJECT-TYPE
    SYNTAX       INTEGER
    MAX-ACCESS   read-only
    STATUS       current
    DESCRIPTION
        "Cisco Firepower compute:MbPowerStatsHist:consumedPower
        managed object property"
    ::= { cfprApComputeMbPowerStatsHistEntry 4 }

cfprApComputeMbPowerStatsHistConsumedPowerAvg OBJECT-TYPE
    SYNTAX       INTEGER
    MAX-ACCESS   read-only
    STATUS       current
    DESCRIPTION
        "Cisco Firepower compute:MbPowerStatsHist:consumedPowerAvg
        managed object property"
    ::= { cfprApComputeMbPowerStatsHistEntry 5 }

cfprApComputeMbPowerStatsHistConsumedPowerMax OBJECT-TYPE
    SYNTAX       INTEGER
    MAX-ACCESS   read-only
    STATUS       current
    DESCRIPTION
        "Cisco Firepower compute:MbPowerStatsHist:consumedPowerMax
        managed object property"
    ::= { cfprApComputeMbPowerStatsHistEntry 6 }

cfprApComputeMbPowerStatsHistConsumedPowerMin OBJECT-TYPE
    SYNTAX       INTEGER
    MAX-ACCESS   read-only
    STATUS       current
    DESCRIPTION
        "Cisco Firepower compute:MbPowerStatsHist:consumedPowerMin
        managed object property"
    ::= { cfprApComputeMbPowerStatsHistEntry 7 }

cfprApComputeMbPowerStatsHistId OBJECT-TYPE
    SYNTAX       Unsigned64
    MAX-ACCESS   read-only
    STATUS       current
    DESCRIPTION
        "Cisco Firepower compute:MbPowerStatsHist:id managed
        object property"
    ::= { cfprApComputeMbPowerStatsHistEntry 8 }

cfprApComputeMbPowerStatsHistInputCurrent OBJECT-TYPE
    SYNTAX       INTEGER
    MAX-ACCESS   read-only
    STATUS       current
    DESCRIPTION
        "Cisco Firepower compute:MbPowerStatsHist:inputCurrent
        managed object property"
    ::= { cfprApComputeMbPowerStatsHistEntry 9 }

cfprApComputeMbPowerStatsHistInputCurrentAvg OBJECT-TYPE
    SYNTAX       INTEGER
    MAX-ACCESS   read-only
    STATUS       current
    DESCRIPTION
        "Cisco Firepower compute:MbPowerStatsHist:inputCurrentAvg
        managed object property"
    ::= { cfprApComputeMbPowerStatsHistEntry 10 }

cfprApComputeMbPowerStatsHistInputCurrentMax OBJECT-TYPE
    SYNTAX       INTEGER
    MAX-ACCESS   read-only
    STATUS       current
    DESCRIPTION
        "Cisco Firepower compute:MbPowerStatsHist:inputCurrentMax
        managed object property"
    ::= { cfprApComputeMbPowerStatsHistEntry 11 }

cfprApComputeMbPowerStatsHistInputCurrentMin OBJECT-TYPE
    SYNTAX       INTEGER
    MAX-ACCESS   read-only
    STATUS       current
    DESCRIPTION
        "Cisco Firepower compute:MbPowerStatsHist:inputCurrentMin
        managed object property"
    ::= { cfprApComputeMbPowerStatsHistEntry 12 }

cfprApComputeMbPowerStatsHistInputVoltage OBJECT-TYPE
    SYNTAX       INTEGER
    MAX-ACCESS   read-only
    STATUS       current
    DESCRIPTION
        "Cisco Firepower compute:MbPowerStatsHist:inputVoltage
        managed object property"
    ::= { cfprApComputeMbPowerStatsHistEntry 13 }

cfprApComputeMbPowerStatsHistInputVoltageAvg OBJECT-TYPE
    SYNTAX       INTEGER
    MAX-ACCESS   read-only
    STATUS       current
    DESCRIPTION
        "Cisco Firepower compute:MbPowerStatsHist:inputVoltageAvg
        managed object property"
    ::= { cfprApComputeMbPowerStatsHistEntry 14 }

cfprApComputeMbPowerStatsHistInputVoltageMax OBJECT-TYPE
    SYNTAX       INTEGER
    MAX-ACCESS   read-only
    STATUS       current
    DESCRIPTION
        "Cisco Firepower compute:MbPowerStatsHist:inputVoltageMax
        managed object property"
    ::= { cfprApComputeMbPowerStatsHistEntry 15 }

cfprApComputeMbPowerStatsHistInputVoltageMin OBJECT-TYPE
    SYNTAX       INTEGER
    MAX-ACCESS   read-only
    STATUS       current
    DESCRIPTION
        "Cisco Firepower compute:MbPowerStatsHist:inputVoltageMin
        managed object property"
    ::= { cfprApComputeMbPowerStatsHistEntry 16 }

cfprApComputeMbPowerStatsHistMostRecent OBJECT-TYPE
    SYNTAX       TruthValue
    MAX-ACCESS   read-only
    STATUS       current
    DESCRIPTION
        "Cisco Firepower compute:MbPowerStatsHist:mostRecent
        managed object property"
    ::= { cfprApComputeMbPowerStatsHistEntry 17 }

cfprApComputeMbPowerStatsHistSuspect OBJECT-TYPE
    SYNTAX       TruthValue
    MAX-ACCESS   read-only
    STATUS       current
    DESCRIPTION
        "Cisco Firepower compute:MbPowerStatsHist:suspect
        managed object property"
    ::= { cfprApComputeMbPowerStatsHistEntry 18 }

cfprApComputeMbPowerStatsHistThresholded OBJECT-TYPE
    SYNTAX       CfprApComputeMbPowerStatsHistThresholded
    MAX-ACCESS   read-only
    STATUS       current
    DESCRIPTION
        "Cisco Firepower compute:MbPowerStatsHist:thresholded
        managed object property"
    ::= { cfprApComputeMbPowerStatsHistEntry 19 }

cfprApComputeMbPowerStatsHistTimeCollected OBJECT-TYPE
    SYNTAX       DateAndTime
    MAX-ACCESS   read-only
    STATUS       current
    DESCRIPTION
        "Cisco Firepower compute:MbPowerStatsHist:timeCollected
        managed object property"
    ::= { cfprApComputeMbPowerStatsHistEntry 20 }

cfprApComputeMbTempStatsTable OBJECT-TYPE
    SYNTAX           SEQUENCE OF CfprApComputeMbTempStatsEntry
    MAX-ACCESS       not-accessible
    STATUS           current
    DESCRIPTION
        "Cisco Firepower compute:MbTempStats managed object table"
    ::= { cfprApComputeObjects 24 }

cfprApComputeMbTempStatsEntry OBJECT-TYPE
    SYNTAX           CfprApComputeMbTempStatsEntry
    MAX-ACCESS       not-accessible
    STATUS           current
    DESCRIPTION
        "Entry for the cfprApComputeMbTempStatsTable table."
    INDEX { cfprApComputeMbTempStatsInstanceId }
    ::= { cfprApComputeMbTempStatsTable 1 }

CfprApComputeMbTempStatsEntry ::= SEQUENCE {
    cfprApComputeMbTempStatsInstanceId                               CfprApManagedObjectId,
    cfprApComputeMbTempStatsDn                                       CfprApManagedObjectDn,
    cfprApComputeMbTempStatsRn                                       SnmpAdminString,
    cfprApComputeMbTempStatsFmTempSenIo                              INTEGER,
    cfprApComputeMbTempStatsFmTempSenIoAvg                           INTEGER,
    cfprApComputeMbTempStatsFmTempSenIoMax                           INTEGER,
    cfprApComputeMbTempStatsFmTempSenIoMin                           INTEGER,
    cfprApComputeMbTempStatsFmTempSenRear                            INTEGER,
    cfprApComputeMbTempStatsFmTempSenRearAvg                         INTEGER,
    cfprApComputeMbTempStatsFmTempSenRearL                           INTEGER,
    cfprApComputeMbTempStatsFmTempSenRearLAvg                        INTEGER,
    cfprApComputeMbTempStatsFmTempSenRearLMax                        INTEGER,
    cfprApComputeMbTempStatsFmTempSenRearLMin                        INTEGER,
    cfprApComputeMbTempStatsFmTempSenRearMax                         INTEGER,
    cfprApComputeMbTempStatsFmTempSenRearMin                         INTEGER,
    cfprApComputeMbTempStatsFmTempSenRearR                           INTEGER,
    cfprApComputeMbTempStatsFmTempSenRearRAvg                        INTEGER,
    cfprApComputeMbTempStatsFmTempSenRearRMax                        INTEGER,
    cfprApComputeMbTempStatsFmTempSenRearRMin                        INTEGER,
    cfprApComputeMbTempStatsIntervals                                Gauge32,
    cfprApComputeMbTempStatsSuspect                                  TruthValue,
    cfprApComputeMbTempStatsThresholded                              CfprApComputeMbTempStatsThresholded,
    cfprApComputeMbTempStatsTimeCollected                            DateAndTime,
    cfprApComputeMbTempStatsUpdate                                   Gauge32
}

cfprApComputeMbTempStatsInstanceId OBJECT-TYPE
    SYNTAX       CfprApManagedObjectId
    MAX-ACCESS   not-accessible
    STATUS       current
    DESCRIPTION
        "Instance identifier of the managed object."
    ::= { cfprApComputeMbTempStatsEntry 1 }

cfprApComputeMbTempStatsDn OBJECT-TYPE
    SYNTAX       CfprApManagedObjectDn
    MAX-ACCESS   read-only
    STATUS       current
    DESCRIPTION
        "Cisco Firepower compute:MbTempStats:dn managed object property"
    ::= { cfprApComputeMbTempStatsEntry 2 }

cfprApComputeMbTempStatsRn OBJECT-TYPE
    SYNTAX       SnmpAdminString
    MAX-ACCESS   read-only
    STATUS       current
    DESCRIPTION
        "Cisco Firepower compute:MbTempStats:rn managed object property"
    ::= { cfprApComputeMbTempStatsEntry 3 }

cfprApComputeMbTempStatsFmTempSenIo OBJECT-TYPE
    SYNTAX       INTEGER
    MAX-ACCESS   read-only
    STATUS       current
    DESCRIPTION
        "Cisco Firepower compute:MbTempStats:fmTempSenIo
        managed object property"
    ::= { cfprApComputeMbTempStatsEntry 4 }

cfprApComputeMbTempStatsFmTempSenIoAvg OBJECT-TYPE
    SYNTAX       INTEGER
    MAX-ACCESS   read-only
    STATUS       current
    DESCRIPTION
        "Cisco Firepower compute:MbTempStats:fmTempSenIoAvg
        managed object property"
    ::= { cfprApComputeMbTempStatsEntry 5 }

cfprApComputeMbTempStatsFmTempSenIoMax OBJECT-TYPE
    SYNTAX       INTEGER
    MAX-ACCESS   read-only
    STATUS       current
    DESCRIPTION
        "Cisco Firepower compute:MbTempStats:fmTempSenIoMax
        managed object property"
    ::= { cfprApComputeMbTempStatsEntry 6 }

cfprApComputeMbTempStatsFmTempSenIoMin OBJECT-TYPE
    SYNTAX       INTEGER
    MAX-ACCESS   read-only
    STATUS       current
    DESCRIPTION
        "Cisco Firepower compute:MbTempStats:fmTempSenIoMin
        managed object property"
    ::= { cfprApComputeMbTempStatsEntry 7 }

cfprApComputeMbTempStatsFmTempSenRear OBJECT-TYPE
    SYNTAX       INTEGER
    MAX-ACCESS   read-only
    STATUS       current
    DESCRIPTION
        "Cisco Firepower compute:MbTempStats:fmTempSenRear
        managed object property"
    ::= { cfprApComputeMbTempStatsEntry 8 }

cfprApComputeMbTempStatsFmTempSenRearAvg OBJECT-TYPE
    SYNTAX       INTEGER
    MAX-ACCESS   read-only
    STATUS       current
    DESCRIPTION
        "Cisco Firepower compute:MbTempStats:fmTempSenRearAvg
        managed object property"
    ::= { cfprApComputeMbTempStatsEntry 9 }

cfprApComputeMbTempStatsFmTempSenRearL OBJECT-TYPE
    SYNTAX       INTEGER
    MAX-ACCESS   read-only
    STATUS       current
    DESCRIPTION
        "Cisco Firepower compute:MbTempStats:fmTempSenRearL
        managed object property"
    ::= { cfprApComputeMbTempStatsEntry 10 }

cfprApComputeMbTempStatsFmTempSenRearLAvg OBJECT-TYPE
    SYNTAX       INTEGER
    MAX-ACCESS   read-only
    STATUS       current
    DESCRIPTION
        "Cisco Firepower compute:MbTempStats:fmTempSenRearLAvg
        managed object property"
    ::= { cfprApComputeMbTempStatsEntry 11 }

cfprApComputeMbTempStatsFmTempSenRearLMax OBJECT-TYPE
    SYNTAX       INTEGER
    MAX-ACCESS   read-only
    STATUS       current
    DESCRIPTION
        "Cisco Firepower compute:MbTempStats:fmTempSenRearLMax
        managed object property"
    ::= { cfprApComputeMbTempStatsEntry 12 }

cfprApComputeMbTempStatsFmTempSenRearLMin OBJECT-TYPE
    SYNTAX       INTEGER
    MAX-ACCESS   read-only
    STATUS       current
    DESCRIPTION
        "Cisco Firepower compute:MbTempStats:fmTempSenRearLMin
        managed object property"
    ::= { cfprApComputeMbTempStatsEntry 13 }

cfprApComputeMbTempStatsFmTempSenRearMax OBJECT-TYPE
    SYNTAX       INTEGER
    MAX-ACCESS   read-only
    STATUS       current
    DESCRIPTION
        "Cisco Firepower compute:MbTempStats:fmTempSenRearMax
        managed object property"
    ::= { cfprApComputeMbTempStatsEntry 14 }

cfprApComputeMbTempStatsFmTempSenRearMin OBJECT-TYPE
    SYNTAX       INTEGER
    MAX-ACCESS   read-only
    STATUS       current
    DESCRIPTION
        "Cisco Firepower compute:MbTempStats:fmTempSenRearMin
        managed object property"
    ::= { cfprApComputeMbTempStatsEntry 15 }

cfprApComputeMbTempStatsFmTempSenRearR OBJECT-TYPE
    SYNTAX       INTEGER
    MAX-ACCESS   read-only
    STATUS       current
    DESCRIPTION
        "Cisco Firepower compute:MbTempStats:fmTempSenRearR
        managed object property"
    ::= { cfprApComputeMbTempStatsEntry 16 }

cfprApComputeMbTempStatsFmTempSenRearRAvg OBJECT-TYPE
    SYNTAX       INTEGER
    MAX-ACCESS   read-only
    STATUS       current
    DESCRIPTION
        "Cisco Firepower compute:MbTempStats:fmTempSenRearRAvg
        managed object property"
    ::= { cfprApComputeMbTempStatsEntry 17 }

cfprApComputeMbTempStatsFmTempSenRearRMax OBJECT-TYPE
    SYNTAX       INTEGER
    MAX-ACCESS   read-only
    STATUS       current
    DESCRIPTION
        "Cisco Firepower compute:MbTempStats:fmTempSenRearRMax
        managed object property"
    ::= { cfprApComputeMbTempStatsEntry 18 }

cfprApComputeMbTempStatsFmTempSenRearRMin OBJECT-TYPE
    SYNTAX       INTEGER
    MAX-ACCESS   read-only
    STATUS       current
    DESCRIPTION
        "Cisco Firepower compute:MbTempStats:fmTempSenRearRMin
        managed object property"
    ::= { cfprApComputeMbTempStatsEntry 19 }

cfprApComputeMbTempStatsIntervals OBJECT-TYPE
    SYNTAX       Gauge32
    MAX-ACCESS   read-only
    STATUS       current
    DESCRIPTION
        "Cisco Firepower compute:MbTempStats:intervals
        managed object property"
    ::= { cfprApComputeMbTempStatsEntry 20 }

cfprApComputeMbTempStatsSuspect OBJECT-TYPE
    SYNTAX       TruthValue
    MAX-ACCESS   read-only
    STATUS       current
    DESCRIPTION
        "Cisco Firepower compute:MbTempStats:suspect managed
        object property"
    ::= { cfprApComputeMbTempStatsEntry 21 }

cfprApComputeMbTempStatsThresholded OBJECT-TYPE
    SYNTAX       CfprApComputeMbTempStatsThresholded
    MAX-ACCESS   read-only
    STATUS       current
    DESCRIPTION
        "Cisco Firepower compute:MbTempStats:thresholded
        managed object property"
    ::= { cfprApComputeMbTempStatsEntry 22 }

cfprApComputeMbTempStatsTimeCollected OBJECT-TYPE
    SYNTAX       DateAndTime
    MAX-ACCESS   read-only
    STATUS       current
    DESCRIPTION
        "Cisco Firepower compute:MbTempStats:timeCollected
        managed object property"
    ::= { cfprApComputeMbTempStatsEntry 23 }

cfprApComputeMbTempStatsUpdate OBJECT-TYPE
    SYNTAX       Gauge32
    MAX-ACCESS   read-only
    STATUS       current
    DESCRIPTION
        "Cisco Firepower compute:MbTempStats:update managed
        object property"
    ::= { cfprApComputeMbTempStatsEntry 24 }

cfprApComputeMbTempStatsHistTable OBJECT-TYPE
    SYNTAX           SEQUENCE OF CfprApComputeMbTempStatsHistEntry
    MAX-ACCESS       not-accessible
    STATUS           current
    DESCRIPTION
        "Cisco Firepower compute:MbTempStatsHist managed object table"
    ::= { cfprApComputeObjects 25 }

cfprApComputeMbTempStatsHistEntry OBJECT-TYPE
    SYNTAX           CfprApComputeMbTempStatsHistEntry
    MAX-ACCESS       not-accessible
    STATUS           current
    DESCRIPTION
        "Entry for the cfprApComputeMbTempStatsHistTable table."
    INDEX { cfprApComputeMbTempStatsHistInstanceId }
    ::= { cfprApComputeMbTempStatsHistTable 1 }

CfprApComputeMbTempStatsHistEntry ::= SEQUENCE {
    cfprApComputeMbTempStatsHistInstanceId                           CfprApManagedObjectId,
    cfprApComputeMbTempStatsHistDn                                   CfprApManagedObjectDn,
    cfprApComputeMbTempStatsHistRn                                   SnmpAdminString,
    cfprApComputeMbTempStatsHistFmTempSenIo                          INTEGER,
    cfprApComputeMbTempStatsHistFmTempSenIoAvg                       INTEGER,
    cfprApComputeMbTempStatsHistFmTempSenIoMax                       INTEGER,
    cfprApComputeMbTempStatsHistFmTempSenIoMin                       INTEGER,
    cfprApComputeMbTempStatsHistFmTempSenRear                        INTEGER,
    cfprApComputeMbTempStatsHistFmTempSenRearAvg                     INTEGER,
    cfprApComputeMbTempStatsHistFmTempSenRearL                       INTEGER,
    cfprApComputeMbTempStatsHistFmTempSenRearLAvg                    INTEGER,
    cfprApComputeMbTempStatsHistFmTempSenRearLMax                    INTEGER,
    cfprApComputeMbTempStatsHistFmTempSenRearLMin                    INTEGER,
    cfprApComputeMbTempStatsHistFmTempSenRearMax                     INTEGER,
    cfprApComputeMbTempStatsHistFmTempSenRearMin                     INTEGER,
    cfprApComputeMbTempStatsHistFmTempSenRearR                       INTEGER,
    cfprApComputeMbTempStatsHistFmTempSenRearRAvg                    INTEGER,
    cfprApComputeMbTempStatsHistFmTempSenRearRMax                    INTEGER,
    cfprApComputeMbTempStatsHistFmTempSenRearRMin                    INTEGER,
    cfprApComputeMbTempStatsHistId                                   Unsigned64,
    cfprApComputeMbTempStatsHistMostRecent                           TruthValue,
    cfprApComputeMbTempStatsHistSuspect                              TruthValue,
    cfprApComputeMbTempStatsHistThresholded                          CfprApComputeMbTempStatsHistThresholded,
    cfprApComputeMbTempStatsHistTimeCollected                        DateAndTime
}

cfprApComputeMbTempStatsHistInstanceId OBJECT-TYPE
    SYNTAX       CfprApManagedObjectId
    MAX-ACCESS   not-accessible
    STATUS       current
    DESCRIPTION
        "Instance identifier of the managed object."
    ::= { cfprApComputeMbTempStatsHistEntry 1 }

cfprApComputeMbTempStatsHistDn OBJECT-TYPE
    SYNTAX       CfprApManagedObjectDn
    MAX-ACCESS   read-only
    STATUS       current
    DESCRIPTION
        "Cisco Firepower compute:MbTempStatsHist:dn managed
        object property"
    ::= { cfprApComputeMbTempStatsHistEntry 2 }

cfprApComputeMbTempStatsHistRn OBJECT-TYPE
    SYNTAX       SnmpAdminString
    MAX-ACCESS   read-only
    STATUS       current
    DESCRIPTION
        "Cisco Firepower compute:MbTempStatsHist:rn managed
        object property"
    ::= { cfprApComputeMbTempStatsHistEntry 3 }

cfprApComputeMbTempStatsHistFmTempSenIo OBJECT-TYPE
    SYNTAX       INTEGER
    MAX-ACCESS   read-only
    STATUS       current
    DESCRIPTION
        "Cisco Firepower compute:MbTempStatsHist:fmTempSenIo
        managed object property"
    ::= { cfprApComputeMbTempStatsHistEntry 4 }

cfprApComputeMbTempStatsHistFmTempSenIoAvg OBJECT-TYPE
    SYNTAX       INTEGER
    MAX-ACCESS   read-only
    STATUS       current
    DESCRIPTION
        "Cisco Firepower compute:MbTempStatsHist:fmTempSenIoAvg
        managed object property"
    ::= { cfprApComputeMbTempStatsHistEntry 5 }

cfprApComputeMbTempStatsHistFmTempSenIoMax OBJECT-TYPE
    SYNTAX       INTEGER
    MAX-ACCESS   read-only
    STATUS       current
    DESCRIPTION
        "Cisco Firepower compute:MbTempStatsHist:fmTempSenIoMax
        managed object property"
    ::= { cfprApComputeMbTempStatsHistEntry 6 }

cfprApComputeMbTempStatsHistFmTempSenIoMin OBJECT-TYPE
    SYNTAX       INTEGER
    MAX-ACCESS   read-only
    STATUS       current
    DESCRIPTION
        "Cisco Firepower compute:MbTempStatsHist:fmTempSenIoMin
        managed object property"
    ::= { cfprApComputeMbTempStatsHistEntry 7 }

cfprApComputeMbTempStatsHistFmTempSenRear OBJECT-TYPE
    SYNTAX       INTEGER
    MAX-ACCESS   read-only
    STATUS       current
    DESCRIPTION
        "Cisco Firepower compute:MbTempStatsHist:fmTempSenRear
        managed object property"
    ::= { cfprApComputeMbTempStatsHistEntry 8 }

cfprApComputeMbTempStatsHistFmTempSenRearAvg OBJECT-TYPE
    SYNTAX       INTEGER
    MAX-ACCESS   read-only
    STATUS       current
    DESCRIPTION
        "Cisco Firepower compute:MbTempStatsHist:fmTempSenRearAvg
        managed object property"
    ::= { cfprApComputeMbTempStatsHistEntry 9 }

cfprApComputeMbTempStatsHistFmTempSenRearL OBJECT-TYPE
    SYNTAX       INTEGER
    MAX-ACCESS   read-only
    STATUS       current
    DESCRIPTION
        "Cisco Firepower compute:MbTempStatsHist:fmTempSenRearL
        managed object property"
    ::= { cfprApComputeMbTempStatsHistEntry 10 }

cfprApComputeMbTempStatsHistFmTempSenRearLAvg OBJECT-TYPE
    SYNTAX       INTEGER
    MAX-ACCESS   read-only
    STATUS       current
    DESCRIPTION
        "Cisco Firepower compute:MbTempStatsHist:fmTempSenRearLAvg
        managed object property"
    ::= { cfprApComputeMbTempStatsHistEntry 11 }

cfprApComputeMbTempStatsHistFmTempSenRearLMax OBJECT-TYPE
    SYNTAX       INTEGER
    MAX-ACCESS   read-only
    STATUS       current
    DESCRIPTION
        "Cisco Firepower compute:MbTempStatsHist:fmTempSenRearLMax
        managed object property"
    ::= { cfprApComputeMbTempStatsHistEntry 12 }

cfprApComputeMbTempStatsHistFmTempSenRearLMin OBJECT-TYPE
    SYNTAX       INTEGER
    MAX-ACCESS   read-only
    STATUS       current
    DESCRIPTION
        "Cisco Firepower compute:MbTempStatsHist:fmTempSenRearLMin
        managed object property"
    ::= { cfprApComputeMbTempStatsHistEntry 13 }

cfprApComputeMbTempStatsHistFmTempSenRearMax OBJECT-TYPE
    SYNTAX       INTEGER
    MAX-ACCESS   read-only
    STATUS       current
    DESCRIPTION
        "Cisco Firepower compute:MbTempStatsHist:fmTempSenRearMax
        managed object property"
    ::= { cfprApComputeMbTempStatsHistEntry 14 }

cfprApComputeMbTempStatsHistFmTempSenRearMin OBJECT-TYPE
    SYNTAX       INTEGER
    MAX-ACCESS   read-only
    STATUS       current
    DESCRIPTION
        "Cisco Firepower compute:MbTempStatsHist:fmTempSenRearMin
        managed object property"
    ::= { cfprApComputeMbTempStatsHistEntry 15 }

cfprApComputeMbTempStatsHistFmTempSenRearR OBJECT-TYPE
    SYNTAX       INTEGER
    MAX-ACCESS   read-only
    STATUS       current
    DESCRIPTION
        "Cisco Firepower compute:MbTempStatsHist:fmTempSenRearR
        managed object property"
    ::= { cfprApComputeMbTempStatsHistEntry 16 }

cfprApComputeMbTempStatsHistFmTempSenRearRAvg OBJECT-TYPE
    SYNTAX       INTEGER
    MAX-ACCESS   read-only
    STATUS       current
    DESCRIPTION
        "Cisco Firepower compute:MbTempStatsHist:fmTempSenRearRAvg
        managed object property"
    ::= { cfprApComputeMbTempStatsHistEntry 17 }

cfprApComputeMbTempStatsHistFmTempSenRearRMax OBJECT-TYPE
    SYNTAX       INTEGER
    MAX-ACCESS   read-only
    STATUS       current
    DESCRIPTION
        "Cisco Firepower compute:MbTempStatsHist:fmTempSenRearRMax
        managed object property"
    ::= { cfprApComputeMbTempStatsHistEntry 18 }

cfprApComputeMbTempStatsHistFmTempSenRearRMin OBJECT-TYPE
    SYNTAX       INTEGER
    MAX-ACCESS   read-only
    STATUS       current
    DESCRIPTION
        "Cisco Firepower compute:MbTempStatsHist:fmTempSenRearRMin
        managed object property"
    ::= { cfprApComputeMbTempStatsHistEntry 19 }

cfprApComputeMbTempStatsHistId OBJECT-TYPE
    SYNTAX       Unsigned64
    MAX-ACCESS   read-only
    STATUS       current
    DESCRIPTION
        "Cisco Firepower compute:MbTempStatsHist:id managed
        object property"
    ::= { cfprApComputeMbTempStatsHistEntry 20 }

cfprApComputeMbTempStatsHistMostRecent OBJECT-TYPE
    SYNTAX       TruthValue
    MAX-ACCESS   read-only
    STATUS       current
    DESCRIPTION
        "Cisco Firepower compute:MbTempStatsHist:mostRecent
        managed object property"
    ::= { cfprApComputeMbTempStatsHistEntry 21 }

cfprApComputeMbTempStatsHistSuspect OBJECT-TYPE
    SYNTAX       TruthValue
    MAX-ACCESS   read-only
    STATUS       current
    DESCRIPTION
        "Cisco Firepower compute:MbTempStatsHist:suspect
        managed object property"
    ::= { cfprApComputeMbTempStatsHistEntry 22 }

cfprApComputeMbTempStatsHistThresholded OBJECT-TYPE
    SYNTAX       CfprApComputeMbTempStatsHistThresholded
    MAX-ACCESS   read-only
    STATUS       current
    DESCRIPTION
        "Cisco Firepower compute:MbTempStatsHist:thresholded
        managed object property"
    ::= { cfprApComputeMbTempStatsHistEntry 23 }

cfprApComputeMbTempStatsHistTimeCollected OBJECT-TYPE
    SYNTAX       DateAndTime
    MAX-ACCESS   read-only
    STATUS       current
    DESCRIPTION
        "Cisco Firepower compute:MbTempStatsHist:timeCollected
        managed object property"
    ::= { cfprApComputeMbTempStatsHistEntry 24 }

cfprApComputeMemoryConfigPolicyTable OBJECT-TYPE
    SYNTAX           SEQUENCE OF CfprApComputeMemoryConfigPolicyEntry
    MAX-ACCESS       not-accessible
    STATUS           current
    DESCRIPTION
        "Cisco Firepower compute:MemoryConfigPolicy managed object table"
    ::= { cfprApComputeObjects 26 }

cfprApComputeMemoryConfigPolicyEntry OBJECT-TYPE
    SYNTAX           CfprApComputeMemoryConfigPolicyEntry
    MAX-ACCESS       not-accessible
    STATUS           current
    DESCRIPTION
        "Entry for the cfprApComputeMemoryConfigPolicyTable table."
    INDEX { cfprApComputeMemoryConfigPolicyInstanceId }
    ::= { cfprApComputeMemoryConfigPolicyTable 1 }

CfprApComputeMemoryConfigPolicyEntry ::= SEQUENCE {
    cfprApComputeMemoryConfigPolicyInstanceId                        CfprApManagedObjectId,
    cfprApComputeMemoryConfigPolicyDn                                CfprApManagedObjectDn,
    cfprApComputeMemoryConfigPolicyRn                                SnmpAdminString,
    cfprApComputeMemoryConfigPolicyBlackListing                      CfprApComputeBlackListing,
    cfprApComputeMemoryConfigPolicyDescr                             SnmpAdminString,
    cfprApComputeMemoryConfigPolicyIntId                             SnmpAdminString,
    cfprApComputeMemoryConfigPolicyName                              SnmpAdminString,
    cfprApComputeMemoryConfigPolicyPolicyLevel                       Gauge32,
    cfprApComputeMemoryConfigPolicyPolicyOwner                       CfprApPolicyPolicyOwner
}

cfprApComputeMemoryConfigPolicyInstanceId OBJECT-TYPE
    SYNTAX       CfprApManagedObjectId
    MAX-ACCESS   not-accessible
    STATUS       current
    DESCRIPTION
        "Instance identifier of the managed object."
    ::= { cfprApComputeMemoryConfigPolicyEntry 1 }

cfprApComputeMemoryConfigPolicyDn OBJECT-TYPE
    SYNTAX       CfprApManagedObjectDn
    MAX-ACCESS   read-only
    STATUS       current
    DESCRIPTION
        "Cisco Firepower compute:MemoryConfigPolicy:dn
        managed object property"
    ::= { cfprApComputeMemoryConfigPolicyEntry 2 }

cfprApComputeMemoryConfigPolicyRn OBJECT-TYPE
    SYNTAX       SnmpAdminString
    MAX-ACCESS   read-only
    STATUS       current
    DESCRIPTION
        "Cisco Firepower compute:MemoryConfigPolicy:rn
        managed object property"
    ::= { cfprApComputeMemoryConfigPolicyEntry 3 }

cfprApComputeMemoryConfigPolicyBlackListing OBJECT-TYPE
    SYNTAX       CfprApComputeBlackListing
    MAX-ACCESS   read-only
    STATUS       current
    DESCRIPTION
        "Cisco Firepower compute:MemoryConfigPolicy:blackListing
        managed object property"
    ::= { cfprApComputeMemoryConfigPolicyEntry 4 }

cfprApComputeMemoryConfigPolicyDescr OBJECT-TYPE
    SYNTAX       SnmpAdminString
    MAX-ACCESS   read-only
    STATUS       current
    DESCRIPTION
        "Cisco Firepower compute:MemoryConfigPolicy:descr
        managed object property"
    ::= { cfprApComputeMemoryConfigPolicyEntry 5 }

cfprApComputeMemoryConfigPolicyIntId OBJECT-TYPE
    SYNTAX       SnmpAdminString
    MAX-ACCESS   read-only
    STATUS       current
    DESCRIPTION
        "Cisco Firepower compute:MemoryConfigPolicy:intId
        managed object property"
    ::= { cfprApComputeMemoryConfigPolicyEntry 6 }

cfprApComputeMemoryConfigPolicyName OBJECT-TYPE
    SYNTAX       SnmpAdminString
    MAX-ACCESS   read-only
    STATUS       current
    DESCRIPTION
        "Cisco Firepower compute:MemoryConfigPolicy:name
        managed object property"
    ::= { cfprApComputeMemoryConfigPolicyEntry 7 }

cfprApComputeMemoryConfigPolicyPolicyLevel OBJECT-TYPE
    SYNTAX       Gauge32
    MAX-ACCESS   read-only
    STATUS       current
    DESCRIPTION
        "Cisco Firepower compute:MemoryConfigPolicy:policyLevel
        managed object property"
    ::= { cfprApComputeMemoryConfigPolicyEntry 8 }

cfprApComputeMemoryConfigPolicyPolicyOwner OBJECT-TYPE
    SYNTAX       CfprApPolicyPolicyOwner
    MAX-ACCESS   read-only
    STATUS       current
    DESCRIPTION
        "Cisco Firepower compute:MemoryConfigPolicy:policyOwner
        managed object property"
    ::= { cfprApComputeMemoryConfigPolicyEntry 9 }

cfprApComputeMemoryConfigurationTable OBJECT-TYPE
    SYNTAX           SEQUENCE OF CfprApComputeMemoryConfigurationEntry
    MAX-ACCESS       not-accessible
    STATUS           current
    DESCRIPTION
        "Cisco Firepower compute:MemoryConfiguration managed object table"
    ::= { cfprApComputeObjects 27 }

cfprApComputeMemoryConfigurationEntry OBJECT-TYPE
    SYNTAX           CfprApComputeMemoryConfigurationEntry
    MAX-ACCESS       not-accessible
    STATUS           current
    DESCRIPTION
        "Entry for the cfprApComputeMemoryConfigurationTable table."
    INDEX { cfprApComputeMemoryConfigurationInstanceId }
    ::= { cfprApComputeMemoryConfigurationTable 1 }

CfprApComputeMemoryConfigurationEntry ::= SEQUENCE {
    cfprApComputeMemoryConfigurationInstanceId                       CfprApManagedObjectId,
    cfprApComputeMemoryConfigurationDn                               CfprApManagedObjectDn,
    cfprApComputeMemoryConfigurationRn                               SnmpAdminString,
    cfprApComputeMemoryConfigurationAdminMemoryState                 CfprApComputeAdminMemoryState,
    cfprApComputeMemoryConfigurationBlackListing                     CfprApComputeBlackListing
}

cfprApComputeMemoryConfigurationInstanceId OBJECT-TYPE
    SYNTAX       CfprApManagedObjectId
    MAX-ACCESS   not-accessible
    STATUS       current
    DESCRIPTION
        "Instance identifier of the managed object."
    ::= { cfprApComputeMemoryConfigurationEntry 1 }

cfprApComputeMemoryConfigurationDn OBJECT-TYPE
    SYNTAX       CfprApManagedObjectDn
    MAX-ACCESS   read-only
    STATUS       current
    DESCRIPTION
        "Cisco Firepower compute:MemoryConfiguration:dn
        managed object property"
    ::= { cfprApComputeMemoryConfigurationEntry 2 }

cfprApComputeMemoryConfigurationRn OBJECT-TYPE
    SYNTAX       SnmpAdminString
    MAX-ACCESS   read-only
    STATUS       current
    DESCRIPTION
        "Cisco Firepower compute:MemoryConfiguration:rn
        managed object property"
    ::= { cfprApComputeMemoryConfigurationEntry 3 }

cfprApComputeMemoryConfigurationAdminMemoryState OBJECT-TYPE
    SYNTAX       CfprApComputeAdminMemoryState
    MAX-ACCESS   read-only
    STATUS       current
    DESCRIPTION
        "Cisco Firepower compute:MemoryConfiguration:adminMemoryState
        managed object property"
    ::= { cfprApComputeMemoryConfigurationEntry 4 }

cfprApComputeMemoryConfigurationBlackListing OBJECT-TYPE
    SYNTAX       CfprApComputeBlackListing
    MAX-ACCESS   read-only
    STATUS       current
    DESCRIPTION
        "Cisco Firepower compute:MemoryConfiguration:blackListing
        managed object property"
    ::= { cfprApComputeMemoryConfigurationEntry 5 }

cfprApComputeMemoryUnitConstraintDefTable OBJECT-TYPE
    SYNTAX           SEQUENCE OF CfprApComputeMemoryUnitConstraintDefEntry
    MAX-ACCESS       not-accessible
    STATUS           current
    DESCRIPTION
        "Cisco Firepower compute:MemoryUnitConstraintDef
        managed object table"
    ::= { cfprApComputeObjects 28 }

cfprApComputeMemoryUnitConstraintDefEntry OBJECT-TYPE
    SYNTAX           CfprApComputeMemoryUnitConstraintDefEntry
    MAX-ACCESS       not-accessible
    STATUS           current
    DESCRIPTION
        "Entry for the cfprApComputeMemoryUnitConstraintDefTable table."
    INDEX { cfprApComputeMemoryUnitConstraintDefInstanceId }
    ::= { cfprApComputeMemoryUnitConstraintDefTable 1 }

CfprApComputeMemoryUnitConstraintDefEntry ::= SEQUENCE {
    cfprApComputeMemoryUnitConstraintDefInstanceId                   CfprApManagedObjectId,
    cfprApComputeMemoryUnitConstraintDefDn                           CfprApManagedObjectDn,
    cfprApComputeMemoryUnitConstraintDefRn                           SnmpAdminString,
    cfprApComputeMemoryUnitConstraintDefDescr                        SnmpAdminString,
    cfprApComputeMemoryUnitConstraintDefIntId                        SnmpAdminString,
    cfprApComputeMemoryUnitConstraintDefName                         SnmpAdminString,
    cfprApComputeMemoryUnitConstraintDefPolicyLevel                  Gauge32,
    cfprApComputeMemoryUnitConstraintDefPolicyOwner                  CfprApPolicyPolicyOwner,
    cfprApComputeMemoryUnitConstraintDefRevisionModifier             SnmpAdminString,
    cfprApComputeMemoryUnitConstraintDefType                         CfprApComputeMemoryUnitConstraintType
}

cfprApComputeMemoryUnitConstraintDefInstanceId OBJECT-TYPE
    SYNTAX       CfprApManagedObjectId
    MAX-ACCESS   not-accessible
    STATUS       current
    DESCRIPTION
        "Instance identifier of the managed object."
    ::= { cfprApComputeMemoryUnitConstraintDefEntry 1 }

cfprApComputeMemoryUnitConstraintDefDn OBJECT-TYPE
    SYNTAX       CfprApManagedObjectDn
    MAX-ACCESS   read-only
    STATUS       current
    DESCRIPTION
        "Cisco Firepower compute:MemoryUnitConstraintDef:dn
        managed object property"
    ::= { cfprApComputeMemoryUnitConstraintDefEntry 2 }

cfprApComputeMemoryUnitConstraintDefRn OBJECT-TYPE
    SYNTAX       SnmpAdminString
    MAX-ACCESS   read-only
    STATUS       current
    DESCRIPTION
        "Cisco Firepower compute:MemoryUnitConstraintDef:rn
        managed object property"
    ::= { cfprApComputeMemoryUnitConstraintDefEntry 3 }

cfprApComputeMemoryUnitConstraintDefDescr OBJECT-TYPE
    SYNTAX       SnmpAdminString
    MAX-ACCESS   read-only
    STATUS       current
    DESCRIPTION
        "Cisco Firepower compute:MemoryUnitConstraintDef:descr
        managed object property"
    ::= { cfprApComputeMemoryUnitConstraintDefEntry 4 }

cfprApComputeMemoryUnitConstraintDefIntId OBJECT-TYPE
    SYNTAX       SnmpAdminString
    MAX-ACCESS   read-only
    STATUS       current
    DESCRIPTION
        "Cisco Firepower compute:MemoryUnitConstraintDef:intId
        managed object property"
    ::= { cfprApComputeMemoryUnitConstraintDefEntry 5 }

cfprApComputeMemoryUnitConstraintDefName OBJECT-TYPE
    SYNTAX       SnmpAdminString
    MAX-ACCESS   read-only
    STATUS       current
    DESCRIPTION
        "Cisco Firepower compute:MemoryUnitConstraintDef:name
        managed object property"
    ::= { cfprApComputeMemoryUnitConstraintDefEntry 6 }

cfprApComputeMemoryUnitConstraintDefPolicyLevel OBJECT-TYPE
    SYNTAX       Gauge32
    MAX-ACCESS   read-only
    STATUS       current
    DESCRIPTION
        "Cisco Firepower compute:MemoryUnitConstraintDef:policyLevel
        managed object property"
    ::= { cfprApComputeMemoryUnitConstraintDefEntry 7 }

cfprApComputeMemoryUnitConstraintDefPolicyOwner OBJECT-TYPE
    SYNTAX       CfprApPolicyPolicyOwner
    MAX-ACCESS   read-only
    STATUS       current
    DESCRIPTION
        "Cisco Firepower compute:MemoryUnitConstraintDef:policyOwner
        managed object property"
    ::= { cfprApComputeMemoryUnitConstraintDefEntry 8 }

cfprApComputeMemoryUnitConstraintDefRevisionModifier OBJECT-TYPE
    SYNTAX       SnmpAdminString
    MAX-ACCESS   read-only
    STATUS       current
    DESCRIPTION
        "Cisco Firepower compute:MemoryUnitConstraintDef:revisionModifier
        managed object property"
    ::= { cfprApComputeMemoryUnitConstraintDefEntry 9 }

cfprApComputeMemoryUnitConstraintDefType OBJECT-TYPE
    SYNTAX       CfprApComputeMemoryUnitConstraintType
    MAX-ACCESS   read-only
    STATUS       current
    DESCRIPTION
        "Cisco Firepower compute:MemoryUnitConstraintDef:type
        managed object property"
    ::= { cfprApComputeMemoryUnitConstraintDefEntry 10 }

cfprApComputeNpuTable OBJECT-TYPE
    SYNTAX           SEQUENCE OF CfprApComputeNpuEntry
    MAX-ACCESS       not-accessible
    STATUS           current
    DESCRIPTION
        "Cisco Firepower compute:Npu managed object table"
    ::= { cfprApComputeObjects 29 }

cfprApComputeNpuEntry OBJECT-TYPE
    SYNTAX           CfprApComputeNpuEntry
    MAX-ACCESS       not-accessible
    STATUS           current
    DESCRIPTION
        "Entry for the cfprApComputeNpuTable table."
    INDEX { cfprApComputeNpuInstanceId }
    ::= { cfprApComputeNpuTable 1 }

CfprApComputeNpuEntry ::= SEQUENCE {
    cfprApComputeNpuInstanceId                                       CfprApManagedObjectId,
    cfprApComputeNpuDn                                               CfprApManagedObjectDn,
    cfprApComputeNpuRn                                               SnmpAdminString,
    cfprApComputeNpuId                                               Gauge32,
    cfprApComputeNpuLocationDn                                       SnmpAdminString,
    cfprApComputeNpuModel                                            SnmpAdminString,
    cfprApComputeNpuOperQualifierReason                              SnmpAdminString,
    cfprApComputeNpuOperState                                        CfprApEquipmentOperability,
    cfprApComputeNpuOperability                                      CfprApEquipmentOperability,
    cfprApComputeNpuPerf                                             CfprApEquipmentSensorThresholdStatus,
    cfprApComputeNpuPower                                            CfprApEquipmentPowerState,
    cfprApComputeNpuPresence                                         CfprApEquipmentPresence,
    cfprApComputeNpuRevision                                         SnmpAdminString,
    cfprApComputeNpuSerial                                           SnmpAdminString,
    cfprApComputeNpuThermal                                          CfprApEquipmentSensorThresholdStatus,
    cfprApComputeNpuVendor                                           SnmpAdminString,
    cfprApComputeNpuVoltage                                          CfprApEquipmentSensorThresholdStatus
}

cfprApComputeNpuInstanceId OBJECT-TYPE
    SYNTAX       CfprApManagedObjectId
    MAX-ACCESS   not-accessible
    STATUS       current
    DESCRIPTION
        "Instance identifier of the managed object."
    ::= { cfprApComputeNpuEntry 1 }

cfprApComputeNpuDn OBJECT-TYPE
    SYNTAX       CfprApManagedObjectDn
    MAX-ACCESS   read-only
    STATUS       current
    DESCRIPTION
        "Cisco Firepower compute:Npu:dn managed object property"
    ::= { cfprApComputeNpuEntry 2 }

cfprApComputeNpuRn OBJECT-TYPE
    SYNTAX       SnmpAdminString
    MAX-ACCESS   read-only
    STATUS       current
    DESCRIPTION
        "Cisco Firepower compute:Npu:rn managed object property"
    ::= { cfprApComputeNpuEntry 3 }

cfprApComputeNpuId OBJECT-TYPE
    SYNTAX       Gauge32
    MAX-ACCESS   read-only
    STATUS       current
    DESCRIPTION
        "Cisco Firepower compute:Npu:id managed object property"
    ::= { cfprApComputeNpuEntry 4 }

cfprApComputeNpuLocationDn OBJECT-TYPE
    SYNTAX       SnmpAdminString
    MAX-ACCESS   read-only
    STATUS       current
    DESCRIPTION
        "Cisco Firepower compute:Npu:locationDn managed object property"
    ::= { cfprApComputeNpuEntry 5 }

cfprApComputeNpuModel OBJECT-TYPE
    SYNTAX       SnmpAdminString
    MAX-ACCESS   read-only
    STATUS       current
    DESCRIPTION
        "Cisco Firepower compute:Npu:model managed object property"
    ::= { cfprApComputeNpuEntry 6 }

cfprApComputeNpuOperQualifierReason OBJECT-TYPE
    SYNTAX       SnmpAdminString
    MAX-ACCESS   read-only
    STATUS       current
    DESCRIPTION
        "Cisco Firepower compute:Npu:operQualifierReason
        managed object property"
    ::= { cfprApComputeNpuEntry 7 }

cfprApComputeNpuOperState OBJECT-TYPE
    SYNTAX       CfprApEquipmentOperability
    MAX-ACCESS   read-only
    STATUS       current
    DESCRIPTION
        "Cisco Firepower compute:Npu:operState managed object property"
    ::= { cfprApComputeNpuEntry 8 }

cfprApComputeNpuOperability OBJECT-TYPE
    SYNTAX       CfprApEquipmentOperability
    MAX-ACCESS   read-only
    STATUS       current
    DESCRIPTION
        "Cisco Firepower compute:Npu:operability managed object property"
    ::= { cfprApComputeNpuEntry 9 }

cfprApComputeNpuPerf OBJECT-TYPE
    SYNTAX       CfprApEquipmentSensorThresholdStatus
    MAX-ACCESS   read-only
    STATUS       current
    DESCRIPTION
        "Cisco Firepower compute:Npu:perf managed object property"
    ::= { cfprApComputeNpuEntry 10 }

cfprApComputeNpuPower OBJECT-TYPE
    SYNTAX       CfprApEquipmentPowerState
    MAX-ACCESS   read-only
    STATUS       current
    DESCRIPTION
        "Cisco Firepower compute:Npu:power managed object property"
    ::= { cfprApComputeNpuEntry 11 }

cfprApComputeNpuPresence OBJECT-TYPE
    SYNTAX       CfprApEquipmentPresence
    MAX-ACCESS   read-only
    STATUS       current
    DESCRIPTION
        "Cisco Firepower compute:Npu:presence managed object property"
    ::= { cfprApComputeNpuEntry 12 }

cfprApComputeNpuRevision OBJECT-TYPE
    SYNTAX       SnmpAdminString
    MAX-ACCESS   read-only
    STATUS       current
    DESCRIPTION
        "Cisco Firepower compute:Npu:revision managed object property"
    ::= { cfprApComputeNpuEntry 13 }

cfprApComputeNpuSerial OBJECT-TYPE
    SYNTAX       SnmpAdminString
    MAX-ACCESS   read-only
    STATUS       current
    DESCRIPTION
        "Cisco Firepower compute:Npu:serial managed object property"
    ::= { cfprApComputeNpuEntry 14 }

cfprApComputeNpuThermal OBJECT-TYPE
    SYNTAX       CfprApEquipmentSensorThresholdStatus
    MAX-ACCESS   read-only
    STATUS       current
    DESCRIPTION
        "Cisco Firepower compute:Npu:thermal managed object property"
    ::= { cfprApComputeNpuEntry 15 }

cfprApComputeNpuVendor OBJECT-TYPE
    SYNTAX       SnmpAdminString
    MAX-ACCESS   read-only
    STATUS       current
    DESCRIPTION
        "Cisco Firepower compute:Npu:vendor managed object property"
    ::= { cfprApComputeNpuEntry 16 }

cfprApComputeNpuVoltage OBJECT-TYPE
    SYNTAX       CfprApEquipmentSensorThresholdStatus
    MAX-ACCESS   read-only
    STATUS       current
    DESCRIPTION
        "Cisco Firepower compute:Npu:voltage managed object property"
    ::= { cfprApComputeNpuEntry 17 }

cfprApComputePCIeFatalCompletionStatsTable OBJECT-TYPE
    SYNTAX           SEQUENCE OF CfprApComputePCIeFatalCompletionStatsEntry
    MAX-ACCESS       not-accessible
    STATUS           current
    DESCRIPTION
        "Cisco Firepower compute:PCIeFatalCompletionStats
        managed object table"
    ::= { cfprApComputeObjects 30 }

cfprApComputePCIeFatalCompletionStatsEntry OBJECT-TYPE
    SYNTAX           CfprApComputePCIeFatalCompletionStatsEntry
    MAX-ACCESS       not-accessible
    STATUS           current
    DESCRIPTION
        "Entry for the cfprApComputePCIeFatalCompletionStatsTable table."
    INDEX { cfprApComputePCIeFatalCompletionStatsInstanceId }
    ::= { cfprApComputePCIeFatalCompletionStatsTable 1 }

CfprApComputePCIeFatalCompletionStatsEntry ::= SEQUENCE {
    cfprApComputePCIeFatalCompletionStatsInstanceId                  CfprApManagedObjectId,
    cfprApComputePCIeFatalCompletionStatsDn                          CfprApManagedObjectDn,
    cfprApComputePCIeFatalCompletionStatsRn                          SnmpAdminString,
    cfprApComputePCIeFatalCompletionStatsAbortErrors                 Counter32,
    cfprApComputePCIeFatalCompletionStatsAbortErrors15Min            Gauge32,
    cfprApComputePCIeFatalCompletionStatsAbortErrors15MinH           Gauge32,
    cfprApComputePCIeFatalCompletionStatsAbortErrors1Day             Gauge32,
    cfprApComputePCIeFatalCompletionStatsAbortErrors1DayH            Gauge32,
    cfprApComputePCIeFatalCompletionStatsAbortErrors1Hour            Gauge32,
    cfprApComputePCIeFatalCompletionStatsAbortErrors1HourH           Gauge32,
    cfprApComputePCIeFatalCompletionStatsAbortErrors1Week            Gauge32,
    cfprApComputePCIeFatalCompletionStatsAbortErrors1WeekH           Gauge32,
    cfprApComputePCIeFatalCompletionStatsAbortErrors2Weeks           Gauge32,
    cfprApComputePCIeFatalCompletionStatsAbortErrors2WeeksH          Gauge32,
    cfprApComputePCIeFatalCompletionStatsTimeoutErrors               Counter32,
    cfprApComputePCIeFatalCompletionStatsTimeoutErrors15Min          Gauge32,
    cfprApComputePCIeFatalCompletionStatsTimeoutErrors15MinH         Gauge32,
    cfprApComputePCIeFatalCompletionStatsTimeoutErrors1Day           Gauge32,
    cfprApComputePCIeFatalCompletionStatsTimeoutErrors1DayH          Gauge32,
    cfprApComputePCIeFatalCompletionStatsTimeoutErrors1Hour          Gauge32,
    cfprApComputePCIeFatalCompletionStatsTimeoutErrors1HourH         Gauge32,
    cfprApComputePCIeFatalCompletionStatsTimeoutErrors1Week          Gauge32,
    cfprApComputePCIeFatalCompletionStatsTimeoutErrors1WeekH         Gauge32,
    cfprApComputePCIeFatalCompletionStatsTimeoutErrors2Weeks         Gauge32,
    cfprApComputePCIeFatalCompletionStatsTimeoutErrors2WeeksH        Gauge32,
    cfprApComputePCIeFatalCompletionStatsIntervals                   Gauge32,
    cfprApComputePCIeFatalCompletionStatsSuspect                     TruthValue,
    cfprApComputePCIeFatalCompletionStatsThresholded                 CfprApComputePCIeFatalCompletionStatsThresholded,
    cfprApComputePCIeFatalCompletionStatsTimeCollected               DateAndTime,
    cfprApComputePCIeFatalCompletionStatsUnexpectedErrors            Counter32,
    cfprApComputePCIeFatalCompletionStatsUnexpectedErrors15Min       Gauge32,
    cfprApComputePCIeFatalCompletionStatsUnexpectedErrors15MinH      Gauge32,
    cfprApComputePCIeFatalCompletionStatsUnexpectedErrors1Day        Gauge32,
    cfprApComputePCIeFatalCompletionStatsUnexpectedErrors1DayH       Gauge32,
    cfprApComputePCIeFatalCompletionStatsUnexpectedErrors1Hour       Gauge32,
    cfprApComputePCIeFatalCompletionStatsUnexpectedErrors1HourH      Gauge32,
    cfprApComputePCIeFatalCompletionStatsUnexpectedErrors1Week       Gauge32,
    cfprApComputePCIeFatalCompletionStatsUnexpectedErrors1WeekH      Gauge32,
    cfprApComputePCIeFatalCompletionStatsUnexpectedErrors2Weeks      Gauge32,
    cfprApComputePCIeFatalCompletionStatsUnexpectedErrors2WeeksH     Gauge32,
    cfprApComputePCIeFatalCompletionStatsUpdate                      Gauge32
}

cfprApComputePCIeFatalCompletionStatsInstanceId OBJECT-TYPE
    SYNTAX       CfprApManagedObjectId
    MAX-ACCESS   not-accessible
    STATUS       current
    DESCRIPTION
        "Instance identifier of the managed object."
    ::= { cfprApComputePCIeFatalCompletionStatsEntry 1 }

cfprApComputePCIeFatalCompletionStatsDn OBJECT-TYPE
    SYNTAX       CfprApManagedObjectDn
    MAX-ACCESS   read-only
    STATUS       current
    DESCRIPTION
        "Cisco Firepower compute:PCIeFatalCompletionStats:dn
        managed object property"
    ::= { cfprApComputePCIeFatalCompletionStatsEntry 2 }

cfprApComputePCIeFatalCompletionStatsRn OBJECT-TYPE
    SYNTAX       SnmpAdminString
    MAX-ACCESS   read-only
    STATUS       current
    DESCRIPTION
        "Cisco Firepower compute:PCIeFatalCompletionStats:rn
        managed object property"
    ::= { cfprApComputePCIeFatalCompletionStatsEntry 3 }

cfprApComputePCIeFatalCompletionStatsAbortErrors OBJECT-TYPE
    SYNTAX       Counter32
    MAX-ACCESS   read-only
    STATUS       current
    DESCRIPTION
        "Cisco Firepower compute:PCIeFatalCompletionStats:AbortErrors
        managed object property"
    ::= { cfprApComputePCIeFatalCompletionStatsEntry 4 }

cfprApComputePCIeFatalCompletionStatsAbortErrors15Min OBJECT-TYPE
    SYNTAX       Gauge32
    MAX-ACCESS   read-only
    STATUS       current
    DESCRIPTION
        "Cisco Firepower compute:PCIeFatalCompletionStats:AbortErrors15Min
         managed object property"
    ::= { cfprApComputePCIeFatalCompletionStatsEntry 5 }

cfprApComputePCIeFatalCompletionStatsAbortErrors15MinH OBJECT-TYPE
    SYNTAX       Gauge32
    MAX-ACCESS   read-only
    STATUS       current
    DESCRIPTION
        "Cisco Firepower compute:PCIeFatalCompletionStats:AbortErrors15Min
        H managed object property"
    ::= { cfprApComputePCIeFatalCompletionStatsEntry 6 }

cfprApComputePCIeFatalCompletionStatsAbortErrors1Day OBJECT-TYPE
    SYNTAX       Gauge32
    MAX-ACCESS   read-only
    STATUS       current
    DESCRIPTION
        "Cisco Firepower compute:PCIeFatalCompletionStats:AbortErrors1Day
        managed object property"
    ::= { cfprApComputePCIeFatalCompletionStatsEntry 7 }

cfprApComputePCIeFatalCompletionStatsAbortErrors1DayH OBJECT-TYPE
    SYNTAX       Gauge32
    MAX-ACCESS   read-only
    STATUS       current
    DESCRIPTION
        "Cisco Firepower compute:PCIeFatalCompletionStats:AbortErrors1DayH
         managed object property"
    ::= { cfprApComputePCIeFatalCompletionStatsEntry 8 }

cfprApComputePCIeFatalCompletionStatsAbortErrors1Hour OBJECT-TYPE
    SYNTAX       Gauge32
    MAX-ACCESS   read-only
    STATUS       current
    DESCRIPTION
        "Cisco Firepower compute:PCIeFatalCompletionStats:AbortErrors1Hour
         managed object property"
    ::= { cfprApComputePCIeFatalCompletionStatsEntry 9 }

cfprApComputePCIeFatalCompletionStatsAbortErrors1HourH OBJECT-TYPE
    SYNTAX       Gauge32
    MAX-ACCESS   read-only
    STATUS       current
    DESCRIPTION
        "Cisco Firepower compute:PCIeFatalCompletionStats:AbortErrors1Hour
        H managed object property"
    ::= { cfprApComputePCIeFatalCompletionStatsEntry 10 }

cfprApComputePCIeFatalCompletionStatsAbortErrors1Week OBJECT-TYPE
    SYNTAX       Gauge32
    MAX-ACCESS   read-only
    STATUS       current
    DESCRIPTION
        "Cisco Firepower compute:PCIeFatalCompletionStats:AbortErrors1Week
         managed object property"
    ::= { cfprApComputePCIeFatalCompletionStatsEntry 11 }

cfprApComputePCIeFatalCompletionStatsAbortErrors1WeekH OBJECT-TYPE
    SYNTAX       Gauge32
    MAX-ACCESS   read-only
    STATUS       current
    DESCRIPTION
        "Cisco Firepower compute:PCIeFatalCompletionStats:AbortErrors1Week
        H managed object property"
    ::= { cfprApComputePCIeFatalCompletionStatsEntry 12 }

cfprApComputePCIeFatalCompletionStatsAbortErrors2Weeks OBJECT-TYPE
    SYNTAX       Gauge32
    MAX-ACCESS   read-only
    STATUS       current
    DESCRIPTION
        "Cisco Firepower compute:PCIeFatalCompletionStats:AbortErrors2Week
        s managed object property"
    ::= { cfprApComputePCIeFatalCompletionStatsEntry 13 }

cfprApComputePCIeFatalCompletionStatsAbortErrors2WeeksH OBJECT-TYPE
    SYNTAX       Gauge32
    MAX-ACCESS   read-only
    STATUS       current
    DESCRIPTION
        "Cisco Firepower compute:PCIeFatalCompletionStats:AbortErrors2Week
        sH managed object property"
    ::= { cfprApComputePCIeFatalCompletionStatsEntry 14 }

cfprApComputePCIeFatalCompletionStatsTimeoutErrors OBJECT-TYPE
    SYNTAX       Counter32
    MAX-ACCESS   read-only
    STATUS       current
    DESCRIPTION
        "Cisco Firepower compute:PCIeFatalCompletionStats:TimeoutErrors
        managed object property"
    ::= { cfprApComputePCIeFatalCompletionStatsEntry 15 }

cfprApComputePCIeFatalCompletionStatsTimeoutErrors15Min OBJECT-TYPE
    SYNTAX       Gauge32
    MAX-ACCESS   read-only
    STATUS       current
    DESCRIPTION
        "Cisco Firepower compute:PCIeFatalCompletionStats:TimeoutErrors15M
        in managed object property"
    ::= { cfprApComputePCIeFatalCompletionStatsEntry 16 }

cfprApComputePCIeFatalCompletionStatsTimeoutErrors15MinH OBJECT-TYPE
    SYNTAX       Gauge32
    MAX-ACCESS   read-only
    STATUS       current
    DESCRIPTION
        "Cisco Firepower compute:PCIeFatalCompletionStats:TimeoutErrors15M
        inH managed object property"
    ::= { cfprApComputePCIeFatalCompletionStatsEntry 17 }

cfprApComputePCIeFatalCompletionStatsTimeoutErrors1Day OBJECT-TYPE
    SYNTAX       Gauge32
    MAX-ACCESS   read-only
    STATUS       current
    DESCRIPTION
        "Cisco Firepower compute:PCIeFatalCompletionStats:TimeoutErrors1Da
        y managed object property"
    ::= { cfprApComputePCIeFatalCompletionStatsEntry 18 }

cfprApComputePCIeFatalCompletionStatsTimeoutErrors1DayH OBJECT-TYPE
    SYNTAX       Gauge32
    MAX-ACCESS   read-only
    STATUS       current
    DESCRIPTION
        "Cisco Firepower compute:PCIeFatalCompletionStats:TimeoutErrors1Da
        yH managed object property"
    ::= { cfprApComputePCIeFatalCompletionStatsEntry 19 }

cfprApComputePCIeFatalCompletionStatsTimeoutErrors1Hour OBJECT-TYPE
    SYNTAX       Gauge32
    MAX-ACCESS   read-only
    STATUS       current
    DESCRIPTION
        "Cisco Firepower compute:PCIeFatalCompletionStats:TimeoutErrors1Ho
        ur managed object property"
    ::= { cfprApComputePCIeFatalCompletionStatsEntry 20 }

cfprApComputePCIeFatalCompletionStatsTimeoutErrors1HourH OBJECT-TYPE
    SYNTAX       Gauge32
    MAX-ACCESS   read-only
    STATUS       current
    DESCRIPTION
        "Cisco Firepower compute:PCIeFatalCompletionStats:TimeoutErrors1Ho
        urH managed object property"
    ::= { cfprApComputePCIeFatalCompletionStatsEntry 21 }

cfprApComputePCIeFatalCompletionStatsTimeoutErrors1Week OBJECT-TYPE
    SYNTAX       Gauge32
    MAX-ACCESS   read-only
    STATUS       current
    DESCRIPTION
        "Cisco Firepower compute:PCIeFatalCompletionStats:TimeoutErrors1We
        ek managed object property"
    ::= { cfprApComputePCIeFatalCompletionStatsEntry 22 }

cfprApComputePCIeFatalCompletionStatsTimeoutErrors1WeekH OBJECT-TYPE
    SYNTAX       Gauge32
    MAX-ACCESS   read-only
    STATUS       current
    DESCRIPTION
        "Cisco Firepower compute:PCIeFatalCompletionStats:TimeoutErrors1We
        ekH managed object property"
    ::= { cfprApComputePCIeFatalCompletionStatsEntry 23 }

cfprApComputePCIeFatalCompletionStatsTimeoutErrors2Weeks OBJECT-TYPE
    SYNTAX       Gauge32
    MAX-ACCESS   read-only
    STATUS       current
    DESCRIPTION
        "Cisco Firepower compute:PCIeFatalCompletionStats:TimeoutErrors2We
        eks managed object property"
    ::= { cfprApComputePCIeFatalCompletionStatsEntry 24 }

cfprApComputePCIeFatalCompletionStatsTimeoutErrors2WeeksH OBJECT-TYPE
    SYNTAX       Gauge32
    MAX-ACCESS   read-only
    STATUS       current
    DESCRIPTION
        "Cisco Firepower compute:PCIeFatalCompletionStats:TimeoutErrors2We
        eksH managed object property"
    ::= { cfprApComputePCIeFatalCompletionStatsEntry 25 }

cfprApComputePCIeFatalCompletionStatsIntervals OBJECT-TYPE
    SYNTAX       Gauge32
    MAX-ACCESS   read-only
    STATUS       current
    DESCRIPTION
        "Cisco Firepower compute:PCIeFatalCompletionStats:intervals
        managed object property"
    ::= { cfprApComputePCIeFatalCompletionStatsEntry 26 }

cfprApComputePCIeFatalCompletionStatsSuspect OBJECT-TYPE
    SYNTAX       TruthValue
    MAX-ACCESS   read-only
    STATUS       current
    DESCRIPTION
        "Cisco Firepower compute:PCIeFatalCompletionStats:suspect
        managed object property"
    ::= { cfprApComputePCIeFatalCompletionStatsEntry 27 }

cfprApComputePCIeFatalCompletionStatsThresholded OBJECT-TYPE
    SYNTAX       CfprApComputePCIeFatalCompletionStatsThresholded
    MAX-ACCESS   read-only
    STATUS       current
    DESCRIPTION
        "Cisco Firepower compute:PCIeFatalCompletionStats:thresholded
        managed object property"
    ::= { cfprApComputePCIeFatalCompletionStatsEntry 28 }

cfprApComputePCIeFatalCompletionStatsTimeCollected OBJECT-TYPE
    SYNTAX       DateAndTime
    MAX-ACCESS   read-only
    STATUS       current
    DESCRIPTION
        "Cisco Firepower compute:PCIeFatalCompletionStats:timeCollected
        managed object property"
    ::= { cfprApComputePCIeFatalCompletionStatsEntry 29 }

cfprApComputePCIeFatalCompletionStatsUnexpectedErrors OBJECT-TYPE
    SYNTAX       Counter32
    MAX-ACCESS   read-only
    STATUS       current
    DESCRIPTION
        "Cisco Firepower compute:PCIeFatalCompletionStats:unexpectedErrors
         managed object property"
    ::= { cfprApComputePCIeFatalCompletionStatsEntry 30 }

cfprApComputePCIeFatalCompletionStatsUnexpectedErrors15Min OBJECT-TYPE
    SYNTAX       Gauge32
    MAX-ACCESS   read-only
    STATUS       current
    DESCRIPTION
        "Cisco Firepower compute:PCIeFatalCompletionStats:unexpectedErrors
        15Min managed object property"
    ::= { cfprApComputePCIeFatalCompletionStatsEntry 31 }

cfprApComputePCIeFatalCompletionStatsUnexpectedErrors15MinH OBJECT-TYPE
    SYNTAX       Gauge32
    MAX-ACCESS   read-only
    STATUS       current
    DESCRIPTION
        "Cisco Firepower compute:PCIeFatalCompletionStats:unexpectedErrors
        15MinH managed object property"
    ::= { cfprApComputePCIeFatalCompletionStatsEntry 32 }

cfprApComputePCIeFatalCompletionStatsUnexpectedErrors1Day OBJECT-TYPE
    SYNTAX       Gauge32
    MAX-ACCESS   read-only
    STATUS       current
    DESCRIPTION
        "Cisco Firepower compute:PCIeFatalCompletionStats:unexpectedErrors
        1Day managed object property"
    ::= { cfprApComputePCIeFatalCompletionStatsEntry 33 }

cfprApComputePCIeFatalCompletionStatsUnexpectedErrors1DayH OBJECT-TYPE
    SYNTAX       Gauge32
    MAX-ACCESS   read-only
    STATUS       current
    DESCRIPTION
        "Cisco Firepower compute:PCIeFatalCompletionStats:unexpectedErrors
        1DayH managed object property"
    ::= { cfprApComputePCIeFatalCompletionStatsEntry 34 }

cfprApComputePCIeFatalCompletionStatsUnexpectedErrors1Hour OBJECT-TYPE
    SYNTAX       Gauge32
    MAX-ACCESS   read-only
    STATUS       current
    DESCRIPTION
        "Cisco Firepower compute:PCIeFatalCompletionStats:unexpectedErrors
        1Hour managed object property"
    ::= { cfprApComputePCIeFatalCompletionStatsEntry 35 }

cfprApComputePCIeFatalCompletionStatsUnexpectedErrors1HourH OBJECT-TYPE
    SYNTAX       Gauge32
    MAX-ACCESS   read-only
    STATUS       current
    DESCRIPTION
        "Cisco Firepower compute:PCIeFatalCompletionStats:unexpectedErrors
        1HourH managed object property"
    ::= { cfprApComputePCIeFatalCompletionStatsEntry 36 }

cfprApComputePCIeFatalCompletionStatsUnexpectedErrors1Week OBJECT-TYPE
    SYNTAX       Gauge32
    MAX-ACCESS   read-only
    STATUS       current
    DESCRIPTION
        "Cisco Firepower compute:PCIeFatalCompletionStats:unexpectedErrors
        1Week managed object property"
    ::= { cfprApComputePCIeFatalCompletionStatsEntry 37 }

cfprApComputePCIeFatalCompletionStatsUnexpectedErrors1WeekH OBJECT-TYPE
    SYNTAX       Gauge32
    MAX-ACCESS   read-only
    STATUS       current
    DESCRIPTION
        "Cisco Firepower compute:PCIeFatalCompletionStats:unexpectedErrors
        1WeekH managed object property"
    ::= { cfprApComputePCIeFatalCompletionStatsEntry 38 }

cfprApComputePCIeFatalCompletionStatsUnexpectedErrors2Weeks OBJECT-TYPE
    SYNTAX       Gauge32
    MAX-ACCESS   read-only
    STATUS       current
    DESCRIPTION
        "Cisco Firepower compute:PCIeFatalCompletionStats:unexpectedErrors
        2Weeks managed object property"
    ::= { cfprApComputePCIeFatalCompletionStatsEntry 39 }

cfprApComputePCIeFatalCompletionStatsUnexpectedErrors2WeeksH OBJECT-TYPE
    SYNTAX       Gauge32
    MAX-ACCESS   read-only
    STATUS       current
    DESCRIPTION
        "Cisco Firepower compute:PCIeFatalCompletionStats:unexpectedErrors
        2WeeksH managed object property"
    ::= { cfprApComputePCIeFatalCompletionStatsEntry 40 }

cfprApComputePCIeFatalCompletionStatsUpdate OBJECT-TYPE
    SYNTAX       Gauge32
    MAX-ACCESS   read-only
    STATUS       current
    DESCRIPTION
        "Cisco Firepower compute:PCIeFatalCompletionStats:update
        managed object property"
    ::= { cfprApComputePCIeFatalCompletionStatsEntry 41 }

cfprApComputePCIeFatalProtocolStatsTable OBJECT-TYPE
    SYNTAX           SEQUENCE OF CfprApComputePCIeFatalProtocolStatsEntry
    MAX-ACCESS       not-accessible
    STATUS           current
    DESCRIPTION
        "Cisco Firepower compute:PCIeFatalProtocolStats
        managed object table"
    ::= { cfprApComputeObjects 31 }

cfprApComputePCIeFatalProtocolStatsEntry OBJECT-TYPE
    SYNTAX           CfprApComputePCIeFatalProtocolStatsEntry
    MAX-ACCESS       not-accessible
    STATUS           current
    DESCRIPTION
        "Entry for the cfprApComputePCIeFatalProtocolStatsTable table."
    INDEX { cfprApComputePCIeFatalProtocolStatsInstanceId }
    ::= { cfprApComputePCIeFatalProtocolStatsTable 1 }

CfprApComputePCIeFatalProtocolStatsEntry ::= SEQUENCE {
    cfprApComputePCIeFatalProtocolStatsInstanceId                    CfprApManagedObjectId,
    cfprApComputePCIeFatalProtocolStatsDn                            CfprApManagedObjectDn,
    cfprApComputePCIeFatalProtocolStatsRn                            SnmpAdminString,
    cfprApComputePCIeFatalProtocolStatsDllpErrors                    Counter32,
    cfprApComputePCIeFatalProtocolStatsDllpErrors15Min               Gauge32,
    cfprApComputePCIeFatalProtocolStatsDllpErrors15MinH              Gauge32,
    cfprApComputePCIeFatalProtocolStatsDllpErrors1Day                Gauge32,
    cfprApComputePCIeFatalProtocolStatsDllpErrors1DayH               Gauge32,
    cfprApComputePCIeFatalProtocolStatsDllpErrors1Hour               Gauge32,
    cfprApComputePCIeFatalProtocolStatsDllpErrors1HourH              Gauge32,
    cfprApComputePCIeFatalProtocolStatsDllpErrors1Week               Gauge32,
    cfprApComputePCIeFatalProtocolStatsDllpErrors1WeekH              Gauge32,
    cfprApComputePCIeFatalProtocolStatsDllpErrors2Weeks              Gauge32,
    cfprApComputePCIeFatalProtocolStatsDllpErrors2WeeksH             Gauge32,
    cfprApComputePCIeFatalProtocolStatsFlowControlErrors             Counter32,
    cfprApComputePCIeFatalProtocolStatsFlowControlErrors15Min        Gauge32,
    cfprApComputePCIeFatalProtocolStatsFlowControlErrors15MinH       Gauge32,
    cfprApComputePCIeFatalProtocolStatsFlowControlErrors1Day         Gauge32,
    cfprApComputePCIeFatalProtocolStatsFlowControlErrors1DayH        Gauge32,
    cfprApComputePCIeFatalProtocolStatsFlowControlErrors1Hour        Gauge32,
    cfprApComputePCIeFatalProtocolStatsFlowControlErrors1HourH       Gauge32,
    cfprApComputePCIeFatalProtocolStatsFlowControlErrors1Week        Gauge32,
    cfprApComputePCIeFatalProtocolStatsFlowControlErrors1WeekH       Gauge32,
    cfprApComputePCIeFatalProtocolStatsFlowControlErrors2Weeks       Gauge32,
    cfprApComputePCIeFatalProtocolStatsFlowControlErrors2WeeksH      Gauge32,
    cfprApComputePCIeFatalProtocolStatsIntervals                     Gauge32,
    cfprApComputePCIeFatalProtocolStatsSuspect                       TruthValue,
    cfprApComputePCIeFatalProtocolStatsThresholded                   CfprApComputePCIeFatalProtocolStatsThresholded,
    cfprApComputePCIeFatalProtocolStatsTimeCollected                 DateAndTime,
    cfprApComputePCIeFatalProtocolStatsUpdate                        Gauge32
}

cfprApComputePCIeFatalProtocolStatsInstanceId OBJECT-TYPE
    SYNTAX       CfprApManagedObjectId
    MAX-ACCESS   not-accessible
    STATUS       current
    DESCRIPTION
        "Instance identifier of the managed object."
    ::= { cfprApComputePCIeFatalProtocolStatsEntry 1 }

cfprApComputePCIeFatalProtocolStatsDn OBJECT-TYPE
    SYNTAX       CfprApManagedObjectDn
    MAX-ACCESS   read-only
    STATUS       current
    DESCRIPTION
        "Cisco Firepower compute:PCIeFatalProtocolStats:dn
        managed object property"
    ::= { cfprApComputePCIeFatalProtocolStatsEntry 2 }

cfprApComputePCIeFatalProtocolStatsRn OBJECT-TYPE
    SYNTAX       SnmpAdminString
    MAX-ACCESS   read-only
    STATUS       current
    DESCRIPTION
        "Cisco Firepower compute:PCIeFatalProtocolStats:rn
        managed object property"
    ::= { cfprApComputePCIeFatalProtocolStatsEntry 3 }

cfprApComputePCIeFatalProtocolStatsDllpErrors OBJECT-TYPE
    SYNTAX       Counter32
    MAX-ACCESS   read-only
    STATUS       current
    DESCRIPTION
        "Cisco Firepower compute:PCIeFatalProtocolStats:dllpErrors
        managed object property"
    ::= { cfprApComputePCIeFatalProtocolStatsEntry 4 }

cfprApComputePCIeFatalProtocolStatsDllpErrors15Min OBJECT-TYPE
    SYNTAX       Gauge32
    MAX-ACCESS   read-only
    STATUS       current
    DESCRIPTION
        "Cisco Firepower compute:PCIeFatalProtocolStats:dllpErrors15Min
        managed object property"
    ::= { cfprApComputePCIeFatalProtocolStatsEntry 5 }

cfprApComputePCIeFatalProtocolStatsDllpErrors15MinH OBJECT-TYPE
    SYNTAX       Gauge32
    MAX-ACCESS   read-only
    STATUS       current
    DESCRIPTION
        "Cisco Firepower compute:PCIeFatalProtocolStats:dllpErrors15MinH
        managed object property"
    ::= { cfprApComputePCIeFatalProtocolStatsEntry 6 }

cfprApComputePCIeFatalProtocolStatsDllpErrors1Day OBJECT-TYPE
    SYNTAX       Gauge32
    MAX-ACCESS   read-only
    STATUS       current
    DESCRIPTION
        "Cisco Firepower compute:PCIeFatalProtocolStats:dllpErrors1Day
        managed object property"
    ::= { cfprApComputePCIeFatalProtocolStatsEntry 7 }

cfprApComputePCIeFatalProtocolStatsDllpErrors1DayH OBJECT-TYPE
    SYNTAX       Gauge32
    MAX-ACCESS   read-only
    STATUS       current
    DESCRIPTION
        "Cisco Firepower compute:PCIeFatalProtocolStats:dllpErrors1DayH
        managed object property"
    ::= { cfprApComputePCIeFatalProtocolStatsEntry 8 }

cfprApComputePCIeFatalProtocolStatsDllpErrors1Hour OBJECT-TYPE
    SYNTAX       Gauge32
    MAX-ACCESS   read-only
    STATUS       current
    DESCRIPTION
        "Cisco Firepower compute:PCIeFatalProtocolStats:dllpErrors1Hour
        managed object property"
    ::= { cfprApComputePCIeFatalProtocolStatsEntry 9 }

cfprApComputePCIeFatalProtocolStatsDllpErrors1HourH OBJECT-TYPE
    SYNTAX       Gauge32
    MAX-ACCESS   read-only
    STATUS       current
    DESCRIPTION
        "Cisco Firepower compute:PCIeFatalProtocolStats:dllpErrors1HourH
        managed object property"
    ::= { cfprApComputePCIeFatalProtocolStatsEntry 10 }

cfprApComputePCIeFatalProtocolStatsDllpErrors1Week OBJECT-TYPE
    SYNTAX       Gauge32
    MAX-ACCESS   read-only
    STATUS       current
    DESCRIPTION
        "Cisco Firepower compute:PCIeFatalProtocolStats:dllpErrors1Week
        managed object property"
    ::= { cfprApComputePCIeFatalProtocolStatsEntry 11 }

cfprApComputePCIeFatalProtocolStatsDllpErrors1WeekH OBJECT-TYPE
    SYNTAX       Gauge32
    MAX-ACCESS   read-only
    STATUS       current
    DESCRIPTION
        "Cisco Firepower compute:PCIeFatalProtocolStats:dllpErrors1WeekH
        managed object property"
    ::= { cfprApComputePCIeFatalProtocolStatsEntry 12 }

cfprApComputePCIeFatalProtocolStatsDllpErrors2Weeks OBJECT-TYPE
    SYNTAX       Gauge32
    MAX-ACCESS   read-only
    STATUS       current
    DESCRIPTION
        "Cisco Firepower compute:PCIeFatalProtocolStats:dllpErrors2Weeks
        managed object property"
    ::= { cfprApComputePCIeFatalProtocolStatsEntry 13 }

cfprApComputePCIeFatalProtocolStatsDllpErrors2WeeksH OBJECT-TYPE
    SYNTAX       Gauge32
    MAX-ACCESS   read-only
    STATUS       current
    DESCRIPTION
        "Cisco Firepower compute:PCIeFatalProtocolStats:dllpErrors2WeeksH
        managed object property"
    ::= { cfprApComputePCIeFatalProtocolStatsEntry 14 }

cfprApComputePCIeFatalProtocolStatsFlowControlErrors OBJECT-TYPE
    SYNTAX       Counter32
    MAX-ACCESS   read-only
    STATUS       current
    DESCRIPTION
        "Cisco Firepower compute:PCIeFatalProtocolStats:flowControlErrors
        managed object property"
    ::= { cfprApComputePCIeFatalProtocolStatsEntry 15 }

cfprApComputePCIeFatalProtocolStatsFlowControlErrors15Min OBJECT-TYPE
    SYNTAX       Gauge32
    MAX-ACCESS   read-only
    STATUS       current
    DESCRIPTION
        "Cisco Firepower compute:PCIeFatalProtocolStats:flowControlErrors1
        5Min managed object property"
    ::= { cfprApComputePCIeFatalProtocolStatsEntry 16 }

cfprApComputePCIeFatalProtocolStatsFlowControlErrors15MinH OBJECT-TYPE
    SYNTAX       Gauge32
    MAX-ACCESS   read-only
    STATUS       current
    DESCRIPTION
        "Cisco Firepower compute:PCIeFatalProtocolStats:flowControlErrors1
        5MinH managed object property"
    ::= { cfprApComputePCIeFatalProtocolStatsEntry 17 }

cfprApComputePCIeFatalProtocolStatsFlowControlErrors1Day OBJECT-TYPE
    SYNTAX       Gauge32
    MAX-ACCESS   read-only
    STATUS       current
    DESCRIPTION
        "Cisco Firepower compute:PCIeFatalProtocolStats:flowControlErrors1
        Day managed object property"
    ::= { cfprApComputePCIeFatalProtocolStatsEntry 18 }

cfprApComputePCIeFatalProtocolStatsFlowControlErrors1DayH OBJECT-TYPE
    SYNTAX       Gauge32
    MAX-ACCESS   read-only
    STATUS       current
    DESCRIPTION
        "Cisco Firepower compute:PCIeFatalProtocolStats:flowControlErrors1
        DayH managed object property"
    ::= { cfprApComputePCIeFatalProtocolStatsEntry 19 }

cfprApComputePCIeFatalProtocolStatsFlowControlErrors1Hour OBJECT-TYPE
    SYNTAX       Gauge32
    MAX-ACCESS   read-only
    STATUS       current
    DESCRIPTION
        "Cisco Firepower compute:PCIeFatalProtocolStats:flowControlErrors1
        Hour managed object property"
    ::= { cfprApComputePCIeFatalProtocolStatsEntry 20 }

cfprApComputePCIeFatalProtocolStatsFlowControlErrors1HourH OBJECT-TYPE
    SYNTAX       Gauge32
    MAX-ACCESS   read-only
    STATUS       current
    DESCRIPTION
        "Cisco Firepower compute:PCIeFatalProtocolStats:flowControlErrors1
        HourH managed object property"
    ::= { cfprApComputePCIeFatalProtocolStatsEntry 21 }

cfprApComputePCIeFatalProtocolStatsFlowControlErrors1Week OBJECT-TYPE
    SYNTAX       Gauge32
    MAX-ACCESS   read-only
    STATUS       current
    DESCRIPTION
        "Cisco Firepower compute:PCIeFatalProtocolStats:flowControlErrors1
        Week managed object property"
    ::= { cfprApComputePCIeFatalProtocolStatsEntry 22 }

cfprApComputePCIeFatalProtocolStatsFlowControlErrors1WeekH OBJECT-TYPE
    SYNTAX       Gauge32
    MAX-ACCESS   read-only
    STATUS       current
    DESCRIPTION
        "Cisco Firepower compute:PCIeFatalProtocolStats:flowControlErrors1
        WeekH managed object property"
    ::= { cfprApComputePCIeFatalProtocolStatsEntry 23 }

cfprApComputePCIeFatalProtocolStatsFlowControlErrors2Weeks OBJECT-TYPE
    SYNTAX       Gauge32
    MAX-ACCESS   read-only
    STATUS       current
    DESCRIPTION
        "Cisco Firepower compute:PCIeFatalProtocolStats:flowControlErrors2
        Weeks managed object property"
    ::= { cfprApComputePCIeFatalProtocolStatsEntry 24 }

cfprApComputePCIeFatalProtocolStatsFlowControlErrors2WeeksH OBJECT-TYPE
    SYNTAX       Gauge32
    MAX-ACCESS   read-only
    STATUS       current
    DESCRIPTION
        "Cisco Firepower compute:PCIeFatalProtocolStats:flowControlErrors2
        WeeksH managed object property"
    ::= { cfprApComputePCIeFatalProtocolStatsEntry 25 }

cfprApComputePCIeFatalProtocolStatsIntervals OBJECT-TYPE
    SYNTAX       Gauge32
    MAX-ACCESS   read-only
    STATUS       current
    DESCRIPTION
        "Cisco Firepower compute:PCIeFatalProtocolStats:intervals
        managed object property"
    ::= { cfprApComputePCIeFatalProtocolStatsEntry 26 }

cfprApComputePCIeFatalProtocolStatsSuspect OBJECT-TYPE
    SYNTAX       TruthValue
    MAX-ACCESS   read-only
    STATUS       current
    DESCRIPTION
        "Cisco Firepower compute:PCIeFatalProtocolStats:suspect
        managed object property"
    ::= { cfprApComputePCIeFatalProtocolStatsEntry 27 }

cfprApComputePCIeFatalProtocolStatsThresholded OBJECT-TYPE
    SYNTAX       CfprApComputePCIeFatalProtocolStatsThresholded
    MAX-ACCESS   read-only
    STATUS       current
    DESCRIPTION
        "Cisco Firepower compute:PCIeFatalProtocolStats:thresholded
        managed object property"
    ::= { cfprApComputePCIeFatalProtocolStatsEntry 28 }

cfprApComputePCIeFatalProtocolStatsTimeCollected OBJECT-TYPE
    SYNTAX       DateAndTime
    MAX-ACCESS   read-only
    STATUS       current
    DESCRIPTION
        "Cisco Firepower compute:PCIeFatalProtocolStats:timeCollected
        managed object property"
    ::= { cfprApComputePCIeFatalProtocolStatsEntry 29 }

cfprApComputePCIeFatalProtocolStatsUpdate OBJECT-TYPE
    SYNTAX       Gauge32
    MAX-ACCESS   read-only
    STATUS       current
    DESCRIPTION
        "Cisco Firepower compute:PCIeFatalProtocolStats:update
        managed object property"
    ::= { cfprApComputePCIeFatalProtocolStatsEntry 30 }

cfprApComputePCIeFatalReceiveStatsTable OBJECT-TYPE
    SYNTAX           SEQUENCE OF CfprApComputePCIeFatalReceiveStatsEntry
    MAX-ACCESS       not-accessible
    STATUS           current
    DESCRIPTION
        "Cisco Firepower compute:PCIeFatalReceiveStats
        managed object table"
    ::= { cfprApComputeObjects 32 }

cfprApComputePCIeFatalReceiveStatsEntry OBJECT-TYPE
    SYNTAX           CfprApComputePCIeFatalReceiveStatsEntry
    MAX-ACCESS       not-accessible
    STATUS           current
    DESCRIPTION
        "Entry for the cfprApComputePCIeFatalReceiveStatsTable table."
    INDEX { cfprApComputePCIeFatalReceiveStatsInstanceId }
    ::= { cfprApComputePCIeFatalReceiveStatsTable 1 }

CfprApComputePCIeFatalReceiveStatsEntry ::= SEQUENCE {
    cfprApComputePCIeFatalReceiveStatsInstanceId                     CfprApManagedObjectId,
    cfprApComputePCIeFatalReceiveStatsDn                             CfprApManagedObjectDn,
    cfprApComputePCIeFatalReceiveStatsRn                             SnmpAdminString,
    cfprApComputePCIeFatalReceiveStatsBufferOverflowErrors           Counter32,
    cfprApComputePCIeFatalReceiveStatsBufferOverflowErrors15Min      Gauge32,
    cfprApComputePCIeFatalReceiveStatsBufferOverflowErrors15MinH     Gauge32,
    cfprApComputePCIeFatalReceiveStatsBufferOverflowErrors1Day       Gauge32,
    cfprApComputePCIeFatalReceiveStatsBufferOverflowErrors1DayH      Gauge32,
    cfprApComputePCIeFatalReceiveStatsBufferOverflowErrors1Hour      Gauge32,
    cfprApComputePCIeFatalReceiveStatsBufferOverflowErrors1HourH     Gauge32,
    cfprApComputePCIeFatalReceiveStatsBufferOverflowErrors1Week      Gauge32,
    cfprApComputePCIeFatalReceiveStatsBufferOverflowErrors1WeekH     Gauge32,
    cfprApComputePCIeFatalReceiveStatsBufferOverflowErrors2Weeks     Gauge32,
    cfprApComputePCIeFatalReceiveStatsBufferOverflowErrors2WeeksH    Gauge32,
    cfprApComputePCIeFatalReceiveStatsErrFatalErrors                 Counter32,
    cfprApComputePCIeFatalReceiveStatsErrFatalErrors15Min            Gauge32,
    cfprApComputePCIeFatalReceiveStatsErrFatalErrors15MinH           Gauge32,
    cfprApComputePCIeFatalReceiveStatsErrFatalErrors1Day             Gauge32,
    cfprApComputePCIeFatalReceiveStatsErrFatalErrors1DayH            Gauge32,
    cfprApComputePCIeFatalReceiveStatsErrFatalErrors1Hour            Gauge32,
    cfprApComputePCIeFatalReceiveStatsErrFatalErrors1HourH           Gauge32,
    cfprApComputePCIeFatalReceiveStatsErrFatalErrors1Week            Gauge32,
    cfprApComputePCIeFatalReceiveStatsErrFatalErrors1WeekH           Gauge32,
    cfprApComputePCIeFatalReceiveStatsErrFatalErrors2Weeks           Gauge32,
    cfprApComputePCIeFatalReceiveStatsErrFatalErrors2WeeksH          Gauge32,
    cfprApComputePCIeFatalReceiveStatsErrNonFatalErrors              Counter32,
    cfprApComputePCIeFatalReceiveStatsErrNonFatalErrors15Min         Gauge32,
    cfprApComputePCIeFatalReceiveStatsErrNonFatalErrors15MinH        Gauge32,
    cfprApComputePCIeFatalReceiveStatsErrNonFatalErrors1Day          Gauge32,
    cfprApComputePCIeFatalReceiveStatsErrNonFatalErrors1DayH         Gauge32,
    cfprApComputePCIeFatalReceiveStatsErrNonFatalErrors1Hour         Gauge32,
    cfprApComputePCIeFatalReceiveStatsErrNonFatalErrors1HourH        Gauge32,
    cfprApComputePCIeFatalReceiveStatsErrNonFatalErrors1Week         Gauge32,
    cfprApComputePCIeFatalReceiveStatsErrNonFatalErrors1WeekH        Gauge32,
    cfprApComputePCIeFatalReceiveStatsErrNonFatalErrors2Weeks        Gauge32,
    cfprApComputePCIeFatalReceiveStatsErrNonFatalErrors2WeeksH       Gauge32,
    cfprApComputePCIeFatalReceiveStatsIntervals                      Gauge32,
    cfprApComputePCIeFatalReceiveStatsSuspect                        TruthValue,
    cfprApComputePCIeFatalReceiveStatsThresholded                    CfprApComputePCIeFatalReceiveStatsThresholded,
    cfprApComputePCIeFatalReceiveStatsTimeCollected                  DateAndTime,
    cfprApComputePCIeFatalReceiveStatsUnsupportedRequestErrors       Counter32,
    cfprApComputePCIeFatalReceiveStatsUnsupportedRequestErrors15Min  Gauge32,
    cfprApComputePCIeFatalReceiveStatsUnsupportedRequestErrors15MinH Gauge32,
    cfprApComputePCIeFatalReceiveStatsUnsupportedRequestErrors1Day   Gauge32,
    cfprApComputePCIeFatalReceiveStatsUnsupportedRequestErrors1DayH  Gauge32,
    cfprApComputePCIeFatalReceiveStatsUnsupportedRequestErrors1Hour  Gauge32,
    cfprApComputePCIeFatalReceiveStatsUnsupportedRequestErrors1HourH Gauge32,
    cfprApComputePCIeFatalReceiveStatsUnsupportedRequestErrors1Week  Gauge32,
    cfprApComputePCIeFatalReceiveStatsUnsupportedRequestErrors1WeekH Gauge32,
    cfprApComputePCIeFatalReceiveStatsUnsupportedRequestErrors2Weeks Gauge32,
    cfprApComputePCIeFatalReceiveStatsUnsupportedRequestErrors2WeeksH Gauge32,
    cfprApComputePCIeFatalReceiveStatsUpdate                         Gauge32
}

cfprApComputePCIeFatalReceiveStatsInstanceId OBJECT-TYPE
    SYNTAX       CfprApManagedObjectId
    MAX-ACCESS   not-accessible
    STATUS       current
    DESCRIPTION
        "Instance identifier of the managed object."
    ::= { cfprApComputePCIeFatalReceiveStatsEntry 1 }

cfprApComputePCIeFatalReceiveStatsDn OBJECT-TYPE
    SYNTAX       CfprApManagedObjectDn
    MAX-ACCESS   read-only
    STATUS       current
    DESCRIPTION
        "Cisco Firepower compute:PCIeFatalReceiveStats:dn
        managed object property"
    ::= { cfprApComputePCIeFatalReceiveStatsEntry 2 }

cfprApComputePCIeFatalReceiveStatsRn OBJECT-TYPE
    SYNTAX       SnmpAdminString
    MAX-ACCESS   read-only
    STATUS       current
    DESCRIPTION
        "Cisco Firepower compute:PCIeFatalReceiveStats:rn
        managed object property"
    ::= { cfprApComputePCIeFatalReceiveStatsEntry 3 }

cfprApComputePCIeFatalReceiveStatsBufferOverflowErrors OBJECT-TYPE
    SYNTAX       Counter32
    MAX-ACCESS   read-only
    STATUS       current
    DESCRIPTION
        "Cisco Firepower compute:PCIeFatalReceiveStats:bufferOverflowError
        s managed object property"
    ::= { cfprApComputePCIeFatalReceiveStatsEntry 4 }

cfprApComputePCIeFatalReceiveStatsBufferOverflowErrors15Min OBJECT-TYPE
    SYNTAX       Gauge32
    MAX-ACCESS   read-only
    STATUS       current
    DESCRIPTION
        "Cisco Firepower compute:PCIeFatalReceiveStats:bufferOverflowError
        s15Min managed object property"
    ::= { cfprApComputePCIeFatalReceiveStatsEntry 5 }

cfprApComputePCIeFatalReceiveStatsBufferOverflowErrors15MinH OBJECT-TYPE
    SYNTAX       Gauge32
    MAX-ACCESS   read-only
    STATUS       current
    DESCRIPTION
        "Cisco Firepower compute:PCIeFatalReceiveStats:bufferOverflowError
        s15MinH managed object property"
    ::= { cfprApComputePCIeFatalReceiveStatsEntry 6 }

cfprApComputePCIeFatalReceiveStatsBufferOverflowErrors1Day OBJECT-TYPE
    SYNTAX       Gauge32
    MAX-ACCESS   read-only
    STATUS       current
    DESCRIPTION
        "Cisco Firepower compute:PCIeFatalReceiveStats:bufferOverflowError
        s1Day managed object property"
    ::= { cfprApComputePCIeFatalReceiveStatsEntry 7 }

cfprApComputePCIeFatalReceiveStatsBufferOverflowErrors1DayH OBJECT-TYPE
    SYNTAX       Gauge32
    MAX-ACCESS   read-only
    STATUS       current
    DESCRIPTION
        "Cisco Firepower compute:PCIeFatalReceiveStats:bufferOverflowError
        s1DayH managed object property"
    ::= { cfprApComputePCIeFatalReceiveStatsEntry 8 }

cfprApComputePCIeFatalReceiveStatsBufferOverflowErrors1Hour OBJECT-TYPE
    SYNTAX       Gauge32
    MAX-ACCESS   read-only
    STATUS       current
    DESCRIPTION
        "Cisco Firepower compute:PCIeFatalReceiveStats:bufferOverflowError
        s1Hour managed object property"
    ::= { cfprApComputePCIeFatalReceiveStatsEntry 9 }

cfprApComputePCIeFatalReceiveStatsBufferOverflowErrors1HourH OBJECT-TYPE
    SYNTAX       Gauge32
    MAX-ACCESS   read-only
    STATUS       current
    DESCRIPTION
        "Cisco Firepower compute:PCIeFatalReceiveStats:bufferOverflowError
        s1HourH managed object property"
    ::= { cfprApComputePCIeFatalReceiveStatsEntry 10 }

cfprApComputePCIeFatalReceiveStatsBufferOverflowErrors1Week OBJECT-TYPE
    SYNTAX       Gauge32
    MAX-ACCESS   read-only
    STATUS       current
    DESCRIPTION
        "Cisco Firepower compute:PCIeFatalReceiveStats:bufferOverflowError
        s1Week managed object property"
    ::= { cfprApComputePCIeFatalReceiveStatsEntry 11 }

cfprApComputePCIeFatalReceiveStatsBufferOverflowErrors1WeekH OBJECT-TYPE
    SYNTAX       Gauge32
    MAX-ACCESS   read-only
    STATUS       current
    DESCRIPTION
        "Cisco Firepower compute:PCIeFatalReceiveStats:bufferOverflowError
        s1WeekH managed object property"
    ::= { cfprApComputePCIeFatalReceiveStatsEntry 12 }

cfprApComputePCIeFatalReceiveStatsBufferOverflowErrors2Weeks OBJECT-TYPE
    SYNTAX       Gauge32
    MAX-ACCESS   read-only
    STATUS       current
    DESCRIPTION
        "Cisco Firepower compute:PCIeFatalReceiveStats:bufferOverflowError
        s2Weeks managed object property"
    ::= { cfprApComputePCIeFatalReceiveStatsEntry 13 }

cfprApComputePCIeFatalReceiveStatsBufferOverflowErrors2WeeksH OBJECT-TYPE
    SYNTAX       Gauge32
    MAX-ACCESS   read-only
    STATUS       current
    DESCRIPTION
        "Cisco Firepower compute:PCIeFatalReceiveStats:bufferOverflowError
        s2WeeksH managed object property"
    ::= { cfprApComputePCIeFatalReceiveStatsEntry 14 }

cfprApComputePCIeFatalReceiveStatsErrFatalErrors OBJECT-TYPE
    SYNTAX       Counter32
    MAX-ACCESS   read-only
    STATUS       current
    DESCRIPTION
        "Cisco Firepower compute:PCIeFatalReceiveStats:errFatalErrors
        managed object property"
    ::= { cfprApComputePCIeFatalReceiveStatsEntry 15 }

cfprApComputePCIeFatalReceiveStatsErrFatalErrors15Min OBJECT-TYPE
    SYNTAX       Gauge32
    MAX-ACCESS   read-only
    STATUS       current
    DESCRIPTION
        "Cisco Firepower compute:PCIeFatalReceiveStats:errFatalErrors15Min
         managed object property"
    ::= { cfprApComputePCIeFatalReceiveStatsEntry 16 }

cfprApComputePCIeFatalReceiveStatsErrFatalErrors15MinH OBJECT-TYPE
    SYNTAX       Gauge32
    MAX-ACCESS   read-only
    STATUS       current
    DESCRIPTION
        "Cisco Firepower compute:PCIeFatalReceiveStats:errFatalErrors15Min
        H managed object property"
    ::= { cfprApComputePCIeFatalReceiveStatsEntry 17 }

cfprApComputePCIeFatalReceiveStatsErrFatalErrors1Day OBJECT-TYPE
    SYNTAX       Gauge32
    MAX-ACCESS   read-only
    STATUS       current
    DESCRIPTION
        "Cisco Firepower compute:PCIeFatalReceiveStats:errFatalErrors1Day
        managed object property"
    ::= { cfprApComputePCIeFatalReceiveStatsEntry 18 }

cfprApComputePCIeFatalReceiveStatsErrFatalErrors1DayH OBJECT-TYPE
    SYNTAX       Gauge32
    MAX-ACCESS   read-only
    STATUS       current
    DESCRIPTION
        "Cisco Firepower compute:PCIeFatalReceiveStats:errFatalErrors1DayH
         managed object property"
    ::= { cfprApComputePCIeFatalReceiveStatsEntry 19 }

cfprApComputePCIeFatalReceiveStatsErrFatalErrors1Hour OBJECT-TYPE
    SYNTAX       Gauge32
    MAX-ACCESS   read-only
    STATUS       current
    DESCRIPTION
        "Cisco Firepower compute:PCIeFatalReceiveStats:errFatalErrors1Hour
         managed object property"
    ::= { cfprApComputePCIeFatalReceiveStatsEntry 20 }

cfprApComputePCIeFatalReceiveStatsErrFatalErrors1HourH OBJECT-TYPE
    SYNTAX       Gauge32
    MAX-ACCESS   read-only
    STATUS       current
    DESCRIPTION
        "Cisco Firepower compute:PCIeFatalReceiveStats:errFatalErrors1Hour
        H managed object property"
    ::= { cfprApComputePCIeFatalReceiveStatsEntry 21 }

cfprApComputePCIeFatalReceiveStatsErrFatalErrors1Week OBJECT-TYPE
    SYNTAX       Gauge32
    MAX-ACCESS   read-only
    STATUS       current
    DESCRIPTION
        "Cisco Firepower compute:PCIeFatalReceiveStats:errFatalErrors1Week
         managed object property"
    ::= { cfprApComputePCIeFatalReceiveStatsEntry 22 }

cfprApComputePCIeFatalReceiveStatsErrFatalErrors1WeekH OBJECT-TYPE
    SYNTAX       Gauge32
    MAX-ACCESS   read-only
    STATUS       current
    DESCRIPTION
        "Cisco Firepower compute:PCIeFatalReceiveStats:errFatalErrors1Week
        H managed object property"
    ::= { cfprApComputePCIeFatalReceiveStatsEntry 23 }

cfprApComputePCIeFatalReceiveStatsErrFatalErrors2Weeks OBJECT-TYPE
    SYNTAX       Gauge32
    MAX-ACCESS   read-only
    STATUS       current
    DESCRIPTION
        "Cisco Firepower compute:PCIeFatalReceiveStats:errFatalErrors2Week
        s managed object property"
    ::= { cfprApComputePCIeFatalReceiveStatsEntry 24 }

cfprApComputePCIeFatalReceiveStatsErrFatalErrors2WeeksH OBJECT-TYPE
    SYNTAX       Gauge32
    MAX-ACCESS   read-only
    STATUS       current
    DESCRIPTION
        "Cisco Firepower compute:PCIeFatalReceiveStats:errFatalErrors2Week
        sH managed object property"
    ::= { cfprApComputePCIeFatalReceiveStatsEntry 25 }

cfprApComputePCIeFatalReceiveStatsErrNonFatalErrors OBJECT-TYPE
    SYNTAX       Counter32
    MAX-ACCESS   read-only
    STATUS       current
    DESCRIPTION
        "Cisco Firepower compute:PCIeFatalReceiveStats:errNonFatalErrors
        managed object property"
    ::= { cfprApComputePCIeFatalReceiveStatsEntry 26 }

cfprApComputePCIeFatalReceiveStatsErrNonFatalErrors15Min OBJECT-TYPE
    SYNTAX       Gauge32
    MAX-ACCESS   read-only
    STATUS       current
    DESCRIPTION
        "Cisco Firepower compute:PCIeFatalReceiveStats:errNonFatalErrors15
        Min managed object property"
    ::= { cfprApComputePCIeFatalReceiveStatsEntry 27 }

cfprApComputePCIeFatalReceiveStatsErrNonFatalErrors15MinH OBJECT-TYPE
    SYNTAX       Gauge32
    MAX-ACCESS   read-only
    STATUS       current
    DESCRIPTION
        "Cisco Firepower compute:PCIeFatalReceiveStats:errNonFatalErrors15
        MinH managed object property"
    ::= { cfprApComputePCIeFatalReceiveStatsEntry 28 }

cfprApComputePCIeFatalReceiveStatsErrNonFatalErrors1Day OBJECT-TYPE
    SYNTAX       Gauge32
    MAX-ACCESS   read-only
    STATUS       current
    DESCRIPTION
        "Cisco Firepower compute:PCIeFatalReceiveStats:errNonFatalErrors1D
        ay managed object property"
    ::= { cfprApComputePCIeFatalReceiveStatsEntry 29 }

cfprApComputePCIeFatalReceiveStatsErrNonFatalErrors1DayH OBJECT-TYPE
    SYNTAX       Gauge32
    MAX-ACCESS   read-only
    STATUS       current
    DESCRIPTION
        "Cisco Firepower compute:PCIeFatalReceiveStats:errNonFatalErrors1D
        ayH managed object property"
    ::= { cfprApComputePCIeFatalReceiveStatsEntry 30 }

cfprApComputePCIeFatalReceiveStatsErrNonFatalErrors1Hour OBJECT-TYPE
    SYNTAX       Gauge32
    MAX-ACCESS   read-only
    STATUS       current
    DESCRIPTION
        "Cisco Firepower compute:PCIeFatalReceiveStats:errNonFatalErrors1H
        our managed object property"
    ::= { cfprApComputePCIeFatalReceiveStatsEntry 31 }

cfprApComputePCIeFatalReceiveStatsErrNonFatalErrors1HourH OBJECT-TYPE
    SYNTAX       Gauge32
    MAX-ACCESS   read-only
    STATUS       current
    DESCRIPTION
        "Cisco Firepower compute:PCIeFatalReceiveStats:errNonFatalErrors1H
        ourH managed object property"
    ::= { cfprApComputePCIeFatalReceiveStatsEntry 32 }

cfprApComputePCIeFatalReceiveStatsErrNonFatalErrors1Week OBJECT-TYPE
    SYNTAX       Gauge32
    MAX-ACCESS   read-only
    STATUS       current
    DESCRIPTION
        "Cisco Firepower compute:PCIeFatalReceiveStats:errNonFatalErrors1W
        eek managed object property"
    ::= { cfprApComputePCIeFatalReceiveStatsEntry 33 }

cfprApComputePCIeFatalReceiveStatsErrNonFatalErrors1WeekH OBJECT-TYPE
    SYNTAX       Gauge32
    MAX-ACCESS   read-only
    STATUS       current
    DESCRIPTION
        "Cisco Firepower compute:PCIeFatalReceiveStats:errNonFatalErrors1W
        eekH managed object property"
    ::= { cfprApComputePCIeFatalReceiveStatsEntry 34 }

cfprApComputePCIeFatalReceiveStatsErrNonFatalErrors2Weeks OBJECT-TYPE
    SYNTAX       Gauge32
    MAX-ACCESS   read-only
    STATUS       current
    DESCRIPTION
        "Cisco Firepower compute:PCIeFatalReceiveStats:errNonFatalErrors2W
        eeks managed object property"
    ::= { cfprApComputePCIeFatalReceiveStatsEntry 35 }

cfprApComputePCIeFatalReceiveStatsErrNonFatalErrors2WeeksH OBJECT-TYPE
    SYNTAX       Gauge32
    MAX-ACCESS   read-only
    STATUS       current
    DESCRIPTION
        "Cisco Firepower compute:PCIeFatalReceiveStats:errNonFatalErrors2W
        eeksH managed object property"
    ::= { cfprApComputePCIeFatalReceiveStatsEntry 36 }

cfprApComputePCIeFatalReceiveStatsIntervals OBJECT-TYPE
    SYNTAX       Gauge32
    MAX-ACCESS   read-only
    STATUS       current
    DESCRIPTION
        "Cisco Firepower compute:PCIeFatalReceiveStats:intervals
        managed object property"
    ::= { cfprApComputePCIeFatalReceiveStatsEntry 37 }

cfprApComputePCIeFatalReceiveStatsSuspect OBJECT-TYPE
    SYNTAX       TruthValue
    MAX-ACCESS   read-only
    STATUS       current
    DESCRIPTION
        "Cisco Firepower compute:PCIeFatalReceiveStats:suspect
        managed object property"
    ::= { cfprApComputePCIeFatalReceiveStatsEntry 38 }

cfprApComputePCIeFatalReceiveStatsThresholded OBJECT-TYPE
    SYNTAX       CfprApComputePCIeFatalReceiveStatsThresholded
    MAX-ACCESS   read-only
    STATUS       current
    DESCRIPTION
        "Cisco Firepower compute:PCIeFatalReceiveStats:thresholded
        managed object property"
    ::= { cfprApComputePCIeFatalReceiveStatsEntry 39 }

cfprApComputePCIeFatalReceiveStatsTimeCollected OBJECT-TYPE
    SYNTAX       DateAndTime
    MAX-ACCESS   read-only
    STATUS       current
    DESCRIPTION
        "Cisco Firepower compute:PCIeFatalReceiveStats:timeCollected
        managed object property"
    ::= { cfprApComputePCIeFatalReceiveStatsEntry 40 }

cfprApComputePCIeFatalReceiveStatsUnsupportedRequestErrors OBJECT-TYPE
    SYNTAX       Counter32
    MAX-ACCESS   read-only
    STATUS       current
    DESCRIPTION
        "Cisco Firepower compute:PCIeFatalReceiveStats:unsupportedRequestE
        rrors managed object property"
    ::= { cfprApComputePCIeFatalReceiveStatsEntry 41 }

cfprApComputePCIeFatalReceiveStatsUnsupportedRequestErrors15Min OBJECT-TYPE
    SYNTAX       Gauge32
    MAX-ACCESS   read-only
    STATUS       current
    DESCRIPTION
        "Cisco Firepower compute:PCIeFatalReceiveStats:unsupportedRequestE
        rrors15Min managed object property"
    ::= { cfprApComputePCIeFatalReceiveStatsEntry 42 }

cfprApComputePCIeFatalReceiveStatsUnsupportedRequestErrors15MinH OBJECT-TYPE
    SYNTAX       Gauge32
    MAX-ACCESS   read-only
    STATUS       current
    DESCRIPTION
        "Cisco Firepower compute:PCIeFatalReceiveStats:unsupportedRequestE
        rrors15MinH managed object property"
    ::= { cfprApComputePCIeFatalReceiveStatsEntry 43 }

cfprApComputePCIeFatalReceiveStatsUnsupportedRequestErrors1Day OBJECT-TYPE
    SYNTAX       Gauge32
    MAX-ACCESS   read-only
    STATUS       current
    DESCRIPTION
        "Cisco Firepower compute:PCIeFatalReceiveStats:unsupportedRequestE
        rrors1Day managed object property"
    ::= { cfprApComputePCIeFatalReceiveStatsEntry 44 }

cfprApComputePCIeFatalReceiveStatsUnsupportedRequestErrors1DayH OBJECT-TYPE
    SYNTAX       Gauge32
    MAX-ACCESS   read-only
    STATUS       current
    DESCRIPTION
        "Cisco Firepower compute:PCIeFatalReceiveStats:unsupportedRequestE
        rrors1DayH managed object property"
    ::= { cfprApComputePCIeFatalReceiveStatsEntry 45 }

cfprApComputePCIeFatalReceiveStatsUnsupportedRequestErrors1Hour OBJECT-TYPE
    SYNTAX       Gauge32
    MAX-ACCESS   read-only
    STATUS       current
    DESCRIPTION
        "Cisco Firepower compute:PCIeFatalReceiveStats:unsupportedRequestE
        rrors1Hour managed object property"
    ::= { cfprApComputePCIeFatalReceiveStatsEntry 46 }

cfprApComputePCIeFatalReceiveStatsUnsupportedRequestErrors1HourH OBJECT-TYPE
    SYNTAX       Gauge32
    MAX-ACCESS   read-only
    STATUS       current
    DESCRIPTION
        "Cisco Firepower compute:PCIeFatalReceiveStats:unsupportedRequestE
        rrors1HourH managed object property"
    ::= { cfprApComputePCIeFatalReceiveStatsEntry 47 }

cfprApComputePCIeFatalReceiveStatsUnsupportedRequestErrors1Week OBJECT-TYPE
    SYNTAX       Gauge32
    MAX-ACCESS   read-only
    STATUS       current
    DESCRIPTION
        "Cisco Firepower compute:PCIeFatalReceiveStats:unsupportedRequestE
        rrors1Week managed object property"
    ::= { cfprApComputePCIeFatalReceiveStatsEntry 48 }

cfprApComputePCIeFatalReceiveStatsUnsupportedRequestErrors1WeekH OBJECT-TYPE
    SYNTAX       Gauge32
    MAX-ACCESS   read-only
    STATUS       current
    DESCRIPTION
        "Cisco Firepower compute:PCIeFatalReceiveStats:unsupportedRequestE
        rrors1WeekH managed object property"
    ::= { cfprApComputePCIeFatalReceiveStatsEntry 49 }

cfprApComputePCIeFatalReceiveStatsUnsupportedRequestErrors2Weeks OBJECT-TYPE
    SYNTAX       Gauge32
    MAX-ACCESS   read-only
    STATUS       current
    DESCRIPTION
        "Cisco Firepower compute:PCIeFatalReceiveStats:unsupportedRequestE
        rrors2Weeks managed object property"
    ::= { cfprApComputePCIeFatalReceiveStatsEntry 50 }

cfprApComputePCIeFatalReceiveStatsUnsupportedRequestErrors2WeeksH OBJECT-TYPE
    SYNTAX       Gauge32
    MAX-ACCESS   read-only
    STATUS       current
    DESCRIPTION
        "Cisco Firepower compute:PCIeFatalReceiveStats:unsupportedRequestE
        rrors2WeeksH managed object property"
    ::= { cfprApComputePCIeFatalReceiveStatsEntry 51 }

cfprApComputePCIeFatalReceiveStatsUpdate OBJECT-TYPE
    SYNTAX       Gauge32
    MAX-ACCESS   read-only
    STATUS       current
    DESCRIPTION
        "Cisco Firepower compute:PCIeFatalReceiveStats:update
        managed object property"
    ::= { cfprApComputePCIeFatalReceiveStatsEntry 52 }

cfprApComputePCIeFatalStatsTable OBJECT-TYPE
    SYNTAX           SEQUENCE OF CfprApComputePCIeFatalStatsEntry
    MAX-ACCESS       not-accessible
    STATUS           current
    DESCRIPTION
        "Cisco Firepower compute:PCIeFatalStats managed object table"
    ::= { cfprApComputeObjects 33 }

cfprApComputePCIeFatalStatsEntry OBJECT-TYPE
    SYNTAX           CfprApComputePCIeFatalStatsEntry
    MAX-ACCESS       not-accessible
    STATUS           current
    DESCRIPTION
        "Entry for the cfprApComputePCIeFatalStatsTable table."
    INDEX { cfprApComputePCIeFatalStatsInstanceId }
    ::= { cfprApComputePCIeFatalStatsTable 1 }

CfprApComputePCIeFatalStatsEntry ::= SEQUENCE {
    cfprApComputePCIeFatalStatsInstanceId                            CfprApManagedObjectId,
    cfprApComputePCIeFatalStatsDn                                    CfprApManagedObjectDn,
    cfprApComputePCIeFatalStatsRn                                    SnmpAdminString,
    cfprApComputePCIeFatalStatsAcsViolationErrors                    Counter32,
    cfprApComputePCIeFatalStatsAcsViolationErrors15Min               Gauge32,
    cfprApComputePCIeFatalStatsAcsViolationErrors15MinH              Gauge32,
    cfprApComputePCIeFatalStatsAcsViolationErrors1Day                Gauge32,
    cfprApComputePCIeFatalStatsAcsViolationErrors1DayH               Gauge32,
    cfprApComputePCIeFatalStatsAcsViolationErrors1Hour               Gauge32,
    cfprApComputePCIeFatalStatsAcsViolationErrors1HourH              Gauge32,
    cfprApComputePCIeFatalStatsAcsViolationErrors1Week               Gauge32,
    cfprApComputePCIeFatalStatsAcsViolationErrors1WeekH              Gauge32,
    cfprApComputePCIeFatalStatsAcsViolationErrors2Weeks              Gauge32,
    cfprApComputePCIeFatalStatsAcsViolationErrors2WeeksH             Gauge32,
    cfprApComputePCIeFatalStatsIntervals                             Gauge32,
    cfprApComputePCIeFatalStatsMalformedTLPErrors                    Counter32,
    cfprApComputePCIeFatalStatsMalformedTLPErrors15Min               Gauge32,
    cfprApComputePCIeFatalStatsMalformedTLPErrors15MinH              Gauge32,
    cfprApComputePCIeFatalStatsMalformedTLPErrors1Day                Gauge32,
    cfprApComputePCIeFatalStatsMalformedTLPErrors1DayH               Gauge32,
    cfprApComputePCIeFatalStatsMalformedTLPErrors1Hour               Gauge32,
    cfprApComputePCIeFatalStatsMalformedTLPErrors1HourH              Gauge32,
    cfprApComputePCIeFatalStatsMalformedTLPErrors1Week               Gauge32,
    cfprApComputePCIeFatalStatsMalformedTLPErrors1WeekH              Gauge32,
    cfprApComputePCIeFatalStatsMalformedTLPErrors2Weeks              Gauge32,
    cfprApComputePCIeFatalStatsMalformedTLPErrors2WeeksH             Gauge32,
    cfprApComputePCIeFatalStatsPoisonedTLPErrors                     Counter32,
    cfprApComputePCIeFatalStatsPoisonedTLPErrors15Min                Gauge32,
    cfprApComputePCIeFatalStatsPoisonedTLPErrors15MinH               Gauge32,
    cfprApComputePCIeFatalStatsPoisonedTLPErrors1Day                 Gauge32,
    cfprApComputePCIeFatalStatsPoisonedTLPErrors1DayH                Gauge32,
    cfprApComputePCIeFatalStatsPoisonedTLPErrors1Hour                Gauge32,
    cfprApComputePCIeFatalStatsPoisonedTLPErrors1HourH               Gauge32,
    cfprApComputePCIeFatalStatsPoisonedTLPErrors1Week                Gauge32,
    cfprApComputePCIeFatalStatsPoisonedTLPErrors1WeekH               Gauge32,
    cfprApComputePCIeFatalStatsPoisonedTLPErrors2Weeks               Gauge32,
    cfprApComputePCIeFatalStatsPoisonedTLPErrors2WeeksH              Gauge32,
    cfprApComputePCIeFatalStatsSurpriseLinkDownErrors                Counter32,
    cfprApComputePCIeFatalStatsSurpriseLinkDownErrors15Min           Gauge32,
    cfprApComputePCIeFatalStatsSurpriseLinkDownErrors15MinH          Gauge32,
    cfprApComputePCIeFatalStatsSurpriseLinkDownErrors1Day            Gauge32,
    cfprApComputePCIeFatalStatsSurpriseLinkDownErrors1DayH           Gauge32,
    cfprApComputePCIeFatalStatsSurpriseLinkDownErrors1Hour           Gauge32,
    cfprApComputePCIeFatalStatsSurpriseLinkDownErrors1HourH          Gauge32,
    cfprApComputePCIeFatalStatsSurpriseLinkDownErrors1Week           Gauge32,
    cfprApComputePCIeFatalStatsSurpriseLinkDownErrors1WeekH          Gauge32,
    cfprApComputePCIeFatalStatsSurpriseLinkDownErrors2Weeks          Gauge32,
    cfprApComputePCIeFatalStatsSurpriseLinkDownErrors2WeeksH         Gauge32,
    cfprApComputePCIeFatalStatsSuspect                               TruthValue,
    cfprApComputePCIeFatalStatsThresholded                           CfprApComputePCIeFatalStatsThresholded,
    cfprApComputePCIeFatalStatsTimeCollected                         DateAndTime,
    cfprApComputePCIeFatalStatsUpdate                                Gauge32
}

cfprApComputePCIeFatalStatsInstanceId OBJECT-TYPE
    SYNTAX       CfprApManagedObjectId
    MAX-ACCESS   not-accessible
    STATUS       current
    DESCRIPTION
        "Instance identifier of the managed object."
    ::= { cfprApComputePCIeFatalStatsEntry 1 }

cfprApComputePCIeFatalStatsDn OBJECT-TYPE
    SYNTAX       CfprApManagedObjectDn
    MAX-ACCESS   read-only
    STATUS       current
    DESCRIPTION
        "Cisco Firepower compute:PCIeFatalStats:dn managed
        object property"
    ::= { cfprApComputePCIeFatalStatsEntry 2 }

cfprApComputePCIeFatalStatsRn OBJECT-TYPE
    SYNTAX       SnmpAdminString
    MAX-ACCESS   read-only
    STATUS       current
    DESCRIPTION
        "Cisco Firepower compute:PCIeFatalStats:rn managed
        object property"
    ::= { cfprApComputePCIeFatalStatsEntry 3 }

cfprApComputePCIeFatalStatsAcsViolationErrors OBJECT-TYPE
    SYNTAX       Counter32
    MAX-ACCESS   read-only
    STATUS       current
    DESCRIPTION
        "Cisco Firepower compute:PCIeFatalStats:acsViolationErrors
        managed object property"
    ::= { cfprApComputePCIeFatalStatsEntry 4 }

cfprApComputePCIeFatalStatsAcsViolationErrors15Min OBJECT-TYPE
    SYNTAX       Gauge32
    MAX-ACCESS   read-only
    STATUS       current
    DESCRIPTION
        "Cisco Firepower compute:PCIeFatalStats:acsViolationErrors15Min
        managed object property"
    ::= { cfprApComputePCIeFatalStatsEntry 5 }

cfprApComputePCIeFatalStatsAcsViolationErrors15MinH OBJECT-TYPE
    SYNTAX       Gauge32
    MAX-ACCESS   read-only
    STATUS       current
    DESCRIPTION
        "Cisco Firepower compute:PCIeFatalStats:acsViolationErrors15MinH
        managed object property"
    ::= { cfprApComputePCIeFatalStatsEntry 6 }

cfprApComputePCIeFatalStatsAcsViolationErrors1Day OBJECT-TYPE
    SYNTAX       Gauge32
    MAX-ACCESS   read-only
    STATUS       current
    DESCRIPTION
        "Cisco Firepower compute:PCIeFatalStats:acsViolationErrors1Day
        managed object property"
    ::= { cfprApComputePCIeFatalStatsEntry 7 }

cfprApComputePCIeFatalStatsAcsViolationErrors1DayH OBJECT-TYPE
    SYNTAX       Gauge32
    MAX-ACCESS   read-only
    STATUS       current
    DESCRIPTION
        "Cisco Firepower compute:PCIeFatalStats:acsViolationErrors1DayH
        managed object property"
    ::= { cfprApComputePCIeFatalStatsEntry 8 }

cfprApComputePCIeFatalStatsAcsViolationErrors1Hour OBJECT-TYPE
    SYNTAX       Gauge32
    MAX-ACCESS   read-only
    STATUS       current
    DESCRIPTION
        "Cisco Firepower compute:PCIeFatalStats:acsViolationErrors1Hour
        managed object property"
    ::= { cfprApComputePCIeFatalStatsEntry 9 }

cfprApComputePCIeFatalStatsAcsViolationErrors1HourH OBJECT-TYPE
    SYNTAX       Gauge32
    MAX-ACCESS   read-only
    STATUS       current
    DESCRIPTION
        "Cisco Firepower compute:PCIeFatalStats:acsViolationErrors1HourH
        managed object property"
    ::= { cfprApComputePCIeFatalStatsEntry 10 }

cfprApComputePCIeFatalStatsAcsViolationErrors1Week OBJECT-TYPE
    SYNTAX       Gauge32
    MAX-ACCESS   read-only
    STATUS       current
    DESCRIPTION
        "Cisco Firepower compute:PCIeFatalStats:acsViolationErrors1Week
        managed object property"
    ::= { cfprApComputePCIeFatalStatsEntry 11 }

cfprApComputePCIeFatalStatsAcsViolationErrors1WeekH OBJECT-TYPE
    SYNTAX       Gauge32
    MAX-ACCESS   read-only
    STATUS       current
    DESCRIPTION
        "Cisco Firepower compute:PCIeFatalStats:acsViolationErrors1WeekH
        managed object property"
    ::= { cfprApComputePCIeFatalStatsEntry 12 }

cfprApComputePCIeFatalStatsAcsViolationErrors2Weeks OBJECT-TYPE
    SYNTAX       Gauge32
    MAX-ACCESS   read-only
    STATUS       current
    DESCRIPTION
        "Cisco Firepower compute:PCIeFatalStats:acsViolationErrors2Weeks
        managed object property"
    ::= { cfprApComputePCIeFatalStatsEntry 13 }

cfprApComputePCIeFatalStatsAcsViolationErrors2WeeksH OBJECT-TYPE
    SYNTAX       Gauge32
    MAX-ACCESS   read-only
    STATUS       current
    DESCRIPTION
        "Cisco Firepower compute:PCIeFatalStats:acsViolationErrors2WeeksH
        managed object property"
    ::= { cfprApComputePCIeFatalStatsEntry 14 }

cfprApComputePCIeFatalStatsIntervals OBJECT-TYPE
    SYNTAX       Gauge32
    MAX-ACCESS   read-only
    STATUS       current
    DESCRIPTION
        "Cisco Firepower compute:PCIeFatalStats:intervals
        managed object property"
    ::= { cfprApComputePCIeFatalStatsEntry 15 }

cfprApComputePCIeFatalStatsMalformedTLPErrors OBJECT-TYPE
    SYNTAX       Counter32
    MAX-ACCESS   read-only
    STATUS       current
    DESCRIPTION
        "Cisco Firepower compute:PCIeFatalStats:malformedTLPErrors
        managed object property"
    ::= { cfprApComputePCIeFatalStatsEntry 16 }

cfprApComputePCIeFatalStatsMalformedTLPErrors15Min OBJECT-TYPE
    SYNTAX       Gauge32
    MAX-ACCESS   read-only
    STATUS       current
    DESCRIPTION
        "Cisco Firepower compute:PCIeFatalStats:malformedTLPErrors15Min
        managed object property"
    ::= { cfprApComputePCIeFatalStatsEntry 17 }

cfprApComputePCIeFatalStatsMalformedTLPErrors15MinH OBJECT-TYPE
    SYNTAX       Gauge32
    MAX-ACCESS   read-only
    STATUS       current
    DESCRIPTION
        "Cisco Firepower compute:PCIeFatalStats:malformedTLPErrors15MinH
        managed object property"
    ::= { cfprApComputePCIeFatalStatsEntry 18 }

cfprApComputePCIeFatalStatsMalformedTLPErrors1Day OBJECT-TYPE
    SYNTAX       Gauge32
    MAX-ACCESS   read-only
    STATUS       current
    DESCRIPTION
        "Cisco Firepower compute:PCIeFatalStats:malformedTLPErrors1Day
        managed object property"
    ::= { cfprApComputePCIeFatalStatsEntry 19 }

cfprApComputePCIeFatalStatsMalformedTLPErrors1DayH OBJECT-TYPE
    SYNTAX       Gauge32
    MAX-ACCESS   read-only
    STATUS       current
    DESCRIPTION
        "Cisco Firepower compute:PCIeFatalStats:malformedTLPErrors1DayH
        managed object property"
    ::= { cfprApComputePCIeFatalStatsEntry 20 }

cfprApComputePCIeFatalStatsMalformedTLPErrors1Hour OBJECT-TYPE
    SYNTAX       Gauge32
    MAX-ACCESS   read-only
    STATUS       current
    DESCRIPTION
        "Cisco Firepower compute:PCIeFatalStats:malformedTLPErrors1Hour
        managed object property"
    ::= { cfprApComputePCIeFatalStatsEntry 21 }

cfprApComputePCIeFatalStatsMalformedTLPErrors1HourH OBJECT-TYPE
    SYNTAX       Gauge32
    MAX-ACCESS   read-only
    STATUS       current
    DESCRIPTION
        "Cisco Firepower compute:PCIeFatalStats:malformedTLPErrors1HourH
        managed object property"
    ::= { cfprApComputePCIeFatalStatsEntry 22 }

cfprApComputePCIeFatalStatsMalformedTLPErrors1Week OBJECT-TYPE
    SYNTAX       Gauge32
    MAX-ACCESS   read-only
    STATUS       current
    DESCRIPTION
        "Cisco Firepower compute:PCIeFatalStats:malformedTLPErrors1Week
        managed object property"
    ::= { cfprApComputePCIeFatalStatsEntry 23 }

cfprApComputePCIeFatalStatsMalformedTLPErrors1WeekH OBJECT-TYPE
    SYNTAX       Gauge32
    MAX-ACCESS   read-only
    STATUS       current
    DESCRIPTION
        "Cisco Firepower compute:PCIeFatalStats:malformedTLPErrors1WeekH
        managed object property"
    ::= { cfprApComputePCIeFatalStatsEntry 24 }

cfprApComputePCIeFatalStatsMalformedTLPErrors2Weeks OBJECT-TYPE
    SYNTAX       Gauge32
    MAX-ACCESS   read-only
    STATUS       current
    DESCRIPTION
        "Cisco Firepower compute:PCIeFatalStats:malformedTLPErrors2Weeks
        managed object property"
    ::= { cfprApComputePCIeFatalStatsEntry 25 }

cfprApComputePCIeFatalStatsMalformedTLPErrors2WeeksH OBJECT-TYPE
    SYNTAX       Gauge32
    MAX-ACCESS   read-only
    STATUS       current
    DESCRIPTION
        "Cisco Firepower compute:PCIeFatalStats:malformedTLPErrors2WeeksH
        managed object property"
    ::= { cfprApComputePCIeFatalStatsEntry 26 }

cfprApComputePCIeFatalStatsPoisonedTLPErrors OBJECT-TYPE
    SYNTAX       Counter32
    MAX-ACCESS   read-only
    STATUS       current
    DESCRIPTION
        "Cisco Firepower compute:PCIeFatalStats:poisonedTLPErrors
        managed object property"
    ::= { cfprApComputePCIeFatalStatsEntry 27 }

cfprApComputePCIeFatalStatsPoisonedTLPErrors15Min OBJECT-TYPE
    SYNTAX       Gauge32
    MAX-ACCESS   read-only
    STATUS       current
    DESCRIPTION
        "Cisco Firepower compute:PCIeFatalStats:poisonedTLPErrors15Min
        managed object property"
    ::= { cfprApComputePCIeFatalStatsEntry 28 }

cfprApComputePCIeFatalStatsPoisonedTLPErrors15MinH OBJECT-TYPE
    SYNTAX       Gauge32
    MAX-ACCESS   read-only
    STATUS       current
    DESCRIPTION
        "Cisco Firepower compute:PCIeFatalStats:poisonedTLPErrors15MinH
        managed object property"
    ::= { cfprApComputePCIeFatalStatsEntry 29 }

cfprApComputePCIeFatalStatsPoisonedTLPErrors1Day OBJECT-TYPE
    SYNTAX       Gauge32
    MAX-ACCESS   read-only
    STATUS       current
    DESCRIPTION
        "Cisco Firepower compute:PCIeFatalStats:poisonedTLPErrors1Day
        managed object property"
    ::= { cfprApComputePCIeFatalStatsEntry 30 }

cfprApComputePCIeFatalStatsPoisonedTLPErrors1DayH OBJECT-TYPE
    SYNTAX       Gauge32
    MAX-ACCESS   read-only
    STATUS       current
    DESCRIPTION
        "Cisco Firepower compute:PCIeFatalStats:poisonedTLPErrors1DayH
        managed object property"
    ::= { cfprApComputePCIeFatalStatsEntry 31 }

cfprApComputePCIeFatalStatsPoisonedTLPErrors1Hour OBJECT-TYPE
    SYNTAX       Gauge32
    MAX-ACCESS   read-only
    STATUS       current
    DESCRIPTION
        "Cisco Firepower compute:PCIeFatalStats:poisonedTLPErrors1Hour
        managed object property"
    ::= { cfprApComputePCIeFatalStatsEntry 32 }

cfprApComputePCIeFatalStatsPoisonedTLPErrors1HourH OBJECT-TYPE
    SYNTAX       Gauge32
    MAX-ACCESS   read-only
    STATUS       current
    DESCRIPTION
        "Cisco Firepower compute:PCIeFatalStats:poisonedTLPErrors1HourH
        managed object property"
    ::= { cfprApComputePCIeFatalStatsEntry 33 }

cfprApComputePCIeFatalStatsPoisonedTLPErrors1Week OBJECT-TYPE
    SYNTAX       Gauge32
    MAX-ACCESS   read-only
    STATUS       current
    DESCRIPTION
        "Cisco Firepower compute:PCIeFatalStats:poisonedTLPErrors1Week
        managed object property"
    ::= { cfprApComputePCIeFatalStatsEntry 34 }

cfprApComputePCIeFatalStatsPoisonedTLPErrors1WeekH OBJECT-TYPE
    SYNTAX       Gauge32
    MAX-ACCESS   read-only
    STATUS       current
    DESCRIPTION
        "Cisco Firepower compute:PCIeFatalStats:poisonedTLPErrors1WeekH
        managed object property"
    ::= { cfprApComputePCIeFatalStatsEntry 35 }

cfprApComputePCIeFatalStatsPoisonedTLPErrors2Weeks OBJECT-TYPE
    SYNTAX       Gauge32
    MAX-ACCESS   read-only
    STATUS       current
    DESCRIPTION
        "Cisco Firepower compute:PCIeFatalStats:poisonedTLPErrors2Weeks
        managed object property"
    ::= { cfprApComputePCIeFatalStatsEntry 36 }

cfprApComputePCIeFatalStatsPoisonedTLPErrors2WeeksH OBJECT-TYPE
    SYNTAX       Gauge32
    MAX-ACCESS   read-only
    STATUS       current
    DESCRIPTION
        "Cisco Firepower compute:PCIeFatalStats:poisonedTLPErrors2WeeksH
        managed object property"
    ::= { cfprApComputePCIeFatalStatsEntry 37 }

cfprApComputePCIeFatalStatsSurpriseLinkDownErrors OBJECT-TYPE
    SYNTAX       Counter32
    MAX-ACCESS   read-only
    STATUS       current
    DESCRIPTION
        "Cisco Firepower compute:PCIeFatalStats:surpriseLinkDownErrors
        managed object property"
    ::= { cfprApComputePCIeFatalStatsEntry 38 }

cfprApComputePCIeFatalStatsSurpriseLinkDownErrors15Min OBJECT-TYPE
    SYNTAX       Gauge32
    MAX-ACCESS   read-only
    STATUS       current
    DESCRIPTION
        "Cisco Firepower compute:PCIeFatalStats:surpriseLinkDownErrors15Mi
        n managed object property"
    ::= { cfprApComputePCIeFatalStatsEntry 39 }

cfprApComputePCIeFatalStatsSurpriseLinkDownErrors15MinH OBJECT-TYPE
    SYNTAX       Gauge32
    MAX-ACCESS   read-only
    STATUS       current
    DESCRIPTION
        "Cisco Firepower compute:PCIeFatalStats:surpriseLinkDownErrors15Mi
        nH managed object property"
    ::= { cfprApComputePCIeFatalStatsEntry 40 }

cfprApComputePCIeFatalStatsSurpriseLinkDownErrors1Day OBJECT-TYPE
    SYNTAX       Gauge32
    MAX-ACCESS   read-only
    STATUS       current
    DESCRIPTION
        "Cisco Firepower compute:PCIeFatalStats:surpriseLinkDownErrors1Day
         managed object property"
    ::= { cfprApComputePCIeFatalStatsEntry 41 }

cfprApComputePCIeFatalStatsSurpriseLinkDownErrors1DayH OBJECT-TYPE
    SYNTAX       Gauge32
    MAX-ACCESS   read-only
    STATUS       current
    DESCRIPTION
        "Cisco Firepower compute:PCIeFatalStats:surpriseLinkDownErrors1Day
        H managed object property"
    ::= { cfprApComputePCIeFatalStatsEntry 42 }

cfprApComputePCIeFatalStatsSurpriseLinkDownErrors1Hour OBJECT-TYPE
    SYNTAX       Gauge32
    MAX-ACCESS   read-only
    STATUS       current
    DESCRIPTION
        "Cisco Firepower compute:PCIeFatalStats:surpriseLinkDownErrors1Hou
        r managed object property"
    ::= { cfprApComputePCIeFatalStatsEntry 43 }

cfprApComputePCIeFatalStatsSurpriseLinkDownErrors1HourH OBJECT-TYPE
    SYNTAX       Gauge32
    MAX-ACCESS   read-only
    STATUS       current
    DESCRIPTION
        "Cisco Firepower compute:PCIeFatalStats:surpriseLinkDownErrors1Hou
        rH managed object property"
    ::= { cfprApComputePCIeFatalStatsEntry 44 }

cfprApComputePCIeFatalStatsSurpriseLinkDownErrors1Week OBJECT-TYPE
    SYNTAX       Gauge32
    MAX-ACCESS   read-only
    STATUS       current
    DESCRIPTION
        "Cisco Firepower compute:PCIeFatalStats:surpriseLinkDownErrors1Wee
        k managed object property"
    ::= { cfprApComputePCIeFatalStatsEntry 45 }

cfprApComputePCIeFatalStatsSurpriseLinkDownErrors1WeekH OBJECT-TYPE
    SYNTAX       Gauge32
    MAX-ACCESS   read-only
    STATUS       current
    DESCRIPTION
        "Cisco Firepower compute:PCIeFatalStats:surpriseLinkDownErrors1Wee
        kH managed object property"
    ::= { cfprApComputePCIeFatalStatsEntry 46 }

cfprApComputePCIeFatalStatsSurpriseLinkDownErrors2Weeks OBJECT-TYPE
    SYNTAX       Gauge32
    MAX-ACCESS   read-only
    STATUS       current
    DESCRIPTION
        "Cisco Firepower compute:PCIeFatalStats:surpriseLinkDownErrors2Wee
        ks managed object property"
    ::= { cfprApComputePCIeFatalStatsEntry 47 }

cfprApComputePCIeFatalStatsSurpriseLinkDownErrors2WeeksH OBJECT-TYPE
    SYNTAX       Gauge32
    MAX-ACCESS   read-only
    STATUS       current
    DESCRIPTION
        "Cisco Firepower compute:PCIeFatalStats:surpriseLinkDownErrors2Wee
        ksH managed object property"
    ::= { cfprApComputePCIeFatalStatsEntry 48 }

cfprApComputePCIeFatalStatsSuspect OBJECT-TYPE
    SYNTAX       TruthValue
    MAX-ACCESS   read-only
    STATUS       current
    DESCRIPTION
        "Cisco Firepower compute:PCIeFatalStats:suspect
        managed object property"
    ::= { cfprApComputePCIeFatalStatsEntry 49 }

cfprApComputePCIeFatalStatsThresholded OBJECT-TYPE
    SYNTAX       CfprApComputePCIeFatalStatsThresholded
    MAX-ACCESS   read-only
    STATUS       current
    DESCRIPTION
        "Cisco Firepower compute:PCIeFatalStats:thresholded
        managed object property"
    ::= { cfprApComputePCIeFatalStatsEntry 50 }

cfprApComputePCIeFatalStatsTimeCollected OBJECT-TYPE
    SYNTAX       DateAndTime
    MAX-ACCESS   read-only
    STATUS       current
    DESCRIPTION
        "Cisco Firepower compute:PCIeFatalStats:timeCollected
        managed object property"
    ::= { cfprApComputePCIeFatalStatsEntry 51 }

cfprApComputePCIeFatalStatsUpdate OBJECT-TYPE
    SYNTAX       Gauge32
    MAX-ACCESS   read-only
    STATUS       current
    DESCRIPTION
        "Cisco Firepower compute:PCIeFatalStats:update
        managed object property"
    ::= { cfprApComputePCIeFatalStatsEntry 52 }

cfprApComputePciCapTable OBJECT-TYPE
    SYNTAX           SEQUENCE OF CfprApComputePciCapEntry
    MAX-ACCESS       not-accessible
    STATUS           current
    DESCRIPTION
        "Cisco Firepower compute:PciCap managed object table"
    ::= { cfprApComputeObjects 34 }

cfprApComputePciCapEntry OBJECT-TYPE
    SYNTAX           CfprApComputePciCapEntry
    MAX-ACCESS       not-accessible
    STATUS           current
    DESCRIPTION
        "Entry for the cfprApComputePciCapTable table."
    INDEX { cfprApComputePciCapInstanceId }
    ::= { cfprApComputePciCapTable 1 }

CfprApComputePciCapEntry ::= SEQUENCE {
    cfprApComputePciCapInstanceId                                    CfprApManagedObjectId,
    cfprApComputePciCapDn                                            CfprApManagedObjectDn,
    cfprApComputePciCapRn                                            SnmpAdminString,
    cfprApComputePciCapMaxBusIdPerSlot                               Gauge32,
    cfprApComputePciCapNumOfPhysSlots                                Gauge32,
    cfprApComputePciCapOrder                                         CfprApComputePciCapOrder,
    cfprApComputePciCapStartsWith                                    Gauge32
}

cfprApComputePciCapInstanceId OBJECT-TYPE
    SYNTAX       CfprApManagedObjectId
    MAX-ACCESS   not-accessible
    STATUS       current
    DESCRIPTION
        "Instance identifier of the managed object."
    ::= { cfprApComputePciCapEntry 1 }

cfprApComputePciCapDn OBJECT-TYPE
    SYNTAX       CfprApManagedObjectDn
    MAX-ACCESS   read-only
    STATUS       current
    DESCRIPTION
        "Cisco Firepower compute:PciCap:dn managed object property"
    ::= { cfprApComputePciCapEntry 2 }

cfprApComputePciCapRn OBJECT-TYPE
    SYNTAX       SnmpAdminString
    MAX-ACCESS   read-only
    STATUS       current
    DESCRIPTION
        "Cisco Firepower compute:PciCap:rn managed object property"
    ::= { cfprApComputePciCapEntry 3 }

cfprApComputePciCapMaxBusIdPerSlot OBJECT-TYPE
    SYNTAX       Gauge32
    MAX-ACCESS   read-only
    STATUS       current
    DESCRIPTION
        "Cisco Firepower compute:PciCap:maxBusIdPerSlot
        managed object property"
    ::= { cfprApComputePciCapEntry 4 }

cfprApComputePciCapNumOfPhysSlots OBJECT-TYPE
    SYNTAX       Gauge32
    MAX-ACCESS   read-only
    STATUS       current
    DESCRIPTION
        "Cisco Firepower compute:PciCap:numOfPhysSlots
        managed object property"
    ::= { cfprApComputePciCapEntry 5 }

cfprApComputePciCapOrder OBJECT-TYPE
    SYNTAX       CfprApComputePciCapOrder
    MAX-ACCESS   read-only
    STATUS       current
    DESCRIPTION
        "Cisco Firepower compute:PciCap:order managed object property"
    ::= { cfprApComputePciCapEntry 6 }

cfprApComputePciCapStartsWith OBJECT-TYPE
    SYNTAX       Gauge32
    MAX-ACCESS   read-only
    STATUS       current
    DESCRIPTION
        "Cisco Firepower compute:PciCap:startsWith managed
        object property"
    ::= { cfprApComputePciCapEntry 7 }

cfprApComputePciSlotScanDefTable OBJECT-TYPE
    SYNTAX           SEQUENCE OF CfprApComputePciSlotScanDefEntry
    MAX-ACCESS       not-accessible
    STATUS           current
    DESCRIPTION
        "Cisco Firepower compute:PciSlotScanDef managed object table"
    ::= { cfprApComputeObjects 35 }

cfprApComputePciSlotScanDefEntry OBJECT-TYPE
    SYNTAX           CfprApComputePciSlotScanDefEntry
    MAX-ACCESS       not-accessible
    STATUS           current
    DESCRIPTION
        "Entry for the cfprApComputePciSlotScanDefTable table."
    INDEX { cfprApComputePciSlotScanDefInstanceId }
    ::= { cfprApComputePciSlotScanDefTable 1 }

CfprApComputePciSlotScanDefEntry ::= SEQUENCE {
    cfprApComputePciSlotScanDefInstanceId                            CfprApManagedObjectId,
    cfprApComputePciSlotScanDefDn                                    CfprApManagedObjectDn,
    cfprApComputePciSlotScanDefRn                                    SnmpAdminString,
    cfprApComputePciSlotScanDefDescr                                 SnmpAdminString,
    cfprApComputePciSlotScanDefIntId                                 SnmpAdminString,
    cfprApComputePciSlotScanDefName                                  SnmpAdminString,
    cfprApComputePciSlotScanDefPolicyLevel                           Gauge32,
    cfprApComputePciSlotScanDefPolicyOwner                           CfprApPolicyPolicyOwner,
    cfprApComputePciSlotScanDefScanOrder                             Gauge32,
    cfprApComputePciSlotScanDefSlotId                                Gauge32
}

cfprApComputePciSlotScanDefInstanceId OBJECT-TYPE
    SYNTAX       CfprApManagedObjectId
    MAX-ACCESS   not-accessible
    STATUS       current
    DESCRIPTION
        "Instance identifier of the managed object."
    ::= { cfprApComputePciSlotScanDefEntry 1 }

cfprApComputePciSlotScanDefDn OBJECT-TYPE
    SYNTAX       CfprApManagedObjectDn
    MAX-ACCESS   read-only
    STATUS       current
    DESCRIPTION
        "Cisco Firepower compute:PciSlotScanDef:dn managed
        object property"
    ::= { cfprApComputePciSlotScanDefEntry 2 }

cfprApComputePciSlotScanDefRn OBJECT-TYPE
    SYNTAX       SnmpAdminString
    MAX-ACCESS   read-only
    STATUS       current
    DESCRIPTION
        "Cisco Firepower compute:PciSlotScanDef:rn managed
        object property"
    ::= { cfprApComputePciSlotScanDefEntry 3 }

cfprApComputePciSlotScanDefDescr OBJECT-TYPE
    SYNTAX       SnmpAdminString
    MAX-ACCESS   read-only
    STATUS       current
    DESCRIPTION
        "Cisco Firepower compute:PciSlotScanDef:descr managed
        object property"
    ::= { cfprApComputePciSlotScanDefEntry 4 }

cfprApComputePciSlotScanDefIntId OBJECT-TYPE
    SYNTAX       SnmpAdminString
    MAX-ACCESS   read-only
    STATUS       current
    DESCRIPTION
        "Cisco Firepower compute:PciSlotScanDef:intId managed
        object property"
    ::= { cfprApComputePciSlotScanDefEntry 5 }

cfprApComputePciSlotScanDefName OBJECT-TYPE
    SYNTAX       SnmpAdminString
    MAX-ACCESS   read-only
    STATUS       current
    DESCRIPTION
        "Cisco Firepower compute:PciSlotScanDef:name managed
        object property"
    ::= { cfprApComputePciSlotScanDefEntry 6 }

cfprApComputePciSlotScanDefPolicyLevel OBJECT-TYPE
    SYNTAX       Gauge32
    MAX-ACCESS   read-only
    STATUS       current
    DESCRIPTION
        "Cisco Firepower compute:PciSlotScanDef:policyLevel
        managed object property"
    ::= { cfprApComputePciSlotScanDefEntry 7 }

cfprApComputePciSlotScanDefPolicyOwner OBJECT-TYPE
    SYNTAX       CfprApPolicyPolicyOwner
    MAX-ACCESS   read-only
    STATUS       current
    DESCRIPTION
        "Cisco Firepower compute:PciSlotScanDef:policyOwner
        managed object property"
    ::= { cfprApComputePciSlotScanDefEntry 8 }

cfprApComputePciSlotScanDefScanOrder OBJECT-TYPE
    SYNTAX       Gauge32
    MAX-ACCESS   read-only
    STATUS       current
    DESCRIPTION
        "Cisco Firepower compute:PciSlotScanDef:scanOrder
        managed object property"
    ::= { cfprApComputePciSlotScanDefEntry 9 }

cfprApComputePciSlotScanDefSlotId OBJECT-TYPE
    SYNTAX       Gauge32
    MAX-ACCESS   read-only
    STATUS       current
    DESCRIPTION
        "Cisco Firepower compute:PciSlotScanDef:slotId
        managed object property"
    ::= { cfprApComputePciSlotScanDefEntry 10 }

cfprApComputePhysicalAssocCtxTable OBJECT-TYPE
    SYNTAX           SEQUENCE OF CfprApComputePhysicalAssocCtxEntry
    MAX-ACCESS       not-accessible
    STATUS           current
    DESCRIPTION
        "Cisco Firepower compute:PhysicalAssocCtx managed object table"
    ::= { cfprApComputeObjects 36 }

cfprApComputePhysicalAssocCtxEntry OBJECT-TYPE
    SYNTAX           CfprApComputePhysicalAssocCtxEntry
    MAX-ACCESS       not-accessible
    STATUS           current
    DESCRIPTION
        "Entry for the cfprApComputePhysicalAssocCtxTable table."
    INDEX { cfprApComputePhysicalAssocCtxInstanceId }
    ::= { cfprApComputePhysicalAssocCtxTable 1 }

CfprApComputePhysicalAssocCtxEntry ::= SEQUENCE {
    cfprApComputePhysicalAssocCtxInstanceId                          CfprApManagedObjectId,
    cfprApComputePhysicalAssocCtxDn                                  CfprApManagedObjectDn,
    cfprApComputePhysicalAssocCtxRn                                  SnmpAdminString,
    cfprApComputePhysicalAssocCtxFruCapDn                            SnmpAdminString
}

cfprApComputePhysicalAssocCtxInstanceId OBJECT-TYPE
    SYNTAX       CfprApManagedObjectId
    MAX-ACCESS   not-accessible
    STATUS       current
    DESCRIPTION
        "Instance identifier of the managed object."
    ::= { cfprApComputePhysicalAssocCtxEntry 1 }

cfprApComputePhysicalAssocCtxDn OBJECT-TYPE
    SYNTAX       CfprApManagedObjectDn
    MAX-ACCESS   read-only
    STATUS       current
    DESCRIPTION
        "Cisco Firepower compute:PhysicalAssocCtx:dn managed
        object property"
    ::= { cfprApComputePhysicalAssocCtxEntry 2 }

cfprApComputePhysicalAssocCtxRn OBJECT-TYPE
    SYNTAX       SnmpAdminString
    MAX-ACCESS   read-only
    STATUS       current
    DESCRIPTION
        "Cisco Firepower compute:PhysicalAssocCtx:rn managed
        object property"
    ::= { cfprApComputePhysicalAssocCtxEntry 3 }

cfprApComputePhysicalAssocCtxFruCapDn OBJECT-TYPE
    SYNTAX       SnmpAdminString
    MAX-ACCESS   read-only
    STATUS       current
    DESCRIPTION
        "Cisco Firepower compute:PhysicalAssocCtx:fruCapDn
        managed object property"
    ::= { cfprApComputePhysicalAssocCtxEntry 4 }

cfprApComputePhysicalFsmTable OBJECT-TYPE
    SYNTAX           SEQUENCE OF CfprApComputePhysicalFsmEntry
    MAX-ACCESS       not-accessible
    STATUS           current
    DESCRIPTION
        "Cisco Firepower compute:PhysicalFsm managed object table"
    ::= { cfprApComputeObjects 37 }

cfprApComputePhysicalFsmEntry OBJECT-TYPE
    SYNTAX           CfprApComputePhysicalFsmEntry
    MAX-ACCESS       not-accessible
    STATUS           current
    DESCRIPTION
        "Entry for the cfprApComputePhysicalFsmTable table."
    INDEX { cfprApComputePhysicalFsmInstanceId }
    ::= { cfprApComputePhysicalFsmTable 1 }

CfprApComputePhysicalFsmEntry ::= SEQUENCE {
    cfprApComputePhysicalFsmInstanceId                               CfprApManagedObjectId,
    cfprApComputePhysicalFsmDn                                       CfprApManagedObjectDn,
    cfprApComputePhysicalFsmRn                                       SnmpAdminString,
    cfprApComputePhysicalFsmCompletionTime                           DateAndTime,
    cfprApComputePhysicalFsmCurrentFsm                               CfprApComputePhysicalFsmCurrentFsm,
    cfprApComputePhysicalFsmDescr                                    SnmpAdminString,
    cfprApComputePhysicalFsmFsmStatus                                CfprApFsmFsmStageStatus,
    cfprApComputePhysicalFsmProgress                                 Gauge32,
    cfprApComputePhysicalFsmRmtErrCode                               Gauge32,
    cfprApComputePhysicalFsmRmtErrDescr                              SnmpAdminString,
    cfprApComputePhysicalFsmRmtRslt                                  CfprApConditionRemoteInvRslt
}

cfprApComputePhysicalFsmInstanceId OBJECT-TYPE
    SYNTAX       CfprApManagedObjectId
    MAX-ACCESS   not-accessible
    STATUS       current
    DESCRIPTION
        "Instance identifier of the managed object."
    ::= { cfprApComputePhysicalFsmEntry 1 }

cfprApComputePhysicalFsmDn OBJECT-TYPE
    SYNTAX       CfprApManagedObjectDn
    MAX-ACCESS   read-only
    STATUS       current
    DESCRIPTION
        "Cisco Firepower compute:PhysicalFsm:dn managed object property"
    ::= { cfprApComputePhysicalFsmEntry 2 }

cfprApComputePhysicalFsmRn OBJECT-TYPE
    SYNTAX       SnmpAdminString
    MAX-ACCESS   read-only
    STATUS       current
    DESCRIPTION
        "Cisco Firepower compute:PhysicalFsm:rn managed object property"
    ::= { cfprApComputePhysicalFsmEntry 3 }

cfprApComputePhysicalFsmCompletionTime OBJECT-TYPE
    SYNTAX       DateAndTime
    MAX-ACCESS   read-only
    STATUS       current
    DESCRIPTION
        "Cisco Firepower compute:PhysicalFsm:completionTime
        managed object property"
    ::= { cfprApComputePhysicalFsmEntry 4 }

cfprApComputePhysicalFsmCurrentFsm OBJECT-TYPE
    SYNTAX       CfprApComputePhysicalFsmCurrentFsm
    MAX-ACCESS   read-only
    STATUS       current
    DESCRIPTION
        "Cisco Firepower compute:PhysicalFsm:currentFsm
        managed object property"
    ::= { cfprApComputePhysicalFsmEntry 5 }

cfprApComputePhysicalFsmDescr OBJECT-TYPE
    SYNTAX       SnmpAdminString
    MAX-ACCESS   read-only
    STATUS       current
    DESCRIPTION
        "Cisco Firepower compute:PhysicalFsm:descr managed
        object property"
    ::= { cfprApComputePhysicalFsmEntry 6 }

cfprApComputePhysicalFsmFsmStatus OBJECT-TYPE
    SYNTAX       CfprApFsmFsmStageStatus
    MAX-ACCESS   read-only
    STATUS       current
    DESCRIPTION
        "Cisco Firepower compute:PhysicalFsm:fsmStatus
        managed object property"
    ::= { cfprApComputePhysicalFsmEntry 7 }

cfprApComputePhysicalFsmProgress OBJECT-TYPE
    SYNTAX       Gauge32
    MAX-ACCESS   read-only
    STATUS       current
    DESCRIPTION
        "Cisco Firepower compute:PhysicalFsm:progress managed
        object property"
    ::= { cfprApComputePhysicalFsmEntry 8 }

cfprApComputePhysicalFsmRmtErrCode OBJECT-TYPE
    SYNTAX       Gauge32
    MAX-ACCESS   read-only
    STATUS       current
    DESCRIPTION
        "Cisco Firepower compute:PhysicalFsm:rmtErrCode
        managed object property"
    ::= { cfprApComputePhysicalFsmEntry 9 }

cfprApComputePhysicalFsmRmtErrDescr OBJECT-TYPE
    SYNTAX       SnmpAdminString
    MAX-ACCESS   read-only
    STATUS       current
    DESCRIPTION
        "Cisco Firepower compute:PhysicalFsm:rmtErrDescr
        managed object property"
    ::= { cfprApComputePhysicalFsmEntry 10 }

cfprApComputePhysicalFsmRmtRslt OBJECT-TYPE
    SYNTAX       CfprApConditionRemoteInvRslt
    MAX-ACCESS   read-only
    STATUS       current
    DESCRIPTION
        "Cisco Firepower compute:PhysicalFsm:rmtRslt managed
        object property"
    ::= { cfprApComputePhysicalFsmEntry 11 }

cfprApComputePhysicalFsmStageTable OBJECT-TYPE
    SYNTAX           SEQUENCE OF CfprApComputePhysicalFsmStageEntry
    MAX-ACCESS       not-accessible
    STATUS           current
    DESCRIPTION
        "Cisco Firepower compute:PhysicalFsmStage managed object table"
    ::= { cfprApComputeObjects 38 }

cfprApComputePhysicalFsmStageEntry OBJECT-TYPE
    SYNTAX           CfprApComputePhysicalFsmStageEntry
    MAX-ACCESS       not-accessible
    STATUS           current
    DESCRIPTION
        "Entry for the cfprApComputePhysicalFsmStageTable table."
    INDEX { cfprApComputePhysicalFsmStageInstanceId }
    ::= { cfprApComputePhysicalFsmStageTable 1 }

CfprApComputePhysicalFsmStageEntry ::= SEQUENCE {
    cfprApComputePhysicalFsmStageInstanceId                          CfprApManagedObjectId,
    cfprApComputePhysicalFsmStageDn                                  CfprApManagedObjectDn,
    cfprApComputePhysicalFsmStageRn                                  SnmpAdminString,
    cfprApComputePhysicalFsmStageDescr                               SnmpAdminString,
    cfprApComputePhysicalFsmStageLastUpdateTime                      DateAndTime,
    cfprApComputePhysicalFsmStageName                                CfprApComputePhysicalFsmStageName,
    cfprApComputePhysicalFsmStageOrder                               Gauge32,
    cfprApComputePhysicalFsmStageRetry                               Gauge32,
    cfprApComputePhysicalFsmStageStageStatus                         CfprApFsmFsmStageStatus
}

cfprApComputePhysicalFsmStageInstanceId OBJECT-TYPE
    SYNTAX       CfprApManagedObjectId
    MAX-ACCESS   not-accessible
    STATUS       current
    DESCRIPTION
        "Instance identifier of the managed object."
    ::= { cfprApComputePhysicalFsmStageEntry 1 }

cfprApComputePhysicalFsmStageDn OBJECT-TYPE
    SYNTAX       CfprApManagedObjectDn
    MAX-ACCESS   read-only
    STATUS       current
    DESCRIPTION
        "Cisco Firepower compute:PhysicalFsmStage:dn managed
        object property"
    ::= { cfprApComputePhysicalFsmStageEntry 2 }

cfprApComputePhysicalFsmStageRn OBJECT-TYPE
    SYNTAX       SnmpAdminString
    MAX-ACCESS   read-only
    STATUS       current
    DESCRIPTION
        "Cisco Firepower compute:PhysicalFsmStage:rn managed
        object property"
    ::= { cfprApComputePhysicalFsmStageEntry 3 }

cfprApComputePhysicalFsmStageDescr OBJECT-TYPE
    SYNTAX       SnmpAdminString
    MAX-ACCESS   read-only
    STATUS       current
    DESCRIPTION
        "Cisco Firepower compute:PhysicalFsmStage:descr
        managed object property"
    ::= { cfprApComputePhysicalFsmStageEntry 4 }

cfprApComputePhysicalFsmStageLastUpdateTime OBJECT-TYPE
    SYNTAX       DateAndTime
    MAX-ACCESS   read-only
    STATUS       current
    DESCRIPTION
        "Cisco Firepower compute:PhysicalFsmStage:lastUpdateTime
        managed object property"
    ::= { cfprApComputePhysicalFsmStageEntry 5 }

cfprApComputePhysicalFsmStageName OBJECT-TYPE
    SYNTAX       CfprApComputePhysicalFsmStageName
    MAX-ACCESS   read-only
    STATUS       current
    DESCRIPTION
        "Cisco Firepower compute:PhysicalFsmStage:name
        managed object property"
    ::= { cfprApComputePhysicalFsmStageEntry 6 }

cfprApComputePhysicalFsmStageOrder OBJECT-TYPE
    SYNTAX       Gauge32
    MAX-ACCESS   read-only
    STATUS       current
    DESCRIPTION
        "Cisco Firepower compute:PhysicalFsmStage:order
        managed object property"
    ::= { cfprApComputePhysicalFsmStageEntry 7 }

cfprApComputePhysicalFsmStageRetry OBJECT-TYPE
    SYNTAX       Gauge32
    MAX-ACCESS   read-only
    STATUS       current
    DESCRIPTION
        "Cisco Firepower compute:PhysicalFsmStage:retry
        managed object property"
    ::= { cfprApComputePhysicalFsmStageEntry 8 }

cfprApComputePhysicalFsmStageStageStatus OBJECT-TYPE
    SYNTAX       CfprApFsmFsmStageStatus
    MAX-ACCESS   read-only
    STATUS       current
    DESCRIPTION
        "Cisco Firepower compute:PhysicalFsmStage:stageStatus
        managed object property"
    ::= { cfprApComputePhysicalFsmStageEntry 9 }

cfprApComputePhysicalFsmTaskTable OBJECT-TYPE
    SYNTAX           SEQUENCE OF CfprApComputePhysicalFsmTaskEntry
    MAX-ACCESS       not-accessible
    STATUS           current
    DESCRIPTION
        "Cisco Firepower compute:PhysicalFsmTask managed object table"
    ::= { cfprApComputeObjects 39 }

cfprApComputePhysicalFsmTaskEntry OBJECT-TYPE
    SYNTAX           CfprApComputePhysicalFsmTaskEntry
    MAX-ACCESS       not-accessible
    STATUS           current
    DESCRIPTION
        "Entry for the cfprApComputePhysicalFsmTaskTable table."
    INDEX { cfprApComputePhysicalFsmTaskInstanceId }
    ::= { cfprApComputePhysicalFsmTaskTable 1 }

CfprApComputePhysicalFsmTaskEntry ::= SEQUENCE {
    cfprApComputePhysicalFsmTaskInstanceId                           CfprApManagedObjectId,
    cfprApComputePhysicalFsmTaskDn                                   CfprApManagedObjectDn,
    cfprApComputePhysicalFsmTaskRn                                   SnmpAdminString,
    cfprApComputePhysicalFsmTaskCompletion                           CfprApFsmCompletion,
    cfprApComputePhysicalFsmTaskFlags                                CfprApFsmFlags,
    cfprApComputePhysicalFsmTaskItem                                 CfprApComputePhysicalFsmTaskItem,
    cfprApComputePhysicalFsmTaskSeqId                                Gauge32
}

cfprApComputePhysicalFsmTaskInstanceId OBJECT-TYPE
    SYNTAX       CfprApManagedObjectId
    MAX-ACCESS   not-accessible
    STATUS       current
    DESCRIPTION
        "Instance identifier of the managed object."
    ::= { cfprApComputePhysicalFsmTaskEntry 1 }

cfprApComputePhysicalFsmTaskDn OBJECT-TYPE
    SYNTAX       CfprApManagedObjectDn
    MAX-ACCESS   read-only
    STATUS       current
    DESCRIPTION
        "Cisco Firepower compute:PhysicalFsmTask:dn managed
        object property"
    ::= { cfprApComputePhysicalFsmTaskEntry 2 }

cfprApComputePhysicalFsmTaskRn OBJECT-TYPE
    SYNTAX       SnmpAdminString
    MAX-ACCESS   read-only
    STATUS       current
    DESCRIPTION
        "Cisco Firepower compute:PhysicalFsmTask:rn managed
        object property"
    ::= { cfprApComputePhysicalFsmTaskEntry 3 }

cfprApComputePhysicalFsmTaskCompletion OBJECT-TYPE
    SYNTAX       CfprApFsmCompletion
    MAX-ACCESS   read-only
    STATUS       current
    DESCRIPTION
        "Cisco Firepower compute:PhysicalFsmTask:completion
        managed object property"
    ::= { cfprApComputePhysicalFsmTaskEntry 4 }

cfprApComputePhysicalFsmTaskFlags OBJECT-TYPE
    SYNTAX       CfprApFsmFlags
    MAX-ACCESS   read-only
    STATUS       current
    DESCRIPTION
        "Cisco Firepower compute:PhysicalFsmTask:flags
        managed object property"
    ::= { cfprApComputePhysicalFsmTaskEntry 5 }

cfprApComputePhysicalFsmTaskItem OBJECT-TYPE
    SYNTAX       CfprApComputePhysicalFsmTaskItem
    MAX-ACCESS   read-only
    STATUS       current
    DESCRIPTION
        "Cisco Firepower compute:PhysicalFsmTask:item managed
        object property"
    ::= { cfprApComputePhysicalFsmTaskEntry 6 }

cfprApComputePhysicalFsmTaskSeqId OBJECT-TYPE
    SYNTAX       Gauge32
    MAX-ACCESS   read-only
    STATUS       current
    DESCRIPTION
        "Cisco Firepower compute:PhysicalFsmTask:seqId
        managed object property"
    ::= { cfprApComputePhysicalFsmTaskEntry 7 }

cfprApComputePhysicalQualTable OBJECT-TYPE
    SYNTAX           SEQUENCE OF CfprApComputePhysicalQualEntry
    MAX-ACCESS       not-accessible
    STATUS           current
    DESCRIPTION
        "Cisco Firepower compute:PhysicalQual managed object table"
    ::= { cfprApComputeObjects 40 }

cfprApComputePhysicalQualEntry OBJECT-TYPE
    SYNTAX           CfprApComputePhysicalQualEntry
    MAX-ACCESS       not-accessible
    STATUS           current
    DESCRIPTION
        "Entry for the cfprApComputePhysicalQualTable table."
    INDEX { cfprApComputePhysicalQualInstanceId }
    ::= { cfprApComputePhysicalQualTable 1 }

CfprApComputePhysicalQualEntry ::= SEQUENCE {
    cfprApComputePhysicalQualInstanceId                              CfprApManagedObjectId,
    cfprApComputePhysicalQualDn                                      CfprApManagedObjectDn,
    cfprApComputePhysicalQualRn                                      SnmpAdminString,
    cfprApComputePhysicalQualModel                                   SnmpAdminString
}

cfprApComputePhysicalQualInstanceId OBJECT-TYPE
    SYNTAX       CfprApManagedObjectId
    MAX-ACCESS   not-accessible
    STATUS       current
    DESCRIPTION
        "Instance identifier of the managed object."
    ::= { cfprApComputePhysicalQualEntry 1 }

cfprApComputePhysicalQualDn OBJECT-TYPE
    SYNTAX       CfprApManagedObjectDn
    MAX-ACCESS   read-only
    STATUS       current
    DESCRIPTION
        "Cisco Firepower compute:PhysicalQual:dn managed object property"
    ::= { cfprApComputePhysicalQualEntry 2 }

cfprApComputePhysicalQualRn OBJECT-TYPE
    SYNTAX       SnmpAdminString
    MAX-ACCESS   read-only
    STATUS       current
    DESCRIPTION
        "Cisco Firepower compute:PhysicalQual:rn managed object property"
    ::= { cfprApComputePhysicalQualEntry 3 }

cfprApComputePhysicalQualModel OBJECT-TYPE
    SYNTAX       SnmpAdminString
    MAX-ACCESS   read-only
    STATUS       current
    DESCRIPTION
        "Cisco Firepower compute:PhysicalQual:model managed
        object property"
    ::= { cfprApComputePhysicalQualEntry 4 }

cfprApComputePlatformTable OBJECT-TYPE
    SYNTAX           SEQUENCE OF CfprApComputePlatformEntry
    MAX-ACCESS       not-accessible
    STATUS           current
    DESCRIPTION
        "Cisco Firepower compute:Platform managed object table"
    ::= { cfprApComputeObjects 41 }

cfprApComputePlatformEntry OBJECT-TYPE
    SYNTAX           CfprApComputePlatformEntry
    MAX-ACCESS       not-accessible
    STATUS           current
    DESCRIPTION
        "Entry for the cfprApComputePlatformTable table."
    INDEX { cfprApComputePlatformInstanceId }
    ::= { cfprApComputePlatformTable 1 }

CfprApComputePlatformEntry ::= SEQUENCE {
    cfprApComputePlatformInstanceId                                  CfprApManagedObjectId,
    cfprApComputePlatformDn                                          CfprApManagedObjectDn,
    cfprApComputePlatformRn                                          SnmpAdminString,
    cfprApComputePlatformModel                                       SnmpAdminString,
    cfprApComputePlatformProductName                                 SnmpAdminString,
    cfprApComputePlatformRevision                                    SnmpAdminString,
    cfprApComputePlatformVendor                                      SnmpAdminString
}

cfprApComputePlatformInstanceId OBJECT-TYPE
    SYNTAX       CfprApManagedObjectId
    MAX-ACCESS   not-accessible
    STATUS       current
    DESCRIPTION
        "Instance identifier of the managed object."
    ::= { cfprApComputePlatformEntry 1 }

cfprApComputePlatformDn OBJECT-TYPE
    SYNTAX       CfprApManagedObjectDn
    MAX-ACCESS   read-only
    STATUS       current
    DESCRIPTION
        "Cisco Firepower compute:Platform:dn managed object property"
    ::= { cfprApComputePlatformEntry 2 }

cfprApComputePlatformRn OBJECT-TYPE
    SYNTAX       SnmpAdminString
    MAX-ACCESS   read-only
    STATUS       current
    DESCRIPTION
        "Cisco Firepower compute:Platform:rn managed object property"
    ::= { cfprApComputePlatformEntry 3 }

cfprApComputePlatformModel OBJECT-TYPE
    SYNTAX       SnmpAdminString
    MAX-ACCESS   read-only
    STATUS       current
    DESCRIPTION
        "Cisco Firepower compute:Platform:model managed object property"
    ::= { cfprApComputePlatformEntry 4 }

cfprApComputePlatformProductName OBJECT-TYPE
    SYNTAX       SnmpAdminString
    MAX-ACCESS   read-only
    STATUS       current
    DESCRIPTION
        "Cisco Firepower compute:Platform:productName managed
        object property"
    ::= { cfprApComputePlatformEntry 5 }

cfprApComputePlatformRevision OBJECT-TYPE
    SYNTAX       SnmpAdminString
    MAX-ACCESS   read-only
    STATUS       current
    DESCRIPTION
        "Cisco Firepower compute:Platform:revision managed
        object property"
    ::= { cfprApComputePlatformEntry 6 }

cfprApComputePlatformVendor OBJECT-TYPE
    SYNTAX       SnmpAdminString
    MAX-ACCESS   read-only
    STATUS       current
    DESCRIPTION
        "Cisco Firepower compute:Platform:vendor managed object property"
    ::= { cfprApComputePlatformEntry 7 }

cfprApComputePnuOSImageTable OBJECT-TYPE
    SYNTAX           SEQUENCE OF CfprApComputePnuOSImageEntry
    MAX-ACCESS       not-accessible
    STATUS           current
    DESCRIPTION
        "Cisco Firepower compute:PnuOSImage managed object table"
    ::= { cfprApComputeObjects 42 }

cfprApComputePnuOSImageEntry OBJECT-TYPE
    SYNTAX           CfprApComputePnuOSImageEntry
    MAX-ACCESS       not-accessible
    STATUS           current
    DESCRIPTION
        "Entry for the cfprApComputePnuOSImageTable table."
    INDEX { cfprApComputePnuOSImageInstanceId }
    ::= { cfprApComputePnuOSImageTable 1 }

CfprApComputePnuOSImageEntry ::= SEQUENCE {
    cfprApComputePnuOSImageInstanceId                                CfprApManagedObjectId,
    cfprApComputePnuOSImageDn                                        CfprApManagedObjectDn,
    cfprApComputePnuOSImageRn                                        SnmpAdminString,
    cfprApComputePnuOSImageImgLFBFFName                              SnmpAdminString,
    cfprApComputePnuOSImageImgLoc                                    SnmpAdminString,
    cfprApComputePnuOSImageImgName                                   SnmpAdminString
}

cfprApComputePnuOSImageInstanceId OBJECT-TYPE
    SYNTAX       CfprApManagedObjectId
    MAX-ACCESS   not-accessible
    STATUS       current
    DESCRIPTION
        "Instance identifier of the managed object."
    ::= { cfprApComputePnuOSImageEntry 1 }

cfprApComputePnuOSImageDn OBJECT-TYPE
    SYNTAX       CfprApManagedObjectDn
    MAX-ACCESS   read-only
    STATUS       current
    DESCRIPTION
        "Cisco Firepower compute:PnuOSImage:dn managed object property"
    ::= { cfprApComputePnuOSImageEntry 2 }

cfprApComputePnuOSImageRn OBJECT-TYPE
    SYNTAX       SnmpAdminString
    MAX-ACCESS   read-only
    STATUS       current
    DESCRIPTION
        "Cisco Firepower compute:PnuOSImage:rn managed object property"
    ::= { cfprApComputePnuOSImageEntry 3 }

cfprApComputePnuOSImageImgLFBFFName OBJECT-TYPE
    SYNTAX       SnmpAdminString
    MAX-ACCESS   read-only
    STATUS       current
    DESCRIPTION
        "Cisco Firepower compute:PnuOSImage:imgLFBFFName
        managed object property"
    ::= { cfprApComputePnuOSImageEntry 4 }

cfprApComputePnuOSImageImgLoc OBJECT-TYPE
    SYNTAX       SnmpAdminString
    MAX-ACCESS   read-only
    STATUS       current
    DESCRIPTION
        "Cisco Firepower compute:PnuOSImage:imgLoc managed
        object property"
    ::= { cfprApComputePnuOSImageEntry 5 }

cfprApComputePnuOSImageImgName OBJECT-TYPE
    SYNTAX       SnmpAdminString
    MAX-ACCESS   read-only
    STATUS       current
    DESCRIPTION
        "Cisco Firepower compute:PnuOSImage:imgName managed
        object property"
    ::= { cfprApComputePnuOSImageEntry 6 }

cfprApComputePoolTable OBJECT-TYPE
    SYNTAX           SEQUENCE OF CfprApComputePoolEntry
    MAX-ACCESS       not-accessible
    STATUS           current
    DESCRIPTION
        "Cisco Firepower compute:Pool managed object table"
    ::= { cfprApComputeObjects 43 }

cfprApComputePoolEntry OBJECT-TYPE
    SYNTAX           CfprApComputePoolEntry
    MAX-ACCESS       not-accessible
    STATUS           current
    DESCRIPTION
        "Entry for the cfprApComputePoolTable table."
    INDEX { cfprApComputePoolInstanceId }
    ::= { cfprApComputePoolTable 1 }

CfprApComputePoolEntry ::= SEQUENCE {
    cfprApComputePoolInstanceId                                      CfprApManagedObjectId,
    cfprApComputePoolDn                                              CfprApManagedObjectDn,
    cfprApComputePoolRn                                              SnmpAdminString,
    cfprApComputePoolAssigned                                        Gauge32,
    cfprApComputePoolAssignmentOrder                                 CfprApPoolPoolAssignmentOrder,
    cfprApComputePoolDescr                                           SnmpAdminString,
    cfprApComputePoolIntId                                           SnmpAdminString,
    cfprApComputePoolName                                            SnmpAdminString,
    cfprApComputePoolPolicyLevel                                     Gauge32,
    cfprApComputePoolPolicyOwner                                     CfprApPolicyPolicyOwner,
    cfprApComputePoolSize                                            Gauge32
}

cfprApComputePoolInstanceId OBJECT-TYPE
    SYNTAX       CfprApManagedObjectId
    MAX-ACCESS   not-accessible
    STATUS       current
    DESCRIPTION
        "Instance identifier of the managed object."
    ::= { cfprApComputePoolEntry 1 }

cfprApComputePoolDn OBJECT-TYPE
    SYNTAX       CfprApManagedObjectDn
    MAX-ACCESS   read-only
    STATUS       current
    DESCRIPTION
        "Cisco Firepower compute:Pool:dn managed object property"
    ::= { cfprApComputePoolEntry 2 }

cfprApComputePoolRn OBJECT-TYPE
    SYNTAX       SnmpAdminString
    MAX-ACCESS   read-only
    STATUS       current
    DESCRIPTION
        "Cisco Firepower compute:Pool:rn managed object property"
    ::= { cfprApComputePoolEntry 3 }

cfprApComputePoolAssigned OBJECT-TYPE
    SYNTAX       Gauge32
    MAX-ACCESS   read-only
    STATUS       current
    DESCRIPTION
        "Cisco Firepower compute:Pool:assigned managed object property"
    ::= { cfprApComputePoolEntry 4 }

cfprApComputePoolAssignmentOrder OBJECT-TYPE
    SYNTAX       CfprApPoolPoolAssignmentOrder
    MAX-ACCESS   read-only
    STATUS       current
    DESCRIPTION
        "Cisco Firepower compute:Pool:assignmentOrder managed
        object property"
    ::= { cfprApComputePoolEntry 5 }

cfprApComputePoolDescr OBJECT-TYPE
    SYNTAX       SnmpAdminString
    MAX-ACCESS   read-only
    STATUS       current
    DESCRIPTION
        "Cisco Firepower compute:Pool:descr managed object property"
    ::= { cfprApComputePoolEntry 6 }

cfprApComputePoolIntId OBJECT-TYPE
    SYNTAX       SnmpAdminString
    MAX-ACCESS   read-only
    STATUS       current
    DESCRIPTION
        "Cisco Firepower compute:Pool:intId managed object property"
    ::= { cfprApComputePoolEntry 7 }

cfprApComputePoolName OBJECT-TYPE
    SYNTAX       SnmpAdminString
    MAX-ACCESS   read-only
    STATUS       current
    DESCRIPTION
        "Cisco Firepower compute:Pool:name managed object property"
    ::= { cfprApComputePoolEntry 8 }

cfprApComputePoolPolicyLevel OBJECT-TYPE
    SYNTAX       Gauge32
    MAX-ACCESS   read-only
    STATUS       current
    DESCRIPTION
        "Cisco Firepower compute:Pool:policyLevel managed object property"
    ::= { cfprApComputePoolEntry 9 }

cfprApComputePoolPolicyOwner OBJECT-TYPE
    SYNTAX       CfprApPolicyPolicyOwner
    MAX-ACCESS   read-only
    STATUS       current
    DESCRIPTION
        "Cisco Firepower compute:Pool:policyOwner managed object property"
    ::= { cfprApComputePoolEntry 10 }

cfprApComputePoolSize OBJECT-TYPE
    SYNTAX       Gauge32
    MAX-ACCESS   read-only
    STATUS       current
    DESCRIPTION
        "Cisco Firepower compute:Pool:size managed object property"
    ::= { cfprApComputePoolEntry 11 }

cfprApComputePoolPolicyRefTable OBJECT-TYPE
    SYNTAX           SEQUENCE OF CfprApComputePoolPolicyRefEntry
    MAX-ACCESS       not-accessible
    STATUS           current
    DESCRIPTION
        "Cisco Firepower compute:PoolPolicyRef managed object table"
    ::= { cfprApComputeObjects 44 }

cfprApComputePoolPolicyRefEntry OBJECT-TYPE
    SYNTAX           CfprApComputePoolPolicyRefEntry
    MAX-ACCESS       not-accessible
    STATUS           current
    DESCRIPTION
        "Entry for the cfprApComputePoolPolicyRefTable table."
    INDEX { cfprApComputePoolPolicyRefInstanceId }
    ::= { cfprApComputePoolPolicyRefTable 1 }

CfprApComputePoolPolicyRefEntry ::= SEQUENCE {
    cfprApComputePoolPolicyRefInstanceId                             CfprApManagedObjectId,
    cfprApComputePoolPolicyRefDn                                     CfprApManagedObjectDn,
    cfprApComputePoolPolicyRefRn                                     SnmpAdminString,
    cfprApComputePoolPolicyRefId                                     Unsigned64,
    cfprApComputePoolPolicyRefPolicyDn                               SnmpAdminString
}

cfprApComputePoolPolicyRefInstanceId OBJECT-TYPE
    SYNTAX       CfprApManagedObjectId
    MAX-ACCESS   not-accessible
    STATUS       current
    DESCRIPTION
        "Instance identifier of the managed object."
    ::= { cfprApComputePoolPolicyRefEntry 1 }

cfprApComputePoolPolicyRefDn OBJECT-TYPE
    SYNTAX       CfprApManagedObjectDn
    MAX-ACCESS   read-only
    STATUS       current
    DESCRIPTION
        "Cisco Firepower compute:PoolPolicyRef:dn managed object property"
    ::= { cfprApComputePoolPolicyRefEntry 2 }

cfprApComputePoolPolicyRefRn OBJECT-TYPE
    SYNTAX       SnmpAdminString
    MAX-ACCESS   read-only
    STATUS       current
    DESCRIPTION
        "Cisco Firepower compute:PoolPolicyRef:rn managed object property"
    ::= { cfprApComputePoolPolicyRefEntry 3 }

cfprApComputePoolPolicyRefId OBJECT-TYPE
    SYNTAX       Unsigned64
    MAX-ACCESS   read-only
    STATUS       current
    DESCRIPTION
        "Cisco Firepower compute:PoolPolicyRef:id managed object property"
    ::= { cfprApComputePoolPolicyRefEntry 4 }

cfprApComputePoolPolicyRefPolicyDn OBJECT-TYPE
    SYNTAX       SnmpAdminString
    MAX-ACCESS   read-only
    STATUS       current
    DESCRIPTION
        "Cisco Firepower compute:PoolPolicyRef:policyDn
        managed object property"
    ::= { cfprApComputePoolPolicyRefEntry 5 }

cfprApComputePoolableTable OBJECT-TYPE
    SYNTAX           SEQUENCE OF CfprApComputePoolableEntry
    MAX-ACCESS       not-accessible
    STATUS           current
    DESCRIPTION
        "Cisco Firepower compute:Poolable managed object table"
    ::= { cfprApComputeObjects 45 }

cfprApComputePoolableEntry OBJECT-TYPE
    SYNTAX           CfprApComputePoolableEntry
    MAX-ACCESS       not-accessible
    STATUS           current
    DESCRIPTION
        "Entry for the cfprApComputePoolableTable table."
    INDEX { cfprApComputePoolableInstanceId }
    ::= { cfprApComputePoolableTable 1 }

CfprApComputePoolableEntry ::= SEQUENCE {
    cfprApComputePoolableInstanceId                                  CfprApManagedObjectId,
    cfprApComputePoolableDn                                          CfprApManagedObjectDn,
    cfprApComputePoolableRn                                          SnmpAdminString,
    cfprApComputePoolableId                                          Unsigned64,
    cfprApComputePoolablePoolDn                                      SnmpAdminString
}

cfprApComputePoolableInstanceId OBJECT-TYPE
    SYNTAX       CfprApManagedObjectId
    MAX-ACCESS   not-accessible
    STATUS       current
    DESCRIPTION
        "Instance identifier of the managed object."
    ::= { cfprApComputePoolableEntry 1 }

cfprApComputePoolableDn OBJECT-TYPE
    SYNTAX       CfprApManagedObjectDn
    MAX-ACCESS   read-only
    STATUS       current
    DESCRIPTION
        "Cisco Firepower compute:Poolable:dn managed object property"
    ::= { cfprApComputePoolableEntry 2 }

cfprApComputePoolableRn OBJECT-TYPE
    SYNTAX       SnmpAdminString
    MAX-ACCESS   read-only
    STATUS       current
    DESCRIPTION
        "Cisco Firepower compute:Poolable:rn managed object property"
    ::= { cfprApComputePoolableEntry 3 }

cfprApComputePoolableId OBJECT-TYPE
    SYNTAX       Unsigned64
    MAX-ACCESS   read-only
    STATUS       current
    DESCRIPTION
        "Cisco Firepower compute:Poolable:id managed object property"
    ::= { cfprApComputePoolableEntry 4 }

cfprApComputePoolablePoolDn OBJECT-TYPE
    SYNTAX       SnmpAdminString
    MAX-ACCESS   read-only
    STATUS       current
    DESCRIPTION
        "Cisco Firepower compute:Poolable:poolDn managed object property"
    ::= { cfprApComputePoolableEntry 5 }

cfprApComputePooledRackUnitTable OBJECT-TYPE
    SYNTAX           SEQUENCE OF CfprApComputePooledRackUnitEntry
    MAX-ACCESS       not-accessible
    STATUS           current
    DESCRIPTION
        "Cisco Firepower compute:PooledRackUnit managed object table"
    ::= { cfprApComputeObjects 46 }

cfprApComputePooledRackUnitEntry OBJECT-TYPE
    SYNTAX           CfprApComputePooledRackUnitEntry
    MAX-ACCESS       not-accessible
    STATUS           current
    DESCRIPTION
        "Entry for the cfprApComputePooledRackUnitTable table."
    INDEX { cfprApComputePooledRackUnitInstanceId }
    ::= { cfprApComputePooledRackUnitTable 1 }

CfprApComputePooledRackUnitEntry ::= SEQUENCE {
    cfprApComputePooledRackUnitInstanceId                            CfprApManagedObjectId,
    cfprApComputePooledRackUnitDn                                    CfprApManagedObjectDn,
    cfprApComputePooledRackUnitRn                                    SnmpAdminString,
    cfprApComputePooledRackUnitAssigned                              TruthValue,
    cfprApComputePooledRackUnitAssignedToDn                          SnmpAdminString,
    cfprApComputePooledRackUnitId                                    CfprApComputePooledRackUnitId,
    cfprApComputePooledRackUnitOwner                                 CfprApComputeOwner,
    cfprApComputePooledRackUnitPoolableDn                            SnmpAdminString,
    cfprApComputePooledRackUnitPrevAssignedToDn                      SnmpAdminString
}

cfprApComputePooledRackUnitInstanceId OBJECT-TYPE
    SYNTAX       CfprApManagedObjectId
    MAX-ACCESS   not-accessible
    STATUS       current
    DESCRIPTION
        "Instance identifier of the managed object."
    ::= { cfprApComputePooledRackUnitEntry 1 }

cfprApComputePooledRackUnitDn OBJECT-TYPE
    SYNTAX       CfprApManagedObjectDn
    MAX-ACCESS   read-only
    STATUS       current
    DESCRIPTION
        "Cisco Firepower compute:PooledRackUnit:dn managed
        object property"
    ::= { cfprApComputePooledRackUnitEntry 2 }

cfprApComputePooledRackUnitRn OBJECT-TYPE
    SYNTAX       SnmpAdminString
    MAX-ACCESS   read-only
    STATUS       current
    DESCRIPTION
        "Cisco Firepower compute:PooledRackUnit:rn managed
        object property"
    ::= { cfprApComputePooledRackUnitEntry 3 }

cfprApComputePooledRackUnitAssigned OBJECT-TYPE
    SYNTAX       TruthValue
    MAX-ACCESS   read-only
    STATUS       current
    DESCRIPTION
        "Cisco Firepower compute:PooledRackUnit:assigned
        managed object property"
    ::= { cfprApComputePooledRackUnitEntry 4 }

cfprApComputePooledRackUnitAssignedToDn OBJECT-TYPE
    SYNTAX       SnmpAdminString
    MAX-ACCESS   read-only
    STATUS       current
    DESCRIPTION
        "Cisco Firepower compute:PooledRackUnit:assignedToDn
        managed object property"
    ::= { cfprApComputePooledRackUnitEntry 5 }

cfprApComputePooledRackUnitId OBJECT-TYPE
    SYNTAX       CfprApComputePooledRackUnitId
    MAX-ACCESS   read-only
    STATUS       current
    DESCRIPTION
        "Cisco Firepower compute:PooledRackUnit:id managed
        object property"
    ::= { cfprApComputePooledRackUnitEntry 6 }

cfprApComputePooledRackUnitOwner OBJECT-TYPE
    SYNTAX       CfprApComputeOwner
    MAX-ACCESS   read-only
    STATUS       current
    DESCRIPTION
        "Cisco Firepower compute:PooledRackUnit:owner managed
        object property"
    ::= { cfprApComputePooledRackUnitEntry 7 }

cfprApComputePooledRackUnitPoolableDn OBJECT-TYPE
    SYNTAX       SnmpAdminString
    MAX-ACCESS   read-only
    STATUS       current
    DESCRIPTION
        "Cisco Firepower compute:PooledRackUnit:poolableDn
        managed object property"
    ::= { cfprApComputePooledRackUnitEntry 8 }

cfprApComputePooledRackUnitPrevAssignedToDn OBJECT-TYPE
    SYNTAX       SnmpAdminString
    MAX-ACCESS   read-only
    STATUS       current
    DESCRIPTION
        "Cisco Firepower compute:PooledRackUnit:prevAssignedToDn
        managed object property"
    ::= { cfprApComputePooledRackUnitEntry 9 }

cfprApComputePooledSlotTable OBJECT-TYPE
    SYNTAX           SEQUENCE OF CfprApComputePooledSlotEntry
    MAX-ACCESS       not-accessible
    STATUS           current
    DESCRIPTION
        "Cisco Firepower compute:PooledSlot managed object table"
    ::= { cfprApComputeObjects 47 }

cfprApComputePooledSlotEntry OBJECT-TYPE
    SYNTAX           CfprApComputePooledSlotEntry
    MAX-ACCESS       not-accessible
    STATUS           current
    DESCRIPTION
        "Entry for the cfprApComputePooledSlotTable table."
    INDEX { cfprApComputePooledSlotInstanceId }
    ::= { cfprApComputePooledSlotTable 1 }

CfprApComputePooledSlotEntry ::= SEQUENCE {
    cfprApComputePooledSlotInstanceId                                CfprApManagedObjectId,
    cfprApComputePooledSlotDn                                        CfprApManagedObjectDn,
    cfprApComputePooledSlotRn                                        SnmpAdminString,
    cfprApComputePooledSlotAssigned                                  TruthValue,
    cfprApComputePooledSlotAssignedToDn                              SnmpAdminString,
    cfprApComputePooledSlotChassisId                                 Gauge32,
    cfprApComputePooledSlotOwner                                     CfprApComputeOwner,
    cfprApComputePooledSlotPoolableDn                                SnmpAdminString,
    cfprApComputePooledSlotPrevAssignedToDn                          SnmpAdminString,
    cfprApComputePooledSlotSlotId                                    CfprApComputePooledSlotSlotId
}

cfprApComputePooledSlotInstanceId OBJECT-TYPE
    SYNTAX       CfprApManagedObjectId
    MAX-ACCESS   not-accessible
    STATUS       current
    DESCRIPTION
        "Instance identifier of the managed object."
    ::= { cfprApComputePooledSlotEntry 1 }

cfprApComputePooledSlotDn OBJECT-TYPE
    SYNTAX       CfprApManagedObjectDn
    MAX-ACCESS   read-only
    STATUS       current
    DESCRIPTION
        "Cisco Firepower compute:PooledSlot:dn managed object property"
    ::= { cfprApComputePooledSlotEntry 2 }

cfprApComputePooledSlotRn OBJECT-TYPE
    SYNTAX       SnmpAdminString
    MAX-ACCESS   read-only
    STATUS       current
    DESCRIPTION
        "Cisco Firepower compute:PooledSlot:rn managed object property"
    ::= { cfprApComputePooledSlotEntry 3 }

cfprApComputePooledSlotAssigned OBJECT-TYPE
    SYNTAX       TruthValue
    MAX-ACCESS   read-only
    STATUS       current
    DESCRIPTION
        "Cisco Firepower compute:PooledSlot:assigned managed
        object property"
    ::= { cfprApComputePooledSlotEntry 4 }

cfprApComputePooledSlotAssignedToDn OBJECT-TYPE
    SYNTAX       SnmpAdminString
    MAX-ACCESS   read-only
    STATUS       current
    DESCRIPTION
        "Cisco Firepower compute:PooledSlot:assignedToDn
        managed object property"
    ::= { cfprApComputePooledSlotEntry 5 }

cfprApComputePooledSlotChassisId OBJECT-TYPE
    SYNTAX       Gauge32
    MAX-ACCESS   read-only
    STATUS       current
    DESCRIPTION
        "Cisco Firepower compute:PooledSlot:chassisId managed
        object property"
    ::= { cfprApComputePooledSlotEntry 6 }

cfprApComputePooledSlotOwner OBJECT-TYPE
    SYNTAX       CfprApComputeOwner
    MAX-ACCESS   read-only
    STATUS       current
    DESCRIPTION
        "Cisco Firepower compute:PooledSlot:owner managed object property"
    ::= { cfprApComputePooledSlotEntry 7 }

cfprApComputePooledSlotPoolableDn OBJECT-TYPE
    SYNTAX       SnmpAdminString
    MAX-ACCESS   read-only
    STATUS       current
    DESCRIPTION
        "Cisco Firepower compute:PooledSlot:poolableDn
        managed object property"
    ::= { cfprApComputePooledSlotEntry 8 }

cfprApComputePooledSlotPrevAssignedToDn OBJECT-TYPE
    SYNTAX       SnmpAdminString
    MAX-ACCESS   read-only
    STATUS       current
    DESCRIPTION
        "Cisco Firepower compute:PooledSlot:prevAssignedToDn
        managed object property"
    ::= { cfprApComputePooledSlotEntry 9 }

cfprApComputePooledSlotSlotId OBJECT-TYPE
    SYNTAX       CfprApComputePooledSlotSlotId
    MAX-ACCESS   read-only
    STATUS       current
    DESCRIPTION
        "Cisco Firepower compute:PooledSlot:slotId managed
        object property"
    ::= { cfprApComputePooledSlotEntry 10 }

cfprApComputePoolingPolicyTable OBJECT-TYPE
    SYNTAX           SEQUENCE OF CfprApComputePoolingPolicyEntry
    MAX-ACCESS       not-accessible
    STATUS           current
    DESCRIPTION
        "Cisco Firepower compute:PoolingPolicy managed object table"
    ::= { cfprApComputeObjects 48 }

cfprApComputePoolingPolicyEntry OBJECT-TYPE
    SYNTAX           CfprApComputePoolingPolicyEntry
    MAX-ACCESS       not-accessible
    STATUS           current
    DESCRIPTION
        "Entry for the cfprApComputePoolingPolicyTable table."
    INDEX { cfprApComputePoolingPolicyInstanceId }
    ::= { cfprApComputePoolingPolicyTable 1 }

CfprApComputePoolingPolicyEntry ::= SEQUENCE {
    cfprApComputePoolingPolicyInstanceId                             CfprApManagedObjectId,
    cfprApComputePoolingPolicyDn                                     CfprApManagedObjectDn,
    cfprApComputePoolingPolicyRn                                     SnmpAdminString,
    cfprApComputePoolingPolicyDescr                                  SnmpAdminString,
    cfprApComputePoolingPolicyIntId                                  SnmpAdminString,
    cfprApComputePoolingPolicyName                                   SnmpAdminString,
    cfprApComputePoolingPolicyPolicyLevel                            Gauge32,
    cfprApComputePoolingPolicyPolicyOwner                            CfprApPolicyPolicyOwner,
    cfprApComputePoolingPolicyPoolDn                                 SnmpAdminString,
    cfprApComputePoolingPolicyQualifier                              SnmpAdminString
}

cfprApComputePoolingPolicyInstanceId OBJECT-TYPE
    SYNTAX       CfprApManagedObjectId
    MAX-ACCESS   not-accessible
    STATUS       current
    DESCRIPTION
        "Instance identifier of the managed object."
    ::= { cfprApComputePoolingPolicyEntry 1 }

cfprApComputePoolingPolicyDn OBJECT-TYPE
    SYNTAX       CfprApManagedObjectDn
    MAX-ACCESS   read-only
    STATUS       current
    DESCRIPTION
        "Cisco Firepower compute:PoolingPolicy:dn managed object property"
    ::= { cfprApComputePoolingPolicyEntry 2 }

cfprApComputePoolingPolicyRn OBJECT-TYPE
    SYNTAX       SnmpAdminString
    MAX-ACCESS   read-only
    STATUS       current
    DESCRIPTION
        "Cisco Firepower compute:PoolingPolicy:rn managed object property"
    ::= { cfprApComputePoolingPolicyEntry 3 }

cfprApComputePoolingPolicyDescr OBJECT-TYPE
    SYNTAX       SnmpAdminString
    MAX-ACCESS   read-only
    STATUS       current
    DESCRIPTION
        "Cisco Firepower compute:PoolingPolicy:descr managed
        object property"
    ::= { cfprApComputePoolingPolicyEntry 4 }

cfprApComputePoolingPolicyIntId OBJECT-TYPE
    SYNTAX       SnmpAdminString
    MAX-ACCESS   read-only
    STATUS       current
    DESCRIPTION
        "Cisco Firepower compute:PoolingPolicy:intId managed
        object property"
    ::= { cfprApComputePoolingPolicyEntry 5 }

cfprApComputePoolingPolicyName OBJECT-TYPE
    SYNTAX       SnmpAdminString
    MAX-ACCESS   read-only
    STATUS       current
    DESCRIPTION
        "Cisco Firepower compute:PoolingPolicy:name managed
        object property"
    ::= { cfprApComputePoolingPolicyEntry 6 }

cfprApComputePoolingPolicyPolicyLevel OBJECT-TYPE
    SYNTAX       Gauge32
    MAX-ACCESS   read-only
    STATUS       current
    DESCRIPTION
        "Cisco Firepower compute:PoolingPolicy:policyLevel
        managed object property"
    ::= { cfprApComputePoolingPolicyEntry 7 }

cfprApComputePoolingPolicyPolicyOwner OBJECT-TYPE
    SYNTAX       CfprApPolicyPolicyOwner
    MAX-ACCESS   read-only
    STATUS       current
    DESCRIPTION
        "Cisco Firepower compute:PoolingPolicy:policyOwner
        managed object property"
    ::= { cfprApComputePoolingPolicyEntry 8 }

cfprApComputePoolingPolicyPoolDn OBJECT-TYPE
    SYNTAX       SnmpAdminString
    MAX-ACCESS   read-only
    STATUS       current
    DESCRIPTION
        "Cisco Firepower compute:PoolingPolicy:poolDn managed
        object property"
    ::= { cfprApComputePoolingPolicyEntry 9 }

cfprApComputePoolingPolicyQualifier OBJECT-TYPE
    SYNTAX       SnmpAdminString
    MAX-ACCESS   read-only
    STATUS       current
    DESCRIPTION
        "Cisco Firepower compute:PoolingPolicy:qualifier
        managed object property"
    ::= { cfprApComputePoolingPolicyEntry 10 }

cfprApComputePsuControlTable OBJECT-TYPE
    SYNTAX           SEQUENCE OF CfprApComputePsuControlEntry
    MAX-ACCESS       not-accessible
    STATUS           current
    DESCRIPTION
        "Cisco Firepower compute:PsuControl managed object table"
    ::= { cfprApComputeObjects 49 }

cfprApComputePsuControlEntry OBJECT-TYPE
    SYNTAX           CfprApComputePsuControlEntry
    MAX-ACCESS       not-accessible
    STATUS           current
    DESCRIPTION
        "Entry for the cfprApComputePsuControlTable table."
    INDEX { cfprApComputePsuControlInstanceId }
    ::= { cfprApComputePsuControlTable 1 }

CfprApComputePsuControlEntry ::= SEQUENCE {
    cfprApComputePsuControlInstanceId                                CfprApManagedObjectId,
    cfprApComputePsuControlDn                                        CfprApManagedObjectDn,
    cfprApComputePsuControlRn                                        SnmpAdminString,
    cfprApComputePsuControlClusterState                              CfprApComputePsuClusterState,
    cfprApComputePsuControlDescr                                     SnmpAdminString,
    cfprApComputePsuControlInputPowerState                           CfprApEquipmentSensorThresholdStatus,
    cfprApComputePsuControlIntId                                     SnmpAdminString,
    cfprApComputePsuControlName                                      SnmpAdminString,
    cfprApComputePsuControlOperQualifier                             CfprApComputePsuRedundancyOperQualifier,
    cfprApComputePsuControlOperState                                 CfprApComputePsuRedundancyOperState,
    cfprApComputePsuControlOutputPowerState                          CfprApEquipmentSensorThresholdStatus,
    cfprApComputePsuControlPolicyLevel                               Gauge32,
    cfprApComputePsuControlPolicyOwner                               CfprApPolicyPolicyOwner,
    cfprApComputePsuControlRedundancy                                CfprApComputePsuControlRedundancy
}

cfprApComputePsuControlInstanceId OBJECT-TYPE
    SYNTAX       CfprApManagedObjectId
    MAX-ACCESS   not-accessible
    STATUS       current
    DESCRIPTION
        "Instance identifier of the managed object."
    ::= { cfprApComputePsuControlEntry 1 }

cfprApComputePsuControlDn OBJECT-TYPE
    SYNTAX       CfprApManagedObjectDn
    MAX-ACCESS   read-only
    STATUS       current
    DESCRIPTION
        "Cisco Firepower compute:PsuControl:dn managed object property"
    ::= { cfprApComputePsuControlEntry 2 }

cfprApComputePsuControlRn OBJECT-TYPE
    SYNTAX       SnmpAdminString
    MAX-ACCESS   read-only
    STATUS       current
    DESCRIPTION
        "Cisco Firepower compute:PsuControl:rn managed object property"
    ::= { cfprApComputePsuControlEntry 3 }

cfprApComputePsuControlClusterState OBJECT-TYPE
    SYNTAX       CfprApComputePsuClusterState
    MAX-ACCESS   read-only
    STATUS       current
    DESCRIPTION
        "Cisco Firepower compute:PsuControl:clusterState
        managed object property"
    ::= { cfprApComputePsuControlEntry 4 }

cfprApComputePsuControlDescr OBJECT-TYPE
    SYNTAX       SnmpAdminString
    MAX-ACCESS   read-only
    STATUS       current
    DESCRIPTION
        "Cisco Firepower compute:PsuControl:descr managed object property"
    ::= { cfprApComputePsuControlEntry 5 }

cfprApComputePsuControlInputPowerState OBJECT-TYPE
    SYNTAX       CfprApEquipmentSensorThresholdStatus
    MAX-ACCESS   read-only
    STATUS       current
    DESCRIPTION
        "Cisco Firepower compute:PsuControl:inputPowerState
        managed object property"
    ::= { cfprApComputePsuControlEntry 6 }

cfprApComputePsuControlIntId OBJECT-TYPE
    SYNTAX       SnmpAdminString
    MAX-ACCESS   read-only
    STATUS       current
    DESCRIPTION
        "Cisco Firepower compute:PsuControl:intId managed object property"
    ::= { cfprApComputePsuControlEntry 7 }

cfprApComputePsuControlName OBJECT-TYPE
    SYNTAX       SnmpAdminString
    MAX-ACCESS   read-only
    STATUS       current
    DESCRIPTION
        "Cisco Firepower compute:PsuControl:name managed object property"
    ::= { cfprApComputePsuControlEntry 8 }

cfprApComputePsuControlOperQualifier OBJECT-TYPE
    SYNTAX       CfprApComputePsuRedundancyOperQualifier
    MAX-ACCESS   read-only
    STATUS       current
    DESCRIPTION
        "Cisco Firepower compute:PsuControl:operQualifier
        managed object property"
    ::= { cfprApComputePsuControlEntry 9 }

cfprApComputePsuControlOperState OBJECT-TYPE
    SYNTAX       CfprApComputePsuRedundancyOperState
    MAX-ACCESS   read-only
    STATUS       current
    DESCRIPTION
        "Cisco Firepower compute:PsuControl:operState managed
        object property"
    ::= { cfprApComputePsuControlEntry 10 }

cfprApComputePsuControlOutputPowerState OBJECT-TYPE
    SYNTAX       CfprApEquipmentSensorThresholdStatus
    MAX-ACCESS   read-only
    STATUS       current
    DESCRIPTION
        "Cisco Firepower compute:PsuControl:outputPowerState
        managed object property"
    ::= { cfprApComputePsuControlEntry 11 }

cfprApComputePsuControlPolicyLevel OBJECT-TYPE
    SYNTAX       Gauge32
    MAX-ACCESS   read-only
    STATUS       current
    DESCRIPTION
        "Cisco Firepower compute:PsuControl:policyLevel
        managed object property"
    ::= { cfprApComputePsuControlEntry 12 }

cfprApComputePsuControlPolicyOwner OBJECT-TYPE
    SYNTAX       CfprApPolicyPolicyOwner
    MAX-ACCESS   read-only
    STATUS       current
    DESCRIPTION
        "Cisco Firepower compute:PsuControl:policyOwner
        managed object property"
    ::= { cfprApComputePsuControlEntry 13 }

cfprApComputePsuControlRedundancy OBJECT-TYPE
    SYNTAX       CfprApComputePsuControlRedundancy
    MAX-ACCESS   read-only
    STATUS       current
    DESCRIPTION
        "Cisco Firepower compute:PsuControl:redundancy
        managed object property"
    ::= { cfprApComputePsuControlEntry 14 }

cfprApComputePsuPolicyTable OBJECT-TYPE
    SYNTAX           SEQUENCE OF CfprApComputePsuPolicyEntry
    MAX-ACCESS       not-accessible
    STATUS           current
    DESCRIPTION
        "Cisco Firepower compute:PsuPolicy managed object table"
    ::= { cfprApComputeObjects 50 }

cfprApComputePsuPolicyEntry OBJECT-TYPE
    SYNTAX           CfprApComputePsuPolicyEntry
    MAX-ACCESS       not-accessible
    STATUS           current
    DESCRIPTION
        "Entry for the cfprApComputePsuPolicyTable table."
    INDEX { cfprApComputePsuPolicyInstanceId }
    ::= { cfprApComputePsuPolicyTable 1 }

CfprApComputePsuPolicyEntry ::= SEQUENCE {
    cfprApComputePsuPolicyInstanceId                                 CfprApManagedObjectId,
    cfprApComputePsuPolicyDn                                         CfprApManagedObjectDn,
    cfprApComputePsuPolicyRn                                         SnmpAdminString,
    cfprApComputePsuPolicyDescr                                      SnmpAdminString,
    cfprApComputePsuPolicyIntId                                      SnmpAdminString,
    cfprApComputePsuPolicyName                                       SnmpAdminString,
    cfprApComputePsuPolicyPolicyLevel                                Gauge32,
    cfprApComputePsuPolicyPolicyOwner                                CfprApPolicyPolicyOwner,
    cfprApComputePsuPolicyRedundancy                                 CfprApComputePsuRedundancy
}

cfprApComputePsuPolicyInstanceId OBJECT-TYPE
    SYNTAX       CfprApManagedObjectId
    MAX-ACCESS   not-accessible
    STATUS       current
    DESCRIPTION
        "Instance identifier of the managed object."
    ::= { cfprApComputePsuPolicyEntry 1 }

cfprApComputePsuPolicyDn OBJECT-TYPE
    SYNTAX       CfprApManagedObjectDn
    MAX-ACCESS   read-only
    STATUS       current
    DESCRIPTION
        "Cisco Firepower compute:PsuPolicy:dn managed object property"
    ::= { cfprApComputePsuPolicyEntry 2 }

cfprApComputePsuPolicyRn OBJECT-TYPE
    SYNTAX       SnmpAdminString
    MAX-ACCESS   read-only
    STATUS       current
    DESCRIPTION
        "Cisco Firepower compute:PsuPolicy:rn managed object property"
    ::= { cfprApComputePsuPolicyEntry 3 }

cfprApComputePsuPolicyDescr OBJECT-TYPE
    SYNTAX       SnmpAdminString
    MAX-ACCESS   read-only
    STATUS       current
    DESCRIPTION
        "Cisco Firepower compute:PsuPolicy:descr managed object property"
    ::= { cfprApComputePsuPolicyEntry 4 }

cfprApComputePsuPolicyIntId OBJECT-TYPE
    SYNTAX       SnmpAdminString
    MAX-ACCESS   read-only
    STATUS       current
    DESCRIPTION
        "Cisco Firepower compute:PsuPolicy:intId managed object property"
    ::= { cfprApComputePsuPolicyEntry 5 }

cfprApComputePsuPolicyName OBJECT-TYPE
    SYNTAX       SnmpAdminString
    MAX-ACCESS   read-only
    STATUS       current
    DESCRIPTION
        "Cisco Firepower compute:PsuPolicy:name managed object property"
    ::= { cfprApComputePsuPolicyEntry 6 }

cfprApComputePsuPolicyPolicyLevel OBJECT-TYPE
    SYNTAX       Gauge32
    MAX-ACCESS   read-only
    STATUS       current
    DESCRIPTION
        "Cisco Firepower compute:PsuPolicy:policyLevel
        managed object property"
    ::= { cfprApComputePsuPolicyEntry 7 }

cfprApComputePsuPolicyPolicyOwner OBJECT-TYPE
    SYNTAX       CfprApPolicyPolicyOwner
    MAX-ACCESS   read-only
    STATUS       current
    DESCRIPTION
        "Cisco Firepower compute:PsuPolicy:policyOwner
        managed object property"
    ::= { cfprApComputePsuPolicyEntry 8 }

cfprApComputePsuPolicyRedundancy OBJECT-TYPE
    SYNTAX       CfprApComputePsuRedundancy
    MAX-ACCESS   read-only
    STATUS       current
    DESCRIPTION
        "Cisco Firepower compute:PsuPolicy:redundancy managed
        object property"
    ::= { cfprApComputePsuPolicyEntry 9 }

cfprApComputeQualTable OBJECT-TYPE
    SYNTAX           SEQUENCE OF CfprApComputeQualEntry
    MAX-ACCESS       not-accessible
    STATUS           current
    DESCRIPTION
        "Cisco Firepower compute:Qual managed object table"
    ::= { cfprApComputeObjects 51 }

cfprApComputeQualEntry OBJECT-TYPE
    SYNTAX           CfprApComputeQualEntry
    MAX-ACCESS       not-accessible
    STATUS           current
    DESCRIPTION
        "Entry for the cfprApComputeQualTable table."
    INDEX { cfprApComputeQualInstanceId }
    ::= { cfprApComputeQualTable 1 }

CfprApComputeQualEntry ::= SEQUENCE {
    cfprApComputeQualInstanceId                                      CfprApManagedObjectId,
    cfprApComputeQualDn                                              CfprApManagedObjectDn,
    cfprApComputeQualRn                                              SnmpAdminString,
    cfprApComputeQualDescr                                           SnmpAdminString,
    cfprApComputeQualIntId                                           SnmpAdminString,
    cfprApComputeQualName                                            SnmpAdminString,
    cfprApComputeQualPolicyLevel                                     Gauge32,
    cfprApComputeQualPolicyOwner                                     CfprApPolicyPolicyOwner
}

cfprApComputeQualInstanceId OBJECT-TYPE
    SYNTAX       CfprApManagedObjectId
    MAX-ACCESS   not-accessible
    STATUS       current
    DESCRIPTION
        "Instance identifier of the managed object."
    ::= { cfprApComputeQualEntry 1 }

cfprApComputeQualDn OBJECT-TYPE
    SYNTAX       CfprApManagedObjectDn
    MAX-ACCESS   read-only
    STATUS       current
    DESCRIPTION
        "Cisco Firepower compute:Qual:dn managed object property"
    ::= { cfprApComputeQualEntry 2 }

cfprApComputeQualRn OBJECT-TYPE
    SYNTAX       SnmpAdminString
    MAX-ACCESS   read-only
    STATUS       current
    DESCRIPTION
        "Cisco Firepower compute:Qual:rn managed object property"
    ::= { cfprApComputeQualEntry 3 }

cfprApComputeQualDescr OBJECT-TYPE
    SYNTAX       SnmpAdminString
    MAX-ACCESS   read-only
    STATUS       current
    DESCRIPTION
        "Cisco Firepower compute:Qual:descr managed object property"
    ::= { cfprApComputeQualEntry 4 }

cfprApComputeQualIntId OBJECT-TYPE
    SYNTAX       SnmpAdminString
    MAX-ACCESS   read-only
    STATUS       current
    DESCRIPTION
        "Cisco Firepower compute:Qual:intId managed object property"
    ::= { cfprApComputeQualEntry 5 }

cfprApComputeQualName OBJECT-TYPE
    SYNTAX       SnmpAdminString
    MAX-ACCESS   read-only
    STATUS       current
    DESCRIPTION
        "Cisco Firepower compute:Qual:name managed object property"
    ::= { cfprApComputeQualEntry 6 }

cfprApComputeQualPolicyLevel OBJECT-TYPE
    SYNTAX       Gauge32
    MAX-ACCESS   read-only
    STATUS       current
    DESCRIPTION
        "Cisco Firepower compute:Qual:policyLevel managed object property"
    ::= { cfprApComputeQualEntry 7 }

cfprApComputeQualPolicyOwner OBJECT-TYPE
    SYNTAX       CfprApPolicyPolicyOwner
    MAX-ACCESS   read-only
    STATUS       current
    DESCRIPTION
        "Cisco Firepower compute:Qual:policyOwner managed object property"
    ::= { cfprApComputeQualEntry 8 }

cfprApComputeRackQualTable OBJECT-TYPE
    SYNTAX           SEQUENCE OF CfprApComputeRackQualEntry
    MAX-ACCESS       not-accessible
    STATUS           current
    DESCRIPTION
        "Cisco Firepower compute:RackQual managed object table"
    ::= { cfprApComputeObjects 52 }

cfprApComputeRackQualEntry OBJECT-TYPE
    SYNTAX           CfprApComputeRackQualEntry
    MAX-ACCESS       not-accessible
    STATUS           current
    DESCRIPTION
        "Entry for the cfprApComputeRackQualTable table."
    INDEX { cfprApComputeRackQualInstanceId }
    ::= { cfprApComputeRackQualTable 1 }

CfprApComputeRackQualEntry ::= SEQUENCE {
    cfprApComputeRackQualInstanceId                                  CfprApManagedObjectId,
    cfprApComputeRackQualDn                                          CfprApManagedObjectDn,
    cfprApComputeRackQualRn                                          SnmpAdminString,
    cfprApComputeRackQualMaxId                                       CfprApComputeRackQualMaxId,
    cfprApComputeRackQualMinId                                       CfprApComputeRackQualMinId
}

cfprApComputeRackQualInstanceId OBJECT-TYPE
    SYNTAX       CfprApManagedObjectId
    MAX-ACCESS   not-accessible
    STATUS       current
    DESCRIPTION
        "Instance identifier of the managed object."
    ::= { cfprApComputeRackQualEntry 1 }

cfprApComputeRackQualDn OBJECT-TYPE
    SYNTAX       CfprApManagedObjectDn
    MAX-ACCESS   read-only
    STATUS       current
    DESCRIPTION
        "Cisco Firepower compute:RackQual:dn managed object property"
    ::= { cfprApComputeRackQualEntry 2 }

cfprApComputeRackQualRn OBJECT-TYPE
    SYNTAX       SnmpAdminString
    MAX-ACCESS   read-only
    STATUS       current
    DESCRIPTION
        "Cisco Firepower compute:RackQual:rn managed object property"
    ::= { cfprApComputeRackQualEntry 3 }

cfprApComputeRackQualMaxId OBJECT-TYPE
    SYNTAX       CfprApComputeRackQualMaxId
    MAX-ACCESS   read-only
    STATUS       current
    DESCRIPTION
        "Cisco Firepower compute:RackQual:maxId managed object property"
    ::= { cfprApComputeRackQualEntry 4 }

cfprApComputeRackQualMinId OBJECT-TYPE
    SYNTAX       CfprApComputeRackQualMinId
    MAX-ACCESS   read-only
    STATUS       current
    DESCRIPTION
        "Cisco Firepower compute:RackQual:minId managed object property"
    ::= { cfprApComputeRackQualEntry 5 }

cfprApComputeRackUnitTable OBJECT-TYPE
    SYNTAX           SEQUENCE OF CfprApComputeRackUnitEntry
    MAX-ACCESS       not-accessible
    STATUS           current
    DESCRIPTION
        "Cisco Firepower compute:RackUnit managed object table"
    ::= { cfprApComputeObjects 53 }

cfprApComputeRackUnitEntry OBJECT-TYPE
    SYNTAX           CfprApComputeRackUnitEntry
    MAX-ACCESS       not-accessible
    STATUS           current
    DESCRIPTION
        "Entry for the cfprApComputeRackUnitTable table."
    INDEX { cfprApComputeRackUnitInstanceId }
    ::= { cfprApComputeRackUnitTable 1 }

CfprApComputeRackUnitEntry ::= SEQUENCE {
    cfprApComputeRackUnitInstanceId                                  CfprApManagedObjectId,
    cfprApComputeRackUnitDn                                          CfprApManagedObjectDn,
    cfprApComputeRackUnitRn                                          SnmpAdminString,
    cfprApComputeRackUnitAdminPower                                  CfprApComputeAdminPowerState,
    cfprApComputeRackUnitAdminState                                  CfprApComputeAdminState,
    cfprApComputeRackUnitAssignedToDn                                SnmpAdminString,
    cfprApComputeRackUnitAssociation                                 CfprApComputeAssociation,
    cfprApComputeRackUnitAvailability                                CfprApComputeAvailability,
    cfprApComputeRackUnitAvailableMemory                             Gauge32,
    cfprApComputeRackUnitCheckPoint                                  CfprApComputeCheckPoint,
    cfprApComputeRackUnitConnPath                                    CfprApEquipmentConnectionStatus,
    cfprApComputeRackUnitConnStatus                                  CfprApEquipmentConnectionStatus,
    cfprApComputeRackUnitDescr                                       SnmpAdminString,
    cfprApComputeRackUnitDiscovery                                   CfprApComputeDiscovery,
    cfprApComputeRackUnitFltAggr                                     Unsigned64,
    cfprApComputeRackUnitFsmDescr                                    SnmpAdminString,
    cfprApComputeRackUnitFsmPrev                                     SnmpAdminString,
    cfprApComputeRackUnitFsmProgr                                    Gauge32,
    cfprApComputeRackUnitFsmRmtInvErrCode                            Gauge32,
    cfprApComputeRackUnitFsmRmtInvErrDescr                           SnmpAdminString,
    cfprApComputeRackUnitFsmRmtInvRslt                               CfprApConditionRemoteInvRslt,
    cfprApComputeRackUnitFsmStageDescr                               SnmpAdminString,
    cfprApComputeRackUnitFsmStamp                                    DateAndTime,
    cfprApComputeRackUnitFsmStatus                                   SnmpAdminString,
    cfprApComputeRackUnitFsmTry                                      Gauge32,
    cfprApComputeRackUnitId                                          CfprApComputeRackUnitId,
    cfprApComputeRackUnitIntId                                       SnmpAdminString,
    cfprApComputeRackUnitLc                                          CfprApComputeAdminTrigger,
    cfprApComputeRackUnitLcTs                                        DateAndTime,
    cfprApComputeRackUnitLocalId                                     SnmpAdminString,
    cfprApComputeRackUnitLowVoltageMemory                            CfprApComputePhysicalLowVoltageMemory,
    cfprApComputeRackUnitManagingInst                                CfprApNetworkSwitchId,
    cfprApComputeRackUnitMemorySpeed                                 Gauge32,
    cfprApComputeRackUnitMfgTime                                     DateAndTime,
    cfprApComputeRackUnitModel                                       SnmpAdminString,
    cfprApComputeRackUnitName                                        SnmpAdminString,
    cfprApComputeRackUnitNumOfAdaptors                               Gauge32,
    cfprApComputeRackUnitNumOfCores                                  Gauge32,
    cfprApComputeRackUnitNumOfCoresEnabled                           Gauge32,
    cfprApComputeRackUnitNumOfCpus                                   Gauge32,
    cfprApComputeRackUnitNumOfEthHostIfs                             Gauge32,
    cfprApComputeRackUnitNumOfFcHostIfs                              Gauge32,
    cfprApComputeRackUnitNumOfThreads                                Gauge32,
    cfprApComputeRackUnitOperPower                                   CfprApEquipmentPowerState,
    cfprApComputeRackUnitOperQualifier                               CfprApComputeIssues,
    cfprApComputeRackUnitOperState                                   CfprApLsOperState,
    cfprApComputeRackUnitOperability                                 CfprApEquipmentOperability,
    cfprApComputeRackUnitOriginalUuid                                SnmpAdminString,
    cfprApComputeRackUnitPartNumber                                  SnmpAdminString,
    cfprApComputeRackUnitPolicyLevel                                 Gauge32,
    cfprApComputeRackUnitPolicyOwner                                 CfprApPolicyPolicyOwner,
    cfprApComputeRackUnitPresence                                    CfprApEquipmentSlotStatus,
    cfprApComputeRackUnitRevision                                    SnmpAdminString,
    cfprApComputeRackUnitSerial                                      SnmpAdminString,
    cfprApComputeRackUnitServerId                                    SnmpAdminString,
    cfprApComputeRackUnitTotalMemory                                 Gauge32,
    cfprApComputeRackUnitUsrLbl                                      SnmpAdminString,
    cfprApComputeRackUnitUuid                                        SnmpAdminString,
    cfprApComputeRackUnitVendor                                      SnmpAdminString,
    cfprApComputeRackUnitVersionHolder                               TruthValue,
    cfprApComputeRackUnitVid                                         SnmpAdminString
}

cfprApComputeRackUnitInstanceId OBJECT-TYPE
    SYNTAX       CfprApManagedObjectId
    MAX-ACCESS   not-accessible
    STATUS       current
    DESCRIPTION
        "Instance identifier of the managed object."
    ::= { cfprApComputeRackUnitEntry 1 }

cfprApComputeRackUnitDn OBJECT-TYPE
    SYNTAX       CfprApManagedObjectDn
    MAX-ACCESS   read-only
    STATUS       current
    DESCRIPTION
        "Cisco Firepower compute:RackUnit:dn managed object property"
    ::= { cfprApComputeRackUnitEntry 2 }

cfprApComputeRackUnitRn OBJECT-TYPE
    SYNTAX       SnmpAdminString
    MAX-ACCESS   read-only
    STATUS       current
    DESCRIPTION
        "Cisco Firepower compute:RackUnit:rn managed object property"
    ::= { cfprApComputeRackUnitEntry 3 }

cfprApComputeRackUnitAdminPower OBJECT-TYPE
    SYNTAX       CfprApComputeAdminPowerState
    MAX-ACCESS   read-only
    STATUS       current
    DESCRIPTION
        "Cisco Firepower compute:RackUnit:adminPower managed
        object property"
    ::= { cfprApComputeRackUnitEntry 4 }

cfprApComputeRackUnitAdminState OBJECT-TYPE
    SYNTAX       CfprApComputeAdminState
    MAX-ACCESS   read-only
    STATUS       current
    DESCRIPTION
        "Cisco Firepower compute:RackUnit:adminState managed
        object property"
    ::= { cfprApComputeRackUnitEntry 5 }

cfprApComputeRackUnitAssignedToDn OBJECT-TYPE
    SYNTAX       SnmpAdminString
    MAX-ACCESS   read-only
    STATUS       current
    DESCRIPTION
        "Cisco Firepower compute:RackUnit:assignedToDn
        managed object property"
    ::= { cfprApComputeRackUnitEntry 6 }

cfprApComputeRackUnitAssociation OBJECT-TYPE
    SYNTAX       CfprApComputeAssociation
    MAX-ACCESS   read-only
    STATUS       current
    DESCRIPTION
        "Cisco Firepower compute:RackUnit:association managed
        object property"
    ::= { cfprApComputeRackUnitEntry 7 }

cfprApComputeRackUnitAvailability OBJECT-TYPE
    SYNTAX       CfprApComputeAvailability
    MAX-ACCESS   read-only
    STATUS       current
    DESCRIPTION
        "Cisco Firepower compute:RackUnit:availability
        managed object property"
    ::= { cfprApComputeRackUnitEntry 8 }

cfprApComputeRackUnitAvailableMemory OBJECT-TYPE
    SYNTAX       Gauge32
    MAX-ACCESS   read-only
    STATUS       current
    DESCRIPTION
        "Cisco Firepower compute:RackUnit:availableMemory
        managed object property"
    ::= { cfprApComputeRackUnitEntry 9 }

cfprApComputeRackUnitCheckPoint OBJECT-TYPE
    SYNTAX       CfprApComputeCheckPoint
    MAX-ACCESS   read-only
    STATUS       current
    DESCRIPTION
        "Cisco Firepower compute:RackUnit:checkPoint managed
        object property"
    ::= { cfprApComputeRackUnitEntry 10 }

cfprApComputeRackUnitConnPath OBJECT-TYPE
    SYNTAX       CfprApEquipmentConnectionStatus
    MAX-ACCESS   read-only
    STATUS       current
    DESCRIPTION
        "Cisco Firepower compute:RackUnit:connPath managed
        object property"
    ::= { cfprApComputeRackUnitEntry 11 }

cfprApComputeRackUnitConnStatus OBJECT-TYPE
    SYNTAX       CfprApEquipmentConnectionStatus
    MAX-ACCESS   read-only
    STATUS       current
    DESCRIPTION
        "Cisco Firepower compute:RackUnit:connStatus managed
        object property"
    ::= { cfprApComputeRackUnitEntry 12 }

cfprApComputeRackUnitDescr OBJECT-TYPE
    SYNTAX       SnmpAdminString
    MAX-ACCESS   read-only
    STATUS       current
    DESCRIPTION
        "Cisco Firepower compute:RackUnit:descr managed object property"
    ::= { cfprApComputeRackUnitEntry 13 }

cfprApComputeRackUnitDiscovery OBJECT-TYPE
    SYNTAX       CfprApComputeDiscovery
    MAX-ACCESS   read-only
    STATUS       current
    DESCRIPTION
        "Cisco Firepower compute:RackUnit:discovery managed
        object property"
    ::= { cfprApComputeRackUnitEntry 14 }

cfprApComputeRackUnitFltAggr OBJECT-TYPE
    SYNTAX       Unsigned64
    MAX-ACCESS   read-only
    STATUS       current
    DESCRIPTION
        "Cisco Firepower compute:RackUnit:fltAggr managed object property"
    ::= { cfprApComputeRackUnitEntry 15 }

cfprApComputeRackUnitFsmDescr OBJECT-TYPE
    SYNTAX       SnmpAdminString
    MAX-ACCESS   read-only
    STATUS       current
    DESCRIPTION
        "Cisco Firepower compute:RackUnit:fsmDescr managed
        object property"
    ::= { cfprApComputeRackUnitEntry 16 }

cfprApComputeRackUnitFsmPrev OBJECT-TYPE
    SYNTAX       SnmpAdminString
    MAX-ACCESS   read-only
    STATUS       current
    DESCRIPTION
        "Cisco Firepower compute:RackUnit:fsmPrev managed object property"
    ::= { cfprApComputeRackUnitEntry 17 }

cfprApComputeRackUnitFsmProgr OBJECT-TYPE
    SYNTAX       Gauge32
    MAX-ACCESS   read-only
    STATUS       current
    DESCRIPTION
        "Cisco Firepower compute:RackUnit:fsmProgr managed
        object property"
    ::= { cfprApComputeRackUnitEntry 18 }

cfprApComputeRackUnitFsmRmtInvErrCode OBJECT-TYPE
    SYNTAX       Gauge32
    MAX-ACCESS   read-only
    STATUS       current
    DESCRIPTION
        "Cisco Firepower compute:RackUnit:fsmRmtInvErrCode
        managed object property"
    ::= { cfprApComputeRackUnitEntry 19 }

cfprApComputeRackUnitFsmRmtInvErrDescr OBJECT-TYPE
    SYNTAX       SnmpAdminString
    MAX-ACCESS   read-only
    STATUS       current
    DESCRIPTION
        "Cisco Firepower compute:RackUnit:fsmRmtInvErrDescr
        managed object property"
    ::= { cfprApComputeRackUnitEntry 20 }

cfprApComputeRackUnitFsmRmtInvRslt OBJECT-TYPE
    SYNTAX       CfprApConditionRemoteInvRslt
    MAX-ACCESS   read-only
    STATUS       current
    DESCRIPTION
        "Cisco Firepower compute:RackUnit:fsmRmtInvRslt
        managed object property"
    ::= { cfprApComputeRackUnitEntry 21 }

cfprApComputeRackUnitFsmStageDescr OBJECT-TYPE
    SYNTAX       SnmpAdminString
    MAX-ACCESS   read-only
    STATUS       current
    DESCRIPTION
        "Cisco Firepower compute:RackUnit:fsmStageDescr
        managed object property"
    ::= { cfprApComputeRackUnitEntry 22 }

cfprApComputeRackUnitFsmStamp OBJECT-TYPE
    SYNTAX       DateAndTime
    MAX-ACCESS   read-only
    STATUS       current
    DESCRIPTION
        "Cisco Firepower compute:RackUnit:fsmStamp managed
        object property"
    ::= { cfprApComputeRackUnitEntry 23 }

cfprApComputeRackUnitFsmStatus OBJECT-TYPE
    SYNTAX       SnmpAdminString
    MAX-ACCESS   read-only
    STATUS       current
    DESCRIPTION
        "Cisco Firepower compute:RackUnit:fsmStatus managed
        object property"
    ::= { cfprApComputeRackUnitEntry 24 }

cfprApComputeRackUnitFsmTry OBJECT-TYPE
    SYNTAX       Gauge32
    MAX-ACCESS   read-only
    STATUS       current
    DESCRIPTION
        "Cisco Firepower compute:RackUnit:fsmTry managed object property"
    ::= { cfprApComputeRackUnitEntry 25 }

cfprApComputeRackUnitId OBJECT-TYPE
    SYNTAX       CfprApComputeRackUnitId
    MAX-ACCESS   read-only
    STATUS       current
    DESCRIPTION
        "Cisco Firepower compute:RackUnit:id managed object property"
    ::= { cfprApComputeRackUnitEntry 26 }

cfprApComputeRackUnitIntId OBJECT-TYPE
    SYNTAX       SnmpAdminString
    MAX-ACCESS   read-only
    STATUS       current
    DESCRIPTION
        "Cisco Firepower compute:RackUnit:intId managed object property"
    ::= { cfprApComputeRackUnitEntry 27 }

cfprApComputeRackUnitLc OBJECT-TYPE
    SYNTAX       CfprApComputeAdminTrigger
    MAX-ACCESS   read-only
    STATUS       current
    DESCRIPTION
        "Cisco Firepower compute:RackUnit:lc managed object property"
    ::= { cfprApComputeRackUnitEntry 28 }

cfprApComputeRackUnitLcTs OBJECT-TYPE
    SYNTAX       DateAndTime
    MAX-ACCESS   read-only
    STATUS       current
    DESCRIPTION
        "Cisco Firepower compute:RackUnit:lcTs managed object property"
    ::= { cfprApComputeRackUnitEntry 29 }

cfprApComputeRackUnitLocalId OBJECT-TYPE
    SYNTAX       SnmpAdminString
    MAX-ACCESS   read-only
    STATUS       current
    DESCRIPTION
        "Cisco Firepower compute:RackUnit:localId managed object property"
    ::= { cfprApComputeRackUnitEntry 30 }

cfprApComputeRackUnitLowVoltageMemory OBJECT-TYPE
    SYNTAX       CfprApComputePhysicalLowVoltageMemory
    MAX-ACCESS   read-only
    STATUS       current
    DESCRIPTION
        "Cisco Firepower compute:RackUnit:lowVoltageMemory
        managed object property"
    ::= { cfprApComputeRackUnitEntry 31 }

cfprApComputeRackUnitManagingInst OBJECT-TYPE
    SYNTAX       CfprApNetworkSwitchId
    MAX-ACCESS   read-only
    STATUS       current
    DESCRIPTION
        "Cisco Firepower compute:RackUnit:managingInst
        managed object property"
    ::= { cfprApComputeRackUnitEntry 32 }

cfprApComputeRackUnitMemorySpeed OBJECT-TYPE
    SYNTAX       Gauge32
    MAX-ACCESS   read-only
    STATUS       current
    DESCRIPTION
        "Cisco Firepower compute:RackUnit:memorySpeed managed
        object property"
    ::= { cfprApComputeRackUnitEntry 33 }

cfprApComputeRackUnitMfgTime OBJECT-TYPE
    SYNTAX       DateAndTime
    MAX-ACCESS   read-only
    STATUS       current
    DESCRIPTION
        "Cisco Firepower compute:RackUnit:mfgTime managed object property"
    ::= { cfprApComputeRackUnitEntry 34 }

cfprApComputeRackUnitModel OBJECT-TYPE
    SYNTAX       SnmpAdminString
    MAX-ACCESS   read-only
    STATUS       current
    DESCRIPTION
        "Cisco Firepower compute:RackUnit:model managed object property"
    ::= { cfprApComputeRackUnitEntry 35 }

cfprApComputeRackUnitName OBJECT-TYPE
    SYNTAX       SnmpAdminString
    MAX-ACCESS   read-only
    STATUS       current
    DESCRIPTION
        "Cisco Firepower compute:RackUnit:name managed object property"
    ::= { cfprApComputeRackUnitEntry 36 }

cfprApComputeRackUnitNumOfAdaptors OBJECT-TYPE
    SYNTAX       Gauge32
    MAX-ACCESS   read-only
    STATUS       current
    DESCRIPTION
        "Cisco Firepower compute:RackUnit:numOfAdaptors
        managed object property"
    ::= { cfprApComputeRackUnitEntry 37 }

cfprApComputeRackUnitNumOfCores OBJECT-TYPE
    SYNTAX       Gauge32
    MAX-ACCESS   read-only
    STATUS       current
    DESCRIPTION
        "Cisco Firepower compute:RackUnit:numOfCores managed
        object property"
    ::= { cfprApComputeRackUnitEntry 38 }

cfprApComputeRackUnitNumOfCoresEnabled OBJECT-TYPE
    SYNTAX       Gauge32
    MAX-ACCESS   read-only
    STATUS       current
    DESCRIPTION
        "Cisco Firepower compute:RackUnit:numOfCoresEnabled
        managed object property"
    ::= { cfprApComputeRackUnitEntry 39 }

cfprApComputeRackUnitNumOfCpus OBJECT-TYPE
    SYNTAX       Gauge32
    MAX-ACCESS   read-only
    STATUS       current
    DESCRIPTION
        "Cisco Firepower compute:RackUnit:numOfCpus managed
        object property"
    ::= { cfprApComputeRackUnitEntry 40 }

cfprApComputeRackUnitNumOfEthHostIfs OBJECT-TYPE
    SYNTAX       Gauge32
    MAX-ACCESS   read-only
    STATUS       current
    DESCRIPTION
        "Cisco Firepower compute:RackUnit:numOfEthHostIfs
        managed object property"
    ::= { cfprApComputeRackUnitEntry 41 }

cfprApComputeRackUnitNumOfFcHostIfs OBJECT-TYPE
    SYNTAX       Gauge32
    MAX-ACCESS   read-only
    STATUS       current
    DESCRIPTION
        "Cisco Firepower compute:RackUnit:numOfFcHostIfs
        managed object property"
    ::= { cfprApComputeRackUnitEntry 42 }

cfprApComputeRackUnitNumOfThreads OBJECT-TYPE
    SYNTAX       Gauge32
    MAX-ACCESS   read-only
    STATUS       current
    DESCRIPTION
        "Cisco Firepower compute:RackUnit:numOfThreads
        managed object property"
    ::= { cfprApComputeRackUnitEntry 43 }

cfprApComputeRackUnitOperPower OBJECT-TYPE
    SYNTAX       CfprApEquipmentPowerState
    MAX-ACCESS   read-only
    STATUS       current
    DESCRIPTION
        "Cisco Firepower compute:RackUnit:operPower managed
        object property"
    ::= { cfprApComputeRackUnitEntry 44 }

cfprApComputeRackUnitOperQualifier OBJECT-TYPE
    SYNTAX       CfprApComputeIssues
    MAX-ACCESS   read-only
    STATUS       current
    DESCRIPTION
        "Cisco Firepower compute:RackUnit:operQualifier
        managed object property"
    ::= { cfprApComputeRackUnitEntry 45 }

cfprApComputeRackUnitOperState OBJECT-TYPE
    SYNTAX       CfprApLsOperState
    MAX-ACCESS   read-only
    STATUS       current
    DESCRIPTION
        "Cisco Firepower compute:RackUnit:operState managed
        object property"
    ::= { cfprApComputeRackUnitEntry 46 }

cfprApComputeRackUnitOperability OBJECT-TYPE
    SYNTAX       CfprApEquipmentOperability
    MAX-ACCESS   read-only
    STATUS       current
    DESCRIPTION
        "Cisco Firepower compute:RackUnit:operability managed
        object property"
    ::= { cfprApComputeRackUnitEntry 47 }

cfprApComputeRackUnitOriginalUuid OBJECT-TYPE
    SYNTAX       SnmpAdminString
    MAX-ACCESS   read-only
    STATUS       current
    DESCRIPTION
        "Cisco Firepower compute:RackUnit:originalUuid
        managed object property"
    ::= { cfprApComputeRackUnitEntry 48 }

cfprApComputeRackUnitPartNumber OBJECT-TYPE
    SYNTAX       SnmpAdminString
    MAX-ACCESS   read-only
    STATUS       current
    DESCRIPTION
        "Cisco Firepower compute:RackUnit:partNumber managed
        object property"
    ::= { cfprApComputeRackUnitEntry 49 }

cfprApComputeRackUnitPolicyLevel OBJECT-TYPE
    SYNTAX       Gauge32
    MAX-ACCESS   read-only
    STATUS       current
    DESCRIPTION
        "Cisco Firepower compute:RackUnit:policyLevel managed
        object property"
    ::= { cfprApComputeRackUnitEntry 50 }

cfprApComputeRackUnitPolicyOwner OBJECT-TYPE
    SYNTAX       CfprApPolicyPolicyOwner
    MAX-ACCESS   read-only
    STATUS       current
    DESCRIPTION
        "Cisco Firepower compute:RackUnit:policyOwner managed
        object property"
    ::= { cfprApComputeRackUnitEntry 51 }

cfprApComputeRackUnitPresence OBJECT-TYPE
    SYNTAX       CfprApEquipmentSlotStatus
    MAX-ACCESS   read-only
    STATUS       current
    DESCRIPTION
        "Cisco Firepower compute:RackUnit:presence managed
        object property"
    ::= { cfprApComputeRackUnitEntry 52 }

cfprApComputeRackUnitRevision OBJECT-TYPE
    SYNTAX       SnmpAdminString
    MAX-ACCESS   read-only
    STATUS       current
    DESCRIPTION
        "Cisco Firepower compute:RackUnit:revision managed
        object property"
    ::= { cfprApComputeRackUnitEntry 53 }

cfprApComputeRackUnitSerial OBJECT-TYPE
    SYNTAX       SnmpAdminString
    MAX-ACCESS   read-only
    STATUS       current
    DESCRIPTION
        "Cisco Firepower compute:RackUnit:serial managed object property"
    ::= { cfprApComputeRackUnitEntry 54 }

cfprApComputeRackUnitServerId OBJECT-TYPE
    SYNTAX       SnmpAdminString
    MAX-ACCESS   read-only
    STATUS       current
    DESCRIPTION
        "Cisco Firepower compute:RackUnit:serverId managed
        object property"
    ::= { cfprApComputeRackUnitEntry 55 }

cfprApComputeRackUnitTotalMemory OBJECT-TYPE
    SYNTAX       Gauge32
    MAX-ACCESS   read-only
    STATUS       current
    DESCRIPTION
        "Cisco Firepower compute:RackUnit:totalMemory managed
        object property"
    ::= { cfprApComputeRackUnitEntry 56 }

cfprApComputeRackUnitUsrLbl OBJECT-TYPE
    SYNTAX       SnmpAdminString
    MAX-ACCESS   read-only
    STATUS       current
    DESCRIPTION
        "Cisco Firepower compute:RackUnit:usrLbl managed object property"
    ::= { cfprApComputeRackUnitEntry 57 }

cfprApComputeRackUnitUuid OBJECT-TYPE
    SYNTAX       SnmpAdminString
    MAX-ACCESS   read-only
    STATUS       current
    DESCRIPTION
        "Cisco Firepower compute:RackUnit:uuid managed object property"
    ::= { cfprApComputeRackUnitEntry 58 }

cfprApComputeRackUnitVendor OBJECT-TYPE
    SYNTAX       SnmpAdminString
    MAX-ACCESS   read-only
    STATUS       current
    DESCRIPTION
        "Cisco Firepower compute:RackUnit:vendor managed object property"
    ::= { cfprApComputeRackUnitEntry 59 }

cfprApComputeRackUnitVersionHolder OBJECT-TYPE
    SYNTAX       TruthValue
    MAX-ACCESS   read-only
    STATUS       current
    DESCRIPTION
        "Cisco Firepower compute:RackUnit:versionHolder
        managed object property"
    ::= { cfprApComputeRackUnitEntry 60 }

cfprApComputeRackUnitVid OBJECT-TYPE
    SYNTAX       SnmpAdminString
    MAX-ACCESS   read-only
    STATUS       current
    DESCRIPTION
        "Cisco Firepower compute:RackUnit:vid managed object property"
    ::= { cfprApComputeRackUnitEntry 61 }

cfprApComputeRackUnitFsmTable OBJECT-TYPE
    SYNTAX           SEQUENCE OF CfprApComputeRackUnitFsmEntry
    MAX-ACCESS       not-accessible
    STATUS           current
    DESCRIPTION
        "Cisco Firepower compute:RackUnitFsm managed object table"
    ::= { cfprApComputeObjects 54 }

cfprApComputeRackUnitFsmEntry OBJECT-TYPE
    SYNTAX           CfprApComputeRackUnitFsmEntry
    MAX-ACCESS       not-accessible
    STATUS           current
    DESCRIPTION
        "Entry for the cfprApComputeRackUnitFsmTable table."
    INDEX { cfprApComputeRackUnitFsmInstanceId }
    ::= { cfprApComputeRackUnitFsmTable 1 }

CfprApComputeRackUnitFsmEntry ::= SEQUENCE {
    cfprApComputeRackUnitFsmInstanceId                               CfprApManagedObjectId,
    cfprApComputeRackUnitFsmDn                                       CfprApManagedObjectDn,
    cfprApComputeRackUnitFsmRn                                       SnmpAdminString,
    cfprApComputeRackUnitFsmCompletionTime                           DateAndTime,
    cfprApComputeRackUnitFsmCurrentFsm                               CfprApComputeRackUnitFsmCurrentFsm,
    cfprApComputeRackUnitFsmDescrData                                SnmpAdminString,
    cfprApComputeRackUnitFsmFsmStatus                                CfprApFsmFsmStageStatus,
    cfprApComputeRackUnitFsmProgress                                 Gauge32,
    cfprApComputeRackUnitFsmRmtErrCode                               Gauge32,
    cfprApComputeRackUnitFsmRmtErrDescr                              SnmpAdminString,
    cfprApComputeRackUnitFsmRmtRslt                                  CfprApConditionRemoteInvRslt
}

cfprApComputeRackUnitFsmInstanceId OBJECT-TYPE
    SYNTAX       CfprApManagedObjectId
    MAX-ACCESS   not-accessible
    STATUS       current
    DESCRIPTION
        "Instance identifier of the managed object."
    ::= { cfprApComputeRackUnitFsmEntry 1 }

cfprApComputeRackUnitFsmDn OBJECT-TYPE
    SYNTAX       CfprApManagedObjectDn
    MAX-ACCESS   read-only
    STATUS       current
    DESCRIPTION
        "Cisco Firepower compute:RackUnitFsm:dn managed object property"
    ::= { cfprApComputeRackUnitFsmEntry 2 }

cfprApComputeRackUnitFsmRn OBJECT-TYPE
    SYNTAX       SnmpAdminString
    MAX-ACCESS   read-only
    STATUS       current
    DESCRIPTION
        "Cisco Firepower compute:RackUnitFsm:rn managed object property"
    ::= { cfprApComputeRackUnitFsmEntry 3 }

cfprApComputeRackUnitFsmCompletionTime OBJECT-TYPE
    SYNTAX       DateAndTime
    MAX-ACCESS   read-only
    STATUS       current
    DESCRIPTION
        "Cisco Firepower compute:RackUnitFsm:completionTime
        managed object property"
    ::= { cfprApComputeRackUnitFsmEntry 4 }

cfprApComputeRackUnitFsmCurrentFsm OBJECT-TYPE
    SYNTAX       CfprApComputeRackUnitFsmCurrentFsm
    MAX-ACCESS   read-only
    STATUS       current
    DESCRIPTION
        "Cisco Firepower compute:RackUnitFsm:currentFsm
        managed object property"
    ::= { cfprApComputeRackUnitFsmEntry 5 }

cfprApComputeRackUnitFsmDescrData OBJECT-TYPE
    SYNTAX       SnmpAdminString
    MAX-ACCESS   read-only
    STATUS       current
    DESCRIPTION
        "Cisco Firepower compute:RackUnitFsm:descr managed
        object property"
    ::= { cfprApComputeRackUnitFsmEntry 6 }

cfprApComputeRackUnitFsmFsmStatus OBJECT-TYPE
    SYNTAX       CfprApFsmFsmStageStatus
    MAX-ACCESS   read-only
    STATUS       current
    DESCRIPTION
        "Cisco Firepower compute:RackUnitFsm:fsmStatus
        managed object property"
    ::= { cfprApComputeRackUnitFsmEntry 7 }

cfprApComputeRackUnitFsmProgress OBJECT-TYPE
    SYNTAX       Gauge32
    MAX-ACCESS   read-only
    STATUS       current
    DESCRIPTION
        "Cisco Firepower compute:RackUnitFsm:progress managed
        object property"
    ::= { cfprApComputeRackUnitFsmEntry 8 }

cfprApComputeRackUnitFsmRmtErrCode OBJECT-TYPE
    SYNTAX       Gauge32
    MAX-ACCESS   read-only
    STATUS       current
    DESCRIPTION
        "Cisco Firepower compute:RackUnitFsm:rmtErrCode
        managed object property"
    ::= { cfprApComputeRackUnitFsmEntry 9 }

cfprApComputeRackUnitFsmRmtErrDescr OBJECT-TYPE
    SYNTAX       SnmpAdminString
    MAX-ACCESS   read-only
    STATUS       current
    DESCRIPTION
        "Cisco Firepower compute:RackUnitFsm:rmtErrDescr
        managed object property"
    ::= { cfprApComputeRackUnitFsmEntry 10 }

cfprApComputeRackUnitFsmRmtRslt OBJECT-TYPE
    SYNTAX       CfprApConditionRemoteInvRslt
    MAX-ACCESS   read-only
    STATUS       current
    DESCRIPTION
        "Cisco Firepower compute:RackUnitFsm:rmtRslt managed
        object property"
    ::= { cfprApComputeRackUnitFsmEntry 11 }

cfprApComputeRackUnitFsmStageTable OBJECT-TYPE
    SYNTAX           SEQUENCE OF CfprApComputeRackUnitFsmStageEntry
    MAX-ACCESS       not-accessible
    STATUS           current
    DESCRIPTION
        "Cisco Firepower compute:RackUnitFsmStage managed object table"
    ::= { cfprApComputeObjects 55 }

cfprApComputeRackUnitFsmStageEntry OBJECT-TYPE
    SYNTAX           CfprApComputeRackUnitFsmStageEntry
    MAX-ACCESS       not-accessible
    STATUS           current
    DESCRIPTION
        "Entry for the cfprApComputeRackUnitFsmStageTable table."
    INDEX { cfprApComputeRackUnitFsmStageInstanceId }
    ::= { cfprApComputeRackUnitFsmStageTable 1 }

CfprApComputeRackUnitFsmStageEntry ::= SEQUENCE {
    cfprApComputeRackUnitFsmStageInstanceId                          CfprApManagedObjectId,
    cfprApComputeRackUnitFsmStageDn                                  CfprApManagedObjectDn,
    cfprApComputeRackUnitFsmStageRn                                  SnmpAdminString,
    cfprApComputeRackUnitFsmStageDescrData                           SnmpAdminString,
    cfprApComputeRackUnitFsmStageLastUpdateTime                      DateAndTime,
    cfprApComputeRackUnitFsmStageName                                CfprApComputeRackUnitFsmStageName,
    cfprApComputeRackUnitFsmStageOrder                               Gauge32,
    cfprApComputeRackUnitFsmStageRetry                               Gauge32,
    cfprApComputeRackUnitFsmStageStageStatus                         CfprApFsmFsmStageStatus
}

cfprApComputeRackUnitFsmStageInstanceId OBJECT-TYPE
    SYNTAX       CfprApManagedObjectId
    MAX-ACCESS   not-accessible
    STATUS       current
    DESCRIPTION
        "Instance identifier of the managed object."
    ::= { cfprApComputeRackUnitFsmStageEntry 1 }

cfprApComputeRackUnitFsmStageDn OBJECT-TYPE
    SYNTAX       CfprApManagedObjectDn
    MAX-ACCESS   read-only
    STATUS       current
    DESCRIPTION
        "Cisco Firepower compute:RackUnitFsmStage:dn managed
        object property"
    ::= { cfprApComputeRackUnitFsmStageEntry 2 }

cfprApComputeRackUnitFsmStageRn OBJECT-TYPE
    SYNTAX       SnmpAdminString
    MAX-ACCESS   read-only
    STATUS       current
    DESCRIPTION
        "Cisco Firepower compute:RackUnitFsmStage:rn managed
        object property"
    ::= { cfprApComputeRackUnitFsmStageEntry 3 }

cfprApComputeRackUnitFsmStageDescrData OBJECT-TYPE
    SYNTAX       SnmpAdminString
    MAX-ACCESS   read-only
    STATUS       current
    DESCRIPTION
        "Cisco Firepower compute:RackUnitFsmStage:descr
        managed object property"
    ::= { cfprApComputeRackUnitFsmStageEntry 4 }

cfprApComputeRackUnitFsmStageLastUpdateTime OBJECT-TYPE
    SYNTAX       DateAndTime
    MAX-ACCESS   read-only
    STATUS       current
    DESCRIPTION
        "Cisco Firepower compute:RackUnitFsmStage:lastUpdateTime
        managed object property"
    ::= { cfprApComputeRackUnitFsmStageEntry 5 }

cfprApComputeRackUnitFsmStageName OBJECT-TYPE
    SYNTAX       CfprApComputeRackUnitFsmStageName
    MAX-ACCESS   read-only
    STATUS       current
    DESCRIPTION
        "Cisco Firepower compute:RackUnitFsmStage:name
        managed object property"
    ::= { cfprApComputeRackUnitFsmStageEntry 6 }

cfprApComputeRackUnitFsmStageOrder OBJECT-TYPE
    SYNTAX       Gauge32
    MAX-ACCESS   read-only
    STATUS       current
    DESCRIPTION
        "Cisco Firepower compute:RackUnitFsmStage:order
        managed object property"
    ::= { cfprApComputeRackUnitFsmStageEntry 7 }

cfprApComputeRackUnitFsmStageRetry OBJECT-TYPE
    SYNTAX       Gauge32
    MAX-ACCESS   read-only
    STATUS       current
    DESCRIPTION
        "Cisco Firepower compute:RackUnitFsmStage:retry
        managed object property"
    ::= { cfprApComputeRackUnitFsmStageEntry 8 }

cfprApComputeRackUnitFsmStageStageStatus OBJECT-TYPE
    SYNTAX       CfprApFsmFsmStageStatus
    MAX-ACCESS   read-only
    STATUS       current
    DESCRIPTION
        "Cisco Firepower compute:RackUnitFsmStage:stageStatus
        managed object property"
    ::= { cfprApComputeRackUnitFsmStageEntry 9 }

cfprApComputeRackUnitMbTempStatsTable OBJECT-TYPE
    SYNTAX           SEQUENCE OF CfprApComputeRackUnitMbTempStatsEntry
    MAX-ACCESS       not-accessible
    STATUS           current
    DESCRIPTION
        "Cisco Firepower compute:RackUnitMbTempStats managed object table"
    ::= { cfprApComputeObjects 56 }

cfprApComputeRackUnitMbTempStatsEntry OBJECT-TYPE
    SYNTAX           CfprApComputeRackUnitMbTempStatsEntry
    MAX-ACCESS       not-accessible
    STATUS           current
    DESCRIPTION
        "Entry for the cfprApComputeRackUnitMbTempStatsTable table."
    INDEX { cfprApComputeRackUnitMbTempStatsInstanceId }
    ::= { cfprApComputeRackUnitMbTempStatsTable 1 }

CfprApComputeRackUnitMbTempStatsEntry ::= SEQUENCE {
    cfprApComputeRackUnitMbTempStatsInstanceId                       CfprApManagedObjectId,
    cfprApComputeRackUnitMbTempStatsDn                               CfprApManagedObjectDn,
    cfprApComputeRackUnitMbTempStatsRn                               SnmpAdminString,
    cfprApComputeRackUnitMbTempStatsAmbientTemp                      INTEGER,
    cfprApComputeRackUnitMbTempStatsAmbientTempAvg                   INTEGER,
    cfprApComputeRackUnitMbTempStatsAmbientTempMax                   INTEGER,
    cfprApComputeRackUnitMbTempStatsAmbientTempMin                   INTEGER,
    cfprApComputeRackUnitMbTempStatsFrontTemp                        INTEGER,
    cfprApComputeRackUnitMbTempStatsFrontTempAvg                     INTEGER,
    cfprApComputeRackUnitMbTempStatsFrontTempMax                     INTEGER,
    cfprApComputeRackUnitMbTempStatsFrontTempMin                     INTEGER,
    cfprApComputeRackUnitMbTempStatsIntervals                        Gauge32,
    cfprApComputeRackUnitMbTempStatsIoh1Temp                         INTEGER,
    cfprApComputeRackUnitMbTempStatsIoh1TempAvg                      INTEGER,
    cfprApComputeRackUnitMbTempStatsIoh1TempMax                      INTEGER,
    cfprApComputeRackUnitMbTempStatsIoh1TempMin                      INTEGER,
    cfprApComputeRackUnitMbTempStatsIoh2Temp                         INTEGER,
    cfprApComputeRackUnitMbTempStatsIoh2TempAvg                      INTEGER,
    cfprApComputeRackUnitMbTempStatsIoh2TempMax                      INTEGER,
    cfprApComputeRackUnitMbTempStatsIoh2TempMin                      INTEGER,
    cfprApComputeRackUnitMbTempStatsRearTemp                         INTEGER,
    cfprApComputeRackUnitMbTempStatsRearTempAvg                      INTEGER,
    cfprApComputeRackUnitMbTempStatsRearTempMax                      INTEGER,
    cfprApComputeRackUnitMbTempStatsRearTempMin                      INTEGER,
    cfprApComputeRackUnitMbTempStatsSuspect                          TruthValue,
    cfprApComputeRackUnitMbTempStatsThresholded                      CfprApComputeRackUnitMbTempStatsThresholded,
    cfprApComputeRackUnitMbTempStatsTimeCollected                    DateAndTime,
    cfprApComputeRackUnitMbTempStatsUpdate                           Gauge32
}

cfprApComputeRackUnitMbTempStatsInstanceId OBJECT-TYPE
    SYNTAX       CfprApManagedObjectId
    MAX-ACCESS   not-accessible
    STATUS       current
    DESCRIPTION
        "Instance identifier of the managed object."
    ::= { cfprApComputeRackUnitMbTempStatsEntry 1 }

cfprApComputeRackUnitMbTempStatsDn OBJECT-TYPE
    SYNTAX       CfprApManagedObjectDn
    MAX-ACCESS   read-only
    STATUS       current
    DESCRIPTION
        "Cisco Firepower compute:RackUnitMbTempStats:dn
        managed object property"
    ::= { cfprApComputeRackUnitMbTempStatsEntry 2 }

cfprApComputeRackUnitMbTempStatsRn OBJECT-TYPE
    SYNTAX       SnmpAdminString
    MAX-ACCESS   read-only
    STATUS       current
    DESCRIPTION
        "Cisco Firepower compute:RackUnitMbTempStats:rn
        managed object property"
    ::= { cfprApComputeRackUnitMbTempStatsEntry 3 }

cfprApComputeRackUnitMbTempStatsAmbientTemp OBJECT-TYPE
    SYNTAX       INTEGER
    MAX-ACCESS   read-only
    STATUS       current
    DESCRIPTION
        "Cisco Firepower compute:RackUnitMbTempStats:ambientTemp
        managed object property"
    ::= { cfprApComputeRackUnitMbTempStatsEntry 4 }

cfprApComputeRackUnitMbTempStatsAmbientTempAvg OBJECT-TYPE
    SYNTAX       INTEGER
    MAX-ACCESS   read-only
    STATUS       current
    DESCRIPTION
        "Cisco Firepower compute:RackUnitMbTempStats:ambientTempAvg
        managed object property"
    ::= { cfprApComputeRackUnitMbTempStatsEntry 5 }

cfprApComputeRackUnitMbTempStatsAmbientTempMax OBJECT-TYPE
    SYNTAX       INTEGER
    MAX-ACCESS   read-only
    STATUS       current
    DESCRIPTION
        "Cisco Firepower compute:RackUnitMbTempStats:ambientTempMax
        managed object property"
    ::= { cfprApComputeRackUnitMbTempStatsEntry 6 }

cfprApComputeRackUnitMbTempStatsAmbientTempMin OBJECT-TYPE
    SYNTAX       INTEGER
    MAX-ACCESS   read-only
    STATUS       current
    DESCRIPTION
        "Cisco Firepower compute:RackUnitMbTempStats:ambientTempMin
        managed object property"
    ::= { cfprApComputeRackUnitMbTempStatsEntry 7 }

cfprApComputeRackUnitMbTempStatsFrontTemp OBJECT-TYPE
    SYNTAX       INTEGER
    MAX-ACCESS   read-only
    STATUS       current
    DESCRIPTION
        "Cisco Firepower compute:RackUnitMbTempStats:frontTemp
        managed object property"
    ::= { cfprApComputeRackUnitMbTempStatsEntry 8 }

cfprApComputeRackUnitMbTempStatsFrontTempAvg OBJECT-TYPE
    SYNTAX       INTEGER
    MAX-ACCESS   read-only
    STATUS       current
    DESCRIPTION
        "Cisco Firepower compute:RackUnitMbTempStats:frontTempAvg
        managed object property"
    ::= { cfprApComputeRackUnitMbTempStatsEntry 9 }

cfprApComputeRackUnitMbTempStatsFrontTempMax OBJECT-TYPE
    SYNTAX       INTEGER
    MAX-ACCESS   read-only
    STATUS       current
    DESCRIPTION
        "Cisco Firepower compute:RackUnitMbTempStats:frontTempMax
        managed object property"
    ::= { cfprApComputeRackUnitMbTempStatsEntry 10 }

cfprApComputeRackUnitMbTempStatsFrontTempMin OBJECT-TYPE
    SYNTAX       INTEGER
    MAX-ACCESS   read-only
    STATUS       current
    DESCRIPTION
        "Cisco Firepower compute:RackUnitMbTempStats:frontTempMin
        managed object property"
    ::= { cfprApComputeRackUnitMbTempStatsEntry 11 }

cfprApComputeRackUnitMbTempStatsIntervals OBJECT-TYPE
    SYNTAX       Gauge32
    MAX-ACCESS   read-only
    STATUS       current
    DESCRIPTION
        "Cisco Firepower compute:RackUnitMbTempStats:intervals
        managed object property"
    ::= { cfprApComputeRackUnitMbTempStatsEntry 12 }

cfprApComputeRackUnitMbTempStatsIoh1Temp OBJECT-TYPE
    SYNTAX       INTEGER
    MAX-ACCESS   read-only
    STATUS       current
    DESCRIPTION
        "Cisco Firepower compute:RackUnitMbTempStats:ioh1Temp
        managed object property"
    ::= { cfprApComputeRackUnitMbTempStatsEntry 13 }

cfprApComputeRackUnitMbTempStatsIoh1TempAvg OBJECT-TYPE
    SYNTAX       INTEGER
    MAX-ACCESS   read-only
    STATUS       current
    DESCRIPTION
        "Cisco Firepower compute:RackUnitMbTempStats:ioh1TempAvg
        managed object property"
    ::= { cfprApComputeRackUnitMbTempStatsEntry 14 }

cfprApComputeRackUnitMbTempStatsIoh1TempMax OBJECT-TYPE
    SYNTAX       INTEGER
    MAX-ACCESS   read-only
    STATUS       current
    DESCRIPTION
        "Cisco Firepower compute:RackUnitMbTempStats:ioh1TempMax
        managed object property"
    ::= { cfprApComputeRackUnitMbTempStatsEntry 15 }

cfprApComputeRackUnitMbTempStatsIoh1TempMin OBJECT-TYPE
    SYNTAX       INTEGER
    MAX-ACCESS   read-only
    STATUS       current
    DESCRIPTION
        "Cisco Firepower compute:RackUnitMbTempStats:ioh1TempMin
        managed object property"
    ::= { cfprApComputeRackUnitMbTempStatsEntry 16 }

cfprApComputeRackUnitMbTempStatsIoh2Temp OBJECT-TYPE
    SYNTAX       INTEGER
    MAX-ACCESS   read-only
    STATUS       current
    DESCRIPTION
        "Cisco Firepower compute:RackUnitMbTempStats:ioh2Temp
        managed object property"
    ::= { cfprApComputeRackUnitMbTempStatsEntry 17 }

cfprApComputeRackUnitMbTempStatsIoh2TempAvg OBJECT-TYPE
    SYNTAX       INTEGER
    MAX-ACCESS   read-only
    STATUS       current
    DESCRIPTION
        "Cisco Firepower compute:RackUnitMbTempStats:ioh2TempAvg
        managed object property"
    ::= { cfprApComputeRackUnitMbTempStatsEntry 18 }

cfprApComputeRackUnitMbTempStatsIoh2TempMax OBJECT-TYPE
    SYNTAX       INTEGER
    MAX-ACCESS   read-only
    STATUS       current
    DESCRIPTION
        "Cisco Firepower compute:RackUnitMbTempStats:ioh2TempMax
        managed object property"
    ::= { cfprApComputeRackUnitMbTempStatsEntry 19 }

cfprApComputeRackUnitMbTempStatsIoh2TempMin OBJECT-TYPE
    SYNTAX       INTEGER
    MAX-ACCESS   read-only
    STATUS       current
    DESCRIPTION
        "Cisco Firepower compute:RackUnitMbTempStats:ioh2TempMin
        managed object property"
    ::= { cfprApComputeRackUnitMbTempStatsEntry 20 }

cfprApComputeRackUnitMbTempStatsRearTemp OBJECT-TYPE
    SYNTAX       INTEGER
    MAX-ACCESS   read-only
    STATUS       current
    DESCRIPTION
        "Cisco Firepower compute:RackUnitMbTempStats:rearTemp
        managed object property"
    ::= { cfprApComputeRackUnitMbTempStatsEntry 21 }

cfprApComputeRackUnitMbTempStatsRearTempAvg OBJECT-TYPE
    SYNTAX       INTEGER
    MAX-ACCESS   read-only
    STATUS       current
    DESCRIPTION
        "Cisco Firepower compute:RackUnitMbTempStats:rearTempAvg
        managed object property"
    ::= { cfprApComputeRackUnitMbTempStatsEntry 22 }

cfprApComputeRackUnitMbTempStatsRearTempMax OBJECT-TYPE
    SYNTAX       INTEGER
    MAX-ACCESS   read-only
    STATUS       current
    DESCRIPTION
        "Cisco Firepower compute:RackUnitMbTempStats:rearTempMax
        managed object property"
    ::= { cfprApComputeRackUnitMbTempStatsEntry 23 }

cfprApComputeRackUnitMbTempStatsRearTempMin OBJECT-TYPE
    SYNTAX       INTEGER
    MAX-ACCESS   read-only
    STATUS       current
    DESCRIPTION
        "Cisco Firepower compute:RackUnitMbTempStats:rearTempMin
        managed object property"
    ::= { cfprApComputeRackUnitMbTempStatsEntry 24 }

cfprApComputeRackUnitMbTempStatsSuspect OBJECT-TYPE
    SYNTAX       TruthValue
    MAX-ACCESS   read-only
    STATUS       current
    DESCRIPTION
        "Cisco Firepower compute:RackUnitMbTempStats:suspect
        managed object property"
    ::= { cfprApComputeRackUnitMbTempStatsEntry 25 }

cfprApComputeRackUnitMbTempStatsThresholded OBJECT-TYPE
    SYNTAX       CfprApComputeRackUnitMbTempStatsThresholded
    MAX-ACCESS   read-only
    STATUS       current
    DESCRIPTION
        "Cisco Firepower compute:RackUnitMbTempStats:thresholded
        managed object property"
    ::= { cfprApComputeRackUnitMbTempStatsEntry 26 }

cfprApComputeRackUnitMbTempStatsTimeCollected OBJECT-TYPE
    SYNTAX       DateAndTime
    MAX-ACCESS   read-only
    STATUS       current
    DESCRIPTION
        "Cisco Firepower compute:RackUnitMbTempStats:timeCollected
        managed object property"
    ::= { cfprApComputeRackUnitMbTempStatsEntry 27 }

cfprApComputeRackUnitMbTempStatsUpdate OBJECT-TYPE
    SYNTAX       Gauge32
    MAX-ACCESS   read-only
    STATUS       current
    DESCRIPTION
        "Cisco Firepower compute:RackUnitMbTempStats:update
        managed object property"
    ::= { cfprApComputeRackUnitMbTempStatsEntry 28 }

cfprApComputeRackUnitMbTempStatsHistTable OBJECT-TYPE
    SYNTAX           SEQUENCE OF CfprApComputeRackUnitMbTempStatsHistEntry
    MAX-ACCESS       not-accessible
    STATUS           current
    DESCRIPTION
        "Cisco Firepower compute:RackUnitMbTempStatsHist
        managed object table"
    ::= { cfprApComputeObjects 57 }

cfprApComputeRackUnitMbTempStatsHistEntry OBJECT-TYPE
    SYNTAX           CfprApComputeRackUnitMbTempStatsHistEntry
    MAX-ACCESS       not-accessible
    STATUS           current
    DESCRIPTION
        "Entry for the cfprApComputeRackUnitMbTempStatsHistTable table."
    INDEX { cfprApComputeRackUnitMbTempStatsHistInstanceId }
    ::= { cfprApComputeRackUnitMbTempStatsHistTable 1 }

CfprApComputeRackUnitMbTempStatsHistEntry ::= SEQUENCE {
    cfprApComputeRackUnitMbTempStatsHistInstanceId                   CfprApManagedObjectId,
    cfprApComputeRackUnitMbTempStatsHistDn                           CfprApManagedObjectDn,
    cfprApComputeRackUnitMbTempStatsHistRn                           SnmpAdminString,
    cfprApComputeRackUnitMbTempStatsHistAmbientTemp                  INTEGER,
    cfprApComputeRackUnitMbTempStatsHistAmbientTempAvg               INTEGER,
    cfprApComputeRackUnitMbTempStatsHistAmbientTempMax               INTEGER,
    cfprApComputeRackUnitMbTempStatsHistAmbientTempMin               INTEGER,
    cfprApComputeRackUnitMbTempStatsHistFrontTemp                    INTEGER,
    cfprApComputeRackUnitMbTempStatsHistFrontTempAvg                 INTEGER,
    cfprApComputeRackUnitMbTempStatsHistFrontTempMax                 INTEGER,
    cfprApComputeRackUnitMbTempStatsHistFrontTempMin                 INTEGER,
    cfprApComputeRackUnitMbTempStatsHistId                           Unsigned64,
    cfprApComputeRackUnitMbTempStatsHistIoh1Temp                     INTEGER,
    cfprApComputeRackUnitMbTempStatsHistIoh1TempAvg                  INTEGER,
    cfprApComputeRackUnitMbTempStatsHistIoh1TempMax                  INTEGER,
    cfprApComputeRackUnitMbTempStatsHistIoh1TempMin                  INTEGER,
    cfprApComputeRackUnitMbTempStatsHistIoh2Temp                     INTEGER,
    cfprApComputeRackUnitMbTempStatsHistIoh2TempAvg                  INTEGER,
    cfprApComputeRackUnitMbTempStatsHistIoh2TempMax                  INTEGER,
    cfprApComputeRackUnitMbTempStatsHistIoh2TempMin                  INTEGER,
    cfprApComputeRackUnitMbTempStatsHistMostRecent                   TruthValue,
    cfprApComputeRackUnitMbTempStatsHistRearTemp                     INTEGER,
    cfprApComputeRackUnitMbTempStatsHistRearTempAvg                  INTEGER,
    cfprApComputeRackUnitMbTempStatsHistRearTempMax                  INTEGER,
    cfprApComputeRackUnitMbTempStatsHistRearTempMin                  INTEGER,
    cfprApComputeRackUnitMbTempStatsHistSuspect                      TruthValue,
    cfprApComputeRackUnitMbTempStatsHistThresholded                  CfprApComputeRackUnitMbTempStatsHistThresholded,
    cfprApComputeRackUnitMbTempStatsHistTimeCollected                DateAndTime
}

cfprApComputeRackUnitMbTempStatsHistInstanceId OBJECT-TYPE
    SYNTAX       CfprApManagedObjectId
    MAX-ACCESS   not-accessible
    STATUS       current
    DESCRIPTION
        "Instance identifier of the managed object."
    ::= { cfprApComputeRackUnitMbTempStatsHistEntry 1 }

cfprApComputeRackUnitMbTempStatsHistDn OBJECT-TYPE
    SYNTAX       CfprApManagedObjectDn
    MAX-ACCESS   read-only
    STATUS       current
    DESCRIPTION
        "Cisco Firepower compute:RackUnitMbTempStatsHist:dn
        managed object property"
    ::= { cfprApComputeRackUnitMbTempStatsHistEntry 2 }

cfprApComputeRackUnitMbTempStatsHistRn OBJECT-TYPE
    SYNTAX       SnmpAdminString
    MAX-ACCESS   read-only
    STATUS       current
    DESCRIPTION
        "Cisco Firepower compute:RackUnitMbTempStatsHist:rn
        managed object property"
    ::= { cfprApComputeRackUnitMbTempStatsHistEntry 3 }

cfprApComputeRackUnitMbTempStatsHistAmbientTemp OBJECT-TYPE
    SYNTAX       INTEGER
    MAX-ACCESS   read-only
    STATUS       current
    DESCRIPTION
        "Cisco Firepower compute:RackUnitMbTempStatsHist:ambientTemp
        managed object property"
    ::= { cfprApComputeRackUnitMbTempStatsHistEntry 4 }

cfprApComputeRackUnitMbTempStatsHistAmbientTempAvg OBJECT-TYPE
    SYNTAX       INTEGER
    MAX-ACCESS   read-only
    STATUS       current
    DESCRIPTION
        "Cisco Firepower compute:RackUnitMbTempStatsHist:ambientTempAvg
        managed object property"
    ::= { cfprApComputeRackUnitMbTempStatsHistEntry 5 }

cfprApComputeRackUnitMbTempStatsHistAmbientTempMax OBJECT-TYPE
    SYNTAX       INTEGER
    MAX-ACCESS   read-only
    STATUS       current
    DESCRIPTION
        "Cisco Firepower compute:RackUnitMbTempStatsHist:ambientTempMax
        managed object property"
    ::= { cfprApComputeRackUnitMbTempStatsHistEntry 6 }

cfprApComputeRackUnitMbTempStatsHistAmbientTempMin OBJECT-TYPE
    SYNTAX       INTEGER
    MAX-ACCESS   read-only
    STATUS       current
    DESCRIPTION
        "Cisco Firepower compute:RackUnitMbTempStatsHist:ambientTempMin
        managed object property"
    ::= { cfprApComputeRackUnitMbTempStatsHistEntry 7 }

cfprApComputeRackUnitMbTempStatsHistFrontTemp OBJECT-TYPE
    SYNTAX       INTEGER
    MAX-ACCESS   read-only
    STATUS       current
    DESCRIPTION
        "Cisco Firepower compute:RackUnitMbTempStatsHist:frontTemp
        managed object property"
    ::= { cfprApComputeRackUnitMbTempStatsHistEntry 8 }

cfprApComputeRackUnitMbTempStatsHistFrontTempAvg OBJECT-TYPE
    SYNTAX       INTEGER
    MAX-ACCESS   read-only
    STATUS       current
    DESCRIPTION
        "Cisco Firepower compute:RackUnitMbTempStatsHist:frontTempAvg
        managed object property"
    ::= { cfprApComputeRackUnitMbTempStatsHistEntry 9 }

cfprApComputeRackUnitMbTempStatsHistFrontTempMax OBJECT-TYPE
    SYNTAX       INTEGER
    MAX-ACCESS   read-only
    STATUS       current
    DESCRIPTION
        "Cisco Firepower compute:RackUnitMbTempStatsHist:frontTempMax
        managed object property"
    ::= { cfprApComputeRackUnitMbTempStatsHistEntry 10 }

cfprApComputeRackUnitMbTempStatsHistFrontTempMin OBJECT-TYPE
    SYNTAX       INTEGER
    MAX-ACCESS   read-only
    STATUS       current
    DESCRIPTION
        "Cisco Firepower compute:RackUnitMbTempStatsHist:frontTempMin
        managed object property"
    ::= { cfprApComputeRackUnitMbTempStatsHistEntry 11 }

cfprApComputeRackUnitMbTempStatsHistId OBJECT-TYPE
    SYNTAX       Unsigned64
    MAX-ACCESS   read-only
    STATUS       current
    DESCRIPTION
        "Cisco Firepower compute:RackUnitMbTempStatsHist:id
        managed object property"
    ::= { cfprApComputeRackUnitMbTempStatsHistEntry 12 }

cfprApComputeRackUnitMbTempStatsHistIoh1Temp OBJECT-TYPE
    SYNTAX       INTEGER
    MAX-ACCESS   read-only
    STATUS       current
    DESCRIPTION
        "Cisco Firepower compute:RackUnitMbTempStatsHist:ioh1Temp
        managed object property"
    ::= { cfprApComputeRackUnitMbTempStatsHistEntry 13 }

cfprApComputeRackUnitMbTempStatsHistIoh1TempAvg OBJECT-TYPE
    SYNTAX       INTEGER
    MAX-ACCESS   read-only
    STATUS       current
    DESCRIPTION
        "Cisco Firepower compute:RackUnitMbTempStatsHist:ioh1TempAvg
        managed object property"
    ::= { cfprApComputeRackUnitMbTempStatsHistEntry 14 }

cfprApComputeRackUnitMbTempStatsHistIoh1TempMax OBJECT-TYPE
    SYNTAX       INTEGER
    MAX-ACCESS   read-only
    STATUS       current
    DESCRIPTION
        "Cisco Firepower compute:RackUnitMbTempStatsHist:ioh1TempMax
        managed object property"
    ::= { cfprApComputeRackUnitMbTempStatsHistEntry 15 }

cfprApComputeRackUnitMbTempStatsHistIoh1TempMin OBJECT-TYPE
    SYNTAX       INTEGER
    MAX-ACCESS   read-only
    STATUS       current
    DESCRIPTION
        "Cisco Firepower compute:RackUnitMbTempStatsHist:ioh1TempMin
        managed object property"
    ::= { cfprApComputeRackUnitMbTempStatsHistEntry 16 }

cfprApComputeRackUnitMbTempStatsHistIoh2Temp OBJECT-TYPE
    SYNTAX       INTEGER
    MAX-ACCESS   read-only
    STATUS       current
    DESCRIPTION
        "Cisco Firepower compute:RackUnitMbTempStatsHist:ioh2Temp
        managed object property"
    ::= { cfprApComputeRackUnitMbTempStatsHistEntry 17 }

cfprApComputeRackUnitMbTempStatsHistIoh2TempAvg OBJECT-TYPE
    SYNTAX       INTEGER
    MAX-ACCESS   read-only
    STATUS       current
    DESCRIPTION
        "Cisco Firepower compute:RackUnitMbTempStatsHist:ioh2TempAvg
        managed object property"
    ::= { cfprApComputeRackUnitMbTempStatsHistEntry 18 }

cfprApComputeRackUnitMbTempStatsHistIoh2TempMax OBJECT-TYPE
    SYNTAX       INTEGER
    MAX-ACCESS   read-only
    STATUS       current
    DESCRIPTION
        "Cisco Firepower compute:RackUnitMbTempStatsHist:ioh2TempMax
        managed object property"
    ::= { cfprApComputeRackUnitMbTempStatsHistEntry 19 }

cfprApComputeRackUnitMbTempStatsHistIoh2TempMin OBJECT-TYPE
    SYNTAX       INTEGER
    MAX-ACCESS   read-only
    STATUS       current
    DESCRIPTION
        "Cisco Firepower compute:RackUnitMbTempStatsHist:ioh2TempMin
        managed object property"
    ::= { cfprApComputeRackUnitMbTempStatsHistEntry 20 }

cfprApComputeRackUnitMbTempStatsHistMostRecent OBJECT-TYPE
    SYNTAX       TruthValue
    MAX-ACCESS   read-only
    STATUS       current
    DESCRIPTION
        "Cisco Firepower compute:RackUnitMbTempStatsHist:mostRecent
        managed object property"
    ::= { cfprApComputeRackUnitMbTempStatsHistEntry 21 }

cfprApComputeRackUnitMbTempStatsHistRearTemp OBJECT-TYPE
    SYNTAX       INTEGER
    MAX-ACCESS   read-only
    STATUS       current
    DESCRIPTION
        "Cisco Firepower compute:RackUnitMbTempStatsHist:rearTemp
        managed object property"
    ::= { cfprApComputeRackUnitMbTempStatsHistEntry 22 }

cfprApComputeRackUnitMbTempStatsHistRearTempAvg OBJECT-TYPE
    SYNTAX       INTEGER
    MAX-ACCESS   read-only
    STATUS       current
    DESCRIPTION
        "Cisco Firepower compute:RackUnitMbTempStatsHist:rearTempAvg
        managed object property"
    ::= { cfprApComputeRackUnitMbTempStatsHistEntry 23 }

cfprApComputeRackUnitMbTempStatsHistRearTempMax OBJECT-TYPE
    SYNTAX       INTEGER
    MAX-ACCESS   read-only
    STATUS       current
    DESCRIPTION
        "Cisco Firepower compute:RackUnitMbTempStatsHist:rearTempMax
        managed object property"
    ::= { cfprApComputeRackUnitMbTempStatsHistEntry 24 }

cfprApComputeRackUnitMbTempStatsHistRearTempMin OBJECT-TYPE
    SYNTAX       INTEGER
    MAX-ACCESS   read-only
    STATUS       current
    DESCRIPTION
        "Cisco Firepower compute:RackUnitMbTempStatsHist:rearTempMin
        managed object property"
    ::= { cfprApComputeRackUnitMbTempStatsHistEntry 25 }

cfprApComputeRackUnitMbTempStatsHistSuspect OBJECT-TYPE
    SYNTAX       TruthValue
    MAX-ACCESS   read-only
    STATUS       current
    DESCRIPTION
        "Cisco Firepower compute:RackUnitMbTempStatsHist:suspect
        managed object property"
    ::= { cfprApComputeRackUnitMbTempStatsHistEntry 26 }

cfprApComputeRackUnitMbTempStatsHistThresholded OBJECT-TYPE
    SYNTAX       CfprApComputeRackUnitMbTempStatsHistThresholded
    MAX-ACCESS   read-only
    STATUS       current
    DESCRIPTION
        "Cisco Firepower compute:RackUnitMbTempStatsHist:thresholded
        managed object property"
    ::= { cfprApComputeRackUnitMbTempStatsHistEntry 27 }

cfprApComputeRackUnitMbTempStatsHistTimeCollected OBJECT-TYPE
    SYNTAX       DateAndTime
    MAX-ACCESS   read-only
    STATUS       current
    DESCRIPTION
        "Cisco Firepower compute:RackUnitMbTempStatsHist:timeCollected
        managed object property"
    ::= { cfprApComputeRackUnitMbTempStatsHistEntry 28 }

cfprApComputeRtcBatteryTable OBJECT-TYPE
    SYNTAX           SEQUENCE OF CfprApComputeRtcBatteryEntry
    MAX-ACCESS       not-accessible
    STATUS           current
    DESCRIPTION
        "Cisco Firepower compute:RtcBattery managed object table"
    ::= { cfprApComputeObjects 58 }

cfprApComputeRtcBatteryEntry OBJECT-TYPE
    SYNTAX           CfprApComputeRtcBatteryEntry
    MAX-ACCESS       not-accessible
    STATUS           current
    DESCRIPTION
        "Entry for the cfprApComputeRtcBatteryTable table."
    INDEX { cfprApComputeRtcBatteryInstanceId }
    ::= { cfprApComputeRtcBatteryTable 1 }

CfprApComputeRtcBatteryEntry ::= SEQUENCE {
    cfprApComputeRtcBatteryInstanceId                                CfprApManagedObjectId,
    cfprApComputeRtcBatteryDn                                        CfprApManagedObjectDn,
    cfprApComputeRtcBatteryRn                                        SnmpAdminString,
    cfprApComputeRtcBatteryId                                        Gauge32,
    cfprApComputeRtcBatteryLocationDn                                SnmpAdminString,
    cfprApComputeRtcBatteryModel                                     SnmpAdminString,
    cfprApComputeRtcBatteryOperQualifierReason                       SnmpAdminString,
    cfprApComputeRtcBatteryOperState                                 CfprApEquipmentOperability,
    cfprApComputeRtcBatteryOperability                               CfprApEquipmentOperability,
    cfprApComputeRtcBatteryPerf                                      CfprApEquipmentSensorThresholdStatus,
    cfprApComputeRtcBatteryPower                                     CfprApEquipmentPowerState,
    cfprApComputeRtcBatteryPresence                                  CfprApEquipmentPresence,
    cfprApComputeRtcBatteryRevision                                  SnmpAdminString,
    cfprApComputeRtcBatterySerial                                    SnmpAdminString,
    cfprApComputeRtcBatteryThermal                                   CfprApEquipmentSensorThresholdStatus,
    cfprApComputeRtcBatteryVendor                                    SnmpAdminString,
    cfprApComputeRtcBatteryVoltage                                   CfprApEquipmentSensorThresholdStatus
}

cfprApComputeRtcBatteryInstanceId OBJECT-TYPE
    SYNTAX       CfprApManagedObjectId
    MAX-ACCESS   not-accessible
    STATUS       current
    DESCRIPTION
        "Instance identifier of the managed object."
    ::= { cfprApComputeRtcBatteryEntry 1 }

cfprApComputeRtcBatteryDn OBJECT-TYPE
    SYNTAX       CfprApManagedObjectDn
    MAX-ACCESS   read-only
    STATUS       current
    DESCRIPTION
        "Cisco Firepower compute:RtcBattery:dn managed object property"
    ::= { cfprApComputeRtcBatteryEntry 2 }

cfprApComputeRtcBatteryRn OBJECT-TYPE
    SYNTAX       SnmpAdminString
    MAX-ACCESS   read-only
    STATUS       current
    DESCRIPTION
        "Cisco Firepower compute:RtcBattery:rn managed object property"
    ::= { cfprApComputeRtcBatteryEntry 3 }

cfprApComputeRtcBatteryId OBJECT-TYPE
    SYNTAX       Gauge32
    MAX-ACCESS   read-only
    STATUS       current
    DESCRIPTION
        "Cisco Firepower compute:RtcBattery:id managed object property"
    ::= { cfprApComputeRtcBatteryEntry 4 }

cfprApComputeRtcBatteryLocationDn OBJECT-TYPE
    SYNTAX       SnmpAdminString
    MAX-ACCESS   read-only
    STATUS       current
    DESCRIPTION
        "Cisco Firepower compute:RtcBattery:locationDn
        managed object property"
    ::= { cfprApComputeRtcBatteryEntry 5 }

cfprApComputeRtcBatteryModel OBJECT-TYPE
    SYNTAX       SnmpAdminString
    MAX-ACCESS   read-only
    STATUS       current
    DESCRIPTION
        "Cisco Firepower compute:RtcBattery:model managed object property"
    ::= { cfprApComputeRtcBatteryEntry 6 }

cfprApComputeRtcBatteryOperQualifierReason OBJECT-TYPE
    SYNTAX       SnmpAdminString
    MAX-ACCESS   read-only
    STATUS       current
    DESCRIPTION
        "Cisco Firepower compute:RtcBattery:operQualifierReason
        managed object property"
    ::= { cfprApComputeRtcBatteryEntry 7 }

cfprApComputeRtcBatteryOperState OBJECT-TYPE
    SYNTAX       CfprApEquipmentOperability
    MAX-ACCESS   read-only
    STATUS       current
    DESCRIPTION
        "Cisco Firepower compute:RtcBattery:operState managed
        object property"
    ::= { cfprApComputeRtcBatteryEntry 8 }

cfprApComputeRtcBatteryOperability OBJECT-TYPE
    SYNTAX       CfprApEquipmentOperability
    MAX-ACCESS   read-only
    STATUS       current
    DESCRIPTION
        "Cisco Firepower compute:RtcBattery:operability
        managed object property"
    ::= { cfprApComputeRtcBatteryEntry 9 }

cfprApComputeRtcBatteryPerf OBJECT-TYPE
    SYNTAX       CfprApEquipmentSensorThresholdStatus
    MAX-ACCESS   read-only
    STATUS       current
    DESCRIPTION
        "Cisco Firepower compute:RtcBattery:perf managed object property"
    ::= { cfprApComputeRtcBatteryEntry 10 }

cfprApComputeRtcBatteryPower OBJECT-TYPE
    SYNTAX       CfprApEquipmentPowerState
    MAX-ACCESS   read-only
    STATUS       current
    DESCRIPTION
        "Cisco Firepower compute:RtcBattery:power managed object property"
    ::= { cfprApComputeRtcBatteryEntry 11 }

cfprApComputeRtcBatteryPresence OBJECT-TYPE
    SYNTAX       CfprApEquipmentPresence
    MAX-ACCESS   read-only
    STATUS       current
    DESCRIPTION
        "Cisco Firepower compute:RtcBattery:presence managed
        object property"
    ::= { cfprApComputeRtcBatteryEntry 12 }

cfprApComputeRtcBatteryRevision OBJECT-TYPE
    SYNTAX       SnmpAdminString
    MAX-ACCESS   read-only
    STATUS       current
    DESCRIPTION
        "Cisco Firepower compute:RtcBattery:revision managed
        object property"
    ::= { cfprApComputeRtcBatteryEntry 13 }

cfprApComputeRtcBatterySerial OBJECT-TYPE
    SYNTAX       SnmpAdminString
    MAX-ACCESS   read-only
    STATUS       current
    DESCRIPTION
        "Cisco Firepower compute:RtcBattery:serial managed
        object property"
    ::= { cfprApComputeRtcBatteryEntry 14 }

cfprApComputeRtcBatteryThermal OBJECT-TYPE
    SYNTAX       CfprApEquipmentSensorThresholdStatus
    MAX-ACCESS   read-only
    STATUS       current
    DESCRIPTION
        "Cisco Firepower compute:RtcBattery:thermal managed
        object property"
    ::= { cfprApComputeRtcBatteryEntry 15 }

cfprApComputeRtcBatteryVendor OBJECT-TYPE
    SYNTAX       SnmpAdminString
    MAX-ACCESS   read-only
    STATUS       current
    DESCRIPTION
        "Cisco Firepower compute:RtcBattery:vendor managed
        object property"
    ::= { cfprApComputeRtcBatteryEntry 16 }

cfprApComputeRtcBatteryVoltage OBJECT-TYPE
    SYNTAX       CfprApEquipmentSensorThresholdStatus
    MAX-ACCESS   read-only
    STATUS       current
    DESCRIPTION
        "Cisco Firepower compute:RtcBattery:voltage managed
        object property"
    ::= { cfprApComputeRtcBatteryEntry 17 }

cfprApComputeScrubPolicyTable OBJECT-TYPE
    SYNTAX           SEQUENCE OF CfprApComputeScrubPolicyEntry
    MAX-ACCESS       not-accessible
    STATUS           current
    DESCRIPTION
        "Cisco Firepower compute:ScrubPolicy managed object table"
    ::= { cfprApComputeObjects 59 }

cfprApComputeScrubPolicyEntry OBJECT-TYPE
    SYNTAX           CfprApComputeScrubPolicyEntry
    MAX-ACCESS       not-accessible
    STATUS           current
    DESCRIPTION
        "Entry for the cfprApComputeScrubPolicyTable table."
    INDEX { cfprApComputeScrubPolicyInstanceId }
    ::= { cfprApComputeScrubPolicyTable 1 }

CfprApComputeScrubPolicyEntry ::= SEQUENCE {
    cfprApComputeScrubPolicyInstanceId                               CfprApManagedObjectId,
    cfprApComputeScrubPolicyDn                                       CfprApManagedObjectDn,
    cfprApComputeScrubPolicyRn                                       SnmpAdminString,
    cfprApComputeScrubPolicyBiosSettingsScrub                        CfprApComputeScrubAction,
    cfprApComputeScrubPolicyDescr                                    SnmpAdminString,
    cfprApComputeScrubPolicyDiskScrub                                CfprApComputeScrubAction,
    cfprApComputeScrubPolicyFlexFlashScrub                           CfprApComputeScrubAction,
    cfprApComputeScrubPolicyIntId                                    SnmpAdminString,
    cfprApComputeScrubPolicyName                                     SnmpAdminString,
    cfprApComputeScrubPolicyPolicyLevel                              Gauge32,
    cfprApComputeScrubPolicyPolicyOwner                              CfprApPolicyPolicyOwner
}

cfprApComputeScrubPolicyInstanceId OBJECT-TYPE
    SYNTAX       CfprApManagedObjectId
    MAX-ACCESS   not-accessible
    STATUS       current
    DESCRIPTION
        "Instance identifier of the managed object."
    ::= { cfprApComputeScrubPolicyEntry 1 }

cfprApComputeScrubPolicyDn OBJECT-TYPE
    SYNTAX       CfprApManagedObjectDn
    MAX-ACCESS   read-only
    STATUS       current
    DESCRIPTION
        "Cisco Firepower compute:ScrubPolicy:dn managed object property"
    ::= { cfprApComputeScrubPolicyEntry 2 }

cfprApComputeScrubPolicyRn OBJECT-TYPE
    SYNTAX       SnmpAdminString
    MAX-ACCESS   read-only
    STATUS       current
    DESCRIPTION
        "Cisco Firepower compute:ScrubPolicy:rn managed object property"
    ::= { cfprApComputeScrubPolicyEntry 3 }

cfprApComputeScrubPolicyBiosSettingsScrub OBJECT-TYPE
    SYNTAX       CfprApComputeScrubAction
    MAX-ACCESS   read-only
    STATUS       current
    DESCRIPTION
        "Cisco Firepower compute:ScrubPolicy:biosSettingsScrub
        managed object property"
    ::= { cfprApComputeScrubPolicyEntry 4 }

cfprApComputeScrubPolicyDescr OBJECT-TYPE
    SYNTAX       SnmpAdminString
    MAX-ACCESS   read-only
    STATUS       current
    DESCRIPTION
        "Cisco Firepower compute:ScrubPolicy:descr managed
        object property"
    ::= { cfprApComputeScrubPolicyEntry 5 }

cfprApComputeScrubPolicyDiskScrub OBJECT-TYPE
    SYNTAX       CfprApComputeScrubAction
    MAX-ACCESS   read-only
    STATUS       current
    DESCRIPTION
        "Cisco Firepower compute:ScrubPolicy:diskScrub
        managed object property"
    ::= { cfprApComputeScrubPolicyEntry 6 }

cfprApComputeScrubPolicyFlexFlashScrub OBJECT-TYPE
    SYNTAX       CfprApComputeScrubAction
    MAX-ACCESS   read-only
    STATUS       current
    DESCRIPTION
        "Cisco Firepower compute:ScrubPolicy:flexFlashScrub
        managed object property"
    ::= { cfprApComputeScrubPolicyEntry 7 }

cfprApComputeScrubPolicyIntId OBJECT-TYPE
    SYNTAX       SnmpAdminString
    MAX-ACCESS   read-only
    STATUS       current
    DESCRIPTION
        "Cisco Firepower compute:ScrubPolicy:intId managed
        object property"
    ::= { cfprApComputeScrubPolicyEntry 8 }

cfprApComputeScrubPolicyName OBJECT-TYPE
    SYNTAX       SnmpAdminString
    MAX-ACCESS   read-only
    STATUS       current
    DESCRIPTION
        "Cisco Firepower compute:ScrubPolicy:name managed object property"
    ::= { cfprApComputeScrubPolicyEntry 9 }

cfprApComputeScrubPolicyPolicyLevel OBJECT-TYPE
    SYNTAX       Gauge32
    MAX-ACCESS   read-only
    STATUS       current
    DESCRIPTION
        "Cisco Firepower compute:ScrubPolicy:policyLevel
        managed object property"
    ::= { cfprApComputeScrubPolicyEntry 10 }

cfprApComputeScrubPolicyPolicyOwner OBJECT-TYPE
    SYNTAX       CfprApPolicyPolicyOwner
    MAX-ACCESS   read-only
    STATUS       current
    DESCRIPTION
        "Cisco Firepower compute:ScrubPolicy:policyOwner
        managed object property"
    ::= { cfprApComputeScrubPolicyEntry 11 }

cfprApComputeServerDiscPolicyTable OBJECT-TYPE
    SYNTAX           SEQUENCE OF CfprApComputeServerDiscPolicyEntry
    MAX-ACCESS       not-accessible
    STATUS           current
    DESCRIPTION
        "Cisco Firepower compute:ServerDiscPolicy managed object table"
    ::= { cfprApComputeObjects 60 }

cfprApComputeServerDiscPolicyEntry OBJECT-TYPE
    SYNTAX           CfprApComputeServerDiscPolicyEntry
    MAX-ACCESS       not-accessible
    STATUS           current
    DESCRIPTION
        "Entry for the cfprApComputeServerDiscPolicyTable table."
    INDEX { cfprApComputeServerDiscPolicyInstanceId }
    ::= { cfprApComputeServerDiscPolicyTable 1 }

CfprApComputeServerDiscPolicyEntry ::= SEQUENCE {
    cfprApComputeServerDiscPolicyInstanceId                          CfprApManagedObjectId,
    cfprApComputeServerDiscPolicyDn                                  CfprApManagedObjectDn,
    cfprApComputeServerDiscPolicyRn                                  SnmpAdminString,
    cfprApComputeServerDiscPolicyAction                              SnmpAdminString,
    cfprApComputeServerDiscPolicyDescr                               SnmpAdminString,
    cfprApComputeServerDiscPolicyFsmDescr                            SnmpAdminString,
    cfprApComputeServerDiscPolicyFsmPrev                             SnmpAdminString,
    cfprApComputeServerDiscPolicyFsmProgr                            Gauge32,
    cfprApComputeServerDiscPolicyFsmRmtInvErrCode                    Gauge32,
    cfprApComputeServerDiscPolicyFsmRmtInvErrDescr                   SnmpAdminString,
    cfprApComputeServerDiscPolicyFsmRmtInvRslt                       CfprApConditionRemoteInvRslt,
    cfprApComputeServerDiscPolicyFsmStageDescr                       SnmpAdminString,
    cfprApComputeServerDiscPolicyFsmStamp                            DateAndTime,
    cfprApComputeServerDiscPolicyFsmStatus                           SnmpAdminString,
    cfprApComputeServerDiscPolicyFsmTry                              Gauge32,
    cfprApComputeServerDiscPolicyIntId                               SnmpAdminString,
    cfprApComputeServerDiscPolicyName                                SnmpAdminString,
    cfprApComputeServerDiscPolicyPolicyLevel                         Gauge32,
    cfprApComputeServerDiscPolicyPolicyOwner                         CfprApPolicyPolicyOwner,
    cfprApComputeServerDiscPolicyQualifier                           SnmpAdminString,
    cfprApComputeServerDiscPolicyScrubPolicyName                     SnmpAdminString
}

cfprApComputeServerDiscPolicyInstanceId OBJECT-TYPE
    SYNTAX       CfprApManagedObjectId
    MAX-ACCESS   not-accessible
    STATUS       current
    DESCRIPTION
        "Instance identifier of the managed object."
    ::= { cfprApComputeServerDiscPolicyEntry 1 }

cfprApComputeServerDiscPolicyDn OBJECT-TYPE
    SYNTAX       CfprApManagedObjectDn
    MAX-ACCESS   read-only
    STATUS       current
    DESCRIPTION
        "Cisco Firepower compute:ServerDiscPolicy:dn managed
        object property"
    ::= { cfprApComputeServerDiscPolicyEntry 2 }

cfprApComputeServerDiscPolicyRn OBJECT-TYPE
    SYNTAX       SnmpAdminString
    MAX-ACCESS   read-only
    STATUS       current
    DESCRIPTION
        "Cisco Firepower compute:ServerDiscPolicy:rn managed
        object property"
    ::= { cfprApComputeServerDiscPolicyEntry 3 }

cfprApComputeServerDiscPolicyAction OBJECT-TYPE
    SYNTAX       SnmpAdminString
    MAX-ACCESS   read-only
    STATUS       current
    DESCRIPTION
        "Cisco Firepower compute:ServerDiscPolicy:action
        managed object property"
    ::= { cfprApComputeServerDiscPolicyEntry 4 }

cfprApComputeServerDiscPolicyDescr OBJECT-TYPE
    SYNTAX       SnmpAdminString
    MAX-ACCESS   read-only
    STATUS       current
    DESCRIPTION
        "Cisco Firepower compute:ServerDiscPolicy:descr
        managed object property"
    ::= { cfprApComputeServerDiscPolicyEntry 5 }

cfprApComputeServerDiscPolicyFsmDescr OBJECT-TYPE
    SYNTAX       SnmpAdminString
    MAX-ACCESS   read-only
    STATUS       current
    DESCRIPTION
        "Cisco Firepower compute:ServerDiscPolicy:fsmDescr
        managed object property"
    ::= { cfprApComputeServerDiscPolicyEntry 6 }

cfprApComputeServerDiscPolicyFsmPrev OBJECT-TYPE
    SYNTAX       SnmpAdminString
    MAX-ACCESS   read-only
    STATUS       current
    DESCRIPTION
        "Cisco Firepower compute:ServerDiscPolicy:fsmPrev
        managed object property"
    ::= { cfprApComputeServerDiscPolicyEntry 7 }

cfprApComputeServerDiscPolicyFsmProgr OBJECT-TYPE
    SYNTAX       Gauge32
    MAX-ACCESS   read-only
    STATUS       current
    DESCRIPTION
        "Cisco Firepower compute:ServerDiscPolicy:fsmProgr
        managed object property"
    ::= { cfprApComputeServerDiscPolicyEntry 8 }

cfprApComputeServerDiscPolicyFsmRmtInvErrCode OBJECT-TYPE
    SYNTAX       Gauge32
    MAX-ACCESS   read-only
    STATUS       current
    DESCRIPTION
        "Cisco Firepower compute:ServerDiscPolicy:fsmRmtInvErrCode
        managed object property"
    ::= { cfprApComputeServerDiscPolicyEntry 9 }

cfprApComputeServerDiscPolicyFsmRmtInvErrDescr OBJECT-TYPE
    SYNTAX       SnmpAdminString
    MAX-ACCESS   read-only
    STATUS       current
    DESCRIPTION
        "Cisco Firepower compute:ServerDiscPolicy:fsmRmtInvErrDescr
        managed object property"
    ::= { cfprApComputeServerDiscPolicyEntry 10 }

cfprApComputeServerDiscPolicyFsmRmtInvRslt OBJECT-TYPE
    SYNTAX       CfprApConditionRemoteInvRslt
    MAX-ACCESS   read-only
    STATUS       current
    DESCRIPTION
        "Cisco Firepower compute:ServerDiscPolicy:fsmRmtInvRslt
        managed object property"
    ::= { cfprApComputeServerDiscPolicyEntry 11 }

cfprApComputeServerDiscPolicyFsmStageDescr OBJECT-TYPE
    SYNTAX       SnmpAdminString
    MAX-ACCESS   read-only
    STATUS       current
    DESCRIPTION
        "Cisco Firepower compute:ServerDiscPolicy:fsmStageDescr
        managed object property"
    ::= { cfprApComputeServerDiscPolicyEntry 12 }

cfprApComputeServerDiscPolicyFsmStamp OBJECT-TYPE
    SYNTAX       DateAndTime
    MAX-ACCESS   read-only
    STATUS       current
    DESCRIPTION
        "Cisco Firepower compute:ServerDiscPolicy:fsmStamp
        managed object property"
    ::= { cfprApComputeServerDiscPolicyEntry 13 }

cfprApComputeServerDiscPolicyFsmStatus OBJECT-TYPE
    SYNTAX       SnmpAdminString
    MAX-ACCESS   read-only
    STATUS       current
    DESCRIPTION
        "Cisco Firepower compute:ServerDiscPolicy:fsmStatus
        managed object property"
    ::= { cfprApComputeServerDiscPolicyEntry 14 }

cfprApComputeServerDiscPolicyFsmTry OBJECT-TYPE
    SYNTAX       Gauge32
    MAX-ACCESS   read-only
    STATUS       current
    DESCRIPTION
        "Cisco Firepower compute:ServerDiscPolicy:fsmTry
        managed object property"
    ::= { cfprApComputeServerDiscPolicyEntry 15 }

cfprApComputeServerDiscPolicyIntId OBJECT-TYPE
    SYNTAX       SnmpAdminString
    MAX-ACCESS   read-only
    STATUS       current
    DESCRIPTION
        "Cisco Firepower compute:ServerDiscPolicy:intId
        managed object property"
    ::= { cfprApComputeServerDiscPolicyEntry 16 }

cfprApComputeServerDiscPolicyName OBJECT-TYPE
    SYNTAX       SnmpAdminString
    MAX-ACCESS   read-only
    STATUS       current
    DESCRIPTION
        "Cisco Firepower compute:ServerDiscPolicy:name
        managed object property"
    ::= { cfprApComputeServerDiscPolicyEntry 17 }

cfprApComputeServerDiscPolicyPolicyLevel OBJECT-TYPE
    SYNTAX       Gauge32
    MAX-ACCESS   read-only
    STATUS       current
    DESCRIPTION
        "Cisco Firepower compute:ServerDiscPolicy:policyLevel
        managed object property"
    ::= { cfprApComputeServerDiscPolicyEntry 18 }

cfprApComputeServerDiscPolicyPolicyOwner OBJECT-TYPE
    SYNTAX       CfprApPolicyPolicyOwner
    MAX-ACCESS   read-only
    STATUS       current
    DESCRIPTION
        "Cisco Firepower compute:ServerDiscPolicy:policyOwner
        managed object property"
    ::= { cfprApComputeServerDiscPolicyEntry 19 }

cfprApComputeServerDiscPolicyQualifier OBJECT-TYPE
    SYNTAX       SnmpAdminString
    MAX-ACCESS   read-only
    STATUS       current
    DESCRIPTION
        "Cisco Firepower compute:ServerDiscPolicy:qualifier
        managed object property"
    ::= { cfprApComputeServerDiscPolicyEntry 20 }

cfprApComputeServerDiscPolicyScrubPolicyName OBJECT-TYPE
    SYNTAX       SnmpAdminString
    MAX-ACCESS   read-only
    STATUS       current
    DESCRIPTION
        "Cisco Firepower compute:ServerDiscPolicy:scrubPolicyName
        managed object property"
    ::= { cfprApComputeServerDiscPolicyEntry 21 }

cfprApComputeServerDiscPolicyFsmTable OBJECT-TYPE
    SYNTAX           SEQUENCE OF CfprApComputeServerDiscPolicyFsmEntry
    MAX-ACCESS       not-accessible
    STATUS           current
    DESCRIPTION
        "Cisco Firepower compute:ServerDiscPolicyFsm managed object table"
    ::= { cfprApComputeObjects 61 }

cfprApComputeServerDiscPolicyFsmEntry OBJECT-TYPE
    SYNTAX           CfprApComputeServerDiscPolicyFsmEntry
    MAX-ACCESS       not-accessible
    STATUS           current
    DESCRIPTION
        "Entry for the cfprApComputeServerDiscPolicyFsmTable table."
    INDEX { cfprApComputeServerDiscPolicyFsmInstanceId }
    ::= { cfprApComputeServerDiscPolicyFsmTable 1 }

CfprApComputeServerDiscPolicyFsmEntry ::= SEQUENCE {
    cfprApComputeServerDiscPolicyFsmInstanceId                       CfprApManagedObjectId,
    cfprApComputeServerDiscPolicyFsmDn                               CfprApManagedObjectDn,
    cfprApComputeServerDiscPolicyFsmRn                               SnmpAdminString,
    cfprApComputeServerDiscPolicyFsmCompletionTime                   DateAndTime,
    cfprApComputeServerDiscPolicyFsmCurrentFsm                       CfprApComputeServerDiscPolicyFsmCurrentFsm,
    cfprApComputeServerDiscPolicyFsmDescrData                        SnmpAdminString,
    cfprApComputeServerDiscPolicyFsmFsmStatus                        CfprApFsmFsmStageStatus,
    cfprApComputeServerDiscPolicyFsmProgress                         Gauge32,
    cfprApComputeServerDiscPolicyFsmRmtErrCode                       Gauge32,
    cfprApComputeServerDiscPolicyFsmRmtErrDescr                      SnmpAdminString,
    cfprApComputeServerDiscPolicyFsmRmtRslt                          CfprApConditionRemoteInvRslt
}

cfprApComputeServerDiscPolicyFsmInstanceId OBJECT-TYPE
    SYNTAX       CfprApManagedObjectId
    MAX-ACCESS   not-accessible
    STATUS       current
    DESCRIPTION
        "Instance identifier of the managed object."
    ::= { cfprApComputeServerDiscPolicyFsmEntry 1 }

cfprApComputeServerDiscPolicyFsmDn OBJECT-TYPE
    SYNTAX       CfprApManagedObjectDn
    MAX-ACCESS   read-only
    STATUS       current
    DESCRIPTION
        "Cisco Firepower compute:ServerDiscPolicyFsm:dn
        managed object property"
    ::= { cfprApComputeServerDiscPolicyFsmEntry 2 }

cfprApComputeServerDiscPolicyFsmRn OBJECT-TYPE
    SYNTAX       SnmpAdminString
    MAX-ACCESS   read-only
    STATUS       current
    DESCRIPTION
        "Cisco Firepower compute:ServerDiscPolicyFsm:rn
        managed object property"
    ::= { cfprApComputeServerDiscPolicyFsmEntry 3 }

cfprApComputeServerDiscPolicyFsmCompletionTime OBJECT-TYPE
    SYNTAX       DateAndTime
    MAX-ACCESS   read-only
    STATUS       current
    DESCRIPTION
        "Cisco Firepower compute:ServerDiscPolicyFsm:completionTime
        managed object property"
    ::= { cfprApComputeServerDiscPolicyFsmEntry 4 }

cfprApComputeServerDiscPolicyFsmCurrentFsm OBJECT-TYPE
    SYNTAX       CfprApComputeServerDiscPolicyFsmCurrentFsm
    MAX-ACCESS   read-only
    STATUS       current
    DESCRIPTION
        "Cisco Firepower compute:ServerDiscPolicyFsm:currentFsm
        managed object property"
    ::= { cfprApComputeServerDiscPolicyFsmEntry 5 }

cfprApComputeServerDiscPolicyFsmDescrData OBJECT-TYPE
    SYNTAX       SnmpAdminString
    MAX-ACCESS   read-only
    STATUS       current
    DESCRIPTION
        "Cisco Firepower compute:ServerDiscPolicyFsm:descr
        managed object property"
    ::= { cfprApComputeServerDiscPolicyFsmEntry 6 }

cfprApComputeServerDiscPolicyFsmFsmStatus OBJECT-TYPE
    SYNTAX       CfprApFsmFsmStageStatus
    MAX-ACCESS   read-only
    STATUS       current
    DESCRIPTION
        "Cisco Firepower compute:ServerDiscPolicyFsm:fsmStatus
        managed object property"
    ::= { cfprApComputeServerDiscPolicyFsmEntry 7 }

cfprApComputeServerDiscPolicyFsmProgress OBJECT-TYPE
    SYNTAX       Gauge32
    MAX-ACCESS   read-only
    STATUS       current
    DESCRIPTION
        "Cisco Firepower compute:ServerDiscPolicyFsm:progress
        managed object property"
    ::= { cfprApComputeServerDiscPolicyFsmEntry 8 }

cfprApComputeServerDiscPolicyFsmRmtErrCode OBJECT-TYPE
    SYNTAX       Gauge32
    MAX-ACCESS   read-only
    STATUS       current
    DESCRIPTION
        "Cisco Firepower compute:ServerDiscPolicyFsm:rmtErrCode
        managed object property"
    ::= { cfprApComputeServerDiscPolicyFsmEntry 9 }

cfprApComputeServerDiscPolicyFsmRmtErrDescr OBJECT-TYPE
    SYNTAX       SnmpAdminString
    MAX-ACCESS   read-only
    STATUS       current
    DESCRIPTION
        "Cisco Firepower compute:ServerDiscPolicyFsm:rmtErrDescr
        managed object property"
    ::= { cfprApComputeServerDiscPolicyFsmEntry 10 }

cfprApComputeServerDiscPolicyFsmRmtRslt OBJECT-TYPE
    SYNTAX       CfprApConditionRemoteInvRslt
    MAX-ACCESS   read-only
    STATUS       current
    DESCRIPTION
        "Cisco Firepower compute:ServerDiscPolicyFsm:rmtRslt
        managed object property"
    ::= { cfprApComputeServerDiscPolicyFsmEntry 11 }

cfprApComputeServerDiscPolicyFsmStageTable OBJECT-TYPE
    SYNTAX           SEQUENCE OF CfprApComputeServerDiscPolicyFsmStageEntry
    MAX-ACCESS       not-accessible
    STATUS           current
    DESCRIPTION
        "Cisco Firepower compute:ServerDiscPolicyFsmStage
        managed object table"
    ::= { cfprApComputeObjects 62 }

cfprApComputeServerDiscPolicyFsmStageEntry OBJECT-TYPE
    SYNTAX           CfprApComputeServerDiscPolicyFsmStageEntry
    MAX-ACCESS       not-accessible
    STATUS           current
    DESCRIPTION
        "Entry for the cfprApComputeServerDiscPolicyFsmStageTable table."
    INDEX { cfprApComputeServerDiscPolicyFsmStageInstanceId }
    ::= { cfprApComputeServerDiscPolicyFsmStageTable 1 }

CfprApComputeServerDiscPolicyFsmStageEntry ::= SEQUENCE {
    cfprApComputeServerDiscPolicyFsmStageInstanceId                  CfprApManagedObjectId,
    cfprApComputeServerDiscPolicyFsmStageDn                          CfprApManagedObjectDn,
    cfprApComputeServerDiscPolicyFsmStageRn                          SnmpAdminString,
    cfprApComputeServerDiscPolicyFsmStageDescrData                   SnmpAdminString,
    cfprApComputeServerDiscPolicyFsmStageLastUpdateTime              DateAndTime,
    cfprApComputeServerDiscPolicyFsmStageName                        CfprApComputeServerDiscPolicyFsmStageName,
    cfprApComputeServerDiscPolicyFsmStageOrder                       Gauge32,
    cfprApComputeServerDiscPolicyFsmStageRetry                       Gauge32,
    cfprApComputeServerDiscPolicyFsmStageStageStatus                 CfprApFsmFsmStageStatus
}

cfprApComputeServerDiscPolicyFsmStageInstanceId OBJECT-TYPE
    SYNTAX       CfprApManagedObjectId
    MAX-ACCESS   not-accessible
    STATUS       current
    DESCRIPTION
        "Instance identifier of the managed object."
    ::= { cfprApComputeServerDiscPolicyFsmStageEntry 1 }

cfprApComputeServerDiscPolicyFsmStageDn OBJECT-TYPE
    SYNTAX       CfprApManagedObjectDn
    MAX-ACCESS   read-only
    STATUS       current
    DESCRIPTION
        "Cisco Firepower compute:ServerDiscPolicyFsmStage:dn
        managed object property"
    ::= { cfprApComputeServerDiscPolicyFsmStageEntry 2 }

cfprApComputeServerDiscPolicyFsmStageRn OBJECT-TYPE
    SYNTAX       SnmpAdminString
    MAX-ACCESS   read-only
    STATUS       current
    DESCRIPTION
        "Cisco Firepower compute:ServerDiscPolicyFsmStage:rn
        managed object property"
    ::= { cfprApComputeServerDiscPolicyFsmStageEntry 3 }

cfprApComputeServerDiscPolicyFsmStageDescrData OBJECT-TYPE
    SYNTAX       SnmpAdminString
    MAX-ACCESS   read-only
    STATUS       current
    DESCRIPTION
        "Cisco Firepower compute:ServerDiscPolicyFsmStage:descr
        managed object property"
    ::= { cfprApComputeServerDiscPolicyFsmStageEntry 4 }

cfprApComputeServerDiscPolicyFsmStageLastUpdateTime OBJECT-TYPE
    SYNTAX       DateAndTime
    MAX-ACCESS   read-only
    STATUS       current
    DESCRIPTION
        "Cisco Firepower compute:ServerDiscPolicyFsmStage:lastUpdateTime
        managed object property"
    ::= { cfprApComputeServerDiscPolicyFsmStageEntry 5 }

cfprApComputeServerDiscPolicyFsmStageName OBJECT-TYPE
    SYNTAX       CfprApComputeServerDiscPolicyFsmStageName
    MAX-ACCESS   read-only
    STATUS       current
    DESCRIPTION
        "Cisco Firepower compute:ServerDiscPolicyFsmStage:name
        managed object property"
    ::= { cfprApComputeServerDiscPolicyFsmStageEntry 6 }

cfprApComputeServerDiscPolicyFsmStageOrder OBJECT-TYPE
    SYNTAX       Gauge32
    MAX-ACCESS   read-only
    STATUS       current
    DESCRIPTION
        "Cisco Firepower compute:ServerDiscPolicyFsmStage:order
        managed object property"
    ::= { cfprApComputeServerDiscPolicyFsmStageEntry 7 }

cfprApComputeServerDiscPolicyFsmStageRetry OBJECT-TYPE
    SYNTAX       Gauge32
    MAX-ACCESS   read-only
    STATUS       current
    DESCRIPTION
        "Cisco Firepower compute:ServerDiscPolicyFsmStage:retry
        managed object property"
    ::= { cfprApComputeServerDiscPolicyFsmStageEntry 8 }

cfprApComputeServerDiscPolicyFsmStageStageStatus OBJECT-TYPE
    SYNTAX       CfprApFsmFsmStageStatus
    MAX-ACCESS   read-only
    STATUS       current
    DESCRIPTION
        "Cisco Firepower compute:ServerDiscPolicyFsmStage:stageStatus
        managed object property"
    ::= { cfprApComputeServerDiscPolicyFsmStageEntry 9 }

cfprApComputeServerDiscPolicyFsmTaskTable OBJECT-TYPE
    SYNTAX           SEQUENCE OF CfprApComputeServerDiscPolicyFsmTaskEntry
    MAX-ACCESS       not-accessible
    STATUS           current
    DESCRIPTION
        "Cisco Firepower compute:ServerDiscPolicyFsmTask
        managed object table"
    ::= { cfprApComputeObjects 63 }

cfprApComputeServerDiscPolicyFsmTaskEntry OBJECT-TYPE
    SYNTAX           CfprApComputeServerDiscPolicyFsmTaskEntry
    MAX-ACCESS       not-accessible
    STATUS           current
    DESCRIPTION
        "Entry for the cfprApComputeServerDiscPolicyFsmTaskTable table."
    INDEX { cfprApComputeServerDiscPolicyFsmTaskInstanceId }
    ::= { cfprApComputeServerDiscPolicyFsmTaskTable 1 }

CfprApComputeServerDiscPolicyFsmTaskEntry ::= SEQUENCE {
    cfprApComputeServerDiscPolicyFsmTaskInstanceId                   CfprApManagedObjectId,
    cfprApComputeServerDiscPolicyFsmTaskDn                           CfprApManagedObjectDn,
    cfprApComputeServerDiscPolicyFsmTaskRn                           SnmpAdminString,
    cfprApComputeServerDiscPolicyFsmTaskCompletion                   CfprApFsmCompletion,
    cfprApComputeServerDiscPolicyFsmTaskFlags                        CfprApFsmFlags,
    cfprApComputeServerDiscPolicyFsmTaskItem                         CfprApComputeServerDiscPolicyFsmTaskItem,
    cfprApComputeServerDiscPolicyFsmTaskSeqId                        Gauge32
}

cfprApComputeServerDiscPolicyFsmTaskInstanceId OBJECT-TYPE
    SYNTAX       CfprApManagedObjectId
    MAX-ACCESS   not-accessible
    STATUS       current
    DESCRIPTION
        "Instance identifier of the managed object."
    ::= { cfprApComputeServerDiscPolicyFsmTaskEntry 1 }

cfprApComputeServerDiscPolicyFsmTaskDn OBJECT-TYPE
    SYNTAX       CfprApManagedObjectDn
    MAX-ACCESS   read-only
    STATUS       current
    DESCRIPTION
        "Cisco Firepower compute:ServerDiscPolicyFsmTask:dn
        managed object property"
    ::= { cfprApComputeServerDiscPolicyFsmTaskEntry 2 }

cfprApComputeServerDiscPolicyFsmTaskRn OBJECT-TYPE
    SYNTAX       SnmpAdminString
    MAX-ACCESS   read-only
    STATUS       current
    DESCRIPTION
        "Cisco Firepower compute:ServerDiscPolicyFsmTask:rn
        managed object property"
    ::= { cfprApComputeServerDiscPolicyFsmTaskEntry 3 }

cfprApComputeServerDiscPolicyFsmTaskCompletion OBJECT-TYPE
    SYNTAX       CfprApFsmCompletion
    MAX-ACCESS   read-only
    STATUS       current
    DESCRIPTION
        "Cisco Firepower compute:ServerDiscPolicyFsmTask:completion
        managed object property"
    ::= { cfprApComputeServerDiscPolicyFsmTaskEntry 4 }

cfprApComputeServerDiscPolicyFsmTaskFlags OBJECT-TYPE
    SYNTAX       CfprApFsmFlags
    MAX-ACCESS   read-only
    STATUS       current
    DESCRIPTION
        "Cisco Firepower compute:ServerDiscPolicyFsmTask:flags
        managed object property"
    ::= { cfprApComputeServerDiscPolicyFsmTaskEntry 5 }

cfprApComputeServerDiscPolicyFsmTaskItem OBJECT-TYPE
    SYNTAX       CfprApComputeServerDiscPolicyFsmTaskItem
    MAX-ACCESS   read-only
    STATUS       current
    DESCRIPTION
        "Cisco Firepower compute:ServerDiscPolicyFsmTask:item
        managed object property"
    ::= { cfprApComputeServerDiscPolicyFsmTaskEntry 6 }

cfprApComputeServerDiscPolicyFsmTaskSeqId OBJECT-TYPE
    SYNTAX       Gauge32
    MAX-ACCESS   read-only
    STATUS       current
    DESCRIPTION
        "Cisco Firepower compute:ServerDiscPolicyFsmTask:seqId
        managed object property"
    ::= { cfprApComputeServerDiscPolicyFsmTaskEntry 7 }

cfprApComputeServerMgmtPolicyTable OBJECT-TYPE
    SYNTAX           SEQUENCE OF CfprApComputeServerMgmtPolicyEntry
    MAX-ACCESS       not-accessible
    STATUS           current
    DESCRIPTION
        "Cisco Firepower compute:ServerMgmtPolicy managed object table"
    ::= { cfprApComputeObjects 64 }

cfprApComputeServerMgmtPolicyEntry OBJECT-TYPE
    SYNTAX           CfprApComputeServerMgmtPolicyEntry
    MAX-ACCESS       not-accessible
    STATUS           current
    DESCRIPTION
        "Entry for the cfprApComputeServerMgmtPolicyTable table."
    INDEX { cfprApComputeServerMgmtPolicyInstanceId }
    ::= { cfprApComputeServerMgmtPolicyTable 1 }

CfprApComputeServerMgmtPolicyEntry ::= SEQUENCE {
    cfprApComputeServerMgmtPolicyInstanceId                          CfprApManagedObjectId,
    cfprApComputeServerMgmtPolicyDn                                  CfprApManagedObjectDn,
    cfprApComputeServerMgmtPolicyRn                                  SnmpAdminString,
    cfprApComputeServerMgmtPolicyAction                              CfprApComputeServerMgmtDiscAction,
    cfprApComputeServerMgmtPolicyDescr                               SnmpAdminString,
    cfprApComputeServerMgmtPolicyIntId                               SnmpAdminString,
    cfprApComputeServerMgmtPolicyName                                SnmpAdminString,
    cfprApComputeServerMgmtPolicyPolicyLevel                         Gauge32,
    cfprApComputeServerMgmtPolicyPolicyOwner                         CfprApPolicyPolicyOwner,
    cfprApComputeServerMgmtPolicyQualifier                           SnmpAdminString
}

cfprApComputeServerMgmtPolicyInstanceId OBJECT-TYPE
    SYNTAX       CfprApManagedObjectId
    MAX-ACCESS   not-accessible
    STATUS       current
    DESCRIPTION
        "Instance identifier of the managed object."
    ::= { cfprApComputeServerMgmtPolicyEntry 1 }

cfprApComputeServerMgmtPolicyDn OBJECT-TYPE
    SYNTAX       CfprApManagedObjectDn
    MAX-ACCESS   read-only
    STATUS       current
    DESCRIPTION
        "Cisco Firepower compute:ServerMgmtPolicy:dn managed
        object property"
    ::= { cfprApComputeServerMgmtPolicyEntry 2 }

cfprApComputeServerMgmtPolicyRn OBJECT-TYPE
    SYNTAX       SnmpAdminString
    MAX-ACCESS   read-only
    STATUS       current
    DESCRIPTION
        "Cisco Firepower compute:ServerMgmtPolicy:rn managed
        object property"
    ::= { cfprApComputeServerMgmtPolicyEntry 3 }

cfprApComputeServerMgmtPolicyAction OBJECT-TYPE
    SYNTAX       CfprApComputeServerMgmtDiscAction
    MAX-ACCESS   read-only
    STATUS       current
    DESCRIPTION
        "Cisco Firepower compute:ServerMgmtPolicy:action
        managed object property"
    ::= { cfprApComputeServerMgmtPolicyEntry 4 }

cfprApComputeServerMgmtPolicyDescr OBJECT-TYPE
    SYNTAX       SnmpAdminString
    MAX-ACCESS   read-only
    STATUS       current
    DESCRIPTION
        "Cisco Firepower compute:ServerMgmtPolicy:descr
        managed object property"
    ::= { cfprApComputeServerMgmtPolicyEntry 5 }

cfprApComputeServerMgmtPolicyIntId OBJECT-TYPE
    SYNTAX       SnmpAdminString
    MAX-ACCESS   read-only
    STATUS       current
    DESCRIPTION
        "Cisco Firepower compute:ServerMgmtPolicy:intId
        managed object property"
    ::= { cfprApComputeServerMgmtPolicyEntry 6 }

cfprApComputeServerMgmtPolicyName OBJECT-TYPE
    SYNTAX       SnmpAdminString
    MAX-ACCESS   read-only
    STATUS       current
    DESCRIPTION
        "Cisco Firepower compute:ServerMgmtPolicy:name
        managed object property"
    ::= { cfprApComputeServerMgmtPolicyEntry 7 }

cfprApComputeServerMgmtPolicyPolicyLevel OBJECT-TYPE
    SYNTAX       Gauge32
    MAX-ACCESS   read-only
    STATUS       current
    DESCRIPTION
        "Cisco Firepower compute:ServerMgmtPolicy:policyLevel
        managed object property"
    ::= { cfprApComputeServerMgmtPolicyEntry 8 }

cfprApComputeServerMgmtPolicyPolicyOwner OBJECT-TYPE
    SYNTAX       CfprApPolicyPolicyOwner
    MAX-ACCESS   read-only
    STATUS       current
    DESCRIPTION
        "Cisco Firepower compute:ServerMgmtPolicy:policyOwner
        managed object property"
    ::= { cfprApComputeServerMgmtPolicyEntry 9 }

cfprApComputeServerMgmtPolicyQualifier OBJECT-TYPE
    SYNTAX       SnmpAdminString
    MAX-ACCESS   read-only
    STATUS       current
    DESCRIPTION
        "Cisco Firepower compute:ServerMgmtPolicy:qualifier
        managed object property"
    ::= { cfprApComputeServerMgmtPolicyEntry 10 }

cfprApComputeSlotQualTable OBJECT-TYPE
    SYNTAX           SEQUENCE OF CfprApComputeSlotQualEntry
    MAX-ACCESS       not-accessible
    STATUS           current
    DESCRIPTION
        "Cisco Firepower compute:SlotQual managed object table"
    ::= { cfprApComputeObjects 65 }

cfprApComputeSlotQualEntry OBJECT-TYPE
    SYNTAX           CfprApComputeSlotQualEntry
    MAX-ACCESS       not-accessible
    STATUS           current
    DESCRIPTION
        "Entry for the cfprApComputeSlotQualTable table."
    INDEX { cfprApComputeSlotQualInstanceId }
    ::= { cfprApComputeSlotQualTable 1 }

CfprApComputeSlotQualEntry ::= SEQUENCE {
    cfprApComputeSlotQualInstanceId                                  CfprApManagedObjectId,
    cfprApComputeSlotQualDn                                          CfprApManagedObjectDn,
    cfprApComputeSlotQualRn                                          SnmpAdminString,
    cfprApComputeSlotQualMaxId                                       CfprApComputeSlotQualMaxId,
    cfprApComputeSlotQualMinId                                       CfprApComputeSlotQualMinId
}

cfprApComputeSlotQualInstanceId OBJECT-TYPE
    SYNTAX       CfprApManagedObjectId
    MAX-ACCESS   not-accessible
    STATUS       current
    DESCRIPTION
        "Instance identifier of the managed object."
    ::= { cfprApComputeSlotQualEntry 1 }

cfprApComputeSlotQualDn OBJECT-TYPE
    SYNTAX       CfprApManagedObjectDn
    MAX-ACCESS   read-only
    STATUS       current
    DESCRIPTION
        "Cisco Firepower compute:SlotQual:dn managed object property"
    ::= { cfprApComputeSlotQualEntry 2 }

cfprApComputeSlotQualRn OBJECT-TYPE
    SYNTAX       SnmpAdminString
    MAX-ACCESS   read-only
    STATUS       current
    DESCRIPTION
        "Cisco Firepower compute:SlotQual:rn managed object property"
    ::= { cfprApComputeSlotQualEntry 3 }

cfprApComputeSlotQualMaxId OBJECT-TYPE
    SYNTAX       CfprApComputeSlotQualMaxId
    MAX-ACCESS   read-only
    STATUS       current
    DESCRIPTION
        "Cisco Firepower compute:SlotQual:maxId managed object property"
    ::= { cfprApComputeSlotQualEntry 4 }

cfprApComputeSlotQualMinId OBJECT-TYPE
    SYNTAX       CfprApComputeSlotQualMinId
    MAX-ACCESS   read-only
    STATUS       current
    DESCRIPTION
        "Cisco Firepower compute:SlotQual:minId managed object property"
    ::= { cfprApComputeSlotQualEntry 5 }

END
