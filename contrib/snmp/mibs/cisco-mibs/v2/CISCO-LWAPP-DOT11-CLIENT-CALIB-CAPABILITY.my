-- *******************************************************************
-- CISCO-LWAPP-DOT11-CLIENT-CALIB MIB CAPABILITY
--
-- November 18, 2020
--
-- Copyright (c) 2020, 2022 by Cisco Systems, Inc.
-- All rights reserved.
-- *******************************************************************

CISCO-LWAPP-DOT11-CLIENT-CALIB-CAPABILITY DEFINITIONS ::= BEGIN


IMPORTS
       MODULE-IDENTITY
           FROM SNMPv2-SMI
       AGENT-CAPABILITIES
           FROM SNMPv2-CONF
       ciscoAgentCapability
           FROM CISCO-SMI;


ciscoLwappDot11ClientCalibCapability  MODULE-IDENTITY

       LAST-UPDATED         "202011180000Z"
       ORGANIZATION         "Cisco Systems, Inc."
       CONTACT-INFO
               "Cisco Systems
               Customer Service

               Postal: 170 W Tasman Drive
               San Jose, CA  95134
               USA

               Tel: +1 800 553-NETS

               E-mail: cs-wnbu-snmp@cisco.com"

       DESCRIPTION
               "Agent capabilities for
               CISCO-LWAPP-DOT11-CLIENT-CALIB-MIB "
       REVISION      "202011180000Z"
       DESCRIPTION
               "Initial version of this MIB module. "

   ::= { ciscoAgentCapability 1165 }

ciscoLwappDot11ClientCalibCapabilityCEV1R0 AGENT-CAPABILITIES

       PRODUCT-RELEASE "Cisco EWLC 1.0"
       STATUS          current
       DESCRIPTION     "CISCO-LWAPP-DOT11-CLIENT-CALIB--MIB capabilities."

       SUPPORTS        CISCO-LWAPP-DOT11-CLIENT-CALIB-MIB
       INCLUDES        {
                           cLD11ClientCalibTable
                       }

       VARIATION       cLD11ClientCalibEntry
       ACCESS          not-implemented
       DESCRIPTION     "Not supported"

       VARIATION       cLD11ClientCalibMacAddress
       ACCESS          not-implemented
       DESCRIPTION     "Not supported"

       VARIATION       cLD11ClientCalibBeaconInterval
       ACCESS          not-implemented
       DESCRIPTION     "Not supported"

       VARIATION       cLD11ClientCalibRowStatus
       ACCESS          not-implemented
       DESCRIPTION     "Not supported"

       VARIATION       cLD11ClientCalibNumberOfRadios
       ACCESS          not-implemented
       DESCRIPTION     "Not supported"

       VARIATION       cLD11ClientCalibNumberOfSamples
       ACCESS          not-implemented
       DESCRIPTION     "Not supported"

       VARIATION       cLD11ClientCalibSamplesCollected
       ACCESS          not-implemented
       DESCRIPTION     "Not supported"

       VARIATION       cLD11ClientCalibBeaconIntervalExt
       ACCESS          not-implemented
       DESCRIPTION     "Not supported"

       VARIATION       cLD11ClientCalibStorageType
       ACCESS          not-implemented
       DESCRIPTION     "Not supported"

       VARIATION       cLD11ClientCalibTableMaxEntries
       ACCESS          not-implemented
       DESCRIPTION     "Not supported"

   ::= { ciscoLwappDot11ClientCalibCapability 1 }

END
