-- ********************************************************************
-- CISCO-FIREPOWER-AP-NOTIFS-MIB.my
-- 
-- Firepower AP Fault notifications (traps)
--
-- Copyright (c) 2005-2017 Cisco Systems, Inc. All rights reserved.
-- ********************************************************************

CISCO-FIREPOWER-AP-NOTIFS-MIB DEFINITIONS ::= BEGIN

IMPORTS
        MODULE-IDENTITY,
        NOTIFICATION-TYPE
                FROM SNMPv2-SMI
    ciscoMgmt
        FROM CISCO-SMI
    ciscoFirepowerApMIB
        FROM CISCO-FIREPOWER-AP-MIB
    cfprApFaultInstInstanceId,
    cfprApFaultInstDescr,
    cfprApFaultInstAffectedObjectId,
    cfprApFaultInstAffectedObjectDn,
    cfprApFaultInstCreated,
    cfprApFaultInstLastTransition,
    cfprApFaultInstCode,
    cfprApFaultInstType,
    cfprApFaultInstCause,
    cfprApFaultInstSeverity,
    cfprApFaultInstOccur,
    cfprApFaultInstId
        FROM CISCO-FIREPOWER-AP-FAULT-MIB;

ciscoFirepowerApMIBNotifs MODULE-IDENTITY
        LAST-UPDATED  "201703151700Z" 
        ORGANIZATION  "Cisco"
        CONTACT-INFO
            "Cisco Systems
            Customer Service

            Postal: 170 West Tasman Drive
            San Jose, CA  95134
            USA

            Tel: +1 800 553-NETS

            E-mail: savbu-snmp-dev@cisco.com"
      DESCRIPTION
         "Fault traps (notifications) issued by the Firepower system"
      REVISION "201001290000Z" 
      DESCRIPTION
         "Initial version of this MIB module."
   ::= { ciscoFirepowerApMIB 0 }

cfprApFaultActiveNotif NOTIFICATION-TYPE
      OBJECTS  {
                cfprApFaultInstInstanceId,
                cfprApFaultInstDescr,
                cfprApFaultInstAffectedObjectId,
                cfprApFaultInstAffectedObjectDn,
                cfprApFaultInstCreated,
                cfprApFaultInstLastTransition,
                cfprApFaultInstCode,
                cfprApFaultInstType,
                cfprApFaultInstCause,
                cfprApFaultInstSeverity,
                cfprApFaultInstOccur,
                cfprApFaultInstId
               }
      STATUS current
      DESCRIPTION
          "This notification is generated by a Firepower node whenever a fault
          is active and the fault state changes."
      ::= { ciscoFirepowerApMIBNotifs 1 }

cfprApFaultClearNotif NOTIFICATION-TYPE
      OBJECTS  {
                cfprApFaultInstInstanceId,
                cfprApFaultInstDescr,
                cfprApFaultInstAffectedObjectId,
                cfprApFaultInstAffectedObjectDn,
                cfprApFaultInstCreated,
                cfprApFaultInstLastTransition,
                cfprApFaultInstCode,
                cfprApFaultInstType,
                cfprApFaultInstCause,
                cfprApFaultInstSeverity,
                cfprApFaultInstOccur,
                cfprApFaultInstId
               }
      STATUS current
      DESCRIPTION
          "This notification is generated by a Firepower node whenever a fault
          is cleared."
      ::= { ciscoFirepowerApMIBNotifs 2 }

END
