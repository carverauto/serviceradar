--------------------------------------------------------------------
-- CISCO ATM SWITCH ADDRESS MIB
--
-- Jan 1996, Yunsen Wang
--
-- Copyright (c) 1996 by cisco Systems, Inc.
-- All rights reserved.
--------------------------------------------------------------------
--

               CISCO-ATM-SWITCH-ADDR-MIB DEFINITIONS ::= BEGIN

               IMPORTS
                  MODULE-IDENTITY, OBJECT-TYPE, Integer32
                      FROM SNMPv2-SMI
                  TEXTUAL-CONVENTION, RowStatus                                
                      FROM SNMPv2-TC
                  MODULE-COMPLIANCE, OBJECT-GROUP
                      FROM SNMPv2-CONF
		  ciscoMgmt	     FROM CISCO-SMI;


ciscoAtmSwAddrMIB MODULE-IDENTITY
	LAST-UPDATED	"9601100000Z"
	ORGANIZATION	"Cisco Systems, Inc."
	CONTACT-INFO
		"       Cisco Systems
			Customer Service

		Postal: 170 W Tasman Drive
			San Jose, CA  95134
			USA

		   Tel: +1 800 553-NETS

		E-mail: cs-snmp@cisco.com"
	DESCRIPTION
		"ATM Switch address MIB"
	REVISION	"9601100000Z"
	DESCRIPTION
		"Initial version of this MIB module."
	::= { ciscoMgmt 51 } 

	ciscoAtmSwAddrMIBObjects  OBJECT IDENTIFIER ::= { ciscoAtmSwAddrMIB 1 }

	AtmAddr ::= TEXTUAL-CONVENTION
		STATUS  current
		DESCRIPTION
		"The ATM address used by the network entity.  The
		address types are: network prefix (13 octets), and NSAP (20
		octets)."
		SYNTAX    OCTET STRING (SIZE(13|20))


          ciscoAtmSwAddrTable    OBJECT-TYPE
               SYNTAX       SEQUENCE OF CiscoAtmSwAddrEntry
               MAX-ACCESS   not-accessible
               STATUS       current
               DESCRIPTION
                 "This table contains an address list on a per switch
                 basis."
               ::= { ciscoAtmSwAddrMIBObjects 1 }

          ciscoAtmSwAddrEntry    OBJECT-TYPE
               SYNTAX            CiscoAtmSwAddrEntry
               MAX-ACCESS        not-accessible
               STATUS            current
               DESCRIPTION
                 "An entry in the ciscoAtmSwAddrTable."
               INDEX { ciscoAtmSwAddrIndex }
               ::= { ciscoAtmSwAddrTable 1 }

          CiscoAtmSwAddrEntry    ::= SEQUENCE  {
               ciscoAtmSwAddrIndex       Integer32,
               ciscoAtmSwAddrAddress     AtmAddr,                         
               ciscoAtmSwAddrRowStatus   RowStatus
                    }

          ciscoAtmSwAddrIndex   OBJECT-TYPE
               SYNTAX             Integer32 (1..65535)
               MAX-ACCESS         not-accessible
               STATUS             current
               DESCRIPTION
                 "A sequence number when address gets created.
		  1 is the primary address. This is dense table and
		  this index will be re-sequenced when a entry get
		  deleted and it can only create new entry when append
		  in the end of table."
               ::= { ciscoAtmSwAddrEntry 1 }

          ciscoAtmSwAddrAddress   OBJECT-TYPE
               SYNTAX             AtmAddr                                 
               MAX-ACCESS         read-create
               STATUS             current
               DESCRIPTION
                 "A valid address for a given switch."
               ::= { ciscoAtmSwAddrEntry 2 }

          ciscoAtmSwAddrRowStatus OBJECT-TYPE
               SYNTAX             RowStatus
               MAX-ACCESS         read-create
               STATUS             current
               DESCRIPTION
                 "This object is used to create and delete rows in the
                 ciscoAtmSwAddrTable."
               ::= { ciscoAtmSwAddrEntry 3 }



          -- ************************************************

          -- Conformance Information

ciscoAtmSwAddrMIBConformance
              OBJECT IDENTIFIER ::= { ciscoAtmSwAddrMIB 3 }
ciscoAtmSwAddrMIBCompliances
              OBJECT IDENTIFIER ::= { ciscoAtmSwAddrMIBConformance 1 }
ciscoAtmSwAddrMIBGroups
              OBJECT IDENTIFIER ::= { ciscoAtmSwAddrMIBConformance 2 }


          -- Compliance Statements

ciscoAtmSwAddrMIBCompliance MODULE-COMPLIANCE
    STATUS  current
    DESCRIPTION
            "The compliance statement for the Cisco ATM switch address
             group."
    MODULE  -- this module

    ::= { ciscoAtmSwAddrMIBCompliances 1 }



          -- **********************************************

          -- Units of Conformance


ciscoAtmSwAddrMIBGroup  OBJECT-GROUP
    OBJECTS { 
	ciscoAtmSwAddrAddress,
	ciscoAtmSwAddrRowStatus
    }
    STATUS    current
    DESCRIPTION
      ""
    ::= { ciscoAtmSwAddrMIBGroups 1 }




END
