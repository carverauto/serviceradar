-- *****************************************************************
-- CISCO-STP-EXTENSIONS-CAPABILITY.my:
-- Cisco CISCO-STP-EXTENSIONS-MIB AGENT-CAPABILITIES
--   
-- August 2003, Lilian Jiang
--   
-- Copyright (c) 2003-2014 by Cisco Systems, Inc.
-- All rights reserved.
-- *****************************************************************

CISCO-STP-EXTENSIONS-CAPABILITY DEFINITIONS ::= BEGIN

IMPORTS
    MODULE-IDENTITY,
    Unsigned32,
    Integer32
        FROM SNMPv2-SMI
    AGENT-CAPABILITIES
        FROM SNMPv2-CONF
    ciscoAgentCapability
        FROM CISCO-SMI;


ciscoStpExtensionsCapability MODULE-IDENTITY
    LAST-UPDATED    "201403270000Z"
    ORGANIZATION    "Cisco Systems, Inc."
    CONTACT-INFO
            "Cisco Systems
            Customer Service

            Postal: 170 West Tasman Drive
            San Jose, CA  95134
            USA

            Tel: +1 800 553-NETS

            E-mail: cs-lan-switch-snmp@cisco.com"
    DESCRIPTION
        "The capabilities description of
        CISCO-STP-EXTENSIONS-MIB."
    REVISION        "201403270000Z"
    DESCRIPTION
        "Added capability statement cstpxCapNxOSV05R0201PN7k."
    REVISION        "201309300000Z"
    DESCRIPTION
        "Added capability statement cstpxCapV15R0102SYPCat6k and
        cstpxCapV15R0102SYPCat6kSup2T.
        Added VARIATION clause on stpxFastStartPortMode to the following 
        capability statements: 
        cstpxCapCatOSV08R0101
        cstpxCapV12R0113E
        cstpxCapV12R0214SX 
        cstpxCapCatOSV08R0301
        cstpxCapV12R0217bSXACat6k
        cstpxCapCatOSV08R0401
        cstpxCapV12R0218SXEPCat6k
        cstpxCapCatOSV08R0501
        cstpxCapV12R0218SXFPCat6k
        cstpxCapV15R0001SYPCat6kSup2T"
    REVISION        "201109300000Z"
    DESCRIPTION
        "Added capability statement cstpxCapV15R0001SYPCat6kSup2T."
    REVISION        "200702230000Z"
    DESCRIPTION
        "Added VARIATION clause for
        stpxUplinkStationLearningGenRate in agent 
        capability statements of 
        cstpxCapV12R0113E, cstpxCapV12R0214SX,
        cstpxCapV12R0217bSXACat6k, cstpxCapV12R0218SXEPCat6k,
        and cstpxCapV12R0218SXFPCat6k."
    REVISION        "200509150000Z"
    DESCRIPTION
        "Added cstpxCapV12R0218SXFPCat6k for Cisco IOS
        12.2(18)SXF."
    REVISION        "200506150000Z"
    DESCRIPTION
        "Added cstpxCapCatOSV08R0501 for Cisco CatOS
        8.5(1)."
    REVISION        "200411200000Z"
    DESCRIPTION
        "Added cstpxCapV12R0218SXEPCat6k for Cisco IOS
        12.2(18)SXE."
    REVISION        "200406020000Z"
    DESCRIPTION
        "Added cstpxCapCatOSV08R0401 for Cisco CatOS
        8.4(1)."
    REVISION        "200404020000Z"
    DESCRIPTION
        "Added cstpxCapV12R0217bSXACat6k for Cisco IOS
        12.2(17b)SXA."
    REVISION        "200401210000Z"
    DESCRIPTION
        "Added cstpxCapCatOSV08R0301 for Cisco CatOS
        8.3(1)."
    REVISION        "200309100000Z"
    DESCRIPTION
        "Initial version of this MIB module."
    ::= { ciscoAgentCapability 360 }



cstpxCapCatOSV08R0101 AGENT-CAPABILITIES
    PRODUCT-RELEASE "Cisco CatOS 8.1(1)."
    STATUS          current
    DESCRIPTION
        "CISCO-STP-EXTENSIONS-MIB capabilities."

    SUPPORTS        CISCO-STP-EXTENSIONS-MIB
    INCLUDES        {
                        stpxUplinkGroup,
                        stpxPreferredVlansGroup,
                        stpxSstpGroup,
                        stpxNotificationsGroup,
                        stpxBackboneGroup,
                        stpxRootGuardGroup,
                        stpxRootInconsistencyNotificationsGroup,
                        stpx4kVlanGroup,
                        stpxSpanningTreeGroup,
                        stpxMISTPGroup,
                        stpxLongPathCostModeGroup,
                        stpxPVSTVlanGroup,
                        stpxMISTPGroup2,
                        stpxLoopGuardGroup,
                        stpxLoopInconsistencyNotificationsGroup,
                        stpxFastStartGroup,
                        stpxBpduSkewingGroup,
                        stpxFastStartGroup2,
                        stpxLoopGuardGroup2,
                        stpxMSTGroup,
                        stpxPreferredMSTInstancesGroup,
                        stpxFastStartGroup3,
                        stpxUplinkGroup2,
                        stpxBackboneGroup2,
                        stpxMSTGroup2,
                        stpxRSTPGroup,
                        stpxRPVSTGroup
                    }
    VARIATION       stpxFastStartPortMode
    SYNTAX          INTEGER  {
                        enable(1),
                        disable(2),
                        enableForTrunk(3),
                        default(4)
                    }
    DESCRIPTION
        "The enumerated values supported are all those
        defined at the time this clause was written."

    ::= { ciscoStpExtensionsCapability 1 }

cstpxCapV12R0113E AGENT-CAPABILITIES
    PRODUCT-RELEASE "Cisco IOS 12.1(13)E on Catalyst 6000/6500
                        and Cisco 7600 series devices."
    STATUS          current
    DESCRIPTION
        "CISCO-STP-EXTENSIONS-MIB capabilities."

    SUPPORTS        CISCO-STP-EXTENSIONS-MIB
    INCLUDES        {
                        stpxUplinkGroup,
                        stpxSstpGroup,
                        stpxNotificationsGroup,
                        stpxBackboneGroup,
                        stpxRootGuardGroup,
                        stpxRootInconsistencyNotificationsGroup,
                        stpxSpanningTreeGroup,
                        stpxLongPathCostModeGroup,
                        stpxPVSTVlanGroup,
                        stpxLoopGuardGroup,
                        stpxLoopInconsistencyNotificationsGroup,
                        stpxFastStartGroup,
                        stpxFastStartGroup2,
                        stpxLoopGuardGroup2,
                        stpxMSTGroup,
                        stpxFastStartGroup3,
                        stpxUplinkGroup2,
                        stpxBackboneGroup2,
                        stpxMSTGroup2,
                        stpxRSTPGroup,
                        stpxRPVSTGroup
                    }
    VARIATION       stpxUplinkStationLearningGenRate
    SYNTAX          Integer32 (0..3200)
    DESCRIPTION
        "Only limited set of values are supported."

    VARIATION       stpxSpanningTreeType
    SYNTAX          INTEGER  {
                        pvstPlus(1),
                        mst(4),
                        rapidPvstPlus(5)
                    }
    DESCRIPTION
        "Only limited set of enumerated values are
        supported."

    VARIATION       stpxMSTRegionEditBufferStatus
    SYNTAX          INTEGER  {
                        released(1),
                        acquiredBySnmp(2)
                    }
    DESCRIPTION
        "Only limited set of enumerated values are
        supported."

    VARIATION       stpxMSTRegionEditBufferOperation
    SYNTAX          INTEGER  {
                        other(1),
                        acquire(2),
                        commit(4),
                        rollBack(5)
                    }
    DESCRIPTION
        "Only limited set of enumerated values are
        supported."

    VARIATION       stpxFastStartPortMode
    SYNTAX          INTEGER  {
                        enable(1),
                        disable(2),
                        enableForTrunk(3),
                        default(4)
                    }
    DESCRIPTION
        "The enumerated values supported are all those
        defined at the time this clause was written."

    ::= { ciscoStpExtensionsCapability 2 }

cstpxCapV12R0214SX AGENT-CAPABILITIES
    PRODUCT-RELEASE "Cisco IOS 12.2(14)SX on Catalyst 6000/6500
                        and Cisco 7600 series devices."
    STATUS          current
    DESCRIPTION
        "CISCO-STP-EXTENSIONS-MIB capabilities."

    SUPPORTS        CISCO-STP-EXTENSIONS-MIB
    INCLUDES        {
                        stpxUplinkGroup,
                        stpxSstpGroup,
                        stpxNotificationsGroup,
                        stpxBackboneGroup,
                        stpxRootGuardGroup,
                        stpxRootInconsistencyNotificationsGroup,
                        stpxSpanningTreeGroup,
                        stpxLongPathCostModeGroup,
                        stpxPVSTVlanGroup,
                        stpxLoopGuardGroup,
                        stpxLoopInconsistencyNotificationsGroup,
                        stpxFastStartGroup,
                        stpxFastStartGroup2,
                        stpxLoopGuardGroup2,
                        stpxMSTGroup,
                        stpxFastStartGroup3,
                        stpxUplinkGroup2,
                        stpxBackboneGroup2,
                        stpxMSTGroup2,
                        stpxRSTPGroup,
                        stpxRPVSTGroup
                    }
    VARIATION       stpxUplinkStationLearningGenRate
    SYNTAX          Integer32 (0..3200)
    DESCRIPTION
        "Only limited set of values are supported."

    VARIATION       stpxSpanningTreeType
    SYNTAX          INTEGER  {
                        pvstPlus(1),
                        mst(4),
                        rapidPvstPlus(5)
                    }
    DESCRIPTION
        "Only limited set of enumerated values are
        supported."

    VARIATION       stpxMSTRegionEditBufferStatus
    SYNTAX          INTEGER  {
                        released(1),
                        acquiredBySnmp(2)
                    }
    DESCRIPTION
        "Only limited set of enumerated values are
        supported."

    VARIATION       stpxMSTRegionEditBufferOperation
    SYNTAX          INTEGER  {
                        other(1),
                        acquire(2),
                        commit(4),
                        rollBack(5)
                    }
    DESCRIPTION
        "Only limited set of enumerated values are
        supported."

    VARIATION       stpxFastStartPortMode
    SYNTAX          INTEGER  {
                        enable(1),
                        disable(2),
                        enableForTrunk(3),
                        default(4)
                    }
    DESCRIPTION
        "The enumerated values supported are all those
        defined at the time this clause was written."

    ::= { ciscoStpExtensionsCapability 3 }

cstpxCapCatOSV08R0301 AGENT-CAPABILITIES
    PRODUCT-RELEASE "Cisco CatOS 8.3(1) on Catalyst 6000/6500
                        and Cisco 7600 series devices."
    STATUS          current
    DESCRIPTION
        "CISCO-STP-EXTENSIONS-MIB capabilities."

    SUPPORTS        CISCO-STP-EXTENSIONS-MIB
    INCLUDES        {
                        stpxUplinkGroup,
                        stpxPreferredVlansGroup,
                        stpxSstpGroup,
                        stpxNotificationsGroup,
                        stpxBackboneGroup,
                        stpxRootGuardGroup,
                        stpxRootInconsistencyNotificationsGroup,
                        stpx4kVlanGroup,
                        stpxSpanningTreeGroup,
                        stpxMISTPGroup,
                        stpxLongPathCostModeGroup,
                        stpxPVSTVlanGroup,
                        stpxMISTPGroup2,
                        stpxLoopGuardGroup,
                        stpxLoopInconsistencyNotificationsGroup,
                        stpxFastStartGroup,
                        stpxBpduSkewingGroup,
                        stpxFastStartGroup2,
                        stpxLoopGuardGroup2,
                        stpxMSTGroup,
                        stpxFastStartGroup3,
                        stpxUplinkGroup2,
                        stpxBackboneGroup2,
                        stpxMSTGroup2,
                        stpxRSTPGroup,
                        stpxRPVSTGroup,
                        stpxExtendedSysIDGroup,
                        stpxNotificationEnableGroup,
                        stpxFastStartOperModeGroup,
                        stpxMSTGroup3,
                        stpxSMSTGroup,
                        stpxSMSTInstanceGroup,
                        stpxSMSTInstanceEditGroup,
                        stpxSMSTPortStatusGroup,
                        stpxSMSTPortHelloTimeGroup
                    }
    VARIATION       stpxSMSTRegionEditRevision
    SYNTAX          Unsigned32 (0..65535)
    DESCRIPTION
        "Only support the revision range from 0 to
        65535."

    VARIATION       stpxSMSTPortAdminHelloTime
    SYNTAX          Unsigned32 (0 | 100..1000)
    DESCRIPTION
        "Only support the value of 0 and the range
        from 100 to 1000."

    VARIATION       stpxNotificationEnable
    SYNTAX          BITS {
                        newRoot(0),
                        topologyChange(1)
                    }
    DESCRIPTION
        "Only limited set of enumerated values
        are supported."

    VARIATION       stpxFastStartPortMode
    SYNTAX          INTEGER  {
                        enable(1),
                        disable(2),
                        enableForTrunk(3),
                        default(4)
                    }
    DESCRIPTION
        "The enumerated values supported are all those
        defined at the time this clause was written."

    ::= { ciscoStpExtensionsCapability 4 }

cstpxCapV12R0217bSXACat6k AGENT-CAPABILITIES
    PRODUCT-RELEASE "Cisco IOS 12.2(17b)SXA on Catalyst 6000/6500
                        and Cisco 7600 series devices."
    STATUS          current
    DESCRIPTION
        "CISCO-STP-EXTENSIONS-MIB capabilities."

    SUPPORTS        CISCO-STP-EXTENSIONS-MIB
    INCLUDES        {
                        stpxUplinkGroup,
                        stpxSstpGroup,
                        stpxNotificationsGroup,
                        stpxBackboneGroup,
                        stpxRootGuardGroup,
                        stpxRootInconsistencyNotificationsGroup,
                        stpxSpanningTreeGroup,
                        stpxLongPathCostModeGroup,
                        stpxPVSTVlanGroup,
                        stpxLoopGuardGroup,
                        stpxLoopInconsistencyNotificationsGroup,
                        stpxFastStartGroup,
                        stpxFastStartGroup2,
                        stpxLoopGuardGroup2,
                        stpxMSTGroup,
                        stpxFastStartGroup3,
                        stpxUplinkGroup2,
                        stpxBackboneGroup2,
                        stpxMSTGroup2,
                        stpxRSTPGroup,
                        stpxRPVSTGroup,
                        stpxExtendedSysIDGroup,
                        stpxNotificationEnableGroup,
                        stpxFastStartOperModeGroup
                    }
    VARIATION       stpxUplinkStationLearningGenRate
    SYNTAX          Integer32 (0..3200)
    DESCRIPTION
        "Only limited set of values are supported."

    VARIATION       stpxSpanningTreeType
    SYNTAX          INTEGER  {
                        pvstPlus(1),
                        mst(4),
                        rapidPvstPlus(5)
                    }
    DESCRIPTION
        "Only limited set of enumerated values are
        supported."

    VARIATION       stpxMSTRegionEditBufferStatus
    SYNTAX          INTEGER  {
                        released(1),
                        acquiredBySnmp(2)
                    }
    DESCRIPTION
        "Only limited set of enumerated values are
        supported."

    VARIATION       stpxMSTRegionEditBufferOperation
    SYNTAX          INTEGER  {
                        other(1),
                        acquire(2),
                        commit(4),
                        rollBack(5)
                    }
    DESCRIPTION
        "Only limited set of enumerated values are
        supported."

    VARIATION       stpxNotificationEnable
    SYNTAX          BITS {
                        newRoot(0),
                        topologyChange(1)
                    }
    DESCRIPTION
        "Only limited set of enumerated values
        are supported."

    VARIATION       stpxFastStartPortMode
    SYNTAX          INTEGER  {
                        enable(1),
                        disable(2),
                        enableForTrunk(3),
                        default(4)
                    }
    DESCRIPTION
        "The enumerated values supported are all those
        defined at the time this clause was written."

    ::= { ciscoStpExtensionsCapability 5 }

cstpxCapCatOSV08R0401 AGENT-CAPABILITIES
    PRODUCT-RELEASE "Cisco CatOS 8.4(1) on Catalyst 6000/6500
                        and Cisco 7600 series devices."
    STATUS          current
    DESCRIPTION
        "CISCO-STP-EXTENSIONS-MIB capabilities."

    SUPPORTS        CISCO-STP-EXTENSIONS-MIB
    INCLUDES        {
                        stpxUplinkGroup,
                        stpxPreferredVlansGroup,
                        stpxSstpGroup,
                        stpxNotificationsGroup,
                        stpxBackboneGroup,
                        stpxRootGuardGroup,
                        stpxRootInconsistencyNotificationsGroup,
                        stpx4kVlanGroup,
                        stpxSpanningTreeGroup,
                        stpxMISTPGroup,
                        stpxLongPathCostModeGroup,
                        stpxPVSTVlanGroup,
                        stpxMISTPGroup2,
                        stpxLoopGuardGroup,
                        stpxLoopInconsistencyNotificationsGroup,
                        stpxFastStartGroup,
                        stpxBpduSkewingGroup,
                        stpxFastStartGroup2,
                        stpxLoopGuardGroup2,
                        stpxMSTGroup,
                        stpxFastStartGroup3,
                        stpxUplinkGroup2,
                        stpxBackboneGroup2,
                        stpxMSTGroup2,
                        stpxRSTPGroup,
                        stpxRPVSTGroup,
                        stpxExtendedSysIDGroup,
                        stpxNotificationEnableGroup,
                        stpxFastStartOperModeGroup,
                        stpxMSTGroup3,
                        stpxSMSTGroup,
                        stpxSMSTInstanceGroup,
                        stpxSMSTInstanceEditGroup,
                        stpxSMSTPortStatusGroup,
                        stpxSMSTPortHelloTimeGroup,
                        stpxSMSTInstanceCISTGroup
                    }
    VARIATION       stpxSMSTRegionEditRevision
    SYNTAX          Unsigned32 (0..65535)
    DESCRIPTION
        "Only a limited set of values is supported."

    VARIATION       stpxSMSTPortAdminHelloTime
    SYNTAX          Unsigned32 (0 | 100..1000)
    DESCRIPTION
        "Only a limited set of values is supported."

    VARIATION       stpxNotificationEnable
    SYNTAX          BITS {
                        newRoot(0),
                        topologyChange(1),
                        inconsistency(2),
                        rootInconsistency(3),
                        loopInconsistency(4)
                    }
    DESCRIPTION
        "The enumerated values supported are all those
        defined at the time this clause was written."

    VARIATION       stpxFastStartPortMode
    SYNTAX          INTEGER  {
                        enable(1),
                        disable(2),
                        enableForTrunk(3),
                        default(4)
                    }
    DESCRIPTION
        "The enumerated values supported are all those
        defined at the time this clause was written."

    ::= { ciscoStpExtensionsCapability 6 }

cstpxCapV12R0218SXEPCat6k AGENT-CAPABILITIES
    PRODUCT-RELEASE "Cisco IOS 12.2(18)SXE on Catalyst 6000/6500
                        and Cisco 7600 series devices."
    STATUS          current
    DESCRIPTION
        "CISCO-STP-EXTENSIONS-MIB capabilities."

    SUPPORTS        CISCO-STP-EXTENSIONS-MIB
    INCLUDES        {
                        stpxUplinkGroup,
                        stpxSstpGroup,
                        stpxNotificationsGroup,
                        stpxBackboneGroup,
                        stpxRootGuardGroup,
                        stpxRootInconsistencyNotificationsGroup,
                        stpxSpanningTreeGroup,
                        stpxLongPathCostModeGroup,
                        stpxPVSTVlanGroup,
                        stpxLoopGuardGroup,
                        stpxLoopInconsistencyNotificationsGroup,
                        stpxFastStartGroup,
                        stpxFastStartGroup2,
                        stpxLoopGuardGroup2,
                        stpxMSTGroup,
                        stpxFastStartGroup3,
                        stpxUplinkGroup2,
                        stpxBackboneGroup2,
                        stpxMSTGroup2,
                        stpxRSTPGroup,
                        stpxRPVSTGroup,
                        stpxExtendedSysIDGroup,
                        stpxNotificationEnableGroup,
                        stpxFastStartOperModeGroup,
                        stpxPathCostOperModeGroup
                    }
    VARIATION       stpxUplinkStationLearningGenRate
    SYNTAX          Integer32 (0..3200)
    DESCRIPTION
        "Only limited set of values are supported."

    VARIATION       stpxSpanningTreeType
    SYNTAX          INTEGER  {
                        pvstPlus(1),
                        mst(4),
                        rapidPvstPlus(5)
                    }
    DESCRIPTION
        "Only limited set of enumerated values are
        supported."

    VARIATION       stpxMSTRegionEditBufferStatus
    SYNTAX          INTEGER  {
                        released(1),
                        acquiredBySnmp(2)
                    }
    DESCRIPTION
        "Only limited set of enumerated values are
        supported."

    VARIATION       stpxMSTRegionEditBufferOperation
    SYNTAX          INTEGER  {
                        other(1),
                        acquire(2),
                        commit(4),
                        rollBack(5)
                    }
    DESCRIPTION
        "Only limited set of enumerated values are
        supported."

    VARIATION       stpxNotificationEnable
    SYNTAX          BITS {
                        newRoot(0),
                        topologyChange(1),
                        inconsistency(2),
                        rootInconsistency(3),
                        loopInconsistency(4)
                    }
    DESCRIPTION
        "The enumerated values supported are all those
        defined at the time this clause was written."

    VARIATION       stpxFastStartPortMode
    SYNTAX          INTEGER  {
                        enable(1),
                        disable(2),
                        enableForTrunk(3),
                        default(4)
                    }
    DESCRIPTION
        "The enumerated values supported are all those
        defined at the time this clause was written."

    ::= { ciscoStpExtensionsCapability 7 }

cstpxCapCatOSV08R0501 AGENT-CAPABILITIES
    PRODUCT-RELEASE "Cisco CatOS 8.5(1)."
    STATUS          current
    DESCRIPTION
        "CISCO-STP-EXTENSIONS-MIB capabilities."

    SUPPORTS        CISCO-STP-EXTENSIONS-MIB
    INCLUDES        {
                        stpxUplinkGroup,
                        stpxPreferredVlansGroup,
                        stpxSstpGroup,
                        stpxNotificationsGroup,
                        stpxBackboneGroup,
                        stpxRootGuardGroup,
                        stpxRootInconsistencyNotificationsGroup,
                        stpx4kVlanGroup,
                        stpxSpanningTreeGroup,
                        stpxMISTPGroup,
                        stpxLongPathCostModeGroup,
                        stpxPVSTVlanGroup,
                        stpxMISTPGroup2,
                        stpxLoopGuardGroup,
                        stpxLoopInconsistencyNotificationsGroup,
                        stpxFastStartGroup,
                        stpxBpduSkewingGroup,
                        stpxFastStartGroup2,
                        stpxLoopGuardGroup2,
                        stpxMSTGroup,
                        stpxFastStartGroup3,
                        stpxUplinkGroup2,
                        stpxBackboneGroup2,
                        stpxMSTGroup2,
                        stpxRSTPGroup,
                        stpxRPVSTGroup,
                        stpxExtendedSysIDGroup,
                        stpxNotificationEnableGroup,
                        stpxFastStartOperModeGroup,
                        stpxMSTGroup3,
                        stpxSMSTGroup,
                        stpxSMSTInstanceGroup,
                        stpxSMSTInstanceEditGroup,
                        stpxSMSTPortStatusGroup,
                        stpxSMSTPortHelloTimeGroup,
                        stpxSMSTInstanceCISTGroup,
                        stpxPathCostOperModeGroup,
                        stpxRSTPTransmitHoldCountGroup,
                        stpxSMSTPortMSTModeGroup,
                        stpxSMSTMaxHopCountGroup,
                        stpxSMSTConfigDigestGroup,
                        stpxMSTGroup4
                    }
    VARIATION       stpxSMSTRegionEditRevision
    SYNTAX          Unsigned32 (0..65535)
    DESCRIPTION
        "Only a limited set of values are supported."

    VARIATION       stpxSMSTPortAdminHelloTime
    SYNTAX          Unsigned32 (0 | 100..1000)
    DESCRIPTION
        "Only a limited set of values are supported."

    VARIATION       stpxNotificationEnable
    SYNTAX          BITS {
                        newRoot(0),
                        topologyChange(1),
                        inconsistency(2),
                        rootInconsistency(3),
                        loopInconsistency(4)
                    }
    DESCRIPTION
        "The enumerated values supported are all those
        defined at the time this clause was written."

    VARIATION       stpxRSTPTransmitHoldCount
    SYNTAX          Unsigned32 (1..10)
    DESCRIPTION
        "Only limited set of values are supported."

    VARIATION       stpxSMSTPortAdminMSTMode
    SYNTAX          INTEGER  {
                        preStandard(1),
                        auto(2)
                    }
    DESCRIPTION
        "The enumerated values supported are all those
        defined at the time this clause was written."

    VARIATION       stpxSMSTMaxHopCount
    SYNTAX          Unsigned32 (1..40)
    DESCRIPTION
        "Only limited set of values are supported."

    VARIATION       stpxFastStartPortMode
    SYNTAX          INTEGER  {
                        enable(1),
                        disable(2),
                        enableForTrunk(3),
                        default(4)
                    }
    DESCRIPTION
        "The enumerated values supported are all those
        defined at the time this clause was written."

    ::= { ciscoStpExtensionsCapability 8 }

cstpxCapV12R0218SXFPCat6k AGENT-CAPABILITIES
    PRODUCT-RELEASE "Cisco IOS 12.2(18)SXF on Catalyst 6000/6500
                    and Cisco 7600 series devices."
    STATUS          current
    DESCRIPTION
        "CISCO-STP-EXTENSIONS-MIB capabilities."

    SUPPORTS        CISCO-STP-EXTENSIONS-MIB
    INCLUDES        {
                        stpxUplinkGroup,
                        stpxSstpGroup,
                        stpxNotificationsGroup,
                        stpxBackboneGroup,
                        stpxRootGuardGroup,
                        stpxRootInconsistencyNotificationsGroup,
                        stpxSpanningTreeGroup,
                        stpxLongPathCostModeGroup,
                        stpxPVSTVlanGroup,
                        stpxLoopGuardGroup,
                        stpxLoopInconsistencyNotificationsGroup,
                        stpxFastStartGroup,
                        stpxFastStartGroup2,
                        stpxLoopGuardGroup2,
                        stpxMSTGroup,
                        stpxFastStartGroup3,
                        stpxUplinkGroup2,
                        stpxBackboneGroup2,
                        stpxMSTGroup2,
                        stpxRSTPGroup,
                        stpxRPVSTGroup,
                        stpxExtendedSysIDGroup,
                        stpxNotificationEnableGroup,
                        stpxFastStartOperModeGroup,
                        stpxPathCostOperModeGroup,
                        stpxSMSTGroup,
                        stpxSMSTInstanceGroup,
                        stpxSMSTInstanceEditGroup,
                        stpxSMSTPortStatusGroup,
                        stpxSMSTInstanceCISTGroup,
                        stpxRSTPTransmitHoldCountGroup,
                        stpxSMSTPortMSTModeGroup,
                        stpxSMSTMaxHopCountGroup,
                        stpxSMSTConfigDigestGroup,
                        stpxMSTGroup4
                    }
    VARIATION       stpxUplinkStationLearningGenRate
    SYNTAX          Integer32 (0..3200)
    DESCRIPTION
        "Only limited set of values are supported."

    VARIATION       stpxSpanningTreeType
    SYNTAX          INTEGER  {
                        pvstPlus(1),
                        mst(4),
                        rapidPvstPlus(5)
                    }
    DESCRIPTION
        "Only limited set of enumerated values are
        supported."

    VARIATION       stpxMSTRegionEditBufferStatus
    SYNTAX          INTEGER  {
                        released(1),
                        acquiredBySnmp(2)
                    }
    DESCRIPTION
        "Only limited set of enumerated values are
        supported."

    VARIATION       stpxMSTRegionEditBufferOperation
    SYNTAX          INTEGER  {
                        other(1),
                        acquire(2),
                        commit(4),
                        rollBack(5)
                    }
    DESCRIPTION
        "Only limited set of enumerated values are
        supported."

    VARIATION       stpxNotificationEnable
    SYNTAX          BITS {
                        newRoot(0),
                        topologyChange(1),
                        inconsistency(2),
                        rootInconsistency(3),
                        loopInconsistency(4)
                    }
    DESCRIPTION
        "The enumerated values supported are all those
        defined at the time this clause was written."

    VARIATION       stpxRSTPTransmitHoldCount
    SYNTAX          Unsigned32 (1..20)
    DESCRIPTION
        "Only limited set of values are supported."

    VARIATION       stpxSMSTRegionEditRevision
    SYNTAX          Unsigned32 (0..65535)
    DESCRIPTION
        "Only limited set of values are supported."

    VARIATION       stpxSMSTPortAdminMSTMode
    SYNTAX          INTEGER  {
                        preStandard(1),
                        auto(2)
                    }
    DESCRIPTION
        "The enumerated values supported are all those
        defined at the time this clause was written."

    VARIATION       stpxSMSTMaxHopCount
    SYNTAX          Unsigned32 (1..255)
    DESCRIPTION
        "Only limited set of values are supported."

    VARIATION       stpxFastStartPortMode
    SYNTAX          INTEGER  {
                        enable(1),
                        disable(2),
                        enableForTrunk(3),
                        default(4)
                    }
    DESCRIPTION
        "The enumerated values supported are all those
        defined at the time this clause was written."

    ::= { ciscoStpExtensionsCapability 9 }

cstpxCapV15R0001SYPCat6kSup2T AGENT-CAPABILITIES
    PRODUCT-RELEASE "Cisco IOS 15.0(1)SY on Catalyst 6000/6500
                    series devices with Supervisor 2T present."
    STATUS          current
    DESCRIPTION
        "CISCO-STP-EXTENSIONS-MIB capabilities."

    SUPPORTS        CISCO-STP-EXTENSIONS-MIB
    INCLUDES        {
                        stpxUplinkGroup,
                        stpxSstpGroup,
                        stpxNotificationsGroup,
                        stpxBackboneGroup,
                        stpxRootGuardGroup,
                        stpxRootInconsistencyNotificationsGroup,
                        stpxSpanningTreeGroup,
                        stpxLongPathCostModeGroup,
                        stpxPVSTVlanGroup,
                        stpxLoopGuardGroup,
                        stpxLoopInconsistencyNotificationsGroup,
                        stpxFastStartGroup,
                        stpxFastStartGroup2,
                        stpxLoopGuardGroup2,
                        stpxMSTGroup,
                        stpxFastStartGroup3,
                        stpxUplinkGroup2,
                        stpxBackboneGroup2,
                        stpxMSTGroup2,
                        stpxRSTPGroup,
                        stpxRPVSTGroup,
                        stpxExtendedSysIDGroup,
                        stpxNotificationEnableGroup,
                        stpxFastStartOperModeGroup,
                        stpxPathCostOperModeGroup,
                        stpxSMSTGroup,
                        stpxSMSTInstanceGroup,
                        stpxSMSTInstanceEditGroup,
                        stpxSMSTPortStatusGroup,
                        stpxSMSTInstanceCISTGroup,
                        stpxRSTPTransmitHoldCountGroup,
                        stpxSMSTPortMSTModeGroup,
                        stpxSMSTMaxHopCountGroup,
                        stpxSMSTConfigDigestGroup,
                        stpxMSTGroup4
                    }
    VARIATION       stpxUplinkStationLearningGenRate
    SYNTAX          Integer32 (0..3200)
    DESCRIPTION
        "Only limited set of values are supported."

    VARIATION       stpxSpanningTreeType
    SYNTAX          INTEGER  {
                        mst(4),
                        rapidPvstPlus(5)
                    }
    DESCRIPTION
        "Only limited set of enumerated values are
        supported."

    VARIATION       stpxMSTRegionEditBufferStatus
    SYNTAX          INTEGER  {
                        released(1),
                        acquiredBySnmp(2)
                    }
    DESCRIPTION
        "Only limited set of enumerated values are
        supported."

    VARIATION       stpxMSTRegionEditBufferOperation
    SYNTAX          INTEGER  {
                        other(1),
                        acquire(2),
                        commit(4),
                        rollBack(5)
                    }
    DESCRIPTION
        "Only limited set of enumerated values are
        supported."

    VARIATION       stpxNotificationEnable
    SYNTAX          BITS {
                        newRoot(0),
                        topologyChange(1),
                        inconsistency(2),
                        rootInconsistency(3),
                        loopInconsistency(4)
                    }
    DESCRIPTION
        "The enumerated values supported are all those
        defined at the time this clause was written."

    VARIATION       stpxRSTPTransmitHoldCount
    SYNTAX          Unsigned32 (1..20)
    DESCRIPTION
        "Only limited set of values are supported."

    VARIATION       stpxSMSTRegionEditRevision
    SYNTAX          Unsigned32 (0..65535)
    DESCRIPTION
        "Only limited set of values are supported."

    VARIATION       stpxSMSTPortAdminMSTMode
    SYNTAX          INTEGER  {
                        preStandard(1),
                        auto(2)
                    }
    DESCRIPTION
        "The enumerated values supported are all those
        defined at the time this clause was written."

    VARIATION       stpxSMSTMaxHopCount
    SYNTAX          Unsigned32 (1..255)
    DESCRIPTION
        "Only limited set of values are supported."

    VARIATION       stpxFastStartPortMode
    SYNTAX          INTEGER  {
                        enable(1),
                        disable(2),
                        enableForTrunk(3),
                        default(4)
                    }
    DESCRIPTION
        "The enumerated values supported are all those
        defined at the time this clause was written."

    ::= { ciscoStpExtensionsCapability 10 }

cstpxCapV15R0102SYPCat6k AGENT-CAPABILITIES
    PRODUCT-RELEASE "Cisco IOS 15.1(2)SY on Catalyst 6000/6500 series devices."
    STATUS          current
    DESCRIPTION
        "CISCO-STP-EXTENSIONS-MIB capabilities."

    SUPPORTS        CISCO-STP-EXTENSIONS-MIB
    INCLUDES        {
                        stpxUplinkGroup,
                        stpxSstpGroup,
                        stpxNotificationsGroup,
                        stpxBackboneGroup,
                        stpxRootGuardGroup,
                        stpxRootInconsistencyNotificationsGroup,
                        stpxSpanningTreeGroup,
                        stpxLongPathCostModeGroup,
                        stpxPVSTVlanGroup,
                        stpxLoopGuardGroup,
                        stpxLoopInconsistencyNotificationsGroup,
                        stpxFastStartGroup,
                        stpxFastStartGroup2,
                        stpxLoopGuardGroup2,
                        stpxMSTGroup,
                        stpxFastStartGroup3,
                        stpxUplinkGroup2,
                        stpxBackboneGroup2,
                        stpxMSTGroup2,
                        stpxRSTPGroup,
                        stpxRPVSTGroup,
                        stpxExtendedSysIDGroup,
                        stpxNotificationEnableGroup,
                        stpxFastStartOperModeGroup,
                        stpxPathCostOperModeGroup,
                        stpxSMSTGroup,
                        stpxSMSTInstanceGroup,
                        stpxSMSTInstanceEditGroup,
                        stpxSMSTPortStatusGroup,
                        stpxSMSTInstanceCISTGroup,
                        stpxRSTPTransmitHoldCountGroup,
                        stpxSMSTPortMSTModeGroup,
                        stpxSMSTMaxHopCountGroup,
                        stpxSMSTConfigDigestGroup,
                        stpxMSTGroup4
                    }
    VARIATION       stpxUplinkStationLearningGenRate
    SYNTAX          Integer32 (0..3200)
    DESCRIPTION
        "Only limited set of values are supported."

    VARIATION       stpxSpanningTreeType
    SYNTAX          INTEGER  {
                        pvstPlus(1),
                        mst(4),
                        rapidPvstPlus(5)
                    }
    DESCRIPTION
        "Only limited set of enumerated values are
        supported."

    VARIATION       stpxMSTRegionEditBufferStatus
    SYNTAX          INTEGER  {
                        released(1),
                        acquiredBySnmp(2)
                    }
    DESCRIPTION
        "Only limited set of enumerated values are
        supported."

    VARIATION       stpxMSTRegionEditBufferOperation
    SYNTAX          INTEGER  {
                        other(1),
                        acquire(2),
                        commit(4),
                        rollBack(5)
                    }
    DESCRIPTION
        "Only limited set of enumerated values are
        supported."

    VARIATION       stpxNotificationEnable
    SYNTAX          BITS {
                        newRoot(0),
                        topologyChange(1),
                        inconsistency(2),
                        rootInconsistency(3),
                        loopInconsistency(4)
                    }
    DESCRIPTION
        "The enumerated values supported are all those
        defined at the time this clause was written."

    VARIATION       stpxRSTPTransmitHoldCount
    SYNTAX          Unsigned32 (1..20)
    DESCRIPTION
        "Only limited set of values are supported."

    VARIATION       stpxSMSTRegionEditRevision
    SYNTAX          Unsigned32 (0..65535)
    DESCRIPTION
        "Only limited set of values are supported."

    VARIATION       stpxSMSTPortAdminMSTMode
    SYNTAX          INTEGER  {
                        preStandard(1),
                        auto(2)
                    }
    DESCRIPTION
        "The enumerated values supported are all those
        defined at the time this clause was written."

    VARIATION       stpxSMSTMaxHopCount
    SYNTAX          Unsigned32 (1..255)
    DESCRIPTION
        "Only limited set of values are supported."

    VARIATION       stpxFastStartPortMode
    SYNTAX          INTEGER  {
                        enable(1),
                        disable(2),
                        enableForTrunk(3),
                        default(4),
                        network(5)
                    }
    DESCRIPTION
        "The enumerated values supported are all those
        defined at the time this clause was written."

    ::= { ciscoStpExtensionsCapability 11 }

cstpxCapV15R0102SYPCat6kSup2T AGENT-CAPABILITIES
    PRODUCT-RELEASE "Cisco IOS 15.1(2)SY on Catalyst 6000/6500
                    series devices with Supervisor 2T present."
    STATUS          current
    DESCRIPTION
        "CISCO-STP-EXTENSIONS-MIB capabilities."

    SUPPORTS        CISCO-STP-EXTENSIONS-MIB
    INCLUDES        {
                        stpxUplinkGroup,
                        stpxSstpGroup,
                        stpxNotificationsGroup,
                        stpxBackboneGroup,
                        stpxRootGuardGroup,
                        stpxRootInconsistencyNotificationsGroup,
                        stpxSpanningTreeGroup,
                        stpxLongPathCostModeGroup,
                        stpxPVSTVlanGroup,
                        stpxLoopGuardGroup,
                        stpxLoopInconsistencyNotificationsGroup,
                        stpxFastStartGroup,
                        stpxFastStartGroup2,
                        stpxLoopGuardGroup2,
                        stpxMSTGroup,
                        stpxFastStartGroup3,
                        stpxUplinkGroup2,
                        stpxBackboneGroup2,
                        stpxMSTGroup2,
                        stpxRSTPGroup,
                        stpxRPVSTGroup,
                        stpxExtendedSysIDGroup,
                        stpxNotificationEnableGroup,
                        stpxFastStartOperModeGroup,
                        stpxPathCostOperModeGroup,
                        stpxSMSTGroup,
                        stpxSMSTInstanceGroup,
                        stpxSMSTInstanceEditGroup,
                        stpxSMSTPortStatusGroup,
                        stpxSMSTInstanceCISTGroup,
                        stpxRSTPTransmitHoldCountGroup,
                        stpxSMSTPortMSTModeGroup,
                        stpxSMSTMaxHopCountGroup,
                        stpxSMSTConfigDigestGroup,
                        stpxMSTGroup4
                    }
    VARIATION       stpxUplinkStationLearningGenRate
    SYNTAX          Integer32 (0..3200)
    DESCRIPTION
        "Only limited set of values are supported."

    VARIATION       stpxSpanningTreeType
    SYNTAX          INTEGER  {
                        mst(4),
                        rapidPvstPlus(5)
                    }
    DESCRIPTION
        "Only limited set of enumerated values are
        supported."

    VARIATION       stpxMSTRegionEditBufferStatus
    SYNTAX          INTEGER  {
                        released(1),
                        acquiredBySnmp(2)
                    }
    DESCRIPTION
        "Only limited set of enumerated values are
        supported."

    VARIATION       stpxMSTRegionEditBufferOperation
    SYNTAX          INTEGER  {
                        other(1),
                        acquire(2),
                        commit(4),
                        rollBack(5)
                    }
    DESCRIPTION
        "Only limited set of enumerated values are
        supported."

    VARIATION       stpxNotificationEnable
    SYNTAX          BITS {
                        newRoot(0),
                        topologyChange(1),
                        inconsistency(2),
                        rootInconsistency(3),
                        loopInconsistency(4)
                    }
    DESCRIPTION
        "The enumerated values supported are all those
        defined at the time this clause was written."

    VARIATION       stpxRSTPTransmitHoldCount
    SYNTAX          Unsigned32 (1..20)
    DESCRIPTION
        "Only limited set of values are supported."

    VARIATION       stpxSMSTRegionEditRevision
    SYNTAX          Unsigned32 (0..65535)
    DESCRIPTION
        "Only limited set of values are supported."

    VARIATION       stpxSMSTPortAdminMSTMode
    SYNTAX          INTEGER  {
                        preStandard(1),
                        auto(2)
                    }
    DESCRIPTION
        "The enumerated values supported are all those
        defined at the time this clause was written."

    VARIATION       stpxSMSTMaxHopCount
    SYNTAX          Unsigned32 (1..255)
    DESCRIPTION
        "Only limited set of values are supported."

    VARIATION       stpxFastStartPortMode
    SYNTAX          INTEGER  {
                        enable(1),
                        disable(2),
                        enableForTrunk(3),
                        default(4),
                        network(5)
                    }
    DESCRIPTION
        "The enumerated values supported are all those
        defined at the time this clause was written."

    ::= { ciscoStpExtensionsCapability 12 }

cstpxCapNxOSV05R0201PN7k AGENT-CAPABILITIES
    PRODUCT-RELEASE "Cisco NX-OS 5.2(1) on Nexus 7000
                    series devices."
    STATUS          current
    DESCRIPTION
        "CISCO-STP-EXTENSIONS-MIB capabilities."

    SUPPORTS        CISCO-STP-EXTENSIONS-MIB
    INCLUDES        {
                        stpxSstpGroup,
                        stpxNotificationsGroup,
                        stpxRootGuardGroup,
                        stpxRootInconsistencyNotificationsGroup,
                        stpxSpanningTreeGroup,
                        stpxLongPathCostModeGroup,
                        stpxPVSTVlanGroup,
                        stpxLoopInconsistencyNotificationsGroup,
                        stpxLoopGuardGroup2,
                        stpxRSTPGroup,
                        stpxRPVSTGroup,
                        stpxPathCostOperModeGroup,
                        stpxSMSTGroup,
                        stpxSMSTInstanceGroup,
                        stpxSMSTPortStatusGroup,
                        stpxSMSTInstanceCISTGroup,
                        stpxSMSTPortMSTModeGroup,
                        stpxSMSTMaxHopCountGroup,
                        stpxSMSTConfigDigestGroup,
                        stpxMSTGroup4
                    }
    VARIATION       stpxSpanningTreeType
    ACCESS          read-only
    DESCRIPTION
        "Write access is not supported."

    VARIATION       stpxMSTRegionEditBufferStatus
    ACCESS          not-implemented
    DESCRIPTION
        "Not supported."

    VARIATION       stpxMSTRegionEditBufferOperation
    ACCESS          not-implemented
    DESCRIPTION
        "Not supported."

    VARIATION       stpxSMSTRegionEditRevision
    ACCESS          not-implemented
    DESCRIPTION
        "Not supported."

    VARIATION       stpxSMSTPortAdminMSTMode
    ACCESS          read-only
    DESCRIPTION
        "Write access is not supported."

    VARIATION       stpxSMSTMaxHopCount
    ACCESS          read-only
    DESCRIPTION
        "Write access is not supported."

    VARIATION       stpxLongStpPortPathCost
    ACCESS          not-implemented
    DESCRIPTION
        "Not supported."

    VARIATION       stpxRSTPPortProtocolMigration
    ACCESS          not-implemented
    DESCRIPTION
        "Not supported."

    VARIATION       stpxMSTRegionEditName
    ACCESS          not-implemented
    DESCRIPTION
        "Not supported."

    VARIATION       stpxPVSTVlanEnable
    ACCESS          read-only
    DESCRIPTION
        "Write access is not supported."

    VARIATION       stpxRootGuardConfigEnabled
    ACCESS          read-only
    DESCRIPTION
        "Write access is not supported."

    VARIATION       stpxSpanningTreePathCostMode
    ACCESS          read-only
    DESCRIPTION
        "Write access is not supported."

    VARIATION       stpxLoopGuardConfigMode
    ACCESS          read-only
    DESCRIPTION
        "Write access is not supported."

    VARIATION       stpxLoopGuardGlobalDefaultMode
    ACCESS          read-only
    DESCRIPTION
        "Write access is not supported."

    VARIATION       stpxRSTPPortAdminLinkType
    ACCESS          read-only
    DESCRIPTION
        "Write access is not supported."

    ::= { ciscoStpExtensionsCapability 13 }

END
