-- *****************************************************************
-- ciscoWanFrConnMIB
--
-- September 2002, Subra.Hegde
--
-- Copyright (c) 2002 by cisco Systems, Inc.
-- All rights reserved.
-- *****************************************************************

CISCO-WAN-FR-CONN-MIB DEFINITIONS ::= BEGIN
IMPORTS

    MODULE-IDENTITY,
    OBJECT-TYPE,
    Counter32,
    Integer32
                               FROM SNMPv2-SMI
    TruthValue                 FROM SNMPv2-TC
    MODULE-COMPLIANCE,
    OBJECT-GROUP               FROM SNMPv2-CONF
    frChan, frameRelay         FROM BASIS-MIB
    ciscoWan                   FROM CISCOWAN-SMI;

ciscoWanFrConnMIB MODULE-IDENTITY
        LAST-UPDATED    "200209180000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
    DESCRIPTION
        "The MIB module to configure the Frame Relay
         connection configuration.
 
         Terminologies Used:

             SIW - Frame-Relay-to ATM Service Interworking.
                   In SIW, the ATM port connected to a frame
                   relay port does not need to be aware that
                   it is connected to an interworking function.

                   This is explained in document FRF.8.
     
             NIW - Frame-Relay-to ATM Network Interworking.
                   In NIW, the ATM port connected to a frame
                   relay port does need to be aware that
                   it is connected to an interworking function.

             PVC - Permanent Virtual Circuit OR
                   Permanent Virtual Connection

                   A frame relay logical link, whose endpoints
                   and class of service are defined by network
                   management. A PVC consists of the originating
                   frame relay network element address, originating
                   DLCI, terminating frame relay network element
                   address and terminating DLCI.

                   This is controlled by PAR(Portable Auto Route)
                   controller.


             SPVC - Soft Permanent Virtual Circuits.
                    This is a PVC controlled by PNNI Controller.

             Frame Relay PVC/SPVC end-point/Channel is referred to as 
             frame Relay connection in this MIB.

             Traffic shaping parameters:
                 CIR, EIR, Bc, Be, DE, Tc, AR corresponding to
                 rate of the physical interface.

             CIR - Committed Information Rate.

                   This is the rate of traffic that the PVC
                   will support as 'comitted' traffic.

                   The committed rate(in bits per second) at which
                   the ingress access interface trunk interfaces,
                   and egress access interface of a frame relay
                   network transfer information to the destination
                   frame relay end system under normal conditions.
                   The rate is averaged over a minimum time interval
                   Tc. 

             AR  - Access Rate
                   The maximum number of bits per second that an end
                   station can transmit into the network is
                   bounded by the acess rate of the user-network
                   interface. The line speed of the user network
                   connection limits the access rate.

             Bc  - Committed Burst Size
                   The maximum amount of data(in bits) that the
                   network agrees to transfer, under normal conditions
                   during a time interval Tc.
                   The data is in bytes in the current implementation.

             Be  - Excess Burst Size
                   The maximum amount of uncommitted data(in bits)
                   in excess of BC that a frame relay network can
                   attempt to deliver during a time interval Tc.
                   This data generally is delivered with a low
                   probability than Bc. The network treats Be
                   data as discard eligible.
                   The data is in bytes in the current implementation.

             Tc  - The committed rate measurement interval.
                   The time interval during which the user can send
                   only BC committed amount of data and BE excess
                   amount of data.

             EIR - Excess Information Rate
                   This is the bandwidth in excess of CIR
                   the PVC will be allowed to burst on a 
                   a given PVC.

                   The average rate at which excess traffic is
                   to be policed. This number is computed based
                   on Bc, Be, CIR and Tc.

             DE  - Discard Eligibility


             Frame Forwarding Port: Frame Forwarding Ports are identified
             by portType = frame-forward(3). 

             NOTE: The objects related to frame relay ports are
                   available in ifTable,if ifTable is implemented
                   in service module/card.

             Following Service Modules support ifTable:
                 FRSM-12
        "

    REVISION    "200209180000Z"
    DESCRIPTION
        "Initial version of the MIB.

        The content of this MIB was originally available
        in CISCO-WAN-AXIPOP-MIB defined using SMIv1.
        The applicable objects from CISCO-WAN-AXIPOP-MIB
        are defined using SMIv2 in this MIB. Also the
        descriptions of some of the objects have been 
        modified."

    ::= { ciscoWan 47 }


frChanCnfGrp		OBJECT IDENTIFIER ::= { frChan 1 }


-- ------------------------------------------------------------------------
--
-- frChannelConfig group
-- Channel configurable parameters  (VC)
--
-- ------------------------------------------------------------------------


frChanCnfGrpTable	OBJECT-TYPE
    SYNTAX	SEQUENCE OF FrChanCnfGrpEntry
    MAX-ACCESS	not-accessible
    STATUS	current
    DESCRIPTION
        "This table is for configuring connection
        parameters for frame relay connections."
    ::= { frChanCnfGrp 1 }

frChanCnfGrpEntry	OBJECT-TYPE
    SYNTAX	FrChanCnfGrpEntry
    MAX-ACCESS	not-accessible
    STATUS	current
    DESCRIPTION
        "An entry for each frame relay connection."
    INDEX	{ chanNum }
    ::= { frChanCnfGrpTable 1 }

FrChanCnfGrpEntry ::=
    SEQUENCE {
        chanNum			   Integer32,
        chanRowStatus          	   INTEGER, 
        chanPortNum                Integer32, 
        dLCI		           Integer32,
        egressQSelect	      	   INTEGER,
        ingressQDepth	      	   Integer32,
        ingressQDEThresh   	   Integer32,
        ingressQECNThresh	   Integer32,
        egressQDepth	      	   Integer32,
        egressQDEThresh	   	   Integer32,
        egressQECNThresh	   Integer32,
        deTaggingEnable     	   INTEGER,
        cir                 	   Integer32,
        bc                  	   Integer32,
        be                  	   Integer32,
        ibs                 	   Integer32,
        foreSightEnable     	   INTEGER,
        qir                 	   Integer32,
        mir                 	   Integer32,
        pir                 	   Integer32,
        chanLocRmtLpbkState	   INTEGER,
        chanTestType               INTEGER,
        chanTestState              INTEGER,
        chanRTDResult              Integer32,
        chanType	           INTEGER,
        chanFECNconfig	           INTEGER,
        chanDEtoCLPmap	           INTEGER,
        chanCLPtoDEmap	           INTEGER,
-- CAC parameters (IngrPcr will be derived from foresightPIR )
        chanIngrPercentUtil	   Integer32,
        chanEgrPercentUtil         Integer32,
        chanEgrSrvRate             Integer32,
        chanOvrSubOvrRide          INTEGER,
        chanFrConnType	           INTEGER,
        frCDRNumber	           Integer32,
-- Connection parameters, used by PXM
        frLocalVpi	           Integer32,
        frLocalVci		   Integer32,
        frLocalNSAP		   OCTET STRING,
        frRemoteVpi		   Integer32,
        frRemoteVci                Integer32,
        frRemoteNSAP	      	   OCTET STRING,
        frMastership		   INTEGER,
        frVpcFlag		   INTEGER,
        frConnServiceType	   INTEGER,
        frRoutingPriority	   Integer32,
        frMaxCost		   Integer32,
        frRestrictTrunkType 	   INTEGER,
        frConnPCR		   Integer32,
        frConnRemotePCR		   Integer32,
        frConnMCR		   Integer32,
        frConnRemoteMCR		   Integer32,
        frConnPercentUtil	   Integer32,
        frConnRemotePercentUtil	   Integer32,
        frConnForeSightEnable	   INTEGER,
        frConnFGCRAEnable	   INTEGER,
        chanServType               INTEGER,
        chanServiceRateOverride	   INTEGER,
        chanServiceRate		   Integer32,
        zeroCirConEir		   Integer32,
        chanReroute                INTEGER,
        frConnSCR                  Integer32,
        frConnRemoteSCR            Integer32,
        frConnTemplateId           Integer32,
        frConnAdminStatus          INTEGER,
        frChanCnfChangeCount       Counter32,
        frChanCnfIgnoreIncomingDE  INTEGER,
        frChanOamCCEnable          INTEGER,
        frChanStatsEnable          INTEGER,
        frChanLocalLpbkEnable      INTEGER,
        frChanUpcEnable            INTEGER,
        frChanSlaveType            INTEGER,
        frConnRemoteMBS            Integer32,
        frChanPrefRouteId          Integer32,  
        frChanDirectRoute          TruthValue
        
    }

chanNum OBJECT-TYPE
    SYNTAX	Integer32(1..2147483647)
    MAX-ACCESS	read-only
    STATUS	current
    DESCRIPTION		  
        "The value of this object identifies the
        frame relay connection/channel index.

        Note that the actual range of the index
        supported by a card depends on the type of card.

        Supported Range for different Card Types:

        FRSM-4T1/E1         : Range is 16..271 (256 entries)
        FRSM-8T1/E1         : Range is 16..1015 (1000 entries)
        FRSM-T3/E3/HS2/
        /HS2B-HSSI/T3B/E3B  : Range is 16..2015 (2000 entries)
        FRSM-2CT3/HS2B-12IN1: Range is 16..4015 (4000 entries)

        For FRSM12 Card     : Range is 16..16015 for Lower 16 bits
                              Upper 16 bits contain Chassis Number
                              and logical slot number."
    ::= { frChanCnfGrpEntry 1}

chanRowStatus  OBJECT-TYPE
    SYNTAX     INTEGER {
	           add(1),
	           del(2),
               	   mod(3),
                   outOfService(4)
	       }
    MAX-ACCESS read-write
    STATUS     current
    DESCRIPTION
        "This object is used for adding/modifying/deleting
         the channel.
        add(1)   : For adding the frame relay connections.
        delete(2): For deleting frame relay connections.
        mod(3)   : For Modifying frame relay connections.
                   This is also used for uping the connection.

        outOfService(4) : Bring the Frame relay connection
                          down."
    ::= { frChanCnfGrpEntry 2 }

chanPortNum OBJECT-TYPE
    SYNTAX	Integer32
    MAX-ACCESS	read-write
    STATUS	current
    DESCRIPTION		  
        "This object refers to the frame relay
        port on which channel is created.
        This is a mandatory object for creating the channel.

        For FRSM12 Card:
        This object contains the port's ifIndex value.
    "
    ::= { frChanCnfGrpEntry 3 }

dLCI OBJECT-TYPE
    SYNTAX	Integer32 (0..8388607)
    MAX-ACCESS	read-write
    STATUS	current
    DESCRIPTION		  
        "The value of this object is the DLCI number of the channel. 

        This is a mandatory object for creating the channel.

        All the connections on the same port should have 
        a unique DLCI number. 

        Note that if we are adding a channel to a port that
        has LMI signalling enabled, then we can not use DLCI
        number 0(ANNEX A & D) and 1023(STRATA LMI). 

        The value of this object can be only 1000 if
        the portType = frame-forward(3) on which the frame relay
        connection is being created. That is, only one Frame Relay
        Connection can be created on a Frame Forwarding Port.

        For portHeaderLen = twoOctets(1) following restrictions apply.
           Range supported is '0..1023'
           DLCI values 0,1007, 1023 can not be used.

        For portHeaderLen = fourOctets(2) following restrictions apply.
           Range supported is '0..8388607'
           DLCI values 0,8257535 can not be used.
        "
    ::= { frChanCnfGrpEntry	4}

egressQSelect OBJECT-TYPE
    SYNTAX	INTEGER {
                    highPriority(1),
                    lowPriority(2),
                    notSupported(3)
                }
    MAX-ACCESS	read-write
    STATUS	current
    DESCRIPTION		  
        "Selects one out of two possible port queues.
        The default port queue number is 1 which is the high 
        pririty queue.
        1 = High priority queue 
        2 = Low priority queue 
        3 = Indicates that this entry is not used (eg: in FRSM-VHS,
        chanServType indicates the channel service type and
        would determine the queue to which the channel gets mapped)
        For FRSM12 Card:
        This object is used to select between the two ATM-COS queues
        in the egress direction.
        "
    DEFVAL { lowPriority }
    ::= { frChanCnfGrpEntry	5}

ingressQDepth	OBJECT-TYPE
    SYNTAX     Integer32 (4510..'1fffff'h)
    MAX-ACCESS read-write
    STATUS     current
    DESCRIPTION
        "This variable sets the max depth for queue, before
        it starts dropping the cells. It is defined in
        terms of number of bytes.
        In all cards except the FRSM-VHS card, the range is
        limited to (4510..'ffff'h).

        ingressQDepth should be greater than ingressQECNThresh
        and ingressQDEThresh
        For FRSM12 Card: Not Supported
        "
    DEFVAL { 65535 }
    ::= { frChanCnfGrpEntry 6}

ingressQECNThresh	OBJECT-TYPE
    SYNTAX     Integer32 (0..'1fffff'h)
    MAX-ACCESS read-write
    STATUS     current
    DESCRIPTION
        "This variable sets the max depth for queue, before
        it  starts flow control. It is defined in terms of
        number of bytes.
        In all cards except the FRSM-VHS card, the range is
        limited to (0..'ffff'h).
        For FRSM12 Card: Not Supported
        "
    DEFVAL { 6553 }
    ::= { frChanCnfGrpEntry 7}

ingressQDEThresh	OBJECT-TYPE
    SYNTAX     Integer32 (0..'1fffff'h)
    MAX-ACCESS read-write
    STATUS     current
    DESCRIPTION
        "This variable sets the max depth for queue, before
        they become discard eligible. It is defined in terms of 
        number of bytes.
        In all cards except the FRSM-VHS card, the range is
        limited to (0..'ffff'h).
        For FRSM12 Card: Not Supported
        "
    DEFVAL { 32767 }
    ::= { frChanCnfGrpEntry 8}

egressQDepth	OBJECT-TYPE
    SYNTAX     Integer32 (0..'1fffff'h)
    MAX-ACCESS read-write
    STATUS     current
    DESCRIPTION
        "This variable sets the max depth for queue, before
        it  starts dropping the cells. It is defined in terms of 
        number of bytes.
        In all cards except the FRSM-VHS card, the range is
        limited to (0..'ffff'h).

        egressQDepth should be greater than egressQDEThresh 
        and egressQECNThresh

        For FRSM12 Card: Not Supported
        "
    DEFVAL { 65535 }
    ::= { frChanCnfGrpEntry 9}

egressQDEThresh	OBJECT-TYPE
    SYNTAX     Integer32 (0..'1fffff'h)
    MAX-ACCESS read-write
    STATUS     current
    DESCRIPTION
        "This variable sets the max depth for queue, before
        they become discard eligible. It is defined in terms of 
        number of bytes.
        In all cards except the FRSM-VHS card, the range is
        limited to (0..'ffff'h).

        For FRSM12 Card: Not Supported
        "
    DEFVAL { 32767 }
    ::= { frChanCnfGrpEntry 10}

egressQECNThresh        OBJECT-TYPE
    SYNTAX     Integer32 (0..'1fffff'h)
    MAX-ACCESS read-write
    STATUS     current
    DESCRIPTION
        "This variable sets the max depth for queue, before
        it  starts flow control. It is defined in terms of 
        number of bytes.
        In all cards except the FRSM-VHS card, the range is
        limited to (0..'ffff'h).
        For FRSM12 Card: Not Supported
    "
    DEFVAL { 6553 }
    ::= { frChanCnfGrpEntry 11}

deTaggingEnable OBJECT-TYPE
    SYNTAX  INTEGER {
                enable(1),
                disable(2)
            } 
    MAX-ACCESS read-write
    STATUS     current
    DESCRIPTION
        "This object enables/disables the DE tagging.
         The  tagging is enabled only in the ingress 
         direction.

        For FRSM12 Card:
        When this object is disabled, the ingress policer will never
        set the DE bit to 1 in the Frame Relay frames even if 
        the incoming frame exceeds the Bc bucket.
        "
    DEFVAL { disable }
    ::= { frChanCnfGrpEntry 12}
 
cir OBJECT-TYPE
    SYNTAX     Integer32 (0..52000000)
    UNITS      "bps"
    MAX-ACCESS read-write
    STATUS     current
    DESCRIPTION
        "The value of this object is equal to the CIR parameter
        for this frame relay connection.

        The CIR value have to be less than or equal to the port speed.
        Any value from 1 to 2399 will be rounded off to 2400.

        Range supported for different interfaces/card:

          For E1 interface : Range is 0..2048000
          For T1 interface : Range is 0..1536000
          For E3 interface : Range is 0..34368000
          For T3 interface : Range is 0..44736000
          For HSSI         : Range is 0..52000000
          For FRSM-2CT3    : Range is 0..1536000
          For FRSM-HS2B-12IN1: Range is 0..10240000

         The CIR value can be 0 only for chanServType = uBR(5).
        "
        DEFVAL { 2400 }
        ::= { frChanCnfGrpEntry 13}
         
bc OBJECT-TYPE
    SYNTAX     Integer32 (0..2097151)
    UNITS      "bytes"
    MAX-ACCESS read-write
    STATUS     current
    DESCRIPTION
        "The value of this object is equal to the
        committed burst size(BC) parameter for this
        PVC endpoint.

        The value of bc can not be 0 when cir is non zero.
        The value of bc has to be 0 if cir is 0.

	The peak value for bc in FRSM-VHS cards is (2^21 -1),
	i.e. 2097151 and for all other cards, it is 65535.
	For FRSM-VHS cards, the relation between CIR and Bc should 
	be such that Tc is always less than 512 seconds. 
        "
    DEFVAL { 5100 }
    ::= { frChanCnfGrpEntry 14}
         
be OBJECT-TYPE
    SYNTAX     Integer32 (0..2097151)
    UNITS      "bytes"
    MAX-ACCESS read-write
    STATUS     current
    DESCRIPTION
        "The value of this object is euqal to the
        excess burst size(Be) parameter for this PVC
        endpoint. 

     	The value be can not be 0 when cir is 0.

        The peak value for be :
            For FRSM-VHS and FRSM12 cards is (2^21 -1), i.e. 2097151 and
            For all other cards, it is 65535.

	 For FRSM-VHS cards, setting the value of 2091751 will 
	    cause the policing to be disabled. "
    DEFVAL { 5100 }
    ::= { frChanCnfGrpEntry 15}
         
ibs OBJECT-TYPE
    SYNTAX     Integer32 (0..2097151)
    MAX-ACCESS read-write
    STATUS     current
    DESCRIPTION
        "The value of this object is euqal to the
        excess burst size(Be) parameter for this PVC
        endpoint. 

	The value of ibs should be less or equal to bc 
        when cir is greater than 0.

        The value of ibs has to be 0 when cir is 0.

        The peak value for ibs in FRSM-VHS cards is (2^21 -1),
	 i.e. 2097151 and for all other cards, it is 65535.

	 For FRSM12 Card: Not Supported
        "
    DEFVAL { 100 }
    ::= { frChanCnfGrpEntry 16}
         
foreSightEnable OBJECT-TYPE
    SYNTAX     INTEGER {
	          enable(1),
	          disable(2)
	       }
    MAX-ACCESS read-write
    STATUS     current
    DESCRIPTION
        "This variable enables/disables foreSight option.

         Following objects can be modified only when this
         object is set to enable(1):

            qir, mir, pir

        The RATE CONTROL FEATURE has to be ON in order to enable 
	foresight and also modify its parameter. 

	 For FRSM12 Card: Not Supported
        "
	DEFVAL { disable }
        ::= { frChanCnfGrpEntry 17}
 
qir OBJECT-TYPE
    SYNTAX     Integer32 (160..6400000)
    UNITS      "fastpackets-per-second"
    MAX-ACCESS read-write
    STATUS     current
    DESCRIPTION
        "The value of this object is euqal to the
        quiescent information rate for Foresight.
 
        The unit is 1 Cell/Sec = 16 fastpackets/sec.

	Following information about cps is for reference only: 
	The peak value for qir in FRSM-VHS cards is 285714 cps and
	for all other cards, it is 10000 cps.
	For FRSM-VHS cards, cell will be the ATM cell (48 byte payload).

	For FRSM12 Card: Not Supported"
	DEFVAL { 160 }
        ::= { frChanCnfGrpEntry 18}
 
mir OBJECT-TYPE
    SYNTAX     Integer32 (160..6400000)
    UNITS      "fastpackets-per-second"
    MAX-ACCESS read-write
    STATUS  current
    DESCRIPTION
        "The value of this object is euqal to the
        minimum information rate for Foresight.

        The unit is 1 Cell/Sec = 16 fastpackets/sec.
	is equal to 16 fastpackets/sec.

         Following information about cps is for reference only: 
	 The peak value for qir in FRSM-VHS cards is 285714 cps and
	 for all other cards, it is 10000 cps.
	 For FRSM-VHS cards, cell will be the ATM cell (48 byte payload).

	 For FRSM12 Card: Not Supported
        "
	DEFVAL { 160 }
        ::= { frChanCnfGrpEntry 19}
         
pir OBJECT-TYPE
    SYNTAX     Integer32 (160..6400000)
    UNITS      "fastpackets-per-second"
    MAX-ACCESS read-write
    STATUS  current
    DESCRIPTION
        "The value of this object is euqal to the
        peak information rate for Foresight.

        The unit is 1 Cell/Sec = 16 fastpackets/sec.
	is equal to 16 fastpackets/sec.

	 Following information about cps is for reference only: 
	 The peak value for qir in FRSM-VHS cards is 285714 cps and
	 for all other cards, it is 10000 cps.
	 For FRSM-VHS cards, cell will be the ATM cell (48 byte payload).

	 For FRSM12 Card: Not Supported
        "
	DEFVAL { 160 }
        ::= { frChanCnfGrpEntry 20}


chanLocRmtLpbkState OBJECT-TYPE 
    SYNTAX     INTEGER {
	          enable(1), 
	          disable(2) 
	       }
    MAX-ACCESS read-write 
    STATUS     current 
    DESCRIPTION 
        "This variable enables or disables the remote loopback for each
	 channel.
	 When you enable this option on a connection (channel) then all the
	 cells that are coming from the network side would be looped back
	 toward the network and all the frames coming from the user side
	 would be dropped.
	 This channel remote loopback has nothing to do with the chanTestType
	 option, each one does a different function. 
	 For example, the channel remote loopback is used for looping the data
	 toward the network and if this connection is terminated on an IPX
	 then they can put a test equipment and measure some of the 
	 characteristics of the network.

	 For FRSM12 Card: Not Supported
        " 
    DEFVAL { disable }
    ::= { frChanCnfGrpEntry 21} 

chanTestType OBJECT-TYPE  
    SYNTAX    INTEGER {
                  testcon(1),
	          testdelay(2),
	          notest(3)
	       }
    MAX-ACCESS read-write 
    STATUS     current  
    DESCRIPTION    
	 "The chanTestType starts testing the continuity 
          or delay of a connection.
	 It sends specific cell patterns toward the network 
         and the terminating end of this connection has to be an
         MGX8220 or ASI of a BPX in order for this test to be working. 

	 The receiving node would loop back when it receives these
	 cells. The test should be done in about couple of seconds.
         The testcon tests the continuity of the connection and 
         testdelay uses the same test except that it measures for 
         delay through the network. 
	 To test the delay follow this procedure:
		a- set chanTestType to testdelay
		b- read chanTestState till it is Pass or Fail 
		c- Read chanRTDResult for the delay if it is Pass
		*Note that the chanTestType would go back to notest when the
		 test is completed 
	 To test the continuity follow this procedure:
		a- set chanTestType to testcon
		b- read chanTestState till it is Pass or Fail 
		*Note that the chanTestType would go back to notest when the
		 test is completed 
	 You CAN NOT select 2 tests back to back,
         you have to select one and wait for
	 the result and then start the other one.
    SYNTAX  
	 When you select testdelay 
	 
	 This is the type of the test
	 1 = Test Continuity
	 2 = Test Delay
	 3 = No Test
        " 
	DEFVAL { notest }
        ::= { frChanCnfGrpEntry 22}  
 
chanTestState OBJECT-TYPE  
    SYNTAX  INTEGER {
	        passed(1),
	        failed(2),
	        inprogress(3),
	        notinprogress(4)
	    } 
    MAX-ACCESS read-only 
    STATUS     current  
    DESCRIPTION    
        "This shows the state of the test
	 When you add a connection then the chanTestState becomes notinprogress
	 and when you select any test, it would go to inprogress state and after
	 it completes the test, it will go to failed or passed state.
	 1 = Passed
	 2 = Failed
	 3 = In Progress 
	 4 = Not In Progress
        " 
	DEFVAL { notinprogress }
        ::= { frChanCnfGrpEntry 23}  
 
chanRTDResult OBJECT-TYPE  
    SYNTAX     Integer32 (1..65535)  
    MAX-ACCESS read-only 
    STATUS     current  
    DESCRIPTION    
        "This is round trip delay in milliseconds.
	 When you select testdelay option for the chanTestType, the result of
	 the test that is measured in milliseconds can be read in chanRTDResult.
        " 
	DEFVAL { 65535 }
        ::= { frChanCnfGrpEntry 24}  
 
chanType	OBJECT-TYPE
    SYNTAX	INTEGER {
                    frNIW(1),
                    frSIW-transparent(2),
                    frSIW-translate(3),
                    frFUNI(4),
                    frForward(5),
                    frNIWReplace(6)
                }
    MAX-ACCESS read-write
    STATUS     current
    DESCRIPTION
        "The value of this object is used for setting the
        channel type of a frame relay connection. If set
        with values frSIW-transparent(2) and frSIW-translate(3),
        all PVC data is subject to service interworking translation
        and mapping in both Frame Relay-to-ATM and ATM-to-Frame relay
        directions.
      
        The possible values are :

          frNIW(1)            : Frame-Relay-to ATM Network 
                                Interworking(NIW-unicast).
                                The traffic crosses the network as
                                ATM Cells.

          frSIW-transparent(2): Service InterWorking with out any 
                                SDU translation. In transparent mode,
                                the service module does not translate.

          frSIW-translate(3)  : Service InterWorking with SDU translation.
                                In translation mode, service module
                                translates protocol between the FR NLPID
                                encapsulation(RFC 1490) and ATM LCC
                                encapsulation(RFC 1483). Translation mode
                                support includes address resolution by
                                transforming address resolution protocol
                                (ARP, RFC 826) and inverse ARP(RFC 1293) 
                                between the frame relay and ATM Formats.

          frFUNI(4)           : Frame based UNI: mode-1a which is ALL5.

          frForward(5)        : frame forwarding. Frame forwarding operates
                                same as standard frame relay except:
                               * 2 byte Q.922 header is not assumed
                                 or interpreted. 
                               * All frames received are mapped to a
                                 specific connection if it exists. Otherwise
                                 the frames are dropped.
                               * No  DE/CLP or FECN/EFCI mapping is performed.
                               * 'llegal Header count' and 'invalid DLCI'
                                 statistics are not kept/applicable.

          frNIWReplace(6)     : Frame Relay network interworking
                                with DLCI in FR-SSCS(Frame Relay Specific
                                Convergence Sublayer)PDU always
                                set to 1022.
        "
    REFERENCE 
        "FRF.8"
    ::= { frChanCnfGrpEntry 25 }

chanFECNconfig	OBJECT-TYPE
    SYNTAX	INTEGER {
                    mapEFCI(1),
                    setEFCIzero(2)
                }
    MAX-ACCESS read-write
    STATUS     current
    DESCRIPTION
        "The value of this object specifies how to map
        from FECN field in the frame Relay PDU to
        the EFCI field in the ATM cells. 

        This object does not apply to NIW.
        This is applicable only
        for SIW.
        
        mapEFCI(1)   : Maps the FECN bits in frame-relay
                       to EFCI bit in the ATM cells. 
                       This value is valid only for SIW.
        setEFCIzero(2): Set EFCI = 0. Do not map FECN to EFCI."
    REFERENCE
        "FRF.8, section 4.3.1.1"
    ::= { frChanCnfGrpEntry 26 }

chanDEtoCLPmap	OBJECT-TYPE
    SYNTAX	INTEGER {
                    mapCLP(1),
                    setCLPzero(2),
                    setCLPone(3) 
                }
    MAX-ACCESS read-write
    STATUS     current
    DESCRIPTION
        "The value of this object specifies how to map
        from DE bit on the Frame Relay side to CLP
        bit on the ATM side.
 
        mapCLP(1)     : Map DE bit to CLP bit in ATM cell.
        setCLPzero(2) : Ignore DE bit. Set CLP to 0.
        setCLPone(3)  : Ignore DE bit. Set CLP to 1.
        For FRSM12 Card:
            Should not be mapCLP for chanType of frForward.
    "
    REFERENCE
        "FRF.5, FRF.8"
    ::= { frChanCnfGrpEntry 27 }

chanCLPtoDEmap	OBJECT-TYPE
    SYNTAX	INTEGER {
                    mapDE(1),
                    setDEzero(2),
                    setDEone(3),
                    ignoreCLP(4) 
                }
    MAX-ACCESS read-write
    STATUS     current
    DESCRIPTION
        "The value of this object enables mapping of 
        Cell Loss Priority(CLP) bit on the ATM Side
        to Discard Eligibility(DE) bit on the Frame relay
        side.

        The possible values are :

          mapDE(1)      : Map CLP bit to DE bit.
                          Valid for SIW and NIW.

          setDEzero(2)  : Ignore CLP. Set DE bit to 0.
                          Valid for SIW.

          setDEone(3)   : Ignore CLP. Set DE bit to 1.
                          Valid for SIW.

          ignoreCLP(4)  : Ignore CLP. No change in receieved DE bit.
                          Valid for NIW.

        For FRSM12 Card:
            Should be ignoreCLP for chanType of frForward.
            Should not be setDEzero/setDEone for chanType of frNIW 
            and frNIWReplace.
            Should not be ignoreCLP for chanType of frSIW-transparent
            and frSIW-translate.
    "
    REFERENCE
        "FRF.8, section 4.2.2
         FRF.5, section 4.4.2"
    ::= { frChanCnfGrpEntry 28 }

chanIngrPercentUtil	OBJECT-TYPE
    SYNTAX	Integer32 (1..100)	
    UNITS       "percentage"
    MAX-ACCESS	read-write
    STATUS	current
    DESCRIPTION
        "The ingress utilization on a 
        frame relay connection."
    DEFVAL { 100 }
    ::= { frChanCnfGrpEntry 29 }

chanEgrPercentUtil  OBJECT-TYPE
    SYNTAX	Integer32 (1..100)	
    UNITS       "percentage"
    MAX-ACCESS	read-write
    STATUS	current
    DESCRIPTION
        "The egress utilization on a 
        frame relay connection."
    DEFVAL { 100 }
    ::= { frChanCnfGrpEntry 30 }

chanEgrSrvRate  OBJECT-TYPE
    SYNTAX     Integer32 (2400..52000000)
    MAX-ACCESS read-write
    STATUS	current
    DESCRIPTION
        "The value of this object identifies egress CIR
        value for a frame relay connection.

        The value of this object must be less than or equal(<=)
        to the port speed.

        The value supported depends upon the interface 
        and service module(card) type.
           
           For E1 Service Module : Range is 2400..2048000
           For T1 Service Module : Range is 2400..1536000
               2CT3 Module       :
           For E3 Service Module : Range is 2400..34368000
           For T3 Service Module : Range is 2400..44736000
           For HSSI Service Module : Range is 2400..52000000

        For FRSM12 Card:
        This object is used only for CAC and the range will be same
        as the range for cir object. The Maximum value is 44736000m.
        "
    DEFVAL { 2400 }
    ::= { frChanCnfGrpEntry 31 }

chanOvrSubOvrRide   OBJECT-TYPE
    SYNTAX  INTEGER {
                disable (1),
                enable (2)
            }
    MAX-ACCESS read-write 
    STATUS     current  
    DESCRIPTION    
        "The value of this object enables/disables the
        oversubscription on a connection.
        This object allows one to add a new connection on a port
        even if it is over subscribed.

        For FRSM12 Card: Not Supported." 
    DEFVAL { disable }
    ::= { frChanCnfGrpEntry 32 }

chanFrConnType	OBJECT-TYPE
    SYNTAX	INTEGER {
                    pvc(1),
                    svc(2),
                    spvc(3),
                    par(4),
                    pnni(5),
                    tag(6)
                }
    MAX-ACCESS read-write
    STATUS     current
    DESCRIPTION
        "The value of this object is used for configuring
        connection type of a frame relay connection.

        The possible values are :

          pvc(1)   : Permanent Virtual Connection
          svc(2)   : Switched Virtual Connection
          spvc(3)  : Soft PVC.
          par(4)   : Portable Auto Route Connection.
                     Valid only for trunk connection
          pnni(5)  : PNNI Connection
                     Valid only for trunk connection
          tag(6)  : Tag/MPLS Connection
                     Valid only for trunk connection
            For FRSM12 Card: Not Supported."
    DEFVAL { pvc }
    ::= { frChanCnfGrpEntry 33 }

frCDRNumber OBJECT-TYPE
    SYNTAX     Integer32 
    MAX-ACCESS read-write
    STATUS     current
    DESCRIPTION
        "The value of this object identifies 
        the CDR(Call Detail Record) number. 
        This is the key to correlate 
        cell/frame counts, start/end record.

         For FRSM12 Card: Not Supported
        "
    ::= { frChanCnfGrpEntry 34 }

frLocalVpi OBJECT-TYPE
    SYNTAX 	Integer32 (0..65535)
    MAX-ACCESS	read-only
    STATUS	current
    DESCRIPTION
        "The value of this object provides the VPI
        value for the local endpoint. 
        This object in conjunction with frLocalVci and
        frLocalNSAP represents the local end point of 
        this connection. 

        The service module sets this to value 0."
    ::= { frChanCnfGrpEntry 35 }

frLocalVci OBJECT-TYPE
    SYNTAX 	Integer32 (0..65535)
    MAX-ACCESS	read-only
    STATUS	current
    DESCRIPTION
        "The value of this object provides the VCI
        value for the local endpoint. 
        This object in conjunction with frLocalVpi and 
        frLocalNSAP represents the local end point of 
        this connection.

        The service module assigns this value 
        specified in object 'dLCI'."
    ::= { frChanCnfGrpEntry 36 }

frLocalNSAP OBJECT-TYPE
    SYNTAX	OCTET STRING (SIZE(0..20))
    MAX-ACCESS	read-write
    STATUS	current
    DESCRIPTION
        "The value of this object identifies the
        NSAP address of the frame relay connection.
        
        The value of this object follows the format:
              Prefix      :  13 Bytes
              Cisco ID    :   2 bytes
              Reserved    :   1 byte
              Slot Number :   1 byte
              Port Number :   2 bytes
              ESL         :   1 byte

        For FRSM12 Card:
            This object will have the NSAP format as required by the
            PNNI controller
        "
    ::= { frChanCnfGrpEntry 37 }

frRemoteVpi OBJECT-TYPE
    SYNTAX 	Integer32 (0..65535)
    MAX-ACCESS	read-write
    STATUS	current
    DESCRIPTION
        "The value of this object identifies the VPI value of remote
        end point of this connection. The frRemoteVpi, frRemoteVci
        and frRemoteNSAP identifies the remote end point of
        this connection."
    ::= { frChanCnfGrpEntry 38 }

frRemoteVci OBJECT-TYPE
    SYNTAX 	Integer32 (0..65535)
    MAX-ACCESS	read-write
    STATUS	current
    DESCRIPTION
        "The value of this object identifies the VCI value of remote
        end point of this connection. The frRemoteVpi, frRemoteVci
        and frRemoteNSAP identifies the remote end point of
        this connection."
    ::= { frChanCnfGrpEntry 39 }

frRemoteNSAP OBJECT-TYPE
    SYNTAX	OCTET STRING (SIZE(0..20))
    MAX-ACCESS	read-write
    STATUS	current
    DESCRIPTION
        "The value of this object identifies the
        NSAP address of the frame relay connection.
        
        The value of this object follows the format:

              Prefix      :  13 Bytes
              Cisco ID    :   2 bytes
              Reserved    :   1 byte
              Slot Number :   1 byte
              Port Number :   2 bytes
              ESL         :   1 byte."
    ::= { frChanCnfGrpEntry 40 }

frMastership OBJECT-TYPE
    SYNTAX INTEGER {
                master (1),
                slave (2),
                unknown (3)
            }
    MAX-ACCESS read-write
    STATUS     current
    DESCRIPTION
        " This is used by PXM to determine if this end point is 
        master or slave, a new type unknown is added to identify
        the SM in MGX8220 shelf and the SM in MGX shelf. In AXIS
        shelf, user can still use addchan to add a channel without
        specifying X/Y/P parameters. But in MGX shelf, if the
        user uses addchan without X/Y/P set (based on this object
        being set to type 3 unknown), SPM on PXM will reject
        the request. It must be supplied in connection setup request.
        In the feeder mode, this is always set to master.
        "
    ::= { frChanCnfGrpEntry 41 }

frVpcFlag OBJECT-TYPE
    SYNTAX INTEGER {
               vpc (1),
               vcc (2)
           }
    MAX-ACCESS read-write
    STATUS     current
    DESCRIPTION
        " This represents the connection type, used for PXM to
        identify VPC/VCC but FRSM card doesn't use it
        always set to vcc for FRSM card
        For FRSM12 Card:
        For chanFrConnType = pnni(5), this object is 
        set to vcc(2) always."
    DEFVAL { vcc }
    ::= { frChanCnfGrpEntry 42 }

frConnServiceType OBJECT-TYPE
    SYNTAX INTEGER{
               cbr    (1),
               vbr    (2),
               notUsed (3),
               ubr    (4),
               atfr   (5),
               abrstd (6),
               abrfst (7),
               vbrrt  (8),
               cbr1   (21),
               vbr1rt (22),
               vbr2rt (23),
               vbr3rt (24),
               vbr1nrt(25),
               vbr2nrt(26),
               vbr3nrt(27),
               ubr1   (28),
               ubr2   (29),
               stdabr (30),
               cbr2   (31),
               cbr3   (32)

               }
    MAX-ACCESS read-write
    STATUS     current
    DESCRIPTION
        "This specifies the service type 
        1 ==> Constant Bit Rate
        2 ==> Variable Bit Rate
        3 ==> Not used
        4 ==> Unspecified Bit Rate
        5 ==> ATM frame relay
        6 ==> standard ABR
        7 ==> foresight ABR
        Note that this is used by PXM card, SV+ doesn't need to set it,
        if not set in the connection setup request, it'll be defaulted
        to ATFR type for FRSM.
        Also to make it compatible with existing AUSM MIB definition,
        value 3 is not used.
        The following types are being added for PNNI support.
        and are based on UNI 4.0
        cbr1   (21) - CBR.1
        vbr1rt (22) - Real time VBR.1
        vbr2rt (23) - Real time VBR.2
        vbr3rt (24) - Real time VBR.3
        vbr1nrt(25) - Non Real time VBR.1
        vbr2nrt(26) - Non Real time VBR.2
        vbr3nrt(27) - Non Real time VBR.3
        ubr1   (28) - UBR.1
        ubr2   (29) - UBR.2
        stdabr (30) - TM 4.0 compliant standard ABR
        cbr2   (31) - CBR.2
        cbr3   (32) - CBR.3

        For FRSM12 Card:
            Not Supported. Derived from chanServType.
        "
    DEFVAL {atfr}
    ::= { frChanCnfGrpEntry 43 }
		
frRoutingPriority OBJECT-TYPE
    SYNTAX     Integer32 (1..15)
    MAX-ACCESS read-write
    STATUS     current
    DESCRIPTION
        " This is used by PXM to determine how important this 
        connection is when selecting connections to route
        "
    DEFVAL {1}
    ::= { frChanCnfGrpEntry 44 }
	
frMaxCost OBJECT-TYPE
    SYNTAX	Integer32 (1..2147483647)
    MAX-ACCESS	read-write
    STATUS	current
    DESCRIPTION
        "The value of this object specifies the
        Maximum allowed cost. It is related to Cost Based Routing.
        This is used by PXM so that it won't choose a path with
        a cost greater than this configured level. This is not
        necessary to be provided in the connection setup request,
        if not provided, the default value 255 will be used.

        Also the range supported depends upon the controller
        configured : 

             Controller           Range              Default Value

         chanFrConnType = par(2)   1..65535           255
         chanFrConnType = pnni(5)  1..2147483647      2147483647.
    "
    ::= { frChanCnfGrpEntry 45 }

frRestrictTrunkType OBJECT-TYPE
	SYNTAX	INTEGER {
		norestriction (1),
		terrestrialTrunk (2),
		sateliteTrunk (3)
	}
	MAX-ACCESS read-write
	STATUS	   current
	DESCRIPTION
		" Restricted trunk type for routing, used by PXM. It 
		  specifies that the connection either cannot be routed over
		  satelite trunks, or terrestrial trunks, or it can be on
		  any type of trunk. It is not necessary to be provide in
		  the connection setup request, the default value is 
		  norestriction(1).

		  For FRSM12 Card: Not Supported
		"
	DEFVAL {norestriction}
	::= { frChanCnfGrpEntry 46 }
 
frConnPCR OBJECT-TYPE
    SYNTAX     Integer32 
    MAX-ACCESS read-write
    STATUS     current
    DESCRIPTION
        "The value of this object identifies
        the PCR(Peak Cell Rate). If not provided in 
        the connection setup request, it'll be derived from 
        object 'pir'.

        For FRSM12 Card:
            Default value is (1.44 * CIR)
    "
    ::= { frChanCnfGrpEntry 47 }

frConnRemotePCR OBJECT-TYPE
    SYNTAX     Integer32 
    MAX-ACCESS read-write
    STATUS     current
    DESCRIPTION
        " Peak cell rate of the other end, if not set, will be
        set to the same as local end PCR (frConnPCR). However,
        note that if the CIRs for both local and remote end
        are set to the different value (i.e., asymmetric conn), 
        then this should be set differently from local end PCR.
        For FRSM12 Card:
            Default value is frConnPCR
    "
    ::= { frChanCnfGrpEntry 48 }

frConnMCR OBJECT-TYPE
    SYNTAX     Integer32 
    MAX-ACCESS read-write
    STATUS     current
    DESCRIPTION
        " Minimum cell rate, if not provided in the connection setup
        request, it'll be derived from object 'mir'.
        For FRSM12 Card:
            Default value is frConnPCR
    "
    ::= { frChanCnfGrpEntry 49 }

frConnRemoteMCR OBJECT-TYPE
    SYNTAX     Integer32 
    MAX-ACCESS read-write
    STATUS     current
    DESCRIPTION
        " Minimum cell rate of the other end, if not set, will be
        set to the same as local end MCR (frConnMCR). However,
        note that if the CIRs for both local and remote end
        are set to the different value (i.e., asymmetric conn),
        then this should be set differently from local end MCR.
        For FRSM12 Card:
        Default value is frConnMCR
        "
    ::= { frChanCnfGrpEntry 50 }

frConnPercentUtil OBJECT-TYPE
    SYNTAX     Integer32  (0..100)
    MAX-ACCESS read-write
    STATUS     current
    DESCRIPTION
        "This is the expected long-term utilization of the
        channel by this end-point. If this is not specified in
        the connection setup request, it'll be defaulted to
        100 percent

        For FRSM12 Card: Not Supported
        "
    DEFVAL {100}
    ::= {frChanCnfGrpEntry 51 }

frConnRemotePercentUtil OBJECT-TYPE
    SYNTAX     Integer32  (0..100)
    MAX-ACCESS read-write
    STATUS     current
    DESCRIPTION
        "This is the expected long-term utilization of the
        channel by the other end-point. If this is not specified in
        the connection setup request, it'll be set to be the same
        as the local end frConnPercentUtil value assuming that the
        connection is symmetric. In a asymmetric connection, this
        object is supposed to be set.

        For FRSM12 Card: Not Supported."
    ::= { frChanCnfGrpEntry 52 }

frConnForeSightEnable OBJECT-TYPE
    SYNTAX  INTEGER {
                enable(1),
                disable(2)
            }
    MAX-ACCESS read-write
    STATUS     current
    DESCRIPTION
        "This object is used by the controller(PAR/PNNI/TAG) to
        set up the Qbin for the connection, if this is not set,
        it'll be defaulted by SM to the same as foreSightEnable
        in the end point parameters. 

        For FRSM12 Card: Not Supported."
    ::= { frChanCnfGrpEntry 53 }

frConnFGCRAEnable     OBJECT-TYPE
    SYNTAX  INTEGER {
                enable (1),
                disable (2)
            }
    MAX-ACCESS read-write
    STATUS     current
    DESCRIPTION
        "The value of this object is used for
        enabling/disabling Frame based GCRA 
        (early packet discard).

        For FRSM12 Card: Not Supported."

        DEFVAL {disable}
    ::= { frChanCnfGrpEntry 54}
 
chanServType OBJECT-TYPE
    SYNTAX INTEGER{
                highpriority(1),
                rtVBR(2),
                nrtVBR(3),
                aBR(4),
                uBR(5),
                queue6(6),
                queue7(7),
                queue8(8),
                stdABR(9)

            }
    MAX-ACCESS read-write
    STATUS     current
    DESCRIPTION
        "The value of this object indicates the 
         indicates the class of the connection.
            1-High priority (typically CBR connections)
            2- real-time VBR
            3- non-real time VBR
            4- Available Bit Rate
            5- Unspecified Bit Rate
            9- Standard ABR
        There are 8 queues actually but only 4 are being used
        (the 4 queues are for CBR, VBR-rt, <VBR-nrt and ABR>, UBR traffic).
        This object is suported only in FRSM-VHS and FRSM-8T1E1.
        For FRSM-8T1E1, a 0 indicates that the connections are of old model
        type where chanServType object is unused.

        For FRSM12 Card:
            The types aBR, queue6, queue7, queue8 are not supported

        This object can not be modified after a frame relay
        connection has been created."
    ::= { frChanCnfGrpEntry 55 }

chanServiceRateOverride	OBJECT-TYPE
    SYNTAX INTEGER{
                enable(1),
                disable(2)
            }
    MAX-ACCESS read-write
    STATUS     current
    DESCRIPTION
        "This variable sets the SAR IR programming option.
        Foresight and chanServiceRateOverride are mutually exclusive.
		
        For FRSM12 Card: Not Supported."
    DEFVAL	{disable}
    ::= { frChanCnfGrpEntry 56 }

chanServiceRate	OBJECT-TYPE
    SYNTAX     Integer32 (160..6400000)
    MAX-ACCESS read-write
    STATUS     current
    DESCRIPTION
        "This is the rate to which IR can be set to when 
        chanServiceRateOverride is set to enable(1). If 
        chanServiceRateOverride is disable(2) then this object
        does not have any significance.
        For FRSM-8T1/8E1,this is defined in fastpackets/sec.
        For FRSM-VHS, this is defined in atm cells per second.
        For VHS the range in cells per second will be 10 to 400000 cps.
		
        For FRSM12 Card: Not Supported."

    ::= { frChanCnfGrpEntry 57 }

zeroCirConEir OBJECT-TYPE
    SYNTAX     Integer32 (0..52000000)
    MAX-ACCESS read-write
    STATUS     current
    DESCRIPTION
        "The value of this object defines defines EIR
        value for '0' CIR connection. 

        If the value is '0', EIR is set to port speed.
        If zeroCirConEir is non-zero value, EIR is set 
        to value of this object, and this value 
        is used for policing in ingress direction. 

        This object is valid only for a zero cir connection.
        zeroCirConEir has to be less than or equal to the port speed."

        DEFVAL {0}
        ::= { frChanCnfGrpEntry 58}

chanReroute    OBJECT-TYPE
    SYNTAX INTEGER {
             true(1),
             false(2)
           }
    MAX-ACCESS read-write
    STATUS     current
    DESCRIPTION
       " This is used by the administrator to trigger the re-routing
         of the connection. The rerouting takes effect, when this object
         is set to true(1). When set to false (2), no action is taken.
         A get on this object always returns false (2).
         This object is not applicable to MGX Release 1.x.
       "
    DEFVAL {false}
    ::= { frChanCnfGrpEntry 59 }

frConnSCR OBJECT-TYPE
    SYNTAX     Integer32
    MAX-ACCESS read-write
    STATUS     current
    DESCRIPTION
        " Sustained cell rate, Used for VBR connections setup with PNNI
          controller.
          For FRSM12 Card: Default value is frConnPCR
          This object is not applicable to MGX Release 1.x."
    ::= { frChanCnfGrpEntry 60 }

frConnRemoteSCR OBJECT-TYPE
    SYNTAX     Integer32
    MAX-ACCESS read-write
    STATUS     current
    DESCRIPTION
        " Sustained cell rate of the other end,  Used for VBR connections
          setup with PNNI controller.
          For FRSM12 Card: Default value is frConnSCR
          This object is not applicable to MGX Release 1.x
        "
    ::= { frChanCnfGrpEntry 61 }

frConnTemplateId OBJECT-TYPE
    SYNTAX     Integer32 (1..17)
    MAX-ACCESS read-write
    STATUS     current
    DESCRIPTION
        "This object specifies the template identifier for the connection
         template associated with this connection.
         The valid range for templates is 1..16.
         A value of 17 indicates no template is associated with this
         connection
         For FRSM12 Card: Not Supported
         This object is not applicable to MGX Release 1.x
        "
    DEFVAL {17}
    ::= { frChanCnfGrpEntry 62 }

frConnAdminStatus OBJECT-TYPE
    SYNTAX INTEGER {
        up(1),
        down(2)
    }
    MAX-ACCESS read-write
    STATUS     current
    DESCRIPTION
        "This object specifies channel admin status. 
         This object is not applicable to MGX Release 1.x."
    DEFVAL {down}
    ::= { frChanCnfGrpEntry 63 }

-- added for FRSM12
frChanCnfChangeCount  OBJECT-TYPE
    SYNTAX	Counter32
    MAX-ACCESS	read-only
    STATUS	current
    DESCRIPTION
        "This object is added only for FRSM12 card.

        This counter tracks the number of configuration changes
	that happen on a channel. The  counter is
	associated only with the end point  and NOT with the
	connection itself.

	This counter is used by the NMS to determine if a connection
	configuration had been modified and requires an upload.
	This functionality is conventionally achieved by time 
	stamping using a time-of-day clock. However, in switches
	where time-of-day clock is not available, the following
	scheme is used:

	The upload counter is incremented, when:

	* assignment of connection to an end point channel. This
	  happens when a connection is added and assigned this 
	  channel number.
	* de-assignment of connection from a channel number. This
	  happens when a connection is deleted and the 
	  end point  resource is released.
	* When there is a configuration change done to the connection
	  that is associated with this end point channel number.
        
        In a new system, an unutilised resouce (channel number)
        has a counter value of zero. When a connection is added to
	this channel end point, the counter is incremented. And is
	incremented for any of the above operations. When a connection
	is deleted the value of this counter is incremented and
	preserved till a new connection gets associated with this
	channel end point.
        
        This object is not applicable to MGX Release 1.x."
            ::= { frChanCnfGrpEntry 64 }

-- added for FRSM12
frChanCnfIgnoreIncomingDE OBJECT-TYPE
	SYNTAX	INTEGER {
		    enable  (1),
		    disable (2)
		}
	MAX-ACCESS read-write
	STATUS	   current
	DESCRIPTION	
	    "This object is added for FRSM12 card.
            When this object is enabled, the incoming frames with 
            DE(Discard Eligible) bit set to 1 are counted in the 
            Bc bucket instead of Be bucket
 
            This object is not applicable to MGX Release 1.x."
        ::= { frChanCnfGrpEntry 65 }

-- FRSM12   Following Object is needed if channel Status Objects in MIB 
-- "cardSpecificSM.my" on FRSM12 due to scalability issues, OAMCC per PVC 
-- will be done as this is handled by HW (ATLAS). The OAM LoopBack as 
-- on FRSM, will not be supported. FRSM12 will loop back incoming OAM loopback
-- cells originating from FRSM. But the test cannot be initiated 
-- on FRSM12 (No HW support, will be too much CPU burning for 16K Conns.) 
-- Instead of the FRSM TRAP "50311", "trapGenFrChanAlarm (50393)
-- will be used when OAM CC detects Chan Failure. 

-- added for FRSM12
frChanOamCCEnable OBJECT-TYPE
    SYNTAX	INTEGER {
                    enable (1),
                    disable (2)
                }
    MAX-ACCESS	read-write
    STATUS	current
    DESCRIPTION	
        "This object is added for FRSM12 card.

        This object serves to enable or disable continuity check(CC)
        on a connection endpoint. When continuity check is enabled 
        on an endpoint, the endpoint anticipates OAM CC cells from its
        peer endpoint. OAM CC cells are sent when the peer endpoint
        does not have traffic cells to send. If the connection is
        idle and this endpoint has not received OAM CC cells for a 
        period of 3.5 +/- 0.5 seconds, it declares continuity failure.

        This object serves to administratively control the CC feature.
        Typical implementations (of this feature) may choose to ignore
        this control or impose other conditions to actually enable CC 
        cell flow. However, if this object is set to false(2), then this 
        feature should be disabled
    
        This object is not applicable to MGX Release 1.x."
    DEFVAL { disable } 
    ::= { frChanCnfGrpEntry 66 }

frChanStatsEnable  OBJECT-TYPE
    SYNTAX	INTEGER {
                    enable  (1),
                    disable (2)
                }
    MAX-ACCESS	read-write
    STATUS	current
    DESCRIPTION
        " This object serves the purpose of enabling/disabling statistics
        collection on a per connection basis. In implementations which
        do not have such limitations, this object can be set to enable(1)
        for all connections.

        Limits imposed by software or hardware implementations
        could restrict the amount of statistical data that can be
        maintained in a physical entity (like a service module card).
        Hence there could be a need to restrict statistics collection
        to a smaller subset.

        This object is not applicable to MGX Release 1.x."
        DEFVAL { disable }
    ::= { frChanCnfGrpEntry 67 }

-- added for FRSM12
frChanLocalLpbkEnable  OBJECT-TYPE
    SYNTAX	INTEGER {
                    enable (1),
                    disable (2)
                }
    MAX-ACCESS	read-write
    STATUS	current
    DESCRIPTION
        "This object is added for FRSM12 card.
        This object when enabled adds a channel-level loopback
        towards the port side.  If the connection is in loopback,
        Connection MIB (FrChanCnfGrpEntry) variables cannot be modified.

        This object is not applicable to MGX Release 1.x.
        "
        DEFVAL { disable }
    ::= { frChanCnfGrpEntry 68 }

frChanUpcEnable  OBJECT-TYPE
    SYNTAX	INTEGER {
                    enable (1),
                    disable (2)
                }
    MAX-ACCESS	read-write
    STATUS	current
    DESCRIPTION
        "
        This object is added for FRSM12 card.

        This object when disabled, disables Frame Relay policing.

        This object is not applicable to MGX Release 1.x.
        "
    DEFVAL { enable }
    ::= { frChanCnfGrpEntry 69 }

frChanSlaveType OBJECT-TYPE
    SYNTAX  INTEGER {
                persistentSlave (1),
                nonPersistentSlave (2)
             }
    MAX-ACCESS read-write
    STATUS     current
    DESCRIPTION
        "This object is added for FRSM12 card.
        This object indicates whether a master endpoint has a persistent
        slave or not. A connection with a master and a non-persistent
        slave is considered a single-ended SPVC.

        This object is only meaningful when 'frMastership'
        contains the value of 'master(1)'. And this variable 
        must be used with 'frMastership' to decide
        if a connection is single-ended or not.

        This object is not applicable to MGX Release 1.x."
    DEFVAL { persistentSlave }
    ::= { frChanCnfGrpEntry 70 }

frConnRemoteMBS OBJECT-TYPE
    SYNTAX     Integer32 (1..5000000)
    MAX-ACCESS read-write
    STATUS     current
    DESCRIPTION
        "Remote Maximum Burst Size in terms of number of cells.
         This object should be set by the user in cases when
         the remote end of the connection is an ATM end-point
         where the Local MBS can be explicitly specified. In such
         cases, this element should be set to be equal to the
         remote end-point's local MBS.

         This object is not applicable to MGX Release 1.x.
         "
    DEFVAL {1024}
    ::= { frChanCnfGrpEntry 71 }

frChanPrefRouteId      OBJECT-TYPE
        SYNTAX     Integer32(0..65535)
        MAX-ACCESS read-write
        STATUS     current
        DESCRIPTION
	    "This object serves to to associate a preferred 
            route with a connection. 

           The value '0' means no preferred route is associated with
           this connection.

            Usage:
              - If the value of this set to 0, the object
                frChanDirectRoute is automatically set to FALSE by
                the switch.
             - The preferred route is defined in cwaPrefRouteConfTable 
               object."
        DEFVAL { 0 }
        ::= { frChanCnfGrpEntry 72 }

frChanDirectRoute       OBJECT-TYPE
        SYNTAX          TruthValue 
        MAX-ACCESS      read-write
        STATUS          current
        DESCRIPTION
	    "This object serves to associate a prefer 
            route as directed route (correspond to the prefer route
            object frChanPrefRouteId).
  
            A directed route specifies that the associated preferred
            route is the only permission route for the connection to
            take. Should the associated preferred route be unavailable,
            the connection is failed.

            The object is not applicable if there is no associated
            preferred route with the connection."
        DEFVAL { false }
        ::= { frChanCnfGrpEntry 73 }

--
--	Next available channel
--

chanNumNextAvailable 	OBJECT-TYPE
	SYNTAX	   Integer32 (16..2147483647) 
	MAX-ACCESS read-only
	STATUS	   current
	DESCRIPTION
           "This variable contains the next UNUSED channel number
	   of the maximum possible value(depends upon the
           service module). 
	   This number can be used in channel config table, the 
	   ChanNumNextAvailable gets updated if the number gets
	   used to create a logical channel.  
	   A '0' indicates that no more channels are available.
          
	   For FRSM12 Card: Not Supported."
	::= { frChanCnfGrp 2 }

-- ------------------------------------------------------------------------
--
-- frstdABRConfig group
-- Channel configurable parameters  (VC)
--
-- ------------------------------------------------------------------------
--

frstdABRCnfGrpTable	OBJECT-TYPE
    SYNTAX	SEQUENCE OF FrstdABRCnfGrpEntry
    MAX-ACCESS	not-accessible
    STATUS	current
    DESCRIPTION
        "This table is used for configuring ABR parameters
        on a frame relay connection. 
    "
    ::= { frChanCnfGrp 3 }
	
frstdABRCnfGrpEntry		OBJECT-TYPE
	SYNTAX	FrstdABRCnfGrpEntry
	MAX-ACCESS	not-accessible
	STATUS	current
	DESCRIPTION
	    "An entry in ABR Configuration table."
	INDEX	{ frstdABRcnfChanNum }
	::= { frstdABRCnfGrpTable 1 }

FrstdABRCnfGrpEntry ::=
    SEQUENCE {
        frstdABRcnfChanNum    Integer32,
        frstdABRTBE	      Integer32,
        frstdABRFRTT 	      Integer32,
        frstdABRRDF	      Integer32,
        frstdABRRIF           Integer32,
        frstdABRNrm	      Integer32,
        frstdABRTrm           Integer32,
        frstdABRCDF	      Integer32,
        frstdABRADTF          Integer32,
        frstdABRICR           Integer32,
        frstdABRMCR           Integer32,
        frstdABRPCR 	      Integer32
    }

frstdABRcnfChanNum OBJECT-TYPE
    SYNTAX Integer32(1..2147483647)
    MAX-ACCESS read-only
    STATUS current
    DESCRIPTION
        "Refers to the virtual connection index.

        The value supported depends upon the type
        of service module.

        Supported Range for different Card Types:

        FRSM-4T1/E1        : supported range is 16..271 (256 entries)
        FRSM-8T1/E1        : supported range is 16..1015 (1000 entries)
        FRSM-T3/E3/HS2/
        /HS2B-HSSI/T3B/E3B : supported range is 16..2015 (2000 entries)
        FRSM-2CT3/HS2B-12IN1: supported range is 16..4015 (4000 entries)

        FRSM12 Card:
            Byte 3 = Chassis Number, Byte 2 = Slot Number,
            Byte 1 & 0 = channel Number.
            Lower two bytes range from 16..16015 (16000 entries)
        "
    ::= { frstdABRCnfGrpEntry 1}

frstdABRTBE OBJECT-TYPE
    SYNTAX     Integer32 (0..16777215)
    UNITS      "cells"
    MAX-ACCESS read-write
    STATUS     current
    DESCRIPTION
        "The value of this object is equal to
        Transient Buffer Exposure(TBE). The TBE is a negotiated
        number of cells that the network would like to limit
        the source to sending during startup periods, before the
        first RM-cell returns."
    DEFVAL  {16777215}
    ::= { frstdABRCnfGrpEntry 2}

frstdABRFRTT OBJECT-TYPE
    SYNTAX     Integer32  (0..16700)
    UNITS      "milli-seconds"
    MAX-ACCESS read-write
    STATUS     current
    DESCRIPTION
        "The value of this object is equal to
        Fixed Round-Trip Time(FRTT). The FRTT is 
        sum of the fixed propogation delays from
        the source to a destination network.

        The Value 0 signifies that FRTT is not available."
    DEFVAL {0}
    ::= { frstdABRCnfGrpEntry 3 }

frstdABRRDF OBJECT-TYPE
    SYNTAX Integer32  (1..32768)
    MAX-ACCESS  read-write
    STATUS  current
    DESCRIPTION
        "The value of this object is equal to
        Rate Decrease Factor(RDF). The RDF controls the
        rate decrease which occurs when backward RM-cells
        with CI=1 are received. Larger values lead to faster
        rate decrease.

        The value specified has to be inverted to
        arrive at the actual value.
        The valid values possible are only powers of 2;
         i.e. 1, 2, 4, 8 ..... 32768.
        The SNMP agent has to verify this compliance."
    DEFVAL {16}
        ::= { frstdABRCnfGrpEntry 4 }

frstdABRRIF OBJECT-TYPE
    SYNTAX Integer32  (1..32768)
    MAX-ACCESS  read-write
    STATUS  current
    DESCRIPTION
        "The value of this object is equal to
        Rate Increase Factor(RIF). The RIF controls the
        rate increase which occurs when a backward RM-cell
        is received with CI=0 and NI=0. 

        The value specified has to be inverted to arrive 
        at the actual value.
        The valid values possible are only powers
        of 2; i.e. 1, 2, 4, 8 ..... 32768.
        The SNMP agent has to verify this
        compliance."
    DEFVAL {64}
    ::= { frstdABRCnfGrpEntry 5 }

frstdABRNrm OBJECT-TYPE
    SYNTAX     Integer32  (2..256)
    MAX-ACCESS read-write
    STATUS     current
    DESCRIPTION
        "The value of this object is equal to
        number of cells a source may send for each
        forward RM cell.
        The valid values possible are only powers of 2
        starting from 2; i.e. 2, 4, 8 ..... 256.
        The SNMP agent has to verify this compliance."
    DEFVAL {64}
    ::= { frstdABRCnfGrpEntry 6 }

frstdABRTrm OBJECT-TYPE
    SYNTAX     Integer32  (3..255)
    UNITS      "milli-seconds"
    MAX-ACCESS read-write
    STATUS     current
    DESCRIPTION
        "The value of this object is equal to
        Upper bound on the time between forward RM
        cells for an active source."
    DEFVAL {255}
    ::= { frstdABRCnfGrpEntry 7 }

frstdABRCDF OBJECT-TYPE
    SYNTAX     Integer32  (0..64)
    MAX-ACCESS read-write
    STATUS     current
    DESCRIPTION
        "The value of this object is equal to
        Cutoff Decrease Factor(CDF). The value specified
        has to be inverted to arrive at the actual value.
        The valid values possible are 0
        and only powers of 2; i.e., 1, 2, 4, 8, 16, 32, 64.
        The SNMP agent has to verify this compliance."
    DEFVAL {16}
    ::= { frstdABRCnfGrpEntry 8 }

frstdABRADTF OBJECT-TYPE
    SYNTAX     Integer32  (10..10230)
    UNITS      "milli-seconds"
    MAX-ACCESS  read-write
    STATUS      current
    DESCRIPTION
        "The value of this object is equal to
        ACR Decrease Time Factor(ADTF). 
        The Granularity allowed is 10 milli seconds.
        i.e. 10,20,30 etc. 
        The SNMP agent has to verify this compliance."
    DEFVAL {500}
    ::= { frstdABRCnfGrpEntry 9 }
		 
frstdABRICR OBJECT-TYPE
    SYNTAX     Integer32  (10..400000)
    UNITS      "cells-per-second"
    MAX-ACCESS read-write
    STATUS     current
    DESCRIPTION
        "The value of this object is equal to
        Initial Cell Rate(ICR). The ICR is the rate at which 
        the source should send initially and after an idle period.
        This includes the bandwidth allocated for both data cells 
        as well as all in-rate RM cells."
    DEFVAL {10}
    ::= { frstdABRCnfGrpEntry 10 }

frstdABRMCR OBJECT-TYPE
    SYNTAX     Integer32  (10..400000)
    UNITS      "cells-per-second"
    MAX-ACCESS read-write
    STATUS     current
    DESCRIPTION
        "The value of this object is equal to
        Minimum Cell Rate(MCR). The MCR is the rate at which 
        the source is allowed to send. This includes the bandwidth
        allocated for both data cells as well as all in-rate RM cells."
    DEFVAL {10}
    ::= { frstdABRCnfGrpEntry 11 }

frstdABRPCR OBJECT-TYPE
    SYNTAX     Integer32  (10..400000)
    UNITS      "cells-per-second"
    MAX-ACCESS read-write
    STATUS     current
    DESCRIPTION
        "The value of this object is equal to
        Peak Cell Rate(PCR). The PCR is the rate at which 
        the source is allowed to send. This includes the
        bandwidth allocated for both data cells as well as
        all in-rate RM cells."
    DEFVAL {10}
    ::= { frstdABRCnfGrpEntry 12 }



frChanStateGrp 	OBJECT IDENTIFIER ::= { frChan 2 }

-- ------------------------------------------------------------------------
--
-- Group frChannelState
-- Contains status information for channels(Frame relay Connections)
--
-- ------------------------------------------------------------------------


frChanStateGrpTable OBJECT-TYPE
    SYNTAX  SEQUENCE OF FrChanStateGrpEntry
    MAX-ACCESS  not-accessible
    STATUS  current
    DESCRIPTION
        "Table of transmit/receive states of channels."
    ::= { frChanStateGrp 1 }

frChanStateGrpEntry OBJECT-TYPE
    SYNTAX FrChanStateGrpEntry
    MAX-ACCESS not-accessible
    STATUS current
    DESCRIPTION
        "An entry for FrChannelStateGrpEntry."
    INDEX	{ stateChanNum }
    ::= { frChanStateGrpTable 1 }

FrChanStateGrpEntry ::=
    SEQUENCE {
        stateChanNum     Integer32,
        chanState        INTEGER,
        xmtAbitState     INTEGER,
        rcvAbitState     INTEGER,
        xmtATMState      INTEGER,
        rcvATMState      INTEGER,
        chanStatusBitMap Integer32
    }

stateChanNum OBJECT-TYPE
    SYNTAX      Integer32(1..2147483647)
    MAX-ACCESS	read-only
    STATUS	current
    DESCRIPTION		  
        "The value of this object refers to 
        frame relay connection.

        The value must be same as the value of
        the object 'chanNum' in frChanCnfGrpTable."
    ::= { frChanStateGrpEntry 1}

chanState OBJECT-TYPE
    SYNTAX  INTEGER {
                notConfigured(1),
                okay(2),
                alarm(3),
                failed(4)
            }
    MAX-ACCESS  read-only
    STATUS  current
    DESCRIPTION
        "This variable indicates the LMI state of the
        VC (channel).
        The possible values are :
           notConfigured(1): Connection Not configured
           okay(2)         : Connection is in Ok state
           alarm(3)        : Connection is in alarm
           failed(4)       : Connection is in failed state.
                             This is applicable only for PNNI."
    ::= { frChanStateGrpEntry 2}
 
xmtAbitState OBJECT-TYPE
    SYNTAX INTEGER { 
               off(1),
               sendingAequal1(2),
               sendingAequal0(3)
           }
    MAX-ACCESS read-only
    STATUS     current
    DESCRIPTION
        "The value of this object identifies the
        A bit transmit state.
 
        The possible values are :
    
          off(1)            :  LMI is off
          sendingAequal1(2) :  LMI is on and connection is O.K.
          sendingAequal0(3) :  LMI is on and connection is failed."
    ::= { frChanStateGrpEntry 3}

rcvAbitState OBJECT-TYPE
    SYNTAX INTEGER {
                off(1),
                rcvingAequal1(2),
                rcvingAequal0(3)
            }
    MAX-ACCESS read-only
    STATUS current
    DESCRIPTION
        "The value of this object identifies the
        A bit receive state.
 
        The possible values are :
    
          off(1)            :  LMI is off
          rcvingAequal1(2)  :  LMI is on and connection is O.K.
          rcvingAequal0(3)  :  LMI is on and connection is failed."
    ::= { frChanStateGrpEntry 4}

xmtATMState OBJECT-TYPE
    SYNTAX  INTEGER {
                notSending(1),
                sendingAIS(2),
                sendingFERF(3)
            }
    MAX-ACCESS  read-only
    STATUS  current
    DESCRIPTION
        "This variable indicates the transmit state of the
        VC (channel) on the ATM side.

        The possible values are :

          notSending(1)   : Not sending any state
          sendingAIS(2)   : Sending AIS OAM state
          sendingFERF(2)  : Sending FERF OAM state."
    ::= { frChanStateGrpEntry 5}
 
rcvATMState OBJECT-TYPE
    SYNTAX  INTEGER {
                notRcving(1),
                rcvingAIS(2),
                rcvingFERF(3)
            }
    MAX-ACCESS  read-only
    STATUS  current
    DESCRIPTION
        "This variable indicates the receive state of the
        VC (channel) on the ATM side.

        The possible values are :

        notRcving(1)   : Not receiving any state
        rcvingAIS(2)   : Receiving AIS OAM 
        rcvingFERF(2)  : Receiving FERF OAM."
    ::= { frChanStateGrpEntry 6}

chanStatusBitMap OBJECT-TYPE
    SYNTAX  Integer32 (0..'ff'h)
    MAX-ACCESS  read-only
    STATUS  current
    DESCRIPTION
        "This variable indicates the consolidated bit map of the channel alarm
        state.

        Individual bit positions are as defined below.

        Bit position   Fail/Alarm     Reason
        ------------   ----------     ------
            0           Alarm         Reserved
            1           Alarm         n/w side AIS/RDI Rx
            2           Fail          Conditioned(A bit from n/w)
            3           Alarm         Reserved         
            4           Fail          CC failed/RAS failed
            5           Fail          Mismatch
            6           Alarm         ingress A bit (LMI)
            7           Alarm         Reserved

            Fail bitmap mask : 0x34
            Alarm bitmap mask: 0xCB

            This object is not applicable to MGX Release 1.x.
        "

    ::= { frChanStateGrpEntry 7}


frEndPtMapGrp  	OBJECT IDENTIFIER ::= { frameRelay 3 }

frEndPtMapGrpTable OBJECT-TYPE
SYNTAX  SEQUENCE OF FrEndPtMapGrpEntry
    MAX-ACCESS  not-accessible
    STATUS  current
    DESCRIPTION
        "This is the Endpoint Mapping table for
        Frame Relay connections."
    ::= { frEndPtMapGrp 1 }

frEndPtMapGrpEntry OBJECT-TYPE
    SYNTAX FrEndPtMapGrpEntry
    MAX-ACCESS not-accessible
    STATUS current
    DESCRIPTION
        "An entry in the frame relay connection Endpoint
        table."
    INDEX  { endPortNum, endDLCI }
    ::= { frEndPtMapGrpTable 1 }

FrEndPtMapGrpEntry ::=
    SEQUENCE {
        endPortNum    Integer32,
        endDLCI       Integer32,
        endChanNum    Integer32,
        endLineNum    Integer32
    }

endPortNum OBJECT-TYPE
    SYNTAX      Integer32(1..2147483647)
    MAX-ACCESS	read-only
    STATUS	current
    DESCRIPTION		  
        "This object identifies the frame relay logical port.
         The value for this object must be same as 'portNum'
         object in frPortCnfPortGrpTable.

        If ifTable is is implemented in a service module,
        this object must be same as the ifIndex of frame relay port."
    ::= { frEndPtMapGrpEntry 1}

endDLCI OBJECT-TYPE
    SYNTAX     Integer32 (0..8388607)
    MAX-ACCESS read-only
    STATUS     current
    DESCRIPTION
        "The value of this object is equal to the
        DLCI value for this PVC endpoint."
    ::= { frEndPtMapGrpEntry 2}
 
endChanNum OBJECT-TYPE
    SYNTAX     Integer32(1..2147483647)
    MAX-ACCESS read-only
    STATUS     current
    DESCRIPTION
        "The value of this object identifies the
        frame relay connection number.

        The value of this object is same as the
        value of 'chanNum' object in frChanCnfGrpTable.

        This object contains value 0, if 
        port.dlci is a multicast group."
    ::= { frEndPtMapGrpEntry 3}

endLineNum OBJECT-TYPE
    SYNTAX     Integer32(1..2147483647)
    MAX-ACCESS read-only
    STATUS     current
    DESCRIPTION
        "The value of this object is equal to the physical
        line(for example T1/E1) or ifIndex on which connection
        is provisioned.

        If ifTable is not implemented in a service module,
        then the range is from 1 to Maximum number of lines
        supported.

        If ifTable is is implemented in a service module,
        this object must be same as the ifIndex of the 
        interface (ifType=ds1(18),ds3(30)).

        The value supported for this object depends upon
        the type of service module:
           FRSM-4T1/E1   :  Range is from  1..4
           FRSM-8T1/E1   :  Range is from  1..8
           FRSM-T3/E3/HS2:  Range is from  1..2
           FRSM-2CT3     :  Range is from  1..56

           with ifTable Support: must refer to ifIndex
                                 of the interface.
        "
    ::= { frEndPtMapGrpEntry 4}


-- conformance information

ciscoWanFrConnMIBConformance OBJECT IDENTIFIER ::= { ciscoWanFrConnMIB 2 }

ciscoWanFrConnMIBGroups      OBJECT IDENTIFIER ::= { ciscoWanFrConnMIBConformance 1 }
ciscoWanFrConnMIBCompliances OBJECT IDENTIFIER ::= { ciscoWanFrConnMIBConformance 2 }


-- compliance statements

ciscoWanFrConnCompliance MODULE-COMPLIANCE
    STATUS  current
    DESCRIPTION
        "The compliance statement for SNMP entities 
         which support Frame realy connection MIB."
    MODULE  -- this module
        MANDATORY-GROUPS {
            ciscoWanFrConnGroup,
            ciscoWanFrConnTestGroup,
            ciscoWanFrConnStateGroup,
            ciscoWanFrConnEndptGroup,
            ciscoWanFrConnABRGroup
        }
    GROUP ciscoWanFrConnForesightGroup
    DESCRIPTION 
        "This group is mandatory for those systems where
        foresight feature is supported."
    GROUP ciscoWanFrConnQueueGroup
    DESCRIPTION 
        "This group is mandatory for those systems where
        threshold configuration for queue is supported."
    ::= { ciscoWanFrConnMIBCompliances 1 }

ciscoWanFrConnGroup OBJECT-GROUP
    OBJECTS {
        chanNum,			
        chanRowStatus,         	 
        chanPortNum,          
        dLCI,        
        egressQSelect,     	
        deTaggingEnable,
        cir,
        bc,
        be,
        ibs,
        chanLocRmtLpbkState,
        chanType,
        chanFECNconfig,
        chanDEtoCLPmap,
        chanCLPtoDEmap,
        chanIngrPercentUtil,	
        chanEgrPercentUtil,
        chanEgrSrvRate,
        chanOvrSubOvrRide,
        chanFrConnType,
        frCDRNumber,
        frLocalVpi,
        frLocalVci,
        frLocalNSAP,
        frRemoteVpi,
        frRemoteVci,
        frRemoteNSAP,
        frMastership,
        frVpcFlag,
        frConnServiceType,
        frRoutingPriority,
        frMaxCost,
        frRestrictTrunkType,
        frConnPCR,
        frConnRemotePCR,
        frConnMCR,
        frConnRemoteMCR,
        frConnPercentUtil,
        frConnRemotePercentUtil,
        frConnForeSightEnable,
        frConnFGCRAEnable,
        chanServType,
        chanServiceRateOverride,
        chanServiceRate,	
        zeroCirConEir,
        chanReroute,
        frConnSCR,
        frConnRemoteSCR,
        frConnTemplateId,
        frConnAdminStatus,
        frChanCnfChangeCount, 
        frChanCnfIgnoreIncomingDE,  
        frChanOamCCEnable,
        frChanStatsEnable ,    
        frChanLocalLpbkEnable, 
        frChanUpcEnable,
        frChanSlaveType,
        frConnRemoteMBS,
        chanNumNextAvailable,
        frChanPrefRouteId,
        frChanDirectRoute
    }
    STATUS current
    DESCRIPTION 
        "A collection of objects providing information
        applicable to a Frame Relay Connection."
    ::= { ciscoWanFrConnMIBGroups 1 }

ciscoWanFrConnForesightGroup OBJECT-GROUP
    OBJECTS {
        foreSightEnable,
        qir,
        mir,
        pir
    }
    STATUS current
    DESCRIPTION 
        "A collection of objects related to foresight
        feature of a frame realay connection."
    ::= { ciscoWanFrConnMIBGroups 2 }

ciscoWanFrConnQueueGroup OBJECT-GROUP
    OBJECTS {
        ingressQDepth,    	
        ingressQDEThresh,	
        ingressQECNThresh,
        egressQDepth,
        egressQDEThresh,	   	
        egressQECNThresh
    }
    STATUS current
    DESCRIPTION 
        "A collection of objects related to queue depth
        egress/ingress thresholds."
    ::= { ciscoWanFrConnMIBGroups 3 }

ciscoWanFrConnTestGroup OBJECT-GROUP
    OBJECTS {
        chanTestType,
        chanTestState,
        chanRTDResult
    }
    STATUS current
    DESCRIPTION 
        "A collection of objects related to testing
        Frame relay connections."
    ::= { ciscoWanFrConnMIBGroups 4 }

ciscoWanFrConnStateGroup OBJECT-GROUP
    OBJECTS {
        stateChanNum,
        chanState,
        xmtAbitState,
	rcvAbitState,
	xmtATMState,
	rcvATMState,
	chanStatusBitMap
    }
    STATUS current
    DESCRIPTION 
        "A collection of objects related to state
        of Frame Relay connections."
    ::= { ciscoWanFrConnMIBGroups 5 }

ciscoWanFrConnEndptGroup OBJECT-GROUP
    OBJECTS {
        endPortNum,
	endDLCI,
	endChanNum,
	endLineNum
    }
    STATUS current
    DESCRIPTION 
        "A collection of objects related to Endpoint
        mapping in Frame Relay Connections."
    ::= { ciscoWanFrConnMIBGroups 6 }

ciscoWanFrConnABRGroup OBJECT-GROUP
    OBJECTS {

        frstdABRcnfChanNum,
	frstdABRTBE,
	frstdABRFRTT,
	frstdABRRDF,
	frstdABRRIF,
	frstdABRNrm,
	frstdABRTrm,
	frstdABRCDF,
	frstdABRADTF,
	frstdABRICR,
	frstdABRMCR,
	frstdABRPCR
    }
    STATUS current
    DESCRIPTION 
        "A collection of objects related to ABR 
        in a frame relay connection."
    ::= { ciscoWanFrConnMIBGroups 7 }

END
