-- *****************************************************************
-- CISCO-CABLE-WIDEBAND-CAPABILITY.my:  CISCO-CABLE-WIDEBAND-MIB.my
-- AGENT-CAPABILITIES
--   
-- July 2006, Wasim Mohammad
--   
-- Copyright (c) 2006, 2010 by cisco Systems Inc.
-- All rights reserved.
-- *****************************************************************

CISCO-CABLE-WIDEBAND-CAPABILITY DEFINITIONS ::= BEGIN

IMPORTS
    MODULE-IDENTITY,
    Unsigned32
        FROM SNMPv2-SMI
    AGENT-CAPABILITIES
        FROM SNMPv2-CONF
    StorageType
        FROM SNMPv2-TC
    InetAddressType
        FROM INET-ADDRESS-MIB
    ciscoAgentCapability
        FROM CISCO-SMI;


ciscoCableWidebandCapability MODULE-IDENTITY
    LAST-UPDATED    "201006090000Z"
    ORGANIZATION    "Cisco Systems, Inc."
    CONTACT-INFO
            "Cisco Systems
            Customer Service

            Postal: Cisco Systems
            170 West Tasman Drive
            San Jose, CA 95134
            U.S.A.
            Phone:  +1 800 553-NETS
            E-mail: cs-ubr@cisco.com"
    DESCRIPTION
        "Agent capabilities for CISCO-CABLE-WIDEBAND-MIB"
    REVISION        "201006090000Z"
    DESCRIPTION
        "Add notInService status for ccwbRFChannelRowStatus"
    REVISION        "200609070000Z"
    DESCRIPTION
        "This is the Initial version"
    ::= { ciscoAgentCapability 520 }



ciscoCableWidebandCapabilityV12R00 AGENT-CAPABILITIES
    PRODUCT-RELEASE "Cisco IOS 12.3BC"
    STATUS          current
    DESCRIPTION
        "Cisco Cable Wideband MIB capabilities."

    SUPPORTS        CISCO-CABLE-WIDEBAND-MIB
    INCLUDES        { ccwbWidebandObjGroup }
    VARIATION       ccwbRFChannelStorageType
    SYNTAX          StorageType {
                        volatile(2)
                    }
    DESCRIPTION
        "Only storage type 'volatile' is supported."

    VARIATION       ccwbRFChanQamTos
    ACCESS          not-implemented
    DESCRIPTION
        "This object is not supported"

    VARIATION       ccwbRFChanQamVlanId
    ACCESS          not-implemented
    DESCRIPTION
        "This object is not supported"

    VARIATION       ccwbRFChanQamPriorityBits
    ACCESS          not-implemented
    DESCRIPTION
        "This object is not supported"

    VARIATION       ccwbWBtoNBRowStatus
    ACCESS          read-only
    DESCRIPTION
        "read-only is implemented"

    VARIATION       ccwbWBtoNBStorageType
    SYNTAX          StorageType {
                        volatile(2)
                    }
    ACCESS          read-only
    DESCRIPTION
        "Only storage type 'volatile' is
        supported.  Write/Create is not implemented"

    VARIATION       ccwbWBtoRFStorageType
    SYNTAX          StorageType {
                        volatile(2)
                    }
    DESCRIPTION
        "Only storage type 'volatile' is supported."

    VARIATION       ccwbWBtoRFRowStatus
    SYNTAX          INTEGER  {
                        active(1),
                        createAndGo(4),
                        destroy(6)
                    }
    DESCRIPTION
        "Only enumerations active(1), createAndGo(4) and destroy(6)
        are supported."

    VARIATION       ccwbFiberNodeDescription
    ACCESS          read-only
    DESCRIPTION
        "Write/Create is not implemented"

    VARIATION       ccwbFiberNodeDescrStorageType
    SYNTAX          StorageType {
                        volatile(2)
                    }
    ACCESS          read-only
    DESCRIPTION
        "Only storage type 'volatile' is
        supported.  Write/Create is not implemented"

    VARIATION       ccwbFiberNodeDescrRowStatus
    ACCESS          read-only
    DESCRIPTION
        "Write/Create is not implemented"

    VARIATION       ccwbFiberNodeNBIfIndx
    ACCESS          read-only
    DESCRIPTION
        "Write/Create is not implemented"

    VARIATION       ccwbFiberNodeWBContlrPhyIndx
    ACCESS          read-only
    DESCRIPTION
        "Write/Create is not implemented"

    VARIATION       ccwbFiberNodeWBRFPort
    ACCESS          read-only
    DESCRIPTION
        "Write/Create is not implemented"

    VARIATION       ccwbFiberNodeStorageType
    SYNTAX          StorageType {
                        volatile(2)
                    }
    ACCESS          read-only
    DESCRIPTION
        "Only storage type 'volatile' is
        supported.  Write/Create is not implemented"

    VARIATION       ccwbFiberNodeRowStatus
    ACCESS          read-only
    DESCRIPTION
        "Write/Create is not implemented"

    VARIATION       ccwbRFChannelFrequency
    SYNTAX          Unsigned32 (55000000..858000000)
    DESCRIPTION
        "A range of 54MHz to 860MHz is appropriate for a cable
        plant using a North American Sub-Split channel plan.
        The spectrum range has been expanded to accommodate
        a lower edge of 47MHz and an upper edge of 862MHz
        for some European channel plans."

    VARIATION       ccwbRFChannelWidth
    ACCESS          read-only
    DESCRIPTION
        "Write/Create is not implemented.The value of 6 MHz
        is appropriate for cable plants running under
        NTSC (National Television Standards Committee) standards.
        The value of 8 MHz is appropriate for cable plants
        running under ETSI standards."

    VARIATION       ccwbRFChannelRowStatus
    SYNTAX          INTEGER  {
                        active(1),
                        createAndGo(4),
                        destroy(6)
                    }
    DESCRIPTION
        "Only enumerations active(1), createAndGo(4) and destroy(6)
        are supported."

    VARIATION       ccwbRFChannelAnnex
    ACCESS          read-create
    DESCRIPTION
        "The value of this object must be same for all
        RF channels."

    VARIATION       ccwbRFChannelModulation
    DESCRIPTION
        "Currently the value of this object must be the same for
        all RF channels."

    VARIATION       ccwbRFChanQamIPAddressType
    SYNTAX          InetAddressType {
                        ipv4(1)
                    }
    DESCRIPTION
        "Only Internet address type 'ipv4' is supported."

    VARIATION       ccwbWBCmStatusValue
    ACCESS          read-only
    DESCRIPTION
        "Current WB Cable Modem connectivity state, as specified
        in the RF Interface Specification. Returned status
        information is the WCM status as assumed by the WCMTS"

    ::= { ciscoCableWidebandCapability 1 }

ciscoCableWidebandCapabilityV122R00 AGENT-CAPABILITIES
    PRODUCT-RELEASE "Cisco IOS 12.2S"
    STATUS          current
    DESCRIPTION
        "Cisco Cable Wideband MIB capabilities."

    SUPPORTS        CISCO-CABLE-WIDEBAND-MIB
    INCLUDES        { ccwbWidebandObjGroup }
    VARIATION       ccwbRFChannelRowStatus
    SYNTAX          INTEGER  {
                        active(1),
                        notInService(2),
                        createAndGo(4),
                        destroy(6)
                    }
    DESCRIPTION
        "Only enumerations active(1), notInService(2), createAndGo(4)
        and destroy(6) are supported."

    ::= { ciscoCableWidebandCapability 2 }

END
