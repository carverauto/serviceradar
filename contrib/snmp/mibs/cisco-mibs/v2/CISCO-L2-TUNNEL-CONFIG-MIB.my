-- *****************************************************************
-- Cisco L2 Tunnel Config MIB
--   
-- April,    2002 Binh Le
-- September,   2003 Seth Wang
--   
-- Copyright (c) 2002-2007 by Cisco Systems, Inc.
--   
-- All rights reserved.
-- ****************************************************************

CISCO-L2-TUNNEL-CONFIG-MIB DEFINITIONS ::= BEGIN

IMPORTS
    MODULE-IDENTITY,
    OBJECT-TYPE,
    NOTIFICATION-TYPE,
    Unsigned32,
    Counter32
        FROM SNMPv2-SMI
    MODULE-COMPLIANCE,
    OBJECT-GROUP,
    NOTIFICATION-GROUP
        FROM SNMPv2-CONF
    TruthValue
        FROM SNMPv2-TC
    ifIndex
        FROM IF-MIB
    QosLayer2Cos
        FROM CISCO-QOS-PIB-MIB
    ciscoMgmt
        FROM CISCO-SMI;


ciscoL2TunnelConfigMIB MODULE-IDENTITY
    LAST-UPDATED    "200702150000Z"
    ORGANIZATION    "Cisco Systems Inc."
    CONTACT-INFO
            "Cisco Systems
            Customer Service

            Postal: 170 W Tasman Drive
                    San Jose, CA 95134
                    USA

            Tel: +1 800 553-NETS

            Email: cs-lan-switch-snmp@cisco.com"
    DESCRIPTION
        "This MIB module is for layer 2 tunneling related configurations
        on a device.

        Tunneling allows separate local networks to be considered as
        a single VLAN. These separate networks are connected via an
        ISP, which will tunnel the packets from one network to another,
        making it appear as if the two networks are actually just one."
    REVISION        "200702150000Z"
    DESCRIPTION
        "Modify the descriptions of cltcTunneledProtocolType and
        cltcTunnelShutdownThreshold.

        Add 'lldp(4)' to cltcTunneledProtocolType,
        'lldp(6)' to cltcTunnelThresholdProtocolIndex and
        'lldp(6)' to cltcTunneledProtocolIndex.

        Add new groups cltcTunnelTotalDropGroup,
        cltcTunnelSysDropNotifEnableGroup,
        cltcTunnelSysDropGroup,
        cltcTunnelSysDropNotifGroup."
    REVISION        "200607250000Z"
    DESCRIPTION
        "Modify the descriptions of cltcTunneledProtocolType and
        cltcTunnelShutdownThreshold."
    REVISION        "200506270000Z"
    DESCRIPTION
        "Add 'eoam(3)' to cltcTunneledProtocolType,
        'eoam(5)' to cltcTunnelThresholdProtocolIndex and
        'eoam(5)' to cltcTunneledProtocolIndex."
    REVISION        "200406090000Z"
    DESCRIPTION
        "Change the description for cltcTunnelThresholdProtocolIndex.
        Add the new groups cltcTunnelThresholdNotifsGroup and
        cltcNotifsEnableGroup."
    REVISION        "200309030000Z"
    DESCRIPTION
        "Add a new object cltcTunnelDropStats. Remove the restriction
        for enabling cltcDot1qTunnelMode from the description."
    REVISION        "200205311000Z"
    DESCRIPTION
        "Add SNMP support for 802.1q All Tagged (dot1q-all-tagged)
        Per Port feature.

        Dot1q-all-tagged feature is an enhancement to tag the packets 
        on the native vlan to avoid any confusion in the ISP network,
        and to avoid vlan hopping when the native vlan for the trunk
        is as same as the vlan assigned for a customer.

        Before this enhancement, this feature can be enabled/disabled 
        globally through the vlanTrunkPortsDot1qTag object in 
        CISCO-VTP-MIB. With this enhacement, vlanTrunkPortsDot1qTag 
        object in CISCO-VTP-MIB is deprecated and replaced by the 
        dot1qAllTaggedEnabled object in this MIB. Additionally, 
        dot1q-all-tag will be able to configure per port basis."
    REVISION        "200202140000Z"
    DESCRIPTION
        "Initial version of this MIB module."
          ::= { ciscoMgmt 246 }


cltcMIBObjects  OBJECT IDENTIFIER
    ::= { ciscoL2TunnelConfigMIB 1 }

cltcGlobal  OBJECT IDENTIFIER
    ::= { cltcMIBObjects 1 }

cltcDot1qTunnel  OBJECT IDENTIFIER
    ::= { cltcMIBObjects 2 }

cltcTunneledProtocol  OBJECT IDENTIFIER
    ::= { cltcMIBObjects 3 }

cltcTunnelThreshold  OBJECT IDENTIFIER
    ::= { cltcMIBObjects 4 }

cltcTunnelStatistics  OBJECT IDENTIFIER
    ::= { cltcMIBObjects 5 }

-- MIB objects for 802.1q All Tagged Per Port(dot1q-all-tagged) feature.
cltcDot1qAllTagged  OBJECT IDENTIFIER
    ::= { cltcMIBObjects 6 }


-- cltcTunnelCos
cltcTunnelCos OBJECT-TYPE
    SYNTAX          QosLayer2Cos
    MAX-ACCESS      read-write
    STATUS          current
    DESCRIPTION
        "Specifies the user priority of the tunneled PDUs and applies
        to all ingress tunneling interfaces." 
    ::= { cltcGlobal 1 }

cltcNotificationEnable OBJECT-TYPE
    SYNTAX          TruthValue
    MAX-ACCESS      read-write
    STATUS          current
    DESCRIPTION
        "This object indicates whether the system will
        generate the cltcTunnelDropThresholdExceeded and
        cltcTunnelShutdownThresholdExceeded notifications." 
    ::= { cltcGlobal 2 }

cltcTunnelSysDropThreshold OBJECT-TYPE
    SYNTAX          Unsigned32
    UNITS           "PDUs/sec"
    MAX-ACCESS      read-write
    STATUS          current
    DESCRIPTION
        "This object specifies the drop threshold at the
        system level.  A value of zero indicates that
        system level rate limiting is disabled." 
    ::= { cltcGlobal 3 }

cltcTunnelSysDropNotifEnable OBJECT-TYPE
    SYNTAX          TruthValue
    MAX-ACCESS      read-write
    STATUS          current
    DESCRIPTION
        "This object specifies whether the system will generate
        the cltcTunnelSysDropThresholdExceeded notification." 
    ::= { cltcGlobal 4 }
-- cltcDot1qTunnelTable

cltcDot1qTunnelTable OBJECT-TYPE
    SYNTAX          SEQUENCE OF CltcDot1qTunnelEntry 
    MAX-ACCESS      not-accessible
    STATUS          current
    DESCRIPTION
        "This table contains information about the dot1q tunnel
        interfaces. Only dot1q tunneling capable interfaces are shown.
        1Q-in-1Q will allow service providers to separate the traffic
        of various customers within their infrastructure while the
        customers appear to be on the same VLANs."
    ::= { cltcDot1qTunnel 1 }

cltcDot1qTunnelEntry OBJECT-TYPE
    SYNTAX          CltcDot1qTunnelEntry
    MAX-ACCESS      not-accessible
    STATUS          current
    DESCRIPTION
        "Information about the dot1q tunnel. Only dot1q tunneling
        capable interfaces are shown."
    INDEX           { ifIndex } 
    ::= { cltcDot1qTunnelTable 1 }

CltcDot1qTunnelEntry ::= SEQUENCE {
        cltcDot1qTunnelMode INTEGER 
}

cltcDot1qTunnelMode OBJECT-TYPE
    SYNTAX          INTEGER  {
                        enabled(1),
                        disabled(2)
                    }
    MAX-ACCESS      read-write
    STATUS          current
    DESCRIPTION
        "Indicates the dot1q tunnel mode of the interface.

        Setting the interface to dot1q tunnel 'disabled' mode causes
        the dot1q tunnel feature to be disabled on this interface.
        Setting the interface to dot1q tunnel 'enabled' mode causes
        the dot1q tunnel feature to be enabled on this interface."
    DEFVAL          { disabled } 
    ::= { cltcDot1qTunnelEntry 1 }
 

-- cltcTunneledProtocolTable

cltcTunneledProtocolTable OBJECT-TYPE
    SYNTAX          SEQUENCE OF CltcTunneledProtocolEntry 
    MAX-ACCESS      not-accessible
    STATUS          current
    DESCRIPTION
        "This table contains information about the protocols being
        tunneled. Only tunneled protocol filtering capable interfaces
        are shown."
    ::= { cltcTunneledProtocol 1 }

cltcTunneledProtocolEntry OBJECT-TYPE
    SYNTAX          CltcTunneledProtocolEntry
    MAX-ACCESS      not-accessible
    STATUS          current
    DESCRIPTION
        "Information about the protocols being tunneled. Only tunneled
        protocol filtering capable interfaces are shown."
    INDEX           { ifIndex } 
    ::= { cltcTunneledProtocolTable 1 }

CltcTunneledProtocolEntry ::= SEQUENCE {
        cltcTunneledProtocolType BITS
}

cltcTunneledProtocolType OBJECT-TYPE
    SYNTAX          BITS {
                        cdp(0),
                        vtp(1),
                        stp(2),
                        eoam(3),
                        lldp(4)
                    }
    MAX-ACCESS      read-write
    STATUS          current
    DESCRIPTION
        "Indicates tunneled protocol of the interface.

        If a BIT is set, then the value of the corresponding
        protocol is tunneled. Specifically, if the 'cdp(0)'
        BIT is set, then the Cisco Discovery Protocol PDU is
        tunneled; if the 'vtp(1)' BIT is set, then the VLAN
        Trunking Protocol PDU is tunneled; if the 'stp(2)' BIT
        is set, then the Spanning Tree Protocol PDU is tunneled;
        if the 'eoam(3)' BIT is set, then the ethernet Operation,
        Administration and Maintenance PDU is tunneled; if the
        'lldp(4)' BIT is set, then the Link Layer Discovery
        Protocol is tunneled.

        If the bit for a given protocol is set for an interface, then
        the statistics for that interface and protocol will start to be
        monitored." 
    ::= { cltcTunneledProtocolEntry 1 }
 

-- cltcTunnelThresholdTable

cltcTunnelThresholdTable OBJECT-TYPE
    SYNTAX          SEQUENCE OF CltcTunnelThresholdEntry 
    MAX-ACCESS      not-accessible
    STATUS          current
    DESCRIPTION
        "This table contains information about the thresholds for
        protocol tunneling. Only tunneled protocol filtering capable
        interfaces are shown. The objects will be on a per interface,
        per protocol basis."
    ::= { cltcTunnelThreshold 1 }

cltcTunnelThresholdEntry OBJECT-TYPE
    SYNTAX          CltcTunnelThresholdEntry
    MAX-ACCESS      not-accessible
    STATUS          current
    DESCRIPTION
        "Information about the thresholds for protocol tunneling. Only
        tunneled protocol filtering capable interfaces are shown. The
        entries will be on a per interface, per protocol basis"
    INDEX           {
                        ifIndex,
                        cltcTunnelThresholdProtocolIndex
                    } 
    ::= { cltcTunnelThresholdTable 1 }

CltcTunnelThresholdEntry ::= SEQUENCE {
        cltcTunnelThresholdProtocolIndex INTEGER,
        cltcTunnelDropThreshold          Unsigned32,
        cltcTunnelShutdownThreshold      Unsigned32
}

cltcTunnelThresholdProtocolIndex OBJECT-TYPE
    SYNTAX          INTEGER {
                        all(1),
                        cdp(2),
                        vtp(3),
                        stp(4),
                        eoam(5),
                        lldp(6)
                    }
    MAX-ACCESS      not-accessible
    STATUS          current
    DESCRIPTION
        "A tunneled protocol of an interface.

        - all(1) is supported for devices which allow the setting
          of thresholds on a per interface basis. This threshold is
          a combined threshold for the interface which includes all
          supported protocols.

        - cdp(2), vtp(3), stp(4), eoam(5) and lldp(6) are supported
          for devices which allow the setting of thresholds on a
          per interface, per protocol basis." 
    ::= { cltcTunnelThresholdEntry 1 }

cltcTunnelDropThreshold OBJECT-TYPE
    SYNTAX          Unsigned32
    UNITS           "PDUs/sec"
    MAX-ACCESS      read-write
    STATUS          current
    DESCRIPTION
        "The drop threshold on an interface for a given protocol. After
        reaching this drop threshold, the interface will start dropping
        PDUs for the given protocol. This value cannot be greater than
        the value of cltcTunnelShutdownThreshold.  A value of 0
        indicates that no limit is set."
    DEFVAL          { 0 } 
    ::= { cltcTunnelThresholdEntry 2 }

cltcTunnelShutdownThreshold OBJECT-TYPE
    SYNTAX          Unsigned32
    UNITS           "PDUs/sec"
    MAX-ACCESS      read-write
    STATUS          current
    DESCRIPTION
        "The shutdown threshold on an interface for a given protocol.
        After reaching the shutdown threshold, the interface will
        shutdown for the given protocol.  This value cannot be less
        than the value of cltcTunnelDropThreshold. A value of 0
        indicates that no limit is set."
    DEFVAL          { 0 } 
    ::= { cltcTunnelThresholdEntry 3 }
 

-- cltcTunnelStatisticsTable

cltcTunnelStatisticsTable OBJECT-TYPE
    SYNTAX          SEQUENCE OF CltcTunnelStatisticsEntry 
    MAX-ACCESS      not-accessible
    STATUS          current
    DESCRIPTION
        "This table contains protocol tunneling statistics on the
        interface."
    ::= { cltcTunnelStatistics 1 }

cltcTunnelStatisticsEntry OBJECT-TYPE
    SYNTAX          CltcTunnelStatisticsEntry
    MAX-ACCESS      not-accessible
    STATUS          current
    DESCRIPTION     "Protocol tunneling statistics on the interface."
    INDEX           {
                        ifIndex,
                        cltcTunneledProtocolIndex
                    } 
    ::= { cltcTunnelStatisticsTable 1 }

CltcTunnelStatisticsEntry ::= SEQUENCE {
        cltcTunneledProtocolIndex INTEGER ,
        cltcTunnelEncapStats      Counter32,
        cltcTunnelDeEncapStats    Counter32,
        cltcTunnelDropStats       Counter32
}

cltcTunneledProtocolIndex OBJECT-TYPE
    SYNTAX          INTEGER  {
                        cdp(2),
                        vtp(3),
                        stp(4),
                        eoam(5),
                        lldp(6)
                    }
    MAX-ACCESS      not-accessible
    STATUS          current
    DESCRIPTION     "A tunneled protocol of an interface." 
    ::= { cltcTunnelStatisticsEntry 1 }

cltcTunnelEncapStats OBJECT-TYPE
    SYNTAX          Counter32
    UNITS           "encapsulated PDUs"
    MAX-ACCESS      read-only
    STATUS          current
    DESCRIPTION
        "The tunneled PDU encapsulation statistics of an interface.
        These statistics cover the number of tunneled ingress
        PDUs." 
    ::= { cltcTunnelStatisticsEntry 2 }

cltcTunnelDeEncapStats OBJECT-TYPE
    SYNTAX          Counter32
    UNITS           "de-encapsulated PDUs"
    MAX-ACCESS      read-only
    STATUS          current
    DESCRIPTION
        "The tunneled PDU de-encapsulation statistics of an interface.
        These statistics cover the number of tunneled egress PDUs." 
    ::= { cltcTunnelStatisticsEntry 3 }

cltcTunnelDropStats OBJECT-TYPE
    SYNTAX          Counter32
    UNITS           "PDUs"
    MAX-ACCESS      read-only
    STATUS          current
    DESCRIPTION
        "The number of PDUs dropped on an interface for a given
        protocol. The PDUs will be dropped when the
        cltcTunnelDropThreshold is reached." 
    ::= { cltcTunnelStatisticsEntry 4 }
 

-- cltcTunnelDropStatTable

cltcTunnelDropStatTable OBJECT-TYPE
    SYNTAX          SEQUENCE OF CltcTunnelDropStatEntry 
    MAX-ACCESS      not-accessible
    STATUS          current
    DESCRIPTION
        "This table contains protocol tunneling drop statistics."
    ::= { cltcTunnelStatistics 2 }

cltcTunnelDropStatEntry OBJECT-TYPE
    SYNTAX          CltcTunnelDropStatEntry
    MAX-ACCESS      not-accessible
    STATUS          current
    DESCRIPTION     "Drop statistics for a tunneled protocol."
    INDEX           { cltcTunneledProtocolIndex } 
    ::= { cltcTunnelDropStatTable 1 }

CltcTunnelDropStatEntry ::= SEQUENCE {
        cltcTunnelTotalDropStats Counter32
}

cltcTunnelTotalDropStats OBJECT-TYPE
    SYNTAX          Counter32
    UNITS           "encapsulated PDUs"
    MAX-ACCESS      read-only
    STATUS          current
    DESCRIPTION
        "The number of tunneled ingress PDUs that have been dropped." 
    ::= { cltcTunnelDropStatEntry 1 }
 


-- dot1qAllTaggedEnabled
cltcDot1qAllTaggedEnabled OBJECT-TYPE
    SYNTAX          TruthValue
    MAX-ACCESS      read-write
    STATUS          current
    DESCRIPTION
        "This object controls if dot1q-all-tagged feature is enabled in
        the managed system." 
    ::= { cltcDot1qAllTagged 1 }
-- cltcDot1qAllTaggedIfTable

cltcDot1qAllTaggedIfTable OBJECT-TYPE
    SYNTAX          SEQUENCE OF CltcDot1qAllTaggedIfEntry 
    MAX-ACCESS      not-accessible
    STATUS          current
    DESCRIPTION
        "This table contains information about the dot1q-all-tagged
        feature's configuration of capable interfaces in the system."
    ::= { cltcDot1qAllTagged 2 }

cltcDot1qAllTaggedIfEntry OBJECT-TYPE
    SYNTAX          CltcDot1qAllTaggedIfEntry
    MAX-ACCESS      not-accessible
    STATUS          current
    DESCRIPTION
        "Configuration of dot1q-all-tagged feature on interfaces. Each
        entry is created for a dot1q-all-tagged capable interface in
        the system."
    INDEX           { ifIndex } 
    ::= { cltcDot1qAllTaggedIfTable 1 }

CltcDot1qAllTaggedIfEntry ::= SEQUENCE {
        cltcDot1qAllTaggedIfEnabled TruthValue
}

cltcDot1qAllTaggedIfEnabled OBJECT-TYPE
    SYNTAX          TruthValue
    MAX-ACCESS      read-write
    STATUS          current
    DESCRIPTION
        "This object specifies whether dot1q-all-tagged feature has been
        enabled on a specific interface." 
    ::= { cltcDot1qAllTaggedIfEntry 1 }
 

-- Notifications
cltcMIBNotifications  OBJECT IDENTIFIER
    ::= { ciscoL2TunnelConfigMIB 2 }

cltcMIBNotificationsPrefix  OBJECT IDENTIFIER
    ::= { cltcMIBNotifications 0 }



cltcTunnelDropThresholdExceeded NOTIFICATION-TYPE
    OBJECTS         { cltcTunnelDropThreshold }
    STATUS          current
    DESCRIPTION
        "This notification is generated when the
        cltcTunnelDropThreshold has been exceeded."
   ::= { cltcMIBNotificationsPrefix 1 }


cltcTunnelShutdownThresholdExceeded NOTIFICATION-TYPE
    OBJECTS         { cltcTunnelShutdownThreshold }
    STATUS          current
    DESCRIPTION
        "This notification is generated when the
        cltcTunnelShutdownThreshold has been exceeded."
   ::= { cltcMIBNotificationsPrefix 2 }


cltcTunnelSysDropThresholdExceeded NOTIFICATION-TYPE
    OBJECTS         { cltcTunnelSysDropThreshold }
    STATUS          current
    DESCRIPTION
        "This notification is generated when the
        cltcTunnelSysDropThreshold has been exceeded."
   ::= { cltcMIBNotificationsPrefix 3 }
-- Conformance
cltcMIBConformance  OBJECT IDENTIFIER
    ::= { ciscoL2TunnelConfigMIB 3 }

cltcMIBCompliances  OBJECT IDENTIFIER
    ::= { cltcMIBConformance 1 }

cltcMIBGroups  OBJECT IDENTIFIER
    ::= { cltcMIBConformance 2 }


-- Compliance
cltcMIBCompliance MODULE-COMPLIANCE
    STATUS          deprecated
    DESCRIPTION
        "The compliance statement for the CISCO-L2-TUNNEL-CONFIG-MIB."
    MODULE          -- this module
    GROUP           cltcDot1qTunnelGroup
    DESCRIPTION
        "A collection of objects for configuring dot1q tunnneling.
        This group is mandatory only in devices which support dot1q
        tunneling."

    GROUP           cltcTunneledProtocolGroup
    DESCRIPTION
        "A collection of objects for configuring tunneled protocols.
        This group is mandatory only in devices which support dot1q
        tunneling."

    GROUP           cltcTunnelThresholdGroup
    DESCRIPTION
        "A collection of objects for configuring the thresholds for
        protocol tunneling. This group is mandatory only in devices
        which support protocol tunneling."

    GROUP           cltcTunnelStatisticsGroup
    DESCRIPTION
        "A collection of objects which give the statistics regarding
        the tunneling interfaces. This group is mandatory only in
        devices which support tunneling statistics."
    ::= { cltcMIBCompliances 1 }

cltcMIBCompliance2 MODULE-COMPLIANCE
    STATUS          deprecated
    DESCRIPTION
        "The compliance statement for the CISCO-L2-TUNNEL-CONFIG-MIB."
    MODULE          -- this module
    GROUP           cltcDot1qTunnelGroup
    DESCRIPTION
        "A collection of objects for configuring dot1q tunnneling.
        This group is mandatory only in devices which support dot1q
        tunneling."

    GROUP           cltcTunneledProtocolGroup
    DESCRIPTION
        "A collection of objects for configuring tunneled protocols.
        This group is mandatory only in devices which support dot1q
        tunneling."

    GROUP           cltcTunnelThresholdGroup
    DESCRIPTION
        "A collection of objects for configuring the thresholds for
        protocol tunneling. This group is mandatory only in devices
        which support protocol tunneling."

    GROUP           cltcTunnelStatisticsGroup
    DESCRIPTION
        "A collection of objects which give the statistics regarding
        the tunneling interfaces. This group is mandatory only in
        devices which support tunneling statistics."

    GROUP           cltcDot1qAllTaggedGroup
    DESCRIPTION
        "This group is mandatory only in devices which support
        dot1q-all-tagged feature."

    OBJECT          cltcDot1qAllTaggedEnabled
    MIN-ACCESS      read-only
    DESCRIPTION     "Write access is not required."

    OBJECT          cltcDot1qAllTaggedIfEnabled
    MIN-ACCESS      read-only
    DESCRIPTION     "Write access is not required."
    ::= { cltcMIBCompliances 2 }

cltcMIBCompliance3 MODULE-COMPLIANCE
    STATUS          deprecated
    DESCRIPTION
        "The compliance statement for the CISCO-L2-TUNNEL-CONFIG-MIB."
    MODULE          -- this module
    GROUP           cltcDot1qTunnelGroup
    DESCRIPTION
        "A collection of objects for configuring dot1q tunnneling.
        This group is mandatory only in devices which support dot1q
        tunneling."

    GROUP           cltcTunneledProtocolGroup
    DESCRIPTION
        "A collection of objects for configuring tunneled protocols.
        This group is mandatory only in devices which support dot1q
        tunneling."

    GROUP           cltcTunnelThresholdGroup
    DESCRIPTION
        "A collection of objects for configuring the thresholds for
        protocol tunneling. This group is mandatory only in devices
        which support protocol tunneling."

    GROUP           cltcTunnelStatisticsGroup
    DESCRIPTION
        "A collection of objects which give the statistics regarding
        the tunneling interfaces. This group is mandatory only in
        devices which support tunneling statistics."

    GROUP           cltcDot1qAllTaggedGroup
    DESCRIPTION
        "This group is mandatory only in devices which support
        dot1q-all-tagged feature."

    GROUP           cltcTunnelDropStatisticsGroup
    DESCRIPTION
        "A collection of objects which give the statistics regarding
        dropped PDUs on the tunneling interfaces. This group is
        mandatory only in devices which support tunneling drop
        statistics."

    OBJECT          cltcDot1qAllTaggedEnabled
    MIN-ACCESS      read-only
    DESCRIPTION     "Write access is not required."

    OBJECT          cltcDot1qAllTaggedIfEnabled
    MIN-ACCESS      read-only
    DESCRIPTION     "Write access is not required."
    ::= { cltcMIBCompliances 3 }

cltcMIBCompliance4 MODULE-COMPLIANCE
    STATUS          deprecated
    DESCRIPTION
        "The compliance statement for the CISCO-L2-TUNNEL-CONFIG-MIB."
    MODULE          -- this module
    GROUP           cltcDot1qTunnelGroup
    DESCRIPTION
        "A collection of objects for configuring dot1q tunnneling.
        This group is mandatory only in devices which support dot1q
        tunneling."

    GROUP           cltcTunneledProtocolGroup
    DESCRIPTION
        "A collection of objects for configuring tunneled protocols.
        This group is mandatory only in devices which support dot1q
        tunneling."

    GROUP           cltcTunnelThresholdGroup
    DESCRIPTION
        "A collection of objects for configuring the thresholds for
        protocol tunneling. This group is mandatory only in devices
        which support protocol tunneling."

    GROUP           cltcTunnelStatisticsGroup
    DESCRIPTION
        "A collection of objects which give the statistics regarding
        the tunneling interfaces. This group is mandatory only in
        devices which support tunneling statistics."

    GROUP           cltcDot1qAllTaggedGroup
    DESCRIPTION
        "This group is mandatory only in devices which support
        dot1q-all-tagged feature."

    GROUP           cltcTunnelDropStatisticsGroup
    DESCRIPTION
        "A collection of objects which give the statistics regarding
        dropped PDUs on the tunneling interfaces. This group is
        mandatory only in devices which support tunneling drop
        statistics."

    GROUP           cltcNotifsEnableGroup
    DESCRIPTION
        "A collections of objects used to enable notifications.
        This group is mandatory only in devices which support
        the protocol tunneling notification feature."

    GROUP           cltcTunnelThresholdNotifsGroup
    DESCRIPTION
        "A collection of notifications used for the tunnel
        thresholds. This group is mandatory only in devices
        which support the protocol tunneling notification
        feature."

    OBJECT          cltcDot1qAllTaggedEnabled
    MIN-ACCESS      read-only
    DESCRIPTION     "Write access is not required."

    OBJECT          cltcDot1qAllTaggedIfEnabled
    MIN-ACCESS      read-only
    DESCRIPTION     "Write access is not required."
    ::= { cltcMIBCompliances 4 }

cltcMIBCompliance5 MODULE-COMPLIANCE
    STATUS          current
    DESCRIPTION
        "The compliance statement for the CISCO-L2-TUNNEL-CONFIG-MIB."
    MODULE          -- this module
    GROUP           cltcDot1qTunnelGroup
    DESCRIPTION
        "This group is mandatory only in devices which support dot1q
        tunneling."

    GROUP           cltcTunneledProtocolGroup
    DESCRIPTION
        "This group is mandatory only in devices which support dot1q
        tunneling."

    GROUP           cltcTunnelThresholdGroup
    DESCRIPTION
        "This group is mandatory only in devices which support
        protocol tunneling threshold feature."

    GROUP           cltcTunnelStatisticsGroup
    DESCRIPTION
        "This group is mandatory only in devices which support
        per interface tunneling statistics."

    GROUP           cltcDot1qAllTaggedGroup
    DESCRIPTION
        "This group is mandatory only in devices which support
        dot1q-all-tagged feature."

    GROUP           cltcTunnelDropStatisticsGroup
    DESCRIPTION
        "This group is mandatory only in devices which support
        per interface tunneling drop statistics."

    GROUP           cltcTunnelTotalDropGroup
    DESCRIPTION
        "This group is mandatory only in devices which support
        per device tunneling drop statistics."

    GROUP           cltcNotifsEnableGroup
    DESCRIPTION
        "This group is mandatory only in devices which support
        the protocol tunneling notification feature."

    GROUP           cltcTunnelThresholdNotifsGroup
    DESCRIPTION
        "This group is mandatory only in devices which support
        the protocol tunneling notification feature."

    GROUP           cltcTunnelSysDropNotifEnableGroup
    DESCRIPTION
        "This group is mandatory only in devices which support
        the notification for the system drop threshold."

    GROUP           cltcTunnelSysDropGroup
    DESCRIPTION
        "This group is mandatory only in devices which support
        the system drop threshold."

    GROUP           cltcTunnelSysDropNotifGroup
    DESCRIPTION
        "This group is mandatory only in devices which support
        the notification for the system drop threshold."

    OBJECT          cltcDot1qAllTaggedEnabled
    MIN-ACCESS      read-only
    DESCRIPTION     "Write access is not required."

    OBJECT          cltcDot1qAllTaggedIfEnabled
    MIN-ACCESS      read-only
    DESCRIPTION     "Write access is not required."
    ::= { cltcMIBCompliances 5 }

-- Units of Conformance
cltcDot1qTunnelGroup OBJECT-GROUP
    OBJECTS         { cltcDot1qTunnelMode }
    STATUS          current
    DESCRIPTION
        "A collection of objects for configuring dot1q tunnneling."
    ::= { cltcMIBGroups 1 }

cltcTunneledProtocolGroup OBJECT-GROUP
    OBJECTS         {
                        cltcTunneledProtocolType,
                        cltcTunnelCos
                    }
    STATUS          current
    DESCRIPTION
        "A collection of objects for configuring tunneled protocols."
    ::= { cltcMIBGroups 2 }

cltcTunnelThresholdGroup OBJECT-GROUP
    OBJECTS         {
                        cltcTunnelDropThreshold,
                        cltcTunnelShutdownThreshold
                    }
    STATUS          current
    DESCRIPTION
        "A collection of objects for configuring the thresholds for
        protocol tunneling."
    ::= { cltcMIBGroups 3 }

cltcTunnelStatisticsGroup OBJECT-GROUP
    OBJECTS         {
                        cltcTunnelEncapStats,
                        cltcTunnelDeEncapStats
                    }
    STATUS          current
    DESCRIPTION
        "A collection of objects which give the statistics regarding
        the tunneling interfaces."
    ::= { cltcMIBGroups 4 }

cltcDot1qAllTaggedGroup OBJECT-GROUP
    OBJECTS         {
                        cltcDot1qAllTaggedEnabled,
                        cltcDot1qAllTaggedIfEnabled
                    }
    STATUS          current
    DESCRIPTION
        "A collection of objects for configuring the dot1q-all-tagged
        feature in the system."
    ::= { cltcMIBGroups 5 }

cltcTunnelDropStatisticsGroup OBJECT-GROUP
    OBJECTS         { cltcTunnelDropStats }
    STATUS          current
    DESCRIPTION
        "A collection of objects which give the statistics regarding
        dropped PDUs on the tunneling interfaces."
    ::= { cltcMIBGroups 6 }

cltcNotifsEnableGroup OBJECT-GROUP
    OBJECTS         { cltcNotificationEnable }
    STATUS          current
    DESCRIPTION
        "A collections of objects used to enable notifications."
    ::= { cltcMIBGroups 7 }

cltcTunnelThresholdNotifsGroup NOTIFICATION-GROUP
   NOTIFICATIONS    {
                        cltcTunnelDropThresholdExceeded,
                        cltcTunnelShutdownThresholdExceeded
                    }
    STATUS          current
    DESCRIPTION
        "A collection of notifications used for the tunnel
        thresholds."
    ::= { cltcMIBGroups 8 }

cltcTunnelTotalDropGroup OBJECT-GROUP
    OBJECTS         { cltcTunnelTotalDropStats }
    STATUS          current
    DESCRIPTION
        "A collection of objects which give the statistics regarding
        total number of dropped PDUs per protocol type."
    ::= { cltcMIBGroups 9 }

cltcTunnelSysDropNotifEnableGroup OBJECT-GROUP
    OBJECTS         { cltcTunnelSysDropNotifEnable }
    STATUS          current
    DESCRIPTION
        "A collection of object to enable
        cltcTunnelSysDropThresholdExceeded notification."
    ::= { cltcMIBGroups 10 }

cltcTunnelSysDropGroup OBJECT-GROUP
    OBJECTS         { cltcTunnelSysDropThreshold }
    STATUS          current
    DESCRIPTION
        "A collection of object for configuring the system level
        rate limiting."
    ::= { cltcMIBGroups 11 }

cltcTunnelSysDropNotifGroup NOTIFICATION-GROUP
   NOTIFICATIONS    { cltcTunnelSysDropThresholdExceeded }
    STATUS          current
    DESCRIPTION
        "A collection of notification used for the system level rate
        limiting has been exceeded."
    ::= { cltcMIBGroups 12 }

END
