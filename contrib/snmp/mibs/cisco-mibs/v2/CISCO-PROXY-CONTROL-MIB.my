-- *****************************************************************
-- CISCO-PROXY-CONTROL-MIB.my: Proxy Control MIB file
--   
-- November 1999 Chris White
--   
-- Copyright (c) 1999, 2000-2005, 2006, 2009 by cisco Systems Inc.
-- All rights reserved.
-- *****************************************************************

CISCO-PROXY-CONTROL-MIB DEFINITIONS ::= BEGIN

IMPORTS
    MODULE-IDENTITY,
    OBJECT-TYPE,
    IpAddress,
    Integer32
        FROM SNMPv2-SMI
    MODULE-COMPLIANCE,
    OBJECT-GROUP
        FROM SNMPv2-CONF
    TEXTUAL-CONVENTION
        FROM SNMPv2-TC
    callActiveSetupTime,
    callActiveIndex,
    AbsoluteCounter32
        FROM DIAL-CONTROL-MIB
    CvcGUid
        FROM CISCO-VOICE-COMMON-DIAL-CONTROL-MIB
    cCallHistoryIndex
        FROM CISCO-DIAL-CONTROL-MIB
    ciscoExperiment
        FROM CISCO-SMI;


ciscoProxyControlMIB MODULE-IDENTITY
    LAST-UPDATED    "200902110000Z"
    ORGANIZATION    "Cisco Systems, Inc."
    CONTACT-INFO
            "Cisco Systems, Inc.
            Customer Service

            Postal: 170 W. Tasman Drive
            San Jose, CA  95134
            USA

            Tel: +1 800 553-NETS

            E-mail: cs-voice@cisco.com"
    DESCRIPTION
        "This MIB module enhances the IETF Dial Control MIB
        (RFC2128) by providing Proxy management information.

        *** ABBREVIATIONS, ACRONYMS AND SYMBOLS ***

        GSM    - Global System for Mobile Communication

        AMR-NB - Adaptive Multi Rate - Narrow Band

        iLBC   - internet Low Bitrate Codec

        iSAC   - internet Speech Audio Codec"
    REVISION        "200902110000Z"
    DESCRIPTION
        "[1] Added acronyms for iSAC codecs
        [2] Added iSAC enum to CProxyAudioCodec textual convention.
        [3] Added REFERENCE clause to CProxyAudioCodec textual
        convention for iSAC codec."
    REVISION        "200603120000Z"
    DESCRIPTION
        "[1] Added acronyms for GSM AMR-NB and iLBC codecs
        [2] Added iLBC enum to CProxyAudioCodec textual 
            convention.
        [3] Added REFERENCE clause to CProxyAudioCodec textual 
            convention for GSM AMR-NB and iLBC codecs."
    REVISION        "200503060000Z"
    DESCRIPTION
        "Added gsmAmrNb enum to CProxyAudioCodec textual
        convention."
    REVISION        "200002040000Z"
    DESCRIPTION
        "First release of this MIB."
    ::= { ciscoExperiment 57 }


-- Voice Proxy Dial Control MIB objects definitions

ciscoProxyControlMIBObjects  OBJECT IDENTIFIER
    ::= { ciscoProxyControlMIB 1 }

-- The Proxy Control MIB consists of the following groups
-- [1] Proxy Control Call Active Group (cProxyCallActive)
-- [2] Proxy Control Call History Group (cProxyCallHistory)

cProxyCallActive  OBJECT IDENTIFIER
    ::= { ciscoProxyControlMIBObjects 1 }

cProxyCallHistory  OBJECT IDENTIFIER
    ::= { ciscoProxyControlMIBObjects 2 }


-- Textual Conventions

CProxyEndptType ::= TEXTUAL-CONVENTION
    STATUS          current
    DESCRIPTION
        "A tag to identify the type of end point that the Proxy
        is connected to."
    SYNTAX          INTEGER  {
                        other(0), -- none of the following
                        proxy(1), -- another h323 proxy
                        gateway(2) -- h323 gateway                        
                    }

CProxyAudioCodec ::= TEXTUAL-CONVENTION
    STATUS          current
    DESCRIPTION
        "A tag to identify the type of encoding used to compress
        the voice data of the call.

        iLBC           - iILBC 13330 or 15200 bps
        iSAC           - iSAC 10 to 32 kbps"

    REFERENCE
        "[1] RFC 3267: For introduction about GSM AMR-NB codec,
        section 3.1
        [2] RFC 3952: For introduction about iLBC codec,
        section 2
        [3] iSAC Codec Description Document from GIPS"
    SYNTAX          INTEGER {
                        other(0),
                        nonStandard(1),
                        g711Alawr64k(2),
                        g711Alawr56k(3),
                        g711Ulawr64k(4),
                        g711Ulawr56k(5),
                        g722r64k(6),
                        g722r56k(7),
                        g722r48k(8),
                        g7231(9),
                        g728(10),
                        g729(11),
                        g729AnnexA(12),
                        is11172(13),
                        is13818(14),
                        g729AnnexB(15),
                        g729AnnexAB(16),
                        g729AnnexC(17),
                        gsmFullRate(18),
                        gsmHalfRate(19),
                        gsmEnhancedFullRate(20),
                        gsmAmrNb(21),
                        iLBC(22),
                        iSAC(23)
                    }

CProxyVideoCodec ::= TEXTUAL-CONVENTION
    STATUS          current
    DESCRIPTION
        "A tag to identify the type of encoding used to compress
        the video data of the call."
    SYNTAX          INTEGER  {
                        other(0),
                        nonStandard(1),
                        h261(2),
                        h262(3),
                        h263(4),
                        is11172(5)
                    }
-- **********************************************************************
-- Proxy Dial Control Call Active Group
-- **********************************************************************
--   

-- Proxy Call Active Table

cProxyCallActiveTable OBJECT-TYPE
    SYNTAX          SEQUENCE OF CProxyCallActiveEntry 
    MAX-ACCESS      not-accessible
    STATUS          current
    DESCRIPTION
        "This table is the Proxy extension to the call Active
        table of IETF Dial Control MIB. It contains Proxy call
        leg information about specific proxied calls."
    REFERENCE       "IETF Dial Control MIB (RFC2128)"
    ::= { cProxyCallActive 1 }

cProxyCallActiveEntry OBJECT-TYPE
    SYNTAX          CProxyCallActiveEntry
    MAX-ACCESS      not-accessible
    STATUS          current
    DESCRIPTION
        "The information regarding a single proxied call leg.
        An entry of this table is created when its associated call
        Active entry in the IETF Dial Control MIB is created and
        the call Active entry contains information for the call
        establishment to the peer on the data network.
        This entry is deleted when its associated Call Active
        entry in the IETF Dial Control MIB is deleted."
    INDEX           {
                        callActiveSetupTime,
                        callActiveIndex
                    } 
    ::= { cProxyCallActiveTable 1 }

CProxyCallActiveEntry ::= SEQUENCE {
        cProxyCallActiveConnectionId     CvcGUid,
        cProxyCallActiveRemoteIPAddress  IpAddress,
        cProxyCallActiveAudioUDPPort     INTEGER,
        cProxyCallActiveVideoUDPPort     INTEGER,
        cProxyCallActiveT120TCPPort1     INTEGER,
        cProxyCallActiveT120TCPPort2     INTEGER,
        cProxyCallActiveT120TCPPort3     INTEGER,
        cProxyCallActiveT120TCPPort4     INTEGER,
        cProxyCallActiveEndpointType     CProxyEndptType,
        cProxyCallActiveEndpointVendor   INTEGER,
        cProxyCallActiveRequestBandwidth Integer32,
        cProxyCallActiveActualBandwidth  Integer32,
        cProxyCallActiveAudioCoderRate   CProxyAudioCodec,
        cProxyCallActiveVideoCoderRate   CProxyVideoCodec,
        cProxyCallActiveRxAudioPackets   AbsoluteCounter32,
        cProxyCallActiveRxAudioBytes     AbsoluteCounter32,
        cProxyCallActiveTxAudioPackets   AbsoluteCounter32,
        cProxyCallActiveTxAudioBytes     AbsoluteCounter32,
        cProxyCallActiveRxVideoPackets   AbsoluteCounter32,
        cProxyCallActiveRxVideoBytes     AbsoluteCounter32,
        cProxyCallActiveTxVideoPackets   AbsoluteCounter32,
        cProxyCallActiveTxVideoBytes     AbsoluteCounter32,
        cProxyCallActiveRxT120Packets    AbsoluteCounter32,
        cProxyCallActiveRxT120Bytes      AbsoluteCounter32,
        cProxyCallActiveTxT120Packets    AbsoluteCounter32,
        cProxyCallActiveTxT120Bytes      AbsoluteCounter32
}

cProxyCallActiveConnectionId OBJECT-TYPE
    SYNTAX          CvcGUid
    MAX-ACCESS      read-only
    STATUS          current
    DESCRIPTION
        "The global call identifier for the Proxy call." 
    ::= { cProxyCallActiveEntry 1 }

cProxyCallActiveRemoteIPAddress OBJECT-TYPE
    SYNTAX          IpAddress
    MAX-ACCESS      read-only
    STATUS          current
    DESCRIPTION
        "Remote system IP address for the call." 
    ::= { cProxyCallActiveEntry 2 }

cProxyCallActiveAudioUDPPort OBJECT-TYPE
    SYNTAX          INTEGER (0..65535)
    MAX-ACCESS      read-only
    STATUS          current
    DESCRIPTION
        "Remote system UDP listener port to which to transmit
        voice packets for the call. A value of zero indicates
        that no port was used." 
    ::= { cProxyCallActiveEntry 3 }

cProxyCallActiveVideoUDPPort OBJECT-TYPE
    SYNTAX          INTEGER (0..65535)
    MAX-ACCESS      read-only
    STATUS          current
    DESCRIPTION
        "Remote system UDP listener port to which to transmit
        video packets for the call. A value of zero indicates
        that no port was used." 
    ::= { cProxyCallActiveEntry 4 }

cProxyCallActiveT120TCPPort1 OBJECT-TYPE
    SYNTAX          INTEGER (0..65535)
    MAX-ACCESS      read-only
    STATUS          current
    DESCRIPTION
        "First remote system UDP listener port to which to transmit
        T120 packets for the call.  A value of zero indicates that
        no port was used." 
    ::= { cProxyCallActiveEntry 5 }

cProxyCallActiveT120TCPPort2 OBJECT-TYPE
    SYNTAX          INTEGER (0..65535)
    MAX-ACCESS      read-only
    STATUS          current
    DESCRIPTION
        "Second remote system UDP listener port to which to
        transmit T120 packets for the call.  A value of zero
        indicates that no port was used." 
    ::= { cProxyCallActiveEntry 6 }

cProxyCallActiveT120TCPPort3 OBJECT-TYPE
    SYNTAX          INTEGER (0..65535)
    MAX-ACCESS      read-only
    STATUS          current
    DESCRIPTION
        "Third remote system UDP listener port to which to transmit
        T120 packets for the call.  A value of zero indicates that
        no port was used." 
    ::= { cProxyCallActiveEntry 7 }

cProxyCallActiveT120TCPPort4 OBJECT-TYPE
    SYNTAX          INTEGER (0..65535)
    MAX-ACCESS      read-only
    STATUS          current
    DESCRIPTION
        "Fourth remote system UDP listener port to which to transmit
        T120 packets for the call.  A value of zero indicates that
        no port was used." 
    ::= { cProxyCallActiveEntry 8 }

cProxyCallActiveEndpointType OBJECT-TYPE
    SYNTAX          CProxyEndptType
    MAX-ACCESS      read-only
    STATUS          current
    DESCRIPTION
        "The type of end point this proxy call leg is connected to." 
    ::= { cProxyCallActiveEntry 9 }

cProxyCallActiveEndpointVendor OBJECT-TYPE
    SYNTAX          INTEGER (0..65535)
    MAX-ACCESS      read-only
    STATUS          current
    DESCRIPTION
        "The H225 Manufacturers code for this endpoint.
        Zero indicates unknown vendor." 
    ::= { cProxyCallActiveEntry 10 }

cProxyCallActiveRequestBandwidth OBJECT-TYPE
    SYNTAX          Integer32 (0..10000000)
    UNITS           "kilobits per second"
    MAX-ACCESS      read-only
    STATUS          current
    DESCRIPTION
        "The requested bandwidth for this proxied call leg." 
    ::= { cProxyCallActiveEntry 11 }

cProxyCallActiveActualBandwidth OBJECT-TYPE
    SYNTAX          Integer32 (0..10000000)
    UNITS           "kilobits per second"
    MAX-ACCESS      read-only
    STATUS          current
    DESCRIPTION
        "The actual bandwidth used by the proxied call." 
    ::= { cProxyCallActiveEntry 12 }

cProxyCallActiveAudioCoderRate OBJECT-TYPE
    SYNTAX          CProxyAudioCodec
    MAX-ACCESS      read-only
    STATUS          current
    DESCRIPTION
        "The negotiated coder rate. It specifies the transmit
        rate of audio compression to its associated call leg
        for the call." 
    ::= { cProxyCallActiveEntry 13 }

cProxyCallActiveVideoCoderRate OBJECT-TYPE
    SYNTAX          CProxyVideoCodec
    MAX-ACCESS      read-only
    STATUS          current
    DESCRIPTION
        "The negotiated coder rate. It specifies the transmit
        rate of video compression to its associated call leg
        for the call." 
    ::= { cProxyCallActiveEntry 14 }

cProxyCallActiveRxAudioPackets OBJECT-TYPE
    SYNTAX          AbsoluteCounter32
    UNITS           "packets"
    MAX-ACCESS      read-only
    STATUS          current
    DESCRIPTION
        "The number of audio packets received from the remote
        end for this call." 
    ::= { cProxyCallActiveEntry 15 }

cProxyCallActiveRxAudioBytes OBJECT-TYPE
    SYNTAX          AbsoluteCounter32
    UNITS           "bytes"
    MAX-ACCESS      read-only
    STATUS          current
    DESCRIPTION
        "The number of audio bytes received from the remote
        end for this call." 
    ::= { cProxyCallActiveEntry 16 }

cProxyCallActiveTxAudioPackets OBJECT-TYPE
    SYNTAX          AbsoluteCounter32
    UNITS           "packets"
    MAX-ACCESS      read-only
    STATUS          current
    DESCRIPTION
        "The number of audio packets transmitted to the remote
        end for this call." 
    ::= { cProxyCallActiveEntry 17 }

cProxyCallActiveTxAudioBytes OBJECT-TYPE
    SYNTAX          AbsoluteCounter32
    UNITS           "bytes"
    MAX-ACCESS      read-only
    STATUS          current
    DESCRIPTION
        "The number of audio bytes transmitted to the remote
        end for this call." 
    ::= { cProxyCallActiveEntry 18 }

cProxyCallActiveRxVideoPackets OBJECT-TYPE
    SYNTAX          AbsoluteCounter32
    UNITS           "packets"
    MAX-ACCESS      read-only
    STATUS          current
    DESCRIPTION
        "The number of video packets received from the remote
        end for this call." 
    ::= { cProxyCallActiveEntry 19 }

cProxyCallActiveRxVideoBytes OBJECT-TYPE
    SYNTAX          AbsoluteCounter32
    UNITS           "bytes"
    MAX-ACCESS      read-only
    STATUS          current
    DESCRIPTION
        "The number of video bytes received from the remote
        end for this call." 
    ::= { cProxyCallActiveEntry 20 }

cProxyCallActiveTxVideoPackets OBJECT-TYPE
    SYNTAX          AbsoluteCounter32
    UNITS           "packets"
    MAX-ACCESS      read-only
    STATUS          current
    DESCRIPTION
        "The number of video packets transmitted to the remote
        end for this call." 
    ::= { cProxyCallActiveEntry 21 }

cProxyCallActiveTxVideoBytes OBJECT-TYPE
    SYNTAX          AbsoluteCounter32
    UNITS           "bytes"
    MAX-ACCESS      read-only
    STATUS          current
    DESCRIPTION
        "The number of video bytes transmitted to the remote
        end for this call." 
    ::= { cProxyCallActiveEntry 22 }

cProxyCallActiveRxT120Packets OBJECT-TYPE
    SYNTAX          AbsoluteCounter32
    UNITS           "packets"
    MAX-ACCESS      read-only
    STATUS          current
    DESCRIPTION
        "The number of T120 data packets received from the
        remote end for this call." 
    ::= { cProxyCallActiveEntry 23 }

cProxyCallActiveRxT120Bytes OBJECT-TYPE
    SYNTAX          AbsoluteCounter32
    UNITS           "bytes"
    MAX-ACCESS      read-only
    STATUS          current
    DESCRIPTION
        "The number of T120 data bytes received from the remote
        end of this call." 
    ::= { cProxyCallActiveEntry 24 }

cProxyCallActiveTxT120Packets OBJECT-TYPE
    SYNTAX          AbsoluteCounter32
    UNITS           "packets"
    MAX-ACCESS      read-only
    STATUS          current
    DESCRIPTION
        "The number of T120 data packets transmitted to the remote
        end for this call." 
    ::= { cProxyCallActiveEntry 25 }

cProxyCallActiveTxT120Bytes OBJECT-TYPE
    SYNTAX          AbsoluteCounter32
    UNITS           "bytes"
    MAX-ACCESS      read-only
    STATUS          current
    DESCRIPTION
        "The number of T120 data bytes transmitted to the remote
        end of this call." 
    ::= { cProxyCallActiveEntry 26 }
 

-- **********************************************************************
-- Proxy Dial Control Call History Group
-- **********************************************************************
--   

-- Proxy Call History Table

cProxyCallHistoryTable OBJECT-TYPE
    SYNTAX          SEQUENCE OF CProxyCallHistoryEntry 
    MAX-ACCESS      not-accessible
    STATUS          current
    DESCRIPTION
        "This table is the Proxy extension to the History call table
        of IETF Dial Control MIB. It contains PROXY call leg
        information about proxied call."
    REFERENCE       "IETF Dial Control MIB (RFC2128)"
    ::= { cProxyCallHistory 1 }

cProxyCallHistoryEntry OBJECT-TYPE
    SYNTAX          CProxyCallHistoryEntry
    MAX-ACCESS      not-accessible
    STATUS          current
    DESCRIPTION
        "The information regarding a single proxied call leg.
        An entry of this table is created when its associated call
        History entry in the IETF Dial Control MIB is created. The
        call History entry contains information for the call
        establishment to the peer on the data network backbone via
        a voice over PROXY peer.
        The entry is deleted when its associated call History entry
        in the IETF Dial Control MIB is deleted."
    INDEX           { cCallHistoryIndex } 
    ::= { cProxyCallHistoryTable 1 }

CProxyCallHistoryEntry ::= SEQUENCE {
        cProxyCallHistoryConnectionId     CvcGUid,
        cProxyCallHistoryRemoteIPAddress  IpAddress,
        cProxyCallHistoryAudioUDPPort     INTEGER,
        cProxyCallHistoryVideoUDPPort     INTEGER,
        cProxyCallHistoryT120TCPPort1     INTEGER,
        cProxyCallHistoryT120TCPPort2     INTEGER,
        cProxyCallHistoryT120TCPPort3     INTEGER,
        cProxyCallHistoryT120TCPPort4     INTEGER,
        cProxyCallHistoryEndpointType     CProxyEndptType,
        cProxyCallHistoryEndpointVendor   INTEGER,
        cProxyCallHistoryRequestBandwidth Integer32,
        cProxyCallHistoryActualBandwidth  Integer32,
        cProxyCallHistoryAudioCoderRate   CProxyAudioCodec,
        cProxyCallHistoryVideoCoderRate   CProxyVideoCodec,
        cProxyCallHistoryRxAudioPackets   AbsoluteCounter32,
        cProxyCallHistoryRxAudioBytes     AbsoluteCounter32,
        cProxyCallHistoryTxAudioPackets   AbsoluteCounter32,
        cProxyCallHistoryTxAudioBytes     AbsoluteCounter32,
        cProxyCallHistoryRxVideoPackets   AbsoluteCounter32,
        cProxyCallHistoryRxVideoBytes     AbsoluteCounter32,
        cProxyCallHistoryTxVideoPackets   AbsoluteCounter32,
        cProxyCallHistoryTxVideoBytes     AbsoluteCounter32,
        cProxyCallHistoryRxT120Packets    AbsoluteCounter32,
        cProxyCallHistoryRxT120Bytes      AbsoluteCounter32,
        cProxyCallHistoryTxT120Packets    AbsoluteCounter32,
        cProxyCallHistoryTxT120Bytes      AbsoluteCounter32
}

cProxyCallHistoryConnectionId OBJECT-TYPE
    SYNTAX          CvcGUid
    MAX-ACCESS      read-only
    STATUS          current
    DESCRIPTION
        "The global call identifier for the Proxy call." 
    ::= { cProxyCallHistoryEntry 1 }

cProxyCallHistoryRemoteIPAddress OBJECT-TYPE
    SYNTAX          IpAddress
    MAX-ACCESS      read-only
    STATUS          current
    DESCRIPTION
        "Remote system IP address for the call." 
    ::= { cProxyCallHistoryEntry 2 }

cProxyCallHistoryAudioUDPPort OBJECT-TYPE
    SYNTAX          INTEGER (0..65535)
    MAX-ACCESS      read-only
    STATUS          current
    DESCRIPTION
        "Remote system UDP listener port to which to transmit
        voice packets for the call. A value of zero indicates
        that no port was used." 
    ::= { cProxyCallHistoryEntry 3 }

cProxyCallHistoryVideoUDPPort OBJECT-TYPE
    SYNTAX          INTEGER (0..65535)
    MAX-ACCESS      read-only
    STATUS          current
    DESCRIPTION
        "Remote system UDP listener port to which to transmit
        video packets for the call. A value of zero indicates
        that no port was used." 
    ::= { cProxyCallHistoryEntry 4 }

cProxyCallHistoryT120TCPPort1 OBJECT-TYPE
    SYNTAX          INTEGER (0..65535)
    MAX-ACCESS      read-only
    STATUS          current
    DESCRIPTION
        "First remote system UDP listener port to which to
        transmit T120 packets for the call.  A value of zero
        indicates that no port was used." 
    ::= { cProxyCallHistoryEntry 5 }

cProxyCallHistoryT120TCPPort2 OBJECT-TYPE
    SYNTAX          INTEGER (0..65535)
    MAX-ACCESS      read-only
    STATUS          current
    DESCRIPTION
        "Second remote system UDP listener port to which to
        transmit T120 packets for the call.  A value of zero
        indicates that no port was used." 
    ::= { cProxyCallHistoryEntry 6 }

cProxyCallHistoryT120TCPPort3 OBJECT-TYPE
    SYNTAX          INTEGER (0..65535)
    MAX-ACCESS      read-only
    STATUS          current
    DESCRIPTION
        "Third remote system UDP listener port to which to
        transmit T120 packets for the call.  A value of zero
        indicates that no port was used." 
    ::= { cProxyCallHistoryEntry 7 }

cProxyCallHistoryT120TCPPort4 OBJECT-TYPE
    SYNTAX          INTEGER (0..65535)
    MAX-ACCESS      read-only
    STATUS          current
    DESCRIPTION
        "Fourth remote system UDP listener port to which to
        transmit T120 packets for the call.  A value of zero
        indicates that no port was used." 
    ::= { cProxyCallHistoryEntry 8 }

cProxyCallHistoryEndpointType OBJECT-TYPE
    SYNTAX          CProxyEndptType
    MAX-ACCESS      read-only
    STATUS          current
    DESCRIPTION
        "The type of end point this proxy call leg is connected to." 
    ::= { cProxyCallHistoryEntry 9 }

cProxyCallHistoryEndpointVendor OBJECT-TYPE
    SYNTAX          INTEGER (0..65535)
    MAX-ACCESS      read-only
    STATUS          current
    DESCRIPTION
        "The H225 Manufacturers code for this endpoint.
        Zero indicates unknown vendor." 
    ::= { cProxyCallHistoryEntry 10 }

cProxyCallHistoryRequestBandwidth OBJECT-TYPE
    SYNTAX          Integer32 (0..10000000)
    UNITS           "kilobits per second"
    MAX-ACCESS      read-only
    STATUS          current
    DESCRIPTION
        "The requested bandwidth for this proxied call leg." 
    ::= { cProxyCallHistoryEntry 11 }

cProxyCallHistoryActualBandwidth OBJECT-TYPE
    SYNTAX          Integer32 (0..10000000)
    UNITS           "kilobits per second"
    MAX-ACCESS      read-only
    STATUS          current
    DESCRIPTION
        "The actual bandwidth used by the proxied call." 
    ::= { cProxyCallHistoryEntry 12 }

cProxyCallHistoryAudioCoderRate OBJECT-TYPE
    SYNTAX          CProxyAudioCodec
    MAX-ACCESS      read-only
    STATUS          current
    DESCRIPTION
        "The negotiated coder rate. It specifies the transmit
        rate of audio compression to its associated call leg
        for the call." 
    ::= { cProxyCallHistoryEntry 13 }

cProxyCallHistoryVideoCoderRate OBJECT-TYPE
    SYNTAX          CProxyVideoCodec
    MAX-ACCESS      read-only
    STATUS          current
    DESCRIPTION
        "The negotiated coder rate. It specifies the transmit
        rate of video compression to its associated call leg
        for the call." 
    ::= { cProxyCallHistoryEntry 14 }

cProxyCallHistoryRxAudioPackets OBJECT-TYPE
    SYNTAX          AbsoluteCounter32
    UNITS           "packets"
    MAX-ACCESS      read-only
    STATUS          current
    DESCRIPTION
        "The number of audio packets received from the remote
        end for this call." 
    ::= { cProxyCallHistoryEntry 15 }

cProxyCallHistoryRxAudioBytes OBJECT-TYPE
    SYNTAX          AbsoluteCounter32
    UNITS           "bytes"
    MAX-ACCESS      read-only
    STATUS          current
    DESCRIPTION
        "The number of audio bytes received from the remote
        end for this call." 
    ::= { cProxyCallHistoryEntry 16 }

cProxyCallHistoryTxAudioPackets OBJECT-TYPE
    SYNTAX          AbsoluteCounter32
    UNITS           "packets"
    MAX-ACCESS      read-only
    STATUS          current
    DESCRIPTION
        "The number of audio packets transmitted to the remote
        end for this call." 
    ::= { cProxyCallHistoryEntry 17 }

cProxyCallHistoryTxAudioBytes OBJECT-TYPE
    SYNTAX          AbsoluteCounter32
    UNITS           "bytes"
    MAX-ACCESS      read-only
    STATUS          current
    DESCRIPTION
        "The number of audio bytes transmitted to the remote
        end for this call." 
    ::= { cProxyCallHistoryEntry 18 }

cProxyCallHistoryRxVideoPackets OBJECT-TYPE
    SYNTAX          AbsoluteCounter32
    UNITS           "packets"
    MAX-ACCESS      read-only
    STATUS          current
    DESCRIPTION
        "The number of video packets received from the remote
        end for this call." 
    ::= { cProxyCallHistoryEntry 19 }

cProxyCallHistoryRxVideoBytes OBJECT-TYPE
    SYNTAX          AbsoluteCounter32
    UNITS           "bytes"
    MAX-ACCESS      read-only
    STATUS          current
    DESCRIPTION
        "The number of video bytes received from the remote
        end for this call." 
    ::= { cProxyCallHistoryEntry 20 }

cProxyCallHistoryTxVideoPackets OBJECT-TYPE
    SYNTAX          AbsoluteCounter32
    UNITS           "packets"
    MAX-ACCESS      read-only
    STATUS          current
    DESCRIPTION
        "The number of video packets transmitted to the remote
        end for this call." 
    ::= { cProxyCallHistoryEntry 21 }

cProxyCallHistoryTxVideoBytes OBJECT-TYPE
    SYNTAX          AbsoluteCounter32
    UNITS           "bytes"
    MAX-ACCESS      read-only
    STATUS          current
    DESCRIPTION
        "The number of video bytes transmitted to the remote end for
        this call." 
    ::= { cProxyCallHistoryEntry 22 }

cProxyCallHistoryRxT120Packets OBJECT-TYPE
    SYNTAX          AbsoluteCounter32
    UNITS           "packets"
    MAX-ACCESS      read-only
    STATUS          current
    DESCRIPTION
        "The number of T120 data packets received from the remote
        end for this call." 
    ::= { cProxyCallHistoryEntry 23 }

cProxyCallHistoryRxT120Bytes OBJECT-TYPE
    SYNTAX          AbsoluteCounter32
    UNITS           "bytes"
    MAX-ACCESS      read-only
    STATUS          current
    DESCRIPTION
        "The number of T120 data bytes received from the remote
        end for this call." 
    ::= { cProxyCallHistoryEntry 24 }

cProxyCallHistoryTxT120Packets OBJECT-TYPE
    SYNTAX          AbsoluteCounter32
    UNITS           "packets"
    MAX-ACCESS      read-only
    STATUS          current
    DESCRIPTION
        "The number of T120 data packets transmitted to the remote
        end for this call." 
    ::= { cProxyCallHistoryEntry 25 }

cProxyCallHistoryTxT120Bytes OBJECT-TYPE
    SYNTAX          AbsoluteCounter32
    UNITS           "bytes"
    MAX-ACCESS      read-only
    STATUS          current
    DESCRIPTION
        "The number of T120 data bytes transmitted to the remote
        end for this call." 
    ::= { cProxyCallHistoryEntry 26 }
 

-- Notifications

ciscoProxyControlMIBNotificationPrefix  OBJECT IDENTIFIER
    ::= { ciscoProxyControlMIB 2 }

ciscoProxyControlMIBNotifications  OBJECT IDENTIFIER
    ::= { ciscoProxyControlMIBNotificationPrefix 0 }

-- Conformancy, Compliance and Group Objects

ciscoProxyControlMIBConformance  OBJECT IDENTIFIER
    ::= { ciscoProxyControlMIB 3 }

ciscoProxyControlMIBCompliances  OBJECT IDENTIFIER
    ::= { ciscoProxyControlMIBConformance 1 }

ciscoProxyControlMIBGroups  OBJECT IDENTIFIER
    ::= { ciscoProxyControlMIBConformance 2 }


-- compliance statements

ciscoProxyControlMIBCompliance MODULE-COMPLIANCE
    STATUS          current
    DESCRIPTION
        "The compliance statement for entities which
        implement the CISCO PROXY CONTROL MIB"
    MODULE          -- this module
    MANDATORY-GROUPS {
                        cProxyCallActiveGroup,
                        cProxyCallHistoryGroup
                    }
    ::= { ciscoProxyControlMIBCompliances 1 }

-- units of conformance

cProxyCallActiveGroup OBJECT-GROUP
    OBJECTS         {
                        cProxyCallActiveConnectionId,
                        cProxyCallActiveRemoteIPAddress,
                        cProxyCallActiveAudioUDPPort,
                        cProxyCallActiveVideoUDPPort,
                        cProxyCallActiveT120TCPPort1,
                        cProxyCallActiveT120TCPPort2,
                        cProxyCallActiveT120TCPPort3,
                        cProxyCallActiveT120TCPPort4,
                        cProxyCallActiveEndpointType,
                        cProxyCallActiveEndpointVendor,
                        cProxyCallActiveRequestBandwidth,
                        cProxyCallActiveActualBandwidth,
                        cProxyCallActiveAudioCoderRate,
                        cProxyCallActiveVideoCoderRate,
                        cProxyCallActiveRxAudioPackets,
                        cProxyCallActiveRxAudioBytes,
                        cProxyCallActiveTxAudioPackets,
                        cProxyCallActiveTxAudioBytes,
                        cProxyCallActiveRxVideoPackets,
                        cProxyCallActiveRxVideoBytes,
                        cProxyCallActiveTxVideoPackets,
                        cProxyCallActiveTxVideoBytes,
                        cProxyCallActiveRxT120Packets,
                        cProxyCallActiveRxT120Bytes,
                        cProxyCallActiveTxT120Packets,
                        cProxyCallActiveTxT120Bytes
                    }
    STATUS          current
    DESCRIPTION
        "A collection of objects providing the PROXY Call Active
        entry capability."
    ::= { ciscoProxyControlMIBGroups 1 }

cProxyCallHistoryGroup OBJECT-GROUP
    OBJECTS         {
                        cProxyCallHistoryConnectionId,
                        cProxyCallHistoryRemoteIPAddress,
                        cProxyCallHistoryAudioUDPPort,
                        cProxyCallHistoryVideoUDPPort,
                        cProxyCallHistoryT120TCPPort1,
                        cProxyCallHistoryT120TCPPort2,
                        cProxyCallHistoryT120TCPPort3,
                        cProxyCallHistoryT120TCPPort4,
                        cProxyCallHistoryEndpointType,
                        cProxyCallHistoryEndpointVendor,
                        cProxyCallHistoryRequestBandwidth,
                        cProxyCallHistoryActualBandwidth,
                        cProxyCallHistoryAudioCoderRate,
                        cProxyCallHistoryVideoCoderRate,
                        cProxyCallHistoryRxAudioPackets,
                        cProxyCallHistoryRxAudioBytes,
                        cProxyCallHistoryTxAudioPackets,
                        cProxyCallHistoryTxAudioBytes,
                        cProxyCallHistoryRxVideoPackets,
                        cProxyCallHistoryRxVideoBytes,
                        cProxyCallHistoryTxVideoPackets,
                        cProxyCallHistoryTxVideoBytes,
                        cProxyCallHistoryRxT120Packets,
                        cProxyCallHistoryRxT120Bytes,
                        cProxyCallHistoryTxT120Packets,
                        cProxyCallHistoryTxT120Bytes
                    }
    STATUS          current
    DESCRIPTION
        "A collection of objects providing the PROXY Call Active
        entry capability."
    ::= { ciscoProxyControlMIBGroups 2 }

END
