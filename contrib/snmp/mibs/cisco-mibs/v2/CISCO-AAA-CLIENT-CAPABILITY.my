-- *****************************************************************
-- CISCO-AAA-CLIENT-CAPABILITY.my:
-- Cisco CISCO-AAA-CLIENT-MIB AGENT-CAPABILITIES
--
-- Aug 2003, Jayakumar Kadirvelu
--
-- Copyright (c) 2003-2004 by Cisco Systems, Inc.
-- All rights reserved.
-- *****************************************************************

CISCO-AAA-CLIENT-CAPABILITY DEFINITIONS ::= BEGIN

IMPORTS
        MODULE-IDENTITY
                FROM SNMPv2-SMI
        AGENT-CAPABILITIES
                FROM SNMPv2-CONF
        TruthValue
                FROM SNMPv2-TC
        ciscoAgentCapability
                FROM CISCO-SMI;

ciscoAaaClientCapability MODULE-IDENTITY
        LAST-UPDATED    "200402030000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of CISCO-AAA-CLIENT-MIB."
        
        REVISION        "200402030000Z"
        DESCRIPTION
                "Added VARIATION for cacEnable and cacPrimaryMethod."

        REVISION        "200308060000Z"
        DESCRIPTION
                "Initial version of this MIB module."
        ::= { ciscoAgentCapability 322 }


ciscoAaaClientCapCatOSV08R0101 AGENT-CAPABILITIES
    PRODUCT-RELEASE     "Cisco CatOS 8.1(1) on Catalyst 6000/6500
                         and Cisco 7600 series devices."
    STATUS              current
    DESCRIPTION         "CISCO-AAA-CLIENT-MIB capabilities."

    SUPPORTS            CISCO-AAA-CLIENT-MIB
        INCLUDES        { cacPriorityGroup,
                          cacLoginConfigGroup,
                          cacLoginConfigGroupRev1
                        }

        VARIATION       cacEnable
            SYNTAX      TruthValue
            DESCRIPTION "Cannot be set to false(2), when the value
                         of cacAuthen is local(4), and the value of
                         cacPrimaryMethod is true(1)."

        VARIATION       cacPrimaryMethod
            SYNTAX      TruthValue
            DESCRIPTION "Cannot be set to false(2)."
    ::= { ciscoAaaClientCapability 1 }

END
