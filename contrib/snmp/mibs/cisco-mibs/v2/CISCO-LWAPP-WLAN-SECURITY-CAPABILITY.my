-- *******************************************************************
-- CISCO-LWAPP-WLAN-SECURITY MIB CAPABILITY
--
-- November 18, 2020
--
-- Copyright (c) 2020, 2022 by Cisco Systems, Inc.
-- All rights reserved.
-- *******************************************************************

CISCO-LWAPP-WLAN-SECURITY-CAPABILITY DEFINITIONS ::= BEGIN


IMPORTS
       MODULE-IDENTITY
           FROM SNMPv2-SMI
       AGENT-CAPABILITIES
           FROM SNMPv2-CONF
       ciscoAgentCapability
           FROM CISCO-SMI;


ciscoLwappWlanSecurityCapability  MODULE-IDENTITY

       LAST-UPDATED         "202011180000Z"
       ORGANIZATION         "Cisco Systems, Inc."
       CONTACT-INFO
               "Cisco Systems
               Customer Service

               Postal: 170 W Tasman Drive
               San Jose, CA  95134
               USA

               Tel: +1 800 553-NETS

               E-mail: cs-wnbu-snmp@cisco.com"

       DESCRIPTION
               "Agent capabilities for
               CISCO-LWAPP-WLAN-SECURITY-MIB "
       REVISION      "202011180000Z"
       DESCRIPTION
               "Initial version of this MIB module. "

   ::= { ciscoAgentCapability 1157 }

ciscoLwappWlanSecurityCapabilityCEV1R0 AGENT-CAPABILITIES

       PRODUCT-RELEASE "Cisco EWLC 1.0"
       STATUS          current
       DESCRIPTION     "CISCO-LWAPP-WLAN-SECURITY--MIB capabilities."

       SUPPORTS        CISCO-LWAPP-WLAN-SECURITY-MIB
       INCLUDES        {
                           cLWSecDot11EssCckmTable,
                           cLWSecDot11EssWebPolicyTable,
                           cLWSecDot11EssCkipTable
                       }

       VARIATION       cLWSecDot11EssFtEnable
       ACCESS          not-implemented
       DESCRIPTION     "Not supported"

       VARIATION       cLWSecDot11EssWebPolicyEntry
       ACCESS          not-implemented
       DESCRIPTION     "Not supported"

       VARIATION       cLWSecDot11EssWebPolicyCondRedirect
       ACCESS          not-implemented
       DESCRIPTION     "Not supported"

       VARIATION       cLWSecDot11EssWebPolicySplashPageWebRedirect
       ACCESS          not-implemented
       DESCRIPTION     "Not supported"

       VARIATION       cLWSecAaaRadiusAuthCallStationIdType
       ACCESS          not-implemented
       DESCRIPTION     "Not supported"

       VARIATION       cLWSecAaaRadiusAccUsernameDelimiter
       ACCESS          not-implemented
       DESCRIPTION     "Not supported"

       VARIATION       cLWSecDot11EssCkipEntry
       ACCESS          not-implemented
       DESCRIPTION     "Not supported"

       VARIATION       cLWSecDot11EssCkipSecurity
       ACCESS          not-implemented
       DESCRIPTION     "Not supported"

       VARIATION       cLWSecDot11EssCkipKeyIndex
       ACCESS          not-implemented
       DESCRIPTION     "Not supported"

       VARIATION       cLWSecDot11EssCkipKeyLength
       ACCESS          not-implemented
       DESCRIPTION     "Not supported"

       VARIATION       cLWSecDot11EssCkipKeyFmt
       ACCESS          not-implemented
       DESCRIPTION     "Not supported"

       VARIATION       cLWSecDot11EssCkipKey
       ACCESS          not-implemented
       DESCRIPTION     "Not supported"

       VARIATION       cLWSecDot11EssCkipMMHMode
       ACCESS          not-implemented
       DESCRIPTION     "Not supported"

       VARIATION       cLWSecDot11EssCkipKPEnable
       ACCESS          not-implemented
       DESCRIPTION     "Not supported"

   ::= { ciscoLwappWlanSecurityCapability 1 }

END
