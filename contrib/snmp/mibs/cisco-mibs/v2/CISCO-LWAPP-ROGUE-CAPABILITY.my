-- *******************************************************************
-- CISCO-LWAPP-ROGUE MIB CAPABILITY
--
-- November 18, 2020
--
-- Copyright (c) 2020, 2022 by Cisco Systems, Inc.
-- All rights reserved.
-- *******************************************************************

CISCO-LWAPP-ROGUE-CAPABILITY DEFINITIONS ::= BEGIN


IMPORTS
       MODULE-IDENTITY
           FROM SNMPv2-SMI
       AGENT-CAPABILITIES
           FROM SNMPv2-CONF
       ciscoAgentCapability
           FROM CISCO-SMI;


ciscoLwappRogueCapability  MODULE-IDENTITY

       LAST-UPDATED         "202011180000Z"
       ORGANIZATION         "Cisco Systems, Inc."
       CONTACT-INFO
               "Cisco Systems
               Customer Service

               Postal: 170 W Tasman Drive
               San Jose, CA  95134
               USA

               Tel: +1 800 553-NETS

               E-mail: cs-wnbu-snmp@cisco.com"

       DESCRIPTION
               "Agent capabilities for
               CISCO-LWAPP-ROGUE-MIB "
       REVISION      "202011180000Z"
       DESCRIPTION
               "Initial version of this MIB module. "

   ::= { ciscoAgentCapability 1164 }

ciscoLwappRogueCapabilityCEV1R0 AGENT-CAPABILITIES

       PRODUCT-RELEASE "Cisco EWLC 1.0"
       STATUS          current
       DESCRIPTION     "CISCO-LWAPP-ROGUE--MIB capabilities."

       SUPPORTS        CISCO-LWAPP-ROGUE-MIB
       INCLUDES        {
                           cLConditionConfigTable,
                           cLConditionSsidConfigTable,
                           cLRuleConfigTable
                       }

       VARIATION       cLConditionType
       ACCESS          not-implemented
       DESCRIPTION     "Not supported"

       VARIATION       cLConditionValue
       ACCESS          not-implemented
       DESCRIPTION     "Not supported"

       VARIATION       cLConditionSsidType
       ACCESS          not-implemented
       DESCRIPTION     "Not supported"

       VARIATION       cLRogueAdhocRogueNotifEnabled
       ACCESS          not-implemented
       DESCRIPTION     "Not supported"

       VARIATION       cLRuleNotifyType
       ACCESS          not-implemented
       DESCRIPTION     "Not supported"

   ::= { ciscoLwappRogueCapability 1 }

END
