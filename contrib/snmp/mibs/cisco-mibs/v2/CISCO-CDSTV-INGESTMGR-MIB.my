-- *****************************************************************
-- CISCO-CDSTV-INGESTMGR-MIB: Cisco CDS-TV Ingest Manager Configuration
-- Management Information Base
--   
-- April 2010, Rajat Ahuja.
--   
-- Copyright (c) 2010 by Cisco Systems, Inc.
--   
-- All rights reserved.
--   
-- *****************************************************************

CISCO-CDSTV-INGESTMGR-MIB DEFINITIONS ::= BEGIN

IMPORTS
    MODULE-IDENTITY,
    OBJECT-TYPE,
    Unsigned32
        FROM SNMPv2-SMI
    MODULE-COMPLIANCE,
    OBJECT-GROUP
        FROM SNMPv2-CONF
    InetPortNumber,
    InetAddressType,
    InetAddress
        FROM INET-ADDRESS-MIB
    TruthValue
        FROM SNMPv2-TC
    CiscoURLString,
    CiscoURLStringOrEmpty,
    TimeIntervalSec,
    TimeIntervalMin
        FROM CISCO-TC
    ciscoMgmt
        FROM CISCO-SMI;


ciscoCdstvIngestmgrMIB MODULE-IDENTITY
    LAST-UPDATED    "201005270000Z"
    ORGANIZATION    "Cisco Systems, Inc."
    CONTACT-INFO
            "Cisco Systems
            Customer Service

            Postal: 170 W Tasman Drive
            San Jose, CA  95134
            USA

            Tel: +1 800 553-NETS

            E-mail: cs-cds@cisco.com"
    DESCRIPTION
        "This MIB module defines ingest manager configuration objects
        that faciliate the management of the Cisco Content Delivery
        System for TV (CDS-TV) product family.

        CDS-TV is a suite of products and software applications
        providing ingest, storage, caching, streaming, playout and
        on-demand delivery of video to television or set-top-box
        clients.

        Abbreviations:

        CCP     Cache Control Protocol
        CDS     Content Delivery System
        CORBA   Common Object Request Broker Architecture 
        ISA     Interactive Services Architecture
        ISV     Integrated Streamer-Vault
        FSI     File Service Interface
        FTP     File Transfer Protocol
        MPEG    Motion Picture Experts Group
        MSA     Managed Services Architecture
        RTSP    Real-Time Streaming Protocol
        STB     Set-Top Box

        Common terms:

        Catcher: Device responsible for receiving content (typically via
        satellite dishes and antennae) from content providers or from a
        Headend-In-The-Sky. 

        Content Ingest: Acquisition of content from a source such as a
        catcher or an FTP server for storing it locally and making it
        available to streamers as needed.

        Ingest Manager: CDS module that takes care of provisioned
        content objects by collecting metadata, sending messages to the
        appropriate subsystem to ingest the content, and sending
        messages to expire the content when the expiration period has
        passed. 

        Device Roles:

        Vault: Content delivery application responsible for ingesting
        and storing video content and making it available to streamers
        and/or caching nodes.

        Caching Nodes: Content delivery application responsible for
        caching content from vault (using CCP) and then streaming
        content out to streamers over HTTP or CCP.

        Streamer: Content delivery application responsible for streaming
        video out to STB's.

        ISV: Content delivery application capable of acting as both a
        vault and as a streamer in a single device."
    REVISION        "201005270000Z"
    DESCRIPTION
        "Initial version of this MIB module."
    ::= { ciscoMgmt 739 }


-- Textual Conventions definition will be defined before this line

ciscoCdstvIngestMgrMIBNotifs  OBJECT IDENTIFIER
    ::= { ciscoCdstvIngestmgrMIB 0 }

ciscoCdstvIngestMgrMIBObjects  OBJECT IDENTIFIER
    ::= { ciscoCdstvIngestmgrMIB 1 }

ciscoCdstvIngestMgrMIBConform  OBJECT IDENTIFIER
    ::= { ciscoCdstvIngestmgrMIB 2 }

ciscoCdstvIngestMgrMIBCompliances  OBJECT IDENTIFIER
    ::= { ciscoCdstvIngestMgrMIBConform 1 }

-- Ingest Manager General Settings

cdstvIngestMgrGeneralSettings  OBJECT IDENTIFIER
    ::= { ciscoCdstvIngestMgrMIBObjects 1 }

-- Ingest Manager Ingest Settings

cdstvIngestMgrIngestSettings  OBJECT IDENTIFIER
    ::= { ciscoCdstvIngestMgrMIBObjects 2 }

-- Ingest Manager Back-office Settings

cdstvIngestMgrBackOfficeSettings  OBJECT IDENTIFIER
    ::= { ciscoCdstvIngestMgrMIBObjects 3 }

-- Ingest Manager Content Store Settings

cdstvIngestMgrContentStoreSettings  OBJECT IDENTIFIER
    ::= { ciscoCdstvIngestMgrMIBObjects 4 }

-- Ingest Manager Encryption Settings

cdstvIngestMgrEncryptionSettings  OBJECT IDENTIFIER
    ::= { ciscoCdstvIngestMgrMIBObjects 5 }


cdstvIngestMgrHostAddressType OBJECT-TYPE
    SYNTAX          InetAddressType
    MAX-ACCESS      read-write
    STATUS          current
    DESCRIPTION
        "This object specifies the type of the IP address (specified by
        cdstvIngestMgrHostAddress) of the Ingest Manager." 
    ::= { cdstvIngestMgrGeneralSettings 1 }

cdstvIngestMgrHostAddress OBJECT-TYPE
    SYNTAX          InetAddress
    MAX-ACCESS      read-write
    STATUS          current
    DESCRIPTION
        "This object specifies the IP address of the Ingest Manager. The
        type of this address is specified by
        cdstvIngestMgrHostAddressType." 
    ::= { cdstvIngestMgrGeneralSettings 2 }

cdstvIngestMgrPort OBJECT-TYPE
    SYNTAX          InetPortNumber (0..65535)
    MAX-ACCESS      read-write
    STATUS          current
    DESCRIPTION
        "This object specifies the port number to use for listening for
        inbound connections." 
    ::= { cdstvIngestMgrGeneralSettings 3 }

cdstvIngestMgrFsiCallbackPort OBJECT-TYPE
    SYNTAX          InetPortNumber (0..65535)
    MAX-ACCESS      read-write
    STATUS          current
    DESCRIPTION
        "This object specifies the port number to use for File Services
        Interface (FSI) callbacks." 
    ::= { cdstvIngestMgrGeneralSettings 4 }

cdstvIngestMgrAdditionalPackageWindow OBJECT-TYPE
    SYNTAX          Unsigned32
    UNITS           "days"
    MAX-ACCESS      read-write
    STATUS          current
    DESCRIPTION
        "This object specifies the additional amount of time to wait
        once the package expiration window has ended before
        destroying the stored content package. Typically, when the
        package expiration window ends, the ingested content package is
        destroyed from the device. The additional package window adds a
        grace period to the expiration window." 
    ::= { cdstvIngestMgrGeneralSettings 5 }

cdstvIngestMgrFtpTimeout OBJECT-TYPE
    SYNTAX          TimeIntervalSec
    MAX-ACCESS      read-write
    STATUS          current
    DESCRIPTION
        "This object specifies the maximum period the Ingest Manager
        waits before timing out an FTP session and terminating
        the process." 
    ::= { cdstvIngestMgrGeneralSettings 6 }

cdstvIngestMgrUseAssetIdEnable OBJECT-TYPE
    SYNTAX          TruthValue
    MAX-ACCESS      read-write
    STATUS          current
    DESCRIPTION
        "This object specifies whether to use the Asset ID (a unique ID
        assigned to each content ingested into the CDS) for the content
        name.
        'true' indicates that Asset ID is used for the content name.
        'false' indicates Asset ID is not used for the content name." 
    ::= { cdstvIngestMgrGeneralSettings 7 }

cdstvIngestMgrManageCorbaServices OBJECT-TYPE
    SYNTAX          TruthValue
    MAX-ACCESS      read-write
    STATUS          current
    DESCRIPTION
        "This object specifies whether the CDS manages the CORBA
        services.
        'true' indicates that CDS manages CORBA services.
        'false' indicates that CDS does not manage CORBA services." 
    ::= { cdstvIngestMgrGeneralSettings 8 }

cdstvIngestMgrRequireNotifyService OBJECT-TYPE
    SYNTAX          TruthValue
    MAX-ACCESS      read-write
    STATUS          current
    DESCRIPTION
        "This object specifies whether the CDS requires the use of ISA
        Notify Service.
        'true' indicates that CDS requires the use of ISA Notify
        Service.
        'false' indicates that CDS does not require the use of ISA
        Notify Service." 
    ::= { cdstvIngestMgrGeneralSettings 9 }

cdstvIngestMgrDebugLevel OBJECT-TYPE
    SYNTAX          INTEGER  {
                        errors(1),
                        all(2),
                        off(3)
                    }
    MAX-ACCESS      read-write
    STATUS          current
    DESCRIPTION
        "This object specifies the amount of debugging information
        logged.
        errors(1) - Only error messages are logged.
        all(2) - Errors, warnings and success message are all logged.
        off(3) - Debugging is disabled." 
    ::= { cdstvIngestMgrGeneralSettings 10 }

cdstvIngestMgrMetaDataPublish OBJECT-TYPE
    SYNTAX          TruthValue
    MAX-ACCESS      read-write
    STATUS          current
    DESCRIPTION
        "This object specifies whether content metadata is published or
        not.
        'true' indicates that content metadata is published.
        'false' indicates that content metadata is not published." 
    ::= { cdstvIngestMgrGeneralSettings 11 }

cdstvIngestMgrMetaPublishUrl OBJECT-TYPE
    SYNTAX          CiscoURLString
    MAX-ACCESS      read-write
    STATUS          current
    DESCRIPTION
        "This object specifies the URL where the metadata is published,
        typically the back-office." 
    ::= { cdstvIngestMgrGeneralSettings 12 }

cdstvIngestMgrMetaPublishBackupUrl OBJECT-TYPE
    SYNTAX          CiscoURLStringOrEmpty
    MAX-ACCESS      read-write
    STATUS          current
    DESCRIPTION
        "This object specifies the URL of the backup server where the
        metadata is published. This string is empty if a backup server
        URL is not configured." 
    ::= { cdstvIngestMgrGeneralSettings 13 }

cdstvIngestMgrIngestInterface OBJECT-TYPE
    SYNTAX          BITS {
                        isa(0),
                        ciscoSoap(1),
                        prodisSoap(2)
                    }
    MAX-ACCESS      read-write
    STATUS          current
    DESCRIPTION
        "This object specifies all ingest interfaces (methods)
        available, i.e. ISA, Cisco SOAP, Prodis SOAP or any combination
        of the three.
        isa(0) - ISA.
        ciscoSoap(1) - Cisco SOAP 
        prodisSoap(2) - Prodis SOAP." 
    ::= { cdstvIngestMgrIngestSettings 1 }

cdstvIngestMgrCiscoSoapUrl OBJECT-TYPE
    SYNTAX          CiscoURLStringOrEmpty
    MAX-ACCESS      read-write
    STATUS          current
    DESCRIPTION
        "This object specifies the URL (IP address, port, and directory)
        on the Vault used to receive content using the Cisco SOAP
        (Simple Object Access Protocol). An example of the Cisco SOAP
        URL is http://10.22.216.251:8793/CiscoAIM. This string is empty
        if Cisco SOAP is not used." 
    ::= { cdstvIngestMgrIngestSettings 2 }

cdstvIngestMgrProdisSoapUrl OBJECT-TYPE
    SYNTAX          CiscoURLStringOrEmpty
    MAX-ACCESS      read-write
    STATUS          current
    DESCRIPTION
        "This object specifies the URL (IP address, port, and directory)
        on the Vault used to receive content using the Prodis
        SOAP(Simple Object Access Protocol). An example of the Prodis
        SOAP URL is http://10.22.216.251:8793/ProdisAIM. This string is
        empty if Prodis SOAP is not used." 
    ::= { cdstvIngestMgrIngestSettings 3 }

cdstvIngestMgrBackOfficeMaxRetries OBJECT-TYPE
    SYNTAX          Unsigned32 (0..1000)
    MAX-ACCESS      read-write
    STATUS          current
    DESCRIPTION
        "This object specifies the maximum number of times to retry a
        failed communication with the back-office." 
    ::= { cdstvIngestMgrBackOfficeSettings 1 }

cdstvIngestMgrBackOfficeRetryInterval OBJECT-TYPE
    SYNTAX          TimeIntervalMin
    MAX-ACCESS      read-write
    STATUS          current
    DESCRIPTION
        "This object specifies the amount of time to wait before
        retrying a failed communication with the back-office." 
    ::= { cdstvIngestMgrBackOfficeSettings 2 }

cdstvIngestMgrBackOfficeTimeout OBJECT-TYPE
    SYNTAX          TimeIntervalSec
    MAX-ACCESS      read-write
    STATUS          current
    DESCRIPTION
        "This object specifies the amount of time to wait for the
        back-office to respond to a communication attempt." 
    ::= { cdstvIngestMgrBackOfficeSettings 3 }

cdstvIngestMgrBackOfficeTable OBJECT-TYPE
    SYNTAX          SEQUENCE OF CdstvIngestMgrBackOfficeEntry 
    MAX-ACCESS      not-accessible
    STATUS          current
    DESCRIPTION
        "A table containing the back-office type and URL
        settings."
    ::= { cdstvIngestMgrBackOfficeSettings 4 }

cdstvIngestMgrBackOfficeEntry OBJECT-TYPE
    SYNTAX          CdstvIngestMgrBackOfficeEntry
    MAX-ACCESS      not-accessible
    STATUS          current
    DESCRIPTION
        "An entry (conceptual row) in the table of back-office type and
        URL settings. Rows are added if new back-offices are
        configured and deleted if back-offices are disabled."
    INDEX           { cdstvIngestMgrBackOfficeIndex } 
    ::= { cdstvIngestMgrBackOfficeTable 1 }

CdstvIngestMgrBackOfficeEntry ::= SEQUENCE {
        cdstvIngestMgrBackOfficeIndex Unsigned32,
        cdstvIngestMgrBackOfficeType  INTEGER,
        cdstvIngestMgrBackOfficeUrl   CiscoURLStringOrEmpty
}

cdstvIngestMgrBackOfficeIndex OBJECT-TYPE
    SYNTAX          Unsigned32
    MAX-ACCESS      not-accessible
    STATUS          current
    DESCRIPTION
        "This object uniquely identifies a back-office." 
    ::= { cdstvIngestMgrBackOfficeEntry 1 }

cdstvIngestMgrBackOfficeType OBJECT-TYPE
    SYNTAX          INTEGER  {
                        none(1),
                        totalManage(2)
                    }
    MAX-ACCESS      read-write
    STATUS          current
    DESCRIPTION
        "This object specifies the type of back-office support used.
        none(1) - No back-office support.
        totalManage(2) - Use TotalManage back-office support." 
    ::= { cdstvIngestMgrBackOfficeEntry 2 }

cdstvIngestMgrBackOfficeUrl OBJECT-TYPE
    SYNTAX          CiscoURLStringOrEmpty
    MAX-ACCESS      read-write
    STATUS          current
    DESCRIPTION
        "This object specifies the location (URL) of the back-office.
        This string is empty if back-office support is disabled." 
    ::= { cdstvIngestMgrBackOfficeEntry 3 }
 


cdstvIngestMgrContentStore OBJECT-TYPE
    SYNTAX          INTEGER  {
                        none(1),
                        isa(2),
                        fsi(3),
                        ngod(4),
                        openStream(5)
                    }
    MAX-ACCESS      read-write
    STATUS          current
    DESCRIPTION
        "This object specifies the type of content store used.
        none(1) - Content store is disabled.
        isa(2) - Use ISA content store.
        fsi(3) - Use FSI content store.
        ngod(4) - Use Next-Generation On-Demand (NGOD) content store.
        openStream(5) - Use OpenStream content store." 
    ::= { cdstvIngestMgrContentStoreSettings 1 }

cdstvIngestMgrContentStoreUrl OBJECT-TYPE
    SYNTAX          CiscoURLStringOrEmpty
    MAX-ACCESS      read-write
    STATUS          current
    DESCRIPTION
        "This object specifies the URL where the content store is
        located. This string is empty if content store is disabled." 
    ::= { cdstvIngestMgrContentStoreSettings 2 }

cdstvIngestMgrEncryptionType OBJECT-TYPE
    SYNTAX          INTEGER  {
                        none(1),
                        verimatrix(2),
                        widevine(3)
                    }
    MAX-ACCESS      read-write
    STATUS          current
    DESCRIPTION
        "This object specifies the type of encryption used.
        none(1) - Encryption is disabled.
        verimatrix(2) - Use Verimatrix encryption.
        widevine(3) - Use Widevine encryption." 
    ::= { cdstvIngestMgrEncryptionSettings 1 }

cdstvIngestMgrEncryptionTargetUrl OBJECT-TYPE
    SYNTAX          CiscoURLStringOrEmpty
    MAX-ACCESS      read-write
    STATUS          current
    DESCRIPTION
        "This object specifies the location on the encryption server
        used to send MPEG files for encryption, for example,
        http://192.168.128.54:7898/files/encrypted. This string will be
        empty if encryption is disabled." 
    ::= { cdstvIngestMgrEncryptionSettings 2 }

cdstvIngestMgrEncryptionRetrievalUrl OBJECT-TYPE
    SYNTAX          CiscoURLStringOrEmpty
    MAX-ACCESS      read-write
    STATUS          current
    DESCRIPTION
        "This object specifies the location on the encryption server
        used to retrieve encrypted MPEG files, for example,
        ftp://192.168.128.54:7899/files/encrypted. This string will be
        empty if encryption is disabled." 
    ::= { cdstvIngestMgrEncryptionSettings 3 }
ciscoCdstvIngestMgrMIBGroups  OBJECT IDENTIFIER
    ::= { ciscoCdstvIngestMgrMIBConform 2 }


ciscoCdstvIngestMgrMIBCompliance MODULE-COMPLIANCE
    STATUS          current
    DESCRIPTION
        "The compliance statement for the entities which
        implement the Cisco CDS TV Ingest Manager MIB."
    MODULE          -- this module
    MANDATORY-GROUPS {
                        ciscoCdstvIngestMgrMIBMainObjectGroup,
                        ciscoCdstvIngestMgrMIBIngestSettingsGroup,
                        ciscoCdstvIngestMgrMIBBackOfficeSettingsGroup,
                        ciscoCdstvIngestMgrMIBContentStoreSettingsGroup,
                        ciscoCdstvIngestMgrMIBEncryptionSettingsGroup
                    }

    OBJECT          cdstvIngestMgrHostAddressType
    MIN-ACCESS      read-only
    DESCRIPTION
        "Write-access is not required."

    OBJECT          cdstvIngestMgrHostAddress
    MIN-ACCESS      read-only
    DESCRIPTION
        "Write-access is not required."

    OBJECT          cdstvIngestMgrPort
    MIN-ACCESS      read-only
    DESCRIPTION
        "Write-access is not required."

    OBJECT          cdstvIngestMgrFsiCallbackPort
    MIN-ACCESS      read-only
    DESCRIPTION
        "Write-access is not required."

    OBJECT          cdstvIngestMgrAdditionalPackageWindow
    MIN-ACCESS      read-only
    DESCRIPTION
        "Write-access is not required."

    OBJECT          cdstvIngestMgrFtpTimeout
    MIN-ACCESS      read-only
    DESCRIPTION
        "Write-access is not required."

    OBJECT          cdstvIngestMgrUseAssetIdEnable
    MIN-ACCESS      read-only
    DESCRIPTION
        "Write-access is not required."

    OBJECT          cdstvIngestMgrManageCorbaServices
    MIN-ACCESS      read-only
    DESCRIPTION
        "Write-access is not required."

    OBJECT          cdstvIngestMgrRequireNotifyService
    MIN-ACCESS      read-only
    DESCRIPTION
        "Write-access is not required."

    OBJECT          cdstvIngestMgrDebugLevel
    MIN-ACCESS      read-only
    DESCRIPTION
        "Write-access is not required."

    OBJECT          cdstvIngestMgrMetaDataPublish
    MIN-ACCESS      read-only
    DESCRIPTION
        "Write-access is not required."

    OBJECT          cdstvIngestMgrMetaPublishUrl
    MIN-ACCESS      read-only
    DESCRIPTION
        "Write-access is not required."

    OBJECT          cdstvIngestMgrMetaPublishBackupUrl
    MIN-ACCESS      read-only
    DESCRIPTION
        "Write-access is not required."

    OBJECT          cdstvIngestMgrIngestInterface
    MIN-ACCESS      read-only
    DESCRIPTION
        "Write-access is not required."

    OBJECT          cdstvIngestMgrCiscoSoapUrl
    MIN-ACCESS      read-only
    DESCRIPTION
        "Write-access is not required."

    OBJECT          cdstvIngestMgrProdisSoapUrl
    MIN-ACCESS      read-only
    DESCRIPTION
        "Write-access is not required."

    OBJECT          cdstvIngestMgrBackOfficeMaxRetries
    MIN-ACCESS      read-only
    DESCRIPTION
        "Write-access is not required."

    OBJECT          cdstvIngestMgrBackOfficeRetryInterval
    MIN-ACCESS      read-only
    DESCRIPTION
        "Write-access is not required."

    OBJECT          cdstvIngestMgrBackOfficeTimeout
    MIN-ACCESS      read-only
    DESCRIPTION
        "Write-access is not required."

    OBJECT          cdstvIngestMgrBackOfficeType
    MIN-ACCESS      read-only
    DESCRIPTION
        "Write-access is not required."

    OBJECT          cdstvIngestMgrBackOfficeUrl
    MIN-ACCESS      read-only
    DESCRIPTION
        "Write-access is not required."

    OBJECT          cdstvIngestMgrContentStore
    MIN-ACCESS      read-only
    DESCRIPTION
        "Write-access is not required."

    OBJECT          cdstvIngestMgrContentStoreUrl
    MIN-ACCESS      read-only
    DESCRIPTION
        "Write-access is not required."

    OBJECT          cdstvIngestMgrEncryptionType
    MIN-ACCESS      read-only
    DESCRIPTION
        "Write-access is not required."

    OBJECT          cdstvIngestMgrEncryptionTargetUrl
    MIN-ACCESS      read-only
    DESCRIPTION
        "Write-access is not required."

    OBJECT          cdstvIngestMgrEncryptionRetrievalUrl
    MIN-ACCESS      read-only
    DESCRIPTION
        "Write-access is not required."
    ::= { ciscoCdstvIngestMgrMIBCompliances 1 }

-- Units of Conformance

ciscoCdstvIngestMgrMIBMainObjectGroup OBJECT-GROUP
    OBJECTS         {
                        cdstvIngestMgrHostAddress,
                        cdstvIngestMgrPort,
                        cdstvIngestMgrFsiCallbackPort,
                        cdstvIngestMgrAdditionalPackageWindow,
                        cdstvIngestMgrFtpTimeout,
                        cdstvIngestMgrUseAssetIdEnable,
                        cdstvIngestMgrManageCorbaServices,
                        cdstvIngestMgrRequireNotifyService,
                        cdstvIngestMgrDebugLevel,
                        cdstvIngestMgrMetaDataPublish,
                        cdstvIngestMgrMetaPublishUrl,
                        cdstvIngestMgrMetaPublishBackupUrl,
                        cdstvIngestMgrHostAddressType
                    }
    STATUS          current
    DESCRIPTION
        "A collection of objects that provide the configuration of
        CDS-TV ingest manager."
    ::= { ciscoCdstvIngestMgrMIBGroups 1 }

ciscoCdstvIngestMgrMIBIngestSettingsGroup OBJECT-GROUP
    OBJECTS         {
                        cdstvIngestMgrIngestInterface,
                        cdstvIngestMgrCiscoSoapUrl,
                        cdstvIngestMgrProdisSoapUrl
                    }
    STATUS          current
    DESCRIPTION
        "A collection of objects that provide the ingest settings of the
        CDS-TV ingest manager."
    ::= { ciscoCdstvIngestMgrMIBGroups 2 }

ciscoCdstvIngestMgrMIBBackOfficeSettingsGroup OBJECT-GROUP
    OBJECTS         {
                        cdstvIngestMgrBackOfficeMaxRetries,
                        cdstvIngestMgrBackOfficeRetryInterval,
                        cdstvIngestMgrBackOfficeTimeout,
                        cdstvIngestMgrBackOfficeType,
                        cdstvIngestMgrBackOfficeUrl
                    }
    STATUS          current
    DESCRIPTION
        "A collection of objects that provide the back-office settings
        of the CDS-TV ingest manager."
    ::= { ciscoCdstvIngestMgrMIBGroups 3 }

ciscoCdstvIngestMgrMIBContentStoreSettingsGroup OBJECT-GROUP
    OBJECTS         {
                        cdstvIngestMgrContentStore,
                        cdstvIngestMgrContentStoreUrl
                    }
    STATUS          current
    DESCRIPTION
        "A collection of objects that provide the content store settings
        of the CDS-TV ingest manager."
    ::= { ciscoCdstvIngestMgrMIBGroups 4 }

ciscoCdstvIngestMgrMIBEncryptionSettingsGroup OBJECT-GROUP
    OBJECTS         {
                        cdstvIngestMgrEncryptionType,
                        cdstvIngestMgrEncryptionTargetUrl,
                        cdstvIngestMgrEncryptionRetrievalUrl
                    }
    STATUS          current
    DESCRIPTION
        "A collection of objects that provide the encryption settings of
        the CDS-TV ingest manager."
    ::= { ciscoCdstvIngestMgrMIBGroups 5 }

END
