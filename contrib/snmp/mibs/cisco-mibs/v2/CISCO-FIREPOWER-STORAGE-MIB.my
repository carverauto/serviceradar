-- *********************************************************************
-- CISCO-FIREPOWER-STORAGE-MIB.my
-- 
-- MIB representation of the Cisco Firepower
-- STORAGE management information model package
-- 
-- Created May 2024 by Charles Bullis
-- 
-- Copyright (c) 2005-2024 Cisco Systems, Inc. All rights reserved.
-- 
-- *********************************************************************

CISCO-FIREPOWER-STORAGE-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB
    CfprAaaConfigState,
    CfprConditionRemoteInvRslt,
    CfprEquipmentOperability,
    CfprEquipmentPowerState,
    CfprEquipmentPresence,
    CfprEquipmentSensorThresholdStatus,
    CfprFabricZoningState,
    CfprFsmCompletion,
    CfprFsmFlags,
    CfprFsmFsmStageStatus,
    CfprFsmLifecycle,
    CfprPolicyPolicyOwner,
    CfprStorageAccessType,
    CfprStorageActualWriteType,
    CfprStorageBatteryType,
    CfprStorageBbuStatus,
    CfprStorageBootableType,
    CfprStorageCacheType,
    CfprStorageConfiguration,
    CfprStorageConfiguredWriteType,
    CfprStorageConnectionProtocol,
    CfprStorageControllerFaultMonitoring,
    CfprStorageControllerId,
    CfprStorageControllerStatus,
    CfprStorageControllerType,
    CfprStorageDisklessAction,
    CfprStorageEpAccess,
    CfprStorageEtherIfVlanType,
    CfprStorageFFCardHealth,
    CfprStorageFFCardMode,
    CfprStorageFFCardSizeMismatch,
    CfprStorageFFCardState,
    CfprStorageFFCardSync,
    CfprStorageFFCardWriteEnable,
    CfprStorageFFControllerHealth,
    CfprStorageFFControllerState,
    CfprStorageFFDriveRemovable,
    CfprStorageFFDriveState,
    CfprStorageFFDriveType,
    CfprStorageFFDriveVisible,
    CfprStorageFFFormatRunning,
    CfprStorageFFHasError,
    CfprStorageFFRAIDHealth,
    CfprStorageFFRAIDState,
    CfprStorageFFRWType,
    CfprStorageFFRaidSyncSupport,
    CfprStorageFFSlotENUM,
    CfprStorageFFType,
    CfprStorageFcZoningType,
    CfprStorageFileSystemStatus,
    CfprStorageFlexFlashControllerFsmCurrentFsm,
    CfprStorageFlexFlashControllerFsmStageName,
    CfprStorageFlexFlashControllerFsmTaskItem,
    CfprStorageFlexFlashControllerId,
    CfprStorageIOType,
    CfprStorageIniGroupOperProtocol,
    CfprStorageIniGroupOwner,
    CfprStorageIniGroupProtocol,
    CfprStorageKeyType,
    CfprStorageLearnCycleRequested,
    CfprStorageLearnMode,
    CfprStorageLinkSpeed,
    CfprStorageLocalDiskConfigFlexFlashRAIDReportingState,
    CfprStorageLocalDiskConfigFlexFlashState,
    CfprStorageLocalDiskMode,
    CfprStorageLocalDiskPartitionType,
    CfprStorageLunType,
    CfprStorageOperState,
    CfprStorageOperatingModeType,
    CfprStorageOperationRequestType,
    CfprStorageOperationState,
    CfprStorageOperationStateType,
    CfprStorageOperationType,
    CfprStoragePDriveStatus,
    CfprStoragePowerState,
    CfprStorageProtocol,
    CfprStorageRaidBatteryOperabilityQualifier,
    CfprStorageReadType,
    CfprStorageSystemFsmCurrentFsm,
    CfprStorageSystemFsmStageName,
    CfprStorageSystemFsmTaskItem,
    CfprStorageTargetPath,
    CfprStorageTechnology,
    CfprStorageVDriveState,
    CfprStorageVsanRefSwitchId,
    CfprVnicConfigIssues
        FROM CISCO-FIREPOWER-TC-MIB;

cfprStorageObjects MODULE-IDENTITY
    LAST-UPDATED    "202405160000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        STORAGE management information model package"
    ::= { ciscoFirepowerMIBObjects 74 }

cfprStorageAuthKeyTable OBJECT-TYPE
    SYNTAX           SEQUENCE OF CfprStorageAuthKeyEntry
    MAX-ACCESS       not-accessible
    STATUS           current
    DESCRIPTION
        "Cisco Firepower storage:AuthKey managed object table"
    ::= { cfprStorageObjects 1 }

cfprStorageAuthKeyEntry OBJECT-TYPE
    SYNTAX           CfprStorageAuthKeyEntry
    MAX-ACCESS       not-accessible
    STATUS           current
    DESCRIPTION
        "Entry for the cfprStorageAuthKeyTable table."
    INDEX { cfprStorageAuthKeyInstanceId }
    ::= { cfprStorageAuthKeyTable 1 }

CfprStorageAuthKeyEntry ::= SEQUENCE {
    cfprStorageAuthKeyInstanceId                                     CfprManagedObjectId,
    cfprStorageAuthKeyDn                                             CfprManagedObjectDn,
    cfprStorageAuthKeyRn                                             SnmpAdminString,
    cfprStorageAuthKeyDescr                                          SnmpAdminString,
    cfprStorageAuthKeyIntId                                          SnmpAdminString,
    cfprStorageAuthKeyName                                           SnmpAdminString,
    cfprStorageAuthKeyPassword                                       SnmpAdminString,
    cfprStorageAuthKeyPolicyLevel                                    Gauge32,
    cfprStorageAuthKeyPolicyOwner                                    CfprPolicyPolicyOwner,
    cfprStorageAuthKeyType                                           CfprStorageKeyType,
    cfprStorageAuthKeyUserId                                         SnmpAdminString
}

cfprStorageAuthKeyInstanceId OBJECT-TYPE
    SYNTAX       CfprManagedObjectId
    MAX-ACCESS   not-accessible
    STATUS       current
    DESCRIPTION
        "Instance identifier of the managed object."
    ::= { cfprStorageAuthKeyEntry 1 }

cfprStorageAuthKeyDn OBJECT-TYPE
    SYNTAX       CfprManagedObjectDn
    MAX-ACCESS   read-only
    STATUS       current
    DESCRIPTION
        "Cisco Firepower storage:AuthKey:dn managed object property"
    ::= { cfprStorageAuthKeyEntry 2 }

cfprStorageAuthKeyRn OBJECT-TYPE
    SYNTAX       SnmpAdminString
    MAX-ACCESS   read-only
    STATUS       current
    DESCRIPTION
        "Cisco Firepower storage:AuthKey:rn managed object property"
    ::= { cfprStorageAuthKeyEntry 3 }

cfprStorageAuthKeyDescr OBJECT-TYPE
    SYNTAX       SnmpAdminString
    MAX-ACCESS   read-only
    STATUS       current
    DESCRIPTION
        "Cisco Firepower storage:AuthKey:descr managed object property"
    ::= { cfprStorageAuthKeyEntry 4 }

cfprStorageAuthKeyIntId OBJECT-TYPE
    SYNTAX       SnmpAdminString
    MAX-ACCESS   read-only
    STATUS       current
    DESCRIPTION
        "Cisco Firepower storage:AuthKey:intId managed object property"
    ::= { cfprStorageAuthKeyEntry 5 }

cfprStorageAuthKeyName OBJECT-TYPE
    SYNTAX       SnmpAdminString
    MAX-ACCESS   read-only
    STATUS       current
    DESCRIPTION
        "Cisco Firepower storage:AuthKey:name managed object property"
    ::= { cfprStorageAuthKeyEntry 6 }

cfprStorageAuthKeyPassword OBJECT-TYPE
    SYNTAX       SnmpAdminString
    MAX-ACCESS   read-only
    STATUS       current
    DESCRIPTION
        "Cisco Firepower storage:AuthKey:password managed object property"
    ::= { cfprStorageAuthKeyEntry 7 }

cfprStorageAuthKeyPolicyLevel OBJECT-TYPE
    SYNTAX       Gauge32
    MAX-ACCESS   read-only
    STATUS       current
    DESCRIPTION
        "Cisco Firepower storage:AuthKey:policyLevel managed
        object property"
    ::= { cfprStorageAuthKeyEntry 8 }

cfprStorageAuthKeyPolicyOwner OBJECT-TYPE
    SYNTAX       CfprPolicyPolicyOwner
    MAX-ACCESS   read-only
    STATUS       current
    DESCRIPTION
        "Cisco Firepower storage:AuthKey:policyOwner managed
        object property"
    ::= { cfprStorageAuthKeyEntry 9 }

cfprStorageAuthKeyType OBJECT-TYPE
    SYNTAX       CfprStorageKeyType
    MAX-ACCESS   read-only
    STATUS       current
    DESCRIPTION
        "Cisco Firepower storage:AuthKey:type managed object property"
    ::= { cfprStorageAuthKeyEntry 10 }

cfprStorageAuthKeyUserId OBJECT-TYPE
    SYNTAX       SnmpAdminString
    MAX-ACCESS   read-only
    STATUS       current
    DESCRIPTION
        "Cisco Firepower storage:AuthKey:userId managed object property"
    ::= { cfprStorageAuthKeyEntry 11 }

cfprStorageConnectionDefTable OBJECT-TYPE
    SYNTAX           SEQUENCE OF CfprStorageConnectionDefEntry
    MAX-ACCESS       not-accessible
    STATUS           current
    DESCRIPTION
        "Cisco Firepower storage:ConnectionDef managed object table"
    ::= { cfprStorageObjects 2 }

cfprStorageConnectionDefEntry OBJECT-TYPE
    SYNTAX           CfprStorageConnectionDefEntry
    MAX-ACCESS       not-accessible
    STATUS           current
    DESCRIPTION
        "Entry for the cfprStorageConnectionDefTable table."
    INDEX { cfprStorageConnectionDefInstanceId }
    ::= { cfprStorageConnectionDefTable 1 }

CfprStorageConnectionDefEntry ::= SEQUENCE {
    cfprStorageConnectionDefInstanceId                               CfprManagedObjectId,
    cfprStorageConnectionDefDn                                       CfprManagedObjectDn,
    cfprStorageConnectionDefRn                                       SnmpAdminString,
    cfprStorageConnectionDefDescr                                    SnmpAdminString,
    cfprStorageConnectionDefIntId                                    SnmpAdminString,
    cfprStorageConnectionDefName                                     SnmpAdminString,
    cfprStorageConnectionDefOperState                                CfprStorageOperState,
    cfprStorageConnectionDefPolicyLevel                              Gauge32,
    cfprStorageConnectionDefPolicyOwner                              CfprPolicyPolicyOwner,
    cfprStorageConnectionDefZoningType                               CfprStorageFcZoningType
}

cfprStorageConnectionDefInstanceId OBJECT-TYPE
    SYNTAX       CfprManagedObjectId
    MAX-ACCESS   not-accessible
    STATUS       current
    DESCRIPTION
        "Instance identifier of the managed object."
    ::= { cfprStorageConnectionDefEntry 1 }

cfprStorageConnectionDefDn OBJECT-TYPE
    SYNTAX       CfprManagedObjectDn
    MAX-ACCESS   read-only
    STATUS       current
    DESCRIPTION
        "Cisco Firepower storage:ConnectionDef:dn managed object property"
    ::= { cfprStorageConnectionDefEntry 2 }

cfprStorageConnectionDefRn OBJECT-TYPE
    SYNTAX       SnmpAdminString
    MAX-ACCESS   read-only
    STATUS       current
    DESCRIPTION
        "Cisco Firepower storage:ConnectionDef:rn managed object property"
    ::= { cfprStorageConnectionDefEntry 3 }

cfprStorageConnectionDefDescr OBJECT-TYPE
    SYNTAX       SnmpAdminString
    MAX-ACCESS   read-only
    STATUS       current
    DESCRIPTION
        "Cisco Firepower storage:ConnectionDef:descr managed
        object property"
    ::= { cfprStorageConnectionDefEntry 4 }

cfprStorageConnectionDefIntId OBJECT-TYPE
    SYNTAX       SnmpAdminString
    MAX-ACCESS   read-only
    STATUS       current
    DESCRIPTION
        "Cisco Firepower storage:ConnectionDef:intId managed
        object property"
    ::= { cfprStorageConnectionDefEntry 5 }

cfprStorageConnectionDefName OBJECT-TYPE
    SYNTAX       SnmpAdminString
    MAX-ACCESS   read-only
    STATUS       current
    DESCRIPTION
        "Cisco Firepower storage:ConnectionDef:name managed
        object property"
    ::= { cfprStorageConnectionDefEntry 6 }

cfprStorageConnectionDefOperState OBJECT-TYPE
    SYNTAX       CfprStorageOperState
    MAX-ACCESS   read-only
    STATUS       current
    DESCRIPTION
        "Cisco Firepower storage:ConnectionDef:operState
        managed object property"
    ::= { cfprStorageConnectionDefEntry 7 }

cfprStorageConnectionDefPolicyLevel OBJECT-TYPE
    SYNTAX       Gauge32
    MAX-ACCESS   read-only
    STATUS       current
    DESCRIPTION
        "Cisco Firepower storage:ConnectionDef:policyLevel
        managed object property"
    ::= { cfprStorageConnectionDefEntry 8 }

cfprStorageConnectionDefPolicyOwner OBJECT-TYPE
    SYNTAX       CfprPolicyPolicyOwner
    MAX-ACCESS   read-only
    STATUS       current
    DESCRIPTION
        "Cisco Firepower storage:ConnectionDef:policyOwner
        managed object property"
    ::= { cfprStorageConnectionDefEntry 9 }

cfprStorageConnectionDefZoningType OBJECT-TYPE
    SYNTAX       CfprStorageFcZoningType
    MAX-ACCESS   read-only
    STATUS       current
    DESCRIPTION
        "Cisco Firepower storage:ConnectionDef:zoningType
        managed object property"
    ::= { cfprStorageConnectionDefEntry 10 }

cfprStorageConnectionPolicyTable OBJECT-TYPE
    SYNTAX           SEQUENCE OF CfprStorageConnectionPolicyEntry
    MAX-ACCESS       not-accessible
    STATUS           current
    DESCRIPTION
        "Cisco Firepower storage:ConnectionPolicy managed object table"
    ::= { cfprStorageObjects 3 }

cfprStorageConnectionPolicyEntry OBJECT-TYPE
    SYNTAX           CfprStorageConnectionPolicyEntry
    MAX-ACCESS       not-accessible
    STATUS           current
    DESCRIPTION
        "Entry for the cfprStorageConnectionPolicyTable table."
    INDEX { cfprStorageConnectionPolicyInstanceId }
    ::= { cfprStorageConnectionPolicyTable 1 }

CfprStorageConnectionPolicyEntry ::= SEQUENCE {
    cfprStorageConnectionPolicyInstanceId                            CfprManagedObjectId,
    cfprStorageConnectionPolicyDn                                    CfprManagedObjectDn,
    cfprStorageConnectionPolicyRn                                    SnmpAdminString,
    cfprStorageConnectionPolicyDescr                                 SnmpAdminString,
    cfprStorageConnectionPolicyIntId                                 SnmpAdminString,
    cfprStorageConnectionPolicyName                                  SnmpAdminString,
    cfprStorageConnectionPolicyOperState                             CfprStorageOperState,
    cfprStorageConnectionPolicyPolicyLevel                           Gauge32,
    cfprStorageConnectionPolicyPolicyOwner                           CfprPolicyPolicyOwner,
    cfprStorageConnectionPolicyZoningType                            CfprStorageFcZoningType
}

cfprStorageConnectionPolicyInstanceId OBJECT-TYPE
    SYNTAX       CfprManagedObjectId
    MAX-ACCESS   not-accessible
    STATUS       current
    DESCRIPTION
        "Instance identifier of the managed object."
    ::= { cfprStorageConnectionPolicyEntry 1 }

cfprStorageConnectionPolicyDn OBJECT-TYPE
    SYNTAX       CfprManagedObjectDn
    MAX-ACCESS   read-only
    STATUS       current
    DESCRIPTION
        "Cisco Firepower storage:ConnectionPolicy:dn managed
        object property"
    ::= { cfprStorageConnectionPolicyEntry 2 }

cfprStorageConnectionPolicyRn OBJECT-TYPE
    SYNTAX       SnmpAdminString
    MAX-ACCESS   read-only
    STATUS       current
    DESCRIPTION
        "Cisco Firepower storage:ConnectionPolicy:rn managed
        object property"
    ::= { cfprStorageConnectionPolicyEntry 3 }

cfprStorageConnectionPolicyDescr OBJECT-TYPE
    SYNTAX       SnmpAdminString
    MAX-ACCESS   read-only
    STATUS       current
    DESCRIPTION
        "Cisco Firepower storage:ConnectionPolicy:descr
        managed object property"
    ::= { cfprStorageConnectionPolicyEntry 4 }

cfprStorageConnectionPolicyIntId OBJECT-TYPE
    SYNTAX       SnmpAdminString
    MAX-ACCESS   read-only
    STATUS       current
    DESCRIPTION
        "Cisco Firepower storage:ConnectionPolicy:intId
        managed object property"
    ::= { cfprStorageConnectionPolicyEntry 5 }

cfprStorageConnectionPolicyName OBJECT-TYPE
    SYNTAX       SnmpAdminString
    MAX-ACCESS   read-only
    STATUS       current
    DESCRIPTION
        "Cisco Firepower storage:ConnectionPolicy:name
        managed object property"
    ::= { cfprStorageConnectionPolicyEntry 6 }

cfprStorageConnectionPolicyOperState OBJECT-TYPE
    SYNTAX       CfprStorageOperState
    MAX-ACCESS   read-only
    STATUS       current
    DESCRIPTION
        "Cisco Firepower storage:ConnectionPolicy:operState
        managed object property"
    ::= { cfprStorageConnectionPolicyEntry 7 }

cfprStorageConnectionPolicyPolicyLevel OBJECT-TYPE
    SYNTAX       Gauge32
    MAX-ACCESS   read-only
    STATUS       current
    DESCRIPTION
        "Cisco Firepower storage:ConnectionPolicy:policyLevel
        managed object property"
    ::= { cfprStorageConnectionPolicyEntry 8 }

cfprStorageConnectionPolicyPolicyOwner OBJECT-TYPE
    SYNTAX       CfprPolicyPolicyOwner
    MAX-ACCESS   read-only
    STATUS       current
    DESCRIPTION
        "Cisco Firepower storage:ConnectionPolicy:policyOwner
        managed object property"
    ::= { cfprStorageConnectionPolicyEntry 9 }

cfprStorageConnectionPolicyZoningType OBJECT-TYPE
    SYNTAX       CfprStorageFcZoningType
    MAX-ACCESS   read-only
    STATUS       current
    DESCRIPTION
        "Cisco Firepower storage:ConnectionPolicy:zoningType
        managed object property"
    ::= { cfprStorageConnectionPolicyEntry 10 }

cfprStorageControllerTable OBJECT-TYPE
    SYNTAX           SEQUENCE OF CfprStorageControllerEntry
    MAX-ACCESS       not-accessible
    STATUS           current
    DESCRIPTION
        "Cisco Firepower storage:Controller managed object table"
    ::= { cfprStorageObjects 4 }

cfprStorageControllerEntry OBJECT-TYPE
    SYNTAX           CfprStorageControllerEntry
    MAX-ACCESS       not-accessible
    STATUS           current
    DESCRIPTION
        "Entry for the cfprStorageControllerTable table."
    INDEX { cfprStorageControllerInstanceId }
    ::= { cfprStorageControllerTable 1 }

CfprStorageControllerEntry ::= SEQUENCE {
    cfprStorageControllerInstanceId                                  CfprManagedObjectId,
    cfprStorageControllerDn                                          CfprManagedObjectDn,
    cfprStorageControllerRn                                          SnmpAdminString,
    cfprStorageControllerControllerStatus                            CfprStorageControllerStatus,
    cfprStorageControllerDeviceRaidSupport                           SnmpAdminString,
    cfprStorageControllerFaultMonitoring                             CfprStorageControllerFaultMonitoring,
    cfprStorageControllerHwRevision                                  SnmpAdminString,
    cfprStorageControllerId                                          CfprStorageControllerId,
    cfprStorageControllerLc                                          CfprFsmLifecycle,
    cfprStorageControllerLocationDn                                  SnmpAdminString,
    cfprStorageControllerModel                                       SnmpAdminString,
    cfprStorageControllerOobControllerId                             Gauge32,
    cfprStorageControllerOobInterfaceSupported                       TruthValue,
    cfprStorageControllerOperQualifierReason                         SnmpAdminString,
    cfprStorageControllerOperState                                   CfprEquipmentOperability,
    cfprStorageControllerOperability                                 CfprEquipmentOperability,
    cfprStorageControllerPartNumber                                  SnmpAdminString,
    cfprStorageControllerPciAddr                                     SnmpAdminString,
    cfprStorageControllerPciSlot                                     SnmpAdminString,
    cfprStorageControllerPerf                                        CfprEquipmentSensorThresholdStatus,
    cfprStorageControllerPower                                       CfprEquipmentPowerState,
    cfprStorageControllerPresence                                    CfprEquipmentPresence,
    cfprStorageControllerRaidSupport                                 SnmpAdminString,
    cfprStorageControllerRebuildRate                                 Gauge32,
    cfprStorageControllerRevision                                    SnmpAdminString,
    cfprStorageControllerSerial                                      SnmpAdminString,
    cfprStorageControllerThermal                                     CfprEquipmentSensorThresholdStatus,
    cfprStorageControllerType                                        CfprStorageControllerType,
    cfprStorageControllerVendor                                      SnmpAdminString,
    cfprStorageControllerVid                                         SnmpAdminString,
    cfprStorageControllerVoltage                                     CfprEquipmentSensorThresholdStatus
}

cfprStorageControllerInstanceId OBJECT-TYPE
    SYNTAX       CfprManagedObjectId
    MAX-ACCESS   not-accessible
    STATUS       current
    DESCRIPTION
        "Instance identifier of the managed object."
    ::= { cfprStorageControllerEntry 1 }

cfprStorageControllerDn OBJECT-TYPE
    SYNTAX       CfprManagedObjectDn
    MAX-ACCESS   read-only
    STATUS       current
    DESCRIPTION
        "Cisco Firepower storage:Controller:dn managed object property"
    ::= { cfprStorageControllerEntry 2 }

cfprStorageControllerRn OBJECT-TYPE
    SYNTAX       SnmpAdminString
    MAX-ACCESS   read-only
    STATUS       current
    DESCRIPTION
        "Cisco Firepower storage:Controller:rn managed object property"
    ::= { cfprStorageControllerEntry 3 }

cfprStorageControllerControllerStatus OBJECT-TYPE
    SYNTAX       CfprStorageControllerStatus
    MAX-ACCESS   read-only
    STATUS       current
    DESCRIPTION
        "Cisco Firepower storage:Controller:controllerStatus
        managed object property"
    ::= { cfprStorageControllerEntry 4 }

cfprStorageControllerDeviceRaidSupport OBJECT-TYPE
    SYNTAX       SnmpAdminString
    MAX-ACCESS   read-only
    STATUS       current
    DESCRIPTION
        "Cisco Firepower storage:Controller:deviceRaidSupport
        managed object property"
    ::= { cfprStorageControllerEntry 5 }

cfprStorageControllerFaultMonitoring OBJECT-TYPE
    SYNTAX       CfprStorageControllerFaultMonitoring
    MAX-ACCESS   read-only
    STATUS       current
    DESCRIPTION
        "Cisco Firepower storage:Controller:faultMonitoring
        managed object property"
    ::= { cfprStorageControllerEntry 6 }

cfprStorageControllerHwRevision OBJECT-TYPE
    SYNTAX       SnmpAdminString
    MAX-ACCESS   read-only
    STATUS       current
    DESCRIPTION
        "Cisco Firepower storage:Controller:hwRevision
        managed object property"
    ::= { cfprStorageControllerEntry 7 }

cfprStorageControllerId OBJECT-TYPE
    SYNTAX       CfprStorageControllerId
    MAX-ACCESS   read-only
    STATUS       current
    DESCRIPTION
        "Cisco Firepower storage:Controller:id managed object property"
    ::= { cfprStorageControllerEntry 8 }

cfprStorageControllerLc OBJECT-TYPE
    SYNTAX       CfprFsmLifecycle
    MAX-ACCESS   read-only
    STATUS       current
    DESCRIPTION
        "Cisco Firepower storage:Controller:lc managed object property"
    ::= { cfprStorageControllerEntry 9 }

cfprStorageControllerLocationDn OBJECT-TYPE
    SYNTAX       SnmpAdminString
    MAX-ACCESS   read-only
    STATUS       current
    DESCRIPTION
        "Cisco Firepower storage:Controller:locationDn
        managed object property"
    ::= { cfprStorageControllerEntry 10 }

cfprStorageControllerModel OBJECT-TYPE
    SYNTAX       SnmpAdminString
    MAX-ACCESS   read-only
    STATUS       current
    DESCRIPTION
        "Cisco Firepower storage:Controller:model managed object property"
    ::= { cfprStorageControllerEntry 11 }

cfprStorageControllerOobControllerId OBJECT-TYPE
    SYNTAX       Gauge32
    MAX-ACCESS   read-only
    STATUS       current
    DESCRIPTION
        "Cisco Firepower storage:Controller:oobControllerId
        managed object property"
    ::= { cfprStorageControllerEntry 12 }

cfprStorageControllerOobInterfaceSupported OBJECT-TYPE
    SYNTAX       TruthValue
    MAX-ACCESS   read-only
    STATUS       current
    DESCRIPTION
        "Cisco Firepower storage:Controller:oobInterfaceSupported
        managed object property"
    ::= { cfprStorageControllerEntry 13 }

cfprStorageControllerOperQualifierReason OBJECT-TYPE
    SYNTAX       SnmpAdminString
    MAX-ACCESS   read-only
    STATUS       current
    DESCRIPTION
        "Cisco Firepower storage:Controller:operQualifierReason
        managed object property"
    ::= { cfprStorageControllerEntry 14 }

cfprStorageControllerOperState OBJECT-TYPE
    SYNTAX       CfprEquipmentOperability
    MAX-ACCESS   read-only
    STATUS       current
    DESCRIPTION
        "Cisco Firepower storage:Controller:operState managed
        object property"
    ::= { cfprStorageControllerEntry 15 }

cfprStorageControllerOperability OBJECT-TYPE
    SYNTAX       CfprEquipmentOperability
    MAX-ACCESS   read-only
    STATUS       current
    DESCRIPTION
        "Cisco Firepower storage:Controller:operability
        managed object property"
    ::= { cfprStorageControllerEntry 16 }

cfprStorageControllerPartNumber OBJECT-TYPE
    SYNTAX       SnmpAdminString
    MAX-ACCESS   read-only
    STATUS       current
    DESCRIPTION
        "Cisco Firepower storage:Controller:partNumber
        managed object property"
    ::= { cfprStorageControllerEntry 17 }

cfprStorageControllerPciAddr OBJECT-TYPE
    SYNTAX       SnmpAdminString
    MAX-ACCESS   read-only
    STATUS       current
    DESCRIPTION
        "Cisco Firepower storage:Controller:pciAddr managed
        object property"
    ::= { cfprStorageControllerEntry 18 }

cfprStorageControllerPciSlot OBJECT-TYPE
    SYNTAX       SnmpAdminString
    MAX-ACCESS   read-only
    STATUS       current
    DESCRIPTION
        "Cisco Firepower storage:Controller:pciSlot managed
        object property"
    ::= { cfprStorageControllerEntry 19 }

cfprStorageControllerPerf OBJECT-TYPE
    SYNTAX       CfprEquipmentSensorThresholdStatus
    MAX-ACCESS   read-only
    STATUS       current
    DESCRIPTION
        "Cisco Firepower storage:Controller:perf managed object property"
    ::= { cfprStorageControllerEntry 20 }

cfprStorageControllerPower OBJECT-TYPE
    SYNTAX       CfprEquipmentPowerState
    MAX-ACCESS   read-only
    STATUS       current
    DESCRIPTION
        "Cisco Firepower storage:Controller:power managed object property"
    ::= { cfprStorageControllerEntry 21 }

cfprStorageControllerPresence OBJECT-TYPE
    SYNTAX       CfprEquipmentPresence
    MAX-ACCESS   read-only
    STATUS       current
    DESCRIPTION
        "Cisco Firepower storage:Controller:presence managed
        object property"
    ::= { cfprStorageControllerEntry 22 }

cfprStorageControllerRaidSupport OBJECT-TYPE
    SYNTAX       SnmpAdminString
    MAX-ACCESS   read-only
    STATUS       current
    DESCRIPTION
        "Cisco Firepower storage:Controller:raidSupport
        managed object property"
    ::= { cfprStorageControllerEntry 23 }

cfprStorageControllerRebuildRate OBJECT-TYPE
    SYNTAX       Gauge32
    MAX-ACCESS   read-only
    STATUS       current
    DESCRIPTION
        "Cisco Firepower storage:Controller:rebuildRate
        managed object property"
    ::= { cfprStorageControllerEntry 24 }

cfprStorageControllerRevision OBJECT-TYPE
    SYNTAX       SnmpAdminString
    MAX-ACCESS   read-only
    STATUS       current
    DESCRIPTION
        "Cisco Firepower storage:Controller:revision managed
        object property"
    ::= { cfprStorageControllerEntry 25 }

cfprStorageControllerSerial OBJECT-TYPE
    SYNTAX       SnmpAdminString
    MAX-ACCESS   read-only
    STATUS       current
    DESCRIPTION
        "Cisco Firepower storage:Controller:serial managed
        object property"
    ::= { cfprStorageControllerEntry 26 }

cfprStorageControllerThermal OBJECT-TYPE
    SYNTAX       CfprEquipmentSensorThresholdStatus
    MAX-ACCESS   read-only
    STATUS       current
    DESCRIPTION
        "Cisco Firepower storage:Controller:thermal managed
        object property"
    ::= { cfprStorageControllerEntry 27 }

cfprStorageControllerType OBJECT-TYPE
    SYNTAX       CfprStorageControllerType
    MAX-ACCESS   read-only
    STATUS       current
    DESCRIPTION
        "Cisco Firepower storage:Controller:type managed object property"
    ::= { cfprStorageControllerEntry 28 }

cfprStorageControllerVendor OBJECT-TYPE
    SYNTAX       SnmpAdminString
    MAX-ACCESS   read-only
    STATUS       current
    DESCRIPTION
        "Cisco Firepower storage:Controller:vendor managed
        object property"
    ::= { cfprStorageControllerEntry 29 }

cfprStorageControllerVid OBJECT-TYPE
    SYNTAX       SnmpAdminString
    MAX-ACCESS   read-only
    STATUS       current
    DESCRIPTION
        "Cisco Firepower storage:Controller:vid managed object property"
    ::= { cfprStorageControllerEntry 30 }

cfprStorageControllerVoltage OBJECT-TYPE
    SYNTAX       CfprEquipmentSensorThresholdStatus
    MAX-ACCESS   read-only
    STATUS       current
    DESCRIPTION
        "Cisco Firepower storage:Controller:voltage managed
        object property"
    ::= { cfprStorageControllerEntry 31 }

cfprStorageDomainEpTable OBJECT-TYPE
    SYNTAX           SEQUENCE OF CfprStorageDomainEpEntry
    MAX-ACCESS       not-accessible
    STATUS           current
    DESCRIPTION
        "Cisco Firepower storage:DomainEp managed object table"
    ::= { cfprStorageObjects 5 }

cfprStorageDomainEpEntry OBJECT-TYPE
    SYNTAX           CfprStorageDomainEpEntry
    MAX-ACCESS       not-accessible
    STATUS           current
    DESCRIPTION
        "Entry for the cfprStorageDomainEpTable table."
    INDEX { cfprStorageDomainEpInstanceId }
    ::= { cfprStorageDomainEpTable 1 }

CfprStorageDomainEpEntry ::= SEQUENCE {
    cfprStorageDomainEpInstanceId                                    CfprManagedObjectId,
    cfprStorageDomainEpDn                                            CfprManagedObjectDn,
    cfprStorageDomainEpRn                                            SnmpAdminString
}

cfprStorageDomainEpInstanceId OBJECT-TYPE
    SYNTAX       CfprManagedObjectId
    MAX-ACCESS   not-accessible
    STATUS       current
    DESCRIPTION
        "Instance identifier of the managed object."
    ::= { cfprStorageDomainEpEntry 1 }

cfprStorageDomainEpDn OBJECT-TYPE
    SYNTAX       CfprManagedObjectDn
    MAX-ACCESS   read-only
    STATUS       current
    DESCRIPTION
        "Cisco Firepower storage:DomainEp:dn managed object property"
    ::= { cfprStorageDomainEpEntry 2 }

cfprStorageDomainEpRn OBJECT-TYPE
    SYNTAX       SnmpAdminString
    MAX-ACCESS   read-only
    STATUS       current
    DESCRIPTION
        "Cisco Firepower storage:DomainEp:rn managed object property"
    ::= { cfprStorageDomainEpEntry 3 }

cfprStorageDriveTable OBJECT-TYPE
    SYNTAX           SEQUENCE OF CfprStorageDriveEntry
    MAX-ACCESS       not-accessible
    STATUS           current
    DESCRIPTION
        "Cisco Firepower storage:Drive managed object table"
    ::= { cfprStorageObjects 6 }

cfprStorageDriveEntry OBJECT-TYPE
    SYNTAX           CfprStorageDriveEntry
    MAX-ACCESS       not-accessible
    STATUS           current
    DESCRIPTION
        "Entry for the cfprStorageDriveTable table."
    INDEX { cfprStorageDriveInstanceId }
    ::= { cfprStorageDriveTable 1 }

CfprStorageDriveEntry ::= SEQUENCE {
    cfprStorageDriveInstanceId                                       CfprManagedObjectId,
    cfprStorageDriveDn                                               CfprManagedObjectDn,
    cfprStorageDriveRn                                               SnmpAdminString,
    cfprStorageDriveId                                               Gauge32,
    cfprStorageDriveModel                                            SnmpAdminString,
    cfprStorageDrivePciAddr                                          SnmpAdminString,
    cfprStorageDriveRevision                                         SnmpAdminString,
    cfprStorageDriveSerial                                           SnmpAdminString,
    cfprStorageDriveVendor                                           SnmpAdminString
}

cfprStorageDriveInstanceId OBJECT-TYPE
    SYNTAX       CfprManagedObjectId
    MAX-ACCESS   not-accessible
    STATUS       current
    DESCRIPTION
        "Instance identifier of the managed object."
    ::= { cfprStorageDriveEntry 1 }

cfprStorageDriveDn OBJECT-TYPE
    SYNTAX       CfprManagedObjectDn
    MAX-ACCESS   read-only
    STATUS       current
    DESCRIPTION
        "Cisco Firepower storage:Drive:dn managed object property"
    ::= { cfprStorageDriveEntry 2 }

cfprStorageDriveRn OBJECT-TYPE
    SYNTAX       SnmpAdminString
    MAX-ACCESS   read-only
    STATUS       current
    DESCRIPTION
        "Cisco Firepower storage:Drive:rn managed object property"
    ::= { cfprStorageDriveEntry 3 }

cfprStorageDriveId OBJECT-TYPE
    SYNTAX       Gauge32
    MAX-ACCESS   read-only
    STATUS       current
    DESCRIPTION
        "Cisco Firepower storage:Drive:id managed object property"
    ::= { cfprStorageDriveEntry 4 }

cfprStorageDriveModel OBJECT-TYPE
    SYNTAX       SnmpAdminString
    MAX-ACCESS   read-only
    STATUS       current
    DESCRIPTION
        "Cisco Firepower storage:Drive:model managed object property"
    ::= { cfprStorageDriveEntry 5 }

cfprStorageDrivePciAddr OBJECT-TYPE
    SYNTAX       SnmpAdminString
    MAX-ACCESS   read-only
    STATUS       current
    DESCRIPTION
        "Cisco Firepower storage:Drive:pciAddr managed object property"
    ::= { cfprStorageDriveEntry 6 }

cfprStorageDriveRevision OBJECT-TYPE
    SYNTAX       SnmpAdminString
    MAX-ACCESS   read-only
    STATUS       current
    DESCRIPTION
        "Cisco Firepower storage:Drive:revision managed object property"
    ::= { cfprStorageDriveEntry 7 }

cfprStorageDriveSerial OBJECT-TYPE
    SYNTAX       SnmpAdminString
    MAX-ACCESS   read-only
    STATUS       current
    DESCRIPTION
        "Cisco Firepower storage:Drive:serial managed object property"
    ::= { cfprStorageDriveEntry 8 }

cfprStorageDriveVendor OBJECT-TYPE
    SYNTAX       SnmpAdminString
    MAX-ACCESS   read-only
    STATUS       current
    DESCRIPTION
        "Cisco Firepower storage:Drive:vendor managed object property"
    ::= { cfprStorageDriveEntry 9 }

cfprStorageEnclosureTable OBJECT-TYPE
    SYNTAX           SEQUENCE OF CfprStorageEnclosureEntry
    MAX-ACCESS       not-accessible
    STATUS           current
    DESCRIPTION
        "Cisco Firepower storage:Enclosure managed object table"
    ::= { cfprStorageObjects 7 }

cfprStorageEnclosureEntry OBJECT-TYPE
    SYNTAX           CfprStorageEnclosureEntry
    MAX-ACCESS       not-accessible
    STATUS           current
    DESCRIPTION
        "Entry for the cfprStorageEnclosureTable table."
    INDEX { cfprStorageEnclosureInstanceId }
    ::= { cfprStorageEnclosureTable 1 }

CfprStorageEnclosureEntry ::= SEQUENCE {
    cfprStorageEnclosureInstanceId                                   CfprManagedObjectId,
    cfprStorageEnclosureDn                                           CfprManagedObjectDn,
    cfprStorageEnclosureRn                                           SnmpAdminString,
    cfprStorageEnclosureId                                           Gauge32,
    cfprStorageEnclosureLc                                           CfprFsmLifecycle,
    cfprStorageEnclosureModel                                        SnmpAdminString,
    cfprStorageEnclosureNumSlots                                     Gauge32,
    cfprStorageEnclosureRevision                                     SnmpAdminString,
    cfprStorageEnclosureSerial                                       SnmpAdminString,
    cfprStorageEnclosureVendor                                       SnmpAdminString
}

cfprStorageEnclosureInstanceId OBJECT-TYPE
    SYNTAX       CfprManagedObjectId
    MAX-ACCESS   not-accessible
    STATUS       current
    DESCRIPTION
        "Instance identifier of the managed object."
    ::= { cfprStorageEnclosureEntry 1 }

cfprStorageEnclosureDn OBJECT-TYPE
    SYNTAX       CfprManagedObjectDn
    MAX-ACCESS   read-only
    STATUS       current
    DESCRIPTION
        "Cisco Firepower storage:Enclosure:dn managed object property"
    ::= { cfprStorageEnclosureEntry 2 }

cfprStorageEnclosureRn OBJECT-TYPE
    SYNTAX       SnmpAdminString
    MAX-ACCESS   read-only
    STATUS       current
    DESCRIPTION
        "Cisco Firepower storage:Enclosure:rn managed object property"
    ::= { cfprStorageEnclosureEntry 3 }

cfprStorageEnclosureId OBJECT-TYPE
    SYNTAX       Gauge32
    MAX-ACCESS   read-only
    STATUS       current
    DESCRIPTION
        "Cisco Firepower storage:Enclosure:id managed object property"
    ::= { cfprStorageEnclosureEntry 4 }

cfprStorageEnclosureLc OBJECT-TYPE
    SYNTAX       CfprFsmLifecycle
    MAX-ACCESS   read-only
    STATUS       current
    DESCRIPTION
        "Cisco Firepower storage:Enclosure:lc managed object property"
    ::= { cfprStorageEnclosureEntry 5 }

cfprStorageEnclosureModel OBJECT-TYPE
    SYNTAX       SnmpAdminString
    MAX-ACCESS   read-only
    STATUS       current
    DESCRIPTION
        "Cisco Firepower storage:Enclosure:model managed object property"
    ::= { cfprStorageEnclosureEntry 6 }

cfprStorageEnclosureNumSlots OBJECT-TYPE
    SYNTAX       Gauge32
    MAX-ACCESS   read-only
    STATUS       current
    DESCRIPTION
        "Cisco Firepower storage:Enclosure:numSlots managed
        object property"
    ::= { cfprStorageEnclosureEntry 7 }

cfprStorageEnclosureRevision OBJECT-TYPE
    SYNTAX       SnmpAdminString
    MAX-ACCESS   read-only
    STATUS       current
    DESCRIPTION
        "Cisco Firepower storage:Enclosure:revision managed
        object property"
    ::= { cfprStorageEnclosureEntry 8 }

cfprStorageEnclosureSerial OBJECT-TYPE
    SYNTAX       SnmpAdminString
    MAX-ACCESS   read-only
    STATUS       current
    DESCRIPTION
        "Cisco Firepower storage:Enclosure:serial managed object property"
    ::= { cfprStorageEnclosureEntry 9 }

cfprStorageEnclosureVendor OBJECT-TYPE
    SYNTAX       SnmpAdminString
    MAX-ACCESS   read-only
    STATUS       current
    DESCRIPTION
        "Cisco Firepower storage:Enclosure:vendor managed object property"
    ::= { cfprStorageEnclosureEntry 10 }

cfprStorageEpUserTable OBJECT-TYPE
    SYNTAX           SEQUENCE OF CfprStorageEpUserEntry
    MAX-ACCESS       not-accessible
    STATUS           current
    DESCRIPTION
        "Cisco Firepower storage:EpUser managed object table"
    ::= { cfprStorageObjects 8 }

cfprStorageEpUserEntry OBJECT-TYPE
    SYNTAX           CfprStorageEpUserEntry
    MAX-ACCESS       not-accessible
    STATUS           current
    DESCRIPTION
        "Entry for the cfprStorageEpUserTable table."
    INDEX { cfprStorageEpUserInstanceId }
    ::= { cfprStorageEpUserTable 1 }

CfprStorageEpUserEntry ::= SEQUENCE {
    cfprStorageEpUserInstanceId                                      CfprManagedObjectId,
    cfprStorageEpUserDn                                              CfprManagedObjectDn,
    cfprStorageEpUserRn                                              SnmpAdminString,
    cfprStorageEpUserConfigState                                     CfprAaaConfigState,
    cfprStorageEpUserConfigStatusMessage                             SnmpAdminString,
    cfprStorageEpUserDescr                                           SnmpAdminString,
    cfprStorageEpUserDomain                                          SnmpAdminString,
    cfprStorageEpUserName                                            SnmpAdminString,
    cfprStorageEpUserPriv                                            CfprStorageEpAccess,
    cfprStorageEpUserPwd                                             SnmpAdminString,
    cfprStorageEpUserPwdSet                                          TruthValue
}

cfprStorageEpUserInstanceId OBJECT-TYPE
    SYNTAX       CfprManagedObjectId
    MAX-ACCESS   not-accessible
    STATUS       current
    DESCRIPTION
        "Instance identifier of the managed object."
    ::= { cfprStorageEpUserEntry 1 }

cfprStorageEpUserDn OBJECT-TYPE
    SYNTAX       CfprManagedObjectDn
    MAX-ACCESS   read-only
    STATUS       current
    DESCRIPTION
        "Cisco Firepower storage:EpUser:dn managed object property"
    ::= { cfprStorageEpUserEntry 2 }

cfprStorageEpUserRn OBJECT-TYPE
    SYNTAX       SnmpAdminString
    MAX-ACCESS   read-only
    STATUS       current
    DESCRIPTION
        "Cisco Firepower storage:EpUser:rn managed object property"
    ::= { cfprStorageEpUserEntry 3 }

cfprStorageEpUserConfigState OBJECT-TYPE
    SYNTAX       CfprAaaConfigState
    MAX-ACCESS   read-only
    STATUS       current
    DESCRIPTION
        "Cisco Firepower storage:EpUser:configState managed
        object property"
    ::= { cfprStorageEpUserEntry 4 }

cfprStorageEpUserConfigStatusMessage OBJECT-TYPE
    SYNTAX       SnmpAdminString
    MAX-ACCESS   read-only
    STATUS       current
    DESCRIPTION
        "Cisco Firepower storage:EpUser:configStatusMessage
        managed object property"
    ::= { cfprStorageEpUserEntry 5 }

cfprStorageEpUserDescr OBJECT-TYPE
    SYNTAX       SnmpAdminString
    MAX-ACCESS   read-only
    STATUS       current
    DESCRIPTION
        "Cisco Firepower storage:EpUser:descr managed object property"
    ::= { cfprStorageEpUserEntry 6 }

cfprStorageEpUserDomain OBJECT-TYPE
    SYNTAX       SnmpAdminString
    MAX-ACCESS   read-only
    STATUS       current
    DESCRIPTION
        "Cisco Firepower storage:EpUser:domain managed object property"
    ::= { cfprStorageEpUserEntry 7 }

cfprStorageEpUserName OBJECT-TYPE
    SYNTAX       SnmpAdminString
    MAX-ACCESS   read-only
    STATUS       current
    DESCRIPTION
        "Cisco Firepower storage:EpUser:name managed object property"
    ::= { cfprStorageEpUserEntry 8 }

cfprStorageEpUserPriv OBJECT-TYPE
    SYNTAX       CfprStorageEpAccess
    MAX-ACCESS   read-only
    STATUS       current
    DESCRIPTION
        "Cisco Firepower storage:EpUser:priv managed object property"
    ::= { cfprStorageEpUserEntry 9 }

cfprStorageEpUserPwd OBJECT-TYPE
    SYNTAX       SnmpAdminString
    MAX-ACCESS   read-only
    STATUS       current
    DESCRIPTION
        "Cisco Firepower storage:EpUser:pwd managed object property"
    ::= { cfprStorageEpUserEntry 10 }

cfprStorageEpUserPwdSet OBJECT-TYPE
    SYNTAX       TruthValue
    MAX-ACCESS   read-only
    STATUS       current
    DESCRIPTION
        "Cisco Firepower storage:EpUser:pwdSet managed object property"
    ::= { cfprStorageEpUserEntry 11 }

cfprStorageEtherIfTable OBJECT-TYPE
    SYNTAX           SEQUENCE OF CfprStorageEtherIfEntry
    MAX-ACCESS       not-accessible
    STATUS           current
    DESCRIPTION
        "Cisco Firepower storage:EtherIf managed object table"
    ::= { cfprStorageObjects 9 }

cfprStorageEtherIfEntry OBJECT-TYPE
    SYNTAX           CfprStorageEtherIfEntry
    MAX-ACCESS       not-accessible
    STATUS           current
    DESCRIPTION
        "Entry for the cfprStorageEtherIfTable table."
    INDEX { cfprStorageEtherIfInstanceId }
    ::= { cfprStorageEtherIfTable 1 }

CfprStorageEtherIfEntry ::= SEQUENCE {
    cfprStorageEtherIfInstanceId                                     CfprManagedObjectId,
    cfprStorageEtherIfDn                                             CfprManagedObjectDn,
    cfprStorageEtherIfRn                                             SnmpAdminString,
    cfprStorageEtherIfName                                           SnmpAdminString,
    cfprStorageEtherIfVlanType                                       CfprStorageEtherIfVlanType
}

cfprStorageEtherIfInstanceId OBJECT-TYPE
    SYNTAX       CfprManagedObjectId
    MAX-ACCESS   not-accessible
    STATUS       current
    DESCRIPTION
        "Instance identifier of the managed object."
    ::= { cfprStorageEtherIfEntry 1 }

cfprStorageEtherIfDn OBJECT-TYPE
    SYNTAX       CfprManagedObjectDn
    MAX-ACCESS   read-only
    STATUS       current
    DESCRIPTION
        "Cisco Firepower storage:EtherIf:dn managed object property"
    ::= { cfprStorageEtherIfEntry 2 }

cfprStorageEtherIfRn OBJECT-TYPE
    SYNTAX       SnmpAdminString
    MAX-ACCESS   read-only
    STATUS       current
    DESCRIPTION
        "Cisco Firepower storage:EtherIf:rn managed object property"
    ::= { cfprStorageEtherIfEntry 3 }

cfprStorageEtherIfName OBJECT-TYPE
    SYNTAX       SnmpAdminString
    MAX-ACCESS   read-only
    STATUS       current
    DESCRIPTION
        "Cisco Firepower storage:EtherIf:name managed object property"
    ::= { cfprStorageEtherIfEntry 4 }

cfprStorageEtherIfVlanType OBJECT-TYPE
    SYNTAX       CfprStorageEtherIfVlanType
    MAX-ACCESS   read-only
    STATUS       current
    DESCRIPTION
        "Cisco Firepower storage:EtherIf:vlanType managed object property"
    ::= { cfprStorageEtherIfEntry 5 }

cfprStorageFcIfTable OBJECT-TYPE
    SYNTAX           SEQUENCE OF CfprStorageFcIfEntry
    MAX-ACCESS       not-accessible
    STATUS           current
    DESCRIPTION
        "Cisco Firepower storage:FcIf managed object table"
    ::= { cfprStorageObjects 10 }

cfprStorageFcIfEntry OBJECT-TYPE
    SYNTAX           CfprStorageFcIfEntry
    MAX-ACCESS       not-accessible
    STATUS           current
    DESCRIPTION
        "Entry for the cfprStorageFcIfTable table."
    INDEX { cfprStorageFcIfInstanceId }
    ::= { cfprStorageFcIfTable 1 }

CfprStorageFcIfEntry ::= SEQUENCE {
    cfprStorageFcIfInstanceId                                        CfprManagedObjectId,
    cfprStorageFcIfDn                                                CfprManagedObjectDn,
    cfprStorageFcIfRn                                                SnmpAdminString,
    cfprStorageFcIfName                                              SnmpAdminString
}

cfprStorageFcIfInstanceId OBJECT-TYPE
    SYNTAX       CfprManagedObjectId
    MAX-ACCESS   not-accessible
    STATUS       current
    DESCRIPTION
        "Instance identifier of the managed object."
    ::= { cfprStorageFcIfEntry 1 }

cfprStorageFcIfDn OBJECT-TYPE
    SYNTAX       CfprManagedObjectDn
    MAX-ACCESS   read-only
    STATUS       current
    DESCRIPTION
        "Cisco Firepower storage:FcIf:dn managed object property"
    ::= { cfprStorageFcIfEntry 2 }

cfprStorageFcIfRn OBJECT-TYPE
    SYNTAX       SnmpAdminString
    MAX-ACCESS   read-only
    STATUS       current
    DESCRIPTION
        "Cisco Firepower storage:FcIf:rn managed object property"
    ::= { cfprStorageFcIfEntry 3 }

cfprStorageFcIfName OBJECT-TYPE
    SYNTAX       SnmpAdminString
    MAX-ACCESS   read-only
    STATUS       current
    DESCRIPTION
        "Cisco Firepower storage:FcIf:name managed object property"
    ::= { cfprStorageFcIfEntry 4 }

cfprStorageFcTargetEpTable OBJECT-TYPE
    SYNTAX           SEQUENCE OF CfprStorageFcTargetEpEntry
    MAX-ACCESS       not-accessible
    STATUS           current
    DESCRIPTION
        "Cisco Firepower storage:FcTargetEp managed object table"
    ::= { cfprStorageObjects 11 }

cfprStorageFcTargetEpEntry OBJECT-TYPE
    SYNTAX           CfprStorageFcTargetEpEntry
    MAX-ACCESS       not-accessible
    STATUS           current
    DESCRIPTION
        "Entry for the cfprStorageFcTargetEpTable table."
    INDEX { cfprStorageFcTargetEpInstanceId }
    ::= { cfprStorageFcTargetEpTable 1 }

CfprStorageFcTargetEpEntry ::= SEQUENCE {
    cfprStorageFcTargetEpInstanceId                                  CfprManagedObjectId,
    cfprStorageFcTargetEpDn                                          CfprManagedObjectDn,
    cfprStorageFcTargetEpRn                                          SnmpAdminString,
    cfprStorageFcTargetEpDescr                                       SnmpAdminString,
    cfprStorageFcTargetEpPath                                        CfprStorageTargetPath,
    cfprStorageFcTargetEpTargetwwpn                                  SnmpAdminString
}

cfprStorageFcTargetEpInstanceId OBJECT-TYPE
    SYNTAX       CfprManagedObjectId
    MAX-ACCESS   not-accessible
    STATUS       current
    DESCRIPTION
        "Instance identifier of the managed object."
    ::= { cfprStorageFcTargetEpEntry 1 }

cfprStorageFcTargetEpDn OBJECT-TYPE
    SYNTAX       CfprManagedObjectDn
    MAX-ACCESS   read-only
    STATUS       current
    DESCRIPTION
        "Cisco Firepower storage:FcTargetEp:dn managed object property"
    ::= { cfprStorageFcTargetEpEntry 2 }

cfprStorageFcTargetEpRn OBJECT-TYPE
    SYNTAX       SnmpAdminString
    MAX-ACCESS   read-only
    STATUS       current
    DESCRIPTION
        "Cisco Firepower storage:FcTargetEp:rn managed object property"
    ::= { cfprStorageFcTargetEpEntry 3 }

cfprStorageFcTargetEpDescr OBJECT-TYPE
    SYNTAX       SnmpAdminString
    MAX-ACCESS   read-only
    STATUS       current
    DESCRIPTION
        "Cisco Firepower storage:FcTargetEp:descr managed object property"
    ::= { cfprStorageFcTargetEpEntry 4 }

cfprStorageFcTargetEpPath OBJECT-TYPE
    SYNTAX       CfprStorageTargetPath
    MAX-ACCESS   read-only
    STATUS       current
    DESCRIPTION
        "Cisco Firepower storage:FcTargetEp:path managed object property"
    ::= { cfprStorageFcTargetEpEntry 5 }

cfprStorageFcTargetEpTargetwwpn OBJECT-TYPE
    SYNTAX       SnmpAdminString
    MAX-ACCESS   read-only
    STATUS       current
    DESCRIPTION
        "Cisco Firepower storage:FcTargetEp:targetwwpn
        managed object property"
    ::= { cfprStorageFcTargetEpEntry 6 }

cfprStorageFcTargetIfTable OBJECT-TYPE
    SYNTAX           SEQUENCE OF CfprStorageFcTargetIfEntry
    MAX-ACCESS       not-accessible
    STATUS           current
    DESCRIPTION
        "Cisco Firepower storage:FcTargetIf managed object table"
    ::= { cfprStorageObjects 12 }

cfprStorageFcTargetIfEntry OBJECT-TYPE
    SYNTAX           CfprStorageFcTargetIfEntry
    MAX-ACCESS       not-accessible
    STATUS           current
    DESCRIPTION
        "Entry for the cfprStorageFcTargetIfTable table."
    INDEX { cfprStorageFcTargetIfInstanceId }
    ::= { cfprStorageFcTargetIfTable 1 }

CfprStorageFcTargetIfEntry ::= SEQUENCE {
    cfprStorageFcTargetIfInstanceId                                  CfprManagedObjectId,
    cfprStorageFcTargetIfDn                                          CfprManagedObjectDn,
    cfprStorageFcTargetIfRn                                          SnmpAdminString,
    cfprStorageFcTargetIfId                                          Unsigned64,
    cfprStorageFcTargetIfProt                                        CfprStorageProtocol
}

cfprStorageFcTargetIfInstanceId OBJECT-TYPE
    SYNTAX       CfprManagedObjectId
    MAX-ACCESS   not-accessible
    STATUS       current
    DESCRIPTION
        "Instance identifier of the managed object."
    ::= { cfprStorageFcTargetIfEntry 1 }

cfprStorageFcTargetIfDn OBJECT-TYPE
    SYNTAX       CfprManagedObjectDn
    MAX-ACCESS   read-only
    STATUS       current
    DESCRIPTION
        "Cisco Firepower storage:FcTargetIf:dn managed object property"
    ::= { cfprStorageFcTargetIfEntry 2 }

cfprStorageFcTargetIfRn OBJECT-TYPE
    SYNTAX       SnmpAdminString
    MAX-ACCESS   read-only
    STATUS       current
    DESCRIPTION
        "Cisco Firepower storage:FcTargetIf:rn managed object property"
    ::= { cfprStorageFcTargetIfEntry 3 }

cfprStorageFcTargetIfId OBJECT-TYPE
    SYNTAX       Unsigned64
    MAX-ACCESS   read-only
    STATUS       current
    DESCRIPTION
        "Cisco Firepower storage:FcTargetIf:id managed object property"
    ::= { cfprStorageFcTargetIfEntry 4 }

cfprStorageFcTargetIfProt OBJECT-TYPE
    SYNTAX       CfprStorageProtocol
    MAX-ACCESS   read-only
    STATUS       current
    DESCRIPTION
        "Cisco Firepower storage:FcTargetIf:prot managed object property"
    ::= { cfprStorageFcTargetIfEntry 5 }

cfprStorageFlexFlashCardTable OBJECT-TYPE
    SYNTAX           SEQUENCE OF CfprStorageFlexFlashCardEntry
    MAX-ACCESS       not-accessible
    STATUS           current
    DESCRIPTION
        "Cisco Firepower storage:FlexFlashCard managed object table"
    ::= { cfprStorageObjects 13 }

cfprStorageFlexFlashCardEntry OBJECT-TYPE
    SYNTAX           CfprStorageFlexFlashCardEntry
    MAX-ACCESS       not-accessible
    STATUS           current
    DESCRIPTION
        "Entry for the cfprStorageFlexFlashCardTable table."
    INDEX { cfprStorageFlexFlashCardInstanceId }
    ::= { cfprStorageFlexFlashCardTable 1 }

CfprStorageFlexFlashCardEntry ::= SEQUENCE {
    cfprStorageFlexFlashCardInstanceId                               CfprManagedObjectId,
    cfprStorageFlexFlashCardDn                                       CfprManagedObjectDn,
    cfprStorageFlexFlashCardRn                                       SnmpAdminString,
    cfprStorageFlexFlashCardBlockSize                                Gauge32,
    cfprStorageFlexFlashCardCardHealth                               CfprStorageFFCardHealth,
    cfprStorageFlexFlashCardCardMode                                 CfprStorageFFCardMode,
    cfprStorageFlexFlashCardCardState                                CfprStorageFFCardState,
    cfprStorageFlexFlashCardCardSync                                 CfprStorageFFCardSync,
    cfprStorageFlexFlashCardCardType                                 SnmpAdminString,
    cfprStorageFlexFlashCardConnectionProtocol                       CfprStorageConnectionProtocol,
    cfprStorageFlexFlashCardControllerIndex                          Gauge32,
    cfprStorageFlexFlashCardDrivesEnabled                            SnmpAdminString,
    cfprStorageFlexFlashCardId                                       Gauge32,
    cfprStorageFlexFlashCardMfgDate                                  SnmpAdminString,
    cfprStorageFlexFlashCardMfgId                                    SnmpAdminString,
    cfprStorageFlexFlashCardModel                                    SnmpAdminString,
    cfprStorageFlexFlashCardNumberOfBlocks                           Unsigned64,
    cfprStorageFlexFlashCardOemId                                    SnmpAdminString,
    cfprStorageFlexFlashCardOperQualifierReason                      SnmpAdminString,
    cfprStorageFlexFlashCardOperability                              CfprEquipmentOperability,
    cfprStorageFlexFlashCardPartitionCount                           Gauge32,
    cfprStorageFlexFlashCardPresence                                 CfprEquipmentPresence,
    cfprStorageFlexFlashCardReadErrorThreshold                       Gauge32,
    cfprStorageFlexFlashCardReadIOErrorCount                         Gauge32,
    cfprStorageFlexFlashCardRevision                                 SnmpAdminString,
    cfprStorageFlexFlashCardSerial                                   SnmpAdminString,
    cfprStorageFlexFlashCardSignature                                SnmpAdminString,
    cfprStorageFlexFlashCardSize                                     Unsigned64,
    cfprStorageFlexFlashCardSlotNumber                               Gauge32,
    cfprStorageFlexFlashCardVendor                                   SnmpAdminString,
    cfprStorageFlexFlashCardWriteEnable                              CfprStorageFFCardWriteEnable,
    cfprStorageFlexFlashCardWriteErrorThreshold                      Gauge32,
    cfprStorageFlexFlashCardWriteIOErrorCount                        Gauge32
}

cfprStorageFlexFlashCardInstanceId OBJECT-TYPE
    SYNTAX       CfprManagedObjectId
    MAX-ACCESS   not-accessible
    STATUS       current
    DESCRIPTION
        "Instance identifier of the managed object."
    ::= { cfprStorageFlexFlashCardEntry 1 }

cfprStorageFlexFlashCardDn OBJECT-TYPE
    SYNTAX       CfprManagedObjectDn
    MAX-ACCESS   read-only
    STATUS       current
    DESCRIPTION
        "Cisco Firepower storage:FlexFlashCard:dn managed object property"
    ::= { cfprStorageFlexFlashCardEntry 2 }

cfprStorageFlexFlashCardRn OBJECT-TYPE
    SYNTAX       SnmpAdminString
    MAX-ACCESS   read-only
    STATUS       current
    DESCRIPTION
        "Cisco Firepower storage:FlexFlashCard:rn managed object property"
    ::= { cfprStorageFlexFlashCardEntry 3 }

cfprStorageFlexFlashCardBlockSize OBJECT-TYPE
    SYNTAX       Gauge32
    MAX-ACCESS   read-only
    STATUS       current
    DESCRIPTION
        "Cisco Firepower storage:FlexFlashCard:blockSize
        managed object property"
    ::= { cfprStorageFlexFlashCardEntry 4 }

cfprStorageFlexFlashCardCardHealth OBJECT-TYPE
    SYNTAX       CfprStorageFFCardHealth
    MAX-ACCESS   read-only
    STATUS       current
    DESCRIPTION
        "Cisco Firepower storage:FlexFlashCard:cardHealth
        managed object property"
    ::= { cfprStorageFlexFlashCardEntry 5 }

cfprStorageFlexFlashCardCardMode OBJECT-TYPE
    SYNTAX       CfprStorageFFCardMode
    MAX-ACCESS   read-only
    STATUS       current
    DESCRIPTION
        "Cisco Firepower storage:FlexFlashCard:cardMode
        managed object property"
    ::= { cfprStorageFlexFlashCardEntry 6 }

cfprStorageFlexFlashCardCardState OBJECT-TYPE
    SYNTAX       CfprStorageFFCardState
    MAX-ACCESS   read-only
    STATUS       current
    DESCRIPTION
        "Cisco Firepower storage:FlexFlashCard:cardState
        managed object property"
    ::= { cfprStorageFlexFlashCardEntry 7 }

cfprStorageFlexFlashCardCardSync OBJECT-TYPE
    SYNTAX       CfprStorageFFCardSync
    MAX-ACCESS   read-only
    STATUS       current
    DESCRIPTION
        "Cisco Firepower storage:FlexFlashCard:cardSync
        managed object property"
    ::= { cfprStorageFlexFlashCardEntry 8 }

cfprStorageFlexFlashCardCardType OBJECT-TYPE
    SYNTAX       SnmpAdminString
    MAX-ACCESS   read-only
    STATUS       current
    DESCRIPTION
        "Cisco Firepower storage:FlexFlashCard:cardType
        managed object property"
    ::= { cfprStorageFlexFlashCardEntry 9 }

cfprStorageFlexFlashCardConnectionProtocol OBJECT-TYPE
    SYNTAX       CfprStorageConnectionProtocol
    MAX-ACCESS   read-only
    STATUS       current
    DESCRIPTION
        "Cisco Firepower storage:FlexFlashCard:connectionProtocol
        managed object property"
    ::= { cfprStorageFlexFlashCardEntry 10 }

cfprStorageFlexFlashCardControllerIndex OBJECT-TYPE
    SYNTAX       Gauge32
    MAX-ACCESS   read-only
    STATUS       current
    DESCRIPTION
        "Cisco Firepower storage:FlexFlashCard:controllerIndex
        managed object property"
    ::= { cfprStorageFlexFlashCardEntry 11 }

cfprStorageFlexFlashCardDrivesEnabled OBJECT-TYPE
    SYNTAX       SnmpAdminString
    MAX-ACCESS   read-only
    STATUS       current
    DESCRIPTION
        "Cisco Firepower storage:FlexFlashCard:drivesEnabled
        managed object property"
    ::= { cfprStorageFlexFlashCardEntry 12 }

cfprStorageFlexFlashCardId OBJECT-TYPE
    SYNTAX       Gauge32
    MAX-ACCESS   read-only
    STATUS       current
    DESCRIPTION
        "Cisco Firepower storage:FlexFlashCard:id managed object property"
    ::= { cfprStorageFlexFlashCardEntry 13 }

cfprStorageFlexFlashCardMfgDate OBJECT-TYPE
    SYNTAX       SnmpAdminString
    MAX-ACCESS   read-only
    STATUS       current
    DESCRIPTION
        "Cisco Firepower storage:FlexFlashCard:mfgDate
        managed object property"
    ::= { cfprStorageFlexFlashCardEntry 14 }

cfprStorageFlexFlashCardMfgId OBJECT-TYPE
    SYNTAX       SnmpAdminString
    MAX-ACCESS   read-only
    STATUS       current
    DESCRIPTION
        "Cisco Firepower storage:FlexFlashCard:mfgId managed
        object property"
    ::= { cfprStorageFlexFlashCardEntry 15 }

cfprStorageFlexFlashCardModel OBJECT-TYPE
    SYNTAX       SnmpAdminString
    MAX-ACCESS   read-only
    STATUS       current
    DESCRIPTION
        "Cisco Firepower storage:FlexFlashCard:model managed
        object property"
    ::= { cfprStorageFlexFlashCardEntry 16 }

cfprStorageFlexFlashCardNumberOfBlocks OBJECT-TYPE
    SYNTAX       Unsigned64
    MAX-ACCESS   read-only
    STATUS       current
    DESCRIPTION
        "Cisco Firepower storage:FlexFlashCard:numberOfBlocks
        managed object property"
    ::= { cfprStorageFlexFlashCardEntry 17 }

cfprStorageFlexFlashCardOemId OBJECT-TYPE
    SYNTAX       SnmpAdminString
    MAX-ACCESS   read-only
    STATUS       current
    DESCRIPTION
        "Cisco Firepower storage:FlexFlashCard:oemId managed
        object property"
    ::= { cfprStorageFlexFlashCardEntry 18 }

cfprStorageFlexFlashCardOperQualifierReason OBJECT-TYPE
    SYNTAX       SnmpAdminString
    MAX-ACCESS   read-only
    STATUS       current
    DESCRIPTION
        "Cisco Firepower storage:FlexFlashCard:operQualifierReason
        managed object property"
    ::= { cfprStorageFlexFlashCardEntry 19 }

cfprStorageFlexFlashCardOperability OBJECT-TYPE
    SYNTAX       CfprEquipmentOperability
    MAX-ACCESS   read-only
    STATUS       current
    DESCRIPTION
        "Cisco Firepower storage:FlexFlashCard:operability
        managed object property"
    ::= { cfprStorageFlexFlashCardEntry 20 }

cfprStorageFlexFlashCardPartitionCount OBJECT-TYPE
    SYNTAX       Gauge32
    MAX-ACCESS   read-only
    STATUS       current
    DESCRIPTION
        "Cisco Firepower storage:FlexFlashCard:partitionCount
        managed object property"
    ::= { cfprStorageFlexFlashCardEntry 21 }

cfprStorageFlexFlashCardPresence OBJECT-TYPE
    SYNTAX       CfprEquipmentPresence
    MAX-ACCESS   read-only
    STATUS       current
    DESCRIPTION
        "Cisco Firepower storage:FlexFlashCard:presence
        managed object property"
    ::= { cfprStorageFlexFlashCardEntry 22 }

cfprStorageFlexFlashCardReadErrorThreshold OBJECT-TYPE
    SYNTAX       Gauge32
    MAX-ACCESS   read-only
    STATUS       current
    DESCRIPTION
        "Cisco Firepower storage:FlexFlashCard:readErrorThreshold
        managed object property"
    ::= { cfprStorageFlexFlashCardEntry 23 }

cfprStorageFlexFlashCardReadIOErrorCount OBJECT-TYPE
    SYNTAX       Gauge32
    MAX-ACCESS   read-only
    STATUS       current
    DESCRIPTION
        "Cisco Firepower storage:FlexFlashCard:readIOErrorCount
        managed object property"
    ::= { cfprStorageFlexFlashCardEntry 24 }

cfprStorageFlexFlashCardRevision OBJECT-TYPE
    SYNTAX       SnmpAdminString
    MAX-ACCESS   read-only
    STATUS       current
    DESCRIPTION
        "Cisco Firepower storage:FlexFlashCard:revision
        managed object property"
    ::= { cfprStorageFlexFlashCardEntry 25 }

cfprStorageFlexFlashCardSerial OBJECT-TYPE
    SYNTAX       SnmpAdminString
    MAX-ACCESS   read-only
    STATUS       current
    DESCRIPTION
        "Cisco Firepower storage:FlexFlashCard:serial managed
        object property"
    ::= { cfprStorageFlexFlashCardEntry 26 }

cfprStorageFlexFlashCardSignature OBJECT-TYPE
    SYNTAX       SnmpAdminString
    MAX-ACCESS   read-only
    STATUS       current
    DESCRIPTION
        "Cisco Firepower storage:FlexFlashCard:signature
        managed object property"
    ::= { cfprStorageFlexFlashCardEntry 27 }

cfprStorageFlexFlashCardSize OBJECT-TYPE
    SYNTAX       Unsigned64
    MAX-ACCESS   read-only
    STATUS       current
    DESCRIPTION
        "Cisco Firepower storage:FlexFlashCard:size managed
        object property"
    ::= { cfprStorageFlexFlashCardEntry 28 }

cfprStorageFlexFlashCardSlotNumber OBJECT-TYPE
    SYNTAX       Gauge32
    MAX-ACCESS   read-only
    STATUS       current
    DESCRIPTION
        "Cisco Firepower storage:FlexFlashCard:slotNumber
        managed object property"
    ::= { cfprStorageFlexFlashCardEntry 29 }

cfprStorageFlexFlashCardVendor OBJECT-TYPE
    SYNTAX       SnmpAdminString
    MAX-ACCESS   read-only
    STATUS       current
    DESCRIPTION
        "Cisco Firepower storage:FlexFlashCard:vendor managed
        object property"
    ::= { cfprStorageFlexFlashCardEntry 30 }

cfprStorageFlexFlashCardWriteEnable OBJECT-TYPE
    SYNTAX       CfprStorageFFCardWriteEnable
    MAX-ACCESS   read-only
    STATUS       current
    DESCRIPTION
        "Cisco Firepower storage:FlexFlashCard:writeEnable
        managed object property"
    ::= { cfprStorageFlexFlashCardEntry 31 }

cfprStorageFlexFlashCardWriteErrorThreshold OBJECT-TYPE
    SYNTAX       Gauge32
    MAX-ACCESS   read-only
    STATUS       current
    DESCRIPTION
        "Cisco Firepower storage:FlexFlashCard:writeErrorThreshold
        managed object property"
    ::= { cfprStorageFlexFlashCardEntry 32 }

cfprStorageFlexFlashCardWriteIOErrorCount OBJECT-TYPE
    SYNTAX       Gauge32
    MAX-ACCESS   read-only
    STATUS       current
    DESCRIPTION
        "Cisco Firepower storage:FlexFlashCard:writeIOErrorCount
        managed object property"
    ::= { cfprStorageFlexFlashCardEntry 33 }

cfprStorageFlexFlashControllerTable OBJECT-TYPE
    SYNTAX           SEQUENCE OF CfprStorageFlexFlashControllerEntry
    MAX-ACCESS       not-accessible
    STATUS           current
    DESCRIPTION
        "Cisco Firepower storage:FlexFlashController managed object table"
    ::= { cfprStorageObjects 14 }

cfprStorageFlexFlashControllerEntry OBJECT-TYPE
    SYNTAX           CfprStorageFlexFlashControllerEntry
    MAX-ACCESS       not-accessible
    STATUS           current
    DESCRIPTION
        "Entry for the cfprStorageFlexFlashControllerTable table."
    INDEX { cfprStorageFlexFlashControllerInstanceId }
    ::= { cfprStorageFlexFlashControllerTable 1 }

CfprStorageFlexFlashControllerEntry ::= SEQUENCE {
    cfprStorageFlexFlashControllerInstanceId                         CfprManagedObjectId,
    cfprStorageFlexFlashControllerDn                                 CfprManagedObjectDn,
    cfprStorageFlexFlashControllerRn                                 SnmpAdminString,
    cfprStorageFlexFlashControllerAdminSlotNumber                    CfprStorageFFSlotENUM,
    cfprStorageFlexFlashControllerConfiguredMode                     CfprStorageOperatingModeType,
    cfprStorageFlexFlashControllerControllerHealth                   CfprStorageFFControllerHealth,
    cfprStorageFlexFlashControllerControllerState                    CfprStorageFFControllerState,
    cfprStorageFlexFlashControllerFirmwareVersion                    SnmpAdminString,
    cfprStorageFlexFlashControllerFlexFlashType                      CfprStorageFFType,
    cfprStorageFlexFlashControllerFsmDescr                           SnmpAdminString,
    cfprStorageFlexFlashControllerFsmPrev                            SnmpAdminString,
    cfprStorageFlexFlashControllerFsmProgr                           Gauge32,
    cfprStorageFlexFlashControllerFsmRmtInvErrCode                   Gauge32,
    cfprStorageFlexFlashControllerFsmRmtInvErrDescr                  SnmpAdminString,
    cfprStorageFlexFlashControllerFsmRmtInvRslt                      CfprConditionRemoteInvRslt,
    cfprStorageFlexFlashControllerFsmStageDescr                      SnmpAdminString,
    cfprStorageFlexFlashControllerFsmStamp                           DateAndTime,
    cfprStorageFlexFlashControllerFsmStatus                          SnmpAdminString,
    cfprStorageFlexFlashControllerFsmTry                             Gauge32,
    cfprStorageFlexFlashControllerHasError                           CfprStorageFFHasError,
    cfprStorageFlexFlashControllerId                                 CfprStorageFlexFlashControllerId,
    cfprStorageFlexFlashControllerIsCardMismatch                     CfprStorageFFCardSizeMismatch,
    cfprStorageFlexFlashControllerIsFormatFSMRunning                 CfprStorageFFFormatRunning,
    cfprStorageFlexFlashControllerLocationDn                         SnmpAdminString,
    cfprStorageFlexFlashControllerModel                              SnmpAdminString,
    cfprStorageFlexFlashControllerOperQualifierReason                SnmpAdminString,
    cfprStorageFlexFlashControllerOperState                          CfprEquipmentOperability,
    cfprStorageFlexFlashControllerOperability                        CfprEquipmentOperability,
    cfprStorageFlexFlashControllerOperatingMode                      CfprStorageOperatingModeType,
    cfprStorageFlexFlashControllerOperationRequest                   CfprStorageOperationRequestType,
    cfprStorageFlexFlashControllerPciAddr                            SnmpAdminString,
    cfprStorageFlexFlashControllerPciSlot                            SnmpAdminString,
    cfprStorageFlexFlashControllerPerf                               CfprEquipmentSensorThresholdStatus,
    cfprStorageFlexFlashControllerPhysicalDriveCount                 Gauge32,
    cfprStorageFlexFlashControllerPower                              CfprEquipmentPowerState,
    cfprStorageFlexFlashControllerPresence                           CfprEquipmentPresence,
    cfprStorageFlexFlashControllerPrimarySlotNumber                  Gauge32,
    cfprStorageFlexFlashControllerRaidSyncSupport                    CfprStorageFFRaidSyncSupport,
    cfprStorageFlexFlashControllerReadErrorThreshold                 Gauge32,
    cfprStorageFlexFlashControllerRevision                           SnmpAdminString,
    cfprStorageFlexFlashControllerSerial                             SnmpAdminString,
    cfprStorageFlexFlashControllerThermal                            CfprEquipmentSensorThresholdStatus,
    cfprStorageFlexFlashControllerType                               CfprStorageControllerType,
    cfprStorageFlexFlashControllerVendor                             SnmpAdminString,
    cfprStorageFlexFlashControllerVirtualDriveCount                  Gauge32,
    cfprStorageFlexFlashControllerVoltage                            CfprEquipmentSensorThresholdStatus,
    cfprStorageFlexFlashControllerWriteErrorThreshold                Gauge32
}

cfprStorageFlexFlashControllerInstanceId OBJECT-TYPE
    SYNTAX       CfprManagedObjectId
    MAX-ACCESS   not-accessible
    STATUS       current
    DESCRIPTION
        "Instance identifier of the managed object."
    ::= { cfprStorageFlexFlashControllerEntry 1 }

cfprStorageFlexFlashControllerDn OBJECT-TYPE
    SYNTAX       CfprManagedObjectDn
    MAX-ACCESS   read-only
    STATUS       current
    DESCRIPTION
        "Cisco Firepower storage:FlexFlashController:dn
        managed object property"
    ::= { cfprStorageFlexFlashControllerEntry 2 }

cfprStorageFlexFlashControllerRn OBJECT-TYPE
    SYNTAX       SnmpAdminString
    MAX-ACCESS   read-only
    STATUS       current
    DESCRIPTION
        "Cisco Firepower storage:FlexFlashController:rn
        managed object property"
    ::= { cfprStorageFlexFlashControllerEntry 3 }

cfprStorageFlexFlashControllerAdminSlotNumber OBJECT-TYPE
    SYNTAX       CfprStorageFFSlotENUM
    MAX-ACCESS   read-only
    STATUS       current
    DESCRIPTION
        "Cisco Firepower storage:FlexFlashController:adminSlotNumber
        managed object property"
    ::= { cfprStorageFlexFlashControllerEntry 4 }

cfprStorageFlexFlashControllerConfiguredMode OBJECT-TYPE
    SYNTAX       CfprStorageOperatingModeType
    MAX-ACCESS   read-only
    STATUS       current
    DESCRIPTION
        "Cisco Firepower storage:FlexFlashController:configuredMode
        managed object property"
    ::= { cfprStorageFlexFlashControllerEntry 5 }

cfprStorageFlexFlashControllerControllerHealth OBJECT-TYPE
    SYNTAX       CfprStorageFFControllerHealth
    MAX-ACCESS   read-only
    STATUS       current
    DESCRIPTION
        "Cisco Firepower storage:FlexFlashController:controllerHealth
        managed object property"
    ::= { cfprStorageFlexFlashControllerEntry 6 }

cfprStorageFlexFlashControllerControllerState OBJECT-TYPE
    SYNTAX       CfprStorageFFControllerState
    MAX-ACCESS   read-only
    STATUS       current
    DESCRIPTION
        "Cisco Firepower storage:FlexFlashController:controllerState
        managed object property"
    ::= { cfprStorageFlexFlashControllerEntry 7 }

cfprStorageFlexFlashControllerFirmwareVersion OBJECT-TYPE
    SYNTAX       SnmpAdminString
    MAX-ACCESS   read-only
    STATUS       current
    DESCRIPTION
        "Cisco Firepower storage:FlexFlashController:firmwareVersion
        managed object property"
    ::= { cfprStorageFlexFlashControllerEntry 8 }

cfprStorageFlexFlashControllerFlexFlashType OBJECT-TYPE
    SYNTAX       CfprStorageFFType
    MAX-ACCESS   read-only
    STATUS       current
    DESCRIPTION
        "Cisco Firepower storage:FlexFlashController:flexFlashType
        managed object property"
    ::= { cfprStorageFlexFlashControllerEntry 9 }

cfprStorageFlexFlashControllerFsmDescr OBJECT-TYPE
    SYNTAX       SnmpAdminString
    MAX-ACCESS   read-only
    STATUS       current
    DESCRIPTION
        "Cisco Firepower storage:FlexFlashController:fsmDescr
        managed object property"
    ::= { cfprStorageFlexFlashControllerEntry 10 }

cfprStorageFlexFlashControllerFsmPrev OBJECT-TYPE
    SYNTAX       SnmpAdminString
    MAX-ACCESS   read-only
    STATUS       current
    DESCRIPTION
        "Cisco Firepower storage:FlexFlashController:fsmPrev
        managed object property"
    ::= { cfprStorageFlexFlashControllerEntry 11 }

cfprStorageFlexFlashControllerFsmProgr OBJECT-TYPE
    SYNTAX       Gauge32
    MAX-ACCESS   read-only
    STATUS       current
    DESCRIPTION
        "Cisco Firepower storage:FlexFlashController:fsmProgr
        managed object property"
    ::= { cfprStorageFlexFlashControllerEntry 12 }

cfprStorageFlexFlashControllerFsmRmtInvErrCode OBJECT-TYPE
    SYNTAX       Gauge32
    MAX-ACCESS   read-only
    STATUS       current
    DESCRIPTION
        "Cisco Firepower storage:FlexFlashController:fsmRmtInvErrCode
        managed object property"
    ::= { cfprStorageFlexFlashControllerEntry 13 }

cfprStorageFlexFlashControllerFsmRmtInvErrDescr OBJECT-TYPE
    SYNTAX       SnmpAdminString
    MAX-ACCESS   read-only
    STATUS       current
    DESCRIPTION
        "Cisco Firepower storage:FlexFlashController:fsmRmtInvErrDescr
        managed object property"
    ::= { cfprStorageFlexFlashControllerEntry 14 }

cfprStorageFlexFlashControllerFsmRmtInvRslt OBJECT-TYPE
    SYNTAX       CfprConditionRemoteInvRslt
    MAX-ACCESS   read-only
    STATUS       current
    DESCRIPTION
        "Cisco Firepower storage:FlexFlashController:fsmRmtInvRslt
        managed object property"
    ::= { cfprStorageFlexFlashControllerEntry 15 }

cfprStorageFlexFlashControllerFsmStageDescr OBJECT-TYPE
    SYNTAX       SnmpAdminString
    MAX-ACCESS   read-only
    STATUS       current
    DESCRIPTION
        "Cisco Firepower storage:FlexFlashController:fsmStageDescr
        managed object property"
    ::= { cfprStorageFlexFlashControllerEntry 16 }

cfprStorageFlexFlashControllerFsmStamp OBJECT-TYPE
    SYNTAX       DateAndTime
    MAX-ACCESS   read-only
    STATUS       current
    DESCRIPTION
        "Cisco Firepower storage:FlexFlashController:fsmStamp
        managed object property"
    ::= { cfprStorageFlexFlashControllerEntry 17 }

cfprStorageFlexFlashControllerFsmStatus OBJECT-TYPE
    SYNTAX       SnmpAdminString
    MAX-ACCESS   read-only
    STATUS       current
    DESCRIPTION
        "Cisco Firepower storage:FlexFlashController:fsmStatus
        managed object property"
    ::= { cfprStorageFlexFlashControllerEntry 18 }

cfprStorageFlexFlashControllerFsmTry OBJECT-TYPE
    SYNTAX       Gauge32
    MAX-ACCESS   read-only
    STATUS       current
    DESCRIPTION
        "Cisco Firepower storage:FlexFlashController:fsmTry
        managed object property"
    ::= { cfprStorageFlexFlashControllerEntry 19 }

cfprStorageFlexFlashControllerHasError OBJECT-TYPE
    SYNTAX       CfprStorageFFHasError
    MAX-ACCESS   read-only
    STATUS       current
    DESCRIPTION
        "Cisco Firepower storage:FlexFlashController:hasError
        managed object property"
    ::= { cfprStorageFlexFlashControllerEntry 20 }

cfprStorageFlexFlashControllerId OBJECT-TYPE
    SYNTAX       CfprStorageFlexFlashControllerId
    MAX-ACCESS   read-only
    STATUS       current
    DESCRIPTION
        "Cisco Firepower storage:FlexFlashController:id
        managed object property"
    ::= { cfprStorageFlexFlashControllerEntry 21 }

cfprStorageFlexFlashControllerIsCardMismatch OBJECT-TYPE
    SYNTAX       CfprStorageFFCardSizeMismatch
    MAX-ACCESS   read-only
    STATUS       current
    DESCRIPTION
        "Cisco Firepower storage:FlexFlashController:isCardMismatch
        managed object property"
    ::= { cfprStorageFlexFlashControllerEntry 22 }

cfprStorageFlexFlashControllerIsFormatFSMRunning OBJECT-TYPE
    SYNTAX       CfprStorageFFFormatRunning
    MAX-ACCESS   read-only
    STATUS       current
    DESCRIPTION
        "Cisco Firepower storage:FlexFlashController:isFormatFSMRunning
        managed object property"
    ::= { cfprStorageFlexFlashControllerEntry 23 }

cfprStorageFlexFlashControllerLocationDn OBJECT-TYPE
    SYNTAX       SnmpAdminString
    MAX-ACCESS   read-only
    STATUS       current
    DESCRIPTION
        "Cisco Firepower storage:FlexFlashController:locationDn
        managed object property"
    ::= { cfprStorageFlexFlashControllerEntry 24 }

cfprStorageFlexFlashControllerModel OBJECT-TYPE
    SYNTAX       SnmpAdminString
    MAX-ACCESS   read-only
    STATUS       current
    DESCRIPTION
        "Cisco Firepower storage:FlexFlashController:model
        managed object property"
    ::= { cfprStorageFlexFlashControllerEntry 25 }

cfprStorageFlexFlashControllerOperQualifierReason OBJECT-TYPE
    SYNTAX       SnmpAdminString
    MAX-ACCESS   read-only
    STATUS       current
    DESCRIPTION
        "Cisco Firepower storage:FlexFlashController:operQualifierReason
        managed object property"
    ::= { cfprStorageFlexFlashControllerEntry 26 }

cfprStorageFlexFlashControllerOperState OBJECT-TYPE
    SYNTAX       CfprEquipmentOperability
    MAX-ACCESS   read-only
    STATUS       current
    DESCRIPTION
        "Cisco Firepower storage:FlexFlashController:operState
        managed object property"
    ::= { cfprStorageFlexFlashControllerEntry 27 }

cfprStorageFlexFlashControllerOperability OBJECT-TYPE
    SYNTAX       CfprEquipmentOperability
    MAX-ACCESS   read-only
    STATUS       current
    DESCRIPTION
        "Cisco Firepower storage:FlexFlashController:operability
        managed object property"
    ::= { cfprStorageFlexFlashControllerEntry 28 }

cfprStorageFlexFlashControllerOperatingMode OBJECT-TYPE
    SYNTAX       CfprStorageOperatingModeType
    MAX-ACCESS   read-only
    STATUS       current
    DESCRIPTION
        "Cisco Firepower storage:FlexFlashController:operatingMode
        managed object property"
    ::= { cfprStorageFlexFlashControllerEntry 29 }

cfprStorageFlexFlashControllerOperationRequest OBJECT-TYPE
    SYNTAX       CfprStorageOperationRequestType
    MAX-ACCESS   read-only
    STATUS       current
    DESCRIPTION
        "Cisco Firepower storage:FlexFlashController:operationRequest
        managed object property"
    ::= { cfprStorageFlexFlashControllerEntry 30 }

cfprStorageFlexFlashControllerPciAddr OBJECT-TYPE
    SYNTAX       SnmpAdminString
    MAX-ACCESS   read-only
    STATUS       current
    DESCRIPTION
        "Cisco Firepower storage:FlexFlashController:pciAddr
        managed object property"
    ::= { cfprStorageFlexFlashControllerEntry 31 }

cfprStorageFlexFlashControllerPciSlot OBJECT-TYPE
    SYNTAX       SnmpAdminString
    MAX-ACCESS   read-only
    STATUS       current
    DESCRIPTION
        "Cisco Firepower storage:FlexFlashController:pciSlot
        managed object property"
    ::= { cfprStorageFlexFlashControllerEntry 32 }

cfprStorageFlexFlashControllerPerf OBJECT-TYPE
    SYNTAX       CfprEquipmentSensorThresholdStatus
    MAX-ACCESS   read-only
    STATUS       current
    DESCRIPTION
        "Cisco Firepower storage:FlexFlashController:perf
        managed object property"
    ::= { cfprStorageFlexFlashControllerEntry 33 }

cfprStorageFlexFlashControllerPhysicalDriveCount OBJECT-TYPE
    SYNTAX       Gauge32
    MAX-ACCESS   read-only
    STATUS       current
    DESCRIPTION
        "Cisco Firepower storage:FlexFlashController:physicalDriveCount
        managed object property"
    ::= { cfprStorageFlexFlashControllerEntry 34 }

cfprStorageFlexFlashControllerPower OBJECT-TYPE
    SYNTAX       CfprEquipmentPowerState
    MAX-ACCESS   read-only
    STATUS       current
    DESCRIPTION
        "Cisco Firepower storage:FlexFlashController:power
        managed object property"
    ::= { cfprStorageFlexFlashControllerEntry 35 }

cfprStorageFlexFlashControllerPresence OBJECT-TYPE
    SYNTAX       CfprEquipmentPresence
    MAX-ACCESS   read-only
    STATUS       current
    DESCRIPTION
        "Cisco Firepower storage:FlexFlashController:presence
        managed object property"
    ::= { cfprStorageFlexFlashControllerEntry 36 }

cfprStorageFlexFlashControllerPrimarySlotNumber OBJECT-TYPE
    SYNTAX       Gauge32
    MAX-ACCESS   read-only
    STATUS       current
    DESCRIPTION
        "Cisco Firepower storage:FlexFlashController:primarySlotNumber
        managed object property"
    ::= { cfprStorageFlexFlashControllerEntry 37 }

cfprStorageFlexFlashControllerRaidSyncSupport OBJECT-TYPE
    SYNTAX       CfprStorageFFRaidSyncSupport
    MAX-ACCESS   read-only
    STATUS       current
    DESCRIPTION
        "Cisco Firepower storage:FlexFlashController:raidSyncSupport
        managed object property"
    ::= { cfprStorageFlexFlashControllerEntry 38 }

cfprStorageFlexFlashControllerReadErrorThreshold OBJECT-TYPE
    SYNTAX       Gauge32
    MAX-ACCESS   read-only
    STATUS       current
    DESCRIPTION
        "Cisco Firepower storage:FlexFlashController:readErrorThreshold
        managed object property"
    ::= { cfprStorageFlexFlashControllerEntry 39 }

cfprStorageFlexFlashControllerRevision OBJECT-TYPE
    SYNTAX       SnmpAdminString
    MAX-ACCESS   read-only
    STATUS       current
    DESCRIPTION
        "Cisco Firepower storage:FlexFlashController:revision
        managed object property"
    ::= { cfprStorageFlexFlashControllerEntry 40 }

cfprStorageFlexFlashControllerSerial OBJECT-TYPE
    SYNTAX       SnmpAdminString
    MAX-ACCESS   read-only
    STATUS       current
    DESCRIPTION
        "Cisco Firepower storage:FlexFlashController:serial
        managed object property"
    ::= { cfprStorageFlexFlashControllerEntry 41 }

cfprStorageFlexFlashControllerThermal OBJECT-TYPE
    SYNTAX       CfprEquipmentSensorThresholdStatus
    MAX-ACCESS   read-only
    STATUS       current
    DESCRIPTION
        "Cisco Firepower storage:FlexFlashController:thermal
        managed object property"
    ::= { cfprStorageFlexFlashControllerEntry 42 }

cfprStorageFlexFlashControllerType OBJECT-TYPE
    SYNTAX       CfprStorageControllerType
    MAX-ACCESS   read-only
    STATUS       current
    DESCRIPTION
        "Cisco Firepower storage:FlexFlashController:type
        managed object property"
    ::= { cfprStorageFlexFlashControllerEntry 43 }

cfprStorageFlexFlashControllerVendor OBJECT-TYPE
    SYNTAX       SnmpAdminString
    MAX-ACCESS   read-only
    STATUS       current
    DESCRIPTION
        "Cisco Firepower storage:FlexFlashController:vendor
        managed object property"
    ::= { cfprStorageFlexFlashControllerEntry 44 }

cfprStorageFlexFlashControllerVirtualDriveCount OBJECT-TYPE
    SYNTAX       Gauge32
    MAX-ACCESS   read-only
    STATUS       current
    DESCRIPTION
        "Cisco Firepower storage:FlexFlashController:virtualDriveCount
        managed object property"
    ::= { cfprStorageFlexFlashControllerEntry 45 }

cfprStorageFlexFlashControllerVoltage OBJECT-TYPE
    SYNTAX       CfprEquipmentSensorThresholdStatus
    MAX-ACCESS   read-only
    STATUS       current
    DESCRIPTION
        "Cisco Firepower storage:FlexFlashController:voltage
        managed object property"
    ::= { cfprStorageFlexFlashControllerEntry 46 }

cfprStorageFlexFlashControllerWriteErrorThreshold OBJECT-TYPE
    SYNTAX       Gauge32
    MAX-ACCESS   read-only
    STATUS       current
    DESCRIPTION
        "Cisco Firepower storage:FlexFlashController:writeErrorThreshold
        managed object property"
    ::= { cfprStorageFlexFlashControllerEntry 47 }

cfprStorageFlexFlashControllerFsmTable OBJECT-TYPE
    SYNTAX           SEQUENCE OF CfprStorageFlexFlashControllerFsmEntry
    MAX-ACCESS       not-accessible
    STATUS           current
    DESCRIPTION
        "Cisco Firepower storage:FlexFlashControllerFsm
        managed object table"
    ::= { cfprStorageObjects 15 }

cfprStorageFlexFlashControllerFsmEntry OBJECT-TYPE
    SYNTAX           CfprStorageFlexFlashControllerFsmEntry
    MAX-ACCESS       not-accessible
    STATUS           current
    DESCRIPTION
        "Entry for the cfprStorageFlexFlashControllerFsmTable table."
    INDEX { cfprStorageFlexFlashControllerFsmInstanceId }
    ::= { cfprStorageFlexFlashControllerFsmTable 1 }

CfprStorageFlexFlashControllerFsmEntry ::= SEQUENCE {
    cfprStorageFlexFlashControllerFsmInstanceId                      CfprManagedObjectId,
    cfprStorageFlexFlashControllerFsmDn                              CfprManagedObjectDn,
    cfprStorageFlexFlashControllerFsmRn                              SnmpAdminString,
    cfprStorageFlexFlashControllerFsmCompletionTime                  DateAndTime,
    cfprStorageFlexFlashControllerFsmCurrentFsm                      CfprStorageFlexFlashControllerFsmCurrentFsm,
    cfprStorageFlexFlashControllerFsmDescrData                       SnmpAdminString,
    cfprStorageFlexFlashControllerFsmFsmStatus                       CfprFsmFsmStageStatus,
    cfprStorageFlexFlashControllerFsmProgress                        Gauge32,
    cfprStorageFlexFlashControllerFsmRmtErrCode                      Gauge32,
    cfprStorageFlexFlashControllerFsmRmtErrDescr                     SnmpAdminString,
    cfprStorageFlexFlashControllerFsmRmtRslt                         CfprConditionRemoteInvRslt
}

cfprStorageFlexFlashControllerFsmInstanceId OBJECT-TYPE
    SYNTAX       CfprManagedObjectId
    MAX-ACCESS   not-accessible
    STATUS       current
    DESCRIPTION
        "Instance identifier of the managed object."
    ::= { cfprStorageFlexFlashControllerFsmEntry 1 }

cfprStorageFlexFlashControllerFsmDn OBJECT-TYPE
    SYNTAX       CfprManagedObjectDn
    MAX-ACCESS   read-only
    STATUS       current
    DESCRIPTION
        "Cisco Firepower storage:FlexFlashControllerFsm:dn
        managed object property"
    ::= { cfprStorageFlexFlashControllerFsmEntry 2 }

cfprStorageFlexFlashControllerFsmRn OBJECT-TYPE
    SYNTAX       SnmpAdminString
    MAX-ACCESS   read-only
    STATUS       current
    DESCRIPTION
        "Cisco Firepower storage:FlexFlashControllerFsm:rn
        managed object property"
    ::= { cfprStorageFlexFlashControllerFsmEntry 3 }

cfprStorageFlexFlashControllerFsmCompletionTime OBJECT-TYPE
    SYNTAX       DateAndTime
    MAX-ACCESS   read-only
    STATUS       current
    DESCRIPTION
        "Cisco Firepower storage:FlexFlashControllerFsm:completionTime
        managed object property"
    ::= { cfprStorageFlexFlashControllerFsmEntry 4 }

cfprStorageFlexFlashControllerFsmCurrentFsm OBJECT-TYPE
    SYNTAX       CfprStorageFlexFlashControllerFsmCurrentFsm
    MAX-ACCESS   read-only
    STATUS       current
    DESCRIPTION
        "Cisco Firepower storage:FlexFlashControllerFsm:currentFsm
        managed object property"
    ::= { cfprStorageFlexFlashControllerFsmEntry 5 }

cfprStorageFlexFlashControllerFsmDescrData OBJECT-TYPE
    SYNTAX       SnmpAdminString
    MAX-ACCESS   read-only
    STATUS       current
    DESCRIPTION
        "Cisco Firepower storage:FlexFlashControllerFsm:descr
        managed object property"
    ::= { cfprStorageFlexFlashControllerFsmEntry 6 }

cfprStorageFlexFlashControllerFsmFsmStatus OBJECT-TYPE
    SYNTAX       CfprFsmFsmStageStatus
    MAX-ACCESS   read-only
    STATUS       current
    DESCRIPTION
        "Cisco Firepower storage:FlexFlashControllerFsm:fsmStatus
        managed object property"
    ::= { cfprStorageFlexFlashControllerFsmEntry 7 }

cfprStorageFlexFlashControllerFsmProgress OBJECT-TYPE
    SYNTAX       Gauge32
    MAX-ACCESS   read-only
    STATUS       current
    DESCRIPTION
        "Cisco Firepower storage:FlexFlashControllerFsm:progress
        managed object property"
    ::= { cfprStorageFlexFlashControllerFsmEntry 8 }

cfprStorageFlexFlashControllerFsmRmtErrCode OBJECT-TYPE
    SYNTAX       Gauge32
    MAX-ACCESS   read-only
    STATUS       current
    DESCRIPTION
        "Cisco Firepower storage:FlexFlashControllerFsm:rmtErrCode
        managed object property"
    ::= { cfprStorageFlexFlashControllerFsmEntry 9 }

cfprStorageFlexFlashControllerFsmRmtErrDescr OBJECT-TYPE
    SYNTAX       SnmpAdminString
    MAX-ACCESS   read-only
    STATUS       current
    DESCRIPTION
        "Cisco Firepower storage:FlexFlashControllerFsm:rmtErrDescr
        managed object property"
    ::= { cfprStorageFlexFlashControllerFsmEntry 10 }

cfprStorageFlexFlashControllerFsmRmtRslt OBJECT-TYPE
    SYNTAX       CfprConditionRemoteInvRslt
    MAX-ACCESS   read-only
    STATUS       current
    DESCRIPTION
        "Cisco Firepower storage:FlexFlashControllerFsm:rmtRslt
        managed object property"
    ::= { cfprStorageFlexFlashControllerFsmEntry 11 }

cfprStorageFlexFlashControllerFsmStageTable OBJECT-TYPE
    SYNTAX           SEQUENCE OF CfprStorageFlexFlashControllerFsmStageEntry
    MAX-ACCESS       not-accessible
    STATUS           current
    DESCRIPTION
        "Cisco Firepower storage:FlexFlashControllerFsmStage
        managed object table"
    ::= { cfprStorageObjects 16 }

cfprStorageFlexFlashControllerFsmStageEntry OBJECT-TYPE
    SYNTAX           CfprStorageFlexFlashControllerFsmStageEntry
    MAX-ACCESS       not-accessible
    STATUS           current
    DESCRIPTION
        "Entry for the cfprStorageFlexFlashControllerFsmStageTable table."
    INDEX { cfprStorageFlexFlashControllerFsmStageInstanceId }
    ::= { cfprStorageFlexFlashControllerFsmStageTable 1 }

CfprStorageFlexFlashControllerFsmStageEntry ::= SEQUENCE {
    cfprStorageFlexFlashControllerFsmStageInstanceId                 CfprManagedObjectId,
    cfprStorageFlexFlashControllerFsmStageDn                         CfprManagedObjectDn,
    cfprStorageFlexFlashControllerFsmStageRn                         SnmpAdminString,
    cfprStorageFlexFlashControllerFsmStageDescrData                  SnmpAdminString,
    cfprStorageFlexFlashControllerFsmStageLastUpdateTime             DateAndTime,
    cfprStorageFlexFlashControllerFsmStageName                       CfprStorageFlexFlashControllerFsmStageName,
    cfprStorageFlexFlashControllerFsmStageOrder                      Gauge32,
    cfprStorageFlexFlashControllerFsmStageRetry                      Gauge32,
    cfprStorageFlexFlashControllerFsmStageStageStatus                CfprFsmFsmStageStatus
}

cfprStorageFlexFlashControllerFsmStageInstanceId OBJECT-TYPE
    SYNTAX       CfprManagedObjectId
    MAX-ACCESS   not-accessible
    STATUS       current
    DESCRIPTION
        "Instance identifier of the managed object."
    ::= { cfprStorageFlexFlashControllerFsmStageEntry 1 }

cfprStorageFlexFlashControllerFsmStageDn OBJECT-TYPE
    SYNTAX       CfprManagedObjectDn
    MAX-ACCESS   read-only
    STATUS       current
    DESCRIPTION
        "Cisco Firepower storage:FlexFlashControllerFsmStage:dn
        managed object property"
    ::= { cfprStorageFlexFlashControllerFsmStageEntry 2 }

cfprStorageFlexFlashControllerFsmStageRn OBJECT-TYPE
    SYNTAX       SnmpAdminString
    MAX-ACCESS   read-only
    STATUS       current
    DESCRIPTION
        "Cisco Firepower storage:FlexFlashControllerFsmStage:rn
        managed object property"
    ::= { cfprStorageFlexFlashControllerFsmStageEntry 3 }

cfprStorageFlexFlashControllerFsmStageDescrData OBJECT-TYPE
    SYNTAX       SnmpAdminString
    MAX-ACCESS   read-only
    STATUS       current
    DESCRIPTION
        "Cisco Firepower storage:FlexFlashControllerFsmStage:descr
        managed object property"
    ::= { cfprStorageFlexFlashControllerFsmStageEntry 4 }

cfprStorageFlexFlashControllerFsmStageLastUpdateTime OBJECT-TYPE
    SYNTAX       DateAndTime
    MAX-ACCESS   read-only
    STATUS       current
    DESCRIPTION
        "Cisco Firepower storage:FlexFlashControllerFsmStage:lastUpdateTim
        e managed object property"
    ::= { cfprStorageFlexFlashControllerFsmStageEntry 5 }

cfprStorageFlexFlashControllerFsmStageName OBJECT-TYPE
    SYNTAX       CfprStorageFlexFlashControllerFsmStageName
    MAX-ACCESS   read-only
    STATUS       current
    DESCRIPTION
        "Cisco Firepower storage:FlexFlashControllerFsmStage:name
        managed object property"
    ::= { cfprStorageFlexFlashControllerFsmStageEntry 6 }

cfprStorageFlexFlashControllerFsmStageOrder OBJECT-TYPE
    SYNTAX       Gauge32
    MAX-ACCESS   read-only
    STATUS       current
    DESCRIPTION
        "Cisco Firepower storage:FlexFlashControllerFsmStage:order
        managed object property"
    ::= { cfprStorageFlexFlashControllerFsmStageEntry 7 }

cfprStorageFlexFlashControllerFsmStageRetry OBJECT-TYPE
    SYNTAX       Gauge32
    MAX-ACCESS   read-only
    STATUS       current
    DESCRIPTION
        "Cisco Firepower storage:FlexFlashControllerFsmStage:retry
        managed object property"
    ::= { cfprStorageFlexFlashControllerFsmStageEntry 8 }

cfprStorageFlexFlashControllerFsmStageStageStatus OBJECT-TYPE
    SYNTAX       CfprFsmFsmStageStatus
    MAX-ACCESS   read-only
    STATUS       current
    DESCRIPTION
        "Cisco Firepower storage:FlexFlashControllerFsmStage:stageStatus
        managed object property"
    ::= { cfprStorageFlexFlashControllerFsmStageEntry 9 }

cfprStorageFlexFlashControllerFsmTaskTable OBJECT-TYPE
    SYNTAX           SEQUENCE OF CfprStorageFlexFlashControllerFsmTaskEntry
    MAX-ACCESS       not-accessible
    STATUS           current
    DESCRIPTION
        "Cisco Firepower storage:FlexFlashControllerFsmTask
        managed object table"
    ::= { cfprStorageObjects 17 }

cfprStorageFlexFlashControllerFsmTaskEntry OBJECT-TYPE
    SYNTAX           CfprStorageFlexFlashControllerFsmTaskEntry
    MAX-ACCESS       not-accessible
    STATUS           current
    DESCRIPTION
        "Entry for the cfprStorageFlexFlashControllerFsmTaskTable table."
    INDEX { cfprStorageFlexFlashControllerFsmTaskInstanceId }
    ::= { cfprStorageFlexFlashControllerFsmTaskTable 1 }

CfprStorageFlexFlashControllerFsmTaskEntry ::= SEQUENCE {
    cfprStorageFlexFlashControllerFsmTaskInstanceId                  CfprManagedObjectId,
    cfprStorageFlexFlashControllerFsmTaskDn                          CfprManagedObjectDn,
    cfprStorageFlexFlashControllerFsmTaskRn                          SnmpAdminString,
    cfprStorageFlexFlashControllerFsmTaskCompletion                  CfprFsmCompletion,
    cfprStorageFlexFlashControllerFsmTaskFlags                       CfprFsmFlags,
    cfprStorageFlexFlashControllerFsmTaskItem                        CfprStorageFlexFlashControllerFsmTaskItem,
    cfprStorageFlexFlashControllerFsmTaskSeqId                       Gauge32
}

cfprStorageFlexFlashControllerFsmTaskInstanceId OBJECT-TYPE
    SYNTAX       CfprManagedObjectId
    MAX-ACCESS   not-accessible
    STATUS       current
    DESCRIPTION
        "Instance identifier of the managed object."
    ::= { cfprStorageFlexFlashControllerFsmTaskEntry 1 }

cfprStorageFlexFlashControllerFsmTaskDn OBJECT-TYPE
    SYNTAX       CfprManagedObjectDn
    MAX-ACCESS   read-only
    STATUS       current
    DESCRIPTION
        "Cisco Firepower storage:FlexFlashControllerFsmTask:dn
        managed object property"
    ::= { cfprStorageFlexFlashControllerFsmTaskEntry 2 }

cfprStorageFlexFlashControllerFsmTaskRn OBJECT-TYPE
    SYNTAX       SnmpAdminString
    MAX-ACCESS   read-only
    STATUS       current
    DESCRIPTION
        "Cisco Firepower storage:FlexFlashControllerFsmTask:rn
        managed object property"
    ::= { cfprStorageFlexFlashControllerFsmTaskEntry 3 }

cfprStorageFlexFlashControllerFsmTaskCompletion OBJECT-TYPE
    SYNTAX       CfprFsmCompletion
    MAX-ACCESS   read-only
    STATUS       current
    DESCRIPTION
        "Cisco Firepower storage:FlexFlashControllerFsmTask:completion
        managed object property"
    ::= { cfprStorageFlexFlashControllerFsmTaskEntry 4 }

cfprStorageFlexFlashControllerFsmTaskFlags OBJECT-TYPE
    SYNTAX       CfprFsmFlags
    MAX-ACCESS   read-only
    STATUS       current
    DESCRIPTION
        "Cisco Firepower storage:FlexFlashControllerFsmTask:flags
        managed object property"
    ::= { cfprStorageFlexFlashControllerFsmTaskEntry 5 }

cfprStorageFlexFlashControllerFsmTaskItem OBJECT-TYPE
    SYNTAX       CfprStorageFlexFlashControllerFsmTaskItem
    MAX-ACCESS   read-only
    STATUS       current
    DESCRIPTION
        "Cisco Firepower storage:FlexFlashControllerFsmTask:item
        managed object property"
    ::= { cfprStorageFlexFlashControllerFsmTaskEntry 6 }

cfprStorageFlexFlashControllerFsmTaskSeqId OBJECT-TYPE
    SYNTAX       Gauge32
    MAX-ACCESS   read-only
    STATUS       current
    DESCRIPTION
        "Cisco Firepower storage:FlexFlashControllerFsmTask:seqId
        managed object property"
    ::= { cfprStorageFlexFlashControllerFsmTaskEntry 7 }

cfprStorageFlexFlashDriveTable OBJECT-TYPE
    SYNTAX           SEQUENCE OF CfprStorageFlexFlashDriveEntry
    MAX-ACCESS       not-accessible
    STATUS           current
    DESCRIPTION
        "Cisco Firepower storage:FlexFlashDrive managed object table"
    ::= { cfprStorageObjects 18 }

cfprStorageFlexFlashDriveEntry OBJECT-TYPE
    SYNTAX           CfprStorageFlexFlashDriveEntry
    MAX-ACCESS       not-accessible
    STATUS           current
    DESCRIPTION
        "Entry for the cfprStorageFlexFlashDriveTable table."
    INDEX { cfprStorageFlexFlashDriveInstanceId }
    ::= { cfprStorageFlexFlashDriveTable 1 }

CfprStorageFlexFlashDriveEntry ::= SEQUENCE {
    cfprStorageFlexFlashDriveInstanceId                              CfprManagedObjectId,
    cfprStorageFlexFlashDriveDn                                      CfprManagedObjectDn,
    cfprStorageFlexFlashDriveRn                                      SnmpAdminString,
    cfprStorageFlexFlashDriveRWType                                  CfprStorageFFRWType,
    cfprStorageFlexFlashDriveBlockSize                               Gauge32,
    cfprStorageFlexFlashDriveConnectionProtocol                      CfprStorageConnectionProtocol,
    cfprStorageFlexFlashDriveControllerIndex                         Gauge32,
    cfprStorageFlexFlashDriveDriveState                              CfprStorageFFDriveState,
    cfprStorageFlexFlashDriveDriveType                               CfprStorageFFDriveType,
    cfprStorageFlexFlashDriveId                                      Gauge32,
    cfprStorageFlexFlashDriveLastOperation                           CfprStorageOperationStateType,
    cfprStorageFlexFlashDriveModel                                   SnmpAdminString,
    cfprStorageFlexFlashDriveName                                    SnmpAdminString,
    cfprStorageFlexFlashDriveNumberOfBlocks                          Unsigned64,
    cfprStorageFlexFlashDriveOperQualifierReason                     SnmpAdminString,
    cfprStorageFlexFlashDriveOperability                             CfprEquipmentOperability,
    cfprStorageFlexFlashDriveOperationState                          CfprStorageOperationStateType,
    cfprStorageFlexFlashDrivePresence                                CfprEquipmentPresence,
    cfprStorageFlexFlashDriveRemovable                               CfprStorageFFDriveRemovable,
    cfprStorageFlexFlashDriveRevision                                SnmpAdminString,
    cfprStorageFlexFlashDriveSerial                                  SnmpAdminString,
    cfprStorageFlexFlashDriveSize                                    Unsigned64,
    cfprStorageFlexFlashDriveSlotNumber                              Gauge32,
    cfprStorageFlexFlashDriveVendor                                  SnmpAdminString,
    cfprStorageFlexFlashDriveVisible                                 CfprStorageFFDriveVisible
}

cfprStorageFlexFlashDriveInstanceId OBJECT-TYPE
    SYNTAX       CfprManagedObjectId
    MAX-ACCESS   not-accessible
    STATUS       current
    DESCRIPTION
        "Instance identifier of the managed object."
    ::= { cfprStorageFlexFlashDriveEntry 1 }

cfprStorageFlexFlashDriveDn OBJECT-TYPE
    SYNTAX       CfprManagedObjectDn
    MAX-ACCESS   read-only
    STATUS       current
    DESCRIPTION
        "Cisco Firepower storage:FlexFlashDrive:dn managed
        object property"
    ::= { cfprStorageFlexFlashDriveEntry 2 }

cfprStorageFlexFlashDriveRn OBJECT-TYPE
    SYNTAX       SnmpAdminString
    MAX-ACCESS   read-only
    STATUS       current
    DESCRIPTION
        "Cisco Firepower storage:FlexFlashDrive:rn managed
        object property"
    ::= { cfprStorageFlexFlashDriveEntry 3 }

cfprStorageFlexFlashDriveRWType OBJECT-TYPE
    SYNTAX       CfprStorageFFRWType
    MAX-ACCESS   read-only
    STATUS       current
    DESCRIPTION
        "Cisco Firepower storage:FlexFlashDrive:RWType
        managed object property"
    ::= { cfprStorageFlexFlashDriveEntry 4 }

cfprStorageFlexFlashDriveBlockSize OBJECT-TYPE
    SYNTAX       Gauge32
    MAX-ACCESS   read-only
    STATUS       current
    DESCRIPTION
        "Cisco Firepower storage:FlexFlashDrive:blockSize
        managed object property"
    ::= { cfprStorageFlexFlashDriveEntry 5 }

cfprStorageFlexFlashDriveConnectionProtocol OBJECT-TYPE
    SYNTAX       CfprStorageConnectionProtocol
    MAX-ACCESS   read-only
    STATUS       current
    DESCRIPTION
        "Cisco Firepower storage:FlexFlashDrive:connectionProtocol
        managed object property"
    ::= { cfprStorageFlexFlashDriveEntry 6 }

cfprStorageFlexFlashDriveControllerIndex OBJECT-TYPE
    SYNTAX       Gauge32
    MAX-ACCESS   read-only
    STATUS       current
    DESCRIPTION
        "Cisco Firepower storage:FlexFlashDrive:controllerIndex
        managed object property"
    ::= { cfprStorageFlexFlashDriveEntry 7 }

cfprStorageFlexFlashDriveDriveState OBJECT-TYPE
    SYNTAX       CfprStorageFFDriveState
    MAX-ACCESS   read-only
    STATUS       current
    DESCRIPTION
        "Cisco Firepower storage:FlexFlashDrive:driveState
        managed object property"
    ::= { cfprStorageFlexFlashDriveEntry 8 }

cfprStorageFlexFlashDriveDriveType OBJECT-TYPE
    SYNTAX       CfprStorageFFDriveType
    MAX-ACCESS   read-only
    STATUS       current
    DESCRIPTION
        "Cisco Firepower storage:FlexFlashDrive:driveType
        managed object property"
    ::= { cfprStorageFlexFlashDriveEntry 9 }

cfprStorageFlexFlashDriveId OBJECT-TYPE
    SYNTAX       Gauge32
    MAX-ACCESS   read-only
    STATUS       current
    DESCRIPTION
        "Cisco Firepower storage:FlexFlashDrive:id managed
        object property"
    ::= { cfprStorageFlexFlashDriveEntry 10 }

cfprStorageFlexFlashDriveLastOperation OBJECT-TYPE
    SYNTAX       CfprStorageOperationStateType
    MAX-ACCESS   read-only
    STATUS       current
    DESCRIPTION
        "Cisco Firepower storage:FlexFlashDrive:lastOperation
        managed object property"
    ::= { cfprStorageFlexFlashDriveEntry 11 }

cfprStorageFlexFlashDriveModel OBJECT-TYPE
    SYNTAX       SnmpAdminString
    MAX-ACCESS   read-only
    STATUS       current
    DESCRIPTION
        "Cisco Firepower storage:FlexFlashDrive:model managed
        object property"
    ::= { cfprStorageFlexFlashDriveEntry 12 }

cfprStorageFlexFlashDriveName OBJECT-TYPE
    SYNTAX       SnmpAdminString
    MAX-ACCESS   read-only
    STATUS       current
    DESCRIPTION
        "Cisco Firepower storage:FlexFlashDrive:name managed
        object property"
    ::= { cfprStorageFlexFlashDriveEntry 13 }

cfprStorageFlexFlashDriveNumberOfBlocks OBJECT-TYPE
    SYNTAX       Unsigned64
    MAX-ACCESS   read-only
    STATUS       current
    DESCRIPTION
        "Cisco Firepower storage:FlexFlashDrive:numberOfBlocks
        managed object property"
    ::= { cfprStorageFlexFlashDriveEntry 14 }

cfprStorageFlexFlashDriveOperQualifierReason OBJECT-TYPE
    SYNTAX       SnmpAdminString
    MAX-ACCESS   read-only
    STATUS       current
    DESCRIPTION
        "Cisco Firepower storage:FlexFlashDrive:operQualifierReason
        managed object property"
    ::= { cfprStorageFlexFlashDriveEntry 15 }

cfprStorageFlexFlashDriveOperability OBJECT-TYPE
    SYNTAX       CfprEquipmentOperability
    MAX-ACCESS   read-only
    STATUS       current
    DESCRIPTION
        "Cisco Firepower storage:FlexFlashDrive:operability
        managed object property"
    ::= { cfprStorageFlexFlashDriveEntry 16 }

cfprStorageFlexFlashDriveOperationState OBJECT-TYPE
    SYNTAX       CfprStorageOperationStateType
    MAX-ACCESS   read-only
    STATUS       current
    DESCRIPTION
        "Cisco Firepower storage:FlexFlashDrive:operationState
        managed object property"
    ::= { cfprStorageFlexFlashDriveEntry 17 }

cfprStorageFlexFlashDrivePresence OBJECT-TYPE
    SYNTAX       CfprEquipmentPresence
    MAX-ACCESS   read-only
    STATUS       current
    DESCRIPTION
        "Cisco Firepower storage:FlexFlashDrive:presence
        managed object property"
    ::= { cfprStorageFlexFlashDriveEntry 18 }

cfprStorageFlexFlashDriveRemovable OBJECT-TYPE
    SYNTAX       CfprStorageFFDriveRemovable
    MAX-ACCESS   read-only
    STATUS       current
    DESCRIPTION
        "Cisco Firepower storage:FlexFlashDrive:removable
        managed object property"
    ::= { cfprStorageFlexFlashDriveEntry 19 }

cfprStorageFlexFlashDriveRevision OBJECT-TYPE
    SYNTAX       SnmpAdminString
    MAX-ACCESS   read-only
    STATUS       current
    DESCRIPTION
        "Cisco Firepower storage:FlexFlashDrive:revision
        managed object property"
    ::= { cfprStorageFlexFlashDriveEntry 20 }

cfprStorageFlexFlashDriveSerial OBJECT-TYPE
    SYNTAX       SnmpAdminString
    MAX-ACCESS   read-only
    STATUS       current
    DESCRIPTION
        "Cisco Firepower storage:FlexFlashDrive:serial
        managed object property"
    ::= { cfprStorageFlexFlashDriveEntry 21 }

cfprStorageFlexFlashDriveSize OBJECT-TYPE
    SYNTAX       Unsigned64
    MAX-ACCESS   read-only
    STATUS       current
    DESCRIPTION
        "Cisco Firepower storage:FlexFlashDrive:size managed
        object property"
    ::= { cfprStorageFlexFlashDriveEntry 22 }

cfprStorageFlexFlashDriveSlotNumber OBJECT-TYPE
    SYNTAX       Gauge32
    MAX-ACCESS   read-only
    STATUS       current
    DESCRIPTION
        "Cisco Firepower storage:FlexFlashDrive:slotNumber
        managed object property"
    ::= { cfprStorageFlexFlashDriveEntry 23 }

cfprStorageFlexFlashDriveVendor OBJECT-TYPE
    SYNTAX       SnmpAdminString
    MAX-ACCESS   read-only
    STATUS       current
    DESCRIPTION
        "Cisco Firepower storage:FlexFlashDrive:vendor
        managed object property"
    ::= { cfprStorageFlexFlashDriveEntry 24 }

cfprStorageFlexFlashDriveVisible OBJECT-TYPE
    SYNTAX       CfprStorageFFDriveVisible
    MAX-ACCESS   read-only
    STATUS       current
    DESCRIPTION
        "Cisco Firepower storage:FlexFlashDrive:visible
        managed object property"
    ::= { cfprStorageFlexFlashDriveEntry 25 }

cfprStorageFlexFlashVirtualDriveTable OBJECT-TYPE
    SYNTAX           SEQUENCE OF CfprStorageFlexFlashVirtualDriveEntry
    MAX-ACCESS       not-accessible
    STATUS           current
    DESCRIPTION
        "Cisco Firepower storage:FlexFlashVirtualDrive
        managed object table"
    ::= { cfprStorageObjects 19 }

cfprStorageFlexFlashVirtualDriveEntry OBJECT-TYPE
    SYNTAX           CfprStorageFlexFlashVirtualDriveEntry
    MAX-ACCESS       not-accessible
    STATUS           current
    DESCRIPTION
        "Entry for the cfprStorageFlexFlashVirtualDriveTable table."
    INDEX { cfprStorageFlexFlashVirtualDriveInstanceId }
    ::= { cfprStorageFlexFlashVirtualDriveTable 1 }

CfprStorageFlexFlashVirtualDriveEntry ::= SEQUENCE {
    cfprStorageFlexFlashVirtualDriveInstanceId                       CfprManagedObjectId,
    cfprStorageFlexFlashVirtualDriveDn                               CfprManagedObjectDn,
    cfprStorageFlexFlashVirtualDriveRn                               SnmpAdminString,
    cfprStorageFlexFlashVirtualDriveBlockSize                        Gauge32,
    cfprStorageFlexFlashVirtualDriveConnectionProtocol               CfprStorageConnectionProtocol,
    cfprStorageFlexFlashVirtualDriveId                               Gauge32,
    cfprStorageFlexFlashVirtualDriveModel                            SnmpAdminString,
    cfprStorageFlexFlashVirtualDriveNumberOfBlocks                   Unsigned64,
    cfprStorageFlexFlashVirtualDriveOperQualifierReason              SnmpAdminString,
    cfprStorageFlexFlashVirtualDriveOperability                      CfprEquipmentOperability,
    cfprStorageFlexFlashVirtualDrivePresence                         CfprEquipmentPresence,
    cfprStorageFlexFlashVirtualDriveRaidHealth                       CfprStorageFFRAIDHealth,
    cfprStorageFlexFlashVirtualDriveRaidState                        CfprStorageFFRAIDState,
    cfprStorageFlexFlashVirtualDriveRevision                         SnmpAdminString,
    cfprStorageFlexFlashVirtualDriveSerial                           SnmpAdminString,
    cfprStorageFlexFlashVirtualDriveSize                             Unsigned64,
    cfprStorageFlexFlashVirtualDriveType                             CfprStorageLunType,
    cfprStorageFlexFlashVirtualDriveVendor                           SnmpAdminString
}

cfprStorageFlexFlashVirtualDriveInstanceId OBJECT-TYPE
    SYNTAX       CfprManagedObjectId
    MAX-ACCESS   not-accessible
    STATUS       current
    DESCRIPTION
        "Instance identifier of the managed object."
    ::= { cfprStorageFlexFlashVirtualDriveEntry 1 }

cfprStorageFlexFlashVirtualDriveDn OBJECT-TYPE
    SYNTAX       CfprManagedObjectDn
    MAX-ACCESS   read-only
    STATUS       current
    DESCRIPTION
        "Cisco Firepower storage:FlexFlashVirtualDrive:dn
        managed object property"
    ::= { cfprStorageFlexFlashVirtualDriveEntry 2 }

cfprStorageFlexFlashVirtualDriveRn OBJECT-TYPE
    SYNTAX       SnmpAdminString
    MAX-ACCESS   read-only
    STATUS       current
    DESCRIPTION
        "Cisco Firepower storage:FlexFlashVirtualDrive:rn
        managed object property"
    ::= { cfprStorageFlexFlashVirtualDriveEntry 3 }

cfprStorageFlexFlashVirtualDriveBlockSize OBJECT-TYPE
    SYNTAX       Gauge32
    MAX-ACCESS   read-only
    STATUS       current
    DESCRIPTION
        "Cisco Firepower storage:FlexFlashVirtualDrive:blockSize
        managed object property"
    ::= { cfprStorageFlexFlashVirtualDriveEntry 4 }

cfprStorageFlexFlashVirtualDriveConnectionProtocol OBJECT-TYPE
    SYNTAX       CfprStorageConnectionProtocol
    MAX-ACCESS   read-only
    STATUS       current
    DESCRIPTION
        "Cisco Firepower storage:FlexFlashVirtualDrive:connectionProtocol
        managed object property"
    ::= { cfprStorageFlexFlashVirtualDriveEntry 5 }

cfprStorageFlexFlashVirtualDriveId OBJECT-TYPE
    SYNTAX       Gauge32
    MAX-ACCESS   read-only
    STATUS       current
    DESCRIPTION
        "Cisco Firepower storage:FlexFlashVirtualDrive:id
        managed object property"
    ::= { cfprStorageFlexFlashVirtualDriveEntry 6 }

cfprStorageFlexFlashVirtualDriveModel OBJECT-TYPE
    SYNTAX       SnmpAdminString
    MAX-ACCESS   read-only
    STATUS       current
    DESCRIPTION
        "Cisco Firepower storage:FlexFlashVirtualDrive:model
        managed object property"
    ::= { cfprStorageFlexFlashVirtualDriveEntry 7 }

cfprStorageFlexFlashVirtualDriveNumberOfBlocks OBJECT-TYPE
    SYNTAX       Unsigned64
    MAX-ACCESS   read-only
    STATUS       current
    DESCRIPTION
        "Cisco Firepower storage:FlexFlashVirtualDrive:numberOfBlocks
        managed object property"
    ::= { cfprStorageFlexFlashVirtualDriveEntry 8 }

cfprStorageFlexFlashVirtualDriveOperQualifierReason OBJECT-TYPE
    SYNTAX       SnmpAdminString
    MAX-ACCESS   read-only
    STATUS       current
    DESCRIPTION
        "Cisco Firepower storage:FlexFlashVirtualDrive:operQualifierReason
         managed object property"
    ::= { cfprStorageFlexFlashVirtualDriveEntry 9 }

cfprStorageFlexFlashVirtualDriveOperability OBJECT-TYPE
    SYNTAX       CfprEquipmentOperability
    MAX-ACCESS   read-only
    STATUS       current
    DESCRIPTION
        "Cisco Firepower storage:FlexFlashVirtualDrive:operability
        managed object property"
    ::= { cfprStorageFlexFlashVirtualDriveEntry 10 }

cfprStorageFlexFlashVirtualDrivePresence OBJECT-TYPE
    SYNTAX       CfprEquipmentPresence
    MAX-ACCESS   read-only
    STATUS       current
    DESCRIPTION
        "Cisco Firepower storage:FlexFlashVirtualDrive:presence
        managed object property"
    ::= { cfprStorageFlexFlashVirtualDriveEntry 11 }

cfprStorageFlexFlashVirtualDriveRaidHealth OBJECT-TYPE
    SYNTAX       CfprStorageFFRAIDHealth
    MAX-ACCESS   read-only
    STATUS       current
    DESCRIPTION
        "Cisco Firepower storage:FlexFlashVirtualDrive:raidHealth
        managed object property"
    ::= { cfprStorageFlexFlashVirtualDriveEntry 12 }

cfprStorageFlexFlashVirtualDriveRaidState OBJECT-TYPE
    SYNTAX       CfprStorageFFRAIDState
    MAX-ACCESS   read-only
    STATUS       current
    DESCRIPTION
        "Cisco Firepower storage:FlexFlashVirtualDrive:raidState
        managed object property"
    ::= { cfprStorageFlexFlashVirtualDriveEntry 13 }

cfprStorageFlexFlashVirtualDriveRevision OBJECT-TYPE
    SYNTAX       SnmpAdminString
    MAX-ACCESS   read-only
    STATUS       current
    DESCRIPTION
        "Cisco Firepower storage:FlexFlashVirtualDrive:revision
        managed object property"
    ::= { cfprStorageFlexFlashVirtualDriveEntry 14 }

cfprStorageFlexFlashVirtualDriveSerial OBJECT-TYPE
    SYNTAX       SnmpAdminString
    MAX-ACCESS   read-only
    STATUS       current
    DESCRIPTION
        "Cisco Firepower storage:FlexFlashVirtualDrive:serial
        managed object property"
    ::= { cfprStorageFlexFlashVirtualDriveEntry 15 }

cfprStorageFlexFlashVirtualDriveSize OBJECT-TYPE
    SYNTAX       Unsigned64
    MAX-ACCESS   read-only
    STATUS       current
    DESCRIPTION
        "Cisco Firepower storage:FlexFlashVirtualDrive:size
        managed object property"
    ::= { cfprStorageFlexFlashVirtualDriveEntry 16 }

cfprStorageFlexFlashVirtualDriveType OBJECT-TYPE
    SYNTAX       CfprStorageLunType
    MAX-ACCESS   read-only
    STATUS       current
    DESCRIPTION
        "Cisco Firepower storage:FlexFlashVirtualDrive:type
        managed object property"
    ::= { cfprStorageFlexFlashVirtualDriveEntry 17 }

cfprStorageFlexFlashVirtualDriveVendor OBJECT-TYPE
    SYNTAX       SnmpAdminString
    MAX-ACCESS   read-only
    STATUS       current
    DESCRIPTION
        "Cisco Firepower storage:FlexFlashVirtualDrive:vendor
        managed object property"
    ::= { cfprStorageFlexFlashVirtualDriveEntry 18 }

cfprStorageIScsiTargetIfTable OBJECT-TYPE
    SYNTAX           SEQUENCE OF CfprStorageIScsiTargetIfEntry
    MAX-ACCESS       not-accessible
    STATUS           current
    DESCRIPTION
        "Cisco Firepower storage:IScsiTargetIf managed object table"
    ::= { cfprStorageObjects 20 }

cfprStorageIScsiTargetIfEntry OBJECT-TYPE
    SYNTAX           CfprStorageIScsiTargetIfEntry
    MAX-ACCESS       not-accessible
    STATUS           current
    DESCRIPTION
        "Entry for the cfprStorageIScsiTargetIfTable table."
    INDEX { cfprStorageIScsiTargetIfInstanceId }
    ::= { cfprStorageIScsiTargetIfTable 1 }

CfprStorageIScsiTargetIfEntry ::= SEQUENCE {
    cfprStorageIScsiTargetIfInstanceId                               CfprManagedObjectId,
    cfprStorageIScsiTargetIfDn                                       CfprManagedObjectDn,
    cfprStorageIScsiTargetIfRn                                       SnmpAdminString,
    cfprStorageIScsiTargetIfName                                     SnmpAdminString,
    cfprStorageIScsiTargetIfProt                                     CfprStorageProtocol
}

cfprStorageIScsiTargetIfInstanceId OBJECT-TYPE
    SYNTAX       CfprManagedObjectId
    MAX-ACCESS   not-accessible
    STATUS       current
    DESCRIPTION
        "Instance identifier of the managed object."
    ::= { cfprStorageIScsiTargetIfEntry 1 }

cfprStorageIScsiTargetIfDn OBJECT-TYPE
    SYNTAX       CfprManagedObjectDn
    MAX-ACCESS   read-only
    STATUS       current
    DESCRIPTION
        "Cisco Firepower storage:IScsiTargetIf:dn managed object property"
    ::= { cfprStorageIScsiTargetIfEntry 2 }

cfprStorageIScsiTargetIfRn OBJECT-TYPE
    SYNTAX       SnmpAdminString
    MAX-ACCESS   read-only
    STATUS       current
    DESCRIPTION
        "Cisco Firepower storage:IScsiTargetIf:rn managed object property"
    ::= { cfprStorageIScsiTargetIfEntry 3 }

cfprStorageIScsiTargetIfName OBJECT-TYPE
    SYNTAX       SnmpAdminString
    MAX-ACCESS   read-only
    STATUS       current
    DESCRIPTION
        "Cisco Firepower storage:IScsiTargetIf:name managed
        object property"
    ::= { cfprStorageIScsiTargetIfEntry 4 }

cfprStorageIScsiTargetIfProt OBJECT-TYPE
    SYNTAX       CfprStorageProtocol
    MAX-ACCESS   read-only
    STATUS       current
    DESCRIPTION
        "Cisco Firepower storage:IScsiTargetIf:prot managed
        object property"
    ::= { cfprStorageIScsiTargetIfEntry 5 }

cfprStorageIniGroupTable OBJECT-TYPE
    SYNTAX           SEQUENCE OF CfprStorageIniGroupEntry
    MAX-ACCESS       not-accessible
    STATUS           current
    DESCRIPTION
        "Cisco Firepower storage:IniGroup managed object table"
    ::= { cfprStorageObjects 21 }

cfprStorageIniGroupEntry OBJECT-TYPE
    SYNTAX           CfprStorageIniGroupEntry
    MAX-ACCESS       not-accessible
    STATUS           current
    DESCRIPTION
        "Entry for the cfprStorageIniGroupTable table."
    INDEX { cfprStorageIniGroupInstanceId }
    ::= { cfprStorageIniGroupTable 1 }

CfprStorageIniGroupEntry ::= SEQUENCE {
    cfprStorageIniGroupInstanceId                                    CfprManagedObjectId,
    cfprStorageIniGroupDn                                            CfprManagedObjectDn,
    cfprStorageIniGroupRn                                            SnmpAdminString,
    cfprStorageIniGroupDescr                                         SnmpAdminString,
    cfprStorageIniGroupGroupPolicyName                               SnmpAdminString,
    cfprStorageIniGroupIntId                                         SnmpAdminString,
    cfprStorageIniGroupName                                          SnmpAdminString,
    cfprStorageIniGroupOperProtocol                                  CfprStorageIniGroupOperProtocol,
    cfprStorageIniGroupOperState                                     CfprStorageOperState,
    cfprStorageIniGroupOwner                                         CfprStorageIniGroupOwner,
    cfprStorageIniGroupPolicyLevel                                   Gauge32,
    cfprStorageIniGroupPolicyName                                    SnmpAdminString,
    cfprStorageIniGroupPolicyOwner                                   CfprPolicyPolicyOwner,
    cfprStorageIniGroupProtocol                                      CfprStorageIniGroupProtocol,
    cfprStorageIniGroupRmtDiskCfgName                                SnmpAdminString
}

cfprStorageIniGroupInstanceId OBJECT-TYPE
    SYNTAX       CfprManagedObjectId
    MAX-ACCESS   not-accessible
    STATUS       current
    DESCRIPTION
        "Instance identifier of the managed object."
    ::= { cfprStorageIniGroupEntry 1 }

cfprStorageIniGroupDn OBJECT-TYPE
    SYNTAX       CfprManagedObjectDn
    MAX-ACCESS   read-only
    STATUS       current
    DESCRIPTION
        "Cisco Firepower storage:IniGroup:dn managed object property"
    ::= { cfprStorageIniGroupEntry 2 }

cfprStorageIniGroupRn OBJECT-TYPE
    SYNTAX       SnmpAdminString
    MAX-ACCESS   read-only
    STATUS       current
    DESCRIPTION
        "Cisco Firepower storage:IniGroup:rn managed object property"
    ::= { cfprStorageIniGroupEntry 3 }

cfprStorageIniGroupDescr OBJECT-TYPE
    SYNTAX       SnmpAdminString
    MAX-ACCESS   read-only
    STATUS       current
    DESCRIPTION
        "Cisco Firepower storage:IniGroup:descr managed object property"
    ::= { cfprStorageIniGroupEntry 4 }

cfprStorageIniGroupGroupPolicyName OBJECT-TYPE
    SYNTAX       SnmpAdminString
    MAX-ACCESS   read-only
    STATUS       current
    DESCRIPTION
        "Cisco Firepower storage:IniGroup:groupPolicyName
        managed object property"
    ::= { cfprStorageIniGroupEntry 5 }

cfprStorageIniGroupIntId OBJECT-TYPE
    SYNTAX       SnmpAdminString
    MAX-ACCESS   read-only
    STATUS       current
    DESCRIPTION
        "Cisco Firepower storage:IniGroup:intId managed object property"
    ::= { cfprStorageIniGroupEntry 6 }

cfprStorageIniGroupName OBJECT-TYPE
    SYNTAX       SnmpAdminString
    MAX-ACCESS   read-only
    STATUS       current
    DESCRIPTION
        "Cisco Firepower storage:IniGroup:name managed object property"
    ::= { cfprStorageIniGroupEntry 7 }

cfprStorageIniGroupOperProtocol OBJECT-TYPE
    SYNTAX       CfprStorageIniGroupOperProtocol
    MAX-ACCESS   read-only
    STATUS       current
    DESCRIPTION
        "Cisco Firepower storage:IniGroup:operProtocol
        managed object property"
    ::= { cfprStorageIniGroupEntry 8 }

cfprStorageIniGroupOperState OBJECT-TYPE
    SYNTAX       CfprStorageOperState
    MAX-ACCESS   read-only
    STATUS       current
    DESCRIPTION
        "Cisco Firepower storage:IniGroup:operState managed
        object property"
    ::= { cfprStorageIniGroupEntry 9 }

cfprStorageIniGroupOwner OBJECT-TYPE
    SYNTAX       CfprStorageIniGroupOwner
    MAX-ACCESS   read-only
    STATUS       current
    DESCRIPTION
        "Cisco Firepower storage:IniGroup:owner managed object property"
    ::= { cfprStorageIniGroupEntry 10 }

cfprStorageIniGroupPolicyLevel OBJECT-TYPE
    SYNTAX       Gauge32
    MAX-ACCESS   read-only
    STATUS       current
    DESCRIPTION
        "Cisco Firepower storage:IniGroup:policyLevel managed
        object property"
    ::= { cfprStorageIniGroupEntry 11 }

cfprStorageIniGroupPolicyName OBJECT-TYPE
    SYNTAX       SnmpAdminString
    MAX-ACCESS   read-only
    STATUS       current
    DESCRIPTION
        "Cisco Firepower storage:IniGroup:policyName managed
        object property"
    ::= { cfprStorageIniGroupEntry 12 }

cfprStorageIniGroupPolicyOwner OBJECT-TYPE
    SYNTAX       CfprPolicyPolicyOwner
    MAX-ACCESS   read-only
    STATUS       current
    DESCRIPTION
        "Cisco Firepower storage:IniGroup:policyOwner managed
        object property"
    ::= { cfprStorageIniGroupEntry 13 }

cfprStorageIniGroupProtocol OBJECT-TYPE
    SYNTAX       CfprStorageIniGroupProtocol
    MAX-ACCESS   read-only
    STATUS       current
    DESCRIPTION
        "Cisco Firepower storage:IniGroup:protocol managed
        object property"
    ::= { cfprStorageIniGroupEntry 14 }

cfprStorageIniGroupRmtDiskCfgName OBJECT-TYPE
    SYNTAX       SnmpAdminString
    MAX-ACCESS   read-only
    STATUS       current
    DESCRIPTION
        "Cisco Firepower storage:IniGroup:rmtDiskCfgName
        managed object property"
    ::= { cfprStorageIniGroupEntry 15 }

cfprStorageInitiatorTable OBJECT-TYPE
    SYNTAX           SEQUENCE OF CfprStorageInitiatorEntry
    MAX-ACCESS       not-accessible
    STATUS           current
    DESCRIPTION
        "Cisco Firepower storage:Initiator managed object table"
    ::= { cfprStorageObjects 22 }

cfprStorageInitiatorEntry OBJECT-TYPE
    SYNTAX           CfprStorageInitiatorEntry
    MAX-ACCESS       not-accessible
    STATUS           current
    DESCRIPTION
        "Entry for the cfprStorageInitiatorTable table."
    INDEX { cfprStorageInitiatorInstanceId }
    ::= { cfprStorageInitiatorTable 1 }

CfprStorageInitiatorEntry ::= SEQUENCE {
    cfprStorageInitiatorInstanceId                                   CfprManagedObjectId,
    cfprStorageInitiatorDn                                           CfprManagedObjectDn,
    cfprStorageInitiatorRn                                           SnmpAdminString,
    cfprStorageInitiatorDescr                                        SnmpAdminString,
    cfprStorageInitiatorDuplicateTarget                              SnmpAdminString,
    cfprStorageInitiatorIntId                                        SnmpAdminString,
    cfprStorageInitiatorName                                         SnmpAdminString,
    cfprStorageInitiatorOperState                                    CfprStorageOperState,
    cfprStorageInitiatorPolicyLevel                                  Gauge32,
    cfprStorageInitiatorPolicyOwner                                  CfprPolicyPolicyOwner
}

cfprStorageInitiatorInstanceId OBJECT-TYPE
    SYNTAX       CfprManagedObjectId
    MAX-ACCESS   not-accessible
    STATUS       current
    DESCRIPTION
        "Instance identifier of the managed object."
    ::= { cfprStorageInitiatorEntry 1 }

cfprStorageInitiatorDn OBJECT-TYPE
    SYNTAX       CfprManagedObjectDn
    MAX-ACCESS   read-only
    STATUS       current
    DESCRIPTION
        "Cisco Firepower storage:Initiator:dn managed object property"
    ::= { cfprStorageInitiatorEntry 2 }

cfprStorageInitiatorRn OBJECT-TYPE
    SYNTAX       SnmpAdminString
    MAX-ACCESS   read-only
    STATUS       current
    DESCRIPTION
        "Cisco Firepower storage:Initiator:rn managed object property"
    ::= { cfprStorageInitiatorEntry 3 }

cfprStorageInitiatorDescr OBJECT-TYPE
    SYNTAX       SnmpAdminString
    MAX-ACCESS   read-only
    STATUS       current
    DESCRIPTION
        "Cisco Firepower storage:Initiator:descr managed object property"
    ::= { cfprStorageInitiatorEntry 4 }

cfprStorageInitiatorDuplicateTarget OBJECT-TYPE
    SYNTAX       SnmpAdminString
    MAX-ACCESS   read-only
    STATUS       current
    DESCRIPTION
        "Cisco Firepower storage:Initiator:duplicateTarget
        managed object property"
    ::= { cfprStorageInitiatorEntry 5 }

cfprStorageInitiatorIntId OBJECT-TYPE
    SYNTAX       SnmpAdminString
    MAX-ACCESS   read-only
    STATUS       current
    DESCRIPTION
        "Cisco Firepower storage:Initiator:intId managed object property"
    ::= { cfprStorageInitiatorEntry 6 }

cfprStorageInitiatorName OBJECT-TYPE
    SYNTAX       SnmpAdminString
    MAX-ACCESS   read-only
    STATUS       current
    DESCRIPTION
        "Cisco Firepower storage:Initiator:name managed object property"
    ::= { cfprStorageInitiatorEntry 7 }

cfprStorageInitiatorOperState OBJECT-TYPE
    SYNTAX       CfprStorageOperState
    MAX-ACCESS   read-only
    STATUS       current
    DESCRIPTION
        "Cisco Firepower storage:Initiator:operState managed
        object property"
    ::= { cfprStorageInitiatorEntry 8 }

cfprStorageInitiatorPolicyLevel OBJECT-TYPE
    SYNTAX       Gauge32
    MAX-ACCESS   read-only
    STATUS       current
    DESCRIPTION
        "Cisco Firepower storage:Initiator:policyLevel
        managed object property"
    ::= { cfprStorageInitiatorEntry 9 }

cfprStorageInitiatorPolicyOwner OBJECT-TYPE
    SYNTAX       CfprPolicyPolicyOwner
    MAX-ACCESS   read-only
    STATUS       current
    DESCRIPTION
        "Cisco Firepower storage:Initiator:policyOwner
        managed object property"
    ::= { cfprStorageInitiatorEntry 10 }

cfprStorageItemTable OBJECT-TYPE
    SYNTAX           SEQUENCE OF CfprStorageItemEntry
    MAX-ACCESS       not-accessible
    STATUS           current
    DESCRIPTION
        "Cisco Firepower storage:Item managed object table"
    ::= { cfprStorageObjects 23 }

cfprStorageItemEntry OBJECT-TYPE
    SYNTAX           CfprStorageItemEntry
    MAX-ACCESS       not-accessible
    STATUS           current
    DESCRIPTION
        "Entry for the cfprStorageItemTable table."
    INDEX { cfprStorageItemInstanceId }
    ::= { cfprStorageItemTable 1 }

CfprStorageItemEntry ::= SEQUENCE {
    cfprStorageItemInstanceId                                        CfprManagedObjectId,
    cfprStorageItemDn                                                CfprManagedObjectDn,
    cfprStorageItemRn                                                SnmpAdminString,
    cfprStorageItemName                                              SnmpAdminString,
    cfprStorageItemOperState                                         CfprStorageFileSystemStatus,
    cfprStorageItemSize                                              Unsigned64,
    cfprStorageItemUsed                                              Gauge32
}

cfprStorageItemInstanceId OBJECT-TYPE
    SYNTAX       CfprManagedObjectId
    MAX-ACCESS   not-accessible
    STATUS       current
    DESCRIPTION
        "Instance identifier of the managed object."
    ::= { cfprStorageItemEntry 1 }

cfprStorageItemDn OBJECT-TYPE
    SYNTAX       CfprManagedObjectDn
    MAX-ACCESS   read-only
    STATUS       current
    DESCRIPTION
        "Cisco Firepower storage:Item:dn managed object property"
    ::= { cfprStorageItemEntry 2 }

cfprStorageItemRn OBJECT-TYPE
    SYNTAX       SnmpAdminString
    MAX-ACCESS   read-only
    STATUS       current
    DESCRIPTION
        "Cisco Firepower storage:Item:rn managed object property"
    ::= { cfprStorageItemEntry 3 }

cfprStorageItemName OBJECT-TYPE
    SYNTAX       SnmpAdminString
    MAX-ACCESS   read-only
    STATUS       current
    DESCRIPTION
        "Cisco Firepower storage:Item:name managed object property"
    ::= { cfprStorageItemEntry 4 }

cfprStorageItemOperState OBJECT-TYPE
    SYNTAX       CfprStorageFileSystemStatus
    MAX-ACCESS   read-only
    STATUS       current
    DESCRIPTION
        "Cisco Firepower storage:Item:operState managed object property"
    ::= { cfprStorageItemEntry 5 }

cfprStorageItemSize OBJECT-TYPE
    SYNTAX       Unsigned64
    MAX-ACCESS   read-only
    STATUS       current
    DESCRIPTION
        "Cisco Firepower storage:Item:size managed object property"
    ::= { cfprStorageItemEntry 6 }

cfprStorageItemUsed OBJECT-TYPE
    SYNTAX       Gauge32
    MAX-ACCESS   read-only
    STATUS       current
    DESCRIPTION
        "Cisco Firepower storage:Item:used managed object property"
    ::= { cfprStorageItemEntry 7 }

cfprStorageLocalDiskTable OBJECT-TYPE
    SYNTAX           SEQUENCE OF CfprStorageLocalDiskEntry
    MAX-ACCESS       not-accessible
    STATUS           current
    DESCRIPTION
        "Cisco Firepower storage:LocalDisk managed object table"
    ::= { cfprStorageObjects 24 }

cfprStorageLocalDiskEntry OBJECT-TYPE
    SYNTAX           CfprStorageLocalDiskEntry
    MAX-ACCESS       not-accessible
    STATUS           current
    DESCRIPTION
        "Entry for the cfprStorageLocalDiskTable table."
    INDEX { cfprStorageLocalDiskInstanceId }
    ::= { cfprStorageLocalDiskTable 1 }

CfprStorageLocalDiskEntry ::= SEQUENCE {
    cfprStorageLocalDiskInstanceId                                   CfprManagedObjectId,
    cfprStorageLocalDiskDn                                           CfprManagedObjectDn,
    cfprStorageLocalDiskRn                                           SnmpAdminString,
    cfprStorageLocalDiskBlockSize                                    Gauge32,
    cfprStorageLocalDiskConnectionProtocol                           CfprStorageConnectionProtocol,
    cfprStorageLocalDiskDeviceType                                   CfprStorageTechnology,
    cfprStorageLocalDiskDiskState                                    CfprStoragePDriveStatus,
    cfprStorageLocalDiskId                                           Gauge32,
    cfprStorageLocalDiskLc                                           CfprFsmLifecycle,
    cfprStorageLocalDiskLinkSpeed                                    CfprStorageLinkSpeed,
    cfprStorageLocalDiskModel                                        SnmpAdminString,
    cfprStorageLocalDiskNumberOfBlocks                               Unsigned64,
    cfprStorageLocalDiskOperQualifierReason                          SnmpAdminString,
    cfprStorageLocalDiskOperability                                  CfprEquipmentOperability,
    cfprStorageLocalDiskPowerState                                   CfprStoragePowerState,
    cfprStorageLocalDiskPresence                                     CfprEquipmentPresence,
    cfprStorageLocalDiskRevision                                     SnmpAdminString,
    cfprStorageLocalDiskSerial                                       SnmpAdminString,
    cfprStorageLocalDiskSize                                         Unsigned64,
    cfprStorageLocalDiskVendor                                       SnmpAdminString
}

cfprStorageLocalDiskInstanceId OBJECT-TYPE
    SYNTAX       CfprManagedObjectId
    MAX-ACCESS   not-accessible
    STATUS       current
    DESCRIPTION
        "Instance identifier of the managed object."
    ::= { cfprStorageLocalDiskEntry 1 }

cfprStorageLocalDiskDn OBJECT-TYPE
    SYNTAX       CfprManagedObjectDn
    MAX-ACCESS   read-only
    STATUS       current
    DESCRIPTION
        "Cisco Firepower storage:LocalDisk:dn managed object property"
    ::= { cfprStorageLocalDiskEntry 2 }

cfprStorageLocalDiskRn OBJECT-TYPE
    SYNTAX       SnmpAdminString
    MAX-ACCESS   read-only
    STATUS       current
    DESCRIPTION
        "Cisco Firepower storage:LocalDisk:rn managed object property"
    ::= { cfprStorageLocalDiskEntry 3 }

cfprStorageLocalDiskBlockSize OBJECT-TYPE
    SYNTAX       Gauge32
    MAX-ACCESS   read-only
    STATUS       current
    DESCRIPTION
        "Cisco Firepower storage:LocalDisk:blockSize managed
        object property"
    ::= { cfprStorageLocalDiskEntry 4 }

cfprStorageLocalDiskConnectionProtocol OBJECT-TYPE
    SYNTAX       CfprStorageConnectionProtocol
    MAX-ACCESS   read-only
    STATUS       current
    DESCRIPTION
        "Cisco Firepower storage:LocalDisk:connectionProtocol
        managed object property"
    ::= { cfprStorageLocalDiskEntry 5 }

cfprStorageLocalDiskDeviceType OBJECT-TYPE
    SYNTAX       CfprStorageTechnology
    MAX-ACCESS   read-only
    STATUS       current
    DESCRIPTION
        "Cisco Firepower storage:LocalDisk:deviceType managed
        object property"
    ::= { cfprStorageLocalDiskEntry 6 }

cfprStorageLocalDiskDiskState OBJECT-TYPE
    SYNTAX       CfprStoragePDriveStatus
    MAX-ACCESS   read-only
    STATUS       current
    DESCRIPTION
        "Cisco Firepower storage:LocalDisk:diskState managed
        object property"
    ::= { cfprStorageLocalDiskEntry 7 }

cfprStorageLocalDiskId OBJECT-TYPE
    SYNTAX       Gauge32
    MAX-ACCESS   read-only
    STATUS       current
    DESCRIPTION
        "Cisco Firepower storage:LocalDisk:id managed object property"
    ::= { cfprStorageLocalDiskEntry 8 }

cfprStorageLocalDiskLc OBJECT-TYPE
    SYNTAX       CfprFsmLifecycle
    MAX-ACCESS   read-only
    STATUS       current
    DESCRIPTION
        "Cisco Firepower storage:LocalDisk:lc managed object property"
    ::= { cfprStorageLocalDiskEntry 9 }

cfprStorageLocalDiskLinkSpeed OBJECT-TYPE
    SYNTAX       CfprStorageLinkSpeed
    MAX-ACCESS   read-only
    STATUS       current
    DESCRIPTION
        "Cisco Firepower storage:LocalDisk:linkSpeed managed
        object property"
    ::= { cfprStorageLocalDiskEntry 10 }

cfprStorageLocalDiskModel OBJECT-TYPE
    SYNTAX       SnmpAdminString
    MAX-ACCESS   read-only
    STATUS       current
    DESCRIPTION
        "Cisco Firepower storage:LocalDisk:model managed object property"
    ::= { cfprStorageLocalDiskEntry 11 }

cfprStorageLocalDiskNumberOfBlocks OBJECT-TYPE
    SYNTAX       Unsigned64
    MAX-ACCESS   read-only
    STATUS       current
    DESCRIPTION
        "Cisco Firepower storage:LocalDisk:numberOfBlocks
        managed object property"
    ::= { cfprStorageLocalDiskEntry 12 }

cfprStorageLocalDiskOperQualifierReason OBJECT-TYPE
    SYNTAX       SnmpAdminString
    MAX-ACCESS   read-only
    STATUS       current
    DESCRIPTION
        "Cisco Firepower storage:LocalDisk:operQualifierReason
        managed object property"
    ::= { cfprStorageLocalDiskEntry 13 }

cfprStorageLocalDiskOperability OBJECT-TYPE
    SYNTAX       CfprEquipmentOperability
    MAX-ACCESS   read-only
    STATUS       current
    DESCRIPTION
        "Cisco Firepower storage:LocalDisk:operability
        managed object property"
    ::= { cfprStorageLocalDiskEntry 14 }

cfprStorageLocalDiskPowerState OBJECT-TYPE
    SYNTAX       CfprStoragePowerState
    MAX-ACCESS   read-only
    STATUS       current
    DESCRIPTION
        "Cisco Firepower storage:LocalDisk:powerState managed
        object property"
    ::= { cfprStorageLocalDiskEntry 15 }

cfprStorageLocalDiskPresence OBJECT-TYPE
    SYNTAX       CfprEquipmentPresence
    MAX-ACCESS   read-only
    STATUS       current
    DESCRIPTION
        "Cisco Firepower storage:LocalDisk:presence managed
        object property"
    ::= { cfprStorageLocalDiskEntry 16 }

cfprStorageLocalDiskRevision OBJECT-TYPE
    SYNTAX       SnmpAdminString
    MAX-ACCESS   read-only
    STATUS       current
    DESCRIPTION
        "Cisco Firepower storage:LocalDisk:revision managed
        object property"
    ::= { cfprStorageLocalDiskEntry 17 }

cfprStorageLocalDiskSerial OBJECT-TYPE
    SYNTAX       SnmpAdminString
    MAX-ACCESS   read-only
    STATUS       current
    DESCRIPTION
        "Cisco Firepower storage:LocalDisk:serial managed object property"
    ::= { cfprStorageLocalDiskEntry 18 }

cfprStorageLocalDiskSize OBJECT-TYPE
    SYNTAX       Unsigned64
    MAX-ACCESS   read-only
    STATUS       current
    DESCRIPTION
        "Cisco Firepower storage:LocalDisk:size managed object property"
    ::= { cfprStorageLocalDiskEntry 19 }

cfprStorageLocalDiskVendor OBJECT-TYPE
    SYNTAX       SnmpAdminString
    MAX-ACCESS   read-only
    STATUS       current
    DESCRIPTION
        "Cisco Firepower storage:LocalDisk:vendor managed object property"
    ::= { cfprStorageLocalDiskEntry 20 }

cfprStorageLocalDiskConfigDefTable OBJECT-TYPE
    SYNTAX           SEQUENCE OF CfprStorageLocalDiskConfigDefEntry
    MAX-ACCESS       not-accessible
    STATUS           current
    DESCRIPTION
        "Cisco Firepower storage:LocalDiskConfigDef managed object table"
    ::= { cfprStorageObjects 25 }

cfprStorageLocalDiskConfigDefEntry OBJECT-TYPE
    SYNTAX           CfprStorageLocalDiskConfigDefEntry
    MAX-ACCESS       not-accessible
    STATUS           current
    DESCRIPTION
        "Entry for the cfprStorageLocalDiskConfigDefTable table."
    INDEX { cfprStorageLocalDiskConfigDefInstanceId }
    ::= { cfprStorageLocalDiskConfigDefTable 1 }

CfprStorageLocalDiskConfigDefEntry ::= SEQUENCE {
    cfprStorageLocalDiskConfigDefInstanceId                          CfprManagedObjectId,
    cfprStorageLocalDiskConfigDefDn                                  CfprManagedObjectDn,
    cfprStorageLocalDiskConfigDefRn                                  SnmpAdminString,
    cfprStorageLocalDiskConfigDefDescr                               SnmpAdminString,
    cfprStorageLocalDiskConfigDefFlexFlashRAIDReportingState         CfprStorageLocalDiskConfigFlexFlashRAIDReportingState,
    cfprStorageLocalDiskConfigDefFlexFlashState                      CfprStorageLocalDiskConfigFlexFlashState,
    cfprStorageLocalDiskConfigDefIntId                               SnmpAdminString,
    cfprStorageLocalDiskConfigDefMode                                CfprStorageLocalDiskMode,
    cfprStorageLocalDiskConfigDefName                                SnmpAdminString,
    cfprStorageLocalDiskConfigDefPolicyLevel                         Gauge32,
    cfprStorageLocalDiskConfigDefPolicyOwner                         CfprPolicyPolicyOwner,
    cfprStorageLocalDiskConfigDefProtectConfig                       TruthValue
}

cfprStorageLocalDiskConfigDefInstanceId OBJECT-TYPE
    SYNTAX       CfprManagedObjectId
    MAX-ACCESS   not-accessible
    STATUS       current
    DESCRIPTION
        "Instance identifier of the managed object."
    ::= { cfprStorageLocalDiskConfigDefEntry 1 }

cfprStorageLocalDiskConfigDefDn OBJECT-TYPE
    SYNTAX       CfprManagedObjectDn
    MAX-ACCESS   read-only
    STATUS       current
    DESCRIPTION
        "Cisco Firepower storage:LocalDiskConfigDef:dn
        managed object property"
    ::= { cfprStorageLocalDiskConfigDefEntry 2 }

cfprStorageLocalDiskConfigDefRn OBJECT-TYPE
    SYNTAX       SnmpAdminString
    MAX-ACCESS   read-only
    STATUS       current
    DESCRIPTION
        "Cisco Firepower storage:LocalDiskConfigDef:rn
        managed object property"
    ::= { cfprStorageLocalDiskConfigDefEntry 3 }

cfprStorageLocalDiskConfigDefDescr OBJECT-TYPE
    SYNTAX       SnmpAdminString
    MAX-ACCESS   read-only
    STATUS       current
    DESCRIPTION
        "Cisco Firepower storage:LocalDiskConfigDef:descr
        managed object property"
    ::= { cfprStorageLocalDiskConfigDefEntry 4 }

cfprStorageLocalDiskConfigDefFlexFlashRAIDReportingState OBJECT-TYPE
    SYNTAX       CfprStorageLocalDiskConfigFlexFlashRAIDReportingState
    MAX-ACCESS   read-only
    STATUS       current
    DESCRIPTION
        "Cisco Firepower storage:LocalDiskConfigDef:flexFlashRAIDReporting
        State managed object property"
    ::= { cfprStorageLocalDiskConfigDefEntry 5 }

cfprStorageLocalDiskConfigDefFlexFlashState OBJECT-TYPE
    SYNTAX       CfprStorageLocalDiskConfigFlexFlashState
    MAX-ACCESS   read-only
    STATUS       current
    DESCRIPTION
        "Cisco Firepower storage:LocalDiskConfigDef:flexFlashState
        managed object property"
    ::= { cfprStorageLocalDiskConfigDefEntry 6 }

cfprStorageLocalDiskConfigDefIntId OBJECT-TYPE
    SYNTAX       SnmpAdminString
    MAX-ACCESS   read-only
    STATUS       current
    DESCRIPTION
        "Cisco Firepower storage:LocalDiskConfigDef:intId
        managed object property"
    ::= { cfprStorageLocalDiskConfigDefEntry 7 }

cfprStorageLocalDiskConfigDefMode OBJECT-TYPE
    SYNTAX       CfprStorageLocalDiskMode
    MAX-ACCESS   read-only
    STATUS       current
    DESCRIPTION
        "Cisco Firepower storage:LocalDiskConfigDef:mode
        managed object property"
    ::= { cfprStorageLocalDiskConfigDefEntry 8 }

cfprStorageLocalDiskConfigDefName OBJECT-TYPE
    SYNTAX       SnmpAdminString
    MAX-ACCESS   read-only
    STATUS       current
    DESCRIPTION
        "Cisco Firepower storage:LocalDiskConfigDef:name
        managed object property"
    ::= { cfprStorageLocalDiskConfigDefEntry 9 }

cfprStorageLocalDiskConfigDefPolicyLevel OBJECT-TYPE
    SYNTAX       Gauge32
    MAX-ACCESS   read-only
    STATUS       current
    DESCRIPTION
        "Cisco Firepower storage:LocalDiskConfigDef:policyLevel
        managed object property"
    ::= { cfprStorageLocalDiskConfigDefEntry 10 }

cfprStorageLocalDiskConfigDefPolicyOwner OBJECT-TYPE
    SYNTAX       CfprPolicyPolicyOwner
    MAX-ACCESS   read-only
    STATUS       current
    DESCRIPTION
        "Cisco Firepower storage:LocalDiskConfigDef:policyOwner
        managed object property"
    ::= { cfprStorageLocalDiskConfigDefEntry 11 }

cfprStorageLocalDiskConfigDefProtectConfig OBJECT-TYPE
    SYNTAX       TruthValue
    MAX-ACCESS   read-only
    STATUS       current
    DESCRIPTION
        "Cisco Firepower storage:LocalDiskConfigDef:protectConfig
        managed object property"
    ::= { cfprStorageLocalDiskConfigDefEntry 12 }

cfprStorageLocalDiskConfigPolicyTable OBJECT-TYPE
    SYNTAX           SEQUENCE OF CfprStorageLocalDiskConfigPolicyEntry
    MAX-ACCESS       not-accessible
    STATUS           current
    DESCRIPTION
        "Cisco Firepower storage:LocalDiskConfigPolicy
        managed object table"
    ::= { cfprStorageObjects 26 }

cfprStorageLocalDiskConfigPolicyEntry OBJECT-TYPE
    SYNTAX           CfprStorageLocalDiskConfigPolicyEntry
    MAX-ACCESS       not-accessible
    STATUS           current
    DESCRIPTION
        "Entry for the cfprStorageLocalDiskConfigPolicyTable table."
    INDEX { cfprStorageLocalDiskConfigPolicyInstanceId }
    ::= { cfprStorageLocalDiskConfigPolicyTable 1 }

CfprStorageLocalDiskConfigPolicyEntry ::= SEQUENCE {
    cfprStorageLocalDiskConfigPolicyInstanceId                       CfprManagedObjectId,
    cfprStorageLocalDiskConfigPolicyDn                               CfprManagedObjectDn,
    cfprStorageLocalDiskConfigPolicyRn                               SnmpAdminString,
    cfprStorageLocalDiskConfigPolicyDescr                            SnmpAdminString,
    cfprStorageLocalDiskConfigPolicyFlexFlashRAIDReportingState      CfprStorageLocalDiskConfigFlexFlashRAIDReportingState,
    cfprStorageLocalDiskConfigPolicyFlexFlashState                   CfprStorageLocalDiskConfigFlexFlashState,
    cfprStorageLocalDiskConfigPolicyIntId                            SnmpAdminString,
    cfprStorageLocalDiskConfigPolicyMode                             CfprStorageLocalDiskMode,
    cfprStorageLocalDiskConfigPolicyName                             SnmpAdminString,
    cfprStorageLocalDiskConfigPolicyPolicyLevel                      Gauge32,
    cfprStorageLocalDiskConfigPolicyPolicyOwner                      CfprPolicyPolicyOwner,
    cfprStorageLocalDiskConfigPolicyProtectConfig                    TruthValue
}

cfprStorageLocalDiskConfigPolicyInstanceId OBJECT-TYPE
    SYNTAX       CfprManagedObjectId
    MAX-ACCESS   not-accessible
    STATUS       current
    DESCRIPTION
        "Instance identifier of the managed object."
    ::= { cfprStorageLocalDiskConfigPolicyEntry 1 }

cfprStorageLocalDiskConfigPolicyDn OBJECT-TYPE
    SYNTAX       CfprManagedObjectDn
    MAX-ACCESS   read-only
    STATUS       current
    DESCRIPTION
        "Cisco Firepower storage:LocalDiskConfigPolicy:dn
        managed object property"
    ::= { cfprStorageLocalDiskConfigPolicyEntry 2 }

cfprStorageLocalDiskConfigPolicyRn OBJECT-TYPE
    SYNTAX       SnmpAdminString
    MAX-ACCESS   read-only
    STATUS       current
    DESCRIPTION
        "Cisco Firepower storage:LocalDiskConfigPolicy:rn
        managed object property"
    ::= { cfprStorageLocalDiskConfigPolicyEntry 3 }

cfprStorageLocalDiskConfigPolicyDescr OBJECT-TYPE
    SYNTAX       SnmpAdminString
    MAX-ACCESS   read-only
    STATUS       current
    DESCRIPTION
        "Cisco Firepower storage:LocalDiskConfigPolicy:descr
        managed object property"
    ::= { cfprStorageLocalDiskConfigPolicyEntry 4 }

cfprStorageLocalDiskConfigPolicyFlexFlashRAIDReportingState OBJECT-TYPE
    SYNTAX       CfprStorageLocalDiskConfigFlexFlashRAIDReportingState
    MAX-ACCESS   read-only
    STATUS       current
    DESCRIPTION
        "Cisco Firepower storage:LocalDiskConfigPolicy:flexFlashRAIDReport
        ingState managed object property"
    ::= { cfprStorageLocalDiskConfigPolicyEntry 5 }

cfprStorageLocalDiskConfigPolicyFlexFlashState OBJECT-TYPE
    SYNTAX       CfprStorageLocalDiskConfigFlexFlashState
    MAX-ACCESS   read-only
    STATUS       current
    DESCRIPTION
        "Cisco Firepower storage:LocalDiskConfigPolicy:flexFlashState
        managed object property"
    ::= { cfprStorageLocalDiskConfigPolicyEntry 6 }

cfprStorageLocalDiskConfigPolicyIntId OBJECT-TYPE
    SYNTAX       SnmpAdminString
    MAX-ACCESS   read-only
    STATUS       current
    DESCRIPTION
        "Cisco Firepower storage:LocalDiskConfigPolicy:intId
        managed object property"
    ::= { cfprStorageLocalDiskConfigPolicyEntry 7 }

cfprStorageLocalDiskConfigPolicyMode OBJECT-TYPE
    SYNTAX       CfprStorageLocalDiskMode
    MAX-ACCESS   read-only
    STATUS       current
    DESCRIPTION
        "Cisco Firepower storage:LocalDiskConfigPolicy:mode
        managed object property"
    ::= { cfprStorageLocalDiskConfigPolicyEntry 8 }

cfprStorageLocalDiskConfigPolicyName OBJECT-TYPE
    SYNTAX       SnmpAdminString
    MAX-ACCESS   read-only
    STATUS       current
    DESCRIPTION
        "Cisco Firepower storage:LocalDiskConfigPolicy:name
        managed object property"
    ::= { cfprStorageLocalDiskConfigPolicyEntry 9 }

cfprStorageLocalDiskConfigPolicyPolicyLevel OBJECT-TYPE
    SYNTAX       Gauge32
    MAX-ACCESS   read-only
    STATUS       current
    DESCRIPTION
        "Cisco Firepower storage:LocalDiskConfigPolicy:policyLevel
        managed object property"
    ::= { cfprStorageLocalDiskConfigPolicyEntry 10 }

cfprStorageLocalDiskConfigPolicyPolicyOwner OBJECT-TYPE
    SYNTAX       CfprPolicyPolicyOwner
    MAX-ACCESS   read-only
    STATUS       current
    DESCRIPTION
        "Cisco Firepower storage:LocalDiskConfigPolicy:policyOwner
        managed object property"
    ::= { cfprStorageLocalDiskConfigPolicyEntry 11 }

cfprStorageLocalDiskConfigPolicyProtectConfig OBJECT-TYPE
    SYNTAX       TruthValue
    MAX-ACCESS   read-only
    STATUS       current
    DESCRIPTION
        "Cisco Firepower storage:LocalDiskConfigPolicy:protectConfig
        managed object property"
    ::= { cfprStorageLocalDiskConfigPolicyEntry 12 }

cfprStorageLocalDiskPartitionTable OBJECT-TYPE
    SYNTAX           SEQUENCE OF CfprStorageLocalDiskPartitionEntry
    MAX-ACCESS       not-accessible
    STATUS           current
    DESCRIPTION
        "Cisco Firepower storage:LocalDiskPartition managed object table"
    ::= { cfprStorageObjects 27 }

cfprStorageLocalDiskPartitionEntry OBJECT-TYPE
    SYNTAX           CfprStorageLocalDiskPartitionEntry
    MAX-ACCESS       not-accessible
    STATUS           current
    DESCRIPTION
        "Entry for the cfprStorageLocalDiskPartitionTable table."
    INDEX { cfprStorageLocalDiskPartitionInstanceId }
    ::= { cfprStorageLocalDiskPartitionTable 1 }

CfprStorageLocalDiskPartitionEntry ::= SEQUENCE {
    cfprStorageLocalDiskPartitionInstanceId                          CfprManagedObjectId,
    cfprStorageLocalDiskPartitionDn                                  CfprManagedObjectDn,
    cfprStorageLocalDiskPartitionRn                                  SnmpAdminString,
    cfprStorageLocalDiskPartitionDescr                               SnmpAdminString,
    cfprStorageLocalDiskPartitionIntId                               SnmpAdminString,
    cfprStorageLocalDiskPartitionName                                SnmpAdminString,
    cfprStorageLocalDiskPartitionOrder                               Gauge32,
    cfprStorageLocalDiskPartitionPolicyLevel                         Gauge32,
    cfprStorageLocalDiskPartitionPolicyOwner                         CfprPolicyPolicyOwner,
    cfprStorageLocalDiskPartitionSize                                Unsigned64,
    cfprStorageLocalDiskPartitionType                                CfprStorageLocalDiskPartitionType
}

cfprStorageLocalDiskPartitionInstanceId OBJECT-TYPE
    SYNTAX       CfprManagedObjectId
    MAX-ACCESS   not-accessible
    STATUS       current
    DESCRIPTION
        "Instance identifier of the managed object."
    ::= { cfprStorageLocalDiskPartitionEntry 1 }

cfprStorageLocalDiskPartitionDn OBJECT-TYPE
    SYNTAX       CfprManagedObjectDn
    MAX-ACCESS   read-only
    STATUS       current
    DESCRIPTION
        "Cisco Firepower storage:LocalDiskPartition:dn
        managed object property"
    ::= { cfprStorageLocalDiskPartitionEntry 2 }

cfprStorageLocalDiskPartitionRn OBJECT-TYPE
    SYNTAX       SnmpAdminString
    MAX-ACCESS   read-only
    STATUS       current
    DESCRIPTION
        "Cisco Firepower storage:LocalDiskPartition:rn
        managed object property"
    ::= { cfprStorageLocalDiskPartitionEntry 3 }

cfprStorageLocalDiskPartitionDescr OBJECT-TYPE
    SYNTAX       SnmpAdminString
    MAX-ACCESS   read-only
    STATUS       current
    DESCRIPTION
        "Cisco Firepower storage:LocalDiskPartition:descr
        managed object property"
    ::= { cfprStorageLocalDiskPartitionEntry 4 }

cfprStorageLocalDiskPartitionIntId OBJECT-TYPE
    SYNTAX       SnmpAdminString
    MAX-ACCESS   read-only
    STATUS       current
    DESCRIPTION
        "Cisco Firepower storage:LocalDiskPartition:intId
        managed object property"
    ::= { cfprStorageLocalDiskPartitionEntry 5 }

cfprStorageLocalDiskPartitionName OBJECT-TYPE
    SYNTAX       SnmpAdminString
    MAX-ACCESS   read-only
    STATUS       current
    DESCRIPTION
        "Cisco Firepower storage:LocalDiskPartition:name
        managed object property"
    ::= { cfprStorageLocalDiskPartitionEntry 6 }

cfprStorageLocalDiskPartitionOrder OBJECT-TYPE
    SYNTAX       Gauge32
    MAX-ACCESS   read-only
    STATUS       current
    DESCRIPTION
        "Cisco Firepower storage:LocalDiskPartition:order
        managed object property"
    ::= { cfprStorageLocalDiskPartitionEntry 7 }

cfprStorageLocalDiskPartitionPolicyLevel OBJECT-TYPE
    SYNTAX       Gauge32
    MAX-ACCESS   read-only
    STATUS       current
    DESCRIPTION
        "Cisco Firepower storage:LocalDiskPartition:policyLevel
        managed object property"
    ::= { cfprStorageLocalDiskPartitionEntry 8 }

cfprStorageLocalDiskPartitionPolicyOwner OBJECT-TYPE
    SYNTAX       CfprPolicyPolicyOwner
    MAX-ACCESS   read-only
    STATUS       current
    DESCRIPTION
        "Cisco Firepower storage:LocalDiskPartition:policyOwner
        managed object property"
    ::= { cfprStorageLocalDiskPartitionEntry 9 }

cfprStorageLocalDiskPartitionSize OBJECT-TYPE
    SYNTAX       Unsigned64
    MAX-ACCESS   read-only
    STATUS       current
    DESCRIPTION
        "Cisco Firepower storage:LocalDiskPartition:size
        managed object property"
    ::= { cfprStorageLocalDiskPartitionEntry 10 }

cfprStorageLocalDiskPartitionType OBJECT-TYPE
    SYNTAX       CfprStorageLocalDiskPartitionType
    MAX-ACCESS   read-only
    STATUS       current
    DESCRIPTION
        "Cisco Firepower storage:LocalDiskPartition:type
        managed object property"
    ::= { cfprStorageLocalDiskPartitionEntry 11 }

cfprStorageLocalDiskSlotEpTable OBJECT-TYPE
    SYNTAX           SEQUENCE OF CfprStorageLocalDiskSlotEpEntry
    MAX-ACCESS       not-accessible
    STATUS           current
    DESCRIPTION
        "Cisco Firepower storage:LocalDiskSlotEp managed object table"
    ::= { cfprStorageObjects 28 }

cfprStorageLocalDiskSlotEpEntry OBJECT-TYPE
    SYNTAX           CfprStorageLocalDiskSlotEpEntry
    MAX-ACCESS       not-accessible
    STATUS           current
    DESCRIPTION
        "Entry for the cfprStorageLocalDiskSlotEpTable table."
    INDEX { cfprStorageLocalDiskSlotEpInstanceId }
    ::= { cfprStorageLocalDiskSlotEpTable 1 }

CfprStorageLocalDiskSlotEpEntry ::= SEQUENCE {
    cfprStorageLocalDiskSlotEpInstanceId                             CfprManagedObjectId,
    cfprStorageLocalDiskSlotEpDn                                     CfprManagedObjectDn,
    cfprStorageLocalDiskSlotEpRn                                     SnmpAdminString,
    cfprStorageLocalDiskSlotEpConfiguration                          CfprStorageConfiguration,
    cfprStorageLocalDiskSlotEpId                                     Gauge32,
    cfprStorageLocalDiskSlotEpOperQualifierReason                    SnmpAdminString,
    cfprStorageLocalDiskSlotEpOperability                            CfprEquipmentOperability,
    cfprStorageLocalDiskSlotEpPeerDn                                 SnmpAdminString,
    cfprStorageLocalDiskSlotEpPresence                               CfprEquipmentPresence
}

cfprStorageLocalDiskSlotEpInstanceId OBJECT-TYPE
    SYNTAX       CfprManagedObjectId
    MAX-ACCESS   not-accessible
    STATUS       current
    DESCRIPTION
        "Instance identifier of the managed object."
    ::= { cfprStorageLocalDiskSlotEpEntry 1 }

cfprStorageLocalDiskSlotEpDn OBJECT-TYPE
    SYNTAX       CfprManagedObjectDn
    MAX-ACCESS   read-only
    STATUS       current
    DESCRIPTION
        "Cisco Firepower storage:LocalDiskSlotEp:dn managed
        object property"
    ::= { cfprStorageLocalDiskSlotEpEntry 2 }

cfprStorageLocalDiskSlotEpRn OBJECT-TYPE
    SYNTAX       SnmpAdminString
    MAX-ACCESS   read-only
    STATUS       current
    DESCRIPTION
        "Cisco Firepower storage:LocalDiskSlotEp:rn managed
        object property"
    ::= { cfprStorageLocalDiskSlotEpEntry 3 }

cfprStorageLocalDiskSlotEpConfiguration OBJECT-TYPE
    SYNTAX       CfprStorageConfiguration
    MAX-ACCESS   read-only
    STATUS       current
    DESCRIPTION
        "Cisco Firepower storage:LocalDiskSlotEp:configuration
        managed object property"
    ::= { cfprStorageLocalDiskSlotEpEntry 4 }

cfprStorageLocalDiskSlotEpId OBJECT-TYPE
    SYNTAX       Gauge32
    MAX-ACCESS   read-only
    STATUS       current
    DESCRIPTION
        "Cisco Firepower storage:LocalDiskSlotEp:id managed
        object property"
    ::= { cfprStorageLocalDiskSlotEpEntry 5 }

cfprStorageLocalDiskSlotEpOperQualifierReason OBJECT-TYPE
    SYNTAX       SnmpAdminString
    MAX-ACCESS   read-only
    STATUS       current
    DESCRIPTION
        "Cisco Firepower storage:LocalDiskSlotEp:operQualifierReason
        managed object property"
    ::= { cfprStorageLocalDiskSlotEpEntry 6 }

cfprStorageLocalDiskSlotEpOperability OBJECT-TYPE
    SYNTAX       CfprEquipmentOperability
    MAX-ACCESS   read-only
    STATUS       current
    DESCRIPTION
        "Cisco Firepower storage:LocalDiskSlotEp:operability
        managed object property"
    ::= { cfprStorageLocalDiskSlotEpEntry 7 }

cfprStorageLocalDiskSlotEpPeerDn OBJECT-TYPE
    SYNTAX       SnmpAdminString
    MAX-ACCESS   read-only
    STATUS       current
    DESCRIPTION
        "Cisco Firepower storage:LocalDiskSlotEp:peerDn
        managed object property"
    ::= { cfprStorageLocalDiskSlotEpEntry 8 }

cfprStorageLocalDiskSlotEpPresence OBJECT-TYPE
    SYNTAX       CfprEquipmentPresence
    MAX-ACCESS   read-only
    STATUS       current
    DESCRIPTION
        "Cisco Firepower storage:LocalDiskSlotEp:presence
        managed object property"
    ::= { cfprStorageLocalDiskSlotEpEntry 9 }

cfprStorageLocalLunTable OBJECT-TYPE
    SYNTAX           SEQUENCE OF CfprStorageLocalLunEntry
    MAX-ACCESS       not-accessible
    STATUS           current
    DESCRIPTION
        "Cisco Firepower storage:LocalLun managed object table"
    ::= { cfprStorageObjects 29 }

cfprStorageLocalLunEntry OBJECT-TYPE
    SYNTAX           CfprStorageLocalLunEntry
    MAX-ACCESS       not-accessible
    STATUS           current
    DESCRIPTION
        "Entry for the cfprStorageLocalLunTable table."
    INDEX { cfprStorageLocalLunInstanceId }
    ::= { cfprStorageLocalLunTable 1 }

CfprStorageLocalLunEntry ::= SEQUENCE {
    cfprStorageLocalLunInstanceId                                    CfprManagedObjectId,
    cfprStorageLocalLunDn                                            CfprManagedObjectDn,
    cfprStorageLocalLunRn                                            SnmpAdminString,
    cfprStorageLocalLunBlockSize                                     Gauge32,
    cfprStorageLocalLunConnectionProtocol                            CfprStorageConnectionProtocol,
    cfprStorageLocalLunId                                            Gauge32,
    cfprStorageLocalLunLc                                            CfprFsmLifecycle,
    cfprStorageLocalLunModel                                         SnmpAdminString,
    cfprStorageLocalLunNumberOfBlocks                                Unsigned64,
    cfprStorageLocalLunOperQualifierReason                           SnmpAdminString,
    cfprStorageLocalLunOperability                                   CfprEquipmentOperability,
    cfprStorageLocalLunPresence                                      CfprEquipmentPresence,
    cfprStorageLocalLunRevision                                      SnmpAdminString,
    cfprStorageLocalLunSerial                                        SnmpAdminString,
    cfprStorageLocalLunSize                                          Unsigned64,
    cfprStorageLocalLunType                                          CfprStorageLunType,
    cfprStorageLocalLunVendor                                        SnmpAdminString
}

cfprStorageLocalLunInstanceId OBJECT-TYPE
    SYNTAX       CfprManagedObjectId
    MAX-ACCESS   not-accessible
    STATUS       current
    DESCRIPTION
        "Instance identifier of the managed object."
    ::= { cfprStorageLocalLunEntry 1 }

cfprStorageLocalLunDn OBJECT-TYPE
    SYNTAX       CfprManagedObjectDn
    MAX-ACCESS   read-only
    STATUS       current
    DESCRIPTION
        "Cisco Firepower storage:LocalLun:dn managed object property"
    ::= { cfprStorageLocalLunEntry 2 }

cfprStorageLocalLunRn OBJECT-TYPE
    SYNTAX       SnmpAdminString
    MAX-ACCESS   read-only
    STATUS       current
    DESCRIPTION
        "Cisco Firepower storage:LocalLun:rn managed object property"
    ::= { cfprStorageLocalLunEntry 3 }

cfprStorageLocalLunBlockSize OBJECT-TYPE
    SYNTAX       Gauge32
    MAX-ACCESS   read-only
    STATUS       current
    DESCRIPTION
        "Cisco Firepower storage:LocalLun:blockSize managed
        object property"
    ::= { cfprStorageLocalLunEntry 4 }

cfprStorageLocalLunConnectionProtocol OBJECT-TYPE
    SYNTAX       CfprStorageConnectionProtocol
    MAX-ACCESS   read-only
    STATUS       current
    DESCRIPTION
        "Cisco Firepower storage:LocalLun:connectionProtocol
        managed object property"
    ::= { cfprStorageLocalLunEntry 5 }

cfprStorageLocalLunId OBJECT-TYPE
    SYNTAX       Gauge32
    MAX-ACCESS   read-only
    STATUS       current
    DESCRIPTION
        "Cisco Firepower storage:LocalLun:id managed object property"
    ::= { cfprStorageLocalLunEntry 6 }

cfprStorageLocalLunLc OBJECT-TYPE
    SYNTAX       CfprFsmLifecycle
    MAX-ACCESS   read-only
    STATUS       current
    DESCRIPTION
        "Cisco Firepower storage:LocalLun:lc managed object property"
    ::= { cfprStorageLocalLunEntry 7 }

cfprStorageLocalLunModel OBJECT-TYPE
    SYNTAX       SnmpAdminString
    MAX-ACCESS   read-only
    STATUS       current
    DESCRIPTION
        "Cisco Firepower storage:LocalLun:model managed object property"
    ::= { cfprStorageLocalLunEntry 8 }

cfprStorageLocalLunNumberOfBlocks OBJECT-TYPE
    SYNTAX       Unsigned64
    MAX-ACCESS   read-only
    STATUS       current
    DESCRIPTION
        "Cisco Firepower storage:LocalLun:numberOfBlocks
        managed object property"
    ::= { cfprStorageLocalLunEntry 9 }

cfprStorageLocalLunOperQualifierReason OBJECT-TYPE
    SYNTAX       SnmpAdminString
    MAX-ACCESS   read-only
    STATUS       current
    DESCRIPTION
        "Cisco Firepower storage:LocalLun:operQualifierReason
        managed object property"
    ::= { cfprStorageLocalLunEntry 10 }

cfprStorageLocalLunOperability OBJECT-TYPE
    SYNTAX       CfprEquipmentOperability
    MAX-ACCESS   read-only
    STATUS       current
    DESCRIPTION
        "Cisco Firepower storage:LocalLun:operability managed
        object property"
    ::= { cfprStorageLocalLunEntry 11 }

cfprStorageLocalLunPresence OBJECT-TYPE
    SYNTAX       CfprEquipmentPresence
    MAX-ACCESS   read-only
    STATUS       current
    DESCRIPTION
        "Cisco Firepower storage:LocalLun:presence managed
        object property"
    ::= { cfprStorageLocalLunEntry 12 }

cfprStorageLocalLunRevision OBJECT-TYPE
    SYNTAX       SnmpAdminString
    MAX-ACCESS   read-only
    STATUS       current
    DESCRIPTION
        "Cisco Firepower storage:LocalLun:revision managed
        object property"
    ::= { cfprStorageLocalLunEntry 13 }

cfprStorageLocalLunSerial OBJECT-TYPE
    SYNTAX       SnmpAdminString
    MAX-ACCESS   read-only
    STATUS       current
    DESCRIPTION
        "Cisco Firepower storage:LocalLun:serial managed object property"
    ::= { cfprStorageLocalLunEntry 14 }

cfprStorageLocalLunSize OBJECT-TYPE
    SYNTAX       Unsigned64
    MAX-ACCESS   read-only
    STATUS       current
    DESCRIPTION
        "Cisco Firepower storage:LocalLun:size managed object property"
    ::= { cfprStorageLocalLunEntry 15 }

cfprStorageLocalLunType OBJECT-TYPE
    SYNTAX       CfprStorageLunType
    MAX-ACCESS   read-only
    STATUS       current
    DESCRIPTION
        "Cisco Firepower storage:LocalLun:type managed object property"
    ::= { cfprStorageLocalLunEntry 16 }

cfprStorageLocalLunVendor OBJECT-TYPE
    SYNTAX       SnmpAdminString
    MAX-ACCESS   read-only
    STATUS       current
    DESCRIPTION
        "Cisco Firepower storage:LocalLun:vendor managed object property"
    ::= { cfprStorageLocalLunEntry 17 }

cfprStorageLunDiskTable OBJECT-TYPE
    SYNTAX           SEQUENCE OF CfprStorageLunDiskEntry
    MAX-ACCESS       not-accessible
    STATUS           current
    DESCRIPTION
        "Cisco Firepower storage:LunDisk managed object table"
    ::= { cfprStorageObjects 30 }

cfprStorageLunDiskEntry OBJECT-TYPE
    SYNTAX           CfprStorageLunDiskEntry
    MAX-ACCESS       not-accessible
    STATUS           current
    DESCRIPTION
        "Entry for the cfprStorageLunDiskTable table."
    INDEX { cfprStorageLunDiskInstanceId }
    ::= { cfprStorageLunDiskTable 1 }

CfprStorageLunDiskEntry ::= SEQUENCE {
    cfprStorageLunDiskInstanceId                                     CfprManagedObjectId,
    cfprStorageLunDiskDn                                             CfprManagedObjectDn,
    cfprStorageLunDiskRn                                             SnmpAdminString,
    cfprStorageLunDiskId                                             Gauge32
}

cfprStorageLunDiskInstanceId OBJECT-TYPE
    SYNTAX       CfprManagedObjectId
    MAX-ACCESS   not-accessible
    STATUS       current
    DESCRIPTION
        "Instance identifier of the managed object."
    ::= { cfprStorageLunDiskEntry 1 }

cfprStorageLunDiskDn OBJECT-TYPE
    SYNTAX       CfprManagedObjectDn
    MAX-ACCESS   read-only
    STATUS       current
    DESCRIPTION
        "Cisco Firepower storage:LunDisk:dn managed object property"
    ::= { cfprStorageLunDiskEntry 2 }

cfprStorageLunDiskRn OBJECT-TYPE
    SYNTAX       SnmpAdminString
    MAX-ACCESS   read-only
    STATUS       current
    DESCRIPTION
        "Cisco Firepower storage:LunDisk:rn managed object property"
    ::= { cfprStorageLunDiskEntry 3 }

cfprStorageLunDiskId OBJECT-TYPE
    SYNTAX       Gauge32
    MAX-ACCESS   read-only
    STATUS       current
    DESCRIPTION
        "Cisco Firepower storage:LunDisk:id managed object property"
    ::= { cfprStorageLunDiskEntry 4 }

cfprStorageMezzFlashLifeTable OBJECT-TYPE
    SYNTAX           SEQUENCE OF CfprStorageMezzFlashLifeEntry
    MAX-ACCESS       not-accessible
    STATUS           current
    DESCRIPTION
        "Cisco Firepower storage:MezzFlashLife managed object table"
    ::= { cfprStorageObjects 31 }

cfprStorageMezzFlashLifeEntry OBJECT-TYPE
    SYNTAX           CfprStorageMezzFlashLifeEntry
    MAX-ACCESS       not-accessible
    STATUS           current
    DESCRIPTION
        "Entry for the cfprStorageMezzFlashLifeTable table."
    INDEX { cfprStorageMezzFlashLifeInstanceId }
    ::= { cfprStorageMezzFlashLifeTable 1 }

CfprStorageMezzFlashLifeEntry ::= SEQUENCE {
    cfprStorageMezzFlashLifeInstanceId                               CfprManagedObjectId,
    cfprStorageMezzFlashLifeDn                                       CfprManagedObjectDn,
    cfprStorageMezzFlashLifeRn                                       SnmpAdminString,
    cfprStorageMezzFlashLifeBlockSize                                Gauge32,
    cfprStorageMezzFlashLifeConnectionProtocol                       CfprStorageConnectionProtocol,
    cfprStorageMezzFlashLifeFlashPercentage                          SnmpAdminString,
    cfprStorageMezzFlashLifeFlashStatus                              SnmpAdminString,
    cfprStorageMezzFlashLifeId                                       Gauge32,
    cfprStorageMezzFlashLifeModel                                    SnmpAdminString,
    cfprStorageMezzFlashLifeNumberOfBlocks                           Unsigned64,
    cfprStorageMezzFlashLifeOperQualifierReason                      SnmpAdminString,
    cfprStorageMezzFlashLifeOperability                              CfprEquipmentOperability,
    cfprStorageMezzFlashLifePresence                                 CfprEquipmentPresence,
    cfprStorageMezzFlashLifeRevision                                 SnmpAdminString,
    cfprStorageMezzFlashLifeSerial                                   SnmpAdminString,
    cfprStorageMezzFlashLifeSize                                     Unsigned64,
    cfprStorageMezzFlashLifeVendor                                   SnmpAdminString
}

cfprStorageMezzFlashLifeInstanceId OBJECT-TYPE
    SYNTAX       CfprManagedObjectId
    MAX-ACCESS   not-accessible
    STATUS       current
    DESCRIPTION
        "Instance identifier of the managed object."
    ::= { cfprStorageMezzFlashLifeEntry 1 }

cfprStorageMezzFlashLifeDn OBJECT-TYPE
    SYNTAX       CfprManagedObjectDn
    MAX-ACCESS   read-only
    STATUS       current
    DESCRIPTION
        "Cisco Firepower storage:MezzFlashLife:dn managed object property"
    ::= { cfprStorageMezzFlashLifeEntry 2 }

cfprStorageMezzFlashLifeRn OBJECT-TYPE
    SYNTAX       SnmpAdminString
    MAX-ACCESS   read-only
    STATUS       current
    DESCRIPTION
        "Cisco Firepower storage:MezzFlashLife:rn managed object property"
    ::= { cfprStorageMezzFlashLifeEntry 3 }

cfprStorageMezzFlashLifeBlockSize OBJECT-TYPE
    SYNTAX       Gauge32
    MAX-ACCESS   read-only
    STATUS       current
    DESCRIPTION
        "Cisco Firepower storage:MezzFlashLife:blockSize
        managed object property"
    ::= { cfprStorageMezzFlashLifeEntry 4 }

cfprStorageMezzFlashLifeConnectionProtocol OBJECT-TYPE
    SYNTAX       CfprStorageConnectionProtocol
    MAX-ACCESS   read-only
    STATUS       current
    DESCRIPTION
        "Cisco Firepower storage:MezzFlashLife:connectionProtocol
        managed object property"
    ::= { cfprStorageMezzFlashLifeEntry 5 }

cfprStorageMezzFlashLifeFlashPercentage OBJECT-TYPE
    SYNTAX       SnmpAdminString
    MAX-ACCESS   read-only
    STATUS       current
    DESCRIPTION
        "Cisco Firepower storage:MezzFlashLife:flashPercentage
        managed object property"
    ::= { cfprStorageMezzFlashLifeEntry 6 }

cfprStorageMezzFlashLifeFlashStatus OBJECT-TYPE
    SYNTAX       SnmpAdminString
    MAX-ACCESS   read-only
    STATUS       current
    DESCRIPTION
        "Cisco Firepower storage:MezzFlashLife:flashStatus
        managed object property"
    ::= { cfprStorageMezzFlashLifeEntry 7 }

cfprStorageMezzFlashLifeId OBJECT-TYPE
    SYNTAX       Gauge32
    MAX-ACCESS   read-only
    STATUS       current
    DESCRIPTION
        "Cisco Firepower storage:MezzFlashLife:id managed object property"
    ::= { cfprStorageMezzFlashLifeEntry 8 }

cfprStorageMezzFlashLifeModel OBJECT-TYPE
    SYNTAX       SnmpAdminString
    MAX-ACCESS   read-only
    STATUS       current
    DESCRIPTION
        "Cisco Firepower storage:MezzFlashLife:model managed
        object property"
    ::= { cfprStorageMezzFlashLifeEntry 9 }

cfprStorageMezzFlashLifeNumberOfBlocks OBJECT-TYPE
    SYNTAX       Unsigned64
    MAX-ACCESS   read-only
    STATUS       current
    DESCRIPTION
        "Cisco Firepower storage:MezzFlashLife:numberOfBlocks
        managed object property"
    ::= { cfprStorageMezzFlashLifeEntry 10 }

cfprStorageMezzFlashLifeOperQualifierReason OBJECT-TYPE
    SYNTAX       SnmpAdminString
    MAX-ACCESS   read-only
    STATUS       current
    DESCRIPTION
        "Cisco Firepower storage:MezzFlashLife:operQualifierReason
        managed object property"
    ::= { cfprStorageMezzFlashLifeEntry 11 }

cfprStorageMezzFlashLifeOperability OBJECT-TYPE
    SYNTAX       CfprEquipmentOperability
    MAX-ACCESS   read-only
    STATUS       current
    DESCRIPTION
        "Cisco Firepower storage:MezzFlashLife:operability
        managed object property"
    ::= { cfprStorageMezzFlashLifeEntry 12 }

cfprStorageMezzFlashLifePresence OBJECT-TYPE
    SYNTAX       CfprEquipmentPresence
    MAX-ACCESS   read-only
    STATUS       current
    DESCRIPTION
        "Cisco Firepower storage:MezzFlashLife:presence
        managed object property"
    ::= { cfprStorageMezzFlashLifeEntry 13 }

cfprStorageMezzFlashLifeRevision OBJECT-TYPE
    SYNTAX       SnmpAdminString
    MAX-ACCESS   read-only
    STATUS       current
    DESCRIPTION
        "Cisco Firepower storage:MezzFlashLife:revision
        managed object property"
    ::= { cfprStorageMezzFlashLifeEntry 14 }

cfprStorageMezzFlashLifeSerial OBJECT-TYPE
    SYNTAX       SnmpAdminString
    MAX-ACCESS   read-only
    STATUS       current
    DESCRIPTION
        "Cisco Firepower storage:MezzFlashLife:serial managed
        object property"
    ::= { cfprStorageMezzFlashLifeEntry 15 }

cfprStorageMezzFlashLifeSize OBJECT-TYPE
    SYNTAX       Unsigned64
    MAX-ACCESS   read-only
    STATUS       current
    DESCRIPTION
        "Cisco Firepower storage:MezzFlashLife:size managed
        object property"
    ::= { cfprStorageMezzFlashLifeEntry 16 }

cfprStorageMezzFlashLifeVendor OBJECT-TYPE
    SYNTAX       SnmpAdminString
    MAX-ACCESS   read-only
    STATUS       current
    DESCRIPTION
        "Cisco Firepower storage:MezzFlashLife:vendor managed
        object property"
    ::= { cfprStorageMezzFlashLifeEntry 17 }

cfprStorageNodeEpTable OBJECT-TYPE
    SYNTAX           SEQUENCE OF CfprStorageNodeEpEntry
    MAX-ACCESS       not-accessible
    STATUS           current
    DESCRIPTION
        "Cisco Firepower storage:NodeEp managed object table"
    ::= { cfprStorageObjects 32 }

cfprStorageNodeEpEntry OBJECT-TYPE
    SYNTAX           CfprStorageNodeEpEntry
    MAX-ACCESS       not-accessible
    STATUS           current
    DESCRIPTION
        "Entry for the cfprStorageNodeEpTable table."
    INDEX { cfprStorageNodeEpInstanceId }
    ::= { cfprStorageNodeEpTable 1 }

CfprStorageNodeEpEntry ::= SEQUENCE {
    cfprStorageNodeEpInstanceId                                      CfprManagedObjectId,
    cfprStorageNodeEpDn                                              CfprManagedObjectDn,
    cfprStorageNodeEpRn                                              SnmpAdminString,
    cfprStorageNodeEpEpDn                                            SnmpAdminString,
    cfprStorageNodeEpId                                              Gauge32
}

cfprStorageNodeEpInstanceId OBJECT-TYPE
    SYNTAX       CfprManagedObjectId
    MAX-ACCESS   not-accessible
    STATUS       current
    DESCRIPTION
        "Instance identifier of the managed object."
    ::= { cfprStorageNodeEpEntry 1 }

cfprStorageNodeEpDn OBJECT-TYPE
    SYNTAX       CfprManagedObjectDn
    MAX-ACCESS   read-only
    STATUS       current
    DESCRIPTION
        "Cisco Firepower storage:NodeEp:dn managed object property"
    ::= { cfprStorageNodeEpEntry 2 }

cfprStorageNodeEpRn OBJECT-TYPE
    SYNTAX       SnmpAdminString
    MAX-ACCESS   read-only
    STATUS       current
    DESCRIPTION
        "Cisco Firepower storage:NodeEp:rn managed object property"
    ::= { cfprStorageNodeEpEntry 3 }

cfprStorageNodeEpEpDn OBJECT-TYPE
    SYNTAX       SnmpAdminString
    MAX-ACCESS   read-only
    STATUS       current
    DESCRIPTION
        "Cisco Firepower storage:NodeEp:epDn managed object property"
    ::= { cfprStorageNodeEpEntry 4 }

cfprStorageNodeEpId OBJECT-TYPE
    SYNTAX       Gauge32
    MAX-ACCESS   read-only
    STATUS       current
    DESCRIPTION
        "Cisco Firepower storage:NodeEp:id managed object property"
    ::= { cfprStorageNodeEpEntry 5 }

cfprStorageOperationTable OBJECT-TYPE
    SYNTAX           SEQUENCE OF CfprStorageOperationEntry
    MAX-ACCESS       not-accessible
    STATUS           current
    DESCRIPTION
        "Cisco Firepower storage:Operation managed object table"
    ::= { cfprStorageObjects 33 }

cfprStorageOperationEntry OBJECT-TYPE
    SYNTAX           CfprStorageOperationEntry
    MAX-ACCESS       not-accessible
    STATUS           current
    DESCRIPTION
        "Entry for the cfprStorageOperationTable table."
    INDEX { cfprStorageOperationInstanceId }
    ::= { cfprStorageOperationTable 1 }

CfprStorageOperationEntry ::= SEQUENCE {
    cfprStorageOperationInstanceId                                   CfprManagedObjectId,
    cfprStorageOperationDn                                           CfprManagedObjectDn,
    cfprStorageOperationRn                                           SnmpAdminString,
    cfprStorageOperationEndTime                                      DateAndTime,
    cfprStorageOperationName                                         CfprStorageOperationType,
    cfprStorageOperationOperState                                    CfprStorageOperationState,
    cfprStorageOperationProgress                                     Gauge32,
    cfprStorageOperationStartTime                                    DateAndTime,
    cfprStorageOperationStatusDescr                                  SnmpAdminString
}

cfprStorageOperationInstanceId OBJECT-TYPE
    SYNTAX       CfprManagedObjectId
    MAX-ACCESS   not-accessible
    STATUS       current
    DESCRIPTION
        "Instance identifier of the managed object."
    ::= { cfprStorageOperationEntry 1 }

cfprStorageOperationDn OBJECT-TYPE
    SYNTAX       CfprManagedObjectDn
    MAX-ACCESS   read-only
    STATUS       current
    DESCRIPTION
        "Cisco Firepower storage:Operation:dn managed object property"
    ::= { cfprStorageOperationEntry 2 }

cfprStorageOperationRn OBJECT-TYPE
    SYNTAX       SnmpAdminString
    MAX-ACCESS   read-only
    STATUS       current
    DESCRIPTION
        "Cisco Firepower storage:Operation:rn managed object property"
    ::= { cfprStorageOperationEntry 3 }

cfprStorageOperationEndTime OBJECT-TYPE
    SYNTAX       DateAndTime
    MAX-ACCESS   read-only
    STATUS       current
    DESCRIPTION
        "Cisco Firepower storage:Operation:endTime managed
        object property"
    ::= { cfprStorageOperationEntry 4 }

cfprStorageOperationName OBJECT-TYPE
    SYNTAX       CfprStorageOperationType
    MAX-ACCESS   read-only
    STATUS       current
    DESCRIPTION
        "Cisco Firepower storage:Operation:name managed object property"
    ::= { cfprStorageOperationEntry 5 }

cfprStorageOperationOperState OBJECT-TYPE
    SYNTAX       CfprStorageOperationState
    MAX-ACCESS   read-only
    STATUS       current
    DESCRIPTION
        "Cisco Firepower storage:Operation:operState managed
        object property"
    ::= { cfprStorageOperationEntry 6 }

cfprStorageOperationProgress OBJECT-TYPE
    SYNTAX       Gauge32
    MAX-ACCESS   read-only
    STATUS       current
    DESCRIPTION
        "Cisco Firepower storage:Operation:progress managed
        object property"
    ::= { cfprStorageOperationEntry 7 }

cfprStorageOperationStartTime OBJECT-TYPE
    SYNTAX       DateAndTime
    MAX-ACCESS   read-only
    STATUS       current
    DESCRIPTION
        "Cisco Firepower storage:Operation:startTime managed
        object property"
    ::= { cfprStorageOperationEntry 8 }

cfprStorageOperationStatusDescr OBJECT-TYPE
    SYNTAX       SnmpAdminString
    MAX-ACCESS   read-only
    STATUS       current
    DESCRIPTION
        "Cisco Firepower storage:Operation:statusDescr
        managed object property"
    ::= { cfprStorageOperationEntry 9 }

cfprStorageQualTable OBJECT-TYPE
    SYNTAX           SEQUENCE OF CfprStorageQualEntry
    MAX-ACCESS       not-accessible
    STATUS           current
    DESCRIPTION
        "Cisco Firepower storage:Qual managed object table"
    ::= { cfprStorageObjects 34 }

cfprStorageQualEntry OBJECT-TYPE
    SYNTAX           CfprStorageQualEntry
    MAX-ACCESS       not-accessible
    STATUS           current
    DESCRIPTION
        "Entry for the cfprStorageQualTable table."
    INDEX { cfprStorageQualInstanceId }
    ::= { cfprStorageQualTable 1 }

CfprStorageQualEntry ::= SEQUENCE {
    cfprStorageQualInstanceId                                        CfprManagedObjectId,
    cfprStorageQualDn                                                CfprManagedObjectDn,
    cfprStorageQualRn                                                SnmpAdminString,
    cfprStorageQualBlockSize                                         Gauge32,
    cfprStorageQualDiskless                                          CfprStorageDisklessAction,
    cfprStorageQualMaxCap                                            Unsigned64,
    cfprStorageQualMinCap                                            Unsigned64,
    cfprStorageQualNumberOfBlocks                                    Unsigned64,
    cfprStorageQualNumberOfFlexFlashCards                            INTEGER,
    cfprStorageQualPerDiskCap                                        Unsigned64,
    cfprStorageQualUnits                                             Gauge32
}

cfprStorageQualInstanceId OBJECT-TYPE
    SYNTAX       CfprManagedObjectId
    MAX-ACCESS   not-accessible
    STATUS       current
    DESCRIPTION
        "Instance identifier of the managed object."
    ::= { cfprStorageQualEntry 1 }

cfprStorageQualDn OBJECT-TYPE
    SYNTAX       CfprManagedObjectDn
    MAX-ACCESS   read-only
    STATUS       current
    DESCRIPTION
        "Cisco Firepower storage:Qual:dn managed object property"
    ::= { cfprStorageQualEntry 2 }

cfprStorageQualRn OBJECT-TYPE
    SYNTAX       SnmpAdminString
    MAX-ACCESS   read-only
    STATUS       current
    DESCRIPTION
        "Cisco Firepower storage:Qual:rn managed object property"
    ::= { cfprStorageQualEntry 3 }

cfprStorageQualBlockSize OBJECT-TYPE
    SYNTAX       Gauge32
    MAX-ACCESS   read-only
    STATUS       current
    DESCRIPTION
        "Cisco Firepower storage:Qual:blockSize managed object property"
    ::= { cfprStorageQualEntry 4 }

cfprStorageQualDiskless OBJECT-TYPE
    SYNTAX       CfprStorageDisklessAction
    MAX-ACCESS   read-only
    STATUS       current
    DESCRIPTION
        "Cisco Firepower storage:Qual:diskless managed object property"
    ::= { cfprStorageQualEntry 5 }

cfprStorageQualMaxCap OBJECT-TYPE
    SYNTAX       Unsigned64
    MAX-ACCESS   read-only
    STATUS       current
    DESCRIPTION
        "Cisco Firepower storage:Qual:maxCap managed object property"
    ::= { cfprStorageQualEntry 6 }

cfprStorageQualMinCap OBJECT-TYPE
    SYNTAX       Unsigned64
    MAX-ACCESS   read-only
    STATUS       current
    DESCRIPTION
        "Cisco Firepower storage:Qual:minCap managed object property"
    ::= { cfprStorageQualEntry 7 }

cfprStorageQualNumberOfBlocks OBJECT-TYPE
    SYNTAX       Unsigned64
    MAX-ACCESS   read-only
    STATUS       current
    DESCRIPTION
        "Cisco Firepower storage:Qual:numberOfBlocks managed
        object property"
    ::= { cfprStorageQualEntry 8 }

cfprStorageQualNumberOfFlexFlashCards OBJECT-TYPE
    SYNTAX       INTEGER
    MAX-ACCESS   read-only
    STATUS       current
    DESCRIPTION
        "Cisco Firepower storage:Qual:numberOfFlexFlashCards
        managed object property"
    ::= { cfprStorageQualEntry 9 }

cfprStorageQualPerDiskCap OBJECT-TYPE
    SYNTAX       Unsigned64
    MAX-ACCESS   read-only
    STATUS       current
    DESCRIPTION
        "Cisco Firepower storage:Qual:perDiskCap managed object property"
    ::= { cfprStorageQualEntry 10 }

cfprStorageQualUnits OBJECT-TYPE
    SYNTAX       Gauge32
    MAX-ACCESS   read-only
    STATUS       current
    DESCRIPTION
        "Cisco Firepower storage:Qual:units managed object property"
    ::= { cfprStorageQualEntry 11 }

cfprStorageRaidBatteryTable OBJECT-TYPE
    SYNTAX           SEQUENCE OF CfprStorageRaidBatteryEntry
    MAX-ACCESS       not-accessible
    STATUS           current
    DESCRIPTION
        "Cisco Firepower storage:RaidBattery managed object table"
    ::= { cfprStorageObjects 35 }

cfprStorageRaidBatteryEntry OBJECT-TYPE
    SYNTAX           CfprStorageRaidBatteryEntry
    MAX-ACCESS       not-accessible
    STATUS           current
    DESCRIPTION
        "Entry for the cfprStorageRaidBatteryTable table."
    INDEX { cfprStorageRaidBatteryInstanceId }
    ::= { cfprStorageRaidBatteryTable 1 }

CfprStorageRaidBatteryEntry ::= SEQUENCE {
    cfprStorageRaidBatteryInstanceId                                 CfprManagedObjectId,
    cfprStorageRaidBatteryDn                                         CfprManagedObjectDn,
    cfprStorageRaidBatteryRn                                         SnmpAdminString,
    cfprStorageRaidBatteryBatteryType                                CfprStorageBatteryType,
    cfprStorageRaidBatteryBbuStatus                                  CfprStorageBbuStatus,
    cfprStorageRaidBatteryBlockSize                                  Gauge32,
    cfprStorageRaidBatteryCapacityPercentage                         Gauge32,
    cfprStorageRaidBatteryConnectionProtocol                         CfprStorageConnectionProtocol,
    cfprStorageRaidBatteryId                                         Gauge32,
    cfprStorageRaidBatteryLc                                         CfprFsmLifecycle,
    cfprStorageRaidBatteryLearnCycleRequested                        CfprStorageLearnCycleRequested,
    cfprStorageRaidBatteryLearnMode                                  CfprStorageLearnMode,
    cfprStorageRaidBatteryModel                                      SnmpAdminString,
    cfprStorageRaidBatteryNextLearnCycleTs                           DateAndTime,
    cfprStorageRaidBatteryNumberOfBlocks                             Unsigned64,
    cfprStorageRaidBatteryOperQualifierReason                        SnmpAdminString,
    cfprStorageRaidBatteryOperability                                CfprEquipmentOperability,
    cfprStorageRaidBatteryOperabilityQualifier                       CfprStorageRaidBatteryOperabilityQualifier,
    cfprStorageRaidBatteryOperabilityQualifierReason                 SnmpAdminString,
    cfprStorageRaidBatteryPresence                                   CfprEquipmentPresence,
    cfprStorageRaidBatteryRevision                                   SnmpAdminString,
    cfprStorageRaidBatterySerial                                     SnmpAdminString,
    cfprStorageRaidBatterySize                                       Unsigned64,
    cfprStorageRaidBatteryTemperature                                INTEGER,
    cfprStorageRaidBatteryVendor                                     SnmpAdminString
}

cfprStorageRaidBatteryInstanceId OBJECT-TYPE
    SYNTAX       CfprManagedObjectId
    MAX-ACCESS   not-accessible
    STATUS       current
    DESCRIPTION
        "Instance identifier of the managed object."
    ::= { cfprStorageRaidBatteryEntry 1 }

cfprStorageRaidBatteryDn OBJECT-TYPE
    SYNTAX       CfprManagedObjectDn
    MAX-ACCESS   read-only
    STATUS       current
    DESCRIPTION
        "Cisco Firepower storage:RaidBattery:dn managed object property"
    ::= { cfprStorageRaidBatteryEntry 2 }

cfprStorageRaidBatteryRn OBJECT-TYPE
    SYNTAX       SnmpAdminString
    MAX-ACCESS   read-only
    STATUS       current
    DESCRIPTION
        "Cisco Firepower storage:RaidBattery:rn managed object property"
    ::= { cfprStorageRaidBatteryEntry 3 }

cfprStorageRaidBatteryBatteryType OBJECT-TYPE
    SYNTAX       CfprStorageBatteryType
    MAX-ACCESS   read-only
    STATUS       current
    DESCRIPTION
        "Cisco Firepower storage:RaidBattery:batteryType
        managed object property"
    ::= { cfprStorageRaidBatteryEntry 4 }

cfprStorageRaidBatteryBbuStatus OBJECT-TYPE
    SYNTAX       CfprStorageBbuStatus
    MAX-ACCESS   read-only
    STATUS       current
    DESCRIPTION
        "Cisco Firepower storage:RaidBattery:bbuStatus
        managed object property"
    ::= { cfprStorageRaidBatteryEntry 5 }

cfprStorageRaidBatteryBlockSize OBJECT-TYPE
    SYNTAX       Gauge32
    MAX-ACCESS   read-only
    STATUS       current
    DESCRIPTION
        "Cisco Firepower storage:RaidBattery:blockSize
        managed object property"
    ::= { cfprStorageRaidBatteryEntry 6 }

cfprStorageRaidBatteryCapacityPercentage OBJECT-TYPE
    SYNTAX       Gauge32
    MAX-ACCESS   read-only
    STATUS       current
    DESCRIPTION
        "Cisco Firepower storage:RaidBattery:capacityPercentage
        managed object property"
    ::= { cfprStorageRaidBatteryEntry 7 }

cfprStorageRaidBatteryConnectionProtocol OBJECT-TYPE
    SYNTAX       CfprStorageConnectionProtocol
    MAX-ACCESS   read-only
    STATUS       current
    DESCRIPTION
        "Cisco Firepower storage:RaidBattery:connectionProtocol
        managed object property"
    ::= { cfprStorageRaidBatteryEntry 8 }

cfprStorageRaidBatteryId OBJECT-TYPE
    SYNTAX       Gauge32
    MAX-ACCESS   read-only
    STATUS       current
    DESCRIPTION
        "Cisco Firepower storage:RaidBattery:id managed object property"
    ::= { cfprStorageRaidBatteryEntry 9 }

cfprStorageRaidBatteryLc OBJECT-TYPE
    SYNTAX       CfprFsmLifecycle
    MAX-ACCESS   read-only
    STATUS       current
    DESCRIPTION
        "Cisco Firepower storage:RaidBattery:lc managed object property"
    ::= { cfprStorageRaidBatteryEntry 10 }

cfprStorageRaidBatteryLearnCycleRequested OBJECT-TYPE
    SYNTAX       CfprStorageLearnCycleRequested
    MAX-ACCESS   read-only
    STATUS       current
    DESCRIPTION
        "Cisco Firepower storage:RaidBattery:learnCycleRequested
        managed object property"
    ::= { cfprStorageRaidBatteryEntry 11 }

cfprStorageRaidBatteryLearnMode OBJECT-TYPE
    SYNTAX       CfprStorageLearnMode
    MAX-ACCESS   read-only
    STATUS       current
    DESCRIPTION
        "Cisco Firepower storage:RaidBattery:learnMode
        managed object property"
    ::= { cfprStorageRaidBatteryEntry 12 }

cfprStorageRaidBatteryModel OBJECT-TYPE
    SYNTAX       SnmpAdminString
    MAX-ACCESS   read-only
    STATUS       current
    DESCRIPTION
        "Cisco Firepower storage:RaidBattery:model managed
        object property"
    ::= { cfprStorageRaidBatteryEntry 13 }

cfprStorageRaidBatteryNextLearnCycleTs OBJECT-TYPE
    SYNTAX       DateAndTime
    MAX-ACCESS   read-only
    STATUS       current
    DESCRIPTION
        "Cisco Firepower storage:RaidBattery:nextLearnCycleTs
        managed object property"
    ::= { cfprStorageRaidBatteryEntry 14 }

cfprStorageRaidBatteryNumberOfBlocks OBJECT-TYPE
    SYNTAX       Unsigned64
    MAX-ACCESS   read-only
    STATUS       current
    DESCRIPTION
        "Cisco Firepower storage:RaidBattery:numberOfBlocks
        managed object property"
    ::= { cfprStorageRaidBatteryEntry 15 }

cfprStorageRaidBatteryOperQualifierReason OBJECT-TYPE
    SYNTAX       SnmpAdminString
    MAX-ACCESS   read-only
    STATUS       current
    DESCRIPTION
        "Cisco Firepower storage:RaidBattery:operQualifierReason
        managed object property"
    ::= { cfprStorageRaidBatteryEntry 16 }

cfprStorageRaidBatteryOperability OBJECT-TYPE
    SYNTAX       CfprEquipmentOperability
    MAX-ACCESS   read-only
    STATUS       current
    DESCRIPTION
        "Cisco Firepower storage:RaidBattery:operability
        managed object property"
    ::= { cfprStorageRaidBatteryEntry 17 }

cfprStorageRaidBatteryOperabilityQualifier OBJECT-TYPE
    SYNTAX       CfprStorageRaidBatteryOperabilityQualifier
    MAX-ACCESS   read-only
    STATUS       current
    DESCRIPTION
        "Cisco Firepower storage:RaidBattery:operabilityQualifier
        managed object property"
    ::= { cfprStorageRaidBatteryEntry 18 }

cfprStorageRaidBatteryOperabilityQualifierReason OBJECT-TYPE
    SYNTAX       SnmpAdminString
    MAX-ACCESS   read-only
    STATUS       current
    DESCRIPTION
        "Cisco Firepower storage:RaidBattery:operabilityQualifierReason
        managed object property"
    ::= { cfprStorageRaidBatteryEntry 19 }

cfprStorageRaidBatteryPresence OBJECT-TYPE
    SYNTAX       CfprEquipmentPresence
    MAX-ACCESS   read-only
    STATUS       current
    DESCRIPTION
        "Cisco Firepower storage:RaidBattery:presence managed
        object property"
    ::= { cfprStorageRaidBatteryEntry 20 }

cfprStorageRaidBatteryRevision OBJECT-TYPE
    SYNTAX       SnmpAdminString
    MAX-ACCESS   read-only
    STATUS       current
    DESCRIPTION
        "Cisco Firepower storage:RaidBattery:revision managed
        object property"
    ::= { cfprStorageRaidBatteryEntry 21 }

cfprStorageRaidBatterySerial OBJECT-TYPE
    SYNTAX       SnmpAdminString
    MAX-ACCESS   read-only
    STATUS       current
    DESCRIPTION
        "Cisco Firepower storage:RaidBattery:serial managed
        object property"
    ::= { cfprStorageRaidBatteryEntry 22 }

cfprStorageRaidBatterySize OBJECT-TYPE
    SYNTAX       Unsigned64
    MAX-ACCESS   read-only
    STATUS       current
    DESCRIPTION
        "Cisco Firepower storage:RaidBattery:size managed object property"
    ::= { cfprStorageRaidBatteryEntry 23 }

cfprStorageRaidBatteryTemperature OBJECT-TYPE
    SYNTAX       INTEGER
    MAX-ACCESS   read-only
    STATUS       current
    DESCRIPTION
        "Cisco Firepower storage:RaidBattery:temperature
        managed object property"
    ::= { cfprStorageRaidBatteryEntry 24 }

cfprStorageRaidBatteryVendor OBJECT-TYPE
    SYNTAX       SnmpAdminString
    MAX-ACCESS   read-only
    STATUS       current
    DESCRIPTION
        "Cisco Firepower storage:RaidBattery:vendor managed
        object property"
    ::= { cfprStorageRaidBatteryEntry 25 }

cfprStorageSystemTable OBJECT-TYPE
    SYNTAX           SEQUENCE OF CfprStorageSystemEntry
    MAX-ACCESS       not-accessible
    STATUS           current
    DESCRIPTION
        "Cisco Firepower storage:System managed object table"
    ::= { cfprStorageObjects 36 }

cfprStorageSystemEntry OBJECT-TYPE
    SYNTAX           CfprStorageSystemEntry
    MAX-ACCESS       not-accessible
    STATUS           current
    DESCRIPTION
        "Entry for the cfprStorageSystemTable table."
    INDEX { cfprStorageSystemInstanceId }
    ::= { cfprStorageSystemTable 1 }

CfprStorageSystemEntry ::= SEQUENCE {
    cfprStorageSystemInstanceId                                      CfprManagedObjectId,
    cfprStorageSystemDn                                              CfprManagedObjectDn,
    cfprStorageSystemRn                                              SnmpAdminString,
    cfprStorageSystemFsmDescr                                        SnmpAdminString,
    cfprStorageSystemFsmPrev                                         SnmpAdminString,
    cfprStorageSystemFsmProgr                                        Gauge32,
    cfprStorageSystemFsmRmtInvErrCode                                Gauge32,
    cfprStorageSystemFsmRmtInvErrDescr                               SnmpAdminString,
    cfprStorageSystemFsmRmtInvRslt                                   CfprConditionRemoteInvRslt,
    cfprStorageSystemFsmStageDescr                                   SnmpAdminString,
    cfprStorageSystemFsmStamp                                        DateAndTime,
    cfprStorageSystemFsmStatus                                       SnmpAdminString,
    cfprStorageSystemFsmTry                                          Gauge32,
    cfprStorageSystemId                                              SnmpAdminString,
    cfprStorageSystemName                                            SnmpAdminString
}

cfprStorageSystemInstanceId OBJECT-TYPE
    SYNTAX       CfprManagedObjectId
    MAX-ACCESS   not-accessible
    STATUS       current
    DESCRIPTION
        "Instance identifier of the managed object."
    ::= { cfprStorageSystemEntry 1 }

cfprStorageSystemDn OBJECT-TYPE
    SYNTAX       CfprManagedObjectDn
    MAX-ACCESS   read-only
    STATUS       current
    DESCRIPTION
        "Cisco Firepower storage:System:dn managed object property"
    ::= { cfprStorageSystemEntry 2 }

cfprStorageSystemRn OBJECT-TYPE
    SYNTAX       SnmpAdminString
    MAX-ACCESS   read-only
    STATUS       current
    DESCRIPTION
        "Cisco Firepower storage:System:rn managed object property"
    ::= { cfprStorageSystemEntry 3 }

cfprStorageSystemFsmDescr OBJECT-TYPE
    SYNTAX       SnmpAdminString
    MAX-ACCESS   read-only
    STATUS       current
    DESCRIPTION
        "Cisco Firepower storage:System:fsmDescr managed object property"
    ::= { cfprStorageSystemEntry 4 }

cfprStorageSystemFsmPrev OBJECT-TYPE
    SYNTAX       SnmpAdminString
    MAX-ACCESS   read-only
    STATUS       current
    DESCRIPTION
        "Cisco Firepower storage:System:fsmPrev managed object property"
    ::= { cfprStorageSystemEntry 5 }

cfprStorageSystemFsmProgr OBJECT-TYPE
    SYNTAX       Gauge32
    MAX-ACCESS   read-only
    STATUS       current
    DESCRIPTION
        "Cisco Firepower storage:System:fsmProgr managed object property"
    ::= { cfprStorageSystemEntry 6 }

cfprStorageSystemFsmRmtInvErrCode OBJECT-TYPE
    SYNTAX       Gauge32
    MAX-ACCESS   read-only
    STATUS       current
    DESCRIPTION
        "Cisco Firepower storage:System:fsmRmtInvErrCode
        managed object property"
    ::= { cfprStorageSystemEntry 7 }

cfprStorageSystemFsmRmtInvErrDescr OBJECT-TYPE
    SYNTAX       SnmpAdminString
    MAX-ACCESS   read-only
    STATUS       current
    DESCRIPTION
        "Cisco Firepower storage:System:fsmRmtInvErrDescr
        managed object property"
    ::= { cfprStorageSystemEntry 8 }

cfprStorageSystemFsmRmtInvRslt OBJECT-TYPE
    SYNTAX       CfprConditionRemoteInvRslt
    MAX-ACCESS   read-only
    STATUS       current
    DESCRIPTION
        "Cisco Firepower storage:System:fsmRmtInvRslt managed
        object property"
    ::= { cfprStorageSystemEntry 9 }

cfprStorageSystemFsmStageDescr OBJECT-TYPE
    SYNTAX       SnmpAdminString
    MAX-ACCESS   read-only
    STATUS       current
    DESCRIPTION
        "Cisco Firepower storage:System:fsmStageDescr managed
        object property"
    ::= { cfprStorageSystemEntry 10 }

cfprStorageSystemFsmStamp OBJECT-TYPE
    SYNTAX       DateAndTime
    MAX-ACCESS   read-only
    STATUS       current
    DESCRIPTION
        "Cisco Firepower storage:System:fsmStamp managed object property"
    ::= { cfprStorageSystemEntry 11 }

cfprStorageSystemFsmStatus OBJECT-TYPE
    SYNTAX       SnmpAdminString
    MAX-ACCESS   read-only
    STATUS       current
    DESCRIPTION
        "Cisco Firepower storage:System:fsmStatus managed object property"
    ::= { cfprStorageSystemEntry 12 }

cfprStorageSystemFsmTry OBJECT-TYPE
    SYNTAX       Gauge32
    MAX-ACCESS   read-only
    STATUS       current
    DESCRIPTION
        "Cisco Firepower storage:System:fsmTry managed object property"
    ::= { cfprStorageSystemEntry 13 }

cfprStorageSystemId OBJECT-TYPE
    SYNTAX       SnmpAdminString
    MAX-ACCESS   read-only
    STATUS       current
    DESCRIPTION
        "Cisco Firepower storage:System:id managed object property"
    ::= { cfprStorageSystemEntry 14 }

cfprStorageSystemName OBJECT-TYPE
    SYNTAX       SnmpAdminString
    MAX-ACCESS   read-only
    STATUS       current
    DESCRIPTION
        "Cisco Firepower storage:System:name managed object property"
    ::= { cfprStorageSystemEntry 15 }

cfprStorageSystemFsmTable OBJECT-TYPE
    SYNTAX           SEQUENCE OF CfprStorageSystemFsmEntry
    MAX-ACCESS       not-accessible
    STATUS           current
    DESCRIPTION
        "Cisco Firepower storage:SystemFsm managed object table"
    ::= { cfprStorageObjects 37 }

cfprStorageSystemFsmEntry OBJECT-TYPE
    SYNTAX           CfprStorageSystemFsmEntry
    MAX-ACCESS       not-accessible
    STATUS           current
    DESCRIPTION
        "Entry for the cfprStorageSystemFsmTable table."
    INDEX { cfprStorageSystemFsmInstanceId }
    ::= { cfprStorageSystemFsmTable 1 }

CfprStorageSystemFsmEntry ::= SEQUENCE {
    cfprStorageSystemFsmInstanceId                                   CfprManagedObjectId,
    cfprStorageSystemFsmDn                                           CfprManagedObjectDn,
    cfprStorageSystemFsmRn                                           SnmpAdminString,
    cfprStorageSystemFsmCompletionTime                               DateAndTime,
    cfprStorageSystemFsmCurrentFsm                                   CfprStorageSystemFsmCurrentFsm,
    cfprStorageSystemFsmDescrData                                    SnmpAdminString,
    cfprStorageSystemFsmFsmStatus                                    CfprFsmFsmStageStatus,
    cfprStorageSystemFsmProgress                                     Gauge32,
    cfprStorageSystemFsmRmtErrCode                                   Gauge32,
    cfprStorageSystemFsmRmtErrDescr                                  SnmpAdminString,
    cfprStorageSystemFsmRmtRslt                                      CfprConditionRemoteInvRslt
}

cfprStorageSystemFsmInstanceId OBJECT-TYPE
    SYNTAX       CfprManagedObjectId
    MAX-ACCESS   not-accessible
    STATUS       current
    DESCRIPTION
        "Instance identifier of the managed object."
    ::= { cfprStorageSystemFsmEntry 1 }

cfprStorageSystemFsmDn OBJECT-TYPE
    SYNTAX       CfprManagedObjectDn
    MAX-ACCESS   read-only
    STATUS       current
    DESCRIPTION
        "Cisco Firepower storage:SystemFsm:dn managed object property"
    ::= { cfprStorageSystemFsmEntry 2 }

cfprStorageSystemFsmRn OBJECT-TYPE
    SYNTAX       SnmpAdminString
    MAX-ACCESS   read-only
    STATUS       current
    DESCRIPTION
        "Cisco Firepower storage:SystemFsm:rn managed object property"
    ::= { cfprStorageSystemFsmEntry 3 }

cfprStorageSystemFsmCompletionTime OBJECT-TYPE
    SYNTAX       DateAndTime
    MAX-ACCESS   read-only
    STATUS       current
    DESCRIPTION
        "Cisco Firepower storage:SystemFsm:completionTime
        managed object property"
    ::= { cfprStorageSystemFsmEntry 4 }

cfprStorageSystemFsmCurrentFsm OBJECT-TYPE
    SYNTAX       CfprStorageSystemFsmCurrentFsm
    MAX-ACCESS   read-only
    STATUS       current
    DESCRIPTION
        "Cisco Firepower storage:SystemFsm:currentFsm managed
        object property"
    ::= { cfprStorageSystemFsmEntry 5 }

cfprStorageSystemFsmDescrData OBJECT-TYPE
    SYNTAX       SnmpAdminString
    MAX-ACCESS   read-only
    STATUS       current
    DESCRIPTION
        "Cisco Firepower storage:SystemFsm:descr managed object property"
    ::= { cfprStorageSystemFsmEntry 6 }

cfprStorageSystemFsmFsmStatus OBJECT-TYPE
    SYNTAX       CfprFsmFsmStageStatus
    MAX-ACCESS   read-only
    STATUS       current
    DESCRIPTION
        "Cisco Firepower storage:SystemFsm:fsmStatus managed
        object property"
    ::= { cfprStorageSystemFsmEntry 7 }

cfprStorageSystemFsmProgress OBJECT-TYPE
    SYNTAX       Gauge32
    MAX-ACCESS   read-only
    STATUS       current
    DESCRIPTION
        "Cisco Firepower storage:SystemFsm:progress managed
        object property"
    ::= { cfprStorageSystemFsmEntry 8 }

cfprStorageSystemFsmRmtErrCode OBJECT-TYPE
    SYNTAX       Gauge32
    MAX-ACCESS   read-only
    STATUS       current
    DESCRIPTION
        "Cisco Firepower storage:SystemFsm:rmtErrCode managed
        object property"
    ::= { cfprStorageSystemFsmEntry 9 }

cfprStorageSystemFsmRmtErrDescr OBJECT-TYPE
    SYNTAX       SnmpAdminString
    MAX-ACCESS   read-only
    STATUS       current
    DESCRIPTION
        "Cisco Firepower storage:SystemFsm:rmtErrDescr
        managed object property"
    ::= { cfprStorageSystemFsmEntry 10 }

cfprStorageSystemFsmRmtRslt OBJECT-TYPE
    SYNTAX       CfprConditionRemoteInvRslt
    MAX-ACCESS   read-only
    STATUS       current
    DESCRIPTION
        "Cisco Firepower storage:SystemFsm:rmtRslt managed
        object property"
    ::= { cfprStorageSystemFsmEntry 11 }

cfprStorageSystemFsmStageTable OBJECT-TYPE
    SYNTAX           SEQUENCE OF CfprStorageSystemFsmStageEntry
    MAX-ACCESS       not-accessible
    STATUS           current
    DESCRIPTION
        "Cisco Firepower storage:SystemFsmStage managed object table"
    ::= { cfprStorageObjects 38 }

cfprStorageSystemFsmStageEntry OBJECT-TYPE
    SYNTAX           CfprStorageSystemFsmStageEntry
    MAX-ACCESS       not-accessible
    STATUS           current
    DESCRIPTION
        "Entry for the cfprStorageSystemFsmStageTable table."
    INDEX { cfprStorageSystemFsmStageInstanceId }
    ::= { cfprStorageSystemFsmStageTable 1 }

CfprStorageSystemFsmStageEntry ::= SEQUENCE {
    cfprStorageSystemFsmStageInstanceId                              CfprManagedObjectId,
    cfprStorageSystemFsmStageDn                                      CfprManagedObjectDn,
    cfprStorageSystemFsmStageRn                                      SnmpAdminString,
    cfprStorageSystemFsmStageDescrData                               SnmpAdminString,
    cfprStorageSystemFsmStageLastUpdateTime                          DateAndTime,
    cfprStorageSystemFsmStageName                                    CfprStorageSystemFsmStageName,
    cfprStorageSystemFsmStageOrder                                   Gauge32,
    cfprStorageSystemFsmStageRetry                                   Gauge32,
    cfprStorageSystemFsmStageStageStatus                             CfprFsmFsmStageStatus
}

cfprStorageSystemFsmStageInstanceId OBJECT-TYPE
    SYNTAX       CfprManagedObjectId
    MAX-ACCESS   not-accessible
    STATUS       current
    DESCRIPTION
        "Instance identifier of the managed object."
    ::= { cfprStorageSystemFsmStageEntry 1 }

cfprStorageSystemFsmStageDn OBJECT-TYPE
    SYNTAX       CfprManagedObjectDn
    MAX-ACCESS   read-only
    STATUS       current
    DESCRIPTION
        "Cisco Firepower storage:SystemFsmStage:dn managed
        object property"
    ::= { cfprStorageSystemFsmStageEntry 2 }

cfprStorageSystemFsmStageRn OBJECT-TYPE
    SYNTAX       SnmpAdminString
    MAX-ACCESS   read-only
    STATUS       current
    DESCRIPTION
        "Cisco Firepower storage:SystemFsmStage:rn managed
        object property"
    ::= { cfprStorageSystemFsmStageEntry 3 }

cfprStorageSystemFsmStageDescrData OBJECT-TYPE
    SYNTAX       SnmpAdminString
    MAX-ACCESS   read-only
    STATUS       current
    DESCRIPTION
        "Cisco Firepower storage:SystemFsmStage:descr managed
        object property"
    ::= { cfprStorageSystemFsmStageEntry 4 }

cfprStorageSystemFsmStageLastUpdateTime OBJECT-TYPE
    SYNTAX       DateAndTime
    MAX-ACCESS   read-only
    STATUS       current
    DESCRIPTION
        "Cisco Firepower storage:SystemFsmStage:lastUpdateTime
        managed object property"
    ::= { cfprStorageSystemFsmStageEntry 5 }

cfprStorageSystemFsmStageName OBJECT-TYPE
    SYNTAX       CfprStorageSystemFsmStageName
    MAX-ACCESS   read-only
    STATUS       current
    DESCRIPTION
        "Cisco Firepower storage:SystemFsmStage:name managed
        object property"
    ::= { cfprStorageSystemFsmStageEntry 6 }

cfprStorageSystemFsmStageOrder OBJECT-TYPE
    SYNTAX       Gauge32
    MAX-ACCESS   read-only
    STATUS       current
    DESCRIPTION
        "Cisco Firepower storage:SystemFsmStage:order managed
        object property"
    ::= { cfprStorageSystemFsmStageEntry 7 }

cfprStorageSystemFsmStageRetry OBJECT-TYPE
    SYNTAX       Gauge32
    MAX-ACCESS   read-only
    STATUS       current
    DESCRIPTION
        "Cisco Firepower storage:SystemFsmStage:retry managed
        object property"
    ::= { cfprStorageSystemFsmStageEntry 8 }

cfprStorageSystemFsmStageStageStatus OBJECT-TYPE
    SYNTAX       CfprFsmFsmStageStatus
    MAX-ACCESS   read-only
    STATUS       current
    DESCRIPTION
        "Cisco Firepower storage:SystemFsmStage:stageStatus
        managed object property"
    ::= { cfprStorageSystemFsmStageEntry 9 }

cfprStorageSystemFsmTaskTable OBJECT-TYPE
    SYNTAX           SEQUENCE OF CfprStorageSystemFsmTaskEntry
    MAX-ACCESS       not-accessible
    STATUS           current
    DESCRIPTION
        "Cisco Firepower storage:SystemFsmTask managed object table"
    ::= { cfprStorageObjects 39 }

cfprStorageSystemFsmTaskEntry OBJECT-TYPE
    SYNTAX           CfprStorageSystemFsmTaskEntry
    MAX-ACCESS       not-accessible
    STATUS           current
    DESCRIPTION
        "Entry for the cfprStorageSystemFsmTaskTable table."
    INDEX { cfprStorageSystemFsmTaskInstanceId }
    ::= { cfprStorageSystemFsmTaskTable 1 }

CfprStorageSystemFsmTaskEntry ::= SEQUENCE {
    cfprStorageSystemFsmTaskInstanceId                               CfprManagedObjectId,
    cfprStorageSystemFsmTaskDn                                       CfprManagedObjectDn,
    cfprStorageSystemFsmTaskRn                                       SnmpAdminString,
    cfprStorageSystemFsmTaskCompletion                               CfprFsmCompletion,
    cfprStorageSystemFsmTaskFlags                                    CfprFsmFlags,
    cfprStorageSystemFsmTaskItem                                     CfprStorageSystemFsmTaskItem,
    cfprStorageSystemFsmTaskSeqId                                    Gauge32
}

cfprStorageSystemFsmTaskInstanceId OBJECT-TYPE
    SYNTAX       CfprManagedObjectId
    MAX-ACCESS   not-accessible
    STATUS       current
    DESCRIPTION
        "Instance identifier of the managed object."
    ::= { cfprStorageSystemFsmTaskEntry 1 }

cfprStorageSystemFsmTaskDn OBJECT-TYPE
    SYNTAX       CfprManagedObjectDn
    MAX-ACCESS   read-only
    STATUS       current
    DESCRIPTION
        "Cisco Firepower storage:SystemFsmTask:dn managed object property"
    ::= { cfprStorageSystemFsmTaskEntry 2 }

cfprStorageSystemFsmTaskRn OBJECT-TYPE
    SYNTAX       SnmpAdminString
    MAX-ACCESS   read-only
    STATUS       current
    DESCRIPTION
        "Cisco Firepower storage:SystemFsmTask:rn managed object property"
    ::= { cfprStorageSystemFsmTaskEntry 3 }

cfprStorageSystemFsmTaskCompletion OBJECT-TYPE
    SYNTAX       CfprFsmCompletion
    MAX-ACCESS   read-only
    STATUS       current
    DESCRIPTION
        "Cisco Firepower storage:SystemFsmTask:completion
        managed object property"
    ::= { cfprStorageSystemFsmTaskEntry 4 }

cfprStorageSystemFsmTaskFlags OBJECT-TYPE
    SYNTAX       CfprFsmFlags
    MAX-ACCESS   read-only
    STATUS       current
    DESCRIPTION
        "Cisco Firepower storage:SystemFsmTask:flags managed
        object property"
    ::= { cfprStorageSystemFsmTaskEntry 5 }

cfprStorageSystemFsmTaskItem OBJECT-TYPE
    SYNTAX       CfprStorageSystemFsmTaskItem
    MAX-ACCESS   read-only
    STATUS       current
    DESCRIPTION
        "Cisco Firepower storage:SystemFsmTask:item managed
        object property"
    ::= { cfprStorageSystemFsmTaskEntry 6 }

cfprStorageSystemFsmTaskSeqId OBJECT-TYPE
    SYNTAX       Gauge32
    MAX-ACCESS   read-only
    STATUS       current
    DESCRIPTION
        "Cisco Firepower storage:SystemFsmTask:seqId managed
        object property"
    ::= { cfprStorageSystemFsmTaskEntry 7 }

cfprStorageTransportableFlashModuleTable OBJECT-TYPE
    SYNTAX           SEQUENCE OF CfprStorageTransportableFlashModuleEntry
    MAX-ACCESS       not-accessible
    STATUS           current
    DESCRIPTION
        "Cisco Firepower storage:TransportableFlashModule
        managed object table"
    ::= { cfprStorageObjects 40 }

cfprStorageTransportableFlashModuleEntry OBJECT-TYPE
    SYNTAX           CfprStorageTransportableFlashModuleEntry
    MAX-ACCESS       not-accessible
    STATUS           current
    DESCRIPTION
        "Entry for the cfprStorageTransportableFlashModuleTable table."
    INDEX { cfprStorageTransportableFlashModuleInstanceId }
    ::= { cfprStorageTransportableFlashModuleTable 1 }

CfprStorageTransportableFlashModuleEntry ::= SEQUENCE {
    cfprStorageTransportableFlashModuleInstanceId                    CfprManagedObjectId,
    cfprStorageTransportableFlashModuleDn                            CfprManagedObjectDn,
    cfprStorageTransportableFlashModuleRn                            SnmpAdminString,
    cfprStorageTransportableFlashModuleBlockSize                     Gauge32,
    cfprStorageTransportableFlashModuleConnectionProtocol            CfprStorageConnectionProtocol,
    cfprStorageTransportableFlashModuleId                            Gauge32,
    cfprStorageTransportableFlashModuleModel                         SnmpAdminString,
    cfprStorageTransportableFlashModuleNumberOfBlocks                Unsigned64,
    cfprStorageTransportableFlashModuleOperQualifierReason           SnmpAdminString,
    cfprStorageTransportableFlashModuleOperability                   CfprEquipmentOperability,
    cfprStorageTransportableFlashModulePresence                      CfprEquipmentPresence,
    cfprStorageTransportableFlashModuleRevision                      SnmpAdminString,
    cfprStorageTransportableFlashModuleSerial                        SnmpAdminString,
    cfprStorageTransportableFlashModuleSize                          Unsigned64,
    cfprStorageTransportableFlashModuleVendor                        SnmpAdminString
}

cfprStorageTransportableFlashModuleInstanceId OBJECT-TYPE
    SYNTAX       CfprManagedObjectId
    MAX-ACCESS   not-accessible
    STATUS       current
    DESCRIPTION
        "Instance identifier of the managed object."
    ::= { cfprStorageTransportableFlashModuleEntry 1 }

cfprStorageTransportableFlashModuleDn OBJECT-TYPE
    SYNTAX       CfprManagedObjectDn
    MAX-ACCESS   read-only
    STATUS       current
    DESCRIPTION
        "Cisco Firepower storage:TransportableFlashModule:dn
        managed object property"
    ::= { cfprStorageTransportableFlashModuleEntry 2 }

cfprStorageTransportableFlashModuleRn OBJECT-TYPE
    SYNTAX       SnmpAdminString
    MAX-ACCESS   read-only
    STATUS       current
    DESCRIPTION
        "Cisco Firepower storage:TransportableFlashModule:rn
        managed object property"
    ::= { cfprStorageTransportableFlashModuleEntry 3 }

cfprStorageTransportableFlashModuleBlockSize OBJECT-TYPE
    SYNTAX       Gauge32
    MAX-ACCESS   read-only
    STATUS       current
    DESCRIPTION
        "Cisco Firepower storage:TransportableFlashModule:blockSize
        managed object property"
    ::= { cfprStorageTransportableFlashModuleEntry 4 }

cfprStorageTransportableFlashModuleConnectionProtocol OBJECT-TYPE
    SYNTAX       CfprStorageConnectionProtocol
    MAX-ACCESS   read-only
    STATUS       current
    DESCRIPTION
        "Cisco Firepower storage:TransportableFlashModule:connectionProtoc
        ol managed object property"
    ::= { cfprStorageTransportableFlashModuleEntry 5 }

cfprStorageTransportableFlashModuleId OBJECT-TYPE
    SYNTAX       Gauge32
    MAX-ACCESS   read-only
    STATUS       current
    DESCRIPTION
        "Cisco Firepower storage:TransportableFlashModule:id
        managed object property"
    ::= { cfprStorageTransportableFlashModuleEntry 6 }

cfprStorageTransportableFlashModuleModel OBJECT-TYPE
    SYNTAX       SnmpAdminString
    MAX-ACCESS   read-only
    STATUS       current
    DESCRIPTION
        "Cisco Firepower storage:TransportableFlashModule:model
        managed object property"
    ::= { cfprStorageTransportableFlashModuleEntry 7 }

cfprStorageTransportableFlashModuleNumberOfBlocks OBJECT-TYPE
    SYNTAX       Unsigned64
    MAX-ACCESS   read-only
    STATUS       current
    DESCRIPTION
        "Cisco Firepower storage:TransportableFlashModule:numberOfBlocks
        managed object property"
    ::= { cfprStorageTransportableFlashModuleEntry 8 }

cfprStorageTransportableFlashModuleOperQualifierReason OBJECT-TYPE
    SYNTAX       SnmpAdminString
    MAX-ACCESS   read-only
    STATUS       current
    DESCRIPTION
        "Cisco Firepower storage:TransportableFlashModule:operQualifierRea
        son managed object property"
    ::= { cfprStorageTransportableFlashModuleEntry 9 }

cfprStorageTransportableFlashModuleOperability OBJECT-TYPE
    SYNTAX       CfprEquipmentOperability
    MAX-ACCESS   read-only
    STATUS       current
    DESCRIPTION
        "Cisco Firepower storage:TransportableFlashModule:operability
        managed object property"
    ::= { cfprStorageTransportableFlashModuleEntry 10 }

cfprStorageTransportableFlashModulePresence OBJECT-TYPE
    SYNTAX       CfprEquipmentPresence
    MAX-ACCESS   read-only
    STATUS       current
    DESCRIPTION
        "Cisco Firepower storage:TransportableFlashModule:presence
        managed object property"
    ::= { cfprStorageTransportableFlashModuleEntry 11 }

cfprStorageTransportableFlashModuleRevision OBJECT-TYPE
    SYNTAX       SnmpAdminString
    MAX-ACCESS   read-only
    STATUS       current
    DESCRIPTION
        "Cisco Firepower storage:TransportableFlashModule:revision
        managed object property"
    ::= { cfprStorageTransportableFlashModuleEntry 12 }

cfprStorageTransportableFlashModuleSerial OBJECT-TYPE
    SYNTAX       SnmpAdminString
    MAX-ACCESS   read-only
    STATUS       current
    DESCRIPTION
        "Cisco Firepower storage:TransportableFlashModule:serial
        managed object property"
    ::= { cfprStorageTransportableFlashModuleEntry 13 }

cfprStorageTransportableFlashModuleSize OBJECT-TYPE
    SYNTAX       Unsigned64
    MAX-ACCESS   read-only
    STATUS       current
    DESCRIPTION
        "Cisco Firepower storage:TransportableFlashModule:size
        managed object property"
    ::= { cfprStorageTransportableFlashModuleEntry 14 }

cfprStorageTransportableFlashModuleVendor OBJECT-TYPE
    SYNTAX       SnmpAdminString
    MAX-ACCESS   read-only
    STATUS       current
    DESCRIPTION
        "Cisco Firepower storage:TransportableFlashModule:vendor
        managed object property"
    ::= { cfprStorageTransportableFlashModuleEntry 15 }

cfprStorageVirtualDriveTable OBJECT-TYPE
    SYNTAX           SEQUENCE OF CfprStorageVirtualDriveEntry
    MAX-ACCESS       not-accessible
    STATUS           current
    DESCRIPTION
        "Cisco Firepower storage:VirtualDrive managed object table"
    ::= { cfprStorageObjects 41 }

cfprStorageVirtualDriveEntry OBJECT-TYPE
    SYNTAX           CfprStorageVirtualDriveEntry
    MAX-ACCESS       not-accessible
    STATUS           current
    DESCRIPTION
        "Entry for the cfprStorageVirtualDriveTable table."
    INDEX { cfprStorageVirtualDriveInstanceId }
    ::= { cfprStorageVirtualDriveTable 1 }

CfprStorageVirtualDriveEntry ::= SEQUENCE {
    cfprStorageVirtualDriveInstanceId                                CfprManagedObjectId,
    cfprStorageVirtualDriveDn                                        CfprManagedObjectDn,
    cfprStorageVirtualDriveRn                                        SnmpAdminString,
    cfprStorageVirtualDriveAccessPolicy                              CfprStorageAccessType,
    cfprStorageVirtualDriveActualWriteCachePolicy                    CfprStorageActualWriteType,
    cfprStorageVirtualDriveBlockSize                                 Gauge32,
    cfprStorageVirtualDriveBootable                                  CfprStorageBootableType,
    cfprStorageVirtualDriveConfiguredWriteCachePolicy                CfprStorageConfiguredWriteType,
    cfprStorageVirtualDriveConnectionProtocol                        CfprStorageConnectionProtocol,
    cfprStorageVirtualDriveDriveCache                                CfprStorageCacheType,
    cfprStorageVirtualDriveDriveState                                CfprStorageVDriveState,
    cfprStorageVirtualDriveId                                        Gauge32,
    cfprStorageVirtualDriveIoPolicy                                  CfprStorageIOType,
    cfprStorageVirtualDriveLc                                        CfprFsmLifecycle,
    cfprStorageVirtualDriveModel                                     SnmpAdminString,
    cfprStorageVirtualDriveNumberOfBlocks                            Unsigned64,
    cfprStorageVirtualDriveOperQualifierReason                       SnmpAdminString,
    cfprStorageVirtualDriveOperability                               CfprEquipmentOperability,
    cfprStorageVirtualDrivePresence                                  CfprEquipmentPresence,
    cfprStorageVirtualDriveReadPolicy                                CfprStorageReadType,
    cfprStorageVirtualDriveRevision                                  SnmpAdminString,
    cfprStorageVirtualDriveSerial                                    SnmpAdminString,
    cfprStorageVirtualDriveSize                                      Unsigned64,
    cfprStorageVirtualDriveStripSize                                 Unsigned64,
    cfprStorageVirtualDriveType                                      CfprStorageLunType,
    cfprStorageVirtualDriveVendor                                    SnmpAdminString
}

cfprStorageVirtualDriveInstanceId OBJECT-TYPE
    SYNTAX       CfprManagedObjectId
    MAX-ACCESS   not-accessible
    STATUS       current
    DESCRIPTION
        "Instance identifier of the managed object."
    ::= { cfprStorageVirtualDriveEntry 1 }

cfprStorageVirtualDriveDn OBJECT-TYPE
    SYNTAX       CfprManagedObjectDn
    MAX-ACCESS   read-only
    STATUS       current
    DESCRIPTION
        "Cisco Firepower storage:VirtualDrive:dn managed object property"
    ::= { cfprStorageVirtualDriveEntry 2 }

cfprStorageVirtualDriveRn OBJECT-TYPE
    SYNTAX       SnmpAdminString
    MAX-ACCESS   read-only
    STATUS       current
    DESCRIPTION
        "Cisco Firepower storage:VirtualDrive:rn managed object property"
    ::= { cfprStorageVirtualDriveEntry 3 }

cfprStorageVirtualDriveAccessPolicy OBJECT-TYPE
    SYNTAX       CfprStorageAccessType
    MAX-ACCESS   read-only
    STATUS       current
    DESCRIPTION
        "Cisco Firepower storage:VirtualDrive:accessPolicy
        managed object property"
    ::= { cfprStorageVirtualDriveEntry 4 }

cfprStorageVirtualDriveActualWriteCachePolicy OBJECT-TYPE
    SYNTAX       CfprStorageActualWriteType
    MAX-ACCESS   read-only
    STATUS       current
    DESCRIPTION
        "Cisco Firepower storage:VirtualDrive:actualWriteCachePolicy
        managed object property"
    ::= { cfprStorageVirtualDriveEntry 5 }

cfprStorageVirtualDriveBlockSize OBJECT-TYPE
    SYNTAX       Gauge32
    MAX-ACCESS   read-only
    STATUS       current
    DESCRIPTION
        "Cisco Firepower storage:VirtualDrive:blockSize
        managed object property"
    ::= { cfprStorageVirtualDriveEntry 6 }

cfprStorageVirtualDriveBootable OBJECT-TYPE
    SYNTAX       CfprStorageBootableType
    MAX-ACCESS   read-only
    STATUS       current
    DESCRIPTION
        "Cisco Firepower storage:VirtualDrive:bootable
        managed object property"
    ::= { cfprStorageVirtualDriveEntry 7 }

cfprStorageVirtualDriveConfiguredWriteCachePolicy OBJECT-TYPE
    SYNTAX       CfprStorageConfiguredWriteType
    MAX-ACCESS   read-only
    STATUS       current
    DESCRIPTION
        "Cisco Firepower storage:VirtualDrive:configuredWriteCachePolicy
        managed object property"
    ::= { cfprStorageVirtualDriveEntry 8 }

cfprStorageVirtualDriveConnectionProtocol OBJECT-TYPE
    SYNTAX       CfprStorageConnectionProtocol
    MAX-ACCESS   read-only
    STATUS       current
    DESCRIPTION
        "Cisco Firepower storage:VirtualDrive:connectionProtocol
        managed object property"
    ::= { cfprStorageVirtualDriveEntry 9 }

cfprStorageVirtualDriveDriveCache OBJECT-TYPE
    SYNTAX       CfprStorageCacheType
    MAX-ACCESS   read-only
    STATUS       current
    DESCRIPTION
        "Cisco Firepower storage:VirtualDrive:driveCache
        managed object property"
    ::= { cfprStorageVirtualDriveEntry 10 }

cfprStorageVirtualDriveDriveState OBJECT-TYPE
    SYNTAX       CfprStorageVDriveState
    MAX-ACCESS   read-only
    STATUS       current
    DESCRIPTION
        "Cisco Firepower storage:VirtualDrive:driveState
        managed object property"
    ::= { cfprStorageVirtualDriveEntry 11 }

cfprStorageVirtualDriveId OBJECT-TYPE
    SYNTAX       Gauge32
    MAX-ACCESS   read-only
    STATUS       current
    DESCRIPTION
        "Cisco Firepower storage:VirtualDrive:id managed object property"
    ::= { cfprStorageVirtualDriveEntry 12 }

cfprStorageVirtualDriveIoPolicy OBJECT-TYPE
    SYNTAX       CfprStorageIOType
    MAX-ACCESS   read-only
    STATUS       current
    DESCRIPTION
        "Cisco Firepower storage:VirtualDrive:ioPolicy
        managed object property"
    ::= { cfprStorageVirtualDriveEntry 13 }

cfprStorageVirtualDriveLc OBJECT-TYPE
    SYNTAX       CfprFsmLifecycle
    MAX-ACCESS   read-only
    STATUS       current
    DESCRIPTION
        "Cisco Firepower storage:VirtualDrive:lc managed object property"
    ::= { cfprStorageVirtualDriveEntry 14 }

cfprStorageVirtualDriveModel OBJECT-TYPE
    SYNTAX       SnmpAdminString
    MAX-ACCESS   read-only
    STATUS       current
    DESCRIPTION
        "Cisco Firepower storage:VirtualDrive:model managed
        object property"
    ::= { cfprStorageVirtualDriveEntry 15 }

cfprStorageVirtualDriveNumberOfBlocks OBJECT-TYPE
    SYNTAX       Unsigned64
    MAX-ACCESS   read-only
    STATUS       current
    DESCRIPTION
        "Cisco Firepower storage:VirtualDrive:numberOfBlocks
        managed object property"
    ::= { cfprStorageVirtualDriveEntry 16 }

cfprStorageVirtualDriveOperQualifierReason OBJECT-TYPE
    SYNTAX       SnmpAdminString
    MAX-ACCESS   read-only
    STATUS       current
    DESCRIPTION
        "Cisco Firepower storage:VirtualDrive:operQualifierReason
        managed object property"
    ::= { cfprStorageVirtualDriveEntry 17 }

cfprStorageVirtualDriveOperability OBJECT-TYPE
    SYNTAX       CfprEquipmentOperability
    MAX-ACCESS   read-only
    STATUS       current
    DESCRIPTION
        "Cisco Firepower storage:VirtualDrive:operability
        managed object property"
    ::= { cfprStorageVirtualDriveEntry 18 }

cfprStorageVirtualDrivePresence OBJECT-TYPE
    SYNTAX       CfprEquipmentPresence
    MAX-ACCESS   read-only
    STATUS       current
    DESCRIPTION
        "Cisco Firepower storage:VirtualDrive:presence
        managed object property"
    ::= { cfprStorageVirtualDriveEntry 19 }

cfprStorageVirtualDriveReadPolicy OBJECT-TYPE
    SYNTAX       CfprStorageReadType
    MAX-ACCESS   read-only
    STATUS       current
    DESCRIPTION
        "Cisco Firepower storage:VirtualDrive:readPolicy
        managed object property"
    ::= { cfprStorageVirtualDriveEntry 20 }

cfprStorageVirtualDriveRevision OBJECT-TYPE
    SYNTAX       SnmpAdminString
    MAX-ACCESS   read-only
    STATUS       current
    DESCRIPTION
        "Cisco Firepower storage:VirtualDrive:revision
        managed object property"
    ::= { cfprStorageVirtualDriveEntry 21 }

cfprStorageVirtualDriveSerial OBJECT-TYPE
    SYNTAX       SnmpAdminString
    MAX-ACCESS   read-only
    STATUS       current
    DESCRIPTION
        "Cisco Firepower storage:VirtualDrive:serial managed
        object property"
    ::= { cfprStorageVirtualDriveEntry 22 }

cfprStorageVirtualDriveSize OBJECT-TYPE
    SYNTAX       Unsigned64
    MAX-ACCESS   read-only
    STATUS       current
    DESCRIPTION
        "Cisco Firepower storage:VirtualDrive:size managed
        object property"
    ::= { cfprStorageVirtualDriveEntry 23 }

cfprStorageVirtualDriveStripSize OBJECT-TYPE
    SYNTAX       Unsigned64
    MAX-ACCESS   read-only
    STATUS       current
    DESCRIPTION
        "Cisco Firepower storage:VirtualDrive:stripSize
        managed object property"
    ::= { cfprStorageVirtualDriveEntry 24 }

cfprStorageVirtualDriveType OBJECT-TYPE
    SYNTAX       CfprStorageLunType
    MAX-ACCESS   read-only
    STATUS       current
    DESCRIPTION
        "Cisco Firepower storage:VirtualDrive:type managed
        object property"
    ::= { cfprStorageVirtualDriveEntry 25 }

cfprStorageVirtualDriveVendor OBJECT-TYPE
    SYNTAX       SnmpAdminString
    MAX-ACCESS   read-only
    STATUS       current
    DESCRIPTION
        "Cisco Firepower storage:VirtualDrive:vendor managed
        object property"
    ::= { cfprStorageVirtualDriveEntry 26 }

cfprStorageVsanRefTable OBJECT-TYPE
    SYNTAX           SEQUENCE OF CfprStorageVsanRefEntry
    MAX-ACCESS       not-accessible
    STATUS           current
    DESCRIPTION
        "Cisco Firepower storage:VsanRef managed object table"
    ::= { cfprStorageObjects 42 }

cfprStorageVsanRefEntry OBJECT-TYPE
    SYNTAX           CfprStorageVsanRefEntry
    MAX-ACCESS       not-accessible
    STATUS           current
    DESCRIPTION
        "Entry for the cfprStorageVsanRefTable table."
    INDEX { cfprStorageVsanRefInstanceId }
    ::= { cfprStorageVsanRefTable 1 }

CfprStorageVsanRefEntry ::= SEQUENCE {
    cfprStorageVsanRefInstanceId                                     CfprManagedObjectId,
    cfprStorageVsanRefDn                                             CfprManagedObjectDn,
    cfprStorageVsanRefRn                                             SnmpAdminString,
    cfprStorageVsanRefConfigQualifier                                CfprVnicConfigIssues,
    cfprStorageVsanRefName                                           SnmpAdminString,
    cfprStorageVsanRefOperVnetDn                                     SnmpAdminString,
    cfprStorageVsanRefOperVnetName                                   SnmpAdminString,
    cfprStorageVsanRefSwitchId                                       CfprStorageVsanRefSwitchId,
    cfprStorageVsanRefVnet                                           Gauge32,
    cfprStorageVsanRefZoningState                                    CfprFabricZoningState
}

cfprStorageVsanRefInstanceId OBJECT-TYPE
    SYNTAX       CfprManagedObjectId
    MAX-ACCESS   not-accessible
    STATUS       current
    DESCRIPTION
        "Instance identifier of the managed object."
    ::= { cfprStorageVsanRefEntry 1 }

cfprStorageVsanRefDn OBJECT-TYPE
    SYNTAX       CfprManagedObjectDn
    MAX-ACCESS   read-only
    STATUS       current
    DESCRIPTION
        "Cisco Firepower storage:VsanRef:dn managed object property"
    ::= { cfprStorageVsanRefEntry 2 }

cfprStorageVsanRefRn OBJECT-TYPE
    SYNTAX       SnmpAdminString
    MAX-ACCESS   read-only
    STATUS       current
    DESCRIPTION
        "Cisco Firepower storage:VsanRef:rn managed object property"
    ::= { cfprStorageVsanRefEntry 3 }

cfprStorageVsanRefConfigQualifier OBJECT-TYPE
    SYNTAX       CfprVnicConfigIssues
    MAX-ACCESS   read-only
    STATUS       current
    DESCRIPTION
        "Cisco Firepower storage:VsanRef:configQualifier
        managed object property"
    ::= { cfprStorageVsanRefEntry 4 }

cfprStorageVsanRefName OBJECT-TYPE
    SYNTAX       SnmpAdminString
    MAX-ACCESS   read-only
    STATUS       current
    DESCRIPTION
        "Cisco Firepower storage:VsanRef:name managed object property"
    ::= { cfprStorageVsanRefEntry 5 }

cfprStorageVsanRefOperVnetDn OBJECT-TYPE
    SYNTAX       SnmpAdminString
    MAX-ACCESS   read-only
    STATUS       current
    DESCRIPTION
        "Cisco Firepower storage:VsanRef:operVnetDn managed
        object property"
    ::= { cfprStorageVsanRefEntry 6 }

cfprStorageVsanRefOperVnetName OBJECT-TYPE
    SYNTAX       SnmpAdminString
    MAX-ACCESS   read-only
    STATUS       current
    DESCRIPTION
        "Cisco Firepower storage:VsanRef:operVnetName managed
        object property"
    ::= { cfprStorageVsanRefEntry 7 }

cfprStorageVsanRefSwitchId OBJECT-TYPE
    SYNTAX       CfprStorageVsanRefSwitchId
    MAX-ACCESS   read-only
    STATUS       current
    DESCRIPTION
        "Cisco Firepower storage:VsanRef:switchId managed object property"
    ::= { cfprStorageVsanRefEntry 8 }

cfprStorageVsanRefVnet OBJECT-TYPE
    SYNTAX       Gauge32
    MAX-ACCESS   read-only
    STATUS       current
    DESCRIPTION
        "Cisco Firepower storage:VsanRef:vnet managed object property"
    ::= { cfprStorageVsanRefEntry 9 }

cfprStorageVsanRefZoningState OBJECT-TYPE
    SYNTAX       CfprFabricZoningState
    MAX-ACCESS   read-only
    STATUS       current
    DESCRIPTION
        "Cisco Firepower storage:VsanRef:zoningState managed
        object property"
    ::= { cfprStorageVsanRefEntry 10 }

END
