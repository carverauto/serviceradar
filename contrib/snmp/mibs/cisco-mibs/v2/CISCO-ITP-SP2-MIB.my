-- *****************************************************************   
-- CISCO-ITP-SP2-MIB: MIB for SS7 Signaling Point - Additional 
--                    Information
--
-- February 2002, John Linton, Shekhar Acharya
--
-- Copyright (c) 2001-2002 by Cisco Systems, Inc.
-- All rights reserved.
-- *****************************************************************
--
-- *****************************************************************
CISCO-ITP-SP2-MIB DEFINITIONS ::= BEGIN

IMPORTS
        CItpTcAclId
                FROM CISCO-ITP-TC-MIB
       
        ciscoMgmt
                FROM CISCO-SMI
                        
        SnmpAdminString
                FROM SNMP-FRAMEWORK-MIB
                
        MODULE-COMPLIANCE,
        OBJECT-GROUP
                FROM SNMPv2-CONF

        RowStatus,
        TEXTUAL-CONVENTION
                FROM SNMPv2-TC
                
        Counter32,
        Integer32,
        Unsigned32,
        MODULE-IDENTITY,
        OBJECT-TYPE
                FROM SNMPv2-SMI;
                
ciscoItpSp2MIB MODULE-IDENTITY
        LAST-UPDATED    "200209160000Z"
        ORGANIZATION    "Cisco Systems, Inc."
        CONTACT-INFO
                "       Cisco Systems, Inc
                        Customer Service

                Postal: 170 W. Tasman Drive
                        San Jose, CA  95134
                        USA

                   Tel: +1 800 553-NETS

                E-mail: cs-ss7@cisco.com"
        DESCRIPTION
               "The MIB for providing information specified
                in ITU Q752 Monitoring and Measurements for
                Signaling System No. 7(SS7) Network. 
                This information can be used to manage messages
                transported over SS7 Network via Cisco IP 
                Transfer Point.  
                
                The Cisco IP Transfer Point (ITP) is a hardware 
                and software solution that transports SS7 traffic 
                using IP. Each ITP node provides function similar
                to SS7 signaling point.   
                
                The relevant ITU documents describing this technology
                is the ITU Q series, including ITU Q.700: Introduction
                to CCITT Signaling System No. 7 and ITU Q.701 
                Functional description of the message transfer part
                (MTP) of Signaling System No. 7.

                The ITP Quality of Service (QoS) model allows the
                definition of 8 QoS classes, 0 through 7.
                QoS classes can be assigned only SCTP links.
                Only one QoS class can be assigned to an SCTP link.
                Class 0 will be designated as the default class.
                Packets that are not classified to a designated QoS
                class will get assigned to the default class. Each
                provisioned QoS class can be assigned an IP precedence
                value or a Differential Services Code Point (DSCP).
                The default  class is initialized to IP precedence
                zero (0). The default class initial TOS setting can
                be changed through the command line interface. The
                Type of Service (TOS) byte in the IP header will be
                set to the IP precedence or DSCP that is assigned to
                class. Every packet forwarded over an SCTP link that
                was provisioned for a given QoS class will have the
                TOS byte set.
                "

        REVISION        "200209160000Z"
        DESCRIPTION
                "The ability to allow multiple instances of 
                 Signalling Points to run in the same device
                 has introduce a new index structure.  All
                 objects in this MIB will be deprecated and 
                 replaced by objects in the CISCO-ITP-GSP2-MIB.my
                 MIB."
                 
        REVISION        "200202210000Z"
        DESCRIPTION
                "Initial version of this MIB module."
        ::= { ciscoMgmt 248 } 
        
-- Top-level structure of the MIB
ciscoItpSp2MIBNotifications OBJECT IDENTIFIER ::= { ciscoItpSp2MIB 0 }
ciscoItpSp2MIBObjects       OBJECT IDENTIFIER ::= { ciscoItpSp2MIB 1 }

cisEvents  OBJECT IDENTIFIER ::= { ciscoItpSp2MIBObjects 1 }
cisQos     OBJECT IDENTIFIER ::= { ciscoItpSp2MIBObjects 2 }

-- *************************************************************
-- *                                                           *
-- * Textual Conventions                                       *
-- *                                                           *
-- *************************************************************

CisTcQosClass ::= TEXTUAL-CONVENTION
        STATUS          deprecated
        DESCRIPTION
            "The quality of service classification to be assigned 
             to the IP packets used to transport the SS7 messages.
             Zero is a special value and is reserved to carry all
             traffic that does not specify a Qos or when exact 
             match of the specified Qos is not available."
        SYNTAX Unsigned32 (0..7) 

-- *************************************************************
-- *                                                           *
-- * Events                                                    *
-- *                                                           *
-- *************************************************************
cisEventSummryLoggedEvents OBJECT-TYPE
        SYNTAX           Counter32
        MAX-ACCESS       read-only
        STATUS           deprecated
        DESCRIPTION
            "The number of SS7 events logged by this 
             Signaling Point."
        ::= { cisEvents  1 }
    
cisEventSummryDroppedEvents OBJECT-TYPE
        SYNTAX           Counter32
        MAX-ACCESS       read-only
        STATUS           deprecated
        DESCRIPTION
            "The number of SS7 events that could not be logged
             due to unavailable resources."
        ::= { cisEvents  2 }
    
cisEventHistoryMaxEntries OBJECT-TYPE
        SYNTAX           Unsigned32 (0..65535)
        MAX-ACCESS       read-write
        STATUS           deprecated
        DESCRIPTION
            "The upper limit on the number of events that the
             cisEventsTable can contain. A value of 0 will 
             prevent any history from being retained. When this
             table is full, the oldest entry will be deleted and
             a new one will be created."
        ::= { cisEvents  3 }

cisEventHistoryTableEntAllowed OBJECT-TYPE
        SYNTAX           Unsigned32 (0..65535)
        MAX-ACCESS       read-only
        STATUS           deprecated
        DESCRIPTION
                "This object specifies the maximum number of events
                 allowed in the events history table for the managed
                 system."
        ::= { cisEvents  4 }
    
cisEventHistoryTable     OBJECT-TYPE
        SYNTAX           SEQUENCE OF CisEventHistoryTableEntry
        MAX-ACCESS       not-accessible
        STATUS           deprecated
        DESCRIPTION
            "A table of SS7 events generated by this device."
        ::= { cisEvents 5 }

cisEventHistoryTableEntry OBJECT-TYPE
        SYNTAX           CisEventHistoryTableEntry
        MAX-ACCESS       not-accessible
        STATUS           deprecated
        DESCRIPTION
            "An SS7 event that was previously generated by this
             device. Each entry is indexed by a event index.

             An entry is added to this table for each SS7 event
             generated on the managed system. The table contains
             the latest number of events defined by the 
             cisEventHistoryMaxEntries object.

             Once the table is full, the oldest entry is removed
             and a new entry is created to accommodate the new event."
        INDEX   { cisEventHistoryIndex }
        ::= { cisEventHistoryTable 1 }

CisEventHistoryTableEntry  ::= SEQUENCE {
        cisEventHistoryIndex   Unsigned32,
        cisEventHistoryDescr   SnmpAdminString
    }

cisEventHistoryIndex     OBJECT-TYPE
        SYNTAX           Unsigned32 (1..2147483647)
        MAX-ACCESS       not-accessible
        STATUS           deprecated
        DESCRIPTION
            "A monotonically increasing integer for the sole
             purpose of indexing events.  When it reaches the
             maximum value the agent flushes the event table 
             and wraps the value back to 1."
        ::= { cisEventHistoryTableEntry 1 }

cisEventHistoryDescr     OBJECT-TYPE
        SYNTAX           SnmpAdminString (SIZE (1..255) )
        MAX-ACCESS       read-only
        STATUS           deprecated
        DESCRIPTION
            "A brief description of the SS7 event. Each event
             provides information of state transitions specific to
             the SS7 protocol."
        ::= { cisEventHistoryTableEntry 2 }
    
--  *************************************************************
--  *                                                           *
--  * Quality of Service                                        *
--  *                                                           *
--  *************************************************************
cisQosTable              OBJECT-TYPE
        SYNTAX           SEQUENCE OF CisQosTableEntry
        MAX-ACCESS       not-accessible
        STATUS           deprecated
        DESCRIPTION
            "A table of information related to the defining
             Quality of Service to transport SS7 packets using
             SCTP/IP.
             
             Entries are added to this table via 
             cisQosRowStatus in accordance with the 
             RowStatusconvention."
        ::= { cisQos 1 }

cisQosTableEntry OBJECT-TYPE
        SYNTAX           CisQosTableEntry
        MAX-ACCESS       not-accessible
        STATUS           deprecated
        DESCRIPTION
            "Each entry define information relate to a Quality
             of Service class as needed to transport SS7 packets 
             using SCTP/IP."
        INDEX   { cisQosClass }
        ::= { cisQosTable 1 }

CisQosTableEntry         ::= SEQUENCE {
        cisQosClass            CisTcQosClass,
        cisQosType             INTEGER,
        cisQosPrecedenceValue  Integer32,
        cisQosIpDscp           Integer32,
        cisQosAclId            CItpTcAclId,
        cisQosRowStatus        RowStatus 
    }

cisQosClass              OBJECT-TYPE
        SYNTAX           CisTcQosClass
        MAX-ACCESS       not-accessible
        STATUS           deprecated
        DESCRIPTION
            "The quality of service class that can be defined to
             transport SS7 Packets using SCTP/IP."
        ::= { cisQosTableEntry 1 }
    
cisQosType               OBJECT-TYPE
        SYNTAX           INTEGER {
                           ipPrecedence(1),
                           ipDscp(2)
                         }
        MAX-ACCESS       read-create
        STATUS           deprecated
        DESCRIPTION
            "Enumerated list of QoS type that can be defined.
             A value ipPrecedence suggests that IP Type of     
             Service (TOS) is based on cisQosPrecedenceValue.
             A value ipDscp suggests that IP Type of Service
             (TOS) is based on cisQosIpDscp."
        ::= { cisQosTableEntry 2 }

cisQosPrecedenceValue    OBJECT-TYPE
        SYNTAX           Integer32 (-1..7)
        MAX-ACCESS       read-create
        STATUS           deprecated
        DESCRIPTION
            "A value to assign to the IP TOS  bits in the 
             IP datagram that carries one or more SS7 packets.

             The IP Precedence value is specified if
             cisQosType is ipPrecedence, otherwise it is -1."
        ::= { cisQosTableEntry 3 }

cisQosIpDscp             OBJECT-TYPE
        SYNTAX           Integer32 (-1..63)
        MAX-ACCESS       read-create
        STATUS           deprecated
        DESCRIPTION
            "DiffServ CodePoint (DSCP) value to assign to the IP
             TOS bits in the IP datagram that carries one or more
             SS7 packets.

             DSCP provides scalable mechanisms to classify packets
             into groups or classes that have similar QoS
             requirements and then gives these groups the required
             treatment at every hop in the network. 

             The DSCP value is specified if cisQosType
             is ipDscp, otherwise it is -1."
        REFERENCE
           "Differentiated Services is described and defined in the
            RFCs: 2474, 2475, 2597, and 2598."
        ::= { cisQosTableEntry 4 }

cisQosAclId              OBJECT-TYPE
        SYNTAX           CItpTcAclId 
        MAX-ACCESS       read-create
        STATUS           deprecated
        DESCRIPTION
            "ITP Access lists can be used to use information
             specific to SS7 packets to assign an Qos class.
             A value of zero indicates that no access control
             list is present."
        DEFVAL { 0 }
        ::= { cisQosTableEntry 5 }
    
cisQosRowStatus         OBJECT-TYPE
    SYNTAX              RowStatus
    MAX-ACCESS          read-create
    STATUS              deprecated
    DESCRIPTION
        "The object is used by a management station to 
         create or delete the row entry in cisQosTable  
         following the RowStatus textual convention."
        ::= { cisQosTableEntry 6 }
        
-- *************************************************************
-- *                                                           *
-- * Notifications                                             *
-- *                                                           *
-- *************************************************************


-- *************************************************************
-- *                                                           *
-- * Conformance Information                                   *
-- *                                                           *
-- *************************************************************
ciscoItpSp2MIBConformance OBJECT IDENTIFIER ::= { ciscoItpSp2MIB 2 }
ciscoItpSp2MIBCompliances OBJECT IDENTIFIER ::=
        { ciscoItpSp2MIBConformance 1 }
ciscoItpSp2MIBGroups      OBJECT IDENTIFIER ::=
        { ciscoItpSp2MIBConformance 2 }

-- ********************************************************************
-- Compliance Statements
-- ********************************************************************
ciscoItpSp2MIBCompliance MODULE-COMPLIANCE
        STATUS deprecated
        DESCRIPTION
            "The compliance statement for entities which implement
             the Cisco Signaling Point2 MIB"
        MODULE -- this module
            MANDATORY-GROUPS {
                              ciscoItpSp2EventsGroup, 
                              ciscoItpSp2QosGroup   
                             }
                             
        OBJECT           cisEventHistoryMaxEntries
        MIN-ACCESS       read-only
        DESCRIPTION      "Write access is not required."
        
        OBJECT           cisQosType
        MIN-ACCESS       read-only
        DESCRIPTION      "Create/Write access is not required."
        
        OBJECT           cisQosPrecedenceValue
        MIN-ACCESS       read-only
        DESCRIPTION      "Create/Write access is not required."
        
        OBJECT           cisQosIpDscp
        MIN-ACCESS       read-only
        DESCRIPTION      "Create/Write access is not required."
        
        OBJECT           cisQosAclId
        MIN-ACCESS       read-only
        DESCRIPTION      "Create/Write access is not required."
        
        OBJECT           cisQosRowStatus   
        MIN-ACCESS       read-only
        DESCRIPTION      "Create/Write access is not required."
        
        ::= { ciscoItpSp2MIBCompliances 1 }

-- ********************************************************************
-- Units of Conformance
-- ********************************************************************
ciscoItpSp2EventsGroup OBJECT-GROUP       
        OBJECTS { 
              cisEventSummryLoggedEvents,
              cisEventSummryDroppedEvents,
              cisEventHistoryMaxEntries,
              cisEventHistoryTableEntAllowed,
              cisEventHistoryDescr
        }
        STATUS deprecated
        DESCRIPTION
              "SS7 Event objects."
        ::= { ciscoItpSp2MIBGroups 1 }
    
ciscoItpSp2QosGroup OBJECT-GROUP       
        OBJECTS {
              cisQosType,
              cisQosPrecedenceValue,
              cisQosIpDscp,
              cisQosAclId,
              cisQosRowStatus 
        }
        STATUS deprecated
        DESCRIPTION
              "SS7 Quality of Service objects."
        ::= { ciscoItpSp2MIBGroups 2 }
    
END
