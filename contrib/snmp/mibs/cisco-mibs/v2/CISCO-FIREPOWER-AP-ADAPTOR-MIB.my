-- *********************************************************************
-- CISCO-FIREPOWER-AP-ADAPTOR-MIB.my
-- 
-- MIB representation of the Cisco Firepower
-- ADAPTOR management information model package
-- 
-- Created January 2023 by Charles Bullis
-- 
-- Copyright (c) 2005-2023 Cisco Systems, Inc. All rights reserved.
-- 
-- *********************************************************************

CISCO-FIREPOWER-AP-ADAPTOR-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerApMIBObjects,
    CfprApManagedObjectId,
    CfprApManagedObjectDn
        FROM CISCO-FIREPOWER-AP-MIB
    CfprApAdaptorAdapterStatsTrafficDir,
    CfprApAdaptorAdminPowerState,
    CfprApAdaptorCIoEpIfType,
    CfprApAdaptorCapDefFwVersionOpr,
    CfprApAdaptorCapDefType,
    CfprApAdaptorCapSpecType,
    CfprApAdaptorDefaultAction,
    CfprApAdaptorEthArfsProfileAccelaratedRFS,
    CfprApAdaptorEthInterruptProfileCoalescingType,
    CfprApAdaptorEthNVGREProfileAdminState,
    CfprApAdaptorEthOffloadProfileLargeReceive,
    CfprApAdaptorEthOffloadProfileTcpRxChecksum,
    CfprApAdaptorEthOffloadProfileTcpSegment,
    CfprApAdaptorEthOffloadProfileTcpTxChecksum,
    CfprApAdaptorEthPortBySizeLargeStatsHistThresholded,
    CfprApAdaptorEthPortBySizeLargeStatsThresholded,
    CfprApAdaptorEthPortBySizeSmallStatsHistThresholded,
    CfprApAdaptorEthPortBySizeSmallStatsThresholded,
    CfprApAdaptorEthPortErrStatsHistThresholded,
    CfprApAdaptorEthPortErrStatsThresholded,
    CfprApAdaptorEthPortMcastStatsHistThresholded,
    CfprApAdaptorEthPortMcastStatsThresholded,
    CfprApAdaptorEthPortOutsizedStatsHistThresholded,
    CfprApAdaptorEthPortOutsizedStatsThresholded,
    CfprApAdaptorEthPortStatsHistThresholded,
    CfprApAdaptorEthPortStatsThresholded,
    CfprApAdaptorEthRoCEProfileAdminState,
    CfprApAdaptorEthVxLANProfileAdminState,
    CfprApAdaptorEtherIfStatsHistThresholded,
    CfprApAdaptorEtherIfStatsThresholded,
    CfprApAdaptorExtEthIfFsmCurrentFsm,
    CfprApAdaptorExtEthIfFsmStageName,
    CfprApAdaptorExtEthIfFsmTaskItem,
    CfprApAdaptorExtEthIfPcEpPortId,
    CfprApAdaptorExtEthIfPcEpSlotId,
    CfprApAdaptorExtEthIfPcPortId,
    CfprApAdaptorExtEthIfPcTransport,
    CfprApAdaptorExtIfAdminState,
    CfprApAdaptorExtIfEpIfRole,
    CfprApAdaptorExtIfEpType,
    CfprApAdaptorExtIfPcIfRole,
    CfprApAdaptorExtIfPcType,
    CfprApAdaptorExtIpV6RssHashProfileIpHash,
    CfprApAdaptorExtIpV6RssHashProfileTcpHash,
    CfprApAdaptorExternalEpLocale,
    CfprApAdaptorExternalPcLocale,
    CfprApAdaptorFcIfEventStatsHistThresholded,
    CfprApAdaptorFcIfEventStatsThresholded,
    CfprApAdaptorFcIfFC4StatsHistThresholded,
    CfprApAdaptorFcIfFC4StatsThresholded,
    CfprApAdaptorFcIfFrameStatsHistThresholded,
    CfprApAdaptorFcIfFrameStatsThresholded,
    CfprApAdaptorFcPortStatsHistThresholded,
    CfprApAdaptorFcPortStatsThresholded,
    CfprApAdaptorHostEthIfFsmCurrentFsm,
    CfprApAdaptorHostEthIfFsmStageName,
    CfprApAdaptorHostEthIfFsmTaskItem,
    CfprApAdaptorHostEthIfHostPort,
    CfprApAdaptorHostFcIfAdminState,
    CfprApAdaptorHostFcIfFsmCurrentFsm,
    CfprApAdaptorHostFcIfFsmStageName,
    CfprApAdaptorHostFcIfFsmTaskItem,
    CfprApAdaptorHostFcIfHostPort,
    CfprApAdaptorHostFcIfPersBind,
    CfprApAdaptorHostIfAdminState,
    CfprApAdaptorHostIfBootDev,
    CfprApAdaptorHostMgmtCapPreboot,
    CfprApAdaptorHostMgmtCapPresence,
    CfprApAdaptorHostPortId,
    CfprApAdaptorHostServiceEthIfIfRole,
    CfprApAdaptorHostVisibility,
    CfprApAdaptorIScsiCapBootOrderType,
    CfprApAdaptorInterruptMode,
    CfprApAdaptorIpV4RssHashProfileIpHash,
    CfprApAdaptorIpV4RssHashProfileTcpHash,
    CfprApAdaptorIpV6RssHashProfileIpHash,
    CfprApAdaptorIpV6RssHashProfileTcpHash,
    CfprApAdaptorIscsiProtConnectionTimeOut,
    CfprApAdaptorIscsiProtDhcpTimeOut,
    CfprApAdaptorIscsiProtLunBusyRetryCount,
    CfprApAdaptorLanCapDefaultVlan,
    CfprApAdaptorLinkState,
    CfprApAdaptorLldpCapSupport,
    CfprApAdaptorMenloBaseErrorStatsHistThresholded,
    CfprApAdaptorMenloBaseErrorStatsThresholded,
    CfprApAdaptorMenloDcePortStatsHistThresholded,
    CfprApAdaptorMenloDcePortStatsThresholded,
    CfprApAdaptorMenloEthErrorStatsHistThresholded,
    CfprApAdaptorMenloEthErrorStatsThresholded,
    CfprApAdaptorMenloEthStatsHistThresholded,
    CfprApAdaptorMenloEthStatsThresholded,
    CfprApAdaptorMenloFcErrorStatsHistThresholded,
    CfprApAdaptorMenloFcErrorStatsThresholded,
    CfprApAdaptorMenloFcStatsHistThresholded,
    CfprApAdaptorMenloFcStatsThresholded,
    CfprApAdaptorMenloHostPortStatsHistThresholded,
    CfprApAdaptorMenloHostPortStatsThresholded,
    CfprApAdaptorMenloMcpuErrorStatsHistThresholded,
    CfprApAdaptorMenloMcpuErrorStatsThresholded,
    CfprApAdaptorMenloMcpuStatsHistThresholded,
    CfprApAdaptorMenloMcpuStatsThresholded,
    CfprApAdaptorMenloNetEgStatsHistThresholded,
    CfprApAdaptorMenloNetEgStatsThresholded,
    CfprApAdaptorMenloNetInStatsHistThresholded,
    CfprApAdaptorMenloNetInStatsThresholded,
    CfprApAdaptorMenloQErrorStatsHistThresholded,
    CfprApAdaptorMenloQErrorStatsThresholded,
    CfprApAdaptorMenloQStatsHistThresholded,
    CfprApAdaptorMenloQStatsThresholded,
    CfprApAdaptorMenloQueueStatsComponent,
    CfprApAdaptorMenloStatsIndex,
    CfprApAdaptorMgmtCapMode,
    CfprApAdaptorMgmtCapOperPowerRequirement,
    CfprApAdaptorMgmtCapRebootActionOnDestructive,
    CfprApAdaptorNwMgmtCapApi,
    CfprApAdaptorNwMgmtCapMgmtTransport,
    CfprApAdaptorOffloadMethod,
    CfprApAdaptorPIoEpIfType,
    CfprApAdaptorPurpose,
    CfprApAdaptorReachability,
    CfprApAdaptorRssProfileReceiveSideScaling,
    CfprApAdaptorSanCapHostNvram,
    CfprApAdaptorServiceState,
    CfprApAdaptorUnitExtnId,
    CfprApAdaptorUnitId,
    CfprApAdaptorVnicStatsHistThresholded,
    CfprApAdaptorVnicStatsThresholded,
    CfprApAddressType,
    CfprApConditionRemoteInvRslt,
    CfprApEquipmentConnectionStatus,
    CfprApEquipmentOperability,
    CfprApEquipmentPowerState,
    CfprApEquipmentPresence,
    CfprApEquipmentSensorThresholdStatus,
    CfprApEtherSatelliteConnectionDisc,
    CfprApFabricAVlanAssocPrimaryVlanSwitchId,
    CfprApFabricAVlanSharing,
    CfprApFabricAVlanTransport,
    CfprApFabricAVlanType,
    CfprApFabricAVsanTransport,
    CfprApFabricAVsanType,
    CfprApFabricEpVlanVlanType,
    CfprApFabricMembershipStatus,
    CfprApFabricVlanAssocPrimaryVlanState,
    CfprApFabricVlanOperState,
    CfprApFabricVlanOverlapState,
    CfprApFabricVnetEpIfRole,
    CfprApFabricVnetEpLocale,
    CfprApFabricVnetEpPolicyOwner,
    CfprApFabricVsanOperState,
    CfprApFabricZoningState,
    CfprApFsmCompletion,
    CfprApFsmFlags,
    CfprApFsmFsmStageStatus,
    CfprApFsmLifecycle,
    CfprApNetworkConnectionType,
    CfprApNetworkLocale,
    CfprApNetworkPhysEpIfType,
    CfprApNetworkPortOperState,
    CfprApNetworkPortRole,
    CfprApNetworkSide,
    CfprApNetworkSwitchId,
    CfprApNetworkTransport,
    CfprApNetworkVnetEpIfType,
    CfprApPolicyPolicyOwner,
    CfprApPortEthSpeed,
    CfprApVnicVirtualizationPreferenceType
        FROM CISCO-FIREPOWER-AP-TC-MIB;

cfprApAdaptorObjects MODULE-IDENTITY
    LAST-UPDATED    "202301250000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        ADAPTOR management information model package"
    ::= { ciscoFirepowerApMIBObjects 3 }

cfprApAdaptorCapQualTable OBJECT-TYPE
    SYNTAX           SEQUENCE OF CfprApAdaptorCapQualEntry
    MAX-ACCESS       not-accessible
    STATUS           current
    DESCRIPTION
        "Cisco Firepower adaptor:CapQual managed object table"
    ::= { cfprApAdaptorObjects 1 }

cfprApAdaptorCapQualEntry OBJECT-TYPE
    SYNTAX           CfprApAdaptorCapQualEntry
    MAX-ACCESS       not-accessible
    STATUS           current
    DESCRIPTION
        "Entry for the cfprApAdaptorCapQualTable table."
    INDEX { cfprApAdaptorCapQualInstanceId }
    ::= { cfprApAdaptorCapQualTable 1 }

CfprApAdaptorCapQualEntry ::= SEQUENCE {
    cfprApAdaptorCapQualInstanceId                                   CfprApManagedObjectId,
    cfprApAdaptorCapQualDn                                           CfprApManagedObjectDn,
    cfprApAdaptorCapQualRn                                           SnmpAdminString,
    cfprApAdaptorCapQualFwVersionHi                                  SnmpAdminString,
    cfprApAdaptorCapQualFwVersionLo                                  SnmpAdminString,
    cfprApAdaptorCapQualFwVersionOpr                                 CfprApAdaptorCapDefFwVersionOpr,
    cfprApAdaptorCapQualMaximum                                      Gauge32,
    cfprApAdaptorCapQualModel                                        SnmpAdminString,
    cfprApAdaptorCapQualType                                         CfprApAdaptorCapDefType
}

cfprApAdaptorCapQualInstanceId OBJECT-TYPE
    SYNTAX       CfprApManagedObjectId
    MAX-ACCESS   not-accessible
    STATUS       current
    DESCRIPTION
        "Instance identifier of the managed object."
    ::= { cfprApAdaptorCapQualEntry 1 }

cfprApAdaptorCapQualDn OBJECT-TYPE
    SYNTAX       CfprApManagedObjectDn
    MAX-ACCESS   read-only
    STATUS       current
    DESCRIPTION
        "Cisco Firepower adaptor:CapQual:dn managed object property"
    ::= { cfprApAdaptorCapQualEntry 2 }

cfprApAdaptorCapQualRn OBJECT-TYPE
    SYNTAX       SnmpAdminString
    MAX-ACCESS   read-only
    STATUS       current
    DESCRIPTION
        "Cisco Firepower adaptor:CapQual:rn managed object property"
    ::= { cfprApAdaptorCapQualEntry 3 }

cfprApAdaptorCapQualFwVersionHi OBJECT-TYPE
    SYNTAX       SnmpAdminString
    MAX-ACCESS   read-only
    STATUS       current
    DESCRIPTION
        "Cisco Firepower adaptor:CapQual:fwVersionHi managed
        object property"
    ::= { cfprApAdaptorCapQualEntry 4 }

cfprApAdaptorCapQualFwVersionLo OBJECT-TYPE
    SYNTAX       SnmpAdminString
    MAX-ACCESS   read-only
    STATUS       current
    DESCRIPTION
        "Cisco Firepower adaptor:CapQual:fwVersionLo managed
        object property"
    ::= { cfprApAdaptorCapQualEntry 5 }

cfprApAdaptorCapQualFwVersionOpr OBJECT-TYPE
    SYNTAX       CfprApAdaptorCapDefFwVersionOpr
    MAX-ACCESS   read-only
    STATUS       current
    DESCRIPTION
        "Cisco Firepower adaptor:CapQual:fwVersionOpr managed
        object property"
    ::= { cfprApAdaptorCapQualEntry 6 }

cfprApAdaptorCapQualMaximum OBJECT-TYPE
    SYNTAX       Gauge32
    MAX-ACCESS   read-only
    STATUS       current
    DESCRIPTION
        "Cisco Firepower adaptor:CapQual:maximum managed object property"
    ::= { cfprApAdaptorCapQualEntry 7 }

cfprApAdaptorCapQualModel OBJECT-TYPE
    SYNTAX       SnmpAdminString
    MAX-ACCESS   read-only
    STATUS       current
    DESCRIPTION
        "Cisco Firepower adaptor:CapQual:model managed object property"
    ::= { cfprApAdaptorCapQualEntry 8 }

cfprApAdaptorCapQualType OBJECT-TYPE
    SYNTAX       CfprApAdaptorCapDefType
    MAX-ACCESS   read-only
    STATUS       current
    DESCRIPTION
        "Cisco Firepower adaptor:CapQual:type managed object property"
    ::= { cfprApAdaptorCapQualEntry 10 }

cfprApAdaptorCapSpecTable OBJECT-TYPE
    SYNTAX           SEQUENCE OF CfprApAdaptorCapSpecEntry
    MAX-ACCESS       not-accessible
    STATUS           current
    DESCRIPTION
        "Cisco Firepower adaptor:CapSpec managed object table"
    ::= { cfprApAdaptorObjects 2 }

cfprApAdaptorCapSpecEntry OBJECT-TYPE
    SYNTAX           CfprApAdaptorCapSpecEntry
    MAX-ACCESS       not-accessible
    STATUS           current
    DESCRIPTION
        "Entry for the cfprApAdaptorCapSpecTable table."
    INDEX { cfprApAdaptorCapSpecInstanceId }
    ::= { cfprApAdaptorCapSpecTable 1 }

CfprApAdaptorCapSpecEntry ::= SEQUENCE {
    cfprApAdaptorCapSpecInstanceId                                   CfprApManagedObjectId,
    cfprApAdaptorCapSpecDn                                           CfprApManagedObjectDn,
    cfprApAdaptorCapSpecRn                                           SnmpAdminString,
    cfprApAdaptorCapSpecFwVersionHi                                  SnmpAdminString,
    cfprApAdaptorCapSpecFwVersionLo                                  SnmpAdminString,
    cfprApAdaptorCapSpecFwVersionOpr                                 CfprApAdaptorCapDefFwVersionOpr,
    cfprApAdaptorCapSpecMaximum                                      Gauge32,
    cfprApAdaptorCapSpecType                                         CfprApAdaptorCapSpecType
}

cfprApAdaptorCapSpecInstanceId OBJECT-TYPE
    SYNTAX       CfprApManagedObjectId
    MAX-ACCESS   not-accessible
    STATUS       current
    DESCRIPTION
        "Instance identifier of the managed object."
    ::= { cfprApAdaptorCapSpecEntry 1 }

cfprApAdaptorCapSpecDn OBJECT-TYPE
    SYNTAX       CfprApManagedObjectDn
    MAX-ACCESS   read-only
    STATUS       current
    DESCRIPTION
        "Cisco Firepower adaptor:CapSpec:dn managed object property"
    ::= { cfprApAdaptorCapSpecEntry 2 }

cfprApAdaptorCapSpecRn OBJECT-TYPE
    SYNTAX       SnmpAdminString
    MAX-ACCESS   read-only
    STATUS       current
    DESCRIPTION
        "Cisco Firepower adaptor:CapSpec:rn managed object property"
    ::= { cfprApAdaptorCapSpecEntry 3 }

cfprApAdaptorCapSpecFwVersionHi OBJECT-TYPE
    SYNTAX       SnmpAdminString
    MAX-ACCESS   read-only
    STATUS       current
    DESCRIPTION
        "Cisco Firepower adaptor:CapSpec:fwVersionHi managed
        object property"
    ::= { cfprApAdaptorCapSpecEntry 4 }

cfprApAdaptorCapSpecFwVersionLo OBJECT-TYPE
    SYNTAX       SnmpAdminString
    MAX-ACCESS   read-only
    STATUS       current
    DESCRIPTION
        "Cisco Firepower adaptor:CapSpec:fwVersionLo managed
        object property"
    ::= { cfprApAdaptorCapSpecEntry 5 }

cfprApAdaptorCapSpecFwVersionOpr OBJECT-TYPE
    SYNTAX       CfprApAdaptorCapDefFwVersionOpr
    MAX-ACCESS   read-only
    STATUS       current
    DESCRIPTION
        "Cisco Firepower adaptor:CapSpec:fwVersionOpr managed
        object property"
    ::= { cfprApAdaptorCapSpecEntry 6 }

cfprApAdaptorCapSpecMaximum OBJECT-TYPE
    SYNTAX       Gauge32
    MAX-ACCESS   read-only
    STATUS       current
    DESCRIPTION
        "Cisco Firepower adaptor:CapSpec:maximum managed object property"
    ::= { cfprApAdaptorCapSpecEntry 7 }

cfprApAdaptorCapSpecType OBJECT-TYPE
    SYNTAX       CfprApAdaptorCapSpecType
    MAX-ACCESS   read-only
    STATUS       current
    DESCRIPTION
        "Cisco Firepower adaptor:CapSpec:type managed object property"
    ::= { cfprApAdaptorCapSpecEntry 9 }

cfprApAdaptorDiagCapTable OBJECT-TYPE
    SYNTAX           SEQUENCE OF CfprApAdaptorDiagCapEntry
    MAX-ACCESS       not-accessible
    STATUS           current
    DESCRIPTION
        "Cisco Firepower adaptor:DiagCap managed object table"
    ::= { cfprApAdaptorObjects 3 }

cfprApAdaptorDiagCapEntry OBJECT-TYPE
    SYNTAX           CfprApAdaptorDiagCapEntry
    MAX-ACCESS       not-accessible
    STATUS           current
    DESCRIPTION
        "Entry for the cfprApAdaptorDiagCapTable table."
    INDEX { cfprApAdaptorDiagCapInstanceId }
    ::= { cfprApAdaptorDiagCapTable 1 }

CfprApAdaptorDiagCapEntry ::= SEQUENCE {
    cfprApAdaptorDiagCapInstanceId                                   CfprApManagedObjectId,
    cfprApAdaptorDiagCapDn                                           CfprApManagedObjectDn,
    cfprApAdaptorDiagCapRn                                           SnmpAdminString,
    cfprApAdaptorDiagCapEnableLldpTransmit                           TruthValue
}

cfprApAdaptorDiagCapInstanceId OBJECT-TYPE
    SYNTAX       CfprApManagedObjectId
    MAX-ACCESS   not-accessible
    STATUS       current
    DESCRIPTION
        "Instance identifier of the managed object."
    ::= { cfprApAdaptorDiagCapEntry 1 }

cfprApAdaptorDiagCapDn OBJECT-TYPE
    SYNTAX       CfprApManagedObjectDn
    MAX-ACCESS   read-only
    STATUS       current
    DESCRIPTION
        "Cisco Firepower adaptor:DiagCap:dn managed object property"
    ::= { cfprApAdaptorDiagCapEntry 2 }

cfprApAdaptorDiagCapRn OBJECT-TYPE
    SYNTAX       SnmpAdminString
    MAX-ACCESS   read-only
    STATUS       current
    DESCRIPTION
        "Cisco Firepower adaptor:DiagCap:rn managed object property"
    ::= { cfprApAdaptorDiagCapEntry 3 }

cfprApAdaptorDiagCapEnableLldpTransmit OBJECT-TYPE
    SYNTAX       TruthValue
    MAX-ACCESS   read-only
    STATUS       current
    DESCRIPTION
        "Cisco Firepower adaptor:DiagCap:enableLldpTransmit
        managed object property"
    ::= { cfprApAdaptorDiagCapEntry 4 }

cfprApAdaptorEthArfsProfileTable OBJECT-TYPE
    SYNTAX           SEQUENCE OF CfprApAdaptorEthArfsProfileEntry
    MAX-ACCESS       not-accessible
    STATUS           current
    DESCRIPTION
        "Cisco Firepower adaptor:EthArfsProfile managed object table"
    ::= { cfprApAdaptorObjects 4 }

cfprApAdaptorEthArfsProfileEntry OBJECT-TYPE
    SYNTAX           CfprApAdaptorEthArfsProfileEntry
    MAX-ACCESS       not-accessible
    STATUS           current
    DESCRIPTION
        "Entry for the cfprApAdaptorEthArfsProfileTable table."
    INDEX { cfprApAdaptorEthArfsProfileInstanceId }
    ::= { cfprApAdaptorEthArfsProfileTable 1 }

CfprApAdaptorEthArfsProfileEntry ::= SEQUENCE {
    cfprApAdaptorEthArfsProfileInstanceId                            CfprApManagedObjectId,
    cfprApAdaptorEthArfsProfileDn                                    CfprApManagedObjectDn,
    cfprApAdaptorEthArfsProfileRn                                    SnmpAdminString,
    cfprApAdaptorEthArfsProfileAccelaratedRFS                        CfprApAdaptorEthArfsProfileAccelaratedRFS
}

cfprApAdaptorEthArfsProfileInstanceId OBJECT-TYPE
    SYNTAX       CfprApManagedObjectId
    MAX-ACCESS   not-accessible
    STATUS       current
    DESCRIPTION
        "Instance identifier of the managed object."
    ::= { cfprApAdaptorEthArfsProfileEntry 1 }

cfprApAdaptorEthArfsProfileDn OBJECT-TYPE
    SYNTAX       CfprApManagedObjectDn
    MAX-ACCESS   read-only
    STATUS       current
    DESCRIPTION
        "Cisco Firepower adaptor:EthArfsProfile:dn managed
        object property"
    ::= { cfprApAdaptorEthArfsProfileEntry 2 }

cfprApAdaptorEthArfsProfileRn OBJECT-TYPE
    SYNTAX       SnmpAdminString
    MAX-ACCESS   read-only
    STATUS       current
    DESCRIPTION
        "Cisco Firepower adaptor:EthArfsProfile:rn managed
        object property"
    ::= { cfprApAdaptorEthArfsProfileEntry 3 }

cfprApAdaptorEthArfsProfileAccelaratedRFS OBJECT-TYPE
    SYNTAX       CfprApAdaptorEthArfsProfileAccelaratedRFS
    MAX-ACCESS   read-only
    STATUS       current
    DESCRIPTION
        "Cisco Firepower adaptor:EthArfsProfile:accelaratedRFS
        managed object property"
    ::= { cfprApAdaptorEthArfsProfileEntry 4 }

cfprApAdaptorEthCompQueueProfileTable OBJECT-TYPE
    SYNTAX           SEQUENCE OF CfprApAdaptorEthCompQueueProfileEntry
    MAX-ACCESS       not-accessible
    STATUS           current
    DESCRIPTION
        "Cisco Firepower adaptor:EthCompQueueProfile managed object table"
    ::= { cfprApAdaptorObjects 5 }

cfprApAdaptorEthCompQueueProfileEntry OBJECT-TYPE
    SYNTAX           CfprApAdaptorEthCompQueueProfileEntry
    MAX-ACCESS       not-accessible
    STATUS           current
    DESCRIPTION
        "Entry for the cfprApAdaptorEthCompQueueProfileTable table."
    INDEX { cfprApAdaptorEthCompQueueProfileInstanceId }
    ::= { cfprApAdaptorEthCompQueueProfileTable 1 }

CfprApAdaptorEthCompQueueProfileEntry ::= SEQUENCE {
    cfprApAdaptorEthCompQueueProfileInstanceId                       CfprApManagedObjectId,
    cfprApAdaptorEthCompQueueProfileDn                               CfprApManagedObjectDn,
    cfprApAdaptorEthCompQueueProfileRn                               SnmpAdminString,
    cfprApAdaptorEthCompQueueProfileCount                            Gauge32,
    cfprApAdaptorEthCompQueueProfileRingSize                         Gauge32
}

cfprApAdaptorEthCompQueueProfileInstanceId OBJECT-TYPE
    SYNTAX       CfprApManagedObjectId
    MAX-ACCESS   not-accessible
    STATUS       current
    DESCRIPTION
        "Instance identifier of the managed object."
    ::= { cfprApAdaptorEthCompQueueProfileEntry 1 }

cfprApAdaptorEthCompQueueProfileDn OBJECT-TYPE
    SYNTAX       CfprApManagedObjectDn
    MAX-ACCESS   read-only
    STATUS       current
    DESCRIPTION
        "Cisco Firepower adaptor:EthCompQueueProfile:dn
        managed object property"
    ::= { cfprApAdaptorEthCompQueueProfileEntry 2 }

cfprApAdaptorEthCompQueueProfileRn OBJECT-TYPE
    SYNTAX       SnmpAdminString
    MAX-ACCESS   read-only
    STATUS       current
    DESCRIPTION
        "Cisco Firepower adaptor:EthCompQueueProfile:rn
        managed object property"
    ::= { cfprApAdaptorEthCompQueueProfileEntry 3 }

cfprApAdaptorEthCompQueueProfileCount OBJECT-TYPE
    SYNTAX       Gauge32
    MAX-ACCESS   read-only
    STATUS       current
    DESCRIPTION
        "Cisco Firepower adaptor:EthCompQueueProfile:count
        managed object property"
    ::= { cfprApAdaptorEthCompQueueProfileEntry 4 }

cfprApAdaptorEthCompQueueProfileRingSize OBJECT-TYPE
    SYNTAX       Gauge32
    MAX-ACCESS   read-only
    STATUS       current
    DESCRIPTION
        "Cisco Firepower adaptor:EthCompQueueProfile:ringSize
        managed object property"
    ::= { cfprApAdaptorEthCompQueueProfileEntry 5 }

cfprApAdaptorEthFailoverProfileTable OBJECT-TYPE
    SYNTAX           SEQUENCE OF CfprApAdaptorEthFailoverProfileEntry
    MAX-ACCESS       not-accessible
    STATUS           current
    DESCRIPTION
        "Cisco Firepower adaptor:EthFailoverProfile managed object table"
    ::= { cfprApAdaptorObjects 6 }

cfprApAdaptorEthFailoverProfileEntry OBJECT-TYPE
    SYNTAX           CfprApAdaptorEthFailoverProfileEntry
    MAX-ACCESS       not-accessible
    STATUS           current
    DESCRIPTION
        "Entry for the cfprApAdaptorEthFailoverProfileTable table."
    INDEX { cfprApAdaptorEthFailoverProfileInstanceId }
    ::= { cfprApAdaptorEthFailoverProfileTable 1 }

CfprApAdaptorEthFailoverProfileEntry ::= SEQUENCE {
    cfprApAdaptorEthFailoverProfileInstanceId                        CfprApManagedObjectId,
    cfprApAdaptorEthFailoverProfileDn                                CfprApManagedObjectDn,
    cfprApAdaptorEthFailoverProfileRn                                SnmpAdminString,
    cfprApAdaptorEthFailoverProfileTimeout                           Gauge32
}

cfprApAdaptorEthFailoverProfileInstanceId OBJECT-TYPE
    SYNTAX       CfprApManagedObjectId
    MAX-ACCESS   not-accessible
    STATUS       current
    DESCRIPTION
        "Instance identifier of the managed object."
    ::= { cfprApAdaptorEthFailoverProfileEntry 1 }

cfprApAdaptorEthFailoverProfileDn OBJECT-TYPE
    SYNTAX       CfprApManagedObjectDn
    MAX-ACCESS   read-only
    STATUS       current
    DESCRIPTION
        "Cisco Firepower adaptor:EthFailoverProfile:dn
        managed object property"
    ::= { cfprApAdaptorEthFailoverProfileEntry 2 }

cfprApAdaptorEthFailoverProfileRn OBJECT-TYPE
    SYNTAX       SnmpAdminString
    MAX-ACCESS   read-only
    STATUS       current
    DESCRIPTION
        "Cisco Firepower adaptor:EthFailoverProfile:rn
        managed object property"
    ::= { cfprApAdaptorEthFailoverProfileEntry 3 }

cfprApAdaptorEthFailoverProfileTimeout OBJECT-TYPE
    SYNTAX       Gauge32
    MAX-ACCESS   read-only
    STATUS       current
    DESCRIPTION
        "Cisco Firepower adaptor:EthFailoverProfile:timeout
        managed object property"
    ::= { cfprApAdaptorEthFailoverProfileEntry 4 }

cfprApAdaptorEthInterruptProfileTable OBJECT-TYPE
    SYNTAX           SEQUENCE OF CfprApAdaptorEthInterruptProfileEntry
    MAX-ACCESS       not-accessible
    STATUS           current
    DESCRIPTION
        "Cisco Firepower adaptor:EthInterruptProfile managed object table"
    ::= { cfprApAdaptorObjects 7 }

cfprApAdaptorEthInterruptProfileEntry OBJECT-TYPE
    SYNTAX           CfprApAdaptorEthInterruptProfileEntry
    MAX-ACCESS       not-accessible
    STATUS           current
    DESCRIPTION
        "Entry for the cfprApAdaptorEthInterruptProfileTable table."
    INDEX { cfprApAdaptorEthInterruptProfileInstanceId }
    ::= { cfprApAdaptorEthInterruptProfileTable 1 }

CfprApAdaptorEthInterruptProfileEntry ::= SEQUENCE {
    cfprApAdaptorEthInterruptProfileInstanceId                       CfprApManagedObjectId,
    cfprApAdaptorEthInterruptProfileDn                               CfprApManagedObjectDn,
    cfprApAdaptorEthInterruptProfileRn                               SnmpAdminString,
    cfprApAdaptorEthInterruptProfileCoalescingTime                   Gauge32,
    cfprApAdaptorEthInterruptProfileCoalescingType                   CfprApAdaptorEthInterruptProfileCoalescingType,
    cfprApAdaptorEthInterruptProfileCount                            Gauge32,
    cfprApAdaptorEthInterruptProfileMode                             CfprApAdaptorInterruptMode
}

cfprApAdaptorEthInterruptProfileInstanceId OBJECT-TYPE
    SYNTAX       CfprApManagedObjectId
    MAX-ACCESS   not-accessible
    STATUS       current
    DESCRIPTION
        "Instance identifier of the managed object."
    ::= { cfprApAdaptorEthInterruptProfileEntry 1 }

cfprApAdaptorEthInterruptProfileDn OBJECT-TYPE
    SYNTAX       CfprApManagedObjectDn
    MAX-ACCESS   read-only
    STATUS       current
    DESCRIPTION
        "Cisco Firepower adaptor:EthInterruptProfile:dn
        managed object property"
    ::= { cfprApAdaptorEthInterruptProfileEntry 2 }

cfprApAdaptorEthInterruptProfileRn OBJECT-TYPE
    SYNTAX       SnmpAdminString
    MAX-ACCESS   read-only
    STATUS       current
    DESCRIPTION
        "Cisco Firepower adaptor:EthInterruptProfile:rn
        managed object property"
    ::= { cfprApAdaptorEthInterruptProfileEntry 3 }

cfprApAdaptorEthInterruptProfileCoalescingTime OBJECT-TYPE
    SYNTAX       Gauge32
    MAX-ACCESS   read-only
    STATUS       current
    DESCRIPTION
        "Cisco Firepower adaptor:EthInterruptProfile:coalescingTime
        managed object property"
    ::= { cfprApAdaptorEthInterruptProfileEntry 4 }

cfprApAdaptorEthInterruptProfileCoalescingType OBJECT-TYPE
    SYNTAX       CfprApAdaptorEthInterruptProfileCoalescingType
    MAX-ACCESS   read-only
    STATUS       current
    DESCRIPTION
        "Cisco Firepower adaptor:EthInterruptProfile:coalescingType
        managed object property"
    ::= { cfprApAdaptorEthInterruptProfileEntry 5 }

cfprApAdaptorEthInterruptProfileCount OBJECT-TYPE
    SYNTAX       Gauge32
    MAX-ACCESS   read-only
    STATUS       current
    DESCRIPTION
        "Cisco Firepower adaptor:EthInterruptProfile:count
        managed object property"
    ::= { cfprApAdaptorEthInterruptProfileEntry 6 }

cfprApAdaptorEthInterruptProfileMode OBJECT-TYPE
    SYNTAX       CfprApAdaptorInterruptMode
    MAX-ACCESS   read-only
    STATUS       current
    DESCRIPTION
        "Cisco Firepower adaptor:EthInterruptProfile:mode
        managed object property"
    ::= { cfprApAdaptorEthInterruptProfileEntry 7 }

cfprApAdaptorEthNVGREProfileTable OBJECT-TYPE
    SYNTAX           SEQUENCE OF CfprApAdaptorEthNVGREProfileEntry
    MAX-ACCESS       not-accessible
    STATUS           current
    DESCRIPTION
        "Cisco Firepower adaptor:EthNVGREProfile managed object table"
    ::= { cfprApAdaptorObjects 8 }

cfprApAdaptorEthNVGREProfileEntry OBJECT-TYPE
    SYNTAX           CfprApAdaptorEthNVGREProfileEntry
    MAX-ACCESS       not-accessible
    STATUS           current
    DESCRIPTION
        "Entry for the cfprApAdaptorEthNVGREProfileTable table."
    INDEX { cfprApAdaptorEthNVGREProfileInstanceId }
    ::= { cfprApAdaptorEthNVGREProfileTable 1 }

CfprApAdaptorEthNVGREProfileEntry ::= SEQUENCE {
    cfprApAdaptorEthNVGREProfileInstanceId                           CfprApManagedObjectId,
    cfprApAdaptorEthNVGREProfileDn                                   CfprApManagedObjectDn,
    cfprApAdaptorEthNVGREProfileRn                                   SnmpAdminString,
    cfprApAdaptorEthNVGREProfileAdminState                           CfprApAdaptorEthNVGREProfileAdminState
}

cfprApAdaptorEthNVGREProfileInstanceId OBJECT-TYPE
    SYNTAX       CfprApManagedObjectId
    MAX-ACCESS   not-accessible
    STATUS       current
    DESCRIPTION
        "Instance identifier of the managed object."
    ::= { cfprApAdaptorEthNVGREProfileEntry 1 }

cfprApAdaptorEthNVGREProfileDn OBJECT-TYPE
    SYNTAX       CfprApManagedObjectDn
    MAX-ACCESS   read-only
    STATUS       current
    DESCRIPTION
        "Cisco Firepower adaptor:EthNVGREProfile:dn managed
        object property"
    ::= { cfprApAdaptorEthNVGREProfileEntry 2 }

cfprApAdaptorEthNVGREProfileRn OBJECT-TYPE
    SYNTAX       SnmpAdminString
    MAX-ACCESS   read-only
    STATUS       current
    DESCRIPTION
        "Cisco Firepower adaptor:EthNVGREProfile:rn managed
        object property"
    ::= { cfprApAdaptorEthNVGREProfileEntry 3 }

cfprApAdaptorEthNVGREProfileAdminState OBJECT-TYPE
    SYNTAX       CfprApAdaptorEthNVGREProfileAdminState
    MAX-ACCESS   read-only
    STATUS       current
    DESCRIPTION
        "Cisco Firepower adaptor:EthNVGREProfile:adminState
        managed object property"
    ::= { cfprApAdaptorEthNVGREProfileEntry 4 }

cfprApAdaptorEthOffloadProfileTable OBJECT-TYPE
    SYNTAX           SEQUENCE OF CfprApAdaptorEthOffloadProfileEntry
    MAX-ACCESS       not-accessible
    STATUS           current
    DESCRIPTION
        "Cisco Firepower adaptor:EthOffloadProfile managed object table"
    ::= { cfprApAdaptorObjects 9 }

cfprApAdaptorEthOffloadProfileEntry OBJECT-TYPE
    SYNTAX           CfprApAdaptorEthOffloadProfileEntry
    MAX-ACCESS       not-accessible
    STATUS           current
    DESCRIPTION
        "Entry for the cfprApAdaptorEthOffloadProfileTable table."
    INDEX { cfprApAdaptorEthOffloadProfileInstanceId }
    ::= { cfprApAdaptorEthOffloadProfileTable 1 }

CfprApAdaptorEthOffloadProfileEntry ::= SEQUENCE {
    cfprApAdaptorEthOffloadProfileInstanceId                         CfprApManagedObjectId,
    cfprApAdaptorEthOffloadProfileDn                                 CfprApManagedObjectDn,
    cfprApAdaptorEthOffloadProfileRn                                 SnmpAdminString,
    cfprApAdaptorEthOffloadProfileLargeReceive                       CfprApAdaptorEthOffloadProfileLargeReceive,
    cfprApAdaptorEthOffloadProfileTcpRxChecksum                      CfprApAdaptorEthOffloadProfileTcpRxChecksum,
    cfprApAdaptorEthOffloadProfileTcpSegment                         CfprApAdaptorEthOffloadProfileTcpSegment,
    cfprApAdaptorEthOffloadProfileTcpTxChecksum                      CfprApAdaptorEthOffloadProfileTcpTxChecksum
}

cfprApAdaptorEthOffloadProfileInstanceId OBJECT-TYPE
    SYNTAX       CfprApManagedObjectId
    MAX-ACCESS   not-accessible
    STATUS       current
    DESCRIPTION
        "Instance identifier of the managed object."
    ::= { cfprApAdaptorEthOffloadProfileEntry 1 }

cfprApAdaptorEthOffloadProfileDn OBJECT-TYPE
    SYNTAX       CfprApManagedObjectDn
    MAX-ACCESS   read-only
    STATUS       current
    DESCRIPTION
        "Cisco Firepower adaptor:EthOffloadProfile:dn managed
        object property"
    ::= { cfprApAdaptorEthOffloadProfileEntry 2 }

cfprApAdaptorEthOffloadProfileRn OBJECT-TYPE
    SYNTAX       SnmpAdminString
    MAX-ACCESS   read-only
    STATUS       current
    DESCRIPTION
        "Cisco Firepower adaptor:EthOffloadProfile:rn managed
        object property"
    ::= { cfprApAdaptorEthOffloadProfileEntry 3 }

cfprApAdaptorEthOffloadProfileLargeReceive OBJECT-TYPE
    SYNTAX       CfprApAdaptorEthOffloadProfileLargeReceive
    MAX-ACCESS   read-only
    STATUS       current
    DESCRIPTION
        "Cisco Firepower adaptor:EthOffloadProfile:largeReceive
        managed object property"
    ::= { cfprApAdaptorEthOffloadProfileEntry 4 }

cfprApAdaptorEthOffloadProfileTcpRxChecksum OBJECT-TYPE
    SYNTAX       CfprApAdaptorEthOffloadProfileTcpRxChecksum
    MAX-ACCESS   read-only
    STATUS       current
    DESCRIPTION
        "Cisco Firepower adaptor:EthOffloadProfile:tcpRxChecksum
        managed object property"
    ::= { cfprApAdaptorEthOffloadProfileEntry 5 }

cfprApAdaptorEthOffloadProfileTcpSegment OBJECT-TYPE
    SYNTAX       CfprApAdaptorEthOffloadProfileTcpSegment
    MAX-ACCESS   read-only
    STATUS       current
    DESCRIPTION
        "Cisco Firepower adaptor:EthOffloadProfile:tcpSegment
        managed object property"
    ::= { cfprApAdaptorEthOffloadProfileEntry 6 }

cfprApAdaptorEthOffloadProfileTcpTxChecksum OBJECT-TYPE
    SYNTAX       CfprApAdaptorEthOffloadProfileTcpTxChecksum
    MAX-ACCESS   read-only
    STATUS       current
    DESCRIPTION
        "Cisco Firepower adaptor:EthOffloadProfile:tcpTxChecksum
        managed object property"
    ::= { cfprApAdaptorEthOffloadProfileEntry 7 }

cfprApAdaptorEthPortBySizeLargeStatsTable OBJECT-TYPE
    SYNTAX           SEQUENCE OF CfprApAdaptorEthPortBySizeLargeStatsEntry
    MAX-ACCESS       not-accessible
    STATUS           current
    DESCRIPTION
        "Cisco Firepower adaptor:EthPortBySizeLargeStats
        managed object table"
    ::= { cfprApAdaptorObjects 10 }

cfprApAdaptorEthPortBySizeLargeStatsEntry OBJECT-TYPE
    SYNTAX           CfprApAdaptorEthPortBySizeLargeStatsEntry
    MAX-ACCESS       not-accessible
    STATUS           current
    DESCRIPTION
        "Entry for the cfprApAdaptorEthPortBySizeLargeStatsTable table."
    INDEX { cfprApAdaptorEthPortBySizeLargeStatsInstanceId }
    ::= { cfprApAdaptorEthPortBySizeLargeStatsTable 1 }

CfprApAdaptorEthPortBySizeLargeStatsEntry ::= SEQUENCE {
    cfprApAdaptorEthPortBySizeLargeStatsInstanceId                   CfprApManagedObjectId,
    cfprApAdaptorEthPortBySizeLargeStatsDn                           CfprApManagedObjectDn,
    cfprApAdaptorEthPortBySizeLargeStatsRn                           SnmpAdminString,
    cfprApAdaptorEthPortBySizeLargeStatsGreaterThanOrEqualTo9216     Unsigned64,
    cfprApAdaptorEthPortBySizeLargeStatsGreaterThanOrEqualTo9216Delta Counter64,
    cfprApAdaptorEthPortBySizeLargeStatsGreaterThanOrEqualTo9216DeltaAvg Unsigned64,
    cfprApAdaptorEthPortBySizeLargeStatsGreaterThanOrEqualTo9216DeltaMax Unsigned64,
    cfprApAdaptorEthPortBySizeLargeStatsGreaterThanOrEqualTo9216DeltaMin Unsigned64,
    cfprApAdaptorEthPortBySizeLargeStatsIntervals                    Gauge32,
    cfprApAdaptorEthPortBySizeLargeStatsLessThan2048                 Unsigned64,
    cfprApAdaptorEthPortBySizeLargeStatsLessThan2048Delta            Counter64,
    cfprApAdaptorEthPortBySizeLargeStatsLessThan2048DeltaAvg         Unsigned64,
    cfprApAdaptorEthPortBySizeLargeStatsLessThan2048DeltaMax         Unsigned64,
    cfprApAdaptorEthPortBySizeLargeStatsLessThan2048DeltaMin         Unsigned64,
    cfprApAdaptorEthPortBySizeLargeStatsLessThan4096                 Unsigned64,
    cfprApAdaptorEthPortBySizeLargeStatsLessThan4096Delta            Counter64,
    cfprApAdaptorEthPortBySizeLargeStatsLessThan4096DeltaAvg         Unsigned64,
    cfprApAdaptorEthPortBySizeLargeStatsLessThan4096DeltaMax         Unsigned64,
    cfprApAdaptorEthPortBySizeLargeStatsLessThan4096DeltaMin         Unsigned64,
    cfprApAdaptorEthPortBySizeLargeStatsLessThan8192                 Unsigned64,
    cfprApAdaptorEthPortBySizeLargeStatsLessThan8192Delta            Counter64,
    cfprApAdaptorEthPortBySizeLargeStatsLessThan8192DeltaAvg         Unsigned64,
    cfprApAdaptorEthPortBySizeLargeStatsLessThan8192DeltaMax         Unsigned64,
    cfprApAdaptorEthPortBySizeLargeStatsLessThan8192DeltaMin         Unsigned64,
    cfprApAdaptorEthPortBySizeLargeStatsLessThan9216                 Unsigned64,
    cfprApAdaptorEthPortBySizeLargeStatsLessThan9216Delta            Counter64,
    cfprApAdaptorEthPortBySizeLargeStatsLessThan9216DeltaAvg         Unsigned64,
    cfprApAdaptorEthPortBySizeLargeStatsLessThan9216DeltaMax         Unsigned64,
    cfprApAdaptorEthPortBySizeLargeStatsLessThan9216DeltaMin         Unsigned64,
    cfprApAdaptorEthPortBySizeLargeStatsLessThanOrEqualTo1518        Unsigned64,
    cfprApAdaptorEthPortBySizeLargeStatsLessThanOrEqualTo1518Delta   Counter64,
    cfprApAdaptorEthPortBySizeLargeStatsLessThanOrEqualTo1518DeltaAvg Unsigned64,
    cfprApAdaptorEthPortBySizeLargeStatsLessThanOrEqualTo1518DeltaMax Unsigned64,
    cfprApAdaptorEthPortBySizeLargeStatsLessThanOrEqualTo1518DeltaMin Unsigned64,
    cfprApAdaptorEthPortBySizeLargeStatsNoBreakdownGreaterThan1518   Unsigned64,
    cfprApAdaptorEthPortBySizeLargeStatsNoBreakdownGreaterThan1518Delta Counter64,
    cfprApAdaptorEthPortBySizeLargeStatsNoBreakdownGreaterThan1518DeltaAvg Unsigned64,
    cfprApAdaptorEthPortBySizeLargeStatsNoBreakdownGreaterThan1518DeltaMax Unsigned64,
    cfprApAdaptorEthPortBySizeLargeStatsNoBreakdownGreaterThan1518DeltaMin Unsigned64,
    cfprApAdaptorEthPortBySizeLargeStatsSuspect                      TruthValue,
    cfprApAdaptorEthPortBySizeLargeStatsThresholded                  CfprApAdaptorEthPortBySizeLargeStatsThresholded,
    cfprApAdaptorEthPortBySizeLargeStatsTimeCollected                DateAndTime,
    cfprApAdaptorEthPortBySizeLargeStatsTrafficDirection             CfprApAdaptorAdapterStatsTrafficDir,
    cfprApAdaptorEthPortBySizeLargeStatsUpdate                       Gauge32
}

cfprApAdaptorEthPortBySizeLargeStatsInstanceId OBJECT-TYPE
    SYNTAX       CfprApManagedObjectId
    MAX-ACCESS   not-accessible
    STATUS       current
    DESCRIPTION
        "Instance identifier of the managed object."
    ::= { cfprApAdaptorEthPortBySizeLargeStatsEntry 1 }

cfprApAdaptorEthPortBySizeLargeStatsDn OBJECT-TYPE
    SYNTAX       CfprApManagedObjectDn
    MAX-ACCESS   read-only
    STATUS       current
    DESCRIPTION
        "Cisco Firepower adaptor:EthPortBySizeLargeStats:dn
        managed object property"
    ::= { cfprApAdaptorEthPortBySizeLargeStatsEntry 2 }

cfprApAdaptorEthPortBySizeLargeStatsRn OBJECT-TYPE
    SYNTAX       SnmpAdminString
    MAX-ACCESS   read-only
    STATUS       current
    DESCRIPTION
        "Cisco Firepower adaptor:EthPortBySizeLargeStats:rn
        managed object property"
    ::= { cfprApAdaptorEthPortBySizeLargeStatsEntry 3 }

cfprApAdaptorEthPortBySizeLargeStatsGreaterThanOrEqualTo9216 OBJECT-TYPE
    SYNTAX       Unsigned64
    MAX-ACCESS   read-only
    STATUS       current
    DESCRIPTION
        "Cisco Firepower adaptor:EthPortBySizeLargeStats:greaterThanOrEqua
        lTo9216 managed object property"
    ::= { cfprApAdaptorEthPortBySizeLargeStatsEntry 4 }

cfprApAdaptorEthPortBySizeLargeStatsGreaterThanOrEqualTo9216Delta OBJECT-TYPE
    SYNTAX       Counter64
    MAX-ACCESS   read-only
    STATUS       current
    DESCRIPTION
        "Cisco Firepower adaptor:EthPortBySizeLargeStats:greaterThanOrEqua
        lTo9216Delta managed object property"
    ::= { cfprApAdaptorEthPortBySizeLargeStatsEntry 5 }

cfprApAdaptorEthPortBySizeLargeStatsGreaterThanOrEqualTo9216DeltaAvg OBJECT-TYPE
    SYNTAX       Unsigned64
    MAX-ACCESS   read-only
    STATUS       current
    DESCRIPTION
        "Cisco Firepower adaptor:EthPortBySizeLargeStats:greaterThanOrEqua
        lTo9216DeltaAvg managed object property"
    ::= { cfprApAdaptorEthPortBySizeLargeStatsEntry 6 }

cfprApAdaptorEthPortBySizeLargeStatsGreaterThanOrEqualTo9216DeltaMax OBJECT-TYPE
    SYNTAX       Unsigned64
    MAX-ACCESS   read-only
    STATUS       current
    DESCRIPTION
        "Cisco Firepower adaptor:EthPortBySizeLargeStats:greaterThanOrEqua
        lTo9216DeltaMax managed object property"
    ::= { cfprApAdaptorEthPortBySizeLargeStatsEntry 7 }

cfprApAdaptorEthPortBySizeLargeStatsGreaterThanOrEqualTo9216DeltaMin OBJECT-TYPE
    SYNTAX       Unsigned64
    MAX-ACCESS   read-only
    STATUS       current
    DESCRIPTION
        "Cisco Firepower adaptor:EthPortBySizeLargeStats:greaterThanOrEqua
        lTo9216DeltaMin managed object property"
    ::= { cfprApAdaptorEthPortBySizeLargeStatsEntry 8 }

cfprApAdaptorEthPortBySizeLargeStatsIntervals OBJECT-TYPE
    SYNTAX       Gauge32
    MAX-ACCESS   read-only
    STATUS       current
    DESCRIPTION
        "Cisco Firepower adaptor:EthPortBySizeLargeStats:intervals
        managed object property"
    ::= { cfprApAdaptorEthPortBySizeLargeStatsEntry 9 }

cfprApAdaptorEthPortBySizeLargeStatsLessThan2048 OBJECT-TYPE
    SYNTAX       Unsigned64
    MAX-ACCESS   read-only
    STATUS       current
    DESCRIPTION
        "Cisco Firepower adaptor:EthPortBySizeLargeStats:lessThan2048
        managed object property"
    ::= { cfprApAdaptorEthPortBySizeLargeStatsEntry 10 }

cfprApAdaptorEthPortBySizeLargeStatsLessThan2048Delta OBJECT-TYPE
    SYNTAX       Counter64
    MAX-ACCESS   read-only
    STATUS       current
    DESCRIPTION
        "Cisco Firepower adaptor:EthPortBySizeLargeStats:lessThan2048Delta
         managed object property"
    ::= { cfprApAdaptorEthPortBySizeLargeStatsEntry 11 }

cfprApAdaptorEthPortBySizeLargeStatsLessThan2048DeltaAvg OBJECT-TYPE
    SYNTAX       Unsigned64
    MAX-ACCESS   read-only
    STATUS       current
    DESCRIPTION
        "Cisco Firepower adaptor:EthPortBySizeLargeStats:lessThan2048Delta
        Avg managed object property"
    ::= { cfprApAdaptorEthPortBySizeLargeStatsEntry 12 }

cfprApAdaptorEthPortBySizeLargeStatsLessThan2048DeltaMax OBJECT-TYPE
    SYNTAX       Unsigned64
    MAX-ACCESS   read-only
    STATUS       current
    DESCRIPTION
        "Cisco Firepower adaptor:EthPortBySizeLargeStats:lessThan2048Delta
        Max managed object property"
    ::= { cfprApAdaptorEthPortBySizeLargeStatsEntry 13 }

cfprApAdaptorEthPortBySizeLargeStatsLessThan2048DeltaMin OBJECT-TYPE
    SYNTAX       Unsigned64
    MAX-ACCESS   read-only
    STATUS       current
    DESCRIPTION
        "Cisco Firepower adaptor:EthPortBySizeLargeStats:lessThan2048Delta
        Min managed object property"
    ::= { cfprApAdaptorEthPortBySizeLargeStatsEntry 14 }

cfprApAdaptorEthPortBySizeLargeStatsLessThan4096 OBJECT-TYPE
    SYNTAX       Unsigned64
    MAX-ACCESS   read-only
    STATUS       current
    DESCRIPTION
        "Cisco Firepower adaptor:EthPortBySizeLargeStats:lessThan4096
        managed object property"
    ::= { cfprApAdaptorEthPortBySizeLargeStatsEntry 15 }

cfprApAdaptorEthPortBySizeLargeStatsLessThan4096Delta OBJECT-TYPE
    SYNTAX       Counter64
    MAX-ACCESS   read-only
    STATUS       current
    DESCRIPTION
        "Cisco Firepower adaptor:EthPortBySizeLargeStats:lessThan4096Delta
         managed object property"
    ::= { cfprApAdaptorEthPortBySizeLargeStatsEntry 16 }

cfprApAdaptorEthPortBySizeLargeStatsLessThan4096DeltaAvg OBJECT-TYPE
    SYNTAX       Unsigned64
    MAX-ACCESS   read-only
    STATUS       current
    DESCRIPTION
        "Cisco Firepower adaptor:EthPortBySizeLargeStats:lessThan4096Delta
        Avg managed object property"
    ::= { cfprApAdaptorEthPortBySizeLargeStatsEntry 17 }

cfprApAdaptorEthPortBySizeLargeStatsLessThan4096DeltaMax OBJECT-TYPE
    SYNTAX       Unsigned64
    MAX-ACCESS   read-only
    STATUS       current
    DESCRIPTION
        "Cisco Firepower adaptor:EthPortBySizeLargeStats:lessThan4096Delta
        Max managed object property"
    ::= { cfprApAdaptorEthPortBySizeLargeStatsEntry 18 }

cfprApAdaptorEthPortBySizeLargeStatsLessThan4096DeltaMin OBJECT-TYPE
    SYNTAX       Unsigned64
    MAX-ACCESS   read-only
    STATUS       current
    DESCRIPTION
        "Cisco Firepower adaptor:EthPortBySizeLargeStats:lessThan4096Delta
        Min managed object property"
    ::= { cfprApAdaptorEthPortBySizeLargeStatsEntry 19 }

cfprApAdaptorEthPortBySizeLargeStatsLessThan8192 OBJECT-TYPE
    SYNTAX       Unsigned64
    MAX-ACCESS   read-only
    STATUS       current
    DESCRIPTION
        "Cisco Firepower adaptor:EthPortBySizeLargeStats:lessThan8192
        managed object property"
    ::= { cfprApAdaptorEthPortBySizeLargeStatsEntry 20 }

cfprApAdaptorEthPortBySizeLargeStatsLessThan8192Delta OBJECT-TYPE
    SYNTAX       Counter64
    MAX-ACCESS   read-only
    STATUS       current
    DESCRIPTION
        "Cisco Firepower adaptor:EthPortBySizeLargeStats:lessThan8192Delta
         managed object property"
    ::= { cfprApAdaptorEthPortBySizeLargeStatsEntry 21 }

cfprApAdaptorEthPortBySizeLargeStatsLessThan8192DeltaAvg OBJECT-TYPE
    SYNTAX       Unsigned64
    MAX-ACCESS   read-only
    STATUS       current
    DESCRIPTION
        "Cisco Firepower adaptor:EthPortBySizeLargeStats:lessThan8192Delta
        Avg managed object property"
    ::= { cfprApAdaptorEthPortBySizeLargeStatsEntry 22 }

cfprApAdaptorEthPortBySizeLargeStatsLessThan8192DeltaMax OBJECT-TYPE
    SYNTAX       Unsigned64
    MAX-ACCESS   read-only
    STATUS       current
    DESCRIPTION
        "Cisco Firepower adaptor:EthPortBySizeLargeStats:lessThan8192Delta
        Max managed object property"
    ::= { cfprApAdaptorEthPortBySizeLargeStatsEntry 23 }

cfprApAdaptorEthPortBySizeLargeStatsLessThan8192DeltaMin OBJECT-TYPE
    SYNTAX       Unsigned64
    MAX-ACCESS   read-only
    STATUS       current
    DESCRIPTION
        "Cisco Firepower adaptor:EthPortBySizeLargeStats:lessThan8192Delta
        Min managed object property"
    ::= { cfprApAdaptorEthPortBySizeLargeStatsEntry 24 }

cfprApAdaptorEthPortBySizeLargeStatsLessThan9216 OBJECT-TYPE
    SYNTAX       Unsigned64
    MAX-ACCESS   read-only
    STATUS       current
    DESCRIPTION
        "Cisco Firepower adaptor:EthPortBySizeLargeStats:lessThan9216
        managed object property"
    ::= { cfprApAdaptorEthPortBySizeLargeStatsEntry 25 }

cfprApAdaptorEthPortBySizeLargeStatsLessThan9216Delta OBJECT-TYPE
    SYNTAX       Counter64
    MAX-ACCESS   read-only
    STATUS       current
    DESCRIPTION
        "Cisco Firepower adaptor:EthPortBySizeLargeStats:lessThan9216Delta
         managed object property"
    ::= { cfprApAdaptorEthPortBySizeLargeStatsEntry 26 }

cfprApAdaptorEthPortBySizeLargeStatsLessThan9216DeltaAvg OBJECT-TYPE
    SYNTAX       Unsigned64
    MAX-ACCESS   read-only
    STATUS       current
    DESCRIPTION
        "Cisco Firepower adaptor:EthPortBySizeLargeStats:lessThan9216Delta
        Avg managed object property"
    ::= { cfprApAdaptorEthPortBySizeLargeStatsEntry 27 }

cfprApAdaptorEthPortBySizeLargeStatsLessThan9216DeltaMax OBJECT-TYPE
    SYNTAX       Unsigned64
    MAX-ACCESS   read-only
    STATUS       current
    DESCRIPTION
        "Cisco Firepower adaptor:EthPortBySizeLargeStats:lessThan9216Delta
        Max managed object property"
    ::= { cfprApAdaptorEthPortBySizeLargeStatsEntry 28 }

cfprApAdaptorEthPortBySizeLargeStatsLessThan9216DeltaMin OBJECT-TYPE
    SYNTAX       Unsigned64
    MAX-ACCESS   read-only
    STATUS       current
    DESCRIPTION
        "Cisco Firepower adaptor:EthPortBySizeLargeStats:lessThan9216Delta
        Min managed object property"
    ::= { cfprApAdaptorEthPortBySizeLargeStatsEntry 29 }

cfprApAdaptorEthPortBySizeLargeStatsLessThanOrEqualTo1518 OBJECT-TYPE
    SYNTAX       Unsigned64
    MAX-ACCESS   read-only
    STATUS       current
    DESCRIPTION
        "Cisco Firepower adaptor:EthPortBySizeLargeStats:lessThanOrEqualTo
        1518 managed object property"
    ::= { cfprApAdaptorEthPortBySizeLargeStatsEntry 30 }

cfprApAdaptorEthPortBySizeLargeStatsLessThanOrEqualTo1518Delta OBJECT-TYPE
    SYNTAX       Counter64
    MAX-ACCESS   read-only
    STATUS       current
    DESCRIPTION
        "Cisco Firepower adaptor:EthPortBySizeLargeStats:lessThanOrEqualTo
        1518Delta managed object property"
    ::= { cfprApAdaptorEthPortBySizeLargeStatsEntry 31 }

cfprApAdaptorEthPortBySizeLargeStatsLessThanOrEqualTo1518DeltaAvg OBJECT-TYPE
    SYNTAX       Unsigned64
    MAX-ACCESS   read-only
    STATUS       current
    DESCRIPTION
        "Cisco Firepower adaptor:EthPortBySizeLargeStats:lessThanOrEqualTo
        1518DeltaAvg managed object property"
    ::= { cfprApAdaptorEthPortBySizeLargeStatsEntry 32 }

cfprApAdaptorEthPortBySizeLargeStatsLessThanOrEqualTo1518DeltaMax OBJECT-TYPE
    SYNTAX       Unsigned64
    MAX-ACCESS   read-only
    STATUS       current
    DESCRIPTION
        "Cisco Firepower adaptor:EthPortBySizeLargeStats:lessThanOrEqualTo
        1518DeltaMax managed object property"
    ::= { cfprApAdaptorEthPortBySizeLargeStatsEntry 33 }

cfprApAdaptorEthPortBySizeLargeStatsLessThanOrEqualTo1518DeltaMin OBJECT-TYPE
    SYNTAX       Unsigned64
    MAX-ACCESS   read-only
    STATUS       current
    DESCRIPTION
        "Cisco Firepower adaptor:EthPortBySizeLargeStats:lessThanOrEqualTo
        1518DeltaMin managed object property"
    ::= { cfprApAdaptorEthPortBySizeLargeStatsEntry 34 }

cfprApAdaptorEthPortBySizeLargeStatsNoBreakdownGreaterThan1518 OBJECT-TYPE
    SYNTAX       Unsigned64
    MAX-ACCESS   read-only
    STATUS       current
    DESCRIPTION
        "Cisco Firepower adaptor:EthPortBySizeLargeStats:noBreakdownGreate
        rThan1518 managed object property"
    ::= { cfprApAdaptorEthPortBySizeLargeStatsEntry 35 }

cfprApAdaptorEthPortBySizeLargeStatsNoBreakdownGreaterThan1518Delta OBJECT-TYPE
    SYNTAX       Counter64
    MAX-ACCESS   read-only
    STATUS       current
    DESCRIPTION
        "Cisco Firepower adaptor:EthPortBySizeLargeStats:noBreakdownGreate
        rThan1518Delta managed object property"
    ::= { cfprApAdaptorEthPortBySizeLargeStatsEntry 36 }

cfprApAdaptorEthPortBySizeLargeStatsNoBreakdownGreaterThan1518DeltaAvg OBJECT-TYPE
    SYNTAX       Unsigned64
    MAX-ACCESS   read-only
    STATUS       current
    DESCRIPTION
        "Cisco Firepower adaptor:EthPortBySizeLargeStats:noBreakdownGreate
        rThan1518DeltaAvg managed object property"
    ::= { cfprApAdaptorEthPortBySizeLargeStatsEntry 37 }

cfprApAdaptorEthPortBySizeLargeStatsNoBreakdownGreaterThan1518DeltaMax OBJECT-TYPE
    SYNTAX       Unsigned64
    MAX-ACCESS   read-only
    STATUS       current
    DESCRIPTION
        "Cisco Firepower adaptor:EthPortBySizeLargeStats:noBreakdownGreate
        rThan1518DeltaMax managed object property"
    ::= { cfprApAdaptorEthPortBySizeLargeStatsEntry 38 }

cfprApAdaptorEthPortBySizeLargeStatsNoBreakdownGreaterThan1518DeltaMin OBJECT-TYPE
    SYNTAX       Unsigned64
    MAX-ACCESS   read-only
    STATUS       current
    DESCRIPTION
        "Cisco Firepower adaptor:EthPortBySizeLargeStats:noBreakdownGreate
        rThan1518DeltaMin managed object property"
    ::= { cfprApAdaptorEthPortBySizeLargeStatsEntry 39 }

cfprApAdaptorEthPortBySizeLargeStatsSuspect OBJECT-TYPE
    SYNTAX       TruthValue
    MAX-ACCESS   read-only
    STATUS       current
    DESCRIPTION
        "Cisco Firepower adaptor:EthPortBySizeLargeStats:suspect
        managed object property"
    ::= { cfprApAdaptorEthPortBySizeLargeStatsEntry 40 }

cfprApAdaptorEthPortBySizeLargeStatsThresholded OBJECT-TYPE
    SYNTAX       CfprApAdaptorEthPortBySizeLargeStatsThresholded
    MAX-ACCESS   read-only
    STATUS       current
    DESCRIPTION
        "Cisco Firepower adaptor:EthPortBySizeLargeStats:thresholded
        managed object property"
    ::= { cfprApAdaptorEthPortBySizeLargeStatsEntry 41 }

cfprApAdaptorEthPortBySizeLargeStatsTimeCollected OBJECT-TYPE
    SYNTAX       DateAndTime
    MAX-ACCESS   read-only
    STATUS       current
    DESCRIPTION
        "Cisco Firepower adaptor:EthPortBySizeLargeStats:timeCollected
        managed object property"
    ::= { cfprApAdaptorEthPortBySizeLargeStatsEntry 42 }

cfprApAdaptorEthPortBySizeLargeStatsTrafficDirection OBJECT-TYPE
    SYNTAX       CfprApAdaptorAdapterStatsTrafficDir
    MAX-ACCESS   read-only
    STATUS       current
    DESCRIPTION
        "Cisco Firepower adaptor:EthPortBySizeLargeStats:trafficDirection
        managed object property"
    ::= { cfprApAdaptorEthPortBySizeLargeStatsEntry 43 }

cfprApAdaptorEthPortBySizeLargeStatsUpdate OBJECT-TYPE
    SYNTAX       Gauge32
    MAX-ACCESS   read-only
    STATUS       current
    DESCRIPTION
        "Cisco Firepower adaptor:EthPortBySizeLargeStats:update
        managed object property"
    ::= { cfprApAdaptorEthPortBySizeLargeStatsEntry 44 }

cfprApAdaptorEthPortBySizeLargeStatsHistTable OBJECT-TYPE
    SYNTAX           SEQUENCE OF CfprApAdaptorEthPortBySizeLargeStatsHistEntry
    MAX-ACCESS       not-accessible
    STATUS           current
    DESCRIPTION
        "Cisco Firepower adaptor:EthPortBySizeLargeStatsHist
        managed object table"
    ::= { cfprApAdaptorObjects 11 }

cfprApAdaptorEthPortBySizeLargeStatsHistEntry OBJECT-TYPE
    SYNTAX           CfprApAdaptorEthPortBySizeLargeStatsHistEntry
    MAX-ACCESS       not-accessible
    STATUS           current
    DESCRIPTION
        "Entry for the cfprApAdaptorEthPortBySizeLargeStatsHistTable table."
    INDEX { cfprApAdaptorEthPortBySizeLargeStatsHistInstanceId }
    ::= { cfprApAdaptorEthPortBySizeLargeStatsHistTable 1 }

CfprApAdaptorEthPortBySizeLargeStatsHistEntry ::= SEQUENCE {
    cfprApAdaptorEthPortBySizeLargeStatsHistInstanceId               CfprApManagedObjectId,
    cfprApAdaptorEthPortBySizeLargeStatsHistDn                       CfprApManagedObjectDn,
    cfprApAdaptorEthPortBySizeLargeStatsHistRn                       SnmpAdminString,
    cfprApAdaptorEthPortBySizeLargeStatsHistGreaterThanOrEqualTo9216 Unsigned64,
    cfprApAdaptorEthPortBySizeLargeStatsHistGreaterThanOrEqualTo9216Delta Unsigned64,
    cfprApAdaptorEthPortBySizeLargeStatsHistGreaterThanOrEqualTo9216DeltaAvg Unsigned64,
    cfprApAdaptorEthPortBySizeLargeStatsHistGreaterThanOrEqualTo9216DeltaMax Unsigned64,
    cfprApAdaptorEthPortBySizeLargeStatsHistGreaterThanOrEqualTo9216DeltaMin Unsigned64,
    cfprApAdaptorEthPortBySizeLargeStatsHistId                       Unsigned64,
    cfprApAdaptorEthPortBySizeLargeStatsHistLessThan2048             Unsigned64,
    cfprApAdaptorEthPortBySizeLargeStatsHistLessThan2048Delta        Unsigned64,
    cfprApAdaptorEthPortBySizeLargeStatsHistLessThan2048DeltaAvg     Unsigned64,
    cfprApAdaptorEthPortBySizeLargeStatsHistLessThan2048DeltaMax     Unsigned64,
    cfprApAdaptorEthPortBySizeLargeStatsHistLessThan2048DeltaMin     Unsigned64,
    cfprApAdaptorEthPortBySizeLargeStatsHistLessThan4096             Unsigned64,
    cfprApAdaptorEthPortBySizeLargeStatsHistLessThan4096Delta        Unsigned64,
    cfprApAdaptorEthPortBySizeLargeStatsHistLessThan4096DeltaAvg     Unsigned64,
    cfprApAdaptorEthPortBySizeLargeStatsHistLessThan4096DeltaMax     Unsigned64,
    cfprApAdaptorEthPortBySizeLargeStatsHistLessThan4096DeltaMin     Unsigned64,
    cfprApAdaptorEthPortBySizeLargeStatsHistLessThan8192             Unsigned64,
    cfprApAdaptorEthPortBySizeLargeStatsHistLessThan8192Delta        Unsigned64,
    cfprApAdaptorEthPortBySizeLargeStatsHistLessThan8192DeltaAvg     Unsigned64,
    cfprApAdaptorEthPortBySizeLargeStatsHistLessThan8192DeltaMax     Unsigned64,
    cfprApAdaptorEthPortBySizeLargeStatsHistLessThan8192DeltaMin     Unsigned64,
    cfprApAdaptorEthPortBySizeLargeStatsHistLessThan9216             Unsigned64,
    cfprApAdaptorEthPortBySizeLargeStatsHistLessThan9216Delta        Unsigned64,
    cfprApAdaptorEthPortBySizeLargeStatsHistLessThan9216DeltaAvg     Unsigned64,
    cfprApAdaptorEthPortBySizeLargeStatsHistLessThan9216DeltaMax     Unsigned64,
    cfprApAdaptorEthPortBySizeLargeStatsHistLessThan9216DeltaMin     Unsigned64,
    cfprApAdaptorEthPortBySizeLargeStatsHistLessThanOrEqualTo1518    Unsigned64,
    cfprApAdaptorEthPortBySizeLargeStatsHistLessThanOrEqualTo1518Delta Unsigned64,
    cfprApAdaptorEthPortBySizeLargeStatsHistLessThanOrEqualTo1518DeltaAvg Unsigned64,
    cfprApAdaptorEthPortBySizeLargeStatsHistLessThanOrEqualTo1518DeltaMax Unsigned64,
    cfprApAdaptorEthPortBySizeLargeStatsHistLessThanOrEqualTo1518DeltaMin Unsigned64,
    cfprApAdaptorEthPortBySizeLargeStatsHistMostRecent               TruthValue,
    cfprApAdaptorEthPortBySizeLargeStatsHistNoBreakdownGreaterThan1518 Unsigned64,
    cfprApAdaptorEthPortBySizeLargeStatsHistNoBreakdownGreaterThan1518Delta Unsigned64,
    cfprApAdaptorEthPortBySizeLargeStatsHistNoBreakdownGreaterThan1518DeltaAvg Unsigned64,
    cfprApAdaptorEthPortBySizeLargeStatsHistNoBreakdownGreaterThan1518DeltaMax Unsigned64,
    cfprApAdaptorEthPortBySizeLargeStatsHistNoBreakdownGreaterThan1518DeltaMin Unsigned64,
    cfprApAdaptorEthPortBySizeLargeStatsHistSuspect                  TruthValue,
    cfprApAdaptorEthPortBySizeLargeStatsHistThresholded              CfprApAdaptorEthPortBySizeLargeStatsHistThresholded,
    cfprApAdaptorEthPortBySizeLargeStatsHistTimeCollected            DateAndTime
}

cfprApAdaptorEthPortBySizeLargeStatsHistInstanceId OBJECT-TYPE
    SYNTAX       CfprApManagedObjectId
    MAX-ACCESS   not-accessible
    STATUS       current
    DESCRIPTION
        "Instance identifier of the managed object."
    ::= { cfprApAdaptorEthPortBySizeLargeStatsHistEntry 1 }

cfprApAdaptorEthPortBySizeLargeStatsHistDn OBJECT-TYPE
    SYNTAX       CfprApManagedObjectDn
    MAX-ACCESS   read-only
    STATUS       current
    DESCRIPTION
        "Cisco Firepower adaptor:EthPortBySizeLargeStatsHist:dn
        managed object property"
    ::= { cfprApAdaptorEthPortBySizeLargeStatsHistEntry 2 }

cfprApAdaptorEthPortBySizeLargeStatsHistRn OBJECT-TYPE
    SYNTAX       SnmpAdminString
    MAX-ACCESS   read-only
    STATUS       current
    DESCRIPTION
        "Cisco Firepower adaptor:EthPortBySizeLargeStatsHist:rn
        managed object property"
    ::= { cfprApAdaptorEthPortBySizeLargeStatsHistEntry 3 }

cfprApAdaptorEthPortBySizeLargeStatsHistGreaterThanOrEqualTo9216 OBJECT-TYPE
    SYNTAX       Unsigned64
    MAX-ACCESS   read-only
    STATUS       current
    DESCRIPTION
        "Cisco Firepower adaptor:EthPortBySizeLargeStatsHist:greaterThanOr
        EqualTo9216 managed object property"
    ::= { cfprApAdaptorEthPortBySizeLargeStatsHistEntry 4 }

cfprApAdaptorEthPortBySizeLargeStatsHistGreaterThanOrEqualTo9216Delta OBJECT-TYPE
    SYNTAX       Unsigned64
    MAX-ACCESS   read-only
    STATUS       current
    DESCRIPTION
        "Cisco Firepower adaptor:EthPortBySizeLargeStatsHist:greaterThanOr
        EqualTo9216Delta managed object property"
    ::= { cfprApAdaptorEthPortBySizeLargeStatsHistEntry 5 }

cfprApAdaptorEthPortBySizeLargeStatsHistGreaterThanOrEqualTo9216DeltaAvg OBJECT-TYPE
    SYNTAX       Unsigned64
    MAX-ACCESS   read-only
    STATUS       current
    DESCRIPTION
        "Cisco Firepower adaptor:EthPortBySizeLargeStatsHist:greaterThanOr
        EqualTo9216DeltaAvg managed object property"
    ::= { cfprApAdaptorEthPortBySizeLargeStatsHistEntry 6 }

cfprApAdaptorEthPortBySizeLargeStatsHistGreaterThanOrEqualTo9216DeltaMax OBJECT-TYPE
    SYNTAX       Unsigned64
    MAX-ACCESS   read-only
    STATUS       current
    DESCRIPTION
        "Cisco Firepower adaptor:EthPortBySizeLargeStatsHist:greaterThanOr
        EqualTo9216DeltaMax managed object property"
    ::= { cfprApAdaptorEthPortBySizeLargeStatsHistEntry 7 }

cfprApAdaptorEthPortBySizeLargeStatsHistGreaterThanOrEqualTo9216DeltaMin OBJECT-TYPE
    SYNTAX       Unsigned64
    MAX-ACCESS   read-only
    STATUS       current
    DESCRIPTION
        "Cisco Firepower adaptor:EthPortBySizeLargeStatsHist:greaterThanOr
        EqualTo9216DeltaMin managed object property"
    ::= { cfprApAdaptorEthPortBySizeLargeStatsHistEntry 8 }

cfprApAdaptorEthPortBySizeLargeStatsHistId OBJECT-TYPE
    SYNTAX       Unsigned64
    MAX-ACCESS   read-only
    STATUS       current
    DESCRIPTION
        "Cisco Firepower adaptor:EthPortBySizeLargeStatsHist:id
        managed object property"
    ::= { cfprApAdaptorEthPortBySizeLargeStatsHistEntry 9 }

cfprApAdaptorEthPortBySizeLargeStatsHistLessThan2048 OBJECT-TYPE
    SYNTAX       Unsigned64
    MAX-ACCESS   read-only
    STATUS       current
    DESCRIPTION
        "Cisco Firepower adaptor:EthPortBySizeLargeStatsHist:lessThan2048
        managed object property"
    ::= { cfprApAdaptorEthPortBySizeLargeStatsHistEntry 10 }

cfprApAdaptorEthPortBySizeLargeStatsHistLessThan2048Delta OBJECT-TYPE
    SYNTAX       Unsigned64
    MAX-ACCESS   read-only
    STATUS       current
    DESCRIPTION
        "Cisco Firepower adaptor:EthPortBySizeLargeStatsHist:lessThan2048D
        elta managed object property"
    ::= { cfprApAdaptorEthPortBySizeLargeStatsHistEntry 11 }

cfprApAdaptorEthPortBySizeLargeStatsHistLessThan2048DeltaAvg OBJECT-TYPE
    SYNTAX       Unsigned64
    MAX-ACCESS   read-only
    STATUS       current
    DESCRIPTION
        "Cisco Firepower adaptor:EthPortBySizeLargeStatsHist:lessThan2048D
        eltaAvg managed object property"
    ::= { cfprApAdaptorEthPortBySizeLargeStatsHistEntry 12 }

cfprApAdaptorEthPortBySizeLargeStatsHistLessThan2048DeltaMax OBJECT-TYPE
    SYNTAX       Unsigned64
    MAX-ACCESS   read-only
    STATUS       current
    DESCRIPTION
        "Cisco Firepower adaptor:EthPortBySizeLargeStatsHist:lessThan2048D
        eltaMax managed object property"
    ::= { cfprApAdaptorEthPortBySizeLargeStatsHistEntry 13 }

cfprApAdaptorEthPortBySizeLargeStatsHistLessThan2048DeltaMin OBJECT-TYPE
    SYNTAX       Unsigned64
    MAX-ACCESS   read-only
    STATUS       current
    DESCRIPTION
        "Cisco Firepower adaptor:EthPortBySizeLargeStatsHist:lessThan2048D
        eltaMin managed object property"
    ::= { cfprApAdaptorEthPortBySizeLargeStatsHistEntry 14 }

cfprApAdaptorEthPortBySizeLargeStatsHistLessThan4096 OBJECT-TYPE
    SYNTAX       Unsigned64
    MAX-ACCESS   read-only
    STATUS       current
    DESCRIPTION
        "Cisco Firepower adaptor:EthPortBySizeLargeStatsHist:lessThan4096
        managed object property"
    ::= { cfprApAdaptorEthPortBySizeLargeStatsHistEntry 15 }

cfprApAdaptorEthPortBySizeLargeStatsHistLessThan4096Delta OBJECT-TYPE
    SYNTAX       Unsigned64
    MAX-ACCESS   read-only
    STATUS       current
    DESCRIPTION
        "Cisco Firepower adaptor:EthPortBySizeLargeStatsHist:lessThan4096D
        elta managed object property"
    ::= { cfprApAdaptorEthPortBySizeLargeStatsHistEntry 16 }

cfprApAdaptorEthPortBySizeLargeStatsHistLessThan4096DeltaAvg OBJECT-TYPE
    SYNTAX       Unsigned64
    MAX-ACCESS   read-only
    STATUS       current
    DESCRIPTION
        "Cisco Firepower adaptor:EthPortBySizeLargeStatsHist:lessThan4096D
        eltaAvg managed object property"
    ::= { cfprApAdaptorEthPortBySizeLargeStatsHistEntry 17 }

cfprApAdaptorEthPortBySizeLargeStatsHistLessThan4096DeltaMax OBJECT-TYPE
    SYNTAX       Unsigned64
    MAX-ACCESS   read-only
    STATUS       current
    DESCRIPTION
        "Cisco Firepower adaptor:EthPortBySizeLargeStatsHist:lessThan4096D
        eltaMax managed object property"
    ::= { cfprApAdaptorEthPortBySizeLargeStatsHistEntry 18 }

cfprApAdaptorEthPortBySizeLargeStatsHistLessThan4096DeltaMin OBJECT-TYPE
    SYNTAX       Unsigned64
    MAX-ACCESS   read-only
    STATUS       current
    DESCRIPTION
        "Cisco Firepower adaptor:EthPortBySizeLargeStatsHist:lessThan4096D
        eltaMin managed object property"
    ::= { cfprApAdaptorEthPortBySizeLargeStatsHistEntry 19 }

cfprApAdaptorEthPortBySizeLargeStatsHistLessThan8192 OBJECT-TYPE
    SYNTAX       Unsigned64
    MAX-ACCESS   read-only
    STATUS       current
    DESCRIPTION
        "Cisco Firepower adaptor:EthPortBySizeLargeStatsHist:lessThan8192
        managed object property"
    ::= { cfprApAdaptorEthPortBySizeLargeStatsHistEntry 20 }

cfprApAdaptorEthPortBySizeLargeStatsHistLessThan8192Delta OBJECT-TYPE
    SYNTAX       Unsigned64
    MAX-ACCESS   read-only
    STATUS       current
    DESCRIPTION
        "Cisco Firepower adaptor:EthPortBySizeLargeStatsHist:lessThan8192D
        elta managed object property"
    ::= { cfprApAdaptorEthPortBySizeLargeStatsHistEntry 21 }

cfprApAdaptorEthPortBySizeLargeStatsHistLessThan8192DeltaAvg OBJECT-TYPE
    SYNTAX       Unsigned64
    MAX-ACCESS   read-only
    STATUS       current
    DESCRIPTION
        "Cisco Firepower adaptor:EthPortBySizeLargeStatsHist:lessThan8192D
        eltaAvg managed object property"
    ::= { cfprApAdaptorEthPortBySizeLargeStatsHistEntry 22 }

cfprApAdaptorEthPortBySizeLargeStatsHistLessThan8192DeltaMax OBJECT-TYPE
    SYNTAX       Unsigned64
    MAX-ACCESS   read-only
    STATUS       current
    DESCRIPTION
        "Cisco Firepower adaptor:EthPortBySizeLargeStatsHist:lessThan8192D
        eltaMax managed object property"
    ::= { cfprApAdaptorEthPortBySizeLargeStatsHistEntry 23 }

cfprApAdaptorEthPortBySizeLargeStatsHistLessThan8192DeltaMin OBJECT-TYPE
    SYNTAX       Unsigned64
    MAX-ACCESS   read-only
    STATUS       current
    DESCRIPTION
        "Cisco Firepower adaptor:EthPortBySizeLargeStatsHist:lessThan8192D
        eltaMin managed object property"
    ::= { cfprApAdaptorEthPortBySizeLargeStatsHistEntry 24 }

cfprApAdaptorEthPortBySizeLargeStatsHistLessThan9216 OBJECT-TYPE
    SYNTAX       Unsigned64
    MAX-ACCESS   read-only
    STATUS       current
    DESCRIPTION
        "Cisco Firepower adaptor:EthPortBySizeLargeStatsHist:lessThan9216
        managed object property"
    ::= { cfprApAdaptorEthPortBySizeLargeStatsHistEntry 25 }

cfprApAdaptorEthPortBySizeLargeStatsHistLessThan9216Delta OBJECT-TYPE
    SYNTAX       Unsigned64
    MAX-ACCESS   read-only
    STATUS       current
    DESCRIPTION
        "Cisco Firepower adaptor:EthPortBySizeLargeStatsHist:lessThan9216D
        elta managed object property"
    ::= { cfprApAdaptorEthPortBySizeLargeStatsHistEntry 26 }

cfprApAdaptorEthPortBySizeLargeStatsHistLessThan9216DeltaAvg OBJECT-TYPE
    SYNTAX       Unsigned64
    MAX-ACCESS   read-only
    STATUS       current
    DESCRIPTION
        "Cisco Firepower adaptor:EthPortBySizeLargeStatsHist:lessThan9216D
        eltaAvg managed object property"
    ::= { cfprApAdaptorEthPortBySizeLargeStatsHistEntry 27 }

cfprApAdaptorEthPortBySizeLargeStatsHistLessThan9216DeltaMax OBJECT-TYPE
    SYNTAX       Unsigned64
    MAX-ACCESS   read-only
    STATUS       current
    DESCRIPTION
        "Cisco Firepower adaptor:EthPortBySizeLargeStatsHist:lessThan9216D
        eltaMax managed object property"
    ::= { cfprApAdaptorEthPortBySizeLargeStatsHistEntry 28 }

cfprApAdaptorEthPortBySizeLargeStatsHistLessThan9216DeltaMin OBJECT-TYPE
    SYNTAX       Unsigned64
    MAX-ACCESS   read-only
    STATUS       current
    DESCRIPTION
        "Cisco Firepower adaptor:EthPortBySizeLargeStatsHist:lessThan9216D
        eltaMin managed object property"
    ::= { cfprApAdaptorEthPortBySizeLargeStatsHistEntry 29 }

cfprApAdaptorEthPortBySizeLargeStatsHistLessThanOrEqualTo1518 OBJECT-TYPE
    SYNTAX       Unsigned64
    MAX-ACCESS   read-only
    STATUS       current
    DESCRIPTION
        "Cisco Firepower adaptor:EthPortBySizeLargeStatsHist:lessThanOrEqu
        alTo1518 managed object property"
    ::= { cfprApAdaptorEthPortBySizeLargeStatsHistEntry 30 }

cfprApAdaptorEthPortBySizeLargeStatsHistLessThanOrEqualTo1518Delta OBJECT-TYPE
    SYNTAX       Unsigned64
    MAX-ACCESS   read-only
    STATUS       current
    DESCRIPTION
        "Cisco Firepower adaptor:EthPortBySizeLargeStatsHist:lessThanOrEqu
        alTo1518Delta managed object property"
    ::= { cfprApAdaptorEthPortBySizeLargeStatsHistEntry 31 }

cfprApAdaptorEthPortBySizeLargeStatsHistLessThanOrEqualTo1518DeltaAvg OBJECT-TYPE
    SYNTAX       Unsigned64
    MAX-ACCESS   read-only
    STATUS       current
    DESCRIPTION
        "Cisco Firepower adaptor:EthPortBySizeLargeStatsHist:lessThanOrEqu
        alTo1518DeltaAvg managed object property"
    ::= { cfprApAdaptorEthPortBySizeLargeStatsHistEntry 32 }

cfprApAdaptorEthPortBySizeLargeStatsHistLessThanOrEqualTo1518DeltaMax OBJECT-TYPE
    SYNTAX       Unsigned64
    MAX-ACCESS   read-only
    STATUS       current
    DESCRIPTION
        "Cisco Firepower adaptor:EthPortBySizeLargeStatsHist:lessThanOrEqu
        alTo1518DeltaMax managed object property"
    ::= { cfprApAdaptorEthPortBySizeLargeStatsHistEntry 33 }

cfprApAdaptorEthPortBySizeLargeStatsHistLessThanOrEqualTo1518DeltaMin OBJECT-TYPE
    SYNTAX       Unsigned64
    MAX-ACCESS   read-only
    STATUS       current
    DESCRIPTION
        "Cisco Firepower adaptor:EthPortBySizeLargeStatsHist:lessThanOrEqu
        alTo1518DeltaMin managed object property"
    ::= { cfprApAdaptorEthPortBySizeLargeStatsHistEntry 34 }

cfprApAdaptorEthPortBySizeLargeStatsHistMostRecent OBJECT-TYPE
    SYNTAX       TruthValue
    MAX-ACCESS   read-only
    STATUS       current
    DESCRIPTION
        "Cisco Firepower adaptor:EthPortBySizeLargeStatsHist:mostRecent
        managed object property"
    ::= { cfprApAdaptorEthPortBySizeLargeStatsHistEntry 35 }

cfprApAdaptorEthPortBySizeLargeStatsHistNoBreakdownGreaterThan1518 OBJECT-TYPE
    SYNTAX       Unsigned64
    MAX-ACCESS   read-only
    STATUS       current
    DESCRIPTION
        "Cisco Firepower adaptor:EthPortBySizeLargeStatsHist:noBreakdownGr
        eaterThan1518 managed object property"
    ::= { cfprApAdaptorEthPortBySizeLargeStatsHistEntry 36 }

cfprApAdaptorEthPortBySizeLargeStatsHistNoBreakdownGreaterThan1518Delta OBJECT-TYPE
    SYNTAX       Unsigned64
    MAX-ACCESS   read-only
    STATUS       current
    DESCRIPTION
        "Cisco Firepower adaptor:EthPortBySizeLargeStatsHist:noBreakdownGr
        eaterThan1518Delta managed object property"
    ::= { cfprApAdaptorEthPortBySizeLargeStatsHistEntry 37 }

cfprApAdaptorEthPortBySizeLargeStatsHistNoBreakdownGreaterThan1518DeltaAvg OBJECT-TYPE
    SYNTAX       Unsigned64
    MAX-ACCESS   read-only
    STATUS       current
    DESCRIPTION
        "Cisco Firepower adaptor:EthPortBySizeLargeStatsHist:noBreakdownGr
        eaterThan1518DeltaAvg managed object property"
    ::= { cfprApAdaptorEthPortBySizeLargeStatsHistEntry 38 }

cfprApAdaptorEthPortBySizeLargeStatsHistNoBreakdownGreaterThan1518DeltaMax OBJECT-TYPE
    SYNTAX       Unsigned64
    MAX-ACCESS   read-only
    STATUS       current
    DESCRIPTION
        "Cisco Firepower adaptor:EthPortBySizeLargeStatsHist:noBreakdownGr
        eaterThan1518DeltaMax managed object property"
    ::= { cfprApAdaptorEthPortBySizeLargeStatsHistEntry 39 }

cfprApAdaptorEthPortBySizeLargeStatsHistNoBreakdownGreaterThan1518DeltaMin OBJECT-TYPE
    SYNTAX       Unsigned64
    MAX-ACCESS   read-only
    STATUS       current
    DESCRIPTION
        "Cisco Firepower adaptor:EthPortBySizeLargeStatsHist:noBreakdownGr
        eaterThan1518DeltaMin managed object property"
    ::= { cfprApAdaptorEthPortBySizeLargeStatsHistEntry 40 }

cfprApAdaptorEthPortBySizeLargeStatsHistSuspect OBJECT-TYPE
    SYNTAX       TruthValue
    MAX-ACCESS   read-only
    STATUS       current
    DESCRIPTION
        "Cisco Firepower adaptor:EthPortBySizeLargeStatsHist:suspect
        managed object property"
    ::= { cfprApAdaptorEthPortBySizeLargeStatsHistEntry 41 }

cfprApAdaptorEthPortBySizeLargeStatsHistThresholded OBJECT-TYPE
    SYNTAX       CfprApAdaptorEthPortBySizeLargeStatsHistThresholded
    MAX-ACCESS   read-only
    STATUS       current
    DESCRIPTION
        "Cisco Firepower adaptor:EthPortBySizeLargeStatsHist:thresholded
        managed object property"
    ::= { cfprApAdaptorEthPortBySizeLargeStatsHistEntry 42 }

cfprApAdaptorEthPortBySizeLargeStatsHistTimeCollected OBJECT-TYPE
    SYNTAX       DateAndTime
    MAX-ACCESS   read-only
    STATUS       current
    DESCRIPTION
        "Cisco Firepower adaptor:EthPortBySizeLargeStatsHist:timeCollected
         managed object property"
    ::= { cfprApAdaptorEthPortBySizeLargeStatsHistEntry 43 }

cfprApAdaptorEthPortBySizeSmallStatsTable OBJECT-TYPE
    SYNTAX           SEQUENCE OF CfprApAdaptorEthPortBySizeSmallStatsEntry
    MAX-ACCESS       not-accessible
    STATUS           current
    DESCRIPTION
        "Cisco Firepower adaptor:EthPortBySizeSmallStats
        managed object table"
    ::= { cfprApAdaptorObjects 12 }

cfprApAdaptorEthPortBySizeSmallStatsEntry OBJECT-TYPE
    SYNTAX           CfprApAdaptorEthPortBySizeSmallStatsEntry
    MAX-ACCESS       not-accessible
    STATUS           current
    DESCRIPTION
        "Entry for the cfprApAdaptorEthPortBySizeSmallStatsTable table."
    INDEX { cfprApAdaptorEthPortBySizeSmallStatsInstanceId }
    ::= { cfprApAdaptorEthPortBySizeSmallStatsTable 1 }

CfprApAdaptorEthPortBySizeSmallStatsEntry ::= SEQUENCE {
    cfprApAdaptorEthPortBySizeSmallStatsInstanceId                   CfprApManagedObjectId,
    cfprApAdaptorEthPortBySizeSmallStatsDn                           CfprApManagedObjectDn,
    cfprApAdaptorEthPortBySizeSmallStatsRn                           SnmpAdminString,
    cfprApAdaptorEthPortBySizeSmallStatsEquals64                     Unsigned64,
    cfprApAdaptorEthPortBySizeSmallStatsEquals64Delta                Counter64,
    cfprApAdaptorEthPortBySizeSmallStatsEquals64DeltaAvg             Unsigned64,
    cfprApAdaptorEthPortBySizeSmallStatsEquals64DeltaMax             Unsigned64,
    cfprApAdaptorEthPortBySizeSmallStatsEquals64DeltaMin             Unsigned64,
    cfprApAdaptorEthPortBySizeSmallStatsIntervals                    Gauge32,
    cfprApAdaptorEthPortBySizeSmallStatsLessThan1024                 Unsigned64,
    cfprApAdaptorEthPortBySizeSmallStatsLessThan1024Delta            Counter64,
    cfprApAdaptorEthPortBySizeSmallStatsLessThan1024DeltaAvg         Unsigned64,
    cfprApAdaptorEthPortBySizeSmallStatsLessThan1024DeltaMax         Unsigned64,
    cfprApAdaptorEthPortBySizeSmallStatsLessThan1024DeltaMin         Unsigned64,
    cfprApAdaptorEthPortBySizeSmallStatsLessThan128                  Unsigned64,
    cfprApAdaptorEthPortBySizeSmallStatsLessThan128Delta             Counter64,
    cfprApAdaptorEthPortBySizeSmallStatsLessThan128DeltaAvg          Unsigned64,
    cfprApAdaptorEthPortBySizeSmallStatsLessThan128DeltaMax          Unsigned64,
    cfprApAdaptorEthPortBySizeSmallStatsLessThan128DeltaMin          Unsigned64,
    cfprApAdaptorEthPortBySizeSmallStatsLessThan256                  Unsigned64,
    cfprApAdaptorEthPortBySizeSmallStatsLessThan256Delta             Counter64,
    cfprApAdaptorEthPortBySizeSmallStatsLessThan256DeltaAvg          Unsigned64,
    cfprApAdaptorEthPortBySizeSmallStatsLessThan256DeltaMax          Unsigned64,
    cfprApAdaptorEthPortBySizeSmallStatsLessThan256DeltaMin          Unsigned64,
    cfprApAdaptorEthPortBySizeSmallStatsLessThan512                  Unsigned64,
    cfprApAdaptorEthPortBySizeSmallStatsLessThan512Delta             Counter64,
    cfprApAdaptorEthPortBySizeSmallStatsLessThan512DeltaAvg          Unsigned64,
    cfprApAdaptorEthPortBySizeSmallStatsLessThan512DeltaMax          Unsigned64,
    cfprApAdaptorEthPortBySizeSmallStatsLessThan512DeltaMin          Unsigned64,
    cfprApAdaptorEthPortBySizeSmallStatsLessThan64                   Unsigned64,
    cfprApAdaptorEthPortBySizeSmallStatsLessThan64Delta              Counter64,
    cfprApAdaptorEthPortBySizeSmallStatsLessThan64DeltaAvg           Unsigned64,
    cfprApAdaptorEthPortBySizeSmallStatsLessThan64DeltaMax           Unsigned64,
    cfprApAdaptorEthPortBySizeSmallStatsLessThan64DeltaMin           Unsigned64,
    cfprApAdaptorEthPortBySizeSmallStatsSuspect                      TruthValue,
    cfprApAdaptorEthPortBySizeSmallStatsThresholded                  CfprApAdaptorEthPortBySizeSmallStatsThresholded,
    cfprApAdaptorEthPortBySizeSmallStatsTimeCollected                DateAndTime,
    cfprApAdaptorEthPortBySizeSmallStatsTrafficDirection             CfprApAdaptorAdapterStatsTrafficDir,
    cfprApAdaptorEthPortBySizeSmallStatsUpdate                       Gauge32
}

cfprApAdaptorEthPortBySizeSmallStatsInstanceId OBJECT-TYPE
    SYNTAX       CfprApManagedObjectId
    MAX-ACCESS   not-accessible
    STATUS       current
    DESCRIPTION
        "Instance identifier of the managed object."
    ::= { cfprApAdaptorEthPortBySizeSmallStatsEntry 1 }

cfprApAdaptorEthPortBySizeSmallStatsDn OBJECT-TYPE
    SYNTAX       CfprApManagedObjectDn
    MAX-ACCESS   read-only
    STATUS       current
    DESCRIPTION
        "Cisco Firepower adaptor:EthPortBySizeSmallStats:dn
        managed object property"
    ::= { cfprApAdaptorEthPortBySizeSmallStatsEntry 2 }

cfprApAdaptorEthPortBySizeSmallStatsRn OBJECT-TYPE
    SYNTAX       SnmpAdminString
    MAX-ACCESS   read-only
    STATUS       current
    DESCRIPTION
        "Cisco Firepower adaptor:EthPortBySizeSmallStats:rn
        managed object property"
    ::= { cfprApAdaptorEthPortBySizeSmallStatsEntry 3 }

cfprApAdaptorEthPortBySizeSmallStatsEquals64 OBJECT-TYPE
    SYNTAX       Unsigned64
    MAX-ACCESS   read-only
    STATUS       current
    DESCRIPTION
        "Cisco Firepower adaptor:EthPortBySizeSmallStats:equals64
        managed object property"
    ::= { cfprApAdaptorEthPortBySizeSmallStatsEntry 4 }

cfprApAdaptorEthPortBySizeSmallStatsEquals64Delta OBJECT-TYPE
    SYNTAX       Counter64
    MAX-ACCESS   read-only
    STATUS       current
    DESCRIPTION
        "Cisco Firepower adaptor:EthPortBySizeSmallStats:equals64Delta
        managed object property"
    ::= { cfprApAdaptorEthPortBySizeSmallStatsEntry 5 }

cfprApAdaptorEthPortBySizeSmallStatsEquals64DeltaAvg OBJECT-TYPE
    SYNTAX       Unsigned64
    MAX-ACCESS   read-only
    STATUS       current
    DESCRIPTION
        "Cisco Firepower adaptor:EthPortBySizeSmallStats:equals64DeltaAvg
        managed object property"
    ::= { cfprApAdaptorEthPortBySizeSmallStatsEntry 6 }

cfprApAdaptorEthPortBySizeSmallStatsEquals64DeltaMax OBJECT-TYPE
    SYNTAX       Unsigned64
    MAX-ACCESS   read-only
    STATUS       current
    DESCRIPTION
        "Cisco Firepower adaptor:EthPortBySizeSmallStats:equals64DeltaMax
        managed object property"
    ::= { cfprApAdaptorEthPortBySizeSmallStatsEntry 7 }

cfprApAdaptorEthPortBySizeSmallStatsEquals64DeltaMin OBJECT-TYPE
    SYNTAX       Unsigned64
    MAX-ACCESS   read-only
    STATUS       current
    DESCRIPTION
        "Cisco Firepower adaptor:EthPortBySizeSmallStats:equals64DeltaMin
        managed object property"
    ::= { cfprApAdaptorEthPortBySizeSmallStatsEntry 8 }

cfprApAdaptorEthPortBySizeSmallStatsIntervals OBJECT-TYPE
    SYNTAX       Gauge32
    MAX-ACCESS   read-only
    STATUS       current
    DESCRIPTION
        "Cisco Firepower adaptor:EthPortBySizeSmallStats:intervals
        managed object property"
    ::= { cfprApAdaptorEthPortBySizeSmallStatsEntry 9 }

cfprApAdaptorEthPortBySizeSmallStatsLessThan1024 OBJECT-TYPE
    SYNTAX       Unsigned64
    MAX-ACCESS   read-only
    STATUS       current
    DESCRIPTION
        "Cisco Firepower adaptor:EthPortBySizeSmallStats:lessThan1024
        managed object property"
    ::= { cfprApAdaptorEthPortBySizeSmallStatsEntry 10 }

cfprApAdaptorEthPortBySizeSmallStatsLessThan1024Delta OBJECT-TYPE
    SYNTAX       Counter64
    MAX-ACCESS   read-only
    STATUS       current
    DESCRIPTION
        "Cisco Firepower adaptor:EthPortBySizeSmallStats:lessThan1024Delta
         managed object property"
    ::= { cfprApAdaptorEthPortBySizeSmallStatsEntry 11 }

cfprApAdaptorEthPortBySizeSmallStatsLessThan1024DeltaAvg OBJECT-TYPE
    SYNTAX       Unsigned64
    MAX-ACCESS   read-only
    STATUS       current
    DESCRIPTION
        "Cisco Firepower adaptor:EthPortBySizeSmallStats:lessThan1024Delta
        Avg managed object property"
    ::= { cfprApAdaptorEthPortBySizeSmallStatsEntry 12 }

cfprApAdaptorEthPortBySizeSmallStatsLessThan1024DeltaMax OBJECT-TYPE
    SYNTAX       Unsigned64
    MAX-ACCESS   read-only
    STATUS       current
    DESCRIPTION
        "Cisco Firepower adaptor:EthPortBySizeSmallStats:lessThan1024Delta
        Max managed object property"
    ::= { cfprApAdaptorEthPortBySizeSmallStatsEntry 13 }

cfprApAdaptorEthPortBySizeSmallStatsLessThan1024DeltaMin OBJECT-TYPE
    SYNTAX       Unsigned64
    MAX-ACCESS   read-only
    STATUS       current
    DESCRIPTION
        "Cisco Firepower adaptor:EthPortBySizeSmallStats:lessThan1024Delta
        Min managed object property"
    ::= { cfprApAdaptorEthPortBySizeSmallStatsEntry 14 }

cfprApAdaptorEthPortBySizeSmallStatsLessThan128 OBJECT-TYPE
    SYNTAX       Unsigned64
    MAX-ACCESS   read-only
    STATUS       current
    DESCRIPTION
        "Cisco Firepower adaptor:EthPortBySizeSmallStats:lessThan128
        managed object property"
    ::= { cfprApAdaptorEthPortBySizeSmallStatsEntry 15 }

cfprApAdaptorEthPortBySizeSmallStatsLessThan128Delta OBJECT-TYPE
    SYNTAX       Counter64
    MAX-ACCESS   read-only
    STATUS       current
    DESCRIPTION
        "Cisco Firepower adaptor:EthPortBySizeSmallStats:lessThan128Delta
        managed object property"
    ::= { cfprApAdaptorEthPortBySizeSmallStatsEntry 16 }

cfprApAdaptorEthPortBySizeSmallStatsLessThan128DeltaAvg OBJECT-TYPE
    SYNTAX       Unsigned64
    MAX-ACCESS   read-only
    STATUS       current
    DESCRIPTION
        "Cisco Firepower adaptor:EthPortBySizeSmallStats:lessThan128DeltaA
        vg managed object property"
    ::= { cfprApAdaptorEthPortBySizeSmallStatsEntry 17 }

cfprApAdaptorEthPortBySizeSmallStatsLessThan128DeltaMax OBJECT-TYPE
    SYNTAX       Unsigned64
    MAX-ACCESS   read-only
    STATUS       current
    DESCRIPTION
        "Cisco Firepower adaptor:EthPortBySizeSmallStats:lessThan128DeltaM
        ax managed object property"
    ::= { cfprApAdaptorEthPortBySizeSmallStatsEntry 18 }

cfprApAdaptorEthPortBySizeSmallStatsLessThan128DeltaMin OBJECT-TYPE
    SYNTAX       Unsigned64
    MAX-ACCESS   read-only
    STATUS       current
    DESCRIPTION
        "Cisco Firepower adaptor:EthPortBySizeSmallStats:lessThan128DeltaM
        in managed object property"
    ::= { cfprApAdaptorEthPortBySizeSmallStatsEntry 19 }

cfprApAdaptorEthPortBySizeSmallStatsLessThan256 OBJECT-TYPE
    SYNTAX       Unsigned64
    MAX-ACCESS   read-only
    STATUS       current
    DESCRIPTION
        "Cisco Firepower adaptor:EthPortBySizeSmallStats:lessThan256
        managed object property"
    ::= { cfprApAdaptorEthPortBySizeSmallStatsEntry 20 }

cfprApAdaptorEthPortBySizeSmallStatsLessThan256Delta OBJECT-TYPE
    SYNTAX       Counter64
    MAX-ACCESS   read-only
    STATUS       current
    DESCRIPTION
        "Cisco Firepower adaptor:EthPortBySizeSmallStats:lessThan256Delta
        managed object property"
    ::= { cfprApAdaptorEthPortBySizeSmallStatsEntry 21 }

cfprApAdaptorEthPortBySizeSmallStatsLessThan256DeltaAvg OBJECT-TYPE
    SYNTAX       Unsigned64
    MAX-ACCESS   read-only
    STATUS       current
    DESCRIPTION
        "Cisco Firepower adaptor:EthPortBySizeSmallStats:lessThan256DeltaA
        vg managed object property"
    ::= { cfprApAdaptorEthPortBySizeSmallStatsEntry 22 }

cfprApAdaptorEthPortBySizeSmallStatsLessThan256DeltaMax OBJECT-TYPE
    SYNTAX       Unsigned64
    MAX-ACCESS   read-only
    STATUS       current
    DESCRIPTION
        "Cisco Firepower adaptor:EthPortBySizeSmallStats:lessThan256DeltaM
        ax managed object property"
    ::= { cfprApAdaptorEthPortBySizeSmallStatsEntry 23 }

cfprApAdaptorEthPortBySizeSmallStatsLessThan256DeltaMin OBJECT-TYPE
    SYNTAX       Unsigned64
    MAX-ACCESS   read-only
    STATUS       current
    DESCRIPTION
        "Cisco Firepower adaptor:EthPortBySizeSmallStats:lessThan256DeltaM
        in managed object property"
    ::= { cfprApAdaptorEthPortBySizeSmallStatsEntry 24 }

cfprApAdaptorEthPortBySizeSmallStatsLessThan512 OBJECT-TYPE
    SYNTAX       Unsigned64
    MAX-ACCESS   read-only
    STATUS       current
    DESCRIPTION
        "Cisco Firepower adaptor:EthPortBySizeSmallStats:lessThan512
        managed object property"
    ::= { cfprApAdaptorEthPortBySizeSmallStatsEntry 25 }

cfprApAdaptorEthPortBySizeSmallStatsLessThan512Delta OBJECT-TYPE
    SYNTAX       Counter64
    MAX-ACCESS   read-only
    STATUS       current
    DESCRIPTION
        "Cisco Firepower adaptor:EthPortBySizeSmallStats:lessThan512Delta
        managed object property"
    ::= { cfprApAdaptorEthPortBySizeSmallStatsEntry 26 }

cfprApAdaptorEthPortBySizeSmallStatsLessThan512DeltaAvg OBJECT-TYPE
    SYNTAX       Unsigned64
    MAX-ACCESS   read-only
    STATUS       current
    DESCRIPTION
        "Cisco Firepower adaptor:EthPortBySizeSmallStats:lessThan512DeltaA
        vg managed object property"
    ::= { cfprApAdaptorEthPortBySizeSmallStatsEntry 27 }

cfprApAdaptorEthPortBySizeSmallStatsLessThan512DeltaMax OBJECT-TYPE
    SYNTAX       Unsigned64
    MAX-ACCESS   read-only
    STATUS       current
    DESCRIPTION
        "Cisco Firepower adaptor:EthPortBySizeSmallStats:lessThan512DeltaM
        ax managed object property"
    ::= { cfprApAdaptorEthPortBySizeSmallStatsEntry 28 }

cfprApAdaptorEthPortBySizeSmallStatsLessThan512DeltaMin OBJECT-TYPE
    SYNTAX       Unsigned64
    MAX-ACCESS   read-only
    STATUS       current
    DESCRIPTION
        "Cisco Firepower adaptor:EthPortBySizeSmallStats:lessThan512DeltaM
        in managed object property"
    ::= { cfprApAdaptorEthPortBySizeSmallStatsEntry 29 }

cfprApAdaptorEthPortBySizeSmallStatsLessThan64 OBJECT-TYPE
    SYNTAX       Unsigned64
    MAX-ACCESS   read-only
    STATUS       current
    DESCRIPTION
        "Cisco Firepower adaptor:EthPortBySizeSmallStats:lessThan64
        managed object property"
    ::= { cfprApAdaptorEthPortBySizeSmallStatsEntry 30 }

cfprApAdaptorEthPortBySizeSmallStatsLessThan64Delta OBJECT-TYPE
    SYNTAX       Counter64
    MAX-ACCESS   read-only
    STATUS       current
    DESCRIPTION
        "Cisco Firepower adaptor:EthPortBySizeSmallStats:lessThan64Delta
        managed object property"
    ::= { cfprApAdaptorEthPortBySizeSmallStatsEntry 31 }

cfprApAdaptorEthPortBySizeSmallStatsLessThan64DeltaAvg OBJECT-TYPE
    SYNTAX       Unsigned64
    MAX-ACCESS   read-only
    STATUS       current
    DESCRIPTION
        "Cisco Firepower adaptor:EthPortBySizeSmallStats:lessThan64DeltaAv
        g managed object property"
    ::= { cfprApAdaptorEthPortBySizeSmallStatsEntry 32 }

cfprApAdaptorEthPortBySizeSmallStatsLessThan64DeltaMax OBJECT-TYPE
    SYNTAX       Unsigned64
    MAX-ACCESS   read-only
    STATUS       current
    DESCRIPTION
        "Cisco Firepower adaptor:EthPortBySizeSmallStats:lessThan64DeltaMa
        x managed object property"
    ::= { cfprApAdaptorEthPortBySizeSmallStatsEntry 33 }

cfprApAdaptorEthPortBySizeSmallStatsLessThan64DeltaMin OBJECT-TYPE
    SYNTAX       Unsigned64
    MAX-ACCESS   read-only
    STATUS       current
    DESCRIPTION
        "Cisco Firepower adaptor:EthPortBySizeSmallStats:lessThan64DeltaMi
        n managed object property"
    ::= { cfprApAdaptorEthPortBySizeSmallStatsEntry 34 }

cfprApAdaptorEthPortBySizeSmallStatsSuspect OBJECT-TYPE
    SYNTAX       TruthValue
    MAX-ACCESS   read-only
    STATUS       current
    DESCRIPTION
        "Cisco Firepower adaptor:EthPortBySizeSmallStats:suspect
        managed object property"
    ::= { cfprApAdaptorEthPortBySizeSmallStatsEntry 35 }

cfprApAdaptorEthPortBySizeSmallStatsThresholded OBJECT-TYPE
    SYNTAX       CfprApAdaptorEthPortBySizeSmallStatsThresholded
    MAX-ACCESS   read-only
    STATUS       current
    DESCRIPTION
        "Cisco Firepower adaptor:EthPortBySizeSmallStats:thresholded
        managed object property"
    ::= { cfprApAdaptorEthPortBySizeSmallStatsEntry 36 }

cfprApAdaptorEthPortBySizeSmallStatsTimeCollected OBJECT-TYPE
    SYNTAX       DateAndTime
    MAX-ACCESS   read-only
    STATUS       current
    DESCRIPTION
        "Cisco Firepower adaptor:EthPortBySizeSmallStats:timeCollected
        managed object property"
    ::= { cfprApAdaptorEthPortBySizeSmallStatsEntry 37 }

cfprApAdaptorEthPortBySizeSmallStatsTrafficDirection OBJECT-TYPE
    SYNTAX       CfprApAdaptorAdapterStatsTrafficDir
    MAX-ACCESS   read-only
    STATUS       current
    DESCRIPTION
        "Cisco Firepower adaptor:EthPortBySizeSmallStats:trafficDirection
        managed object property"
    ::= { cfprApAdaptorEthPortBySizeSmallStatsEntry 38 }

cfprApAdaptorEthPortBySizeSmallStatsUpdate OBJECT-TYPE
    SYNTAX       Gauge32
    MAX-ACCESS   read-only
    STATUS       current
    DESCRIPTION
        "Cisco Firepower adaptor:EthPortBySizeSmallStats:update
        managed object property"
    ::= { cfprApAdaptorEthPortBySizeSmallStatsEntry 39 }

cfprApAdaptorEthPortBySizeSmallStatsHistTable OBJECT-TYPE
    SYNTAX           SEQUENCE OF CfprApAdaptorEthPortBySizeSmallStatsHistEntry
    MAX-ACCESS       not-accessible
    STATUS           current
    DESCRIPTION
        "Cisco Firepower adaptor:EthPortBySizeSmallStatsHist
        managed object table"
    ::= { cfprApAdaptorObjects 13 }

cfprApAdaptorEthPortBySizeSmallStatsHistEntry OBJECT-TYPE
    SYNTAX           CfprApAdaptorEthPortBySizeSmallStatsHistEntry
    MAX-ACCESS       not-accessible
    STATUS           current
    DESCRIPTION
        "Entry for the cfprApAdaptorEthPortBySizeSmallStatsHistTable table."
    INDEX { cfprApAdaptorEthPortBySizeSmallStatsHistInstanceId }
    ::= { cfprApAdaptorEthPortBySizeSmallStatsHistTable 1 }

CfprApAdaptorEthPortBySizeSmallStatsHistEntry ::= SEQUENCE {
    cfprApAdaptorEthPortBySizeSmallStatsHistInstanceId               CfprApManagedObjectId,
    cfprApAdaptorEthPortBySizeSmallStatsHistDn                       CfprApManagedObjectDn,
    cfprApAdaptorEthPortBySizeSmallStatsHistRn                       SnmpAdminString,
    cfprApAdaptorEthPortBySizeSmallStatsHistEquals64                 Unsigned64,
    cfprApAdaptorEthPortBySizeSmallStatsHistEquals64Delta            Unsigned64,
    cfprApAdaptorEthPortBySizeSmallStatsHistEquals64DeltaAvg         Unsigned64,
    cfprApAdaptorEthPortBySizeSmallStatsHistEquals64DeltaMax         Unsigned64,
    cfprApAdaptorEthPortBySizeSmallStatsHistEquals64DeltaMin         Unsigned64,
    cfprApAdaptorEthPortBySizeSmallStatsHistId                       Unsigned64,
    cfprApAdaptorEthPortBySizeSmallStatsHistLessThan1024             Unsigned64,
    cfprApAdaptorEthPortBySizeSmallStatsHistLessThan1024Delta        Unsigned64,
    cfprApAdaptorEthPortBySizeSmallStatsHistLessThan1024DeltaAvg     Unsigned64,
    cfprApAdaptorEthPortBySizeSmallStatsHistLessThan1024DeltaMax     Unsigned64,
    cfprApAdaptorEthPortBySizeSmallStatsHistLessThan1024DeltaMin     Unsigned64,
    cfprApAdaptorEthPortBySizeSmallStatsHistLessThan128              Unsigned64,
    cfprApAdaptorEthPortBySizeSmallStatsHistLessThan128Delta         Unsigned64,
    cfprApAdaptorEthPortBySizeSmallStatsHistLessThan128DeltaAvg      Unsigned64,
    cfprApAdaptorEthPortBySizeSmallStatsHistLessThan128DeltaMax      Unsigned64,
    cfprApAdaptorEthPortBySizeSmallStatsHistLessThan128DeltaMin      Unsigned64,
    cfprApAdaptorEthPortBySizeSmallStatsHistLessThan256              Unsigned64,
    cfprApAdaptorEthPortBySizeSmallStatsHistLessThan256Delta         Unsigned64,
    cfprApAdaptorEthPortBySizeSmallStatsHistLessThan256DeltaAvg      Unsigned64,
    cfprApAdaptorEthPortBySizeSmallStatsHistLessThan256DeltaMax      Unsigned64,
    cfprApAdaptorEthPortBySizeSmallStatsHistLessThan256DeltaMin      Unsigned64,
    cfprApAdaptorEthPortBySizeSmallStatsHistLessThan512              Unsigned64,
    cfprApAdaptorEthPortBySizeSmallStatsHistLessThan512Delta         Unsigned64,
    cfprApAdaptorEthPortBySizeSmallStatsHistLessThan512DeltaAvg      Unsigned64,
    cfprApAdaptorEthPortBySizeSmallStatsHistLessThan512DeltaMax      Unsigned64,
    cfprApAdaptorEthPortBySizeSmallStatsHistLessThan512DeltaMin      Unsigned64,
    cfprApAdaptorEthPortBySizeSmallStatsHistLessThan64               Unsigned64,
    cfprApAdaptorEthPortBySizeSmallStatsHistLessThan64Delta          Unsigned64,
    cfprApAdaptorEthPortBySizeSmallStatsHistLessThan64DeltaAvg       Unsigned64,
    cfprApAdaptorEthPortBySizeSmallStatsHistLessThan64DeltaMax       Unsigned64,
    cfprApAdaptorEthPortBySizeSmallStatsHistLessThan64DeltaMin       Unsigned64,
    cfprApAdaptorEthPortBySizeSmallStatsHistMostRecent               TruthValue,
    cfprApAdaptorEthPortBySizeSmallStatsHistSuspect                  TruthValue,
    cfprApAdaptorEthPortBySizeSmallStatsHistThresholded              CfprApAdaptorEthPortBySizeSmallStatsHistThresholded,
    cfprApAdaptorEthPortBySizeSmallStatsHistTimeCollected            DateAndTime
}

cfprApAdaptorEthPortBySizeSmallStatsHistInstanceId OBJECT-TYPE
    SYNTAX       CfprApManagedObjectId
    MAX-ACCESS   not-accessible
    STATUS       current
    DESCRIPTION
        "Instance identifier of the managed object."
    ::= { cfprApAdaptorEthPortBySizeSmallStatsHistEntry 1 }

cfprApAdaptorEthPortBySizeSmallStatsHistDn OBJECT-TYPE
    SYNTAX       CfprApManagedObjectDn
    MAX-ACCESS   read-only
    STATUS       current
    DESCRIPTION
        "Cisco Firepower adaptor:EthPortBySizeSmallStatsHist:dn
        managed object property"
    ::= { cfprApAdaptorEthPortBySizeSmallStatsHistEntry 2 }

cfprApAdaptorEthPortBySizeSmallStatsHistRn OBJECT-TYPE
    SYNTAX       SnmpAdminString
    MAX-ACCESS   read-only
    STATUS       current
    DESCRIPTION
        "Cisco Firepower adaptor:EthPortBySizeSmallStatsHist:rn
        managed object property"
    ::= { cfprApAdaptorEthPortBySizeSmallStatsHistEntry 3 }

cfprApAdaptorEthPortBySizeSmallStatsHistEquals64 OBJECT-TYPE
    SYNTAX       Unsigned64
    MAX-ACCESS   read-only
    STATUS       current
    DESCRIPTION
        "Cisco Firepower adaptor:EthPortBySizeSmallStatsHist:equals64
        managed object property"
    ::= { cfprApAdaptorEthPortBySizeSmallStatsHistEntry 4 }

cfprApAdaptorEthPortBySizeSmallStatsHistEquals64Delta OBJECT-TYPE
    SYNTAX       Unsigned64
    MAX-ACCESS   read-only
    STATUS       current
    DESCRIPTION
        "Cisco Firepower adaptor:EthPortBySizeSmallStatsHist:equals64Delta
         managed object property"
    ::= { cfprApAdaptorEthPortBySizeSmallStatsHistEntry 5 }

cfprApAdaptorEthPortBySizeSmallStatsHistEquals64DeltaAvg OBJECT-TYPE
    SYNTAX       Unsigned64
    MAX-ACCESS   read-only
    STATUS       current
    DESCRIPTION
        "Cisco Firepower adaptor:EthPortBySizeSmallStatsHist:equals64Delta
        Avg managed object property"
    ::= { cfprApAdaptorEthPortBySizeSmallStatsHistEntry 6 }

cfprApAdaptorEthPortBySizeSmallStatsHistEquals64DeltaMax OBJECT-TYPE
    SYNTAX       Unsigned64
    MAX-ACCESS   read-only
    STATUS       current
    DESCRIPTION
        "Cisco Firepower adaptor:EthPortBySizeSmallStatsHist:equals64Delta
        Max managed object property"
    ::= { cfprApAdaptorEthPortBySizeSmallStatsHistEntry 7 }

cfprApAdaptorEthPortBySizeSmallStatsHistEquals64DeltaMin OBJECT-TYPE
    SYNTAX       Unsigned64
    MAX-ACCESS   read-only
    STATUS       current
    DESCRIPTION
        "Cisco Firepower adaptor:EthPortBySizeSmallStatsHist:equals64Delta
        Min managed object property"
    ::= { cfprApAdaptorEthPortBySizeSmallStatsHistEntry 8 }

cfprApAdaptorEthPortBySizeSmallStatsHistId OBJECT-TYPE
    SYNTAX       Unsigned64
    MAX-ACCESS   read-only
    STATUS       current
    DESCRIPTION
        "Cisco Firepower adaptor:EthPortBySizeSmallStatsHist:id
        managed object property"
    ::= { cfprApAdaptorEthPortBySizeSmallStatsHistEntry 9 }

cfprApAdaptorEthPortBySizeSmallStatsHistLessThan1024 OBJECT-TYPE
    SYNTAX       Unsigned64
    MAX-ACCESS   read-only
    STATUS       current
    DESCRIPTION
        "Cisco Firepower adaptor:EthPortBySizeSmallStatsHist:lessThan1024
        managed object property"
    ::= { cfprApAdaptorEthPortBySizeSmallStatsHistEntry 10 }

cfprApAdaptorEthPortBySizeSmallStatsHistLessThan1024Delta OBJECT-TYPE
    SYNTAX       Unsigned64
    MAX-ACCESS   read-only
    STATUS       current
    DESCRIPTION
        "Cisco Firepower adaptor:EthPortBySizeSmallStatsHist:lessThan1024D
        elta managed object property"
    ::= { cfprApAdaptorEthPortBySizeSmallStatsHistEntry 11 }

cfprApAdaptorEthPortBySizeSmallStatsHistLessThan1024DeltaAvg OBJECT-TYPE
    SYNTAX       Unsigned64
    MAX-ACCESS   read-only
    STATUS       current
    DESCRIPTION
        "Cisco Firepower adaptor:EthPortBySizeSmallStatsHist:lessThan1024D
        eltaAvg managed object property"
    ::= { cfprApAdaptorEthPortBySizeSmallStatsHistEntry 12 }

cfprApAdaptorEthPortBySizeSmallStatsHistLessThan1024DeltaMax OBJECT-TYPE
    SYNTAX       Unsigned64
    MAX-ACCESS   read-only
    STATUS       current
    DESCRIPTION
        "Cisco Firepower adaptor:EthPortBySizeSmallStatsHist:lessThan1024D
        eltaMax managed object property"
    ::= { cfprApAdaptorEthPortBySizeSmallStatsHistEntry 13 }

cfprApAdaptorEthPortBySizeSmallStatsHistLessThan1024DeltaMin OBJECT-TYPE
    SYNTAX       Unsigned64
    MAX-ACCESS   read-only
    STATUS       current
    DESCRIPTION
        "Cisco Firepower adaptor:EthPortBySizeSmallStatsHist:lessThan1024D
        eltaMin managed object property"
    ::= { cfprApAdaptorEthPortBySizeSmallStatsHistEntry 14 }

cfprApAdaptorEthPortBySizeSmallStatsHistLessThan128 OBJECT-TYPE
    SYNTAX       Unsigned64
    MAX-ACCESS   read-only
    STATUS       current
    DESCRIPTION
        "Cisco Firepower adaptor:EthPortBySizeSmallStatsHist:lessThan128
        managed object property"
    ::= { cfprApAdaptorEthPortBySizeSmallStatsHistEntry 15 }

cfprApAdaptorEthPortBySizeSmallStatsHistLessThan128Delta OBJECT-TYPE
    SYNTAX       Unsigned64
    MAX-ACCESS   read-only
    STATUS       current
    DESCRIPTION
        "Cisco Firepower adaptor:EthPortBySizeSmallStatsHist:lessThan128De
        lta managed object property"
    ::= { cfprApAdaptorEthPortBySizeSmallStatsHistEntry 16 }

cfprApAdaptorEthPortBySizeSmallStatsHistLessThan128DeltaAvg OBJECT-TYPE
    SYNTAX       Unsigned64
    MAX-ACCESS   read-only
    STATUS       current
    DESCRIPTION
        "Cisco Firepower adaptor:EthPortBySizeSmallStatsHist:lessThan128De
        ltaAvg managed object property"
    ::= { cfprApAdaptorEthPortBySizeSmallStatsHistEntry 17 }

cfprApAdaptorEthPortBySizeSmallStatsHistLessThan128DeltaMax OBJECT-TYPE
    SYNTAX       Unsigned64
    MAX-ACCESS   read-only
    STATUS       current
    DESCRIPTION
        "Cisco Firepower adaptor:EthPortBySizeSmallStatsHist:lessThan128De
        ltaMax managed object property"
    ::= { cfprApAdaptorEthPortBySizeSmallStatsHistEntry 18 }

cfprApAdaptorEthPortBySizeSmallStatsHistLessThan128DeltaMin OBJECT-TYPE
    SYNTAX       Unsigned64
    MAX-ACCESS   read-only
    STATUS       current
    DESCRIPTION
        "Cisco Firepower adaptor:EthPortBySizeSmallStatsHist:lessThan128De
        ltaMin managed object property"
    ::= { cfprApAdaptorEthPortBySizeSmallStatsHistEntry 19 }

cfprApAdaptorEthPortBySizeSmallStatsHistLessThan256 OBJECT-TYPE
    SYNTAX       Unsigned64
    MAX-ACCESS   read-only
    STATUS       current
    DESCRIPTION
        "Cisco Firepower adaptor:EthPortBySizeSmallStatsHist:lessThan256
        managed object property"
    ::= { cfprApAdaptorEthPortBySizeSmallStatsHistEntry 20 }

cfprApAdaptorEthPortBySizeSmallStatsHistLessThan256Delta OBJECT-TYPE
    SYNTAX       Unsigned64
    MAX-ACCESS   read-only
    STATUS       current
    DESCRIPTION
        "Cisco Firepower adaptor:EthPortBySizeSmallStatsHist:lessThan256De
        lta managed object property"
    ::= { cfprApAdaptorEthPortBySizeSmallStatsHistEntry 21 }

cfprApAdaptorEthPortBySizeSmallStatsHistLessThan256DeltaAvg OBJECT-TYPE
    SYNTAX       Unsigned64
    MAX-ACCESS   read-only
    STATUS       current
    DESCRIPTION
        "Cisco Firepower adaptor:EthPortBySizeSmallStatsHist:lessThan256De
        ltaAvg managed object property"
    ::= { cfprApAdaptorEthPortBySizeSmallStatsHistEntry 22 }

cfprApAdaptorEthPortBySizeSmallStatsHistLessThan256DeltaMax OBJECT-TYPE
    SYNTAX       Unsigned64
    MAX-ACCESS   read-only
    STATUS       current
    DESCRIPTION
        "Cisco Firepower adaptor:EthPortBySizeSmallStatsHist:lessThan256De
        ltaMax managed object property"
    ::= { cfprApAdaptorEthPortBySizeSmallStatsHistEntry 23 }

cfprApAdaptorEthPortBySizeSmallStatsHistLessThan256DeltaMin OBJECT-TYPE
    SYNTAX       Unsigned64
    MAX-ACCESS   read-only
    STATUS       current
    DESCRIPTION
        "Cisco Firepower adaptor:EthPortBySizeSmallStatsHist:lessThan256De
        ltaMin managed object property"
    ::= { cfprApAdaptorEthPortBySizeSmallStatsHistEntry 24 }

cfprApAdaptorEthPortBySizeSmallStatsHistLessThan512 OBJECT-TYPE
    SYNTAX       Unsigned64
    MAX-ACCESS   read-only
    STATUS       current
    DESCRIPTION
        "Cisco Firepower adaptor:EthPortBySizeSmallStatsHist:lessThan512
        managed object property"
    ::= { cfprApAdaptorEthPortBySizeSmallStatsHistEntry 25 }

cfprApAdaptorEthPortBySizeSmallStatsHistLessThan512Delta OBJECT-TYPE
    SYNTAX       Unsigned64
    MAX-ACCESS   read-only
    STATUS       current
    DESCRIPTION
        "Cisco Firepower adaptor:EthPortBySizeSmallStatsHist:lessThan512De
        lta managed object property"
    ::= { cfprApAdaptorEthPortBySizeSmallStatsHistEntry 26 }

cfprApAdaptorEthPortBySizeSmallStatsHistLessThan512DeltaAvg OBJECT-TYPE
    SYNTAX       Unsigned64
    MAX-ACCESS   read-only
    STATUS       current
    DESCRIPTION
        "Cisco Firepower adaptor:EthPortBySizeSmallStatsHist:lessThan512De
        ltaAvg managed object property"
    ::= { cfprApAdaptorEthPortBySizeSmallStatsHistEntry 27 }

cfprApAdaptorEthPortBySizeSmallStatsHistLessThan512DeltaMax OBJECT-TYPE
    SYNTAX       Unsigned64
    MAX-ACCESS   read-only
    STATUS       current
    DESCRIPTION
        "Cisco Firepower adaptor:EthPortBySizeSmallStatsHist:lessThan512De
        ltaMax managed object property"
    ::= { cfprApAdaptorEthPortBySizeSmallStatsHistEntry 28 }

cfprApAdaptorEthPortBySizeSmallStatsHistLessThan512DeltaMin OBJECT-TYPE
    SYNTAX       Unsigned64
    MAX-ACCESS   read-only
    STATUS       current
    DESCRIPTION
        "Cisco Firepower adaptor:EthPortBySizeSmallStatsHist:lessThan512De
        ltaMin managed object property"
    ::= { cfprApAdaptorEthPortBySizeSmallStatsHistEntry 29 }

cfprApAdaptorEthPortBySizeSmallStatsHistLessThan64 OBJECT-TYPE
    SYNTAX       Unsigned64
    MAX-ACCESS   read-only
    STATUS       current
    DESCRIPTION
        "Cisco Firepower adaptor:EthPortBySizeSmallStatsHist:lessThan64
        managed object property"
    ::= { cfprApAdaptorEthPortBySizeSmallStatsHistEntry 30 }

cfprApAdaptorEthPortBySizeSmallStatsHistLessThan64Delta OBJECT-TYPE
    SYNTAX       Unsigned64
    MAX-ACCESS   read-only
    STATUS       current
    DESCRIPTION
        "Cisco Firepower adaptor:EthPortBySizeSmallStatsHist:lessThan64Del
        ta managed object property"
    ::= { cfprApAdaptorEthPortBySizeSmallStatsHistEntry 31 }

cfprApAdaptorEthPortBySizeSmallStatsHistLessThan64DeltaAvg OBJECT-TYPE
    SYNTAX       Unsigned64
    MAX-ACCESS   read-only
    STATUS       current
    DESCRIPTION
        "Cisco Firepower adaptor:EthPortBySizeSmallStatsHist:lessThan64Del
        taAvg managed object property"
    ::= { cfprApAdaptorEthPortBySizeSmallStatsHistEntry 32 }

cfprApAdaptorEthPortBySizeSmallStatsHistLessThan64DeltaMax OBJECT-TYPE
    SYNTAX       Unsigned64
    MAX-ACCESS   read-only
    STATUS       current
    DESCRIPTION
        "Cisco Firepower adaptor:EthPortBySizeSmallStatsHist:lessThan64Del
        taMax managed object property"
    ::= { cfprApAdaptorEthPortBySizeSmallStatsHistEntry 33 }

cfprApAdaptorEthPortBySizeSmallStatsHistLessThan64DeltaMin OBJECT-TYPE
    SYNTAX       Unsigned64
    MAX-ACCESS   read-only
    STATUS       current
    DESCRIPTION
        "Cisco Firepower adaptor:EthPortBySizeSmallStatsHist:lessThan64Del
        taMin managed object property"
    ::= { cfprApAdaptorEthPortBySizeSmallStatsHistEntry 34 }

cfprApAdaptorEthPortBySizeSmallStatsHistMostRecent OBJECT-TYPE
    SYNTAX       TruthValue
    MAX-ACCESS   read-only
    STATUS       current
    DESCRIPTION
        "Cisco Firepower adaptor:EthPortBySizeSmallStatsHist:mostRecent
        managed object property"
    ::= { cfprApAdaptorEthPortBySizeSmallStatsHistEntry 35 }

cfprApAdaptorEthPortBySizeSmallStatsHistSuspect OBJECT-TYPE
    SYNTAX       TruthValue
    MAX-ACCESS   read-only
    STATUS       current
    DESCRIPTION
        "Cisco Firepower adaptor:EthPortBySizeSmallStatsHist:suspect
        managed object property"
    ::= { cfprApAdaptorEthPortBySizeSmallStatsHistEntry 36 }

cfprApAdaptorEthPortBySizeSmallStatsHistThresholded OBJECT-TYPE
    SYNTAX       CfprApAdaptorEthPortBySizeSmallStatsHistThresholded
    MAX-ACCESS   read-only
    STATUS       current
    DESCRIPTION
        "Cisco Firepower adaptor:EthPortBySizeSmallStatsHist:thresholded
        managed object property"
    ::= { cfprApAdaptorEthPortBySizeSmallStatsHistEntry 37 }

cfprApAdaptorEthPortBySizeSmallStatsHistTimeCollected OBJECT-TYPE
    SYNTAX       DateAndTime
    MAX-ACCESS   read-only
    STATUS       current
    DESCRIPTION
        "Cisco Firepower adaptor:EthPortBySizeSmallStatsHist:timeCollected
         managed object property"
    ::= { cfprApAdaptorEthPortBySizeSmallStatsHistEntry 38 }

cfprApAdaptorEthPortErrStatsTable OBJECT-TYPE
    SYNTAX           SEQUENCE OF CfprApAdaptorEthPortErrStatsEntry
    MAX-ACCESS       not-accessible
    STATUS           current
    DESCRIPTION
        "Cisco Firepower adaptor:EthPortErrStats managed object table"
    ::= { cfprApAdaptorObjects 14 }

cfprApAdaptorEthPortErrStatsEntry OBJECT-TYPE
    SYNTAX           CfprApAdaptorEthPortErrStatsEntry
    MAX-ACCESS       not-accessible
    STATUS           current
    DESCRIPTION
        "Entry for the cfprApAdaptorEthPortErrStatsTable table."
    INDEX { cfprApAdaptorEthPortErrStatsInstanceId }
    ::= { cfprApAdaptorEthPortErrStatsTable 1 }

CfprApAdaptorEthPortErrStatsEntry ::= SEQUENCE {
    cfprApAdaptorEthPortErrStatsInstanceId                           CfprApManagedObjectId,
    cfprApAdaptorEthPortErrStatsDn                                   CfprApManagedObjectDn,
    cfprApAdaptorEthPortErrStatsRn                                   SnmpAdminString,
    cfprApAdaptorEthPortErrStatsBadCrcPackets                        Unsigned64,
    cfprApAdaptorEthPortErrStatsBadCrcPacketsDelta                   Counter64,
    cfprApAdaptorEthPortErrStatsBadCrcPacketsDeltaAvg                Unsigned64,
    cfprApAdaptorEthPortErrStatsBadCrcPacketsDeltaMax                Unsigned64,
    cfprApAdaptorEthPortErrStatsBadCrcPacketsDeltaMin                Unsigned64,
    cfprApAdaptorEthPortErrStatsBadLengthPackets                     Unsigned64,
    cfprApAdaptorEthPortErrStatsBadLengthPacketsDelta                Counter64,
    cfprApAdaptorEthPortErrStatsBadLengthPacketsDeltaAvg             Unsigned64,
    cfprApAdaptorEthPortErrStatsBadLengthPacketsDeltaMax             Unsigned64,
    cfprApAdaptorEthPortErrStatsBadLengthPacketsDeltaMin             Unsigned64,
    cfprApAdaptorEthPortErrStatsIntervals                            Gauge32,
    cfprApAdaptorEthPortErrStatsMacDiscardedPackets                  Unsigned64,
    cfprApAdaptorEthPortErrStatsMacDiscardedPacketsDelta             Counter64,
    cfprApAdaptorEthPortErrStatsMacDiscardedPacketsDeltaAvg          Unsigned64,
    cfprApAdaptorEthPortErrStatsMacDiscardedPacketsDeltaMax          Unsigned64,
    cfprApAdaptorEthPortErrStatsMacDiscardedPacketsDeltaMin          Unsigned64,
    cfprApAdaptorEthPortErrStatsSuspect                              TruthValue,
    cfprApAdaptorEthPortErrStatsThresholded                          CfprApAdaptorEthPortErrStatsThresholded,
    cfprApAdaptorEthPortErrStatsTimeCollected                        DateAndTime,
    cfprApAdaptorEthPortErrStatsTrafficDirection                     CfprApAdaptorAdapterStatsTrafficDir,
    cfprApAdaptorEthPortErrStatsUpdate                               Gauge32
}

cfprApAdaptorEthPortErrStatsInstanceId OBJECT-TYPE
    SYNTAX       CfprApManagedObjectId
    MAX-ACCESS   not-accessible
    STATUS       current
    DESCRIPTION
        "Instance identifier of the managed object."
    ::= { cfprApAdaptorEthPortErrStatsEntry 1 }

cfprApAdaptorEthPortErrStatsDn OBJECT-TYPE
    SYNTAX       CfprApManagedObjectDn
    MAX-ACCESS   read-only
    STATUS       current
    DESCRIPTION
        "Cisco Firepower adaptor:EthPortErrStats:dn managed
        object property"
    ::= { cfprApAdaptorEthPortErrStatsEntry 2 }

cfprApAdaptorEthPortErrStatsRn OBJECT-TYPE
    SYNTAX       SnmpAdminString
    MAX-ACCESS   read-only
    STATUS       current
    DESCRIPTION
        "Cisco Firepower adaptor:EthPortErrStats:rn managed
        object property"
    ::= { cfprApAdaptorEthPortErrStatsEntry 3 }

cfprApAdaptorEthPortErrStatsBadCrcPackets OBJECT-TYPE
    SYNTAX       Unsigned64
    MAX-ACCESS   read-only
    STATUS       current
    DESCRIPTION
        "Cisco Firepower adaptor:EthPortErrStats:badCrcPackets
        managed object property"
    ::= { cfprApAdaptorEthPortErrStatsEntry 4 }

cfprApAdaptorEthPortErrStatsBadCrcPacketsDelta OBJECT-TYPE
    SYNTAX       Counter64
    MAX-ACCESS   read-only
    STATUS       current
    DESCRIPTION
        "Cisco Firepower adaptor:EthPortErrStats:badCrcPacketsDelta
        managed object property"
    ::= { cfprApAdaptorEthPortErrStatsEntry 5 }

cfprApAdaptorEthPortErrStatsBadCrcPacketsDeltaAvg OBJECT-TYPE
    SYNTAX       Unsigned64
    MAX-ACCESS   read-only
    STATUS       current
    DESCRIPTION
        "Cisco Firepower adaptor:EthPortErrStats:badCrcPacketsDeltaAvg
        managed object property"
    ::= { cfprApAdaptorEthPortErrStatsEntry 6 }

cfprApAdaptorEthPortErrStatsBadCrcPacketsDeltaMax OBJECT-TYPE
    SYNTAX       Unsigned64
    MAX-ACCESS   read-only
    STATUS       current
    DESCRIPTION
        "Cisco Firepower adaptor:EthPortErrStats:badCrcPacketsDeltaMax
        managed object property"
    ::= { cfprApAdaptorEthPortErrStatsEntry 7 }

cfprApAdaptorEthPortErrStatsBadCrcPacketsDeltaMin OBJECT-TYPE
    SYNTAX       Unsigned64
    MAX-ACCESS   read-only
    STATUS       current
    DESCRIPTION
        "Cisco Firepower adaptor:EthPortErrStats:badCrcPacketsDeltaMin
        managed object property"
    ::= { cfprApAdaptorEthPortErrStatsEntry 8 }

cfprApAdaptorEthPortErrStatsBadLengthPackets OBJECT-TYPE
    SYNTAX       Unsigned64
    MAX-ACCESS   read-only
    STATUS       current
    DESCRIPTION
        "Cisco Firepower adaptor:EthPortErrStats:badLengthPackets
        managed object property"
    ::= { cfprApAdaptorEthPortErrStatsEntry 9 }

cfprApAdaptorEthPortErrStatsBadLengthPacketsDelta OBJECT-TYPE
    SYNTAX       Counter64
    MAX-ACCESS   read-only
    STATUS       current
    DESCRIPTION
        "Cisco Firepower adaptor:EthPortErrStats:badLengthPacketsDelta
        managed object property"
    ::= { cfprApAdaptorEthPortErrStatsEntry 10 }

cfprApAdaptorEthPortErrStatsBadLengthPacketsDeltaAvg OBJECT-TYPE
    SYNTAX       Unsigned64
    MAX-ACCESS   read-only
    STATUS       current
    DESCRIPTION
        "Cisco Firepower adaptor:EthPortErrStats:badLengthPacketsDeltaAvg
        managed object property"
    ::= { cfprApAdaptorEthPortErrStatsEntry 11 }

cfprApAdaptorEthPortErrStatsBadLengthPacketsDeltaMax OBJECT-TYPE
    SYNTAX       Unsigned64
    MAX-ACCESS   read-only
    STATUS       current
    DESCRIPTION
        "Cisco Firepower adaptor:EthPortErrStats:badLengthPacketsDeltaMax
        managed object property"
    ::= { cfprApAdaptorEthPortErrStatsEntry 12 }

cfprApAdaptorEthPortErrStatsBadLengthPacketsDeltaMin OBJECT-TYPE
    SYNTAX       Unsigned64
    MAX-ACCESS   read-only
    STATUS       current
    DESCRIPTION
        "Cisco Firepower adaptor:EthPortErrStats:badLengthPacketsDeltaMin
        managed object property"
    ::= { cfprApAdaptorEthPortErrStatsEntry 13 }

cfprApAdaptorEthPortErrStatsIntervals OBJECT-TYPE
    SYNTAX       Gauge32
    MAX-ACCESS   read-only
    STATUS       current
    DESCRIPTION
        "Cisco Firepower adaptor:EthPortErrStats:intervals
        managed object property"
    ::= { cfprApAdaptorEthPortErrStatsEntry 14 }

cfprApAdaptorEthPortErrStatsMacDiscardedPackets OBJECT-TYPE
    SYNTAX       Unsigned64
    MAX-ACCESS   read-only
    STATUS       current
    DESCRIPTION
        "Cisco Firepower adaptor:EthPortErrStats:macDiscardedPackets
        managed object property"
    ::= { cfprApAdaptorEthPortErrStatsEntry 15 }

cfprApAdaptorEthPortErrStatsMacDiscardedPacketsDelta OBJECT-TYPE
    SYNTAX       Counter64
    MAX-ACCESS   read-only
    STATUS       current
    DESCRIPTION
        "Cisco Firepower adaptor:EthPortErrStats:macDiscardedPacketsDelta
        managed object property"
    ::= { cfprApAdaptorEthPortErrStatsEntry 16 }

cfprApAdaptorEthPortErrStatsMacDiscardedPacketsDeltaAvg OBJECT-TYPE
    SYNTAX       Unsigned64
    MAX-ACCESS   read-only
    STATUS       current
    DESCRIPTION
        "Cisco Firepower adaptor:EthPortErrStats:macDiscardedPacketsDeltaA
        vg managed object property"
    ::= { cfprApAdaptorEthPortErrStatsEntry 17 }

cfprApAdaptorEthPortErrStatsMacDiscardedPacketsDeltaMax OBJECT-TYPE
    SYNTAX       Unsigned64
    MAX-ACCESS   read-only
    STATUS       current
    DESCRIPTION
        "Cisco Firepower adaptor:EthPortErrStats:macDiscardedPacketsDeltaM
        ax managed object property"
    ::= { cfprApAdaptorEthPortErrStatsEntry 18 }

cfprApAdaptorEthPortErrStatsMacDiscardedPacketsDeltaMin OBJECT-TYPE
    SYNTAX       Unsigned64
    MAX-ACCESS   read-only
    STATUS       current
    DESCRIPTION
        "Cisco Firepower adaptor:EthPortErrStats:macDiscardedPacketsDeltaM
        in managed object property"
    ::= { cfprApAdaptorEthPortErrStatsEntry 19 }

cfprApAdaptorEthPortErrStatsSuspect OBJECT-TYPE
    SYNTAX       TruthValue
    MAX-ACCESS   read-only
    STATUS       current
    DESCRIPTION
        "Cisco Firepower adaptor:EthPortErrStats:suspect
        managed object property"
    ::= { cfprApAdaptorEthPortErrStatsEntry 20 }

cfprApAdaptorEthPortErrStatsThresholded OBJECT-TYPE
    SYNTAX       CfprApAdaptorEthPortErrStatsThresholded
    MAX-ACCESS   read-only
    STATUS       current
    DESCRIPTION
        "Cisco Firepower adaptor:EthPortErrStats:thresholded
        managed object property"
    ::= { cfprApAdaptorEthPortErrStatsEntry 21 }

cfprApAdaptorEthPortErrStatsTimeCollected OBJECT-TYPE
    SYNTAX       DateAndTime
    MAX-ACCESS   read-only
    STATUS       current
    DESCRIPTION
        "Cisco Firepower adaptor:EthPortErrStats:timeCollected
        managed object property"
    ::= { cfprApAdaptorEthPortErrStatsEntry 22 }

cfprApAdaptorEthPortErrStatsTrafficDirection OBJECT-TYPE
    SYNTAX       CfprApAdaptorAdapterStatsTrafficDir
    MAX-ACCESS   read-only
    STATUS       current
    DESCRIPTION
        "Cisco Firepower adaptor:EthPortErrStats:trafficDirection
        managed object property"
    ::= { cfprApAdaptorEthPortErrStatsEntry 23 }

cfprApAdaptorEthPortErrStatsUpdate OBJECT-TYPE
    SYNTAX       Gauge32
    MAX-ACCESS   read-only
    STATUS       current
    DESCRIPTION
        "Cisco Firepower adaptor:EthPortErrStats:update
        managed object property"
    ::= { cfprApAdaptorEthPortErrStatsEntry 24 }

cfprApAdaptorEthPortErrStatsHistTable OBJECT-TYPE
    SYNTAX           SEQUENCE OF CfprApAdaptorEthPortErrStatsHistEntry
    MAX-ACCESS       not-accessible
    STATUS           current
    DESCRIPTION
        "Cisco Firepower adaptor:EthPortErrStatsHist managed object table"
    ::= { cfprApAdaptorObjects 15 }

cfprApAdaptorEthPortErrStatsHistEntry OBJECT-TYPE
    SYNTAX           CfprApAdaptorEthPortErrStatsHistEntry
    MAX-ACCESS       not-accessible
    STATUS           current
    DESCRIPTION
        "Entry for the cfprApAdaptorEthPortErrStatsHistTable table."
    INDEX { cfprApAdaptorEthPortErrStatsHistInstanceId }
    ::= { cfprApAdaptorEthPortErrStatsHistTable 1 }

CfprApAdaptorEthPortErrStatsHistEntry ::= SEQUENCE {
    cfprApAdaptorEthPortErrStatsHistInstanceId                       CfprApManagedObjectId,
    cfprApAdaptorEthPortErrStatsHistDn                               CfprApManagedObjectDn,
    cfprApAdaptorEthPortErrStatsHistRn                               SnmpAdminString,
    cfprApAdaptorEthPortErrStatsHistBadCrcPackets                    Unsigned64,
    cfprApAdaptorEthPortErrStatsHistBadCrcPacketsDelta               Unsigned64,
    cfprApAdaptorEthPortErrStatsHistBadCrcPacketsDeltaAvg            Unsigned64,
    cfprApAdaptorEthPortErrStatsHistBadCrcPacketsDeltaMax            Unsigned64,
    cfprApAdaptorEthPortErrStatsHistBadCrcPacketsDeltaMin            Unsigned64,
    cfprApAdaptorEthPortErrStatsHistBadLengthPackets                 Unsigned64,
    cfprApAdaptorEthPortErrStatsHistBadLengthPacketsDelta            Unsigned64,
    cfprApAdaptorEthPortErrStatsHistBadLengthPacketsDeltaAvg         Unsigned64,
    cfprApAdaptorEthPortErrStatsHistBadLengthPacketsDeltaMax         Unsigned64,
    cfprApAdaptorEthPortErrStatsHistBadLengthPacketsDeltaMin         Unsigned64,
    cfprApAdaptorEthPortErrStatsHistId                               Unsigned64,
    cfprApAdaptorEthPortErrStatsHistMacDiscardedPackets              Unsigned64,
    cfprApAdaptorEthPortErrStatsHistMacDiscardedPacketsDelta         Unsigned64,
    cfprApAdaptorEthPortErrStatsHistMacDiscardedPacketsDeltaAvg      Unsigned64,
    cfprApAdaptorEthPortErrStatsHistMacDiscardedPacketsDeltaMax      Unsigned64,
    cfprApAdaptorEthPortErrStatsHistMacDiscardedPacketsDeltaMin      Unsigned64,
    cfprApAdaptorEthPortErrStatsHistMostRecent                       TruthValue,
    cfprApAdaptorEthPortErrStatsHistSuspect                          TruthValue,
    cfprApAdaptorEthPortErrStatsHistThresholded                      CfprApAdaptorEthPortErrStatsHistThresholded,
    cfprApAdaptorEthPortErrStatsHistTimeCollected                    DateAndTime
}

cfprApAdaptorEthPortErrStatsHistInstanceId OBJECT-TYPE
    SYNTAX       CfprApManagedObjectId
    MAX-ACCESS   not-accessible
    STATUS       current
    DESCRIPTION
        "Instance identifier of the managed object."
    ::= { cfprApAdaptorEthPortErrStatsHistEntry 1 }

cfprApAdaptorEthPortErrStatsHistDn OBJECT-TYPE
    SYNTAX       CfprApManagedObjectDn
    MAX-ACCESS   read-only
    STATUS       current
    DESCRIPTION
        "Cisco Firepower adaptor:EthPortErrStatsHist:dn
        managed object property"
    ::= { cfprApAdaptorEthPortErrStatsHistEntry 2 }

cfprApAdaptorEthPortErrStatsHistRn OBJECT-TYPE
    SYNTAX       SnmpAdminString
    MAX-ACCESS   read-only
    STATUS       current
    DESCRIPTION
        "Cisco Firepower adaptor:EthPortErrStatsHist:rn
        managed object property"
    ::= { cfprApAdaptorEthPortErrStatsHistEntry 3 }

cfprApAdaptorEthPortErrStatsHistBadCrcPackets OBJECT-TYPE
    SYNTAX       Unsigned64
    MAX-ACCESS   read-only
    STATUS       current
    DESCRIPTION
        "Cisco Firepower adaptor:EthPortErrStatsHist:badCrcPackets
        managed object property"
    ::= { cfprApAdaptorEthPortErrStatsHistEntry 4 }

cfprApAdaptorEthPortErrStatsHistBadCrcPacketsDelta OBJECT-TYPE
    SYNTAX       Unsigned64
    MAX-ACCESS   read-only
    STATUS       current
    DESCRIPTION
        "Cisco Firepower adaptor:EthPortErrStatsHist:badCrcPacketsDelta
        managed object property"
    ::= { cfprApAdaptorEthPortErrStatsHistEntry 5 }

cfprApAdaptorEthPortErrStatsHistBadCrcPacketsDeltaAvg OBJECT-TYPE
    SYNTAX       Unsigned64
    MAX-ACCESS   read-only
    STATUS       current
    DESCRIPTION
        "Cisco Firepower adaptor:EthPortErrStatsHist:badCrcPacketsDeltaAvg
         managed object property"
    ::= { cfprApAdaptorEthPortErrStatsHistEntry 6 }

cfprApAdaptorEthPortErrStatsHistBadCrcPacketsDeltaMax OBJECT-TYPE
    SYNTAX       Unsigned64
    MAX-ACCESS   read-only
    STATUS       current
    DESCRIPTION
        "Cisco Firepower adaptor:EthPortErrStatsHist:badCrcPacketsDeltaMax
         managed object property"
    ::= { cfprApAdaptorEthPortErrStatsHistEntry 7 }

cfprApAdaptorEthPortErrStatsHistBadCrcPacketsDeltaMin OBJECT-TYPE
    SYNTAX       Unsigned64
    MAX-ACCESS   read-only
    STATUS       current
    DESCRIPTION
        "Cisco Firepower adaptor:EthPortErrStatsHist:badCrcPacketsDeltaMin
         managed object property"
    ::= { cfprApAdaptorEthPortErrStatsHistEntry 8 }

cfprApAdaptorEthPortErrStatsHistBadLengthPackets OBJECT-TYPE
    SYNTAX       Unsigned64
    MAX-ACCESS   read-only
    STATUS       current
    DESCRIPTION
        "Cisco Firepower adaptor:EthPortErrStatsHist:badLengthPackets
        managed object property"
    ::= { cfprApAdaptorEthPortErrStatsHistEntry 9 }

cfprApAdaptorEthPortErrStatsHistBadLengthPacketsDelta OBJECT-TYPE
    SYNTAX       Unsigned64
    MAX-ACCESS   read-only
    STATUS       current
    DESCRIPTION
        "Cisco Firepower adaptor:EthPortErrStatsHist:badLengthPacketsDelta
         managed object property"
    ::= { cfprApAdaptorEthPortErrStatsHistEntry 10 }

cfprApAdaptorEthPortErrStatsHistBadLengthPacketsDeltaAvg OBJECT-TYPE
    SYNTAX       Unsigned64
    MAX-ACCESS   read-only
    STATUS       current
    DESCRIPTION
        "Cisco Firepower adaptor:EthPortErrStatsHist:badLengthPacketsDelta
        Avg managed object property"
    ::= { cfprApAdaptorEthPortErrStatsHistEntry 11 }

cfprApAdaptorEthPortErrStatsHistBadLengthPacketsDeltaMax OBJECT-TYPE
    SYNTAX       Unsigned64
    MAX-ACCESS   read-only
    STATUS       current
    DESCRIPTION
        "Cisco Firepower adaptor:EthPortErrStatsHist:badLengthPacketsDelta
        Max managed object property"
    ::= { cfprApAdaptorEthPortErrStatsHistEntry 12 }

cfprApAdaptorEthPortErrStatsHistBadLengthPacketsDeltaMin OBJECT-TYPE
    SYNTAX       Unsigned64
    MAX-ACCESS   read-only
    STATUS       current
    DESCRIPTION
        "Cisco Firepower adaptor:EthPortErrStatsHist:badLengthPacketsDelta
        Min managed object property"
    ::= { cfprApAdaptorEthPortErrStatsHistEntry 13 }

cfprApAdaptorEthPortErrStatsHistId OBJECT-TYPE
    SYNTAX       Unsigned64
    MAX-ACCESS   read-only
    STATUS       current
    DESCRIPTION
        "Cisco Firepower adaptor:EthPortErrStatsHist:id
        managed object property"
    ::= { cfprApAdaptorEthPortErrStatsHistEntry 14 }

cfprApAdaptorEthPortErrStatsHistMacDiscardedPackets OBJECT-TYPE
    SYNTAX       Unsigned64
    MAX-ACCESS   read-only
    STATUS       current
    DESCRIPTION
        "Cisco Firepower adaptor:EthPortErrStatsHist:macDiscardedPackets
        managed object property"
    ::= { cfprApAdaptorEthPortErrStatsHistEntry 15 }

cfprApAdaptorEthPortErrStatsHistMacDiscardedPacketsDelta OBJECT-TYPE
    SYNTAX       Unsigned64
    MAX-ACCESS   read-only
    STATUS       current
    DESCRIPTION
        "Cisco Firepower adaptor:EthPortErrStatsHist:macDiscardedPacketsDe
        lta managed object property"
    ::= { cfprApAdaptorEthPortErrStatsHistEntry 16 }

cfprApAdaptorEthPortErrStatsHistMacDiscardedPacketsDeltaAvg OBJECT-TYPE
    SYNTAX       Unsigned64
    MAX-ACCESS   read-only
    STATUS       current
    DESCRIPTION
        "Cisco Firepower adaptor:EthPortErrStatsHist:macDiscardedPacketsDe
        ltaAvg managed object property"
    ::= { cfprApAdaptorEthPortErrStatsHistEntry 17 }

cfprApAdaptorEthPortErrStatsHistMacDiscardedPacketsDeltaMax OBJECT-TYPE
    SYNTAX       Unsigned64
    MAX-ACCESS   read-only
    STATUS       current
    DESCRIPTION
        "Cisco Firepower adaptor:EthPortErrStatsHist:macDiscardedPacketsDe
        ltaMax managed object property"
    ::= { cfprApAdaptorEthPortErrStatsHistEntry 18 }

cfprApAdaptorEthPortErrStatsHistMacDiscardedPacketsDeltaMin OBJECT-TYPE
    SYNTAX       Unsigned64
    MAX-ACCESS   read-only
    STATUS       current
    DESCRIPTION
        "Cisco Firepower adaptor:EthPortErrStatsHist:macDiscardedPacketsDe
        ltaMin managed object property"
    ::= { cfprApAdaptorEthPortErrStatsHistEntry 19 }

cfprApAdaptorEthPortErrStatsHistMostRecent OBJECT-TYPE
    SYNTAX       TruthValue
    MAX-ACCESS   read-only
    STATUS       current
    DESCRIPTION
        "Cisco Firepower adaptor:EthPortErrStatsHist:mostRecent
        managed object property"
    ::= { cfprApAdaptorEthPortErrStatsHistEntry 20 }

cfprApAdaptorEthPortErrStatsHistSuspect OBJECT-TYPE
    SYNTAX       TruthValue
    MAX-ACCESS   read-only
    STATUS       current
    DESCRIPTION
        "Cisco Firepower adaptor:EthPortErrStatsHist:suspect
        managed object property"
    ::= { cfprApAdaptorEthPortErrStatsHistEntry 21 }

cfprApAdaptorEthPortErrStatsHistThresholded OBJECT-TYPE
    SYNTAX       CfprApAdaptorEthPortErrStatsHistThresholded
    MAX-ACCESS   read-only
    STATUS       current
    DESCRIPTION
        "Cisco Firepower adaptor:EthPortErrStatsHist:thresholded
        managed object property"
    ::= { cfprApAdaptorEthPortErrStatsHistEntry 22 }

cfprApAdaptorEthPortErrStatsHistTimeCollected OBJECT-TYPE
    SYNTAX       DateAndTime
    MAX-ACCESS   read-only
    STATUS       current
    DESCRIPTION
        "Cisco Firepower adaptor:EthPortErrStatsHist:timeCollected
        managed object property"
    ::= { cfprApAdaptorEthPortErrStatsHistEntry 23 }

cfprApAdaptorEthPortMcastStatsTable OBJECT-TYPE
    SYNTAX           SEQUENCE OF CfprApAdaptorEthPortMcastStatsEntry
    MAX-ACCESS       not-accessible
    STATUS           current
    DESCRIPTION
        "Cisco Firepower adaptor:EthPortMcastStats managed object table"
    ::= { cfprApAdaptorObjects 16 }

cfprApAdaptorEthPortMcastStatsEntry OBJECT-TYPE
    SYNTAX           CfprApAdaptorEthPortMcastStatsEntry
    MAX-ACCESS       not-accessible
    STATUS           current
    DESCRIPTION
        "Entry for the cfprApAdaptorEthPortMcastStatsTable table."
    INDEX { cfprApAdaptorEthPortMcastStatsInstanceId }
    ::= { cfprApAdaptorEthPortMcastStatsTable 1 }

CfprApAdaptorEthPortMcastStatsEntry ::= SEQUENCE {
    cfprApAdaptorEthPortMcastStatsInstanceId                         CfprApManagedObjectId,
    cfprApAdaptorEthPortMcastStatsDn                                 CfprApManagedObjectDn,
    cfprApAdaptorEthPortMcastStatsRn                                 SnmpAdminString,
    cfprApAdaptorEthPortMcastStatsBroadcastPackets                   Unsigned64,
    cfprApAdaptorEthPortMcastStatsBroadcastPacketsDelta              Counter64,
    cfprApAdaptorEthPortMcastStatsBroadcastPacketsDeltaAvg           Unsigned64,
    cfprApAdaptorEthPortMcastStatsBroadcastPacketsDeltaMax           Unsigned64,
    cfprApAdaptorEthPortMcastStatsBroadcastPacketsDeltaMin           Unsigned64,
    cfprApAdaptorEthPortMcastStatsIntervals                          Gauge32,
    cfprApAdaptorEthPortMcastStatsMulticastPackets                   Unsigned64,
    cfprApAdaptorEthPortMcastStatsMulticastPacketsDelta              Counter64,
    cfprApAdaptorEthPortMcastStatsMulticastPacketsDeltaAvg           Unsigned64,
    cfprApAdaptorEthPortMcastStatsMulticastPacketsDeltaMax           Unsigned64,
    cfprApAdaptorEthPortMcastStatsMulticastPacketsDeltaMin           Unsigned64,
    cfprApAdaptorEthPortMcastStatsSuspect                            TruthValue,
    cfprApAdaptorEthPortMcastStatsThresholded                        CfprApAdaptorEthPortMcastStatsThresholded,
    cfprApAdaptorEthPortMcastStatsTimeCollected                      DateAndTime,
    cfprApAdaptorEthPortMcastStatsTrafficDirection                   CfprApAdaptorAdapterStatsTrafficDir,
    cfprApAdaptorEthPortMcastStatsUnicastPackets                     Unsigned64,
    cfprApAdaptorEthPortMcastStatsUnicastPacketsDelta                Counter64,
    cfprApAdaptorEthPortMcastStatsUnicastPacketsDeltaAvg             Unsigned64,
    cfprApAdaptorEthPortMcastStatsUnicastPacketsDeltaMax             Unsigned64,
    cfprApAdaptorEthPortMcastStatsUnicastPacketsDeltaMin             Unsigned64,
    cfprApAdaptorEthPortMcastStatsUpdate                             Gauge32
}

cfprApAdaptorEthPortMcastStatsInstanceId OBJECT-TYPE
    SYNTAX       CfprApManagedObjectId
    MAX-ACCESS   not-accessible
    STATUS       current
    DESCRIPTION
        "Instance identifier of the managed object."
    ::= { cfprApAdaptorEthPortMcastStatsEntry 1 }

cfprApAdaptorEthPortMcastStatsDn OBJECT-TYPE
    SYNTAX       CfprApManagedObjectDn
    MAX-ACCESS   read-only
    STATUS       current
    DESCRIPTION
        "Cisco Firepower adaptor:EthPortMcastStats:dn managed
        object property"
    ::= { cfprApAdaptorEthPortMcastStatsEntry 2 }

cfprApAdaptorEthPortMcastStatsRn OBJECT-TYPE
    SYNTAX       SnmpAdminString
    MAX-ACCESS   read-only
    STATUS       current
    DESCRIPTION
        "Cisco Firepower adaptor:EthPortMcastStats:rn managed
        object property"
    ::= { cfprApAdaptorEthPortMcastStatsEntry 3 }

cfprApAdaptorEthPortMcastStatsBroadcastPackets OBJECT-TYPE
    SYNTAX       Unsigned64
    MAX-ACCESS   read-only
    STATUS       current
    DESCRIPTION
        "Cisco Firepower adaptor:EthPortMcastStats:broadcastPackets
        managed object property"
    ::= { cfprApAdaptorEthPortMcastStatsEntry 4 }

cfprApAdaptorEthPortMcastStatsBroadcastPacketsDelta OBJECT-TYPE
    SYNTAX       Counter64
    MAX-ACCESS   read-only
    STATUS       current
    DESCRIPTION
        "Cisco Firepower adaptor:EthPortMcastStats:broadcastPacketsDelta
        managed object property"
    ::= { cfprApAdaptorEthPortMcastStatsEntry 5 }

cfprApAdaptorEthPortMcastStatsBroadcastPacketsDeltaAvg OBJECT-TYPE
    SYNTAX       Unsigned64
    MAX-ACCESS   read-only
    STATUS       current
    DESCRIPTION
        "Cisco Firepower adaptor:EthPortMcastStats:broadcastPacketsDeltaAv
        g managed object property"
    ::= { cfprApAdaptorEthPortMcastStatsEntry 6 }

cfprApAdaptorEthPortMcastStatsBroadcastPacketsDeltaMax OBJECT-TYPE
    SYNTAX       Unsigned64
    MAX-ACCESS   read-only
    STATUS       current
    DESCRIPTION
        "Cisco Firepower adaptor:EthPortMcastStats:broadcastPacketsDeltaMa
        x managed object property"
    ::= { cfprApAdaptorEthPortMcastStatsEntry 7 }

cfprApAdaptorEthPortMcastStatsBroadcastPacketsDeltaMin OBJECT-TYPE
    SYNTAX       Unsigned64
    MAX-ACCESS   read-only
    STATUS       current
    DESCRIPTION
        "Cisco Firepower adaptor:EthPortMcastStats:broadcastPacketsDeltaMi
        n managed object property"
    ::= { cfprApAdaptorEthPortMcastStatsEntry 8 }

cfprApAdaptorEthPortMcastStatsIntervals OBJECT-TYPE
    SYNTAX       Gauge32
    MAX-ACCESS   read-only
    STATUS       current
    DESCRIPTION
        "Cisco Firepower adaptor:EthPortMcastStats:intervals
        managed object property"
    ::= { cfprApAdaptorEthPortMcastStatsEntry 9 }

cfprApAdaptorEthPortMcastStatsMulticastPackets OBJECT-TYPE
    SYNTAX       Unsigned64
    MAX-ACCESS   read-only
    STATUS       current
    DESCRIPTION
        "Cisco Firepower adaptor:EthPortMcastStats:multicastPackets
        managed object property"
    ::= { cfprApAdaptorEthPortMcastStatsEntry 10 }

cfprApAdaptorEthPortMcastStatsMulticastPacketsDelta OBJECT-TYPE
    SYNTAX       Counter64
    MAX-ACCESS   read-only
    STATUS       current
    DESCRIPTION
        "Cisco Firepower adaptor:EthPortMcastStats:multicastPacketsDelta
        managed object property"
    ::= { cfprApAdaptorEthPortMcastStatsEntry 11 }

cfprApAdaptorEthPortMcastStatsMulticastPacketsDeltaAvg OBJECT-TYPE
    SYNTAX       Unsigned64
    MAX-ACCESS   read-only
    STATUS       current
    DESCRIPTION
        "Cisco Firepower adaptor:EthPortMcastStats:multicastPacketsDeltaAv
        g managed object property"
    ::= { cfprApAdaptorEthPortMcastStatsEntry 12 }

cfprApAdaptorEthPortMcastStatsMulticastPacketsDeltaMax OBJECT-TYPE
    SYNTAX       Unsigned64
    MAX-ACCESS   read-only
    STATUS       current
    DESCRIPTION
        "Cisco Firepower adaptor:EthPortMcastStats:multicastPacketsDeltaMa
        x managed object property"
    ::= { cfprApAdaptorEthPortMcastStatsEntry 13 }

cfprApAdaptorEthPortMcastStatsMulticastPacketsDeltaMin OBJECT-TYPE
    SYNTAX       Unsigned64
    MAX-ACCESS   read-only
    STATUS       current
    DESCRIPTION
        "Cisco Firepower adaptor:EthPortMcastStats:multicastPacketsDeltaMi
        n managed object property"
    ::= { cfprApAdaptorEthPortMcastStatsEntry 14 }

cfprApAdaptorEthPortMcastStatsSuspect OBJECT-TYPE
    SYNTAX       TruthValue
    MAX-ACCESS   read-only
    STATUS       current
    DESCRIPTION
        "Cisco Firepower adaptor:EthPortMcastStats:suspect
        managed object property"
    ::= { cfprApAdaptorEthPortMcastStatsEntry 15 }

cfprApAdaptorEthPortMcastStatsThresholded OBJECT-TYPE
    SYNTAX       CfprApAdaptorEthPortMcastStatsThresholded
    MAX-ACCESS   read-only
    STATUS       current
    DESCRIPTION
        "Cisco Firepower adaptor:EthPortMcastStats:thresholded
        managed object property"
    ::= { cfprApAdaptorEthPortMcastStatsEntry 16 }

cfprApAdaptorEthPortMcastStatsTimeCollected OBJECT-TYPE
    SYNTAX       DateAndTime
    MAX-ACCESS   read-only
    STATUS       current
    DESCRIPTION
        "Cisco Firepower adaptor:EthPortMcastStats:timeCollected
        managed object property"
    ::= { cfprApAdaptorEthPortMcastStatsEntry 17 }

cfprApAdaptorEthPortMcastStatsTrafficDirection OBJECT-TYPE
    SYNTAX       CfprApAdaptorAdapterStatsTrafficDir
    MAX-ACCESS   read-only
    STATUS       current
    DESCRIPTION
        "Cisco Firepower adaptor:EthPortMcastStats:trafficDirection
        managed object property"
    ::= { cfprApAdaptorEthPortMcastStatsEntry 18 }

cfprApAdaptorEthPortMcastStatsUnicastPackets OBJECT-TYPE
    SYNTAX       Unsigned64
    MAX-ACCESS   read-only
    STATUS       current
    DESCRIPTION
        "Cisco Firepower adaptor:EthPortMcastStats:unicastPackets
        managed object property"
    ::= { cfprApAdaptorEthPortMcastStatsEntry 19 }

cfprApAdaptorEthPortMcastStatsUnicastPacketsDelta OBJECT-TYPE
    SYNTAX       Counter64
    MAX-ACCESS   read-only
    STATUS       current
    DESCRIPTION
        "Cisco Firepower adaptor:EthPortMcastStats:unicastPacketsDelta
        managed object property"
    ::= { cfprApAdaptorEthPortMcastStatsEntry 20 }

cfprApAdaptorEthPortMcastStatsUnicastPacketsDeltaAvg OBJECT-TYPE
    SYNTAX       Unsigned64
    MAX-ACCESS   read-only
    STATUS       current
    DESCRIPTION
        "Cisco Firepower adaptor:EthPortMcastStats:unicastPacketsDeltaAvg
        managed object property"
    ::= { cfprApAdaptorEthPortMcastStatsEntry 21 }

cfprApAdaptorEthPortMcastStatsUnicastPacketsDeltaMax OBJECT-TYPE
    SYNTAX       Unsigned64
    MAX-ACCESS   read-only
    STATUS       current
    DESCRIPTION
        "Cisco Firepower adaptor:EthPortMcastStats:unicastPacketsDeltaMax
        managed object property"
    ::= { cfprApAdaptorEthPortMcastStatsEntry 22 }

cfprApAdaptorEthPortMcastStatsUnicastPacketsDeltaMin OBJECT-TYPE
    SYNTAX       Unsigned64
    MAX-ACCESS   read-only
    STATUS       current
    DESCRIPTION
        "Cisco Firepower adaptor:EthPortMcastStats:unicastPacketsDeltaMin
        managed object property"
    ::= { cfprApAdaptorEthPortMcastStatsEntry 23 }

cfprApAdaptorEthPortMcastStatsUpdate OBJECT-TYPE
    SYNTAX       Gauge32
    MAX-ACCESS   read-only
    STATUS       current
    DESCRIPTION
        "Cisco Firepower adaptor:EthPortMcastStats:update
        managed object property"
    ::= { cfprApAdaptorEthPortMcastStatsEntry 24 }

cfprApAdaptorEthPortMcastStatsHistTable OBJECT-TYPE
    SYNTAX           SEQUENCE OF CfprApAdaptorEthPortMcastStatsHistEntry
    MAX-ACCESS       not-accessible
    STATUS           current
    DESCRIPTION
        "Cisco Firepower adaptor:EthPortMcastStatsHist
        managed object table"
    ::= { cfprApAdaptorObjects 17 }

cfprApAdaptorEthPortMcastStatsHistEntry OBJECT-TYPE
    SYNTAX           CfprApAdaptorEthPortMcastStatsHistEntry
    MAX-ACCESS       not-accessible
    STATUS           current
    DESCRIPTION
        "Entry for the cfprApAdaptorEthPortMcastStatsHistTable table."
    INDEX { cfprApAdaptorEthPortMcastStatsHistInstanceId }
    ::= { cfprApAdaptorEthPortMcastStatsHistTable 1 }

CfprApAdaptorEthPortMcastStatsHistEntry ::= SEQUENCE {
    cfprApAdaptorEthPortMcastStatsHistInstanceId                     CfprApManagedObjectId,
    cfprApAdaptorEthPortMcastStatsHistDn                             CfprApManagedObjectDn,
    cfprApAdaptorEthPortMcastStatsHistRn                             SnmpAdminString,
    cfprApAdaptorEthPortMcastStatsHistBroadcastPackets               Unsigned64,
    cfprApAdaptorEthPortMcastStatsHistBroadcastPacketsDelta          Unsigned64,
    cfprApAdaptorEthPortMcastStatsHistBroadcastPacketsDeltaAvg       Unsigned64,
    cfprApAdaptorEthPortMcastStatsHistBroadcastPacketsDeltaMax       Unsigned64,
    cfprApAdaptorEthPortMcastStatsHistBroadcastPacketsDeltaMin       Unsigned64,
    cfprApAdaptorEthPortMcastStatsHistId                             Unsigned64,
    cfprApAdaptorEthPortMcastStatsHistMostRecent                     TruthValue,
    cfprApAdaptorEthPortMcastStatsHistMulticastPackets               Unsigned64,
    cfprApAdaptorEthPortMcastStatsHistMulticastPacketsDelta          Unsigned64,
    cfprApAdaptorEthPortMcastStatsHistMulticastPacketsDeltaAvg       Unsigned64,
    cfprApAdaptorEthPortMcastStatsHistMulticastPacketsDeltaMax       Unsigned64,
    cfprApAdaptorEthPortMcastStatsHistMulticastPacketsDeltaMin       Unsigned64,
    cfprApAdaptorEthPortMcastStatsHistSuspect                        TruthValue,
    cfprApAdaptorEthPortMcastStatsHistThresholded                    CfprApAdaptorEthPortMcastStatsHistThresholded,
    cfprApAdaptorEthPortMcastStatsHistTimeCollected                  DateAndTime,
    cfprApAdaptorEthPortMcastStatsHistUnicastPackets                 Unsigned64,
    cfprApAdaptorEthPortMcastStatsHistUnicastPacketsDelta            Unsigned64,
    cfprApAdaptorEthPortMcastStatsHistUnicastPacketsDeltaAvg         Unsigned64,
    cfprApAdaptorEthPortMcastStatsHistUnicastPacketsDeltaMax         Unsigned64,
    cfprApAdaptorEthPortMcastStatsHistUnicastPacketsDeltaMin         Unsigned64
}

cfprApAdaptorEthPortMcastStatsHistInstanceId OBJECT-TYPE
    SYNTAX       CfprApManagedObjectId
    MAX-ACCESS   not-accessible
    STATUS       current
    DESCRIPTION
        "Instance identifier of the managed object."
    ::= { cfprApAdaptorEthPortMcastStatsHistEntry 1 }

cfprApAdaptorEthPortMcastStatsHistDn OBJECT-TYPE
    SYNTAX       CfprApManagedObjectDn
    MAX-ACCESS   read-only
    STATUS       current
    DESCRIPTION
        "Cisco Firepower adaptor:EthPortMcastStatsHist:dn
        managed object property"
    ::= { cfprApAdaptorEthPortMcastStatsHistEntry 2 }

cfprApAdaptorEthPortMcastStatsHistRn OBJECT-TYPE
    SYNTAX       SnmpAdminString
    MAX-ACCESS   read-only
    STATUS       current
    DESCRIPTION
        "Cisco Firepower adaptor:EthPortMcastStatsHist:rn
        managed object property"
    ::= { cfprApAdaptorEthPortMcastStatsHistEntry 3 }

cfprApAdaptorEthPortMcastStatsHistBroadcastPackets OBJECT-TYPE
    SYNTAX       Unsigned64
    MAX-ACCESS   read-only
    STATUS       current
    DESCRIPTION
        "Cisco Firepower adaptor:EthPortMcastStatsHist:broadcastPackets
        managed object property"
    ::= { cfprApAdaptorEthPortMcastStatsHistEntry 4 }

cfprApAdaptorEthPortMcastStatsHistBroadcastPacketsDelta OBJECT-TYPE
    SYNTAX       Unsigned64
    MAX-ACCESS   read-only
    STATUS       current
    DESCRIPTION
        "Cisco Firepower adaptor:EthPortMcastStatsHist:broadcastPacketsDel
        ta managed object property"
    ::= { cfprApAdaptorEthPortMcastStatsHistEntry 5 }

cfprApAdaptorEthPortMcastStatsHistBroadcastPacketsDeltaAvg OBJECT-TYPE
    SYNTAX       Unsigned64
    MAX-ACCESS   read-only
    STATUS       current
    DESCRIPTION
        "Cisco Firepower adaptor:EthPortMcastStatsHist:broadcastPacketsDel
        taAvg managed object property"
    ::= { cfprApAdaptorEthPortMcastStatsHistEntry 6 }

cfprApAdaptorEthPortMcastStatsHistBroadcastPacketsDeltaMax OBJECT-TYPE
    SYNTAX       Unsigned64
    MAX-ACCESS   read-only
    STATUS       current
    DESCRIPTION
        "Cisco Firepower adaptor:EthPortMcastStatsHist:broadcastPacketsDel
        taMax managed object property"
    ::= { cfprApAdaptorEthPortMcastStatsHistEntry 7 }

cfprApAdaptorEthPortMcastStatsHistBroadcastPacketsDeltaMin OBJECT-TYPE
    SYNTAX       Unsigned64
    MAX-ACCESS   read-only
    STATUS       current
    DESCRIPTION
        "Cisco Firepower adaptor:EthPortMcastStatsHist:broadcastPacketsDel
        taMin managed object property"
    ::= { cfprApAdaptorEthPortMcastStatsHistEntry 8 }

cfprApAdaptorEthPortMcastStatsHistId OBJECT-TYPE
    SYNTAX       Unsigned64
    MAX-ACCESS   read-only
    STATUS       current
    DESCRIPTION
        "Cisco Firepower adaptor:EthPortMcastStatsHist:id
        managed object property"
    ::= { cfprApAdaptorEthPortMcastStatsHistEntry 9 }

cfprApAdaptorEthPortMcastStatsHistMostRecent OBJECT-TYPE
    SYNTAX       TruthValue
    MAX-ACCESS   read-only
    STATUS       current
    DESCRIPTION
        "Cisco Firepower adaptor:EthPortMcastStatsHist:mostRecent
        managed object property"
    ::= { cfprApAdaptorEthPortMcastStatsHistEntry 10 }

cfprApAdaptorEthPortMcastStatsHistMulticastPackets OBJECT-TYPE
    SYNTAX       Unsigned64
    MAX-ACCESS   read-only
    STATUS       current
    DESCRIPTION
        "Cisco Firepower adaptor:EthPortMcastStatsHist:multicastPackets
        managed object property"
    ::= { cfprApAdaptorEthPortMcastStatsHistEntry 11 }

cfprApAdaptorEthPortMcastStatsHistMulticastPacketsDelta OBJECT-TYPE
    SYNTAX       Unsigned64
    MAX-ACCESS   read-only
    STATUS       current
    DESCRIPTION
        "Cisco Firepower adaptor:EthPortMcastStatsHist:multicastPacketsDel
        ta managed object property"
    ::= { cfprApAdaptorEthPortMcastStatsHistEntry 12 }

cfprApAdaptorEthPortMcastStatsHistMulticastPacketsDeltaAvg OBJECT-TYPE
    SYNTAX       Unsigned64
    MAX-ACCESS   read-only
    STATUS       current
    DESCRIPTION
        "Cisco Firepower adaptor:EthPortMcastStatsHist:multicastPacketsDel
        taAvg managed object property"
    ::= { cfprApAdaptorEthPortMcastStatsHistEntry 13 }

cfprApAdaptorEthPortMcastStatsHistMulticastPacketsDeltaMax OBJECT-TYPE
    SYNTAX       Unsigned64
    MAX-ACCESS   read-only
    STATUS       current
    DESCRIPTION
        "Cisco Firepower adaptor:EthPortMcastStatsHist:multicastPacketsDel
        taMax managed object property"
    ::= { cfprApAdaptorEthPortMcastStatsHistEntry 14 }

cfprApAdaptorEthPortMcastStatsHistMulticastPacketsDeltaMin OBJECT-TYPE
    SYNTAX       Unsigned64
    MAX-ACCESS   read-only
    STATUS       current
    DESCRIPTION
        "Cisco Firepower adaptor:EthPortMcastStatsHist:multicastPacketsDel
        taMin managed object property"
    ::= { cfprApAdaptorEthPortMcastStatsHistEntry 15 }

cfprApAdaptorEthPortMcastStatsHistSuspect OBJECT-TYPE
    SYNTAX       TruthValue
    MAX-ACCESS   read-only
    STATUS       current
    DESCRIPTION
        "Cisco Firepower adaptor:EthPortMcastStatsHist:suspect
        managed object property"
    ::= { cfprApAdaptorEthPortMcastStatsHistEntry 16 }

cfprApAdaptorEthPortMcastStatsHistThresholded OBJECT-TYPE
    SYNTAX       CfprApAdaptorEthPortMcastStatsHistThresholded
    MAX-ACCESS   read-only
    STATUS       current
    DESCRIPTION
        "Cisco Firepower adaptor:EthPortMcastStatsHist:thresholded
        managed object property"
    ::= { cfprApAdaptorEthPortMcastStatsHistEntry 17 }

cfprApAdaptorEthPortMcastStatsHistTimeCollected OBJECT-TYPE
    SYNTAX       DateAndTime
    MAX-ACCESS   read-only
    STATUS       current
    DESCRIPTION
        "Cisco Firepower adaptor:EthPortMcastStatsHist:timeCollected
        managed object property"
    ::= { cfprApAdaptorEthPortMcastStatsHistEntry 18 }

cfprApAdaptorEthPortMcastStatsHistUnicastPackets OBJECT-TYPE
    SYNTAX       Unsigned64
    MAX-ACCESS   read-only
    STATUS       current
    DESCRIPTION
        "Cisco Firepower adaptor:EthPortMcastStatsHist:unicastPackets
        managed object property"
    ::= { cfprApAdaptorEthPortMcastStatsHistEntry 19 }

cfprApAdaptorEthPortMcastStatsHistUnicastPacketsDelta OBJECT-TYPE
    SYNTAX       Unsigned64
    MAX-ACCESS   read-only
    STATUS       current
    DESCRIPTION
        "Cisco Firepower adaptor:EthPortMcastStatsHist:unicastPacketsDelta
         managed object property"
    ::= { cfprApAdaptorEthPortMcastStatsHistEntry 20 }

cfprApAdaptorEthPortMcastStatsHistUnicastPacketsDeltaAvg OBJECT-TYPE
    SYNTAX       Unsigned64
    MAX-ACCESS   read-only
    STATUS       current
    DESCRIPTION
        "Cisco Firepower adaptor:EthPortMcastStatsHist:unicastPacketsDelta
        Avg managed object property"
    ::= { cfprApAdaptorEthPortMcastStatsHistEntry 21 }

cfprApAdaptorEthPortMcastStatsHistUnicastPacketsDeltaMax OBJECT-TYPE
    SYNTAX       Unsigned64
    MAX-ACCESS   read-only
    STATUS       current
    DESCRIPTION
        "Cisco Firepower adaptor:EthPortMcastStatsHist:unicastPacketsDelta
        Max managed object property"
    ::= { cfprApAdaptorEthPortMcastStatsHistEntry 22 }

cfprApAdaptorEthPortMcastStatsHistUnicastPacketsDeltaMin OBJECT-TYPE
    SYNTAX       Unsigned64
    MAX-ACCESS   read-only
    STATUS       current
    DESCRIPTION
        "Cisco Firepower adaptor:EthPortMcastStatsHist:unicastPacketsDelta
        Min managed object property"
    ::= { cfprApAdaptorEthPortMcastStatsHistEntry 23 }

cfprApAdaptorEthPortOutsizedStatsTable OBJECT-TYPE
    SYNTAX           SEQUENCE OF CfprApAdaptorEthPortOutsizedStatsEntry
    MAX-ACCESS       not-accessible
    STATUS           current
    DESCRIPTION
        "Cisco Firepower adaptor:EthPortOutsizedStats managed
        object table"
    ::= { cfprApAdaptorObjects 18 }

cfprApAdaptorEthPortOutsizedStatsEntry OBJECT-TYPE
    SYNTAX           CfprApAdaptorEthPortOutsizedStatsEntry
    MAX-ACCESS       not-accessible
    STATUS           current
    DESCRIPTION
        "Entry for the cfprApAdaptorEthPortOutsizedStatsTable table."
    INDEX { cfprApAdaptorEthPortOutsizedStatsInstanceId }
    ::= { cfprApAdaptorEthPortOutsizedStatsTable 1 }

CfprApAdaptorEthPortOutsizedStatsEntry ::= SEQUENCE {
    cfprApAdaptorEthPortOutsizedStatsInstanceId                      CfprApManagedObjectId,
    cfprApAdaptorEthPortOutsizedStatsDn                              CfprApManagedObjectDn,
    cfprApAdaptorEthPortOutsizedStatsRn                              SnmpAdminString,
    cfprApAdaptorEthPortOutsizedStatsIntervals                       Gauge32,
    cfprApAdaptorEthPortOutsizedStatsOversizedBadCrcPackets          Unsigned64,
    cfprApAdaptorEthPortOutsizedStatsOversizedBadCrcPacketsDelta     Counter64,
    cfprApAdaptorEthPortOutsizedStatsOversizedBadCrcPacketsDeltaAvg  Unsigned64,
    cfprApAdaptorEthPortOutsizedStatsOversizedBadCrcPacketsDeltaMax  Unsigned64,
    cfprApAdaptorEthPortOutsizedStatsOversizedBadCrcPacketsDeltaMin  Unsigned64,
    cfprApAdaptorEthPortOutsizedStatsOversizedGoodCrcPackets         Unsigned64,
    cfprApAdaptorEthPortOutsizedStatsOversizedGoodCrcPacketsDelta    Counter64,
    cfprApAdaptorEthPortOutsizedStatsOversizedGoodCrcPacketsDeltaAvg Unsigned64,
    cfprApAdaptorEthPortOutsizedStatsOversizedGoodCrcPacketsDeltaMax Unsigned64,
    cfprApAdaptorEthPortOutsizedStatsOversizedGoodCrcPacketsDeltaMin Unsigned64,
    cfprApAdaptorEthPortOutsizedStatsOversizedPackets                Unsigned64,
    cfprApAdaptorEthPortOutsizedStatsOversizedPacketsDelta           Counter64,
    cfprApAdaptorEthPortOutsizedStatsOversizedPacketsDeltaAvg        Unsigned64,
    cfprApAdaptorEthPortOutsizedStatsOversizedPacketsDeltaMax        Unsigned64,
    cfprApAdaptorEthPortOutsizedStatsOversizedPacketsDeltaMin        Unsigned64,
    cfprApAdaptorEthPortOutsizedStatsSuspect                         TruthValue,
    cfprApAdaptorEthPortOutsizedStatsThresholded                     CfprApAdaptorEthPortOutsizedStatsThresholded,
    cfprApAdaptorEthPortOutsizedStatsTimeCollected                   DateAndTime,
    cfprApAdaptorEthPortOutsizedStatsTrafficDirection                CfprApAdaptorAdapterStatsTrafficDir,
    cfprApAdaptorEthPortOutsizedStatsUndersizedBadCrcPackets         Unsigned64,
    cfprApAdaptorEthPortOutsizedStatsUndersizedBadCrcPacketsDelta    Counter64,
    cfprApAdaptorEthPortOutsizedStatsUndersizedBadCrcPacketsDeltaAvg Unsigned64,
    cfprApAdaptorEthPortOutsizedStatsUndersizedBadCrcPacketsDeltaMax Unsigned64,
    cfprApAdaptorEthPortOutsizedStatsUndersizedBadCrcPacketsDeltaMin Unsigned64,
    cfprApAdaptorEthPortOutsizedStatsUndersizedGoodCrcPackets        Unsigned64,
    cfprApAdaptorEthPortOutsizedStatsUndersizedGoodCrcPacketsDelta   Counter64,
    cfprApAdaptorEthPortOutsizedStatsUndersizedGoodCrcPacketsDeltaAvg Unsigned64,
    cfprApAdaptorEthPortOutsizedStatsUndersizedGoodCrcPacketsDeltaMax Unsigned64,
    cfprApAdaptorEthPortOutsizedStatsUndersizedGoodCrcPacketsDeltaMin Unsigned64,
    cfprApAdaptorEthPortOutsizedStatsUpdate                          Gauge32
}

cfprApAdaptorEthPortOutsizedStatsInstanceId OBJECT-TYPE
    SYNTAX       CfprApManagedObjectId
    MAX-ACCESS   not-accessible
    STATUS       current
    DESCRIPTION
        "Instance identifier of the managed object."
    ::= { cfprApAdaptorEthPortOutsizedStatsEntry 1 }

cfprApAdaptorEthPortOutsizedStatsDn OBJECT-TYPE
    SYNTAX       CfprApManagedObjectDn
    MAX-ACCESS   read-only
    STATUS       current
    DESCRIPTION
        "Cisco Firepower adaptor:EthPortOutsizedStats:dn
        managed object property"
    ::= { cfprApAdaptorEthPortOutsizedStatsEntry 2 }

cfprApAdaptorEthPortOutsizedStatsRn OBJECT-TYPE
    SYNTAX       SnmpAdminString
    MAX-ACCESS   read-only
    STATUS       current
    DESCRIPTION
        "Cisco Firepower adaptor:EthPortOutsizedStats:rn
        managed object property"
    ::= { cfprApAdaptorEthPortOutsizedStatsEntry 3 }

cfprApAdaptorEthPortOutsizedStatsIntervals OBJECT-TYPE
    SYNTAX       Gauge32
    MAX-ACCESS   read-only
    STATUS       current
    DESCRIPTION
        "Cisco Firepower adaptor:EthPortOutsizedStats:intervals
        managed object property"
    ::= { cfprApAdaptorEthPortOutsizedStatsEntry 4 }

cfprApAdaptorEthPortOutsizedStatsOversizedBadCrcPackets OBJECT-TYPE
    SYNTAX       Unsigned64
    MAX-ACCESS   read-only
    STATUS       current
    DESCRIPTION
        "Cisco Firepower adaptor:EthPortOutsizedStats:oversizedBadCrcPacke
        ts managed object property"
    ::= { cfprApAdaptorEthPortOutsizedStatsEntry 5 }

cfprApAdaptorEthPortOutsizedStatsOversizedBadCrcPacketsDelta OBJECT-TYPE
    SYNTAX       Counter64
    MAX-ACCESS   read-only
    STATUS       current
    DESCRIPTION
        "Cisco Firepower adaptor:EthPortOutsizedStats:oversizedBadCrcPacke
        tsDelta managed object property"
    ::= { cfprApAdaptorEthPortOutsizedStatsEntry 6 }

cfprApAdaptorEthPortOutsizedStatsOversizedBadCrcPacketsDeltaAvg OBJECT-TYPE
    SYNTAX       Unsigned64
    MAX-ACCESS   read-only
    STATUS       current
    DESCRIPTION
        "Cisco Firepower adaptor:EthPortOutsizedStats:oversizedBadCrcPacke
        tsDeltaAvg managed object property"
    ::= { cfprApAdaptorEthPortOutsizedStatsEntry 7 }

cfprApAdaptorEthPortOutsizedStatsOversizedBadCrcPacketsDeltaMax OBJECT-TYPE
    SYNTAX       Unsigned64
    MAX-ACCESS   read-only
    STATUS       current
    DESCRIPTION
        "Cisco Firepower adaptor:EthPortOutsizedStats:oversizedBadCrcPacke
        tsDeltaMax managed object property"
    ::= { cfprApAdaptorEthPortOutsizedStatsEntry 8 }

cfprApAdaptorEthPortOutsizedStatsOversizedBadCrcPacketsDeltaMin OBJECT-TYPE
    SYNTAX       Unsigned64
    MAX-ACCESS   read-only
    STATUS       current
    DESCRIPTION
        "Cisco Firepower adaptor:EthPortOutsizedStats:oversizedBadCrcPacke
        tsDeltaMin managed object property"
    ::= { cfprApAdaptorEthPortOutsizedStatsEntry 9 }

cfprApAdaptorEthPortOutsizedStatsOversizedGoodCrcPackets OBJECT-TYPE
    SYNTAX       Unsigned64
    MAX-ACCESS   read-only
    STATUS       current
    DESCRIPTION
        "Cisco Firepower adaptor:EthPortOutsizedStats:oversizedGoodCrcPack
        ets managed object property"
    ::= { cfprApAdaptorEthPortOutsizedStatsEntry 10 }

cfprApAdaptorEthPortOutsizedStatsOversizedGoodCrcPacketsDelta OBJECT-TYPE
    SYNTAX       Counter64
    MAX-ACCESS   read-only
    STATUS       current
    DESCRIPTION
        "Cisco Firepower adaptor:EthPortOutsizedStats:oversizedGoodCrcPack
        etsDelta managed object property"
    ::= { cfprApAdaptorEthPortOutsizedStatsEntry 11 }

cfprApAdaptorEthPortOutsizedStatsOversizedGoodCrcPacketsDeltaAvg OBJECT-TYPE
    SYNTAX       Unsigned64
    MAX-ACCESS   read-only
    STATUS       current
    DESCRIPTION
        "Cisco Firepower adaptor:EthPortOutsizedStats:oversizedGoodCrcPack
        etsDeltaAvg managed object property"
    ::= { cfprApAdaptorEthPortOutsizedStatsEntry 12 }

cfprApAdaptorEthPortOutsizedStatsOversizedGoodCrcPacketsDeltaMax OBJECT-TYPE
    SYNTAX       Unsigned64
    MAX-ACCESS   read-only
    STATUS       current
    DESCRIPTION
        "Cisco Firepower adaptor:EthPortOutsizedStats:oversizedGoodCrcPack
        etsDeltaMax managed object property"
    ::= { cfprApAdaptorEthPortOutsizedStatsEntry 13 }

cfprApAdaptorEthPortOutsizedStatsOversizedGoodCrcPacketsDeltaMin OBJECT-TYPE
    SYNTAX       Unsigned64
    MAX-ACCESS   read-only
    STATUS       current
    DESCRIPTION
        "Cisco Firepower adaptor:EthPortOutsizedStats:oversizedGoodCrcPack
        etsDeltaMin managed object property"
    ::= { cfprApAdaptorEthPortOutsizedStatsEntry 14 }

cfprApAdaptorEthPortOutsizedStatsOversizedPackets OBJECT-TYPE
    SYNTAX       Unsigned64
    MAX-ACCESS   read-only
    STATUS       current
    DESCRIPTION
        "Cisco Firepower adaptor:EthPortOutsizedStats:oversizedPackets
        managed object property"
    ::= { cfprApAdaptorEthPortOutsizedStatsEntry 15 }

cfprApAdaptorEthPortOutsizedStatsOversizedPacketsDelta OBJECT-TYPE
    SYNTAX       Counter64
    MAX-ACCESS   read-only
    STATUS       current
    DESCRIPTION
        "Cisco Firepower adaptor:EthPortOutsizedStats:oversizedPacketsDelt
        a managed object property"
    ::= { cfprApAdaptorEthPortOutsizedStatsEntry 16 }

cfprApAdaptorEthPortOutsizedStatsOversizedPacketsDeltaAvg OBJECT-TYPE
    SYNTAX       Unsigned64
    MAX-ACCESS   read-only
    STATUS       current
    DESCRIPTION
        "Cisco Firepower adaptor:EthPortOutsizedStats:oversizedPacketsDelt
        aAvg managed object property"
    ::= { cfprApAdaptorEthPortOutsizedStatsEntry 17 }

cfprApAdaptorEthPortOutsizedStatsOversizedPacketsDeltaMax OBJECT-TYPE
    SYNTAX       Unsigned64
    MAX-ACCESS   read-only
    STATUS       current
    DESCRIPTION
        "Cisco Firepower adaptor:EthPortOutsizedStats:oversizedPacketsDelt
        aMax managed object property"
    ::= { cfprApAdaptorEthPortOutsizedStatsEntry 18 }

cfprApAdaptorEthPortOutsizedStatsOversizedPacketsDeltaMin OBJECT-TYPE
    SYNTAX       Unsigned64
    MAX-ACCESS   read-only
    STATUS       current
    DESCRIPTION
        "Cisco Firepower adaptor:EthPortOutsizedStats:oversizedPacketsDelt
        aMin managed object property"
    ::= { cfprApAdaptorEthPortOutsizedStatsEntry 19 }

cfprApAdaptorEthPortOutsizedStatsSuspect OBJECT-TYPE
    SYNTAX       TruthValue
    MAX-ACCESS   read-only
    STATUS       current
    DESCRIPTION
        "Cisco Firepower adaptor:EthPortOutsizedStats:suspect
        managed object property"
    ::= { cfprApAdaptorEthPortOutsizedStatsEntry 20 }

cfprApAdaptorEthPortOutsizedStatsThresholded OBJECT-TYPE
    SYNTAX       CfprApAdaptorEthPortOutsizedStatsThresholded
    MAX-ACCESS   read-only
    STATUS       current
    DESCRIPTION
        "Cisco Firepower adaptor:EthPortOutsizedStats:thresholded
        managed object property"
    ::= { cfprApAdaptorEthPortOutsizedStatsEntry 21 }

cfprApAdaptorEthPortOutsizedStatsTimeCollected OBJECT-TYPE
    SYNTAX       DateAndTime
    MAX-ACCESS   read-only
    STATUS       current
    DESCRIPTION
        "Cisco Firepower adaptor:EthPortOutsizedStats:timeCollected
        managed object property"
    ::= { cfprApAdaptorEthPortOutsizedStatsEntry 22 }

cfprApAdaptorEthPortOutsizedStatsTrafficDirection OBJECT-TYPE
    SYNTAX       CfprApAdaptorAdapterStatsTrafficDir
    MAX-ACCESS   read-only
    STATUS       current
    DESCRIPTION
        "Cisco Firepower adaptor:EthPortOutsizedStats:trafficDirection
        managed object property"
    ::= { cfprApAdaptorEthPortOutsizedStatsEntry 23 }

cfprApAdaptorEthPortOutsizedStatsUndersizedBadCrcPackets OBJECT-TYPE
    SYNTAX       Unsigned64
    MAX-ACCESS   read-only
    STATUS       current
    DESCRIPTION
        "Cisco Firepower adaptor:EthPortOutsizedStats:undersizedBadCrcPack
        ets managed object property"
    ::= { cfprApAdaptorEthPortOutsizedStatsEntry 24 }

cfprApAdaptorEthPortOutsizedStatsUndersizedBadCrcPacketsDelta OBJECT-TYPE
    SYNTAX       Counter64
    MAX-ACCESS   read-only
    STATUS       current
    DESCRIPTION
        "Cisco Firepower adaptor:EthPortOutsizedStats:undersizedBadCrcPack
        etsDelta managed object property"
    ::= { cfprApAdaptorEthPortOutsizedStatsEntry 25 }

cfprApAdaptorEthPortOutsizedStatsUndersizedBadCrcPacketsDeltaAvg OBJECT-TYPE
    SYNTAX       Unsigned64
    MAX-ACCESS   read-only
    STATUS       current
    DESCRIPTION
        "Cisco Firepower adaptor:EthPortOutsizedStats:undersizedBadCrcPack
        etsDeltaAvg managed object property"
    ::= { cfprApAdaptorEthPortOutsizedStatsEntry 26 }

cfprApAdaptorEthPortOutsizedStatsUndersizedBadCrcPacketsDeltaMax OBJECT-TYPE
    SYNTAX       Unsigned64
    MAX-ACCESS   read-only
    STATUS       current
    DESCRIPTION
        "Cisco Firepower adaptor:EthPortOutsizedStats:undersizedBadCrcPack
        etsDeltaMax managed object property"
    ::= { cfprApAdaptorEthPortOutsizedStatsEntry 27 }

cfprApAdaptorEthPortOutsizedStatsUndersizedBadCrcPacketsDeltaMin OBJECT-TYPE
    SYNTAX       Unsigned64
    MAX-ACCESS   read-only
    STATUS       current
    DESCRIPTION
        "Cisco Firepower adaptor:EthPortOutsizedStats:undersizedBadCrcPack
        etsDeltaMin managed object property"
    ::= { cfprApAdaptorEthPortOutsizedStatsEntry 28 }

cfprApAdaptorEthPortOutsizedStatsUndersizedGoodCrcPackets OBJECT-TYPE
    SYNTAX       Unsigned64
    MAX-ACCESS   read-only
    STATUS       current
    DESCRIPTION
        "Cisco Firepower adaptor:EthPortOutsizedStats:undersizedGoodCrcPac
        kets managed object property"
    ::= { cfprApAdaptorEthPortOutsizedStatsEntry 29 }

cfprApAdaptorEthPortOutsizedStatsUndersizedGoodCrcPacketsDelta OBJECT-TYPE
    SYNTAX       Counter64
    MAX-ACCESS   read-only
    STATUS       current
    DESCRIPTION
        "Cisco Firepower adaptor:EthPortOutsizedStats:undersizedGoodCrcPac
        ketsDelta managed object property"
    ::= { cfprApAdaptorEthPortOutsizedStatsEntry 30 }

cfprApAdaptorEthPortOutsizedStatsUndersizedGoodCrcPacketsDeltaAvg OBJECT-TYPE
    SYNTAX       Unsigned64
    MAX-ACCESS   read-only
    STATUS       current
    DESCRIPTION
        "Cisco Firepower adaptor:EthPortOutsizedStats:undersizedGoodCrcPac
        ketsDeltaAvg managed object property"
    ::= { cfprApAdaptorEthPortOutsizedStatsEntry 31 }

cfprApAdaptorEthPortOutsizedStatsUndersizedGoodCrcPacketsDeltaMax OBJECT-TYPE
    SYNTAX       Unsigned64
    MAX-ACCESS   read-only
    STATUS       current
    DESCRIPTION
        "Cisco Firepower adaptor:EthPortOutsizedStats:undersizedGoodCrcPac
        ketsDeltaMax managed object property"
    ::= { cfprApAdaptorEthPortOutsizedStatsEntry 32 }

cfprApAdaptorEthPortOutsizedStatsUndersizedGoodCrcPacketsDeltaMin OBJECT-TYPE
    SYNTAX       Unsigned64
    MAX-ACCESS   read-only
    STATUS       current
    DESCRIPTION
        "Cisco Firepower adaptor:EthPortOutsizedStats:undersizedGoodCrcPac
        ketsDeltaMin managed object property"
    ::= { cfprApAdaptorEthPortOutsizedStatsEntry 33 }

cfprApAdaptorEthPortOutsizedStatsUpdate OBJECT-TYPE
    SYNTAX       Gauge32
    MAX-ACCESS   read-only
    STATUS       current
    DESCRIPTION
        "Cisco Firepower adaptor:EthPortOutsizedStats:update
        managed object property"
    ::= { cfprApAdaptorEthPortOutsizedStatsEntry 34 }

cfprApAdaptorEthPortOutsizedStatsHistTable OBJECT-TYPE
    SYNTAX           SEQUENCE OF CfprApAdaptorEthPortOutsizedStatsHistEntry
    MAX-ACCESS       not-accessible
    STATUS           current
    DESCRIPTION
        "Cisco Firepower adaptor:EthPortOutsizedStatsHist
        managed object table"
    ::= { cfprApAdaptorObjects 19 }

cfprApAdaptorEthPortOutsizedStatsHistEntry OBJECT-TYPE
    SYNTAX           CfprApAdaptorEthPortOutsizedStatsHistEntry
    MAX-ACCESS       not-accessible
    STATUS           current
    DESCRIPTION
        "Entry for the cfprApAdaptorEthPortOutsizedStatsHistTable table."
    INDEX { cfprApAdaptorEthPortOutsizedStatsHistInstanceId }
    ::= { cfprApAdaptorEthPortOutsizedStatsHistTable 1 }

CfprApAdaptorEthPortOutsizedStatsHistEntry ::= SEQUENCE {
    cfprApAdaptorEthPortOutsizedStatsHistInstanceId                  CfprApManagedObjectId,
    cfprApAdaptorEthPortOutsizedStatsHistDn                          CfprApManagedObjectDn,
    cfprApAdaptorEthPortOutsizedStatsHistRn                          SnmpAdminString,
    cfprApAdaptorEthPortOutsizedStatsHistId                          Unsigned64,
    cfprApAdaptorEthPortOutsizedStatsHistMostRecent                  TruthValue,
    cfprApAdaptorEthPortOutsizedStatsHistOversizedBadCrcPackets      Unsigned64,
    cfprApAdaptorEthPortOutsizedStatsHistOversizedBadCrcPacketsDelta Unsigned64,
    cfprApAdaptorEthPortOutsizedStatsHistOversizedBadCrcPacketsDeltaAvg Unsigned64,
    cfprApAdaptorEthPortOutsizedStatsHistOversizedBadCrcPacketsDeltaMax Unsigned64,
    cfprApAdaptorEthPortOutsizedStatsHistOversizedBadCrcPacketsDeltaMin Unsigned64,
    cfprApAdaptorEthPortOutsizedStatsHistOversizedGoodCrcPackets     Unsigned64,
    cfprApAdaptorEthPortOutsizedStatsHistOversizedGoodCrcPacketsDelta Unsigned64,
    cfprApAdaptorEthPortOutsizedStatsHistOversizedGoodCrcPacketsDeltaAvg Unsigned64,
    cfprApAdaptorEthPortOutsizedStatsHistOversizedGoodCrcPacketsDeltaMax Unsigned64,
    cfprApAdaptorEthPortOutsizedStatsHistOversizedGoodCrcPacketsDeltaMin Unsigned64,
    cfprApAdaptorEthPortOutsizedStatsHistOversizedPackets            Unsigned64,
    cfprApAdaptorEthPortOutsizedStatsHistOversizedPacketsDelta       Unsigned64,
    cfprApAdaptorEthPortOutsizedStatsHistOversizedPacketsDeltaAvg    Unsigned64,
    cfprApAdaptorEthPortOutsizedStatsHistOversizedPacketsDeltaMax    Unsigned64,
    cfprApAdaptorEthPortOutsizedStatsHistOversizedPacketsDeltaMin    Unsigned64,
    cfprApAdaptorEthPortOutsizedStatsHistSuspect                     TruthValue,
    cfprApAdaptorEthPortOutsizedStatsHistThresholded                 CfprApAdaptorEthPortOutsizedStatsHistThresholded,
    cfprApAdaptorEthPortOutsizedStatsHistTimeCollected               DateAndTime,
    cfprApAdaptorEthPortOutsizedStatsHistUndersizedBadCrcPackets     Unsigned64,
    cfprApAdaptorEthPortOutsizedStatsHistUndersizedBadCrcPacketsDelta Unsigned64,
    cfprApAdaptorEthPortOutsizedStatsHistUndersizedBadCrcPacketsDeltaAvg Unsigned64,
    cfprApAdaptorEthPortOutsizedStatsHistUndersizedBadCrcPacketsDeltaMax Unsigned64,
    cfprApAdaptorEthPortOutsizedStatsHistUndersizedBadCrcPacketsDeltaMin Unsigned64,
    cfprApAdaptorEthPortOutsizedStatsHistUndersizedGoodCrcPackets    Unsigned64,
    cfprApAdaptorEthPortOutsizedStatsHistUndersizedGoodCrcPacketsDelta Unsigned64,
    cfprApAdaptorEthPortOutsizedStatsHistUndersizedGoodCrcPacketsDeltaAvg Unsigned64,
    cfprApAdaptorEthPortOutsizedStatsHistUndersizedGoodCrcPacketsDeltaMax Unsigned64,
    cfprApAdaptorEthPortOutsizedStatsHistUndersizedGoodCrcPacketsDeltaMin Unsigned64
}

cfprApAdaptorEthPortOutsizedStatsHistInstanceId OBJECT-TYPE
    SYNTAX       CfprApManagedObjectId
    MAX-ACCESS   not-accessible
    STATUS       current
    DESCRIPTION
        "Instance identifier of the managed object."
    ::= { cfprApAdaptorEthPortOutsizedStatsHistEntry 1 }

cfprApAdaptorEthPortOutsizedStatsHistDn OBJECT-TYPE
    SYNTAX       CfprApManagedObjectDn
    MAX-ACCESS   read-only
    STATUS       current
    DESCRIPTION
        "Cisco Firepower adaptor:EthPortOutsizedStatsHist:dn
        managed object property"
    ::= { cfprApAdaptorEthPortOutsizedStatsHistEntry 2 }

cfprApAdaptorEthPortOutsizedStatsHistRn OBJECT-TYPE
    SYNTAX       SnmpAdminString
    MAX-ACCESS   read-only
    STATUS       current
    DESCRIPTION
        "Cisco Firepower adaptor:EthPortOutsizedStatsHist:rn
        managed object property"
    ::= { cfprApAdaptorEthPortOutsizedStatsHistEntry 3 }

cfprApAdaptorEthPortOutsizedStatsHistId OBJECT-TYPE
    SYNTAX       Unsigned64
    MAX-ACCESS   read-only
    STATUS       current
    DESCRIPTION
        "Cisco Firepower adaptor:EthPortOutsizedStatsHist:id
        managed object property"
    ::= { cfprApAdaptorEthPortOutsizedStatsHistEntry 4 }

cfprApAdaptorEthPortOutsizedStatsHistMostRecent OBJECT-TYPE
    SYNTAX       TruthValue
    MAX-ACCESS   read-only
    STATUS       current
    DESCRIPTION
        "Cisco Firepower adaptor:EthPortOutsizedStatsHist:mostRecent
        managed object property"
    ::= { cfprApAdaptorEthPortOutsizedStatsHistEntry 5 }

cfprApAdaptorEthPortOutsizedStatsHistOversizedBadCrcPackets OBJECT-TYPE
    SYNTAX       Unsigned64
    MAX-ACCESS   read-only
    STATUS       current
    DESCRIPTION
        "Cisco Firepower adaptor:EthPortOutsizedStatsHist:oversizedBadCrcP
        ackets managed object property"
    ::= { cfprApAdaptorEthPortOutsizedStatsHistEntry 6 }

cfprApAdaptorEthPortOutsizedStatsHistOversizedBadCrcPacketsDelta OBJECT-TYPE
    SYNTAX       Unsigned64
    MAX-ACCESS   read-only
    STATUS       current
    DESCRIPTION
        "Cisco Firepower adaptor:EthPortOutsizedStatsHist:oversizedBadCrcP
        acketsDelta managed object property"
    ::= { cfprApAdaptorEthPortOutsizedStatsHistEntry 7 }

cfprApAdaptorEthPortOutsizedStatsHistOversizedBadCrcPacketsDeltaAvg OBJECT-TYPE
    SYNTAX       Unsigned64
    MAX-ACCESS   read-only
    STATUS       current
    DESCRIPTION
        "Cisco Firepower adaptor:EthPortOutsizedStatsHist:oversizedBadCrcP
        acketsDeltaAvg managed object property"
    ::= { cfprApAdaptorEthPortOutsizedStatsHistEntry 8 }

cfprApAdaptorEthPortOutsizedStatsHistOversizedBadCrcPacketsDeltaMax OBJECT-TYPE
    SYNTAX       Unsigned64
    MAX-ACCESS   read-only
    STATUS       current
    DESCRIPTION
        "Cisco Firepower adaptor:EthPortOutsizedStatsHist:oversizedBadCrcP
        acketsDeltaMax managed object property"
    ::= { cfprApAdaptorEthPortOutsizedStatsHistEntry 9 }

cfprApAdaptorEthPortOutsizedStatsHistOversizedBadCrcPacketsDeltaMin OBJECT-TYPE
    SYNTAX       Unsigned64
    MAX-ACCESS   read-only
    STATUS       current
    DESCRIPTION
        "Cisco Firepower adaptor:EthPortOutsizedStatsHist:oversizedBadCrcP
        acketsDeltaMin managed object property"
    ::= { cfprApAdaptorEthPortOutsizedStatsHistEntry 10 }

cfprApAdaptorEthPortOutsizedStatsHistOversizedGoodCrcPackets OBJECT-TYPE
    SYNTAX       Unsigned64
    MAX-ACCESS   read-only
    STATUS       current
    DESCRIPTION
        "Cisco Firepower adaptor:EthPortOutsizedStatsHist:oversizedGoodCrc
        Packets managed object property"
    ::= { cfprApAdaptorEthPortOutsizedStatsHistEntry 11 }

cfprApAdaptorEthPortOutsizedStatsHistOversizedGoodCrcPacketsDelta OBJECT-TYPE
    SYNTAX       Unsigned64
    MAX-ACCESS   read-only
    STATUS       current
    DESCRIPTION
        "Cisco Firepower adaptor:EthPortOutsizedStatsHist:oversizedGoodCrc
        PacketsDelta managed object property"
    ::= { cfprApAdaptorEthPortOutsizedStatsHistEntry 12 }

cfprApAdaptorEthPortOutsizedStatsHistOversizedGoodCrcPacketsDeltaAvg OBJECT-TYPE
    SYNTAX       Unsigned64
    MAX-ACCESS   read-only
    STATUS       current
    DESCRIPTION
        "Cisco Firepower adaptor:EthPortOutsizedStatsHist:oversizedGoodCrc
        PacketsDeltaAvg managed object property"
    ::= { cfprApAdaptorEthPortOutsizedStatsHistEntry 13 }

cfprApAdaptorEthPortOutsizedStatsHistOversizedGoodCrcPacketsDeltaMax OBJECT-TYPE
    SYNTAX       Unsigned64
    MAX-ACCESS   read-only
    STATUS       current
    DESCRIPTION
        "Cisco Firepower adaptor:EthPortOutsizedStatsHist:oversizedGoodCrc
        PacketsDeltaMax managed object property"
    ::= { cfprApAdaptorEthPortOutsizedStatsHistEntry 14 }

cfprApAdaptorEthPortOutsizedStatsHistOversizedGoodCrcPacketsDeltaMin OBJECT-TYPE
    SYNTAX       Unsigned64
    MAX-ACCESS   read-only
    STATUS       current
    DESCRIPTION
        "Cisco Firepower adaptor:EthPortOutsizedStatsHist:oversizedGoodCrc
        PacketsDeltaMin managed object property"
    ::= { cfprApAdaptorEthPortOutsizedStatsHistEntry 15 }

cfprApAdaptorEthPortOutsizedStatsHistOversizedPackets OBJECT-TYPE
    SYNTAX       Unsigned64
    MAX-ACCESS   read-only
    STATUS       current
    DESCRIPTION
        "Cisco Firepower adaptor:EthPortOutsizedStatsHist:oversizedPackets
         managed object property"
    ::= { cfprApAdaptorEthPortOutsizedStatsHistEntry 16 }

cfprApAdaptorEthPortOutsizedStatsHistOversizedPacketsDelta OBJECT-TYPE
    SYNTAX       Unsigned64
    MAX-ACCESS   read-only
    STATUS       current
    DESCRIPTION
        "Cisco Firepower adaptor:EthPortOutsizedStatsHist:oversizedPackets
        Delta managed object property"
    ::= { cfprApAdaptorEthPortOutsizedStatsHistEntry 17 }

cfprApAdaptorEthPortOutsizedStatsHistOversizedPacketsDeltaAvg OBJECT-TYPE
    SYNTAX       Unsigned64
    MAX-ACCESS   read-only
    STATUS       current
    DESCRIPTION
        "Cisco Firepower adaptor:EthPortOutsizedStatsHist:oversizedPackets
        DeltaAvg managed object property"
    ::= { cfprApAdaptorEthPortOutsizedStatsHistEntry 18 }

cfprApAdaptorEthPortOutsizedStatsHistOversizedPacketsDeltaMax OBJECT-TYPE
    SYNTAX       Unsigned64
    MAX-ACCESS   read-only
    STATUS       current
    DESCRIPTION
        "Cisco Firepower adaptor:EthPortOutsizedStatsHist:oversizedPackets
        DeltaMax managed object property"
    ::= { cfprApAdaptorEthPortOutsizedStatsHistEntry 19 }

cfprApAdaptorEthPortOutsizedStatsHistOversizedPacketsDeltaMin OBJECT-TYPE
    SYNTAX       Unsigned64
    MAX-ACCESS   read-only
    STATUS       current
    DESCRIPTION
        "Cisco Firepower adaptor:EthPortOutsizedStatsHist:oversizedPackets
        DeltaMin managed object property"
    ::= { cfprApAdaptorEthPortOutsizedStatsHistEntry 20 }

cfprApAdaptorEthPortOutsizedStatsHistSuspect OBJECT-TYPE
    SYNTAX       TruthValue
    MAX-ACCESS   read-only
    STATUS       current
    DESCRIPTION
        "Cisco Firepower adaptor:EthPortOutsizedStatsHist:suspect
        managed object property"
    ::= { cfprApAdaptorEthPortOutsizedStatsHistEntry 21 }

cfprApAdaptorEthPortOutsizedStatsHistThresholded OBJECT-TYPE
    SYNTAX       CfprApAdaptorEthPortOutsizedStatsHistThresholded
    MAX-ACCESS   read-only
    STATUS       current
    DESCRIPTION
        "Cisco Firepower adaptor:EthPortOutsizedStatsHist:thresholded
        managed object property"
    ::= { cfprApAdaptorEthPortOutsizedStatsHistEntry 22 }

cfprApAdaptorEthPortOutsizedStatsHistTimeCollected OBJECT-TYPE
    SYNTAX       DateAndTime
    MAX-ACCESS   read-only
    STATUS       current
    DESCRIPTION
        "Cisco Firepower adaptor:EthPortOutsizedStatsHist:timeCollected
        managed object property"
    ::= { cfprApAdaptorEthPortOutsizedStatsHistEntry 23 }

cfprApAdaptorEthPortOutsizedStatsHistUndersizedBadCrcPackets OBJECT-TYPE
    SYNTAX       Unsigned64
    MAX-ACCESS   read-only
    STATUS       current
    DESCRIPTION
        "Cisco Firepower adaptor:EthPortOutsizedStatsHist:undersizedBadCrc
        Packets managed object property"
    ::= { cfprApAdaptorEthPortOutsizedStatsHistEntry 24 }

cfprApAdaptorEthPortOutsizedStatsHistUndersizedBadCrcPacketsDelta OBJECT-TYPE
    SYNTAX       Unsigned64
    MAX-ACCESS   read-only
    STATUS       current
    DESCRIPTION
        "Cisco Firepower adaptor:EthPortOutsizedStatsHist:undersizedBadCrc
        PacketsDelta managed object property"
    ::= { cfprApAdaptorEthPortOutsizedStatsHistEntry 25 }

cfprApAdaptorEthPortOutsizedStatsHistUndersizedBadCrcPacketsDeltaAvg OBJECT-TYPE
    SYNTAX       Unsigned64
    MAX-ACCESS   read-only
    STATUS       current
    DESCRIPTION
        "Cisco Firepower adaptor:EthPortOutsizedStatsHist:undersizedBadCrc
        PacketsDeltaAvg managed object property"
    ::= { cfprApAdaptorEthPortOutsizedStatsHistEntry 26 }

cfprApAdaptorEthPortOutsizedStatsHistUndersizedBadCrcPacketsDeltaMax OBJECT-TYPE
    SYNTAX       Unsigned64
    MAX-ACCESS   read-only
    STATUS       current
    DESCRIPTION
        "Cisco Firepower adaptor:EthPortOutsizedStatsHist:undersizedBadCrc
        PacketsDeltaMax managed object property"
    ::= { cfprApAdaptorEthPortOutsizedStatsHistEntry 27 }

cfprApAdaptorEthPortOutsizedStatsHistUndersizedBadCrcPacketsDeltaMin OBJECT-TYPE
    SYNTAX       Unsigned64
    MAX-ACCESS   read-only
    STATUS       current
    DESCRIPTION
        "Cisco Firepower adaptor:EthPortOutsizedStatsHist:undersizedBadCrc
        PacketsDeltaMin managed object property"
    ::= { cfprApAdaptorEthPortOutsizedStatsHistEntry 28 }

cfprApAdaptorEthPortOutsizedStatsHistUndersizedGoodCrcPackets OBJECT-TYPE
    SYNTAX       Unsigned64
    MAX-ACCESS   read-only
    STATUS       current
    DESCRIPTION
        "Cisco Firepower adaptor:EthPortOutsizedStatsHist:undersizedGoodCr
        cPackets managed object property"
    ::= { cfprApAdaptorEthPortOutsizedStatsHistEntry 29 }

cfprApAdaptorEthPortOutsizedStatsHistUndersizedGoodCrcPacketsDelta OBJECT-TYPE
    SYNTAX       Unsigned64
    MAX-ACCESS   read-only
    STATUS       current
    DESCRIPTION
        "Cisco Firepower adaptor:EthPortOutsizedStatsHist:undersizedGoodCr
        cPacketsDelta managed object property"
    ::= { cfprApAdaptorEthPortOutsizedStatsHistEntry 30 }

cfprApAdaptorEthPortOutsizedStatsHistUndersizedGoodCrcPacketsDeltaAvg OBJECT-TYPE
    SYNTAX       Unsigned64
    MAX-ACCESS   read-only
    STATUS       current
    DESCRIPTION
        "Cisco Firepower adaptor:EthPortOutsizedStatsHist:undersizedGoodCr
        cPacketsDeltaAvg managed object property"
    ::= { cfprApAdaptorEthPortOutsizedStatsHistEntry 31 }

cfprApAdaptorEthPortOutsizedStatsHistUndersizedGoodCrcPacketsDeltaMax OBJECT-TYPE
    SYNTAX       Unsigned64
    MAX-ACCESS   read-only
    STATUS       current
    DESCRIPTION
        "Cisco Firepower adaptor:EthPortOutsizedStatsHist:undersizedGoodCr
        cPacketsDeltaMax managed object property"
    ::= { cfprApAdaptorEthPortOutsizedStatsHistEntry 32 }

cfprApAdaptorEthPortOutsizedStatsHistUndersizedGoodCrcPacketsDeltaMin OBJECT-TYPE
    SYNTAX       Unsigned64
    MAX-ACCESS   read-only
    STATUS       current
    DESCRIPTION
        "Cisco Firepower adaptor:EthPortOutsizedStatsHist:undersizedGoodCr
        cPacketsDeltaMin managed object property"
    ::= { cfprApAdaptorEthPortOutsizedStatsHistEntry 33 }

cfprApAdaptorEthPortStatsTable OBJECT-TYPE
    SYNTAX           SEQUENCE OF CfprApAdaptorEthPortStatsEntry
    MAX-ACCESS       not-accessible
    STATUS           current
    DESCRIPTION
        "Cisco Firepower adaptor:EthPortStats managed object table"
    ::= { cfprApAdaptorObjects 20 }

cfprApAdaptorEthPortStatsEntry OBJECT-TYPE
    SYNTAX           CfprApAdaptorEthPortStatsEntry
    MAX-ACCESS       not-accessible
    STATUS           current
    DESCRIPTION
        "Entry for the cfprApAdaptorEthPortStatsTable table."
    INDEX { cfprApAdaptorEthPortStatsInstanceId }
    ::= { cfprApAdaptorEthPortStatsTable 1 }

CfprApAdaptorEthPortStatsEntry ::= SEQUENCE {
    cfprApAdaptorEthPortStatsInstanceId                              CfprApManagedObjectId,
    cfprApAdaptorEthPortStatsDn                                      CfprApManagedObjectDn,
    cfprApAdaptorEthPortStatsRn                                      SnmpAdminString,
    cfprApAdaptorEthPortStatsGoodPackets                             Unsigned64,
    cfprApAdaptorEthPortStatsGoodPacketsDelta                        Counter64,
    cfprApAdaptorEthPortStatsGoodPacketsDeltaAvg                     Unsigned64,
    cfprApAdaptorEthPortStatsGoodPacketsDeltaMax                     Unsigned64,
    cfprApAdaptorEthPortStatsGoodPacketsDeltaMin                     Unsigned64,
    cfprApAdaptorEthPortStatsIntervals                               Gauge32,
    cfprApAdaptorEthPortStatsPausePackets                            Unsigned64,
    cfprApAdaptorEthPortStatsPausePacketsDelta                       Counter64,
    cfprApAdaptorEthPortStatsPausePacketsDeltaAvg                    Unsigned64,
    cfprApAdaptorEthPortStatsPausePacketsDeltaMax                    Unsigned64,
    cfprApAdaptorEthPortStatsPausePacketsDeltaMin                    Unsigned64,
    cfprApAdaptorEthPortStatsPerPriorityPausePackets                 Unsigned64,
    cfprApAdaptorEthPortStatsPerPriorityPausePacketsDelta            Counter64,
    cfprApAdaptorEthPortStatsPerPriorityPausePacketsDeltaAvg         Unsigned64,
    cfprApAdaptorEthPortStatsPerPriorityPausePacketsDeltaMax         Unsigned64,
    cfprApAdaptorEthPortStatsPerPriorityPausePacketsDeltaMin         Unsigned64,
    cfprApAdaptorEthPortStatsPppPackets                              Unsigned64,
    cfprApAdaptorEthPortStatsPppPacketsDelta                         Counter64,
    cfprApAdaptorEthPortStatsPppPacketsDeltaAvg                      Unsigned64,
    cfprApAdaptorEthPortStatsPppPacketsDeltaMax                      Unsigned64,
    cfprApAdaptorEthPortStatsPppPacketsDeltaMin                      Unsigned64,
    cfprApAdaptorEthPortStatsSuspect                                 TruthValue,
    cfprApAdaptorEthPortStatsThresholded                             CfprApAdaptorEthPortStatsThresholded,
    cfprApAdaptorEthPortStatsTimeCollected                           DateAndTime,
    cfprApAdaptorEthPortStatsTotalPackets                            Unsigned64,
    cfprApAdaptorEthPortStatsTotalPacketsDelta                       Counter64,
    cfprApAdaptorEthPortStatsTotalPacketsDeltaAvg                    Unsigned64,
    cfprApAdaptorEthPortStatsTotalPacketsDeltaMax                    Unsigned64,
    cfprApAdaptorEthPortStatsTotalPacketsDeltaMin                    Unsigned64,
    cfprApAdaptorEthPortStatsTrafficDirection                        CfprApAdaptorAdapterStatsTrafficDir,
    cfprApAdaptorEthPortStatsUpdate                                  Gauge32,
    cfprApAdaptorEthPortStatsVlanPackets                             Unsigned64,
    cfprApAdaptorEthPortStatsVlanPacketsDelta                        Counter64,
    cfprApAdaptorEthPortStatsVlanPacketsDeltaAvg                     Unsigned64,
    cfprApAdaptorEthPortStatsVlanPacketsDeltaMax                     Unsigned64,
    cfprApAdaptorEthPortStatsVlanPacketsDeltaMin                     Unsigned64
}

cfprApAdaptorEthPortStatsInstanceId OBJECT-TYPE
    SYNTAX       CfprApManagedObjectId
    MAX-ACCESS   not-accessible
    STATUS       current
    DESCRIPTION
        "Instance identifier of the managed object."
    ::= { cfprApAdaptorEthPortStatsEntry 1 }

cfprApAdaptorEthPortStatsDn OBJECT-TYPE
    SYNTAX       CfprApManagedObjectDn
    MAX-ACCESS   read-only
    STATUS       current
    DESCRIPTION
        "Cisco Firepower adaptor:EthPortStats:dn managed object property"
    ::= { cfprApAdaptorEthPortStatsEntry 2 }

cfprApAdaptorEthPortStatsRn OBJECT-TYPE
    SYNTAX       SnmpAdminString
    MAX-ACCESS   read-only
    STATUS       current
    DESCRIPTION
        "Cisco Firepower adaptor:EthPortStats:rn managed object property"
    ::= { cfprApAdaptorEthPortStatsEntry 3 }

cfprApAdaptorEthPortStatsGoodPackets OBJECT-TYPE
    SYNTAX       Unsigned64
    MAX-ACCESS   read-only
    STATUS       current
    DESCRIPTION
        "Cisco Firepower adaptor:EthPortStats:goodPackets
        managed object property"
    ::= { cfprApAdaptorEthPortStatsEntry 4 }

cfprApAdaptorEthPortStatsGoodPacketsDelta OBJECT-TYPE
    SYNTAX       Counter64
    MAX-ACCESS   read-only
    STATUS       current
    DESCRIPTION
        "Cisco Firepower adaptor:EthPortStats:goodPacketsDelta
        managed object property"
    ::= { cfprApAdaptorEthPortStatsEntry 5 }

cfprApAdaptorEthPortStatsGoodPacketsDeltaAvg OBJECT-TYPE
    SYNTAX       Unsigned64
    MAX-ACCESS   read-only
    STATUS       current
    DESCRIPTION
        "Cisco Firepower adaptor:EthPortStats:goodPacketsDeltaAvg
        managed object property"
    ::= { cfprApAdaptorEthPortStatsEntry 6 }

cfprApAdaptorEthPortStatsGoodPacketsDeltaMax OBJECT-TYPE
    SYNTAX       Unsigned64
    MAX-ACCESS   read-only
    STATUS       current
    DESCRIPTION
        "Cisco Firepower adaptor:EthPortStats:goodPacketsDeltaMax
        managed object property"
    ::= { cfprApAdaptorEthPortStatsEntry 7 }

cfprApAdaptorEthPortStatsGoodPacketsDeltaMin OBJECT-TYPE
    SYNTAX       Unsigned64
    MAX-ACCESS   read-only
    STATUS       current
    DESCRIPTION
        "Cisco Firepower adaptor:EthPortStats:goodPacketsDeltaMin
        managed object property"
    ::= { cfprApAdaptorEthPortStatsEntry 8 }

cfprApAdaptorEthPortStatsIntervals OBJECT-TYPE
    SYNTAX       Gauge32
    MAX-ACCESS   read-only
    STATUS       current
    DESCRIPTION
        "Cisco Firepower adaptor:EthPortStats:intervals
        managed object property"
    ::= { cfprApAdaptorEthPortStatsEntry 9 }

cfprApAdaptorEthPortStatsPausePackets OBJECT-TYPE
    SYNTAX       Unsigned64
    MAX-ACCESS   read-only
    STATUS       current
    DESCRIPTION
        "Cisco Firepower adaptor:EthPortStats:pausePackets
        managed object property"
    ::= { cfprApAdaptorEthPortStatsEntry 10 }

cfprApAdaptorEthPortStatsPausePacketsDelta OBJECT-TYPE
    SYNTAX       Counter64
    MAX-ACCESS   read-only
    STATUS       current
    DESCRIPTION
        "Cisco Firepower adaptor:EthPortStats:pausePacketsDelta
        managed object property"
    ::= { cfprApAdaptorEthPortStatsEntry 11 }

cfprApAdaptorEthPortStatsPausePacketsDeltaAvg OBJECT-TYPE
    SYNTAX       Unsigned64
    MAX-ACCESS   read-only
    STATUS       current
    DESCRIPTION
        "Cisco Firepower adaptor:EthPortStats:pausePacketsDeltaAvg
        managed object property"
    ::= { cfprApAdaptorEthPortStatsEntry 12 }

cfprApAdaptorEthPortStatsPausePacketsDeltaMax OBJECT-TYPE
    SYNTAX       Unsigned64
    MAX-ACCESS   read-only
    STATUS       current
    DESCRIPTION
        "Cisco Firepower adaptor:EthPortStats:pausePacketsDeltaMax
        managed object property"
    ::= { cfprApAdaptorEthPortStatsEntry 13 }

cfprApAdaptorEthPortStatsPausePacketsDeltaMin OBJECT-TYPE
    SYNTAX       Unsigned64
    MAX-ACCESS   read-only
    STATUS       current
    DESCRIPTION
        "Cisco Firepower adaptor:EthPortStats:pausePacketsDeltaMin
        managed object property"
    ::= { cfprApAdaptorEthPortStatsEntry 14 }

cfprApAdaptorEthPortStatsPerPriorityPausePackets OBJECT-TYPE
    SYNTAX       Unsigned64
    MAX-ACCESS   read-only
    STATUS       current
    DESCRIPTION
        "Cisco Firepower adaptor:EthPortStats:perPriorityPausePackets
        managed object property"
    ::= { cfprApAdaptorEthPortStatsEntry 15 }

cfprApAdaptorEthPortStatsPerPriorityPausePacketsDelta OBJECT-TYPE
    SYNTAX       Counter64
    MAX-ACCESS   read-only
    STATUS       current
    DESCRIPTION
        "Cisco Firepower adaptor:EthPortStats:perPriorityPausePacketsDelta
         managed object property"
    ::= { cfprApAdaptorEthPortStatsEntry 16 }

cfprApAdaptorEthPortStatsPerPriorityPausePacketsDeltaAvg OBJECT-TYPE
    SYNTAX       Unsigned64
    MAX-ACCESS   read-only
    STATUS       current
    DESCRIPTION
        "Cisco Firepower adaptor:EthPortStats:perPriorityPausePacketsDelta
        Avg managed object property"
    ::= { cfprApAdaptorEthPortStatsEntry 17 }

cfprApAdaptorEthPortStatsPerPriorityPausePacketsDeltaMax OBJECT-TYPE
    SYNTAX       Unsigned64
    MAX-ACCESS   read-only
    STATUS       current
    DESCRIPTION
        "Cisco Firepower adaptor:EthPortStats:perPriorityPausePacketsDelta
        Max managed object property"
    ::= { cfprApAdaptorEthPortStatsEntry 18 }

cfprApAdaptorEthPortStatsPerPriorityPausePacketsDeltaMin OBJECT-TYPE
    SYNTAX       Unsigned64
    MAX-ACCESS   read-only
    STATUS       current
    DESCRIPTION
        "Cisco Firepower adaptor:EthPortStats:perPriorityPausePacketsDelta
        Min managed object property"
    ::= { cfprApAdaptorEthPortStatsEntry 19 }

cfprApAdaptorEthPortStatsPppPackets OBJECT-TYPE
    SYNTAX       Unsigned64
    MAX-ACCESS   read-only
    STATUS       current
    DESCRIPTION
        "Cisco Firepower adaptor:EthPortStats:pppPackets
        managed object property"
    ::= { cfprApAdaptorEthPortStatsEntry 20 }

cfprApAdaptorEthPortStatsPppPacketsDelta OBJECT-TYPE
    SYNTAX       Counter64
    MAX-ACCESS   read-only
    STATUS       current
    DESCRIPTION
        "Cisco Firepower adaptor:EthPortStats:pppPacketsDelta
        managed object property"
    ::= { cfprApAdaptorEthPortStatsEntry 21 }

cfprApAdaptorEthPortStatsPppPacketsDeltaAvg OBJECT-TYPE
    SYNTAX       Unsigned64
    MAX-ACCESS   read-only
    STATUS       current
    DESCRIPTION
        "Cisco Firepower adaptor:EthPortStats:pppPacketsDeltaAvg
        managed object property"
    ::= { cfprApAdaptorEthPortStatsEntry 22 }

cfprApAdaptorEthPortStatsPppPacketsDeltaMax OBJECT-TYPE
    SYNTAX       Unsigned64
    MAX-ACCESS   read-only
    STATUS       current
    DESCRIPTION
        "Cisco Firepower adaptor:EthPortStats:pppPacketsDeltaMax
        managed object property"
    ::= { cfprApAdaptorEthPortStatsEntry 23 }

cfprApAdaptorEthPortStatsPppPacketsDeltaMin OBJECT-TYPE
    SYNTAX       Unsigned64
    MAX-ACCESS   read-only
    STATUS       current
    DESCRIPTION
        "Cisco Firepower adaptor:EthPortStats:pppPacketsDeltaMin
        managed object property"
    ::= { cfprApAdaptorEthPortStatsEntry 24 }

cfprApAdaptorEthPortStatsSuspect OBJECT-TYPE
    SYNTAX       TruthValue
    MAX-ACCESS   read-only
    STATUS       current
    DESCRIPTION
        "Cisco Firepower adaptor:EthPortStats:suspect managed
        object property"
    ::= { cfprApAdaptorEthPortStatsEntry 25 }

cfprApAdaptorEthPortStatsThresholded OBJECT-TYPE
    SYNTAX       CfprApAdaptorEthPortStatsThresholded
    MAX-ACCESS   read-only
    STATUS       current
    DESCRIPTION
        "Cisco Firepower adaptor:EthPortStats:thresholded
        managed object property"
    ::= { cfprApAdaptorEthPortStatsEntry 26 }

cfprApAdaptorEthPortStatsTimeCollected OBJECT-TYPE
    SYNTAX       DateAndTime
    MAX-ACCESS   read-only
    STATUS       current
    DESCRIPTION
        "Cisco Firepower adaptor:EthPortStats:timeCollected
        managed object property"
    ::= { cfprApAdaptorEthPortStatsEntry 27 }

cfprApAdaptorEthPortStatsTotalPackets OBJECT-TYPE
    SYNTAX       Unsigned64
    MAX-ACCESS   read-only
    STATUS       current
    DESCRIPTION
        "Cisco Firepower adaptor:EthPortStats:totalPackets
        managed object property"
    ::= { cfprApAdaptorEthPortStatsEntry 28 }

cfprApAdaptorEthPortStatsTotalPacketsDelta OBJECT-TYPE
    SYNTAX       Counter64
    MAX-ACCESS   read-only
    STATUS       current
    DESCRIPTION
        "Cisco Firepower adaptor:EthPortStats:totalPacketsDelta
        managed object property"
    ::= { cfprApAdaptorEthPortStatsEntry 29 }

cfprApAdaptorEthPortStatsTotalPacketsDeltaAvg OBJECT-TYPE
    SYNTAX       Unsigned64
    MAX-ACCESS   read-only
    STATUS       current
    DESCRIPTION
        "Cisco Firepower adaptor:EthPortStats:totalPacketsDeltaAvg
        managed object property"
    ::= { cfprApAdaptorEthPortStatsEntry 30 }

cfprApAdaptorEthPortStatsTotalPacketsDeltaMax OBJECT-TYPE
    SYNTAX       Unsigned64
    MAX-ACCESS   read-only
    STATUS       current
    DESCRIPTION
        "Cisco Firepower adaptor:EthPortStats:totalPacketsDeltaMax
        managed object property"
    ::= { cfprApAdaptorEthPortStatsEntry 31 }

cfprApAdaptorEthPortStatsTotalPacketsDeltaMin OBJECT-TYPE
    SYNTAX       Unsigned64
    MAX-ACCESS   read-only
    STATUS       current
    DESCRIPTION
        "Cisco Firepower adaptor:EthPortStats:totalPacketsDeltaMin
        managed object property"
    ::= { cfprApAdaptorEthPortStatsEntry 32 }

cfprApAdaptorEthPortStatsTrafficDirection OBJECT-TYPE
    SYNTAX       CfprApAdaptorAdapterStatsTrafficDir
    MAX-ACCESS   read-only
    STATUS       current
    DESCRIPTION
        "Cisco Firepower adaptor:EthPortStats:trafficDirection
        managed object property"
    ::= { cfprApAdaptorEthPortStatsEntry 33 }

cfprApAdaptorEthPortStatsUpdate OBJECT-TYPE
    SYNTAX       Gauge32
    MAX-ACCESS   read-only
    STATUS       current
    DESCRIPTION
        "Cisco Firepower adaptor:EthPortStats:update managed
        object property"
    ::= { cfprApAdaptorEthPortStatsEntry 34 }

cfprApAdaptorEthPortStatsVlanPackets OBJECT-TYPE
    SYNTAX       Unsigned64
    MAX-ACCESS   read-only
    STATUS       current
    DESCRIPTION
        "Cisco Firepower adaptor:EthPortStats:vlanPackets
        managed object property"
    ::= { cfprApAdaptorEthPortStatsEntry 35 }

cfprApAdaptorEthPortStatsVlanPacketsDelta OBJECT-TYPE
    SYNTAX       Counter64
    MAX-ACCESS   read-only
    STATUS       current
    DESCRIPTION
        "Cisco Firepower adaptor:EthPortStats:vlanPacketsDelta
        managed object property"
    ::= { cfprApAdaptorEthPortStatsEntry 36 }

cfprApAdaptorEthPortStatsVlanPacketsDeltaAvg OBJECT-TYPE
    SYNTAX       Unsigned64
    MAX-ACCESS   read-only
    STATUS       current
    DESCRIPTION
        "Cisco Firepower adaptor:EthPortStats:vlanPacketsDeltaAvg
        managed object property"
    ::= { cfprApAdaptorEthPortStatsEntry 37 }

cfprApAdaptorEthPortStatsVlanPacketsDeltaMax OBJECT-TYPE
    SYNTAX       Unsigned64
    MAX-ACCESS   read-only
    STATUS       current
    DESCRIPTION
        "Cisco Firepower adaptor:EthPortStats:vlanPacketsDeltaMax
        managed object property"
    ::= { cfprApAdaptorEthPortStatsEntry 38 }

cfprApAdaptorEthPortStatsVlanPacketsDeltaMin OBJECT-TYPE
    SYNTAX       Unsigned64
    MAX-ACCESS   read-only
    STATUS       current
    DESCRIPTION
        "Cisco Firepower adaptor:EthPortStats:vlanPacketsDeltaMin
        managed object property"
    ::= { cfprApAdaptorEthPortStatsEntry 39 }

cfprApAdaptorEthPortStatsHistTable OBJECT-TYPE
    SYNTAX           SEQUENCE OF CfprApAdaptorEthPortStatsHistEntry
    MAX-ACCESS       not-accessible
    STATUS           current
    DESCRIPTION
        "Cisco Firepower adaptor:EthPortStatsHist managed object table"
    ::= { cfprApAdaptorObjects 21 }

cfprApAdaptorEthPortStatsHistEntry OBJECT-TYPE
    SYNTAX           CfprApAdaptorEthPortStatsHistEntry
    MAX-ACCESS       not-accessible
    STATUS           current
    DESCRIPTION
        "Entry for the cfprApAdaptorEthPortStatsHistTable table."
    INDEX { cfprApAdaptorEthPortStatsHistInstanceId }
    ::= { cfprApAdaptorEthPortStatsHistTable 1 }

CfprApAdaptorEthPortStatsHistEntry ::= SEQUENCE {
    cfprApAdaptorEthPortStatsHistInstanceId                          CfprApManagedObjectId,
    cfprApAdaptorEthPortStatsHistDn                                  CfprApManagedObjectDn,
    cfprApAdaptorEthPortStatsHistRn                                  SnmpAdminString,
    cfprApAdaptorEthPortStatsHistGoodPackets                         Unsigned64,
    cfprApAdaptorEthPortStatsHistGoodPacketsDelta                    Unsigned64,
    cfprApAdaptorEthPortStatsHistGoodPacketsDeltaAvg                 Unsigned64,
    cfprApAdaptorEthPortStatsHistGoodPacketsDeltaMax                 Unsigned64,
    cfprApAdaptorEthPortStatsHistGoodPacketsDeltaMin                 Unsigned64,
    cfprApAdaptorEthPortStatsHistId                                  Unsigned64,
    cfprApAdaptorEthPortStatsHistMostRecent                          TruthValue,
    cfprApAdaptorEthPortStatsHistPausePackets                        Unsigned64,
    cfprApAdaptorEthPortStatsHistPausePacketsDelta                   Unsigned64,
    cfprApAdaptorEthPortStatsHistPausePacketsDeltaAvg                Unsigned64,
    cfprApAdaptorEthPortStatsHistPausePacketsDeltaMax                Unsigned64,
    cfprApAdaptorEthPortStatsHistPausePacketsDeltaMin                Unsigned64,
    cfprApAdaptorEthPortStatsHistPerPriorityPausePackets             Unsigned64,
    cfprApAdaptorEthPortStatsHistPerPriorityPausePacketsDelta        Unsigned64,
    cfprApAdaptorEthPortStatsHistPerPriorityPausePacketsDeltaAvg     Unsigned64,
    cfprApAdaptorEthPortStatsHistPerPriorityPausePacketsDeltaMax     Unsigned64,
    cfprApAdaptorEthPortStatsHistPerPriorityPausePacketsDeltaMin     Unsigned64,
    cfprApAdaptorEthPortStatsHistPppPackets                          Unsigned64,
    cfprApAdaptorEthPortStatsHistPppPacketsDelta                     Unsigned64,
    cfprApAdaptorEthPortStatsHistPppPacketsDeltaAvg                  Unsigned64,
    cfprApAdaptorEthPortStatsHistPppPacketsDeltaMax                  Unsigned64,
    cfprApAdaptorEthPortStatsHistPppPacketsDeltaMin                  Unsigned64,
    cfprApAdaptorEthPortStatsHistSuspect                             TruthValue,
    cfprApAdaptorEthPortStatsHistThresholded                         CfprApAdaptorEthPortStatsHistThresholded,
    cfprApAdaptorEthPortStatsHistTimeCollected                       DateAndTime,
    cfprApAdaptorEthPortStatsHistTotalPackets                        Unsigned64,
    cfprApAdaptorEthPortStatsHistTotalPacketsDelta                   Unsigned64,
    cfprApAdaptorEthPortStatsHistTotalPacketsDeltaAvg                Unsigned64,
    cfprApAdaptorEthPortStatsHistTotalPacketsDeltaMax                Unsigned64,
    cfprApAdaptorEthPortStatsHistTotalPacketsDeltaMin                Unsigned64,
    cfprApAdaptorEthPortStatsHistVlanPackets                         Unsigned64,
    cfprApAdaptorEthPortStatsHistVlanPacketsDelta                    Unsigned64,
    cfprApAdaptorEthPortStatsHistVlanPacketsDeltaAvg                 Unsigned64,
    cfprApAdaptorEthPortStatsHistVlanPacketsDeltaMax                 Unsigned64,
    cfprApAdaptorEthPortStatsHistVlanPacketsDeltaMin                 Unsigned64
}

cfprApAdaptorEthPortStatsHistInstanceId OBJECT-TYPE
    SYNTAX       CfprApManagedObjectId
    MAX-ACCESS   not-accessible
    STATUS       current
    DESCRIPTION
        "Instance identifier of the managed object."
    ::= { cfprApAdaptorEthPortStatsHistEntry 1 }

cfprApAdaptorEthPortStatsHistDn OBJECT-TYPE
    SYNTAX       CfprApManagedObjectDn
    MAX-ACCESS   read-only
    STATUS       current
    DESCRIPTION
        "Cisco Firepower adaptor:EthPortStatsHist:dn managed
        object property"
    ::= { cfprApAdaptorEthPortStatsHistEntry 2 }

cfprApAdaptorEthPortStatsHistRn OBJECT-TYPE
    SYNTAX       SnmpAdminString
    MAX-ACCESS   read-only
    STATUS       current
    DESCRIPTION
        "Cisco Firepower adaptor:EthPortStatsHist:rn managed
        object property"
    ::= { cfprApAdaptorEthPortStatsHistEntry 3 }

cfprApAdaptorEthPortStatsHistGoodPackets OBJECT-TYPE
    SYNTAX       Unsigned64
    MAX-ACCESS   read-only
    STATUS       current
    DESCRIPTION
        "Cisco Firepower adaptor:EthPortStatsHist:goodPackets
        managed object property"
    ::= { cfprApAdaptorEthPortStatsHistEntry 4 }

cfprApAdaptorEthPortStatsHistGoodPacketsDelta OBJECT-TYPE
    SYNTAX       Unsigned64
    MAX-ACCESS   read-only
    STATUS       current
    DESCRIPTION
        "Cisco Firepower adaptor:EthPortStatsHist:goodPacketsDelta
        managed object property"
    ::= { cfprApAdaptorEthPortStatsHistEntry 5 }

cfprApAdaptorEthPortStatsHistGoodPacketsDeltaAvg OBJECT-TYPE
    SYNTAX       Unsigned64
    MAX-ACCESS   read-only
    STATUS       current
    DESCRIPTION
        "Cisco Firepower adaptor:EthPortStatsHist:goodPacketsDeltaAvg
        managed object property"
    ::= { cfprApAdaptorEthPortStatsHistEntry 6 }

cfprApAdaptorEthPortStatsHistGoodPacketsDeltaMax OBJECT-TYPE
    SYNTAX       Unsigned64
    MAX-ACCESS   read-only
    STATUS       current
    DESCRIPTION
        "Cisco Firepower adaptor:EthPortStatsHist:goodPacketsDeltaMax
        managed object property"
    ::= { cfprApAdaptorEthPortStatsHistEntry 7 }

cfprApAdaptorEthPortStatsHistGoodPacketsDeltaMin OBJECT-TYPE
    SYNTAX       Unsigned64
    MAX-ACCESS   read-only
    STATUS       current
    DESCRIPTION
        "Cisco Firepower adaptor:EthPortStatsHist:goodPacketsDeltaMin
        managed object property"
    ::= { cfprApAdaptorEthPortStatsHistEntry 8 }

cfprApAdaptorEthPortStatsHistId OBJECT-TYPE
    SYNTAX       Unsigned64
    MAX-ACCESS   read-only
    STATUS       current
    DESCRIPTION
        "Cisco Firepower adaptor:EthPortStatsHist:id managed
        object property"
    ::= { cfprApAdaptorEthPortStatsHistEntry 9 }

cfprApAdaptorEthPortStatsHistMostRecent OBJECT-TYPE
    SYNTAX       TruthValue
    MAX-ACCESS   read-only
    STATUS       current
    DESCRIPTION
        "Cisco Firepower adaptor:EthPortStatsHist:mostRecent
        managed object property"
    ::= { cfprApAdaptorEthPortStatsHistEntry 10 }

cfprApAdaptorEthPortStatsHistPausePackets OBJECT-TYPE
    SYNTAX       Unsigned64
    MAX-ACCESS   read-only
    STATUS       current
    DESCRIPTION
        "Cisco Firepower adaptor:EthPortStatsHist:pausePackets
        managed object property"
    ::= { cfprApAdaptorEthPortStatsHistEntry 11 }

cfprApAdaptorEthPortStatsHistPausePacketsDelta OBJECT-TYPE
    SYNTAX       Unsigned64
    MAX-ACCESS   read-only
    STATUS       current
    DESCRIPTION
        "Cisco Firepower adaptor:EthPortStatsHist:pausePacketsDelta
        managed object property"
    ::= { cfprApAdaptorEthPortStatsHistEntry 12 }

cfprApAdaptorEthPortStatsHistPausePacketsDeltaAvg OBJECT-TYPE
    SYNTAX       Unsigned64
    MAX-ACCESS   read-only
    STATUS       current
    DESCRIPTION
        "Cisco Firepower adaptor:EthPortStatsHist:pausePacketsDeltaAvg
        managed object property"
    ::= { cfprApAdaptorEthPortStatsHistEntry 13 }

cfprApAdaptorEthPortStatsHistPausePacketsDeltaMax OBJECT-TYPE
    SYNTAX       Unsigned64
    MAX-ACCESS   read-only
    STATUS       current
    DESCRIPTION
        "Cisco Firepower adaptor:EthPortStatsHist:pausePacketsDeltaMax
        managed object property"
    ::= { cfprApAdaptorEthPortStatsHistEntry 14 }

cfprApAdaptorEthPortStatsHistPausePacketsDeltaMin OBJECT-TYPE
    SYNTAX       Unsigned64
    MAX-ACCESS   read-only
    STATUS       current
    DESCRIPTION
        "Cisco Firepower adaptor:EthPortStatsHist:pausePacketsDeltaMin
        managed object property"
    ::= { cfprApAdaptorEthPortStatsHistEntry 15 }

cfprApAdaptorEthPortStatsHistPerPriorityPausePackets OBJECT-TYPE
    SYNTAX       Unsigned64
    MAX-ACCESS   read-only
    STATUS       current
    DESCRIPTION
        "Cisco Firepower adaptor:EthPortStatsHist:perPriorityPausePackets
        managed object property"
    ::= { cfprApAdaptorEthPortStatsHistEntry 16 }

cfprApAdaptorEthPortStatsHistPerPriorityPausePacketsDelta OBJECT-TYPE
    SYNTAX       Unsigned64
    MAX-ACCESS   read-only
    STATUS       current
    DESCRIPTION
        "Cisco Firepower adaptor:EthPortStatsHist:perPriorityPausePacketsD
        elta managed object property"
    ::= { cfprApAdaptorEthPortStatsHistEntry 17 }

cfprApAdaptorEthPortStatsHistPerPriorityPausePacketsDeltaAvg OBJECT-TYPE
    SYNTAX       Unsigned64
    MAX-ACCESS   read-only
    STATUS       current
    DESCRIPTION
        "Cisco Firepower adaptor:EthPortStatsHist:perPriorityPausePacketsD
        eltaAvg managed object property"
    ::= { cfprApAdaptorEthPortStatsHistEntry 18 }

cfprApAdaptorEthPortStatsHistPerPriorityPausePacketsDeltaMax OBJECT-TYPE
    SYNTAX       Unsigned64
    MAX-ACCESS   read-only
    STATUS       current
    DESCRIPTION
        "Cisco Firepower adaptor:EthPortStatsHist:perPriorityPausePacketsD
        eltaMax managed object property"
    ::= { cfprApAdaptorEthPortStatsHistEntry 19 }

cfprApAdaptorEthPortStatsHistPerPriorityPausePacketsDeltaMin OBJECT-TYPE
    SYNTAX       Unsigned64
    MAX-ACCESS   read-only
    STATUS       current
    DESCRIPTION
        "Cisco Firepower adaptor:EthPortStatsHist:perPriorityPausePacketsD
        eltaMin managed object property"
    ::= { cfprApAdaptorEthPortStatsHistEntry 20 }

cfprApAdaptorEthPortStatsHistPppPackets OBJECT-TYPE
    SYNTAX       Unsigned64
    MAX-ACCESS   read-only
    STATUS       current
    DESCRIPTION
        "Cisco Firepower adaptor:EthPortStatsHist:pppPackets
        managed object property"
    ::= { cfprApAdaptorEthPortStatsHistEntry 21 }

cfprApAdaptorEthPortStatsHistPppPacketsDelta OBJECT-TYPE
    SYNTAX       Unsigned64
    MAX-ACCESS   read-only
    STATUS       current
    DESCRIPTION
        "Cisco Firepower adaptor:EthPortStatsHist:pppPacketsDelta
        managed object property"
    ::= { cfprApAdaptorEthPortStatsHistEntry 22 }

cfprApAdaptorEthPortStatsHistPppPacketsDeltaAvg OBJECT-TYPE
    SYNTAX       Unsigned64
    MAX-ACCESS   read-only
    STATUS       current
    DESCRIPTION
        "Cisco Firepower adaptor:EthPortStatsHist:pppPacketsDeltaAvg
        managed object property"
    ::= { cfprApAdaptorEthPortStatsHistEntry 23 }

cfprApAdaptorEthPortStatsHistPppPacketsDeltaMax OBJECT-TYPE
    SYNTAX       Unsigned64
    MAX-ACCESS   read-only
    STATUS       current
    DESCRIPTION
        "Cisco Firepower adaptor:EthPortStatsHist:pppPacketsDeltaMax
        managed object property"
    ::= { cfprApAdaptorEthPortStatsHistEntry 24 }

cfprApAdaptorEthPortStatsHistPppPacketsDeltaMin OBJECT-TYPE
    SYNTAX       Unsigned64
    MAX-ACCESS   read-only
    STATUS       current
    DESCRIPTION
        "Cisco Firepower adaptor:EthPortStatsHist:pppPacketsDeltaMin
        managed object property"
    ::= { cfprApAdaptorEthPortStatsHistEntry 25 }

cfprApAdaptorEthPortStatsHistSuspect OBJECT-TYPE
    SYNTAX       TruthValue
    MAX-ACCESS   read-only
    STATUS       current
    DESCRIPTION
        "Cisco Firepower adaptor:EthPortStatsHist:suspect
        managed object property"
    ::= { cfprApAdaptorEthPortStatsHistEntry 26 }

cfprApAdaptorEthPortStatsHistThresholded OBJECT-TYPE
    SYNTAX       CfprApAdaptorEthPortStatsHistThresholded
    MAX-ACCESS   read-only
    STATUS       current
    DESCRIPTION
        "Cisco Firepower adaptor:EthPortStatsHist:thresholded
        managed object property"
    ::= { cfprApAdaptorEthPortStatsHistEntry 27 }

cfprApAdaptorEthPortStatsHistTimeCollected OBJECT-TYPE
    SYNTAX       DateAndTime
    MAX-ACCESS   read-only
    STATUS       current
    DESCRIPTION
        "Cisco Firepower adaptor:EthPortStatsHist:timeCollected
        managed object property"
    ::= { cfprApAdaptorEthPortStatsHistEntry 28 }

cfprApAdaptorEthPortStatsHistTotalPackets OBJECT-TYPE
    SYNTAX       Unsigned64
    MAX-ACCESS   read-only
    STATUS       current
    DESCRIPTION
        "Cisco Firepower adaptor:EthPortStatsHist:totalPackets
        managed object property"
    ::= { cfprApAdaptorEthPortStatsHistEntry 29 }

cfprApAdaptorEthPortStatsHistTotalPacketsDelta OBJECT-TYPE
    SYNTAX       Unsigned64
    MAX-ACCESS   read-only
    STATUS       current
    DESCRIPTION
        "Cisco Firepower adaptor:EthPortStatsHist:totalPacketsDelta
        managed object property"
    ::= { cfprApAdaptorEthPortStatsHistEntry 30 }

cfprApAdaptorEthPortStatsHistTotalPacketsDeltaAvg OBJECT-TYPE
    SYNTAX       Unsigned64
    MAX-ACCESS   read-only
    STATUS       current
    DESCRIPTION
        "Cisco Firepower adaptor:EthPortStatsHist:totalPacketsDeltaAvg
        managed object property"
    ::= { cfprApAdaptorEthPortStatsHistEntry 31 }

cfprApAdaptorEthPortStatsHistTotalPacketsDeltaMax OBJECT-TYPE
    SYNTAX       Unsigned64
    MAX-ACCESS   read-only
    STATUS       current
    DESCRIPTION
        "Cisco Firepower adaptor:EthPortStatsHist:totalPacketsDeltaMax
        managed object property"
    ::= { cfprApAdaptorEthPortStatsHistEntry 32 }

cfprApAdaptorEthPortStatsHistTotalPacketsDeltaMin OBJECT-TYPE
    SYNTAX       Unsigned64
    MAX-ACCESS   read-only
    STATUS       current
    DESCRIPTION
        "Cisco Firepower adaptor:EthPortStatsHist:totalPacketsDeltaMin
        managed object property"
    ::= { cfprApAdaptorEthPortStatsHistEntry 33 }

cfprApAdaptorEthPortStatsHistVlanPackets OBJECT-TYPE
    SYNTAX       Unsigned64
    MAX-ACCESS   read-only
    STATUS       current
    DESCRIPTION
        "Cisco Firepower adaptor:EthPortStatsHist:vlanPackets
        managed object property"
    ::= { cfprApAdaptorEthPortStatsHistEntry 34 }

cfprApAdaptorEthPortStatsHistVlanPacketsDelta OBJECT-TYPE
    SYNTAX       Unsigned64
    MAX-ACCESS   read-only
    STATUS       current
    DESCRIPTION
        "Cisco Firepower adaptor:EthPortStatsHist:vlanPacketsDelta
        managed object property"
    ::= { cfprApAdaptorEthPortStatsHistEntry 35 }

cfprApAdaptorEthPortStatsHistVlanPacketsDeltaAvg OBJECT-TYPE
    SYNTAX       Unsigned64
    MAX-ACCESS   read-only
    STATUS       current
    DESCRIPTION
        "Cisco Firepower adaptor:EthPortStatsHist:vlanPacketsDeltaAvg
        managed object property"
    ::= { cfprApAdaptorEthPortStatsHistEntry 36 }

cfprApAdaptorEthPortStatsHistVlanPacketsDeltaMax OBJECT-TYPE
    SYNTAX       Unsigned64
    MAX-ACCESS   read-only
    STATUS       current
    DESCRIPTION
        "Cisco Firepower adaptor:EthPortStatsHist:vlanPacketsDeltaMax
        managed object property"
    ::= { cfprApAdaptorEthPortStatsHistEntry 37 }

cfprApAdaptorEthPortStatsHistVlanPacketsDeltaMin OBJECT-TYPE
    SYNTAX       Unsigned64
    MAX-ACCESS   read-only
    STATUS       current
    DESCRIPTION
        "Cisco Firepower adaptor:EthPortStatsHist:vlanPacketsDeltaMin
        managed object property"
    ::= { cfprApAdaptorEthPortStatsHistEntry 38 }

cfprApAdaptorEthRecvQueueProfileTable OBJECT-TYPE
    SYNTAX           SEQUENCE OF CfprApAdaptorEthRecvQueueProfileEntry
    MAX-ACCESS       not-accessible
    STATUS           current
    DESCRIPTION
        "Cisco Firepower adaptor:EthRecvQueueProfile managed object table"
    ::= { cfprApAdaptorObjects 22 }

cfprApAdaptorEthRecvQueueProfileEntry OBJECT-TYPE
    SYNTAX           CfprApAdaptorEthRecvQueueProfileEntry
    MAX-ACCESS       not-accessible
    STATUS           current
    DESCRIPTION
        "Entry for the cfprApAdaptorEthRecvQueueProfileTable table."
    INDEX { cfprApAdaptorEthRecvQueueProfileInstanceId }
    ::= { cfprApAdaptorEthRecvQueueProfileTable 1 }

CfprApAdaptorEthRecvQueueProfileEntry ::= SEQUENCE {
    cfprApAdaptorEthRecvQueueProfileInstanceId                       CfprApManagedObjectId,
    cfprApAdaptorEthRecvQueueProfileDn                               CfprApManagedObjectDn,
    cfprApAdaptorEthRecvQueueProfileRn                               SnmpAdminString,
    cfprApAdaptorEthRecvQueueProfileCount                            Gauge32,
    cfprApAdaptorEthRecvQueueProfileRingSize                         Gauge32
}

cfprApAdaptorEthRecvQueueProfileInstanceId OBJECT-TYPE
    SYNTAX       CfprApManagedObjectId
    MAX-ACCESS   not-accessible
    STATUS       current
    DESCRIPTION
        "Instance identifier of the managed object."
    ::= { cfprApAdaptorEthRecvQueueProfileEntry 1 }

cfprApAdaptorEthRecvQueueProfileDn OBJECT-TYPE
    SYNTAX       CfprApManagedObjectDn
    MAX-ACCESS   read-only
    STATUS       current
    DESCRIPTION
        "Cisco Firepower adaptor:EthRecvQueueProfile:dn
        managed object property"
    ::= { cfprApAdaptorEthRecvQueueProfileEntry 2 }

cfprApAdaptorEthRecvQueueProfileRn OBJECT-TYPE
    SYNTAX       SnmpAdminString
    MAX-ACCESS   read-only
    STATUS       current
    DESCRIPTION
        "Cisco Firepower adaptor:EthRecvQueueProfile:rn
        managed object property"
    ::= { cfprApAdaptorEthRecvQueueProfileEntry 3 }

cfprApAdaptorEthRecvQueueProfileCount OBJECT-TYPE
    SYNTAX       Gauge32
    MAX-ACCESS   read-only
    STATUS       current
    DESCRIPTION
        "Cisco Firepower adaptor:EthRecvQueueProfile:count
        managed object property"
    ::= { cfprApAdaptorEthRecvQueueProfileEntry 4 }

cfprApAdaptorEthRecvQueueProfileRingSize OBJECT-TYPE
    SYNTAX       Gauge32
    MAX-ACCESS   read-only
    STATUS       current
    DESCRIPTION
        "Cisco Firepower adaptor:EthRecvQueueProfile:ringSize
        managed object property"
    ::= { cfprApAdaptorEthRecvQueueProfileEntry 5 }

cfprApAdaptorEthRoCEProfileTable OBJECT-TYPE
    SYNTAX           SEQUENCE OF CfprApAdaptorEthRoCEProfileEntry
    MAX-ACCESS       not-accessible
    STATUS           current
    DESCRIPTION
        "Cisco Firepower adaptor:EthRoCEProfile managed object table"
    ::= { cfprApAdaptorObjects 23 }

cfprApAdaptorEthRoCEProfileEntry OBJECT-TYPE
    SYNTAX           CfprApAdaptorEthRoCEProfileEntry
    MAX-ACCESS       not-accessible
    STATUS           current
    DESCRIPTION
        "Entry for the cfprApAdaptorEthRoCEProfileTable table."
    INDEX { cfprApAdaptorEthRoCEProfileInstanceId }
    ::= { cfprApAdaptorEthRoCEProfileTable 1 }

CfprApAdaptorEthRoCEProfileEntry ::= SEQUENCE {
    cfprApAdaptorEthRoCEProfileInstanceId                            CfprApManagedObjectId,
    cfprApAdaptorEthRoCEProfileDn                                    CfprApManagedObjectDn,
    cfprApAdaptorEthRoCEProfileRn                                    SnmpAdminString,
    cfprApAdaptorEthRoCEProfileAdminState                            CfprApAdaptorEthRoCEProfileAdminState,
    cfprApAdaptorEthRoCEProfileMemoryRegions                         Gauge32,
    cfprApAdaptorEthRoCEProfileQueuePairs                            Gauge32,
    cfprApAdaptorEthRoCEProfileResourceGroups                        Gauge32
}

cfprApAdaptorEthRoCEProfileInstanceId OBJECT-TYPE
    SYNTAX       CfprApManagedObjectId
    MAX-ACCESS   not-accessible
    STATUS       current
    DESCRIPTION
        "Instance identifier of the managed object."
    ::= { cfprApAdaptorEthRoCEProfileEntry 1 }

cfprApAdaptorEthRoCEProfileDn OBJECT-TYPE
    SYNTAX       CfprApManagedObjectDn
    MAX-ACCESS   read-only
    STATUS       current
    DESCRIPTION
        "Cisco Firepower adaptor:EthRoCEProfile:dn managed
        object property"
    ::= { cfprApAdaptorEthRoCEProfileEntry 2 }

cfprApAdaptorEthRoCEProfileRn OBJECT-TYPE
    SYNTAX       SnmpAdminString
    MAX-ACCESS   read-only
    STATUS       current
    DESCRIPTION
        "Cisco Firepower adaptor:EthRoCEProfile:rn managed
        object property"
    ::= { cfprApAdaptorEthRoCEProfileEntry 3 }

cfprApAdaptorEthRoCEProfileAdminState OBJECT-TYPE
    SYNTAX       CfprApAdaptorEthRoCEProfileAdminState
    MAX-ACCESS   read-only
    STATUS       current
    DESCRIPTION
        "Cisco Firepower adaptor:EthRoCEProfile:adminState
        managed object property"
    ::= { cfprApAdaptorEthRoCEProfileEntry 4 }

cfprApAdaptorEthRoCEProfileMemoryRegions OBJECT-TYPE
    SYNTAX       Gauge32
    MAX-ACCESS   read-only
    STATUS       current
    DESCRIPTION
        "Cisco Firepower adaptor:EthRoCEProfile:memoryRegions
        managed object property"
    ::= { cfprApAdaptorEthRoCEProfileEntry 5 }

cfprApAdaptorEthRoCEProfileQueuePairs OBJECT-TYPE
    SYNTAX       Gauge32
    MAX-ACCESS   read-only
    STATUS       current
    DESCRIPTION
        "Cisco Firepower adaptor:EthRoCEProfile:queuePairs
        managed object property"
    ::= { cfprApAdaptorEthRoCEProfileEntry 6 }

cfprApAdaptorEthRoCEProfileResourceGroups OBJECT-TYPE
    SYNTAX       Gauge32
    MAX-ACCESS   read-only
    STATUS       current
    DESCRIPTION
        "Cisco Firepower adaptor:EthRoCEProfile:resourceGroups
        managed object property"
    ::= { cfprApAdaptorEthRoCEProfileEntry 7 }

cfprApAdaptorEthVxLANProfileTable OBJECT-TYPE
    SYNTAX           SEQUENCE OF CfprApAdaptorEthVxLANProfileEntry
    MAX-ACCESS       not-accessible
    STATUS           current
    DESCRIPTION
        "Cisco Firepower adaptor:EthVxLANProfile managed object table"
    ::= { cfprApAdaptorObjects 24 }

cfprApAdaptorEthVxLANProfileEntry OBJECT-TYPE
    SYNTAX           CfprApAdaptorEthVxLANProfileEntry
    MAX-ACCESS       not-accessible
    STATUS           current
    DESCRIPTION
        "Entry for the cfprApAdaptorEthVxLANProfileTable table."
    INDEX { cfprApAdaptorEthVxLANProfileInstanceId }
    ::= { cfprApAdaptorEthVxLANProfileTable 1 }

CfprApAdaptorEthVxLANProfileEntry ::= SEQUENCE {
    cfprApAdaptorEthVxLANProfileInstanceId                           CfprApManagedObjectId,
    cfprApAdaptorEthVxLANProfileDn                                   CfprApManagedObjectDn,
    cfprApAdaptorEthVxLANProfileRn                                   SnmpAdminString,
    cfprApAdaptorEthVxLANProfileAdminState                           CfprApAdaptorEthVxLANProfileAdminState
}

cfprApAdaptorEthVxLANProfileInstanceId OBJECT-TYPE
    SYNTAX       CfprApManagedObjectId
    MAX-ACCESS   not-accessible
    STATUS       current
    DESCRIPTION
        "Instance identifier of the managed object."
    ::= { cfprApAdaptorEthVxLANProfileEntry 1 }

cfprApAdaptorEthVxLANProfileDn OBJECT-TYPE
    SYNTAX       CfprApManagedObjectDn
    MAX-ACCESS   read-only
    STATUS       current
    DESCRIPTION
        "Cisco Firepower adaptor:EthVxLANProfile:dn managed
        object property"
    ::= { cfprApAdaptorEthVxLANProfileEntry 2 }

cfprApAdaptorEthVxLANProfileRn OBJECT-TYPE
    SYNTAX       SnmpAdminString
    MAX-ACCESS   read-only
    STATUS       current
    DESCRIPTION
        "Cisco Firepower adaptor:EthVxLANProfile:rn managed
        object property"
    ::= { cfprApAdaptorEthVxLANProfileEntry 3 }

cfprApAdaptorEthVxLANProfileAdminState OBJECT-TYPE
    SYNTAX       CfprApAdaptorEthVxLANProfileAdminState
    MAX-ACCESS   read-only
    STATUS       current
    DESCRIPTION
        "Cisco Firepower adaptor:EthVxLANProfile:adminState
        managed object property"
    ::= { cfprApAdaptorEthVxLANProfileEntry 4 }

cfprApAdaptorEthWorkQueueProfileTable OBJECT-TYPE
    SYNTAX           SEQUENCE OF CfprApAdaptorEthWorkQueueProfileEntry
    MAX-ACCESS       not-accessible
    STATUS           current
    DESCRIPTION
        "Cisco Firepower adaptor:EthWorkQueueProfile managed object table"
    ::= { cfprApAdaptorObjects 25 }

cfprApAdaptorEthWorkQueueProfileEntry OBJECT-TYPE
    SYNTAX           CfprApAdaptorEthWorkQueueProfileEntry
    MAX-ACCESS       not-accessible
    STATUS           current
    DESCRIPTION
        "Entry for the cfprApAdaptorEthWorkQueueProfileTable table."
    INDEX { cfprApAdaptorEthWorkQueueProfileInstanceId }
    ::= { cfprApAdaptorEthWorkQueueProfileTable 1 }

CfprApAdaptorEthWorkQueueProfileEntry ::= SEQUENCE {
    cfprApAdaptorEthWorkQueueProfileInstanceId                       CfprApManagedObjectId,
    cfprApAdaptorEthWorkQueueProfileDn                               CfprApManagedObjectDn,
    cfprApAdaptorEthWorkQueueProfileRn                               SnmpAdminString,
    cfprApAdaptorEthWorkQueueProfileCount                            Gauge32,
    cfprApAdaptorEthWorkQueueProfileRingSize                         Gauge32
}

cfprApAdaptorEthWorkQueueProfileInstanceId OBJECT-TYPE
    SYNTAX       CfprApManagedObjectId
    MAX-ACCESS   not-accessible
    STATUS       current
    DESCRIPTION
        "Instance identifier of the managed object."
    ::= { cfprApAdaptorEthWorkQueueProfileEntry 1 }

cfprApAdaptorEthWorkQueueProfileDn OBJECT-TYPE
    SYNTAX       CfprApManagedObjectDn
    MAX-ACCESS   read-only
    STATUS       current
    DESCRIPTION
        "Cisco Firepower adaptor:EthWorkQueueProfile:dn
        managed object property"
    ::= { cfprApAdaptorEthWorkQueueProfileEntry 2 }

cfprApAdaptorEthWorkQueueProfileRn OBJECT-TYPE
    SYNTAX       SnmpAdminString
    MAX-ACCESS   read-only
    STATUS       current
    DESCRIPTION
        "Cisco Firepower adaptor:EthWorkQueueProfile:rn
        managed object property"
    ::= { cfprApAdaptorEthWorkQueueProfileEntry 3 }

cfprApAdaptorEthWorkQueueProfileCount OBJECT-TYPE
    SYNTAX       Gauge32
    MAX-ACCESS   read-only
    STATUS       current
    DESCRIPTION
        "Cisco Firepower adaptor:EthWorkQueueProfile:count
        managed object property"
    ::= { cfprApAdaptorEthWorkQueueProfileEntry 4 }

cfprApAdaptorEthWorkQueueProfileRingSize OBJECT-TYPE
    SYNTAX       Gauge32
    MAX-ACCESS   read-only
    STATUS       current
    DESCRIPTION
        "Cisco Firepower adaptor:EthWorkQueueProfile:ringSize
        managed object property"
    ::= { cfprApAdaptorEthWorkQueueProfileEntry 5 }

cfprApAdaptorEtherIfStatsTable OBJECT-TYPE
    SYNTAX           SEQUENCE OF CfprApAdaptorEtherIfStatsEntry
    MAX-ACCESS       not-accessible
    STATUS           current
    DESCRIPTION
        "Cisco Firepower adaptor:EtherIfStats managed object table"
    ::= { cfprApAdaptorObjects 26 }

cfprApAdaptorEtherIfStatsEntry OBJECT-TYPE
    SYNTAX           CfprApAdaptorEtherIfStatsEntry
    MAX-ACCESS       not-accessible
    STATUS           current
    DESCRIPTION
        "Entry for the cfprApAdaptorEtherIfStatsTable table."
    INDEX { cfprApAdaptorEtherIfStatsInstanceId }
    ::= { cfprApAdaptorEtherIfStatsTable 1 }

CfprApAdaptorEtherIfStatsEntry ::= SEQUENCE {
    cfprApAdaptorEtherIfStatsInstanceId                              CfprApManagedObjectId,
    cfprApAdaptorEtherIfStatsDn                                      CfprApManagedObjectDn,
    cfprApAdaptorEtherIfStatsRn                                      SnmpAdminString,
    cfprApAdaptorEtherIfStatsIntervals                               Gauge32,
    cfprApAdaptorEtherIfStatsRxBytes                                 Gauge32,
    cfprApAdaptorEtherIfStatsRxBytesDelta                            Counter32,
    cfprApAdaptorEtherIfStatsRxBytesDeltaAvg                         Gauge32,
    cfprApAdaptorEtherIfStatsRxBytesDeltaMax                         Gauge32,
    cfprApAdaptorEtherIfStatsRxBytesDeltaMin                         Gauge32,
    cfprApAdaptorEtherIfStatsRxDropped                               Gauge32,
    cfprApAdaptorEtherIfStatsRxDroppedDelta                          Counter32,
    cfprApAdaptorEtherIfStatsRxDroppedDeltaAvg                       Gauge32,
    cfprApAdaptorEtherIfStatsRxDroppedDeltaMax                       Gauge32,
    cfprApAdaptorEtherIfStatsRxDroppedDeltaMin                       Gauge32,
    cfprApAdaptorEtherIfStatsRxErrors                                Gauge32,
    cfprApAdaptorEtherIfStatsRxErrorsDelta                           Counter32,
    cfprApAdaptorEtherIfStatsRxErrorsDeltaAvg                        Gauge32,
    cfprApAdaptorEtherIfStatsRxErrorsDeltaMax                        Gauge32,
    cfprApAdaptorEtherIfStatsRxErrorsDeltaMin                        Gauge32,
    cfprApAdaptorEtherIfStatsRxPackets                               Gauge32,
    cfprApAdaptorEtherIfStatsRxPacketsDelta                          Counter32,
    cfprApAdaptorEtherIfStatsRxPacketsDeltaAvg                       Gauge32,
    cfprApAdaptorEtherIfStatsRxPacketsDeltaMax                       Gauge32,
    cfprApAdaptorEtherIfStatsRxPacketsDeltaMin                       Gauge32,
    cfprApAdaptorEtherIfStatsSuspect                                 TruthValue,
    cfprApAdaptorEtherIfStatsThresholded                             CfprApAdaptorEtherIfStatsThresholded,
    cfprApAdaptorEtherIfStatsTimeCollected                           DateAndTime,
    cfprApAdaptorEtherIfStatsTxBytes                                 Gauge32,
    cfprApAdaptorEtherIfStatsTxBytesDelta                            Counter32,
    cfprApAdaptorEtherIfStatsTxBytesDeltaAvg                         Gauge32,
    cfprApAdaptorEtherIfStatsTxBytesDeltaMax                         Gauge32,
    cfprApAdaptorEtherIfStatsTxBytesDeltaMin                         Gauge32,
    cfprApAdaptorEtherIfStatsTxDropped                               Gauge32,
    cfprApAdaptorEtherIfStatsTxDroppedDelta                          Counter32,
    cfprApAdaptorEtherIfStatsTxDroppedDeltaAvg                       Gauge32,
    cfprApAdaptorEtherIfStatsTxDroppedDeltaMax                       Gauge32,
    cfprApAdaptorEtherIfStatsTxDroppedDeltaMin                       Gauge32,
    cfprApAdaptorEtherIfStatsTxErrors                                Gauge32,
    cfprApAdaptorEtherIfStatsTxErrorsDelta                           Counter32,
    cfprApAdaptorEtherIfStatsTxErrorsDeltaAvg                        Gauge32,
    cfprApAdaptorEtherIfStatsTxErrorsDeltaMax                        Gauge32,
    cfprApAdaptorEtherIfStatsTxErrorsDeltaMin                        Gauge32,
    cfprApAdaptorEtherIfStatsTxPackets                               Gauge32,
    cfprApAdaptorEtherIfStatsTxPacketsDelta                          Counter32,
    cfprApAdaptorEtherIfStatsTxPacketsDeltaAvg                       Gauge32,
    cfprApAdaptorEtherIfStatsTxPacketsDeltaMax                       Gauge32,
    cfprApAdaptorEtherIfStatsTxPacketsDeltaMin                       Gauge32,
    cfprApAdaptorEtherIfStatsUpdate                                  Gauge32
}

cfprApAdaptorEtherIfStatsInstanceId OBJECT-TYPE
    SYNTAX       CfprApManagedObjectId
    MAX-ACCESS   not-accessible
    STATUS       current
    DESCRIPTION
        "Instance identifier of the managed object."
    ::= { cfprApAdaptorEtherIfStatsEntry 1 }

cfprApAdaptorEtherIfStatsDn OBJECT-TYPE
    SYNTAX       CfprApManagedObjectDn
    MAX-ACCESS   read-only
    STATUS       current
    DESCRIPTION
        "Cisco Firepower adaptor:EtherIfStats:dn managed object property"
    ::= { cfprApAdaptorEtherIfStatsEntry 2 }

cfprApAdaptorEtherIfStatsRn OBJECT-TYPE
    SYNTAX       SnmpAdminString
    MAX-ACCESS   read-only
    STATUS       current
    DESCRIPTION
        "Cisco Firepower adaptor:EtherIfStats:rn managed object property"
    ::= { cfprApAdaptorEtherIfStatsEntry 3 }

cfprApAdaptorEtherIfStatsIntervals OBJECT-TYPE
    SYNTAX       Gauge32
    MAX-ACCESS   read-only
    STATUS       current
    DESCRIPTION
        "Cisco Firepower adaptor:EtherIfStats:intervals
        managed object property"
    ::= { cfprApAdaptorEtherIfStatsEntry 4 }

cfprApAdaptorEtherIfStatsRxBytes OBJECT-TYPE
    SYNTAX       Gauge32
    MAX-ACCESS   read-only
    STATUS       current
    DESCRIPTION
        "Cisco Firepower adaptor:EtherIfStats:rxBytes managed
        object property"
    ::= { cfprApAdaptorEtherIfStatsEntry 5 }

cfprApAdaptorEtherIfStatsRxBytesDelta OBJECT-TYPE
    SYNTAX       Counter32
    MAX-ACCESS   read-only
    STATUS       current
    DESCRIPTION
        "Cisco Firepower adaptor:EtherIfStats:rxBytesDelta
        managed object property"
    ::= { cfprApAdaptorEtherIfStatsEntry 6 }

cfprApAdaptorEtherIfStatsRxBytesDeltaAvg OBJECT-TYPE
    SYNTAX       Gauge32
    MAX-ACCESS   read-only
    STATUS       current
    DESCRIPTION
        "Cisco Firepower adaptor:EtherIfStats:rxBytesDeltaAvg
        managed object property"
    ::= { cfprApAdaptorEtherIfStatsEntry 7 }

cfprApAdaptorEtherIfStatsRxBytesDeltaMax OBJECT-TYPE
    SYNTAX       Gauge32
    MAX-ACCESS   read-only
    STATUS       current
    DESCRIPTION
        "Cisco Firepower adaptor:EtherIfStats:rxBytesDeltaMax
        managed object property"
    ::= { cfprApAdaptorEtherIfStatsEntry 8 }

cfprApAdaptorEtherIfStatsRxBytesDeltaMin OBJECT-TYPE
    SYNTAX       Gauge32
    MAX-ACCESS   read-only
    STATUS       current
    DESCRIPTION
        "Cisco Firepower adaptor:EtherIfStats:rxBytesDeltaMin
        managed object property"
    ::= { cfprApAdaptorEtherIfStatsEntry 9 }

cfprApAdaptorEtherIfStatsRxDropped OBJECT-TYPE
    SYNTAX       Gauge32
    MAX-ACCESS   read-only
    STATUS       current
    DESCRIPTION
        "Cisco Firepower adaptor:EtherIfStats:rxDropped
        managed object property"
    ::= { cfprApAdaptorEtherIfStatsEntry 10 }

cfprApAdaptorEtherIfStatsRxDroppedDelta OBJECT-TYPE
    SYNTAX       Counter32
    MAX-ACCESS   read-only
    STATUS       current
    DESCRIPTION
        "Cisco Firepower adaptor:EtherIfStats:rxDroppedDelta
        managed object property"
    ::= { cfprApAdaptorEtherIfStatsEntry 11 }

cfprApAdaptorEtherIfStatsRxDroppedDeltaAvg OBJECT-TYPE
    SYNTAX       Gauge32
    MAX-ACCESS   read-only
    STATUS       current
    DESCRIPTION
        "Cisco Firepower adaptor:EtherIfStats:rxDroppedDeltaAvg
        managed object property"
    ::= { cfprApAdaptorEtherIfStatsEntry 12 }

cfprApAdaptorEtherIfStatsRxDroppedDeltaMax OBJECT-TYPE
    SYNTAX       Gauge32
    MAX-ACCESS   read-only
    STATUS       current
    DESCRIPTION
        "Cisco Firepower adaptor:EtherIfStats:rxDroppedDeltaMax
        managed object property"
    ::= { cfprApAdaptorEtherIfStatsEntry 13 }

cfprApAdaptorEtherIfStatsRxDroppedDeltaMin OBJECT-TYPE
    SYNTAX       Gauge32
    MAX-ACCESS   read-only
    STATUS       current
    DESCRIPTION
        "Cisco Firepower adaptor:EtherIfStats:rxDroppedDeltaMin
        managed object property"
    ::= { cfprApAdaptorEtherIfStatsEntry 14 }

cfprApAdaptorEtherIfStatsRxErrors OBJECT-TYPE
    SYNTAX       Gauge32
    MAX-ACCESS   read-only
    STATUS       current
    DESCRIPTION
        "Cisco Firepower adaptor:EtherIfStats:rxErrors
        managed object property"
    ::= { cfprApAdaptorEtherIfStatsEntry 15 }

cfprApAdaptorEtherIfStatsRxErrorsDelta OBJECT-TYPE
    SYNTAX       Counter32
    MAX-ACCESS   read-only
    STATUS       current
    DESCRIPTION
        "Cisco Firepower adaptor:EtherIfStats:rxErrorsDelta
        managed object property"
    ::= { cfprApAdaptorEtherIfStatsEntry 16 }

cfprApAdaptorEtherIfStatsRxErrorsDeltaAvg OBJECT-TYPE
    SYNTAX       Gauge32
    MAX-ACCESS   read-only
    STATUS       current
    DESCRIPTION
        "Cisco Firepower adaptor:EtherIfStats:rxErrorsDeltaAvg
        managed object property"
    ::= { cfprApAdaptorEtherIfStatsEntry 17 }

cfprApAdaptorEtherIfStatsRxErrorsDeltaMax OBJECT-TYPE
    SYNTAX       Gauge32
    MAX-ACCESS   read-only
    STATUS       current
    DESCRIPTION
        "Cisco Firepower adaptor:EtherIfStats:rxErrorsDeltaMax
        managed object property"
    ::= { cfprApAdaptorEtherIfStatsEntry 18 }

cfprApAdaptorEtherIfStatsRxErrorsDeltaMin OBJECT-TYPE
    SYNTAX       Gauge32
    MAX-ACCESS   read-only
    STATUS       current
    DESCRIPTION
        "Cisco Firepower adaptor:EtherIfStats:rxErrorsDeltaMin
        managed object property"
    ::= { cfprApAdaptorEtherIfStatsEntry 19 }

cfprApAdaptorEtherIfStatsRxPackets OBJECT-TYPE
    SYNTAX       Gauge32
    MAX-ACCESS   read-only
    STATUS       current
    DESCRIPTION
        "Cisco Firepower adaptor:EtherIfStats:rxPackets
        managed object property"
    ::= { cfprApAdaptorEtherIfStatsEntry 20 }

cfprApAdaptorEtherIfStatsRxPacketsDelta OBJECT-TYPE
    SYNTAX       Counter32
    MAX-ACCESS   read-only
    STATUS       current
    DESCRIPTION
        "Cisco Firepower adaptor:EtherIfStats:rxPacketsDelta
        managed object property"
    ::= { cfprApAdaptorEtherIfStatsEntry 21 }

cfprApAdaptorEtherIfStatsRxPacketsDeltaAvg OBJECT-TYPE
    SYNTAX       Gauge32
    MAX-ACCESS   read-only
    STATUS       current
    DESCRIPTION
        "Cisco Firepower adaptor:EtherIfStats:rxPacketsDeltaAvg
        managed object property"
    ::= { cfprApAdaptorEtherIfStatsEntry 22 }

cfprApAdaptorEtherIfStatsRxPacketsDeltaMax OBJECT-TYPE
    SYNTAX       Gauge32
    MAX-ACCESS   read-only
    STATUS       current
    DESCRIPTION
        "Cisco Firepower adaptor:EtherIfStats:rxPacketsDeltaMax
        managed object property"
    ::= { cfprApAdaptorEtherIfStatsEntry 23 }

cfprApAdaptorEtherIfStatsRxPacketsDeltaMin OBJECT-TYPE
    SYNTAX       Gauge32
    MAX-ACCESS   read-only
    STATUS       current
    DESCRIPTION
        "Cisco Firepower adaptor:EtherIfStats:rxPacketsDeltaMin
        managed object property"
    ::= { cfprApAdaptorEtherIfStatsEntry 24 }

cfprApAdaptorEtherIfStatsSuspect OBJECT-TYPE
    SYNTAX       TruthValue
    MAX-ACCESS   read-only
    STATUS       current
    DESCRIPTION
        "Cisco Firepower adaptor:EtherIfStats:suspect managed
        object property"
    ::= { cfprApAdaptorEtherIfStatsEntry 25 }

cfprApAdaptorEtherIfStatsThresholded OBJECT-TYPE
    SYNTAX       CfprApAdaptorEtherIfStatsThresholded
    MAX-ACCESS   read-only
    STATUS       current
    DESCRIPTION
        "Cisco Firepower adaptor:EtherIfStats:thresholded
        managed object property"
    ::= { cfprApAdaptorEtherIfStatsEntry 26 }

cfprApAdaptorEtherIfStatsTimeCollected OBJECT-TYPE
    SYNTAX       DateAndTime
    MAX-ACCESS   read-only
    STATUS       current
    DESCRIPTION
        "Cisco Firepower adaptor:EtherIfStats:timeCollected
        managed object property"
    ::= { cfprApAdaptorEtherIfStatsEntry 27 }

cfprApAdaptorEtherIfStatsTxBytes OBJECT-TYPE
    SYNTAX       Gauge32
    MAX-ACCESS   read-only
    STATUS       current
    DESCRIPTION
        "Cisco Firepower adaptor:EtherIfStats:txBytes managed
        object property"
    ::= { cfprApAdaptorEtherIfStatsEntry 28 }

cfprApAdaptorEtherIfStatsTxBytesDelta OBJECT-TYPE
    SYNTAX       Counter32
    MAX-ACCESS   read-only
    STATUS       current
    DESCRIPTION
        "Cisco Firepower adaptor:EtherIfStats:txBytesDelta
        managed object property"
    ::= { cfprApAdaptorEtherIfStatsEntry 29 }

cfprApAdaptorEtherIfStatsTxBytesDeltaAvg OBJECT-TYPE
    SYNTAX       Gauge32
    MAX-ACCESS   read-only
    STATUS       current
    DESCRIPTION
        "Cisco Firepower adaptor:EtherIfStats:txBytesDeltaAvg
        managed object property"
    ::= { cfprApAdaptorEtherIfStatsEntry 30 }

cfprApAdaptorEtherIfStatsTxBytesDeltaMax OBJECT-TYPE
    SYNTAX       Gauge32
    MAX-ACCESS   read-only
    STATUS       current
    DESCRIPTION
        "Cisco Firepower adaptor:EtherIfStats:txBytesDeltaMax
        managed object property"
    ::= { cfprApAdaptorEtherIfStatsEntry 31 }

cfprApAdaptorEtherIfStatsTxBytesDeltaMin OBJECT-TYPE
    SYNTAX       Gauge32
    MAX-ACCESS   read-only
    STATUS       current
    DESCRIPTION
        "Cisco Firepower adaptor:EtherIfStats:txBytesDeltaMin
        managed object property"
    ::= { cfprApAdaptorEtherIfStatsEntry 32 }

cfprApAdaptorEtherIfStatsTxDropped OBJECT-TYPE
    SYNTAX       Gauge32
    MAX-ACCESS   read-only
    STATUS       current
    DESCRIPTION
        "Cisco Firepower adaptor:EtherIfStats:txDropped
        managed object property"
    ::= { cfprApAdaptorEtherIfStatsEntry 33 }

cfprApAdaptorEtherIfStatsTxDroppedDelta OBJECT-TYPE
    SYNTAX       Counter32
    MAX-ACCESS   read-only
    STATUS       current
    DESCRIPTION
        "Cisco Firepower adaptor:EtherIfStats:txDroppedDelta
        managed object property"
    ::= { cfprApAdaptorEtherIfStatsEntry 34 }

cfprApAdaptorEtherIfStatsTxDroppedDeltaAvg OBJECT-TYPE
    SYNTAX       Gauge32
    MAX-ACCESS   read-only
    STATUS       current
    DESCRIPTION
        "Cisco Firepower adaptor:EtherIfStats:txDroppedDeltaAvg
        managed object property"
    ::= { cfprApAdaptorEtherIfStatsEntry 35 }

cfprApAdaptorEtherIfStatsTxDroppedDeltaMax OBJECT-TYPE
    SYNTAX       Gauge32
    MAX-ACCESS   read-only
    STATUS       current
    DESCRIPTION
        "Cisco Firepower adaptor:EtherIfStats:txDroppedDeltaMax
        managed object property"
    ::= { cfprApAdaptorEtherIfStatsEntry 36 }

cfprApAdaptorEtherIfStatsTxDroppedDeltaMin OBJECT-TYPE
    SYNTAX       Gauge32
    MAX-ACCESS   read-only
    STATUS       current
    DESCRIPTION
        "Cisco Firepower adaptor:EtherIfStats:txDroppedDeltaMin
        managed object property"
    ::= { cfprApAdaptorEtherIfStatsEntry 37 }

cfprApAdaptorEtherIfStatsTxErrors OBJECT-TYPE
    SYNTAX       Gauge32
    MAX-ACCESS   read-only
    STATUS       current
    DESCRIPTION
        "Cisco Firepower adaptor:EtherIfStats:txErrors
        managed object property"
    ::= { cfprApAdaptorEtherIfStatsEntry 38 }

cfprApAdaptorEtherIfStatsTxErrorsDelta OBJECT-TYPE
    SYNTAX       Counter32
    MAX-ACCESS   read-only
    STATUS       current
    DESCRIPTION
        "Cisco Firepower adaptor:EtherIfStats:txErrorsDelta
        managed object property"
    ::= { cfprApAdaptorEtherIfStatsEntry 39 }

cfprApAdaptorEtherIfStatsTxErrorsDeltaAvg OBJECT-TYPE
    SYNTAX       Gauge32
    MAX-ACCESS   read-only
    STATUS       current
    DESCRIPTION
        "Cisco Firepower adaptor:EtherIfStats:txErrorsDeltaAvg
        managed object property"
    ::= { cfprApAdaptorEtherIfStatsEntry 40 }

cfprApAdaptorEtherIfStatsTxErrorsDeltaMax OBJECT-TYPE
    SYNTAX       Gauge32
    MAX-ACCESS   read-only
    STATUS       current
    DESCRIPTION
        "Cisco Firepower adaptor:EtherIfStats:txErrorsDeltaMax
        managed object property"
    ::= { cfprApAdaptorEtherIfStatsEntry 41 }

cfprApAdaptorEtherIfStatsTxErrorsDeltaMin OBJECT-TYPE
    SYNTAX       Gauge32
    MAX-ACCESS   read-only
    STATUS       current
    DESCRIPTION
        "Cisco Firepower adaptor:EtherIfStats:txErrorsDeltaMin
        managed object property"
    ::= { cfprApAdaptorEtherIfStatsEntry 42 }

cfprApAdaptorEtherIfStatsTxPackets OBJECT-TYPE
    SYNTAX       Gauge32
    MAX-ACCESS   read-only
    STATUS       current
    DESCRIPTION
        "Cisco Firepower adaptor:EtherIfStats:txPackets
        managed object property"
    ::= { cfprApAdaptorEtherIfStatsEntry 43 }

cfprApAdaptorEtherIfStatsTxPacketsDelta OBJECT-TYPE
    SYNTAX       Counter32
    MAX-ACCESS   read-only
    STATUS       current
    DESCRIPTION
        "Cisco Firepower adaptor:EtherIfStats:txPacketsDelta
        managed object property"
    ::= { cfprApAdaptorEtherIfStatsEntry 44 }

cfprApAdaptorEtherIfStatsTxPacketsDeltaAvg OBJECT-TYPE
    SYNTAX       Gauge32
    MAX-ACCESS   read-only
    STATUS       current
    DESCRIPTION
        "Cisco Firepower adaptor:EtherIfStats:txPacketsDeltaAvg
        managed object property"
    ::= { cfprApAdaptorEtherIfStatsEntry 45 }

cfprApAdaptorEtherIfStatsTxPacketsDeltaMax OBJECT-TYPE
    SYNTAX       Gauge32
    MAX-ACCESS   read-only
    STATUS       current
    DESCRIPTION
        "Cisco Firepower adaptor:EtherIfStats:txPacketsDeltaMax
        managed object property"
    ::= { cfprApAdaptorEtherIfStatsEntry 46 }

cfprApAdaptorEtherIfStatsTxPacketsDeltaMin OBJECT-TYPE
    SYNTAX       Gauge32
    MAX-ACCESS   read-only
    STATUS       current
    DESCRIPTION
        "Cisco Firepower adaptor:EtherIfStats:txPacketsDeltaMin
        managed object property"
    ::= { cfprApAdaptorEtherIfStatsEntry 47 }

cfprApAdaptorEtherIfStatsUpdate OBJECT-TYPE
    SYNTAX       Gauge32
    MAX-ACCESS   read-only
    STATUS       current
    DESCRIPTION
        "Cisco Firepower adaptor:EtherIfStats:update managed
        object property"
    ::= { cfprApAdaptorEtherIfStatsEntry 48 }

cfprApAdaptorEtherIfStatsHistTable OBJECT-TYPE
    SYNTAX           SEQUENCE OF CfprApAdaptorEtherIfStatsHistEntry
    MAX-ACCESS       not-accessible
    STATUS           current
    DESCRIPTION
        "Cisco Firepower adaptor:EtherIfStatsHist managed object table"
    ::= { cfprApAdaptorObjects 27 }

cfprApAdaptorEtherIfStatsHistEntry OBJECT-TYPE
    SYNTAX           CfprApAdaptorEtherIfStatsHistEntry
    MAX-ACCESS       not-accessible
    STATUS           current
    DESCRIPTION
        "Entry for the cfprApAdaptorEtherIfStatsHistTable table."
    INDEX { cfprApAdaptorEtherIfStatsHistInstanceId }
    ::= { cfprApAdaptorEtherIfStatsHistTable 1 }

CfprApAdaptorEtherIfStatsHistEntry ::= SEQUENCE {
    cfprApAdaptorEtherIfStatsHistInstanceId                          CfprApManagedObjectId,
    cfprApAdaptorEtherIfStatsHistDn                                  CfprApManagedObjectDn,
    cfprApAdaptorEtherIfStatsHistRn                                  SnmpAdminString,
    cfprApAdaptorEtherIfStatsHistId                                  Unsigned64,
    cfprApAdaptorEtherIfStatsHistMostRecent                          TruthValue,
    cfprApAdaptorEtherIfStatsHistRxBytes                             Gauge32,
    cfprApAdaptorEtherIfStatsHistRxBytesDelta                        Gauge32,
    cfprApAdaptorEtherIfStatsHistRxBytesDeltaAvg                     Gauge32,
    cfprApAdaptorEtherIfStatsHistRxBytesDeltaMax                     Gauge32,
    cfprApAdaptorEtherIfStatsHistRxBytesDeltaMin                     Gauge32,
    cfprApAdaptorEtherIfStatsHistRxDropped                           Gauge32,
    cfprApAdaptorEtherIfStatsHistRxDroppedDelta                      Gauge32,
    cfprApAdaptorEtherIfStatsHistRxDroppedDeltaAvg                   Gauge32,
    cfprApAdaptorEtherIfStatsHistRxDroppedDeltaMax                   Gauge32,
    cfprApAdaptorEtherIfStatsHistRxDroppedDeltaMin                   Gauge32,
    cfprApAdaptorEtherIfStatsHistRxErrors                            Gauge32,
    cfprApAdaptorEtherIfStatsHistRxErrorsDelta                       Gauge32,
    cfprApAdaptorEtherIfStatsHistRxErrorsDeltaAvg                    Gauge32,
    cfprApAdaptorEtherIfStatsHistRxErrorsDeltaMax                    Gauge32,
    cfprApAdaptorEtherIfStatsHistRxErrorsDeltaMin                    Gauge32,
    cfprApAdaptorEtherIfStatsHistRxPackets                           Gauge32,
    cfprApAdaptorEtherIfStatsHistRxPacketsDelta                      Gauge32,
    cfprApAdaptorEtherIfStatsHistRxPacketsDeltaAvg                   Gauge32,
    cfprApAdaptorEtherIfStatsHistRxPacketsDeltaMax                   Gauge32,
    cfprApAdaptorEtherIfStatsHistRxPacketsDeltaMin                   Gauge32,
    cfprApAdaptorEtherIfStatsHistSuspect                             TruthValue,
    cfprApAdaptorEtherIfStatsHistThresholded                         CfprApAdaptorEtherIfStatsHistThresholded,
    cfprApAdaptorEtherIfStatsHistTimeCollected                       DateAndTime,
    cfprApAdaptorEtherIfStatsHistTxBytes                             Gauge32,
    cfprApAdaptorEtherIfStatsHistTxBytesDelta                        Gauge32,
    cfprApAdaptorEtherIfStatsHistTxBytesDeltaAvg                     Gauge32,
    cfprApAdaptorEtherIfStatsHistTxBytesDeltaMax                     Gauge32,
    cfprApAdaptorEtherIfStatsHistTxBytesDeltaMin                     Gauge32,
    cfprApAdaptorEtherIfStatsHistTxDropped                           Gauge32,
    cfprApAdaptorEtherIfStatsHistTxDroppedDelta                      Gauge32,
    cfprApAdaptorEtherIfStatsHistTxDroppedDeltaAvg                   Gauge32,
    cfprApAdaptorEtherIfStatsHistTxDroppedDeltaMax                   Gauge32,
    cfprApAdaptorEtherIfStatsHistTxDroppedDeltaMin                   Gauge32,
    cfprApAdaptorEtherIfStatsHistTxErrors                            Gauge32,
    cfprApAdaptorEtherIfStatsHistTxErrorsDelta                       Gauge32,
    cfprApAdaptorEtherIfStatsHistTxErrorsDeltaAvg                    Gauge32,
    cfprApAdaptorEtherIfStatsHistTxErrorsDeltaMax                    Gauge32,
    cfprApAdaptorEtherIfStatsHistTxErrorsDeltaMin                    Gauge32,
    cfprApAdaptorEtherIfStatsHistTxPackets                           Gauge32,
    cfprApAdaptorEtherIfStatsHistTxPacketsDelta                      Gauge32,
    cfprApAdaptorEtherIfStatsHistTxPacketsDeltaAvg                   Gauge32,
    cfprApAdaptorEtherIfStatsHistTxPacketsDeltaMax                   Gauge32,
    cfprApAdaptorEtherIfStatsHistTxPacketsDeltaMin                   Gauge32
}

cfprApAdaptorEtherIfStatsHistInstanceId OBJECT-TYPE
    SYNTAX       CfprApManagedObjectId
    MAX-ACCESS   not-accessible
    STATUS       current
    DESCRIPTION
        "Instance identifier of the managed object."
    ::= { cfprApAdaptorEtherIfStatsHistEntry 1 }

cfprApAdaptorEtherIfStatsHistDn OBJECT-TYPE
    SYNTAX       CfprApManagedObjectDn
    MAX-ACCESS   read-only
    STATUS       current
    DESCRIPTION
        "Cisco Firepower adaptor:EtherIfStatsHist:dn managed
        object property"
    ::= { cfprApAdaptorEtherIfStatsHistEntry 2 }

cfprApAdaptorEtherIfStatsHistRn OBJECT-TYPE
    SYNTAX       SnmpAdminString
    MAX-ACCESS   read-only
    STATUS       current
    DESCRIPTION
        "Cisco Firepower adaptor:EtherIfStatsHist:rn managed
        object property"
    ::= { cfprApAdaptorEtherIfStatsHistEntry 3 }

cfprApAdaptorEtherIfStatsHistId OBJECT-TYPE
    SYNTAX       Unsigned64
    MAX-ACCESS   read-only
    STATUS       current
    DESCRIPTION
        "Cisco Firepower adaptor:EtherIfStatsHist:id managed
        object property"
    ::= { cfprApAdaptorEtherIfStatsHistEntry 4 }

cfprApAdaptorEtherIfStatsHistMostRecent OBJECT-TYPE
    SYNTAX       TruthValue
    MAX-ACCESS   read-only
    STATUS       current
    DESCRIPTION
        "Cisco Firepower adaptor:EtherIfStatsHist:mostRecent
        managed object property"
    ::= { cfprApAdaptorEtherIfStatsHistEntry 5 }

cfprApAdaptorEtherIfStatsHistRxBytes OBJECT-TYPE
    SYNTAX       Gauge32
    MAX-ACCESS   read-only
    STATUS       current
    DESCRIPTION
        "Cisco Firepower adaptor:EtherIfStatsHist:rxBytes
        managed object property"
    ::= { cfprApAdaptorEtherIfStatsHistEntry 6 }

cfprApAdaptorEtherIfStatsHistRxBytesDelta OBJECT-TYPE
    SYNTAX       Gauge32
    MAX-ACCESS   read-only
    STATUS       current
    DESCRIPTION
        "Cisco Firepower adaptor:EtherIfStatsHist:rxBytesDelta
        managed object property"
    ::= { cfprApAdaptorEtherIfStatsHistEntry 7 }

cfprApAdaptorEtherIfStatsHistRxBytesDeltaAvg OBJECT-TYPE
    SYNTAX       Gauge32
    MAX-ACCESS   read-only
    STATUS       current
    DESCRIPTION
        "Cisco Firepower adaptor:EtherIfStatsHist:rxBytesDeltaAvg
        managed object property"
    ::= { cfprApAdaptorEtherIfStatsHistEntry 8 }

cfprApAdaptorEtherIfStatsHistRxBytesDeltaMax OBJECT-TYPE
    SYNTAX       Gauge32
    MAX-ACCESS   read-only
    STATUS       current
    DESCRIPTION
        "Cisco Firepower adaptor:EtherIfStatsHist:rxBytesDeltaMax
        managed object property"
    ::= { cfprApAdaptorEtherIfStatsHistEntry 9 }

cfprApAdaptorEtherIfStatsHistRxBytesDeltaMin OBJECT-TYPE
    SYNTAX       Gauge32
    MAX-ACCESS   read-only
    STATUS       current
    DESCRIPTION
        "Cisco Firepower adaptor:EtherIfStatsHist:rxBytesDeltaMin
        managed object property"
    ::= { cfprApAdaptorEtherIfStatsHistEntry 10 }

cfprApAdaptorEtherIfStatsHistRxDropped OBJECT-TYPE
    SYNTAX       Gauge32
    MAX-ACCESS   read-only
    STATUS       current
    DESCRIPTION
        "Cisco Firepower adaptor:EtherIfStatsHist:rxDropped
        managed object property"
    ::= { cfprApAdaptorEtherIfStatsHistEntry 11 }

cfprApAdaptorEtherIfStatsHistRxDroppedDelta OBJECT-TYPE
    SYNTAX       Gauge32
    MAX-ACCESS   read-only
    STATUS       current
    DESCRIPTION
        "Cisco Firepower adaptor:EtherIfStatsHist:rxDroppedDelta
        managed object property"
    ::= { cfprApAdaptorEtherIfStatsHistEntry 12 }

cfprApAdaptorEtherIfStatsHistRxDroppedDeltaAvg OBJECT-TYPE
    SYNTAX       Gauge32
    MAX-ACCESS   read-only
    STATUS       current
    DESCRIPTION
        "Cisco Firepower adaptor:EtherIfStatsHist:rxDroppedDeltaAvg
        managed object property"
    ::= { cfprApAdaptorEtherIfStatsHistEntry 13 }

cfprApAdaptorEtherIfStatsHistRxDroppedDeltaMax OBJECT-TYPE
    SYNTAX       Gauge32
    MAX-ACCESS   read-only
    STATUS       current
    DESCRIPTION
        "Cisco Firepower adaptor:EtherIfStatsHist:rxDroppedDeltaMax
        managed object property"
    ::= { cfprApAdaptorEtherIfStatsHistEntry 14 }

cfprApAdaptorEtherIfStatsHistRxDroppedDeltaMin OBJECT-TYPE
    SYNTAX       Gauge32
    MAX-ACCESS   read-only
    STATUS       current
    DESCRIPTION
        "Cisco Firepower adaptor:EtherIfStatsHist:rxDroppedDeltaMin
        managed object property"
    ::= { cfprApAdaptorEtherIfStatsHistEntry 15 }

cfprApAdaptorEtherIfStatsHistRxErrors OBJECT-TYPE
    SYNTAX       Gauge32
    MAX-ACCESS   read-only
    STATUS       current
    DESCRIPTION
        "Cisco Firepower adaptor:EtherIfStatsHist:rxErrors
        managed object property"
    ::= { cfprApAdaptorEtherIfStatsHistEntry 16 }

cfprApAdaptorEtherIfStatsHistRxErrorsDelta OBJECT-TYPE
    SYNTAX       Gauge32
    MAX-ACCESS   read-only
    STATUS       current
    DESCRIPTION
        "Cisco Firepower adaptor:EtherIfStatsHist:rxErrorsDelta
        managed object property"
    ::= { cfprApAdaptorEtherIfStatsHistEntry 17 }

cfprApAdaptorEtherIfStatsHistRxErrorsDeltaAvg OBJECT-TYPE
    SYNTAX       Gauge32
    MAX-ACCESS   read-only
    STATUS       current
    DESCRIPTION
        "Cisco Firepower adaptor:EtherIfStatsHist:rxErrorsDeltaAvg
        managed object property"
    ::= { cfprApAdaptorEtherIfStatsHistEntry 18 }

cfprApAdaptorEtherIfStatsHistRxErrorsDeltaMax OBJECT-TYPE
    SYNTAX       Gauge32
    MAX-ACCESS   read-only
    STATUS       current
    DESCRIPTION
        "Cisco Firepower adaptor:EtherIfStatsHist:rxErrorsDeltaMax
        managed object property"
    ::= { cfprApAdaptorEtherIfStatsHistEntry 19 }

cfprApAdaptorEtherIfStatsHistRxErrorsDeltaMin OBJECT-TYPE
    SYNTAX       Gauge32
    MAX-ACCESS   read-only
    STATUS       current
    DESCRIPTION
        "Cisco Firepower adaptor:EtherIfStatsHist:rxErrorsDeltaMin
        managed object property"
    ::= { cfprApAdaptorEtherIfStatsHistEntry 20 }

cfprApAdaptorEtherIfStatsHistRxPackets OBJECT-TYPE
    SYNTAX       Gauge32
    MAX-ACCESS   read-only
    STATUS       current
    DESCRIPTION
        "Cisco Firepower adaptor:EtherIfStatsHist:rxPackets
        managed object property"
    ::= { cfprApAdaptorEtherIfStatsHistEntry 21 }

cfprApAdaptorEtherIfStatsHistRxPacketsDelta OBJECT-TYPE
    SYNTAX       Gauge32
    MAX-ACCESS   read-only
    STATUS       current
    DESCRIPTION
        "Cisco Firepower adaptor:EtherIfStatsHist:rxPacketsDelta
        managed object property"
    ::= { cfprApAdaptorEtherIfStatsHistEntry 22 }

cfprApAdaptorEtherIfStatsHistRxPacketsDeltaAvg OBJECT-TYPE
    SYNTAX       Gauge32
    MAX-ACCESS   read-only
    STATUS       current
    DESCRIPTION
        "Cisco Firepower adaptor:EtherIfStatsHist:rxPacketsDeltaAvg
        managed object property"
    ::= { cfprApAdaptorEtherIfStatsHistEntry 23 }

cfprApAdaptorEtherIfStatsHistRxPacketsDeltaMax OBJECT-TYPE
    SYNTAX       Gauge32
    MAX-ACCESS   read-only
    STATUS       current
    DESCRIPTION
        "Cisco Firepower adaptor:EtherIfStatsHist:rxPacketsDeltaMax
        managed object property"
    ::= { cfprApAdaptorEtherIfStatsHistEntry 24 }

cfprApAdaptorEtherIfStatsHistRxPacketsDeltaMin OBJECT-TYPE
    SYNTAX       Gauge32
    MAX-ACCESS   read-only
    STATUS       current
    DESCRIPTION
        "Cisco Firepower adaptor:EtherIfStatsHist:rxPacketsDeltaMin
        managed object property"
    ::= { cfprApAdaptorEtherIfStatsHistEntry 25 }

cfprApAdaptorEtherIfStatsHistSuspect OBJECT-TYPE
    SYNTAX       TruthValue
    MAX-ACCESS   read-only
    STATUS       current
    DESCRIPTION
        "Cisco Firepower adaptor:EtherIfStatsHist:suspect
        managed object property"
    ::= { cfprApAdaptorEtherIfStatsHistEntry 26 }

cfprApAdaptorEtherIfStatsHistThresholded OBJECT-TYPE
    SYNTAX       CfprApAdaptorEtherIfStatsHistThresholded
    MAX-ACCESS   read-only
    STATUS       current
    DESCRIPTION
        "Cisco Firepower adaptor:EtherIfStatsHist:thresholded
        managed object property"
    ::= { cfprApAdaptorEtherIfStatsHistEntry 27 }

cfprApAdaptorEtherIfStatsHistTimeCollected OBJECT-TYPE
    SYNTAX       DateAndTime
    MAX-ACCESS   read-only
    STATUS       current
    DESCRIPTION
        "Cisco Firepower adaptor:EtherIfStatsHist:timeCollected
        managed object property"
    ::= { cfprApAdaptorEtherIfStatsHistEntry 28 }

cfprApAdaptorEtherIfStatsHistTxBytes OBJECT-TYPE
    SYNTAX       Gauge32
    MAX-ACCESS   read-only
    STATUS       current
    DESCRIPTION
        "Cisco Firepower adaptor:EtherIfStatsHist:txBytes
        managed object property"
    ::= { cfprApAdaptorEtherIfStatsHistEntry 29 }

cfprApAdaptorEtherIfStatsHistTxBytesDelta OBJECT-TYPE
    SYNTAX       Gauge32
    MAX-ACCESS   read-only
    STATUS       current
    DESCRIPTION
        "Cisco Firepower adaptor:EtherIfStatsHist:txBytesDelta
        managed object property"
    ::= { cfprApAdaptorEtherIfStatsHistEntry 30 }

cfprApAdaptorEtherIfStatsHistTxBytesDeltaAvg OBJECT-TYPE
    SYNTAX       Gauge32
    MAX-ACCESS   read-only
    STATUS       current
    DESCRIPTION
        "Cisco Firepower adaptor:EtherIfStatsHist:txBytesDeltaAvg
        managed object property"
    ::= { cfprApAdaptorEtherIfStatsHistEntry 31 }

cfprApAdaptorEtherIfStatsHistTxBytesDeltaMax OBJECT-TYPE
    SYNTAX       Gauge32
    MAX-ACCESS   read-only
    STATUS       current
    DESCRIPTION
        "Cisco Firepower adaptor:EtherIfStatsHist:txBytesDeltaMax
        managed object property"
    ::= { cfprApAdaptorEtherIfStatsHistEntry 32 }

cfprApAdaptorEtherIfStatsHistTxBytesDeltaMin OBJECT-TYPE
    SYNTAX       Gauge32
    MAX-ACCESS   read-only
    STATUS       current
    DESCRIPTION
        "Cisco Firepower adaptor:EtherIfStatsHist:txBytesDeltaMin
        managed object property"
    ::= { cfprApAdaptorEtherIfStatsHistEntry 33 }

cfprApAdaptorEtherIfStatsHistTxDropped OBJECT-TYPE
    SYNTAX       Gauge32
    MAX-ACCESS   read-only
    STATUS       current
    DESCRIPTION
        "Cisco Firepower adaptor:EtherIfStatsHist:txDropped
        managed object property"
    ::= { cfprApAdaptorEtherIfStatsHistEntry 34 }

cfprApAdaptorEtherIfStatsHistTxDroppedDelta OBJECT-TYPE
    SYNTAX       Gauge32
    MAX-ACCESS   read-only
    STATUS       current
    DESCRIPTION
        "Cisco Firepower adaptor:EtherIfStatsHist:txDroppedDelta
        managed object property"
    ::= { cfprApAdaptorEtherIfStatsHistEntry 35 }

cfprApAdaptorEtherIfStatsHistTxDroppedDeltaAvg OBJECT-TYPE
    SYNTAX       Gauge32
    MAX-ACCESS   read-only
    STATUS       current
    DESCRIPTION
        "Cisco Firepower adaptor:EtherIfStatsHist:txDroppedDeltaAvg
        managed object property"
    ::= { cfprApAdaptorEtherIfStatsHistEntry 36 }

cfprApAdaptorEtherIfStatsHistTxDroppedDeltaMax OBJECT-TYPE
    SYNTAX       Gauge32
    MAX-ACCESS   read-only
    STATUS       current
    DESCRIPTION
        "Cisco Firepower adaptor:EtherIfStatsHist:txDroppedDeltaMax
        managed object property"
    ::= { cfprApAdaptorEtherIfStatsHistEntry 37 }

cfprApAdaptorEtherIfStatsHistTxDroppedDeltaMin OBJECT-TYPE
    SYNTAX       Gauge32
    MAX-ACCESS   read-only
    STATUS       current
    DESCRIPTION
        "Cisco Firepower adaptor:EtherIfStatsHist:txDroppedDeltaMin
        managed object property"
    ::= { cfprApAdaptorEtherIfStatsHistEntry 38 }

cfprApAdaptorEtherIfStatsHistTxErrors OBJECT-TYPE
    SYNTAX       Gauge32
    MAX-ACCESS   read-only
    STATUS       current
    DESCRIPTION
        "Cisco Firepower adaptor:EtherIfStatsHist:txErrors
        managed object property"
    ::= { cfprApAdaptorEtherIfStatsHistEntry 39 }

cfprApAdaptorEtherIfStatsHistTxErrorsDelta OBJECT-TYPE
    SYNTAX       Gauge32
    MAX-ACCESS   read-only
    STATUS       current
    DESCRIPTION
        "Cisco Firepower adaptor:EtherIfStatsHist:txErrorsDelta
        managed object property"
    ::= { cfprApAdaptorEtherIfStatsHistEntry 40 }

cfprApAdaptorEtherIfStatsHistTxErrorsDeltaAvg OBJECT-TYPE
    SYNTAX       Gauge32
    MAX-ACCESS   read-only
    STATUS       current
    DESCRIPTION
        "Cisco Firepower adaptor:EtherIfStatsHist:txErrorsDeltaAvg
        managed object property"
    ::= { cfprApAdaptorEtherIfStatsHistEntry 41 }

cfprApAdaptorEtherIfStatsHistTxErrorsDeltaMax OBJECT-TYPE
    SYNTAX       Gauge32
    MAX-ACCESS   read-only
    STATUS       current
    DESCRIPTION
        "Cisco Firepower adaptor:EtherIfStatsHist:txErrorsDeltaMax
        managed object property"
    ::= { cfprApAdaptorEtherIfStatsHistEntry 42 }

cfprApAdaptorEtherIfStatsHistTxErrorsDeltaMin OBJECT-TYPE
    SYNTAX       Gauge32
    MAX-ACCESS   read-only
    STATUS       current
    DESCRIPTION
        "Cisco Firepower adaptor:EtherIfStatsHist:txErrorsDeltaMin
        managed object property"
    ::= { cfprApAdaptorEtherIfStatsHistEntry 43 }

cfprApAdaptorEtherIfStatsHistTxPackets OBJECT-TYPE
    SYNTAX       Gauge32
    MAX-ACCESS   read-only
    STATUS       current
    DESCRIPTION
        "Cisco Firepower adaptor:EtherIfStatsHist:txPackets
        managed object property"
    ::= { cfprApAdaptorEtherIfStatsHistEntry 44 }

cfprApAdaptorEtherIfStatsHistTxPacketsDelta OBJECT-TYPE
    SYNTAX       Gauge32
    MAX-ACCESS   read-only
    STATUS       current
    DESCRIPTION
        "Cisco Firepower adaptor:EtherIfStatsHist:txPacketsDelta
        managed object property"
    ::= { cfprApAdaptorEtherIfStatsHistEntry 45 }

cfprApAdaptorEtherIfStatsHistTxPacketsDeltaAvg OBJECT-TYPE
    SYNTAX       Gauge32
    MAX-ACCESS   read-only
    STATUS       current
    DESCRIPTION
        "Cisco Firepower adaptor:EtherIfStatsHist:txPacketsDeltaAvg
        managed object property"
    ::= { cfprApAdaptorEtherIfStatsHistEntry 46 }

cfprApAdaptorEtherIfStatsHistTxPacketsDeltaMax OBJECT-TYPE
    SYNTAX       Gauge32
    MAX-ACCESS   read-only
    STATUS       current
    DESCRIPTION
        "Cisco Firepower adaptor:EtherIfStatsHist:txPacketsDeltaMax
        managed object property"
    ::= { cfprApAdaptorEtherIfStatsHistEntry 47 }

cfprApAdaptorEtherIfStatsHistTxPacketsDeltaMin OBJECT-TYPE
    SYNTAX       Gauge32
    MAX-ACCESS   read-only
    STATUS       current
    DESCRIPTION
        "Cisco Firepower adaptor:EtherIfStatsHist:txPacketsDeltaMin
        managed object property"
    ::= { cfprApAdaptorEtherIfStatsHistEntry 48 }

cfprApAdaptorExtEthIfTable OBJECT-TYPE
    SYNTAX           SEQUENCE OF CfprApAdaptorExtEthIfEntry
    MAX-ACCESS       not-accessible
    STATUS           current
    DESCRIPTION
        "Cisco Firepower adaptor:ExtEthIf managed object table"
    ::= { cfprApAdaptorObjects 28 }

cfprApAdaptorExtEthIfEntry OBJECT-TYPE
    SYNTAX           CfprApAdaptorExtEthIfEntry
    MAX-ACCESS       not-accessible
    STATUS           current
    DESCRIPTION
        "Entry for the cfprApAdaptorExtEthIfTable table."
    INDEX { cfprApAdaptorExtEthIfInstanceId }
    ::= { cfprApAdaptorExtEthIfTable 1 }

CfprApAdaptorExtEthIfEntry ::= SEQUENCE {
    cfprApAdaptorExtEthIfInstanceId                                  CfprApManagedObjectId,
    cfprApAdaptorExtEthIfDn                                          CfprApManagedObjectDn,
    cfprApAdaptorExtEthIfRn                                          SnmpAdminString,
    cfprApAdaptorExtEthIfAdapterId                                   Gauge32,
    cfprApAdaptorExtEthIfAdminState                                  CfprApAdaptorExtIfAdminState,
    cfprApAdaptorExtEthIfAggrPortId                                  Gauge32,
    cfprApAdaptorExtEthIfChassisId                                   Gauge32,
    cfprApAdaptorExtEthIfDiscovery                                   CfprApEtherSatelliteConnectionDisc,
    cfprApAdaptorExtEthIfEpDn                                        SnmpAdminString,
    cfprApAdaptorExtEthIfFsmDescr                                    SnmpAdminString,
    cfprApAdaptorExtEthIfFsmPrev                                     SnmpAdminString,
    cfprApAdaptorExtEthIfFsmProgr                                    Gauge32,
    cfprApAdaptorExtEthIfFsmRmtInvErrCode                            Gauge32,
    cfprApAdaptorExtEthIfFsmRmtInvErrDescr                           SnmpAdminString,
    cfprApAdaptorExtEthIfFsmRmtInvRslt                               CfprApConditionRemoteInvRslt,
    cfprApAdaptorExtEthIfFsmStageDescr                               SnmpAdminString,
    cfprApAdaptorExtEthIfFsmStamp                                    DateAndTime,
    cfprApAdaptorExtEthIfFsmStatus                                   SnmpAdminString,
    cfprApAdaptorExtEthIfFsmTry                                      Gauge32,
    cfprApAdaptorExtEthIfId                                          Gauge32,
    cfprApAdaptorExtEthIfIfRole                                      CfprApNetworkPortRole,
    cfprApAdaptorExtEthIfIfType                                      CfprApNetworkPhysEpIfType,
    cfprApAdaptorExtEthIfLinkState                                   CfprApAdaptorLinkState,
    cfprApAdaptorExtEthIfLldpMac                                     MacAddress,
    cfprApAdaptorExtEthIfLocale                                      CfprApNetworkLocale,
    cfprApAdaptorExtEthIfMac                                         MacAddress,
    cfprApAdaptorExtEthIfMacAddrType                                 CfprApAddressType,
    cfprApAdaptorExtEthIfName                                        SnmpAdminString,
    cfprApAdaptorExtEthIfOperState                                   CfprApNetworkPortOperState,
    cfprApAdaptorExtEthIfOperStateDesc                               SnmpAdminString,
    cfprApAdaptorExtEthIfPeerAggrPortId                              Gauge32,
    cfprApAdaptorExtEthIfPeerChassisId                               Gauge32,
    cfprApAdaptorExtEthIfPeerDn                                      SnmpAdminString,
    cfprApAdaptorExtEthIfPeerPortId                                  Gauge32,
    cfprApAdaptorExtEthIfPeerSlotId                                  Gauge32,
    cfprApAdaptorExtEthIfPhysEpDn                                    SnmpAdminString,
    cfprApAdaptorExtEthIfPortId                                      Gauge32,
    cfprApAdaptorExtEthIfPurpose                                     CfprApAdaptorPurpose,
    cfprApAdaptorExtEthIfServiceState                                CfprApAdaptorServiceState,
    cfprApAdaptorExtEthIfSide                                        CfprApNetworkSide,
    cfprApAdaptorExtEthIfSlotId                                      Gauge32,
    cfprApAdaptorExtEthIfSwitchId                                    CfprApNetworkSwitchId,
    cfprApAdaptorExtEthIfTransport                                   CfprApNetworkTransport,
    cfprApAdaptorExtEthIfType                                        CfprApNetworkConnectionType
}

cfprApAdaptorExtEthIfInstanceId OBJECT-TYPE
    SYNTAX       CfprApManagedObjectId
    MAX-ACCESS   not-accessible
    STATUS       current
    DESCRIPTION
        "Instance identifier of the managed object."
    ::= { cfprApAdaptorExtEthIfEntry 1 }

cfprApAdaptorExtEthIfDn OBJECT-TYPE
    SYNTAX       CfprApManagedObjectDn
    MAX-ACCESS   read-only
    STATUS       current
    DESCRIPTION
        "Cisco Firepower adaptor:ExtEthIf:dn managed object property"
    ::= { cfprApAdaptorExtEthIfEntry 2 }

cfprApAdaptorExtEthIfRn OBJECT-TYPE
    SYNTAX       SnmpAdminString
    MAX-ACCESS   read-only
    STATUS       current
    DESCRIPTION
        "Cisco Firepower adaptor:ExtEthIf:rn managed object property"
    ::= { cfprApAdaptorExtEthIfEntry 3 }

cfprApAdaptorExtEthIfAdapterId OBJECT-TYPE
    SYNTAX       Gauge32
    MAX-ACCESS   read-only
    STATUS       current
    DESCRIPTION
        "Cisco Firepower adaptor:ExtEthIf:adapterId managed
        object property"
    ::= { cfprApAdaptorExtEthIfEntry 4 }

cfprApAdaptorExtEthIfAdminState OBJECT-TYPE
    SYNTAX       CfprApAdaptorExtIfAdminState
    MAX-ACCESS   read-only
    STATUS       current
    DESCRIPTION
        "Cisco Firepower adaptor:ExtEthIf:adminState managed
        object property"
    ::= { cfprApAdaptorExtEthIfEntry 5 }

cfprApAdaptorExtEthIfAggrPortId OBJECT-TYPE
    SYNTAX       Gauge32
    MAX-ACCESS   read-only
    STATUS       current
    DESCRIPTION
        "Cisco Firepower adaptor:ExtEthIf:aggrPortId managed
        object property"
    ::= { cfprApAdaptorExtEthIfEntry 6 }

cfprApAdaptorExtEthIfChassisId OBJECT-TYPE
    SYNTAX       Gauge32
    MAX-ACCESS   read-only
    STATUS       current
    DESCRIPTION
        "Cisco Firepower adaptor:ExtEthIf:chassisId managed
        object property"
    ::= { cfprApAdaptorExtEthIfEntry 7 }

cfprApAdaptorExtEthIfDiscovery OBJECT-TYPE
    SYNTAX       CfprApEtherSatelliteConnectionDisc
    MAX-ACCESS   read-only
    STATUS       current
    DESCRIPTION
        "Cisco Firepower adaptor:ExtEthIf:discovery managed
        object property"
    ::= { cfprApAdaptorExtEthIfEntry 8 }

cfprApAdaptorExtEthIfEpDn OBJECT-TYPE
    SYNTAX       SnmpAdminString
    MAX-ACCESS   read-only
    STATUS       current
    DESCRIPTION
        "Cisco Firepower adaptor:ExtEthIf:epDn managed object property"
    ::= { cfprApAdaptorExtEthIfEntry 9 }

cfprApAdaptorExtEthIfFsmDescr OBJECT-TYPE
    SYNTAX       SnmpAdminString
    MAX-ACCESS   read-only
    STATUS       current
    DESCRIPTION
        "Cisco Firepower adaptor:ExtEthIf:fsmDescr managed
        object property"
    ::= { cfprApAdaptorExtEthIfEntry 10 }

cfprApAdaptorExtEthIfFsmPrev OBJECT-TYPE
    SYNTAX       SnmpAdminString
    MAX-ACCESS   read-only
    STATUS       current
    DESCRIPTION
        "Cisco Firepower adaptor:ExtEthIf:fsmPrev managed object property"
    ::= { cfprApAdaptorExtEthIfEntry 11 }

cfprApAdaptorExtEthIfFsmProgr OBJECT-TYPE
    SYNTAX       Gauge32
    MAX-ACCESS   read-only
    STATUS       current
    DESCRIPTION
        "Cisco Firepower adaptor:ExtEthIf:fsmProgr managed
        object property"
    ::= { cfprApAdaptorExtEthIfEntry 12 }

cfprApAdaptorExtEthIfFsmRmtInvErrCode OBJECT-TYPE
    SYNTAX       Gauge32
    MAX-ACCESS   read-only
    STATUS       current
    DESCRIPTION
        "Cisco Firepower adaptor:ExtEthIf:fsmRmtInvErrCode
        managed object property"
    ::= { cfprApAdaptorExtEthIfEntry 13 }

cfprApAdaptorExtEthIfFsmRmtInvErrDescr OBJECT-TYPE
    SYNTAX       SnmpAdminString
    MAX-ACCESS   read-only
    STATUS       current
    DESCRIPTION
        "Cisco Firepower adaptor:ExtEthIf:fsmRmtInvErrDescr
        managed object property"
    ::= { cfprApAdaptorExtEthIfEntry 14 }

cfprApAdaptorExtEthIfFsmRmtInvRslt OBJECT-TYPE
    SYNTAX       CfprApConditionRemoteInvRslt
    MAX-ACCESS   read-only
    STATUS       current
    DESCRIPTION
        "Cisco Firepower adaptor:ExtEthIf:fsmRmtInvRslt
        managed object property"
    ::= { cfprApAdaptorExtEthIfEntry 15 }

cfprApAdaptorExtEthIfFsmStageDescr OBJECT-TYPE
    SYNTAX       SnmpAdminString
    MAX-ACCESS   read-only
    STATUS       current
    DESCRIPTION
        "Cisco Firepower adaptor:ExtEthIf:fsmStageDescr
        managed object property"
    ::= { cfprApAdaptorExtEthIfEntry 16 }

cfprApAdaptorExtEthIfFsmStamp OBJECT-TYPE
    SYNTAX       DateAndTime
    MAX-ACCESS   read-only
    STATUS       current
    DESCRIPTION
        "Cisco Firepower adaptor:ExtEthIf:fsmStamp managed
        object property"
    ::= { cfprApAdaptorExtEthIfEntry 17 }

cfprApAdaptorExtEthIfFsmStatus OBJECT-TYPE
    SYNTAX       SnmpAdminString
    MAX-ACCESS   read-only
    STATUS       current
    DESCRIPTION
        "Cisco Firepower adaptor:ExtEthIf:fsmStatus managed
        object property"
    ::= { cfprApAdaptorExtEthIfEntry 18 }

cfprApAdaptorExtEthIfFsmTry OBJECT-TYPE
    SYNTAX       Gauge32
    MAX-ACCESS   read-only
    STATUS       current
    DESCRIPTION
        "Cisco Firepower adaptor:ExtEthIf:fsmTry managed object property"
    ::= { cfprApAdaptorExtEthIfEntry 19 }

cfprApAdaptorExtEthIfId OBJECT-TYPE
    SYNTAX       Gauge32
    MAX-ACCESS   read-only
    STATUS       current
    DESCRIPTION
        "Cisco Firepower adaptor:ExtEthIf:id managed object property"
    ::= { cfprApAdaptorExtEthIfEntry 20 }

cfprApAdaptorExtEthIfIfRole OBJECT-TYPE
    SYNTAX       CfprApNetworkPortRole
    MAX-ACCESS   read-only
    STATUS       current
    DESCRIPTION
        "Cisco Firepower adaptor:ExtEthIf:ifRole managed object property"
    ::= { cfprApAdaptorExtEthIfEntry 21 }

cfprApAdaptorExtEthIfIfType OBJECT-TYPE
    SYNTAX       CfprApNetworkPhysEpIfType
    MAX-ACCESS   read-only
    STATUS       current
    DESCRIPTION
        "Cisco Firepower adaptor:ExtEthIf:ifType managed object property"
    ::= { cfprApAdaptorExtEthIfEntry 22 }

cfprApAdaptorExtEthIfLinkState OBJECT-TYPE
    SYNTAX       CfprApAdaptorLinkState
    MAX-ACCESS   read-only
    STATUS       current
    DESCRIPTION
        "Cisco Firepower adaptor:ExtEthIf:linkState managed
        object property"
    ::= { cfprApAdaptorExtEthIfEntry 23 }

cfprApAdaptorExtEthIfLldpMac OBJECT-TYPE
    SYNTAX       MacAddress
    MAX-ACCESS   read-only
    STATUS       current
    DESCRIPTION
        "Cisco Firepower adaptor:ExtEthIf:lldpMac managed object property"
    ::= { cfprApAdaptorExtEthIfEntry 24 }

cfprApAdaptorExtEthIfLocale OBJECT-TYPE
    SYNTAX       CfprApNetworkLocale
    MAX-ACCESS   read-only
    STATUS       current
    DESCRIPTION
        "Cisco Firepower adaptor:ExtEthIf:locale managed object property"
    ::= { cfprApAdaptorExtEthIfEntry 25 }

cfprApAdaptorExtEthIfMac OBJECT-TYPE
    SYNTAX       MacAddress
    MAX-ACCESS   read-only
    STATUS       current
    DESCRIPTION
        "Cisco Firepower adaptor:ExtEthIf:mac managed object property"
    ::= { cfprApAdaptorExtEthIfEntry 26 }

cfprApAdaptorExtEthIfMacAddrType OBJECT-TYPE
    SYNTAX       CfprApAddressType
    MAX-ACCESS   read-only
    STATUS       current
    DESCRIPTION
        "Cisco Firepower adaptor:ExtEthIf:macAddrType managed
        object property"
    ::= { cfprApAdaptorExtEthIfEntry 27 }

cfprApAdaptorExtEthIfName OBJECT-TYPE
    SYNTAX       SnmpAdminString
    MAX-ACCESS   read-only
    STATUS       current
    DESCRIPTION
        "Cisco Firepower adaptor:ExtEthIf:name managed object property"
    ::= { cfprApAdaptorExtEthIfEntry 28 }

cfprApAdaptorExtEthIfOperState OBJECT-TYPE
    SYNTAX       CfprApNetworkPortOperState
    MAX-ACCESS   read-only
    STATUS       current
    DESCRIPTION
        "Cisco Firepower adaptor:ExtEthIf:operState managed
        object property"
    ::= { cfprApAdaptorExtEthIfEntry 29 }

cfprApAdaptorExtEthIfOperStateDesc OBJECT-TYPE
    SYNTAX       SnmpAdminString
    MAX-ACCESS   read-only
    STATUS       current
    DESCRIPTION
        "Cisco Firepower adaptor:ExtEthIf:operStateDesc
        managed object property"
    ::= { cfprApAdaptorExtEthIfEntry 30 }

cfprApAdaptorExtEthIfPeerAggrPortId OBJECT-TYPE
    SYNTAX       Gauge32
    MAX-ACCESS   read-only
    STATUS       current
    DESCRIPTION
        "Cisco Firepower adaptor:ExtEthIf:peerAggrPortId
        managed object property"
    ::= { cfprApAdaptorExtEthIfEntry 31 }

cfprApAdaptorExtEthIfPeerChassisId OBJECT-TYPE
    SYNTAX       Gauge32
    MAX-ACCESS   read-only
    STATUS       current
    DESCRIPTION
        "Cisco Firepower adaptor:ExtEthIf:peerChassisId
        managed object property"
    ::= { cfprApAdaptorExtEthIfEntry 32 }

cfprApAdaptorExtEthIfPeerDn OBJECT-TYPE
    SYNTAX       SnmpAdminString
    MAX-ACCESS   read-only
    STATUS       current
    DESCRIPTION
        "Cisco Firepower adaptor:ExtEthIf:peerDn managed object property"
    ::= { cfprApAdaptorExtEthIfEntry 33 }

cfprApAdaptorExtEthIfPeerPortId OBJECT-TYPE
    SYNTAX       Gauge32
    MAX-ACCESS   read-only
    STATUS       current
    DESCRIPTION
        "Cisco Firepower adaptor:ExtEthIf:peerPortId managed
        object property"
    ::= { cfprApAdaptorExtEthIfEntry 34 }

cfprApAdaptorExtEthIfPeerSlotId OBJECT-TYPE
    SYNTAX       Gauge32
    MAX-ACCESS   read-only
    STATUS       current
    DESCRIPTION
        "Cisco Firepower adaptor:ExtEthIf:peerSlotId managed
        object property"
    ::= { cfprApAdaptorExtEthIfEntry 35 }

cfprApAdaptorExtEthIfPhysEpDn OBJECT-TYPE
    SYNTAX       SnmpAdminString
    MAX-ACCESS   read-only
    STATUS       current
    DESCRIPTION
        "Cisco Firepower adaptor:ExtEthIf:physEpDn managed
        object property"
    ::= { cfprApAdaptorExtEthIfEntry 36 }

cfprApAdaptorExtEthIfPortId OBJECT-TYPE
    SYNTAX       Gauge32
    MAX-ACCESS   read-only
    STATUS       current
    DESCRIPTION
        "Cisco Firepower adaptor:ExtEthIf:portId managed object property"
    ::= { cfprApAdaptorExtEthIfEntry 37 }

cfprApAdaptorExtEthIfPurpose OBJECT-TYPE
    SYNTAX       CfprApAdaptorPurpose
    MAX-ACCESS   read-only
    STATUS       current
    DESCRIPTION
        "Cisco Firepower adaptor:ExtEthIf:purpose managed object property"
    ::= { cfprApAdaptorExtEthIfEntry 38 }

cfprApAdaptorExtEthIfServiceState OBJECT-TYPE
    SYNTAX       CfprApAdaptorServiceState
    MAX-ACCESS   read-only
    STATUS       current
    DESCRIPTION
        "Cisco Firepower adaptor:ExtEthIf:serviceState
        managed object property"
    ::= { cfprApAdaptorExtEthIfEntry 39 }

cfprApAdaptorExtEthIfSide OBJECT-TYPE
    SYNTAX       CfprApNetworkSide
    MAX-ACCESS   read-only
    STATUS       current
    DESCRIPTION
        "Cisco Firepower adaptor:ExtEthIf:side managed object property"
    ::= { cfprApAdaptorExtEthIfEntry 40 }

cfprApAdaptorExtEthIfSlotId OBJECT-TYPE
    SYNTAX       Gauge32
    MAX-ACCESS   read-only
    STATUS       current
    DESCRIPTION
        "Cisco Firepower adaptor:ExtEthIf:slotId managed object property"
    ::= { cfprApAdaptorExtEthIfEntry 41 }

cfprApAdaptorExtEthIfSwitchId OBJECT-TYPE
    SYNTAX       CfprApNetworkSwitchId
    MAX-ACCESS   read-only
    STATUS       current
    DESCRIPTION
        "Cisco Firepower adaptor:ExtEthIf:switchId managed
        object property"
    ::= { cfprApAdaptorExtEthIfEntry 42 }

cfprApAdaptorExtEthIfTransport OBJECT-TYPE
    SYNTAX       CfprApNetworkTransport
    MAX-ACCESS   read-only
    STATUS       current
    DESCRIPTION
        "Cisco Firepower adaptor:ExtEthIf:transport managed
        object property"
    ::= { cfprApAdaptorExtEthIfEntry 43 }

cfprApAdaptorExtEthIfType OBJECT-TYPE
    SYNTAX       CfprApNetworkConnectionType
    MAX-ACCESS   read-only
    STATUS       current
    DESCRIPTION
        "Cisco Firepower adaptor:ExtEthIf:type managed object property"
    ::= { cfprApAdaptorExtEthIfEntry 44 }

cfprApAdaptorExtEthIfFsmTable OBJECT-TYPE
    SYNTAX           SEQUENCE OF CfprApAdaptorExtEthIfFsmEntry
    MAX-ACCESS       not-accessible
    STATUS           current
    DESCRIPTION
        "Cisco Firepower adaptor:ExtEthIfFsm managed object table"
    ::= { cfprApAdaptorObjects 29 }

cfprApAdaptorExtEthIfFsmEntry OBJECT-TYPE
    SYNTAX           CfprApAdaptorExtEthIfFsmEntry
    MAX-ACCESS       not-accessible
    STATUS           current
    DESCRIPTION
        "Entry for the cfprApAdaptorExtEthIfFsmTable table."
    INDEX { cfprApAdaptorExtEthIfFsmInstanceId }
    ::= { cfprApAdaptorExtEthIfFsmTable 1 }

CfprApAdaptorExtEthIfFsmEntry ::= SEQUENCE {
    cfprApAdaptorExtEthIfFsmInstanceId                               CfprApManagedObjectId,
    cfprApAdaptorExtEthIfFsmDn                                       CfprApManagedObjectDn,
    cfprApAdaptorExtEthIfFsmRn                                       SnmpAdminString,
    cfprApAdaptorExtEthIfFsmCompletionTime                           DateAndTime,
    cfprApAdaptorExtEthIfFsmCurrentFsm                               CfprApAdaptorExtEthIfFsmCurrentFsm,
    cfprApAdaptorExtEthIfFsmDescrData                                SnmpAdminString,
    cfprApAdaptorExtEthIfFsmFsmStatus                                CfprApFsmFsmStageStatus,
    cfprApAdaptorExtEthIfFsmProgress                                 Gauge32,
    cfprApAdaptorExtEthIfFsmRmtErrCode                               Gauge32,
    cfprApAdaptorExtEthIfFsmRmtErrDescr                              SnmpAdminString,
    cfprApAdaptorExtEthIfFsmRmtRslt                                  CfprApConditionRemoteInvRslt
}

cfprApAdaptorExtEthIfFsmInstanceId OBJECT-TYPE
    SYNTAX       CfprApManagedObjectId
    MAX-ACCESS   not-accessible
    STATUS       current
    DESCRIPTION
        "Instance identifier of the managed object."
    ::= { cfprApAdaptorExtEthIfFsmEntry 1 }

cfprApAdaptorExtEthIfFsmDn OBJECT-TYPE
    SYNTAX       CfprApManagedObjectDn
    MAX-ACCESS   read-only
    STATUS       current
    DESCRIPTION
        "Cisco Firepower adaptor:ExtEthIfFsm:dn managed object property"
    ::= { cfprApAdaptorExtEthIfFsmEntry 2 }

cfprApAdaptorExtEthIfFsmRn OBJECT-TYPE
    SYNTAX       SnmpAdminString
    MAX-ACCESS   read-only
    STATUS       current
    DESCRIPTION
        "Cisco Firepower adaptor:ExtEthIfFsm:rn managed object property"
    ::= { cfprApAdaptorExtEthIfFsmEntry 3 }

cfprApAdaptorExtEthIfFsmCompletionTime OBJECT-TYPE
    SYNTAX       DateAndTime
    MAX-ACCESS   read-only
    STATUS       current
    DESCRIPTION
        "Cisco Firepower adaptor:ExtEthIfFsm:completionTime
        managed object property"
    ::= { cfprApAdaptorExtEthIfFsmEntry 4 }

cfprApAdaptorExtEthIfFsmCurrentFsm OBJECT-TYPE
    SYNTAX       CfprApAdaptorExtEthIfFsmCurrentFsm
    MAX-ACCESS   read-only
    STATUS       current
    DESCRIPTION
        "Cisco Firepower adaptor:ExtEthIfFsm:currentFsm
        managed object property"
    ::= { cfprApAdaptorExtEthIfFsmEntry 5 }

cfprApAdaptorExtEthIfFsmDescrData OBJECT-TYPE
    SYNTAX       SnmpAdminString
    MAX-ACCESS   read-only
    STATUS       current
    DESCRIPTION
        "Cisco Firepower adaptor:ExtEthIfFsm:descr managed
        object property"
    ::= { cfprApAdaptorExtEthIfFsmEntry 6 }

cfprApAdaptorExtEthIfFsmFsmStatus OBJECT-TYPE
    SYNTAX       CfprApFsmFsmStageStatus
    MAX-ACCESS   read-only
    STATUS       current
    DESCRIPTION
        "Cisco Firepower adaptor:ExtEthIfFsm:fsmStatus
        managed object property"
    ::= { cfprApAdaptorExtEthIfFsmEntry 7 }

cfprApAdaptorExtEthIfFsmProgress OBJECT-TYPE
    SYNTAX       Gauge32
    MAX-ACCESS   read-only
    STATUS       current
    DESCRIPTION
        "Cisco Firepower adaptor:ExtEthIfFsm:progress managed
        object property"
    ::= { cfprApAdaptorExtEthIfFsmEntry 8 }

cfprApAdaptorExtEthIfFsmRmtErrCode OBJECT-TYPE
    SYNTAX       Gauge32
    MAX-ACCESS   read-only
    STATUS       current
    DESCRIPTION
        "Cisco Firepower adaptor:ExtEthIfFsm:rmtErrCode
        managed object property"
    ::= { cfprApAdaptorExtEthIfFsmEntry 9 }

cfprApAdaptorExtEthIfFsmRmtErrDescr OBJECT-TYPE
    SYNTAX       SnmpAdminString
    MAX-ACCESS   read-only
    STATUS       current
    DESCRIPTION
        "Cisco Firepower adaptor:ExtEthIfFsm:rmtErrDescr
        managed object property"
    ::= { cfprApAdaptorExtEthIfFsmEntry 10 }

cfprApAdaptorExtEthIfFsmRmtRslt OBJECT-TYPE
    SYNTAX       CfprApConditionRemoteInvRslt
    MAX-ACCESS   read-only
    STATUS       current
    DESCRIPTION
        "Cisco Firepower adaptor:ExtEthIfFsm:rmtRslt managed
        object property"
    ::= { cfprApAdaptorExtEthIfFsmEntry 11 }

cfprApAdaptorExtEthIfFsmStageTable OBJECT-TYPE
    SYNTAX           SEQUENCE OF CfprApAdaptorExtEthIfFsmStageEntry
    MAX-ACCESS       not-accessible
    STATUS           current
    DESCRIPTION
        "Cisco Firepower adaptor:ExtEthIfFsmStage managed object table"
    ::= { cfprApAdaptorObjects 30 }

cfprApAdaptorExtEthIfFsmStageEntry OBJECT-TYPE
    SYNTAX           CfprApAdaptorExtEthIfFsmStageEntry
    MAX-ACCESS       not-accessible
    STATUS           current
    DESCRIPTION
        "Entry for the cfprApAdaptorExtEthIfFsmStageTable table."
    INDEX { cfprApAdaptorExtEthIfFsmStageInstanceId }
    ::= { cfprApAdaptorExtEthIfFsmStageTable 1 }

CfprApAdaptorExtEthIfFsmStageEntry ::= SEQUENCE {
    cfprApAdaptorExtEthIfFsmStageInstanceId                          CfprApManagedObjectId,
    cfprApAdaptorExtEthIfFsmStageDn                                  CfprApManagedObjectDn,
    cfprApAdaptorExtEthIfFsmStageRn                                  SnmpAdminString,
    cfprApAdaptorExtEthIfFsmStageDescrData                           SnmpAdminString,
    cfprApAdaptorExtEthIfFsmStageLastUpdateTime                      DateAndTime,
    cfprApAdaptorExtEthIfFsmStageName                                CfprApAdaptorExtEthIfFsmStageName,
    cfprApAdaptorExtEthIfFsmStageOrder                               Gauge32,
    cfprApAdaptorExtEthIfFsmStageRetry                               Gauge32,
    cfprApAdaptorExtEthIfFsmStageStageStatus                         CfprApFsmFsmStageStatus
}

cfprApAdaptorExtEthIfFsmStageInstanceId OBJECT-TYPE
    SYNTAX       CfprApManagedObjectId
    MAX-ACCESS   not-accessible
    STATUS       current
    DESCRIPTION
        "Instance identifier of the managed object."
    ::= { cfprApAdaptorExtEthIfFsmStageEntry 1 }

cfprApAdaptorExtEthIfFsmStageDn OBJECT-TYPE
    SYNTAX       CfprApManagedObjectDn
    MAX-ACCESS   read-only
    STATUS       current
    DESCRIPTION
        "Cisco Firepower adaptor:ExtEthIfFsmStage:dn managed
        object property"
    ::= { cfprApAdaptorExtEthIfFsmStageEntry 2 }

cfprApAdaptorExtEthIfFsmStageRn OBJECT-TYPE
    SYNTAX       SnmpAdminString
    MAX-ACCESS   read-only
    STATUS       current
    DESCRIPTION
        "Cisco Firepower adaptor:ExtEthIfFsmStage:rn managed
        object property"
    ::= { cfprApAdaptorExtEthIfFsmStageEntry 3 }

cfprApAdaptorExtEthIfFsmStageDescrData OBJECT-TYPE
    SYNTAX       SnmpAdminString
    MAX-ACCESS   read-only
    STATUS       current
    DESCRIPTION
        "Cisco Firepower adaptor:ExtEthIfFsmStage:descr
        managed object property"
    ::= { cfprApAdaptorExtEthIfFsmStageEntry 4 }

cfprApAdaptorExtEthIfFsmStageLastUpdateTime OBJECT-TYPE
    SYNTAX       DateAndTime
    MAX-ACCESS   read-only
    STATUS       current
    DESCRIPTION
        "Cisco Firepower adaptor:ExtEthIfFsmStage:lastUpdateTime
        managed object property"
    ::= { cfprApAdaptorExtEthIfFsmStageEntry 5 }

cfprApAdaptorExtEthIfFsmStageName OBJECT-TYPE
    SYNTAX       CfprApAdaptorExtEthIfFsmStageName
    MAX-ACCESS   read-only
    STATUS       current
    DESCRIPTION
        "Cisco Firepower adaptor:ExtEthIfFsmStage:name
        managed object property"
    ::= { cfprApAdaptorExtEthIfFsmStageEntry 6 }

cfprApAdaptorExtEthIfFsmStageOrder OBJECT-TYPE
    SYNTAX       Gauge32
    MAX-ACCESS   read-only
    STATUS       current
    DESCRIPTION
        "Cisco Firepower adaptor:ExtEthIfFsmStage:order
        managed object property"
    ::= { cfprApAdaptorExtEthIfFsmStageEntry 7 }

cfprApAdaptorExtEthIfFsmStageRetry OBJECT-TYPE
    SYNTAX       Gauge32
    MAX-ACCESS   read-only
    STATUS       current
    DESCRIPTION
        "Cisco Firepower adaptor:ExtEthIfFsmStage:retry
        managed object property"
    ::= { cfprApAdaptorExtEthIfFsmStageEntry 8 }

cfprApAdaptorExtEthIfFsmStageStageStatus OBJECT-TYPE
    SYNTAX       CfprApFsmFsmStageStatus
    MAX-ACCESS   read-only
    STATUS       current
    DESCRIPTION
        "Cisco Firepower adaptor:ExtEthIfFsmStage:stageStatus
        managed object property"
    ::= { cfprApAdaptorExtEthIfFsmStageEntry 9 }

cfprApAdaptorExtEthIfFsmTaskTable OBJECT-TYPE
    SYNTAX           SEQUENCE OF CfprApAdaptorExtEthIfFsmTaskEntry
    MAX-ACCESS       not-accessible
    STATUS           current
    DESCRIPTION
        "Cisco Firepower adaptor:ExtEthIfFsmTask managed object table"
    ::= { cfprApAdaptorObjects 31 }

cfprApAdaptorExtEthIfFsmTaskEntry OBJECT-TYPE
    SYNTAX           CfprApAdaptorExtEthIfFsmTaskEntry
    MAX-ACCESS       not-accessible
    STATUS           current
    DESCRIPTION
        "Entry for the cfprApAdaptorExtEthIfFsmTaskTable table."
    INDEX { cfprApAdaptorExtEthIfFsmTaskInstanceId }
    ::= { cfprApAdaptorExtEthIfFsmTaskTable 1 }

CfprApAdaptorExtEthIfFsmTaskEntry ::= SEQUENCE {
    cfprApAdaptorExtEthIfFsmTaskInstanceId                           CfprApManagedObjectId,
    cfprApAdaptorExtEthIfFsmTaskDn                                   CfprApManagedObjectDn,
    cfprApAdaptorExtEthIfFsmTaskRn                                   SnmpAdminString,
    cfprApAdaptorExtEthIfFsmTaskCompletion                           CfprApFsmCompletion,
    cfprApAdaptorExtEthIfFsmTaskFlags                                CfprApFsmFlags,
    cfprApAdaptorExtEthIfFsmTaskItem                                 CfprApAdaptorExtEthIfFsmTaskItem,
    cfprApAdaptorExtEthIfFsmTaskSeqId                                Gauge32
}

cfprApAdaptorExtEthIfFsmTaskInstanceId OBJECT-TYPE
    SYNTAX       CfprApManagedObjectId
    MAX-ACCESS   not-accessible
    STATUS       current
    DESCRIPTION
        "Instance identifier of the managed object."
    ::= { cfprApAdaptorExtEthIfFsmTaskEntry 1 }

cfprApAdaptorExtEthIfFsmTaskDn OBJECT-TYPE
    SYNTAX       CfprApManagedObjectDn
    MAX-ACCESS   read-only
    STATUS       current
    DESCRIPTION
        "Cisco Firepower adaptor:ExtEthIfFsmTask:dn managed
        object property"
    ::= { cfprApAdaptorExtEthIfFsmTaskEntry 2 }

cfprApAdaptorExtEthIfFsmTaskRn OBJECT-TYPE
    SYNTAX       SnmpAdminString
    MAX-ACCESS   read-only
    STATUS       current
    DESCRIPTION
        "Cisco Firepower adaptor:ExtEthIfFsmTask:rn managed
        object property"
    ::= { cfprApAdaptorExtEthIfFsmTaskEntry 3 }

cfprApAdaptorExtEthIfFsmTaskCompletion OBJECT-TYPE
    SYNTAX       CfprApFsmCompletion
    MAX-ACCESS   read-only
    STATUS       current
    DESCRIPTION
        "Cisco Firepower adaptor:ExtEthIfFsmTask:completion
        managed object property"
    ::= { cfprApAdaptorExtEthIfFsmTaskEntry 4 }

cfprApAdaptorExtEthIfFsmTaskFlags OBJECT-TYPE
    SYNTAX       CfprApFsmFlags
    MAX-ACCESS   read-only
    STATUS       current
    DESCRIPTION
        "Cisco Firepower adaptor:ExtEthIfFsmTask:flags
        managed object property"
    ::= { cfprApAdaptorExtEthIfFsmTaskEntry 5 }

cfprApAdaptorExtEthIfFsmTaskItem OBJECT-TYPE
    SYNTAX       CfprApAdaptorExtEthIfFsmTaskItem
    MAX-ACCESS   read-only
    STATUS       current
    DESCRIPTION
        "Cisco Firepower adaptor:ExtEthIfFsmTask:item managed
        object property"
    ::= { cfprApAdaptorExtEthIfFsmTaskEntry 6 }

cfprApAdaptorExtEthIfFsmTaskSeqId OBJECT-TYPE
    SYNTAX       Gauge32
    MAX-ACCESS   read-only
    STATUS       current
    DESCRIPTION
        "Cisco Firepower adaptor:ExtEthIfFsmTask:seqId
        managed object property"
    ::= { cfprApAdaptorExtEthIfFsmTaskEntry 7 }

cfprApAdaptorExtEthIfPcTable OBJECT-TYPE
    SYNTAX           SEQUENCE OF CfprApAdaptorExtEthIfPcEntry
    MAX-ACCESS       not-accessible
    STATUS           current
    DESCRIPTION
        "Cisco Firepower adaptor:ExtEthIfPc managed object table"
    ::= { cfprApAdaptorObjects 32 }

cfprApAdaptorExtEthIfPcEntry OBJECT-TYPE
    SYNTAX           CfprApAdaptorExtEthIfPcEntry
    MAX-ACCESS       not-accessible
    STATUS           current
    DESCRIPTION
        "Entry for the cfprApAdaptorExtEthIfPcTable table."
    INDEX { cfprApAdaptorExtEthIfPcInstanceId }
    ::= { cfprApAdaptorExtEthIfPcTable 1 }

CfprApAdaptorExtEthIfPcEntry ::= SEQUENCE {
    cfprApAdaptorExtEthIfPcInstanceId                                CfprApManagedObjectId,
    cfprApAdaptorExtEthIfPcDn                                        CfprApManagedObjectDn,
    cfprApAdaptorExtEthIfPcRn                                        SnmpAdminString,
    cfprApAdaptorExtEthIfPcEpDn                                      SnmpAdminString,
    cfprApAdaptorExtEthIfPcFltAggr                                   Unsigned64,
    cfprApAdaptorExtEthIfPcIfRole                                    CfprApAdaptorExtIfPcIfRole,
    cfprApAdaptorExtEthIfPcIfType                                    CfprApAdaptorCIoEpIfType,
    cfprApAdaptorExtEthIfPcLocale                                    CfprApAdaptorExternalPcLocale,
    cfprApAdaptorExtEthIfPcMac                                       MacAddress,
    cfprApAdaptorExtEthIfPcName                                      SnmpAdminString,
    cfprApAdaptorExtEthIfPcOperSpeed                                 CfprApPortEthSpeed,
    cfprApAdaptorExtEthIfPcOperState                                 CfprApNetworkPortOperState,
    cfprApAdaptorExtEthIfPcPeerDn                                    SnmpAdminString,
    cfprApAdaptorExtEthIfPcPortId                                    CfprApAdaptorExtEthIfPcPortId,
    cfprApAdaptorExtEthIfPcStateQual                                 SnmpAdminString,
    cfprApAdaptorExtEthIfPcSwitchId                                  CfprApNetworkSwitchId,
    cfprApAdaptorExtEthIfPcTransport                                 CfprApAdaptorExtEthIfPcTransport,
    cfprApAdaptorExtEthIfPcType                                      CfprApAdaptorExtIfPcType
}

cfprApAdaptorExtEthIfPcInstanceId OBJECT-TYPE
    SYNTAX       CfprApManagedObjectId
    MAX-ACCESS   not-accessible
    STATUS       current
    DESCRIPTION
        "Instance identifier of the managed object."
    ::= { cfprApAdaptorExtEthIfPcEntry 1 }

cfprApAdaptorExtEthIfPcDn OBJECT-TYPE
    SYNTAX       CfprApManagedObjectDn
    MAX-ACCESS   read-only
    STATUS       current
    DESCRIPTION
        "Cisco Firepower adaptor:ExtEthIfPc:dn managed object property"
    ::= { cfprApAdaptorExtEthIfPcEntry 2 }

cfprApAdaptorExtEthIfPcRn OBJECT-TYPE
    SYNTAX       SnmpAdminString
    MAX-ACCESS   read-only
    STATUS       current
    DESCRIPTION
        "Cisco Firepower adaptor:ExtEthIfPc:rn managed object property"
    ::= { cfprApAdaptorExtEthIfPcEntry 3 }

cfprApAdaptorExtEthIfPcEpDn OBJECT-TYPE
    SYNTAX       SnmpAdminString
    MAX-ACCESS   read-only
    STATUS       current
    DESCRIPTION
        "Cisco Firepower adaptor:ExtEthIfPc:epDn managed object property"
    ::= { cfprApAdaptorExtEthIfPcEntry 4 }

cfprApAdaptorExtEthIfPcFltAggr OBJECT-TYPE
    SYNTAX       Unsigned64
    MAX-ACCESS   read-only
    STATUS       current
    DESCRIPTION
        "Cisco Firepower adaptor:ExtEthIfPc:fltAggr managed
        object property"
    ::= { cfprApAdaptorExtEthIfPcEntry 5 }

cfprApAdaptorExtEthIfPcIfRole OBJECT-TYPE
    SYNTAX       CfprApAdaptorExtIfPcIfRole
    MAX-ACCESS   read-only
    STATUS       current
    DESCRIPTION
        "Cisco Firepower adaptor:ExtEthIfPc:ifRole managed
        object property"
    ::= { cfprApAdaptorExtEthIfPcEntry 6 }

cfprApAdaptorExtEthIfPcIfType OBJECT-TYPE
    SYNTAX       CfprApAdaptorCIoEpIfType
    MAX-ACCESS   read-only
    STATUS       current
    DESCRIPTION
        "Cisco Firepower adaptor:ExtEthIfPc:ifType managed
        object property"
    ::= { cfprApAdaptorExtEthIfPcEntry 7 }

cfprApAdaptorExtEthIfPcLocale OBJECT-TYPE
    SYNTAX       CfprApAdaptorExternalPcLocale
    MAX-ACCESS   read-only
    STATUS       current
    DESCRIPTION
        "Cisco Firepower adaptor:ExtEthIfPc:locale managed
        object property"
    ::= { cfprApAdaptorExtEthIfPcEntry 8 }

cfprApAdaptorExtEthIfPcMac OBJECT-TYPE
    SYNTAX       MacAddress
    MAX-ACCESS   read-only
    STATUS       current
    DESCRIPTION
        "Cisco Firepower adaptor:ExtEthIfPc:mac managed object property"
    ::= { cfprApAdaptorExtEthIfPcEntry 9 }

cfprApAdaptorExtEthIfPcName OBJECT-TYPE
    SYNTAX       SnmpAdminString
    MAX-ACCESS   read-only
    STATUS       current
    DESCRIPTION
        "Cisco Firepower adaptor:ExtEthIfPc:name managed object property"
    ::= { cfprApAdaptorExtEthIfPcEntry 10 }

cfprApAdaptorExtEthIfPcOperSpeed OBJECT-TYPE
    SYNTAX       CfprApPortEthSpeed
    MAX-ACCESS   read-only
    STATUS       current
    DESCRIPTION
        "Cisco Firepower adaptor:ExtEthIfPc:operSpeed managed
        object property"
    ::= { cfprApAdaptorExtEthIfPcEntry 11 }

cfprApAdaptorExtEthIfPcOperState OBJECT-TYPE
    SYNTAX       CfprApNetworkPortOperState
    MAX-ACCESS   read-only
    STATUS       current
    DESCRIPTION
        "Cisco Firepower adaptor:ExtEthIfPc:operState managed
        object property"
    ::= { cfprApAdaptorExtEthIfPcEntry 12 }

cfprApAdaptorExtEthIfPcPeerDn OBJECT-TYPE
    SYNTAX       SnmpAdminString
    MAX-ACCESS   read-only
    STATUS       current
    DESCRIPTION
        "Cisco Firepower adaptor:ExtEthIfPc:peerDn managed
        object property"
    ::= { cfprApAdaptorExtEthIfPcEntry 13 }

cfprApAdaptorExtEthIfPcPortId OBJECT-TYPE
    SYNTAX       CfprApAdaptorExtEthIfPcPortId
    MAX-ACCESS   read-only
    STATUS       current
    DESCRIPTION
        "Cisco Firepower adaptor:ExtEthIfPc:portId managed
        object property"
    ::= { cfprApAdaptorExtEthIfPcEntry 14 }

cfprApAdaptorExtEthIfPcStateQual OBJECT-TYPE
    SYNTAX       SnmpAdminString
    MAX-ACCESS   read-only
    STATUS       current
    DESCRIPTION
        "Cisco Firepower adaptor:ExtEthIfPc:stateQual managed
        object property"
    ::= { cfprApAdaptorExtEthIfPcEntry 15 }

cfprApAdaptorExtEthIfPcSwitchId OBJECT-TYPE
    SYNTAX       CfprApNetworkSwitchId
    MAX-ACCESS   read-only
    STATUS       current
    DESCRIPTION
        "Cisco Firepower adaptor:ExtEthIfPc:switchId managed
        object property"
    ::= { cfprApAdaptorExtEthIfPcEntry 16 }

cfprApAdaptorExtEthIfPcTransport OBJECT-TYPE
    SYNTAX       CfprApAdaptorExtEthIfPcTransport
    MAX-ACCESS   read-only
    STATUS       current
    DESCRIPTION
        "Cisco Firepower adaptor:ExtEthIfPc:transport managed
        object property"
    ::= { cfprApAdaptorExtEthIfPcEntry 17 }

cfprApAdaptorExtEthIfPcType OBJECT-TYPE
    SYNTAX       CfprApAdaptorExtIfPcType
    MAX-ACCESS   read-only
    STATUS       current
    DESCRIPTION
        "Cisco Firepower adaptor:ExtEthIfPc:type managed object property"
    ::= { cfprApAdaptorExtEthIfPcEntry 18 }

cfprApAdaptorExtEthIfPcEpTable OBJECT-TYPE
    SYNTAX           SEQUENCE OF CfprApAdaptorExtEthIfPcEpEntry
    MAX-ACCESS       not-accessible
    STATUS           current
    DESCRIPTION
        "Cisco Firepower adaptor:ExtEthIfPcEp managed object table"
    ::= { cfprApAdaptorObjects 33 }

cfprApAdaptorExtEthIfPcEpEntry OBJECT-TYPE
    SYNTAX           CfprApAdaptorExtEthIfPcEpEntry
    MAX-ACCESS       not-accessible
    STATUS           current
    DESCRIPTION
        "Entry for the cfprApAdaptorExtEthIfPcEpTable table."
    INDEX { cfprApAdaptorExtEthIfPcEpInstanceId }
    ::= { cfprApAdaptorExtEthIfPcEpTable 1 }

CfprApAdaptorExtEthIfPcEpEntry ::= SEQUENCE {
    cfprApAdaptorExtEthIfPcEpInstanceId                              CfprApManagedObjectId,
    cfprApAdaptorExtEthIfPcEpDnData                                  CfprApManagedObjectDn,
    cfprApAdaptorExtEthIfPcEpRn                                      SnmpAdminString,
    cfprApAdaptorExtEthIfPcEpAggrPortId                              Gauge32,
    cfprApAdaptorExtEthIfPcEpChassisId                               Gauge32,
    cfprApAdaptorExtEthIfPcEpEpDn                                    SnmpAdminString,
    cfprApAdaptorExtEthIfPcEpIfRole                                  CfprApAdaptorExtIfEpIfRole,
    cfprApAdaptorExtEthIfPcEpIfType                                  CfprApAdaptorPIoEpIfType,
    cfprApAdaptorExtEthIfPcEpLocale                                  CfprApAdaptorExternalEpLocale,
    cfprApAdaptorExtEthIfPcEpMembership                              CfprApFabricMembershipStatus,
    cfprApAdaptorExtEthIfPcEpName                                    SnmpAdminString,
    cfprApAdaptorExtEthIfPcEpPeerAggrPortId                          Gauge32,
    cfprApAdaptorExtEthIfPcEpPeerChassisId                           Gauge32,
    cfprApAdaptorExtEthIfPcEpPeerDn                                  SnmpAdminString,
    cfprApAdaptorExtEthIfPcEpPeerPortId                              Gauge32,
    cfprApAdaptorExtEthIfPcEpPeerSlotId                              Gauge32,
    cfprApAdaptorExtEthIfPcEpPortId                                  CfprApAdaptorExtEthIfPcEpPortId,
    cfprApAdaptorExtEthIfPcEpSlotId                                  CfprApAdaptorExtEthIfPcEpSlotId,
    cfprApAdaptorExtEthIfPcEpSwitchId                                CfprApNetworkSwitchId,
    cfprApAdaptorExtEthIfPcEpTransport                               CfprApNetworkTransport,
    cfprApAdaptorExtEthIfPcEpType                                    CfprApAdaptorExtIfEpType
}

cfprApAdaptorExtEthIfPcEpInstanceId OBJECT-TYPE
    SYNTAX       CfprApManagedObjectId
    MAX-ACCESS   not-accessible
    STATUS       current
    DESCRIPTION
        "Instance identifier of the managed object."
    ::= { cfprApAdaptorExtEthIfPcEpEntry 1 }

cfprApAdaptorExtEthIfPcEpDnData OBJECT-TYPE
    SYNTAX       CfprApManagedObjectDn
    MAX-ACCESS   read-only
    STATUS       current
    DESCRIPTION
        "Cisco Firepower adaptor:ExtEthIfPcEp:dn managed object property"
    ::= { cfprApAdaptorExtEthIfPcEpEntry 2 }

cfprApAdaptorExtEthIfPcEpRn OBJECT-TYPE
    SYNTAX       SnmpAdminString
    MAX-ACCESS   read-only
    STATUS       current
    DESCRIPTION
        "Cisco Firepower adaptor:ExtEthIfPcEp:rn managed object property"
    ::= { cfprApAdaptorExtEthIfPcEpEntry 3 }

cfprApAdaptorExtEthIfPcEpAggrPortId OBJECT-TYPE
    SYNTAX       Gauge32
    MAX-ACCESS   read-only
    STATUS       current
    DESCRIPTION
        "Cisco Firepower adaptor:ExtEthIfPcEp:aggrPortId
        managed object property"
    ::= { cfprApAdaptorExtEthIfPcEpEntry 4 }

cfprApAdaptorExtEthIfPcEpChassisId OBJECT-TYPE
    SYNTAX       Gauge32
    MAX-ACCESS   read-only
    STATUS       current
    DESCRIPTION
        "Cisco Firepower adaptor:ExtEthIfPcEp:chassisId
        managed object property"
    ::= { cfprApAdaptorExtEthIfPcEpEntry 5 }

cfprApAdaptorExtEthIfPcEpEpDn OBJECT-TYPE
    SYNTAX       SnmpAdminString
    MAX-ACCESS   read-only
    STATUS       current
    DESCRIPTION
        "Cisco Firepower adaptor:ExtEthIfPcEp:epDn managed
        object property"
    ::= { cfprApAdaptorExtEthIfPcEpEntry 6 }

cfprApAdaptorExtEthIfPcEpIfRole OBJECT-TYPE
    SYNTAX       CfprApAdaptorExtIfEpIfRole
    MAX-ACCESS   read-only
    STATUS       current
    DESCRIPTION
        "Cisco Firepower adaptor:ExtEthIfPcEp:ifRole managed
        object property"
    ::= { cfprApAdaptorExtEthIfPcEpEntry 7 }

cfprApAdaptorExtEthIfPcEpIfType OBJECT-TYPE
    SYNTAX       CfprApAdaptorPIoEpIfType
    MAX-ACCESS   read-only
    STATUS       current
    DESCRIPTION
        "Cisco Firepower adaptor:ExtEthIfPcEp:ifType managed
        object property"
    ::= { cfprApAdaptorExtEthIfPcEpEntry 8 }

cfprApAdaptorExtEthIfPcEpLocale OBJECT-TYPE
    SYNTAX       CfprApAdaptorExternalEpLocale
    MAX-ACCESS   read-only
    STATUS       current
    DESCRIPTION
        "Cisco Firepower adaptor:ExtEthIfPcEp:locale managed
        object property"
    ::= { cfprApAdaptorExtEthIfPcEpEntry 9 }

cfprApAdaptorExtEthIfPcEpMembership OBJECT-TYPE
    SYNTAX       CfprApFabricMembershipStatus
    MAX-ACCESS   read-only
    STATUS       current
    DESCRIPTION
        "Cisco Firepower adaptor:ExtEthIfPcEp:membership
        managed object property"
    ::= { cfprApAdaptorExtEthIfPcEpEntry 10 }

cfprApAdaptorExtEthIfPcEpName OBJECT-TYPE
    SYNTAX       SnmpAdminString
    MAX-ACCESS   read-only
    STATUS       current
    DESCRIPTION
        "Cisco Firepower adaptor:ExtEthIfPcEp:name managed
        object property"
    ::= { cfprApAdaptorExtEthIfPcEpEntry 11 }

cfprApAdaptorExtEthIfPcEpPeerAggrPortId OBJECT-TYPE
    SYNTAX       Gauge32
    MAX-ACCESS   read-only
    STATUS       current
    DESCRIPTION
        "Cisco Firepower adaptor:ExtEthIfPcEp:peerAggrPortId
        managed object property"
    ::= { cfprApAdaptorExtEthIfPcEpEntry 12 }

cfprApAdaptorExtEthIfPcEpPeerChassisId OBJECT-TYPE
    SYNTAX       Gauge32
    MAX-ACCESS   read-only
    STATUS       current
    DESCRIPTION
        "Cisco Firepower adaptor:ExtEthIfPcEp:peerChassisId
        managed object property"
    ::= { cfprApAdaptorExtEthIfPcEpEntry 13 }

cfprApAdaptorExtEthIfPcEpPeerDn OBJECT-TYPE
    SYNTAX       SnmpAdminString
    MAX-ACCESS   read-only
    STATUS       current
    DESCRIPTION
        "Cisco Firepower adaptor:ExtEthIfPcEp:peerDn managed
        object property"
    ::= { cfprApAdaptorExtEthIfPcEpEntry 14 }

cfprApAdaptorExtEthIfPcEpPeerPortId OBJECT-TYPE
    SYNTAX       Gauge32
    MAX-ACCESS   read-only
    STATUS       current
    DESCRIPTION
        "Cisco Firepower adaptor:ExtEthIfPcEp:peerPortId
        managed object property"
    ::= { cfprApAdaptorExtEthIfPcEpEntry 15 }

cfprApAdaptorExtEthIfPcEpPeerSlotId OBJECT-TYPE
    SYNTAX       Gauge32
    MAX-ACCESS   read-only
    STATUS       current
    DESCRIPTION
        "Cisco Firepower adaptor:ExtEthIfPcEp:peerSlotId
        managed object property"
    ::= { cfprApAdaptorExtEthIfPcEpEntry 16 }

cfprApAdaptorExtEthIfPcEpPortId OBJECT-TYPE
    SYNTAX       CfprApAdaptorExtEthIfPcEpPortId
    MAX-ACCESS   read-only
    STATUS       current
    DESCRIPTION
        "Cisco Firepower adaptor:ExtEthIfPcEp:portId managed
        object property"
    ::= { cfprApAdaptorExtEthIfPcEpEntry 17 }

cfprApAdaptorExtEthIfPcEpSlotId OBJECT-TYPE
    SYNTAX       CfprApAdaptorExtEthIfPcEpSlotId
    MAX-ACCESS   read-only
    STATUS       current
    DESCRIPTION
        "Cisco Firepower adaptor:ExtEthIfPcEp:slotId managed
        object property"
    ::= { cfprApAdaptorExtEthIfPcEpEntry 18 }

cfprApAdaptorExtEthIfPcEpSwitchId OBJECT-TYPE
    SYNTAX       CfprApNetworkSwitchId
    MAX-ACCESS   read-only
    STATUS       current
    DESCRIPTION
        "Cisco Firepower adaptor:ExtEthIfPcEp:switchId
        managed object property"
    ::= { cfprApAdaptorExtEthIfPcEpEntry 19 }

cfprApAdaptorExtEthIfPcEpTransport OBJECT-TYPE
    SYNTAX       CfprApNetworkTransport
    MAX-ACCESS   read-only
    STATUS       current
    DESCRIPTION
        "Cisco Firepower adaptor:ExtEthIfPcEp:transport
        managed object property"
    ::= { cfprApAdaptorExtEthIfPcEpEntry 20 }

cfprApAdaptorExtEthIfPcEpType OBJECT-TYPE
    SYNTAX       CfprApAdaptorExtIfEpType
    MAX-ACCESS   read-only
    STATUS       current
    DESCRIPTION
        "Cisco Firepower adaptor:ExtEthIfPcEp:type managed
        object property"
    ::= { cfprApAdaptorExtEthIfPcEpEntry 21 }

cfprApAdaptorExtIpV6RssHashProfileTable OBJECT-TYPE
    SYNTAX           SEQUENCE OF CfprApAdaptorExtIpV6RssHashProfileEntry
    MAX-ACCESS       not-accessible
    STATUS           current
    DESCRIPTION
        "Cisco Firepower adaptor:ExtIpV6RssHashProfile
        managed object table"
    ::= { cfprApAdaptorObjects 34 }

cfprApAdaptorExtIpV6RssHashProfileEntry OBJECT-TYPE
    SYNTAX           CfprApAdaptorExtIpV6RssHashProfileEntry
    MAX-ACCESS       not-accessible
    STATUS           current
    DESCRIPTION
        "Entry for the cfprApAdaptorExtIpV6RssHashProfileTable table."
    INDEX { cfprApAdaptorExtIpV6RssHashProfileInstanceId }
    ::= { cfprApAdaptorExtIpV6RssHashProfileTable 1 }

CfprApAdaptorExtIpV6RssHashProfileEntry ::= SEQUENCE {
    cfprApAdaptorExtIpV6RssHashProfileInstanceId                     CfprApManagedObjectId,
    cfprApAdaptorExtIpV6RssHashProfileDn                             CfprApManagedObjectDn,
    cfprApAdaptorExtIpV6RssHashProfileRn                             SnmpAdminString,
    cfprApAdaptorExtIpV6RssHashProfileIpHash                         CfprApAdaptorExtIpV6RssHashProfileIpHash,
    cfprApAdaptorExtIpV6RssHashProfileTcpHash                        CfprApAdaptorExtIpV6RssHashProfileTcpHash
}

cfprApAdaptorExtIpV6RssHashProfileInstanceId OBJECT-TYPE
    SYNTAX       CfprApManagedObjectId
    MAX-ACCESS   not-accessible
    STATUS       current
    DESCRIPTION
        "Instance identifier of the managed object."
    ::= { cfprApAdaptorExtIpV6RssHashProfileEntry 1 }

cfprApAdaptorExtIpV6RssHashProfileDn OBJECT-TYPE
    SYNTAX       CfprApManagedObjectDn
    MAX-ACCESS   read-only
    STATUS       current
    DESCRIPTION
        "Cisco Firepower adaptor:ExtIpV6RssHashProfile:dn
        managed object property"
    ::= { cfprApAdaptorExtIpV6RssHashProfileEntry 2 }

cfprApAdaptorExtIpV6RssHashProfileRn OBJECT-TYPE
    SYNTAX       SnmpAdminString
    MAX-ACCESS   read-only
    STATUS       current
    DESCRIPTION
        "Cisco Firepower adaptor:ExtIpV6RssHashProfile:rn
        managed object property"
    ::= { cfprApAdaptorExtIpV6RssHashProfileEntry 3 }

cfprApAdaptorExtIpV6RssHashProfileIpHash OBJECT-TYPE
    SYNTAX       CfprApAdaptorExtIpV6RssHashProfileIpHash
    MAX-ACCESS   read-only
    STATUS       current
    DESCRIPTION
        "Cisco Firepower adaptor:ExtIpV6RssHashProfile:ipHash
        managed object property"
    ::= { cfprApAdaptorExtIpV6RssHashProfileEntry 4 }

cfprApAdaptorExtIpV6RssHashProfileTcpHash OBJECT-TYPE
    SYNTAX       CfprApAdaptorExtIpV6RssHashProfileTcpHash
    MAX-ACCESS   read-only
    STATUS       current
    DESCRIPTION
        "Cisco Firepower adaptor:ExtIpV6RssHashProfile:tcpHash
        managed object property"
    ::= { cfprApAdaptorExtIpV6RssHashProfileEntry 5 }

cfprApAdaptorFamilyTypeDefTable OBJECT-TYPE
    SYNTAX           SEQUENCE OF CfprApAdaptorFamilyTypeDefEntry
    MAX-ACCESS       not-accessible
    STATUS           current
    DESCRIPTION
        "Cisco Firepower adaptor:FamilyTypeDef managed object table"
    ::= { cfprApAdaptorObjects 35 }

cfprApAdaptorFamilyTypeDefEntry OBJECT-TYPE
    SYNTAX           CfprApAdaptorFamilyTypeDefEntry
    MAX-ACCESS       not-accessible
    STATUS           current
    DESCRIPTION
        "Entry for the cfprApAdaptorFamilyTypeDefTable table."
    INDEX { cfprApAdaptorFamilyTypeDefInstanceId }
    ::= { cfprApAdaptorFamilyTypeDefTable 1 }

CfprApAdaptorFamilyTypeDefEntry ::= SEQUENCE {
    cfprApAdaptorFamilyTypeDefInstanceId                             CfprApManagedObjectId,
    cfprApAdaptorFamilyTypeDefDn                                     CfprApManagedObjectDn,
    cfprApAdaptorFamilyTypeDefRn                                     SnmpAdminString,
    cfprApAdaptorFamilyTypeDefIsPassthrough                          TruthValue,
    cfprApAdaptorFamilyTypeDefNumDcePorts                            Gauge32,
    cfprApAdaptorFamilyTypeDefPortFamily                             SnmpAdminString,
    cfprApAdaptorFamilyTypeDefType                                   SnmpAdminString
}

cfprApAdaptorFamilyTypeDefInstanceId OBJECT-TYPE
    SYNTAX       CfprApManagedObjectId
    MAX-ACCESS   not-accessible
    STATUS       current
    DESCRIPTION
        "Instance identifier of the managed object."
    ::= { cfprApAdaptorFamilyTypeDefEntry 1 }

cfprApAdaptorFamilyTypeDefDn OBJECT-TYPE
    SYNTAX       CfprApManagedObjectDn
    MAX-ACCESS   read-only
    STATUS       current
    DESCRIPTION
        "Cisco Firepower adaptor:FamilyTypeDef:dn managed object property"
    ::= { cfprApAdaptorFamilyTypeDefEntry 2 }

cfprApAdaptorFamilyTypeDefRn OBJECT-TYPE
    SYNTAX       SnmpAdminString
    MAX-ACCESS   read-only
    STATUS       current
    DESCRIPTION
        "Cisco Firepower adaptor:FamilyTypeDef:rn managed object property"
    ::= { cfprApAdaptorFamilyTypeDefEntry 3 }

cfprApAdaptorFamilyTypeDefIsPassthrough OBJECT-TYPE
    SYNTAX       TruthValue
    MAX-ACCESS   read-only
    STATUS       current
    DESCRIPTION
        "Cisco Firepower adaptor:FamilyTypeDef:isPassthrough
        managed object property"
    ::= { cfprApAdaptorFamilyTypeDefEntry 4 }

cfprApAdaptorFamilyTypeDefNumDcePorts OBJECT-TYPE
    SYNTAX       Gauge32
    MAX-ACCESS   read-only
    STATUS       current
    DESCRIPTION
        "Cisco Firepower adaptor:FamilyTypeDef:numDcePorts
        managed object property"
    ::= { cfprApAdaptorFamilyTypeDefEntry 5 }

cfprApAdaptorFamilyTypeDefPortFamily OBJECT-TYPE
    SYNTAX       SnmpAdminString
    MAX-ACCESS   read-only
    STATUS       current
    DESCRIPTION
        "Cisco Firepower adaptor:FamilyTypeDef:portFamily
        managed object property"
    ::= { cfprApAdaptorFamilyTypeDefEntry 6 }

cfprApAdaptorFamilyTypeDefType OBJECT-TYPE
    SYNTAX       SnmpAdminString
    MAX-ACCESS   read-only
    STATUS       current
    DESCRIPTION
        "Cisco Firepower adaptor:FamilyTypeDef:type managed
        object property"
    ::= { cfprApAdaptorFamilyTypeDefEntry 7 }

cfprApAdaptorFcIfEventStatsTable OBJECT-TYPE
    SYNTAX           SEQUENCE OF CfprApAdaptorFcIfEventStatsEntry
    MAX-ACCESS       not-accessible
    STATUS           current
    DESCRIPTION
        "Cisco Firepower adaptor:FcIfEventStats managed object table"
    ::= { cfprApAdaptorObjects 38 }

cfprApAdaptorFcIfEventStatsEntry OBJECT-TYPE
    SYNTAX           CfprApAdaptorFcIfEventStatsEntry
    MAX-ACCESS       not-accessible
    STATUS           current
    DESCRIPTION
        "Entry for the cfprApAdaptorFcIfEventStatsTable table."
    INDEX { cfprApAdaptorFcIfEventStatsInstanceId }
    ::= { cfprApAdaptorFcIfEventStatsTable 1 }

CfprApAdaptorFcIfEventStatsEntry ::= SEQUENCE {
    cfprApAdaptorFcIfEventStatsInstanceId                            CfprApManagedObjectId,
    cfprApAdaptorFcIfEventStatsDn                                    CfprApManagedObjectDn,
    cfprApAdaptorFcIfEventStatsRn                                    SnmpAdminString,
    cfprApAdaptorFcIfEventStatsIntervals                             Gauge32,
    cfprApAdaptorFcIfEventStatsInvalidCRCCount                       Unsigned64,
    cfprApAdaptorFcIfEventStatsInvalidCRCCountDelta                  Counter64,
    cfprApAdaptorFcIfEventStatsInvalidCRCCountDeltaAvg               Unsigned64,
    cfprApAdaptorFcIfEventStatsInvalidCRCCountDeltaMax               Unsigned64,
    cfprApAdaptorFcIfEventStatsInvalidCRCCountDeltaMin               Unsigned64,
    cfprApAdaptorFcIfEventStatsLinkFailureCount                      Unsigned64,
    cfprApAdaptorFcIfEventStatsLinkFailureCountDelta                 Counter64,
    cfprApAdaptorFcIfEventStatsLinkFailureCountDeltaAvg              Unsigned64,
    cfprApAdaptorFcIfEventStatsLinkFailureCountDeltaMax              Unsigned64,
    cfprApAdaptorFcIfEventStatsLinkFailureCountDeltaMin              Unsigned64,
    cfprApAdaptorFcIfEventStatsLipCount                              Unsigned64,
    cfprApAdaptorFcIfEventStatsLipCountDelta                         Counter64,
    cfprApAdaptorFcIfEventStatsLipCountDeltaAvg                      Unsigned64,
    cfprApAdaptorFcIfEventStatsLipCountDeltaMax                      Unsigned64,
    cfprApAdaptorFcIfEventStatsLipCountDeltaMin                      Unsigned64,
    cfprApAdaptorFcIfEventStatsLossOfSignalCount                     Unsigned64,
    cfprApAdaptorFcIfEventStatsLossOfSignalCountDelta                Counter64,
    cfprApAdaptorFcIfEventStatsLossOfSignalCountDeltaAvg             Unsigned64,
    cfprApAdaptorFcIfEventStatsLossOfSignalCountDeltaMax             Unsigned64,
    cfprApAdaptorFcIfEventStatsLossOfSignalCountDeltaMin             Unsigned64,
    cfprApAdaptorFcIfEventStatsLossOfSyncCount                       Unsigned64,
    cfprApAdaptorFcIfEventStatsLossOfSyncCountDelta                  Counter64,
    cfprApAdaptorFcIfEventStatsLossOfSyncCountDeltaAvg               Unsigned64,
    cfprApAdaptorFcIfEventStatsLossOfSyncCountDeltaMax               Unsigned64,
    cfprApAdaptorFcIfEventStatsLossOfSyncCountDeltaMin               Unsigned64,
    cfprApAdaptorFcIfEventStatsNOSCount                              Unsigned64,
    cfprApAdaptorFcIfEventStatsNOSCountDelta                         Counter64,
    cfprApAdaptorFcIfEventStatsNOSCountDeltaAvg                      Unsigned64,
    cfprApAdaptorFcIfEventStatsNOSCountDeltaMax                      Unsigned64,
    cfprApAdaptorFcIfEventStatsNOSCountDeltaMin                      Unsigned64,
    cfprApAdaptorFcIfEventStatsSecondsSinceLastReset                 Unsigned64,
    cfprApAdaptorFcIfEventStatsSecondsSinceLastResetDelta            Counter64,
    cfprApAdaptorFcIfEventStatsSecondsSinceLastResetDeltaAvg         Unsigned64,
    cfprApAdaptorFcIfEventStatsSecondsSinceLastResetDeltaMax         Unsigned64,
    cfprApAdaptorFcIfEventStatsSecondsSinceLastResetDeltaMin         Unsigned64,
    cfprApAdaptorFcIfEventStatsSeqProtocolErrCount                   Unsigned64,
    cfprApAdaptorFcIfEventStatsSeqProtocolErrCountDelta              Counter64,
    cfprApAdaptorFcIfEventStatsSeqProtocolErrCountDeltaAvg           Unsigned64,
    cfprApAdaptorFcIfEventStatsSeqProtocolErrCountDeltaMax           Unsigned64,
    cfprApAdaptorFcIfEventStatsSeqProtocolErrCountDeltaMin           Unsigned64,
    cfprApAdaptorFcIfEventStatsSuspect                               TruthValue,
    cfprApAdaptorFcIfEventStatsThresholded                           CfprApAdaptorFcIfEventStatsThresholded,
    cfprApAdaptorFcIfEventStatsTimeCollected                         DateAndTime,
    cfprApAdaptorFcIfEventStatsUpdate                                Gauge32
}

cfprApAdaptorFcIfEventStatsInstanceId OBJECT-TYPE
    SYNTAX       CfprApManagedObjectId
    MAX-ACCESS   not-accessible
    STATUS       current
    DESCRIPTION
        "Instance identifier of the managed object."
    ::= { cfprApAdaptorFcIfEventStatsEntry 1 }

cfprApAdaptorFcIfEventStatsDn OBJECT-TYPE
    SYNTAX       CfprApManagedObjectDn
    MAX-ACCESS   read-only
    STATUS       current
    DESCRIPTION
        "Cisco Firepower adaptor:FcIfEventStats:dn managed
        object property"
    ::= { cfprApAdaptorFcIfEventStatsEntry 2 }

cfprApAdaptorFcIfEventStatsRn OBJECT-TYPE
    SYNTAX       SnmpAdminString
    MAX-ACCESS   read-only
    STATUS       current
    DESCRIPTION
        "Cisco Firepower adaptor:FcIfEventStats:rn managed
        object property"
    ::= { cfprApAdaptorFcIfEventStatsEntry 3 }

cfprApAdaptorFcIfEventStatsIntervals OBJECT-TYPE
    SYNTAX       Gauge32
    MAX-ACCESS   read-only
    STATUS       current
    DESCRIPTION
        "Cisco Firepower adaptor:FcIfEventStats:intervals
        managed object property"
    ::= { cfprApAdaptorFcIfEventStatsEntry 4 }

cfprApAdaptorFcIfEventStatsInvalidCRCCount OBJECT-TYPE
    SYNTAX       Unsigned64
    MAX-ACCESS   read-only
    STATUS       current
    DESCRIPTION
        "Cisco Firepower adaptor:FcIfEventStats:invalidCRCCount
        managed object property"
    ::= { cfprApAdaptorFcIfEventStatsEntry 5 }

cfprApAdaptorFcIfEventStatsInvalidCRCCountDelta OBJECT-TYPE
    SYNTAX       Counter64
    MAX-ACCESS   read-only
    STATUS       current
    DESCRIPTION
        "Cisco Firepower adaptor:FcIfEventStats:invalidCRCCountDelta
        managed object property"
    ::= { cfprApAdaptorFcIfEventStatsEntry 6 }

cfprApAdaptorFcIfEventStatsInvalidCRCCountDeltaAvg OBJECT-TYPE
    SYNTAX       Unsigned64
    MAX-ACCESS   read-only
    STATUS       current
    DESCRIPTION
        "Cisco Firepower adaptor:FcIfEventStats:invalidCRCCountDeltaAvg
        managed object property"
    ::= { cfprApAdaptorFcIfEventStatsEntry 7 }

cfprApAdaptorFcIfEventStatsInvalidCRCCountDeltaMax OBJECT-TYPE
    SYNTAX       Unsigned64
    MAX-ACCESS   read-only
    STATUS       current
    DESCRIPTION
        "Cisco Firepower adaptor:FcIfEventStats:invalidCRCCountDeltaMax
        managed object property"
    ::= { cfprApAdaptorFcIfEventStatsEntry 8 }

cfprApAdaptorFcIfEventStatsInvalidCRCCountDeltaMin OBJECT-TYPE
    SYNTAX       Unsigned64
    MAX-ACCESS   read-only
    STATUS       current
    DESCRIPTION
        "Cisco Firepower adaptor:FcIfEventStats:invalidCRCCountDeltaMin
        managed object property"
    ::= { cfprApAdaptorFcIfEventStatsEntry 9 }

cfprApAdaptorFcIfEventStatsLinkFailureCount OBJECT-TYPE
    SYNTAX       Unsigned64
    MAX-ACCESS   read-only
    STATUS       current
    DESCRIPTION
        "Cisco Firepower adaptor:FcIfEventStats:linkFailureCount
        managed object property"
    ::= { cfprApAdaptorFcIfEventStatsEntry 10 }

cfprApAdaptorFcIfEventStatsLinkFailureCountDelta OBJECT-TYPE
    SYNTAX       Counter64
    MAX-ACCESS   read-only
    STATUS       current
    DESCRIPTION
        "Cisco Firepower adaptor:FcIfEventStats:linkFailureCountDelta
        managed object property"
    ::= { cfprApAdaptorFcIfEventStatsEntry 11 }

cfprApAdaptorFcIfEventStatsLinkFailureCountDeltaAvg OBJECT-TYPE
    SYNTAX       Unsigned64
    MAX-ACCESS   read-only
    STATUS       current
    DESCRIPTION
        "Cisco Firepower adaptor:FcIfEventStats:linkFailureCountDeltaAvg
        managed object property"
    ::= { cfprApAdaptorFcIfEventStatsEntry 12 }

cfprApAdaptorFcIfEventStatsLinkFailureCountDeltaMax OBJECT-TYPE
    SYNTAX       Unsigned64
    MAX-ACCESS   read-only
    STATUS       current
    DESCRIPTION
        "Cisco Firepower adaptor:FcIfEventStats:linkFailureCountDeltaMax
        managed object property"
    ::= { cfprApAdaptorFcIfEventStatsEntry 13 }

cfprApAdaptorFcIfEventStatsLinkFailureCountDeltaMin OBJECT-TYPE
    SYNTAX       Unsigned64
    MAX-ACCESS   read-only
    STATUS       current
    DESCRIPTION
        "Cisco Firepower adaptor:FcIfEventStats:linkFailureCountDeltaMin
        managed object property"
    ::= { cfprApAdaptorFcIfEventStatsEntry 14 }

cfprApAdaptorFcIfEventStatsLipCount OBJECT-TYPE
    SYNTAX       Unsigned64
    MAX-ACCESS   read-only
    STATUS       current
    DESCRIPTION
        "Cisco Firepower adaptor:FcIfEventStats:lipCount
        managed object property"
    ::= { cfprApAdaptorFcIfEventStatsEntry 15 }

cfprApAdaptorFcIfEventStatsLipCountDelta OBJECT-TYPE
    SYNTAX       Counter64
    MAX-ACCESS   read-only
    STATUS       current
    DESCRIPTION
        "Cisco Firepower adaptor:FcIfEventStats:lipCountDelta
        managed object property"
    ::= { cfprApAdaptorFcIfEventStatsEntry 16 }

cfprApAdaptorFcIfEventStatsLipCountDeltaAvg OBJECT-TYPE
    SYNTAX       Unsigned64
    MAX-ACCESS   read-only
    STATUS       current
    DESCRIPTION
        "Cisco Firepower adaptor:FcIfEventStats:lipCountDeltaAvg
        managed object property"
    ::= { cfprApAdaptorFcIfEventStatsEntry 17 }

cfprApAdaptorFcIfEventStatsLipCountDeltaMax OBJECT-TYPE
    SYNTAX       Unsigned64
    MAX-ACCESS   read-only
    STATUS       current
    DESCRIPTION
        "Cisco Firepower adaptor:FcIfEventStats:lipCountDeltaMax
        managed object property"
    ::= { cfprApAdaptorFcIfEventStatsEntry 18 }

cfprApAdaptorFcIfEventStatsLipCountDeltaMin OBJECT-TYPE
    SYNTAX       Unsigned64
    MAX-ACCESS   read-only
    STATUS       current
    DESCRIPTION
        "Cisco Firepower adaptor:FcIfEventStats:lipCountDeltaMin
        managed object property"
    ::= { cfprApAdaptorFcIfEventStatsEntry 19 }

cfprApAdaptorFcIfEventStatsLossOfSignalCount OBJECT-TYPE
    SYNTAX       Unsigned64
    MAX-ACCESS   read-only
    STATUS       current
    DESCRIPTION
        "Cisco Firepower adaptor:FcIfEventStats:lossOfSignalCount
        managed object property"
    ::= { cfprApAdaptorFcIfEventStatsEntry 20 }

cfprApAdaptorFcIfEventStatsLossOfSignalCountDelta OBJECT-TYPE
    SYNTAX       Counter64
    MAX-ACCESS   read-only
    STATUS       current
    DESCRIPTION
        "Cisco Firepower adaptor:FcIfEventStats:lossOfSignalCountDelta
        managed object property"
    ::= { cfprApAdaptorFcIfEventStatsEntry 21 }

cfprApAdaptorFcIfEventStatsLossOfSignalCountDeltaAvg OBJECT-TYPE
    SYNTAX       Unsigned64
    MAX-ACCESS   read-only
    STATUS       current
    DESCRIPTION
        "Cisco Firepower adaptor:FcIfEventStats:lossOfSignalCountDeltaAvg
        managed object property"
    ::= { cfprApAdaptorFcIfEventStatsEntry 22 }

cfprApAdaptorFcIfEventStatsLossOfSignalCountDeltaMax OBJECT-TYPE
    SYNTAX       Unsigned64
    MAX-ACCESS   read-only
    STATUS       current
    DESCRIPTION
        "Cisco Firepower adaptor:FcIfEventStats:lossOfSignalCountDeltaMax
        managed object property"
    ::= { cfprApAdaptorFcIfEventStatsEntry 23 }

cfprApAdaptorFcIfEventStatsLossOfSignalCountDeltaMin OBJECT-TYPE
    SYNTAX       Unsigned64
    MAX-ACCESS   read-only
    STATUS       current
    DESCRIPTION
        "Cisco Firepower adaptor:FcIfEventStats:lossOfSignalCountDeltaMin
        managed object property"
    ::= { cfprApAdaptorFcIfEventStatsEntry 24 }

cfprApAdaptorFcIfEventStatsLossOfSyncCount OBJECT-TYPE
    SYNTAX       Unsigned64
    MAX-ACCESS   read-only
    STATUS       current
    DESCRIPTION
        "Cisco Firepower adaptor:FcIfEventStats:lossOfSyncCount
        managed object property"
    ::= { cfprApAdaptorFcIfEventStatsEntry 25 }

cfprApAdaptorFcIfEventStatsLossOfSyncCountDelta OBJECT-TYPE
    SYNTAX       Counter64
    MAX-ACCESS   read-only
    STATUS       current
    DESCRIPTION
        "Cisco Firepower adaptor:FcIfEventStats:lossOfSyncCountDelta
        managed object property"
    ::= { cfprApAdaptorFcIfEventStatsEntry 26 }

cfprApAdaptorFcIfEventStatsLossOfSyncCountDeltaAvg OBJECT-TYPE
    SYNTAX       Unsigned64
    MAX-ACCESS   read-only
    STATUS       current
    DESCRIPTION
        "Cisco Firepower adaptor:FcIfEventStats:lossOfSyncCountDeltaAvg
        managed object property"
    ::= { cfprApAdaptorFcIfEventStatsEntry 27 }

cfprApAdaptorFcIfEventStatsLossOfSyncCountDeltaMax OBJECT-TYPE
    SYNTAX       Unsigned64
    MAX-ACCESS   read-only
    STATUS       current
    DESCRIPTION
        "Cisco Firepower adaptor:FcIfEventStats:lossOfSyncCountDeltaMax
        managed object property"
    ::= { cfprApAdaptorFcIfEventStatsEntry 28 }

cfprApAdaptorFcIfEventStatsLossOfSyncCountDeltaMin OBJECT-TYPE
    SYNTAX       Unsigned64
    MAX-ACCESS   read-only
    STATUS       current
    DESCRIPTION
        "Cisco Firepower adaptor:FcIfEventStats:lossOfSyncCountDeltaMin
        managed object property"
    ::= { cfprApAdaptorFcIfEventStatsEntry 29 }

cfprApAdaptorFcIfEventStatsNOSCount OBJECT-TYPE
    SYNTAX       Unsigned64
    MAX-ACCESS   read-only
    STATUS       current
    DESCRIPTION
        "Cisco Firepower adaptor:FcIfEventStats:nOSCount
        managed object property"
    ::= { cfprApAdaptorFcIfEventStatsEntry 30 }

cfprApAdaptorFcIfEventStatsNOSCountDelta OBJECT-TYPE
    SYNTAX       Counter64
    MAX-ACCESS   read-only
    STATUS       current
    DESCRIPTION
        "Cisco Firepower adaptor:FcIfEventStats:nOSCountDelta
        managed object property"
    ::= { cfprApAdaptorFcIfEventStatsEntry 31 }

cfprApAdaptorFcIfEventStatsNOSCountDeltaAvg OBJECT-TYPE
    SYNTAX       Unsigned64
    MAX-ACCESS   read-only
    STATUS       current
    DESCRIPTION
        "Cisco Firepower adaptor:FcIfEventStats:nOSCountDeltaAvg
        managed object property"
    ::= { cfprApAdaptorFcIfEventStatsEntry 32 }

cfprApAdaptorFcIfEventStatsNOSCountDeltaMax OBJECT-TYPE
    SYNTAX       Unsigned64
    MAX-ACCESS   read-only
    STATUS       current
    DESCRIPTION
        "Cisco Firepower adaptor:FcIfEventStats:nOSCountDeltaMax
        managed object property"
    ::= { cfprApAdaptorFcIfEventStatsEntry 33 }

cfprApAdaptorFcIfEventStatsNOSCountDeltaMin OBJECT-TYPE
    SYNTAX       Unsigned64
    MAX-ACCESS   read-only
    STATUS       current
    DESCRIPTION
        "Cisco Firepower adaptor:FcIfEventStats:nOSCountDeltaMin
        managed object property"
    ::= { cfprApAdaptorFcIfEventStatsEntry 34 }

cfprApAdaptorFcIfEventStatsSecondsSinceLastReset OBJECT-TYPE
    SYNTAX       Unsigned64
    MAX-ACCESS   read-only
    STATUS       current
    DESCRIPTION
        "Cisco Firepower adaptor:FcIfEventStats:secondsSinceLastReset
        managed object property"
    ::= { cfprApAdaptorFcIfEventStatsEntry 35 }

cfprApAdaptorFcIfEventStatsSecondsSinceLastResetDelta OBJECT-TYPE
    SYNTAX       Counter64
    MAX-ACCESS   read-only
    STATUS       current
    DESCRIPTION
        "Cisco Firepower adaptor:FcIfEventStats:secondsSinceLastResetDelta
         managed object property"
    ::= { cfprApAdaptorFcIfEventStatsEntry 36 }

cfprApAdaptorFcIfEventStatsSecondsSinceLastResetDeltaAvg OBJECT-TYPE
    SYNTAX       Unsigned64
    MAX-ACCESS   read-only
    STATUS       current
    DESCRIPTION
        "Cisco Firepower adaptor:FcIfEventStats:secondsSinceLastResetDelta
        Avg managed object property"
    ::= { cfprApAdaptorFcIfEventStatsEntry 37 }

cfprApAdaptorFcIfEventStatsSecondsSinceLastResetDeltaMax OBJECT-TYPE
    SYNTAX       Unsigned64
    MAX-ACCESS   read-only
    STATUS       current
    DESCRIPTION
        "Cisco Firepower adaptor:FcIfEventStats:secondsSinceLastResetDelta
        Max managed object property"
    ::= { cfprApAdaptorFcIfEventStatsEntry 38 }

cfprApAdaptorFcIfEventStatsSecondsSinceLastResetDeltaMin OBJECT-TYPE
    SYNTAX       Unsigned64
    MAX-ACCESS   read-only
    STATUS       current
    DESCRIPTION
        "Cisco Firepower adaptor:FcIfEventStats:secondsSinceLastResetDelta
        Min managed object property"
    ::= { cfprApAdaptorFcIfEventStatsEntry 39 }

cfprApAdaptorFcIfEventStatsSeqProtocolErrCount OBJECT-TYPE
    SYNTAX       Unsigned64
    MAX-ACCESS   read-only
    STATUS       current
    DESCRIPTION
        "Cisco Firepower adaptor:FcIfEventStats:seqProtocolErrCount
        managed object property"
    ::= { cfprApAdaptorFcIfEventStatsEntry 40 }

cfprApAdaptorFcIfEventStatsSeqProtocolErrCountDelta OBJECT-TYPE
    SYNTAX       Counter64
    MAX-ACCESS   read-only
    STATUS       current
    DESCRIPTION
        "Cisco Firepower adaptor:FcIfEventStats:seqProtocolErrCountDelta
        managed object property"
    ::= { cfprApAdaptorFcIfEventStatsEntry 41 }

cfprApAdaptorFcIfEventStatsSeqProtocolErrCountDeltaAvg OBJECT-TYPE
    SYNTAX       Unsigned64
    MAX-ACCESS   read-only
    STATUS       current
    DESCRIPTION
        "Cisco Firepower adaptor:FcIfEventStats:seqProtocolErrCountDeltaAv
        g managed object property"
    ::= { cfprApAdaptorFcIfEventStatsEntry 42 }

cfprApAdaptorFcIfEventStatsSeqProtocolErrCountDeltaMax OBJECT-TYPE
    SYNTAX       Unsigned64
    MAX-ACCESS   read-only
    STATUS       current
    DESCRIPTION
        "Cisco Firepower adaptor:FcIfEventStats:seqProtocolErrCountDeltaMa
        x managed object property"
    ::= { cfprApAdaptorFcIfEventStatsEntry 43 }

cfprApAdaptorFcIfEventStatsSeqProtocolErrCountDeltaMin OBJECT-TYPE
    SYNTAX       Unsigned64
    MAX-ACCESS   read-only
    STATUS       current
    DESCRIPTION
        "Cisco Firepower adaptor:FcIfEventStats:seqProtocolErrCountDeltaMi
        n managed object property"
    ::= { cfprApAdaptorFcIfEventStatsEntry 44 }

cfprApAdaptorFcIfEventStatsSuspect OBJECT-TYPE
    SYNTAX       TruthValue
    MAX-ACCESS   read-only
    STATUS       current
    DESCRIPTION
        "Cisco Firepower adaptor:FcIfEventStats:suspect
        managed object property"
    ::= { cfprApAdaptorFcIfEventStatsEntry 45 }

cfprApAdaptorFcIfEventStatsThresholded OBJECT-TYPE
    SYNTAX       CfprApAdaptorFcIfEventStatsThresholded
    MAX-ACCESS   read-only
    STATUS       current
    DESCRIPTION
        "Cisco Firepower adaptor:FcIfEventStats:thresholded
        managed object property"
    ::= { cfprApAdaptorFcIfEventStatsEntry 46 }

cfprApAdaptorFcIfEventStatsTimeCollected OBJECT-TYPE
    SYNTAX       DateAndTime
    MAX-ACCESS   read-only
    STATUS       current
    DESCRIPTION
        "Cisco Firepower adaptor:FcIfEventStats:timeCollected
        managed object property"
    ::= { cfprApAdaptorFcIfEventStatsEntry 47 }

cfprApAdaptorFcIfEventStatsUpdate OBJECT-TYPE
    SYNTAX       Gauge32
    MAX-ACCESS   read-only
    STATUS       current
    DESCRIPTION
        "Cisco Firepower adaptor:FcIfEventStats:update
        managed object property"
    ::= { cfprApAdaptorFcIfEventStatsEntry 48 }

cfprApAdaptorFcIfEventStatsHistTable OBJECT-TYPE
    SYNTAX           SEQUENCE OF CfprApAdaptorFcIfEventStatsHistEntry
    MAX-ACCESS       not-accessible
    STATUS           current
    DESCRIPTION
        "Cisco Firepower adaptor:FcIfEventStatsHist managed object table"
    ::= { cfprApAdaptorObjects 39 }

cfprApAdaptorFcIfEventStatsHistEntry OBJECT-TYPE
    SYNTAX           CfprApAdaptorFcIfEventStatsHistEntry
    MAX-ACCESS       not-accessible
    STATUS           current
    DESCRIPTION
        "Entry for the cfprApAdaptorFcIfEventStatsHistTable table."
    INDEX { cfprApAdaptorFcIfEventStatsHistInstanceId }
    ::= { cfprApAdaptorFcIfEventStatsHistTable 1 }

CfprApAdaptorFcIfEventStatsHistEntry ::= SEQUENCE {
    cfprApAdaptorFcIfEventStatsHistInstanceId                        CfprApManagedObjectId,
    cfprApAdaptorFcIfEventStatsHistDn                                CfprApManagedObjectDn,
    cfprApAdaptorFcIfEventStatsHistRn                                SnmpAdminString,
    cfprApAdaptorFcIfEventStatsHistId                                Unsigned64,
    cfprApAdaptorFcIfEventStatsHistInvalidCRCCount                   Unsigned64,
    cfprApAdaptorFcIfEventStatsHistInvalidCRCCountDelta              Unsigned64,
    cfprApAdaptorFcIfEventStatsHistInvalidCRCCountDeltaAvg           Unsigned64,
    cfprApAdaptorFcIfEventStatsHistInvalidCRCCountDeltaMax           Unsigned64,
    cfprApAdaptorFcIfEventStatsHistInvalidCRCCountDeltaMin           Unsigned64,
    cfprApAdaptorFcIfEventStatsHistLinkFailureCount                  Unsigned64,
    cfprApAdaptorFcIfEventStatsHistLinkFailureCountDelta             Unsigned64,
    cfprApAdaptorFcIfEventStatsHistLinkFailureCountDeltaAvg          Unsigned64,
    cfprApAdaptorFcIfEventStatsHistLinkFailureCountDeltaMax          Unsigned64,
    cfprApAdaptorFcIfEventStatsHistLinkFailureCountDeltaMin          Unsigned64,
    cfprApAdaptorFcIfEventStatsHistLipCount                          Unsigned64,
    cfprApAdaptorFcIfEventStatsHistLipCountDelta                     Unsigned64,
    cfprApAdaptorFcIfEventStatsHistLipCountDeltaAvg                  Unsigned64,
    cfprApAdaptorFcIfEventStatsHistLipCountDeltaMax                  Unsigned64,
    cfprApAdaptorFcIfEventStatsHistLipCountDeltaMin                  Unsigned64,
    cfprApAdaptorFcIfEventStatsHistLossOfSignalCount                 Unsigned64,
    cfprApAdaptorFcIfEventStatsHistLossOfSignalCountDelta            Unsigned64,
    cfprApAdaptorFcIfEventStatsHistLossOfSignalCountDeltaAvg         Unsigned64,
    cfprApAdaptorFcIfEventStatsHistLossOfSignalCountDeltaMax         Unsigned64,
    cfprApAdaptorFcIfEventStatsHistLossOfSignalCountDeltaMin         Unsigned64,
    cfprApAdaptorFcIfEventStatsHistLossOfSyncCount                   Unsigned64,
    cfprApAdaptorFcIfEventStatsHistLossOfSyncCountDelta              Unsigned64,
    cfprApAdaptorFcIfEventStatsHistLossOfSyncCountDeltaAvg           Unsigned64,
    cfprApAdaptorFcIfEventStatsHistLossOfSyncCountDeltaMax           Unsigned64,
    cfprApAdaptorFcIfEventStatsHistLossOfSyncCountDeltaMin           Unsigned64,
    cfprApAdaptorFcIfEventStatsHistMostRecent                        TruthValue,
    cfprApAdaptorFcIfEventStatsHistNOSCount                          Unsigned64,
    cfprApAdaptorFcIfEventStatsHistNOSCountDelta                     Unsigned64,
    cfprApAdaptorFcIfEventStatsHistNOSCountDeltaAvg                  Unsigned64,
    cfprApAdaptorFcIfEventStatsHistNOSCountDeltaMax                  Unsigned64,
    cfprApAdaptorFcIfEventStatsHistNOSCountDeltaMin                  Unsigned64,
    cfprApAdaptorFcIfEventStatsHistSecondsSinceLastReset             Unsigned64,
    cfprApAdaptorFcIfEventStatsHistSecondsSinceLastResetDelta        Unsigned64,
    cfprApAdaptorFcIfEventStatsHistSecondsSinceLastResetDeltaAvg     Unsigned64,
    cfprApAdaptorFcIfEventStatsHistSecondsSinceLastResetDeltaMax     Unsigned64,
    cfprApAdaptorFcIfEventStatsHistSecondsSinceLastResetDeltaMin     Unsigned64,
    cfprApAdaptorFcIfEventStatsHistSeqProtocolErrCount               Unsigned64,
    cfprApAdaptorFcIfEventStatsHistSeqProtocolErrCountDelta          Unsigned64,
    cfprApAdaptorFcIfEventStatsHistSeqProtocolErrCountDeltaAvg       Unsigned64,
    cfprApAdaptorFcIfEventStatsHistSeqProtocolErrCountDeltaMax       Unsigned64,
    cfprApAdaptorFcIfEventStatsHistSeqProtocolErrCountDeltaMin       Unsigned64,
    cfprApAdaptorFcIfEventStatsHistSuspect                           TruthValue,
    cfprApAdaptorFcIfEventStatsHistThresholded                       CfprApAdaptorFcIfEventStatsHistThresholded,
    cfprApAdaptorFcIfEventStatsHistTimeCollected                     DateAndTime
}

cfprApAdaptorFcIfEventStatsHistInstanceId OBJECT-TYPE
    SYNTAX       CfprApManagedObjectId
    MAX-ACCESS   not-accessible
    STATUS       current
    DESCRIPTION
        "Instance identifier of the managed object."
    ::= { cfprApAdaptorFcIfEventStatsHistEntry 1 }

cfprApAdaptorFcIfEventStatsHistDn OBJECT-TYPE
    SYNTAX       CfprApManagedObjectDn
    MAX-ACCESS   read-only
    STATUS       current
    DESCRIPTION
        "Cisco Firepower adaptor:FcIfEventStatsHist:dn
        managed object property"
    ::= { cfprApAdaptorFcIfEventStatsHistEntry 2 }

cfprApAdaptorFcIfEventStatsHistRn OBJECT-TYPE
    SYNTAX       SnmpAdminString
    MAX-ACCESS   read-only
    STATUS       current
    DESCRIPTION
        "Cisco Firepower adaptor:FcIfEventStatsHist:rn
        managed object property"
    ::= { cfprApAdaptorFcIfEventStatsHistEntry 3 }

cfprApAdaptorFcIfEventStatsHistId OBJECT-TYPE
    SYNTAX       Unsigned64
    MAX-ACCESS   read-only
    STATUS       current
    DESCRIPTION
        "Cisco Firepower adaptor:FcIfEventStatsHist:id
        managed object property"
    ::= { cfprApAdaptorFcIfEventStatsHistEntry 4 }

cfprApAdaptorFcIfEventStatsHistInvalidCRCCount OBJECT-TYPE
    SYNTAX       Unsigned64
    MAX-ACCESS   read-only
    STATUS       current
    DESCRIPTION
        "Cisco Firepower adaptor:FcIfEventStatsHist:invalidCRCCount
        managed object property"
    ::= { cfprApAdaptorFcIfEventStatsHistEntry 5 }

cfprApAdaptorFcIfEventStatsHistInvalidCRCCountDelta OBJECT-TYPE
    SYNTAX       Unsigned64
    MAX-ACCESS   read-only
    STATUS       current
    DESCRIPTION
        "Cisco Firepower adaptor:FcIfEventStatsHist:invalidCRCCountDelta
        managed object property"
    ::= { cfprApAdaptorFcIfEventStatsHistEntry 6 }

cfprApAdaptorFcIfEventStatsHistInvalidCRCCountDeltaAvg OBJECT-TYPE
    SYNTAX       Unsigned64
    MAX-ACCESS   read-only
    STATUS       current
    DESCRIPTION
        "Cisco Firepower adaptor:FcIfEventStatsHist:invalidCRCCountDeltaAv
        g managed object property"
    ::= { cfprApAdaptorFcIfEventStatsHistEntry 7 }

cfprApAdaptorFcIfEventStatsHistInvalidCRCCountDeltaMax OBJECT-TYPE
    SYNTAX       Unsigned64
    MAX-ACCESS   read-only
    STATUS       current
    DESCRIPTION
        "Cisco Firepower adaptor:FcIfEventStatsHist:invalidCRCCountDeltaMa
        x managed object property"
    ::= { cfprApAdaptorFcIfEventStatsHistEntry 8 }

cfprApAdaptorFcIfEventStatsHistInvalidCRCCountDeltaMin OBJECT-TYPE
    SYNTAX       Unsigned64
    MAX-ACCESS   read-only
    STATUS       current
    DESCRIPTION
        "Cisco Firepower adaptor:FcIfEventStatsHist:invalidCRCCountDeltaMi
        n managed object property"
    ::= { cfprApAdaptorFcIfEventStatsHistEntry 9 }

cfprApAdaptorFcIfEventStatsHistLinkFailureCount OBJECT-TYPE
    SYNTAX       Unsigned64
    MAX-ACCESS   read-only
    STATUS       current
    DESCRIPTION
        "Cisco Firepower adaptor:FcIfEventStatsHist:linkFailureCount
        managed object property"
    ::= { cfprApAdaptorFcIfEventStatsHistEntry 10 }

cfprApAdaptorFcIfEventStatsHistLinkFailureCountDelta OBJECT-TYPE
    SYNTAX       Unsigned64
    MAX-ACCESS   read-only
    STATUS       current
    DESCRIPTION
        "Cisco Firepower adaptor:FcIfEventStatsHist:linkFailureCountDelta
        managed object property"
    ::= { cfprApAdaptorFcIfEventStatsHistEntry 11 }

cfprApAdaptorFcIfEventStatsHistLinkFailureCountDeltaAvg OBJECT-TYPE
    SYNTAX       Unsigned64
    MAX-ACCESS   read-only
    STATUS       current
    DESCRIPTION
        "Cisco Firepower adaptor:FcIfEventStatsHist:linkFailureCountDeltaA
        vg managed object property"
    ::= { cfprApAdaptorFcIfEventStatsHistEntry 12 }

cfprApAdaptorFcIfEventStatsHistLinkFailureCountDeltaMax OBJECT-TYPE
    SYNTAX       Unsigned64
    MAX-ACCESS   read-only
    STATUS       current
    DESCRIPTION
        "Cisco Firepower adaptor:FcIfEventStatsHist:linkFailureCountDeltaM
        ax managed object property"
    ::= { cfprApAdaptorFcIfEventStatsHistEntry 13 }

cfprApAdaptorFcIfEventStatsHistLinkFailureCountDeltaMin OBJECT-TYPE
    SYNTAX       Unsigned64
    MAX-ACCESS   read-only
    STATUS       current
    DESCRIPTION
        "Cisco Firepower adaptor:FcIfEventStatsHist:linkFailureCountDeltaM
        in managed object property"
    ::= { cfprApAdaptorFcIfEventStatsHistEntry 14 }

cfprApAdaptorFcIfEventStatsHistLipCount OBJECT-TYPE
    SYNTAX       Unsigned64
    MAX-ACCESS   read-only
    STATUS       current
    DESCRIPTION
        "Cisco Firepower adaptor:FcIfEventStatsHist:lipCount
        managed object property"
    ::= { cfprApAdaptorFcIfEventStatsHistEntry 15 }

cfprApAdaptorFcIfEventStatsHistLipCountDelta OBJECT-TYPE
    SYNTAX       Unsigned64
    MAX-ACCESS   read-only
    STATUS       current
    DESCRIPTION
        "Cisco Firepower adaptor:FcIfEventStatsHist:lipCountDelta
        managed object property"
    ::= { cfprApAdaptorFcIfEventStatsHistEntry 16 }

cfprApAdaptorFcIfEventStatsHistLipCountDeltaAvg OBJECT-TYPE
    SYNTAX       Unsigned64
    MAX-ACCESS   read-only
    STATUS       current
    DESCRIPTION
        "Cisco Firepower adaptor:FcIfEventStatsHist:lipCountDeltaAvg
        managed object property"
    ::= { cfprApAdaptorFcIfEventStatsHistEntry 17 }

cfprApAdaptorFcIfEventStatsHistLipCountDeltaMax OBJECT-TYPE
    SYNTAX       Unsigned64
    MAX-ACCESS   read-only
    STATUS       current
    DESCRIPTION
        "Cisco Firepower adaptor:FcIfEventStatsHist:lipCountDeltaMax
        managed object property"
    ::= { cfprApAdaptorFcIfEventStatsHistEntry 18 }

cfprApAdaptorFcIfEventStatsHistLipCountDeltaMin OBJECT-TYPE
    SYNTAX       Unsigned64
    MAX-ACCESS   read-only
    STATUS       current
    DESCRIPTION
        "Cisco Firepower adaptor:FcIfEventStatsHist:lipCountDeltaMin
        managed object property"
    ::= { cfprApAdaptorFcIfEventStatsHistEntry 19 }

cfprApAdaptorFcIfEventStatsHistLossOfSignalCount OBJECT-TYPE
    SYNTAX       Unsigned64
    MAX-ACCESS   read-only
    STATUS       current
    DESCRIPTION
        "Cisco Firepower adaptor:FcIfEventStatsHist:lossOfSignalCount
        managed object property"
    ::= { cfprApAdaptorFcIfEventStatsHistEntry 20 }

cfprApAdaptorFcIfEventStatsHistLossOfSignalCountDelta OBJECT-TYPE
    SYNTAX       Unsigned64
    MAX-ACCESS   read-only
    STATUS       current
    DESCRIPTION
        "Cisco Firepower adaptor:FcIfEventStatsHist:lossOfSignalCountDelta
         managed object property"
    ::= { cfprApAdaptorFcIfEventStatsHistEntry 21 }

cfprApAdaptorFcIfEventStatsHistLossOfSignalCountDeltaAvg OBJECT-TYPE
    SYNTAX       Unsigned64
    MAX-ACCESS   read-only
    STATUS       current
    DESCRIPTION
        "Cisco Firepower adaptor:FcIfEventStatsHist:lossOfSignalCountDelta
        Avg managed object property"
    ::= { cfprApAdaptorFcIfEventStatsHistEntry 22 }

cfprApAdaptorFcIfEventStatsHistLossOfSignalCountDeltaMax OBJECT-TYPE
    SYNTAX       Unsigned64
    MAX-ACCESS   read-only
    STATUS       current
    DESCRIPTION
        "Cisco Firepower adaptor:FcIfEventStatsHist:lossOfSignalCountDelta
        Max managed object property"
    ::= { cfprApAdaptorFcIfEventStatsHistEntry 23 }

cfprApAdaptorFcIfEventStatsHistLossOfSignalCountDeltaMin OBJECT-TYPE
    SYNTAX       Unsigned64
    MAX-ACCESS   read-only
    STATUS       current
    DESCRIPTION
        "Cisco Firepower adaptor:FcIfEventStatsHist:lossOfSignalCountDelta
        Min managed object property"
    ::= { cfprApAdaptorFcIfEventStatsHistEntry 24 }

cfprApAdaptorFcIfEventStatsHistLossOfSyncCount OBJECT-TYPE
    SYNTAX       Unsigned64
    MAX-ACCESS   read-only
    STATUS       current
    DESCRIPTION
        "Cisco Firepower adaptor:FcIfEventStatsHist:lossOfSyncCount
        managed object property"
    ::= { cfprApAdaptorFcIfEventStatsHistEntry 25 }

cfprApAdaptorFcIfEventStatsHistLossOfSyncCountDelta OBJECT-TYPE
    SYNTAX       Unsigned64
    MAX-ACCESS   read-only
    STATUS       current
    DESCRIPTION
        "Cisco Firepower adaptor:FcIfEventStatsHist:lossOfSyncCountDelta
        managed object property"
    ::= { cfprApAdaptorFcIfEventStatsHistEntry 26 }

cfprApAdaptorFcIfEventStatsHistLossOfSyncCountDeltaAvg OBJECT-TYPE
    SYNTAX       Unsigned64
    MAX-ACCESS   read-only
    STATUS       current
    DESCRIPTION
        "Cisco Firepower adaptor:FcIfEventStatsHist:lossOfSyncCountDeltaAv
        g managed object property"
    ::= { cfprApAdaptorFcIfEventStatsHistEntry 27 }

cfprApAdaptorFcIfEventStatsHistLossOfSyncCountDeltaMax OBJECT-TYPE
    SYNTAX       Unsigned64
    MAX-ACCESS   read-only
    STATUS       current
    DESCRIPTION
        "Cisco Firepower adaptor:FcIfEventStatsHist:lossOfSyncCountDeltaMa
        x managed object property"
    ::= { cfprApAdaptorFcIfEventStatsHistEntry 28 }

cfprApAdaptorFcIfEventStatsHistLossOfSyncCountDeltaMin OBJECT-TYPE
    SYNTAX       Unsigned64
    MAX-ACCESS   read-only
    STATUS       current
    DESCRIPTION
        "Cisco Firepower adaptor:FcIfEventStatsHist:lossOfSyncCountDeltaMi
        n managed object property"
    ::= { cfprApAdaptorFcIfEventStatsHistEntry 29 }

cfprApAdaptorFcIfEventStatsHistMostRecent OBJECT-TYPE
    SYNTAX       TruthValue
    MAX-ACCESS   read-only
    STATUS       current
    DESCRIPTION
        "Cisco Firepower adaptor:FcIfEventStatsHist:mostRecent
        managed object property"
    ::= { cfprApAdaptorFcIfEventStatsHistEntry 30 }

cfprApAdaptorFcIfEventStatsHistNOSCount OBJECT-TYPE
    SYNTAX       Unsigned64
    MAX-ACCESS   read-only
    STATUS       current
    DESCRIPTION
        "Cisco Firepower adaptor:FcIfEventStatsHist:nOSCount
        managed object property"
    ::= { cfprApAdaptorFcIfEventStatsHistEntry 31 }

cfprApAdaptorFcIfEventStatsHistNOSCountDelta OBJECT-TYPE
    SYNTAX       Unsigned64
    MAX-ACCESS   read-only
    STATUS       current
    DESCRIPTION
        "Cisco Firepower adaptor:FcIfEventStatsHist:nOSCountDelta
        managed object property"
    ::= { cfprApAdaptorFcIfEventStatsHistEntry 32 }

cfprApAdaptorFcIfEventStatsHistNOSCountDeltaAvg OBJECT-TYPE
    SYNTAX       Unsigned64
    MAX-ACCESS   read-only
    STATUS       current
    DESCRIPTION
        "Cisco Firepower adaptor:FcIfEventStatsHist:nOSCountDeltaAvg
        managed object property"
    ::= { cfprApAdaptorFcIfEventStatsHistEntry 33 }

cfprApAdaptorFcIfEventStatsHistNOSCountDeltaMax OBJECT-TYPE
    SYNTAX       Unsigned64
    MAX-ACCESS   read-only
    STATUS       current
    DESCRIPTION
        "Cisco Firepower adaptor:FcIfEventStatsHist:nOSCountDeltaMax
        managed object property"
    ::= { cfprApAdaptorFcIfEventStatsHistEntry 34 }

cfprApAdaptorFcIfEventStatsHistNOSCountDeltaMin OBJECT-TYPE
    SYNTAX       Unsigned64
    MAX-ACCESS   read-only
    STATUS       current
    DESCRIPTION
        "Cisco Firepower adaptor:FcIfEventStatsHist:nOSCountDeltaMin
        managed object property"
    ::= { cfprApAdaptorFcIfEventStatsHistEntry 35 }

cfprApAdaptorFcIfEventStatsHistSecondsSinceLastReset OBJECT-TYPE
    SYNTAX       Unsigned64
    MAX-ACCESS   read-only
    STATUS       current
    DESCRIPTION
        "Cisco Firepower adaptor:FcIfEventStatsHist:secondsSinceLastReset
        managed object property"
    ::= { cfprApAdaptorFcIfEventStatsHistEntry 36 }

cfprApAdaptorFcIfEventStatsHistSecondsSinceLastResetDelta OBJECT-TYPE
    SYNTAX       Unsigned64
    MAX-ACCESS   read-only
    STATUS       current
    DESCRIPTION
        "Cisco Firepower adaptor:FcIfEventStatsHist:secondsSinceLastResetD
        elta managed object property"
    ::= { cfprApAdaptorFcIfEventStatsHistEntry 37 }

cfprApAdaptorFcIfEventStatsHistSecondsSinceLastResetDeltaAvg OBJECT-TYPE
    SYNTAX       Unsigned64
    MAX-ACCESS   read-only
    STATUS       current
    DESCRIPTION
        "Cisco Firepower adaptor:FcIfEventStatsHist:secondsSinceLastResetD
        eltaAvg managed object property"
    ::= { cfprApAdaptorFcIfEventStatsHistEntry 38 }

cfprApAdaptorFcIfEventStatsHistSecondsSinceLastResetDeltaMax OBJECT-TYPE
    SYNTAX       Unsigned64
    MAX-ACCESS   read-only
    STATUS       current
    DESCRIPTION
        "Cisco Firepower adaptor:FcIfEventStatsHist:secondsSinceLastResetD
        eltaMax managed object property"
    ::= { cfprApAdaptorFcIfEventStatsHistEntry 39 }

cfprApAdaptorFcIfEventStatsHistSecondsSinceLastResetDeltaMin OBJECT-TYPE
    SYNTAX       Unsigned64
    MAX-ACCESS   read-only
    STATUS       current
    DESCRIPTION
        "Cisco Firepower adaptor:FcIfEventStatsHist:secondsSinceLastResetD
        eltaMin managed object property"
    ::= { cfprApAdaptorFcIfEventStatsHistEntry 40 }

cfprApAdaptorFcIfEventStatsHistSeqProtocolErrCount OBJECT-TYPE
    SYNTAX       Unsigned64
    MAX-ACCESS   read-only
    STATUS       current
    DESCRIPTION
        "Cisco Firepower adaptor:FcIfEventStatsHist:seqProtocolErrCount
        managed object property"
    ::= { cfprApAdaptorFcIfEventStatsHistEntry 41 }

cfprApAdaptorFcIfEventStatsHistSeqProtocolErrCountDelta OBJECT-TYPE
    SYNTAX       Unsigned64
    MAX-ACCESS   read-only
    STATUS       current
    DESCRIPTION
        "Cisco Firepower adaptor:FcIfEventStatsHist:seqProtocolErrCountDel
        ta managed object property"
    ::= { cfprApAdaptorFcIfEventStatsHistEntry 42 }

cfprApAdaptorFcIfEventStatsHistSeqProtocolErrCountDeltaAvg OBJECT-TYPE
    SYNTAX       Unsigned64
    MAX-ACCESS   read-only
    STATUS       current
    DESCRIPTION
        "Cisco Firepower adaptor:FcIfEventStatsHist:seqProtocolErrCountDel
        taAvg managed object property"
    ::= { cfprApAdaptorFcIfEventStatsHistEntry 43 }

cfprApAdaptorFcIfEventStatsHistSeqProtocolErrCountDeltaMax OBJECT-TYPE
    SYNTAX       Unsigned64
    MAX-ACCESS   read-only
    STATUS       current
    DESCRIPTION
        "Cisco Firepower adaptor:FcIfEventStatsHist:seqProtocolErrCountDel
        taMax managed object property"
    ::= { cfprApAdaptorFcIfEventStatsHistEntry 44 }

cfprApAdaptorFcIfEventStatsHistSeqProtocolErrCountDeltaMin OBJECT-TYPE
    SYNTAX       Unsigned64
    MAX-ACCESS   read-only
    STATUS       current
    DESCRIPTION
        "Cisco Firepower adaptor:FcIfEventStatsHist:seqProtocolErrCountDel
        taMin managed object property"
    ::= { cfprApAdaptorFcIfEventStatsHistEntry 45 }

cfprApAdaptorFcIfEventStatsHistSuspect OBJECT-TYPE
    SYNTAX       TruthValue
    MAX-ACCESS   read-only
    STATUS       current
    DESCRIPTION
        "Cisco Firepower adaptor:FcIfEventStatsHist:suspect
        managed object property"
    ::= { cfprApAdaptorFcIfEventStatsHistEntry 46 }

cfprApAdaptorFcIfEventStatsHistThresholded OBJECT-TYPE
    SYNTAX       CfprApAdaptorFcIfEventStatsHistThresholded
    MAX-ACCESS   read-only
    STATUS       current
    DESCRIPTION
        "Cisco Firepower adaptor:FcIfEventStatsHist:thresholded
        managed object property"
    ::= { cfprApAdaptorFcIfEventStatsHistEntry 47 }

cfprApAdaptorFcIfEventStatsHistTimeCollected OBJECT-TYPE
    SYNTAX       DateAndTime
    MAX-ACCESS   read-only
    STATUS       current
    DESCRIPTION
        "Cisco Firepower adaptor:FcIfEventStatsHist:timeCollected
        managed object property"
    ::= { cfprApAdaptorFcIfEventStatsHistEntry 48 }

cfprApAdaptorFcIfFC4StatsTable OBJECT-TYPE
    SYNTAX           SEQUENCE OF CfprApAdaptorFcIfFC4StatsEntry
    MAX-ACCESS       not-accessible
    STATUS           current
    DESCRIPTION
        "Cisco Firepower adaptor:FcIfFC4Stats managed object table"
    ::= { cfprApAdaptorObjects 40 }

cfprApAdaptorFcIfFC4StatsEntry OBJECT-TYPE
    SYNTAX           CfprApAdaptorFcIfFC4StatsEntry
    MAX-ACCESS       not-accessible
    STATUS           current
    DESCRIPTION
        "Entry for the cfprApAdaptorFcIfFC4StatsTable table."
    INDEX { cfprApAdaptorFcIfFC4StatsInstanceId }
    ::= { cfprApAdaptorFcIfFC4StatsTable 1 }

CfprApAdaptorFcIfFC4StatsEntry ::= SEQUENCE {
    cfprApAdaptorFcIfFC4StatsInstanceId                              CfprApManagedObjectId,
    cfprApAdaptorFcIfFC4StatsDn                                      CfprApManagedObjectDn,
    cfprApAdaptorFcIfFC4StatsRn                                      SnmpAdminString,
    cfprApAdaptorFcIfFC4StatsControlRequests                         Unsigned64,
    cfprApAdaptorFcIfFC4StatsControlRequestsDelta                    Counter64,
    cfprApAdaptorFcIfFC4StatsControlRequestsDeltaAvg                 Unsigned64,
    cfprApAdaptorFcIfFC4StatsControlRequestsDeltaMax                 Unsigned64,
    cfprApAdaptorFcIfFC4StatsControlRequestsDeltaMin                 Unsigned64,
    cfprApAdaptorFcIfFC4StatsInputMegabytes                          Unsigned64,
    cfprApAdaptorFcIfFC4StatsInputMegabytesDelta                     Counter64,
    cfprApAdaptorFcIfFC4StatsInputMegabytesDeltaAvg                  Unsigned64,
    cfprApAdaptorFcIfFC4StatsInputMegabytesDeltaMax                  Unsigned64,
    cfprApAdaptorFcIfFC4StatsInputMegabytesDeltaMin                  Unsigned64,
    cfprApAdaptorFcIfFC4StatsInputRequests                           Unsigned64,
    cfprApAdaptorFcIfFC4StatsInputRequestsDelta                      Counter64,
    cfprApAdaptorFcIfFC4StatsInputRequestsDeltaAvg                   Unsigned64,
    cfprApAdaptorFcIfFC4StatsInputRequestsDeltaMax                   Unsigned64,
    cfprApAdaptorFcIfFC4StatsInputRequestsDeltaMin                   Unsigned64,
    cfprApAdaptorFcIfFC4StatsIntervals                               Gauge32,
    cfprApAdaptorFcIfFC4StatsOutputMegabytes                         Unsigned64,
    cfprApAdaptorFcIfFC4StatsOutputMegabytesDelta                    Counter64,
    cfprApAdaptorFcIfFC4StatsOutputMegabytesDeltaAvg                 Unsigned64,
    cfprApAdaptorFcIfFC4StatsOutputMegabytesDeltaMax                 Unsigned64,
    cfprApAdaptorFcIfFC4StatsOutputMegabytesDeltaMin                 Unsigned64,
    cfprApAdaptorFcIfFC4StatsOutputRequests                          Unsigned64,
    cfprApAdaptorFcIfFC4StatsOutputRequestsDelta                     Counter64,
    cfprApAdaptorFcIfFC4StatsOutputRequestsDeltaAvg                  Unsigned64,
    cfprApAdaptorFcIfFC4StatsOutputRequestsDeltaMax                  Unsigned64,
    cfprApAdaptorFcIfFC4StatsOutputRequestsDeltaMin                  Unsigned64,
    cfprApAdaptorFcIfFC4StatsSuspect                                 TruthValue,
    cfprApAdaptorFcIfFC4StatsThresholded                             CfprApAdaptorFcIfFC4StatsThresholded,
    cfprApAdaptorFcIfFC4StatsTimeCollected                           DateAndTime,
    cfprApAdaptorFcIfFC4StatsUpdate                                  Gauge32
}

cfprApAdaptorFcIfFC4StatsInstanceId OBJECT-TYPE
    SYNTAX       CfprApManagedObjectId
    MAX-ACCESS   not-accessible
    STATUS       current
    DESCRIPTION
        "Instance identifier of the managed object."
    ::= { cfprApAdaptorFcIfFC4StatsEntry 1 }

cfprApAdaptorFcIfFC4StatsDn OBJECT-TYPE
    SYNTAX       CfprApManagedObjectDn
    MAX-ACCESS   read-only
    STATUS       current
    DESCRIPTION
        "Cisco Firepower adaptor:FcIfFC4Stats:dn managed object property"
    ::= { cfprApAdaptorFcIfFC4StatsEntry 2 }

cfprApAdaptorFcIfFC4StatsRn OBJECT-TYPE
    SYNTAX       SnmpAdminString
    MAX-ACCESS   read-only
    STATUS       current
    DESCRIPTION
        "Cisco Firepower adaptor:FcIfFC4Stats:rn managed object property"
    ::= { cfprApAdaptorFcIfFC4StatsEntry 3 }

cfprApAdaptorFcIfFC4StatsControlRequests OBJECT-TYPE
    SYNTAX       Unsigned64
    MAX-ACCESS   read-only
    STATUS       current
    DESCRIPTION
        "Cisco Firepower adaptor:FcIfFC4Stats:controlRequests
        managed object property"
    ::= { cfprApAdaptorFcIfFC4StatsEntry 4 }

cfprApAdaptorFcIfFC4StatsControlRequestsDelta OBJECT-TYPE
    SYNTAX       Counter64
    MAX-ACCESS   read-only
    STATUS       current
    DESCRIPTION
        "Cisco Firepower adaptor:FcIfFC4Stats:controlRequestsDelta
        managed object property"
    ::= { cfprApAdaptorFcIfFC4StatsEntry 5 }

cfprApAdaptorFcIfFC4StatsControlRequestsDeltaAvg OBJECT-TYPE
    SYNTAX       Unsigned64
    MAX-ACCESS   read-only
    STATUS       current
    DESCRIPTION
        "Cisco Firepower adaptor:FcIfFC4Stats:controlRequestsDeltaAvg
        managed object property"
    ::= { cfprApAdaptorFcIfFC4StatsEntry 6 }

cfprApAdaptorFcIfFC4StatsControlRequestsDeltaMax OBJECT-TYPE
    SYNTAX       Unsigned64
    MAX-ACCESS   read-only
    STATUS       current
    DESCRIPTION
        "Cisco Firepower adaptor:FcIfFC4Stats:controlRequestsDeltaMax
        managed object property"
    ::= { cfprApAdaptorFcIfFC4StatsEntry 7 }

cfprApAdaptorFcIfFC4StatsControlRequestsDeltaMin OBJECT-TYPE
    SYNTAX       Unsigned64
    MAX-ACCESS   read-only
    STATUS       current
    DESCRIPTION
        "Cisco Firepower adaptor:FcIfFC4Stats:controlRequestsDeltaMin
        managed object property"
    ::= { cfprApAdaptorFcIfFC4StatsEntry 8 }

cfprApAdaptorFcIfFC4StatsInputMegabytes OBJECT-TYPE
    SYNTAX       Unsigned64
    MAX-ACCESS   read-only
    STATUS       current
    DESCRIPTION
        "Cisco Firepower adaptor:FcIfFC4Stats:inputMegabytes
        managed object property"
    ::= { cfprApAdaptorFcIfFC4StatsEntry 9 }

cfprApAdaptorFcIfFC4StatsInputMegabytesDelta OBJECT-TYPE
    SYNTAX       Counter64
    MAX-ACCESS   read-only
    STATUS       current
    DESCRIPTION
        "Cisco Firepower adaptor:FcIfFC4Stats:inputMegabytesDelta
        managed object property"
    ::= { cfprApAdaptorFcIfFC4StatsEntry 10 }

cfprApAdaptorFcIfFC4StatsInputMegabytesDeltaAvg OBJECT-TYPE
    SYNTAX       Unsigned64
    MAX-ACCESS   read-only
    STATUS       current
    DESCRIPTION
        "Cisco Firepower adaptor:FcIfFC4Stats:inputMegabytesDeltaAvg
        managed object property"
    ::= { cfprApAdaptorFcIfFC4StatsEntry 11 }

cfprApAdaptorFcIfFC4StatsInputMegabytesDeltaMax OBJECT-TYPE
    SYNTAX       Unsigned64
    MAX-ACCESS   read-only
    STATUS       current
    DESCRIPTION
        "Cisco Firepower adaptor:FcIfFC4Stats:inputMegabytesDeltaMax
        managed object property"
    ::= { cfprApAdaptorFcIfFC4StatsEntry 12 }

cfprApAdaptorFcIfFC4StatsInputMegabytesDeltaMin OBJECT-TYPE
    SYNTAX       Unsigned64
    MAX-ACCESS   read-only
    STATUS       current
    DESCRIPTION
        "Cisco Firepower adaptor:FcIfFC4Stats:inputMegabytesDeltaMin
        managed object property"
    ::= { cfprApAdaptorFcIfFC4StatsEntry 13 }

cfprApAdaptorFcIfFC4StatsInputRequests OBJECT-TYPE
    SYNTAX       Unsigned64
    MAX-ACCESS   read-only
    STATUS       current
    DESCRIPTION
        "Cisco Firepower adaptor:FcIfFC4Stats:inputRequests
        managed object property"
    ::= { cfprApAdaptorFcIfFC4StatsEntry 14 }

cfprApAdaptorFcIfFC4StatsInputRequestsDelta OBJECT-TYPE
    SYNTAX       Counter64
    MAX-ACCESS   read-only
    STATUS       current
    DESCRIPTION
        "Cisco Firepower adaptor:FcIfFC4Stats:inputRequestsDelta
        managed object property"
    ::= { cfprApAdaptorFcIfFC4StatsEntry 15 }

cfprApAdaptorFcIfFC4StatsInputRequestsDeltaAvg OBJECT-TYPE
    SYNTAX       Unsigned64
    MAX-ACCESS   read-only
    STATUS       current
    DESCRIPTION
        "Cisco Firepower adaptor:FcIfFC4Stats:inputRequestsDeltaAvg
        managed object property"
    ::= { cfprApAdaptorFcIfFC4StatsEntry 16 }

cfprApAdaptorFcIfFC4StatsInputRequestsDeltaMax OBJECT-TYPE
    SYNTAX       Unsigned64
    MAX-ACCESS   read-only
    STATUS       current
    DESCRIPTION
        "Cisco Firepower adaptor:FcIfFC4Stats:inputRequestsDeltaMax
        managed object property"
    ::= { cfprApAdaptorFcIfFC4StatsEntry 17 }

cfprApAdaptorFcIfFC4StatsInputRequestsDeltaMin OBJECT-TYPE
    SYNTAX       Unsigned64
    MAX-ACCESS   read-only
    STATUS       current
    DESCRIPTION
        "Cisco Firepower adaptor:FcIfFC4Stats:inputRequestsDeltaMin
        managed object property"
    ::= { cfprApAdaptorFcIfFC4StatsEntry 18 }

cfprApAdaptorFcIfFC4StatsIntervals OBJECT-TYPE
    SYNTAX       Gauge32
    MAX-ACCESS   read-only
    STATUS       current
    DESCRIPTION
        "Cisco Firepower adaptor:FcIfFC4Stats:intervals
        managed object property"
    ::= { cfprApAdaptorFcIfFC4StatsEntry 19 }

cfprApAdaptorFcIfFC4StatsOutputMegabytes OBJECT-TYPE
    SYNTAX       Unsigned64
    MAX-ACCESS   read-only
    STATUS       current
    DESCRIPTION
        "Cisco Firepower adaptor:FcIfFC4Stats:outputMegabytes
        managed object property"
    ::= { cfprApAdaptorFcIfFC4StatsEntry 20 }

cfprApAdaptorFcIfFC4StatsOutputMegabytesDelta OBJECT-TYPE
    SYNTAX       Counter64
    MAX-ACCESS   read-only
    STATUS       current
    DESCRIPTION
        "Cisco Firepower adaptor:FcIfFC4Stats:outputMegabytesDelta
        managed object property"
    ::= { cfprApAdaptorFcIfFC4StatsEntry 21 }

cfprApAdaptorFcIfFC4StatsOutputMegabytesDeltaAvg OBJECT-TYPE
    SYNTAX       Unsigned64
    MAX-ACCESS   read-only
    STATUS       current
    DESCRIPTION
        "Cisco Firepower adaptor:FcIfFC4Stats:outputMegabytesDeltaAvg
        managed object property"
    ::= { cfprApAdaptorFcIfFC4StatsEntry 22 }

cfprApAdaptorFcIfFC4StatsOutputMegabytesDeltaMax OBJECT-TYPE
    SYNTAX       Unsigned64
    MAX-ACCESS   read-only
    STATUS       current
    DESCRIPTION
        "Cisco Firepower adaptor:FcIfFC4Stats:outputMegabytesDeltaMax
        managed object property"
    ::= { cfprApAdaptorFcIfFC4StatsEntry 23 }

cfprApAdaptorFcIfFC4StatsOutputMegabytesDeltaMin OBJECT-TYPE
    SYNTAX       Unsigned64
    MAX-ACCESS   read-only
    STATUS       current
    DESCRIPTION
        "Cisco Firepower adaptor:FcIfFC4Stats:outputMegabytesDeltaMin
        managed object property"
    ::= { cfprApAdaptorFcIfFC4StatsEntry 24 }

cfprApAdaptorFcIfFC4StatsOutputRequests OBJECT-TYPE
    SYNTAX       Unsigned64
    MAX-ACCESS   read-only
    STATUS       current
    DESCRIPTION
        "Cisco Firepower adaptor:FcIfFC4Stats:outputRequests
        managed object property"
    ::= { cfprApAdaptorFcIfFC4StatsEntry 25 }

cfprApAdaptorFcIfFC4StatsOutputRequestsDelta OBJECT-TYPE
    SYNTAX       Counter64
    MAX-ACCESS   read-only
    STATUS       current
    DESCRIPTION
        "Cisco Firepower adaptor:FcIfFC4Stats:outputRequestsDelta
        managed object property"
    ::= { cfprApAdaptorFcIfFC4StatsEntry 26 }

cfprApAdaptorFcIfFC4StatsOutputRequestsDeltaAvg OBJECT-TYPE
    SYNTAX       Unsigned64
    MAX-ACCESS   read-only
    STATUS       current
    DESCRIPTION
        "Cisco Firepower adaptor:FcIfFC4Stats:outputRequestsDeltaAvg
        managed object property"
    ::= { cfprApAdaptorFcIfFC4StatsEntry 27 }

cfprApAdaptorFcIfFC4StatsOutputRequestsDeltaMax OBJECT-TYPE
    SYNTAX       Unsigned64
    MAX-ACCESS   read-only
    STATUS       current
    DESCRIPTION
        "Cisco Firepower adaptor:FcIfFC4Stats:outputRequestsDeltaMax
        managed object property"
    ::= { cfprApAdaptorFcIfFC4StatsEntry 28 }

cfprApAdaptorFcIfFC4StatsOutputRequestsDeltaMin OBJECT-TYPE
    SYNTAX       Unsigned64
    MAX-ACCESS   read-only
    STATUS       current
    DESCRIPTION
        "Cisco Firepower adaptor:FcIfFC4Stats:outputRequestsDeltaMin
        managed object property"
    ::= { cfprApAdaptorFcIfFC4StatsEntry 29 }

cfprApAdaptorFcIfFC4StatsSuspect OBJECT-TYPE
    SYNTAX       TruthValue
    MAX-ACCESS   read-only
    STATUS       current
    DESCRIPTION
        "Cisco Firepower adaptor:FcIfFC4Stats:suspect managed
        object property"
    ::= { cfprApAdaptorFcIfFC4StatsEntry 30 }

cfprApAdaptorFcIfFC4StatsThresholded OBJECT-TYPE
    SYNTAX       CfprApAdaptorFcIfFC4StatsThresholded
    MAX-ACCESS   read-only
    STATUS       current
    DESCRIPTION
        "Cisco Firepower adaptor:FcIfFC4Stats:thresholded
        managed object property"
    ::= { cfprApAdaptorFcIfFC4StatsEntry 31 }

cfprApAdaptorFcIfFC4StatsTimeCollected OBJECT-TYPE
    SYNTAX       DateAndTime
    MAX-ACCESS   read-only
    STATUS       current
    DESCRIPTION
        "Cisco Firepower adaptor:FcIfFC4Stats:timeCollected
        managed object property"
    ::= { cfprApAdaptorFcIfFC4StatsEntry 32 }

cfprApAdaptorFcIfFC4StatsUpdate OBJECT-TYPE
    SYNTAX       Gauge32
    MAX-ACCESS   read-only
    STATUS       current
    DESCRIPTION
        "Cisco Firepower adaptor:FcIfFC4Stats:update managed
        object property"
    ::= { cfprApAdaptorFcIfFC4StatsEntry 33 }

cfprApAdaptorFcIfFC4StatsHistTable OBJECT-TYPE
    SYNTAX           SEQUENCE OF CfprApAdaptorFcIfFC4StatsHistEntry
    MAX-ACCESS       not-accessible
    STATUS           current
    DESCRIPTION
        "Cisco Firepower adaptor:FcIfFC4StatsHist managed object table"
    ::= { cfprApAdaptorObjects 41 }

cfprApAdaptorFcIfFC4StatsHistEntry OBJECT-TYPE
    SYNTAX           CfprApAdaptorFcIfFC4StatsHistEntry
    MAX-ACCESS       not-accessible
    STATUS           current
    DESCRIPTION
        "Entry for the cfprApAdaptorFcIfFC4StatsHistTable table."
    INDEX { cfprApAdaptorFcIfFC4StatsHistInstanceId }
    ::= { cfprApAdaptorFcIfFC4StatsHistTable 1 }

CfprApAdaptorFcIfFC4StatsHistEntry ::= SEQUENCE {
    cfprApAdaptorFcIfFC4StatsHistInstanceId                          CfprApManagedObjectId,
    cfprApAdaptorFcIfFC4StatsHistDn                                  CfprApManagedObjectDn,
    cfprApAdaptorFcIfFC4StatsHistRn                                  SnmpAdminString,
    cfprApAdaptorFcIfFC4StatsHistControlRequests                     Unsigned64,
    cfprApAdaptorFcIfFC4StatsHistControlRequestsDelta                Unsigned64,
    cfprApAdaptorFcIfFC4StatsHistControlRequestsDeltaAvg             Unsigned64,
    cfprApAdaptorFcIfFC4StatsHistControlRequestsDeltaMax             Unsigned64,
    cfprApAdaptorFcIfFC4StatsHistControlRequestsDeltaMin             Unsigned64,
    cfprApAdaptorFcIfFC4StatsHistId                                  Unsigned64,
    cfprApAdaptorFcIfFC4StatsHistInputMegabytes                      Unsigned64,
    cfprApAdaptorFcIfFC4StatsHistInputMegabytesDelta                 Unsigned64,
    cfprApAdaptorFcIfFC4StatsHistInputMegabytesDeltaAvg              Unsigned64,
    cfprApAdaptorFcIfFC4StatsHistInputMegabytesDeltaMax              Unsigned64,
    cfprApAdaptorFcIfFC4StatsHistInputMegabytesDeltaMin              Unsigned64,
    cfprApAdaptorFcIfFC4StatsHistInputRequests                       Unsigned64,
    cfprApAdaptorFcIfFC4StatsHistInputRequestsDelta                  Unsigned64,
    cfprApAdaptorFcIfFC4StatsHistInputRequestsDeltaAvg               Unsigned64,
    cfprApAdaptorFcIfFC4StatsHistInputRequestsDeltaMax               Unsigned64,
    cfprApAdaptorFcIfFC4StatsHistInputRequestsDeltaMin               Unsigned64,
    cfprApAdaptorFcIfFC4StatsHistMostRecent                          TruthValue,
    cfprApAdaptorFcIfFC4StatsHistOutputMegabytes                     Unsigned64,
    cfprApAdaptorFcIfFC4StatsHistOutputMegabytesDelta                Unsigned64,
    cfprApAdaptorFcIfFC4StatsHistOutputMegabytesDeltaAvg             Unsigned64,
    cfprApAdaptorFcIfFC4StatsHistOutputMegabytesDeltaMax             Unsigned64,
    cfprApAdaptorFcIfFC4StatsHistOutputMegabytesDeltaMin             Unsigned64,
    cfprApAdaptorFcIfFC4StatsHistOutputRequests                      Unsigned64,
    cfprApAdaptorFcIfFC4StatsHistOutputRequestsDelta                 Unsigned64,
    cfprApAdaptorFcIfFC4StatsHistOutputRequestsDeltaAvg              Unsigned64,
    cfprApAdaptorFcIfFC4StatsHistOutputRequestsDeltaMax              Unsigned64,
    cfprApAdaptorFcIfFC4StatsHistOutputRequestsDeltaMin              Unsigned64,
    cfprApAdaptorFcIfFC4StatsHistSuspect                             TruthValue,
    cfprApAdaptorFcIfFC4StatsHistThresholded                         CfprApAdaptorFcIfFC4StatsHistThresholded,
    cfprApAdaptorFcIfFC4StatsHistTimeCollected                       DateAndTime
}

cfprApAdaptorFcIfFC4StatsHistInstanceId OBJECT-TYPE
    SYNTAX       CfprApManagedObjectId
    MAX-ACCESS   not-accessible
    STATUS       current
    DESCRIPTION
        "Instance identifier of the managed object."
    ::= { cfprApAdaptorFcIfFC4StatsHistEntry 1 }

cfprApAdaptorFcIfFC4StatsHistDn OBJECT-TYPE
    SYNTAX       CfprApManagedObjectDn
    MAX-ACCESS   read-only
    STATUS       current
    DESCRIPTION
        "Cisco Firepower adaptor:FcIfFC4StatsHist:dn managed
        object property"
    ::= { cfprApAdaptorFcIfFC4StatsHistEntry 2 }

cfprApAdaptorFcIfFC4StatsHistRn OBJECT-TYPE
    SYNTAX       SnmpAdminString
    MAX-ACCESS   read-only
    STATUS       current
    DESCRIPTION
        "Cisco Firepower adaptor:FcIfFC4StatsHist:rn managed
        object property"
    ::= { cfprApAdaptorFcIfFC4StatsHistEntry 3 }

cfprApAdaptorFcIfFC4StatsHistControlRequests OBJECT-TYPE
    SYNTAX       Unsigned64
    MAX-ACCESS   read-only
    STATUS       current
    DESCRIPTION
        "Cisco Firepower adaptor:FcIfFC4StatsHist:controlRequests
        managed object property"
    ::= { cfprApAdaptorFcIfFC4StatsHistEntry 4 }

cfprApAdaptorFcIfFC4StatsHistControlRequestsDelta OBJECT-TYPE
    SYNTAX       Unsigned64
    MAX-ACCESS   read-only
    STATUS       current
    DESCRIPTION
        "Cisco Firepower adaptor:FcIfFC4StatsHist:controlRequestsDelta
        managed object property"
    ::= { cfprApAdaptorFcIfFC4StatsHistEntry 5 }

cfprApAdaptorFcIfFC4StatsHistControlRequestsDeltaAvg OBJECT-TYPE
    SYNTAX       Unsigned64
    MAX-ACCESS   read-only
    STATUS       current
    DESCRIPTION
        "Cisco Firepower adaptor:FcIfFC4StatsHist:controlRequestsDeltaAvg
        managed object property"
    ::= { cfprApAdaptorFcIfFC4StatsHistEntry 6 }

cfprApAdaptorFcIfFC4StatsHistControlRequestsDeltaMax OBJECT-TYPE
    SYNTAX       Unsigned64
    MAX-ACCESS   read-only
    STATUS       current
    DESCRIPTION
        "Cisco Firepower adaptor:FcIfFC4StatsHist:controlRequestsDeltaMax
        managed object property"
    ::= { cfprApAdaptorFcIfFC4StatsHistEntry 7 }

cfprApAdaptorFcIfFC4StatsHistControlRequestsDeltaMin OBJECT-TYPE
    SYNTAX       Unsigned64
    MAX-ACCESS   read-only
    STATUS       current
    DESCRIPTION
        "Cisco Firepower adaptor:FcIfFC4StatsHist:controlRequestsDeltaMin
        managed object property"
    ::= { cfprApAdaptorFcIfFC4StatsHistEntry 8 }

cfprApAdaptorFcIfFC4StatsHistId OBJECT-TYPE
    SYNTAX       Unsigned64
    MAX-ACCESS   read-only
    STATUS       current
    DESCRIPTION
        "Cisco Firepower adaptor:FcIfFC4StatsHist:id managed
        object property"
    ::= { cfprApAdaptorFcIfFC4StatsHistEntry 9 }

cfprApAdaptorFcIfFC4StatsHistInputMegabytes OBJECT-TYPE
    SYNTAX       Unsigned64
    MAX-ACCESS   read-only
    STATUS       current
    DESCRIPTION
        "Cisco Firepower adaptor:FcIfFC4StatsHist:inputMegabytes
        managed object property"
    ::= { cfprApAdaptorFcIfFC4StatsHistEntry 10 }

cfprApAdaptorFcIfFC4StatsHistInputMegabytesDelta OBJECT-TYPE
    SYNTAX       Unsigned64
    MAX-ACCESS   read-only
    STATUS       current
    DESCRIPTION
        "Cisco Firepower adaptor:FcIfFC4StatsHist:inputMegabytesDelta
        managed object property"
    ::= { cfprApAdaptorFcIfFC4StatsHistEntry 11 }

cfprApAdaptorFcIfFC4StatsHistInputMegabytesDeltaAvg OBJECT-TYPE
    SYNTAX       Unsigned64
    MAX-ACCESS   read-only
    STATUS       current
    DESCRIPTION
        "Cisco Firepower adaptor:FcIfFC4StatsHist:inputMegabytesDeltaAvg
        managed object property"
    ::= { cfprApAdaptorFcIfFC4StatsHistEntry 12 }

cfprApAdaptorFcIfFC4StatsHistInputMegabytesDeltaMax OBJECT-TYPE
    SYNTAX       Unsigned64
    MAX-ACCESS   read-only
    STATUS       current
    DESCRIPTION
        "Cisco Firepower adaptor:FcIfFC4StatsHist:inputMegabytesDeltaMax
        managed object property"
    ::= { cfprApAdaptorFcIfFC4StatsHistEntry 13 }

cfprApAdaptorFcIfFC4StatsHistInputMegabytesDeltaMin OBJECT-TYPE
    SYNTAX       Unsigned64
    MAX-ACCESS   read-only
    STATUS       current
    DESCRIPTION
        "Cisco Firepower adaptor:FcIfFC4StatsHist:inputMegabytesDeltaMin
        managed object property"
    ::= { cfprApAdaptorFcIfFC4StatsHistEntry 14 }

cfprApAdaptorFcIfFC4StatsHistInputRequests OBJECT-TYPE
    SYNTAX       Unsigned64
    MAX-ACCESS   read-only
    STATUS       current
    DESCRIPTION
        "Cisco Firepower adaptor:FcIfFC4StatsHist:inputRequests
        managed object property"
    ::= { cfprApAdaptorFcIfFC4StatsHistEntry 15 }

cfprApAdaptorFcIfFC4StatsHistInputRequestsDelta OBJECT-TYPE
    SYNTAX       Unsigned64
    MAX-ACCESS   read-only
    STATUS       current
    DESCRIPTION
        "Cisco Firepower adaptor:FcIfFC4StatsHist:inputRequestsDelta
        managed object property"
    ::= { cfprApAdaptorFcIfFC4StatsHistEntry 16 }

cfprApAdaptorFcIfFC4StatsHistInputRequestsDeltaAvg OBJECT-TYPE
    SYNTAX       Unsigned64
    MAX-ACCESS   read-only
    STATUS       current
    DESCRIPTION
        "Cisco Firepower adaptor:FcIfFC4StatsHist:inputRequestsDeltaAvg
        managed object property"
    ::= { cfprApAdaptorFcIfFC4StatsHistEntry 17 }

cfprApAdaptorFcIfFC4StatsHistInputRequestsDeltaMax OBJECT-TYPE
    SYNTAX       Unsigned64
    MAX-ACCESS   read-only
    STATUS       current
    DESCRIPTION
        "Cisco Firepower adaptor:FcIfFC4StatsHist:inputRequestsDeltaMax
        managed object property"
    ::= { cfprApAdaptorFcIfFC4StatsHistEntry 18 }

cfprApAdaptorFcIfFC4StatsHistInputRequestsDeltaMin OBJECT-TYPE
    SYNTAX       Unsigned64
    MAX-ACCESS   read-only
    STATUS       current
    DESCRIPTION
        "Cisco Firepower adaptor:FcIfFC4StatsHist:inputRequestsDeltaMin
        managed object property"
    ::= { cfprApAdaptorFcIfFC4StatsHistEntry 19 }

cfprApAdaptorFcIfFC4StatsHistMostRecent OBJECT-TYPE
    SYNTAX       TruthValue
    MAX-ACCESS   read-only
    STATUS       current
    DESCRIPTION
        "Cisco Firepower adaptor:FcIfFC4StatsHist:mostRecent
        managed object property"
    ::= { cfprApAdaptorFcIfFC4StatsHistEntry 20 }

cfprApAdaptorFcIfFC4StatsHistOutputMegabytes OBJECT-TYPE
    SYNTAX       Unsigned64
    MAX-ACCESS   read-only
    STATUS       current
    DESCRIPTION
        "Cisco Firepower adaptor:FcIfFC4StatsHist:outputMegabytes
        managed object property"
    ::= { cfprApAdaptorFcIfFC4StatsHistEntry 21 }

cfprApAdaptorFcIfFC4StatsHistOutputMegabytesDelta OBJECT-TYPE
    SYNTAX       Unsigned64
    MAX-ACCESS   read-only
    STATUS       current
    DESCRIPTION
        "Cisco Firepower adaptor:FcIfFC4StatsHist:outputMegabytesDelta
        managed object property"
    ::= { cfprApAdaptorFcIfFC4StatsHistEntry 22 }

cfprApAdaptorFcIfFC4StatsHistOutputMegabytesDeltaAvg OBJECT-TYPE
    SYNTAX       Unsigned64
    MAX-ACCESS   read-only
    STATUS       current
    DESCRIPTION
        "Cisco Firepower adaptor:FcIfFC4StatsHist:outputMegabytesDeltaAvg
        managed object property"
    ::= { cfprApAdaptorFcIfFC4StatsHistEntry 23 }

cfprApAdaptorFcIfFC4StatsHistOutputMegabytesDeltaMax OBJECT-TYPE
    SYNTAX       Unsigned64
    MAX-ACCESS   read-only
    STATUS       current
    DESCRIPTION
        "Cisco Firepower adaptor:FcIfFC4StatsHist:outputMegabytesDeltaMax
        managed object property"
    ::= { cfprApAdaptorFcIfFC4StatsHistEntry 24 }

cfprApAdaptorFcIfFC4StatsHistOutputMegabytesDeltaMin OBJECT-TYPE
    SYNTAX       Unsigned64
    MAX-ACCESS   read-only
    STATUS       current
    DESCRIPTION
        "Cisco Firepower adaptor:FcIfFC4StatsHist:outputMegabytesDeltaMin
        managed object property"
    ::= { cfprApAdaptorFcIfFC4StatsHistEntry 25 }

cfprApAdaptorFcIfFC4StatsHistOutputRequests OBJECT-TYPE
    SYNTAX       Unsigned64
    MAX-ACCESS   read-only
    STATUS       current
    DESCRIPTION
        "Cisco Firepower adaptor:FcIfFC4StatsHist:outputRequests
        managed object property"
    ::= { cfprApAdaptorFcIfFC4StatsHistEntry 26 }

cfprApAdaptorFcIfFC4StatsHistOutputRequestsDelta OBJECT-TYPE
    SYNTAX       Unsigned64
    MAX-ACCESS   read-only
    STATUS       current
    DESCRIPTION
        "Cisco Firepower adaptor:FcIfFC4StatsHist:outputRequestsDelta
        managed object property"
    ::= { cfprApAdaptorFcIfFC4StatsHistEntry 27 }

cfprApAdaptorFcIfFC4StatsHistOutputRequestsDeltaAvg OBJECT-TYPE
    SYNTAX       Unsigned64
    MAX-ACCESS   read-only
    STATUS       current
    DESCRIPTION
        "Cisco Firepower adaptor:FcIfFC4StatsHist:outputRequestsDeltaAvg
        managed object property"
    ::= { cfprApAdaptorFcIfFC4StatsHistEntry 28 }

cfprApAdaptorFcIfFC4StatsHistOutputRequestsDeltaMax OBJECT-TYPE
    SYNTAX       Unsigned64
    MAX-ACCESS   read-only
    STATUS       current
    DESCRIPTION
        "Cisco Firepower adaptor:FcIfFC4StatsHist:outputRequestsDeltaMax
        managed object property"
    ::= { cfprApAdaptorFcIfFC4StatsHistEntry 29 }

cfprApAdaptorFcIfFC4StatsHistOutputRequestsDeltaMin OBJECT-TYPE
    SYNTAX       Unsigned64
    MAX-ACCESS   read-only
    STATUS       current
    DESCRIPTION
        "Cisco Firepower adaptor:FcIfFC4StatsHist:outputRequestsDeltaMin
        managed object property"
    ::= { cfprApAdaptorFcIfFC4StatsHistEntry 30 }

cfprApAdaptorFcIfFC4StatsHistSuspect OBJECT-TYPE
    SYNTAX       TruthValue
    MAX-ACCESS   read-only
    STATUS       current
    DESCRIPTION
        "Cisco Firepower adaptor:FcIfFC4StatsHist:suspect
        managed object property"
    ::= { cfprApAdaptorFcIfFC4StatsHistEntry 31 }

cfprApAdaptorFcIfFC4StatsHistThresholded OBJECT-TYPE
    SYNTAX       CfprApAdaptorFcIfFC4StatsHistThresholded
    MAX-ACCESS   read-only
    STATUS       current
    DESCRIPTION
        "Cisco Firepower adaptor:FcIfFC4StatsHist:thresholded
        managed object property"
    ::= { cfprApAdaptorFcIfFC4StatsHistEntry 32 }

cfprApAdaptorFcIfFC4StatsHistTimeCollected OBJECT-TYPE
    SYNTAX       DateAndTime
    MAX-ACCESS   read-only
    STATUS       current
    DESCRIPTION
        "Cisco Firepower adaptor:FcIfFC4StatsHist:timeCollected
        managed object property"
    ::= { cfprApAdaptorFcIfFC4StatsHistEntry 33 }

cfprApAdaptorFcIfFrameStatsTable OBJECT-TYPE
    SYNTAX           SEQUENCE OF CfprApAdaptorFcIfFrameStatsEntry
    MAX-ACCESS       not-accessible
    STATUS           current
    DESCRIPTION
        "Cisco Firepower adaptor:FcIfFrameStats managed object table"
    ::= { cfprApAdaptorObjects 42 }

cfprApAdaptorFcIfFrameStatsEntry OBJECT-TYPE
    SYNTAX           CfprApAdaptorFcIfFrameStatsEntry
    MAX-ACCESS       not-accessible
    STATUS           current
    DESCRIPTION
        "Entry for the cfprApAdaptorFcIfFrameStatsTable table."
    INDEX { cfprApAdaptorFcIfFrameStatsInstanceId }
    ::= { cfprApAdaptorFcIfFrameStatsTable 1 }

CfprApAdaptorFcIfFrameStatsEntry ::= SEQUENCE {
    cfprApAdaptorFcIfFrameStatsInstanceId                            CfprApManagedObjectId,
    cfprApAdaptorFcIfFrameStatsDn                                    CfprApManagedObjectDn,
    cfprApAdaptorFcIfFrameStatsRn                                    SnmpAdminString,
    cfprApAdaptorFcIfFrameStatsDumpedFrames                          Unsigned64,
    cfprApAdaptorFcIfFrameStatsDumpedFramesDelta                     Counter64,
    cfprApAdaptorFcIfFrameStatsDumpedFramesDeltaAvg                  Unsigned64,
    cfprApAdaptorFcIfFrameStatsDumpedFramesDeltaMax                  Unsigned64,
    cfprApAdaptorFcIfFrameStatsDumpedFramesDeltaMin                  Unsigned64,
    cfprApAdaptorFcIfFrameStatsErrorFrames                           Unsigned64,
    cfprApAdaptorFcIfFrameStatsErrorFramesDelta                      Counter64,
    cfprApAdaptorFcIfFrameStatsErrorFramesDeltaAvg                   Unsigned64,
    cfprApAdaptorFcIfFrameStatsErrorFramesDeltaMax                   Unsigned64,
    cfprApAdaptorFcIfFrameStatsErrorFramesDeltaMin                   Unsigned64,
    cfprApAdaptorFcIfFrameStatsIntervals                             Gauge32,
    cfprApAdaptorFcIfFrameStatsRxFrames                              Unsigned64,
    cfprApAdaptorFcIfFrameStatsRxFramesDelta                         Counter64,
    cfprApAdaptorFcIfFrameStatsRxFramesDeltaAvg                      Unsigned64,
    cfprApAdaptorFcIfFrameStatsRxFramesDeltaMax                      Unsigned64,
    cfprApAdaptorFcIfFrameStatsRxFramesDeltaMin                      Unsigned64,
    cfprApAdaptorFcIfFrameStatsSuspect                               TruthValue,
    cfprApAdaptorFcIfFrameStatsThresholded                           CfprApAdaptorFcIfFrameStatsThresholded,
    cfprApAdaptorFcIfFrameStatsTimeCollected                         DateAndTime,
    cfprApAdaptorFcIfFrameStatsTxFrames                              Unsigned64,
    cfprApAdaptorFcIfFrameStatsTxFramesDelta                         Counter64,
    cfprApAdaptorFcIfFrameStatsTxFramesDeltaAvg                      Unsigned64,
    cfprApAdaptorFcIfFrameStatsTxFramesDeltaMax                      Unsigned64,
    cfprApAdaptorFcIfFrameStatsTxFramesDeltaMin                      Unsigned64,
    cfprApAdaptorFcIfFrameStatsUpdate                                Gauge32
}

cfprApAdaptorFcIfFrameStatsInstanceId OBJECT-TYPE
    SYNTAX       CfprApManagedObjectId
    MAX-ACCESS   not-accessible
    STATUS       current
    DESCRIPTION
        "Instance identifier of the managed object."
    ::= { cfprApAdaptorFcIfFrameStatsEntry 1 }

cfprApAdaptorFcIfFrameStatsDn OBJECT-TYPE
    SYNTAX       CfprApManagedObjectDn
    MAX-ACCESS   read-only
    STATUS       current
    DESCRIPTION
        "Cisco Firepower adaptor:FcIfFrameStats:dn managed
        object property"
    ::= { cfprApAdaptorFcIfFrameStatsEntry 2 }

cfprApAdaptorFcIfFrameStatsRn OBJECT-TYPE
    SYNTAX       SnmpAdminString
    MAX-ACCESS   read-only
    STATUS       current
    DESCRIPTION
        "Cisco Firepower adaptor:FcIfFrameStats:rn managed
        object property"
    ::= { cfprApAdaptorFcIfFrameStatsEntry 3 }

cfprApAdaptorFcIfFrameStatsDumpedFrames OBJECT-TYPE
    SYNTAX       Unsigned64
    MAX-ACCESS   read-only
    STATUS       current
    DESCRIPTION
        "Cisco Firepower adaptor:FcIfFrameStats:dumpedFrames
        managed object property"
    ::= { cfprApAdaptorFcIfFrameStatsEntry 4 }

cfprApAdaptorFcIfFrameStatsDumpedFramesDelta OBJECT-TYPE
    SYNTAX       Counter64
    MAX-ACCESS   read-only
    STATUS       current
    DESCRIPTION
        "Cisco Firepower adaptor:FcIfFrameStats:dumpedFramesDelta
        managed object property"
    ::= { cfprApAdaptorFcIfFrameStatsEntry 5 }

cfprApAdaptorFcIfFrameStatsDumpedFramesDeltaAvg OBJECT-TYPE
    SYNTAX       Unsigned64
    MAX-ACCESS   read-only
    STATUS       current
    DESCRIPTION
        "Cisco Firepower adaptor:FcIfFrameStats:dumpedFramesDeltaAvg
        managed object property"
    ::= { cfprApAdaptorFcIfFrameStatsEntry 6 }

cfprApAdaptorFcIfFrameStatsDumpedFramesDeltaMax OBJECT-TYPE
    SYNTAX       Unsigned64
    MAX-ACCESS   read-only
    STATUS       current
    DESCRIPTION
        "Cisco Firepower adaptor:FcIfFrameStats:dumpedFramesDeltaMax
        managed object property"
    ::= { cfprApAdaptorFcIfFrameStatsEntry 7 }

cfprApAdaptorFcIfFrameStatsDumpedFramesDeltaMin OBJECT-TYPE
    SYNTAX       Unsigned64
    MAX-ACCESS   read-only
    STATUS       current
    DESCRIPTION
        "Cisco Firepower adaptor:FcIfFrameStats:dumpedFramesDeltaMin
        managed object property"
    ::= { cfprApAdaptorFcIfFrameStatsEntry 8 }

cfprApAdaptorFcIfFrameStatsErrorFrames OBJECT-TYPE
    SYNTAX       Unsigned64
    MAX-ACCESS   read-only
    STATUS       current
    DESCRIPTION
        "Cisco Firepower adaptor:FcIfFrameStats:errorFrames
        managed object property"
    ::= { cfprApAdaptorFcIfFrameStatsEntry 9 }

cfprApAdaptorFcIfFrameStatsErrorFramesDelta OBJECT-TYPE
    SYNTAX       Counter64
    MAX-ACCESS   read-only
    STATUS       current
    DESCRIPTION
        "Cisco Firepower adaptor:FcIfFrameStats:errorFramesDelta
        managed object property"
    ::= { cfprApAdaptorFcIfFrameStatsEntry 10 }

cfprApAdaptorFcIfFrameStatsErrorFramesDeltaAvg OBJECT-TYPE
    SYNTAX       Unsigned64
    MAX-ACCESS   read-only
    STATUS       current
    DESCRIPTION
        "Cisco Firepower adaptor:FcIfFrameStats:errorFramesDeltaAvg
        managed object property"
    ::= { cfprApAdaptorFcIfFrameStatsEntry 11 }

cfprApAdaptorFcIfFrameStatsErrorFramesDeltaMax OBJECT-TYPE
    SYNTAX       Unsigned64
    MAX-ACCESS   read-only
    STATUS       current
    DESCRIPTION
        "Cisco Firepower adaptor:FcIfFrameStats:errorFramesDeltaMax
        managed object property"
    ::= { cfprApAdaptorFcIfFrameStatsEntry 12 }

cfprApAdaptorFcIfFrameStatsErrorFramesDeltaMin OBJECT-TYPE
    SYNTAX       Unsigned64
    MAX-ACCESS   read-only
    STATUS       current
    DESCRIPTION
        "Cisco Firepower adaptor:FcIfFrameStats:errorFramesDeltaMin
        managed object property"
    ::= { cfprApAdaptorFcIfFrameStatsEntry 13 }

cfprApAdaptorFcIfFrameStatsIntervals OBJECT-TYPE
    SYNTAX       Gauge32
    MAX-ACCESS   read-only
    STATUS       current
    DESCRIPTION
        "Cisco Firepower adaptor:FcIfFrameStats:intervals
        managed object property"
    ::= { cfprApAdaptorFcIfFrameStatsEntry 14 }

cfprApAdaptorFcIfFrameStatsRxFrames OBJECT-TYPE
    SYNTAX       Unsigned64
    MAX-ACCESS   read-only
    STATUS       current
    DESCRIPTION
        "Cisco Firepower adaptor:FcIfFrameStats:rxFrames
        managed object property"
    ::= { cfprApAdaptorFcIfFrameStatsEntry 15 }

cfprApAdaptorFcIfFrameStatsRxFramesDelta OBJECT-TYPE
    SYNTAX       Counter64
    MAX-ACCESS   read-only
    STATUS       current
    DESCRIPTION
        "Cisco Firepower adaptor:FcIfFrameStats:rxFramesDelta
        managed object property"
    ::= { cfprApAdaptorFcIfFrameStatsEntry 16 }

cfprApAdaptorFcIfFrameStatsRxFramesDeltaAvg OBJECT-TYPE
    SYNTAX       Unsigned64
    MAX-ACCESS   read-only
    STATUS       current
    DESCRIPTION
        "Cisco Firepower adaptor:FcIfFrameStats:rxFramesDeltaAvg
        managed object property"
    ::= { cfprApAdaptorFcIfFrameStatsEntry 17 }

cfprApAdaptorFcIfFrameStatsRxFramesDeltaMax OBJECT-TYPE
    SYNTAX       Unsigned64
    MAX-ACCESS   read-only
    STATUS       current
    DESCRIPTION
        "Cisco Firepower adaptor:FcIfFrameStats:rxFramesDeltaMax
        managed object property"
    ::= { cfprApAdaptorFcIfFrameStatsEntry 18 }

cfprApAdaptorFcIfFrameStatsRxFramesDeltaMin OBJECT-TYPE
    SYNTAX       Unsigned64
    MAX-ACCESS   read-only
    STATUS       current
    DESCRIPTION
        "Cisco Firepower adaptor:FcIfFrameStats:rxFramesDeltaMin
        managed object property"
    ::= { cfprApAdaptorFcIfFrameStatsEntry 19 }

cfprApAdaptorFcIfFrameStatsSuspect OBJECT-TYPE
    SYNTAX       TruthValue
    MAX-ACCESS   read-only
    STATUS       current
    DESCRIPTION
        "Cisco Firepower adaptor:FcIfFrameStats:suspect
        managed object property"
    ::= { cfprApAdaptorFcIfFrameStatsEntry 20 }

cfprApAdaptorFcIfFrameStatsThresholded OBJECT-TYPE
    SYNTAX       CfprApAdaptorFcIfFrameStatsThresholded
    MAX-ACCESS   read-only
    STATUS       current
    DESCRIPTION
        "Cisco Firepower adaptor:FcIfFrameStats:thresholded
        managed object property"
    ::= { cfprApAdaptorFcIfFrameStatsEntry 21 }

cfprApAdaptorFcIfFrameStatsTimeCollected OBJECT-TYPE
    SYNTAX       DateAndTime
    MAX-ACCESS   read-only
    STATUS       current
    DESCRIPTION
        "Cisco Firepower adaptor:FcIfFrameStats:timeCollected
        managed object property"
    ::= { cfprApAdaptorFcIfFrameStatsEntry 22 }

cfprApAdaptorFcIfFrameStatsTxFrames OBJECT-TYPE
    SYNTAX       Unsigned64
    MAX-ACCESS   read-only
    STATUS       current
    DESCRIPTION
        "Cisco Firepower adaptor:FcIfFrameStats:txFrames
        managed object property"
    ::= { cfprApAdaptorFcIfFrameStatsEntry 23 }

cfprApAdaptorFcIfFrameStatsTxFramesDelta OBJECT-TYPE
    SYNTAX       Counter64
    MAX-ACCESS   read-only
    STATUS       current
    DESCRIPTION
        "Cisco Firepower adaptor:FcIfFrameStats:txFramesDelta
        managed object property"
    ::= { cfprApAdaptorFcIfFrameStatsEntry 24 }

cfprApAdaptorFcIfFrameStatsTxFramesDeltaAvg OBJECT-TYPE
    SYNTAX       Unsigned64
    MAX-ACCESS   read-only
    STATUS       current
    DESCRIPTION
        "Cisco Firepower adaptor:FcIfFrameStats:txFramesDeltaAvg
        managed object property"
    ::= { cfprApAdaptorFcIfFrameStatsEntry 25 }

cfprApAdaptorFcIfFrameStatsTxFramesDeltaMax OBJECT-TYPE
    SYNTAX       Unsigned64
    MAX-ACCESS   read-only
    STATUS       current
    DESCRIPTION
        "Cisco Firepower adaptor:FcIfFrameStats:txFramesDeltaMax
        managed object property"
    ::= { cfprApAdaptorFcIfFrameStatsEntry 26 }

cfprApAdaptorFcIfFrameStatsTxFramesDeltaMin OBJECT-TYPE
    SYNTAX       Unsigned64
    MAX-ACCESS   read-only
    STATUS       current
    DESCRIPTION
        "Cisco Firepower adaptor:FcIfFrameStats:txFramesDeltaMin
        managed object property"
    ::= { cfprApAdaptorFcIfFrameStatsEntry 27 }

cfprApAdaptorFcIfFrameStatsUpdate OBJECT-TYPE
    SYNTAX       Gauge32
    MAX-ACCESS   read-only
    STATUS       current
    DESCRIPTION
        "Cisco Firepower adaptor:FcIfFrameStats:update
        managed object property"
    ::= { cfprApAdaptorFcIfFrameStatsEntry 28 }

cfprApAdaptorFcIfFrameStatsHistTable OBJECT-TYPE
    SYNTAX           SEQUENCE OF CfprApAdaptorFcIfFrameStatsHistEntry
    MAX-ACCESS       not-accessible
    STATUS           current
    DESCRIPTION
        "Cisco Firepower adaptor:FcIfFrameStatsHist managed object table"
    ::= { cfprApAdaptorObjects 43 }

cfprApAdaptorFcIfFrameStatsHistEntry OBJECT-TYPE
    SYNTAX           CfprApAdaptorFcIfFrameStatsHistEntry
    MAX-ACCESS       not-accessible
    STATUS           current
    DESCRIPTION
        "Entry for the cfprApAdaptorFcIfFrameStatsHistTable table."
    INDEX { cfprApAdaptorFcIfFrameStatsHistInstanceId }
    ::= { cfprApAdaptorFcIfFrameStatsHistTable 1 }

CfprApAdaptorFcIfFrameStatsHistEntry ::= SEQUENCE {
    cfprApAdaptorFcIfFrameStatsHistInstanceId                        CfprApManagedObjectId,
    cfprApAdaptorFcIfFrameStatsHistDn                                CfprApManagedObjectDn,
    cfprApAdaptorFcIfFrameStatsHistRn                                SnmpAdminString,
    cfprApAdaptorFcIfFrameStatsHistDumpedFrames                      Unsigned64,
    cfprApAdaptorFcIfFrameStatsHistDumpedFramesDelta                 Unsigned64,
    cfprApAdaptorFcIfFrameStatsHistDumpedFramesDeltaAvg              Unsigned64,
    cfprApAdaptorFcIfFrameStatsHistDumpedFramesDeltaMax              Unsigned64,
    cfprApAdaptorFcIfFrameStatsHistDumpedFramesDeltaMin              Unsigned64,
    cfprApAdaptorFcIfFrameStatsHistErrorFrames                       Unsigned64,
    cfprApAdaptorFcIfFrameStatsHistErrorFramesDelta                  Unsigned64,
    cfprApAdaptorFcIfFrameStatsHistErrorFramesDeltaAvg               Unsigned64,
    cfprApAdaptorFcIfFrameStatsHistErrorFramesDeltaMax               Unsigned64,
    cfprApAdaptorFcIfFrameStatsHistErrorFramesDeltaMin               Unsigned64,
    cfprApAdaptorFcIfFrameStatsHistId                                Unsigned64,
    cfprApAdaptorFcIfFrameStatsHistMostRecent                        TruthValue,
    cfprApAdaptorFcIfFrameStatsHistRxFrames                          Unsigned64,
    cfprApAdaptorFcIfFrameStatsHistRxFramesDelta                     Unsigned64,
    cfprApAdaptorFcIfFrameStatsHistRxFramesDeltaAvg                  Unsigned64,
    cfprApAdaptorFcIfFrameStatsHistRxFramesDeltaMax                  Unsigned64,
    cfprApAdaptorFcIfFrameStatsHistRxFramesDeltaMin                  Unsigned64,
    cfprApAdaptorFcIfFrameStatsHistSuspect                           TruthValue,
    cfprApAdaptorFcIfFrameStatsHistThresholded                       CfprApAdaptorFcIfFrameStatsHistThresholded,
    cfprApAdaptorFcIfFrameStatsHistTimeCollected                     DateAndTime,
    cfprApAdaptorFcIfFrameStatsHistTxFrames                          Unsigned64,
    cfprApAdaptorFcIfFrameStatsHistTxFramesDelta                     Unsigned64,
    cfprApAdaptorFcIfFrameStatsHistTxFramesDeltaAvg                  Unsigned64,
    cfprApAdaptorFcIfFrameStatsHistTxFramesDeltaMax                  Unsigned64,
    cfprApAdaptorFcIfFrameStatsHistTxFramesDeltaMin                  Unsigned64
}

cfprApAdaptorFcIfFrameStatsHistInstanceId OBJECT-TYPE
    SYNTAX       CfprApManagedObjectId
    MAX-ACCESS   not-accessible
    STATUS       current
    DESCRIPTION
        "Instance identifier of the managed object."
    ::= { cfprApAdaptorFcIfFrameStatsHistEntry 1 }

cfprApAdaptorFcIfFrameStatsHistDn OBJECT-TYPE
    SYNTAX       CfprApManagedObjectDn
    MAX-ACCESS   read-only
    STATUS       current
    DESCRIPTION
        "Cisco Firepower adaptor:FcIfFrameStatsHist:dn
        managed object property"
    ::= { cfprApAdaptorFcIfFrameStatsHistEntry 2 }

cfprApAdaptorFcIfFrameStatsHistRn OBJECT-TYPE
    SYNTAX       SnmpAdminString
    MAX-ACCESS   read-only
    STATUS       current
    DESCRIPTION
        "Cisco Firepower adaptor:FcIfFrameStatsHist:rn
        managed object property"
    ::= { cfprApAdaptorFcIfFrameStatsHistEntry 3 }

cfprApAdaptorFcIfFrameStatsHistDumpedFrames OBJECT-TYPE
    SYNTAX       Unsigned64
    MAX-ACCESS   read-only
    STATUS       current
    DESCRIPTION
        "Cisco Firepower adaptor:FcIfFrameStatsHist:dumpedFrames
        managed object property"
    ::= { cfprApAdaptorFcIfFrameStatsHistEntry 4 }

cfprApAdaptorFcIfFrameStatsHistDumpedFramesDelta OBJECT-TYPE
    SYNTAX       Unsigned64
    MAX-ACCESS   read-only
    STATUS       current
    DESCRIPTION
        "Cisco Firepower adaptor:FcIfFrameStatsHist:dumpedFramesDelta
        managed object property"
    ::= { cfprApAdaptorFcIfFrameStatsHistEntry 5 }

cfprApAdaptorFcIfFrameStatsHistDumpedFramesDeltaAvg OBJECT-TYPE
    SYNTAX       Unsigned64
    MAX-ACCESS   read-only
    STATUS       current
    DESCRIPTION
        "Cisco Firepower adaptor:FcIfFrameStatsHist:dumpedFramesDeltaAvg
        managed object property"
    ::= { cfprApAdaptorFcIfFrameStatsHistEntry 6 }

cfprApAdaptorFcIfFrameStatsHistDumpedFramesDeltaMax OBJECT-TYPE
    SYNTAX       Unsigned64
    MAX-ACCESS   read-only
    STATUS       current
    DESCRIPTION
        "Cisco Firepower adaptor:FcIfFrameStatsHist:dumpedFramesDeltaMax
        managed object property"
    ::= { cfprApAdaptorFcIfFrameStatsHistEntry 7 }

cfprApAdaptorFcIfFrameStatsHistDumpedFramesDeltaMin OBJECT-TYPE
    SYNTAX       Unsigned64
    MAX-ACCESS   read-only
    STATUS       current
    DESCRIPTION
        "Cisco Firepower adaptor:FcIfFrameStatsHist:dumpedFramesDeltaMin
        managed object property"
    ::= { cfprApAdaptorFcIfFrameStatsHistEntry 8 }

cfprApAdaptorFcIfFrameStatsHistErrorFrames OBJECT-TYPE
    SYNTAX       Unsigned64
    MAX-ACCESS   read-only
    STATUS       current
    DESCRIPTION
        "Cisco Firepower adaptor:FcIfFrameStatsHist:errorFrames
        managed object property"
    ::= { cfprApAdaptorFcIfFrameStatsHistEntry 9 }

cfprApAdaptorFcIfFrameStatsHistErrorFramesDelta OBJECT-TYPE
    SYNTAX       Unsigned64
    MAX-ACCESS   read-only
    STATUS       current
    DESCRIPTION
        "Cisco Firepower adaptor:FcIfFrameStatsHist:errorFramesDelta
        managed object property"
    ::= { cfprApAdaptorFcIfFrameStatsHistEntry 10 }

cfprApAdaptorFcIfFrameStatsHistErrorFramesDeltaAvg OBJECT-TYPE
    SYNTAX       Unsigned64
    MAX-ACCESS   read-only
    STATUS       current
    DESCRIPTION
        "Cisco Firepower adaptor:FcIfFrameStatsHist:errorFramesDeltaAvg
        managed object property"
    ::= { cfprApAdaptorFcIfFrameStatsHistEntry 11 }

cfprApAdaptorFcIfFrameStatsHistErrorFramesDeltaMax OBJECT-TYPE
    SYNTAX       Unsigned64
    MAX-ACCESS   read-only
    STATUS       current
    DESCRIPTION
        "Cisco Firepower adaptor:FcIfFrameStatsHist:errorFramesDeltaMax
        managed object property"
    ::= { cfprApAdaptorFcIfFrameStatsHistEntry 12 }

cfprApAdaptorFcIfFrameStatsHistErrorFramesDeltaMin OBJECT-TYPE
    SYNTAX       Unsigned64
    MAX-ACCESS   read-only
    STATUS       current
    DESCRIPTION
        "Cisco Firepower adaptor:FcIfFrameStatsHist:errorFramesDeltaMin
        managed object property"
    ::= { cfprApAdaptorFcIfFrameStatsHistEntry 13 }

cfprApAdaptorFcIfFrameStatsHistId OBJECT-TYPE
    SYNTAX       Unsigned64
    MAX-ACCESS   read-only
    STATUS       current
    DESCRIPTION
        "Cisco Firepower adaptor:FcIfFrameStatsHist:id
        managed object property"
    ::= { cfprApAdaptorFcIfFrameStatsHistEntry 14 }

cfprApAdaptorFcIfFrameStatsHistMostRecent OBJECT-TYPE
    SYNTAX       TruthValue
    MAX-ACCESS   read-only
    STATUS       current
    DESCRIPTION
        "Cisco Firepower adaptor:FcIfFrameStatsHist:mostRecent
        managed object property"
    ::= { cfprApAdaptorFcIfFrameStatsHistEntry 15 }

cfprApAdaptorFcIfFrameStatsHistRxFrames OBJECT-TYPE
    SYNTAX       Unsigned64
    MAX-ACCESS   read-only
    STATUS       current
    DESCRIPTION
        "Cisco Firepower adaptor:FcIfFrameStatsHist:rxFrames
        managed object property"
    ::= { cfprApAdaptorFcIfFrameStatsHistEntry 16 }

cfprApAdaptorFcIfFrameStatsHistRxFramesDelta OBJECT-TYPE
    SYNTAX       Unsigned64
    MAX-ACCESS   read-only
    STATUS       current
    DESCRIPTION
        "Cisco Firepower adaptor:FcIfFrameStatsHist:rxFramesDelta
        managed object property"
    ::= { cfprApAdaptorFcIfFrameStatsHistEntry 17 }

cfprApAdaptorFcIfFrameStatsHistRxFramesDeltaAvg OBJECT-TYPE
    SYNTAX       Unsigned64
    MAX-ACCESS   read-only
    STATUS       current
    DESCRIPTION
        "Cisco Firepower adaptor:FcIfFrameStatsHist:rxFramesDeltaAvg
        managed object property"
    ::= { cfprApAdaptorFcIfFrameStatsHistEntry 18 }

cfprApAdaptorFcIfFrameStatsHistRxFramesDeltaMax OBJECT-TYPE
    SYNTAX       Unsigned64
    MAX-ACCESS   read-only
    STATUS       current
    DESCRIPTION
        "Cisco Firepower adaptor:FcIfFrameStatsHist:rxFramesDeltaMax
        managed object property"
    ::= { cfprApAdaptorFcIfFrameStatsHistEntry 19 }

cfprApAdaptorFcIfFrameStatsHistRxFramesDeltaMin OBJECT-TYPE
    SYNTAX       Unsigned64
    MAX-ACCESS   read-only
    STATUS       current
    DESCRIPTION
        "Cisco Firepower adaptor:FcIfFrameStatsHist:rxFramesDeltaMin
        managed object property"
    ::= { cfprApAdaptorFcIfFrameStatsHistEntry 20 }

cfprApAdaptorFcIfFrameStatsHistSuspect OBJECT-TYPE
    SYNTAX       TruthValue
    MAX-ACCESS   read-only
    STATUS       current
    DESCRIPTION
        "Cisco Firepower adaptor:FcIfFrameStatsHist:suspect
        managed object property"
    ::= { cfprApAdaptorFcIfFrameStatsHistEntry 21 }

cfprApAdaptorFcIfFrameStatsHistThresholded OBJECT-TYPE
    SYNTAX       CfprApAdaptorFcIfFrameStatsHistThresholded
    MAX-ACCESS   read-only
    STATUS       current
    DESCRIPTION
        "Cisco Firepower adaptor:FcIfFrameStatsHist:thresholded
        managed object property"
    ::= { cfprApAdaptorFcIfFrameStatsHistEntry 22 }

cfprApAdaptorFcIfFrameStatsHistTimeCollected OBJECT-TYPE
    SYNTAX       DateAndTime
    MAX-ACCESS   read-only
    STATUS       current
    DESCRIPTION
        "Cisco Firepower adaptor:FcIfFrameStatsHist:timeCollected
        managed object property"
    ::= { cfprApAdaptorFcIfFrameStatsHistEntry 23 }

cfprApAdaptorFcIfFrameStatsHistTxFrames OBJECT-TYPE
    SYNTAX       Unsigned64
    MAX-ACCESS   read-only
    STATUS       current
    DESCRIPTION
        "Cisco Firepower adaptor:FcIfFrameStatsHist:txFrames
        managed object property"
    ::= { cfprApAdaptorFcIfFrameStatsHistEntry 24 }

cfprApAdaptorFcIfFrameStatsHistTxFramesDelta OBJECT-TYPE
    SYNTAX       Unsigned64
    MAX-ACCESS   read-only
    STATUS       current
    DESCRIPTION
        "Cisco Firepower adaptor:FcIfFrameStatsHist:txFramesDelta
        managed object property"
    ::= { cfprApAdaptorFcIfFrameStatsHistEntry 25 }

cfprApAdaptorFcIfFrameStatsHistTxFramesDeltaAvg OBJECT-TYPE
    SYNTAX       Unsigned64
    MAX-ACCESS   read-only
    STATUS       current
    DESCRIPTION
        "Cisco Firepower adaptor:FcIfFrameStatsHist:txFramesDeltaAvg
        managed object property"
    ::= { cfprApAdaptorFcIfFrameStatsHistEntry 26 }

cfprApAdaptorFcIfFrameStatsHistTxFramesDeltaMax OBJECT-TYPE
    SYNTAX       Unsigned64
    MAX-ACCESS   read-only
    STATUS       current
    DESCRIPTION
        "Cisco Firepower adaptor:FcIfFrameStatsHist:txFramesDeltaMax
        managed object property"
    ::= { cfprApAdaptorFcIfFrameStatsHistEntry 27 }

cfprApAdaptorFcIfFrameStatsHistTxFramesDeltaMin OBJECT-TYPE
    SYNTAX       Unsigned64
    MAX-ACCESS   read-only
    STATUS       current
    DESCRIPTION
        "Cisco Firepower adaptor:FcIfFrameStatsHist:txFramesDeltaMin
        managed object property"
    ::= { cfprApAdaptorFcIfFrameStatsHistEntry 28 }

cfprApAdaptorFcOEIfTable OBJECT-TYPE
    SYNTAX           SEQUENCE OF CfprApAdaptorFcOEIfEntry
    MAX-ACCESS       not-accessible
    STATUS           current
    DESCRIPTION
        "Cisco Firepower adaptor:FcOEIf managed object table"
    ::= { cfprApAdaptorObjects 45 }

cfprApAdaptorFcOEIfEntry OBJECT-TYPE
    SYNTAX           CfprApAdaptorFcOEIfEntry
    MAX-ACCESS       not-accessible
    STATUS           current
    DESCRIPTION
        "Entry for the cfprApAdaptorFcOEIfTable table."
    INDEX { cfprApAdaptorFcOEIfInstanceId }
    ::= { cfprApAdaptorFcOEIfTable 1 }

CfprApAdaptorFcOEIfEntry ::= SEQUENCE {
    cfprApAdaptorFcOEIfInstanceId                                    CfprApManagedObjectId,
    cfprApAdaptorFcOEIfDn                                            CfprApManagedObjectDn,
    cfprApAdaptorFcOEIfRn                                            SnmpAdminString,
    cfprApAdaptorFcOEIfEpDn                                          SnmpAdminString,
    cfprApAdaptorFcOEIfFcoeVlan                                      Gauge32,
    cfprApAdaptorFcOEIfId                                            Gauge32,
    cfprApAdaptorFcOEIfIfRole                                        CfprApFabricVnetEpIfRole,
    cfprApAdaptorFcOEIfIfType                                        CfprApNetworkVnetEpIfType,
    cfprApAdaptorFcOEIfLc                                            CfprApFsmLifecycle,
    cfprApAdaptorFcOEIfLocale                                        CfprApFabricVnetEpLocale,
    cfprApAdaptorFcOEIfMac                                           MacAddress,
    cfprApAdaptorFcOEIfName                                          SnmpAdminString,
    cfprApAdaptorFcOEIfOperState                                     CfprApFabricVsanOperState,
    cfprApAdaptorFcOEIfPeerDn                                        SnmpAdminString,
    cfprApAdaptorFcOEIfPolicyOwner                                   CfprApFabricVnetEpPolicyOwner,
    cfprApAdaptorFcOEIfSwitchId                                      CfprApNetworkSwitchId,
    cfprApAdaptorFcOEIfTransport                                     CfprApFabricAVsanTransport,
    cfprApAdaptorFcOEIfType                                          CfprApFabricAVsanType,
    cfprApAdaptorFcOEIfZoningState                                   CfprApFabricZoningState
}

cfprApAdaptorFcOEIfInstanceId OBJECT-TYPE
    SYNTAX       CfprApManagedObjectId
    MAX-ACCESS   not-accessible
    STATUS       current
    DESCRIPTION
        "Instance identifier of the managed object."
    ::= { cfprApAdaptorFcOEIfEntry 1 }

cfprApAdaptorFcOEIfDn OBJECT-TYPE
    SYNTAX       CfprApManagedObjectDn
    MAX-ACCESS   read-only
    STATUS       current
    DESCRIPTION
        "Cisco Firepower adaptor:FcOEIf:dn managed object property"
    ::= { cfprApAdaptorFcOEIfEntry 2 }

cfprApAdaptorFcOEIfRn OBJECT-TYPE
    SYNTAX       SnmpAdminString
    MAX-ACCESS   read-only
    STATUS       current
    DESCRIPTION
        "Cisco Firepower adaptor:FcOEIf:rn managed object property"
    ::= { cfprApAdaptorFcOEIfEntry 3 }

cfprApAdaptorFcOEIfEpDn OBJECT-TYPE
    SYNTAX       SnmpAdminString
    MAX-ACCESS   read-only
    STATUS       current
    DESCRIPTION
        "Cisco Firepower adaptor:FcOEIf:epDn managed object property"
    ::= { cfprApAdaptorFcOEIfEntry 4 }

cfprApAdaptorFcOEIfFcoeVlan OBJECT-TYPE
    SYNTAX       Gauge32
    MAX-ACCESS   read-only
    STATUS       current
    DESCRIPTION
        "Cisco Firepower adaptor:FcOEIf:fcoeVlan managed object property"
    ::= { cfprApAdaptorFcOEIfEntry 5 }

cfprApAdaptorFcOEIfId OBJECT-TYPE
    SYNTAX       Gauge32
    MAX-ACCESS   read-only
    STATUS       current
    DESCRIPTION
        "Cisco Firepower adaptor:FcOEIf:id managed object property"
    ::= { cfprApAdaptorFcOEIfEntry 6 }

cfprApAdaptorFcOEIfIfRole OBJECT-TYPE
    SYNTAX       CfprApFabricVnetEpIfRole
    MAX-ACCESS   read-only
    STATUS       current
    DESCRIPTION
        "Cisco Firepower adaptor:FcOEIf:ifRole managed object property"
    ::= { cfprApAdaptorFcOEIfEntry 7 }

cfprApAdaptorFcOEIfIfType OBJECT-TYPE
    SYNTAX       CfprApNetworkVnetEpIfType
    MAX-ACCESS   read-only
    STATUS       current
    DESCRIPTION
        "Cisco Firepower adaptor:FcOEIf:ifType managed object property"
    ::= { cfprApAdaptorFcOEIfEntry 8 }

cfprApAdaptorFcOEIfLc OBJECT-TYPE
    SYNTAX       CfprApFsmLifecycle
    MAX-ACCESS   read-only
    STATUS       current
    DESCRIPTION
        "Cisco Firepower adaptor:FcOEIf:lc managed object property"
    ::= { cfprApAdaptorFcOEIfEntry 9 }

cfprApAdaptorFcOEIfLocale OBJECT-TYPE
    SYNTAX       CfprApFabricVnetEpLocale
    MAX-ACCESS   read-only
    STATUS       current
    DESCRIPTION
        "Cisco Firepower adaptor:FcOEIf:locale managed object property"
    ::= { cfprApAdaptorFcOEIfEntry 10 }

cfprApAdaptorFcOEIfMac OBJECT-TYPE
    SYNTAX       MacAddress
    MAX-ACCESS   read-only
    STATUS       current
    DESCRIPTION
        "Cisco Firepower adaptor:FcOEIf:mac managed object property"
    ::= { cfprApAdaptorFcOEIfEntry 11 }

cfprApAdaptorFcOEIfName OBJECT-TYPE
    SYNTAX       SnmpAdminString
    MAX-ACCESS   read-only
    STATUS       current
    DESCRIPTION
        "Cisco Firepower adaptor:FcOEIf:name managed object property"
    ::= { cfprApAdaptorFcOEIfEntry 12 }

cfprApAdaptorFcOEIfOperState OBJECT-TYPE
    SYNTAX       CfprApFabricVsanOperState
    MAX-ACCESS   read-only
    STATUS       current
    DESCRIPTION
        "Cisco Firepower adaptor:FcOEIf:operState managed object property"
    ::= { cfprApAdaptorFcOEIfEntry 13 }

cfprApAdaptorFcOEIfPeerDn OBJECT-TYPE
    SYNTAX       SnmpAdminString
    MAX-ACCESS   read-only
    STATUS       current
    DESCRIPTION
        "Cisco Firepower adaptor:FcOEIf:peerDn managed object property"
    ::= { cfprApAdaptorFcOEIfEntry 14 }

cfprApAdaptorFcOEIfPolicyOwner OBJECT-TYPE
    SYNTAX       CfprApFabricVnetEpPolicyOwner
    MAX-ACCESS   read-only
    STATUS       current
    DESCRIPTION
        "Cisco Firepower adaptor:FcOEIf:policyOwner managed
        object property"
    ::= { cfprApAdaptorFcOEIfEntry 15 }

cfprApAdaptorFcOEIfSwitchId OBJECT-TYPE
    SYNTAX       CfprApNetworkSwitchId
    MAX-ACCESS   read-only
    STATUS       current
    DESCRIPTION
        "Cisco Firepower adaptor:FcOEIf:switchId managed object property"
    ::= { cfprApAdaptorFcOEIfEntry 16 }

cfprApAdaptorFcOEIfTransport OBJECT-TYPE
    SYNTAX       CfprApFabricAVsanTransport
    MAX-ACCESS   read-only
    STATUS       current
    DESCRIPTION
        "Cisco Firepower adaptor:FcOEIf:transport managed object property"
    ::= { cfprApAdaptorFcOEIfEntry 17 }

cfprApAdaptorFcOEIfType OBJECT-TYPE
    SYNTAX       CfprApFabricAVsanType
    MAX-ACCESS   read-only
    STATUS       current
    DESCRIPTION
        "Cisco Firepower adaptor:FcOEIf:type managed object property"
    ::= { cfprApAdaptorFcOEIfEntry 18 }

cfprApAdaptorFcOEIfZoningState OBJECT-TYPE
    SYNTAX       CfprApFabricZoningState
    MAX-ACCESS   read-only
    STATUS       current
    DESCRIPTION
        "Cisco Firepower adaptor:FcOEIf:zoningState managed
        object property"
    ::= { cfprApAdaptorFcOEIfEntry 19 }

cfprApAdaptorFcPortStatsTable OBJECT-TYPE
    SYNTAX           SEQUENCE OF CfprApAdaptorFcPortStatsEntry
    MAX-ACCESS       not-accessible
    STATUS           current
    DESCRIPTION
        "Cisco Firepower adaptor:FcPortStats managed object table"
    ::= { cfprApAdaptorObjects 49 }

cfprApAdaptorFcPortStatsEntry OBJECT-TYPE
    SYNTAX           CfprApAdaptorFcPortStatsEntry
    MAX-ACCESS       not-accessible
    STATUS           current
    DESCRIPTION
        "Entry for the cfprApAdaptorFcPortStatsTable table."
    INDEX { cfprApAdaptorFcPortStatsInstanceId }
    ::= { cfprApAdaptorFcPortStatsTable 1 }

CfprApAdaptorFcPortStatsEntry ::= SEQUENCE {
    cfprApAdaptorFcPortStatsInstanceId                               CfprApManagedObjectId,
    cfprApAdaptorFcPortStatsDn                                       CfprApManagedObjectDn,
    cfprApAdaptorFcPortStatsRn                                       SnmpAdminString,
    cfprApAdaptorFcPortStatsIntervals                                Gauge32,
    cfprApAdaptorFcPortStatsRxBadFrames                              Unsigned64,
    cfprApAdaptorFcPortStatsRxBadFramesDelta                         Counter64,
    cfprApAdaptorFcPortStatsRxBadFramesDeltaAvg                      Unsigned64,
    cfprApAdaptorFcPortStatsRxBadFramesDeltaMax                      Unsigned64,
    cfprApAdaptorFcPortStatsRxBadFramesDeltaMin                      Unsigned64,
    cfprApAdaptorFcPortStatsRxFrames                                 Unsigned64,
    cfprApAdaptorFcPortStatsRxFramesDelta                            Counter64,
    cfprApAdaptorFcPortStatsRxFramesDeltaAvg                         Unsigned64,
    cfprApAdaptorFcPortStatsRxFramesDeltaMax                         Unsigned64,
    cfprApAdaptorFcPortStatsRxFramesDeltaMin                         Unsigned64,
    cfprApAdaptorFcPortStatsSuspect                                  TruthValue,
    cfprApAdaptorFcPortStatsThresholded                              CfprApAdaptorFcPortStatsThresholded,
    cfprApAdaptorFcPortStatsTimeCollected                            DateAndTime,
    cfprApAdaptorFcPortStatsTxBadFrames                              Unsigned64,
    cfprApAdaptorFcPortStatsTxBadFramesDelta                         Counter64,
    cfprApAdaptorFcPortStatsTxBadFramesDeltaAvg                      Unsigned64,
    cfprApAdaptorFcPortStatsTxBadFramesDeltaMax                      Unsigned64,
    cfprApAdaptorFcPortStatsTxBadFramesDeltaMin                      Unsigned64,
    cfprApAdaptorFcPortStatsTxFrames                                 Unsigned64,
    cfprApAdaptorFcPortStatsTxFramesDelta                            Counter64,
    cfprApAdaptorFcPortStatsTxFramesDeltaAvg                         Unsigned64,
    cfprApAdaptorFcPortStatsTxFramesDeltaMax                         Unsigned64,
    cfprApAdaptorFcPortStatsTxFramesDeltaMin                         Unsigned64,
    cfprApAdaptorFcPortStatsUpdate                                   Gauge32
}

cfprApAdaptorFcPortStatsInstanceId OBJECT-TYPE
    SYNTAX       CfprApManagedObjectId
    MAX-ACCESS   not-accessible
    STATUS       current
    DESCRIPTION
        "Instance identifier of the managed object."
    ::= { cfprApAdaptorFcPortStatsEntry 1 }

cfprApAdaptorFcPortStatsDn OBJECT-TYPE
    SYNTAX       CfprApManagedObjectDn
    MAX-ACCESS   read-only
    STATUS       current
    DESCRIPTION
        "Cisco Firepower adaptor:FcPortStats:dn managed object property"
    ::= { cfprApAdaptorFcPortStatsEntry 2 }

cfprApAdaptorFcPortStatsRn OBJECT-TYPE
    SYNTAX       SnmpAdminString
    MAX-ACCESS   read-only
    STATUS       current
    DESCRIPTION
        "Cisco Firepower adaptor:FcPortStats:rn managed object property"
    ::= { cfprApAdaptorFcPortStatsEntry 3 }

cfprApAdaptorFcPortStatsIntervals OBJECT-TYPE
    SYNTAX       Gauge32
    MAX-ACCESS   read-only
    STATUS       current
    DESCRIPTION
        "Cisco Firepower adaptor:FcPortStats:intervals
        managed object property"
    ::= { cfprApAdaptorFcPortStatsEntry 4 }

cfprApAdaptorFcPortStatsRxBadFrames OBJECT-TYPE
    SYNTAX       Unsigned64
    MAX-ACCESS   read-only
    STATUS       current
    DESCRIPTION
        "Cisco Firepower adaptor:FcPortStats:rxBadFrames
        managed object property"
    ::= { cfprApAdaptorFcPortStatsEntry 5 }

cfprApAdaptorFcPortStatsRxBadFramesDelta OBJECT-TYPE
    SYNTAX       Counter64
    MAX-ACCESS   read-only
    STATUS       current
    DESCRIPTION
        "Cisco Firepower adaptor:FcPortStats:rxBadFramesDelta
        managed object property"
    ::= { cfprApAdaptorFcPortStatsEntry 6 }

cfprApAdaptorFcPortStatsRxBadFramesDeltaAvg OBJECT-TYPE
    SYNTAX       Unsigned64
    MAX-ACCESS   read-only
    STATUS       current
    DESCRIPTION
        "Cisco Firepower adaptor:FcPortStats:rxBadFramesDeltaAvg
        managed object property"
    ::= { cfprApAdaptorFcPortStatsEntry 7 }

cfprApAdaptorFcPortStatsRxBadFramesDeltaMax OBJECT-TYPE
    SYNTAX       Unsigned64
    MAX-ACCESS   read-only
    STATUS       current
    DESCRIPTION
        "Cisco Firepower adaptor:FcPortStats:rxBadFramesDeltaMax
        managed object property"
    ::= { cfprApAdaptorFcPortStatsEntry 8 }

cfprApAdaptorFcPortStatsRxBadFramesDeltaMin OBJECT-TYPE
    SYNTAX       Unsigned64
    MAX-ACCESS   read-only
    STATUS       current
    DESCRIPTION
        "Cisco Firepower adaptor:FcPortStats:rxBadFramesDeltaMin
        managed object property"
    ::= { cfprApAdaptorFcPortStatsEntry 9 }

cfprApAdaptorFcPortStatsRxFrames OBJECT-TYPE
    SYNTAX       Unsigned64
    MAX-ACCESS   read-only
    STATUS       current
    DESCRIPTION
        "Cisco Firepower adaptor:FcPortStats:rxFrames managed
        object property"
    ::= { cfprApAdaptorFcPortStatsEntry 10 }

cfprApAdaptorFcPortStatsRxFramesDelta OBJECT-TYPE
    SYNTAX       Counter64
    MAX-ACCESS   read-only
    STATUS       current
    DESCRIPTION
        "Cisco Firepower adaptor:FcPortStats:rxFramesDelta
        managed object property"
    ::= { cfprApAdaptorFcPortStatsEntry 11 }

cfprApAdaptorFcPortStatsRxFramesDeltaAvg OBJECT-TYPE
    SYNTAX       Unsigned64
    MAX-ACCESS   read-only
    STATUS       current
    DESCRIPTION
        "Cisco Firepower adaptor:FcPortStats:rxFramesDeltaAvg
        managed object property"
    ::= { cfprApAdaptorFcPortStatsEntry 12 }

cfprApAdaptorFcPortStatsRxFramesDeltaMax OBJECT-TYPE
    SYNTAX       Unsigned64
    MAX-ACCESS   read-only
    STATUS       current
    DESCRIPTION
        "Cisco Firepower adaptor:FcPortStats:rxFramesDeltaMax
        managed object property"
    ::= { cfprApAdaptorFcPortStatsEntry 13 }

cfprApAdaptorFcPortStatsRxFramesDeltaMin OBJECT-TYPE
    SYNTAX       Unsigned64
    MAX-ACCESS   read-only
    STATUS       current
    DESCRIPTION
        "Cisco Firepower adaptor:FcPortStats:rxFramesDeltaMin
        managed object property"
    ::= { cfprApAdaptorFcPortStatsEntry 14 }

cfprApAdaptorFcPortStatsSuspect OBJECT-TYPE
    SYNTAX       TruthValue
    MAX-ACCESS   read-only
    STATUS       current
    DESCRIPTION
        "Cisco Firepower adaptor:FcPortStats:suspect managed
        object property"
    ::= { cfprApAdaptorFcPortStatsEntry 15 }

cfprApAdaptorFcPortStatsThresholded OBJECT-TYPE
    SYNTAX       CfprApAdaptorFcPortStatsThresholded
    MAX-ACCESS   read-only
    STATUS       current
    DESCRIPTION
        "Cisco Firepower adaptor:FcPortStats:thresholded
        managed object property"
    ::= { cfprApAdaptorFcPortStatsEntry 16 }

cfprApAdaptorFcPortStatsTimeCollected OBJECT-TYPE
    SYNTAX       DateAndTime
    MAX-ACCESS   read-only
    STATUS       current
    DESCRIPTION
        "Cisco Firepower adaptor:FcPortStats:timeCollected
        managed object property"
    ::= { cfprApAdaptorFcPortStatsEntry 17 }

cfprApAdaptorFcPortStatsTxBadFrames OBJECT-TYPE
    SYNTAX       Unsigned64
    MAX-ACCESS   read-only
    STATUS       current
    DESCRIPTION
        "Cisco Firepower adaptor:FcPortStats:txBadFrames
        managed object property"
    ::= { cfprApAdaptorFcPortStatsEntry 18 }

cfprApAdaptorFcPortStatsTxBadFramesDelta OBJECT-TYPE
    SYNTAX       Counter64
    MAX-ACCESS   read-only
    STATUS       current
    DESCRIPTION
        "Cisco Firepower adaptor:FcPortStats:txBadFramesDelta
        managed object property"
    ::= { cfprApAdaptorFcPortStatsEntry 19 }

cfprApAdaptorFcPortStatsTxBadFramesDeltaAvg OBJECT-TYPE
    SYNTAX       Unsigned64
    MAX-ACCESS   read-only
    STATUS       current
    DESCRIPTION
        "Cisco Firepower adaptor:FcPortStats:txBadFramesDeltaAvg
        managed object property"
    ::= { cfprApAdaptorFcPortStatsEntry 20 }

cfprApAdaptorFcPortStatsTxBadFramesDeltaMax OBJECT-TYPE
    SYNTAX       Unsigned64
    MAX-ACCESS   read-only
    STATUS       current
    DESCRIPTION
        "Cisco Firepower adaptor:FcPortStats:txBadFramesDeltaMax
        managed object property"
    ::= { cfprApAdaptorFcPortStatsEntry 21 }

cfprApAdaptorFcPortStatsTxBadFramesDeltaMin OBJECT-TYPE
    SYNTAX       Unsigned64
    MAX-ACCESS   read-only
    STATUS       current
    DESCRIPTION
        "Cisco Firepower adaptor:FcPortStats:txBadFramesDeltaMin
        managed object property"
    ::= { cfprApAdaptorFcPortStatsEntry 22 }

cfprApAdaptorFcPortStatsTxFrames OBJECT-TYPE
    SYNTAX       Unsigned64
    MAX-ACCESS   read-only
    STATUS       current
    DESCRIPTION
        "Cisco Firepower adaptor:FcPortStats:txFrames managed
        object property"
    ::= { cfprApAdaptorFcPortStatsEntry 23 }

cfprApAdaptorFcPortStatsTxFramesDelta OBJECT-TYPE
    SYNTAX       Counter64
    MAX-ACCESS   read-only
    STATUS       current
    DESCRIPTION
        "Cisco Firepower adaptor:FcPortStats:txFramesDelta
        managed object property"
    ::= { cfprApAdaptorFcPortStatsEntry 24 }

cfprApAdaptorFcPortStatsTxFramesDeltaAvg OBJECT-TYPE
    SYNTAX       Unsigned64
    MAX-ACCESS   read-only
    STATUS       current
    DESCRIPTION
        "Cisco Firepower adaptor:FcPortStats:txFramesDeltaAvg
        managed object property"
    ::= { cfprApAdaptorFcPortStatsEntry 25 }

cfprApAdaptorFcPortStatsTxFramesDeltaMax OBJECT-TYPE
    SYNTAX       Unsigned64
    MAX-ACCESS   read-only
    STATUS       current
    DESCRIPTION
        "Cisco Firepower adaptor:FcPortStats:txFramesDeltaMax
        managed object property"
    ::= { cfprApAdaptorFcPortStatsEntry 26 }

cfprApAdaptorFcPortStatsTxFramesDeltaMin OBJECT-TYPE
    SYNTAX       Unsigned64
    MAX-ACCESS   read-only
    STATUS       current
    DESCRIPTION
        "Cisco Firepower adaptor:FcPortStats:txFramesDeltaMin
        managed object property"
    ::= { cfprApAdaptorFcPortStatsEntry 27 }

cfprApAdaptorFcPortStatsUpdate OBJECT-TYPE
    SYNTAX       Gauge32
    MAX-ACCESS   read-only
    STATUS       current
    DESCRIPTION
        "Cisco Firepower adaptor:FcPortStats:update managed
        object property"
    ::= { cfprApAdaptorFcPortStatsEntry 28 }

cfprApAdaptorFcPortStatsHistTable OBJECT-TYPE
    SYNTAX           SEQUENCE OF CfprApAdaptorFcPortStatsHistEntry
    MAX-ACCESS       not-accessible
    STATUS           current
    DESCRIPTION
        "Cisco Firepower adaptor:FcPortStatsHist managed object table"
    ::= { cfprApAdaptorObjects 50 }

cfprApAdaptorFcPortStatsHistEntry OBJECT-TYPE
    SYNTAX           CfprApAdaptorFcPortStatsHistEntry
    MAX-ACCESS       not-accessible
    STATUS           current
    DESCRIPTION
        "Entry for the cfprApAdaptorFcPortStatsHistTable table."
    INDEX { cfprApAdaptorFcPortStatsHistInstanceId }
    ::= { cfprApAdaptorFcPortStatsHistTable 1 }

CfprApAdaptorFcPortStatsHistEntry ::= SEQUENCE {
    cfprApAdaptorFcPortStatsHistInstanceId                           CfprApManagedObjectId,
    cfprApAdaptorFcPortStatsHistDn                                   CfprApManagedObjectDn,
    cfprApAdaptorFcPortStatsHistRn                                   SnmpAdminString,
    cfprApAdaptorFcPortStatsHistId                                   Unsigned64,
    cfprApAdaptorFcPortStatsHistMostRecent                           TruthValue,
    cfprApAdaptorFcPortStatsHistRxBadFrames                          Unsigned64,
    cfprApAdaptorFcPortStatsHistRxBadFramesDelta                     Unsigned64,
    cfprApAdaptorFcPortStatsHistRxBadFramesDeltaAvg                  Unsigned64,
    cfprApAdaptorFcPortStatsHistRxBadFramesDeltaMax                  Unsigned64,
    cfprApAdaptorFcPortStatsHistRxBadFramesDeltaMin                  Unsigned64,
    cfprApAdaptorFcPortStatsHistRxFrames                             Unsigned64,
    cfprApAdaptorFcPortStatsHistRxFramesDelta                        Unsigned64,
    cfprApAdaptorFcPortStatsHistRxFramesDeltaAvg                     Unsigned64,
    cfprApAdaptorFcPortStatsHistRxFramesDeltaMax                     Unsigned64,
    cfprApAdaptorFcPortStatsHistRxFramesDeltaMin                     Unsigned64,
    cfprApAdaptorFcPortStatsHistSuspect                              TruthValue,
    cfprApAdaptorFcPortStatsHistThresholded                          CfprApAdaptorFcPortStatsHistThresholded,
    cfprApAdaptorFcPortStatsHistTimeCollected                        DateAndTime,
    cfprApAdaptorFcPortStatsHistTxBadFrames                          Unsigned64,
    cfprApAdaptorFcPortStatsHistTxBadFramesDelta                     Unsigned64,
    cfprApAdaptorFcPortStatsHistTxBadFramesDeltaAvg                  Unsigned64,
    cfprApAdaptorFcPortStatsHistTxBadFramesDeltaMax                  Unsigned64,
    cfprApAdaptorFcPortStatsHistTxBadFramesDeltaMin                  Unsigned64,
    cfprApAdaptorFcPortStatsHistTxFrames                             Unsigned64,
    cfprApAdaptorFcPortStatsHistTxFramesDelta                        Unsigned64,
    cfprApAdaptorFcPortStatsHistTxFramesDeltaAvg                     Unsigned64,
    cfprApAdaptorFcPortStatsHistTxFramesDeltaMax                     Unsigned64,
    cfprApAdaptorFcPortStatsHistTxFramesDeltaMin                     Unsigned64
}

cfprApAdaptorFcPortStatsHistInstanceId OBJECT-TYPE
    SYNTAX       CfprApManagedObjectId
    MAX-ACCESS   not-accessible
    STATUS       current
    DESCRIPTION
        "Instance identifier of the managed object."
    ::= { cfprApAdaptorFcPortStatsHistEntry 1 }

cfprApAdaptorFcPortStatsHistDn OBJECT-TYPE
    SYNTAX       CfprApManagedObjectDn
    MAX-ACCESS   read-only
    STATUS       current
    DESCRIPTION
        "Cisco Firepower adaptor:FcPortStatsHist:dn managed
        object property"
    ::= { cfprApAdaptorFcPortStatsHistEntry 2 }

cfprApAdaptorFcPortStatsHistRn OBJECT-TYPE
    SYNTAX       SnmpAdminString
    MAX-ACCESS   read-only
    STATUS       current
    DESCRIPTION
        "Cisco Firepower adaptor:FcPortStatsHist:rn managed
        object property"
    ::= { cfprApAdaptorFcPortStatsHistEntry 3 }

cfprApAdaptorFcPortStatsHistId OBJECT-TYPE
    SYNTAX       Unsigned64
    MAX-ACCESS   read-only
    STATUS       current
    DESCRIPTION
        "Cisco Firepower adaptor:FcPortStatsHist:id managed
        object property"
    ::= { cfprApAdaptorFcPortStatsHistEntry 4 }

cfprApAdaptorFcPortStatsHistMostRecent OBJECT-TYPE
    SYNTAX       TruthValue
    MAX-ACCESS   read-only
    STATUS       current
    DESCRIPTION
        "Cisco Firepower adaptor:FcPortStatsHist:mostRecent
        managed object property"
    ::= { cfprApAdaptorFcPortStatsHistEntry 5 }

cfprApAdaptorFcPortStatsHistRxBadFrames OBJECT-TYPE
    SYNTAX       Unsigned64
    MAX-ACCESS   read-only
    STATUS       current
    DESCRIPTION
        "Cisco Firepower adaptor:FcPortStatsHist:rxBadFrames
        managed object property"
    ::= { cfprApAdaptorFcPortStatsHistEntry 6 }

cfprApAdaptorFcPortStatsHistRxBadFramesDelta OBJECT-TYPE
    SYNTAX       Unsigned64
    MAX-ACCESS   read-only
    STATUS       current
    DESCRIPTION
        "Cisco Firepower adaptor:FcPortStatsHist:rxBadFramesDelta
        managed object property"
    ::= { cfprApAdaptorFcPortStatsHistEntry 7 }

cfprApAdaptorFcPortStatsHistRxBadFramesDeltaAvg OBJECT-TYPE
    SYNTAX       Unsigned64
    MAX-ACCESS   read-only
    STATUS       current
    DESCRIPTION
        "Cisco Firepower adaptor:FcPortStatsHist:rxBadFramesDeltaAvg
        managed object property"
    ::= { cfprApAdaptorFcPortStatsHistEntry 8 }

cfprApAdaptorFcPortStatsHistRxBadFramesDeltaMax OBJECT-TYPE
    SYNTAX       Unsigned64
    MAX-ACCESS   read-only
    STATUS       current
    DESCRIPTION
        "Cisco Firepower adaptor:FcPortStatsHist:rxBadFramesDeltaMax
        managed object property"
    ::= { cfprApAdaptorFcPortStatsHistEntry 9 }

cfprApAdaptorFcPortStatsHistRxBadFramesDeltaMin OBJECT-TYPE
    SYNTAX       Unsigned64
    MAX-ACCESS   read-only
    STATUS       current
    DESCRIPTION
        "Cisco Firepower adaptor:FcPortStatsHist:rxBadFramesDeltaMin
        managed object property"
    ::= { cfprApAdaptorFcPortStatsHistEntry 10 }

cfprApAdaptorFcPortStatsHistRxFrames OBJECT-TYPE
    SYNTAX       Unsigned64
    MAX-ACCESS   read-only
    STATUS       current
    DESCRIPTION
        "Cisco Firepower adaptor:FcPortStatsHist:rxFrames
        managed object property"
    ::= { cfprApAdaptorFcPortStatsHistEntry 11 }

cfprApAdaptorFcPortStatsHistRxFramesDelta OBJECT-TYPE
    SYNTAX       Unsigned64
    MAX-ACCESS   read-only
    STATUS       current
    DESCRIPTION
        "Cisco Firepower adaptor:FcPortStatsHist:rxFramesDelta
        managed object property"
    ::= { cfprApAdaptorFcPortStatsHistEntry 12 }

cfprApAdaptorFcPortStatsHistRxFramesDeltaAvg OBJECT-TYPE
    SYNTAX       Unsigned64
    MAX-ACCESS   read-only
    STATUS       current
    DESCRIPTION
        "Cisco Firepower adaptor:FcPortStatsHist:rxFramesDeltaAvg
        managed object property"
    ::= { cfprApAdaptorFcPortStatsHistEntry 13 }

cfprApAdaptorFcPortStatsHistRxFramesDeltaMax OBJECT-TYPE
    SYNTAX       Unsigned64
    MAX-ACCESS   read-only
    STATUS       current
    DESCRIPTION
        "Cisco Firepower adaptor:FcPortStatsHist:rxFramesDeltaMax
        managed object property"
    ::= { cfprApAdaptorFcPortStatsHistEntry 14 }

cfprApAdaptorFcPortStatsHistRxFramesDeltaMin OBJECT-TYPE
    SYNTAX       Unsigned64
    MAX-ACCESS   read-only
    STATUS       current
    DESCRIPTION
        "Cisco Firepower adaptor:FcPortStatsHist:rxFramesDeltaMin
        managed object property"
    ::= { cfprApAdaptorFcPortStatsHistEntry 15 }

cfprApAdaptorFcPortStatsHistSuspect OBJECT-TYPE
    SYNTAX       TruthValue
    MAX-ACCESS   read-only
    STATUS       current
    DESCRIPTION
        "Cisco Firepower adaptor:FcPortStatsHist:suspect
        managed object property"
    ::= { cfprApAdaptorFcPortStatsHistEntry 16 }

cfprApAdaptorFcPortStatsHistThresholded OBJECT-TYPE
    SYNTAX       CfprApAdaptorFcPortStatsHistThresholded
    MAX-ACCESS   read-only
    STATUS       current
    DESCRIPTION
        "Cisco Firepower adaptor:FcPortStatsHist:thresholded
        managed object property"
    ::= { cfprApAdaptorFcPortStatsHistEntry 17 }

cfprApAdaptorFcPortStatsHistTimeCollected OBJECT-TYPE
    SYNTAX       DateAndTime
    MAX-ACCESS   read-only
    STATUS       current
    DESCRIPTION
        "Cisco Firepower adaptor:FcPortStatsHist:timeCollected
        managed object property"
    ::= { cfprApAdaptorFcPortStatsHistEntry 18 }

cfprApAdaptorFcPortStatsHistTxBadFrames OBJECT-TYPE
    SYNTAX       Unsigned64
    MAX-ACCESS   read-only
    STATUS       current
    DESCRIPTION
        "Cisco Firepower adaptor:FcPortStatsHist:txBadFrames
        managed object property"
    ::= { cfprApAdaptorFcPortStatsHistEntry 19 }

cfprApAdaptorFcPortStatsHistTxBadFramesDelta OBJECT-TYPE
    SYNTAX       Unsigned64
    MAX-ACCESS   read-only
    STATUS       current
    DESCRIPTION
        "Cisco Firepower adaptor:FcPortStatsHist:txBadFramesDelta
        managed object property"
    ::= { cfprApAdaptorFcPortStatsHistEntry 20 }

cfprApAdaptorFcPortStatsHistTxBadFramesDeltaAvg OBJECT-TYPE
    SYNTAX       Unsigned64
    MAX-ACCESS   read-only
    STATUS       current
    DESCRIPTION
        "Cisco Firepower adaptor:FcPortStatsHist:txBadFramesDeltaAvg
        managed object property"
    ::= { cfprApAdaptorFcPortStatsHistEntry 21 }

cfprApAdaptorFcPortStatsHistTxBadFramesDeltaMax OBJECT-TYPE
    SYNTAX       Unsigned64
    MAX-ACCESS   read-only
    STATUS       current
    DESCRIPTION
        "Cisco Firepower adaptor:FcPortStatsHist:txBadFramesDeltaMax
        managed object property"
    ::= { cfprApAdaptorFcPortStatsHistEntry 22 }

cfprApAdaptorFcPortStatsHistTxBadFramesDeltaMin OBJECT-TYPE
    SYNTAX       Unsigned64
    MAX-ACCESS   read-only
    STATUS       current
    DESCRIPTION
        "Cisco Firepower adaptor:FcPortStatsHist:txBadFramesDeltaMin
        managed object property"
    ::= { cfprApAdaptorFcPortStatsHistEntry 23 }

cfprApAdaptorFcPortStatsHistTxFrames OBJECT-TYPE
    SYNTAX       Unsigned64
    MAX-ACCESS   read-only
    STATUS       current
    DESCRIPTION
        "Cisco Firepower adaptor:FcPortStatsHist:txFrames
        managed object property"
    ::= { cfprApAdaptorFcPortStatsHistEntry 24 }

cfprApAdaptorFcPortStatsHistTxFramesDelta OBJECT-TYPE
    SYNTAX       Unsigned64
    MAX-ACCESS   read-only
    STATUS       current
    DESCRIPTION
        "Cisco Firepower adaptor:FcPortStatsHist:txFramesDelta
        managed object property"
    ::= { cfprApAdaptorFcPortStatsHistEntry 25 }

cfprApAdaptorFcPortStatsHistTxFramesDeltaAvg OBJECT-TYPE
    SYNTAX       Unsigned64
    MAX-ACCESS   read-only
    STATUS       current
    DESCRIPTION
        "Cisco Firepower adaptor:FcPortStatsHist:txFramesDeltaAvg
        managed object property"
    ::= { cfprApAdaptorFcPortStatsHistEntry 26 }

cfprApAdaptorFcPortStatsHistTxFramesDeltaMax OBJECT-TYPE
    SYNTAX       Unsigned64
    MAX-ACCESS   read-only
    STATUS       current
    DESCRIPTION
        "Cisco Firepower adaptor:FcPortStatsHist:txFramesDeltaMax
        managed object property"
    ::= { cfprApAdaptorFcPortStatsHistEntry 27 }

cfprApAdaptorFcPortStatsHistTxFramesDeltaMin OBJECT-TYPE
    SYNTAX       Unsigned64
    MAX-ACCESS   read-only
    STATUS       current
    DESCRIPTION
        "Cisco Firepower adaptor:FcPortStatsHist:txFramesDeltaMin
        managed object property"
    ::= { cfprApAdaptorFcPortStatsHistEntry 28 }

cfprApAdaptorFruCapProviderTable OBJECT-TYPE
    SYNTAX           SEQUENCE OF CfprApAdaptorFruCapProviderEntry
    MAX-ACCESS       not-accessible
    STATUS           current
    DESCRIPTION
        "Cisco Firepower adaptor:FruCapProvider managed object table"
    ::= { cfprApAdaptorObjects 53 }

cfprApAdaptorFruCapProviderEntry OBJECT-TYPE
    SYNTAX           CfprApAdaptorFruCapProviderEntry
    MAX-ACCESS       not-accessible
    STATUS           current
    DESCRIPTION
        "Entry for the cfprApAdaptorFruCapProviderTable table."
    INDEX { cfprApAdaptorFruCapProviderInstanceId }
    ::= { cfprApAdaptorFruCapProviderTable 1 }

CfprApAdaptorFruCapProviderEntry ::= SEQUENCE {
    cfprApAdaptorFruCapProviderInstanceId                            CfprApManagedObjectId,
    cfprApAdaptorFruCapProviderDn                                    CfprApManagedObjectDn,
    cfprApAdaptorFruCapProviderRn                                    SnmpAdminString,
    cfprApAdaptorFruCapProviderDeleted                               TruthValue,
    cfprApAdaptorFruCapProviderDeprecated                            TruthValue,
    cfprApAdaptorFruCapProviderElementLoadFailures                   Gauge32,
    cfprApAdaptorFruCapProviderElementsLoaded                        Gauge32,
    cfprApAdaptorFruCapProviderGencount                              Gauge32,
    cfprApAdaptorFruCapProviderLoadErrors                            Gauge32,
    cfprApAdaptorFruCapProviderLoadWarnings                          Gauge32,
    cfprApAdaptorFruCapProviderMgmtPlaneVer                          SnmpAdminString,
    cfprApAdaptorFruCapProviderModel                                 SnmpAdminString,
    cfprApAdaptorFruCapProviderPromCardType                          Gauge32,
    cfprApAdaptorFruCapProviderRevision                              SnmpAdminString,
    cfprApAdaptorFruCapProviderVendor                                SnmpAdminString
}

cfprApAdaptorFruCapProviderInstanceId OBJECT-TYPE
    SYNTAX       CfprApManagedObjectId
    MAX-ACCESS   not-accessible
    STATUS       current
    DESCRIPTION
        "Instance identifier of the managed object."
    ::= { cfprApAdaptorFruCapProviderEntry 1 }

cfprApAdaptorFruCapProviderDn OBJECT-TYPE
    SYNTAX       CfprApManagedObjectDn
    MAX-ACCESS   read-only
    STATUS       current
    DESCRIPTION
        "Cisco Firepower adaptor:FruCapProvider:dn managed
        object property"
    ::= { cfprApAdaptorFruCapProviderEntry 2 }

cfprApAdaptorFruCapProviderRn OBJECT-TYPE
    SYNTAX       SnmpAdminString
    MAX-ACCESS   read-only
    STATUS       current
    DESCRIPTION
        "Cisco Firepower adaptor:FruCapProvider:rn managed
        object property"
    ::= { cfprApAdaptorFruCapProviderEntry 3 }

cfprApAdaptorFruCapProviderDeleted OBJECT-TYPE
    SYNTAX       TruthValue
    MAX-ACCESS   read-only
    STATUS       current
    DESCRIPTION
        "Cisco Firepower adaptor:FruCapProvider:deleted
        managed object property"
    ::= { cfprApAdaptorFruCapProviderEntry 4 }

cfprApAdaptorFruCapProviderDeprecated OBJECT-TYPE
    SYNTAX       TruthValue
    MAX-ACCESS   read-only
    STATUS       current
    DESCRIPTION
        "Cisco Firepower adaptor:FruCapProvider:deprecated
        managed object property"
    ::= { cfprApAdaptorFruCapProviderEntry 5 }

cfprApAdaptorFruCapProviderElementLoadFailures OBJECT-TYPE
    SYNTAX       Gauge32
    MAX-ACCESS   read-only
    STATUS       current
    DESCRIPTION
        "Cisco Firepower adaptor:FruCapProvider:elementLoadFailures
        managed object property"
    ::= { cfprApAdaptorFruCapProviderEntry 6 }

cfprApAdaptorFruCapProviderElementsLoaded OBJECT-TYPE
    SYNTAX       Gauge32
    MAX-ACCESS   read-only
    STATUS       current
    DESCRIPTION
        "Cisco Firepower adaptor:FruCapProvider:elementsLoaded
        managed object property"
    ::= { cfprApAdaptorFruCapProviderEntry 7 }

cfprApAdaptorFruCapProviderGencount OBJECT-TYPE
    SYNTAX       Gauge32
    MAX-ACCESS   read-only
    STATUS       current
    DESCRIPTION
        "Cisco Firepower adaptor:FruCapProvider:gencount
        managed object property"
    ::= { cfprApAdaptorFruCapProviderEntry 8 }

cfprApAdaptorFruCapProviderLoadErrors OBJECT-TYPE
    SYNTAX       Gauge32
    MAX-ACCESS   read-only
    STATUS       current
    DESCRIPTION
        "Cisco Firepower adaptor:FruCapProvider:loadErrors
        managed object property"
    ::= { cfprApAdaptorFruCapProviderEntry 9 }

cfprApAdaptorFruCapProviderLoadWarnings OBJECT-TYPE
    SYNTAX       Gauge32
    MAX-ACCESS   read-only
    STATUS       current
    DESCRIPTION
        "Cisco Firepower adaptor:FruCapProvider:loadWarnings
        managed object property"
    ::= { cfprApAdaptorFruCapProviderEntry 10 }

cfprApAdaptorFruCapProviderMgmtPlaneVer OBJECT-TYPE
    SYNTAX       SnmpAdminString
    MAX-ACCESS   read-only
    STATUS       current
    DESCRIPTION
        "Cisco Firepower adaptor:FruCapProvider:mgmtPlaneVer
        managed object property"
    ::= { cfprApAdaptorFruCapProviderEntry 11 }

cfprApAdaptorFruCapProviderModel OBJECT-TYPE
    SYNTAX       SnmpAdminString
    MAX-ACCESS   read-only
    STATUS       current
    DESCRIPTION
        "Cisco Firepower adaptor:FruCapProvider:model managed
        object property"
    ::= { cfprApAdaptorFruCapProviderEntry 12 }

cfprApAdaptorFruCapProviderPromCardType OBJECT-TYPE
    SYNTAX       Gauge32
    MAX-ACCESS   read-only
    STATUS       current
    DESCRIPTION
        "Cisco Firepower adaptor:FruCapProvider:promCardType
        managed object property"
    ::= { cfprApAdaptorFruCapProviderEntry 13 }

cfprApAdaptorFruCapProviderRevision OBJECT-TYPE
    SYNTAX       SnmpAdminString
    MAX-ACCESS   read-only
    STATUS       current
    DESCRIPTION
        "Cisco Firepower adaptor:FruCapProvider:revision
        managed object property"
    ::= { cfprApAdaptorFruCapProviderEntry 14 }

cfprApAdaptorFruCapProviderVendor OBJECT-TYPE
    SYNTAX       SnmpAdminString
    MAX-ACCESS   read-only
    STATUS       current
    DESCRIPTION
        "Cisco Firepower adaptor:FruCapProvider:vendor
        managed object property"
    ::= { cfprApAdaptorFruCapProviderEntry 15 }

cfprApAdaptorFruCapRefTable OBJECT-TYPE
    SYNTAX           SEQUENCE OF CfprApAdaptorFruCapRefEntry
    MAX-ACCESS       not-accessible
    STATUS           current
    DESCRIPTION
        "Cisco Firepower adaptor:FruCapRef managed object table"
    ::= { cfprApAdaptorObjects 54 }

cfprApAdaptorFruCapRefEntry OBJECT-TYPE
    SYNTAX           CfprApAdaptorFruCapRefEntry
    MAX-ACCESS       not-accessible
    STATUS           current
    DESCRIPTION
        "Entry for the cfprApAdaptorFruCapRefTable table."
    INDEX { cfprApAdaptorFruCapRefInstanceId }
    ::= { cfprApAdaptorFruCapRefTable 1 }

CfprApAdaptorFruCapRefEntry ::= SEQUENCE {
    cfprApAdaptorFruCapRefInstanceId                                 CfprApManagedObjectId,
    cfprApAdaptorFruCapRefDn                                         CfprApManagedObjectDn,
    cfprApAdaptorFruCapRefRn                                         SnmpAdminString,
    cfprApAdaptorFruCapRefIsSupported                                CfprApAdaptorDefaultAction,
    cfprApAdaptorFruCapRefModel                                      SnmpAdminString,
    cfprApAdaptorFruCapRefRevision                                   SnmpAdminString,
    cfprApAdaptorFruCapRefVendor                                     SnmpAdminString
}

cfprApAdaptorFruCapRefInstanceId OBJECT-TYPE
    SYNTAX       CfprApManagedObjectId
    MAX-ACCESS   not-accessible
    STATUS       current
    DESCRIPTION
        "Instance identifier of the managed object."
    ::= { cfprApAdaptorFruCapRefEntry 1 }

cfprApAdaptorFruCapRefDn OBJECT-TYPE
    SYNTAX       CfprApManagedObjectDn
    MAX-ACCESS   read-only
    STATUS       current
    DESCRIPTION
        "Cisco Firepower adaptor:FruCapRef:dn managed object property"
    ::= { cfprApAdaptorFruCapRefEntry 2 }

cfprApAdaptorFruCapRefRn OBJECT-TYPE
    SYNTAX       SnmpAdminString
    MAX-ACCESS   read-only
    STATUS       current
    DESCRIPTION
        "Cisco Firepower adaptor:FruCapRef:rn managed object property"
    ::= { cfprApAdaptorFruCapRefEntry 3 }

cfprApAdaptorFruCapRefIsSupported OBJECT-TYPE
    SYNTAX       CfprApAdaptorDefaultAction
    MAX-ACCESS   read-only
    STATUS       current
    DESCRIPTION
        "Cisco Firepower adaptor:FruCapRef:isSupported
        managed object property"
    ::= { cfprApAdaptorFruCapRefEntry 4 }

cfprApAdaptorFruCapRefModel OBJECT-TYPE
    SYNTAX       SnmpAdminString
    MAX-ACCESS   read-only
    STATUS       current
    DESCRIPTION
        "Cisco Firepower adaptor:FruCapRef:model managed object property"
    ::= { cfprApAdaptorFruCapRefEntry 5 }

cfprApAdaptorFruCapRefRevision OBJECT-TYPE
    SYNTAX       SnmpAdminString
    MAX-ACCESS   read-only
    STATUS       current
    DESCRIPTION
        "Cisco Firepower adaptor:FruCapRef:revision managed
        object property"
    ::= { cfprApAdaptorFruCapRefEntry 6 }

cfprApAdaptorFruCapRefVendor OBJECT-TYPE
    SYNTAX       SnmpAdminString
    MAX-ACCESS   read-only
    STATUS       current
    DESCRIPTION
        "Cisco Firepower adaptor:FruCapRef:vendor managed object property"
    ::= { cfprApAdaptorFruCapRefEntry 7 }

cfprApAdaptorFwCapProviderTable OBJECT-TYPE
    SYNTAX           SEQUENCE OF CfprApAdaptorFwCapProviderEntry
    MAX-ACCESS       not-accessible
    STATUS           current
    DESCRIPTION
        "Cisco Firepower adaptor:FwCapProvider managed object table"
    ::= { cfprApAdaptorObjects 55 }

cfprApAdaptorFwCapProviderEntry OBJECT-TYPE
    SYNTAX           CfprApAdaptorFwCapProviderEntry
    MAX-ACCESS       not-accessible
    STATUS           current
    DESCRIPTION
        "Entry for the cfprApAdaptorFwCapProviderTable table."
    INDEX { cfprApAdaptorFwCapProviderInstanceId }
    ::= { cfprApAdaptorFwCapProviderTable 1 }

CfprApAdaptorFwCapProviderEntry ::= SEQUENCE {
    cfprApAdaptorFwCapProviderInstanceId                             CfprApManagedObjectId,
    cfprApAdaptorFwCapProviderDn                                     CfprApManagedObjectDn,
    cfprApAdaptorFwCapProviderRn                                     SnmpAdminString,
    cfprApAdaptorFwCapProviderDeleted                                TruthValue,
    cfprApAdaptorFwCapProviderDeprecated                             TruthValue,
    cfprApAdaptorFwCapProviderElementLoadFailures                    Gauge32,
    cfprApAdaptorFwCapProviderElementsLoaded                         Gauge32,
    cfprApAdaptorFwCapProviderGencount                               Gauge32,
    cfprApAdaptorFwCapProviderLoadErrors                             Gauge32,
    cfprApAdaptorFwCapProviderLoadWarnings                           Gauge32,
    cfprApAdaptorFwCapProviderMgmtPlaneVer                           SnmpAdminString,
    cfprApAdaptorFwCapProviderModel                                  SnmpAdminString,
    cfprApAdaptorFwCapProviderVendor                                 SnmpAdminString,
    cfprApAdaptorFwCapProviderVersion                                SnmpAdminString
}

cfprApAdaptorFwCapProviderInstanceId OBJECT-TYPE
    SYNTAX       CfprApManagedObjectId
    MAX-ACCESS   not-accessible
    STATUS       current
    DESCRIPTION
        "Instance identifier of the managed object."
    ::= { cfprApAdaptorFwCapProviderEntry 1 }

cfprApAdaptorFwCapProviderDn OBJECT-TYPE
    SYNTAX       CfprApManagedObjectDn
    MAX-ACCESS   read-only
    STATUS       current
    DESCRIPTION
        "Cisco Firepower adaptor:FwCapProvider:dn managed object property"
    ::= { cfprApAdaptorFwCapProviderEntry 2 }

cfprApAdaptorFwCapProviderRn OBJECT-TYPE
    SYNTAX       SnmpAdminString
    MAX-ACCESS   read-only
    STATUS       current
    DESCRIPTION
        "Cisco Firepower adaptor:FwCapProvider:rn managed object property"
    ::= { cfprApAdaptorFwCapProviderEntry 3 }

cfprApAdaptorFwCapProviderDeleted OBJECT-TYPE
    SYNTAX       TruthValue
    MAX-ACCESS   read-only
    STATUS       current
    DESCRIPTION
        "Cisco Firepower adaptor:FwCapProvider:deleted
        managed object property"
    ::= { cfprApAdaptorFwCapProviderEntry 4 }

cfprApAdaptorFwCapProviderDeprecated OBJECT-TYPE
    SYNTAX       TruthValue
    MAX-ACCESS   read-only
    STATUS       current
    DESCRIPTION
        "Cisco Firepower adaptor:FwCapProvider:deprecated
        managed object property"
    ::= { cfprApAdaptorFwCapProviderEntry 5 }

cfprApAdaptorFwCapProviderElementLoadFailures OBJECT-TYPE
    SYNTAX       Gauge32
    MAX-ACCESS   read-only
    STATUS       current
    DESCRIPTION
        "Cisco Firepower adaptor:FwCapProvider:elementLoadFailures
        managed object property"
    ::= { cfprApAdaptorFwCapProviderEntry 6 }

cfprApAdaptorFwCapProviderElementsLoaded OBJECT-TYPE
    SYNTAX       Gauge32
    MAX-ACCESS   read-only
    STATUS       current
    DESCRIPTION
        "Cisco Firepower adaptor:FwCapProvider:elementsLoaded
        managed object property"
    ::= { cfprApAdaptorFwCapProviderEntry 7 }

cfprApAdaptorFwCapProviderGencount OBJECT-TYPE
    SYNTAX       Gauge32
    MAX-ACCESS   read-only
    STATUS       current
    DESCRIPTION
        "Cisco Firepower adaptor:FwCapProvider:gencount
        managed object property"
    ::= { cfprApAdaptorFwCapProviderEntry 8 }

cfprApAdaptorFwCapProviderLoadErrors OBJECT-TYPE
    SYNTAX       Gauge32
    MAX-ACCESS   read-only
    STATUS       current
    DESCRIPTION
        "Cisco Firepower adaptor:FwCapProvider:loadErrors
        managed object property"
    ::= { cfprApAdaptorFwCapProviderEntry 9 }

cfprApAdaptorFwCapProviderLoadWarnings OBJECT-TYPE
    SYNTAX       Gauge32
    MAX-ACCESS   read-only
    STATUS       current
    DESCRIPTION
        "Cisco Firepower adaptor:FwCapProvider:loadWarnings
        managed object property"
    ::= { cfprApAdaptorFwCapProviderEntry 10 }

cfprApAdaptorFwCapProviderMgmtPlaneVer OBJECT-TYPE
    SYNTAX       SnmpAdminString
    MAX-ACCESS   read-only
    STATUS       current
    DESCRIPTION
        "Cisco Firepower adaptor:FwCapProvider:mgmtPlaneVer
        managed object property"
    ::= { cfprApAdaptorFwCapProviderEntry 11 }

cfprApAdaptorFwCapProviderModel OBJECT-TYPE
    SYNTAX       SnmpAdminString
    MAX-ACCESS   read-only
    STATUS       current
    DESCRIPTION
        "Cisco Firepower adaptor:FwCapProvider:model managed
        object property"
    ::= { cfprApAdaptorFwCapProviderEntry 12 }

cfprApAdaptorFwCapProviderVendor OBJECT-TYPE
    SYNTAX       SnmpAdminString
    MAX-ACCESS   read-only
    STATUS       current
    DESCRIPTION
        "Cisco Firepower adaptor:FwCapProvider:vendor managed
        object property"
    ::= { cfprApAdaptorFwCapProviderEntry 13 }

cfprApAdaptorFwCapProviderVersion OBJECT-TYPE
    SYNTAX       SnmpAdminString
    MAX-ACCESS   read-only
    STATUS       current
    DESCRIPTION
        "Cisco Firepower adaptor:FwCapProvider:version
        managed object property"
    ::= { cfprApAdaptorFwCapProviderEntry 14 }

cfprApAdaptorHostEthIfTable OBJECT-TYPE
    SYNTAX           SEQUENCE OF CfprApAdaptorHostEthIfEntry
    MAX-ACCESS       not-accessible
    STATUS           current
    DESCRIPTION
        "Cisco Firepower adaptor:HostEthIf managed object table"
    ::= { cfprApAdaptorObjects 56 }

cfprApAdaptorHostEthIfEntry OBJECT-TYPE
    SYNTAX           CfprApAdaptorHostEthIfEntry
    MAX-ACCESS       not-accessible
    STATUS           current
    DESCRIPTION
        "Entry for the cfprApAdaptorHostEthIfTable table."
    INDEX { cfprApAdaptorHostEthIfInstanceId }
    ::= { cfprApAdaptorHostEthIfTable 1 }

CfprApAdaptorHostEthIfEntry ::= SEQUENCE {
    cfprApAdaptorHostEthIfInstanceId                                 CfprApManagedObjectId,
    cfprApAdaptorHostEthIfDn                                         CfprApManagedObjectDn,
    cfprApAdaptorHostEthIfRn                                         SnmpAdminString,
    cfprApAdaptorHostEthIfAdminState                                 CfprApAdaptorHostIfAdminState,
    cfprApAdaptorHostEthIfBootDev                                    CfprApAdaptorHostIfBootDev,
    cfprApAdaptorHostEthIfChassisId                                  Gauge32,
    cfprApAdaptorHostEthIfDiscovery                                  CfprApEtherSatelliteConnectionDisc,
    cfprApAdaptorHostEthIfEpDn                                       SnmpAdminString,
    cfprApAdaptorHostEthIfFltAggr                                    Unsigned64,
    cfprApAdaptorHostEthIfFsmDescr                                   SnmpAdminString,
    cfprApAdaptorHostEthIfFsmPrev                                    SnmpAdminString,
    cfprApAdaptorHostEthIfFsmProgr                                   Gauge32,
    cfprApAdaptorHostEthIfFsmRmtInvErrCode                           Gauge32,
    cfprApAdaptorHostEthIfFsmRmtInvErrDescr                          SnmpAdminString,
    cfprApAdaptorHostEthIfFsmRmtInvRslt                              CfprApConditionRemoteInvRslt,
    cfprApAdaptorHostEthIfFsmStageDescr                              SnmpAdminString,
    cfprApAdaptorHostEthIfFsmStamp                                   DateAndTime,
    cfprApAdaptorHostEthIfFsmStatus                                  SnmpAdminString,
    cfprApAdaptorHostEthIfFsmTry                                     Gauge32,
    cfprApAdaptorHostEthIfHostPort                                   CfprApAdaptorHostEthIfHostPort,
    cfprApAdaptorHostEthIfId                                         Gauge32,
    cfprApAdaptorHostEthIfIfRole                                     CfprApNetworkPortRole,
    cfprApAdaptorHostEthIfIfType                                     CfprApNetworkPhysEpIfType,
    cfprApAdaptorHostEthIfLc                                         CfprApFsmLifecycle,
    cfprApAdaptorHostEthIfLinkState                                  CfprApAdaptorLinkState,
    cfprApAdaptorHostEthIfLocale                                     CfprApNetworkLocale,
    cfprApAdaptorHostEthIfMac                                        MacAddress,
    cfprApAdaptorHostEthIfModel                                      SnmpAdminString,
    cfprApAdaptorHostEthIfMtu                                        Gauge32,
    cfprApAdaptorHostEthIfName                                       SnmpAdminString,
    cfprApAdaptorHostEthIfOperQualifierReason                        SnmpAdminString,
    cfprApAdaptorHostEthIfOperState                                  CfprApEquipmentOperability,
    cfprApAdaptorHostEthIfOperability                                CfprApEquipmentOperability,
    cfprApAdaptorHostEthIfOrder                                      Gauge32,
    cfprApAdaptorHostEthIfOriginalMac                                MacAddress,
    cfprApAdaptorHostEthIfPciAddr                                    SnmpAdminString,
    cfprApAdaptorHostEthIfPciFunc                                    Gauge32,
    cfprApAdaptorHostEthIfPciSlot                                    Gauge32,
    cfprApAdaptorHostEthIfPeerChassisId                              Gauge32,
    cfprApAdaptorHostEthIfPeerDn                                     SnmpAdminString,
    cfprApAdaptorHostEthIfPeerPortId                                 Gauge32,
    cfprApAdaptorHostEthIfPeerSlotId                                 Gauge32,
    cfprApAdaptorHostEthIfPerf                                       CfprApEquipmentSensorThresholdStatus,
    cfprApAdaptorHostEthIfPfDn                                       SnmpAdminString,
    cfprApAdaptorHostEthIfPortId                                     Gauge32,
    cfprApAdaptorHostEthIfPower                                      CfprApEquipmentPowerState,
    cfprApAdaptorHostEthIfPresence                                   CfprApEquipmentPresence,
    cfprApAdaptorHostEthIfPurpose                                    CfprApAdaptorPurpose,
    cfprApAdaptorHostEthIfRevision                                   SnmpAdminString,
    cfprApAdaptorHostEthIfSerial                                     SnmpAdminString,
    cfprApAdaptorHostEthIfServiceState                               CfprApAdaptorServiceState,
    cfprApAdaptorHostEthIfSide                                       CfprApNetworkSide,
    cfprApAdaptorHostEthIfSlotId                                     Gauge32,
    cfprApAdaptorHostEthIfSwitchId                                   CfprApNetworkSwitchId,
    cfprApAdaptorHostEthIfThermal                                    CfprApEquipmentSensorThresholdStatus,
    cfprApAdaptorHostEthIfTransport                                  CfprApNetworkTransport,
    cfprApAdaptorHostEthIfType                                       CfprApNetworkConnectionType,
    cfprApAdaptorHostEthIfVendor                                     SnmpAdminString,
    cfprApAdaptorHostEthIfVirtualizationPreference                   CfprApVnicVirtualizationPreferenceType,
    cfprApAdaptorHostEthIfVnicDn                                     SnmpAdminString,
    cfprApAdaptorHostEthIfVoltage                                    CfprApEquipmentSensorThresholdStatus
}

cfprApAdaptorHostEthIfInstanceId OBJECT-TYPE
    SYNTAX       CfprApManagedObjectId
    MAX-ACCESS   not-accessible
    STATUS       current
    DESCRIPTION
        "Instance identifier of the managed object."
    ::= { cfprApAdaptorHostEthIfEntry 1 }

cfprApAdaptorHostEthIfDn OBJECT-TYPE
    SYNTAX       CfprApManagedObjectDn
    MAX-ACCESS   read-only
    STATUS       current
    DESCRIPTION
        "Cisco Firepower adaptor:HostEthIf:dn managed object property"
    ::= { cfprApAdaptorHostEthIfEntry 2 }

cfprApAdaptorHostEthIfRn OBJECT-TYPE
    SYNTAX       SnmpAdminString
    MAX-ACCESS   read-only
    STATUS       current
    DESCRIPTION
        "Cisco Firepower adaptor:HostEthIf:rn managed object property"
    ::= { cfprApAdaptorHostEthIfEntry 3 }

cfprApAdaptorHostEthIfAdminState OBJECT-TYPE
    SYNTAX       CfprApAdaptorHostIfAdminState
    MAX-ACCESS   read-only
    STATUS       current
    DESCRIPTION
        "Cisco Firepower adaptor:HostEthIf:adminState managed
        object property"
    ::= { cfprApAdaptorHostEthIfEntry 4 }

cfprApAdaptorHostEthIfBootDev OBJECT-TYPE
    SYNTAX       CfprApAdaptorHostIfBootDev
    MAX-ACCESS   read-only
    STATUS       current
    DESCRIPTION
        "Cisco Firepower adaptor:HostEthIf:bootDev managed
        object property"
    ::= { cfprApAdaptorHostEthIfEntry 5 }

cfprApAdaptorHostEthIfChassisId OBJECT-TYPE
    SYNTAX       Gauge32
    MAX-ACCESS   read-only
    STATUS       current
    DESCRIPTION
        "Cisco Firepower adaptor:HostEthIf:chassisId managed
        object property"
    ::= { cfprApAdaptorHostEthIfEntry 6 }

cfprApAdaptorHostEthIfDiscovery OBJECT-TYPE
    SYNTAX       CfprApEtherSatelliteConnectionDisc
    MAX-ACCESS   read-only
    STATUS       current
    DESCRIPTION
        "Cisco Firepower adaptor:HostEthIf:discovery managed
        object property"
    ::= { cfprApAdaptorHostEthIfEntry 7 }

cfprApAdaptorHostEthIfEpDn OBJECT-TYPE
    SYNTAX       SnmpAdminString
    MAX-ACCESS   read-only
    STATUS       current
    DESCRIPTION
        "Cisco Firepower adaptor:HostEthIf:epDn managed object property"
    ::= { cfprApAdaptorHostEthIfEntry 8 }

cfprApAdaptorHostEthIfFltAggr OBJECT-TYPE
    SYNTAX       Unsigned64
    MAX-ACCESS   read-only
    STATUS       current
    DESCRIPTION
        "Cisco Firepower adaptor:HostEthIf:fltAggr managed
        object property"
    ::= { cfprApAdaptorHostEthIfEntry 9 }

cfprApAdaptorHostEthIfFsmDescr OBJECT-TYPE
    SYNTAX       SnmpAdminString
    MAX-ACCESS   read-only
    STATUS       current
    DESCRIPTION
        "Cisco Firepower adaptor:HostEthIf:fsmDescr managed
        object property"
    ::= { cfprApAdaptorHostEthIfEntry 10 }

cfprApAdaptorHostEthIfFsmPrev OBJECT-TYPE
    SYNTAX       SnmpAdminString
    MAX-ACCESS   read-only
    STATUS       current
    DESCRIPTION
        "Cisco Firepower adaptor:HostEthIf:fsmPrev managed
        object property"
    ::= { cfprApAdaptorHostEthIfEntry 11 }

cfprApAdaptorHostEthIfFsmProgr OBJECT-TYPE
    SYNTAX       Gauge32
    MAX-ACCESS   read-only
    STATUS       current
    DESCRIPTION
        "Cisco Firepower adaptor:HostEthIf:fsmProgr managed
        object property"
    ::= { cfprApAdaptorHostEthIfEntry 12 }

cfprApAdaptorHostEthIfFsmRmtInvErrCode OBJECT-TYPE
    SYNTAX       Gauge32
    MAX-ACCESS   read-only
    STATUS       current
    DESCRIPTION
        "Cisco Firepower adaptor:HostEthIf:fsmRmtInvErrCode
        managed object property"
    ::= { cfprApAdaptorHostEthIfEntry 13 }

cfprApAdaptorHostEthIfFsmRmtInvErrDescr OBJECT-TYPE
    SYNTAX       SnmpAdminString
    MAX-ACCESS   read-only
    STATUS       current
    DESCRIPTION
        "Cisco Firepower adaptor:HostEthIf:fsmRmtInvErrDescr
        managed object property"
    ::= { cfprApAdaptorHostEthIfEntry 14 }

cfprApAdaptorHostEthIfFsmRmtInvRslt OBJECT-TYPE
    SYNTAX       CfprApConditionRemoteInvRslt
    MAX-ACCESS   read-only
    STATUS       current
    DESCRIPTION
        "Cisco Firepower adaptor:HostEthIf:fsmRmtInvRslt
        managed object property"
    ::= { cfprApAdaptorHostEthIfEntry 15 }

cfprApAdaptorHostEthIfFsmStageDescr OBJECT-TYPE
    SYNTAX       SnmpAdminString
    MAX-ACCESS   read-only
    STATUS       current
    DESCRIPTION
        "Cisco Firepower adaptor:HostEthIf:fsmStageDescr
        managed object property"
    ::= { cfprApAdaptorHostEthIfEntry 16 }

cfprApAdaptorHostEthIfFsmStamp OBJECT-TYPE
    SYNTAX       DateAndTime
    MAX-ACCESS   read-only
    STATUS       current
    DESCRIPTION
        "Cisco Firepower adaptor:HostEthIf:fsmStamp managed
        object property"
    ::= { cfprApAdaptorHostEthIfEntry 17 }

cfprApAdaptorHostEthIfFsmStatus OBJECT-TYPE
    SYNTAX       SnmpAdminString
    MAX-ACCESS   read-only
    STATUS       current
    DESCRIPTION
        "Cisco Firepower adaptor:HostEthIf:fsmStatus managed
        object property"
    ::= { cfprApAdaptorHostEthIfEntry 18 }

cfprApAdaptorHostEthIfFsmTry OBJECT-TYPE
    SYNTAX       Gauge32
    MAX-ACCESS   read-only
    STATUS       current
    DESCRIPTION
        "Cisco Firepower adaptor:HostEthIf:fsmTry managed object property"
    ::= { cfprApAdaptorHostEthIfEntry 19 }

cfprApAdaptorHostEthIfHostPort OBJECT-TYPE
    SYNTAX       CfprApAdaptorHostEthIfHostPort
    MAX-ACCESS   read-only
    STATUS       current
    DESCRIPTION
        "Cisco Firepower adaptor:HostEthIf:hostPort managed
        object property"
    ::= { cfprApAdaptorHostEthIfEntry 20 }

cfprApAdaptorHostEthIfId OBJECT-TYPE
    SYNTAX       Gauge32
    MAX-ACCESS   read-only
    STATUS       current
    DESCRIPTION
        "Cisco Firepower adaptor:HostEthIf:id managed object property"
    ::= { cfprApAdaptorHostEthIfEntry 21 }

cfprApAdaptorHostEthIfIfRole OBJECT-TYPE
    SYNTAX       CfprApNetworkPortRole
    MAX-ACCESS   read-only
    STATUS       current
    DESCRIPTION
        "Cisco Firepower adaptor:HostEthIf:ifRole managed object property"
    ::= { cfprApAdaptorHostEthIfEntry 22 }

cfprApAdaptorHostEthIfIfType OBJECT-TYPE
    SYNTAX       CfprApNetworkPhysEpIfType
    MAX-ACCESS   read-only
    STATUS       current
    DESCRIPTION
        "Cisco Firepower adaptor:HostEthIf:ifType managed object property"
    ::= { cfprApAdaptorHostEthIfEntry 23 }

cfprApAdaptorHostEthIfLc OBJECT-TYPE
    SYNTAX       CfprApFsmLifecycle
    MAX-ACCESS   read-only
    STATUS       current
    DESCRIPTION
        "Cisco Firepower adaptor:HostEthIf:lc managed object property"
    ::= { cfprApAdaptorHostEthIfEntry 24 }

cfprApAdaptorHostEthIfLinkState OBJECT-TYPE
    SYNTAX       CfprApAdaptorLinkState
    MAX-ACCESS   read-only
    STATUS       current
    DESCRIPTION
        "Cisco Firepower adaptor:HostEthIf:linkState managed
        object property"
    ::= { cfprApAdaptorHostEthIfEntry 25 }

cfprApAdaptorHostEthIfLocale OBJECT-TYPE
    SYNTAX       CfprApNetworkLocale
    MAX-ACCESS   read-only
    STATUS       current
    DESCRIPTION
        "Cisco Firepower adaptor:HostEthIf:locale managed object property"
    ::= { cfprApAdaptorHostEthIfEntry 26 }

cfprApAdaptorHostEthIfMac OBJECT-TYPE
    SYNTAX       MacAddress
    MAX-ACCESS   read-only
    STATUS       current
    DESCRIPTION
        "Cisco Firepower adaptor:HostEthIf:mac managed object property"
    ::= { cfprApAdaptorHostEthIfEntry 27 }

cfprApAdaptorHostEthIfModel OBJECT-TYPE
    SYNTAX       SnmpAdminString
    MAX-ACCESS   read-only
    STATUS       current
    DESCRIPTION
        "Cisco Firepower adaptor:HostEthIf:model managed object property"
    ::= { cfprApAdaptorHostEthIfEntry 28 }

cfprApAdaptorHostEthIfMtu OBJECT-TYPE
    SYNTAX       Gauge32
    MAX-ACCESS   read-only
    STATUS       current
    DESCRIPTION
        "Cisco Firepower adaptor:HostEthIf:mtu managed object property"
    ::= { cfprApAdaptorHostEthIfEntry 29 }

cfprApAdaptorHostEthIfName OBJECT-TYPE
    SYNTAX       SnmpAdminString
    MAX-ACCESS   read-only
    STATUS       current
    DESCRIPTION
        "Cisco Firepower adaptor:HostEthIf:name managed object property"
    ::= { cfprApAdaptorHostEthIfEntry 30 }

cfprApAdaptorHostEthIfOperQualifierReason OBJECT-TYPE
    SYNTAX       SnmpAdminString
    MAX-ACCESS   read-only
    STATUS       current
    DESCRIPTION
        "Cisco Firepower adaptor:HostEthIf:operQualifierReason
        managed object property"
    ::= { cfprApAdaptorHostEthIfEntry 31 }

cfprApAdaptorHostEthIfOperState OBJECT-TYPE
    SYNTAX       CfprApEquipmentOperability
    MAX-ACCESS   read-only
    STATUS       current
    DESCRIPTION
        "Cisco Firepower adaptor:HostEthIf:operState managed
        object property"
    ::= { cfprApAdaptorHostEthIfEntry 32 }

cfprApAdaptorHostEthIfOperability OBJECT-TYPE
    SYNTAX       CfprApEquipmentOperability
    MAX-ACCESS   read-only
    STATUS       current
    DESCRIPTION
        "Cisco Firepower adaptor:HostEthIf:operability
        managed object property"
    ::= { cfprApAdaptorHostEthIfEntry 33 }

cfprApAdaptorHostEthIfOrder OBJECT-TYPE
    SYNTAX       Gauge32
    MAX-ACCESS   read-only
    STATUS       current
    DESCRIPTION
        "Cisco Firepower adaptor:HostEthIf:order managed object property"
    ::= { cfprApAdaptorHostEthIfEntry 34 }

cfprApAdaptorHostEthIfOriginalMac OBJECT-TYPE
    SYNTAX       MacAddress
    MAX-ACCESS   read-only
    STATUS       current
    DESCRIPTION
        "Cisco Firepower adaptor:HostEthIf:originalMac
        managed object property"
    ::= { cfprApAdaptorHostEthIfEntry 35 }

cfprApAdaptorHostEthIfPciAddr OBJECT-TYPE
    SYNTAX       SnmpAdminString
    MAX-ACCESS   read-only
    STATUS       current
    DESCRIPTION
        "Cisco Firepower adaptor:HostEthIf:pciAddr managed
        object property"
    ::= { cfprApAdaptorHostEthIfEntry 36 }

cfprApAdaptorHostEthIfPciFunc OBJECT-TYPE
    SYNTAX       Gauge32
    MAX-ACCESS   read-only
    STATUS       current
    DESCRIPTION
        "Cisco Firepower adaptor:HostEthIf:pciFunc managed
        object property"
    ::= { cfprApAdaptorHostEthIfEntry 37 }

cfprApAdaptorHostEthIfPciSlot OBJECT-TYPE
    SYNTAX       Gauge32
    MAX-ACCESS   read-only
    STATUS       current
    DESCRIPTION
        "Cisco Firepower adaptor:HostEthIf:pciSlot managed
        object property"
    ::= { cfprApAdaptorHostEthIfEntry 38 }

cfprApAdaptorHostEthIfPeerChassisId OBJECT-TYPE
    SYNTAX       Gauge32
    MAX-ACCESS   read-only
    STATUS       current
    DESCRIPTION
        "Cisco Firepower adaptor:HostEthIf:peerChassisId
        managed object property"
    ::= { cfprApAdaptorHostEthIfEntry 39 }

cfprApAdaptorHostEthIfPeerDn OBJECT-TYPE
    SYNTAX       SnmpAdminString
    MAX-ACCESS   read-only
    STATUS       current
    DESCRIPTION
        "Cisco Firepower adaptor:HostEthIf:peerDn managed object property"
    ::= { cfprApAdaptorHostEthIfEntry 40 }

cfprApAdaptorHostEthIfPeerPortId OBJECT-TYPE
    SYNTAX       Gauge32
    MAX-ACCESS   read-only
    STATUS       current
    DESCRIPTION
        "Cisco Firepower adaptor:HostEthIf:peerPortId managed
        object property"
    ::= { cfprApAdaptorHostEthIfEntry 41 }

cfprApAdaptorHostEthIfPeerSlotId OBJECT-TYPE
    SYNTAX       Gauge32
    MAX-ACCESS   read-only
    STATUS       current
    DESCRIPTION
        "Cisco Firepower adaptor:HostEthIf:peerSlotId managed
        object property"
    ::= { cfprApAdaptorHostEthIfEntry 42 }

cfprApAdaptorHostEthIfPerf OBJECT-TYPE
    SYNTAX       CfprApEquipmentSensorThresholdStatus
    MAX-ACCESS   read-only
    STATUS       current
    DESCRIPTION
        "Cisco Firepower adaptor:HostEthIf:perf managed object property"
    ::= { cfprApAdaptorHostEthIfEntry 43 }

cfprApAdaptorHostEthIfPfDn OBJECT-TYPE
    SYNTAX       SnmpAdminString
    MAX-ACCESS   read-only
    STATUS       current
    DESCRIPTION
        "Cisco Firepower adaptor:HostEthIf:pfDn managed object property"
    ::= { cfprApAdaptorHostEthIfEntry 44 }

cfprApAdaptorHostEthIfPortId OBJECT-TYPE
    SYNTAX       Gauge32
    MAX-ACCESS   read-only
    STATUS       current
    DESCRIPTION
        "Cisco Firepower adaptor:HostEthIf:portId managed object property"
    ::= { cfprApAdaptorHostEthIfEntry 45 }

cfprApAdaptorHostEthIfPower OBJECT-TYPE
    SYNTAX       CfprApEquipmentPowerState
    MAX-ACCESS   read-only
    STATUS       current
    DESCRIPTION
        "Cisco Firepower adaptor:HostEthIf:power managed object property"
    ::= { cfprApAdaptorHostEthIfEntry 46 }

cfprApAdaptorHostEthIfPresence OBJECT-TYPE
    SYNTAX       CfprApEquipmentPresence
    MAX-ACCESS   read-only
    STATUS       current
    DESCRIPTION
        "Cisco Firepower adaptor:HostEthIf:presence managed
        object property"
    ::= { cfprApAdaptorHostEthIfEntry 47 }

cfprApAdaptorHostEthIfPurpose OBJECT-TYPE
    SYNTAX       CfprApAdaptorPurpose
    MAX-ACCESS   read-only
    STATUS       current
    DESCRIPTION
        "Cisco Firepower adaptor:HostEthIf:purpose managed
        object property"
    ::= { cfprApAdaptorHostEthIfEntry 48 }

cfprApAdaptorHostEthIfRevision OBJECT-TYPE
    SYNTAX       SnmpAdminString
    MAX-ACCESS   read-only
    STATUS       current
    DESCRIPTION
        "Cisco Firepower adaptor:HostEthIf:revision managed
        object property"
    ::= { cfprApAdaptorHostEthIfEntry 49 }

cfprApAdaptorHostEthIfSerial OBJECT-TYPE
    SYNTAX       SnmpAdminString
    MAX-ACCESS   read-only
    STATUS       current
    DESCRIPTION
        "Cisco Firepower adaptor:HostEthIf:serial managed object property"
    ::= { cfprApAdaptorHostEthIfEntry 50 }

cfprApAdaptorHostEthIfServiceState OBJECT-TYPE
    SYNTAX       CfprApAdaptorServiceState
    MAX-ACCESS   read-only
    STATUS       current
    DESCRIPTION
        "Cisco Firepower adaptor:HostEthIf:serviceState
        managed object property"
    ::= { cfprApAdaptorHostEthIfEntry 51 }

cfprApAdaptorHostEthIfSide OBJECT-TYPE
    SYNTAX       CfprApNetworkSide
    MAX-ACCESS   read-only
    STATUS       current
    DESCRIPTION
        "Cisco Firepower adaptor:HostEthIf:side managed object property"
    ::= { cfprApAdaptorHostEthIfEntry 52 }

cfprApAdaptorHostEthIfSlotId OBJECT-TYPE
    SYNTAX       Gauge32
    MAX-ACCESS   read-only
    STATUS       current
    DESCRIPTION
        "Cisco Firepower adaptor:HostEthIf:slotId managed object property"
    ::= { cfprApAdaptorHostEthIfEntry 53 }

cfprApAdaptorHostEthIfSwitchId OBJECT-TYPE
    SYNTAX       CfprApNetworkSwitchId
    MAX-ACCESS   read-only
    STATUS       current
    DESCRIPTION
        "Cisco Firepower adaptor:HostEthIf:switchId managed
        object property"
    ::= { cfprApAdaptorHostEthIfEntry 54 }

cfprApAdaptorHostEthIfThermal OBJECT-TYPE
    SYNTAX       CfprApEquipmentSensorThresholdStatus
    MAX-ACCESS   read-only
    STATUS       current
    DESCRIPTION
        "Cisco Firepower adaptor:HostEthIf:thermal managed
        object property"
    ::= { cfprApAdaptorHostEthIfEntry 55 }

cfprApAdaptorHostEthIfTransport OBJECT-TYPE
    SYNTAX       CfprApNetworkTransport
    MAX-ACCESS   read-only
    STATUS       current
    DESCRIPTION
        "Cisco Firepower adaptor:HostEthIf:transport managed
        object property"
    ::= { cfprApAdaptorHostEthIfEntry 56 }

cfprApAdaptorHostEthIfType OBJECT-TYPE
    SYNTAX       CfprApNetworkConnectionType
    MAX-ACCESS   read-only
    STATUS       current
    DESCRIPTION
        "Cisco Firepower adaptor:HostEthIf:type managed object property"
    ::= { cfprApAdaptorHostEthIfEntry 57 }

cfprApAdaptorHostEthIfVendor OBJECT-TYPE
    SYNTAX       SnmpAdminString
    MAX-ACCESS   read-only
    STATUS       current
    DESCRIPTION
        "Cisco Firepower adaptor:HostEthIf:vendor managed object property"
    ::= { cfprApAdaptorHostEthIfEntry 58 }

cfprApAdaptorHostEthIfVirtualizationPreference OBJECT-TYPE
    SYNTAX       CfprApVnicVirtualizationPreferenceType
    MAX-ACCESS   read-only
    STATUS       current
    DESCRIPTION
        "Cisco Firepower adaptor:HostEthIf:virtualizationPreference
        managed object property"
    ::= { cfprApAdaptorHostEthIfEntry 59 }

cfprApAdaptorHostEthIfVnicDn OBJECT-TYPE
    SYNTAX       SnmpAdminString
    MAX-ACCESS   read-only
    STATUS       current
    DESCRIPTION
        "Cisco Firepower adaptor:HostEthIf:vnicDn managed object property"
    ::= { cfprApAdaptorHostEthIfEntry 60 }

cfprApAdaptorHostEthIfVoltage OBJECT-TYPE
    SYNTAX       CfprApEquipmentSensorThresholdStatus
    MAX-ACCESS   read-only
    STATUS       current
    DESCRIPTION
        "Cisco Firepower adaptor:HostEthIf:voltage managed
        object property"
    ::= { cfprApAdaptorHostEthIfEntry 61 }

cfprApAdaptorHostEthIfFsmTable OBJECT-TYPE
    SYNTAX           SEQUENCE OF CfprApAdaptorHostEthIfFsmEntry
    MAX-ACCESS       not-accessible
    STATUS           current
    DESCRIPTION
        "Cisco Firepower adaptor:HostEthIfFsm managed object table"
    ::= { cfprApAdaptorObjects 57 }

cfprApAdaptorHostEthIfFsmEntry OBJECT-TYPE
    SYNTAX           CfprApAdaptorHostEthIfFsmEntry
    MAX-ACCESS       not-accessible
    STATUS           current
    DESCRIPTION
        "Entry for the cfprApAdaptorHostEthIfFsmTable table."
    INDEX { cfprApAdaptorHostEthIfFsmInstanceId }
    ::= { cfprApAdaptorHostEthIfFsmTable 1 }

CfprApAdaptorHostEthIfFsmEntry ::= SEQUENCE {
    cfprApAdaptorHostEthIfFsmInstanceId                              CfprApManagedObjectId,
    cfprApAdaptorHostEthIfFsmDn                                      CfprApManagedObjectDn,
    cfprApAdaptorHostEthIfFsmRn                                      SnmpAdminString,
    cfprApAdaptorHostEthIfFsmCompletionTime                          DateAndTime,
    cfprApAdaptorHostEthIfFsmCurrentFsm                              CfprApAdaptorHostEthIfFsmCurrentFsm,
    cfprApAdaptorHostEthIfFsmDescrData                               SnmpAdminString,
    cfprApAdaptorHostEthIfFsmFsmStatus                               CfprApFsmFsmStageStatus,
    cfprApAdaptorHostEthIfFsmProgress                                Gauge32,
    cfprApAdaptorHostEthIfFsmRmtErrCode                              Gauge32,
    cfprApAdaptorHostEthIfFsmRmtErrDescr                             SnmpAdminString,
    cfprApAdaptorHostEthIfFsmRmtRslt                                 CfprApConditionRemoteInvRslt
}

cfprApAdaptorHostEthIfFsmInstanceId OBJECT-TYPE
    SYNTAX       CfprApManagedObjectId
    MAX-ACCESS   not-accessible
    STATUS       current
    DESCRIPTION
        "Instance identifier of the managed object."
    ::= { cfprApAdaptorHostEthIfFsmEntry 1 }

cfprApAdaptorHostEthIfFsmDn OBJECT-TYPE
    SYNTAX       CfprApManagedObjectDn
    MAX-ACCESS   read-only
    STATUS       current
    DESCRIPTION
        "Cisco Firepower adaptor:HostEthIfFsm:dn managed object property"
    ::= { cfprApAdaptorHostEthIfFsmEntry 2 }

cfprApAdaptorHostEthIfFsmRn OBJECT-TYPE
    SYNTAX       SnmpAdminString
    MAX-ACCESS   read-only
    STATUS       current
    DESCRIPTION
        "Cisco Firepower adaptor:HostEthIfFsm:rn managed object property"
    ::= { cfprApAdaptorHostEthIfFsmEntry 3 }

cfprApAdaptorHostEthIfFsmCompletionTime OBJECT-TYPE
    SYNTAX       DateAndTime
    MAX-ACCESS   read-only
    STATUS       current
    DESCRIPTION
        "Cisco Firepower adaptor:HostEthIfFsm:completionTime
        managed object property"
    ::= { cfprApAdaptorHostEthIfFsmEntry 4 }

cfprApAdaptorHostEthIfFsmCurrentFsm OBJECT-TYPE
    SYNTAX       CfprApAdaptorHostEthIfFsmCurrentFsm
    MAX-ACCESS   read-only
    STATUS       current
    DESCRIPTION
        "Cisco Firepower adaptor:HostEthIfFsm:currentFsm
        managed object property"
    ::= { cfprApAdaptorHostEthIfFsmEntry 5 }

cfprApAdaptorHostEthIfFsmDescrData OBJECT-TYPE
    SYNTAX       SnmpAdminString
    MAX-ACCESS   read-only
    STATUS       current
    DESCRIPTION
        "Cisco Firepower adaptor:HostEthIfFsm:descr managed
        object property"
    ::= { cfprApAdaptorHostEthIfFsmEntry 6 }

cfprApAdaptorHostEthIfFsmFsmStatus OBJECT-TYPE
    SYNTAX       CfprApFsmFsmStageStatus
    MAX-ACCESS   read-only
    STATUS       current
    DESCRIPTION
        "Cisco Firepower adaptor:HostEthIfFsm:fsmStatus
        managed object property"
    ::= { cfprApAdaptorHostEthIfFsmEntry 7 }

cfprApAdaptorHostEthIfFsmProgress OBJECT-TYPE
    SYNTAX       Gauge32
    MAX-ACCESS   read-only
    STATUS       current
    DESCRIPTION
        "Cisco Firepower adaptor:HostEthIfFsm:progress
        managed object property"
    ::= { cfprApAdaptorHostEthIfFsmEntry 8 }

cfprApAdaptorHostEthIfFsmRmtErrCode OBJECT-TYPE
    SYNTAX       Gauge32
    MAX-ACCESS   read-only
    STATUS       current
    DESCRIPTION
        "Cisco Firepower adaptor:HostEthIfFsm:rmtErrCode
        managed object property"
    ::= { cfprApAdaptorHostEthIfFsmEntry 9 }

cfprApAdaptorHostEthIfFsmRmtErrDescr OBJECT-TYPE
    SYNTAX       SnmpAdminString
    MAX-ACCESS   read-only
    STATUS       current
    DESCRIPTION
        "Cisco Firepower adaptor:HostEthIfFsm:rmtErrDescr
        managed object property"
    ::= { cfprApAdaptorHostEthIfFsmEntry 10 }

cfprApAdaptorHostEthIfFsmRmtRslt OBJECT-TYPE
    SYNTAX       CfprApConditionRemoteInvRslt
    MAX-ACCESS   read-only
    STATUS       current
    DESCRIPTION
        "Cisco Firepower adaptor:HostEthIfFsm:rmtRslt managed
        object property"
    ::= { cfprApAdaptorHostEthIfFsmEntry 11 }

cfprApAdaptorHostEthIfFsmStageTable OBJECT-TYPE
    SYNTAX           SEQUENCE OF CfprApAdaptorHostEthIfFsmStageEntry
    MAX-ACCESS       not-accessible
    STATUS           current
    DESCRIPTION
        "Cisco Firepower adaptor:HostEthIfFsmStage managed object table"
    ::= { cfprApAdaptorObjects 58 }

cfprApAdaptorHostEthIfFsmStageEntry OBJECT-TYPE
    SYNTAX           CfprApAdaptorHostEthIfFsmStageEntry
    MAX-ACCESS       not-accessible
    STATUS           current
    DESCRIPTION
        "Entry for the cfprApAdaptorHostEthIfFsmStageTable table."
    INDEX { cfprApAdaptorHostEthIfFsmStageInstanceId }
    ::= { cfprApAdaptorHostEthIfFsmStageTable 1 }

CfprApAdaptorHostEthIfFsmStageEntry ::= SEQUENCE {
    cfprApAdaptorHostEthIfFsmStageInstanceId                         CfprApManagedObjectId,
    cfprApAdaptorHostEthIfFsmStageDn                                 CfprApManagedObjectDn,
    cfprApAdaptorHostEthIfFsmStageRn                                 SnmpAdminString,
    cfprApAdaptorHostEthIfFsmStageDescrData                          SnmpAdminString,
    cfprApAdaptorHostEthIfFsmStageLastUpdateTime                     DateAndTime,
    cfprApAdaptorHostEthIfFsmStageName                               CfprApAdaptorHostEthIfFsmStageName,
    cfprApAdaptorHostEthIfFsmStageOrder                              Gauge32,
    cfprApAdaptorHostEthIfFsmStageRetry                              Gauge32,
    cfprApAdaptorHostEthIfFsmStageStageStatus                        CfprApFsmFsmStageStatus
}

cfprApAdaptorHostEthIfFsmStageInstanceId OBJECT-TYPE
    SYNTAX       CfprApManagedObjectId
    MAX-ACCESS   not-accessible
    STATUS       current
    DESCRIPTION
        "Instance identifier of the managed object."
    ::= { cfprApAdaptorHostEthIfFsmStageEntry 1 }

cfprApAdaptorHostEthIfFsmStageDn OBJECT-TYPE
    SYNTAX       CfprApManagedObjectDn
    MAX-ACCESS   read-only
    STATUS       current
    DESCRIPTION
        "Cisco Firepower adaptor:HostEthIfFsmStage:dn managed
        object property"
    ::= { cfprApAdaptorHostEthIfFsmStageEntry 2 }

cfprApAdaptorHostEthIfFsmStageRn OBJECT-TYPE
    SYNTAX       SnmpAdminString
    MAX-ACCESS   read-only
    STATUS       current
    DESCRIPTION
        "Cisco Firepower adaptor:HostEthIfFsmStage:rn managed
        object property"
    ::= { cfprApAdaptorHostEthIfFsmStageEntry 3 }

cfprApAdaptorHostEthIfFsmStageDescrData OBJECT-TYPE
    SYNTAX       SnmpAdminString
    MAX-ACCESS   read-only
    STATUS       current
    DESCRIPTION
        "Cisco Firepower adaptor:HostEthIfFsmStage:descr
        managed object property"
    ::= { cfprApAdaptorHostEthIfFsmStageEntry 4 }

cfprApAdaptorHostEthIfFsmStageLastUpdateTime OBJECT-TYPE
    SYNTAX       DateAndTime
    MAX-ACCESS   read-only
    STATUS       current
    DESCRIPTION
        "Cisco Firepower adaptor:HostEthIfFsmStage:lastUpdateTime
        managed object property"
    ::= { cfprApAdaptorHostEthIfFsmStageEntry 5 }

cfprApAdaptorHostEthIfFsmStageName OBJECT-TYPE
    SYNTAX       CfprApAdaptorHostEthIfFsmStageName
    MAX-ACCESS   read-only
    STATUS       current
    DESCRIPTION
        "Cisco Firepower adaptor:HostEthIfFsmStage:name
        managed object property"
    ::= { cfprApAdaptorHostEthIfFsmStageEntry 6 }

cfprApAdaptorHostEthIfFsmStageOrder OBJECT-TYPE
    SYNTAX       Gauge32
    MAX-ACCESS   read-only
    STATUS       current
    DESCRIPTION
        "Cisco Firepower adaptor:HostEthIfFsmStage:order
        managed object property"
    ::= { cfprApAdaptorHostEthIfFsmStageEntry 7 }

cfprApAdaptorHostEthIfFsmStageRetry OBJECT-TYPE
    SYNTAX       Gauge32
    MAX-ACCESS   read-only
    STATUS       current
    DESCRIPTION
        "Cisco Firepower adaptor:HostEthIfFsmStage:retry
        managed object property"
    ::= { cfprApAdaptorHostEthIfFsmStageEntry 8 }

cfprApAdaptorHostEthIfFsmStageStageStatus OBJECT-TYPE
    SYNTAX       CfprApFsmFsmStageStatus
    MAX-ACCESS   read-only
    STATUS       current
    DESCRIPTION
        "Cisco Firepower adaptor:HostEthIfFsmStage:stageStatus
        managed object property"
    ::= { cfprApAdaptorHostEthIfFsmStageEntry 9 }

cfprApAdaptorHostEthIfFsmTaskTable OBJECT-TYPE
    SYNTAX           SEQUENCE OF CfprApAdaptorHostEthIfFsmTaskEntry
    MAX-ACCESS       not-accessible
    STATUS           current
    DESCRIPTION
        "Cisco Firepower adaptor:HostEthIfFsmTask managed object table"
    ::= { cfprApAdaptorObjects 59 }

cfprApAdaptorHostEthIfFsmTaskEntry OBJECT-TYPE
    SYNTAX           CfprApAdaptorHostEthIfFsmTaskEntry
    MAX-ACCESS       not-accessible
    STATUS           current
    DESCRIPTION
        "Entry for the cfprApAdaptorHostEthIfFsmTaskTable table."
    INDEX { cfprApAdaptorHostEthIfFsmTaskInstanceId }
    ::= { cfprApAdaptorHostEthIfFsmTaskTable 1 }

CfprApAdaptorHostEthIfFsmTaskEntry ::= SEQUENCE {
    cfprApAdaptorHostEthIfFsmTaskInstanceId                          CfprApManagedObjectId,
    cfprApAdaptorHostEthIfFsmTaskDn                                  CfprApManagedObjectDn,
    cfprApAdaptorHostEthIfFsmTaskRn                                  SnmpAdminString,
    cfprApAdaptorHostEthIfFsmTaskCompletion                          CfprApFsmCompletion,
    cfprApAdaptorHostEthIfFsmTaskFlags                               CfprApFsmFlags,
    cfprApAdaptorHostEthIfFsmTaskItem                                CfprApAdaptorHostEthIfFsmTaskItem,
    cfprApAdaptorHostEthIfFsmTaskSeqId                               Gauge32
}

cfprApAdaptorHostEthIfFsmTaskInstanceId OBJECT-TYPE
    SYNTAX       CfprApManagedObjectId
    MAX-ACCESS   not-accessible
    STATUS       current
    DESCRIPTION
        "Instance identifier of the managed object."
    ::= { cfprApAdaptorHostEthIfFsmTaskEntry 1 }

cfprApAdaptorHostEthIfFsmTaskDn OBJECT-TYPE
    SYNTAX       CfprApManagedObjectDn
    MAX-ACCESS   read-only
    STATUS       current
    DESCRIPTION
        "Cisco Firepower adaptor:HostEthIfFsmTask:dn managed
        object property"
    ::= { cfprApAdaptorHostEthIfFsmTaskEntry 2 }

cfprApAdaptorHostEthIfFsmTaskRn OBJECT-TYPE
    SYNTAX       SnmpAdminString
    MAX-ACCESS   read-only
    STATUS       current
    DESCRIPTION
        "Cisco Firepower adaptor:HostEthIfFsmTask:rn managed
        object property"
    ::= { cfprApAdaptorHostEthIfFsmTaskEntry 3 }

cfprApAdaptorHostEthIfFsmTaskCompletion OBJECT-TYPE
    SYNTAX       CfprApFsmCompletion
    MAX-ACCESS   read-only
    STATUS       current
    DESCRIPTION
        "Cisco Firepower adaptor:HostEthIfFsmTask:completion
        managed object property"
    ::= { cfprApAdaptorHostEthIfFsmTaskEntry 4 }

cfprApAdaptorHostEthIfFsmTaskFlags OBJECT-TYPE
    SYNTAX       CfprApFsmFlags
    MAX-ACCESS   read-only
    STATUS       current
    DESCRIPTION
        "Cisco Firepower adaptor:HostEthIfFsmTask:flags
        managed object property"
    ::= { cfprApAdaptorHostEthIfFsmTaskEntry 5 }

cfprApAdaptorHostEthIfFsmTaskItem OBJECT-TYPE
    SYNTAX       CfprApAdaptorHostEthIfFsmTaskItem
    MAX-ACCESS   read-only
    STATUS       current
    DESCRIPTION
        "Cisco Firepower adaptor:HostEthIfFsmTask:item
        managed object property"
    ::= { cfprApAdaptorHostEthIfFsmTaskEntry 6 }

cfprApAdaptorHostEthIfFsmTaskSeqId OBJECT-TYPE
    SYNTAX       Gauge32
    MAX-ACCESS   read-only
    STATUS       current
    DESCRIPTION
        "Cisco Firepower adaptor:HostEthIfFsmTask:seqId
        managed object property"
    ::= { cfprApAdaptorHostEthIfFsmTaskEntry 7 }

cfprApAdaptorHostEthIfProfileTable OBJECT-TYPE
    SYNTAX           SEQUENCE OF CfprApAdaptorHostEthIfProfileEntry
    MAX-ACCESS       not-accessible
    STATUS           current
    DESCRIPTION
        "Cisco Firepower adaptor:HostEthIfProfile managed object table"
    ::= { cfprApAdaptorObjects 60 }

cfprApAdaptorHostEthIfProfileEntry OBJECT-TYPE
    SYNTAX           CfprApAdaptorHostEthIfProfileEntry
    MAX-ACCESS       not-accessible
    STATUS           current
    DESCRIPTION
        "Entry for the cfprApAdaptorHostEthIfProfileTable table."
    INDEX { cfprApAdaptorHostEthIfProfileInstanceId }
    ::= { cfprApAdaptorHostEthIfProfileTable 1 }

CfprApAdaptorHostEthIfProfileEntry ::= SEQUENCE {
    cfprApAdaptorHostEthIfProfileInstanceId                          CfprApManagedObjectId,
    cfprApAdaptorHostEthIfProfileDn                                  CfprApManagedObjectDn,
    cfprApAdaptorHostEthIfProfileRn                                  SnmpAdminString,
    cfprApAdaptorHostEthIfProfileDescr                               SnmpAdminString,
    cfprApAdaptorHostEthIfProfileIntId                               SnmpAdminString,
    cfprApAdaptorHostEthIfProfileName                                SnmpAdminString,
    cfprApAdaptorHostEthIfProfilePolicyLevel                         Gauge32,
    cfprApAdaptorHostEthIfProfilePolicyOwner                         CfprApPolicyPolicyOwner
}

cfprApAdaptorHostEthIfProfileInstanceId OBJECT-TYPE
    SYNTAX       CfprApManagedObjectId
    MAX-ACCESS   not-accessible
    STATUS       current
    DESCRIPTION
        "Instance identifier of the managed object."
    ::= { cfprApAdaptorHostEthIfProfileEntry 1 }

cfprApAdaptorHostEthIfProfileDn OBJECT-TYPE
    SYNTAX       CfprApManagedObjectDn
    MAX-ACCESS   read-only
    STATUS       current
    DESCRIPTION
        "Cisco Firepower adaptor:HostEthIfProfile:dn managed
        object property"
    ::= { cfprApAdaptorHostEthIfProfileEntry 2 }

cfprApAdaptorHostEthIfProfileRn OBJECT-TYPE
    SYNTAX       SnmpAdminString
    MAX-ACCESS   read-only
    STATUS       current
    DESCRIPTION
        "Cisco Firepower adaptor:HostEthIfProfile:rn managed
        object property"
    ::= { cfprApAdaptorHostEthIfProfileEntry 3 }

cfprApAdaptorHostEthIfProfileDescr OBJECT-TYPE
    SYNTAX       SnmpAdminString
    MAX-ACCESS   read-only
    STATUS       current
    DESCRIPTION
        "Cisco Firepower adaptor:HostEthIfProfile:descr
        managed object property"
    ::= { cfprApAdaptorHostEthIfProfileEntry 4 }

cfprApAdaptorHostEthIfProfileIntId OBJECT-TYPE
    SYNTAX       SnmpAdminString
    MAX-ACCESS   read-only
    STATUS       current
    DESCRIPTION
        "Cisco Firepower adaptor:HostEthIfProfile:intId
        managed object property"
    ::= { cfprApAdaptorHostEthIfProfileEntry 5 }

cfprApAdaptorHostEthIfProfileName OBJECT-TYPE
    SYNTAX       SnmpAdminString
    MAX-ACCESS   read-only
    STATUS       current
    DESCRIPTION
        "Cisco Firepower adaptor:HostEthIfProfile:name
        managed object property"
    ::= { cfprApAdaptorHostEthIfProfileEntry 6 }

cfprApAdaptorHostEthIfProfilePolicyLevel OBJECT-TYPE
    SYNTAX       Gauge32
    MAX-ACCESS   read-only
    STATUS       current
    DESCRIPTION
        "Cisco Firepower adaptor:HostEthIfProfile:policyLevel
        managed object property"
    ::= { cfprApAdaptorHostEthIfProfileEntry 7 }

cfprApAdaptorHostEthIfProfilePolicyOwner OBJECT-TYPE
    SYNTAX       CfprApPolicyPolicyOwner
    MAX-ACCESS   read-only
    STATUS       current
    DESCRIPTION
        "Cisco Firepower adaptor:HostEthIfProfile:policyOwner
        managed object property"
    ::= { cfprApAdaptorHostEthIfProfileEntry 8 }

cfprApAdaptorHostFcIfTable OBJECT-TYPE
    SYNTAX           SEQUENCE OF CfprApAdaptorHostFcIfEntry
    MAX-ACCESS       not-accessible
    STATUS           current
    DESCRIPTION
        "Cisco Firepower adaptor:HostFcIf managed object table"
    ::= { cfprApAdaptorObjects 61 }

cfprApAdaptorHostFcIfEntry OBJECT-TYPE
    SYNTAX           CfprApAdaptorHostFcIfEntry
    MAX-ACCESS       not-accessible
    STATUS           current
    DESCRIPTION
        "Entry for the cfprApAdaptorHostFcIfTable table."
    INDEX { cfprApAdaptorHostFcIfInstanceId }
    ::= { cfprApAdaptorHostFcIfTable 1 }

CfprApAdaptorHostFcIfEntry ::= SEQUENCE {
    cfprApAdaptorHostFcIfInstanceId                                  CfprApManagedObjectId,
    cfprApAdaptorHostFcIfDn                                          CfprApManagedObjectDn,
    cfprApAdaptorHostFcIfRn                                          SnmpAdminString,
    cfprApAdaptorHostFcIfAdminState                                  CfprApAdaptorHostFcIfAdminState,
    cfprApAdaptorHostFcIfBootDev                                     CfprApAdaptorHostIfBootDev,
    cfprApAdaptorHostFcIfChassisId                                   Gauge32,
    cfprApAdaptorHostFcIfDiscovery                                   CfprApEtherSatelliteConnectionDisc,
    cfprApAdaptorHostFcIfEpDn                                        SnmpAdminString,
    cfprApAdaptorHostFcIfFltAggr                                     Unsigned64,
    cfprApAdaptorHostFcIfFsmDescr                                    SnmpAdminString,
    cfprApAdaptorHostFcIfFsmPrev                                     SnmpAdminString,
    cfprApAdaptorHostFcIfFsmProgr                                    Gauge32,
    cfprApAdaptorHostFcIfFsmRmtInvErrCode                            Gauge32,
    cfprApAdaptorHostFcIfFsmRmtInvErrDescr                           SnmpAdminString,
    cfprApAdaptorHostFcIfFsmRmtInvRslt                               CfprApConditionRemoteInvRslt,
    cfprApAdaptorHostFcIfFsmStageDescr                               SnmpAdminString,
    cfprApAdaptorHostFcIfFsmStamp                                    DateAndTime,
    cfprApAdaptorHostFcIfFsmStatus                                   SnmpAdminString,
    cfprApAdaptorHostFcIfFsmTry                                      Gauge32,
    cfprApAdaptorHostFcIfHostPort                                    CfprApAdaptorHostFcIfHostPort,
    cfprApAdaptorHostFcIfId                                          Gauge32,
    cfprApAdaptorHostFcIfIfRole                                      CfprApNetworkPortRole,
    cfprApAdaptorHostFcIfIfType                                      CfprApNetworkPhysEpIfType,
    cfprApAdaptorHostFcIfLc                                          CfprApFsmLifecycle,
    cfprApAdaptorHostFcIfLinkState                                   CfprApAdaptorLinkState,
    cfprApAdaptorHostFcIfLocale                                      CfprApNetworkLocale,
    cfprApAdaptorHostFcIfMaxDataFieldSize                            Gauge32,
    cfprApAdaptorHostFcIfModel                                       SnmpAdminString,
    cfprApAdaptorHostFcIfName                                        SnmpAdminString,
    cfprApAdaptorHostFcIfNodeWwn                                     Unsigned64,
    cfprApAdaptorHostFcIfOperQualifierReason                         SnmpAdminString,
    cfprApAdaptorHostFcIfOperState                                   CfprApEquipmentOperability,
    cfprApAdaptorHostFcIfOperability                                 CfprApEquipmentOperability,
    cfprApAdaptorHostFcIfOrder                                       Gauge32,
    cfprApAdaptorHostFcIfOriginalNodeWwn                             Unsigned64,
    cfprApAdaptorHostFcIfOriginalWwn                                 Unsigned64,
    cfprApAdaptorHostFcIfPciAddr                                     SnmpAdminString,
    cfprApAdaptorHostFcIfPciFunc                                     Gauge32,
    cfprApAdaptorHostFcIfPciSlot                                     Gauge32,
    cfprApAdaptorHostFcIfPeerChassisId                               Gauge32,
    cfprApAdaptorHostFcIfPeerDn                                      SnmpAdminString,
    cfprApAdaptorHostFcIfPeerPortId                                  Gauge32,
    cfprApAdaptorHostFcIfPeerSlotId                                  Gauge32,
    cfprApAdaptorHostFcIfPerf                                        CfprApEquipmentSensorThresholdStatus,
    cfprApAdaptorHostFcIfPersBind                                    CfprApAdaptorHostFcIfPersBind,
    cfprApAdaptorHostFcIfPortId                                      Gauge32,
    cfprApAdaptorHostFcIfPower                                       CfprApEquipmentPowerState,
    cfprApAdaptorHostFcIfPresence                                    CfprApEquipmentPresence,
    cfprApAdaptorHostFcIfPurpose                                     CfprApAdaptorPurpose,
    cfprApAdaptorHostFcIfRevision                                    SnmpAdminString,
    cfprApAdaptorHostFcIfSerial                                      SnmpAdminString,
    cfprApAdaptorHostFcIfServiceState                                CfprApAdaptorServiceState,
    cfprApAdaptorHostFcIfSide                                        CfprApNetworkSide,
    cfprApAdaptorHostFcIfSlotId                                      Gauge32,
    cfprApAdaptorHostFcIfSwitchId                                    CfprApNetworkSwitchId,
    cfprApAdaptorHostFcIfThermal                                     CfprApEquipmentSensorThresholdStatus,
    cfprApAdaptorHostFcIfTransport                                   CfprApNetworkTransport,
    cfprApAdaptorHostFcIfType                                        CfprApNetworkConnectionType,
    cfprApAdaptorHostFcIfVendor                                      SnmpAdminString,
    cfprApAdaptorHostFcIfVnicDn                                      SnmpAdminString,
    cfprApAdaptorHostFcIfVoltage                                     CfprApEquipmentSensorThresholdStatus,
    cfprApAdaptorHostFcIfWwn                                         Unsigned64
}

cfprApAdaptorHostFcIfInstanceId OBJECT-TYPE
    SYNTAX       CfprApManagedObjectId
    MAX-ACCESS   not-accessible
    STATUS       current
    DESCRIPTION
        "Instance identifier of the managed object."
    ::= { cfprApAdaptorHostFcIfEntry 1 }

cfprApAdaptorHostFcIfDn OBJECT-TYPE
    SYNTAX       CfprApManagedObjectDn
    MAX-ACCESS   read-only
    STATUS       current
    DESCRIPTION
        "Cisco Firepower adaptor:HostFcIf:dn managed object property"
    ::= { cfprApAdaptorHostFcIfEntry 2 }

cfprApAdaptorHostFcIfRn OBJECT-TYPE
    SYNTAX       SnmpAdminString
    MAX-ACCESS   read-only
    STATUS       current
    DESCRIPTION
        "Cisco Firepower adaptor:HostFcIf:rn managed object property"
    ::= { cfprApAdaptorHostFcIfEntry 3 }

cfprApAdaptorHostFcIfAdminState OBJECT-TYPE
    SYNTAX       CfprApAdaptorHostFcIfAdminState
    MAX-ACCESS   read-only
    STATUS       current
    DESCRIPTION
        "Cisco Firepower adaptor:HostFcIf:adminState managed
        object property"
    ::= { cfprApAdaptorHostFcIfEntry 4 }

cfprApAdaptorHostFcIfBootDev OBJECT-TYPE
    SYNTAX       CfprApAdaptorHostIfBootDev
    MAX-ACCESS   read-only
    STATUS       current
    DESCRIPTION
        "Cisco Firepower adaptor:HostFcIf:bootDev managed object property"
    ::= { cfprApAdaptorHostFcIfEntry 5 }

cfprApAdaptorHostFcIfChassisId OBJECT-TYPE
    SYNTAX       Gauge32
    MAX-ACCESS   read-only
    STATUS       current
    DESCRIPTION
        "Cisco Firepower adaptor:HostFcIf:chassisId managed
        object property"
    ::= { cfprApAdaptorHostFcIfEntry 6 }

cfprApAdaptorHostFcIfDiscovery OBJECT-TYPE
    SYNTAX       CfprApEtherSatelliteConnectionDisc
    MAX-ACCESS   read-only
    STATUS       current
    DESCRIPTION
        "Cisco Firepower adaptor:HostFcIf:discovery managed
        object property"
    ::= { cfprApAdaptorHostFcIfEntry 7 }

cfprApAdaptorHostFcIfEpDn OBJECT-TYPE
    SYNTAX       SnmpAdminString
    MAX-ACCESS   read-only
    STATUS       current
    DESCRIPTION
        "Cisco Firepower adaptor:HostFcIf:epDn managed object property"
    ::= { cfprApAdaptorHostFcIfEntry 8 }

cfprApAdaptorHostFcIfFltAggr OBJECT-TYPE
    SYNTAX       Unsigned64
    MAX-ACCESS   read-only
    STATUS       current
    DESCRIPTION
        "Cisco Firepower adaptor:HostFcIf:fltAggr managed object property"
    ::= { cfprApAdaptorHostFcIfEntry 9 }

cfprApAdaptorHostFcIfFsmDescr OBJECT-TYPE
    SYNTAX       SnmpAdminString
    MAX-ACCESS   read-only
    STATUS       current
    DESCRIPTION
        "Cisco Firepower adaptor:HostFcIf:fsmDescr managed
        object property"
    ::= { cfprApAdaptorHostFcIfEntry 10 }

cfprApAdaptorHostFcIfFsmPrev OBJECT-TYPE
    SYNTAX       SnmpAdminString
    MAX-ACCESS   read-only
    STATUS       current
    DESCRIPTION
        "Cisco Firepower adaptor:HostFcIf:fsmPrev managed object property"
    ::= { cfprApAdaptorHostFcIfEntry 11 }

cfprApAdaptorHostFcIfFsmProgr OBJECT-TYPE
    SYNTAX       Gauge32
    MAX-ACCESS   read-only
    STATUS       current
    DESCRIPTION
        "Cisco Firepower adaptor:HostFcIf:fsmProgr managed
        object property"
    ::= { cfprApAdaptorHostFcIfEntry 12 }

cfprApAdaptorHostFcIfFsmRmtInvErrCode OBJECT-TYPE
    SYNTAX       Gauge32
    MAX-ACCESS   read-only
    STATUS       current
    DESCRIPTION
        "Cisco Firepower adaptor:HostFcIf:fsmRmtInvErrCode
        managed object property"
    ::= { cfprApAdaptorHostFcIfEntry 13 }

cfprApAdaptorHostFcIfFsmRmtInvErrDescr OBJECT-TYPE
    SYNTAX       SnmpAdminString
    MAX-ACCESS   read-only
    STATUS       current
    DESCRIPTION
        "Cisco Firepower adaptor:HostFcIf:fsmRmtInvErrDescr
        managed object property"
    ::= { cfprApAdaptorHostFcIfEntry 14 }

cfprApAdaptorHostFcIfFsmRmtInvRslt OBJECT-TYPE
    SYNTAX       CfprApConditionRemoteInvRslt
    MAX-ACCESS   read-only
    STATUS       current
    DESCRIPTION
        "Cisco Firepower adaptor:HostFcIf:fsmRmtInvRslt
        managed object property"
    ::= { cfprApAdaptorHostFcIfEntry 15 }

cfprApAdaptorHostFcIfFsmStageDescr OBJECT-TYPE
    SYNTAX       SnmpAdminString
    MAX-ACCESS   read-only
    STATUS       current
    DESCRIPTION
        "Cisco Firepower adaptor:HostFcIf:fsmStageDescr
        managed object property"
    ::= { cfprApAdaptorHostFcIfEntry 16 }

cfprApAdaptorHostFcIfFsmStamp OBJECT-TYPE
    SYNTAX       DateAndTime
    MAX-ACCESS   read-only
    STATUS       current
    DESCRIPTION
        "Cisco Firepower adaptor:HostFcIf:fsmStamp managed
        object property"
    ::= { cfprApAdaptorHostFcIfEntry 17 }

cfprApAdaptorHostFcIfFsmStatus OBJECT-TYPE
    SYNTAX       SnmpAdminString
    MAX-ACCESS   read-only
    STATUS       current
    DESCRIPTION
        "Cisco Firepower adaptor:HostFcIf:fsmStatus managed
        object property"
    ::= { cfprApAdaptorHostFcIfEntry 18 }

cfprApAdaptorHostFcIfFsmTry OBJECT-TYPE
    SYNTAX       Gauge32
    MAX-ACCESS   read-only
    STATUS       current
    DESCRIPTION
        "Cisco Firepower adaptor:HostFcIf:fsmTry managed object property"
    ::= { cfprApAdaptorHostFcIfEntry 19 }

cfprApAdaptorHostFcIfHostPort OBJECT-TYPE
    SYNTAX       CfprApAdaptorHostFcIfHostPort
    MAX-ACCESS   read-only
    STATUS       current
    DESCRIPTION
        "Cisco Firepower adaptor:HostFcIf:hostPort managed
        object property"
    ::= { cfprApAdaptorHostFcIfEntry 20 }

cfprApAdaptorHostFcIfId OBJECT-TYPE
    SYNTAX       Gauge32
    MAX-ACCESS   read-only
    STATUS       current
    DESCRIPTION
        "Cisco Firepower adaptor:HostFcIf:id managed object property"
    ::= { cfprApAdaptorHostFcIfEntry 21 }

cfprApAdaptorHostFcIfIfRole OBJECT-TYPE
    SYNTAX       CfprApNetworkPortRole
    MAX-ACCESS   read-only
    STATUS       current
    DESCRIPTION
        "Cisco Firepower adaptor:HostFcIf:ifRole managed object property"
    ::= { cfprApAdaptorHostFcIfEntry 22 }

cfprApAdaptorHostFcIfIfType OBJECT-TYPE
    SYNTAX       CfprApNetworkPhysEpIfType
    MAX-ACCESS   read-only
    STATUS       current
    DESCRIPTION
        "Cisco Firepower adaptor:HostFcIf:ifType managed object property"
    ::= { cfprApAdaptorHostFcIfEntry 23 }

cfprApAdaptorHostFcIfLc OBJECT-TYPE
    SYNTAX       CfprApFsmLifecycle
    MAX-ACCESS   read-only
    STATUS       current
    DESCRIPTION
        "Cisco Firepower adaptor:HostFcIf:lc managed object property"
    ::= { cfprApAdaptorHostFcIfEntry 24 }

cfprApAdaptorHostFcIfLinkState OBJECT-TYPE
    SYNTAX       CfprApAdaptorLinkState
    MAX-ACCESS   read-only
    STATUS       current
    DESCRIPTION
        "Cisco Firepower adaptor:HostFcIf:linkState managed
        object property"
    ::= { cfprApAdaptorHostFcIfEntry 25 }

cfprApAdaptorHostFcIfLocale OBJECT-TYPE
    SYNTAX       CfprApNetworkLocale
    MAX-ACCESS   read-only
    STATUS       current
    DESCRIPTION
        "Cisco Firepower adaptor:HostFcIf:locale managed object property"
    ::= { cfprApAdaptorHostFcIfEntry 26 }

cfprApAdaptorHostFcIfMaxDataFieldSize OBJECT-TYPE
    SYNTAX       Gauge32
    MAX-ACCESS   read-only
    STATUS       current
    DESCRIPTION
        "Cisco Firepower adaptor:HostFcIf:maxDataFieldSize
        managed object property"
    ::= { cfprApAdaptorHostFcIfEntry 27 }

cfprApAdaptorHostFcIfModel OBJECT-TYPE
    SYNTAX       SnmpAdminString
    MAX-ACCESS   read-only
    STATUS       current
    DESCRIPTION
        "Cisco Firepower adaptor:HostFcIf:model managed object property"
    ::= { cfprApAdaptorHostFcIfEntry 28 }

cfprApAdaptorHostFcIfName OBJECT-TYPE
    SYNTAX       SnmpAdminString
    MAX-ACCESS   read-only
    STATUS       current
    DESCRIPTION
        "Cisco Firepower adaptor:HostFcIf:name managed object property"
    ::= { cfprApAdaptorHostFcIfEntry 29 }

cfprApAdaptorHostFcIfNodeWwn OBJECT-TYPE
    SYNTAX       Unsigned64
    MAX-ACCESS   read-only
    STATUS       current
    DESCRIPTION
        "Cisco Firepower adaptor:HostFcIf:nodeWwn managed object property"
    ::= { cfprApAdaptorHostFcIfEntry 30 }

cfprApAdaptorHostFcIfOperQualifierReason OBJECT-TYPE
    SYNTAX       SnmpAdminString
    MAX-ACCESS   read-only
    STATUS       current
    DESCRIPTION
        "Cisco Firepower adaptor:HostFcIf:operQualifierReason
        managed object property"
    ::= { cfprApAdaptorHostFcIfEntry 31 }

cfprApAdaptorHostFcIfOperState OBJECT-TYPE
    SYNTAX       CfprApEquipmentOperability
    MAX-ACCESS   read-only
    STATUS       current
    DESCRIPTION
        "Cisco Firepower adaptor:HostFcIf:operState managed
        object property"
    ::= { cfprApAdaptorHostFcIfEntry 32 }

cfprApAdaptorHostFcIfOperability OBJECT-TYPE
    SYNTAX       CfprApEquipmentOperability
    MAX-ACCESS   read-only
    STATUS       current
    DESCRIPTION
        "Cisco Firepower adaptor:HostFcIf:operability managed
        object property"
    ::= { cfprApAdaptorHostFcIfEntry 33 }

cfprApAdaptorHostFcIfOrder OBJECT-TYPE
    SYNTAX       Gauge32
    MAX-ACCESS   read-only
    STATUS       current
    DESCRIPTION
        "Cisco Firepower adaptor:HostFcIf:order managed object property"
    ::= { cfprApAdaptorHostFcIfEntry 34 }

cfprApAdaptorHostFcIfOriginalNodeWwn OBJECT-TYPE
    SYNTAX       Unsigned64
    MAX-ACCESS   read-only
    STATUS       current
    DESCRIPTION
        "Cisco Firepower adaptor:HostFcIf:originalNodeWwn
        managed object property"
    ::= { cfprApAdaptorHostFcIfEntry 35 }

cfprApAdaptorHostFcIfOriginalWwn OBJECT-TYPE
    SYNTAX       Unsigned64
    MAX-ACCESS   read-only
    STATUS       current
    DESCRIPTION
        "Cisco Firepower adaptor:HostFcIf:originalWwn managed
        object property"
    ::= { cfprApAdaptorHostFcIfEntry 36 }

cfprApAdaptorHostFcIfPciAddr OBJECT-TYPE
    SYNTAX       SnmpAdminString
    MAX-ACCESS   read-only
    STATUS       current
    DESCRIPTION
        "Cisco Firepower adaptor:HostFcIf:pciAddr managed object property"
    ::= { cfprApAdaptorHostFcIfEntry 37 }

cfprApAdaptorHostFcIfPciFunc OBJECT-TYPE
    SYNTAX       Gauge32
    MAX-ACCESS   read-only
    STATUS       current
    DESCRIPTION
        "Cisco Firepower adaptor:HostFcIf:pciFunc managed object property"
    ::= { cfprApAdaptorHostFcIfEntry 38 }

cfprApAdaptorHostFcIfPciSlot OBJECT-TYPE
    SYNTAX       Gauge32
    MAX-ACCESS   read-only
    STATUS       current
    DESCRIPTION
        "Cisco Firepower adaptor:HostFcIf:pciSlot managed object property"
    ::= { cfprApAdaptorHostFcIfEntry 39 }

cfprApAdaptorHostFcIfPeerChassisId OBJECT-TYPE
    SYNTAX       Gauge32
    MAX-ACCESS   read-only
    STATUS       current
    DESCRIPTION
        "Cisco Firepower adaptor:HostFcIf:peerChassisId
        managed object property"
    ::= { cfprApAdaptorHostFcIfEntry 40 }

cfprApAdaptorHostFcIfPeerDn OBJECT-TYPE
    SYNTAX       SnmpAdminString
    MAX-ACCESS   read-only
    STATUS       current
    DESCRIPTION
        "Cisco Firepower adaptor:HostFcIf:peerDn managed object property"
    ::= { cfprApAdaptorHostFcIfEntry 41 }

cfprApAdaptorHostFcIfPeerPortId OBJECT-TYPE
    SYNTAX       Gauge32
    MAX-ACCESS   read-only
    STATUS       current
    DESCRIPTION
        "Cisco Firepower adaptor:HostFcIf:peerPortId managed
        object property"
    ::= { cfprApAdaptorHostFcIfEntry 42 }

cfprApAdaptorHostFcIfPeerSlotId OBJECT-TYPE
    SYNTAX       Gauge32
    MAX-ACCESS   read-only
    STATUS       current
    DESCRIPTION
        "Cisco Firepower adaptor:HostFcIf:peerSlotId managed
        object property"
    ::= { cfprApAdaptorHostFcIfEntry 43 }

cfprApAdaptorHostFcIfPerf OBJECT-TYPE
    SYNTAX       CfprApEquipmentSensorThresholdStatus
    MAX-ACCESS   read-only
    STATUS       current
    DESCRIPTION
        "Cisco Firepower adaptor:HostFcIf:perf managed object property"
    ::= { cfprApAdaptorHostFcIfEntry 44 }

cfprApAdaptorHostFcIfPersBind OBJECT-TYPE
    SYNTAX       CfprApAdaptorHostFcIfPersBind
    MAX-ACCESS   read-only
    STATUS       current
    DESCRIPTION
        "Cisco Firepower adaptor:HostFcIf:persBind managed
        object property"
    ::= { cfprApAdaptorHostFcIfEntry 45 }

cfprApAdaptorHostFcIfPortId OBJECT-TYPE
    SYNTAX       Gauge32
    MAX-ACCESS   read-only
    STATUS       current
    DESCRIPTION
        "Cisco Firepower adaptor:HostFcIf:portId managed object property"
    ::= { cfprApAdaptorHostFcIfEntry 46 }

cfprApAdaptorHostFcIfPower OBJECT-TYPE
    SYNTAX       CfprApEquipmentPowerState
    MAX-ACCESS   read-only
    STATUS       current
    DESCRIPTION
        "Cisco Firepower adaptor:HostFcIf:power managed object property"
    ::= { cfprApAdaptorHostFcIfEntry 47 }

cfprApAdaptorHostFcIfPresence OBJECT-TYPE
    SYNTAX       CfprApEquipmentPresence
    MAX-ACCESS   read-only
    STATUS       current
    DESCRIPTION
        "Cisco Firepower adaptor:HostFcIf:presence managed
        object property"
    ::= { cfprApAdaptorHostFcIfEntry 48 }

cfprApAdaptorHostFcIfPurpose OBJECT-TYPE
    SYNTAX       CfprApAdaptorPurpose
    MAX-ACCESS   read-only
    STATUS       current
    DESCRIPTION
        "Cisco Firepower adaptor:HostFcIf:purpose managed object property"
    ::= { cfprApAdaptorHostFcIfEntry 49 }

cfprApAdaptorHostFcIfRevision OBJECT-TYPE
    SYNTAX       SnmpAdminString
    MAX-ACCESS   read-only
    STATUS       current
    DESCRIPTION
        "Cisco Firepower adaptor:HostFcIf:revision managed
        object property"
    ::= { cfprApAdaptorHostFcIfEntry 50 }

cfprApAdaptorHostFcIfSerial OBJECT-TYPE
    SYNTAX       SnmpAdminString
    MAX-ACCESS   read-only
    STATUS       current
    DESCRIPTION
        "Cisco Firepower adaptor:HostFcIf:serial managed object property"
    ::= { cfprApAdaptorHostFcIfEntry 51 }

cfprApAdaptorHostFcIfServiceState OBJECT-TYPE
    SYNTAX       CfprApAdaptorServiceState
    MAX-ACCESS   read-only
    STATUS       current
    DESCRIPTION
        "Cisco Firepower adaptor:HostFcIf:serviceState
        managed object property"
    ::= { cfprApAdaptorHostFcIfEntry 52 }

cfprApAdaptorHostFcIfSide OBJECT-TYPE
    SYNTAX       CfprApNetworkSide
    MAX-ACCESS   read-only
    STATUS       current
    DESCRIPTION
        "Cisco Firepower adaptor:HostFcIf:side managed object property"
    ::= { cfprApAdaptorHostFcIfEntry 53 }

cfprApAdaptorHostFcIfSlotId OBJECT-TYPE
    SYNTAX       Gauge32
    MAX-ACCESS   read-only
    STATUS       current
    DESCRIPTION
        "Cisco Firepower adaptor:HostFcIf:slotId managed object property"
    ::= { cfprApAdaptorHostFcIfEntry 54 }

cfprApAdaptorHostFcIfSwitchId OBJECT-TYPE
    SYNTAX       CfprApNetworkSwitchId
    MAX-ACCESS   read-only
    STATUS       current
    DESCRIPTION
        "Cisco Firepower adaptor:HostFcIf:switchId managed
        object property"
    ::= { cfprApAdaptorHostFcIfEntry 55 }

cfprApAdaptorHostFcIfThermal OBJECT-TYPE
    SYNTAX       CfprApEquipmentSensorThresholdStatus
    MAX-ACCESS   read-only
    STATUS       current
    DESCRIPTION
        "Cisco Firepower adaptor:HostFcIf:thermal managed object property"
    ::= { cfprApAdaptorHostFcIfEntry 56 }

cfprApAdaptorHostFcIfTransport OBJECT-TYPE
    SYNTAX       CfprApNetworkTransport
    MAX-ACCESS   read-only
    STATUS       current
    DESCRIPTION
        "Cisco Firepower adaptor:HostFcIf:transport managed
        object property"
    ::= { cfprApAdaptorHostFcIfEntry 57 }

cfprApAdaptorHostFcIfType OBJECT-TYPE
    SYNTAX       CfprApNetworkConnectionType
    MAX-ACCESS   read-only
    STATUS       current
    DESCRIPTION
        "Cisco Firepower adaptor:HostFcIf:type managed object property"
    ::= { cfprApAdaptorHostFcIfEntry 58 }

cfprApAdaptorHostFcIfVendor OBJECT-TYPE
    SYNTAX       SnmpAdminString
    MAX-ACCESS   read-only
    STATUS       current
    DESCRIPTION
        "Cisco Firepower adaptor:HostFcIf:vendor managed object property"
    ::= { cfprApAdaptorHostFcIfEntry 59 }

cfprApAdaptorHostFcIfVnicDn OBJECT-TYPE
    SYNTAX       SnmpAdminString
    MAX-ACCESS   read-only
    STATUS       current
    DESCRIPTION
        "Cisco Firepower adaptor:HostFcIf:vnicDn managed object property"
    ::= { cfprApAdaptorHostFcIfEntry 60 }

cfprApAdaptorHostFcIfVoltage OBJECT-TYPE
    SYNTAX       CfprApEquipmentSensorThresholdStatus
    MAX-ACCESS   read-only
    STATUS       current
    DESCRIPTION
        "Cisco Firepower adaptor:HostFcIf:voltage managed object property"
    ::= { cfprApAdaptorHostFcIfEntry 61 }

cfprApAdaptorHostFcIfWwn OBJECT-TYPE
    SYNTAX       Unsigned64
    MAX-ACCESS   read-only
    STATUS       current
    DESCRIPTION
        "Cisco Firepower adaptor:HostFcIf:wwn managed object property"
    ::= { cfprApAdaptorHostFcIfEntry 62 }

cfprApAdaptorHostFcIfFsmTable OBJECT-TYPE
    SYNTAX           SEQUENCE OF CfprApAdaptorHostFcIfFsmEntry
    MAX-ACCESS       not-accessible
    STATUS           current
    DESCRIPTION
        "Cisco Firepower adaptor:HostFcIfFsm managed object table"
    ::= { cfprApAdaptorObjects 62 }

cfprApAdaptorHostFcIfFsmEntry OBJECT-TYPE
    SYNTAX           CfprApAdaptorHostFcIfFsmEntry
    MAX-ACCESS       not-accessible
    STATUS           current
    DESCRIPTION
        "Entry for the cfprApAdaptorHostFcIfFsmTable table."
    INDEX { cfprApAdaptorHostFcIfFsmInstanceId }
    ::= { cfprApAdaptorHostFcIfFsmTable 1 }

CfprApAdaptorHostFcIfFsmEntry ::= SEQUENCE {
    cfprApAdaptorHostFcIfFsmInstanceId                               CfprApManagedObjectId,
    cfprApAdaptorHostFcIfFsmDn                                       CfprApManagedObjectDn,
    cfprApAdaptorHostFcIfFsmRn                                       SnmpAdminString,
    cfprApAdaptorHostFcIfFsmCompletionTime                           DateAndTime,
    cfprApAdaptorHostFcIfFsmCurrentFsm                               CfprApAdaptorHostFcIfFsmCurrentFsm,
    cfprApAdaptorHostFcIfFsmDescrData                                SnmpAdminString,
    cfprApAdaptorHostFcIfFsmFsmStatus                                CfprApFsmFsmStageStatus,
    cfprApAdaptorHostFcIfFsmProgress                                 Gauge32,
    cfprApAdaptorHostFcIfFsmRmtErrCode                               Gauge32,
    cfprApAdaptorHostFcIfFsmRmtErrDescr                              SnmpAdminString,
    cfprApAdaptorHostFcIfFsmRmtRslt                                  CfprApConditionRemoteInvRslt
}

cfprApAdaptorHostFcIfFsmInstanceId OBJECT-TYPE
    SYNTAX       CfprApManagedObjectId
    MAX-ACCESS   not-accessible
    STATUS       current
    DESCRIPTION
        "Instance identifier of the managed object."
    ::= { cfprApAdaptorHostFcIfFsmEntry 1 }

cfprApAdaptorHostFcIfFsmDn OBJECT-TYPE
    SYNTAX       CfprApManagedObjectDn
    MAX-ACCESS   read-only
    STATUS       current
    DESCRIPTION
        "Cisco Firepower adaptor:HostFcIfFsm:dn managed object property"
    ::= { cfprApAdaptorHostFcIfFsmEntry 2 }

cfprApAdaptorHostFcIfFsmRn OBJECT-TYPE
    SYNTAX       SnmpAdminString
    MAX-ACCESS   read-only
    STATUS       current
    DESCRIPTION
        "Cisco Firepower adaptor:HostFcIfFsm:rn managed object property"
    ::= { cfprApAdaptorHostFcIfFsmEntry 3 }

cfprApAdaptorHostFcIfFsmCompletionTime OBJECT-TYPE
    SYNTAX       DateAndTime
    MAX-ACCESS   read-only
    STATUS       current
    DESCRIPTION
        "Cisco Firepower adaptor:HostFcIfFsm:completionTime
        managed object property"
    ::= { cfprApAdaptorHostFcIfFsmEntry 4 }

cfprApAdaptorHostFcIfFsmCurrentFsm OBJECT-TYPE
    SYNTAX       CfprApAdaptorHostFcIfFsmCurrentFsm
    MAX-ACCESS   read-only
    STATUS       current
    DESCRIPTION
        "Cisco Firepower adaptor:HostFcIfFsm:currentFsm
        managed object property"
    ::= { cfprApAdaptorHostFcIfFsmEntry 5 }

cfprApAdaptorHostFcIfFsmDescrData OBJECT-TYPE
    SYNTAX       SnmpAdminString
    MAX-ACCESS   read-only
    STATUS       current
    DESCRIPTION
        "Cisco Firepower adaptor:HostFcIfFsm:descr managed
        object property"
    ::= { cfprApAdaptorHostFcIfFsmEntry 6 }

cfprApAdaptorHostFcIfFsmFsmStatus OBJECT-TYPE
    SYNTAX       CfprApFsmFsmStageStatus
    MAX-ACCESS   read-only
    STATUS       current
    DESCRIPTION
        "Cisco Firepower adaptor:HostFcIfFsm:fsmStatus
        managed object property"
    ::= { cfprApAdaptorHostFcIfFsmEntry 7 }

cfprApAdaptorHostFcIfFsmProgress OBJECT-TYPE
    SYNTAX       Gauge32
    MAX-ACCESS   read-only
    STATUS       current
    DESCRIPTION
        "Cisco Firepower adaptor:HostFcIfFsm:progress managed
        object property"
    ::= { cfprApAdaptorHostFcIfFsmEntry 8 }

cfprApAdaptorHostFcIfFsmRmtErrCode OBJECT-TYPE
    SYNTAX       Gauge32
    MAX-ACCESS   read-only
    STATUS       current
    DESCRIPTION
        "Cisco Firepower adaptor:HostFcIfFsm:rmtErrCode
        managed object property"
    ::= { cfprApAdaptorHostFcIfFsmEntry 9 }

cfprApAdaptorHostFcIfFsmRmtErrDescr OBJECT-TYPE
    SYNTAX       SnmpAdminString
    MAX-ACCESS   read-only
    STATUS       current
    DESCRIPTION
        "Cisco Firepower adaptor:HostFcIfFsm:rmtErrDescr
        managed object property"
    ::= { cfprApAdaptorHostFcIfFsmEntry 10 }

cfprApAdaptorHostFcIfFsmRmtRslt OBJECT-TYPE
    SYNTAX       CfprApConditionRemoteInvRslt
    MAX-ACCESS   read-only
    STATUS       current
    DESCRIPTION
        "Cisco Firepower adaptor:HostFcIfFsm:rmtRslt managed
        object property"
    ::= { cfprApAdaptorHostFcIfFsmEntry 11 }

cfprApAdaptorHostFcIfFsmStageTable OBJECT-TYPE
    SYNTAX           SEQUENCE OF CfprApAdaptorHostFcIfFsmStageEntry
    MAX-ACCESS       not-accessible
    STATUS           current
    DESCRIPTION
        "Cisco Firepower adaptor:HostFcIfFsmStage managed object table"
    ::= { cfprApAdaptorObjects 63 }

cfprApAdaptorHostFcIfFsmStageEntry OBJECT-TYPE
    SYNTAX           CfprApAdaptorHostFcIfFsmStageEntry
    MAX-ACCESS       not-accessible
    STATUS           current
    DESCRIPTION
        "Entry for the cfprApAdaptorHostFcIfFsmStageTable table."
    INDEX { cfprApAdaptorHostFcIfFsmStageInstanceId }
    ::= { cfprApAdaptorHostFcIfFsmStageTable 1 }

CfprApAdaptorHostFcIfFsmStageEntry ::= SEQUENCE {
    cfprApAdaptorHostFcIfFsmStageInstanceId                          CfprApManagedObjectId,
    cfprApAdaptorHostFcIfFsmStageDn                                  CfprApManagedObjectDn,
    cfprApAdaptorHostFcIfFsmStageRn                                  SnmpAdminString,
    cfprApAdaptorHostFcIfFsmStageDescrData                           SnmpAdminString,
    cfprApAdaptorHostFcIfFsmStageLastUpdateTime                      DateAndTime,
    cfprApAdaptorHostFcIfFsmStageName                                CfprApAdaptorHostFcIfFsmStageName,
    cfprApAdaptorHostFcIfFsmStageOrder                               Gauge32,
    cfprApAdaptorHostFcIfFsmStageRetry                               Gauge32,
    cfprApAdaptorHostFcIfFsmStageStageStatus                         CfprApFsmFsmStageStatus
}

cfprApAdaptorHostFcIfFsmStageInstanceId OBJECT-TYPE
    SYNTAX       CfprApManagedObjectId
    MAX-ACCESS   not-accessible
    STATUS       current
    DESCRIPTION
        "Instance identifier of the managed object."
    ::= { cfprApAdaptorHostFcIfFsmStageEntry 1 }

cfprApAdaptorHostFcIfFsmStageDn OBJECT-TYPE
    SYNTAX       CfprApManagedObjectDn
    MAX-ACCESS   read-only
    STATUS       current
    DESCRIPTION
        "Cisco Firepower adaptor:HostFcIfFsmStage:dn managed
        object property"
    ::= { cfprApAdaptorHostFcIfFsmStageEntry 2 }

cfprApAdaptorHostFcIfFsmStageRn OBJECT-TYPE
    SYNTAX       SnmpAdminString
    MAX-ACCESS   read-only
    STATUS       current
    DESCRIPTION
        "Cisco Firepower adaptor:HostFcIfFsmStage:rn managed
        object property"
    ::= { cfprApAdaptorHostFcIfFsmStageEntry 3 }

cfprApAdaptorHostFcIfFsmStageDescrData OBJECT-TYPE
    SYNTAX       SnmpAdminString
    MAX-ACCESS   read-only
    STATUS       current
    DESCRIPTION
        "Cisco Firepower adaptor:HostFcIfFsmStage:descr
        managed object property"
    ::= { cfprApAdaptorHostFcIfFsmStageEntry 4 }

cfprApAdaptorHostFcIfFsmStageLastUpdateTime OBJECT-TYPE
    SYNTAX       DateAndTime
    MAX-ACCESS   read-only
    STATUS       current
    DESCRIPTION
        "Cisco Firepower adaptor:HostFcIfFsmStage:lastUpdateTime
        managed object property"
    ::= { cfprApAdaptorHostFcIfFsmStageEntry 5 }

cfprApAdaptorHostFcIfFsmStageName OBJECT-TYPE
    SYNTAX       CfprApAdaptorHostFcIfFsmStageName
    MAX-ACCESS   read-only
    STATUS       current
    DESCRIPTION
        "Cisco Firepower adaptor:HostFcIfFsmStage:name
        managed object property"
    ::= { cfprApAdaptorHostFcIfFsmStageEntry 6 }

cfprApAdaptorHostFcIfFsmStageOrder OBJECT-TYPE
    SYNTAX       Gauge32
    MAX-ACCESS   read-only
    STATUS       current
    DESCRIPTION
        "Cisco Firepower adaptor:HostFcIfFsmStage:order
        managed object property"
    ::= { cfprApAdaptorHostFcIfFsmStageEntry 7 }

cfprApAdaptorHostFcIfFsmStageRetry OBJECT-TYPE
    SYNTAX       Gauge32
    MAX-ACCESS   read-only
    STATUS       current
    DESCRIPTION
        "Cisco Firepower adaptor:HostFcIfFsmStage:retry
        managed object property"
    ::= { cfprApAdaptorHostFcIfFsmStageEntry 8 }

cfprApAdaptorHostFcIfFsmStageStageStatus OBJECT-TYPE
    SYNTAX       CfprApFsmFsmStageStatus
    MAX-ACCESS   read-only
    STATUS       current
    DESCRIPTION
        "Cisco Firepower adaptor:HostFcIfFsmStage:stageStatus
        managed object property"
    ::= { cfprApAdaptorHostFcIfFsmStageEntry 9 }

cfprApAdaptorHostFcIfFsmTaskTable OBJECT-TYPE
    SYNTAX           SEQUENCE OF CfprApAdaptorHostFcIfFsmTaskEntry
    MAX-ACCESS       not-accessible
    STATUS           current
    DESCRIPTION
        "Cisco Firepower adaptor:HostFcIfFsmTask managed object table"
    ::= { cfprApAdaptorObjects 64 }

cfprApAdaptorHostFcIfFsmTaskEntry OBJECT-TYPE
    SYNTAX           CfprApAdaptorHostFcIfFsmTaskEntry
    MAX-ACCESS       not-accessible
    STATUS           current
    DESCRIPTION
        "Entry for the cfprApAdaptorHostFcIfFsmTaskTable table."
    INDEX { cfprApAdaptorHostFcIfFsmTaskInstanceId }
    ::= { cfprApAdaptorHostFcIfFsmTaskTable 1 }

CfprApAdaptorHostFcIfFsmTaskEntry ::= SEQUENCE {
    cfprApAdaptorHostFcIfFsmTaskInstanceId                           CfprApManagedObjectId,
    cfprApAdaptorHostFcIfFsmTaskDn                                   CfprApManagedObjectDn,
    cfprApAdaptorHostFcIfFsmTaskRn                                   SnmpAdminString,
    cfprApAdaptorHostFcIfFsmTaskCompletion                           CfprApFsmCompletion,
    cfprApAdaptorHostFcIfFsmTaskFlags                                CfprApFsmFlags,
    cfprApAdaptorHostFcIfFsmTaskItem                                 CfprApAdaptorHostFcIfFsmTaskItem,
    cfprApAdaptorHostFcIfFsmTaskSeqId                                Gauge32
}

cfprApAdaptorHostFcIfFsmTaskInstanceId OBJECT-TYPE
    SYNTAX       CfprApManagedObjectId
    MAX-ACCESS   not-accessible
    STATUS       current
    DESCRIPTION
        "Instance identifier of the managed object."
    ::= { cfprApAdaptorHostFcIfFsmTaskEntry 1 }

cfprApAdaptorHostFcIfFsmTaskDn OBJECT-TYPE
    SYNTAX       CfprApManagedObjectDn
    MAX-ACCESS   read-only
    STATUS       current
    DESCRIPTION
        "Cisco Firepower adaptor:HostFcIfFsmTask:dn managed
        object property"
    ::= { cfprApAdaptorHostFcIfFsmTaskEntry 2 }

cfprApAdaptorHostFcIfFsmTaskRn OBJECT-TYPE
    SYNTAX       SnmpAdminString
    MAX-ACCESS   read-only
    STATUS       current
    DESCRIPTION
        "Cisco Firepower adaptor:HostFcIfFsmTask:rn managed
        object property"
    ::= { cfprApAdaptorHostFcIfFsmTaskEntry 3 }

cfprApAdaptorHostFcIfFsmTaskCompletion OBJECT-TYPE
    SYNTAX       CfprApFsmCompletion
    MAX-ACCESS   read-only
    STATUS       current
    DESCRIPTION
        "Cisco Firepower adaptor:HostFcIfFsmTask:completion
        managed object property"
    ::= { cfprApAdaptorHostFcIfFsmTaskEntry 4 }

cfprApAdaptorHostFcIfFsmTaskFlags OBJECT-TYPE
    SYNTAX       CfprApFsmFlags
    MAX-ACCESS   read-only
    STATUS       current
    DESCRIPTION
        "Cisco Firepower adaptor:HostFcIfFsmTask:flags
        managed object property"
    ::= { cfprApAdaptorHostFcIfFsmTaskEntry 5 }

cfprApAdaptorHostFcIfFsmTaskItem OBJECT-TYPE
    SYNTAX       CfprApAdaptorHostFcIfFsmTaskItem
    MAX-ACCESS   read-only
    STATUS       current
    DESCRIPTION
        "Cisco Firepower adaptor:HostFcIfFsmTask:item managed
        object property"
    ::= { cfprApAdaptorHostFcIfFsmTaskEntry 6 }

cfprApAdaptorHostFcIfFsmTaskSeqId OBJECT-TYPE
    SYNTAX       Gauge32
    MAX-ACCESS   read-only
    STATUS       current
    DESCRIPTION
        "Cisco Firepower adaptor:HostFcIfFsmTask:seqId
        managed object property"
    ::= { cfprApAdaptorHostFcIfFsmTaskEntry 7 }

cfprApAdaptorHostIscsiIfTable OBJECT-TYPE
    SYNTAX           SEQUENCE OF CfprApAdaptorHostIscsiIfEntry
    MAX-ACCESS       not-accessible
    STATUS           current
    DESCRIPTION
        "Cisco Firepower adaptor:HostIscsiIf managed object table"
    ::= { cfprApAdaptorObjects 66 }

cfprApAdaptorHostIscsiIfEntry OBJECT-TYPE
    SYNTAX           CfprApAdaptorHostIscsiIfEntry
    MAX-ACCESS       not-accessible
    STATUS           current
    DESCRIPTION
        "Entry for the cfprApAdaptorHostIscsiIfTable table."
    INDEX { cfprApAdaptorHostIscsiIfInstanceId }
    ::= { cfprApAdaptorHostIscsiIfTable 1 }

CfprApAdaptorHostIscsiIfEntry ::= SEQUENCE {
    cfprApAdaptorHostIscsiIfInstanceId                               CfprApManagedObjectId,
    cfprApAdaptorHostIscsiIfDn                                       CfprApManagedObjectDn,
    cfprApAdaptorHostIscsiIfRn                                       SnmpAdminString,
    cfprApAdaptorHostIscsiIfAdminState                               CfprApAdaptorHostIfAdminState,
    cfprApAdaptorHostIscsiIfBootDev                                  CfprApAdaptorHostIfBootDev,
    cfprApAdaptorHostIscsiIfChassisId                                Gauge32,
    cfprApAdaptorHostIscsiIfDiscovery                                CfprApEtherSatelliteConnectionDisc,
    cfprApAdaptorHostIscsiIfEpDn                                     SnmpAdminString,
    cfprApAdaptorHostIscsiIfEthEpDn                                  SnmpAdminString,
    cfprApAdaptorHostIscsiIfFltAggr                                  Unsigned64,
    cfprApAdaptorHostIscsiIfHostVisible                              CfprApAdaptorHostVisibility,
    cfprApAdaptorHostIscsiIfId                                       Gauge32,
    cfprApAdaptorHostIscsiIfIfRole                                   CfprApNetworkPortRole,
    cfprApAdaptorHostIscsiIfIfType                                   CfprApNetworkPhysEpIfType,
    cfprApAdaptorHostIscsiIfInitiatorName                            SnmpAdminString,
    cfprApAdaptorHostIscsiIfLc                                       CfprApFsmLifecycle,
    cfprApAdaptorHostIscsiIfLinkState                                CfprApAdaptorLinkState,
    cfprApAdaptorHostIscsiIfLocale                                   CfprApNetworkLocale,
    cfprApAdaptorHostIscsiIfMac                                      MacAddress,
    cfprApAdaptorHostIscsiIfModel                                    SnmpAdminString,
    cfprApAdaptorHostIscsiIfName                                     SnmpAdminString,
    cfprApAdaptorHostIscsiIfOperQualifierReason                      SnmpAdminString,
    cfprApAdaptorHostIscsiIfOperState                                CfprApEquipmentOperability,
    cfprApAdaptorHostIscsiIfOperability                              CfprApEquipmentOperability,
    cfprApAdaptorHostIscsiIfOrder                                    Gauge32,
    cfprApAdaptorHostIscsiIfOriginalMac                              MacAddress,
    cfprApAdaptorHostIscsiIfPciAddr                                  SnmpAdminString,
    cfprApAdaptorHostIscsiIfPciFunc                                  Gauge32,
    cfprApAdaptorHostIscsiIfPciSlot                                  Gauge32,
    cfprApAdaptorHostIscsiIfPeerChassisId                            Gauge32,
    cfprApAdaptorHostIscsiIfPeerDn                                   SnmpAdminString,
    cfprApAdaptorHostIscsiIfPeerPortId                               Gauge32,
    cfprApAdaptorHostIscsiIfPeerSlotId                               Gauge32,
    cfprApAdaptorHostIscsiIfPerf                                     CfprApEquipmentSensorThresholdStatus,
    cfprApAdaptorHostIscsiIfPortId                                   Gauge32,
    cfprApAdaptorHostIscsiIfPower                                    CfprApEquipmentPowerState,
    cfprApAdaptorHostIscsiIfPresence                                 CfprApEquipmentPresence,
    cfprApAdaptorHostIscsiIfPurpose                                  CfprApAdaptorPurpose,
    cfprApAdaptorHostIscsiIfRevision                                 SnmpAdminString,
    cfprApAdaptorHostIscsiIfSerial                                   SnmpAdminString,
    cfprApAdaptorHostIscsiIfServiceState                             CfprApAdaptorServiceState,
    cfprApAdaptorHostIscsiIfSide                                     CfprApNetworkSide,
    cfprApAdaptorHostIscsiIfSlotId                                   Gauge32,
    cfprApAdaptorHostIscsiIfSwitchId                                 CfprApNetworkSwitchId,
    cfprApAdaptorHostIscsiIfThermal                                  CfprApEquipmentSensorThresholdStatus,
    cfprApAdaptorHostIscsiIfTransport                                CfprApNetworkTransport,
    cfprApAdaptorHostIscsiIfType                                     CfprApNetworkConnectionType,
    cfprApAdaptorHostIscsiIfVendor                                   SnmpAdminString,
    cfprApAdaptorHostIscsiIfVnicDn                                   SnmpAdminString,
    cfprApAdaptorHostIscsiIfVnicName                                 SnmpAdminString,
    cfprApAdaptorHostIscsiIfVoltage                                  CfprApEquipmentSensorThresholdStatus
}

cfprApAdaptorHostIscsiIfInstanceId OBJECT-TYPE
    SYNTAX       CfprApManagedObjectId
    MAX-ACCESS   not-accessible
    STATUS       current
    DESCRIPTION
        "Instance identifier of the managed object."
    ::= { cfprApAdaptorHostIscsiIfEntry 1 }

cfprApAdaptorHostIscsiIfDn OBJECT-TYPE
    SYNTAX       CfprApManagedObjectDn
    MAX-ACCESS   read-only
    STATUS       current
    DESCRIPTION
        "Cisco Firepower adaptor:HostIscsiIf:dn managed object property"
    ::= { cfprApAdaptorHostIscsiIfEntry 2 }

cfprApAdaptorHostIscsiIfRn OBJECT-TYPE
    SYNTAX       SnmpAdminString
    MAX-ACCESS   read-only
    STATUS       current
    DESCRIPTION
        "Cisco Firepower adaptor:HostIscsiIf:rn managed object property"
    ::= { cfprApAdaptorHostIscsiIfEntry 3 }

cfprApAdaptorHostIscsiIfAdminState OBJECT-TYPE
    SYNTAX       CfprApAdaptorHostIfAdminState
    MAX-ACCESS   read-only
    STATUS       current
    DESCRIPTION
        "Cisco Firepower adaptor:HostIscsiIf:adminState
        managed object property"
    ::= { cfprApAdaptorHostIscsiIfEntry 4 }

cfprApAdaptorHostIscsiIfBootDev OBJECT-TYPE
    SYNTAX       CfprApAdaptorHostIfBootDev
    MAX-ACCESS   read-only
    STATUS       current
    DESCRIPTION
        "Cisco Firepower adaptor:HostIscsiIf:bootDev managed
        object property"
    ::= { cfprApAdaptorHostIscsiIfEntry 5 }

cfprApAdaptorHostIscsiIfChassisId OBJECT-TYPE
    SYNTAX       Gauge32
    MAX-ACCESS   read-only
    STATUS       current
    DESCRIPTION
        "Cisco Firepower adaptor:HostIscsiIf:chassisId
        managed object property"
    ::= { cfprApAdaptorHostIscsiIfEntry 6 }

cfprApAdaptorHostIscsiIfDiscovery OBJECT-TYPE
    SYNTAX       CfprApEtherSatelliteConnectionDisc
    MAX-ACCESS   read-only
    STATUS       current
    DESCRIPTION
        "Cisco Firepower adaptor:HostIscsiIf:discovery
        managed object property"
    ::= { cfprApAdaptorHostIscsiIfEntry 7 }

cfprApAdaptorHostIscsiIfEpDn OBJECT-TYPE
    SYNTAX       SnmpAdminString
    MAX-ACCESS   read-only
    STATUS       current
    DESCRIPTION
        "Cisco Firepower adaptor:HostIscsiIf:epDn managed object property"
    ::= { cfprApAdaptorHostIscsiIfEntry 8 }

cfprApAdaptorHostIscsiIfEthEpDn OBJECT-TYPE
    SYNTAX       SnmpAdminString
    MAX-ACCESS   read-only
    STATUS       current
    DESCRIPTION
        "Cisco Firepower adaptor:HostIscsiIf:ethEpDn managed
        object property"
    ::= { cfprApAdaptorHostIscsiIfEntry 9 }

cfprApAdaptorHostIscsiIfFltAggr OBJECT-TYPE
    SYNTAX       Unsigned64
    MAX-ACCESS   read-only
    STATUS       current
    DESCRIPTION
        "Cisco Firepower adaptor:HostIscsiIf:fltAggr managed
        object property"
    ::= { cfprApAdaptorHostIscsiIfEntry 10 }

cfprApAdaptorHostIscsiIfHostVisible OBJECT-TYPE
    SYNTAX       CfprApAdaptorHostVisibility
    MAX-ACCESS   read-only
    STATUS       current
    DESCRIPTION
        "Cisco Firepower adaptor:HostIscsiIf:hostVisible
        managed object property"
    ::= { cfprApAdaptorHostIscsiIfEntry 11 }

cfprApAdaptorHostIscsiIfId OBJECT-TYPE
    SYNTAX       Gauge32
    MAX-ACCESS   read-only
    STATUS       current
    DESCRIPTION
        "Cisco Firepower adaptor:HostIscsiIf:id managed object property"
    ::= { cfprApAdaptorHostIscsiIfEntry 12 }

cfprApAdaptorHostIscsiIfIfRole OBJECT-TYPE
    SYNTAX       CfprApNetworkPortRole
    MAX-ACCESS   read-only
    STATUS       current
    DESCRIPTION
        "Cisco Firepower adaptor:HostIscsiIf:ifRole managed
        object property"
    ::= { cfprApAdaptorHostIscsiIfEntry 13 }

cfprApAdaptorHostIscsiIfIfType OBJECT-TYPE
    SYNTAX       CfprApNetworkPhysEpIfType
    MAX-ACCESS   read-only
    STATUS       current
    DESCRIPTION
        "Cisco Firepower adaptor:HostIscsiIf:ifType managed
        object property"
    ::= { cfprApAdaptorHostIscsiIfEntry 14 }

cfprApAdaptorHostIscsiIfInitiatorName OBJECT-TYPE
    SYNTAX       SnmpAdminString
    MAX-ACCESS   read-only
    STATUS       current
    DESCRIPTION
        "Cisco Firepower adaptor:HostIscsiIf:initiatorName
        managed object property"
    ::= { cfprApAdaptorHostIscsiIfEntry 15 }

cfprApAdaptorHostIscsiIfLc OBJECT-TYPE
    SYNTAX       CfprApFsmLifecycle
    MAX-ACCESS   read-only
    STATUS       current
    DESCRIPTION
        "Cisco Firepower adaptor:HostIscsiIf:lc managed object property"
    ::= { cfprApAdaptorHostIscsiIfEntry 16 }

cfprApAdaptorHostIscsiIfLinkState OBJECT-TYPE
    SYNTAX       CfprApAdaptorLinkState
    MAX-ACCESS   read-only
    STATUS       current
    DESCRIPTION
        "Cisco Firepower adaptor:HostIscsiIf:linkState
        managed object property"
    ::= { cfprApAdaptorHostIscsiIfEntry 17 }

cfprApAdaptorHostIscsiIfLocale OBJECT-TYPE
    SYNTAX       CfprApNetworkLocale
    MAX-ACCESS   read-only
    STATUS       current
    DESCRIPTION
        "Cisco Firepower adaptor:HostIscsiIf:locale managed
        object property"
    ::= { cfprApAdaptorHostIscsiIfEntry 18 }

cfprApAdaptorHostIscsiIfMac OBJECT-TYPE
    SYNTAX       MacAddress
    MAX-ACCESS   read-only
    STATUS       current
    DESCRIPTION
        "Cisco Firepower adaptor:HostIscsiIf:mac managed object property"
    ::= { cfprApAdaptorHostIscsiIfEntry 19 }

cfprApAdaptorHostIscsiIfModel OBJECT-TYPE
    SYNTAX       SnmpAdminString
    MAX-ACCESS   read-only
    STATUS       current
    DESCRIPTION
        "Cisco Firepower adaptor:HostIscsiIf:model managed
        object property"
    ::= { cfprApAdaptorHostIscsiIfEntry 20 }

cfprApAdaptorHostIscsiIfName OBJECT-TYPE
    SYNTAX       SnmpAdminString
    MAX-ACCESS   read-only
    STATUS       current
    DESCRIPTION
        "Cisco Firepower adaptor:HostIscsiIf:name managed object property"
    ::= { cfprApAdaptorHostIscsiIfEntry 21 }

cfprApAdaptorHostIscsiIfOperQualifierReason OBJECT-TYPE
    SYNTAX       SnmpAdminString
    MAX-ACCESS   read-only
    STATUS       current
    DESCRIPTION
        "Cisco Firepower adaptor:HostIscsiIf:operQualifierReason
        managed object property"
    ::= { cfprApAdaptorHostIscsiIfEntry 22 }

cfprApAdaptorHostIscsiIfOperState OBJECT-TYPE
    SYNTAX       CfprApEquipmentOperability
    MAX-ACCESS   read-only
    STATUS       current
    DESCRIPTION
        "Cisco Firepower adaptor:HostIscsiIf:operState
        managed object property"
    ::= { cfprApAdaptorHostIscsiIfEntry 23 }

cfprApAdaptorHostIscsiIfOperability OBJECT-TYPE
    SYNTAX       CfprApEquipmentOperability
    MAX-ACCESS   read-only
    STATUS       current
    DESCRIPTION
        "Cisco Firepower adaptor:HostIscsiIf:operability
        managed object property"
    ::= { cfprApAdaptorHostIscsiIfEntry 24 }

cfprApAdaptorHostIscsiIfOrder OBJECT-TYPE
    SYNTAX       Gauge32
    MAX-ACCESS   read-only
    STATUS       current
    DESCRIPTION
        "Cisco Firepower adaptor:HostIscsiIf:order managed
        object property"
    ::= { cfprApAdaptorHostIscsiIfEntry 25 }

cfprApAdaptorHostIscsiIfOriginalMac OBJECT-TYPE
    SYNTAX       MacAddress
    MAX-ACCESS   read-only
    STATUS       current
    DESCRIPTION
        "Cisco Firepower adaptor:HostIscsiIf:originalMac
        managed object property"
    ::= { cfprApAdaptorHostIscsiIfEntry 26 }

cfprApAdaptorHostIscsiIfPciAddr OBJECT-TYPE
    SYNTAX       SnmpAdminString
    MAX-ACCESS   read-only
    STATUS       current
    DESCRIPTION
        "Cisco Firepower adaptor:HostIscsiIf:pciAddr managed
        object property"
    ::= { cfprApAdaptorHostIscsiIfEntry 27 }

cfprApAdaptorHostIscsiIfPciFunc OBJECT-TYPE
    SYNTAX       Gauge32
    MAX-ACCESS   read-only
    STATUS       current
    DESCRIPTION
        "Cisco Firepower adaptor:HostIscsiIf:pciFunc managed
        object property"
    ::= { cfprApAdaptorHostIscsiIfEntry 28 }

cfprApAdaptorHostIscsiIfPciSlot OBJECT-TYPE
    SYNTAX       Gauge32
    MAX-ACCESS   read-only
    STATUS       current
    DESCRIPTION
        "Cisco Firepower adaptor:HostIscsiIf:pciSlot managed
        object property"
    ::= { cfprApAdaptorHostIscsiIfEntry 29 }

cfprApAdaptorHostIscsiIfPeerChassisId OBJECT-TYPE
    SYNTAX       Gauge32
    MAX-ACCESS   read-only
    STATUS       current
    DESCRIPTION
        "Cisco Firepower adaptor:HostIscsiIf:peerChassisId
        managed object property"
    ::= { cfprApAdaptorHostIscsiIfEntry 30 }

cfprApAdaptorHostIscsiIfPeerDn OBJECT-TYPE
    SYNTAX       SnmpAdminString
    MAX-ACCESS   read-only
    STATUS       current
    DESCRIPTION
        "Cisco Firepower adaptor:HostIscsiIf:peerDn managed
        object property"
    ::= { cfprApAdaptorHostIscsiIfEntry 31 }

cfprApAdaptorHostIscsiIfPeerPortId OBJECT-TYPE
    SYNTAX       Gauge32
    MAX-ACCESS   read-only
    STATUS       current
    DESCRIPTION
        "Cisco Firepower adaptor:HostIscsiIf:peerPortId
        managed object property"
    ::= { cfprApAdaptorHostIscsiIfEntry 32 }

cfprApAdaptorHostIscsiIfPeerSlotId OBJECT-TYPE
    SYNTAX       Gauge32
    MAX-ACCESS   read-only
    STATUS       current
    DESCRIPTION
        "Cisco Firepower adaptor:HostIscsiIf:peerSlotId
        managed object property"
    ::= { cfprApAdaptorHostIscsiIfEntry 33 }

cfprApAdaptorHostIscsiIfPerf OBJECT-TYPE
    SYNTAX       CfprApEquipmentSensorThresholdStatus
    MAX-ACCESS   read-only
    STATUS       current
    DESCRIPTION
        "Cisco Firepower adaptor:HostIscsiIf:perf managed object property"
    ::= { cfprApAdaptorHostIscsiIfEntry 34 }

cfprApAdaptorHostIscsiIfPortId OBJECT-TYPE
    SYNTAX       Gauge32
    MAX-ACCESS   read-only
    STATUS       current
    DESCRIPTION
        "Cisco Firepower adaptor:HostIscsiIf:portId managed
        object property"
    ::= { cfprApAdaptorHostIscsiIfEntry 35 }

cfprApAdaptorHostIscsiIfPower OBJECT-TYPE
    SYNTAX       CfprApEquipmentPowerState
    MAX-ACCESS   read-only
    STATUS       current
    DESCRIPTION
        "Cisco Firepower adaptor:HostIscsiIf:power managed
        object property"
    ::= { cfprApAdaptorHostIscsiIfEntry 36 }

cfprApAdaptorHostIscsiIfPresence OBJECT-TYPE
    SYNTAX       CfprApEquipmentPresence
    MAX-ACCESS   read-only
    STATUS       current
    DESCRIPTION
        "Cisco Firepower adaptor:HostIscsiIf:presence managed
        object property"
    ::= { cfprApAdaptorHostIscsiIfEntry 37 }

cfprApAdaptorHostIscsiIfPurpose OBJECT-TYPE
    SYNTAX       CfprApAdaptorPurpose
    MAX-ACCESS   read-only
    STATUS       current
    DESCRIPTION
        "Cisco Firepower adaptor:HostIscsiIf:purpose managed
        object property"
    ::= { cfprApAdaptorHostIscsiIfEntry 38 }

cfprApAdaptorHostIscsiIfRevision OBJECT-TYPE
    SYNTAX       SnmpAdminString
    MAX-ACCESS   read-only
    STATUS       current
    DESCRIPTION
        "Cisco Firepower adaptor:HostIscsiIf:revision managed
        object property"
    ::= { cfprApAdaptorHostIscsiIfEntry 39 }

cfprApAdaptorHostIscsiIfSerial OBJECT-TYPE
    SYNTAX       SnmpAdminString
    MAX-ACCESS   read-only
    STATUS       current
    DESCRIPTION
        "Cisco Firepower adaptor:HostIscsiIf:serial managed
        object property"
    ::= { cfprApAdaptorHostIscsiIfEntry 40 }

cfprApAdaptorHostIscsiIfServiceState OBJECT-TYPE
    SYNTAX       CfprApAdaptorServiceState
    MAX-ACCESS   read-only
    STATUS       current
    DESCRIPTION
        "Cisco Firepower adaptor:HostIscsiIf:serviceState
        managed object property"
    ::= { cfprApAdaptorHostIscsiIfEntry 41 }

cfprApAdaptorHostIscsiIfSide OBJECT-TYPE
    SYNTAX       CfprApNetworkSide
    MAX-ACCESS   read-only
    STATUS       current
    DESCRIPTION
        "Cisco Firepower adaptor:HostIscsiIf:side managed object property"
    ::= { cfprApAdaptorHostIscsiIfEntry 42 }

cfprApAdaptorHostIscsiIfSlotId OBJECT-TYPE
    SYNTAX       Gauge32
    MAX-ACCESS   read-only
    STATUS       current
    DESCRIPTION
        "Cisco Firepower adaptor:HostIscsiIf:slotId managed
        object property"
    ::= { cfprApAdaptorHostIscsiIfEntry 43 }

cfprApAdaptorHostIscsiIfSwitchId OBJECT-TYPE
    SYNTAX       CfprApNetworkSwitchId
    MAX-ACCESS   read-only
    STATUS       current
    DESCRIPTION
        "Cisco Firepower adaptor:HostIscsiIf:switchId managed
        object property"
    ::= { cfprApAdaptorHostIscsiIfEntry 44 }

cfprApAdaptorHostIscsiIfThermal OBJECT-TYPE
    SYNTAX       CfprApEquipmentSensorThresholdStatus
    MAX-ACCESS   read-only
    STATUS       current
    DESCRIPTION
        "Cisco Firepower adaptor:HostIscsiIf:thermal managed
        object property"
    ::= { cfprApAdaptorHostIscsiIfEntry 45 }

cfprApAdaptorHostIscsiIfTransport OBJECT-TYPE
    SYNTAX       CfprApNetworkTransport
    MAX-ACCESS   read-only
    STATUS       current
    DESCRIPTION
        "Cisco Firepower adaptor:HostIscsiIf:transport
        managed object property"
    ::= { cfprApAdaptorHostIscsiIfEntry 46 }

cfprApAdaptorHostIscsiIfType OBJECT-TYPE
    SYNTAX       CfprApNetworkConnectionType
    MAX-ACCESS   read-only
    STATUS       current
    DESCRIPTION
        "Cisco Firepower adaptor:HostIscsiIf:type managed object property"
    ::= { cfprApAdaptorHostIscsiIfEntry 47 }

cfprApAdaptorHostIscsiIfVendor OBJECT-TYPE
    SYNTAX       SnmpAdminString
    MAX-ACCESS   read-only
    STATUS       current
    DESCRIPTION
        "Cisco Firepower adaptor:HostIscsiIf:vendor managed
        object property"
    ::= { cfprApAdaptorHostIscsiIfEntry 48 }

cfprApAdaptorHostIscsiIfVnicDn OBJECT-TYPE
    SYNTAX       SnmpAdminString
    MAX-ACCESS   read-only
    STATUS       current
    DESCRIPTION
        "Cisco Firepower adaptor:HostIscsiIf:vnicDn managed
        object property"
    ::= { cfprApAdaptorHostIscsiIfEntry 49 }

cfprApAdaptorHostIscsiIfVnicName OBJECT-TYPE
    SYNTAX       SnmpAdminString
    MAX-ACCESS   read-only
    STATUS       current
    DESCRIPTION
        "Cisco Firepower adaptor:HostIscsiIf:vnicName managed
        object property"
    ::= { cfprApAdaptorHostIscsiIfEntry 50 }

cfprApAdaptorHostIscsiIfVoltage OBJECT-TYPE
    SYNTAX       CfprApEquipmentSensorThresholdStatus
    MAX-ACCESS   read-only
    STATUS       current
    DESCRIPTION
        "Cisco Firepower adaptor:HostIscsiIf:voltage managed
        object property"
    ::= { cfprApAdaptorHostIscsiIfEntry 51 }

cfprApAdaptorHostMgmtCapTable OBJECT-TYPE
    SYNTAX           SEQUENCE OF CfprApAdaptorHostMgmtCapEntry
    MAX-ACCESS       not-accessible
    STATUS           current
    DESCRIPTION
        "Cisco Firepower adaptor:HostMgmtCap managed object table"
    ::= { cfprApAdaptorObjects 68 }

cfprApAdaptorHostMgmtCapEntry OBJECT-TYPE
    SYNTAX           CfprApAdaptorHostMgmtCapEntry
    MAX-ACCESS       not-accessible
    STATUS           current
    DESCRIPTION
        "Entry for the cfprApAdaptorHostMgmtCapTable table."
    INDEX { cfprApAdaptorHostMgmtCapInstanceId }
    ::= { cfprApAdaptorHostMgmtCapTable 1 }

CfprApAdaptorHostMgmtCapEntry ::= SEQUENCE {
    cfprApAdaptorHostMgmtCapInstanceId                               CfprApManagedObjectId,
    cfprApAdaptorHostMgmtCapDn                                       CfprApManagedObjectDn,
    cfprApAdaptorHostMgmtCapRn                                       SnmpAdminString,
    cfprApAdaptorHostMgmtCapMode                                     CfprApAdaptorMgmtCapMode,
    cfprApAdaptorHostMgmtCapOperPowerRequirement                     CfprApAdaptorMgmtCapOperPowerRequirement,
    cfprApAdaptorHostMgmtCapPreboot                                  CfprApAdaptorHostMgmtCapPreboot,
    cfprApAdaptorHostMgmtCapPresence                                 CfprApAdaptorHostMgmtCapPresence,
    cfprApAdaptorHostMgmtCapRebootActionOnDestructive                CfprApAdaptorMgmtCapRebootActionOnDestructive
}

cfprApAdaptorHostMgmtCapInstanceId OBJECT-TYPE
    SYNTAX       CfprApManagedObjectId
    MAX-ACCESS   not-accessible
    STATUS       current
    DESCRIPTION
        "Instance identifier of the managed object."
    ::= { cfprApAdaptorHostMgmtCapEntry 1 }

cfprApAdaptorHostMgmtCapDn OBJECT-TYPE
    SYNTAX       CfprApManagedObjectDn
    MAX-ACCESS   read-only
    STATUS       current
    DESCRIPTION
        "Cisco Firepower adaptor:HostMgmtCap:dn managed object property"
    ::= { cfprApAdaptorHostMgmtCapEntry 2 }

cfprApAdaptorHostMgmtCapRn OBJECT-TYPE
    SYNTAX       SnmpAdminString
    MAX-ACCESS   read-only
    STATUS       current
    DESCRIPTION
        "Cisco Firepower adaptor:HostMgmtCap:rn managed object property"
    ::= { cfprApAdaptorHostMgmtCapEntry 3 }

cfprApAdaptorHostMgmtCapMode OBJECT-TYPE
    SYNTAX       CfprApAdaptorMgmtCapMode
    MAX-ACCESS   read-only
    STATUS       current
    DESCRIPTION
        "Cisco Firepower adaptor:HostMgmtCap:mode managed object property"
    ::= { cfprApAdaptorHostMgmtCapEntry 4 }

cfprApAdaptorHostMgmtCapOperPowerRequirement OBJECT-TYPE
    SYNTAX       CfprApAdaptorMgmtCapOperPowerRequirement
    MAX-ACCESS   read-only
    STATUS       current
    DESCRIPTION
        "Cisco Firepower adaptor:HostMgmtCap:operPowerRequirement
        managed object property"
    ::= { cfprApAdaptorHostMgmtCapEntry 5 }

cfprApAdaptorHostMgmtCapPreboot OBJECT-TYPE
    SYNTAX       CfprApAdaptorHostMgmtCapPreboot
    MAX-ACCESS   read-only
    STATUS       current
    DESCRIPTION
        "Cisco Firepower adaptor:HostMgmtCap:preboot managed
        object property"
    ::= { cfprApAdaptorHostMgmtCapEntry 6 }

cfprApAdaptorHostMgmtCapPresence OBJECT-TYPE
    SYNTAX       CfprApAdaptorHostMgmtCapPresence
    MAX-ACCESS   read-only
    STATUS       current
    DESCRIPTION
        "Cisco Firepower adaptor:HostMgmtCap:presence managed
        object property"
    ::= { cfprApAdaptorHostMgmtCapEntry 7 }

cfprApAdaptorHostMgmtCapRebootActionOnDestructive OBJECT-TYPE
    SYNTAX       CfprApAdaptorMgmtCapRebootActionOnDestructive
    MAX-ACCESS   read-only
    STATUS       current
    DESCRIPTION
        "Cisco Firepower adaptor:HostMgmtCap:rebootActionOnDestructive
        managed object property"
    ::= { cfprApAdaptorHostMgmtCapEntry 8 }

cfprApAdaptorHostPortTable OBJECT-TYPE
    SYNTAX           SEQUENCE OF CfprApAdaptorHostPortEntry
    MAX-ACCESS       not-accessible
    STATUS           current
    DESCRIPTION
        "Cisco Firepower adaptor:HostPort managed object table"
    ::= { cfprApAdaptorObjects 69 }

cfprApAdaptorHostPortEntry OBJECT-TYPE
    SYNTAX           CfprApAdaptorHostPortEntry
    MAX-ACCESS       not-accessible
    STATUS           current
    DESCRIPTION
        "Entry for the cfprApAdaptorHostPortTable table."
    INDEX { cfprApAdaptorHostPortInstanceId }
    ::= { cfprApAdaptorHostPortTable 1 }

CfprApAdaptorHostPortEntry ::= SEQUENCE {
    cfprApAdaptorHostPortInstanceId                                  CfprApManagedObjectId,
    cfprApAdaptorHostPortDn                                          CfprApManagedObjectDn,
    cfprApAdaptorHostPortRn                                          SnmpAdminString,
    cfprApAdaptorHostPortFltAggr                                     Unsigned64,
    cfprApAdaptorHostPortId                                          CfprApAdaptorHostPortId,
    cfprApAdaptorHostPortLocationDn                                  SnmpAdminString,
    cfprApAdaptorHostPortModel                                       SnmpAdminString,
    cfprApAdaptorHostPortOperQualifierReason                         SnmpAdminString,
    cfprApAdaptorHostPortOperState                                   CfprApEquipmentOperability,
    cfprApAdaptorHostPortOperability                                 CfprApEquipmentOperability,
    cfprApAdaptorHostPortPerf                                        CfprApEquipmentSensorThresholdStatus,
    cfprApAdaptorHostPortPower                                       CfprApEquipmentPowerState,
    cfprApAdaptorHostPortPresence                                    CfprApEquipmentPresence,
    cfprApAdaptorHostPortRevision                                    SnmpAdminString,
    cfprApAdaptorHostPortSerial                                      SnmpAdminString,
    cfprApAdaptorHostPortThermal                                     CfprApEquipmentSensorThresholdStatus,
    cfprApAdaptorHostPortVendor                                      SnmpAdminString,
    cfprApAdaptorHostPortVoltage                                     CfprApEquipmentSensorThresholdStatus
}

cfprApAdaptorHostPortInstanceId OBJECT-TYPE
    SYNTAX       CfprApManagedObjectId
    MAX-ACCESS   not-accessible
    STATUS       current
    DESCRIPTION
        "Instance identifier of the managed object."
    ::= { cfprApAdaptorHostPortEntry 1 }

cfprApAdaptorHostPortDn OBJECT-TYPE
    SYNTAX       CfprApManagedObjectDn
    MAX-ACCESS   read-only
    STATUS       current
    DESCRIPTION
        "Cisco Firepower adaptor:HostPort:dn managed object property"
    ::= { cfprApAdaptorHostPortEntry 2 }

cfprApAdaptorHostPortRn OBJECT-TYPE
    SYNTAX       SnmpAdminString
    MAX-ACCESS   read-only
    STATUS       current
    DESCRIPTION
        "Cisco Firepower adaptor:HostPort:rn managed object property"
    ::= { cfprApAdaptorHostPortEntry 3 }

cfprApAdaptorHostPortFltAggr OBJECT-TYPE
    SYNTAX       Unsigned64
    MAX-ACCESS   read-only
    STATUS       current
    DESCRIPTION
        "Cisco Firepower adaptor:HostPort:fltAggr managed object property"
    ::= { cfprApAdaptorHostPortEntry 4 }

cfprApAdaptorHostPortId OBJECT-TYPE
    SYNTAX       CfprApAdaptorHostPortId
    MAX-ACCESS   read-only
    STATUS       current
    DESCRIPTION
        "Cisco Firepower adaptor:HostPort:id managed object property"
    ::= { cfprApAdaptorHostPortEntry 5 }

cfprApAdaptorHostPortLocationDn OBJECT-TYPE
    SYNTAX       SnmpAdminString
    MAX-ACCESS   read-only
    STATUS       current
    DESCRIPTION
        "Cisco Firepower adaptor:HostPort:locationDn managed
        object property"
    ::= { cfprApAdaptorHostPortEntry 6 }

cfprApAdaptorHostPortModel OBJECT-TYPE
    SYNTAX       SnmpAdminString
    MAX-ACCESS   read-only
    STATUS       current
    DESCRIPTION
        "Cisco Firepower adaptor:HostPort:model managed object property"
    ::= { cfprApAdaptorHostPortEntry 7 }

cfprApAdaptorHostPortOperQualifierReason OBJECT-TYPE
    SYNTAX       SnmpAdminString
    MAX-ACCESS   read-only
    STATUS       current
    DESCRIPTION
        "Cisco Firepower adaptor:HostPort:operQualifierReason
        managed object property"
    ::= { cfprApAdaptorHostPortEntry 8 }

cfprApAdaptorHostPortOperState OBJECT-TYPE
    SYNTAX       CfprApEquipmentOperability
    MAX-ACCESS   read-only
    STATUS       current
    DESCRIPTION
        "Cisco Firepower adaptor:HostPort:operState managed
        object property"
    ::= { cfprApAdaptorHostPortEntry 9 }

cfprApAdaptorHostPortOperability OBJECT-TYPE
    SYNTAX       CfprApEquipmentOperability
    MAX-ACCESS   read-only
    STATUS       current
    DESCRIPTION
        "Cisco Firepower adaptor:HostPort:operability managed
        object property"
    ::= { cfprApAdaptorHostPortEntry 10 }

cfprApAdaptorHostPortPerf OBJECT-TYPE
    SYNTAX       CfprApEquipmentSensorThresholdStatus
    MAX-ACCESS   read-only
    STATUS       current
    DESCRIPTION
        "Cisco Firepower adaptor:HostPort:perf managed object property"
    ::= { cfprApAdaptorHostPortEntry 11 }

cfprApAdaptorHostPortPower OBJECT-TYPE
    SYNTAX       CfprApEquipmentPowerState
    MAX-ACCESS   read-only
    STATUS       current
    DESCRIPTION
        "Cisco Firepower adaptor:HostPort:power managed object property"
    ::= { cfprApAdaptorHostPortEntry 12 }

cfprApAdaptorHostPortPresence OBJECT-TYPE
    SYNTAX       CfprApEquipmentPresence
    MAX-ACCESS   read-only
    STATUS       current
    DESCRIPTION
        "Cisco Firepower adaptor:HostPort:presence managed
        object property"
    ::= { cfprApAdaptorHostPortEntry 13 }

cfprApAdaptorHostPortRevision OBJECT-TYPE
    SYNTAX       SnmpAdminString
    MAX-ACCESS   read-only
    STATUS       current
    DESCRIPTION
        "Cisco Firepower adaptor:HostPort:revision managed
        object property"
    ::= { cfprApAdaptorHostPortEntry 14 }

cfprApAdaptorHostPortSerial OBJECT-TYPE
    SYNTAX       SnmpAdminString
    MAX-ACCESS   read-only
    STATUS       current
    DESCRIPTION
        "Cisco Firepower adaptor:HostPort:serial managed object property"
    ::= { cfprApAdaptorHostPortEntry 15 }

cfprApAdaptorHostPortThermal OBJECT-TYPE
    SYNTAX       CfprApEquipmentSensorThresholdStatus
    MAX-ACCESS   read-only
    STATUS       current
    DESCRIPTION
        "Cisco Firepower adaptor:HostPort:thermal managed object property"
    ::= { cfprApAdaptorHostPortEntry 16 }

cfprApAdaptorHostPortVendor OBJECT-TYPE
    SYNTAX       SnmpAdminString
    MAX-ACCESS   read-only
    STATUS       current
    DESCRIPTION
        "Cisco Firepower adaptor:HostPort:vendor managed object property"
    ::= { cfprApAdaptorHostPortEntry 17 }

cfprApAdaptorHostPortVoltage OBJECT-TYPE
    SYNTAX       CfprApEquipmentSensorThresholdStatus
    MAX-ACCESS   read-only
    STATUS       current
    DESCRIPTION
        "Cisco Firepower adaptor:HostPort:voltage managed object property"
    ::= { cfprApAdaptorHostPortEntry 18 }

cfprApAdaptorHostPortCapTable OBJECT-TYPE
    SYNTAX           SEQUENCE OF CfprApAdaptorHostPortCapEntry
    MAX-ACCESS       not-accessible
    STATUS           current
    DESCRIPTION
        "Cisco Firepower adaptor:HostPortCap managed object table"
    ::= { cfprApAdaptorObjects 70 }

cfprApAdaptorHostPortCapEntry OBJECT-TYPE
    SYNTAX           CfprApAdaptorHostPortCapEntry
    MAX-ACCESS       not-accessible
    STATUS           current
    DESCRIPTION
        "Entry for the cfprApAdaptorHostPortCapTable table."
    INDEX { cfprApAdaptorHostPortCapInstanceId }
    ::= { cfprApAdaptorHostPortCapTable 1 }

CfprApAdaptorHostPortCapEntry ::= SEQUENCE {
    cfprApAdaptorHostPortCapInstanceId                               CfprApManagedObjectId,
    cfprApAdaptorHostPortCapDn                                       CfprApManagedObjectDn,
    cfprApAdaptorHostPortCapRn                                       SnmpAdminString,
    cfprApAdaptorHostPortCapMaxPorts                                 Gauge32
}

cfprApAdaptorHostPortCapInstanceId OBJECT-TYPE
    SYNTAX       CfprApManagedObjectId
    MAX-ACCESS   not-accessible
    STATUS       current
    DESCRIPTION
        "Instance identifier of the managed object."
    ::= { cfprApAdaptorHostPortCapEntry 1 }

cfprApAdaptorHostPortCapDn OBJECT-TYPE
    SYNTAX       CfprApManagedObjectDn
    MAX-ACCESS   read-only
    STATUS       current
    DESCRIPTION
        "Cisco Firepower adaptor:HostPortCap:dn managed object property"
    ::= { cfprApAdaptorHostPortCapEntry 2 }

cfprApAdaptorHostPortCapRn OBJECT-TYPE
    SYNTAX       SnmpAdminString
    MAX-ACCESS   read-only
    STATUS       current
    DESCRIPTION
        "Cisco Firepower adaptor:HostPortCap:rn managed object property"
    ::= { cfprApAdaptorHostPortCapEntry 3 }

cfprApAdaptorHostPortCapMaxPorts OBJECT-TYPE
    SYNTAX       Gauge32
    MAX-ACCESS   read-only
    STATUS       current
    DESCRIPTION
        "Cisco Firepower adaptor:HostPortCap:maxPorts managed
        object property"
    ::= { cfprApAdaptorHostPortCapEntry 4 }

cfprApAdaptorHostServiceEthIfTable OBJECT-TYPE
    SYNTAX           SEQUENCE OF CfprApAdaptorHostServiceEthIfEntry
    MAX-ACCESS       not-accessible
    STATUS           current
    DESCRIPTION
        "Cisco Firepower adaptor:HostServiceEthIf managed object table"
    ::= { cfprApAdaptorObjects 71 }

cfprApAdaptorHostServiceEthIfEntry OBJECT-TYPE
    SYNTAX           CfprApAdaptorHostServiceEthIfEntry
    MAX-ACCESS       not-accessible
    STATUS           current
    DESCRIPTION
        "Entry for the cfprApAdaptorHostServiceEthIfTable table."
    INDEX { cfprApAdaptorHostServiceEthIfInstanceId }
    ::= { cfprApAdaptorHostServiceEthIfTable 1 }

CfprApAdaptorHostServiceEthIfEntry ::= SEQUENCE {
    cfprApAdaptorHostServiceEthIfInstanceId                          CfprApManagedObjectId,
    cfprApAdaptorHostServiceEthIfDn                                  CfprApManagedObjectDn,
    cfprApAdaptorHostServiceEthIfRn                                  SnmpAdminString,
    cfprApAdaptorHostServiceEthIfAdminState                          CfprApAdaptorHostIfAdminState,
    cfprApAdaptorHostServiceEthIfBootDev                             CfprApAdaptorHostIfBootDev,
    cfprApAdaptorHostServiceEthIfChassisId                           Gauge32,
    cfprApAdaptorHostServiceEthIfDiscovery                           CfprApEtherSatelliteConnectionDisc,
    cfprApAdaptorHostServiceEthIfEpDn                                SnmpAdminString,
    cfprApAdaptorHostServiceEthIfFltAggr                             Unsigned64,
    cfprApAdaptorHostServiceEthIfId                                  Gauge32,
    cfprApAdaptorHostServiceEthIfIfRole                              CfprApAdaptorHostServiceEthIfIfRole,
    cfprApAdaptorHostServiceEthIfIfType                              CfprApNetworkPhysEpIfType,
    cfprApAdaptorHostServiceEthIfLc                                  CfprApFsmLifecycle,
    cfprApAdaptorHostServiceEthIfLinkState                           CfprApAdaptorLinkState,
    cfprApAdaptorHostServiceEthIfLocale                              CfprApNetworkLocale,
    cfprApAdaptorHostServiceEthIfMac                                 MacAddress,
    cfprApAdaptorHostServiceEthIfModel                               SnmpAdminString,
    cfprApAdaptorHostServiceEthIfMtu                                 Gauge32,
    cfprApAdaptorHostServiceEthIfName                                SnmpAdminString,
    cfprApAdaptorHostServiceEthIfOperQualifierReason                 SnmpAdminString,
    cfprApAdaptorHostServiceEthIfOperState                           CfprApEquipmentOperability,
    cfprApAdaptorHostServiceEthIfOperability                         CfprApEquipmentOperability,
    cfprApAdaptorHostServiceEthIfOrder                               Gauge32,
    cfprApAdaptorHostServiceEthIfOriginalMac                         MacAddress,
    cfprApAdaptorHostServiceEthIfPciAddr                             SnmpAdminString,
    cfprApAdaptorHostServiceEthIfPciFunc                             Gauge32,
    cfprApAdaptorHostServiceEthIfPciSlot                             Gauge32,
    cfprApAdaptorHostServiceEthIfPeerChassisId                       Gauge32,
    cfprApAdaptorHostServiceEthIfPeerDn                              SnmpAdminString,
    cfprApAdaptorHostServiceEthIfPeerPortId                          Gauge32,
    cfprApAdaptorHostServiceEthIfPeerSlotId                          Gauge32,
    cfprApAdaptorHostServiceEthIfPerf                                CfprApEquipmentSensorThresholdStatus,
    cfprApAdaptorHostServiceEthIfPortId                              Gauge32,
    cfprApAdaptorHostServiceEthIfPower                               CfprApEquipmentPowerState,
    cfprApAdaptorHostServiceEthIfPresence                            CfprApEquipmentPresence,
    cfprApAdaptorHostServiceEthIfPurpose                             CfprApAdaptorPurpose,
    cfprApAdaptorHostServiceEthIfRevision                            SnmpAdminString,
    cfprApAdaptorHostServiceEthIfSerial                              SnmpAdminString,
    cfprApAdaptorHostServiceEthIfServiceState                        CfprApAdaptorServiceState,
    cfprApAdaptorHostServiceEthIfSide                                CfprApNetworkSide,
    cfprApAdaptorHostServiceEthIfSlotId                              Gauge32,
    cfprApAdaptorHostServiceEthIfSwitchId                            CfprApNetworkSwitchId,
    cfprApAdaptorHostServiceEthIfThermal                             CfprApEquipmentSensorThresholdStatus,
    cfprApAdaptorHostServiceEthIfTransport                           CfprApNetworkTransport,
    cfprApAdaptorHostServiceEthIfType                                CfprApNetworkConnectionType,
    cfprApAdaptorHostServiceEthIfVendor                              SnmpAdminString,
    cfprApAdaptorHostServiceEthIfVnicDn                              SnmpAdminString,
    cfprApAdaptorHostServiceEthIfVoltage                             CfprApEquipmentSensorThresholdStatus
}

cfprApAdaptorHostServiceEthIfInstanceId OBJECT-TYPE
    SYNTAX       CfprApManagedObjectId
    MAX-ACCESS   not-accessible
    STATUS       current
    DESCRIPTION
        "Instance identifier of the managed object."
    ::= { cfprApAdaptorHostServiceEthIfEntry 1 }

cfprApAdaptorHostServiceEthIfDn OBJECT-TYPE
    SYNTAX       CfprApManagedObjectDn
    MAX-ACCESS   read-only
    STATUS       current
    DESCRIPTION
        "Cisco Firepower adaptor:HostServiceEthIf:dn managed
        object property"
    ::= { cfprApAdaptorHostServiceEthIfEntry 2 }

cfprApAdaptorHostServiceEthIfRn OBJECT-TYPE
    SYNTAX       SnmpAdminString
    MAX-ACCESS   read-only
    STATUS       current
    DESCRIPTION
        "Cisco Firepower adaptor:HostServiceEthIf:rn managed
        object property"
    ::= { cfprApAdaptorHostServiceEthIfEntry 3 }

cfprApAdaptorHostServiceEthIfAdminState OBJECT-TYPE
    SYNTAX       CfprApAdaptorHostIfAdminState
    MAX-ACCESS   read-only
    STATUS       current
    DESCRIPTION
        "Cisco Firepower adaptor:HostServiceEthIf:adminState
        managed object property"
    ::= { cfprApAdaptorHostServiceEthIfEntry 4 }

cfprApAdaptorHostServiceEthIfBootDev OBJECT-TYPE
    SYNTAX       CfprApAdaptorHostIfBootDev
    MAX-ACCESS   read-only
    STATUS       current
    DESCRIPTION
        "Cisco Firepower adaptor:HostServiceEthIf:bootDev
        managed object property"
    ::= { cfprApAdaptorHostServiceEthIfEntry 5 }

cfprApAdaptorHostServiceEthIfChassisId OBJECT-TYPE
    SYNTAX       Gauge32
    MAX-ACCESS   read-only
    STATUS       current
    DESCRIPTION
        "Cisco Firepower adaptor:HostServiceEthIf:chassisId
        managed object property"
    ::= { cfprApAdaptorHostServiceEthIfEntry 6 }

cfprApAdaptorHostServiceEthIfDiscovery OBJECT-TYPE
    SYNTAX       CfprApEtherSatelliteConnectionDisc
    MAX-ACCESS   read-only
    STATUS       current
    DESCRIPTION
        "Cisco Firepower adaptor:HostServiceEthIf:discovery
        managed object property"
    ::= { cfprApAdaptorHostServiceEthIfEntry 7 }

cfprApAdaptorHostServiceEthIfEpDn OBJECT-TYPE
    SYNTAX       SnmpAdminString
    MAX-ACCESS   read-only
    STATUS       current
    DESCRIPTION
        "Cisco Firepower adaptor:HostServiceEthIf:epDn
        managed object property"
    ::= { cfprApAdaptorHostServiceEthIfEntry 8 }

cfprApAdaptorHostServiceEthIfFltAggr OBJECT-TYPE
    SYNTAX       Unsigned64
    MAX-ACCESS   read-only
    STATUS       current
    DESCRIPTION
        "Cisco Firepower adaptor:HostServiceEthIf:fltAggr
        managed object property"
    ::= { cfprApAdaptorHostServiceEthIfEntry 9 }

cfprApAdaptorHostServiceEthIfId OBJECT-TYPE
    SYNTAX       Gauge32
    MAX-ACCESS   read-only
    STATUS       current
    DESCRIPTION
        "Cisco Firepower adaptor:HostServiceEthIf:id managed
        object property"
    ::= { cfprApAdaptorHostServiceEthIfEntry 10 }

cfprApAdaptorHostServiceEthIfIfRole OBJECT-TYPE
    SYNTAX       CfprApAdaptorHostServiceEthIfIfRole
    MAX-ACCESS   read-only
    STATUS       current
    DESCRIPTION
        "Cisco Firepower adaptor:HostServiceEthIf:ifRole
        managed object property"
    ::= { cfprApAdaptorHostServiceEthIfEntry 11 }

cfprApAdaptorHostServiceEthIfIfType OBJECT-TYPE
    SYNTAX       CfprApNetworkPhysEpIfType
    MAX-ACCESS   read-only
    STATUS       current
    DESCRIPTION
        "Cisco Firepower adaptor:HostServiceEthIf:ifType
        managed object property"
    ::= { cfprApAdaptorHostServiceEthIfEntry 12 }

cfprApAdaptorHostServiceEthIfLc OBJECT-TYPE
    SYNTAX       CfprApFsmLifecycle
    MAX-ACCESS   read-only
    STATUS       current
    DESCRIPTION
        "Cisco Firepower adaptor:HostServiceEthIf:lc managed
        object property"
    ::= { cfprApAdaptorHostServiceEthIfEntry 13 }

cfprApAdaptorHostServiceEthIfLinkState OBJECT-TYPE
    SYNTAX       CfprApAdaptorLinkState
    MAX-ACCESS   read-only
    STATUS       current
    DESCRIPTION
        "Cisco Firepower adaptor:HostServiceEthIf:linkState
        managed object property"
    ::= { cfprApAdaptorHostServiceEthIfEntry 14 }

cfprApAdaptorHostServiceEthIfLocale OBJECT-TYPE
    SYNTAX       CfprApNetworkLocale
    MAX-ACCESS   read-only
    STATUS       current
    DESCRIPTION
        "Cisco Firepower adaptor:HostServiceEthIf:locale
        managed object property"
    ::= { cfprApAdaptorHostServiceEthIfEntry 15 }

cfprApAdaptorHostServiceEthIfMac OBJECT-TYPE
    SYNTAX       MacAddress
    MAX-ACCESS   read-only
    STATUS       current
    DESCRIPTION
        "Cisco Firepower adaptor:HostServiceEthIf:mac managed
        object property"
    ::= { cfprApAdaptorHostServiceEthIfEntry 16 }

cfprApAdaptorHostServiceEthIfModel OBJECT-TYPE
    SYNTAX       SnmpAdminString
    MAX-ACCESS   read-only
    STATUS       current
    DESCRIPTION
        "Cisco Firepower adaptor:HostServiceEthIf:model
        managed object property"
    ::= { cfprApAdaptorHostServiceEthIfEntry 17 }

cfprApAdaptorHostServiceEthIfMtu OBJECT-TYPE
    SYNTAX       Gauge32
    MAX-ACCESS   read-only
    STATUS       current
    DESCRIPTION
        "Cisco Firepower adaptor:HostServiceEthIf:mtu managed
        object property"
    ::= { cfprApAdaptorHostServiceEthIfEntry 18 }

cfprApAdaptorHostServiceEthIfName OBJECT-TYPE
    SYNTAX       SnmpAdminString
    MAX-ACCESS   read-only
    STATUS       current
    DESCRIPTION
        "Cisco Firepower adaptor:HostServiceEthIf:name
        managed object property"
    ::= { cfprApAdaptorHostServiceEthIfEntry 19 }

cfprApAdaptorHostServiceEthIfOperQualifierReason OBJECT-TYPE
    SYNTAX       SnmpAdminString
    MAX-ACCESS   read-only
    STATUS       current
    DESCRIPTION
        "Cisco Firepower adaptor:HostServiceEthIf:operQualifierReason
        managed object property"
    ::= { cfprApAdaptorHostServiceEthIfEntry 20 }

cfprApAdaptorHostServiceEthIfOperState OBJECT-TYPE
    SYNTAX       CfprApEquipmentOperability
    MAX-ACCESS   read-only
    STATUS       current
    DESCRIPTION
        "Cisco Firepower adaptor:HostServiceEthIf:operState
        managed object property"
    ::= { cfprApAdaptorHostServiceEthIfEntry 21 }

cfprApAdaptorHostServiceEthIfOperability OBJECT-TYPE
    SYNTAX       CfprApEquipmentOperability
    MAX-ACCESS   read-only
    STATUS       current
    DESCRIPTION
        "Cisco Firepower adaptor:HostServiceEthIf:operability
        managed object property"
    ::= { cfprApAdaptorHostServiceEthIfEntry 22 }

cfprApAdaptorHostServiceEthIfOrder OBJECT-TYPE
    SYNTAX       Gauge32
    MAX-ACCESS   read-only
    STATUS       current
    DESCRIPTION
        "Cisco Firepower adaptor:HostServiceEthIf:order
        managed object property"
    ::= { cfprApAdaptorHostServiceEthIfEntry 23 }

cfprApAdaptorHostServiceEthIfOriginalMac OBJECT-TYPE
    SYNTAX       MacAddress
    MAX-ACCESS   read-only
    STATUS       current
    DESCRIPTION
        "Cisco Firepower adaptor:HostServiceEthIf:originalMac
        managed object property"
    ::= { cfprApAdaptorHostServiceEthIfEntry 24 }

cfprApAdaptorHostServiceEthIfPciAddr OBJECT-TYPE
    SYNTAX       SnmpAdminString
    MAX-ACCESS   read-only
    STATUS       current
    DESCRIPTION
        "Cisco Firepower adaptor:HostServiceEthIf:pciAddr
        managed object property"
    ::= { cfprApAdaptorHostServiceEthIfEntry 25 }

cfprApAdaptorHostServiceEthIfPciFunc OBJECT-TYPE
    SYNTAX       Gauge32
    MAX-ACCESS   read-only
    STATUS       current
    DESCRIPTION
        "Cisco Firepower adaptor:HostServiceEthIf:pciFunc
        managed object property"
    ::= { cfprApAdaptorHostServiceEthIfEntry 26 }

cfprApAdaptorHostServiceEthIfPciSlot OBJECT-TYPE
    SYNTAX       Gauge32
    MAX-ACCESS   read-only
    STATUS       current
    DESCRIPTION
        "Cisco Firepower adaptor:HostServiceEthIf:pciSlot
        managed object property"
    ::= { cfprApAdaptorHostServiceEthIfEntry 27 }

cfprApAdaptorHostServiceEthIfPeerChassisId OBJECT-TYPE
    SYNTAX       Gauge32
    MAX-ACCESS   read-only
    STATUS       current
    DESCRIPTION
        "Cisco Firepower adaptor:HostServiceEthIf:peerChassisId
        managed object property"
    ::= { cfprApAdaptorHostServiceEthIfEntry 28 }

cfprApAdaptorHostServiceEthIfPeerDn OBJECT-TYPE
    SYNTAX       SnmpAdminString
    MAX-ACCESS   read-only
    STATUS       current
    DESCRIPTION
        "Cisco Firepower adaptor:HostServiceEthIf:peerDn
        managed object property"
    ::= { cfprApAdaptorHostServiceEthIfEntry 29 }

cfprApAdaptorHostServiceEthIfPeerPortId OBJECT-TYPE
    SYNTAX       Gauge32
    MAX-ACCESS   read-only
    STATUS       current
    DESCRIPTION
        "Cisco Firepower adaptor:HostServiceEthIf:peerPortId
        managed object property"
    ::= { cfprApAdaptorHostServiceEthIfEntry 30 }

cfprApAdaptorHostServiceEthIfPeerSlotId OBJECT-TYPE
    SYNTAX       Gauge32
    MAX-ACCESS   read-only
    STATUS       current
    DESCRIPTION
        "Cisco Firepower adaptor:HostServiceEthIf:peerSlotId
        managed object property"
    ::= { cfprApAdaptorHostServiceEthIfEntry 31 }

cfprApAdaptorHostServiceEthIfPerf OBJECT-TYPE
    SYNTAX       CfprApEquipmentSensorThresholdStatus
    MAX-ACCESS   read-only
    STATUS       current
    DESCRIPTION
        "Cisco Firepower adaptor:HostServiceEthIf:perf
        managed object property"
    ::= { cfprApAdaptorHostServiceEthIfEntry 32 }

cfprApAdaptorHostServiceEthIfPortId OBJECT-TYPE
    SYNTAX       Gauge32
    MAX-ACCESS   read-only
    STATUS       current
    DESCRIPTION
        "Cisco Firepower adaptor:HostServiceEthIf:portId
        managed object property"
    ::= { cfprApAdaptorHostServiceEthIfEntry 33 }

cfprApAdaptorHostServiceEthIfPower OBJECT-TYPE
    SYNTAX       CfprApEquipmentPowerState
    MAX-ACCESS   read-only
    STATUS       current
    DESCRIPTION
        "Cisco Firepower adaptor:HostServiceEthIf:power
        managed object property"
    ::= { cfprApAdaptorHostServiceEthIfEntry 34 }

cfprApAdaptorHostServiceEthIfPresence OBJECT-TYPE
    SYNTAX       CfprApEquipmentPresence
    MAX-ACCESS   read-only
    STATUS       current
    DESCRIPTION
        "Cisco Firepower adaptor:HostServiceEthIf:presence
        managed object property"
    ::= { cfprApAdaptorHostServiceEthIfEntry 35 }

cfprApAdaptorHostServiceEthIfPurpose OBJECT-TYPE
    SYNTAX       CfprApAdaptorPurpose
    MAX-ACCESS   read-only
    STATUS       current
    DESCRIPTION
        "Cisco Firepower adaptor:HostServiceEthIf:purpose
        managed object property"
    ::= { cfprApAdaptorHostServiceEthIfEntry 36 }

cfprApAdaptorHostServiceEthIfRevision OBJECT-TYPE
    SYNTAX       SnmpAdminString
    MAX-ACCESS   read-only
    STATUS       current
    DESCRIPTION
        "Cisco Firepower adaptor:HostServiceEthIf:revision
        managed object property"
    ::= { cfprApAdaptorHostServiceEthIfEntry 37 }

cfprApAdaptorHostServiceEthIfSerial OBJECT-TYPE
    SYNTAX       SnmpAdminString
    MAX-ACCESS   read-only
    STATUS       current
    DESCRIPTION
        "Cisco Firepower adaptor:HostServiceEthIf:serial
        managed object property"
    ::= { cfprApAdaptorHostServiceEthIfEntry 38 }

cfprApAdaptorHostServiceEthIfServiceState OBJECT-TYPE
    SYNTAX       CfprApAdaptorServiceState
    MAX-ACCESS   read-only
    STATUS       current
    DESCRIPTION
        "Cisco Firepower adaptor:HostServiceEthIf:serviceState
        managed object property"
    ::= { cfprApAdaptorHostServiceEthIfEntry 39 }

cfprApAdaptorHostServiceEthIfSide OBJECT-TYPE
    SYNTAX       CfprApNetworkSide
    MAX-ACCESS   read-only
    STATUS       current
    DESCRIPTION
        "Cisco Firepower adaptor:HostServiceEthIf:side
        managed object property"
    ::= { cfprApAdaptorHostServiceEthIfEntry 40 }

cfprApAdaptorHostServiceEthIfSlotId OBJECT-TYPE
    SYNTAX       Gauge32
    MAX-ACCESS   read-only
    STATUS       current
    DESCRIPTION
        "Cisco Firepower adaptor:HostServiceEthIf:slotId
        managed object property"
    ::= { cfprApAdaptorHostServiceEthIfEntry 41 }

cfprApAdaptorHostServiceEthIfSwitchId OBJECT-TYPE
    SYNTAX       CfprApNetworkSwitchId
    MAX-ACCESS   read-only
    STATUS       current
    DESCRIPTION
        "Cisco Firepower adaptor:HostServiceEthIf:switchId
        managed object property"
    ::= { cfprApAdaptorHostServiceEthIfEntry 42 }

cfprApAdaptorHostServiceEthIfThermal OBJECT-TYPE
    SYNTAX       CfprApEquipmentSensorThresholdStatus
    MAX-ACCESS   read-only
    STATUS       current
    DESCRIPTION
        "Cisco Firepower adaptor:HostServiceEthIf:thermal
        managed object property"
    ::= { cfprApAdaptorHostServiceEthIfEntry 43 }

cfprApAdaptorHostServiceEthIfTransport OBJECT-TYPE
    SYNTAX       CfprApNetworkTransport
    MAX-ACCESS   read-only
    STATUS       current
    DESCRIPTION
        "Cisco Firepower adaptor:HostServiceEthIf:transport
        managed object property"
    ::= { cfprApAdaptorHostServiceEthIfEntry 44 }

cfprApAdaptorHostServiceEthIfType OBJECT-TYPE
    SYNTAX       CfprApNetworkConnectionType
    MAX-ACCESS   read-only
    STATUS       current
    DESCRIPTION
        "Cisco Firepower adaptor:HostServiceEthIf:type
        managed object property"
    ::= { cfprApAdaptorHostServiceEthIfEntry 45 }

cfprApAdaptorHostServiceEthIfVendor OBJECT-TYPE
    SYNTAX       SnmpAdminString
    MAX-ACCESS   read-only
    STATUS       current
    DESCRIPTION
        "Cisco Firepower adaptor:HostServiceEthIf:vendor
        managed object property"
    ::= { cfprApAdaptorHostServiceEthIfEntry 46 }

cfprApAdaptorHostServiceEthIfVnicDn OBJECT-TYPE
    SYNTAX       SnmpAdminString
    MAX-ACCESS   read-only
    STATUS       current
    DESCRIPTION
        "Cisco Firepower adaptor:HostServiceEthIf:vnicDn
        managed object property"
    ::= { cfprApAdaptorHostServiceEthIfEntry 47 }

cfprApAdaptorHostServiceEthIfVoltage OBJECT-TYPE
    SYNTAX       CfprApEquipmentSensorThresholdStatus
    MAX-ACCESS   read-only
    STATUS       current
    DESCRIPTION
        "Cisco Firepower adaptor:HostServiceEthIf:voltage
        managed object property"
    ::= { cfprApAdaptorHostServiceEthIfEntry 48 }

cfprApAdaptorHostethHwAddrCapTable OBJECT-TYPE
    SYNTAX           SEQUENCE OF CfprApAdaptorHostethHwAddrCapEntry
    MAX-ACCESS       not-accessible
    STATUS           current
    DESCRIPTION
        "Cisco Firepower adaptor:HostethHwAddrCap managed object table"
    ::= { cfprApAdaptorObjects 72 }

cfprApAdaptorHostethHwAddrCapEntry OBJECT-TYPE
    SYNTAX           CfprApAdaptorHostethHwAddrCapEntry
    MAX-ACCESS       not-accessible
    STATUS           current
    DESCRIPTION
        "Entry for the cfprApAdaptorHostethHwAddrCapTable table."
    INDEX { cfprApAdaptorHostethHwAddrCapInstanceId }
    ::= { cfprApAdaptorHostethHwAddrCapTable 1 }

CfprApAdaptorHostethHwAddrCapEntry ::= SEQUENCE {
    cfprApAdaptorHostethHwAddrCapInstanceId                          CfprApManagedObjectId,
    cfprApAdaptorHostethHwAddrCapDn                                  CfprApManagedObjectDn,
    cfprApAdaptorHostethHwAddrCapRn                                  SnmpAdminString,
    cfprApAdaptorHostethHwAddrCapMacOffset1                          Gauge32,
    cfprApAdaptorHostethHwAddrCapMacOffset2                          Gauge32
}

cfprApAdaptorHostethHwAddrCapInstanceId OBJECT-TYPE
    SYNTAX       CfprApManagedObjectId
    MAX-ACCESS   not-accessible
    STATUS       current
    DESCRIPTION
        "Instance identifier of the managed object."
    ::= { cfprApAdaptorHostethHwAddrCapEntry 1 }

cfprApAdaptorHostethHwAddrCapDn OBJECT-TYPE
    SYNTAX       CfprApManagedObjectDn
    MAX-ACCESS   read-only
    STATUS       current
    DESCRIPTION
        "Cisco Firepower adaptor:HostethHwAddrCap:dn managed
        object property"
    ::= { cfprApAdaptorHostethHwAddrCapEntry 2 }

cfprApAdaptorHostethHwAddrCapRn OBJECT-TYPE
    SYNTAX       SnmpAdminString
    MAX-ACCESS   read-only
    STATUS       current
    DESCRIPTION
        "Cisco Firepower adaptor:HostethHwAddrCap:rn managed
        object property"
    ::= { cfprApAdaptorHostethHwAddrCapEntry 3 }

cfprApAdaptorHostethHwAddrCapMacOffset1 OBJECT-TYPE
    SYNTAX       Gauge32
    MAX-ACCESS   read-only
    STATUS       current
    DESCRIPTION
        "Cisco Firepower adaptor:HostethHwAddrCap:macOffset1
        managed object property"
    ::= { cfprApAdaptorHostethHwAddrCapEntry 4 }

cfprApAdaptorHostethHwAddrCapMacOffset2 OBJECT-TYPE
    SYNTAX       Gauge32
    MAX-ACCESS   read-only
    STATUS       current
    DESCRIPTION
        "Cisco Firepower adaptor:HostethHwAddrCap:macOffset2
        managed object property"
    ::= { cfprApAdaptorHostethHwAddrCapEntry 5 }

cfprApAdaptorHostfcHwAddrCapTable OBJECT-TYPE
    SYNTAX           SEQUENCE OF CfprApAdaptorHostfcHwAddrCapEntry
    MAX-ACCESS       not-accessible
    STATUS           current
    DESCRIPTION
        "Cisco Firepower adaptor:HostfcHwAddrCap managed object table"
    ::= { cfprApAdaptorObjects 73 }

cfprApAdaptorHostfcHwAddrCapEntry OBJECT-TYPE
    SYNTAX           CfprApAdaptorHostfcHwAddrCapEntry
    MAX-ACCESS       not-accessible
    STATUS           current
    DESCRIPTION
        "Entry for the cfprApAdaptorHostfcHwAddrCapTable table."
    INDEX { cfprApAdaptorHostfcHwAddrCapInstanceId }
    ::= { cfprApAdaptorHostfcHwAddrCapTable 1 }

CfprApAdaptorHostfcHwAddrCapEntry ::= SEQUENCE {
    cfprApAdaptorHostfcHwAddrCapInstanceId                           CfprApManagedObjectId,
    cfprApAdaptorHostfcHwAddrCapDn                                   CfprApManagedObjectDn,
    cfprApAdaptorHostfcHwAddrCapRn                                   SnmpAdminString,
    cfprApAdaptorHostfcHwAddrCapMacOffset1                           Gauge32,
    cfprApAdaptorHostfcHwAddrCapMacOffset2                           Gauge32,
    cfprApAdaptorHostfcHwAddrCapWwnReverseMaskA                      Unsigned64,
    cfprApAdaptorHostfcHwAddrCapWwnReverseMaskB                      Unsigned64,
    cfprApAdaptorHostfcHwAddrCapWwnnReverseMaskA                     Unsigned64,
    cfprApAdaptorHostfcHwAddrCapWwnnReverseMaskB                     Unsigned64
}

cfprApAdaptorHostfcHwAddrCapInstanceId OBJECT-TYPE
    SYNTAX       CfprApManagedObjectId
    MAX-ACCESS   not-accessible
    STATUS       current
    DESCRIPTION
        "Instance identifier of the managed object."
    ::= { cfprApAdaptorHostfcHwAddrCapEntry 1 }

cfprApAdaptorHostfcHwAddrCapDn OBJECT-TYPE
    SYNTAX       CfprApManagedObjectDn
    MAX-ACCESS   read-only
    STATUS       current
    DESCRIPTION
        "Cisco Firepower adaptor:HostfcHwAddrCap:dn managed
        object property"
    ::= { cfprApAdaptorHostfcHwAddrCapEntry 2 }

cfprApAdaptorHostfcHwAddrCapRn OBJECT-TYPE
    SYNTAX       SnmpAdminString
    MAX-ACCESS   read-only
    STATUS       current
    DESCRIPTION
        "Cisco Firepower adaptor:HostfcHwAddrCap:rn managed
        object property"
    ::= { cfprApAdaptorHostfcHwAddrCapEntry 3 }

cfprApAdaptorHostfcHwAddrCapMacOffset1 OBJECT-TYPE
    SYNTAX       Gauge32
    MAX-ACCESS   read-only
    STATUS       current
    DESCRIPTION
        "Cisco Firepower adaptor:HostfcHwAddrCap:macOffset1
        managed object property"
    ::= { cfprApAdaptorHostfcHwAddrCapEntry 4 }

cfprApAdaptorHostfcHwAddrCapMacOffset2 OBJECT-TYPE
    SYNTAX       Gauge32
    MAX-ACCESS   read-only
    STATUS       current
    DESCRIPTION
        "Cisco Firepower adaptor:HostfcHwAddrCap:macOffset2
        managed object property"
    ::= { cfprApAdaptorHostfcHwAddrCapEntry 5 }

cfprApAdaptorHostfcHwAddrCapWwnReverseMaskA OBJECT-TYPE
    SYNTAX       Unsigned64
    MAX-ACCESS   read-only
    STATUS       current
    DESCRIPTION
        "Cisco Firepower adaptor:HostfcHwAddrCap:wwnReverseMaskA
        managed object property"
    ::= { cfprApAdaptorHostfcHwAddrCapEntry 6 }

cfprApAdaptorHostfcHwAddrCapWwnReverseMaskB OBJECT-TYPE
    SYNTAX       Unsigned64
    MAX-ACCESS   read-only
    STATUS       current
    DESCRIPTION
        "Cisco Firepower adaptor:HostfcHwAddrCap:wwnReverseMaskB
        managed object property"
    ::= { cfprApAdaptorHostfcHwAddrCapEntry 7 }

cfprApAdaptorHostfcHwAddrCapWwnnReverseMaskA OBJECT-TYPE
    SYNTAX       Unsigned64
    MAX-ACCESS   read-only
    STATUS       current
    DESCRIPTION
        "Cisco Firepower adaptor:HostfcHwAddrCap:wwnnReverseMaskA
        managed object property"
    ::= { cfprApAdaptorHostfcHwAddrCapEntry 8 }

cfprApAdaptorHostfcHwAddrCapWwnnReverseMaskB OBJECT-TYPE
    SYNTAX       Unsigned64
    MAX-ACCESS   read-only
    STATUS       current
    DESCRIPTION
        "Cisco Firepower adaptor:HostfcHwAddrCap:wwnnReverseMaskB
        managed object property"
    ::= { cfprApAdaptorHostfcHwAddrCapEntry 9 }

cfprApAdaptorIScsiCapTable OBJECT-TYPE
    SYNTAX           SEQUENCE OF CfprApAdaptorIScsiCapEntry
    MAX-ACCESS       not-accessible
    STATUS           current
    DESCRIPTION
        "Cisco Firepower adaptor:IScsiCap managed object table"
    ::= { cfprApAdaptorObjects 74 }

cfprApAdaptorIScsiCapEntry OBJECT-TYPE
    SYNTAX           CfprApAdaptorIScsiCapEntry
    MAX-ACCESS       not-accessible
    STATUS           current
    DESCRIPTION
        "Entry for the cfprApAdaptorIScsiCapTable table."
    INDEX { cfprApAdaptorIScsiCapInstanceId }
    ::= { cfprApAdaptorIScsiCapTable 1 }

CfprApAdaptorIScsiCapEntry ::= SEQUENCE {
    cfprApAdaptorIScsiCapInstanceId                                  CfprApManagedObjectId,
    cfprApAdaptorIScsiCapDn                                          CfprApManagedObjectDn,
    cfprApAdaptorIScsiCapRn                                          SnmpAdminString,
    cfprApAdaptorIScsiCapBootOrderType                               CfprApAdaptorIScsiCapBootOrderType,
    cfprApAdaptorIScsiCapMacOffset1                                  Gauge32,
    cfprApAdaptorIScsiCapMacOffset2                                  Gauge32,
    cfprApAdaptorIScsiCapOffloadSupport                              TruthValue,
    cfprApAdaptorIScsiCapOffloadType                                 CfprApAdaptorOffloadMethod,
    cfprApAdaptorIScsiCapVlanForBoot                                 TruthValue
}

cfprApAdaptorIScsiCapInstanceId OBJECT-TYPE
    SYNTAX       CfprApManagedObjectId
    MAX-ACCESS   not-accessible
    STATUS       current
    DESCRIPTION
        "Instance identifier of the managed object."
    ::= { cfprApAdaptorIScsiCapEntry 1 }

cfprApAdaptorIScsiCapDn OBJECT-TYPE
    SYNTAX       CfprApManagedObjectDn
    MAX-ACCESS   read-only
    STATUS       current
    DESCRIPTION
        "Cisco Firepower adaptor:IScsiCap:dn managed object property"
    ::= { cfprApAdaptorIScsiCapEntry 2 }

cfprApAdaptorIScsiCapRn OBJECT-TYPE
    SYNTAX       SnmpAdminString
    MAX-ACCESS   read-only
    STATUS       current
    DESCRIPTION
        "Cisco Firepower adaptor:IScsiCap:rn managed object property"
    ::= { cfprApAdaptorIScsiCapEntry 3 }

cfprApAdaptorIScsiCapBootOrderType OBJECT-TYPE
    SYNTAX       CfprApAdaptorIScsiCapBootOrderType
    MAX-ACCESS   read-only
    STATUS       current
    DESCRIPTION
        "Cisco Firepower adaptor:IScsiCap:bootOrderType
        managed object property"
    ::= { cfprApAdaptorIScsiCapEntry 4 }

cfprApAdaptorIScsiCapMacOffset1 OBJECT-TYPE
    SYNTAX       Gauge32
    MAX-ACCESS   read-only
    STATUS       current
    DESCRIPTION
        "Cisco Firepower adaptor:IScsiCap:macOffset1 managed
        object property"
    ::= { cfprApAdaptorIScsiCapEntry 5 }

cfprApAdaptorIScsiCapMacOffset2 OBJECT-TYPE
    SYNTAX       Gauge32
    MAX-ACCESS   read-only
    STATUS       current
    DESCRIPTION
        "Cisco Firepower adaptor:IScsiCap:macOffset2 managed
        object property"
    ::= { cfprApAdaptorIScsiCapEntry 6 }

cfprApAdaptorIScsiCapOffloadSupport OBJECT-TYPE
    SYNTAX       TruthValue
    MAX-ACCESS   read-only
    STATUS       current
    DESCRIPTION
        "Cisco Firepower adaptor:IScsiCap:offloadSupport
        managed object property"
    ::= { cfprApAdaptorIScsiCapEntry 7 }

cfprApAdaptorIScsiCapOffloadType OBJECT-TYPE
    SYNTAX       CfprApAdaptorOffloadMethod
    MAX-ACCESS   read-only
    STATUS       current
    DESCRIPTION
        "Cisco Firepower adaptor:IScsiCap:offloadType managed
        object property"
    ::= { cfprApAdaptorIScsiCapEntry 8 }

cfprApAdaptorIScsiCapVlanForBoot OBJECT-TYPE
    SYNTAX       TruthValue
    MAX-ACCESS   read-only
    STATUS       current
    DESCRIPTION
        "Cisco Firepower adaptor:IScsiCap:vlanForBoot managed
        object property"
    ::= { cfprApAdaptorIScsiCapEntry 9 }

cfprApAdaptorIpV4RssHashProfileTable OBJECT-TYPE
    SYNTAX           SEQUENCE OF CfprApAdaptorIpV4RssHashProfileEntry
    MAX-ACCESS       not-accessible
    STATUS           current
    DESCRIPTION
        "Cisco Firepower adaptor:IpV4RssHashProfile managed object table"
    ::= { cfprApAdaptorObjects 75 }

cfprApAdaptorIpV4RssHashProfileEntry OBJECT-TYPE
    SYNTAX           CfprApAdaptorIpV4RssHashProfileEntry
    MAX-ACCESS       not-accessible
    STATUS           current
    DESCRIPTION
        "Entry for the cfprApAdaptorIpV4RssHashProfileTable table."
    INDEX { cfprApAdaptorIpV4RssHashProfileInstanceId }
    ::= { cfprApAdaptorIpV4RssHashProfileTable 1 }

CfprApAdaptorIpV4RssHashProfileEntry ::= SEQUENCE {
    cfprApAdaptorIpV4RssHashProfileInstanceId                        CfprApManagedObjectId,
    cfprApAdaptorIpV4RssHashProfileDn                                CfprApManagedObjectDn,
    cfprApAdaptorIpV4RssHashProfileRn                                SnmpAdminString,
    cfprApAdaptorIpV4RssHashProfileIpHash                            CfprApAdaptorIpV4RssHashProfileIpHash,
    cfprApAdaptorIpV4RssHashProfileTcpHash                           CfprApAdaptorIpV4RssHashProfileTcpHash
}

cfprApAdaptorIpV4RssHashProfileInstanceId OBJECT-TYPE
    SYNTAX       CfprApManagedObjectId
    MAX-ACCESS   not-accessible
    STATUS       current
    DESCRIPTION
        "Instance identifier of the managed object."
    ::= { cfprApAdaptorIpV4RssHashProfileEntry 1 }

cfprApAdaptorIpV4RssHashProfileDn OBJECT-TYPE
    SYNTAX       CfprApManagedObjectDn
    MAX-ACCESS   read-only
    STATUS       current
    DESCRIPTION
        "Cisco Firepower adaptor:IpV4RssHashProfile:dn
        managed object property"
    ::= { cfprApAdaptorIpV4RssHashProfileEntry 2 }

cfprApAdaptorIpV4RssHashProfileRn OBJECT-TYPE
    SYNTAX       SnmpAdminString
    MAX-ACCESS   read-only
    STATUS       current
    DESCRIPTION
        "Cisco Firepower adaptor:IpV4RssHashProfile:rn
        managed object property"
    ::= { cfprApAdaptorIpV4RssHashProfileEntry 3 }

cfprApAdaptorIpV4RssHashProfileIpHash OBJECT-TYPE
    SYNTAX       CfprApAdaptorIpV4RssHashProfileIpHash
    MAX-ACCESS   read-only
    STATUS       current
    DESCRIPTION
        "Cisco Firepower adaptor:IpV4RssHashProfile:ipHash
        managed object property"
    ::= { cfprApAdaptorIpV4RssHashProfileEntry 4 }

cfprApAdaptorIpV4RssHashProfileTcpHash OBJECT-TYPE
    SYNTAX       CfprApAdaptorIpV4RssHashProfileTcpHash
    MAX-ACCESS   read-only
    STATUS       current
    DESCRIPTION
        "Cisco Firepower adaptor:IpV4RssHashProfile:tcpHash
        managed object property"
    ::= { cfprApAdaptorIpV4RssHashProfileEntry 5 }

cfprApAdaptorIpV6RssHashProfileTable OBJECT-TYPE
    SYNTAX           SEQUENCE OF CfprApAdaptorIpV6RssHashProfileEntry
    MAX-ACCESS       not-accessible
    STATUS           current
    DESCRIPTION
        "Cisco Firepower adaptor:IpV6RssHashProfile managed object table"
    ::= { cfprApAdaptorObjects 76 }

cfprApAdaptorIpV6RssHashProfileEntry OBJECT-TYPE
    SYNTAX           CfprApAdaptorIpV6RssHashProfileEntry
    MAX-ACCESS       not-accessible
    STATUS           current
    DESCRIPTION
        "Entry for the cfprApAdaptorIpV6RssHashProfileTable table."
    INDEX { cfprApAdaptorIpV6RssHashProfileInstanceId }
    ::= { cfprApAdaptorIpV6RssHashProfileTable 1 }

CfprApAdaptorIpV6RssHashProfileEntry ::= SEQUENCE {
    cfprApAdaptorIpV6RssHashProfileInstanceId                        CfprApManagedObjectId,
    cfprApAdaptorIpV6RssHashProfileDn                                CfprApManagedObjectDn,
    cfprApAdaptorIpV6RssHashProfileRn                                SnmpAdminString,
    cfprApAdaptorIpV6RssHashProfileIpHash                            CfprApAdaptorIpV6RssHashProfileIpHash,
    cfprApAdaptorIpV6RssHashProfileTcpHash                           CfprApAdaptorIpV6RssHashProfileTcpHash
}

cfprApAdaptorIpV6RssHashProfileInstanceId OBJECT-TYPE
    SYNTAX       CfprApManagedObjectId
    MAX-ACCESS   not-accessible
    STATUS       current
    DESCRIPTION
        "Instance identifier of the managed object."
    ::= { cfprApAdaptorIpV6RssHashProfileEntry 1 }

cfprApAdaptorIpV6RssHashProfileDn OBJECT-TYPE
    SYNTAX       CfprApManagedObjectDn
    MAX-ACCESS   read-only
    STATUS       current
    DESCRIPTION
        "Cisco Firepower adaptor:IpV6RssHashProfile:dn
        managed object property"
    ::= { cfprApAdaptorIpV6RssHashProfileEntry 2 }

cfprApAdaptorIpV6RssHashProfileRn OBJECT-TYPE
    SYNTAX       SnmpAdminString
    MAX-ACCESS   read-only
    STATUS       current
    DESCRIPTION
        "Cisco Firepower adaptor:IpV6RssHashProfile:rn
        managed object property"
    ::= { cfprApAdaptorIpV6RssHashProfileEntry 3 }

cfprApAdaptorIpV6RssHashProfileIpHash OBJECT-TYPE
    SYNTAX       CfprApAdaptorIpV6RssHashProfileIpHash
    MAX-ACCESS   read-only
    STATUS       current
    DESCRIPTION
        "Cisco Firepower adaptor:IpV6RssHashProfile:ipHash
        managed object property"
    ::= { cfprApAdaptorIpV6RssHashProfileEntry 4 }

cfprApAdaptorIpV6RssHashProfileTcpHash OBJECT-TYPE
    SYNTAX       CfprApAdaptorIpV6RssHashProfileTcpHash
    MAX-ACCESS   read-only
    STATUS       current
    DESCRIPTION
        "Cisco Firepower adaptor:IpV6RssHashProfile:tcpHash
        managed object property"
    ::= { cfprApAdaptorIpV6RssHashProfileEntry 5 }

cfprApAdaptorIscsiAuthTable OBJECT-TYPE
    SYNTAX           SEQUENCE OF CfprApAdaptorIscsiAuthEntry
    MAX-ACCESS       not-accessible
    STATUS           current
    DESCRIPTION
        "Cisco Firepower adaptor:IscsiAuth managed object table"
    ::= { cfprApAdaptorObjects 77 }

cfprApAdaptorIscsiAuthEntry OBJECT-TYPE
    SYNTAX           CfprApAdaptorIscsiAuthEntry
    MAX-ACCESS       not-accessible
    STATUS           current
    DESCRIPTION
        "Entry for the cfprApAdaptorIscsiAuthTable table."
    INDEX { cfprApAdaptorIscsiAuthInstanceId }
    ::= { cfprApAdaptorIscsiAuthTable 1 }

CfprApAdaptorIscsiAuthEntry ::= SEQUENCE {
    cfprApAdaptorIscsiAuthInstanceId                                 CfprApManagedObjectId,
    cfprApAdaptorIscsiAuthDn                                         CfprApManagedObjectDn,
    cfprApAdaptorIscsiAuthRn                                         SnmpAdminString,
    cfprApAdaptorIscsiAuthPassword                                   SnmpAdminString,
    cfprApAdaptorIscsiAuthUserId                                     SnmpAdminString
}

cfprApAdaptorIscsiAuthInstanceId OBJECT-TYPE
    SYNTAX       CfprApManagedObjectId
    MAX-ACCESS   not-accessible
    STATUS       current
    DESCRIPTION
        "Instance identifier of the managed object."
    ::= { cfprApAdaptorIscsiAuthEntry 1 }

cfprApAdaptorIscsiAuthDn OBJECT-TYPE
    SYNTAX       CfprApManagedObjectDn
    MAX-ACCESS   read-only
    STATUS       current
    DESCRIPTION
        "Cisco Firepower adaptor:IscsiAuth:dn managed object property"
    ::= { cfprApAdaptorIscsiAuthEntry 2 }

cfprApAdaptorIscsiAuthRn OBJECT-TYPE
    SYNTAX       SnmpAdminString
    MAX-ACCESS   read-only
    STATUS       current
    DESCRIPTION
        "Cisco Firepower adaptor:IscsiAuth:rn managed object property"
    ::= { cfprApAdaptorIscsiAuthEntry 3 }

cfprApAdaptorIscsiAuthPassword OBJECT-TYPE
    SYNTAX       SnmpAdminString
    MAX-ACCESS   read-only
    STATUS       current
    DESCRIPTION
        "Cisco Firepower adaptor:IscsiAuth:password managed
        object property"
    ::= { cfprApAdaptorIscsiAuthEntry 4 }

cfprApAdaptorIscsiAuthUserId OBJECT-TYPE
    SYNTAX       SnmpAdminString
    MAX-ACCESS   read-only
    STATUS       current
    DESCRIPTION
        "Cisco Firepower adaptor:IscsiAuth:userId managed object property"
    ::= { cfprApAdaptorIscsiAuthEntry 5 }

cfprApAdaptorIscsiProtTable OBJECT-TYPE
    SYNTAX           SEQUENCE OF CfprApAdaptorIscsiProtEntry
    MAX-ACCESS       not-accessible
    STATUS           current
    DESCRIPTION
        "Cisco Firepower adaptor:IscsiProt managed object table"
    ::= { cfprApAdaptorObjects 78 }

cfprApAdaptorIscsiProtEntry OBJECT-TYPE
    SYNTAX           CfprApAdaptorIscsiProtEntry
    MAX-ACCESS       not-accessible
    STATUS           current
    DESCRIPTION
        "Entry for the cfprApAdaptorIscsiProtTable table."
    INDEX { cfprApAdaptorIscsiProtInstanceId }
    ::= { cfprApAdaptorIscsiProtTable 1 }

CfprApAdaptorIscsiProtEntry ::= SEQUENCE {
    cfprApAdaptorIscsiProtInstanceId                                 CfprApManagedObjectId,
    cfprApAdaptorIscsiProtDn                                         CfprApManagedObjectDn,
    cfprApAdaptorIscsiProtRn                                         SnmpAdminString,
    cfprApAdaptorIscsiProtConnectionTimeOut                          CfprApAdaptorIscsiProtConnectionTimeOut,
    cfprApAdaptorIscsiProtDhcpTimeOut                                CfprApAdaptorIscsiProtDhcpTimeOut,
    cfprApAdaptorIscsiProtFltAggr                                    Unsigned64,
    cfprApAdaptorIscsiProtInitiatorName                              SnmpAdminString,
    cfprApAdaptorIscsiProtLunBusyRetryCount                          CfprApAdaptorIscsiProtLunBusyRetryCount,
    cfprApAdaptorIscsiProtTcpTimeStamp                               TruthValue
}

cfprApAdaptorIscsiProtInstanceId OBJECT-TYPE
    SYNTAX       CfprApManagedObjectId
    MAX-ACCESS   not-accessible
    STATUS       current
    DESCRIPTION
        "Instance identifier of the managed object."
    ::= { cfprApAdaptorIscsiProtEntry 1 }

cfprApAdaptorIscsiProtDn OBJECT-TYPE
    SYNTAX       CfprApManagedObjectDn
    MAX-ACCESS   read-only
    STATUS       current
    DESCRIPTION
        "Cisco Firepower adaptor:IscsiProt:dn managed object property"
    ::= { cfprApAdaptorIscsiProtEntry 2 }

cfprApAdaptorIscsiProtRn OBJECT-TYPE
    SYNTAX       SnmpAdminString
    MAX-ACCESS   read-only
    STATUS       current
    DESCRIPTION
        "Cisco Firepower adaptor:IscsiProt:rn managed object property"
    ::= { cfprApAdaptorIscsiProtEntry 3 }

cfprApAdaptorIscsiProtConnectionTimeOut OBJECT-TYPE
    SYNTAX       CfprApAdaptorIscsiProtConnectionTimeOut
    MAX-ACCESS   read-only
    STATUS       current
    DESCRIPTION
        "Cisco Firepower adaptor:IscsiProt:connectionTimeOut
        managed object property"
    ::= { cfprApAdaptorIscsiProtEntry 4 }

cfprApAdaptorIscsiProtDhcpTimeOut OBJECT-TYPE
    SYNTAX       CfprApAdaptorIscsiProtDhcpTimeOut
    MAX-ACCESS   read-only
    STATUS       current
    DESCRIPTION
        "Cisco Firepower adaptor:IscsiProt:dhcpTimeOut
        managed object property"
    ::= { cfprApAdaptorIscsiProtEntry 5 }

cfprApAdaptorIscsiProtFltAggr OBJECT-TYPE
    SYNTAX       Unsigned64
    MAX-ACCESS   read-only
    STATUS       current
    DESCRIPTION
        "Cisco Firepower adaptor:IscsiProt:fltAggr managed
        object property"
    ::= { cfprApAdaptorIscsiProtEntry 6 }

cfprApAdaptorIscsiProtInitiatorName OBJECT-TYPE
    SYNTAX       SnmpAdminString
    MAX-ACCESS   read-only
    STATUS       current
    DESCRIPTION
        "Cisco Firepower adaptor:IscsiProt:initiatorName
        managed object property"
    ::= { cfprApAdaptorIscsiProtEntry 7 }

cfprApAdaptorIscsiProtLunBusyRetryCount OBJECT-TYPE
    SYNTAX       CfprApAdaptorIscsiProtLunBusyRetryCount
    MAX-ACCESS   read-only
    STATUS       current
    DESCRIPTION
        "Cisco Firepower adaptor:IscsiProt:lunBusyRetryCount
        managed object property"
    ::= { cfprApAdaptorIscsiProtEntry 8 }

cfprApAdaptorIscsiProtTcpTimeStamp OBJECT-TYPE
    SYNTAX       TruthValue
    MAX-ACCESS   read-only
    STATUS       current
    DESCRIPTION
        "Cisco Firepower adaptor:IscsiProt:tcpTimeStamp
        managed object property"
    ::= { cfprApAdaptorIscsiProtEntry 9 }

cfprApAdaptorIscsiTargetIfTable OBJECT-TYPE
    SYNTAX           SEQUENCE OF CfprApAdaptorIscsiTargetIfEntry
    MAX-ACCESS       not-accessible
    STATUS           current
    DESCRIPTION
        "Cisco Firepower adaptor:IscsiTargetIf managed object table"
    ::= { cfprApAdaptorObjects 79 }

cfprApAdaptorIscsiTargetIfEntry OBJECT-TYPE
    SYNTAX           CfprApAdaptorIscsiTargetIfEntry
    MAX-ACCESS       not-accessible
    STATUS           current
    DESCRIPTION
        "Entry for the cfprApAdaptorIscsiTargetIfTable table."
    INDEX { cfprApAdaptorIscsiTargetIfInstanceId }
    ::= { cfprApAdaptorIscsiTargetIfTable 1 }

CfprApAdaptorIscsiTargetIfEntry ::= SEQUENCE {
    cfprApAdaptorIscsiTargetIfInstanceId                             CfprApManagedObjectId,
    cfprApAdaptorIscsiTargetIfDn                                     CfprApManagedObjectDn,
    cfprApAdaptorIscsiTargetIfRn                                     SnmpAdminString,
    cfprApAdaptorIscsiTargetIfDhcpVendorId                           SnmpAdminString,
    cfprApAdaptorIscsiTargetIfFltAggr                                Unsigned64,
    cfprApAdaptorIscsiTargetIfIpAddress                              InetAddressIPv4,
    cfprApAdaptorIscsiTargetIfLun                                    Gauge32,
    cfprApAdaptorIscsiTargetIfName                                   SnmpAdminString,
    cfprApAdaptorIscsiTargetIfPortNumber                             Gauge32,
    cfprApAdaptorIscsiTargetIfPriority                               Gauge32
}

cfprApAdaptorIscsiTargetIfInstanceId OBJECT-TYPE
    SYNTAX       CfprApManagedObjectId
    MAX-ACCESS   not-accessible
    STATUS       current
    DESCRIPTION
        "Instance identifier of the managed object."
    ::= { cfprApAdaptorIscsiTargetIfEntry 1 }

cfprApAdaptorIscsiTargetIfDn OBJECT-TYPE
    SYNTAX       CfprApManagedObjectDn
    MAX-ACCESS   read-only
    STATUS       current
    DESCRIPTION
        "Cisco Firepower adaptor:IscsiTargetIf:dn managed object property"
    ::= { cfprApAdaptorIscsiTargetIfEntry 2 }

cfprApAdaptorIscsiTargetIfRn OBJECT-TYPE
    SYNTAX       SnmpAdminString
    MAX-ACCESS   read-only
    STATUS       current
    DESCRIPTION
        "Cisco Firepower adaptor:IscsiTargetIf:rn managed object property"
    ::= { cfprApAdaptorIscsiTargetIfEntry 3 }

cfprApAdaptorIscsiTargetIfDhcpVendorId OBJECT-TYPE
    SYNTAX       SnmpAdminString
    MAX-ACCESS   read-only
    STATUS       current
    DESCRIPTION
        "Cisco Firepower adaptor:IscsiTargetIf:dhcpVendorId
        managed object property"
    ::= { cfprApAdaptorIscsiTargetIfEntry 4 }

cfprApAdaptorIscsiTargetIfFltAggr OBJECT-TYPE
    SYNTAX       Unsigned64
    MAX-ACCESS   read-only
    STATUS       current
    DESCRIPTION
        "Cisco Firepower adaptor:IscsiTargetIf:fltAggr
        managed object property"
    ::= { cfprApAdaptorIscsiTargetIfEntry 5 }

cfprApAdaptorIscsiTargetIfIpAddress OBJECT-TYPE
    SYNTAX       InetAddressIPv4
    MAX-ACCESS   read-only
    STATUS       current
    DESCRIPTION
        "Cisco Firepower adaptor:IscsiTargetIf:ipAddress
        managed object property"
    ::= { cfprApAdaptorIscsiTargetIfEntry 6 }

cfprApAdaptorIscsiTargetIfLun OBJECT-TYPE
    SYNTAX       Gauge32
    MAX-ACCESS   read-only
    STATUS       current
    DESCRIPTION
        "Cisco Firepower adaptor:IscsiTargetIf:lun managed
        object property"
    ::= { cfprApAdaptorIscsiTargetIfEntry 7 }

cfprApAdaptorIscsiTargetIfName OBJECT-TYPE
    SYNTAX       SnmpAdminString
    MAX-ACCESS   read-only
    STATUS       current
    DESCRIPTION
        "Cisco Firepower adaptor:IscsiTargetIf:name managed
        object property"
    ::= { cfprApAdaptorIscsiTargetIfEntry 8 }

cfprApAdaptorIscsiTargetIfPortNumber OBJECT-TYPE
    SYNTAX       Gauge32
    MAX-ACCESS   read-only
    STATUS       current
    DESCRIPTION
        "Cisco Firepower adaptor:IscsiTargetIf:portNumber
        managed object property"
    ::= { cfprApAdaptorIscsiTargetIfEntry 9 }

cfprApAdaptorIscsiTargetIfPriority OBJECT-TYPE
    SYNTAX       Gauge32
    MAX-ACCESS   read-only
    STATUS       current
    DESCRIPTION
        "Cisco Firepower adaptor:IscsiTargetIf:priority
        managed object property"
    ::= { cfprApAdaptorIscsiTargetIfEntry 10 }

cfprApAdaptorLanCapTable OBJECT-TYPE
    SYNTAX           SEQUENCE OF CfprApAdaptorLanCapEntry
    MAX-ACCESS       not-accessible
    STATUS           current
    DESCRIPTION
        "Cisco Firepower adaptor:LanCap managed object table"
    ::= { cfprApAdaptorObjects 80 }

cfprApAdaptorLanCapEntry OBJECT-TYPE
    SYNTAX           CfprApAdaptorLanCapEntry
    MAX-ACCESS       not-accessible
    STATUS           current
    DESCRIPTION
        "Entry for the cfprApAdaptorLanCapTable table."
    INDEX { cfprApAdaptorLanCapInstanceId }
    ::= { cfprApAdaptorLanCapTable 1 }

CfprApAdaptorLanCapEntry ::= SEQUENCE {
    cfprApAdaptorLanCapInstanceId                                    CfprApManagedObjectId,
    cfprApAdaptorLanCapDn                                            CfprApManagedObjectDn,
    cfprApAdaptorLanCapRn                                            SnmpAdminString,
    cfprApAdaptorLanCapDefaultVlan                                   CfprApAdaptorLanCapDefaultVlan
}

cfprApAdaptorLanCapInstanceId OBJECT-TYPE
    SYNTAX       CfprApManagedObjectId
    MAX-ACCESS   not-accessible
    STATUS       current
    DESCRIPTION
        "Instance identifier of the managed object."
    ::= { cfprApAdaptorLanCapEntry 1 }

cfprApAdaptorLanCapDn OBJECT-TYPE
    SYNTAX       CfprApManagedObjectDn
    MAX-ACCESS   read-only
    STATUS       current
    DESCRIPTION
        "Cisco Firepower adaptor:LanCap:dn managed object property"
    ::= { cfprApAdaptorLanCapEntry 2 }

cfprApAdaptorLanCapRn OBJECT-TYPE
    SYNTAX       SnmpAdminString
    MAX-ACCESS   read-only
    STATUS       current
    DESCRIPTION
        "Cisco Firepower adaptor:LanCap:rn managed object property"
    ::= { cfprApAdaptorLanCapEntry 3 }

cfprApAdaptorLanCapDefaultVlan OBJECT-TYPE
    SYNTAX       CfprApAdaptorLanCapDefaultVlan
    MAX-ACCESS   read-only
    STATUS       current
    DESCRIPTION
        "Cisco Firepower adaptor:LanCap:defaultVlan managed
        object property"
    ::= { cfprApAdaptorLanCapEntry 4 }

cfprApAdaptorLldpCapTable OBJECT-TYPE
    SYNTAX           SEQUENCE OF CfprApAdaptorLldpCapEntry
    MAX-ACCESS       not-accessible
    STATUS           current
    DESCRIPTION
        "Cisco Firepower adaptor:LldpCap managed object table"
    ::= { cfprApAdaptorObjects 81 }

cfprApAdaptorLldpCapEntry OBJECT-TYPE
    SYNTAX           CfprApAdaptorLldpCapEntry
    MAX-ACCESS       not-accessible
    STATUS           current
    DESCRIPTION
        "Entry for the cfprApAdaptorLldpCapTable table."
    INDEX { cfprApAdaptorLldpCapInstanceId }
    ::= { cfprApAdaptorLldpCapTable 1 }

CfprApAdaptorLldpCapEntry ::= SEQUENCE {
    cfprApAdaptorLldpCapInstanceId                                   CfprApManagedObjectId,
    cfprApAdaptorLldpCapDn                                           CfprApManagedObjectDn,
    cfprApAdaptorLldpCapRn                                           SnmpAdminString,
    cfprApAdaptorLldpCapSupport                                      CfprApAdaptorLldpCapSupport
}

cfprApAdaptorLldpCapInstanceId OBJECT-TYPE
    SYNTAX       CfprApManagedObjectId
    MAX-ACCESS   not-accessible
    STATUS       current
    DESCRIPTION
        "Instance identifier of the managed object."
    ::= { cfprApAdaptorLldpCapEntry 1 }

cfprApAdaptorLldpCapDn OBJECT-TYPE
    SYNTAX       CfprApManagedObjectDn
    MAX-ACCESS   read-only
    STATUS       current
    DESCRIPTION
        "Cisco Firepower adaptor:LldpCap:dn managed object property"
    ::= { cfprApAdaptorLldpCapEntry 2 }

cfprApAdaptorLldpCapRn OBJECT-TYPE
    SYNTAX       SnmpAdminString
    MAX-ACCESS   read-only
    STATUS       current
    DESCRIPTION
        "Cisco Firepower adaptor:LldpCap:rn managed object property"
    ::= { cfprApAdaptorLldpCapEntry 3 }

cfprApAdaptorLldpCapSupport OBJECT-TYPE
    SYNTAX       CfprApAdaptorLldpCapSupport
    MAX-ACCESS   read-only
    STATUS       current
    DESCRIPTION
        "Cisco Firepower adaptor:LldpCap:support managed object property"
    ::= { cfprApAdaptorLldpCapEntry 4 }

cfprApAdaptorMenloBaseErrorStatsTable OBJECT-TYPE
    SYNTAX           SEQUENCE OF CfprApAdaptorMenloBaseErrorStatsEntry
    MAX-ACCESS       not-accessible
    STATUS           current
    DESCRIPTION
        "Cisco Firepower adaptor:MenloBaseErrorStats managed object table"
    ::= { cfprApAdaptorObjects 82 }

cfprApAdaptorMenloBaseErrorStatsEntry OBJECT-TYPE
    SYNTAX           CfprApAdaptorMenloBaseErrorStatsEntry
    MAX-ACCESS       not-accessible
    STATUS           current
    DESCRIPTION
        "Entry for the cfprApAdaptorMenloBaseErrorStatsTable table."
    INDEX { cfprApAdaptorMenloBaseErrorStatsInstanceId }
    ::= { cfprApAdaptorMenloBaseErrorStatsTable 1 }

CfprApAdaptorMenloBaseErrorStatsEntry ::= SEQUENCE {
    cfprApAdaptorMenloBaseErrorStatsInstanceId                       CfprApManagedObjectId,
    cfprApAdaptorMenloBaseErrorStatsDn                               CfprApManagedObjectDn,
    cfprApAdaptorMenloBaseErrorStatsRn                               SnmpAdminString,
    cfprApAdaptorMenloBaseErrorStatsCorrectableErrors                Unsigned64,
    cfprApAdaptorMenloBaseErrorStatsCorrectableErrorsDelta           Counter64,
    cfprApAdaptorMenloBaseErrorStatsCorrectableErrorsDeltaAvg        Unsigned64,
    cfprApAdaptorMenloBaseErrorStatsCorrectableErrorsDeltaMax        Unsigned64,
    cfprApAdaptorMenloBaseErrorStatsCorrectableErrorsDeltaMin        Unsigned64,
    cfprApAdaptorMenloBaseErrorStatsIntervals                        Gauge32,
    cfprApAdaptorMenloBaseErrorStatsSuspect                          TruthValue,
    cfprApAdaptorMenloBaseErrorStatsThresholded                      CfprApAdaptorMenloBaseErrorStatsThresholded,
    cfprApAdaptorMenloBaseErrorStatsTimeCollected                    DateAndTime,
    cfprApAdaptorMenloBaseErrorStatsUncorrectableErrors              Unsigned64,
    cfprApAdaptorMenloBaseErrorStatsUncorrectableErrorsDelta         Counter64,
    cfprApAdaptorMenloBaseErrorStatsUncorrectableErrorsDeltaAvg      Unsigned64,
    cfprApAdaptorMenloBaseErrorStatsUncorrectableErrorsDeltaMax      Unsigned64,
    cfprApAdaptorMenloBaseErrorStatsUncorrectableErrorsDeltaMin      Unsigned64,
    cfprApAdaptorMenloBaseErrorStatsUpdate                           Gauge32
}

cfprApAdaptorMenloBaseErrorStatsInstanceId OBJECT-TYPE
    SYNTAX       CfprApManagedObjectId
    MAX-ACCESS   not-accessible
    STATUS       current
    DESCRIPTION
        "Instance identifier of the managed object."
    ::= { cfprApAdaptorMenloBaseErrorStatsEntry 1 }

cfprApAdaptorMenloBaseErrorStatsDn OBJECT-TYPE
    SYNTAX       CfprApManagedObjectDn
    MAX-ACCESS   read-only
    STATUS       current
    DESCRIPTION
        "Cisco Firepower adaptor:MenloBaseErrorStats:dn
        managed object property"
    ::= { cfprApAdaptorMenloBaseErrorStatsEntry 2 }

cfprApAdaptorMenloBaseErrorStatsRn OBJECT-TYPE
    SYNTAX       SnmpAdminString
    MAX-ACCESS   read-only
    STATUS       current
    DESCRIPTION
        "Cisco Firepower adaptor:MenloBaseErrorStats:rn
        managed object property"
    ::= { cfprApAdaptorMenloBaseErrorStatsEntry 3 }

cfprApAdaptorMenloBaseErrorStatsCorrectableErrors OBJECT-TYPE
    SYNTAX       Unsigned64
    MAX-ACCESS   read-only
    STATUS       current
    DESCRIPTION
        "Cisco Firepower adaptor:MenloBaseErrorStats:correctableErrors
        managed object property"
    ::= { cfprApAdaptorMenloBaseErrorStatsEntry 4 }

cfprApAdaptorMenloBaseErrorStatsCorrectableErrorsDelta OBJECT-TYPE
    SYNTAX       Counter64
    MAX-ACCESS   read-only
    STATUS       current
    DESCRIPTION
        "Cisco Firepower adaptor:MenloBaseErrorStats:correctableErrorsDelt
        a managed object property"
    ::= { cfprApAdaptorMenloBaseErrorStatsEntry 5 }

cfprApAdaptorMenloBaseErrorStatsCorrectableErrorsDeltaAvg OBJECT-TYPE
    SYNTAX       Unsigned64
    MAX-ACCESS   read-only
    STATUS       current
    DESCRIPTION
        "Cisco Firepower adaptor:MenloBaseErrorStats:correctableErrorsDelt
        aAvg managed object property"
    ::= { cfprApAdaptorMenloBaseErrorStatsEntry 6 }

cfprApAdaptorMenloBaseErrorStatsCorrectableErrorsDeltaMax OBJECT-TYPE
    SYNTAX       Unsigned64
    MAX-ACCESS   read-only
    STATUS       current
    DESCRIPTION
        "Cisco Firepower adaptor:MenloBaseErrorStats:correctableErrorsDelt
        aMax managed object property"
    ::= { cfprApAdaptorMenloBaseErrorStatsEntry 7 }

cfprApAdaptorMenloBaseErrorStatsCorrectableErrorsDeltaMin OBJECT-TYPE
    SYNTAX       Unsigned64
    MAX-ACCESS   read-only
    STATUS       current
    DESCRIPTION
        "Cisco Firepower adaptor:MenloBaseErrorStats:correctableErrorsDelt
        aMin managed object property"
    ::= { cfprApAdaptorMenloBaseErrorStatsEntry 8 }

cfprApAdaptorMenloBaseErrorStatsIntervals OBJECT-TYPE
    SYNTAX       Gauge32
    MAX-ACCESS   read-only
    STATUS       current
    DESCRIPTION
        "Cisco Firepower adaptor:MenloBaseErrorStats:intervals
        managed object property"
    ::= { cfprApAdaptorMenloBaseErrorStatsEntry 9 }

cfprApAdaptorMenloBaseErrorStatsSuspect OBJECT-TYPE
    SYNTAX       TruthValue
    MAX-ACCESS   read-only
    STATUS       current
    DESCRIPTION
        "Cisco Firepower adaptor:MenloBaseErrorStats:suspect
        managed object property"
    ::= { cfprApAdaptorMenloBaseErrorStatsEntry 10 }

cfprApAdaptorMenloBaseErrorStatsThresholded OBJECT-TYPE
    SYNTAX       CfprApAdaptorMenloBaseErrorStatsThresholded
    MAX-ACCESS   read-only
    STATUS       current
    DESCRIPTION
        "Cisco Firepower adaptor:MenloBaseErrorStats:thresholded
        managed object property"
    ::= { cfprApAdaptorMenloBaseErrorStatsEntry 11 }

cfprApAdaptorMenloBaseErrorStatsTimeCollected OBJECT-TYPE
    SYNTAX       DateAndTime
    MAX-ACCESS   read-only
    STATUS       current
    DESCRIPTION
        "Cisco Firepower adaptor:MenloBaseErrorStats:timeCollected
        managed object property"
    ::= { cfprApAdaptorMenloBaseErrorStatsEntry 12 }

cfprApAdaptorMenloBaseErrorStatsUncorrectableErrors OBJECT-TYPE
    SYNTAX       Unsigned64
    MAX-ACCESS   read-only
    STATUS       current
    DESCRIPTION
        "Cisco Firepower adaptor:MenloBaseErrorStats:uncorrectableErrors
        managed object property"
    ::= { cfprApAdaptorMenloBaseErrorStatsEntry 13 }

cfprApAdaptorMenloBaseErrorStatsUncorrectableErrorsDelta OBJECT-TYPE
    SYNTAX       Counter64
    MAX-ACCESS   read-only
    STATUS       current
    DESCRIPTION
        "Cisco Firepower adaptor:MenloBaseErrorStats:uncorrectableErrorsDe
        lta managed object property"
    ::= { cfprApAdaptorMenloBaseErrorStatsEntry 14 }

cfprApAdaptorMenloBaseErrorStatsUncorrectableErrorsDeltaAvg OBJECT-TYPE
    SYNTAX       Unsigned64
    MAX-ACCESS   read-only
    STATUS       current
    DESCRIPTION
        "Cisco Firepower adaptor:MenloBaseErrorStats:uncorrectableErrorsDe
        ltaAvg managed object property"
    ::= { cfprApAdaptorMenloBaseErrorStatsEntry 15 }

cfprApAdaptorMenloBaseErrorStatsUncorrectableErrorsDeltaMax OBJECT-TYPE
    SYNTAX       Unsigned64
    MAX-ACCESS   read-only
    STATUS       current
    DESCRIPTION
        "Cisco Firepower adaptor:MenloBaseErrorStats:uncorrectableErrorsDe
        ltaMax managed object property"
    ::= { cfprApAdaptorMenloBaseErrorStatsEntry 16 }

cfprApAdaptorMenloBaseErrorStatsUncorrectableErrorsDeltaMin OBJECT-TYPE
    SYNTAX       Unsigned64
    MAX-ACCESS   read-only
    STATUS       current
    DESCRIPTION
        "Cisco Firepower adaptor:MenloBaseErrorStats:uncorrectableErrorsDe
        ltaMin managed object property"
    ::= { cfprApAdaptorMenloBaseErrorStatsEntry 17 }

cfprApAdaptorMenloBaseErrorStatsUpdate OBJECT-TYPE
    SYNTAX       Gauge32
    MAX-ACCESS   read-only
    STATUS       current
    DESCRIPTION
        "Cisco Firepower adaptor:MenloBaseErrorStats:update
        managed object property"
    ::= { cfprApAdaptorMenloBaseErrorStatsEntry 18 }

cfprApAdaptorMenloBaseErrorStatsHistTable OBJECT-TYPE
    SYNTAX           SEQUENCE OF CfprApAdaptorMenloBaseErrorStatsHistEntry
    MAX-ACCESS       not-accessible
    STATUS           current
    DESCRIPTION
        "Cisco Firepower adaptor:MenloBaseErrorStatsHist
        managed object table"
    ::= { cfprApAdaptorObjects 83 }

cfprApAdaptorMenloBaseErrorStatsHistEntry OBJECT-TYPE
    SYNTAX           CfprApAdaptorMenloBaseErrorStatsHistEntry
    MAX-ACCESS       not-accessible
    STATUS           current
    DESCRIPTION
        "Entry for the cfprApAdaptorMenloBaseErrorStatsHistTable table."
    INDEX { cfprApAdaptorMenloBaseErrorStatsHistInstanceId }
    ::= { cfprApAdaptorMenloBaseErrorStatsHistTable 1 }

CfprApAdaptorMenloBaseErrorStatsHistEntry ::= SEQUENCE {
    cfprApAdaptorMenloBaseErrorStatsHistInstanceId                   CfprApManagedObjectId,
    cfprApAdaptorMenloBaseErrorStatsHistDn                           CfprApManagedObjectDn,
    cfprApAdaptorMenloBaseErrorStatsHistRn                           SnmpAdminString,
    cfprApAdaptorMenloBaseErrorStatsHistCorrectableErrors            Unsigned64,
    cfprApAdaptorMenloBaseErrorStatsHistCorrectableErrorsDelta       Unsigned64,
    cfprApAdaptorMenloBaseErrorStatsHistCorrectableErrorsDeltaAvg    Unsigned64,
    cfprApAdaptorMenloBaseErrorStatsHistCorrectableErrorsDeltaMax    Unsigned64,
    cfprApAdaptorMenloBaseErrorStatsHistCorrectableErrorsDeltaMin    Unsigned64,
    cfprApAdaptorMenloBaseErrorStatsHistId                           Unsigned64,
    cfprApAdaptorMenloBaseErrorStatsHistMostRecent                   TruthValue,
    cfprApAdaptorMenloBaseErrorStatsHistSuspect                      TruthValue,
    cfprApAdaptorMenloBaseErrorStatsHistThresholded                  CfprApAdaptorMenloBaseErrorStatsHistThresholded,
    cfprApAdaptorMenloBaseErrorStatsHistTimeCollected                DateAndTime,
    cfprApAdaptorMenloBaseErrorStatsHistUncorrectableErrors          Unsigned64,
    cfprApAdaptorMenloBaseErrorStatsHistUncorrectableErrorsDelta     Unsigned64,
    cfprApAdaptorMenloBaseErrorStatsHistUncorrectableErrorsDeltaAvg  Unsigned64,
    cfprApAdaptorMenloBaseErrorStatsHistUncorrectableErrorsDeltaMax  Unsigned64,
    cfprApAdaptorMenloBaseErrorStatsHistUncorrectableErrorsDeltaMin  Unsigned64
}

cfprApAdaptorMenloBaseErrorStatsHistInstanceId OBJECT-TYPE
    SYNTAX       CfprApManagedObjectId
    MAX-ACCESS   not-accessible
    STATUS       current
    DESCRIPTION
        "Instance identifier of the managed object."
    ::= { cfprApAdaptorMenloBaseErrorStatsHistEntry 1 }

cfprApAdaptorMenloBaseErrorStatsHistDn OBJECT-TYPE
    SYNTAX       CfprApManagedObjectDn
    MAX-ACCESS   read-only
    STATUS       current
    DESCRIPTION
        "Cisco Firepower adaptor:MenloBaseErrorStatsHist:dn
        managed object property"
    ::= { cfprApAdaptorMenloBaseErrorStatsHistEntry 2 }

cfprApAdaptorMenloBaseErrorStatsHistRn OBJECT-TYPE
    SYNTAX       SnmpAdminString
    MAX-ACCESS   read-only
    STATUS       current
    DESCRIPTION
        "Cisco Firepower adaptor:MenloBaseErrorStatsHist:rn
        managed object property"
    ::= { cfprApAdaptorMenloBaseErrorStatsHistEntry 3 }

cfprApAdaptorMenloBaseErrorStatsHistCorrectableErrors OBJECT-TYPE
    SYNTAX       Unsigned64
    MAX-ACCESS   read-only
    STATUS       current
    DESCRIPTION
        "Cisco Firepower adaptor:MenloBaseErrorStatsHist:correctableErrors
         managed object property"
    ::= { cfprApAdaptorMenloBaseErrorStatsHistEntry 4 }

cfprApAdaptorMenloBaseErrorStatsHistCorrectableErrorsDelta OBJECT-TYPE
    SYNTAX       Unsigned64
    MAX-ACCESS   read-only
    STATUS       current
    DESCRIPTION
        "Cisco Firepower adaptor:MenloBaseErrorStatsHist:correctableErrors
        Delta managed object property"
    ::= { cfprApAdaptorMenloBaseErrorStatsHistEntry 5 }

cfprApAdaptorMenloBaseErrorStatsHistCorrectableErrorsDeltaAvg OBJECT-TYPE
    SYNTAX       Unsigned64
    MAX-ACCESS   read-only
    STATUS       current
    DESCRIPTION
        "Cisco Firepower adaptor:MenloBaseErrorStatsHist:correctableErrors
        DeltaAvg managed object property"
    ::= { cfprApAdaptorMenloBaseErrorStatsHistEntry 6 }

cfprApAdaptorMenloBaseErrorStatsHistCorrectableErrorsDeltaMax OBJECT-TYPE
    SYNTAX       Unsigned64
    MAX-ACCESS   read-only
    STATUS       current
    DESCRIPTION
        "Cisco Firepower adaptor:MenloBaseErrorStatsHist:correctableErrors
        DeltaMax managed object property"
    ::= { cfprApAdaptorMenloBaseErrorStatsHistEntry 7 }

cfprApAdaptorMenloBaseErrorStatsHistCorrectableErrorsDeltaMin OBJECT-TYPE
    SYNTAX       Unsigned64
    MAX-ACCESS   read-only
    STATUS       current
    DESCRIPTION
        "Cisco Firepower adaptor:MenloBaseErrorStatsHist:correctableErrors
        DeltaMin managed object property"
    ::= { cfprApAdaptorMenloBaseErrorStatsHistEntry 8 }

cfprApAdaptorMenloBaseErrorStatsHistId OBJECT-TYPE
    SYNTAX       Unsigned64
    MAX-ACCESS   read-only
    STATUS       current
    DESCRIPTION
        "Cisco Firepower adaptor:MenloBaseErrorStatsHist:id
        managed object property"
    ::= { cfprApAdaptorMenloBaseErrorStatsHistEntry 9 }

cfprApAdaptorMenloBaseErrorStatsHistMostRecent OBJECT-TYPE
    SYNTAX       TruthValue
    MAX-ACCESS   read-only
    STATUS       current
    DESCRIPTION
        "Cisco Firepower adaptor:MenloBaseErrorStatsHist:mostRecent
        managed object property"
    ::= { cfprApAdaptorMenloBaseErrorStatsHistEntry 10 }

cfprApAdaptorMenloBaseErrorStatsHistSuspect OBJECT-TYPE
    SYNTAX       TruthValue
    MAX-ACCESS   read-only
    STATUS       current
    DESCRIPTION
        "Cisco Firepower adaptor:MenloBaseErrorStatsHist:suspect
        managed object property"
    ::= { cfprApAdaptorMenloBaseErrorStatsHistEntry 11 }

cfprApAdaptorMenloBaseErrorStatsHistThresholded OBJECT-TYPE
    SYNTAX       CfprApAdaptorMenloBaseErrorStatsHistThresholded
    MAX-ACCESS   read-only
    STATUS       current
    DESCRIPTION
        "Cisco Firepower adaptor:MenloBaseErrorStatsHist:thresholded
        managed object property"
    ::= { cfprApAdaptorMenloBaseErrorStatsHistEntry 12 }

cfprApAdaptorMenloBaseErrorStatsHistTimeCollected OBJECT-TYPE
    SYNTAX       DateAndTime
    MAX-ACCESS   read-only
    STATUS       current
    DESCRIPTION
        "Cisco Firepower adaptor:MenloBaseErrorStatsHist:timeCollected
        managed object property"
    ::= { cfprApAdaptorMenloBaseErrorStatsHistEntry 13 }

cfprApAdaptorMenloBaseErrorStatsHistUncorrectableErrors OBJECT-TYPE
    SYNTAX       Unsigned64
    MAX-ACCESS   read-only
    STATUS       current
    DESCRIPTION
        "Cisco Firepower adaptor:MenloBaseErrorStatsHist:uncorrectableErro
        rs managed object property"
    ::= { cfprApAdaptorMenloBaseErrorStatsHistEntry 14 }

cfprApAdaptorMenloBaseErrorStatsHistUncorrectableErrorsDelta OBJECT-TYPE
    SYNTAX       Unsigned64
    MAX-ACCESS   read-only
    STATUS       current
    DESCRIPTION
        "Cisco Firepower adaptor:MenloBaseErrorStatsHist:uncorrectableErro
        rsDelta managed object property"
    ::= { cfprApAdaptorMenloBaseErrorStatsHistEntry 15 }

cfprApAdaptorMenloBaseErrorStatsHistUncorrectableErrorsDeltaAvg OBJECT-TYPE
    SYNTAX       Unsigned64
    MAX-ACCESS   read-only
    STATUS       current
    DESCRIPTION
        "Cisco Firepower adaptor:MenloBaseErrorStatsHist:uncorrectableErro
        rsDeltaAvg managed object property"
    ::= { cfprApAdaptorMenloBaseErrorStatsHistEntry 16 }

cfprApAdaptorMenloBaseErrorStatsHistUncorrectableErrorsDeltaMax OBJECT-TYPE
    SYNTAX       Unsigned64
    MAX-ACCESS   read-only
    STATUS       current
    DESCRIPTION
        "Cisco Firepower adaptor:MenloBaseErrorStatsHist:uncorrectableErro
        rsDeltaMax managed object property"
    ::= { cfprApAdaptorMenloBaseErrorStatsHistEntry 17 }

cfprApAdaptorMenloBaseErrorStatsHistUncorrectableErrorsDeltaMin OBJECT-TYPE
    SYNTAX       Unsigned64
    MAX-ACCESS   read-only
    STATUS       current
    DESCRIPTION
        "Cisco Firepower adaptor:MenloBaseErrorStatsHist:uncorrectableErro
        rsDeltaMin managed object property"
    ::= { cfprApAdaptorMenloBaseErrorStatsHistEntry 18 }

cfprApAdaptorMenloDcePortStatsTable OBJECT-TYPE
    SYNTAX           SEQUENCE OF CfprApAdaptorMenloDcePortStatsEntry
    MAX-ACCESS       not-accessible
    STATUS           current
    DESCRIPTION
        "Cisco Firepower adaptor:MenloDcePortStats managed object table"
    ::= { cfprApAdaptorObjects 84 }

cfprApAdaptorMenloDcePortStatsEntry OBJECT-TYPE
    SYNTAX           CfprApAdaptorMenloDcePortStatsEntry
    MAX-ACCESS       not-accessible
    STATUS           current
    DESCRIPTION
        "Entry for the cfprApAdaptorMenloDcePortStatsTable table."
    INDEX { cfprApAdaptorMenloDcePortStatsInstanceId }
    ::= { cfprApAdaptorMenloDcePortStatsTable 1 }

CfprApAdaptorMenloDcePortStatsEntry ::= SEQUENCE {
    cfprApAdaptorMenloDcePortStatsInstanceId                         CfprApManagedObjectId,
    cfprApAdaptorMenloDcePortStatsDn                                 CfprApManagedObjectDn,
    cfprApAdaptorMenloDcePortStatsRn                                 SnmpAdminString,
    cfprApAdaptorMenloDcePortStatsIntervals                          Gauge32,
    cfprApAdaptorMenloDcePortStatsMenloPortIndex                     CfprApAdaptorMenloStatsIndex,
    cfprApAdaptorMenloDcePortStatsRxPauseCFC                         Unsigned64,
    cfprApAdaptorMenloDcePortStatsRxPauseCFCDelta                    Counter64,
    cfprApAdaptorMenloDcePortStatsRxPauseCFCDeltaAvg                 Unsigned64,
    cfprApAdaptorMenloDcePortStatsRxPauseCFCDeltaMax                 Unsigned64,
    cfprApAdaptorMenloDcePortStatsRxPauseCFCDeltaMin                 Unsigned64,
    cfprApAdaptorMenloDcePortStatsRxPausePFC                         Unsigned64,
    cfprApAdaptorMenloDcePortStatsRxPausePFCDelta                    Counter64,
    cfprApAdaptorMenloDcePortStatsRxPausePFCDeltaAvg                 Unsigned64,
    cfprApAdaptorMenloDcePortStatsRxPausePFCDeltaMax                 Unsigned64,
    cfprApAdaptorMenloDcePortStatsRxPausePFCDeltaMin                 Unsigned64,
    cfprApAdaptorMenloDcePortStatsSuspect                            TruthValue,
    cfprApAdaptorMenloDcePortStatsThresholded                        CfprApAdaptorMenloDcePortStatsThresholded,
    cfprApAdaptorMenloDcePortStatsTimeCollected                      DateAndTime,
    cfprApAdaptorMenloDcePortStatsTxPauseCFC                         Unsigned64,
    cfprApAdaptorMenloDcePortStatsTxPauseCFCDelta                    Counter64,
    cfprApAdaptorMenloDcePortStatsTxPauseCFCDeltaAvg                 Unsigned64,
    cfprApAdaptorMenloDcePortStatsTxPauseCFCDeltaMax                 Unsigned64,
    cfprApAdaptorMenloDcePortStatsTxPauseCFCDeltaMin                 Unsigned64,
    cfprApAdaptorMenloDcePortStatsTxPausePFC                         Unsigned64,
    cfprApAdaptorMenloDcePortStatsTxPausePFCDelta                    Counter64,
    cfprApAdaptorMenloDcePortStatsTxPausePFCDeltaAvg                 Unsigned64,
    cfprApAdaptorMenloDcePortStatsTxPausePFCDeltaMax                 Unsigned64,
    cfprApAdaptorMenloDcePortStatsTxPausePFCDeltaMin                 Unsigned64,
    cfprApAdaptorMenloDcePortStatsUpdate                             Gauge32
}

cfprApAdaptorMenloDcePortStatsInstanceId OBJECT-TYPE
    SYNTAX       CfprApManagedObjectId
    MAX-ACCESS   not-accessible
    STATUS       current
    DESCRIPTION
        "Instance identifier of the managed object."
    ::= { cfprApAdaptorMenloDcePortStatsEntry 1 }

cfprApAdaptorMenloDcePortStatsDn OBJECT-TYPE
    SYNTAX       CfprApManagedObjectDn
    MAX-ACCESS   read-only
    STATUS       current
    DESCRIPTION
        "Cisco Firepower adaptor:MenloDcePortStats:dn managed
        object property"
    ::= { cfprApAdaptorMenloDcePortStatsEntry 2 }

cfprApAdaptorMenloDcePortStatsRn OBJECT-TYPE
    SYNTAX       SnmpAdminString
    MAX-ACCESS   read-only
    STATUS       current
    DESCRIPTION
        "Cisco Firepower adaptor:MenloDcePortStats:rn managed
        object property"
    ::= { cfprApAdaptorMenloDcePortStatsEntry 3 }

cfprApAdaptorMenloDcePortStatsIntervals OBJECT-TYPE
    SYNTAX       Gauge32
    MAX-ACCESS   read-only
    STATUS       current
    DESCRIPTION
        "Cisco Firepower adaptor:MenloDcePortStats:intervals
        managed object property"
    ::= { cfprApAdaptorMenloDcePortStatsEntry 4 }

cfprApAdaptorMenloDcePortStatsMenloPortIndex OBJECT-TYPE
    SYNTAX       CfprApAdaptorMenloStatsIndex
    MAX-ACCESS   read-only
    STATUS       current
    DESCRIPTION
        "Cisco Firepower adaptor:MenloDcePortStats:menloPortIndex
        managed object property"
    ::= { cfprApAdaptorMenloDcePortStatsEntry 5 }

cfprApAdaptorMenloDcePortStatsRxPauseCFC OBJECT-TYPE
    SYNTAX       Unsigned64
    MAX-ACCESS   read-only
    STATUS       current
    DESCRIPTION
        "Cisco Firepower adaptor:MenloDcePortStats:rxPauseCFC
        managed object property"
    ::= { cfprApAdaptorMenloDcePortStatsEntry 6 }

cfprApAdaptorMenloDcePortStatsRxPauseCFCDelta OBJECT-TYPE
    SYNTAX       Counter64
    MAX-ACCESS   read-only
    STATUS       current
    DESCRIPTION
        "Cisco Firepower adaptor:MenloDcePortStats:rxPauseCFCDelta
        managed object property"
    ::= { cfprApAdaptorMenloDcePortStatsEntry 7 }

cfprApAdaptorMenloDcePortStatsRxPauseCFCDeltaAvg OBJECT-TYPE
    SYNTAX       Unsigned64
    MAX-ACCESS   read-only
    STATUS       current
    DESCRIPTION
        "Cisco Firepower adaptor:MenloDcePortStats:rxPauseCFCDeltaAvg
        managed object property"
    ::= { cfprApAdaptorMenloDcePortStatsEntry 8 }

cfprApAdaptorMenloDcePortStatsRxPauseCFCDeltaMax OBJECT-TYPE
    SYNTAX       Unsigned64
    MAX-ACCESS   read-only
    STATUS       current
    DESCRIPTION
        "Cisco Firepower adaptor:MenloDcePortStats:rxPauseCFCDeltaMax
        managed object property"
    ::= { cfprApAdaptorMenloDcePortStatsEntry 9 }

cfprApAdaptorMenloDcePortStatsRxPauseCFCDeltaMin OBJECT-TYPE
    SYNTAX       Unsigned64
    MAX-ACCESS   read-only
    STATUS       current
    DESCRIPTION
        "Cisco Firepower adaptor:MenloDcePortStats:rxPauseCFCDeltaMin
        managed object property"
    ::= { cfprApAdaptorMenloDcePortStatsEntry 10 }

cfprApAdaptorMenloDcePortStatsRxPausePFC OBJECT-TYPE
    SYNTAX       Unsigned64
    MAX-ACCESS   read-only
    STATUS       current
    DESCRIPTION
        "Cisco Firepower adaptor:MenloDcePortStats:rxPausePFC
        managed object property"
    ::= { cfprApAdaptorMenloDcePortStatsEntry 11 }

cfprApAdaptorMenloDcePortStatsRxPausePFCDelta OBJECT-TYPE
    SYNTAX       Counter64
    MAX-ACCESS   read-only
    STATUS       current
    DESCRIPTION
        "Cisco Firepower adaptor:MenloDcePortStats:rxPausePFCDelta
        managed object property"
    ::= { cfprApAdaptorMenloDcePortStatsEntry 12 }

cfprApAdaptorMenloDcePortStatsRxPausePFCDeltaAvg OBJECT-TYPE
    SYNTAX       Unsigned64
    MAX-ACCESS   read-only
    STATUS       current
    DESCRIPTION
        "Cisco Firepower adaptor:MenloDcePortStats:rxPausePFCDeltaAvg
        managed object property"
    ::= { cfprApAdaptorMenloDcePortStatsEntry 13 }

cfprApAdaptorMenloDcePortStatsRxPausePFCDeltaMax OBJECT-TYPE
    SYNTAX       Unsigned64
    MAX-ACCESS   read-only
    STATUS       current
    DESCRIPTION
        "Cisco Firepower adaptor:MenloDcePortStats:rxPausePFCDeltaMax
        managed object property"
    ::= { cfprApAdaptorMenloDcePortStatsEntry 14 }

cfprApAdaptorMenloDcePortStatsRxPausePFCDeltaMin OBJECT-TYPE
    SYNTAX       Unsigned64
    MAX-ACCESS   read-only
    STATUS       current
    DESCRIPTION
        "Cisco Firepower adaptor:MenloDcePortStats:rxPausePFCDeltaMin
        managed object property"
    ::= { cfprApAdaptorMenloDcePortStatsEntry 15 }

cfprApAdaptorMenloDcePortStatsSuspect OBJECT-TYPE
    SYNTAX       TruthValue
    MAX-ACCESS   read-only
    STATUS       current
    DESCRIPTION
        "Cisco Firepower adaptor:MenloDcePortStats:suspect
        managed object property"
    ::= { cfprApAdaptorMenloDcePortStatsEntry 16 }

cfprApAdaptorMenloDcePortStatsThresholded OBJECT-TYPE
    SYNTAX       CfprApAdaptorMenloDcePortStatsThresholded
    MAX-ACCESS   read-only
    STATUS       current
    DESCRIPTION
        "Cisco Firepower adaptor:MenloDcePortStats:thresholded
        managed object property"
    ::= { cfprApAdaptorMenloDcePortStatsEntry 17 }

cfprApAdaptorMenloDcePortStatsTimeCollected OBJECT-TYPE
    SYNTAX       DateAndTime
    MAX-ACCESS   read-only
    STATUS       current
    DESCRIPTION
        "Cisco Firepower adaptor:MenloDcePortStats:timeCollected
        managed object property"
    ::= { cfprApAdaptorMenloDcePortStatsEntry 18 }

cfprApAdaptorMenloDcePortStatsTxPauseCFC OBJECT-TYPE
    SYNTAX       Unsigned64
    MAX-ACCESS   read-only
    STATUS       current
    DESCRIPTION
        "Cisco Firepower adaptor:MenloDcePortStats:txPauseCFC
        managed object property"
    ::= { cfprApAdaptorMenloDcePortStatsEntry 19 }

cfprApAdaptorMenloDcePortStatsTxPauseCFCDelta OBJECT-TYPE
    SYNTAX       Counter64
    MAX-ACCESS   read-only
    STATUS       current
    DESCRIPTION
        "Cisco Firepower adaptor:MenloDcePortStats:txPauseCFCDelta
        managed object property"
    ::= { cfprApAdaptorMenloDcePortStatsEntry 20 }

cfprApAdaptorMenloDcePortStatsTxPauseCFCDeltaAvg OBJECT-TYPE
    SYNTAX       Unsigned64
    MAX-ACCESS   read-only
    STATUS       current
    DESCRIPTION
        "Cisco Firepower adaptor:MenloDcePortStats:txPauseCFCDeltaAvg
        managed object property"
    ::= { cfprApAdaptorMenloDcePortStatsEntry 21 }

cfprApAdaptorMenloDcePortStatsTxPauseCFCDeltaMax OBJECT-TYPE
    SYNTAX       Unsigned64
    MAX-ACCESS   read-only
    STATUS       current
    DESCRIPTION
        "Cisco Firepower adaptor:MenloDcePortStats:txPauseCFCDeltaMax
        managed object property"
    ::= { cfprApAdaptorMenloDcePortStatsEntry 22 }

cfprApAdaptorMenloDcePortStatsTxPauseCFCDeltaMin OBJECT-TYPE
    SYNTAX       Unsigned64
    MAX-ACCESS   read-only
    STATUS       current
    DESCRIPTION
        "Cisco Firepower adaptor:MenloDcePortStats:txPauseCFCDeltaMin
        managed object property"
    ::= { cfprApAdaptorMenloDcePortStatsEntry 23 }

cfprApAdaptorMenloDcePortStatsTxPausePFC OBJECT-TYPE
    SYNTAX       Unsigned64
    MAX-ACCESS   read-only
    STATUS       current
    DESCRIPTION
        "Cisco Firepower adaptor:MenloDcePortStats:txPausePFC
        managed object property"
    ::= { cfprApAdaptorMenloDcePortStatsEntry 24 }

cfprApAdaptorMenloDcePortStatsTxPausePFCDelta OBJECT-TYPE
    SYNTAX       Counter64
    MAX-ACCESS   read-only
    STATUS       current
    DESCRIPTION
        "Cisco Firepower adaptor:MenloDcePortStats:txPausePFCDelta
        managed object property"
    ::= { cfprApAdaptorMenloDcePortStatsEntry 25 }

cfprApAdaptorMenloDcePortStatsTxPausePFCDeltaAvg OBJECT-TYPE
    SYNTAX       Unsigned64
    MAX-ACCESS   read-only
    STATUS       current
    DESCRIPTION
        "Cisco Firepower adaptor:MenloDcePortStats:txPausePFCDeltaAvg
        managed object property"
    ::= { cfprApAdaptorMenloDcePortStatsEntry 26 }

cfprApAdaptorMenloDcePortStatsTxPausePFCDeltaMax OBJECT-TYPE
    SYNTAX       Unsigned64
    MAX-ACCESS   read-only
    STATUS       current
    DESCRIPTION
        "Cisco Firepower adaptor:MenloDcePortStats:txPausePFCDeltaMax
        managed object property"
    ::= { cfprApAdaptorMenloDcePortStatsEntry 27 }

cfprApAdaptorMenloDcePortStatsTxPausePFCDeltaMin OBJECT-TYPE
    SYNTAX       Unsigned64
    MAX-ACCESS   read-only
    STATUS       current
    DESCRIPTION
        "Cisco Firepower adaptor:MenloDcePortStats:txPausePFCDeltaMin
        managed object property"
    ::= { cfprApAdaptorMenloDcePortStatsEntry 28 }

cfprApAdaptorMenloDcePortStatsUpdate OBJECT-TYPE
    SYNTAX       Gauge32
    MAX-ACCESS   read-only
    STATUS       current
    DESCRIPTION
        "Cisco Firepower adaptor:MenloDcePortStats:update
        managed object property"
    ::= { cfprApAdaptorMenloDcePortStatsEntry 29 }

cfprApAdaptorMenloDcePortStatsHistTable OBJECT-TYPE
    SYNTAX           SEQUENCE OF CfprApAdaptorMenloDcePortStatsHistEntry
    MAX-ACCESS       not-accessible
    STATUS           current
    DESCRIPTION
        "Cisco Firepower adaptor:MenloDcePortStatsHist
        managed object table"
    ::= { cfprApAdaptorObjects 85 }

cfprApAdaptorMenloDcePortStatsHistEntry OBJECT-TYPE
    SYNTAX           CfprApAdaptorMenloDcePortStatsHistEntry
    MAX-ACCESS       not-accessible
    STATUS           current
    DESCRIPTION
        "Entry for the cfprApAdaptorMenloDcePortStatsHistTable table."
    INDEX { cfprApAdaptorMenloDcePortStatsHistInstanceId }
    ::= { cfprApAdaptorMenloDcePortStatsHistTable 1 }

CfprApAdaptorMenloDcePortStatsHistEntry ::= SEQUENCE {
    cfprApAdaptorMenloDcePortStatsHistInstanceId                     CfprApManagedObjectId,
    cfprApAdaptorMenloDcePortStatsHistDn                             CfprApManagedObjectDn,
    cfprApAdaptorMenloDcePortStatsHistRn                             SnmpAdminString,
    cfprApAdaptorMenloDcePortStatsHistId                             Unsigned64,
    cfprApAdaptorMenloDcePortStatsHistMostRecent                     TruthValue,
    cfprApAdaptorMenloDcePortStatsHistRxPauseCFC                     Unsigned64,
    cfprApAdaptorMenloDcePortStatsHistRxPauseCFCDelta                Unsigned64,
    cfprApAdaptorMenloDcePortStatsHistRxPauseCFCDeltaAvg             Unsigned64,
    cfprApAdaptorMenloDcePortStatsHistRxPauseCFCDeltaMax             Unsigned64,
    cfprApAdaptorMenloDcePortStatsHistRxPauseCFCDeltaMin             Unsigned64,
    cfprApAdaptorMenloDcePortStatsHistRxPausePFC                     Unsigned64,
    cfprApAdaptorMenloDcePortStatsHistRxPausePFCDelta                Unsigned64,
    cfprApAdaptorMenloDcePortStatsHistRxPausePFCDeltaAvg             Unsigned64,
    cfprApAdaptorMenloDcePortStatsHistRxPausePFCDeltaMax             Unsigned64,
    cfprApAdaptorMenloDcePortStatsHistRxPausePFCDeltaMin             Unsigned64,
    cfprApAdaptorMenloDcePortStatsHistSuspect                        TruthValue,
    cfprApAdaptorMenloDcePortStatsHistThresholded                    CfprApAdaptorMenloDcePortStatsHistThresholded,
    cfprApAdaptorMenloDcePortStatsHistTimeCollected                  DateAndTime,
    cfprApAdaptorMenloDcePortStatsHistTxPauseCFC                     Unsigned64,
    cfprApAdaptorMenloDcePortStatsHistTxPauseCFCDelta                Unsigned64,
    cfprApAdaptorMenloDcePortStatsHistTxPauseCFCDeltaAvg             Unsigned64,
    cfprApAdaptorMenloDcePortStatsHistTxPauseCFCDeltaMax             Unsigned64,
    cfprApAdaptorMenloDcePortStatsHistTxPauseCFCDeltaMin             Unsigned64,
    cfprApAdaptorMenloDcePortStatsHistTxPausePFC                     Unsigned64,
    cfprApAdaptorMenloDcePortStatsHistTxPausePFCDelta                Unsigned64,
    cfprApAdaptorMenloDcePortStatsHistTxPausePFCDeltaAvg             Unsigned64,
    cfprApAdaptorMenloDcePortStatsHistTxPausePFCDeltaMax             Unsigned64,
    cfprApAdaptorMenloDcePortStatsHistTxPausePFCDeltaMin             Unsigned64
}

cfprApAdaptorMenloDcePortStatsHistInstanceId OBJECT-TYPE
    SYNTAX       CfprApManagedObjectId
    MAX-ACCESS   not-accessible
    STATUS       current
    DESCRIPTION
        "Instance identifier of the managed object."
    ::= { cfprApAdaptorMenloDcePortStatsHistEntry 1 }

cfprApAdaptorMenloDcePortStatsHistDn OBJECT-TYPE
    SYNTAX       CfprApManagedObjectDn
    MAX-ACCESS   read-only
    STATUS       current
    DESCRIPTION
        "Cisco Firepower adaptor:MenloDcePortStatsHist:dn
        managed object property"
    ::= { cfprApAdaptorMenloDcePortStatsHistEntry 2 }

cfprApAdaptorMenloDcePortStatsHistRn OBJECT-TYPE
    SYNTAX       SnmpAdminString
    MAX-ACCESS   read-only
    STATUS       current
    DESCRIPTION
        "Cisco Firepower adaptor:MenloDcePortStatsHist:rn
        managed object property"
    ::= { cfprApAdaptorMenloDcePortStatsHistEntry 3 }

cfprApAdaptorMenloDcePortStatsHistId OBJECT-TYPE
    SYNTAX       Unsigned64
    MAX-ACCESS   read-only
    STATUS       current
    DESCRIPTION
        "Cisco Firepower adaptor:MenloDcePortStatsHist:id
        managed object property"
    ::= { cfprApAdaptorMenloDcePortStatsHistEntry 4 }

cfprApAdaptorMenloDcePortStatsHistMostRecent OBJECT-TYPE
    SYNTAX       TruthValue
    MAX-ACCESS   read-only
    STATUS       current
    DESCRIPTION
        "Cisco Firepower adaptor:MenloDcePortStatsHist:mostRecent
        managed object property"
    ::= { cfprApAdaptorMenloDcePortStatsHistEntry 5 }

cfprApAdaptorMenloDcePortStatsHistRxPauseCFC OBJECT-TYPE
    SYNTAX       Unsigned64
    MAX-ACCESS   read-only
    STATUS       current
    DESCRIPTION
        "Cisco Firepower adaptor:MenloDcePortStatsHist:rxPauseCFC
        managed object property"
    ::= { cfprApAdaptorMenloDcePortStatsHistEntry 6 }

cfprApAdaptorMenloDcePortStatsHistRxPauseCFCDelta OBJECT-TYPE
    SYNTAX       Unsigned64
    MAX-ACCESS   read-only
    STATUS       current
    DESCRIPTION
        "Cisco Firepower adaptor:MenloDcePortStatsHist:rxPauseCFCDelta
        managed object property"
    ::= { cfprApAdaptorMenloDcePortStatsHistEntry 7 }

cfprApAdaptorMenloDcePortStatsHistRxPauseCFCDeltaAvg OBJECT-TYPE
    SYNTAX       Unsigned64
    MAX-ACCESS   read-only
    STATUS       current
    DESCRIPTION
        "Cisco Firepower adaptor:MenloDcePortStatsHist:rxPauseCFCDeltaAvg
        managed object property"
    ::= { cfprApAdaptorMenloDcePortStatsHistEntry 8 }

cfprApAdaptorMenloDcePortStatsHistRxPauseCFCDeltaMax OBJECT-TYPE
    SYNTAX       Unsigned64
    MAX-ACCESS   read-only
    STATUS       current
    DESCRIPTION
        "Cisco Firepower adaptor:MenloDcePortStatsHist:rxPauseCFCDeltaMax
        managed object property"
    ::= { cfprApAdaptorMenloDcePortStatsHistEntry 9 }

cfprApAdaptorMenloDcePortStatsHistRxPauseCFCDeltaMin OBJECT-TYPE
    SYNTAX       Unsigned64
    MAX-ACCESS   read-only
    STATUS       current
    DESCRIPTION
        "Cisco Firepower adaptor:MenloDcePortStatsHist:rxPauseCFCDeltaMin
        managed object property"
    ::= { cfprApAdaptorMenloDcePortStatsHistEntry 10 }

cfprApAdaptorMenloDcePortStatsHistRxPausePFC OBJECT-TYPE
    SYNTAX       Unsigned64
    MAX-ACCESS   read-only
    STATUS       current
    DESCRIPTION
        "Cisco Firepower adaptor:MenloDcePortStatsHist:rxPausePFC
        managed object property"
    ::= { cfprApAdaptorMenloDcePortStatsHistEntry 11 }

cfprApAdaptorMenloDcePortStatsHistRxPausePFCDelta OBJECT-TYPE
    SYNTAX       Unsigned64
    MAX-ACCESS   read-only
    STATUS       current
    DESCRIPTION
        "Cisco Firepower adaptor:MenloDcePortStatsHist:rxPausePFCDelta
        managed object property"
    ::= { cfprApAdaptorMenloDcePortStatsHistEntry 12 }

cfprApAdaptorMenloDcePortStatsHistRxPausePFCDeltaAvg OBJECT-TYPE
    SYNTAX       Unsigned64
    MAX-ACCESS   read-only
    STATUS       current
    DESCRIPTION
        "Cisco Firepower adaptor:MenloDcePortStatsHist:rxPausePFCDeltaAvg
        managed object property"
    ::= { cfprApAdaptorMenloDcePortStatsHistEntry 13 }

cfprApAdaptorMenloDcePortStatsHistRxPausePFCDeltaMax OBJECT-TYPE
    SYNTAX       Unsigned64
    MAX-ACCESS   read-only
    STATUS       current
    DESCRIPTION
        "Cisco Firepower adaptor:MenloDcePortStatsHist:rxPausePFCDeltaMax
        managed object property"
    ::= { cfprApAdaptorMenloDcePortStatsHistEntry 14 }

cfprApAdaptorMenloDcePortStatsHistRxPausePFCDeltaMin OBJECT-TYPE
    SYNTAX       Unsigned64
    MAX-ACCESS   read-only
    STATUS       current
    DESCRIPTION
        "Cisco Firepower adaptor:MenloDcePortStatsHist:rxPausePFCDeltaMin
        managed object property"
    ::= { cfprApAdaptorMenloDcePortStatsHistEntry 15 }

cfprApAdaptorMenloDcePortStatsHistSuspect OBJECT-TYPE
    SYNTAX       TruthValue
    MAX-ACCESS   read-only
    STATUS       current
    DESCRIPTION
        "Cisco Firepower adaptor:MenloDcePortStatsHist:suspect
        managed object property"
    ::= { cfprApAdaptorMenloDcePortStatsHistEntry 16 }

cfprApAdaptorMenloDcePortStatsHistThresholded OBJECT-TYPE
    SYNTAX       CfprApAdaptorMenloDcePortStatsHistThresholded
    MAX-ACCESS   read-only
    STATUS       current
    DESCRIPTION
        "Cisco Firepower adaptor:MenloDcePortStatsHist:thresholded
        managed object property"
    ::= { cfprApAdaptorMenloDcePortStatsHistEntry 17 }

cfprApAdaptorMenloDcePortStatsHistTimeCollected OBJECT-TYPE
    SYNTAX       DateAndTime
    MAX-ACCESS   read-only
    STATUS       current
    DESCRIPTION
        "Cisco Firepower adaptor:MenloDcePortStatsHist:timeCollected
        managed object property"
    ::= { cfprApAdaptorMenloDcePortStatsHistEntry 18 }

cfprApAdaptorMenloDcePortStatsHistTxPauseCFC OBJECT-TYPE
    SYNTAX       Unsigned64
    MAX-ACCESS   read-only
    STATUS       current
    DESCRIPTION
        "Cisco Firepower adaptor:MenloDcePortStatsHist:txPauseCFC
        managed object property"
    ::= { cfprApAdaptorMenloDcePortStatsHistEntry 19 }

cfprApAdaptorMenloDcePortStatsHistTxPauseCFCDelta OBJECT-TYPE
    SYNTAX       Unsigned64
    MAX-ACCESS   read-only
    STATUS       current
    DESCRIPTION
        "Cisco Firepower adaptor:MenloDcePortStatsHist:txPauseCFCDelta
        managed object property"
    ::= { cfprApAdaptorMenloDcePortStatsHistEntry 20 }

cfprApAdaptorMenloDcePortStatsHistTxPauseCFCDeltaAvg OBJECT-TYPE
    SYNTAX       Unsigned64
    MAX-ACCESS   read-only
    STATUS       current
    DESCRIPTION
        "Cisco Firepower adaptor:MenloDcePortStatsHist:txPauseCFCDeltaAvg
        managed object property"
    ::= { cfprApAdaptorMenloDcePortStatsHistEntry 21 }

cfprApAdaptorMenloDcePortStatsHistTxPauseCFCDeltaMax OBJECT-TYPE
    SYNTAX       Unsigned64
    MAX-ACCESS   read-only
    STATUS       current
    DESCRIPTION
        "Cisco Firepower adaptor:MenloDcePortStatsHist:txPauseCFCDeltaMax
        managed object property"
    ::= { cfprApAdaptorMenloDcePortStatsHistEntry 22 }

cfprApAdaptorMenloDcePortStatsHistTxPauseCFCDeltaMin OBJECT-TYPE
    SYNTAX       Unsigned64
    MAX-ACCESS   read-only
    STATUS       current
    DESCRIPTION
        "Cisco Firepower adaptor:MenloDcePortStatsHist:txPauseCFCDeltaMin
        managed object property"
    ::= { cfprApAdaptorMenloDcePortStatsHistEntry 23 }

cfprApAdaptorMenloDcePortStatsHistTxPausePFC OBJECT-TYPE
    SYNTAX       Unsigned64
    MAX-ACCESS   read-only
    STATUS       current
    DESCRIPTION
        "Cisco Firepower adaptor:MenloDcePortStatsHist:txPausePFC
        managed object property"
    ::= { cfprApAdaptorMenloDcePortStatsHistEntry 24 }

cfprApAdaptorMenloDcePortStatsHistTxPausePFCDelta OBJECT-TYPE
    SYNTAX       Unsigned64
    MAX-ACCESS   read-only
    STATUS       current
    DESCRIPTION
        "Cisco Firepower adaptor:MenloDcePortStatsHist:txPausePFCDelta
        managed object property"
    ::= { cfprApAdaptorMenloDcePortStatsHistEntry 25 }

cfprApAdaptorMenloDcePortStatsHistTxPausePFCDeltaAvg OBJECT-TYPE
    SYNTAX       Unsigned64
    MAX-ACCESS   read-only
    STATUS       current
    DESCRIPTION
        "Cisco Firepower adaptor:MenloDcePortStatsHist:txPausePFCDeltaAvg
        managed object property"
    ::= { cfprApAdaptorMenloDcePortStatsHistEntry 26 }

cfprApAdaptorMenloDcePortStatsHistTxPausePFCDeltaMax OBJECT-TYPE
    SYNTAX       Unsigned64
    MAX-ACCESS   read-only
    STATUS       current
    DESCRIPTION
        "Cisco Firepower adaptor:MenloDcePortStatsHist:txPausePFCDeltaMax
        managed object property"
    ::= { cfprApAdaptorMenloDcePortStatsHistEntry 27 }

cfprApAdaptorMenloDcePortStatsHistTxPausePFCDeltaMin OBJECT-TYPE
    SYNTAX       Unsigned64
    MAX-ACCESS   read-only
    STATUS       current
    DESCRIPTION
        "Cisco Firepower adaptor:MenloDcePortStatsHist:txPausePFCDeltaMin
        managed object property"
    ::= { cfprApAdaptorMenloDcePortStatsHistEntry 28 }

cfprApAdaptorMenloEthErrorStatsTable OBJECT-TYPE
    SYNTAX           SEQUENCE OF CfprApAdaptorMenloEthErrorStatsEntry
    MAX-ACCESS       not-accessible
    STATUS           current
    DESCRIPTION
        "Cisco Firepower adaptor:MenloEthErrorStats managed object table"
    ::= { cfprApAdaptorObjects 86 }

cfprApAdaptorMenloEthErrorStatsEntry OBJECT-TYPE
    SYNTAX           CfprApAdaptorMenloEthErrorStatsEntry
    MAX-ACCESS       not-accessible
    STATUS           current
    DESCRIPTION
        "Entry for the cfprApAdaptorMenloEthErrorStatsTable table."
    INDEX { cfprApAdaptorMenloEthErrorStatsInstanceId }
    ::= { cfprApAdaptorMenloEthErrorStatsTable 1 }

CfprApAdaptorMenloEthErrorStatsEntry ::= SEQUENCE {
    cfprApAdaptorMenloEthErrorStatsInstanceId                        CfprApManagedObjectId,
    cfprApAdaptorMenloEthErrorStatsDn                                CfprApManagedObjectDn,
    cfprApAdaptorMenloEthErrorStatsRn                                SnmpAdminString,
    cfprApAdaptorMenloEthErrorStatsCorrectableErrors                 Unsigned64,
    cfprApAdaptorMenloEthErrorStatsCorrectableErrorsDelta            Counter64,
    cfprApAdaptorMenloEthErrorStatsCorrectableErrorsDeltaAvg         Unsigned64,
    cfprApAdaptorMenloEthErrorStatsCorrectableErrorsDeltaMax         Unsigned64,
    cfprApAdaptorMenloEthErrorStatsCorrectableErrorsDeltaMin         Unsigned64,
    cfprApAdaptorMenloEthErrorStatsDropAcl                           Unsigned64,
    cfprApAdaptorMenloEthErrorStatsDropAclDelta                      Counter64,
    cfprApAdaptorMenloEthErrorStatsDropAclDeltaAvg                   Unsigned64,
    cfprApAdaptorMenloEthErrorStatsDropAclDeltaMax                   Unsigned64,
    cfprApAdaptorMenloEthErrorStatsDropAclDeltaMin                   Unsigned64,
    cfprApAdaptorMenloEthErrorStatsIntervals                         Gauge32,
    cfprApAdaptorMenloEthErrorStatsMenloEthIndex                     CfprApAdaptorMenloStatsIndex,
    cfprApAdaptorMenloEthErrorStatsPopErrors                         Unsigned64,
    cfprApAdaptorMenloEthErrorStatsPopErrorsDelta                    Counter64,
    cfprApAdaptorMenloEthErrorStatsPopErrorsDeltaAvg                 Unsigned64,
    cfprApAdaptorMenloEthErrorStatsPopErrorsDeltaMax                 Unsigned64,
    cfprApAdaptorMenloEthErrorStatsPopErrorsDeltaMin                 Unsigned64,
    cfprApAdaptorMenloEthErrorStatsPushErrors                        Unsigned64,
    cfprApAdaptorMenloEthErrorStatsPushErrorsDelta                   Counter64,
    cfprApAdaptorMenloEthErrorStatsPushErrorsDeltaAvg                Unsigned64,
    cfprApAdaptorMenloEthErrorStatsPushErrorsDeltaMax                Unsigned64,
    cfprApAdaptorMenloEthErrorStatsPushErrorsDeltaMin                Unsigned64,
    cfprApAdaptorMenloEthErrorStatsSuspect                           TruthValue,
    cfprApAdaptorMenloEthErrorStatsThresholded                       CfprApAdaptorMenloEthErrorStatsThresholded,
    cfprApAdaptorMenloEthErrorStatsTimeCollected                     DateAndTime,
    cfprApAdaptorMenloEthErrorStatsUncorrectableErrors               Unsigned64,
    cfprApAdaptorMenloEthErrorStatsUncorrectableErrorsDelta          Counter64,
    cfprApAdaptorMenloEthErrorStatsUncorrectableErrorsDeltaAvg       Unsigned64,
    cfprApAdaptorMenloEthErrorStatsUncorrectableErrorsDeltaMax       Unsigned64,
    cfprApAdaptorMenloEthErrorStatsUncorrectableErrorsDeltaMin       Unsigned64,
    cfprApAdaptorMenloEthErrorStatsUpdate                            Gauge32
}

cfprApAdaptorMenloEthErrorStatsInstanceId OBJECT-TYPE
    SYNTAX       CfprApManagedObjectId
    MAX-ACCESS   not-accessible
    STATUS       current
    DESCRIPTION
        "Instance identifier of the managed object."
    ::= { cfprApAdaptorMenloEthErrorStatsEntry 1 }

cfprApAdaptorMenloEthErrorStatsDn OBJECT-TYPE
    SYNTAX       CfprApManagedObjectDn
    MAX-ACCESS   read-only
    STATUS       current
    DESCRIPTION
        "Cisco Firepower adaptor:MenloEthErrorStats:dn
        managed object property"
    ::= { cfprApAdaptorMenloEthErrorStatsEntry 2 }

cfprApAdaptorMenloEthErrorStatsRn OBJECT-TYPE
    SYNTAX       SnmpAdminString
    MAX-ACCESS   read-only
    STATUS       current
    DESCRIPTION
        "Cisco Firepower adaptor:MenloEthErrorStats:rn
        managed object property"
    ::= { cfprApAdaptorMenloEthErrorStatsEntry 3 }

cfprApAdaptorMenloEthErrorStatsCorrectableErrors OBJECT-TYPE
    SYNTAX       Unsigned64
    MAX-ACCESS   read-only
    STATUS       current
    DESCRIPTION
        "Cisco Firepower adaptor:MenloEthErrorStats:correctableErrors
        managed object property"
    ::= { cfprApAdaptorMenloEthErrorStatsEntry 4 }

cfprApAdaptorMenloEthErrorStatsCorrectableErrorsDelta OBJECT-TYPE
    SYNTAX       Counter64
    MAX-ACCESS   read-only
    STATUS       current
    DESCRIPTION
        "Cisco Firepower adaptor:MenloEthErrorStats:correctableErrorsDelta
         managed object property"
    ::= { cfprApAdaptorMenloEthErrorStatsEntry 5 }

cfprApAdaptorMenloEthErrorStatsCorrectableErrorsDeltaAvg OBJECT-TYPE
    SYNTAX       Unsigned64
    MAX-ACCESS   read-only
    STATUS       current
    DESCRIPTION
        "Cisco Firepower adaptor:MenloEthErrorStats:correctableErrorsDelta
        Avg managed object property"
    ::= { cfprApAdaptorMenloEthErrorStatsEntry 6 }

cfprApAdaptorMenloEthErrorStatsCorrectableErrorsDeltaMax OBJECT-TYPE
    SYNTAX       Unsigned64
    MAX-ACCESS   read-only
    STATUS       current
    DESCRIPTION
        "Cisco Firepower adaptor:MenloEthErrorStats:correctableErrorsDelta
        Max managed object property"
    ::= { cfprApAdaptorMenloEthErrorStatsEntry 7 }

cfprApAdaptorMenloEthErrorStatsCorrectableErrorsDeltaMin OBJECT-TYPE
    SYNTAX       Unsigned64
    MAX-ACCESS   read-only
    STATUS       current
    DESCRIPTION
        "Cisco Firepower adaptor:MenloEthErrorStats:correctableErrorsDelta
        Min managed object property"
    ::= { cfprApAdaptorMenloEthErrorStatsEntry 8 }

cfprApAdaptorMenloEthErrorStatsDropAcl OBJECT-TYPE
    SYNTAX       Unsigned64
    MAX-ACCESS   read-only
    STATUS       current
    DESCRIPTION
        "Cisco Firepower adaptor:MenloEthErrorStats:dropAcl
        managed object property"
    ::= { cfprApAdaptorMenloEthErrorStatsEntry 9 }

cfprApAdaptorMenloEthErrorStatsDropAclDelta OBJECT-TYPE
    SYNTAX       Counter64
    MAX-ACCESS   read-only
    STATUS       current
    DESCRIPTION
        "Cisco Firepower adaptor:MenloEthErrorStats:dropAclDelta
        managed object property"
    ::= { cfprApAdaptorMenloEthErrorStatsEntry 10 }

cfprApAdaptorMenloEthErrorStatsDropAclDeltaAvg OBJECT-TYPE
    SYNTAX       Unsigned64
    MAX-ACCESS   read-only
    STATUS       current
    DESCRIPTION
        "Cisco Firepower adaptor:MenloEthErrorStats:dropAclDeltaAvg
        managed object property"
    ::= { cfprApAdaptorMenloEthErrorStatsEntry 11 }

cfprApAdaptorMenloEthErrorStatsDropAclDeltaMax OBJECT-TYPE
    SYNTAX       Unsigned64
    MAX-ACCESS   read-only
    STATUS       current
    DESCRIPTION
        "Cisco Firepower adaptor:MenloEthErrorStats:dropAclDeltaMax
        managed object property"
    ::= { cfprApAdaptorMenloEthErrorStatsEntry 12 }

cfprApAdaptorMenloEthErrorStatsDropAclDeltaMin OBJECT-TYPE
    SYNTAX       Unsigned64
    MAX-ACCESS   read-only
    STATUS       current
    DESCRIPTION
        "Cisco Firepower adaptor:MenloEthErrorStats:dropAclDeltaMin
        managed object property"
    ::= { cfprApAdaptorMenloEthErrorStatsEntry 13 }

cfprApAdaptorMenloEthErrorStatsIntervals OBJECT-TYPE
    SYNTAX       Gauge32
    MAX-ACCESS   read-only
    STATUS       current
    DESCRIPTION
        "Cisco Firepower adaptor:MenloEthErrorStats:intervals
        managed object property"
    ::= { cfprApAdaptorMenloEthErrorStatsEntry 14 }

cfprApAdaptorMenloEthErrorStatsMenloEthIndex OBJECT-TYPE
    SYNTAX       CfprApAdaptorMenloStatsIndex
    MAX-ACCESS   read-only
    STATUS       current
    DESCRIPTION
        "Cisco Firepower adaptor:MenloEthErrorStats:menloEthIndex
        managed object property"
    ::= { cfprApAdaptorMenloEthErrorStatsEntry 15 }

cfprApAdaptorMenloEthErrorStatsPopErrors OBJECT-TYPE
    SYNTAX       Unsigned64
    MAX-ACCESS   read-only
    STATUS       current
    DESCRIPTION
        "Cisco Firepower adaptor:MenloEthErrorStats:popErrors
        managed object property"
    ::= { cfprApAdaptorMenloEthErrorStatsEntry 16 }

cfprApAdaptorMenloEthErrorStatsPopErrorsDelta OBJECT-TYPE
    SYNTAX       Counter64
    MAX-ACCESS   read-only
    STATUS       current
    DESCRIPTION
        "Cisco Firepower adaptor:MenloEthErrorStats:popErrorsDelta
        managed object property"
    ::= { cfprApAdaptorMenloEthErrorStatsEntry 17 }

cfprApAdaptorMenloEthErrorStatsPopErrorsDeltaAvg OBJECT-TYPE
    SYNTAX       Unsigned64
    MAX-ACCESS   read-only
    STATUS       current
    DESCRIPTION
        "Cisco Firepower adaptor:MenloEthErrorStats:popErrorsDeltaAvg
        managed object property"
    ::= { cfprApAdaptorMenloEthErrorStatsEntry 18 }

cfprApAdaptorMenloEthErrorStatsPopErrorsDeltaMax OBJECT-TYPE
    SYNTAX       Unsigned64
    MAX-ACCESS   read-only
    STATUS       current
    DESCRIPTION
        "Cisco Firepower adaptor:MenloEthErrorStats:popErrorsDeltaMax
        managed object property"
    ::= { cfprApAdaptorMenloEthErrorStatsEntry 19 }

cfprApAdaptorMenloEthErrorStatsPopErrorsDeltaMin OBJECT-TYPE
    SYNTAX       Unsigned64
    MAX-ACCESS   read-only
    STATUS       current
    DESCRIPTION
        "Cisco Firepower adaptor:MenloEthErrorStats:popErrorsDeltaMin
        managed object property"
    ::= { cfprApAdaptorMenloEthErrorStatsEntry 20 }

cfprApAdaptorMenloEthErrorStatsPushErrors OBJECT-TYPE
    SYNTAX       Unsigned64
    MAX-ACCESS   read-only
    STATUS       current
    DESCRIPTION
        "Cisco Firepower adaptor:MenloEthErrorStats:pushErrors
        managed object property"
    ::= { cfprApAdaptorMenloEthErrorStatsEntry 21 }

cfprApAdaptorMenloEthErrorStatsPushErrorsDelta OBJECT-TYPE
    SYNTAX       Counter64
    MAX-ACCESS   read-only
    STATUS       current
    DESCRIPTION
        "Cisco Firepower adaptor:MenloEthErrorStats:pushErrorsDelta
        managed object property"
    ::= { cfprApAdaptorMenloEthErrorStatsEntry 22 }

cfprApAdaptorMenloEthErrorStatsPushErrorsDeltaAvg OBJECT-TYPE
    SYNTAX       Unsigned64
    MAX-ACCESS   read-only
    STATUS       current
    DESCRIPTION
        "Cisco Firepower adaptor:MenloEthErrorStats:pushErrorsDeltaAvg
        managed object property"
    ::= { cfprApAdaptorMenloEthErrorStatsEntry 23 }

cfprApAdaptorMenloEthErrorStatsPushErrorsDeltaMax OBJECT-TYPE
    SYNTAX       Unsigned64
    MAX-ACCESS   read-only
    STATUS       current
    DESCRIPTION
        "Cisco Firepower adaptor:MenloEthErrorStats:pushErrorsDeltaMax
        managed object property"
    ::= { cfprApAdaptorMenloEthErrorStatsEntry 24 }

cfprApAdaptorMenloEthErrorStatsPushErrorsDeltaMin OBJECT-TYPE
    SYNTAX       Unsigned64
    MAX-ACCESS   read-only
    STATUS       current
    DESCRIPTION
        "Cisco Firepower adaptor:MenloEthErrorStats:pushErrorsDeltaMin
        managed object property"
    ::= { cfprApAdaptorMenloEthErrorStatsEntry 25 }

cfprApAdaptorMenloEthErrorStatsSuspect OBJECT-TYPE
    SYNTAX       TruthValue
    MAX-ACCESS   read-only
    STATUS       current
    DESCRIPTION
        "Cisco Firepower adaptor:MenloEthErrorStats:suspect
        managed object property"
    ::= { cfprApAdaptorMenloEthErrorStatsEntry 26 }

cfprApAdaptorMenloEthErrorStatsThresholded OBJECT-TYPE
    SYNTAX       CfprApAdaptorMenloEthErrorStatsThresholded
    MAX-ACCESS   read-only
    STATUS       current
    DESCRIPTION
        "Cisco Firepower adaptor:MenloEthErrorStats:thresholded
        managed object property"
    ::= { cfprApAdaptorMenloEthErrorStatsEntry 27 }

cfprApAdaptorMenloEthErrorStatsTimeCollected OBJECT-TYPE
    SYNTAX       DateAndTime
    MAX-ACCESS   read-only
    STATUS       current
    DESCRIPTION
        "Cisco Firepower adaptor:MenloEthErrorStats:timeCollected
        managed object property"
    ::= { cfprApAdaptorMenloEthErrorStatsEntry 28 }

cfprApAdaptorMenloEthErrorStatsUncorrectableErrors OBJECT-TYPE
    SYNTAX       Unsigned64
    MAX-ACCESS   read-only
    STATUS       current
    DESCRIPTION
        "Cisco Firepower adaptor:MenloEthErrorStats:uncorrectableErrors
        managed object property"
    ::= { cfprApAdaptorMenloEthErrorStatsEntry 29 }

cfprApAdaptorMenloEthErrorStatsUncorrectableErrorsDelta OBJECT-TYPE
    SYNTAX       Counter64
    MAX-ACCESS   read-only
    STATUS       current
    DESCRIPTION
        "Cisco Firepower adaptor:MenloEthErrorStats:uncorrectableErrorsDel
        ta managed object property"
    ::= { cfprApAdaptorMenloEthErrorStatsEntry 30 }

cfprApAdaptorMenloEthErrorStatsUncorrectableErrorsDeltaAvg OBJECT-TYPE
    SYNTAX       Unsigned64
    MAX-ACCESS   read-only
    STATUS       current
    DESCRIPTION
        "Cisco Firepower adaptor:MenloEthErrorStats:uncorrectableErrorsDel
        taAvg managed object property"
    ::= { cfprApAdaptorMenloEthErrorStatsEntry 31 }

cfprApAdaptorMenloEthErrorStatsUncorrectableErrorsDeltaMax OBJECT-TYPE
    SYNTAX       Unsigned64
    MAX-ACCESS   read-only
    STATUS       current
    DESCRIPTION
        "Cisco Firepower adaptor:MenloEthErrorStats:uncorrectableErrorsDel
        taMax managed object property"
    ::= { cfprApAdaptorMenloEthErrorStatsEntry 32 }

cfprApAdaptorMenloEthErrorStatsUncorrectableErrorsDeltaMin OBJECT-TYPE
    SYNTAX       Unsigned64
    MAX-ACCESS   read-only
    STATUS       current
    DESCRIPTION
        "Cisco Firepower adaptor:MenloEthErrorStats:uncorrectableErrorsDel
        taMin managed object property"
    ::= { cfprApAdaptorMenloEthErrorStatsEntry 33 }

cfprApAdaptorMenloEthErrorStatsUpdate OBJECT-TYPE
    SYNTAX       Gauge32
    MAX-ACCESS   read-only
    STATUS       current
    DESCRIPTION
        "Cisco Firepower adaptor:MenloEthErrorStats:update
        managed object property"
    ::= { cfprApAdaptorMenloEthErrorStatsEntry 34 }

cfprApAdaptorMenloEthErrorStatsHistTable OBJECT-TYPE
    SYNTAX           SEQUENCE OF CfprApAdaptorMenloEthErrorStatsHistEntry
    MAX-ACCESS       not-accessible
    STATUS           current
    DESCRIPTION
        "Cisco Firepower adaptor:MenloEthErrorStatsHist
        managed object table"
    ::= { cfprApAdaptorObjects 87 }

cfprApAdaptorMenloEthErrorStatsHistEntry OBJECT-TYPE
    SYNTAX           CfprApAdaptorMenloEthErrorStatsHistEntry
    MAX-ACCESS       not-accessible
    STATUS           current
    DESCRIPTION
        "Entry for the cfprApAdaptorMenloEthErrorStatsHistTable table."
    INDEX { cfprApAdaptorMenloEthErrorStatsHistInstanceId }
    ::= { cfprApAdaptorMenloEthErrorStatsHistTable 1 }

CfprApAdaptorMenloEthErrorStatsHistEntry ::= SEQUENCE {
    cfprApAdaptorMenloEthErrorStatsHistInstanceId                    CfprApManagedObjectId,
    cfprApAdaptorMenloEthErrorStatsHistDn                            CfprApManagedObjectDn,
    cfprApAdaptorMenloEthErrorStatsHistRn                            SnmpAdminString,
    cfprApAdaptorMenloEthErrorStatsHistCorrectableErrors             Unsigned64,
    cfprApAdaptorMenloEthErrorStatsHistCorrectableErrorsDelta        Unsigned64,
    cfprApAdaptorMenloEthErrorStatsHistCorrectableErrorsDeltaAvg     Unsigned64,
    cfprApAdaptorMenloEthErrorStatsHistCorrectableErrorsDeltaMax     Unsigned64,
    cfprApAdaptorMenloEthErrorStatsHistCorrectableErrorsDeltaMin     Unsigned64,
    cfprApAdaptorMenloEthErrorStatsHistDropAcl                       Unsigned64,
    cfprApAdaptorMenloEthErrorStatsHistDropAclDelta                  Unsigned64,
    cfprApAdaptorMenloEthErrorStatsHistDropAclDeltaAvg               Unsigned64,
    cfprApAdaptorMenloEthErrorStatsHistDropAclDeltaMax               Unsigned64,
    cfprApAdaptorMenloEthErrorStatsHistDropAclDeltaMin               Unsigned64,
    cfprApAdaptorMenloEthErrorStatsHistId                            Unsigned64,
    cfprApAdaptorMenloEthErrorStatsHistMostRecent                    TruthValue,
    cfprApAdaptorMenloEthErrorStatsHistPopErrors                     Unsigned64,
    cfprApAdaptorMenloEthErrorStatsHistPopErrorsDelta                Unsigned64,
    cfprApAdaptorMenloEthErrorStatsHistPopErrorsDeltaAvg             Unsigned64,
    cfprApAdaptorMenloEthErrorStatsHistPopErrorsDeltaMax             Unsigned64,
    cfprApAdaptorMenloEthErrorStatsHistPopErrorsDeltaMin             Unsigned64,
    cfprApAdaptorMenloEthErrorStatsHistPushErrors                    Unsigned64,
    cfprApAdaptorMenloEthErrorStatsHistPushErrorsDelta               Unsigned64,
    cfprApAdaptorMenloEthErrorStatsHistPushErrorsDeltaAvg            Unsigned64,
    cfprApAdaptorMenloEthErrorStatsHistPushErrorsDeltaMax            Unsigned64,
    cfprApAdaptorMenloEthErrorStatsHistPushErrorsDeltaMin            Unsigned64,
    cfprApAdaptorMenloEthErrorStatsHistSuspect                       TruthValue,
    cfprApAdaptorMenloEthErrorStatsHistThresholded                   CfprApAdaptorMenloEthErrorStatsHistThresholded,
    cfprApAdaptorMenloEthErrorStatsHistTimeCollected                 DateAndTime,
    cfprApAdaptorMenloEthErrorStatsHistUncorrectableErrors           Unsigned64,
    cfprApAdaptorMenloEthErrorStatsHistUncorrectableErrorsDelta      Unsigned64,
    cfprApAdaptorMenloEthErrorStatsHistUncorrectableErrorsDeltaAvg   Unsigned64,
    cfprApAdaptorMenloEthErrorStatsHistUncorrectableErrorsDeltaMax   Unsigned64,
    cfprApAdaptorMenloEthErrorStatsHistUncorrectableErrorsDeltaMin   Unsigned64
}

cfprApAdaptorMenloEthErrorStatsHistInstanceId OBJECT-TYPE
    SYNTAX       CfprApManagedObjectId
    MAX-ACCESS   not-accessible
    STATUS       current
    DESCRIPTION
        "Instance identifier of the managed object."
    ::= { cfprApAdaptorMenloEthErrorStatsHistEntry 1 }

cfprApAdaptorMenloEthErrorStatsHistDn OBJECT-TYPE
    SYNTAX       CfprApManagedObjectDn
    MAX-ACCESS   read-only
    STATUS       current
    DESCRIPTION
        "Cisco Firepower adaptor:MenloEthErrorStatsHist:dn
        managed object property"
    ::= { cfprApAdaptorMenloEthErrorStatsHistEntry 2 }

cfprApAdaptorMenloEthErrorStatsHistRn OBJECT-TYPE
    SYNTAX       SnmpAdminString
    MAX-ACCESS   read-only
    STATUS       current
    DESCRIPTION
        "Cisco Firepower adaptor:MenloEthErrorStatsHist:rn
        managed object property"
    ::= { cfprApAdaptorMenloEthErrorStatsHistEntry 3 }

cfprApAdaptorMenloEthErrorStatsHistCorrectableErrors OBJECT-TYPE
    SYNTAX       Unsigned64
    MAX-ACCESS   read-only
    STATUS       current
    DESCRIPTION
        "Cisco Firepower adaptor:MenloEthErrorStatsHist:correctableErrors
        managed object property"
    ::= { cfprApAdaptorMenloEthErrorStatsHistEntry 4 }

cfprApAdaptorMenloEthErrorStatsHistCorrectableErrorsDelta OBJECT-TYPE
    SYNTAX       Unsigned64
    MAX-ACCESS   read-only
    STATUS       current
    DESCRIPTION
        "Cisco Firepower adaptor:MenloEthErrorStatsHist:correctableErrorsD
        elta managed object property"
    ::= { cfprApAdaptorMenloEthErrorStatsHistEntry 5 }

cfprApAdaptorMenloEthErrorStatsHistCorrectableErrorsDeltaAvg OBJECT-TYPE
    SYNTAX       Unsigned64
    MAX-ACCESS   read-only
    STATUS       current
    DESCRIPTION
        "Cisco Firepower adaptor:MenloEthErrorStatsHist:correctableErrorsD
        eltaAvg managed object property"
    ::= { cfprApAdaptorMenloEthErrorStatsHistEntry 6 }

cfprApAdaptorMenloEthErrorStatsHistCorrectableErrorsDeltaMax OBJECT-TYPE
    SYNTAX       Unsigned64
    MAX-ACCESS   read-only
    STATUS       current
    DESCRIPTION
        "Cisco Firepower adaptor:MenloEthErrorStatsHist:correctableErrorsD
        eltaMax managed object property"
    ::= { cfprApAdaptorMenloEthErrorStatsHistEntry 7 }

cfprApAdaptorMenloEthErrorStatsHistCorrectableErrorsDeltaMin OBJECT-TYPE
    SYNTAX       Unsigned64
    MAX-ACCESS   read-only
    STATUS       current
    DESCRIPTION
        "Cisco Firepower adaptor:MenloEthErrorStatsHist:correctableErrorsD
        eltaMin managed object property"
    ::= { cfprApAdaptorMenloEthErrorStatsHistEntry 8 }

cfprApAdaptorMenloEthErrorStatsHistDropAcl OBJECT-TYPE
    SYNTAX       Unsigned64
    MAX-ACCESS   read-only
    STATUS       current
    DESCRIPTION
        "Cisco Firepower adaptor:MenloEthErrorStatsHist:dropAcl
        managed object property"
    ::= { cfprApAdaptorMenloEthErrorStatsHistEntry 9 }

cfprApAdaptorMenloEthErrorStatsHistDropAclDelta OBJECT-TYPE
    SYNTAX       Unsigned64
    MAX-ACCESS   read-only
    STATUS       current
    DESCRIPTION
        "Cisco Firepower adaptor:MenloEthErrorStatsHist:dropAclDelta
        managed object property"
    ::= { cfprApAdaptorMenloEthErrorStatsHistEntry 10 }

cfprApAdaptorMenloEthErrorStatsHistDropAclDeltaAvg OBJECT-TYPE
    SYNTAX       Unsigned64
    MAX-ACCESS   read-only
    STATUS       current
    DESCRIPTION
        "Cisco Firepower adaptor:MenloEthErrorStatsHist:dropAclDeltaAvg
        managed object property"
    ::= { cfprApAdaptorMenloEthErrorStatsHistEntry 11 }

cfprApAdaptorMenloEthErrorStatsHistDropAclDeltaMax OBJECT-TYPE
    SYNTAX       Unsigned64
    MAX-ACCESS   read-only
    STATUS       current
    DESCRIPTION
        "Cisco Firepower adaptor:MenloEthErrorStatsHist:dropAclDeltaMax
        managed object property"
    ::= { cfprApAdaptorMenloEthErrorStatsHistEntry 12 }

cfprApAdaptorMenloEthErrorStatsHistDropAclDeltaMin OBJECT-TYPE
    SYNTAX       Unsigned64
    MAX-ACCESS   read-only
    STATUS       current
    DESCRIPTION
        "Cisco Firepower adaptor:MenloEthErrorStatsHist:dropAclDeltaMin
        managed object property"
    ::= { cfprApAdaptorMenloEthErrorStatsHistEntry 13 }

cfprApAdaptorMenloEthErrorStatsHistId OBJECT-TYPE
    SYNTAX       Unsigned64
    MAX-ACCESS   read-only
    STATUS       current
    DESCRIPTION
        "Cisco Firepower adaptor:MenloEthErrorStatsHist:id
        managed object property"
    ::= { cfprApAdaptorMenloEthErrorStatsHistEntry 14 }

cfprApAdaptorMenloEthErrorStatsHistMostRecent OBJECT-TYPE
    SYNTAX       TruthValue
    MAX-ACCESS   read-only
    STATUS       current
    DESCRIPTION
        "Cisco Firepower adaptor:MenloEthErrorStatsHist:mostRecent
        managed object property"
    ::= { cfprApAdaptorMenloEthErrorStatsHistEntry 15 }

cfprApAdaptorMenloEthErrorStatsHistPopErrors OBJECT-TYPE
    SYNTAX       Unsigned64
    MAX-ACCESS   read-only
    STATUS       current
    DESCRIPTION
        "Cisco Firepower adaptor:MenloEthErrorStatsHist:popErrors
        managed object property"
    ::= { cfprApAdaptorMenloEthErrorStatsHistEntry 16 }

cfprApAdaptorMenloEthErrorStatsHistPopErrorsDelta OBJECT-TYPE
    SYNTAX       Unsigned64
    MAX-ACCESS   read-only
    STATUS       current
    DESCRIPTION
        "Cisco Firepower adaptor:MenloEthErrorStatsHist:popErrorsDelta
        managed object property"
    ::= { cfprApAdaptorMenloEthErrorStatsHistEntry 17 }

cfprApAdaptorMenloEthErrorStatsHistPopErrorsDeltaAvg OBJECT-TYPE
    SYNTAX       Unsigned64
    MAX-ACCESS   read-only
    STATUS       current
    DESCRIPTION
        "Cisco Firepower adaptor:MenloEthErrorStatsHist:popErrorsDeltaAvg
        managed object property"
    ::= { cfprApAdaptorMenloEthErrorStatsHistEntry 18 }

cfprApAdaptorMenloEthErrorStatsHistPopErrorsDeltaMax OBJECT-TYPE
    SYNTAX       Unsigned64
    MAX-ACCESS   read-only
    STATUS       current
    DESCRIPTION
        "Cisco Firepower adaptor:MenloEthErrorStatsHist:popErrorsDeltaMax
        managed object property"
    ::= { cfprApAdaptorMenloEthErrorStatsHistEntry 19 }

cfprApAdaptorMenloEthErrorStatsHistPopErrorsDeltaMin OBJECT-TYPE
    SYNTAX       Unsigned64
    MAX-ACCESS   read-only
    STATUS       current
    DESCRIPTION
        "Cisco Firepower adaptor:MenloEthErrorStatsHist:popErrorsDeltaMin
        managed object property"
    ::= { cfprApAdaptorMenloEthErrorStatsHistEntry 20 }

cfprApAdaptorMenloEthErrorStatsHistPushErrors OBJECT-TYPE
    SYNTAX       Unsigned64
    MAX-ACCESS   read-only
    STATUS       current
    DESCRIPTION
        "Cisco Firepower adaptor:MenloEthErrorStatsHist:pushErrors
        managed object property"
    ::= { cfprApAdaptorMenloEthErrorStatsHistEntry 21 }

cfprApAdaptorMenloEthErrorStatsHistPushErrorsDelta OBJECT-TYPE
    SYNTAX       Unsigned64
    MAX-ACCESS   read-only
    STATUS       current
    DESCRIPTION
        "Cisco Firepower adaptor:MenloEthErrorStatsHist:pushErrorsDelta
        managed object property"
    ::= { cfprApAdaptorMenloEthErrorStatsHistEntry 22 }

cfprApAdaptorMenloEthErrorStatsHistPushErrorsDeltaAvg OBJECT-TYPE
    SYNTAX       Unsigned64
    MAX-ACCESS   read-only
    STATUS       current
    DESCRIPTION
        "Cisco Firepower adaptor:MenloEthErrorStatsHist:pushErrorsDeltaAvg
         managed object property"
    ::= { cfprApAdaptorMenloEthErrorStatsHistEntry 23 }

cfprApAdaptorMenloEthErrorStatsHistPushErrorsDeltaMax OBJECT-TYPE
    SYNTAX       Unsigned64
    MAX-ACCESS   read-only
    STATUS       current
    DESCRIPTION
        "Cisco Firepower adaptor:MenloEthErrorStatsHist:pushErrorsDeltaMax
         managed object property"
    ::= { cfprApAdaptorMenloEthErrorStatsHistEntry 24 }

cfprApAdaptorMenloEthErrorStatsHistPushErrorsDeltaMin OBJECT-TYPE
    SYNTAX       Unsigned64
    MAX-ACCESS   read-only
    STATUS       current
    DESCRIPTION
        "Cisco Firepower adaptor:MenloEthErrorStatsHist:pushErrorsDeltaMin
         managed object property"
    ::= { cfprApAdaptorMenloEthErrorStatsHistEntry 25 }

cfprApAdaptorMenloEthErrorStatsHistSuspect OBJECT-TYPE
    SYNTAX       TruthValue
    MAX-ACCESS   read-only
    STATUS       current
    DESCRIPTION
        "Cisco Firepower adaptor:MenloEthErrorStatsHist:suspect
        managed object property"
    ::= { cfprApAdaptorMenloEthErrorStatsHistEntry 26 }

cfprApAdaptorMenloEthErrorStatsHistThresholded OBJECT-TYPE
    SYNTAX       CfprApAdaptorMenloEthErrorStatsHistThresholded
    MAX-ACCESS   read-only
    STATUS       current
    DESCRIPTION
        "Cisco Firepower adaptor:MenloEthErrorStatsHist:thresholded
        managed object property"
    ::= { cfprApAdaptorMenloEthErrorStatsHistEntry 27 }

cfprApAdaptorMenloEthErrorStatsHistTimeCollected OBJECT-TYPE
    SYNTAX       DateAndTime
    MAX-ACCESS   read-only
    STATUS       current
    DESCRIPTION
        "Cisco Firepower adaptor:MenloEthErrorStatsHist:timeCollected
        managed object property"
    ::= { cfprApAdaptorMenloEthErrorStatsHistEntry 28 }

cfprApAdaptorMenloEthErrorStatsHistUncorrectableErrors OBJECT-TYPE
    SYNTAX       Unsigned64
    MAX-ACCESS   read-only
    STATUS       current
    DESCRIPTION
        "Cisco Firepower adaptor:MenloEthErrorStatsHist:uncorrectableError
        s managed object property"
    ::= { cfprApAdaptorMenloEthErrorStatsHistEntry 29 }

cfprApAdaptorMenloEthErrorStatsHistUncorrectableErrorsDelta OBJECT-TYPE
    SYNTAX       Unsigned64
    MAX-ACCESS   read-only
    STATUS       current
    DESCRIPTION
        "Cisco Firepower adaptor:MenloEthErrorStatsHist:uncorrectableError
        sDelta managed object property"
    ::= { cfprApAdaptorMenloEthErrorStatsHistEntry 30 }

cfprApAdaptorMenloEthErrorStatsHistUncorrectableErrorsDeltaAvg OBJECT-TYPE
    SYNTAX       Unsigned64
    MAX-ACCESS   read-only
    STATUS       current
    DESCRIPTION
        "Cisco Firepower adaptor:MenloEthErrorStatsHist:uncorrectableError
        sDeltaAvg managed object property"
    ::= { cfprApAdaptorMenloEthErrorStatsHistEntry 31 }

cfprApAdaptorMenloEthErrorStatsHistUncorrectableErrorsDeltaMax OBJECT-TYPE
    SYNTAX       Unsigned64
    MAX-ACCESS   read-only
    STATUS       current
    DESCRIPTION
        "Cisco Firepower adaptor:MenloEthErrorStatsHist:uncorrectableError
        sDeltaMax managed object property"
    ::= { cfprApAdaptorMenloEthErrorStatsHistEntry 32 }

cfprApAdaptorMenloEthErrorStatsHistUncorrectableErrorsDeltaMin OBJECT-TYPE
    SYNTAX       Unsigned64
    MAX-ACCESS   read-only
    STATUS       current
    DESCRIPTION
        "Cisco Firepower adaptor:MenloEthErrorStatsHist:uncorrectableError
        sDeltaMin managed object property"
    ::= { cfprApAdaptorMenloEthErrorStatsHistEntry 33 }

cfprApAdaptorMenloEthStatsTable OBJECT-TYPE
    SYNTAX           SEQUENCE OF CfprApAdaptorMenloEthStatsEntry
    MAX-ACCESS       not-accessible
    STATUS           current
    DESCRIPTION
        "Cisco Firepower adaptor:MenloEthStats managed object table"
    ::= { cfprApAdaptorObjects 88 }

cfprApAdaptorMenloEthStatsEntry OBJECT-TYPE
    SYNTAX           CfprApAdaptorMenloEthStatsEntry
    MAX-ACCESS       not-accessible
    STATUS           current
    DESCRIPTION
        "Entry for the cfprApAdaptorMenloEthStatsTable table."
    INDEX { cfprApAdaptorMenloEthStatsInstanceId }
    ::= { cfprApAdaptorMenloEthStatsTable 1 }

CfprApAdaptorMenloEthStatsEntry ::= SEQUENCE {
    cfprApAdaptorMenloEthStatsInstanceId                             CfprApManagedObjectId,
    cfprApAdaptorMenloEthStatsDn                                     CfprApManagedObjectDn,
    cfprApAdaptorMenloEthStatsRn                                     SnmpAdminString,
    cfprApAdaptorMenloEthStatsDropOverrun                            Unsigned64,
    cfprApAdaptorMenloEthStatsDropOverrunDelta                       Counter64,
    cfprApAdaptorMenloEthStatsDropOverrunDeltaAvg                    Unsigned64,
    cfprApAdaptorMenloEthStatsDropOverrunDeltaMax                    Unsigned64,
    cfprApAdaptorMenloEthStatsDropOverrunDeltaMin                    Unsigned64,
    cfprApAdaptorMenloEthStatsDropRunt                               Unsigned64,
    cfprApAdaptorMenloEthStatsDropRuntDelta                          Counter64,
    cfprApAdaptorMenloEthStatsDropRuntDeltaAvg                       Unsigned64,
    cfprApAdaptorMenloEthStatsDropRuntDeltaMax                       Unsigned64,
    cfprApAdaptorMenloEthStatsDropRuntDeltaMin                       Unsigned64,
    cfprApAdaptorMenloEthStatsIntervals                              Gauge32,
    cfprApAdaptorMenloEthStatsMenloEthIndex                          CfprApAdaptorMenloStatsIndex,
    cfprApAdaptorMenloEthStatsSuspect                                TruthValue,
    cfprApAdaptorMenloEthStatsThresholded                            CfprApAdaptorMenloEthStatsThresholded,
    cfprApAdaptorMenloEthStatsTimeCollected                          DateAndTime,
    cfprApAdaptorMenloEthStatsTruncateOverrun                        Unsigned64,
    cfprApAdaptorMenloEthStatsTruncateOverrunDelta                   Counter64,
    cfprApAdaptorMenloEthStatsTruncateOverrunDeltaAvg                Unsigned64,
    cfprApAdaptorMenloEthStatsTruncateOverrunDeltaMax                Unsigned64,
    cfprApAdaptorMenloEthStatsTruncateOverrunDeltaMin                Unsigned64,
    cfprApAdaptorMenloEthStatsUpdate                                 Gauge32
}

cfprApAdaptorMenloEthStatsInstanceId OBJECT-TYPE
    SYNTAX       CfprApManagedObjectId
    MAX-ACCESS   not-accessible
    STATUS       current
    DESCRIPTION
        "Instance identifier of the managed object."
    ::= { cfprApAdaptorMenloEthStatsEntry 1 }

cfprApAdaptorMenloEthStatsDn OBJECT-TYPE
    SYNTAX       CfprApManagedObjectDn
    MAX-ACCESS   read-only
    STATUS       current
    DESCRIPTION
        "Cisco Firepower adaptor:MenloEthStats:dn managed object property"
    ::= { cfprApAdaptorMenloEthStatsEntry 2 }

cfprApAdaptorMenloEthStatsRn OBJECT-TYPE
    SYNTAX       SnmpAdminString
    MAX-ACCESS   read-only
    STATUS       current
    DESCRIPTION
        "Cisco Firepower adaptor:MenloEthStats:rn managed object property"
    ::= { cfprApAdaptorMenloEthStatsEntry 3 }

cfprApAdaptorMenloEthStatsDropOverrun OBJECT-TYPE
    SYNTAX       Unsigned64
    MAX-ACCESS   read-only
    STATUS       current
    DESCRIPTION
        "Cisco Firepower adaptor:MenloEthStats:dropOverrun
        managed object property"
    ::= { cfprApAdaptorMenloEthStatsEntry 4 }

cfprApAdaptorMenloEthStatsDropOverrunDelta OBJECT-TYPE
    SYNTAX       Counter64
    MAX-ACCESS   read-only
    STATUS       current
    DESCRIPTION
        "Cisco Firepower adaptor:MenloEthStats:dropOverrunDelta
        managed object property"
    ::= { cfprApAdaptorMenloEthStatsEntry 5 }

cfprApAdaptorMenloEthStatsDropOverrunDeltaAvg OBJECT-TYPE
    SYNTAX       Unsigned64
    MAX-ACCESS   read-only
    STATUS       current
    DESCRIPTION
        "Cisco Firepower adaptor:MenloEthStats:dropOverrunDeltaAvg
        managed object property"
    ::= { cfprApAdaptorMenloEthStatsEntry 6 }

cfprApAdaptorMenloEthStatsDropOverrunDeltaMax OBJECT-TYPE
    SYNTAX       Unsigned64
    MAX-ACCESS   read-only
    STATUS       current
    DESCRIPTION
        "Cisco Firepower adaptor:MenloEthStats:dropOverrunDeltaMax
        managed object property"
    ::= { cfprApAdaptorMenloEthStatsEntry 7 }

cfprApAdaptorMenloEthStatsDropOverrunDeltaMin OBJECT-TYPE
    SYNTAX       Unsigned64
    MAX-ACCESS   read-only
    STATUS       current
    DESCRIPTION
        "Cisco Firepower adaptor:MenloEthStats:dropOverrunDeltaMin
        managed object property"
    ::= { cfprApAdaptorMenloEthStatsEntry 8 }

cfprApAdaptorMenloEthStatsDropRunt OBJECT-TYPE
    SYNTAX       Unsigned64
    MAX-ACCESS   read-only
    STATUS       current
    DESCRIPTION
        "Cisco Firepower adaptor:MenloEthStats:dropRunt
        managed object property"
    ::= { cfprApAdaptorMenloEthStatsEntry 9 }

cfprApAdaptorMenloEthStatsDropRuntDelta OBJECT-TYPE
    SYNTAX       Counter64
    MAX-ACCESS   read-only
    STATUS       current
    DESCRIPTION
        "Cisco Firepower adaptor:MenloEthStats:dropRuntDelta
        managed object property"
    ::= { cfprApAdaptorMenloEthStatsEntry 10 }

cfprApAdaptorMenloEthStatsDropRuntDeltaAvg OBJECT-TYPE
    SYNTAX       Unsigned64
    MAX-ACCESS   read-only
    STATUS       current
    DESCRIPTION
        "Cisco Firepower adaptor:MenloEthStats:dropRuntDeltaAvg
        managed object property"
    ::= { cfprApAdaptorMenloEthStatsEntry 11 }

cfprApAdaptorMenloEthStatsDropRuntDeltaMax OBJECT-TYPE
    SYNTAX       Unsigned64
    MAX-ACCESS   read-only
    STATUS       current
    DESCRIPTION
        "Cisco Firepower adaptor:MenloEthStats:dropRuntDeltaMax
        managed object property"
    ::= { cfprApAdaptorMenloEthStatsEntry 12 }

cfprApAdaptorMenloEthStatsDropRuntDeltaMin OBJECT-TYPE
    SYNTAX       Unsigned64
    MAX-ACCESS   read-only
    STATUS       current
    DESCRIPTION
        "Cisco Firepower adaptor:MenloEthStats:dropRuntDeltaMin
        managed object property"
    ::= { cfprApAdaptorMenloEthStatsEntry 13 }

cfprApAdaptorMenloEthStatsIntervals OBJECT-TYPE
    SYNTAX       Gauge32
    MAX-ACCESS   read-only
    STATUS       current
    DESCRIPTION
        "Cisco Firepower adaptor:MenloEthStats:intervals
        managed object property"
    ::= { cfprApAdaptorMenloEthStatsEntry 14 }

cfprApAdaptorMenloEthStatsMenloEthIndex OBJECT-TYPE
    SYNTAX       CfprApAdaptorMenloStatsIndex
    MAX-ACCESS   read-only
    STATUS       current
    DESCRIPTION
        "Cisco Firepower adaptor:MenloEthStats:menloEthIndex
        managed object property"
    ::= { cfprApAdaptorMenloEthStatsEntry 15 }

cfprApAdaptorMenloEthStatsSuspect OBJECT-TYPE
    SYNTAX       TruthValue
    MAX-ACCESS   read-only
    STATUS       current
    DESCRIPTION
        "Cisco Firepower adaptor:MenloEthStats:suspect
        managed object property"
    ::= { cfprApAdaptorMenloEthStatsEntry 16 }

cfprApAdaptorMenloEthStatsThresholded OBJECT-TYPE
    SYNTAX       CfprApAdaptorMenloEthStatsThresholded
    MAX-ACCESS   read-only
    STATUS       current
    DESCRIPTION
        "Cisco Firepower adaptor:MenloEthStats:thresholded
        managed object property"
    ::= { cfprApAdaptorMenloEthStatsEntry 17 }

cfprApAdaptorMenloEthStatsTimeCollected OBJECT-TYPE
    SYNTAX       DateAndTime
    MAX-ACCESS   read-only
    STATUS       current
    DESCRIPTION
        "Cisco Firepower adaptor:MenloEthStats:timeCollected
        managed object property"
    ::= { cfprApAdaptorMenloEthStatsEntry 18 }

cfprApAdaptorMenloEthStatsTruncateOverrun OBJECT-TYPE
    SYNTAX       Unsigned64
    MAX-ACCESS   read-only
    STATUS       current
    DESCRIPTION
        "Cisco Firepower adaptor:MenloEthStats:truncateOverrun
        managed object property"
    ::= { cfprApAdaptorMenloEthStatsEntry 19 }

cfprApAdaptorMenloEthStatsTruncateOverrunDelta OBJECT-TYPE
    SYNTAX       Counter64
    MAX-ACCESS   read-only
    STATUS       current
    DESCRIPTION
        "Cisco Firepower adaptor:MenloEthStats:truncateOverrunDelta
        managed object property"
    ::= { cfprApAdaptorMenloEthStatsEntry 20 }

cfprApAdaptorMenloEthStatsTruncateOverrunDeltaAvg OBJECT-TYPE
    SYNTAX       Unsigned64
    MAX-ACCESS   read-only
    STATUS       current
    DESCRIPTION
        "Cisco Firepower adaptor:MenloEthStats:truncateOverrunDeltaAvg
        managed object property"
    ::= { cfprApAdaptorMenloEthStatsEntry 21 }

cfprApAdaptorMenloEthStatsTruncateOverrunDeltaMax OBJECT-TYPE
    SYNTAX       Unsigned64
    MAX-ACCESS   read-only
    STATUS       current
    DESCRIPTION
        "Cisco Firepower adaptor:MenloEthStats:truncateOverrunDeltaMax
        managed object property"
    ::= { cfprApAdaptorMenloEthStatsEntry 22 }

cfprApAdaptorMenloEthStatsTruncateOverrunDeltaMin OBJECT-TYPE
    SYNTAX       Unsigned64
    MAX-ACCESS   read-only
    STATUS       current
    DESCRIPTION
        "Cisco Firepower adaptor:MenloEthStats:truncateOverrunDeltaMin
        managed object property"
    ::= { cfprApAdaptorMenloEthStatsEntry 23 }

cfprApAdaptorMenloEthStatsUpdate OBJECT-TYPE
    SYNTAX       Gauge32
    MAX-ACCESS   read-only
    STATUS       current
    DESCRIPTION
        "Cisco Firepower adaptor:MenloEthStats:update managed
        object property"
    ::= { cfprApAdaptorMenloEthStatsEntry 24 }

cfprApAdaptorMenloEthStatsHistTable OBJECT-TYPE
    SYNTAX           SEQUENCE OF CfprApAdaptorMenloEthStatsHistEntry
    MAX-ACCESS       not-accessible
    STATUS           current
    DESCRIPTION
        "Cisco Firepower adaptor:MenloEthStatsHist managed object table"
    ::= { cfprApAdaptorObjects 89 }

cfprApAdaptorMenloEthStatsHistEntry OBJECT-TYPE
    SYNTAX           CfprApAdaptorMenloEthStatsHistEntry
    MAX-ACCESS       not-accessible
    STATUS           current
    DESCRIPTION
        "Entry for the cfprApAdaptorMenloEthStatsHistTable table."
    INDEX { cfprApAdaptorMenloEthStatsHistInstanceId }
    ::= { cfprApAdaptorMenloEthStatsHistTable 1 }

CfprApAdaptorMenloEthStatsHistEntry ::= SEQUENCE {
    cfprApAdaptorMenloEthStatsHistInstanceId                         CfprApManagedObjectId,
    cfprApAdaptorMenloEthStatsHistDn                                 CfprApManagedObjectDn,
    cfprApAdaptorMenloEthStatsHistRn                                 SnmpAdminString,
    cfprApAdaptorMenloEthStatsHistDropOverrun                        Unsigned64,
    cfprApAdaptorMenloEthStatsHistDropOverrunDelta                   Unsigned64,
    cfprApAdaptorMenloEthStatsHistDropOverrunDeltaAvg                Unsigned64,
    cfprApAdaptorMenloEthStatsHistDropOverrunDeltaMax                Unsigned64,
    cfprApAdaptorMenloEthStatsHistDropOverrunDeltaMin                Unsigned64,
    cfprApAdaptorMenloEthStatsHistDropRunt                           Unsigned64,
    cfprApAdaptorMenloEthStatsHistDropRuntDelta                      Unsigned64,
    cfprApAdaptorMenloEthStatsHistDropRuntDeltaAvg                   Unsigned64,
    cfprApAdaptorMenloEthStatsHistDropRuntDeltaMax                   Unsigned64,
    cfprApAdaptorMenloEthStatsHistDropRuntDeltaMin                   Unsigned64,
    cfprApAdaptorMenloEthStatsHistId                                 Unsigned64,
    cfprApAdaptorMenloEthStatsHistMostRecent                         TruthValue,
    cfprApAdaptorMenloEthStatsHistSuspect                            TruthValue,
    cfprApAdaptorMenloEthStatsHistThresholded                        CfprApAdaptorMenloEthStatsHistThresholded,
    cfprApAdaptorMenloEthStatsHistTimeCollected                      DateAndTime,
    cfprApAdaptorMenloEthStatsHistTruncateOverrun                    Unsigned64,
    cfprApAdaptorMenloEthStatsHistTruncateOverrunDelta               Unsigned64,
    cfprApAdaptorMenloEthStatsHistTruncateOverrunDeltaAvg            Unsigned64,
    cfprApAdaptorMenloEthStatsHistTruncateOverrunDeltaMax            Unsigned64,
    cfprApAdaptorMenloEthStatsHistTruncateOverrunDeltaMin            Unsigned64
}

cfprApAdaptorMenloEthStatsHistInstanceId OBJECT-TYPE
    SYNTAX       CfprApManagedObjectId
    MAX-ACCESS   not-accessible
    STATUS       current
    DESCRIPTION
        "Instance identifier of the managed object."
    ::= { cfprApAdaptorMenloEthStatsHistEntry 1 }

cfprApAdaptorMenloEthStatsHistDn OBJECT-TYPE
    SYNTAX       CfprApManagedObjectDn
    MAX-ACCESS   read-only
    STATUS       current
    DESCRIPTION
        "Cisco Firepower adaptor:MenloEthStatsHist:dn managed
        object property"
    ::= { cfprApAdaptorMenloEthStatsHistEntry 2 }

cfprApAdaptorMenloEthStatsHistRn OBJECT-TYPE
    SYNTAX       SnmpAdminString
    MAX-ACCESS   read-only
    STATUS       current
    DESCRIPTION
        "Cisco Firepower adaptor:MenloEthStatsHist:rn managed
        object property"
    ::= { cfprApAdaptorMenloEthStatsHistEntry 3 }

cfprApAdaptorMenloEthStatsHistDropOverrun OBJECT-TYPE
    SYNTAX       Unsigned64
    MAX-ACCESS   read-only
    STATUS       current
    DESCRIPTION
        "Cisco Firepower adaptor:MenloEthStatsHist:dropOverrun
        managed object property"
    ::= { cfprApAdaptorMenloEthStatsHistEntry 4 }

cfprApAdaptorMenloEthStatsHistDropOverrunDelta OBJECT-TYPE
    SYNTAX       Unsigned64
    MAX-ACCESS   read-only
    STATUS       current
    DESCRIPTION
        "Cisco Firepower adaptor:MenloEthStatsHist:dropOverrunDelta
        managed object property"
    ::= { cfprApAdaptorMenloEthStatsHistEntry 5 }

cfprApAdaptorMenloEthStatsHistDropOverrunDeltaAvg OBJECT-TYPE
    SYNTAX       Unsigned64
    MAX-ACCESS   read-only
    STATUS       current
    DESCRIPTION
        "Cisco Firepower adaptor:MenloEthStatsHist:dropOverrunDeltaAvg
        managed object property"
    ::= { cfprApAdaptorMenloEthStatsHistEntry 6 }

cfprApAdaptorMenloEthStatsHistDropOverrunDeltaMax OBJECT-TYPE
    SYNTAX       Unsigned64
    MAX-ACCESS   read-only
    STATUS       current
    DESCRIPTION
        "Cisco Firepower adaptor:MenloEthStatsHist:dropOverrunDeltaMax
        managed object property"
    ::= { cfprApAdaptorMenloEthStatsHistEntry 7 }

cfprApAdaptorMenloEthStatsHistDropOverrunDeltaMin OBJECT-TYPE
    SYNTAX       Unsigned64
    MAX-ACCESS   read-only
    STATUS       current
    DESCRIPTION
        "Cisco Firepower adaptor:MenloEthStatsHist:dropOverrunDeltaMin
        managed object property"
    ::= { cfprApAdaptorMenloEthStatsHistEntry 8 }

cfprApAdaptorMenloEthStatsHistDropRunt OBJECT-TYPE
    SYNTAX       Unsigned64
    MAX-ACCESS   read-only
    STATUS       current
    DESCRIPTION
        "Cisco Firepower adaptor:MenloEthStatsHist:dropRunt
        managed object property"
    ::= { cfprApAdaptorMenloEthStatsHistEntry 9 }

cfprApAdaptorMenloEthStatsHistDropRuntDelta OBJECT-TYPE
    SYNTAX       Unsigned64
    MAX-ACCESS   read-only
    STATUS       current
    DESCRIPTION
        "Cisco Firepower adaptor:MenloEthStatsHist:dropRuntDelta
        managed object property"
    ::= { cfprApAdaptorMenloEthStatsHistEntry 10 }

cfprApAdaptorMenloEthStatsHistDropRuntDeltaAvg OBJECT-TYPE
    SYNTAX       Unsigned64
    MAX-ACCESS   read-only
    STATUS       current
    DESCRIPTION
        "Cisco Firepower adaptor:MenloEthStatsHist:dropRuntDeltaAvg
        managed object property"
    ::= { cfprApAdaptorMenloEthStatsHistEntry 11 }

cfprApAdaptorMenloEthStatsHistDropRuntDeltaMax OBJECT-TYPE
    SYNTAX       Unsigned64
    MAX-ACCESS   read-only
    STATUS       current
    DESCRIPTION
        "Cisco Firepower adaptor:MenloEthStatsHist:dropRuntDeltaMax
        managed object property"
    ::= { cfprApAdaptorMenloEthStatsHistEntry 12 }

cfprApAdaptorMenloEthStatsHistDropRuntDeltaMin OBJECT-TYPE
    SYNTAX       Unsigned64
    MAX-ACCESS   read-only
    STATUS       current
    DESCRIPTION
        "Cisco Firepower adaptor:MenloEthStatsHist:dropRuntDeltaMin
        managed object property"
    ::= { cfprApAdaptorMenloEthStatsHistEntry 13 }

cfprApAdaptorMenloEthStatsHistId OBJECT-TYPE
    SYNTAX       Unsigned64
    MAX-ACCESS   read-only
    STATUS       current
    DESCRIPTION
        "Cisco Firepower adaptor:MenloEthStatsHist:id managed
        object property"
    ::= { cfprApAdaptorMenloEthStatsHistEntry 14 }

cfprApAdaptorMenloEthStatsHistMostRecent OBJECT-TYPE
    SYNTAX       TruthValue
    MAX-ACCESS   read-only
    STATUS       current
    DESCRIPTION
        "Cisco Firepower adaptor:MenloEthStatsHist:mostRecent
        managed object property"
    ::= { cfprApAdaptorMenloEthStatsHistEntry 15 }

cfprApAdaptorMenloEthStatsHistSuspect OBJECT-TYPE
    SYNTAX       TruthValue
    MAX-ACCESS   read-only
    STATUS       current
    DESCRIPTION
        "Cisco Firepower adaptor:MenloEthStatsHist:suspect
        managed object property"
    ::= { cfprApAdaptorMenloEthStatsHistEntry 16 }

cfprApAdaptorMenloEthStatsHistThresholded OBJECT-TYPE
    SYNTAX       CfprApAdaptorMenloEthStatsHistThresholded
    MAX-ACCESS   read-only
    STATUS       current
    DESCRIPTION
        "Cisco Firepower adaptor:MenloEthStatsHist:thresholded
        managed object property"
    ::= { cfprApAdaptorMenloEthStatsHistEntry 17 }

cfprApAdaptorMenloEthStatsHistTimeCollected OBJECT-TYPE
    SYNTAX       DateAndTime
    MAX-ACCESS   read-only
    STATUS       current
    DESCRIPTION
        "Cisco Firepower adaptor:MenloEthStatsHist:timeCollected
        managed object property"
    ::= { cfprApAdaptorMenloEthStatsHistEntry 18 }

cfprApAdaptorMenloEthStatsHistTruncateOverrun OBJECT-TYPE
    SYNTAX       Unsigned64
    MAX-ACCESS   read-only
    STATUS       current
    DESCRIPTION
        "Cisco Firepower adaptor:MenloEthStatsHist:truncateOverrun
        managed object property"
    ::= { cfprApAdaptorMenloEthStatsHistEntry 19 }

cfprApAdaptorMenloEthStatsHistTruncateOverrunDelta OBJECT-TYPE
    SYNTAX       Unsigned64
    MAX-ACCESS   read-only
    STATUS       current
    DESCRIPTION
        "Cisco Firepower adaptor:MenloEthStatsHist:truncateOverrunDelta
        managed object property"
    ::= { cfprApAdaptorMenloEthStatsHistEntry 20 }

cfprApAdaptorMenloEthStatsHistTruncateOverrunDeltaAvg OBJECT-TYPE
    SYNTAX       Unsigned64
    MAX-ACCESS   read-only
    STATUS       current
    DESCRIPTION
        "Cisco Firepower adaptor:MenloEthStatsHist:truncateOverrunDeltaAvg
         managed object property"
    ::= { cfprApAdaptorMenloEthStatsHistEntry 21 }

cfprApAdaptorMenloEthStatsHistTruncateOverrunDeltaMax OBJECT-TYPE
    SYNTAX       Unsigned64
    MAX-ACCESS   read-only
    STATUS       current
    DESCRIPTION
        "Cisco Firepower adaptor:MenloEthStatsHist:truncateOverrunDeltaMax
         managed object property"
    ::= { cfprApAdaptorMenloEthStatsHistEntry 22 }

cfprApAdaptorMenloEthStatsHistTruncateOverrunDeltaMin OBJECT-TYPE
    SYNTAX       Unsigned64
    MAX-ACCESS   read-only
    STATUS       current
    DESCRIPTION
        "Cisco Firepower adaptor:MenloEthStatsHist:truncateOverrunDeltaMin
         managed object property"
    ::= { cfprApAdaptorMenloEthStatsHistEntry 23 }

cfprApAdaptorMenloFcErrorStatsTable OBJECT-TYPE
    SYNTAX           SEQUENCE OF CfprApAdaptorMenloFcErrorStatsEntry
    MAX-ACCESS       not-accessible
    STATUS           current
    DESCRIPTION
        "Cisco Firepower adaptor:MenloFcErrorStats managed object table"
    ::= { cfprApAdaptorObjects 90 }

cfprApAdaptorMenloFcErrorStatsEntry OBJECT-TYPE
    SYNTAX           CfprApAdaptorMenloFcErrorStatsEntry
    MAX-ACCESS       not-accessible
    STATUS           current
    DESCRIPTION
        "Entry for the cfprApAdaptorMenloFcErrorStatsTable table."
    INDEX { cfprApAdaptorMenloFcErrorStatsInstanceId }
    ::= { cfprApAdaptorMenloFcErrorStatsTable 1 }

CfprApAdaptorMenloFcErrorStatsEntry ::= SEQUENCE {
    cfprApAdaptorMenloFcErrorStatsInstanceId                         CfprApManagedObjectId,
    cfprApAdaptorMenloFcErrorStatsDn                                 CfprApManagedObjectDn,
    cfprApAdaptorMenloFcErrorStatsRn                                 SnmpAdminString,
    cfprApAdaptorMenloFcErrorStatsCorrectableErrors                  Unsigned64,
    cfprApAdaptorMenloFcErrorStatsCorrectableErrorsDelta             Counter64,
    cfprApAdaptorMenloFcErrorStatsCorrectableErrorsDeltaAvg          Unsigned64,
    cfprApAdaptorMenloFcErrorStatsCorrectableErrorsDeltaMax          Unsigned64,
    cfprApAdaptorMenloFcErrorStatsCorrectableErrorsDeltaMin          Unsigned64,
    cfprApAdaptorMenloFcErrorStatsIntervals                          Gauge32,
    cfprApAdaptorMenloFcErrorStatsMenloFcIndex                       CfprApAdaptorMenloStatsIndex,
    cfprApAdaptorMenloFcErrorStatsPopErrors                          Unsigned64,
    cfprApAdaptorMenloFcErrorStatsPopErrorsDelta                     Counter64,
    cfprApAdaptorMenloFcErrorStatsPopErrorsDeltaAvg                  Unsigned64,
    cfprApAdaptorMenloFcErrorStatsPopErrorsDeltaMax                  Unsigned64,
    cfprApAdaptorMenloFcErrorStatsPopErrorsDeltaMin                  Unsigned64,
    cfprApAdaptorMenloFcErrorStatsPushErrors                         Unsigned64,
    cfprApAdaptorMenloFcErrorStatsPushErrorsDelta                    Counter64,
    cfprApAdaptorMenloFcErrorStatsPushErrorsDeltaAvg                 Unsigned64,
    cfprApAdaptorMenloFcErrorStatsPushErrorsDeltaMax                 Unsigned64,
    cfprApAdaptorMenloFcErrorStatsPushErrorsDeltaMin                 Unsigned64,
    cfprApAdaptorMenloFcErrorStatsSuspect                            TruthValue,
    cfprApAdaptorMenloFcErrorStatsThresholded                        CfprApAdaptorMenloFcErrorStatsThresholded,
    cfprApAdaptorMenloFcErrorStatsTimeCollected                      DateAndTime,
    cfprApAdaptorMenloFcErrorStatsUncorrectableErrors                Unsigned64,
    cfprApAdaptorMenloFcErrorStatsUncorrectableErrorsDelta           Counter64,
    cfprApAdaptorMenloFcErrorStatsUncorrectableErrorsDeltaAvg        Unsigned64,
    cfprApAdaptorMenloFcErrorStatsUncorrectableErrorsDeltaMax        Unsigned64,
    cfprApAdaptorMenloFcErrorStatsUncorrectableErrorsDeltaMin        Unsigned64,
    cfprApAdaptorMenloFcErrorStatsUpdate                             Gauge32
}

cfprApAdaptorMenloFcErrorStatsInstanceId OBJECT-TYPE
    SYNTAX       CfprApManagedObjectId
    MAX-ACCESS   not-accessible
    STATUS       current
    DESCRIPTION
        "Instance identifier of the managed object."
    ::= { cfprApAdaptorMenloFcErrorStatsEntry 1 }

cfprApAdaptorMenloFcErrorStatsDn OBJECT-TYPE
    SYNTAX       CfprApManagedObjectDn
    MAX-ACCESS   read-only
    STATUS       current
    DESCRIPTION
        "Cisco Firepower adaptor:MenloFcErrorStats:dn managed
        object property"
    ::= { cfprApAdaptorMenloFcErrorStatsEntry 2 }

cfprApAdaptorMenloFcErrorStatsRn OBJECT-TYPE
    SYNTAX       SnmpAdminString
    MAX-ACCESS   read-only
    STATUS       current
    DESCRIPTION
        "Cisco Firepower adaptor:MenloFcErrorStats:rn managed
        object property"
    ::= { cfprApAdaptorMenloFcErrorStatsEntry 3 }

cfprApAdaptorMenloFcErrorStatsCorrectableErrors OBJECT-TYPE
    SYNTAX       Unsigned64
    MAX-ACCESS   read-only
    STATUS       current
    DESCRIPTION
        "Cisco Firepower adaptor:MenloFcErrorStats:correctableErrors
        managed object property"
    ::= { cfprApAdaptorMenloFcErrorStatsEntry 4 }

cfprApAdaptorMenloFcErrorStatsCorrectableErrorsDelta OBJECT-TYPE
    SYNTAX       Counter64
    MAX-ACCESS   read-only
    STATUS       current
    DESCRIPTION
        "Cisco Firepower adaptor:MenloFcErrorStats:correctableErrorsDelta
        managed object property"
    ::= { cfprApAdaptorMenloFcErrorStatsEntry 5 }

cfprApAdaptorMenloFcErrorStatsCorrectableErrorsDeltaAvg OBJECT-TYPE
    SYNTAX       Unsigned64
    MAX-ACCESS   read-only
    STATUS       current
    DESCRIPTION
        "Cisco Firepower adaptor:MenloFcErrorStats:correctableErrorsDeltaA
        vg managed object property"
    ::= { cfprApAdaptorMenloFcErrorStatsEntry 6 }

cfprApAdaptorMenloFcErrorStatsCorrectableErrorsDeltaMax OBJECT-TYPE
    SYNTAX       Unsigned64
    MAX-ACCESS   read-only
    STATUS       current
    DESCRIPTION
        "Cisco Firepower adaptor:MenloFcErrorStats:correctableErrorsDeltaM
        ax managed object property"
    ::= { cfprApAdaptorMenloFcErrorStatsEntry 7 }

cfprApAdaptorMenloFcErrorStatsCorrectableErrorsDeltaMin OBJECT-TYPE
    SYNTAX       Unsigned64
    MAX-ACCESS   read-only
    STATUS       current
    DESCRIPTION
        "Cisco Firepower adaptor:MenloFcErrorStats:correctableErrorsDeltaM
        in managed object property"
    ::= { cfprApAdaptorMenloFcErrorStatsEntry 8 }

cfprApAdaptorMenloFcErrorStatsIntervals OBJECT-TYPE
    SYNTAX       Gauge32
    MAX-ACCESS   read-only
    STATUS       current
    DESCRIPTION
        "Cisco Firepower adaptor:MenloFcErrorStats:intervals
        managed object property"
    ::= { cfprApAdaptorMenloFcErrorStatsEntry 9 }

cfprApAdaptorMenloFcErrorStatsMenloFcIndex OBJECT-TYPE
    SYNTAX       CfprApAdaptorMenloStatsIndex
    MAX-ACCESS   read-only
    STATUS       current
    DESCRIPTION
        "Cisco Firepower adaptor:MenloFcErrorStats:menloFcIndex
        managed object property"
    ::= { cfprApAdaptorMenloFcErrorStatsEntry 10 }

cfprApAdaptorMenloFcErrorStatsPopErrors OBJECT-TYPE
    SYNTAX       Unsigned64
    MAX-ACCESS   read-only
    STATUS       current
    DESCRIPTION
        "Cisco Firepower adaptor:MenloFcErrorStats:popErrors
        managed object property"
    ::= { cfprApAdaptorMenloFcErrorStatsEntry 11 }

cfprApAdaptorMenloFcErrorStatsPopErrorsDelta OBJECT-TYPE
    SYNTAX       Counter64
    MAX-ACCESS   read-only
    STATUS       current
    DESCRIPTION
        "Cisco Firepower adaptor:MenloFcErrorStats:popErrorsDelta
        managed object property"
    ::= { cfprApAdaptorMenloFcErrorStatsEntry 12 }

cfprApAdaptorMenloFcErrorStatsPopErrorsDeltaAvg OBJECT-TYPE
    SYNTAX       Unsigned64
    MAX-ACCESS   read-only
    STATUS       current
    DESCRIPTION
        "Cisco Firepower adaptor:MenloFcErrorStats:popErrorsDeltaAvg
        managed object property"
    ::= { cfprApAdaptorMenloFcErrorStatsEntry 13 }

cfprApAdaptorMenloFcErrorStatsPopErrorsDeltaMax OBJECT-TYPE
    SYNTAX       Unsigned64
    MAX-ACCESS   read-only
    STATUS       current
    DESCRIPTION
        "Cisco Firepower adaptor:MenloFcErrorStats:popErrorsDeltaMax
        managed object property"
    ::= { cfprApAdaptorMenloFcErrorStatsEntry 14 }

cfprApAdaptorMenloFcErrorStatsPopErrorsDeltaMin OBJECT-TYPE
    SYNTAX       Unsigned64
    MAX-ACCESS   read-only
    STATUS       current
    DESCRIPTION
        "Cisco Firepower adaptor:MenloFcErrorStats:popErrorsDeltaMin
        managed object property"
    ::= { cfprApAdaptorMenloFcErrorStatsEntry 15 }

cfprApAdaptorMenloFcErrorStatsPushErrors OBJECT-TYPE
    SYNTAX       Unsigned64
    MAX-ACCESS   read-only
    STATUS       current
    DESCRIPTION
        "Cisco Firepower adaptor:MenloFcErrorStats:pushErrors
        managed object property"
    ::= { cfprApAdaptorMenloFcErrorStatsEntry 16 }

cfprApAdaptorMenloFcErrorStatsPushErrorsDelta OBJECT-TYPE
    SYNTAX       Counter64
    MAX-ACCESS   read-only
    STATUS       current
    DESCRIPTION
        "Cisco Firepower adaptor:MenloFcErrorStats:pushErrorsDelta
        managed object property"
    ::= { cfprApAdaptorMenloFcErrorStatsEntry 17 }

cfprApAdaptorMenloFcErrorStatsPushErrorsDeltaAvg OBJECT-TYPE
    SYNTAX       Unsigned64
    MAX-ACCESS   read-only
    STATUS       current
    DESCRIPTION
        "Cisco Firepower adaptor:MenloFcErrorStats:pushErrorsDeltaAvg
        managed object property"
    ::= { cfprApAdaptorMenloFcErrorStatsEntry 18 }

cfprApAdaptorMenloFcErrorStatsPushErrorsDeltaMax OBJECT-TYPE
    SYNTAX       Unsigned64
    MAX-ACCESS   read-only
    STATUS       current
    DESCRIPTION
        "Cisco Firepower adaptor:MenloFcErrorStats:pushErrorsDeltaMax
        managed object property"
    ::= { cfprApAdaptorMenloFcErrorStatsEntry 19 }

cfprApAdaptorMenloFcErrorStatsPushErrorsDeltaMin OBJECT-TYPE
    SYNTAX       Unsigned64
    MAX-ACCESS   read-only
    STATUS       current
    DESCRIPTION
        "Cisco Firepower adaptor:MenloFcErrorStats:pushErrorsDeltaMin
        managed object property"
    ::= { cfprApAdaptorMenloFcErrorStatsEntry 20 }

cfprApAdaptorMenloFcErrorStatsSuspect OBJECT-TYPE
    SYNTAX       TruthValue
    MAX-ACCESS   read-only
    STATUS       current
    DESCRIPTION
        "Cisco Firepower adaptor:MenloFcErrorStats:suspect
        managed object property"
    ::= { cfprApAdaptorMenloFcErrorStatsEntry 21 }

cfprApAdaptorMenloFcErrorStatsThresholded OBJECT-TYPE
    SYNTAX       CfprApAdaptorMenloFcErrorStatsThresholded
    MAX-ACCESS   read-only
    STATUS       current
    DESCRIPTION
        "Cisco Firepower adaptor:MenloFcErrorStats:thresholded
        managed object property"
    ::= { cfprApAdaptorMenloFcErrorStatsEntry 22 }

cfprApAdaptorMenloFcErrorStatsTimeCollected OBJECT-TYPE
    SYNTAX       DateAndTime
    MAX-ACCESS   read-only
    STATUS       current
    DESCRIPTION
        "Cisco Firepower adaptor:MenloFcErrorStats:timeCollected
        managed object property"
    ::= { cfprApAdaptorMenloFcErrorStatsEntry 23 }

cfprApAdaptorMenloFcErrorStatsUncorrectableErrors OBJECT-TYPE
    SYNTAX       Unsigned64
    MAX-ACCESS   read-only
    STATUS       current
    DESCRIPTION
        "Cisco Firepower adaptor:MenloFcErrorStats:uncorrectableErrors
        managed object property"
    ::= { cfprApAdaptorMenloFcErrorStatsEntry 24 }

cfprApAdaptorMenloFcErrorStatsUncorrectableErrorsDelta OBJECT-TYPE
    SYNTAX       Counter64
    MAX-ACCESS   read-only
    STATUS       current
    DESCRIPTION
        "Cisco Firepower adaptor:MenloFcErrorStats:uncorrectableErrorsDelt
        a managed object property"
    ::= { cfprApAdaptorMenloFcErrorStatsEntry 25 }

cfprApAdaptorMenloFcErrorStatsUncorrectableErrorsDeltaAvg OBJECT-TYPE
    SYNTAX       Unsigned64
    MAX-ACCESS   read-only
    STATUS       current
    DESCRIPTION
        "Cisco Firepower adaptor:MenloFcErrorStats:uncorrectableErrorsDelt
        aAvg managed object property"
    ::= { cfprApAdaptorMenloFcErrorStatsEntry 26 }

cfprApAdaptorMenloFcErrorStatsUncorrectableErrorsDeltaMax OBJECT-TYPE
    SYNTAX       Unsigned64
    MAX-ACCESS   read-only
    STATUS       current
    DESCRIPTION
        "Cisco Firepower adaptor:MenloFcErrorStats:uncorrectableErrorsDelt
        aMax managed object property"
    ::= { cfprApAdaptorMenloFcErrorStatsEntry 27 }

cfprApAdaptorMenloFcErrorStatsUncorrectableErrorsDeltaMin OBJECT-TYPE
    SYNTAX       Unsigned64
    MAX-ACCESS   read-only
    STATUS       current
    DESCRIPTION
        "Cisco Firepower adaptor:MenloFcErrorStats:uncorrectableErrorsDelt
        aMin managed object property"
    ::= { cfprApAdaptorMenloFcErrorStatsEntry 28 }

cfprApAdaptorMenloFcErrorStatsUpdate OBJECT-TYPE
    SYNTAX       Gauge32
    MAX-ACCESS   read-only
    STATUS       current
    DESCRIPTION
        "Cisco Firepower adaptor:MenloFcErrorStats:update
        managed object property"
    ::= { cfprApAdaptorMenloFcErrorStatsEntry 29 }

cfprApAdaptorMenloFcErrorStatsHistTable OBJECT-TYPE
    SYNTAX           SEQUENCE OF CfprApAdaptorMenloFcErrorStatsHistEntry
    MAX-ACCESS       not-accessible
    STATUS           current
    DESCRIPTION
        "Cisco Firepower adaptor:MenloFcErrorStatsHist
        managed object table"
    ::= { cfprApAdaptorObjects 91 }

cfprApAdaptorMenloFcErrorStatsHistEntry OBJECT-TYPE
    SYNTAX           CfprApAdaptorMenloFcErrorStatsHistEntry
    MAX-ACCESS       not-accessible
    STATUS           current
    DESCRIPTION
        "Entry for the cfprApAdaptorMenloFcErrorStatsHistTable table."
    INDEX { cfprApAdaptorMenloFcErrorStatsHistInstanceId }
    ::= { cfprApAdaptorMenloFcErrorStatsHistTable 1 }

CfprApAdaptorMenloFcErrorStatsHistEntry ::= SEQUENCE {
    cfprApAdaptorMenloFcErrorStatsHistInstanceId                     CfprApManagedObjectId,
    cfprApAdaptorMenloFcErrorStatsHistDn                             CfprApManagedObjectDn,
    cfprApAdaptorMenloFcErrorStatsHistRn                             SnmpAdminString,
    cfprApAdaptorMenloFcErrorStatsHistCorrectableErrors              Unsigned64,
    cfprApAdaptorMenloFcErrorStatsHistCorrectableErrorsDelta         Unsigned64,
    cfprApAdaptorMenloFcErrorStatsHistCorrectableErrorsDeltaAvg      Unsigned64,
    cfprApAdaptorMenloFcErrorStatsHistCorrectableErrorsDeltaMax      Unsigned64,
    cfprApAdaptorMenloFcErrorStatsHistCorrectableErrorsDeltaMin      Unsigned64,
    cfprApAdaptorMenloFcErrorStatsHistId                             Unsigned64,
    cfprApAdaptorMenloFcErrorStatsHistMostRecent                     TruthValue,
    cfprApAdaptorMenloFcErrorStatsHistPopErrors                      Unsigned64,
    cfprApAdaptorMenloFcErrorStatsHistPopErrorsDelta                 Unsigned64,
    cfprApAdaptorMenloFcErrorStatsHistPopErrorsDeltaAvg              Unsigned64,
    cfprApAdaptorMenloFcErrorStatsHistPopErrorsDeltaMax              Unsigned64,
    cfprApAdaptorMenloFcErrorStatsHistPopErrorsDeltaMin              Unsigned64,
    cfprApAdaptorMenloFcErrorStatsHistPushErrors                     Unsigned64,
    cfprApAdaptorMenloFcErrorStatsHistPushErrorsDelta                Unsigned64,
    cfprApAdaptorMenloFcErrorStatsHistPushErrorsDeltaAvg             Unsigned64,
    cfprApAdaptorMenloFcErrorStatsHistPushErrorsDeltaMax             Unsigned64,
    cfprApAdaptorMenloFcErrorStatsHistPushErrorsDeltaMin             Unsigned64,
    cfprApAdaptorMenloFcErrorStatsHistSuspect                        TruthValue,
    cfprApAdaptorMenloFcErrorStatsHistThresholded                    CfprApAdaptorMenloFcErrorStatsHistThresholded,
    cfprApAdaptorMenloFcErrorStatsHistTimeCollected                  DateAndTime,
    cfprApAdaptorMenloFcErrorStatsHistUncorrectableErrors            Unsigned64,
    cfprApAdaptorMenloFcErrorStatsHistUncorrectableErrorsDelta       Unsigned64,
    cfprApAdaptorMenloFcErrorStatsHistUncorrectableErrorsDeltaAvg    Unsigned64,
    cfprApAdaptorMenloFcErrorStatsHistUncorrectableErrorsDeltaMax    Unsigned64,
    cfprApAdaptorMenloFcErrorStatsHistUncorrectableErrorsDeltaMin    Unsigned64
}

cfprApAdaptorMenloFcErrorStatsHistInstanceId OBJECT-TYPE
    SYNTAX       CfprApManagedObjectId
    MAX-ACCESS   not-accessible
    STATUS       current
    DESCRIPTION
        "Instance identifier of the managed object."
    ::= { cfprApAdaptorMenloFcErrorStatsHistEntry 1 }

cfprApAdaptorMenloFcErrorStatsHistDn OBJECT-TYPE
    SYNTAX       CfprApManagedObjectDn
    MAX-ACCESS   read-only
    STATUS       current
    DESCRIPTION
        "Cisco Firepower adaptor:MenloFcErrorStatsHist:dn
        managed object property"
    ::= { cfprApAdaptorMenloFcErrorStatsHistEntry 2 }

cfprApAdaptorMenloFcErrorStatsHistRn OBJECT-TYPE
    SYNTAX       SnmpAdminString
    MAX-ACCESS   read-only
    STATUS       current
    DESCRIPTION
        "Cisco Firepower adaptor:MenloFcErrorStatsHist:rn
        managed object property"
    ::= { cfprApAdaptorMenloFcErrorStatsHistEntry 3 }

cfprApAdaptorMenloFcErrorStatsHistCorrectableErrors OBJECT-TYPE
    SYNTAX       Unsigned64
    MAX-ACCESS   read-only
    STATUS       current
    DESCRIPTION
        "Cisco Firepower adaptor:MenloFcErrorStatsHist:correctableErrors
        managed object property"
    ::= { cfprApAdaptorMenloFcErrorStatsHistEntry 4 }

cfprApAdaptorMenloFcErrorStatsHistCorrectableErrorsDelta OBJECT-TYPE
    SYNTAX       Unsigned64
    MAX-ACCESS   read-only
    STATUS       current
    DESCRIPTION
        "Cisco Firepower adaptor:MenloFcErrorStatsHist:correctableErrorsDe
        lta managed object property"
    ::= { cfprApAdaptorMenloFcErrorStatsHistEntry 5 }

cfprApAdaptorMenloFcErrorStatsHistCorrectableErrorsDeltaAvg OBJECT-TYPE
    SYNTAX       Unsigned64
    MAX-ACCESS   read-only
    STATUS       current
    DESCRIPTION
        "Cisco Firepower adaptor:MenloFcErrorStatsHist:correctableErrorsDe
        ltaAvg managed object property"
    ::= { cfprApAdaptorMenloFcErrorStatsHistEntry 6 }

cfprApAdaptorMenloFcErrorStatsHistCorrectableErrorsDeltaMax OBJECT-TYPE
    SYNTAX       Unsigned64
    MAX-ACCESS   read-only
    STATUS       current
    DESCRIPTION
        "Cisco Firepower adaptor:MenloFcErrorStatsHist:correctableErrorsDe
        ltaMax managed object property"
    ::= { cfprApAdaptorMenloFcErrorStatsHistEntry 7 }

cfprApAdaptorMenloFcErrorStatsHistCorrectableErrorsDeltaMin OBJECT-TYPE
    SYNTAX       Unsigned64
    MAX-ACCESS   read-only
    STATUS       current
    DESCRIPTION
        "Cisco Firepower adaptor:MenloFcErrorStatsHist:correctableErrorsDe
        ltaMin managed object property"
    ::= { cfprApAdaptorMenloFcErrorStatsHistEntry 8 }

cfprApAdaptorMenloFcErrorStatsHistId OBJECT-TYPE
    SYNTAX       Unsigned64
    MAX-ACCESS   read-only
    STATUS       current
    DESCRIPTION
        "Cisco Firepower adaptor:MenloFcErrorStatsHist:id
        managed object property"
    ::= { cfprApAdaptorMenloFcErrorStatsHistEntry 9 }

cfprApAdaptorMenloFcErrorStatsHistMostRecent OBJECT-TYPE
    SYNTAX       TruthValue
    MAX-ACCESS   read-only
    STATUS       current
    DESCRIPTION
        "Cisco Firepower adaptor:MenloFcErrorStatsHist:mostRecent
        managed object property"
    ::= { cfprApAdaptorMenloFcErrorStatsHistEntry 10 }

cfprApAdaptorMenloFcErrorStatsHistPopErrors OBJECT-TYPE
    SYNTAX       Unsigned64
    MAX-ACCESS   read-only
    STATUS       current
    DESCRIPTION
        "Cisco Firepower adaptor:MenloFcErrorStatsHist:popErrors
        managed object property"
    ::= { cfprApAdaptorMenloFcErrorStatsHistEntry 11 }

cfprApAdaptorMenloFcErrorStatsHistPopErrorsDelta OBJECT-TYPE
    SYNTAX       Unsigned64
    MAX-ACCESS   read-only
    STATUS       current
    DESCRIPTION
        "Cisco Firepower adaptor:MenloFcErrorStatsHist:popErrorsDelta
        managed object property"
    ::= { cfprApAdaptorMenloFcErrorStatsHistEntry 12 }

cfprApAdaptorMenloFcErrorStatsHistPopErrorsDeltaAvg OBJECT-TYPE
    SYNTAX       Unsigned64
    MAX-ACCESS   read-only
    STATUS       current
    DESCRIPTION
        "Cisco Firepower adaptor:MenloFcErrorStatsHist:popErrorsDeltaAvg
        managed object property"
    ::= { cfprApAdaptorMenloFcErrorStatsHistEntry 13 }

cfprApAdaptorMenloFcErrorStatsHistPopErrorsDeltaMax OBJECT-TYPE
    SYNTAX       Unsigned64
    MAX-ACCESS   read-only
    STATUS       current
    DESCRIPTION
        "Cisco Firepower adaptor:MenloFcErrorStatsHist:popErrorsDeltaMax
        managed object property"
    ::= { cfprApAdaptorMenloFcErrorStatsHistEntry 14 }

cfprApAdaptorMenloFcErrorStatsHistPopErrorsDeltaMin OBJECT-TYPE
    SYNTAX       Unsigned64
    MAX-ACCESS   read-only
    STATUS       current
    DESCRIPTION
        "Cisco Firepower adaptor:MenloFcErrorStatsHist:popErrorsDeltaMin
        managed object property"
    ::= { cfprApAdaptorMenloFcErrorStatsHistEntry 15 }

cfprApAdaptorMenloFcErrorStatsHistPushErrors OBJECT-TYPE
    SYNTAX       Unsigned64
    MAX-ACCESS   read-only
    STATUS       current
    DESCRIPTION
        "Cisco Firepower adaptor:MenloFcErrorStatsHist:pushErrors
        managed object property"
    ::= { cfprApAdaptorMenloFcErrorStatsHistEntry 16 }

cfprApAdaptorMenloFcErrorStatsHistPushErrorsDelta OBJECT-TYPE
    SYNTAX       Unsigned64
    MAX-ACCESS   read-only
    STATUS       current
    DESCRIPTION
        "Cisco Firepower adaptor:MenloFcErrorStatsHist:pushErrorsDelta
        managed object property"
    ::= { cfprApAdaptorMenloFcErrorStatsHistEntry 17 }

cfprApAdaptorMenloFcErrorStatsHistPushErrorsDeltaAvg OBJECT-TYPE
    SYNTAX       Unsigned64
    MAX-ACCESS   read-only
    STATUS       current
    DESCRIPTION
        "Cisco Firepower adaptor:MenloFcErrorStatsHist:pushErrorsDeltaAvg
        managed object property"
    ::= { cfprApAdaptorMenloFcErrorStatsHistEntry 18 }

cfprApAdaptorMenloFcErrorStatsHistPushErrorsDeltaMax OBJECT-TYPE
    SYNTAX       Unsigned64
    MAX-ACCESS   read-only
    STATUS       current
    DESCRIPTION
        "Cisco Firepower adaptor:MenloFcErrorStatsHist:pushErrorsDeltaMax
        managed object property"
    ::= { cfprApAdaptorMenloFcErrorStatsHistEntry 19 }

cfprApAdaptorMenloFcErrorStatsHistPushErrorsDeltaMin OBJECT-TYPE
    SYNTAX       Unsigned64
    MAX-ACCESS   read-only
    STATUS       current
    DESCRIPTION
        "Cisco Firepower adaptor:MenloFcErrorStatsHist:pushErrorsDeltaMin
        managed object property"
    ::= { cfprApAdaptorMenloFcErrorStatsHistEntry 20 }

cfprApAdaptorMenloFcErrorStatsHistSuspect OBJECT-TYPE
    SYNTAX       TruthValue
    MAX-ACCESS   read-only
    STATUS       current
    DESCRIPTION
        "Cisco Firepower adaptor:MenloFcErrorStatsHist:suspect
        managed object property"
    ::= { cfprApAdaptorMenloFcErrorStatsHistEntry 21 }

cfprApAdaptorMenloFcErrorStatsHistThresholded OBJECT-TYPE
    SYNTAX       CfprApAdaptorMenloFcErrorStatsHistThresholded
    MAX-ACCESS   read-only
    STATUS       current
    DESCRIPTION
        "Cisco Firepower adaptor:MenloFcErrorStatsHist:thresholded
        managed object property"
    ::= { cfprApAdaptorMenloFcErrorStatsHistEntry 22 }

cfprApAdaptorMenloFcErrorStatsHistTimeCollected OBJECT-TYPE
    SYNTAX       DateAndTime
    MAX-ACCESS   read-only
    STATUS       current
    DESCRIPTION
        "Cisco Firepower adaptor:MenloFcErrorStatsHist:timeCollected
        managed object property"
    ::= { cfprApAdaptorMenloFcErrorStatsHistEntry 23 }

cfprApAdaptorMenloFcErrorStatsHistUncorrectableErrors OBJECT-TYPE
    SYNTAX       Unsigned64
    MAX-ACCESS   read-only
    STATUS       current
    DESCRIPTION
        "Cisco Firepower adaptor:MenloFcErrorStatsHist:uncorrectableErrors
         managed object property"
    ::= { cfprApAdaptorMenloFcErrorStatsHistEntry 24 }

cfprApAdaptorMenloFcErrorStatsHistUncorrectableErrorsDelta OBJECT-TYPE
    SYNTAX       Unsigned64
    MAX-ACCESS   read-only
    STATUS       current
    DESCRIPTION
        "Cisco Firepower adaptor:MenloFcErrorStatsHist:uncorrectableErrors
        Delta managed object property"
    ::= { cfprApAdaptorMenloFcErrorStatsHistEntry 25 }

cfprApAdaptorMenloFcErrorStatsHistUncorrectableErrorsDeltaAvg OBJECT-TYPE
    SYNTAX       Unsigned64
    MAX-ACCESS   read-only
    STATUS       current
    DESCRIPTION
        "Cisco Firepower adaptor:MenloFcErrorStatsHist:uncorrectableErrors
        DeltaAvg managed object property"
    ::= { cfprApAdaptorMenloFcErrorStatsHistEntry 26 }

cfprApAdaptorMenloFcErrorStatsHistUncorrectableErrorsDeltaMax OBJECT-TYPE
    SYNTAX       Unsigned64
    MAX-ACCESS   read-only
    STATUS       current
    DESCRIPTION
        "Cisco Firepower adaptor:MenloFcErrorStatsHist:uncorrectableErrors
        DeltaMax managed object property"
    ::= { cfprApAdaptorMenloFcErrorStatsHistEntry 27 }

cfprApAdaptorMenloFcErrorStatsHistUncorrectableErrorsDeltaMin OBJECT-TYPE
    SYNTAX       Unsigned64
    MAX-ACCESS   read-only
    STATUS       current
    DESCRIPTION
        "Cisco Firepower adaptor:MenloFcErrorStatsHist:uncorrectableErrors
        DeltaMin managed object property"
    ::= { cfprApAdaptorMenloFcErrorStatsHistEntry 28 }

cfprApAdaptorMenloFcStatsTable OBJECT-TYPE
    SYNTAX           SEQUENCE OF CfprApAdaptorMenloFcStatsEntry
    MAX-ACCESS       not-accessible
    STATUS           current
    DESCRIPTION
        "Cisco Firepower adaptor:MenloFcStats managed object table"
    ::= { cfprApAdaptorObjects 92 }

cfprApAdaptorMenloFcStatsEntry OBJECT-TYPE
    SYNTAX           CfprApAdaptorMenloFcStatsEntry
    MAX-ACCESS       not-accessible
    STATUS           current
    DESCRIPTION
        "Entry for the cfprApAdaptorMenloFcStatsTable table."
    INDEX { cfprApAdaptorMenloFcStatsInstanceId }
    ::= { cfprApAdaptorMenloFcStatsTable 1 }

CfprApAdaptorMenloFcStatsEntry ::= SEQUENCE {
    cfprApAdaptorMenloFcStatsInstanceId                              CfprApManagedObjectId,
    cfprApAdaptorMenloFcStatsDn                                      CfprApManagedObjectDn,
    cfprApAdaptorMenloFcStatsRn                                      SnmpAdminString,
    cfprApAdaptorMenloFcStatsDropAcl                                 Unsigned64,
    cfprApAdaptorMenloFcStatsDropAclDelta                            Counter64,
    cfprApAdaptorMenloFcStatsDropAclDeltaAvg                         Unsigned64,
    cfprApAdaptorMenloFcStatsDropAclDeltaMax                         Unsigned64,
    cfprApAdaptorMenloFcStatsDropAclDeltaMin                         Unsigned64,
    cfprApAdaptorMenloFcStatsDropOverrun                             Unsigned64,
    cfprApAdaptorMenloFcStatsDropOverrunDelta                        Counter64,
    cfprApAdaptorMenloFcStatsDropOverrunDeltaAvg                     Unsigned64,
    cfprApAdaptorMenloFcStatsDropOverrunDeltaMax                     Unsigned64,
    cfprApAdaptorMenloFcStatsDropOverrunDeltaMin                     Unsigned64,
    cfprApAdaptorMenloFcStatsDropRunt                                Unsigned64,
    cfprApAdaptorMenloFcStatsDropRuntDelta                           Counter64,
    cfprApAdaptorMenloFcStatsDropRuntDeltaAvg                        Unsigned64,
    cfprApAdaptorMenloFcStatsDropRuntDeltaMax                        Unsigned64,
    cfprApAdaptorMenloFcStatsDropRuntDeltaMin                        Unsigned64,
    cfprApAdaptorMenloFcStatsIntervals                               Gauge32,
    cfprApAdaptorMenloFcStatsMenloFcIndex                            CfprApAdaptorMenloStatsIndex,
    cfprApAdaptorMenloFcStatsSuspect                                 TruthValue,
    cfprApAdaptorMenloFcStatsThresholded                             CfprApAdaptorMenloFcStatsThresholded,
    cfprApAdaptorMenloFcStatsTimeCollected                           DateAndTime,
    cfprApAdaptorMenloFcStatsTruncateOverrun                         Unsigned64,
    cfprApAdaptorMenloFcStatsTruncateOverrunDelta                    Counter64,
    cfprApAdaptorMenloFcStatsTruncateOverrunDeltaAvg                 Unsigned64,
    cfprApAdaptorMenloFcStatsTruncateOverrunDeltaMax                 Unsigned64,
    cfprApAdaptorMenloFcStatsTruncateOverrunDeltaMin                 Unsigned64,
    cfprApAdaptorMenloFcStatsUpdate                                  Gauge32
}

cfprApAdaptorMenloFcStatsInstanceId OBJECT-TYPE
    SYNTAX       CfprApManagedObjectId
    MAX-ACCESS   not-accessible
    STATUS       current
    DESCRIPTION
        "Instance identifier of the managed object."
    ::= { cfprApAdaptorMenloFcStatsEntry 1 }

cfprApAdaptorMenloFcStatsDn OBJECT-TYPE
    SYNTAX       CfprApManagedObjectDn
    MAX-ACCESS   read-only
    STATUS       current
    DESCRIPTION
        "Cisco Firepower adaptor:MenloFcStats:dn managed object property"
    ::= { cfprApAdaptorMenloFcStatsEntry 2 }

cfprApAdaptorMenloFcStatsRn OBJECT-TYPE
    SYNTAX       SnmpAdminString
    MAX-ACCESS   read-only
    STATUS       current
    DESCRIPTION
        "Cisco Firepower adaptor:MenloFcStats:rn managed object property"
    ::= { cfprApAdaptorMenloFcStatsEntry 3 }

cfprApAdaptorMenloFcStatsDropAcl OBJECT-TYPE
    SYNTAX       Unsigned64
    MAX-ACCESS   read-only
    STATUS       current
    DESCRIPTION
        "Cisco Firepower adaptor:MenloFcStats:dropAcl managed
        object property"
    ::= { cfprApAdaptorMenloFcStatsEntry 4 }

cfprApAdaptorMenloFcStatsDropAclDelta OBJECT-TYPE
    SYNTAX       Counter64
    MAX-ACCESS   read-only
    STATUS       current
    DESCRIPTION
        "Cisco Firepower adaptor:MenloFcStats:dropAclDelta
        managed object property"
    ::= { cfprApAdaptorMenloFcStatsEntry 5 }

cfprApAdaptorMenloFcStatsDropAclDeltaAvg OBJECT-TYPE
    SYNTAX       Unsigned64
    MAX-ACCESS   read-only
    STATUS       current
    DESCRIPTION
        "Cisco Firepower adaptor:MenloFcStats:dropAclDeltaAvg
        managed object property"
    ::= { cfprApAdaptorMenloFcStatsEntry 6 }

cfprApAdaptorMenloFcStatsDropAclDeltaMax OBJECT-TYPE
    SYNTAX       Unsigned64
    MAX-ACCESS   read-only
    STATUS       current
    DESCRIPTION
        "Cisco Firepower adaptor:MenloFcStats:dropAclDeltaMax
        managed object property"
    ::= { cfprApAdaptorMenloFcStatsEntry 7 }

cfprApAdaptorMenloFcStatsDropAclDeltaMin OBJECT-TYPE
    SYNTAX       Unsigned64
    MAX-ACCESS   read-only
    STATUS       current
    DESCRIPTION
        "Cisco Firepower adaptor:MenloFcStats:dropAclDeltaMin
        managed object property"
    ::= { cfprApAdaptorMenloFcStatsEntry 8 }

cfprApAdaptorMenloFcStatsDropOverrun OBJECT-TYPE
    SYNTAX       Unsigned64
    MAX-ACCESS   read-only
    STATUS       current
    DESCRIPTION
        "Cisco Firepower adaptor:MenloFcStats:dropOverrun
        managed object property"
    ::= { cfprApAdaptorMenloFcStatsEntry 9 }

cfprApAdaptorMenloFcStatsDropOverrunDelta OBJECT-TYPE
    SYNTAX       Counter64
    MAX-ACCESS   read-only
    STATUS       current
    DESCRIPTION
        "Cisco Firepower adaptor:MenloFcStats:dropOverrunDelta
        managed object property"
    ::= { cfprApAdaptorMenloFcStatsEntry 10 }

cfprApAdaptorMenloFcStatsDropOverrunDeltaAvg OBJECT-TYPE
    SYNTAX       Unsigned64
    MAX-ACCESS   read-only
    STATUS       current
    DESCRIPTION
        "Cisco Firepower adaptor:MenloFcStats:dropOverrunDeltaAvg
        managed object property"
    ::= { cfprApAdaptorMenloFcStatsEntry 11 }

cfprApAdaptorMenloFcStatsDropOverrunDeltaMax OBJECT-TYPE
    SYNTAX       Unsigned64
    MAX-ACCESS   read-only
    STATUS       current
    DESCRIPTION
        "Cisco Firepower adaptor:MenloFcStats:dropOverrunDeltaMax
        managed object property"
    ::= { cfprApAdaptorMenloFcStatsEntry 12 }

cfprApAdaptorMenloFcStatsDropOverrunDeltaMin OBJECT-TYPE
    SYNTAX       Unsigned64
    MAX-ACCESS   read-only
    STATUS       current
    DESCRIPTION
        "Cisco Firepower adaptor:MenloFcStats:dropOverrunDeltaMin
        managed object property"
    ::= { cfprApAdaptorMenloFcStatsEntry 13 }

cfprApAdaptorMenloFcStatsDropRunt OBJECT-TYPE
    SYNTAX       Unsigned64
    MAX-ACCESS   read-only
    STATUS       current
    DESCRIPTION
        "Cisco Firepower adaptor:MenloFcStats:dropRunt
        managed object property"
    ::= { cfprApAdaptorMenloFcStatsEntry 14 }

cfprApAdaptorMenloFcStatsDropRuntDelta OBJECT-TYPE
    SYNTAX       Counter64
    MAX-ACCESS   read-only
    STATUS       current
    DESCRIPTION
        "Cisco Firepower adaptor:MenloFcStats:dropRuntDelta
        managed object property"
    ::= { cfprApAdaptorMenloFcStatsEntry 15 }

cfprApAdaptorMenloFcStatsDropRuntDeltaAvg OBJECT-TYPE
    SYNTAX       Unsigned64
    MAX-ACCESS   read-only
    STATUS       current
    DESCRIPTION
        "Cisco Firepower adaptor:MenloFcStats:dropRuntDeltaAvg
        managed object property"
    ::= { cfprApAdaptorMenloFcStatsEntry 16 }

cfprApAdaptorMenloFcStatsDropRuntDeltaMax OBJECT-TYPE
    SYNTAX       Unsigned64
    MAX-ACCESS   read-only
    STATUS       current
    DESCRIPTION
        "Cisco Firepower adaptor:MenloFcStats:dropRuntDeltaMax
        managed object property"
    ::= { cfprApAdaptorMenloFcStatsEntry 17 }

cfprApAdaptorMenloFcStatsDropRuntDeltaMin OBJECT-TYPE
    SYNTAX       Unsigned64
    MAX-ACCESS   read-only
    STATUS       current
    DESCRIPTION
        "Cisco Firepower adaptor:MenloFcStats:dropRuntDeltaMin
        managed object property"
    ::= { cfprApAdaptorMenloFcStatsEntry 18 }

cfprApAdaptorMenloFcStatsIntervals OBJECT-TYPE
    SYNTAX       Gauge32
    MAX-ACCESS   read-only
    STATUS       current
    DESCRIPTION
        "Cisco Firepower adaptor:MenloFcStats:intervals
        managed object property"
    ::= { cfprApAdaptorMenloFcStatsEntry 19 }

cfprApAdaptorMenloFcStatsMenloFcIndex OBJECT-TYPE
    SYNTAX       CfprApAdaptorMenloStatsIndex
    MAX-ACCESS   read-only
    STATUS       current
    DESCRIPTION
        "Cisco Firepower adaptor:MenloFcStats:menloFcIndex
        managed object property"
    ::= { cfprApAdaptorMenloFcStatsEntry 20 }

cfprApAdaptorMenloFcStatsSuspect OBJECT-TYPE
    SYNTAX       TruthValue
    MAX-ACCESS   read-only
    STATUS       current
    DESCRIPTION
        "Cisco Firepower adaptor:MenloFcStats:suspect managed
        object property"
    ::= { cfprApAdaptorMenloFcStatsEntry 21 }

cfprApAdaptorMenloFcStatsThresholded OBJECT-TYPE
    SYNTAX       CfprApAdaptorMenloFcStatsThresholded
    MAX-ACCESS   read-only
    STATUS       current
    DESCRIPTION
        "Cisco Firepower adaptor:MenloFcStats:thresholded
        managed object property"
    ::= { cfprApAdaptorMenloFcStatsEntry 22 }

cfprApAdaptorMenloFcStatsTimeCollected OBJECT-TYPE
    SYNTAX       DateAndTime
    MAX-ACCESS   read-only
    STATUS       current
    DESCRIPTION
        "Cisco Firepower adaptor:MenloFcStats:timeCollected
        managed object property"
    ::= { cfprApAdaptorMenloFcStatsEntry 23 }

cfprApAdaptorMenloFcStatsTruncateOverrun OBJECT-TYPE
    SYNTAX       Unsigned64
    MAX-ACCESS   read-only
    STATUS       current
    DESCRIPTION
        "Cisco Firepower adaptor:MenloFcStats:truncateOverrun
        managed object property"
    ::= { cfprApAdaptorMenloFcStatsEntry 24 }

cfprApAdaptorMenloFcStatsTruncateOverrunDelta OBJECT-TYPE
    SYNTAX       Counter64
    MAX-ACCESS   read-only
    STATUS       current
    DESCRIPTION
        "Cisco Firepower adaptor:MenloFcStats:truncateOverrunDelta
        managed object property"
    ::= { cfprApAdaptorMenloFcStatsEntry 25 }

cfprApAdaptorMenloFcStatsTruncateOverrunDeltaAvg OBJECT-TYPE
    SYNTAX       Unsigned64
    MAX-ACCESS   read-only
    STATUS       current
    DESCRIPTION
        "Cisco Firepower adaptor:MenloFcStats:truncateOverrunDeltaAvg
        managed object property"
    ::= { cfprApAdaptorMenloFcStatsEntry 26 }

cfprApAdaptorMenloFcStatsTruncateOverrunDeltaMax OBJECT-TYPE
    SYNTAX       Unsigned64
    MAX-ACCESS   read-only
    STATUS       current
    DESCRIPTION
        "Cisco Firepower adaptor:MenloFcStats:truncateOverrunDeltaMax
        managed object property"
    ::= { cfprApAdaptorMenloFcStatsEntry 27 }

cfprApAdaptorMenloFcStatsTruncateOverrunDeltaMin OBJECT-TYPE
    SYNTAX       Unsigned64
    MAX-ACCESS   read-only
    STATUS       current
    DESCRIPTION
        "Cisco Firepower adaptor:MenloFcStats:truncateOverrunDeltaMin
        managed object property"
    ::= { cfprApAdaptorMenloFcStatsEntry 28 }

cfprApAdaptorMenloFcStatsUpdate OBJECT-TYPE
    SYNTAX       Gauge32
    MAX-ACCESS   read-only
    STATUS       current
    DESCRIPTION
        "Cisco Firepower adaptor:MenloFcStats:update managed
        object property"
    ::= { cfprApAdaptorMenloFcStatsEntry 29 }

cfprApAdaptorMenloFcStatsHistTable OBJECT-TYPE
    SYNTAX           SEQUENCE OF CfprApAdaptorMenloFcStatsHistEntry
    MAX-ACCESS       not-accessible
    STATUS           current
    DESCRIPTION
        "Cisco Firepower adaptor:MenloFcStatsHist managed object table"
    ::= { cfprApAdaptorObjects 93 }

cfprApAdaptorMenloFcStatsHistEntry OBJECT-TYPE
    SYNTAX           CfprApAdaptorMenloFcStatsHistEntry
    MAX-ACCESS       not-accessible
    STATUS           current
    DESCRIPTION
        "Entry for the cfprApAdaptorMenloFcStatsHistTable table."
    INDEX { cfprApAdaptorMenloFcStatsHistInstanceId }
    ::= { cfprApAdaptorMenloFcStatsHistTable 1 }

CfprApAdaptorMenloFcStatsHistEntry ::= SEQUENCE {
    cfprApAdaptorMenloFcStatsHistInstanceId                          CfprApManagedObjectId,
    cfprApAdaptorMenloFcStatsHistDn                                  CfprApManagedObjectDn,
    cfprApAdaptorMenloFcStatsHistRn                                  SnmpAdminString,
    cfprApAdaptorMenloFcStatsHistDropAcl                             Unsigned64,
    cfprApAdaptorMenloFcStatsHistDropAclDelta                        Unsigned64,
    cfprApAdaptorMenloFcStatsHistDropAclDeltaAvg                     Unsigned64,
    cfprApAdaptorMenloFcStatsHistDropAclDeltaMax                     Unsigned64,
    cfprApAdaptorMenloFcStatsHistDropAclDeltaMin                     Unsigned64,
    cfprApAdaptorMenloFcStatsHistDropOverrun                         Unsigned64,
    cfprApAdaptorMenloFcStatsHistDropOverrunDelta                    Unsigned64,
    cfprApAdaptorMenloFcStatsHistDropOverrunDeltaAvg                 Unsigned64,
    cfprApAdaptorMenloFcStatsHistDropOverrunDeltaMax                 Unsigned64,
    cfprApAdaptorMenloFcStatsHistDropOverrunDeltaMin                 Unsigned64,
    cfprApAdaptorMenloFcStatsHistDropRunt                            Unsigned64,
    cfprApAdaptorMenloFcStatsHistDropRuntDelta                       Unsigned64,
    cfprApAdaptorMenloFcStatsHistDropRuntDeltaAvg                    Unsigned64,
    cfprApAdaptorMenloFcStatsHistDropRuntDeltaMax                    Unsigned64,
    cfprApAdaptorMenloFcStatsHistDropRuntDeltaMin                    Unsigned64,
    cfprApAdaptorMenloFcStatsHistId                                  Unsigned64,
    cfprApAdaptorMenloFcStatsHistMostRecent                          TruthValue,
    cfprApAdaptorMenloFcStatsHistSuspect                             TruthValue,
    cfprApAdaptorMenloFcStatsHistThresholded                         CfprApAdaptorMenloFcStatsHistThresholded,
    cfprApAdaptorMenloFcStatsHistTimeCollected                       DateAndTime,
    cfprApAdaptorMenloFcStatsHistTruncateOverrun                     Unsigned64,
    cfprApAdaptorMenloFcStatsHistTruncateOverrunDelta                Unsigned64,
    cfprApAdaptorMenloFcStatsHistTruncateOverrunDeltaAvg             Unsigned64,
    cfprApAdaptorMenloFcStatsHistTruncateOverrunDeltaMax             Unsigned64,
    cfprApAdaptorMenloFcStatsHistTruncateOverrunDeltaMin             Unsigned64
}

cfprApAdaptorMenloFcStatsHistInstanceId OBJECT-TYPE
    SYNTAX       CfprApManagedObjectId
    MAX-ACCESS   not-accessible
    STATUS       current
    DESCRIPTION
        "Instance identifier of the managed object."
    ::= { cfprApAdaptorMenloFcStatsHistEntry 1 }

cfprApAdaptorMenloFcStatsHistDn OBJECT-TYPE
    SYNTAX       CfprApManagedObjectDn
    MAX-ACCESS   read-only
    STATUS       current
    DESCRIPTION
        "Cisco Firepower adaptor:MenloFcStatsHist:dn managed
        object property"
    ::= { cfprApAdaptorMenloFcStatsHistEntry 2 }

cfprApAdaptorMenloFcStatsHistRn OBJECT-TYPE
    SYNTAX       SnmpAdminString
    MAX-ACCESS   read-only
    STATUS       current
    DESCRIPTION
        "Cisco Firepower adaptor:MenloFcStatsHist:rn managed
        object property"
    ::= { cfprApAdaptorMenloFcStatsHistEntry 3 }

cfprApAdaptorMenloFcStatsHistDropAcl OBJECT-TYPE
    SYNTAX       Unsigned64
    MAX-ACCESS   read-only
    STATUS       current
    DESCRIPTION
        "Cisco Firepower adaptor:MenloFcStatsHist:dropAcl
        managed object property"
    ::= { cfprApAdaptorMenloFcStatsHistEntry 4 }

cfprApAdaptorMenloFcStatsHistDropAclDelta OBJECT-TYPE
    SYNTAX       Unsigned64
    MAX-ACCESS   read-only
    STATUS       current
    DESCRIPTION
        "Cisco Firepower adaptor:MenloFcStatsHist:dropAclDelta
        managed object property"
    ::= { cfprApAdaptorMenloFcStatsHistEntry 5 }

cfprApAdaptorMenloFcStatsHistDropAclDeltaAvg OBJECT-TYPE
    SYNTAX       Unsigned64
    MAX-ACCESS   read-only
    STATUS       current
    DESCRIPTION
        "Cisco Firepower adaptor:MenloFcStatsHist:dropAclDeltaAvg
        managed object property"
    ::= { cfprApAdaptorMenloFcStatsHistEntry 6 }

cfprApAdaptorMenloFcStatsHistDropAclDeltaMax OBJECT-TYPE
    SYNTAX       Unsigned64
    MAX-ACCESS   read-only
    STATUS       current
    DESCRIPTION
        "Cisco Firepower adaptor:MenloFcStatsHist:dropAclDeltaMax
        managed object property"
    ::= { cfprApAdaptorMenloFcStatsHistEntry 7 }

cfprApAdaptorMenloFcStatsHistDropAclDeltaMin OBJECT-TYPE
    SYNTAX       Unsigned64
    MAX-ACCESS   read-only
    STATUS       current
    DESCRIPTION
        "Cisco Firepower adaptor:MenloFcStatsHist:dropAclDeltaMin
        managed object property"
    ::= { cfprApAdaptorMenloFcStatsHistEntry 8 }

cfprApAdaptorMenloFcStatsHistDropOverrun OBJECT-TYPE
    SYNTAX       Unsigned64
    MAX-ACCESS   read-only
    STATUS       current
    DESCRIPTION
        "Cisco Firepower adaptor:MenloFcStatsHist:dropOverrun
        managed object property"
    ::= { cfprApAdaptorMenloFcStatsHistEntry 9 }

cfprApAdaptorMenloFcStatsHistDropOverrunDelta OBJECT-TYPE
    SYNTAX       Unsigned64
    MAX-ACCESS   read-only
    STATUS       current
    DESCRIPTION
        "Cisco Firepower adaptor:MenloFcStatsHist:dropOverrunDelta
        managed object property"
    ::= { cfprApAdaptorMenloFcStatsHistEntry 10 }

cfprApAdaptorMenloFcStatsHistDropOverrunDeltaAvg OBJECT-TYPE
    SYNTAX       Unsigned64
    MAX-ACCESS   read-only
    STATUS       current
    DESCRIPTION
        "Cisco Firepower adaptor:MenloFcStatsHist:dropOverrunDeltaAvg
        managed object property"
    ::= { cfprApAdaptorMenloFcStatsHistEntry 11 }

cfprApAdaptorMenloFcStatsHistDropOverrunDeltaMax OBJECT-TYPE
    SYNTAX       Unsigned64
    MAX-ACCESS   read-only
    STATUS       current
    DESCRIPTION
        "Cisco Firepower adaptor:MenloFcStatsHist:dropOverrunDeltaMax
        managed object property"
    ::= { cfprApAdaptorMenloFcStatsHistEntry 12 }

cfprApAdaptorMenloFcStatsHistDropOverrunDeltaMin OBJECT-TYPE
    SYNTAX       Unsigned64
    MAX-ACCESS   read-only
    STATUS       current
    DESCRIPTION
        "Cisco Firepower adaptor:MenloFcStatsHist:dropOverrunDeltaMin
        managed object property"
    ::= { cfprApAdaptorMenloFcStatsHistEntry 13 }

cfprApAdaptorMenloFcStatsHistDropRunt OBJECT-TYPE
    SYNTAX       Unsigned64
    MAX-ACCESS   read-only
    STATUS       current
    DESCRIPTION
        "Cisco Firepower adaptor:MenloFcStatsHist:dropRunt
        managed object property"
    ::= { cfprApAdaptorMenloFcStatsHistEntry 14 }

cfprApAdaptorMenloFcStatsHistDropRuntDelta OBJECT-TYPE
    SYNTAX       Unsigned64
    MAX-ACCESS   read-only
    STATUS       current
    DESCRIPTION
        "Cisco Firepower adaptor:MenloFcStatsHist:dropRuntDelta
        managed object property"
    ::= { cfprApAdaptorMenloFcStatsHistEntry 15 }

cfprApAdaptorMenloFcStatsHistDropRuntDeltaAvg OBJECT-TYPE
    SYNTAX       Unsigned64
    MAX-ACCESS   read-only
    STATUS       current
    DESCRIPTION
        "Cisco Firepower adaptor:MenloFcStatsHist:dropRuntDeltaAvg
        managed object property"
    ::= { cfprApAdaptorMenloFcStatsHistEntry 16 }

cfprApAdaptorMenloFcStatsHistDropRuntDeltaMax OBJECT-TYPE
    SYNTAX       Unsigned64
    MAX-ACCESS   read-only
    STATUS       current
    DESCRIPTION
        "Cisco Firepower adaptor:MenloFcStatsHist:dropRuntDeltaMax
        managed object property"
    ::= { cfprApAdaptorMenloFcStatsHistEntry 17 }

cfprApAdaptorMenloFcStatsHistDropRuntDeltaMin OBJECT-TYPE
    SYNTAX       Unsigned64
    MAX-ACCESS   read-only
    STATUS       current
    DESCRIPTION
        "Cisco Firepower adaptor:MenloFcStatsHist:dropRuntDeltaMin
        managed object property"
    ::= { cfprApAdaptorMenloFcStatsHistEntry 18 }

cfprApAdaptorMenloFcStatsHistId OBJECT-TYPE
    SYNTAX       Unsigned64
    MAX-ACCESS   read-only
    STATUS       current
    DESCRIPTION
        "Cisco Firepower adaptor:MenloFcStatsHist:id managed
        object property"
    ::= { cfprApAdaptorMenloFcStatsHistEntry 19 }

cfprApAdaptorMenloFcStatsHistMostRecent OBJECT-TYPE
    SYNTAX       TruthValue
    MAX-ACCESS   read-only
    STATUS       current
    DESCRIPTION
        "Cisco Firepower adaptor:MenloFcStatsHist:mostRecent
        managed object property"
    ::= { cfprApAdaptorMenloFcStatsHistEntry 20 }

cfprApAdaptorMenloFcStatsHistSuspect OBJECT-TYPE
    SYNTAX       TruthValue
    MAX-ACCESS   read-only
    STATUS       current
    DESCRIPTION
        "Cisco Firepower adaptor:MenloFcStatsHist:suspect
        managed object property"
    ::= { cfprApAdaptorMenloFcStatsHistEntry 21 }

cfprApAdaptorMenloFcStatsHistThresholded OBJECT-TYPE
    SYNTAX       CfprApAdaptorMenloFcStatsHistThresholded
    MAX-ACCESS   read-only
    STATUS       current
    DESCRIPTION
        "Cisco Firepower adaptor:MenloFcStatsHist:thresholded
        managed object property"
    ::= { cfprApAdaptorMenloFcStatsHistEntry 22 }

cfprApAdaptorMenloFcStatsHistTimeCollected OBJECT-TYPE
    SYNTAX       DateAndTime
    MAX-ACCESS   read-only
    STATUS       current
    DESCRIPTION
        "Cisco Firepower adaptor:MenloFcStatsHist:timeCollected
        managed object property"
    ::= { cfprApAdaptorMenloFcStatsHistEntry 23 }

cfprApAdaptorMenloFcStatsHistTruncateOverrun OBJECT-TYPE
    SYNTAX       Unsigned64
    MAX-ACCESS   read-only
    STATUS       current
    DESCRIPTION
        "Cisco Firepower adaptor:MenloFcStatsHist:truncateOverrun
        managed object property"
    ::= { cfprApAdaptorMenloFcStatsHistEntry 24 }

cfprApAdaptorMenloFcStatsHistTruncateOverrunDelta OBJECT-TYPE
    SYNTAX       Unsigned64
    MAX-ACCESS   read-only
    STATUS       current
    DESCRIPTION
        "Cisco Firepower adaptor:MenloFcStatsHist:truncateOverrunDelta
        managed object property"
    ::= { cfprApAdaptorMenloFcStatsHistEntry 25 }

cfprApAdaptorMenloFcStatsHistTruncateOverrunDeltaAvg OBJECT-TYPE
    SYNTAX       Unsigned64
    MAX-ACCESS   read-only
    STATUS       current
    DESCRIPTION
        "Cisco Firepower adaptor:MenloFcStatsHist:truncateOverrunDeltaAvg
        managed object property"
    ::= { cfprApAdaptorMenloFcStatsHistEntry 26 }

cfprApAdaptorMenloFcStatsHistTruncateOverrunDeltaMax OBJECT-TYPE
    SYNTAX       Unsigned64
    MAX-ACCESS   read-only
    STATUS       current
    DESCRIPTION
        "Cisco Firepower adaptor:MenloFcStatsHist:truncateOverrunDeltaMax
        managed object property"
    ::= { cfprApAdaptorMenloFcStatsHistEntry 27 }

cfprApAdaptorMenloFcStatsHistTruncateOverrunDeltaMin OBJECT-TYPE
    SYNTAX       Unsigned64
    MAX-ACCESS   read-only
    STATUS       current
    DESCRIPTION
        "Cisco Firepower adaptor:MenloFcStatsHist:truncateOverrunDeltaMin
        managed object property"
    ::= { cfprApAdaptorMenloFcStatsHistEntry 28 }

cfprApAdaptorMenloHostPortStatsTable OBJECT-TYPE
    SYNTAX           SEQUENCE OF CfprApAdaptorMenloHostPortStatsEntry
    MAX-ACCESS       not-accessible
    STATUS           current
    DESCRIPTION
        "Cisco Firepower adaptor:MenloHostPortStats managed object table"
    ::= { cfprApAdaptorObjects 94 }

cfprApAdaptorMenloHostPortStatsEntry OBJECT-TYPE
    SYNTAX           CfprApAdaptorMenloHostPortStatsEntry
    MAX-ACCESS       not-accessible
    STATUS           current
    DESCRIPTION
        "Entry for the cfprApAdaptorMenloHostPortStatsTable table."
    INDEX { cfprApAdaptorMenloHostPortStatsInstanceId }
    ::= { cfprApAdaptorMenloHostPortStatsTable 1 }

CfprApAdaptorMenloHostPortStatsEntry ::= SEQUENCE {
    cfprApAdaptorMenloHostPortStatsInstanceId                        CfprApManagedObjectId,
    cfprApAdaptorMenloHostPortStatsDn                                CfprApManagedObjectDn,
    cfprApAdaptorMenloHostPortStatsRn                                SnmpAdminString,
    cfprApAdaptorMenloHostPortStatsIntervals                         Gauge32,
    cfprApAdaptorMenloHostPortStatsMenloPortIndex                    CfprApAdaptorMenloStatsIndex,
    cfprApAdaptorMenloHostPortStatsRxPauseCFC                        Unsigned64,
    cfprApAdaptorMenloHostPortStatsRxPauseCFCDelta                   Counter64,
    cfprApAdaptorMenloHostPortStatsRxPauseCFCDeltaAvg                Unsigned64,
    cfprApAdaptorMenloHostPortStatsRxPauseCFCDeltaMax                Unsigned64,
    cfprApAdaptorMenloHostPortStatsRxPauseCFCDeltaMin                Unsigned64,
    cfprApAdaptorMenloHostPortStatsRxPausePFC                        Unsigned64,
    cfprApAdaptorMenloHostPortStatsRxPausePFCDelta                   Counter64,
    cfprApAdaptorMenloHostPortStatsRxPausePFCDeltaAvg                Unsigned64,
    cfprApAdaptorMenloHostPortStatsRxPausePFCDeltaMax                Unsigned64,
    cfprApAdaptorMenloHostPortStatsRxPausePFCDeltaMin                Unsigned64,
    cfprApAdaptorMenloHostPortStatsSuspect                           TruthValue,
    cfprApAdaptorMenloHostPortStatsThresholded                       CfprApAdaptorMenloHostPortStatsThresholded,
    cfprApAdaptorMenloHostPortStatsTimeCollected                     DateAndTime,
    cfprApAdaptorMenloHostPortStatsTxPauseCFC                        Unsigned64,
    cfprApAdaptorMenloHostPortStatsTxPauseCFCDelta                   Counter64,
    cfprApAdaptorMenloHostPortStatsTxPauseCFCDeltaAvg                Unsigned64,
    cfprApAdaptorMenloHostPortStatsTxPauseCFCDeltaMax                Unsigned64,
    cfprApAdaptorMenloHostPortStatsTxPauseCFCDeltaMin                Unsigned64,
    cfprApAdaptorMenloHostPortStatsTxPausePFC                        Unsigned64,
    cfprApAdaptorMenloHostPortStatsTxPausePFCDelta                   Counter64,
    cfprApAdaptorMenloHostPortStatsTxPausePFCDeltaAvg                Unsigned64,
    cfprApAdaptorMenloHostPortStatsTxPausePFCDeltaMax                Unsigned64,
    cfprApAdaptorMenloHostPortStatsTxPausePFCDeltaMin                Unsigned64,
    cfprApAdaptorMenloHostPortStatsUpdate                            Gauge32
}

cfprApAdaptorMenloHostPortStatsInstanceId OBJECT-TYPE
    SYNTAX       CfprApManagedObjectId
    MAX-ACCESS   not-accessible
    STATUS       current
    DESCRIPTION
        "Instance identifier of the managed object."
    ::= { cfprApAdaptorMenloHostPortStatsEntry 1 }

cfprApAdaptorMenloHostPortStatsDn OBJECT-TYPE
    SYNTAX       CfprApManagedObjectDn
    MAX-ACCESS   read-only
    STATUS       current
    DESCRIPTION
        "Cisco Firepower adaptor:MenloHostPortStats:dn
        managed object property"
    ::= { cfprApAdaptorMenloHostPortStatsEntry 2 }

cfprApAdaptorMenloHostPortStatsRn OBJECT-TYPE
    SYNTAX       SnmpAdminString
    MAX-ACCESS   read-only
    STATUS       current
    DESCRIPTION
        "Cisco Firepower adaptor:MenloHostPortStats:rn
        managed object property"
    ::= { cfprApAdaptorMenloHostPortStatsEntry 3 }

cfprApAdaptorMenloHostPortStatsIntervals OBJECT-TYPE
    SYNTAX       Gauge32
    MAX-ACCESS   read-only
    STATUS       current
    DESCRIPTION
        "Cisco Firepower adaptor:MenloHostPortStats:intervals
        managed object property"
    ::= { cfprApAdaptorMenloHostPortStatsEntry 4 }

cfprApAdaptorMenloHostPortStatsMenloPortIndex OBJECT-TYPE
    SYNTAX       CfprApAdaptorMenloStatsIndex
    MAX-ACCESS   read-only
    STATUS       current
    DESCRIPTION
        "Cisco Firepower adaptor:MenloHostPortStats:menloPortIndex
        managed object property"
    ::= { cfprApAdaptorMenloHostPortStatsEntry 5 }

cfprApAdaptorMenloHostPortStatsRxPauseCFC OBJECT-TYPE
    SYNTAX       Unsigned64
    MAX-ACCESS   read-only
    STATUS       current
    DESCRIPTION
        "Cisco Firepower adaptor:MenloHostPortStats:rxPauseCFC
        managed object property"
    ::= { cfprApAdaptorMenloHostPortStatsEntry 6 }

cfprApAdaptorMenloHostPortStatsRxPauseCFCDelta OBJECT-TYPE
    SYNTAX       Counter64
    MAX-ACCESS   read-only
    STATUS       current
    DESCRIPTION
        "Cisco Firepower adaptor:MenloHostPortStats:rxPauseCFCDelta
        managed object property"
    ::= { cfprApAdaptorMenloHostPortStatsEntry 7 }

cfprApAdaptorMenloHostPortStatsRxPauseCFCDeltaAvg OBJECT-TYPE
    SYNTAX       Unsigned64
    MAX-ACCESS   read-only
    STATUS       current
    DESCRIPTION
        "Cisco Firepower adaptor:MenloHostPortStats:rxPauseCFCDeltaAvg
        managed object property"
    ::= { cfprApAdaptorMenloHostPortStatsEntry 8 }

cfprApAdaptorMenloHostPortStatsRxPauseCFCDeltaMax OBJECT-TYPE
    SYNTAX       Unsigned64
    MAX-ACCESS   read-only
    STATUS       current
    DESCRIPTION
        "Cisco Firepower adaptor:MenloHostPortStats:rxPauseCFCDeltaMax
        managed object property"
    ::= { cfprApAdaptorMenloHostPortStatsEntry 9 }

cfprApAdaptorMenloHostPortStatsRxPauseCFCDeltaMin OBJECT-TYPE
    SYNTAX       Unsigned64
    MAX-ACCESS   read-only
    STATUS       current
    DESCRIPTION
        "Cisco Firepower adaptor:MenloHostPortStats:rxPauseCFCDeltaMin
        managed object property"
    ::= { cfprApAdaptorMenloHostPortStatsEntry 10 }

cfprApAdaptorMenloHostPortStatsRxPausePFC OBJECT-TYPE
    SYNTAX       Unsigned64
    MAX-ACCESS   read-only
    STATUS       current
    DESCRIPTION
        "Cisco Firepower adaptor:MenloHostPortStats:rxPausePFC
        managed object property"
    ::= { cfprApAdaptorMenloHostPortStatsEntry 11 }

cfprApAdaptorMenloHostPortStatsRxPausePFCDelta OBJECT-TYPE
    SYNTAX       Counter64
    MAX-ACCESS   read-only
    STATUS       current
    DESCRIPTION
        "Cisco Firepower adaptor:MenloHostPortStats:rxPausePFCDelta
        managed object property"
    ::= { cfprApAdaptorMenloHostPortStatsEntry 12 }

cfprApAdaptorMenloHostPortStatsRxPausePFCDeltaAvg OBJECT-TYPE
    SYNTAX       Unsigned64
    MAX-ACCESS   read-only
    STATUS       current
    DESCRIPTION
        "Cisco Firepower adaptor:MenloHostPortStats:rxPausePFCDeltaAvg
        managed object property"
    ::= { cfprApAdaptorMenloHostPortStatsEntry 13 }

cfprApAdaptorMenloHostPortStatsRxPausePFCDeltaMax OBJECT-TYPE
    SYNTAX       Unsigned64
    MAX-ACCESS   read-only
    STATUS       current
    DESCRIPTION
        "Cisco Firepower adaptor:MenloHostPortStats:rxPausePFCDeltaMax
        managed object property"
    ::= { cfprApAdaptorMenloHostPortStatsEntry 14 }

cfprApAdaptorMenloHostPortStatsRxPausePFCDeltaMin OBJECT-TYPE
    SYNTAX       Unsigned64
    MAX-ACCESS   read-only
    STATUS       current
    DESCRIPTION
        "Cisco Firepower adaptor:MenloHostPortStats:rxPausePFCDeltaMin
        managed object property"
    ::= { cfprApAdaptorMenloHostPortStatsEntry 15 }

cfprApAdaptorMenloHostPortStatsSuspect OBJECT-TYPE
    SYNTAX       TruthValue
    MAX-ACCESS   read-only
    STATUS       current
    DESCRIPTION
        "Cisco Firepower adaptor:MenloHostPortStats:suspect
        managed object property"
    ::= { cfprApAdaptorMenloHostPortStatsEntry 16 }

cfprApAdaptorMenloHostPortStatsThresholded OBJECT-TYPE
    SYNTAX       CfprApAdaptorMenloHostPortStatsThresholded
    MAX-ACCESS   read-only
    STATUS       current
    DESCRIPTION
        "Cisco Firepower adaptor:MenloHostPortStats:thresholded
        managed object property"
    ::= { cfprApAdaptorMenloHostPortStatsEntry 17 }

cfprApAdaptorMenloHostPortStatsTimeCollected OBJECT-TYPE
    SYNTAX       DateAndTime
    MAX-ACCESS   read-only
    STATUS       current
    DESCRIPTION
        "Cisco Firepower adaptor:MenloHostPortStats:timeCollected
        managed object property"
    ::= { cfprApAdaptorMenloHostPortStatsEntry 18 }

cfprApAdaptorMenloHostPortStatsTxPauseCFC OBJECT-TYPE
    SYNTAX       Unsigned64
    MAX-ACCESS   read-only
    STATUS       current
    DESCRIPTION
        "Cisco Firepower adaptor:MenloHostPortStats:txPauseCFC
        managed object property"
    ::= { cfprApAdaptorMenloHostPortStatsEntry 19 }

cfprApAdaptorMenloHostPortStatsTxPauseCFCDelta OBJECT-TYPE
    SYNTAX       Counter64
    MAX-ACCESS   read-only
    STATUS       current
    DESCRIPTION
        "Cisco Firepower adaptor:MenloHostPortStats:txPauseCFCDelta
        managed object property"
    ::= { cfprApAdaptorMenloHostPortStatsEntry 20 }

cfprApAdaptorMenloHostPortStatsTxPauseCFCDeltaAvg OBJECT-TYPE
    SYNTAX       Unsigned64
    MAX-ACCESS   read-only
    STATUS       current
    DESCRIPTION
        "Cisco Firepower adaptor:MenloHostPortStats:txPauseCFCDeltaAvg
        managed object property"
    ::= { cfprApAdaptorMenloHostPortStatsEntry 21 }

cfprApAdaptorMenloHostPortStatsTxPauseCFCDeltaMax OBJECT-TYPE
    SYNTAX       Unsigned64
    MAX-ACCESS   read-only
    STATUS       current
    DESCRIPTION
        "Cisco Firepower adaptor:MenloHostPortStats:txPauseCFCDeltaMax
        managed object property"
    ::= { cfprApAdaptorMenloHostPortStatsEntry 22 }

cfprApAdaptorMenloHostPortStatsTxPauseCFCDeltaMin OBJECT-TYPE
    SYNTAX       Unsigned64
    MAX-ACCESS   read-only
    STATUS       current
    DESCRIPTION
        "Cisco Firepower adaptor:MenloHostPortStats:txPauseCFCDeltaMin
        managed object property"
    ::= { cfprApAdaptorMenloHostPortStatsEntry 23 }

cfprApAdaptorMenloHostPortStatsTxPausePFC OBJECT-TYPE
    SYNTAX       Unsigned64
    MAX-ACCESS   read-only
    STATUS       current
    DESCRIPTION
        "Cisco Firepower adaptor:MenloHostPortStats:txPausePFC
        managed object property"
    ::= { cfprApAdaptorMenloHostPortStatsEntry 24 }

cfprApAdaptorMenloHostPortStatsTxPausePFCDelta OBJECT-TYPE
    SYNTAX       Counter64
    MAX-ACCESS   read-only
    STATUS       current
    DESCRIPTION
        "Cisco Firepower adaptor:MenloHostPortStats:txPausePFCDelta
        managed object property"
    ::= { cfprApAdaptorMenloHostPortStatsEntry 25 }

cfprApAdaptorMenloHostPortStatsTxPausePFCDeltaAvg OBJECT-TYPE
    SYNTAX       Unsigned64
    MAX-ACCESS   read-only
    STATUS       current
    DESCRIPTION
        "Cisco Firepower adaptor:MenloHostPortStats:txPausePFCDeltaAvg
        managed object property"
    ::= { cfprApAdaptorMenloHostPortStatsEntry 26 }

cfprApAdaptorMenloHostPortStatsTxPausePFCDeltaMax OBJECT-TYPE
    SYNTAX       Unsigned64
    MAX-ACCESS   read-only
    STATUS       current
    DESCRIPTION
        "Cisco Firepower adaptor:MenloHostPortStats:txPausePFCDeltaMax
        managed object property"
    ::= { cfprApAdaptorMenloHostPortStatsEntry 27 }

cfprApAdaptorMenloHostPortStatsTxPausePFCDeltaMin OBJECT-TYPE
    SYNTAX       Unsigned64
    MAX-ACCESS   read-only
    STATUS       current
    DESCRIPTION
        "Cisco Firepower adaptor:MenloHostPortStats:txPausePFCDeltaMin
        managed object property"
    ::= { cfprApAdaptorMenloHostPortStatsEntry 28 }

cfprApAdaptorMenloHostPortStatsUpdate OBJECT-TYPE
    SYNTAX       Gauge32
    MAX-ACCESS   read-only
    STATUS       current
    DESCRIPTION
        "Cisco Firepower adaptor:MenloHostPortStats:update
        managed object property"
    ::= { cfprApAdaptorMenloHostPortStatsEntry 29 }

cfprApAdaptorMenloHostPortStatsHistTable OBJECT-TYPE
    SYNTAX           SEQUENCE OF CfprApAdaptorMenloHostPortStatsHistEntry
    MAX-ACCESS       not-accessible
    STATUS           current
    DESCRIPTION
        "Cisco Firepower adaptor:MenloHostPortStatsHist
        managed object table"
    ::= { cfprApAdaptorObjects 95 }

cfprApAdaptorMenloHostPortStatsHistEntry OBJECT-TYPE
    SYNTAX           CfprApAdaptorMenloHostPortStatsHistEntry
    MAX-ACCESS       not-accessible
    STATUS           current
    DESCRIPTION
        "Entry for the cfprApAdaptorMenloHostPortStatsHistTable table."
    INDEX { cfprApAdaptorMenloHostPortStatsHistInstanceId }
    ::= { cfprApAdaptorMenloHostPortStatsHistTable 1 }

CfprApAdaptorMenloHostPortStatsHistEntry ::= SEQUENCE {
    cfprApAdaptorMenloHostPortStatsHistInstanceId                    CfprApManagedObjectId,
    cfprApAdaptorMenloHostPortStatsHistDn                            CfprApManagedObjectDn,
    cfprApAdaptorMenloHostPortStatsHistRn                            SnmpAdminString,
    cfprApAdaptorMenloHostPortStatsHistId                            Unsigned64,
    cfprApAdaptorMenloHostPortStatsHistMostRecent                    TruthValue,
    cfprApAdaptorMenloHostPortStatsHistRxPauseCFC                    Unsigned64,
    cfprApAdaptorMenloHostPortStatsHistRxPauseCFCDelta               Unsigned64,
    cfprApAdaptorMenloHostPortStatsHistRxPauseCFCDeltaAvg            Unsigned64,
    cfprApAdaptorMenloHostPortStatsHistRxPauseCFCDeltaMax            Unsigned64,
    cfprApAdaptorMenloHostPortStatsHistRxPauseCFCDeltaMin            Unsigned64,
    cfprApAdaptorMenloHostPortStatsHistRxPausePFC                    Unsigned64,
    cfprApAdaptorMenloHostPortStatsHistRxPausePFCDelta               Unsigned64,
    cfprApAdaptorMenloHostPortStatsHistRxPausePFCDeltaAvg            Unsigned64,
    cfprApAdaptorMenloHostPortStatsHistRxPausePFCDeltaMax            Unsigned64,
    cfprApAdaptorMenloHostPortStatsHistRxPausePFCDeltaMin            Unsigned64,
    cfprApAdaptorMenloHostPortStatsHistSuspect                       TruthValue,
    cfprApAdaptorMenloHostPortStatsHistThresholded                   CfprApAdaptorMenloHostPortStatsHistThresholded,
    cfprApAdaptorMenloHostPortStatsHistTimeCollected                 DateAndTime,
    cfprApAdaptorMenloHostPortStatsHistTxPauseCFC                    Unsigned64,
    cfprApAdaptorMenloHostPortStatsHistTxPauseCFCDelta               Unsigned64,
    cfprApAdaptorMenloHostPortStatsHistTxPauseCFCDeltaAvg            Unsigned64,
    cfprApAdaptorMenloHostPortStatsHistTxPauseCFCDeltaMax            Unsigned64,
    cfprApAdaptorMenloHostPortStatsHistTxPauseCFCDeltaMin            Unsigned64,
    cfprApAdaptorMenloHostPortStatsHistTxPausePFC                    Unsigned64,
    cfprApAdaptorMenloHostPortStatsHistTxPausePFCDelta               Unsigned64,
    cfprApAdaptorMenloHostPortStatsHistTxPausePFCDeltaAvg            Unsigned64,
    cfprApAdaptorMenloHostPortStatsHistTxPausePFCDeltaMax            Unsigned64,
    cfprApAdaptorMenloHostPortStatsHistTxPausePFCDeltaMin            Unsigned64
}

cfprApAdaptorMenloHostPortStatsHistInstanceId OBJECT-TYPE
    SYNTAX       CfprApManagedObjectId
    MAX-ACCESS   not-accessible
    STATUS       current
    DESCRIPTION
        "Instance identifier of the managed object."
    ::= { cfprApAdaptorMenloHostPortStatsHistEntry 1 }

cfprApAdaptorMenloHostPortStatsHistDn OBJECT-TYPE
    SYNTAX       CfprApManagedObjectDn
    MAX-ACCESS   read-only
    STATUS       current
    DESCRIPTION
        "Cisco Firepower adaptor:MenloHostPortStatsHist:dn
        managed object property"
    ::= { cfprApAdaptorMenloHostPortStatsHistEntry 2 }

cfprApAdaptorMenloHostPortStatsHistRn OBJECT-TYPE
    SYNTAX       SnmpAdminString
    MAX-ACCESS   read-only
    STATUS       current
    DESCRIPTION
        "Cisco Firepower adaptor:MenloHostPortStatsHist:rn
        managed object property"
    ::= { cfprApAdaptorMenloHostPortStatsHistEntry 3 }

cfprApAdaptorMenloHostPortStatsHistId OBJECT-TYPE
    SYNTAX       Unsigned64
    MAX-ACCESS   read-only
    STATUS       current
    DESCRIPTION
        "Cisco Firepower adaptor:MenloHostPortStatsHist:id
        managed object property"
    ::= { cfprApAdaptorMenloHostPortStatsHistEntry 4 }

cfprApAdaptorMenloHostPortStatsHistMostRecent OBJECT-TYPE
    SYNTAX       TruthValue
    MAX-ACCESS   read-only
    STATUS       current
    DESCRIPTION
        "Cisco Firepower adaptor:MenloHostPortStatsHist:mostRecent
        managed object property"
    ::= { cfprApAdaptorMenloHostPortStatsHistEntry 5 }

cfprApAdaptorMenloHostPortStatsHistRxPauseCFC OBJECT-TYPE
    SYNTAX       Unsigned64
    MAX-ACCESS   read-only
    STATUS       current
    DESCRIPTION
        "Cisco Firepower adaptor:MenloHostPortStatsHist:rxPauseCFC
        managed object property"
    ::= { cfprApAdaptorMenloHostPortStatsHistEntry 6 }

cfprApAdaptorMenloHostPortStatsHistRxPauseCFCDelta OBJECT-TYPE
    SYNTAX       Unsigned64
    MAX-ACCESS   read-only
    STATUS       current
    DESCRIPTION
        "Cisco Firepower adaptor:MenloHostPortStatsHist:rxPauseCFCDelta
        managed object property"
    ::= { cfprApAdaptorMenloHostPortStatsHistEntry 7 }

cfprApAdaptorMenloHostPortStatsHistRxPauseCFCDeltaAvg OBJECT-TYPE
    SYNTAX       Unsigned64
    MAX-ACCESS   read-only
    STATUS       current
    DESCRIPTION
        "Cisco Firepower adaptor:MenloHostPortStatsHist:rxPauseCFCDeltaAvg
         managed object property"
    ::= { cfprApAdaptorMenloHostPortStatsHistEntry 8 }

cfprApAdaptorMenloHostPortStatsHistRxPauseCFCDeltaMax OBJECT-TYPE
    SYNTAX       Unsigned64
    MAX-ACCESS   read-only
    STATUS       current
    DESCRIPTION
        "Cisco Firepower adaptor:MenloHostPortStatsHist:rxPauseCFCDeltaMax
         managed object property"
    ::= { cfprApAdaptorMenloHostPortStatsHistEntry 9 }

cfprApAdaptorMenloHostPortStatsHistRxPauseCFCDeltaMin OBJECT-TYPE
    SYNTAX       Unsigned64
    MAX-ACCESS   read-only
    STATUS       current
    DESCRIPTION
        "Cisco Firepower adaptor:MenloHostPortStatsHist:rxPauseCFCDeltaMin
         managed object property"
    ::= { cfprApAdaptorMenloHostPortStatsHistEntry 10 }

cfprApAdaptorMenloHostPortStatsHistRxPausePFC OBJECT-TYPE
    SYNTAX       Unsigned64
    MAX-ACCESS   read-only
    STATUS       current
    DESCRIPTION
        "Cisco Firepower adaptor:MenloHostPortStatsHist:rxPausePFC
        managed object property"
    ::= { cfprApAdaptorMenloHostPortStatsHistEntry 11 }

cfprApAdaptorMenloHostPortStatsHistRxPausePFCDelta OBJECT-TYPE
    SYNTAX       Unsigned64
    MAX-ACCESS   read-only
    STATUS       current
    DESCRIPTION
        "Cisco Firepower adaptor:MenloHostPortStatsHist:rxPausePFCDelta
        managed object property"
    ::= { cfprApAdaptorMenloHostPortStatsHistEntry 12 }

cfprApAdaptorMenloHostPortStatsHistRxPausePFCDeltaAvg OBJECT-TYPE
    SYNTAX       Unsigned64
    MAX-ACCESS   read-only
    STATUS       current
    DESCRIPTION
        "Cisco Firepower adaptor:MenloHostPortStatsHist:rxPausePFCDeltaAvg
         managed object property"
    ::= { cfprApAdaptorMenloHostPortStatsHistEntry 13 }

cfprApAdaptorMenloHostPortStatsHistRxPausePFCDeltaMax OBJECT-TYPE
    SYNTAX       Unsigned64
    MAX-ACCESS   read-only
    STATUS       current
    DESCRIPTION
        "Cisco Firepower adaptor:MenloHostPortStatsHist:rxPausePFCDeltaMax
         managed object property"
    ::= { cfprApAdaptorMenloHostPortStatsHistEntry 14 }

cfprApAdaptorMenloHostPortStatsHistRxPausePFCDeltaMin OBJECT-TYPE
    SYNTAX       Unsigned64
    MAX-ACCESS   read-only
    STATUS       current
    DESCRIPTION
        "Cisco Firepower adaptor:MenloHostPortStatsHist:rxPausePFCDeltaMin
         managed object property"
    ::= { cfprApAdaptorMenloHostPortStatsHistEntry 15 }

cfprApAdaptorMenloHostPortStatsHistSuspect OBJECT-TYPE
    SYNTAX       TruthValue
    MAX-ACCESS   read-only
    STATUS       current
    DESCRIPTION
        "Cisco Firepower adaptor:MenloHostPortStatsHist:suspect
        managed object property"
    ::= { cfprApAdaptorMenloHostPortStatsHistEntry 16 }

cfprApAdaptorMenloHostPortStatsHistThresholded OBJECT-TYPE
    SYNTAX       CfprApAdaptorMenloHostPortStatsHistThresholded
    MAX-ACCESS   read-only
    STATUS       current
    DESCRIPTION
        "Cisco Firepower adaptor:MenloHostPortStatsHist:thresholded
        managed object property"
    ::= { cfprApAdaptorMenloHostPortStatsHistEntry 17 }

cfprApAdaptorMenloHostPortStatsHistTimeCollected OBJECT-TYPE
    SYNTAX       DateAndTime
    MAX-ACCESS   read-only
    STATUS       current
    DESCRIPTION
        "Cisco Firepower adaptor:MenloHostPortStatsHist:timeCollected
        managed object property"
    ::= { cfprApAdaptorMenloHostPortStatsHistEntry 18 }

cfprApAdaptorMenloHostPortStatsHistTxPauseCFC OBJECT-TYPE
    SYNTAX       Unsigned64
    MAX-ACCESS   read-only
    STATUS       current
    DESCRIPTION
        "Cisco Firepower adaptor:MenloHostPortStatsHist:txPauseCFC
        managed object property"
    ::= { cfprApAdaptorMenloHostPortStatsHistEntry 19 }

cfprApAdaptorMenloHostPortStatsHistTxPauseCFCDelta OBJECT-TYPE
    SYNTAX       Unsigned64
    MAX-ACCESS   read-only
    STATUS       current
    DESCRIPTION
        "Cisco Firepower adaptor:MenloHostPortStatsHist:txPauseCFCDelta
        managed object property"
    ::= { cfprApAdaptorMenloHostPortStatsHistEntry 20 }

cfprApAdaptorMenloHostPortStatsHistTxPauseCFCDeltaAvg OBJECT-TYPE
    SYNTAX       Unsigned64
    MAX-ACCESS   read-only
    STATUS       current
    DESCRIPTION
        "Cisco Firepower adaptor:MenloHostPortStatsHist:txPauseCFCDeltaAvg
         managed object property"
    ::= { cfprApAdaptorMenloHostPortStatsHistEntry 21 }

cfprApAdaptorMenloHostPortStatsHistTxPauseCFCDeltaMax OBJECT-TYPE
    SYNTAX       Unsigned64
    MAX-ACCESS   read-only
    STATUS       current
    DESCRIPTION
        "Cisco Firepower adaptor:MenloHostPortStatsHist:txPauseCFCDeltaMax
         managed object property"
    ::= { cfprApAdaptorMenloHostPortStatsHistEntry 22 }

cfprApAdaptorMenloHostPortStatsHistTxPauseCFCDeltaMin OBJECT-TYPE
    SYNTAX       Unsigned64
    MAX-ACCESS   read-only
    STATUS       current
    DESCRIPTION
        "Cisco Firepower adaptor:MenloHostPortStatsHist:txPauseCFCDeltaMin
         managed object property"
    ::= { cfprApAdaptorMenloHostPortStatsHistEntry 23 }

cfprApAdaptorMenloHostPortStatsHistTxPausePFC OBJECT-TYPE
    SYNTAX       Unsigned64
    MAX-ACCESS   read-only
    STATUS       current
    DESCRIPTION
        "Cisco Firepower adaptor:MenloHostPortStatsHist:txPausePFC
        managed object property"
    ::= { cfprApAdaptorMenloHostPortStatsHistEntry 24 }

cfprApAdaptorMenloHostPortStatsHistTxPausePFCDelta OBJECT-TYPE
    SYNTAX       Unsigned64
    MAX-ACCESS   read-only
    STATUS       current
    DESCRIPTION
        "Cisco Firepower adaptor:MenloHostPortStatsHist:txPausePFCDelta
        managed object property"
    ::= { cfprApAdaptorMenloHostPortStatsHistEntry 25 }

cfprApAdaptorMenloHostPortStatsHistTxPausePFCDeltaAvg OBJECT-TYPE
    SYNTAX       Unsigned64
    MAX-ACCESS   read-only
    STATUS       current
    DESCRIPTION
        "Cisco Firepower adaptor:MenloHostPortStatsHist:txPausePFCDeltaAvg
         managed object property"
    ::= { cfprApAdaptorMenloHostPortStatsHistEntry 26 }

cfprApAdaptorMenloHostPortStatsHistTxPausePFCDeltaMax OBJECT-TYPE
    SYNTAX       Unsigned64
    MAX-ACCESS   read-only
    STATUS       current
    DESCRIPTION
        "Cisco Firepower adaptor:MenloHostPortStatsHist:txPausePFCDeltaMax
         managed object property"
    ::= { cfprApAdaptorMenloHostPortStatsHistEntry 27 }

cfprApAdaptorMenloHostPortStatsHistTxPausePFCDeltaMin OBJECT-TYPE
    SYNTAX       Unsigned64
    MAX-ACCESS   read-only
    STATUS       current
    DESCRIPTION
        "Cisco Firepower adaptor:MenloHostPortStatsHist:txPausePFCDeltaMin
         managed object property"
    ::= { cfprApAdaptorMenloHostPortStatsHistEntry 28 }

cfprApAdaptorMenloMcpuErrorStatsTable OBJECT-TYPE
    SYNTAX           SEQUENCE OF CfprApAdaptorMenloMcpuErrorStatsEntry
    MAX-ACCESS       not-accessible
    STATUS           current
    DESCRIPTION
        "Cisco Firepower adaptor:MenloMcpuErrorStats managed object table"
    ::= { cfprApAdaptorObjects 96 }

cfprApAdaptorMenloMcpuErrorStatsEntry OBJECT-TYPE
    SYNTAX           CfprApAdaptorMenloMcpuErrorStatsEntry
    MAX-ACCESS       not-accessible
    STATUS           current
    DESCRIPTION
        "Entry for the cfprApAdaptorMenloMcpuErrorStatsTable table."
    INDEX { cfprApAdaptorMenloMcpuErrorStatsInstanceId }
    ::= { cfprApAdaptorMenloMcpuErrorStatsTable 1 }

CfprApAdaptorMenloMcpuErrorStatsEntry ::= SEQUENCE {
    cfprApAdaptorMenloMcpuErrorStatsInstanceId                       CfprApManagedObjectId,
    cfprApAdaptorMenloMcpuErrorStatsDn                               CfprApManagedObjectDn,
    cfprApAdaptorMenloMcpuErrorStatsRn                               SnmpAdminString,
    cfprApAdaptorMenloMcpuErrorStatsCorrectableErrors                Unsigned64,
    cfprApAdaptorMenloMcpuErrorStatsCorrectableErrorsDelta           Counter64,
    cfprApAdaptorMenloMcpuErrorStatsCorrectableErrorsDeltaAvg        Unsigned64,
    cfprApAdaptorMenloMcpuErrorStatsCorrectableErrorsDeltaMax        Unsigned64,
    cfprApAdaptorMenloMcpuErrorStatsCorrectableErrorsDeltaMin        Unsigned64,
    cfprApAdaptorMenloMcpuErrorStatsIntervals                        Gauge32,
    cfprApAdaptorMenloMcpuErrorStatsMenloMcpuIndex                   CfprApAdaptorMenloStatsIndex,
    cfprApAdaptorMenloMcpuErrorStatsPopErrors                        Unsigned64,
    cfprApAdaptorMenloMcpuErrorStatsPopErrorsDelta                   Counter64,
    cfprApAdaptorMenloMcpuErrorStatsPopErrorsDeltaAvg                Unsigned64,
    cfprApAdaptorMenloMcpuErrorStatsPopErrorsDeltaMax                Unsigned64,
    cfprApAdaptorMenloMcpuErrorStatsPopErrorsDeltaMin                Unsigned64,
    cfprApAdaptorMenloMcpuErrorStatsPushErrors                       Unsigned64,
    cfprApAdaptorMenloMcpuErrorStatsPushErrorsDelta                  Counter64,
    cfprApAdaptorMenloMcpuErrorStatsPushErrorsDeltaAvg               Unsigned64,
    cfprApAdaptorMenloMcpuErrorStatsPushErrorsDeltaMax               Unsigned64,
    cfprApAdaptorMenloMcpuErrorStatsPushErrorsDeltaMin               Unsigned64,
    cfprApAdaptorMenloMcpuErrorStatsSuspect                          TruthValue,
    cfprApAdaptorMenloMcpuErrorStatsThresholded                      CfprApAdaptorMenloMcpuErrorStatsThresholded,
    cfprApAdaptorMenloMcpuErrorStatsTimeCollected                    DateAndTime,
    cfprApAdaptorMenloMcpuErrorStatsUncorrectableErrors              Unsigned64,
    cfprApAdaptorMenloMcpuErrorStatsUncorrectableErrorsDelta         Counter64,
    cfprApAdaptorMenloMcpuErrorStatsUncorrectableErrorsDeltaAvg      Unsigned64,
    cfprApAdaptorMenloMcpuErrorStatsUncorrectableErrorsDeltaMax      Unsigned64,
    cfprApAdaptorMenloMcpuErrorStatsUncorrectableErrorsDeltaMin      Unsigned64,
    cfprApAdaptorMenloMcpuErrorStatsUpdate                           Gauge32
}

cfprApAdaptorMenloMcpuErrorStatsInstanceId OBJECT-TYPE
    SYNTAX       CfprApManagedObjectId
    MAX-ACCESS   not-accessible
    STATUS       current
    DESCRIPTION
        "Instance identifier of the managed object."
    ::= { cfprApAdaptorMenloMcpuErrorStatsEntry 1 }

cfprApAdaptorMenloMcpuErrorStatsDn OBJECT-TYPE
    SYNTAX       CfprApManagedObjectDn
    MAX-ACCESS   read-only
    STATUS       current
    DESCRIPTION
        "Cisco Firepower adaptor:MenloMcpuErrorStats:dn
        managed object property"
    ::= { cfprApAdaptorMenloMcpuErrorStatsEntry 2 }

cfprApAdaptorMenloMcpuErrorStatsRn OBJECT-TYPE
    SYNTAX       SnmpAdminString
    MAX-ACCESS   read-only
    STATUS       current
    DESCRIPTION
        "Cisco Firepower adaptor:MenloMcpuErrorStats:rn
        managed object property"
    ::= { cfprApAdaptorMenloMcpuErrorStatsEntry 3 }

cfprApAdaptorMenloMcpuErrorStatsCorrectableErrors OBJECT-TYPE
    SYNTAX       Unsigned64
    MAX-ACCESS   read-only
    STATUS       current
    DESCRIPTION
        "Cisco Firepower adaptor:MenloMcpuErrorStats:correctableErrors
        managed object property"
    ::= { cfprApAdaptorMenloMcpuErrorStatsEntry 4 }

cfprApAdaptorMenloMcpuErrorStatsCorrectableErrorsDelta OBJECT-TYPE
    SYNTAX       Counter64
    MAX-ACCESS   read-only
    STATUS       current
    DESCRIPTION
        "Cisco Firepower adaptor:MenloMcpuErrorStats:correctableErrorsDelt
        a managed object property"
    ::= { cfprApAdaptorMenloMcpuErrorStatsEntry 5 }

cfprApAdaptorMenloMcpuErrorStatsCorrectableErrorsDeltaAvg OBJECT-TYPE
    SYNTAX       Unsigned64
    MAX-ACCESS   read-only
    STATUS       current
    DESCRIPTION
        "Cisco Firepower adaptor:MenloMcpuErrorStats:correctableErrorsDelt
        aAvg managed object property"
    ::= { cfprApAdaptorMenloMcpuErrorStatsEntry 6 }

cfprApAdaptorMenloMcpuErrorStatsCorrectableErrorsDeltaMax OBJECT-TYPE
    SYNTAX       Unsigned64
    MAX-ACCESS   read-only
    STATUS       current
    DESCRIPTION
        "Cisco Firepower adaptor:MenloMcpuErrorStats:correctableErrorsDelt
        aMax managed object property"
    ::= { cfprApAdaptorMenloMcpuErrorStatsEntry 7 }

cfprApAdaptorMenloMcpuErrorStatsCorrectableErrorsDeltaMin OBJECT-TYPE
    SYNTAX       Unsigned64
    MAX-ACCESS   read-only
    STATUS       current
    DESCRIPTION
        "Cisco Firepower adaptor:MenloMcpuErrorStats:correctableErrorsDelt
        aMin managed object property"
    ::= { cfprApAdaptorMenloMcpuErrorStatsEntry 8 }

cfprApAdaptorMenloMcpuErrorStatsIntervals OBJECT-TYPE
    SYNTAX       Gauge32
    MAX-ACCESS   read-only
    STATUS       current
    DESCRIPTION
        "Cisco Firepower adaptor:MenloMcpuErrorStats:intervals
        managed object property"
    ::= { cfprApAdaptorMenloMcpuErrorStatsEntry 9 }

cfprApAdaptorMenloMcpuErrorStatsMenloMcpuIndex OBJECT-TYPE
    SYNTAX       CfprApAdaptorMenloStatsIndex
    MAX-ACCESS   read-only
    STATUS       current
    DESCRIPTION
        "Cisco Firepower adaptor:MenloMcpuErrorStats:menloMcpuIndex
        managed object property"
    ::= { cfprApAdaptorMenloMcpuErrorStatsEntry 10 }

cfprApAdaptorMenloMcpuErrorStatsPopErrors OBJECT-TYPE
    SYNTAX       Unsigned64
    MAX-ACCESS   read-only
    STATUS       current
    DESCRIPTION
        "Cisco Firepower adaptor:MenloMcpuErrorStats:popErrors
        managed object property"
    ::= { cfprApAdaptorMenloMcpuErrorStatsEntry 11 }

cfprApAdaptorMenloMcpuErrorStatsPopErrorsDelta OBJECT-TYPE
    SYNTAX       Counter64
    MAX-ACCESS   read-only
    STATUS       current
    DESCRIPTION
        "Cisco Firepower adaptor:MenloMcpuErrorStats:popErrorsDelta
        managed object property"
    ::= { cfprApAdaptorMenloMcpuErrorStatsEntry 12 }

cfprApAdaptorMenloMcpuErrorStatsPopErrorsDeltaAvg OBJECT-TYPE
    SYNTAX       Unsigned64
    MAX-ACCESS   read-only
    STATUS       current
    DESCRIPTION
        "Cisco Firepower adaptor:MenloMcpuErrorStats:popErrorsDeltaAvg
        managed object property"
    ::= { cfprApAdaptorMenloMcpuErrorStatsEntry 13 }

cfprApAdaptorMenloMcpuErrorStatsPopErrorsDeltaMax OBJECT-TYPE
    SYNTAX       Unsigned64
    MAX-ACCESS   read-only
    STATUS       current
    DESCRIPTION
        "Cisco Firepower adaptor:MenloMcpuErrorStats:popErrorsDeltaMax
        managed object property"
    ::= { cfprApAdaptorMenloMcpuErrorStatsEntry 14 }

cfprApAdaptorMenloMcpuErrorStatsPopErrorsDeltaMin OBJECT-TYPE
    SYNTAX       Unsigned64
    MAX-ACCESS   read-only
    STATUS       current
    DESCRIPTION
        "Cisco Firepower adaptor:MenloMcpuErrorStats:popErrorsDeltaMin
        managed object property"
    ::= { cfprApAdaptorMenloMcpuErrorStatsEntry 15 }

cfprApAdaptorMenloMcpuErrorStatsPushErrors OBJECT-TYPE
    SYNTAX       Unsigned64
    MAX-ACCESS   read-only
    STATUS       current
    DESCRIPTION
        "Cisco Firepower adaptor:MenloMcpuErrorStats:pushErrors
        managed object property"
    ::= { cfprApAdaptorMenloMcpuErrorStatsEntry 16 }

cfprApAdaptorMenloMcpuErrorStatsPushErrorsDelta OBJECT-TYPE
    SYNTAX       Counter64
    MAX-ACCESS   read-only
    STATUS       current
    DESCRIPTION
        "Cisco Firepower adaptor:MenloMcpuErrorStats:pushErrorsDelta
        managed object property"
    ::= { cfprApAdaptorMenloMcpuErrorStatsEntry 17 }

cfprApAdaptorMenloMcpuErrorStatsPushErrorsDeltaAvg OBJECT-TYPE
    SYNTAX       Unsigned64
    MAX-ACCESS   read-only
    STATUS       current
    DESCRIPTION
        "Cisco Firepower adaptor:MenloMcpuErrorStats:pushErrorsDeltaAvg
        managed object property"
    ::= { cfprApAdaptorMenloMcpuErrorStatsEntry 18 }

cfprApAdaptorMenloMcpuErrorStatsPushErrorsDeltaMax OBJECT-TYPE
    SYNTAX       Unsigned64
    MAX-ACCESS   read-only
    STATUS       current
    DESCRIPTION
        "Cisco Firepower adaptor:MenloMcpuErrorStats:pushErrorsDeltaMax
        managed object property"
    ::= { cfprApAdaptorMenloMcpuErrorStatsEntry 19 }

cfprApAdaptorMenloMcpuErrorStatsPushErrorsDeltaMin OBJECT-TYPE
    SYNTAX       Unsigned64
    MAX-ACCESS   read-only
    STATUS       current
    DESCRIPTION
        "Cisco Firepower adaptor:MenloMcpuErrorStats:pushErrorsDeltaMin
        managed object property"
    ::= { cfprApAdaptorMenloMcpuErrorStatsEntry 20 }

cfprApAdaptorMenloMcpuErrorStatsSuspect OBJECT-TYPE
    SYNTAX       TruthValue
    MAX-ACCESS   read-only
    STATUS       current
    DESCRIPTION
        "Cisco Firepower adaptor:MenloMcpuErrorStats:suspect
        managed object property"
    ::= { cfprApAdaptorMenloMcpuErrorStatsEntry 21 }

cfprApAdaptorMenloMcpuErrorStatsThresholded OBJECT-TYPE
    SYNTAX       CfprApAdaptorMenloMcpuErrorStatsThresholded
    MAX-ACCESS   read-only
    STATUS       current
    DESCRIPTION
        "Cisco Firepower adaptor:MenloMcpuErrorStats:thresholded
        managed object property"
    ::= { cfprApAdaptorMenloMcpuErrorStatsEntry 22 }

cfprApAdaptorMenloMcpuErrorStatsTimeCollected OBJECT-TYPE
    SYNTAX       DateAndTime
    MAX-ACCESS   read-only
    STATUS       current
    DESCRIPTION
        "Cisco Firepower adaptor:MenloMcpuErrorStats:timeCollected
        managed object property"
    ::= { cfprApAdaptorMenloMcpuErrorStatsEntry 23 }

cfprApAdaptorMenloMcpuErrorStatsUncorrectableErrors OBJECT-TYPE
    SYNTAX       Unsigned64
    MAX-ACCESS   read-only
    STATUS       current
    DESCRIPTION
        "Cisco Firepower adaptor:MenloMcpuErrorStats:uncorrectableErrors
        managed object property"
    ::= { cfprApAdaptorMenloMcpuErrorStatsEntry 24 }

cfprApAdaptorMenloMcpuErrorStatsUncorrectableErrorsDelta OBJECT-TYPE
    SYNTAX       Counter64
    MAX-ACCESS   read-only
    STATUS       current
    DESCRIPTION
        "Cisco Firepower adaptor:MenloMcpuErrorStats:uncorrectableErrorsDe
        lta managed object property"
    ::= { cfprApAdaptorMenloMcpuErrorStatsEntry 25 }

cfprApAdaptorMenloMcpuErrorStatsUncorrectableErrorsDeltaAvg OBJECT-TYPE
    SYNTAX       Unsigned64
    MAX-ACCESS   read-only
    STATUS       current
    DESCRIPTION
        "Cisco Firepower adaptor:MenloMcpuErrorStats:uncorrectableErrorsDe
        ltaAvg managed object property"
    ::= { cfprApAdaptorMenloMcpuErrorStatsEntry 26 }

cfprApAdaptorMenloMcpuErrorStatsUncorrectableErrorsDeltaMax OBJECT-TYPE
    SYNTAX       Unsigned64
    MAX-ACCESS   read-only
    STATUS       current
    DESCRIPTION
        "Cisco Firepower adaptor:MenloMcpuErrorStats:uncorrectableErrorsDe
        ltaMax managed object property"
    ::= { cfprApAdaptorMenloMcpuErrorStatsEntry 27 }

cfprApAdaptorMenloMcpuErrorStatsUncorrectableErrorsDeltaMin OBJECT-TYPE
    SYNTAX       Unsigned64
    MAX-ACCESS   read-only
    STATUS       current
    DESCRIPTION
        "Cisco Firepower adaptor:MenloMcpuErrorStats:uncorrectableErrorsDe
        ltaMin managed object property"
    ::= { cfprApAdaptorMenloMcpuErrorStatsEntry 28 }

cfprApAdaptorMenloMcpuErrorStatsUpdate OBJECT-TYPE
    SYNTAX       Gauge32
    MAX-ACCESS   read-only
    STATUS       current
    DESCRIPTION
        "Cisco Firepower adaptor:MenloMcpuErrorStats:update
        managed object property"
    ::= { cfprApAdaptorMenloMcpuErrorStatsEntry 29 }

cfprApAdaptorMenloMcpuErrorStatsHistTable OBJECT-TYPE
    SYNTAX           SEQUENCE OF CfprApAdaptorMenloMcpuErrorStatsHistEntry
    MAX-ACCESS       not-accessible
    STATUS           current
    DESCRIPTION
        "Cisco Firepower adaptor:MenloMcpuErrorStatsHist
        managed object table"
    ::= { cfprApAdaptorObjects 97 }

cfprApAdaptorMenloMcpuErrorStatsHistEntry OBJECT-TYPE
    SYNTAX           CfprApAdaptorMenloMcpuErrorStatsHistEntry
    MAX-ACCESS       not-accessible
    STATUS           current
    DESCRIPTION
        "Entry for the cfprApAdaptorMenloMcpuErrorStatsHistTable table."
    INDEX { cfprApAdaptorMenloMcpuErrorStatsHistInstanceId }
    ::= { cfprApAdaptorMenloMcpuErrorStatsHistTable 1 }

CfprApAdaptorMenloMcpuErrorStatsHistEntry ::= SEQUENCE {
    cfprApAdaptorMenloMcpuErrorStatsHistInstanceId                   CfprApManagedObjectId,
    cfprApAdaptorMenloMcpuErrorStatsHistDn                           CfprApManagedObjectDn,
    cfprApAdaptorMenloMcpuErrorStatsHistRn                           SnmpAdminString,
    cfprApAdaptorMenloMcpuErrorStatsHistCorrectableErrors            Unsigned64,
    cfprApAdaptorMenloMcpuErrorStatsHistCorrectableErrorsDelta       Unsigned64,
    cfprApAdaptorMenloMcpuErrorStatsHistCorrectableErrorsDeltaAvg    Unsigned64,
    cfprApAdaptorMenloMcpuErrorStatsHistCorrectableErrorsDeltaMax    Unsigned64,
    cfprApAdaptorMenloMcpuErrorStatsHistCorrectableErrorsDeltaMin    Unsigned64,
    cfprApAdaptorMenloMcpuErrorStatsHistId                           Unsigned64,
    cfprApAdaptorMenloMcpuErrorStatsHistMostRecent                   TruthValue,
    cfprApAdaptorMenloMcpuErrorStatsHistPopErrors                    Unsigned64,
    cfprApAdaptorMenloMcpuErrorStatsHistPopErrorsDelta               Unsigned64,
    cfprApAdaptorMenloMcpuErrorStatsHistPopErrorsDeltaAvg            Unsigned64,
    cfprApAdaptorMenloMcpuErrorStatsHistPopErrorsDeltaMax            Unsigned64,
    cfprApAdaptorMenloMcpuErrorStatsHistPopErrorsDeltaMin            Unsigned64,
    cfprApAdaptorMenloMcpuErrorStatsHistPushErrors                   Unsigned64,
    cfprApAdaptorMenloMcpuErrorStatsHistPushErrorsDelta              Unsigned64,
    cfprApAdaptorMenloMcpuErrorStatsHistPushErrorsDeltaAvg           Unsigned64,
    cfprApAdaptorMenloMcpuErrorStatsHistPushErrorsDeltaMax           Unsigned64,
    cfprApAdaptorMenloMcpuErrorStatsHistPushErrorsDeltaMin           Unsigned64,
    cfprApAdaptorMenloMcpuErrorStatsHistSuspect                      TruthValue,
    cfprApAdaptorMenloMcpuErrorStatsHistThresholded                  CfprApAdaptorMenloMcpuErrorStatsHistThresholded,
    cfprApAdaptorMenloMcpuErrorStatsHistTimeCollected                DateAndTime,
    cfprApAdaptorMenloMcpuErrorStatsHistUncorrectableErrors          Unsigned64,
    cfprApAdaptorMenloMcpuErrorStatsHistUncorrectableErrorsDelta     Unsigned64,
    cfprApAdaptorMenloMcpuErrorStatsHistUncorrectableErrorsDeltaAvg  Unsigned64,
    cfprApAdaptorMenloMcpuErrorStatsHistUncorrectableErrorsDeltaMax  Unsigned64,
    cfprApAdaptorMenloMcpuErrorStatsHistUncorrectableErrorsDeltaMin  Unsigned64
}

cfprApAdaptorMenloMcpuErrorStatsHistInstanceId OBJECT-TYPE
    SYNTAX       CfprApManagedObjectId
    MAX-ACCESS   not-accessible
    STATUS       current
    DESCRIPTION
        "Instance identifier of the managed object."
    ::= { cfprApAdaptorMenloMcpuErrorStatsHistEntry 1 }

cfprApAdaptorMenloMcpuErrorStatsHistDn OBJECT-TYPE
    SYNTAX       CfprApManagedObjectDn
    MAX-ACCESS   read-only
    STATUS       current
    DESCRIPTION
        "Cisco Firepower adaptor:MenloMcpuErrorStatsHist:dn
        managed object property"
    ::= { cfprApAdaptorMenloMcpuErrorStatsHistEntry 2 }

cfprApAdaptorMenloMcpuErrorStatsHistRn OBJECT-TYPE
    SYNTAX       SnmpAdminString
    MAX-ACCESS   read-only
    STATUS       current
    DESCRIPTION
        "Cisco Firepower adaptor:MenloMcpuErrorStatsHist:rn
        managed object property"
    ::= { cfprApAdaptorMenloMcpuErrorStatsHistEntry 3 }

cfprApAdaptorMenloMcpuErrorStatsHistCorrectableErrors OBJECT-TYPE
    SYNTAX       Unsigned64
    MAX-ACCESS   read-only
    STATUS       current
    DESCRIPTION
        "Cisco Firepower adaptor:MenloMcpuErrorStatsHist:correctableErrors
         managed object property"
    ::= { cfprApAdaptorMenloMcpuErrorStatsHistEntry 4 }

cfprApAdaptorMenloMcpuErrorStatsHistCorrectableErrorsDelta OBJECT-TYPE
    SYNTAX       Unsigned64
    MAX-ACCESS   read-only
    STATUS       current
    DESCRIPTION
        "Cisco Firepower adaptor:MenloMcpuErrorStatsHist:correctableErrors
        Delta managed object property"
    ::= { cfprApAdaptorMenloMcpuErrorStatsHistEntry 5 }

cfprApAdaptorMenloMcpuErrorStatsHistCorrectableErrorsDeltaAvg OBJECT-TYPE
    SYNTAX       Unsigned64
    MAX-ACCESS   read-only
    STATUS       current
    DESCRIPTION
        "Cisco Firepower adaptor:MenloMcpuErrorStatsHist:correctableErrors
        DeltaAvg managed object property"
    ::= { cfprApAdaptorMenloMcpuErrorStatsHistEntry 6 }

cfprApAdaptorMenloMcpuErrorStatsHistCorrectableErrorsDeltaMax OBJECT-TYPE
    SYNTAX       Unsigned64
    MAX-ACCESS   read-only
    STATUS       current
    DESCRIPTION
        "Cisco Firepower adaptor:MenloMcpuErrorStatsHist:correctableErrors
        DeltaMax managed object property"
    ::= { cfprApAdaptorMenloMcpuErrorStatsHistEntry 7 }

cfprApAdaptorMenloMcpuErrorStatsHistCorrectableErrorsDeltaMin OBJECT-TYPE
    SYNTAX       Unsigned64
    MAX-ACCESS   read-only
    STATUS       current
    DESCRIPTION
        "Cisco Firepower adaptor:MenloMcpuErrorStatsHist:correctableErrors
        DeltaMin managed object property"
    ::= { cfprApAdaptorMenloMcpuErrorStatsHistEntry 8 }

cfprApAdaptorMenloMcpuErrorStatsHistId OBJECT-TYPE
    SYNTAX       Unsigned64
    MAX-ACCESS   read-only
    STATUS       current
    DESCRIPTION
        "Cisco Firepower adaptor:MenloMcpuErrorStatsHist:id
        managed object property"
    ::= { cfprApAdaptorMenloMcpuErrorStatsHistEntry 9 }

cfprApAdaptorMenloMcpuErrorStatsHistMostRecent OBJECT-TYPE
    SYNTAX       TruthValue
    MAX-ACCESS   read-only
    STATUS       current
    DESCRIPTION
        "Cisco Firepower adaptor:MenloMcpuErrorStatsHist:mostRecent
        managed object property"
    ::= { cfprApAdaptorMenloMcpuErrorStatsHistEntry 10 }

cfprApAdaptorMenloMcpuErrorStatsHistPopErrors OBJECT-TYPE
    SYNTAX       Unsigned64
    MAX-ACCESS   read-only
    STATUS       current
    DESCRIPTION
        "Cisco Firepower adaptor:MenloMcpuErrorStatsHist:popErrors
        managed object property"
    ::= { cfprApAdaptorMenloMcpuErrorStatsHistEntry 11 }

cfprApAdaptorMenloMcpuErrorStatsHistPopErrorsDelta OBJECT-TYPE
    SYNTAX       Unsigned64
    MAX-ACCESS   read-only
    STATUS       current
    DESCRIPTION
        "Cisco Firepower adaptor:MenloMcpuErrorStatsHist:popErrorsDelta
        managed object property"
    ::= { cfprApAdaptorMenloMcpuErrorStatsHistEntry 12 }

cfprApAdaptorMenloMcpuErrorStatsHistPopErrorsDeltaAvg OBJECT-TYPE
    SYNTAX       Unsigned64
    MAX-ACCESS   read-only
    STATUS       current
    DESCRIPTION
        "Cisco Firepower adaptor:MenloMcpuErrorStatsHist:popErrorsDeltaAvg
         managed object property"
    ::= { cfprApAdaptorMenloMcpuErrorStatsHistEntry 13 }

cfprApAdaptorMenloMcpuErrorStatsHistPopErrorsDeltaMax OBJECT-TYPE
    SYNTAX       Unsigned64
    MAX-ACCESS   read-only
    STATUS       current
    DESCRIPTION
        "Cisco Firepower adaptor:MenloMcpuErrorStatsHist:popErrorsDeltaMax
         managed object property"
    ::= { cfprApAdaptorMenloMcpuErrorStatsHistEntry 14 }

cfprApAdaptorMenloMcpuErrorStatsHistPopErrorsDeltaMin OBJECT-TYPE
    SYNTAX       Unsigned64
    MAX-ACCESS   read-only
    STATUS       current
    DESCRIPTION
        "Cisco Firepower adaptor:MenloMcpuErrorStatsHist:popErrorsDeltaMin
         managed object property"
    ::= { cfprApAdaptorMenloMcpuErrorStatsHistEntry 15 }

cfprApAdaptorMenloMcpuErrorStatsHistPushErrors OBJECT-TYPE
    SYNTAX       Unsigned64
    MAX-ACCESS   read-only
    STATUS       current
    DESCRIPTION
        "Cisco Firepower adaptor:MenloMcpuErrorStatsHist:pushErrors
        managed object property"
    ::= { cfprApAdaptorMenloMcpuErrorStatsHistEntry 16 }

cfprApAdaptorMenloMcpuErrorStatsHistPushErrorsDelta OBJECT-TYPE
    SYNTAX       Unsigned64
    MAX-ACCESS   read-only
    STATUS       current
    DESCRIPTION
        "Cisco Firepower adaptor:MenloMcpuErrorStatsHist:pushErrorsDelta
        managed object property"
    ::= { cfprApAdaptorMenloMcpuErrorStatsHistEntry 17 }

cfprApAdaptorMenloMcpuErrorStatsHistPushErrorsDeltaAvg OBJECT-TYPE
    SYNTAX       Unsigned64
    MAX-ACCESS   read-only
    STATUS       current
    DESCRIPTION
        "Cisco Firepower adaptor:MenloMcpuErrorStatsHist:pushErrorsDeltaAv
        g managed object property"
    ::= { cfprApAdaptorMenloMcpuErrorStatsHistEntry 18 }

cfprApAdaptorMenloMcpuErrorStatsHistPushErrorsDeltaMax OBJECT-TYPE
    SYNTAX       Unsigned64
    MAX-ACCESS   read-only
    STATUS       current
    DESCRIPTION
        "Cisco Firepower adaptor:MenloMcpuErrorStatsHist:pushErrorsDeltaMa
        x managed object property"
    ::= { cfprApAdaptorMenloMcpuErrorStatsHistEntry 19 }

cfprApAdaptorMenloMcpuErrorStatsHistPushErrorsDeltaMin OBJECT-TYPE
    SYNTAX       Unsigned64
    MAX-ACCESS   read-only
    STATUS       current
    DESCRIPTION
        "Cisco Firepower adaptor:MenloMcpuErrorStatsHist:pushErrorsDeltaMi
        n managed object property"
    ::= { cfprApAdaptorMenloMcpuErrorStatsHistEntry 20 }

cfprApAdaptorMenloMcpuErrorStatsHistSuspect OBJECT-TYPE
    SYNTAX       TruthValue
    MAX-ACCESS   read-only
    STATUS       current
    DESCRIPTION
        "Cisco Firepower adaptor:MenloMcpuErrorStatsHist:suspect
        managed object property"
    ::= { cfprApAdaptorMenloMcpuErrorStatsHistEntry 21 }

cfprApAdaptorMenloMcpuErrorStatsHistThresholded OBJECT-TYPE
    SYNTAX       CfprApAdaptorMenloMcpuErrorStatsHistThresholded
    MAX-ACCESS   read-only
    STATUS       current
    DESCRIPTION
        "Cisco Firepower adaptor:MenloMcpuErrorStatsHist:thresholded
        managed object property"
    ::= { cfprApAdaptorMenloMcpuErrorStatsHistEntry 22 }

cfprApAdaptorMenloMcpuErrorStatsHistTimeCollected OBJECT-TYPE
    SYNTAX       DateAndTime
    MAX-ACCESS   read-only
    STATUS       current
    DESCRIPTION
        "Cisco Firepower adaptor:MenloMcpuErrorStatsHist:timeCollected
        managed object property"
    ::= { cfprApAdaptorMenloMcpuErrorStatsHistEntry 23 }

cfprApAdaptorMenloMcpuErrorStatsHistUncorrectableErrors OBJECT-TYPE
    SYNTAX       Unsigned64
    MAX-ACCESS   read-only
    STATUS       current
    DESCRIPTION
        "Cisco Firepower adaptor:MenloMcpuErrorStatsHist:uncorrectableErro
        rs managed object property"
    ::= { cfprApAdaptorMenloMcpuErrorStatsHistEntry 24 }

cfprApAdaptorMenloMcpuErrorStatsHistUncorrectableErrorsDelta OBJECT-TYPE
    SYNTAX       Unsigned64
    MAX-ACCESS   read-only
    STATUS       current
    DESCRIPTION
        "Cisco Firepower adaptor:MenloMcpuErrorStatsHist:uncorrectableErro
        rsDelta managed object property"
    ::= { cfprApAdaptorMenloMcpuErrorStatsHistEntry 25 }

cfprApAdaptorMenloMcpuErrorStatsHistUncorrectableErrorsDeltaAvg OBJECT-TYPE
    SYNTAX       Unsigned64
    MAX-ACCESS   read-only
    STATUS       current
    DESCRIPTION
        "Cisco Firepower adaptor:MenloMcpuErrorStatsHist:uncorrectableErro
        rsDeltaAvg managed object property"
    ::= { cfprApAdaptorMenloMcpuErrorStatsHistEntry 26 }

cfprApAdaptorMenloMcpuErrorStatsHistUncorrectableErrorsDeltaMax OBJECT-TYPE
    SYNTAX       Unsigned64
    MAX-ACCESS   read-only
    STATUS       current
    DESCRIPTION
        "Cisco Firepower adaptor:MenloMcpuErrorStatsHist:uncorrectableErro
        rsDeltaMax managed object property"
    ::= { cfprApAdaptorMenloMcpuErrorStatsHistEntry 27 }

cfprApAdaptorMenloMcpuErrorStatsHistUncorrectableErrorsDeltaMin OBJECT-TYPE
    SYNTAX       Unsigned64
    MAX-ACCESS   read-only
    STATUS       current
    DESCRIPTION
        "Cisco Firepower adaptor:MenloMcpuErrorStatsHist:uncorrectableErro
        rsDeltaMin managed object property"
    ::= { cfprApAdaptorMenloMcpuErrorStatsHistEntry 28 }

cfprApAdaptorMenloMcpuStatsTable OBJECT-TYPE
    SYNTAX           SEQUENCE OF CfprApAdaptorMenloMcpuStatsEntry
    MAX-ACCESS       not-accessible
    STATUS           current
    DESCRIPTION
        "Cisco Firepower adaptor:MenloMcpuStats managed object table"
    ::= { cfprApAdaptorObjects 98 }

cfprApAdaptorMenloMcpuStatsEntry OBJECT-TYPE
    SYNTAX           CfprApAdaptorMenloMcpuStatsEntry
    MAX-ACCESS       not-accessible
    STATUS           current
    DESCRIPTION
        "Entry for the cfprApAdaptorMenloMcpuStatsTable table."
    INDEX { cfprApAdaptorMenloMcpuStatsInstanceId }
    ::= { cfprApAdaptorMenloMcpuStatsTable 1 }

CfprApAdaptorMenloMcpuStatsEntry ::= SEQUENCE {
    cfprApAdaptorMenloMcpuStatsInstanceId                            CfprApManagedObjectId,
    cfprApAdaptorMenloMcpuStatsDn                                    CfprApManagedObjectDn,
    cfprApAdaptorMenloMcpuStatsRn                                    SnmpAdminString,
    cfprApAdaptorMenloMcpuStatsDropAcl                               Unsigned64,
    cfprApAdaptorMenloMcpuStatsDropAclDelta                          Counter64,
    cfprApAdaptorMenloMcpuStatsDropAclDeltaAvg                       Unsigned64,
    cfprApAdaptorMenloMcpuStatsDropAclDeltaMax                       Unsigned64,
    cfprApAdaptorMenloMcpuStatsDropAclDeltaMin                       Unsigned64,
    cfprApAdaptorMenloMcpuStatsDropOverrun                           Unsigned64,
    cfprApAdaptorMenloMcpuStatsDropOverrunDelta                      Counter64,
    cfprApAdaptorMenloMcpuStatsDropOverrunDeltaAvg                   Unsigned64,
    cfprApAdaptorMenloMcpuStatsDropOverrunDeltaMax                   Unsigned64,
    cfprApAdaptorMenloMcpuStatsDropOverrunDeltaMin                   Unsigned64,
    cfprApAdaptorMenloMcpuStatsDropRunt                              Unsigned64,
    cfprApAdaptorMenloMcpuStatsDropRuntDelta                         Counter64,
    cfprApAdaptorMenloMcpuStatsDropRuntDeltaAvg                      Unsigned64,
    cfprApAdaptorMenloMcpuStatsDropRuntDeltaMax                      Unsigned64,
    cfprApAdaptorMenloMcpuStatsDropRuntDeltaMin                      Unsigned64,
    cfprApAdaptorMenloMcpuStatsIntervals                             Gauge32,
    cfprApAdaptorMenloMcpuStatsMenloMcpuIndex                        CfprApAdaptorMenloStatsIndex,
    cfprApAdaptorMenloMcpuStatsSuspect                               TruthValue,
    cfprApAdaptorMenloMcpuStatsThresholded                           CfprApAdaptorMenloMcpuStatsThresholded,
    cfprApAdaptorMenloMcpuStatsTimeCollected                         DateAndTime,
    cfprApAdaptorMenloMcpuStatsTruncateOverrun                       Unsigned64,
    cfprApAdaptorMenloMcpuStatsTruncateOverrunDelta                  Counter64,
    cfprApAdaptorMenloMcpuStatsTruncateOverrunDeltaAvg               Unsigned64,
    cfprApAdaptorMenloMcpuStatsTruncateOverrunDeltaMax               Unsigned64,
    cfprApAdaptorMenloMcpuStatsTruncateOverrunDeltaMin               Unsigned64,
    cfprApAdaptorMenloMcpuStatsUpdate                                Gauge32
}

cfprApAdaptorMenloMcpuStatsInstanceId OBJECT-TYPE
    SYNTAX       CfprApManagedObjectId
    MAX-ACCESS   not-accessible
    STATUS       current
    DESCRIPTION
        "Instance identifier of the managed object."
    ::= { cfprApAdaptorMenloMcpuStatsEntry 1 }

cfprApAdaptorMenloMcpuStatsDn OBJECT-TYPE
    SYNTAX       CfprApManagedObjectDn
    MAX-ACCESS   read-only
    STATUS       current
    DESCRIPTION
        "Cisco Firepower adaptor:MenloMcpuStats:dn managed
        object property"
    ::= { cfprApAdaptorMenloMcpuStatsEntry 2 }

cfprApAdaptorMenloMcpuStatsRn OBJECT-TYPE
    SYNTAX       SnmpAdminString
    MAX-ACCESS   read-only
    STATUS       current
    DESCRIPTION
        "Cisco Firepower adaptor:MenloMcpuStats:rn managed
        object property"
    ::= { cfprApAdaptorMenloMcpuStatsEntry 3 }

cfprApAdaptorMenloMcpuStatsDropAcl OBJECT-TYPE
    SYNTAX       Unsigned64
    MAX-ACCESS   read-only
    STATUS       current
    DESCRIPTION
        "Cisco Firepower adaptor:MenloMcpuStats:dropAcl
        managed object property"
    ::= { cfprApAdaptorMenloMcpuStatsEntry 4 }

cfprApAdaptorMenloMcpuStatsDropAclDelta OBJECT-TYPE
    SYNTAX       Counter64
    MAX-ACCESS   read-only
    STATUS       current
    DESCRIPTION
        "Cisco Firepower adaptor:MenloMcpuStats:dropAclDelta
        managed object property"
    ::= { cfprApAdaptorMenloMcpuStatsEntry 5 }

cfprApAdaptorMenloMcpuStatsDropAclDeltaAvg OBJECT-TYPE
    SYNTAX       Unsigned64
    MAX-ACCESS   read-only
    STATUS       current
    DESCRIPTION
        "Cisco Firepower adaptor:MenloMcpuStats:dropAclDeltaAvg
        managed object property"
    ::= { cfprApAdaptorMenloMcpuStatsEntry 6 }

cfprApAdaptorMenloMcpuStatsDropAclDeltaMax OBJECT-TYPE
    SYNTAX       Unsigned64
    MAX-ACCESS   read-only
    STATUS       current
    DESCRIPTION
        "Cisco Firepower adaptor:MenloMcpuStats:dropAclDeltaMax
        managed object property"
    ::= { cfprApAdaptorMenloMcpuStatsEntry 7 }

cfprApAdaptorMenloMcpuStatsDropAclDeltaMin OBJECT-TYPE
    SYNTAX       Unsigned64
    MAX-ACCESS   read-only
    STATUS       current
    DESCRIPTION
        "Cisco Firepower adaptor:MenloMcpuStats:dropAclDeltaMin
        managed object property"
    ::= { cfprApAdaptorMenloMcpuStatsEntry 8 }

cfprApAdaptorMenloMcpuStatsDropOverrun OBJECT-TYPE
    SYNTAX       Unsigned64
    MAX-ACCESS   read-only
    STATUS       current
    DESCRIPTION
        "Cisco Firepower adaptor:MenloMcpuStats:dropOverrun
        managed object property"
    ::= { cfprApAdaptorMenloMcpuStatsEntry 9 }

cfprApAdaptorMenloMcpuStatsDropOverrunDelta OBJECT-TYPE
    SYNTAX       Counter64
    MAX-ACCESS   read-only
    STATUS       current
    DESCRIPTION
        "Cisco Firepower adaptor:MenloMcpuStats:dropOverrunDelta
        managed object property"
    ::= { cfprApAdaptorMenloMcpuStatsEntry 10 }

cfprApAdaptorMenloMcpuStatsDropOverrunDeltaAvg OBJECT-TYPE
    SYNTAX       Unsigned64
    MAX-ACCESS   read-only
    STATUS       current
    DESCRIPTION
        "Cisco Firepower adaptor:MenloMcpuStats:dropOverrunDeltaAvg
        managed object property"
    ::= { cfprApAdaptorMenloMcpuStatsEntry 11 }

cfprApAdaptorMenloMcpuStatsDropOverrunDeltaMax OBJECT-TYPE
    SYNTAX       Unsigned64
    MAX-ACCESS   read-only
    STATUS       current
    DESCRIPTION
        "Cisco Firepower adaptor:MenloMcpuStats:dropOverrunDeltaMax
        managed object property"
    ::= { cfprApAdaptorMenloMcpuStatsEntry 12 }

cfprApAdaptorMenloMcpuStatsDropOverrunDeltaMin OBJECT-TYPE
    SYNTAX       Unsigned64
    MAX-ACCESS   read-only
    STATUS       current
    DESCRIPTION
        "Cisco Firepower adaptor:MenloMcpuStats:dropOverrunDeltaMin
        managed object property"
    ::= { cfprApAdaptorMenloMcpuStatsEntry 13 }

cfprApAdaptorMenloMcpuStatsDropRunt OBJECT-TYPE
    SYNTAX       Unsigned64
    MAX-ACCESS   read-only
    STATUS       current
    DESCRIPTION
        "Cisco Firepower adaptor:MenloMcpuStats:dropRunt
        managed object property"
    ::= { cfprApAdaptorMenloMcpuStatsEntry 14 }

cfprApAdaptorMenloMcpuStatsDropRuntDelta OBJECT-TYPE
    SYNTAX       Counter64
    MAX-ACCESS   read-only
    STATUS       current
    DESCRIPTION
        "Cisco Firepower adaptor:MenloMcpuStats:dropRuntDelta
        managed object property"
    ::= { cfprApAdaptorMenloMcpuStatsEntry 15 }

cfprApAdaptorMenloMcpuStatsDropRuntDeltaAvg OBJECT-TYPE
    SYNTAX       Unsigned64
    MAX-ACCESS   read-only
    STATUS       current
    DESCRIPTION
        "Cisco Firepower adaptor:MenloMcpuStats:dropRuntDeltaAvg
        managed object property"
    ::= { cfprApAdaptorMenloMcpuStatsEntry 16 }

cfprApAdaptorMenloMcpuStatsDropRuntDeltaMax OBJECT-TYPE
    SYNTAX       Unsigned64
    MAX-ACCESS   read-only
    STATUS       current
    DESCRIPTION
        "Cisco Firepower adaptor:MenloMcpuStats:dropRuntDeltaMax
        managed object property"
    ::= { cfprApAdaptorMenloMcpuStatsEntry 17 }

cfprApAdaptorMenloMcpuStatsDropRuntDeltaMin OBJECT-TYPE
    SYNTAX       Unsigned64
    MAX-ACCESS   read-only
    STATUS       current
    DESCRIPTION
        "Cisco Firepower adaptor:MenloMcpuStats:dropRuntDeltaMin
        managed object property"
    ::= { cfprApAdaptorMenloMcpuStatsEntry 18 }

cfprApAdaptorMenloMcpuStatsIntervals OBJECT-TYPE
    SYNTAX       Gauge32
    MAX-ACCESS   read-only
    STATUS       current
    DESCRIPTION
        "Cisco Firepower adaptor:MenloMcpuStats:intervals
        managed object property"
    ::= { cfprApAdaptorMenloMcpuStatsEntry 19 }

cfprApAdaptorMenloMcpuStatsMenloMcpuIndex OBJECT-TYPE
    SYNTAX       CfprApAdaptorMenloStatsIndex
    MAX-ACCESS   read-only
    STATUS       current
    DESCRIPTION
        "Cisco Firepower adaptor:MenloMcpuStats:menloMcpuIndex
        managed object property"
    ::= { cfprApAdaptorMenloMcpuStatsEntry 20 }

cfprApAdaptorMenloMcpuStatsSuspect OBJECT-TYPE
    SYNTAX       TruthValue
    MAX-ACCESS   read-only
    STATUS       current
    DESCRIPTION
        "Cisco Firepower adaptor:MenloMcpuStats:suspect
        managed object property"
    ::= { cfprApAdaptorMenloMcpuStatsEntry 21 }

cfprApAdaptorMenloMcpuStatsThresholded OBJECT-TYPE
    SYNTAX       CfprApAdaptorMenloMcpuStatsThresholded
    MAX-ACCESS   read-only
    STATUS       current
    DESCRIPTION
        "Cisco Firepower adaptor:MenloMcpuStats:thresholded
        managed object property"
    ::= { cfprApAdaptorMenloMcpuStatsEntry 22 }

cfprApAdaptorMenloMcpuStatsTimeCollected OBJECT-TYPE
    SYNTAX       DateAndTime
    MAX-ACCESS   read-only
    STATUS       current
    DESCRIPTION
        "Cisco Firepower adaptor:MenloMcpuStats:timeCollected
        managed object property"
    ::= { cfprApAdaptorMenloMcpuStatsEntry 23 }

cfprApAdaptorMenloMcpuStatsTruncateOverrun OBJECT-TYPE
    SYNTAX       Unsigned64
    MAX-ACCESS   read-only
    STATUS       current
    DESCRIPTION
        "Cisco Firepower adaptor:MenloMcpuStats:truncateOverrun
        managed object property"
    ::= { cfprApAdaptorMenloMcpuStatsEntry 24 }

cfprApAdaptorMenloMcpuStatsTruncateOverrunDelta OBJECT-TYPE
    SYNTAX       Counter64
    MAX-ACCESS   read-only
    STATUS       current
    DESCRIPTION
        "Cisco Firepower adaptor:MenloMcpuStats:truncateOverrunDelta
        managed object property"
    ::= { cfprApAdaptorMenloMcpuStatsEntry 25 }

cfprApAdaptorMenloMcpuStatsTruncateOverrunDeltaAvg OBJECT-TYPE
    SYNTAX       Unsigned64
    MAX-ACCESS   read-only
    STATUS       current
    DESCRIPTION
        "Cisco Firepower adaptor:MenloMcpuStats:truncateOverrunDeltaAvg
        managed object property"
    ::= { cfprApAdaptorMenloMcpuStatsEntry 26 }

cfprApAdaptorMenloMcpuStatsTruncateOverrunDeltaMax OBJECT-TYPE
    SYNTAX       Unsigned64
    MAX-ACCESS   read-only
    STATUS       current
    DESCRIPTION
        "Cisco Firepower adaptor:MenloMcpuStats:truncateOverrunDeltaMax
        managed object property"
    ::= { cfprApAdaptorMenloMcpuStatsEntry 27 }

cfprApAdaptorMenloMcpuStatsTruncateOverrunDeltaMin OBJECT-TYPE
    SYNTAX       Unsigned64
    MAX-ACCESS   read-only
    STATUS       current
    DESCRIPTION
        "Cisco Firepower adaptor:MenloMcpuStats:truncateOverrunDeltaMin
        managed object property"
    ::= { cfprApAdaptorMenloMcpuStatsEntry 28 }

cfprApAdaptorMenloMcpuStatsUpdate OBJECT-TYPE
    SYNTAX       Gauge32
    MAX-ACCESS   read-only
    STATUS       current
    DESCRIPTION
        "Cisco Firepower adaptor:MenloMcpuStats:update
        managed object property"
    ::= { cfprApAdaptorMenloMcpuStatsEntry 29 }

cfprApAdaptorMenloMcpuStatsHistTable OBJECT-TYPE
    SYNTAX           SEQUENCE OF CfprApAdaptorMenloMcpuStatsHistEntry
    MAX-ACCESS       not-accessible
    STATUS           current
    DESCRIPTION
        "Cisco Firepower adaptor:MenloMcpuStatsHist managed object table"
    ::= { cfprApAdaptorObjects 99 }

cfprApAdaptorMenloMcpuStatsHistEntry OBJECT-TYPE
    SYNTAX           CfprApAdaptorMenloMcpuStatsHistEntry
    MAX-ACCESS       not-accessible
    STATUS           current
    DESCRIPTION
        "Entry for the cfprApAdaptorMenloMcpuStatsHistTable table."
    INDEX { cfprApAdaptorMenloMcpuStatsHistInstanceId }
    ::= { cfprApAdaptorMenloMcpuStatsHistTable 1 }

CfprApAdaptorMenloMcpuStatsHistEntry ::= SEQUENCE {
    cfprApAdaptorMenloMcpuStatsHistInstanceId                        CfprApManagedObjectId,
    cfprApAdaptorMenloMcpuStatsHistDn                                CfprApManagedObjectDn,
    cfprApAdaptorMenloMcpuStatsHistRn                                SnmpAdminString,
    cfprApAdaptorMenloMcpuStatsHistDropAcl                           Unsigned64,
    cfprApAdaptorMenloMcpuStatsHistDropAclDelta                      Unsigned64,
    cfprApAdaptorMenloMcpuStatsHistDropAclDeltaAvg                   Unsigned64,
    cfprApAdaptorMenloMcpuStatsHistDropAclDeltaMax                   Unsigned64,
    cfprApAdaptorMenloMcpuStatsHistDropAclDeltaMin                   Unsigned64,
    cfprApAdaptorMenloMcpuStatsHistDropOverrun                       Unsigned64,
    cfprApAdaptorMenloMcpuStatsHistDropOverrunDelta                  Unsigned64,
    cfprApAdaptorMenloMcpuStatsHistDropOverrunDeltaAvg               Unsigned64,
    cfprApAdaptorMenloMcpuStatsHistDropOverrunDeltaMax               Unsigned64,
    cfprApAdaptorMenloMcpuStatsHistDropOverrunDeltaMin               Unsigned64,
    cfprApAdaptorMenloMcpuStatsHistDropRunt                          Unsigned64,
    cfprApAdaptorMenloMcpuStatsHistDropRuntDelta                     Unsigned64,
    cfprApAdaptorMenloMcpuStatsHistDropRuntDeltaAvg                  Unsigned64,
    cfprApAdaptorMenloMcpuStatsHistDropRuntDeltaMax                  Unsigned64,
    cfprApAdaptorMenloMcpuStatsHistDropRuntDeltaMin                  Unsigned64,
    cfprApAdaptorMenloMcpuStatsHistId                                Unsigned64,
    cfprApAdaptorMenloMcpuStatsHistMostRecent                        TruthValue,
    cfprApAdaptorMenloMcpuStatsHistSuspect                           TruthValue,
    cfprApAdaptorMenloMcpuStatsHistThresholded                       CfprApAdaptorMenloMcpuStatsHistThresholded,
    cfprApAdaptorMenloMcpuStatsHistTimeCollected                     DateAndTime,
    cfprApAdaptorMenloMcpuStatsHistTruncateOverrun                   Unsigned64,
    cfprApAdaptorMenloMcpuStatsHistTruncateOverrunDelta              Unsigned64,
    cfprApAdaptorMenloMcpuStatsHistTruncateOverrunDeltaAvg           Unsigned64,
    cfprApAdaptorMenloMcpuStatsHistTruncateOverrunDeltaMax           Unsigned64,
    cfprApAdaptorMenloMcpuStatsHistTruncateOverrunDeltaMin           Unsigned64
}

cfprApAdaptorMenloMcpuStatsHistInstanceId OBJECT-TYPE
    SYNTAX       CfprApManagedObjectId
    MAX-ACCESS   not-accessible
    STATUS       current
    DESCRIPTION
        "Instance identifier of the managed object."
    ::= { cfprApAdaptorMenloMcpuStatsHistEntry 1 }

cfprApAdaptorMenloMcpuStatsHistDn OBJECT-TYPE
    SYNTAX       CfprApManagedObjectDn
    MAX-ACCESS   read-only
    STATUS       current
    DESCRIPTION
        "Cisco Firepower adaptor:MenloMcpuStatsHist:dn
        managed object property"
    ::= { cfprApAdaptorMenloMcpuStatsHistEntry 2 }

cfprApAdaptorMenloMcpuStatsHistRn OBJECT-TYPE
    SYNTAX       SnmpAdminString
    MAX-ACCESS   read-only
    STATUS       current
    DESCRIPTION
        "Cisco Firepower adaptor:MenloMcpuStatsHist:rn
        managed object property"
    ::= { cfprApAdaptorMenloMcpuStatsHistEntry 3 }

cfprApAdaptorMenloMcpuStatsHistDropAcl OBJECT-TYPE
    SYNTAX       Unsigned64
    MAX-ACCESS   read-only
    STATUS       current
    DESCRIPTION
        "Cisco Firepower adaptor:MenloMcpuStatsHist:dropAcl
        managed object property"
    ::= { cfprApAdaptorMenloMcpuStatsHistEntry 4 }

cfprApAdaptorMenloMcpuStatsHistDropAclDelta OBJECT-TYPE
    SYNTAX       Unsigned64
    MAX-ACCESS   read-only
    STATUS       current
    DESCRIPTION
        "Cisco Firepower adaptor:MenloMcpuStatsHist:dropAclDelta
        managed object property"
    ::= { cfprApAdaptorMenloMcpuStatsHistEntry 5 }

cfprApAdaptorMenloMcpuStatsHistDropAclDeltaAvg OBJECT-TYPE
    SYNTAX       Unsigned64
    MAX-ACCESS   read-only
    STATUS       current
    DESCRIPTION
        "Cisco Firepower adaptor:MenloMcpuStatsHist:dropAclDeltaAvg
        managed object property"
    ::= { cfprApAdaptorMenloMcpuStatsHistEntry 6 }

cfprApAdaptorMenloMcpuStatsHistDropAclDeltaMax OBJECT-TYPE
    SYNTAX       Unsigned64
    MAX-ACCESS   read-only
    STATUS       current
    DESCRIPTION
        "Cisco Firepower adaptor:MenloMcpuStatsHist:dropAclDeltaMax
        managed object property"
    ::= { cfprApAdaptorMenloMcpuStatsHistEntry 7 }

cfprApAdaptorMenloMcpuStatsHistDropAclDeltaMin OBJECT-TYPE
    SYNTAX       Unsigned64
    MAX-ACCESS   read-only
    STATUS       current
    DESCRIPTION
        "Cisco Firepower adaptor:MenloMcpuStatsHist:dropAclDeltaMin
        managed object property"
    ::= { cfprApAdaptorMenloMcpuStatsHistEntry 8 }

cfprApAdaptorMenloMcpuStatsHistDropOverrun OBJECT-TYPE
    SYNTAX       Unsigned64
    MAX-ACCESS   read-only
    STATUS       current
    DESCRIPTION
        "Cisco Firepower adaptor:MenloMcpuStatsHist:dropOverrun
        managed object property"
    ::= { cfprApAdaptorMenloMcpuStatsHistEntry 9 }

cfprApAdaptorMenloMcpuStatsHistDropOverrunDelta OBJECT-TYPE
    SYNTAX       Unsigned64
    MAX-ACCESS   read-only
    STATUS       current
    DESCRIPTION
        "Cisco Firepower adaptor:MenloMcpuStatsHist:dropOverrunDelta
        managed object property"
    ::= { cfprApAdaptorMenloMcpuStatsHistEntry 10 }

cfprApAdaptorMenloMcpuStatsHistDropOverrunDeltaAvg OBJECT-TYPE
    SYNTAX       Unsigned64
    MAX-ACCESS   read-only
    STATUS       current
    DESCRIPTION
        "Cisco Firepower adaptor:MenloMcpuStatsHist:dropOverrunDeltaAvg
        managed object property"
    ::= { cfprApAdaptorMenloMcpuStatsHistEntry 11 }

cfprApAdaptorMenloMcpuStatsHistDropOverrunDeltaMax OBJECT-TYPE
    SYNTAX       Unsigned64
    MAX-ACCESS   read-only
    STATUS       current
    DESCRIPTION
        "Cisco Firepower adaptor:MenloMcpuStatsHist:dropOverrunDeltaMax
        managed object property"
    ::= { cfprApAdaptorMenloMcpuStatsHistEntry 12 }

cfprApAdaptorMenloMcpuStatsHistDropOverrunDeltaMin OBJECT-TYPE
    SYNTAX       Unsigned64
    MAX-ACCESS   read-only
    STATUS       current
    DESCRIPTION
        "Cisco Firepower adaptor:MenloMcpuStatsHist:dropOverrunDeltaMin
        managed object property"
    ::= { cfprApAdaptorMenloMcpuStatsHistEntry 13 }

cfprApAdaptorMenloMcpuStatsHistDropRunt OBJECT-TYPE
    SYNTAX       Unsigned64
    MAX-ACCESS   read-only
    STATUS       current
    DESCRIPTION
        "Cisco Firepower adaptor:MenloMcpuStatsHist:dropRunt
        managed object property"
    ::= { cfprApAdaptorMenloMcpuStatsHistEntry 14 }

cfprApAdaptorMenloMcpuStatsHistDropRuntDelta OBJECT-TYPE
    SYNTAX       Unsigned64
    MAX-ACCESS   read-only
    STATUS       current
    DESCRIPTION
        "Cisco Firepower adaptor:MenloMcpuStatsHist:dropRuntDelta
        managed object property"
    ::= { cfprApAdaptorMenloMcpuStatsHistEntry 15 }

cfprApAdaptorMenloMcpuStatsHistDropRuntDeltaAvg OBJECT-TYPE
    SYNTAX       Unsigned64
    MAX-ACCESS   read-only
    STATUS       current
    DESCRIPTION
        "Cisco Firepower adaptor:MenloMcpuStatsHist:dropRuntDeltaAvg
        managed object property"
    ::= { cfprApAdaptorMenloMcpuStatsHistEntry 16 }

cfprApAdaptorMenloMcpuStatsHistDropRuntDeltaMax OBJECT-TYPE
    SYNTAX       Unsigned64
    MAX-ACCESS   read-only
    STATUS       current
    DESCRIPTION
        "Cisco Firepower adaptor:MenloMcpuStatsHist:dropRuntDeltaMax
        managed object property"
    ::= { cfprApAdaptorMenloMcpuStatsHistEntry 17 }

cfprApAdaptorMenloMcpuStatsHistDropRuntDeltaMin OBJECT-TYPE
    SYNTAX       Unsigned64
    MAX-ACCESS   read-only
    STATUS       current
    DESCRIPTION
        "Cisco Firepower adaptor:MenloMcpuStatsHist:dropRuntDeltaMin
        managed object property"
    ::= { cfprApAdaptorMenloMcpuStatsHistEntry 18 }

cfprApAdaptorMenloMcpuStatsHistId OBJECT-TYPE
    SYNTAX       Unsigned64
    MAX-ACCESS   read-only
    STATUS       current
    DESCRIPTION
        "Cisco Firepower adaptor:MenloMcpuStatsHist:id
        managed object property"
    ::= { cfprApAdaptorMenloMcpuStatsHistEntry 19 }

cfprApAdaptorMenloMcpuStatsHistMostRecent OBJECT-TYPE
    SYNTAX       TruthValue
    MAX-ACCESS   read-only
    STATUS       current
    DESCRIPTION
        "Cisco Firepower adaptor:MenloMcpuStatsHist:mostRecent
        managed object property"
    ::= { cfprApAdaptorMenloMcpuStatsHistEntry 20 }

cfprApAdaptorMenloMcpuStatsHistSuspect OBJECT-TYPE
    SYNTAX       TruthValue
    MAX-ACCESS   read-only
    STATUS       current
    DESCRIPTION
        "Cisco Firepower adaptor:MenloMcpuStatsHist:suspect
        managed object property"
    ::= { cfprApAdaptorMenloMcpuStatsHistEntry 21 }

cfprApAdaptorMenloMcpuStatsHistThresholded OBJECT-TYPE
    SYNTAX       CfprApAdaptorMenloMcpuStatsHistThresholded
    MAX-ACCESS   read-only
    STATUS       current
    DESCRIPTION
        "Cisco Firepower adaptor:MenloMcpuStatsHist:thresholded
        managed object property"
    ::= { cfprApAdaptorMenloMcpuStatsHistEntry 22 }

cfprApAdaptorMenloMcpuStatsHistTimeCollected OBJECT-TYPE
    SYNTAX       DateAndTime
    MAX-ACCESS   read-only
    STATUS       current
    DESCRIPTION
        "Cisco Firepower adaptor:MenloMcpuStatsHist:timeCollected
        managed object property"
    ::= { cfprApAdaptorMenloMcpuStatsHistEntry 23 }

cfprApAdaptorMenloMcpuStatsHistTruncateOverrun OBJECT-TYPE
    SYNTAX       Unsigned64
    MAX-ACCESS   read-only
    STATUS       current
    DESCRIPTION
        "Cisco Firepower adaptor:MenloMcpuStatsHist:truncateOverrun
        managed object property"
    ::= { cfprApAdaptorMenloMcpuStatsHistEntry 24 }

cfprApAdaptorMenloMcpuStatsHistTruncateOverrunDelta OBJECT-TYPE
    SYNTAX       Unsigned64
    MAX-ACCESS   read-only
    STATUS       current
    DESCRIPTION
        "Cisco Firepower adaptor:MenloMcpuStatsHist:truncateOverrunDelta
        managed object property"
    ::= { cfprApAdaptorMenloMcpuStatsHistEntry 25 }

cfprApAdaptorMenloMcpuStatsHistTruncateOverrunDeltaAvg OBJECT-TYPE
    SYNTAX       Unsigned64
    MAX-ACCESS   read-only
    STATUS       current
    DESCRIPTION
        "Cisco Firepower adaptor:MenloMcpuStatsHist:truncateOverrunDeltaAv
        g managed object property"
    ::= { cfprApAdaptorMenloMcpuStatsHistEntry 26 }

cfprApAdaptorMenloMcpuStatsHistTruncateOverrunDeltaMax OBJECT-TYPE
    SYNTAX       Unsigned64
    MAX-ACCESS   read-only
    STATUS       current
    DESCRIPTION
        "Cisco Firepower adaptor:MenloMcpuStatsHist:truncateOverrunDeltaMa
        x managed object property"
    ::= { cfprApAdaptorMenloMcpuStatsHistEntry 27 }

cfprApAdaptorMenloMcpuStatsHistTruncateOverrunDeltaMin OBJECT-TYPE
    SYNTAX       Unsigned64
    MAX-ACCESS   read-only
    STATUS       current
    DESCRIPTION
        "Cisco Firepower adaptor:MenloMcpuStatsHist:truncateOverrunDeltaMi
        n managed object property"
    ::= { cfprApAdaptorMenloMcpuStatsHistEntry 28 }

cfprApAdaptorMenloNetEgStatsTable OBJECT-TYPE
    SYNTAX           SEQUENCE OF CfprApAdaptorMenloNetEgStatsEntry
    MAX-ACCESS       not-accessible
    STATUS           current
    DESCRIPTION
        "Cisco Firepower adaptor:MenloNetEgStats managed object table"
    ::= { cfprApAdaptorObjects 100 }

cfprApAdaptorMenloNetEgStatsEntry OBJECT-TYPE
    SYNTAX           CfprApAdaptorMenloNetEgStatsEntry
    MAX-ACCESS       not-accessible
    STATUS           current
    DESCRIPTION
        "Entry for the cfprApAdaptorMenloNetEgStatsTable table."
    INDEX { cfprApAdaptorMenloNetEgStatsInstanceId }
    ::= { cfprApAdaptorMenloNetEgStatsTable 1 }

CfprApAdaptorMenloNetEgStatsEntry ::= SEQUENCE {
    cfprApAdaptorMenloNetEgStatsInstanceId                           CfprApManagedObjectId,
    cfprApAdaptorMenloNetEgStatsDn                                   CfprApManagedObjectDn,
    cfprApAdaptorMenloNetEgStatsRn                                   SnmpAdminString,
    cfprApAdaptorMenloNetEgStatsDropCmd                              Unsigned64,
    cfprApAdaptorMenloNetEgStatsDropCmdDelta                         Counter64,
    cfprApAdaptorMenloNetEgStatsDropCmdDeltaAvg                      Unsigned64,
    cfprApAdaptorMenloNetEgStatsDropCmdDeltaMax                      Unsigned64,
    cfprApAdaptorMenloNetEgStatsDropCmdDeltaMin                      Unsigned64,
    cfprApAdaptorMenloNetEgStatsDropLifCfgInvalid                    Unsigned64,
    cfprApAdaptorMenloNetEgStatsDropLifCfgInvalidDelta               Counter64,
    cfprApAdaptorMenloNetEgStatsDropLifCfgInvalidDeltaAvg            Unsigned64,
    cfprApAdaptorMenloNetEgStatsDropLifCfgInvalidDeltaMax            Unsigned64,
    cfprApAdaptorMenloNetEgStatsDropLifCfgInvalidDeltaMin            Unsigned64,
    cfprApAdaptorMenloNetEgStatsDropLifMapNoHit                      Unsigned64,
    cfprApAdaptorMenloNetEgStatsDropLifMapNoHitDelta                 Counter64,
    cfprApAdaptorMenloNetEgStatsDropLifMapNoHitDeltaAvg              Unsigned64,
    cfprApAdaptorMenloNetEgStatsDropLifMapNoHitDeltaMax              Unsigned64,
    cfprApAdaptorMenloNetEgStatsDropLifMapNoHitDeltaMin              Unsigned64,
    cfprApAdaptorMenloNetEgStatsDropSrcBind                          Unsigned64,
    cfprApAdaptorMenloNetEgStatsDropSrcBindDelta                     Counter64,
    cfprApAdaptorMenloNetEgStatsDropSrcBindDeltaAvg                  Unsigned64,
    cfprApAdaptorMenloNetEgStatsDropSrcBindDeltaMax                  Unsigned64,
    cfprApAdaptorMenloNetEgStatsDropSrcBindDeltaMin                  Unsigned64,
    cfprApAdaptorMenloNetEgStatsIntervals                            Gauge32,
    cfprApAdaptorMenloNetEgStatsLearnReqDrop                         Unsigned64,
    cfprApAdaptorMenloNetEgStatsLearnReqDropDelta                    Counter64,
    cfprApAdaptorMenloNetEgStatsLearnReqDropDeltaAvg                 Unsigned64,
    cfprApAdaptorMenloNetEgStatsLearnReqDropDeltaMax                 Unsigned64,
    cfprApAdaptorMenloNetEgStatsLearnReqDropDeltaMin                 Unsigned64,
    cfprApAdaptorMenloNetEgStatsMenloNetIndex                        CfprApAdaptorMenloStatsIndex,
    cfprApAdaptorMenloNetEgStatsSuspect                              TruthValue,
    cfprApAdaptorMenloNetEgStatsThresholded                          CfprApAdaptorMenloNetEgStatsThresholded,
    cfprApAdaptorMenloNetEgStatsTimeCollected                        DateAndTime,
    cfprApAdaptorMenloNetEgStatsUpdate                               Gauge32
}

cfprApAdaptorMenloNetEgStatsInstanceId OBJECT-TYPE
    SYNTAX       CfprApManagedObjectId
    MAX-ACCESS   not-accessible
    STATUS       current
    DESCRIPTION
        "Instance identifier of the managed object."
    ::= { cfprApAdaptorMenloNetEgStatsEntry 1 }

cfprApAdaptorMenloNetEgStatsDn OBJECT-TYPE
    SYNTAX       CfprApManagedObjectDn
    MAX-ACCESS   read-only
    STATUS       current
    DESCRIPTION
        "Cisco Firepower adaptor:MenloNetEgStats:dn managed
        object property"
    ::= { cfprApAdaptorMenloNetEgStatsEntry 2 }

cfprApAdaptorMenloNetEgStatsRn OBJECT-TYPE
    SYNTAX       SnmpAdminString
    MAX-ACCESS   read-only
    STATUS       current
    DESCRIPTION
        "Cisco Firepower adaptor:MenloNetEgStats:rn managed
        object property"
    ::= { cfprApAdaptorMenloNetEgStatsEntry 3 }

cfprApAdaptorMenloNetEgStatsDropCmd OBJECT-TYPE
    SYNTAX       Unsigned64
    MAX-ACCESS   read-only
    STATUS       current
    DESCRIPTION
        "Cisco Firepower adaptor:MenloNetEgStats:dropCmd
        managed object property"
    ::= { cfprApAdaptorMenloNetEgStatsEntry 4 }

cfprApAdaptorMenloNetEgStatsDropCmdDelta OBJECT-TYPE
    SYNTAX       Counter64
    MAX-ACCESS   read-only
    STATUS       current
    DESCRIPTION
        "Cisco Firepower adaptor:MenloNetEgStats:dropCmdDelta
        managed object property"
    ::= { cfprApAdaptorMenloNetEgStatsEntry 5 }

cfprApAdaptorMenloNetEgStatsDropCmdDeltaAvg OBJECT-TYPE
    SYNTAX       Unsigned64
    MAX-ACCESS   read-only
    STATUS       current
    DESCRIPTION
        "Cisco Firepower adaptor:MenloNetEgStats:dropCmdDeltaAvg
        managed object property"
    ::= { cfprApAdaptorMenloNetEgStatsEntry 6 }

cfprApAdaptorMenloNetEgStatsDropCmdDeltaMax OBJECT-TYPE
    SYNTAX       Unsigned64
    MAX-ACCESS   read-only
    STATUS       current
    DESCRIPTION
        "Cisco Firepower adaptor:MenloNetEgStats:dropCmdDeltaMax
        managed object property"
    ::= { cfprApAdaptorMenloNetEgStatsEntry 7 }

cfprApAdaptorMenloNetEgStatsDropCmdDeltaMin OBJECT-TYPE
    SYNTAX       Unsigned64
    MAX-ACCESS   read-only
    STATUS       current
    DESCRIPTION
        "Cisco Firepower adaptor:MenloNetEgStats:dropCmdDeltaMin
        managed object property"
    ::= { cfprApAdaptorMenloNetEgStatsEntry 8 }

cfprApAdaptorMenloNetEgStatsDropLifCfgInvalid OBJECT-TYPE
    SYNTAX       Unsigned64
    MAX-ACCESS   read-only
    STATUS       current
    DESCRIPTION
        "Cisco Firepower adaptor:MenloNetEgStats:dropLifCfgInvalid
        managed object property"
    ::= { cfprApAdaptorMenloNetEgStatsEntry 9 }

cfprApAdaptorMenloNetEgStatsDropLifCfgInvalidDelta OBJECT-TYPE
    SYNTAX       Counter64
    MAX-ACCESS   read-only
    STATUS       current
    DESCRIPTION
        "Cisco Firepower adaptor:MenloNetEgStats:dropLifCfgInvalidDelta
        managed object property"
    ::= { cfprApAdaptorMenloNetEgStatsEntry 10 }

cfprApAdaptorMenloNetEgStatsDropLifCfgInvalidDeltaAvg OBJECT-TYPE
    SYNTAX       Unsigned64
    MAX-ACCESS   read-only
    STATUS       current
    DESCRIPTION
        "Cisco Firepower adaptor:MenloNetEgStats:dropLifCfgInvalidDeltaAvg
         managed object property"
    ::= { cfprApAdaptorMenloNetEgStatsEntry 11 }

cfprApAdaptorMenloNetEgStatsDropLifCfgInvalidDeltaMax OBJECT-TYPE
    SYNTAX       Unsigned64
    MAX-ACCESS   read-only
    STATUS       current
    DESCRIPTION
        "Cisco Firepower adaptor:MenloNetEgStats:dropLifCfgInvalidDeltaMax
         managed object property"
    ::= { cfprApAdaptorMenloNetEgStatsEntry 12 }

cfprApAdaptorMenloNetEgStatsDropLifCfgInvalidDeltaMin OBJECT-TYPE
    SYNTAX       Unsigned64
    MAX-ACCESS   read-only
    STATUS       current
    DESCRIPTION
        "Cisco Firepower adaptor:MenloNetEgStats:dropLifCfgInvalidDeltaMin
         managed object property"
    ::= { cfprApAdaptorMenloNetEgStatsEntry 13 }

cfprApAdaptorMenloNetEgStatsDropLifMapNoHit OBJECT-TYPE
    SYNTAX       Unsigned64
    MAX-ACCESS   read-only
    STATUS       current
    DESCRIPTION
        "Cisco Firepower adaptor:MenloNetEgStats:dropLifMapNoHit
        managed object property"
    ::= { cfprApAdaptorMenloNetEgStatsEntry 14 }

cfprApAdaptorMenloNetEgStatsDropLifMapNoHitDelta OBJECT-TYPE
    SYNTAX       Counter64
    MAX-ACCESS   read-only
    STATUS       current
    DESCRIPTION
        "Cisco Firepower adaptor:MenloNetEgStats:dropLifMapNoHitDelta
        managed object property"
    ::= { cfprApAdaptorMenloNetEgStatsEntry 15 }

cfprApAdaptorMenloNetEgStatsDropLifMapNoHitDeltaAvg OBJECT-TYPE
    SYNTAX       Unsigned64
    MAX-ACCESS   read-only
    STATUS       current
    DESCRIPTION
        "Cisco Firepower adaptor:MenloNetEgStats:dropLifMapNoHitDeltaAvg
        managed object property"
    ::= { cfprApAdaptorMenloNetEgStatsEntry 16 }

cfprApAdaptorMenloNetEgStatsDropLifMapNoHitDeltaMax OBJECT-TYPE
    SYNTAX       Unsigned64
    MAX-ACCESS   read-only
    STATUS       current
    DESCRIPTION
        "Cisco Firepower adaptor:MenloNetEgStats:dropLifMapNoHitDeltaMax
        managed object property"
    ::= { cfprApAdaptorMenloNetEgStatsEntry 17 }

cfprApAdaptorMenloNetEgStatsDropLifMapNoHitDeltaMin OBJECT-TYPE
    SYNTAX       Unsigned64
    MAX-ACCESS   read-only
    STATUS       current
    DESCRIPTION
        "Cisco Firepower adaptor:MenloNetEgStats:dropLifMapNoHitDeltaMin
        managed object property"
    ::= { cfprApAdaptorMenloNetEgStatsEntry 18 }

cfprApAdaptorMenloNetEgStatsDropSrcBind OBJECT-TYPE
    SYNTAX       Unsigned64
    MAX-ACCESS   read-only
    STATUS       current
    DESCRIPTION
        "Cisco Firepower adaptor:MenloNetEgStats:dropSrcBind
        managed object property"
    ::= { cfprApAdaptorMenloNetEgStatsEntry 19 }

cfprApAdaptorMenloNetEgStatsDropSrcBindDelta OBJECT-TYPE
    SYNTAX       Counter64
    MAX-ACCESS   read-only
    STATUS       current
    DESCRIPTION
        "Cisco Firepower adaptor:MenloNetEgStats:dropSrcBindDelta
        managed object property"
    ::= { cfprApAdaptorMenloNetEgStatsEntry 20 }

cfprApAdaptorMenloNetEgStatsDropSrcBindDeltaAvg OBJECT-TYPE
    SYNTAX       Unsigned64
    MAX-ACCESS   read-only
    STATUS       current
    DESCRIPTION
        "Cisco Firepower adaptor:MenloNetEgStats:dropSrcBindDeltaAvg
        managed object property"
    ::= { cfprApAdaptorMenloNetEgStatsEntry 21 }

cfprApAdaptorMenloNetEgStatsDropSrcBindDeltaMax OBJECT-TYPE
    SYNTAX       Unsigned64
    MAX-ACCESS   read-only
    STATUS       current
    DESCRIPTION
        "Cisco Firepower adaptor:MenloNetEgStats:dropSrcBindDeltaMax
        managed object property"
    ::= { cfprApAdaptorMenloNetEgStatsEntry 22 }

cfprApAdaptorMenloNetEgStatsDropSrcBindDeltaMin OBJECT-TYPE
    SYNTAX       Unsigned64
    MAX-ACCESS   read-only
    STATUS       current
    DESCRIPTION
        "Cisco Firepower adaptor:MenloNetEgStats:dropSrcBindDeltaMin
        managed object property"
    ::= { cfprApAdaptorMenloNetEgStatsEntry 23 }

cfprApAdaptorMenloNetEgStatsIntervals OBJECT-TYPE
    SYNTAX       Gauge32
    MAX-ACCESS   read-only
    STATUS       current
    DESCRIPTION
        "Cisco Firepower adaptor:MenloNetEgStats:intervals
        managed object property"
    ::= { cfprApAdaptorMenloNetEgStatsEntry 24 }

cfprApAdaptorMenloNetEgStatsLearnReqDrop OBJECT-TYPE
    SYNTAX       Unsigned64
    MAX-ACCESS   read-only
    STATUS       current
    DESCRIPTION
        "Cisco Firepower adaptor:MenloNetEgStats:learnReqDrop
        managed object property"
    ::= { cfprApAdaptorMenloNetEgStatsEntry 25 }

cfprApAdaptorMenloNetEgStatsLearnReqDropDelta OBJECT-TYPE
    SYNTAX       Counter64
    MAX-ACCESS   read-only
    STATUS       current
    DESCRIPTION
        "Cisco Firepower adaptor:MenloNetEgStats:learnReqDropDelta
        managed object property"
    ::= { cfprApAdaptorMenloNetEgStatsEntry 26 }

cfprApAdaptorMenloNetEgStatsLearnReqDropDeltaAvg OBJECT-TYPE
    SYNTAX       Unsigned64
    MAX-ACCESS   read-only
    STATUS       current
    DESCRIPTION
        "Cisco Firepower adaptor:MenloNetEgStats:learnReqDropDeltaAvg
        managed object property"
    ::= { cfprApAdaptorMenloNetEgStatsEntry 27 }

cfprApAdaptorMenloNetEgStatsLearnReqDropDeltaMax OBJECT-TYPE
    SYNTAX       Unsigned64
    MAX-ACCESS   read-only
    STATUS       current
    DESCRIPTION
        "Cisco Firepower adaptor:MenloNetEgStats:learnReqDropDeltaMax
        managed object property"
    ::= { cfprApAdaptorMenloNetEgStatsEntry 28 }

cfprApAdaptorMenloNetEgStatsLearnReqDropDeltaMin OBJECT-TYPE
    SYNTAX       Unsigned64
    MAX-ACCESS   read-only
    STATUS       current
    DESCRIPTION
        "Cisco Firepower adaptor:MenloNetEgStats:learnReqDropDeltaMin
        managed object property"
    ::= { cfprApAdaptorMenloNetEgStatsEntry 29 }

cfprApAdaptorMenloNetEgStatsMenloNetIndex OBJECT-TYPE
    SYNTAX       CfprApAdaptorMenloStatsIndex
    MAX-ACCESS   read-only
    STATUS       current
    DESCRIPTION
        "Cisco Firepower adaptor:MenloNetEgStats:menloNetIndex
        managed object property"
    ::= { cfprApAdaptorMenloNetEgStatsEntry 30 }

cfprApAdaptorMenloNetEgStatsSuspect OBJECT-TYPE
    SYNTAX       TruthValue
    MAX-ACCESS   read-only
    STATUS       current
    DESCRIPTION
        "Cisco Firepower adaptor:MenloNetEgStats:suspect
        managed object property"
    ::= { cfprApAdaptorMenloNetEgStatsEntry 31 }

cfprApAdaptorMenloNetEgStatsThresholded OBJECT-TYPE
    SYNTAX       CfprApAdaptorMenloNetEgStatsThresholded
    MAX-ACCESS   read-only
    STATUS       current
    DESCRIPTION
        "Cisco Firepower adaptor:MenloNetEgStats:thresholded
        managed object property"
    ::= { cfprApAdaptorMenloNetEgStatsEntry 32 }

cfprApAdaptorMenloNetEgStatsTimeCollected OBJECT-TYPE
    SYNTAX       DateAndTime
    MAX-ACCESS   read-only
    STATUS       current
    DESCRIPTION
        "Cisco Firepower adaptor:MenloNetEgStats:timeCollected
        managed object property"
    ::= { cfprApAdaptorMenloNetEgStatsEntry 33 }

cfprApAdaptorMenloNetEgStatsUpdate OBJECT-TYPE
    SYNTAX       Gauge32
    MAX-ACCESS   read-only
    STATUS       current
    DESCRIPTION
        "Cisco Firepower adaptor:MenloNetEgStats:update
        managed object property"
    ::= { cfprApAdaptorMenloNetEgStatsEntry 34 }

cfprApAdaptorMenloNetEgStatsHistTable OBJECT-TYPE
    SYNTAX           SEQUENCE OF CfprApAdaptorMenloNetEgStatsHistEntry
    MAX-ACCESS       not-accessible
    STATUS           current
    DESCRIPTION
        "Cisco Firepower adaptor:MenloNetEgStatsHist managed object table"
    ::= { cfprApAdaptorObjects 101 }

cfprApAdaptorMenloNetEgStatsHistEntry OBJECT-TYPE
    SYNTAX           CfprApAdaptorMenloNetEgStatsHistEntry
    MAX-ACCESS       not-accessible
    STATUS           current
    DESCRIPTION
        "Entry for the cfprApAdaptorMenloNetEgStatsHistTable table."
    INDEX { cfprApAdaptorMenloNetEgStatsHistInstanceId }
    ::= { cfprApAdaptorMenloNetEgStatsHistTable 1 }

CfprApAdaptorMenloNetEgStatsHistEntry ::= SEQUENCE {
    cfprApAdaptorMenloNetEgStatsHistInstanceId                       CfprApManagedObjectId,
    cfprApAdaptorMenloNetEgStatsHistDn                               CfprApManagedObjectDn,
    cfprApAdaptorMenloNetEgStatsHistRn                               SnmpAdminString,
    cfprApAdaptorMenloNetEgStatsHistDropCmd                          Unsigned64,
    cfprApAdaptorMenloNetEgStatsHistDropCmdDelta                     Unsigned64,
    cfprApAdaptorMenloNetEgStatsHistDropCmdDeltaAvg                  Unsigned64,
    cfprApAdaptorMenloNetEgStatsHistDropCmdDeltaMax                  Unsigned64,
    cfprApAdaptorMenloNetEgStatsHistDropCmdDeltaMin                  Unsigned64,
    cfprApAdaptorMenloNetEgStatsHistDropLifCfgInvalid                Unsigned64,
    cfprApAdaptorMenloNetEgStatsHistDropLifCfgInvalidDelta           Unsigned64,
    cfprApAdaptorMenloNetEgStatsHistDropLifCfgInvalidDeltaAvg        Unsigned64,
    cfprApAdaptorMenloNetEgStatsHistDropLifCfgInvalidDeltaMax        Unsigned64,
    cfprApAdaptorMenloNetEgStatsHistDropLifCfgInvalidDeltaMin        Unsigned64,
    cfprApAdaptorMenloNetEgStatsHistDropLifMapNoHit                  Unsigned64,
    cfprApAdaptorMenloNetEgStatsHistDropLifMapNoHitDelta             Unsigned64,
    cfprApAdaptorMenloNetEgStatsHistDropLifMapNoHitDeltaAvg          Unsigned64,
    cfprApAdaptorMenloNetEgStatsHistDropLifMapNoHitDeltaMax          Unsigned64,
    cfprApAdaptorMenloNetEgStatsHistDropLifMapNoHitDeltaMin          Unsigned64,
    cfprApAdaptorMenloNetEgStatsHistDropSrcBind                      Unsigned64,
    cfprApAdaptorMenloNetEgStatsHistDropSrcBindDelta                 Unsigned64,
    cfprApAdaptorMenloNetEgStatsHistDropSrcBindDeltaAvg              Unsigned64,
    cfprApAdaptorMenloNetEgStatsHistDropSrcBindDeltaMax              Unsigned64,
    cfprApAdaptorMenloNetEgStatsHistDropSrcBindDeltaMin              Unsigned64,
    cfprApAdaptorMenloNetEgStatsHistId                               Unsigned64,
    cfprApAdaptorMenloNetEgStatsHistLearnReqDrop                     Unsigned64,
    cfprApAdaptorMenloNetEgStatsHistLearnReqDropDelta                Unsigned64,
    cfprApAdaptorMenloNetEgStatsHistLearnReqDropDeltaAvg             Unsigned64,
    cfprApAdaptorMenloNetEgStatsHistLearnReqDropDeltaMax             Unsigned64,
    cfprApAdaptorMenloNetEgStatsHistLearnReqDropDeltaMin             Unsigned64,
    cfprApAdaptorMenloNetEgStatsHistMostRecent                       TruthValue,
    cfprApAdaptorMenloNetEgStatsHistSuspect                          TruthValue,
    cfprApAdaptorMenloNetEgStatsHistThresholded                      CfprApAdaptorMenloNetEgStatsHistThresholded,
    cfprApAdaptorMenloNetEgStatsHistTimeCollected                    DateAndTime
}

cfprApAdaptorMenloNetEgStatsHistInstanceId OBJECT-TYPE
    SYNTAX       CfprApManagedObjectId
    MAX-ACCESS   not-accessible
    STATUS       current
    DESCRIPTION
        "Instance identifier of the managed object."
    ::= { cfprApAdaptorMenloNetEgStatsHistEntry 1 }

cfprApAdaptorMenloNetEgStatsHistDn OBJECT-TYPE
    SYNTAX       CfprApManagedObjectDn
    MAX-ACCESS   read-only
    STATUS       current
    DESCRIPTION
        "Cisco Firepower adaptor:MenloNetEgStatsHist:dn
        managed object property"
    ::= { cfprApAdaptorMenloNetEgStatsHistEntry 2 }

cfprApAdaptorMenloNetEgStatsHistRn OBJECT-TYPE
    SYNTAX       SnmpAdminString
    MAX-ACCESS   read-only
    STATUS       current
    DESCRIPTION
        "Cisco Firepower adaptor:MenloNetEgStatsHist:rn
        managed object property"
    ::= { cfprApAdaptorMenloNetEgStatsHistEntry 3 }

cfprApAdaptorMenloNetEgStatsHistDropCmd OBJECT-TYPE
    SYNTAX       Unsigned64
    MAX-ACCESS   read-only
    STATUS       current
    DESCRIPTION
        "Cisco Firepower adaptor:MenloNetEgStatsHist:dropCmd
        managed object property"
    ::= { cfprApAdaptorMenloNetEgStatsHistEntry 4 }

cfprApAdaptorMenloNetEgStatsHistDropCmdDelta OBJECT-TYPE
    SYNTAX       Unsigned64
    MAX-ACCESS   read-only
    STATUS       current
    DESCRIPTION
        "Cisco Firepower adaptor:MenloNetEgStatsHist:dropCmdDelta
        managed object property"
    ::= { cfprApAdaptorMenloNetEgStatsHistEntry 5 }

cfprApAdaptorMenloNetEgStatsHistDropCmdDeltaAvg OBJECT-TYPE
    SYNTAX       Unsigned64
    MAX-ACCESS   read-only
    STATUS       current
    DESCRIPTION
        "Cisco Firepower adaptor:MenloNetEgStatsHist:dropCmdDeltaAvg
        managed object property"
    ::= { cfprApAdaptorMenloNetEgStatsHistEntry 6 }

cfprApAdaptorMenloNetEgStatsHistDropCmdDeltaMax OBJECT-TYPE
    SYNTAX       Unsigned64
    MAX-ACCESS   read-only
    STATUS       current
    DESCRIPTION
        "Cisco Firepower adaptor:MenloNetEgStatsHist:dropCmdDeltaMax
        managed object property"
    ::= { cfprApAdaptorMenloNetEgStatsHistEntry 7 }

cfprApAdaptorMenloNetEgStatsHistDropCmdDeltaMin OBJECT-TYPE
    SYNTAX       Unsigned64
    MAX-ACCESS   read-only
    STATUS       current
    DESCRIPTION
        "Cisco Firepower adaptor:MenloNetEgStatsHist:dropCmdDeltaMin
        managed object property"
    ::= { cfprApAdaptorMenloNetEgStatsHistEntry 8 }

cfprApAdaptorMenloNetEgStatsHistDropLifCfgInvalid OBJECT-TYPE
    SYNTAX       Unsigned64
    MAX-ACCESS   read-only
    STATUS       current
    DESCRIPTION
        "Cisco Firepower adaptor:MenloNetEgStatsHist:dropLifCfgInvalid
        managed object property"
    ::= { cfprApAdaptorMenloNetEgStatsHistEntry 9 }

cfprApAdaptorMenloNetEgStatsHistDropLifCfgInvalidDelta OBJECT-TYPE
    SYNTAX       Unsigned64
    MAX-ACCESS   read-only
    STATUS       current
    DESCRIPTION
        "Cisco Firepower adaptor:MenloNetEgStatsHist:dropLifCfgInvalidDelt
        a managed object property"
    ::= { cfprApAdaptorMenloNetEgStatsHistEntry 10 }

cfprApAdaptorMenloNetEgStatsHistDropLifCfgInvalidDeltaAvg OBJECT-TYPE
    SYNTAX       Unsigned64
    MAX-ACCESS   read-only
    STATUS       current
    DESCRIPTION
        "Cisco Firepower adaptor:MenloNetEgStatsHist:dropLifCfgInvalidDelt
        aAvg managed object property"
    ::= { cfprApAdaptorMenloNetEgStatsHistEntry 11 }

cfprApAdaptorMenloNetEgStatsHistDropLifCfgInvalidDeltaMax OBJECT-TYPE
    SYNTAX       Unsigned64
    MAX-ACCESS   read-only
    STATUS       current
    DESCRIPTION
        "Cisco Firepower adaptor:MenloNetEgStatsHist:dropLifCfgInvalidDelt
        aMax managed object property"
    ::= { cfprApAdaptorMenloNetEgStatsHistEntry 12 }

cfprApAdaptorMenloNetEgStatsHistDropLifCfgInvalidDeltaMin OBJECT-TYPE
    SYNTAX       Unsigned64
    MAX-ACCESS   read-only
    STATUS       current
    DESCRIPTION
        "Cisco Firepower adaptor:MenloNetEgStatsHist:dropLifCfgInvalidDelt
        aMin managed object property"
    ::= { cfprApAdaptorMenloNetEgStatsHistEntry 13 }

cfprApAdaptorMenloNetEgStatsHistDropLifMapNoHit OBJECT-TYPE
    SYNTAX       Unsigned64
    MAX-ACCESS   read-only
    STATUS       current
    DESCRIPTION
        "Cisco Firepower adaptor:MenloNetEgStatsHist:dropLifMapNoHit
        managed object property"
    ::= { cfprApAdaptorMenloNetEgStatsHistEntry 14 }

cfprApAdaptorMenloNetEgStatsHistDropLifMapNoHitDelta OBJECT-TYPE
    SYNTAX       Unsigned64
    MAX-ACCESS   read-only
    STATUS       current
    DESCRIPTION
        "Cisco Firepower adaptor:MenloNetEgStatsHist:dropLifMapNoHitDelta
        managed object property"
    ::= { cfprApAdaptorMenloNetEgStatsHistEntry 15 }

cfprApAdaptorMenloNetEgStatsHistDropLifMapNoHitDeltaAvg OBJECT-TYPE
    SYNTAX       Unsigned64
    MAX-ACCESS   read-only
    STATUS       current
    DESCRIPTION
        "Cisco Firepower adaptor:MenloNetEgStatsHist:dropLifMapNoHitDeltaA
        vg managed object property"
    ::= { cfprApAdaptorMenloNetEgStatsHistEntry 16 }

cfprApAdaptorMenloNetEgStatsHistDropLifMapNoHitDeltaMax OBJECT-TYPE
    SYNTAX       Unsigned64
    MAX-ACCESS   read-only
    STATUS       current
    DESCRIPTION
        "Cisco Firepower adaptor:MenloNetEgStatsHist:dropLifMapNoHitDeltaM
        ax managed object property"
    ::= { cfprApAdaptorMenloNetEgStatsHistEntry 17 }

cfprApAdaptorMenloNetEgStatsHistDropLifMapNoHitDeltaMin OBJECT-TYPE
    SYNTAX       Unsigned64
    MAX-ACCESS   read-only
    STATUS       current
    DESCRIPTION
        "Cisco Firepower adaptor:MenloNetEgStatsHist:dropLifMapNoHitDeltaM
        in managed object property"
    ::= { cfprApAdaptorMenloNetEgStatsHistEntry 18 }

cfprApAdaptorMenloNetEgStatsHistDropSrcBind OBJECT-TYPE
    SYNTAX       Unsigned64
    MAX-ACCESS   read-only
    STATUS       current
    DESCRIPTION
        "Cisco Firepower adaptor:MenloNetEgStatsHist:dropSrcBind
        managed object property"
    ::= { cfprApAdaptorMenloNetEgStatsHistEntry 19 }

cfprApAdaptorMenloNetEgStatsHistDropSrcBindDelta OBJECT-TYPE
    SYNTAX       Unsigned64
    MAX-ACCESS   read-only
    STATUS       current
    DESCRIPTION
        "Cisco Firepower adaptor:MenloNetEgStatsHist:dropSrcBindDelta
        managed object property"
    ::= { cfprApAdaptorMenloNetEgStatsHistEntry 20 }

cfprApAdaptorMenloNetEgStatsHistDropSrcBindDeltaAvg OBJECT-TYPE
    SYNTAX       Unsigned64
    MAX-ACCESS   read-only
    STATUS       current
    DESCRIPTION
        "Cisco Firepower adaptor:MenloNetEgStatsHist:dropSrcBindDeltaAvg
        managed object property"
    ::= { cfprApAdaptorMenloNetEgStatsHistEntry 21 }

cfprApAdaptorMenloNetEgStatsHistDropSrcBindDeltaMax OBJECT-TYPE
    SYNTAX       Unsigned64
    MAX-ACCESS   read-only
    STATUS       current
    DESCRIPTION
        "Cisco Firepower adaptor:MenloNetEgStatsHist:dropSrcBindDeltaMax
        managed object property"
    ::= { cfprApAdaptorMenloNetEgStatsHistEntry 22 }

cfprApAdaptorMenloNetEgStatsHistDropSrcBindDeltaMin OBJECT-TYPE
    SYNTAX       Unsigned64
    MAX-ACCESS   read-only
    STATUS       current
    DESCRIPTION
        "Cisco Firepower adaptor:MenloNetEgStatsHist:dropSrcBindDeltaMin
        managed object property"
    ::= { cfprApAdaptorMenloNetEgStatsHistEntry 23 }

cfprApAdaptorMenloNetEgStatsHistId OBJECT-TYPE
    SYNTAX       Unsigned64
    MAX-ACCESS   read-only
    STATUS       current
    DESCRIPTION
        "Cisco Firepower adaptor:MenloNetEgStatsHist:id
        managed object property"
    ::= { cfprApAdaptorMenloNetEgStatsHistEntry 24 }

cfprApAdaptorMenloNetEgStatsHistLearnReqDrop OBJECT-TYPE
    SYNTAX       Unsigned64
    MAX-ACCESS   read-only
    STATUS       current
    DESCRIPTION
        "Cisco Firepower adaptor:MenloNetEgStatsHist:learnReqDrop
        managed object property"
    ::= { cfprApAdaptorMenloNetEgStatsHistEntry 25 }

cfprApAdaptorMenloNetEgStatsHistLearnReqDropDelta OBJECT-TYPE
    SYNTAX       Unsigned64
    MAX-ACCESS   read-only
    STATUS       current
    DESCRIPTION
        "Cisco Firepower adaptor:MenloNetEgStatsHist:learnReqDropDelta
        managed object property"
    ::= { cfprApAdaptorMenloNetEgStatsHistEntry 26 }

cfprApAdaptorMenloNetEgStatsHistLearnReqDropDeltaAvg OBJECT-TYPE
    SYNTAX       Unsigned64
    MAX-ACCESS   read-only
    STATUS       current
    DESCRIPTION
        "Cisco Firepower adaptor:MenloNetEgStatsHist:learnReqDropDeltaAvg
        managed object property"
    ::= { cfprApAdaptorMenloNetEgStatsHistEntry 27 }

cfprApAdaptorMenloNetEgStatsHistLearnReqDropDeltaMax OBJECT-TYPE
    SYNTAX       Unsigned64
    MAX-ACCESS   read-only
    STATUS       current
    DESCRIPTION
        "Cisco Firepower adaptor:MenloNetEgStatsHist:learnReqDropDeltaMax
        managed object property"
    ::= { cfprApAdaptorMenloNetEgStatsHistEntry 28 }

cfprApAdaptorMenloNetEgStatsHistLearnReqDropDeltaMin OBJECT-TYPE
    SYNTAX       Unsigned64
    MAX-ACCESS   read-only
    STATUS       current
    DESCRIPTION
        "Cisco Firepower adaptor:MenloNetEgStatsHist:learnReqDropDeltaMin
        managed object property"
    ::= { cfprApAdaptorMenloNetEgStatsHistEntry 29 }

cfprApAdaptorMenloNetEgStatsHistMostRecent OBJECT-TYPE
    SYNTAX       TruthValue
    MAX-ACCESS   read-only
    STATUS       current
    DESCRIPTION
        "Cisco Firepower adaptor:MenloNetEgStatsHist:mostRecent
        managed object property"
    ::= { cfprApAdaptorMenloNetEgStatsHistEntry 30 }

cfprApAdaptorMenloNetEgStatsHistSuspect OBJECT-TYPE
    SYNTAX       TruthValue
    MAX-ACCESS   read-only
    STATUS       current
    DESCRIPTION
        "Cisco Firepower adaptor:MenloNetEgStatsHist:suspect
        managed object property"
    ::= { cfprApAdaptorMenloNetEgStatsHistEntry 31 }

cfprApAdaptorMenloNetEgStatsHistThresholded OBJECT-TYPE
    SYNTAX       CfprApAdaptorMenloNetEgStatsHistThresholded
    MAX-ACCESS   read-only
    STATUS       current
    DESCRIPTION
        "Cisco Firepower adaptor:MenloNetEgStatsHist:thresholded
        managed object property"
    ::= { cfprApAdaptorMenloNetEgStatsHistEntry 32 }

cfprApAdaptorMenloNetEgStatsHistTimeCollected OBJECT-TYPE
    SYNTAX       DateAndTime
    MAX-ACCESS   read-only
    STATUS       current
    DESCRIPTION
        "Cisco Firepower adaptor:MenloNetEgStatsHist:timeCollected
        managed object property"
    ::= { cfprApAdaptorMenloNetEgStatsHistEntry 33 }

cfprApAdaptorMenloNetInStatsTable OBJECT-TYPE
    SYNTAX           SEQUENCE OF CfprApAdaptorMenloNetInStatsEntry
    MAX-ACCESS       not-accessible
    STATUS           current
    DESCRIPTION
        "Cisco Firepower adaptor:MenloNetInStats managed object table"
    ::= { cfprApAdaptorObjects 102 }

cfprApAdaptorMenloNetInStatsEntry OBJECT-TYPE
    SYNTAX           CfprApAdaptorMenloNetInStatsEntry
    MAX-ACCESS       not-accessible
    STATUS           current
    DESCRIPTION
        "Entry for the cfprApAdaptorMenloNetInStatsTable table."
    INDEX { cfprApAdaptorMenloNetInStatsInstanceId }
    ::= { cfprApAdaptorMenloNetInStatsTable 1 }

CfprApAdaptorMenloNetInStatsEntry ::= SEQUENCE {
    cfprApAdaptorMenloNetInStatsInstanceId                           CfprApManagedObjectId,
    cfprApAdaptorMenloNetInStatsDn                                   CfprApManagedObjectDn,
    cfprApAdaptorMenloNetInStatsRn                                   SnmpAdminString,
    cfprApAdaptorMenloNetInStatsDropFcLifInvalid                     Unsigned64,
    cfprApAdaptorMenloNetInStatsDropFcLifInvalidDelta                Counter64,
    cfprApAdaptorMenloNetInStatsDropFcLifInvalidDeltaAvg             Unsigned64,
    cfprApAdaptorMenloNetInStatsDropFcLifInvalidDeltaMax             Unsigned64,
    cfprApAdaptorMenloNetInStatsDropFcLifInvalidDeltaMin             Unsigned64,
    cfprApAdaptorMenloNetInStatsDropFcMulticast                      Unsigned64,
    cfprApAdaptorMenloNetInStatsDropFcMulticastDelta                 Counter64,
    cfprApAdaptorMenloNetInStatsDropFcMulticastDeltaAvg              Unsigned64,
    cfprApAdaptorMenloNetInStatsDropFcMulticastDeltaMax              Unsigned64,
    cfprApAdaptorMenloNetInStatsDropFcMulticastDeltaMin              Unsigned64,
    cfprApAdaptorMenloNetInStatsDropNullPif                          Unsigned64,
    cfprApAdaptorMenloNetInStatsDropNullPifDelta                     Counter64,
    cfprApAdaptorMenloNetInStatsDropNullPifDeltaAvg                  Unsigned64,
    cfprApAdaptorMenloNetInStatsDropNullPifDeltaMax                  Unsigned64,
    cfprApAdaptorMenloNetInStatsDropNullPifDeltaMin                  Unsigned64,
    cfprApAdaptorMenloNetInStatsFwdLookupNoHit                       Unsigned64,
    cfprApAdaptorMenloNetInStatsFwdLookupNoHitDelta                  Counter64,
    cfprApAdaptorMenloNetInStatsFwdLookupNoHitDeltaAvg               Unsigned64,
    cfprApAdaptorMenloNetInStatsFwdLookupNoHitDeltaMax               Unsigned64,
    cfprApAdaptorMenloNetInStatsFwdLookupNoHitDeltaMin               Unsigned64,
    cfprApAdaptorMenloNetInStatsIntervals                            Gauge32,
    cfprApAdaptorMenloNetInStatsMenloNetIndex                        CfprApAdaptorMenloStatsIndex,
    cfprApAdaptorMenloNetInStatsSuspect                              TruthValue,
    cfprApAdaptorMenloNetInStatsThresholded                          CfprApAdaptorMenloNetInStatsThresholded,
    cfprApAdaptorMenloNetInStatsTimeCollected                        DateAndTime,
    cfprApAdaptorMenloNetInStatsUpdate                               Gauge32
}

cfprApAdaptorMenloNetInStatsInstanceId OBJECT-TYPE
    SYNTAX       CfprApManagedObjectId
    MAX-ACCESS   not-accessible
    STATUS       current
    DESCRIPTION
        "Instance identifier of the managed object."
    ::= { cfprApAdaptorMenloNetInStatsEntry 1 }

cfprApAdaptorMenloNetInStatsDn OBJECT-TYPE
    SYNTAX       CfprApManagedObjectDn
    MAX-ACCESS   read-only
    STATUS       current
    DESCRIPTION
        "Cisco Firepower adaptor:MenloNetInStats:dn managed
        object property"
    ::= { cfprApAdaptorMenloNetInStatsEntry 2 }

cfprApAdaptorMenloNetInStatsRn OBJECT-TYPE
    SYNTAX       SnmpAdminString
    MAX-ACCESS   read-only
    STATUS       current
    DESCRIPTION
        "Cisco Firepower adaptor:MenloNetInStats:rn managed
        object property"
    ::= { cfprApAdaptorMenloNetInStatsEntry 3 }

cfprApAdaptorMenloNetInStatsDropFcLifInvalid OBJECT-TYPE
    SYNTAX       Unsigned64
    MAX-ACCESS   read-only
    STATUS       current
    DESCRIPTION
        "Cisco Firepower adaptor:MenloNetInStats:dropFcLifInvalid
        managed object property"
    ::= { cfprApAdaptorMenloNetInStatsEntry 4 }

cfprApAdaptorMenloNetInStatsDropFcLifInvalidDelta OBJECT-TYPE
    SYNTAX       Counter64
    MAX-ACCESS   read-only
    STATUS       current
    DESCRIPTION
        "Cisco Firepower adaptor:MenloNetInStats:dropFcLifInvalidDelta
        managed object property"
    ::= { cfprApAdaptorMenloNetInStatsEntry 5 }

cfprApAdaptorMenloNetInStatsDropFcLifInvalidDeltaAvg OBJECT-TYPE
    SYNTAX       Unsigned64
    MAX-ACCESS   read-only
    STATUS       current
    DESCRIPTION
        "Cisco Firepower adaptor:MenloNetInStats:dropFcLifInvalidDeltaAvg
        managed object property"
    ::= { cfprApAdaptorMenloNetInStatsEntry 6 }

cfprApAdaptorMenloNetInStatsDropFcLifInvalidDeltaMax OBJECT-TYPE
    SYNTAX       Unsigned64
    MAX-ACCESS   read-only
    STATUS       current
    DESCRIPTION
        "Cisco Firepower adaptor:MenloNetInStats:dropFcLifInvalidDeltaMax
        managed object property"
    ::= { cfprApAdaptorMenloNetInStatsEntry 7 }

cfprApAdaptorMenloNetInStatsDropFcLifInvalidDeltaMin OBJECT-TYPE
    SYNTAX       Unsigned64
    MAX-ACCESS   read-only
    STATUS       current
    DESCRIPTION
        "Cisco Firepower adaptor:MenloNetInStats:dropFcLifInvalidDeltaMin
        managed object property"
    ::= { cfprApAdaptorMenloNetInStatsEntry 8 }

cfprApAdaptorMenloNetInStatsDropFcMulticast OBJECT-TYPE
    SYNTAX       Unsigned64
    MAX-ACCESS   read-only
    STATUS       current
    DESCRIPTION
        "Cisco Firepower adaptor:MenloNetInStats:dropFcMulticast
        managed object property"
    ::= { cfprApAdaptorMenloNetInStatsEntry 9 }

cfprApAdaptorMenloNetInStatsDropFcMulticastDelta OBJECT-TYPE
    SYNTAX       Counter64
    MAX-ACCESS   read-only
    STATUS       current
    DESCRIPTION
        "Cisco Firepower adaptor:MenloNetInStats:dropFcMulticastDelta
        managed object property"
    ::= { cfprApAdaptorMenloNetInStatsEntry 10 }

cfprApAdaptorMenloNetInStatsDropFcMulticastDeltaAvg OBJECT-TYPE
    SYNTAX       Unsigned64
    MAX-ACCESS   read-only
    STATUS       current
    DESCRIPTION
        "Cisco Firepower adaptor:MenloNetInStats:dropFcMulticastDeltaAvg
        managed object property"
    ::= { cfprApAdaptorMenloNetInStatsEntry 11 }

cfprApAdaptorMenloNetInStatsDropFcMulticastDeltaMax OBJECT-TYPE
    SYNTAX       Unsigned64
    MAX-ACCESS   read-only
    STATUS       current
    DESCRIPTION
        "Cisco Firepower adaptor:MenloNetInStats:dropFcMulticastDeltaMax
        managed object property"
    ::= { cfprApAdaptorMenloNetInStatsEntry 12 }

cfprApAdaptorMenloNetInStatsDropFcMulticastDeltaMin OBJECT-TYPE
    SYNTAX       Unsigned64
    MAX-ACCESS   read-only
    STATUS       current
    DESCRIPTION
        "Cisco Firepower adaptor:MenloNetInStats:dropFcMulticastDeltaMin
        managed object property"
    ::= { cfprApAdaptorMenloNetInStatsEntry 13 }

cfprApAdaptorMenloNetInStatsDropNullPif OBJECT-TYPE
    SYNTAX       Unsigned64
    MAX-ACCESS   read-only
    STATUS       current
    DESCRIPTION
        "Cisco Firepower adaptor:MenloNetInStats:dropNullPif
        managed object property"
    ::= { cfprApAdaptorMenloNetInStatsEntry 14 }

cfprApAdaptorMenloNetInStatsDropNullPifDelta OBJECT-TYPE
    SYNTAX       Counter64
    MAX-ACCESS   read-only
    STATUS       current
    DESCRIPTION
        "Cisco Firepower adaptor:MenloNetInStats:dropNullPifDelta
        managed object property"
    ::= { cfprApAdaptorMenloNetInStatsEntry 15 }

cfprApAdaptorMenloNetInStatsDropNullPifDeltaAvg OBJECT-TYPE
    SYNTAX       Unsigned64
    MAX-ACCESS   read-only
    STATUS       current
    DESCRIPTION
        "Cisco Firepower adaptor:MenloNetInStats:dropNullPifDeltaAvg
        managed object property"
    ::= { cfprApAdaptorMenloNetInStatsEntry 16 }

cfprApAdaptorMenloNetInStatsDropNullPifDeltaMax OBJECT-TYPE
    SYNTAX       Unsigned64
    MAX-ACCESS   read-only
    STATUS       current
    DESCRIPTION
        "Cisco Firepower adaptor:MenloNetInStats:dropNullPifDeltaMax
        managed object property"
    ::= { cfprApAdaptorMenloNetInStatsEntry 17 }

cfprApAdaptorMenloNetInStatsDropNullPifDeltaMin OBJECT-TYPE
    SYNTAX       Unsigned64
    MAX-ACCESS   read-only
    STATUS       current
    DESCRIPTION
        "Cisco Firepower adaptor:MenloNetInStats:dropNullPifDeltaMin
        managed object property"
    ::= { cfprApAdaptorMenloNetInStatsEntry 18 }

cfprApAdaptorMenloNetInStatsFwdLookupNoHit OBJECT-TYPE
    SYNTAX       Unsigned64
    MAX-ACCESS   read-only
    STATUS       current
    DESCRIPTION
        "Cisco Firepower adaptor:MenloNetInStats:fwdLookupNoHit
        managed object property"
    ::= { cfprApAdaptorMenloNetInStatsEntry 19 }

cfprApAdaptorMenloNetInStatsFwdLookupNoHitDelta OBJECT-TYPE
    SYNTAX       Counter64
    MAX-ACCESS   read-only
    STATUS       current
    DESCRIPTION
        "Cisco Firepower adaptor:MenloNetInStats:fwdLookupNoHitDelta
        managed object property"
    ::= { cfprApAdaptorMenloNetInStatsEntry 20 }

cfprApAdaptorMenloNetInStatsFwdLookupNoHitDeltaAvg OBJECT-TYPE
    SYNTAX       Unsigned64
    MAX-ACCESS   read-only
    STATUS       current
    DESCRIPTION
        "Cisco Firepower adaptor:MenloNetInStats:fwdLookupNoHitDeltaAvg
        managed object property"
    ::= { cfprApAdaptorMenloNetInStatsEntry 21 }

cfprApAdaptorMenloNetInStatsFwdLookupNoHitDeltaMax OBJECT-TYPE
    SYNTAX       Unsigned64
    MAX-ACCESS   read-only
    STATUS       current
    DESCRIPTION
        "Cisco Firepower adaptor:MenloNetInStats:fwdLookupNoHitDeltaMax
        managed object property"
    ::= { cfprApAdaptorMenloNetInStatsEntry 22 }

cfprApAdaptorMenloNetInStatsFwdLookupNoHitDeltaMin OBJECT-TYPE
    SYNTAX       Unsigned64
    MAX-ACCESS   read-only
    STATUS       current
    DESCRIPTION
        "Cisco Firepower adaptor:MenloNetInStats:fwdLookupNoHitDeltaMin
        managed object property"
    ::= { cfprApAdaptorMenloNetInStatsEntry 23 }

cfprApAdaptorMenloNetInStatsIntervals OBJECT-TYPE
    SYNTAX       Gauge32
    MAX-ACCESS   read-only
    STATUS       current
    DESCRIPTION
        "Cisco Firepower adaptor:MenloNetInStats:intervals
        managed object property"
    ::= { cfprApAdaptorMenloNetInStatsEntry 24 }

cfprApAdaptorMenloNetInStatsMenloNetIndex OBJECT-TYPE
    SYNTAX       CfprApAdaptorMenloStatsIndex
    MAX-ACCESS   read-only
    STATUS       current
    DESCRIPTION
        "Cisco Firepower adaptor:MenloNetInStats:menloNetIndex
        managed object property"
    ::= { cfprApAdaptorMenloNetInStatsEntry 25 }

cfprApAdaptorMenloNetInStatsSuspect OBJECT-TYPE
    SYNTAX       TruthValue
    MAX-ACCESS   read-only
    STATUS       current
    DESCRIPTION
        "Cisco Firepower adaptor:MenloNetInStats:suspect
        managed object property"
    ::= { cfprApAdaptorMenloNetInStatsEntry 26 }

cfprApAdaptorMenloNetInStatsThresholded OBJECT-TYPE
    SYNTAX       CfprApAdaptorMenloNetInStatsThresholded
    MAX-ACCESS   read-only
    STATUS       current
    DESCRIPTION
        "Cisco Firepower adaptor:MenloNetInStats:thresholded
        managed object property"
    ::= { cfprApAdaptorMenloNetInStatsEntry 27 }

cfprApAdaptorMenloNetInStatsTimeCollected OBJECT-TYPE
    SYNTAX       DateAndTime
    MAX-ACCESS   read-only
    STATUS       current
    DESCRIPTION
        "Cisco Firepower adaptor:MenloNetInStats:timeCollected
        managed object property"
    ::= { cfprApAdaptorMenloNetInStatsEntry 28 }

cfprApAdaptorMenloNetInStatsUpdate OBJECT-TYPE
    SYNTAX       Gauge32
    MAX-ACCESS   read-only
    STATUS       current
    DESCRIPTION
        "Cisco Firepower adaptor:MenloNetInStats:update
        managed object property"
    ::= { cfprApAdaptorMenloNetInStatsEntry 29 }

cfprApAdaptorMenloNetInStatsHistTable OBJECT-TYPE
    SYNTAX           SEQUENCE OF CfprApAdaptorMenloNetInStatsHistEntry
    MAX-ACCESS       not-accessible
    STATUS           current
    DESCRIPTION
        "Cisco Firepower adaptor:MenloNetInStatsHist managed object table"
    ::= { cfprApAdaptorObjects 103 }

cfprApAdaptorMenloNetInStatsHistEntry OBJECT-TYPE
    SYNTAX           CfprApAdaptorMenloNetInStatsHistEntry
    MAX-ACCESS       not-accessible
    STATUS           current
    DESCRIPTION
        "Entry for the cfprApAdaptorMenloNetInStatsHistTable table."
    INDEX { cfprApAdaptorMenloNetInStatsHistInstanceId }
    ::= { cfprApAdaptorMenloNetInStatsHistTable 1 }

CfprApAdaptorMenloNetInStatsHistEntry ::= SEQUENCE {
    cfprApAdaptorMenloNetInStatsHistInstanceId                       CfprApManagedObjectId,
    cfprApAdaptorMenloNetInStatsHistDn                               CfprApManagedObjectDn,
    cfprApAdaptorMenloNetInStatsHistRn                               SnmpAdminString,
    cfprApAdaptorMenloNetInStatsHistDropFcLifInvalid                 Unsigned64,
    cfprApAdaptorMenloNetInStatsHistDropFcLifInvalidDelta            Unsigned64,
    cfprApAdaptorMenloNetInStatsHistDropFcLifInvalidDeltaAvg         Unsigned64,
    cfprApAdaptorMenloNetInStatsHistDropFcLifInvalidDeltaMax         Unsigned64,
    cfprApAdaptorMenloNetInStatsHistDropFcLifInvalidDeltaMin         Unsigned64,
    cfprApAdaptorMenloNetInStatsHistDropFcMulticast                  Unsigned64,
    cfprApAdaptorMenloNetInStatsHistDropFcMulticastDelta             Unsigned64,
    cfprApAdaptorMenloNetInStatsHistDropFcMulticastDeltaAvg          Unsigned64,
    cfprApAdaptorMenloNetInStatsHistDropFcMulticastDeltaMax          Unsigned64,
    cfprApAdaptorMenloNetInStatsHistDropFcMulticastDeltaMin          Unsigned64,
    cfprApAdaptorMenloNetInStatsHistDropNullPif                      Unsigned64,
    cfprApAdaptorMenloNetInStatsHistDropNullPifDelta                 Unsigned64,
    cfprApAdaptorMenloNetInStatsHistDropNullPifDeltaAvg              Unsigned64,
    cfprApAdaptorMenloNetInStatsHistDropNullPifDeltaMax              Unsigned64,
    cfprApAdaptorMenloNetInStatsHistDropNullPifDeltaMin              Unsigned64,
    cfprApAdaptorMenloNetInStatsHistFwdLookupNoHit                   Unsigned64,
    cfprApAdaptorMenloNetInStatsHistFwdLookupNoHitDelta              Unsigned64,
    cfprApAdaptorMenloNetInStatsHistFwdLookupNoHitDeltaAvg           Unsigned64,
    cfprApAdaptorMenloNetInStatsHistFwdLookupNoHitDeltaMax           Unsigned64,
    cfprApAdaptorMenloNetInStatsHistFwdLookupNoHitDeltaMin           Unsigned64,
    cfprApAdaptorMenloNetInStatsHistId                               Unsigned64,
    cfprApAdaptorMenloNetInStatsHistMostRecent                       TruthValue,
    cfprApAdaptorMenloNetInStatsHistSuspect                          TruthValue,
    cfprApAdaptorMenloNetInStatsHistThresholded                      CfprApAdaptorMenloNetInStatsHistThresholded,
    cfprApAdaptorMenloNetInStatsHistTimeCollected                    DateAndTime
}

cfprApAdaptorMenloNetInStatsHistInstanceId OBJECT-TYPE
    SYNTAX       CfprApManagedObjectId
    MAX-ACCESS   not-accessible
    STATUS       current
    DESCRIPTION
        "Instance identifier of the managed object."
    ::= { cfprApAdaptorMenloNetInStatsHistEntry 1 }

cfprApAdaptorMenloNetInStatsHistDn OBJECT-TYPE
    SYNTAX       CfprApManagedObjectDn
    MAX-ACCESS   read-only
    STATUS       current
    DESCRIPTION
        "Cisco Firepower adaptor:MenloNetInStatsHist:dn
        managed object property"
    ::= { cfprApAdaptorMenloNetInStatsHistEntry 2 }

cfprApAdaptorMenloNetInStatsHistRn OBJECT-TYPE
    SYNTAX       SnmpAdminString
    MAX-ACCESS   read-only
    STATUS       current
    DESCRIPTION
        "Cisco Firepower adaptor:MenloNetInStatsHist:rn
        managed object property"
    ::= { cfprApAdaptorMenloNetInStatsHistEntry 3 }

cfprApAdaptorMenloNetInStatsHistDropFcLifInvalid OBJECT-TYPE
    SYNTAX       Unsigned64
    MAX-ACCESS   read-only
    STATUS       current
    DESCRIPTION
        "Cisco Firepower adaptor:MenloNetInStatsHist:dropFcLifInvalid
        managed object property"
    ::= { cfprApAdaptorMenloNetInStatsHistEntry 4 }

cfprApAdaptorMenloNetInStatsHistDropFcLifInvalidDelta OBJECT-TYPE
    SYNTAX       Unsigned64
    MAX-ACCESS   read-only
    STATUS       current
    DESCRIPTION
        "Cisco Firepower adaptor:MenloNetInStatsHist:dropFcLifInvalidDelta
         managed object property"
    ::= { cfprApAdaptorMenloNetInStatsHistEntry 5 }

cfprApAdaptorMenloNetInStatsHistDropFcLifInvalidDeltaAvg OBJECT-TYPE
    SYNTAX       Unsigned64
    MAX-ACCESS   read-only
    STATUS       current
    DESCRIPTION
        "Cisco Firepower adaptor:MenloNetInStatsHist:dropFcLifInvalidDelta
        Avg managed object property"
    ::= { cfprApAdaptorMenloNetInStatsHistEntry 6 }

cfprApAdaptorMenloNetInStatsHistDropFcLifInvalidDeltaMax OBJECT-TYPE
    SYNTAX       Unsigned64
    MAX-ACCESS   read-only
    STATUS       current
    DESCRIPTION
        "Cisco Firepower adaptor:MenloNetInStatsHist:dropFcLifInvalidDelta
        Max managed object property"
    ::= { cfprApAdaptorMenloNetInStatsHistEntry 7 }

cfprApAdaptorMenloNetInStatsHistDropFcLifInvalidDeltaMin OBJECT-TYPE
    SYNTAX       Unsigned64
    MAX-ACCESS   read-only
    STATUS       current
    DESCRIPTION
        "Cisco Firepower adaptor:MenloNetInStatsHist:dropFcLifInvalidDelta
        Min managed object property"
    ::= { cfprApAdaptorMenloNetInStatsHistEntry 8 }

cfprApAdaptorMenloNetInStatsHistDropFcMulticast OBJECT-TYPE
    SYNTAX       Unsigned64
    MAX-ACCESS   read-only
    STATUS       current
    DESCRIPTION
        "Cisco Firepower adaptor:MenloNetInStatsHist:dropFcMulticast
        managed object property"
    ::= { cfprApAdaptorMenloNetInStatsHistEntry 9 }

cfprApAdaptorMenloNetInStatsHistDropFcMulticastDelta OBJECT-TYPE
    SYNTAX       Unsigned64
    MAX-ACCESS   read-only
    STATUS       current
    DESCRIPTION
        "Cisco Firepower adaptor:MenloNetInStatsHist:dropFcMulticastDelta
        managed object property"
    ::= { cfprApAdaptorMenloNetInStatsHistEntry 10 }

cfprApAdaptorMenloNetInStatsHistDropFcMulticastDeltaAvg OBJECT-TYPE
    SYNTAX       Unsigned64
    MAX-ACCESS   read-only
    STATUS       current
    DESCRIPTION
        "Cisco Firepower adaptor:MenloNetInStatsHist:dropFcMulticastDeltaA
        vg managed object property"
    ::= { cfprApAdaptorMenloNetInStatsHistEntry 11 }

cfprApAdaptorMenloNetInStatsHistDropFcMulticastDeltaMax OBJECT-TYPE
    SYNTAX       Unsigned64
    MAX-ACCESS   read-only
    STATUS       current
    DESCRIPTION
        "Cisco Firepower adaptor:MenloNetInStatsHist:dropFcMulticastDeltaM
        ax managed object property"
    ::= { cfprApAdaptorMenloNetInStatsHistEntry 12 }

cfprApAdaptorMenloNetInStatsHistDropFcMulticastDeltaMin OBJECT-TYPE
    SYNTAX       Unsigned64
    MAX-ACCESS   read-only
    STATUS       current
    DESCRIPTION
        "Cisco Firepower adaptor:MenloNetInStatsHist:dropFcMulticastDeltaM
        in managed object property"
    ::= { cfprApAdaptorMenloNetInStatsHistEntry 13 }

cfprApAdaptorMenloNetInStatsHistDropNullPif OBJECT-TYPE
    SYNTAX       Unsigned64
    MAX-ACCESS   read-only
    STATUS       current
    DESCRIPTION
        "Cisco Firepower adaptor:MenloNetInStatsHist:dropNullPif
        managed object property"
    ::= { cfprApAdaptorMenloNetInStatsHistEntry 14 }

cfprApAdaptorMenloNetInStatsHistDropNullPifDelta OBJECT-TYPE
    SYNTAX       Unsigned64
    MAX-ACCESS   read-only
    STATUS       current
    DESCRIPTION
        "Cisco Firepower adaptor:MenloNetInStatsHist:dropNullPifDelta
        managed object property"
    ::= { cfprApAdaptorMenloNetInStatsHistEntry 15 }

cfprApAdaptorMenloNetInStatsHistDropNullPifDeltaAvg OBJECT-TYPE
    SYNTAX       Unsigned64
    MAX-ACCESS   read-only
    STATUS       current
    DESCRIPTION
        "Cisco Firepower adaptor:MenloNetInStatsHist:dropNullPifDeltaAvg
        managed object property"
    ::= { cfprApAdaptorMenloNetInStatsHistEntry 16 }

cfprApAdaptorMenloNetInStatsHistDropNullPifDeltaMax OBJECT-TYPE
    SYNTAX       Unsigned64
    MAX-ACCESS   read-only
    STATUS       current
    DESCRIPTION
        "Cisco Firepower adaptor:MenloNetInStatsHist:dropNullPifDeltaMax
        managed object property"
    ::= { cfprApAdaptorMenloNetInStatsHistEntry 17 }

cfprApAdaptorMenloNetInStatsHistDropNullPifDeltaMin OBJECT-TYPE
    SYNTAX       Unsigned64
    MAX-ACCESS   read-only
    STATUS       current
    DESCRIPTION
        "Cisco Firepower adaptor:MenloNetInStatsHist:dropNullPifDeltaMin
        managed object property"
    ::= { cfprApAdaptorMenloNetInStatsHistEntry 18 }

cfprApAdaptorMenloNetInStatsHistFwdLookupNoHit OBJECT-TYPE
    SYNTAX       Unsigned64
    MAX-ACCESS   read-only
    STATUS       current
    DESCRIPTION
        "Cisco Firepower adaptor:MenloNetInStatsHist:fwdLookupNoHit
        managed object property"
    ::= { cfprApAdaptorMenloNetInStatsHistEntry 19 }

cfprApAdaptorMenloNetInStatsHistFwdLookupNoHitDelta OBJECT-TYPE
    SYNTAX       Unsigned64
    MAX-ACCESS   read-only
    STATUS       current
    DESCRIPTION
        "Cisco Firepower adaptor:MenloNetInStatsHist:fwdLookupNoHitDelta
        managed object property"
    ::= { cfprApAdaptorMenloNetInStatsHistEntry 20 }

cfprApAdaptorMenloNetInStatsHistFwdLookupNoHitDeltaAvg OBJECT-TYPE
    SYNTAX       Unsigned64
    MAX-ACCESS   read-only
    STATUS       current
    DESCRIPTION
        "Cisco Firepower adaptor:MenloNetInStatsHist:fwdLookupNoHitDeltaAv
        g managed object property"
    ::= { cfprApAdaptorMenloNetInStatsHistEntry 21 }

cfprApAdaptorMenloNetInStatsHistFwdLookupNoHitDeltaMax OBJECT-TYPE
    SYNTAX       Unsigned64
    MAX-ACCESS   read-only
    STATUS       current
    DESCRIPTION
        "Cisco Firepower adaptor:MenloNetInStatsHist:fwdLookupNoHitDeltaMa
        x managed object property"
    ::= { cfprApAdaptorMenloNetInStatsHistEntry 22 }

cfprApAdaptorMenloNetInStatsHistFwdLookupNoHitDeltaMin OBJECT-TYPE
    SYNTAX       Unsigned64
    MAX-ACCESS   read-only
    STATUS       current
    DESCRIPTION
        "Cisco Firepower adaptor:MenloNetInStatsHist:fwdLookupNoHitDeltaMi
        n managed object property"
    ::= { cfprApAdaptorMenloNetInStatsHistEntry 23 }

cfprApAdaptorMenloNetInStatsHistId OBJECT-TYPE
    SYNTAX       Unsigned64
    MAX-ACCESS   read-only
    STATUS       current
    DESCRIPTION
        "Cisco Firepower adaptor:MenloNetInStatsHist:id
        managed object property"
    ::= { cfprApAdaptorMenloNetInStatsHistEntry 24 }

cfprApAdaptorMenloNetInStatsHistMostRecent OBJECT-TYPE
    SYNTAX       TruthValue
    MAX-ACCESS   read-only
    STATUS       current
    DESCRIPTION
        "Cisco Firepower adaptor:MenloNetInStatsHist:mostRecent
        managed object property"
    ::= { cfprApAdaptorMenloNetInStatsHistEntry 25 }

cfprApAdaptorMenloNetInStatsHistSuspect OBJECT-TYPE
    SYNTAX       TruthValue
    MAX-ACCESS   read-only
    STATUS       current
    DESCRIPTION
        "Cisco Firepower adaptor:MenloNetInStatsHist:suspect
        managed object property"
    ::= { cfprApAdaptorMenloNetInStatsHistEntry 26 }

cfprApAdaptorMenloNetInStatsHistThresholded OBJECT-TYPE
    SYNTAX       CfprApAdaptorMenloNetInStatsHistThresholded
    MAX-ACCESS   read-only
    STATUS       current
    DESCRIPTION
        "Cisco Firepower adaptor:MenloNetInStatsHist:thresholded
        managed object property"
    ::= { cfprApAdaptorMenloNetInStatsHistEntry 27 }

cfprApAdaptorMenloNetInStatsHistTimeCollected OBJECT-TYPE
    SYNTAX       DateAndTime
    MAX-ACCESS   read-only
    STATUS       current
    DESCRIPTION
        "Cisco Firepower adaptor:MenloNetInStatsHist:timeCollected
        managed object property"
    ::= { cfprApAdaptorMenloNetInStatsHistEntry 28 }

cfprApAdaptorMenloQErrorStatsTable OBJECT-TYPE
    SYNTAX           SEQUENCE OF CfprApAdaptorMenloQErrorStatsEntry
    MAX-ACCESS       not-accessible
    STATUS           current
    DESCRIPTION
        "Cisco Firepower adaptor:MenloQErrorStats managed object table"
    ::= { cfprApAdaptorObjects 104 }

cfprApAdaptorMenloQErrorStatsEntry OBJECT-TYPE
    SYNTAX           CfprApAdaptorMenloQErrorStatsEntry
    MAX-ACCESS       not-accessible
    STATUS           current
    DESCRIPTION
        "Entry for the cfprApAdaptorMenloQErrorStatsTable table."
    INDEX { cfprApAdaptorMenloQErrorStatsInstanceId }
    ::= { cfprApAdaptorMenloQErrorStatsTable 1 }

CfprApAdaptorMenloQErrorStatsEntry ::= SEQUENCE {
    cfprApAdaptorMenloQErrorStatsInstanceId                          CfprApManagedObjectId,
    cfprApAdaptorMenloQErrorStatsDn                                  CfprApManagedObjectDn,
    cfprApAdaptorMenloQErrorStatsRn                                  SnmpAdminString,
    cfprApAdaptorMenloQErrorStatsCorrectableErrors                   Unsigned64,
    cfprApAdaptorMenloQErrorStatsCorrectableErrorsDelta              Counter64,
    cfprApAdaptorMenloQErrorStatsCorrectableErrorsDeltaAvg           Unsigned64,
    cfprApAdaptorMenloQErrorStatsCorrectableErrorsDeltaMax           Unsigned64,
    cfprApAdaptorMenloQErrorStatsCorrectableErrorsDeltaMin           Unsigned64,
    cfprApAdaptorMenloQErrorStatsIntervals                           Gauge32,
    cfprApAdaptorMenloQErrorStatsMenloQueueComponent                 CfprApAdaptorMenloQueueStatsComponent,
    cfprApAdaptorMenloQErrorStatsMenloQueueIndex                     CfprApAdaptorMenloStatsIndex,
    cfprApAdaptorMenloQErrorStatsPopErrors                           Unsigned64,
    cfprApAdaptorMenloQErrorStatsPopErrorsDelta                      Counter64,
    cfprApAdaptorMenloQErrorStatsPopErrorsDeltaAvg                   Unsigned64,
    cfprApAdaptorMenloQErrorStatsPopErrorsDeltaMax                   Unsigned64,
    cfprApAdaptorMenloQErrorStatsPopErrorsDeltaMin                   Unsigned64,
    cfprApAdaptorMenloQErrorStatsPushErrors                          Unsigned64,
    cfprApAdaptorMenloQErrorStatsPushErrorsDelta                     Counter64,
    cfprApAdaptorMenloQErrorStatsPushErrorsDeltaAvg                  Unsigned64,
    cfprApAdaptorMenloQErrorStatsPushErrorsDeltaMax                  Unsigned64,
    cfprApAdaptorMenloQErrorStatsPushErrorsDeltaMin                  Unsigned64,
    cfprApAdaptorMenloQErrorStatsSuspect                             TruthValue,
    cfprApAdaptorMenloQErrorStatsThresholded                         CfprApAdaptorMenloQErrorStatsThresholded,
    cfprApAdaptorMenloQErrorStatsTimeCollected                       DateAndTime,
    cfprApAdaptorMenloQErrorStatsUncorrectableErrors                 Unsigned64,
    cfprApAdaptorMenloQErrorStatsUncorrectableErrorsDelta            Counter64,
    cfprApAdaptorMenloQErrorStatsUncorrectableErrorsDeltaAvg         Unsigned64,
    cfprApAdaptorMenloQErrorStatsUncorrectableErrorsDeltaMax         Unsigned64,
    cfprApAdaptorMenloQErrorStatsUncorrectableErrorsDeltaMin         Unsigned64,
    cfprApAdaptorMenloQErrorStatsUpdate                              Gauge32
}

cfprApAdaptorMenloQErrorStatsInstanceId OBJECT-TYPE
    SYNTAX       CfprApManagedObjectId
    MAX-ACCESS   not-accessible
    STATUS       current
    DESCRIPTION
        "Instance identifier of the managed object."
    ::= { cfprApAdaptorMenloQErrorStatsEntry 1 }

cfprApAdaptorMenloQErrorStatsDn OBJECT-TYPE
    SYNTAX       CfprApManagedObjectDn
    MAX-ACCESS   read-only
    STATUS       current
    DESCRIPTION
        "Cisco Firepower adaptor:MenloQErrorStats:dn managed
        object property"
    ::= { cfprApAdaptorMenloQErrorStatsEntry 2 }

cfprApAdaptorMenloQErrorStatsRn OBJECT-TYPE
    SYNTAX       SnmpAdminString
    MAX-ACCESS   read-only
    STATUS       current
    DESCRIPTION
        "Cisco Firepower adaptor:MenloQErrorStats:rn managed
        object property"
    ::= { cfprApAdaptorMenloQErrorStatsEntry 3 }

cfprApAdaptorMenloQErrorStatsCorrectableErrors OBJECT-TYPE
    SYNTAX       Unsigned64
    MAX-ACCESS   read-only
    STATUS       current
    DESCRIPTION
        "Cisco Firepower adaptor:MenloQErrorStats:correctableErrors
        managed object property"
    ::= { cfprApAdaptorMenloQErrorStatsEntry 4 }

cfprApAdaptorMenloQErrorStatsCorrectableErrorsDelta OBJECT-TYPE
    SYNTAX       Counter64
    MAX-ACCESS   read-only
    STATUS       current
    DESCRIPTION
        "Cisco Firepower adaptor:MenloQErrorStats:correctableErrorsDelta
        managed object property"
    ::= { cfprApAdaptorMenloQErrorStatsEntry 5 }

cfprApAdaptorMenloQErrorStatsCorrectableErrorsDeltaAvg OBJECT-TYPE
    SYNTAX       Unsigned64
    MAX-ACCESS   read-only
    STATUS       current
    DESCRIPTION
        "Cisco Firepower adaptor:MenloQErrorStats:correctableErrorsDeltaAv
        g managed object property"
    ::= { cfprApAdaptorMenloQErrorStatsEntry 6 }

cfprApAdaptorMenloQErrorStatsCorrectableErrorsDeltaMax OBJECT-TYPE
    SYNTAX       Unsigned64
    MAX-ACCESS   read-only
    STATUS       current
    DESCRIPTION
        "Cisco Firepower adaptor:MenloQErrorStats:correctableErrorsDeltaMa
        x managed object property"
    ::= { cfprApAdaptorMenloQErrorStatsEntry 7 }

cfprApAdaptorMenloQErrorStatsCorrectableErrorsDeltaMin OBJECT-TYPE
    SYNTAX       Unsigned64
    MAX-ACCESS   read-only
    STATUS       current
    DESCRIPTION
        "Cisco Firepower adaptor:MenloQErrorStats:correctableErrorsDeltaMi
        n managed object property"
    ::= { cfprApAdaptorMenloQErrorStatsEntry 8 }

cfprApAdaptorMenloQErrorStatsIntervals OBJECT-TYPE
    SYNTAX       Gauge32
    MAX-ACCESS   read-only
    STATUS       current
    DESCRIPTION
        "Cisco Firepower adaptor:MenloQErrorStats:intervals
        managed object property"
    ::= { cfprApAdaptorMenloQErrorStatsEntry 9 }

cfprApAdaptorMenloQErrorStatsMenloQueueComponent OBJECT-TYPE
    SYNTAX       CfprApAdaptorMenloQueueStatsComponent
    MAX-ACCESS   read-only
    STATUS       current
    DESCRIPTION
        "Cisco Firepower adaptor:MenloQErrorStats:menloQueueComponent
        managed object property"
    ::= { cfprApAdaptorMenloQErrorStatsEntry 10 }

cfprApAdaptorMenloQErrorStatsMenloQueueIndex OBJECT-TYPE
    SYNTAX       CfprApAdaptorMenloStatsIndex
    MAX-ACCESS   read-only
    STATUS       current
    DESCRIPTION
        "Cisco Firepower adaptor:MenloQErrorStats:menloQueueIndex
        managed object property"
    ::= { cfprApAdaptorMenloQErrorStatsEntry 11 }

cfprApAdaptorMenloQErrorStatsPopErrors OBJECT-TYPE
    SYNTAX       Unsigned64
    MAX-ACCESS   read-only
    STATUS       current
    DESCRIPTION
        "Cisco Firepower adaptor:MenloQErrorStats:popErrors
        managed object property"
    ::= { cfprApAdaptorMenloQErrorStatsEntry 12 }

cfprApAdaptorMenloQErrorStatsPopErrorsDelta OBJECT-TYPE
    SYNTAX       Counter64
    MAX-ACCESS   read-only
    STATUS       current
    DESCRIPTION
        "Cisco Firepower adaptor:MenloQErrorStats:popErrorsDelta
        managed object property"
    ::= { cfprApAdaptorMenloQErrorStatsEntry 13 }

cfprApAdaptorMenloQErrorStatsPopErrorsDeltaAvg OBJECT-TYPE
    SYNTAX       Unsigned64
    MAX-ACCESS   read-only
    STATUS       current
    DESCRIPTION
        "Cisco Firepower adaptor:MenloQErrorStats:popErrorsDeltaAvg
        managed object property"
    ::= { cfprApAdaptorMenloQErrorStatsEntry 14 }

cfprApAdaptorMenloQErrorStatsPopErrorsDeltaMax OBJECT-TYPE
    SYNTAX       Unsigned64
    MAX-ACCESS   read-only
    STATUS       current
    DESCRIPTION
        "Cisco Firepower adaptor:MenloQErrorStats:popErrorsDeltaMax
        managed object property"
    ::= { cfprApAdaptorMenloQErrorStatsEntry 15 }

cfprApAdaptorMenloQErrorStatsPopErrorsDeltaMin OBJECT-TYPE
    SYNTAX       Unsigned64
    MAX-ACCESS   read-only
    STATUS       current
    DESCRIPTION
        "Cisco Firepower adaptor:MenloQErrorStats:popErrorsDeltaMin
        managed object property"
    ::= { cfprApAdaptorMenloQErrorStatsEntry 16 }

cfprApAdaptorMenloQErrorStatsPushErrors OBJECT-TYPE
    SYNTAX       Unsigned64
    MAX-ACCESS   read-only
    STATUS       current
    DESCRIPTION
        "Cisco Firepower adaptor:MenloQErrorStats:pushErrors
        managed object property"
    ::= { cfprApAdaptorMenloQErrorStatsEntry 17 }

cfprApAdaptorMenloQErrorStatsPushErrorsDelta OBJECT-TYPE
    SYNTAX       Counter64
    MAX-ACCESS   read-only
    STATUS       current
    DESCRIPTION
        "Cisco Firepower adaptor:MenloQErrorStats:pushErrorsDelta
        managed object property"
    ::= { cfprApAdaptorMenloQErrorStatsEntry 18 }

cfprApAdaptorMenloQErrorStatsPushErrorsDeltaAvg OBJECT-TYPE
    SYNTAX       Unsigned64
    MAX-ACCESS   read-only
    STATUS       current
    DESCRIPTION
        "Cisco Firepower adaptor:MenloQErrorStats:pushErrorsDeltaAvg
        managed object property"
    ::= { cfprApAdaptorMenloQErrorStatsEntry 19 }

cfprApAdaptorMenloQErrorStatsPushErrorsDeltaMax OBJECT-TYPE
    SYNTAX       Unsigned64
    MAX-ACCESS   read-only
    STATUS       current
    DESCRIPTION
        "Cisco Firepower adaptor:MenloQErrorStats:pushErrorsDeltaMax
        managed object property"
    ::= { cfprApAdaptorMenloQErrorStatsEntry 20 }

cfprApAdaptorMenloQErrorStatsPushErrorsDeltaMin OBJECT-TYPE
    SYNTAX       Unsigned64
    MAX-ACCESS   read-only
    STATUS       current
    DESCRIPTION
        "Cisco Firepower adaptor:MenloQErrorStats:pushErrorsDeltaMin
        managed object property"
    ::= { cfprApAdaptorMenloQErrorStatsEntry 21 }

cfprApAdaptorMenloQErrorStatsSuspect OBJECT-TYPE
    SYNTAX       TruthValue
    MAX-ACCESS   read-only
    STATUS       current
    DESCRIPTION
        "Cisco Firepower adaptor:MenloQErrorStats:suspect
        managed object property"
    ::= { cfprApAdaptorMenloQErrorStatsEntry 22 }

cfprApAdaptorMenloQErrorStatsThresholded OBJECT-TYPE
    SYNTAX       CfprApAdaptorMenloQErrorStatsThresholded
    MAX-ACCESS   read-only
    STATUS       current
    DESCRIPTION
        "Cisco Firepower adaptor:MenloQErrorStats:thresholded
        managed object property"
    ::= { cfprApAdaptorMenloQErrorStatsEntry 23 }

cfprApAdaptorMenloQErrorStatsTimeCollected OBJECT-TYPE
    SYNTAX       DateAndTime
    MAX-ACCESS   read-only
    STATUS       current
    DESCRIPTION
        "Cisco Firepower adaptor:MenloQErrorStats:timeCollected
        managed object property"
    ::= { cfprApAdaptorMenloQErrorStatsEntry 24 }

cfprApAdaptorMenloQErrorStatsUncorrectableErrors OBJECT-TYPE
    SYNTAX       Unsigned64
    MAX-ACCESS   read-only
    STATUS       current
    DESCRIPTION
        "Cisco Firepower adaptor:MenloQErrorStats:uncorrectableErrors
        managed object property"
    ::= { cfprApAdaptorMenloQErrorStatsEntry 25 }

cfprApAdaptorMenloQErrorStatsUncorrectableErrorsDelta OBJECT-TYPE
    SYNTAX       Counter64
    MAX-ACCESS   read-only
    STATUS       current
    DESCRIPTION
        "Cisco Firepower adaptor:MenloQErrorStats:uncorrectableErrorsDelta
         managed object property"
    ::= { cfprApAdaptorMenloQErrorStatsEntry 26 }

cfprApAdaptorMenloQErrorStatsUncorrectableErrorsDeltaAvg OBJECT-TYPE
    SYNTAX       Unsigned64
    MAX-ACCESS   read-only
    STATUS       current
    DESCRIPTION
        "Cisco Firepower adaptor:MenloQErrorStats:uncorrectableErrorsDelta
        Avg managed object property"
    ::= { cfprApAdaptorMenloQErrorStatsEntry 27 }

cfprApAdaptorMenloQErrorStatsUncorrectableErrorsDeltaMax OBJECT-TYPE
    SYNTAX       Unsigned64
    MAX-ACCESS   read-only
    STATUS       current
    DESCRIPTION
        "Cisco Firepower adaptor:MenloQErrorStats:uncorrectableErrorsDelta
        Max managed object property"
    ::= { cfprApAdaptorMenloQErrorStatsEntry 28 }

cfprApAdaptorMenloQErrorStatsUncorrectableErrorsDeltaMin OBJECT-TYPE
    SYNTAX       Unsigned64
    MAX-ACCESS   read-only
    STATUS       current
    DESCRIPTION
        "Cisco Firepower adaptor:MenloQErrorStats:uncorrectableErrorsDelta
        Min managed object property"
    ::= { cfprApAdaptorMenloQErrorStatsEntry 29 }

cfprApAdaptorMenloQErrorStatsUpdate OBJECT-TYPE
    SYNTAX       Gauge32
    MAX-ACCESS   read-only
    STATUS       current
    DESCRIPTION
        "Cisco Firepower adaptor:MenloQErrorStats:update
        managed object property"
    ::= { cfprApAdaptorMenloQErrorStatsEntry 30 }

cfprApAdaptorMenloQErrorStatsHistTable OBJECT-TYPE
    SYNTAX           SEQUENCE OF CfprApAdaptorMenloQErrorStatsHistEntry
    MAX-ACCESS       not-accessible
    STATUS           current
    DESCRIPTION
        "Cisco Firepower adaptor:MenloQErrorStatsHist managed
        object table"
    ::= { cfprApAdaptorObjects 105 }

cfprApAdaptorMenloQErrorStatsHistEntry OBJECT-TYPE
    SYNTAX           CfprApAdaptorMenloQErrorStatsHistEntry
    MAX-ACCESS       not-accessible
    STATUS           current
    DESCRIPTION
        "Entry for the cfprApAdaptorMenloQErrorStatsHistTable table."
    INDEX { cfprApAdaptorMenloQErrorStatsHistInstanceId }
    ::= { cfprApAdaptorMenloQErrorStatsHistTable 1 }

CfprApAdaptorMenloQErrorStatsHistEntry ::= SEQUENCE {
    cfprApAdaptorMenloQErrorStatsHistInstanceId                      CfprApManagedObjectId,
    cfprApAdaptorMenloQErrorStatsHistDn                              CfprApManagedObjectDn,
    cfprApAdaptorMenloQErrorStatsHistRn                              SnmpAdminString,
    cfprApAdaptorMenloQErrorStatsHistCorrectableErrors               Unsigned64,
    cfprApAdaptorMenloQErrorStatsHistCorrectableErrorsDelta          Unsigned64,
    cfprApAdaptorMenloQErrorStatsHistCorrectableErrorsDeltaAvg       Unsigned64,
    cfprApAdaptorMenloQErrorStatsHistCorrectableErrorsDeltaMax       Unsigned64,
    cfprApAdaptorMenloQErrorStatsHistCorrectableErrorsDeltaMin       Unsigned64,
    cfprApAdaptorMenloQErrorStatsHistId                              Unsigned64,
    cfprApAdaptorMenloQErrorStatsHistMostRecent                      TruthValue,
    cfprApAdaptorMenloQErrorStatsHistPopErrors                       Unsigned64,
    cfprApAdaptorMenloQErrorStatsHistPopErrorsDelta                  Unsigned64,
    cfprApAdaptorMenloQErrorStatsHistPopErrorsDeltaAvg               Unsigned64,
    cfprApAdaptorMenloQErrorStatsHistPopErrorsDeltaMax               Unsigned64,
    cfprApAdaptorMenloQErrorStatsHistPopErrorsDeltaMin               Unsigned64,
    cfprApAdaptorMenloQErrorStatsHistPushErrors                      Unsigned64,
    cfprApAdaptorMenloQErrorStatsHistPushErrorsDelta                 Unsigned64,
    cfprApAdaptorMenloQErrorStatsHistPushErrorsDeltaAvg              Unsigned64,
    cfprApAdaptorMenloQErrorStatsHistPushErrorsDeltaMax              Unsigned64,
    cfprApAdaptorMenloQErrorStatsHistPushErrorsDeltaMin              Unsigned64,
    cfprApAdaptorMenloQErrorStatsHistSuspect                         TruthValue,
    cfprApAdaptorMenloQErrorStatsHistThresholded                     CfprApAdaptorMenloQErrorStatsHistThresholded,
    cfprApAdaptorMenloQErrorStatsHistTimeCollected                   DateAndTime,
    cfprApAdaptorMenloQErrorStatsHistUncorrectableErrors             Unsigned64,
    cfprApAdaptorMenloQErrorStatsHistUncorrectableErrorsDelta        Unsigned64,
    cfprApAdaptorMenloQErrorStatsHistUncorrectableErrorsDeltaAvg     Unsigned64,
    cfprApAdaptorMenloQErrorStatsHistUncorrectableErrorsDeltaMax     Unsigned64,
    cfprApAdaptorMenloQErrorStatsHistUncorrectableErrorsDeltaMin     Unsigned64
}

cfprApAdaptorMenloQErrorStatsHistInstanceId OBJECT-TYPE
    SYNTAX       CfprApManagedObjectId
    MAX-ACCESS   not-accessible
    STATUS       current
    DESCRIPTION
        "Instance identifier of the managed object."
    ::= { cfprApAdaptorMenloQErrorStatsHistEntry 1 }

cfprApAdaptorMenloQErrorStatsHistDn OBJECT-TYPE
    SYNTAX       CfprApManagedObjectDn
    MAX-ACCESS   read-only
    STATUS       current
    DESCRIPTION
        "Cisco Firepower adaptor:MenloQErrorStatsHist:dn
        managed object property"
    ::= { cfprApAdaptorMenloQErrorStatsHistEntry 2 }

cfprApAdaptorMenloQErrorStatsHistRn OBJECT-TYPE
    SYNTAX       SnmpAdminString
    MAX-ACCESS   read-only
    STATUS       current
    DESCRIPTION
        "Cisco Firepower adaptor:MenloQErrorStatsHist:rn
        managed object property"
    ::= { cfprApAdaptorMenloQErrorStatsHistEntry 3 }

cfprApAdaptorMenloQErrorStatsHistCorrectableErrors OBJECT-TYPE
    SYNTAX       Unsigned64
    MAX-ACCESS   read-only
    STATUS       current
    DESCRIPTION
        "Cisco Firepower adaptor:MenloQErrorStatsHist:correctableErrors
        managed object property"
    ::= { cfprApAdaptorMenloQErrorStatsHistEntry 4 }

cfprApAdaptorMenloQErrorStatsHistCorrectableErrorsDelta OBJECT-TYPE
    SYNTAX       Unsigned64
    MAX-ACCESS   read-only
    STATUS       current
    DESCRIPTION
        "Cisco Firepower adaptor:MenloQErrorStatsHist:correctableErrorsDel
        ta managed object property"
    ::= { cfprApAdaptorMenloQErrorStatsHistEntry 5 }

cfprApAdaptorMenloQErrorStatsHistCorrectableErrorsDeltaAvg OBJECT-TYPE
    SYNTAX       Unsigned64
    MAX-ACCESS   read-only
    STATUS       current
    DESCRIPTION
        "Cisco Firepower adaptor:MenloQErrorStatsHist:correctableErrorsDel
        taAvg managed object property"
    ::= { cfprApAdaptorMenloQErrorStatsHistEntry 6 }

cfprApAdaptorMenloQErrorStatsHistCorrectableErrorsDeltaMax OBJECT-TYPE
    SYNTAX       Unsigned64
    MAX-ACCESS   read-only
    STATUS       current
    DESCRIPTION
        "Cisco Firepower adaptor:MenloQErrorStatsHist:correctableErrorsDel
        taMax managed object property"
    ::= { cfprApAdaptorMenloQErrorStatsHistEntry 7 }

cfprApAdaptorMenloQErrorStatsHistCorrectableErrorsDeltaMin OBJECT-TYPE
    SYNTAX       Unsigned64
    MAX-ACCESS   read-only
    STATUS       current
    DESCRIPTION
        "Cisco Firepower adaptor:MenloQErrorStatsHist:correctableErrorsDel
        taMin managed object property"
    ::= { cfprApAdaptorMenloQErrorStatsHistEntry 8 }

cfprApAdaptorMenloQErrorStatsHistId OBJECT-TYPE
    SYNTAX       Unsigned64
    MAX-ACCESS   read-only
    STATUS       current
    DESCRIPTION
        "Cisco Firepower adaptor:MenloQErrorStatsHist:id
        managed object property"
    ::= { cfprApAdaptorMenloQErrorStatsHistEntry 9 }

cfprApAdaptorMenloQErrorStatsHistMostRecent OBJECT-TYPE
    SYNTAX       TruthValue
    MAX-ACCESS   read-only
    STATUS       current
    DESCRIPTION
        "Cisco Firepower adaptor:MenloQErrorStatsHist:mostRecent
        managed object property"
    ::= { cfprApAdaptorMenloQErrorStatsHistEntry 10 }

cfprApAdaptorMenloQErrorStatsHistPopErrors OBJECT-TYPE
    SYNTAX       Unsigned64
    MAX-ACCESS   read-only
    STATUS       current
    DESCRIPTION
        "Cisco Firepower adaptor:MenloQErrorStatsHist:popErrors
        managed object property"
    ::= { cfprApAdaptorMenloQErrorStatsHistEntry 11 }

cfprApAdaptorMenloQErrorStatsHistPopErrorsDelta OBJECT-TYPE
    SYNTAX       Unsigned64
    MAX-ACCESS   read-only
    STATUS       current
    DESCRIPTION
        "Cisco Firepower adaptor:MenloQErrorStatsHist:popErrorsDelta
        managed object property"
    ::= { cfprApAdaptorMenloQErrorStatsHistEntry 12 }

cfprApAdaptorMenloQErrorStatsHistPopErrorsDeltaAvg OBJECT-TYPE
    SYNTAX       Unsigned64
    MAX-ACCESS   read-only
    STATUS       current
    DESCRIPTION
        "Cisco Firepower adaptor:MenloQErrorStatsHist:popErrorsDeltaAvg
        managed object property"
    ::= { cfprApAdaptorMenloQErrorStatsHistEntry 13 }

cfprApAdaptorMenloQErrorStatsHistPopErrorsDeltaMax OBJECT-TYPE
    SYNTAX       Unsigned64
    MAX-ACCESS   read-only
    STATUS       current
    DESCRIPTION
        "Cisco Firepower adaptor:MenloQErrorStatsHist:popErrorsDeltaMax
        managed object property"
    ::= { cfprApAdaptorMenloQErrorStatsHistEntry 14 }

cfprApAdaptorMenloQErrorStatsHistPopErrorsDeltaMin OBJECT-TYPE
    SYNTAX       Unsigned64
    MAX-ACCESS   read-only
    STATUS       current
    DESCRIPTION
        "Cisco Firepower adaptor:MenloQErrorStatsHist:popErrorsDeltaMin
        managed object property"
    ::= { cfprApAdaptorMenloQErrorStatsHistEntry 15 }

cfprApAdaptorMenloQErrorStatsHistPushErrors OBJECT-TYPE
    SYNTAX       Unsigned64
    MAX-ACCESS   read-only
    STATUS       current
    DESCRIPTION
        "Cisco Firepower adaptor:MenloQErrorStatsHist:pushErrors
        managed object property"
    ::= { cfprApAdaptorMenloQErrorStatsHistEntry 16 }

cfprApAdaptorMenloQErrorStatsHistPushErrorsDelta OBJECT-TYPE
    SYNTAX       Unsigned64
    MAX-ACCESS   read-only
    STATUS       current
    DESCRIPTION
        "Cisco Firepower adaptor:MenloQErrorStatsHist:pushErrorsDelta
        managed object property"
    ::= { cfprApAdaptorMenloQErrorStatsHistEntry 17 }

cfprApAdaptorMenloQErrorStatsHistPushErrorsDeltaAvg OBJECT-TYPE
    SYNTAX       Unsigned64
    MAX-ACCESS   read-only
    STATUS       current
    DESCRIPTION
        "Cisco Firepower adaptor:MenloQErrorStatsHist:pushErrorsDeltaAvg
        managed object property"
    ::= { cfprApAdaptorMenloQErrorStatsHistEntry 18 }

cfprApAdaptorMenloQErrorStatsHistPushErrorsDeltaMax OBJECT-TYPE
    SYNTAX       Unsigned64
    MAX-ACCESS   read-only
    STATUS       current
    DESCRIPTION
        "Cisco Firepower adaptor:MenloQErrorStatsHist:pushErrorsDeltaMax
        managed object property"
    ::= { cfprApAdaptorMenloQErrorStatsHistEntry 19 }

cfprApAdaptorMenloQErrorStatsHistPushErrorsDeltaMin OBJECT-TYPE
    SYNTAX       Unsigned64
    MAX-ACCESS   read-only
    STATUS       current
    DESCRIPTION
        "Cisco Firepower adaptor:MenloQErrorStatsHist:pushErrorsDeltaMin
        managed object property"
    ::= { cfprApAdaptorMenloQErrorStatsHistEntry 20 }

cfprApAdaptorMenloQErrorStatsHistSuspect OBJECT-TYPE
    SYNTAX       TruthValue
    MAX-ACCESS   read-only
    STATUS       current
    DESCRIPTION
        "Cisco Firepower adaptor:MenloQErrorStatsHist:suspect
        managed object property"
    ::= { cfprApAdaptorMenloQErrorStatsHistEntry 21 }

cfprApAdaptorMenloQErrorStatsHistThresholded OBJECT-TYPE
    SYNTAX       CfprApAdaptorMenloQErrorStatsHistThresholded
    MAX-ACCESS   read-only
    STATUS       current
    DESCRIPTION
        "Cisco Firepower adaptor:MenloQErrorStatsHist:thresholded
        managed object property"
    ::= { cfprApAdaptorMenloQErrorStatsHistEntry 22 }

cfprApAdaptorMenloQErrorStatsHistTimeCollected OBJECT-TYPE
    SYNTAX       DateAndTime
    MAX-ACCESS   read-only
    STATUS       current
    DESCRIPTION
        "Cisco Firepower adaptor:MenloQErrorStatsHist:timeCollected
        managed object property"
    ::= { cfprApAdaptorMenloQErrorStatsHistEntry 23 }

cfprApAdaptorMenloQErrorStatsHistUncorrectableErrors OBJECT-TYPE
    SYNTAX       Unsigned64
    MAX-ACCESS   read-only
    STATUS       current
    DESCRIPTION
        "Cisco Firepower adaptor:MenloQErrorStatsHist:uncorrectableErrors
        managed object property"
    ::= { cfprApAdaptorMenloQErrorStatsHistEntry 24 }

cfprApAdaptorMenloQErrorStatsHistUncorrectableErrorsDelta OBJECT-TYPE
    SYNTAX       Unsigned64
    MAX-ACCESS   read-only
    STATUS       current
    DESCRIPTION
        "Cisco Firepower adaptor:MenloQErrorStatsHist:uncorrectableErrorsD
        elta managed object property"
    ::= { cfprApAdaptorMenloQErrorStatsHistEntry 25 }

cfprApAdaptorMenloQErrorStatsHistUncorrectableErrorsDeltaAvg OBJECT-TYPE
    SYNTAX       Unsigned64
    MAX-ACCESS   read-only
    STATUS       current
    DESCRIPTION
        "Cisco Firepower adaptor:MenloQErrorStatsHist:uncorrectableErrorsD
        eltaAvg managed object property"
    ::= { cfprApAdaptorMenloQErrorStatsHistEntry 26 }

cfprApAdaptorMenloQErrorStatsHistUncorrectableErrorsDeltaMax OBJECT-TYPE
    SYNTAX       Unsigned64
    MAX-ACCESS   read-only
    STATUS       current
    DESCRIPTION
        "Cisco Firepower adaptor:MenloQErrorStatsHist:uncorrectableErrorsD
        eltaMax managed object property"
    ::= { cfprApAdaptorMenloQErrorStatsHistEntry 27 }

cfprApAdaptorMenloQErrorStatsHistUncorrectableErrorsDeltaMin OBJECT-TYPE
    SYNTAX       Unsigned64
    MAX-ACCESS   read-only
    STATUS       current
    DESCRIPTION
        "Cisco Firepower adaptor:MenloQErrorStatsHist:uncorrectableErrorsD
        eltaMin managed object property"
    ::= { cfprApAdaptorMenloQErrorStatsHistEntry 28 }

cfprApAdaptorMenloQStatsTable OBJECT-TYPE
    SYNTAX           SEQUENCE OF CfprApAdaptorMenloQStatsEntry
    MAX-ACCESS       not-accessible
    STATUS           current
    DESCRIPTION
        "Cisco Firepower adaptor:MenloQStats managed object table"
    ::= { cfprApAdaptorObjects 106 }

cfprApAdaptorMenloQStatsEntry OBJECT-TYPE
    SYNTAX           CfprApAdaptorMenloQStatsEntry
    MAX-ACCESS       not-accessible
    STATUS           current
    DESCRIPTION
        "Entry for the cfprApAdaptorMenloQStatsTable table."
    INDEX { cfprApAdaptorMenloQStatsInstanceId }
    ::= { cfprApAdaptorMenloQStatsTable 1 }

CfprApAdaptorMenloQStatsEntry ::= SEQUENCE {
    cfprApAdaptorMenloQStatsInstanceId                               CfprApManagedObjectId,
    cfprApAdaptorMenloQStatsDn                                       CfprApManagedObjectDn,
    cfprApAdaptorMenloQStatsRn                                       SnmpAdminString,
    cfprApAdaptorMenloQStatsDropOverrunN0                            Unsigned64,
    cfprApAdaptorMenloQStatsDropOverrunN0Delta                       Counter64,
    cfprApAdaptorMenloQStatsDropOverrunN0DeltaAvg                    Unsigned64,
    cfprApAdaptorMenloQStatsDropOverrunN0DeltaMax                    Unsigned64,
    cfprApAdaptorMenloQStatsDropOverrunN0DeltaMin                    Unsigned64,
    cfprApAdaptorMenloQStatsDropOverrunN1                            Unsigned64,
    cfprApAdaptorMenloQStatsDropOverrunN1Delta                       Counter64,
    cfprApAdaptorMenloQStatsDropOverrunN1DeltaAvg                    Unsigned64,
    cfprApAdaptorMenloQStatsDropOverrunN1DeltaMax                    Unsigned64,
    cfprApAdaptorMenloQStatsDropOverrunN1DeltaMin                    Unsigned64,
    cfprApAdaptorMenloQStatsIntervals                                Gauge32,
    cfprApAdaptorMenloQStatsMenloQueueComponent                      CfprApAdaptorMenloQueueStatsComponent,
    cfprApAdaptorMenloQStatsMenloQueueIndex                          CfprApAdaptorMenloStatsIndex,
    cfprApAdaptorMenloQStatsSuspect                                  TruthValue,
    cfprApAdaptorMenloQStatsThresholded                              CfprApAdaptorMenloQStatsThresholded,
    cfprApAdaptorMenloQStatsTimeCollected                            DateAndTime,
    cfprApAdaptorMenloQStatsTruncateOverrunN0                        Unsigned64,
    cfprApAdaptorMenloQStatsTruncateOverrunN0Delta                   Counter64,
    cfprApAdaptorMenloQStatsTruncateOverrunN0DeltaAvg                Unsigned64,
    cfprApAdaptorMenloQStatsTruncateOverrunN0DeltaMax                Unsigned64,
    cfprApAdaptorMenloQStatsTruncateOverrunN0DeltaMin                Unsigned64,
    cfprApAdaptorMenloQStatsTruncateOverrunN1                        Unsigned64,
    cfprApAdaptorMenloQStatsTruncateOverrunN1Delta                   Counter64,
    cfprApAdaptorMenloQStatsTruncateOverrunN1DeltaAvg                Unsigned64,
    cfprApAdaptorMenloQStatsTruncateOverrunN1DeltaMax                Unsigned64,
    cfprApAdaptorMenloQStatsTruncateOverrunN1DeltaMin                Unsigned64,
    cfprApAdaptorMenloQStatsUpdate                                   Gauge32
}

cfprApAdaptorMenloQStatsInstanceId OBJECT-TYPE
    SYNTAX       CfprApManagedObjectId
    MAX-ACCESS   not-accessible
    STATUS       current
    DESCRIPTION
        "Instance identifier of the managed object."
    ::= { cfprApAdaptorMenloQStatsEntry 1 }

cfprApAdaptorMenloQStatsDn OBJECT-TYPE
    SYNTAX       CfprApManagedObjectDn
    MAX-ACCESS   read-only
    STATUS       current
    DESCRIPTION
        "Cisco Firepower adaptor:MenloQStats:dn managed object property"
    ::= { cfprApAdaptorMenloQStatsEntry 2 }

cfprApAdaptorMenloQStatsRn OBJECT-TYPE
    SYNTAX       SnmpAdminString
    MAX-ACCESS   read-only
    STATUS       current
    DESCRIPTION
        "Cisco Firepower adaptor:MenloQStats:rn managed object property"
    ::= { cfprApAdaptorMenloQStatsEntry 3 }

cfprApAdaptorMenloQStatsDropOverrunN0 OBJECT-TYPE
    SYNTAX       Unsigned64
    MAX-ACCESS   read-only
    STATUS       current
    DESCRIPTION
        "Cisco Firepower adaptor:MenloQStats:dropOverrunN0
        managed object property"
    ::= { cfprApAdaptorMenloQStatsEntry 4 }

cfprApAdaptorMenloQStatsDropOverrunN0Delta OBJECT-TYPE
    SYNTAX       Counter64
    MAX-ACCESS   read-only
    STATUS       current
    DESCRIPTION
        "Cisco Firepower adaptor:MenloQStats:dropOverrunN0Delta
        managed object property"
    ::= { cfprApAdaptorMenloQStatsEntry 5 }

cfprApAdaptorMenloQStatsDropOverrunN0DeltaAvg OBJECT-TYPE
    SYNTAX       Unsigned64
    MAX-ACCESS   read-only
    STATUS       current
    DESCRIPTION
        "Cisco Firepower adaptor:MenloQStats:dropOverrunN0DeltaAvg
        managed object property"
    ::= { cfprApAdaptorMenloQStatsEntry 6 }

cfprApAdaptorMenloQStatsDropOverrunN0DeltaMax OBJECT-TYPE
    SYNTAX       Unsigned64
    MAX-ACCESS   read-only
    STATUS       current
    DESCRIPTION
        "Cisco Firepower adaptor:MenloQStats:dropOverrunN0DeltaMax
        managed object property"
    ::= { cfprApAdaptorMenloQStatsEntry 7 }

cfprApAdaptorMenloQStatsDropOverrunN0DeltaMin OBJECT-TYPE
    SYNTAX       Unsigned64
    MAX-ACCESS   read-only
    STATUS       current
    DESCRIPTION
        "Cisco Firepower adaptor:MenloQStats:dropOverrunN0DeltaMin
        managed object property"
    ::= { cfprApAdaptorMenloQStatsEntry 8 }

cfprApAdaptorMenloQStatsDropOverrunN1 OBJECT-TYPE
    SYNTAX       Unsigned64
    MAX-ACCESS   read-only
    STATUS       current
    DESCRIPTION
        "Cisco Firepower adaptor:MenloQStats:dropOverrunN1
        managed object property"
    ::= { cfprApAdaptorMenloQStatsEntry 9 }

cfprApAdaptorMenloQStatsDropOverrunN1Delta OBJECT-TYPE
    SYNTAX       Counter64
    MAX-ACCESS   read-only
    STATUS       current
    DESCRIPTION
        "Cisco Firepower adaptor:MenloQStats:dropOverrunN1Delta
        managed object property"
    ::= { cfprApAdaptorMenloQStatsEntry 10 }

cfprApAdaptorMenloQStatsDropOverrunN1DeltaAvg OBJECT-TYPE
    SYNTAX       Unsigned64
    MAX-ACCESS   read-only
    STATUS       current
    DESCRIPTION
        "Cisco Firepower adaptor:MenloQStats:dropOverrunN1DeltaAvg
        managed object property"
    ::= { cfprApAdaptorMenloQStatsEntry 11 }

cfprApAdaptorMenloQStatsDropOverrunN1DeltaMax OBJECT-TYPE
    SYNTAX       Unsigned64
    MAX-ACCESS   read-only
    STATUS       current
    DESCRIPTION
        "Cisco Firepower adaptor:MenloQStats:dropOverrunN1DeltaMax
        managed object property"
    ::= { cfprApAdaptorMenloQStatsEntry 12 }

cfprApAdaptorMenloQStatsDropOverrunN1DeltaMin OBJECT-TYPE
    SYNTAX       Unsigned64
    MAX-ACCESS   read-only
    STATUS       current
    DESCRIPTION
        "Cisco Firepower adaptor:MenloQStats:dropOverrunN1DeltaMin
        managed object property"
    ::= { cfprApAdaptorMenloQStatsEntry 13 }

cfprApAdaptorMenloQStatsIntervals OBJECT-TYPE
    SYNTAX       Gauge32
    MAX-ACCESS   read-only
    STATUS       current
    DESCRIPTION
        "Cisco Firepower adaptor:MenloQStats:intervals
        managed object property"
    ::= { cfprApAdaptorMenloQStatsEntry 14 }

cfprApAdaptorMenloQStatsMenloQueueComponent OBJECT-TYPE
    SYNTAX       CfprApAdaptorMenloQueueStatsComponent
    MAX-ACCESS   read-only
    STATUS       current
    DESCRIPTION
        "Cisco Firepower adaptor:MenloQStats:menloQueueComponent
        managed object property"
    ::= { cfprApAdaptorMenloQStatsEntry 15 }

cfprApAdaptorMenloQStatsMenloQueueIndex OBJECT-TYPE
    SYNTAX       CfprApAdaptorMenloStatsIndex
    MAX-ACCESS   read-only
    STATUS       current
    DESCRIPTION
        "Cisco Firepower adaptor:MenloQStats:menloQueueIndex
        managed object property"
    ::= { cfprApAdaptorMenloQStatsEntry 16 }

cfprApAdaptorMenloQStatsSuspect OBJECT-TYPE
    SYNTAX       TruthValue
    MAX-ACCESS   read-only
    STATUS       current
    DESCRIPTION
        "Cisco Firepower adaptor:MenloQStats:suspect managed
        object property"
    ::= { cfprApAdaptorMenloQStatsEntry 17 }

cfprApAdaptorMenloQStatsThresholded OBJECT-TYPE
    SYNTAX       CfprApAdaptorMenloQStatsThresholded
    MAX-ACCESS   read-only
    STATUS       current
    DESCRIPTION
        "Cisco Firepower adaptor:MenloQStats:thresholded
        managed object property"
    ::= { cfprApAdaptorMenloQStatsEntry 18 }

cfprApAdaptorMenloQStatsTimeCollected OBJECT-TYPE
    SYNTAX       DateAndTime
    MAX-ACCESS   read-only
    STATUS       current
    DESCRIPTION
        "Cisco Firepower adaptor:MenloQStats:timeCollected
        managed object property"
    ::= { cfprApAdaptorMenloQStatsEntry 19 }

cfprApAdaptorMenloQStatsTruncateOverrunN0 OBJECT-TYPE
    SYNTAX       Unsigned64
    MAX-ACCESS   read-only
    STATUS       current
    DESCRIPTION
        "Cisco Firepower adaptor:MenloQStats:truncateOverrunN0
        managed object property"
    ::= { cfprApAdaptorMenloQStatsEntry 20 }

cfprApAdaptorMenloQStatsTruncateOverrunN0Delta OBJECT-TYPE
    SYNTAX       Counter64
    MAX-ACCESS   read-only
    STATUS       current
    DESCRIPTION
        "Cisco Firepower adaptor:MenloQStats:truncateOverrunN0Delta
        managed object property"
    ::= { cfprApAdaptorMenloQStatsEntry 21 }

cfprApAdaptorMenloQStatsTruncateOverrunN0DeltaAvg OBJECT-TYPE
    SYNTAX       Unsigned64
    MAX-ACCESS   read-only
    STATUS       current
    DESCRIPTION
        "Cisco Firepower adaptor:MenloQStats:truncateOverrunN0DeltaAvg
        managed object property"
    ::= { cfprApAdaptorMenloQStatsEntry 22 }

cfprApAdaptorMenloQStatsTruncateOverrunN0DeltaMax OBJECT-TYPE
    SYNTAX       Unsigned64
    MAX-ACCESS   read-only
    STATUS       current
    DESCRIPTION
        "Cisco Firepower adaptor:MenloQStats:truncateOverrunN0DeltaMax
        managed object property"
    ::= { cfprApAdaptorMenloQStatsEntry 23 }

cfprApAdaptorMenloQStatsTruncateOverrunN0DeltaMin OBJECT-TYPE
    SYNTAX       Unsigned64
    MAX-ACCESS   read-only
    STATUS       current
    DESCRIPTION
        "Cisco Firepower adaptor:MenloQStats:truncateOverrunN0DeltaMin
        managed object property"
    ::= { cfprApAdaptorMenloQStatsEntry 24 }

cfprApAdaptorMenloQStatsTruncateOverrunN1 OBJECT-TYPE
    SYNTAX       Unsigned64
    MAX-ACCESS   read-only
    STATUS       current
    DESCRIPTION
        "Cisco Firepower adaptor:MenloQStats:truncateOverrunN1
        managed object property"
    ::= { cfprApAdaptorMenloQStatsEntry 25 }

cfprApAdaptorMenloQStatsTruncateOverrunN1Delta OBJECT-TYPE
    SYNTAX       Counter64
    MAX-ACCESS   read-only
    STATUS       current
    DESCRIPTION
        "Cisco Firepower adaptor:MenloQStats:truncateOverrunN1Delta
        managed object property"
    ::= { cfprApAdaptorMenloQStatsEntry 26 }

cfprApAdaptorMenloQStatsTruncateOverrunN1DeltaAvg OBJECT-TYPE
    SYNTAX       Unsigned64
    MAX-ACCESS   read-only
    STATUS       current
    DESCRIPTION
        "Cisco Firepower adaptor:MenloQStats:truncateOverrunN1DeltaAvg
        managed object property"
    ::= { cfprApAdaptorMenloQStatsEntry 27 }

cfprApAdaptorMenloQStatsTruncateOverrunN1DeltaMax OBJECT-TYPE
    SYNTAX       Unsigned64
    MAX-ACCESS   read-only
    STATUS       current
    DESCRIPTION
        "Cisco Firepower adaptor:MenloQStats:truncateOverrunN1DeltaMax
        managed object property"
    ::= { cfprApAdaptorMenloQStatsEntry 28 }

cfprApAdaptorMenloQStatsTruncateOverrunN1DeltaMin OBJECT-TYPE
    SYNTAX       Unsigned64
    MAX-ACCESS   read-only
    STATUS       current
    DESCRIPTION
        "Cisco Firepower adaptor:MenloQStats:truncateOverrunN1DeltaMin
        managed object property"
    ::= { cfprApAdaptorMenloQStatsEntry 29 }

cfprApAdaptorMenloQStatsUpdate OBJECT-TYPE
    SYNTAX       Gauge32
    MAX-ACCESS   read-only
    STATUS       current
    DESCRIPTION
        "Cisco Firepower adaptor:MenloQStats:update managed
        object property"
    ::= { cfprApAdaptorMenloQStatsEntry 30 }

cfprApAdaptorMenloQStatsHistTable OBJECT-TYPE
    SYNTAX           SEQUENCE OF CfprApAdaptorMenloQStatsHistEntry
    MAX-ACCESS       not-accessible
    STATUS           current
    DESCRIPTION
        "Cisco Firepower adaptor:MenloQStatsHist managed object table"
    ::= { cfprApAdaptorObjects 107 }

cfprApAdaptorMenloQStatsHistEntry OBJECT-TYPE
    SYNTAX           CfprApAdaptorMenloQStatsHistEntry
    MAX-ACCESS       not-accessible
    STATUS           current
    DESCRIPTION
        "Entry for the cfprApAdaptorMenloQStatsHistTable table."
    INDEX { cfprApAdaptorMenloQStatsHistInstanceId }
    ::= { cfprApAdaptorMenloQStatsHistTable 1 }

CfprApAdaptorMenloQStatsHistEntry ::= SEQUENCE {
    cfprApAdaptorMenloQStatsHistInstanceId                           CfprApManagedObjectId,
    cfprApAdaptorMenloQStatsHistDn                                   CfprApManagedObjectDn,
    cfprApAdaptorMenloQStatsHistRn                                   SnmpAdminString,
    cfprApAdaptorMenloQStatsHistDropOverrunN0                        Unsigned64,
    cfprApAdaptorMenloQStatsHistDropOverrunN0Delta                   Unsigned64,
    cfprApAdaptorMenloQStatsHistDropOverrunN0DeltaAvg                Unsigned64,
    cfprApAdaptorMenloQStatsHistDropOverrunN0DeltaMax                Unsigned64,
    cfprApAdaptorMenloQStatsHistDropOverrunN0DeltaMin                Unsigned64,
    cfprApAdaptorMenloQStatsHistDropOverrunN1                        Unsigned64,
    cfprApAdaptorMenloQStatsHistDropOverrunN1Delta                   Unsigned64,
    cfprApAdaptorMenloQStatsHistDropOverrunN1DeltaAvg                Unsigned64,
    cfprApAdaptorMenloQStatsHistDropOverrunN1DeltaMax                Unsigned64,
    cfprApAdaptorMenloQStatsHistDropOverrunN1DeltaMin                Unsigned64,
    cfprApAdaptorMenloQStatsHistId                                   Unsigned64,
    cfprApAdaptorMenloQStatsHistMostRecent                           TruthValue,
    cfprApAdaptorMenloQStatsHistSuspect                              TruthValue,
    cfprApAdaptorMenloQStatsHistThresholded                          CfprApAdaptorMenloQStatsHistThresholded,
    cfprApAdaptorMenloQStatsHistTimeCollected                        DateAndTime,
    cfprApAdaptorMenloQStatsHistTruncateOverrunN0                    Unsigned64,
    cfprApAdaptorMenloQStatsHistTruncateOverrunN0Delta               Unsigned64,
    cfprApAdaptorMenloQStatsHistTruncateOverrunN0DeltaAvg            Unsigned64,
    cfprApAdaptorMenloQStatsHistTruncateOverrunN0DeltaMax            Unsigned64,
    cfprApAdaptorMenloQStatsHistTruncateOverrunN0DeltaMin            Unsigned64,
    cfprApAdaptorMenloQStatsHistTruncateOverrunN1                    Unsigned64,
    cfprApAdaptorMenloQStatsHistTruncateOverrunN1Delta               Unsigned64,
    cfprApAdaptorMenloQStatsHistTruncateOverrunN1DeltaAvg            Unsigned64,
    cfprApAdaptorMenloQStatsHistTruncateOverrunN1DeltaMax            Unsigned64,
    cfprApAdaptorMenloQStatsHistTruncateOverrunN1DeltaMin            Unsigned64
}

cfprApAdaptorMenloQStatsHistInstanceId OBJECT-TYPE
    SYNTAX       CfprApManagedObjectId
    MAX-ACCESS   not-accessible
    STATUS       current
    DESCRIPTION
        "Instance identifier of the managed object."
    ::= { cfprApAdaptorMenloQStatsHistEntry 1 }

cfprApAdaptorMenloQStatsHistDn OBJECT-TYPE
    SYNTAX       CfprApManagedObjectDn
    MAX-ACCESS   read-only
    STATUS       current
    DESCRIPTION
        "Cisco Firepower adaptor:MenloQStatsHist:dn managed
        object property"
    ::= { cfprApAdaptorMenloQStatsHistEntry 2 }

cfprApAdaptorMenloQStatsHistRn OBJECT-TYPE
    SYNTAX       SnmpAdminString
    MAX-ACCESS   read-only
    STATUS       current
    DESCRIPTION
        "Cisco Firepower adaptor:MenloQStatsHist:rn managed
        object property"
    ::= { cfprApAdaptorMenloQStatsHistEntry 3 }

cfprApAdaptorMenloQStatsHistDropOverrunN0 OBJECT-TYPE
    SYNTAX       Unsigned64
    MAX-ACCESS   read-only
    STATUS       current
    DESCRIPTION
        "Cisco Firepower adaptor:MenloQStatsHist:dropOverrunN0
        managed object property"
    ::= { cfprApAdaptorMenloQStatsHistEntry 4 }

cfprApAdaptorMenloQStatsHistDropOverrunN0Delta OBJECT-TYPE
    SYNTAX       Unsigned64
    MAX-ACCESS   read-only
    STATUS       current
    DESCRIPTION
        "Cisco Firepower adaptor:MenloQStatsHist:dropOverrunN0Delta
        managed object property"
    ::= { cfprApAdaptorMenloQStatsHistEntry 5 }

cfprApAdaptorMenloQStatsHistDropOverrunN0DeltaAvg OBJECT-TYPE
    SYNTAX       Unsigned64
    MAX-ACCESS   read-only
    STATUS       current
    DESCRIPTION
        "Cisco Firepower adaptor:MenloQStatsHist:dropOverrunN0DeltaAvg
        managed object property"
    ::= { cfprApAdaptorMenloQStatsHistEntry 6 }

cfprApAdaptorMenloQStatsHistDropOverrunN0DeltaMax OBJECT-TYPE
    SYNTAX       Unsigned64
    MAX-ACCESS   read-only
    STATUS       current
    DESCRIPTION
        "Cisco Firepower adaptor:MenloQStatsHist:dropOverrunN0DeltaMax
        managed object property"
    ::= { cfprApAdaptorMenloQStatsHistEntry 7 }

cfprApAdaptorMenloQStatsHistDropOverrunN0DeltaMin OBJECT-TYPE
    SYNTAX       Unsigned64
    MAX-ACCESS   read-only
    STATUS       current
    DESCRIPTION
        "Cisco Firepower adaptor:MenloQStatsHist:dropOverrunN0DeltaMin
        managed object property"
    ::= { cfprApAdaptorMenloQStatsHistEntry 8 }

cfprApAdaptorMenloQStatsHistDropOverrunN1 OBJECT-TYPE
    SYNTAX       Unsigned64
    MAX-ACCESS   read-only
    STATUS       current
    DESCRIPTION
        "Cisco Firepower adaptor:MenloQStatsHist:dropOverrunN1
        managed object property"
    ::= { cfprApAdaptorMenloQStatsHistEntry 9 }

cfprApAdaptorMenloQStatsHistDropOverrunN1Delta OBJECT-TYPE
    SYNTAX       Unsigned64
    MAX-ACCESS   read-only
    STATUS       current
    DESCRIPTION
        "Cisco Firepower adaptor:MenloQStatsHist:dropOverrunN1Delta
        managed object property"
    ::= { cfprApAdaptorMenloQStatsHistEntry 10 }

cfprApAdaptorMenloQStatsHistDropOverrunN1DeltaAvg OBJECT-TYPE
    SYNTAX       Unsigned64
    MAX-ACCESS   read-only
    STATUS       current
    DESCRIPTION
        "Cisco Firepower adaptor:MenloQStatsHist:dropOverrunN1DeltaAvg
        managed object property"
    ::= { cfprApAdaptorMenloQStatsHistEntry 11 }

cfprApAdaptorMenloQStatsHistDropOverrunN1DeltaMax OBJECT-TYPE
    SYNTAX       Unsigned64
    MAX-ACCESS   read-only
    STATUS       current
    DESCRIPTION
        "Cisco Firepower adaptor:MenloQStatsHist:dropOverrunN1DeltaMax
        managed object property"
    ::= { cfprApAdaptorMenloQStatsHistEntry 12 }

cfprApAdaptorMenloQStatsHistDropOverrunN1DeltaMin OBJECT-TYPE
    SYNTAX       Unsigned64
    MAX-ACCESS   read-only
    STATUS       current
    DESCRIPTION
        "Cisco Firepower adaptor:MenloQStatsHist:dropOverrunN1DeltaMin
        managed object property"
    ::= { cfprApAdaptorMenloQStatsHistEntry 13 }

cfprApAdaptorMenloQStatsHistId OBJECT-TYPE
    SYNTAX       Unsigned64
    MAX-ACCESS   read-only
    STATUS       current
    DESCRIPTION
        "Cisco Firepower adaptor:MenloQStatsHist:id managed
        object property"
    ::= { cfprApAdaptorMenloQStatsHistEntry 14 }

cfprApAdaptorMenloQStatsHistMostRecent OBJECT-TYPE
    SYNTAX       TruthValue
    MAX-ACCESS   read-only
    STATUS       current
    DESCRIPTION
        "Cisco Firepower adaptor:MenloQStatsHist:mostRecent
        managed object property"
    ::= { cfprApAdaptorMenloQStatsHistEntry 15 }

cfprApAdaptorMenloQStatsHistSuspect OBJECT-TYPE
    SYNTAX       TruthValue
    MAX-ACCESS   read-only
    STATUS       current
    DESCRIPTION
        "Cisco Firepower adaptor:MenloQStatsHist:suspect
        managed object property"
    ::= { cfprApAdaptorMenloQStatsHistEntry 16 }

cfprApAdaptorMenloQStatsHistThresholded OBJECT-TYPE
    SYNTAX       CfprApAdaptorMenloQStatsHistThresholded
    MAX-ACCESS   read-only
    STATUS       current
    DESCRIPTION
        "Cisco Firepower adaptor:MenloQStatsHist:thresholded
        managed object property"
    ::= { cfprApAdaptorMenloQStatsHistEntry 17 }

cfprApAdaptorMenloQStatsHistTimeCollected OBJECT-TYPE
    SYNTAX       DateAndTime
    MAX-ACCESS   read-only
    STATUS       current
    DESCRIPTION
        "Cisco Firepower adaptor:MenloQStatsHist:timeCollected
        managed object property"
    ::= { cfprApAdaptorMenloQStatsHistEntry 18 }

cfprApAdaptorMenloQStatsHistTruncateOverrunN0 OBJECT-TYPE
    SYNTAX       Unsigned64
    MAX-ACCESS   read-only
    STATUS       current
    DESCRIPTION
        "Cisco Firepower adaptor:MenloQStatsHist:truncateOverrunN0
        managed object property"
    ::= { cfprApAdaptorMenloQStatsHistEntry 19 }

cfprApAdaptorMenloQStatsHistTruncateOverrunN0Delta OBJECT-TYPE
    SYNTAX       Unsigned64
    MAX-ACCESS   read-only
    STATUS       current
    DESCRIPTION
        "Cisco Firepower adaptor:MenloQStatsHist:truncateOverrunN0Delta
        managed object property"
    ::= { cfprApAdaptorMenloQStatsHistEntry 20 }

cfprApAdaptorMenloQStatsHistTruncateOverrunN0DeltaAvg OBJECT-TYPE
    SYNTAX       Unsigned64
    MAX-ACCESS   read-only
    STATUS       current
    DESCRIPTION
        "Cisco Firepower adaptor:MenloQStatsHist:truncateOverrunN0DeltaAvg
         managed object property"
    ::= { cfprApAdaptorMenloQStatsHistEntry 21 }

cfprApAdaptorMenloQStatsHistTruncateOverrunN0DeltaMax OBJECT-TYPE
    SYNTAX       Unsigned64
    MAX-ACCESS   read-only
    STATUS       current
    DESCRIPTION
        "Cisco Firepower adaptor:MenloQStatsHist:truncateOverrunN0DeltaMax
         managed object property"
    ::= { cfprApAdaptorMenloQStatsHistEntry 22 }

cfprApAdaptorMenloQStatsHistTruncateOverrunN0DeltaMin OBJECT-TYPE
    SYNTAX       Unsigned64
    MAX-ACCESS   read-only
    STATUS       current
    DESCRIPTION
        "Cisco Firepower adaptor:MenloQStatsHist:truncateOverrunN0DeltaMin
         managed object property"
    ::= { cfprApAdaptorMenloQStatsHistEntry 23 }

cfprApAdaptorMenloQStatsHistTruncateOverrunN1 OBJECT-TYPE
    SYNTAX       Unsigned64
    MAX-ACCESS   read-only
    STATUS       current
    DESCRIPTION
        "Cisco Firepower adaptor:MenloQStatsHist:truncateOverrunN1
        managed object property"
    ::= { cfprApAdaptorMenloQStatsHistEntry 24 }

cfprApAdaptorMenloQStatsHistTruncateOverrunN1Delta OBJECT-TYPE
    SYNTAX       Unsigned64
    MAX-ACCESS   read-only
    STATUS       current
    DESCRIPTION
        "Cisco Firepower adaptor:MenloQStatsHist:truncateOverrunN1Delta
        managed object property"
    ::= { cfprApAdaptorMenloQStatsHistEntry 25 }

cfprApAdaptorMenloQStatsHistTruncateOverrunN1DeltaAvg OBJECT-TYPE
    SYNTAX       Unsigned64
    MAX-ACCESS   read-only
    STATUS       current
    DESCRIPTION
        "Cisco Firepower adaptor:MenloQStatsHist:truncateOverrunN1DeltaAvg
         managed object property"
    ::= { cfprApAdaptorMenloQStatsHistEntry 26 }

cfprApAdaptorMenloQStatsHistTruncateOverrunN1DeltaMax OBJECT-TYPE
    SYNTAX       Unsigned64
    MAX-ACCESS   read-only
    STATUS       current
    DESCRIPTION
        "Cisco Firepower adaptor:MenloQStatsHist:truncateOverrunN1DeltaMax
         managed object property"
    ::= { cfprApAdaptorMenloQStatsHistEntry 27 }

cfprApAdaptorMenloQStatsHistTruncateOverrunN1DeltaMin OBJECT-TYPE
    SYNTAX       Unsigned64
    MAX-ACCESS   read-only
    STATUS       current
    DESCRIPTION
        "Cisco Firepower adaptor:MenloQStatsHist:truncateOverrunN1DeltaMin
         managed object property"
    ::= { cfprApAdaptorMenloQStatsHistEntry 28 }

cfprApAdaptorNwMgmtCapTable OBJECT-TYPE
    SYNTAX           SEQUENCE OF CfprApAdaptorNwMgmtCapEntry
    MAX-ACCESS       not-accessible
    STATUS           current
    DESCRIPTION
        "Cisco Firepower adaptor:NwMgmtCap managed object table"
    ::= { cfprApAdaptorObjects 108 }

cfprApAdaptorNwMgmtCapEntry OBJECT-TYPE
    SYNTAX           CfprApAdaptorNwMgmtCapEntry
    MAX-ACCESS       not-accessible
    STATUS           current
    DESCRIPTION
        "Entry for the cfprApAdaptorNwMgmtCapTable table."
    INDEX { cfprApAdaptorNwMgmtCapInstanceId }
    ::= { cfprApAdaptorNwMgmtCapTable 1 }

CfprApAdaptorNwMgmtCapEntry ::= SEQUENCE {
    cfprApAdaptorNwMgmtCapInstanceId                                 CfprApManagedObjectId,
    cfprApAdaptorNwMgmtCapDn                                         CfprApManagedObjectDn,
    cfprApAdaptorNwMgmtCapRn                                         SnmpAdminString,
    cfprApAdaptorNwMgmtCapApi                                        CfprApAdaptorNwMgmtCapApi,
    cfprApAdaptorNwMgmtCapMgmtTransport                              CfprApAdaptorNwMgmtCapMgmtTransport,
    cfprApAdaptorNwMgmtCapMode                                       CfprApAdaptorMgmtCapMode,
    cfprApAdaptorNwMgmtCapOperPowerRequirement                       CfprApAdaptorMgmtCapOperPowerRequirement,
    cfprApAdaptorNwMgmtCapRebootActionOnDestructive                  CfprApAdaptorMgmtCapRebootActionOnDestructive
}

cfprApAdaptorNwMgmtCapInstanceId OBJECT-TYPE
    SYNTAX       CfprApManagedObjectId
    MAX-ACCESS   not-accessible
    STATUS       current
    DESCRIPTION
        "Instance identifier of the managed object."
    ::= { cfprApAdaptorNwMgmtCapEntry 1 }

cfprApAdaptorNwMgmtCapDn OBJECT-TYPE
    SYNTAX       CfprApManagedObjectDn
    MAX-ACCESS   read-only
    STATUS       current
    DESCRIPTION
        "Cisco Firepower adaptor:NwMgmtCap:dn managed object property"
    ::= { cfprApAdaptorNwMgmtCapEntry 2 }

cfprApAdaptorNwMgmtCapRn OBJECT-TYPE
    SYNTAX       SnmpAdminString
    MAX-ACCESS   read-only
    STATUS       current
    DESCRIPTION
        "Cisco Firepower adaptor:NwMgmtCap:rn managed object property"
    ::= { cfprApAdaptorNwMgmtCapEntry 3 }

cfprApAdaptorNwMgmtCapApi OBJECT-TYPE
    SYNTAX       CfprApAdaptorNwMgmtCapApi
    MAX-ACCESS   read-only
    STATUS       current
    DESCRIPTION
        "Cisco Firepower adaptor:NwMgmtCap:api managed object property"
    ::= { cfprApAdaptorNwMgmtCapEntry 4 }

cfprApAdaptorNwMgmtCapMgmtTransport OBJECT-TYPE
    SYNTAX       CfprApAdaptorNwMgmtCapMgmtTransport
    MAX-ACCESS   read-only
    STATUS       current
    DESCRIPTION
        "Cisco Firepower adaptor:NwMgmtCap:mgmtTransport
        managed object property"
    ::= { cfprApAdaptorNwMgmtCapEntry 5 }

cfprApAdaptorNwMgmtCapMode OBJECT-TYPE
    SYNTAX       CfprApAdaptorMgmtCapMode
    MAX-ACCESS   read-only
    STATUS       current
    DESCRIPTION
        "Cisco Firepower adaptor:NwMgmtCap:mode managed object property"
    ::= { cfprApAdaptorNwMgmtCapEntry 6 }

cfprApAdaptorNwMgmtCapOperPowerRequirement OBJECT-TYPE
    SYNTAX       CfprApAdaptorMgmtCapOperPowerRequirement
    MAX-ACCESS   read-only
    STATUS       current
    DESCRIPTION
        "Cisco Firepower adaptor:NwMgmtCap:operPowerRequirement
        managed object property"
    ::= { cfprApAdaptorNwMgmtCapEntry 7 }

cfprApAdaptorNwMgmtCapRebootActionOnDestructive OBJECT-TYPE
    SYNTAX       CfprApAdaptorMgmtCapRebootActionOnDestructive
    MAX-ACCESS   read-only
    STATUS       current
    DESCRIPTION
        "Cisco Firepower adaptor:NwMgmtCap:rebootActionOnDestructive
        managed object property"
    ::= { cfprApAdaptorNwMgmtCapEntry 8 }

cfprApAdaptorQualTable OBJECT-TYPE
    SYNTAX           SEQUENCE OF CfprApAdaptorQualEntry
    MAX-ACCESS       not-accessible
    STATUS           current
    DESCRIPTION
        "Cisco Firepower adaptor:Qual managed object table"
    ::= { cfprApAdaptorObjects 110 }

cfprApAdaptorQualEntry OBJECT-TYPE
    SYNTAX           CfprApAdaptorQualEntry
    MAX-ACCESS       not-accessible
    STATUS           current
    DESCRIPTION
        "Entry for the cfprApAdaptorQualTable table."
    INDEX { cfprApAdaptorQualInstanceId }
    ::= { cfprApAdaptorQualTable 1 }

CfprApAdaptorQualEntry ::= SEQUENCE {
    cfprApAdaptorQualInstanceId                                      CfprApManagedObjectId,
    cfprApAdaptorQualDn                                              CfprApManagedObjectDn,
    cfprApAdaptorQualRn                                              SnmpAdminString
}

cfprApAdaptorQualInstanceId OBJECT-TYPE
    SYNTAX       CfprApManagedObjectId
    MAX-ACCESS   not-accessible
    STATUS       current
    DESCRIPTION
        "Instance identifier of the managed object."
    ::= { cfprApAdaptorQualEntry 1 }

cfprApAdaptorQualDn OBJECT-TYPE
    SYNTAX       CfprApManagedObjectDn
    MAX-ACCESS   read-only
    STATUS       current
    DESCRIPTION
        "Cisco Firepower adaptor:Qual:dn managed object property"
    ::= { cfprApAdaptorQualEntry 2 }

cfprApAdaptorQualRn OBJECT-TYPE
    SYNTAX       SnmpAdminString
    MAX-ACCESS   read-only
    STATUS       current
    DESCRIPTION
        "Cisco Firepower adaptor:Qual:rn managed object property"
    ::= { cfprApAdaptorQualEntry 3 }

cfprApAdaptorRssProfileTable OBJECT-TYPE
    SYNTAX           SEQUENCE OF CfprApAdaptorRssProfileEntry
    MAX-ACCESS       not-accessible
    STATUS           current
    DESCRIPTION
        "Cisco Firepower adaptor:RssProfile managed object table"
    ::= { cfprApAdaptorObjects 111 }

cfprApAdaptorRssProfileEntry OBJECT-TYPE
    SYNTAX           CfprApAdaptorRssProfileEntry
    MAX-ACCESS       not-accessible
    STATUS           current
    DESCRIPTION
        "Entry for the cfprApAdaptorRssProfileTable table."
    INDEX { cfprApAdaptorRssProfileInstanceId }
    ::= { cfprApAdaptorRssProfileTable 1 }

CfprApAdaptorRssProfileEntry ::= SEQUENCE {
    cfprApAdaptorRssProfileInstanceId                                CfprApManagedObjectId,
    cfprApAdaptorRssProfileDn                                        CfprApManagedObjectDn,
    cfprApAdaptorRssProfileRn                                        SnmpAdminString,
    cfprApAdaptorRssProfileReceiveSideScaling                        CfprApAdaptorRssProfileReceiveSideScaling
}

cfprApAdaptorRssProfileInstanceId OBJECT-TYPE
    SYNTAX       CfprApManagedObjectId
    MAX-ACCESS   not-accessible
    STATUS       current
    DESCRIPTION
        "Instance identifier of the managed object."
    ::= { cfprApAdaptorRssProfileEntry 1 }

cfprApAdaptorRssProfileDn OBJECT-TYPE
    SYNTAX       CfprApManagedObjectDn
    MAX-ACCESS   read-only
    STATUS       current
    DESCRIPTION
        "Cisco Firepower adaptor:RssProfile:dn managed object property"
    ::= { cfprApAdaptorRssProfileEntry 2 }

cfprApAdaptorRssProfileRn OBJECT-TYPE
    SYNTAX       SnmpAdminString
    MAX-ACCESS   read-only
    STATUS       current
    DESCRIPTION
        "Cisco Firepower adaptor:RssProfile:rn managed object property"
    ::= { cfprApAdaptorRssProfileEntry 3 }

cfprApAdaptorRssProfileReceiveSideScaling OBJECT-TYPE
    SYNTAX       CfprApAdaptorRssProfileReceiveSideScaling
    MAX-ACCESS   read-only
    STATUS       current
    DESCRIPTION
        "Cisco Firepower adaptor:RssProfile:receiveSideScaling
        managed object property"
    ::= { cfprApAdaptorRssProfileEntry 4 }

cfprApAdaptorSanCapTable OBJECT-TYPE
    SYNTAX           SEQUENCE OF CfprApAdaptorSanCapEntry
    MAX-ACCESS       not-accessible
    STATUS           current
    DESCRIPTION
        "Cisco Firepower adaptor:SanCap managed object table"
    ::= { cfprApAdaptorObjects 112 }

cfprApAdaptorSanCapEntry OBJECT-TYPE
    SYNTAX           CfprApAdaptorSanCapEntry
    MAX-ACCESS       not-accessible
    STATUS           current
    DESCRIPTION
        "Entry for the cfprApAdaptorSanCapTable table."
    INDEX { cfprApAdaptorSanCapInstanceId }
    ::= { cfprApAdaptorSanCapTable 1 }

CfprApAdaptorSanCapEntry ::= SEQUENCE {
    cfprApAdaptorSanCapInstanceId                                    CfprApManagedObjectId,
    cfprApAdaptorSanCapDn                                            CfprApManagedObjectDn,
    cfprApAdaptorSanCapRn                                            SnmpAdminString,
    cfprApAdaptorSanCapHostNvram                                     CfprApAdaptorSanCapHostNvram
}

cfprApAdaptorSanCapInstanceId OBJECT-TYPE
    SYNTAX       CfprApManagedObjectId
    MAX-ACCESS   not-accessible
    STATUS       current
    DESCRIPTION
        "Instance identifier of the managed object."
    ::= { cfprApAdaptorSanCapEntry 1 }

cfprApAdaptorSanCapDn OBJECT-TYPE
    SYNTAX       CfprApManagedObjectDn
    MAX-ACCESS   read-only
    STATUS       current
    DESCRIPTION
        "Cisco Firepower adaptor:SanCap:dn managed object property"
    ::= { cfprApAdaptorSanCapEntry 2 }

cfprApAdaptorSanCapRn OBJECT-TYPE
    SYNTAX       SnmpAdminString
    MAX-ACCESS   read-only
    STATUS       current
    DESCRIPTION
        "Cisco Firepower adaptor:SanCap:rn managed object property"
    ::= { cfprApAdaptorSanCapEntry 3 }

cfprApAdaptorSanCapHostNvram OBJECT-TYPE
    SYNTAX       CfprApAdaptorSanCapHostNvram
    MAX-ACCESS   read-only
    STATUS       current
    DESCRIPTION
        "Cisco Firepower adaptor:SanCap:hostNvram managed object property"
    ::= { cfprApAdaptorSanCapEntry 4 }

cfprApAdaptorUnitTable OBJECT-TYPE
    SYNTAX           SEQUENCE OF CfprApAdaptorUnitEntry
    MAX-ACCESS       not-accessible
    STATUS           current
    DESCRIPTION
        "Cisco Firepower adaptor:Unit managed object table"
    ::= { cfprApAdaptorObjects 113 }

cfprApAdaptorUnitEntry OBJECT-TYPE
    SYNTAX           CfprApAdaptorUnitEntry
    MAX-ACCESS       not-accessible
    STATUS           current
    DESCRIPTION
        "Entry for the cfprApAdaptorUnitTable table."
    INDEX { cfprApAdaptorUnitInstanceId }
    ::= { cfprApAdaptorUnitTable 1 }

CfprApAdaptorUnitEntry ::= SEQUENCE {
    cfprApAdaptorUnitInstanceId                                      CfprApManagedObjectId,
    cfprApAdaptorUnitDn                                              CfprApManagedObjectDn,
    cfprApAdaptorUnitRn                                              SnmpAdminString,
    cfprApAdaptorUnitAdminPowerState                                 CfprApAdaptorAdminPowerState,
    cfprApAdaptorUnitBaseMac                                         MacAddress,
    cfprApAdaptorUnitBladeId                                         Gauge32,
    cfprApAdaptorUnitChassisId                                       Gauge32,
    cfprApAdaptorUnitConnPath                                        CfprApEquipmentConnectionStatus,
    cfprApAdaptorUnitConnStatus                                      CfprApEquipmentConnectionStatus,
    cfprApAdaptorUnitFltAggr                                         Unsigned64,
    cfprApAdaptorUnitId                                              CfprApAdaptorUnitId,
    cfprApAdaptorUnitIntegrated                                      TruthValue,
    cfprApAdaptorUnitLocationDn                                      SnmpAdminString,
    cfprApAdaptorUnitManagingInst                                    CfprApNetworkSwitchId,
    cfprApAdaptorUnitMfgTime                                         DateAndTime,
    cfprApAdaptorUnitModel                                           SnmpAdminString,
    cfprApAdaptorUnitOperQualifierReason                             SnmpAdminString,
    cfprApAdaptorUnitOperState                                       CfprApEquipmentOperability,
    cfprApAdaptorUnitOperability                                     CfprApEquipmentOperability,
    cfprApAdaptorUnitPartNumber                                      SnmpAdminString,
    cfprApAdaptorUnitPciAddr                                         SnmpAdminString,
    cfprApAdaptorUnitPciSlot                                         SnmpAdminString,
    cfprApAdaptorUnitPerf                                            CfprApEquipmentSensorThresholdStatus,
    cfprApAdaptorUnitPower                                           CfprApEquipmentPowerState,
    cfprApAdaptorUnitPresence                                        CfprApEquipmentPresence,
    cfprApAdaptorUnitReachability                                    CfprApAdaptorReachability,
    cfprApAdaptorUnitRevision                                        SnmpAdminString,
    cfprApAdaptorUnitSerial                                          SnmpAdminString,
    cfprApAdaptorUnitThermal                                         CfprApEquipmentSensorThresholdStatus,
    cfprApAdaptorUnitVendor                                          SnmpAdminString,
    cfprApAdaptorUnitVoltage                                         CfprApEquipmentSensorThresholdStatus
}

cfprApAdaptorUnitInstanceId OBJECT-TYPE
    SYNTAX       CfprApManagedObjectId
    MAX-ACCESS   not-accessible
    STATUS       current
    DESCRIPTION
        "Instance identifier of the managed object."
    ::= { cfprApAdaptorUnitEntry 1 }

cfprApAdaptorUnitDn OBJECT-TYPE
    SYNTAX       CfprApManagedObjectDn
    MAX-ACCESS   read-only
    STATUS       current
    DESCRIPTION
        "Cisco Firepower adaptor:Unit:dn managed object property"
    ::= { cfprApAdaptorUnitEntry 2 }

cfprApAdaptorUnitRn OBJECT-TYPE
    SYNTAX       SnmpAdminString
    MAX-ACCESS   read-only
    STATUS       current
    DESCRIPTION
        "Cisco Firepower adaptor:Unit:rn managed object property"
    ::= { cfprApAdaptorUnitEntry 3 }

cfprApAdaptorUnitAdminPowerState OBJECT-TYPE
    SYNTAX       CfprApAdaptorAdminPowerState
    MAX-ACCESS   read-only
    STATUS       current
    DESCRIPTION
        "Cisco Firepower adaptor:Unit:adminPowerState managed
        object property"
    ::= { cfprApAdaptorUnitEntry 4 }

cfprApAdaptorUnitBaseMac OBJECT-TYPE
    SYNTAX       MacAddress
    MAX-ACCESS   read-only
    STATUS       current
    DESCRIPTION
        "Cisco Firepower adaptor:Unit:baseMac managed object property"
    ::= { cfprApAdaptorUnitEntry 5 }

cfprApAdaptorUnitBladeId OBJECT-TYPE
    SYNTAX       Gauge32
    MAX-ACCESS   read-only
    STATUS       current
    DESCRIPTION
        "Cisco Firepower adaptor:Unit:bladeId managed object property"
    ::= { cfprApAdaptorUnitEntry 6 }

cfprApAdaptorUnitChassisId OBJECT-TYPE
    SYNTAX       Gauge32
    MAX-ACCESS   read-only
    STATUS       current
    DESCRIPTION
        "Cisco Firepower adaptor:Unit:chassisId managed object property"
    ::= { cfprApAdaptorUnitEntry 7 }

cfprApAdaptorUnitConnPath OBJECT-TYPE
    SYNTAX       CfprApEquipmentConnectionStatus
    MAX-ACCESS   read-only
    STATUS       current
    DESCRIPTION
        "Cisco Firepower adaptor:Unit:connPath managed object property"
    ::= { cfprApAdaptorUnitEntry 8 }

cfprApAdaptorUnitConnStatus OBJECT-TYPE
    SYNTAX       CfprApEquipmentConnectionStatus
    MAX-ACCESS   read-only
    STATUS       current
    DESCRIPTION
        "Cisco Firepower adaptor:Unit:connStatus managed object property"
    ::= { cfprApAdaptorUnitEntry 9 }

cfprApAdaptorUnitFltAggr OBJECT-TYPE
    SYNTAX       Unsigned64
    MAX-ACCESS   read-only
    STATUS       current
    DESCRIPTION
        "Cisco Firepower adaptor:Unit:fltAggr managed object property"
    ::= { cfprApAdaptorUnitEntry 10 }

cfprApAdaptorUnitId OBJECT-TYPE
    SYNTAX       CfprApAdaptorUnitId
    MAX-ACCESS   read-only
    STATUS       current
    DESCRIPTION
        "Cisco Firepower adaptor:Unit:id managed object property"
    ::= { cfprApAdaptorUnitEntry 11 }

cfprApAdaptorUnitIntegrated OBJECT-TYPE
    SYNTAX       TruthValue
    MAX-ACCESS   read-only
    STATUS       current
    DESCRIPTION
        "Cisco Firepower adaptor:Unit:integrated managed object property"
    ::= { cfprApAdaptorUnitEntry 12 }

cfprApAdaptorUnitLocationDn OBJECT-TYPE
    SYNTAX       SnmpAdminString
    MAX-ACCESS   read-only
    STATUS       current
    DESCRIPTION
        "Cisco Firepower adaptor:Unit:locationDn managed object property"
    ::= { cfprApAdaptorUnitEntry 13 }

cfprApAdaptorUnitManagingInst OBJECT-TYPE
    SYNTAX       CfprApNetworkSwitchId
    MAX-ACCESS   read-only
    STATUS       current
    DESCRIPTION
        "Cisco Firepower adaptor:Unit:managingInst managed
        object property"
    ::= { cfprApAdaptorUnitEntry 14 }

cfprApAdaptorUnitMfgTime OBJECT-TYPE
    SYNTAX       DateAndTime
    MAX-ACCESS   read-only
    STATUS       current
    DESCRIPTION
        "Cisco Firepower adaptor:Unit:mfgTime managed object property"
    ::= { cfprApAdaptorUnitEntry 15 }

cfprApAdaptorUnitModel OBJECT-TYPE
    SYNTAX       SnmpAdminString
    MAX-ACCESS   read-only
    STATUS       current
    DESCRIPTION
        "Cisco Firepower adaptor:Unit:model managed object property"
    ::= { cfprApAdaptorUnitEntry 16 }

cfprApAdaptorUnitOperQualifierReason OBJECT-TYPE
    SYNTAX       SnmpAdminString
    MAX-ACCESS   read-only
    STATUS       current
    DESCRIPTION
        "Cisco Firepower adaptor:Unit:operQualifierReason
        managed object property"
    ::= { cfprApAdaptorUnitEntry 17 }

cfprApAdaptorUnitOperState OBJECT-TYPE
    SYNTAX       CfprApEquipmentOperability
    MAX-ACCESS   read-only
    STATUS       current
    DESCRIPTION
        "Cisco Firepower adaptor:Unit:operState managed object property"
    ::= { cfprApAdaptorUnitEntry 18 }

cfprApAdaptorUnitOperability OBJECT-TYPE
    SYNTAX       CfprApEquipmentOperability
    MAX-ACCESS   read-only
    STATUS       current
    DESCRIPTION
        "Cisco Firepower adaptor:Unit:operability managed object property"
    ::= { cfprApAdaptorUnitEntry 19 }

cfprApAdaptorUnitPartNumber OBJECT-TYPE
    SYNTAX       SnmpAdminString
    MAX-ACCESS   read-only
    STATUS       current
    DESCRIPTION
        "Cisco Firepower adaptor:Unit:partNumber managed object property"
    ::= { cfprApAdaptorUnitEntry 20 }

cfprApAdaptorUnitPciAddr OBJECT-TYPE
    SYNTAX       SnmpAdminString
    MAX-ACCESS   read-only
    STATUS       current
    DESCRIPTION
        "Cisco Firepower adaptor:Unit:pciAddr managed object property"
    ::= { cfprApAdaptorUnitEntry 21 }

cfprApAdaptorUnitPciSlot OBJECT-TYPE
    SYNTAX       SnmpAdminString
    MAX-ACCESS   read-only
    STATUS       current
    DESCRIPTION
        "Cisco Firepower adaptor:Unit:pciSlot managed object property"
    ::= { cfprApAdaptorUnitEntry 22 }

cfprApAdaptorUnitPerf OBJECT-TYPE
    SYNTAX       CfprApEquipmentSensorThresholdStatus
    MAX-ACCESS   read-only
    STATUS       current
    DESCRIPTION
        "Cisco Firepower adaptor:Unit:perf managed object property"
    ::= { cfprApAdaptorUnitEntry 23 }

cfprApAdaptorUnitPower OBJECT-TYPE
    SYNTAX       CfprApEquipmentPowerState
    MAX-ACCESS   read-only
    STATUS       current
    DESCRIPTION
        "Cisco Firepower adaptor:Unit:power managed object property"
    ::= { cfprApAdaptorUnitEntry 24 }

cfprApAdaptorUnitPresence OBJECT-TYPE
    SYNTAX       CfprApEquipmentPresence
    MAX-ACCESS   read-only
    STATUS       current
    DESCRIPTION
        "Cisco Firepower adaptor:Unit:presence managed object property"
    ::= { cfprApAdaptorUnitEntry 25 }

cfprApAdaptorUnitReachability OBJECT-TYPE
    SYNTAX       CfprApAdaptorReachability
    MAX-ACCESS   read-only
    STATUS       current
    DESCRIPTION
        "Cisco Firepower adaptor:Unit:reachability managed
        object property"
    ::= { cfprApAdaptorUnitEntry 26 }

cfprApAdaptorUnitRevision OBJECT-TYPE
    SYNTAX       SnmpAdminString
    MAX-ACCESS   read-only
    STATUS       current
    DESCRIPTION
        "Cisco Firepower adaptor:Unit:revision managed object property"
    ::= { cfprApAdaptorUnitEntry 27 }

cfprApAdaptorUnitSerial OBJECT-TYPE
    SYNTAX       SnmpAdminString
    MAX-ACCESS   read-only
    STATUS       current
    DESCRIPTION
        "Cisco Firepower adaptor:Unit:serial managed object property"
    ::= { cfprApAdaptorUnitEntry 28 }

cfprApAdaptorUnitThermal OBJECT-TYPE
    SYNTAX       CfprApEquipmentSensorThresholdStatus
    MAX-ACCESS   read-only
    STATUS       current
    DESCRIPTION
        "Cisco Firepower adaptor:Unit:thermal managed object property"
    ::= { cfprApAdaptorUnitEntry 29 }

cfprApAdaptorUnitVendor OBJECT-TYPE
    SYNTAX       SnmpAdminString
    MAX-ACCESS   read-only
    STATUS       current
    DESCRIPTION
        "Cisco Firepower adaptor:Unit:vendor managed object property"
    ::= { cfprApAdaptorUnitEntry 30 }

cfprApAdaptorUnitVoltage OBJECT-TYPE
    SYNTAX       CfprApEquipmentSensorThresholdStatus
    MAX-ACCESS   read-only
    STATUS       current
    DESCRIPTION
        "Cisco Firepower adaptor:Unit:voltage managed object property"
    ::= { cfprApAdaptorUnitEntry 31 }

cfprApAdaptorUnitAssocCtxTable OBJECT-TYPE
    SYNTAX           SEQUENCE OF CfprApAdaptorUnitAssocCtxEntry
    MAX-ACCESS       not-accessible
    STATUS           current
    DESCRIPTION
        "Cisco Firepower adaptor:UnitAssocCtx managed object table"
    ::= { cfprApAdaptorObjects 114 }

cfprApAdaptorUnitAssocCtxEntry OBJECT-TYPE
    SYNTAX           CfprApAdaptorUnitAssocCtxEntry
    MAX-ACCESS       not-accessible
    STATUS           current
    DESCRIPTION
        "Entry for the cfprApAdaptorUnitAssocCtxTable table."
    INDEX { cfprApAdaptorUnitAssocCtxInstanceId }
    ::= { cfprApAdaptorUnitAssocCtxTable 1 }

CfprApAdaptorUnitAssocCtxEntry ::= SEQUENCE {
    cfprApAdaptorUnitAssocCtxInstanceId                              CfprApManagedObjectId,
    cfprApAdaptorUnitAssocCtxDn                                      CfprApManagedObjectDn,
    cfprApAdaptorUnitAssocCtxRn                                      SnmpAdminString,
    cfprApAdaptorUnitAssocCtxFruCapDn                                SnmpAdminString,
    cfprApAdaptorUnitAssocCtxId                                      Gauge32,
    cfprApAdaptorUnitAssocCtxPciAddr                                 SnmpAdminString
}

cfprApAdaptorUnitAssocCtxInstanceId OBJECT-TYPE
    SYNTAX       CfprApManagedObjectId
    MAX-ACCESS   not-accessible
    STATUS       current
    DESCRIPTION
        "Instance identifier of the managed object."
    ::= { cfprApAdaptorUnitAssocCtxEntry 1 }

cfprApAdaptorUnitAssocCtxDn OBJECT-TYPE
    SYNTAX       CfprApManagedObjectDn
    MAX-ACCESS   read-only
    STATUS       current
    DESCRIPTION
        "Cisco Firepower adaptor:UnitAssocCtx:dn managed object property"
    ::= { cfprApAdaptorUnitAssocCtxEntry 2 }

cfprApAdaptorUnitAssocCtxRn OBJECT-TYPE
    SYNTAX       SnmpAdminString
    MAX-ACCESS   read-only
    STATUS       current
    DESCRIPTION
        "Cisco Firepower adaptor:UnitAssocCtx:rn managed object property"
    ::= { cfprApAdaptorUnitAssocCtxEntry 3 }

cfprApAdaptorUnitAssocCtxFruCapDn OBJECT-TYPE
    SYNTAX       SnmpAdminString
    MAX-ACCESS   read-only
    STATUS       current
    DESCRIPTION
        "Cisco Firepower adaptor:UnitAssocCtx:fruCapDn
        managed object property"
    ::= { cfprApAdaptorUnitAssocCtxEntry 4 }

cfprApAdaptorUnitAssocCtxId OBJECT-TYPE
    SYNTAX       Gauge32
    MAX-ACCESS   read-only
    STATUS       current
    DESCRIPTION
        "Cisco Firepower adaptor:UnitAssocCtx:id managed object property"
    ::= { cfprApAdaptorUnitAssocCtxEntry 5 }

cfprApAdaptorUnitAssocCtxPciAddr OBJECT-TYPE
    SYNTAX       SnmpAdminString
    MAX-ACCESS   read-only
    STATUS       current
    DESCRIPTION
        "Cisco Firepower adaptor:UnitAssocCtx:pciAddr managed
        object property"
    ::= { cfprApAdaptorUnitAssocCtxEntry 6 }

cfprApAdaptorUnitExtnTable OBJECT-TYPE
    SYNTAX           SEQUENCE OF CfprApAdaptorUnitExtnEntry
    MAX-ACCESS       not-accessible
    STATUS           current
    DESCRIPTION
        "Cisco Firepower adaptor:UnitExtn managed object table"
    ::= { cfprApAdaptorObjects 115 }

cfprApAdaptorUnitExtnEntry OBJECT-TYPE
    SYNTAX           CfprApAdaptorUnitExtnEntry
    MAX-ACCESS       not-accessible
    STATUS           current
    DESCRIPTION
        "Entry for the cfprApAdaptorUnitExtnTable table."
    INDEX { cfprApAdaptorUnitExtnInstanceId }
    ::= { cfprApAdaptorUnitExtnTable 1 }

CfprApAdaptorUnitExtnEntry ::= SEQUENCE {
    cfprApAdaptorUnitExtnInstanceId                                  CfprApManagedObjectId,
    cfprApAdaptorUnitExtnDn                                          CfprApManagedObjectDn,
    cfprApAdaptorUnitExtnRn                                          SnmpAdminString,
    cfprApAdaptorUnitExtnAdaptorId                                   Gauge32,
    cfprApAdaptorUnitExtnBladeId                                     Gauge32,
    cfprApAdaptorUnitExtnChassisId                                   Gauge32,
    cfprApAdaptorUnitExtnFltAggr                                     Unsigned64,
    cfprApAdaptorUnitExtnId                                          CfprApAdaptorUnitExtnId,
    cfprApAdaptorUnitExtnLocationDn                                  SnmpAdminString,
    cfprApAdaptorUnitExtnModel                                       SnmpAdminString,
    cfprApAdaptorUnitExtnOperQualifierReason                         SnmpAdminString,
    cfprApAdaptorUnitExtnOperState                                   CfprApEquipmentOperability,
    cfprApAdaptorUnitExtnOperability                                 CfprApEquipmentOperability,
    cfprApAdaptorUnitExtnPartNumber                                  SnmpAdminString,
    cfprApAdaptorUnitExtnPerf                                        CfprApEquipmentSensorThresholdStatus,
    cfprApAdaptorUnitExtnPower                                       CfprApEquipmentPowerState,
    cfprApAdaptorUnitExtnPresence                                    CfprApEquipmentPresence,
    cfprApAdaptorUnitExtnRevision                                    SnmpAdminString,
    cfprApAdaptorUnitExtnSerial                                      SnmpAdminString,
    cfprApAdaptorUnitExtnThermal                                     CfprApEquipmentSensorThresholdStatus,
    cfprApAdaptorUnitExtnVendor                                      SnmpAdminString,
    cfprApAdaptorUnitExtnVoltage                                     CfprApEquipmentSensorThresholdStatus
}

cfprApAdaptorUnitExtnInstanceId OBJECT-TYPE
    SYNTAX       CfprApManagedObjectId
    MAX-ACCESS   not-accessible
    STATUS       current
    DESCRIPTION
        "Instance identifier of the managed object."
    ::= { cfprApAdaptorUnitExtnEntry 1 }

cfprApAdaptorUnitExtnDn OBJECT-TYPE
    SYNTAX       CfprApManagedObjectDn
    MAX-ACCESS   read-only
    STATUS       current
    DESCRIPTION
        "Cisco Firepower adaptor:UnitExtn:dn managed object property"
    ::= { cfprApAdaptorUnitExtnEntry 2 }

cfprApAdaptorUnitExtnRn OBJECT-TYPE
    SYNTAX       SnmpAdminString
    MAX-ACCESS   read-only
    STATUS       current
    DESCRIPTION
        "Cisco Firepower adaptor:UnitExtn:rn managed object property"
    ::= { cfprApAdaptorUnitExtnEntry 3 }

cfprApAdaptorUnitExtnAdaptorId OBJECT-TYPE
    SYNTAX       Gauge32
    MAX-ACCESS   read-only
    STATUS       current
    DESCRIPTION
        "Cisco Firepower adaptor:UnitExtn:adaptorId managed
        object property"
    ::= { cfprApAdaptorUnitExtnEntry 4 }

cfprApAdaptorUnitExtnBladeId OBJECT-TYPE
    SYNTAX       Gauge32
    MAX-ACCESS   read-only
    STATUS       current
    DESCRIPTION
        "Cisco Firepower adaptor:UnitExtn:bladeId managed object property"
    ::= { cfprApAdaptorUnitExtnEntry 5 }

cfprApAdaptorUnitExtnChassisId OBJECT-TYPE
    SYNTAX       Gauge32
    MAX-ACCESS   read-only
    STATUS       current
    DESCRIPTION
        "Cisco Firepower adaptor:UnitExtn:chassisId managed
        object property"
    ::= { cfprApAdaptorUnitExtnEntry 6 }

cfprApAdaptorUnitExtnFltAggr OBJECT-TYPE
    SYNTAX       Unsigned64
    MAX-ACCESS   read-only
    STATUS       current
    DESCRIPTION
        "Cisco Firepower adaptor:UnitExtn:fltAggr managed object property"
    ::= { cfprApAdaptorUnitExtnEntry 7 }

cfprApAdaptorUnitExtnId OBJECT-TYPE
    SYNTAX       CfprApAdaptorUnitExtnId
    MAX-ACCESS   read-only
    STATUS       current
    DESCRIPTION
        "Cisco Firepower adaptor:UnitExtn:id managed object property"
    ::= { cfprApAdaptorUnitExtnEntry 8 }

cfprApAdaptorUnitExtnLocationDn OBJECT-TYPE
    SYNTAX       SnmpAdminString
    MAX-ACCESS   read-only
    STATUS       current
    DESCRIPTION
        "Cisco Firepower adaptor:UnitExtn:locationDn managed
        object property"
    ::= { cfprApAdaptorUnitExtnEntry 9 }

cfprApAdaptorUnitExtnModel OBJECT-TYPE
    SYNTAX       SnmpAdminString
    MAX-ACCESS   read-only
    STATUS       current
    DESCRIPTION
        "Cisco Firepower adaptor:UnitExtn:model managed object property"
    ::= { cfprApAdaptorUnitExtnEntry 10 }

cfprApAdaptorUnitExtnOperQualifierReason OBJECT-TYPE
    SYNTAX       SnmpAdminString
    MAX-ACCESS   read-only
    STATUS       current
    DESCRIPTION
        "Cisco Firepower adaptor:UnitExtn:operQualifierReason
        managed object property"
    ::= { cfprApAdaptorUnitExtnEntry 11 }

cfprApAdaptorUnitExtnOperState OBJECT-TYPE
    SYNTAX       CfprApEquipmentOperability
    MAX-ACCESS   read-only
    STATUS       current
    DESCRIPTION
        "Cisco Firepower adaptor:UnitExtn:operState managed
        object property"
    ::= { cfprApAdaptorUnitExtnEntry 12 }

cfprApAdaptorUnitExtnOperability OBJECT-TYPE
    SYNTAX       CfprApEquipmentOperability
    MAX-ACCESS   read-only
    STATUS       current
    DESCRIPTION
        "Cisco Firepower adaptor:UnitExtn:operability managed
        object property"
    ::= { cfprApAdaptorUnitExtnEntry 13 }

cfprApAdaptorUnitExtnPartNumber OBJECT-TYPE
    SYNTAX       SnmpAdminString
    MAX-ACCESS   read-only
    STATUS       current
    DESCRIPTION
        "Cisco Firepower adaptor:UnitExtn:partNumber managed
        object property"
    ::= { cfprApAdaptorUnitExtnEntry 14 }

cfprApAdaptorUnitExtnPerf OBJECT-TYPE
    SYNTAX       CfprApEquipmentSensorThresholdStatus
    MAX-ACCESS   read-only
    STATUS       current
    DESCRIPTION
        "Cisco Firepower adaptor:UnitExtn:perf managed object property"
    ::= { cfprApAdaptorUnitExtnEntry 15 }

cfprApAdaptorUnitExtnPower OBJECT-TYPE
    SYNTAX       CfprApEquipmentPowerState
    MAX-ACCESS   read-only
    STATUS       current
    DESCRIPTION
        "Cisco Firepower adaptor:UnitExtn:power managed object property"
    ::= { cfprApAdaptorUnitExtnEntry 16 }

cfprApAdaptorUnitExtnPresence OBJECT-TYPE
    SYNTAX       CfprApEquipmentPresence
    MAX-ACCESS   read-only
    STATUS       current
    DESCRIPTION
        "Cisco Firepower adaptor:UnitExtn:presence managed
        object property"
    ::= { cfprApAdaptorUnitExtnEntry 17 }

cfprApAdaptorUnitExtnRevision OBJECT-TYPE
    SYNTAX       SnmpAdminString
    MAX-ACCESS   read-only
    STATUS       current
    DESCRIPTION
        "Cisco Firepower adaptor:UnitExtn:revision managed
        object property"
    ::= { cfprApAdaptorUnitExtnEntry 18 }

cfprApAdaptorUnitExtnSerial OBJECT-TYPE
    SYNTAX       SnmpAdminString
    MAX-ACCESS   read-only
    STATUS       current
    DESCRIPTION
        "Cisco Firepower adaptor:UnitExtn:serial managed object property"
    ::= { cfprApAdaptorUnitExtnEntry 19 }

cfprApAdaptorUnitExtnThermal OBJECT-TYPE
    SYNTAX       CfprApEquipmentSensorThresholdStatus
    MAX-ACCESS   read-only
    STATUS       current
    DESCRIPTION
        "Cisco Firepower adaptor:UnitExtn:thermal managed object property"
    ::= { cfprApAdaptorUnitExtnEntry 20 }

cfprApAdaptorUnitExtnVendor OBJECT-TYPE
    SYNTAX       SnmpAdminString
    MAX-ACCESS   read-only
    STATUS       current
    DESCRIPTION
        "Cisco Firepower adaptor:UnitExtn:vendor managed object property"
    ::= { cfprApAdaptorUnitExtnEntry 21 }

cfprApAdaptorUnitExtnVoltage OBJECT-TYPE
    SYNTAX       CfprApEquipmentSensorThresholdStatus
    MAX-ACCESS   read-only
    STATUS       current
    DESCRIPTION
        "Cisco Firepower adaptor:UnitExtn:voltage managed object property"
    ::= { cfprApAdaptorUnitExtnEntry 22 }

cfprApAdaptorUplinkHwAddrCapTable OBJECT-TYPE
    SYNTAX           SEQUENCE OF CfprApAdaptorUplinkHwAddrCapEntry
    MAX-ACCESS       not-accessible
    STATUS           current
    DESCRIPTION
        "Cisco Firepower adaptor:UplinkHwAddrCap managed object table"
    ::= { cfprApAdaptorObjects 116 }

cfprApAdaptorUplinkHwAddrCapEntry OBJECT-TYPE
    SYNTAX           CfprApAdaptorUplinkHwAddrCapEntry
    MAX-ACCESS       not-accessible
    STATUS           current
    DESCRIPTION
        "Entry for the cfprApAdaptorUplinkHwAddrCapTable table."
    INDEX { cfprApAdaptorUplinkHwAddrCapInstanceId }
    ::= { cfprApAdaptorUplinkHwAddrCapTable 1 }

CfprApAdaptorUplinkHwAddrCapEntry ::= SEQUENCE {
    cfprApAdaptorUplinkHwAddrCapInstanceId                           CfprApManagedObjectId,
    cfprApAdaptorUplinkHwAddrCapDn                                   CfprApManagedObjectDn,
    cfprApAdaptorUplinkHwAddrCapRn                                   SnmpAdminString,
    cfprApAdaptorUplinkHwAddrCapLldpMacOffset1                       Gauge32,
    cfprApAdaptorUplinkHwAddrCapLldpMacOffset2                       Gauge32,
    cfprApAdaptorUplinkHwAddrCapMacOffset1                           Gauge32,
    cfprApAdaptorUplinkHwAddrCapMacOffset2                           Gauge32,
    cfprApAdaptorUplinkHwAddrCapMacOffsetSub00                       Gauge32,
    cfprApAdaptorUplinkHwAddrCapMacOffsetSub01                       Gauge32,
    cfprApAdaptorUplinkHwAddrCapMacOffsetSub02                       Gauge32,
    cfprApAdaptorUplinkHwAddrCapMacOffsetSub03                       Gauge32,
    cfprApAdaptorUplinkHwAddrCapMacOffsetSub10                       Gauge32,
    cfprApAdaptorUplinkHwAddrCapMacOffsetSub11                       Gauge32,
    cfprApAdaptorUplinkHwAddrCapMacOffsetSub12                       Gauge32,
    cfprApAdaptorUplinkHwAddrCapMacOffsetSub13                       Gauge32
}

cfprApAdaptorUplinkHwAddrCapInstanceId OBJECT-TYPE
    SYNTAX       CfprApManagedObjectId
    MAX-ACCESS   not-accessible
    STATUS       current
    DESCRIPTION
        "Instance identifier of the managed object."
    ::= { cfprApAdaptorUplinkHwAddrCapEntry 1 }

cfprApAdaptorUplinkHwAddrCapDn OBJECT-TYPE
    SYNTAX       CfprApManagedObjectDn
    MAX-ACCESS   read-only
    STATUS       current
    DESCRIPTION
        "Cisco Firepower adaptor:UplinkHwAddrCap:dn managed
        object property"
    ::= { cfprApAdaptorUplinkHwAddrCapEntry 2 }

cfprApAdaptorUplinkHwAddrCapRn OBJECT-TYPE
    SYNTAX       SnmpAdminString
    MAX-ACCESS   read-only
    STATUS       current
    DESCRIPTION
        "Cisco Firepower adaptor:UplinkHwAddrCap:rn managed
        object property"
    ::= { cfprApAdaptorUplinkHwAddrCapEntry 3 }

cfprApAdaptorUplinkHwAddrCapLldpMacOffset1 OBJECT-TYPE
    SYNTAX       Gauge32
    MAX-ACCESS   read-only
    STATUS       current
    DESCRIPTION
        "Cisco Firepower adaptor:UplinkHwAddrCap:lldpMacOffset1
        managed object property"
    ::= { cfprApAdaptorUplinkHwAddrCapEntry 4 }

cfprApAdaptorUplinkHwAddrCapLldpMacOffset2 OBJECT-TYPE
    SYNTAX       Gauge32
    MAX-ACCESS   read-only
    STATUS       current
    DESCRIPTION
        "Cisco Firepower adaptor:UplinkHwAddrCap:lldpMacOffset2
        managed object property"
    ::= { cfprApAdaptorUplinkHwAddrCapEntry 5 }

cfprApAdaptorUplinkHwAddrCapMacOffset1 OBJECT-TYPE
    SYNTAX       Gauge32
    MAX-ACCESS   read-only
    STATUS       current
    DESCRIPTION
        "Cisco Firepower adaptor:UplinkHwAddrCap:macOffset1
        managed object property"
    ::= { cfprApAdaptorUplinkHwAddrCapEntry 6 }

cfprApAdaptorUplinkHwAddrCapMacOffset2 OBJECT-TYPE
    SYNTAX       Gauge32
    MAX-ACCESS   read-only
    STATUS       current
    DESCRIPTION
        "Cisco Firepower adaptor:UplinkHwAddrCap:macOffset2
        managed object property"
    ::= { cfprApAdaptorUplinkHwAddrCapEntry 7 }

cfprApAdaptorUplinkHwAddrCapMacOffsetSub00 OBJECT-TYPE
    SYNTAX       Gauge32
    MAX-ACCESS   read-only
    STATUS       current
    DESCRIPTION
        "Cisco Firepower adaptor:UplinkHwAddrCap:macOffsetSub00
        managed object property"
    ::= { cfprApAdaptorUplinkHwAddrCapEntry 8 }

cfprApAdaptorUplinkHwAddrCapMacOffsetSub01 OBJECT-TYPE
    SYNTAX       Gauge32
    MAX-ACCESS   read-only
    STATUS       current
    DESCRIPTION
        "Cisco Firepower adaptor:UplinkHwAddrCap:macOffsetSub01
        managed object property"
    ::= { cfprApAdaptorUplinkHwAddrCapEntry 9 }

cfprApAdaptorUplinkHwAddrCapMacOffsetSub02 OBJECT-TYPE
    SYNTAX       Gauge32
    MAX-ACCESS   read-only
    STATUS       current
    DESCRIPTION
        "Cisco Firepower adaptor:UplinkHwAddrCap:macOffsetSub02
        managed object property"
    ::= { cfprApAdaptorUplinkHwAddrCapEntry 10 }

cfprApAdaptorUplinkHwAddrCapMacOffsetSub03 OBJECT-TYPE
    SYNTAX       Gauge32
    MAX-ACCESS   read-only
    STATUS       current
    DESCRIPTION
        "Cisco Firepower adaptor:UplinkHwAddrCap:macOffsetSub03
        managed object property"
    ::= { cfprApAdaptorUplinkHwAddrCapEntry 11 }

cfprApAdaptorUplinkHwAddrCapMacOffsetSub10 OBJECT-TYPE
    SYNTAX       Gauge32
    MAX-ACCESS   read-only
    STATUS       current
    DESCRIPTION
        "Cisco Firepower adaptor:UplinkHwAddrCap:macOffsetSub10
        managed object property"
    ::= { cfprApAdaptorUplinkHwAddrCapEntry 12 }

cfprApAdaptorUplinkHwAddrCapMacOffsetSub11 OBJECT-TYPE
    SYNTAX       Gauge32
    MAX-ACCESS   read-only
    STATUS       current
    DESCRIPTION
        "Cisco Firepower adaptor:UplinkHwAddrCap:macOffsetSub11
        managed object property"
    ::= { cfprApAdaptorUplinkHwAddrCapEntry 13 }

cfprApAdaptorUplinkHwAddrCapMacOffsetSub12 OBJECT-TYPE
    SYNTAX       Gauge32
    MAX-ACCESS   read-only
    STATUS       current
    DESCRIPTION
        "Cisco Firepower adaptor:UplinkHwAddrCap:macOffsetSub12
        managed object property"
    ::= { cfprApAdaptorUplinkHwAddrCapEntry 14 }

cfprApAdaptorUplinkHwAddrCapMacOffsetSub13 OBJECT-TYPE
    SYNTAX       Gauge32
    MAX-ACCESS   read-only
    STATUS       current
    DESCRIPTION
        "Cisco Firepower adaptor:UplinkHwAddrCap:macOffsetSub13
        managed object property"
    ::= { cfprApAdaptorUplinkHwAddrCapEntry 15 }

cfprApAdaptorUsnicConnDefTable OBJECT-TYPE
    SYNTAX           SEQUENCE OF CfprApAdaptorUsnicConnDefEntry
    MAX-ACCESS       not-accessible
    STATUS           current
    DESCRIPTION
        "Cisco Firepower adaptor:UsnicConnDef managed object table"
    ::= { cfprApAdaptorObjects 117 }

cfprApAdaptorUsnicConnDefEntry OBJECT-TYPE
    SYNTAX           CfprApAdaptorUsnicConnDefEntry
    MAX-ACCESS       not-accessible
    STATUS           current
    DESCRIPTION
        "Entry for the cfprApAdaptorUsnicConnDefTable table."
    INDEX { cfprApAdaptorUsnicConnDefInstanceId }
    ::= { cfprApAdaptorUsnicConnDefTable 1 }

CfprApAdaptorUsnicConnDefEntry ::= SEQUENCE {
    cfprApAdaptorUsnicConnDefInstanceId                              CfprApManagedObjectId,
    cfprApAdaptorUsnicConnDefDn                                      CfprApManagedObjectDn,
    cfprApAdaptorUsnicConnDefRn                                      SnmpAdminString,
    cfprApAdaptorUsnicConnDefConPolicyName                           SnmpAdminString,
    cfprApAdaptorUsnicConnDefUsnicCount                              Gauge32
}

cfprApAdaptorUsnicConnDefInstanceId OBJECT-TYPE
    SYNTAX       CfprApManagedObjectId
    MAX-ACCESS   not-accessible
    STATUS       current
    DESCRIPTION
        "Instance identifier of the managed object."
    ::= { cfprApAdaptorUsnicConnDefEntry 1 }

cfprApAdaptorUsnicConnDefDn OBJECT-TYPE
    SYNTAX       CfprApManagedObjectDn
    MAX-ACCESS   read-only
    STATUS       current
    DESCRIPTION
        "Cisco Firepower adaptor:UsnicConnDef:dn managed object property"
    ::= { cfprApAdaptorUsnicConnDefEntry 2 }

cfprApAdaptorUsnicConnDefRn OBJECT-TYPE
    SYNTAX       SnmpAdminString
    MAX-ACCESS   read-only
    STATUS       current
    DESCRIPTION
        "Cisco Firepower adaptor:UsnicConnDef:rn managed object property"
    ::= { cfprApAdaptorUsnicConnDefEntry 3 }

cfprApAdaptorUsnicConnDefConPolicyName OBJECT-TYPE
    SYNTAX       SnmpAdminString
    MAX-ACCESS   read-only
    STATUS       current
    DESCRIPTION
        "Cisco Firepower adaptor:UsnicConnDef:conPolicyName
        managed object property"
    ::= { cfprApAdaptorUsnicConnDefEntry 4 }

cfprApAdaptorUsnicConnDefUsnicCount OBJECT-TYPE
    SYNTAX       Gauge32
    MAX-ACCESS   read-only
    STATUS       current
    DESCRIPTION
        "Cisco Firepower adaptor:UsnicConnDef:usnicCount
        managed object property"
    ::= { cfprApAdaptorUsnicConnDefEntry 5 }

cfprApAdaptorVlanTable OBJECT-TYPE
    SYNTAX           SEQUENCE OF CfprApAdaptorVlanEntry
    MAX-ACCESS       not-accessible
    STATUS           current
    DESCRIPTION
        "Cisco Firepower adaptor:Vlan managed object table"
    ::= { cfprApAdaptorObjects 118 }

cfprApAdaptorVlanEntry OBJECT-TYPE
    SYNTAX           CfprApAdaptorVlanEntry
    MAX-ACCESS       not-accessible
    STATUS           current
    DESCRIPTION
        "Entry for the cfprApAdaptorVlanTable table."
    INDEX { cfprApAdaptorVlanInstanceId }
    ::= { cfprApAdaptorVlanTable 1 }

CfprApAdaptorVlanEntry ::= SEQUENCE {
    cfprApAdaptorVlanInstanceId                                      CfprApManagedObjectId,
    cfprApAdaptorVlanDn                                              CfprApManagedObjectDn,
    cfprApAdaptorVlanRn                                              SnmpAdminString,
    cfprApAdaptorVlanAssocPrimaryVlanState                           CfprApFabricVlanAssocPrimaryVlanState,
    cfprApAdaptorVlanAssocPrimaryVlanSwitchId                        CfprApFabricAVlanAssocPrimaryVlanSwitchId,
    cfprApAdaptorVlanEpDn                                            SnmpAdminString,
    cfprApAdaptorVlanId                                              Gauge32,
    cfprApAdaptorVlanIfRole                                          CfprApFabricVnetEpIfRole,
    cfprApAdaptorVlanIfType                                          CfprApNetworkVnetEpIfType,
    cfprApAdaptorVlanLc                                              CfprApFsmLifecycle,
    cfprApAdaptorVlanLocale                                          CfprApFabricVnetEpLocale,
    cfprApAdaptorVlanName                                            SnmpAdminString,
    cfprApAdaptorVlanOperState                                       CfprApFabricVlanOperState,
    cfprApAdaptorVlanOverlapStateForA                                CfprApFabricVlanOverlapState,
    cfprApAdaptorVlanOverlapStateForB                                CfprApFabricVlanOverlapState,
    cfprApAdaptorVlanPeerDn                                          SnmpAdminString,
    cfprApAdaptorVlanPolicyOwner                                     CfprApFabricVnetEpPolicyOwner,
    cfprApAdaptorVlanPubNwDn                                         SnmpAdminString,
    cfprApAdaptorVlanPubNwId                                         Gauge32,
    cfprApAdaptorVlanPubNwName                                       SnmpAdminString,
    cfprApAdaptorVlanSharing                                         CfprApFabricAVlanSharing,
    cfprApAdaptorVlanSwitchId                                        CfprApNetworkSwitchId,
    cfprApAdaptorVlanTransport                                       CfprApFabricAVlanTransport,
    cfprApAdaptorVlanType                                            CfprApFabricAVlanType,
    cfprApAdaptorVlanVlanType                                        CfprApFabricEpVlanVlanType
}

cfprApAdaptorVlanInstanceId OBJECT-TYPE
    SYNTAX       CfprApManagedObjectId
    MAX-ACCESS   not-accessible
    STATUS       current
    DESCRIPTION
        "Instance identifier of the managed object."
    ::= { cfprApAdaptorVlanEntry 1 }

cfprApAdaptorVlanDn OBJECT-TYPE
    SYNTAX       CfprApManagedObjectDn
    MAX-ACCESS   read-only
    STATUS       current
    DESCRIPTION
        "Cisco Firepower adaptor:Vlan:dn managed object property"
    ::= { cfprApAdaptorVlanEntry 2 }

cfprApAdaptorVlanRn OBJECT-TYPE
    SYNTAX       SnmpAdminString
    MAX-ACCESS   read-only
    STATUS       current
    DESCRIPTION
        "Cisco Firepower adaptor:Vlan:rn managed object property"
    ::= { cfprApAdaptorVlanEntry 3 }

cfprApAdaptorVlanAssocPrimaryVlanState OBJECT-TYPE
    SYNTAX       CfprApFabricVlanAssocPrimaryVlanState
    MAX-ACCESS   read-only
    STATUS       current
    DESCRIPTION
        "Cisco Firepower adaptor:Vlan:assocPrimaryVlanState
        managed object property"
    ::= { cfprApAdaptorVlanEntry 4 }

cfprApAdaptorVlanAssocPrimaryVlanSwitchId OBJECT-TYPE
    SYNTAX       CfprApFabricAVlanAssocPrimaryVlanSwitchId
    MAX-ACCESS   read-only
    STATUS       current
    DESCRIPTION
        "Cisco Firepower adaptor:Vlan:assocPrimaryVlanSwitchId
        managed object property"
    ::= { cfprApAdaptorVlanEntry 5 }

cfprApAdaptorVlanEpDn OBJECT-TYPE
    SYNTAX       SnmpAdminString
    MAX-ACCESS   read-only
    STATUS       current
    DESCRIPTION
        "Cisco Firepower adaptor:Vlan:epDn managed object property"
    ::= { cfprApAdaptorVlanEntry 6 }

cfprApAdaptorVlanId OBJECT-TYPE
    SYNTAX       Gauge32
    MAX-ACCESS   read-only
    STATUS       current
    DESCRIPTION
        "Cisco Firepower adaptor:Vlan:id managed object property"
    ::= { cfprApAdaptorVlanEntry 7 }

cfprApAdaptorVlanIfRole OBJECT-TYPE
    SYNTAX       CfprApFabricVnetEpIfRole
    MAX-ACCESS   read-only
    STATUS       current
    DESCRIPTION
        "Cisco Firepower adaptor:Vlan:ifRole managed object property"
    ::= { cfprApAdaptorVlanEntry 8 }

cfprApAdaptorVlanIfType OBJECT-TYPE
    SYNTAX       CfprApNetworkVnetEpIfType
    MAX-ACCESS   read-only
    STATUS       current
    DESCRIPTION
        "Cisco Firepower adaptor:Vlan:ifType managed object property"
    ::= { cfprApAdaptorVlanEntry 9 }

cfprApAdaptorVlanLc OBJECT-TYPE
    SYNTAX       CfprApFsmLifecycle
    MAX-ACCESS   read-only
    STATUS       current
    DESCRIPTION
        "Cisco Firepower adaptor:Vlan:lc managed object property"
    ::= { cfprApAdaptorVlanEntry 10 }

cfprApAdaptorVlanLocale OBJECT-TYPE
    SYNTAX       CfprApFabricVnetEpLocale
    MAX-ACCESS   read-only
    STATUS       current
    DESCRIPTION
        "Cisco Firepower adaptor:Vlan:locale managed object property"
    ::= { cfprApAdaptorVlanEntry 11 }

cfprApAdaptorVlanName OBJECT-TYPE
    SYNTAX       SnmpAdminString
    MAX-ACCESS   read-only
    STATUS       current
    DESCRIPTION
        "Cisco Firepower adaptor:Vlan:name managed object property"
    ::= { cfprApAdaptorVlanEntry 12 }

cfprApAdaptorVlanOperState OBJECT-TYPE
    SYNTAX       CfprApFabricVlanOperState
    MAX-ACCESS   read-only
    STATUS       current
    DESCRIPTION
        "Cisco Firepower adaptor:Vlan:operState managed object property"
    ::= { cfprApAdaptorVlanEntry 13 }

cfprApAdaptorVlanOverlapStateForA OBJECT-TYPE
    SYNTAX       CfprApFabricVlanOverlapState
    MAX-ACCESS   read-only
    STATUS       current
    DESCRIPTION
        "Cisco Firepower adaptor:Vlan:overlapStateForA
        managed object property"
    ::= { cfprApAdaptorVlanEntry 14 }

cfprApAdaptorVlanOverlapStateForB OBJECT-TYPE
    SYNTAX       CfprApFabricVlanOverlapState
    MAX-ACCESS   read-only
    STATUS       current
    DESCRIPTION
        "Cisco Firepower adaptor:Vlan:overlapStateForB
        managed object property"
    ::= { cfprApAdaptorVlanEntry 15 }

cfprApAdaptorVlanPeerDn OBJECT-TYPE
    SYNTAX       SnmpAdminString
    MAX-ACCESS   read-only
    STATUS       current
    DESCRIPTION
        "Cisco Firepower adaptor:Vlan:peerDn managed object property"
    ::= { cfprApAdaptorVlanEntry 16 }

cfprApAdaptorVlanPolicyOwner OBJECT-TYPE
    SYNTAX       CfprApFabricVnetEpPolicyOwner
    MAX-ACCESS   read-only
    STATUS       current
    DESCRIPTION
        "Cisco Firepower adaptor:Vlan:policyOwner managed object property"
    ::= { cfprApAdaptorVlanEntry 17 }

cfprApAdaptorVlanPubNwDn OBJECT-TYPE
    SYNTAX       SnmpAdminString
    MAX-ACCESS   read-only
    STATUS       current
    DESCRIPTION
        "Cisco Firepower adaptor:Vlan:pubNwDn managed object property"
    ::= { cfprApAdaptorVlanEntry 18 }

cfprApAdaptorVlanPubNwId OBJECT-TYPE
    SYNTAX       Gauge32
    MAX-ACCESS   read-only
    STATUS       current
    DESCRIPTION
        "Cisco Firepower adaptor:Vlan:pubNwId managed object property"
    ::= { cfprApAdaptorVlanEntry 19 }

cfprApAdaptorVlanPubNwName OBJECT-TYPE
    SYNTAX       SnmpAdminString
    MAX-ACCESS   read-only
    STATUS       current
    DESCRIPTION
        "Cisco Firepower adaptor:Vlan:pubNwName managed object property"
    ::= { cfprApAdaptorVlanEntry 20 }

cfprApAdaptorVlanSharing OBJECT-TYPE
    SYNTAX       CfprApFabricAVlanSharing
    MAX-ACCESS   read-only
    STATUS       current
    DESCRIPTION
        "Cisco Firepower adaptor:Vlan:sharing managed object property"
    ::= { cfprApAdaptorVlanEntry 21 }

cfprApAdaptorVlanSwitchId OBJECT-TYPE
    SYNTAX       CfprApNetworkSwitchId
    MAX-ACCESS   read-only
    STATUS       current
    DESCRIPTION
        "Cisco Firepower adaptor:Vlan:switchId managed object property"
    ::= { cfprApAdaptorVlanEntry 22 }

cfprApAdaptorVlanTransport OBJECT-TYPE
    SYNTAX       CfprApFabricAVlanTransport
    MAX-ACCESS   read-only
    STATUS       current
    DESCRIPTION
        "Cisco Firepower adaptor:Vlan:transport managed object property"
    ::= { cfprApAdaptorVlanEntry 23 }

cfprApAdaptorVlanType OBJECT-TYPE
    SYNTAX       CfprApFabricAVlanType
    MAX-ACCESS   read-only
    STATUS       current
    DESCRIPTION
        "Cisco Firepower adaptor:Vlan:type managed object property"
    ::= { cfprApAdaptorVlanEntry 24 }

cfprApAdaptorVlanVlanType OBJECT-TYPE
    SYNTAX       CfprApFabricEpVlanVlanType
    MAX-ACCESS   read-only
    STATUS       current
    DESCRIPTION
        "Cisco Firepower adaptor:Vlan:vlanType managed object property"
    ::= { cfprApAdaptorVlanEntry 25 }

cfprApAdaptorVnicStatsTable OBJECT-TYPE
    SYNTAX           SEQUENCE OF CfprApAdaptorVnicStatsEntry
    MAX-ACCESS       not-accessible
    STATUS           current
    DESCRIPTION
        "Cisco Firepower adaptor:VnicStats managed object table"
    ::= { cfprApAdaptorObjects 119 }

cfprApAdaptorVnicStatsEntry OBJECT-TYPE
    SYNTAX           CfprApAdaptorVnicStatsEntry
    MAX-ACCESS       not-accessible
    STATUS           current
    DESCRIPTION
        "Entry for the cfprApAdaptorVnicStatsTable table."
    INDEX { cfprApAdaptorVnicStatsInstanceId }
    ::= { cfprApAdaptorVnicStatsTable 1 }

CfprApAdaptorVnicStatsEntry ::= SEQUENCE {
    cfprApAdaptorVnicStatsInstanceId                                 CfprApManagedObjectId,
    cfprApAdaptorVnicStatsDn                                         CfprApManagedObjectDn,
    cfprApAdaptorVnicStatsRn                                         SnmpAdminString,
    cfprApAdaptorVnicStatsBytesRx                                    Unsigned64,
    cfprApAdaptorVnicStatsBytesRxDelta                               Counter64,
    cfprApAdaptorVnicStatsBytesRxDeltaAvg                            Unsigned64,
    cfprApAdaptorVnicStatsBytesRxDeltaMax                            Unsigned64,
    cfprApAdaptorVnicStatsBytesRxDeltaMin                            Unsigned64,
    cfprApAdaptorVnicStatsBytesTx                                    Unsigned64,
    cfprApAdaptorVnicStatsBytesTxDelta                               Counter64,
    cfprApAdaptorVnicStatsBytesTxDeltaAvg                            Unsigned64,
    cfprApAdaptorVnicStatsBytesTxDeltaMax                            Unsigned64,
    cfprApAdaptorVnicStatsBytesTxDeltaMin                            Unsigned64,
    cfprApAdaptorVnicStatsDroppedRx                                  Unsigned64,
    cfprApAdaptorVnicStatsDroppedRxDelta                             Counter64,
    cfprApAdaptorVnicStatsDroppedRxDeltaAvg                          Unsigned64,
    cfprApAdaptorVnicStatsDroppedRxDeltaMax                          Unsigned64,
    cfprApAdaptorVnicStatsDroppedRxDeltaMin                          Unsigned64,
    cfprApAdaptorVnicStatsDroppedTx                                  Unsigned64,
    cfprApAdaptorVnicStatsDroppedTxDelta                             Counter64,
    cfprApAdaptorVnicStatsDroppedTxDeltaAvg                          Unsigned64,
    cfprApAdaptorVnicStatsDroppedTxDeltaMax                          Unsigned64,
    cfprApAdaptorVnicStatsDroppedTxDeltaMin                          Unsigned64,
    cfprApAdaptorVnicStatsErrorsRx                                   Unsigned64,
    cfprApAdaptorVnicStatsErrorsRxDelta                              Counter64,
    cfprApAdaptorVnicStatsErrorsRxDeltaAvg                           Unsigned64,
    cfprApAdaptorVnicStatsErrorsRxDeltaMax                           Unsigned64,
    cfprApAdaptorVnicStatsErrorsRxDeltaMin                           Unsigned64,
    cfprApAdaptorVnicStatsErrorsTx                                   Unsigned64,
    cfprApAdaptorVnicStatsErrorsTxDelta                              Counter64,
    cfprApAdaptorVnicStatsErrorsTxDeltaAvg                           Unsigned64,
    cfprApAdaptorVnicStatsErrorsTxDeltaMax                           Unsigned64,
    cfprApAdaptorVnicStatsErrorsTxDeltaMin                           Unsigned64,
    cfprApAdaptorVnicStatsIntervals                                  Gauge32,
    cfprApAdaptorVnicStatsPacketsRx                                  Unsigned64,
    cfprApAdaptorVnicStatsPacketsRxDelta                             Counter64,
    cfprApAdaptorVnicStatsPacketsRxDeltaAvg                          Unsigned64,
    cfprApAdaptorVnicStatsPacketsRxDeltaMax                          Unsigned64,
    cfprApAdaptorVnicStatsPacketsRxDeltaMin                          Unsigned64,
    cfprApAdaptorVnicStatsPacketsTx                                  Unsigned64,
    cfprApAdaptorVnicStatsPacketsTxDelta                             Counter64,
    cfprApAdaptorVnicStatsPacketsTxDeltaAvg                          Unsigned64,
    cfprApAdaptorVnicStatsPacketsTxDeltaMax                          Unsigned64,
    cfprApAdaptorVnicStatsPacketsTxDeltaMin                          Unsigned64,
    cfprApAdaptorVnicStatsSuspect                                    TruthValue,
    cfprApAdaptorVnicStatsThresholded                                CfprApAdaptorVnicStatsThresholded,
    cfprApAdaptorVnicStatsTimeCollected                              DateAndTime,
    cfprApAdaptorVnicStatsUpdate                                     Gauge32
}

cfprApAdaptorVnicStatsInstanceId OBJECT-TYPE
    SYNTAX       CfprApManagedObjectId
    MAX-ACCESS   not-accessible
    STATUS       current
    DESCRIPTION
        "Instance identifier of the managed object."
    ::= { cfprApAdaptorVnicStatsEntry 1 }

cfprApAdaptorVnicStatsDn OBJECT-TYPE
    SYNTAX       CfprApManagedObjectDn
    MAX-ACCESS   read-only
    STATUS       current
    DESCRIPTION
        "Cisco Firepower adaptor:VnicStats:dn managed object property"
    ::= { cfprApAdaptorVnicStatsEntry 2 }

cfprApAdaptorVnicStatsRn OBJECT-TYPE
    SYNTAX       SnmpAdminString
    MAX-ACCESS   read-only
    STATUS       current
    DESCRIPTION
        "Cisco Firepower adaptor:VnicStats:rn managed object property"
    ::= { cfprApAdaptorVnicStatsEntry 3 }

cfprApAdaptorVnicStatsBytesRx OBJECT-TYPE
    SYNTAX       Unsigned64
    MAX-ACCESS   read-only
    STATUS       current
    DESCRIPTION
        "Cisco Firepower adaptor:VnicStats:bytesRx managed
        object property"
    ::= { cfprApAdaptorVnicStatsEntry 4 }

cfprApAdaptorVnicStatsBytesRxDelta OBJECT-TYPE
    SYNTAX       Counter64
    MAX-ACCESS   read-only
    STATUS       current
    DESCRIPTION
        "Cisco Firepower adaptor:VnicStats:bytesRxDelta
        managed object property"
    ::= { cfprApAdaptorVnicStatsEntry 5 }

cfprApAdaptorVnicStatsBytesRxDeltaAvg OBJECT-TYPE
    SYNTAX       Unsigned64
    MAX-ACCESS   read-only
    STATUS       current
    DESCRIPTION
        "Cisco Firepower adaptor:VnicStats:bytesRxDeltaAvg
        managed object property"
    ::= { cfprApAdaptorVnicStatsEntry 6 }

cfprApAdaptorVnicStatsBytesRxDeltaMax OBJECT-TYPE
    SYNTAX       Unsigned64
    MAX-ACCESS   read-only
    STATUS       current
    DESCRIPTION
        "Cisco Firepower adaptor:VnicStats:bytesRxDeltaMax
        managed object property"
    ::= { cfprApAdaptorVnicStatsEntry 7 }

cfprApAdaptorVnicStatsBytesRxDeltaMin OBJECT-TYPE
    SYNTAX       Unsigned64
    MAX-ACCESS   read-only
    STATUS       current
    DESCRIPTION
        "Cisco Firepower adaptor:VnicStats:bytesRxDeltaMin
        managed object property"
    ::= { cfprApAdaptorVnicStatsEntry 8 }

cfprApAdaptorVnicStatsBytesTx OBJECT-TYPE
    SYNTAX       Unsigned64
    MAX-ACCESS   read-only
    STATUS       current
    DESCRIPTION
        "Cisco Firepower adaptor:VnicStats:bytesTx managed
        object property"
    ::= { cfprApAdaptorVnicStatsEntry 9 }

cfprApAdaptorVnicStatsBytesTxDelta OBJECT-TYPE
    SYNTAX       Counter64
    MAX-ACCESS   read-only
    STATUS       current
    DESCRIPTION
        "Cisco Firepower adaptor:VnicStats:bytesTxDelta
        managed object property"
    ::= { cfprApAdaptorVnicStatsEntry 10 }

cfprApAdaptorVnicStatsBytesTxDeltaAvg OBJECT-TYPE
    SYNTAX       Unsigned64
    MAX-ACCESS   read-only
    STATUS       current
    DESCRIPTION
        "Cisco Firepower adaptor:VnicStats:bytesTxDeltaAvg
        managed object property"
    ::= { cfprApAdaptorVnicStatsEntry 11 }

cfprApAdaptorVnicStatsBytesTxDeltaMax OBJECT-TYPE
    SYNTAX       Unsigned64
    MAX-ACCESS   read-only
    STATUS       current
    DESCRIPTION
        "Cisco Firepower adaptor:VnicStats:bytesTxDeltaMax
        managed object property"
    ::= { cfprApAdaptorVnicStatsEntry 12 }

cfprApAdaptorVnicStatsBytesTxDeltaMin OBJECT-TYPE
    SYNTAX       Unsigned64
    MAX-ACCESS   read-only
    STATUS       current
    DESCRIPTION
        "Cisco Firepower adaptor:VnicStats:bytesTxDeltaMin
        managed object property"
    ::= { cfprApAdaptorVnicStatsEntry 13 }

cfprApAdaptorVnicStatsDroppedRx OBJECT-TYPE
    SYNTAX       Unsigned64
    MAX-ACCESS   read-only
    STATUS       current
    DESCRIPTION
        "Cisco Firepower adaptor:VnicStats:droppedRx managed
        object property"
    ::= { cfprApAdaptorVnicStatsEntry 14 }

cfprApAdaptorVnicStatsDroppedRxDelta OBJECT-TYPE
    SYNTAX       Counter64
    MAX-ACCESS   read-only
    STATUS       current
    DESCRIPTION
        "Cisco Firepower adaptor:VnicStats:droppedRxDelta
        managed object property"
    ::= { cfprApAdaptorVnicStatsEntry 15 }

cfprApAdaptorVnicStatsDroppedRxDeltaAvg OBJECT-TYPE
    SYNTAX       Unsigned64
    MAX-ACCESS   read-only
    STATUS       current
    DESCRIPTION
        "Cisco Firepower adaptor:VnicStats:droppedRxDeltaAvg
        managed object property"
    ::= { cfprApAdaptorVnicStatsEntry 16 }

cfprApAdaptorVnicStatsDroppedRxDeltaMax OBJECT-TYPE
    SYNTAX       Unsigned64
    MAX-ACCESS   read-only
    STATUS       current
    DESCRIPTION
        "Cisco Firepower adaptor:VnicStats:droppedRxDeltaMax
        managed object property"
    ::= { cfprApAdaptorVnicStatsEntry 17 }

cfprApAdaptorVnicStatsDroppedRxDeltaMin OBJECT-TYPE
    SYNTAX       Unsigned64
    MAX-ACCESS   read-only
    STATUS       current
    DESCRIPTION
        "Cisco Firepower adaptor:VnicStats:droppedRxDeltaMin
        managed object property"
    ::= { cfprApAdaptorVnicStatsEntry 18 }

cfprApAdaptorVnicStatsDroppedTx OBJECT-TYPE
    SYNTAX       Unsigned64
    MAX-ACCESS   read-only
    STATUS       current
    DESCRIPTION
        "Cisco Firepower adaptor:VnicStats:droppedTx managed
        object property"
    ::= { cfprApAdaptorVnicStatsEntry 19 }

cfprApAdaptorVnicStatsDroppedTxDelta OBJECT-TYPE
    SYNTAX       Counter64
    MAX-ACCESS   read-only
    STATUS       current
    DESCRIPTION
        "Cisco Firepower adaptor:VnicStats:droppedTxDelta
        managed object property"
    ::= { cfprApAdaptorVnicStatsEntry 20 }

cfprApAdaptorVnicStatsDroppedTxDeltaAvg OBJECT-TYPE
    SYNTAX       Unsigned64
    MAX-ACCESS   read-only
    STATUS       current
    DESCRIPTION
        "Cisco Firepower adaptor:VnicStats:droppedTxDeltaAvg
        managed object property"
    ::= { cfprApAdaptorVnicStatsEntry 21 }

cfprApAdaptorVnicStatsDroppedTxDeltaMax OBJECT-TYPE
    SYNTAX       Unsigned64
    MAX-ACCESS   read-only
    STATUS       current
    DESCRIPTION
        "Cisco Firepower adaptor:VnicStats:droppedTxDeltaMax
        managed object property"
    ::= { cfprApAdaptorVnicStatsEntry 22 }

cfprApAdaptorVnicStatsDroppedTxDeltaMin OBJECT-TYPE
    SYNTAX       Unsigned64
    MAX-ACCESS   read-only
    STATUS       current
    DESCRIPTION
        "Cisco Firepower adaptor:VnicStats:droppedTxDeltaMin
        managed object property"
    ::= { cfprApAdaptorVnicStatsEntry 23 }

cfprApAdaptorVnicStatsErrorsRx OBJECT-TYPE
    SYNTAX       Unsigned64
    MAX-ACCESS   read-only
    STATUS       current
    DESCRIPTION
        "Cisco Firepower adaptor:VnicStats:errorsRx managed
        object property"
    ::= { cfprApAdaptorVnicStatsEntry 24 }

cfprApAdaptorVnicStatsErrorsRxDelta OBJECT-TYPE
    SYNTAX       Counter64
    MAX-ACCESS   read-only
    STATUS       current
    DESCRIPTION
        "Cisco Firepower adaptor:VnicStats:errorsRxDelta
        managed object property"
    ::= { cfprApAdaptorVnicStatsEntry 25 }

cfprApAdaptorVnicStatsErrorsRxDeltaAvg OBJECT-TYPE
    SYNTAX       Unsigned64
    MAX-ACCESS   read-only
    STATUS       current
    DESCRIPTION
        "Cisco Firepower adaptor:VnicStats:errorsRxDeltaAvg
        managed object property"
    ::= { cfprApAdaptorVnicStatsEntry 26 }

cfprApAdaptorVnicStatsErrorsRxDeltaMax OBJECT-TYPE
    SYNTAX       Unsigned64
    MAX-ACCESS   read-only
    STATUS       current
    DESCRIPTION
        "Cisco Firepower adaptor:VnicStats:errorsRxDeltaMax
        managed object property"
    ::= { cfprApAdaptorVnicStatsEntry 27 }

cfprApAdaptorVnicStatsErrorsRxDeltaMin OBJECT-TYPE
    SYNTAX       Unsigned64
    MAX-ACCESS   read-only
    STATUS       current
    DESCRIPTION
        "Cisco Firepower adaptor:VnicStats:errorsRxDeltaMin
        managed object property"
    ::= { cfprApAdaptorVnicStatsEntry 28 }

cfprApAdaptorVnicStatsErrorsTx OBJECT-TYPE
    SYNTAX       Unsigned64
    MAX-ACCESS   read-only
    STATUS       current
    DESCRIPTION
        "Cisco Firepower adaptor:VnicStats:errorsTx managed
        object property"
    ::= { cfprApAdaptorVnicStatsEntry 29 }

cfprApAdaptorVnicStatsErrorsTxDelta OBJECT-TYPE
    SYNTAX       Counter64
    MAX-ACCESS   read-only
    STATUS       current
    DESCRIPTION
        "Cisco Firepower adaptor:VnicStats:errorsTxDelta
        managed object property"
    ::= { cfprApAdaptorVnicStatsEntry 30 }

cfprApAdaptorVnicStatsErrorsTxDeltaAvg OBJECT-TYPE
    SYNTAX       Unsigned64
    MAX-ACCESS   read-only
    STATUS       current
    DESCRIPTION
        "Cisco Firepower adaptor:VnicStats:errorsTxDeltaAvg
        managed object property"
    ::= { cfprApAdaptorVnicStatsEntry 31 }

cfprApAdaptorVnicStatsErrorsTxDeltaMax OBJECT-TYPE
    SYNTAX       Unsigned64
    MAX-ACCESS   read-only
    STATUS       current
    DESCRIPTION
        "Cisco Firepower adaptor:VnicStats:errorsTxDeltaMax
        managed object property"
    ::= { cfprApAdaptorVnicStatsEntry 32 }

cfprApAdaptorVnicStatsErrorsTxDeltaMin OBJECT-TYPE
    SYNTAX       Unsigned64
    MAX-ACCESS   read-only
    STATUS       current
    DESCRIPTION
        "Cisco Firepower adaptor:VnicStats:errorsTxDeltaMin
        managed object property"
    ::= { cfprApAdaptorVnicStatsEntry 33 }

cfprApAdaptorVnicStatsIntervals OBJECT-TYPE
    SYNTAX       Gauge32
    MAX-ACCESS   read-only
    STATUS       current
    DESCRIPTION
        "Cisco Firepower adaptor:VnicStats:intervals managed
        object property"
    ::= { cfprApAdaptorVnicStatsEntry 34 }

cfprApAdaptorVnicStatsPacketsRx OBJECT-TYPE
    SYNTAX       Unsigned64
    MAX-ACCESS   read-only
    STATUS       current
    DESCRIPTION
        "Cisco Firepower adaptor:VnicStats:packetsRx managed
        object property"
    ::= { cfprApAdaptorVnicStatsEntry 35 }

cfprApAdaptorVnicStatsPacketsRxDelta OBJECT-TYPE
    SYNTAX       Counter64
    MAX-ACCESS   read-only
    STATUS       current
    DESCRIPTION
        "Cisco Firepower adaptor:VnicStats:packetsRxDelta
        managed object property"
    ::= { cfprApAdaptorVnicStatsEntry 36 }

cfprApAdaptorVnicStatsPacketsRxDeltaAvg OBJECT-TYPE
    SYNTAX       Unsigned64
    MAX-ACCESS   read-only
    STATUS       current
    DESCRIPTION
        "Cisco Firepower adaptor:VnicStats:packetsRxDeltaAvg
        managed object property"
    ::= { cfprApAdaptorVnicStatsEntry 37 }

cfprApAdaptorVnicStatsPacketsRxDeltaMax OBJECT-TYPE
    SYNTAX       Unsigned64
    MAX-ACCESS   read-only
    STATUS       current
    DESCRIPTION
        "Cisco Firepower adaptor:VnicStats:packetsRxDeltaMax
        managed object property"
    ::= { cfprApAdaptorVnicStatsEntry 38 }

cfprApAdaptorVnicStatsPacketsRxDeltaMin OBJECT-TYPE
    SYNTAX       Unsigned64
    MAX-ACCESS   read-only
    STATUS       current
    DESCRIPTION
        "Cisco Firepower adaptor:VnicStats:packetsRxDeltaMin
        managed object property"
    ::= { cfprApAdaptorVnicStatsEntry 39 }

cfprApAdaptorVnicStatsPacketsTx OBJECT-TYPE
    SYNTAX       Unsigned64
    MAX-ACCESS   read-only
    STATUS       current
    DESCRIPTION
        "Cisco Firepower adaptor:VnicStats:packetsTx managed
        object property"
    ::= { cfprApAdaptorVnicStatsEntry 40 }

cfprApAdaptorVnicStatsPacketsTxDelta OBJECT-TYPE
    SYNTAX       Counter64
    MAX-ACCESS   read-only
    STATUS       current
    DESCRIPTION
        "Cisco Firepower adaptor:VnicStats:packetsTxDelta
        managed object property"
    ::= { cfprApAdaptorVnicStatsEntry 41 }

cfprApAdaptorVnicStatsPacketsTxDeltaAvg OBJECT-TYPE
    SYNTAX       Unsigned64
    MAX-ACCESS   read-only
    STATUS       current
    DESCRIPTION
        "Cisco Firepower adaptor:VnicStats:packetsTxDeltaAvg
        managed object property"
    ::= { cfprApAdaptorVnicStatsEntry 42 }

cfprApAdaptorVnicStatsPacketsTxDeltaMax OBJECT-TYPE
    SYNTAX       Unsigned64
    MAX-ACCESS   read-only
    STATUS       current
    DESCRIPTION
        "Cisco Firepower adaptor:VnicStats:packetsTxDeltaMax
        managed object property"
    ::= { cfprApAdaptorVnicStatsEntry 43 }

cfprApAdaptorVnicStatsPacketsTxDeltaMin OBJECT-TYPE
    SYNTAX       Unsigned64
    MAX-ACCESS   read-only
    STATUS       current
    DESCRIPTION
        "Cisco Firepower adaptor:VnicStats:packetsTxDeltaMin
        managed object property"
    ::= { cfprApAdaptorVnicStatsEntry 44 }

cfprApAdaptorVnicStatsSuspect OBJECT-TYPE
    SYNTAX       TruthValue
    MAX-ACCESS   read-only
    STATUS       current
    DESCRIPTION
        "Cisco Firepower adaptor:VnicStats:suspect managed
        object property"
    ::= { cfprApAdaptorVnicStatsEntry 45 }

cfprApAdaptorVnicStatsThresholded OBJECT-TYPE
    SYNTAX       CfprApAdaptorVnicStatsThresholded
    MAX-ACCESS   read-only
    STATUS       current
    DESCRIPTION
        "Cisco Firepower adaptor:VnicStats:thresholded
        managed object property"
    ::= { cfprApAdaptorVnicStatsEntry 46 }

cfprApAdaptorVnicStatsTimeCollected OBJECT-TYPE
    SYNTAX       DateAndTime
    MAX-ACCESS   read-only
    STATUS       current
    DESCRIPTION
        "Cisco Firepower adaptor:VnicStats:timeCollected
        managed object property"
    ::= { cfprApAdaptorVnicStatsEntry 47 }

cfprApAdaptorVnicStatsUpdate OBJECT-TYPE
    SYNTAX       Gauge32
    MAX-ACCESS   read-only
    STATUS       current
    DESCRIPTION
        "Cisco Firepower adaptor:VnicStats:update managed object property"
    ::= { cfprApAdaptorVnicStatsEntry 48 }

cfprApAdaptorVnicStatsHistTable OBJECT-TYPE
    SYNTAX           SEQUENCE OF CfprApAdaptorVnicStatsHistEntry
    MAX-ACCESS       not-accessible
    STATUS           current
    DESCRIPTION
        "Cisco Firepower adaptor:VnicStatsHist managed object table"
    ::= { cfprApAdaptorObjects 120 }

cfprApAdaptorVnicStatsHistEntry OBJECT-TYPE
    SYNTAX           CfprApAdaptorVnicStatsHistEntry
    MAX-ACCESS       not-accessible
    STATUS           current
    DESCRIPTION
        "Entry for the cfprApAdaptorVnicStatsHistTable table."
    INDEX { cfprApAdaptorVnicStatsHistInstanceId }
    ::= { cfprApAdaptorVnicStatsHistTable 1 }

CfprApAdaptorVnicStatsHistEntry ::= SEQUENCE {
    cfprApAdaptorVnicStatsHistInstanceId                             CfprApManagedObjectId,
    cfprApAdaptorVnicStatsHistDn                                     CfprApManagedObjectDn,
    cfprApAdaptorVnicStatsHistRn                                     SnmpAdminString,
    cfprApAdaptorVnicStatsHistBytesRx                                Unsigned64,
    cfprApAdaptorVnicStatsHistBytesRxDelta                           Unsigned64,
    cfprApAdaptorVnicStatsHistBytesRxDeltaAvg                        Unsigned64,
    cfprApAdaptorVnicStatsHistBytesRxDeltaMax                        Unsigned64,
    cfprApAdaptorVnicStatsHistBytesRxDeltaMin                        Unsigned64,
    cfprApAdaptorVnicStatsHistBytesTx                                Unsigned64,
    cfprApAdaptorVnicStatsHistBytesTxDelta                           Unsigned64,
    cfprApAdaptorVnicStatsHistBytesTxDeltaAvg                        Unsigned64,
    cfprApAdaptorVnicStatsHistBytesTxDeltaMax                        Unsigned64,
    cfprApAdaptorVnicStatsHistBytesTxDeltaMin                        Unsigned64,
    cfprApAdaptorVnicStatsHistDroppedRx                              Unsigned64,
    cfprApAdaptorVnicStatsHistDroppedRxDelta                         Unsigned64,
    cfprApAdaptorVnicStatsHistDroppedRxDeltaAvg                      Unsigned64,
    cfprApAdaptorVnicStatsHistDroppedRxDeltaMax                      Unsigned64,
    cfprApAdaptorVnicStatsHistDroppedRxDeltaMin                      Unsigned64,
    cfprApAdaptorVnicStatsHistDroppedTx                              Unsigned64,
    cfprApAdaptorVnicStatsHistDroppedTxDelta                         Unsigned64,
    cfprApAdaptorVnicStatsHistDroppedTxDeltaAvg                      Unsigned64,
    cfprApAdaptorVnicStatsHistDroppedTxDeltaMax                      Unsigned64,
    cfprApAdaptorVnicStatsHistDroppedTxDeltaMin                      Unsigned64,
    cfprApAdaptorVnicStatsHistErrorsRx                               Unsigned64,
    cfprApAdaptorVnicStatsHistErrorsRxDelta                          Unsigned64,
    cfprApAdaptorVnicStatsHistErrorsRxDeltaAvg                       Unsigned64,
    cfprApAdaptorVnicStatsHistErrorsRxDeltaMax                       Unsigned64,
    cfprApAdaptorVnicStatsHistErrorsRxDeltaMin                       Unsigned64,
    cfprApAdaptorVnicStatsHistErrorsTx                               Unsigned64,
    cfprApAdaptorVnicStatsHistErrorsTxDelta                          Unsigned64,
    cfprApAdaptorVnicStatsHistErrorsTxDeltaAvg                       Unsigned64,
    cfprApAdaptorVnicStatsHistErrorsTxDeltaMax                       Unsigned64,
    cfprApAdaptorVnicStatsHistErrorsTxDeltaMin                       Unsigned64,
    cfprApAdaptorVnicStatsHistId                                     Unsigned64,
    cfprApAdaptorVnicStatsHistMostRecent                             TruthValue,
    cfprApAdaptorVnicStatsHistPacketsRx                              Unsigned64,
    cfprApAdaptorVnicStatsHistPacketsRxDelta                         Unsigned64,
    cfprApAdaptorVnicStatsHistPacketsRxDeltaAvg                      Unsigned64,
    cfprApAdaptorVnicStatsHistPacketsRxDeltaMax                      Unsigned64,
    cfprApAdaptorVnicStatsHistPacketsRxDeltaMin                      Unsigned64,
    cfprApAdaptorVnicStatsHistPacketsTx                              Unsigned64,
    cfprApAdaptorVnicStatsHistPacketsTxDelta                         Unsigned64,
    cfprApAdaptorVnicStatsHistPacketsTxDeltaAvg                      Unsigned64,
    cfprApAdaptorVnicStatsHistPacketsTxDeltaMax                      Unsigned64,
    cfprApAdaptorVnicStatsHistPacketsTxDeltaMin                      Unsigned64,
    cfprApAdaptorVnicStatsHistSuspect                                TruthValue,
    cfprApAdaptorVnicStatsHistThresholded                            CfprApAdaptorVnicStatsHistThresholded,
    cfprApAdaptorVnicStatsHistTimeCollected                          DateAndTime
}

cfprApAdaptorVnicStatsHistInstanceId OBJECT-TYPE
    SYNTAX       CfprApManagedObjectId
    MAX-ACCESS   not-accessible
    STATUS       current
    DESCRIPTION
        "Instance identifier of the managed object."
    ::= { cfprApAdaptorVnicStatsHistEntry 1 }

cfprApAdaptorVnicStatsHistDn OBJECT-TYPE
    SYNTAX       CfprApManagedObjectDn
    MAX-ACCESS   read-only
    STATUS       current
    DESCRIPTION
        "Cisco Firepower adaptor:VnicStatsHist:dn managed object property"
    ::= { cfprApAdaptorVnicStatsHistEntry 2 }

cfprApAdaptorVnicStatsHistRn OBJECT-TYPE
    SYNTAX       SnmpAdminString
    MAX-ACCESS   read-only
    STATUS       current
    DESCRIPTION
        "Cisco Firepower adaptor:VnicStatsHist:rn managed object property"
    ::= { cfprApAdaptorVnicStatsHistEntry 3 }

cfprApAdaptorVnicStatsHistBytesRx OBJECT-TYPE
    SYNTAX       Unsigned64
    MAX-ACCESS   read-only
    STATUS       current
    DESCRIPTION
        "Cisco Firepower adaptor:VnicStatsHist:bytesRx
        managed object property"
    ::= { cfprApAdaptorVnicStatsHistEntry 4 }

cfprApAdaptorVnicStatsHistBytesRxDelta OBJECT-TYPE
    SYNTAX       Unsigned64
    MAX-ACCESS   read-only
    STATUS       current
    DESCRIPTION
        "Cisco Firepower adaptor:VnicStatsHist:bytesRxDelta
        managed object property"
    ::= { cfprApAdaptorVnicStatsHistEntry 5 }

cfprApAdaptorVnicStatsHistBytesRxDeltaAvg OBJECT-TYPE
    SYNTAX       Unsigned64
    MAX-ACCESS   read-only
    STATUS       current
    DESCRIPTION
        "Cisco Firepower adaptor:VnicStatsHist:bytesRxDeltaAvg
        managed object property"
    ::= { cfprApAdaptorVnicStatsHistEntry 6 }

cfprApAdaptorVnicStatsHistBytesRxDeltaMax OBJECT-TYPE
    SYNTAX       Unsigned64
    MAX-ACCESS   read-only
    STATUS       current
    DESCRIPTION
        "Cisco Firepower adaptor:VnicStatsHist:bytesRxDeltaMax
        managed object property"
    ::= { cfprApAdaptorVnicStatsHistEntry 7 }

cfprApAdaptorVnicStatsHistBytesRxDeltaMin OBJECT-TYPE
    SYNTAX       Unsigned64
    MAX-ACCESS   read-only
    STATUS       current
    DESCRIPTION
        "Cisco Firepower adaptor:VnicStatsHist:bytesRxDeltaMin
        managed object property"
    ::= { cfprApAdaptorVnicStatsHistEntry 8 }

cfprApAdaptorVnicStatsHistBytesTx OBJECT-TYPE
    SYNTAX       Unsigned64
    MAX-ACCESS   read-only
    STATUS       current
    DESCRIPTION
        "Cisco Firepower adaptor:VnicStatsHist:bytesTx
        managed object property"
    ::= { cfprApAdaptorVnicStatsHistEntry 9 }

cfprApAdaptorVnicStatsHistBytesTxDelta OBJECT-TYPE
    SYNTAX       Unsigned64
    MAX-ACCESS   read-only
    STATUS       current
    DESCRIPTION
        "Cisco Firepower adaptor:VnicStatsHist:bytesTxDelta
        managed object property"
    ::= { cfprApAdaptorVnicStatsHistEntry 10 }

cfprApAdaptorVnicStatsHistBytesTxDeltaAvg OBJECT-TYPE
    SYNTAX       Unsigned64
    MAX-ACCESS   read-only
    STATUS       current
    DESCRIPTION
        "Cisco Firepower adaptor:VnicStatsHist:bytesTxDeltaAvg
        managed object property"
    ::= { cfprApAdaptorVnicStatsHistEntry 11 }

cfprApAdaptorVnicStatsHistBytesTxDeltaMax OBJECT-TYPE
    SYNTAX       Unsigned64
    MAX-ACCESS   read-only
    STATUS       current
    DESCRIPTION
        "Cisco Firepower adaptor:VnicStatsHist:bytesTxDeltaMax
        managed object property"
    ::= { cfprApAdaptorVnicStatsHistEntry 12 }

cfprApAdaptorVnicStatsHistBytesTxDeltaMin OBJECT-TYPE
    SYNTAX       Unsigned64
    MAX-ACCESS   read-only
    STATUS       current
    DESCRIPTION
        "Cisco Firepower adaptor:VnicStatsHist:bytesTxDeltaMin
        managed object property"
    ::= { cfprApAdaptorVnicStatsHistEntry 13 }

cfprApAdaptorVnicStatsHistDroppedRx OBJECT-TYPE
    SYNTAX       Unsigned64
    MAX-ACCESS   read-only
    STATUS       current
    DESCRIPTION
        "Cisco Firepower adaptor:VnicStatsHist:droppedRx
        managed object property"
    ::= { cfprApAdaptorVnicStatsHistEntry 14 }

cfprApAdaptorVnicStatsHistDroppedRxDelta OBJECT-TYPE
    SYNTAX       Unsigned64
    MAX-ACCESS   read-only
    STATUS       current
    DESCRIPTION
        "Cisco Firepower adaptor:VnicStatsHist:droppedRxDelta
        managed object property"
    ::= { cfprApAdaptorVnicStatsHistEntry 15 }

cfprApAdaptorVnicStatsHistDroppedRxDeltaAvg OBJECT-TYPE
    SYNTAX       Unsigned64
    MAX-ACCESS   read-only
    STATUS       current
    DESCRIPTION
        "Cisco Firepower adaptor:VnicStatsHist:droppedRxDeltaAvg
        managed object property"
    ::= { cfprApAdaptorVnicStatsHistEntry 16 }

cfprApAdaptorVnicStatsHistDroppedRxDeltaMax OBJECT-TYPE
    SYNTAX       Unsigned64
    MAX-ACCESS   read-only
    STATUS       current
    DESCRIPTION
        "Cisco Firepower adaptor:VnicStatsHist:droppedRxDeltaMax
        managed object property"
    ::= { cfprApAdaptorVnicStatsHistEntry 17 }

cfprApAdaptorVnicStatsHistDroppedRxDeltaMin OBJECT-TYPE
    SYNTAX       Unsigned64
    MAX-ACCESS   read-only
    STATUS       current
    DESCRIPTION
        "Cisco Firepower adaptor:VnicStatsHist:droppedRxDeltaMin
        managed object property"
    ::= { cfprApAdaptorVnicStatsHistEntry 18 }

cfprApAdaptorVnicStatsHistDroppedTx OBJECT-TYPE
    SYNTAX       Unsigned64
    MAX-ACCESS   read-only
    STATUS       current
    DESCRIPTION
        "Cisco Firepower adaptor:VnicStatsHist:droppedTx
        managed object property"
    ::= { cfprApAdaptorVnicStatsHistEntry 19 }

cfprApAdaptorVnicStatsHistDroppedTxDelta OBJECT-TYPE
    SYNTAX       Unsigned64
    MAX-ACCESS   read-only
    STATUS       current
    DESCRIPTION
        "Cisco Firepower adaptor:VnicStatsHist:droppedTxDelta
        managed object property"
    ::= { cfprApAdaptorVnicStatsHistEntry 20 }

cfprApAdaptorVnicStatsHistDroppedTxDeltaAvg OBJECT-TYPE
    SYNTAX       Unsigned64
    MAX-ACCESS   read-only
    STATUS       current
    DESCRIPTION
        "Cisco Firepower adaptor:VnicStatsHist:droppedTxDeltaAvg
        managed object property"
    ::= { cfprApAdaptorVnicStatsHistEntry 21 }

cfprApAdaptorVnicStatsHistDroppedTxDeltaMax OBJECT-TYPE
    SYNTAX       Unsigned64
    MAX-ACCESS   read-only
    STATUS       current
    DESCRIPTION
        "Cisco Firepower adaptor:VnicStatsHist:droppedTxDeltaMax
        managed object property"
    ::= { cfprApAdaptorVnicStatsHistEntry 22 }

cfprApAdaptorVnicStatsHistDroppedTxDeltaMin OBJECT-TYPE
    SYNTAX       Unsigned64
    MAX-ACCESS   read-only
    STATUS       current
    DESCRIPTION
        "Cisco Firepower adaptor:VnicStatsHist:droppedTxDeltaMin
        managed object property"
    ::= { cfprApAdaptorVnicStatsHistEntry 23 }

cfprApAdaptorVnicStatsHistErrorsRx OBJECT-TYPE
    SYNTAX       Unsigned64
    MAX-ACCESS   read-only
    STATUS       current
    DESCRIPTION
        "Cisco Firepower adaptor:VnicStatsHist:errorsRx
        managed object property"
    ::= { cfprApAdaptorVnicStatsHistEntry 24 }

cfprApAdaptorVnicStatsHistErrorsRxDelta OBJECT-TYPE
    SYNTAX       Unsigned64
    MAX-ACCESS   read-only
    STATUS       current
    DESCRIPTION
        "Cisco Firepower adaptor:VnicStatsHist:errorsRxDelta
        managed object property"
    ::= { cfprApAdaptorVnicStatsHistEntry 25 }

cfprApAdaptorVnicStatsHistErrorsRxDeltaAvg OBJECT-TYPE
    SYNTAX       Unsigned64
    MAX-ACCESS   read-only
    STATUS       current
    DESCRIPTION
        "Cisco Firepower adaptor:VnicStatsHist:errorsRxDeltaAvg
        managed object property"
    ::= { cfprApAdaptorVnicStatsHistEntry 26 }

cfprApAdaptorVnicStatsHistErrorsRxDeltaMax OBJECT-TYPE
    SYNTAX       Unsigned64
    MAX-ACCESS   read-only
    STATUS       current
    DESCRIPTION
        "Cisco Firepower adaptor:VnicStatsHist:errorsRxDeltaMax
        managed object property"
    ::= { cfprApAdaptorVnicStatsHistEntry 27 }

cfprApAdaptorVnicStatsHistErrorsRxDeltaMin OBJECT-TYPE
    SYNTAX       Unsigned64
    MAX-ACCESS   read-only
    STATUS       current
    DESCRIPTION
        "Cisco Firepower adaptor:VnicStatsHist:errorsRxDeltaMin
        managed object property"
    ::= { cfprApAdaptorVnicStatsHistEntry 28 }

cfprApAdaptorVnicStatsHistErrorsTx OBJECT-TYPE
    SYNTAX       Unsigned64
    MAX-ACCESS   read-only
    STATUS       current
    DESCRIPTION
        "Cisco Firepower adaptor:VnicStatsHist:errorsTx
        managed object property"
    ::= { cfprApAdaptorVnicStatsHistEntry 29 }

cfprApAdaptorVnicStatsHistErrorsTxDelta OBJECT-TYPE
    SYNTAX       Unsigned64
    MAX-ACCESS   read-only
    STATUS       current
    DESCRIPTION
        "Cisco Firepower adaptor:VnicStatsHist:errorsTxDelta
        managed object property"
    ::= { cfprApAdaptorVnicStatsHistEntry 30 }

cfprApAdaptorVnicStatsHistErrorsTxDeltaAvg OBJECT-TYPE
    SYNTAX       Unsigned64
    MAX-ACCESS   read-only
    STATUS       current
    DESCRIPTION
        "Cisco Firepower adaptor:VnicStatsHist:errorsTxDeltaAvg
        managed object property"
    ::= { cfprApAdaptorVnicStatsHistEntry 31 }

cfprApAdaptorVnicStatsHistErrorsTxDeltaMax OBJECT-TYPE
    SYNTAX       Unsigned64
    MAX-ACCESS   read-only
    STATUS       current
    DESCRIPTION
        "Cisco Firepower adaptor:VnicStatsHist:errorsTxDeltaMax
        managed object property"
    ::= { cfprApAdaptorVnicStatsHistEntry 32 }

cfprApAdaptorVnicStatsHistErrorsTxDeltaMin OBJECT-TYPE
    SYNTAX       Unsigned64
    MAX-ACCESS   read-only
    STATUS       current
    DESCRIPTION
        "Cisco Firepower adaptor:VnicStatsHist:errorsTxDeltaMin
        managed object property"
    ::= { cfprApAdaptorVnicStatsHistEntry 33 }

cfprApAdaptorVnicStatsHistId OBJECT-TYPE
    SYNTAX       Unsigned64
    MAX-ACCESS   read-only
    STATUS       current
    DESCRIPTION
        "Cisco Firepower adaptor:VnicStatsHist:id managed object property"
    ::= { cfprApAdaptorVnicStatsHistEntry 34 }

cfprApAdaptorVnicStatsHistMostRecent OBJECT-TYPE
    SYNTAX       TruthValue
    MAX-ACCESS   read-only
    STATUS       current
    DESCRIPTION
        "Cisco Firepower adaptor:VnicStatsHist:mostRecent
        managed object property"
    ::= { cfprApAdaptorVnicStatsHistEntry 35 }

cfprApAdaptorVnicStatsHistPacketsRx OBJECT-TYPE
    SYNTAX       Unsigned64
    MAX-ACCESS   read-only
    STATUS       current
    DESCRIPTION
        "Cisco Firepower adaptor:VnicStatsHist:packetsRx
        managed object property"
    ::= { cfprApAdaptorVnicStatsHistEntry 36 }

cfprApAdaptorVnicStatsHistPacketsRxDelta OBJECT-TYPE
    SYNTAX       Unsigned64
    MAX-ACCESS   read-only
    STATUS       current
    DESCRIPTION
        "Cisco Firepower adaptor:VnicStatsHist:packetsRxDelta
        managed object property"
    ::= { cfprApAdaptorVnicStatsHistEntry 37 }

cfprApAdaptorVnicStatsHistPacketsRxDeltaAvg OBJECT-TYPE
    SYNTAX       Unsigned64
    MAX-ACCESS   read-only
    STATUS       current
    DESCRIPTION
        "Cisco Firepower adaptor:VnicStatsHist:packetsRxDeltaAvg
        managed object property"
    ::= { cfprApAdaptorVnicStatsHistEntry 38 }

cfprApAdaptorVnicStatsHistPacketsRxDeltaMax OBJECT-TYPE
    SYNTAX       Unsigned64
    MAX-ACCESS   read-only
    STATUS       current
    DESCRIPTION
        "Cisco Firepower adaptor:VnicStatsHist:packetsRxDeltaMax
        managed object property"
    ::= { cfprApAdaptorVnicStatsHistEntry 39 }

cfprApAdaptorVnicStatsHistPacketsRxDeltaMin OBJECT-TYPE
    SYNTAX       Unsigned64
    MAX-ACCESS   read-only
    STATUS       current
    DESCRIPTION
        "Cisco Firepower adaptor:VnicStatsHist:packetsRxDeltaMin
        managed object property"
    ::= { cfprApAdaptorVnicStatsHistEntry 40 }

cfprApAdaptorVnicStatsHistPacketsTx OBJECT-TYPE
    SYNTAX       Unsigned64
    MAX-ACCESS   read-only
    STATUS       current
    DESCRIPTION
        "Cisco Firepower adaptor:VnicStatsHist:packetsTx
        managed object property"
    ::= { cfprApAdaptorVnicStatsHistEntry 41 }

cfprApAdaptorVnicStatsHistPacketsTxDelta OBJECT-TYPE
    SYNTAX       Unsigned64
    MAX-ACCESS   read-only
    STATUS       current
    DESCRIPTION
        "Cisco Firepower adaptor:VnicStatsHist:packetsTxDelta
        managed object property"
    ::= { cfprApAdaptorVnicStatsHistEntry 42 }

cfprApAdaptorVnicStatsHistPacketsTxDeltaAvg OBJECT-TYPE
    SYNTAX       Unsigned64
    MAX-ACCESS   read-only
    STATUS       current
    DESCRIPTION
        "Cisco Firepower adaptor:VnicStatsHist:packetsTxDeltaAvg
        managed object property"
    ::= { cfprApAdaptorVnicStatsHistEntry 43 }

cfprApAdaptorVnicStatsHistPacketsTxDeltaMax OBJECT-TYPE
    SYNTAX       Unsigned64
    MAX-ACCESS   read-only
    STATUS       current
    DESCRIPTION
        "Cisco Firepower adaptor:VnicStatsHist:packetsTxDeltaMax
        managed object property"
    ::= { cfprApAdaptorVnicStatsHistEntry 44 }

cfprApAdaptorVnicStatsHistPacketsTxDeltaMin OBJECT-TYPE
    SYNTAX       Unsigned64
    MAX-ACCESS   read-only
    STATUS       current
    DESCRIPTION
        "Cisco Firepower adaptor:VnicStatsHist:packetsTxDeltaMin
        managed object property"
    ::= { cfprApAdaptorVnicStatsHistEntry 45 }

cfprApAdaptorVnicStatsHistSuspect OBJECT-TYPE
    SYNTAX       TruthValue
    MAX-ACCESS   read-only
    STATUS       current
    DESCRIPTION
        "Cisco Firepower adaptor:VnicStatsHist:suspect
        managed object property"
    ::= { cfprApAdaptorVnicStatsHistEntry 46 }

cfprApAdaptorVnicStatsHistThresholded OBJECT-TYPE
    SYNTAX       CfprApAdaptorVnicStatsHistThresholded
    MAX-ACCESS   read-only
    STATUS       current
    DESCRIPTION
        "Cisco Firepower adaptor:VnicStatsHist:thresholded
        managed object property"
    ::= { cfprApAdaptorVnicStatsHistEntry 47 }

cfprApAdaptorVnicStatsHistTimeCollected OBJECT-TYPE
    SYNTAX       DateAndTime
    MAX-ACCESS   read-only
    STATUS       current
    DESCRIPTION
        "Cisco Firepower adaptor:VnicStatsHist:timeCollected
        managed object property"
    ::= { cfprApAdaptorVnicStatsHistEntry 48 }

cfprApAdaptorVsanTable OBJECT-TYPE
    SYNTAX           SEQUENCE OF CfprApAdaptorVsanEntry
    MAX-ACCESS       not-accessible
    STATUS           current
    DESCRIPTION
        "Cisco Firepower adaptor:Vsan managed object table"
    ::= { cfprApAdaptorObjects 121 }

cfprApAdaptorVsanEntry OBJECT-TYPE
    SYNTAX           CfprApAdaptorVsanEntry
    MAX-ACCESS       not-accessible
    STATUS           current
    DESCRIPTION
        "Entry for the cfprApAdaptorVsanTable table."
    INDEX { cfprApAdaptorVsanInstanceId }
    ::= { cfprApAdaptorVsanTable 1 }

CfprApAdaptorVsanEntry ::= SEQUENCE {
    cfprApAdaptorVsanInstanceId                                      CfprApManagedObjectId,
    cfprApAdaptorVsanDn                                              CfprApManagedObjectDn,
    cfprApAdaptorVsanRn                                              SnmpAdminString,
    cfprApAdaptorVsanEpDn                                            SnmpAdminString,
    cfprApAdaptorVsanFcoeVlan                                        Gauge32,
    cfprApAdaptorVsanId                                              Gauge32,
    cfprApAdaptorVsanIfRole                                          CfprApFabricVnetEpIfRole,
    cfprApAdaptorVsanIfType                                          CfprApNetworkVnetEpIfType,
    cfprApAdaptorVsanLc                                              CfprApFsmLifecycle,
    cfprApAdaptorVsanLocale                                          CfprApFabricVnetEpLocale,
    cfprApAdaptorVsanName                                            SnmpAdminString,
    cfprApAdaptorVsanOperState                                       CfprApFabricVsanOperState,
    cfprApAdaptorVsanPeerDn                                          SnmpAdminString,
    cfprApAdaptorVsanPolicyOwner                                     CfprApFabricVnetEpPolicyOwner,
    cfprApAdaptorVsanSwitchId                                        CfprApNetworkSwitchId,
    cfprApAdaptorVsanTransport                                       CfprApFabricAVsanTransport,
    cfprApAdaptorVsanType                                            CfprApFabricAVsanType,
    cfprApAdaptorVsanZoningState                                     CfprApFabricZoningState
}

cfprApAdaptorVsanInstanceId OBJECT-TYPE
    SYNTAX       CfprApManagedObjectId
    MAX-ACCESS   not-accessible
    STATUS       current
    DESCRIPTION
        "Instance identifier of the managed object."
    ::= { cfprApAdaptorVsanEntry 1 }

cfprApAdaptorVsanDn OBJECT-TYPE
    SYNTAX       CfprApManagedObjectDn
    MAX-ACCESS   read-only
    STATUS       current
    DESCRIPTION
        "Cisco Firepower adaptor:Vsan:dn managed object property"
    ::= { cfprApAdaptorVsanEntry 2 }

cfprApAdaptorVsanRn OBJECT-TYPE
    SYNTAX       SnmpAdminString
    MAX-ACCESS   read-only
    STATUS       current
    DESCRIPTION
        "Cisco Firepower adaptor:Vsan:rn managed object property"
    ::= { cfprApAdaptorVsanEntry 3 }

cfprApAdaptorVsanEpDn OBJECT-TYPE
    SYNTAX       SnmpAdminString
    MAX-ACCESS   read-only
    STATUS       current
    DESCRIPTION
        "Cisco Firepower adaptor:Vsan:epDn managed object property"
    ::= { cfprApAdaptorVsanEntry 4 }

cfprApAdaptorVsanFcoeVlan OBJECT-TYPE
    SYNTAX       Gauge32
    MAX-ACCESS   read-only
    STATUS       current
    DESCRIPTION
        "Cisco Firepower adaptor:Vsan:fcoeVlan managed object property"
    ::= { cfprApAdaptorVsanEntry 5 }

cfprApAdaptorVsanId OBJECT-TYPE
    SYNTAX       Gauge32
    MAX-ACCESS   read-only
    STATUS       current
    DESCRIPTION
        "Cisco Firepower adaptor:Vsan:id managed object property"
    ::= { cfprApAdaptorVsanEntry 6 }

cfprApAdaptorVsanIfRole OBJECT-TYPE
    SYNTAX       CfprApFabricVnetEpIfRole
    MAX-ACCESS   read-only
    STATUS       current
    DESCRIPTION
        "Cisco Firepower adaptor:Vsan:ifRole managed object property"
    ::= { cfprApAdaptorVsanEntry 7 }

cfprApAdaptorVsanIfType OBJECT-TYPE
    SYNTAX       CfprApNetworkVnetEpIfType
    MAX-ACCESS   read-only
    STATUS       current
    DESCRIPTION
        "Cisco Firepower adaptor:Vsan:ifType managed object property"
    ::= { cfprApAdaptorVsanEntry 8 }

cfprApAdaptorVsanLc OBJECT-TYPE
    SYNTAX       CfprApFsmLifecycle
    MAX-ACCESS   read-only
    STATUS       current
    DESCRIPTION
        "Cisco Firepower adaptor:Vsan:lc managed object property"
    ::= { cfprApAdaptorVsanEntry 9 }

cfprApAdaptorVsanLocale OBJECT-TYPE
    SYNTAX       CfprApFabricVnetEpLocale
    MAX-ACCESS   read-only
    STATUS       current
    DESCRIPTION
        "Cisco Firepower adaptor:Vsan:locale managed object property"
    ::= { cfprApAdaptorVsanEntry 10 }

cfprApAdaptorVsanName OBJECT-TYPE
    SYNTAX       SnmpAdminString
    MAX-ACCESS   read-only
    STATUS       current
    DESCRIPTION
        "Cisco Firepower adaptor:Vsan:name managed object property"
    ::= { cfprApAdaptorVsanEntry 11 }

cfprApAdaptorVsanOperState OBJECT-TYPE
    SYNTAX       CfprApFabricVsanOperState
    MAX-ACCESS   read-only
    STATUS       current
    DESCRIPTION
        "Cisco Firepower adaptor:Vsan:operState managed object property"
    ::= { cfprApAdaptorVsanEntry 12 }

cfprApAdaptorVsanPeerDn OBJECT-TYPE
    SYNTAX       SnmpAdminString
    MAX-ACCESS   read-only
    STATUS       current
    DESCRIPTION
        "Cisco Firepower adaptor:Vsan:peerDn managed object property"
    ::= { cfprApAdaptorVsanEntry 13 }

cfprApAdaptorVsanPolicyOwner OBJECT-TYPE
    SYNTAX       CfprApFabricVnetEpPolicyOwner
    MAX-ACCESS   read-only
    STATUS       current
    DESCRIPTION
        "Cisco Firepower adaptor:Vsan:policyOwner managed object property"
    ::= { cfprApAdaptorVsanEntry 14 }

cfprApAdaptorVsanSwitchId OBJECT-TYPE
    SYNTAX       CfprApNetworkSwitchId
    MAX-ACCESS   read-only
    STATUS       current
    DESCRIPTION
        "Cisco Firepower adaptor:Vsan:switchId managed object property"
    ::= { cfprApAdaptorVsanEntry 15 }

cfprApAdaptorVsanTransport OBJECT-TYPE
    SYNTAX       CfprApFabricAVsanTransport
    MAX-ACCESS   read-only
    STATUS       current
    DESCRIPTION
        "Cisco Firepower adaptor:Vsan:transport managed object property"
    ::= { cfprApAdaptorVsanEntry 16 }

cfprApAdaptorVsanType OBJECT-TYPE
    SYNTAX       CfprApFabricAVsanType
    MAX-ACCESS   read-only
    STATUS       current
    DESCRIPTION
        "Cisco Firepower adaptor:Vsan:type managed object property"
    ::= { cfprApAdaptorVsanEntry 17 }

cfprApAdaptorVsanZoningState OBJECT-TYPE
    SYNTAX       CfprApFabricZoningState
    MAX-ACCESS   read-only
    STATUS       current
    DESCRIPTION
        "Cisco Firepower adaptor:Vsan:zoningState managed object property"
    ::= { cfprApAdaptorVsanEntry 18 }

END
