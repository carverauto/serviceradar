-- *********************************************************************
-- CISCO-FIREPOWER-TRIG-MIB.my
-- 
-- MIB representation of the Cisco Firepower
-- TRIG management information model package
-- 
-- Created May 2024 by Charles Bullis
-- 
-- Copyright (c) 2005-2024 Cisco Systems, Inc. All rights reserved.
-- 
-- *********************************************************************

CISCO-FIREPOWER-TRIG-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB
    CfprPolicyPolicyOwner,
    CfprTrigAdminState,
    CfprTrigDay,
    CfprTrigOperState,
    CfprTrigTokenOperState,
    CfprTrigTrigOperState,
    CfprTrigTriggeredState
        FROM CISCO-FIREPOWER-TC-MIB;

cfprTrigObjects MODULE-IDENTITY
    LAST-UPDATED    "202405160000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        TRIG management information model package"
    ::= { ciscoFirepowerMIBObjects 79 }

cfprTrigAbsWindowTable OBJECT-TYPE
    SYNTAX           SEQUENCE OF CfprTrigAbsWindowEntry
    MAX-ACCESS       not-accessible
    STATUS           current
    DESCRIPTION
        "Cisco Firepower trig:AbsWindow managed object table"
    ::= { cfprTrigObjects 1 }

cfprTrigAbsWindowEntry OBJECT-TYPE
    SYNTAX           CfprTrigAbsWindowEntry
    MAX-ACCESS       not-accessible
    STATUS           current
    DESCRIPTION
        "Entry for the cfprTrigAbsWindowTable table."
    INDEX { cfprTrigAbsWindowInstanceId }
    ::= { cfprTrigAbsWindowTable 1 }

CfprTrigAbsWindowEntry ::= SEQUENCE {
    cfprTrigAbsWindowInstanceId                                      CfprManagedObjectId,
    cfprTrigAbsWindowDn                                              CfprManagedObjectDn,
    cfprTrigAbsWindowRn                                              SnmpAdminString,
    cfprTrigAbsWindowConcurCap                                       Gauge32,
    cfprTrigAbsWindowDate                                            DateAndTime,
    cfprTrigAbsWindowJobCount                                        Gauge32,
    cfprTrigAbsWindowName                                            SnmpAdminString,
    cfprTrigAbsWindowProcBreak                                       SnmpAdminString,
    cfprTrigAbsWindowProcCap                                         Gauge32,
    cfprTrigAbsWindowTimeCap                                         SnmpAdminString,
    cfprTrigAbsWindowStart                                           TruthValue
}

cfprTrigAbsWindowInstanceId OBJECT-TYPE
    SYNTAX       CfprManagedObjectId
    MAX-ACCESS   not-accessible
    STATUS       current
    DESCRIPTION
        "Instance identifier of the managed object."
    ::= { cfprTrigAbsWindowEntry 1 }

cfprTrigAbsWindowDn OBJECT-TYPE
    SYNTAX       CfprManagedObjectDn
    MAX-ACCESS   read-only
    STATUS       current
    DESCRIPTION
        "Cisco Firepower trig:AbsWindow:dn managed object property"
    ::= { cfprTrigAbsWindowEntry 2 }

cfprTrigAbsWindowRn OBJECT-TYPE
    SYNTAX       SnmpAdminString
    MAX-ACCESS   read-only
    STATUS       current
    DESCRIPTION
        "Cisco Firepower trig:AbsWindow:rn managed object property"
    ::= { cfprTrigAbsWindowEntry 3 }

cfprTrigAbsWindowConcurCap OBJECT-TYPE
    SYNTAX       Gauge32
    MAX-ACCESS   read-only
    STATUS       current
    DESCRIPTION
        "Cisco Firepower trig:AbsWindow:concurCap managed object property"
    ::= { cfprTrigAbsWindowEntry 4 }

cfprTrigAbsWindowDate OBJECT-TYPE
    SYNTAX       DateAndTime
    MAX-ACCESS   read-only
    STATUS       current
    DESCRIPTION
        "Cisco Firepower trig:AbsWindow:date managed object property"
    ::= { cfprTrigAbsWindowEntry 5 }

cfprTrigAbsWindowJobCount OBJECT-TYPE
    SYNTAX       Gauge32
    MAX-ACCESS   read-only
    STATUS       current
    DESCRIPTION
        "Cisco Firepower trig:AbsWindow:jobCount managed object property"
    ::= { cfprTrigAbsWindowEntry 6 }

cfprTrigAbsWindowName OBJECT-TYPE
    SYNTAX       SnmpAdminString
    MAX-ACCESS   read-only
    STATUS       current
    DESCRIPTION
        "Cisco Firepower trig:AbsWindow:name managed object property"
    ::= { cfprTrigAbsWindowEntry 7 }

cfprTrigAbsWindowProcBreak OBJECT-TYPE
    SYNTAX       SnmpAdminString
    MAX-ACCESS   read-only
    STATUS       current
    DESCRIPTION
        "Cisco Firepower trig:AbsWindow:procBreak managed object property"
    ::= { cfprTrigAbsWindowEntry 8 }

cfprTrigAbsWindowProcCap OBJECT-TYPE
    SYNTAX       Gauge32
    MAX-ACCESS   read-only
    STATUS       current
    DESCRIPTION
        "Cisco Firepower trig:AbsWindow:procCap managed object property"
    ::= { cfprTrigAbsWindowEntry 9 }

cfprTrigAbsWindowTimeCap OBJECT-TYPE
    SYNTAX       SnmpAdminString
    MAX-ACCESS   read-only
    STATUS       current
    DESCRIPTION
        "Cisco Firepower trig:AbsWindow:timeCap managed object property"
    ::= { cfprTrigAbsWindowEntry 10 }

cfprTrigAbsWindowStart OBJECT-TYPE
    SYNTAX       TruthValue
    MAX-ACCESS   read-only
    STATUS       current
    DESCRIPTION
        "Cisco Firepower trig:AbsWindow:start managed object property"
    ::= { cfprTrigAbsWindowEntry 11 }

cfprTrigClientTokenTable OBJECT-TYPE
    SYNTAX           SEQUENCE OF CfprTrigClientTokenEntry
    MAX-ACCESS       not-accessible
    STATUS           current
    DESCRIPTION
        "Cisco Firepower trig:ClientToken managed object table"
    ::= { cfprTrigObjects 2 }

cfprTrigClientTokenEntry OBJECT-TYPE
    SYNTAX           CfprTrigClientTokenEntry
    MAX-ACCESS       not-accessible
    STATUS           current
    DESCRIPTION
        "Entry for the cfprTrigClientTokenTable table."
    INDEX { cfprTrigClientTokenInstanceId }
    ::= { cfprTrigClientTokenTable 1 }

CfprTrigClientTokenEntry ::= SEQUENCE {
    cfprTrigClientTokenInstanceId                                    CfprManagedObjectId,
    cfprTrigClientTokenDn                                            CfprManagedObjectDn,
    cfprTrigClientTokenRn                                            SnmpAdminString,
    cfprTrigClientTokenActivityTs                                    DateAndTime,
    cfprTrigClientTokenId                                            Unsigned64,
    cfprTrigClientTokenOperState                                     CfprTrigTokenOperState
}

cfprTrigClientTokenInstanceId OBJECT-TYPE
    SYNTAX       CfprManagedObjectId
    MAX-ACCESS   not-accessible
    STATUS       current
    DESCRIPTION
        "Instance identifier of the managed object."
    ::= { cfprTrigClientTokenEntry 1 }

cfprTrigClientTokenDn OBJECT-TYPE
    SYNTAX       CfprManagedObjectDn
    MAX-ACCESS   read-only
    STATUS       current
    DESCRIPTION
        "Cisco Firepower trig:ClientToken:dn managed object property"
    ::= { cfprTrigClientTokenEntry 2 }

cfprTrigClientTokenRn OBJECT-TYPE
    SYNTAX       SnmpAdminString
    MAX-ACCESS   read-only
    STATUS       current
    DESCRIPTION
        "Cisco Firepower trig:ClientToken:rn managed object property"
    ::= { cfprTrigClientTokenEntry 3 }

cfprTrigClientTokenActivityTs OBJECT-TYPE
    SYNTAX       DateAndTime
    MAX-ACCESS   read-only
    STATUS       current
    DESCRIPTION
        "Cisco Firepower trig:ClientToken:activityTs managed
        object property"
    ::= { cfprTrigClientTokenEntry 4 }

cfprTrigClientTokenId OBJECT-TYPE
    SYNTAX       Unsigned64
    MAX-ACCESS   read-only
    STATUS       current
    DESCRIPTION
        "Cisco Firepower trig:ClientToken:id managed object property"
    ::= { cfprTrigClientTokenEntry 5 }

cfprTrigClientTokenOperState OBJECT-TYPE
    SYNTAX       CfprTrigTokenOperState
    MAX-ACCESS   read-only
    STATUS       current
    DESCRIPTION
        "Cisco Firepower trig:ClientToken:operState managed
        object property"
    ::= { cfprTrigClientTokenEntry 6 }

cfprTrigLocalAbsWindowTable OBJECT-TYPE
    SYNTAX           SEQUENCE OF CfprTrigLocalAbsWindowEntry
    MAX-ACCESS       not-accessible
    STATUS           current
    DESCRIPTION
        "Cisco Firepower trig:LocalAbsWindow managed object table"
    ::= { cfprTrigObjects 3 }

cfprTrigLocalAbsWindowEntry OBJECT-TYPE
    SYNTAX           CfprTrigLocalAbsWindowEntry
    MAX-ACCESS       not-accessible
    STATUS           current
    DESCRIPTION
        "Entry for the cfprTrigLocalAbsWindowTable table."
    INDEX { cfprTrigLocalAbsWindowInstanceId }
    ::= { cfprTrigLocalAbsWindowTable 1 }

CfprTrigLocalAbsWindowEntry ::= SEQUENCE {
    cfprTrigLocalAbsWindowInstanceId                                 CfprManagedObjectId,
    cfprTrigLocalAbsWindowDn                                         CfprManagedObjectDn,
    cfprTrigLocalAbsWindowRn                                         SnmpAdminString,
    cfprTrigLocalAbsWindowConcurCap                                  Gauge32,
    cfprTrigLocalAbsWindowDate                                       DateAndTime,
    cfprTrigLocalAbsWindowJobCount                                   Gauge32,
    cfprTrigLocalAbsWindowName                                       SnmpAdminString,
    cfprTrigLocalAbsWindowProcBreak                                  SnmpAdminString,
    cfprTrigLocalAbsWindowProcCap                                    Gauge32,
    cfprTrigLocalAbsWindowTimeCap                                    SnmpAdminString,
    cfprTrigLocalAbsWindowStart                                      TruthValue
}

cfprTrigLocalAbsWindowInstanceId OBJECT-TYPE
    SYNTAX       CfprManagedObjectId
    MAX-ACCESS   not-accessible
    STATUS       current
    DESCRIPTION
        "Instance identifier of the managed object."
    ::= { cfprTrigLocalAbsWindowEntry 1 }

cfprTrigLocalAbsWindowDn OBJECT-TYPE
    SYNTAX       CfprManagedObjectDn
    MAX-ACCESS   read-only
    STATUS       current
    DESCRIPTION
        "Cisco Firepower trig:LocalAbsWindow:dn managed object property"
    ::= { cfprTrigLocalAbsWindowEntry 2 }

cfprTrigLocalAbsWindowRn OBJECT-TYPE
    SYNTAX       SnmpAdminString
    MAX-ACCESS   read-only
    STATUS       current
    DESCRIPTION
        "Cisco Firepower trig:LocalAbsWindow:rn managed object property"
    ::= { cfprTrigLocalAbsWindowEntry 3 }

cfprTrigLocalAbsWindowConcurCap OBJECT-TYPE
    SYNTAX       Gauge32
    MAX-ACCESS   read-only
    STATUS       current
    DESCRIPTION
        "Cisco Firepower trig:LocalAbsWindow:concurCap
        managed object property"
    ::= { cfprTrigLocalAbsWindowEntry 4 }

cfprTrigLocalAbsWindowDate OBJECT-TYPE
    SYNTAX       DateAndTime
    MAX-ACCESS   read-only
    STATUS       current
    DESCRIPTION
        "Cisco Firepower trig:LocalAbsWindow:date managed object property"
    ::= { cfprTrigLocalAbsWindowEntry 5 }

cfprTrigLocalAbsWindowJobCount OBJECT-TYPE
    SYNTAX       Gauge32
    MAX-ACCESS   read-only
    STATUS       current
    DESCRIPTION
        "Cisco Firepower trig:LocalAbsWindow:jobCount managed
        object property"
    ::= { cfprTrigLocalAbsWindowEntry 6 }

cfprTrigLocalAbsWindowName OBJECT-TYPE
    SYNTAX       SnmpAdminString
    MAX-ACCESS   read-only
    STATUS       current
    DESCRIPTION
        "Cisco Firepower trig:LocalAbsWindow:name managed object property"
    ::= { cfprTrigLocalAbsWindowEntry 7 }

cfprTrigLocalAbsWindowProcBreak OBJECT-TYPE
    SYNTAX       SnmpAdminString
    MAX-ACCESS   read-only
    STATUS       current
    DESCRIPTION
        "Cisco Firepower trig:LocalAbsWindow:procBreak
        managed object property"
    ::= { cfprTrigLocalAbsWindowEntry 8 }

cfprTrigLocalAbsWindowProcCap OBJECT-TYPE
    SYNTAX       Gauge32
    MAX-ACCESS   read-only
    STATUS       current
    DESCRIPTION
        "Cisco Firepower trig:LocalAbsWindow:procCap managed
        object property"
    ::= { cfprTrigLocalAbsWindowEntry 9 }

cfprTrigLocalAbsWindowTimeCap OBJECT-TYPE
    SYNTAX       SnmpAdminString
    MAX-ACCESS   read-only
    STATUS       current
    DESCRIPTION
        "Cisco Firepower trig:LocalAbsWindow:timeCap managed
        object property"
    ::= { cfprTrigLocalAbsWindowEntry 10 }

cfprTrigLocalAbsWindowStart OBJECT-TYPE
    SYNTAX       TruthValue
    MAX-ACCESS   read-only
    STATUS       current
    DESCRIPTION
        "Cisco Firepower trig:LocalAbsWindow:start managed
        object property"
    ::= { cfprTrigLocalAbsWindowEntry 11 }

cfprTrigLocalSchedTable OBJECT-TYPE
    SYNTAX           SEQUENCE OF CfprTrigLocalSchedEntry
    MAX-ACCESS       not-accessible
    STATUS           current
    DESCRIPTION
        "Cisco Firepower trig:LocalSched managed object table"
    ::= { cfprTrigObjects 4 }

cfprTrigLocalSchedEntry OBJECT-TYPE
    SYNTAX           CfprTrigLocalSchedEntry
    MAX-ACCESS       not-accessible
    STATUS           current
    DESCRIPTION
        "Entry for the cfprTrigLocalSchedTable table."
    INDEX { cfprTrigLocalSchedInstanceId }
    ::= { cfprTrigLocalSchedTable 1 }

CfprTrigLocalSchedEntry ::= SEQUENCE {
    cfprTrigLocalSchedInstanceId                                     CfprManagedObjectId,
    cfprTrigLocalSchedDn                                             CfprManagedObjectDn,
    cfprTrigLocalSchedRn                                             SnmpAdminString,
    cfprTrigLocalSchedAdminState                                     CfprTrigAdminState,
    cfprTrigLocalSchedDescr                                          SnmpAdminString,
    cfprTrigLocalSchedFlgInitialActive                               TruthValue,
    cfprTrigLocalSchedIntId                                          SnmpAdminString,
    cfprTrigLocalSchedName                                           SnmpAdminString,
    cfprTrigLocalSchedOperState                                      CfprTrigOperState,
    cfprTrigLocalSchedPolicyLevel                                    Gauge32,
    cfprTrigLocalSchedPolicyOwner                                    CfprPolicyPolicyOwner
}

cfprTrigLocalSchedInstanceId OBJECT-TYPE
    SYNTAX       CfprManagedObjectId
    MAX-ACCESS   not-accessible
    STATUS       current
    DESCRIPTION
        "Instance identifier of the managed object."
    ::= { cfprTrigLocalSchedEntry 1 }

cfprTrigLocalSchedDn OBJECT-TYPE
    SYNTAX       CfprManagedObjectDn
    MAX-ACCESS   read-only
    STATUS       current
    DESCRIPTION
        "Cisco Firepower trig:LocalSched:dn managed object property"
    ::= { cfprTrigLocalSchedEntry 2 }

cfprTrigLocalSchedRn OBJECT-TYPE
    SYNTAX       SnmpAdminString
    MAX-ACCESS   read-only
    STATUS       current
    DESCRIPTION
        "Cisco Firepower trig:LocalSched:rn managed object property"
    ::= { cfprTrigLocalSchedEntry 3 }

cfprTrigLocalSchedAdminState OBJECT-TYPE
    SYNTAX       CfprTrigAdminState
    MAX-ACCESS   read-only
    STATUS       current
    DESCRIPTION
        "Cisco Firepower trig:LocalSched:adminState managed
        object property"
    ::= { cfprTrigLocalSchedEntry 4 }

cfprTrigLocalSchedDescr OBJECT-TYPE
    SYNTAX       SnmpAdminString
    MAX-ACCESS   read-only
    STATUS       current
    DESCRIPTION
        "Cisco Firepower trig:LocalSched:descr managed object property"
    ::= { cfprTrigLocalSchedEntry 5 }

cfprTrigLocalSchedFlgInitialActive OBJECT-TYPE
    SYNTAX       TruthValue
    MAX-ACCESS   read-only
    STATUS       current
    DESCRIPTION
        "Cisco Firepower trig:LocalSched:flgInitialActive
        managed object property"
    ::= { cfprTrigLocalSchedEntry 6 }

cfprTrigLocalSchedIntId OBJECT-TYPE
    SYNTAX       SnmpAdminString
    MAX-ACCESS   read-only
    STATUS       current
    DESCRIPTION
        "Cisco Firepower trig:LocalSched:intId managed object property"
    ::= { cfprTrigLocalSchedEntry 7 }

cfprTrigLocalSchedName OBJECT-TYPE
    SYNTAX       SnmpAdminString
    MAX-ACCESS   read-only
    STATUS       current
    DESCRIPTION
        "Cisco Firepower trig:LocalSched:name managed object property"
    ::= { cfprTrigLocalSchedEntry 8 }

cfprTrigLocalSchedOperState OBJECT-TYPE
    SYNTAX       CfprTrigOperState
    MAX-ACCESS   read-only
    STATUS       current
    DESCRIPTION
        "Cisco Firepower trig:LocalSched:operState managed
        object property"
    ::= { cfprTrigLocalSchedEntry 9 }

cfprTrigLocalSchedPolicyLevel OBJECT-TYPE
    SYNTAX       Gauge32
    MAX-ACCESS   read-only
    STATUS       current
    DESCRIPTION
        "Cisco Firepower trig:LocalSched:policyLevel managed
        object property"
    ::= { cfprTrigLocalSchedEntry 10 }

cfprTrigLocalSchedPolicyOwner OBJECT-TYPE
    SYNTAX       CfprPolicyPolicyOwner
    MAX-ACCESS   read-only
    STATUS       current
    DESCRIPTION
        "Cisco Firepower trig:LocalSched:policyOwner managed
        object property"
    ::= { cfprTrigLocalSchedEntry 11 }

cfprTrigMetaTable OBJECT-TYPE
    SYNTAX           SEQUENCE OF CfprTrigMetaEntry
    MAX-ACCESS       not-accessible
    STATUS           current
    DESCRIPTION
        "Cisco Firepower trig:Meta managed object table"
    ::= { cfprTrigObjects 5 }

cfprTrigMetaEntry OBJECT-TYPE
    SYNTAX           CfprTrigMetaEntry
    MAX-ACCESS       not-accessible
    STATUS           current
    DESCRIPTION
        "Entry for the cfprTrigMetaTable table."
    INDEX { cfprTrigMetaInstanceId }
    ::= { cfprTrigMetaTable 1 }

CfprTrigMetaEntry ::= SEQUENCE {
    cfprTrigMetaInstanceId                                           CfprManagedObjectId,
    cfprTrigMetaDn                                                   CfprManagedObjectDn,
    cfprTrigMetaRn                                                   SnmpAdminString,
    cfprTrigMetaAdminState                                           CfprTrigAdminState,
    cfprTrigMetaDescr                                                SnmpAdminString,
    cfprTrigMetaIntId                                                SnmpAdminString,
    cfprTrigMetaJobCount                                             Gauge32,
    cfprTrigMetaName                                                 SnmpAdminString,
    cfprTrigMetaOperState                                            CfprTrigOperState,
    cfprTrigMetaPolicyLevel                                          Gauge32,
    cfprTrigMetaPolicyOwner                                          CfprPolicyPolicyOwner,
    cfprTrigMetaSchedName                                            SnmpAdminString,
    cfprTrigMetaTrigTime                                             DateAndTime,
    cfprTrigMetaWindowDn                                             SnmpAdminString
}

cfprTrigMetaInstanceId OBJECT-TYPE
    SYNTAX       CfprManagedObjectId
    MAX-ACCESS   not-accessible
    STATUS       current
    DESCRIPTION
        "Instance identifier of the managed object."
    ::= { cfprTrigMetaEntry 1 }

cfprTrigMetaDn OBJECT-TYPE
    SYNTAX       CfprManagedObjectDn
    MAX-ACCESS   read-only
    STATUS       current
    DESCRIPTION
        "Cisco Firepower trig:Meta:dn managed object property"
    ::= { cfprTrigMetaEntry 2 }

cfprTrigMetaRn OBJECT-TYPE
    SYNTAX       SnmpAdminString
    MAX-ACCESS   read-only
    STATUS       current
    DESCRIPTION
        "Cisco Firepower trig:Meta:rn managed object property"
    ::= { cfprTrigMetaEntry 3 }

cfprTrigMetaAdminState OBJECT-TYPE
    SYNTAX       CfprTrigAdminState
    MAX-ACCESS   read-only
    STATUS       current
    DESCRIPTION
        "Cisco Firepower trig:Meta:adminState managed object property"
    ::= { cfprTrigMetaEntry 4 }

cfprTrigMetaDescr OBJECT-TYPE
    SYNTAX       SnmpAdminString
    MAX-ACCESS   read-only
    STATUS       current
    DESCRIPTION
        "Cisco Firepower trig:Meta:descr managed object property"
    ::= { cfprTrigMetaEntry 5 }

cfprTrigMetaIntId OBJECT-TYPE
    SYNTAX       SnmpAdminString
    MAX-ACCESS   read-only
    STATUS       current
    DESCRIPTION
        "Cisco Firepower trig:Meta:intId managed object property"
    ::= { cfprTrigMetaEntry 6 }

cfprTrigMetaJobCount OBJECT-TYPE
    SYNTAX       Gauge32
    MAX-ACCESS   read-only
    STATUS       current
    DESCRIPTION
        "Cisco Firepower trig:Meta:jobCount managed object property"
    ::= { cfprTrigMetaEntry 7 }

cfprTrigMetaName OBJECT-TYPE
    SYNTAX       SnmpAdminString
    MAX-ACCESS   read-only
    STATUS       current
    DESCRIPTION
        "Cisco Firepower trig:Meta:name managed object property"
    ::= { cfprTrigMetaEntry 8 }

cfprTrigMetaOperState OBJECT-TYPE
    SYNTAX       CfprTrigOperState
    MAX-ACCESS   read-only
    STATUS       current
    DESCRIPTION
        "Cisco Firepower trig:Meta:operState managed object property"
    ::= { cfprTrigMetaEntry 9 }

cfprTrigMetaPolicyLevel OBJECT-TYPE
    SYNTAX       Gauge32
    MAX-ACCESS   read-only
    STATUS       current
    DESCRIPTION
        "Cisco Firepower trig:Meta:policyLevel managed object property"
    ::= { cfprTrigMetaEntry 10 }

cfprTrigMetaPolicyOwner OBJECT-TYPE
    SYNTAX       CfprPolicyPolicyOwner
    MAX-ACCESS   read-only
    STATUS       current
    DESCRIPTION
        "Cisco Firepower trig:Meta:policyOwner managed object property"
    ::= { cfprTrigMetaEntry 11 }

cfprTrigMetaSchedName OBJECT-TYPE
    SYNTAX       SnmpAdminString
    MAX-ACCESS   read-only
    STATUS       current
    DESCRIPTION
        "Cisco Firepower trig:Meta:schedName managed object property"
    ::= { cfprTrigMetaEntry 12 }

cfprTrigMetaTrigTime OBJECT-TYPE
    SYNTAX       DateAndTime
    MAX-ACCESS   read-only
    STATUS       current
    DESCRIPTION
        "Cisco Firepower trig:Meta:trigTime managed object property"
    ::= { cfprTrigMetaEntry 13 }

cfprTrigMetaWindowDn OBJECT-TYPE
    SYNTAX       SnmpAdminString
    MAX-ACCESS   read-only
    STATUS       current
    DESCRIPTION
        "Cisco Firepower trig:Meta:windowDn managed object property"
    ::= { cfprTrigMetaEntry 14 }

cfprTrigRecurrWindowTable OBJECT-TYPE
    SYNTAX           SEQUENCE OF CfprTrigRecurrWindowEntry
    MAX-ACCESS       not-accessible
    STATUS           current
    DESCRIPTION
        "Cisco Firepower trig:RecurrWindow managed object table"
    ::= { cfprTrigObjects 6 }

cfprTrigRecurrWindowEntry OBJECT-TYPE
    SYNTAX           CfprTrigRecurrWindowEntry
    MAX-ACCESS       not-accessible
    STATUS           current
    DESCRIPTION
        "Entry for the cfprTrigRecurrWindowTable table."
    INDEX { cfprTrigRecurrWindowInstanceId }
    ::= { cfprTrigRecurrWindowTable 1 }

CfprTrigRecurrWindowEntry ::= SEQUENCE {
    cfprTrigRecurrWindowInstanceId                                   CfprManagedObjectId,
    cfprTrigRecurrWindowDn                                           CfprManagedObjectDn,
    cfprTrigRecurrWindowRn                                           SnmpAdminString,
    cfprTrigRecurrWindowConcurCap                                    Gauge32,
    cfprTrigRecurrWindowDay                                          CfprTrigDay,
    cfprTrigRecurrWindowHour                                         Gauge32,
    cfprTrigRecurrWindowJobCount                                     Gauge32,
    cfprTrigRecurrWindowMinute                                       Gauge32,
    cfprTrigRecurrWindowName                                         SnmpAdminString,
    cfprTrigRecurrWindowProcBreak                                    SnmpAdminString,
    cfprTrigRecurrWindowProcCap                                      Gauge32,
    cfprTrigRecurrWindowTimeCap                                      SnmpAdminString
}

cfprTrigRecurrWindowInstanceId OBJECT-TYPE
    SYNTAX       CfprManagedObjectId
    MAX-ACCESS   not-accessible
    STATUS       current
    DESCRIPTION
        "Instance identifier of the managed object."
    ::= { cfprTrigRecurrWindowEntry 1 }

cfprTrigRecurrWindowDn OBJECT-TYPE
    SYNTAX       CfprManagedObjectDn
    MAX-ACCESS   read-only
    STATUS       current
    DESCRIPTION
        "Cisco Firepower trig:RecurrWindow:dn managed object property"
    ::= { cfprTrigRecurrWindowEntry 2 }

cfprTrigRecurrWindowRn OBJECT-TYPE
    SYNTAX       SnmpAdminString
    MAX-ACCESS   read-only
    STATUS       current
    DESCRIPTION
        "Cisco Firepower trig:RecurrWindow:rn managed object property"
    ::= { cfprTrigRecurrWindowEntry 3 }

cfprTrigRecurrWindowConcurCap OBJECT-TYPE
    SYNTAX       Gauge32
    MAX-ACCESS   read-only
    STATUS       current
    DESCRIPTION
        "Cisco Firepower trig:RecurrWindow:concurCap managed
        object property"
    ::= { cfprTrigRecurrWindowEntry 4 }

cfprTrigRecurrWindowDay OBJECT-TYPE
    SYNTAX       CfprTrigDay
    MAX-ACCESS   read-only
    STATUS       current
    DESCRIPTION
        "Cisco Firepower trig:RecurrWindow:day managed object property"
    ::= { cfprTrigRecurrWindowEntry 5 }

cfprTrigRecurrWindowHour OBJECT-TYPE
    SYNTAX       Gauge32
    MAX-ACCESS   read-only
    STATUS       current
    DESCRIPTION
        "Cisco Firepower trig:RecurrWindow:hour managed object property"
    ::= { cfprTrigRecurrWindowEntry 6 }

cfprTrigRecurrWindowJobCount OBJECT-TYPE
    SYNTAX       Gauge32
    MAX-ACCESS   read-only
    STATUS       current
    DESCRIPTION
        "Cisco Firepower trig:RecurrWindow:jobCount managed
        object property"
    ::= { cfprTrigRecurrWindowEntry 7 }

cfprTrigRecurrWindowMinute OBJECT-TYPE
    SYNTAX       Gauge32
    MAX-ACCESS   read-only
    STATUS       current
    DESCRIPTION
        "Cisco Firepower trig:RecurrWindow:minute managed object property"
    ::= { cfprTrigRecurrWindowEntry 8 }

cfprTrigRecurrWindowName OBJECT-TYPE
    SYNTAX       SnmpAdminString
    MAX-ACCESS   read-only
    STATUS       current
    DESCRIPTION
        "Cisco Firepower trig:RecurrWindow:name managed object property"
    ::= { cfprTrigRecurrWindowEntry 9 }

cfprTrigRecurrWindowProcBreak OBJECT-TYPE
    SYNTAX       SnmpAdminString
    MAX-ACCESS   read-only
    STATUS       current
    DESCRIPTION
        "Cisco Firepower trig:RecurrWindow:procBreak managed
        object property"
    ::= { cfprTrigRecurrWindowEntry 10 }

cfprTrigRecurrWindowProcCap OBJECT-TYPE
    SYNTAX       Gauge32
    MAX-ACCESS   read-only
    STATUS       current
    DESCRIPTION
        "Cisco Firepower trig:RecurrWindow:procCap managed
        object property"
    ::= { cfprTrigRecurrWindowEntry 11 }

cfprTrigRecurrWindowTimeCap OBJECT-TYPE
    SYNTAX       SnmpAdminString
    MAX-ACCESS   read-only
    STATUS       current
    DESCRIPTION
        "Cisco Firepower trig:RecurrWindow:timeCap managed
        object property"
    ::= { cfprTrigRecurrWindowEntry 12 }

cfprTrigSchedTable OBJECT-TYPE
    SYNTAX           SEQUENCE OF CfprTrigSchedEntry
    MAX-ACCESS       not-accessible
    STATUS           current
    DESCRIPTION
        "Cisco Firepower trig:Sched managed object table"
    ::= { cfprTrigObjects 7 }

cfprTrigSchedEntry OBJECT-TYPE
    SYNTAX           CfprTrigSchedEntry
    MAX-ACCESS       not-accessible
    STATUS           current
    DESCRIPTION
        "Entry for the cfprTrigSchedTable table."
    INDEX { cfprTrigSchedInstanceId }
    ::= { cfprTrigSchedTable 1 }

CfprTrigSchedEntry ::= SEQUENCE {
    cfprTrigSchedInstanceId                                          CfprManagedObjectId,
    cfprTrigSchedDn                                                  CfprManagedObjectDn,
    cfprTrigSchedRn                                                  SnmpAdminString,
    cfprTrigSchedAdminState                                          CfprTrigAdminState,
    cfprTrigSchedDescr                                               SnmpAdminString,
    cfprTrigSchedFlgInitialActive                                    TruthValue,
    cfprTrigSchedIntId                                               SnmpAdminString,
    cfprTrigSchedName                                                SnmpAdminString,
    cfprTrigSchedOperState                                           CfprTrigOperState,
    cfprTrigSchedPolicyLevel                                         Gauge32,
    cfprTrigSchedPolicyOwner                                         CfprPolicyPolicyOwner
}

cfprTrigSchedInstanceId OBJECT-TYPE
    SYNTAX       CfprManagedObjectId
    MAX-ACCESS   not-accessible
    STATUS       current
    DESCRIPTION
        "Instance identifier of the managed object."
    ::= { cfprTrigSchedEntry 1 }

cfprTrigSchedDn OBJECT-TYPE
    SYNTAX       CfprManagedObjectDn
    MAX-ACCESS   read-only
    STATUS       current
    DESCRIPTION
        "Cisco Firepower trig:Sched:dn managed object property"
    ::= { cfprTrigSchedEntry 2 }

cfprTrigSchedRn OBJECT-TYPE
    SYNTAX       SnmpAdminString
    MAX-ACCESS   read-only
    STATUS       current
    DESCRIPTION
        "Cisco Firepower trig:Sched:rn managed object property"
    ::= { cfprTrigSchedEntry 3 }

cfprTrigSchedAdminState OBJECT-TYPE
    SYNTAX       CfprTrigAdminState
    MAX-ACCESS   read-only
    STATUS       current
    DESCRIPTION
        "Cisco Firepower trig:Sched:adminState managed object property"
    ::= { cfprTrigSchedEntry 4 }

cfprTrigSchedDescr OBJECT-TYPE
    SYNTAX       SnmpAdminString
    MAX-ACCESS   read-only
    STATUS       current
    DESCRIPTION
        "Cisco Firepower trig:Sched:descr managed object property"
    ::= { cfprTrigSchedEntry 5 }

cfprTrigSchedFlgInitialActive OBJECT-TYPE
    SYNTAX       TruthValue
    MAX-ACCESS   read-only
    STATUS       current
    DESCRIPTION
        "Cisco Firepower trig:Sched:flgInitialActive managed
        object property"
    ::= { cfprTrigSchedEntry 6 }

cfprTrigSchedIntId OBJECT-TYPE
    SYNTAX       SnmpAdminString
    MAX-ACCESS   read-only
    STATUS       current
    DESCRIPTION
        "Cisco Firepower trig:Sched:intId managed object property"
    ::= { cfprTrigSchedEntry 7 }

cfprTrigSchedName OBJECT-TYPE
    SYNTAX       SnmpAdminString
    MAX-ACCESS   read-only
    STATUS       current
    DESCRIPTION
        "Cisco Firepower trig:Sched:name managed object property"
    ::= { cfprTrigSchedEntry 8 }

cfprTrigSchedOperState OBJECT-TYPE
    SYNTAX       CfprTrigOperState
    MAX-ACCESS   read-only
    STATUS       current
    DESCRIPTION
        "Cisco Firepower trig:Sched:operState managed object property"
    ::= { cfprTrigSchedEntry 9 }

cfprTrigSchedPolicyLevel OBJECT-TYPE
    SYNTAX       Gauge32
    MAX-ACCESS   read-only
    STATUS       current
    DESCRIPTION
        "Cisco Firepower trig:Sched:policyLevel managed object property"
    ::= { cfprTrigSchedEntry 10 }

cfprTrigSchedPolicyOwner OBJECT-TYPE
    SYNTAX       CfprPolicyPolicyOwner
    MAX-ACCESS   read-only
    STATUS       current
    DESCRIPTION
        "Cisco Firepower trig:Sched:policyOwner managed object property"
    ::= { cfprTrigSchedEntry 11 }

cfprTrigTestTable OBJECT-TYPE
    SYNTAX           SEQUENCE OF CfprTrigTestEntry
    MAX-ACCESS       not-accessible
    STATUS           current
    DESCRIPTION
        "Cisco Firepower trig:Test managed object table"
    ::= { cfprTrigObjects 8 }

cfprTrigTestEntry OBJECT-TYPE
    SYNTAX           CfprTrigTestEntry
    MAX-ACCESS       not-accessible
    STATUS           current
    DESCRIPTION
        "Entry for the cfprTrigTestTable table."
    INDEX { cfprTrigTestInstanceId }
    ::= { cfprTrigTestTable 1 }

CfprTrigTestEntry ::= SEQUENCE {
    cfprTrigTestInstanceId                                           CfprManagedObjectId,
    cfprTrigTestDn                                                   CfprManagedObjectDn,
    cfprTrigTestRn                                                   SnmpAdminString,
    cfprTrigTestAdminState                                           CfprTrigAdminState,
    cfprTrigTestAutoDelete                                           TruthValue,
    cfprTrigTestCreationDate                                         DateAndTime,
    cfprTrigTestDescr                                                SnmpAdminString,
    cfprTrigTestIgnoreCap                                            TruthValue,
    cfprTrigTestIntId                                                SnmpAdminString,
    cfprTrigTestName                                                 SnmpAdminString,
    cfprTrigTestOperScheduler                                        SnmpAdminString,
    cfprTrigTestOperState                                            CfprTrigTrigOperState,
    cfprTrigTestPolicyLevel                                          Gauge32,
    cfprTrigTestPolicyOwner                                          CfprPolicyPolicyOwner,
    cfprTrigTestScheduler                                            SnmpAdminString
}

cfprTrigTestInstanceId OBJECT-TYPE
    SYNTAX       CfprManagedObjectId
    MAX-ACCESS   not-accessible
    STATUS       current
    DESCRIPTION
        "Instance identifier of the managed object."
    ::= { cfprTrigTestEntry 1 }

cfprTrigTestDn OBJECT-TYPE
    SYNTAX       CfprManagedObjectDn
    MAX-ACCESS   read-only
    STATUS       current
    DESCRIPTION
        "Cisco Firepower trig:Test:dn managed object property"
    ::= { cfprTrigTestEntry 2 }

cfprTrigTestRn OBJECT-TYPE
    SYNTAX       SnmpAdminString
    MAX-ACCESS   read-only
    STATUS       current
    DESCRIPTION
        "Cisco Firepower trig:Test:rn managed object property"
    ::= { cfprTrigTestEntry 3 }

cfprTrigTestAdminState OBJECT-TYPE
    SYNTAX       CfprTrigAdminState
    MAX-ACCESS   read-only
    STATUS       current
    DESCRIPTION
        "Cisco Firepower trig:Test:adminState managed object property"
    ::= { cfprTrigTestEntry 4 }

cfprTrigTestAutoDelete OBJECT-TYPE
    SYNTAX       TruthValue
    MAX-ACCESS   read-only
    STATUS       current
    DESCRIPTION
        "Cisco Firepower trig:Test:autoDelete managed object property"
    ::= { cfprTrigTestEntry 5 }

cfprTrigTestCreationDate OBJECT-TYPE
    SYNTAX       DateAndTime
    MAX-ACCESS   read-only
    STATUS       current
    DESCRIPTION
        "Cisco Firepower trig:Test:creationDate managed object property"
    ::= { cfprTrigTestEntry 6 }

cfprTrigTestDescr OBJECT-TYPE
    SYNTAX       SnmpAdminString
    MAX-ACCESS   read-only
    STATUS       current
    DESCRIPTION
        "Cisco Firepower trig:Test:descr managed object property"
    ::= { cfprTrigTestEntry 7 }

cfprTrigTestIgnoreCap OBJECT-TYPE
    SYNTAX       TruthValue
    MAX-ACCESS   read-only
    STATUS       current
    DESCRIPTION
        "Cisco Firepower trig:Test:ignoreCap managed object property"
    ::= { cfprTrigTestEntry 8 }

cfprTrigTestIntId OBJECT-TYPE
    SYNTAX       SnmpAdminString
    MAX-ACCESS   read-only
    STATUS       current
    DESCRIPTION
        "Cisco Firepower trig:Test:intId managed object property"
    ::= { cfprTrigTestEntry 9 }

cfprTrigTestName OBJECT-TYPE
    SYNTAX       SnmpAdminString
    MAX-ACCESS   read-only
    STATUS       current
    DESCRIPTION
        "Cisco Firepower trig:Test:name managed object property"
    ::= { cfprTrigTestEntry 10 }

cfprTrigTestOperScheduler OBJECT-TYPE
    SYNTAX       SnmpAdminString
    MAX-ACCESS   read-only
    STATUS       current
    DESCRIPTION
        "Cisco Firepower trig:Test:operScheduler managed object property"
    ::= { cfprTrigTestEntry 11 }

cfprTrigTestOperState OBJECT-TYPE
    SYNTAX       CfprTrigTrigOperState
    MAX-ACCESS   read-only
    STATUS       current
    DESCRIPTION
        "Cisco Firepower trig:Test:operState managed object property"
    ::= { cfprTrigTestEntry 12 }

cfprTrigTestPolicyLevel OBJECT-TYPE
    SYNTAX       Gauge32
    MAX-ACCESS   read-only
    STATUS       current
    DESCRIPTION
        "Cisco Firepower trig:Test:policyLevel managed object property"
    ::= { cfprTrigTestEntry 13 }

cfprTrigTestPolicyOwner OBJECT-TYPE
    SYNTAX       CfprPolicyPolicyOwner
    MAX-ACCESS   read-only
    STATUS       current
    DESCRIPTION
        "Cisco Firepower trig:Test:policyOwner managed object property"
    ::= { cfprTrigTestEntry 14 }

cfprTrigTestScheduler OBJECT-TYPE
    SYNTAX       SnmpAdminString
    MAX-ACCESS   read-only
    STATUS       current
    DESCRIPTION
        "Cisco Firepower trig:Test:scheduler managed object property"
    ::= { cfprTrigTestEntry 15 }

cfprTrigTriggeredTable OBJECT-TYPE
    SYNTAX           SEQUENCE OF CfprTrigTriggeredEntry
    MAX-ACCESS       not-accessible
    STATUS           current
    DESCRIPTION
        "Cisco Firepower trig:Triggered managed object table"
    ::= { cfprTrigObjects 9 }

cfprTrigTriggeredEntry OBJECT-TYPE
    SYNTAX           CfprTrigTriggeredEntry
    MAX-ACCESS       not-accessible
    STATUS           current
    DESCRIPTION
        "Entry for the cfprTrigTriggeredTable table."
    INDEX { cfprTrigTriggeredInstanceId }
    ::= { cfprTrigTriggeredTable 1 }

CfprTrigTriggeredEntry ::= SEQUENCE {
    cfprTrigTriggeredInstanceId                                      CfprManagedObjectId,
    cfprTrigTriggeredDn                                              CfprManagedObjectDn,
    cfprTrigTriggeredRn                                              SnmpAdminString,
    cfprTrigTriggeredJobCount                                        Gauge32,
    cfprTrigTriggeredOperState                                       CfprTrigTriggeredState,
    cfprTrigTriggeredOrder                                           Gauge32,
    cfprTrigTriggeredTrDn                                            SnmpAdminString,
    cfprTrigTriggeredTrId                                            Gauge32
}

cfprTrigTriggeredInstanceId OBJECT-TYPE
    SYNTAX       CfprManagedObjectId
    MAX-ACCESS   not-accessible
    STATUS       current
    DESCRIPTION
        "Instance identifier of the managed object."
    ::= { cfprTrigTriggeredEntry 1 }

cfprTrigTriggeredDn OBJECT-TYPE
    SYNTAX       CfprManagedObjectDn
    MAX-ACCESS   read-only
    STATUS       current
    DESCRIPTION
        "Cisco Firepower trig:Triggered:dn managed object property"
    ::= { cfprTrigTriggeredEntry 2 }

cfprTrigTriggeredRn OBJECT-TYPE
    SYNTAX       SnmpAdminString
    MAX-ACCESS   read-only
    STATUS       current
    DESCRIPTION
        "Cisco Firepower trig:Triggered:rn managed object property"
    ::= { cfprTrigTriggeredEntry 3 }

cfprTrigTriggeredJobCount OBJECT-TYPE
    SYNTAX       Gauge32
    MAX-ACCESS   read-only
    STATUS       current
    DESCRIPTION
        "Cisco Firepower trig:Triggered:jobCount managed object property"
    ::= { cfprTrigTriggeredEntry 4 }

cfprTrigTriggeredOperState OBJECT-TYPE
    SYNTAX       CfprTrigTriggeredState
    MAX-ACCESS   read-only
    STATUS       current
    DESCRIPTION
        "Cisco Firepower trig:Triggered:operState managed object property"
    ::= { cfprTrigTriggeredEntry 5 }

cfprTrigTriggeredOrder OBJECT-TYPE
    SYNTAX       Gauge32
    MAX-ACCESS   read-only
    STATUS       current
    DESCRIPTION
        "Cisco Firepower trig:Triggered:order managed object property"
    ::= { cfprTrigTriggeredEntry 6 }

cfprTrigTriggeredTrDn OBJECT-TYPE
    SYNTAX       SnmpAdminString
    MAX-ACCESS   read-only
    STATUS       current
    DESCRIPTION
        "Cisco Firepower trig:Triggered:trDn managed object property"
    ::= { cfprTrigTriggeredEntry 7 }

cfprTrigTriggeredTrId OBJECT-TYPE
    SYNTAX       Gauge32
    MAX-ACCESS   read-only
    STATUS       current
    DESCRIPTION
        "Cisco Firepower trig:Triggered:trId managed object property"
    ::= { cfprTrigTriggeredEntry 8 }

END
