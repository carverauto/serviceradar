--------------------------------------------------------------------
-- CISCO-COMPRESSION-SERVICE-ADAPTER-MIB.my:  
--          Cisco compression service adaptor MIB file. 
--
-- April 1996, Subodh Nijsure, Ram Montinola
--
-- Copyright (c) 1996-1997 by cisco Systems, Inc.
-- All rights reserved.
--------------------------------------------------------------------
--

CISCO-COMPRESSION-SERVICE-ADAPTER-MIB DEFINITIONS ::= BEGIN

-- MIB Definitions for Cisco Compression Service Adapter management.
-- A compression service adapter is a hardware unit used to
-- compress/decompress data. 
-- This MIB is intended to
--     Provide performance information about a compression service 
--     adapter. 
--     Enable or disable the compression service adapter. 
--
--
IMPORTS
	MODULE-IDENTITY, OBJECT-TYPE, Counter32 , Gauge32
		FROM SNMPv2-SMI
	MODULE-COMPLIANCE, OBJECT-GROUP
		FROM SNMPv2-CONF
	TruthValue
		FROM SNMPv2-TC 
	ciscoMgmt
		FROM CISCO-SMI
	cardIndex
		FROM OLD-CISCO-CHASSIS-MIB;

-- ***************************************************************
-- Define Compression service adapter MIB objects
-- ***************************************************************

ciscoCompressionServiceAdapterMIB MODULE-IDENTITY
	LAST-UPDATED	"9608150000Z"
	ORGANIZATION	"Cisco Systems, Inc."
	CONTACT-INFO  
		"	Cisco Systems
		Customer Service

		Postal: 170 West Tasman Drive
		San Jose, CA  95134
		USA
	
		Tel: +1 800 553-NETS

		E-mail: cs-snmp@cisco.com"
	DESCRIPTION
		"Used to manage the compression service adapter."
	::= { ciscoMgmt 57 }

ciscoCSAMIBObjects OBJECT IDENTIFIER ::= { ciscoCompressionServiceAdapterMIB 1 }
-- 
-- Define cisco compression mib objects
--

csaStats	OBJECT IDENTIFIER ::= { ciscoCSAMIBObjects 1 }


csaStatsTable OBJECT-TYPE
	SYNTAX     SEQUENCE OF CsaStatsEntry
	MAX-ACCESS not-accessible
	STATUS     current
	DESCRIPTION
		"A table describing performance statistics and status of 
		compression service adapter."
	::= { csaStats 1 }

csaStatsEntry OBJECT-TYPE
	SYNTAX CsaStatsEntry
	MAX-ACCESS not-accessible
	STATUS     current
	DESCRIPTION
		"Each entry in this table describes performance statistics 
		 for a compression service. A new entry is created or removed
		 when compression service adapter is physically added or 
		 removed from the device.
		 Each entry is indexed by cardIndex object, which is an
		 index for cardTable in chassis mib. Every card of type
		 sa-compression in cardTable will have corresponding entry
		 in csaStatsTable."
	INDEX { cardIndex }
	::= { csaStatsTable 1 }

CsaStatsEntry ::=
	SEQUENCE {
		csaInOctets
			Counter32,
		csaOutOctets
		        Counter32,	
		csaInPackets 
			Counter32,
		csaOutPackets 
			Counter32,	
                csaInPacketsDrop 
			Counter32,	
                csaOutPacketsDrop 
			Counter32,
		csaNumberOfRestarts
			Counter32,
		csaCompressionRatio 
			Gauge32,
		csaDecompressionRatio 
			Gauge32,
		csaEnable 
			TruthValue
	}

csaInOctets  OBJECT-TYPE
	SYNTAX	Counter32
	MAX-ACCESS read-only
	STATUS current
	DESCRIPTION
		"Total number of compressed octets received by the compression
		service adaptor."
	::= { csaStatsEntry 1 }


csaOutOctets OBJECT-TYPE
	SYNTAX Counter32	
	MAX-ACCESS read-only
	STATUS	current
	DESCRIPTION
		"Total number of compressed octets sent by the compression
		service adaptor."
	::= { csaStatsEntry 2 }

csaInPackets  OBJECT-TYPE
	SYNTAX	Counter32
	MAX-ACCESS read-only
	STATUS current
	DESCRIPTION
		"Total number of compressed packets received by the compression
		service adaptor."
	::= { csaStatsEntry 3 }


csaOutPackets OBJECT-TYPE
	SYNTAX Counter32	
	MAX-ACCESS read-only
	STATUS	current
	DESCRIPTION
		"Total number of compressed packets sent by the compression
		service adaptor."
	::= { csaStatsEntry 4 }

csaInPacketsDrop OBJECT-TYPE
	SYNTAX  Counter32	
	MAX-ACCESS read-only
	STATUS current
	DESCRIPTION
		"Total number of output packets dropped.
                 A large number of packets dropped by a compression adaptor
                 would indicate, amount of data being passed to the adaptor
                 for processing, exceeds its capacity."

	::= { csaStatsEntry 5 }

csaOutPacketsDrop OBJECT-TYPE
	SYNTAX  Counter32	
	MAX-ACCESS read-only
	STATUS current
	DESCRIPTION
		"Total number of input packets dropped.
                 A large number of packets dropped by a compression adaptor
                 would indicate, amount of data being passed to the adaptor
                 for processing, exceeds its capacity."
	::= { csaStatsEntry 6 }

csaNumberOfRestarts OBJECT-TYPE
	SYNTAX  Counter32	
	MAX-ACCESS read-only
	STATUS current
	DESCRIPTION
		"Number of compression session restarts. A large number of 
		restarts could indicate incompatible remote router, data being
		corrupted in transmission or packet order not being 
		maintained." 
	::= { csaStatsEntry 7 }

csaCompressionRatio OBJECT-TYPE
	SYNTAX  Gauge32	 (0..100)
	MAX-ACCESS read-only
	STATUS current
	DESCRIPTION
		"Current Compression ratio, the percentage the data was 
		compressed.  This is an instantaneous value. 
		Compression ratio of 0% would indicate no 
		compression, a compression ratio of 90% could mean 100 
		octets were compressed into 10 octets."
	::= { csaStatsEntry 8 }

csaDecompressionRatio OBJECT-TYPE
	SYNTAX  Gauge32	 (0..100)
	MAX-ACCESS read-only
	STATUS current
	DESCRIPTION
		"Current decompression ratio, the percentage the data was 
		decompressed.  This is an instantaneous value. 
		Decompression ratio of 0% would indicate no decompression, 
		a decompression ratio of 90% could mean 10 octets were 
		decompressed into 100 octets."
	::= { csaStatsEntry 9 }

csaEnable OBJECT-TYPE
        SYNTAX  TruthValue 
	MAX-ACCESS read-write
	STATUS current
	DESCRIPTION
                "Indicates whether compression service adapter is currently
                 active.  Also allows users to set status via SNMP." 
	::= {  csaStatsEntry 10 }

-- conformance information

ciscoCSAMIBConformance OBJECT IDENTIFIER ::= { ciscoCompressionServiceAdapterMIB  3 }

csaMIBCompliances OBJECT IDENTIFIER ::= { ciscoCSAMIBConformance 1 }

csaMIBGroups      OBJECT IDENTIFIER ::= { ciscoCSAMIBConformance 2 }


-- compliance statements

csaMIBCompliance MODULE-COMPLIANCE
	STATUS  current
	DESCRIPTION
		"The Cisco Compression Service Adapter MIB is required in all 
		systems supporting such an adaptor."   
	MODULE  -- this module
	MANDATORY-GROUPS { csaMIBGroup }
	::= { csaMIBCompliances 1 }

-- units of conformance

csaMIBGroup OBJECT-GROUP
	OBJECTS {
		csaInOctets,
		csaOutOctets,	
		csaInPackets,
		csaOutPackets,	
                csaInPacketsDrop,
		csaOutPacketsDrop,	
		csaNumberOfRestarts, 
		csaCompressionRatio,
		csaDecompressionRatio,
                csaEnable 
	}
	STATUS  current
	DESCRIPTION
		"A collection of objects providing information about 
		Cisco compression service adapter." 
	::= { csaMIBGroups 1 }

END
