-- *********************************************************************
-- CISCO-FIREPOWER-FLOWCTRL-MIB.my
-- 
-- MIB representation of the Cisco Firepower
-- FLOWCTRL management information model package
-- 
-- Created May 2024 by Charles Bullis
-- 
-- Copyright (c) 2005-2024 Cisco Systems, Inc. All rights reserved.
-- 
-- *********************************************************************

CISCO-FIREPOWER-FLOWCTRL-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB
    CfprFlowctrlFlowControlRx,
    CfprFlowctrlFlowControlTx,
    CfprFlowctrlPriorityPause,
    CfprPolicyPolicyOwner
        FROM CISCO-FIREPOWER-TC-MIB;

cfprFlowctrlObjects MODULE-IDENTITY
    LAST-UPDATED    "202405160000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        FLOWCTRL management information model package"
    ::= { ciscoFirepowerMIBObjects 31 }

cfprFlowctrlDefinitionTable OBJECT-TYPE
    SYNTAX           SEQUENCE OF CfprFlowctrlDefinitionEntry
    MAX-ACCESS       not-accessible
    STATUS           current
    DESCRIPTION
        "Cisco Firepower flowctrl:Definition managed object table"
    ::= { cfprFlowctrlObjects 1 }

cfprFlowctrlDefinitionEntry OBJECT-TYPE
    SYNTAX           CfprFlowctrlDefinitionEntry
    MAX-ACCESS       not-accessible
    STATUS           current
    DESCRIPTION
        "Entry for the cfprFlowctrlDefinitionTable table."
    INDEX { cfprFlowctrlDefinitionInstanceId }
    ::= { cfprFlowctrlDefinitionTable 1 }

CfprFlowctrlDefinitionEntry ::= SEQUENCE {
    cfprFlowctrlDefinitionInstanceId                                 CfprManagedObjectId,
    cfprFlowctrlDefinitionDn                                         CfprManagedObjectDn,
    cfprFlowctrlDefinitionRn                                         SnmpAdminString,
    cfprFlowctrlDefinitionDescr                                      SnmpAdminString,
    cfprFlowctrlDefinitionIntId                                      SnmpAdminString,
    cfprFlowctrlDefinitionName                                       SnmpAdminString,
    cfprFlowctrlDefinitionPolicyLevel                                Gauge32,
    cfprFlowctrlDefinitionPolicyOwner                                CfprPolicyPolicyOwner
}

cfprFlowctrlDefinitionInstanceId OBJECT-TYPE
    SYNTAX       CfprManagedObjectId
    MAX-ACCESS   not-accessible
    STATUS       current
    DESCRIPTION
        "Instance identifier of the managed object."
    ::= { cfprFlowctrlDefinitionEntry 1 }

cfprFlowctrlDefinitionDn OBJECT-TYPE
    SYNTAX       CfprManagedObjectDn
    MAX-ACCESS   read-only
    STATUS       current
    DESCRIPTION
        "Cisco Firepower flowctrl:Definition:dn managed object property"
    ::= { cfprFlowctrlDefinitionEntry 2 }

cfprFlowctrlDefinitionRn OBJECT-TYPE
    SYNTAX       SnmpAdminString
    MAX-ACCESS   read-only
    STATUS       current
    DESCRIPTION
        "Cisco Firepower flowctrl:Definition:rn managed object property"
    ::= { cfprFlowctrlDefinitionEntry 3 }

cfprFlowctrlDefinitionDescr OBJECT-TYPE
    SYNTAX       SnmpAdminString
    MAX-ACCESS   read-only
    STATUS       current
    DESCRIPTION
        "Cisco Firepower flowctrl:Definition:descr managed
        object property"
    ::= { cfprFlowctrlDefinitionEntry 4 }

cfprFlowctrlDefinitionIntId OBJECT-TYPE
    SYNTAX       SnmpAdminString
    MAX-ACCESS   read-only
    STATUS       current
    DESCRIPTION
        "Cisco Firepower flowctrl:Definition:intId managed
        object property"
    ::= { cfprFlowctrlDefinitionEntry 5 }

cfprFlowctrlDefinitionName OBJECT-TYPE
    SYNTAX       SnmpAdminString
    MAX-ACCESS   read-only
    STATUS       current
    DESCRIPTION
        "Cisco Firepower flowctrl:Definition:name managed object property"
    ::= { cfprFlowctrlDefinitionEntry 6 }

cfprFlowctrlDefinitionPolicyLevel OBJECT-TYPE
    SYNTAX       Gauge32
    MAX-ACCESS   read-only
    STATUS       current
    DESCRIPTION
        "Cisco Firepower flowctrl:Definition:policyLevel
        managed object property"
    ::= { cfprFlowctrlDefinitionEntry 7 }

cfprFlowctrlDefinitionPolicyOwner OBJECT-TYPE
    SYNTAX       CfprPolicyPolicyOwner
    MAX-ACCESS   read-only
    STATUS       current
    DESCRIPTION
        "Cisco Firepower flowctrl:Definition:policyOwner
        managed object property"
    ::= { cfprFlowctrlDefinitionEntry 8 }

cfprFlowctrlItemTable OBJECT-TYPE
    SYNTAX           SEQUENCE OF CfprFlowctrlItemEntry
    MAX-ACCESS       not-accessible
    STATUS           current
    DESCRIPTION
        "Cisco Firepower flowctrl:Item managed object table"
    ::= { cfprFlowctrlObjects 2 }

cfprFlowctrlItemEntry OBJECT-TYPE
    SYNTAX           CfprFlowctrlItemEntry
    MAX-ACCESS       not-accessible
    STATUS           current
    DESCRIPTION
        "Entry for the cfprFlowctrlItemTable table."
    INDEX { cfprFlowctrlItemInstanceId }
    ::= { cfprFlowctrlItemTable 1 }

CfprFlowctrlItemEntry ::= SEQUENCE {
    cfprFlowctrlItemInstanceId                                       CfprManagedObjectId,
    cfprFlowctrlItemDn                                               CfprManagedObjectDn,
    cfprFlowctrlItemRn                                               SnmpAdminString,
    cfprFlowctrlItemName                                             SnmpAdminString,
    cfprFlowctrlItemPrio                                             CfprFlowctrlPriorityPause,
    cfprFlowctrlItemRcv                                              CfprFlowctrlFlowControlRx,
    cfprFlowctrlItemSnd                                              CfprFlowctrlFlowControlTx
}

cfprFlowctrlItemInstanceId OBJECT-TYPE
    SYNTAX       CfprManagedObjectId
    MAX-ACCESS   not-accessible
    STATUS       current
    DESCRIPTION
        "Instance identifier of the managed object."
    ::= { cfprFlowctrlItemEntry 1 }

cfprFlowctrlItemDn OBJECT-TYPE
    SYNTAX       CfprManagedObjectDn
    MAX-ACCESS   read-only
    STATUS       current
    DESCRIPTION
        "Cisco Firepower flowctrl:Item:dn managed object property"
    ::= { cfprFlowctrlItemEntry 2 }

cfprFlowctrlItemRn OBJECT-TYPE
    SYNTAX       SnmpAdminString
    MAX-ACCESS   read-only
    STATUS       current
    DESCRIPTION
        "Cisco Firepower flowctrl:Item:rn managed object property"
    ::= { cfprFlowctrlItemEntry 3 }

cfprFlowctrlItemName OBJECT-TYPE
    SYNTAX       SnmpAdminString
    MAX-ACCESS   read-only
    STATUS       current
    DESCRIPTION
        "Cisco Firepower flowctrl:Item:name managed object property"
    ::= { cfprFlowctrlItemEntry 4 }

cfprFlowctrlItemPrio OBJECT-TYPE
    SYNTAX       CfprFlowctrlPriorityPause
    MAX-ACCESS   read-only
    STATUS       current
    DESCRIPTION
        "Cisco Firepower flowctrl:Item:prio managed object property"
    ::= { cfprFlowctrlItemEntry 5 }

cfprFlowctrlItemRcv OBJECT-TYPE
    SYNTAX       CfprFlowctrlFlowControlRx
    MAX-ACCESS   read-only
    STATUS       current
    DESCRIPTION
        "Cisco Firepower flowctrl:Item:rcv managed object property"
    ::= { cfprFlowctrlItemEntry 6 }

cfprFlowctrlItemSnd OBJECT-TYPE
    SYNTAX       CfprFlowctrlFlowControlTx
    MAX-ACCESS   read-only
    STATUS       current
    DESCRIPTION
        "Cisco Firepower flowctrl:Item:snd managed object property"
    ::= { cfprFlowctrlItemEntry 7 }

END
