-- *****************************************************************
-- CISCO-DOT11-CONTEXT-SERVICES-CAPABILITY.my:  Cisco DOT11 CONTEXT 
-- SERVICES MIB CAPABILITIES
--
-- August 2003 -  Parthasarathy Venkatavaradhan,
-- Prasanna Viswakumar
--
-- Copyright (c) 2003 by cisco Systems, Inc.
-- All rights reserved.
--
-- *****************************************************************

CISCO-DOT11-CONTEXT-SERVICES-CAPABILITY DEFINITIONS ::= BEGIN

IMPORTS
        MODULE-IDENTITY
                FROM SNMPv2-SMI
        AGENT-CAPABILITIES
                FROM SNMPv2-CONF
        ciscoAgentCapability
                FROM CISCO-SMI;

cDot11ContextServicesCapability     MODULE-IDENTITY  
        LAST-UPDATED          "200309170000Z"
        ORGANIZATION          "Cisco Systems, Inc."
        CONTACT-INFO
                "             Cisco Systems
                              Customer Service

                              Postal: 170 W Tasman Drive
                              San Jose, CA  95134
                              USA
  
                              Tel: +1 800 553-NETS
 
                              E-mail: cs-dot11@cisco.com"
        DESCRIPTION
                "Agent capabilities for 
                 CISCO-DOT11-CONTEXT-SERVICES-MIB"
        ::= { ciscoAgentCapability 347 }

--********************************************************************
cDot11ContextServicesCapabilityV1   AGENT-CAPABILITIES
    
PRODUCT-RELEASE "Cisco IOS 12.2"
        STATUS          current
        DESCRIPTION     "Cisco Context Services MIB capabilities"

        SUPPORTS        CISCO-DOT11-CONTEXT-SERVICES-MIB
        INCLUDES        { cDot11csConfigGlobalGroup,
                          cDot11csDescendantInGroup,
                          cDot11csMnGroup,
                          cDot11csMIBNotifGroup
                        }   
                           
        VARIATION       cDot11csServiceType
                        ACCESS read-only
                        DESCRIPTION
                                "The values currently supported are
                                 'none' and 'wds'. "
                        
        VARIATION       cDot11csPrimaryRootNodeAddrType
                        ACCESS not-implemented
                        DESCRIPTION
                                "This object is currently not
                                 supported. "

        VARIATION       cDot11csPrimaryRootNodeAddr
                        ACCESS not-implemented
                        DESCRIPTION
                                "This object is currently not 
                                 supported."

        VARIATION       cDot11csSecondaryRootNodeAddrType 
                        ACCESS not-implemented
                        DESCRIPTION
                                "This object is currently not
                                 supported. "

        VARIATION       cDot11csSecondaryRootNodeAddr 
                        ACCESS not-implemented
                        DESCRIPTION
                                "This object is currently not
                                 supported. "

        VARIATION       cDot11csCurrentRootNodeAddr
                        DESCRIPTION
                                "WDS acts as the root in the
                                 current implementation and hence
                                 this object always returns
                                 0.0.0.0. for an active as well as
                                 a backup WDS."

        VARIATION       cDot11csWdsInstanceInterfaceIndex    
                        ACCESS read-only
                        DESCRIPTION
                               "Current implementation supports BVI
                                interfaces only. "

        VARIATION       cDot11csWnsEntityName
                        ACCESS not-implemented
                        DESCRIPTION
                                "This object is currently not
                                 supported. "

	VARIATION	cDot11csWnsSubnetMask 
                        ACCESS not-implemented
                        DESCRIPTION
                                "The Table for cDot11csWnsEntry is
                                 currently not supported. "

        VARIATION       cDot11csWnsRowStatus  
                        ACCESS not-implemented
                        DESCRIPTION
                                "The Table for cDot11csWnsEntry is
                                 currently not supported. "

        VARIATION       cDot11csWnmConfigRowStatus      
                        DESCRIPTION
                                "Current implementation supports
                                 only a single row in the 
                                 cDot11csWnmConfigTable."

        VARIATION       cDot11csStatusAdminStatus
                        ACCESS not-implemented
                        DESCRIPTION
                              "This object is not supported." 


        VARIATION       cDot11csStatusOperStatus
                        ACCESS not-implemented
                        DESCRIPTION
                              "This object is not supported." 


        VARIATION       cDot11csStatusChangeTimeStamp   
                        ACCESS not-implemented
                        DESCRIPTION
                              "This object is not supported." 


        VARIATION       cDot11csStatusInRegistrations
                        ACCESS not-implemented
                        DESCRIPTION
                              "This object is not supported." 

        VARIATION       cDot11csStatusInDeRegistrations
                        ACCESS not-implemented
                        DESCRIPTION
                              "This object is not supported." 

        VARIATION       cDot11csStatusSentAdvts
                        ACCESS not-implemented
                        DESCRIPTION
                              "This object is not supported."

        VARIATION       cDot11csDescendantInCtkRefreshes
                        ACCESS not-implemented
                        DESCRIPTION
                              "This object is not supported." 

       VARIATION       cDot11csMnContextSsid
                        ACCESS not-implemented
                        DESCRIPTION
                              "The Table for CDot11csMnContextEntry 
                              is currently not supported.  "

       VARIATION       cDot11csMnContextSystemName
                        ACCESS not-implemented
                        DESCRIPTION
                              "The Table for CDot11csMnContextEntry 
                              is currently not supported.  "


       VARIATION       cDot11csMnContextUserId
                        ACCESS not-implemented
                        DESCRIPTION
                              "The Table for CDot11csMnContextEntry 
                              is currently not supported.  "


       VARIATION       cDot11csMnContextIpAddressType
                        ACCESS not-implemented
                        DESCRIPTION
                              "The Table for CDot11csMnContextEntry 
                              is currently not supported.   "


       VARIATION       cDot11csMnContextIpAddress
                        ACCESS not-implemented
                        DESCRIPTION
                              "The Table for CDot11csMnContextEntry 
                              is currently not supported.  "


       VARIATION       cDot11csMnParentInIpAddress    
                        ACCESS not-implemented
                        DESCRIPTION
                              "The Table for CDot11csMnContextEntry 
                              is currently not supported.  "

       VARIATION       cDot11csMnRegistrationAge
                        ACCESS not-implemented
                        DESCRIPTION
                              "The Table for CDot11csMnContextEntry 
                              is currently not supported.  "


       VARIATION       cDot11csMnNskExpiryTimeOut
                        ACCESS not-implemented
                        DESCRIPTION
                              "The Table for CDot11csMnContextEntry 
                              is currently not supported.  "

       VARIATION       cDot11csMnCipherNegotiated
                        ACCESS not-implemented
                        DESCRIPTION
                              "The Table for CDot11csMnContextEntry 
                              is currently not supported.  "

        VARIATION       cDot11csElectedAsWdsEnable
                        ACCESS not-implemented
                        DESCRIPTION
                              "Notifications are not supported and
                              and hence this object is not supported."

        VARIATION       cDot11csInRegisteredWithWsEnable
                        ACCESS not-implemented
                        DESCRIPTION
                              "Notifications are not supported and
                              and hence this object is not supported."

        VARIATION       cDot11csInDeRegisteredWithWsEnable
                        ACCESS not-implemented
                        DESCRIPTION
                              "Notifications are not supported and
                              and hence this object is not supported."

        VARIATION       cDot11csElectedAsWds
                        ACCESS not-implemented
                        DESCRIPTION
                              "Notifications are not supported and
                              and hence this object is not supported."

        VARIATION       cDot11csInRegisteredWithWs 
                        ACCESS not-implemented
                        DESCRIPTION
                              "Notifications are not supported and
                              and hence this object is not supported."

        VARIATION       cDot11csInDeRegisteredWithWs
                        ACCESS not-implemented
                        DESCRIPTION
                              "Notifications are not supported and
                              and hence this object is not supported."

::= { cDot11ContextServicesCapability 1 }

END
