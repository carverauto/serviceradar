-- *******************************************************************
-- CISCO-LWAPP-MOBILITY MIB CAPABILITY
--
-- November 18, 2020
--
-- Copyright (c) 2020, 2022 by Cisco Systems, Inc.
-- All rights reserved.
-- *******************************************************************

CISCO-LWAPP-MOBILITY-CAPABILITY DEFINITIONS ::= BEGIN


IMPORTS
       MODULE-IDENTITY
           FROM SNMPv2-SMI
       AGENT-CAPABILITIES
           FROM SNMPv2-CONF
       ciscoAgentCapability
           FROM CISCO-SMI;


ciscoLwappMobilityCapability  MODULE-IDENTITY

       LAST-UPDATED         "202011180000Z"
       ORGANIZATION         "Cisco Systems, Inc."
       CONTACT-INFO
               "Cisco Systems
               Customer Service

               Postal: 170 W Tasman Drive
               San Jose, CA  95134
               USA

               Tel: +1 800 553-NETS

               E-mail: cs-wnbu-snmp@cisco.com"

       DESCRIPTION
               "Agent capabilities for
               CISCO-LWAPP-MOBILITY-MIB "
       REVISION      "202011180000Z"
       DESCRIPTION
               "Initial version of this MIB module. "

   ::= { ciscoAgentCapability 1156 }

ciscoLwappMobilityCapabilityCEV1R0 AGENT-CAPABILITIES

       PRODUCT-RELEASE "Cisco EWLC 1.0"
       STATUS          current
       DESCRIPTION     "CISCO-LWAPP-MOBILITY--MIB capabilities."

       SUPPORTS        CISCO-LWAPP-MOBILITY-MIB
       INCLUDES        {
                           cLMobilityForeignWlcMapTable,
                           cLMobilityMulticastGroupTable,
                           cLMobilityGroupMembersTable,
                           cLMobilityAnchorTable
                       }

       VARIATION       cLMobilityForeignWlcMapEntry
       ACCESS          not-implemented
       DESCRIPTION     "Not supported"

       VARIATION       cLMobilityForeignWlcMapMacAddress
       ACCESS          not-implemented
       DESCRIPTION     "Not supported"

       VARIATION       cLMobilityForeignWlcMapIf
       ACCESS          not-implemented
       DESCRIPTION     "Not supported"

       VARIATION       cLMobilityForeignWlcMapRowStatus
       ACCESS          not-implemented
       DESCRIPTION     "Not supported"

       VARIATION       cLMobilityIncomingCount
       ACCESS          not-implemented
       DESCRIPTION     "Not supported"

       VARIATION       cLMobilityOutgoingCount
       ACCESS          not-implemented
       DESCRIPTION     "Not supported"

       VARIATION       cLMobilityMulticastGroupEntry
       ACCESS          not-implemented
       DESCRIPTION     "Not supported"

       VARIATION       cLMobilityMulticastGroupIPAddressType
       ACCESS          not-implemented
       DESCRIPTION     "Not supported"

       VARIATION       cLMobilityMulticastGroupIPAddress
       ACCESS          not-implemented
       DESCRIPTION     "Not supported"

       VARIATION       cLMobilityGroupMemberControlPathStatusUp
       ACCESS          not-implemented
       DESCRIPTION     "Not supported"

       VARIATION       cLMobilityGroupMemberDataPathStatusUp
       ACCESS          not-implemented
       DESCRIPTION     "Not supported"

       VARIATION       cLMobilityAnchorEntry
       ACCESS          not-implemented
       DESCRIPTION     "Not supported"

       VARIATION       cLMobilityAnchorWlanProfileName
       ACCESS          not-implemented
       DESCRIPTION     "Not supported"

       VARIATION       cLMobilityAnchorSwitchIPAddress
       ACCESS          not-implemented
       DESCRIPTION     "Not supported"

       VARIATION       cLMobilityAnchorStatus
       ACCESS          not-implemented
       DESCRIPTION     "Not supported"

       VARIATION       cLMobilityAnchorRowStatus
       ACCESS          not-implemented
       DESCRIPTION     "Not supported"

       VARIATION       cLMobilityMCMOEnableStatus
       ACCESS          not-implemented
       DESCRIPTION     "Not supported"

       VARIATION       cLMobilityMCMOAdminEnableStatus
       ACCESS          not-implemented
       DESCRIPTION     "Not supported"

       VARIATION       cLMobilityMCEnableStatus
       ACCESS          not-implemented
       DESCRIPTION     "Not supported"

       VARIATION       cLMobilityMCAdminEnableStatus
       ACCESS          not-implemented
       DESCRIPTION     "Not supported"

       VARIATION       cLMobilityMCMulticastMode
       ACCESS          not-implemented
       DESCRIPTION     "Not supported"

       VARIATION       cLMobilityMCMOPublicAddressType
       ACCESS          not-implemented
       DESCRIPTION     "Not supported"

       VARIATION       cLMobilityMCMOPublicAddress
       ACCESS          not-implemented
       DESCRIPTION     "Not supported"

       VARIATION       cLMobilityMCApCountLicensesInUse
       ACCESS          not-implemented
       DESCRIPTION     "Not supported"

       VARIATION       cLMobilityMCMONumberOfClients
       ACCESS          not-implemented
       DESCRIPTION     "Not supported"

       VARIATION       cLMobilityMCNumberOfMCs
       ACCESS          not-implemented
       DESCRIPTION     "Not supported"

       VARIATION       cLMobilityMCTotalNumberOfReportedAPs
       ACCESS          not-implemented
       DESCRIPTION     "Not supported"

       VARIATION       cLMobilityMCNumberOfReportedAPsInSubDomain
       ACCESS          not-implemented
       DESCRIPTION     "Not supported"

       VARIATION       cLMobilityAnchorGroupKeepAliveNumber
       ACCESS          not-implemented
       DESCRIPTION     "Not supported"

       VARIATION       cLMobilityAnchorGroupKeepAliveInterval
       ACCESS          not-implemented
       DESCRIPTION     "Not supported"

       VARIATION       cLMobilityAnchorSmtStatus
       ACCESS          not-implemented
       DESCRIPTION     "Not supported"

       VARIATION       cLMobilityAnchorCurrentSmt
       ACCESS          not-implemented
       DESCRIPTION     "Not supported"

       VARIATION       cLMobilityAnchorDscpValue
       ACCESS          not-implemented
       DESCRIPTION     "Not supported"

       VARIATION       cLMobilityMulticastMessagingEnable
       ACCESS          not-implemented
       DESCRIPTION     "Not supported"

   ::= { ciscoLwappMobilityCapability 1 }

END
