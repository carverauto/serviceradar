-- *****************************************************************
-- ciscoVsiControllerCapability - 
-- AGENT-CAPABILITIES for CISCO-VSI-CONTROLLER-MIB 
--
-- May 2002, Subra Hegde
--
-- Copyright (c) 2002 by cisco Systems, Inc.
-- All rights reserved.
--
-- *****************************************************************

CISCO-VSI-CONTROLLER-CAPABILITY DEFINITIONS ::= BEGIN

IMPORTS
        MODULE-IDENTITY
                FROM SNMPv2-SMI
        AGENT-CAPABILITIES
                FROM SNMPv2-CONF
        DisplayString
                FROM SNMPv2-TC
        ciscoAgentCapability
                FROM CISCO-SMI;   

ciscoVsiControllerCapability MODULE-IDENTITY
    LAST-UPDATED    "200205020000Z"
    ORGANIZATION    "Cisco Systems, Inc."
    CONTACT-INFO  
        "       Cisco Systems

                Customer Service

           Postal: 170 West Tasman Drive
           San Jose, CA  95134
           USA

           Tel: +1 800 553-NETS

          E-mail: cs-wanatm@cisco.com"
    DESCRIPTION
        "Agent capabilities for CISCO-VSI-CONTROLLER-MIB."

    REVISION "200205020000Z"
    DESCRIPTION
        "Initial version of the MIB module."
    ::= { ciscoAgentCapability 9999 }

ciscoVsiControllerCapabilityVR200 AGENT-CAPABILITIES

PRODUCT-RELEASE "MGX8850 Release 2.00."
STATUS          current
DESCRIPTION     "The agent capabilities for 
                CISCO-VSI-CONTROLLER-MIB."

SUPPORTS    CISCO-VSI-CONTROLLER-MIB
INCLUDES    { cvcConfGroup }

VARIATION cvcConfRowStatus
SYNTAX    INTEGER {
                createAndGo(4),
                destroy(6)
          }     
DESCRIPTION
    "Does not support values active(1), notInService(2) and
    createAndWait(5) for write operation."

VARIATION    cvcConfControllerName
SYNTAX       DisplayString (SIZE (0..32)) 
DESCRIPTION
    "Supports limited characters."

    ::= { ciscoVsiControllerCapability 1 } 
 
END
