-- *******************************************************************
-- CISCO-LWAPP-DOT11 MIB CAPABILITY
--   
-- November 18, 2020
--   
-- Copyright (c) 2020, 2022 by Cisco Systems, Inc.
-- All rights reserved.
-- *******************************************************************

CISCO-LWAPP-DOT11-CAPABILITY DEFINITIONS ::= BEGIN

IMPORTS
    MODULE-IDENTITY
        FROM SNMPv2-SMI
    AGENT-CAPABILITIES
        FROM SNMPv2-CONF
    ciscoAgentCapability
        FROM CISCO-SMI;


ciscoLwappDot11Capability MODULE-IDENTITY
    LAST-UPDATED    "202011180000Z"
    ORGANIZATION    "Cisco Systems, Inc."
    CONTACT-INFO
            "Cisco Systems
            Customer Service

            Postal: 170 W Tasman Drive
            San Jose, CA  95134
            USA

            Tel: +1 800 553-NETS

            E-mail: cs-wnbu-snmp@cisco.com"
    DESCRIPTION
        "Agent capabilities for
        CISCO-LWAPP-DOT11-MIB"
    REVISION        "202011180000Z"
    DESCRIPTION
        "Initial version of this MIB module."
    ::= { ciscoAgentCapability 1167 }



ciscoLwappDot11CapabilityCEV1R0 AGENT-CAPABILITIES
    PRODUCT-RELEASE "Cisco EWLC 1.0"
    STATUS          current
    DESCRIPTION
        "CISCO-LWAPP-DOT11--MIB capabilities."

    SUPPORTS        CISCO-LWAPP-DOT11-MIB
    INCLUDES        {
                        cldHtMacOperationsTable,
                        cld11acMcsTable,
                        cldConfiguredCountryTable,
                        cld11nMcsTable
                    }
    VARIATION       cldHtDot11nAmsduEnable
    ACCESS          not-implemented
    DESCRIPTION
        "Not supported"

    VARIATION       cldHtDot11nAmpduEnable
    ACCESS          not-implemented
    DESCRIPTION
        "Not supported"

    VARIATION       cldLoadBalancingTrafficThreshold
    ACCESS          not-implemented
    DESCRIPTION
        "Not supported"

    VARIATION       cldCountryChangeNotifEnable
    ACCESS          not-implemented
    DESCRIPTION
        "Not supported"

    VARIATION       cld11nMcsModulation
    ACCESS          not-implemented
    DESCRIPTION
        "Not supported"

    ::= { ciscoLwappDot11Capability 1 }

END
