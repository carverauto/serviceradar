-- *******************************************************************
-- CISCO-LWAPP-WLAN-POLICY MIB CAPABILITY
--
-- November 18, 2020
--
-- Copyright (c) 2020, 2022 by Cisco Systems, Inc.
-- All rights reserved.
-- *******************************************************************

CISCO-LWAPP-WLAN-POLICY-CAPABILITY DEFINITIONS ::= BEGIN


IMPORTS
       MODULE-IDENTITY
           FROM SNMPv2-SMI
       AGENT-CAPABILITIES
           FROM SNMPv2-CONF
       ciscoAgentCapability
           FROM CISCO-SMI;


ciscoLwappWlanPolicyCapability  MODULE-IDENTITY

       LAST-UPDATED         "202011180000Z"
       ORGANIZATION         "Cisco Systems, Inc."
       CONTACT-INFO
               "Cisco Systems
               Customer Service

               Postal: 170 W Tasman Drive
               San Jose, CA  95134
               USA

               Tel: +1 800 553-NETS

               E-mail: cs-wnbu-snmp@cisco.com"

       DESCRIPTION
               "Agent capabilities for
               CISCO-LWAPP-WLAN-POLICY-MIB "
       REVISION      "202011180000Z"
       DESCRIPTION
               "Initial version of this MIB module. "

   ::= { ciscoAgentCapability 1169 }

ciscoLwappWlanPolicyCapabilityCEV1R0 AGENT-CAPABILITIES

       PRODUCT-RELEASE "Cisco EWLC 1.0"
       STATUS          current
       DESCRIPTION     "CISCO-LWAPP-WLAN-POLICY--MIB capabilities."

       SUPPORTS        CISCO-LWAPP-WLAN-POLICY-MIB
       INCLUDES        {
                           cLWlanPolicyConfigTable
                       }

       VARIATION       cLWlanPolicyNativeProfiling
       ACCESS          not-implemented
       DESCRIPTION     "Not supported"

       VARIATION       cLWlanPolicyNetflowIPv4InputMonitorName
       ACCESS          not-implemented
       DESCRIPTION     "Not supported"

       VARIATION       cLWlanPolicyNetflowIPv4OutputMonitorName
       ACCESS          not-implemented
       DESCRIPTION     "Not supported"

       VARIATION       cLWlanPolicyNetflowIPv6InputMonitorName
       ACCESS          not-implemented
       DESCRIPTION     "Not supported"

       VARIATION       cLWlanPolicyNetflowIPv6OutputMonitorName
       ACCESS          not-implemented
       DESCRIPTION     "Not supported"

   ::= { ciscoLwappWlanPolicyCapability 1 }

END
