-- *******************************************************************
-- CISCO-GPRS-ACC-PT-MIB.my: GPRS access point management MIB
--   
-- Dec 1999, Huiyang Yang
-- Oct 2007, 2008 Annie Mishalini Devasahayam
--   
-- Copyright (c) 1999-2012 by Cisco Systems Inc.
--   
-- All rights reserved.
-- *****************************************************************

CISCO-GPRS-ACC-PT-MIB DEFINITIONS ::= BEGIN

IMPORTS
    MODULE-IDENTITY,
    OBJECT-TYPE,
    NOTIFICATION-TYPE,
    Integer32,
    Gauge32,
    IpAddress,
    Counter32,
    Counter64,
    Unsigned32
        FROM SNMPv2-SMI
    MODULE-COMPLIANCE,
    OBJECT-GROUP,
    NOTIFICATION-GROUP
        FROM SNMPv2-CONF
    TEXTUAL-CONVENTION,
    TruthValue,
    RowStatus,
    DisplayString
        FROM SNMPv2-TC
    SnmpAdminString
        FROM SNMP-FRAMEWORK-MIB
    InetAddressType,
    InetAddress,
    InetPortNumber
        FROM INET-ADDRESS-MIB
    InterfaceIndexOrZero,
    CiscoInetAddressMask
        FROM CISCO-TC
    ciscoMgmt
        FROM CISCO-SMI;


ciscoGprsAccPtMIB MODULE-IDENTITY
    LAST-UPDATED    "201204040000Z"
    ORGANIZATION    "Cisco Systems, Inc."
    CONTACT-INFO
            "Cisco Systems
            Customer Service

            Postal: 170 W Tasman Drive
            San Jose, CA  95134
            USA

            Tel: +1 800 553-NETS

            E-mail: cs-gprs@cisco.com"
    DESCRIPTION
        "This MIB module supports access point configuration
        for GGSN in a GPRS system. GPRS [1] is a GSM network 
        providing mobile wireless data communication services.

        GGSN is the Gateway GPRS Support Node in the GPRS
        architecture. It provides interworking with external 
        packet-switched networks - PDNs or other data networks. 

        GGSN is a software extension of a router.

        A GGSN provides data access for its mobile subscribers 
        to parts of the data network identified by the list of 
        APNs configured on the node. 

        The following diagram illustrates the network 
        elements in a GPRS network, and the interfaces 
        between them: 

            +=====+    +======+      +======+      +=====+ 
            | BSS |----| SGSN |--Gn--| GGSN |--Gi--| PDN |
            +=====+    +======+      +======+      +=====+ 
               ^                         ^
              /|\                       /|\
               |                         |
               | Visited access      +--------+
               | provider network    | Access |
               |                     | point  |
              \|/                    | table  |
               V                     +--------+
            +=====+
            | MS  |
            +=====+

        Access points must be configured on the GGSN.
        The Access Point Name is defined in GSM 03.03 [2] and 
        consists of two parts, the APN Network Identifier and 
        the APN Operator Identifier (more details in the 
        object description in this MIB module). The 
        cgprsAccPtTable contains the list of APNs supported 
        by this GGSN and a set of engineering parameters that 
        define the access point's operation. 

        This MIB is also supported in the Evolved Packet
        Core(EPC) architecture. The details of this architecture
        is discussed in CISCO-EPC-GATEWAY-MIB description. Hence,
        the MIB will be supported by GGSN Gateway, PDN Gateway(PGW),
        Serving Gateway(SGW) and a combined PGW and SGW Gateway
        SPGW(SGW PGW Gateway).

        Acronyms and terms:

            3GPP   3rd Generation Partnership Project

            APN    Access Point Name

            BSS    Base Station Subsystem

            CAC    Call Admission Control

            COA    Change of Authorization

            CSG2   Content Service Gateway Release 2

            ETSI   European Telecommunications Standards 
                   Institute 

            Gi     Name of the Interface between GGSN and PDN

            Gn     Name of the Interface between GGSN and SGSN

            GGSN   Gateway GPRS Support Node

            GPRS   General Packet Radio Service 

            GSM    Global System for Mobile communication

            Gx     Dynamic Charging and Policy Interface

            IMS    IP Multimedia Subsystem

            MME    Mobility Management Entity

            MS     Mobile Station

            P-CSCF Proxy Call Session Control Function

            PCO    Protocol Config Options

            PDF    Policy Decision Function

            PDN    Public Data Network 

            PDP    Packet Data Protocol         

            PLMN   Public Land Mobile Network

            QOS    Quality Of Service

            SGSN   Serving GPRS support Node

            UE     User Equipment

            VPN    Virtual Private Network

            VRF    VPN Routing and Forwarding

        REFERENCE

        [1] GSM 03.60: Digital cellular telecommunications 
            system (Phase 2+); General Packet Radio Service 
            (GPRS); Service description; Stage 2.

        [2] GSM 03.03: Digital cellular telecommunication 
            system (Phase 2+); General Packet Radio Service 
            (GPRS); Service description; Stage 1."
    REVISION        "201204040000Z"
    DESCRIPTION
        "The following changes have been made.

        [1] The following objects have been added
            to cgprsAccPtStatisticsTable.          

             cgprsAccPtFailMsActivatedPdps,
             cgprsAccPtFailPdpUpdate,
             cgprsAccPtUpdateRspTimeOut       

        [2] Added cgprsAccPtStatisticsGroupSup6 group.

        [3] Deprecated cgprsAccPtMIBComplianceRev14 and 
            replaced it with cgprsAccPtMIBComplianceRev15."
    REVISION        "201109220000Z"
    DESCRIPTION
        "The following changes have been made.

        [1] The following objects have been added
            to cgprsAccPtStatisticsTable.          

            cgprsAccPtIpv4v6MsActivatedDynamicPdps,
            cgprsAccPtIpv4v6MsSuccActivatedDynamicPdps.

        [2] Added cgprsAccPtStatisticsGroupSup5 group.

        [3] Deprecated cgprsAccPtMIBComplianceRev13 and 
            replaced it with cgprsAccPtMIBComplianceRev14."
    REVISION        "201103140000Z"
    DESCRIPTION
        "The following changes have been made.

        [1] The following objects has been added
            to cgprsAccPtStatisticsTable.

            cgprsAccPtActiveBearers,
            cgprsAccPtDhcpProxServTxErrDrops,
            cgprsAccPtDhcpProxServIpAllocErr,
            cgprsAccPtDedBearerDeactivations,
            cgprsAccPtDedBearerQosUpdate,
            cgprsAccPtDedBearerSucQosUpdate,
            cgprsAccPtDedBearerNoQosUpdate,
            cgprsAccPtDedBearerSucNoQosUpdate.

        [2] Added table cgprsAccPtDhcpv6ProxyStatsTable which
            includes the following objects.

            cgprsAccPtDhcpv6ProxInforeqRcvd,
            cgprsAccPtDhcpv6ProxInforeqRply,
            cgprsAccPtDhcpv6ProxInforeqLocRply,
            cgprsAccPtDhcpv6ProxIpAllocSuc,
            cgprsAccPtDhcpv6ProxIpAllocFail,
            cgprsAccPtDhcpv6ProxIpRelease,
            cgprsAccPtDhcpv6ProxIpRenewFail,
            cgprsAccPtDhcpv6ProxUnkwnMsg,
            cgprsAccPtDhcpv6ProxErrs.  

        [3] The following objects has been added
            to cgprsAccPtExtTable.   

            cgprsAccPtVerifyDownlinkAddr.

        [4] The following objects has been added
            to cgprsAccPtIpv6Table.

            cgprsAccPtDhcpv6ProxClientIntf,
            cgprsAccptDhcpv6RapidCommit,
            cgprsAccptDhcpv6PoolName.            

        [5] Modified the description for the following
            objects to extend Bearer support to the MIB.

            cgprsAccPtTable,
            cgprsAccPtEntry,
            cgprsAccPtIndex,
            cgprsAccPtMode,
            cgprsAccPtIpAddressPool,
            cgprsAccPtDHCPGwAddr,
            cgprsAccPtIPAccListGroupIn,
            cgprsAccPtIPAccListGroupOut,
            cgprsAccPtNetworkInitiated,
            cgprsAccPtIpAddrAllocations,
            cgprsAccPtIdlePdpPurgeTimer,
            cgprsAccPtMsIsdnSuppressed,
            cgprsAccPtType,
            cgprsAccPtPppRegenEnable,
            cgprsAccPtPppRegenMaxSessions,
            cgprsAccPtPcscfServerGroupName,
            cgprsAccPtAggregTable,
            cgprsAccPtAggregEntry,
            cgprsAccPtGtpRespMesgWaitAcctng,
            cgprsAccPtInterimAccountinEnable,
            cgprsAccPtVerifyUpStrTpduSrcAddr,
            cgprsAccPtVerifyUpStrTpduDstAddr,
            cgprsAccPtRedirInterMobilAddr,
            cgprsAccPtSuppressRadiusAttribs,
            cgprsAccPtSetRadiusAttributes,
            cgprsAccPtOperationMode,
            cgprsAccPtAbsoluteSessionTimer,
            cgprsAccPtRadiusAttrNasId,
            cgprsAccPtPdpInServicePolicyName,
            cgprsAccPtPdpOutServicePolicyNam,
            cgprsAccPtAdvDownlinkNextHopAddr,
            cgprsAccPtGtpUpdateFailDelete,
            cgprsAccPtAaaAccountInterPeriod,
            cgprsAccPtAaaAccountInterRadius,
            cgprsAccPtPcscfLoadBalance,
            cgprsAccPtNetworkBehindMsEnable,
            cgprsAccPtChargingRecordType,
            cgprsAccPtImsConfigTable,
            cgprsAccPtChgProfTable,
            cgprsAccPtMsType,
            cgprsAccPtChgProfOverride,
            cgprsAccPtCacTable,
            cgprsAccPtCacPolicyName,
            cgprsAccPtCacUpStrBandWidthPool,
            cgprsAccPtRouteProbeTable,
            cgprsAccPtIpv6Table,
            cgprsAccPtIpv6BaseVTemplate,
            cgprsAccPtIpv6Enable,
            cgprsAccPtIpv6Exclusive,
            cgprsAccPtIpv6AddrPool,
            cgprsAccPtIpv6Redirect,
            cgprsAccPtIpv6SecurityVerifySrc,
            cgprsAccPtIpv6SecurityVerifyDst,
            cgprsAccPtCfgNotifIndex,
            cgprsAccPtStatisticsTable,
            cgprsAccPtMsActivatedPdps,
            cgprsAccPtSuccMsActivatedPdps,
            cgprsAccPtMsActivatedDynPdps,
            cgprsAccPtSuccMsActivatedDynPdps,
            cgprsAccPtMsDeactivatedPdps,
            cgprsAccPtSuccMsDeactivatedPdps,
            cgprsAccPtNetworkInitPdps,
            cgprsAccPtSuccNetworkInitPdps,
            cgprsAccPtGgsnDeactivatedPdps,
            cgprsAccPtSuccGgsDeactivatedPdps,
            cgprsAccPtActivePdps,
            cgprsAccPtDhcpAddrRequests,
            cgprsAccPtSuccDhcpAddrRequests,
            cgprsAccPtDhcpAddrReleases,
            cgprsAccPtIpv6MsActivatedPdps,
            cgprsAccPtIpv6MsSuccActivatedPdps,
            cgprsAccPtIpv6NetworkInitDeactPdps,
            cgprsAccPtIpv6NetworkInitDeactSuccPdps,
            cgprsAccPtIpv6MsActivatedDynPdps,
            cgprsAccPtIpv6MsSuccActivatedDynPdps,
            cgprsAccPtIpv6MsDeactivatedPdps,
            cgprsAccPtIpv6MsSuccDeactivatedPdps,
            cgprsAccPtIpv6GgsnDeactivatedPdps,
            cgprsAccPtIpv6GgsnSuccDeactivatedPdps,
            cgprsAccPtPdpUpdateReqSent,
            cgprsAccPtSuccPdpUpdateResRcvd,
            cgprsAccPtCoaSuccess,
            cgprsAccPtDtEnabled,
            cgprsAccPtTotalBearers,
            cgprsAccPtTotRmtInitCreateBearers,
            cgprsAccPtSuccRmtInitCreateBearers,
            cgprsAccPtNetworkInitDeleteBearers,
            cgprsAccPtTotRmtInitModifyBearers,
            cgprsAccPtSuccRmtInitModifyBearers,
            cgprsAccPtTotNetworkInitUpdateBearers,
            cgprsAccPtSuccNetworkInitUpdateBearers,
            cgprsAccPtTotNetworkInitCreateDedBearers,
            cgprsAccPtSuccNetworkInitCreateDedBearers,
            cgprsAccPtTotNetworkInitCreateIPv6DedBearers,
            cgprsAccPtSuccNetworkInitCreateIPv6DedBearers,
            cgprsAccPtv4v6MsActivatedPdps,
            cgprsAccPtv4v6SuccMsActivatedPdps,
            cgprsAccPtv4v6MsDeactivatedPdps,
            cgprsAccPtv4v6SuccMsDeactivatedPdps,
            cgprsAccPtv4v6ActDedbearerPdps,
            cgprsAccPtv4v6SuccActDedbearerPdps,
            cgprsAccPtDhcpProxServRelease,
            cgprsAccPtDhcpProxServOffer,
            cgprsAccPtDhcpProxServAcks,
            cgprsAccPtDhcpProxServNaks,
            cgprsAccPtDhcpProxServInform,
            cgprsAccPtDhcpProxServUnknowMsg,
            cgprsAccPtDhcpProxServRetryDrops,
            cgprsAccPtDhcpProxServErrDrops,
            cgprsAccPtThruputStatsTable,
            cgprsAccPtRouteProbeGroup,
            cgprsAccPtIpv6Group.

        [6] Added the following groups
            cgprsAccPtExtMIBGroupSup2,
            cgprsAccPtDhcpv6ProxyStatsGroup,
            cgprsAccPtStatisticsGroupSup4. 

        [7] Deprecated MODULE-COMPLIANCE
            cgprsAccPtMIBComplianceRev12 and is superceded by
            cgprsAccPtMIBComplianceRev13."
    REVISION        "201004290000Z"
    DESCRIPTION
        "The following changes have been made.

        [1] The following objects has been added
            to cgprsAccPtStatisticsTable.

            cgprsAccPtv4v6MsActivatedPdps,                             
            cgprsAccPtv4v6SuccMsActivatedPdps,            
            cgprsAccPtv4v6MsDeactivatedPdps,               
            cgprsAccPtv4v6SuccMsDeactivatedPdps,
            cgprsAccPtv4v6SuccActDedbearerPdps,           
            cgprsAccPtv4v6SuccActDedbearerPdps,
            cgprsAccPtDhcpProxServDiscover,
            cgprsAccPtDhcpProxServRequest,
            cgprsAccPtDhcpProxServDeclines,
            cgprsAccPtDhcpProxServRelease,
            cgprsAccPtDhcpProxServOffer,
            cgprsAccPtDhcpProxServAcks,
            cgprsAccPtDhcpProxServNaks,
            cgprsAccPtDhcpProxServInform,
            cgprsAccPtDhcpProxServUnknowMsg,
            cgprsAccPtDhcpProxServRetryDrops,
            cgprsAccPtDhcpProxServErrDrops

        [2] The following objects has been added
            to cgprsAccPtExtTable.

            cgprsAccPtDualAddrEnabled

        [3] The following objects has been added 
            to cgprsAccPtIpv6Table.

            cgprsAccPtIpv6AddrAllocations

        [4] Added group cgprsAccPtStatisticsGroupSup3, which
            deprecates cgprsAccPtStatisticsGroupSup2.

        [5] Added new group cgprsAccPtMIBGroupSup1.

        [6] Deprecated MODULE-COMPLIANCE
            cgprsAccPtMIBComplianceRev11 and is superceded by
            cgprsAccPtMIBComplianceRev12."
    REVISION        "201004022000Z"
    DESCRIPTION
        "The following changes have been made.

        [1] The following objects has been added
            to cgprsAccPtStatisticsTable.

            cgprsAccPtTotalBearers,
            cgprsAccPtTotRmtInitCreateBearers,
            cgprsAccPtSuccRmtInitCreateBearers,
            cgprsAccPtNetworkInitDeleteBearers,
            cgprsAccPtTotNetworkInitUpdateBearers,
            cgprsAccPtSuccNetworkInitUpdateBearers,
            cgprsAccPtTotNetworkInitCreateDedBearers,
            cgprsAccPtSuccNetworkInitCreateDedBearers,
            cgprsAccPtTotRmtInitModifyBearers,
            cgprsAccPtSuccRmtInitModifyBearers,
            cgprsAccPtTotNetworkInitCreateIPv6DedBearers,
            cgprsAccPtSuccNetworkInitCreateIPv6DedBearers

        [2] The following objects has been added
            to cgprsAccPtExtTable.

            cgprsAccPtChargingRecordType,
            cgprsAccPtChargingGrp,
            cgprsAccPtIpAddrPoolNoRedistribute

        [3] The following object has been added to 
            cgprsAccPtAggregTable.

            cgprsAccPtAggregCsgGroup

        [4] Added cgprsAccPtCsgGroupTable to ciscoGprsAccPtConfig.

        [5] Added group cgprsAccPtStatisticsGroupSup2, which
            deprecates cgprsAccPtStatisticsGroupSup1.

        [6] Added group cgprsAccPtMIBR90GroupRev1, which
            deprecates cgprsAccPtMIBR90Group.

        [7] Added new group cgprsAccPtMIBR92Group.  

        [8] Added new group cgprsAccPtMIBR100Group.   

        [9] Deprecated MODULE-COMPLIANCE
            cgprsAccPtMIBComplianceRev10 and is superceded by
            cgprsAccPtMIBComplianceRev11."
    REVISION        "200812190000Z"
    DESCRIPTION
        "Added cgprsAccPtGxEnable,
        cgprsAccPtPcscfLoadBalance,
        cgprsAccPtNetworkBehindMsEnable,
        cgprsAccPtMaxSubnetsBehindMobile to
        cgprsAccPtExtTable."
    REVISION        "200803030000Z"
    DESCRIPTION
        "Added cgprsAccPtAaaAccountInterRadius to
        cgprsAccPtExtTable."
    REVISION        "200802270000Z"
    DESCRIPTION
        "Added cgprsAccPtGtpUpdateFailDelete,
        cgprsAccPtAaaAccountInterPeriod to
        cgprsAccPtExtTable.

        Added cgprsAccPtPdpUpdateReqSent,
        cgprsAccPtSuccPdpUpdateResRcvd,
        cgprsAccPtCoaRcvd,
        cgprsAccPtCoaSuccess,
        cgprsAccPtDtEnabled to
        cgprsAccPtStatisticsTable."
    REVISION        "200608300000Z"
    DESCRIPTION
        "Deprecated cgprsAccPtImsConfigTable, as IMS is
        not supported from GGSN release 5.0 onwards.

        Added cgprsAccPtPcscfServerGroupName to 
        cgprsAccPtTable."
    REVISION        "200605181300Z"
    DESCRIPTION
        "Added cgprsAccPtIpv6Configs to ciscoGprsAccPtConfig.

        Added following objects to cgprsAccPtStatisticsTable:
         cgprsAccPtIpv6MsActivatedPdps,
         cgprsAccPtIpv6MsSuccActivatedPdps,
         cgprsAccPtIpv6NetworkInitDeactPdps,
         cgprsAccPtIpv6NetworkInitDeactSuccPdps,
         cgprsAccPtIpv6MsActivatedDynPdps,
         cgprsAccPtIpv6MsSuccActivatedDynPdps,
         cgprsAccPtIpv6MsDeactivatedPdps,
         cgprsAccPtIpv6MsSuccDeactivatedPdps,
         cgprsAccPtIpv6GgsnDeactivatedPdps,
         cgprsAccPtIpv6GgsnSuccDeactivatedPdps,
         cgprsAccPtIpv6UpstreamTrafficVolume,
         cgprsAccPtIpv6DownstreamTrafficVolume,
         cgprsAccPtIpv6UpstreamPackets,
         cgprsAccPtIpv6DownstreamPackets."
    REVISION        "200511221400Z"
    DESCRIPTION
        "Changed the range of cgprsAccPtName and
        cgprsAccPtMsIsdnSuppressedValue."
    REVISION        "200510281700Z"
    DESCRIPTION
        "Modified the description for the object
        cgprsAccPtName.

        Modified the description for the object
        cgprsAccPtChgProfile.

        Added new value to the object
        cgprsAccPtType.

        Added new objects cgprsAccPtServiceAware,
        cgprsAccPtAdvDownlinkNextHopAddrType,
        cgprsAccPtAdvDownlinkNextHopAddr to 
        cgprsAccPtExtTable."
    REVISION        "200407260200Z"
    DESCRIPTION
        "Modified the description for the object
        cgprsAccPtChgProfile."
    REVISION        "200402112000Z"
    DESCRIPTION
        "+ Added cgprsAccPtInterimAccountinEnable,
        cgprsAccPtSetRadiusAttributes,
        cgprsAccPtOperationMode,
        cgprsAccPtAbsoluteSessionTimer,
        cgprsAccPtRadiusAttrNasId,
        cgprsAccPtPdpInServicePolicyName,
        cgprsAccPtPdpOutServicePolicyNam,
        cgprsAccPtPppRegenVerifyDomain,
        cgprsAccPtIpAddrLocalPoolName to cgprsAccPtExtTable.

        + Added cgprsAccPtGenServerConfigs,
        cgprsAccPtImsConfigs, cgprsAccPtChargingParams,
        cgprsAccPtCacConfigs, cgprsAccPtRouteProbeConfigs to
        ciscoGprsAccPtConfig.

        + Added cgprsAccPtThruputStatsTable to
        ciscoGprsAccPtStatistics.

        + Added cgprsAccPtRevUpstreamTrafficVol,
        cgprsAccPtRevDownstrTrafficVol,
        cgprsAccPtUpstreamPacketCount,
        cgprsAccPtDownstreamPacketCount,
        cgprsAccPtDhcpAddrRequests,
        cgprsAccPtSuccDhcpAddrRequests,
        cgprsAccPtDhcpAddrReleases to
        cgprsAccPtStatisticsTable.

        + Added cgprsAccPtSecSrcViolNotif,
        cgprsAccPtSecDestViolNotif,
        cgprsAccPtMaintenanceNotif and 
        cgprsAccPtInServiceNotif to
        cgprsAccPtMIBNotifications.

        + Deprecated cgprsAccPtUpstreamTrafficVol,
        cgprsAccPtDownstreamTrafficVol."
    REVISION        "200208261800Z"
    DESCRIPTION
        "+ Added cgprsAccPtSuppressRadiusAttribs to
        cgprsAccPtExtTable.
        + Deprecated cgprsAccPtImsiSuppressed."
    REVISION        "200206131800Z"
    DESCRIPTION
        "+ Added cgprsAccPtImsiSuppressed,
        cgprsAccPtVerifyUpStrTpduSrcAddr,
        cgprsAccPtVerifyUpStrTpduDstAddr,
        cgprsAccPtRedirInterMobilAddrTyp,
        cgprsAccPtRedirInterMobilAddr to cgprsAccPtExtTable.
        + Added cgprsAccPtSourceAddrViolTpdus,
        cgprsAccPtDestAddrViolTpdus,
        cgprsAccPtRedirInterMobilTraffic to 
        cgprsAccPtStatisticsTable.
        + Updated the DESCRIPTION and DEFVAL of 
        cgprsAccPtPppRegenMaxSessions.
        + Updated the DESCRIPTION of 
        cgprsAccPtMsIsdnSuppressed."
    REVISION        "200112281430Z"
    DESCRIPTION
        "+ Added cgprsAccPtExtTable.
        + Added cgprsAccPtType, cgprsAccPtVrfName,
          cgprsAccPtDhcpAddrSpace,
          cgprsAccPtPppRegenEnable, 
          cgprsAccPtPppRegenMaxSessions,
          cgprsAccPtPppRegenSetupTime, 
          cgprsAccPtAutoAggregation.
        + Added objects for performance data measurements
          related to GGSN.
        + Added cgprsAccPtIdlePdpPurgeTimer, 
          cgprsAccPtBlockMsRoaming,
          cgprsAccPtAnonymousUserName, 
          cgprsAccPtAnonymousUserPassword
          cgprsAccPtMsIsdnSuppressed, 
          cgprsAccPtMsIsdnSuppressedValue,
          cgprsAccPtAaaAuthServerGroup,
          cgprsAccPtAaaAccountServerGroup,
          cgprsAccPtAaaAccountingEnable.
        + Deprecated cgprsAccPtUsers, cgprsAccPtRadiusServerPri
          and cgprsAccPtRadiusServerSec."
    REVISION        "200007210000Z"
    DESCRIPTION
        "Initial version of this MIB module."
    ::= { ciscoMgmt 183 }



AccessControlListId ::= TEXTUAL-CONVENTION
    STATUS          current
    DESCRIPTION
        "Access Control List (ACL) specifies criteria by
        which packets are evaluated as matching or
        non-matching. The ACL also specifies an action
        which is applied to packets which match.
        Objects which use this textual convention identify
        ACLs. 

        ACLs are configured/defined outside the scope of 
        this MIB. The value of an object with this syntax 
        associates to an ACL with the same ACL number."
    SYNTAX          Integer32 (1..2699)

AccessControlListOrZero ::= TEXTUAL-CONVENTION
    STATUS          current
    DESCRIPTION
        "Access Control List (ACL) specifies criteria by
        which packets are evaluated as matching or
        non-matching. The ACL also specifies an action
        which is applied to packets which match.
        Objects which use this textual convention identify
        ACLs.

        ACLs are configured/defined outside the scope of
        this MIB. The value of an object with this syntax
        associates to an ACL with the same ACL number.

        A value of zero indicates no ACL is configured."
    SYNTAX          Integer32 (0..199 | 1300..2699)

AccessControlListName ::= TEXTUAL-CONVENTION
    STATUS          current
    DESCRIPTION
        "Access Control List (ACL) specifies the criteria by
        which packets are evaluated as matching or
        non-matching. The ACL also specifies an action,
        which is applied to packets which match.
        Objects which use this textual convention identify
        ACLs.

        ACLs are configured/defined outside the scope of
        this MIB. The name of an object with this syntax
        associates to an ACL with the same ACL name."
    SYNTAX          OCTET STRING (SIZE (0..255))
-- Object Definitions

ciscoGprsAccPtMIBObjects  OBJECT IDENTIFIER
    ::= { ciscoGprsAccPtMIB 1 }

ciscoGprsAccPtConfig  OBJECT IDENTIFIER
    ::= { ciscoGprsAccPtMIBObjects 1 }

ciscoGprsAccPtCfgNotifInfo  OBJECT IDENTIFIER
    ::= { ciscoGprsAccPtMIBObjects 2 }

ciscoGprsAccPtStatistics  OBJECT IDENTIFIER
    ::= { ciscoGprsAccPtMIBObjects 3 }

ciscoGprsAccPtNotifInfo  OBJECT IDENTIFIER
    ::= { ciscoGprsAccPtMIBObjects 4 }

-- *********************************************************************
-- Access Point Table
-- *********************************************************************

cgprsAccPtTable OBJECT-TYPE
    SYNTAX          SEQUENCE OF CgprsAccPtEntry 
    MAX-ACCESS      not-accessible
    STATUS          current
    DESCRIPTION
        "This table contains a list of access points configured
        on this Gateway."
    ::= { ciscoGprsAccPtConfig 1 }

cgprsAccPtEntry OBJECT-TYPE
    SYNTAX          CgprsAccPtEntry
    MAX-ACCESS      not-accessible
    STATUS          current
    DESCRIPTION
        "A description of an access point. Access point
        parameters cannot be changed when active PDP's or
        Bearer's exists on the Gateway."
    INDEX           { cgprsAccPtIndex } 
    ::= { cgprsAccPtTable 1 }

CgprsAccPtEntry ::= SEQUENCE {
        cgprsAccPtIndex                 Unsigned32,
        cgprsAccPtRowStatus             RowStatus,
        cgprsAccPtName                  SnmpAdminString,
        cgprsAccPtMode                  INTEGER,
        cgprsAccPtIpAddressPool         INTEGER,
        cgprsAccPtDHCPServerPri         IpAddress,
        cgprsAccPtDHCPServerSec         IpAddress,
        cgprsAccPtDHCPGwAddr            IpAddress,
        cgprsAccPtRadiusServerPri       IpAddress,
        cgprsAccPtRadiusServerSec       IpAddress,
        cgprsAccPtIPAccListGroupIn      AccessControlListId,
        cgprsAccPtIPAccListGroupOut     AccessControlListId,
        cgprsAccPtIfIndex               InterfaceIndexOrZero,
        cgprsAccPtIfNextHop             IpAddress,
        cgprsAccPtAccessViolation       INTEGER,
        cgprsAccPtSubrRequired          TruthValue,
        cgprsAccPtNetworkInitiated      TruthValue,
        cgprsAccPtIpAddrAllocations     Gauge32,
        cgprsAccPtUsers                 Gauge32,
        cgprsAccPtIdlePdpPurgeTimer     Unsigned32,
        cgprsAccPtBlockMsRoaming        TruthValue,
        cgprsAccPtAnonymousUserName     SnmpAdminString,
        cgprsAccPtAnonymousUserPassword SnmpAdminString,
        cgprsAccPtMsIsdnSuppressed      TruthValue,
        cgprsAccPtMsIsdnSuppressedValue DisplayString,
        cgprsAccPtAaaAuthServerGroup    SnmpAdminString,
        cgprsAccPtAaaAccountServerGroup SnmpAdminString,
        cgprsAccPtAaaAccountingEnable   TruthValue,
        cgprsAccPtType                  INTEGER,
        cgprsAccPtVrfName               SnmpAdminString,
        cgprsAccPtDhcpAddrSpace         INTEGER,
        cgprsAccPtPppRegenEnable        TruthValue,
        cgprsAccPtPppRegenMaxSessions   Integer32,
        cgprsAccPtPppRegenSetupTime     Integer32,
        cgprsAccPtAutoAggregation       TruthValue,
        cgprsAccPtPcscfServerGroupName  SnmpAdminString
}

cgprsAccPtIndex OBJECT-TYPE
    SYNTAX          Unsigned32 (1..65535)
    MAX-ACCESS      not-accessible
    STATUS          current
    DESCRIPTION
        "A locally unique identifier for this access point on
        this Gateway." 
    ::= { cgprsAccPtEntry 1 }

cgprsAccPtRowStatus OBJECT-TYPE
    SYNTAX          RowStatus
    MAX-ACCESS      read-create
    STATUS          current
    DESCRIPTION
        "This object is used to create or delete conceptual
        row in this table.

        To create a row, set this object to 'createAndGo'.
        There are no mandatory objects in a create request.

        To delete a row, set this object to 'destroy'." 
    ::= { cgprsAccPtEntry 2 }

cgprsAccPtName OBJECT-TYPE
    SYNTAX          SnmpAdminString (SIZE  (0..100))
    MAX-ACCESS      read-create
    STATUS          current
    DESCRIPTION
        "The Access Point Name. It is composed of two parts:

        - The APN Network Identifier is mandatory and is a 
          fully qualified domain name according to the DNS
          naming conventions, e.g., 'company.com.'. 

        - The APN Operator Identifier is optional. It is a
          fully qualified domain name according to the DNS
          naming convention, and consists of three labels,
          the last of which must be '.gprs'. For example, 
          'mncyyyy.mcczzzz.gprs'.

        An example of a full APN name with both the Network
        and operator identifiers is 
        'company.com.mncyyyy.mcczzzz.gprs'."
    REFERENCE
        "GSM 03.03: Digital cellular telecommunication system 
        (Phase 2+); General Packet Radio Service (GPRS); 
        Service description; Stage 1."
    DEFVAL          { ''H } 
    ::= { cgprsAccPtEntry 3 }

cgprsAccPtMode OBJECT-TYPE
    SYNTAX          INTEGER  {
                        transparent(1),
                        nontransparent(2)
                    }
    MAX-ACCESS      read-create
    STATUS          current
    DESCRIPTION
        "Specifies the type of access allowed to the PDN
        through this access point.

            - 'transparent', indicates that users can access 
            without authentication.

            - 'nontransparent', indicates that users must 
            be authenticated by the Gateway."
    DEFVAL          { transparent } 
    ::= { cgprsAccPtEntry 4 }

cgprsAccPtIpAddressPool OBJECT-TYPE
    SYNTAX          INTEGER  {
                        global(1),
                        dhcp(2),
                        radius(3),
                        disable(4),
                        local(5)
                    }
    MAX-ACCESS      read-create
    STATUS          current
    DESCRIPTION
        "Specifies a dynamic address allocation method for
        this access point.

            - 'global', which indicates that no method is 
            defined specifically to this access point and the 
            DHCP or radius server configured for this Gateway 
            'globally' will be used to allocation a dynamic IP 
            address to the user. 

            - 'dhcp', which indicates that the DHCP server 
            will be used.

            - 'radius', which indicates that the radius server
            will be used.

            - 'disable', which indicates that dynamic address 
            allocation is disabled.

            - 'local', indicates that local address pool
            configured on the Gateway is going to be used.
            cgprsAccPtIpAddrLocalPoolName denotes the name
            of the corresponding address pool."
    DEFVAL          { global } 
    ::= { cgprsAccPtEntry 5 }

cgprsAccPtDHCPServerPri OBJECT-TYPE
    SYNTAX          IpAddress
    MAX-ACCESS      read-create
    STATUS          current
    DESCRIPTION
        "This object specifies the IP address of the primary
        DHCP server from which a mobile subscriber can request
        an IP address assignment for the access of this APN.

        In case this DHCP server is not available, the 
        secondary DHCP server is used." 
    ::= { cgprsAccPtEntry 6 }

cgprsAccPtDHCPServerSec OBJECT-TYPE
    SYNTAX          IpAddress
    MAX-ACCESS      read-create
    STATUS          current
    DESCRIPTION
        "The IP address of the secondary DHCP server.

        The secondary DHCP server is used if the primary
        DHCP server is not available. This object can be
        set after configuring primary DHCP server." 
    ::= { cgprsAccPtEntry 7 }

cgprsAccPtDHCPGwAddr OBJECT-TYPE
    SYNTAX          IpAddress
    MAX-ACCESS      read-create
    STATUS          current
    DESCRIPTION
        "This object specifies the DHCP Gateway address that
        is used in the 'giaddr' field of the DHCP request. 
        It is used by DHCP to determine from which pool the 
        IP address will be allocated. 

        If no DHCP Gateway is specified, the IP address 
        associated with the Gn interface is used." 
    ::= { cgprsAccPtEntry 8 }

cgprsAccPtRadiusServerPri OBJECT-TYPE
    SYNTAX          IpAddress
    MAX-ACCESS      read-create
    STATUS          obsolete
    DESCRIPTION
        "This object specifies the IP address of the primary
        RADIUS server used by this access point to 
        authenticate and/or authorize mobile users to access 
        the PDN.

        In case this RADIUS server is not available, the 
        secondary will be used.

        Obsoleted by cgprsAccPtAaaAuthServerGroup and
        cgprsAccPtAaaAccountServerGroup." 
    ::= { cgprsAccPtEntry 9 }

cgprsAccPtRadiusServerSec OBJECT-TYPE
    SYNTAX          IpAddress
    MAX-ACCESS      read-create
    STATUS          obsolete
    DESCRIPTION
        "Specifies a secondary RADIUS server.

        The secondary RADIUS server will be used if the primary 
        RADIUS server is not available.

        Obsoleted by cgprsAccPtAaaAuthServerGroup and
        cgprsAccPtAaaAccountServerGroup." 
    ::= { cgprsAccPtEntry 10 }

cgprsAccPtIPAccListGroupIn OBJECT-TYPE
    SYNTAX          AccessControlListId
    MAX-ACCESS      read-create
    STATUS          current
    DESCRIPTION
        "This object specifies the ACL against which to compare
        packets received at this Access Point from the PDN for
        forwarding towards an MS.

        Access list at the access point level is used to 
        control which packets are allowed access between the 
        APN and the MS. Access violations by a packet according
        to the rules in this ACL could cause this packet to be
        dropped or its PDP or Bearer session terminated. Which
        of these treatments is taken is specified by the object
        cgprsAccPtAccessViolation.

        This object is ignored if cgprsAccPtIPAccListInEnable 
        is set to 'false'." 
    ::= { cgprsAccPtEntry 11 }

cgprsAccPtIPAccListGroupOut OBJECT-TYPE
    SYNTAX          AccessControlListId
    MAX-ACCESS      read-create
    STATUS          current
    DESCRIPTION
        "This object specifies the ACL against which to compare
        packets originated by an MS and received by at this 
        Access Point for forwarding to the PDN.

        Access list at the access point level is used to 
        control which packets are allowed access between the 
        APN and the MS. Access violations by a packet according
        to the rules in this ACL could cause this packet to be
        dropped or its PDP or Bearer session terminated. Which
        of these treatments is taken is specified by the object
        cgprsAccPtAccessViolation.

        This object is ignored if cgprsAccPtIPAccListOutEnable 
        is set to 'false'." 
    ::= { cgprsAccPtEntry 12 }

cgprsAccPtIfIndex OBJECT-TYPE
    SYNTAX          InterfaceIndexOrZero
    MAX-ACCESS      read-create
    STATUS          obsolete
    DESCRIPTION
        "Specifies an interface to be used by GGSN on Gi
        interface. 

        The value zero indicates that no interface is 
        specified. 

        The cgprsAccPtIfNextHop must be specified if this 
        object is set to the Gi associated interface."
    DEFVAL          { 0 } 
    ::= { cgprsAccPtEntry 13 }

cgprsAccPtIfNextHop OBJECT-TYPE
    SYNTAX          IpAddress
    MAX-ACCESS      read-create
    STATUS          obsolete
    DESCRIPTION
        "Specifies the IP address of the next hop for the
        Gi interface, specified by cgprsAccPtIfIndex.

        This value is mandatory if the value of 
        cgprsAccPtIfIndex is non-zero. Setting the 
        cgprsAccPtIfIndex object to zero will reset this 
        object to the value of '00000000'H, which means 
        it is not used." 
    ::= { cgprsAccPtEntry 14 }

cgprsAccPtAccessViolation OBJECT-TYPE
    SYNTAX          INTEGER  {
                        discardPacket(1),
                        terminateSession(2)
                    }
    MAX-ACCESS      read-create
    STATUS          current
    DESCRIPTION
        "Specifies how access violation should be treated.

        An access violation occurs if the IP packets violates
        any rules in ACL as specified by either 
        cgprsAccPtIPAccListGroupIn or 
        cgprsAccPtIPAccListGroupOut.

            - 'discardPacket', packets are discarded.

            - 'terminateSession', the user's session is 
            terminated."
    DEFVAL          { discardPacket } 
    ::= { cgprsAccPtEntry 15 }

cgprsAccPtSubrRequired OBJECT-TYPE
    SYNTAX          TruthValue
    MAX-ACCESS      read-create
    STATUS          current
    DESCRIPTION
        "This object indicates if a user needs to subscribe
        to this access point before accessing it."
    DEFVAL          { false } 
    ::= { cgprsAccPtEntry 16 }

cgprsAccPtNetworkInitiated OBJECT-TYPE
    SYNTAX          TruthValue
    MAX-ACCESS      read-create
    STATUS          current
    DESCRIPTION
        "This object indicates whether network (PDN)
        initiated PDP or Bearer sessions are allowed for
        this access point. The more common case, is false,
        which indicates that the PDP or Bearer is initiated
        by the MS."
    DEFVAL          { false } 
    ::= { cgprsAccPtEntry 17 }

cgprsAccPtIpAddrAllocations OBJECT-TYPE
    SYNTAX          Gauge32
    MAX-ACCESS      read-only
    STATUS          current
    DESCRIPTION
        "Indicates the number of IP addresses allocated to
        MS's.

        Trigger Condition: This gauge is 
        incremented/decremented by successful completion of
        create/delete dynamic PDP or Bearer context request
        message respectively." 
    ::= { cgprsAccPtEntry 18 }

cgprsAccPtUsers OBJECT-TYPE
    SYNTAX          Gauge32
    MAX-ACCESS      read-only
    STATUS          obsolete
    DESCRIPTION
        "The number of mobile subscribers currently accessing
        this APN.  Obsoleted by cgprsAccPtActivePdps." 
    ::= { cgprsAccPtEntry 19 }

cgprsAccPtIdlePdpPurgeTimer OBJECT-TYPE
    SYNTAX          Unsigned32 (0..168)
    UNITS           "hours"
    MAX-ACCESS      read-create
    STATUS          current
    DESCRIPTION
        "This object indicates maximum idle connection time
        allowed to the PDP or Bearer context before termination of the 
        GTP session.  A value of 0 means session idle timer 
        is not used."
    DEFVAL          { 0 } 
    ::= { cgprsAccPtEntry 20 }

cgprsAccPtBlockMsRoaming OBJECT-TYPE
    SYNTAX          TruthValue
    MAX-ACCESS      read-create
    STATUS          current
    DESCRIPTION
        "This object indicates whether access to a roaming
        MS needs to be blocked for this APN."
    DEFVAL          { false } 
    ::= { cgprsAccPtEntry 21 }

cgprsAccPtAnonymousUserName OBJECT-TYPE
    SYNTAX          SnmpAdminString
    MAX-ACCESS      read-create
    STATUS          current
    DESCRIPTION
        "This object specifies the anonymous user name, which
        is used when a MS tries to access a non-transparent 
        APN without supplying user name and password."
    REFERENCE
        "GSM 03.03: Digital cellular telecommunication
        system (Phase 2+); General Packet Radio Service
        (GPRS); Service description; Stage 1." 
    ::= { cgprsAccPtEntry 22 }

cgprsAccPtAnonymousUserPassword OBJECT-TYPE
    SYNTAX          SnmpAdminString
    MAX-ACCESS      read-create
    STATUS          current
    DESCRIPTION
        "This object specifies the password corresponding
        to cgprsAccPtAnonymousUserName.  For security reasons, 
        retrieving this object returns a zero-length string."
    REFERENCE
        "GSM 03.03: Digital cellular telecommunication
        system (Phase 2+); General Packet Radio Service
        (GPRS); Service description; Stage 1." 
    ::= { cgprsAccPtEntry 23 }

cgprsAccPtMsIsdnSuppressed OBJECT-TYPE
    SYNTAX          TruthValue
    MAX-ACCESS      read-create
    STATUS          current
    DESCRIPTION
        "This object specifies whether the ISDN ID used
        by the MS, when authenticating with a radius server,
        needs to be suppressed or not.  When set to 'true', 
        the ISDN ID attribute will not be sent by the Gateway.
        When set to 'false', the ISDN ID attribute will be 
        sent by the Gateway.  To set this object to 'true', AAA
        radius group for authentication should have been
        configured on the Gateway(either at global or APN level)."
    REFERENCE
        "GSM 09.02: Digital cellular telecommunication
        system (Phase 2+); Mobile Application Part (MAP) 
        specification."
    DEFVAL          { false } 
    ::= { cgprsAccPtEntry 24 }

cgprsAccPtMsIsdnSuppressedValue OBJECT-TYPE
    SYNTAX          DisplayString (SIZE  (0..20))
    MAX-ACCESS      read-create
    STATUS          current
    DESCRIPTION
        "This object specifies the value that will be
        transmitted to the radius server in place of 
        mobile stations ISDN ID.  This object can only 
        be set if cgprsAccPtMsIsdnSuppressed is 'true'.

        Valid characters for this object are 0..9, 
        a, b, c, * and #.  If no value is set, no MS-ISDN
        ID will be sent to the radius server."
    REFERENCE
        "GSM 09.02: Digital cellular telecommunication
        system (Phase 2+); Mobile Application Part (MAP) 
        specification."
    DEFVAL          { ''H } 
    ::= { cgprsAccPtEntry 25 }

cgprsAccPtAaaAuthServerGroup OBJECT-TYPE
    SYNTAX          SnmpAdminString
    MAX-ACCESS      read-create
    STATUS          current
    DESCRIPTION
        "This object specifies the AAA radius server group
        that is used for authentication by this APN." 
    ::= { cgprsAccPtEntry 26 }

cgprsAccPtAaaAccountServerGroup OBJECT-TYPE
    SYNTAX          SnmpAdminString
    MAX-ACCESS      read-create
    STATUS          current
    DESCRIPTION
        "This object specifies the AAA radius server group
        that is used for accounting by this APN.  If no
        group is specified for accounting,
        cgprsAccPtAaaAuthServerGroup will be used." 
    ::= { cgprsAccPtEntry 27 }

cgprsAccPtAaaAccountingEnable OBJECT-TYPE
    SYNTAX          TruthValue
    MAX-ACCESS      read-create
    STATUS          current
    DESCRIPTION
        "This object is used to enable accounting when the
        APN is in 'transparent' mode.  When the object is set to
        'true', cgprsAccPtAaaAccountServerGroup is used for
        accounting.  If cgprsAccPtAaaAccountServerGroup is not
        specified, cgprsAccPtAaaAuthServerGroup will be used.

        When the APN is in 'non-transparent' mode, the 
        accounting will always be enabled i.e., this object 
        will be 'true' by default." 
    ::= { cgprsAccPtEntry 28 }

cgprsAccPtType OBJECT-TYPE
    SYNTAX          INTEGER  {
                        real(1),
                        virtual(2),
                        virtualPreAuth(3)
                    }
    MAX-ACCESS      read-create
    STATUS          current
    DESCRIPTION
        "This object specifies the type of APN.

        'virtual' - Specifies an APN type that is not 
        associated with any specific physical target network 
        on the Gateway.  When this object is set to 'virtual', 
        all other APN parameters are ignored.

        'real' - Specifies an APN type that corresponds to a 
        physical interface to an external network on the Gateway.

        'virtualPreAuth' - Specifies an APN type that is not
        associated with any specific physical target network
        on the Gateway. It applies a pre-authentication phase 
        for any create PDP or Bearer request that includes a virtual 
        APN. During pre-authentication, an Access-Request 
        message is sent to an AAA server and the AAA server 
        then returns a target APN encoded in a Radius 
        attribute in the Access-Accept message."
    DEFVAL          { real } 
    ::= { cgprsAccPtEntry 29 }

cgprsAccPtVrfName OBJECT-TYPE
    SYNTAX          SnmpAdminString
    MAX-ACCESS      read-create
    STATUS          current
    DESCRIPTION
        "This object specifies the name of the VRF with
        which this APN is associated." 
    ::= { cgprsAccPtEntry 30 }

cgprsAccPtDhcpAddrSpace OBJECT-TYPE
    SYNTAX          INTEGER  {
                        global(1),
                        vrf(2)
                    }
    MAX-ACCESS      read-create
    STATUS          current
    DESCRIPTION
        "This object specifies the address space used
        by the dhcp server.  This object can only be
        set if cgprsAccPtDHCPServerPri is set."
    DEFVAL          { global } 
    ::= { cgprsAccPtEntry 31 }

cgprsAccPtPppRegenEnable OBJECT-TYPE
    SYNTAX          TruthValue
    MAX-ACCESS      read-create
    STATUS          current
    DESCRIPTION
        "This object is used to enable Gateway to regenerate
        a PPP session for each IP PDP or Bearer context on
        this APN."
    DEFVAL          { false } 
    ::= { cgprsAccPtEntry 32 }

cgprsAccPtPppRegenMaxSessions OBJECT-TYPE
    SYNTAX          Integer32 (1..65535)
    MAX-ACCESS      read-create
    STATUS          current
    DESCRIPTION
        "This object specifies the maximum number of regenerated
        PPP sessions allowed for this access-point.

        This object can only be set if cgprsAccPtPppRegenEnable
        is set to 'true'.

        The maximum value that can be held by this object
        depends on the Gateway's platform."
    DEFVAL          { 65535 } 
    ::= { cgprsAccPtEntry 33 }

cgprsAccPtPppRegenSetupTime OBJECT-TYPE
    SYNTAX          Integer32 (1..65535)
    UNITS           "seconds"
    MAX-ACCESS      read-create
    STATUS          current
    DESCRIPTION
        "This object specifies the maximum tolerance time within
        which a regenerated PPP session has to fully come up.

        This object can only be set if cgprsAccPtPppRegenEnable
        is set to 'true'."
    DEFVAL          { 60 } 
    ::= { cgprsAccPtEntry 34 }

cgprsAccPtAutoAggregation OBJECT-TYPE
    SYNTAX          TruthValue
    MAX-ACCESS      read-create
    STATUS          current
    DESCRIPTION
        "This object is used to enable auto aggregation on this
        APN.  When a user tries to configure entries in 
        cgprsAccPtAggregTable, this object will automatically 
        be set to 'false'. When this object is set to 'true',
        the entries in cgprsAccPtAggregTable, if any, will be
        deleted."
    DEFVAL          { false } 
    ::= { cgprsAccPtEntry 35 }

cgprsAccPtPcscfServerGroupName OBJECT-TYPE
    SYNTAX          SnmpAdminString (SIZE  (0..100))
    MAX-ACCESS      read-create
    STATUS          current
    DESCRIPTION
        "This object represents the Proxy-CSCF server group that
        will be used by this APN.  The Proxy-CSCF server group
        contains a list of Proxy-CSCF addresses which will be
        provided to the MS(UE) in response to a PDP or Bearer
        contexts for which the P-CSCF address request field is
        set in PCO." 
    ::= { cgprsAccPtEntry 36 }
 


cgprsAccPtAggregTable OBJECT-TYPE
    SYNTAX          SEQUENCE OF CgprsAccPtAggregEntry 
    MAX-ACCESS      not-accessible
    STATUS          current
    DESCRIPTION
        "This table contains the list of aggregate routes
        configured on this APN. Gateway uses a static host route 
        to forward user data packets for each PDP or Bearer context 
        received from Gi interface to Gn interface.  Using the 
        aggregate route (address range), total number of static 
        routes implemented in the Gateway for PDP or Bearer requests
        can be greatly reduced.  If there is no aggregate route 
        configured on this access-point, then default aggregate 
        routes configured on Gateway will be used."
    ::= { ciscoGprsAccPtConfig 2 }

cgprsAccPtAggregEntry OBJECT-TYPE
    SYNTAX          CgprsAccPtAggregEntry
    MAX-ACCESS      not-accessible
    STATUS          current
    DESCRIPTION
        "An Entry contains the IP network prefix which is used
        to combine the routes of PDP or Bearer requests for the same 
        network as a single route on the Gateway."
    INDEX           {
                        cgprsAccPtIndex,
                        cgprsAccPtAggregIpAddrType,
                        cgprsAccPtAggregIpAddr,
                        cgprsAccPtAggregIpMask
                    } 
    ::= { cgprsAccPtAggregTable 1 }

CgprsAccPtAggregEntry ::= SEQUENCE {
        cgprsAccPtAggregIpAddrType InetAddressType,
        cgprsAccPtAggregIpAddr     InetAddress,
        cgprsAccPtAggregIpMask     CiscoInetAddressMask,
        cgprsAccPtAggregRowStatus  RowStatus,
        cgprsAccPtAggregCsgGroup   SnmpAdminString
}

cgprsAccPtAggregIpAddrType OBJECT-TYPE
    SYNTAX          InetAddressType
    MAX-ACCESS      not-accessible
    STATUS          current
    DESCRIPTION
        "This object specifies the type of Internet address
        denoted by cgprsAccPtAggregIpAddr." 
    ::= { cgprsAccPtAggregEntry 1 }

cgprsAccPtAggregIpAddr OBJECT-TYPE
    SYNTAX          InetAddress
    MAX-ACCESS      not-accessible
    STATUS          current
    DESCRIPTION
        "This object specifies the IP address whose network
        prefix is going to be defined by 
        cgprsAccPtAggregIpMask.

        When this object is set, cgprsAccPtAggregIpMask must be 
        specified." 
    ::= { cgprsAccPtAggregEntry 2 }

cgprsAccPtAggregIpMask OBJECT-TYPE
    SYNTAX          CiscoInetAddressMask
    MAX-ACCESS      not-accessible
    STATUS          current
    DESCRIPTION
        "This object specifies the net-mask pertaining to
        cgprsAccPtAggregIpAddr." 
    ::= { cgprsAccPtAggregEntry 3 }

cgprsAccPtAggregRowStatus OBJECT-TYPE
    SYNTAX          RowStatus
    MAX-ACCESS      read-create
    STATUS          current
    DESCRIPTION
        "This object is used to create a new row or delete an
        existing row in this table.

        To create a row, set this object to 'createAndGo'.
        To delete a row, set this object to 'destroy'." 
    ::= { cgprsAccPtAggregEntry 4 }

cgprsAccPtAggregCsgGroup OBJECT-TYPE
    SYNTAX          SnmpAdminString
    MAX-ACCESS      read-create
    STATUS          current
    DESCRIPTION
        "This object specifies the name of the CSG Group.

        The value must be same as an entry in
        cgprsAccPtCsgGroupTable identified by
        cgprsAccPtCsgGroupName." 
    ::= { cgprsAccPtAggregEntry 5 }
 


cgprsAccPtExtTable OBJECT-TYPE
    SYNTAX          SEQUENCE OF CgprsAccPtExtEntry 
    MAX-ACCESS      not-accessible
    STATUS          current
    DESCRIPTION
        "This table is an extension of cgprsAccPtTable."
    ::= { ciscoGprsAccPtConfig 3 }

cgprsAccPtExtEntry OBJECT-TYPE
    SYNTAX          CgprsAccPtExtEntry
    MAX-ACCESS      not-accessible
    STATUS          current
    DESCRIPTION
        "An entry in cgprsAccPtExtTable."
    AUGMENTS           { cgprsAccPtEntry  } 
    ::= { cgprsAccPtExtTable 1 }

CgprsAccPtExtEntry ::= SEQUENCE {
        cgprsAccPtIPAccListInEnable          TruthValue,
        cgprsAccPtIPAccListOutEnable         TruthValue,
        cgprsAccPtGtpRespMesgWaitAcctng      TruthValue,
        cgprsAccPtImsiSuppressed             TruthValue,
        cgprsAccPtVerifyUpStrTpduSrcAddr     TruthValue,
        cgprsAccPtVerifyUpStrTpduDstAddr     TruthValue,
        cgprsAccPtRedirInterMobilAddrTyp     InetAddressType,
        cgprsAccPtRedirInterMobilAddr        InetAddress,
        cgprsAccPtSuppressRadiusAttribs      BITS,
        cgprsAccPtInterimAccountinEnable     TruthValue,
        cgprsAccPtSetRadiusAttributes        BITS,
        cgprsAccPtOperationMode              INTEGER,
        cgprsAccPtAbsoluteSessionTimer       Unsigned32,
        cgprsAccPtRadiusAttrNasId            SnmpAdminString,
        cgprsAccPtPdpInServicePolicyName     SnmpAdminString,
        cgprsAccPtPdpOutServicePolicyNam     SnmpAdminString,
        cgprsAccPtPppRegenVerifyDomain       TruthValue,
        cgprsAccPtIpAddrLocalPoolName        SnmpAdminString,
        cgprsAccPtServiceAware               TruthValue,
        cgprsAccPtAdvDownlinkNextHopAddrType InetAddressType,
        cgprsAccPtAdvDownlinkNextHopAddr     InetAddress,
        cgprsAccPtGtpUpdateFailDelete        TruthValue,
        cgprsAccPtAaaAccountInterPeriod      Unsigned32,
        cgprsAccPtAaaAccountInterRadius      TruthValue,
        cgprsAccPtGxEnable                   TruthValue,
        cgprsAccPtPcscfLoadBalance           TruthValue,
        cgprsAccPtNetworkBehindMsEnable      TruthValue,
        cgprsAccPtMaxSubnetsBehindMobile     Unsigned32,
        cgprsAccPtChargingRecordType         INTEGER,
        cgprsAccPtChargingGrp                Unsigned32,
        cgprsAccPtIpAddrPoolNoRedistribute   TruthValue,
        cgprsAccPtDualAddrEnabled            TruthValue,
        cgprsAccPtVerifyDownlinkAddr         TruthValue
}

cgprsAccPtIPAccListInEnable OBJECT-TYPE
    SYNTAX          TruthValue
    MAX-ACCESS      read-create
    STATUS          current
    DESCRIPTION
        "When this object is set to 'true', ACL denoted by
        cgprsAccPtIPAccListGroupIn will be active. When
        set to 'false', it will become inactive."
    DEFVAL          { false } 
    ::= { cgprsAccPtExtEntry 1 }

cgprsAccPtIPAccListOutEnable OBJECT-TYPE
    SYNTAX          TruthValue
    MAX-ACCESS      read-create
    STATUS          current
    DESCRIPTION
        "When this object is set to 'true', ACL denoted by
        cgprsAccPtIPAccListGroupOut will be active. When
        set to 'false', it will become inactive."
    DEFVAL          { false } 
    ::= { cgprsAccPtExtEntry 2 }

cgprsAccPtGtpRespMesgWaitAcctng OBJECT-TYPE
    SYNTAX          TruthValue
    MAX-ACCESS      read-create
    STATUS          current
    DESCRIPTION
        "When this object is set to 'true', Gateway waits for a
        RADIUS accounting response before sending a create PDP
        or Bearer context response to the MME or SGSN, for create
        PDP or Bearer context requests received at a particular APN.

        When this object is set to 'false', Gateway sends create
        PDP or Bearer response to MME or SGSN after sending a RADIUS
        start accounting message to the RADIUS server (without waiting
        for a response from the RADIUS accounting server)."
    DEFVAL          { false } 
    ::= { cgprsAccPtExtEntry 3 }

cgprsAccPtImsiSuppressed OBJECT-TYPE
    SYNTAX          TruthValue
    MAX-ACCESS      read-create
    STATUS          obsolete
    DESCRIPTION
        "This object specifies whether GGSN will be sending
        the radius attribute, IMSI value, in any of the 
        radius requests to the radius server or not.  When set
        to 'true', the IMSI attribute will not be sent by
        the GGSN.  When set to 'false', the IMSI attribute 
        will be sent by the GGSN.  This object is obsoleted by 
        cgprsAccPtSuppressRadiusAttribs."
    REFERENCE
        "3GPP TS 29.061 Release 1999: Digital cellular 
        telecommunications system (Phase 2+) (GSM); Universal 
        Mobile Telecommunications System (UMTS);Interworking 
        between the Public Land Mobile Network (PLMN) 
        supporting Packet Based services and Packet Data 
        Networks (PDN)."
    DEFVAL          { false } 
    ::= { cgprsAccPtExtEntry 4 }

cgprsAccPtVerifyUpStrTpduSrcAddr OBJECT-TYPE
    SYNTAX          TruthValue
    MAX-ACCESS      read-create
    STATUS          current
    DESCRIPTION
        "When this object is set to 'true', the Gateway will check the
        upstream TPDU source address against the address 
        previously assigned to this user.  If the addresses are
        different, the TPDU is dropped, the notification
        cgprsAccPtSecSrcViolNotif is generated and
        cgprsAccPtSourceAddrViolTpdus is incremented.  This 
        check will enable the Gateway to restrict the users with 
        fake identity.

        When the object is set to 'false', no checking is
        performed by the Gateway."
    DEFVAL          { false } 
    ::= { cgprsAccPtExtEntry 5 }

cgprsAccPtVerifyUpStrTpduDstAddr OBJECT-TYPE
    SYNTAX          TruthValue
    MAX-ACCESS      read-create
    STATUS          current
    DESCRIPTION
        "When this object is set to 'true', Gateway will check the
        upstream TPDU destination address against the range of
        IP addresses reserved for PLMN devices.  If there is a
        match, the TPDU is dropped, the notification
        cgprsAccPtSecDestViolNotif is generated and 
        cgprsAccPtDestAddrViolTpdus is incremented.  The 
        configuration of IP address ranges reserved for PLMN 
        device is out of the scope of this MIB.  This check
        would enable the Gateway to protect the GPRS network from
        some hacker who may try to flood the Gateway and PLMN 
        nodes with intense data traffic.

        When the object is set to 'false', no checking is
        performed by the Gateway."
    DEFVAL          { false } 
    ::= { cgprsAccPtExtEntry 6 }

cgprsAccPtRedirInterMobilAddrTyp OBJECT-TYPE
    SYNTAX          InetAddressType
    MAX-ACCESS      read-create
    STATUS          current
    DESCRIPTION
        "This object indicates the type of Internet address by
        which cgprsAccPtRedirInterMobilAddr is reachable." 
    ::= { cgprsAccPtExtEntry 7 }

cgprsAccPtRedirInterMobilAddr OBJECT-TYPE
    SYNTAX          InetAddress
    MAX-ACCESS      read-create
    STATUS          current
    DESCRIPTION
        "This object represents the IP address of the device
        to which inter-mobile traffic will be re-directed.
        When this redirection is active on an APN, before
        downstream packets exit the Gateway, they are screened
        to see if they come from other GTP tunnels.  If so,
        they won't be GTP-tunneled downstream, but will get
        redirected to the device specified by this object and
        cgprsAccPtRedirInterMobilTraffic is incremented.
        When this object is set to zero value, inter-mobile
        traffic will not be redirected i.e., the traffic will
        get switched through Gateway without going through any
        Gi interface." 
    ::= { cgprsAccPtExtEntry 8 }

cgprsAccPtSuppressRadiusAttribs OBJECT-TYPE
    SYNTAX          BITS {
                        none(0),
                        imsi(1),
                        sgsnAddr(2),
                        qos(3)
                    }
    MAX-ACCESS      read-create
    STATUS          current
    DESCRIPTION
        "This object indicates the attributes that will be
        suppressed by the Gateway in its its authorization and
        accounting requests to the RADIUS server."
    REFERENCE
        "3GPP TS 29.061 Release 1999: Digital cellular
        telecommunications system (Phase 2+) (GSM); Universal
        Mobile Telecommunications System (UMTS);Interworking
        between the Public Land Mobile Network (PLMN)
        supporting Packet Based services and Packet Data
        Networks (PDN)."
    DEFVAL          { { none } } 
    ::= { cgprsAccPtExtEntry 9 }

cgprsAccPtInterimAccountinEnable OBJECT-TYPE
    SYNTAX          TruthValue
    MAX-ACCESS      read-create
    STATUS          current
    DESCRIPTION
        "This object is used to enable Interim Accounting for a
        PDP or Bearer context on this APN.  When set to 'true',
        accounting updates will be triggered whenever a update
        PDP or Bearer request is received. This object can set
        to 'true' only when accounting(cgprsAccPtAaaAccountingEnable)
        is enabled."
    DEFVAL          { false } 
    ::= { cgprsAccPtExtEntry 10 }

cgprsAccPtSetRadiusAttributes OBJECT-TYPE
    SYNTAX          BITS {
                        none(0),
                        userNameMsisdn(1),
                        accSessIdChargingId(2)
                    }
    MAX-ACCESS      read-create
    STATUS          current
    DESCRIPTION
        "This object indicates the values set in various radius
        attributes by the Gateway while communicating with RADIUS
        Server.  When set to

        'none' - reset the value set by the options below.

        'userNameMsisdn' - MSISDN of the mobile is sent in the
             user-name attribute.

        'accSessIdChargingId' - Charging ID is sent in the
             accounting session ID attribute." 
    ::= { cgprsAccPtExtEntry 11 }

cgprsAccPtOperationMode OBJECT-TYPE
    SYNTAX          INTEGER  {
                        inService(0),
                        maintenance(1)
                    }
    MAX-ACCESS      read-create
    STATUS          current
    DESCRIPTION
        "This object denotes the operation mode of this APN.
        Each mode has different PDP or Bearer context activation and
        deactivation behavior and is given as below:

        inService - normal operational mode in which all
            functions are allowed.  cgprsAccPtInServiceNotif
            notification will be sent to indicate the state
            change.

        maintenance - No new PDPs or Bearers can be activated in this
            state. cgprsAccPtMaintenanceNotif notification
            will be sent to indicate the state change."
    DEFVAL          { inService } 
    ::= { cgprsAccPtExtEntry 12 }

cgprsAccPtAbsoluteSessionTimer OBJECT-TYPE
    SYNTAX          Unsigned32 (0 | 30..4294967)
    UNITS           "seconds"
    MAX-ACCESS      read-create
    STATUS          current
    DESCRIPTION
        "Absolute session timer is a RADIUS attribute (#27) sent
        by the AAA server in the Access-Accept packet. The Gateway 
        will deactivate the PDP or Bearer when this timer expires.  This
        object denotes the timer used by the Gateway when the same
        is not received from the AAA server.  Value of '0'
        denotes that the timer is disabled."
    DEFVAL          { 0 } 
    ::= { cgprsAccPtExtEntry 13 }

cgprsAccPtRadiusAttrNasId OBJECT-TYPE
    SYNTAX          SnmpAdminString
    MAX-ACCESS      read-create
    STATUS          current
    DESCRIPTION
        "This object denotes the value used as NAS ID in the
        RADIUS access requests sent by the Gateway on this APN.  A
        zero length string needs to be set to unconfigure the
        NAS ID value." 
    ::= { cgprsAccPtExtEntry 14 }

cgprsAccPtPdpInServicePolicyName OBJECT-TYPE
    SYNTAX          SnmpAdminString (SIZE  (0..40))
    MAX-ACCESS      read-create
    STATUS          current
    DESCRIPTION
        "Per PDP or Bearer Policy feature on the Gateway ensures
        that the PDP or Bearer contexts does not exceed bandwidth
        negotiated as part of PDP or Bearer context activation
        procedure. A service policy contains classification and
        policing parameters, details of the same is out of the scope
        of this MIB. This object denotes the name of the service
        policy that is applicable to inbound traffic on all the PDP's
        pertaining to this APN." 
    ::= { cgprsAccPtExtEntry 15 }

cgprsAccPtPdpOutServicePolicyNam OBJECT-TYPE
    SYNTAX          SnmpAdminString (SIZE  (0..40))
    MAX-ACCESS      read-create
    STATUS          current
    DESCRIPTION
        "This object denotes the name of the service policy that
        is applicable to outbound traffic on all the PDP's or Bearer's
        pertaining to this APN." 
    ::= { cgprsAccPtExtEntry 16 }

cgprsAccPtPppRegenVerifyDomain OBJECT-TYPE
    SYNTAX          TruthValue
    MAX-ACCESS      read-create
    STATUS          current
    DESCRIPTION
        "When this object is set to 'true', a PPP regen session
        creation would be rejected if the domain name in PCO
        field is different than the APN name.  This object can
        only be set when cgprsAccPtPppRegenEnable is 'true'."
    DEFVAL          { false } 
    ::= { cgprsAccPtExtEntry 17 }

cgprsAccPtIpAddrLocalPoolName OBJECT-TYPE
    SYNTAX          SnmpAdminString
    MAX-ACCESS      read-create
    STATUS          current
    DESCRIPTION
        "This object represents the name of the local address
        pool used when cgprsAccPtIpAddressPool is set to
        'local'." 
    ::= { cgprsAccPtExtEntry 18 }

cgprsAccPtServiceAware OBJECT-TYPE
    SYNTAX          TruthValue
    MAX-ACCESS      read-create
    STATUS          current
    DESCRIPTION
        "This object is to enable service-aware billing
        (Diameter Credit Control Application [DCCA]
        support) on the access-point. This object can be
        set only when the object cGgsnSAServiceAware present
        in CISCO-GGSN-SERVICE-AWARE-MIB is set to 'true'."
    DEFVAL          { false } 
    ::= { cgprsAccPtExtEntry 19 }

cgprsAccPtAdvDownlinkNextHopAddrType OBJECT-TYPE
    SYNTAX          InetAddressType
    MAX-ACCESS      read-create
    STATUS          current
    DESCRIPTION
        "This object indicates the type of Internet address
        of downlink next hop address." 
    ::= { cgprsAccPtExtEntry 20 }

cgprsAccPtAdvDownlinkNextHopAddr OBJECT-TYPE
    SYNTAX          InetAddress
    MAX-ACCESS      read-create
    STATUS          current
    DESCRIPTION
        "This object advertises the next hop address on the
        Gateway to which downlink traffic destined for the Gateway 
        is to be routed. The address type is given by the  
        cgprsAccPtAdvDownlinkNextHopAddrType object." 
    ::= { cgprsAccPtExtEntry 21 }

cgprsAccPtGtpUpdateFailDelete OBJECT-TYPE
    SYNTAX          TruthValue
    MAX-ACCESS      read-create
    STATUS          current
    DESCRIPTION
        "This object denotes the action to be taken when a COA
        initiated update request for QOS change fails for a
        PDP or Bearer context on this Access Point. If the object is
        set to 'true' and the update response from MME or SGSN (for
        a update request) is not got after the configured retries
        or the received response indicates a cause value other than
        'request accepted', then the PDP or Bearer context will be
        deleted by the Gateway."
    DEFVAL          { false } 
    ::= { cgprsAccPtExtEntry 22 }

cgprsAccPtAaaAccountInterPeriod OBJECT-TYPE
    SYNTAX          Unsigned32 (0 | 15..71582)
    UNITS           "minutes"
    MAX-ACCESS      read-create
    STATUS          current
    DESCRIPTION
        "This object specifies the periodic accounting timer
        interval value for the access point. When this object 
        is set to a value, 'interim' type accounting records
        will be sent at the specified interval for the PDP or
        Bearer contexts on this APN. When set to '0' the 'interim'
        type accounting records will not be sent out."
    DEFVAL          { 0 } 
    ::= { cgprsAccPtExtEntry 23 }

cgprsAccPtAaaAccountInterRadius OBJECT-TYPE
    SYNTAX          TruthValue
    MAX-ACCESS      read-create
    STATUS          current
    DESCRIPTION
        "This object when set to 'true', enables Gateway to receive
        and use the Accounting Periodic Interval from Radius for 
        the PDP or Bearer contexts on this APN."
    DEFVAL          { false } 
    ::= { cgprsAccPtExtEntry 24 }

cgprsAccPtGxEnable OBJECT-TYPE
    SYNTAX          TruthValue
    MAX-ACCESS      read-create
    STATUS          current
    DESCRIPTION
        "This object when set to 'true', indicates that this APN
        is Gx enabled."
    DEFVAL          { false } 
    ::= { cgprsAccPtExtEntry 25 }

cgprsAccPtPcscfLoadBalance OBJECT-TYPE
    SYNTAX          TruthValue
    MAX-ACCESS      read-create
    STATUS          current
    DESCRIPTION
        "The Proxy-CSCF server group represented by the object
        cgprsAccPtPcscfServerGroupName contains a list of
        Proxy-CSCF addresses which will be provided to the MS(UE)
        in the PCO (Protocol Configuration Option) response message.
        The object cgprsAccPtPcscfLoadBalance when set to 'true',
        enables Gateway to include the IP address of the least loaded
        P-CSCF server in the PCO response message. Round Robin
        algorithm is used for the selection of the least loaded
        P-CSCF server."
    DEFVAL          { false } 
    ::= { cgprsAccPtExtEntry 26 }

cgprsAccPtNetworkBehindMsEnable OBJECT-TYPE
    SYNTAX          TruthValue
    MAX-ACCESS      read-create
    STATUS          current
    DESCRIPTION
        "This object when set to 'true', enables the Gateway to support
        a network behind the Mobile Station."
    DEFVAL          { false } 
    ::= { cgprsAccPtExtEntry 27 }

cgprsAccPtMaxSubnetsBehindMobile OBJECT-TYPE
    SYNTAX          Unsigned32 (0..16)
    MAX-ACCESS      read-create
    STATUS          current
    DESCRIPTION
        "This object indicates the number of subnetworks that can
        be permitted behind the Mobile station. This object can be
        set only when the object cgprsAccPtNetworkBehindMsEnable is
        set to 'true' as this object can take effect only when
        cgprsAccPtNetworkBehindMsEnable is 'true'. Setting the value
        of '0' to this object will not take effect. The value of this
        object will be set to '0' only if the object
        cgprsAccPtNetworkBehindMsEnable is set to 'false'."
    DEFVAL          { 0 } 
    ::= { cgprsAccPtExtEntry 28 }

cgprsAccPtChargingRecordType OBJECT-TYPE
    SYNTAX          INTEGER  {
                        noconfig(0),
                        none(1),
                        gcdr(2),
                        egcdr(3)
                    }
    MAX-ACCESS      read-create
    STATUS          current
    DESCRIPTION
        "This object denotes the charging record type of this APN.
        Each type has different PDP or Bearer context behavior and
        is given as below:

        noconfig - When no record type is configured.

        none - when there are no active PDP or Bearer contexts under
               this APN

        gcdr - When the derived record type is gcdr, the Gateway
               indicates CSG2 that gcdr generation is configured for
               this user, so that CSG2 will generate service level
               CDRs.

        egcdr - When the derived record type is egcdr, the Gateway
               indicates CSG2 that egcdr generation is configured
               for this user, so that CSG2 will not generate
               service level CDRs."
    DEFVAL          { noconfig } 
    ::= { cgprsAccPtExtEntry 29 }

cgprsAccPtChargingGrp OBJECT-TYPE
    SYNTAX          Unsigned32 (0..29)
    MAX-ACCESS      read-create
    STATUS          current
    DESCRIPTION
        "This object provides the charging group identifier to
        which an access point is associated with. By default the
        value of this object is 0, it indicates that the default
        charging group is associated with this access point entry.

        The value of this object must be same as one of the values
        identified by cgprsCgGroupIndex."
    REFERENCE
        "csgprsCgGroupIndex is defined in CISCO-GPRS-CHARGING-MIB."
    DEFVAL          { 0 } 
    ::= { cgprsAccPtExtEntry 30 }

cgprsAccPtIpAddrPoolNoRedistribute OBJECT-TYPE
    SYNTAX          TruthValue
    MAX-ACCESS      read-create
    STATUS          current
    DESCRIPTION
        "This object indicates whether route propagation from PCOP to
        SUP (Supervisor) shall occur. This object can be set/unset
        only when the object cgprsAccPtIpAddressPool is configured.
        By default the value of this object is false.
        Setting it to true does not allow the redistribution of routes 
        from PCOP to the SUP."
    DEFVAL          { false } 
    ::= { cgprsAccPtExtEntry 31 }

cgprsAccPtDualAddrEnabled OBJECT-TYPE
    SYNTAX          TruthValue
    MAX-ACCESS      read-create
    STATUS          current
    DESCRIPTION
        "This object when set to 'true' indicates that the APN has dual
        stack capability."
    DEFVAL          { false } 
    ::= { cgprsAccPtExtEntry 32 }

cgprsAccPtVerifyDownlinkAddr OBJECT-TYPE
    SYNTAX          TruthValue
    MAX-ACCESS      read-create
    STATUS          current
    DESCRIPTION
        "This object indicates that the Gateway is programmed
        to check and reject all downstream packets with same
        source and destination.

        When the value is set to 'true', the Gateway check and
        reject all downstream packets with same source and
        destination and 'false' means this feature is disabled."
    DEFVAL          { false } 
    ::= { cgprsAccPtExtEntry 33 }
 

-- Generic Servers

cgprsAccPtGenServerConfigs  OBJECT IDENTIFIER
    ::= { ciscoGprsAccPtConfig 4 }


cgprsAccPtGenServerConfigTable OBJECT-TYPE
    SYNTAX          SEQUENCE OF CgprsAccPtGenServerConfigEntry 
    MAX-ACCESS      not-accessible
    STATUS          current
    DESCRIPTION
        "Each column in this table represent IP address of
        different generic servers, for example: DNS, NetBIOS, 
        configured on the APN."
    ::= { cgprsAccPtGenServerConfigs 1 }

cgprsAccPtGenServerConfigEntry OBJECT-TYPE
    SYNTAX          CgprsAccPtGenServerConfigEntry
    MAX-ACCESS      not-accessible
    STATUS          current
    DESCRIPTION
        "An entry in cgprsAccPtGenServerConfigTable."
    AUGMENTS           { cgprsAccPtEntry  } 
    ::= { cgprsAccPtGenServerConfigTable 1 }

CgprsAccPtGenServerConfigEntry ::= SEQUENCE {
        cgprsAccPtDnsServerAddrType     InetAddressType,
        cgprsAccPtPriDnsServer          InetAddress,
        cgprsAccPtSecDnsServer          InetAddress,
        cgprsAccPtNetbiosServerAddrType InetAddressType,
        cgprsAccPtPriNetbiosServer      InetAddress,
        cgprsAccPtSecNetbiosServer      InetAddress
}

cgprsAccPtDnsServerAddrType OBJECT-TYPE
    SYNTAX          InetAddressType
    MAX-ACCESS      read-create
    STATUS          current
    DESCRIPTION
        "This object indicates the type of Internet address by
        which cgprsAccPtPriDnsServer and cgprsAccPtSecDnsServer
        are reachable.

        DNS addresses to be sent to the MS can come from DHCP
        server or RADIUS server based on IP address allocation
        scheme chosen by cgprsAccPtIpAddressPool.  The IP
        address configured to cgprsAccPtPriDnsServer and
        cgprsAccPtSecDnsServer will be sent to MS only when

         - DHCP/RADIUS servers does not return any DNS address.
         - local address pool is used for IP address
           allocation for MS." 
    ::= { cgprsAccPtGenServerConfigEntry 1 }

cgprsAccPtPriDnsServer OBJECT-TYPE
    SYNTAX          InetAddress
    MAX-ACCESS      read-create
    STATUS          current
    DESCRIPTION
        "This object specifies the IP address of the primary
        DNS server that will be sent to MS." 
    ::= { cgprsAccPtGenServerConfigEntry 2 }

cgprsAccPtSecDnsServer OBJECT-TYPE
    SYNTAX          InetAddress
    MAX-ACCESS      read-create
    STATUS          current
    DESCRIPTION
        "This object specifies the IP address of the secondary
        DNS server that will be sent to MS.  A secondary server
        can be configured only if primary exists." 
    ::= { cgprsAccPtGenServerConfigEntry 3 }

cgprsAccPtNetbiosServerAddrType OBJECT-TYPE
    SYNTAX          InetAddressType
    MAX-ACCESS      read-create
    STATUS          current
    DESCRIPTION
        "This object indicates the type of Internet address by
        which cgprsAccPtPriNetbiosServer and
        cgprsAccPtSecNetbiosServer are reachable.

        NBNS addresses to be sent to the MS can come from DHCP
        server or RADIUS server based on IP address allocation
        scheme chosen by cgprsAccPtIpAddressPool.  The IP
        address configured to cgprsAccPtPriNetbiosServer and
        cgprsAccPtSecNetbiosServer will be sent to MS only when

         - DHCP/RADIUS servers does not return any NBNS address.
         - local address pool is used for IP address allocation
           for MS." 
    ::= { cgprsAccPtGenServerConfigEntry 4 }

cgprsAccPtPriNetbiosServer OBJECT-TYPE
    SYNTAX          InetAddress
    MAX-ACCESS      read-create
    STATUS          current
    DESCRIPTION
        "This object specifies the IP address of the primary
        NetBIOS name server(NBNS) that will be sent to MS." 
    ::= { cgprsAccPtGenServerConfigEntry 5 }

cgprsAccPtSecNetbiosServer OBJECT-TYPE
    SYNTAX          InetAddress
    MAX-ACCESS      read-create
    STATUS          current
    DESCRIPTION
        "This object specifies the IP address of the secondary
        NetBIOS name server(NBNS) that will be sent to MS.  A
        secondary server can be configured only if primary
        exists." 
    ::= { cgprsAccPtGenServerConfigEntry 6 }
 

-- IMS Params

cgprsAccPtImsConfigs  OBJECT IDENTIFIER
    ::= { ciscoGprsAccPtConfig 5 }


cgprsAccPtImsConfigTable OBJECT-TYPE
    SYNTAX          SEQUENCE OF CgprsAccPtImsConfigEntry 
    MAX-ACCESS      not-accessible
    STATUS          deprecated
    DESCRIPTION
        "IP Multimedia Subsystem(IMS) has been introduced in
        3GPP release 5 for the provision of multimedia services.
        The Gateway terminates the GPRS Bearer to carry IMS signaling
        and traffic. It communicates with Policy Decision
        Function(PDF) over the Go interface and acts as a Policy
        Enforcement Point(PEP) to enforce QoS per media flows
        using COPS protocol.

        This table represents various parameters required to
        support IMS.  This table is deprecated as IMS is not
        supported from GGSN 5.0 release onwards."
    REFERENCE       "3GPP TS 29.207: Policy Control over Go interface."
    ::= { cgprsAccPtImsConfigs 1 }

cgprsAccPtImsConfigEntry OBJECT-TYPE
    SYNTAX          CgprsAccPtImsConfigEntry
    MAX-ACCESS      not-accessible
    STATUS          deprecated
    DESCRIPTION
        "An entry in cgprsAccPtImsConfigTable"
    AUGMENTS           { cgprsAccPtEntry  } 
    ::= { cgprsAccPtImsConfigTable 1 }

CgprsAccPtImsConfigEntry ::= SEQUENCE {
        cgprsAccPtImsEnable         BITS,
        cgprsAccPtPCscfGroupName    SnmpAdminString,
        cgprsAccPtImsSigAccGroupIn  AccessControlListOrZero,
        cgprsAccPtImsSigAccGroupOut AccessControlListOrZero,
        cgprsAccPtRejNonImsPdp      TruthValue
}

cgprsAccPtImsEnable OBJECT-TYPE
    SYNTAX          BITS {
                        disable(0),
                        enable(1),
                        exclusive(2),
                        transformPrimary(3)
                    }
    MAX-ACCESS      read-create
    STATUS          deprecated
    DESCRIPTION
        "This object indicates whether IMS traffic, both
        signaling and data, is allowed on this APN. When set to

        disable   - IMS traffic is not allowed.
        enable    - IMS traffic is allowed.
        exclusive - Only IMS traffic is allowed, non-IMS
                    traffic will be rejected.
        transformPrimary - non IMS traffic will be allowed
                    but all the rules applicable to IMS
                    traffic will also apply, for example. ACL's.

        The options 'exclusive' and 'transformPrimary' are
        mutually exclusive and can be set only when IMS is
        enabled, i.e., when 'enable' is set."
    DEFVAL          { { disable } } 
    ::= { cgprsAccPtImsConfigEntry 1 }

cgprsAccPtPCscfGroupName OBJECT-TYPE
    SYNTAX          SnmpAdminString (SIZE  (0..100))
    MAX-ACCESS      read-create
    STATUS          deprecated
    DESCRIPTION
        "This object represents the Proxy-CSCF server group that
        will be used by this APN.  Proxy-CSCF server group
        contains list of Proxy-CSCF addresses which will be
        provided to MS(UE) in response to a PDP contexts
        for which P-CSCF address request field is set in PCO." 
    ::= { cgprsAccPtImsConfigEntry 2 }

cgprsAccPtImsSigAccGroupIn OBJECT-TYPE
    SYNTAX          AccessControlListOrZero
    MAX-ACCESS      read-create
    STATUS          deprecated
    DESCRIPTION
        "This object represents the access list that will be
        applied to all the IMS signaling PDP context received
        by this APN from the PDN for forwarding towards a MS.
        An IMS signaling PDP context will have IMS signaling
        flag set in the PCO field."
    DEFVAL          { 0 } 
    ::= { cgprsAccPtImsConfigEntry 3 }

cgprsAccPtImsSigAccGroupOut OBJECT-TYPE
    SYNTAX          AccessControlListOrZero
    MAX-ACCESS      read-create
    STATUS          deprecated
    DESCRIPTION
        "This object represents the access list that will be
        applied to all the IMS signaling PDP context received
        by this APN from a MS for forwarding towards PDN.  An
        IMS signaling PDP context will have IMS signaling flag
        set in the PCO field."
    DEFVAL          { 0 } 
    ::= { cgprsAccPtImsConfigEntry 4 }

cgprsAccPtRejNonImsPdp OBJECT-TYPE
    SYNTAX          TruthValue
    MAX-ACCESS      read-create
    STATUS          deprecated
    DESCRIPTION
        "This object represents the action to be taken on a non
        IMS PDP context, when cgprsAccPtImsEnable is set to
        'true' on this APN.  When this object is set to 'true',
        respective PDP context activation will be rejected.
        When set to 'false', PDP activation will be based on the
        QoS negotiation."
    DEFVAL          { false } 
    ::= { cgprsAccPtImsConfigEntry 5 }
 

-- Charging Parameters

cgprsAccPtChargingParams  OBJECT IDENTIFIER
    ::= { ciscoGprsAccPtConfig 6 }


cgprsAccPtChgProfTable OBJECT-TYPE
    SYNTAX          SEQUENCE OF CgprsAccPtChgProfEntry 
    MAX-ACCESS      not-accessible
    STATUS          current
    DESCRIPTION
        "Charging characteristics is a parameter that allows the
        operator to apply different charging methods on a per
        PDP or Bearer basis.  Each charging profile is associated
        with an index, set of charging parameters like subscriber
        category, volume limit trigger, etc., details of the
        same is outside the scope of the MIB and are defined
        in CISCO-GPRS-CHARGING-MIB.

        Charging characteristics can be received from MME or SGSN as
        an Information Element in the create PDP/Bearer request or
        defaults can be configured at the Gateway and/or APN level.

        This table represents the charging profiles that can
        be applied to different type of mobile subscribers on
        an APN.  The Gateway level configurations are dealt in
        CISCO-GPRS-CHARGING-MIB."
    REFERENCE
        "3GPP TS 32.215 V5.2.0 Charging data description for 
        the Packet Switched domain(Release 4)."
    ::= { cgprsAccPtChargingParams 1 }

cgprsAccPtChgProfEntry OBJECT-TYPE
    SYNTAX          CgprsAccPtChgProfEntry
    MAX-ACCESS      not-accessible
    STATUS          current
    DESCRIPTION
        "An entry in cgprsAccPtChgProfTable."
    INDEX           {
                        cgprsAccPtIndex,
                        cgprsAccPtMsType
                    } 
    ::= { cgprsAccPtChgProfTable 1 }

CgprsAccPtChgProfEntry ::= SEQUENCE {
        cgprsAccPtMsType           INTEGER,
        cgprsAccPtChgProfile       Unsigned32,
        cgprsAccPtChgProfOverride  TruthValue,
        cgprsAccPtChgProfRowStatus RowStatus
}

cgprsAccPtMsType OBJECT-TYPE
    SYNTAX          INTEGER  {
                        all(1),
                        home(2),
                        roaming(3),
                        roamingTrusted(4),
                        visiting(5),
                        visitingTrusted(6)
                    }
    MAX-ACCESS      not-accessible
    STATUS          current
    DESCRIPTION
        "This object represents the type of MS to which the
        charging profile selected by cgprsAccPtChgProfile is
        applied on this APN. Different types of MS -

        A roaming MS belongs to a MME/SGSN of a different PLMN.
        A visitor MS is one whose IMSI value belongs to a
        different PLMN.  A home MS is neither roamer nor
        visitor, i.e., IMSI and MME/SGSN corresponds to same PLMN.

        A roamer/visitor is said to be Trusted/Friendly if
        the different PLMN is a trusted/friendly PLMN." 
    ::= { cgprsAccPtChgProfEntry 1 }

cgprsAccPtChgProfile OBJECT-TYPE
    SYNTAX          Unsigned32
    MAX-ACCESS      read-create
    STATUS          current
    DESCRIPTION
        "This object represents the charging profile number to
        be applied to MS denoted by cgprsAccPtMsType on this
        APN.  Details of charging profile parameters are outside
        the scope of this MIB and are covered by 
        CISCO-GPRS-CHARGING-MIB.  This object is mandatory while
        creating a row. The current valid values are 1 to 255." 
    ::= { cgprsAccPtChgProfEntry 2 }

cgprsAccPtChgProfOverride OBJECT-TYPE
    SYNTAX          TruthValue
    MAX-ACCESS      read-create
    STATUS          current
    DESCRIPTION
        "This object specifies whether charging characteristics
        value supplied by MME or SGSN will be ignored and the values
        supplied in this table are used.  When this object is
        set to 'true', the value supplied by MME or SGSN will be
        ignored."
    DEFVAL          { true } 
    ::= { cgprsAccPtChgProfEntry 3 }

cgprsAccPtChgProfRowStatus OBJECT-TYPE
    SYNTAX          RowStatus
    MAX-ACCESS      read-create
    STATUS          current
    DESCRIPTION
        "This object is used to create a new row or delete an
        existing row in this table.

        To create a row, set this object to 'createAndGo'.
        To delete a row, set this object to 'destroy'." 
    ::= { cgprsAccPtChgProfEntry 4 }
 

-- Call Admission Control(CAC) configs

cgprsAccPtCacConfigs  OBJECT IDENTIFIER
    ::= { ciscoGprsAccPtConfig 7 }


cgprsAccPtCacTable OBJECT-TYPE
    SYNTAX          SEQUENCE OF CgprsAccPtCacEntry 
    MAX-ACCESS      not-accessible
    STATUS          current
    DESCRIPTION
        "Call Admission Control(CAC) on the Gateway ensures that
        required network resources are available for real-time
        data traffic, such as voice, video, etc., and to support
        establishment and modification of the QoS parameters by
        signaling and negotiating during PDP or Bearer context
        activation procedure and modification procedure. CAC
        performs this by examining various QoS parameters like
        traffic class, maximum bit rate and guaranteed bit rate
        for both uplink and downlink received from the MME or
        SGSN with the local configured parameters or policy
        received from Policy Decision Function(PDF).

        This table represents various parameters required to
        support CAC."
    ::= { cgprsAccPtCacConfigs 1 }

cgprsAccPtCacEntry OBJECT-TYPE
    SYNTAX          CgprsAccPtCacEntry
    MAX-ACCESS      not-accessible
    STATUS          current
    DESCRIPTION
        "An entry in cgprsAccPtCacTable."
    AUGMENTS           { cgprsAccPtEntry  } 
    ::= { cgprsAccPtCacTable 1 }

CgprsAccPtCacEntry ::= SEQUENCE {
        cgprsAccPtCacPolicyName         SnmpAdminString,
        cgprsAccPtCacUpStrBandWidthPool SnmpAdminString,
        cgprsAccPtCacDnStrBandWidthPool SnmpAdminString
}

cgprsAccPtCacPolicyName OBJECT-TYPE
    SYNTAX          SnmpAdminString (SIZE  (0..40))
    MAX-ACCESS      read-create
    STATUS          current
    DESCRIPTION
        "This object represents the local policy name that will
        be used by CAC for the PDP's or Bearer's pertaining to
        this APN.

        Details of QoS parameters pertaining to a CAC policy
        are out of scope of this MIB and are covered in
        CISCO-GGSN-QOS-MIB.

        A zero-length string denotes that no policy is
        configured." 
    ::= { cgprsAccPtCacEntry 1 }

cgprsAccPtCacUpStrBandWidthPool OBJECT-TYPE
    SYNTAX          SnmpAdminString (SIZE  (0..40))
    MAX-ACCESS      read-create
    STATUS          current
    DESCRIPTION
        "A Bandwidth pool is a user defined pool with bandwidth
        pre-allocation details like amount of available
        bandwidth, percent of bandwidth available to a specific
        traffic class.  CAC uses this information during PDP or
        Bearer context activation and modification procedures.

        This object represents the name of the bandwidth pool
        used for upstream traffic. Configuration of the
        bandwidth pool is covered in CISCO-GGSN-QOS-MIB.

        A zero-length string denotes that no policy is
        configured." 
    ::= { cgprsAccPtCacEntry 2 }

cgprsAccPtCacDnStrBandWidthPool OBJECT-TYPE
    SYNTAX          SnmpAdminString (SIZE  (0..40))
    MAX-ACCESS      read-create
    STATUS          current
    DESCRIPTION
        "This object represents the name of the bandwidth pool
        used for downstream traffic. Configuration of the
        bandwidth pool is covered in CISCO-GGSN-QOS-MIB.

        A zero-length string denotes that no policy is
        configured." 
    ::= { cgprsAccPtCacEntry 3 }
 

-- Route Probe Configs

cgprsAccPtRouteProbeConfigs  OBJECT IDENTIFIER
    ::= { ciscoGprsAccPtConfig 8 }


cgprsAccPtRouteProbeTable OBJECT-TYPE
    SYNTAX          SEQUENCE OF CgprsAccPtRouteProbeEntry 
    MAX-ACCESS      not-accessible
    STATUS          current
    DESCRIPTION
        "Route probe feature enables the Gateway to send out a route
        probe packet to a configured destination after a
        successful PDP or Bearer activation procedure.  The source IP
        address of the packet would be the IP address of the
        PDP or Bearer context.

        This table represents various parameters set in the
        route probe packet.  At this point, UDP packets will be
        sent, a new column will be added to represent the
        protocol when the support is extended to other
        protocols."
    ::= { cgprsAccPtRouteProbeConfigs 1 }

cgprsAccPtRouteProbeEntry OBJECT-TYPE
    SYNTAX          CgprsAccPtRouteProbeEntry
    MAX-ACCESS      not-accessible
    STATUS          current
    DESCRIPTION
        "An entry in cgprsAccPtRouteProbeTable."
    AUGMENTS           { cgprsAccPtEntry  } 
    ::= { cgprsAccPtRouteProbeTable 1 }

CgprsAccPtRouteProbeEntry ::= SEQUENCE {
        cgprsAccPtRpDestAddrType InetAddressType,
        cgprsAccPtRpDestAddr     InetAddress,
        cgprsAccPtRpProtocol     INTEGER,
        cgprsAccPtRpDestPort     InetPortNumber,
        cgprsAccPtRpTtl          Unsigned32
}

cgprsAccPtRpDestAddrType OBJECT-TYPE
    SYNTAX          InetAddressType
    MAX-ACCESS      read-create
    STATUS          current
    DESCRIPTION
        "This object indicates the type of Internet address by
        which cgprsAccPtRpDestAddr is reachable." 
    ::= { cgprsAccPtRouteProbeEntry 1 }

cgprsAccPtRpDestAddr OBJECT-TYPE
    SYNTAX          InetAddress
    MAX-ACCESS      read-create
    STATUS          current
    DESCRIPTION
        "This object specifies the destination IP address to
        which the route probe packet needs to be sent." 
    ::= { cgprsAccPtRouteProbeEntry 2 }

cgprsAccPtRpProtocol OBJECT-TYPE
    SYNTAX          INTEGER  {
                        udp(1),
                        icmp(2)
                    }
    MAX-ACCESS      read-create
    STATUS          current
    DESCRIPTION
        "This objects specifies the protocol type of route probe
        packet.  This object can be set only after
        cgprsAccPtRpDestAddr is being set."
    DEFVAL          { udp } 
    ::= { cgprsAccPtRouteProbeEntry 3 }

cgprsAccPtRpDestPort OBJECT-TYPE
    SYNTAX          InetPortNumber
    MAX-ACCESS      read-create
    STATUS          current
    DESCRIPTION
        "This object specifies the destination port number of
        the route probe packet when cgprsAccPtRpProtocol is
        set to 'udp'.  This object can be set only after
        cgprsAccPtRpDestAddr is being set."
    DEFVAL          { 9 } 
    ::= { cgprsAccPtRouteProbeEntry 4 }

cgprsAccPtRpTtl OBJECT-TYPE
    SYNTAX          Unsigned32 (1..255)
    UNITS           "seconds"
    MAX-ACCESS      read-create
    STATUS          current
    DESCRIPTION
        "This object specifies the TTL value set in the route
        probe packet.  This object can be set only after
        cgprsAccPtRpDestAddr is being set."
    DEFVAL          { 255 } 
    ::= { cgprsAccPtRouteProbeEntry 5 }
 

-- APN IPv6 Configs

cgprsAccPtIpv6Configs  OBJECT IDENTIFIER
    ::= { ciscoGprsAccPtConfig 9 }


cgprsAccPtIpv6Table OBJECT-TYPE
    SYNTAX          SEQUENCE OF CgprsAccPtIpv6Entry 
    MAX-ACCESS      not-accessible
    STATUS          current
    DESCRIPTION
        "The Gateway supports IPv6 PDP or Bearer type and its user
        traffic. It will provide the IPv6 prefix and interface
        identifier to the MS; generate IPv6 PDP or Bearer address
        in the appropriate charging records and AAA accounting record.

        This table represents various parameters required to 
        support IPv6 PDP or Bearer under APN."
    ::= { cgprsAccPtIpv6Configs 1 }

cgprsAccPtIpv6Entry OBJECT-TYPE
    SYNTAX          CgprsAccPtIpv6Entry
    MAX-ACCESS      not-accessible
    STATUS          current
    DESCRIPTION
        "An entry in cgprsAccPtIpv6Table.

        The agent can create/destroy/modify a profile as a
        result of actions from the local console.  The table
        objects can be modified, when the RowStatus is active.

        The entries in this table are stored in NVRAM when the
        agent writes the configuration to memory before 
        restart."
    AUGMENTS           { cgprsAccPtEntry  } 
    ::= { cgprsAccPtIpv6Table 1 }

CgprsAccPtIpv6Entry ::= SEQUENCE {
        cgprsAccPtIpv6BaseVTemplate     Unsigned32,
        cgprsAccPtIpv6DnsAddrType       InetAddressType,
        cgprsAccPtIpv6DnsPriAddress     InetAddress,
        cgprsAccPtIpv6DnsSecAddress     InetAddress,
        cgprsAccPtIpv6Enable            TruthValue,
        cgprsAccPtIpv6Exclusive         TruthValue,
        cgprsAccPtIpv6AccessGroupDown   AccessControlListName,
        cgprsAccPtIpv6AccessGroupUp     AccessControlListName,
        cgprsAccPtIpv6AddrPool          INTEGER,
        cgprsAccPtIpv6AddrLocalPoolName SnmpAdminString,
        cgprsAccPtIpv6Redirect          INTEGER,
        cgprsAccPtIpv6RedirectAddrType  InetAddressType,
        cgprsAccPtIpv6RedirectAddr      InetAddress,
        cgprsAccPtIpv6SecurityVerifySrc TruthValue,
        cgprsAccPtIpv6SecurityVerifyDst TruthValue,
        cgprsAccPtIpv6AddrAllocations   Gauge32,
        cgprsAccPtDhcpv6ProxClientIntf  InterfaceIndexOrZero,
        cgprsAccptDhcpv6RapidCommit     TruthValue,
        cgprsAccptDhcpv6PoolName        SnmpAdminString
}

cgprsAccPtIpv6BaseVTemplate OBJECT-TYPE
    SYNTAX          Unsigned32
    MAX-ACCESS      read-create
    STATUS          current
    DESCRIPTION
        "This object specifies the base virtual template
        for an APN.  To create a sub-interface for each PDP or
        Bearer, a base virtual-template needs to be configured so
        that virtual-access interface can be cloned from it. Many 
        APN can share one base virtual-template.  But one APN  
        can only use one base virtual-template.

        This object must be set to appropriate value for IPv6 
        APN i.e., when the object cgprsAccPtIpv6Enable or 
        cgprsAccPtIpv6Exclusive is set to 'true'." 
    ::= { cgprsAccPtIpv6Entry 1 }

cgprsAccPtIpv6DnsAddrType OBJECT-TYPE
    SYNTAX          InetAddressType
    MAX-ACCESS      read-create
    STATUS          current
    DESCRIPTION
        "This object specifies the type of
        cgprsAccPtIpv6DnsPriAddress and 
        cgprsAccPtIpv6DnsSecAddress.

        DNS addresses to be sent to the MS can come from DHCP
        server or RADIUS server based on IP address allocation
        scheme chosen by cgprsAccPtIpv6AddrPool.  The IP address
        configured to cgprsAccPtIpv6DnsPriAddress and 
        cgprsAccPtIpv6DnsSecAddress will be sent to MS only when

         - DHCP/RADIUS servers does not return any DNS address.
         - local address pool is used for IP address
           allocation for MS." 
    ::= { cgprsAccPtIpv6Entry 2 }

cgprsAccPtIpv6DnsPriAddress OBJECT-TYPE
    SYNTAX          InetAddress
    MAX-ACCESS      read-create
    STATUS          current
    DESCRIPTION
        "This object specifies the IPv6 address of the primary
        DNS server that will be sent to MS." 
    ::= { cgprsAccPtIpv6Entry 3 }

cgprsAccPtIpv6DnsSecAddress OBJECT-TYPE
    SYNTAX          InetAddress
    MAX-ACCESS      read-create
    STATUS          current
    DESCRIPTION
        "This object specifies the IPv6 address of the secondary
        DNS server that will be sent to MS.  This object can 
        be configured only after configuring the primary DNS
        address(cgprsAccPtIpv6DnsPriAddress)." 
    ::= { cgprsAccPtIpv6Entry 4 }

cgprsAccPtIpv6Enable OBJECT-TYPE
    SYNTAX          TruthValue
    MAX-ACCESS      read-create
    STATUS          current
    DESCRIPTION
        "This object specifies whether the APN supports
        IPv6 PDP or Bearer. 

        The Gateway supports dual stack APN.  Both IPv6 and IPv4 PDP 
        or Bearer can be created for the same APN." 
    ::= { cgprsAccPtIpv6Entry 5 }

cgprsAccPtIpv6Exclusive OBJECT-TYPE
    SYNTAX          TruthValue
    MAX-ACCESS      read-create
    STATUS          current
    DESCRIPTION
        "This object specifies whether the APN supports only
        IPv6 PDPs or Bearers." 
    ::= { cgprsAccPtIpv6Entry 6 }

cgprsAccPtIpv6AccessGroupDown OBJECT-TYPE
    SYNTAX          AccessControlListName
    MAX-ACCESS      read-create
    STATUS          current
    DESCRIPTION
        "This object specifies the name of the access list
        applied to all the traffic received by this APN from 
        the PDN,  for forwarding towards a MS." 
    ::= { cgprsAccPtIpv6Entry 7 }

cgprsAccPtIpv6AccessGroupUp OBJECT-TYPE
    SYNTAX          AccessControlListName
    MAX-ACCESS      read-create
    STATUS          current
    DESCRIPTION
        "This object specifies the name of the access list
        applied to all the traffic received by this APN from
        a MS,  for forwarding towards PDN." 
    ::= { cgprsAccPtIpv6Entry 8 }

cgprsAccPtIpv6AddrPool OBJECT-TYPE
    SYNTAX          INTEGER  {
                        global(1),
                        dhcp(2),
                        disable(3),
                        local(4),
                        radius(5)
                    }
    MAX-ACCESS      read-create
    STATUS          current
    DESCRIPTION
        "This object specifies a dynamic address allocation
        method followed by this access point.

            - 'global', which indicates that no method is
            defined specifically to this access point and the
            DHCP or radius server configured for this Gateway
            under AAA configurations will be used to 
            allocation a dynamic IPv6 address to the user.

            - 'dhcp', which indicates that the DHCP server
            will be used.

            - 'radius', which indicates that the radius server
            will be used.

            - 'disable', which indicates that dynamic address
            allocation is disabled.

            - 'local', indicates that local address pool
            configured on the Gateway is going to be used.
            cgprsAccPtIpv6AddrLocalPoolName denotes the name
            of the corresponding address pool."
    DEFVAL          { global } 
    ::= { cgprsAccPtIpv6Entry 9 }

cgprsAccPtIpv6AddrLocalPoolName OBJECT-TYPE
    SYNTAX          SnmpAdminString
    MAX-ACCESS      read-create
    STATUS          current
    DESCRIPTION
        "This object specifies the name of the local address
        pool used when cgprsAccPtIpv6AddrPool is set to
        'local'." 
    ::= { cgprsAccPtIpv6Entry 10 }

cgprsAccPtIpv6Redirect OBJECT-TYPE
    SYNTAX          INTEGER  {
                        none(0),
                        all(1),
                        intermobile(2)
                    }
    MAX-ACCESS      read-create
    STATUS          current
    DESCRIPTION
        "This object specifies the traffic redirection in an
        APN.

         - 'none', indicates that, traffic will not be 
         redirected i.e., the traffic will get switched through 
         the Gateway without going through any Gi interface. 

         - 'intermobile', when this redirection is active on 
         an APN, before downstream packets exit the Gateway, they
         are screened to see if they come from other GTP 
         tunnels.  If so, packets won't be GTP-tunneled 
         downstream, but will get redirected to the device
         specified by the object cgprsAccPtIpv6RedirectAddr. 

         - 'all', when this redirection is active on an APN, 
         redirect all packets to a specified destination, given
         by the object cgprsAccPtIpv6RedirectAddr, regardless  
         whether the destination address belongs to a MS on the 
         same Gateway or not." 
    ::= { cgprsAccPtIpv6Entry 11 }

cgprsAccPtIpv6RedirectAddrType OBJECT-TYPE
    SYNTAX          InetAddressType
    MAX-ACCESS      read-create
    STATUS          current
    DESCRIPTION
        "This object specifies the type of
        cgprsAccPtIpv6RedirectAddr." 
    ::= { cgprsAccPtIpv6Entry 12 }

cgprsAccPtIpv6RedirectAddr OBJECT-TYPE
    SYNTAX          InetAddress
    MAX-ACCESS      read-create
    STATUS          current
    DESCRIPTION
        "This object specifies the Internet address of the
        device to which traffic will be re-directed." 
    ::= { cgprsAccPtIpv6Entry 13 }

cgprsAccPtIpv6SecurityVerifySrc OBJECT-TYPE
    SYNTAX          TruthValue
    MAX-ACCESS      read-create
    STATUS          current
    DESCRIPTION
        "When this object is set to 'true', the Gateway will check the
        upstream TPDU source address against the address
        previously assigned to this user.  If the addresses are
        different, the TPDU is dropped. This check will enable
        the Gateway to restrict the users with fake identity.

        When the object is set to 'false', the Gateway will not
        perform any checking on the upstream TPDU for the 
        source address."
    DEFVAL          { false } 
    ::= { cgprsAccPtIpv6Entry 14 }

cgprsAccPtIpv6SecurityVerifyDst OBJECT-TYPE
    SYNTAX          TruthValue
    MAX-ACCESS      read-create
    STATUS          current
    DESCRIPTION
        "When this object is set to 'true', the Gateway will check the
        upstream TPDU destination address against the range of
        IP addresses reserved for PLMN devices.  If there is a
        match, the TPDU is dropped. This check would enable 
        the Gateway to protect the GPRS network from some hacker
        who may try to flood the Gateway and PLMN nodes with 
        intense data traffic.

        When the object is set to 'false', the Gateway will not
        perform any checking on the upstream TPDU for the 
        destination address."
    DEFVAL          { false } 
    ::= { cgprsAccPtIpv6Entry 15 }

cgprsAccPtIpv6AddrAllocations OBJECT-TYPE
    SYNTAX          Gauge32
    MAX-ACCESS      read-only
    STATUS          current
    DESCRIPTION
        "This object indicates the total number of IPv6
        addresses currently allocated to user." 
    ::= { cgprsAccPtIpv6Entry 16 }

cgprsAccPtDhcpv6ProxClientIntf OBJECT-TYPE
    SYNTAX          InterfaceIndexOrZero
    MAX-ACCESS      read-create
    STATUS          current
    DESCRIPTION
        "The object indicates the interface index, of the
        interface which is to be used for DHCPv6 request
        multicasting." 
    ::= { cgprsAccPtIpv6Entry 17 }

cgprsAccptDhcpv6RapidCommit OBJECT-TYPE
    SYNTAX          TruthValue
    MAX-ACCESS      read-create
    STATUS          current
    DESCRIPTION
        "This object indicates that whether DHCPv6 rapid-commit
        feature is enabled for this APN." 
    ::= { cgprsAccPtIpv6Entry 18 }

cgprsAccptDhcpv6PoolName OBJECT-TYPE
    SYNTAX          SnmpAdminString (SIZE  (1..255))
    MAX-ACCESS      read-create
    STATUS          current
    DESCRIPTION
        "This object represents the IPV6 DHCP
        pool-name configured for this APN." 
    ::= { cgprsAccPtIpv6Entry 19 }
 

-- APN CSG Group Configs

cgprsAccPtCsgGroupTable OBJECT-TYPE
    SYNTAX          SEQUENCE OF CgprsAccPtCsgGroupEntry 
    MAX-ACCESS      not-accessible
    STATUS          current
    DESCRIPTION
        "This table contains the list of CSG Groups
        configured on this APN."
    ::= { ciscoGprsAccPtConfig 10 }

cgprsAccPtCsgGroupEntry OBJECT-TYPE
    SYNTAX          CgprsAccPtCsgGroupEntry
    MAX-ACCESS      not-accessible
    STATUS          current
    DESCRIPTION
        "An Entry contains the CSG Group name configured
        under the access point entry with index
        cgprsAccPtIndex.
        The agent can create/destroy a CSG group under
        access point."
    INDEX           {
                        cgprsAccPtIndex,
                        cgprsAccPtCsgGroupName
                    } 
    ::= { cgprsAccPtCsgGroupTable 1 }

CgprsAccPtCsgGroupEntry ::= SEQUENCE {
        cgprsAccPtCsgGroupName      SnmpAdminString,
        cgprsAccPtCsgGroupRowStatus RowStatus
}

cgprsAccPtCsgGroupName OBJECT-TYPE
    SYNTAX          SnmpAdminString
    MAX-ACCESS      not-accessible
    STATUS          current
    DESCRIPTION
        "This object specifies CSG Group name to use to
        communicate with the CSG server in an access point
        configuration.

        The value must be same as an entry in cGgsnSACsgTable
        identified by cGgsnSACsgGroupName."
    REFERENCE
        "cGgsnSACsgGroupName is defined in
        CISCO-GGSN-SERVICE-AWARE-MIB." 
    ::= { cgprsAccPtCsgGroupEntry 1 }

cgprsAccPtCsgGroupRowStatus OBJECT-TYPE
    SYNTAX          RowStatus
    MAX-ACCESS      read-create
    STATUS          current
    DESCRIPTION
        "This object is used to create a new row or delete an
        existing row in this table.
        This object must be set to 'creatAndGo' to create 
        an entry and set to 'destroy' to delete an entry.

        The value in any column may be modified any time even the
        value of this entry rowStatus object is 'active'." 
    ::= { cgprsAccPtCsgGroupEntry 2 }
 

-- *********************************************************************
-- Configuration change notification history information
-- *********************************************************************

cgprsAccPtCfgNotifHistTable OBJECT-TYPE
    SYNTAX          SEQUENCE OF CgprsAccPtCfgNotifHistEntry 
    MAX-ACCESS      not-accessible
    STATUS          current
    DESCRIPTION
        "This table contains a history of access point
        configuration change notifications generated by 
        the agent for changes in the access point 
        configuration. 

        The object cgprsAccPtCfgNotifHistMax specifies the 
        maximum number of entries stored in this table. 
        When the table is full, the oldest entries are 
        discarded to make space for new entries."
    ::= { ciscoGprsAccPtCfgNotifInfo 1 }

cgprsAccPtCfgNotifHistEntry OBJECT-TYPE
    SYNTAX          CgprsAccPtCfgNotifHistEntry
    MAX-ACCESS      not-accessible
    STATUS          current
    DESCRIPTION
        "A description of a configuration change in the
        cgprsAccPtTable. A configuration change is said 
        to occur if one of the following happens:

            - An access point has been created. In this 
            case the object cgprsAccPtCfgNotifAccPtIndex
            is set to the index of the access point being
            created and cgprsAccPtCfgNotifReason is 
            set to 'creation'.

            - An access point has been deleted. In this 
            case the object cgprsAccPtCfgNotifAccPtIndex
            is set to the index of the access point being
            deleted and cgprsAccPtCfgNotifReason is
            set to 'deletion'.

            - The configuration of an access point has 
            changed. In this case the object 
            cgprsAccPtCfgNotifAccPtIndex is set to the 
            index of the access point being changed and
            cgprsAccPtCfgNotifReason is set to 
            'modification'. The configuration change of 
            an access point is said to occur if any of the 
            configurable attributes are changed."
    INDEX           { cgprsAccPtCfgNotifIndex } 
    ::= { cgprsAccPtCfgNotifHistTable 1 }

CgprsAccPtCfgNotifHistEntry ::= SEQUENCE {
        cgprsAccPtCfgNotifIndex      Unsigned32,
        cgprsAccPtCfgNotifAccPtIndex Unsigned32,
        cgprsAccPtCfgNotifReason     INTEGER
}

cgprsAccPtCfgNotifIndex OBJECT-TYPE
    SYNTAX          Unsigned32 (1..4294967295)
    MAX-ACCESS      not-accessible
    STATUS          current
    DESCRIPTION
        "An arbitrary non-zero integer value uniquely
        identifying each notification previously sent 
        by the GPRS. This value increases monotonically 
        with each notification sent by the Gateway.

        When it reaches the maximum value, it wraps to 1." 
    ::= { cgprsAccPtCfgNotifHistEntry 1 }

cgprsAccPtCfgNotifAccPtIndex OBJECT-TYPE
    SYNTAX          Unsigned32 (1..65535)
    MAX-ACCESS      read-only
    STATUS          current
    DESCRIPTION
        "This object specifies the access point which has
        been created, changed or modified." 
    ::= { cgprsAccPtCfgNotifHistEntry 2 }

cgprsAccPtCfgNotifReason OBJECT-TYPE
    SYNTAX          INTEGER  {
                        modification(1),
                        creation(2),
                        deletion(3)
                    }
    MAX-ACCESS      read-only
    STATUS          current
    DESCRIPTION
        "This object describes the reason of the notification." 
    ::= { cgprsAccPtCfgNotifHistEntry 3 }
 


-- *********************************************************************
-- System Information
-- *********************************************************************

cgprsAccPtCfgNotifEnable OBJECT-TYPE
    SYNTAX          TruthValue
    MAX-ACCESS      read-write
    STATUS          current
    DESCRIPTION
        "This object controls whether the access point
        notifications, cgprsAccPtMIBNotifications, are
        generated. Note that entries in the
        cgprsAccPtCfgNotifHistTable are generated 
        irrespectively to this object."
    DEFVAL          { false } 
    ::= { ciscoGprsAccPtCfgNotifInfo 2 }

cgprsAccPtCfgNotifHistMax OBJECT-TYPE
    SYNTAX          Unsigned32 (1..5000)
    MAX-ACCESS      read-write
    STATUS          current
    DESCRIPTION
        "The maximum size of the event history table,
        cgprsAccPtCfgNotifHistTable.

        When the table is full, the oldest entries are 
        removed to make space for new entries."
    DEFVAL          { 200 } 
    ::= { ciscoGprsAccPtCfgNotifInfo 3 }

cgprsAccPtCfgNotifLatestIndex OBJECT-TYPE
    SYNTAX          Unsigned32 (1..4294967295)
    MAX-ACCESS      read-only
    STATUS          current
    DESCRIPTION
        "The value of cgprsAccPtCfgNotifIndex for the most
        recently created entry in cgprsAccPtCfgNotifHistTable." 
    ::= { ciscoGprsAccPtCfgNotifInfo 4 }
-- *********************************************************************
-- Statistics
-- *********************************************************************

cgprsAccPtStatisticsTable OBJECT-TYPE
    SYNTAX          SEQUENCE OF CgprsAccPtStatisticsEntry 
    MAX-ACCESS      not-accessible
    STATUS          current
    DESCRIPTION
        "This table contains the performance statistics of
        each APN on this Gateway."
    ::= { ciscoGprsAccPtStatistics 1 }

cgprsAccPtStatisticsEntry OBJECT-TYPE
    SYNTAX          CgprsAccPtStatisticsEntry
    MAX-ACCESS      not-accessible
    STATUS          current
    DESCRIPTION
        "Entry for each APN in statistics table."
    AUGMENTS           { cgprsAccPtEntry  } 
    ::= { cgprsAccPtStatisticsTable 1 }

CgprsAccPtStatisticsEntry ::= SEQUENCE {
        cgprsAccPtMsActivatedPdps                     Counter32,
        cgprsAccPtSuccMsActivatedPdps                 Counter32,
        cgprsAccPtMsActivatedDynPdps                  Counter32,
        cgprsAccPtSuccMsActivatedDynPdps              Counter32,
        cgprsAccPtMsDeactivatedPdps                   Counter32,
        cgprsAccPtSuccMsDeactivatedPdps               Counter32,
        cgprsAccPtNetworkInitPdps                     Counter32,
        cgprsAccPtSuccNetworkInitPdps                 Counter32,
        cgprsAccPtGgsnDeactivatedPdps                 Counter32,
        cgprsAccPtSuccGgsDeactivatedPdps              Counter32,
        cgprsAccPtActivePdps                          Gauge32,
        cgprsAccPtUpstreamTrafficVol                  Counter32,
        cgprsAccPtDownstreamTrafficVol                Counter32,
        cgprsAccPtSourceAddrViolTpdus                 Counter32,
        cgprsAccPtDestAddrViolTpdus                   Counter32,
        cgprsAccPtRedirInterMobilTraffic              Counter32,
        cgprsAccPtRevUpstreamTrafficVol               Counter64,
        cgprsAccPtRevDownstrTrafficVol                Counter64,
        cgprsAccPtUpstreamPacketCount                 Counter32,
        cgprsAccPtDownstreamPacketCount               Counter32,
        cgprsAccPtDhcpAddrRequests                    Counter32,
        cgprsAccPtSuccDhcpAddrRequests                Counter32,
        cgprsAccPtDhcpAddrReleases                    Counter32,
        cgprsAccPtIpv6MsActivatedPdps                 Counter32,
        cgprsAccPtIpv6MsSuccActivatedPdps             Counter32,
        cgprsAccPtIpv6NetworkInitDeactPdps            Counter32,
        cgprsAccPtIpv6NetworkInitDeactSuccPdps        Counter32,
        cgprsAccPtIpv6MsActivatedDynPdps              Counter32,
        cgprsAccPtIpv6MsSuccActivatedDynPdps          Counter32,
        cgprsAccPtIpv6MsDeactivatedPdps               Counter32,
        cgprsAccPtIpv6MsSuccDeactivatedPdps           Counter32,
        cgprsAccPtIpv6GgsnDeactivatedPdps             Counter32,
        cgprsAccPtIpv6GgsnSuccDeactivatedPdps         Counter32,
        cgprsAccPtIpv6UpstreamTrafficVolume           Counter64,
        cgprsAccPtIpv6DownstreamTrafficVolume         Counter64,
        cgprsAccPtIpv6UpstreamPackets                 Counter32,
        cgprsAccPtIpv6DownstreamPackets               Counter32,
        cgprsAccPtPdpUpdateReqSent                    Counter32,
        cgprsAccPtSuccPdpUpdateResRcvd                Counter32,
        cgprsAccPtCoaRcvd                             Counter32,
        cgprsAccPtCoaSuccess                          Counter32,
        cgprsAccPtDtEnabled                           Counter32,
        cgprsAccPtTotalBearers                        Counter32,
        cgprsAccPtTotRmtInitCreateBearers             Counter32,
        cgprsAccPtSuccRmtInitCreateBearers            Counter32,
        cgprsAccPtNetworkInitDeleteBearers            Counter32,
        cgprsAccPtTotRmtInitModifyBearers             Counter32,
        cgprsAccPtSuccRmtInitModifyBearers            Counter32,
        cgprsAccPtTotNetworkInitUpdateBearers         Counter32,
        cgprsAccPtSuccNetworkInitUpdateBearers        Counter32,
        cgprsAccPtTotNetworkInitCreateDedBearers      Counter32,
        cgprsAccPtSuccNetworkInitCreateDedBearers     Counter32,
        cgprsAccPtTotNetworkInitCreateIPv6DedBearers  Counter32,
        cgprsAccPtSuccNetworkInitCreateIPv6DedBearers Counter32,
        cgprsAccPtv4v6MsActivatedPdps                 Counter32,
        cgprsAccPtv4v6SuccMsActivatedPdps             Counter32,
        cgprsAccPtv4v6MsDeactivatedPdps               Counter32,
        cgprsAccPtv4v6SuccMsDeactivatedPdps           Counter32,
        cgprsAccPtv4v6ActDedbearerPdps                Counter32,
        cgprsAccPtv4v6SuccActDedbearerPdps            Counter32,
        cgprsAccPtDhcpProxServDiscover                Counter32,
        cgprsAccPtDhcpProxServRequest                 Counter32,
        cgprsAccPtDhcpProxServDeclines                Counter32,
        cgprsAccPtDhcpProxServRelease                 Counter32,
        cgprsAccPtDhcpProxServOffer                   Counter32,
        cgprsAccPtDhcpProxServAcks                    Counter32,
        cgprsAccPtDhcpProxServNaks                    Counter32,
        cgprsAccPtDhcpProxServInform                  Counter32,
        cgprsAccPtDhcpProxServUnknowMsg               Counter32,
        cgprsAccPtDhcpProxServRetryDrops              Counter32,
        cgprsAccPtDhcpProxServErrDrops                Counter32,
        cgprsAccPtActiveBearers                       Gauge32,
        cgprsAccPtDhcpProxServTxErrDrops              Counter32,
        cgprsAccPtDhcpProxServIpAllocErr              Counter32,
        cgprsAccPtDedBearerDeactivations              Counter32,
        cgprsAccPtDedBearerQosUpdate                  Counter32,
        cgprsAccPtDedBearerSucQosUpdate               Counter32,
        cgprsAccPtDedBearerNoQosUpdate                Counter32,
        cgprsAccPtDedBearerSucNoQosUpdate             Counter32,
        cgprsAccPtIpv4v6MsActivatedDynamicPdps        Counter32,
        cgprsAccPtIpv4v6MsSuccActivatedDynamicPdps    Counter32,
        cgprsAccPtFailMsActivatedPdps                 Counter32,
        cgprsAccPtFailPdpUpdate                       Counter32,
        cgprsAccPtUpdateRspTimeOut                    Counter32
}

cgprsAccPtMsActivatedPdps OBJECT-TYPE
    SYNTAX          Counter32
    MAX-ACCESS      read-only
    STATUS          current
    DESCRIPTION
        "This object indicates the total number of PDP or Bearer
        context activation procedures initiated by any MS on this APN.

        Trigger Condition: This counter is triggered by create
        PDP or Bearer request message."
    REFERENCE
        "GSM 12.04: Digital cellular telecommunications
        system (Phase 2+); Performance data measurements,
        Section: B.9.1.1." 
    ::= { cgprsAccPtStatisticsEntry 1 }

cgprsAccPtSuccMsActivatedPdps OBJECT-TYPE
    SYNTAX          Counter32
    MAX-ACCESS      read-only
    STATUS          current
    DESCRIPTION
        "This object indicates the total number of successfully
        completed PDP or Bearer context activation procedures initiated
        by MS on this APN.

        Trigger Condition: This counter is triggered by create
        PDP or Bearer request message."
    REFERENCE
        "GSM 12.04: Digital cellular telecommunications
        system (Phase 2+); Performance data measurements,
        Section: B.9.1.2." 
    ::= { cgprsAccPtStatisticsEntry 2 }

cgprsAccPtMsActivatedDynPdps OBJECT-TYPE
    SYNTAX          Counter32
    MAX-ACCESS      read-only
    STATUS          current
    DESCRIPTION
        "This object indicates the total number of dynamic
        PDP or Bearer context activation procedures initiated by the 
        MS on this APN.  When a MS requests dynamic PDP or Bearer
        address from the PLMN, a dynamic PDP or Bearer context
        activation procedure is initiated.

        Trigger Condition: This counter is triggered by a request
        message to create a PDP or Bearer context."
    REFERENCE
        "GSM 12.04: Digital cellular telecommunications
        system (Phase 2+); Performance data measurements,
        Section: B.9.1.3." 
    ::= { cgprsAccPtStatisticsEntry 3 }

cgprsAccPtSuccMsActivatedDynPdps OBJECT-TYPE
    SYNTAX          Counter32
    MAX-ACCESS      read-only
    STATUS          current
    DESCRIPTION
        "This object indicates the total number of successfully
        completed dynamic PDP or Bearer context activation procedures 
        initiated by MS on this APN.

        Trigger Condition: This counter is triggered by a request
        message to create a PDP or Bearer context."
    REFERENCE
        "GSM 12.04: Digital cellular telecommunications
        system (Phase 2+); Performance data measurements,
        Section: B.9.1.4." 
    ::= { cgprsAccPtStatisticsEntry 4 }

cgprsAccPtMsDeactivatedPdps OBJECT-TYPE
    SYNTAX          Counter32
    MAX-ACCESS      read-only
    STATUS          current
    DESCRIPTION
        "This object indicates the total number of PDP
        or Bearer context deactivation procedures initiated by the 
        MS on this APN.

        Trigger Condition: This counter is triggered by a request
        message to delete PDP or Bearer context."
    REFERENCE
        "GSM 12.04: Digital cellular telecommunications
        system (Phase 2+); Performance data measurements,
        Section: B.9.1.5." 
    ::= { cgprsAccPtStatisticsEntry 5 }

cgprsAccPtSuccMsDeactivatedPdps OBJECT-TYPE
    SYNTAX          Counter32
    MAX-ACCESS      read-only
    STATUS          current
    DESCRIPTION
        "This object indicates the total number of
        successfully completed PDP or Bearer context deactivation 
        procedures initiated by the MS.

        Trigger Condition: This counter is triggered by a request
        message to delete PDP or Bearer context."
    REFERENCE
        "GSM 12.04: Digital cellular telecommunications
        system (Phase 2+); Performance data measurements,
        Section: B.9.1.6." 
    ::= { cgprsAccPtStatisticsEntry 6 }

cgprsAccPtNetworkInitPdps OBJECT-TYPE
    SYNTAX          Counter32
    MAX-ACCESS      read-only
    STATUS          current
    DESCRIPTION
        "This object indicates the total number of network
        initiated PDP or Bearer context activation procedures.

        Trigger Condition: This counter is triggered by a request
        message to create PDP or Bearer context." 
    ::= { cgprsAccPtStatisticsEntry 7 }

cgprsAccPtSuccNetworkInitPdps OBJECT-TYPE
    SYNTAX          Counter32
    MAX-ACCESS      read-only
    STATUS          current
    DESCRIPTION
        "This object indicates the total number of
        successfully completed network initiated PDP 
        or Bearer context activation procedures.

        Trigger Condition: This counter is triggered by a request
        message to create PDP or Bearer context." 
    ::= { cgprsAccPtStatisticsEntry 8 }

cgprsAccPtGgsnDeactivatedPdps OBJECT-TYPE
    SYNTAX          Counter32
    MAX-ACCESS      read-only
    STATUS          current
    DESCRIPTION
        "This object indicates the total number of PDP
        context deactivation procedures initiated by the 
        Gateway.

        Trigger Condition: This counter is triggered by delete
        PDP request message."
    REFERENCE
        "GSM 12.04: Digital cellular telecommunications
        system (Phase 2+); Performance data measurements,
        Section: B.9.1.7." 
    ::= { cgprsAccPtStatisticsEntry 9 }

cgprsAccPtSuccGgsDeactivatedPdps OBJECT-TYPE
    SYNTAX          Counter32
    MAX-ACCESS      read-only
    STATUS          current
    DESCRIPTION
        "This object indicates the total number of
        successfully completed PDP context deactivation 
        procedures initiated by the Gateway.

        Trigger Condition: This counter is triggered by delete
        PDP request message."
    REFERENCE
        "GSM 12.04: Digital cellular telecommunications
        system (Phase 2+); Performance data measurements,
        Section: B.9.1.8." 
    ::= { cgprsAccPtStatisticsEntry 10 }

cgprsAccPtActivePdps OBJECT-TYPE
    SYNTAX          Gauge32
    MAX-ACCESS      read-only
    STATUS          current
    DESCRIPTION
        "This object indicates the current number of active
        PDP or Bearer contexts on this APN.

        Trigger Condition: This counter is incremented/
        decremented by a request message to create/delete
        PDP or Bearer context respectively."
    REFERENCE
        "GSM 12.04: Digital cellular telecommunications
        system (Phase 2+); Performance data measurements,
        Section: B.9.1.9." 
    ::= { cgprsAccPtStatisticsEntry 11 }

cgprsAccPtUpstreamTrafficVol OBJECT-TYPE
    SYNTAX          Counter32
    UNITS           "bytes"
    MAX-ACCESS      read-only
    STATUS          deprecated
    DESCRIPTION
        "This object indicates the total payload volume in
        upstream traffic.  Data flow from MS to PDN is 
        considered to be upstream traffic.

        This object is deprecated by
        cgprsAccPtRevUpstreamTrafficVol." 
    ::= { cgprsAccPtStatisticsEntry 12 }

cgprsAccPtDownstreamTrafficVol OBJECT-TYPE
    SYNTAX          Counter32
    UNITS           "bytes"
    MAX-ACCESS      read-only
    STATUS          deprecated
    DESCRIPTION
        "This object indicates the total payload volume in
        downstream traffic.  Data flow from PDN to MS is 
        considered as downstream traffic.

        This object is deprecated by
        cgprsAccPtRevDownstrTrafficVol." 
    ::= { cgprsAccPtStatisticsEntry 13 }

cgprsAccPtSourceAddrViolTpdus OBJECT-TYPE
    SYNTAX          Counter32
    UNITS           "packets"
    MAX-ACCESS      read-only
    STATUS          current
    DESCRIPTION
        "This object indicates the total number of upstream
        TPDU's that have been dropped due to source address 
        violation as specified by 
        cgprsAccPtVerifyUpStrTpduSrcAddr." 
    ::= { cgprsAccPtStatisticsEntry 14 }

cgprsAccPtDestAddrViolTpdus OBJECT-TYPE
    SYNTAX          Counter32
    UNITS           "packets"
    MAX-ACCESS      read-only
    STATUS          current
    DESCRIPTION
        "This object indicates the total number of upstream
        TPDU's that have been dropped due to destination
        address violation as specified by
        cgprsAccPtVerifyUpStrTpduDstAddr." 
    ::= { cgprsAccPtStatisticsEntry 15 }

cgprsAccPtRedirInterMobilTraffic OBJECT-TYPE
    SYNTAX          Counter32
    UNITS           "packets"
    MAX-ACCESS      read-only
    STATUS          current
    DESCRIPTION
        "This object represents the total number of packets,
        pertaining to inter mobile communication, that have 
        been redirected to device specified by
        cgprsAccPtRedirInterMobilAddr." 
    ::= { cgprsAccPtStatisticsEntry 16 }

cgprsAccPtRevUpstreamTrafficVol OBJECT-TYPE
    SYNTAX          Counter64
    UNITS           "bytes"
    MAX-ACCESS      read-only
    STATUS          current
    DESCRIPTION
        "This object indicates the total payload volume in
        upstream traffic.  Data flow from MS to PDN is
        considered to be upstream traffic.

        Trigger Condition: This counter is triggered when
        upstream traffic is being routed to PDN." 
    ::= { cgprsAccPtStatisticsEntry 17 }

cgprsAccPtRevDownstrTrafficVol OBJECT-TYPE
    SYNTAX          Counter64
    UNITS           "bytes"
    MAX-ACCESS      read-only
    STATUS          current
    DESCRIPTION
        "This object indicates the total payload volume in
        downstream traffic.  Data flow from PDN to MS is
        considered as downstream traffic.

        Trigger Condition: This counter is triggered when
        downstream traffic is being routed to PDN." 
    ::= { cgprsAccPtStatisticsEntry 18 }

cgprsAccPtUpstreamPacketCount OBJECT-TYPE
    SYNTAX          Counter32
    UNITS           "packets"
    MAX-ACCESS      read-only
    STATUS          current
    DESCRIPTION
        "This object represents the total number of upstream
        packets sent on this APN.  Data flow from MS to PDN is
        considered to be upstream traffic.

        Trigger Condition: This counter is triggered when
        upstream traffic is being routed to PDN." 
    ::= { cgprsAccPtStatisticsEntry 19 }

cgprsAccPtDownstreamPacketCount OBJECT-TYPE
    SYNTAX          Counter32
    UNITS           "packets"
    MAX-ACCESS      read-only
    STATUS          current
    DESCRIPTION
        "This object represents the total number of downstream
        packets sent on this APN.  Data flow from PDN to MS is
        considered to be downstream traffic.

        Trigger Condition: This counter is triggered when
        downstream traffic is being routed to PDN." 
    ::= { cgprsAccPtStatisticsEntry 20 }

cgprsAccPtDhcpAddrRequests OBJECT-TYPE
    SYNTAX          Counter32
    UNITS           "packets"
    MAX-ACCESS      read-only
    STATUS          current
    DESCRIPTION
        "This object represents the total number of DHCP
        address request sent by the Gateway on this APN.

        Trigger Condition: This counter is triggered by create
        PDP or Bearer request message." 
    ::= { cgprsAccPtStatisticsEntry 21 }

cgprsAccPtSuccDhcpAddrRequests OBJECT-TYPE
    SYNTAX          Counter32
    UNITS           "packets"
    MAX-ACCESS      read-only
    STATUS          current
    DESCRIPTION
        "This object represents the total number of successful
        DHCP address request sent by the Gateway on this APN.

        Trigger Condition: This counter is triggered by create
        PDP or Bearer request message." 
    ::= { cgprsAccPtStatisticsEntry 22 }

cgprsAccPtDhcpAddrReleases OBJECT-TYPE
    SYNTAX          Counter32
    UNITS           "packets"
    MAX-ACCESS      read-only
    STATUS          current
    DESCRIPTION
        "This object represents the total number of DHCP
        address release request sent by the Gateway on this APN.

        Trigger Condition: This counter is triggered by delete
        PDP or Bearer request message." 
    ::= { cgprsAccPtStatisticsEntry 23 }

cgprsAccPtIpv6MsActivatedPdps OBJECT-TYPE
    SYNTAX          Counter32
    MAX-ACCESS      read-only
    STATUS          current
    DESCRIPTION
        "This object indicates the total number of IPv6 PDP
        or Bearer context activation procedures initiated by any MS on
        this APN.

        Trigger Condition: This counter is triggered by a request
        message to create PDP or Bearer context." 
    ::= { cgprsAccPtStatisticsEntry 24 }

cgprsAccPtIpv6MsSuccActivatedPdps OBJECT-TYPE
    SYNTAX          Counter32
    MAX-ACCESS      read-only
    STATUS          current
    DESCRIPTION
        "This object indicates the total number of successfully
        completed IPv6 PDP or Bearer context activation procedures 
        initiated by MS on this APN.

        Trigger Condition: This counter is triggered by create
        PDP or Bearer response message sent by the Gateway." 
    ::= { cgprsAccPtStatisticsEntry 25 }

cgprsAccPtIpv6NetworkInitDeactPdps OBJECT-TYPE
    SYNTAX          Counter32
    MAX-ACCESS      read-only
    STATUS          current
    DESCRIPTION
        "This object indicates the total number of IPv6 PDP
        or Bearer context deactivation procedures initiated by network.

        Trigger Condition: This counter is triggered by delete 
        PDP or Bearer request message by network." 
    ::= { cgprsAccPtStatisticsEntry 26 }

cgprsAccPtIpv6NetworkInitDeactSuccPdps OBJECT-TYPE
    SYNTAX          Counter32
    MAX-ACCESS      read-only
    STATUS          current
    DESCRIPTION
        "This object indicates the total number of
        successfully completed IPv6 PDP or Bearer context deactivation
        procedures initiated by the network on this APN.

        Trigger Condition: This counter is triggered by delete 
        PDP or Bearer response message by network." 
    ::= { cgprsAccPtStatisticsEntry 27 }

cgprsAccPtIpv6MsActivatedDynPdps OBJECT-TYPE
    SYNTAX          Counter32
    MAX-ACCESS      read-only
    STATUS          current
    DESCRIPTION
        "This object indicates the total number of dynamic IPv6
        PDP or Bearer context activation procedures initiated by the MS
        on this APN.  When a MS requests dynamic PDP or Bearer address 
        from the PLMN, a dynamic PDP or Bearer context activation 
        procedure is initiated.

        Trigger Condition: This counter is triggered by create
        PDP or Bearer request message, received by Gateway from an MS." 
    ::= { cgprsAccPtStatisticsEntry 28 }

cgprsAccPtIpv6MsSuccActivatedDynPdps OBJECT-TYPE
    SYNTAX          Counter32
    MAX-ACCESS      read-only
    STATUS          current
    DESCRIPTION
        "This object indicates the total number of successfully
        completed dynamic IPv6 PDP or Bearer context activation
        procedures initiated by MS on this APN.

        Trigger Condition: This counter is triggered by create
        PDP or Bearer response message." 
    ::= { cgprsAccPtStatisticsEntry 29 }

cgprsAccPtIpv6MsDeactivatedPdps OBJECT-TYPE
    SYNTAX          Counter32
    MAX-ACCESS      read-only
    STATUS          current
    DESCRIPTION
        "This object indicates the total number of IPv6 PDP
        or Bearer context deactivation procedures initiated by the
        MS on this APN.

        Trigger Condition: This counter is triggered by delete
        PDP or Bearer request message." 
    ::= { cgprsAccPtStatisticsEntry 30 }

cgprsAccPtIpv6MsSuccDeactivatedPdps OBJECT-TYPE
    SYNTAX          Counter32
    MAX-ACCESS      read-only
    STATUS          current
    DESCRIPTION
        "This object indicates the total number of
        successfully completed IPv6 PDP or Bearer context deactivation
        procedures initiated by the MS on this APN.

        Trigger Condition: This counter is triggered by delete
        PDP or Bearer context response message." 
    ::= { cgprsAccPtStatisticsEntry 31 }

cgprsAccPtIpv6GgsnDeactivatedPdps OBJECT-TYPE
    SYNTAX          Counter32
    MAX-ACCESS      read-only
    STATUS          current
    DESCRIPTION
        "This object indicates the total number of IPv6 PDP
        context deactivation procedures initiated by the
        Gateway on this APN.

        Trigger Condition: This counter is triggered by delete
        PDP request message, sent by the Gateway to a MME or  SGSN." 
    ::= { cgprsAccPtStatisticsEntry 32 }

cgprsAccPtIpv6GgsnSuccDeactivatedPdps OBJECT-TYPE
    SYNTAX          Counter32
    MAX-ACCESS      read-only
    STATUS          current
    DESCRIPTION
        "This object indicates the total number of
        successfully completed IPv6 PDP context deactivation
        procedures initiated by the Gateway on this APN.

        Trigger Condition: This counter is triggered by delete
        PDP response message, received by the Gateway from a
        MME or SGSN." 
    ::= { cgprsAccPtStatisticsEntry 33 }

cgprsAccPtIpv6UpstreamTrafficVolume OBJECT-TYPE
    SYNTAX          Counter64
    UNITS           "bytes"
    MAX-ACCESS      read-only
    STATUS          current
    DESCRIPTION
        "This object indicates the total payload volume in
        upstream traffic sent on this APN.  Data flow from 
        MS to PDN is considered to be upstream traffic.

        Trigger Condition: This counter is triggered when
        upstream traffic is being routed to PDN." 
    ::= { cgprsAccPtStatisticsEntry 34 }

cgprsAccPtIpv6DownstreamTrafficVolume OBJECT-TYPE
    SYNTAX          Counter64
    UNITS           "bytes"
    MAX-ACCESS      read-only
    STATUS          current
    DESCRIPTION
        "This object indicates the total payload volume in
        downstream traffic sent on this APN.  Data flow from 
        PDN to MS is considered as downstream traffic.

        Trigger Condition: This counter is triggered when
        downstream traffic is being routed to PDN." 
    ::= { cgprsAccPtStatisticsEntry 35 }

cgprsAccPtIpv6UpstreamPackets OBJECT-TYPE
    SYNTAX          Counter32
    UNITS           "packets"
    MAX-ACCESS      read-only
    STATUS          current
    DESCRIPTION
        "This object indicates the total number of upstream
        packets sent on this APN.  Data flow from MS to PDN is
        considered to be upstream traffic.

        Trigger Condition: This counter is triggered when
        upstream traffic is being routed to PDN." 
    ::= { cgprsAccPtStatisticsEntry 36 }

cgprsAccPtIpv6DownstreamPackets OBJECT-TYPE
    SYNTAX          Counter32
    UNITS           "packets"
    MAX-ACCESS      read-only
    STATUS          current
    DESCRIPTION
        "This object represents the total number of downstream
        packets sent on this APN.  Data flow from PDN to MS is
        considered to be downstream traffic.

        Trigger Condition: This counter is triggered when
        downstream traffic is being routed to PDN." 
    ::= { cgprsAccPtStatisticsEntry 37 }

cgprsAccPtPdpUpdateReqSent OBJECT-TYPE
    SYNTAX          Counter32
    UNITS           "messages"
    MAX-ACCESS      read-only
    STATUS          current
    DESCRIPTION
        "This object represents the total number of PDP
        or Bearer context update requests sent on this APN.

        Trigger Condition: This counter is triggered when a
        PDP or Bearer context update request is initiated." 
    ::= { cgprsAccPtStatisticsEntry 38 }

cgprsAccPtSuccPdpUpdateResRcvd OBJECT-TYPE
    SYNTAX          Counter32
    UNITS           "messages"
    MAX-ACCESS      read-only
    STATUS          current
    DESCRIPTION
        "This object represents the total number of successful
        PDP or Bearer context update responses received with a cause
        value 'Request accepted' for the initiated update
        requests on this APN.

        Trigger condition: This counter is triggered when a 
        update response with cause value 'Request accepted' is
        received on this APN." 
    ::= { cgprsAccPtStatisticsEntry 39 }

cgprsAccPtCoaRcvd OBJECT-TYPE
    SYNTAX          Counter32
    UNITS           "messages"
    MAX-ACCESS      read-only
    STATUS          current
    DESCRIPTION
        "This object represents the total number of Change of
        Authorization (COA) messages received on this APN.
        Trigger condition: This counter is triggered when a COA
        message is received." 
    ::= { cgprsAccPtStatisticsEntry 40 }

cgprsAccPtCoaSuccess OBJECT-TYPE
    SYNTAX          Counter32
    UNITS           "messages"
    MAX-ACCESS      read-only
    STATUS          current
    DESCRIPTION
        "This object represents the number of COA messages
        that were acknowledged by the Gateway with a COA ACK. 

        Trigger condition: This counter is triggered when a
        COA ACK is sent by the Gateway." 
    ::= { cgprsAccPtStatisticsEntry 41 }

cgprsAccPtDtEnabled OBJECT-TYPE
    SYNTAX          Counter32
    UNITS           "pdps"
    MAX-ACCESS      read-only
    STATUS          current
    DESCRIPTION
        "This object represents the number of times Direct
        tunnel is enabled for the PDP contexts on this APN
        in Gateway." 
    ::= { cgprsAccPtStatisticsEntry 42 }

cgprsAccPtTotalBearers OBJECT-TYPE
    SYNTAX          Counter32
    MAX-ACCESS      read-only
    STATUS          current
    DESCRIPTION
        "This object indicates the total number of Bearers
        in this APN." 
    ::= { cgprsAccPtStatisticsEntry 43 }

cgprsAccPtTotRmtInitCreateBearers OBJECT-TYPE
    SYNTAX          Counter32
    MAX-ACCESS      read-only
    STATUS          current
    DESCRIPTION
        "This object indicates the total number of Bearer
        creation initiated by MME, SGSN or MS." 
    ::= { cgprsAccPtStatisticsEntry 44 }

cgprsAccPtSuccRmtInitCreateBearers OBJECT-TYPE
    SYNTAX          Counter32
    MAX-ACCESS      read-only
    STATUS          current
    DESCRIPTION
        "This object indicates the total number of successful
        Bearer creation initiated by MME, SGSN or MS." 
    ::= { cgprsAccPtStatisticsEntry 45 }

cgprsAccPtNetworkInitDeleteBearers OBJECT-TYPE
    SYNTAX          Counter32
    MAX-ACCESS      read-only
    STATUS          current
    DESCRIPTION
        "This object indicates the total number of Bearer
        delete initiated by network." 
    ::= { cgprsAccPtStatisticsEntry 46 }

cgprsAccPtTotRmtInitModifyBearers OBJECT-TYPE
    SYNTAX          Counter32
    MAX-ACCESS      read-only
    STATUS          current
    DESCRIPTION
        "This object indicates the total number of Bearer
        modify initiated by MME or SGSN." 
    ::= { cgprsAccPtStatisticsEntry 47 }

cgprsAccPtSuccRmtInitModifyBearers OBJECT-TYPE
    SYNTAX          Counter32
    MAX-ACCESS      read-only
    STATUS          current
    DESCRIPTION
        "This object indicates the total number of successful
        Bearer modify initiated by MME or SGSN." 
    ::= { cgprsAccPtStatisticsEntry 48 }

cgprsAccPtTotNetworkInitUpdateBearers OBJECT-TYPE
    SYNTAX          Counter32
    MAX-ACCESS      read-only
    STATUS          current
    DESCRIPTION
        "This object indicates the total number of Bearer
        update initiated by network." 
    ::= { cgprsAccPtStatisticsEntry 49 }

cgprsAccPtSuccNetworkInitUpdateBearers OBJECT-TYPE
    SYNTAX          Counter32
    MAX-ACCESS      read-only
    STATUS          current
    DESCRIPTION
        "This object indicates the total number of successful
        Bearer update initiated by network." 
    ::= { cgprsAccPtStatisticsEntry 50 }

cgprsAccPtTotNetworkInitCreateDedBearers OBJECT-TYPE
    SYNTAX          Counter32
    MAX-ACCESS      read-only
    STATUS          current
    DESCRIPTION
        "This object indicates the total number of dedicated
        Bearer creation initiated by network." 
    ::= { cgprsAccPtStatisticsEntry 51 }

cgprsAccPtSuccNetworkInitCreateDedBearers OBJECT-TYPE
    SYNTAX          Counter32
    MAX-ACCESS      read-only
    STATUS          current
    DESCRIPTION
        "This object indicates the total number of successful
        dedicated Bearer creation initiated by network." 
    ::= { cgprsAccPtStatisticsEntry 52 }

cgprsAccPtTotNetworkInitCreateIPv6DedBearers OBJECT-TYPE
    SYNTAX          Counter32
    MAX-ACCESS      read-only
    STATUS          current
    DESCRIPTION
        "This object indicates the total number of IPv6
        dedicated Bearer creation initiated by network." 
    ::= { cgprsAccPtStatisticsEntry 53 }

cgprsAccPtSuccNetworkInitCreateIPv6DedBearers OBJECT-TYPE
    SYNTAX          Counter32
    MAX-ACCESS      read-only
    STATUS          current
    DESCRIPTION
        "This object indicates the total number of IPv6
        dedicated Bearer creation initiated by network." 
    ::= { cgprsAccPtStatisticsEntry 54 }

cgprsAccPtv4v6MsActivatedPdps OBJECT-TYPE
    SYNTAX          Counter32
    MAX-ACCESS      read-only
    STATUS          current
    DESCRIPTION
        "This object indicates the total number of IPv4v6 PDP
        or Bearer context activation procedures initiated by any MS on 
        this APN." 
    ::= { cgprsAccPtStatisticsEntry 55 }

cgprsAccPtv4v6SuccMsActivatedPdps OBJECT-TYPE
    SYNTAX          Counter32
    MAX-ACCESS      read-only
    STATUS          current
    DESCRIPTION
        "This object indicates the total number of successfully
        completed IPv4v6 PDP or Bearer context activation procedures 
        initiated by MS on this APN." 
    ::= { cgprsAccPtStatisticsEntry 56 }

cgprsAccPtv4v6MsDeactivatedPdps OBJECT-TYPE
    SYNTAX          Counter32
    MAX-ACCESS      read-only
    STATUS          current
    DESCRIPTION
        "This object indicates the total number of IPv4v6 PDP
        or Bearer context deactivation procedures initiated by the
        MS on this APN." 
    ::= { cgprsAccPtStatisticsEntry 57 }

cgprsAccPtv4v6SuccMsDeactivatedPdps OBJECT-TYPE
    SYNTAX          Counter32
    MAX-ACCESS      read-only
    STATUS          current
    DESCRIPTION
        "This object indicates the total number of
        successfully completed IPv4v6 PDP or Bearer context
        deactivation procedures initiated by the MS on this APN." 
    ::= { cgprsAccPtStatisticsEntry 58 }

cgprsAccPtv4v6ActDedbearerPdps OBJECT-TYPE
    SYNTAX          Counter32
    MAX-ACCESS      read-only
    STATUS          current
    DESCRIPTION
        "This object indicates the total number of IPv4v6, dedicated
        Bearer activations that were initiated by the PGW on this APN." 
    ::= { cgprsAccPtStatisticsEntry 59 }

cgprsAccPtv4v6SuccActDedbearerPdps OBJECT-TYPE
    SYNTAX          Counter32
    MAX-ACCESS      read-only
    STATUS          current
    DESCRIPTION
        "This object indicates the total number of IPv4v6 dedicated
        Bearers that were successfully activated by the PGW." 
    ::= { cgprsAccPtStatisticsEntry 60 }

cgprsAccPtDhcpProxServDiscover OBJECT-TYPE
    SYNTAX          Counter32
    MAX-ACCESS      read-only
    STATUS          current
    DESCRIPTION
        "This object represents the number of DHCP Discover messages
        received by the Gateway.

        The UE sends this message upon bootup/lease rebinding timer
        expiry." 
    ::= { cgprsAccPtStatisticsEntry 61 }

cgprsAccPtDhcpProxServRequest OBJECT-TYPE
    SYNTAX          Counter32
    MAX-ACCESS      read-only
    STATUS          current
    DESCRIPTION
        "This object represents the number of DHCP request messages
        received by the Gateway.

        The UE may send the DHCP-Request message with
        Requested-IP-Address option in one of the many following
        scenarios:
         UE is rebooting and it has an IPv4-address with unexpired
        lease.
         UE is selecting an offer from the DHCP-server. 
         UE is renewing the lease. 
         UE is attempting to rebind the lease." 
    ::= { cgprsAccPtStatisticsEntry 62 }

cgprsAccPtDhcpProxServDeclines OBJECT-TYPE
    SYNTAX          Counter32
    MAX-ACCESS      read-only
    STATUS          current
    DESCRIPTION
        "This object represents the number of DHCP decline messages
        received by the Gateway from UE.

        The UE may send this message when the IP-address it received is
        found to be already in use by another device." 
    ::= { cgprsAccPtStatisticsEntry 63 }

cgprsAccPtDhcpProxServRelease OBJECT-TYPE
    SYNTAX          Counter32
    MAX-ACCESS      read-only
    STATUS          current
    DESCRIPTION
        "This object represents the number DHCP - Release messages
        received
        by the Gateway.

        The User Equipment may send this message when the IPv4-session 
        is terminated." 
    ::= { cgprsAccPtStatisticsEntry 64 }

cgprsAccPtDhcpProxServOffer OBJECT-TYPE
    SYNTAX          Counter32
    MAX-ACCESS      read-only
    STATUS          current
    DESCRIPTION
        "This object represents the number of DHCP offer messages sent
        by the Gateway.
        The Gateway sends this message on allocating a Requested IP
        address to the User equipment." 
    ::= { cgprsAccPtStatisticsEntry 65 }

cgprsAccPtDhcpProxServAcks OBJECT-TYPE
    SYNTAX          Counter32
    MAX-ACCESS      read-only
    STATUS          current
    DESCRIPTION
        "This object represents the number of DHCP Acknowledge messages
        sent by the Gateway.
        The Gateway sends this message to the User equipment in response
        to a DHCP-Request message." 
    ::= { cgprsAccPtStatisticsEntry 66 }

cgprsAccPtDhcpProxServNaks OBJECT-TYPE
    SYNTAX          Counter32
    MAX-ACCESS      read-only
    STATUS          current
    DESCRIPTION
        "This object represents the number of DHCP-Negative-Acknowledge
        messages sent by the Gateway.

        The Gateway sends DHCP-Negative acknowledge message to the User
        Equipment in the following cases:
          If the DHCP-Request contains an IP-address that is different 
          from the address that PGW sent in the DHCP-Offer.

          If PGW is unable to allocate the offered IP-address" 
    ::= { cgprsAccPtStatisticsEntry 67 }

cgprsAccPtDhcpProxServInform OBJECT-TYPE
    SYNTAX          Counter32
    MAX-ACCESS      read-only
    STATUS          current
    DESCRIPTION
        "This object represents the number of DHCP-Inform message sent
        by the Gateway.
        The Gateway shall respond with a DHCP-Acknowledge to the
        DHCP-Inform message sent by the UE" 
    ::= { cgprsAccPtStatisticsEntry 68 }

cgprsAccPtDhcpProxServUnknowMsg OBJECT-TYPE
    SYNTAX          Counter32
    MAX-ACCESS      read-only
    STATUS          current
    DESCRIPTION
        "This object represents the number of DHCP-Unknown messages
        received by the Gateway.
        DHCP-Control messages, with unknown format are specified as
        DHCP-uknown message." 
    ::= { cgprsAccPtStatisticsEntry 69 }

cgprsAccPtDhcpProxServRetryDrops OBJECT-TYPE
    SYNTAX          Counter32
    MAX-ACCESS      read-only
    STATUS          current
    DESCRIPTION
        "This object represents the number of times the Gateway has
        retried to establish a connection with the Proxy server." 
    ::= { cgprsAccPtStatisticsEntry 70 }

cgprsAccPtDhcpProxServErrDrops OBJECT-TYPE
    SYNTAX          Counter32
    MAX-ACCESS      read-only
    STATUS          current
    DESCRIPTION
        "This object represents the number of times a DHCP proxy server
        control message is dropped by the Gateway due to some error in
        the message." 
    ::= { cgprsAccPtStatisticsEntry 71 }

cgprsAccPtActiveBearers OBJECT-TYPE
    SYNTAX          Gauge32
    UNITS           "bearers"
    MAX-ACCESS      read-only
    STATUS          current
    DESCRIPTION
        "This object indicates the current number of active
        Bearer on this APN." 
    ::= { cgprsAccPtStatisticsEntry 72 }

cgprsAccPtDhcpProxServTxErrDrops OBJECT-TYPE
    SYNTAX          Counter32
    MAX-ACCESS      read-only
    STATUS          current
    DESCRIPTION
        "This object represents the number of times an outgoing DHCP
        proxy server control message is dropped by the Gateway due to
        some failure in the Gateway." 
    ::= { cgprsAccPtStatisticsEntry 73 }

cgprsAccPtDhcpProxServIpAllocErr OBJECT-TYPE
    SYNTAX          Counter32
    MAX-ACCESS      read-only
    STATUS          current
    DESCRIPTION
        "This object represents the number of times an incoming DHCP
        proxy server control message has been dropped by the Gateway
        due to IP allocation error in the message." 
    ::= { cgprsAccPtStatisticsEntry 74 }

cgprsAccPtDedBearerDeactivations OBJECT-TYPE
    SYNTAX          Counter32
    MAX-ACCESS      read-only
    STATUS          current
    DESCRIPTION
        "This object represents the total number dedicated bearer
        deactivation request initiated by the Gateway." 
    ::= { cgprsAccPtStatisticsEntry 75 }

cgprsAccPtDedBearerQosUpdate OBJECT-TYPE
    SYNTAX          Counter32
    MAX-ACCESS      read-only
    STATUS          current
    DESCRIPTION
        "This object represents the total number of dedicated bearer
        modification request with QoS change initiated by the Gateway." 
    ::= { cgprsAccPtStatisticsEntry 76 }

cgprsAccPtDedBearerSucQosUpdate OBJECT-TYPE
    SYNTAX          Counter32
    MAX-ACCESS      read-only
    STATUS          current
    DESCRIPTION
        "This object represents the total number of successful
        dedicated bearer modification request with QoS change
        initiated by the Gateway." 
    ::= { cgprsAccPtStatisticsEntry 77 }

cgprsAccPtDedBearerNoQosUpdate OBJECT-TYPE
    SYNTAX          Counter32
    MAX-ACCESS      read-only
    STATUS          current
    DESCRIPTION
        "This object represents the total number of dedicated bearer
        modification request without QoS change initiated by the
        Gateway." 
    ::= { cgprsAccPtStatisticsEntry 78 }

cgprsAccPtDedBearerSucNoQosUpdate OBJECT-TYPE
    SYNTAX          Counter32
    MAX-ACCESS      read-only
    STATUS          current
    DESCRIPTION
        "This object represents the total number of successful
        dedicated bearer modification request without QoS change
        initiated by the Gateway." 
    ::= { cgprsAccPtStatisticsEntry 79 }

cgprsAccPtIpv4v6MsActivatedDynamicPdps OBJECT-TYPE
    SYNTAX          Counter32
    MAX-ACCESS      read-only
    STATUS          current
    DESCRIPTION
        "This object indicates the total number of IPv4v6 PDP
        or Bearer context activation procedures initiated by any MS on
        this APN." 
    ::= { cgprsAccPtStatisticsEntry 80 }

cgprsAccPtIpv4v6MsSuccActivatedDynamicPdps OBJECT-TYPE
    SYNTAX          Counter32
    MAX-ACCESS      read-only
    STATUS          current
    DESCRIPTION
        "This object indicates the total number of successfully
        completed IPv4v6 PDP or Bearer context activation procedures 
        initiated by MS on this APN." 
    ::= { cgprsAccPtStatisticsEntry 81 }

cgprsAccPtFailMsActivatedPdps OBJECT-TYPE
    SYNTAX          Counter32
    MAX-ACCESS      read-only
    STATUS          current
    DESCRIPTION
        "This object indicates the total number of failed PDP or Bearer
        context activation procedures initiated by MS on this APN." 
    ::= { cgprsAccPtStatisticsEntry 82 }

cgprsAccPtFailPdpUpdate OBJECT-TYPE
    SYNTAX          Counter32
    MAX-ACCESS      read-only
    STATUS          current
    DESCRIPTION
        "This object represents the total number of failed PDP or Bearer
        context update for the initiated update requests on this APN." 
    ::= { cgprsAccPtStatisticsEntry 83 }

cgprsAccPtUpdateRspTimeOut OBJECT-TYPE
    SYNTAX          Counter32
    MAX-ACCESS      read-only
    STATUS          current
    DESCRIPTION
        "This object represents the total number of failed PDP or
        Bearer context update response not received due to the time out
        for the initiated update requests on this APN." 
    ::= { cgprsAccPtStatisticsEntry 84 }
 

-- *******************************************************************
-- APN DHCPv6 Statistics
-- *******************************************************************

cgprsAccPtDhcpv6ProxyStatsTable OBJECT-TYPE
    SYNTAX          SEQUENCE OF CgprsAccPtDhcpv6ProxyStatsEntry 
    MAX-ACCESS      not-accessible
    STATUS          current
    DESCRIPTION
        "This table contains the DHCPv6 proxy server
        performance statistics for each APN on this Gateway."
    ::= { ciscoGprsAccPtStatistics 2 }

cgprsAccPtDhcpv6ProxyStatsEntry OBJECT-TYPE
    SYNTAX          CgprsAccPtDhcpv6ProxyStatsEntry
    MAX-ACCESS      not-accessible
    STATUS          current
    DESCRIPTION
        "There is an entry in this table for each APN in
        the Gateway."
    AUGMENTS           { cgprsAccPtEntry  } 
    ::= { cgprsAccPtDhcpv6ProxyStatsTable 1 }

CgprsAccPtDhcpv6ProxyStatsEntry ::= SEQUENCE {
        cgprsAccPtDhcpv6ProxInforeqRcvd    Counter32,
        cgprsAccPtDhcpv6ProxInforeqRply    Counter32,
        cgprsAccPtDhcpv6ProxInforeqLocRply Counter32,
        cgprsAccPtDhcpv6ProxIpAllocSuc     Counter32,
        cgprsAccPtDhcpv6ProxIpAllocFail    Counter32,
        cgprsAccPtDhcpv6ProxIpRelease      Counter32,
        cgprsAccPtDhcpv6ProxIpRenewFail    Counter32,
        cgprsAccPtDhcpv6ProxUnkwnMsg       Counter32,
        cgprsAccPtDhcpv6ProxErrs           Counter32
}

cgprsAccPtDhcpv6ProxInforeqRcvd OBJECT-TYPE
    SYNTAX          Counter32
    MAX-ACCESS      read-only
    STATUS          current
    DESCRIPTION
        "This object represents the total number of DHCPv6
        information request message handled by the Gateway's
        DHCPv6 proxy-client." 
    ::= { cgprsAccPtDhcpv6ProxyStatsEntry 1 }

cgprsAccPtDhcpv6ProxInforeqRply OBJECT-TYPE
    SYNTAX          Counter32
    MAX-ACCESS      read-only
    STATUS          current
    DESCRIPTION
        "This object represents the total number of DHCPv6 response
        message sent by the Gateway's DHCPv6 proxy-client." 
    ::= { cgprsAccPtDhcpv6ProxyStatsEntry 2 }

cgprsAccPtDhcpv6ProxInforeqLocRply OBJECT-TYPE
    SYNTAX          Counter32
    MAX-ACCESS      read-only
    STATUS          current
    DESCRIPTION
        "This object represents the total number of times a local
        response was sent for the DHCPv6 information request received
        by the Gateway's DHCPv6 proxy-client." 
    ::= { cgprsAccPtDhcpv6ProxyStatsEntry 3 }

cgprsAccPtDhcpv6ProxIpAllocSuc OBJECT-TYPE
    SYNTAX          Counter32
    MAX-ACCESS      read-only
    STATUS          current
    DESCRIPTION
        "This object represents the total number of times DHCPv6
        IP allocation was successful." 
    ::= { cgprsAccPtDhcpv6ProxyStatsEntry 4 }

cgprsAccPtDhcpv6ProxIpAllocFail OBJECT-TYPE
    SYNTAX          Counter32
    MAX-ACCESS      read-only
    STATUS          current
    DESCRIPTION
        "This object represents the total number of times DHCPv6
        IP allocation was failed." 
    ::= { cgprsAccPtDhcpv6ProxyStatsEntry 5 }

cgprsAccPtDhcpv6ProxIpRelease OBJECT-TYPE
    SYNTAX          Counter32
    MAX-ACCESS      read-only
    STATUS          current
    DESCRIPTION
        "This object represents the total number of times an allocated
        DHCPv6 IP was released." 
    ::= { cgprsAccPtDhcpv6ProxyStatsEntry 6 }

cgprsAccPtDhcpv6ProxIpRenewFail OBJECT-TYPE
    SYNTAX          Counter32
    MAX-ACCESS      read-only
    STATUS          current
    DESCRIPTION
        "This object represents the total number of times an allocated
        DHCPv6 IP renewal was failed." 
    ::= { cgprsAccPtDhcpv6ProxyStatsEntry 7 }

cgprsAccPtDhcpv6ProxUnkwnMsg OBJECT-TYPE
    SYNTAX          Counter32
    MAX-ACCESS      read-only
    STATUS          current
    DESCRIPTION
        "This object represents the total number of times an unknown
        message was handled by the Gateway's DHCPv6 proxy-client." 
    ::= { cgprsAccPtDhcpv6ProxyStatsEntry 8 }

cgprsAccPtDhcpv6ProxErrs OBJECT-TYPE
    SYNTAX          Counter32
    MAX-ACCESS      read-only
    STATUS          current
    DESCRIPTION
        "This object represents the total number of times an error
        has occurred at the Gateway's DHCPv6 proxy-client." 
    ::= { cgprsAccPtDhcpv6ProxyStatsEntry 9 }
 

-- *******************************************************************
-- APN Throughput Statistics
-- *******************************************************************

cgprsAccPtThruputStatsTable OBJECT-TYPE
    SYNTAX          SEQUENCE OF CgprsAccPtThruputStatsEntry 
    MAX-ACCESS      not-accessible
    STATUS          current
    DESCRIPTION
        "This table contains the throughput statistics of
        each APN on this Gateway."
    ::= { ciscoGprsAccPtStatistics 3 }

cgprsAccPtThruputStatsEntry OBJECT-TYPE
    SYNTAX          CgprsAccPtThruputStatsEntry
    MAX-ACCESS      not-accessible
    STATUS          current
    DESCRIPTION
        "An entry in this table."
    INDEX           {
                        cgprsAccPtIndex,
                        cgprsAccPtThruputInterval
                    } 
    ::= { cgprsAccPtThruputStatsTable 1 }

CgprsAccPtThruputStatsEntry ::= SEQUENCE {
        cgprsAccPtThruputInterval      Integer32,
        cgprsAccPtThruPutLastCollected Integer32,
        cgprsAccPtUpstrByteCount       Gauge32,
        cgprsAccPtDownstrByteCount     Gauge32,
        cgprsAccPtUpstrPktCount        Gauge32,
        cgprsAccPtDownstrPktCount      Gauge32
}

cgprsAccPtThruputInterval OBJECT-TYPE
    SYNTAX          Integer32 (1..65535)
    UNITS           "minutes"
    MAX-ACCESS      not-accessible
    STATUS          current
    DESCRIPTION
        "This object represents the time interval at which the
        statistics are sampled.  Interval configuration is out
        of the scope of the MIB and are covered in
        CISCO-GGSN-MIB." 
    ::= { cgprsAccPtThruputStatsEntry 1 }

cgprsAccPtThruPutLastCollected OBJECT-TYPE
    SYNTAX          Integer32 (0..65535)
    UNITS           "minutes"
    MAX-ACCESS      read-only
    STATUS          current
    DESCRIPTION
        "This object represents the delta value between the time
        when this data is collected and the time it is been
        retrieved." 
    ::= { cgprsAccPtThruputStatsEntry 2 }

cgprsAccPtUpstrByteCount OBJECT-TYPE
    SYNTAX          Gauge32
    UNITS           "bytes"
    MAX-ACCESS      read-only
    STATUS          current
    DESCRIPTION
        "This object represents the total payload volume in
        upstream traffic sent on this APN in the last sampling
        period specified by cgprsAccPtThruputInterval." 
    ::= { cgprsAccPtThruputStatsEntry 3 }

cgprsAccPtDownstrByteCount OBJECT-TYPE
    SYNTAX          Gauge32
    UNITS           "bytes"
    MAX-ACCESS      read-only
    STATUS          current
    DESCRIPTION
        "This object represents the total payload volume in
        downstream traffic sent on this APN in the last sampling
        period specified by cgprsAccPtThruputInterval." 
    ::= { cgprsAccPtThruputStatsEntry 4 }

cgprsAccPtUpstrPktCount OBJECT-TYPE
    SYNTAX          Gauge32
    UNITS           "packets"
    MAX-ACCESS      read-only
    STATUS          current
    DESCRIPTION
        "This object represents the number of upstream packets
        sent on this APN in the last sampling period specified
        by cgprsAccPtThruputInterval." 
    ::= { cgprsAccPtThruputStatsEntry 5 }

cgprsAccPtDownstrPktCount OBJECT-TYPE
    SYNTAX          Gauge32
    UNITS           "packets"
    MAX-ACCESS      read-only
    STATUS          current
    DESCRIPTION
        "This object represents the number of downstream packets
        sent on this APN in the last sampling period specified
        by cgprsAccPtThruputInterval." 
    ::= { cgprsAccPtThruputStatsEntry 6 }
 


-- *********************************************************************
-- NotifInfo
-- *********************************************************************

cgprsAccPtMsAddrType OBJECT-TYPE
    SYNTAX          InetAddressType
    MAX-ACCESS      accessible-for-notify
    STATUS          current
    DESCRIPTION
        "This object specifies the type of Internet address
        denoted by cgprsAccPtMsAllocAddr, cgprsAccPtMsNewAddr 
        and cgprsAccPtMsTpduDstAddr." 
    ::= { ciscoGprsAccPtNotifInfo 1 }

cgprsAccPtMsAllocAddr OBJECT-TYPE
    SYNTAX          InetAddress
    MAX-ACCESS      accessible-for-notify
    STATUS          current
    DESCRIPTION
        "This object specifies the IP address that is assigned
        to the MS during PDP activation." 
    ::= { ciscoGprsAccPtNotifInfo 2 }

cgprsAccPtMsNewAddr OBJECT-TYPE
    SYNTAX          InetAddress
    MAX-ACCESS      accessible-for-notify
    STATUS          current
    DESCRIPTION
        "This object specifies the fake IP address that is used
        by the MS." 
    ::= { ciscoGprsAccPtNotifInfo 3 }

cgprsAccPtMsTpduDstAddr OBJECT-TYPE
    SYNTAX          InetAddress
    MAX-ACCESS      accessible-for-notify
    STATUS          current
    DESCRIPTION
        "This object specifies the upstream TPDU destination
        address used by a MS that falls in the reserved range
        of IP addresses for PLMN devices." 
    ::= { ciscoGprsAccPtNotifInfo 4 }
-- *********************************************************************
-- Notification
-- *********************************************************************

cgprsAccPtMIBNotificationPrefix  OBJECT IDENTIFIER
    ::= { ciscoGprsAccPtMIB 2 }

cgprsAccPtMIBNotifications  OBJECT IDENTIFIER
    ::= { cgprsAccPtMIBNotificationPrefix 0 }


cgprsAccPtCfgNotif NOTIFICATION-TYPE
    OBJECTS         {
                        cgprsAccPtCfgNotifAccPtIndex,
                        cgprsAccPtCfgNotifReason
                    }
    STATUS          current
    DESCRIPTION
        "A notification of this type is generated when an
        entry is generated in the 
        cgprsAccPtCfgNotifHistTable and 
        cgprsAccPtCfgNotifEnable is set to true."
   ::= { cgprsAccPtMIBNotifications 1 }

cgprsAccPtSecSrcViolNotif NOTIFICATION-TYPE
    OBJECTS         {
                        cgprsAccPtCfgNotifAccPtIndex,
                        cgprsAccPtMsAddrType,
                        cgprsAccPtMsAllocAddr,
                        cgprsAccPtMsNewAddr
                    }
    STATUS          current
    DESCRIPTION
        "A notification of this type is generated when security
        violation as specified by
        cgprsAccPtVerifyUpStrTpduSrcAddr occurs on an APN."
   ::= { cgprsAccPtMIBNotifications 2 }

cgprsAccPtSecDestViolNotif NOTIFICATION-TYPE
    OBJECTS         {
                        cgprsAccPtCfgNotifAccPtIndex,
                        cgprsAccPtMsAddrType,
                        cgprsAccPtMsAllocAddr,
                        cgprsAccPtMsTpduDstAddr
                    }
    STATUS          current
    DESCRIPTION
        "A notification of this type is generated when security
        violation as specified by
        cgprsAccPtVerifyUpStrTpduDstAddr occurs on an APN."
   ::= { cgprsAccPtMIBNotifications 3 }

cgprsAccPtMaintenanceNotif NOTIFICATION-TYPE
    OBJECTS         { cgprsAccPtCfgNotifAccPtIndex }
    STATUS          current
    DESCRIPTION
        "A notification of this type is generated when APN is
        placed in maintenance mode which is specified by
        cgprsAccPtOperationMode."
   ::= { cgprsAccPtMIBNotifications 4 }

cgprsAccPtInServiceNotif NOTIFICATION-TYPE
    OBJECTS         { cgprsAccPtCfgNotifAccPtIndex }
    STATUS          current
    DESCRIPTION
        "A notification of this type is generated when APN is
        placed in in-service mode which is specified by
        cgprsAccPtOperationMode."
   ::= { cgprsAccPtMIBNotifications 5 }
-- *********************************************************************
-- Conformance Information
-- *********************************************************************

cgprsAccPtConformances  OBJECT IDENTIFIER
    ::= { ciscoGprsAccPtMIB 3 }

cgprsAccPtMIBCompliances  OBJECT IDENTIFIER
    ::= { cgprsAccPtConformances 1 }

cgprsAccPtMIBGroups  OBJECT IDENTIFIER
    ::= { cgprsAccPtConformances 2 }


-- Compliance statements

cgprsAccPtMIBCompliance MODULE-COMPLIANCE
    STATUS          obsolete
    DESCRIPTION
        "The compliance statements for entities which
        implement the CISCO-GPRS-ACC-PT-MIB."
    MODULE          -- this module
    MANDATORY-GROUPS {
                        cgprsAccPtMIBGroup,
                        cgprsAccPtCfgNotifGroup
                    }
    ::= { cgprsAccPtMIBCompliances 1 }

cgprsAccPtMIBComplianceRev1 MODULE-COMPLIANCE
    STATUS          obsolete
    DESCRIPTION
        "The compliance statements for entities which
        implement the CISCO-GPRS-ACC-PT-MIB."
    MODULE          -- this module
    MANDATORY-GROUPS {
                        cgprsAccPtMIBGroupRev1,
                        cgprsAccPtCfgNotifGroup,
                        cgprsAccPtStatisticsGroup,
                        cgprsAccPtExtMIBGroup,
                        cgprsAccPtMIBNotifGroup
                    }
    ::= { cgprsAccPtMIBCompliances 2 }

cgprsAccPtMIBComplianceRev2 MODULE-COMPLIANCE
    STATUS          obsolete
    DESCRIPTION
        "The compliance statements for entities which
        implement the CISCO-GPRS-ACC-PT-MIB. This is
        obsoleted by cgprsAccPtMIBComplianceRev3."
    MODULE          -- this module
    MANDATORY-GROUPS {
                        cgprsAccPtMIBGroupRev1,
                        cgprsAccPtCfgNotifGroup,
                        cgprsAccPtStatisticsGroupRev1,
                        cgprsAccPtExtMIBGroupRev1,
                        cgprsAccPtMIBNotifGroup
                    }
    ::= { cgprsAccPtMIBCompliances 3 }

cgprsAccPtMIBComplianceRev3 MODULE-COMPLIANCE
    STATUS          deprecated
    DESCRIPTION
        "The compliance statements for entities which
        implement the CISCO-GPRS-ACC-PT-MIB. This is
        deprecated by cgprsAccPtMIBComplianceRev4."
    MODULE          -- this module
    MANDATORY-GROUPS {
                        cgprsAccPtMIBGroupRev1,
                        cgprsAccPtCfgNotifGroup,
                        cgprsAccPtStatisticsGroupRev1,
                        cgprsAccPtExtMIBGroupRev2,
                        cgprsAccPtMIBNotifGroup
                    }
    ::= { cgprsAccPtMIBCompliances 4 }

cgprsAccPtMIBComplianceRev4 MODULE-COMPLIANCE
    STATUS          deprecated
    DESCRIPTION
        "The compliance statements for entities which
        implement the CISCO-GPRS-ACC-PT-MIB."
    MODULE          -- this module
    MANDATORY-GROUPS {
                        cgprsAccPtMIBGroupRev1,
                        cgprsAccPtCfgNotifGroup,
                        cgprsAccPtExtMIBGroupRev3,
                        cgprsAccPtGenServerGroup,
                        cgprsAccPtImsGroup,
                        cgprsAccPtChargingGroup,
                        cgprsAccPtCacGroup,
                        cgprsAccPtRouteProbeGroup,
                        cgprsAccPtStatisticsGroupRev2,
                        cgprsAccPtThruPutGroup,
                        cgprsAccPtNotifInfoGroup,
                        cgprsAccPtMIBNotifGroupRev1
                    }
    ::= { cgprsAccPtMIBCompliances 5 }

cgprsAccPtMIBComplianceRev5 MODULE-COMPLIANCE
    STATUS          deprecated
    DESCRIPTION
        "The compliance statements for entities which
        implement the CISCO-GPRS-ACC-PT-MIB."
    MODULE          -- this module
    MANDATORY-GROUPS {
                        cgprsAccPtMIBGroupRev1,
                        cgprsAccPtCfgNotifGroup,
                        cgprsAccPtExtMIBGroupRev3,
                        cgprsAccPtGenServerGroup,
                        cgprsAccPtImsGroup,
                        cgprsAccPtChargingGroup,
                        cgprsAccPtCacGroup,
                        cgprsAccPtRouteProbeGroup,
                        cgprsAccPtStatisticsGroupRev2,
                        cgprsAccPtThruPutGroup,
                        cgprsAccPtNotifInfoGroup,
                        cgprsAccPtMIBNotifGroupRev1,
                        cgprsAccPtMIBR60Group
                    }
    ::= { cgprsAccPtMIBCompliances 6 }

cgprsAccPtMIBComplianceRev6 MODULE-COMPLIANCE
    STATUS          deprecated
    DESCRIPTION
        "The compliance statements for entities which
        implement the CISCO-GPRS-ACC-PT-MIB."
    MODULE          -- this module
    MANDATORY-GROUPS {
                        cgprsAccPtMIBGroupRev1,
                        cgprsAccPtCfgNotifGroup,
                        cgprsAccPtExtMIBGroupRev3,
                        cgprsAccPtGenServerGroup,
                        cgprsAccPtImsGroup,
                        cgprsAccPtChargingGroup,
                        cgprsAccPtCacGroup,
                        cgprsAccPtRouteProbeGroup,
                        cgprsAccPtStatisticsGroupRev3,
                        cgprsAccPtThruPutGroup,
                        cgprsAccPtNotifInfoGroup,
                        cgprsAccPtMIBNotifGroupRev1,
                        cgprsAccPtMIBR60Group,
                        cgprsAccPtIpv6Group
                    }
    ::= { cgprsAccPtMIBCompliances 7 }

cgprsAccPtMIBComplianceRev7 MODULE-COMPLIANCE
    STATUS          deprecated
    DESCRIPTION
        "The compliance statements for entities which
        implement the CISCO-GPRS-ACC-PT-MIB."
    MODULE          -- this module
    MANDATORY-GROUPS {
                        cgprsAccPtMIBGroupRev1,
                        cgprsAccPtCfgNotifGroup,
                        cgprsAccPtExtMIBGroupRev3,
                        cgprsAccPtGenServerGroup,
                        cgprsAccPtChargingGroup,
                        cgprsAccPtCacGroup,
                        cgprsAccPtRouteProbeGroup,
                        cgprsAccPtStatisticsGroupRev3,
                        cgprsAccPtThruPutGroup,
                        cgprsAccPtNotifInfoGroup,
                        cgprsAccPtMIBNotifGroupRev1,
                        cgprsAccPtMIBR60Group,
                        cgprsAccPtIpv6Group,
                        cgprsAccPtPcscfGroup
                    }
    ::= { cgprsAccPtMIBCompliances 8 }

cgprsAccPtMIBComplianceRev8 MODULE-COMPLIANCE
    STATUS          deprecated
    DESCRIPTION
        "The compliance statements for entities which
        implement the CISCO-GPRS-ACC-PT-MIB. This is deprecated
        by cgprsAccPtMIBComplianceRev9."
    MODULE          -- this module
    MANDATORY-GROUPS {
                        cgprsAccPtMIBGroupRev1,
                        cgprsAccPtCfgNotifGroup,
                        cgprsAccPtExtMIBGroupRev3,
                        cgprsAccPtGenServerGroup,
                        cgprsAccPtChargingGroup,
                        cgprsAccPtCacGroup,
                        cgprsAccPtRouteProbeGroup,
                        cgprsAccPtStatisticsGroupRev3,
                        cgprsAccPtThruPutGroup,
                        cgprsAccPtNotifInfoGroup,
                        cgprsAccPtMIBNotifGroupRev1,
                        cgprsAccPtMIBR60Group,
                        cgprsAccPtIpv6Group,
                        cgprsAccPtPcscfGroup,
                        cgprsAccPtMIBR80Group,
                        cgprsAccPtStatisticsGroupSup1
                    }
    ::= { cgprsAccPtMIBCompliances 9 }

cgprsAccPtMIBComplianceRev9 MODULE-COMPLIANCE
    STATUS          deprecated
    DESCRIPTION
        "The compliance statements for entities which
        implement the CISCO-GPRS-ACC-PT-MIB. This is
        deprecated by cgprsAccPtMIBComplianceRev10."
    MODULE          -- this module
    MANDATORY-GROUPS {
                        cgprsAccPtMIBGroupRev1,
                        cgprsAccPtCfgNotifGroup,
                        cgprsAccPtExtMIBGroupRev3,
                        cgprsAccPtGenServerGroup,
                        cgprsAccPtChargingGroup,
                        cgprsAccPtCacGroup,
                        cgprsAccPtRouteProbeGroup,
                        cgprsAccPtStatisticsGroupRev3,
                        cgprsAccPtThruPutGroup,
                        cgprsAccPtNotifInfoGroup,
                        cgprsAccPtMIBNotifGroupRev1,
                        cgprsAccPtMIBR60Group,
                        cgprsAccPtIpv6Group,
                        cgprsAccPtPcscfGroup,
                        cgprsAccPtMIBR80Group,
                        cgprsAccPtStatisticsGroupSup1,
                        cgprsAccPtMIBR80GroupSup1
                    }
    ::= { cgprsAccPtMIBCompliances 10 }

cgprsAccPtMIBComplianceRev10 MODULE-COMPLIANCE
    STATUS          deprecated
    DESCRIPTION
        "The compliance statements for entities which
        implement the CISCO-GPRS-ACC-PT-MIB. This is
        deprecated by cgprsAccPtMIBComplianceRev11."
    MODULE          -- this module
    MANDATORY-GROUPS {
                        cgprsAccPtMIBGroupRev1,
                        cgprsAccPtCfgNotifGroup,
                        cgprsAccPtExtMIBGroupRev3,
                        cgprsAccPtGenServerGroup,
                        cgprsAccPtChargingGroup,
                        cgprsAccPtCacGroup,
                        cgprsAccPtRouteProbeGroup,
                        cgprsAccPtStatisticsGroupRev3,
                        cgprsAccPtThruPutGroup,
                        cgprsAccPtNotifInfoGroup,
                        cgprsAccPtMIBNotifGroupRev1,
                        cgprsAccPtMIBR60Group,
                        cgprsAccPtIpv6Group,
                        cgprsAccPtPcscfGroup,
                        cgprsAccPtMIBR80Group,
                        cgprsAccPtStatisticsGroupSup1,
                        cgprsAccPtMIBR80GroupSup1,
                        cgprsAccPtMIBR90Group
                    }
    ::= { cgprsAccPtMIBCompliances 11 }

cgprsAccPtMIBComplianceRev11 MODULE-COMPLIANCE
    STATUS          deprecated
    DESCRIPTION
        "The compliance statements for entities which
        implement the CISCO-GPRS-ACC-PT-MIB. This is
        deprecated by cgprsAccPtMIBComplianceRev12."
    MODULE          -- this module
    MANDATORY-GROUPS {
                        cgprsAccPtMIBGroupRev1,
                        cgprsAccPtCfgNotifGroup,
                        cgprsAccPtExtMIBGroupRev3,
                        cgprsAccPtGenServerGroup,
                        cgprsAccPtChargingGroup,
                        cgprsAccPtCacGroup,
                        cgprsAccPtRouteProbeGroup,
                        cgprsAccPtStatisticsGroupRev3,
                        cgprsAccPtThruPutGroup,
                        cgprsAccPtNotifInfoGroup,
                        cgprsAccPtMIBNotifGroupRev1,
                        cgprsAccPtMIBR60Group,
                        cgprsAccPtIpv6Group,
                        cgprsAccPtPcscfGroup,
                        cgprsAccPtMIBR80Group,
                        cgprsAccPtStatisticsGroupSup2,
                        cgprsAccPtMIBR80GroupSup1,
                        cgprsAccPtMIBR92Group,
                        cgprsAccPtMIBR90GroupRev1,
                        cgprsAccPtMIBR100Group
                    }
    ::= { cgprsAccPtMIBCompliances 12 }

cgprsAccPtMIBComplianceRev12 MODULE-COMPLIANCE
    STATUS          deprecated
    DESCRIPTION
        "The compliance statements for entities which
        implement the CISCO-GPRS-ACC-PT-MIB. This is
        deprecated by cgprsAccPtMIBComplianceRev13."
    MODULE          -- this module
    MANDATORY-GROUPS {
                        cgprsAccPtMIBGroupRev1,
                        cgprsAccPtCfgNotifGroup,
                        cgprsAccPtExtMIBGroupRev3,
                        cgprsAccPtGenServerGroup,
                        cgprsAccPtChargingGroup,
                        cgprsAccPtCacGroup,
                        cgprsAccPtRouteProbeGroup,
                        cgprsAccPtStatisticsGroupRev3,
                        cgprsAccPtThruPutGroup,
                        cgprsAccPtNotifInfoGroup,
                        cgprsAccPtMIBNotifGroupRev1,
                        cgprsAccPtMIBR60Group,
                        cgprsAccPtIpv6Group,
                        cgprsAccPtPcscfGroup,
                        cgprsAccPtMIBR80Group,
                        cgprsAccPtStatisticsGroupSup3,
                        cgprsAccPtMIBR80GroupSup1,
                        cgprsAccPtMIBR92Group,
                        cgprsAccPtMIBR90GroupRev1,
                        cgprsAccPtMIBR100Group,
                        cgprsAccPtExtMIBGroupSup1,
                        cgprsAccPtIpv6GroupSup1
                    }
    ::= { cgprsAccPtMIBCompliances 13 }

cgprsAccPtMIBComplianceRev13 MODULE-COMPLIANCE
    STATUS          deprecated
    DESCRIPTION
        "The compliance statements for entities which
        implement the CISCO-GPRS-ACC-PT-MIB. This is
        superceded by cgprsAccPtMIBComplianceRev14."
    MODULE          -- this module
    MANDATORY-GROUPS {
                        cgprsAccPtMIBGroupRev1,
                        cgprsAccPtCfgNotifGroup,
                        cgprsAccPtExtMIBGroupRev3,
                        cgprsAccPtGenServerGroup,
                        cgprsAccPtChargingGroup,
                        cgprsAccPtCacGroup,
                        cgprsAccPtRouteProbeGroup,
                        cgprsAccPtStatisticsGroupRev3,
                        cgprsAccPtThruPutGroup,
                        cgprsAccPtNotifInfoGroup,
                        cgprsAccPtMIBNotifGroupRev1,
                        cgprsAccPtMIBR60Group,
                        cgprsAccPtIpv6Group,
                        cgprsAccPtPcscfGroup,
                        cgprsAccPtMIBR80Group,
                        cgprsAccPtStatisticsGroupSup3,
                        cgprsAccPtStatisticsGroupSup4,
                        cgprsAccPtMIBR80GroupSup1,
                        cgprsAccPtMIBR92Group,
                        cgprsAccPtMIBR90GroupRev1,
                        cgprsAccPtMIBR100Group,
                        cgprsAccPtExtMIBGroupSup1,
                        cgprsAccPtIpv6GroupSup1,
                        cgprsAccPtExtMIBGroupSup2,
                        cgprsAccPtDhcpv6ProxyStatsGroup
                    }
    ::= { cgprsAccPtMIBCompliances 14 }

cgprsAccPtMIBComplianceRev14 MODULE-COMPLIANCE
    STATUS          deprecated
    DESCRIPTION
        "The compliance statements for entities which implement the
        CISCO-GPRS-ACC-PT-MIB. This is superceded by cgprsAccPtMIBComplianceRev15."
    MODULE          -- this module
    MANDATORY-GROUPS {
                        cgprsAccPtCfgNotifGroup,
                        cgprsAccPtMIBGroupRev1,
                        cgprsAccPtExtMIBGroupRev3,
                        cgprsAccPtGenServerGroup,
                        cgprsAccPtChargingGroup,
                        cgprsAccPtCacGroup,
                        cgprsAccPtRouteProbeGroup,
                        cgprsAccPtThruPutGroup,
                        cgprsAccPtNotifInfoGroup,
                        cgprsAccPtMIBNotifGroupRev1,
                        cgprsAccPtMIBR60Group,
                        cgprsAccPtIpv6Group,
                        cgprsAccPtStatisticsGroupRev3,
                        cgprsAccPtPcscfGroup,
                        cgprsAccPtMIBR80Group,
                        cgprsAccPtMIBR80GroupSup1,
                        cgprsAccPtMIBR92Group,
                        cgprsAccPtMIBR90GroupRev1,
                        cgprsAccPtMIBR100Group,
                        cgprsAccPtStatisticsGroupSup3,
                        cgprsAccPtExtMIBGroupSup1,
                        cgprsAccPtIpv6GroupSup1,
                        cgprsAccPtStatisticsGroupSup4,
                        cgprsAccPtDhcpv6ProxyStatsGroup,
                        cgprsAccPtExtMIBGroupSup2,
                        cgprsAccPtStatisticsGroupSup5
                    }
    ::= { cgprsAccPtMIBCompliances 15 }

cgprsAccPtMIBComplianceRev15 MODULE-COMPLIANCE
    STATUS          current
    DESCRIPTION
        "The compliance statements for entities which
        implement the CISCO-GPRS-ACC-PT-MIB."
    MODULE          -- this module
    MANDATORY-GROUPS {
                        cgprsAccPtCfgNotifGroup,
                        cgprsAccPtMIBGroupRev1,
                        cgprsAccPtExtMIBGroupRev3,
                        cgprsAccPtGenServerGroup,
                        cgprsAccPtChargingGroup,
                        cgprsAccPtCacGroup,
                        cgprsAccPtRouteProbeGroup,
                        cgprsAccPtThruPutGroup,
                        cgprsAccPtNotifInfoGroup,
                        cgprsAccPtMIBNotifGroupRev1,
                        cgprsAccPtMIBR60Group,
                        cgprsAccPtIpv6Group,
                        cgprsAccPtStatisticsGroupRev3,
                        cgprsAccPtPcscfGroup,
                        cgprsAccPtMIBR80Group,
                        cgprsAccPtMIBR80GroupSup1,
                        cgprsAccPtMIBR92Group,
                        cgprsAccPtMIBR90GroupRev1,
                        cgprsAccPtMIBR100Group,
                        cgprsAccPtStatisticsGroupSup3,
                        cgprsAccPtExtMIBGroupSup1,
                        cgprsAccPtIpv6GroupSup1,
                        cgprsAccPtStatisticsGroupSup4,
                        cgprsAccPtDhcpv6ProxyStatsGroup,
                        cgprsAccPtExtMIBGroupSup2,
                        cgprsAccPtStatisticsGroupSup5,
                        cgprsAccPtStatisticsGroupSup6
                    }
    ::= { cgprsAccPtMIBCompliances 16 }

-- Unit Conformance

cgprsAccPtMIBGroup OBJECT-GROUP
    OBJECTS         {
                        cgprsAccPtRowStatus,
                        cgprsAccPtName,
                        cgprsAccPtMode,
                        cgprsAccPtIpAddressPool,
                        cgprsAccPtDHCPServerPri,
                        cgprsAccPtDHCPServerSec,
                        cgprsAccPtDHCPGwAddr,
                        cgprsAccPtRadiusServerPri,
                        cgprsAccPtRadiusServerSec,
                        cgprsAccPtIPAccListGroupIn,
                        cgprsAccPtIPAccListGroupOut,
                        cgprsAccPtIfIndex,
                        cgprsAccPtIfNextHop,
                        cgprsAccPtAccessViolation,
                        cgprsAccPtSubrRequired,
                        cgprsAccPtNetworkInitiated,
                        cgprsAccPtIpAddrAllocations,
                        cgprsAccPtUsers,
                        cgprsAccPtIdlePdpPurgeTimer,
                        cgprsAccPtBlockMsRoaming,
                        cgprsAccPtAnonymousUserName,
                        cgprsAccPtAnonymousUserPassword,
                        cgprsAccPtMsIsdnSuppressed,
                        cgprsAccPtMsIsdnSuppressedValue,
                        cgprsAccPtAaaAuthServerGroup,
                        cgprsAccPtAaaAccountServerGroup,
                        cgprsAccPtAaaAccountingEnable,
                        cgprsAccPtAggregRowStatus
                    }
    STATUS          obsolete
    DESCRIPTION
        "A collection of objects providing APN configurations."
    ::= { cgprsAccPtMIBGroups 1 }

cgprsAccPtCfgNotifGroup OBJECT-GROUP
    OBJECTS         {
                        cgprsAccPtCfgNotifEnable,
                        cgprsAccPtCfgNotifAccPtIndex,
                        cgprsAccPtCfgNotifReason,
                        cgprsAccPtCfgNotifHistMax,
                        cgprsAccPtCfgNotifLatestIndex
                    }
    STATUS          current
    DESCRIPTION
        "A collection of objects providing GPRS access point
        configuration change event related information."
    ::= { cgprsAccPtMIBGroups 2 }

cgprsAccPtStatisticsGroup OBJECT-GROUP
    OBJECTS         {
                        cgprsAccPtMsActivatedPdps,
                        cgprsAccPtSuccMsActivatedPdps,
                        cgprsAccPtMsActivatedDynPdps,
                        cgprsAccPtSuccMsActivatedDynPdps,
                        cgprsAccPtMsDeactivatedPdps,
                        cgprsAccPtSuccMsDeactivatedPdps,
                        cgprsAccPtNetworkInitPdps,
                        cgprsAccPtSuccNetworkInitPdps,
                        cgprsAccPtGgsnDeactivatedPdps,
                        cgprsAccPtSuccGgsDeactivatedPdps,
                        cgprsAccPtActivePdps,
                        cgprsAccPtUpstreamTrafficVol,
                        cgprsAccPtDownstreamTrafficVol
                    }
    STATUS          obsolete
    DESCRIPTION
        "A collection of objects providing GPRS access point
        performance statistics.
        This is obsoleted by cgprsAccPtStatisticsGroupRev1."
    ::= { cgprsAccPtMIBGroups 3 }

cgprsAccPtMIBGroupRev1 OBJECT-GROUP
    OBJECTS         {
                        cgprsAccPtRowStatus,
                        cgprsAccPtName,
                        cgprsAccPtMode,
                        cgprsAccPtIpAddressPool,
                        cgprsAccPtDHCPServerPri,
                        cgprsAccPtDHCPServerSec,
                        cgprsAccPtDHCPGwAddr,
                        cgprsAccPtIPAccListGroupIn,
                        cgprsAccPtIPAccListGroupOut,
                        cgprsAccPtAccessViolation,
                        cgprsAccPtSubrRequired,
                        cgprsAccPtNetworkInitiated,
                        cgprsAccPtIpAddrAllocations,
                        cgprsAccPtIdlePdpPurgeTimer,
                        cgprsAccPtBlockMsRoaming,
                        cgprsAccPtAnonymousUserName,
                        cgprsAccPtAnonymousUserPassword,
                        cgprsAccPtMsIsdnSuppressed,
                        cgprsAccPtMsIsdnSuppressedValue,
                        cgprsAccPtAaaAuthServerGroup,
                        cgprsAccPtAaaAccountServerGroup,
                        cgprsAccPtAaaAccountingEnable,
                        cgprsAccPtType,
                        cgprsAccPtVrfName,
                        cgprsAccPtDhcpAddrSpace,
                        cgprsAccPtPppRegenEnable,
                        cgprsAccPtPppRegenMaxSessions,
                        cgprsAccPtPppRegenSetupTime,
                        cgprsAccPtAutoAggregation,
                        cgprsAccPtAggregRowStatus
                    }
    STATUS          current
    DESCRIPTION
        "A collection of objects providing APN configurations."
    ::= { cgprsAccPtMIBGroups 4 }

cgprsAccPtExtMIBGroup OBJECT-GROUP
    OBJECTS         {
                        cgprsAccPtIPAccListInEnable,
                        cgprsAccPtIPAccListOutEnable,
                        cgprsAccPtGtpRespMesgWaitAcctng
                    }
    STATUS          obsolete
    DESCRIPTION
        "A collection of objects providing APN configurations."
    ::= { cgprsAccPtMIBGroups 5 }

cgprsAccPtMIBNotifGroup NOTIFICATION-GROUP
   NOTIFICATIONS    { cgprsAccPtCfgNotif }
    STATUS          deprecated
    DESCRIPTION
        "A collection of objects providing GPRS access point
        notifications."
    ::= { cgprsAccPtMIBGroups 6 }

cgprsAccPtExtMIBGroupRev1 OBJECT-GROUP
    OBJECTS         {
                        cgprsAccPtIPAccListInEnable,
                        cgprsAccPtIPAccListOutEnable,
                        cgprsAccPtGtpRespMesgWaitAcctng,
                        cgprsAccPtImsiSuppressed,
                        cgprsAccPtVerifyUpStrTpduSrcAddr,
                        cgprsAccPtVerifyUpStrTpduDstAddr,
                        cgprsAccPtRedirInterMobilAddrTyp,
                        cgprsAccPtRedirInterMobilAddr
                    }
    STATUS          obsolete
    DESCRIPTION
        "A collection of objects providing APN configurations.
        This is obsoleted by cgprsAccPtExtMIBGroupRev2."
    ::= { cgprsAccPtMIBGroups 7 }

cgprsAccPtStatisticsGroupRev1 OBJECT-GROUP
    OBJECTS         {
                        cgprsAccPtMsActivatedPdps,
                        cgprsAccPtSuccMsActivatedPdps,
                        cgprsAccPtMsActivatedDynPdps,
                        cgprsAccPtSuccMsActivatedDynPdps,
                        cgprsAccPtMsDeactivatedPdps,
                        cgprsAccPtSuccMsDeactivatedPdps,
                        cgprsAccPtNetworkInitPdps,
                        cgprsAccPtSuccNetworkInitPdps,
                        cgprsAccPtGgsnDeactivatedPdps,
                        cgprsAccPtSuccGgsDeactivatedPdps,
                        cgprsAccPtActivePdps,
                        cgprsAccPtUpstreamTrafficVol,
                        cgprsAccPtDownstreamTrafficVol,
                        cgprsAccPtSourceAddrViolTpdus,
                        cgprsAccPtDestAddrViolTpdus,
                        cgprsAccPtRedirInterMobilTraffic
                    }
    STATUS          deprecated
    DESCRIPTION
        "A collection of objects providing GPRS access point
        performance statistics.  This is deprecated by
        cgprsAccPtStatisticsGroupRev2."
    ::= { cgprsAccPtMIBGroups 8 }

cgprsAccPtExtMIBGroupRev2 OBJECT-GROUP
    OBJECTS         {
                        cgprsAccPtIPAccListInEnable,
                        cgprsAccPtIPAccListOutEnable,
                        cgprsAccPtGtpRespMesgWaitAcctng,
                        cgprsAccPtVerifyUpStrTpduSrcAddr,
                        cgprsAccPtVerifyUpStrTpduDstAddr,
                        cgprsAccPtRedirInterMobilAddrTyp,
                        cgprsAccPtRedirInterMobilAddr,
                        cgprsAccPtSuppressRadiusAttribs
                    }
    STATUS          deprecated
    DESCRIPTION
        "A collection of objects providing APN configurations.
        This is deprecated by cgprsAccPtExtMIBGroupRev3."
    ::= { cgprsAccPtMIBGroups 9 }

cgprsAccPtExtMIBGroupRev3 OBJECT-GROUP
    OBJECTS         {
                        cgprsAccPtIPAccListInEnable,
                        cgprsAccPtIPAccListOutEnable,
                        cgprsAccPtGtpRespMesgWaitAcctng,
                        cgprsAccPtVerifyUpStrTpduSrcAddr,
                        cgprsAccPtVerifyUpStrTpduDstAddr,
                        cgprsAccPtRedirInterMobilAddrTyp,
                        cgprsAccPtRedirInterMobilAddr,
                        cgprsAccPtSuppressRadiusAttribs,
                        cgprsAccPtInterimAccountinEnable,
                        cgprsAccPtSetRadiusAttributes,
                        cgprsAccPtOperationMode,
                        cgprsAccPtAbsoluteSessionTimer,
                        cgprsAccPtRadiusAttrNasId,
                        cgprsAccPtPdpInServicePolicyName,
                        cgprsAccPtPdpOutServicePolicyNam,
                        cgprsAccPtPppRegenVerifyDomain,
                        cgprsAccPtIpAddrLocalPoolName
                    }
    STATUS          current
    DESCRIPTION
        "A collection of objects providing APN configurations."
    ::= { cgprsAccPtMIBGroups 10 }

cgprsAccPtGenServerGroup OBJECT-GROUP
    OBJECTS         {
                        cgprsAccPtDnsServerAddrType,
                        cgprsAccPtPriDnsServer,
                        cgprsAccPtSecDnsServer,
                        cgprsAccPtNetbiosServerAddrType,
                        cgprsAccPtPriNetbiosServer,
                        cgprsAccPtSecNetbiosServer
                    }
    STATUS          current
    DESCRIPTION
        "A collection of objects providing address of generic
        server configurations on the APN."
    ::= { cgprsAccPtMIBGroups 11 }

cgprsAccPtImsGroup OBJECT-GROUP
    OBJECTS         {
                        cgprsAccPtImsEnable,
                        cgprsAccPtPCscfGroupName,
                        cgprsAccPtImsSigAccGroupIn,
                        cgprsAccPtImsSigAccGroupOut,
                        cgprsAccPtRejNonImsPdp
                    }
    STATUS          deprecated
    DESCRIPTION
        "A collection of objects providing IMS configurations
        under APN."
    ::= { cgprsAccPtMIBGroups 12 }

cgprsAccPtChargingGroup OBJECT-GROUP
    OBJECTS         {
                        cgprsAccPtChgProfile,
                        cgprsAccPtChgProfOverride,
                        cgprsAccPtChgProfRowStatus
                    }
    STATUS          current
    DESCRIPTION
        "A collection of objects providing Charging
        configurations under APN."
    ::= { cgprsAccPtMIBGroups 13 }

cgprsAccPtCacGroup OBJECT-GROUP
    OBJECTS         {
                        cgprsAccPtCacPolicyName,
                        cgprsAccPtCacUpStrBandWidthPool,
                        cgprsAccPtCacDnStrBandWidthPool
                    }
    STATUS          current
    DESCRIPTION
        "A collection of objects providing CAC configurations
        under APN."
    ::= { cgprsAccPtMIBGroups 14 }

cgprsAccPtRouteProbeGroup OBJECT-GROUP
    OBJECTS         {
                        cgprsAccPtRpDestAddrType,
                        cgprsAccPtRpDestAddr,
                        cgprsAccPtRpProtocol,
                        cgprsAccPtRpDestPort,
                        cgprsAccPtRpTtl
                    }
    STATUS          current
    DESCRIPTION
        "A collection of objects providing configurations for
        route probe feature."
    ::= { cgprsAccPtMIBGroups 15 }

cgprsAccPtStatisticsGroupRev2 OBJECT-GROUP
    OBJECTS         {
                        cgprsAccPtMsActivatedPdps,
                        cgprsAccPtSuccMsActivatedPdps,
                        cgprsAccPtMsActivatedDynPdps,
                        cgprsAccPtSuccMsActivatedDynPdps,
                        cgprsAccPtMsDeactivatedPdps,
                        cgprsAccPtSuccMsDeactivatedPdps,
                        cgprsAccPtNetworkInitPdps,
                        cgprsAccPtSuccNetworkInitPdps,
                        cgprsAccPtGgsnDeactivatedPdps,
                        cgprsAccPtSuccGgsDeactivatedPdps,
                        cgprsAccPtActivePdps,
                        cgprsAccPtSourceAddrViolTpdus,
                        cgprsAccPtDestAddrViolTpdus,
                        cgprsAccPtRedirInterMobilTraffic,
                        cgprsAccPtRevUpstreamTrafficVol,
                        cgprsAccPtRevDownstrTrafficVol,
                        cgprsAccPtUpstreamPacketCount,
                        cgprsAccPtDownstreamPacketCount,
                        cgprsAccPtDhcpAddrRequests,
                        cgprsAccPtSuccDhcpAddrRequests,
                        cgprsAccPtDhcpAddrReleases
                    }
    STATUS          deprecated
    DESCRIPTION
        "A collection of objects providing GPRS access point
        performance statistics per name. This is deprecated by
        cgprsAccPtStatisticsGroupRev3."
    ::= { cgprsAccPtMIBGroups 16 }

cgprsAccPtThruPutGroup OBJECT-GROUP
    OBJECTS         {
                        cgprsAccPtThruPutLastCollected,
                        cgprsAccPtUpstrByteCount,
                        cgprsAccPtDownstrByteCount,
                        cgprsAccPtUpstrPktCount,
                        cgprsAccPtDownstrPktCount
                    }
    STATUS          current
    DESCRIPTION
        "A collection of objects providing throughput statistics
        per APN."
    ::= { cgprsAccPtMIBGroups 17 }

cgprsAccPtNotifInfoGroup OBJECT-GROUP
    OBJECTS         {
                        cgprsAccPtMsAddrType,
                        cgprsAccPtMsAllocAddr,
                        cgprsAccPtMsNewAddr,
                        cgprsAccPtMsTpduDstAddr
                    }
    STATUS          current
    DESCRIPTION
        "A collection of objects providing notification info on
        an APN."
    ::= { cgprsAccPtMIBGroups 18 }

cgprsAccPtMIBNotifGroupRev1 NOTIFICATION-GROUP
   NOTIFICATIONS    {
                        cgprsAccPtCfgNotif,
                        cgprsAccPtSecSrcViolNotif,
                        cgprsAccPtSecDestViolNotif,
                        cgprsAccPtMaintenanceNotif,
                        cgprsAccPtInServiceNotif
                    }
    STATUS          current
    DESCRIPTION
        "A collection of objects providing GPRS access point
        notifications."
    ::= { cgprsAccPtMIBGroups 19 }

cgprsAccPtMIBR60Group OBJECT-GROUP
    OBJECTS         {
                        cgprsAccPtServiceAware,
                        cgprsAccPtAdvDownlinkNextHopAddrType,
                        cgprsAccPtAdvDownlinkNextHopAddr
                    }
    STATUS          current
    DESCRIPTION
        "A collection of objects added as a part of GGSN R6.0
        release."
    ::= { cgprsAccPtMIBGroups 20 }

cgprsAccPtIpv6Group OBJECT-GROUP
    OBJECTS         {
                        cgprsAccPtIpv6BaseVTemplate,
                        cgprsAccPtIpv6DnsAddrType,
                        cgprsAccPtIpv6DnsPriAddress,
                        cgprsAccPtIpv6DnsSecAddress,
                        cgprsAccPtIpv6Enable,
                        cgprsAccPtIpv6Exclusive,
                        cgprsAccPtIpv6AccessGroupDown,
                        cgprsAccPtIpv6AccessGroupUp,
                        cgprsAccPtIpv6AddrPool,
                        cgprsAccPtIpv6AddrLocalPoolName,
                        cgprsAccPtIpv6Redirect,
                        cgprsAccPtIpv6RedirectAddrType,
                        cgprsAccPtIpv6RedirectAddr,
                        cgprsAccPtIpv6SecurityVerifySrc,
                        cgprsAccPtIpv6SecurityVerifyDst
                    }
    STATUS          current
    DESCRIPTION
        "A collection of objects providing configurations for
        IPv6 feature."
    ::= { cgprsAccPtMIBGroups 21 }

cgprsAccPtStatisticsGroupRev3 OBJECT-GROUP
    OBJECTS         {
                        cgprsAccPtMsActivatedPdps,
                        cgprsAccPtSuccMsActivatedPdps,
                        cgprsAccPtMsActivatedDynPdps,
                        cgprsAccPtSuccMsActivatedDynPdps,
                        cgprsAccPtMsDeactivatedPdps,
                        cgprsAccPtSuccMsDeactivatedPdps,
                        cgprsAccPtNetworkInitPdps,
                        cgprsAccPtSuccNetworkInitPdps,
                        cgprsAccPtGgsnDeactivatedPdps,
                        cgprsAccPtSuccGgsDeactivatedPdps,
                        cgprsAccPtActivePdps,
                        cgprsAccPtSourceAddrViolTpdus,
                        cgprsAccPtDestAddrViolTpdus,
                        cgprsAccPtRedirInterMobilTraffic,
                        cgprsAccPtRevUpstreamTrafficVol,
                        cgprsAccPtRevDownstrTrafficVol,
                        cgprsAccPtUpstreamPacketCount,
                        cgprsAccPtDownstreamPacketCount,
                        cgprsAccPtDhcpAddrRequests,
                        cgprsAccPtSuccDhcpAddrRequests,
                        cgprsAccPtDhcpAddrReleases,
                        cgprsAccPtIpv6MsActivatedPdps,
                        cgprsAccPtIpv6MsSuccActivatedPdps,
                        cgprsAccPtIpv6NetworkInitDeactPdps,
                        cgprsAccPtIpv6NetworkInitDeactSuccPdps,
                        cgprsAccPtIpv6MsActivatedDynPdps,
                        cgprsAccPtIpv6MsSuccActivatedDynPdps,
                        cgprsAccPtIpv6MsDeactivatedPdps,
                        cgprsAccPtIpv6MsSuccDeactivatedPdps,
                        cgprsAccPtIpv6GgsnDeactivatedPdps,
                        cgprsAccPtIpv6GgsnSuccDeactivatedPdps,
                        cgprsAccPtIpv6UpstreamTrafficVolume,
                        cgprsAccPtIpv6DownstreamTrafficVolume,
                        cgprsAccPtIpv6UpstreamPackets,
                        cgprsAccPtIpv6DownstreamPackets
                    }
    STATUS          current
    DESCRIPTION
        "A collection of objects providing GPRS access point
        performance statistics per name."
    ::= { cgprsAccPtMIBGroups 22 }

cgprsAccPtPcscfGroup OBJECT-GROUP
    OBJECTS         { cgprsAccPtPcscfServerGroupName }
    STATUS          current
    DESCRIPTION
        "A collection of pcscf related objects."
    ::= { cgprsAccPtMIBGroups 23 }

cgprsAccPtMIBR80Group OBJECT-GROUP
    OBJECTS         {
                        cgprsAccPtGtpUpdateFailDelete,
                        cgprsAccPtAaaAccountInterPeriod
                    }
    STATUS          current
    DESCRIPTION
        "A collection of config objects added for GGSN 8.0."
    ::= { cgprsAccPtMIBGroups 24 }

cgprsAccPtStatisticsGroupSup1 OBJECT-GROUP
    OBJECTS         {
                        cgprsAccPtPdpUpdateReqSent,
                        cgprsAccPtSuccPdpUpdateResRcvd,
                        cgprsAccPtCoaRcvd,
                        cgprsAccPtCoaSuccess,
                        cgprsAccPtDtEnabled
                    }
    STATUS          deprecated
    DESCRIPTION
        "A collection of objects providing GPRS access point
        performance statistics per name. This is deprecated by
        cgprsAccPtStatisticsGroupSup2."
    ::= { cgprsAccPtMIBGroups 25 }

cgprsAccPtMIBR80GroupSup1 OBJECT-GROUP
    OBJECTS         { cgprsAccPtAaaAccountInterRadius }
    STATUS          current
    DESCRIPTION
        "A collection of config objects added for GGSN 8.0."
    ::= { cgprsAccPtMIBGroups 26 }

cgprsAccPtMIBR90Group OBJECT-GROUP
    OBJECTS         {
                        cgprsAccPtGxEnable,
                        cgprsAccPtPcscfLoadBalance,
                        cgprsAccPtNetworkBehindMsEnable,
                        cgprsAccPtMaxSubnetsBehindMobile
                    }
    STATUS          deprecated
    DESCRIPTION
        "A collection of config objects added for GGSN 9.0.
        This is deprecated by cgprsAccPtMIBR90GroupRev1."
    ::= { cgprsAccPtMIBGroups 27 }

cgprsAccPtStatisticsGroupSup2 OBJECT-GROUP
    OBJECTS         {
                        cgprsAccPtPdpUpdateReqSent,
                        cgprsAccPtSuccPdpUpdateResRcvd,
                        cgprsAccPtCoaRcvd,
                        cgprsAccPtCoaSuccess,
                        cgprsAccPtDtEnabled,
                        cgprsAccPtTotalBearers,
                        cgprsAccPtTotRmtInitCreateBearers,
                        cgprsAccPtSuccRmtInitCreateBearers,
                        cgprsAccPtNetworkInitDeleteBearers,
                        cgprsAccPtTotNetworkInitUpdateBearers,
                        cgprsAccPtSuccNetworkInitUpdateBearers,
                        cgprsAccPtTotNetworkInitCreateDedBearers,
                        cgprsAccPtSuccNetworkInitCreateDedBearers,
                        cgprsAccPtTotRmtInitModifyBearers,
                        cgprsAccPtSuccRmtInitModifyBearers,
                        cgprsAccPtTotNetworkInitCreateIPv6DedBearers,
                        cgprsAccPtSuccNetworkInitCreateIPv6DedBearers
                    }
    STATUS          deprecated
    DESCRIPTION
        "A collection of objects providing GPRS access point
        performance statistics per name. This is deprecated by
        cgprsAccPtStatisticsGroupSup3."
    ::= { cgprsAccPtMIBGroups 28 }

cgprsAccPtMIBR92Group OBJECT-GROUP
    OBJECTS         { cgprsAccPtChargingRecordType }
    STATUS          current
    DESCRIPTION
        "A collection of config objects added for GGSN."
    ::= { cgprsAccPtMIBGroups 29 }

cgprsAccPtMIBR90GroupRev1 OBJECT-GROUP
    OBJECTS         {
                        cgprsAccPtGxEnable,
                        cgprsAccPtPcscfLoadBalance,
                        cgprsAccPtNetworkBehindMsEnable,
                        cgprsAccPtMaxSubnetsBehindMobile,
                        cgprsAccPtChargingGrp
                    }
    STATUS          current
    DESCRIPTION
        "A collection of config objects added for GGSN."
    ::= { cgprsAccPtMIBGroups 30 }

cgprsAccPtMIBR100Group OBJECT-GROUP
    OBJECTS         {
                        cgprsAccPtAggregCsgGroup,
                        cgprsAccPtCsgGroupRowStatus,
                        cgprsAccPtIpAddrPoolNoRedistribute
                    }
    STATUS          current
    DESCRIPTION
        "A collection of config objects added for providing the name
        of the CSG Group and allowing the redistribution of routes 
        from PCOP to the SUP (Supervisor)."
    ::= { cgprsAccPtMIBGroups 31 }

cgprsAccPtStatisticsGroupSup3 OBJECT-GROUP
    OBJECTS         {
                        cgprsAccPtPdpUpdateReqSent,
                        cgprsAccPtSuccPdpUpdateResRcvd,
                        cgprsAccPtCoaRcvd,
                        cgprsAccPtCoaSuccess,
                        cgprsAccPtDtEnabled,
                        cgprsAccPtTotalBearers,
                        cgprsAccPtTotRmtInitCreateBearers,
                        cgprsAccPtSuccRmtInitCreateBearers,
                        cgprsAccPtNetworkInitDeleteBearers,
                        cgprsAccPtTotNetworkInitUpdateBearers,
                        cgprsAccPtSuccNetworkInitUpdateBearers,
                        cgprsAccPtTotNetworkInitCreateDedBearers,
                        cgprsAccPtSuccNetworkInitCreateDedBearers,
                        cgprsAccPtTotRmtInitModifyBearers,
                        cgprsAccPtSuccRmtInitModifyBearers,
                        cgprsAccPtTotNetworkInitCreateIPv6DedBearers,
                        cgprsAccPtSuccNetworkInitCreateIPv6DedBearers,
                        cgprsAccPtv4v6MsActivatedPdps,
                        cgprsAccPtv4v6SuccMsActivatedPdps,
                        cgprsAccPtv4v6MsDeactivatedPdps,
                        cgprsAccPtv4v6SuccMsDeactivatedPdps,
                        cgprsAccPtv4v6ActDedbearerPdps,
                        cgprsAccPtv4v6SuccActDedbearerPdps,
                        cgprsAccPtDhcpProxServDiscover,
                        cgprsAccPtDhcpProxServRequest,
                        cgprsAccPtDhcpProxServDeclines,
                        cgprsAccPtDhcpProxServRelease,
                        cgprsAccPtDhcpProxServOffer,
                        cgprsAccPtDhcpProxServAcks,
                        cgprsAccPtDhcpProxServNaks,
                        cgprsAccPtDhcpProxServInform,
                        cgprsAccPtDhcpProxServUnknowMsg,
                        cgprsAccPtDhcpProxServRetryDrops,
                        cgprsAccPtDhcpProxServErrDrops
                    }
    STATUS          current
    DESCRIPTION
        "A collection of objects providing GPRS access point
        performance statistics per name."
    ::= { cgprsAccPtMIBGroups 32 }

cgprsAccPtExtMIBGroupSup1 OBJECT-GROUP
    OBJECTS         { cgprsAccPtDualAddrEnabled }
    STATUS          current
    DESCRIPTION
        "This group supplements cgprsAccPtExtMIBGroupRev3 to provide
        dual stack APN configurations."
    ::= { cgprsAccPtMIBGroups 33 }

cgprsAccPtIpv6GroupSup1 OBJECT-GROUP
    OBJECTS         { cgprsAccPtIpv6AddrAllocations }
    STATUS          current
    DESCRIPTION
        "This group supplements cgprsAccPtIpv6Group to
        provide Ipv6 address allocation status."
    ::= { cgprsAccPtMIBGroups 34 }

cgprsAccPtStatisticsGroupSup4 OBJECT-GROUP
    OBJECTS         {
                        cgprsAccPtActiveBearers,
                        cgprsAccPtDhcpProxServTxErrDrops,
                        cgprsAccPtDhcpProxServIpAllocErr,
                        cgprsAccPtDedBearerDeactivations,
                        cgprsAccPtDedBearerQosUpdate,
                        cgprsAccPtDedBearerSucQosUpdate,
                        cgprsAccPtDedBearerNoQosUpdate,
                        cgprsAccPtDedBearerSucNoQosUpdate
                    }
    STATUS          current
    DESCRIPTION
        "A collection of objects providing GPRS access point
        performance statistics per name."
    ::= { cgprsAccPtMIBGroups 35 }

cgprsAccPtDhcpv6ProxyStatsGroup OBJECT-GROUP
    OBJECTS         {
                        cgprsAccPtDhcpv6ProxInforeqRcvd,
                        cgprsAccPtDhcpv6ProxInforeqRply,
                        cgprsAccPtDhcpv6ProxInforeqLocRply,
                        cgprsAccPtDhcpv6ProxIpAllocSuc,
                        cgprsAccPtDhcpv6ProxIpAllocFail,
                        cgprsAccPtDhcpv6ProxIpRelease,
                        cgprsAccPtDhcpv6ProxIpRenewFail,
                        cgprsAccPtDhcpv6ProxUnkwnMsg,
                        cgprsAccPtDhcpv6ProxErrs
                    }
    STATUS          current
    DESCRIPTION
        "A collection of objects providing DHCPv6 proxy server
        performance statistics for each GPRS access point."
    ::= { cgprsAccPtMIBGroups 36 }

cgprsAccPtExtMIBGroupSup2 OBJECT-GROUP
    OBJECTS         {
                        cgprsAccPtVerifyDownlinkAddr,
                        cgprsAccPtDhcpv6ProxClientIntf,
                        cgprsAccptDhcpv6RapidCommit,
                        cgprsAccptDhcpv6PoolName
                    }
    STATUS          current
    DESCRIPTION
        "This group supplements cgprsAccPtExtMIBGroupRev3 to provide
        APN configurations."
    ::= { cgprsAccPtMIBGroups 37 }

cgprsAccPtStatisticsGroupSup5 OBJECT-GROUP
    OBJECTS         {
                        cgprsAccPtIpv4v6MsActivatedDynamicPdps,
                        cgprsAccPtIpv4v6MsSuccActivatedDynamicPdps
                    }
    STATUS          current
    DESCRIPTION
        "A collection of objects providing GPRS access point
        performance statistics per name."
    ::= { cgprsAccPtMIBGroups 38 }

cgprsAccPtStatisticsGroupSup6 OBJECT-GROUP
    OBJECTS         {
                        cgprsAccPtFailMsActivatedPdps,
                        cgprsAccPtFailPdpUpdate,
                        cgprsAccPtUpdateRspTimeOut
                    }
    STATUS          current
    DESCRIPTION
        "A collection of objects providing GPRS access point
        performance statistics per name."
    ::= { cgprsAccPtMIBGroups 39 }

END
