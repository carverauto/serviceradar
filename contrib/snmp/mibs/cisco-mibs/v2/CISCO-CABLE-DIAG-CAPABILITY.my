-- *****************************************************************
-- CISCO-CABLE-DIAG-CAPABILITY.my:
-- CISCO-CABLE-DIAG-MIB AGENT-CAPABILITIES
--
-- February 2004, Lilian Jiang 
--
-- Copyright (c) 2004 by Cisco Systems, Inc.
-- All rights reserved.
-- *****************************************************************

CISCO-CABLE-DIAG-CAPABILITY DEFINITIONS ::= BEGIN

IMPORTS
        MODULE-IDENTITY
                FROM SNMPv2-SMI
        AGENT-CAPABILITIES
                FROM SNMPv2-CONF
        ciscoAgentCapability
                FROM CISCO-SMI;

ciscoCableDiagCapability MODULE-IDENTITY
        LAST-UPDATED    "200402030000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The agent capabilities description of 
                CISCO-CABLE-DIAG-MIB."
        REVISION        "200402030000Z"
        DESCRIPTION
                "Initial version of this MIB module."
        ::= { ciscoAgentCapability 394 }

ciscoCableDiagCapCatOSV08R0301 AGENT-CAPABILITIES
    PRODUCT-RELEASE     "Cisco CatOS 8.3(1) on Catalyst 6000/6500
                        and Cisco 7600 series devices."
    STATUS              current
    DESCRIPTION         "CISCO-CABLE-DIAG-MIB agent capabilities."

    SUPPORTS            CISCO-CABLE-DIAG-MIB
        INCLUDES        { 
                          ccdPrbsGroup,
                          ccdTdrGroup
                        }
    ::= { ciscoCableDiagCapability 1 }

END
