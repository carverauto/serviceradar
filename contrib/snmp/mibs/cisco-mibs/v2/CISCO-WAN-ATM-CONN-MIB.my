-- *****************************************************************
-- CISCO-WAN-ATM-CONN-MIB.my: CISCO MSSBU ATM connection MIB
--
-- July 2002, muthumayan
--
-- Copyright (c) 1998-2003 by cisco Systems, Inc.
-- All rights reserved.
-- 
-- *****************************************************************
-- 
--                   SPVC provisioning Model
--                   =======================
-- 
-- To use this MIB it is essential to understand the provisioning 
-- model employed in MGX8800 Series products. This provisioning model 
-- was designed considering the multiple types of services such as 
-- frame relay,circuit emulation, voice etc. that need to be supported.
-- 
-- To start with, the connection termination points are termed 
-- `endpoints'. These endpoints derive their characteristics from
-- from the type of service they handle. Thus frame relay endpoints
-- are characterised by a frame relay identifier (DLCI) and the 
-- committed frame rate and so on. The endpoints could also 
-- terminate an ATM interface.
-- 
-- The connection between these endpoints is a switched ATM virtual
-- circuit (SVC). The routing of a connection within an ATM network
-- is handled by a network `controller' e.g PNNI.
-- 
-- From a user perspective, the endpoint is identified by:
-- * physical entities: nodename, shelf, slot, physical line
-- * logical entities : this could be a DLCI in a frame relay.
--                      or a T1 slot number in a voice card
--                      or a VPI/VCI in an ATM card.
-- 
-- We term the above identifiers as `user addresses'. There is yet
-- another set of addresses that define the endpoints within an
-- ATM network. This is the address of the endpoint, as known to
-- the network controller and hence termed `network address'.
-- The network address is assigned by the switch (MGX) when a
-- user provisions an endpoint. The network address is of little
-- significance from the user's perspective, but is mandatory for
-- routing a connection. The network address in this ATM network
-- is a combination of an NSAP address (a 20 octet number uniquely
-- identifying a logical interface) and a VPI/VCI within this 
-- interface.
-- 
-- In any switched network, there is always a `calling' and a 
-- `called' party. Likewise in the ATM network, one endpoint is
-- responsible for setting up the connection (making a call).
-- This endpoint is termed the `master' endpoint, the other one
-- being the slave. To route a call from the master to slave, the
-- master endpoint needs to know the `network' address of the
-- slave endpoint. And this information needs to be conveyed 
-- when provisioning a master endpoint.
-- 
-- This imposes a sequence in provisioning a connection:
-- * The NMS first adds the slave endpoint. The slave endpoint's
--   user address is specified during the add operation. The
--   switch assigns a network address to this added endpoint.
-- * NMS gets the slave's network address from switch.
-- * NMS adds the master endpoint. The master's user address
--   is specified, along with the slave's network address.
-- * SPVC provisioning is deemed successful, only if both the
--   endpoints are added. The routing of the connection takes
--   place only after the master endpoint is added.
-- 
-- *****************************************************************

CISCO-WAN-ATM-CONN-MIB DEFINITIONS ::= BEGIN
IMPORTS
        MODULE-IDENTITY,
        OBJECT-TYPE,
        Integer32, Unsigned32
                                                FROM SNMPv2-SMI
        RowStatus,TruthValue,
        TEXTUAL-CONVENTION                      FROM SNMPv2-TC
        MODULE-COMPLIANCE, OBJECT-GROUP         FROM SNMPv2-CONF
        ifIndex                                 FROM IF-MIB
        ciscoWan                                FROM CISCOWAN-SMI;


ciscoWanAtmConnMIB      MODULE-IDENTITY
        LAST-UPDATED    "200303300000Z"
        ORGANIZATION    "Cisco Systems, Inc."
        CONTACT-INFO
                "       Cisco Systems
                        Customer Service

                Postal: 170 W Tasman Drive
                        San Jose, CA 95134
                        USA

                        Tel: +1 800 553-NETS

                E-mail: cs-wanatm@cisco.com"

        DESCRIPTION
           "This MIB is used for configuring/provisioning SPVCs on
            the ATM interfaces. This is used for ATM switch
            connection management.

            Terminologies used:
            GCRA - The Generic Cell Rate Algorithm(GCRA) is used to
                   define comformance with repect to the traffic
                   contract.For each cell arrival, the GCRA determines
                   whether the cell conforms to the traffic contract
                   of the connection.
            PCR  - The Peak Cell Rate(PCR) traffic parameter specifies
                   an upper bound on the rate at which traffic can
                   be submitted on an ATM connection.
            SCR  - Sustained Cell Rate.
            MBS  - Maximum Burst Size.
            MCR  - Minimum Cell Rate is the rate at which the source
                   is always allowed to send.
            ACR  - Allowed Cell Rate is the current rate at which
                   a source is allowed to send.
            RDF  - Rate Decrease Factor controls the decrease in the
                   cell transmission rate
            CRM  - Missing RM-cell count. CRM limits the number of 
                   forward RM-cells which may be sent in the absence
                   of received backward RM-cells.
            CDF  - The Cutoff Decrease Factor controls the decrease
                   in ACR assoicated with the CRM.              

            CDVT - Cell Delay Transfer Variation Tolerance

            CBR  - The Constant Bit Rate(CBR) service category is used
                   by connections that request a static amount of 
                   bandwidth that is continuously available during the 
                   connection lifetime. This amount of bandwidth is
                   characterized by a PCR value.
          rt-VBR - The real-time Variable Bit Rate(rt-VBR) service
                   category is intended for real-time applications,
                   i.e.,those requiring tightly constrainded delay
                   and delay variation, as would be appropriate for
                   voice and video applications.The rt-VBR connections
                   are characterized in terms of a PCR, SCR and MBS.
         nrt-VBR - The non-real-time Variable Bit Rate(nrt-VBR)
                   service category is intended for non-real-time
                   applications which have bursty traffic 
                   characteristics. The nrt-VBR is characterized
                   in terms of a PCR,SCR and MBS.
            UBR  - The Unspecified Bit Rate(UBR) service category is
                   intended for non-real-time applications,i.e.,those 
                   not requiring tightly constrained delay and delay
                   variation. The UBR service does not specify traffic
                   related service gurantees. The UBR service is
                   indicated by use of the Best Effort Indicator in
                   ATM User Cell Rate Information element.
            ABR  - The Available Bit Rate(ABR) is an ATM layer 
                   service category for which the limiting ATM layer
                   transfer characteristics provided by the network
                   may change subsequent to connection establishment.

            CAC  - The Connection Admission Control(CAC) function is
                   defined as the set of actions taken by the network
                   at SVC establishment or by network management during
                   PVC establishment in order to determine whether
                   a connection can be progressed or should be rejected.
            UPC  - Usage Parameter Control(UPC) is defined as the set
                   of actions taken by the network to monitor and
                   control traffic.
                "

        REVISION        "200303300000Z"
        DESCRIPTION     "a) MAX-ACCESS clauses of objects in cwAtmChanTestTable 
                            are changed from read-create to read-write
                            since this table does not have RowStaus object.
                        "
        REVISION        "200209180000Z"
        DESCRIPTION  "a) Added following objects in cwAtmChanCnfgTable: 
                      cwaChanP2MP

                      b) The DESCRIPTION of following objects are
                         updated as a result of adding 
                         'cwaChanP2MP' object:
                         'cwaChanRemoteVpi', 'cwaChanRemoteVci',
                         'cwaChanRemoteNSAPAddr', 'cwaChanRemotePCR', 
                         'cwaChanRemoteMCR', 'cwaChanRemoteSCR',
                         'cwaChanRemoteCDV', 'cwaChanRemoteCTD',
                         'cwaChanRemoteMBS', 'cwaChanRemoteCDVT',
                         'cwaChanRemotePercentUtil', 'cwaChanRemoteCLR' 
                         and 'cwaChanSlaveType'

                      c) Importing Unsigned32 from SNMPv2-SMI.
                      d) Added  'cwGlobalChanDataTable'  Table.
                      e) Added following objects in cwAtmChanCnfgTable: 
                            cwaChanPrefRouteId      
                            cwaChanDirectRoute       
               "

        REVISION     "200203240000Z"
        DESCRIPTION  "a) Added following objects in cwAtmChanCnfgTable:
                           cwaChanSlaveType 
                           cwaChanRoutingPriority.
  
                      b) Added following objects under cwAtmChanInformation:
                           cwaChanNumVPCsInAlarm
                           cwaChanNumVCCsInAlarm.

                      c) Clarified the ifIndex usage in DESCRIPTION of
                         cwAtmChanCnfgEntry.
            
                      d) Updated the DESCRIPTION of following objects:
                          cwaChanServiceCategory
                          cwaChanVpcFlag
                          cwaChanIdentifier
                          cwaChanRowStatus

                      e) Modified the range from 0..100 to 1..100 for
                         following objects:
                            cwaChanPercentUtil
                            cwaChanRemotePercentUtil.
                      f) Deprecated following objects:
                            cwaChanAbrERS
                            cwaChanAisIWCapability
                        "

        REVISION     "200102090000Z"
        DESCRIPTION  "Update description for cwaChanVpcFlag,
                      cwaChanStatsEnable, 
                      cwaChanRoutingMastership, and cwaChanAbrVSVDEnable"

        REVISION     "200101030000Z"
        DESCRIPTION  "Change description to indicate that cwaChanCDV,
                      cwaChanCTD, cwaChanRemoteCDV, cwaChanRemoteCTD and
                      cwaChanMaxCost parameters cannot be set on a
                      slave endpoint."

        REVISION     "200011150000Z"
        DESCRIPTION  "Added cwaChanOamSegEpEnable object in
                     cwAtmChanCnfgTable."

        REVISION     "200007170000Z"
        DESCRIPTION  "Deprecated object cwaChanRemoteCDVT"

        REVISION     "200006190000Z"
        DESCRIPTION  "Initial version of the MIB"
        ::= { ciscoWan 1 }


cwConnMibObjects        OBJECT IDENTIFIER ::= { ciscoWanAtmConnMIB 1 }
cwAtmChanCnfg           OBJECT IDENTIFIER ::= { cwConnMibObjects 1 }
cwAtmChanState          OBJECT IDENTIFIER ::= { cwConnMibObjects 2 }
cwAtmChanTest           OBJECT IDENTIFIER ::= { cwConnMibObjects 3 }
cwAtmChanInformation    OBJECT IDENTIFIER ::= { cwConnMibObjects 4 }
cwGlobalChanDataGroup   OBJECT IDENTIFIER ::= { cwConnMibObjects 5 }


-- ----------------------------------------------------------------------------
-- TEXTUAL CONVENTIONS USED IN THIS MIB
-- ----------------------------------------------------------------------------

CiscoAtmServiceCategory ::= TEXTUAL-CONVENTION
        STATUS  current
        DESCRIPTION
                "The ATM forum service categories.
                 For sake of backward compatibility with UNI3.1, two CBR
                 service types cbr2 and cbr3 have been added.
                "
        REFERENCE "ATM Forum Traffic Management Specification Version 4.0
                   Section 4.5.4"
        SYNTAX  INTEGER { 
                cbr1(1),
                vbr1RT(2),
                vbr2RT(3),
                vbr3RT(4),
                vbr1nRT(5),
                vbr2nRT(6),
                vbr3nRT(7),
                ubr1(8),
                ubr2(9),
                abr(10),
                cbr2(11),
                cbr3(12)
        }

CiscoWanLpbkTypes ::= TEXTUAL-CONVENTION
        STATUS  current
        DESCRIPTION
          "Defines possible loopback configurations for a connection:
           noLoopback    : no loopback or clear configured loopback
           destructive   : loopback all cells, causing data disruption.
           nonDestructive: loopback performed using OAM loopback cells.
                           Does not disrupt regular traffic."
        SYNTAX  INTEGER {
                noLpbk(1),
                destructive(2),
                nonDestructive(3)
        }

CiscoWanLpbkDir ::= TEXTUAL-CONVENTION
        STATUS  current
        DESCRIPTION
                "Direction in which looped should be effected:
                external : loop port traffic back to port. Applicable
                            only for destructive mode.
                internal : loop switch's egress traffic back to switch.
                           Applicable only for destructive mode.
                forward  : inject OAM loopback cells towards the
                           switching fabric (ingress). Applicable only
                           for non-destructive mode.
                reverse  : inject OAM loopback cells towards the
                           port (egress). Applicable only for non-
                           destructive mode."
        SYNTAX  INTEGER {
                external(1),
                internal(2),
                forward(3),
                reverse(4)
        }

CiscoWanTestStatus ::= TEXTUAL-CONVENTION
        STATUS  current
        DESCRIPTION
                "Defines possible loopback test status at an endpoint."
        SYNTAX  INTEGER {
                noStatus (1),
                lpbkInProgress(2),
                lpbkSuccess(3),
                lpbkAbort(4),
                lpbkTimeOut(5),
                lpbkInEffect(6)
        }

CiscoWanOperStatus ::= TEXTUAL-CONVENTION
        STATUS  current
        DESCRIPTION
                "Defines operational status of an endpoint"
        SYNTAX  INTEGER {
                operOk(1),
                operFail(2),
                adminDown(3)
        }

CiscoWanNsapAtmAddress ::= TEXTUAL-CONVENTION
        STATUS  current
        DESCRIPTION
                "ATM address used by the networking entity. The only 
                address type presently supported is NSAP (20 octets)"
        SYNTAX  OCTET STRING (SIZE(20))


CiscoWanAlarmState ::= TEXTUAL-CONVENTION
        STATUS  current
        DESCRIPTION
                "Defines possible alarms at an endpoint:
                ingAisRdi       : Endpoint receiving AIS or RDI cells
                                  in ingress direction
                egrAisRdi       : Endpoint receiving AIS or RDI cells
                                  in egress direction
                conditioned     : Networking entity has forced the 
                                  endpoint out of service. This could
                                  be attributed to either routing 
                                  failure or to a maintenance operation
                                  initiated by the networking entity.
                interfaceFail   : The interface to which this connection
                                  belongs has failed.
                ccFail          : The OAM continuity check between the
                                  connection and its peer endpoint has
                                  detected a failure.
                mismatch        : connection exists in SM database, but
                                  not in the network controller database
                ingAbitFail     : Feeder connection detects A-bit failure
                                  in the ingress direction.

                Each of the alarm conditions is represented as a bit of an
                integer. Hence a value of zero indicates that there are no
                alarms."
        SYNTAX  INTEGER {
                ingAisRdi (1),
                egrAisRdi (2),
                conditioned (4),
                interfaceFail(8),
                ccFail(16),
                mismatch (32),
                ingAbitFail (64)
        }


CiscoWanXmtState ::= TEXTUAL-CONVENTION
        STATUS  current
        DESCRIPTION
                "Defines possible transmit states of an endpoint:
                normal          : Endpoint transmitting normal traffic.
                sendingAIS      : Endpoint inhibits regular traffic,
                                  sends AIS on egress
                sendingRDI      : Endpoint inhibits regular traffic,
                                  sends AIS on egress"
        SYNTAX  INTEGER {
                normal(1),
                sendingAIS(2),
                sendingRDI(3)
        }


CiscoWanRcvState ::= TEXTUAL-CONVENTION
        STATUS  current
        DESCRIPTION
                "Defines possible receive states of an endpoint
                normal          : Endpoint receiving normal traffic.
                receivingAIS    : Endpoint receiving AIS, in either 
                                  ingress/egress
                receivingRDI    : Endpoint receiving RDI, in either
                                  ingress/egress
                ccFailure       : Endpoint does not receive OAM CC cells"
        SYNTAX  INTEGER {
                normal(1),
                receivingRDI(2),
                receivingAIS(3),
                ccFailure(4)
        }


CiscoWanERSConfg ::= TEXTUAL-CONVENTION
        STATUS  current
        DESCRIPTION
                "Defines possible configuration for Explicit Rate Stamping (ERS):
                None            : Disable the ERS on connection
                enableIngress   : Enable ERS in the Ingress direction ONLY
                enableEgress    : Enable ERS in the Engress direction ONLY
                enableBoth      : Enable ERS in both direction"
        SYNTAX  INTEGER {
                none(1),
                enableIngress(2),
                enableEgress(3),
                enableBoth(4)
        }

CiscoWanVSVDConfg ::= TEXTUAL-CONVENTION
        STATUS  current
        DESCRIPTION
                "Defines possible VSVD configuration applicable to an endpoint:
                vsvdOff         : Disable VSVD
                vsvdOn          : Enable VSVD
                switchDefault   : Use default settings on switch."
        SYNTAX INTEGER {
                vsvdOff(1),
                vsvdOn(2),
                switchDefault(3)
        }

CiscoWanAisIW ::= TEXTUAL-CONVENTION
        STATUS  current
        DESCRIPTION
                "Defines an SPVC endpoint's AIS capability:
                e2eAisCapable   : Endpoint capable of detecting/generating 
                                  e2e AIS.
                segAisCapable   : Endpoint capable of detecting/generating seg
                                  AIS."
        SYNTAX INTEGER {
                e2eAisCapable(1),
                segAisCapable(2)
        }

AbrRateFactors ::= TEXTUAL-CONVENTION
        STATUS  current
        DESCRIPTION
                "Defines possible rate factors to be used in 
                 increasing/decreasing ABR cell rate."
        SYNTAX  INTEGER {
                oneOver32768(1),
                oneOver16384(2),
                oneOver8192(3),
                oneOver4096(4),
                oneOver2048(5),
                oneOver1024(6),
                oneOver512(7),
                oneOver256(8),
                oneOver128(9),
                oneOver64(10),
                oneOver32(11),
                oneOver16(12),
                oneOver8(13),
                oneOver4(14),
                oneOver2(15),
                one(16)
        }


-- ------------------------------------------------------------------------
-- Channel configuration group : Contains all objects required for 
-- configuring a SPVC on a ATM Capable Service Module.
-- ------------------------------------------------------------------------

cwAtmChanCnfgTable      OBJECT-TYPE
        SYNTAX          SEQUENCE OF CwAtmChanCnfgEntry
        MAX-ACCESS      not-accessible
        STATUS          current
        DESCRIPTION
                "This table contains mandatory endpoint configuration
                for all SPVC connections.Most of the objects in this
                table are applicable to all provisioned endpoints for all
                service categories. The objects cwaChanAbrZZZ however,
                provide additional configuration information which apply
                to ABR endpoints only.
                
                Routing parameters 'cwaChanCDV', 'cwaChanCTD',
                'cwaChanRemoteCDV', 'cwaChanRemoteCTD' and 
                'cwaChanMaxCost' cannot be set
                on a slave endpoint(i.e.if 'cwaChanRoutingMastership'
                is set to 'false')."
        ::= { cwAtmChanCnfg 1 }

 
cwAtmChanCnfgEntry      OBJECT-TYPE
        SYNTAX          CwAtmChanCnfgEntry
        MAX-ACCESS      not-accessible
        STATUS          current
        DESCRIPTION
                "An entry in the cwAtmChanCnfgTable. The each entry
                 corresponds to a connection endpoint identified
                 by interface(ifIndex),Virtual Path Identifier(VPI)
                 and Virtual Channel Identifier(VCI). The ifIndex
                 is for those entries in ifTable identified by
                 ifType values atmVirtual(149) and propAtm(197)."
        INDEX   { ifIndex, cwaChanVpi, cwaChanVci }
        ::= { cwAtmChanCnfgTable 1 }


CwAtmChanCnfgEntry ::=
        SEQUENCE {
                cwaChanVpi                      Unsigned32,
                cwaChanVci                      Unsigned32,
                cwaChanServiceCategory          CiscoAtmServiceCategory,
                cwaChanVpcFlag                  TruthValue,

                cwaChanIdentifier               Unsigned32,
                cwaChanUploadCounter            Unsigned32,

                cwaChanStatsEnable              TruthValue,
                cwaChanCCEnable                 TruthValue,

                cwaChanLocalVpi                 Unsigned32,
                cwaChanLocalVci                 Unsigned32,
                cwaChanLocalNSAPAddr            CiscoWanNsapAtmAddress,

                cwaChanRemoteVpi                Unsigned32,
                cwaChanRemoteVci                Unsigned32,
                cwaChanRemoteNSAPAddr           CiscoWanNsapAtmAddress,

                cwaChanControllerId             Unsigned32,
                cwaChanRoutingMastership        TruthValue,
                cwaChanMaxCost                  Unsigned32,
                cwaChanReroute                  TruthValue,
                cwaChanFrameDiscard             TruthValue,
                cwaChanOperStatus               CiscoWanOperStatus,

                cwaChanPCR                      Unsigned32,
                cwaChanMCR                      Unsigned32,
                cwaChanSCR                      Unsigned32,
                cwaChanCDV                      Unsigned32,
                cwaChanCTD                      Unsigned32,
                cwaChanMBS                      Unsigned32,
                cwaChanCDVT                     Unsigned32,
                cwaChanPercentUtil              Unsigned32,

                cwaChanRemotePCR                Unsigned32,
                cwaChanRemoteMCR                Unsigned32,
                cwaChanRemoteSCR                Unsigned32,
                cwaChanRemoteCDV                Unsigned32,
                cwaChanRemoteCTD                Unsigned32,
                cwaChanRemoteMBS                Unsigned32,
                cwaChanRemoteCDVT               Unsigned32,
                cwaChanRemotePercentUtil        Unsigned32,

                cwaChanAbrICR                   Unsigned32,
                cwaChanAbrADTF                  Unsigned32,
                cwaChanAbrRDF                   AbrRateFactors,
                cwaChanAbrRIF                   AbrRateFactors,
                cwaChanAbrNRM                   INTEGER,
                cwaChanAbrTRM                   INTEGER,
                cwaChanAbrCDF                   INTEGER,
                cwaChanAbrFRTT                  Unsigned32,
                cwaChanAbrTBE                   Unsigned32,
                cwaChanAbrERS                   CiscoWanERSConfg,

                cwaChanAbrVSVDEnable            TruthValue,
                cwaChanRowStatus                RowStatus,

                cwaChanIntAbrVSVD               CiscoWanVSVDConfg,
                cwaChanExtAbrVSVD               CiscoWanVSVDConfg,
                cwaChanAisIWCapability          CiscoWanAisIW,
                cwaChanCLR                      Unsigned32,
                cwaChanRemoteCLR                Unsigned32,
                cwaChanOamSegEpEnable           INTEGER,
                cwaChanSlaveType                INTEGER,
                cwaChanRoutingPriority          Integer32,
                cwaChanP2MP                     TruthValue,
                cwaChanPrefRouteId              Integer32,  
                cwaChanDirectRoute              TruthValue
        }
 
cwaChanVpi              OBJECT-TYPE
        SYNTAX          Unsigned32 (0..4095)
        MAX-ACCESS      not-accessible
        STATUS          current
        DESCRIPTION
                "The VPI value of a VP or VC connection. The cwaChanVpcFlag
                serves to distinguish if this is a VP/VC connection"
        ::= { cwAtmChanCnfgEntry 1 }

cwaChanVci              OBJECT-TYPE
        SYNTAX          Unsigned32 (0..65535)
        MAX-ACCESS      not-accessible
        STATUS          current
        DESCRIPTION
                "The VCI value of VC connection. The cwaChanVpcFlag serves 
                to distinguish if this is a VP/VC connection. For a VPC, 
                the VCI is irrelevant and is set to a value of 0"
        ::= { cwAtmChanCnfgEntry 2 }

cwaChanServiceCategory  OBJECT-TYPE
        SYNTAX          CiscoAtmServiceCategory
        MAX-ACCESS      read-create
        STATUS          current
        DESCRIPTION
                "This object identifies the service type to which
                this connection belongs. The service type specified
                is one among the ATM forum service types and 
                implicitly determines the configuration for GCRA.
               
                This Object can be set only during row creation."
        ::= { cwAtmChanCnfgEntry 3 }

cwaChanVpcFlag          OBJECT-TYPE
        SYNTAX          TruthValue
        MAX-ACCESS      read-create
        STATUS          current
        DESCRIPTION
                "This object indentifies if the endpoint is a
                VP/VC endpoint. For a VPC, this object is set to 
                true(1); For a VCC, this object is set to false(2).

                This Object can be set only during row creation."
        ::= { cwAtmChanCnfgEntry 4 }

cwaChanIdentifier       OBJECT-TYPE
        SYNTAX          Unsigned32 (0..4294967295)
        MAX-ACCESS      read-only
        STATUS          current
        DESCRIPTION
                "This number represents a RESOURCE at the switch that
                has been assigned for this connection (identified
                by ifIndex, cwaChanVpi and cwaChanVci). An example of this
                resource could be the LCN/GLCN used by the switch. Another 
                example could be a record number assigned for this connection 
                in a database of records.

                When a connection gets deleted, this resource gets 
                released into a free pool. When a new endpoint is added
                (different ifIndex, cwaChanVpi & cwaChanVci), the switch may
                re-assign this resource.

                Thus all connections in a switch would have an unique
                cwaChanIdentifier. Since the number of resources in the
                switch is a much lesser subset as compared to all possible
                combinations of ifIndex, vpi and vci, this number serves as 
                a quick reference index between the switch and the NMS.

                This is especially useful during the configuration upload
                of connections from the switch to the NMS."
        ::= { cwAtmChanCnfgEntry 5 }

cwaChanUploadCounter    OBJECT-TYPE             
        SYNTAX          Unsigned32 (0..4294967295)
        MAX-ACCESS      read-only
        STATUS          current
        DESCRIPTION
            "This counter tracks the number of configuration changes
            that happen on a specific endpoint (identified by ifIndex,
            cwaChanVpi, and cwaChanVci).

            The value of this object is derived from 
            cwChanGlobalTransactionId. For every connection changes
            (add/delete/modify/up/down), the value of
            cwChanGlobalTransactionId is incremented and that value
            is used for this object.

            This counter is used by the NMS to determine if a connection
            configuration had been modified and requires an upload."
        ::= { cwAtmChanCnfgEntry 6 }

cwaChanStatsEnable      OBJECT-TYPE             
        SYNTAX          TruthValue
        MAX-ACCESS      read-create
        STATUS          current
        DESCRIPTION
                "Limits imposed by software or hardware implementations
                could restrict the amount of statistical data that can be
                maintained in a physical entity (like a service module card).
                Hence there could be a need to restrict statistics collection
                to a smaller subset.
                This object serves the purpose of enabling/disabling statistics
                collection on a per connection basis. In implementations which 
                do not have such limitations, this object can be set to true(1) 
                for all connections.
                When set to true(1), statistics collection is enabled; 
                When set to false(2), stats collection is disabled"
        DEFVAL { false }
        ::= { cwAtmChanCnfgEntry 7 }

cwaChanCCEnable         OBJECT-TYPE             
        SYNTAX          TruthValue
        MAX-ACCESS      read-create
        STATUS          current
        DESCRIPTION
                "This object serves to enable or disable continuity check(CC)
                on a connection endpoint. When continuity check is enabled 
                on an endpoint, the endpoint anticipates OAM CC cells from its
                peer endpoint. OAM CC cells are sent when the peer endpoint
                does not have traffic cells to send. If the connection is
                idle and this endpoint has not received OAM CC cells for a 
                period of 3.5 +/- 0.5 seconds, it declares continuity failure.

                This object serves to administratively control the CC feature.
                Typical implementations (of this feature) may choose to ignore
                this control or impose other conditions to actually enable CC 
                cell flow. However, if this object is set to false(2), then this 
                feature should be disabled"
        DEFVAL { false }
        ::= { cwAtmChanCnfgEntry 8 }

cwaChanLocalVpi         OBJECT-TYPE
        SYNTAX          Unsigned32 (0..4095)
        MAX-ACCESS      read-only
        STATUS          current
        DESCRIPTION
                "This object identifies the internal VPI assigned to a local
                endpoint, by the switch. The cwaChanLocalVpi, cwaChanLocalVci
                and the cwaChanLocalNSAPAddr, form a unique identifier for
                the connection endpoint in the networking domain"
        ::= { cwAtmChanCnfgEntry 9 }

cwaChanLocalVci         OBJECT-TYPE
        SYNTAX          Unsigned32 (0..65535)
        MAX-ACCESS      read-only
        STATUS          current
        DESCRIPTION
                "This object identifies the internal VCI assigned to a local
                endpoint, by the switch. The cwaChanLocalVpi, cwaChanLocalVci
                and the cwaChanLocalNSAPAddr, form a unique identifier for
                the connection endpoint in the networking domain"
        ::= { cwAtmChanCnfgEntry 10 }

cwaChanLocalNSAPAddr    OBJECT-TYPE
        SYNTAX          CiscoWanNsapAtmAddress
        MAX-ACCESS      read-only
        STATUS          current
        DESCRIPTION
                "This object identifies the internal NSAP assigned to a local
                endpoint, by the switch. The cwaChanLocalVpi, cwaChanLocalVci
                and the cwaChanLocalNSAPAddr, form a unique identifier for
                the connection endpoint in the networking domain"
        ::= { cwAtmChanCnfgEntry 11 } 

cwaChanRemoteVpi        OBJECT-TYPE
        SYNTAX          Unsigned32 (0..4095)
        MAX-ACCESS      read-create
        STATUS          current
        DESCRIPTION
                "This object identifies the VPI of the peer endpoint. The 
                cwaChanRemoteVpi, cwaChanRemoteVpi and the 
                cwaChanRemoteNSAPAddr, identify the peer endpoint in 
                the networking domain.

                If the object 'cwaChanP2MP' is set to 'true', this object
                should not be 'set' and the value
                of this object, if any, is not meaningful.

                This Object can be set only during row creation."
        ::= { cwAtmChanCnfgEntry 12 }

cwaChanRemoteVci        OBJECT-TYPE
        SYNTAX          Unsigned32 (0..65535)
        MAX-ACCESS      read-create
        STATUS          current
        DESCRIPTION
                "This object identifies the VCI of the peer endpoint. The 
                cwaChanRemoteVpi, cwaChanRemoteVpi and the 
                cwaChanRemoteNSAPAddr, identify the peer endpoint in 
                the networking domain.

                If the object 'cwaChanP2MP' is set to 'true', this object
                should not be 'set' and the value
                of this object, if any, is not meaningful.

                This Object can be set only during row creation."
        ::= { cwAtmChanCnfgEntry 13 }

cwaChanRemoteNSAPAddr   OBJECT-TYPE
        SYNTAX          CiscoWanNsapAtmAddress
        MAX-ACCESS      read-create
        STATUS          current
        DESCRIPTION
                "This object identifies the NSAP of the peer endpoint. The 
                cwaChanRemoteVpi, cwaChanRemoteVpi and the 
                cwaChanRemoteNSAPAddr, identify the peer endpoint in 
                the networking domain.

                If the object 'cwaChanP2MP' is set to 'true', this object
                should not be 'set' and the value
                of this object, if any, is not meaningful.

                This Object can be set only during row creation."
        ::= { cwAtmChanCnfgEntry 14 } 

cwaChanControllerId     OBJECT-TYPE
        SYNTAX          Unsigned32 (1..255)
        MAX-ACCESS      read-create
        STATUS          current
        DESCRIPTION
                "This object serves to associate an endpoint with a specific
                controller. Usually resource partitioning makes the association 
                between a controller and a range of vpi-vci. There could be
                switches where hard partitioning of vpi-vci may not be 
                implemented, in which case this object serves to tie a 
                specific vpi-vci to a controller.
                This object can not be modified after the row is created."
         ::= { cwAtmChanCnfgEntry 15 } 

cwaChanRoutingMastership OBJECT-TYPE
        SYNTAX          TruthValue
        MAX-ACCESS      read-create
        STATUS          current
        DESCRIPTION
                "This object, if set to true(1) identifies that this endpoint
                as the `master' endpoint of the connection. When set to false(2)
                this identifies the `slave' endpoint of the connection. The
                slave endpoint is the called party, while the master endpoint
                is the calling party in the SPVC call setup. The networking 
                entity initiates routing of a SPVC connection only after a 
                master endpoint is added. Mastership of a SPVC cannot be
                changed, once provisioned, implying that this object can 
                be set only during row creation."
        DEFVAL { false }
         ::= { cwAtmChanCnfgEntry 16 } 

cwaChanMaxCost          OBJECT-TYPE
        SYNTAX          Unsigned32 (0..4294967295)
        MAX-ACCESS      read-create
        STATUS          current
        DESCRIPTION
                "This object is used by the networking entity to select a route 
                based on administrative weight of possible routes.

                Administrative weights of links and nodes contained in a path
                are aggregated and compared against this object. The networking
                entity prefers a path whose aggregate administrative weight is 
                lesser than the value of this object.

                Setting this parameter to 0 indicates to the switch that only
                the best available route should be chosen. If this
                object is set to a value of 0xFFFFFFFF(4294967295),
                then switch ignore this metric in making routing decisions.

                This parameter is not allowed to be set on a slave endpoint.
                (i.e. if 'cwaChanRoutingMastership' is set to 'false')."
        DEFVAL { 'FFFFFFFF'h }
        ::= { cwAtmChanCnfgEntry 17 }

cwaChanReroute          OBJECT-TYPE
        SYNTAX          TruthValue
        MAX-ACCESS      read-create
        STATUS          current
        DESCRIPTION
                "This is used by the administrator to trigger the
                re-routing of the connection.

                * Rerouting takes effect, when this object is set to true(1).
                When set to false(2), no action is taken.

                * A get on this object always returns false(2).

                * When this object is set, no other object other than the
                RowStatus should be set in the MIB.

                * Reroute can be triggered only from the master endpoint.
                Any attempt to trigger reroute from the slave endpoint would
                result in a failure of the SET operation. "

        DEFVAL { false }
        ::= { cwAtmChanCnfgEntry 18 }

cwaChanFrameDiscard     OBJECT-TYPE
        SYNTAX          TruthValue
        MAX-ACCESS      read-create 
        STATUS          current
        DESCRIPTION
                "When set to true(1), enables the frame discard feature
                for the connection. This is applicable only to the master
                endpoint (cwaChanRoutingMastership is true) and only for
                VCC connections."
        DEFVAL { false }
        ::= { cwAtmChanCnfgEntry 19 }

cwaChanOperStatus       OBJECT-TYPE
        SYNTAX          CiscoWanOperStatus
        MAX-ACCESS      read-only 
        STATUS          current
        DESCRIPTION
                "Reflects operational status of an endpoint.
                * This object is set to operFail(2), if the connection is 
                  not routed or if the endpoint receives AIS/RDI or if there
                  is a CC failure.
                * If the connection is administratively down, this object 
                would be set to adminDown(3).
                * For a normal case, this is set to operOk(1)"
        ::= { cwAtmChanCnfgEntry 20 }

cwaChanPCR              OBJECT-TYPE
        SYNTAX          Unsigned32 (0..4294967295)
        UNITS           "cells per second"
        MAX-ACCESS      read-create
        STATUS          current
        DESCRIPTION
                "Peak cell rate (PCR) for the direction local -> remote"
        ::= { cwAtmChanCnfgEntry 21 }

cwaChanMCR              OBJECT-TYPE
        SYNTAX          Unsigned32 (0..4294967295)
        UNITS           "cells per second"
        MAX-ACCESS      read-create
        STATUS          current
        DESCRIPTION
                "Minimum cell rate (MCR) for the direction local -> remote"
        ::= { cwAtmChanCnfgEntry 22 }

cwaChanSCR              OBJECT-TYPE
        SYNTAX          Unsigned32 (0..4294967295)
        UNITS           "cells per second"
        MAX-ACCESS      read-create
        STATUS          current
        DESCRIPTION
                "Sustainable cell rate (SCR) for the direction local -> remote"
        ::= { cwAtmChanCnfgEntry 23 }

cwaChanCDV              OBJECT-TYPE
        SYNTAX          Unsigned32 (0..16777215)
        UNITS           "microseconds"
        MAX-ACCESS      read-create
        STATUS          current
        DESCRIPTION
                "Maximum tolerable cell delay variation in the direction 
                local -> remote.

                Setting this parameter to 0xFFFFFF(16777215) indicates to 
                the switch that this parameter does not have significance 
                in SPVC call setup.

                This parameter is not allowed to be set on a slave endpoint.
                (i.e. if 'cwaChanRoutingMastership' is set to 'false')."
        DEFVAL { 'FFFFFF'h }
        ::= { cwAtmChanCnfgEntry 24 }

cwaChanCTD              OBJECT-TYPE
        SYNTAX          Unsigned32 (0..65535)
        UNITS           "milliseconds"
        MAX-ACCESS      read-create
        STATUS          current
        DESCRIPTION
                "Maximum tolerable network transfer delay in the 
                direction local -> remote.

                Setting this parameter to 0xFFFF(65535) indicates to the 
                switch that this parameter does not have significance in 
                SPVC call setup.

                This parameter is not allowed to be set on a slave endpoint.
                (i.e. if 'cwaChanRoutingMastership' is set to 'false')."
        DEFVAL { 'FFFF'h }
        ::= { cwAtmChanCnfgEntry 25 }

cwaChanMBS              OBJECT-TYPE
        SYNTAX          Unsigned32 (0..5000000)
        UNITS           "cells"
        MAX-ACCESS      read-create
        STATUS          current
        DESCRIPTION
            "Maximum Burst Size (MBS) used in the direction local -> remote"
        REFERENCE
                "ATM Forum Traffice Management Specification Version 4.0
                 Annex C"
        ::= { cwAtmChanCnfgEntry 26 }

cwaChanCDVT             OBJECT-TYPE
        SYNTAX          Unsigned32 (0..4294967295)
        UNITS           "microseconds"
        MAX-ACCESS      read-create 
        STATUS          current
        DESCRIPTION
                "Cell delay variation tolerance(CDVT) used in the direction 
                local -> remote.

                Setting this parameter to 0xFFFFFFFF(4294967295) indicates to 
                the switch that it may use a default value of CDVT"
        REFERENCE
                "ATM Forum Traffice Management Specification Version 4.0
                 Annex C"
        DEFVAL { 'FFFFFFFF'h }
        ::= { cwAtmChanCnfgEntry 27 }
 
cwaChanPercentUtil      OBJECT-TYPE
        SYNTAX          Unsigned32 (1..100)
        MAX-ACCESS      read-create
        STATUS          current
        DESCRIPTION
                "This factor provides a per connection control
                for overbooking bandwidth. This is used in 
                conjunction with the VSI interface policy while
                performing CAC. This is applied for the direction
                local -> remote"
        DEFVAL { 100 }
        ::= { cwAtmChanCnfgEntry 28 } 

cwaChanRemotePCR        OBJECT-TYPE
        SYNTAX          Unsigned32 (0..4294967295)
        UNITS           "cells per second"
        MAX-ACCESS      read-create
        STATUS          current
        DESCRIPTION
                "Peak cell rate (PCR) for the direction remote -> local.

                If the object 'cwaChanP2MP' is set to 'true', this object
                should not be 'set' and the value
                of this object, if any, is not meaningful."
        ::= { cwAtmChanCnfgEntry 29 } 

cwaChanRemoteMCR        OBJECT-TYPE
        SYNTAX          Unsigned32 (0..4294967295)
        UNITS           "cells per second"
        MAX-ACCESS      read-create
        STATUS          current
        DESCRIPTION
                "Minimum cell rate for the direction remote -> local"
        ::= { cwAtmChanCnfgEntry 30 }

cwaChanRemoteSCR        OBJECT-TYPE
        SYNTAX          Unsigned32 (0..4294967295)
        UNITS           "cells per second"
        MAX-ACCESS      read-create
        STATUS          current
        DESCRIPTION
                "Sustainable cell rate for the direction remote -> local"
        ::= { cwAtmChanCnfgEntry 31 }

cwaChanRemoteCDV        OBJECT-TYPE
        SYNTAX          Unsigned32 (0..16777215)
        UNITS           "microseconds"
        MAX-ACCESS      read-create
        STATUS          current
        DESCRIPTION
                "Maximum tolerable cell delay variation for the direction 
                remote -> local.
                Setting this parameter to 0xFFFFFF(16777215) indicates to 
                the switch that this parameter does not have significance 
                in SPVC call setup.

                This parameter is not allowed to be set on a slave endpoint.
                (i.e. if 'cwaChanRoutingMastership' is set to 'false')."
        DEFVAL { 'FFFFFF'h }
        ::= { cwAtmChanCnfgEntry 32 }

cwaChanRemoteCTD        OBJECT-TYPE
        SYNTAX          Unsigned32 (0..65535)
        UNITS           "milliseconds"
        MAX-ACCESS      read-create
        STATUS          current
        DESCRIPTION
                "Maximum tolerable network transfer delay in the 
                direction direction remote -> local.

                Setting this parameter to 0xFFFF(65535) indicates to the switch
                that this parameter does not have significance in SPVC call 
                setup.

                This parameter is not allowed to be set on a slave endpoint.
                (i.e. if 'cwaChanRoutingMastership' is set to 'false').

                If the object 'cwaChanP2MP' is set to 'true', this object
                should not be 'set' and the value
                of this object, if any, is not meaningful."
        DEFVAL { 'FFFF'h }
        ::= { cwAtmChanCnfgEntry 33 }

cwaChanRemoteMBS        OBJECT-TYPE
        SYNTAX          Unsigned32 (0..5000000)
        UNITS           "cells"
        MAX-ACCESS      read-create
        STATUS          current
        DESCRIPTION
            "Maximum Burst Size (MBS) used in the direction remote -> local.
             If the object 'cwaChanP2MP' is set to 'true', this object
             should not be 'set' and the value
             of this object, if any, is not meaningful."
        REFERENCE
            "ATM Forum Traffice Management Specification Version 
            4.0 Annex C."
        ::= { cwAtmChanCnfgEntry 34 }

cwaChanRemoteCDVT       OBJECT-TYPE
        SYNTAX          Unsigned32 (0..4294967295)
        UNITS           "cells"
        MAX-ACCESS      read-create 
        STATUS          deprecated
        DESCRIPTION
                "Cell delay variation tolerance(CDVT) used in the direction 
                remote -> local.

                Setting this parameter to 0xFFFFFFFF(4294967295) indicates
                to the switch that it may use a default value of CDVT.

                If the object 'cwaChanP2MP' is set to 'true', this object
                should not be 'set' and the value
                of this object, if any, is not meaningful."
        REFERENCE
            "ATM Forum Traffice Management Specification Version 4.0 Annex C"
        DEFVAL { 'FFFFFFFF'h }
        ::= { cwAtmChanCnfgEntry 35 }
 

cwaChanRemotePercentUtil OBJECT-TYPE
        SYNTAX          Unsigned32 (1..100)
        MAX-ACCESS      read-create
        STATUS          current
        DESCRIPTION
                "This factor provides a per connection control
                for overbooking bandwidth. This is used in 
                conjunction with the VSI interface policy while
                performing CAC. This is applied for the direction
                remote -> local.

                If the object 'cwaChanP2MP' is set to 'true', this object
                should not be 'set' and the value
                of this object, if any, is not meaningful."
        DEFVAL { 100 }
        ::= { cwAtmChanCnfgEntry 36 }

cwaChanAbrICR           OBJECT-TYPE
        SYNTAX          Unsigned32 (0..4294967295)
        UNITS           "cells/sec"
        MAX-ACCESS      read-create
        STATUS          current
        DESCRIPTION
                "Initial cell rate: Rate at which a source should send initially
                after an idle period. The value must not be larger than the PCR"
        REFERENCE
                "ATM Forum Traffic Management Specification
                Version 4.0 Section 5.10.2"
        ::= { cwAtmChanCnfgEntry 37 }

cwaChanAbrADTF          OBJECT-TYPE
        SYNTAX          Unsigned32 (1..1023)
        UNITS           "10 milliseconds"
        MAX-ACCESS      read-create
        STATUS          current
        DESCRIPTION
                "ACR Decrease Time Factor. This is the time permitted between
                sending RM-cells (Resource Mangement Cells) before the rate is
                decreased to ICR (Initial Cell Rate)."
        REFERENCE
                "ATM Forum Traffic Management Specification
                Version 4.0 Section 5.10.2"
        ::= { cwAtmChanCnfgEntry 38 }
 
cwaChanAbrRDF           OBJECT-TYPE
        SYNTAX          AbrRateFactors
        MAX-ACCESS      read-create
        STATUS          current
        DESCRIPTION
                "Rate Decrease Factor: Controls the rate decrease which occurs
                when backward RM-cells with CI=1 are received. Larger values
                lead to faster rate decrease.
                This factor is applied at both the local and remote endpoints,
                thus making the loop control symmetrical. Backward RM cells at
                the local endpoint correspond to RM cells received in the 
                remote->local direction. Backward RM cells at the remote 
                endpoint correspond to RM cells received in the local->remote
                direction."
        REFERENCE
                "ATM Forum Traffic Management Specification
                Version 4.0 Section 5.10.2"
        ::= { cwAtmChanCnfgEntry 39 }
 
cwaChanAbrRIF           OBJECT-TYPE
        SYNTAX          AbrRateFactors
        MAX-ACCESS      read-create
        STATUS          current
        DESCRIPTION
                "Rate Increase Factor: Controls the rate increase which occurs
                when a backward RM-cell is received with CI=0 and NI=0. Larger 
                values lead to faster rate increase
                This factor is applied at both the local and remote endpoints,
                thus making the loop control symmetrical. Backward RM cells at
                the local endpoint correspond to RM cells received in the 
                remote->local direction. Backward RM cells at the remote 
                endpoint correspond to RM cells received in the local->remote
                direction."
        REFERENCE
                "ATM Forum Traffic Management Specification
                Version 4.0 Section 5.10.2"
        ::= { cwAtmChanCnfgEntry 40 }
 
cwaChanAbrNRM           OBJECT-TYPE
        SYNTAX          INTEGER {
                                nrm2(1),
                                nrm4(2),
                                nrm8(3),
                                nrm16(4),
                                nrm32(5),
                                nrm64(6),
                                nrm128(7),
                                nrm256(8)
                        }
        MAX-ACCESS      read-create
        STATUS          current
        DESCRIPTION
                "Maximum number of cells a source may send for each forward
                RM-cell"
        REFERENCE
                "ATM Forum Traffic Management Specification
                Version 4.0 Section 5.10.2"
        ::= { cwAtmChanCnfgEntry 41 }

cwaChanAbrTRM           OBJECT-TYPE
        SYNTAX          INTEGER {
                                trm0point78125(1),
                                trm1point5625(2),
                                trm3point125(3),
                                trm6point25(4),
                                trm12point5(5),
                                trm25(6),
                                trm50(7),
                                trm100(8)
                        }
        MAX-ACCESS      read-create
        STATUS          current
        DESCRIPTION
                "Upper bound on the time between forward RM-cells for an 
                active source (in milliseconds)"
        REFERENCE
                "ATM Forum Traffic Management Specification
                Version 4.0 Section 5.10.2"
        ::= { cwAtmChanCnfgEntry 42 }
 
cwaChanAbrCDF           OBJECT-TYPE
        SYNTAX          INTEGER {
                                cdf0(1),
                                cdfOneOver64(2),
                                cdfOneOver32(3),
                                cdfOneOver16(4),
                                cdfOneOver8(5),
                                cdfOneOver4(6),
                                cdfOneOver2(7),
                                cdfOne(8)
                        }
        MAX-ACCESS      read-create
        STATUS          current
        DESCRIPTION
                "Cutoff Decrease Factor: Controls the rate decrease associated
                with lost or delayed backward RM cells. Larger values result in
                faster rate decrease"
        REFERENCE
                "ATM Forum Traffic Management Specification
                Version 4.0 Section 5.10.2"
        ::= { cwAtmChanCnfgEntry 43 }
 
cwaChanAbrFRTT          OBJECT-TYPE
        SYNTAX          Unsigned32 (0..16700000)
        UNITS           "microseconds"
        MAX-ACCESS      read-create
        STATUS          current
        DESCRIPTION
                "Fixed round trip time: Sum of the fixed propagation delays from
                the source to a destination network."
        REFERENCE
                "ATM Forum Traffic Management Specification
                Version 4.0 Section 5.10.2"
        ::= { cwAtmChanCnfgEntry 44 } 

cwaChanAbrTBE           OBJECT-TYPE
        SYNTAX          Unsigned32 (0..16777215)
        MAX-ACCESS      read-create
        STATUS          current
        DESCRIPTION
            "Transient Buffer Exposure. This is a negotiated number of
            cells that the network would like to limit the source to
            sending during startup periods, before the first RM-cell returns"
        REFERENCE
                "ATM Forum Traffic Management Specification
                Version 4.0 Section 5.10.2"
        ::= { cwAtmChanCnfgEntry 45 }
 
cwaChanAbrERS           OBJECT-TYPE
        SYNTAX          CiscoWanERSConfg
        MAX-ACCESS      read-create
        STATUS          deprecated
        DESCRIPTION
                "Configuration of an endpoint for Explicit Rate Stamping.
                Refer the Textual convention for possible values"
        DEFVAL { none }
        ::= { cwAtmChanCnfgEntry 46 }
 
cwaChanAbrVSVDEnable    OBJECT-TYPE
        SYNTAX          TruthValue
        MAX-ACCESS      read-create
        STATUS          current
        DESCRIPTION
                "Abr connections require close loop control to limit the 
                transmission rate, depending on the network bandwidth. Now 
                this close loop can be end to end or between intermediate 
                network segments. When terminating an Abr VPL, the endpoint 
                needs to act like a Virtual Destination to the incoming traffic 
                and generate backward RM cells. While doing this it also needs 
                to act as a virtual source and send forward RM cells to the 
                real destination. This is a feature that can be enabled/disabled
                under the control of this object. When set to true(1), this 
                feature is enabled; and is disabled when set to false(2)"
        REFERENCE
                "ATM Forum Traffic Management Specification
                Version 4.0 Section 5.10.2"
        DEFVAL { false }
        ::= { cwAtmChanCnfgEntry 47 }

cwaChanRowStatus        OBJECT-TYPE             
        SYNTAX          RowStatus
        MAX-ACCESS      read-create
        STATUS          current
        DESCRIPTION
                "This object is used to create, modify or delete an entry
                in the ciscoWanAtmChanTable.

                * A row may be created using the 'CreateAndGo' option. When
                the row is successfully created, the RowStatus would be
                set to 'active' by the agent.
  
                Following mandatory objects need to be specified for the
                successful creation of the row(for both master and slave 
                endpoints):
 
                        cwaChanServiceCategory
                        cwaChanVpcFlag
                        cwaChanRoutingMastership
 
                Following mandatory objects are needed for 
                creation of master endpoint:

                    cwaChanRemoteVpi
                    cwaChanRemoteVci
                    cwaChanRemoteNSAPAddr
                       
                * A row may be deleted by setting the RowStatus to 'destroy'.

                * When there is a need to administratively down the connection,
                the RowStatus could be set to 'notInService'. When the switch 
                completes the 'down' operation, the value of this object would
                be 'notInService'.

                * The connection can be made active again, by setting this
                object to 'active'.

                * RowStatus modification from 'notInService' to 'active' or 
                vice-versa will impact only the administrative status of the
                connection.

                * Administrative status control is limited to the master
                endpoint only. The switch would reject any request for 
                administrative state change on the slave endpoint.

                * Other options such as `CreateAndWait' will not be used."

        ::= { cwAtmChanCnfgEntry 48 }
 
cwaChanIntAbrVSVD       OBJECT-TYPE
        SYNTAX          CiscoWanVSVDConfg
        MAX-ACCESS      read-create
        STATUS          current
        DESCRIPTION
            "This object is used for enabling/disabling VSVD internal 
            to a segment i.e the closed loop control is in effect between 
            the two provisioned endpoints of the SPVC."
        REFERENCE
                "ATM Forum Traffic Management Specification
                Version 4.0 Section 5.10.2"
        DEFVAL { switchDefault }
        ::= { cwAtmChanCnfgEntry 49 }

cwaChanExtAbrVSVD       OBJECT-TYPE
        SYNTAX          CiscoWanVSVDConfg
        MAX-ACCESS      read-create
        STATUS          current
        DESCRIPTION
            "This object is used for enabling/disabling VSVD external 
            to the segment which hosts the two endpoints of the SPVC 
            i.e the closed loop control will be in effect outside the 
            segment either towards a CPE or towards another segment."
        REFERENCE
                "ATM Forum Traffic Management Specification
                Version 4.0 Section 5.10.2"
        DEFVAL { switchDefault }
        ::= { cwAtmChanCnfgEntry 50 }

cwaChanAisIWCapability  OBJECT-TYPE
        SYNTAX          CiscoWanAisIW
        MAX-ACCESS      read-create
        STATUS          deprecated
        DESCRIPTION
            "This object is used for achieving OAM inter-operability 
            between switches that cannot generate/detect segment AIS 
            cells. This attribute enables the newer generation of 
            switches to understand the OAM capability of the peer
            endpoint and accordingly generate/detect seg/e2e AIS as 
            required. The value of this attribute is decided during 
            provisioning time by network management."
        DEFVAL { e2eAisCapable }
        ::= { cwAtmChanCnfgEntry 51 }

cwaChanCLR              OBJECT-TYPE
        SYNTAX          Unsigned32 (1..15)
        MAX-ACCESS      read-create
        STATUS          current
        DESCRIPTION
            "Encoded value representing the maximum tolerable cell loss ratio
            in the direction local -> remote. The actual CLR value is derived 
            as the negative logarithm of this value."
        DEFVAL { 6 }
        ::= { cwAtmChanCnfgEntry 52 }

cwaChanRemoteCLR        OBJECT-TYPE
        SYNTAX          Unsigned32 (1..15)
        MAX-ACCESS      read-create
        STATUS          current
        DESCRIPTION
            "Encoded value representing the maximum tolerable cell loss ratio
            in the direction remote -> local. The actual CLR value is derived 
            as the negative logarithm of this value.
                
            If the object 'cwaChanP2MP' is set to 'true', this object
            should not be 'set' and the value
            of this object, if any, is not meaningful."
        DEFVAL { 6 }
        ::= { cwAtmChanCnfgEntry 53 }

cwaChanOamSegEpEnable   OBJECT-TYPE
        SYNTAX          INTEGER {
                                oamSegEp(1),
                                nonOamSegEp(2)
         }
        MAX-ACCESS      read-create
        STATUS          current
        DESCRIPTION
            "This object controls the setting / resetting of the OAM segment 
            endpoint. When set to OamSegEp (1), the SPVC endpoint would 
            terminate all segment OAM FM cells and loopback all OAM segment 
            loopback cells.  When set to NonOamSegEp (2), the SPVC endpoint 
            would be configured as a non-endpoint for OAM cells.  This means 
            that all OAM FM cells and loopback cells would pass transparently 
            through this endpoint.
            If this object is not specified during a SET operation, the 
            switch would apply a default configuration maintained for the 
            port."
        ::= { cwAtmChanCnfgEntry 54 }

cwaChanSlaveType       OBJECT-TYPE
        SYNTAX          INTEGER {
                                persistentSlave(1),
                                nonPersistentSlave(2)
         }
        MAX-ACCESS      read-create
        STATUS          current
        DESCRIPTION
            "This object indicates whether a master endpoint has a persistent
            slave or not. A connection with a master and a non-persistent
            slave is considered a single-ended SPVC.

            This object is only meaningful when 'cwaChanRoutingMastership'
            contains the value of 'true(1)'. And this variable must be used
            with 'cwaChanRoutingMastership' to decide
            if a connection is single-ended or not.

            If the object 'cwaChanP2MP' is set to 'true', this object
            should not be 'set' and the value
            of this object, if any, is not meaningful."
        DEFVAL {persistentSlave}
        ::= { cwAtmChanCnfgEntry 55 }

cwaChanRoutingPriority  OBJECT-TYPE
        SYNTAX          Integer32(1..15)
        MAX-ACCESS      read-create
        STATUS          current
        DESCRIPTION
                "This object is the routing priority of the connection. When
                adding the connection, a default routing priority of 8 is used
                if this is not specified. This parameter is not allowed to be
                set at the slave endpoint(i.e. if 'cwaChanRoutingMastership' is
                set to 'false(2)'). Any attempt to change the priority at the
                slave endpoint would result in a failure of the SET operation.

                A connection tagged with a routing priority of 1 is routed (and
                derouted) ahead of connections tagged with other priorities."
        DEFVAL {8}
        ::= { cwAtmChanCnfgEntry 56 }

cwaChanP2MP          OBJECT-TYPE
        SYNTAX          TruthValue
        MAX-ACCESS      read-create
        STATUS          current
        DESCRIPTION
                "This is used by the administrator to configure this master 
                endpoint to be the root of a point-to-multipoint 
                connection.

                When this variable is set to 'true', this master endpoint
                is the root of a point-to-multipoint connection. The 
                objects 'cwaChanRemoteVpi', 'cwaChanRemoteVci', 
                'cwaChanRemoteNSAPAddr', 'cwaChanRemotePCR', 'cwaChanRemoteMCR'
                'cwaChanRemoteSCR', 'cwaChanRemoteCDV', 'cwaChanRemoteCTD',
                'cwaChanRemoteMBS', 'cwaChanRemoteCDVT', 
                'cwaChanRemotePercentUtil', 'cwaChanRemoteCLR' and
                'cwaChanSlaveType'  should not be set and the
                values of these objects are not meaningful.

                When this variable is set to 'false', this master endpoint
                is not a root of a point-to-multipoint connection.

                If the object 'cwaChanPrefRouteId' is non-zero, this
                object could not be set to true.
                "
        DEFVAL { false }
        ::= { cwAtmChanCnfgEntry 57 }

cwaChanPrefRouteId      OBJECT-TYPE
        SYNTAX          Integer32(0..65535)
        MAX-ACCESS      read-create
        STATUS          current
        DESCRIPTION
                "This object serves to to associate a preferred 
                 route with a connection. 

                 The value '0' means no preferred route is associated with
                 this connection.

                 Usage:
                 - If the value of this set to 0, the object
                   cwaChanDirectRoute is automatically set to FALSE by
                   the switch.
                 - The preferred route is defined in cwaPrefRouteConfTable
                   object. 

                If the object 'cwaChanP2MP' is true, this object could
                not be set to a non-zero value.
                "
        DEFVAL { 0 }
        ::= { cwAtmChanCnfgEntry 58 }

cwaChanDirectRoute      OBJECT-TYPE
        SYNTAX          TruthValue
        MAX-ACCESS      read-create
        STATUS          current
        DESCRIPTION
                "This object serves to associate a prefer 
                 route as directed route (correspond to the prefer route
                 object cwaChanPrefRouteId).
  
                 A directed route specifies that the associated preferred
                 route is the only permission route for the connection to
                 take. Should the associated preferred route be unavailable,
                 the connection is failed.

                 The object is not applicable if there is no associated
                 preferred route with the connection."
        DEFVAL { false }
        ::= { cwAtmChanCnfgEntry 59 }

-- ------------------------------------------------------------------------
-- Channel state group : Contains all objects reflecting the state of an
-- SPVC on a ATM Capable Service Module.
-- ------------------------------------------------------------------------

cwAtmChanStateTable     OBJECT-TYPE
        SYNTAX          SEQUENCE OF CwAtmChanStateEntry
        MAX-ACCESS      not-accessible
        STATUS          current
        DESCRIPTION
                "This table contains channel status information for all 
                 ATM connections configured in cwAtmChanCnfgTable."
        ::= { cwAtmChanState 1 }

 
cwAtmChanStateEntry     OBJECT-TYPE
        SYNTAX          CwAtmChanStateEntry
        MAX-ACCESS      not-accessible
        STATUS          current
        DESCRIPTION
                "An entry in cwAtmChanStateTable."
        INDEX   { ifIndex, cwaChanVpi, cwaChanVci }
        ::= { cwAtmChanStateTable 1 }

CwAtmChanStateEntry ::=
        SEQUENCE {
                cwaChanAlarmState               CiscoWanAlarmState,
                cwaChanEgressXmtState           CiscoWanXmtState,
                cwaChanEgressRcvState           CiscoWanRcvState,
                cwaChanIngressXmtState          CiscoWanXmtState,
                cwaChanIngressRcvState          CiscoWanRcvState
        }
 
cwaChanAlarmState       OBJECT-TYPE
        SYNTAX          CiscoWanAlarmState
        MAX-ACCESS      read-only 
        STATUS          current
        DESCRIPTION
                "Defines alarms associated with an endpoint. Refer description
                in the textual convention."
        ::= { cwAtmChanStateEntry 1 }

cwaChanEgressXmtState   OBJECT-TYPE
        SYNTAX          CiscoWanXmtState
        MAX-ACCESS      read-only 
        STATUS          current
        DESCRIPTION
                "This is the state of the transmit portion of the endpoint
                in the egress direction"
        ::= { cwAtmChanStateEntry 2 }

cwaChanEgressRcvState   OBJECT-TYPE
        SYNTAX          CiscoWanRcvState
        MAX-ACCESS      read-only 
        STATUS          current
        DESCRIPTION
                "This is the state of the receive portion of the endpoint
                in the egress direction"
        ::= { cwAtmChanStateEntry 3 }

cwaChanIngressXmtState  OBJECT-TYPE
        SYNTAX          CiscoWanXmtState
        MAX-ACCESS      read-only 
        STATUS          current
        DESCRIPTION
                "This is the state of the transmit portion of the endpoint
                in the ingress direction"
        ::= { cwAtmChanStateEntry 4 }

cwaChanIngressRcvState  OBJECT-TYPE
        SYNTAX          CiscoWanRcvState
        MAX-ACCESS      read-only 
        STATUS          current
        DESCRIPTION
                "This is the state of the receive portion of the endpoint
                in the ingress direction"
        ::= { cwAtmChanStateEntry 5 }


-- ------------------------------------------------------------------------
-- Channel test group : Contains all objects needed for SPVC diagnostics
-- ------------------------------------------------------------------------

cwAtmChanTestTable      OBJECT-TYPE
        SYNTAX          SEQUENCE OF CwAtmChanTestEntry
        MAX-ACCESS      not-accessible
        STATUS          current
        DESCRIPTION
                "This table contains configuration information for performing
                 connection diagnostics on ATM Connections and to obtain
                results after testing"
        ::= { cwAtmChanTest 1 }

cwAtmChanTestEntry      OBJECT-TYPE
        SYNTAX          CwAtmChanTestEntry
        MAX-ACCESS      not-accessible
        STATUS          current
        DESCRIPTION
                "An entry in cwAtmChanTestTable for each ATM Connection
                endpoints."
        INDEX   { ifIndex, cwaChanVpi, cwaChanVci }
        ::= { cwAtmChanTestTable 1 }

CwAtmChanTestEntry ::=
        SEQUENCE {
                cwaChanTestType                 CiscoWanLpbkTypes,
                cwaChanTestDir                  CiscoWanLpbkDir,
                cwaChanTestIterations           Unsigned32,
                cwaChanTestState                CiscoWanTestStatus,
                cwaChanTestRoundTripDelay       Unsigned32
        }

cwaChanTestType         OBJECT-TYPE
        SYNTAX          CiscoWanLpbkTypes
        MAX-ACCESS      read-write 
        STATUS          current
        DESCRIPTION
                "This object configures an endpoint in loopback:

                 This is a mandatory object.

                * To configure a destructive loopback, this object needs to
                  be set to destructive (2). The direction in which this 
                  destructive loopback needs to be effected, should be 
                  specified using the cwaChanTestDir object. To de-configure
                  destructive loopback, this object needs to be set to
                  noLpbk(1).
                * To configure a non-destructive loopback, this object needs
                  to be set to nonDestructive(3). The direction in which this
                  non-destructive loopback needs to be effected, should be
                  specified using the cwaChanTestDir object. Non-destructive
                  loopback gets de-configured automatically at the switch after
                  a certain timeout. However, if there is a need to abort
                  a non-destructive loopback, a set operation on this object
                  should be performed with a value noLpbk (1).
                * Attempting to set a channel in loopback, when one is already
                  in progress results in a failure of the set operation (with
                  appropriate error code)"
        DEFVAL { noLpbk }
        ::= { cwAtmChanTestEntry 1 }

cwaChanTestDir          OBJECT-TYPE
        SYNTAX          CiscoWanLpbkDir
        MAX-ACCESS      read-write 
        STATUS          current
        DESCRIPTION
                "Specifies the direction in which loopback should be effected:

                 This is a mandatory object.

                * For destructive loopback, this takes values external (1) and
                  internal (2).
                * For non-destructive loopback, this takes values forward (3)
                  and reverse (4).
                * When cwaChanTestType is noLpbk (1), this object is ignored."
        ::= { cwAtmChanTestEntry 2 }

cwaChanTestIterations   OBJECT-TYPE
        SYNTAX          Unsigned32 (1..255)
        MAX-ACCESS      read-write 
        STATUS          current
        DESCRIPTION
                "Specifies number of loopback cells to inject. This applies to
                the non-destructive mode of loopback tests only. Get operation
                on this object returns the successful number of loopback 
                iterations performed on the endpoint."
        DEFVAL { 1 }
        ::= { cwAtmChanTestEntry 3 }

cwaChanTestState        OBJECT-TYPE
        SYNTAX          CiscoWanTestStatus
        MAX-ACCESS      read-only
        STATUS          current
        DESCRIPTION
                "This object reflects the status of the last requested test:
                * If a loopback had never been effected on an endpoint,
                  this object reads noStatus (1).
                * If a destructive mode of loopback is configured on an 
                  endpoint, this object always reads lpbkInEffect(6).
                * If a non-destructive mode of loopback is in progress, this
                  reads lpbkInProgress(2).
                * If a non-destructive mode of loopback has completed
                  successfully, this reads lpbkSuccess(3).
                * If a non-destructive mode of loopback has aborted, either
                  due to user request or switch's limitation, this reads
                  lpbkAbort (4).
                * If a non-destructive mode of loopback has failed, this 
                  reads lpbkTimeOut(5)."
        DEFVAL { noStatus }
        ::= { cwAtmChanTestEntry 4 }

cwaChanTestRoundTripDelay OBJECT-TYPE
        SYNTAX          Unsigned32 (1..100000000)
        UNITS           "microseconds"
        MAX-ACCESS      read-only
        STATUS          current
        DESCRIPTION
                "This object is applicable only for non-destructive mode of
                loopback. It returns the round trip delay measured during 
                the last non-destructive loopback test"
        ::= { cwAtmChanTestEntry 5 }

cwaChanNumVPCsInAlarm OBJECT-TYPE
    SYNTAX      Unsigned32
--  MAX-ACCESS  accessible-for-notify
    MAX-ACCESS  read-only
    STATUS      current
    DESCRIPTION
        "This object contains the number of VPCs currently in
        alarm.
        This object is intended only in traps/notifications."
    ::= { cwAtmChanInformation 1 }

cwaChanNumVCCsInAlarm OBJECT-TYPE
    SYNTAX      Unsigned32
--  MAX-ACCESS  accessible-for-notify
    MAX-ACCESS  read-only
    STATUS      current
    DESCRIPTION
        "This object contains the number of VCCs currently in
        alarm.
        This object is intended only in traps/notifications."
    ::= { cwAtmChanInformation 2 }

-- ------------------------------------------------------------------------
-- Global connection data group. Contains connection attributes 
-- that apply globally to all provisioned connections.
-- ------------------------------------------------------------------------
cwGlobalChanDataTable OBJECT-TYPE
    SYNTAX      SEQUENCE OF CwGlobalChanDataEntry
    MAX-ACCESS  not-accessible
    STATUS      current
    DESCRIPTION
        "This table contains objects that are required for
        configuration upload. The configuration upload
        is a mechanism where the configuration(physical or
        logical information)of a switch is created in
        a file and that file is uploaded by the NMS application
        using file transfer method(for example FTP)."
    ::= { cwGlobalChanDataGroup 1}

cwGlobalChanDataEntry OBJECT-TYPE
    SYNTAX CwGlobalChanDataEntry
    MAX-ACCESS  not-accessible
    STATUS      current
    DESCRIPTION
        "Entry containing generic information that apply to
        all provisined connections(ATM/Frame Relay)."
     INDEX       { cwSlotIndex } 
    ::= { cwGlobalChanDataTable 1 }

CwGlobalChanDataEntry ::=
    SEQUENCE {
        cwSlotIndex                         Unsigned32,
        cwChanGlobalTransactionId           Unsigned32
    }

cwSlotIndex OBJECT-TYPE
    SYNTAX      Unsigned32 (1..429496729)
    MAX-ACCESS  not-accessible
    STATUS      current
    DESCRIPTION
        "This object's value generally corresponds to the
         Slot number where the module resides. However,
         System wide uniqueness is the only true requirement."
    ::= {cwGlobalChanDataEntry  1 }

cwChanGlobalTransactionId OBJECT-TYPE
    SYNTAX      Unsigned32 (0..4294967295)
    MAX-ACCESS  read-only
    STATUS      current
    DESCRIPTION
        "This reflects the transaction Identifier of the last 
        successful connection configuration on the slot
        (represented by cwSlotIndex).

        The value of this object is incremented every time a 
        connection(ATM/Frame Relay) is successfully added, 
        deleted, modified or administratively up/down.

        The transaction identifier of the each provisioned 
        ATM connection endpoint is represented by cwaChanUploadCounter 
        in the cwaChanCnfgTable.

        The transcation identifer of the each provisioned 
        Frame Relay connection endpoint is represented by 
        frChanCnfChangeCount in frChanCnfGrpTable."
    REFERENCE
        "frChanCnfChangeCount in CISCO-WAN-FR-CONN-MIB.my"
    ::= {cwGlobalChanDataEntry  2 }

-- conformance information

ciscoWanAtmConnMIBConformance
                OBJECT IDENTIFIER ::= { ciscoWanAtmConnMIB 2 }
ciscoWanAtmConnMIBCompliances
                OBJECT IDENTIFIER ::= { ciscoWanAtmConnMIBConformance 1 }
ciscoWanAtmConnMIBGroups
                OBJECT IDENTIFIER ::= { ciscoWanAtmConnMIBConformance 2 }


-- compliance statements

ciscoWanAtmConnMIBCompliance MODULE-COMPLIANCE
        STATUS  deprecated  -- replaced by ciscoWanAtmConnMIBCompliance2
        DESCRIPTION
        "The compliance statement for the Cisco ATM connection 
        management group."
        MODULE  -- this module
            MANDATORY-GROUPS { ciscoWanAtmConnChanMIBGroup }
        
        GROUP    ciscoWanAtmConnStateGroup
        DESCRIPTION 
            "Implementation of this group is optional for the
             systems where connection state is not available
             per connection basis."
        
        OBJECT     cwaChanFrameDiscard
        MIN-ACCESS not-accessible
        DESCRIPTION
            "Read and write access is not required for the switches
             which does not support frame discard feature."

        OBJECT     cwaChanCCEnable
        MIN-ACCESS not-accessible
        DESCRIPTION
            "Read and write access is not required for the switches
             which does not support Continuity Check capability."

        OBJECT     cwaChanStatsEnable
        MIN-ACCESS not-accessible
        DESCRIPTION 
            "Read and write access is not required for the switches
             does not support the connection related statistics
             collection."

        OBJECT     cwaChanAbrERS 
        MIN-ACCESS not-accessible
        DESCRIPTION 
            "Read and write access is not required for the switches
             which does not support Explicit Rate Stamping(ERS)."

        OBJECT     cwaChanAbrVSVDEnable
        MIN-ACCESS not-accessible
        DESCRIPTION 
            "Read and write access is not required for the switches
             which does not support Virtual Source Virtual Destination
             feature."
        ::= { ciscoWanAtmConnMIBCompliances 1 }


ciscoWanAtmConnMIBCompliance2 MODULE-COMPLIANCE
        STATUS deprecated  -- replaced by ciscoWanAtmConnMIBCompliance3 
        DESCRIPTION
        "The compliance statement for the Cisco ATM connection 
        management group."
        MODULE  -- this module
            MANDATORY-GROUPS { ciscoWanAtmConnChan2MIBGroup }
        
        GROUP    ciscoWanAtmConnStateGroup
        DESCRIPTION 
            "Implementation of this group is optional for the
             systems where connection state is not available
             per connection basis."
        
        OBJECT     cwaChanFrameDiscard
        MIN-ACCESS not-accessible
        DESCRIPTION
            "Read and write access is not required for the switches
             which does not support frame discard feature."

        OBJECT     cwaChanCCEnable
        MIN-ACCESS not-accessible
        DESCRIPTION
            "Read and write access is not required for the switches
             which does not support Continuity Check capability."

        OBJECT     cwaChanStatsEnable
        MIN-ACCESS not-accessible
        DESCRIPTION 
            "Read and write access is not required for the switches
             does not support the connection related statistics
             collection."

        OBJECT     cwaChanAbrERS 
        MIN-ACCESS not-accessible
        DESCRIPTION 
            "Read and write access is not required for the switches
             which does not support Explicit Rate Stamping(ERS)."

        OBJECT     cwaChanAbrVSVDEnable
        MIN-ACCESS not-accessible
        DESCRIPTION 
            "Read and write access is not required for the switches
             which does not support Virtual Source Virtual Destination
             feature."
        ::= { ciscoWanAtmConnMIBCompliances 2 }


ciscoWanAtmConnMIBCompliance3 MODULE-COMPLIANCE
        STATUS  deprecated  -- replaced by ciscoWanAtmConnMIBCompliance4 
        DESCRIPTION
        "The compliance statement for the Cisco ATM connection
        management group."
        MODULE  -- this module
            MANDATORY-GROUPS { ciscoWanAtmConnChan3MIBGroup }

        GROUP    ciscoWanAtmConnStateGroup
        DESCRIPTION
            "Implementation of this group is optional for the
             systems where connection state is not available
             per connection basis."

        GROUP ciscoWanAtmInformationGroup
        DESCRIPTION
            "Implementation of this group is mandatory for
             systems supporting those traps/notifications
             with these objects."

        OBJECT     cwaChanFrameDiscard
        MIN-ACCESS not-accessible
        DESCRIPTION
            "Read and write access is not required for the switches
             which does not support frame discard feature."

        OBJECT     cwaChanCCEnable
        MIN-ACCESS not-accessible
        DESCRIPTION
            "Read and write access is not required for the switches
             which does not support Continuity Check capability."

        OBJECT     cwaChanStatsEnable
        MIN-ACCESS not-accessible
        DESCRIPTION
            "Read and write access is not required for the switches
             does not support the connection related statistics
             collection."

        OBJECT     cwaChanAbrVSVDEnable
        MIN-ACCESS not-accessible
        DESCRIPTION
            "Read and write access is not required for the switches
             which does not support Virtual Source Virtual Destination
             feature."

        OBJECT     cwaChanSlaveType
        MIN-ACCESS not-accessible
        DESCRIPTION
            "Read and write access is not required for the switches
             which does not support non-persistent SPVC." 

        OBJECT     cwaChanRoutingPriority
        MIN-ACCESS not-accessible
        DESCRIPTION
            "Read and write access is not required for the switches
             which does not support Routing Priority." 

        ::= { ciscoWanAtmConnMIBCompliances 3 }

ciscoWanAtmConnMIBCompliance4 MODULE-COMPLIANCE
        STATUS  current
        DESCRIPTION
        "The compliance statement for the Cisco ATM connection
        management group."
        MODULE  -- this module
        MANDATORY-GROUPS { ciscoWanAtmConnChan4MIBGroup }

        GROUP    ciscoWanAtmConnStateGroup
        DESCRIPTION
            "Implementation of this group is optional for the
             systems where connection state is not available
             per connection basis."

        GROUP ciscoWanAtmInformationGroup
        DESCRIPTION
            "Implementation of this group is mandatory for
             systems supporting those traps/notifications
             with these objects."

        OBJECT     cwaChanFrameDiscard
        MIN-ACCESS not-accessible
        DESCRIPTION
            "Read and write access is not required for the switches
             which does not support frame discard feature."

        OBJECT     cwaChanCCEnable
        MIN-ACCESS not-accessible
        DESCRIPTION
            "Read and write access is not required for the switches
             which does not support Continuity Check capability."

        OBJECT     cwaChanStatsEnable
        MIN-ACCESS not-accessible
        DESCRIPTION
            "Read and write access is not required for the switches
             does not support the connection related statistics
             collection."

        OBJECT     cwaChanAbrVSVDEnable
        MIN-ACCESS not-accessible
        DESCRIPTION
            "Read and write access is not required for the switches
             which does not support Virtual Source Virtual Destination
             feature."

        OBJECT     cwaChanSlaveType
        MIN-ACCESS not-accessible
        DESCRIPTION
            "Read and write access is not required for the switches
             which does not support non-persistent SPVC."

        OBJECT     cwaChanRoutingPriority
        MIN-ACCESS not-accessible
        DESCRIPTION
            "Read and write access is not required for the switches
             which does not support Routing Priority."

        OBJECT     cwaChanP2MP
        MIN-ACCESS not-accessible
        DESCRIPTION
            "Read and write access is not required for the switches
             which does not support point-to-multipoint connections."

        OBJECT     cwaChanPrefRouteId 
        MIN-ACCESS not-accessible
        DESCRIPTION
            "Read and write access is not required for the switches
             which does not support preferred route connections."

        OBJECT     cwaChanDirectRoute 
        MIN-ACCESS not-accessible
        DESCRIPTION
            "Read and write access is not required for the switches
             which does not support preferred route connections."

        ::= { ciscoWanAtmConnMIBCompliances 4 }


-- units of conformance


ciscoWanAtmConnChanMIBGroup     OBJECT-GROUP
        OBJECTS { 
                cwaChanServiceCategory,
                cwaChanVpcFlag,

                cwaChanStatsEnable,
                cwaChanCCEnable,

                cwaChanUploadCounter,
                cwaChanIdentifier,

                cwaChanLocalVpi,
                cwaChanLocalVci,
                cwaChanLocalNSAPAddr,

                cwaChanRemoteVpi,
                cwaChanRemoteVci,
                cwaChanRemoteNSAPAddr,

                cwaChanControllerId,
                cwaChanRoutingMastership,
                cwaChanMaxCost,
                cwaChanReroute,
                cwaChanFrameDiscard,
                cwaChanOperStatus,

                cwaChanPCR,
                cwaChanMCR,
                cwaChanSCR,
                cwaChanCDV,
                cwaChanCTD,
                cwaChanMBS,
                cwaChanCDVT,
                cwaChanPercentUtil,

                cwaChanRemotePCR,
                cwaChanRemoteMCR,
                cwaChanRemoteSCR,
                cwaChanRemoteCDV,
                cwaChanRemoteCTD,
                cwaChanRemoteMBS,
                cwaChanRemoteCDVT,
                cwaChanRemotePercentUtil,

                cwaChanAbrICR,
                cwaChanAbrADTF,
                cwaChanAbrRDF,
                cwaChanAbrRIF,
                cwaChanAbrNRM,
                cwaChanAbrTRM,
                cwaChanAbrCDF,
                cwaChanAbrFRTT,
                cwaChanAbrTBE,
                cwaChanAbrERS,
                cwaChanAbrVSVDEnable,
                cwaChanRowStatus,
                cwaChanIntAbrVSVD,
                cwaChanExtAbrVSVD,
                cwaChanAisIWCapability,
                cwaChanCLR,
                cwaChanRemoteCLR,

                cwaChanTestType,
                cwaChanTestDir,
                cwaChanTestIterations,
                cwaChanTestState,
                cwaChanTestRoundTripDelay
        }
        STATUS  deprecated -- replaced by ciscoWanAtmConnChan2MIBGroup
        DESCRIPTION
            "Objects related to connection information."
        ::= { ciscoWanAtmConnMIBGroups 1 }

ciscoWanAtmConnStateGroup OBJECT-GROUP
        OBJECTS { 
                cwaChanAlarmState,
                cwaChanEgressXmtState,
                cwaChanEgressRcvState,
                cwaChanIngressXmtState,
                cwaChanIngressRcvState
        }
        STATUS  current
        DESCRIPTION
            "Objects related to connection state information."
        ::= { ciscoWanAtmConnMIBGroups 2 }


ciscoWanAtmConnChan2MIBGroup    OBJECT-GROUP -- replaced by ciscoWanAtmConnChan3MIBGroup
        OBJECTS { 
                cwaChanServiceCategory,
                cwaChanVpcFlag,

                cwaChanStatsEnable,
                cwaChanCCEnable,

                cwaChanUploadCounter,
                cwaChanIdentifier,

                cwaChanLocalVpi,
                cwaChanLocalVci,
                cwaChanLocalNSAPAddr,

                cwaChanRemoteVpi,
                cwaChanRemoteVci,
                cwaChanRemoteNSAPAddr,

                cwaChanControllerId,
                cwaChanRoutingMastership,
                cwaChanMaxCost,
                cwaChanReroute,
                cwaChanFrameDiscard,
                cwaChanOperStatus,

                cwaChanPCR,
                cwaChanMCR,
                cwaChanSCR,
                cwaChanCDV,
                cwaChanCTD,
                cwaChanMBS,
                cwaChanCDVT,
                cwaChanPercentUtil,

                cwaChanRemotePCR,
                cwaChanRemoteMCR,
                cwaChanRemoteSCR,
                cwaChanRemoteCDV,
                cwaChanRemoteCTD,
                cwaChanRemoteMBS,
                cwaChanRemotePercentUtil,

                cwaChanAbrICR,
                cwaChanAbrADTF,
                cwaChanAbrRDF,
                cwaChanAbrRIF,
                cwaChanAbrNRM,
                cwaChanAbrTRM,
                cwaChanAbrCDF,
                cwaChanAbrFRTT,
                cwaChanAbrTBE,
                cwaChanAbrERS,
                cwaChanAbrVSVDEnable,
                cwaChanRowStatus,
                cwaChanIntAbrVSVD,
                cwaChanExtAbrVSVD,
                cwaChanAisIWCapability,
                cwaChanCLR,
                cwaChanRemoteCLR,
                cwaChanOamSegEpEnable,

                cwaChanTestType,
                cwaChanTestDir,
                cwaChanTestIterations,
                cwaChanTestState,
                cwaChanTestRoundTripDelay
        }
        STATUS  deprecated -- replaced by ciscoWanAtmConnChan3MIBGroup
        DESCRIPTION
            "Objects related to connection information."
        ::= { ciscoWanAtmConnMIBGroups 3 }

ciscoWanAtmConnChan3MIBGroup    OBJECT-GROUP
        OBJECTS {
                cwaChanServiceCategory,
                cwaChanVpcFlag,

                cwaChanStatsEnable,
                cwaChanCCEnable,

                cwaChanUploadCounter,
                cwaChanIdentifier,

                cwaChanLocalVpi,
                cwaChanLocalVci,
                cwaChanLocalNSAPAddr,

                cwaChanRemoteVpi,
                cwaChanRemoteVci,
                cwaChanRemoteNSAPAddr,

                cwaChanControllerId,
                cwaChanRoutingMastership,
                cwaChanMaxCost,
                cwaChanReroute,
                cwaChanFrameDiscard,
                cwaChanOperStatus,

                cwaChanPCR,
                cwaChanMCR,
                cwaChanSCR,
                cwaChanCDV,
                cwaChanCTD,
                cwaChanMBS,
                cwaChanCDVT,
                cwaChanPercentUtil,

                cwaChanRemotePCR,
                cwaChanRemoteMCR,
                cwaChanRemoteSCR,
                cwaChanRemoteCDV,
                cwaChanRemoteCTD,
                cwaChanRemoteMBS,
                cwaChanRemotePercentUtil,

                cwaChanAbrICR,
                cwaChanAbrADTF,
                cwaChanAbrRDF,
                cwaChanAbrRIF,
                cwaChanAbrNRM,
                cwaChanAbrTRM,
                cwaChanAbrCDF,
                cwaChanAbrFRTT,
                cwaChanAbrTBE,
                cwaChanAbrVSVDEnable,
                cwaChanRowStatus,
                cwaChanIntAbrVSVD,
                cwaChanExtAbrVSVD,
                cwaChanCLR,
                cwaChanRemoteCLR,
                cwaChanOamSegEpEnable,
                cwaChanSlaveType,
                cwaChanRoutingPriority,

                cwaChanTestType,
                cwaChanTestDir,
                cwaChanTestIterations,
                cwaChanTestState,
                cwaChanTestRoundTripDelay
        }
        STATUS  deprecated -- replaced by ciscoWanAtmConnChan4MIBGroup 
        DESCRIPTION
            "Objects related to connection information."
        ::= { ciscoWanAtmConnMIBGroups 4 }

ciscoWanAtmInformationGroup OBJECT-GROUP
    OBJECTS {
        cwaChanNumVPCsInAlarm,
        cwaChanNumVCCsInAlarm
    }
    STATUS  current
    DESCRIPTION
        "This group contains objects related to the
        number of VPCs and VCCs in alarm."
    ::= { ciscoWanAtmConnMIBGroups 5 }

ciscoWanAtmConnChan4MIBGroup    OBJECT-GROUP
        OBJECTS {
                cwaChanServiceCategory,
                cwaChanVpcFlag,

                cwaChanStatsEnable,
                cwaChanCCEnable,

                cwaChanUploadCounter,
                cwaChanIdentifier,

                cwaChanLocalVpi,
                cwaChanLocalVci,
                cwaChanLocalNSAPAddr,

                cwaChanRemoteVpi,
                cwaChanRemoteVci,
                cwaChanRemoteNSAPAddr,

                cwaChanControllerId,
                cwaChanRoutingMastership,
                cwaChanMaxCost,
                cwaChanReroute,
                cwaChanFrameDiscard,
                cwaChanOperStatus,

                cwaChanPCR,
                cwaChanMCR,
                cwaChanSCR,
                cwaChanCDV,
                cwaChanCTD,
                cwaChanMBS,
                cwaChanCDVT,
                cwaChanPercentUtil,

                cwaChanRemotePCR,
                cwaChanRemoteMCR,
                cwaChanRemoteSCR,
                cwaChanRemoteCDV,
                cwaChanRemoteCTD,
                cwaChanRemoteMBS,
                cwaChanRemotePercentUtil,

                cwaChanAbrICR,
                cwaChanAbrADTF,
                cwaChanAbrRDF,
                cwaChanAbrRIF,
                cwaChanAbrNRM,
                cwaChanAbrTRM,
                cwaChanAbrCDF,
                cwaChanAbrFRTT,
                cwaChanAbrTBE,
                cwaChanAbrVSVDEnable,
                cwaChanRowStatus,
                cwaChanIntAbrVSVD,
                cwaChanExtAbrVSVD,
                cwaChanCLR,
                cwaChanRemoteCLR,
                cwaChanOamSegEpEnable,
                cwaChanSlaveType,
                cwaChanRoutingPriority,
                cwaChanP2MP,
                cwaChanPrefRouteId,
                cwaChanDirectRoute, 

                cwaChanTestType,
                cwaChanTestDir,
                cwaChanTestIterations,
                cwaChanTestState,
                cwaChanTestRoundTripDelay
        }
        STATUS  current
        DESCRIPTION
            "Objects related to connection information."
        ::= { ciscoWanAtmConnMIBGroups 6 }

ciscoWanConMIBGroup    OBJECT-GROUP
        OBJECTS {

                cwChanGlobalTransactionId
        }
        STATUS  current
        DESCRIPTION
            "The group containing Objects related to
            connection provision changes."
        ::= { ciscoWanAtmConnMIBGroups 7 }

END
