-- *****************************************************************
-- CISCO-SIP-UA-CAPABILITY.my:  Session Initiation Protocol User
--                              Agent capability mib
--
-- August 2000, Kevin Lingle
--
-- Copyright (c) 2000, 2001, 2003 by cisco Systems, Inc.
-- All rights reserved.
-- *****************************************************************
CISCO-SIP-UA-CAPABILITY DEFINITIONS ::= BEGIN

IMPORTS
        MODULE-IDENTITY
                FROM SNMPv2-SMI
        AGENT-CAPABILITIES
                FROM SNMPv2-CONF
        ciscoAgentCapability
                FROM CISCO-SMI;

ciscoSipUaCapability MODULE-IDENTITY
                LAST-UPDATED    "200506220000Z"
                ORGANIZATION    "Cisco Systems, Inc."
                CONTACT-INFO
                        "       Cisco Systems
                                Customer Service
                        
                        Postal: 170 West Tasman Drive
                                San Jose, CA  95134
                                USA
                        
                           Tel: +1 800 553-NETS
                        
                        E-mail: cs-sip@cisco.com"
                DESCRIPTION
                        "Agent capabilities for the CISCO-SIP-UA-MIB."
                REVISION        "200506220000Z"
                DESCRIPTION
                        "Adding AGENT-CAPABILITIES clause for IOS
                         12.4(2)T."
                REVISION        "200307300000Z"
                DESCRIPTION
                        "Adding AGENT-CAPABILITIES clauses for IOS
                         12.3(2)."
                REVISION        "200303210000Z"
                DESCRIPTION
                        "Adding AGENT-CAPABILITIES clauses for IOS
                         12.2(8), 12.2(11) & 12.2(15)."
                REVISION        "200109260000Z"
                DESCRIPTION
                        "Adding AGENT-CAPABILITIES clause for IOS
                         12.2(2)."

                REVISION        "200106110000Z"
                DESCRIPTION
                        "Initial version of this MIB module."
        ::= { ciscoAgentCapability 172 }

ciscoSipUaCapabilityV12R0202 AGENT-CAPABILITIES

PRODUCT-RELEASE "Cisco IOS 12.2(2)."
  STATUS          current
  DESCRIPTION     "IOS 12.2 Cisco SIP User Agent MIB capabilities."

SUPPORTS        CISCO-SIP-UA-MIB
  INCLUDES      { ciscoSipBaseConfigGroup,
                  ciscoSipStatsInfoStatusCodesGroup,
                  ciscoSipStatsSuccessStatusCodesGroup,
                  ciscoSipStatsGlobalStatusCodesGroup,
                  ciscoSipTrafficStatsGroup,
                  ciscoSipTimerConfigGroup,
                  ciscoSipRetryConfigGroup,
                  ciscoSipRetryStatsGroup,
                  ciscoSipStatsRedirStatusCodesGroup,
                  ciscoSipStatsClientStatusCodesGroup,
                  ciscoSipStatsServerStatusCodesGroup }

VARIATION cSipCfgRetryRegister
  ACCESS    not-implemented
  DESCRIPTION "Not implemented."

VARIATION cSipStatsTrafficRegisterIns
  ACCESS    not-implemented
  DESCRIPTION "Not implemented."

VARIATION cSipStatsTrafficRegisterOuts
  ACCESS    not-implemented
  DESCRIPTION "Not implemented."

::= { ciscoSipUaCapability 1 }

ciscoSipUaCapabilityV12R0208 AGENT-CAPABILITIES

PRODUCT-RELEASE "Cisco IOS 12.2(8)."
  STATUS          current
  DESCRIPTION     "IOS 12.2 Cisco SIP User Agent MIB capabilities."

SUPPORTS        CISCO-SIP-UA-MIB
  INCLUDES      { ciscoSipBaseConfigGroupRev1,
                  ciscoSipStatsInfoStatusCodesGroup,
                  ciscoSipStatsSuccessStatusCodesGroup,
                  ciscoSipStatsGlobalStatusCodesGroup,
                  ciscoSipTrafficStatsGroupRev1,
                  ciscoSipTimerConfigGroupRev1,
                  ciscoSipRetryConfigGroupRev1,
                  ciscoSipRetryStatsGroupRev1,
                  ciscoSipStatsRedirStatusCodesGroup,
                  ciscoSipStatsClientStatusCodesGroupRev1,
                  ciscoSipStatsServerStatusCodesGroupRev1,
                  ciscoSipCfgPeerGroup }

VARIATION cSipCfgRetryRegister
  ACCESS    not-implemented
  DESCRIPTION "Not implemented."

VARIATION cSipStatsTrafficRegisterIns
  ACCESS    not-implemented
  DESCRIPTION "Not implemented."

VARIATION cSipStatsTrafficRegisterOuts
  ACCESS    not-implemented
  DESCRIPTION "Not implemented."

::= { ciscoSipUaCapability 2 }

ciscoSipUaCapabilityV12R0211 AGENT-CAPABILITIES

PRODUCT-RELEASE "Cisco IOS 12.2(11)."
  STATUS          current
  DESCRIPTION     "IOS 12.2 Cisco SIP User Agent MIB capabilities."

SUPPORTS        CISCO-SIP-UA-MIB
  INCLUDES      { ciscoSipBaseConfigGroupRev2,
                  ciscoSipStatsInfoStatusCodesGroup,
                  ciscoSipStatsSuccessStatusCodesGroupRev1,
                  ciscoSipStatsGlobalStatusCodesGroup,
                  ciscoSipTrafficStatsGroupRev2,
                  ciscoSipTimerConfigGroupRev2,
                  ciscoSipRetryConfigGroupRev2,
                  ciscoSipRetryStatsGroupRev2,
                  ciscoSipStatsRedirStatusCodesGroupRev1,
                  ciscoSipStatsClientStatusCodesGroupRev2,
                  ciscoSipStatsServerStatusCodesGroupRev1,
                  ciscoSipCfgPeerGroup,
                  ciscoSipStatusCauseMapGroup,
                  ciscoSipCfgAaaGroup }

VARIATION cSipCfgRetryRegister
  ACCESS    not-implemented
  DESCRIPTION "Not implemented."

VARIATION cSipStatsTrafficRegisterIns
  ACCESS    not-implemented
  DESCRIPTION "Not implemented."

VARIATION cSipStatsTrafficRegisterOuts
  ACCESS    not-implemented
  DESCRIPTION "Not implemented."

VARIATION cSipCfgStatusCauseStoreStatus
  ACCESS    not-implemented
  DESCRIPTION "Not implemented."

VARIATION cSipCfgCauseStatusStoreStatus
  ACCESS    not-implemented
  DESCRIPTION "Not implemented."

::= { ciscoSipUaCapability 3 }

ciscoSipUaCapabilityV12R0215 AGENT-CAPABILITIES

PRODUCT-RELEASE "Cisco IOS 12.2(15)."
  STATUS          current
  DESCRIPTION     "IOS 12.2 Cisco SIP User Agent MIB capabilities."

SUPPORTS        CISCO-SIP-UA-MIB
  INCLUDES      { ciscoSipBaseConfigGroupRev2,
                  ciscoSipStatsInfoStatusCodesGroup,
                  ciscoSipStatsSuccessStatusCodesGroupRev1,
                  ciscoSipStatsGlobalStatusCodesGroup,
                  ciscoSipTrafficStatsGroupRev2,
                  ciscoSipTimerConfigGroupRev3,
                  ciscoSipRetryConfigGroupRev3,
                  ciscoSipRetryStatsGroupRev3,
                  ciscoSipStatsRedirStatusCodesGroupRev1,
                  ciscoSipStatsClientStatusCodesGroupRev2,
                  ciscoSipStatsServerStatusCodesGroupRev1,
                  ciscoSipCfgPeerGroup,
                  ciscoSipStatusCauseMapGroup,
                  ciscoSipCfgAaaGroup }

VARIATION cSipCfgRetryRegister
  ACCESS    not-implemented
  DESCRIPTION "Not implemented."

VARIATION cSipStatsTrafficRegisterIns
  ACCESS    not-implemented
  DESCRIPTION "Not implemented."

VARIATION cSipStatsTrafficRegisterOuts
  ACCESS    not-implemented
  DESCRIPTION "Not implemented."

VARIATION cSipCfgStatusCauseStoreStatus
  ACCESS    not-implemented
  DESCRIPTION "Not implemented."

VARIATION cSipCfgCauseStatusStoreStatus
  ACCESS    not-implemented
  DESCRIPTION "Not implemented."

::= { ciscoSipUaCapability 4 }

ciscoSipUaCapabilityV12R0302 AGENT-CAPABILITIES

PRODUCT-RELEASE "Cisco IOS 12.3(2)."
  STATUS          current
  DESCRIPTION     "IOS 12.3 Cisco SIP User Agent MIB capabilities."

SUPPORTS        CISCO-SIP-UA-MIB
  INCLUDES      { ciscoSipBaseConfigGroupRev3,
                  ciscoSipStatsInfoStatusCodesGroup,
                  ciscoSipStatsSuccessStatusCodesGroupRev2,
                  ciscoSipStatsGlobalStatusCodesGroup,
                  ciscoSipTrafficStatsGroupRev2,
                  ciscoSipTimerConfigGroupRev3,
                  ciscoSipRetryConfigGroupRev3,
                  ciscoSipRetryStatsGroupRev3,
                  ciscoSipStatsRedirStatusCodesGroupRev1,
                  ciscoSipStatsClientStatusCodesGroupRev3,
                  ciscoSipStatsServerStatusCodesGroupRev1,
                  ciscoSipCfgPeerGroup,
                  ciscoSipStatusCauseMapGroup,
                  ciscoSipCfgAaaGroup,
                  ciscoSipStatsMiscGroup,
                  ciscoSipBaseIOSConfigGroup }

VARIATION cSipCfgRetryRegister
  ACCESS    not-implemented
  DESCRIPTION "Not implemented."

VARIATION cSipStatsTrafficRegisterIns
  ACCESS    not-implemented
  DESCRIPTION "Not implemented."

VARIATION cSipStatsTrafficRegisterOuts
  ACCESS    not-implemented
  DESCRIPTION "Not implemented."

VARIATION cSipCfgStatusCauseStoreStatus
  ACCESS    not-implemented
  DESCRIPTION "Not implemented."

VARIATION cSipCfgCauseStatusStoreStatus
  ACCESS    not-implemented
  DESCRIPTION "Not implemented."

::= { ciscoSipUaCapability 5 }

ciscoSipUaCapabilityV12R0402T AGENT-CAPABILITIES

PRODUCT-RELEASE "Cisco IOS 12.4(2)T."
  STATUS          current
  DESCRIPTION     "IOS 12.4(2)T Cisco SIP User Agent MIB capabilities."

SUPPORTS        CISCO-SIP-UA-MIB
  INCLUDES      { ciscoSipBaseConfigGroupRev3,
                  ciscoSipStatsInfoStatusCodesGroup,
                  ciscoSipStatsSuccessStatusCodesGroupRev2,
                  ciscoSipStatsGlobalStatusCodesGroup,
                  ciscoSipTrafficStatsGroupRev3,
                  ciscoSipTimerConfigGroupRev4,
                  ciscoSipRetryConfigGroupRev4,
                  ciscoSipRetryStatsGroupRev4,
                  ciscoSipStatsRedirStatusCodesGroupRev2,
                  ciscoSipStatsClientStatusCodesGroupRev4,
                  ciscoSipStatsServerStatusCodesGroupRev1,
                  ciscoSipCfgPeerGroupRev1,
                  ciscoSipStatusCauseMapGroup,
                  ciscoSipCfgAaaGroup,
                  ciscoSipStatsMiscGroup,
                  ciscoSipBaseIOSConfigGroupRev1,
                  ciscoSipCfgVoiceServiceVoipGroup,
                  ciscoSipStatsConnectionGroup }

VARIATION cSipCfgRetryRegister
  ACCESS    not-implemented
  DESCRIPTION "Not implemented."

VARIATION cSipStatsTrafficRegisterIns
  ACCESS    not-implemented
  DESCRIPTION "Not implemented."

VARIATION cSipStatsTrafficRegisterOuts
  ACCESS    not-implemented
  DESCRIPTION "Not implemented."

VARIATION cSipCfgStatusCauseStoreStatus
  ACCESS    not-implemented
  DESCRIPTION "Not implemented."

VARIATION cSipCfgCauseStatusStoreStatus
  ACCESS    not-implemented
  DESCRIPTION "Not implemented."

::= { ciscoSipUaCapability 6 }

END
