-- *******************************************************************
-- CISCO-LWAPP-TUNNEL MIB CAPABILITY
--
-- November 18, 2020
--
-- Copyright (c) 2020, 2022 by Cisco Systems, Inc.
-- All rights reserved.
-- *******************************************************************

CISCO-LWAPP-TUNNEL-CAPABILITY DEFINITIONS ::= BEGIN


IMPORTS
       MODULE-IDENTITY
           FROM SNMPv2-SMI
       AGENT-CAPABILITIES
           FROM SNMPv2-CONF
       ciscoAgentCapability
           FROM CISCO-SMI;


ciscoLwappTunnelCapability  MODULE-IDENTITY

       LAST-UPDATED         "202011180000Z"
       ORGANIZATION         "Cisco Systems, Inc."
       CONTACT-INFO
               "Cisco Systems
               Customer Service

               Postal: 170 W Tasman Drive
               San Jose, CA  95134
               USA

               Tel: +1 800 553-NETS

               E-mail: cs-wnbu-snmp@cisco.com"

       DESCRIPTION
               "Agent capabilities for
               CISCO-LWAPP-TUNNEL-MIB "
       REVISION      "202011180000Z"
       DESCRIPTION
               "Initial version of this MIB module. "

   ::= { ciscoAgentCapability 1159 }

ciscoLwappTunnelCapabilityCEV1R0 AGENT-CAPABILITIES

       PRODUCT-RELEASE "Cisco EWLC 1.0"
       STATUS          current
       DESCRIPTION     "CISCO-LWAPP-TUNNEL--MIB capabilities."

       SUPPORTS        CISCO-LWAPP-TUNNEL-MIB
       INCLUDES        {
                           cLGatewayWlanConfigTable,
                           clGatewayDomainGatewayListTable
                       }

       VARIATION       cLGatewayWlanConfigEntry
       ACCESS          not-implemented
       DESCRIPTION     "Not supported"

       VARIATION       cLGatewayWlanVlanOverrideEnable
       ACCESS          not-implemented
       DESCRIPTION     "Not supported"

       VARIATION       cLGatewayWlanVlanId
       ACCESS          not-implemented
       DESCRIPTION     "Not supported"

       VARIATION       clGatewayDomainGatewayListRowStatus
       ACCESS          not-implemented
       DESCRIPTION     "Not supported"

   ::= { ciscoLwappTunnelCapability 1 }

END
