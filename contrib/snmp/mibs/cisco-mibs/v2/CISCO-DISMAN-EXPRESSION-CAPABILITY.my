-- *****************************************************************
-- CISCO-DISMAN-EXPRESSION-CAPABILITY.my:
-- Cisco DISMAN-EXPRESSION-MIB AGENT-CAPABILITIES
--
-- February 2006, Sreenivasulu Chalamcharla
--
-- Copyright (c) 2006 by Cisco Systems, Inc.
-- All rights reserved.
-- *****************************************************************

CISCO-DISMAN-EXPRESSION-CAPABILITY DEFINITIONS ::= BEGIN

IMPORTS
        MODULE-IDENTITY
                FROM SNMPv2-SMI
        AGENT-CAPABILITIES
                FROM SNMPv2-CONF
        ciscoAgentCapability
                FROM CISCO-SMI;

cdismanExpressionCapability MODULE-IDENTITY
        LAST-UPDATED    "200602160000Z"
        ORGANIZATION    "Cisco Systems, Inc."
        CONTACT-INFO
                "       Cisco Systems
                        Customer Service

                Postal: 170 West Tasman Drive
                        San Jose, CA  95134
                        USA

                   Tel: +1 800 553-NETS

                E-mail: cs-snmp@cisco.com"
                       
        DESCRIPTION
                "The capabilities description of
                 DISMAN-EXPRESSION-MIB."

        REVISION        "200602160000Z"
        DESCRIPTION
                "Initial version of this MIB module."
        ::= { ciscoAgentCapability 484 }

cdismanExpressionCapIOSXRV3R2R0CRS1 AGENT-CAPABILITIES
    PRODUCT-RELEASE     "Cisco IOS XR 3.2.0 for CRS-1"
    STATUS              current
    DESCRIPTION         "DISMAN-EXPRESSION-MIB capabilities for
                        IOS XR release 3.2.0"

    SUPPORTS            DISMAN-EXPRESSION-MIB
        INCLUDES        { dismanExpressionResourceGroup,
                          dismanExpressionDefinitionGroup,
                          dismanExpressionValueGroup
                        }
    VARIATION           expObjectDeltaDiscontinuityID
    ACCESS              not-implemented
    DESCRIPTION         "This object is not implemented in the
                        current MIB implementation."

    VARIATION           expObjectDiscontinuityIDWildcard
    ACCESS              not-implemented
    DESCRIPTION         "This object is not implemented in the
                        current MIB implementation."

    VARIATION           expObjectDiscontinuityIDType
    ACCESS              not-implemented
    DESCRIPTION         "This object is not implemented in the
                        current MIB implementation."

    ::= { cdismanExpressionCapability 1 }

END
