-- *****************************************************************
-- CISCO-CATOS-ACL-QOS-CAPABILITY.my:
-- Cisco CISCO-CATOS-ACL-QOS-MIB AGENT-CAPABILITIES
--
-- August 2003, Edward Pham 
--
-- Copyright (c) 2003, 2004, 2005, 2008 by Cisco Systems, Inc.
-- All rights reserved.
-- *****************************************************************

CISCO-CATOS-ACL-QOS-CAPABILITY DEFINITIONS ::= BEGIN

IMPORTS
        MODULE-IDENTITY
                FROM SNMPv2-SMI
        AGENT-CAPABILITIES
                FROM SNMPv2-CONF
        ciscoAgentCapability
                FROM CISCO-SMI;

ciscoCatOSAclQosCapability MODULE-IDENTITY
        LAST-UPDATED    "200803170000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The agent capabilities description of 
                 CISCO-CATOS-ACL-QOS-MIB."
        REVISION        "200803170000Z"
        DESCRIPTION
                "Add caqCapabilityV08R0701Cat6KPfc, 
                 caqCapabilityV08R0701Cat6KPfc2,
                 caqCapabilityV08R0701Cat6KPfc3,
                 caqCapabilityV08R0701Cat6KPfc3b
                 agent capability statements."
        REVISION        "200606290000Z"
        DESCRIPTION
                "Add caqCapabilityV08R0601Cat6KPfc, 
                 caqCapabilityV08R0601Cat6KPfc2,
                 caqCapabilityV08R0601Cat6KPfc3,
                 caqCapabilityV08R0601Cat6KPfc3b
                 agent capability statements."
        REVISION        "200509060000Z"
        DESCRIPTION
                "Add caqCapabilityV08R0501Cat6KPfc, 
                 caqCapabilityV08R0501Cat6KPfc2,
                 caqCapabilityV08R0501Cat6KPfc3,
                 caqCapabilityV08R0501Cat6KPfc3b
                 agent capability statements.

                 Add VARIATION clauses for caqIpAceProtocolMatchCriteria
                 object in all existing agent capability statements."
        REVISION        "200406240000Z"
        DESCRIPTION
                "Add caqCapabilityV08R0401Cat6KPfc, 
                 caqCapabilityV08R0401Cat6KPfc2,
                 caqCapabilityV08R0401Cat6KPfc3,
                 caqCapabilityV08R0401Cat6KPfc3b
                 agent capability statements."
        REVISION        "200401270000Z"
        DESCRIPTION
                "Add caqCapabilityV08R0301Cat6KPfc, 
                 caqCapabilityV08R0301Cat6KPfc2,
                 caqCapabilityV08R0301Cat6KPfc3
                 agent capability statements."
        REVISION        "200312190000Z"
        DESCRIPTION
                "Correct BITS syntax typo."
        REVISION        "200308251000Z"
        DESCRIPTION
                "Initial version of this MIB module."

        ::= { ciscoAgentCapability 325 }

caqCapabilityV08R0101Cat6KPfc AGENT-CAPABILITIES
    PRODUCT-RELEASE     "Cisco CatOS 8.1(1) on Catalyst 6000/6500
                         and Cisco 7600 series devices with PFC
                         card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqIpxAceGroup,
                          caqMacAceGroup,
                          caqActionGroup,
                          caqPolicingGroup,
                          caqQosMappingGroup,
                          caqQueueAssignmentGroup,
                          caqQueueGroup,
                          caqQosBridgedFlowPolicerGroup,
                          caqQosStatsGroup,
                          caqSecurityGroup, 
                          caqFlowPolicingCpbGroup,
                          caqQosStatsGroup2,
                          caqIfTrustDeviceGroup,
                          caqQosDefaultActionGroup,
                          caqIfAclConfigGroup2
                        }
        VARIATION       caqDscpMappingERPolicedDscp 
            ACCESS      not-implemented
            DESCRIPTION "Not supported."

        VARIATION       caqAggPolicerERExceedPackets 
            ACCESS      not-implemented
            DESCRIPTION "Not supported."

        VARIATION       caqSecurityAction 
            SYNTAX      INTEGER { permit(1), deny(2), redirect(3) } 
            DESCRIPTION "Only limited set of enumerated values
                         are supported."

        VARIATION       caqClassifierMapDirection 
            SYNTAX      BITS { ingress(0) } 
            DESCRIPTION "Only limited set of enumerated values
                         are supported."

        VARIATION       caqIpAceProtocolMatchCriteria
            SYNTAX      INTEGER { 
                             none(1),
                             matchIgmpType(2),
                             matchIcmpType(3),
                             matchIcmpTypeAndCode(4),
                             matchEstablished(5)
                        } 
            DESCRIPTION "Only limited set of enumerated values
                         are supported."

    ::= { ciscoCatOSAclQosCapability 1 }

caqCapabilityV08R0101Cat6KPfc2 AGENT-CAPABILITIES
    PRODUCT-RELEASE     "Cisco CatOS 8.1(1) on Catalyst 6000/6500
                         and Cisco 7600 series devices with PFC2
                         card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqIpxAceGroup,
                          caqMacAceGroup,
                          caqActionGroup,
                          caqPolicingGroup,
                          caqQosExcessRateGroup,
                          caqQosMappingGroup,
                          caqQueueAssignmentGroup,
                          caqQueueGroup,
                          caqQosBridgedFlowPolicerGroup,
                          caqQosStatsGroup,
                          caqSecurityGroup, 
                          caqFlowPolicingCpbGroup,
                          caqQosStatsGroup2,
                          caqSecurityPBFGroup,
                          caqQosExcessBurstGroup,
                          caqIfTrustDeviceGroup,
                          caqLoggingGroup,
                          caqArpInspGroup,
                          caqSecurityRateLimitGroup,
                          caqQosDefaultActionGroup,
                          caqIfAclConfigGroup2
                        }
        VARIATION       caqClassifierMapDirection 
            SYNTAX      BITS { ingress(0) }
            DESCRIPTION "Only limited set of enumerated values
                         are supported."

        VARIATION       caqIpAceProtocolMatchCriteria
            SYNTAX      INTEGER { 
                             none(1),
                             matchIgmpType(2),
                             matchIcmpType(3),
                             matchIcmpTypeAndCode(4),
                             matchEstablished(5)
                        } 
            DESCRIPTION "Only limited set of enumerated values
                         are supported."

    ::= { ciscoCatOSAclQosCapability 2 }

caqCapabilityV08R0101Cat6KPfc3 AGENT-CAPABILITIES
    PRODUCT-RELEASE     "Cisco CatOS 8.1(1) on Catalyst 6000/6500
                         and Cisco 7600 series devices with PFC3
                         card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqMacAceGroup,
                          caqActionGroup,
                          caqPolicingGroup,
                          caqQosExcessRateGroup,
                          caqQosMappingGroup,
                          caqQueueAssignmentGroup,
                          caqQueueGroup,
                          caqQosBridgedFlowPolicerGroup,
                          caqQosStatsGroup,
                          caqSecurityGroup, 
                          caqFlowPolicingCpbGroup,
                          caqSecurityPBFGroup,
                          caqQosExcessBurstGroup,
                          caqIfTrustDeviceGroup,
                          caqLoggingGroup,
                          caqArpInspGroup,
                          caqSecurityRateLimitGroup,
                          caqDscpMutationGroup,
                          caqQosDefaultActionGroup,
                          caqIfAclConfigGroup2,
                          caqDscpRewriteGroup,
                          caqAggPolicerOctetStatsGroup
                        }

        VARIATION       caqIpAceProtocolMatchCriteria
            SYNTAX      INTEGER { 
                             none(1),
                             matchIgmpType(2),
                             matchIcmpType(3),
                             matchIcmpTypeAndCode(4),
                             matchEstablished(5)
                        } 
            DESCRIPTION "Only limited set of enumerated values
                         are supported."

    ::= { ciscoCatOSAclQosCapability 3 }

caqCapabilityV08R0101Cat4K AGENT-CAPABILITIES
    PRODUCT-RELEASE     "Cisco CatOS 8.1(1) on Catalyst 4000 series
                         devices."
    STATUS              current
    DESCRIPTION         "CISCO-CATOS-ACL-QOS-MIB agent capabilities."

    SUPPORTS            CISCO-CATOS-ACL-QOS-MIB
        INCLUDES        { caqIfConfigGroup,
                          caqAclCpbGroup,
                          caqFlowPolicingCpbGroup,
                          caqQueueAssignmentGroup,
                          caqPolicingGroup
                        }

        VARIATION       caqIfTrustStateConfig 
            SYNTAX      INTEGER { trustCoS(2) }
            DESCRIPTION "Only limited set of enumerated values
                         are supported."
    
        VARIATION       caqFlowPolicerType 
            ACCESS      not-implemented
            DESCRIPTION "Not supported."

        VARIATION       caqFlowPolicerNormalRateRequest
            ACCESS      not-implemented
            DESCRIPTION "Not supported."

        VARIATION       caqFlowPolicerNormalRateGrant 
            ACCESS      not-implemented
            DESCRIPTION "Not supported."

        VARIATION       caqFlowPolicerBurstSizeRequest 
            ACCESS      not-implemented
            DESCRIPTION "Not supported."

        VARIATION       caqFlowPolicerBurstSizeGrant 
            ACCESS      not-implemented
            DESCRIPTION "Not supported."

        VARIATION       caqFlowPolicerNormalRateAction
            ACCESS      not-implemented
            DESCRIPTION "Not supported."

        VARIATION       caqFlowPolicerStatus 
            ACCESS      not-implemented
            DESCRIPTION "Not supported."

    ::= { ciscoCatOSAclQosCapability 4 }

caqCapabilityV08R0301Cat6KPfc AGENT-CAPABILITIES
    PRODUCT-RELEASE     "Cisco CatOS 8.3(1) on Catalyst 6000/6500
                         and Cisco 7600 series devices with PFC
                         card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqIpxAceGroup,
                          caqMacAceGroup,
                          caqActionGroup,
                          caqPolicingGroup,
                          caqQosMappingGroup,
                          caqQueueAssignmentGroup,
                          caqQueueGroup,
                          caqQosBridgedFlowPolicerGroup,
                          caqQosStatsGroup,
                          caqSecurityGroup, 
                          caqFlowPolicingCpbGroup,
                          caqQosStatsGroup2,
                          caqIfTrustDeviceGroup,
                          caqQosDefaultActionGroup,
                          caqIfAclConfigGroup2,
                          caqIpAceExtGroup 
                        }
        VARIATION       caqDscpMappingERPolicedDscp 
            ACCESS      not-implemented
            DESCRIPTION "Not supported."

        VARIATION       caqAggPolicerERExceedPackets 
            ACCESS      not-implemented
            DESCRIPTION "Not supported."

        VARIATION       caqSecurityAction 
            SYNTAX      INTEGER { permit(1), deny(2), redirect(3) } 
            DESCRIPTION "Only limited set of enumerated values
                         are supported."

        VARIATION       caqClassifierMapDirection 
            SYNTAX      BITS { ingress(0) } 
            DESCRIPTION "Only limited set of enumerated values
                         are supported."

        VARIATION       caqIpAceProtocolMatchCriteria
            SYNTAX      INTEGER { 
                             none(1),
                             matchIgmpType(2),
                             matchIcmpType(3),
                             matchIcmpTypeAndCode(4),
                             matchEstablished(5)
                        } 
            DESCRIPTION "Only limited set of enumerated values
                         are supported."

    ::= { ciscoCatOSAclQosCapability 5 }

caqCapabilityV08R0301Cat6KPfc2 AGENT-CAPABILITIES
    PRODUCT-RELEASE     "Cisco CatOS 8.3(1) on Catalyst 6000/6500
                         and Cisco 7600 series devices with PFC2
                         card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqIpxAceGroup,
                          caqMacAceGroup,
                          caqActionGroup,
                          caqPolicingGroup,
                          caqQosExcessRateGroup,
                          caqQosMappingGroup,
                          caqQueueAssignmentGroup,
                          caqQueueGroup,
                          caqQosBridgedFlowPolicerGroup,
                          caqQosStatsGroup,
                          caqSecurityGroup, 
                          caqFlowPolicingCpbGroup,
                          caqQosStatsGroup2,
                          caqSecurityPBFGroup,
                          caqQosExcessBurstGroup,
                          caqIfTrustDeviceGroup,
                          caqLoggingGroup,
                          caqArpInspGroup,
                          caqSecurityRateLimitGroup,
                          caqQosDefaultActionGroup,
                          caqIfAclConfigGroup2,
                          caqIpAceExtGroup
                        }
        VARIATION       caqClassifierMapDirection 
            SYNTAX      BITS { ingress(0) }
            DESCRIPTION "Only limited set of enumerated values
                         are supported."

        VARIATION       caqIpAceProtocolMatchCriteria
            SYNTAX      INTEGER { 
                             none(1),
                             matchIgmpType(2),
                             matchIcmpType(3),
                             matchIcmpTypeAndCode(4),
                             matchEstablished(5)
                        } 
            DESCRIPTION "Only limited set of enumerated values
                         are supported."

    ::= { ciscoCatOSAclQosCapability 6 }

caqCapabilityV08R0301Cat6KPfc3 AGENT-CAPABILITIES
    PRODUCT-RELEASE     "Cisco CatOS 8.3(1) on Catalyst 6000/6500
                         and Cisco 7600 series devices with PFC3
                         card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqMacAceGroup,
                          caqActionGroup,
                          caqPolicingGroup,
                          caqQosExcessRateGroup,
                          caqQosMappingGroup,
                          caqQueueAssignmentGroup,
                          caqQueueGroup,
                          caqQosBridgedFlowPolicerGroup,
                          caqQosStatsGroup,
                          caqSecurityGroup, 
                          caqFlowPolicingCpbGroup,
                          caqSecurityPBFGroup,
                          caqQosExcessBurstGroup,
                          caqIfTrustDeviceGroup,
                          caqLoggingGroup,
                          caqArpInspGroup,
                          caqSecurityRateLimitGroup,
                          caqDscpMutationGroup,
                          caqQosDefaultActionGroup,
                          caqIfAclConfigGroup2,
                          caqDscpRewriteGroup,
                          caqAggPolicerOctetStatsGroup,
                          caqIpAceExtGroup,
                          caqIfSecurityAclConfigGroup
                        }

        VARIATION       caqIpAceProtocolMatchCriteria
            SYNTAX      INTEGER { 
                             none(1),
                             matchIgmpType(2),
                             matchIcmpType(3),
                             matchIcmpTypeAndCode(4),
                             matchEstablished(5)
                        } 
            DESCRIPTION "Only limited set of enumerated values
                         are supported."

    ::= { ciscoCatOSAclQosCapability 7 }

caqCapabilityV08R0401Cat6KPfc AGENT-CAPABILITIES
    PRODUCT-RELEASE     "Cisco CatOS 8.4(1) on Catalyst 6000/6500
                         and Cisco 7600 series devices with PFC
                         card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqIpxAceGroup,
                          caqMacAceGroup,
                          caqActionGroup,
                          caqPolicingGroup,
                          caqQosMappingGroup,
                          caqQueueAssignmentGroup,
                          caqQueueGroup,
                          caqQosBridgedFlowPolicerGroup,
                          caqQosStatsGroup,
                          caqSecurityGroup, 
                          caqFlowPolicingCpbGroup,
                          caqQosStatsGroup2,
                          caqIfTrustDeviceGroup,
                          caqQosDefaultActionGroup,
                          caqIfAclConfigGroup2,
                          caqIpAceExtGroup 
                        }
        VARIATION       caqDscpMappingERPolicedDscp 
            ACCESS      not-implemented
            DESCRIPTION "Not supported."

        VARIATION       caqAggPolicerERExceedPackets 
            ACCESS      not-implemented
            DESCRIPTION "Not supported."

        VARIATION       caqSecurityAction 
            SYNTAX      INTEGER { permit(1), deny(2), redirect(3) } 
            DESCRIPTION "Only limited set of enumerated values
                         are supported."

        VARIATION       caqClassifierMapDirection 
            SYNTAX      BITS { ingress(0) } 
            DESCRIPTION "Only limited set of enumerated values
                         are supported."

        VARIATION       caqIpAceProtocolMatchCriteria
            SYNTAX      INTEGER { 
                             none(1),
                             matchIgmpType(2),
                             matchIcmpType(3),
                             matchIcmpTypeAndCode(4),
                             matchEstablished(5)
                        } 
            DESCRIPTION "Only limited set of enumerated values
                         are supported."

    ::= { ciscoCatOSAclQosCapability 8 }

caqCapabilityV08R0401Cat6KPfc2 AGENT-CAPABILITIES
    PRODUCT-RELEASE     "Cisco CatOS 8.4(1) on Catalyst 6000/6500
                         and Cisco 7600 series devices with PFC2
                         card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqIpxAceGroup,
                          caqMacAceGroup,
                          caqActionGroup,
                          caqPolicingGroup,
                          caqQosExcessRateGroup,
                          caqQosMappingGroup,
                          caqQueueAssignmentGroup,
                          caqQueueGroup,
                          caqQosBridgedFlowPolicerGroup,
                          caqQosStatsGroup,
                          caqSecurityGroup, 
                          caqFlowPolicingCpbGroup,
                          caqQosStatsGroup2,
                          caqSecurityPBFGroup,
                          caqQosExcessBurstGroup,
                          caqIfTrustDeviceGroup,
                          caqLoggingGroup,
                          caqArpInspGroup,
                          caqSecurityRateLimitGroup,
                          caqQosDefaultActionGroup,
                          caqIfAclConfigGroup2,
                          caqIpAceExtGroup,
                          caqAclHitCountGroup,
                          caqAclFeatureGroup,
                          caqVlanAclHitCountGroup
                        }
        VARIATION       caqClassifierMapDirection 
            SYNTAX      BITS { ingress(0) }
            DESCRIPTION "Only limited set of enumerated values
                         are supported."

        VARIATION       caqAclFeatureCpb 
            SYNTAX      BITS { vlanAclHitCount(0) }
            DESCRIPTION "Only limited set of enumerated values
                         are supported."

        VARIATION       caqIpAceProtocolMatchCriteria
            SYNTAX      INTEGER { 
                             none(1),
                             matchIgmpType(2),
                             matchIcmpType(3),
                             matchIcmpTypeAndCode(4),
                             matchEstablished(5)
                        } 
            DESCRIPTION "Only limited set of enumerated values
                         are supported."

    ::= { ciscoCatOSAclQosCapability 9 }

caqCapabilityV08R0401Cat6KPfc3 AGENT-CAPABILITIES
    PRODUCT-RELEASE     "Cisco CatOS 8.4(1) on Catalyst 6000/6500
                         and Cisco 7600 series devices with PFC3
                         card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqMacAceGroup,
                          caqActionGroup,
                          caqPolicingGroup,
                          caqQosExcessRateGroup,
                          caqQosMappingGroup,
                          caqQueueAssignmentGroup,
                          caqQueueGroup,
                          caqQosBridgedFlowPolicerGroup,
                          caqQosStatsGroup,
                          caqSecurityGroup, 
                          caqFlowPolicingCpbGroup,
                          caqSecurityPBFGroup,
                          caqQosExcessBurstGroup,
                          caqIfTrustDeviceGroup,
                          caqLoggingGroup,
                          caqArpInspGroup,
                          caqSecurityRateLimitGroup,
                          caqDscpMutationGroup,
                          caqQosDefaultActionGroup,
                          caqIfAclConfigGroup2,
                          caqDscpRewriteGroup,
                          caqAggPolicerOctetStatsGroup,
                          caqIpAceExtGroup,
                          caqIfSecurityAclConfigGroup,
                          caqAclHitCountGroup,
                          caqAclFeatureGroup,
                          caqPortAclHitCountGroup,
                          caqVlanAclHitCountGroup
                        }

        VARIATION       caqAclHitCountAclType 
            SYNTAX      INTEGER { ipSecurity(1), macSecurity(3) }
            DESCRIPTION "Only limited set of enumerated values
                         are supported."

        VARIATION       caqAceHitCountAclType 
            SYNTAX      INTEGER { ipSecurity(1), macSecurity(3) }
            DESCRIPTION "Only limited set of enumerated values
                         are supported."

        VARIATION       caqIfAclHitCountAclType 
            SYNTAX      INTEGER { ipSecurity(1), macSecurity(3) }
            DESCRIPTION "Only limited set of enumerated values
                         are supported."

        VARIATION       caqIpAceProtocolMatchCriteria
            SYNTAX      INTEGER { 
                             none(1),
                             matchIgmpType(2),
                             matchIcmpType(3),
                             matchIcmpTypeAndCode(4),
                             matchEstablished(5)
                        } 
            DESCRIPTION "Only limited set of enumerated values
                         are supported."

    ::= { ciscoCatOSAclQosCapability 10 }

caqCapabilityV08R0401Cat6KPfc3b AGENT-CAPABILITIES
    PRODUCT-RELEASE     "Cisco CatOS 8.4(1) on Catalyst 6000/6500
                         and Cisco 7600 series devices with PFC3B
                         or PFC3BXL card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqMacAceGroup,
                          caqActionGroup,
                          caqPolicingGroup,
                          caqQosExcessRateGroup,
                          caqQosMappingGroup,
                          caqQueueAssignmentGroup,
                          caqQueueGroup,
                          caqQosBridgedFlowPolicerGroup,
                          caqQosStatsGroup,
                          caqSecurityGroup, 
                          caqFlowPolicingCpbGroup,
                          caqSecurityPBFGroup,
                          caqQosExcessBurstGroup,
                          caqIfTrustDeviceGroup,
                          caqLoggingGroup,
                          caqArpInspGroup,
                          caqSecurityRateLimitGroup,
                          caqDscpMutationGroup,
                          caqQosDefaultActionGroup,
                          caqIfAclConfigGroup2,
                          caqDscpRewriteGroup,
                          caqAggPolicerOctetStatsGroup,
                          caqIpAceExtGroup,
                          caqIfSecurityAclConfigGroup,
                          caqAclHitCountGroup,
                          caqMacAceExtGroup,
                          caqMacPktClassifyVlanGroup,
                          caqAclFeatureGroup,
                          caqPortAclHitCountGroup,
                          caqVlanAclHitCountGroup
                        }

        VARIATION       caqAclHitCountAclType 
            SYNTAX      INTEGER { ipSecurity(1), macSecurity(3) }
            DESCRIPTION "Only limited set of enumerated values
                         are supported."

        VARIATION       caqAceHitCountAclType 
            SYNTAX      INTEGER { ipSecurity(1), macSecurity(3) }
            DESCRIPTION "Only limited set of enumerated values
                         are supported."

        VARIATION       caqIfAclHitCountAclType 
            SYNTAX      INTEGER { ipSecurity(1), macSecurity(3) }
            DESCRIPTION "Only limited set of enumerated values
                         are supported."

        VARIATION       caqIpAceProtocolMatchCriteria
            SYNTAX      INTEGER { 
                             none(1),
                             matchIgmpType(2),
                             matchIcmpType(3),
                             matchIcmpTypeAndCode(4),
                             matchEstablished(5)
                        } 
            DESCRIPTION "Only limited set of enumerated values
                         are supported."

    ::= { ciscoCatOSAclQosCapability 11 }

caqCapabilityV08R0501Cat6KPfc AGENT-CAPABILITIES
    PRODUCT-RELEASE     "Cisco CatOS 8.5(1) on Catalyst 6000/6500
                         and Cisco 7600 series devices with PFC
                         card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqIpxAceGroup,
                          caqMacAceGroup,
                          caqActionGroup,
                          caqPolicingGroup,
                          caqQosMappingGroup,
                          caqQueueAssignmentGroup,
                          caqQueueGroup,
                          caqQosBridgedFlowPolicerGroup,
                          caqQosStatsGroup,
                          caqSecurityGroup, 
                          caqFlowPolicingCpbGroup,
                          caqQosStatsGroup2,
                          caqIfTrustDeviceGroup,
                          caqQosDefaultActionGroup,
                          caqIfAclConfigGroup2,
                          caqIpAceExtGroup 
                        }
        VARIATION       caqDscpMappingERPolicedDscp 
            ACCESS      not-implemented
            DESCRIPTION "Not supported."

        VARIATION       caqAggPolicerERExceedPackets 
            ACCESS      not-implemented
            DESCRIPTION "Not supported."

        VARIATION       caqSecurityAction 
            SYNTAX      INTEGER { permit(1), deny(2), redirect(3) } 
            DESCRIPTION "Only limited set of enumerated values
                         are supported."

        VARIATION       caqClassifierMapDirection 
            SYNTAX      BITS { ingress(0) } 
            DESCRIPTION "Only limited set of enumerated values
                         are supported."

        VARIATION       caqIpAceProtocolMatchCriteria
            SYNTAX      INTEGER { 
                             none(1),
                             matchIgmpType(2),
                             matchIcmpType(3),
                             matchIcmpTypeAndCode(4),
                             matchEstablished(5),
                             matchEapoudp(7),
                             matchUrlRedirect(8)
                        } 
            DESCRIPTION "Only limited set of enumerated values
                         are supported. When caqIpAceFeature has
                         the value of 'qos', the supported values
                         have the additional limitation that
                         'matchEapoudp' and 'matchUrlRedirect' are
                         not supported."

    ::= { ciscoCatOSAclQosCapability 12 }

caqCapabilityV08R0501Cat6KPfc2 AGENT-CAPABILITIES
    PRODUCT-RELEASE     "Cisco CatOS 8.5(1) on Catalyst 6000/6500
                         and Cisco 7600 series devices with PFC2
                         card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqIpxAceGroup,
                          caqMacAceGroup,
                          caqActionGroup,
                          caqPolicingGroup,
                          caqQosExcessRateGroup,
                          caqQosMappingGroup,
                          caqQueueAssignmentGroup,
                          caqQueueGroup,
                          caqQosBridgedFlowPolicerGroup,
                          caqQosStatsGroup,
                          caqSecurityGroup, 
                          caqFlowPolicingCpbGroup,
                          caqQosStatsGroup2,
                          caqSecurityPBFGroup,
                          caqQosExcessBurstGroup,
                          caqIfTrustDeviceGroup,
                          caqLoggingGroup,
                          caqArpInspGroup,
                          caqSecurityRateLimitGroup,
                          caqQosDefaultActionGroup,
                          caqIfAclConfigGroup2,
                          caqIpAceExtGroup,
                          caqAclHitCountGroup,
                          caqAclFeatureGroup,
                          caqVlanAclHitCountGroup
                        }
        VARIATION       caqClassifierMapDirection 
            SYNTAX      BITS { ingress(0) }
            DESCRIPTION "Only limited set of enumerated values
                         are supported."

        VARIATION       caqAclFeatureCpb 
            SYNTAX      BITS { vlanAclHitCount(0) }
            DESCRIPTION "Only limited set of enumerated values
                         are supported."

        VARIATION       caqIpAceProtocolMatchCriteria
            SYNTAX      INTEGER { 
                             none(1),
                             matchIgmpType(2),
                             matchIcmpType(3),
                             matchIcmpTypeAndCode(4),
                             matchEstablished(5),
                             matchEapoudp(7),
                             matchUrlRedirect(8)
                        } 
            DESCRIPTION "Only limited set of enumerated values
                         are supported. When caqIpAceFeature has
                         the value of 'qos', the supported values
                         have the additional limitation that
                         'matchEapoudp' and 'matchUrlRedirect' are
                         not supported."
    ::= { ciscoCatOSAclQosCapability 13 }

caqCapabilityV08R0501Cat6KPfc3 AGENT-CAPABILITIES
    PRODUCT-RELEASE     "Cisco CatOS 8.5(1) on Catalyst 6000/6500
                         and Cisco 7600 series devices with PFC3
                         card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqMacAceGroup,
                          caqActionGroup,
                          caqPolicingGroup,
                          caqQosExcessRateGroup,
                          caqQosMappingGroup,
                          caqQueueAssignmentGroup,
                          caqQueueGroup,
                          caqQosBridgedFlowPolicerGroup,
                          caqQosStatsGroup,
                          caqSecurityGroup, 
                          caqFlowPolicingCpbGroup,
                          caqSecurityPBFGroup,
                          caqQosExcessBurstGroup,
                          caqIfTrustDeviceGroup,
                          caqLoggingGroup,
                          caqArpInspGroup,
                          caqSecurityRateLimitGroup,
                          caqDscpMutationGroup,
                          caqQosDefaultActionGroup,
                          caqIfAclConfigGroup2,
                          caqDscpRewriteGroup,
                          caqAggPolicerOctetStatsGroup,
                          caqIpAceExtGroup,
                          caqIfSecurityAclConfigGroup,
                          caqAclHitCountGroup,
                          caqAclFeatureGroup,
                          caqPortAclHitCountGroup,
                          caqVlanAclHitCountGroup
                        }

        VARIATION       caqAclHitCountAclType 
            SYNTAX      INTEGER { ipSecurity(1), macSecurity(3) }
            DESCRIPTION "Only limited set of enumerated values
                         are supported."

        VARIATION       caqAceHitCountAclType 
            SYNTAX      INTEGER { ipSecurity(1), macSecurity(3) }
            DESCRIPTION "Only limited set of enumerated values
                         are supported."

        VARIATION       caqIfAclHitCountAclType 
            SYNTAX      INTEGER { ipSecurity(1), macSecurity(3) }
            DESCRIPTION "Only limited set of enumerated values
                         are supported."

        VARIATION       caqIpAceProtocolMatchCriteria
            SYNTAX      INTEGER { 
                             none(1),
                             matchIgmpType(2),
                             matchIcmpType(3),
                             matchIcmpTypeAndCode(4),
                             matchEstablished(5),
                             matchEapoudp(7),
                             matchUrlRedirect(8)
                        } 
            DESCRIPTION "Only limited set of enumerated values
                         are supported. When caqIpAceFeature has
                         the value of 'qos', the supported values
                         have the additional limitation that
                         'matchEapoudp' and 'matchUrlRedirect' are
                         not supported."
    ::= { ciscoCatOSAclQosCapability 14 }

caqCapabilityV08R0501Cat6KPfc3b AGENT-CAPABILITIES
    PRODUCT-RELEASE     "Cisco CatOS 8.5(1) on Catalyst 6000/6500
                         and Cisco 7600 series devices with PFC3B
                         or PFC3BXL card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqMacAceGroup,
                          caqActionGroup,
                          caqPolicingGroup,
                          caqQosExcessRateGroup,
                          caqQosMappingGroup,
                          caqQueueAssignmentGroup,
                          caqQueueGroup,
                          caqQosBridgedFlowPolicerGroup,
                          caqQosStatsGroup,
                          caqSecurityGroup, 
                          caqFlowPolicingCpbGroup,
                          caqSecurityPBFGroup,
                          caqQosExcessBurstGroup,
                          caqIfTrustDeviceGroup,
                          caqLoggingGroup,
                          caqArpInspGroup,
                          caqSecurityRateLimitGroup,
                          caqDscpMutationGroup,
                          caqQosDefaultActionGroup,
                          caqIfAclConfigGroup2,
                          caqDscpRewriteGroup,
                          caqAggPolicerOctetStatsGroup,
                          caqIpAceExtGroup,
                          caqIfSecurityAclConfigGroup,
                          caqAclHitCountGroup,
                          caqMacAceExtGroup,
                          caqMacPktClassifyVlanGroup,
                          caqAclFeatureGroup,
                          caqPortAclHitCountGroup,
                          caqVlanAclHitCountGroup
                        }

        VARIATION       caqAclHitCountAclType 
            SYNTAX      INTEGER { ipSecurity(1), macSecurity(3) }
            DESCRIPTION "Only limited set of enumerated values
                         are supported."

        VARIATION       caqAceHitCountAclType 
            SYNTAX      INTEGER { ipSecurity(1), macSecurity(3) }
            DESCRIPTION "Only limited set of enumerated values
                         are supported."

        VARIATION       caqIfAclHitCountAclType 
            SYNTAX      INTEGER { ipSecurity(1), macSecurity(3) }
            DESCRIPTION "Only limited set of enumerated values
                         are supported."

        VARIATION       caqIpAceProtocolMatchCriteria
            SYNTAX      INTEGER { 
                             none(1),
                             matchIgmpType(2),
                             matchIcmpType(3),
                             matchIcmpTypeAndCode(4),
                             matchEstablished(5),
                             matchEapoudp(7),
                             matchUrlRedirect(8)
                        } 
            DESCRIPTION "Only limited set of enumerated values
                         are supported. When caqIpAceFeature has
                         the value of 'qos', the supported values
                         have the additional limitation that
                         'matchEapoudp' and 'matchUrlRedirect' are
                         not supported."
    ::= { ciscoCatOSAclQosCapability 15 }

caqCapabilityV08R0601Cat6KPfc AGENT-CAPABILITIES
    PRODUCT-RELEASE     "Cisco CatOS 8.6(1) on Catalyst 6000/6500
                         and Cisco 7600 series devices with PFC
                         card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqIpxAceGroup,
                          caqMacAceGroup,
                          caqActionGroup,
                          caqPolicingGroup,
                          caqQosMappingGroup,
                          caqQueueAssignmentGroup,
                          caqQueueGroup,
                          caqQosBridgedFlowPolicerGroup,
                          caqQosStatsGroup,
                          caqSecurityGroup, 
                          caqFlowPolicingCpbGroup,
                          caqQosStatsGroup2,
                          caqIfTrustDeviceGroup,
                          caqQosDefaultActionGroup,
                          caqIfAclConfigGroup2,
                          caqIpAceExtGroup,
                          caqQosL3StatsRateGroup,
                          caqQosL3StatsPeakGroup,
                          caqAggPolicerPacketsRateGroup,
                          caqAggPolicerPacketsPeakGroup,
                          caqQosPortRateGroup,
                          caqQosPortPeakGroup,
                          caqSecurityActionDnldAceGroup 
                        }
        VARIATION       caqDscpMappingERPolicedDscp 
            ACCESS      not-implemented
            DESCRIPTION "Not supported."

        VARIATION       caqAggPolicerERExceedPackets 
            ACCESS      not-implemented
            DESCRIPTION "Not supported."

        VARIATION       caqSecurityAction 
            SYNTAX      INTEGER { permit(1), deny(2), redirect(3) } 
            DESCRIPTION "Only limited set of enumerated values
                         are supported."

        VARIATION       caqClassifierMapDirection 
            SYNTAX      BITS { ingress(0) } 
            DESCRIPTION "Only limited set of enumerated values
                         are supported."

        VARIATION       caqIpAceProtocolMatchCriteria
            SYNTAX      INTEGER { 
                             none(1),
                             matchIgmpType(2),
                             matchIcmpType(3),
                             matchIcmpTypeAndCode(4),
                             matchEstablished(5),
                             matchEapoudp(7),
                             matchUrlRedirect(8)
                        } 
            DESCRIPTION "Only limited set of enumerated values
                         are supported. When caqIpAceFeature has
                         the value of 'qos', the supported values
                         have the additional limitation that
                         'matchEapoudp' and 'matchUrlRedirect' are
                         not supported."

    ::= { ciscoCatOSAclQosCapability 16 }

caqCapabilityV08R0601Cat6KPfc2 AGENT-CAPABILITIES
    PRODUCT-RELEASE     "Cisco CatOS 8.6(1) on Catalyst 6000/6500
                         and Cisco 7600 series devices with PFC2
                         card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqIpxAceGroup,
                          caqMacAceGroup,
                          caqActionGroup,
                          caqPolicingGroup,
                          caqQosExcessRateGroup,
                          caqQosMappingGroup,
                          caqQueueAssignmentGroup,
                          caqQueueGroup,
                          caqQosBridgedFlowPolicerGroup,
                          caqQosStatsGroup,
                          caqSecurityGroup, 
                          caqFlowPolicingCpbGroup,
                          caqQosStatsGroup2,
                          caqSecurityPBFGroup,
                          caqQosExcessBurstGroup,
                          caqIfTrustDeviceGroup,
                          caqLoggingGroup,
                          caqArpInspGroup,
                          caqSecurityRateLimitGroup,
                          caqQosDefaultActionGroup,
                          caqIfAclConfigGroup2,
                          caqIpAceExtGroup,
                          caqAclHitCountGroup,
                          caqAclFeatureGroup,
                          caqVlanAclHitCountGroup,
                          caqQosL3StatsRateGroup,
                          caqQosL3StatsPeakGroup,
                          caqAggPolicerPacketsRateGroup,
                          caqAggPolicerPacketsPeakGroup,
                          caqQosPortRateGroup,
                          caqQosPortPeakGroup,
                          caqSecurityActionDnldAceGroup
                        }
        VARIATION       caqClassifierMapDirection 
            SYNTAX      BITS { ingress(0) }
            DESCRIPTION "Only limited set of enumerated values
                         are supported."

        VARIATION       caqAclFeatureCpb 
            SYNTAX      BITS { vlanAclHitCount(0) }
            DESCRIPTION "Only limited set of enumerated values
                         are supported."

        VARIATION       caqSecurityAction 
            SYNTAX      INTEGER { 
                             permit(1), 
                             deny(2), 
                             redirect(3),
                             redirectWithAdj(4),
                             denyWithLog(5),
                             denyArpInspection(6),
                             denyArpInspWithLog(7),
                             permitArpInspection(8)
                         } 
            DESCRIPTION "Only limited set of enumerated values
                         are supported."

        VARIATION       caqIpAceProtocolMatchCriteria
            SYNTAX      INTEGER { 
                             none(1),
                             matchIgmpType(2),
                             matchIcmpType(3),
                             matchIcmpTypeAndCode(4),
                             matchEstablished(5),
                             matchEapoudp(7),
                             matchUrlRedirect(8)
                        } 
            DESCRIPTION "Only limited set of enumerated values
                         are supported. When caqIpAceFeature has
                         the value of 'qos', the supported values
                         have the additional limitation that
                         'matchEapoudp' and 'matchUrlRedirect' are
                         not supported."
    ::= { ciscoCatOSAclQosCapability 17 }

caqCapabilityV08R0601Cat6KPfc3 AGENT-CAPABILITIES
    PRODUCT-RELEASE     "Cisco CatOS 8.6(1) on Catalyst 6000/6500
                         and Cisco 7600 series devices with PFC3
                         card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqMacAceGroup,
                          caqActionGroup,
                          caqPolicingGroup,
                          caqQosExcessRateGroup,
                          caqQosMappingGroup,
                          caqQueueAssignmentGroup,
                          caqQueueGroup,
                          caqQosBridgedFlowPolicerGroup,
                          caqQosStatsGroup,
                          caqSecurityGroup, 
                          caqFlowPolicingCpbGroup,
                          caqSecurityPBFGroup,
                          caqQosExcessBurstGroup,
                          caqIfTrustDeviceGroup,
                          caqLoggingGroup,
                          caqArpInspGroup,
                          caqSecurityRateLimitGroup,
                          caqDscpMutationGroup,
                          caqQosDefaultActionGroup,
                          caqIfAclConfigGroup2,
                          caqDscpRewriteGroup,
                          caqAggPolicerOctetStatsGroup,
                          caqIpAceExtGroup,
                          caqIfSecurityAclConfigGroup,
                          caqAclHitCountGroup,
                          caqAclFeatureGroup,
                          caqPortAclHitCountGroup,
                          caqVlanAclHitCountGroup,
                          caqQosL3StatsRateGroup,
                          caqQosL3StatsPeakGroup,
                          caqAggPolicerOctetsRateGroup,
                          caqAggPolicerOctetsPeakGroup,
                          caqQosPortRateGroup,
                          caqQosPortPeakGroup,
                          caqSecurityActionDnldAceGroup 
                        }

        VARIATION       caqAclHitCountAclType 
            SYNTAX      INTEGER { ipSecurity(1), macSecurity(3) }
            DESCRIPTION "Only limited set of enumerated values
                         are supported."

        VARIATION       caqAceHitCountAclType 
            SYNTAX      INTEGER { ipSecurity(1), macSecurity(3) }
            DESCRIPTION "Only limited set of enumerated values
                         are supported."

        VARIATION       caqIfAclHitCountAclType 
            SYNTAX      INTEGER { ipSecurity(1), macSecurity(3) }
            DESCRIPTION "Only limited set of enumerated values
                         are supported."

        VARIATION       caqIpAceProtocolMatchCriteria
            SYNTAX      INTEGER { 
                             none(1),
                             matchIgmpType(2),
                             matchIcmpType(3),
                             matchIcmpTypeAndCode(4),
                             matchEstablished(5),
                             matchEapoudp(7),
                             matchUrlRedirect(8)
                        } 
            DESCRIPTION "Only limited set of enumerated values
                         are supported. When caqIpAceFeature has
                         the value of 'qos', the supported values
                         have the additional limitation that
                         'matchEapoudp' and 'matchUrlRedirect' are
                         not supported."
    ::= { ciscoCatOSAclQosCapability 18 }

caqCapabilityV08R0601Cat6KPfc3b AGENT-CAPABILITIES
    PRODUCT-RELEASE     "Cisco CatOS 8.6(1) on Catalyst 6000/6500
                         and Cisco 7600 series devices with PFC3B
                         or PFC3BXL card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqMacAceGroup,
                          caqActionGroup,
                          caqPolicingGroup,
                          caqQosExcessRateGroup,
                          caqQosMappingGroup,
                          caqQueueAssignmentGroup,
                          caqQueueGroup,
                          caqQosBridgedFlowPolicerGroup,
                          caqQosStatsGroup,
                          caqSecurityGroup, 
                          caqFlowPolicingCpbGroup,
                          caqSecurityPBFGroup,
                          caqQosExcessBurstGroup,
                          caqIfTrustDeviceGroup,
                          caqLoggingGroup,
                          caqArpInspGroup,
                          caqSecurityRateLimitGroup,
                          caqDscpMutationGroup,
                          caqQosDefaultActionGroup,
                          caqIfAclConfigGroup2,
                          caqDscpRewriteGroup,
                          caqAggPolicerOctetStatsGroup,
                          caqIpAceExtGroup,
                          caqIfSecurityAclConfigGroup,
                          caqAclHitCountGroup,
                          caqMacAceExtGroup,
                          caqMacPktClassifyVlanGroup,
                          caqAclFeatureGroup,
                          caqPortAclHitCountGroup,
                          caqVlanAclHitCountGroup,
                          caqQosL3StatsRateGroup,
                          caqQosL3StatsPeakGroup,
                          caqAggPolicerOctetsRateGroup,
                          caqAggPolicerOctetsPeakGroup,
                          caqQosPortRateGroup,
                          caqQosPortPeakGroup,
                          caqSecurityActionDnldAceGroup 
                        }

        VARIATION       caqAclHitCountAclType 
            SYNTAX      INTEGER { ipSecurity(1), macSecurity(3) }
            DESCRIPTION "Only limited set of enumerated values
                         are supported."

        VARIATION       caqAceHitCountAclType 
            SYNTAX      INTEGER { ipSecurity(1), macSecurity(3) }
            DESCRIPTION "Only limited set of enumerated values
                         are supported."

        VARIATION       caqIfAclHitCountAclType 
            SYNTAX      INTEGER { ipSecurity(1), macSecurity(3) }
            DESCRIPTION "Only limited set of enumerated values
                         are supported."

        VARIATION       caqIpAceProtocolMatchCriteria
            SYNTAX      INTEGER { 
                             none(1),
                             matchIgmpType(2),
                             matchIcmpType(3),
                             matchIcmpTypeAndCode(4),
                             matchEstablished(5),
                             matchEapoudp(7),
                             matchUrlRedirect(8)
                        } 
            DESCRIPTION "Only limited set of enumerated values
                         are supported. When caqIpAceFeature has
                         the value of 'qos', the supported values
                         have the additional limitation that
                         'matchEapoudp' and 'matchUrlRedirect' are
                         not supported."
    ::= { ciscoCatOSAclQosCapability 19 }

caqCapabilityV08R0701Cat6KPfc AGENT-CAPABILITIES
    PRODUCT-RELEASE     "Cisco CatOS 8.7(1) on Catalyst 6000/6500
                         and Cisco 7600 series devices with PFC
                         card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqIpxAceGroup,
                          caqMacAceGroup,
                          caqActionGroup,
                          caqPolicingGroup,
                          caqQosMappingGroup,
                          caqQueueAssignmentGroup,
                          caqQueueGroup,
                          caqQosBridgedFlowPolicerGroup,
                          caqQosStatsGroup,
                          caqSecurityGroup, 
                          caqFlowPolicingCpbGroup,
                          caqQosStatsGroup2,
                          caqIfTrustDeviceGroup,
                          caqQosDefaultActionGroup,
                          caqIfAclConfigGroup2,
                          caqIpAceExtGroup,
                          caqQosL3StatsRateGroup,
                          caqQosL3StatsPeakGroup,
                          caqAggPolicerPacketsRateGroup,
                          caqAggPolicerPacketsPeakGroup,
                          caqQosPortRateGroup,
                          caqQosPortPeakGroup,
                          caqSecurityActionDnldAceGroup,
                          caqIpOperClassifierGroup 
                        }
        VARIATION       caqDscpMappingERPolicedDscp 
            ACCESS      not-implemented
            DESCRIPTION "Not supported."

        VARIATION       caqAggPolicerERExceedPackets 
            ACCESS      not-implemented
            DESCRIPTION "Not supported."

        VARIATION       caqSecurityAction 
            SYNTAX      INTEGER { permit(1), deny(2), redirect(3) } 
            DESCRIPTION "Only limited set of enumerated values
                         are supported."

        VARIATION       caqClassifierMapDirection 
            SYNTAX      BITS { ingress(0) } 
            DESCRIPTION "Only limited set of enumerated values
                         are supported."

        VARIATION       caqIpAceProtocolMatchCriteria
            SYNTAX      INTEGER { 
                             none(1),
                             matchIgmpType(2),
                             matchIcmpType(3),
                             matchIcmpTypeAndCode(4),
                             matchEstablished(5),
                             matchEapoudp(7),
                             matchUrlRedirect(8)
                        } 
            DESCRIPTION "Only limited set of enumerated values
                         are supported. When caqIpAceFeature has
                         the value of 'qos', the supported values
                         have the additional limitation that
                         'matchEapoudp' and 'matchUrlRedirect' are
                         not supported."

    ::= { ciscoCatOSAclQosCapability 20 }

caqCapabilityV08R0701Cat6KPfc2 AGENT-CAPABILITIES
    PRODUCT-RELEASE     "Cisco CatOS 8.7(1) on Catalyst 6000/6500
                         and Cisco 7600 series devices with PFC2
                         card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqIpxAceGroup,
                          caqMacAceGroup,
                          caqActionGroup,
                          caqPolicingGroup,
                          caqQosExcessRateGroup,
                          caqQosMappingGroup,
                          caqQueueAssignmentGroup,
                          caqQueueGroup,
                          caqQosBridgedFlowPolicerGroup,
                          caqQosStatsGroup,
                          caqSecurityGroup, 
                          caqFlowPolicingCpbGroup,
                          caqQosStatsGroup2,
                          caqSecurityPBFGroup,
                          caqQosExcessBurstGroup,
                          caqIfTrustDeviceGroup,
                          caqLoggingGroup,
                          caqArpInspGroup,
                          caqSecurityRateLimitGroup,
                          caqQosDefaultActionGroup,
                          caqIfAclConfigGroup2,
                          caqIpAceExtGroup,
                          caqAclHitCountGroup,
                          caqAclFeatureGroup,
                          caqVlanAclHitCountGroup,
                          caqQosL3StatsRateGroup,
                          caqQosL3StatsPeakGroup,
                          caqAggPolicerPacketsRateGroup,
                          caqAggPolicerPacketsPeakGroup,
                          caqQosPortRateGroup,
                          caqQosPortPeakGroup,
                          caqSecurityActionDnldAceGroup,
                          caqIpOperClassifierGroup,
                          caqDownloadClassifierGroup,
                          caqArpLoggingSourceGroup
                        }
        VARIATION       caqClassifierMapDirection 
            SYNTAX      BITS { ingress(0) }
            DESCRIPTION "Only limited set of enumerated values
                         are supported."

        VARIATION       caqAclFeatureCpb 
            SYNTAX      BITS { vlanAclHitCount(0) }
            DESCRIPTION "Only limited set of enumerated values
                         are supported."

        VARIATION       caqSecurityAction 
            SYNTAX      INTEGER { 
                             permit(1), 
                             deny(2), 
                             redirect(3),
                             redirectWithAdj(4),
                             denyWithLog(5),
                             denyArpInspection(6),
                             denyArpInspWithLog(7),
                             permitArpInspection(8)
                         } 
            DESCRIPTION "Only limited set of enumerated values
                         are supported."

        VARIATION       caqIpAceProtocolMatchCriteria
            SYNTAX      INTEGER { 
                             none(1),
                             matchIgmpType(2),
                             matchIcmpType(3),
                             matchIcmpTypeAndCode(4),
                             matchEstablished(5),
                             matchEapoudp(7),
                             matchUrlRedirect(8)
                        } 
            DESCRIPTION "Only limited set of enumerated values
                         are supported. When caqIpAceFeature has
                         the value of 'qos', the supported values
                         have the additional limitation that
                         'matchEapoudp' and 'matchUrlRedirect' are
                         not supported."
    ::= { ciscoCatOSAclQosCapability 21 }

caqCapabilityV08R0701Cat6KPfc3 AGENT-CAPABILITIES
    PRODUCT-RELEASE     "Cisco CatOS 8.7(1) on Catalyst 6000/6500
                         and Cisco 7600 series devices with PFC3
                         card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqMacAceGroup,
                          caqActionGroup,
                          caqPolicingGroup,
                          caqQosExcessRateGroup,
                          caqQosMappingGroup,
                          caqQueueAssignmentGroup,
                          caqQueueGroup,
                          caqQosBridgedFlowPolicerGroup,
                          caqQosStatsGroup,
                          caqSecurityGroup, 
                          caqFlowPolicingCpbGroup,
                          caqSecurityPBFGroup,
                          caqQosExcessBurstGroup,
                          caqIfTrustDeviceGroup,
                          caqLoggingGroup,
                          caqArpInspGroup,
                          caqSecurityRateLimitGroup,
                          caqDscpMutationGroup,
                          caqQosDefaultActionGroup,
                          caqIfAclConfigGroup2,
                          caqDscpRewriteGroup,
                          caqAggPolicerOctetStatsGroup,
                          caqIpAceExtGroup,
                          caqIfSecurityAclConfigGroup,
                          caqAclHitCountGroup,
                          caqAclFeatureGroup,
                          caqPortAclHitCountGroup,
                          caqVlanAclHitCountGroup,
                          caqQosL3StatsRateGroup,
                          caqQosL3StatsPeakGroup,
                          caqAggPolicerOctetsRateGroup,
                          caqAggPolicerOctetsPeakGroup,
                          caqQosPortRateGroup,
                          caqQosPortPeakGroup,
                          caqSecurityActionDnldAceGroup,
                          caqDownloadClassifierGroup,
                          caqIpOperClassifierGroup,
                          caqSecurityDownloadAclInfoGroup,
                          caqSecurityDownloadIpAceGroup,
                          caqIfDownloadAclMapGroup,
                          caqIfIpPhoneMapGroup,
                          caqArpLoggingSourceGroup,
                          caqIpAceTypeGroup
                        }

        VARIATION       caqAclHitCountAclType 
            SYNTAX      INTEGER { ipSecurity(1), macSecurity(3) }
            DESCRIPTION "Only limited set of enumerated values
                         are supported."

        VARIATION       caqAceHitCountAclType 
            SYNTAX      INTEGER { ipSecurity(1), macSecurity(3) }
            DESCRIPTION "Only limited set of enumerated values
                         are supported."

        VARIATION       caqIfAclHitCountAclType 
            SYNTAX      INTEGER { ipSecurity(1), macSecurity(3) }
            DESCRIPTION "Only limited set of enumerated values
                         are supported."

        VARIATION       caqIpAceProtocolMatchCriteria
            SYNTAX      INTEGER { 
                             none(1),
                             matchIgmpType(2),
                             matchIcmpType(3),
                             matchIcmpTypeAndCode(4),
                             matchEstablished(5),
                             matchEapoudp(7),
                             matchUrlRedirect(8)
                        } 
            DESCRIPTION "Only limited set of enumerated values
                         are supported. When caqIpAceFeature has
                         the value of 'qos', the supported values
                         have the additional limitation that
                         'matchEapoudp' and 'matchUrlRedirect' are
                         not supported."
    ::= { ciscoCatOSAclQosCapability 22 }

caqCapabilityV08R0701Cat6KPfc3b AGENT-CAPABILITIES
    PRODUCT-RELEASE     "Cisco CatOS 8.7(1) on Catalyst 6000/6500
                         and Cisco 7600 series devices with PFC3B
                         or PFC3BXL card."
    STATUS              current
    DESCRIPTION         "CISCO-CATOS-ACL-QOS-MIB agent capabilities."

    SUPPORTS            CISCO-CATOS-ACL-QOS-MIB
        INCLUDES        { caqIfConfigGroup,
                          caqIfAclConfigGroup,
                          caqAclCpbGroup,
                          caqIpAceGroup,
                          caqMacAceGroup,
                          caqActionGroup,
                          caqPolicingGroup,
                          caqQosExcessRateGroup,
                          caqQosMappingGroup,
                          caqQueueAssignmentGroup,
                          caqQueueGroup,
                          caqQosBridgedFlowPolicerGroup,
                          caqQosStatsGroup,
                          caqSecurityGroup, 
                          caqFlowPolicingCpbGroup,
                          caqSecurityPBFGroup,
                          caqQosExcessBurstGroup,
                          caqIfTrustDeviceGroup,
                          caqLoggingGroup,
                          caqArpInspGroup,
                          caqSecurityRateLimitGroup,
                          caqDscpMutationGroup,
                          caqQosDefaultActionGroup,
                          caqIfAclConfigGroup2,
                          caqDscpRewriteGroup,
                          caqAggPolicerOctetStatsGroup,
                          caqIpAceExtGroup,
                          caqIfSecurityAclConfigGroup,
                          caqAclHitCountGroup,
                          caqMacAceExtGroup,
                          caqMacPktClassifyVlanGroup,
                          caqAclFeatureGroup,
                          caqPortAclHitCountGroup,
                          caqVlanAclHitCountGroup,
                          caqQosL3StatsRateGroup,
                          caqQosL3StatsPeakGroup,
                          caqAggPolicerOctetsRateGroup,
                          caqAggPolicerOctetsPeakGroup,
                          caqQosPortRateGroup,
                          caqQosPortPeakGroup,
                          caqSecurityActionDnldAceGroup,
                          caqDownloadClassifierGroup,
                          caqIpOperClassifierGroup,
                          caqSecurityDownloadAclInfoGroup,
                          caqSecurityDownloadIpAceGroup,
                          caqIfDownloadAclMapGroup,
                          caqIfIpPhoneMapGroup,
                          caqArpLoggingSourceGroup,
                          caqIpAceTypeGroup
                        }

        VARIATION       caqAclHitCountAclType 
            SYNTAX      INTEGER { ipSecurity(1), macSecurity(3) }
            DESCRIPTION "Only limited set of enumerated values
                         are supported."

        VARIATION       caqAceHitCountAclType 
            SYNTAX      INTEGER { ipSecurity(1), macSecurity(3) }
            DESCRIPTION "Only limited set of enumerated values
                         are supported."

        VARIATION       caqIfAclHitCountAclType 
            SYNTAX      INTEGER { ipSecurity(1), macSecurity(3) }
            DESCRIPTION "Only limited set of enumerated values
                         are supported."

        VARIATION       caqIpAceProtocolMatchCriteria
            SYNTAX      INTEGER { 
                             none(1),
                             matchIgmpType(2),
                             matchIcmpType(3),
                             matchIcmpTypeAndCode(4),
                             matchEstablished(5),
                             matchEapoudp(7),
                             matchUrlRedirect(8)
                        } 
            DESCRIPTION "Only limited set of enumerated values
                         are supported. When caqIpAceFeature has
                         the value of 'qos', the supported values
                         have the additional limitation that
                         'matchEapoudp' and 'matchUrlRedirect' are
                         not supported."
    ::= { ciscoCatOSAclQosCapability 23 }

END
