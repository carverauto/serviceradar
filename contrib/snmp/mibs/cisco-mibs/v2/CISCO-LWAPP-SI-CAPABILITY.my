-- *******************************************************************
-- CISCO-LWAPP-SI MIB CAPABILITY
--
-- November 18, 2020
--
-- Copyright (c) 2020, 2022 by Cisco Systems, Inc.
-- All rights reserved.
-- *******************************************************************

CISCO-LWAPP-SI-CAPABILITY DEFINITIONS ::= BEGIN


IMPORTS
       MODULE-IDENTITY
           FROM SNMPv2-SMI
       AGENT-CAPABILITIES
           FROM SNMPv2-CONF
       ciscoAgentCapability
           FROM CISCO-SMI;


ciscoLwappSiCapability  MODULE-IDENTITY

       LAST-UPDATED         "202011180000Z"
       ORGANIZATION         "Cisco Systems, Inc."
       CONTACT-INFO
               "Cisco Systems
               Customer Service

               Postal: 170 W Tasman Drive
               San Jose, CA  95134
               USA

               Tel: +1 800 553-NETS

               E-mail: cs-wnbu-snmp@cisco.com"

       DESCRIPTION
               "Agent capabilities for
               CISCO-LWAPP-SI-MIB "
       REVISION      "202011180000Z"
       DESCRIPTION
               "Initial version of this MIB module. "

   ::= { ciscoAgentCapability 1160 }

ciscoLwappSiCapabilityCEV1R0 AGENT-CAPABILITIES

       PRODUCT-RELEASE "Cisco EWLC 1.0"
       STATUS          current
       DESCRIPTION     "CISCO-LWAPP-SI--MIB capabilities."

       SUPPORTS        CISCO-LWAPP-SI-MIB
       INCLUDES        {
                           cLSiDot11BandTable,
                           cLSiIdrTable,
                           cLSiPersistentDeviceTable,
                           cLSiPersistentDeviceChanTable,
                           cLSiAqInterferenceClassReportTable,
                           cLSiIdrClusterTable,
                           cLSiAqTable
                       }

       VARIATION       cLSiD11IdrPersistentDevicePropagation
       ACCESS          not-implemented
       DESCRIPTION     "Not supported"

       VARIATION       cLSiIdrEntry
       ACCESS          not-implemented
       DESCRIPTION     "Not supported"

       VARIATION       cLSiIdrTimeStamp
       ACCESS          not-implemented
       DESCRIPTION     "Not supported"

       VARIATION       cLSiIdrDetectingApMac
       ACCESS          not-implemented
       DESCRIPTION     "Not supported"

       VARIATION       cLSiIdrDutyCycle
       ACCESS          not-implemented
       DESCRIPTION     "Not supported"

       VARIATION       cLSiIdrAntennaId
       ACCESS          not-implemented
       DESCRIPTION     "Not supported"

       VARIATION       cLSiIdrRssi
       ACCESS          not-implemented
       DESCRIPTION     "Not supported"

       VARIATION       cLSiIdrRadioBandId
       ACCESS          not-implemented
       DESCRIPTION     "Not supported"

       VARIATION       cLSiIdrDeviceSignatureLen
       ACCESS          not-implemented
       DESCRIPTION     "Not supported"

       VARIATION       cLSiIdrDeviceSignature
       ACCESS          not-implemented
       DESCRIPTION     "Not supported"

       VARIATION       cLSiPersistentDeviceEntry
       ACCESS          not-implemented
       DESCRIPTION     "Not supported"

       VARIATION       cLSiPersistentDeviceId
       ACCESS          not-implemented
       DESCRIPTION     "Not supported"

       VARIATION       cLSiPersistentDeviceType
       ACCESS          not-implemented
       DESCRIPTION     "Not supported"

       VARIATION       cLSiPersistentTimeStamp
       ACCESS          not-implemented
       DESCRIPTION     "Not supported"

       VARIATION       cLSiPersistentDeviceChanEntry
       ACCESS          not-implemented
       DESCRIPTION     "Not supported"

       VARIATION       cLSiPersistentDeviceChanIndex
       ACCESS          not-implemented
       DESCRIPTION     "Not supported"

       VARIATION       cLSiChannelAffected
       ACCESS          not-implemented
       DESCRIPTION     "Not supported"

       VARIATION       cLSiChannelUtil
       ACCESS          not-implemented
       DESCRIPTION     "Not supported"

       VARIATION       cLSiChannelRSSI
       ACCESS          not-implemented
       DESCRIPTION     "Not supported"

       VARIATION       cLSiChannelPropagationFlag
       ACCESS          not-implemented
       DESCRIPTION     "Not supported"

       VARIATION       cLSiAqInterferenceClassReportEntry
       ACCESS          not-implemented
       DESCRIPTION     "Not supported"

       VARIATION       cLSiAqInterferenceClassReportIndex
       ACCESS          not-implemented
       DESCRIPTION     "Not supported"

       VARIATION       cLSiAqInterferenceClassReportClass
       ACCESS          not-implemented
       DESCRIPTION     "Not supported"

       VARIATION       cLSiAqInterferenceClassReportSeverityIndex
       ACCESS          not-implemented
       DESCRIPTION     "Not supported"

       VARIATION       cLSiAqInterferenceClassReportPower
       ACCESS          not-implemented
       DESCRIPTION     "Not supported"

       VARIATION       cLSiAqInterferenceClassReportDutyCycle
       ACCESS          not-implemented
       DESCRIPTION     "Not supported"

       VARIATION       cLSiAqInterferenceClassReportDeviceCount
       ACCESS          not-implemented
       DESCRIPTION     "Not supported"

       VARIATION       cLSiIdrClusterEntry
       ACCESS          not-implemented
       DESCRIPTION     "Not supported"

       VARIATION       cLSiIdrClusterRadioBandId
       ACCESS          not-implemented
       DESCRIPTION     "Not supported"

       VARIATION       cLSiIdrClusterClusterId
       ACCESS          not-implemented
       DESCRIPTION     "Not supported"

       VARIATION       cLSiIdrClusterDeviceIndex
       ACCESS          not-implemented
       DESCRIPTION     "Not supported"

       VARIATION       cLSiIdrClusterDeviceId
       ACCESS          not-implemented
       DESCRIPTION     "Not supported"

       VARIATION       cLSiIdrClusterTimeStamp
       ACCESS          not-implemented
       DESCRIPTION     "Not supported"

       VARIATION       cLSiIdrClusterDeviceType
       ACCESS          not-implemented
       DESCRIPTION     "Not supported"

       VARIATION       cLSiIdrClusterSeverity
       ACCESS          not-implemented
       DESCRIPTION     "Not supported"

       VARIATION       cLSiIdrClusterDetectingApMac
       ACCESS          not-implemented
       DESCRIPTION     "Not supported"

       VARIATION       cLSiIdrClusterDutyCycle
       ACCESS          not-implemented
       DESCRIPTION     "Not supported"

       VARIATION       cLSiIdrClusterAntennaId
       ACCESS          not-implemented
       DESCRIPTION     "Not supported"

       VARIATION       cLSiIdrClusterRssi
       ACCESS          not-implemented
       DESCRIPTION     "Not supported"

       VARIATION       cLSiIdrClusterAffectedChannels
       ACCESS          not-implemented
       DESCRIPTION     "Not supported"

       VARIATION       cLSiIdrClusterDeviceSignatureLen
       ACCESS          not-implemented
       DESCRIPTION     "Not supported"

       VARIATION       cLSiIdrClusterDeviceSignature
       ACCESS          not-implemented
       DESCRIPTION     "Not supported"

       VARIATION       cLSiIdrClusterCenterIndex
       ACCESS          not-implemented
       DESCRIPTION     "Not supported"

       VARIATION       cLSiIdrClusterType
       ACCESS          not-implemented
       DESCRIPTION     "Not supported"

       VARIATION       cLSiAqEntry
       ACCESS          not-implemented
       DESCRIPTION     "Not supported"

       VARIATION       cLSiAqMinIndex
       ACCESS          not-implemented
       DESCRIPTION     "Not supported"

       VARIATION       cLSiAqTotalChannelPower
       ACCESS          not-implemented
       DESCRIPTION     "Not supported"

       VARIATION       cLSiAqTotalChannelDutyCycle
       ACCESS          not-implemented
       DESCRIPTION     "Not supported"

       VARIATION       cLSiAqInterferencePower
       ACCESS          not-implemented
       DESCRIPTION     "Not supported"

       VARIATION       cLSiAqInterferenceDutyCycle
       ACCESS          not-implemented
       DESCRIPTION     "Not supported"

       VARIATION       cLSiAqInterferenceDeviceCount
       ACCESS          not-implemented
       DESCRIPTION     "Not supported"

       VARIATION       cLSiAqInterfererClassReportCount
       ACCESS          not-implemented
       DESCRIPTION     "Not supported"

       VARIATION       cLSiAqTimeStamp
       ACCESS          not-implemented
       DESCRIPTION     "Not supported"

   ::= { ciscoLwappSiCapability 1 }

END
