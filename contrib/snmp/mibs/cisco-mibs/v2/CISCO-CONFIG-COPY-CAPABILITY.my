-- *****************************************************************
-- CISCO-CONFIG-COPY-CAPABILITY.my:  
-- CISCO-CONFIG-COPY-MIB AGENT-CAPABILITIES
--
-- October 1999, Vinod B C
-- April 2002, Subra Hegde
--
-- Copyright (c) 1999, 2002, 2004-2006 by Cisco Systems, Inc.
-- All rights reserved.
-- 
-- *****************************************************************
--

CISCO-CONFIG-COPY-CAPABILITY DEFINITIONS ::= BEGIN

IMPORTS
        MODULE-IDENTITY
                FROM SNMPv2-SMI
        TruthValue, DisplayString
                FROM SNMPv2-TC
        AGENT-CAPABILITIES
                FROM SNMPv2-CONF
        ciscoAgentCapability
                FROM CISCO-SMI
        ConfigCopyProtocol, ConfigFileType, 
        ConfigCopyFailCause, ConfigCopyState
                FROM CISCO-CONFIG-COPY-MIB;

ciscoConfigCopyCapability MODULE-IDENTITY
        LAST-UPDATED    "200602080000Z"
        ORGANIZATION    "Cisco Systems, Inc."
        CONTACT-INFO
                "       Cisco Systems
                        Customer Service

                Postal: 170 West Tasman Drive
                        San Jose, CA  95134
                        USA

                   Tel: +1 800 553-NETS

                E-mail: cs-snmp@cisco.com
                        cs-lan-switch-snmp@cisco.com"
        DESCRIPTION
                "This is the Agent Capabilities for
                 CISCO-CONFIG-COPY-MIB."

        REVISION        "200602080000Z"
        DESCRIPTION
                "Added Agent Capability statement
                 ciscoConfigCopyCapIOSXRV2R0CRS1."
        REVISION        "200505240000Z" 
        DESCRIPTION
                "Added capability statement 
                 ciscoConfigCopyCapMDS3R0."
        REVISION        "200406080000Z" 
        DESCRIPTION
                "Added capability statement 
                 ciscoConfigCopyCapCatOSV08R0401."
        REVISION        "200403170000Z" 
        DESCRIPTION
                "Adding new varbind for ccCopyCompletion 
                 Notification."
        REVISION        "200204290000Z"
        DESCRIPTION
                "Added ciscoConfigCopyCapabilityV2R0175
                 for RPM-PR module in MGX8850."
        REVISION        "200009060000Z"
        DESCRIPTION
                "Added VARIATION clauses to 
                 ccCopySourceFileType and ccCopyDestFileType."
        REVISION        "9910070000Z"
        DESCRIPTION
                "Initial version of this MIB module."
        ::= { ciscoAgentCapability 128 }

ciscoConfigCopyCapabilityV12R00 AGENT-CAPABILITIES
    PRODUCT-RELEASE     "Cisco IOS 12.0"
    STATUS              current
    DESCRIPTION         "CONFIG-COPY MIB capabilities"

    SUPPORTS            CISCO-CONFIG-COPY-MIB
        INCLUDES        { ccCopyGroup }

        VARIATION       ccCopyProtocol
            SYNTAX      INTEGER { tftp(1) }
            DESCRIPTION "ftp(2) and rcp(3) are not available"

        ::= { ciscoConfigCopyCapability 1 }

ciscoConfigCopyCapabilityV12R01 AGENT-CAPABILITIES
    PRODUCT-RELEASE     "Cisco IOS 12.1"
    STATUS              current
    DESCRIPTION         "CONFIG-COPY MIB capabilities"

    SUPPORTS            CISCO-CONFIG-COPY-MIB
        INCLUDES        { ccCopyGroup }

        VARIATION       ccCopyProtocol
            SYNTAX      INTEGER { tftp(1) }
            -- no       { ftp(2) and rcp(3) }
            DESCRIPTION "ftp(2) and rcp(3) are not available"

        VARIATION       ccCopySourceFileType
            SYNTAX      INTEGER { 
                            networkFile(1), 
                            startupConfig(3), 
                            runningConfig(4) 
                        }
            -- no       { iosFile(2) and terminal(5) }
            DESCRIPTION "iosFile(2) and terminal(5) not supported."

        VARIATION       ccCopyDestFileType
            SYNTAX      INTEGER {
                            networkFile(1), 
                            startupConfig(3), 
                            runningConfig(4) 
                        }
            -- no       { iosFile(2) and terminal(5) }
            DESCRIPTION "iosFile(2) and terminal(5) not supported."

        ::= { ciscoConfigCopyCapability 2 }

ciscoConfigCopyCapabilityV2R0175 AGENT-CAPABILITIES
    PRODUCT-RELEASE     "MGX8850 Release 2.1.75"
    STATUS              current
    DESCRIPTION         "CISCO-CONFIG-COPY-MIB Capabilities
                         for RPM-PR(Router Module)."

    SUPPORTS CISCO-CONFIG-COPY-MIB
        INCLUDES { ccCopyGroup }

        VARIATION       ccCopyProtocol
            ACCESS      not-implemented
            DESCRIPTION "Not supported."

        VARIATION       ccCopySourceFileType
            SYNTAX      INTEGER { runningConfig(4) }
            DESCRIPTION "Values networkFile(1), iosFile(2),
                         startupConfig(3), terminal(5) are 
                         not supported."

        VARIATION       ccCopyDestFileType
            SYNTAX      INTEGER { startupConfig(3) }
            DESCRIPTION "Values networkFile(1), iosFile(2),
                         runningConfig(4), terminal(5) are 
                         not supported."

        VARIATION       ccCopyServerAddress
            ACCESS      not-implemented
            DESCRIPTION "Not supported."

        VARIATION       ccCopyFileName
            ACCESS      not-implemented
            DESCRIPTION "Not supported."

        VARIATION       ccCopyUserName
            ACCESS      not-implemented
            DESCRIPTION "Not supported."

        VARIATION       ccCopyUserPassword
            ACCESS      not-implemented
            DESCRIPTION "Not supported."

        VARIATION       ccCopyNotificationOnCompletion
            ACCESS      not-implemented
            DESCRIPTION "Not supported."

        VARIATION       ccCopyEntryRowStatus
            SYNTAX      INTEGER {
                            active(1),
                            createAndGo(4),
                            destroy(6)
                        }
            DESCRIPTION "The Values notInService(2), notReady(3),
                         createAndWait(5) are not supported.
                         Value active(1) is Read-Only."

    ::= { ciscoConfigCopyCapability 3 }

ciscoConfigCopyCapabilityV12R30S AGENT-CAPABILITIES
    PRODUCT-RELEASE     "Cisco IOS 12.30S"
    STATUS              current
    DESCRIPTION         "CONFIG-COPY MIB capabilities"

    SUPPORTS            CISCO-CONFIG-COPY-MIB
        INCLUDES        { ccCopyGroupRev1,
                          ccCopyNotificationsGroup 
                        }

        VARIATION       ccCopyProtocol
            SYNTAX      INTEGER { tftp(1) }
            DESCRIPTION "ftp(2) and rcp(3) are not available"

        VARIATION       ccCopyCompletion      -- NOTIFICATION-TYPE
            -- OBJECTS  { ccCopyServerAddressRev1 }
            DESCRIPTION "ccCopyServerAddress will contain the address of
                         the server for IPv4 transport type. For other 
                         transport type it will contain 0.0.0.0. And 
                         ccCopyServerAddressRev1 will contain the 
                         address of the server even for other 
                         defined transport type."

     ::= { ciscoConfigCopyCapability 4 }

ciscoConfigCopyCapCatOSV08R0401 AGENT-CAPABILITIES
    PRODUCT-RELEASE     "Cisco CatOS 8.4(1)."
    STATUS               current
    DESCRIPTION         "CISCO-CONFIG-COPY-MIB capabilities."

    SUPPORTS            CISCO-CONFIG-COPY-MIB
        INCLUDES        { ccCopyGroup }

        VARIATION       ccCopyProtocol
            SYNTAX      INTEGER {
                            tftp(1), 
                            ftp(2), 
                            rcp(3)
                        }
            DESCRIPTION "Only limited set of enumerated values
                         are supported."

        VARIATION       ccCopySourceFileType
            SYNTAX      INTEGER {
                            networkFile(1), 
                            iosFile(2), 
                            runningConfig(4)
                        }
            DESCRIPTION "Only limited set of enumerated values
                         are supported."

        VARIATION       ccCopyDestFileType
            SYNTAX      INTEGER {
                            networkFile(1), 
                            iosFile(2), 
                            runningConfig(4)
                        }
            DESCRIPTION "Only limited set of enumerated values
                         are supported."

        VARIATION       ccCopyFileName
            SYNTAX      DisplayString(SIZE (1..98))
            DESCRIPTION "The length of the value for an instance of 
                         ccCopyFileName ranges from 1 through 98 
                         when the value of either instance of 
                         ccCopySourceFileType and ccCopyDestFileType 
                         is 'iosFile', and from 1 through 63 when 
                         either of them is 'networkFile'."

        VARIATION       ccCopyNotificationOnCompletion
            SYNTAX      INTEGER { false(2) }
            DESCRIPTION "'true' is not supported."

        VARIATION       ccCopyState
            SYNTAX      INTEGER { 
                            waiting(1),
                            running(2),
                            successful(3),
                            failed(4)
                        }
            DESCRIPTION "The enumerated values supported are all those
                         defined at the time this clause was written."

        VARIATION       ccCopyFailCause
            SYNTAX      INTEGER { 
                            unknown(1), 
                            badFileName(2), 
                            timeout(3), 
                            noMem(4), 
                            noConfig(5)
                        }    
            DESCRIPTION "Only limited set of enumerated values
                         are supported."

         ::= { ciscoConfigCopyCapability 5 }

ciscoConfigCopyCapMDS3R0 AGENT-CAPABILITIES
    PRODUCT-RELEASE     "Cisco MDS 3.0(1)."
    STATUS               current
    DESCRIPTION         "CISCO-CONFIG-COPY-MIB capabilities."

    SUPPORTS            CISCO-CONFIG-COPY-MIB
        INCLUDES        { ccCopyGroupRev1 }

        VARIATION       ccCopySourceFileType
            SYNTAX      INTEGER {
                            networkFile(1),
                            startupConfig(3),
                            runningConfig(4),
                            fabricStartupConfig(6)
                        }
            DESCRIPTION "Only limited set of enumerated values
                         are supported."

        VARIATION       ccCopyDestFileType
            SYNTAX      INTEGER {
                            networkFile(1),
                            startupConfig(3),
                            runningConfig(4),
                            fabricStartupConfig(6) 
                        }
            DESCRIPTION "Only limited set of enumerated values
                         are supported."
         
         ::= { ciscoConfigCopyCapability 6 }

ciscoConfigCopyCapIOSXRV2R0CRS1 AGENT-CAPABILITIES
        PRODUCT-RELEASE "Cisco IOS XR 2.0 for CRS-1"
        STATUS          current
        DESCRIPTION     "CISCO-CONFIG-COPY-MIB Capabilities
                         for IOS XR release 2.0"

        SUPPORTS        CISCO-CONFIG-COPY-MIB
        INCLUDES        { ccCopyGroup }

        VARIATION       ccCopyProtocol
        SYNTAX          INTEGER {
                            tftp(1),
                            ftp(2)
                        }
        DESCRIPTION     "Current MIB Implementaion doesn't
                         support rcp(3)."

        VARIATION       ccCopySourceFileType
        SYNTAX          INTEGER {
                            networkFile(1),
                            iosFile(2),
                            runningConfig(4)
                        }
        DESCRIPTION     "Current MIB Implementaion doesn't
                         support startupConfig(3) and terminal(5)."

        VARIATION       ccCopyDestFileType
        SYNTAX          INTEGER {                
                            networkFile(1),
                            iosFile(2),
                            runningConfig(4)
                        }
        DESCRIPTION     "Current MIB Implementaion doesn't
                         support startupConfig(3) and terminal(5)."

        ::= { ciscoConfigCopyCapability 7 }
END
