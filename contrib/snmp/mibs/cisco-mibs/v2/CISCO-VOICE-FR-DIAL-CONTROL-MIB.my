-- *****************************************************************
-- CISCO-VOICE-FR-DIAL-CONTROL-MIB.my: Voice FR Dial Control MIB 
--                                     file
--
-- April 1998, Steve Yang
--
-- Copyright (c) 1998 by cisco Systems, Inc.
-- All rights reserved.
-- *****************************************************************

CISCO-VOICE-FR-DIAL-CONTROL-MIB DEFINITIONS ::= BEGIN

IMPORTS
        MODULE-IDENTITY,
        OBJECT-TYPE
                FROM SNMPv2-SMI
        DisplayString
                FROM SNMPv2-TC
        MODULE-COMPLIANCE,
        OBJECT-GROUP
                FROM SNMPv2-CONF
        CvcGUid
                FROM  CISCO-VOICE-DIAL-CONTROL-MIB
        cCallHistoryIndex
                FROM CISCO-DIAL-CONTROL-MIB
        ciscoExperiment 
                FROM CISCO-SMI;
 
ciscoVoiceFrDialControlMIB MODULE-IDENTITY
        LAST-UPDATED    "9804140000Z"
        ORGANIZATION    "Cisco Systems, Inc."
        CONTACT-INFO
                "       Cisco Systems
                        Customer Service

                Postal: 170 W. Tasman Drive
                        San Jose, CA  95134
                        USA
 
                Tel: +1 800 553-NETS
 
                E-mail: cs-voice@cisco.com"
        DESCRIPTION
                "This MIB module enhances the IETF Dial Control MIB (RFC2128)
                 by providing FR management information over a data network.
                "
        ::= { ciscoExperiment 36 }

-- Voice FR Dial Control MIB objects definitions

cvfrdcMIBObjects OBJECT IDENTIFIER ::= { ciscoVoiceFrDialControlMIB 1 }

-- The Voice Dial Control MIB consists of the following group
-- [1] Voice FR Dial Control Call History Group (cvFrCallHistory)

cvFrCallHistory        OBJECT IDENTIFIER ::= { cvfrdcMIBObjects 1 }


--****************************************************************************
-- Voice over FR Dial Control Call History Group
--****************************************************************************

--
-- Voice over FR Call History Table
-- 

cvFrCallHistoryTable OBJECT-TYPE
        SYNTAX      SEQUENCE OF CvFrCallHistoryEntry
        MAX-ACCESS  not-accessible
        STATUS      current
        DESCRIPTION
            "This table is the FR extension to the call history table of
             IETF Dial Control MIB. It contains FR call leg information
             about specific voice over FR call.
            "
        ::= { cvFrCallHistory 1 }

cvFrCallHistoryEntry OBJECT-TYPE
        SYNTAX      CvFrCallHistoryEntry
        MAX-ACCESS  not-accessible
        STATUS      current
        DESCRIPTION
            "The information regarding a single FR call leg.
             An entry of this table is created when its associated call
             history entry in the IETF Dial Control MIB is created and the
             call history entry contains information for the call
             establishment to the peer on the data network backbone via a 
             voice over FR peer.
             The entry is deleted when its associated call history entry in
             the IETF Dial Control MIB is deleted.
            "
        INDEX       { cCallHistoryIndex }
        ::= { cvFrCallHistoryTable 1 }


CvFrCallHistoryEntry ::=
        SEQUENCE {
            cvFrCallHistoryConnectionId             CvcGUid,
            cvFrCallHistoryDlci                     INTEGER,
            cvFrCallHistoryLowerIfName              DisplayString,
            cvFrCallHistorySessionTarget            DisplayString
        }

cvFrCallHistoryConnectionId OBJECT-TYPE
        SYNTAX      CvcGUid 
        MAX-ACCESS  read-only
        STATUS      current
        DESCRIPTION
            "The global call identifier for the tandem call."
        ::= { cvFrCallHistoryEntry 1 }

cvFrCallHistoryDlci OBJECT-TYPE
    SYNTAX      INTEGER (0..65535) 
    MAX-ACCESS  read-only
    STATUS      current
    DESCRIPTION
            "The Dlci used for this FR connection."
    ::= { cvFrCallHistoryEntry 2 }
 
cvFrCallHistoryLowerIfName OBJECT-TYPE
    SYNTAX      DisplayString (SIZE (0..24))
    MAX-ACCESS  read-only 
    STATUS      current
    DESCRIPTION
            "The textual name of physical interface associated 
             with this FR call."
    ::= { cvFrCallHistoryEntry 3 }

cvFrCallHistorySessionTarget OBJECT-TYPE
    SYNTAX      DisplayString 
    MAX-ACCESS  read-only
    STATUS      current
    DESCRIPTION
            "The object specifies the session target of the peer that
             is used for the voice over FR call. A null string indicates 
             that the value is unavailable."
    ::= { cvFrCallHistoryEntry 4 }

cvfrdcMIBConformance OBJECT IDENTIFIER ::=
                                { ciscoVoiceFrDialControlMIB 3 }
cvfrdcMIBCompliances OBJECT IDENTIFIER ::=
                                { cvfrdcMIBConformance 1 }
cvfrdcMIBGroups      OBJECT IDENTIFIER ::=
                                { cvfrdcMIBConformance 2 }
 
-- compliance statements

cvfrdcMIBCompliance MODULE-COMPLIANCE
        STATUS      current
        DESCRIPTION
            "The compliance statement for entities which
             implement the CISCO VOICE FR DIAL CONTROL MIB"
        MODULE      -- this module
        MANDATORY-GROUPS
            { cvFrCallHistoryGroup }
        ::= { cvfrdcMIBCompliances 1 }

-- units of conformance


cvFrCallHistoryGroup OBJECT-GROUP
        OBJECTS {
            cvFrCallHistoryConnectionId,
            cvFrCallHistoryDlci,                      
            cvFrCallHistoryLowerIfName,
            cvFrCallHistorySessionTarget            
        }
        STATUS      current
        DESCRIPTION
            "A collection of objects providing the FR Call
             capability."
        ::= { cvfrdcMIBGroups 1 }
END
