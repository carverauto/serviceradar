-- *****************************************************************
-- CISCO-MLD-SNOOPING-CAPABILITY.my
--   
-- Feb, 2010 - Salvo Valenza
--   
-- Copyright (c) 2006, 2010 by cisco Systems Inc.
-- All rights reserved.
--   
-- *****************************************************************

CISCO-MLD-SNOOPING-CAPABILITY DEFINITIONS ::= BEGIN

IMPORTS
    MODULE-IDENTITY
        FROM SNMPv2-SMI
    AGENT-CAPABILITIES
        FROM SNMPv2-CONF
    ciscoAgentCapability
        FROM CISCO-SMI;


ciscoMldSnoopingCapability MODULE-IDENTITY
    LAST-UPDATED    "201003020000Z"
    ORGANIZATION    "Cisco Systems, Inc."
    CONTACT-INFO
            "Cisco Systems
            Customer Service


            Postal: 170 W Tasman Drive

            San Jose, CA  95134

            USA


            Tel: +1 800 553-NETS


            E-mail: cs-<list>@cisco.com"
    DESCRIPTION
        "The capabilities description of CISCO-MLD-SNOOPING-MIB."
    REVISION        "201003020000Z"
    DESCRIPTION
        "Initial version of this MIB module."
    ::= { ciscoAgentCapability 586 }



ciscoMldSnoopingCapabilityV04R01 AGENT-CAPABILITIES
    PRODUCT-RELEASE "Cisco IOS-XR"
    STATUS          current
    DESCRIPTION
        "Capabilities description for CISCO-MLD-SNOOPING-MIB."

    SUPPORTS        CISCO-MLD-SNOOPING-MIB
    INCLUDES        {
                        ciscoMldSnoopingMIBConfigMainObjectGroup,
                        ciscoMldSnoopingMIBInfoMainObjectGroup,
                        ciscoMldSnoopingMIBStatsMainObjectGroup,
                        ciscoMldSnoopingMIBConfigDetailedObjectGroup,
                        ciscoMldSnoopingMIBStatsDetailedObjectGroup
                    }
    VARIATION       cmsProfileInternalQuerier
    ACCESS          read-only
    DESCRIPTION
        "The implementation does not allow setting this object through
        the MIB."

    VARIATION       cmsProfileReportSuppression
    ACCESS          read-only
    DESCRIPTION
        "The implementation does not allow setting this object through
        the MIB."

    VARIATION       cmsProfileRouterGuard
    ACCESS          read-only
    DESCRIPTION
        "The implementation does not allow setting this object through
        the MIB."

    VARIATION       cmsProfileStaticMRouter
    ACCESS          read-only
    DESCRIPTION
        "The implementation does not allow setting this object through
        the MIB."

    VARIATION       cmsProfileImmediateLeave
    ACCESS          read-only
    DESCRIPTION
        "The implementation does not allow setting this object through
        the MIB."

    VARIATION       cmsConfigPortProfileName
    ACCESS          read-only
    DESCRIPTION
        "The implementation does not allow setting this object through
        the MIB."

    ::= { ciscoMldSnoopingCapability 1 }

END
