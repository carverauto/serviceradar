-- *****************************************************************
-- CISCO-MEDIA-GATEWAY-CAPABILITY 
--
-- AGENT-CAPABILITIES MIB for CISCO-MEDIA-GATEWAY-MIB 
--
-- February 2004, Feng Luo
--
-- Copyright(c) 2004 by Cisco Systems,Inc.
--
-- *****************************************************************

CISCO-MEDIA-GATEWAY-CAPABILITY DEFINITIONS ::= BEGIN
IMPORTS
        MODULE-IDENTITY,
        Integer32, Unsigned32
                FROM SNMPv2-SMI
        AGENT-CAPABILITIES
                FROM SNMPv2-CONF
        SnmpAdminString
                FROM SNMP-FRAMEWORK-MIB
        ciscoAgentCapability
                FROM CISCO-SMI;   

ciscoMediaGatewayCapability MODULE-IDENTITY
        LAST-UPDATED    "200402050000Z"
        ORGANIZATION    "Cisco Systems, Inc."
        CONTACT-INFO
                "       Cisco Systems
                        Customer Service

                Postal: 170 W Tasman Drive
                        San Jose, CA  95134
                        USA

                        Tel: +1 800 553-NETS

                E-mail: cs-voice-gateway@cisco.com"
        DESCRIPTION
                "The agent capabilities for CISCO-MEDIA-GATEWAY-MIB."

        REVISION "200402050000Z"
        DESCRIPTION
            "Initial version of this MIB module."

        ::= { ciscoAgentCapability 375 }


cMediaGatewayCapV5R00 AGENT-CAPABILITIES

PRODUCT-RELEASE "MGX8850 Release 5.0.0"
STATUS          current
DESCRIPTION     "Agent capabilities for VXSM in Release 5.0.0."

    SUPPORTS CISCO-MEDIA-GATEWAY-MIB
    INCLUDES { 
               cMediaGwGroup,
               cmgwSignalProtocolGroup,
               cmgwDomainNameGroup,
               cMediaGwIpGroup,
               cmgwDnsIpGroup,
               cmgwLifGroup,
               cmgwCallControlGroup
             }

    VARIATION    cmgwIpConfigVpi
    SYNTAX       Integer32 (0..255)
    DESCRIPTION  "Valid values are 0 to 255"

    VARIATION    cmgwIpConfigVci
    SYNTAX       Integer32 (0..65535)
    DESCRIPTION  "Valid values are 0 to 65535"

    VARIATION    cmgwIpConfigAddrType
    SYNTAX       INTEGER { ipv4(1) }
    DESCRIPTION  "Only 'ipv4' type is supported.
                  'ipv6', 'ipv4z', 'ipv6z' and 'dns' are not supported"

    VARIATION    cmgwIpConfigAddress
    SYNTAX       OCTET STRING (SIZE(4))
    DESCRIPTION  "Only InetAddressIPv4 is supported.
                  InetAddressIPv6, InetAddressIPv4z, InetAddressIPv6z,
                  and InetAddressDNS are not supported."

    VARIATION    cmgwSignalProtocolIndex 
    SYNTAX       Integer32 (1..1)
    DESCRIPTION  "Only MGCP 1.0 protocol is supported."

    VARIATION    cmgwSignalProtocolPort 
    SYNTAX       Integer32 (1024..65535)
    DESCRIPTION  "Valid values are 1024 to 65535."

    VARIATION    cmgwDnsIpIndex 
    SYNTAX       Integer32 (1..3)
    DESCRIPTION  "3 DNS IP addresses are supported."

    VARIATION    cmgwDnsIpType
    SYNTAX       INTEGER { ipv4(1) }
    DESCRIPTION  "Only 'ipv4' type is supported.
                  'ipv6', 'ipv4z', 'ipv6z' and 'dns' are not supported"

    VARIATION    cmgwDnsIp 
    SYNTAX       OCTET STRING (SIZE(4))
    DESCRIPTION  "Only InetAddressIPv4 is supported.
                  InetAddressIPv6, InetAddressIPv4z, InetAddressIPv6z,
                  and InetAddressDNS are not supported."

    VARIATION    cmgwGraceTime
    ACCESS       not-implemented
    DESCRIPTION  "Not supported."

    VARIATION    cmgwServiceState
    ACCESS       not-implemented
    DESCRIPTION  "Not supported."

    VARIATION    cmgwAdminState
    ACCESS       not-implemented
    DESCRIPTION  "Not supported."

    VARIATION    cmgwLifNumber 
    SYNTAX       Unsigned32 (1..1)
    DESCRIPTION  "Only 1 LIF supported in the current release."
    
    VARIATION    cMediaGwCcCfgControlTos  
    DEFVAL       { 104 }
    DESCRIPTION  "Default control TOS is set to 104." 

    VARIATION    cMediaGwCcCfgBearerTos  
    DEFVAL       { 184 }
    DESCRIPTION  "Default bearer TOS is set to 184." 

    VARIATION    cMediaGwCcCfgDefaultTonePlanId 
    SYNTAX       Unsigned32 (1..200)
    DEFVAL       { 148 }
    DESCRIPTION  "200 tone plans are supported and default is 148." 
    
    VARIATION    cMediaGwCcCfgDsNamePrefix 
    SYNTAX       SnmpAdminString ( SIZE (1..18) )
    DESCRIPTION  "Supports up to 18 characters length in name
                  prefix. Only alphabets, digits, '/', or '_'
                  allowed, and first character must be alphabet."
    
    VARIATION    cMediaGwCcCfgRtpNamePrefix 
    SYNTAX       SnmpAdminString ( SIZE (1..18) )
    DESCRIPTION  "Supports up to 18 characters length in name
                  prefix. Only alphabets, digits, '/', or '_'
                  allowed, and first character must be alphabet."
    
    VARIATION    cMediaGwCcCfgAal1SvcNamePrefix 
    SYNTAX       SnmpAdminString ( SIZE (1..18) )
    DESCRIPTION  "Supports up to 18 characters length in name
                  prefix. Only alphabets, digits, '/', or '_'
                  allowed, and first character must be alphabet."
    
    VARIATION    cMediaGwCcCfgAal2SvcNamePrefix 
    SYNTAX       SnmpAdminString ( SIZE (1..18) )
    DESCRIPTION  "Supports up to 18 characters length in name
                  prefix. Only alphabets, digits, '/', or '_'
                  allowed, and first character must be alphabet."

    VARIATION    cMediaGwCcCfgVbdJitterDelayMode
    SYNTAX       INTEGER {
                         fixed (2)
                 }
    ACCESS       read-only
    DESCRIPTION  "Supports fixed(2) only and cannot be modified."

    VARIATION    cMediaGwCcCfgVbdJitterMaxDelay
    ACCESS       not-implemented
    DESCRIPTION  "Not supported."

    VARIATION    cMediaGwCcCfgVbdJitterMinDelay
    ACCESS       not-implemented
    DESCRIPTION  "Not supported."

    VARIATION    cmgwIpConfigForRemoteMapping 
    ACCESS       not-implemented      
    DESCRIPTION  "Not supported."

    VARIATION    cMediaGwCcCfgClusterEnabled 
    SYNTAX       INTEGER { 
                     disabled              (1),
                     enabled               (2)
                  }
    DESCRIPTION  "Supports disabled(1) and enabled(2).
                  Does not support conditionalEnabled(3)."
    
    ::= { ciscoMediaGatewayCapability 1 }

END
