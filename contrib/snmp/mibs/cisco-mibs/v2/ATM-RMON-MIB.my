-- *****************************************************************
-- ATM-RMON MIB
--
-- Feb 1997, Andy Bierman
--
-- Copyright (c) 1996-1997 by cisco Systems, Inc.
-- All rights reserved.
-- *****************************************************************
--
-- This mib was extracted from an ATM Forum Draft.
-- It currently uses a ciscoExperiment number.

ATM-RMON-MIB DEFINITIONS ::= BEGIN

IMPORTS
    MODULE-IDENTITY, OBJECT-TYPE, Counter32, Integer32,
    Counter64, Gauge32, TimeTicks
        FROM SNMPv2-SMI
    TEXTUAL-CONVENTION, RowStatus, DisplayString,
    TimeStamp
        FROM SNMPv2-TC
    MODULE-COMPLIANCE, OBJECT-GROUP
        FROM SNMPv2-CONF
    ifIndex, OwnerString
        FROM IF-MIB
    ciscoExperiment
	FROM CISCO-SMI;

-- This TC is not imported from the RMON MIB because that MIB is on
-- the SNMPv1-only list, not compiled with SNMPv2 SMI
-- It's imported from IF-MIB just so this MIB will compile
-- since IF-MIB must be included for ifIndex
--
-- OwnerString
--      FROM RMON-MIB
--
-- These TCs are not imported from RMON-2, because our tools
-- would not compile RMON-2 and RMON-1 together, and the Token Ring
-- RMON MIB must also be imported by RMON-2
--
--    ZeroBasedCounter32, LastCreateTime
--        FROM RMON2-MIB
--
-- This TC is not imported from the CISCO-ATM-ADDR-MIB.my, or
-- the AtomMIB WG ATM-TC-MIB. This copy will change when the
-- ATM-TC-MIB is standardized.
--
--    AtmAddr
--        FROM ATM-TC-MIB;
--

--  Remote Network Monitoring MIB for ATM Networks
atmRmon MODULE-IDENTITY
    LAST-UPDATED "9701240000Z"
    ORGANIZATION "IETF"   -- should this be Cisco instead?
    CONTACT-INFO
        "Andy Bierman
         Cisco Systems, Inc.
         Phone: +1 408 527-3711
         Email: abierman@cisco.com

         Keith McCloghrie
         Cisco Systems, Inc.
         Phone: +1 408 526-5260
         Email: kzm@cisco.com"
    DESCRIPTION
            "The MIB module for managing remote monitoring device
            implementations for ATM networks."
    ::= { ciscoExperiment 16 }

-- ATM-RMON MIB groups
atmRmonMIBObjects       OBJECT IDENTIFIER ::= { atmRmon 1 }
atmRmonNotifications    OBJECT IDENTIFIER ::= { atmRmon 2 }
atmRmonConformance      OBJECT IDENTIFIER ::= { atmRmon 3 }

-- ATM-RMON MIB object groups
portSelect         OBJECT IDENTIFIER ::= { atmRmonMIBObjects 1 }
atmStats           OBJECT IDENTIFIER ::= { atmRmonMIBObjects 2 }
atmHost            OBJECT IDENTIFIER ::= { atmRmonMIBObjects 3 }
atmMatrix          OBJECT IDENTIFIER ::= { atmRmonMIBObjects 4 }

-- cisco extensions
atmConfig          OBJECT IDENTIFIER ::= { atmRmonMIBObjects 5 }

-- Textual Conventions:

-- temp: copied from RMON-2:
      ZeroBasedCounter32 ::= TEXTUAL-CONVENTION
          STATUS current
          DESCRIPTION
              "This TC describes an object which counts events with the
              following semantics: objects of this type will be set to
              zero(0) on creation and will thereafter count appropriate
              events, wrapping back to zero(0) when the value 2^32 is
              reached.

              Provided that an application discovers the new object within
              the minimum time to wrap it can use the initial value as a
              delta since it last polled the table of which this object is
              part.  It is important for a management station to be aware of
              this minimum time and the actual time between polls, and to
              discard data if the actual time is too long or there is no
              defined minimum time.

              Typically this TC is used in tables where the INDEX space is
              constantly changing and/or the TimeFilter mechanism is in use."
          SYNTAX Gauge32

-- temp: copied from RMON-2
      LastCreateTime ::= TEXTUAL-CONVENTION
          STATUS current
          DESCRIPTION
              "This TC describes an object that stores the last time its
              entry was created.

              This can be used for polling applications to determine that an
              entry has been deleted and re-created between polls, causing
              an otherwise undetectable discontinuity in the data."
          SYNTAX TimeTicks

-- temp: copied from the ATM-TC-MIB
AtmAddr ::= TEXTUAL-CONVENTION
    STATUS  current
    DESCRIPTION
		"The ATM address used by the network entity.  The
		address types are: no address (0 octets), E.164 (8
		octets), network prefix (13 octets), and NSAP (20
		octets).  Note: The E.164 address is encoded in
		BCD format."
SYNTAX    OCTET STRING (SIZE(0|8|13|20))

ServiceClass ::= TEXTUAL-CONVENTION
    STATUS current
    DESCRIPTION
            "This TC describes an object that identifies the cell
            delivery class-of-service classification, associated with a
            particular statistics collection.  In order to conserve
            agent resources, the classifications are limited to two
            enumerations which distinguish delay-guarantee.

            Statistics gathered on behalf on collections identified by
            the 'cbrAndVbr(1)' enumeration represent constant-bit-rate
            (CBR), real-time and non-real-time variable bit rate (VBR)
            traffic.

            Statistics gathered on behalf on collections identified by
            the 'abrAndUbr(2)' enumeration represent available-bit-rate
            (ABR) and unspecified-bit-rate (UBR) traffic."
    SYNTAX INTEGER  {
        cbrAndVbr(1),     -- constant and variable bit rate
        abrAndUbr(2)      -- available and unspecified bit rate
    }

ResourcePriority ::= TEXTUAL-CONVENTION
    STATUS current
    DESCRIPTION
            "This TC describes an object which indicates the desired
            resource priority of the entire entry. Lower priorities
            indicate a lesser requirement to retain resources than
            higher priority values.

            A management station can use the resource priority to
            provide a probe with additional information for managing
            memory allocation.  A probe is strongly encouraged, but not
            required, to honor all priority requests, all of the time.

            Objects declared with this TC should be contained within a
            conceptual control table entry. The indicated resource
            priority applies to the control entry, all internal data
            structures maintained on behalf of the control entry, and
            all external MIB data represented by the control entry.

            A probe should honor the priority requests in an


            implementation-dependent way. The data allocation
            granularity (i.e., shared data structures) may vary greatly
            for different implementations, so a particular
            implementation strategy is not mandated. However, the
            following guidelines are suggested for those agents which
            implement garbage-collection based on 'least-recently used'
            (LRU) or other criteria:

            In the event that the probe runs short of resources, and
            data entries are to be removed from particular tables to
            reclaim resources, then entries associated with lower
            ResourcePriority values should be deleted before entries
            associated with higher ResourcePriority values, regardless
            of the resource reclamation algorithm in use. In addition,
            entries associated with a higher AddressCollectScope value
            should be deleted before entries with a lower
            AddressCollectScope value.

            Note that the priority ordering of entries with the same
            ResourcePriority and addressCollectScope values is
            unspecified."
    SYNTAX INTEGER  {
        lowPriority(1),
        normalPriority(2),
        highPriority(3)
    }

AddressCollectScope ::= TEXTUAL-CONVENTION
    STATUS current
    DESCRIPTION
            "This TC describes an object which indicates the granularity
            of the addresses represented in associated ATM-RMON
            collections.

            Addresses gathered on behalf of collections identified by
            the 'prefix(1)' enumeration will be cleared to zero in bytes
            13 through 20, for indexing and counting purposes.

            Addresses gathered on behalf of collections identified by
            the 'prefixAndEsi(2)' enumeration will be cleared to zero in
            byte 20, for indexing and counting purposes.

            Addresses gathered on behalf of collections identified by
            the 'entireAddr(3)' enumeration will be unmodified, for
            indexing and counting purposes."
    SYNTAX INTEGER {
         prefix(1),
         prefixAndEsi(2),
         entireAddr(3)
    }

ConnectTime ::= TEXTUAL-CONVENTION
    STATUS current
    DESCRIPTION
            "This TC describes an object which indicates the sum of the
            elapsed times of all connections associated with a
            particular collection. This is a cumulative total and
            includes all connections which currently exist and all
            connections which have been released.

            Elapsed connection time begins when the call attempt is
            detected, and ends when the call is released. It is an
            implementation-specific matter whether call attempts which
            do not result in successful connections are represented in
            this total.

            Call duration is maintained in units of seconds, and are
            rounded to the nearest second when counted."
      SYNTAX Gauge32

--
-- Port Selection (portSelect Group)
--
-- Defines the ports to be included or excluded in
-- a particular stats, host or matrix collection
--
--    portSelGrpTable
--    portSelTable

portSelGrpTable OBJECT-TYPE
    SYNTAX      SEQUENCE OF PortSelGrpEntry
    MAX-ACCESS  not-accessible
    STATUS      current
    DESCRIPTION
            "Controls the setup of port and ATM connection selection
            criteria used on behalf of any collection associated with
            entries in this table (e.g., atmHostTable).


            This table allows portSelTable entries with the same value
            of the portSelCollectGroup object to be grouped together to
            form port select groups.

            Note that an agent implementation may restrict the actual
            number of portSelGrp entries, due to resource limitations."
    ::= { portSelect 1 }

portSelGrpEntry OBJECT-TYPE
    SYNTAX      PortSelGrpEntry
    MAX-ACCESS  not-accessible
    STATUS      current
    DESCRIPTION
            "A conceptual row in the portSelGrpTable.

            An example of the indexing of this entry is
            portSelGrpCreateTime.7 ."
    INDEX { portSelGrpIndex }
    ::= { portSelGrpTable 1 }

PortSelGrpEntry ::= SEQUENCE {
    portSelGrpIndex                Integer32,
    portSelGrpDescr                DisplayString,
    portSelGrpCreateTime           LastCreateTime,
    portSelGrpOwner                OwnerString,
    portSelGrpStatus               RowStatus
}

portSelGrpIndex OBJECT-TYPE
    SYNTAX      Integer32 (1..65535)
    MAX-ACCESS  not-accessible
    STATUS      current
    DESCRIPTION
            "An arbitrary and unique index for this portSelGrpEntry.  If
            portSelGrpTable entries are recreated by the agent after a
            restart, then the portSelGrpIndex value must be retained
            across a restart as well."
    ::= { portSelGrpEntry 1 }

portSelGrpDescr  OBJECT-TYPE
    SYNTAX      DisplayString (SIZE(0..64))
    MAX-ACCESS  read-create
    STATUS      current
    DESCRIPTION
            "An administratively-assigned descriptive label for this


            portSelGrp entry."
    ::= { portSelGrpEntry 2 }

portSelGrpCreateTime OBJECT-TYPE
    SYNTAX      LastCreateTime
    MAX-ACCESS  read-only
    STATUS      current
    DESCRIPTION
            "The value of sysUpTime when this portSelGrp entry was
            activated.  This can be used by the management station to
            ensure that the table has not been deleted and recreated
            between polls."
    ::= { portSelGrpEntry 3 }

portSelGrpOwner OBJECT-TYPE
    SYNTAX      OwnerString
    MAX-ACCESS  read-create
    STATUS      current
    DESCRIPTION
            "The entity that configured this entry and is therefore
            using the resources assigned to it."
    ::= { portSelGrpEntry 4 }

portSelGrpStatus OBJECT-TYPE
    SYNTAX      RowStatus
    MAX-ACCESS  read-create
    STATUS      current
    DESCRIPTION
            "The status of this row.

            An entry may not exist in the active state unless all
            objects in the entry have an appropriate value.  No objects
            are required to be written prior to the row being set to
            active(1).  However, all portSelTable entries which are to
            be included in collections on behalf of this
            portSelectGroup, must be completely configured and activated
            before this object is set to active(1), since the associated
            instances of portSelStatus cannot be modified once this
            object has been set to active(1).

            If this object is not equal to active(1), all associated
            data collections shall be deleted (e.g., any associated
            collections in the atmStats, atmHostTable or
            atmMatrixSDTable).


            Note that associated portSelTable and any configured
            collection control entries (e.g., atmHostControlTable) are
            not deleted when this entry leaves the active state."
    ::= { portSelGrpEntry 5 }

--
-- portSelTable: used to specify the collection configuration
-- for a single ATM port
--

portSelTable OBJECT-TYPE
    SYNTAX      SEQUENCE OF PortSelEntry
    MAX-ACCESS  not-accessible
    STATUS      current
    DESCRIPTION
            "Controls the setup of selection criteria for a single ATM
            port, used on behalf of any collections identified with the
            associated portSelectGroup (identified by its
            portSelGrpIndex value).

            This table identifies the collection characteristics for the
            ATM port indicated by the ifIndex value in the index.

            Note that an agent implementation may restrict the actual
            number of portSelTable entries, due to resource
            limitations."
    ::= { portSelect 2 }

portSelEntry OBJECT-TYPE
    SYNTAX      PortSelEntry
    MAX-ACCESS  not-accessible
    STATUS      current
    DESCRIPTION
            "A conceptual row in the portSelTable.

            Entries may only be created on behalf of ATM interfaces.
            That is, the ifType value associated with each ifIndex value
            must be equal to atm(37) or atmLogicalPort(80).

            An example of the indexing of this entry is
            portSelCreateTime.7 ."
    INDEX { ifIndex }
    ::= { portSelTable 1 }


PortSelEntry ::= SEQUENCE {
    portSelCollectGroup            Integer32,
    portSelCreateTime              LastCreateTime,
    portSelOwner                   OwnerString,
    portSelStatus                  RowStatus
}

portSelCollectGroup OBJECT-TYPE
    SYNTAX      Integer32 (1..65535)
    MAX-ACCESS  read-create
    STATUS      current
    DESCRIPTION
            "This object identifies the associated instance of
            portSelGrpIndex, which indicates the portSelectGroup to
            which this port is assigned.

            This object may not be modified if the associated instance
            of portSelStatus is equal to active(1)."
    ::= { portSelEntry 1 }

portSelCreateTime OBJECT-TYPE
    SYNTAX      LastCreateTime
    MAX-ACCESS  read-only
    STATUS      current
    DESCRIPTION
            "The value of sysUpTime when this entry was activated.  This
            can be used by the management station to ensure that the
            table has not been deleted and recreated between polls."
    ::= { portSelEntry 2 }

portSelOwner OBJECT-TYPE
    SYNTAX      OwnerString
    MAX-ACCESS  read-create
    STATUS      current
    DESCRIPTION
            "The entity that configured this entry and is therefore
            using the resources assigned to it."
    ::= { portSelEntry 3 }

portSelStatus OBJECT-TYPE
    SYNTAX      RowStatus
    MAX-ACCESS  read-create
    STATUS      current
    DESCRIPTION
            "The status of this row.


            An entry may not exist in the active state unless all
            objects in the entry have an appropriate value.
            Specifically, an appropriate value for the
            portSelCollectGroup object must be set before this object
            may be set to active(1). An agent may wish to allow
            portSelTable entries to exist which reference non-existent
            portSelGrpTable entries, in order to reduce row creation
            order dependencies.

            All portSelTable entries which are to be included in a
            particular collection (as indicated by the
            portSelCollectGroup object), should be completely configured
            and activated before the associated portSelGrpStatus object
            is set to active(1).  Configuration of a portSelectGroup
            cannot be modified once collections on its behalf have been
            started.

            This object may not be modified if the associated
            portSelGroupStatus in in the active(1) state, indicated by a
            portSelGrpIndex value identical to the value of the
            portSelCollectGroup object in this entry."
    ::= { portSelEntry 4 }

--
-- ATM Stats Group
--
-- Counts the total amount of traffic
-- counted on behalf of one or more portSelectGroups

atmStatsControlTable OBJECT-TYPE
    SYNTAX      SEQUENCE OF AtmStatsControlEntry
    MAX-ACCESS  not-accessible
    STATUS      current
    DESCRIPTION
            "A list of ATM basic statistic collection table control
            entries.  These entries will enable the collection of
            statistical totals for an entire portSelectGroup."
    ::= { atmStats 1 }

atmStatsControlEntry OBJECT-TYPE
    SYNTAX      AtmStatsControlEntry
    MAX-ACCESS  not-accessible
    STATUS      current
    DESCRIPTION


            "A conceptual row in the atmStatsControlTable.  Entries in
            this table are identified and indexed by the portSelGrpIndex
            object.  At most one atmStats collection is done per
            portSelectGroup.

            An example of the indexing of this entry is
            atmStatsDropEvents.1 ."
    INDEX { portSelGrpIndex }
    ::= { atmStatsControlTable 1 }

AtmStatsControlEntry ::= SEQUENCE {
    atmStatsControlDropEvents           Counter32,
    atmStatsControlOwner                OwnerString,
    atmStatsControlStatus               RowStatus
}

atmStatsControlDropEvents OBJECT-TYPE
    SYNTAX     Counter32
    MAX-ACCESS read-only
    STATUS     current
    DESCRIPTION
            "The total number of events in which cells which should have
            been counted in the associated atmStatsEntry, but were
            dropped by the probe due to lack of resources.  Note that
            this number is not necessarily the number of cells or calls
            dropped; it is just the number of times this condition has
            been detected."
    ::= { atmStatsControlEntry 1 }

atmStatsControlOwner OBJECT-TYPE
    SYNTAX      OwnerString
    MAX-ACCESS  read-create
    STATUS      current
    DESCRIPTION
            "The entity that configured this entry and is therefore
            using the resources assigned to it."
    ::= { atmStatsControlEntry 2 }

atmStatsControlStatus OBJECT-TYPE
    SYNTAX      RowStatus
    MAX-ACCESS  read-create
    STATUS      current
    DESCRIPTION
            "The status of this atmStatsControlEntry.


            This control entry may be created and destroyed
            independently of the associated portSelGrpEntry, however its
            associated atmStatsTable can exist only when the
            portSelGrpEntry controlling this collection is active.

            If this object is not equal to active(1), all associated
            entries in the atmStatsTable shall be deleted."
    ::= { atmStatsControlEntry 3 }

-- atmStatsTable
-- call and traffic basic statistics collected on behalf of specific
-- portSelectGroups

atmStatsTable OBJECT-TYPE
    SYNTAX      SEQUENCE OF AtmStatsEntry
    MAX-ACCESS  not-accessible
    STATUS      current
    DESCRIPTION
            "A collection of statistical totals for all ATM addresses
            that have been discovered on behalf of the portSelectGroup
            associated with this entry."
    ::= { atmStats 2 }

atmStatsEntry OBJECT-TYPE
    SYNTAX      AtmStatsEntry
    MAX-ACCESS  not-accessible
    STATUS      current
    DESCRIPTION
            "A conceptual row in the atmStatsTable.

            The portSelGrpIndex value in the index identifies the
            portSelectGroup on whose behalf this entry was created.

            An example of the indexing of this entry is
            atmStatsCells.8.1"
    INDEX { portSelGrpIndex, atmStatsSClass }
    ::= { atmStatsTable 1 }

AtmStatsEntry ::= SEQUENCE {
    atmStatsSClass              ServiceClass,
    atmStatsCreateTime          LastCreateTime,
    atmStatsCells               Counter32,
    atmStatsCellsRollovers      Counter32,
    atmStatsHCCells             Counter64,


    atmStatsNumCallAttempts     Counter32,
    atmStatsNumCalls            Counter32,
    atmStatsConnTime            ConnectTime
}

atmStatsSClass OBJECT-TYPE
    SYNTAX      ServiceClass
    MAX-ACCESS  not-accessible
    STATUS      current
    DESCRIPTION
            "The quality of service classification for this entry.  See
            the ServiceClass textual convention for details and specific
            class-of-service values."
    ::= { atmStatsEntry 1 }

atmStatsCreateTime OBJECT-TYPE
    SYNTAX     LastCreateTime
    MAX-ACCESS read-only
    STATUS     current
    DESCRIPTION
            "The value of sysUpTime when this entry was created.  This
            can be used by the management station to ensure that the
            entry has not been deleted and recreated between polls."
    ::= { atmStatsEntry 2 }

atmStatsCells OBJECT-TYPE
    SYNTAX      Counter32
    MAX-ACCESS  read-only
    STATUS      current
    DESCRIPTION
            "The total number of error-free cells detected on all ATM
            connections on behalf of this portSelectGroup collection.
            Note that a particular cell may only cause this counter to
            increment once, even if multiple criteria is met for
            inclusion in this portSelectGroup."
    ::= { atmStatsEntry 3 }

atmStatsCellsRollovers OBJECT-TYPE
    SYNTAX      Counter32
    MAX-ACCESS  read-only
    STATUS      current
    DESCRIPTION
            "The number of times that the associated instance of the
            atmStatsCells object has transitioned from the value 2^^32-1
            to zero."


    ::= { atmStatsEntry 4 }

atmStatsHCCells OBJECT-TYPE
    SYNTAX      Counter64
    MAX-ACCESS  read-only
    STATUS      current
    DESCRIPTION
            "The high capacity version of the atmStatsCells object."
    ::= { atmStatsEntry 5 }

atmStatsNumCallAttempts OBJECT-TYPE
    SYNTAX      Counter32
    MAX-ACCESS  read-only
    STATUS      current
    DESCRIPTION
            "The number of call attempts detected on all signalled ATM
            connections on behalf of this portSelectGroup collection.  A
            probe should increment this counter each time a connection
            setup attempt (identified with this portSelectGroup) is
            detected. For point-to-multipoint connections, this counter
            is incremented once per counted connection, regardless of
            the number of leafs identified in the connection."
    ::= { atmStatsEntry 6 }

atmStatsNumCalls OBJECT-TYPE
    SYNTAX      Counter32
    MAX-ACCESS  read-only
    STATUS      current
    DESCRIPTION
            "The number of successfully established calls detected on
            all signalled ATM connections on behalf of this
            portSelectGroup collection.  Note that this value includes
            successfully established calls that are currently in
            progress.  A probe should increment this counter each time a
            valid connection (identified with this portSelectGroup) is
            successfully established. For point-to-multipoint ATM
            connections, this counter is incremented once per counted
            connection, regardless of the number of leafs identified in
            the connection. Note that when a point-to-point connection
            setup enters on one port and leaves on another port in the
            same port select group, it is counted only once."
    ::= { atmStatsEntry 7 }

atmStatsConnTime OBJECT-TYPE
    SYNTAX      ConnectTime


    UNITS       "seconds"
    MAX-ACCESS  read-only
    STATUS      current
    DESCRIPTION
            "The elapsed time of all calls identified by the associated
            instance of the atmStatsNumCallAttempts object.  Note that
            point-to-multipoint calls are counted only once, regardless
            of the number of leafs participating in the call."
    ::= { atmStatsEntry 8 }

--
-- ATM Host Group
--
-- Counts the amount of traffic sent on behalf of each ATM address
-- discovered by the probe, according to associated portSelectGroup
-- criteria

atmHostControlTable OBJECT-TYPE
    SYNTAX      SEQUENCE OF AtmHostControlEntry
    MAX-ACCESS  not-accessible
    STATUS      current
    DESCRIPTION
            "A list of ATM host table control entries.

            These entries will enable the collection of ATM host
            information in the atmHostTable.

            Entries in the atmHostTable will be created on behalf of
            each entry in this table. A probe is required to support at
            most one atmHost collection per instance of an associated
            portSelectGroup, therefore the table is indexed by the
            portSelGrpIndex."
    ::= { atmHost 1 }

atmHostControlEntry OBJECT-TYPE
    SYNTAX      AtmHostControlEntry
    MAX-ACCESS  not-accessible
    STATUS      current
    DESCRIPTION
            "A conceptual row in the atmHostControlTable.  Entries in
            this table are identified and indexed by the portSelGrpIndex
            object.  At most one atmHost collection is done per
            portSelectGroup.


            An example of the indexing of this entry is
            atmHostControlInserts.1"
    INDEX { portSelGrpIndex }
    ::= { atmHostControlTable 1 }

AtmHostControlEntry ::= SEQUENCE {
    atmHostControlInserts               Counter32,
    atmHostControlDeletes               Counter32,
    atmHostControlMaxDesiredEntries     Integer32,
    atmHostControlPriority              ResourcePriority,
    atmHostControlAddrCollectScope      AddressCollectScope,
    atmHostControlDropEvents            Counter32,
    atmHostControlOwner                 OwnerString,
    atmHostControlStatus                RowStatus
}

atmHostControlInserts OBJECT-TYPE
    SYNTAX     Counter32
    MAX-ACCESS read-only
    STATUS     current
    DESCRIPTION
            "The number of times an atmHost entry has been inserted into
            the atmHost table.  If an entry is inserted, then deleted,
            and then inserted, this counter will be incremented by 2.

            To allow for efficient implementation strategies, agents may
            delay updating this object for short periods of time.  For
            example, an implementation strategy may allow internal data
            structures to differ from those visible via SNMP for short
            periods of time.  This counter may reflect the internal data
            structures for those short periods of time.

            Note that the table size can be determined by subtracting
            atmHostControlDeletes from atmHostControlInserts."
    ::= { atmHostControlEntry 1 }

atmHostControlDeletes OBJECT-TYPE
    SYNTAX     Counter32
    MAX-ACCESS read-only
    STATUS     current
    DESCRIPTION
            "The number of times an atmHost entry has been deleted from
            the atmHost table (for any reason).  If an entry is deleted,
            then inserted, and then deleted, this counter will be
            incremented by 2.


            To allow for efficient implementation strategies, agents may
            delay updating this object for short periods of time.  For
            example, an implementation strategy may allow internal data
            structures to differ from those visible via SNMP for short
            periods of time.  This counter may reflect the internal data
            structures for those short periods of time.

            Note that the table size can be determined by subtracting
            atmHostControlDeletes from atmHostControlInserts."
    ::= { atmHostControlEntry 2 }

atmHostControlMaxDesiredEntries OBJECT-TYPE
    SYNTAX      Integer32
    MAX-ACCESS  read-create
    STATUS      current
    DESCRIPTION
            "The maximum number of entries that are desired in the
            atmHostTable on behalf of this control entry. The probe will
            not create more than this number of associated entries in
            the table, but may choose to create fewer entries in this
            table for any reason including the lack of resources.

            If this value is set to -1, the probe may create any number
            of entries in this table.

            If the associated instance of atmHostControlStatus object is
            equal to active(1), this object may not be modified."
    DEFVAL { -1 }
    ::= { atmHostControlEntry 3 }

atmHostControlPriority OBJECT-TYPE
    SYNTAX      ResourcePriority
    MAX-ACCESS  read-create
    STATUS      current
    DESCRIPTION
            "The priority this collection should be given to retain
            resources, in the event the probe must reclaim some
            resources in order to add new entries to an existing atmHost
            collection or add new collections of other types.

            If the associated instance of atmHostControlStatus object is
            equal to active(1), this object may not be modified."
    DEFVAL { normalPriority }
    ::= { atmHostControlEntry 4 }


atmHostControlAddrCollectScope OBJECT-TYPE
    SYNTAX      AddressCollectScope
    MAX-ACCESS  read-create
    STATUS      current
    DESCRIPTION
            "This object controls the granularity of address collection
            in atmHostTable entries created on behalf of this control
            entry, according to the rules specified by the
            AddressCollectScope textual convention.

            If the associated instance of atmHostControlStatus object is
            equal to active(1), this object may not be modified."
    DEFVAL { prefixAndEsi }
    ::= { atmHostControlEntry 5 }

atmHostControlDropEvents OBJECT-TYPE
    SYNTAX      Counter32
    MAX-ACCESS  read-only
    STATUS      current
    DESCRIPTION
            "The total number of events in which cells which should have
            been counted in the associated atmHostEntry, but were
            dropped by the probe due to lack of resources.  Note that
            this number is not necessarily the number of cells or calls
            dropped; it is just the number of times this condition has
            been detected."
    ::= { atmHostControlEntry 6 }

atmHostControlOwner OBJECT-TYPE
    SYNTAX      OwnerString
    MAX-ACCESS  read-create
    STATUS      current
    DESCRIPTION
            "The entity that configured this entry and is therefore
            using the resources assigned to it."
    ::= { atmHostControlEntry 7 }

atmHostControlStatus OBJECT-TYPE
    SYNTAX      RowStatus
    MAX-ACCESS  read-create
    STATUS      current
    DESCRIPTION
            "The status of this atmHostControlEntry.

            An entry may not exist in the active state unless all


            objects in the entry have an appropriate value.
            Specifically, appropriate values for the associated
            instances of atmHostControlMaxDesiredEntries,
            atmHostControlPriority, and atmHostControlAddrCollectScope
            must be set before this object may be set to active(1).

            This control entry may be created and destroyed
            independently of the associated portSelGrpEntry, however its
            associated atmHostTable can exist only when the
            portSelGrpEntry controlling this collection is active.

            If this object is not equal to active(1), all associated
            entries in the atmHostTable shall be deleted."
    ::= { atmHostControlEntry 8 }

--
-- ATM Host Table
--

atmHostTable OBJECT-TYPE
    SYNTAX      SEQUENCE OF AtmHostEntry
    MAX-ACCESS  not-accessible
    STATUS      current
    DESCRIPTION
            "A collection of statistics for a particular ATM host
            address that has been discovered on behalf of the
            portSelectGroup associated with this entry.

            The probe will add to this table all addresses seen as the
            source or destination address in all calls, on all ports
            configured in the portSelGrpEntry controlling this
            collection."
    ::= { atmHost 2 }

atmHostEntry OBJECT-TYPE
    SYNTAX      AtmHostEntry
    MAX-ACCESS  not-accessible
    STATUS      current
    DESCRIPTION
            "A conceptual row in the atmHostTable.

            The portSelGrpIndex value in the index identifies the
            portSelectGroup on whose behalf this entry was created.


            An example of the indexing of this entry is
            atmHostInCells.4.20.<NSAP>.2"
    INDEX { portSelGrpIndex, atmHostAddress, atmHostSClass }
    ::= { atmHostTable 1 }

AtmHostEntry ::= SEQUENCE {
    atmHostAddress              AtmAddr,
    atmHostSClass               ServiceClass,
    atmHostCreateTime           LastCreateTime,
    atmHostInCells              ZeroBasedCounter32,
    atmHostInCellsRollovers     ZeroBasedCounter32,
    atmHostInHCCells            Counter64,
    atmHostOutCells             ZeroBasedCounter32,
    atmHostOutCellsRollovers    ZeroBasedCounter32,
    atmHostOutHCCells           Counter64,
    atmHostInNumCallAttempts    ZeroBasedCounter32,
    atmHostInNumCalls           ZeroBasedCounter32,
    atmHostOutNumCallAttempts   ZeroBasedCounter32,
    atmHostOutNumCalls          ZeroBasedCounter32,
    atmHostInConnTime           ConnectTime,
    atmHostOutConnTime          ConnectTime
}

atmHostAddress OBJECT-TYPE
    SYNTAX      AtmAddr
    MAX-ACCESS  not-accessible
    STATUS      current
    DESCRIPTION
            "The ATM address for this atmHostEntry.

            This is represented as an octet string with specific
            semantics and length as identified by the AtmAddr textual
            convention.

            Note that only 20 octet 'AtmAddr' addresses are collected in
            this table."
    ::= { atmHostEntry 1 }

atmHostSClass OBJECT-TYPE
    SYNTAX      ServiceClass
    MAX-ACCESS  not-accessible
    STATUS      current
    DESCRIPTION
            "The quality of service classification for this entry.  See
            the ServiceClass textual convention for details and specific


            class-of-service values."
    ::= { atmHostEntry 2 }

atmHostCreateTime OBJECT-TYPE
    SYNTAX      LastCreateTime
    MAX-ACCESS  read-only
    STATUS      current
    DESCRIPTION
            "The value of sysUpTime when this entry was activated.  This
            can be used by the management station to ensure that the
            entry has not been deleted and recreated between polls."
    ::= { atmHostEntry 3 }

atmHostInCells OBJECT-TYPE
    SYNTAX      ZeroBasedCounter32
    MAX-ACCESS  read-only
    STATUS      current
    DESCRIPTION
            "The number of error-free cells detected on ATM connections
            associated with this portSelectGroup, in which this ATM
            address was identified as the receiver address, or one of
            the leaf addresses on a point-to-multipoint ATM connection."
    ::= { atmHostEntry 4 }

atmHostInCellsRollovers OBJECT-TYPE
    SYNTAX      ZeroBasedCounter32
    MAX-ACCESS  read-only
    STATUS      current
    DESCRIPTION
            "The number of times that the associated instance of the
            atmHostInCells object has transitioned from the value
            2^^32-1 to zero."
    ::= { atmHostEntry 5 }

atmHostInHCCells OBJECT-TYPE
    SYNTAX      Counter64
    MAX-ACCESS  read-only
    STATUS      current
    DESCRIPTION
            "The high capacity version of the atmHostInCells object."
    ::= { atmHostEntry 6 }

atmHostOutCells OBJECT-TYPE
    SYNTAX      ZeroBasedCounter32
    MAX-ACCESS  read-only


    STATUS      current
    DESCRIPTION
            "The number of error-free cells detected on ATM connections
            associated with this portSelectGroup, in which this ATM
            address was identified as the sender address."
    ::= { atmHostEntry 7 }

atmHostOutCellsRollovers OBJECT-TYPE
    SYNTAX      ZeroBasedCounter32
    MAX-ACCESS  read-only
    STATUS      current
    DESCRIPTION
            "The number of times that the associated instance of the
            atmHostOutCells object has transitioned from the value
            2^^32-1 to zero."
    ::= { atmHostEntry 8 }

atmHostOutHCCells OBJECT-TYPE
    SYNTAX      Counter64
    MAX-ACCESS  read-only
    STATUS      current
    DESCRIPTION
            "The high capacity version of the atmHostOutCells object."
    ::= { atmHostEntry 9 }

atmHostInNumCallAttempts OBJECT-TYPE
    SYNTAX      ZeroBasedCounter32
    MAX-ACCESS  read-only
    STATUS      current
    DESCRIPTION
            "The number of calls detected on ATM connections associated
            with this entry, in which the associated endpoint address
            was identified as the Called Party in an signalled ATM
            connection establishment attempt.

            Note that this value includes calls that are currently in
            progress.  A probe should increment this counter each time a
            connection attempt is detected in which this ATM host is
            identified as the Called Party, or one of the leaf addresses
            for point-to-multipoint ATM connections."
    ::= { atmHostEntry 10 }

atmHostInNumCalls OBJECT-TYPE
    SYNTAX      ZeroBasedCounter32
    MAX-ACCESS  read-only


    STATUS      current
    DESCRIPTION
            "The number of successfully established calls detected on
            ATM connections associated with this entry, in which the
            associated endpoint address was identified as the Called
            Party address.

            Note that this value includes calls that are currently in
            progress.  A probe should increment this counter each time a
            connection is successfully established in which this ATM
            host is identified as the Called Party address, or one of
            the leaf addresses for point-to-multipoint ATM connections."
    ::= { atmHostEntry 11 }

atmHostOutNumCallAttempts OBJECT-TYPE
    SYNTAX      ZeroBasedCounter32
    MAX-ACCESS  read-only
    STATUS      current
    DESCRIPTION
            "The number of calls detected on ATM connections associated
            with this entry, in which the associated endpoint address
            was identified as the Calling Party in an signalled ATM
            connection establishment attempt.

            Note that this value includes calls that are currently in
            progress.  A probe should increment this counter each time a
            connection attempt is detected in which this ATM host is
            identified as the Calling Party.

            Note that for point-to-multipoint ATM connections, this
            counter is incremented only once per call, regardless of the
            number of leafs established at setup time or the number of
            leaf-initiated-join attempts since the call was
            established."
    ::= { atmHostEntry 12 }

atmHostOutNumCalls OBJECT-TYPE
    SYNTAX      ZeroBasedCounter32
    MAX-ACCESS  read-only
    STATUS      current
    DESCRIPTION
            "The number of successfully established calls detected on
            ATM connections associated with this entry, in which the
            associated endpoint address was identified as the Calling
            Party address.


            Note that this value includes calls that are currently in
            progress.  A probe should increment this counter each time a
            connection is successfully established in which this ATM
            host is identified as the Calling Party address."
    ::= { atmHostEntry 13 }

atmHostInConnTime OBJECT-TYPE
    SYNTAX      ConnectTime
    UNITS       "seconds"
    MAX-ACCESS  read-only
    STATUS      current
    DESCRIPTION
            "The elapsed time of all calls identified by the associated
            instance of atmHostInNumCallAttempts."
    ::= { atmHostEntry 14 }

atmHostOutConnTime OBJECT-TYPE
    SYNTAX      ConnectTime
    UNITS       "seconds"
    MAX-ACCESS  read-only
    STATUS      current
    DESCRIPTION
            "The elapsed time of all calls identified by the associated
            instance of atmHostOutNumCallAttempts."
    ::= { atmHostEntry 15 }

--
-- ATM Matrix Group
--
-- Counts the amount of traffic sent on behalf of each source
-- and destination ATM address discovered by the probe,
-- according to associated portSelectGroup criteria

atmMatrixControlTable OBJECT-TYPE
    SYNTAX      SEQUENCE OF AtmMatrixControlEntry
    MAX-ACCESS  not-accessible
    STATUS      current
    DESCRIPTION
            "A list of ATM matrix table control entries.

            These entries will enable the collection of ATM matrix
            information in the atmMatrixSDTable and atmMatrixDSTable.

            A probe is required to support at most one atmMatrix


            collection per instance of an associated portSelectGroup,
            therefore the table is indexed by the portSelGrpIndex."
    ::= { atmMatrix 1 }

atmMatrixControlEntry OBJECT-TYPE
    SYNTAX      AtmMatrixControlEntry
    MAX-ACCESS  not-accessible
    STATUS      current
    DESCRIPTION
            "A conceptual row in the atmMatrixControlTable.

            An example of the indexing of this entry is
            atmMatrixControlInserts.1"
    INDEX { portSelGrpIndex }
    ::= { atmMatrixControlTable 1 }

AtmMatrixControlEntry    ::= SEQUENCE {
    atmMatrixControlInserts             Counter32,
    atmMatrixControlDeletes             Counter32,
    atmMatrixControlMaxDesiredEntries   Integer32,
    atmMatrixControlPriority            ResourcePriority,
    atmMatrixControlAddrCollectScope    AddressCollectScope,
    atmMatrixControlDropEvents          Counter32,
    atmMatrixControlOwner               OwnerString,
    atmMatrixControlStatus              RowStatus
}

atmMatrixControlInserts OBJECT-TYPE
    SYNTAX      Counter32
    MAX-ACCESS  read-only
    STATUS      current
    DESCRIPTION
            "The number of times an atmMatrix entry has been inserted
            into the atmMatrix table.  If an entry is inserted, then
            deleted, and then inserted, this counter will be incremented
            by 2.  The addition of a conversation into both the
            atmMatrixSDTable and atmMatrixDSTable shall be counted as
            two insertions (even though every addition into one table
            must be accompanied by an insertion into the other).

            To allow for efficient implementation strategies, agents may
            delay updating this object for short periods of time.  For
            example, an implementation strategy may allow internal data
            structures to differ from those visible via SNMP for short
            periods of time.  This counter may reflect the internal data


            structures for those short periods of time.

            Note that the table size can be determined by subtracting
            atmMatrixControlDeletes from atmMatrixControlInserts, and
            dividing the result by two."
    ::= { atmMatrixControlEntry 1 }

atmMatrixControlDeletes OBJECT-TYPE
    SYNTAX      Counter32
    MAX-ACCESS  read-only
    STATUS      current
    DESCRIPTION
            "The number of times an atmMatrix entry has been deleted
            from the atmMatrix table (for any reason).  If an entry is
            deleted, then inserted, and then deleted, this counter will
            be incremented by 2.  The deletion of a conversation from
            both the atmMatrixSDTable and atmMatrixDSTable shall be
            counted as two deletions (even though every deletion from
            one table must be accompanied by a deletion from the other).

            To allow for efficient implementation strategies, agents may
            delay updating this object for short periods of time.  For
            example, an implementation strategy may allow internal data
            structures to differ from those visible via SNMP for short
            periods of time.  This counter may reflect the internal data
            structures for those short periods of time.

            Note that the table size can be determined by subtracting
            atmMatrixControlDeletes from atmMatrixControlInserts, and
            dividing the result by two."
    ::= { atmMatrixControlEntry 2 }

atmMatrixControlMaxDesiredEntries OBJECT-TYPE
    SYNTAX      Integer32
    MAX-ACCESS  read-create
    STATUS      current
    DESCRIPTION
            "The maximum number of entries that are desired in the
            atmMatrixTable on behalf of this control entry. The probe
            will not create more than this number of associated entries
            in the table, but may choose to create fewer entries in this
            table for any reason including the lack of resources.

            If this value is set to -1, the probe may create any number
            of entries in this table.


            If the associated instance of atmMatrixControlStatus object
            is equal to active(1), this object may not be modified."
    DEFVAL { -1 }
    ::= { atmMatrixControlEntry 3 }

atmMatrixControlPriority OBJECT-TYPE
    SYNTAX      ResourcePriority
    MAX-ACCESS  read-create
    STATUS      current
    DESCRIPTION
            "The priority this collection should be given to retain
            resources, in the event the probe must reclaim some
            resources in order to add new entries to an existing
            atmMatrix collection or add new collections of other types.

            If the associated instance of atmMatrixControlStatus object
            is equal to active(1), this object may not be modified."
    DEFVAL { normalPriority }
    ::= { atmMatrixControlEntry 4 }

atmMatrixControlAddrCollectScope OBJECT-TYPE
    SYNTAX AddressCollectScope
    MAX-ACCESS  read-create
    STATUS      current
    DESCRIPTION
            "This object controls the granularity of address collection
            in atmMatrixSDTable and atmMatrixDSTable entries created on
            behalf of this control entry, according to the rules
            specified by the AddressCollectScope textual convention.

            If the associated instance of atmMatrixControlStatus object
            is equal to active(1), this object may not be modified."
    DEFVAL { prefixAndEsi }
    ::= { atmMatrixControlEntry 5 }

atmMatrixControlDropEvents OBJECT-TYPE
    SYNTAX      Counter32
    MAX-ACCESS  read-only
    STATUS      current
    DESCRIPTION
            "The total number of events in which cells which should have
            been counted in the associated atmMatrixSDEntry and
            atmMatrixDSEntry, but were dropped by the probe due to lack
            of resources.  Note that this number is not necessarily the
            number of cells or calls dropped; it is just the number of


            times this condition has been detected."
    ::= { atmMatrixControlEntry 6 }

atmMatrixControlOwner OBJECT-TYPE
    SYNTAX      OwnerString
    MAX-ACCESS  read-create
    STATUS      current
    DESCRIPTION
            "The entity that configured this entry and is therefore
            using the resources assigned to it."
    ::= { atmMatrixControlEntry 7 }

atmMatrixControlStatus OBJECT-TYPE
    SYNTAX      RowStatus
    MAX-ACCESS  read-create
    STATUS      current
    DESCRIPTION
            "The status of this atmMatrixControlEntry.

            An entry may not exist in the active state unless all
            objects in the entry have an appropriate value.
            Specifically, the associated instances of
            atmMatrixControlMaxDesiredEntries, atmMatrixControlPriority,
            and atmMatrixControlAddrCollectScope objects must be set to
            appropriate values before this object may be set to
            active(1).

            This control entry may be created and destroyed
            independently of the associated portSelGrpEntry, however its
            associated atmMatrixSDTable and atmMatrixDSTable can exist
            only when the portSelGrpEntry controlling this collection is
            active.

            If this object is not equal to active(1), all associated
            entries in the atmMatrixSDTable and atmMatrixDSTable shall
            be deleted."
    ::= { atmMatrixControlEntry 8 }

-- atmMatrixSDTable
-- call and traffic data collected on behalf of specific
-- portSelectGroups; sorted by src address first

atmMatrixSDTable OBJECT-TYPE
    SYNTAX      SEQUENCE OF AtmMatrixSDEntry


    MAX-ACCESS  not-accessible
    STATUS      current
    DESCRIPTION
            "A collection of statistics for conversations between
            particular ATM endpoint addresses that have been discovered
            on behalf of the portSelectGroup associated with this entry.

            The probe will add a new entry to this table for all
            conversations (connections) between distinct source and
            destination address pairs, detected in all calls, on all
            ports configured in the portSelGrpEntry controlling this
            collection.

            Further, this table will only contain entries that have a
            corresponding entry in the atmMatrixDSTable with the same
            source address and destination address."
    ::= { atmMatrix 2 }

atmMatrixSDEntry OBJECT-TYPE
    SYNTAX      AtmMatrixSDEntry
    MAX-ACCESS  not-accessible
    STATUS      current
    DESCRIPTION
            "A conceptual row in the atmMatrixSDTable.

            The portSelGrpIndex value in the index identifies the
            portSelectGroup on whose behalf this entry was created.

            An example of the indexing of this entry is
            atmMatrixSDCells.1.20.<NSAP>.20.<NSAP>.2"
    INDEX { portSelGrpIndex, atmMatrixSDSrcAddress,
            atmMatrixSDDstAddress, atmMatrixSDSClass }
    ::= { atmMatrixSDTable 1 }

AtmMatrixSDEntry    ::= SEQUENCE {
    atmMatrixSDSrcAddress               AtmAddr,
    atmMatrixSDDstAddress               AtmAddr,
    atmMatrixSDSClass                   ServiceClass,
    atmMatrixSDCreateTime               LastCreateTime,
    atmMatrixSDCells                    ZeroBasedCounter32,
    atmMatrixSDCellsRollovers           ZeroBasedCounter32,
    atmMatrixSDHCCells                  Counter64,
    atmMatrixSDNumCallAttempts          ZeroBasedCounter32,
    atmMatrixSDNumCalls                 ZeroBasedCounter32,
    atmMatrixSDConnTime                 ConnectTime


}

atmMatrixSDSrcAddress OBJECT-TYPE
    SYNTAX      AtmAddr
    MAX-ACCESS  not-accessible
    STATUS      current
    DESCRIPTION
            "The transmitting endpoint ATM address for this
            atmMatrixSDEntry.

            This is represented as an octet string with specific
            semantics and length as identified by the AtmAddr textual
            convention.

            Note that only 20 octet 'AtmAddr' addresses are collected in
            this table."
    ::= { atmMatrixSDEntry 1 }

atmMatrixSDDstAddress OBJECT-TYPE
    SYNTAX      AtmAddr
    MAX-ACCESS  not-accessible
    STATUS      current
    DESCRIPTION
            "The destination endpoint ATM address for this
            atmMatrixSDEntry.

            This is represented as an octet string with specific
            semantics and length as identified by the AtmAddr textual
            convention.

            Note that only 20 octet 'AtmAddr' addresses are collected in
            this table."
    ::= { atmMatrixSDEntry 2 }

atmMatrixSDSClass OBJECT-TYPE
    SYNTAX      ServiceClass
    MAX-ACCESS  not-accessible
    STATUS      current
    DESCRIPTION
            "The quality of service classification for this entry.  See
            the ServiceClass textual convention for details and specific
            class-of-service values."
    ::= { atmMatrixSDEntry 3 }

atmMatrixSDCreateTime OBJECT-TYPE


    SYNTAX      LastCreateTime
    MAX-ACCESS  read-only
    STATUS      current
    DESCRIPTION
            "The value of sysUpTime when this entry was activated.  This
            can be used by the management station to ensure that the
            entry has not been deleted and recreated between polls."
    ::= { atmMatrixSDEntry 4 }

atmMatrixSDCells OBJECT-TYPE
    SYNTAX      ZeroBasedCounter32
    MAX-ACCESS  read-only
    STATUS      current
    DESCRIPTION
            "The number of error-free cells detected on connections in
            which these ATM addresses were identified as the
            transmitting and receiving endpoint addresses.

            Note that for point-to-multipoint connections, an entry is
            created for each root-to-leaf address-pair that exists, and
            each cell sent from the root on a point-to-multipoint ATM
            connection is counted once in each distinct matrix entry."
    ::= { atmMatrixSDEntry 5 }

atmMatrixSDCellsRollovers OBJECT-TYPE
    SYNTAX      ZeroBasedCounter32
    MAX-ACCESS  read-only
    STATUS      current
    DESCRIPTION
            "The number of times that the associated instance of the
            atmMatrixSDCells object has transitioned from the value
            2^^32-1 to zero."
    ::= { atmMatrixSDEntry 6 }

atmMatrixSDHCCells OBJECT-TYPE
    SYNTAX      Counter64
    MAX-ACCESS  read-only
    STATUS      current
    DESCRIPTION
            "The high capacity version of the atmMatrixSDCells object."
    ::= { atmMatrixSDEntry 7 }

atmMatrixSDNumCallAttempts OBJECT-TYPE
    SYNTAX      ZeroBasedCounter32
    MAX-ACCESS  read-only


    STATUS      current
    DESCRIPTION
            "The number of SVC call setup attempts detected on ATM
            connections within the specified portSelectGroup, in which
            the indicated atmMatrixSDSrcAddress endpoint address was
            identified as the Calling Party and the indicated
            atmMatrixSDDstAddress was identified as the Called Party.

            Note that this value includes calls that are currently in
            progress.  A probe should increment this counter each time a
            connection attempt is detected in which these ATM addresses
            are identified as the calling and called parties."
    ::= { atmMatrixSDEntry 8 }

atmMatrixSDNumCalls OBJECT-TYPE
    SYNTAX      ZeroBasedCounter32
    MAX-ACCESS  read-only
    STATUS      current
    DESCRIPTION
            "The number of successful SVC call setups detected on ATM
            connections within the specified portSelectGroup, in which
            the indicated atmMatrixSDSrcAddress endpoint address was
            identified as the Calling Party and the indicated
            atmMatrixSDDstAddress was identified as the Called Party.

            Note that this value includes calls that are currently in
            progress.  A probe should increment this counter each time a
            valid connection is established in which these ATM addresses
            are identified as the calling and called parties."
    ::= { atmMatrixSDEntry 9 }

atmMatrixSDConnTime OBJECT-TYPE
    SYNTAX      ConnectTime
    UNITS       "seconds"
    MAX-ACCESS  read-only
    STATUS      current
    DESCRIPTION
            "The elapsed time of all calls identified by the associated
            instance of atmMatrixSDNumCallAttempts."
    ::= { atmMatrixSDEntry 10 }

-- atmMatrixDSTable
-- call and traffic data collected on behalf of specific
-- portSelectGroups; sorted by destination address first


atmMatrixDSTable OBJECT-TYPE
    SYNTAX      SEQUENCE OF AtmMatrixDSEntry
    MAX-ACCESS  not-accessible
    STATUS      current
    DESCRIPTION
            "A collection of statistics for conversations between
            particular ATM endpoint addresses that have been discovered
            on behalf of the portSelectGroup associated with this entry.

            The probe will add a new entry to this table for all
            conversations (connections) between distinct source and
            destination address pairs, detected in all cells identified
            by the associated portSelGrpEntry criteria.

            Further, this table will only contain entries that have a
            corresponding entry in the atmMatrixSDTable with the same
            source address and destination address."
    ::= { atmMatrix 3 }

atmMatrixDSEntry OBJECT-TYPE
    SYNTAX      AtmMatrixDSEntry
    MAX-ACCESS  not-accessible
    STATUS      current
    DESCRIPTION
            "A conceptual row in the atmMatrixDSTable.

            The portSelGrpIndex value in the index identifies the
            portSelectGroup on whose behalf this entry was created.

            An example of the indexing of this entry is
            atmMatrixDSCells.1.20.<NSAP>.20.<NSAP>.2"
    INDEX { portSelGrpIndex, atmMatrixDSDstAddress,
            atmMatrixDSSrcAddress, atmMatrixDSSClass }
    ::= { atmMatrixDSTable 1 }

AtmMatrixDSEntry    ::= SEQUENCE {
    atmMatrixDSSrcAddress               AtmAddr,
    atmMatrixDSDstAddress               AtmAddr,
    atmMatrixDSSClass                   ServiceClass,
    atmMatrixDSCreateTime               LastCreateTime,
    atmMatrixDSCells                    ZeroBasedCounter32,
    atmMatrixDSCellsRollovers           ZeroBasedCounter32,
    atmMatrixDSHCCells                  Counter64,
    atmMatrixDSNumCallAttempts          ZeroBasedCounter32,
    atmMatrixDSNumCalls                 ZeroBasedCounter32,


    atmMatrixDSConnTime                 ConnectTime
}

atmMatrixDSSrcAddress OBJECT-TYPE
    SYNTAX      AtmAddr
    MAX-ACCESS  not-accessible
    STATUS      current
    DESCRIPTION
            "The transmitting endpoint ATM address for this
            atmMatrixDSEntry.

            This is represented as an octet string with specific
            semantics and length as identified by the AtmAddr textual
            convention.

            Note that only 20 octet 'AtmAddr' addresses are collected in
            this table."
    ::= { atmMatrixDSEntry 1 }

atmMatrixDSDstAddress OBJECT-TYPE
    SYNTAX      AtmAddr
    MAX-ACCESS  not-accessible
    STATUS      current
    DESCRIPTION
            "The destination endpoint ATM address for this
            atmMatrixDSEntry.

            This is represented as an octet string with specific
            semantics and length as identified by the AtmAddr textual
            convention.

            Note that only 20 octet 'AtmAddr' addresses are collected in
            this table."
    ::= { atmMatrixDSEntry 2 }

atmMatrixDSSClass OBJECT-TYPE
    SYNTAX      ServiceClass
    MAX-ACCESS  not-accessible
    STATUS      current
    DESCRIPTION
            "The quality of service classification for this entry.  See
            the ServiceClass textual convention for details and specific
            class-of-service values."
    ::= { atmMatrixDSEntry 3 }


atmMatrixDSCreateTime OBJECT-TYPE
    SYNTAX      LastCreateTime
    MAX-ACCESS  read-only
    STATUS      current
    DESCRIPTION
            "The value of sysUpTime when this entry was activated.  This
            can be used by the management station to ensure that the
            entry has not been deleted and recreated between polls."
    ::= { atmMatrixDSEntry 4 }

atmMatrixDSCells OBJECT-TYPE
    SYNTAX      ZeroBasedCounter32
    MAX-ACCESS  read-only
    STATUS      current
    DESCRIPTION
            "The number of error-free cells detected on ATM connections
            in which these ATM addresses were identified as the
            transmitting and receiving endpoint addresses.

            Note that for point-to-multipoint connections, an entry is
            created for each root-to-leaf address-pair that exists, and
            each cell sent from the root on a point-to-multipoint ATM
            connection is counted once in each distinct matrix entry."
    ::= { atmMatrixDSEntry 5 }

atmMatrixDSCellsRollovers OBJECT-TYPE
    SYNTAX      ZeroBasedCounter32
    MAX-ACCESS  read-only
    STATUS      current
    DESCRIPTION
            "The number of times that the associated instance of the
            atmMatrixDSCells object has transitioned from the value
            2^^32-1 to zero."
    ::= { atmMatrixDSEntry 6 }

atmMatrixDSHCCells OBJECT-TYPE
    SYNTAX      Counter64
    MAX-ACCESS  read-only
    STATUS      current
    DESCRIPTION
            "The high capacity version of the atmMatrixDSCells object."
    ::= { atmMatrixDSEntry 7 }

atmMatrixDSNumCallAttempts OBJECT-TYPE
    SYNTAX      ZeroBasedCounter32


    MAX-ACCESS  read-only
    STATUS      current
    DESCRIPTION
            "The number of SVC call setup attempts detected on ATM
            connections within the specified portSelectGroup, in which
            the indicated atmMatrixDSSrcAddress endpoint address was
            identified as the Calling Party and the indicated
            atmMatrixDSDstAddress was identified as the Called Party.

            Note that this value includes calls that are currently in
            progress.  A probe should increment this counter each time a
            connection attempt is detected in which these ATM addresses
            are identified as the calling and called parties."
    ::= { atmMatrixDSEntry 8 }

atmMatrixDSNumCalls OBJECT-TYPE
    SYNTAX      ZeroBasedCounter32
    MAX-ACCESS  read-only
    STATUS      current
    DESCRIPTION
            "The number of successful SVC call setups detected on ATM
            connections within the specified portSelectGroup, in which
            the indicated atmMatrixDSSrcAddress endpoint address was
            identified as the Calling Party and the indicated
            atmMatrixDSDstAddress was identified as the Called Party.

            Note that this value includes calls that are currently in
            progress.  A probe should increment this counter each time a
            valid connection is established in which these ATM addresses
            are identified as the calling and called parties."
    ::= { atmMatrixDSEntry 9 }

atmMatrixDSConnTime OBJECT-TYPE
    SYNTAX      ConnectTime
    UNITS       "seconds"
    MAX-ACCESS  read-only
    STATUS      current
    DESCRIPTION
            "The elapsed time of all calls identified by the associated
            instance of atmMatrixDSNumCallAttempts."
    ::= { atmMatrixDSEntry 10 }

--
-- ATM MatrixTopN Tables


--
-- Finds and reports the top traffic contributors,
-- according to associated portSelectGroup criteria

atmMatrixTopNControlTable OBJECT-TYPE
    SYNTAX      SEQUENCE OF AtmMatrixTopNControlEntry
    MAX-ACCESS  not-accessible
    STATUS      current
    DESCRIPTION
            "A set of parameters that control the creation of a report
            of the top N matrix entries according to a selected metric."
    ::= { atmMatrix 4 }

atmMatrixTopNControlEntry OBJECT-TYPE
    SYNTAX      AtmMatrixTopNControlEntry
    MAX-ACCESS  not-accessible
    STATUS      current
    DESCRIPTION
            "A conceptual row in the atmMatrixTopNControlTable.

            An example of the indexing of this table is
            atmMatrixTopNControlDuration.3.1"
    INDEX { portSelGrpIndex, atmMatrixTopNControlIndex }
    ::= { atmMatrixTopNControlTable 1 }

AtmMatrixTopNControlEntry    ::= SEQUENCE {
    atmMatrixTopNControlIndex            Integer32,
    atmMatrixTopNControlRateBase         INTEGER,
    atmMatrixTopNControlSClass           ServiceClass,
    atmMatrixTopNControlTimeRemaining    Integer32,
    atmMatrixTopNControlGeneratedReports Counter32,
    atmMatrixTopNControlDuration         Integer32,
    atmMatrixTopNControlRequestedSize    Integer32,
    atmMatrixTopNControlGrantedSize      Integer32,
    atmMatrixTopNControlStartTime        TimeStamp,
    atmMatrixTopNControlOwner            OwnerString,
    atmMatrixTopNControlStatus           RowStatus
}

atmMatrixTopNControlIndex OBJECT-TYPE
    SYNTAX      Integer32 (1..65535)
    MAX-ACCESS  not-accessible
    STATUS      current
    DESCRIPTION
            "An index that is used to uniquely identify an entry in the


            atmMatrixTopNControlTable.  Each such entry defines one top
            N report prepared on behalf of one atmMatrix entry, which
            must exist before this entry may be created."
    ::= { atmMatrixTopNControlEntry 1 }

atmMatrixTopNControlRateBase OBJECT-TYPE
    SYNTAX INTEGER {
        atmMatrixTopNCells(1),
        atmMatrixTopNNumCallAttempts(2),
        atmMatrixTopNNumCalls(3),
        atmMatrixTopNConnTime(4)
    }
    MAX-ACCESS          read-create
    STATUS              current
    DESCRIPTION
            "The variable for each atmMatrix entry that the
            atmMatrixTopNEntries are sorted by.

            This object may not be modified if the associated
            atmMatrixTopNControlStatus object is equal to active(1)."
    ::= { atmMatrixTopNControlEntry 2 }

atmMatrixTopNControlSClass OBJECT-TYPE
    SYNTAX              ServiceClass
    MAX-ACCESS          read-create
    STATUS              current
    DESCRIPTION
            "The service class for which this topN control entry is
            collecting information in associated atmMatrixTopN reports.

            This object may not be modified if the associated
            atmMatrixTopNControlStatus object is equal to active(1)."
    ::= { atmMatrixTopNControlEntry 3 }

atmMatrixTopNControlTimeRemaining OBJECT-TYPE
    SYNTAX      Integer32
    MAX-ACCESS  read-create
    STATUS      current
    DESCRIPTION
            "The number of seconds left in the report currently being
            collected.  When this object is modified by the management
            station, a new collection is started, possibly aborting a
            currently running report.  The new value is used as the
            requested duration of this report, and is immediately loaded
            into the associated atmMatrixTopNControlDuration object.


            When the report finishes, the probe will automatically start
            another collection with the same initial value of
            atmMatrixTopNControlTimeRemaining.  Thus the management
            station may simply read the resulting reports repeatedly,
            checking the startTime and duration each time to ensure that
            a report was not missed or that the report parameters were
            not changed.

            While the value of this object is non-zero, it decrements by
            one per second until it reaches zero.  At the time that this
            object decrements to zero, the report is made accessible in
            the atmMatrixTopNTable, overwriting any report that may be
            there.

            When this object is modified by the management station, any
            associated entries in the atmMatrixTopNTable shall be
            deleted."
    DEFVAL { 1800 }
    ::= { atmMatrixTopNControlEntry 4 }

atmMatrixTopNControlGeneratedReports OBJECT-TYPE
    SYNTAX      Counter32
    MAX-ACCESS  read-only
    STATUS      current
    DESCRIPTION
            "The number of reports that have been generated by this
            entry."
    ::= { atmMatrixTopNControlEntry 5 }

atmMatrixTopNControlDuration OBJECT-TYPE
    SYNTAX      Integer32
    MAX-ACCESS  read-only
    STATUS      current
    DESCRIPTION
            "The number of seconds that this report has collected during
            the last sampling interval.

            When the associated atmMatrixTopNControlTimeRemaining object
            is set, this object shall be set by the probe to the same
            value and shall not be modified until the next time the
            atmMatrixTopNControlTimeRemaining is set.

            This value shall be zero if no reports have been requested
            for this atmMatrixTopNControlEntry."
    ::= { atmMatrixTopNControlEntry 6 }


atmMatrixTopNControlRequestedSize OBJECT-TYPE
    SYNTAX      Integer32
    MAX-ACCESS  read-create
    STATUS      current
    DESCRIPTION
            "The maximum number of host entries requested for this
            report.

            When this object is created or modified, the probe should
            set atmMatrixTopNControlGrantedSize as closely to this
            object as is possible for the particular probe
            implementation and available resources."
    DEFVAL { 150 }
    ::= { atmMatrixTopNControlEntry 7 }

atmMatrixTopNControlGrantedSize OBJECT-TYPE
    SYNTAX      Integer32
    MAX-ACCESS  read-only
    STATUS      current
    DESCRIPTION
            "The maximum number of host entries in this report.

            When the associated atmMatrixTopNControlRequestedSize object
            is created or modified, the probe should set this object as
            closely to the requested value as is possible for the
            particular implementation and available resources. The probe
            must not lower this value except as a result of a set to the
            associated atmMatrixTopNControlRequestedSize object.

            For example, if the value of atmMatrixTopNControlRateBase is
            equal to atmMatrixTopNCells(1), when the next topN report is
            generated, host entries with the highest value of
            atmMatrixSDCells shall be placed in this table in decreasing
            order of this rate until there is no more room or until
            there are no more matrix entries. Each atmMatrixSDCells
            value is copied to the associated atmMatrixTopNRate object.

            It is an implementation-specific matter how entries with the
            same value are sorted.  It is also an implementation-
            specific matter as to whether or not zero-valued entries are
            available."
    ::= { atmMatrixTopNControlEntry 8 }

atmMatrixTopNControlStartTime OBJECT-TYPE
    SYNTAX      TimeStamp
    MAX-ACCESS  read-only
    STATUS      current
    DESCRIPTION
            "The value of sysUpTime when this top N report was last
            started.  In other words, this is the time that the
            associated atmMatrixTopNControlTimeRemaining object was
            modified to start the requested report or the time the
            report was last automatically (re)started.

            This object may be used by the management station to
            determine if a report was missed or not."
    ::= { atmMatrixTopNControlEntry 9 }

atmMatrixTopNControlOwner OBJECT-TYPE
    SYNTAX      OwnerString
    MAX-ACCESS  read-create
    STATUS      current
    DESCRIPTION
            "The entity that configured this entry and is therefore
            using the resources assigned to it."
    ::= { atmMatrixTopNControlEntry 10 }

atmMatrixTopNControlStatus OBJECT-TYPE
    SYNTAX      RowStatus
    MAX-ACCESS  read-create
    STATUS      current
    DESCRIPTION
            "The status of this atmMatrixTopNControlEntry.

            An entry may not exist in the active state unless all
            objects in the entry have an appropriate value.

            If this object is not equal to active(1), all associated
            entries in the atmMatrixTopNTable shall be deleted by the
            agent."
    ::= { atmMatrixTopNControlEntry 11 }

--
-- atmMatrixTopNTable
--
atmMatrixTopNTable OBJECT-TYPE
    SYNTAX      SEQUENCE OF AtmMatrixTopNEntry
    MAX-ACCESS  not-accessible
    STATUS      current


    DESCRIPTION
            "A set of statistics for those matrix entries that have
            counted the highest number of cells, calls, or connection
            time."
    ::= { atmMatrix 5 }

atmMatrixTopNEntry OBJECT-TYPE
    SYNTAX      AtmMatrixTopNEntry
    MAX-ACCESS  not-accessible
    STATUS      current
    DESCRIPTION
            "A conceptual row in the atmMatrixTopNTable.

            The atmMatrixTopNControlIndex value in the index identifies
            the atmMatrixTopNControlEntry on whose behalf this entry was
            created.

            An example of the indexing of this table is
            atmMatrixTopNSrcAddress.1.3.10"
    INDEX { portSelGrpIndex, atmMatrixTopNControlIndex,
            atmMatrixTopNIndex }
    ::= { atmMatrixTopNTable 1 }

AtmMatrixTopNEntry    ::= SEQUENCE {
    atmMatrixTopNIndex          Integer32,
    atmMatrixTopNSrcAddress     AtmAddr,
    atmMatrixTopNDstAddress     AtmAddr,
    atmMatrixTopNRate           Integer32,
    atmMatrixTopNReverseRate    Integer32
}

atmMatrixTopNIndex OBJECT-TYPE
    SYNTAX      Integer32 (1..65535)
    MAX-ACCESS  not-accessible
    STATUS      current
    DESCRIPTION
            "An index that uniquely identifies an entry in the
            atmMatrixTopNTable among those in the same report.  This
            index is between 1 and N, where N is the number of entries
            in this report.

            Each conversation in the selected atmMatrixSDTable, for the
            report interval, is ranked in descending order of the metric
            identified by the atmMatrixTopNRate object.


            For example, if the value of atmMatrixTopNControlRateBase is
            equal to atmMatrixTopNCells(1), increasing values of
            atmMatrixTopNIndex shall be assigned to entries with
            decreasing delta values of atmMatrixSDCells (for the report
            interval), until index N is assigned or there are no more
            atmMatrixSDEntries."
    ::= { atmMatrixTopNEntry 1 }

atmMatrixTopNSrcAddress OBJECT-TYPE
    SYNTAX      AtmAddr
    MAX-ACCESS  read-only
    STATUS      current
    DESCRIPTION
            "The ATM endpoint address identified as the source of the
            traffic measured in this report.

            Note that only 20 octet 'AtmAddr' addresses are collected in
            this table."
    ::= { atmMatrixTopNEntry 2 }

atmMatrixTopNDstAddress OBJECT-TYPE
    SYNTAX      AtmAddr
    MAX-ACCESS  read-only
    STATUS      current
    DESCRIPTION
            "The ATM endpoint address identified as the destination of
            the traffic measured in this report.

            Note that only 20 octet 'AtmAddr' addresses are collected in
            this table."
    ::= { atmMatrixTopNEntry 3 }

atmMatrixTopNRate OBJECT-TYPE
    SYNTAX      Integer32
    MAX-ACCESS  read-only
    STATUS      current
    DESCRIPTION
            "The value of the ranked metric for this conversation, for
            this report.

            If the associated value of atmMatrixTopNRateBase is equal to
            atmMatrixTopNCells(1), then this object is assigned the
            delta value of the atmMatrixSDCells object during this
            report interval.


            If the associated value of atmMatrixTopNRateBase is equal to
            atmMatrixTopNNumCallAttempts(2), then this object is
            assigned the delta value of the atmMatrixSDNumCallAttempts
            object during this report interval.

            If the associated value of atmMatrixTopNRateBase is equal to
            atmMatrixTopNNumCalls(3), then this object is assigned the
            delta value of the atmMatrixSDNumCalls object during this
            report interval.

            If the associated value of atmMatrixTopNRateBase is equal to
            atmMatrixTopNConnTime(4), then this object is assigned the
            delta value of the atmMatrixSDConnTime object during this
            report interval."
    ::= { atmMatrixTopNEntry 4 }

atmMatrixTopNReverseRate OBJECT-TYPE
    SYNTAX      Integer32
    MAX-ACCESS  read-only
    STATUS      current
    DESCRIPTION
            "The value of the associated metric for this conversation,
            and for this report, but for the reverse direction.

            For example, if the associated value of
            atmMatrixTopNRateBase is equal to atmMatrixTopNCells(1),
            then this object contains the atmMatrixSDCells delta cell
            rate for the reverse direction traffic (i.e., destination to
            source traffic)."
    ::= { atmMatrixTopNEntry 5 }

-- atmConfig group; cisco extensions for agent configuration
atmRmonDataCollectMode OBJECT-TYPE
    SYNTAX INTEGER {
	active(1),   	-- data collection active
	inactive(2)   	-- data collection inactive
    }
    MAX-ACCESS  read-write
    STATUS      current
    DESCRIPTION
            "Controls the internal data collection for the
	     entire ATM-RMON agent. If this object has a
	     value of 'active(1)', then data tables will be created
	     and maintained (normal behavior). If this object
	     has a value of 'inactive(2)' then ATM-RMON monitoring
	     will not occur, even if valid control tables exist
	     for particular collections. 

	     Data tables for active collections are deleted when this 
	     object is changed to 'inactive(2)', but control tables are
	     not deleted. When this object is changed to 'active(1)', 
	     data collection is started for all valid control tables. "
--  DEFVAL { inactive(2) }    
    ::= { atmConfig 1 }


-- Conformance Macros

atmRmonMIBCompliances   OBJECT IDENTIFIER ::= { atmRmonConformance 1 }
atmRmonMIBGroups        OBJECT IDENTIFIER ::= { atmRmonConformance 2 }

atmRmonMIBCompliance MODULE-COMPLIANCE
    STATUS  current
    DESCRIPTION
            "Describes the requirements for conformance to the ATM-RMON
            MIB."
    MODULE  -- this module
    MANDATORY-GROUPS {  portSelectGroup,
                        atmStatsGroup,
                        atmHostGroup,
                        atmMatrixGroup
                     }
    ::= { atmRmonMIBCompliances 1 }

portSelectGroup OBJECT-GROUP
    OBJECTS {
                portSelGrpDescr,
                portSelGrpCreateTime,
                portSelGrpOwner,
                portSelGrpStatus,
                portSelCollectGroup,
                portSelCreateTime,
                portSelOwner,
                portSelStatus
            }
    STATUS      current
    DESCRIPTION
            "Selects the ATM connections that should be monitored as
            part of a specific collection-group."
    ::= { atmRmonMIBGroups 1 }

atmStatsGroup OBJECT-GROUP
          OBJECTS {
                atmStatsControlDropEvents,
                atmStatsControlOwner,
                atmStatsControlStatus,
                atmStatsCreateTime,
                atmStatsCells,
                atmStatsCellsRollovers,
                atmStatsNumCallAttempts,
                atmStatsNumCalls,
                atmStatsConnTime
          }
    STATUS current
    DESCRIPTION
            "Counts the basic statistics for collections on behalf of
            particular portSelectGroup collections."
    ::= { atmRmonMIBGroups 2 }

atmStatsHCGroup OBJECT-GROUP
          OBJECTS {
            atmStatsHCCells
          }


    STATUS current
    DESCRIPTION
            "Counts the high capacity basic statistics for collections
            on behalf of particular portSelectGroup collections. The
            atmStatsGroup must be implemented if the atmStatsHCGroup is
            implemented.  This group is mandatory for implementations
            which support high capacity counters."
    ::= { atmRmonMIBGroups 3 }

atmHostGroup OBJECT-GROUP
    OBJECTS {
                atmHostControlInserts,
                atmHostControlDeletes,
                atmHostControlMaxDesiredEntries,
                atmHostControlPriority,
                atmHostControlAddrCollectScope,
                atmHostControlDropEvents,
                atmHostControlOwner,
                atmHostControlStatus,
                atmHostCreateTime,
                atmHostInCells,
                atmHostInCellsRollovers,
                atmHostOutCells,
                atmHostOutCellsRollovers,
                atmHostInNumCallAttempts,
                atmHostInNumCalls,
                atmHostOutNumCallAttempts,
                atmHostOutNumCalls,
                atmHostInConnTime,
                atmHostOutConnTime
    }
    STATUS  current
    DESCRIPTION
            "Counts the amount of traffic sent from and to each ATM
            address discovered by the probe, on behalf of particular
            portSelectGroup collections."
    ::= { atmRmonMIBGroups 4 }

atmHostHCGroup OBJECT-GROUP
    OBJECTS {
           atmHostInHCCells,
           atmHostOutHCCells
    }
    STATUS  current
    DESCRIPTION


            "Counts the amount of traffic sent from and to each ATM
            address discovered by the probe, on behalf of particular
            portSelectGroup collections, using high-capacity counters.
            The atmHostGroup must be implemented if the atmHostHCGroup
            is implemented.  This group is mandatory for implementations
            which support high capacity counters."
    ::= { atmRmonMIBGroups 5 }

atmMatrixGroup OBJECT-GROUP
    OBJECTS {
                atmMatrixControlInserts,
                atmMatrixControlDeletes,
                atmMatrixControlMaxDesiredEntries,
                atmMatrixControlPriority,
                atmMatrixControlAddrCollectScope,
                atmMatrixControlDropEvents,
                atmMatrixControlOwner,
                atmMatrixControlStatus,
                atmMatrixSDCreateTime,
                atmMatrixSDCells,
                atmMatrixSDCellsRollovers,
                atmMatrixSDNumCallAttempts,
                atmMatrixSDNumCalls,
                atmMatrixSDConnTime,
                atmMatrixDSCreateTime,
                atmMatrixDSCells,
                atmMatrixDSCellsRollovers,
                atmMatrixDSNumCallAttempts,
                atmMatrixDSNumCalls,
                atmMatrixDSConnTime,
                atmMatrixTopNControlRateBase,
                atmMatrixTopNControlSClass,
                atmMatrixTopNControlTimeRemaining,
                atmMatrixTopNControlGeneratedReports,
                atmMatrixTopNControlDuration,
                atmMatrixTopNControlRequestedSize,
                atmMatrixTopNControlGrantedSize,
                atmMatrixTopNControlStartTime,
                atmMatrixTopNControlOwner,
                atmMatrixTopNControlStatus,
                atmMatrixTopNSrcAddress,
                atmMatrixTopNDstAddress,
                atmMatrixTopNRate,
                atmMatrixTopNReverseRate
}


    STATUS  current
    DESCRIPTION
            "Counts the amount of traffic sent between each pair of ATM
            addresses discovered by the probe, on behalf of particular
            portSelectGroup collections."
    ::= { atmRmonMIBGroups 6 }

atmMatrixHCGroup OBJECT-GROUP
    OBJECTS {
         atmMatrixSDHCCells,
         atmMatrixDSHCCells
    }
    STATUS  current
    DESCRIPTION
            "Counts the amount of traffic sent between each pair of ATM
            addresses discovered by the probe, on behalf of particular
            portSelectGroup collections, using high capacity counters.
            The atmMatrixGroup must be implemented if the
            atmMatrixHCGroup is implemented.  This group is mandatory
            for implementations which support high capacity counters."
    ::= { atmRmonMIBGroups 7 }

atmConfigGroup OBJECT-GROUP
    OBJECTS {
           atmRmonDataCollectMode
    }
    STATUS  current
    DESCRIPTION
	   "Configuration extentions used to control internal
	    agent behavior."
    ::= { atmRmonMIBGroups 8 }

END
