-- *********************************************************************
-- CISCO-FIREPOWER-EXTMGMT-MIB.my
-- 
-- MIB representation of the Cisco Firepower
-- EXTMGMT management information model package
-- 
-- Created May 2024 by Charles Bullis
-- 
-- Copyright (c) 2005-2024 Cisco Systems, Inc. All rights reserved.
-- 
-- *********************************************************************

CISCO-FIREPOWER-EXTMGMT-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB
    CfprAaaConfigState,
    CfprExtmgmtArpTargetsMaxDeadlineTimeout,
    CfprExtmgmtArpTargetsNumberOfArpRequests,
    CfprExtmgmtGatewayPingMaxDeadlineTimeout,
    CfprExtmgmtGatewayPingNumberOfPingRequests,
    CfprExtmgmtIfFailureReason,
    CfprExtmgmtIfMonPolicyAdminState,
    CfprExtmgmtIfMonPolicyMonitorMechanism,
    CfprExtmgmtIfType,
    CfprExtmgmtMiiStatusMaxRetryCount,
    CfprExtmgmtMiiStatusRetryInterval,
    CfprExtmgmtNdiscTargetsMaxDeadlineTimeout,
    CfprExtmgmtNdiscTargetsNumberOfNdiscRequests,
    CfprNetworkIfStatus,
    CfprNetworkLocale,
    CfprNetworkPortRole,
    CfprNetworkPortType,
    CfprNetworkSwitchId,
    CfprNetworkTransport,
    CfprPolicyPolicyOwner
        FROM CISCO-FIREPOWER-TC-MIB;

cfprExtmgmtObjects MODULE-IDENTITY
    LAST-UPDATED    "202405160000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        EXTMGMT management information model package"
    ::= { ciscoFirepowerMIBObjects 23 }

cfprExtmgmtArpTargetsTable OBJECT-TYPE
    SYNTAX           SEQUENCE OF CfprExtmgmtArpTargetsEntry
    MAX-ACCESS       not-accessible
    STATUS           current
    DESCRIPTION
        "Cisco Firepower extmgmt:ArpTargets managed object table"
    ::= { cfprExtmgmtObjects 1 }

cfprExtmgmtArpTargetsEntry OBJECT-TYPE
    SYNTAX           CfprExtmgmtArpTargetsEntry
    MAX-ACCESS       not-accessible
    STATUS           current
    DESCRIPTION
        "Entry for the cfprExtmgmtArpTargetsTable table."
    INDEX { cfprExtmgmtArpTargetsInstanceId }
    ::= { cfprExtmgmtArpTargetsTable 1 }

CfprExtmgmtArpTargetsEntry ::= SEQUENCE {
    cfprExtmgmtArpTargetsInstanceId                                  CfprManagedObjectId,
    cfprExtmgmtArpTargetsDn                                          CfprManagedObjectDn,
    cfprExtmgmtArpTargetsRn                                          SnmpAdminString,
    cfprExtmgmtArpTargetsConfigState                                 CfprAaaConfigState,
    cfprExtmgmtArpTargetsConfigStatusMessage                         SnmpAdminString,
    cfprExtmgmtArpTargetsMaxDeadlineTimeout                          CfprExtmgmtArpTargetsMaxDeadlineTimeout,
    cfprExtmgmtArpTargetsNumberOfArpRequests                         CfprExtmgmtArpTargetsNumberOfArpRequests,
    cfprExtmgmtArpTargetsTargetIp1                                   InetAddressIPv4,
    cfprExtmgmtArpTargetsTargetIp2                                   InetAddressIPv4,
    cfprExtmgmtArpTargetsTargetIp3                                   InetAddressIPv4
}

cfprExtmgmtArpTargetsInstanceId OBJECT-TYPE
    SYNTAX       CfprManagedObjectId
    MAX-ACCESS   not-accessible
    STATUS       current
    DESCRIPTION
        "Instance identifier of the managed object."
    ::= { cfprExtmgmtArpTargetsEntry 1 }

cfprExtmgmtArpTargetsDn OBJECT-TYPE
    SYNTAX       CfprManagedObjectDn
    MAX-ACCESS   read-only
    STATUS       current
    DESCRIPTION
        "Cisco Firepower extmgmt:ArpTargets:dn managed object property"
    ::= { cfprExtmgmtArpTargetsEntry 2 }

cfprExtmgmtArpTargetsRn OBJECT-TYPE
    SYNTAX       SnmpAdminString
    MAX-ACCESS   read-only
    STATUS       current
    DESCRIPTION
        "Cisco Firepower extmgmt:ArpTargets:rn managed object property"
    ::= { cfprExtmgmtArpTargetsEntry 3 }

cfprExtmgmtArpTargetsConfigState OBJECT-TYPE
    SYNTAX       CfprAaaConfigState
    MAX-ACCESS   read-only
    STATUS       current
    DESCRIPTION
        "Cisco Firepower extmgmt:ArpTargets:configState
        managed object property"
    ::= { cfprExtmgmtArpTargetsEntry 4 }

cfprExtmgmtArpTargetsConfigStatusMessage OBJECT-TYPE
    SYNTAX       SnmpAdminString
    MAX-ACCESS   read-only
    STATUS       current
    DESCRIPTION
        "Cisco Firepower extmgmt:ArpTargets:configStatusMessage
        managed object property"
    ::= { cfprExtmgmtArpTargetsEntry 5 }

cfprExtmgmtArpTargetsMaxDeadlineTimeout OBJECT-TYPE
    SYNTAX       CfprExtmgmtArpTargetsMaxDeadlineTimeout
    MAX-ACCESS   read-only
    STATUS       current
    DESCRIPTION
        "Cisco Firepower extmgmt:ArpTargets:maxDeadlineTimeout
        managed object property"
    ::= { cfprExtmgmtArpTargetsEntry 6 }

cfprExtmgmtArpTargetsNumberOfArpRequests OBJECT-TYPE
    SYNTAX       CfprExtmgmtArpTargetsNumberOfArpRequests
    MAX-ACCESS   read-only
    STATUS       current
    DESCRIPTION
        "Cisco Firepower extmgmt:ArpTargets:numberOfArpRequests
        managed object property"
    ::= { cfprExtmgmtArpTargetsEntry 7 }

cfprExtmgmtArpTargetsTargetIp1 OBJECT-TYPE
    SYNTAX       InetAddressIPv4
    MAX-ACCESS   read-only
    STATUS       current
    DESCRIPTION
        "Cisco Firepower extmgmt:ArpTargets:targetIp1 managed
        object property"
    ::= { cfprExtmgmtArpTargetsEntry 8 }

cfprExtmgmtArpTargetsTargetIp2 OBJECT-TYPE
    SYNTAX       InetAddressIPv4
    MAX-ACCESS   read-only
    STATUS       current
    DESCRIPTION
        "Cisco Firepower extmgmt:ArpTargets:targetIp2 managed
        object property"
    ::= { cfprExtmgmtArpTargetsEntry 9 }

cfprExtmgmtArpTargetsTargetIp3 OBJECT-TYPE
    SYNTAX       InetAddressIPv4
    MAX-ACCESS   read-only
    STATUS       current
    DESCRIPTION
        "Cisco Firepower extmgmt:ArpTargets:targetIp3 managed
        object property"
    ::= { cfprExtmgmtArpTargetsEntry 10 }

cfprExtmgmtGatewayPingTable OBJECT-TYPE
    SYNTAX           SEQUENCE OF CfprExtmgmtGatewayPingEntry
    MAX-ACCESS       not-accessible
    STATUS           current
    DESCRIPTION
        "Cisco Firepower extmgmt:GatewayPing managed object table"
    ::= { cfprExtmgmtObjects 2 }

cfprExtmgmtGatewayPingEntry OBJECT-TYPE
    SYNTAX           CfprExtmgmtGatewayPingEntry
    MAX-ACCESS       not-accessible
    STATUS           current
    DESCRIPTION
        "Entry for the cfprExtmgmtGatewayPingTable table."
    INDEX { cfprExtmgmtGatewayPingInstanceId }
    ::= { cfprExtmgmtGatewayPingTable 1 }

CfprExtmgmtGatewayPingEntry ::= SEQUENCE {
    cfprExtmgmtGatewayPingInstanceId                                 CfprManagedObjectId,
    cfprExtmgmtGatewayPingDn                                         CfprManagedObjectDn,
    cfprExtmgmtGatewayPingRn                                         SnmpAdminString,
    cfprExtmgmtGatewayPingMaxDeadlineTimeout                         CfprExtmgmtGatewayPingMaxDeadlineTimeout,
    cfprExtmgmtGatewayPingNumberOfPingRequests                       CfprExtmgmtGatewayPingNumberOfPingRequests
}

cfprExtmgmtGatewayPingInstanceId OBJECT-TYPE
    SYNTAX       CfprManagedObjectId
    MAX-ACCESS   not-accessible
    STATUS       current
    DESCRIPTION
        "Instance identifier of the managed object."
    ::= { cfprExtmgmtGatewayPingEntry 1 }

cfprExtmgmtGatewayPingDn OBJECT-TYPE
    SYNTAX       CfprManagedObjectDn
    MAX-ACCESS   read-only
    STATUS       current
    DESCRIPTION
        "Cisco Firepower extmgmt:GatewayPing:dn managed object property"
    ::= { cfprExtmgmtGatewayPingEntry 2 }

cfprExtmgmtGatewayPingRn OBJECT-TYPE
    SYNTAX       SnmpAdminString
    MAX-ACCESS   read-only
    STATUS       current
    DESCRIPTION
        "Cisco Firepower extmgmt:GatewayPing:rn managed object property"
    ::= { cfprExtmgmtGatewayPingEntry 3 }

cfprExtmgmtGatewayPingMaxDeadlineTimeout OBJECT-TYPE
    SYNTAX       CfprExtmgmtGatewayPingMaxDeadlineTimeout
    MAX-ACCESS   read-only
    STATUS       current
    DESCRIPTION
        "Cisco Firepower extmgmt:GatewayPing:maxDeadlineTimeout
        managed object property"
    ::= { cfprExtmgmtGatewayPingEntry 4 }

cfprExtmgmtGatewayPingNumberOfPingRequests OBJECT-TYPE
    SYNTAX       CfprExtmgmtGatewayPingNumberOfPingRequests
    MAX-ACCESS   read-only
    STATUS       current
    DESCRIPTION
        "Cisco Firepower extmgmt:GatewayPing:numberOfPingRequests
        managed object property"
    ::= { cfprExtmgmtGatewayPingEntry 5 }

cfprExtmgmtIfTable OBJECT-TYPE
    SYNTAX           SEQUENCE OF CfprExtmgmtIfEntry
    MAX-ACCESS       not-accessible
    STATUS           current
    DESCRIPTION
        "Cisco Firepower extmgmt:If managed object table"
    ::= { cfprExtmgmtObjects 3 }

cfprExtmgmtIfEntry OBJECT-TYPE
    SYNTAX           CfprExtmgmtIfEntry
    MAX-ACCESS       not-accessible
    STATUS           current
    DESCRIPTION
        "Entry for the cfprExtmgmtIfTable table."
    INDEX { cfprExtmgmtIfInstanceId }
    ::= { cfprExtmgmtIfTable 1 }

CfprExtmgmtIfEntry ::= SEQUENCE {
    cfprExtmgmtIfInstanceId                                          CfprManagedObjectId,
    cfprExtmgmtIfDn                                                  CfprManagedObjectDn,
    cfprExtmgmtIfRn                                                  SnmpAdminString,
    cfprExtmgmtIfEpDn                                                SnmpAdminString,
    cfprExtmgmtIfFailReportCount                                     Gauge32,
    cfprExtmgmtIfFltAggr                                             Unsigned64,
    cfprExtmgmtIfId                                                  CfprNetworkSwitchId,
    cfprExtmgmtIfIfRole                                              CfprNetworkPortRole,
    cfprExtmgmtIfIfType                                              CfprNetworkPortType,
    cfprExtmgmtIfLastOperStateReport                                 CfprNetworkIfStatus,
    cfprExtmgmtIfLocale                                              CfprNetworkLocale,
    cfprExtmgmtIfName                                                SnmpAdminString,
    cfprExtmgmtIfOperState                                           CfprNetworkIfStatus,
    cfprExtmgmtIfPeerDn                                              SnmpAdminString,
    cfprExtmgmtIfTransport                                           CfprNetworkTransport,
    cfprExtmgmtIfType                                                CfprExtmgmtIfType,
    cfprExtmgmtIfFailureReason                                       CfprExtmgmtIfFailureReason
}

cfprExtmgmtIfInstanceId OBJECT-TYPE
    SYNTAX       CfprManagedObjectId
    MAX-ACCESS   not-accessible
    STATUS       current
    DESCRIPTION
        "Instance identifier of the managed object."
    ::= { cfprExtmgmtIfEntry 1 }

cfprExtmgmtIfDn OBJECT-TYPE
    SYNTAX       CfprManagedObjectDn
    MAX-ACCESS   read-only
    STATUS       current
    DESCRIPTION
        "Cisco Firepower extmgmt:If:dn managed object property"
    ::= { cfprExtmgmtIfEntry 2 }

cfprExtmgmtIfRn OBJECT-TYPE
    SYNTAX       SnmpAdminString
    MAX-ACCESS   read-only
    STATUS       current
    DESCRIPTION
        "Cisco Firepower extmgmt:If:rn managed object property"
    ::= { cfprExtmgmtIfEntry 3 }

cfprExtmgmtIfEpDn OBJECT-TYPE
    SYNTAX       SnmpAdminString
    MAX-ACCESS   read-only
    STATUS       current
    DESCRIPTION
        "Cisco Firepower extmgmt:If:epDn managed object property"
    ::= { cfprExtmgmtIfEntry 4 }

cfprExtmgmtIfFailReportCount OBJECT-TYPE
    SYNTAX       Gauge32
    MAX-ACCESS   read-only
    STATUS       current
    DESCRIPTION
        "Cisco Firepower extmgmt:If:failReportCount managed
        object property"
    ::= { cfprExtmgmtIfEntry 5 }

cfprExtmgmtIfFltAggr OBJECT-TYPE
    SYNTAX       Unsigned64
    MAX-ACCESS   read-only
    STATUS       current
    DESCRIPTION
        "Cisco Firepower extmgmt:If:fltAggr managed object property"
    ::= { cfprExtmgmtIfEntry 6 }

cfprExtmgmtIfId OBJECT-TYPE
    SYNTAX       CfprNetworkSwitchId
    MAX-ACCESS   read-only
    STATUS       current
    DESCRIPTION
        "Cisco Firepower extmgmt:If:id managed object property"
    ::= { cfprExtmgmtIfEntry 7 }

cfprExtmgmtIfIfRole OBJECT-TYPE
    SYNTAX       CfprNetworkPortRole
    MAX-ACCESS   read-only
    STATUS       current
    DESCRIPTION
        "Cisco Firepower extmgmt:If:ifRole managed object property"
    ::= { cfprExtmgmtIfEntry 8 }

cfprExtmgmtIfIfType OBJECT-TYPE
    SYNTAX       CfprNetworkPortType
    MAX-ACCESS   read-only
    STATUS       current
    DESCRIPTION
        "Cisco Firepower extmgmt:If:ifType managed object property"
    ::= { cfprExtmgmtIfEntry 9 }

cfprExtmgmtIfLastOperStateReport OBJECT-TYPE
    SYNTAX       CfprNetworkIfStatus
    MAX-ACCESS   read-only
    STATUS       current
    DESCRIPTION
        "Cisco Firepower extmgmt:If:lastOperStateReport
        managed object property"
    ::= { cfprExtmgmtIfEntry 10 }

cfprExtmgmtIfLocale OBJECT-TYPE
    SYNTAX       CfprNetworkLocale
    MAX-ACCESS   read-only
    STATUS       current
    DESCRIPTION
        "Cisco Firepower extmgmt:If:locale managed object property"
    ::= { cfprExtmgmtIfEntry 11 }

cfprExtmgmtIfName OBJECT-TYPE
    SYNTAX       SnmpAdminString
    MAX-ACCESS   read-only
    STATUS       current
    DESCRIPTION
        "Cisco Firepower extmgmt:If:name managed object property"
    ::= { cfprExtmgmtIfEntry 12 }

cfprExtmgmtIfOperState OBJECT-TYPE
    SYNTAX       CfprNetworkIfStatus
    MAX-ACCESS   read-only
    STATUS       current
    DESCRIPTION
        "Cisco Firepower extmgmt:If:operState managed object property"
    ::= { cfprExtmgmtIfEntry 13 }

cfprExtmgmtIfPeerDn OBJECT-TYPE
    SYNTAX       SnmpAdminString
    MAX-ACCESS   read-only
    STATUS       current
    DESCRIPTION
        "Cisco Firepower extmgmt:If:peerDn managed object property"
    ::= { cfprExtmgmtIfEntry 14 }

cfprExtmgmtIfTransport OBJECT-TYPE
    SYNTAX       CfprNetworkTransport
    MAX-ACCESS   read-only
    STATUS       current
    DESCRIPTION
        "Cisco Firepower extmgmt:If:transport managed object property"
    ::= { cfprExtmgmtIfEntry 15 }

cfprExtmgmtIfType OBJECT-TYPE
    SYNTAX       CfprExtmgmtIfType
    MAX-ACCESS   read-only
    STATUS       current
    DESCRIPTION
        "Cisco Firepower extmgmt:If:type managed object property"
    ::= { cfprExtmgmtIfEntry 16 }

cfprExtmgmtIfFailureReason OBJECT-TYPE
    SYNTAX       CfprExtmgmtIfFailureReason
    MAX-ACCESS   read-only
    STATUS       current
    DESCRIPTION
        "Cisco Firepower extmgmt:If:failureReason managed object property"
    ::= { cfprExtmgmtIfEntry 17 }

cfprExtmgmtIfMonPolicyTable OBJECT-TYPE
    SYNTAX           SEQUENCE OF CfprExtmgmtIfMonPolicyEntry
    MAX-ACCESS       not-accessible
    STATUS           current
    DESCRIPTION
        "Cisco Firepower extmgmt:IfMonPolicy managed object table"
    ::= { cfprExtmgmtObjects 4 }

cfprExtmgmtIfMonPolicyEntry OBJECT-TYPE
    SYNTAX           CfprExtmgmtIfMonPolicyEntry
    MAX-ACCESS       not-accessible
    STATUS           current
    DESCRIPTION
        "Entry for the cfprExtmgmtIfMonPolicyTable table."
    INDEX { cfprExtmgmtIfMonPolicyInstanceId }
    ::= { cfprExtmgmtIfMonPolicyTable 1 }

CfprExtmgmtIfMonPolicyEntry ::= SEQUENCE {
    cfprExtmgmtIfMonPolicyInstanceId                                 CfprManagedObjectId,
    cfprExtmgmtIfMonPolicyDn                                         CfprManagedObjectDn,
    cfprExtmgmtIfMonPolicyRn                                         SnmpAdminString,
    cfprExtmgmtIfMonPolicyAdminState                                 CfprExtmgmtIfMonPolicyAdminState,
    cfprExtmgmtIfMonPolicyDescr                                      SnmpAdminString,
    cfprExtmgmtIfMonPolicyEnableHAFailover                           TruthValue,
    cfprExtmgmtIfMonPolicyIntId                                      SnmpAdminString,
    cfprExtmgmtIfMonPolicyMaxFailReportCount                         Gauge32,
    cfprExtmgmtIfMonPolicyMonitorMechanism                           CfprExtmgmtIfMonPolicyMonitorMechanism,
    cfprExtmgmtIfMonPolicyName                                       SnmpAdminString,
    cfprExtmgmtIfMonPolicyPolicyLevel                                Gauge32,
    cfprExtmgmtIfMonPolicyPolicyOwner                                CfprPolicyPolicyOwner,
    cfprExtmgmtIfMonPolicyPollInterval                               Gauge32
}

cfprExtmgmtIfMonPolicyInstanceId OBJECT-TYPE
    SYNTAX       CfprManagedObjectId
    MAX-ACCESS   not-accessible
    STATUS       current
    DESCRIPTION
        "Instance identifier of the managed object."
    ::= { cfprExtmgmtIfMonPolicyEntry 1 }

cfprExtmgmtIfMonPolicyDn OBJECT-TYPE
    SYNTAX       CfprManagedObjectDn
    MAX-ACCESS   read-only
    STATUS       current
    DESCRIPTION
        "Cisco Firepower extmgmt:IfMonPolicy:dn managed object property"
    ::= { cfprExtmgmtIfMonPolicyEntry 2 }

cfprExtmgmtIfMonPolicyRn OBJECT-TYPE
    SYNTAX       SnmpAdminString
    MAX-ACCESS   read-only
    STATUS       current
    DESCRIPTION
        "Cisco Firepower extmgmt:IfMonPolicy:rn managed object property"
    ::= { cfprExtmgmtIfMonPolicyEntry 3 }

cfprExtmgmtIfMonPolicyAdminState OBJECT-TYPE
    SYNTAX       CfprExtmgmtIfMonPolicyAdminState
    MAX-ACCESS   read-only
    STATUS       current
    DESCRIPTION
        "Cisco Firepower extmgmt:IfMonPolicy:adminState
        managed object property"
    ::= { cfprExtmgmtIfMonPolicyEntry 4 }

cfprExtmgmtIfMonPolicyDescr OBJECT-TYPE
    SYNTAX       SnmpAdminString
    MAX-ACCESS   read-only
    STATUS       current
    DESCRIPTION
        "Cisco Firepower extmgmt:IfMonPolicy:descr managed
        object property"
    ::= { cfprExtmgmtIfMonPolicyEntry 5 }

cfprExtmgmtIfMonPolicyEnableHAFailover OBJECT-TYPE
    SYNTAX       TruthValue
    MAX-ACCESS   read-only
    STATUS       current
    DESCRIPTION
        "Cisco Firepower extmgmt:IfMonPolicy:enableHAFailover
        managed object property"
    ::= { cfprExtmgmtIfMonPolicyEntry 6 }

cfprExtmgmtIfMonPolicyIntId OBJECT-TYPE
    SYNTAX       SnmpAdminString
    MAX-ACCESS   read-only
    STATUS       current
    DESCRIPTION
        "Cisco Firepower extmgmt:IfMonPolicy:intId managed
        object property"
    ::= { cfprExtmgmtIfMonPolicyEntry 7 }

cfprExtmgmtIfMonPolicyMaxFailReportCount OBJECT-TYPE
    SYNTAX       Gauge32
    MAX-ACCESS   read-only
    STATUS       current
    DESCRIPTION
        "Cisco Firepower extmgmt:IfMonPolicy:maxFailReportCount
        managed object property"
    ::= { cfprExtmgmtIfMonPolicyEntry 8 }

cfprExtmgmtIfMonPolicyMonitorMechanism OBJECT-TYPE
    SYNTAX       CfprExtmgmtIfMonPolicyMonitorMechanism
    MAX-ACCESS   read-only
    STATUS       current
    DESCRIPTION
        "Cisco Firepower extmgmt:IfMonPolicy:monitorMechanism
        managed object property"
    ::= { cfprExtmgmtIfMonPolicyEntry 9 }

cfprExtmgmtIfMonPolicyName OBJECT-TYPE
    SYNTAX       SnmpAdminString
    MAX-ACCESS   read-only
    STATUS       current
    DESCRIPTION
        "Cisco Firepower extmgmt:IfMonPolicy:name managed object property"
    ::= { cfprExtmgmtIfMonPolicyEntry 10 }

cfprExtmgmtIfMonPolicyPolicyLevel OBJECT-TYPE
    SYNTAX       Gauge32
    MAX-ACCESS   read-only
    STATUS       current
    DESCRIPTION
        "Cisco Firepower extmgmt:IfMonPolicy:policyLevel
        managed object property"
    ::= { cfprExtmgmtIfMonPolicyEntry 11 }

cfprExtmgmtIfMonPolicyPolicyOwner OBJECT-TYPE
    SYNTAX       CfprPolicyPolicyOwner
    MAX-ACCESS   read-only
    STATUS       current
    DESCRIPTION
        "Cisco Firepower extmgmt:IfMonPolicy:policyOwner
        managed object property"
    ::= { cfprExtmgmtIfMonPolicyEntry 12 }

cfprExtmgmtIfMonPolicyPollInterval OBJECT-TYPE
    SYNTAX       Gauge32
    MAX-ACCESS   read-only
    STATUS       current
    DESCRIPTION
        "Cisco Firepower extmgmt:IfMonPolicy:pollInterval
        managed object property"
    ::= { cfprExtmgmtIfMonPolicyEntry 13 }

cfprExtmgmtMiiStatusTable OBJECT-TYPE
    SYNTAX           SEQUENCE OF CfprExtmgmtMiiStatusEntry
    MAX-ACCESS       not-accessible
    STATUS           current
    DESCRIPTION
        "Cisco Firepower extmgmt:MiiStatus managed object table"
    ::= { cfprExtmgmtObjects 5 }

cfprExtmgmtMiiStatusEntry OBJECT-TYPE
    SYNTAX           CfprExtmgmtMiiStatusEntry
    MAX-ACCESS       not-accessible
    STATUS           current
    DESCRIPTION
        "Entry for the cfprExtmgmtMiiStatusTable table."
    INDEX { cfprExtmgmtMiiStatusInstanceId }
    ::= { cfprExtmgmtMiiStatusTable 1 }

CfprExtmgmtMiiStatusEntry ::= SEQUENCE {
    cfprExtmgmtMiiStatusInstanceId                                   CfprManagedObjectId,
    cfprExtmgmtMiiStatusDn                                           CfprManagedObjectDn,
    cfprExtmgmtMiiStatusRn                                           SnmpAdminString,
    cfprExtmgmtMiiStatusMaxRetryCount                                CfprExtmgmtMiiStatusMaxRetryCount,
    cfprExtmgmtMiiStatusRetryInterval                                CfprExtmgmtMiiStatusRetryInterval
}

cfprExtmgmtMiiStatusInstanceId OBJECT-TYPE
    SYNTAX       CfprManagedObjectId
    MAX-ACCESS   not-accessible
    STATUS       current
    DESCRIPTION
        "Instance identifier of the managed object."
    ::= { cfprExtmgmtMiiStatusEntry 1 }

cfprExtmgmtMiiStatusDn OBJECT-TYPE
    SYNTAX       CfprManagedObjectDn
    MAX-ACCESS   read-only
    STATUS       current
    DESCRIPTION
        "Cisco Firepower extmgmt:MiiStatus:dn managed object property"
    ::= { cfprExtmgmtMiiStatusEntry 2 }

cfprExtmgmtMiiStatusRn OBJECT-TYPE
    SYNTAX       SnmpAdminString
    MAX-ACCESS   read-only
    STATUS       current
    DESCRIPTION
        "Cisco Firepower extmgmt:MiiStatus:rn managed object property"
    ::= { cfprExtmgmtMiiStatusEntry 3 }

cfprExtmgmtMiiStatusMaxRetryCount OBJECT-TYPE
    SYNTAX       CfprExtmgmtMiiStatusMaxRetryCount
    MAX-ACCESS   read-only
    STATUS       current
    DESCRIPTION
        "Cisco Firepower extmgmt:MiiStatus:maxRetryCount
        managed object property"
    ::= { cfprExtmgmtMiiStatusEntry 4 }

cfprExtmgmtMiiStatusRetryInterval OBJECT-TYPE
    SYNTAX       CfprExtmgmtMiiStatusRetryInterval
    MAX-ACCESS   read-only
    STATUS       current
    DESCRIPTION
        "Cisco Firepower extmgmt:MiiStatus:retryInterval
        managed object property"
    ::= { cfprExtmgmtMiiStatusEntry 5 }

cfprExtmgmtNdiscTargetsTable OBJECT-TYPE
    SYNTAX           SEQUENCE OF CfprExtmgmtNdiscTargetsEntry
    MAX-ACCESS       not-accessible
    STATUS           current
    DESCRIPTION
        "Cisco Firepower extmgmt:NdiscTargets managed object table"
    ::= { cfprExtmgmtObjects 6 }

cfprExtmgmtNdiscTargetsEntry OBJECT-TYPE
    SYNTAX           CfprExtmgmtNdiscTargetsEntry
    MAX-ACCESS       not-accessible
    STATUS           current
    DESCRIPTION
        "Entry for the cfprExtmgmtNdiscTargetsTable table."
    INDEX { cfprExtmgmtNdiscTargetsInstanceId }
    ::= { cfprExtmgmtNdiscTargetsTable 1 }

CfprExtmgmtNdiscTargetsEntry ::= SEQUENCE {
    cfprExtmgmtNdiscTargetsInstanceId                                CfprManagedObjectId,
    cfprExtmgmtNdiscTargetsDn                                        CfprManagedObjectDn,
    cfprExtmgmtNdiscTargetsRn                                        SnmpAdminString,
    cfprExtmgmtNdiscTargetsConfigState                               CfprAaaConfigState,
    cfprExtmgmtNdiscTargetsConfigStatusMessage                       SnmpAdminString,
    cfprExtmgmtNdiscTargetsIpv6Target1                               InetAddressIPv6,
    cfprExtmgmtNdiscTargetsIpv6Target2                               InetAddressIPv6,
    cfprExtmgmtNdiscTargetsIpv6Target3                               InetAddressIPv6,
    cfprExtmgmtNdiscTargetsMaxDeadlineTimeout                        CfprExtmgmtNdiscTargetsMaxDeadlineTimeout,
    cfprExtmgmtNdiscTargetsNumberOfNdiscRequests                     CfprExtmgmtNdiscTargetsNumberOfNdiscRequests
}

cfprExtmgmtNdiscTargetsInstanceId OBJECT-TYPE
    SYNTAX       CfprManagedObjectId
    MAX-ACCESS   not-accessible
    STATUS       current
    DESCRIPTION
        "Instance identifier of the managed object."
    ::= { cfprExtmgmtNdiscTargetsEntry 1 }

cfprExtmgmtNdiscTargetsDn OBJECT-TYPE
    SYNTAX       CfprManagedObjectDn
    MAX-ACCESS   read-only
    STATUS       current
    DESCRIPTION
        "Cisco Firepower extmgmt:NdiscTargets:dn managed object property"
    ::= { cfprExtmgmtNdiscTargetsEntry 2 }

cfprExtmgmtNdiscTargetsRn OBJECT-TYPE
    SYNTAX       SnmpAdminString
    MAX-ACCESS   read-only
    STATUS       current
    DESCRIPTION
        "Cisco Firepower extmgmt:NdiscTargets:rn managed object property"
    ::= { cfprExtmgmtNdiscTargetsEntry 3 }

cfprExtmgmtNdiscTargetsConfigState OBJECT-TYPE
    SYNTAX       CfprAaaConfigState
    MAX-ACCESS   read-only
    STATUS       current
    DESCRIPTION
        "Cisco Firepower extmgmt:NdiscTargets:configState
        managed object property"
    ::= { cfprExtmgmtNdiscTargetsEntry 4 }

cfprExtmgmtNdiscTargetsConfigStatusMessage OBJECT-TYPE
    SYNTAX       SnmpAdminString
    MAX-ACCESS   read-only
    STATUS       current
    DESCRIPTION
        "Cisco Firepower extmgmt:NdiscTargets:configStatusMessage
        managed object property"
    ::= { cfprExtmgmtNdiscTargetsEntry 5 }

cfprExtmgmtNdiscTargetsIpv6Target1 OBJECT-TYPE
    SYNTAX       InetAddressIPv6
    MAX-ACCESS   read-only
    STATUS       current
    DESCRIPTION
        "Cisco Firepower extmgmt:NdiscTargets:ipv6Target1
        managed object property"
    ::= { cfprExtmgmtNdiscTargetsEntry 6 }

cfprExtmgmtNdiscTargetsIpv6Target2 OBJECT-TYPE
    SYNTAX       InetAddressIPv6
    MAX-ACCESS   read-only
    STATUS       current
    DESCRIPTION
        "Cisco Firepower extmgmt:NdiscTargets:ipv6Target2
        managed object property"
    ::= { cfprExtmgmtNdiscTargetsEntry 7 }

cfprExtmgmtNdiscTargetsIpv6Target3 OBJECT-TYPE
    SYNTAX       InetAddressIPv6
    MAX-ACCESS   read-only
    STATUS       current
    DESCRIPTION
        "Cisco Firepower extmgmt:NdiscTargets:ipv6Target3
        managed object property"
    ::= { cfprExtmgmtNdiscTargetsEntry 8 }

cfprExtmgmtNdiscTargetsMaxDeadlineTimeout OBJECT-TYPE
    SYNTAX       CfprExtmgmtNdiscTargetsMaxDeadlineTimeout
    MAX-ACCESS   read-only
    STATUS       current
    DESCRIPTION
        "Cisco Firepower extmgmt:NdiscTargets:maxDeadlineTimeout
        managed object property"
    ::= { cfprExtmgmtNdiscTargetsEntry 9 }

cfprExtmgmtNdiscTargetsNumberOfNdiscRequests OBJECT-TYPE
    SYNTAX       CfprExtmgmtNdiscTargetsNumberOfNdiscRequests
    MAX-ACCESS   read-only
    STATUS       current
    DESCRIPTION
        "Cisco Firepower extmgmt:NdiscTargets:numberOfNdiscRequests
        managed object property"
    ::= { cfprExtmgmtNdiscTargetsEntry 10 }

END
