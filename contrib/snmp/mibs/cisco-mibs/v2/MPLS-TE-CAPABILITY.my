-- *****************************************************************
-- MPLS-TE-CAPABILITY.my:  Capability statement for MPLS Traffic 
--                         Engineering MIB
--
-- Sept 2001, Michael T Piecuch
--
-- Copyright (c) 2000, 2001, 2003 by cisco Systems, Inc.
-- All rights reserved.
-- 
-- *****************************************************************

MPLS-TE-CAPABILITY DEFINITIONS ::= BEGIN

IMPORTS
   MODULE-IDENTITY
      FROM SNMPv2-SMI

   AGENT-CAPABILITIES 
      FROM SNMPv2-CONF

  ciscoAgentCapability
      FROM CISCO-SMI;

mplsTeCapability MODULE-IDENTITY
   LAST-UPDATED
      "200308131200Z" -- 13 Aug 2003 12:00:00 EST
   ORGANIZATION
      "Cisco Systems, Inc."
   CONTACT-INFO
          "             Cisco Systems
                        Customer Service

                Postal: 170 W. Tasman Drive
                        San Jose, CA  95134
                        USA

                Tel: +1 800 553-NETS

                E-mail: support@cisco.com"
   DESCRIPTION
          "Agent capabilities for MPLS-TE-MIB"

   -- Revision history.

   REVISION
          "200308131200Z" -- 13 Aug 2003 12:00:00 EST
   DESCRIPTION
          "Adding missing IMPORT for ciscoAgentCapability."
   REVISION
          "200109181200Z"  -- 18 September 2001 12:00:00 EST
   DESCRIPTION
          "Added section mplsTeCapabilityV10R00 for trap support"
   REVISION
          "200103291200Z"  -- 29 March 2001 12:00:00 EST
   DESCRIPTION
          "Initial draft version."

   ::= { ciscoAgentCapability 213 }

mplsTeCapability AGENT-CAPABILITIES

PRODUCT-RELEASE "Cisco IOS 12.0(16)S, 12.0(14)ST, 12.2(1)T"
STATUS      current
DESCRIPTION "MPLS Traffic Engineering MIB capabilities"

SUPPORTS    MPLS-TE-MIB
INCLUDES    { mplsTunnelGroup, mplsTunnelManualGroup, 
              mplsTunnelSignaledGroup, mplsTunnelScalarGroup,
              mplsTunnelIsIntfcGroup, mplsTunnelIsNotIntfcGroup,
              mplsTunnelOptionalGroup }


-- mplsTunnelTable

    VARIATION mplsTunnelName
      ACCESS read-only
      DESCRIPTION "read-only implementation"

    VARIATION mplsTunnelDescr
      ACCESS read-only
      DESCRIPTION "read-only implementation"

    VARIATION mplsTunnelIsIf
      ACCESS read-only
      DESCRIPTION "read-only implementation"

    VARIATION mplsTunnelXCPointer
      ACCESS read-only
      DESCRIPTION "read-only implementation (applicable only to midpoint LSPs)"

    VARIATION mplsTunnelSignallingProto
      ACCESS read-only
      DESCRIPTION "read-only implementation"

    VARIATION mplsTunnelSetupPrio
      ACCESS read-only
      DESCRIPTION "read-only implementation"

    VARIATION mplsTunnelHoldingPrio
      ACCESS read-only
      DESCRIPTION "read-only implementation"

    VARIATION mplsTunnelSessionAttributes
      ACCESS read-only
      DESCRIPTION "read-only implementation"

    VARIATION mplsTunnelOwner
      ACCESS read-only
      DESCRIPTION "read-only implementation"

    VARIATION mplsTunnelLocalProtectInUse
      ACCESS read-only
      DESCRIPTION "read-only implementation (always false)"

    VARIATION mplsTunnelResourcePointer
      ACCESS read-only
      DESCRIPTION "read-only implementation"

    VARIATION mplsTunnelInstancePriority
      ACCESS read-only
      DESCRIPTION "read-only implementation (always 0)"

    VARIATION mplsTunnelHopTableIndex
      ACCESS read-only
      DESCRIPTION "read-only implementation"

    VARIATION mplsTunnelIncludeAnyAffinity
      ACCESS read-only
      DESCRIPTION "read-only implementation"

    VARIATION mplsTunnelIncludeAllAffinity
      ACCESS read-only
      DESCRIPTION "read-only implementation"

    VARIATION mplsTunnelExcludeAllAffinity
      ACCESS read-only
      DESCRIPTION "read-only implementation"

    VARIATION mplsTunnelPathInUse
      ACCESS read-only
      DESCRIPTION "read-only implementation"

    VARIATION mplsTunnelRole
      ACCESS read-only
      DESCRIPTION "read-only implementation"

    VARIATION mplsTunnelTotalUpTime
      ACCESS read-only
      DESCRIPTION "read-only implementation"

    VARIATION mplsTunnelInstanceUpTime
      ACCESS read-only
      DESCRIPTION "read-only implementation (always 0)"

    VARIATION mplsTunnelAdminStatus
      ACCESS read-only
      DESCRIPTION "read-only implementation"

    VARIATION mplsTunnelRowStatus
      ACCESS read-only
      DESCRIPTION "read-only implementation"

    VARIATION mplsTunnelStorageType
      ACCESS read-only
      DESCRIPTION "read-only implementation"

-- mplsTunnelHopTable

    VARIATION mplsTunnelHopAddrType
      ACCESS read-only
      DESCRIPTION "read-only implementation"

    VARIATION mplsTunnelHopIpv4Addr
      ACCESS read-only
      DESCRIPTION "read-only implementation"

    VARIATION mplsTunnelHopIpv4PrefixLen
      ACCESS read-only
      DESCRIPTION "read-only implementation"

    VARIATION mplsTunnelHopIpv6Addr
      ACCESS read-only
      DESCRIPTION "read-only implementation"

    VARIATION mplsTunnelHopIpv6PrefixLen
      ACCESS read-only
      DESCRIPTION "read-only implementation"

    VARIATION mplsTunnelHopAsNumber
      ACCESS read-only
      DESCRIPTION "read-only implementation"

    VARIATION mplsTunnelHopLspId
      ACCESS read-only
      DESCRIPTION "read-only implementation"

    VARIATION mplsTunnelHopType
      ACCESS read-only
      DESCRIPTION "read-only implementation"

    VARIATION mplsTunnelHopRowStatus
      ACCESS read-only
      DESCRIPTION "read-only implementation"

    VARIATION mplsTunnelHopStorageType
      ACCESS read-only
      DESCRIPTION "read-only implementation"

-- mplsTunnelResourceEntry

    VARIATION mplsTunnelResourceMaxRate
      ACCESS read-only
      DESCRIPTION "read-only implementation"

    VARIATION mplsTunnelResourceMeanRate
      ACCESS read-only
      DESCRIPTION "read-only implementation"

    VARIATION mplsTunnelResourceMaxBurstSize
      ACCESS read-only
      DESCRIPTION "read-only implementation"

    VARIATION mplsTunnelResourceRowStatus
      ACCESS read-only
      DESCRIPTION "read-only implementation"

    VARIATION mplsTunnelResourceStorageType
      ACCESS read-only
      DESCRIPTION "read-only implementation"

-- Traps

    VARIATION mplsTunnelTrapEnable
      ACCESS read-only
      DESCRIPTION "Traps not supported"

 
    ::= { mplsTeCapability 1 }

mplsTeCapabilityV10R00 AGENT-CAPABILITIES

PRODUCT-RELEASE "Cisco IOS 12.0(17)S, 12.0(17)ST, 12.2(3)T"
STATUS      current
DESCRIPTION "MPLS Traffic Engineering MIB capabilities with trap support"

SUPPORTS    MPLS-TE-MIB

INCLUDES    { mplsTunnelGroup, mplsTunnelManualGroup, 
              mplsTunnelSignaledGroup, mplsTunnelScalarGroup,
              mplsTunnelIsIntfcGroup, mplsTunnelIsNotIntfcGroup,
              mplsTunnelOptionalGroup }


-- mplsTunnelTable

    VARIATION mplsTunnelName
      ACCESS read-only
      DESCRIPTION "read-only implementation"

    VARIATION mplsTunnelDescr
      ACCESS read-only
      DESCRIPTION "read-only implementation"

    VARIATION mplsTunnelIsIf
      ACCESS read-only
      DESCRIPTION "read-only implementation"

    VARIATION mplsTunnelXCPointer
      ACCESS read-only
      DESCRIPTION "read-only implementation (applicable only to midpoint LSPs)"

    VARIATION mplsTunnelSignallingProto
      ACCESS read-only
      DESCRIPTION "read-only implementation"

    VARIATION mplsTunnelSetupPrio
      ACCESS read-only
      DESCRIPTION "read-only implementation"

    VARIATION mplsTunnelHoldingPrio
      ACCESS read-only
      DESCRIPTION "read-only implementation"

    VARIATION mplsTunnelSessionAttributes
      ACCESS read-only
      DESCRIPTION "read-only implementation"

    VARIATION mplsTunnelOwner
      ACCESS read-only
      DESCRIPTION "read-only implementation"

    VARIATION mplsTunnelLocalProtectInUse
      ACCESS read-only
      DESCRIPTION "read-only implementation (always false)"

    VARIATION mplsTunnelResourcePointer
      ACCESS read-only
      DESCRIPTION "read-only implementation"

    VARIATION mplsTunnelInstancePriority
      ACCESS read-only
      DESCRIPTION "read-only implementation (always 0)"

    VARIATION mplsTunnelHopTableIndex
      ACCESS read-only
      DESCRIPTION "read-only implementation"

    VARIATION mplsTunnelIncludeAnyAffinity
      ACCESS read-only
      DESCRIPTION "read-only implementation"

    VARIATION mplsTunnelIncludeAllAffinity
      ACCESS read-only
      DESCRIPTION "read-only implementation"

    VARIATION mplsTunnelExcludeAllAffinity
      ACCESS read-only
      DESCRIPTION "read-only implementation"

    VARIATION mplsTunnelPathInUse
      ACCESS read-only
      DESCRIPTION "read-only implementation"

    VARIATION mplsTunnelRole
      ACCESS read-only
      DESCRIPTION "read-only implementation"

    VARIATION mplsTunnelTotalUpTime
      ACCESS read-only
      DESCRIPTION "read-only implementation"

    VARIATION mplsTunnelInstanceUpTime
      ACCESS read-only
      DESCRIPTION "read-only implementation (always 0)"

    VARIATION mplsTunnelAdminStatus
      ACCESS read-only
      DESCRIPTION "read-only implementation"

    VARIATION mplsTunnelRowStatus
      ACCESS read-only
      DESCRIPTION "read-only implementation"

    VARIATION mplsTunnelStorageType
      ACCESS read-only
      DESCRIPTION "read-only implementation"

-- mplsTunnelHopTable

    VARIATION mplsTunnelHopAddrType
      ACCESS read-only
      DESCRIPTION "read-only implementation"

    VARIATION mplsTunnelHopIpv4Addr
      ACCESS read-only
      DESCRIPTION "read-only implementation"

    VARIATION mplsTunnelHopIpv4PrefixLen
      ACCESS read-only
      DESCRIPTION "read-only implementation"

    VARIATION mplsTunnelHopIpv6Addr
      ACCESS read-only
      DESCRIPTION "read-only implementation"

    VARIATION mplsTunnelHopIpv6PrefixLen
      ACCESS read-only
      DESCRIPTION "read-only implementation"

    VARIATION mplsTunnelHopAsNumber
      ACCESS read-only
      DESCRIPTION "read-only implementation"

    VARIATION mplsTunnelHopLspId
      ACCESS read-only
      DESCRIPTION "read-only implementation"

    VARIATION mplsTunnelHopType
      ACCESS read-only
      DESCRIPTION "read-only implementation"

    VARIATION mplsTunnelHopRowStatus
      ACCESS read-only
      DESCRIPTION "read-only implementation"

    VARIATION mplsTunnelHopStorageType
      ACCESS read-only
      DESCRIPTION "read-only implementation"

-- mplsTunnelResourceEntry

    VARIATION mplsTunnelResourceMaxRate
      ACCESS read-only
      DESCRIPTION "read-only implementation"

    VARIATION mplsTunnelResourceMeanRate
      ACCESS read-only
      DESCRIPTION "read-only implementation"

    VARIATION mplsTunnelResourceMaxBurstSize
      ACCESS read-only
      DESCRIPTION "read-only implementation"

    VARIATION mplsTunnelResourceRowStatus
      ACCESS read-only
      DESCRIPTION "read-only implementation"

    VARIATION mplsTunnelResourceStorageType
      ACCESS read-only
      DESCRIPTION "read-only implementation"


    ::= { mplsTeCapability 2 }

END
