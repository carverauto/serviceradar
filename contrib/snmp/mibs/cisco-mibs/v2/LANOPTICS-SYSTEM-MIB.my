-- *****************************************************************
-- L A N O P T I C S - S Y S T E M - M I B . m y
-- 
-- March 1996, Keith Horil
--
-- Copyright (c) 1996 by cisco Systems, Inc.
-- All rights reserved.
-- *****************************************************************
--
-- This mib was developed by LanOptics


LANOPTICS-SYSTEM-MIB DEFINITIONS ::= BEGIN

IMPORTS 
        OBJECT-TYPE
                FROM RFC-1212
         enterprises, IpAddress
       	        FROM RFC1155-SMI
         DisplayString
                FROM RFC1213-MIB;

   lanOptics    OBJECT IDENTIFIER  ::= { enterprises 224 }
   lanOpticsSystem    OBJECT IDENTIFIER ::= { lanOptics 2 }
   lanOpticsSystemCMOS       OBJECT IDENTIFIER ::= { lanOpticsSystem 3 }
   lanOpticsSystemCMOSIp     OBJECT IDENTIFIER ::= { lanOpticsSystemCMOS 1 }
   lanOpticsSystemCMOSHub    OBJECT IDENTIFIER ::= { lanOpticsSystemCMOS 2 }
   lanOpticsSystemCMOSRPL    OBJECT IDENTIFIER ::= { lanOpticsSystemCMOS 3 }
   lanOpticsSystemCMOSSerial OBJECT IDENTIFIER ::= { lanOpticsSystemCMOS 4 }
   lanOpticsSystemCMOSSRAM   OBJECT IDENTIFIER ::= { lanOpticsSystemCMOS 5 }
   lanOpticsSystemCMOSSNMP   OBJECT IDENTIFIER ::= { lanOpticsSystemCMOS 6 }
   lanOpticsSystemCMOSACCESS OBJECT IDENTIFIER ::= { lanOpticsSystemCMOS 7 }
   lanOpticsSystemCMOSBRDG   OBJECT IDENTIFIER ::= { lanOpticsSystemCMOS 8 }

   snSysDirectory OBJECT-TYPE
   	     SYNTAX  DisplayString
   	     ACCESS  read-only
   	     STATUS  mandatory
   	     DESCRIPTION
   		"Gives the agent directory content
                    (make DOS DIR command on agent directory)."
   	     ::= { lanOpticsSystem 1 }

   snAgentVersion OBJECT-TYPE
   	     SYNTAX  INTEGER
   	     ACCESS  read-only
   	     STATUS  mandatory
   	     DESCRIPTION
   		"Gives the agent major version in the high order word
                 and the minor version in low order word."
   	     ::= { lanOpticsSystem 2 }


   snSysCMOSIpInterfaceTable OBJECT-TYPE
             SYNTAX  SEQUENCE OF SnSysCMOSIpInterfaceEntry
             ACCESS  not-accessible
             STATUS  mandatory
             DESCRIPTION
             "A list of network interfaces."
            ::= { lanOpticsSystemCMOSIp 1 }

   snSysCMOSIpInterfaceEntry     OBJECT-TYPE
            SYNTAX                SnSysCMOSIpInterfaceEntry
            ACCESS  not-accessible
            STATUS                mandatory
            DESCRIPTION
            "An interface entry containing the Ipaddress and net-mask."
            INDEX {INTEGER }
            ::=   { snSysCMOSIpInterfaceTable 1 }

   SnSysCMOSIpInterfaceEntry ::= SEQUENCE {
            snSysCMOSIpIpAddr 
              IpAddress,
            snSysCMOSIpNetMask
              IpAddress
   }

   snSysCMOSIpIpAddr OBJECT-TYPE
   	     SYNTAX  IpAddress
             ACCESS     read-write
   	     STATUS  mandatory
   	     DESCRIPTION
   		"Gives the interface's IpAddress"
   	     ::= { snSysCMOSIpInterfaceEntry 1}


   snSysCMOSIpNetMask OBJECT-TYPE
   	     SYNTAX  IpAddress
             ACCESS     read-write
   	     STATUS  mandatory
   	     DESCRIPTION
   		"Gives the interfaces's netmask"
   	     ::= { snSysCMOSIpInterfaceEntry 2 }



   snSysCMOSIpDefGw OBJECT-TYPE
   	     SYNTAX  IpAddress
             ACCESS     read-write
   	     STATUS  mandatory
   	     DESCRIPTION
   		"Gives the agent's default gateway."
   	     ::= { lanOpticsSystemCMOSIp 2 }

   snSysCMOSIpTFTPOp OBJECT-TYPE
   	     SYNTAX  INTEGER {
                noTFTP (1),
                limited (2),
                continuous (3)
             }
             ACCESS  read-write
   	     STATUS  mandatory
   	     DESCRIPTION
   		"Gives the TFTP policy:
                  1 - No TFTP, 2 - Optional, 3 - Always"
   	     ::= { lanOpticsSystemCMOSIp 3 }

   snSysCMOSIpTFTPAddr OBJECT-TYPE
   	     SYNTAX  IpAddress
             ACCESS  read-write
   	     STATUS  mandatory
   	     DESCRIPTION
   		"Gives the TFTP server Ip address."
   	     ::= { lanOpticsSystemCMOSIp 4 }

   snSysCMOSIpTFTPFileName OBJECT-TYPE
   	     SYNTAX  DisplayString
             ACCESS  read-write
   	     STATUS  mandatory
   	     DESCRIPTION
   		"Gives the boot file name at the server (full path)."
   	     ::= { lanOpticsSystemCMOSIp 5 }

   snSysCMOSIpTFTPDrive OBJECT-TYPE
   	     SYNTAX  INTEGER {
                driveA (41),
                driveB (42),
                driveC (43),
                driveD (44)
             }
             ACCESS  read-write
   	     STATUS  mandatory
   	     DESCRIPTION
   		"Gives the TFTP operation destination drive 
                (value of ASCII character)."
   	     ::= { lanOpticsSystemCMOSIp 6 }

   snSysCMOSHubSlotConfigTable OBJECT-TYPE
             SYNTAX  SEQUENCE OF SnSysCMOSHubSlotConfigEntry
             ACCESS  not-accessible
             STATUS  mandatory
             DESCRIPTION
             "A list of slots entries. Each entry in this table, 
              contains the last 20 operations performed on the slot."
            ::= { lanOpticsSystemCMOSHub 1 }

   snSysCMOSHubSlotConfigEntry OBJECT-TYPE
                    SYNTAX  SnSysCMOSHubSlotConfigEntry
                    ACCESS  not-accessible
                    STATUS  mandatory
                    INDEX {INTEGER }
                    ::= { snSysCMOSHubSlotConfigTable 1 }

   SnSysCMOSHubSlotConfigEntry  ::= SEQUENCE {
         snSysSlotLastOperations 
             OCTET STRING,
         snSysResetSlotQueue 
             INTEGER
   }

   snSysSlotLastOperations  OBJECT-TYPE        
        SYNTAX OCTET STRING      
              ACCESS   read-write
              STATUS   mandatory
              DESCRIPTION
              " A description of last 20 operations performed,
                on the slot"
              ::= { snSysCMOSHubSlotConfigEntry 1 }

   snSysResetSlotQueue OBJECT-TYPE
             SYNTAX  INTEGER
             ACCESS  read-write
             STATUS  mandatory
             DESCRIPTION
             " Resets the last 20 operations queue."
              ::= { snSysCMOSHubSlotConfigEntry 2 }


   snSysCMOSHubSaveHubFunctions OBJECT-TYPE
   	     SYNTAX  INTEGER {
                not-saved(1),
                saved    (2)
             }
   	     ACCESS  read-write
             STATUS  mandatory
             DESCRIPTION
             "Save (2) /Do not Save (1) Hub managment functions in 
              non-volatile memory."
            ::= { lanOpticsSystemCMOSHub 2 }

   snSysCMOSRPLMode OBJECT-TYPE
   	     SYNTAX  INTEGER {
                rpl-off (1),
                rpl-on (2)
             }
             ACCESS     read-write
   	     STATUS  mandatory
   	     DESCRIPTION
   		"Determine if the image will be loaded 
                 through RPL at next boot: RPL off - 1, RPL on - 2."
   	     ::=  { lanOpticsSystemCMOSRPL 1 }

   snSysCMOSFlashMode OBJECT-TYPE
   	     SYNTAX  INTEGER {
                flash-off (1),
                flash-on (2)
             }
             ACCESS     read-write
   	     STATUS  mandatory
   	     DESCRIPTION
   		"Determine if the image will be loaded 
                 from flash memory at next boot :
                 flash on - 2, flash off - 1."
   	     ::=  { lanOpticsSystemCMOSRPL 2 }


   snSysCMOSSerialMode OBJECT-TYPE
   	     SYNTAX  INTEGER {
                proprietary (1),
                slip (2),
                none (3)
             }
             ACCESS     read-write
   	     STATUS  mandatory
   	     DESCRIPTION
   		"Determine the serial port usage mode :
                 Proprietary - 1, SLIP - 2, None - 3."
   	     ::=  { lanOpticsSystemCMOSSerial 1 }

   snSysCMOSSerialComSelect OBJECT-TYPE
   	     SYNTAX  INTEGER {
                sr-COM1 (1),
                sr-COM2 (2)
             }
             ACCESS     read-write
   	     STATUS  mandatory
   	     DESCRIPTION
   		"Determine which COM port is used. "
   	     ::=  { lanOpticsSystemCMOSSerial 2 }


   snSysCMOSSerialBaudRate OBJECT-TYPE
   	     SYNTAX  INTEGER {
                baud1200  (1),
                baud2400  (2),
                baud4800  (3),
                baud9600  (4),
                baud19200 (5),
                baud38300 (6),
                baud57600 (7)
             }
             ACCESS     read-write
   	     STATUS  mandatory
   	     DESCRIPTION
   		"Determine the serial port baud rate :
                1200 - 1, 2400 - 2, 4800 - 3, 9600 - 4,
                19200 - 5, 38300 - 6, 57600 - 7 "
   	     ::=  { lanOpticsSystemCMOSSerial 3 }

   snSysCMOSSerialWordLength OBJECT-TYPE
   	     SYNTAX  INTEGER {
                bits-7 (1),
                bits-8  (2)
             }
             ACCESS     read-write
   	     STATUS  mandatory
   	     DESCRIPTION
   		"Determine the data bits length : 7 Bits - 1, 8 Bits -2 "
   	     ::=  { lanOpticsSystemCMOSSerial 4 }

   snSysCMOSSerialStopBits OBJECT-TYPE
   	     SYNTAX  INTEGER {
                bits-1 (1),
                bits-15  (2),
                bits-2 (3)
             }
             ACCESS     read-write
   	     STATUS  mandatory
   	     DESCRIPTION
   		"Determine the number of stop bits;
                values allowed : 1 Bit - 1, 1.5 Bits - 2, 2 Bits - 3."
   	     ::=  { lanOpticsSystemCMOSSerial 5 }


   snSysCMOSSerialParityCheck OBJECT-TYPE
   	     SYNTAX  INTEGER {
                even (1),
                odd  (2),
                none (3)
             }
             ACCESS     read-write
   	     STATUS  mandatory
   	     DESCRIPTION
   		"Determine the parity check policy :
                Even - 1, Odd - 2, None - 3."
   	     ::=  { lanOpticsSystemCMOSSerial 6 }


   snSysCMOSSRAMKeepAliveSecInterval OBJECT-TYPE
   	     SYNTAX  INTEGER 
             ACCESS     read-write
   	     STATUS  mandatory
   	     DESCRIPTION
   		"Determine the interval of the keep alive frame in seconds "
   	     ::=  { lanOpticsSystemCMOSSRAM 1 }

   snSysCMOSSNMPCommunitiesNum OBJECT-TYPE
   	     SYNTAX  INTEGER 
             ACCESS     read-only
   	     STATUS  mandatory
   	     DESCRIPTION
   		"Keeps the number of communities."
   	     ::=  { lanOpticsSystemCMOSSNMP 1 }


   snSysCMOSSNMPTrapManagersNum OBJECT-TYPE
   	     SYNTAX  INTEGER 
             ACCESS     read-only
   	     STATUS  mandatory
   	     DESCRIPTION
   		"Keeps the number of managers that traps are send to."
   	     ::=  { lanOpticsSystemCMOSSNMP 2 }

                                         
   snSysCMOSSNMPCommunitiesTable    OBJECT-TYPE
     SYNTAX  SEQUENCE OF SnSysCMOSSNMPCommunitiesEntry
     ACCESS  not-accessible
     STATUS  mandatory
     DESCRIPTION
	"A table containing the SNMP communities"
     ::=  { lanOpticsSystemCMOSSNMP 3 }

   snSysCMOSSNMPCommunitiesEntry    OBJECT-TYPE
     SYNTAX  SnSysCMOSSNMPCommunitiesEntry
     ACCESS  not-accessible
     STATUS  mandatory
     DESCRIPTION
	"An entry community info"
     INDEX { INTEGER }  
   ::= { snSysCMOSSNMPCommunitiesTable 1 }

   SnSysCMOSSNMPCommunitiesEntry ::=   SEQUENCE{
	 snSysCMOSSNMPCommunityName
	     DisplayString,
	 snSysCMOSSNMPCommunityPrivs
	     INTEGER
     }

     snSysCMOSSNMPCommunityName OBJECT-TYPE
     SYNTAX  DisplayString
     ACCESS  read-write
     STATUS  mandatory
     DESCRIPTION
	"This variable will give the community name."
     ::= { snSysCMOSSNMPCommunitiesEntry 1 }

     snSysCMOSSNMPCommunityPrivs OBJECT-TYPE
     SYNTAX  INTEGER {
        read-Only(1),
        read-Write(2)
            }
     ACCESS  read-write
     STATUS  mandatory
     DESCRIPTION
	"This variable will give the community privilages:
              Read Only - 1, Read/Write - 2."
     ::= { snSysCMOSSNMPCommunitiesEntry 2 }


   snSysCMOSSNMPTrapCommunitiesTable    OBJECT-TYPE
     SYNTAX  SEQUENCE OF SnSysCMOSSNMPTrapCommunitiesEntry
     ACCESS  not-accessible
     STATUS  mandatory
     DESCRIPTION
	"A table containing the SNMP communities"
     ::=  { lanOpticsSystemCMOSSNMP 4 }

   snSysCMOSSNMPTrapCommunitiesEntry   OBJECT-TYPE
     SYNTAX  SnSysCMOSSNMPTrapCommunitiesEntry
     ACCESS  not-accessible
     STATUS  mandatory
     DESCRIPTION
	"An entry of trap IP destinations."
     INDEX {INTEGER }
   ::= { snSysCMOSSNMPTrapCommunitiesTable 1 }

   SnSysCMOSSNMPTrapCommunitiesEntry ::=   SEQUENCE{
	 snSysCMOSSNMPTrapCommunityIpAddr
	     IpAddress
     }

     snSysCMOSSNMPTrapCommunityIpAddr OBJECT-TYPE
     SYNTAX  IpAddress
     ACCESS  read-write
     STATUS  mandatory
     DESCRIPTION
	"This variable gives a manager IP address for traps destination."
     ::= { snSysCMOSSNMPTrapCommunitiesEntry 1 }


   snSysCMOSACCESSOffset OBJECT-TYPE
   	     SYNTAX  INTEGER 
             ACCESS  read-write
             STATUS  mandatory
             DESCRIPTION
   		"Gives the offset in the CMOS array. 
                  For internal use only"
   	     ::= { lanOpticsSystemCMOSACCESS 1 }

   snSysCMOSACCESSLength OBJECT-TYPE
   	     SYNTAX  INTEGER 
             ACCESS  read-write
             STATUS  mandatory
             DESCRIPTION
   		"Gives the length (max 512) in the CMOS array. 
                  For internal use only,"
   	     ::= { lanOpticsSystemCMOSACCESS 2 }

   snSysCMOSACCESSSequence OBJECT-TYPE
   	     SYNTAX  INTEGER 
             ACCESS  read-write
             STATUS  mandatory
             DESCRIPTION
   		"Gives a sequnce of bytes from CMOS array. 
                  For internal use only"
   	     ::= { lanOpticsSystemCMOSACCESS 3 }

   snSysCMOSBRDGradius OBJECT-TYPE
   	     SYNTAX  INTEGER 
             ACCESS  read-write
             STATUS  mandatory
             DESCRIPTION
   		"Sets the discovery radius. 
                  Value = 0-7. 0=disable bridge."
   	     ::= { lanOpticsSystemCMOSBRDG  1 }

   snSysCMOSBRDGlinkNumber OBJECT-TYPE
   	     SYNTAX  INTEGER(0..3)
             ACCESS  read-write
             STATUS  mandatory
             DESCRIPTION
   		"Sets the Link number. 
                  Value = 0-3. "
   	     ::= { lanOpticsSystemCMOSBRDG  2 }

   snSysCMOSBRDGpassword OBJECT-TYPE
   	     SYNTAX  DisplayString
             ACCESS  read-write
             STATUS  mandatory
             DESCRIPTION
   		"Sets the bridge password. 
                 8 characters . "
   	     ::= { lanOpticsSystemCMOSBRDG  3 }
   
END
