-- *****************************************************************
-- CISCO-P-BRIDGE-CAPABILITY.my:
-- Cisco P-BRIDGE-MIB AGENT-CAPABILITIES
--
-- January 2004, Edward Pham, Guichuan Tang 
--
-- Copyright (c) 2004 by Cisco Systems, Inc.
-- All rights reserved.
-- *****************************************************************

CISCO-P-BRIDGE-CAPABILITY DEFINITIONS ::= BEGIN

IMPORTS
        MODULE-IDENTITY
                FROM SNMPv2-SMI

        AGENT-CAPABILITIES
                FROM SNMPv2-CONF

        TimeInterval 
                FROM SNMPv2-TC

        ciscoAgentCapability
                FROM CISCO-SMI;

ciscoPBridgeCapability MODULE-IDENTITY
        LAST-UPDATED    "200401140000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The agent capabilities description of
                 P-BRIDGE-MIB."

        REVISION        "200401140000Z"
        DESCRIPTION
                "Initial version of this MIB module."
        ::= { ciscoAgentCapability 385 }

ciscoPBridgeCapCatOSV08R0301 AGENT-CAPABILITIES
    PRODUCT-RELEASE      "Cisco CatOS 8.3(1) on Catalyst 6000/6500
                          and Cisco 7600 series devices."
    STATUS               current
    DESCRIPTION          "P-BRIDGE-MIB agent capabilities."
 
    SUPPORTS             P-BRIDGE-MIB
        INCLUDES         { pBridgeDefaultPriorityGroup,
                           pBridgePriorityGroup,
                           pBridgePortGarpGroup
                         } 

        VARIATION        dot1dPortNumTrafficClasses 
            ACCESS       read-only
            DESCRIPTION
                   "Only supports read-only access."

        VARIATION        dot1dPortGarpJoinTime 
            SYNTAX       TimeInterval (1..107374181)
            DESCRIPTION 
                   "Takes on values 1 to 107374181.
                    The instance value for dot1dPortGarpLeaveTime
                    should be greater than twice the instance
                    value for dot1dPortGarpJoinTime in set
                    operations."

        VARIATION        dot1dPortGarpLeaveTime 
            SYNTAX       TimeInterval (3..214748363)
            DESCRIPTION 
                   "Takes on values 3 to 214748363.
                    The instance value for dot1dPortGarpLeaveTime
                    should be greater than twice the instance
                    value for dot1dPortGarpJoinTime and less
                    than that for dot1dPortGarpLeaveAllTime
                    in set operations."

        VARIATION        dot1dPortGarpLeaveAllTime 
            SYNTAX       TimeInterval (4..214748364)
            DESCRIPTION 
                   "Takes on values 4 to 214748364.
                    The instance value for dot1dPortGarpLeaveTime
                    should be less than instance value for
                    dot1dPortGarpLeaveAllTime in set operations."

    ::= { ciscoPBridgeCapability 1 }

END
