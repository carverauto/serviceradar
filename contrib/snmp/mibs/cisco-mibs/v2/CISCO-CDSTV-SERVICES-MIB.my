-- *****************************************************************
-- CISCO-CDSTV-SERVICES-MIB: Cisco CDS-TV Services Management
-- Information Base
--   
-- Copyright (c) 2010 by Cisco Systems, Inc.
--   
-- All rights reserved.
--   
-- *****************************************************************

CISCO-CDSTV-SERVICES-MIB DEFINITIONS ::= BEGIN

IMPORTS
    MODULE-IDENTITY,
    OBJECT-TYPE,
    NOTIFICATION-TYPE,
    Unsigned32
        FROM SNMPv2-SMI
    MODULE-COMPLIANCE,
    NOTIFICATION-GROUP,
    OBJECT-GROUP
        FROM SNMPv2-CONF
    SnmpAdminString
        FROM SNMP-FRAMEWORK-MIB
    TruthValue
        FROM SNMPv2-TC
    ciscoMgmt
        FROM CISCO-SMI;


ciscoCdstvServicesMIB MODULE-IDENTITY
    LAST-UPDATED    "201003290000Z"
    ORGANIZATION    "Cisco Systems, Inc."
    CONTACT-INFO
            "Cisco Systems
            Customer Service

            Postal: 170 W Tasman Drive
            San Jose, CA  95134
            USA

            Tel: +1 800 553-NETS

            E-mail: cs-cds@cisco.com"
    DESCRIPTION
        "This MIB module defines service monitoring objects that
        faciliate the management of the Cisco Content Delivery System
        for TV (CDS-TV) product family.

        CDS-TV is a suite of products and software applications
        providing ingest, storage, caching, streaming, playout and
        on-demand delivery of video to television or set-top-box
        clients.

        Abbreviations:

        CDS     Content Delivery System
        ISA     Interactive Services Architecture
        ISV     Integrated Streamer-Vault
        FSI     File Service Interface
        MSA     Managed Services Architecture
        RTSP    Real-Time Streaming Protocol"
    REVISION        "201003290000Z"
    DESCRIPTION
        "Initial version of this MIB module."
    ::= { ciscoMgmt 729 }


-- Textual Conventions definition will be defined before this line

ciscoCdstvServicesMIBNotifs  OBJECT IDENTIFIER
    ::= { ciscoCdstvServicesMIB 0 }

ciscoCdstvServicesMIBObjects  OBJECT IDENTIFIER
    ::= { ciscoCdstvServicesMIB 1 }

ciscoCdstvServicesMIBConform  OBJECT IDENTIFIER
    ::= { ciscoCdstvServicesMIB 2 }


cdstvServicesMonitorTable OBJECT-TYPE
    SYNTAX          SEQUENCE OF CdstvServicesMonitorTableEntry 
    MAX-ACCESS      not-accessible
    STATUS          current
    DESCRIPTION
        "This table lists the services being monitored."
    ::= { ciscoCdstvServicesMIBObjects 1 }

cdstvServicesMonitorTableEntry OBJECT-TYPE
    SYNTAX          CdstvServicesMonitorTableEntry
    MAX-ACCESS      not-accessible
    STATUS          current
    DESCRIPTION
        "An entry (conceptual row) in the cdstvServicesMonitorTable.
        Each entry represents a service configured to run on the server
        and its status (whether running or stopped). Rows are added for
        each configured service and the number of rows does not change
        for a particular server with a specific configuration."
    INDEX           { cdstvServicesMonitorIndex } 
    ::= { cdstvServicesMonitorTable 1 }

CdstvServicesMonitorTableEntry ::= SEQUENCE {
        cdstvServicesMonitorIndex Unsigned32,
        cdstvServiceName          SnmpAdminString,
        cdstvServiceStatus        INTEGER
}

cdstvServicesMonitorIndex OBJECT-TYPE
    SYNTAX          Unsigned32 (1..4294967295)
    MAX-ACCESS      not-accessible
    STATUS          current
    DESCRIPTION
        "A unique identifier for the services being monitored on this
        device, i.e. streamer, cache, vault or ISV." 
    ::= { cdstvServicesMonitorTableEntry 1 }

cdstvServiceName OBJECT-TYPE
    SYNTAX          SnmpAdminString
    MAX-ACCESS      read-only
    STATUS          current
    DESCRIPTION
        "This object indicates the name of the service/process being
        monitored." 
    ::= { cdstvServicesMonitorTableEntry 2 }

cdstvServiceStatus OBJECT-TYPE
    SYNTAX          INTEGER  {
                        up(1),
                        down(2)
                    }
    MAX-ACCESS      read-only
    STATUS          current
    DESCRIPTION
        "This object indicates the status of the service/process being
        monitored: up(1), or down(2)." 
    ::= { cdstvServicesMonitorTableEntry 3 }
 

cdstvServiceTrapsEnable  OBJECT IDENTIFIER
    ::= { ciscoCdstvServicesMIBObjects 2 }


cdstvServiceUpNotifEnable OBJECT-TYPE
    SYNTAX          TruthValue
    MAX-ACCESS      read-write
    STATUS          current
    DESCRIPTION
        "This object specifies whether cdstvServiceUp notification is
        generated by the system.

        Setting this object to 'true' will enable generation of
        cdstvServiceUp. 

        Setting this object to 'false' will disable generation of 
        cdstvServiceUp." 
    ::= { cdstvServiceTrapsEnable 1 }

cdstvServiceDownNotifEnable OBJECT-TYPE
    SYNTAX          TruthValue
    MAX-ACCESS      read-write
    STATUS          current
    DESCRIPTION
        "This object specifies whether cdstvServiceDown notification is
        generated by the system. 

        Setting this object to 'true' will enable generation of
        cdstvServiceDown. 

        Setting this object to 'false' will disable generation of 
        cdstvServiceDown" 
    ::= { cdstvServiceTrapsEnable 2 }

cdstvServiceUp NOTIFICATION-TYPE
    OBJECTS         { cdstvServiceName }
    STATUS          current
    DESCRIPTION
        "The SNMP entity generates the cdstvServiceUp notification when
        the status (indicated by the object cdstvServiceStatus) of a
        service being monitored (indicated by the object
        cdstvServiceName) changes to 'up'."
   ::= { ciscoCdstvServicesMIBNotifs 1 }

cdstvServiceDown NOTIFICATION-TYPE
    OBJECTS         { cdstvServiceName }
    STATUS          current
    DESCRIPTION
        "The SNMP entity generates the cdstvServiceDown notification
        when the status (indicated by the object cdstvServiceStatus) 
        of a service being monitored (indicated by the object 
        cdstvServiceName), changes to 'down'."
   ::= { ciscoCdstvServicesMIBNotifs 2 }
ciscoCdstvServicesMIBCompliances  OBJECT IDENTIFIER
    ::= { ciscoCdstvServicesMIBConform 1 }

ciscoCdstvServicesMIBGroups  OBJECT IDENTIFIER
    ::= { ciscoCdstvServicesMIBConform 2 }


ciscoCdstvServicesMIBCompliance MODULE-COMPLIANCE
    STATUS          current
    DESCRIPTION
        "The compliance statement for the entities which
        implement the Cisco CDS TV Services MIB."
    MODULE          -- this module
    MANDATORY-GROUPS {
                        ciscoCdstvServicesMIBMainObjectGroup,
                        ciscoCdstvServicesMIBNotificationGroup
                    }

    GROUP           ciscoCdstvServicesMIBNotifEnableObjectGroup
    DESCRIPTION
        "This group is mandatory only for platforms that support
        enabling/disabling of service notifications."

    OBJECT          cdstvServiceUpNotifEnable
    MIN-ACCESS      read-only
    DESCRIPTION
        "Write access is not required."

    OBJECT          cdstvServiceDownNotifEnable
    MIN-ACCESS      read-only
    DESCRIPTION
        "Write access is not required."
    ::= { ciscoCdstvServicesMIBCompliances 1 }

-- Units of Conformance

ciscoCdstvServicesMIBMainObjectGroup OBJECT-GROUP
    OBJECTS         {
                        cdstvServiceName,
                        cdstvServiceStatus
                    }
    STATUS          current
    DESCRIPTION
        "A collection of objects that provide status of monitored
        services."
    ::= { ciscoCdstvServicesMIBGroups 1 }

ciscoCdstvServicesMIBNotificationGroup NOTIFICATION-GROUP
   NOTIFICATIONS    {
                        cdstvServiceUp,
                        cdstvServiceDown
                    }
    STATUS          current
    DESCRIPTION
        "A collection of notifications generated by this MIB module."
    ::= { ciscoCdstvServicesMIBGroups 2 }

ciscoCdstvServicesMIBNotifEnableObjectGroup OBJECT-GROUP
    OBJECTS         {
                        cdstvServiceUpNotifEnable,
                        cdstvServiceDownNotifEnable
                    }
    STATUS          current
    DESCRIPTION
        "A collection of objects that enable/disable generation of
        CDS-TV service notifications."
    ::= { ciscoCdstvServicesMIBGroups 3 }

END
