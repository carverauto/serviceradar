-- *********************************************************************
-- CISCO-FIREPOWER-AP-EQUIPMENT-MIB.my
-- 
-- MIB representation of the Cisco Firepower
-- EQUIPMENT management information model package
-- 
-- Created January 2023 by Charles Bullis
-- 
-- Copyright (c) 2005-2023 Cisco Systems, Inc. All rights reserved.
-- 
-- *********************************************************************

CISCO-FIREPOWER-AP-EQUIPMENT-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerApMIBObjects,
    CfprApManagedObjectId,
    CfprApManagedObjectDn
        FROM CISCO-FIREPOWER-AP-MIB
    CfprApComputeLinkAggregationCap,
    CfprApComputeMemoryUnitConstraintType,
    CfprApConditionRemoteInvRslt,
    CfprApConditionSeverity,
    CfprApEquipmentActiveStatus,
    CfprApEquipmentAdminPowerState,
    CfprApEquipmentAirflowDirection,
    CfprApEquipmentAsicType,
    CfprApEquipmentBeaconLedFsmCurrentFsm,
    CfprApEquipmentBeaconLedFsmStageName,
    CfprApEquipmentBeaconLedFsmTaskItem,
    CfprApEquipmentBeaconLedState,
    CfprApEquipmentBiosUpdateMethod,
    CfprApEquipmentCType,
    CfprApEquipmentCardStatsHistThresholded,
    CfprApEquipmentCardStatsThresholded,
    CfprApEquipmentChassisAdminState,
    CfprApEquipmentChassisConfigProgressIndicator,
    CfprApEquipmentChassisConfigState,
    CfprApEquipmentChassisFsmCurrentFsm,
    CfprApEquipmentChassisFsmStageName,
    CfprApEquipmentChassisFsmTaskItem,
    CfprApEquipmentChassisId,
    CfprApEquipmentChassisIssues,
    CfprApEquipmentChassisPowerOperState,
    CfprApEquipmentChassisStatsHistThresholded,
    CfprApEquipmentChassisStatsThresholded,
    CfprApEquipmentCommStatus,
    CfprApEquipmentConnectionStatus,
    CfprApEquipmentDiscoveryCapOperPowerRequirement,
    CfprApEquipmentDiscoveryState,
    CfprApEquipmentEnabledStatus,
    CfprApEquipmentEthPortSpeedCap,
    CfprApEquipmentFanId,
    CfprApEquipmentFanModule,
    CfprApEquipmentFanModuleId,
    CfprApEquipmentFanModuleStatsHistThresholded,
    CfprApEquipmentFanModuleStatsThresholded,
    CfprApEquipmentFanModuleTray,
    CfprApEquipmentFanStatsHistThresholded,
    CfprApEquipmentFanStatsThresholded,
    CfprApEquipmentFanTray,
    CfprApEquipmentFexCapProviderRole,
    CfprApEquipmentFexEnvStatsHistThresholded,
    CfprApEquipmentFexEnvStatsThresholded,
    CfprApEquipmentFexId,
    CfprApEquipmentFexPowerSummaryHistThresholded,
    CfprApEquipmentFexPowerSummaryThresholded,
    CfprApEquipmentFexPsuInputStatsHistThresholded,
    CfprApEquipmentFexPsuInputStatsThresholded,
    CfprApEquipmentHealthLedState,
    CfprApEquipmentIOCardBaseFsmCurrentFsm,
    CfprApEquipmentIOCardBaseFsmStageName,
    CfprApEquipmentIOCardBaseFsmTaskFlags,
    CfprApEquipmentIOCardBaseFsmTaskItem,
    CfprApEquipmentIOCardFsmCurrentFsm,
    CfprApEquipmentIOCardFsmStageName,
    CfprApEquipmentIOCardFsmTaskItem,
    CfprApEquipmentIOCardId,
    CfprApEquipmentIOCardIssues,
    CfprApEquipmentIOCardStatsHistThresholded,
    CfprApEquipmentIOCardStatsThresholded,
    CfprApEquipmentInternalFanType,
    CfprApEquipmentIsSupported,
    CfprApEquipmentLedColor,
    CfprApEquipmentLedLocatorState,
    CfprApEquipmentLedOperState,
    CfprApEquipmentLocatorLedFsmCurrentFsm,
    CfprApEquipmentLocatorLedFsmStageName,
    CfprApEquipmentLocatorLedFsmTaskItem,
    CfprApEquipmentMemoryUnitDiscoveryModifierAction,
    CfprApEquipmentMethod,
    CfprApEquipmentNetworkElementFanStatsHistThresholded,
    CfprApEquipmentNetworkElementFanStatsThresholded,
    CfprApEquipmentOperability,
    CfprApEquipmentOwnership,
    CfprApEquipmentPOSTRecoverability,
    CfprApEquipmentPasswordState,
    CfprApEquipmentPictureType,
    CfprApEquipmentPortAttribute,
    CfprApEquipmentPowerCapDefProfileMethod,
    CfprApEquipmentPowerState,
    CfprApEquipmentPresence,
    CfprApEquipmentPsuFanStatus,
    CfprApEquipmentPsuId,
    CfprApEquipmentPsuInputSrc,
    CfprApEquipmentPsuInputStatsHistThresholded,
    CfprApEquipmentPsuInputStatsThresholded,
    CfprApEquipmentPsuOutputStatsHistThresholded,
    CfprApEquipmentPsuOutputStatsThresholded,
    CfprApEquipmentPsuStateQualifier,
    CfprApEquipmentPsuStatsHistThresholded,
    CfprApEquipmentPsuStatsThresholded,
    CfprApEquipmentPsuType,
    CfprApEquipmentPsuVoltageType,
    CfprApEquipmentRackUnitFanStatsHistThresholded,
    CfprApEquipmentRackUnitFanStatsThresholded,
    CfprApEquipmentRackUnitPsuStatsHistThresholded,
    CfprApEquipmentRackUnitPsuStatsThresholded,
    CfprApEquipmentRemovalConditions,
    CfprApEquipmentResetOn,
    CfprApEquipmentSecureBios,
    CfprApEquipmentSensorThresholdStatus,
    CfprApEquipmentSlotArrayLocation,
    CfprApEquipmentSlotArrayOrientation,
    CfprApEquipmentSlotArraySelector,
    CfprApEquipmentSlotSpanOrientation,
    CfprApEquipmentStorageMethod,
    CfprApEquipmentSwitchIOCardFsmCurrentFsm,
    CfprApEquipmentSwitchIOCardFsmStageName,
    CfprApEquipmentSwitchIOCardId,
    CfprApEquipmentTpmType,
    CfprApEquipmentUnifiedPortAlgorithm,
    CfprApEquipmentUuidFeatureCapUuidSupportMode,
    CfprApEquipmentXcvrId,
    CfprApEquipmentXcvrType,
    CfprApFsmCompletion,
    CfprApFsmFlags,
    CfprApFsmFsmStageStatus,
    CfprApLicenseState,
    CfprApMgmtUpgradeStatus,
    CfprApNetworkSide,
    CfprApNetworkSwitchId,
    CfprApPolicyPolicyOwner,
    CfprApPortEthSpeed,
    CfprApPortGroupType,
    CfprApPortSpeed,
    CfprApStorageControllerForm,
    CfprApStorageLocalDiskMode,
    CfprApStorageTechnology
        FROM CISCO-FIREPOWER-AP-TC-MIB;

cfprApEquipmentObjects MODULE-IDENTITY
    LAST-UPDATED    "202301250000Z"
    ORGANIZATION    "Cisco Systems Inc."
    CONTACT-INFO
        "Cisco Systems
        Customer Service
        
        Postal: 170 W Tasman Drive
        San Jose, CA  95134
        USA
        
        Tel: +1 800 553-NETS
        
        E-mail: firepower-mibs@cisco.com"
    DESCRIPTION
        "MIB representation of the Cisco Firepower
        EQUIPMENT management information model package"
    ::= { ciscoFirepowerApMIBObjects 20 }

cfprApEquipmentAdaptorConnDefTable OBJECT-TYPE
    SYNTAX           SEQUENCE OF CfprApEquipmentAdaptorConnDefEntry
    MAX-ACCESS       not-accessible
    STATUS           current
    DESCRIPTION
        "Cisco Firepower equipment:AdaptorConnDef managed object table"
    ::= { cfprApEquipmentObjects 1 }

cfprApEquipmentAdaptorConnDefEntry OBJECT-TYPE
    SYNTAX           CfprApEquipmentAdaptorConnDefEntry
    MAX-ACCESS       not-accessible
    STATUS           current
    DESCRIPTION
        "Entry for the cfprApEquipmentAdaptorConnDefTable table."
    INDEX { cfprApEquipmentAdaptorConnDefInstanceId }
    ::= { cfprApEquipmentAdaptorConnDefTable 1 }

CfprApEquipmentAdaptorConnDefEntry ::= SEQUENCE {
    cfprApEquipmentAdaptorConnDefInstanceId                          CfprApManagedObjectId,
    cfprApEquipmentAdaptorConnDefDn                                  CfprApManagedObjectDn,
    cfprApEquipmentAdaptorConnDefRn                                  SnmpAdminString,
    cfprApEquipmentAdaptorConnDefAdaptorEp                           Gauge32,
    cfprApEquipmentAdaptorConnDefDescr                               SnmpAdminString,
    cfprApEquipmentAdaptorConnDefIntId                               SnmpAdminString,
    cfprApEquipmentAdaptorConnDefIomEp                               Gauge32,
    cfprApEquipmentAdaptorConnDefName                                SnmpAdminString,
    cfprApEquipmentAdaptorConnDefPolicyLevel                         Gauge32,
    cfprApEquipmentAdaptorConnDefPolicyOwner                         CfprApPolicyPolicyOwner
}

cfprApEquipmentAdaptorConnDefInstanceId OBJECT-TYPE
    SYNTAX       CfprApManagedObjectId
    MAX-ACCESS   not-accessible
    STATUS       current
    DESCRIPTION
        "Instance identifier of the managed object."
    ::= { cfprApEquipmentAdaptorConnDefEntry 1 }

cfprApEquipmentAdaptorConnDefDn OBJECT-TYPE
    SYNTAX       CfprApManagedObjectDn
    MAX-ACCESS   read-only
    STATUS       current
    DESCRIPTION
        "Cisco Firepower equipment:AdaptorConnDef:dn managed
        object property"
    ::= { cfprApEquipmentAdaptorConnDefEntry 2 }

cfprApEquipmentAdaptorConnDefRn OBJECT-TYPE
    SYNTAX       SnmpAdminString
    MAX-ACCESS   read-only
    STATUS       current
    DESCRIPTION
        "Cisco Firepower equipment:AdaptorConnDef:rn managed
        object property"
    ::= { cfprApEquipmentAdaptorConnDefEntry 3 }

cfprApEquipmentAdaptorConnDefAdaptorEp OBJECT-TYPE
    SYNTAX       Gauge32
    MAX-ACCESS   read-only
    STATUS       current
    DESCRIPTION
        "Cisco Firepower equipment:AdaptorConnDef:adaptorEp
        managed object property"
    ::= { cfprApEquipmentAdaptorConnDefEntry 4 }

cfprApEquipmentAdaptorConnDefDescr OBJECT-TYPE
    SYNTAX       SnmpAdminString
    MAX-ACCESS   read-only
    STATUS       current
    DESCRIPTION
        "Cisco Firepower equipment:AdaptorConnDef:descr
        managed object property"
    ::= { cfprApEquipmentAdaptorConnDefEntry 5 }

cfprApEquipmentAdaptorConnDefIntId OBJECT-TYPE
    SYNTAX       SnmpAdminString
    MAX-ACCESS   read-only
    STATUS       current
    DESCRIPTION
        "Cisco Firepower equipment:AdaptorConnDef:intId
        managed object property"
    ::= { cfprApEquipmentAdaptorConnDefEntry 6 }

cfprApEquipmentAdaptorConnDefIomEp OBJECT-TYPE
    SYNTAX       Gauge32
    MAX-ACCESS   read-only
    STATUS       current
    DESCRIPTION
        "Cisco Firepower equipment:AdaptorConnDef:iomEp
        managed object property"
    ::= { cfprApEquipmentAdaptorConnDefEntry 7 }

cfprApEquipmentAdaptorConnDefName OBJECT-TYPE
    SYNTAX       SnmpAdminString
    MAX-ACCESS   read-only
    STATUS       current
    DESCRIPTION
        "Cisco Firepower equipment:AdaptorConnDef:name
        managed object property"
    ::= { cfprApEquipmentAdaptorConnDefEntry 8 }

cfprApEquipmentAdaptorConnDefPolicyLevel OBJECT-TYPE
    SYNTAX       Gauge32
    MAX-ACCESS   read-only
    STATUS       current
    DESCRIPTION
        "Cisco Firepower equipment:AdaptorConnDef:policyLevel
        managed object property"
    ::= { cfprApEquipmentAdaptorConnDefEntry 9 }

cfprApEquipmentAdaptorConnDefPolicyOwner OBJECT-TYPE
    SYNTAX       CfprApPolicyPolicyOwner
    MAX-ACCESS   read-only
    STATUS       current
    DESCRIPTION
        "Cisco Firepower equipment:AdaptorConnDef:policyOwner
        managed object property"
    ::= { cfprApEquipmentAdaptorConnDefEntry 10 }

cfprApEquipmentAdaptorDefTable OBJECT-TYPE
    SYNTAX           SEQUENCE OF CfprApEquipmentAdaptorDefEntry
    MAX-ACCESS       not-accessible
    STATUS           current
    DESCRIPTION
        "Cisco Firepower equipment:AdaptorDef managed object table"
    ::= { cfprApEquipmentObjects 2 }

cfprApEquipmentAdaptorDefEntry OBJECT-TYPE
    SYNTAX           CfprApEquipmentAdaptorDefEntry
    MAX-ACCESS       not-accessible
    STATUS           current
    DESCRIPTION
        "Entry for the cfprApEquipmentAdaptorDefTable table."
    INDEX { cfprApEquipmentAdaptorDefInstanceId }
    ::= { cfprApEquipmentAdaptorDefTable 1 }

CfprApEquipmentAdaptorDefEntry ::= SEQUENCE {
    cfprApEquipmentAdaptorDefInstanceId                              CfprApManagedObjectId,
    cfprApEquipmentAdaptorDefDn                                      CfprApManagedObjectDn,
    cfprApEquipmentAdaptorDefRn                                      SnmpAdminString,
    cfprApEquipmentAdaptorDefDescr                                   SnmpAdminString,
    cfprApEquipmentAdaptorDefEthernetPortSpeed                       Unsigned64,
    cfprApEquipmentAdaptorDefFibreChannelPortSpeed                   Unsigned64,
    cfprApEquipmentAdaptorDefIntId                                   SnmpAdminString,
    cfprApEquipmentAdaptorDefName                                    SnmpAdminString,
    cfprApEquipmentAdaptorDefPolicyLevel                             Gauge32,
    cfprApEquipmentAdaptorDefPolicyOwner                             CfprApPolicyPolicyOwner
}

cfprApEquipmentAdaptorDefInstanceId OBJECT-TYPE
    SYNTAX       CfprApManagedObjectId
    MAX-ACCESS   not-accessible
    STATUS       current
    DESCRIPTION
        "Instance identifier of the managed object."
    ::= { cfprApEquipmentAdaptorDefEntry 1 }

cfprApEquipmentAdaptorDefDn OBJECT-TYPE
    SYNTAX       CfprApManagedObjectDn
    MAX-ACCESS   read-only
    STATUS       current
    DESCRIPTION
        "Cisco Firepower equipment:AdaptorDef:dn managed object property"
    ::= { cfprApEquipmentAdaptorDefEntry 2 }

cfprApEquipmentAdaptorDefRn OBJECT-TYPE
    SYNTAX       SnmpAdminString
    MAX-ACCESS   read-only
    STATUS       current
    DESCRIPTION
        "Cisco Firepower equipment:AdaptorDef:rn managed object property"
    ::= { cfprApEquipmentAdaptorDefEntry 3 }

cfprApEquipmentAdaptorDefDescr OBJECT-TYPE
    SYNTAX       SnmpAdminString
    MAX-ACCESS   read-only
    STATUS       current
    DESCRIPTION
        "Cisco Firepower equipment:AdaptorDef:descr managed
        object property"
    ::= { cfprApEquipmentAdaptorDefEntry 4 }

cfprApEquipmentAdaptorDefEthernetPortSpeed OBJECT-TYPE
    SYNTAX       Unsigned64
    MAX-ACCESS   read-only
    STATUS       current
    DESCRIPTION
        "Cisco Firepower equipment:AdaptorDef:ethernetPortSpeed
        managed object property"
    ::= { cfprApEquipmentAdaptorDefEntry 5 }

cfprApEquipmentAdaptorDefFibreChannelPortSpeed OBJECT-TYPE
    SYNTAX       Unsigned64
    MAX-ACCESS   read-only
    STATUS       current
    DESCRIPTION
        "Cisco Firepower equipment:AdaptorDef:fibreChannelPortSpeed
        managed object property"
    ::= { cfprApEquipmentAdaptorDefEntry 6 }

cfprApEquipmentAdaptorDefIntId OBJECT-TYPE
    SYNTAX       SnmpAdminString
    MAX-ACCESS   read-only
    STATUS       current
    DESCRIPTION
        "Cisco Firepower equipment:AdaptorDef:intId managed
        object property"
    ::= { cfprApEquipmentAdaptorDefEntry 7 }

cfprApEquipmentAdaptorDefName OBJECT-TYPE
    SYNTAX       SnmpAdminString
    MAX-ACCESS   read-only
    STATUS       current
    DESCRIPTION
        "Cisco Firepower equipment:AdaptorDef:name managed
        object property"
    ::= { cfprApEquipmentAdaptorDefEntry 8 }

cfprApEquipmentAdaptorDefPolicyLevel OBJECT-TYPE
    SYNTAX       Gauge32
    MAX-ACCESS   read-only
    STATUS       current
    DESCRIPTION
        "Cisco Firepower equipment:AdaptorDef:policyLevel
        managed object property"
    ::= { cfprApEquipmentAdaptorDefEntry 9 }

cfprApEquipmentAdaptorDefPolicyOwner OBJECT-TYPE
    SYNTAX       CfprApPolicyPolicyOwner
    MAX-ACCESS   read-only
    STATUS       current
    DESCRIPTION
        "Cisco Firepower equipment:AdaptorDef:policyOwner
        managed object property"
    ::= { cfprApEquipmentAdaptorDefEntry 10 }

cfprApEquipmentAdvancedBootOrderTable OBJECT-TYPE
    SYNTAX           SEQUENCE OF CfprApEquipmentAdvancedBootOrderEntry
    MAX-ACCESS       not-accessible
    STATUS           current
    DESCRIPTION
        "Cisco Firepower equipment:AdvancedBootOrder managed object table"
    ::= { cfprApEquipmentObjects 3 }

cfprApEquipmentAdvancedBootOrderEntry OBJECT-TYPE
    SYNTAX           CfprApEquipmentAdvancedBootOrderEntry
    MAX-ACCESS       not-accessible
    STATUS           current
    DESCRIPTION
        "Entry for the cfprApEquipmentAdvancedBootOrderTable table."
    INDEX { cfprApEquipmentAdvancedBootOrderInstanceId }
    ::= { cfprApEquipmentAdvancedBootOrderTable 1 }

CfprApEquipmentAdvancedBootOrderEntry ::= SEQUENCE {
    cfprApEquipmentAdvancedBootOrderInstanceId                       CfprApManagedObjectId,
    cfprApEquipmentAdvancedBootOrderDn                               CfprApManagedObjectDn,
    cfprApEquipmentAdvancedBootOrderRn                               SnmpAdminString,
    cfprApEquipmentAdvancedBootOrderDescr                            SnmpAdminString,
    cfprApEquipmentAdvancedBootOrderIntId                            SnmpAdminString,
    cfprApEquipmentAdvancedBootOrderIsSupported                      TruthValue,
    cfprApEquipmentAdvancedBootOrderMinBiosVersion                   SnmpAdminString,
    cfprApEquipmentAdvancedBootOrderMinCimcVersion                   SnmpAdminString,
    cfprApEquipmentAdvancedBootOrderName                             SnmpAdminString,
    cfprApEquipmentAdvancedBootOrderPolicyLevel                      Gauge32,
    cfprApEquipmentAdvancedBootOrderPolicyOwner                      CfprApPolicyPolicyOwner
}

cfprApEquipmentAdvancedBootOrderInstanceId OBJECT-TYPE
    SYNTAX       CfprApManagedObjectId
    MAX-ACCESS   not-accessible
    STATUS       current
    DESCRIPTION
        "Instance identifier of the managed object."
    ::= { cfprApEquipmentAdvancedBootOrderEntry 1 }

cfprApEquipmentAdvancedBootOrderDn OBJECT-TYPE
    SYNTAX       CfprApManagedObjectDn
    MAX-ACCESS   read-only
    STATUS       current
    DESCRIPTION
        "Cisco Firepower equipment:AdvancedBootOrder:dn
        managed object property"
    ::= { cfprApEquipmentAdvancedBootOrderEntry 2 }

cfprApEquipmentAdvancedBootOrderRn OBJECT-TYPE
    SYNTAX       SnmpAdminString
    MAX-ACCESS   read-only
    STATUS       current
    DESCRIPTION
        "Cisco Firepower equipment:AdvancedBootOrder:rn
        managed object property"
    ::= { cfprApEquipmentAdvancedBootOrderEntry 3 }

cfprApEquipmentAdvancedBootOrderDescr OBJECT-TYPE
    SYNTAX       SnmpAdminString
    MAX-ACCESS   read-only
    STATUS       current
    DESCRIPTION
        "Cisco Firepower equipment:AdvancedBootOrder:descr
        managed object property"
    ::= { cfprApEquipmentAdvancedBootOrderEntry 4 }

cfprApEquipmentAdvancedBootOrderIntId OBJECT-TYPE
    SYNTAX       SnmpAdminString
    MAX-ACCESS   read-only
    STATUS       current
    DESCRIPTION
        "Cisco Firepower equipment:AdvancedBootOrder:intId
        managed object property"
    ::= { cfprApEquipmentAdvancedBootOrderEntry 5 }

cfprApEquipmentAdvancedBootOrderIsSupported OBJECT-TYPE
    SYNTAX       TruthValue
    MAX-ACCESS   read-only
    STATUS       current
    DESCRIPTION
        "Cisco Firepower equipment:AdvancedBootOrder:isSupported
        managed object property"
    ::= { cfprApEquipmentAdvancedBootOrderEntry 6 }

cfprApEquipmentAdvancedBootOrderMinBiosVersion OBJECT-TYPE
    SYNTAX       SnmpAdminString
    MAX-ACCESS   read-only
    STATUS       current
    DESCRIPTION
        "Cisco Firepower equipment:AdvancedBootOrder:minBiosVersion
        managed object property"
    ::= { cfprApEquipmentAdvancedBootOrderEntry 7 }

cfprApEquipmentAdvancedBootOrderMinCimcVersion OBJECT-TYPE
    SYNTAX       SnmpAdminString
    MAX-ACCESS   read-only
    STATUS       current
    DESCRIPTION
        "Cisco Firepower equipment:AdvancedBootOrder:minCimcVersion
        managed object property"
    ::= { cfprApEquipmentAdvancedBootOrderEntry 8 }

cfprApEquipmentAdvancedBootOrderName OBJECT-TYPE
    SYNTAX       SnmpAdminString
    MAX-ACCESS   read-only
    STATUS       current
    DESCRIPTION
        "Cisco Firepower equipment:AdvancedBootOrder:name
        managed object property"
    ::= { cfprApEquipmentAdvancedBootOrderEntry 9 }

cfprApEquipmentAdvancedBootOrderPolicyLevel OBJECT-TYPE
    SYNTAX       Gauge32
    MAX-ACCESS   read-only
    STATUS       current
    DESCRIPTION
        "Cisco Firepower equipment:AdvancedBootOrder:policyLevel
        managed object property"
    ::= { cfprApEquipmentAdvancedBootOrderEntry 10 }

cfprApEquipmentAdvancedBootOrderPolicyOwner OBJECT-TYPE
    SYNTAX       CfprApPolicyPolicyOwner
    MAX-ACCESS   read-only
    STATUS       current
    DESCRIPTION
        "Cisco Firepower equipment:AdvancedBootOrder:policyOwner
        managed object property"
    ::= { cfprApEquipmentAdvancedBootOrderEntry 11 }

cfprApEquipmentBaseBoardCapProviderTable OBJECT-TYPE
    SYNTAX           SEQUENCE OF CfprApEquipmentBaseBoardCapProviderEntry
    MAX-ACCESS       not-accessible
    STATUS           current
    DESCRIPTION
        "Cisco Firepower equipment:BaseBoardCapProvider
        managed object table"
    ::= { cfprApEquipmentObjects 4 }

cfprApEquipmentBaseBoardCapProviderEntry OBJECT-TYPE
    SYNTAX           CfprApEquipmentBaseBoardCapProviderEntry
    MAX-ACCESS       not-accessible
    STATUS           current
    DESCRIPTION
        "Entry for the cfprApEquipmentBaseBoardCapProviderTable table."
    INDEX { cfprApEquipmentBaseBoardCapProviderInstanceId }
    ::= { cfprApEquipmentBaseBoardCapProviderTable 1 }

CfprApEquipmentBaseBoardCapProviderEntry ::= SEQUENCE {
    cfprApEquipmentBaseBoardCapProviderInstanceId                    CfprApManagedObjectId,
    cfprApEquipmentBaseBoardCapProviderDn                            CfprApManagedObjectDn,
    cfprApEquipmentBaseBoardCapProviderRn                            SnmpAdminString,
    cfprApEquipmentBaseBoardCapProviderDeleted                       TruthValue,
    cfprApEquipmentBaseBoardCapProviderDeprecated                    TruthValue,
    cfprApEquipmentBaseBoardCapProviderElementLoadFailures           Gauge32,
    cfprApEquipmentBaseBoardCapProviderElementsLoaded                Gauge32,
    cfprApEquipmentBaseBoardCapProviderGencount                      Gauge32,
    cfprApEquipmentBaseBoardCapProviderLoadErrors                    Gauge32,
    cfprApEquipmentBaseBoardCapProviderLoadWarnings                  Gauge32,
    cfprApEquipmentBaseBoardCapProviderMgmtPlaneVer                  SnmpAdminString,
    cfprApEquipmentBaseBoardCapProviderModel                         SnmpAdminString,
    cfprApEquipmentBaseBoardCapProviderPromCardType                  Gauge32,
    cfprApEquipmentBaseBoardCapProviderRevision                      SnmpAdminString,
    cfprApEquipmentBaseBoardCapProviderVendor                        SnmpAdminString
}

cfprApEquipmentBaseBoardCapProviderInstanceId OBJECT-TYPE
    SYNTAX       CfprApManagedObjectId
    MAX-ACCESS   not-accessible
    STATUS       current
    DESCRIPTION
        "Instance identifier of the managed object."
    ::= { cfprApEquipmentBaseBoardCapProviderEntry 1 }

cfprApEquipmentBaseBoardCapProviderDn OBJECT-TYPE
    SYNTAX       CfprApManagedObjectDn
    MAX-ACCESS   read-only
    STATUS       current
    DESCRIPTION
        "Cisco Firepower equipment:BaseBoardCapProvider:dn
        managed object property"
    ::= { cfprApEquipmentBaseBoardCapProviderEntry 2 }

cfprApEquipmentBaseBoardCapProviderRn OBJECT-TYPE
    SYNTAX       SnmpAdminString
    MAX-ACCESS   read-only
    STATUS       current
    DESCRIPTION
        "Cisco Firepower equipment:BaseBoardCapProvider:rn
        managed object property"
    ::= { cfprApEquipmentBaseBoardCapProviderEntry 3 }

cfprApEquipmentBaseBoardCapProviderDeleted OBJECT-TYPE
    SYNTAX       TruthValue
    MAX-ACCESS   read-only
    STATUS       current
    DESCRIPTION
        "Cisco Firepower equipment:BaseBoardCapProvider:deleted
        managed object property"
    ::= { cfprApEquipmentBaseBoardCapProviderEntry 4 }

cfprApEquipmentBaseBoardCapProviderDeprecated OBJECT-TYPE
    SYNTAX       TruthValue
    MAX-ACCESS   read-only
    STATUS       current
    DESCRIPTION
        "Cisco Firepower equipment:BaseBoardCapProvider:deprecated
        managed object property"
    ::= { cfprApEquipmentBaseBoardCapProviderEntry 5 }

cfprApEquipmentBaseBoardCapProviderElementLoadFailures OBJECT-TYPE
    SYNTAX       Gauge32
    MAX-ACCESS   read-only
    STATUS       current
    DESCRIPTION
        "Cisco Firepower equipment:BaseBoardCapProvider:elementLoadFailure
        s managed object property"
    ::= { cfprApEquipmentBaseBoardCapProviderEntry 6 }

cfprApEquipmentBaseBoardCapProviderElementsLoaded OBJECT-TYPE
    SYNTAX       Gauge32
    MAX-ACCESS   read-only
    STATUS       current
    DESCRIPTION
        "Cisco Firepower equipment:BaseBoardCapProvider:elementsLoaded
        managed object property"
    ::= { cfprApEquipmentBaseBoardCapProviderEntry 7 }

cfprApEquipmentBaseBoardCapProviderGencount OBJECT-TYPE
    SYNTAX       Gauge32
    MAX-ACCESS   read-only
    STATUS       current
    DESCRIPTION
        "Cisco Firepower equipment:BaseBoardCapProvider:gencount
        managed object property"
    ::= { cfprApEquipmentBaseBoardCapProviderEntry 8 }

cfprApEquipmentBaseBoardCapProviderLoadErrors OBJECT-TYPE
    SYNTAX       Gauge32
    MAX-ACCESS   read-only
    STATUS       current
    DESCRIPTION
        "Cisco Firepower equipment:BaseBoardCapProvider:loadErrors
        managed object property"
    ::= { cfprApEquipmentBaseBoardCapProviderEntry 9 }

cfprApEquipmentBaseBoardCapProviderLoadWarnings OBJECT-TYPE
    SYNTAX       Gauge32
    MAX-ACCESS   read-only
    STATUS       current
    DESCRIPTION
        "Cisco Firepower equipment:BaseBoardCapProvider:loadWarnings
        managed object property"
    ::= { cfprApEquipmentBaseBoardCapProviderEntry 10 }

cfprApEquipmentBaseBoardCapProviderMgmtPlaneVer OBJECT-TYPE
    SYNTAX       SnmpAdminString
    MAX-ACCESS   read-only
    STATUS       current
    DESCRIPTION
        "Cisco Firepower equipment:BaseBoardCapProvider:mgmtPlaneVer
        managed object property"
    ::= { cfprApEquipmentBaseBoardCapProviderEntry 11 }

cfprApEquipmentBaseBoardCapProviderModel OBJECT-TYPE
    SYNTAX       SnmpAdminString
    MAX-ACCESS   read-only
    STATUS       current
    DESCRIPTION
        "Cisco Firepower equipment:BaseBoardCapProvider:model
        managed object property"
    ::= { cfprApEquipmentBaseBoardCapProviderEntry 12 }

cfprApEquipmentBaseBoardCapProviderPromCardType OBJECT-TYPE
    SYNTAX       Gauge32
    MAX-ACCESS   read-only
    STATUS       current
    DESCRIPTION
        "Cisco Firepower equipment:BaseBoardCapProvider:promCardType
        managed object property"
    ::= { cfprApEquipmentBaseBoardCapProviderEntry 13 }

cfprApEquipmentBaseBoardCapProviderRevision OBJECT-TYPE
    SYNTAX       SnmpAdminString
    MAX-ACCESS   read-only
    STATUS       current
    DESCRIPTION
        "Cisco Firepower equipment:BaseBoardCapProvider:revision
        managed object property"
    ::= { cfprApEquipmentBaseBoardCapProviderEntry 14 }

cfprApEquipmentBaseBoardCapProviderVendor OBJECT-TYPE
    SYNTAX       SnmpAdminString
    MAX-ACCESS   read-only
    STATUS       current
    DESCRIPTION
        "Cisco Firepower equipment:BaseBoardCapProvider:vendor
        managed object property"
    ::= { cfprApEquipmentBaseBoardCapProviderEntry 15 }

cfprApEquipmentBeaconCapProviderTable OBJECT-TYPE
    SYNTAX           SEQUENCE OF CfprApEquipmentBeaconCapProviderEntry
    MAX-ACCESS       not-accessible
    STATUS           current
    DESCRIPTION
        "Cisco Firepower equipment:BeaconCapProvider managed object table"
    ::= { cfprApEquipmentObjects 5 }

cfprApEquipmentBeaconCapProviderEntry OBJECT-TYPE
    SYNTAX           CfprApEquipmentBeaconCapProviderEntry
    MAX-ACCESS       not-accessible
    STATUS           current
    DESCRIPTION
        "Entry for the cfprApEquipmentBeaconCapProviderTable table."
    INDEX { cfprApEquipmentBeaconCapProviderInstanceId }
    ::= { cfprApEquipmentBeaconCapProviderTable 1 }

CfprApEquipmentBeaconCapProviderEntry ::= SEQUENCE {
    cfprApEquipmentBeaconCapProviderInstanceId                       CfprApManagedObjectId,
    cfprApEquipmentBeaconCapProviderDn                               CfprApManagedObjectDn,
    cfprApEquipmentBeaconCapProviderRn                               SnmpAdminString,
    cfprApEquipmentBeaconCapProviderDescr                            SnmpAdminString,
    cfprApEquipmentBeaconCapProviderIntId                            SnmpAdminString,
    cfprApEquipmentBeaconCapProviderName                             SnmpAdminString,
    cfprApEquipmentBeaconCapProviderPolicyLevel                      Gauge32,
    cfprApEquipmentBeaconCapProviderPolicyOwner                      CfprApPolicyPolicyOwner,
    cfprApEquipmentBeaconCapProviderPortModeBeacon                   TruthValue
}

cfprApEquipmentBeaconCapProviderInstanceId OBJECT-TYPE
    SYNTAX       CfprApManagedObjectId
    MAX-ACCESS   not-accessible
    STATUS       current
    DESCRIPTION
        "Instance identifier of the managed object."
    ::= { cfprApEquipmentBeaconCapProviderEntry 1 }

cfprApEquipmentBeaconCapProviderDn OBJECT-TYPE
    SYNTAX       CfprApManagedObjectDn
    MAX-ACCESS   read-only
    STATUS       current
    DESCRIPTION
        "Cisco Firepower equipment:BeaconCapProvider:dn
        managed object property"
    ::= { cfprApEquipmentBeaconCapProviderEntry 2 }

cfprApEquipmentBeaconCapProviderRn OBJECT-TYPE
    SYNTAX       SnmpAdminString
    MAX-ACCESS   read-only
    STATUS       current
    DESCRIPTION
        "Cisco Firepower equipment:BeaconCapProvider:rn
        managed object property"
    ::= { cfprApEquipmentBeaconCapProviderEntry 3 }

cfprApEquipmentBeaconCapProviderDescr OBJECT-TYPE
    SYNTAX       SnmpAdminString
    MAX-ACCESS   read-only
    STATUS       current
    DESCRIPTION
        "Cisco Firepower equipment:BeaconCapProvider:descr
        managed object property"
    ::= { cfprApEquipmentBeaconCapProviderEntry 4 }

cfprApEquipmentBeaconCapProviderIntId OBJECT-TYPE
    SYNTAX       SnmpAdminString
    MAX-ACCESS   read-only
    STATUS       current
    DESCRIPTION
        "Cisco Firepower equipment:BeaconCapProvider:intId
        managed object property"
    ::= { cfprApEquipmentBeaconCapProviderEntry 5 }

cfprApEquipmentBeaconCapProviderName OBJECT-TYPE
    SYNTAX       SnmpAdminString
    MAX-ACCESS   read-only
    STATUS       current
    DESCRIPTION
        "Cisco Firepower equipment:BeaconCapProvider:name
        managed object property"
    ::= { cfprApEquipmentBeaconCapProviderEntry 6 }

cfprApEquipmentBeaconCapProviderPolicyLevel OBJECT-TYPE
    SYNTAX       Gauge32
    MAX-ACCESS   read-only
    STATUS       current
    DESCRIPTION
        "Cisco Firepower equipment:BeaconCapProvider:policyLevel
        managed object property"
    ::= { cfprApEquipmentBeaconCapProviderEntry 7 }

cfprApEquipmentBeaconCapProviderPolicyOwner OBJECT-TYPE
    SYNTAX       CfprApPolicyPolicyOwner
    MAX-ACCESS   read-only
    STATUS       current
    DESCRIPTION
        "Cisco Firepower equipment:BeaconCapProvider:policyOwner
        managed object property"
    ::= { cfprApEquipmentBeaconCapProviderEntry 8 }

cfprApEquipmentBeaconCapProviderPortModeBeacon OBJECT-TYPE
    SYNTAX       TruthValue
    MAX-ACCESS   read-only
    STATUS       current
    DESCRIPTION
        "Cisco Firepower equipment:BeaconCapProvider:portModeBeacon
        managed object property"
    ::= { cfprApEquipmentBeaconCapProviderEntry 9 }

cfprApEquipmentBeaconLedTable OBJECT-TYPE
    SYNTAX           SEQUENCE OF CfprApEquipmentBeaconLedEntry
    MAX-ACCESS       not-accessible
    STATUS           current
    DESCRIPTION
        "Cisco Firepower equipment:BeaconLed managed object table"
    ::= { cfprApEquipmentObjects 6 }

cfprApEquipmentBeaconLedEntry OBJECT-TYPE
    SYNTAX           CfprApEquipmentBeaconLedEntry
    MAX-ACCESS       not-accessible
    STATUS           current
    DESCRIPTION
        "Entry for the cfprApEquipmentBeaconLedTable table."
    INDEX { cfprApEquipmentBeaconLedInstanceId }
    ::= { cfprApEquipmentBeaconLedTable 1 }

CfprApEquipmentBeaconLedEntry ::= SEQUENCE {
    cfprApEquipmentBeaconLedInstanceId                               CfprApManagedObjectId,
    cfprApEquipmentBeaconLedDn                                       CfprApManagedObjectDn,
    cfprApEquipmentBeaconLedRn                                       SnmpAdminString,
    cfprApEquipmentBeaconLedAdminState                               CfprApEquipmentBeaconLedState,
    cfprApEquipmentBeaconLedColor                                    CfprApEquipmentLedColor,
    cfprApEquipmentBeaconLedFsmDescr                                 SnmpAdminString,
    cfprApEquipmentBeaconLedFsmPrev                                  SnmpAdminString,
    cfprApEquipmentBeaconLedFsmProgr                                 Gauge32,
    cfprApEquipmentBeaconLedFsmRmtInvErrCode                         Gauge32,
    cfprApEquipmentBeaconLedFsmRmtInvErrDescr                        SnmpAdminString,
    cfprApEquipmentBeaconLedFsmRmtInvRslt                            CfprApConditionRemoteInvRslt,
    cfprApEquipmentBeaconLedFsmStageDescr                            SnmpAdminString,
    cfprApEquipmentBeaconLedFsmStamp                                 DateAndTime,
    cfprApEquipmentBeaconLedFsmStatus                                SnmpAdminString,
    cfprApEquipmentBeaconLedFsmTry                                   Gauge32,
    cfprApEquipmentBeaconLedId                                       Gauge32,
    cfprApEquipmentBeaconLedName                                     SnmpAdminString,
    cfprApEquipmentBeaconLedOperState                                CfprApEquipmentLedOperState
}

cfprApEquipmentBeaconLedInstanceId OBJECT-TYPE
    SYNTAX       CfprApManagedObjectId
    MAX-ACCESS   not-accessible
    STATUS       current
    DESCRIPTION
        "Instance identifier of the managed object."
    ::= { cfprApEquipmentBeaconLedEntry 1 }

cfprApEquipmentBeaconLedDn OBJECT-TYPE
    SYNTAX       CfprApManagedObjectDn
    MAX-ACCESS   read-only
    STATUS       current
    DESCRIPTION
        "Cisco Firepower equipment:BeaconLed:dn managed object property"
    ::= { cfprApEquipmentBeaconLedEntry 2 }

cfprApEquipmentBeaconLedRn OBJECT-TYPE
    SYNTAX       SnmpAdminString
    MAX-ACCESS   read-only
    STATUS       current
    DESCRIPTION
        "Cisco Firepower equipment:BeaconLed:rn managed object property"
    ::= { cfprApEquipmentBeaconLedEntry 3 }

cfprApEquipmentBeaconLedAdminState OBJECT-TYPE
    SYNTAX       CfprApEquipmentBeaconLedState
    MAX-ACCESS   read-only
    STATUS       current
    DESCRIPTION
        "Cisco Firepower equipment:BeaconLed:adminState
        managed object property"
    ::= { cfprApEquipmentBeaconLedEntry 4 }

cfprApEquipmentBeaconLedColor OBJECT-TYPE
    SYNTAX       CfprApEquipmentLedColor
    MAX-ACCESS   read-only
    STATUS       current
    DESCRIPTION
        "Cisco Firepower equipment:BeaconLed:color managed
        object property"
    ::= { cfprApEquipmentBeaconLedEntry 5 }

cfprApEquipmentBeaconLedFsmDescr OBJECT-TYPE
    SYNTAX       SnmpAdminString
    MAX-ACCESS   read-only
    STATUS       current
    DESCRIPTION
        "Cisco Firepower equipment:BeaconLed:fsmDescr managed
        object property"
    ::= { cfprApEquipmentBeaconLedEntry 6 }

cfprApEquipmentBeaconLedFsmPrev OBJECT-TYPE
    SYNTAX       SnmpAdminString
    MAX-ACCESS   read-only
    STATUS       current
    DESCRIPTION
        "Cisco Firepower equipment:BeaconLed:fsmPrev managed
        object property"
    ::= { cfprApEquipmentBeaconLedEntry 7 }

cfprApEquipmentBeaconLedFsmProgr OBJECT-TYPE
    SYNTAX       Gauge32
    MAX-ACCESS   read-only
    STATUS       current
    DESCRIPTION
        "Cisco Firepower equipment:BeaconLed:fsmProgr managed
        object property"
    ::= { cfprApEquipmentBeaconLedEntry 8 }

cfprApEquipmentBeaconLedFsmRmtInvErrCode OBJECT-TYPE
    SYNTAX       Gauge32
    MAX-ACCESS   read-only
    STATUS       current
    DESCRIPTION
        "Cisco Firepower equipment:BeaconLed:fsmRmtInvErrCode
        managed object property"
    ::= { cfprApEquipmentBeaconLedEntry 9 }

cfprApEquipmentBeaconLedFsmRmtInvErrDescr OBJECT-TYPE
    SYNTAX       SnmpAdminString
    MAX-ACCESS   read-only
    STATUS       current
    DESCRIPTION
        "Cisco Firepower equipment:BeaconLed:fsmRmtInvErrDescr
        managed object property"
    ::= { cfprApEquipmentBeaconLedEntry 10 }

cfprApEquipmentBeaconLedFsmRmtInvRslt OBJECT-TYPE
    SYNTAX       CfprApConditionRemoteInvRslt
    MAX-ACCESS   read-only
    STATUS       current
    DESCRIPTION
        "Cisco Firepower equipment:BeaconLed:fsmRmtInvRslt
        managed object property"
    ::= { cfprApEquipmentBeaconLedEntry 11 }

cfprApEquipmentBeaconLedFsmStageDescr OBJECT-TYPE
    SYNTAX       SnmpAdminString
    MAX-ACCESS   read-only
    STATUS       current
    DESCRIPTION
        "Cisco Firepower equipment:BeaconLed:fsmStageDescr
        managed object property"
    ::= { cfprApEquipmentBeaconLedEntry 12 }

cfprApEquipmentBeaconLedFsmStamp OBJECT-TYPE
    SYNTAX       DateAndTime
    MAX-ACCESS   read-only
    STATUS       current
    DESCRIPTION
        "Cisco Firepower equipment:BeaconLed:fsmStamp managed
        object property"
    ::= { cfprApEquipmentBeaconLedEntry 13 }

cfprApEquipmentBeaconLedFsmStatus OBJECT-TYPE
    SYNTAX       SnmpAdminString
    MAX-ACCESS   read-only
    STATUS       current
    DESCRIPTION
        "Cisco Firepower equipment:BeaconLed:fsmStatus
        managed object property"
    ::= { cfprApEquipmentBeaconLedEntry 14 }

cfprApEquipmentBeaconLedFsmTry OBJECT-TYPE
    SYNTAX       Gauge32
    MAX-ACCESS   read-only
    STATUS       current
    DESCRIPTION
        "Cisco Firepower equipment:BeaconLed:fsmTry managed
        object property"
    ::= { cfprApEquipmentBeaconLedEntry 15 }

cfprApEquipmentBeaconLedId OBJECT-TYPE
    SYNTAX       Gauge32
    MAX-ACCESS   read-only
    STATUS       current
    DESCRIPTION
        "Cisco Firepower equipment:BeaconLed:id managed object property"
    ::= { cfprApEquipmentBeaconLedEntry 16 }

cfprApEquipmentBeaconLedName OBJECT-TYPE
    SYNTAX       SnmpAdminString
    MAX-ACCESS   read-only
    STATUS       current
    DESCRIPTION
        "Cisco Firepower equipment:BeaconLed:name managed object property"
    ::= { cfprApEquipmentBeaconLedEntry 17 }

cfprApEquipmentBeaconLedOperState OBJECT-TYPE
    SYNTAX       CfprApEquipmentLedOperState
    MAX-ACCESS   read-only
    STATUS       current
    DESCRIPTION
        "Cisco Firepower equipment:BeaconLed:operState
        managed object property"
    ::= { cfprApEquipmentBeaconLedEntry 18 }

cfprApEquipmentBeaconLedFsmTable OBJECT-TYPE
    SYNTAX           SEQUENCE OF CfprApEquipmentBeaconLedFsmEntry
    MAX-ACCESS       not-accessible
    STATUS           current
    DESCRIPTION
        "Cisco Firepower equipment:BeaconLedFsm managed object table"
    ::= { cfprApEquipmentObjects 7 }

cfprApEquipmentBeaconLedFsmEntry OBJECT-TYPE
    SYNTAX           CfprApEquipmentBeaconLedFsmEntry
    MAX-ACCESS       not-accessible
    STATUS           current
    DESCRIPTION
        "Entry for the cfprApEquipmentBeaconLedFsmTable table."
    INDEX { cfprApEquipmentBeaconLedFsmInstanceId }
    ::= { cfprApEquipmentBeaconLedFsmTable 1 }

CfprApEquipmentBeaconLedFsmEntry ::= SEQUENCE {
    cfprApEquipmentBeaconLedFsmInstanceId                            CfprApManagedObjectId,
    cfprApEquipmentBeaconLedFsmDn                                    CfprApManagedObjectDn,
    cfprApEquipmentBeaconLedFsmRn                                    SnmpAdminString,
    cfprApEquipmentBeaconLedFsmCompletionTime                        DateAndTime,
    cfprApEquipmentBeaconLedFsmCurrentFsm                            CfprApEquipmentBeaconLedFsmCurrentFsm,
    cfprApEquipmentBeaconLedFsmDescrData                             SnmpAdminString,
    cfprApEquipmentBeaconLedFsmFsmStatus                             CfprApFsmFsmStageStatus,
    cfprApEquipmentBeaconLedFsmProgress                              Gauge32,
    cfprApEquipmentBeaconLedFsmRmtErrCode                            Gauge32,
    cfprApEquipmentBeaconLedFsmRmtErrDescr                           SnmpAdminString,
    cfprApEquipmentBeaconLedFsmRmtRslt                               CfprApConditionRemoteInvRslt
}

cfprApEquipmentBeaconLedFsmInstanceId OBJECT-TYPE
    SYNTAX       CfprApManagedObjectId
    MAX-ACCESS   not-accessible
    STATUS       current
    DESCRIPTION
        "Instance identifier of the managed object."
    ::= { cfprApEquipmentBeaconLedFsmEntry 1 }

cfprApEquipmentBeaconLedFsmDn OBJECT-TYPE
    SYNTAX       CfprApManagedObjectDn
    MAX-ACCESS   read-only
    STATUS       current
    DESCRIPTION
        "Cisco Firepower equipment:BeaconLedFsm:dn managed
        object property"
    ::= { cfprApEquipmentBeaconLedFsmEntry 2 }

cfprApEquipmentBeaconLedFsmRn OBJECT-TYPE
    SYNTAX       SnmpAdminString
    MAX-ACCESS   read-only
    STATUS       current
    DESCRIPTION
        "Cisco Firepower equipment:BeaconLedFsm:rn managed
        object property"
    ::= { cfprApEquipmentBeaconLedFsmEntry 3 }

cfprApEquipmentBeaconLedFsmCompletionTime OBJECT-TYPE
    SYNTAX       DateAndTime
    MAX-ACCESS   read-only
    STATUS       current
    DESCRIPTION
        "Cisco Firepower equipment:BeaconLedFsm:completionTime
        managed object property"
    ::= { cfprApEquipmentBeaconLedFsmEntry 4 }

cfprApEquipmentBeaconLedFsmCurrentFsm OBJECT-TYPE
    SYNTAX       CfprApEquipmentBeaconLedFsmCurrentFsm
    MAX-ACCESS   read-only
    STATUS       current
    DESCRIPTION
        "Cisco Firepower equipment:BeaconLedFsm:currentFsm
        managed object property"
    ::= { cfprApEquipmentBeaconLedFsmEntry 5 }

cfprApEquipmentBeaconLedFsmDescrData OBJECT-TYPE
    SYNTAX       SnmpAdminString
    MAX-ACCESS   read-only
    STATUS       current
    DESCRIPTION
        "Cisco Firepower equipment:BeaconLedFsm:descr managed
        object property"
    ::= { cfprApEquipmentBeaconLedFsmEntry 6 }

cfprApEquipmentBeaconLedFsmFsmStatus OBJECT-TYPE
    SYNTAX       CfprApFsmFsmStageStatus
    MAX-ACCESS   read-only
    STATUS       current
    DESCRIPTION
        "Cisco Firepower equipment:BeaconLedFsm:fsmStatus
        managed object property"
    ::= { cfprApEquipmentBeaconLedFsmEntry 7 }

cfprApEquipmentBeaconLedFsmProgress OBJECT-TYPE
    SYNTAX       Gauge32
    MAX-ACCESS   read-only
    STATUS       current
    DESCRIPTION
        "Cisco Firepower equipment:BeaconLedFsm:progress
        managed object property"
    ::= { cfprApEquipmentBeaconLedFsmEntry 8 }

cfprApEquipmentBeaconLedFsmRmtErrCode OBJECT-TYPE
    SYNTAX       Gauge32
    MAX-ACCESS   read-only
    STATUS       current
    DESCRIPTION
        "Cisco Firepower equipment:BeaconLedFsm:rmtErrCode
        managed object property"
    ::= { cfprApEquipmentBeaconLedFsmEntry 9 }

cfprApEquipmentBeaconLedFsmRmtErrDescr OBJECT-TYPE
    SYNTAX       SnmpAdminString
    MAX-ACCESS   read-only
    STATUS       current
    DESCRIPTION
        "Cisco Firepower equipment:BeaconLedFsm:rmtErrDescr
        managed object property"
    ::= { cfprApEquipmentBeaconLedFsmEntry 10 }

cfprApEquipmentBeaconLedFsmRmtRslt OBJECT-TYPE
    SYNTAX       CfprApConditionRemoteInvRslt
    MAX-ACCESS   read-only
    STATUS       current
    DESCRIPTION
        "Cisco Firepower equipment:BeaconLedFsm:rmtRslt
        managed object property"
    ::= { cfprApEquipmentBeaconLedFsmEntry 11 }

cfprApEquipmentBeaconLedFsmStageTable OBJECT-TYPE
    SYNTAX           SEQUENCE OF CfprApEquipmentBeaconLedFsmStageEntry
    MAX-ACCESS       not-accessible
    STATUS           current
    DESCRIPTION
        "Cisco Firepower equipment:BeaconLedFsmStage managed object table"
    ::= { cfprApEquipmentObjects 8 }

cfprApEquipmentBeaconLedFsmStageEntry OBJECT-TYPE
    SYNTAX           CfprApEquipmentBeaconLedFsmStageEntry
    MAX-ACCESS       not-accessible
    STATUS           current
    DESCRIPTION
        "Entry for the cfprApEquipmentBeaconLedFsmStageTable table."
    INDEX { cfprApEquipmentBeaconLedFsmStageInstanceId }
    ::= { cfprApEquipmentBeaconLedFsmStageTable 1 }

CfprApEquipmentBeaconLedFsmStageEntry ::= SEQUENCE {
    cfprApEquipmentBeaconLedFsmStageInstanceId                       CfprApManagedObjectId,
    cfprApEquipmentBeaconLedFsmStageDn                               CfprApManagedObjectDn,
    cfprApEquipmentBeaconLedFsmStageRn                               SnmpAdminString,
    cfprApEquipmentBeaconLedFsmStageDescrData                        SnmpAdminString,
    cfprApEquipmentBeaconLedFsmStageLastUpdateTime                   DateAndTime,
    cfprApEquipmentBeaconLedFsmStageName                             CfprApEquipmentBeaconLedFsmStageName,
    cfprApEquipmentBeaconLedFsmStageOrder                            Gauge32,
    cfprApEquipmentBeaconLedFsmStageRetry                            Gauge32,
    cfprApEquipmentBeaconLedFsmStageStageStatus                      CfprApFsmFsmStageStatus
}

cfprApEquipmentBeaconLedFsmStageInstanceId OBJECT-TYPE
    SYNTAX       CfprApManagedObjectId
    MAX-ACCESS   not-accessible
    STATUS       current
    DESCRIPTION
        "Instance identifier of the managed object."
    ::= { cfprApEquipmentBeaconLedFsmStageEntry 1 }

cfprApEquipmentBeaconLedFsmStageDn OBJECT-TYPE
    SYNTAX       CfprApManagedObjectDn
    MAX-ACCESS   read-only
    STATUS       current
    DESCRIPTION
        "Cisco Firepower equipment:BeaconLedFsmStage:dn
        managed object property"
    ::= { cfprApEquipmentBeaconLedFsmStageEntry 2 }

cfprApEquipmentBeaconLedFsmStageRn OBJECT-TYPE
    SYNTAX       SnmpAdminString
    MAX-ACCESS   read-only
    STATUS       current
    DESCRIPTION
        "Cisco Firepower equipment:BeaconLedFsmStage:rn
        managed object property"
    ::= { cfprApEquipmentBeaconLedFsmStageEntry 3 }

cfprApEquipmentBeaconLedFsmStageDescrData OBJECT-TYPE
    SYNTAX       SnmpAdminString
    MAX-ACCESS   read-only
    STATUS       current
    DESCRIPTION
        "Cisco Firepower equipment:BeaconLedFsmStage:descr
        managed object property"
    ::= { cfprApEquipmentBeaconLedFsmStageEntry 4 }

cfprApEquipmentBeaconLedFsmStageLastUpdateTime OBJECT-TYPE
    SYNTAX       DateAndTime
    MAX-ACCESS   read-only
    STATUS       current
    DESCRIPTION
        "Cisco Firepower equipment:BeaconLedFsmStage:lastUpdateTime
        managed object property"
    ::= { cfprApEquipmentBeaconLedFsmStageEntry 5 }

cfprApEquipmentBeaconLedFsmStageName OBJECT-TYPE
    SYNTAX       CfprApEquipmentBeaconLedFsmStageName
    MAX-ACCESS   read-only
    STATUS       current
    DESCRIPTION
        "Cisco Firepower equipment:BeaconLedFsmStage:name
        managed object property"
    ::= { cfprApEquipmentBeaconLedFsmStageEntry 6 }

cfprApEquipmentBeaconLedFsmStageOrder OBJECT-TYPE
    SYNTAX       Gauge32
    MAX-ACCESS   read-only
    STATUS       current
    DESCRIPTION
        "Cisco Firepower equipment:BeaconLedFsmStage:order
        managed object property"
    ::= { cfprApEquipmentBeaconLedFsmStageEntry 7 }

cfprApEquipmentBeaconLedFsmStageRetry OBJECT-TYPE
    SYNTAX       Gauge32
    MAX-ACCESS   read-only
    STATUS       current
    DESCRIPTION
        "Cisco Firepower equipment:BeaconLedFsmStage:retry
        managed object property"
    ::= { cfprApEquipmentBeaconLedFsmStageEntry 8 }

cfprApEquipmentBeaconLedFsmStageStageStatus OBJECT-TYPE
    SYNTAX       CfprApFsmFsmStageStatus
    MAX-ACCESS   read-only
    STATUS       current
    DESCRIPTION
        "Cisco Firepower equipment:BeaconLedFsmStage:stageStatus
        managed object property"
    ::= { cfprApEquipmentBeaconLedFsmStageEntry 9 }

cfprApEquipmentBeaconLedFsmTaskTable OBJECT-TYPE
    SYNTAX           SEQUENCE OF CfprApEquipmentBeaconLedFsmTaskEntry
    MAX-ACCESS       not-accessible
    STATUS           current
    DESCRIPTION
        "Cisco Firepower equipment:BeaconLedFsmTask managed object table"
    ::= { cfprApEquipmentObjects 9 }

cfprApEquipmentBeaconLedFsmTaskEntry OBJECT-TYPE
    SYNTAX           CfprApEquipmentBeaconLedFsmTaskEntry
    MAX-ACCESS       not-accessible
    STATUS           current
    DESCRIPTION
        "Entry for the cfprApEquipmentBeaconLedFsmTaskTable table."
    INDEX { cfprApEquipmentBeaconLedFsmTaskInstanceId }
    ::= { cfprApEquipmentBeaconLedFsmTaskTable 1 }

CfprApEquipmentBeaconLedFsmTaskEntry ::= SEQUENCE {
    cfprApEquipmentBeaconLedFsmTaskInstanceId                        CfprApManagedObjectId,
    cfprApEquipmentBeaconLedFsmTaskDn                                CfprApManagedObjectDn,
    cfprApEquipmentBeaconLedFsmTaskRn                                SnmpAdminString,
    cfprApEquipmentBeaconLedFsmTaskCompletion                        CfprApFsmCompletion,
    cfprApEquipmentBeaconLedFsmTaskFlags                             CfprApFsmFlags,
    cfprApEquipmentBeaconLedFsmTaskItem                              CfprApEquipmentBeaconLedFsmTaskItem,
    cfprApEquipmentBeaconLedFsmTaskSeqId                             Gauge32
}

cfprApEquipmentBeaconLedFsmTaskInstanceId OBJECT-TYPE
    SYNTAX       CfprApManagedObjectId
    MAX-ACCESS   not-accessible
    STATUS       current
    DESCRIPTION
        "Instance identifier of the managed object."
    ::= { cfprApEquipmentBeaconLedFsmTaskEntry 1 }

cfprApEquipmentBeaconLedFsmTaskDn OBJECT-TYPE
    SYNTAX       CfprApManagedObjectDn
    MAX-ACCESS   read-only
    STATUS       current
    DESCRIPTION
        "Cisco Firepower equipment:BeaconLedFsmTask:dn
        managed object property"
    ::= { cfprApEquipmentBeaconLedFsmTaskEntry 2 }

cfprApEquipmentBeaconLedFsmTaskRn OBJECT-TYPE
    SYNTAX       SnmpAdminString
    MAX-ACCESS   read-only
    STATUS       current
    DESCRIPTION
        "Cisco Firepower equipment:BeaconLedFsmTask:rn
        managed object property"
    ::= { cfprApEquipmentBeaconLedFsmTaskEntry 3 }

cfprApEquipmentBeaconLedFsmTaskCompletion OBJECT-TYPE
    SYNTAX       CfprApFsmCompletion
    MAX-ACCESS   read-only
    STATUS       current
    DESCRIPTION
        "Cisco Firepower equipment:BeaconLedFsmTask:completion
        managed object property"
    ::= { cfprApEquipmentBeaconLedFsmTaskEntry 4 }

cfprApEquipmentBeaconLedFsmTaskFlags OBJECT-TYPE
    SYNTAX       CfprApFsmFlags
    MAX-ACCESS   read-only
    STATUS       current
    DESCRIPTION
        "Cisco Firepower equipment:BeaconLedFsmTask:flags
        managed object property"
    ::= { cfprApEquipmentBeaconLedFsmTaskEntry 5 }

cfprApEquipmentBeaconLedFsmTaskItem OBJECT-TYPE
    SYNTAX       CfprApEquipmentBeaconLedFsmTaskItem
    MAX-ACCESS   read-only
    STATUS       current
    DESCRIPTION
        "Cisco Firepower equipment:BeaconLedFsmTask:item
        managed object property"
    ::= { cfprApEquipmentBeaconLedFsmTaskEntry 6 }

cfprApEquipmentBeaconLedFsmTaskSeqId OBJECT-TYPE
    SYNTAX       Gauge32
    MAX-ACCESS   read-only
    STATUS       current
    DESCRIPTION
        "Cisco Firepower equipment:BeaconLedFsmTask:seqId
        managed object property"
    ::= { cfprApEquipmentBeaconLedFsmTaskEntry 7 }

cfprApEquipmentBiosDefTable OBJECT-TYPE
    SYNTAX           SEQUENCE OF CfprApEquipmentBiosDefEntry
    MAX-ACCESS       not-accessible
    STATUS           current
    DESCRIPTION
        "Cisco Firepower equipment:BiosDef managed object table"
    ::= { cfprApEquipmentObjects 10 }

cfprApEquipmentBiosDefEntry OBJECT-TYPE
    SYNTAX           CfprApEquipmentBiosDefEntry
    MAX-ACCESS       not-accessible
    STATUS           current
    DESCRIPTION
        "Entry for the cfprApEquipmentBiosDefTable table."
    INDEX { cfprApEquipmentBiosDefInstanceId }
    ::= { cfprApEquipmentBiosDefTable 1 }

CfprApEquipmentBiosDefEntry ::= SEQUENCE {
    cfprApEquipmentBiosDefInstanceId                                 CfprApManagedObjectId,
    cfprApEquipmentBiosDefDn                                         CfprApManagedObjectDn,
    cfprApEquipmentBiosDefRn                                         SnmpAdminString,
    cfprApEquipmentBiosDefDescr                                      SnmpAdminString,
    cfprApEquipmentBiosDefIntId                                      SnmpAdminString,
    cfprApEquipmentBiosDefName                                       SnmpAdminString,
    cfprApEquipmentBiosDefPolicyLevel                                Gauge32,
    cfprApEquipmentBiosDefPolicyOwner                                CfprApPolicyPolicyOwner,
    cfprApEquipmentBiosDefResetOn                                    CfprApEquipmentResetOn,
    cfprApEquipmentBiosDefSecureBios                                 CfprApEquipmentSecureBios,
    cfprApEquipmentBiosDefStorageMethod                              CfprApEquipmentStorageMethod,
    cfprApEquipmentBiosDefUpdateMethod                               CfprApEquipmentBiosUpdateMethod
}

cfprApEquipmentBiosDefInstanceId OBJECT-TYPE
    SYNTAX       CfprApManagedObjectId
    MAX-ACCESS   not-accessible
    STATUS       current
    DESCRIPTION
        "Instance identifier of the managed object."
    ::= { cfprApEquipmentBiosDefEntry 1 }

cfprApEquipmentBiosDefDn OBJECT-TYPE
    SYNTAX       CfprApManagedObjectDn
    MAX-ACCESS   read-only
    STATUS       current
    DESCRIPTION
        "Cisco Firepower equipment:BiosDef:dn managed object property"
    ::= { cfprApEquipmentBiosDefEntry 2 }

cfprApEquipmentBiosDefRn OBJECT-TYPE
    SYNTAX       SnmpAdminString
    MAX-ACCESS   read-only
    STATUS       current
    DESCRIPTION
        "Cisco Firepower equipment:BiosDef:rn managed object property"
    ::= { cfprApEquipmentBiosDefEntry 3 }

cfprApEquipmentBiosDefDescr OBJECT-TYPE
    SYNTAX       SnmpAdminString
    MAX-ACCESS   read-only
    STATUS       current
    DESCRIPTION
        "Cisco Firepower equipment:BiosDef:descr managed object property"
    ::= { cfprApEquipmentBiosDefEntry 4 }

cfprApEquipmentBiosDefIntId OBJECT-TYPE
    SYNTAX       SnmpAdminString
    MAX-ACCESS   read-only
    STATUS       current
    DESCRIPTION
        "Cisco Firepower equipment:BiosDef:intId managed object property"
    ::= { cfprApEquipmentBiosDefEntry 5 }

cfprApEquipmentBiosDefName OBJECT-TYPE
    SYNTAX       SnmpAdminString
    MAX-ACCESS   read-only
    STATUS       current
    DESCRIPTION
        "Cisco Firepower equipment:BiosDef:name managed object property"
    ::= { cfprApEquipmentBiosDefEntry 6 }

cfprApEquipmentBiosDefPolicyLevel OBJECT-TYPE
    SYNTAX       Gauge32
    MAX-ACCESS   read-only
    STATUS       current
    DESCRIPTION
        "Cisco Firepower equipment:BiosDef:policyLevel
        managed object property"
    ::= { cfprApEquipmentBiosDefEntry 7 }

cfprApEquipmentBiosDefPolicyOwner OBJECT-TYPE
    SYNTAX       CfprApPolicyPolicyOwner
    MAX-ACCESS   read-only
    STATUS       current
    DESCRIPTION
        "Cisco Firepower equipment:BiosDef:policyOwner
        managed object property"
    ::= { cfprApEquipmentBiosDefEntry 8 }

cfprApEquipmentBiosDefResetOn OBJECT-TYPE
    SYNTAX       CfprApEquipmentResetOn
    MAX-ACCESS   read-only
    STATUS       current
    DESCRIPTION
        "Cisco Firepower equipment:BiosDef:resetOn managed
        object property"
    ::= { cfprApEquipmentBiosDefEntry 9 }

cfprApEquipmentBiosDefSecureBios OBJECT-TYPE
    SYNTAX       CfprApEquipmentSecureBios
    MAX-ACCESS   read-only
    STATUS       current
    DESCRIPTION
        "Cisco Firepower equipment:BiosDef:secureBios managed
        object property"
    ::= { cfprApEquipmentBiosDefEntry 10 }

cfprApEquipmentBiosDefStorageMethod OBJECT-TYPE
    SYNTAX       CfprApEquipmentStorageMethod
    MAX-ACCESS   read-only
    STATUS       current
    DESCRIPTION
        "Cisco Firepower equipment:BiosDef:storageMethod
        managed object property"
    ::= { cfprApEquipmentBiosDefEntry 11 }

cfprApEquipmentBiosDefUpdateMethod OBJECT-TYPE
    SYNTAX       CfprApEquipmentBiosUpdateMethod
    MAX-ACCESS   read-only
    STATUS       current
    DESCRIPTION
        "Cisco Firepower equipment:BiosDef:updateMethod
        managed object property"
    ::= { cfprApEquipmentBiosDefEntry 12 }

cfprApEquipmentBladeAGLibraryTable OBJECT-TYPE
    SYNTAX           SEQUENCE OF CfprApEquipmentBladeAGLibraryEntry
    MAX-ACCESS       not-accessible
    STATUS           current
    DESCRIPTION
        "Cisco Firepower equipment:BladeAGLibrary managed object table"
    ::= { cfprApEquipmentObjects 11 }

cfprApEquipmentBladeAGLibraryEntry OBJECT-TYPE
    SYNTAX           CfprApEquipmentBladeAGLibraryEntry
    MAX-ACCESS       not-accessible
    STATUS           current
    DESCRIPTION
        "Entry for the cfprApEquipmentBladeAGLibraryTable table."
    INDEX { cfprApEquipmentBladeAGLibraryInstanceId }
    ::= { cfprApEquipmentBladeAGLibraryTable 1 }

CfprApEquipmentBladeAGLibraryEntry ::= SEQUENCE {
    cfprApEquipmentBladeAGLibraryInstanceId                          CfprApManagedObjectId,
    cfprApEquipmentBladeAGLibraryDn                                  CfprApManagedObjectDn,
    cfprApEquipmentBladeAGLibraryRn                                  SnmpAdminString,
    cfprApEquipmentBladeAGLibraryDescr                               SnmpAdminString,
    cfprApEquipmentBladeAGLibraryIntId                               SnmpAdminString,
    cfprApEquipmentBladeAGLibraryName                                SnmpAdminString,
    cfprApEquipmentBladeAGLibraryPolicyLevel                         Gauge32,
    cfprApEquipmentBladeAGLibraryPolicyOwner                         CfprApPolicyPolicyOwner
}

cfprApEquipmentBladeAGLibraryInstanceId OBJECT-TYPE
    SYNTAX       CfprApManagedObjectId
    MAX-ACCESS   not-accessible
    STATUS       current
    DESCRIPTION
        "Instance identifier of the managed object."
    ::= { cfprApEquipmentBladeAGLibraryEntry 1 }

cfprApEquipmentBladeAGLibraryDn OBJECT-TYPE
    SYNTAX       CfprApManagedObjectDn
    MAX-ACCESS   read-only
    STATUS       current
    DESCRIPTION
        "Cisco Firepower equipment:BladeAGLibrary:dn managed
        object property"
    ::= { cfprApEquipmentBladeAGLibraryEntry 2 }

cfprApEquipmentBladeAGLibraryRn OBJECT-TYPE
    SYNTAX       SnmpAdminString
    MAX-ACCESS   read-only
    STATUS       current
    DESCRIPTION
        "Cisco Firepower equipment:BladeAGLibrary:rn managed
        object property"
    ::= { cfprApEquipmentBladeAGLibraryEntry 3 }

cfprApEquipmentBladeAGLibraryDescr OBJECT-TYPE
    SYNTAX       SnmpAdminString
    MAX-ACCESS   read-only
    STATUS       current
    DESCRIPTION
        "Cisco Firepower equipment:BladeAGLibrary:descr
        managed object property"
    ::= { cfprApEquipmentBladeAGLibraryEntry 4 }

cfprApEquipmentBladeAGLibraryIntId OBJECT-TYPE
    SYNTAX       SnmpAdminString
    MAX-ACCESS   read-only
    STATUS       current
    DESCRIPTION
        "Cisco Firepower equipment:BladeAGLibrary:intId
        managed object property"
    ::= { cfprApEquipmentBladeAGLibraryEntry 5 }

cfprApEquipmentBladeAGLibraryName OBJECT-TYPE
    SYNTAX       SnmpAdminString
    MAX-ACCESS   read-only
    STATUS       current
    DESCRIPTION
        "Cisco Firepower equipment:BladeAGLibrary:name
        managed object property"
    ::= { cfprApEquipmentBladeAGLibraryEntry 6 }

cfprApEquipmentBladeAGLibraryPolicyLevel OBJECT-TYPE
    SYNTAX       Gauge32
    MAX-ACCESS   read-only
    STATUS       current
    DESCRIPTION
        "Cisco Firepower equipment:BladeAGLibrary:policyLevel
        managed object property"
    ::= { cfprApEquipmentBladeAGLibraryEntry 7 }

cfprApEquipmentBladeAGLibraryPolicyOwner OBJECT-TYPE
    SYNTAX       CfprApPolicyPolicyOwner
    MAX-ACCESS   read-only
    STATUS       current
    DESCRIPTION
        "Cisco Firepower equipment:BladeAGLibrary:policyOwner
        managed object property"
    ::= { cfprApEquipmentBladeAGLibraryEntry 8 }

cfprApEquipmentBladeAggregationCapRefTable OBJECT-TYPE
    SYNTAX           SEQUENCE OF CfprApEquipmentBladeAggregationCapRefEntry
    MAX-ACCESS       not-accessible
    STATUS           current
    DESCRIPTION
        "Cisco Firepower equipment:BladeAggregationCapRef
        managed object table"
    ::= { cfprApEquipmentObjects 12 }

cfprApEquipmentBladeAggregationCapRefEntry OBJECT-TYPE
    SYNTAX           CfprApEquipmentBladeAggregationCapRefEntry
    MAX-ACCESS       not-accessible
    STATUS           current
    DESCRIPTION
        "Entry for the cfprApEquipmentBladeAggregationCapRefTable table."
    INDEX { cfprApEquipmentBladeAggregationCapRefInstanceId }
    ::= { cfprApEquipmentBladeAggregationCapRefTable 1 }

CfprApEquipmentBladeAggregationCapRefEntry ::= SEQUENCE {
    cfprApEquipmentBladeAggregationCapRefInstanceId                  CfprApManagedObjectId,
    cfprApEquipmentBladeAggregationCapRefDn                          CfprApManagedObjectDn,
    cfprApEquipmentBladeAggregationCapRefRn                          SnmpAdminString,
    cfprApEquipmentBladeAggregationCapRefIsSupported                 TruthValue
}

cfprApEquipmentBladeAggregationCapRefInstanceId OBJECT-TYPE
    SYNTAX       CfprApManagedObjectId
    MAX-ACCESS   not-accessible
    STATUS       current
    DESCRIPTION
        "Instance identifier of the managed object."
    ::= { cfprApEquipmentBladeAggregationCapRefEntry 1 }

cfprApEquipmentBladeAggregationCapRefDn OBJECT-TYPE
    SYNTAX       CfprApManagedObjectDn
    MAX-ACCESS   read-only
    STATUS       current
    DESCRIPTION
        "Cisco Firepower equipment:BladeAggregationCapRef:dn
        managed object property"
    ::= { cfprApEquipmentBladeAggregationCapRefEntry 2 }

cfprApEquipmentBladeAggregationCapRefRn OBJECT-TYPE
    SYNTAX       SnmpAdminString
    MAX-ACCESS   read-only
    STATUS       current
    DESCRIPTION
        "Cisco Firepower equipment:BladeAggregationCapRef:rn
        managed object property"
    ::= { cfprApEquipmentBladeAggregationCapRefEntry 3 }

cfprApEquipmentBladeAggregationCapRefIsSupported OBJECT-TYPE
    SYNTAX       TruthValue
    MAX-ACCESS   read-only
    STATUS       current
    DESCRIPTION
        "Cisco Firepower equipment:BladeAggregationCapRef:isSupported
        managed object property"
    ::= { cfprApEquipmentBladeAggregationCapRefEntry 4 }

cfprApEquipmentBladeBiosCapProviderTable OBJECT-TYPE
    SYNTAX           SEQUENCE OF CfprApEquipmentBladeBiosCapProviderEntry
    MAX-ACCESS       not-accessible
    STATUS           current
    DESCRIPTION
        "Cisco Firepower equipment:BladeBiosCapProvider
        managed object table"
    ::= { cfprApEquipmentObjects 13 }

cfprApEquipmentBladeBiosCapProviderEntry OBJECT-TYPE
    SYNTAX           CfprApEquipmentBladeBiosCapProviderEntry
    MAX-ACCESS       not-accessible
    STATUS           current
    DESCRIPTION
        "Entry for the cfprApEquipmentBladeBiosCapProviderTable table."
    INDEX { cfprApEquipmentBladeBiosCapProviderInstanceId }
    ::= { cfprApEquipmentBladeBiosCapProviderTable 1 }

CfprApEquipmentBladeBiosCapProviderEntry ::= SEQUENCE {
    cfprApEquipmentBladeBiosCapProviderInstanceId                    CfprApManagedObjectId,
    cfprApEquipmentBladeBiosCapProviderDn                            CfprApManagedObjectDn,
    cfprApEquipmentBladeBiosCapProviderRn                            SnmpAdminString,
    cfprApEquipmentBladeBiosCapProviderDeleted                       TruthValue,
    cfprApEquipmentBladeBiosCapProviderDeprecated                    TruthValue,
    cfprApEquipmentBladeBiosCapProviderElementLoadFailures           Gauge32,
    cfprApEquipmentBladeBiosCapProviderElementsLoaded                Gauge32,
    cfprApEquipmentBladeBiosCapProviderGencount                      Gauge32,
    cfprApEquipmentBladeBiosCapProviderLoadErrors                    Gauge32,
    cfprApEquipmentBladeBiosCapProviderLoadWarnings                  Gauge32,
    cfprApEquipmentBladeBiosCapProviderMgmtPlaneVer                  SnmpAdminString,
    cfprApEquipmentBladeBiosCapProviderModel                         SnmpAdminString,
    cfprApEquipmentBladeBiosCapProviderProductName                   SnmpAdminString,
    cfprApEquipmentBladeBiosCapProviderPromCardType                  Gauge32,
    cfprApEquipmentBladeBiosCapProviderRevision                      SnmpAdminString,
    cfprApEquipmentBladeBiosCapProviderVendor                        SnmpAdminString
}

cfprApEquipmentBladeBiosCapProviderInstanceId OBJECT-TYPE
    SYNTAX       CfprApManagedObjectId
    MAX-ACCESS   not-accessible
    STATUS       current
    DESCRIPTION
        "Instance identifier of the managed object."
    ::= { cfprApEquipmentBladeBiosCapProviderEntry 1 }

cfprApEquipmentBladeBiosCapProviderDn OBJECT-TYPE
    SYNTAX       CfprApManagedObjectDn
    MAX-ACCESS   read-only
    STATUS       current
    DESCRIPTION
        "Cisco Firepower equipment:BladeBiosCapProvider:dn
        managed object property"
    ::= { cfprApEquipmentBladeBiosCapProviderEntry 2 }

cfprApEquipmentBladeBiosCapProviderRn OBJECT-TYPE
    SYNTAX       SnmpAdminString
    MAX-ACCESS   read-only
    STATUS       current
    DESCRIPTION
        "Cisco Firepower equipment:BladeBiosCapProvider:rn
        managed object property"
    ::= { cfprApEquipmentBladeBiosCapProviderEntry 3 }

cfprApEquipmentBladeBiosCapProviderDeleted OBJECT-TYPE
    SYNTAX       TruthValue
    MAX-ACCESS   read-only
    STATUS       current
    DESCRIPTION
        "Cisco Firepower equipment:BladeBiosCapProvider:deleted
        managed object property"
    ::= { cfprApEquipmentBladeBiosCapProviderEntry 4 }

cfprApEquipmentBladeBiosCapProviderDeprecated OBJECT-TYPE
    SYNTAX       TruthValue
    MAX-ACCESS   read-only
    STATUS       current
    DESCRIPTION
        "Cisco Firepower equipment:BladeBiosCapProvider:deprecated
        managed object property"
    ::= { cfprApEquipmentBladeBiosCapProviderEntry 5 }

cfprApEquipmentBladeBiosCapProviderElementLoadFailures OBJECT-TYPE
    SYNTAX       Gauge32
    MAX-ACCESS   read-only
    STATUS       current
    DESCRIPTION
        "Cisco Firepower equipment:BladeBiosCapProvider:elementLoadFailure
        s managed object property"
    ::= { cfprApEquipmentBladeBiosCapProviderEntry 6 }

cfprApEquipmentBladeBiosCapProviderElementsLoaded OBJECT-TYPE
    SYNTAX       Gauge32
    MAX-ACCESS   read-only
    STATUS       current
    DESCRIPTION
        "Cisco Firepower equipment:BladeBiosCapProvider:elementsLoaded
        managed object property"
    ::= { cfprApEquipmentBladeBiosCapProviderEntry 7 }

cfprApEquipmentBladeBiosCapProviderGencount OBJECT-TYPE
    SYNTAX       Gauge32
    MAX-ACCESS   read-only
    STATUS       current
    DESCRIPTION
        "Cisco Firepower equipment:BladeBiosCapProvider:gencount
        managed object property"
    ::= { cfprApEquipmentBladeBiosCapProviderEntry 8 }

cfprApEquipmentBladeBiosCapProviderLoadErrors OBJECT-TYPE
    SYNTAX       Gauge32
    MAX-ACCESS   read-only
    STATUS       current
    DESCRIPTION
        "Cisco Firepower equipment:BladeBiosCapProvider:loadErrors
        managed object property"
    ::= { cfprApEquipmentBladeBiosCapProviderEntry 9 }

cfprApEquipmentBladeBiosCapProviderLoadWarnings OBJECT-TYPE
    SYNTAX       Gauge32
    MAX-ACCESS   read-only
    STATUS       current
    DESCRIPTION
        "Cisco Firepower equipment:BladeBiosCapProvider:loadWarnings
        managed object property"
    ::= { cfprApEquipmentBladeBiosCapProviderEntry 10 }

cfprApEquipmentBladeBiosCapProviderMgmtPlaneVer OBJECT-TYPE
    SYNTAX       SnmpAdminString
    MAX-ACCESS   read-only
    STATUS       current
    DESCRIPTION
        "Cisco Firepower equipment:BladeBiosCapProvider:mgmtPlaneVer
        managed object property"
    ::= { cfprApEquipmentBladeBiosCapProviderEntry 11 }

cfprApEquipmentBladeBiosCapProviderModel OBJECT-TYPE
    SYNTAX       SnmpAdminString
    MAX-ACCESS   read-only
    STATUS       current
    DESCRIPTION
        "Cisco Firepower equipment:BladeBiosCapProvider:model
        managed object property"
    ::= { cfprApEquipmentBladeBiosCapProviderEntry 12 }

cfprApEquipmentBladeBiosCapProviderProductName OBJECT-TYPE
    SYNTAX       SnmpAdminString
    MAX-ACCESS   read-only
    STATUS       current
    DESCRIPTION
        "Cisco Firepower equipment:BladeBiosCapProvider:productName
        managed object property"
    ::= { cfprApEquipmentBladeBiosCapProviderEntry 13 }

cfprApEquipmentBladeBiosCapProviderPromCardType OBJECT-TYPE
    SYNTAX       Gauge32
    MAX-ACCESS   read-only
    STATUS       current
    DESCRIPTION
        "Cisco Firepower equipment:BladeBiosCapProvider:promCardType
        managed object property"
    ::= { cfprApEquipmentBladeBiosCapProviderEntry 14 }

cfprApEquipmentBladeBiosCapProviderRevision OBJECT-TYPE
    SYNTAX       SnmpAdminString
    MAX-ACCESS   read-only
    STATUS       current
    DESCRIPTION
        "Cisco Firepower equipment:BladeBiosCapProvider:revision
        managed object property"
    ::= { cfprApEquipmentBladeBiosCapProviderEntry 15 }

cfprApEquipmentBladeBiosCapProviderVendor OBJECT-TYPE
    SYNTAX       SnmpAdminString
    MAX-ACCESS   read-only
    STATUS       current
    DESCRIPTION
        "Cisco Firepower equipment:BladeBiosCapProvider:vendor
        managed object property"
    ::= { cfprApEquipmentBladeBiosCapProviderEntry 16 }

cfprApEquipmentBladeCapProviderTable OBJECT-TYPE
    SYNTAX           SEQUENCE OF CfprApEquipmentBladeCapProviderEntry
    MAX-ACCESS       not-accessible
    STATUS           current
    DESCRIPTION
        "Cisco Firepower equipment:BladeCapProvider managed object table"
    ::= { cfprApEquipmentObjects 14 }

cfprApEquipmentBladeCapProviderEntry OBJECT-TYPE
    SYNTAX           CfprApEquipmentBladeCapProviderEntry
    MAX-ACCESS       not-accessible
    STATUS           current
    DESCRIPTION
        "Entry for the cfprApEquipmentBladeCapProviderTable table."
    INDEX { cfprApEquipmentBladeCapProviderInstanceId }
    ::= { cfprApEquipmentBladeCapProviderTable 1 }

CfprApEquipmentBladeCapProviderEntry ::= SEQUENCE {
    cfprApEquipmentBladeCapProviderInstanceId                        CfprApManagedObjectId,
    cfprApEquipmentBladeCapProviderDn                                CfprApManagedObjectDn,
    cfprApEquipmentBladeCapProviderRn                                SnmpAdminString,
    cfprApEquipmentBladeCapProviderDeleted                           TruthValue,
    cfprApEquipmentBladeCapProviderDeprecated                        TruthValue,
    cfprApEquipmentBladeCapProviderElementLoadFailures               Gauge32,
    cfprApEquipmentBladeCapProviderElementsLoaded                    Gauge32,
    cfprApEquipmentBladeCapProviderGencount                          Gauge32,
    cfprApEquipmentBladeCapProviderLoadErrors                        Gauge32,
    cfprApEquipmentBladeCapProviderLoadWarnings                      Gauge32,
    cfprApEquipmentBladeCapProviderMgmtPlaneVer                      SnmpAdminString,
    cfprApEquipmentBladeCapProviderModel                             SnmpAdminString,
    cfprApEquipmentBladeCapProviderPromCardType                      Gauge32,
    cfprApEquipmentBladeCapProviderRevision                          SnmpAdminString,
    cfprApEquipmentBladeCapProviderVendor                            SnmpAdminString
}

cfprApEquipmentBladeCapProviderInstanceId OBJECT-TYPE
    SYNTAX       CfprApManagedObjectId
    MAX-ACCESS   not-accessible
    STATUS       current
    DESCRIPTION
        "Instance identifier of the managed object."
    ::= { cfprApEquipmentBladeCapProviderEntry 1 }

cfprApEquipmentBladeCapProviderDn OBJECT-TYPE
    SYNTAX       CfprApManagedObjectDn
    MAX-ACCESS   read-only
    STATUS       current
    DESCRIPTION
        "Cisco Firepower equipment:BladeCapProvider:dn
        managed object property"
    ::= { cfprApEquipmentBladeCapProviderEntry 2 }

cfprApEquipmentBladeCapProviderRn OBJECT-TYPE
    SYNTAX       SnmpAdminString
    MAX-ACCESS   read-only
    STATUS       current
    DESCRIPTION
        "Cisco Firepower equipment:BladeCapProvider:rn
        managed object property"
    ::= { cfprApEquipmentBladeCapProviderEntry 3 }

cfprApEquipmentBladeCapProviderDeleted OBJECT-TYPE
    SYNTAX       TruthValue
    MAX-ACCESS   read-only
    STATUS       current
    DESCRIPTION
        "Cisco Firepower equipment:BladeCapProvider:deleted
        managed object property"
    ::= { cfprApEquipmentBladeCapProviderEntry 4 }

cfprApEquipmentBladeCapProviderDeprecated OBJECT-TYPE
    SYNTAX       TruthValue
    MAX-ACCESS   read-only
    STATUS       current
    DESCRIPTION
        "Cisco Firepower equipment:BladeCapProvider:deprecated
        managed object property"
    ::= { cfprApEquipmentBladeCapProviderEntry 5 }

cfprApEquipmentBladeCapProviderElementLoadFailures OBJECT-TYPE
    SYNTAX       Gauge32
    MAX-ACCESS   read-only
    STATUS       current
    DESCRIPTION
        "Cisco Firepower equipment:BladeCapProvider:elementLoadFailures
        managed object property"
    ::= { cfprApEquipmentBladeCapProviderEntry 6 }

cfprApEquipmentBladeCapProviderElementsLoaded OBJECT-TYPE
    SYNTAX       Gauge32
    MAX-ACCESS   read-only
    STATUS       current
    DESCRIPTION
        "Cisco Firepower equipment:BladeCapProvider:elementsLoaded
        managed object property"
    ::= { cfprApEquipmentBladeCapProviderEntry 7 }

cfprApEquipmentBladeCapProviderGencount OBJECT-TYPE
    SYNTAX       Gauge32
    MAX-ACCESS   read-only
    STATUS       current
    DESCRIPTION
        "Cisco Firepower equipment:BladeCapProvider:gencount
        managed object property"
    ::= { cfprApEquipmentBladeCapProviderEntry 8 }

cfprApEquipmentBladeCapProviderLoadErrors OBJECT-TYPE
    SYNTAX       Gauge32
    MAX-ACCESS   read-only
    STATUS       current
    DESCRIPTION
        "Cisco Firepower equipment:BladeCapProvider:loadErrors
        managed object property"
    ::= { cfprApEquipmentBladeCapProviderEntry 9 }

cfprApEquipmentBladeCapProviderLoadWarnings OBJECT-TYPE
    SYNTAX       Gauge32
    MAX-ACCESS   read-only
    STATUS       current
    DESCRIPTION
        "Cisco Firepower equipment:BladeCapProvider:loadWarnings
        managed object property"
    ::= { cfprApEquipmentBladeCapProviderEntry 10 }

cfprApEquipmentBladeCapProviderMgmtPlaneVer OBJECT-TYPE
    SYNTAX       SnmpAdminString
    MAX-ACCESS   read-only
    STATUS       current
    DESCRIPTION
        "Cisco Firepower equipment:BladeCapProvider:mgmtPlaneVer
        managed object property"
    ::= { cfprApEquipmentBladeCapProviderEntry 11 }

cfprApEquipmentBladeCapProviderModel OBJECT-TYPE
    SYNTAX       SnmpAdminString
    MAX-ACCESS   read-only
    STATUS       current
    DESCRIPTION
        "Cisco Firepower equipment:BladeCapProvider:model
        managed object property"
    ::= { cfprApEquipmentBladeCapProviderEntry 12 }

cfprApEquipmentBladeCapProviderPromCardType OBJECT-TYPE
    SYNTAX       Gauge32
    MAX-ACCESS   read-only
    STATUS       current
    DESCRIPTION
        "Cisco Firepower equipment:BladeCapProvider:promCardType
        managed object property"
    ::= { cfprApEquipmentBladeCapProviderEntry 13 }

cfprApEquipmentBladeCapProviderRevision OBJECT-TYPE
    SYNTAX       SnmpAdminString
    MAX-ACCESS   read-only
    STATUS       current
    DESCRIPTION
        "Cisco Firepower equipment:BladeCapProvider:revision
        managed object property"
    ::= { cfprApEquipmentBladeCapProviderEntry 14 }

cfprApEquipmentBladeCapProviderVendor OBJECT-TYPE
    SYNTAX       SnmpAdminString
    MAX-ACCESS   read-only
    STATUS       current
    DESCRIPTION
        "Cisco Firepower equipment:BladeCapProvider:vendor
        managed object property"
    ::= { cfprApEquipmentBladeCapProviderEntry 15 }

cfprApEquipmentBladeConnDefTable OBJECT-TYPE
    SYNTAX           SEQUENCE OF CfprApEquipmentBladeConnDefEntry
    MAX-ACCESS       not-accessible
    STATUS           current
    DESCRIPTION
        "Cisco Firepower equipment:BladeConnDef managed object table"
    ::= { cfprApEquipmentObjects 15 }

cfprApEquipmentBladeConnDefEntry OBJECT-TYPE
    SYNTAX           CfprApEquipmentBladeConnDefEntry
    MAX-ACCESS       not-accessible
    STATUS           current
    DESCRIPTION
        "Entry for the cfprApEquipmentBladeConnDefTable table."
    INDEX { cfprApEquipmentBladeConnDefInstanceId }
    ::= { cfprApEquipmentBladeConnDefTable 1 }

CfprApEquipmentBladeConnDefEntry ::= SEQUENCE {
    cfprApEquipmentBladeConnDefInstanceId                            CfprApManagedObjectId,
    cfprApEquipmentBladeConnDefDn                                    CfprApManagedObjectDn,
    cfprApEquipmentBladeConnDefRn                                    SnmpAdminString,
    cfprApEquipmentBladeConnDefAdaptorFamily                         SnmpAdminString,
    cfprApEquipmentBladeConnDefAdaptorSlotNumber                     Gauge32,
    cfprApEquipmentBladeConnDefAdaptorSlotSpan                       Gauge32,
    cfprApEquipmentBladeConnDefAdaptorType                           SnmpAdminString,
    cfprApEquipmentBladeConnDefDescr                                 SnmpAdminString,
    cfprApEquipmentBladeConnDefIntId                                 SnmpAdminString,
    cfprApEquipmentBladeConnDefName                                  SnmpAdminString,
    cfprApEquipmentBladeConnDefParentAdaptorSlotNum                  Gauge32,
    cfprApEquipmentBladeConnDefPolicyLevel                           Gauge32,
    cfprApEquipmentBladeConnDefPolicyOwner                           CfprApPolicyPolicyOwner,
    cfprApEquipmentBladeConnDefSwitchPortMuxOffset                   Gauge32
}

cfprApEquipmentBladeConnDefInstanceId OBJECT-TYPE
    SYNTAX       CfprApManagedObjectId
    MAX-ACCESS   not-accessible
    STATUS       current
    DESCRIPTION
        "Instance identifier of the managed object."
    ::= { cfprApEquipmentBladeConnDefEntry 1 }

cfprApEquipmentBladeConnDefDn OBJECT-TYPE
    SYNTAX       CfprApManagedObjectDn
    MAX-ACCESS   read-only
    STATUS       current
    DESCRIPTION
        "Cisco Firepower equipment:BladeConnDef:dn managed
        object property"
    ::= { cfprApEquipmentBladeConnDefEntry 2 }

cfprApEquipmentBladeConnDefRn OBJECT-TYPE
    SYNTAX       SnmpAdminString
    MAX-ACCESS   read-only
    STATUS       current
    DESCRIPTION
        "Cisco Firepower equipment:BladeConnDef:rn managed
        object property"
    ::= { cfprApEquipmentBladeConnDefEntry 3 }

cfprApEquipmentBladeConnDefAdaptorFamily OBJECT-TYPE
    SYNTAX       SnmpAdminString
    MAX-ACCESS   read-only
    STATUS       current
    DESCRIPTION
        "Cisco Firepower equipment:BladeConnDef:adaptorFamily
        managed object property"
    ::= { cfprApEquipmentBladeConnDefEntry 4 }

cfprApEquipmentBladeConnDefAdaptorSlotNumber OBJECT-TYPE
    SYNTAX       Gauge32
    MAX-ACCESS   read-only
    STATUS       current
    DESCRIPTION
        "Cisco Firepower equipment:BladeConnDef:adaptorSlotNumber
        managed object property"
    ::= { cfprApEquipmentBladeConnDefEntry 5 }

cfprApEquipmentBladeConnDefAdaptorSlotSpan OBJECT-TYPE
    SYNTAX       Gauge32
    MAX-ACCESS   read-only
    STATUS       current
    DESCRIPTION
        "Cisco Firepower equipment:BladeConnDef:adaptorSlotSpan
        managed object property"
    ::= { cfprApEquipmentBladeConnDefEntry 6 }

cfprApEquipmentBladeConnDefAdaptorType OBJECT-TYPE
    SYNTAX       SnmpAdminString
    MAX-ACCESS   read-only
    STATUS       current
    DESCRIPTION
        "Cisco Firepower equipment:BladeConnDef:adaptorType
        managed object property"
    ::= { cfprApEquipmentBladeConnDefEntry 7 }

cfprApEquipmentBladeConnDefDescr OBJECT-TYPE
    SYNTAX       SnmpAdminString
    MAX-ACCESS   read-only
    STATUS       current
    DESCRIPTION
        "Cisco Firepower equipment:BladeConnDef:descr managed
        object property"
    ::= { cfprApEquipmentBladeConnDefEntry 8 }

cfprApEquipmentBladeConnDefIntId OBJECT-TYPE
    SYNTAX       SnmpAdminString
    MAX-ACCESS   read-only
    STATUS       current
    DESCRIPTION
        "Cisco Firepower equipment:BladeConnDef:intId managed
        object property"
    ::= { cfprApEquipmentBladeConnDefEntry 9 }

cfprApEquipmentBladeConnDefName OBJECT-TYPE
    SYNTAX       SnmpAdminString
    MAX-ACCESS   read-only
    STATUS       current
    DESCRIPTION
        "Cisco Firepower equipment:BladeConnDef:name managed
        object property"
    ::= { cfprApEquipmentBladeConnDefEntry 10 }

cfprApEquipmentBladeConnDefParentAdaptorSlotNum OBJECT-TYPE
    SYNTAX       Gauge32
    MAX-ACCESS   read-only
    STATUS       current
    DESCRIPTION
        "Cisco Firepower equipment:BladeConnDef:parentAdaptorSlotNum
        managed object property"
    ::= { cfprApEquipmentBladeConnDefEntry 11 }

cfprApEquipmentBladeConnDefPolicyLevel OBJECT-TYPE
    SYNTAX       Gauge32
    MAX-ACCESS   read-only
    STATUS       current
    DESCRIPTION
        "Cisco Firepower equipment:BladeConnDef:policyLevel
        managed object property"
    ::= { cfprApEquipmentBladeConnDefEntry 12 }

cfprApEquipmentBladeConnDefPolicyOwner OBJECT-TYPE
    SYNTAX       CfprApPolicyPolicyOwner
    MAX-ACCESS   read-only
    STATUS       current
    DESCRIPTION
        "Cisco Firepower equipment:BladeConnDef:policyOwner
        managed object property"
    ::= { cfprApEquipmentBladeConnDefEntry 13 }

cfprApEquipmentBladeConnDefSwitchPortMuxOffset OBJECT-TYPE
    SYNTAX       Gauge32
    MAX-ACCESS   read-only
    STATUS       current
    DESCRIPTION
        "Cisco Firepower equipment:BladeConnDef:switchPortMuxOffset
        managed object property"
    ::= { cfprApEquipmentBladeConnDefEntry 14 }

cfprApEquipmentBladeIOMConnDefTable OBJECT-TYPE
    SYNTAX           SEQUENCE OF CfprApEquipmentBladeIOMConnDefEntry
    MAX-ACCESS       not-accessible
    STATUS           current
    DESCRIPTION
        "Cisco Firepower equipment:BladeIOMConnDef managed object table"
    ::= { cfprApEquipmentObjects 16 }

cfprApEquipmentBladeIOMConnDefEntry OBJECT-TYPE
    SYNTAX           CfprApEquipmentBladeIOMConnDefEntry
    MAX-ACCESS       not-accessible
    STATUS           current
    DESCRIPTION
        "Entry for the cfprApEquipmentBladeIOMConnDefTable table."
    INDEX { cfprApEquipmentBladeIOMConnDefInstanceId }
    ::= { cfprApEquipmentBladeIOMConnDefTable 1 }

CfprApEquipmentBladeIOMConnDefEntry ::= SEQUENCE {
    cfprApEquipmentBladeIOMConnDefInstanceId                         CfprApManagedObjectId,
    cfprApEquipmentBladeIOMConnDefDn                                 CfprApManagedObjectDn,
    cfprApEquipmentBladeIOMConnDefRn                                 SnmpAdminString,
    cfprApEquipmentBladeIOMConnDefDescr                              SnmpAdminString,
    cfprApEquipmentBladeIOMConnDefIntId                              SnmpAdminString,
    cfprApEquipmentBladeIOMConnDefIocardType                         SnmpAdminString,
    cfprApEquipmentBladeIOMConnDefName                               SnmpAdminString,
    cfprApEquipmentBladeIOMConnDefPolicyLevel                        Gauge32,
    cfprApEquipmentBladeIOMConnDefPolicyOwner                        CfprApPolicyPolicyOwner,
    cfprApEquipmentBladeIOMConnDefPortBandwidth                      CfprApPortEthSpeed
}

cfprApEquipmentBladeIOMConnDefInstanceId OBJECT-TYPE
    SYNTAX       CfprApManagedObjectId
    MAX-ACCESS   not-accessible
    STATUS       current
    DESCRIPTION
        "Instance identifier of the managed object."
    ::= { cfprApEquipmentBladeIOMConnDefEntry 1 }

cfprApEquipmentBladeIOMConnDefDn OBJECT-TYPE
    SYNTAX       CfprApManagedObjectDn
    MAX-ACCESS   read-only
    STATUS       current
    DESCRIPTION
        "Cisco Firepower equipment:BladeIOMConnDef:dn managed
        object property"
    ::= { cfprApEquipmentBladeIOMConnDefEntry 2 }

cfprApEquipmentBladeIOMConnDefRn OBJECT-TYPE
    SYNTAX       SnmpAdminString
    MAX-ACCESS   read-only
    STATUS       current
    DESCRIPTION
        "Cisco Firepower equipment:BladeIOMConnDef:rn managed
        object property"
    ::= { cfprApEquipmentBladeIOMConnDefEntry 3 }

cfprApEquipmentBladeIOMConnDefDescr OBJECT-TYPE
    SYNTAX       SnmpAdminString
    MAX-ACCESS   read-only
    STATUS       current
    DESCRIPTION
        "Cisco Firepower equipment:BladeIOMConnDef:descr
        managed object property"
    ::= { cfprApEquipmentBladeIOMConnDefEntry 4 }

cfprApEquipmentBladeIOMConnDefIntId OBJECT-TYPE
    SYNTAX       SnmpAdminString
    MAX-ACCESS   read-only
    STATUS       current
    DESCRIPTION
        "Cisco Firepower equipment:BladeIOMConnDef:intId
        managed object property"
    ::= { cfprApEquipmentBladeIOMConnDefEntry 5 }

cfprApEquipmentBladeIOMConnDefIocardType OBJECT-TYPE
    SYNTAX       SnmpAdminString
    MAX-ACCESS   read-only
    STATUS       current
    DESCRIPTION
        "Cisco Firepower equipment:BladeIOMConnDef:iocardType
        managed object property"
    ::= { cfprApEquipmentBladeIOMConnDefEntry 6 }

cfprApEquipmentBladeIOMConnDefName OBJECT-TYPE
    SYNTAX       SnmpAdminString
    MAX-ACCESS   read-only
    STATUS       current
    DESCRIPTION
        "Cisco Firepower equipment:BladeIOMConnDef:name
        managed object property"
    ::= { cfprApEquipmentBladeIOMConnDefEntry 7 }

cfprApEquipmentBladeIOMConnDefPolicyLevel OBJECT-TYPE
    SYNTAX       Gauge32
    MAX-ACCESS   read-only
    STATUS       current
    DESCRIPTION
        "Cisco Firepower equipment:BladeIOMConnDef:policyLevel
        managed object property"
    ::= { cfprApEquipmentBladeIOMConnDefEntry 8 }

cfprApEquipmentBladeIOMConnDefPolicyOwner OBJECT-TYPE
    SYNTAX       CfprApPolicyPolicyOwner
    MAX-ACCESS   read-only
    STATUS       current
    DESCRIPTION
        "Cisco Firepower equipment:BladeIOMConnDef:policyOwner
        managed object property"
    ::= { cfprApEquipmentBladeIOMConnDefEntry 9 }

cfprApEquipmentBladeIOMConnDefPortBandwidth OBJECT-TYPE
    SYNTAX       CfprApPortEthSpeed
    MAX-ACCESS   read-only
    STATUS       current
    DESCRIPTION
        "Cisco Firepower equipment:BladeIOMConnDef:portBandwidth
        managed object property"
    ::= { cfprApEquipmentBladeIOMConnDefEntry 10 }

cfprApEquipmentBladeSwitchConnDefTable OBJECT-TYPE
    SYNTAX           SEQUENCE OF CfprApEquipmentBladeSwitchConnDefEntry
    MAX-ACCESS       not-accessible
    STATUS           current
    DESCRIPTION
        "Cisco Firepower equipment:BladeSwitchConnDef managed
        object table"
    ::= { cfprApEquipmentObjects 17 }

cfprApEquipmentBladeSwitchConnDefEntry OBJECT-TYPE
    SYNTAX           CfprApEquipmentBladeSwitchConnDefEntry
    MAX-ACCESS       not-accessible
    STATUS           current
    DESCRIPTION
        "Entry for the cfprApEquipmentBladeSwitchConnDefTable table."
    INDEX { cfprApEquipmentBladeSwitchConnDefInstanceId }
    ::= { cfprApEquipmentBladeSwitchConnDefTable 1 }

CfprApEquipmentBladeSwitchConnDefEntry ::= SEQUENCE {
    cfprApEquipmentBladeSwitchConnDefInstanceId                      CfprApManagedObjectId,
    cfprApEquipmentBladeSwitchConnDefDn                              CfprApManagedObjectDn,
    cfprApEquipmentBladeSwitchConnDefRn                              SnmpAdminString,
    cfprApEquipmentBladeSwitchConnDefDescr                           SnmpAdminString,
    cfprApEquipmentBladeSwitchConnDefIntId                           SnmpAdminString,
    cfprApEquipmentBladeSwitchConnDefName                            SnmpAdminString,
    cfprApEquipmentBladeSwitchConnDefPolicyLevel                     Gauge32,
    cfprApEquipmentBladeSwitchConnDefPolicyOwner                     CfprApPolicyPolicyOwner,
    cfprApEquipmentBladeSwitchConnDefPortBandwidth                   CfprApPortEthSpeed,
    cfprApEquipmentBladeSwitchConnDefSwitchType                      SnmpAdminString
}

cfprApEquipmentBladeSwitchConnDefInstanceId OBJECT-TYPE
    SYNTAX       CfprApManagedObjectId
    MAX-ACCESS   not-accessible
    STATUS       current
    DESCRIPTION
        "Instance identifier of the managed object."
    ::= { cfprApEquipmentBladeSwitchConnDefEntry 1 }

cfprApEquipmentBladeSwitchConnDefDn OBJECT-TYPE
    SYNTAX       CfprApManagedObjectDn
    MAX-ACCESS   read-only
    STATUS       current
    DESCRIPTION
        "Cisco Firepower equipment:BladeSwitchConnDef:dn
        managed object property"
    ::= { cfprApEquipmentBladeSwitchConnDefEntry 2 }

cfprApEquipmentBladeSwitchConnDefRn OBJECT-TYPE
    SYNTAX       SnmpAdminString
    MAX-ACCESS   read-only
    STATUS       current
    DESCRIPTION
        "Cisco Firepower equipment:BladeSwitchConnDef:rn
        managed object property"
    ::= { cfprApEquipmentBladeSwitchConnDefEntry 3 }

cfprApEquipmentBladeSwitchConnDefDescr OBJECT-TYPE
    SYNTAX       SnmpAdminString
    MAX-ACCESS   read-only
    STATUS       current
    DESCRIPTION
        "Cisco Firepower equipment:BladeSwitchConnDef:descr
        managed object property"
    ::= { cfprApEquipmentBladeSwitchConnDefEntry 4 }

cfprApEquipmentBladeSwitchConnDefIntId OBJECT-TYPE
    SYNTAX       SnmpAdminString
    MAX-ACCESS   read-only
    STATUS       current
    DESCRIPTION
        "Cisco Firepower equipment:BladeSwitchConnDef:intId
        managed object property"
    ::= { cfprApEquipmentBladeSwitchConnDefEntry 5 }

cfprApEquipmentBladeSwitchConnDefName OBJECT-TYPE
    SYNTAX       SnmpAdminString
    MAX-ACCESS   read-only
    STATUS       current
    DESCRIPTION
        "Cisco Firepower equipment:BladeSwitchConnDef:name
        managed object property"
    ::= { cfprApEquipmentBladeSwitchConnDefEntry 6 }

cfprApEquipmentBladeSwitchConnDefPolicyLevel OBJECT-TYPE
    SYNTAX       Gauge32
    MAX-ACCESS   read-only
    STATUS       current
    DESCRIPTION
        "Cisco Firepower equipment:BladeSwitchConnDef:policyLevel
        managed object property"
    ::= { cfprApEquipmentBladeSwitchConnDefEntry 7 }

cfprApEquipmentBladeSwitchConnDefPolicyOwner OBJECT-TYPE
    SYNTAX       CfprApPolicyPolicyOwner
    MAX-ACCESS   read-only
    STATUS       current
    DESCRIPTION
        "Cisco Firepower equipment:BladeSwitchConnDef:policyOwner
        managed object property"
    ::= { cfprApEquipmentBladeSwitchConnDefEntry 8 }

cfprApEquipmentBladeSwitchConnDefPortBandwidth OBJECT-TYPE
    SYNTAX       CfprApPortEthSpeed
    MAX-ACCESS   read-only
    STATUS       current
    DESCRIPTION
        "Cisco Firepower equipment:BladeSwitchConnDef:portBandwidth
        managed object property"
    ::= { cfprApEquipmentBladeSwitchConnDefEntry 9 }

cfprApEquipmentBladeSwitchConnDefSwitchType OBJECT-TYPE
    SYNTAX       SnmpAdminString
    MAX-ACCESS   read-only
    STATUS       current
    DESCRIPTION
        "Cisco Firepower equipment:BladeSwitchConnDef:switchType
        managed object property"
    ::= { cfprApEquipmentBladeSwitchConnDefEntry 10 }

cfprApEquipmentBoardControllerDefTable OBJECT-TYPE
    SYNTAX           SEQUENCE OF CfprApEquipmentBoardControllerDefEntry
    MAX-ACCESS       not-accessible
    STATUS           current
    DESCRIPTION
        "Cisco Firepower equipment:BoardControllerDef managed
        object table"
    ::= { cfprApEquipmentObjects 18 }

cfprApEquipmentBoardControllerDefEntry OBJECT-TYPE
    SYNTAX           CfprApEquipmentBoardControllerDefEntry
    MAX-ACCESS       not-accessible
    STATUS           current
    DESCRIPTION
        "Entry for the cfprApEquipmentBoardControllerDefTable table."
    INDEX { cfprApEquipmentBoardControllerDefInstanceId }
    ::= { cfprApEquipmentBoardControllerDefTable 1 }

CfprApEquipmentBoardControllerDefEntry ::= SEQUENCE {
    cfprApEquipmentBoardControllerDefInstanceId                      CfprApManagedObjectId,
    cfprApEquipmentBoardControllerDefDn                              CfprApManagedObjectDn,
    cfprApEquipmentBoardControllerDefRn                              SnmpAdminString,
    cfprApEquipmentBoardControllerDefDescr                           SnmpAdminString,
    cfprApEquipmentBoardControllerDefIntId                           SnmpAdminString,
    cfprApEquipmentBoardControllerDefName                            SnmpAdminString,
    cfprApEquipmentBoardControllerDefPolicyLevel                     Gauge32,
    cfprApEquipmentBoardControllerDefPolicyOwner                     CfprApPolicyPolicyOwner
}

cfprApEquipmentBoardControllerDefInstanceId OBJECT-TYPE
    SYNTAX       CfprApManagedObjectId
    MAX-ACCESS   not-accessible
    STATUS       current
    DESCRIPTION
        "Instance identifier of the managed object."
    ::= { cfprApEquipmentBoardControllerDefEntry 1 }

cfprApEquipmentBoardControllerDefDn OBJECT-TYPE
    SYNTAX       CfprApManagedObjectDn
    MAX-ACCESS   read-only
    STATUS       current
    DESCRIPTION
        "Cisco Firepower equipment:BoardControllerDef:dn
        managed object property"
    ::= { cfprApEquipmentBoardControllerDefEntry 2 }

cfprApEquipmentBoardControllerDefRn OBJECT-TYPE
    SYNTAX       SnmpAdminString
    MAX-ACCESS   read-only
    STATUS       current
    DESCRIPTION
        "Cisco Firepower equipment:BoardControllerDef:rn
        managed object property"
    ::= { cfprApEquipmentBoardControllerDefEntry 3 }

cfprApEquipmentBoardControllerDefDescr OBJECT-TYPE
    SYNTAX       SnmpAdminString
    MAX-ACCESS   read-only
    STATUS       current
    DESCRIPTION
        "Cisco Firepower equipment:BoardControllerDef:descr
        managed object property"
    ::= { cfprApEquipmentBoardControllerDefEntry 4 }

cfprApEquipmentBoardControllerDefIntId OBJECT-TYPE
    SYNTAX       SnmpAdminString
    MAX-ACCESS   read-only
    STATUS       current
    DESCRIPTION
        "Cisco Firepower equipment:BoardControllerDef:intId
        managed object property"
    ::= { cfprApEquipmentBoardControllerDefEntry 5 }

cfprApEquipmentBoardControllerDefName OBJECT-TYPE
    SYNTAX       SnmpAdminString
    MAX-ACCESS   read-only
    STATUS       current
    DESCRIPTION
        "Cisco Firepower equipment:BoardControllerDef:name
        managed object property"
    ::= { cfprApEquipmentBoardControllerDefEntry 6 }

cfprApEquipmentBoardControllerDefPolicyLevel OBJECT-TYPE
    SYNTAX       Gauge32
    MAX-ACCESS   read-only
    STATUS       current
    DESCRIPTION
        "Cisco Firepower equipment:BoardControllerDef:policyLevel
        managed object property"
    ::= { cfprApEquipmentBoardControllerDefEntry 7 }

cfprApEquipmentBoardControllerDefPolicyOwner OBJECT-TYPE
    SYNTAX       CfprApPolicyPolicyOwner
    MAX-ACCESS   read-only
    STATUS       current
    DESCRIPTION
        "Cisco Firepower equipment:BoardControllerDef:policyOwner
        managed object property"
    ::= { cfprApEquipmentBoardControllerDefEntry 8 }

cfprApEquipmentBreakOutCapProviderTable OBJECT-TYPE
    SYNTAX           SEQUENCE OF CfprApEquipmentBreakOutCapProviderEntry
    MAX-ACCESS       not-accessible
    STATUS           current
    DESCRIPTION
        "Cisco Firepower equipment:BreakOutCapProvider
        managed object table"
    ::= { cfprApEquipmentObjects 19 }

cfprApEquipmentBreakOutCapProviderEntry OBJECT-TYPE
    SYNTAX           CfprApEquipmentBreakOutCapProviderEntry
    MAX-ACCESS       not-accessible
    STATUS           current
    DESCRIPTION
        "Entry for the cfprApEquipmentBreakOutCapProviderTable table."
    INDEX { cfprApEquipmentBreakOutCapProviderInstanceId }
    ::= { cfprApEquipmentBreakOutCapProviderTable 1 }

CfprApEquipmentBreakOutCapProviderEntry ::= SEQUENCE {
    cfprApEquipmentBreakOutCapProviderInstanceId                     CfprApManagedObjectId,
    cfprApEquipmentBreakOutCapProviderDn                             CfprApManagedObjectDn,
    cfprApEquipmentBreakOutCapProviderRn                             SnmpAdminString,
    cfprApEquipmentBreakOutCapProviderBreakoutSupported              TruthValue,
    cfprApEquipmentBreakOutCapProviderDescr                          SnmpAdminString,
    cfprApEquipmentBreakOutCapProviderIntId                          SnmpAdminString,
    cfprApEquipmentBreakOutCapProviderName                           SnmpAdminString,
    cfprApEquipmentBreakOutCapProviderPolicyLevel                    Gauge32,
    cfprApEquipmentBreakOutCapProviderPolicyOwner                    CfprApPolicyPolicyOwner,
    cfprApEquipmentBreakOutCapProviderPortSpeedCap                   CfprApEquipmentEthPortSpeedCap
}

cfprApEquipmentBreakOutCapProviderInstanceId OBJECT-TYPE
    SYNTAX       CfprApManagedObjectId
    MAX-ACCESS   not-accessible
    STATUS       current
    DESCRIPTION
        "Instance identifier of the managed object."
    ::= { cfprApEquipmentBreakOutCapProviderEntry 1 }

cfprApEquipmentBreakOutCapProviderDn OBJECT-TYPE
    SYNTAX       CfprApManagedObjectDn
    MAX-ACCESS   read-only
    STATUS       current
    DESCRIPTION
        "Cisco Firepower equipment:BreakOutCapProvider:dn
        managed object property"
    ::= { cfprApEquipmentBreakOutCapProviderEntry 2 }

cfprApEquipmentBreakOutCapProviderRn OBJECT-TYPE
    SYNTAX       SnmpAdminString
    MAX-ACCESS   read-only
    STATUS       current
    DESCRIPTION
        "Cisco Firepower equipment:BreakOutCapProvider:rn
        managed object property"
    ::= { cfprApEquipmentBreakOutCapProviderEntry 3 }

cfprApEquipmentBreakOutCapProviderBreakoutSupported OBJECT-TYPE
    SYNTAX       TruthValue
    MAX-ACCESS   read-only
    STATUS       current
    DESCRIPTION
        "Cisco Firepower equipment:BreakOutCapProvider:breakoutSupported
        managed object property"
    ::= { cfprApEquipmentBreakOutCapProviderEntry 4 }

cfprApEquipmentBreakOutCapProviderDescr OBJECT-TYPE
    SYNTAX       SnmpAdminString
    MAX-ACCESS   read-only
    STATUS       current
    DESCRIPTION
        "Cisco Firepower equipment:BreakOutCapProvider:descr
        managed object property"
    ::= { cfprApEquipmentBreakOutCapProviderEntry 5 }

cfprApEquipmentBreakOutCapProviderIntId OBJECT-TYPE
    SYNTAX       SnmpAdminString
    MAX-ACCESS   read-only
    STATUS       current
    DESCRIPTION
        "Cisco Firepower equipment:BreakOutCapProvider:intId
        managed object property"
    ::= { cfprApEquipmentBreakOutCapProviderEntry 6 }

cfprApEquipmentBreakOutCapProviderName OBJECT-TYPE
    SYNTAX       SnmpAdminString
    MAX-ACCESS   read-only
    STATUS       current
    DESCRIPTION
        "Cisco Firepower equipment:BreakOutCapProvider:name
        managed object property"
    ::= { cfprApEquipmentBreakOutCapProviderEntry 7 }

cfprApEquipmentBreakOutCapProviderPolicyLevel OBJECT-TYPE
    SYNTAX       Gauge32
    MAX-ACCESS   read-only
    STATUS       current
    DESCRIPTION
        "Cisco Firepower equipment:BreakOutCapProvider:policyLevel
        managed object property"
    ::= { cfprApEquipmentBreakOutCapProviderEntry 8 }

cfprApEquipmentBreakOutCapProviderPolicyOwner OBJECT-TYPE
    SYNTAX       CfprApPolicyPolicyOwner
    MAX-ACCESS   read-only
    STATUS       current
    DESCRIPTION
        "Cisco Firepower equipment:BreakOutCapProvider:policyOwner
        managed object property"
    ::= { cfprApEquipmentBreakOutCapProviderEntry 9 }

cfprApEquipmentBreakOutCapProviderPortSpeedCap OBJECT-TYPE
    SYNTAX       CfprApEquipmentEthPortSpeedCap
    MAX-ACCESS   read-only
    STATUS       current
    DESCRIPTION
        "Cisco Firepower equipment:BreakOutCapProvider:portSpeedCap
        managed object property"
    ::= { cfprApEquipmentBreakOutCapProviderEntry 10 }

cfprApEquipmentCardStatsTable OBJECT-TYPE
    SYNTAX           SEQUENCE OF CfprApEquipmentCardStatsEntry
    MAX-ACCESS       not-accessible
    STATUS           current
    DESCRIPTION
        "Cisco Firepower equipment:CardStats managed object table"
    ::= { cfprApEquipmentObjects 20 }

cfprApEquipmentCardStatsEntry OBJECT-TYPE
    SYNTAX           CfprApEquipmentCardStatsEntry
    MAX-ACCESS       not-accessible
    STATUS           current
    DESCRIPTION
        "Entry for the cfprApEquipmentCardStatsTable table."
    INDEX { cfprApEquipmentCardStatsInstanceId }
    ::= { cfprApEquipmentCardStatsTable 1 }

CfprApEquipmentCardStatsEntry ::= SEQUENCE {
    cfprApEquipmentCardStatsInstanceId                               CfprApManagedObjectId,
    cfprApEquipmentCardStatsDn                                       CfprApManagedObjectDn,
    cfprApEquipmentCardStatsRn                                       SnmpAdminString,
    cfprApEquipmentCardStatsIntervals                                Gauge32,
    cfprApEquipmentCardStatsSuspect                                  TruthValue,
    cfprApEquipmentCardStatsTemp                                     INTEGER,
    cfprApEquipmentCardStatsTempAvg                                  INTEGER,
    cfprApEquipmentCardStatsTempMax                                  INTEGER,
    cfprApEquipmentCardStatsTempMin                                  INTEGER,
    cfprApEquipmentCardStatsThresholded                              CfprApEquipmentCardStatsThresholded,
    cfprApEquipmentCardStatsTimeCollected                            DateAndTime,
    cfprApEquipmentCardStatsUpdate                                   Gauge32
}

cfprApEquipmentCardStatsInstanceId OBJECT-TYPE
    SYNTAX       CfprApManagedObjectId
    MAX-ACCESS   not-accessible
    STATUS       current
    DESCRIPTION
        "Instance identifier of the managed object."
    ::= { cfprApEquipmentCardStatsEntry 1 }

cfprApEquipmentCardStatsDn OBJECT-TYPE
    SYNTAX       CfprApManagedObjectDn
    MAX-ACCESS   read-only
    STATUS       current
    DESCRIPTION
        "Cisco Firepower equipment:CardStats:dn managed object property"
    ::= { cfprApEquipmentCardStatsEntry 2 }

cfprApEquipmentCardStatsRn OBJECT-TYPE
    SYNTAX       SnmpAdminString
    MAX-ACCESS   read-only
    STATUS       current
    DESCRIPTION
        "Cisco Firepower equipment:CardStats:rn managed object property"
    ::= { cfprApEquipmentCardStatsEntry 3 }

cfprApEquipmentCardStatsIntervals OBJECT-TYPE
    SYNTAX       Gauge32
    MAX-ACCESS   read-only
    STATUS       current
    DESCRIPTION
        "Cisco Firepower equipment:CardStats:intervals
        managed object property"
    ::= { cfprApEquipmentCardStatsEntry 4 }

cfprApEquipmentCardStatsSuspect OBJECT-TYPE
    SYNTAX       TruthValue
    MAX-ACCESS   read-only
    STATUS       current
    DESCRIPTION
        "Cisco Firepower equipment:CardStats:suspect managed
        object property"
    ::= { cfprApEquipmentCardStatsEntry 5 }

cfprApEquipmentCardStatsTemp OBJECT-TYPE
    SYNTAX       INTEGER
    MAX-ACCESS   read-only
    STATUS       current
    DESCRIPTION
        "Cisco Firepower equipment:CardStats:temp managed object property"
    ::= { cfprApEquipmentCardStatsEntry 6 }

cfprApEquipmentCardStatsTempAvg OBJECT-TYPE
    SYNTAX       INTEGER
    MAX-ACCESS   read-only
    STATUS       current
    DESCRIPTION
        "Cisco Firepower equipment:CardStats:tempAvg managed
        object property"
    ::= { cfprApEquipmentCardStatsEntry 7 }

cfprApEquipmentCardStatsTempMax OBJECT-TYPE
    SYNTAX       INTEGER
    MAX-ACCESS   read-only
    STATUS       current
    DESCRIPTION
        "Cisco Firepower equipment:CardStats:tempMax managed
        object property"
    ::= { cfprApEquipmentCardStatsEntry 8 }

cfprApEquipmentCardStatsTempMin OBJECT-TYPE
    SYNTAX       INTEGER
    MAX-ACCESS   read-only
    STATUS       current
    DESCRIPTION
        "Cisco Firepower equipment:CardStats:tempMin managed
        object property"
    ::= { cfprApEquipmentCardStatsEntry 9 }

cfprApEquipmentCardStatsThresholded OBJECT-TYPE
    SYNTAX       CfprApEquipmentCardStatsThresholded
    MAX-ACCESS   read-only
    STATUS       current
    DESCRIPTION
        "Cisco Firepower equipment:CardStats:thresholded
        managed object property"
    ::= { cfprApEquipmentCardStatsEntry 10 }

cfprApEquipmentCardStatsTimeCollected OBJECT-TYPE
    SYNTAX       DateAndTime
    MAX-ACCESS   read-only
    STATUS       current
    DESCRIPTION
        "Cisco Firepower equipment:CardStats:timeCollected
        managed object property"
    ::= { cfprApEquipmentCardStatsEntry 11 }

cfprApEquipmentCardStatsUpdate OBJECT-TYPE
    SYNTAX       Gauge32
    MAX-ACCESS   read-only
    STATUS       current
    DESCRIPTION
        "Cisco Firepower equipment:CardStats:update managed
        object property"
    ::= { cfprApEquipmentCardStatsEntry 12 }

cfprApEquipmentCardStatsHistTable OBJECT-TYPE
    SYNTAX           SEQUENCE OF CfprApEquipmentCardStatsHistEntry
    MAX-ACCESS       not-accessible
    STATUS           current
    DESCRIPTION
        "Cisco Firepower equipment:CardStatsHist managed object table"
    ::= { cfprApEquipmentObjects 21 }

cfprApEquipmentCardStatsHistEntry OBJECT-TYPE
    SYNTAX           CfprApEquipmentCardStatsHistEntry
    MAX-ACCESS       not-accessible
    STATUS           current
    DESCRIPTION
        "Entry for the cfprApEquipmentCardStatsHistTable table."
    INDEX { cfprApEquipmentCardStatsHistInstanceId }
    ::= { cfprApEquipmentCardStatsHistTable 1 }

CfprApEquipmentCardStatsHistEntry ::= SEQUENCE {
    cfprApEquipmentCardStatsHistInstanceId                           CfprApManagedObjectId,
    cfprApEquipmentCardStatsHistDn                                   CfprApManagedObjectDn,
    cfprApEquipmentCardStatsHistRn                                   SnmpAdminString,
    cfprApEquipmentCardStatsHistId                                   Unsigned64,
    cfprApEquipmentCardStatsHistMostRecent                           TruthValue,
    cfprApEquipmentCardStatsHistSuspect                              TruthValue,
    cfprApEquipmentCardStatsHistTemp                                 INTEGER,
    cfprApEquipmentCardStatsHistTempAvg                              INTEGER,
    cfprApEquipmentCardStatsHistTempMax                              INTEGER,
    cfprApEquipmentCardStatsHistTempMin                              INTEGER,
    cfprApEquipmentCardStatsHistThresholded                          CfprApEquipmentCardStatsHistThresholded,
    cfprApEquipmentCardStatsHistTimeCollected                        DateAndTime
}

cfprApEquipmentCardStatsHistInstanceId OBJECT-TYPE
    SYNTAX       CfprApManagedObjectId
    MAX-ACCESS   not-accessible
    STATUS       current
    DESCRIPTION
        "Instance identifier of the managed object."
    ::= { cfprApEquipmentCardStatsHistEntry 1 }

cfprApEquipmentCardStatsHistDn OBJECT-TYPE
    SYNTAX       CfprApManagedObjectDn
    MAX-ACCESS   read-only
    STATUS       current
    DESCRIPTION
        "Cisco Firepower equipment:CardStatsHist:dn managed
        object property"
    ::= { cfprApEquipmentCardStatsHistEntry 2 }

cfprApEquipmentCardStatsHistRn OBJECT-TYPE
    SYNTAX       SnmpAdminString
    MAX-ACCESS   read-only
    STATUS       current
    DESCRIPTION
        "Cisco Firepower equipment:CardStatsHist:rn managed
        object property"
    ::= { cfprApEquipmentCardStatsHistEntry 3 }

cfprApEquipmentCardStatsHistId OBJECT-TYPE
    SYNTAX       Unsigned64
    MAX-ACCESS   read-only
    STATUS       current
    DESCRIPTION
        "Cisco Firepower equipment:CardStatsHist:id managed
        object property"
    ::= { cfprApEquipmentCardStatsHistEntry 4 }

cfprApEquipmentCardStatsHistMostRecent OBJECT-TYPE
    SYNTAX       TruthValue
    MAX-ACCESS   read-only
    STATUS       current
    DESCRIPTION
        "Cisco Firepower equipment:CardStatsHist:mostRecent
        managed object property"
    ::= { cfprApEquipmentCardStatsHistEntry 5 }

cfprApEquipmentCardStatsHistSuspect OBJECT-TYPE
    SYNTAX       TruthValue
    MAX-ACCESS   read-only
    STATUS       current
    DESCRIPTION
        "Cisco Firepower equipment:CardStatsHist:suspect
        managed object property"
    ::= { cfprApEquipmentCardStatsHistEntry 6 }

cfprApEquipmentCardStatsHistTemp OBJECT-TYPE
    SYNTAX       INTEGER
    MAX-ACCESS   read-only
    STATUS       current
    DESCRIPTION
        "Cisco Firepower equipment:CardStatsHist:temp managed
        object property"
    ::= { cfprApEquipmentCardStatsHistEntry 7 }

cfprApEquipmentCardStatsHistTempAvg OBJECT-TYPE
    SYNTAX       INTEGER
    MAX-ACCESS   read-only
    STATUS       current
    DESCRIPTION
        "Cisco Firepower equipment:CardStatsHist:tempAvg
        managed object property"
    ::= { cfprApEquipmentCardStatsHistEntry 8 }

cfprApEquipmentCardStatsHistTempMax OBJECT-TYPE
    SYNTAX       INTEGER
    MAX-ACCESS   read-only
    STATUS       current
    DESCRIPTION
        "Cisco Firepower equipment:CardStatsHist:tempMax
        managed object property"
    ::= { cfprApEquipmentCardStatsHistEntry 9 }

cfprApEquipmentCardStatsHistTempMin OBJECT-TYPE
    SYNTAX       INTEGER
    MAX-ACCESS   read-only
    STATUS       current
    DESCRIPTION
        "Cisco Firepower equipment:CardStatsHist:tempMin
        managed object property"
    ::= { cfprApEquipmentCardStatsHistEntry 10 }

cfprApEquipmentCardStatsHistThresholded OBJECT-TYPE
    SYNTAX       CfprApEquipmentCardStatsHistThresholded
    MAX-ACCESS   read-only
    STATUS       current
    DESCRIPTION
        "Cisco Firepower equipment:CardStatsHist:thresholded
        managed object property"
    ::= { cfprApEquipmentCardStatsHistEntry 11 }

cfprApEquipmentCardStatsHistTimeCollected OBJECT-TYPE
    SYNTAX       DateAndTime
    MAX-ACCESS   read-only
    STATUS       current
    DESCRIPTION
        "Cisco Firepower equipment:CardStatsHist:timeCollected
        managed object property"
    ::= { cfprApEquipmentCardStatsHistEntry 12 }

cfprApEquipmentCatalogCapProviderTable OBJECT-TYPE
    SYNTAX           SEQUENCE OF CfprApEquipmentCatalogCapProviderEntry
    MAX-ACCESS       not-accessible
    STATUS           current
    DESCRIPTION
        "Cisco Firepower equipment:CatalogCapProvider managed
        object table"
    ::= { cfprApEquipmentObjects 22 }

cfprApEquipmentCatalogCapProviderEntry OBJECT-TYPE
    SYNTAX           CfprApEquipmentCatalogCapProviderEntry
    MAX-ACCESS       not-accessible
    STATUS           current
    DESCRIPTION
        "Entry for the cfprApEquipmentCatalogCapProviderTable table."
    INDEX { cfprApEquipmentCatalogCapProviderInstanceId }
    ::= { cfprApEquipmentCatalogCapProviderTable 1 }

CfprApEquipmentCatalogCapProviderEntry ::= SEQUENCE {
    cfprApEquipmentCatalogCapProviderInstanceId                      CfprApManagedObjectId,
    cfprApEquipmentCatalogCapProviderDn                              CfprApManagedObjectDn,
    cfprApEquipmentCatalogCapProviderRn                              SnmpAdminString,
    cfprApEquipmentCatalogCapProviderDeleted                         TruthValue,
    cfprApEquipmentCatalogCapProviderDeprecated                      TruthValue,
    cfprApEquipmentCatalogCapProviderElementLoadFailures             Gauge32,
    cfprApEquipmentCatalogCapProviderElementsLoaded                  Gauge32,
    cfprApEquipmentCatalogCapProviderGencount                        Gauge32,
    cfprApEquipmentCatalogCapProviderLoadErrors                      Gauge32,
    cfprApEquipmentCatalogCapProviderLoadWarnings                    Gauge32,
    cfprApEquipmentCatalogCapProviderMgmtPlaneVer                    SnmpAdminString,
    cfprApEquipmentCatalogCapProviderModel                           SnmpAdminString,
    cfprApEquipmentCatalogCapProviderPromCardType                    Gauge32,
    cfprApEquipmentCatalogCapProviderRevision                        SnmpAdminString,
    cfprApEquipmentCatalogCapProviderVendor                          SnmpAdminString
}

cfprApEquipmentCatalogCapProviderInstanceId OBJECT-TYPE
    SYNTAX       CfprApManagedObjectId
    MAX-ACCESS   not-accessible
    STATUS       current
    DESCRIPTION
        "Instance identifier of the managed object."
    ::= { cfprApEquipmentCatalogCapProviderEntry 1 }

cfprApEquipmentCatalogCapProviderDn OBJECT-TYPE
    SYNTAX       CfprApManagedObjectDn
    MAX-ACCESS   read-only
    STATUS       current
    DESCRIPTION
        "Cisco Firepower equipment:CatalogCapProvider:dn
        managed object property"
    ::= { cfprApEquipmentCatalogCapProviderEntry 2 }

cfprApEquipmentCatalogCapProviderRn OBJECT-TYPE
    SYNTAX       SnmpAdminString
    MAX-ACCESS   read-only
    STATUS       current
    DESCRIPTION
        "Cisco Firepower equipment:CatalogCapProvider:rn
        managed object property"
    ::= { cfprApEquipmentCatalogCapProviderEntry 3 }

cfprApEquipmentCatalogCapProviderDeleted OBJECT-TYPE
    SYNTAX       TruthValue
    MAX-ACCESS   read-only
    STATUS       current
    DESCRIPTION
        "Cisco Firepower equipment:CatalogCapProvider:deleted
        managed object property"
    ::= { cfprApEquipmentCatalogCapProviderEntry 4 }

cfprApEquipmentCatalogCapProviderDeprecated OBJECT-TYPE
    SYNTAX       TruthValue
    MAX-ACCESS   read-only
    STATUS       current
    DESCRIPTION
        "Cisco Firepower equipment:CatalogCapProvider:deprecated
        managed object property"
    ::= { cfprApEquipmentCatalogCapProviderEntry 5 }

cfprApEquipmentCatalogCapProviderElementLoadFailures OBJECT-TYPE
    SYNTAX       Gauge32
    MAX-ACCESS   read-only
    STATUS       current
    DESCRIPTION
        "Cisco Firepower equipment:CatalogCapProvider:elementLoadFailures
        managed object property"
    ::= { cfprApEquipmentCatalogCapProviderEntry 6 }

cfprApEquipmentCatalogCapProviderElementsLoaded OBJECT-TYPE
    SYNTAX       Gauge32
    MAX-ACCESS   read-only
    STATUS       current
    DESCRIPTION
        "Cisco Firepower equipment:CatalogCapProvider:elementsLoaded
        managed object property"
    ::= { cfprApEquipmentCatalogCapProviderEntry 7 }

cfprApEquipmentCatalogCapProviderGencount OBJECT-TYPE
    SYNTAX       Gauge32
    MAX-ACCESS   read-only
    STATUS       current
    DESCRIPTION
        "Cisco Firepower equipment:CatalogCapProvider:gencount
        managed object property"
    ::= { cfprApEquipmentCatalogCapProviderEntry 8 }

cfprApEquipmentCatalogCapProviderLoadErrors OBJECT-TYPE
    SYNTAX       Gauge32
    MAX-ACCESS   read-only
    STATUS       current
    DESCRIPTION
        "Cisco Firepower equipment:CatalogCapProvider:loadErrors
        managed object property"
    ::= { cfprApEquipmentCatalogCapProviderEntry 9 }

cfprApEquipmentCatalogCapProviderLoadWarnings OBJECT-TYPE
    SYNTAX       Gauge32
    MAX-ACCESS   read-only
    STATUS       current
    DESCRIPTION
        "Cisco Firepower equipment:CatalogCapProvider:loadWarnings
        managed object property"
    ::= { cfprApEquipmentCatalogCapProviderEntry 10 }

cfprApEquipmentCatalogCapProviderMgmtPlaneVer OBJECT-TYPE
    SYNTAX       SnmpAdminString
    MAX-ACCESS   read-only
    STATUS       current
    DESCRIPTION
        "Cisco Firepower equipment:CatalogCapProvider:mgmtPlaneVer
        managed object property"
    ::= { cfprApEquipmentCatalogCapProviderEntry 11 }

cfprApEquipmentCatalogCapProviderModel OBJECT-TYPE
    SYNTAX       SnmpAdminString
    MAX-ACCESS   read-only
    STATUS       current
    DESCRIPTION
        "Cisco Firepower equipment:CatalogCapProvider:model
        managed object property"
    ::= { cfprApEquipmentCatalogCapProviderEntry 12 }

cfprApEquipmentCatalogCapProviderPromCardType OBJECT-TYPE
    SYNTAX       Gauge32
    MAX-ACCESS   read-only
    STATUS       current
    DESCRIPTION
        "Cisco Firepower equipment:CatalogCapProvider:promCardType
        managed object property"
    ::= { cfprApEquipmentCatalogCapProviderEntry 13 }

cfprApEquipmentCatalogCapProviderRevision OBJECT-TYPE
    SYNTAX       SnmpAdminString
    MAX-ACCESS   read-only
    STATUS       current
    DESCRIPTION
        "Cisco Firepower equipment:CatalogCapProvider:revision
        managed object property"
    ::= { cfprApEquipmentCatalogCapProviderEntry 14 }

cfprApEquipmentCatalogCapProviderVendor OBJECT-TYPE
    SYNTAX       SnmpAdminString
    MAX-ACCESS   read-only
    STATUS       current
    DESCRIPTION
        "Cisco Firepower equipment:CatalogCapProvider:vendor
        managed object property"
    ::= { cfprApEquipmentCatalogCapProviderEntry 15 }

cfprApEquipmentChassisTable OBJECT-TYPE
    SYNTAX           SEQUENCE OF CfprApEquipmentChassisEntry
    MAX-ACCESS       not-accessible
    STATUS           current
    DESCRIPTION
        "Cisco Firepower equipment:Chassis managed object table"
    ::= { cfprApEquipmentObjects 23 }

cfprApEquipmentChassisEntry OBJECT-TYPE
    SYNTAX           CfprApEquipmentChassisEntry
    MAX-ACCESS       not-accessible
    STATUS           current
    DESCRIPTION
        "Entry for the cfprApEquipmentChassisTable table."
    INDEX { cfprApEquipmentChassisInstanceId }
    ::= { cfprApEquipmentChassisTable 1 }

CfprApEquipmentChassisEntry ::= SEQUENCE {
    cfprApEquipmentChassisInstanceId                                 CfprApManagedObjectId,
    cfprApEquipmentChassisDn                                         CfprApManagedObjectDn,
    cfprApEquipmentChassisRn                                         SnmpAdminString,
    cfprApEquipmentChassisAckProgressIndicator                       CfprApEquipmentChassisConfigProgressIndicator,
    cfprApEquipmentChassisAdminState                                 CfprApEquipmentChassisAdminState,
    cfprApEquipmentChassisConfigState                                CfprApEquipmentChassisConfigState,
    cfprApEquipmentChassisConnPath                                   CfprApEquipmentConnectionStatus,
    cfprApEquipmentChassisConnStatus                                 CfprApEquipmentConnectionStatus,
    cfprApEquipmentChassisFabricEpDn                                 SnmpAdminString,
    cfprApEquipmentChassisFltAggr                                    Unsigned64,
    cfprApEquipmentChassisFsmDescr                                   SnmpAdminString,
    cfprApEquipmentChassisFsmPrev                                    SnmpAdminString,
    cfprApEquipmentChassisFsmProgr                                   Gauge32,
    cfprApEquipmentChassisFsmRmtInvErrCode                           Gauge32,
    cfprApEquipmentChassisFsmRmtInvErrDescr                          SnmpAdminString,
    cfprApEquipmentChassisFsmRmtInvRslt                              CfprApConditionRemoteInvRslt,
    cfprApEquipmentChassisFsmStageDescr                              SnmpAdminString,
    cfprApEquipmentChassisFsmStamp                                   DateAndTime,
    cfprApEquipmentChassisFsmStatus                                  SnmpAdminString,
    cfprApEquipmentChassisFsmTry                                     Gauge32,
    cfprApEquipmentChassisId                                         CfprApEquipmentChassisId,
    cfprApEquipmentChassisLcTs                                       DateAndTime,
    cfprApEquipmentChassisLicGP                                      Unsigned64,
    cfprApEquipmentChassisLicState                                   CfprApLicenseState,
    cfprApEquipmentChassisManagingInst                               CfprApNetworkSwitchId,
    cfprApEquipmentChassisMfgTime                                    DateAndTime,
    cfprApEquipmentChassisModel                                      SnmpAdminString,
    cfprApEquipmentChassisOperQualifier                              CfprApEquipmentChassisIssues,
    cfprApEquipmentChassisOperQualifierReason                        SnmpAdminString,
    cfprApEquipmentChassisOperState                                  CfprApEquipmentOperability,
    cfprApEquipmentChassisOperability                                CfprApEquipmentOperability,
    cfprApEquipmentChassisPartNumber                                 SnmpAdminString,
    cfprApEquipmentChassisPower                                      CfprApEquipmentChassisPowerOperState,
    cfprApEquipmentChassisPresence                                   CfprApEquipmentPresence,
    cfprApEquipmentChassisRevision                                   SnmpAdminString,
    cfprApEquipmentChassisSerial                                     SnmpAdminString,
    cfprApEquipmentChassisThermal                                    CfprApEquipmentSensorThresholdStatus,
    cfprApEquipmentChassisThermalStateQualifier                      SnmpAdminString,
    cfprApEquipmentChassisUsrLbl                                     SnmpAdminString,
    cfprApEquipmentChassisVendor                                     SnmpAdminString,
    cfprApEquipmentChassisVersionHolder                              TruthValue,
    cfprApEquipmentChassisVid                                        SnmpAdminString
}

cfprApEquipmentChassisInstanceId OBJECT-TYPE
    SYNTAX       CfprApManagedObjectId
    MAX-ACCESS   not-accessible
    STATUS       current
    DESCRIPTION
        "Instance identifier of the managed object."
    ::= { cfprApEquipmentChassisEntry 1 }

cfprApEquipmentChassisDn OBJECT-TYPE
    SYNTAX       CfprApManagedObjectDn
    MAX-ACCESS   read-only
    STATUS       current
    DESCRIPTION
        "Cisco Firepower equipment:Chassis:dn managed object property"
    ::= { cfprApEquipmentChassisEntry 2 }

cfprApEquipmentChassisRn OBJECT-TYPE
    SYNTAX       SnmpAdminString
    MAX-ACCESS   read-only
    STATUS       current
    DESCRIPTION
        "Cisco Firepower equipment:Chassis:rn managed object property"
    ::= { cfprApEquipmentChassisEntry 3 }

cfprApEquipmentChassisAckProgressIndicator OBJECT-TYPE
    SYNTAX       CfprApEquipmentChassisConfigProgressIndicator
    MAX-ACCESS   read-only
    STATUS       current
    DESCRIPTION
        "Cisco Firepower equipment:Chassis:ackProgressIndicator
        managed object property"
    ::= { cfprApEquipmentChassisEntry 4 }

cfprApEquipmentChassisAdminState OBJECT-TYPE
    SYNTAX       CfprApEquipmentChassisAdminState
    MAX-ACCESS   read-only
    STATUS       current
    DESCRIPTION
        "Cisco Firepower equipment:Chassis:adminState managed
        object property"
    ::= { cfprApEquipmentChassisEntry 5 }

cfprApEquipmentChassisConfigState OBJECT-TYPE
    SYNTAX       CfprApEquipmentChassisConfigState
    MAX-ACCESS   read-only
    STATUS       current
    DESCRIPTION
        "Cisco Firepower equipment:Chassis:configState
        managed object property"
    ::= { cfprApEquipmentChassisEntry 6 }

cfprApEquipmentChassisConnPath OBJECT-TYPE
    SYNTAX       CfprApEquipmentConnectionStatus
    MAX-ACCESS   read-only
    STATUS       current
    DESCRIPTION
        "Cisco Firepower equipment:Chassis:connPath managed
        object property"
    ::= { cfprApEquipmentChassisEntry 7 }

cfprApEquipmentChassisConnStatus OBJECT-TYPE
    SYNTAX       CfprApEquipmentConnectionStatus
    MAX-ACCESS   read-only
    STATUS       current
    DESCRIPTION
        "Cisco Firepower equipment:Chassis:connStatus managed
        object property"
    ::= { cfprApEquipmentChassisEntry 8 }

cfprApEquipmentChassisFabricEpDn OBJECT-TYPE
    SYNTAX       SnmpAdminString
    MAX-ACCESS   read-only
    STATUS       current
    DESCRIPTION
        "Cisco Firepower equipment:Chassis:fabricEpDn managed
        object property"
    ::= { cfprApEquipmentChassisEntry 9 }

cfprApEquipmentChassisFltAggr OBJECT-TYPE
    SYNTAX       Unsigned64
    MAX-ACCESS   read-only
    STATUS       current
    DESCRIPTION
        "Cisco Firepower equipment:Chassis:fltAggr managed
        object property"
    ::= { cfprApEquipmentChassisEntry 10 }

cfprApEquipmentChassisFsmDescr OBJECT-TYPE
    SYNTAX       SnmpAdminString
    MAX-ACCESS   read-only
    STATUS       current
    DESCRIPTION
        "Cisco Firepower equipment:Chassis:fsmDescr managed
        object property"
    ::= { cfprApEquipmentChassisEntry 11 }

cfprApEquipmentChassisFsmPrev OBJECT-TYPE
    SYNTAX       SnmpAdminString
    MAX-ACCESS   read-only
    STATUS       current
    DESCRIPTION
        "Cisco Firepower equipment:Chassis:fsmPrev managed
        object property"
    ::= { cfprApEquipmentChassisEntry 12 }

cfprApEquipmentChassisFsmProgr OBJECT-TYPE
    SYNTAX       Gauge32
    MAX-ACCESS   read-only
    STATUS       current
    DESCRIPTION
        "Cisco Firepower equipment:Chassis:fsmProgr managed
        object property"
    ::= { cfprApEquipmentChassisEntry 13 }

cfprApEquipmentChassisFsmRmtInvErrCode OBJECT-TYPE
    SYNTAX       Gauge32
    MAX-ACCESS   read-only
    STATUS       current
    DESCRIPTION
        "Cisco Firepower equipment:Chassis:fsmRmtInvErrCode
        managed object property"
    ::= { cfprApEquipmentChassisEntry 14 }

cfprApEquipmentChassisFsmRmtInvErrDescr OBJECT-TYPE
    SYNTAX       SnmpAdminString
    MAX-ACCESS   read-only
    STATUS       current
    DESCRIPTION
        "Cisco Firepower equipment:Chassis:fsmRmtInvErrDescr
        managed object property"
    ::= { cfprApEquipmentChassisEntry 15 }

cfprApEquipmentChassisFsmRmtInvRslt OBJECT-TYPE
    SYNTAX       CfprApConditionRemoteInvRslt
    MAX-ACCESS   read-only
    STATUS       current
    DESCRIPTION
        "Cisco Firepower equipment:Chassis:fsmRmtInvRslt
        managed object property"
    ::= { cfprApEquipmentChassisEntry 16 }

cfprApEquipmentChassisFsmStageDescr OBJECT-TYPE
    SYNTAX       SnmpAdminString
    MAX-ACCESS   read-only
    STATUS       current
    DESCRIPTION
        "Cisco Firepower equipment:Chassis:fsmStageDescr
        managed object property"
    ::= { cfprApEquipmentChassisEntry 17 }

cfprApEquipmentChassisFsmStamp OBJECT-TYPE
    SYNTAX       DateAndTime
    MAX-ACCESS   read-only
    STATUS       current
    DESCRIPTION
        "Cisco Firepower equipment:Chassis:fsmStamp managed
        object property"
    ::= { cfprApEquipmentChassisEntry 18 }

cfprApEquipmentChassisFsmStatus OBJECT-TYPE
    SYNTAX       SnmpAdminString
    MAX-ACCESS   read-only
    STATUS       current
    DESCRIPTION
        "Cisco Firepower equipment:Chassis:fsmStatus managed
        object property"
    ::= { cfprApEquipmentChassisEntry 19 }

cfprApEquipmentChassisFsmTry OBJECT-TYPE
    SYNTAX       Gauge32
    MAX-ACCESS   read-only
    STATUS       current
    DESCRIPTION
        "Cisco Firepower equipment:Chassis:fsmTry managed object property"
    ::= { cfprApEquipmentChassisEntry 20 }

cfprApEquipmentChassisId OBJECT-TYPE
    SYNTAX       CfprApEquipmentChassisId
    MAX-ACCESS   read-only
    STATUS       current
    DESCRIPTION
        "Cisco Firepower equipment:Chassis:id managed object property"
    ::= { cfprApEquipmentChassisEntry 21 }

cfprApEquipmentChassisLcTs OBJECT-TYPE
    SYNTAX       DateAndTime
    MAX-ACCESS   read-only
    STATUS       current
    DESCRIPTION
        "Cisco Firepower equipment:Chassis:lcTs managed object property"
    ::= { cfprApEquipmentChassisEntry 22 }

cfprApEquipmentChassisLicGP OBJECT-TYPE
    SYNTAX       Unsigned64
    MAX-ACCESS   read-only
    STATUS       current
    DESCRIPTION
        "Cisco Firepower equipment:Chassis:licGP managed object property"
    ::= { cfprApEquipmentChassisEntry 23 }

cfprApEquipmentChassisLicState OBJECT-TYPE
    SYNTAX       CfprApLicenseState
    MAX-ACCESS   read-only
    STATUS       current
    DESCRIPTION
        "Cisco Firepower equipment:Chassis:licState managed
        object property"
    ::= { cfprApEquipmentChassisEntry 24 }

cfprApEquipmentChassisManagingInst OBJECT-TYPE
    SYNTAX       CfprApNetworkSwitchId
    MAX-ACCESS   read-only
    STATUS       current
    DESCRIPTION
        "Cisco Firepower equipment:Chassis:managingInst
        managed object property"
    ::= { cfprApEquipmentChassisEntry 25 }

cfprApEquipmentChassisMfgTime OBJECT-TYPE
    SYNTAX       DateAndTime
    MAX-ACCESS   read-only
    STATUS       current
    DESCRIPTION
        "Cisco Firepower equipment:Chassis:mfgTime managed
        object property"
    ::= { cfprApEquipmentChassisEntry 26 }

cfprApEquipmentChassisModel OBJECT-TYPE
    SYNTAX       SnmpAdminString
    MAX-ACCESS   read-only
    STATUS       current
    DESCRIPTION
        "Cisco Firepower equipment:Chassis:model managed object property"
    ::= { cfprApEquipmentChassisEntry 27 }

cfprApEquipmentChassisOperQualifier OBJECT-TYPE
    SYNTAX       CfprApEquipmentChassisIssues
    MAX-ACCESS   read-only
    STATUS       current
    DESCRIPTION
        "Cisco Firepower equipment:Chassis:operQualifier
        managed object property"
    ::= { cfprApEquipmentChassisEntry 28 }

cfprApEquipmentChassisOperQualifierReason OBJECT-TYPE
    SYNTAX       SnmpAdminString
    MAX-ACCESS   read-only
    STATUS       current
    DESCRIPTION
        "Cisco Firepower equipment:Chassis:operQualifierReason
        managed object property"
    ::= { cfprApEquipmentChassisEntry 29 }

cfprApEquipmentChassisOperState OBJECT-TYPE
    SYNTAX       CfprApEquipmentOperability
    MAX-ACCESS   read-only
    STATUS       current
    DESCRIPTION
        "Cisco Firepower equipment:Chassis:operState managed
        object property"
    ::= { cfprApEquipmentChassisEntry 30 }

cfprApEquipmentChassisOperability OBJECT-TYPE
    SYNTAX       CfprApEquipmentOperability
    MAX-ACCESS   read-only
    STATUS       current
    DESCRIPTION
        "Cisco Firepower equipment:Chassis:operability
        managed object property"
    ::= { cfprApEquipmentChassisEntry 31 }

cfprApEquipmentChassisPartNumber OBJECT-TYPE
    SYNTAX       SnmpAdminString
    MAX-ACCESS   read-only
    STATUS       current
    DESCRIPTION
        "Cisco Firepower equipment:Chassis:partNumber managed
        object property"
    ::= { cfprApEquipmentChassisEntry 32 }

cfprApEquipmentChassisPower OBJECT-TYPE
    SYNTAX       CfprApEquipmentChassisPowerOperState
    MAX-ACCESS   read-only
    STATUS       current
    DESCRIPTION
        "Cisco Firepower equipment:Chassis:power managed object property"
    ::= { cfprApEquipmentChassisEntry 33 }

cfprApEquipmentChassisPresence OBJECT-TYPE
    SYNTAX       CfprApEquipmentPresence
    MAX-ACCESS   read-only
    STATUS       current
    DESCRIPTION
        "Cisco Firepower equipment:Chassis:presence managed
        object property"
    ::= { cfprApEquipmentChassisEntry 34 }

cfprApEquipmentChassisRevision OBJECT-TYPE
    SYNTAX       SnmpAdminString
    MAX-ACCESS   read-only
    STATUS       current
    DESCRIPTION
        "Cisco Firepower equipment:Chassis:revision managed
        object property"
    ::= { cfprApEquipmentChassisEntry 35 }

cfprApEquipmentChassisSerial OBJECT-TYPE
    SYNTAX       SnmpAdminString
    MAX-ACCESS   read-only
    STATUS       current
    DESCRIPTION
        "Cisco Firepower equipment:Chassis:serial managed object property"
    ::= { cfprApEquipmentChassisEntry 37 }

cfprApEquipmentChassisThermal OBJECT-TYPE
    SYNTAX       CfprApEquipmentSensorThresholdStatus
    MAX-ACCESS   read-only
    STATUS       current
    DESCRIPTION
        "Cisco Firepower equipment:Chassis:thermal managed
        object property"
    ::= { cfprApEquipmentChassisEntry 38 }

cfprApEquipmentChassisThermalStateQualifier OBJECT-TYPE
    SYNTAX       SnmpAdminString
    MAX-ACCESS   read-only
    STATUS       current
    DESCRIPTION
        "Cisco Firepower equipment:Chassis:thermalStateQualifier
        managed object property"
    ::= { cfprApEquipmentChassisEntry 39 }

cfprApEquipmentChassisUsrLbl OBJECT-TYPE
    SYNTAX       SnmpAdminString
    MAX-ACCESS   read-only
    STATUS       current
    DESCRIPTION
        "Cisco Firepower equipment:Chassis:usrLbl managed object property"
    ::= { cfprApEquipmentChassisEntry 40 }

cfprApEquipmentChassisVendor OBJECT-TYPE
    SYNTAX       SnmpAdminString
    MAX-ACCESS   read-only
    STATUS       current
    DESCRIPTION
        "Cisco Firepower equipment:Chassis:vendor managed object property"
    ::= { cfprApEquipmentChassisEntry 41 }

cfprApEquipmentChassisVersionHolder OBJECT-TYPE
    SYNTAX       TruthValue
    MAX-ACCESS   read-only
    STATUS       current
    DESCRIPTION
        "Cisco Firepower equipment:Chassis:versionHolder
        managed object property"
    ::= { cfprApEquipmentChassisEntry 42 }

cfprApEquipmentChassisVid OBJECT-TYPE
    SYNTAX       SnmpAdminString
    MAX-ACCESS   read-only
    STATUS       current
    DESCRIPTION
        "Cisco Firepower equipment:Chassis:vid managed object property"
    ::= { cfprApEquipmentChassisEntry 43 }

cfprApEquipmentChassisCapProviderTable OBJECT-TYPE
    SYNTAX           SEQUENCE OF CfprApEquipmentChassisCapProviderEntry
    MAX-ACCESS       not-accessible
    STATUS           current
    DESCRIPTION
        "Cisco Firepower equipment:ChassisCapProvider managed
        object table"
    ::= { cfprApEquipmentObjects 24 }

cfprApEquipmentChassisCapProviderEntry OBJECT-TYPE
    SYNTAX           CfprApEquipmentChassisCapProviderEntry
    MAX-ACCESS       not-accessible
    STATUS           current
    DESCRIPTION
        "Entry for the cfprApEquipmentChassisCapProviderTable table."
    INDEX { cfprApEquipmentChassisCapProviderInstanceId }
    ::= { cfprApEquipmentChassisCapProviderTable 1 }

CfprApEquipmentChassisCapProviderEntry ::= SEQUENCE {
    cfprApEquipmentChassisCapProviderInstanceId                      CfprApManagedObjectId,
    cfprApEquipmentChassisCapProviderDn                              CfprApManagedObjectDn,
    cfprApEquipmentChassisCapProviderRn                              SnmpAdminString,
    cfprApEquipmentChassisCapProviderDeleted                         TruthValue,
    cfprApEquipmentChassisCapProviderDeprecated                      TruthValue,
    cfprApEquipmentChassisCapProviderElementLoadFailures             Gauge32,
    cfprApEquipmentChassisCapProviderElementsLoaded                  Gauge32,
    cfprApEquipmentChassisCapProviderGencount                        Gauge32,
    cfprApEquipmentChassisCapProviderLoadErrors                      Gauge32,
    cfprApEquipmentChassisCapProviderLoadWarnings                    Gauge32,
    cfprApEquipmentChassisCapProviderMgmtPlaneVer                    SnmpAdminString,
    cfprApEquipmentChassisCapProviderModel                           SnmpAdminString,
    cfprApEquipmentChassisCapProviderPromCardType                    Gauge32,
    cfprApEquipmentChassisCapProviderRevision                        SnmpAdminString,
    cfprApEquipmentChassisCapProviderVendor                          SnmpAdminString
}

cfprApEquipmentChassisCapProviderInstanceId OBJECT-TYPE
    SYNTAX       CfprApManagedObjectId
    MAX-ACCESS   not-accessible
    STATUS       current
    DESCRIPTION
        "Instance identifier of the managed object."
    ::= { cfprApEquipmentChassisCapProviderEntry 1 }

cfprApEquipmentChassisCapProviderDn OBJECT-TYPE
    SYNTAX       CfprApManagedObjectDn
    MAX-ACCESS   read-only
    STATUS       current
    DESCRIPTION
        "Cisco Firepower equipment:ChassisCapProvider:dn
        managed object property"
    ::= { cfprApEquipmentChassisCapProviderEntry 2 }

cfprApEquipmentChassisCapProviderRn OBJECT-TYPE
    SYNTAX       SnmpAdminString
    MAX-ACCESS   read-only
    STATUS       current
    DESCRIPTION
        "Cisco Firepower equipment:ChassisCapProvider:rn
        managed object property"
    ::= { cfprApEquipmentChassisCapProviderEntry 3 }

cfprApEquipmentChassisCapProviderDeleted OBJECT-TYPE
    SYNTAX       TruthValue
    MAX-ACCESS   read-only
    STATUS       current
    DESCRIPTION
        "Cisco Firepower equipment:ChassisCapProvider:deleted
        managed object property"
    ::= { cfprApEquipmentChassisCapProviderEntry 4 }

cfprApEquipmentChassisCapProviderDeprecated OBJECT-TYPE
    SYNTAX       TruthValue
    MAX-ACCESS   read-only
    STATUS       current
    DESCRIPTION
        "Cisco Firepower equipment:ChassisCapProvider:deprecated
        managed object property"
    ::= { cfprApEquipmentChassisCapProviderEntry 5 }

cfprApEquipmentChassisCapProviderElementLoadFailures OBJECT-TYPE
    SYNTAX       Gauge32
    MAX-ACCESS   read-only
    STATUS       current
    DESCRIPTION
        "Cisco Firepower equipment:ChassisCapProvider:elementLoadFailures
        managed object property"
    ::= { cfprApEquipmentChassisCapProviderEntry 6 }

cfprApEquipmentChassisCapProviderElementsLoaded OBJECT-TYPE
    SYNTAX       Gauge32
    MAX-ACCESS   read-only
    STATUS       current
    DESCRIPTION
        "Cisco Firepower equipment:ChassisCapProvider:elementsLoaded
        managed object property"
    ::= { cfprApEquipmentChassisCapProviderEntry 7 }

cfprApEquipmentChassisCapProviderGencount OBJECT-TYPE
    SYNTAX       Gauge32
    MAX-ACCESS   read-only
    STATUS       current
    DESCRIPTION
        "Cisco Firepower equipment:ChassisCapProvider:gencount
        managed object property"
    ::= { cfprApEquipmentChassisCapProviderEntry 8 }

cfprApEquipmentChassisCapProviderLoadErrors OBJECT-TYPE
    SYNTAX       Gauge32
    MAX-ACCESS   read-only
    STATUS       current
    DESCRIPTION
        "Cisco Firepower equipment:ChassisCapProvider:loadErrors
        managed object property"
    ::= { cfprApEquipmentChassisCapProviderEntry 9 }

cfprApEquipmentChassisCapProviderLoadWarnings OBJECT-TYPE
    SYNTAX       Gauge32
    MAX-ACCESS   read-only
    STATUS       current
    DESCRIPTION
        "Cisco Firepower equipment:ChassisCapProvider:loadWarnings
        managed object property"
    ::= { cfprApEquipmentChassisCapProviderEntry 10 }

cfprApEquipmentChassisCapProviderMgmtPlaneVer OBJECT-TYPE
    SYNTAX       SnmpAdminString
    MAX-ACCESS   read-only
    STATUS       current
    DESCRIPTION
        "Cisco Firepower equipment:ChassisCapProvider:mgmtPlaneVer
        managed object property"
    ::= { cfprApEquipmentChassisCapProviderEntry 11 }

cfprApEquipmentChassisCapProviderModel OBJECT-TYPE
    SYNTAX       SnmpAdminString
    MAX-ACCESS   read-only
    STATUS       current
    DESCRIPTION
        "Cisco Firepower equipment:ChassisCapProvider:model
        managed object property"
    ::= { cfprApEquipmentChassisCapProviderEntry 12 }

cfprApEquipmentChassisCapProviderPromCardType OBJECT-TYPE
    SYNTAX       Gauge32
    MAX-ACCESS   read-only
    STATUS       current
    DESCRIPTION
        "Cisco Firepower equipment:ChassisCapProvider:promCardType
        managed object property"
    ::= { cfprApEquipmentChassisCapProviderEntry 13 }

cfprApEquipmentChassisCapProviderRevision OBJECT-TYPE
    SYNTAX       SnmpAdminString
    MAX-ACCESS   read-only
    STATUS       current
    DESCRIPTION
        "Cisco Firepower equipment:ChassisCapProvider:revision
        managed object property"
    ::= { cfprApEquipmentChassisCapProviderEntry 14 }

cfprApEquipmentChassisCapProviderVendor OBJECT-TYPE
    SYNTAX       SnmpAdminString
    MAX-ACCESS   read-only
    STATUS       current
    DESCRIPTION
        "Cisco Firepower equipment:ChassisCapProvider:vendor
        managed object property"
    ::= { cfprApEquipmentChassisCapProviderEntry 15 }

cfprApEquipmentChassisFsmTable OBJECT-TYPE
    SYNTAX           SEQUENCE OF CfprApEquipmentChassisFsmEntry
    MAX-ACCESS       not-accessible
    STATUS           current
    DESCRIPTION
        "Cisco Firepower equipment:ChassisFsm managed object table"
    ::= { cfprApEquipmentObjects 25 }

cfprApEquipmentChassisFsmEntry OBJECT-TYPE
    SYNTAX           CfprApEquipmentChassisFsmEntry
    MAX-ACCESS       not-accessible
    STATUS           current
    DESCRIPTION
        "Entry for the cfprApEquipmentChassisFsmTable table."
    INDEX { cfprApEquipmentChassisFsmInstanceId }
    ::= { cfprApEquipmentChassisFsmTable 1 }

CfprApEquipmentChassisFsmEntry ::= SEQUENCE {
    cfprApEquipmentChassisFsmInstanceId                              CfprApManagedObjectId,
    cfprApEquipmentChassisFsmDn                                      CfprApManagedObjectDn,
    cfprApEquipmentChassisFsmRn                                      SnmpAdminString,
    cfprApEquipmentChassisFsmCompletionTime                          DateAndTime,
    cfprApEquipmentChassisFsmCurrentFsm                              CfprApEquipmentChassisFsmCurrentFsm,
    cfprApEquipmentChassisFsmDescrData                               SnmpAdminString,
    cfprApEquipmentChassisFsmFsmStatus                               CfprApFsmFsmStageStatus,
    cfprApEquipmentChassisFsmProgress                                Gauge32,
    cfprApEquipmentChassisFsmRmtErrCode                              Gauge32,
    cfprApEquipmentChassisFsmRmtErrDescr                             SnmpAdminString,
    cfprApEquipmentChassisFsmRmtRslt                                 CfprApConditionRemoteInvRslt
}

cfprApEquipmentChassisFsmInstanceId OBJECT-TYPE
    SYNTAX       CfprApManagedObjectId
    MAX-ACCESS   not-accessible
    STATUS       current
    DESCRIPTION
        "Instance identifier of the managed object."
    ::= { cfprApEquipmentChassisFsmEntry 1 }

cfprApEquipmentChassisFsmDn OBJECT-TYPE
    SYNTAX       CfprApManagedObjectDn
    MAX-ACCESS   read-only
    STATUS       current
    DESCRIPTION
        "Cisco Firepower equipment:ChassisFsm:dn managed object property"
    ::= { cfprApEquipmentChassisFsmEntry 2 }

cfprApEquipmentChassisFsmRn OBJECT-TYPE
    SYNTAX       SnmpAdminString
    MAX-ACCESS   read-only
    STATUS       current
    DESCRIPTION
        "Cisco Firepower equipment:ChassisFsm:rn managed object property"
    ::= { cfprApEquipmentChassisFsmEntry 3 }

cfprApEquipmentChassisFsmCompletionTime OBJECT-TYPE
    SYNTAX       DateAndTime
    MAX-ACCESS   read-only
    STATUS       current
    DESCRIPTION
        "Cisco Firepower equipment:ChassisFsm:completionTime
        managed object property"
    ::= { cfprApEquipmentChassisFsmEntry 4 }

cfprApEquipmentChassisFsmCurrentFsm OBJECT-TYPE
    SYNTAX       CfprApEquipmentChassisFsmCurrentFsm
    MAX-ACCESS   read-only
    STATUS       current
    DESCRIPTION
        "Cisco Firepower equipment:ChassisFsm:currentFsm
        managed object property"
    ::= { cfprApEquipmentChassisFsmEntry 5 }

cfprApEquipmentChassisFsmDescrData OBJECT-TYPE
    SYNTAX       SnmpAdminString
    MAX-ACCESS   read-only
    STATUS       current
    DESCRIPTION
        "Cisco Firepower equipment:ChassisFsm:descr managed
        object property"
    ::= { cfprApEquipmentChassisFsmEntry 6 }

cfprApEquipmentChassisFsmFsmStatus OBJECT-TYPE
    SYNTAX       CfprApFsmFsmStageStatus
    MAX-ACCESS   read-only
    STATUS       current
    DESCRIPTION
        "Cisco Firepower equipment:ChassisFsm:fsmStatus
        managed object property"
    ::= { cfprApEquipmentChassisFsmEntry 7 }

cfprApEquipmentChassisFsmProgress OBJECT-TYPE
    SYNTAX       Gauge32
    MAX-ACCESS   read-only
    STATUS       current
    DESCRIPTION
        "Cisco Firepower equipment:ChassisFsm:progress
        managed object property"
    ::= { cfprApEquipmentChassisFsmEntry 8 }

cfprApEquipmentChassisFsmRmtErrCode OBJECT-TYPE
    SYNTAX       Gauge32
    MAX-ACCESS   read-only
    STATUS       current
    DESCRIPTION
        "Cisco Firepower equipment:ChassisFsm:rmtErrCode
        managed object property"
    ::= { cfprApEquipmentChassisFsmEntry 9 }

cfprApEquipmentChassisFsmRmtErrDescr OBJECT-TYPE
    SYNTAX       SnmpAdminString
    MAX-ACCESS   read-only
    STATUS       current
    DESCRIPTION
        "Cisco Firepower equipment:ChassisFsm:rmtErrDescr
        managed object property"
    ::= { cfprApEquipmentChassisFsmEntry 10 }

cfprApEquipmentChassisFsmRmtRslt OBJECT-TYPE
    SYNTAX       CfprApConditionRemoteInvRslt
    MAX-ACCESS   read-only
    STATUS       current
    DESCRIPTION
        "Cisco Firepower equipment:ChassisFsm:rmtRslt managed
        object property"
    ::= { cfprApEquipmentChassisFsmEntry 11 }

cfprApEquipmentChassisFsmStageTable OBJECT-TYPE
    SYNTAX           SEQUENCE OF CfprApEquipmentChassisFsmStageEntry
    MAX-ACCESS       not-accessible
    STATUS           current
    DESCRIPTION
        "Cisco Firepower equipment:ChassisFsmStage managed object table"
    ::= { cfprApEquipmentObjects 26 }

cfprApEquipmentChassisFsmStageEntry OBJECT-TYPE
    SYNTAX           CfprApEquipmentChassisFsmStageEntry
    MAX-ACCESS       not-accessible
    STATUS           current
    DESCRIPTION
        "Entry for the cfprApEquipmentChassisFsmStageTable table."
    INDEX { cfprApEquipmentChassisFsmStageInstanceId }
    ::= { cfprApEquipmentChassisFsmStageTable 1 }

CfprApEquipmentChassisFsmStageEntry ::= SEQUENCE {
    cfprApEquipmentChassisFsmStageInstanceId                         CfprApManagedObjectId,
    cfprApEquipmentChassisFsmStageDn                                 CfprApManagedObjectDn,
    cfprApEquipmentChassisFsmStageRn                                 SnmpAdminString,
    cfprApEquipmentChassisFsmStageDescrData                          SnmpAdminString,
    cfprApEquipmentChassisFsmStageLastUpdateTime                     DateAndTime,
    cfprApEquipmentChassisFsmStageName                               CfprApEquipmentChassisFsmStageName,
    cfprApEquipmentChassisFsmStageOrder                              Gauge32,
    cfprApEquipmentChassisFsmStageRetry                              Gauge32,
    cfprApEquipmentChassisFsmStageStageStatus                        CfprApFsmFsmStageStatus
}

cfprApEquipmentChassisFsmStageInstanceId OBJECT-TYPE
    SYNTAX       CfprApManagedObjectId
    MAX-ACCESS   not-accessible
    STATUS       current
    DESCRIPTION
        "Instance identifier of the managed object."
    ::= { cfprApEquipmentChassisFsmStageEntry 1 }

cfprApEquipmentChassisFsmStageDn OBJECT-TYPE
    SYNTAX       CfprApManagedObjectDn
    MAX-ACCESS   read-only
    STATUS       current
    DESCRIPTION
        "Cisco Firepower equipment:ChassisFsmStage:dn managed
        object property"
    ::= { cfprApEquipmentChassisFsmStageEntry 2 }

cfprApEquipmentChassisFsmStageRn OBJECT-TYPE
    SYNTAX       SnmpAdminString
    MAX-ACCESS   read-only
    STATUS       current
    DESCRIPTION
        "Cisco Firepower equipment:ChassisFsmStage:rn managed
        object property"
    ::= { cfprApEquipmentChassisFsmStageEntry 3 }

cfprApEquipmentChassisFsmStageDescrData OBJECT-TYPE
    SYNTAX       SnmpAdminString
    MAX-ACCESS   read-only
    STATUS       current
    DESCRIPTION
        "Cisco Firepower equipment:ChassisFsmStage:descr
        managed object property"
    ::= { cfprApEquipmentChassisFsmStageEntry 4 }

cfprApEquipmentChassisFsmStageLastUpdateTime OBJECT-TYPE
    SYNTAX       DateAndTime
    MAX-ACCESS   read-only
    STATUS       current
    DESCRIPTION
        "Cisco Firepower equipment:ChassisFsmStage:lastUpdateTime
        managed object property"
    ::= { cfprApEquipmentChassisFsmStageEntry 5 }

cfprApEquipmentChassisFsmStageName OBJECT-TYPE
    SYNTAX       CfprApEquipmentChassisFsmStageName
    MAX-ACCESS   read-only
    STATUS       current
    DESCRIPTION
        "Cisco Firepower equipment:ChassisFsmStage:name
        managed object property"
    ::= { cfprApEquipmentChassisFsmStageEntry 6 }

cfprApEquipmentChassisFsmStageOrder OBJECT-TYPE
    SYNTAX       Gauge32
    MAX-ACCESS   read-only
    STATUS       current
    DESCRIPTION
        "Cisco Firepower equipment:ChassisFsmStage:order
        managed object property"
    ::= { cfprApEquipmentChassisFsmStageEntry 7 }

cfprApEquipmentChassisFsmStageRetry OBJECT-TYPE
    SYNTAX       Gauge32
    MAX-ACCESS   read-only
    STATUS       current
    DESCRIPTION
        "Cisco Firepower equipment:ChassisFsmStage:retry
        managed object property"
    ::= { cfprApEquipmentChassisFsmStageEntry 8 }

cfprApEquipmentChassisFsmStageStageStatus OBJECT-TYPE
    SYNTAX       CfprApFsmFsmStageStatus
    MAX-ACCESS   read-only
    STATUS       current
    DESCRIPTION
        "Cisco Firepower equipment:ChassisFsmStage:stageStatus
        managed object property"
    ::= { cfprApEquipmentChassisFsmStageEntry 9 }

cfprApEquipmentChassisFsmTaskTable OBJECT-TYPE
    SYNTAX           SEQUENCE OF CfprApEquipmentChassisFsmTaskEntry
    MAX-ACCESS       not-accessible
    STATUS           current
    DESCRIPTION
        "Cisco Firepower equipment:ChassisFsmTask managed object table"
    ::= { cfprApEquipmentObjects 27 }

cfprApEquipmentChassisFsmTaskEntry OBJECT-TYPE
    SYNTAX           CfprApEquipmentChassisFsmTaskEntry
    MAX-ACCESS       not-accessible
    STATUS           current
    DESCRIPTION
        "Entry for the cfprApEquipmentChassisFsmTaskTable table."
    INDEX { cfprApEquipmentChassisFsmTaskInstanceId }
    ::= { cfprApEquipmentChassisFsmTaskTable 1 }

CfprApEquipmentChassisFsmTaskEntry ::= SEQUENCE {
    cfprApEquipmentChassisFsmTaskInstanceId                          CfprApManagedObjectId,
    cfprApEquipmentChassisFsmTaskDn                                  CfprApManagedObjectDn,
    cfprApEquipmentChassisFsmTaskRn                                  SnmpAdminString,
    cfprApEquipmentChassisFsmTaskCompletion                          CfprApFsmCompletion,
    cfprApEquipmentChassisFsmTaskFlags                               CfprApFsmFlags,
    cfprApEquipmentChassisFsmTaskItem                                CfprApEquipmentChassisFsmTaskItem,
    cfprApEquipmentChassisFsmTaskSeqId                               Gauge32
}

cfprApEquipmentChassisFsmTaskInstanceId OBJECT-TYPE
    SYNTAX       CfprApManagedObjectId
    MAX-ACCESS   not-accessible
    STATUS       current
    DESCRIPTION
        "Instance identifier of the managed object."
    ::= { cfprApEquipmentChassisFsmTaskEntry 1 }

cfprApEquipmentChassisFsmTaskDn OBJECT-TYPE
    SYNTAX       CfprApManagedObjectDn
    MAX-ACCESS   read-only
    STATUS       current
    DESCRIPTION
        "Cisco Firepower equipment:ChassisFsmTask:dn managed
        object property"
    ::= { cfprApEquipmentChassisFsmTaskEntry 2 }

cfprApEquipmentChassisFsmTaskRn OBJECT-TYPE
    SYNTAX       SnmpAdminString
    MAX-ACCESS   read-only
    STATUS       current
    DESCRIPTION
        "Cisco Firepower equipment:ChassisFsmTask:rn managed
        object property"
    ::= { cfprApEquipmentChassisFsmTaskEntry 3 }

cfprApEquipmentChassisFsmTaskCompletion OBJECT-TYPE
    SYNTAX       CfprApFsmCompletion
    MAX-ACCESS   read-only
    STATUS       current
    DESCRIPTION
        "Cisco Firepower equipment:ChassisFsmTask:completion
        managed object property"
    ::= { cfprApEquipmentChassisFsmTaskEntry 4 }

cfprApEquipmentChassisFsmTaskFlags OBJECT-TYPE
    SYNTAX       CfprApFsmFlags
    MAX-ACCESS   read-only
    STATUS       current
    DESCRIPTION
        "Cisco Firepower equipment:ChassisFsmTask:flags
        managed object property"
    ::= { cfprApEquipmentChassisFsmTaskEntry 5 }

cfprApEquipmentChassisFsmTaskItem OBJECT-TYPE
    SYNTAX       CfprApEquipmentChassisFsmTaskItem
    MAX-ACCESS   read-only
    STATUS       current
    DESCRIPTION
        "Cisco Firepower equipment:ChassisFsmTask:item
        managed object property"
    ::= { cfprApEquipmentChassisFsmTaskEntry 6 }

cfprApEquipmentChassisFsmTaskSeqId OBJECT-TYPE
    SYNTAX       Gauge32
    MAX-ACCESS   read-only
    STATUS       current
    DESCRIPTION
        "Cisco Firepower equipment:ChassisFsmTask:seqId
        managed object property"
    ::= { cfprApEquipmentChassisFsmTaskEntry 7 }

cfprApEquipmentChassisStatsTable OBJECT-TYPE
    SYNTAX           SEQUENCE OF CfprApEquipmentChassisStatsEntry
    MAX-ACCESS       not-accessible
    STATUS           current
    DESCRIPTION
        "Cisco Firepower equipment:ChassisStats managed object table"
    ::= { cfprApEquipmentObjects 28 }

cfprApEquipmentChassisStatsEntry OBJECT-TYPE
    SYNTAX           CfprApEquipmentChassisStatsEntry
    MAX-ACCESS       not-accessible
    STATUS           current
    DESCRIPTION
        "Entry for the cfprApEquipmentChassisStatsTable table."
    INDEX { cfprApEquipmentChassisStatsInstanceId }
    ::= { cfprApEquipmentChassisStatsTable 1 }

CfprApEquipmentChassisStatsEntry ::= SEQUENCE {
    cfprApEquipmentChassisStatsInstanceId                            CfprApManagedObjectId,
    cfprApEquipmentChassisStatsDn                                    CfprApManagedObjectDn,
    cfprApEquipmentChassisStatsRn                                    SnmpAdminString,
    cfprApEquipmentChassisStatsIntervals                             Gauge32,
    cfprApEquipmentChassisStatsOutletTemp1                           INTEGER,
    cfprApEquipmentChassisStatsOutletTemp1Avg                        INTEGER,
    cfprApEquipmentChassisStatsOutletTemp1Max                        INTEGER,
    cfprApEquipmentChassisStatsOutletTemp1Min                        INTEGER,
    cfprApEquipmentChassisStatsOutletTemp2                           INTEGER,
    cfprApEquipmentChassisStatsOutletTemp2Avg                        INTEGER,
    cfprApEquipmentChassisStatsOutletTemp2Max                        INTEGER,
    cfprApEquipmentChassisStatsOutletTemp2Min                        INTEGER,
    cfprApEquipmentChassisStatsSuspect                               TruthValue,
    cfprApEquipmentChassisStatsThresholded                           CfprApEquipmentChassisStatsThresholded,
    cfprApEquipmentChassisStatsTimeCollected                         DateAndTime,
    cfprApEquipmentChassisStatsUpdate                                Gauge32
}

cfprApEquipmentChassisStatsInstanceId OBJECT-TYPE
    SYNTAX       CfprApManagedObjectId
    MAX-ACCESS   not-accessible
    STATUS       current
    DESCRIPTION
        "Instance identifier of the managed object."
    ::= { cfprApEquipmentChassisStatsEntry 1 }

cfprApEquipmentChassisStatsDn OBJECT-TYPE
    SYNTAX       CfprApManagedObjectDn
    MAX-ACCESS   read-only
    STATUS       current
    DESCRIPTION
        "Cisco Firepower equipment:ChassisStats:dn managed
        object property"
    ::= { cfprApEquipmentChassisStatsEntry 2 }

cfprApEquipmentChassisStatsRn OBJECT-TYPE
    SYNTAX       SnmpAdminString
    MAX-ACCESS   read-only
    STATUS       current
    DESCRIPTION
        "Cisco Firepower equipment:ChassisStats:rn managed
        object property"
    ::= { cfprApEquipmentChassisStatsEntry 3 }

cfprApEquipmentChassisStatsIntervals OBJECT-TYPE
    SYNTAX       Gauge32
    MAX-ACCESS   read-only
    STATUS       current
    DESCRIPTION
        "Cisco Firepower equipment:ChassisStats:intervals
        managed object property"
    ::= { cfprApEquipmentChassisStatsEntry 16 }

cfprApEquipmentChassisStatsOutletTemp1 OBJECT-TYPE
    SYNTAX       INTEGER
    MAX-ACCESS   read-only
    STATUS       current
    DESCRIPTION
        "Cisco Firepower equipment:ChassisStats:outletTemp1
        managed object property"
    ::= { cfprApEquipmentChassisStatsEntry 17 }

cfprApEquipmentChassisStatsOutletTemp1Avg OBJECT-TYPE
    SYNTAX       INTEGER
    MAX-ACCESS   read-only
    STATUS       current
    DESCRIPTION
        "Cisco Firepower equipment:ChassisStats:outletTemp1Avg
        managed object property"
    ::= { cfprApEquipmentChassisStatsEntry 18 }

cfprApEquipmentChassisStatsOutletTemp1Max OBJECT-TYPE
    SYNTAX       INTEGER
    MAX-ACCESS   read-only
    STATUS       current
    DESCRIPTION
        "Cisco Firepower equipment:ChassisStats:outletTemp1Max
        managed object property"
    ::= { cfprApEquipmentChassisStatsEntry 19 }

cfprApEquipmentChassisStatsOutletTemp1Min OBJECT-TYPE
    SYNTAX       INTEGER
    MAX-ACCESS   read-only
    STATUS       current
    DESCRIPTION
        "Cisco Firepower equipment:ChassisStats:outletTemp1Min
        managed object property"
    ::= { cfprApEquipmentChassisStatsEntry 20 }

cfprApEquipmentChassisStatsOutletTemp2 OBJECT-TYPE
    SYNTAX       INTEGER
    MAX-ACCESS   read-only
    STATUS       current
    DESCRIPTION
        "Cisco Firepower equipment:ChassisStats:outletTemp2
        managed object property"
    ::= { cfprApEquipmentChassisStatsEntry 21 }

cfprApEquipmentChassisStatsOutletTemp2Avg OBJECT-TYPE
    SYNTAX       INTEGER
    MAX-ACCESS   read-only
    STATUS       current
    DESCRIPTION
        "Cisco Firepower equipment:ChassisStats:outletTemp2Avg
        managed object property"
    ::= { cfprApEquipmentChassisStatsEntry 22 }

cfprApEquipmentChassisStatsOutletTemp2Max OBJECT-TYPE
    SYNTAX       INTEGER
    MAX-ACCESS   read-only
    STATUS       current
    DESCRIPTION
        "Cisco Firepower equipment:ChassisStats:outletTemp2Max
        managed object property"
    ::= { cfprApEquipmentChassisStatsEntry 23 }

cfprApEquipmentChassisStatsOutletTemp2Min OBJECT-TYPE
    SYNTAX       INTEGER
    MAX-ACCESS   read-only
    STATUS       current
    DESCRIPTION
        "Cisco Firepower equipment:ChassisStats:outletTemp2Min
        managed object property"
    ::= { cfprApEquipmentChassisStatsEntry 24 }

cfprApEquipmentChassisStatsSuspect OBJECT-TYPE
    SYNTAX       TruthValue
    MAX-ACCESS   read-only
    STATUS       current
    DESCRIPTION
        "Cisco Firepower equipment:ChassisStats:suspect
        managed object property"
    ::= { cfprApEquipmentChassisStatsEntry 29 }

cfprApEquipmentChassisStatsThresholded OBJECT-TYPE
    SYNTAX       CfprApEquipmentChassisStatsThresholded
    MAX-ACCESS   read-only
    STATUS       current
    DESCRIPTION
        "Cisco Firepower equipment:ChassisStats:thresholded
        managed object property"
    ::= { cfprApEquipmentChassisStatsEntry 30 }

cfprApEquipmentChassisStatsTimeCollected OBJECT-TYPE
    SYNTAX       DateAndTime
    MAX-ACCESS   read-only
    STATUS       current
    DESCRIPTION
        "Cisco Firepower equipment:ChassisStats:timeCollected
        managed object property"
    ::= { cfprApEquipmentChassisStatsEntry 31 }

cfprApEquipmentChassisStatsUpdate OBJECT-TYPE
    SYNTAX       Gauge32
    MAX-ACCESS   read-only
    STATUS       current
    DESCRIPTION
        "Cisco Firepower equipment:ChassisStats:update
        managed object property"
    ::= { cfprApEquipmentChassisStatsEntry 32 }

cfprApEquipmentChassisStatsHistTable OBJECT-TYPE
    SYNTAX           SEQUENCE OF CfprApEquipmentChassisStatsHistEntry
    MAX-ACCESS       not-accessible
    STATUS           current
    DESCRIPTION
        "Cisco Firepower equipment:ChassisStatsHist managed object table"
    ::= { cfprApEquipmentObjects 29 }

cfprApEquipmentChassisStatsHistEntry OBJECT-TYPE
    SYNTAX           CfprApEquipmentChassisStatsHistEntry
    MAX-ACCESS       not-accessible
    STATUS           current
    DESCRIPTION
        "Entry for the cfprApEquipmentChassisStatsHistTable table."
    INDEX { cfprApEquipmentChassisStatsHistInstanceId }
    ::= { cfprApEquipmentChassisStatsHistTable 1 }

CfprApEquipmentChassisStatsHistEntry ::= SEQUENCE {
    cfprApEquipmentChassisStatsHistInstanceId                        CfprApManagedObjectId,
    cfprApEquipmentChassisStatsHistDn                                CfprApManagedObjectDn,
    cfprApEquipmentChassisStatsHistRn                                SnmpAdminString,
    cfprApEquipmentChassisStatsHistId                                Unsigned64,
    cfprApEquipmentChassisStatsHistMostRecent                        TruthValue,
    cfprApEquipmentChassisStatsHistOutletTemp1                       INTEGER,
    cfprApEquipmentChassisStatsHistOutletTemp1Avg                    INTEGER,
    cfprApEquipmentChassisStatsHistOutletTemp1Max                    INTEGER,
    cfprApEquipmentChassisStatsHistOutletTemp1Min                    INTEGER,
    cfprApEquipmentChassisStatsHistOutletTemp2                       INTEGER,
    cfprApEquipmentChassisStatsHistOutletTemp2Avg                    INTEGER,
    cfprApEquipmentChassisStatsHistOutletTemp2Max                    INTEGER,
    cfprApEquipmentChassisStatsHistOutletTemp2Min                    INTEGER,
    cfprApEquipmentChassisStatsHistSuspect                           TruthValue,
    cfprApEquipmentChassisStatsHistThresholded                       CfprApEquipmentChassisStatsHistThresholded,
    cfprApEquipmentChassisStatsHistTimeCollected                     DateAndTime
}

cfprApEquipmentChassisStatsHistInstanceId OBJECT-TYPE
    SYNTAX       CfprApManagedObjectId
    MAX-ACCESS   not-accessible
    STATUS       current
    DESCRIPTION
        "Instance identifier of the managed object."
    ::= { cfprApEquipmentChassisStatsHistEntry 1 }

cfprApEquipmentChassisStatsHistDn OBJECT-TYPE
    SYNTAX       CfprApManagedObjectDn
    MAX-ACCESS   read-only
    STATUS       current
    DESCRIPTION
        "Cisco Firepower equipment:ChassisStatsHist:dn
        managed object property"
    ::= { cfprApEquipmentChassisStatsHistEntry 2 }

cfprApEquipmentChassisStatsHistRn OBJECT-TYPE
    SYNTAX       SnmpAdminString
    MAX-ACCESS   read-only
    STATUS       current
    DESCRIPTION
        "Cisco Firepower equipment:ChassisStatsHist:rn
        managed object property"
    ::= { cfprApEquipmentChassisStatsHistEntry 3 }

cfprApEquipmentChassisStatsHistId OBJECT-TYPE
    SYNTAX       Unsigned64
    MAX-ACCESS   read-only
    STATUS       current
    DESCRIPTION
        "Cisco Firepower equipment:ChassisStatsHist:id
        managed object property"
    ::= { cfprApEquipmentChassisStatsHistEntry 4 }

cfprApEquipmentChassisStatsHistMostRecent OBJECT-TYPE
    SYNTAX       TruthValue
    MAX-ACCESS   read-only
    STATUS       current
    DESCRIPTION
        "Cisco Firepower equipment:ChassisStatsHist:mostRecent
        managed object property"
    ::= { cfprApEquipmentChassisStatsHistEntry 17 }

cfprApEquipmentChassisStatsHistOutletTemp1 OBJECT-TYPE
    SYNTAX       INTEGER
    MAX-ACCESS   read-only
    STATUS       current
    DESCRIPTION
        "Cisco Firepower equipment:ChassisStatsHist:outletTemp1
        managed object property"
    ::= { cfprApEquipmentChassisStatsHistEntry 18 }

cfprApEquipmentChassisStatsHistOutletTemp1Avg OBJECT-TYPE
    SYNTAX       INTEGER
    MAX-ACCESS   read-only
    STATUS       current
    DESCRIPTION
        "Cisco Firepower equipment:ChassisStatsHist:outletTemp1Avg
        managed object property"
    ::= { cfprApEquipmentChassisStatsHistEntry 19 }

cfprApEquipmentChassisStatsHistOutletTemp1Max OBJECT-TYPE
    SYNTAX       INTEGER
    MAX-ACCESS   read-only
    STATUS       current
    DESCRIPTION
        "Cisco Firepower equipment:ChassisStatsHist:outletTemp1Max
        managed object property"
    ::= { cfprApEquipmentChassisStatsHistEntry 20 }

cfprApEquipmentChassisStatsHistOutletTemp1Min OBJECT-TYPE
    SYNTAX       INTEGER
    MAX-ACCESS   read-only
    STATUS       current
    DESCRIPTION
        "Cisco Firepower equipment:ChassisStatsHist:outletTemp1Min
        managed object property"
    ::= { cfprApEquipmentChassisStatsHistEntry 21 }

cfprApEquipmentChassisStatsHistOutletTemp2 OBJECT-TYPE
    SYNTAX       INTEGER
    MAX-ACCESS   read-only
    STATUS       current
    DESCRIPTION
        "Cisco Firepower equipment:ChassisStatsHist:outletTemp2
        managed object property"
    ::= { cfprApEquipmentChassisStatsHistEntry 22 }

cfprApEquipmentChassisStatsHistOutletTemp2Avg OBJECT-TYPE
    SYNTAX       INTEGER
    MAX-ACCESS   read-only
    STATUS       current
    DESCRIPTION
        "Cisco Firepower equipment:ChassisStatsHist:outletTemp2Avg
        managed object property"
    ::= { cfprApEquipmentChassisStatsHistEntry 23 }

cfprApEquipmentChassisStatsHistOutletTemp2Max OBJECT-TYPE
    SYNTAX       INTEGER
    MAX-ACCESS   read-only
    STATUS       current
    DESCRIPTION
        "Cisco Firepower equipment:ChassisStatsHist:outletTemp2Max
        managed object property"
    ::= { cfprApEquipmentChassisStatsHistEntry 24 }

cfprApEquipmentChassisStatsHistOutletTemp2Min OBJECT-TYPE
    SYNTAX       INTEGER
    MAX-ACCESS   read-only
    STATUS       current
    DESCRIPTION
        "Cisco Firepower equipment:ChassisStatsHist:outletTemp2Min
        managed object property"
    ::= { cfprApEquipmentChassisStatsHistEntry 25 }

cfprApEquipmentChassisStatsHistSuspect OBJECT-TYPE
    SYNTAX       TruthValue
    MAX-ACCESS   read-only
    STATUS       current
    DESCRIPTION
        "Cisco Firepower equipment:ChassisStatsHist:suspect
        managed object property"
    ::= { cfprApEquipmentChassisStatsHistEntry 30 }

cfprApEquipmentChassisStatsHistThresholded OBJECT-TYPE
    SYNTAX       CfprApEquipmentChassisStatsHistThresholded
    MAX-ACCESS   read-only
    STATUS       current
    DESCRIPTION
        "Cisco Firepower equipment:ChassisStatsHist:thresholded
        managed object property"
    ::= { cfprApEquipmentChassisStatsHistEntry 31 }

cfprApEquipmentChassisStatsHistTimeCollected OBJECT-TYPE
    SYNTAX       DateAndTime
    MAX-ACCESS   read-only
    STATUS       current
    DESCRIPTION
        "Cisco Firepower equipment:ChassisStatsHist:timeCollected
        managed object property"
    ::= { cfprApEquipmentChassisStatsHistEntry 32 }

cfprApEquipmentCimcVmediaTable OBJECT-TYPE
    SYNTAX           SEQUENCE OF CfprApEquipmentCimcVmediaEntry
    MAX-ACCESS       not-accessible
    STATUS           current
    DESCRIPTION
        "Cisco Firepower equipment:CimcVmedia managed object table"
    ::= { cfprApEquipmentObjects 30 }

cfprApEquipmentCimcVmediaEntry OBJECT-TYPE
    SYNTAX           CfprApEquipmentCimcVmediaEntry
    MAX-ACCESS       not-accessible
    STATUS           current
    DESCRIPTION
        "Entry for the cfprApEquipmentCimcVmediaTable table."
    INDEX { cfprApEquipmentCimcVmediaInstanceId }
    ::= { cfprApEquipmentCimcVmediaTable 1 }

CfprApEquipmentCimcVmediaEntry ::= SEQUENCE {
    cfprApEquipmentCimcVmediaInstanceId                              CfprApManagedObjectId,
    cfprApEquipmentCimcVmediaDn                                      CfprApManagedObjectDn,
    cfprApEquipmentCimcVmediaRn                                      SnmpAdminString,
    cfprApEquipmentCimcVmediaDescr                                   SnmpAdminString,
    cfprApEquipmentCimcVmediaIntId                                   SnmpAdminString,
    cfprApEquipmentCimcVmediaIsSupported                             TruthValue,
    cfprApEquipmentCimcVmediaMinBiosVersion                          SnmpAdminString,
    cfprApEquipmentCimcVmediaMinCimcVersion                          SnmpAdminString,
    cfprApEquipmentCimcVmediaName                                    SnmpAdminString,
    cfprApEquipmentCimcVmediaPolicyLevel                             Gauge32,
    cfprApEquipmentCimcVmediaPolicyOwner                             CfprApPolicyPolicyOwner
}

cfprApEquipmentCimcVmediaInstanceId OBJECT-TYPE
    SYNTAX       CfprApManagedObjectId
    MAX-ACCESS   not-accessible
    STATUS       current
    DESCRIPTION
        "Instance identifier of the managed object."
    ::= { cfprApEquipmentCimcVmediaEntry 1 }

cfprApEquipmentCimcVmediaDn OBJECT-TYPE
    SYNTAX       CfprApManagedObjectDn
    MAX-ACCESS   read-only
    STATUS       current
    DESCRIPTION
        "Cisco Firepower equipment:CimcVmedia:dn managed object property"
    ::= { cfprApEquipmentCimcVmediaEntry 2 }

cfprApEquipmentCimcVmediaRn OBJECT-TYPE
    SYNTAX       SnmpAdminString
    MAX-ACCESS   read-only
    STATUS       current
    DESCRIPTION
        "Cisco Firepower equipment:CimcVmedia:rn managed object property"
    ::= { cfprApEquipmentCimcVmediaEntry 3 }

cfprApEquipmentCimcVmediaDescr OBJECT-TYPE
    SYNTAX       SnmpAdminString
    MAX-ACCESS   read-only
    STATUS       current
    DESCRIPTION
        "Cisco Firepower equipment:CimcVmedia:descr managed
        object property"
    ::= { cfprApEquipmentCimcVmediaEntry 4 }

cfprApEquipmentCimcVmediaIntId OBJECT-TYPE
    SYNTAX       SnmpAdminString
    MAX-ACCESS   read-only
    STATUS       current
    DESCRIPTION
        "Cisco Firepower equipment:CimcVmedia:intId managed
        object property"
    ::= { cfprApEquipmentCimcVmediaEntry 5 }

cfprApEquipmentCimcVmediaIsSupported OBJECT-TYPE
    SYNTAX       TruthValue
    MAX-ACCESS   read-only
    STATUS       current
    DESCRIPTION
        "Cisco Firepower equipment:CimcVmedia:isSupported
        managed object property"
    ::= { cfprApEquipmentCimcVmediaEntry 6 }

cfprApEquipmentCimcVmediaMinBiosVersion OBJECT-TYPE
    SYNTAX       SnmpAdminString
    MAX-ACCESS   read-only
    STATUS       current
    DESCRIPTION
        "Cisco Firepower equipment:CimcVmedia:minBiosVersion
        managed object property"
    ::= { cfprApEquipmentCimcVmediaEntry 7 }

cfprApEquipmentCimcVmediaMinCimcVersion OBJECT-TYPE
    SYNTAX       SnmpAdminString
    MAX-ACCESS   read-only
    STATUS       current
    DESCRIPTION
        "Cisco Firepower equipment:CimcVmedia:minCimcVersion
        managed object property"
    ::= { cfprApEquipmentCimcVmediaEntry 8 }

cfprApEquipmentCimcVmediaName OBJECT-TYPE
    SYNTAX       SnmpAdminString
    MAX-ACCESS   read-only
    STATUS       current
    DESCRIPTION
        "Cisco Firepower equipment:CimcVmedia:name managed
        object property"
    ::= { cfprApEquipmentCimcVmediaEntry 9 }

cfprApEquipmentCimcVmediaPolicyLevel OBJECT-TYPE
    SYNTAX       Gauge32
    MAX-ACCESS   read-only
    STATUS       current
    DESCRIPTION
        "Cisco Firepower equipment:CimcVmedia:policyLevel
        managed object property"
    ::= { cfprApEquipmentCimcVmediaEntry 10 }

cfprApEquipmentCimcVmediaPolicyOwner OBJECT-TYPE
    SYNTAX       CfprApPolicyPolicyOwner
    MAX-ACCESS   read-only
    STATUS       current
    DESCRIPTION
        "Cisco Firepower equipment:CimcVmedia:policyOwner
        managed object property"
    ::= { cfprApEquipmentCimcVmediaEntry 11 }

cfprApEquipmentDbgPluginCapProviderTable OBJECT-TYPE
    SYNTAX           SEQUENCE OF CfprApEquipmentDbgPluginCapProviderEntry
    MAX-ACCESS       not-accessible
    STATUS           current
    DESCRIPTION
        "Cisco Firepower equipment:DbgPluginCapProvider
        managed object table"
    ::= { cfprApEquipmentObjects 31 }

cfprApEquipmentDbgPluginCapProviderEntry OBJECT-TYPE
    SYNTAX           CfprApEquipmentDbgPluginCapProviderEntry
    MAX-ACCESS       not-accessible
    STATUS           current
    DESCRIPTION
        "Entry for the cfprApEquipmentDbgPluginCapProviderTable table."
    INDEX { cfprApEquipmentDbgPluginCapProviderInstanceId }
    ::= { cfprApEquipmentDbgPluginCapProviderTable 1 }

CfprApEquipmentDbgPluginCapProviderEntry ::= SEQUENCE {
    cfprApEquipmentDbgPluginCapProviderInstanceId                    CfprApManagedObjectId,
    cfprApEquipmentDbgPluginCapProviderDn                            CfprApManagedObjectDn,
    cfprApEquipmentDbgPluginCapProviderRn                            SnmpAdminString,
    cfprApEquipmentDbgPluginCapProviderDeleted                       TruthValue,
    cfprApEquipmentDbgPluginCapProviderDeprecated                    TruthValue,
    cfprApEquipmentDbgPluginCapProviderElementLoadFailures           Gauge32,
    cfprApEquipmentDbgPluginCapProviderElementsLoaded                Gauge32,
    cfprApEquipmentDbgPluginCapProviderGencount                      Gauge32,
    cfprApEquipmentDbgPluginCapProviderLoadErrors                    Gauge32,
    cfprApEquipmentDbgPluginCapProviderLoadWarnings                  Gauge32,
    cfprApEquipmentDbgPluginCapProviderMgmtPlaneVer                  SnmpAdminString,
    cfprApEquipmentDbgPluginCapProviderModel                         SnmpAdminString,
    cfprApEquipmentDbgPluginCapProviderPromCardType                  Gauge32,
    cfprApEquipmentDbgPluginCapProviderRevision                      SnmpAdminString,
    cfprApEquipmentDbgPluginCapProviderVendor                        SnmpAdminString
}

cfprApEquipmentDbgPluginCapProviderInstanceId OBJECT-TYPE
    SYNTAX       CfprApManagedObjectId
    MAX-ACCESS   not-accessible
    STATUS       current
    DESCRIPTION
        "Instance identifier of the managed object."
    ::= { cfprApEquipmentDbgPluginCapProviderEntry 1 }

cfprApEquipmentDbgPluginCapProviderDn OBJECT-TYPE
    SYNTAX       CfprApManagedObjectDn
    MAX-ACCESS   read-only
    STATUS       current
    DESCRIPTION
        "Cisco Firepower equipment:DbgPluginCapProvider:dn
        managed object property"
    ::= { cfprApEquipmentDbgPluginCapProviderEntry 2 }

cfprApEquipmentDbgPluginCapProviderRn OBJECT-TYPE
    SYNTAX       SnmpAdminString
    MAX-ACCESS   read-only
    STATUS       current
    DESCRIPTION
        "Cisco Firepower equipment:DbgPluginCapProvider:rn
        managed object property"
    ::= { cfprApEquipmentDbgPluginCapProviderEntry 3 }

cfprApEquipmentDbgPluginCapProviderDeleted OBJECT-TYPE
    SYNTAX       TruthValue
    MAX-ACCESS   read-only
    STATUS       current
    DESCRIPTION
        "Cisco Firepower equipment:DbgPluginCapProvider:deleted
        managed object property"
    ::= { cfprApEquipmentDbgPluginCapProviderEntry 4 }

cfprApEquipmentDbgPluginCapProviderDeprecated OBJECT-TYPE
    SYNTAX       TruthValue
    MAX-ACCESS   read-only
    STATUS       current
    DESCRIPTION
        "Cisco Firepower equipment:DbgPluginCapProvider:deprecated
        managed object property"
    ::= { cfprApEquipmentDbgPluginCapProviderEntry 5 }

cfprApEquipmentDbgPluginCapProviderElementLoadFailures OBJECT-TYPE
    SYNTAX       Gauge32
    MAX-ACCESS   read-only
    STATUS       current
    DESCRIPTION
        "Cisco Firepower equipment:DbgPluginCapProvider:elementLoadFailure
        s managed object property"
    ::= { cfprApEquipmentDbgPluginCapProviderEntry 6 }

cfprApEquipmentDbgPluginCapProviderElementsLoaded OBJECT-TYPE
    SYNTAX       Gauge32
    MAX-ACCESS   read-only
    STATUS       current
    DESCRIPTION
        "Cisco Firepower equipment:DbgPluginCapProvider:elementsLoaded
        managed object property"
    ::= { cfprApEquipmentDbgPluginCapProviderEntry 7 }

cfprApEquipmentDbgPluginCapProviderGencount OBJECT-TYPE
    SYNTAX       Gauge32
    MAX-ACCESS   read-only
    STATUS       current
    DESCRIPTION
        "Cisco Firepower equipment:DbgPluginCapProvider:gencount
        managed object property"
    ::= { cfprApEquipmentDbgPluginCapProviderEntry 8 }

cfprApEquipmentDbgPluginCapProviderLoadErrors OBJECT-TYPE
    SYNTAX       Gauge32
    MAX-ACCESS   read-only
    STATUS       current
    DESCRIPTION
        "Cisco Firepower equipment:DbgPluginCapProvider:loadErrors
        managed object property"
    ::= { cfprApEquipmentDbgPluginCapProviderEntry 9 }

cfprApEquipmentDbgPluginCapProviderLoadWarnings OBJECT-TYPE
    SYNTAX       Gauge32
    MAX-ACCESS   read-only
    STATUS       current
    DESCRIPTION
        "Cisco Firepower equipment:DbgPluginCapProvider:loadWarnings
        managed object property"
    ::= { cfprApEquipmentDbgPluginCapProviderEntry 10 }

cfprApEquipmentDbgPluginCapProviderMgmtPlaneVer OBJECT-TYPE
    SYNTAX       SnmpAdminString
    MAX-ACCESS   read-only
    STATUS       current
    DESCRIPTION
        "Cisco Firepower equipment:DbgPluginCapProvider:mgmtPlaneVer
        managed object property"
    ::= { cfprApEquipmentDbgPluginCapProviderEntry 11 }

cfprApEquipmentDbgPluginCapProviderModel OBJECT-TYPE
    SYNTAX       SnmpAdminString
    MAX-ACCESS   read-only
    STATUS       current
    DESCRIPTION
        "Cisco Firepower equipment:DbgPluginCapProvider:model
        managed object property"
    ::= { cfprApEquipmentDbgPluginCapProviderEntry 12 }

cfprApEquipmentDbgPluginCapProviderPromCardType OBJECT-TYPE
    SYNTAX       Gauge32
    MAX-ACCESS   read-only
    STATUS       current
    DESCRIPTION
        "Cisco Firepower equipment:DbgPluginCapProvider:promCardType
        managed object property"
    ::= { cfprApEquipmentDbgPluginCapProviderEntry 13 }

cfprApEquipmentDbgPluginCapProviderRevision OBJECT-TYPE
    SYNTAX       SnmpAdminString
    MAX-ACCESS   read-only
    STATUS       current
    DESCRIPTION
        "Cisco Firepower equipment:DbgPluginCapProvider:revision
        managed object property"
    ::= { cfprApEquipmentDbgPluginCapProviderEntry 14 }

cfprApEquipmentDbgPluginCapProviderVendor OBJECT-TYPE
    SYNTAX       SnmpAdminString
    MAX-ACCESS   read-only
    STATUS       current
    DESCRIPTION
        "Cisco Firepower equipment:DbgPluginCapProvider:vendor
        managed object property"
    ::= { cfprApEquipmentDbgPluginCapProviderEntry 15 }

cfprApEquipmentDimmEntryTable OBJECT-TYPE
    SYNTAX           SEQUENCE OF CfprApEquipmentDimmEntryEntry
    MAX-ACCESS       not-accessible
    STATUS           current
    DESCRIPTION
        "Cisco Firepower equipment:DimmEntry managed object table"
    ::= { cfprApEquipmentObjects 32 }

cfprApEquipmentDimmEntryEntry OBJECT-TYPE
    SYNTAX           CfprApEquipmentDimmEntryEntry
    MAX-ACCESS       not-accessible
    STATUS           current
    DESCRIPTION
        "Entry for the cfprApEquipmentDimmEntryTable table."
    INDEX { cfprApEquipmentDimmEntryInstanceId }
    ::= { cfprApEquipmentDimmEntryTable 1 }

CfprApEquipmentDimmEntryEntry ::= SEQUENCE {
    cfprApEquipmentDimmEntryInstanceId                               CfprApManagedObjectId,
    cfprApEquipmentDimmEntryDn                                       CfprApManagedObjectDn,
    cfprApEquipmentDimmEntryRn                                       SnmpAdminString,
    cfprApEquipmentDimmEntryId                                       Gauge32,
    cfprApEquipmentDimmEntrySmbiosname                               SnmpAdminString
}

cfprApEquipmentDimmEntryInstanceId OBJECT-TYPE
    SYNTAX       CfprApManagedObjectId
    MAX-ACCESS   not-accessible
    STATUS       current
    DESCRIPTION
        "Instance identifier of the managed object."
    ::= { cfprApEquipmentDimmEntryEntry 1 }

cfprApEquipmentDimmEntryDn OBJECT-TYPE
    SYNTAX       CfprApManagedObjectDn
    MAX-ACCESS   read-only
    STATUS       current
    DESCRIPTION
        "Cisco Firepower equipment:DimmEntry:dn managed object property"
    ::= { cfprApEquipmentDimmEntryEntry 2 }

cfprApEquipmentDimmEntryRn OBJECT-TYPE
    SYNTAX       SnmpAdminString
    MAX-ACCESS   read-only
    STATUS       current
    DESCRIPTION
        "Cisco Firepower equipment:DimmEntry:rn managed object property"
    ::= { cfprApEquipmentDimmEntryEntry 3 }

cfprApEquipmentDimmEntryId OBJECT-TYPE
    SYNTAX       Gauge32
    MAX-ACCESS   read-only
    STATUS       current
    DESCRIPTION
        "Cisco Firepower equipment:DimmEntry:id managed object property"
    ::= { cfprApEquipmentDimmEntryEntry 4 }

cfprApEquipmentDimmEntrySmbiosname OBJECT-TYPE
    SYNTAX       SnmpAdminString
    MAX-ACCESS   read-only
    STATUS       current
    DESCRIPTION
        "Cisco Firepower equipment:DimmEntry:smbiosname
        managed object property"
    ::= { cfprApEquipmentDimmEntryEntry 5 }

cfprApEquipmentDimmMappingTable OBJECT-TYPE
    SYNTAX           SEQUENCE OF CfprApEquipmentDimmMappingEntry
    MAX-ACCESS       not-accessible
    STATUS           current
    DESCRIPTION
        "Cisco Firepower equipment:DimmMapping managed object table"
    ::= { cfprApEquipmentObjects 33 }

cfprApEquipmentDimmMappingEntry OBJECT-TYPE
    SYNTAX           CfprApEquipmentDimmMappingEntry
    MAX-ACCESS       not-accessible
    STATUS           current
    DESCRIPTION
        "Entry for the cfprApEquipmentDimmMappingTable table."
    INDEX { cfprApEquipmentDimmMappingInstanceId }
    ::= { cfprApEquipmentDimmMappingTable 1 }

CfprApEquipmentDimmMappingEntry ::= SEQUENCE {
    cfprApEquipmentDimmMappingInstanceId                             CfprApManagedObjectId,
    cfprApEquipmentDimmMappingDn                                     CfprApManagedObjectDn,
    cfprApEquipmentDimmMappingRn                                     SnmpAdminString,
    cfprApEquipmentDimmMappingDescr                                  SnmpAdminString,
    cfprApEquipmentDimmMappingIntId                                  SnmpAdminString,
    cfprApEquipmentDimmMappingName                                   SnmpAdminString,
    cfprApEquipmentDimmMappingPolicyLevel                            Gauge32,
    cfprApEquipmentDimmMappingPolicyOwner                            CfprApPolicyPolicyOwner
}

cfprApEquipmentDimmMappingInstanceId OBJECT-TYPE
    SYNTAX       CfprApManagedObjectId
    MAX-ACCESS   not-accessible
    STATUS       current
    DESCRIPTION
        "Instance identifier of the managed object."
    ::= { cfprApEquipmentDimmMappingEntry 1 }

cfprApEquipmentDimmMappingDn OBJECT-TYPE
    SYNTAX       CfprApManagedObjectDn
    MAX-ACCESS   read-only
    STATUS       current
    DESCRIPTION
        "Cisco Firepower equipment:DimmMapping:dn managed object property"
    ::= { cfprApEquipmentDimmMappingEntry 2 }

cfprApEquipmentDimmMappingRn OBJECT-TYPE
    SYNTAX       SnmpAdminString
    MAX-ACCESS   read-only
    STATUS       current
    DESCRIPTION
        "Cisco Firepower equipment:DimmMapping:rn managed object property"
    ::= { cfprApEquipmentDimmMappingEntry 3 }

cfprApEquipmentDimmMappingDescr OBJECT-TYPE
    SYNTAX       SnmpAdminString
    MAX-ACCESS   read-only
    STATUS       current
    DESCRIPTION
        "Cisco Firepower equipment:DimmMapping:descr managed
        object property"
    ::= { cfprApEquipmentDimmMappingEntry 4 }

cfprApEquipmentDimmMappingIntId OBJECT-TYPE
    SYNTAX       SnmpAdminString
    MAX-ACCESS   read-only
    STATUS       current
    DESCRIPTION
        "Cisco Firepower equipment:DimmMapping:intId managed
        object property"
    ::= { cfprApEquipmentDimmMappingEntry 5 }

cfprApEquipmentDimmMappingName OBJECT-TYPE
    SYNTAX       SnmpAdminString
    MAX-ACCESS   read-only
    STATUS       current
    DESCRIPTION
        "Cisco Firepower equipment:DimmMapping:name managed
        object property"
    ::= { cfprApEquipmentDimmMappingEntry 6 }

cfprApEquipmentDimmMappingPolicyLevel OBJECT-TYPE
    SYNTAX       Gauge32
    MAX-ACCESS   read-only
    STATUS       current
    DESCRIPTION
        "Cisco Firepower equipment:DimmMapping:policyLevel
        managed object property"
    ::= { cfprApEquipmentDimmMappingEntry 7 }

cfprApEquipmentDimmMappingPolicyOwner OBJECT-TYPE
    SYNTAX       CfprApPolicyPolicyOwner
    MAX-ACCESS   read-only
    STATUS       current
    DESCRIPTION
        "Cisco Firepower equipment:DimmMapping:policyOwner
        managed object property"
    ::= { cfprApEquipmentDimmMappingEntry 8 }

cfprApEquipmentDiscoveryCapTable OBJECT-TYPE
    SYNTAX           SEQUENCE OF CfprApEquipmentDiscoveryCapEntry
    MAX-ACCESS       not-accessible
    STATUS           current
    DESCRIPTION
        "Cisco Firepower equipment:DiscoveryCap managed object table"
    ::= { cfprApEquipmentObjects 34 }

cfprApEquipmentDiscoveryCapEntry OBJECT-TYPE
    SYNTAX           CfprApEquipmentDiscoveryCapEntry
    MAX-ACCESS       not-accessible
    STATUS           current
    DESCRIPTION
        "Entry for the cfprApEquipmentDiscoveryCapTable table."
    INDEX { cfprApEquipmentDiscoveryCapInstanceId }
    ::= { cfprApEquipmentDiscoveryCapTable 1 }

CfprApEquipmentDiscoveryCapEntry ::= SEQUENCE {
    cfprApEquipmentDiscoveryCapInstanceId                            CfprApManagedObjectId,
    cfprApEquipmentDiscoveryCapDn                                    CfprApManagedObjectDn,
    cfprApEquipmentDiscoveryCapRn                                    SnmpAdminString,
    cfprApEquipmentDiscoveryCapOperPowerRequirement                  CfprApEquipmentDiscoveryCapOperPowerRequirement
}

cfprApEquipmentDiscoveryCapInstanceId OBJECT-TYPE
    SYNTAX       CfprApManagedObjectId
    MAX-ACCESS   not-accessible
    STATUS       current
    DESCRIPTION
        "Instance identifier of the managed object."
    ::= { cfprApEquipmentDiscoveryCapEntry 1 }

cfprApEquipmentDiscoveryCapDn OBJECT-TYPE
    SYNTAX       CfprApManagedObjectDn
    MAX-ACCESS   read-only
    STATUS       current
    DESCRIPTION
        "Cisco Firepower equipment:DiscoveryCap:dn managed
        object property"
    ::= { cfprApEquipmentDiscoveryCapEntry 2 }

cfprApEquipmentDiscoveryCapRn OBJECT-TYPE
    SYNTAX       SnmpAdminString
    MAX-ACCESS   read-only
    STATUS       current
    DESCRIPTION
        "Cisco Firepower equipment:DiscoveryCap:rn managed
        object property"
    ::= { cfprApEquipmentDiscoveryCapEntry 3 }

cfprApEquipmentDiscoveryCapOperPowerRequirement OBJECT-TYPE
    SYNTAX       CfprApEquipmentDiscoveryCapOperPowerRequirement
    MAX-ACCESS   read-only
    STATUS       current
    DESCRIPTION
        "Cisco Firepower equipment:DiscoveryCap:operPowerRequirement
        managed object property"
    ::= { cfprApEquipmentDiscoveryCapEntry 4 }

cfprApEquipmentDowngradeConstraintTable OBJECT-TYPE
    SYNTAX           SEQUENCE OF CfprApEquipmentDowngradeConstraintEntry
    MAX-ACCESS       not-accessible
    STATUS           current
    DESCRIPTION
        "Cisco Firepower equipment:DowngradeConstraint
        managed object table"
    ::= { cfprApEquipmentObjects 35 }

cfprApEquipmentDowngradeConstraintEntry OBJECT-TYPE
    SYNTAX           CfprApEquipmentDowngradeConstraintEntry
    MAX-ACCESS       not-accessible
    STATUS           current
    DESCRIPTION
        "Entry for the cfprApEquipmentDowngradeConstraintTable table."
    INDEX { cfprApEquipmentDowngradeConstraintInstanceId }
    ::= { cfprApEquipmentDowngradeConstraintTable 1 }

CfprApEquipmentDowngradeConstraintEntry ::= SEQUENCE {
    cfprApEquipmentDowngradeConstraintInstanceId                     CfprApManagedObjectId,
    cfprApEquipmentDowngradeConstraintDn                             CfprApManagedObjectDn,
    cfprApEquipmentDowngradeConstraintRn                             SnmpAdminString,
    cfprApEquipmentDowngradeConstraintMinVer                         SnmpAdminString
}

cfprApEquipmentDowngradeConstraintInstanceId OBJECT-TYPE
    SYNTAX       CfprApManagedObjectId
    MAX-ACCESS   not-accessible
    STATUS       current
    DESCRIPTION
        "Instance identifier of the managed object."
    ::= { cfprApEquipmentDowngradeConstraintEntry 1 }

cfprApEquipmentDowngradeConstraintDn OBJECT-TYPE
    SYNTAX       CfprApManagedObjectDn
    MAX-ACCESS   read-only
    STATUS       current
    DESCRIPTION
        "Cisco Firepower equipment:DowngradeConstraint:dn
        managed object property"
    ::= { cfprApEquipmentDowngradeConstraintEntry 2 }

cfprApEquipmentDowngradeConstraintRn OBJECT-TYPE
    SYNTAX       SnmpAdminString
    MAX-ACCESS   read-only
    STATUS       current
    DESCRIPTION
        "Cisco Firepower equipment:DowngradeConstraint:rn
        managed object property"
    ::= { cfprApEquipmentDowngradeConstraintEntry 3 }

cfprApEquipmentDowngradeConstraintMinVer OBJECT-TYPE
    SYNTAX       SnmpAdminString
    MAX-ACCESS   read-only
    STATUS       current
    DESCRIPTION
        "Cisco Firepower equipment:DowngradeConstraint:minVer
        managed object property"
    ::= { cfprApEquipmentDowngradeConstraintEntry 4 }

cfprApEquipmentFailToWireCapProviderTable OBJECT-TYPE
    SYNTAX           SEQUENCE OF CfprApEquipmentFailToWireCapProviderEntry
    MAX-ACCESS       not-accessible
    STATUS           current
    DESCRIPTION
        "Cisco Firepower equipment:FailToWireCapProvider
        managed object table"
    ::= { cfprApEquipmentObjects 36 }

cfprApEquipmentFailToWireCapProviderEntry OBJECT-TYPE
    SYNTAX           CfprApEquipmentFailToWireCapProviderEntry
    MAX-ACCESS       not-accessible
    STATUS           current
    DESCRIPTION
        "Entry for the cfprApEquipmentFailToWireCapProviderTable table."
    INDEX { cfprApEquipmentFailToWireCapProviderInstanceId }
    ::= { cfprApEquipmentFailToWireCapProviderTable 1 }

CfprApEquipmentFailToWireCapProviderEntry ::= SEQUENCE {
    cfprApEquipmentFailToWireCapProviderInstanceId                   CfprApManagedObjectId,
    cfprApEquipmentFailToWireCapProviderDn                           CfprApManagedObjectDn,
    cfprApEquipmentFailToWireCapProviderRn                           SnmpAdminString,
    cfprApEquipmentFailToWireCapProviderDescr                        SnmpAdminString,
    cfprApEquipmentFailToWireCapProviderIntId                        SnmpAdminString,
    cfprApEquipmentFailToWireCapProviderName                         SnmpAdminString,
    cfprApEquipmentFailToWireCapProviderPolicyLevel                  Gauge32,
    cfprApEquipmentFailToWireCapProviderPolicyOwner                  CfprApPolicyPolicyOwner
}

cfprApEquipmentFailToWireCapProviderInstanceId OBJECT-TYPE
    SYNTAX       CfprApManagedObjectId
    MAX-ACCESS   not-accessible
    STATUS       current
    DESCRIPTION
        "Instance identifier of the managed object."
    ::= { cfprApEquipmentFailToWireCapProviderEntry 1 }

cfprApEquipmentFailToWireCapProviderDn OBJECT-TYPE
    SYNTAX       CfprApManagedObjectDn
    MAX-ACCESS   read-only
    STATUS       current
    DESCRIPTION
        "Cisco Firepower equipment:FailToWireCapProvider:dn
        managed object property"
    ::= { cfprApEquipmentFailToWireCapProviderEntry 2 }

cfprApEquipmentFailToWireCapProviderRn OBJECT-TYPE
    SYNTAX       SnmpAdminString
    MAX-ACCESS   read-only
    STATUS       current
    DESCRIPTION
        "Cisco Firepower equipment:FailToWireCapProvider:rn
        managed object property"
    ::= { cfprApEquipmentFailToWireCapProviderEntry 3 }

cfprApEquipmentFailToWireCapProviderDescr OBJECT-TYPE
    SYNTAX       SnmpAdminString
    MAX-ACCESS   read-only
    STATUS       current
    DESCRIPTION
        "Cisco Firepower equipment:FailToWireCapProvider:descr
        managed object property"
    ::= { cfprApEquipmentFailToWireCapProviderEntry 4 }

cfprApEquipmentFailToWireCapProviderIntId OBJECT-TYPE
    SYNTAX       SnmpAdminString
    MAX-ACCESS   read-only
    STATUS       current
    DESCRIPTION
        "Cisco Firepower equipment:FailToWireCapProvider:intId
        managed object property"
    ::= { cfprApEquipmentFailToWireCapProviderEntry 5 }

cfprApEquipmentFailToWireCapProviderName OBJECT-TYPE
    SYNTAX       SnmpAdminString
    MAX-ACCESS   read-only
    STATUS       current
    DESCRIPTION
        "Cisco Firepower equipment:FailToWireCapProvider:name
        managed object property"
    ::= { cfprApEquipmentFailToWireCapProviderEntry 6 }

cfprApEquipmentFailToWireCapProviderPolicyLevel OBJECT-TYPE
    SYNTAX       Gauge32
    MAX-ACCESS   read-only
    STATUS       current
    DESCRIPTION
        "Cisco Firepower equipment:FailToWireCapProvider:policyLevel
        managed object property"
    ::= { cfprApEquipmentFailToWireCapProviderEntry 7 }

cfprApEquipmentFailToWireCapProviderPolicyOwner OBJECT-TYPE
    SYNTAX       CfprApPolicyPolicyOwner
    MAX-ACCESS   read-only
    STATUS       current
    DESCRIPTION
        "Cisco Firepower equipment:FailToWireCapProvider:policyOwner
        managed object property"
    ::= { cfprApEquipmentFailToWireCapProviderEntry 8 }

cfprApEquipmentFailToWirePortDefTable OBJECT-TYPE
    SYNTAX           SEQUENCE OF CfprApEquipmentFailToWirePortDefEntry
    MAX-ACCESS       not-accessible
    STATUS           current
    DESCRIPTION
        "Cisco Firepower equipment:FailToWirePortDef managed object table"
    ::= { cfprApEquipmentObjects 37 }

cfprApEquipmentFailToWirePortDefEntry OBJECT-TYPE
    SYNTAX           CfprApEquipmentFailToWirePortDefEntry
    MAX-ACCESS       not-accessible
    STATUS           current
    DESCRIPTION
        "Entry for the cfprApEquipmentFailToWirePortDefTable table."
    INDEX { cfprApEquipmentFailToWirePortDefInstanceId }
    ::= { cfprApEquipmentFailToWirePortDefTable 1 }

CfprApEquipmentFailToWirePortDefEntry ::= SEQUENCE {
    cfprApEquipmentFailToWirePortDefInstanceId                       CfprApManagedObjectId,
    cfprApEquipmentFailToWirePortDefDn                               CfprApManagedObjectDn,
    cfprApEquipmentFailToWirePortDefRn                               SnmpAdminString,
    cfprApEquipmentFailToWirePortDefAggrId                           Gauge32,
    cfprApEquipmentFailToWirePortDefDescr                            SnmpAdminString,
    cfprApEquipmentFailToWirePortDefIntId                            SnmpAdminString,
    cfprApEquipmentFailToWirePortDefName                             SnmpAdminString,
    cfprApEquipmentFailToWirePortDefPolicyLevel                      Gauge32,
    cfprApEquipmentFailToWirePortDefPolicyOwner                      CfprApPolicyPolicyOwner,
    cfprApEquipmentFailToWirePortDefPortA                            Gauge32,
    cfprApEquipmentFailToWirePortDefPortB                            Gauge32
}

cfprApEquipmentFailToWirePortDefInstanceId OBJECT-TYPE
    SYNTAX       CfprApManagedObjectId
    MAX-ACCESS   not-accessible
    STATUS       current
    DESCRIPTION
        "Instance identifier of the managed object."
    ::= { cfprApEquipmentFailToWirePortDefEntry 1 }

cfprApEquipmentFailToWirePortDefDn OBJECT-TYPE
    SYNTAX       CfprApManagedObjectDn
    MAX-ACCESS   read-only
    STATUS       current
    DESCRIPTION
        "Cisco Firepower equipment:FailToWirePortDef:dn
        managed object property"
    ::= { cfprApEquipmentFailToWirePortDefEntry 2 }

cfprApEquipmentFailToWirePortDefRn OBJECT-TYPE
    SYNTAX       SnmpAdminString
    MAX-ACCESS   read-only
    STATUS       current
    DESCRIPTION
        "Cisco Firepower equipment:FailToWirePortDef:rn
        managed object property"
    ::= { cfprApEquipmentFailToWirePortDefEntry 3 }

cfprApEquipmentFailToWirePortDefAggrId OBJECT-TYPE
    SYNTAX       Gauge32
    MAX-ACCESS   read-only
    STATUS       current
    DESCRIPTION
        "Cisco Firepower equipment:FailToWirePortDef:aggrId
        managed object property"
    ::= { cfprApEquipmentFailToWirePortDefEntry 4 }

cfprApEquipmentFailToWirePortDefDescr OBJECT-TYPE
    SYNTAX       SnmpAdminString
    MAX-ACCESS   read-only
    STATUS       current
    DESCRIPTION
        "Cisco Firepower equipment:FailToWirePortDef:descr
        managed object property"
    ::= { cfprApEquipmentFailToWirePortDefEntry 5 }

cfprApEquipmentFailToWirePortDefIntId OBJECT-TYPE
    SYNTAX       SnmpAdminString
    MAX-ACCESS   read-only
    STATUS       current
    DESCRIPTION
        "Cisco Firepower equipment:FailToWirePortDef:intId
        managed object property"
    ::= { cfprApEquipmentFailToWirePortDefEntry 6 }

cfprApEquipmentFailToWirePortDefName OBJECT-TYPE
    SYNTAX       SnmpAdminString
    MAX-ACCESS   read-only
    STATUS       current
    DESCRIPTION
        "Cisco Firepower equipment:FailToWirePortDef:name
        managed object property"
    ::= { cfprApEquipmentFailToWirePortDefEntry 7 }

cfprApEquipmentFailToWirePortDefPolicyLevel OBJECT-TYPE
    SYNTAX       Gauge32
    MAX-ACCESS   read-only
    STATUS       current
    DESCRIPTION
        "Cisco Firepower equipment:FailToWirePortDef:policyLevel
        managed object property"
    ::= { cfprApEquipmentFailToWirePortDefEntry 8 }

cfprApEquipmentFailToWirePortDefPolicyOwner OBJECT-TYPE
    SYNTAX       CfprApPolicyPolicyOwner
    MAX-ACCESS   read-only
    STATUS       current
    DESCRIPTION
        "Cisco Firepower equipment:FailToWirePortDef:policyOwner
        managed object property"
    ::= { cfprApEquipmentFailToWirePortDefEntry 9 }

cfprApEquipmentFailToWirePortDefPortA OBJECT-TYPE
    SYNTAX       Gauge32
    MAX-ACCESS   read-only
    STATUS       current
    DESCRIPTION
        "Cisco Firepower equipment:FailToWirePortDef:portA
        managed object property"
    ::= { cfprApEquipmentFailToWirePortDefEntry 10 }

cfprApEquipmentFailToWirePortDefPortB OBJECT-TYPE
    SYNTAX       Gauge32
    MAX-ACCESS   read-only
    STATUS       current
    DESCRIPTION
        "Cisco Firepower equipment:FailToWirePortDef:portB
        managed object property"
    ::= { cfprApEquipmentFailToWirePortDefEntry 11 }

cfprApEquipmentFanTable OBJECT-TYPE
    SYNTAX           SEQUENCE OF CfprApEquipmentFanEntry
    MAX-ACCESS       not-accessible
    STATUS           current
    DESCRIPTION
        "Cisco Firepower equipment:Fan managed object table"
    ::= { cfprApEquipmentObjects 38 }

cfprApEquipmentFanEntry OBJECT-TYPE
    SYNTAX           CfprApEquipmentFanEntry
    MAX-ACCESS       not-accessible
    STATUS           current
    DESCRIPTION
        "Entry for the cfprApEquipmentFanTable table."
    INDEX { cfprApEquipmentFanInstanceId }
    ::= { cfprApEquipmentFanTable 1 }

CfprApEquipmentFanEntry ::= SEQUENCE {
    cfprApEquipmentFanInstanceId                                     CfprApManagedObjectId,
    cfprApEquipmentFanDn                                             CfprApManagedObjectDn,
    cfprApEquipmentFanRn                                             SnmpAdminString,
    cfprApEquipmentFanFltAggr                                        Unsigned64,
    cfprApEquipmentFanId                                             CfprApEquipmentFanId,
    cfprApEquipmentFanIntType                                        CfprApEquipmentInternalFanType,
    cfprApEquipmentFanModel                                          SnmpAdminString,
    cfprApEquipmentFanModule                                         CfprApEquipmentFanModule,
    cfprApEquipmentFanOperQualifierReason                            SnmpAdminString,
    cfprApEquipmentFanOperState                                      CfprApEquipmentOperability,
    cfprApEquipmentFanOperability                                    CfprApEquipmentOperability,
    cfprApEquipmentFanPerf                                           CfprApEquipmentSensorThresholdStatus,
    cfprApEquipmentFanPower                                          CfprApEquipmentPowerState,
    cfprApEquipmentFanPresence                                       CfprApEquipmentPresence,
    cfprApEquipmentFanRevision                                       SnmpAdminString,
    cfprApEquipmentFanSerial                                         SnmpAdminString,
    cfprApEquipmentFanThermal                                        CfprApEquipmentSensorThresholdStatus,
    cfprApEquipmentFanTray                                           CfprApEquipmentFanTray,
    cfprApEquipmentFanVendor                                         SnmpAdminString,
    cfprApEquipmentFanVoltage                                        CfprApEquipmentSensorThresholdStatus
}

cfprApEquipmentFanInstanceId OBJECT-TYPE
    SYNTAX       CfprApManagedObjectId
    MAX-ACCESS   not-accessible
    STATUS       current
    DESCRIPTION
        "Instance identifier of the managed object."
    ::= { cfprApEquipmentFanEntry 1 }

cfprApEquipmentFanDn OBJECT-TYPE
    SYNTAX       CfprApManagedObjectDn
    MAX-ACCESS   read-only
    STATUS       current
    DESCRIPTION
        "Cisco Firepower equipment:Fan:dn managed object property"
    ::= { cfprApEquipmentFanEntry 2 }

cfprApEquipmentFanRn OBJECT-TYPE
    SYNTAX       SnmpAdminString
    MAX-ACCESS   read-only
    STATUS       current
    DESCRIPTION
        "Cisco Firepower equipment:Fan:rn managed object property"
    ::= { cfprApEquipmentFanEntry 3 }

cfprApEquipmentFanFltAggr OBJECT-TYPE
    SYNTAX       Unsigned64
    MAX-ACCESS   read-only
    STATUS       current
    DESCRIPTION
        "Cisco Firepower equipment:Fan:fltAggr managed object property"
    ::= { cfprApEquipmentFanEntry 4 }

cfprApEquipmentFanId OBJECT-TYPE
    SYNTAX       CfprApEquipmentFanId
    MAX-ACCESS   read-only
    STATUS       current
    DESCRIPTION
        "Cisco Firepower equipment:Fan:id managed object property"
    ::= { cfprApEquipmentFanEntry 5 }

cfprApEquipmentFanIntType OBJECT-TYPE
    SYNTAX       CfprApEquipmentInternalFanType
    MAX-ACCESS   read-only
    STATUS       current
    DESCRIPTION
        "Cisco Firepower equipment:Fan:intType managed object property"
    ::= { cfprApEquipmentFanEntry 6 }

cfprApEquipmentFanModel OBJECT-TYPE
    SYNTAX       SnmpAdminString
    MAX-ACCESS   read-only
    STATUS       current
    DESCRIPTION
        "Cisco Firepower equipment:Fan:model managed object property"
    ::= { cfprApEquipmentFanEntry 7 }

cfprApEquipmentFanModule OBJECT-TYPE
    SYNTAX       CfprApEquipmentFanModule
    MAX-ACCESS   read-only
    STATUS       current
    DESCRIPTION
        "Cisco Firepower equipment:Fan:module managed object property"
    ::= { cfprApEquipmentFanEntry 8 }

cfprApEquipmentFanOperQualifierReason OBJECT-TYPE
    SYNTAX       SnmpAdminString
    MAX-ACCESS   read-only
    STATUS       current
    DESCRIPTION
        "Cisco Firepower equipment:Fan:operQualifierReason
        managed object property"
    ::= { cfprApEquipmentFanEntry 9 }

cfprApEquipmentFanOperState OBJECT-TYPE
    SYNTAX       CfprApEquipmentOperability
    MAX-ACCESS   read-only
    STATUS       current
    DESCRIPTION
        "Cisco Firepower equipment:Fan:operState managed object property"
    ::= { cfprApEquipmentFanEntry 10 }

cfprApEquipmentFanOperability OBJECT-TYPE
    SYNTAX       CfprApEquipmentOperability
    MAX-ACCESS   read-only
    STATUS       current
    DESCRIPTION
        "Cisco Firepower equipment:Fan:operability managed
        object property"
    ::= { cfprApEquipmentFanEntry 11 }

cfprApEquipmentFanPerf OBJECT-TYPE
    SYNTAX       CfprApEquipmentSensorThresholdStatus
    MAX-ACCESS   read-only
    STATUS       current
    DESCRIPTION
        "Cisco Firepower equipment:Fan:perf managed object property"
    ::= { cfprApEquipmentFanEntry 12 }

cfprApEquipmentFanPower OBJECT-TYPE
    SYNTAX       CfprApEquipmentPowerState
    MAX-ACCESS   read-only
    STATUS       current
    DESCRIPTION
        "Cisco Firepower equipment:Fan:power managed object property"
    ::= { cfprApEquipmentFanEntry 13 }

cfprApEquipmentFanPresence OBJECT-TYPE
    SYNTAX       CfprApEquipmentPresence
    MAX-ACCESS   read-only
    STATUS       current
    DESCRIPTION
        "Cisco Firepower equipment:Fan:presence managed object property"
    ::= { cfprApEquipmentFanEntry 14 }

cfprApEquipmentFanRevision OBJECT-TYPE
    SYNTAX       SnmpAdminString
    MAX-ACCESS   read-only
    STATUS       current
    DESCRIPTION
        "Cisco Firepower equipment:Fan:revision managed object property"
    ::= { cfprApEquipmentFanEntry 15 }

cfprApEquipmentFanSerial OBJECT-TYPE
    SYNTAX       SnmpAdminString
    MAX-ACCESS   read-only
    STATUS       current
    DESCRIPTION
        "Cisco Firepower equipment:Fan:serial managed object property"
    ::= { cfprApEquipmentFanEntry 16 }

cfprApEquipmentFanThermal OBJECT-TYPE
    SYNTAX       CfprApEquipmentSensorThresholdStatus
    MAX-ACCESS   read-only
    STATUS       current
    DESCRIPTION
        "Cisco Firepower equipment:Fan:thermal managed object property"
    ::= { cfprApEquipmentFanEntry 17 }

cfprApEquipmentFanTray OBJECT-TYPE
    SYNTAX       CfprApEquipmentFanTray
    MAX-ACCESS   read-only
    STATUS       current
    DESCRIPTION
        "Cisco Firepower equipment:Fan:tray managed object property"
    ::= { cfprApEquipmentFanEntry 18 }

cfprApEquipmentFanVendor OBJECT-TYPE
    SYNTAX       SnmpAdminString
    MAX-ACCESS   read-only
    STATUS       current
    DESCRIPTION
        "Cisco Firepower equipment:Fan:vendor managed object property"
    ::= { cfprApEquipmentFanEntry 19 }

cfprApEquipmentFanVoltage OBJECT-TYPE
    SYNTAX       CfprApEquipmentSensorThresholdStatus
    MAX-ACCESS   read-only
    STATUS       current
    DESCRIPTION
        "Cisco Firepower equipment:Fan:voltage managed object property"
    ::= { cfprApEquipmentFanEntry 20 }

cfprApEquipmentFanModuleTable OBJECT-TYPE
    SYNTAX           SEQUENCE OF CfprApEquipmentFanModuleEntry
    MAX-ACCESS       not-accessible
    STATUS           current
    DESCRIPTION
        "Cisco Firepower equipment:FanModule managed object table"
    ::= { cfprApEquipmentObjects 39 }

cfprApEquipmentFanModuleEntry OBJECT-TYPE
    SYNTAX           CfprApEquipmentFanModuleEntry
    MAX-ACCESS       not-accessible
    STATUS           current
    DESCRIPTION
        "Entry for the cfprApEquipmentFanModuleTable table."
    INDEX { cfprApEquipmentFanModuleInstanceId }
    ::= { cfprApEquipmentFanModuleTable 1 }

CfprApEquipmentFanModuleEntry ::= SEQUENCE {
    cfprApEquipmentFanModuleInstanceId                               CfprApManagedObjectId,
    cfprApEquipmentFanModuleDn                                       CfprApManagedObjectDn,
    cfprApEquipmentFanModuleRn                                       SnmpAdminString,
    cfprApEquipmentFanModuleFltAggr                                  Unsigned64,
    cfprApEquipmentFanModuleId                                       CfprApEquipmentFanModuleId,
    cfprApEquipmentFanModuleMfgTime                                  DateAndTime,
    cfprApEquipmentFanModuleModel                                    SnmpAdminString,
    cfprApEquipmentFanModuleOperQualifierReason                      SnmpAdminString,
    cfprApEquipmentFanModuleOperState                                CfprApEquipmentOperability,
    cfprApEquipmentFanModuleOperability                              CfprApEquipmentOperability,
    cfprApEquipmentFanModulePartNumber                               SnmpAdminString,
    cfprApEquipmentFanModulePerf                                     CfprApEquipmentSensorThresholdStatus,
    cfprApEquipmentFanModulePower                                    CfprApEquipmentPowerState,
    cfprApEquipmentFanModulePresence                                 CfprApEquipmentPresence,
    cfprApEquipmentFanModuleRevision                                 SnmpAdminString,
    cfprApEquipmentFanModuleSerial                                   SnmpAdminString,
    cfprApEquipmentFanModuleThermal                                  CfprApEquipmentSensorThresholdStatus,
    cfprApEquipmentFanModuleTray                                     CfprApEquipmentFanModuleTray,
    cfprApEquipmentFanModuleVendor                                   SnmpAdminString,
    cfprApEquipmentFanModuleVid                                      SnmpAdminString,
    cfprApEquipmentFanModuleVoltage                                  CfprApEquipmentSensorThresholdStatus
}

cfprApEquipmentFanModuleInstanceId OBJECT-TYPE
    SYNTAX       CfprApManagedObjectId
    MAX-ACCESS   not-accessible
    STATUS       current
    DESCRIPTION
        "Instance identifier of the managed object."
    ::= { cfprApEquipmentFanModuleEntry 1 }

cfprApEquipmentFanModuleDn OBJECT-TYPE
    SYNTAX       CfprApManagedObjectDn
    MAX-ACCESS   read-only
    STATUS       current
    DESCRIPTION
        "Cisco Firepower equipment:FanModule:dn managed object property"
    ::= { cfprApEquipmentFanModuleEntry 2 }

cfprApEquipmentFanModuleRn OBJECT-TYPE
    SYNTAX       SnmpAdminString
    MAX-ACCESS   read-only
    STATUS       current
    DESCRIPTION
        "Cisco Firepower equipment:FanModule:rn managed object property"
    ::= { cfprApEquipmentFanModuleEntry 3 }

cfprApEquipmentFanModuleFltAggr OBJECT-TYPE
    SYNTAX       Unsigned64
    MAX-ACCESS   read-only
    STATUS       current
    DESCRIPTION
        "Cisco Firepower equipment:FanModule:fltAggr managed
        object property"
    ::= { cfprApEquipmentFanModuleEntry 4 }

cfprApEquipmentFanModuleId OBJECT-TYPE
    SYNTAX       CfprApEquipmentFanModuleId
    MAX-ACCESS   read-only
    STATUS       current
    DESCRIPTION
        "Cisco Firepower equipment:FanModule:id managed object property"
    ::= { cfprApEquipmentFanModuleEntry 5 }

cfprApEquipmentFanModuleMfgTime OBJECT-TYPE
    SYNTAX       DateAndTime
    MAX-ACCESS   read-only
    STATUS       current
    DESCRIPTION
        "Cisco Firepower equipment:FanModule:mfgTime managed
        object property"
    ::= { cfprApEquipmentFanModuleEntry 6 }

cfprApEquipmentFanModuleModel OBJECT-TYPE
    SYNTAX       SnmpAdminString
    MAX-ACCESS   read-only
    STATUS       current
    DESCRIPTION
        "Cisco Firepower equipment:FanModule:model managed
        object property"
    ::= { cfprApEquipmentFanModuleEntry 7 }

cfprApEquipmentFanModuleOperQualifierReason OBJECT-TYPE
    SYNTAX       SnmpAdminString
    MAX-ACCESS   read-only
    STATUS       current
    DESCRIPTION
        "Cisco Firepower equipment:FanModule:operQualifierReason
        managed object property"
    ::= { cfprApEquipmentFanModuleEntry 8 }

cfprApEquipmentFanModuleOperState OBJECT-TYPE
    SYNTAX       CfprApEquipmentOperability
    MAX-ACCESS   read-only
    STATUS       current
    DESCRIPTION
        "Cisco Firepower equipment:FanModule:operState
        managed object property"
    ::= { cfprApEquipmentFanModuleEntry 9 }

cfprApEquipmentFanModuleOperability OBJECT-TYPE
    SYNTAX       CfprApEquipmentOperability
    MAX-ACCESS   read-only
    STATUS       current
    DESCRIPTION
        "Cisco Firepower equipment:FanModule:operability
        managed object property"
    ::= { cfprApEquipmentFanModuleEntry 10 }

cfprApEquipmentFanModulePartNumber OBJECT-TYPE
    SYNTAX       SnmpAdminString
    MAX-ACCESS   read-only
    STATUS       current
    DESCRIPTION
        "Cisco Firepower equipment:FanModule:partNumber
        managed object property"
    ::= { cfprApEquipmentFanModuleEntry 11 }

cfprApEquipmentFanModulePerf OBJECT-TYPE
    SYNTAX       CfprApEquipmentSensorThresholdStatus
    MAX-ACCESS   read-only
    STATUS       current
    DESCRIPTION
        "Cisco Firepower equipment:FanModule:perf managed object property"
    ::= { cfprApEquipmentFanModuleEntry 12 }

cfprApEquipmentFanModulePower OBJECT-TYPE
    SYNTAX       CfprApEquipmentPowerState
    MAX-ACCESS   read-only
    STATUS       current
    DESCRIPTION
        "Cisco Firepower equipment:FanModule:power managed
        object property"
    ::= { cfprApEquipmentFanModuleEntry 13 }

cfprApEquipmentFanModulePresence OBJECT-TYPE
    SYNTAX       CfprApEquipmentPresence
    MAX-ACCESS   read-only
    STATUS       current
    DESCRIPTION
        "Cisco Firepower equipment:FanModule:presence managed
        object property"
    ::= { cfprApEquipmentFanModuleEntry 14 }

cfprApEquipmentFanModuleRevision OBJECT-TYPE
    SYNTAX       SnmpAdminString
    MAX-ACCESS   read-only
    STATUS       current
    DESCRIPTION
        "Cisco Firepower equipment:FanModule:revision managed
        object property"
    ::= { cfprApEquipmentFanModuleEntry 15 }

cfprApEquipmentFanModuleSerial OBJECT-TYPE
    SYNTAX       SnmpAdminString
    MAX-ACCESS   read-only
    STATUS       current
    DESCRIPTION
        "Cisco Firepower equipment:FanModule:serial managed
        object property"
    ::= { cfprApEquipmentFanModuleEntry 16 }

cfprApEquipmentFanModuleThermal OBJECT-TYPE
    SYNTAX       CfprApEquipmentSensorThresholdStatus
    MAX-ACCESS   read-only
    STATUS       current
    DESCRIPTION
        "Cisco Firepower equipment:FanModule:thermal managed
        object property"
    ::= { cfprApEquipmentFanModuleEntry 17 }

cfprApEquipmentFanModuleTray OBJECT-TYPE
    SYNTAX       CfprApEquipmentFanModuleTray
    MAX-ACCESS   read-only
    STATUS       current
    DESCRIPTION
        "Cisco Firepower equipment:FanModule:tray managed object property"
    ::= { cfprApEquipmentFanModuleEntry 18 }

cfprApEquipmentFanModuleVendor OBJECT-TYPE
    SYNTAX       SnmpAdminString
    MAX-ACCESS   read-only
    STATUS       current
    DESCRIPTION
        "Cisco Firepower equipment:FanModule:vendor managed
        object property"
    ::= { cfprApEquipmentFanModuleEntry 19 }

cfprApEquipmentFanModuleVid OBJECT-TYPE
    SYNTAX       SnmpAdminString
    MAX-ACCESS   read-only
    STATUS       current
    DESCRIPTION
        "Cisco Firepower equipment:FanModule:vid managed object property"
    ::= { cfprApEquipmentFanModuleEntry 20 }

cfprApEquipmentFanModuleVoltage OBJECT-TYPE
    SYNTAX       CfprApEquipmentSensorThresholdStatus
    MAX-ACCESS   read-only
    STATUS       current
    DESCRIPTION
        "Cisco Firepower equipment:FanModule:voltage managed
        object property"
    ::= { cfprApEquipmentFanModuleEntry 21 }

cfprApEquipmentFanModuleCapProviderTable OBJECT-TYPE
    SYNTAX           SEQUENCE OF CfprApEquipmentFanModuleCapProviderEntry
    MAX-ACCESS       not-accessible
    STATUS           current
    DESCRIPTION
        "Cisco Firepower equipment:FanModuleCapProvider
        managed object table"
    ::= { cfprApEquipmentObjects 40 }

cfprApEquipmentFanModuleCapProviderEntry OBJECT-TYPE
    SYNTAX           CfprApEquipmentFanModuleCapProviderEntry
    MAX-ACCESS       not-accessible
    STATUS           current
    DESCRIPTION
        "Entry for the cfprApEquipmentFanModuleCapProviderTable table."
    INDEX { cfprApEquipmentFanModuleCapProviderInstanceId }
    ::= { cfprApEquipmentFanModuleCapProviderTable 1 }

CfprApEquipmentFanModuleCapProviderEntry ::= SEQUENCE {
    cfprApEquipmentFanModuleCapProviderInstanceId                    CfprApManagedObjectId,
    cfprApEquipmentFanModuleCapProviderDn                            CfprApManagedObjectDn,
    cfprApEquipmentFanModuleCapProviderRn                            SnmpAdminString,
    cfprApEquipmentFanModuleCapProviderDeleted                       TruthValue,
    cfprApEquipmentFanModuleCapProviderDeprecated                    TruthValue,
    cfprApEquipmentFanModuleCapProviderElementLoadFailures           Gauge32,
    cfprApEquipmentFanModuleCapProviderElementsLoaded                Gauge32,
    cfprApEquipmentFanModuleCapProviderGencount                      Gauge32,
    cfprApEquipmentFanModuleCapProviderLoadErrors                    Gauge32,
    cfprApEquipmentFanModuleCapProviderLoadWarnings                  Gauge32,
    cfprApEquipmentFanModuleCapProviderMgmtPlaneVer                  SnmpAdminString,
    cfprApEquipmentFanModuleCapProviderModel                         SnmpAdminString,
    cfprApEquipmentFanModuleCapProviderPromCardType                  Gauge32,
    cfprApEquipmentFanModuleCapProviderRevision                      SnmpAdminString,
    cfprApEquipmentFanModuleCapProviderVendor                        SnmpAdminString
}

cfprApEquipmentFanModuleCapProviderInstanceId OBJECT-TYPE
    SYNTAX       CfprApManagedObjectId
    MAX-ACCESS   not-accessible
    STATUS       current
    DESCRIPTION
        "Instance identifier of the managed object."
    ::= { cfprApEquipmentFanModuleCapProviderEntry 1 }

cfprApEquipmentFanModuleCapProviderDn OBJECT-TYPE
    SYNTAX       CfprApManagedObjectDn
    MAX-ACCESS   read-only
    STATUS       current
    DESCRIPTION
        "Cisco Firepower equipment:FanModuleCapProvider:dn
        managed object property"
    ::= { cfprApEquipmentFanModuleCapProviderEntry 2 }

cfprApEquipmentFanModuleCapProviderRn OBJECT-TYPE
    SYNTAX       SnmpAdminString
    MAX-ACCESS   read-only
    STATUS       current
    DESCRIPTION
        "Cisco Firepower equipment:FanModuleCapProvider:rn
        managed object property"
    ::= { cfprApEquipmentFanModuleCapProviderEntry 3 }

cfprApEquipmentFanModuleCapProviderDeleted OBJECT-TYPE
    SYNTAX       TruthValue
    MAX-ACCESS   read-only
    STATUS       current
    DESCRIPTION
        "Cisco Firepower equipment:FanModuleCapProvider:deleted
        managed object property"
    ::= { cfprApEquipmentFanModuleCapProviderEntry 4 }

cfprApEquipmentFanModuleCapProviderDeprecated OBJECT-TYPE
    SYNTAX       TruthValue
    MAX-ACCESS   read-only
    STATUS       current
    DESCRIPTION
        "Cisco Firepower equipment:FanModuleCapProvider:deprecated
        managed object property"
    ::= { cfprApEquipmentFanModuleCapProviderEntry 5 }

cfprApEquipmentFanModuleCapProviderElementLoadFailures OBJECT-TYPE
    SYNTAX       Gauge32
    MAX-ACCESS   read-only
    STATUS       current
    DESCRIPTION
        "Cisco Firepower equipment:FanModuleCapProvider:elementLoadFailure
        s managed object property"
    ::= { cfprApEquipmentFanModuleCapProviderEntry 6 }

cfprApEquipmentFanModuleCapProviderElementsLoaded OBJECT-TYPE
    SYNTAX       Gauge32
    MAX-ACCESS   read-only
    STATUS       current
    DESCRIPTION
        "Cisco Firepower equipment:FanModuleCapProvider:elementsLoaded
        managed object property"
    ::= { cfprApEquipmentFanModuleCapProviderEntry 7 }

cfprApEquipmentFanModuleCapProviderGencount OBJECT-TYPE
    SYNTAX       Gauge32
    MAX-ACCESS   read-only
    STATUS       current
    DESCRIPTION
        "Cisco Firepower equipment:FanModuleCapProvider:gencount
        managed object property"
    ::= { cfprApEquipmentFanModuleCapProviderEntry 8 }

cfprApEquipmentFanModuleCapProviderLoadErrors OBJECT-TYPE
    SYNTAX       Gauge32
    MAX-ACCESS   read-only
    STATUS       current
    DESCRIPTION
        "Cisco Firepower equipment:FanModuleCapProvider:loadErrors
        managed object property"
    ::= { cfprApEquipmentFanModuleCapProviderEntry 9 }

cfprApEquipmentFanModuleCapProviderLoadWarnings OBJECT-TYPE
    SYNTAX       Gauge32
    MAX-ACCESS   read-only
    STATUS       current
    DESCRIPTION
        "Cisco Firepower equipment:FanModuleCapProvider:loadWarnings
        managed object property"
    ::= { cfprApEquipmentFanModuleCapProviderEntry 10 }

cfprApEquipmentFanModuleCapProviderMgmtPlaneVer OBJECT-TYPE
    SYNTAX       SnmpAdminString
    MAX-ACCESS   read-only
    STATUS       current
    DESCRIPTION
        "Cisco Firepower equipment:FanModuleCapProvider:mgmtPlaneVer
        managed object property"
    ::= { cfprApEquipmentFanModuleCapProviderEntry 11 }

cfprApEquipmentFanModuleCapProviderModel OBJECT-TYPE
    SYNTAX       SnmpAdminString
    MAX-ACCESS   read-only
    STATUS       current
    DESCRIPTION
        "Cisco Firepower equipment:FanModuleCapProvider:model
        managed object property"
    ::= { cfprApEquipmentFanModuleCapProviderEntry 12 }

cfprApEquipmentFanModuleCapProviderPromCardType OBJECT-TYPE
    SYNTAX       Gauge32
    MAX-ACCESS   read-only
    STATUS       current
    DESCRIPTION
        "Cisco Firepower equipment:FanModuleCapProvider:promCardType
        managed object property"
    ::= { cfprApEquipmentFanModuleCapProviderEntry 13 }

cfprApEquipmentFanModuleCapProviderRevision OBJECT-TYPE
    SYNTAX       SnmpAdminString
    MAX-ACCESS   read-only
    STATUS       current
    DESCRIPTION
        "Cisco Firepower equipment:FanModuleCapProvider:revision
        managed object property"
    ::= { cfprApEquipmentFanModuleCapProviderEntry 14 }

cfprApEquipmentFanModuleCapProviderVendor OBJECT-TYPE
    SYNTAX       SnmpAdminString
    MAX-ACCESS   read-only
    STATUS       current
    DESCRIPTION
        "Cisco Firepower equipment:FanModuleCapProvider:vendor
        managed object property"
    ::= { cfprApEquipmentFanModuleCapProviderEntry 15 }

cfprApEquipmentFanModuleDefTable OBJECT-TYPE
    SYNTAX           SEQUENCE OF CfprApEquipmentFanModuleDefEntry
    MAX-ACCESS       not-accessible
    STATUS           current
    DESCRIPTION
        "Cisco Firepower equipment:FanModuleDef managed object table"
    ::= { cfprApEquipmentObjects 41 }

cfprApEquipmentFanModuleDefEntry OBJECT-TYPE
    SYNTAX           CfprApEquipmentFanModuleDefEntry
    MAX-ACCESS       not-accessible
    STATUS           current
    DESCRIPTION
        "Entry for the cfprApEquipmentFanModuleDefTable table."
    INDEX { cfprApEquipmentFanModuleDefInstanceId }
    ::= { cfprApEquipmentFanModuleDefTable 1 }

CfprApEquipmentFanModuleDefEntry ::= SEQUENCE {
    cfprApEquipmentFanModuleDefInstanceId                            CfprApManagedObjectId,
    cfprApEquipmentFanModuleDefDn                                    CfprApManagedObjectDn,
    cfprApEquipmentFanModuleDefRn                                    SnmpAdminString,
    cfprApEquipmentFanModuleDefDescr                                 SnmpAdminString,
    cfprApEquipmentFanModuleDefFanCapacity                           Gauge32,
    cfprApEquipmentFanModuleDefIntId                                 SnmpAdminString,
    cfprApEquipmentFanModuleDefName                                  SnmpAdminString,
    cfprApEquipmentFanModuleDefPolicyLevel                           Gauge32,
    cfprApEquipmentFanModuleDefPolicyOwner                           CfprApPolicyPolicyOwner
}

cfprApEquipmentFanModuleDefInstanceId OBJECT-TYPE
    SYNTAX       CfprApManagedObjectId
    MAX-ACCESS   not-accessible
    STATUS       current
    DESCRIPTION
        "Instance identifier of the managed object."
    ::= { cfprApEquipmentFanModuleDefEntry 1 }

cfprApEquipmentFanModuleDefDn OBJECT-TYPE
    SYNTAX       CfprApManagedObjectDn
    MAX-ACCESS   read-only
    STATUS       current
    DESCRIPTION
        "Cisco Firepower equipment:FanModuleDef:dn managed
        object property"
    ::= { cfprApEquipmentFanModuleDefEntry 2 }

cfprApEquipmentFanModuleDefRn OBJECT-TYPE
    SYNTAX       SnmpAdminString
    MAX-ACCESS   read-only
    STATUS       current
    DESCRIPTION
        "Cisco Firepower equipment:FanModuleDef:rn managed
        object property"
    ::= { cfprApEquipmentFanModuleDefEntry 3 }

cfprApEquipmentFanModuleDefDescr OBJECT-TYPE
    SYNTAX       SnmpAdminString
    MAX-ACCESS   read-only
    STATUS       current
    DESCRIPTION
        "Cisco Firepower equipment:FanModuleDef:descr managed
        object property"
    ::= { cfprApEquipmentFanModuleDefEntry 4 }

cfprApEquipmentFanModuleDefFanCapacity OBJECT-TYPE
    SYNTAX       Gauge32
    MAX-ACCESS   read-only
    STATUS       current
    DESCRIPTION
        "Cisco Firepower equipment:FanModuleDef:fanCapacity
        managed object property"
    ::= { cfprApEquipmentFanModuleDefEntry 5 }

cfprApEquipmentFanModuleDefIntId OBJECT-TYPE
    SYNTAX       SnmpAdminString
    MAX-ACCESS   read-only
    STATUS       current
    DESCRIPTION
        "Cisco Firepower equipment:FanModuleDef:intId managed
        object property"
    ::= { cfprApEquipmentFanModuleDefEntry 6 }

cfprApEquipmentFanModuleDefName OBJECT-TYPE
    SYNTAX       SnmpAdminString
    MAX-ACCESS   read-only
    STATUS       current
    DESCRIPTION
        "Cisco Firepower equipment:FanModuleDef:name managed
        object property"
    ::= { cfprApEquipmentFanModuleDefEntry 7 }

cfprApEquipmentFanModuleDefPolicyLevel OBJECT-TYPE
    SYNTAX       Gauge32
    MAX-ACCESS   read-only
    STATUS       current
    DESCRIPTION
        "Cisco Firepower equipment:FanModuleDef:policyLevel
        managed object property"
    ::= { cfprApEquipmentFanModuleDefEntry 8 }

cfprApEquipmentFanModuleDefPolicyOwner OBJECT-TYPE
    SYNTAX       CfprApPolicyPolicyOwner
    MAX-ACCESS   read-only
    STATUS       current
    DESCRIPTION
        "Cisco Firepower equipment:FanModuleDef:policyOwner
        managed object property"
    ::= { cfprApEquipmentFanModuleDefEntry 9 }

cfprApEquipmentFanModuleStatsTable OBJECT-TYPE
    SYNTAX           SEQUENCE OF CfprApEquipmentFanModuleStatsEntry
    MAX-ACCESS       not-accessible
    STATUS           current
    DESCRIPTION
        "Cisco Firepower equipment:FanModuleStats managed object table"
    ::= { cfprApEquipmentObjects 42 }

cfprApEquipmentFanModuleStatsEntry OBJECT-TYPE
    SYNTAX           CfprApEquipmentFanModuleStatsEntry
    MAX-ACCESS       not-accessible
    STATUS           current
    DESCRIPTION
        "Entry for the cfprApEquipmentFanModuleStatsTable table."
    INDEX { cfprApEquipmentFanModuleStatsInstanceId }
    ::= { cfprApEquipmentFanModuleStatsTable 1 }

CfprApEquipmentFanModuleStatsEntry ::= SEQUENCE {
    cfprApEquipmentFanModuleStatsInstanceId                          CfprApManagedObjectId,
    cfprApEquipmentFanModuleStatsDn                                  CfprApManagedObjectDn,
    cfprApEquipmentFanModuleStatsRn                                  SnmpAdminString,
    cfprApEquipmentFanModuleStatsAmbientTemp                         INTEGER,
    cfprApEquipmentFanModuleStatsAmbientTempAvg                      INTEGER,
    cfprApEquipmentFanModuleStatsAmbientTempMax                      INTEGER,
    cfprApEquipmentFanModuleStatsAmbientTempMin                      INTEGER,
    cfprApEquipmentFanModuleStatsIntervals                           Gauge32,
    cfprApEquipmentFanModuleStatsSuspect                             TruthValue,
    cfprApEquipmentFanModuleStatsThresholded                         CfprApEquipmentFanModuleStatsThresholded,
    cfprApEquipmentFanModuleStatsTimeCollected                       DateAndTime,
    cfprApEquipmentFanModuleStatsUpdate                              Gauge32
}

cfprApEquipmentFanModuleStatsInstanceId OBJECT-TYPE
    SYNTAX       CfprApManagedObjectId
    MAX-ACCESS   not-accessible
    STATUS       current
    DESCRIPTION
        "Instance identifier of the managed object."
    ::= { cfprApEquipmentFanModuleStatsEntry 1 }

cfprApEquipmentFanModuleStatsDn OBJECT-TYPE
    SYNTAX       CfprApManagedObjectDn
    MAX-ACCESS   read-only
    STATUS       current
    DESCRIPTION
        "Cisco Firepower equipment:FanModuleStats:dn managed
        object property"
    ::= { cfprApEquipmentFanModuleStatsEntry 2 }

cfprApEquipmentFanModuleStatsRn OBJECT-TYPE
    SYNTAX       SnmpAdminString
    MAX-ACCESS   read-only
    STATUS       current
    DESCRIPTION
        "Cisco Firepower equipment:FanModuleStats:rn managed
        object property"
    ::= { cfprApEquipmentFanModuleStatsEntry 3 }

cfprApEquipmentFanModuleStatsAmbientTemp OBJECT-TYPE
    SYNTAX       INTEGER
    MAX-ACCESS   read-only
    STATUS       current
    DESCRIPTION
        "Cisco Firepower equipment:FanModuleStats:ambientTemp
        managed object property"
    ::= { cfprApEquipmentFanModuleStatsEntry 4 }

cfprApEquipmentFanModuleStatsAmbientTempAvg OBJECT-TYPE
    SYNTAX       INTEGER
    MAX-ACCESS   read-only
    STATUS       current
    DESCRIPTION
        "Cisco Firepower equipment:FanModuleStats:ambientTempAvg
        managed object property"
    ::= { cfprApEquipmentFanModuleStatsEntry 5 }

cfprApEquipmentFanModuleStatsAmbientTempMax OBJECT-TYPE
    SYNTAX       INTEGER
    MAX-ACCESS   read-only
    STATUS       current
    DESCRIPTION
        "Cisco Firepower equipment:FanModuleStats:ambientTempMax
        managed object property"
    ::= { cfprApEquipmentFanModuleStatsEntry 6 }

cfprApEquipmentFanModuleStatsAmbientTempMin OBJECT-TYPE
    SYNTAX       INTEGER
    MAX-ACCESS   read-only
    STATUS       current
    DESCRIPTION
        "Cisco Firepower equipment:FanModuleStats:ambientTempMin
        managed object property"
    ::= { cfprApEquipmentFanModuleStatsEntry 7 }

cfprApEquipmentFanModuleStatsIntervals OBJECT-TYPE
    SYNTAX       Gauge32
    MAX-ACCESS   read-only
    STATUS       current
    DESCRIPTION
        "Cisco Firepower equipment:FanModuleStats:intervals
        managed object property"
    ::= { cfprApEquipmentFanModuleStatsEntry 8 }

cfprApEquipmentFanModuleStatsSuspect OBJECT-TYPE
    SYNTAX       TruthValue
    MAX-ACCESS   read-only
    STATUS       current
    DESCRIPTION
        "Cisco Firepower equipment:FanModuleStats:suspect
        managed object property"
    ::= { cfprApEquipmentFanModuleStatsEntry 9 }

cfprApEquipmentFanModuleStatsThresholded OBJECT-TYPE
    SYNTAX       CfprApEquipmentFanModuleStatsThresholded
    MAX-ACCESS   read-only
    STATUS       current
    DESCRIPTION
        "Cisco Firepower equipment:FanModuleStats:thresholded
        managed object property"
    ::= { cfprApEquipmentFanModuleStatsEntry 10 }

cfprApEquipmentFanModuleStatsTimeCollected OBJECT-TYPE
    SYNTAX       DateAndTime
    MAX-ACCESS   read-only
    STATUS       current
    DESCRIPTION
        "Cisco Firepower equipment:FanModuleStats:timeCollected
        managed object property"
    ::= { cfprApEquipmentFanModuleStatsEntry 11 }

cfprApEquipmentFanModuleStatsUpdate OBJECT-TYPE
    SYNTAX       Gauge32
    MAX-ACCESS   read-only
    STATUS       current
    DESCRIPTION
        "Cisco Firepower equipment:FanModuleStats:update
        managed object property"
    ::= { cfprApEquipmentFanModuleStatsEntry 12 }

cfprApEquipmentFanModuleStatsHistTable OBJECT-TYPE
    SYNTAX           SEQUENCE OF CfprApEquipmentFanModuleStatsHistEntry
    MAX-ACCESS       not-accessible
    STATUS           current
    DESCRIPTION
        "Cisco Firepower equipment:FanModuleStatsHist managed
        object table"
    ::= { cfprApEquipmentObjects 43 }

cfprApEquipmentFanModuleStatsHistEntry OBJECT-TYPE
    SYNTAX           CfprApEquipmentFanModuleStatsHistEntry
    MAX-ACCESS       not-accessible
    STATUS           current
    DESCRIPTION
        "Entry for the cfprApEquipmentFanModuleStatsHistTable table."
    INDEX { cfprApEquipmentFanModuleStatsHistInstanceId }
    ::= { cfprApEquipmentFanModuleStatsHistTable 1 }

CfprApEquipmentFanModuleStatsHistEntry ::= SEQUENCE {
    cfprApEquipmentFanModuleStatsHistInstanceId                      CfprApManagedObjectId,
    cfprApEquipmentFanModuleStatsHistDn                              CfprApManagedObjectDn,
    cfprApEquipmentFanModuleStatsHistRn                              SnmpAdminString,
    cfprApEquipmentFanModuleStatsHistAmbientTemp                     INTEGER,
    cfprApEquipmentFanModuleStatsHistAmbientTempAvg                  INTEGER,
    cfprApEquipmentFanModuleStatsHistAmbientTempMax                  INTEGER,
    cfprApEquipmentFanModuleStatsHistAmbientTempMin                  INTEGER,
    cfprApEquipmentFanModuleStatsHistId                              Unsigned64,
    cfprApEquipmentFanModuleStatsHistMostRecent                      TruthValue,
    cfprApEquipmentFanModuleStatsHistSuspect                         TruthValue,
    cfprApEquipmentFanModuleStatsHistThresholded                     CfprApEquipmentFanModuleStatsHistThresholded,
    cfprApEquipmentFanModuleStatsHistTimeCollected                   DateAndTime
}

cfprApEquipmentFanModuleStatsHistInstanceId OBJECT-TYPE
    SYNTAX       CfprApManagedObjectId
    MAX-ACCESS   not-accessible
    STATUS       current
    DESCRIPTION
        "Instance identifier of the managed object."
    ::= { cfprApEquipmentFanModuleStatsHistEntry 1 }

cfprApEquipmentFanModuleStatsHistDn OBJECT-TYPE
    SYNTAX       CfprApManagedObjectDn
    MAX-ACCESS   read-only
    STATUS       current
    DESCRIPTION
        "Cisco Firepower equipment:FanModuleStatsHist:dn
        managed object property"
    ::= { cfprApEquipmentFanModuleStatsHistEntry 2 }

cfprApEquipmentFanModuleStatsHistRn OBJECT-TYPE
    SYNTAX       SnmpAdminString
    MAX-ACCESS   read-only
    STATUS       current
    DESCRIPTION
        "Cisco Firepower equipment:FanModuleStatsHist:rn
        managed object property"
    ::= { cfprApEquipmentFanModuleStatsHistEntry 3 }

cfprApEquipmentFanModuleStatsHistAmbientTemp OBJECT-TYPE
    SYNTAX       INTEGER
    MAX-ACCESS   read-only
    STATUS       current
    DESCRIPTION
        "Cisco Firepower equipment:FanModuleStatsHist:ambientTemp
        managed object property"
    ::= { cfprApEquipmentFanModuleStatsHistEntry 4 }

cfprApEquipmentFanModuleStatsHistAmbientTempAvg OBJECT-TYPE
    SYNTAX       INTEGER
    MAX-ACCESS   read-only
    STATUS       current
    DESCRIPTION
        "Cisco Firepower equipment:FanModuleStatsHist:ambientTempAvg
        managed object property"
    ::= { cfprApEquipmentFanModuleStatsHistEntry 5 }

cfprApEquipmentFanModuleStatsHistAmbientTempMax OBJECT-TYPE
    SYNTAX       INTEGER
    MAX-ACCESS   read-only
    STATUS       current
    DESCRIPTION
        "Cisco Firepower equipment:FanModuleStatsHist:ambientTempMax
        managed object property"
    ::= { cfprApEquipmentFanModuleStatsHistEntry 6 }

cfprApEquipmentFanModuleStatsHistAmbientTempMin OBJECT-TYPE
    SYNTAX       INTEGER
    MAX-ACCESS   read-only
    STATUS       current
    DESCRIPTION
        "Cisco Firepower equipment:FanModuleStatsHist:ambientTempMin
        managed object property"
    ::= { cfprApEquipmentFanModuleStatsHistEntry 7 }

cfprApEquipmentFanModuleStatsHistId OBJECT-TYPE
    SYNTAX       Unsigned64
    MAX-ACCESS   read-only
    STATUS       current
    DESCRIPTION
        "Cisco Firepower equipment:FanModuleStatsHist:id
        managed object property"
    ::= { cfprApEquipmentFanModuleStatsHistEntry 8 }

cfprApEquipmentFanModuleStatsHistMostRecent OBJECT-TYPE
    SYNTAX       TruthValue
    MAX-ACCESS   read-only
    STATUS       current
    DESCRIPTION
        "Cisco Firepower equipment:FanModuleStatsHist:mostRecent
        managed object property"
    ::= { cfprApEquipmentFanModuleStatsHistEntry 9 }

cfprApEquipmentFanModuleStatsHistSuspect OBJECT-TYPE
    SYNTAX       TruthValue
    MAX-ACCESS   read-only
    STATUS       current
    DESCRIPTION
        "Cisco Firepower equipment:FanModuleStatsHist:suspect
        managed object property"
    ::= { cfprApEquipmentFanModuleStatsHistEntry 10 }

cfprApEquipmentFanModuleStatsHistThresholded OBJECT-TYPE
    SYNTAX       CfprApEquipmentFanModuleStatsHistThresholded
    MAX-ACCESS   read-only
    STATUS       current
    DESCRIPTION
        "Cisco Firepower equipment:FanModuleStatsHist:thresholded
        managed object property"
    ::= { cfprApEquipmentFanModuleStatsHistEntry 11 }

cfprApEquipmentFanModuleStatsHistTimeCollected OBJECT-TYPE
    SYNTAX       DateAndTime
    MAX-ACCESS   read-only
    STATUS       current
    DESCRIPTION
        "Cisco Firepower equipment:FanModuleStatsHist:timeCollected
        managed object property"
    ::= { cfprApEquipmentFanModuleStatsHistEntry 12 }

cfprApEquipmentFanStatsTable OBJECT-TYPE
    SYNTAX           SEQUENCE OF CfprApEquipmentFanStatsEntry
    MAX-ACCESS       not-accessible
    STATUS           current
    DESCRIPTION
        "Cisco Firepower equipment:FanStats managed object table"
    ::= { cfprApEquipmentObjects 44 }

cfprApEquipmentFanStatsEntry OBJECT-TYPE
    SYNTAX           CfprApEquipmentFanStatsEntry
    MAX-ACCESS       not-accessible
    STATUS           current
    DESCRIPTION
        "Entry for the cfprApEquipmentFanStatsTable table."
    INDEX { cfprApEquipmentFanStatsInstanceId }
    ::= { cfprApEquipmentFanStatsTable 1 }

CfprApEquipmentFanStatsEntry ::= SEQUENCE {
    cfprApEquipmentFanStatsInstanceId                                CfprApManagedObjectId,
    cfprApEquipmentFanStatsDn                                        CfprApManagedObjectDn,
    cfprApEquipmentFanStatsRn                                        SnmpAdminString,
    cfprApEquipmentFanStatsIntervals                                 Gauge32,
    cfprApEquipmentFanStatsSpeed                                     Gauge32,
    cfprApEquipmentFanStatsSpeedAvg                                  Gauge32,
    cfprApEquipmentFanStatsSpeedMax                                  Gauge32,
    cfprApEquipmentFanStatsSpeedMin                                  Gauge32,
    cfprApEquipmentFanStatsSuspect                                   TruthValue,
    cfprApEquipmentFanStatsThresholded                               CfprApEquipmentFanStatsThresholded,
    cfprApEquipmentFanStatsTimeCollected                             DateAndTime,
    cfprApEquipmentFanStatsUpdate                                    Gauge32
}

cfprApEquipmentFanStatsInstanceId OBJECT-TYPE
    SYNTAX       CfprApManagedObjectId
    MAX-ACCESS   not-accessible
    STATUS       current
    DESCRIPTION
        "Instance identifier of the managed object."
    ::= { cfprApEquipmentFanStatsEntry 1 }

cfprApEquipmentFanStatsDn OBJECT-TYPE
    SYNTAX       CfprApManagedObjectDn
    MAX-ACCESS   read-only
    STATUS       current
    DESCRIPTION
        "Cisco Firepower equipment:FanStats:dn managed object property"
    ::= { cfprApEquipmentFanStatsEntry 2 }

cfprApEquipmentFanStatsRn OBJECT-TYPE
    SYNTAX       SnmpAdminString
    MAX-ACCESS   read-only
    STATUS       current
    DESCRIPTION
        "Cisco Firepower equipment:FanStats:rn managed object property"
    ::= { cfprApEquipmentFanStatsEntry 3 }

cfprApEquipmentFanStatsIntervals OBJECT-TYPE
    SYNTAX       Gauge32
    MAX-ACCESS   read-only
    STATUS       current
    DESCRIPTION
        "Cisco Firepower equipment:FanStats:intervals managed
        object property"
    ::= { cfprApEquipmentFanStatsEntry 4 }

cfprApEquipmentFanStatsSpeed OBJECT-TYPE
    SYNTAX       Gauge32
    MAX-ACCESS   read-only
    STATUS       current
    DESCRIPTION
        "Cisco Firepower equipment:FanStats:speed managed object property"
    ::= { cfprApEquipmentFanStatsEntry 5 }

cfprApEquipmentFanStatsSpeedAvg OBJECT-TYPE
    SYNTAX       Gauge32
    MAX-ACCESS   read-only
    STATUS       current
    DESCRIPTION
        "Cisco Firepower equipment:FanStats:speedAvg managed
        object property"
    ::= { cfprApEquipmentFanStatsEntry 6 }

cfprApEquipmentFanStatsSpeedMax OBJECT-TYPE
    SYNTAX       Gauge32
    MAX-ACCESS   read-only
    STATUS       current
    DESCRIPTION
        "Cisco Firepower equipment:FanStats:speedMax managed
        object property"
    ::= { cfprApEquipmentFanStatsEntry 7 }

cfprApEquipmentFanStatsSpeedMin OBJECT-TYPE
    SYNTAX       Gauge32
    MAX-ACCESS   read-only
    STATUS       current
    DESCRIPTION
        "Cisco Firepower equipment:FanStats:speedMin managed
        object property"
    ::= { cfprApEquipmentFanStatsEntry 8 }

cfprApEquipmentFanStatsSuspect OBJECT-TYPE
    SYNTAX       TruthValue
    MAX-ACCESS   read-only
    STATUS       current
    DESCRIPTION
        "Cisco Firepower equipment:FanStats:suspect managed
        object property"
    ::= { cfprApEquipmentFanStatsEntry 9 }

cfprApEquipmentFanStatsThresholded OBJECT-TYPE
    SYNTAX       CfprApEquipmentFanStatsThresholded
    MAX-ACCESS   read-only
    STATUS       current
    DESCRIPTION
        "Cisco Firepower equipment:FanStats:thresholded
        managed object property"
    ::= { cfprApEquipmentFanStatsEntry 10 }

cfprApEquipmentFanStatsTimeCollected OBJECT-TYPE
    SYNTAX       DateAndTime
    MAX-ACCESS   read-only
    STATUS       current
    DESCRIPTION
        "Cisco Firepower equipment:FanStats:timeCollected
        managed object property"
    ::= { cfprApEquipmentFanStatsEntry 11 }

cfprApEquipmentFanStatsUpdate OBJECT-TYPE
    SYNTAX       Gauge32
    MAX-ACCESS   read-only
    STATUS       current
    DESCRIPTION
        "Cisco Firepower equipment:FanStats:update managed
        object property"
    ::= { cfprApEquipmentFanStatsEntry 12 }

cfprApEquipmentFanStatsHistTable OBJECT-TYPE
    SYNTAX           SEQUENCE OF CfprApEquipmentFanStatsHistEntry
    MAX-ACCESS       not-accessible
    STATUS           current
    DESCRIPTION
        "Cisco Firepower equipment:FanStatsHist managed object table"
    ::= { cfprApEquipmentObjects 45 }

cfprApEquipmentFanStatsHistEntry OBJECT-TYPE
    SYNTAX           CfprApEquipmentFanStatsHistEntry
    MAX-ACCESS       not-accessible
    STATUS           current
    DESCRIPTION
        "Entry for the cfprApEquipmentFanStatsHistTable table."
    INDEX { cfprApEquipmentFanStatsHistInstanceId }
    ::= { cfprApEquipmentFanStatsHistTable 1 }

CfprApEquipmentFanStatsHistEntry ::= SEQUENCE {
    cfprApEquipmentFanStatsHistInstanceId                            CfprApManagedObjectId,
    cfprApEquipmentFanStatsHistDn                                    CfprApManagedObjectDn,
    cfprApEquipmentFanStatsHistRn                                    SnmpAdminString,
    cfprApEquipmentFanStatsHistId                                    Unsigned64,
    cfprApEquipmentFanStatsHistMostRecent                            TruthValue,
    cfprApEquipmentFanStatsHistSpeed                                 Gauge32,
    cfprApEquipmentFanStatsHistSpeedAvg                              Gauge32,
    cfprApEquipmentFanStatsHistSpeedMax                              Gauge32,
    cfprApEquipmentFanStatsHistSpeedMin                              Gauge32,
    cfprApEquipmentFanStatsHistSuspect                               TruthValue,
    cfprApEquipmentFanStatsHistThresholded                           CfprApEquipmentFanStatsHistThresholded,
    cfprApEquipmentFanStatsHistTimeCollected                         DateAndTime
}

cfprApEquipmentFanStatsHistInstanceId OBJECT-TYPE
    SYNTAX       CfprApManagedObjectId
    MAX-ACCESS   not-accessible
    STATUS       current
    DESCRIPTION
        "Instance identifier of the managed object."
    ::= { cfprApEquipmentFanStatsHistEntry 1 }

cfprApEquipmentFanStatsHistDn OBJECT-TYPE
    SYNTAX       CfprApManagedObjectDn
    MAX-ACCESS   read-only
    STATUS       current
    DESCRIPTION
        "Cisco Firepower equipment:FanStatsHist:dn managed
        object property"
    ::= { cfprApEquipmentFanStatsHistEntry 2 }

cfprApEquipmentFanStatsHistRn OBJECT-TYPE
    SYNTAX       SnmpAdminString
    MAX-ACCESS   read-only
    STATUS       current
    DESCRIPTION
        "Cisco Firepower equipment:FanStatsHist:rn managed
        object property"
    ::= { cfprApEquipmentFanStatsHistEntry 3 }

cfprApEquipmentFanStatsHistId OBJECT-TYPE
    SYNTAX       Unsigned64
    MAX-ACCESS   read-only
    STATUS       current
    DESCRIPTION
        "Cisco Firepower equipment:FanStatsHist:id managed
        object property"
    ::= { cfprApEquipmentFanStatsHistEntry 4 }

cfprApEquipmentFanStatsHistMostRecent OBJECT-TYPE
    SYNTAX       TruthValue
    MAX-ACCESS   read-only
    STATUS       current
    DESCRIPTION
        "Cisco Firepower equipment:FanStatsHist:mostRecent
        managed object property"
    ::= { cfprApEquipmentFanStatsHistEntry 5 }

cfprApEquipmentFanStatsHistSpeed OBJECT-TYPE
    SYNTAX       Gauge32
    MAX-ACCESS   read-only
    STATUS       current
    DESCRIPTION
        "Cisco Firepower equipment:FanStatsHist:speed managed
        object property"
    ::= { cfprApEquipmentFanStatsHistEntry 6 }

cfprApEquipmentFanStatsHistSpeedAvg OBJECT-TYPE
    SYNTAX       Gauge32
    MAX-ACCESS   read-only
    STATUS       current
    DESCRIPTION
        "Cisco Firepower equipment:FanStatsHist:speedAvg
        managed object property"
    ::= { cfprApEquipmentFanStatsHistEntry 7 }

cfprApEquipmentFanStatsHistSpeedMax OBJECT-TYPE
    SYNTAX       Gauge32
    MAX-ACCESS   read-only
    STATUS       current
    DESCRIPTION
        "Cisco Firepower equipment:FanStatsHist:speedMax
        managed object property"
    ::= { cfprApEquipmentFanStatsHistEntry 8 }

cfprApEquipmentFanStatsHistSpeedMin OBJECT-TYPE
    SYNTAX       Gauge32
    MAX-ACCESS   read-only
    STATUS       current
    DESCRIPTION
        "Cisco Firepower equipment:FanStatsHist:speedMin
        managed object property"
    ::= { cfprApEquipmentFanStatsHistEntry 9 }

cfprApEquipmentFanStatsHistSuspect OBJECT-TYPE
    SYNTAX       TruthValue
    MAX-ACCESS   read-only
    STATUS       current
    DESCRIPTION
        "Cisco Firepower equipment:FanStatsHist:suspect
        managed object property"
    ::= { cfprApEquipmentFanStatsHistEntry 10 }

cfprApEquipmentFanStatsHistThresholded OBJECT-TYPE
    SYNTAX       CfprApEquipmentFanStatsHistThresholded
    MAX-ACCESS   read-only
    STATUS       current
    DESCRIPTION
        "Cisco Firepower equipment:FanStatsHist:thresholded
        managed object property"
    ::= { cfprApEquipmentFanStatsHistEntry 11 }

cfprApEquipmentFanStatsHistTimeCollected OBJECT-TYPE
    SYNTAX       DateAndTime
    MAX-ACCESS   read-only
    STATUS       current
    DESCRIPTION
        "Cisco Firepower equipment:FanStatsHist:timeCollected
        managed object property"
    ::= { cfprApEquipmentFanStatsHistEntry 12 }

cfprApEquipmentFexTable OBJECT-TYPE
    SYNTAX           SEQUENCE OF CfprApEquipmentFexEntry
    MAX-ACCESS       not-accessible
    STATUS           current
    DESCRIPTION
        "Cisco Firepower equipment:Fex managed object table"
    ::= { cfprApEquipmentObjects 46 }

cfprApEquipmentFexEntry OBJECT-TYPE
    SYNTAX           CfprApEquipmentFexEntry
    MAX-ACCESS       not-accessible
    STATUS           current
    DESCRIPTION
        "Entry for the cfprApEquipmentFexTable table."
    INDEX { cfprApEquipmentFexInstanceId }
    ::= { cfprApEquipmentFexTable 1 }

CfprApEquipmentFexEntry ::= SEQUENCE {
    cfprApEquipmentFexInstanceId                                     CfprApManagedObjectId,
    cfprApEquipmentFexDn                                             CfprApManagedObjectDn,
    cfprApEquipmentFexRn                                             SnmpAdminString,
    cfprApEquipmentFexAdminPowerState                                CfprApEquipmentAdminPowerState,
    cfprApEquipmentFexAdminState                                     CfprApEquipmentChassisAdminState,
    cfprApEquipmentFexConfigState                                    CfprApEquipmentChassisConfigState,
    cfprApEquipmentFexFltAggr                                        Unsigned64,
    cfprApEquipmentFexId                                             CfprApEquipmentFexId,
    cfprApEquipmentFexLicGP                                          Unsigned64,
    cfprApEquipmentFexLicState                                       CfprApLicenseState,
    cfprApEquipmentFexModel                                          SnmpAdminString,
    cfprApEquipmentFexOperQualifier                                  CfprApEquipmentChassisIssues,
    cfprApEquipmentFexOperQualifierReason                            SnmpAdminString,
    cfprApEquipmentFexOperState                                      CfprApEquipmentOperability,
    cfprApEquipmentFexOperability                                    CfprApEquipmentOperability,
    cfprApEquipmentFexPower                                          CfprApEquipmentPowerState,
    cfprApEquipmentFexPresence                                       CfprApEquipmentPresence,
    cfprApEquipmentFexRevision                                       SnmpAdminString,
    cfprApEquipmentFexSerial                                         SnmpAdminString,
    cfprApEquipmentFexSwitchId                                       CfprApNetworkSwitchId,
    cfprApEquipmentFexThermal                                        CfprApEquipmentSensorThresholdStatus,
    cfprApEquipmentFexUsrLbl                                         SnmpAdminString,
    cfprApEquipmentFexVendor                                         SnmpAdminString,
    cfprApEquipmentFexVoltage                                        CfprApEquipmentSensorThresholdStatus
}

cfprApEquipmentFexInstanceId OBJECT-TYPE
    SYNTAX       CfprApManagedObjectId
    MAX-ACCESS   not-accessible
    STATUS       current
    DESCRIPTION
        "Instance identifier of the managed object."
    ::= { cfprApEquipmentFexEntry 1 }

cfprApEquipmentFexDn OBJECT-TYPE
    SYNTAX       CfprApManagedObjectDn
    MAX-ACCESS   read-only
    STATUS       current
    DESCRIPTION
        "Cisco Firepower equipment:Fex:dn managed object property"
    ::= { cfprApEquipmentFexEntry 2 }

cfprApEquipmentFexRn OBJECT-TYPE
    SYNTAX       SnmpAdminString
    MAX-ACCESS   read-only
    STATUS       current
    DESCRIPTION
        "Cisco Firepower equipment:Fex:rn managed object property"
    ::= { cfprApEquipmentFexEntry 3 }

cfprApEquipmentFexAdminPowerState OBJECT-TYPE
    SYNTAX       CfprApEquipmentAdminPowerState
    MAX-ACCESS   read-only
    STATUS       current
    DESCRIPTION
        "Cisco Firepower equipment:Fex:adminPowerState
        managed object property"
    ::= { cfprApEquipmentFexEntry 4 }

cfprApEquipmentFexAdminState OBJECT-TYPE
    SYNTAX       CfprApEquipmentChassisAdminState
    MAX-ACCESS   read-only
    STATUS       current
    DESCRIPTION
        "Cisco Firepower equipment:Fex:adminState managed object property"
    ::= { cfprApEquipmentFexEntry 5 }

cfprApEquipmentFexConfigState OBJECT-TYPE
    SYNTAX       CfprApEquipmentChassisConfigState
    MAX-ACCESS   read-only
    STATUS       current
    DESCRIPTION
        "Cisco Firepower equipment:Fex:configState managed
        object property"
    ::= { cfprApEquipmentFexEntry 6 }

cfprApEquipmentFexFltAggr OBJECT-TYPE
    SYNTAX       Unsigned64
    MAX-ACCESS   read-only
    STATUS       current
    DESCRIPTION
        "Cisco Firepower equipment:Fex:fltAggr managed object property"
    ::= { cfprApEquipmentFexEntry 7 }

cfprApEquipmentFexId OBJECT-TYPE
    SYNTAX       CfprApEquipmentFexId
    MAX-ACCESS   read-only
    STATUS       current
    DESCRIPTION
        "Cisco Firepower equipment:Fex:id managed object property"
    ::= { cfprApEquipmentFexEntry 8 }

cfprApEquipmentFexLicGP OBJECT-TYPE
    SYNTAX       Unsigned64
    MAX-ACCESS   read-only
    STATUS       current
    DESCRIPTION
        "Cisco Firepower equipment:Fex:licGP managed object property"
    ::= { cfprApEquipmentFexEntry 9 }

cfprApEquipmentFexLicState OBJECT-TYPE
    SYNTAX       CfprApLicenseState
    MAX-ACCESS   read-only
    STATUS       current
    DESCRIPTION
        "Cisco Firepower equipment:Fex:licState managed object property"
    ::= { cfprApEquipmentFexEntry 10 }

cfprApEquipmentFexModel OBJECT-TYPE
    SYNTAX       SnmpAdminString
    MAX-ACCESS   read-only
    STATUS       current
    DESCRIPTION
        "Cisco Firepower equipment:Fex:model managed object property"
    ::= { cfprApEquipmentFexEntry 11 }

cfprApEquipmentFexOperQualifier OBJECT-TYPE
    SYNTAX       CfprApEquipmentChassisIssues
    MAX-ACCESS   read-only
    STATUS       current
    DESCRIPTION
        "Cisco Firepower equipment:Fex:operQualifier managed
        object property"
    ::= { cfprApEquipmentFexEntry 12 }

cfprApEquipmentFexOperQualifierReason OBJECT-TYPE
    SYNTAX       SnmpAdminString
    MAX-ACCESS   read-only
    STATUS       current
    DESCRIPTION
        "Cisco Firepower equipment:Fex:operQualifierReason
        managed object property"
    ::= { cfprApEquipmentFexEntry 13 }

cfprApEquipmentFexOperState OBJECT-TYPE
    SYNTAX       CfprApEquipmentOperability
    MAX-ACCESS   read-only
    STATUS       current
    DESCRIPTION
        "Cisco Firepower equipment:Fex:operState managed object property"
    ::= { cfprApEquipmentFexEntry 14 }

cfprApEquipmentFexOperability OBJECT-TYPE
    SYNTAX       CfprApEquipmentOperability
    MAX-ACCESS   read-only
    STATUS       current
    DESCRIPTION
        "Cisco Firepower equipment:Fex:operability managed
        object property"
    ::= { cfprApEquipmentFexEntry 15 }

cfprApEquipmentFexPower OBJECT-TYPE
    SYNTAX       CfprApEquipmentPowerState
    MAX-ACCESS   read-only
    STATUS       current
    DESCRIPTION
        "Cisco Firepower equipment:Fex:power managed object property"
    ::= { cfprApEquipmentFexEntry 16 }

cfprApEquipmentFexPresence OBJECT-TYPE
    SYNTAX       CfprApEquipmentPresence
    MAX-ACCESS   read-only
    STATUS       current
    DESCRIPTION
        "Cisco Firepower equipment:Fex:presence managed object property"
    ::= { cfprApEquipmentFexEntry 17 }

cfprApEquipmentFexRevision OBJECT-TYPE
    SYNTAX       SnmpAdminString
    MAX-ACCESS   read-only
    STATUS       current
    DESCRIPTION
        "Cisco Firepower equipment:Fex:revision managed object property"
    ::= { cfprApEquipmentFexEntry 18 }

cfprApEquipmentFexSerial OBJECT-TYPE
    SYNTAX       SnmpAdminString
    MAX-ACCESS   read-only
    STATUS       current
    DESCRIPTION
        "Cisco Firepower equipment:Fex:serial managed object property"
    ::= { cfprApEquipmentFexEntry 19 }

cfprApEquipmentFexSwitchId OBJECT-TYPE
    SYNTAX       CfprApNetworkSwitchId
    MAX-ACCESS   read-only
    STATUS       current
    DESCRIPTION
        "Cisco Firepower equipment:Fex:switchId managed object property"
    ::= { cfprApEquipmentFexEntry 20 }

cfprApEquipmentFexThermal OBJECT-TYPE
    SYNTAX       CfprApEquipmentSensorThresholdStatus
    MAX-ACCESS   read-only
    STATUS       current
    DESCRIPTION
        "Cisco Firepower equipment:Fex:thermal managed object property"
    ::= { cfprApEquipmentFexEntry 21 }

cfprApEquipmentFexUsrLbl OBJECT-TYPE
    SYNTAX       SnmpAdminString
    MAX-ACCESS   read-only
    STATUS       current
    DESCRIPTION
        "Cisco Firepower equipment:Fex:usrLbl managed object property"
    ::= { cfprApEquipmentFexEntry 22 }

cfprApEquipmentFexVendor OBJECT-TYPE
    SYNTAX       SnmpAdminString
    MAX-ACCESS   read-only
    STATUS       current
    DESCRIPTION
        "Cisco Firepower equipment:Fex:vendor managed object property"
    ::= { cfprApEquipmentFexEntry 23 }

cfprApEquipmentFexVoltage OBJECT-TYPE
    SYNTAX       CfprApEquipmentSensorThresholdStatus
    MAX-ACCESS   read-only
    STATUS       current
    DESCRIPTION
        "Cisco Firepower equipment:Fex:voltage managed object property"
    ::= { cfprApEquipmentFexEntry 24 }

cfprApEquipmentFexCapProviderTable OBJECT-TYPE
    SYNTAX           SEQUENCE OF CfprApEquipmentFexCapProviderEntry
    MAX-ACCESS       not-accessible
    STATUS           current
    DESCRIPTION
        "Cisco Firepower equipment:FexCapProvider managed object table"
    ::= { cfprApEquipmentObjects 47 }

cfprApEquipmentFexCapProviderEntry OBJECT-TYPE
    SYNTAX           CfprApEquipmentFexCapProviderEntry
    MAX-ACCESS       not-accessible
    STATUS           current
    DESCRIPTION
        "Entry for the cfprApEquipmentFexCapProviderTable table."
    INDEX { cfprApEquipmentFexCapProviderInstanceId }
    ::= { cfprApEquipmentFexCapProviderTable 1 }

CfprApEquipmentFexCapProviderEntry ::= SEQUENCE {
    cfprApEquipmentFexCapProviderInstanceId                          CfprApManagedObjectId,
    cfprApEquipmentFexCapProviderDn                                  CfprApManagedObjectDn,
    cfprApEquipmentFexCapProviderRn                                  SnmpAdminString,
    cfprApEquipmentFexCapProviderDeleted                             TruthValue,
    cfprApEquipmentFexCapProviderDeprecated                          TruthValue,
    cfprApEquipmentFexCapProviderElementLoadFailures                 Gauge32,
    cfprApEquipmentFexCapProviderElementsLoaded                      Gauge32,
    cfprApEquipmentFexCapProviderGencount                            Gauge32,
    cfprApEquipmentFexCapProviderLoadErrors                          Gauge32,
    cfprApEquipmentFexCapProviderLoadWarnings                        Gauge32,
    cfprApEquipmentFexCapProviderMgmtPlaneVer                        SnmpAdminString,
    cfprApEquipmentFexCapProviderModel                               SnmpAdminString,
    cfprApEquipmentFexCapProviderPromCardType                        Gauge32,
    cfprApEquipmentFexCapProviderRevision                            SnmpAdminString,
    cfprApEquipmentFexCapProviderRole                                CfprApEquipmentFexCapProviderRole,
    cfprApEquipmentFexCapProviderVendor                              SnmpAdminString
}

cfprApEquipmentFexCapProviderInstanceId OBJECT-TYPE
    SYNTAX       CfprApManagedObjectId
    MAX-ACCESS   not-accessible
    STATUS       current
    DESCRIPTION
        "Instance identifier of the managed object."
    ::= { cfprApEquipmentFexCapProviderEntry 1 }

cfprApEquipmentFexCapProviderDn OBJECT-TYPE
    SYNTAX       CfprApManagedObjectDn
    MAX-ACCESS   read-only
    STATUS       current
    DESCRIPTION
        "Cisco Firepower equipment:FexCapProvider:dn managed
        object property"
    ::= { cfprApEquipmentFexCapProviderEntry 2 }

cfprApEquipmentFexCapProviderRn OBJECT-TYPE
    SYNTAX       SnmpAdminString
    MAX-ACCESS   read-only
    STATUS       current
    DESCRIPTION
        "Cisco Firepower equipment:FexCapProvider:rn managed
        object property"
    ::= { cfprApEquipmentFexCapProviderEntry 3 }

cfprApEquipmentFexCapProviderDeleted OBJECT-TYPE
    SYNTAX       TruthValue
    MAX-ACCESS   read-only
    STATUS       current
    DESCRIPTION
        "Cisco Firepower equipment:FexCapProvider:deleted
        managed object property"
    ::= { cfprApEquipmentFexCapProviderEntry 4 }

cfprApEquipmentFexCapProviderDeprecated OBJECT-TYPE
    SYNTAX       TruthValue
    MAX-ACCESS   read-only
    STATUS       current
    DESCRIPTION
        "Cisco Firepower equipment:FexCapProvider:deprecated
        managed object property"
    ::= { cfprApEquipmentFexCapProviderEntry 5 }

cfprApEquipmentFexCapProviderElementLoadFailures OBJECT-TYPE
    SYNTAX       Gauge32
    MAX-ACCESS   read-only
    STATUS       current
    DESCRIPTION
        "Cisco Firepower equipment:FexCapProvider:elementLoadFailures
        managed object property"
    ::= { cfprApEquipmentFexCapProviderEntry 6 }

cfprApEquipmentFexCapProviderElementsLoaded OBJECT-TYPE
    SYNTAX       Gauge32
    MAX-ACCESS   read-only
    STATUS       current
    DESCRIPTION
        "Cisco Firepower equipment:FexCapProvider:elementsLoaded
        managed object property"
    ::= { cfprApEquipmentFexCapProviderEntry 7 }

cfprApEquipmentFexCapProviderGencount OBJECT-TYPE
    SYNTAX       Gauge32
    MAX-ACCESS   read-only
    STATUS       current
    DESCRIPTION
        "Cisco Firepower equipment:FexCapProvider:gencount
        managed object property"
    ::= { cfprApEquipmentFexCapProviderEntry 8 }

cfprApEquipmentFexCapProviderLoadErrors OBJECT-TYPE
    SYNTAX       Gauge32
    MAX-ACCESS   read-only
    STATUS       current
    DESCRIPTION
        "Cisco Firepower equipment:FexCapProvider:loadErrors
        managed object property"
    ::= { cfprApEquipmentFexCapProviderEntry 9 }

cfprApEquipmentFexCapProviderLoadWarnings OBJECT-TYPE
    SYNTAX       Gauge32
    MAX-ACCESS   read-only
    STATUS       current
    DESCRIPTION
        "Cisco Firepower equipment:FexCapProvider:loadWarnings
        managed object property"
    ::= { cfprApEquipmentFexCapProviderEntry 10 }

cfprApEquipmentFexCapProviderMgmtPlaneVer OBJECT-TYPE
    SYNTAX       SnmpAdminString
    MAX-ACCESS   read-only
    STATUS       current
    DESCRIPTION
        "Cisco Firepower equipment:FexCapProvider:mgmtPlaneVer
        managed object property"
    ::= { cfprApEquipmentFexCapProviderEntry 11 }

cfprApEquipmentFexCapProviderModel OBJECT-TYPE
    SYNTAX       SnmpAdminString
    MAX-ACCESS   read-only
    STATUS       current
    DESCRIPTION
        "Cisco Firepower equipment:FexCapProvider:model
        managed object property"
    ::= { cfprApEquipmentFexCapProviderEntry 12 }

cfprApEquipmentFexCapProviderPromCardType OBJECT-TYPE
    SYNTAX       Gauge32
    MAX-ACCESS   read-only
    STATUS       current
    DESCRIPTION
        "Cisco Firepower equipment:FexCapProvider:promCardType
        managed object property"
    ::= { cfprApEquipmentFexCapProviderEntry 13 }

cfprApEquipmentFexCapProviderRevision OBJECT-TYPE
    SYNTAX       SnmpAdminString
    MAX-ACCESS   read-only
    STATUS       current
    DESCRIPTION
        "Cisco Firepower equipment:FexCapProvider:revision
        managed object property"
    ::= { cfprApEquipmentFexCapProviderEntry 14 }

cfprApEquipmentFexCapProviderRole OBJECT-TYPE
    SYNTAX       CfprApEquipmentFexCapProviderRole
    MAX-ACCESS   read-only
    STATUS       current
    DESCRIPTION
        "Cisco Firepower equipment:FexCapProvider:role
        managed object property"
    ::= { cfprApEquipmentFexCapProviderEntry 15 }

cfprApEquipmentFexCapProviderVendor OBJECT-TYPE
    SYNTAX       SnmpAdminString
    MAX-ACCESS   read-only
    STATUS       current
    DESCRIPTION
        "Cisco Firepower equipment:FexCapProvider:vendor
        managed object property"
    ::= { cfprApEquipmentFexCapProviderEntry 16 }

cfprApEquipmentFexEnvStatsTable OBJECT-TYPE
    SYNTAX           SEQUENCE OF CfprApEquipmentFexEnvStatsEntry
    MAX-ACCESS       not-accessible
    STATUS           current
    DESCRIPTION
        "Cisco Firepower equipment:FexEnvStats managed object table"
    ::= { cfprApEquipmentObjects 48 }

cfprApEquipmentFexEnvStatsEntry OBJECT-TYPE
    SYNTAX           CfprApEquipmentFexEnvStatsEntry
    MAX-ACCESS       not-accessible
    STATUS           current
    DESCRIPTION
        "Entry for the cfprApEquipmentFexEnvStatsTable table."
    INDEX { cfprApEquipmentFexEnvStatsInstanceId }
    ::= { cfprApEquipmentFexEnvStatsTable 1 }

CfprApEquipmentFexEnvStatsEntry ::= SEQUENCE {
    cfprApEquipmentFexEnvStatsInstanceId                             CfprApManagedObjectId,
    cfprApEquipmentFexEnvStatsDn                                     CfprApManagedObjectDn,
    cfprApEquipmentFexEnvStatsRn                                     SnmpAdminString,
    cfprApEquipmentFexEnvStatsDie1                                   INTEGER,
    cfprApEquipmentFexEnvStatsDie1Avg                                INTEGER,
    cfprApEquipmentFexEnvStatsDie1Max                                INTEGER,
    cfprApEquipmentFexEnvStatsDie1Min                                INTEGER,
    cfprApEquipmentFexEnvStatsInlet                                  INTEGER,
    cfprApEquipmentFexEnvStatsInlet1                                 INTEGER,
    cfprApEquipmentFexEnvStatsInlet1Avg                              INTEGER,
    cfprApEquipmentFexEnvStatsInlet1Max                              INTEGER,
    cfprApEquipmentFexEnvStatsInlet1Min                              INTEGER,
    cfprApEquipmentFexEnvStatsInletAvg                               INTEGER,
    cfprApEquipmentFexEnvStatsInletMax                               INTEGER,
    cfprApEquipmentFexEnvStatsInletMin                               INTEGER,
    cfprApEquipmentFexEnvStatsInputStatus                            SnmpAdminString,
    cfprApEquipmentFexEnvStatsIntervals                              Gauge32,
    cfprApEquipmentFexEnvStatsOutlet1                                INTEGER,
    cfprApEquipmentFexEnvStatsOutlet1Avg                             INTEGER,
    cfprApEquipmentFexEnvStatsOutlet1Max                             INTEGER,
    cfprApEquipmentFexEnvStatsOutlet1Min                             INTEGER,
    cfprApEquipmentFexEnvStatsOutlet2                                INTEGER,
    cfprApEquipmentFexEnvStatsOutlet2Avg                             INTEGER,
    cfprApEquipmentFexEnvStatsOutlet2Max                             INTEGER,
    cfprApEquipmentFexEnvStatsOutlet2Min                             INTEGER,
    cfprApEquipmentFexEnvStatsSuspect                                TruthValue,
    cfprApEquipmentFexEnvStatsThresholded                            CfprApEquipmentFexEnvStatsThresholded,
    cfprApEquipmentFexEnvStatsTimeCollected                          DateAndTime,
    cfprApEquipmentFexEnvStatsUpdate                                 Gauge32
}

cfprApEquipmentFexEnvStatsInstanceId OBJECT-TYPE
    SYNTAX       CfprApManagedObjectId
    MAX-ACCESS   not-accessible
    STATUS       current
    DESCRIPTION
        "Instance identifier of the managed object."
    ::= { cfprApEquipmentFexEnvStatsEntry 1 }

cfprApEquipmentFexEnvStatsDn OBJECT-TYPE
    SYNTAX       CfprApManagedObjectDn
    MAX-ACCESS   read-only
    STATUS       current
    DESCRIPTION
        "Cisco Firepower equipment:FexEnvStats:dn managed object property"
    ::= { cfprApEquipmentFexEnvStatsEntry 2 }

cfprApEquipmentFexEnvStatsRn OBJECT-TYPE
    SYNTAX       SnmpAdminString
    MAX-ACCESS   read-only
    STATUS       current
    DESCRIPTION
        "Cisco Firepower equipment:FexEnvStats:rn managed object property"
    ::= { cfprApEquipmentFexEnvStatsEntry 3 }

cfprApEquipmentFexEnvStatsDie1 OBJECT-TYPE
    SYNTAX       INTEGER
    MAX-ACCESS   read-only
    STATUS       current
    DESCRIPTION
        "Cisco Firepower equipment:FexEnvStats:die1 managed
        object property"
    ::= { cfprApEquipmentFexEnvStatsEntry 4 }

cfprApEquipmentFexEnvStatsDie1Avg OBJECT-TYPE
    SYNTAX       INTEGER
    MAX-ACCESS   read-only
    STATUS       current
    DESCRIPTION
        "Cisco Firepower equipment:FexEnvStats:die1Avg
        managed object property"
    ::= { cfprApEquipmentFexEnvStatsEntry 5 }

cfprApEquipmentFexEnvStatsDie1Max OBJECT-TYPE
    SYNTAX       INTEGER
    MAX-ACCESS   read-only
    STATUS       current
    DESCRIPTION
        "Cisco Firepower equipment:FexEnvStats:die1Max
        managed object property"
    ::= { cfprApEquipmentFexEnvStatsEntry 6 }

cfprApEquipmentFexEnvStatsDie1Min OBJECT-TYPE
    SYNTAX       INTEGER
    MAX-ACCESS   read-only
    STATUS       current
    DESCRIPTION
        "Cisco Firepower equipment:FexEnvStats:die1Min
        managed object property"
    ::= { cfprApEquipmentFexEnvStatsEntry 7 }

cfprApEquipmentFexEnvStatsInlet OBJECT-TYPE
    SYNTAX       INTEGER
    MAX-ACCESS   read-only
    STATUS       current
    DESCRIPTION
        "Cisco Firepower equipment:FexEnvStats:inlet managed
        object property"
    ::= { cfprApEquipmentFexEnvStatsEntry 8 }

cfprApEquipmentFexEnvStatsInlet1 OBJECT-TYPE
    SYNTAX       INTEGER
    MAX-ACCESS   read-only
    STATUS       current
    DESCRIPTION
        "Cisco Firepower equipment:FexEnvStats:inlet1 managed
        object property"
    ::= { cfprApEquipmentFexEnvStatsEntry 9 }

cfprApEquipmentFexEnvStatsInlet1Avg OBJECT-TYPE
    SYNTAX       INTEGER
    MAX-ACCESS   read-only
    STATUS       current
    DESCRIPTION
        "Cisco Firepower equipment:FexEnvStats:inlet1Avg
        managed object property"
    ::= { cfprApEquipmentFexEnvStatsEntry 10 }

cfprApEquipmentFexEnvStatsInlet1Max OBJECT-TYPE
    SYNTAX       INTEGER
    MAX-ACCESS   read-only
    STATUS       current
    DESCRIPTION
        "Cisco Firepower equipment:FexEnvStats:inlet1Max
        managed object property"
    ::= { cfprApEquipmentFexEnvStatsEntry 11 }

cfprApEquipmentFexEnvStatsInlet1Min OBJECT-TYPE
    SYNTAX       INTEGER
    MAX-ACCESS   read-only
    STATUS       current
    DESCRIPTION
        "Cisco Firepower equipment:FexEnvStats:inlet1Min
        managed object property"
    ::= { cfprApEquipmentFexEnvStatsEntry 12 }

cfprApEquipmentFexEnvStatsInletAvg OBJECT-TYPE
    SYNTAX       INTEGER
    MAX-ACCESS   read-only
    STATUS       current
    DESCRIPTION
        "Cisco Firepower equipment:FexEnvStats:inletAvg
        managed object property"
    ::= { cfprApEquipmentFexEnvStatsEntry 13 }

cfprApEquipmentFexEnvStatsInletMax OBJECT-TYPE
    SYNTAX       INTEGER
    MAX-ACCESS   read-only
    STATUS       current
    DESCRIPTION
        "Cisco Firepower equipment:FexEnvStats:inletMax
        managed object property"
    ::= { cfprApEquipmentFexEnvStatsEntry 14 }

cfprApEquipmentFexEnvStatsInletMin OBJECT-TYPE
    SYNTAX       INTEGER
    MAX-ACCESS   read-only
    STATUS       current
    DESCRIPTION
        "Cisco Firepower equipment:FexEnvStats:inletMin
        managed object property"
    ::= { cfprApEquipmentFexEnvStatsEntry 15 }

cfprApEquipmentFexEnvStatsInputStatus OBJECT-TYPE
    SYNTAX       SnmpAdminString
    MAX-ACCESS   read-only
    STATUS       current
    DESCRIPTION
        "Cisco Firepower equipment:FexEnvStats:inputStatus
        managed object property"
    ::= { cfprApEquipmentFexEnvStatsEntry 16 }

cfprApEquipmentFexEnvStatsIntervals OBJECT-TYPE
    SYNTAX       Gauge32
    MAX-ACCESS   read-only
    STATUS       current
    DESCRIPTION
        "Cisco Firepower equipment:FexEnvStats:intervals
        managed object property"
    ::= { cfprApEquipmentFexEnvStatsEntry 17 }

cfprApEquipmentFexEnvStatsOutlet1 OBJECT-TYPE
    SYNTAX       INTEGER
    MAX-ACCESS   read-only
    STATUS       current
    DESCRIPTION
        "Cisco Firepower equipment:FexEnvStats:outlet1
        managed object property"
    ::= { cfprApEquipmentFexEnvStatsEntry 18 }

cfprApEquipmentFexEnvStatsOutlet1Avg OBJECT-TYPE
    SYNTAX       INTEGER
    MAX-ACCESS   read-only
    STATUS       current
    DESCRIPTION
        "Cisco Firepower equipment:FexEnvStats:outlet1Avg
        managed object property"
    ::= { cfprApEquipmentFexEnvStatsEntry 19 }

cfprApEquipmentFexEnvStatsOutlet1Max OBJECT-TYPE
    SYNTAX       INTEGER
    MAX-ACCESS   read-only
    STATUS       current
    DESCRIPTION
        "Cisco Firepower equipment:FexEnvStats:outlet1Max
        managed object property"
    ::= { cfprApEquipmentFexEnvStatsEntry 20 }

cfprApEquipmentFexEnvStatsOutlet1Min OBJECT-TYPE
    SYNTAX       INTEGER
    MAX-ACCESS   read-only
    STATUS       current
    DESCRIPTION
        "Cisco Firepower equipment:FexEnvStats:outlet1Min
        managed object property"
    ::= { cfprApEquipmentFexEnvStatsEntry 21 }

cfprApEquipmentFexEnvStatsOutlet2 OBJECT-TYPE
    SYNTAX       INTEGER
    MAX-ACCESS   read-only
    STATUS       current
    DESCRIPTION
        "Cisco Firepower equipment:FexEnvStats:outlet2
        managed object property"
    ::= { cfprApEquipmentFexEnvStatsEntry 22 }

cfprApEquipmentFexEnvStatsOutlet2Avg OBJECT-TYPE
    SYNTAX       INTEGER
    MAX-ACCESS   read-only
    STATUS       current
    DESCRIPTION
        "Cisco Firepower equipment:FexEnvStats:outlet2Avg
        managed object property"
    ::= { cfprApEquipmentFexEnvStatsEntry 23 }

cfprApEquipmentFexEnvStatsOutlet2Max OBJECT-TYPE
    SYNTAX       INTEGER
    MAX-ACCESS   read-only
    STATUS       current
    DESCRIPTION
        "Cisco Firepower equipment:FexEnvStats:outlet2Max
        managed object property"
    ::= { cfprApEquipmentFexEnvStatsEntry 24 }

cfprApEquipmentFexEnvStatsOutlet2Min OBJECT-TYPE
    SYNTAX       INTEGER
    MAX-ACCESS   read-only
    STATUS       current
    DESCRIPTION
        "Cisco Firepower equipment:FexEnvStats:outlet2Min
        managed object property"
    ::= { cfprApEquipmentFexEnvStatsEntry 25 }

cfprApEquipmentFexEnvStatsSuspect OBJECT-TYPE
    SYNTAX       TruthValue
    MAX-ACCESS   read-only
    STATUS       current
    DESCRIPTION
        "Cisco Firepower equipment:FexEnvStats:suspect
        managed object property"
    ::= { cfprApEquipmentFexEnvStatsEntry 26 }

cfprApEquipmentFexEnvStatsThresholded OBJECT-TYPE
    SYNTAX       CfprApEquipmentFexEnvStatsThresholded
    MAX-ACCESS   read-only
    STATUS       current
    DESCRIPTION
        "Cisco Firepower equipment:FexEnvStats:thresholded
        managed object property"
    ::= { cfprApEquipmentFexEnvStatsEntry 27 }

cfprApEquipmentFexEnvStatsTimeCollected OBJECT-TYPE
    SYNTAX       DateAndTime
    MAX-ACCESS   read-only
    STATUS       current
    DESCRIPTION
        "Cisco Firepower equipment:FexEnvStats:timeCollected
        managed object property"
    ::= { cfprApEquipmentFexEnvStatsEntry 28 }

cfprApEquipmentFexEnvStatsUpdate OBJECT-TYPE
    SYNTAX       Gauge32
    MAX-ACCESS   read-only
    STATUS       current
    DESCRIPTION
        "Cisco Firepower equipment:FexEnvStats:update managed
        object property"
    ::= { cfprApEquipmentFexEnvStatsEntry 29 }

cfprApEquipmentFexEnvStatsHistTable OBJECT-TYPE
    SYNTAX           SEQUENCE OF CfprApEquipmentFexEnvStatsHistEntry
    MAX-ACCESS       not-accessible
    STATUS           current
    DESCRIPTION
        "Cisco Firepower equipment:FexEnvStatsHist managed object table"
    ::= { cfprApEquipmentObjects 49 }

cfprApEquipmentFexEnvStatsHistEntry OBJECT-TYPE
    SYNTAX           CfprApEquipmentFexEnvStatsHistEntry
    MAX-ACCESS       not-accessible
    STATUS           current
    DESCRIPTION
        "Entry for the cfprApEquipmentFexEnvStatsHistTable table."
    INDEX { cfprApEquipmentFexEnvStatsHistInstanceId }
    ::= { cfprApEquipmentFexEnvStatsHistTable 1 }

CfprApEquipmentFexEnvStatsHistEntry ::= SEQUENCE {
    cfprApEquipmentFexEnvStatsHistInstanceId                         CfprApManagedObjectId,
    cfprApEquipmentFexEnvStatsHistDn                                 CfprApManagedObjectDn,
    cfprApEquipmentFexEnvStatsHistRn                                 SnmpAdminString,
    cfprApEquipmentFexEnvStatsHistDie1                               INTEGER,
    cfprApEquipmentFexEnvStatsHistDie1Avg                            INTEGER,
    cfprApEquipmentFexEnvStatsHistDie1Max                            INTEGER,
    cfprApEquipmentFexEnvStatsHistDie1Min                            INTEGER,
    cfprApEquipmentFexEnvStatsHistId                                 Unsigned64,
    cfprApEquipmentFexEnvStatsHistInlet                              INTEGER,
    cfprApEquipmentFexEnvStatsHistInlet1                             INTEGER,
    cfprApEquipmentFexEnvStatsHistInlet1Avg                          INTEGER,
    cfprApEquipmentFexEnvStatsHistInlet1Max                          INTEGER,
    cfprApEquipmentFexEnvStatsHistInlet1Min                          INTEGER,
    cfprApEquipmentFexEnvStatsHistInletAvg                           INTEGER,
    cfprApEquipmentFexEnvStatsHistInletMax                           INTEGER,
    cfprApEquipmentFexEnvStatsHistInletMin                           INTEGER,
    cfprApEquipmentFexEnvStatsHistMostRecent                         TruthValue,
    cfprApEquipmentFexEnvStatsHistOutlet1                            INTEGER,
    cfprApEquipmentFexEnvStatsHistOutlet1Avg                         INTEGER,
    cfprApEquipmentFexEnvStatsHistOutlet1Max                         INTEGER,
    cfprApEquipmentFexEnvStatsHistOutlet1Min                         INTEGER,
    cfprApEquipmentFexEnvStatsHistOutlet2                            INTEGER,
    cfprApEquipmentFexEnvStatsHistOutlet2Avg                         INTEGER,
    cfprApEquipmentFexEnvStatsHistOutlet2Max                         INTEGER,
    cfprApEquipmentFexEnvStatsHistOutlet2Min                         INTEGER,
    cfprApEquipmentFexEnvStatsHistSuspect                            TruthValue,
    cfprApEquipmentFexEnvStatsHistThresholded                        CfprApEquipmentFexEnvStatsHistThresholded,
    cfprApEquipmentFexEnvStatsHistTimeCollected                      DateAndTime
}

cfprApEquipmentFexEnvStatsHistInstanceId OBJECT-TYPE
    SYNTAX       CfprApManagedObjectId
    MAX-ACCESS   not-accessible
    STATUS       current
    DESCRIPTION
        "Instance identifier of the managed object."
    ::= { cfprApEquipmentFexEnvStatsHistEntry 1 }

cfprApEquipmentFexEnvStatsHistDn OBJECT-TYPE
    SYNTAX       CfprApManagedObjectDn
    MAX-ACCESS   read-only
    STATUS       current
    DESCRIPTION
        "Cisco Firepower equipment:FexEnvStatsHist:dn managed
        object property"
    ::= { cfprApEquipmentFexEnvStatsHistEntry 2 }

cfprApEquipmentFexEnvStatsHistRn OBJECT-TYPE
    SYNTAX       SnmpAdminString
    MAX-ACCESS   read-only
    STATUS       current
    DESCRIPTION
        "Cisco Firepower equipment:FexEnvStatsHist:rn managed
        object property"
    ::= { cfprApEquipmentFexEnvStatsHistEntry 3 }

cfprApEquipmentFexEnvStatsHistDie1 OBJECT-TYPE
    SYNTAX       INTEGER
    MAX-ACCESS   read-only
    STATUS       current
    DESCRIPTION
        "Cisco Firepower equipment:FexEnvStatsHist:die1
        managed object property"
    ::= { cfprApEquipmentFexEnvStatsHistEntry 4 }

cfprApEquipmentFexEnvStatsHistDie1Avg OBJECT-TYPE
    SYNTAX       INTEGER
    MAX-ACCESS   read-only
    STATUS       current
    DESCRIPTION
        "Cisco Firepower equipment:FexEnvStatsHist:die1Avg
        managed object property"
    ::= { cfprApEquipmentFexEnvStatsHistEntry 5 }

cfprApEquipmentFexEnvStatsHistDie1Max OBJECT-TYPE
    SYNTAX       INTEGER
    MAX-ACCESS   read-only
    STATUS       current
    DESCRIPTION
        "Cisco Firepower equipment:FexEnvStatsHist:die1Max
        managed object property"
    ::= { cfprApEquipmentFexEnvStatsHistEntry 6 }

cfprApEquipmentFexEnvStatsHistDie1Min OBJECT-TYPE
    SYNTAX       INTEGER
    MAX-ACCESS   read-only
    STATUS       current
    DESCRIPTION
        "Cisco Firepower equipment:FexEnvStatsHist:die1Min
        managed object property"
    ::= { cfprApEquipmentFexEnvStatsHistEntry 7 }

cfprApEquipmentFexEnvStatsHistId OBJECT-TYPE
    SYNTAX       Unsigned64
    MAX-ACCESS   read-only
    STATUS       current
    DESCRIPTION
        "Cisco Firepower equipment:FexEnvStatsHist:id managed
        object property"
    ::= { cfprApEquipmentFexEnvStatsHistEntry 8 }

cfprApEquipmentFexEnvStatsHistInlet OBJECT-TYPE
    SYNTAX       INTEGER
    MAX-ACCESS   read-only
    STATUS       current
    DESCRIPTION
        "Cisco Firepower equipment:FexEnvStatsHist:inlet
        managed object property"
    ::= { cfprApEquipmentFexEnvStatsHistEntry 9 }

cfprApEquipmentFexEnvStatsHistInlet1 OBJECT-TYPE
    SYNTAX       INTEGER
    MAX-ACCESS   read-only
    STATUS       current
    DESCRIPTION
        "Cisco Firepower equipment:FexEnvStatsHist:inlet1
        managed object property"
    ::= { cfprApEquipmentFexEnvStatsHistEntry 10 }

cfprApEquipmentFexEnvStatsHistInlet1Avg OBJECT-TYPE
    SYNTAX       INTEGER
    MAX-ACCESS   read-only
    STATUS       current
    DESCRIPTION
        "Cisco Firepower equipment:FexEnvStatsHist:inlet1Avg
        managed object property"
    ::= { cfprApEquipmentFexEnvStatsHistEntry 11 }

cfprApEquipmentFexEnvStatsHistInlet1Max OBJECT-TYPE
    SYNTAX       INTEGER
    MAX-ACCESS   read-only
    STATUS       current
    DESCRIPTION
        "Cisco Firepower equipment:FexEnvStatsHist:inlet1Max
        managed object property"
    ::= { cfprApEquipmentFexEnvStatsHistEntry 12 }

cfprApEquipmentFexEnvStatsHistInlet1Min OBJECT-TYPE
    SYNTAX       INTEGER
    MAX-ACCESS   read-only
    STATUS       current
    DESCRIPTION
        "Cisco Firepower equipment:FexEnvStatsHist:inlet1Min
        managed object property"
    ::= { cfprApEquipmentFexEnvStatsHistEntry 13 }

cfprApEquipmentFexEnvStatsHistInletAvg OBJECT-TYPE
    SYNTAX       INTEGER
    MAX-ACCESS   read-only
    STATUS       current
    DESCRIPTION
        "Cisco Firepower equipment:FexEnvStatsHist:inletAvg
        managed object property"
    ::= { cfprApEquipmentFexEnvStatsHistEntry 14 }

cfprApEquipmentFexEnvStatsHistInletMax OBJECT-TYPE
    SYNTAX       INTEGER
    MAX-ACCESS   read-only
    STATUS       current
    DESCRIPTION
        "Cisco Firepower equipment:FexEnvStatsHist:inletMax
        managed object property"
    ::= { cfprApEquipmentFexEnvStatsHistEntry 15 }

cfprApEquipmentFexEnvStatsHistInletMin OBJECT-TYPE
    SYNTAX       INTEGER
    MAX-ACCESS   read-only
    STATUS       current
    DESCRIPTION
        "Cisco Firepower equipment:FexEnvStatsHist:inletMin
        managed object property"
    ::= { cfprApEquipmentFexEnvStatsHistEntry 16 }

cfprApEquipmentFexEnvStatsHistMostRecent OBJECT-TYPE
    SYNTAX       TruthValue
    MAX-ACCESS   read-only
    STATUS       current
    DESCRIPTION
        "Cisco Firepower equipment:FexEnvStatsHist:mostRecent
        managed object property"
    ::= { cfprApEquipmentFexEnvStatsHistEntry 17 }

cfprApEquipmentFexEnvStatsHistOutlet1 OBJECT-TYPE
    SYNTAX       INTEGER
    MAX-ACCESS   read-only
    STATUS       current
    DESCRIPTION
        "Cisco Firepower equipment:FexEnvStatsHist:outlet1
        managed object property"
    ::= { cfprApEquipmentFexEnvStatsHistEntry 18 }

cfprApEquipmentFexEnvStatsHistOutlet1Avg OBJECT-TYPE
    SYNTAX       INTEGER
    MAX-ACCESS   read-only
    STATUS       current
    DESCRIPTION
        "Cisco Firepower equipment:FexEnvStatsHist:outlet1Avg
        managed object property"
    ::= { cfprApEquipmentFexEnvStatsHistEntry 19 }

cfprApEquipmentFexEnvStatsHistOutlet1Max OBJECT-TYPE
    SYNTAX       INTEGER
    MAX-ACCESS   read-only
    STATUS       current
    DESCRIPTION
        "Cisco Firepower equipment:FexEnvStatsHist:outlet1Max
        managed object property"
    ::= { cfprApEquipmentFexEnvStatsHistEntry 20 }

cfprApEquipmentFexEnvStatsHistOutlet1Min OBJECT-TYPE
    SYNTAX       INTEGER
    MAX-ACCESS   read-only
    STATUS       current
    DESCRIPTION
        "Cisco Firepower equipment:FexEnvStatsHist:outlet1Min
        managed object property"
    ::= { cfprApEquipmentFexEnvStatsHistEntry 21 }

cfprApEquipmentFexEnvStatsHistOutlet2 OBJECT-TYPE
    SYNTAX       INTEGER
    MAX-ACCESS   read-only
    STATUS       current
    DESCRIPTION
        "Cisco Firepower equipment:FexEnvStatsHist:outlet2
        managed object property"
    ::= { cfprApEquipmentFexEnvStatsHistEntry 22 }

cfprApEquipmentFexEnvStatsHistOutlet2Avg OBJECT-TYPE
    SYNTAX       INTEGER
    MAX-ACCESS   read-only
    STATUS       current
    DESCRIPTION
        "Cisco Firepower equipment:FexEnvStatsHist:outlet2Avg
        managed object property"
    ::= { cfprApEquipmentFexEnvStatsHistEntry 23 }

cfprApEquipmentFexEnvStatsHistOutlet2Max OBJECT-TYPE
    SYNTAX       INTEGER
    MAX-ACCESS   read-only
    STATUS       current
    DESCRIPTION
        "Cisco Firepower equipment:FexEnvStatsHist:outlet2Max
        managed object property"
    ::= { cfprApEquipmentFexEnvStatsHistEntry 24 }

cfprApEquipmentFexEnvStatsHistOutlet2Min OBJECT-TYPE
    SYNTAX       INTEGER
    MAX-ACCESS   read-only
    STATUS       current
    DESCRIPTION
        "Cisco Firepower equipment:FexEnvStatsHist:outlet2Min
        managed object property"
    ::= { cfprApEquipmentFexEnvStatsHistEntry 25 }

cfprApEquipmentFexEnvStatsHistSuspect OBJECT-TYPE
    SYNTAX       TruthValue
    MAX-ACCESS   read-only
    STATUS       current
    DESCRIPTION
        "Cisco Firepower equipment:FexEnvStatsHist:suspect
        managed object property"
    ::= { cfprApEquipmentFexEnvStatsHistEntry 26 }

cfprApEquipmentFexEnvStatsHistThresholded OBJECT-TYPE
    SYNTAX       CfprApEquipmentFexEnvStatsHistThresholded
    MAX-ACCESS   read-only
    STATUS       current
    DESCRIPTION
        "Cisco Firepower equipment:FexEnvStatsHist:thresholded
        managed object property"
    ::= { cfprApEquipmentFexEnvStatsHistEntry 27 }

cfprApEquipmentFexEnvStatsHistTimeCollected OBJECT-TYPE
    SYNTAX       DateAndTime
    MAX-ACCESS   read-only
    STATUS       current
    DESCRIPTION
        "Cisco Firepower equipment:FexEnvStatsHist:timeCollected
        managed object property"
    ::= { cfprApEquipmentFexEnvStatsHistEntry 28 }

cfprApEquipmentFexPowerSummaryTable OBJECT-TYPE
    SYNTAX           SEQUENCE OF CfprApEquipmentFexPowerSummaryEntry
    MAX-ACCESS       not-accessible
    STATUS           current
    DESCRIPTION
        "Cisco Firepower equipment:FexPowerSummary managed object table"
    ::= { cfprApEquipmentObjects 50 }

cfprApEquipmentFexPowerSummaryEntry OBJECT-TYPE
    SYNTAX           CfprApEquipmentFexPowerSummaryEntry
    MAX-ACCESS       not-accessible
    STATUS           current
    DESCRIPTION
        "Entry for the cfprApEquipmentFexPowerSummaryTable table."
    INDEX { cfprApEquipmentFexPowerSummaryInstanceId }
    ::= { cfprApEquipmentFexPowerSummaryTable 1 }

CfprApEquipmentFexPowerSummaryEntry ::= SEQUENCE {
    cfprApEquipmentFexPowerSummaryInstanceId                         CfprApManagedObjectId,
    cfprApEquipmentFexPowerSummaryDn                                 CfprApManagedObjectDn,
    cfprApEquipmentFexPowerSummaryRn                                 SnmpAdminString,
    cfprApEquipmentFexPowerSummaryModulePower                        INTEGER,
    cfprApEquipmentFexPowerSummaryModulePowerAvg                     INTEGER,
    cfprApEquipmentFexPowerSummaryModulePowerMax                     INTEGER,
    cfprApEquipmentFexPowerSummaryModulePowerMin                     INTEGER,
    cfprApEquipmentFexPowerSummaryAvailablePower                     INTEGER,
    cfprApEquipmentFexPowerSummaryAvailablePowerAvg                  INTEGER,
    cfprApEquipmentFexPowerSummaryAvailablePowerMax                  INTEGER,
    cfprApEquipmentFexPowerSummaryAvailablePowerMin                  INTEGER,
    cfprApEquipmentFexPowerSummaryIntervals                          Gauge32,
    cfprApEquipmentFexPowerSummaryReservedPower                      INTEGER,
    cfprApEquipmentFexPowerSummaryReservedPowerAvg                   INTEGER,
    cfprApEquipmentFexPowerSummaryReservedPowerMax                   INTEGER,
    cfprApEquipmentFexPowerSummaryReservedPowerMin                   INTEGER,
    cfprApEquipmentFexPowerSummarySuspect                            TruthValue,
    cfprApEquipmentFexPowerSummaryThresholded                        CfprApEquipmentFexPowerSummaryThresholded,
    cfprApEquipmentFexPowerSummaryTimeCollected                      DateAndTime,
    cfprApEquipmentFexPowerSummaryTotalPower                         INTEGER,
    cfprApEquipmentFexPowerSummaryTotalPowerAvg                      INTEGER,
    cfprApEquipmentFexPowerSummaryTotalPowerMax                      INTEGER,
    cfprApEquipmentFexPowerSummaryTotalPowerMin                      INTEGER,
    cfprApEquipmentFexPowerSummaryUpdate                             Gauge32
}

cfprApEquipmentFexPowerSummaryInstanceId OBJECT-TYPE
    SYNTAX       CfprApManagedObjectId
    MAX-ACCESS   not-accessible
    STATUS       current
    DESCRIPTION
        "Instance identifier of the managed object."
    ::= { cfprApEquipmentFexPowerSummaryEntry 1 }

cfprApEquipmentFexPowerSummaryDn OBJECT-TYPE
    SYNTAX       CfprApManagedObjectDn
    MAX-ACCESS   read-only
    STATUS       current
    DESCRIPTION
        "Cisco Firepower equipment:FexPowerSummary:dn managed
        object property"
    ::= { cfprApEquipmentFexPowerSummaryEntry 2 }

cfprApEquipmentFexPowerSummaryRn OBJECT-TYPE
    SYNTAX       SnmpAdminString
    MAX-ACCESS   read-only
    STATUS       current
    DESCRIPTION
        "Cisco Firepower equipment:FexPowerSummary:rn managed
        object property"
    ::= { cfprApEquipmentFexPowerSummaryEntry 3 }

cfprApEquipmentFexPowerSummaryModulePower OBJECT-TYPE
    SYNTAX       INTEGER
    MAX-ACCESS   read-only
    STATUS       current
    DESCRIPTION
        "Cisco Firepower equipment:FexPowerSummary:ModulePower
        managed object property"
    ::= { cfprApEquipmentFexPowerSummaryEntry 4 }

cfprApEquipmentFexPowerSummaryModulePowerAvg OBJECT-TYPE
    SYNTAX       INTEGER
    MAX-ACCESS   read-only
    STATUS       current
    DESCRIPTION
        "Cisco Firepower equipment:FexPowerSummary:ModulePowerAvg
        managed object property"
    ::= { cfprApEquipmentFexPowerSummaryEntry 5 }

cfprApEquipmentFexPowerSummaryModulePowerMax OBJECT-TYPE
    SYNTAX       INTEGER
    MAX-ACCESS   read-only
    STATUS       current
    DESCRIPTION
        "Cisco Firepower equipment:FexPowerSummary:ModulePowerMax
        managed object property"
    ::= { cfprApEquipmentFexPowerSummaryEntry 6 }

cfprApEquipmentFexPowerSummaryModulePowerMin OBJECT-TYPE
    SYNTAX       INTEGER
    MAX-ACCESS   read-only
    STATUS       current
    DESCRIPTION
        "Cisco Firepower equipment:FexPowerSummary:ModulePowerMin
        managed object property"
    ::= { cfprApEquipmentFexPowerSummaryEntry 7 }

cfprApEquipmentFexPowerSummaryAvailablePower OBJECT-TYPE
    SYNTAX       INTEGER
    MAX-ACCESS   read-only
    STATUS       current
    DESCRIPTION
        "Cisco Firepower equipment:FexPowerSummary:availablePower
        managed object property"
    ::= { cfprApEquipmentFexPowerSummaryEntry 8 }

cfprApEquipmentFexPowerSummaryAvailablePowerAvg OBJECT-TYPE
    SYNTAX       INTEGER
    MAX-ACCESS   read-only
    STATUS       current
    DESCRIPTION
        "Cisco Firepower equipment:FexPowerSummary:availablePowerAvg
        managed object property"
    ::= { cfprApEquipmentFexPowerSummaryEntry 9 }

cfprApEquipmentFexPowerSummaryAvailablePowerMax OBJECT-TYPE
    SYNTAX       INTEGER
    MAX-ACCESS   read-only
    STATUS       current
    DESCRIPTION
        "Cisco Firepower equipment:FexPowerSummary:availablePowerMax
        managed object property"
    ::= { cfprApEquipmentFexPowerSummaryEntry 10 }

cfprApEquipmentFexPowerSummaryAvailablePowerMin OBJECT-TYPE
    SYNTAX       INTEGER
    MAX-ACCESS   read-only
    STATUS       current
    DESCRIPTION
        "Cisco Firepower equipment:FexPowerSummary:availablePowerMin
        managed object property"
    ::= { cfprApEquipmentFexPowerSummaryEntry 11 }

cfprApEquipmentFexPowerSummaryIntervals OBJECT-TYPE
    SYNTAX       Gauge32
    MAX-ACCESS   read-only
    STATUS       current
    DESCRIPTION
        "Cisco Firepower equipment:FexPowerSummary:intervals
        managed object property"
    ::= { cfprApEquipmentFexPowerSummaryEntry 12 }

cfprApEquipmentFexPowerSummaryReservedPower OBJECT-TYPE
    SYNTAX       INTEGER
    MAX-ACCESS   read-only
    STATUS       current
    DESCRIPTION
        "Cisco Firepower equipment:FexPowerSummary:reservedPower
        managed object property"
    ::= { cfprApEquipmentFexPowerSummaryEntry 13 }

cfprApEquipmentFexPowerSummaryReservedPowerAvg OBJECT-TYPE
    SYNTAX       INTEGER
    MAX-ACCESS   read-only
    STATUS       current
    DESCRIPTION
        "Cisco Firepower equipment:FexPowerSummary:reservedPowerAvg
        managed object property"
    ::= { cfprApEquipmentFexPowerSummaryEntry 14 }

cfprApEquipmentFexPowerSummaryReservedPowerMax OBJECT-TYPE
    SYNTAX       INTEGER
    MAX-ACCESS   read-only
    STATUS       current
    DESCRIPTION
        "Cisco Firepower equipment:FexPowerSummary:reservedPowerMax
        managed object property"
    ::= { cfprApEquipmentFexPowerSummaryEntry 15 }

cfprApEquipmentFexPowerSummaryReservedPowerMin OBJECT-TYPE
    SYNTAX       INTEGER
    MAX-ACCESS   read-only
    STATUS       current
    DESCRIPTION
        "Cisco Firepower equipment:FexPowerSummary:reservedPowerMin
        managed object property"
    ::= { cfprApEquipmentFexPowerSummaryEntry 16 }

cfprApEquipmentFexPowerSummarySuspect OBJECT-TYPE
    SYNTAX       TruthValue
    MAX-ACCESS   read-only
    STATUS       current
    DESCRIPTION
        "Cisco Firepower equipment:FexPowerSummary:suspect
        managed object property"
    ::= { cfprApEquipmentFexPowerSummaryEntry 17 }

cfprApEquipmentFexPowerSummaryThresholded OBJECT-TYPE
    SYNTAX       CfprApEquipmentFexPowerSummaryThresholded
    MAX-ACCESS   read-only
    STATUS       current
    DESCRIPTION
        "Cisco Firepower equipment:FexPowerSummary:thresholded
        managed object property"
    ::= { cfprApEquipmentFexPowerSummaryEntry 18 }

cfprApEquipmentFexPowerSummaryTimeCollected OBJECT-TYPE
    SYNTAX       DateAndTime
    MAX-ACCESS   read-only
    STATUS       current
    DESCRIPTION
        "Cisco Firepower equipment:FexPowerSummary:timeCollected
        managed object property"
    ::= { cfprApEquipmentFexPowerSummaryEntry 19 }

cfprApEquipmentFexPowerSummaryTotalPower OBJECT-TYPE
    SYNTAX       INTEGER
    MAX-ACCESS   read-only
    STATUS       current
    DESCRIPTION
        "Cisco Firepower equipment:FexPowerSummary:totalPower
        managed object property"
    ::= { cfprApEquipmentFexPowerSummaryEntry 20 }

cfprApEquipmentFexPowerSummaryTotalPowerAvg OBJECT-TYPE
    SYNTAX       INTEGER
    MAX-ACCESS   read-only
    STATUS       current
    DESCRIPTION
        "Cisco Firepower equipment:FexPowerSummary:totalPowerAvg
        managed object property"
    ::= { cfprApEquipmentFexPowerSummaryEntry 21 }

cfprApEquipmentFexPowerSummaryTotalPowerMax OBJECT-TYPE
    SYNTAX       INTEGER
    MAX-ACCESS   read-only
    STATUS       current
    DESCRIPTION
        "Cisco Firepower equipment:FexPowerSummary:totalPowerMax
        managed object property"
    ::= { cfprApEquipmentFexPowerSummaryEntry 22 }

cfprApEquipmentFexPowerSummaryTotalPowerMin OBJECT-TYPE
    SYNTAX       INTEGER
    MAX-ACCESS   read-only
    STATUS       current
    DESCRIPTION
        "Cisco Firepower equipment:FexPowerSummary:totalPowerMin
        managed object property"
    ::= { cfprApEquipmentFexPowerSummaryEntry 23 }

cfprApEquipmentFexPowerSummaryUpdate OBJECT-TYPE
    SYNTAX       Gauge32
    MAX-ACCESS   read-only
    STATUS       current
    DESCRIPTION
        "Cisco Firepower equipment:FexPowerSummary:update
        managed object property"
    ::= { cfprApEquipmentFexPowerSummaryEntry 24 }

cfprApEquipmentFexPowerSummaryHistTable OBJECT-TYPE
    SYNTAX           SEQUENCE OF CfprApEquipmentFexPowerSummaryHistEntry
    MAX-ACCESS       not-accessible
    STATUS           current
    DESCRIPTION
        "Cisco Firepower equipment:FexPowerSummaryHist
        managed object table"
    ::= { cfprApEquipmentObjects 51 }

cfprApEquipmentFexPowerSummaryHistEntry OBJECT-TYPE
    SYNTAX           CfprApEquipmentFexPowerSummaryHistEntry
    MAX-ACCESS       not-accessible
    STATUS           current
    DESCRIPTION
        "Entry for the cfprApEquipmentFexPowerSummaryHistTable table."
    INDEX { cfprApEquipmentFexPowerSummaryHistInstanceId }
    ::= { cfprApEquipmentFexPowerSummaryHistTable 1 }

CfprApEquipmentFexPowerSummaryHistEntry ::= SEQUENCE {
    cfprApEquipmentFexPowerSummaryHistInstanceId                     CfprApManagedObjectId,
    cfprApEquipmentFexPowerSummaryHistDn                             CfprApManagedObjectDn,
    cfprApEquipmentFexPowerSummaryHistRn                             SnmpAdminString,
    cfprApEquipmentFexPowerSummaryHistModulePower                    INTEGER,
    cfprApEquipmentFexPowerSummaryHistModulePowerAvg                 INTEGER,
    cfprApEquipmentFexPowerSummaryHistModulePowerMax                 INTEGER,
    cfprApEquipmentFexPowerSummaryHistModulePowerMin                 INTEGER,
    cfprApEquipmentFexPowerSummaryHistAvailablePower                 INTEGER,
    cfprApEquipmentFexPowerSummaryHistAvailablePowerAvg              INTEGER,
    cfprApEquipmentFexPowerSummaryHistAvailablePowerMax              INTEGER,
    cfprApEquipmentFexPowerSummaryHistAvailablePowerMin              INTEGER,
    cfprApEquipmentFexPowerSummaryHistId                             Unsigned64,
    cfprApEquipmentFexPowerSummaryHistMostRecent                     TruthValue,
    cfprApEquipmentFexPowerSummaryHistReservedPower                  INTEGER,
    cfprApEquipmentFexPowerSummaryHistReservedPowerAvg               INTEGER,
    cfprApEquipmentFexPowerSummaryHistReservedPowerMax               INTEGER,
    cfprApEquipmentFexPowerSummaryHistReservedPowerMin               INTEGER,
    cfprApEquipmentFexPowerSummaryHistSuspect                        TruthValue,
    cfprApEquipmentFexPowerSummaryHistThresholded                    CfprApEquipmentFexPowerSummaryHistThresholded,
    cfprApEquipmentFexPowerSummaryHistTimeCollected                  DateAndTime,
    cfprApEquipmentFexPowerSummaryHistTotalPower                     INTEGER,
    cfprApEquipmentFexPowerSummaryHistTotalPowerAvg                  INTEGER,
    cfprApEquipmentFexPowerSummaryHistTotalPowerMax                  INTEGER,
    cfprApEquipmentFexPowerSummaryHistTotalPowerMin                  INTEGER
}

cfprApEquipmentFexPowerSummaryHistInstanceId OBJECT-TYPE
    SYNTAX       CfprApManagedObjectId
    MAX-ACCESS   not-accessible
    STATUS       current
    DESCRIPTION
        "Instance identifier of the managed object."
    ::= { cfprApEquipmentFexPowerSummaryHistEntry 1 }

cfprApEquipmentFexPowerSummaryHistDn OBJECT-TYPE
    SYNTAX       CfprApManagedObjectDn
    MAX-ACCESS   read-only
    STATUS       current
    DESCRIPTION
        "Cisco Firepower equipment:FexPowerSummaryHist:dn
        managed object property"
    ::= { cfprApEquipmentFexPowerSummaryHistEntry 2 }

cfprApEquipmentFexPowerSummaryHistRn OBJECT-TYPE
    SYNTAX       SnmpAdminString
    MAX-ACCESS   read-only
    STATUS       current
    DESCRIPTION
        "Cisco Firepower equipment:FexPowerSummaryHist:rn
        managed object property"
    ::= { cfprApEquipmentFexPowerSummaryHistEntry 3 }

cfprApEquipmentFexPowerSummaryHistModulePower OBJECT-TYPE
    SYNTAX       INTEGER
    MAX-ACCESS   read-only
    STATUS       current
    DESCRIPTION
        "Cisco Firepower equipment:FexPowerSummaryHist:ModulePower
        managed object property"
    ::= { cfprApEquipmentFexPowerSummaryHistEntry 4 }

cfprApEquipmentFexPowerSummaryHistModulePowerAvg OBJECT-TYPE
    SYNTAX       INTEGER
    MAX-ACCESS   read-only
    STATUS       current
    DESCRIPTION
        "Cisco Firepower equipment:FexPowerSummaryHist:ModulePowerAvg
        managed object property"
    ::= { cfprApEquipmentFexPowerSummaryHistEntry 5 }

cfprApEquipmentFexPowerSummaryHistModulePowerMax OBJECT-TYPE
    SYNTAX       INTEGER
    MAX-ACCESS   read-only
    STATUS       current
    DESCRIPTION
        "Cisco Firepower equipment:FexPowerSummaryHist:ModulePowerMax
        managed object property"
    ::= { cfprApEquipmentFexPowerSummaryHistEntry 6 }

cfprApEquipmentFexPowerSummaryHistModulePowerMin OBJECT-TYPE
    SYNTAX       INTEGER
    MAX-ACCESS   read-only
    STATUS       current
    DESCRIPTION
        "Cisco Firepower equipment:FexPowerSummaryHist:ModulePowerMin
        managed object property"
    ::= { cfprApEquipmentFexPowerSummaryHistEntry 7 }

cfprApEquipmentFexPowerSummaryHistAvailablePower OBJECT-TYPE
    SYNTAX       INTEGER
    MAX-ACCESS   read-only
    STATUS       current
    DESCRIPTION
        "Cisco Firepower equipment:FexPowerSummaryHist:availablePower
        managed object property"
    ::= { cfprApEquipmentFexPowerSummaryHistEntry 8 }

cfprApEquipmentFexPowerSummaryHistAvailablePowerAvg OBJECT-TYPE
    SYNTAX       INTEGER
    MAX-ACCESS   read-only
    STATUS       current
    DESCRIPTION
        "Cisco Firepower equipment:FexPowerSummaryHist:availablePowerAvg
        managed object property"
    ::= { cfprApEquipmentFexPowerSummaryHistEntry 9 }

cfprApEquipmentFexPowerSummaryHistAvailablePowerMax OBJECT-TYPE
    SYNTAX       INTEGER
    MAX-ACCESS   read-only
    STATUS       current
    DESCRIPTION
        "Cisco Firepower equipment:FexPowerSummaryHist:availablePowerMax
        managed object property"
    ::= { cfprApEquipmentFexPowerSummaryHistEntry 10 }

cfprApEquipmentFexPowerSummaryHistAvailablePowerMin OBJECT-TYPE
    SYNTAX       INTEGER
    MAX-ACCESS   read-only
    STATUS       current
    DESCRIPTION
        "Cisco Firepower equipment:FexPowerSummaryHist:availablePowerMin
        managed object property"
    ::= { cfprApEquipmentFexPowerSummaryHistEntry 11 }

cfprApEquipmentFexPowerSummaryHistId OBJECT-TYPE
    SYNTAX       Unsigned64
    MAX-ACCESS   read-only
    STATUS       current
    DESCRIPTION
        "Cisco Firepower equipment:FexPowerSummaryHist:id
        managed object property"
    ::= { cfprApEquipmentFexPowerSummaryHistEntry 12 }

cfprApEquipmentFexPowerSummaryHistMostRecent OBJECT-TYPE
    SYNTAX       TruthValue
    MAX-ACCESS   read-only
    STATUS       current
    DESCRIPTION
        "Cisco Firepower equipment:FexPowerSummaryHist:mostRecent
        managed object property"
    ::= { cfprApEquipmentFexPowerSummaryHistEntry 13 }

cfprApEquipmentFexPowerSummaryHistReservedPower OBJECT-TYPE
    SYNTAX       INTEGER
    MAX-ACCESS   read-only
    STATUS       current
    DESCRIPTION
        "Cisco Firepower equipment:FexPowerSummaryHist:reservedPower
        managed object property"
    ::= { cfprApEquipmentFexPowerSummaryHistEntry 14 }

cfprApEquipmentFexPowerSummaryHistReservedPowerAvg OBJECT-TYPE
    SYNTAX       INTEGER
    MAX-ACCESS   read-only
    STATUS       current
    DESCRIPTION
        "Cisco Firepower equipment:FexPowerSummaryHist:reservedPowerAvg
        managed object property"
    ::= { cfprApEquipmentFexPowerSummaryHistEntry 15 }

cfprApEquipmentFexPowerSummaryHistReservedPowerMax OBJECT-TYPE
    SYNTAX       INTEGER
    MAX-ACCESS   read-only
    STATUS       current
    DESCRIPTION
        "Cisco Firepower equipment:FexPowerSummaryHist:reservedPowerMax
        managed object property"
    ::= { cfprApEquipmentFexPowerSummaryHistEntry 16 }

cfprApEquipmentFexPowerSummaryHistReservedPowerMin OBJECT-TYPE
    SYNTAX       INTEGER
    MAX-ACCESS   read-only
    STATUS       current
    DESCRIPTION
        "Cisco Firepower equipment:FexPowerSummaryHist:reservedPowerMin
        managed object property"
    ::= { cfprApEquipmentFexPowerSummaryHistEntry 17 }

cfprApEquipmentFexPowerSummaryHistSuspect OBJECT-TYPE
    SYNTAX       TruthValue
    MAX-ACCESS   read-only
    STATUS       current
    DESCRIPTION
        "Cisco Firepower equipment:FexPowerSummaryHist:suspect
        managed object property"
    ::= { cfprApEquipmentFexPowerSummaryHistEntry 18 }

cfprApEquipmentFexPowerSummaryHistThresholded OBJECT-TYPE
    SYNTAX       CfprApEquipmentFexPowerSummaryHistThresholded
    MAX-ACCESS   read-only
    STATUS       current
    DESCRIPTION
        "Cisco Firepower equipment:FexPowerSummaryHist:thresholded
        managed object property"
    ::= { cfprApEquipmentFexPowerSummaryHistEntry 19 }

cfprApEquipmentFexPowerSummaryHistTimeCollected OBJECT-TYPE
    SYNTAX       DateAndTime
    MAX-ACCESS   read-only
    STATUS       current
    DESCRIPTION
        "Cisco Firepower equipment:FexPowerSummaryHist:timeCollected
        managed object property"
    ::= { cfprApEquipmentFexPowerSummaryHistEntry 20 }

cfprApEquipmentFexPowerSummaryHistTotalPower OBJECT-TYPE
    SYNTAX       INTEGER
    MAX-ACCESS   read-only
    STATUS       current
    DESCRIPTION
        "Cisco Firepower equipment:FexPowerSummaryHist:totalPower
        managed object property"
    ::= { cfprApEquipmentFexPowerSummaryHistEntry 21 }

cfprApEquipmentFexPowerSummaryHistTotalPowerAvg OBJECT-TYPE
    SYNTAX       INTEGER
    MAX-ACCESS   read-only
    STATUS       current
    DESCRIPTION
        "Cisco Firepower equipment:FexPowerSummaryHist:totalPowerAvg
        managed object property"
    ::= { cfprApEquipmentFexPowerSummaryHistEntry 22 }

cfprApEquipmentFexPowerSummaryHistTotalPowerMax OBJECT-TYPE
    SYNTAX       INTEGER
    MAX-ACCESS   read-only
    STATUS       current
    DESCRIPTION
        "Cisco Firepower equipment:FexPowerSummaryHist:totalPowerMax
        managed object property"
    ::= { cfprApEquipmentFexPowerSummaryHistEntry 23 }

cfprApEquipmentFexPowerSummaryHistTotalPowerMin OBJECT-TYPE
    SYNTAX       INTEGER
    MAX-ACCESS   read-only
    STATUS       current
    DESCRIPTION
        "Cisco Firepower equipment:FexPowerSummaryHist:totalPowerMin
        managed object property"
    ::= { cfprApEquipmentFexPowerSummaryHistEntry 24 }

cfprApEquipmentFexPsuInputStatsTable OBJECT-TYPE
    SYNTAX           SEQUENCE OF CfprApEquipmentFexPsuInputStatsEntry
    MAX-ACCESS       not-accessible
    STATUS           current
    DESCRIPTION
        "Cisco Firepower equipment:FexPsuInputStats managed object table"
    ::= { cfprApEquipmentObjects 52 }

cfprApEquipmentFexPsuInputStatsEntry OBJECT-TYPE
    SYNTAX           CfprApEquipmentFexPsuInputStatsEntry
    MAX-ACCESS       not-accessible
    STATUS           current
    DESCRIPTION
        "Entry for the cfprApEquipmentFexPsuInputStatsTable table."
    INDEX { cfprApEquipmentFexPsuInputStatsInstanceId }
    ::= { cfprApEquipmentFexPsuInputStatsTable 1 }

CfprApEquipmentFexPsuInputStatsEntry ::= SEQUENCE {
    cfprApEquipmentFexPsuInputStatsInstanceId                        CfprApManagedObjectId,
    cfprApEquipmentFexPsuInputStatsDn                                CfprApManagedObjectDn,
    cfprApEquipmentFexPsuInputStatsRn                                SnmpAdminString,
    cfprApEquipmentFexPsuInputStatsCurrent                           INTEGER,
    cfprApEquipmentFexPsuInputStatsCurrentAvg                        INTEGER,
    cfprApEquipmentFexPsuInputStatsCurrentMax                        INTEGER,
    cfprApEquipmentFexPsuInputStatsCurrentMin                        INTEGER,
    cfprApEquipmentFexPsuInputStatsInputStatus                       SnmpAdminString,
    cfprApEquipmentFexPsuInputStatsIntervals                         Gauge32,
    cfprApEquipmentFexPsuInputStatsPower                             INTEGER,
    cfprApEquipmentFexPsuInputStatsPowerAvg                          INTEGER,
    cfprApEquipmentFexPsuInputStatsPowerMax                          INTEGER,
    cfprApEquipmentFexPsuInputStatsPowerMin                          INTEGER,
    cfprApEquipmentFexPsuInputStatsSuspect                           TruthValue,
    cfprApEquipmentFexPsuInputStatsThresholded                       CfprApEquipmentFexPsuInputStatsThresholded,
    cfprApEquipmentFexPsuInputStatsTimeCollected                     DateAndTime,
    cfprApEquipmentFexPsuInputStatsUpdate                            Gauge32,
    cfprApEquipmentFexPsuInputStatsVoltage                           INTEGER,
    cfprApEquipmentFexPsuInputStatsVoltageAvg                        INTEGER,
    cfprApEquipmentFexPsuInputStatsVoltageMax                        INTEGER,
    cfprApEquipmentFexPsuInputStatsVoltageMin                        INTEGER
}

cfprApEquipmentFexPsuInputStatsInstanceId OBJECT-TYPE
    SYNTAX       CfprApManagedObjectId
    MAX-ACCESS   not-accessible
    STATUS       current
    DESCRIPTION
        "Instance identifier of the managed object."
    ::= { cfprApEquipmentFexPsuInputStatsEntry 1 }

cfprApEquipmentFexPsuInputStatsDn OBJECT-TYPE
    SYNTAX       CfprApManagedObjectDn
    MAX-ACCESS   read-only
    STATUS       current
    DESCRIPTION
        "Cisco Firepower equipment:FexPsuInputStats:dn
        managed object property"
    ::= { cfprApEquipmentFexPsuInputStatsEntry 2 }

cfprApEquipmentFexPsuInputStatsRn OBJECT-TYPE
    SYNTAX       SnmpAdminString
    MAX-ACCESS   read-only
    STATUS       current
    DESCRIPTION
        "Cisco Firepower equipment:FexPsuInputStats:rn
        managed object property"
    ::= { cfprApEquipmentFexPsuInputStatsEntry 3 }

cfprApEquipmentFexPsuInputStatsCurrent OBJECT-TYPE
    SYNTAX       INTEGER
    MAX-ACCESS   read-only
    STATUS       current
    DESCRIPTION
        "Cisco Firepower equipment:FexPsuInputStats:current
        managed object property"
    ::= { cfprApEquipmentFexPsuInputStatsEntry 4 }

cfprApEquipmentFexPsuInputStatsCurrentAvg OBJECT-TYPE
    SYNTAX       INTEGER
    MAX-ACCESS   read-only
    STATUS       current
    DESCRIPTION
        "Cisco Firepower equipment:FexPsuInputStats:currentAvg
        managed object property"
    ::= { cfprApEquipmentFexPsuInputStatsEntry 5 }

cfprApEquipmentFexPsuInputStatsCurrentMax OBJECT-TYPE
    SYNTAX       INTEGER
    MAX-ACCESS   read-only
    STATUS       current
    DESCRIPTION
        "Cisco Firepower equipment:FexPsuInputStats:currentMax
        managed object property"
    ::= { cfprApEquipmentFexPsuInputStatsEntry 6 }

cfprApEquipmentFexPsuInputStatsCurrentMin OBJECT-TYPE
    SYNTAX       INTEGER
    MAX-ACCESS   read-only
    STATUS       current
    DESCRIPTION
        "Cisco Firepower equipment:FexPsuInputStats:currentMin
        managed object property"
    ::= { cfprApEquipmentFexPsuInputStatsEntry 7 }

cfprApEquipmentFexPsuInputStatsInputStatus OBJECT-TYPE
    SYNTAX       SnmpAdminString
    MAX-ACCESS   read-only
    STATUS       current
    DESCRIPTION
        "Cisco Firepower equipment:FexPsuInputStats:inputStatus
        managed object property"
    ::= { cfprApEquipmentFexPsuInputStatsEntry 8 }

cfprApEquipmentFexPsuInputStatsIntervals OBJECT-TYPE
    SYNTAX       Gauge32
    MAX-ACCESS   read-only
    STATUS       current
    DESCRIPTION
        "Cisco Firepower equipment:FexPsuInputStats:intervals
        managed object property"
    ::= { cfprApEquipmentFexPsuInputStatsEntry 9 }

cfprApEquipmentFexPsuInputStatsPower OBJECT-TYPE
    SYNTAX       INTEGER
    MAX-ACCESS   read-only
    STATUS       current
    DESCRIPTION
        "Cisco Firepower equipment:FexPsuInputStats:power
        managed object property"
    ::= { cfprApEquipmentFexPsuInputStatsEntry 10 }

cfprApEquipmentFexPsuInputStatsPowerAvg OBJECT-TYPE
    SYNTAX       INTEGER
    MAX-ACCESS   read-only
    STATUS       current
    DESCRIPTION
        "Cisco Firepower equipment:FexPsuInputStats:powerAvg
        managed object property"
    ::= { cfprApEquipmentFexPsuInputStatsEntry 11 }

cfprApEquipmentFexPsuInputStatsPowerMax OBJECT-TYPE
    SYNTAX       INTEGER
    MAX-ACCESS   read-only
    STATUS       current
    DESCRIPTION
        "Cisco Firepower equipment:FexPsuInputStats:powerMax
        managed object property"
    ::= { cfprApEquipmentFexPsuInputStatsEntry 12 }

cfprApEquipmentFexPsuInputStatsPowerMin OBJECT-TYPE
    SYNTAX       INTEGER
    MAX-ACCESS   read-only
    STATUS       current
    DESCRIPTION
        "Cisco Firepower equipment:FexPsuInputStats:powerMin
        managed object property"
    ::= { cfprApEquipmentFexPsuInputStatsEntry 13 }

cfprApEquipmentFexPsuInputStatsSuspect OBJECT-TYPE
    SYNTAX       TruthValue
    MAX-ACCESS   read-only
    STATUS       current
    DESCRIPTION
        "Cisco Firepower equipment:FexPsuInputStats:suspect
        managed object property"
    ::= { cfprApEquipmentFexPsuInputStatsEntry 14 }

cfprApEquipmentFexPsuInputStatsThresholded OBJECT-TYPE
    SYNTAX       CfprApEquipmentFexPsuInputStatsThresholded
    MAX-ACCESS   read-only
    STATUS       current
    DESCRIPTION
        "Cisco Firepower equipment:FexPsuInputStats:thresholded
        managed object property"
    ::= { cfprApEquipmentFexPsuInputStatsEntry 15 }

cfprApEquipmentFexPsuInputStatsTimeCollected OBJECT-TYPE
    SYNTAX       DateAndTime
    MAX-ACCESS   read-only
    STATUS       current
    DESCRIPTION
        "Cisco Firepower equipment:FexPsuInputStats:timeCollected
        managed object property"
    ::= { cfprApEquipmentFexPsuInputStatsEntry 16 }

cfprApEquipmentFexPsuInputStatsUpdate OBJECT-TYPE
    SYNTAX       Gauge32
    MAX-ACCESS   read-only
    STATUS       current
    DESCRIPTION
        "Cisco Firepower equipment:FexPsuInputStats:update
        managed object property"
    ::= { cfprApEquipmentFexPsuInputStatsEntry 17 }

cfprApEquipmentFexPsuInputStatsVoltage OBJECT-TYPE
    SYNTAX       INTEGER
    MAX-ACCESS   read-only
    STATUS       current
    DESCRIPTION
        "Cisco Firepower equipment:FexPsuInputStats:voltage
        managed object property"
    ::= { cfprApEquipmentFexPsuInputStatsEntry 18 }

cfprApEquipmentFexPsuInputStatsVoltageAvg OBJECT-TYPE
    SYNTAX       INTEGER
    MAX-ACCESS   read-only
    STATUS       current
    DESCRIPTION
        "Cisco Firepower equipment:FexPsuInputStats:voltageAvg
        managed object property"
    ::= { cfprApEquipmentFexPsuInputStatsEntry 19 }

cfprApEquipmentFexPsuInputStatsVoltageMax OBJECT-TYPE
    SYNTAX       INTEGER
    MAX-ACCESS   read-only
    STATUS       current
    DESCRIPTION
        "Cisco Firepower equipment:FexPsuInputStats:voltageMax
        managed object property"
    ::= { cfprApEquipmentFexPsuInputStatsEntry 20 }

cfprApEquipmentFexPsuInputStatsVoltageMin OBJECT-TYPE
    SYNTAX       INTEGER
    MAX-ACCESS   read-only
    STATUS       current
    DESCRIPTION
        "Cisco Firepower equipment:FexPsuInputStats:voltageMin
        managed object property"
    ::= { cfprApEquipmentFexPsuInputStatsEntry 21 }

cfprApEquipmentFexPsuInputStatsHistTable OBJECT-TYPE
    SYNTAX           SEQUENCE OF CfprApEquipmentFexPsuInputStatsHistEntry
    MAX-ACCESS       not-accessible
    STATUS           current
    DESCRIPTION
        "Cisco Firepower equipment:FexPsuInputStatsHist
        managed object table"
    ::= { cfprApEquipmentObjects 53 }

cfprApEquipmentFexPsuInputStatsHistEntry OBJECT-TYPE
    SYNTAX           CfprApEquipmentFexPsuInputStatsHistEntry
    MAX-ACCESS       not-accessible
    STATUS           current
    DESCRIPTION
        "Entry for the cfprApEquipmentFexPsuInputStatsHistTable table."
    INDEX { cfprApEquipmentFexPsuInputStatsHistInstanceId }
    ::= { cfprApEquipmentFexPsuInputStatsHistTable 1 }

CfprApEquipmentFexPsuInputStatsHistEntry ::= SEQUENCE {
    cfprApEquipmentFexPsuInputStatsHistInstanceId                    CfprApManagedObjectId,
    cfprApEquipmentFexPsuInputStatsHistDn                            CfprApManagedObjectDn,
    cfprApEquipmentFexPsuInputStatsHistRn                            SnmpAdminString,
    cfprApEquipmentFexPsuInputStatsHistCurrent                       INTEGER,
    cfprApEquipmentFexPsuInputStatsHistCurrentAvg                    INTEGER,
    cfprApEquipmentFexPsuInputStatsHistCurrentMax                    INTEGER,
    cfprApEquipmentFexPsuInputStatsHistCurrentMin                    INTEGER,
    cfprApEquipmentFexPsuInputStatsHistId                            Unsigned64,
    cfprApEquipmentFexPsuInputStatsHistMostRecent                    TruthValue,
    cfprApEquipmentFexPsuInputStatsHistPower                         INTEGER,
    cfprApEquipmentFexPsuInputStatsHistPowerAvg                      INTEGER,
    cfprApEquipmentFexPsuInputStatsHistPowerMax                      INTEGER,
    cfprApEquipmentFexPsuInputStatsHistPowerMin                      INTEGER,
    cfprApEquipmentFexPsuInputStatsHistSuspect                       TruthValue,
    cfprApEquipmentFexPsuInputStatsHistThresholded                   CfprApEquipmentFexPsuInputStatsHistThresholded,
    cfprApEquipmentFexPsuInputStatsHistTimeCollected                 DateAndTime,
    cfprApEquipmentFexPsuInputStatsHistVoltage                       INTEGER,
    cfprApEquipmentFexPsuInputStatsHistVoltageAvg                    INTEGER,
    cfprApEquipmentFexPsuInputStatsHistVoltageMax                    INTEGER,
    cfprApEquipmentFexPsuInputStatsHistVoltageMin                    INTEGER
}

cfprApEquipmentFexPsuInputStatsHistInstanceId OBJECT-TYPE
    SYNTAX       CfprApManagedObjectId
    MAX-ACCESS   not-accessible
    STATUS       current
    DESCRIPTION
        "Instance identifier of the managed object."
    ::= { cfprApEquipmentFexPsuInputStatsHistEntry 1 }

cfprApEquipmentFexPsuInputStatsHistDn OBJECT-TYPE
    SYNTAX       CfprApManagedObjectDn
    MAX-ACCESS   read-only
    STATUS       current
    DESCRIPTION
        "Cisco Firepower equipment:FexPsuInputStatsHist:dn
        managed object property"
    ::= { cfprApEquipmentFexPsuInputStatsHistEntry 2 }

cfprApEquipmentFexPsuInputStatsHistRn OBJECT-TYPE
    SYNTAX       SnmpAdminString
    MAX-ACCESS   read-only
    STATUS       current
    DESCRIPTION
        "Cisco Firepower equipment:FexPsuInputStatsHist:rn
        managed object property"
    ::= { cfprApEquipmentFexPsuInputStatsHistEntry 3 }

cfprApEquipmentFexPsuInputStatsHistCurrent OBJECT-TYPE
    SYNTAX       INTEGER
    MAX-ACCESS   read-only
    STATUS       current
    DESCRIPTION
        "Cisco Firepower equipment:FexPsuInputStatsHist:current
        managed object property"
    ::= { cfprApEquipmentFexPsuInputStatsHistEntry 4 }

cfprApEquipmentFexPsuInputStatsHistCurrentAvg OBJECT-TYPE
    SYNTAX       INTEGER
    MAX-ACCESS   read-only
    STATUS       current
    DESCRIPTION
        "Cisco Firepower equipment:FexPsuInputStatsHist:currentAvg
        managed object property"
    ::= { cfprApEquipmentFexPsuInputStatsHistEntry 5 }

cfprApEquipmentFexPsuInputStatsHistCurrentMax OBJECT-TYPE
    SYNTAX       INTEGER
    MAX-ACCESS   read-only
    STATUS       current
    DESCRIPTION
        "Cisco Firepower equipment:FexPsuInputStatsHist:currentMax
        managed object property"
    ::= { cfprApEquipmentFexPsuInputStatsHistEntry 6 }

cfprApEquipmentFexPsuInputStatsHistCurrentMin OBJECT-TYPE
    SYNTAX       INTEGER
    MAX-ACCESS   read-only
    STATUS       current
    DESCRIPTION
        "Cisco Firepower equipment:FexPsuInputStatsHist:currentMin
        managed object property"
    ::= { cfprApEquipmentFexPsuInputStatsHistEntry 7 }

cfprApEquipmentFexPsuInputStatsHistId OBJECT-TYPE
    SYNTAX       Unsigned64
    MAX-ACCESS   read-only
    STATUS       current
    DESCRIPTION
        "Cisco Firepower equipment:FexPsuInputStatsHist:id
        managed object property"
    ::= { cfprApEquipmentFexPsuInputStatsHistEntry 8 }

cfprApEquipmentFexPsuInputStatsHistMostRecent OBJECT-TYPE
    SYNTAX       TruthValue
    MAX-ACCESS   read-only
    STATUS       current
    DESCRIPTION
        "Cisco Firepower equipment:FexPsuInputStatsHist:mostRecent
        managed object property"
    ::= { cfprApEquipmentFexPsuInputStatsHistEntry 9 }

cfprApEquipmentFexPsuInputStatsHistPower OBJECT-TYPE
    SYNTAX       INTEGER
    MAX-ACCESS   read-only
    STATUS       current
    DESCRIPTION
        "Cisco Firepower equipment:FexPsuInputStatsHist:power
        managed object property"
    ::= { cfprApEquipmentFexPsuInputStatsHistEntry 10 }

cfprApEquipmentFexPsuInputStatsHistPowerAvg OBJECT-TYPE
    SYNTAX       INTEGER
    MAX-ACCESS   read-only
    STATUS       current
    DESCRIPTION
        "Cisco Firepower equipment:FexPsuInputStatsHist:powerAvg
        managed object property"
    ::= { cfprApEquipmentFexPsuInputStatsHistEntry 11 }

cfprApEquipmentFexPsuInputStatsHistPowerMax OBJECT-TYPE
    SYNTAX       INTEGER
    MAX-ACCESS   read-only
    STATUS       current
    DESCRIPTION
        "Cisco Firepower equipment:FexPsuInputStatsHist:powerMax
        managed object property"
    ::= { cfprApEquipmentFexPsuInputStatsHistEntry 12 }

cfprApEquipmentFexPsuInputStatsHistPowerMin OBJECT-TYPE
    SYNTAX       INTEGER
    MAX-ACCESS   read-only
    STATUS       current
    DESCRIPTION
        "Cisco Firepower equipment:FexPsuInputStatsHist:powerMin
        managed object property"
    ::= { cfprApEquipmentFexPsuInputStatsHistEntry 13 }

cfprApEquipmentFexPsuInputStatsHistSuspect OBJECT-TYPE
    SYNTAX       TruthValue
    MAX-ACCESS   read-only
    STATUS       current
    DESCRIPTION
        "Cisco Firepower equipment:FexPsuInputStatsHist:suspect
        managed object property"
    ::= { cfprApEquipmentFexPsuInputStatsHistEntry 14 }

cfprApEquipmentFexPsuInputStatsHistThresholded OBJECT-TYPE
    SYNTAX       CfprApEquipmentFexPsuInputStatsHistThresholded
    MAX-ACCESS   read-only
    STATUS       current
    DESCRIPTION
        "Cisco Firepower equipment:FexPsuInputStatsHist:thresholded
        managed object property"
    ::= { cfprApEquipmentFexPsuInputStatsHistEntry 15 }

cfprApEquipmentFexPsuInputStatsHistTimeCollected OBJECT-TYPE
    SYNTAX       DateAndTime
    MAX-ACCESS   read-only
    STATUS       current
    DESCRIPTION
        "Cisco Firepower equipment:FexPsuInputStatsHist:timeCollected
        managed object property"
    ::= { cfprApEquipmentFexPsuInputStatsHistEntry 16 }

cfprApEquipmentFexPsuInputStatsHistVoltage OBJECT-TYPE
    SYNTAX       INTEGER
    MAX-ACCESS   read-only
    STATUS       current
    DESCRIPTION
        "Cisco Firepower equipment:FexPsuInputStatsHist:voltage
        managed object property"
    ::= { cfprApEquipmentFexPsuInputStatsHistEntry 17 }

cfprApEquipmentFexPsuInputStatsHistVoltageAvg OBJECT-TYPE
    SYNTAX       INTEGER
    MAX-ACCESS   read-only
    STATUS       current
    DESCRIPTION
        "Cisco Firepower equipment:FexPsuInputStatsHist:voltageAvg
        managed object property"
    ::= { cfprApEquipmentFexPsuInputStatsHistEntry 18 }

cfprApEquipmentFexPsuInputStatsHistVoltageMax OBJECT-TYPE
    SYNTAX       INTEGER
    MAX-ACCESS   read-only
    STATUS       current
    DESCRIPTION
        "Cisco Firepower equipment:FexPsuInputStatsHist:voltageMax
        managed object property"
    ::= { cfprApEquipmentFexPsuInputStatsHistEntry 19 }

cfprApEquipmentFexPsuInputStatsHistVoltageMin OBJECT-TYPE
    SYNTAX       INTEGER
    MAX-ACCESS   read-only
    STATUS       current
    DESCRIPTION
        "Cisco Firepower equipment:FexPsuInputStatsHist:voltageMin
        managed object property"
    ::= { cfprApEquipmentFexPsuInputStatsHistEntry 20 }

cfprApEquipmentFirmwareConstraintTable OBJECT-TYPE
    SYNTAX           SEQUENCE OF CfprApEquipmentFirmwareConstraintEntry
    MAX-ACCESS       not-accessible
    STATUS           current
    DESCRIPTION
        "Cisco Firepower equipment:FirmwareConstraint managed
        object table"
    ::= { cfprApEquipmentObjects 54 }

cfprApEquipmentFirmwareConstraintEntry OBJECT-TYPE
    SYNTAX           CfprApEquipmentFirmwareConstraintEntry
    MAX-ACCESS       not-accessible
    STATUS           current
    DESCRIPTION
        "Entry for the cfprApEquipmentFirmwareConstraintTable table."
    INDEX { cfprApEquipmentFirmwareConstraintInstanceId }
    ::= { cfprApEquipmentFirmwareConstraintTable 1 }

CfprApEquipmentFirmwareConstraintEntry ::= SEQUENCE {
    cfprApEquipmentFirmwareConstraintInstanceId                      CfprApManagedObjectId,
    cfprApEquipmentFirmwareConstraintDn                              CfprApManagedObjectDn,
    cfprApEquipmentFirmwareConstraintRn                              SnmpAdminString,
    cfprApEquipmentFirmwareConstraintMinVer1                         SnmpAdminString,
    cfprApEquipmentFirmwareConstraintMinVer2                         SnmpAdminString
}

cfprApEquipmentFirmwareConstraintInstanceId OBJECT-TYPE
    SYNTAX       CfprApManagedObjectId
    MAX-ACCESS   not-accessible
    STATUS       current
    DESCRIPTION
        "Instance identifier of the managed object."
    ::= { cfprApEquipmentFirmwareConstraintEntry 1 }

cfprApEquipmentFirmwareConstraintDn OBJECT-TYPE
    SYNTAX       CfprApManagedObjectDn
    MAX-ACCESS   read-only
    STATUS       current
    DESCRIPTION
        "Cisco Firepower equipment:FirmwareConstraint:dn
        managed object property"
    ::= { cfprApEquipmentFirmwareConstraintEntry 2 }

cfprApEquipmentFirmwareConstraintRn OBJECT-TYPE
    SYNTAX       SnmpAdminString
    MAX-ACCESS   read-only
    STATUS       current
    DESCRIPTION
        "Cisco Firepower equipment:FirmwareConstraint:rn
        managed object property"
    ::= { cfprApEquipmentFirmwareConstraintEntry 3 }

cfprApEquipmentFirmwareConstraintMinVer1 OBJECT-TYPE
    SYNTAX       SnmpAdminString
    MAX-ACCESS   read-only
    STATUS       current
    DESCRIPTION
        "Cisco Firepower equipment:FirmwareConstraint:minVer1
        managed object property"
    ::= { cfprApEquipmentFirmwareConstraintEntry 4 }

cfprApEquipmentFirmwareConstraintMinVer2 OBJECT-TYPE
    SYNTAX       SnmpAdminString
    MAX-ACCESS   read-only
    STATUS       current
    DESCRIPTION
        "Cisco Firepower equipment:FirmwareConstraint:minVer2
        managed object property"
    ::= { cfprApEquipmentFirmwareConstraintEntry 5 }

cfprApEquipmentFlashLifeTable OBJECT-TYPE
    SYNTAX           SEQUENCE OF CfprApEquipmentFlashLifeEntry
    MAX-ACCESS       not-accessible
    STATUS           current
    DESCRIPTION
        "Cisco Firepower equipment:FlashLife managed object table"
    ::= { cfprApEquipmentObjects 55 }

cfprApEquipmentFlashLifeEntry OBJECT-TYPE
    SYNTAX           CfprApEquipmentFlashLifeEntry
    MAX-ACCESS       not-accessible
    STATUS           current
    DESCRIPTION
        "Entry for the cfprApEquipmentFlashLifeTable table."
    INDEX { cfprApEquipmentFlashLifeInstanceId }
    ::= { cfprApEquipmentFlashLifeTable 1 }

CfprApEquipmentFlashLifeEntry ::= SEQUENCE {
    cfprApEquipmentFlashLifeInstanceId                               CfprApManagedObjectId,
    cfprApEquipmentFlashLifeDn                                       CfprApManagedObjectDn,
    cfprApEquipmentFlashLifeRn                                       SnmpAdminString,
    cfprApEquipmentFlashLifeCardParamType                            Gauge32,
    cfprApEquipmentFlashLifeDescr                                    SnmpAdminString,
    cfprApEquipmentFlashLifeIntId                                    SnmpAdminString,
    cfprApEquipmentFlashLifeName                                     SnmpAdminString,
    cfprApEquipmentFlashLifePolicyLevel                              Gauge32,
    cfprApEquipmentFlashLifePolicyOwner                              CfprApPolicyPolicyOwner,
    cfprApEquipmentFlashLifeSuportType                               Gauge32
}

cfprApEquipmentFlashLifeInstanceId OBJECT-TYPE
    SYNTAX       CfprApManagedObjectId
    MAX-ACCESS   not-accessible
    STATUS       current
    DESCRIPTION
        "Instance identifier of the managed object."
    ::= { cfprApEquipmentFlashLifeEntry 1 }

cfprApEquipmentFlashLifeDn OBJECT-TYPE
    SYNTAX       CfprApManagedObjectDn
    MAX-ACCESS   read-only
    STATUS       current
    DESCRIPTION
        "Cisco Firepower equipment:FlashLife:dn managed object property"
    ::= { cfprApEquipmentFlashLifeEntry 2 }

cfprApEquipmentFlashLifeRn OBJECT-TYPE
    SYNTAX       SnmpAdminString
    MAX-ACCESS   read-only
    STATUS       current
    DESCRIPTION
        "Cisco Firepower equipment:FlashLife:rn managed object property"
    ::= { cfprApEquipmentFlashLifeEntry 3 }

cfprApEquipmentFlashLifeCardParamType OBJECT-TYPE
    SYNTAX       Gauge32
    MAX-ACCESS   read-only
    STATUS       current
    DESCRIPTION
        "Cisco Firepower equipment:FlashLife:cardParamType
        managed object property"
    ::= { cfprApEquipmentFlashLifeEntry 4 }

cfprApEquipmentFlashLifeDescr OBJECT-TYPE
    SYNTAX       SnmpAdminString
    MAX-ACCESS   read-only
    STATUS       current
    DESCRIPTION
        "Cisco Firepower equipment:FlashLife:descr managed
        object property"
    ::= { cfprApEquipmentFlashLifeEntry 5 }

cfprApEquipmentFlashLifeIntId OBJECT-TYPE
    SYNTAX       SnmpAdminString
    MAX-ACCESS   read-only
    STATUS       current
    DESCRIPTION
        "Cisco Firepower equipment:FlashLife:intId managed
        object property"
    ::= { cfprApEquipmentFlashLifeEntry 6 }

cfprApEquipmentFlashLifeName OBJECT-TYPE
    SYNTAX       SnmpAdminString
    MAX-ACCESS   read-only
    STATUS       current
    DESCRIPTION
        "Cisco Firepower equipment:FlashLife:name managed object property"
    ::= { cfprApEquipmentFlashLifeEntry 7 }

cfprApEquipmentFlashLifePolicyLevel OBJECT-TYPE
    SYNTAX       Gauge32
    MAX-ACCESS   read-only
    STATUS       current
    DESCRIPTION
        "Cisco Firepower equipment:FlashLife:policyLevel
        managed object property"
    ::= { cfprApEquipmentFlashLifeEntry 8 }

cfprApEquipmentFlashLifePolicyOwner OBJECT-TYPE
    SYNTAX       CfprApPolicyPolicyOwner
    MAX-ACCESS   read-only
    STATUS       current
    DESCRIPTION
        "Cisco Firepower equipment:FlashLife:policyOwner
        managed object property"
    ::= { cfprApEquipmentFlashLifeEntry 9 }

cfprApEquipmentFlashLifeSuportType OBJECT-TYPE
    SYNTAX       Gauge32
    MAX-ACCESS   read-only
    STATUS       current
    DESCRIPTION
        "Cisco Firepower equipment:FlashLife:suportType
        managed object property"
    ::= { cfprApEquipmentFlashLifeEntry 10 }

cfprApEquipmentFpgaTable OBJECT-TYPE
    SYNTAX           SEQUENCE OF CfprApEquipmentFpgaEntry
    MAX-ACCESS       not-accessible
    STATUS           current
    DESCRIPTION
        "Cisco Firepower equipment:Fpga managed object table"
    ::= { cfprApEquipmentObjects 56 }

cfprApEquipmentFpgaEntry OBJECT-TYPE
    SYNTAX           CfprApEquipmentFpgaEntry
    MAX-ACCESS       not-accessible
    STATUS           current
    DESCRIPTION
        "Entry for the cfprApEquipmentFpgaTable table."
    INDEX { cfprApEquipmentFpgaInstanceId }
    ::= { cfprApEquipmentFpgaTable 1 }

CfprApEquipmentFpgaEntry ::= SEQUENCE {
    cfprApEquipmentFpgaInstanceId                                    CfprApManagedObjectId,
    cfprApEquipmentFpgaDn                                            CfprApManagedObjectDn,
    cfprApEquipmentFpgaRn                                            SnmpAdminString,
    cfprApEquipmentFpgaBkupPackageVersion                            SnmpAdminString,
    cfprApEquipmentFpgaBkupVersion                                   SnmpAdminString,
    cfprApEquipmentFpgaFltAggr                                       Unsigned64,
    cfprApEquipmentFpgaModel                                         SnmpAdminString,
    cfprApEquipmentFpgaRevision                                      SnmpAdminString,
    cfprApEquipmentFpgaSerial                                        SnmpAdminString,
    cfprApEquipmentFpgaUpgradeStatus                                 SnmpAdminString,
    cfprApEquipmentFpgaVendor                                        SnmpAdminString
}

cfprApEquipmentFpgaInstanceId OBJECT-TYPE
    SYNTAX       CfprApManagedObjectId
    MAX-ACCESS   not-accessible
    STATUS       current
    DESCRIPTION
        "Instance identifier of the managed object."
    ::= { cfprApEquipmentFpgaEntry 1 }

cfprApEquipmentFpgaDn OBJECT-TYPE
    SYNTAX       CfprApManagedObjectDn
    MAX-ACCESS   read-only
    STATUS       current
    DESCRIPTION
        "Cisco Firepower equipment:Fpga:dn managed object property"
    ::= { cfprApEquipmentFpgaEntry 2 }

cfprApEquipmentFpgaRn OBJECT-TYPE
    SYNTAX       SnmpAdminString
    MAX-ACCESS   read-only
    STATUS       current
    DESCRIPTION
        "Cisco Firepower equipment:Fpga:rn managed object property"
    ::= { cfprApEquipmentFpgaEntry 3 }

cfprApEquipmentFpgaBkupPackageVersion OBJECT-TYPE
    SYNTAX       SnmpAdminString
    MAX-ACCESS   read-only
    STATUS       current
    DESCRIPTION
        "Cisco Firepower equipment:Fpga:bkupPackageVersion
        managed object property"
    ::= { cfprApEquipmentFpgaEntry 4 }

cfprApEquipmentFpgaBkupVersion OBJECT-TYPE
    SYNTAX       SnmpAdminString
    MAX-ACCESS   read-only
    STATUS       current
    DESCRIPTION
        "Cisco Firepower equipment:Fpga:bkupVersion managed
        object property"
    ::= { cfprApEquipmentFpgaEntry 5 }

cfprApEquipmentFpgaFltAggr OBJECT-TYPE
    SYNTAX       Unsigned64
    MAX-ACCESS   read-only
    STATUS       current
    DESCRIPTION
        "Cisco Firepower equipment:Fpga:fltAggr managed object property"
    ::= { cfprApEquipmentFpgaEntry 6 }

cfprApEquipmentFpgaModel OBJECT-TYPE
    SYNTAX       SnmpAdminString
    MAX-ACCESS   read-only
    STATUS       current
    DESCRIPTION
        "Cisco Firepower equipment:Fpga:model managed object property"
    ::= { cfprApEquipmentFpgaEntry 7 }

cfprApEquipmentFpgaRevision OBJECT-TYPE
    SYNTAX       SnmpAdminString
    MAX-ACCESS   read-only
    STATUS       current
    DESCRIPTION
        "Cisco Firepower equipment:Fpga:revision managed object property"
    ::= { cfprApEquipmentFpgaEntry 8 }

cfprApEquipmentFpgaSerial OBJECT-TYPE
    SYNTAX       SnmpAdminString
    MAX-ACCESS   read-only
    STATUS       current
    DESCRIPTION
        "Cisco Firepower equipment:Fpga:serial managed object property"
    ::= { cfprApEquipmentFpgaEntry 9 }

cfprApEquipmentFpgaUpgradeStatus OBJECT-TYPE
    SYNTAX       SnmpAdminString
    MAX-ACCESS   read-only
    STATUS       current
    DESCRIPTION
        "Cisco Firepower equipment:Fpga:upgradeStatus managed
        object property"
    ::= { cfprApEquipmentFpgaEntry 10 }

cfprApEquipmentFpgaVendor OBJECT-TYPE
    SYNTAX       SnmpAdminString
    MAX-ACCESS   read-only
    STATUS       current
    DESCRIPTION
        "Cisco Firepower equipment:Fpga:vendor managed object property"
    ::= { cfprApEquipmentFpgaEntry 11 }

cfprApEquipmentGemCapProviderTable OBJECT-TYPE
    SYNTAX           SEQUENCE OF CfprApEquipmentGemCapProviderEntry
    MAX-ACCESS       not-accessible
    STATUS           current
    DESCRIPTION
        "Cisco Firepower equipment:GemCapProvider managed object table"
    ::= { cfprApEquipmentObjects 57 }

cfprApEquipmentGemCapProviderEntry OBJECT-TYPE
    SYNTAX           CfprApEquipmentGemCapProviderEntry
    MAX-ACCESS       not-accessible
    STATUS           current
    DESCRIPTION
        "Entry for the cfprApEquipmentGemCapProviderTable table."
    INDEX { cfprApEquipmentGemCapProviderInstanceId }
    ::= { cfprApEquipmentGemCapProviderTable 1 }

CfprApEquipmentGemCapProviderEntry ::= SEQUENCE {
    cfprApEquipmentGemCapProviderInstanceId                          CfprApManagedObjectId,
    cfprApEquipmentGemCapProviderDn                                  CfprApManagedObjectDn,
    cfprApEquipmentGemCapProviderRn                                  SnmpAdminString,
    cfprApEquipmentGemCapProviderDeleted                             TruthValue,
    cfprApEquipmentGemCapProviderDeprecated                          TruthValue,
    cfprApEquipmentGemCapProviderElementLoadFailures                 Gauge32,
    cfprApEquipmentGemCapProviderElementsLoaded                      Gauge32,
    cfprApEquipmentGemCapProviderGencount                            Gauge32,
    cfprApEquipmentGemCapProviderLoadErrors                          Gauge32,
    cfprApEquipmentGemCapProviderLoadWarnings                        Gauge32,
    cfprApEquipmentGemCapProviderMgmtPlaneVer                        SnmpAdminString,
    cfprApEquipmentGemCapProviderModel                               SnmpAdminString,
    cfprApEquipmentGemCapProviderPromCardType                        Gauge32,
    cfprApEquipmentGemCapProviderRevision                            SnmpAdminString,
    cfprApEquipmentGemCapProviderVendor                              SnmpAdminString
}

cfprApEquipmentGemCapProviderInstanceId OBJECT-TYPE
    SYNTAX       CfprApManagedObjectId
    MAX-ACCESS   not-accessible
    STATUS       current
    DESCRIPTION
        "Instance identifier of the managed object."
    ::= { cfprApEquipmentGemCapProviderEntry 1 }

cfprApEquipmentGemCapProviderDn OBJECT-TYPE
    SYNTAX       CfprApManagedObjectDn
    MAX-ACCESS   read-only
    STATUS       current
    DESCRIPTION
        "Cisco Firepower equipment:GemCapProvider:dn managed
        object property"
    ::= { cfprApEquipmentGemCapProviderEntry 2 }

cfprApEquipmentGemCapProviderRn OBJECT-TYPE
    SYNTAX       SnmpAdminString
    MAX-ACCESS   read-only
    STATUS       current
    DESCRIPTION
        "Cisco Firepower equipment:GemCapProvider:rn managed
        object property"
    ::= { cfprApEquipmentGemCapProviderEntry 3 }

cfprApEquipmentGemCapProviderDeleted OBJECT-TYPE
    SYNTAX       TruthValue
    MAX-ACCESS   read-only
    STATUS       current
    DESCRIPTION
        "Cisco Firepower equipment:GemCapProvider:deleted
        managed object property"
    ::= { cfprApEquipmentGemCapProviderEntry 4 }

cfprApEquipmentGemCapProviderDeprecated OBJECT-TYPE
    SYNTAX       TruthValue
    MAX-ACCESS   read-only
    STATUS       current
    DESCRIPTION
        "Cisco Firepower equipment:GemCapProvider:deprecated
        managed object property"
    ::= { cfprApEquipmentGemCapProviderEntry 5 }

cfprApEquipmentGemCapProviderElementLoadFailures OBJECT-TYPE
    SYNTAX       Gauge32
    MAX-ACCESS   read-only
    STATUS       current
    DESCRIPTION
        "Cisco Firepower equipment:GemCapProvider:elementLoadFailures
        managed object property"
    ::= { cfprApEquipmentGemCapProviderEntry 6 }

cfprApEquipmentGemCapProviderElementsLoaded OBJECT-TYPE
    SYNTAX       Gauge32
    MAX-ACCESS   read-only
    STATUS       current
    DESCRIPTION
        "Cisco Firepower equipment:GemCapProvider:elementsLoaded
        managed object property"
    ::= { cfprApEquipmentGemCapProviderEntry 7 }

cfprApEquipmentGemCapProviderGencount OBJECT-TYPE
    SYNTAX       Gauge32
    MAX-ACCESS   read-only
    STATUS       current
    DESCRIPTION
        "Cisco Firepower equipment:GemCapProvider:gencount
        managed object property"
    ::= { cfprApEquipmentGemCapProviderEntry 8 }

cfprApEquipmentGemCapProviderLoadErrors OBJECT-TYPE
    SYNTAX       Gauge32
    MAX-ACCESS   read-only
    STATUS       current
    DESCRIPTION
        "Cisco Firepower equipment:GemCapProvider:loadErrors
        managed object property"
    ::= { cfprApEquipmentGemCapProviderEntry 9 }

cfprApEquipmentGemCapProviderLoadWarnings OBJECT-TYPE
    SYNTAX       Gauge32
    MAX-ACCESS   read-only
    STATUS       current
    DESCRIPTION
        "Cisco Firepower equipment:GemCapProvider:loadWarnings
        managed object property"
    ::= { cfprApEquipmentGemCapProviderEntry 10 }

cfprApEquipmentGemCapProviderMgmtPlaneVer OBJECT-TYPE
    SYNTAX       SnmpAdminString
    MAX-ACCESS   read-only
    STATUS       current
    DESCRIPTION
        "Cisco Firepower equipment:GemCapProvider:mgmtPlaneVer
        managed object property"
    ::= { cfprApEquipmentGemCapProviderEntry 11 }

cfprApEquipmentGemCapProviderModel OBJECT-TYPE
    SYNTAX       SnmpAdminString
    MAX-ACCESS   read-only
    STATUS       current
    DESCRIPTION
        "Cisco Firepower equipment:GemCapProvider:model
        managed object property"
    ::= { cfprApEquipmentGemCapProviderEntry 12 }

cfprApEquipmentGemCapProviderPromCardType OBJECT-TYPE
    SYNTAX       Gauge32
    MAX-ACCESS   read-only
    STATUS       current
    DESCRIPTION
        "Cisco Firepower equipment:GemCapProvider:promCardType
        managed object property"
    ::= { cfprApEquipmentGemCapProviderEntry 13 }

cfprApEquipmentGemCapProviderRevision OBJECT-TYPE
    SYNTAX       SnmpAdminString
    MAX-ACCESS   read-only
    STATUS       current
    DESCRIPTION
        "Cisco Firepower equipment:GemCapProvider:revision
        managed object property"
    ::= { cfprApEquipmentGemCapProviderEntry 14 }

cfprApEquipmentGemCapProviderVendor OBJECT-TYPE
    SYNTAX       SnmpAdminString
    MAX-ACCESS   read-only
    STATUS       current
    DESCRIPTION
        "Cisco Firepower equipment:GemCapProvider:vendor
        managed object property"
    ::= { cfprApEquipmentGemCapProviderEntry 15 }

cfprApEquipmentGemPortCapTable OBJECT-TYPE
    SYNTAX           SEQUENCE OF CfprApEquipmentGemPortCapEntry
    MAX-ACCESS       not-accessible
    STATUS           current
    DESCRIPTION
        "Cisco Firepower equipment:GemPortCap managed object table"
    ::= { cfprApEquipmentObjects 58 }

cfprApEquipmentGemPortCapEntry OBJECT-TYPE
    SYNTAX           CfprApEquipmentGemPortCapEntry
    MAX-ACCESS       not-accessible
    STATUS           current
    DESCRIPTION
        "Entry for the cfprApEquipmentGemPortCapTable table."
    INDEX { cfprApEquipmentGemPortCapInstanceId }
    ::= { cfprApEquipmentGemPortCapTable 1 }

CfprApEquipmentGemPortCapEntry ::= SEQUENCE {
    cfprApEquipmentGemPortCapInstanceId                              CfprApManagedObjectId,
    cfprApEquipmentGemPortCapDn                                      CfprApManagedObjectDn,
    cfprApEquipmentGemPortCapRn                                      SnmpAdminString,
    cfprApEquipmentGemPortCapDescr                                   SnmpAdminString,
    cfprApEquipmentGemPortCapIntId                                   SnmpAdminString,
    cfprApEquipmentGemPortCapMaxFcSpeed                              CfprApPortSpeed,
    cfprApEquipmentGemPortCapName                                    SnmpAdminString,
    cfprApEquipmentGemPortCapPolicyLevel                             Gauge32,
    cfprApEquipmentGemPortCapPolicyOwner                             CfprApPolicyPolicyOwner,
    cfprApEquipmentGemPortCapPortNumber                              Gauge32,
    cfprApEquipmentGemPortCapPortSpeedCap                            CfprApEquipmentEthPortSpeedCap
}

cfprApEquipmentGemPortCapInstanceId OBJECT-TYPE
    SYNTAX       CfprApManagedObjectId
    MAX-ACCESS   not-accessible
    STATUS       current
    DESCRIPTION
        "Instance identifier of the managed object."
    ::= { cfprApEquipmentGemPortCapEntry 1 }

cfprApEquipmentGemPortCapDn OBJECT-TYPE
    SYNTAX       CfprApManagedObjectDn
    MAX-ACCESS   read-only
    STATUS       current
    DESCRIPTION
        "Cisco Firepower equipment:GemPortCap:dn managed object property"
    ::= { cfprApEquipmentGemPortCapEntry 2 }

cfprApEquipmentGemPortCapRn OBJECT-TYPE
    SYNTAX       SnmpAdminString
    MAX-ACCESS   read-only
    STATUS       current
    DESCRIPTION
        "Cisco Firepower equipment:GemPortCap:rn managed object property"
    ::= { cfprApEquipmentGemPortCapEntry 3 }

cfprApEquipmentGemPortCapDescr OBJECT-TYPE
    SYNTAX       SnmpAdminString
    MAX-ACCESS   read-only
    STATUS       current
    DESCRIPTION
        "Cisco Firepower equipment:GemPortCap:descr managed
        object property"
    ::= { cfprApEquipmentGemPortCapEntry 4 }

cfprApEquipmentGemPortCapIntId OBJECT-TYPE
    SYNTAX       SnmpAdminString
    MAX-ACCESS   read-only
    STATUS       current
    DESCRIPTION
        "Cisco Firepower equipment:GemPortCap:intId managed
        object property"
    ::= { cfprApEquipmentGemPortCapEntry 5 }

cfprApEquipmentGemPortCapMaxFcSpeed OBJECT-TYPE
    SYNTAX       CfprApPortSpeed
    MAX-ACCESS   read-only
    STATUS       current
    DESCRIPTION
        "Cisco Firepower equipment:GemPortCap:maxFcSpeed
        managed object property"
    ::= { cfprApEquipmentGemPortCapEntry 6 }

cfprApEquipmentGemPortCapName OBJECT-TYPE
    SYNTAX       SnmpAdminString
    MAX-ACCESS   read-only
    STATUS       current
    DESCRIPTION
        "Cisco Firepower equipment:GemPortCap:name managed
        object property"
    ::= { cfprApEquipmentGemPortCapEntry 7 }

cfprApEquipmentGemPortCapPolicyLevel OBJECT-TYPE
    SYNTAX       Gauge32
    MAX-ACCESS   read-only
    STATUS       current
    DESCRIPTION
        "Cisco Firepower equipment:GemPortCap:policyLevel
        managed object property"
    ::= { cfprApEquipmentGemPortCapEntry 8 }

cfprApEquipmentGemPortCapPolicyOwner OBJECT-TYPE
    SYNTAX       CfprApPolicyPolicyOwner
    MAX-ACCESS   read-only
    STATUS       current
    DESCRIPTION
        "Cisco Firepower equipment:GemPortCap:policyOwner
        managed object property"
    ::= { cfprApEquipmentGemPortCapEntry 9 }

cfprApEquipmentGemPortCapPortNumber OBJECT-TYPE
    SYNTAX       Gauge32
    MAX-ACCESS   read-only
    STATUS       current
    DESCRIPTION
        "Cisco Firepower equipment:GemPortCap:portNumber
        managed object property"
    ::= { cfprApEquipmentGemPortCapEntry 10 }

cfprApEquipmentGemPortCapPortSpeedCap OBJECT-TYPE
    SYNTAX       CfprApEquipmentEthPortSpeedCap
    MAX-ACCESS   read-only
    STATUS       current
    DESCRIPTION
        "Cisco Firepower equipment:GemPortCap:portSpeedCap
        managed object property"
    ::= { cfprApEquipmentGemPortCapEntry 11 }

cfprApEquipmentGraphicsCardCapProviderTable OBJECT-TYPE
    SYNTAX           SEQUENCE OF CfprApEquipmentGraphicsCardCapProviderEntry
    MAX-ACCESS       not-accessible
    STATUS           current
    DESCRIPTION
        "Cisco Firepower equipment:GraphicsCardCapProvider
        managed object table"
    ::= { cfprApEquipmentObjects 59 }

cfprApEquipmentGraphicsCardCapProviderEntry OBJECT-TYPE
    SYNTAX           CfprApEquipmentGraphicsCardCapProviderEntry
    MAX-ACCESS       not-accessible
    STATUS           current
    DESCRIPTION
        "Entry for the cfprApEquipmentGraphicsCardCapProviderTable table."
    INDEX { cfprApEquipmentGraphicsCardCapProviderInstanceId }
    ::= { cfprApEquipmentGraphicsCardCapProviderTable 1 }

CfprApEquipmentGraphicsCardCapProviderEntry ::= SEQUENCE {
    cfprApEquipmentGraphicsCardCapProviderInstanceId                 CfprApManagedObjectId,
    cfprApEquipmentGraphicsCardCapProviderDn                         CfprApManagedObjectDn,
    cfprApEquipmentGraphicsCardCapProviderRn                         SnmpAdminString,
    cfprApEquipmentGraphicsCardCapProviderDeleted                    TruthValue,
    cfprApEquipmentGraphicsCardCapProviderDeprecated                 TruthValue,
    cfprApEquipmentGraphicsCardCapProviderElementLoadFailures        Gauge32,
    cfprApEquipmentGraphicsCardCapProviderElementsLoaded             Gauge32,
    cfprApEquipmentGraphicsCardCapProviderGencount                   Gauge32,
    cfprApEquipmentGraphicsCardCapProviderLoadErrors                 Gauge32,
    cfprApEquipmentGraphicsCardCapProviderLoadWarnings               Gauge32,
    cfprApEquipmentGraphicsCardCapProviderMgmtPlaneVer               SnmpAdminString,
    cfprApEquipmentGraphicsCardCapProviderModel                      SnmpAdminString,
    cfprApEquipmentGraphicsCardCapProviderNumGpu                     Gauge32,
    cfprApEquipmentGraphicsCardCapProviderPromCardType               Gauge32,
    cfprApEquipmentGraphicsCardCapProviderRevision                   SnmpAdminString,
    cfprApEquipmentGraphicsCardCapProviderVendor                     SnmpAdminString
}

cfprApEquipmentGraphicsCardCapProviderInstanceId OBJECT-TYPE
    SYNTAX       CfprApManagedObjectId
    MAX-ACCESS   not-accessible
    STATUS       current
    DESCRIPTION
        "Instance identifier of the managed object."
    ::= { cfprApEquipmentGraphicsCardCapProviderEntry 1 }

cfprApEquipmentGraphicsCardCapProviderDn OBJECT-TYPE
    SYNTAX       CfprApManagedObjectDn
    MAX-ACCESS   read-only
    STATUS       current
    DESCRIPTION
        "Cisco Firepower equipment:GraphicsCardCapProvider:dn
        managed object property"
    ::= { cfprApEquipmentGraphicsCardCapProviderEntry 2 }

cfprApEquipmentGraphicsCardCapProviderRn OBJECT-TYPE
    SYNTAX       SnmpAdminString
    MAX-ACCESS   read-only
    STATUS       current
    DESCRIPTION
        "Cisco Firepower equipment:GraphicsCardCapProvider:rn
        managed object property"
    ::= { cfprApEquipmentGraphicsCardCapProviderEntry 3 }

cfprApEquipmentGraphicsCardCapProviderDeleted OBJECT-TYPE
    SYNTAX       TruthValue
    MAX-ACCESS   read-only
    STATUS       current
    DESCRIPTION
        "Cisco Firepower equipment:GraphicsCardCapProvider:deleted
        managed object property"
    ::= { cfprApEquipmentGraphicsCardCapProviderEntry 4 }

cfprApEquipmentGraphicsCardCapProviderDeprecated OBJECT-TYPE
    SYNTAX       TruthValue
    MAX-ACCESS   read-only
    STATUS       current
    DESCRIPTION
        "Cisco Firepower equipment:GraphicsCardCapProvider:deprecated
        managed object property"
    ::= { cfprApEquipmentGraphicsCardCapProviderEntry 5 }

cfprApEquipmentGraphicsCardCapProviderElementLoadFailures OBJECT-TYPE
    SYNTAX       Gauge32
    MAX-ACCESS   read-only
    STATUS       current
    DESCRIPTION
        "Cisco Firepower equipment:GraphicsCardCapProvider:elementLoadFail
        ures managed object property"
    ::= { cfprApEquipmentGraphicsCardCapProviderEntry 6 }

cfprApEquipmentGraphicsCardCapProviderElementsLoaded OBJECT-TYPE
    SYNTAX       Gauge32
    MAX-ACCESS   read-only
    STATUS       current
    DESCRIPTION
        "Cisco Firepower equipment:GraphicsCardCapProvider:elementsLoaded
        managed object property"
    ::= { cfprApEquipmentGraphicsCardCapProviderEntry 7 }

cfprApEquipmentGraphicsCardCapProviderGencount OBJECT-TYPE
    SYNTAX       Gauge32
    MAX-ACCESS   read-only
    STATUS       current
    DESCRIPTION
        "Cisco Firepower equipment:GraphicsCardCapProvider:gencount
        managed object property"
    ::= { cfprApEquipmentGraphicsCardCapProviderEntry 8 }

cfprApEquipmentGraphicsCardCapProviderLoadErrors OBJECT-TYPE
    SYNTAX       Gauge32
    MAX-ACCESS   read-only
    STATUS       current
    DESCRIPTION
        "Cisco Firepower equipment:GraphicsCardCapProvider:loadErrors
        managed object property"
    ::= { cfprApEquipmentGraphicsCardCapProviderEntry 9 }

cfprApEquipmentGraphicsCardCapProviderLoadWarnings OBJECT-TYPE
    SYNTAX       Gauge32
    MAX-ACCESS   read-only
    STATUS       current
    DESCRIPTION
        "Cisco Firepower equipment:GraphicsCardCapProvider:loadWarnings
        managed object property"
    ::= { cfprApEquipmentGraphicsCardCapProviderEntry 10 }

cfprApEquipmentGraphicsCardCapProviderMgmtPlaneVer OBJECT-TYPE
    SYNTAX       SnmpAdminString
    MAX-ACCESS   read-only
    STATUS       current
    DESCRIPTION
        "Cisco Firepower equipment:GraphicsCardCapProvider:mgmtPlaneVer
        managed object property"
    ::= { cfprApEquipmentGraphicsCardCapProviderEntry 11 }

cfprApEquipmentGraphicsCardCapProviderModel OBJECT-TYPE
    SYNTAX       SnmpAdminString
    MAX-ACCESS   read-only
    STATUS       current
    DESCRIPTION
        "Cisco Firepower equipment:GraphicsCardCapProvider:model
        managed object property"
    ::= { cfprApEquipmentGraphicsCardCapProviderEntry 12 }

cfprApEquipmentGraphicsCardCapProviderNumGpu OBJECT-TYPE
    SYNTAX       Gauge32
    MAX-ACCESS   read-only
    STATUS       current
    DESCRIPTION
        "Cisco Firepower equipment:GraphicsCardCapProvider:numGpu
        managed object property"
    ::= { cfprApEquipmentGraphicsCardCapProviderEntry 13 }

cfprApEquipmentGraphicsCardCapProviderPromCardType OBJECT-TYPE
    SYNTAX       Gauge32
    MAX-ACCESS   read-only
    STATUS       current
    DESCRIPTION
        "Cisco Firepower equipment:GraphicsCardCapProvider:promCardType
        managed object property"
    ::= { cfprApEquipmentGraphicsCardCapProviderEntry 14 }

cfprApEquipmentGraphicsCardCapProviderRevision OBJECT-TYPE
    SYNTAX       SnmpAdminString
    MAX-ACCESS   read-only
    STATUS       current
    DESCRIPTION
        "Cisco Firepower equipment:GraphicsCardCapProvider:revision
        managed object property"
    ::= { cfprApEquipmentGraphicsCardCapProviderEntry 15 }

cfprApEquipmentGraphicsCardCapProviderVendor OBJECT-TYPE
    SYNTAX       SnmpAdminString
    MAX-ACCESS   read-only
    STATUS       current
    DESCRIPTION
        "Cisco Firepower equipment:GraphicsCardCapProvider:vendor
        managed object property"
    ::= { cfprApEquipmentGraphicsCardCapProviderEntry 16 }

cfprApEquipmentGraphicsCardCapRefTable OBJECT-TYPE
    SYNTAX           SEQUENCE OF CfprApEquipmentGraphicsCardCapRefEntry
    MAX-ACCESS       not-accessible
    STATUS           current
    DESCRIPTION
        "Cisco Firepower equipment:GraphicsCardCapRef managed
        object table"
    ::= { cfprApEquipmentObjects 60 }

cfprApEquipmentGraphicsCardCapRefEntry OBJECT-TYPE
    SYNTAX           CfprApEquipmentGraphicsCardCapRefEntry
    MAX-ACCESS       not-accessible
    STATUS           current
    DESCRIPTION
        "Entry for the cfprApEquipmentGraphicsCardCapRefTable table."
    INDEX { cfprApEquipmentGraphicsCardCapRefInstanceId }
    ::= { cfprApEquipmentGraphicsCardCapRefTable 1 }

CfprApEquipmentGraphicsCardCapRefEntry ::= SEQUENCE {
    cfprApEquipmentGraphicsCardCapRefInstanceId                      CfprApManagedObjectId,
    cfprApEquipmentGraphicsCardCapRefDn                              CfprApManagedObjectDn,
    cfprApEquipmentGraphicsCardCapRefRn                              SnmpAdminString,
    cfprApEquipmentGraphicsCardCapRefModel                           SnmpAdminString,
    cfprApEquipmentGraphicsCardCapRefRevision                        SnmpAdminString,
    cfprApEquipmentGraphicsCardCapRefVendor                          SnmpAdminString
}

cfprApEquipmentGraphicsCardCapRefInstanceId OBJECT-TYPE
    SYNTAX       CfprApManagedObjectId
    MAX-ACCESS   not-accessible
    STATUS       current
    DESCRIPTION
        "Instance identifier of the managed object."
    ::= { cfprApEquipmentGraphicsCardCapRefEntry 1 }

cfprApEquipmentGraphicsCardCapRefDn OBJECT-TYPE
    SYNTAX       CfprApManagedObjectDn
    MAX-ACCESS   read-only
    STATUS       current
    DESCRIPTION
        "Cisco Firepower equipment:GraphicsCardCapRef:dn
        managed object property"
    ::= { cfprApEquipmentGraphicsCardCapRefEntry 2 }

cfprApEquipmentGraphicsCardCapRefRn OBJECT-TYPE
    SYNTAX       SnmpAdminString
    MAX-ACCESS   read-only
    STATUS       current
    DESCRIPTION
        "Cisco Firepower equipment:GraphicsCardCapRef:rn
        managed object property"
    ::= { cfprApEquipmentGraphicsCardCapRefEntry 3 }

cfprApEquipmentGraphicsCardCapRefModel OBJECT-TYPE
    SYNTAX       SnmpAdminString
    MAX-ACCESS   read-only
    STATUS       current
    DESCRIPTION
        "Cisco Firepower equipment:GraphicsCardCapRef:model
        managed object property"
    ::= { cfprApEquipmentGraphicsCardCapRefEntry 4 }

cfprApEquipmentGraphicsCardCapRefRevision OBJECT-TYPE
    SYNTAX       SnmpAdminString
    MAX-ACCESS   read-only
    STATUS       current
    DESCRIPTION
        "Cisco Firepower equipment:GraphicsCardCapRef:revision
        managed object property"
    ::= { cfprApEquipmentGraphicsCardCapRefEntry 5 }

cfprApEquipmentGraphicsCardCapRefVendor OBJECT-TYPE
    SYNTAX       SnmpAdminString
    MAX-ACCESS   read-only
    STATUS       current
    DESCRIPTION
        "Cisco Firepower equipment:GraphicsCardCapRef:vendor
        managed object property"
    ::= { cfprApEquipmentGraphicsCardCapRefEntry 6 }

cfprApEquipmentHDDFaultMonDefTable OBJECT-TYPE
    SYNTAX           SEQUENCE OF CfprApEquipmentHDDFaultMonDefEntry
    MAX-ACCESS       not-accessible
    STATUS           current
    DESCRIPTION
        "Cisco Firepower equipment:HDDFaultMonDef managed object table"
    ::= { cfprApEquipmentObjects 61 }

cfprApEquipmentHDDFaultMonDefEntry OBJECT-TYPE
    SYNTAX           CfprApEquipmentHDDFaultMonDefEntry
    MAX-ACCESS       not-accessible
    STATUS           current
    DESCRIPTION
        "Entry for the cfprApEquipmentHDDFaultMonDefTable table."
    INDEX { cfprApEquipmentHDDFaultMonDefInstanceId }
    ::= { cfprApEquipmentHDDFaultMonDefTable 1 }

CfprApEquipmentHDDFaultMonDefEntry ::= SEQUENCE {
    cfprApEquipmentHDDFaultMonDefInstanceId                          CfprApManagedObjectId,
    cfprApEquipmentHDDFaultMonDefDn                                  CfprApManagedObjectDn,
    cfprApEquipmentHDDFaultMonDefRn                                  SnmpAdminString,
    cfprApEquipmentHDDFaultMonDefControllerFwVersion                 SnmpAdminString,
    cfprApEquipmentHDDFaultMonDefControllerModel                     SnmpAdminString,
    cfprApEquipmentHDDFaultMonDefHDDMonSupport                       SnmpAdminString,
    cfprApEquipmentHDDFaultMonDefDescr                               SnmpAdminString,
    cfprApEquipmentHDDFaultMonDefIntId                               SnmpAdminString,
    cfprApEquipmentHDDFaultMonDefName                                SnmpAdminString,
    cfprApEquipmentHDDFaultMonDefPolicyLevel                         Gauge32,
    cfprApEquipmentHDDFaultMonDefPolicyOwner                         CfprApPolicyPolicyOwner
}

cfprApEquipmentHDDFaultMonDefInstanceId OBJECT-TYPE
    SYNTAX       CfprApManagedObjectId
    MAX-ACCESS   not-accessible
    STATUS       current
    DESCRIPTION
        "Instance identifier of the managed object."
    ::= { cfprApEquipmentHDDFaultMonDefEntry 1 }

cfprApEquipmentHDDFaultMonDefDn OBJECT-TYPE
    SYNTAX       CfprApManagedObjectDn
    MAX-ACCESS   read-only
    STATUS       current
    DESCRIPTION
        "Cisco Firepower equipment:HDDFaultMonDef:dn managed
        object property"
    ::= { cfprApEquipmentHDDFaultMonDefEntry 2 }

cfprApEquipmentHDDFaultMonDefRn OBJECT-TYPE
    SYNTAX       SnmpAdminString
    MAX-ACCESS   read-only
    STATUS       current
    DESCRIPTION
        "Cisco Firepower equipment:HDDFaultMonDef:rn managed
        object property"
    ::= { cfprApEquipmentHDDFaultMonDefEntry 3 }

cfprApEquipmentHDDFaultMonDefControllerFwVersion OBJECT-TYPE
    SYNTAX       SnmpAdminString
    MAX-ACCESS   read-only
    STATUS       current
    DESCRIPTION
        "Cisco Firepower equipment:HDDFaultMonDef:ControllerFwVersion
        managed object property"
    ::= { cfprApEquipmentHDDFaultMonDefEntry 4 }

cfprApEquipmentHDDFaultMonDefControllerModel OBJECT-TYPE
    SYNTAX       SnmpAdminString
    MAX-ACCESS   read-only
    STATUS       current
    DESCRIPTION
        "Cisco Firepower equipment:HDDFaultMonDef:ControllerModel
        managed object property"
    ::= { cfprApEquipmentHDDFaultMonDefEntry 5 }

cfprApEquipmentHDDFaultMonDefHDDMonSupport OBJECT-TYPE
    SYNTAX       SnmpAdminString
    MAX-ACCESS   read-only
    STATUS       current
    DESCRIPTION
        "Cisco Firepower equipment:HDDFaultMonDef:HDDMonSupport
        managed object property"
    ::= { cfprApEquipmentHDDFaultMonDefEntry 6 }

cfprApEquipmentHDDFaultMonDefDescr OBJECT-TYPE
    SYNTAX       SnmpAdminString
    MAX-ACCESS   read-only
    STATUS       current
    DESCRIPTION
        "Cisco Firepower equipment:HDDFaultMonDef:descr
        managed object property"
    ::= { cfprApEquipmentHDDFaultMonDefEntry 7 }

cfprApEquipmentHDDFaultMonDefIntId OBJECT-TYPE
    SYNTAX       SnmpAdminString
    MAX-ACCESS   read-only
    STATUS       current
    DESCRIPTION
        "Cisco Firepower equipment:HDDFaultMonDef:intId
        managed object property"
    ::= { cfprApEquipmentHDDFaultMonDefEntry 8 }

cfprApEquipmentHDDFaultMonDefName OBJECT-TYPE
    SYNTAX       SnmpAdminString
    MAX-ACCESS   read-only
    STATUS       current
    DESCRIPTION
        "Cisco Firepower equipment:HDDFaultMonDef:name
        managed object property"
    ::= { cfprApEquipmentHDDFaultMonDefEntry 9 }

cfprApEquipmentHDDFaultMonDefPolicyLevel OBJECT-TYPE
    SYNTAX       Gauge32
    MAX-ACCESS   read-only
    STATUS       current
    DESCRIPTION
        "Cisco Firepower equipment:HDDFaultMonDef:policyLevel
        managed object property"
    ::= { cfprApEquipmentHDDFaultMonDefEntry 10 }

cfprApEquipmentHDDFaultMonDefPolicyOwner OBJECT-TYPE
    SYNTAX       CfprApPolicyPolicyOwner
    MAX-ACCESS   read-only
    STATUS       current
    DESCRIPTION
        "Cisco Firepower equipment:HDDFaultMonDef:policyOwner
        managed object property"
    ::= { cfprApEquipmentHDDFaultMonDefEntry 11 }

cfprApEquipmentHealthLedTable OBJECT-TYPE
    SYNTAX           SEQUENCE OF CfprApEquipmentHealthLedEntry
    MAX-ACCESS       not-accessible
    STATUS           current
    DESCRIPTION
        "Cisco Firepower equipment:HealthLed managed object table"
    ::= { cfprApEquipmentObjects 62 }

cfprApEquipmentHealthLedEntry OBJECT-TYPE
    SYNTAX           CfprApEquipmentHealthLedEntry
    MAX-ACCESS       not-accessible
    STATUS           current
    DESCRIPTION
        "Entry for the cfprApEquipmentHealthLedTable table."
    INDEX { cfprApEquipmentHealthLedInstanceId }
    ::= { cfprApEquipmentHealthLedTable 1 }

CfprApEquipmentHealthLedEntry ::= SEQUENCE {
    cfprApEquipmentHealthLedInstanceId                               CfprApManagedObjectId,
    cfprApEquipmentHealthLedDn                                       CfprApManagedObjectDn,
    cfprApEquipmentHealthLedRn                                       SnmpAdminString,
    cfprApEquipmentHealthLedColor                                    CfprApEquipmentLedColor,
    cfprApEquipmentHealthLedHealthLedState                           CfprApEquipmentHealthLedState,
    cfprApEquipmentHealthLedHealthLedStateQualifier                  SnmpAdminString,
    cfprApEquipmentHealthLedId                                       Gauge32,
    cfprApEquipmentHealthLedName                                     SnmpAdminString,
    cfprApEquipmentHealthLedOperState                                CfprApEquipmentLedOperState
}

cfprApEquipmentHealthLedInstanceId OBJECT-TYPE
    SYNTAX       CfprApManagedObjectId
    MAX-ACCESS   not-accessible
    STATUS       current
    DESCRIPTION
        "Instance identifier of the managed object."
    ::= { cfprApEquipmentHealthLedEntry 1 }

cfprApEquipmentHealthLedDn OBJECT-TYPE
    SYNTAX       CfprApManagedObjectDn
    MAX-ACCESS   read-only
    STATUS       current
    DESCRIPTION
        "Cisco Firepower equipment:HealthLed:dn managed object property"
    ::= { cfprApEquipmentHealthLedEntry 2 }

cfprApEquipmentHealthLedRn OBJECT-TYPE
    SYNTAX       SnmpAdminString
    MAX-ACCESS   read-only
    STATUS       current
    DESCRIPTION
        "Cisco Firepower equipment:HealthLed:rn managed object property"
    ::= { cfprApEquipmentHealthLedEntry 3 }

cfprApEquipmentHealthLedColor OBJECT-TYPE
    SYNTAX       CfprApEquipmentLedColor
    MAX-ACCESS   read-only
    STATUS       current
    DESCRIPTION
        "Cisco Firepower equipment:HealthLed:color managed
        object property"
    ::= { cfprApEquipmentHealthLedEntry 4 }

cfprApEquipmentHealthLedHealthLedState OBJECT-TYPE
    SYNTAX       CfprApEquipmentHealthLedState
    MAX-ACCESS   read-only
    STATUS       current
    DESCRIPTION
        "Cisco Firepower equipment:HealthLed:healthLedState
        managed object property"
    ::= { cfprApEquipmentHealthLedEntry 5 }

cfprApEquipmentHealthLedHealthLedStateQualifier OBJECT-TYPE
    SYNTAX       SnmpAdminString
    MAX-ACCESS   read-only
    STATUS       current
    DESCRIPTION
        "Cisco Firepower equipment:HealthLed:healthLedStateQualifier
        managed object property"
    ::= { cfprApEquipmentHealthLedEntry 6 }

cfprApEquipmentHealthLedId OBJECT-TYPE
    SYNTAX       Gauge32
    MAX-ACCESS   read-only
    STATUS       current
    DESCRIPTION
        "Cisco Firepower equipment:HealthLed:id managed object property"
    ::= { cfprApEquipmentHealthLedEntry 7 }

cfprApEquipmentHealthLedName OBJECT-TYPE
    SYNTAX       SnmpAdminString
    MAX-ACCESS   read-only
    STATUS       current
    DESCRIPTION
        "Cisco Firepower equipment:HealthLed:name managed object property"
    ::= { cfprApEquipmentHealthLedEntry 8 }

cfprApEquipmentHealthLedOperState OBJECT-TYPE
    SYNTAX       CfprApEquipmentLedOperState
    MAX-ACCESS   read-only
    STATUS       current
    DESCRIPTION
        "Cisco Firepower equipment:HealthLed:operState
        managed object property"
    ::= { cfprApEquipmentHealthLedEntry 9 }

cfprApEquipmentHostIfCapProviderTable OBJECT-TYPE
    SYNTAX           SEQUENCE OF CfprApEquipmentHostIfCapProviderEntry
    MAX-ACCESS       not-accessible
    STATUS           current
    DESCRIPTION
        "Cisco Firepower equipment:HostIfCapProvider managed object table"
    ::= { cfprApEquipmentObjects 63 }

cfprApEquipmentHostIfCapProviderEntry OBJECT-TYPE
    SYNTAX           CfprApEquipmentHostIfCapProviderEntry
    MAX-ACCESS       not-accessible
    STATUS           current
    DESCRIPTION
        "Entry for the cfprApEquipmentHostIfCapProviderTable table."
    INDEX { cfprApEquipmentHostIfCapProviderInstanceId }
    ::= { cfprApEquipmentHostIfCapProviderTable 1 }

CfprApEquipmentHostIfCapProviderEntry ::= SEQUENCE {
    cfprApEquipmentHostIfCapProviderInstanceId                       CfprApManagedObjectId,
    cfprApEquipmentHostIfCapProviderDn                               CfprApManagedObjectDn,
    cfprApEquipmentHostIfCapProviderRn                               SnmpAdminString,
    cfprApEquipmentHostIfCapProviderDeleted                          TruthValue,
    cfprApEquipmentHostIfCapProviderDeprecated                       TruthValue,
    cfprApEquipmentHostIfCapProviderElementLoadFailures              Gauge32,
    cfprApEquipmentHostIfCapProviderElementsLoaded                   Gauge32,
    cfprApEquipmentHostIfCapProviderGencount                         Gauge32,
    cfprApEquipmentHostIfCapProviderLoadErrors                       Gauge32,
    cfprApEquipmentHostIfCapProviderLoadWarnings                     Gauge32,
    cfprApEquipmentHostIfCapProviderMgmtPlaneVer                     SnmpAdminString,
    cfprApEquipmentHostIfCapProviderModel                            SnmpAdminString,
    cfprApEquipmentHostIfCapProviderPromCardType                     Gauge32,
    cfprApEquipmentHostIfCapProviderRevision                         SnmpAdminString,
    cfprApEquipmentHostIfCapProviderVendor                           SnmpAdminString
}

cfprApEquipmentHostIfCapProviderInstanceId OBJECT-TYPE
    SYNTAX       CfprApManagedObjectId
    MAX-ACCESS   not-accessible
    STATUS       current
    DESCRIPTION
        "Instance identifier of the managed object."
    ::= { cfprApEquipmentHostIfCapProviderEntry 1 }

cfprApEquipmentHostIfCapProviderDn OBJECT-TYPE
    SYNTAX       CfprApManagedObjectDn
    MAX-ACCESS   read-only
    STATUS       current
    DESCRIPTION
        "Cisco Firepower equipment:HostIfCapProvider:dn
        managed object property"
    ::= { cfprApEquipmentHostIfCapProviderEntry 2 }

cfprApEquipmentHostIfCapProviderRn OBJECT-TYPE
    SYNTAX       SnmpAdminString
    MAX-ACCESS   read-only
    STATUS       current
    DESCRIPTION
        "Cisco Firepower equipment:HostIfCapProvider:rn
        managed object property"
    ::= { cfprApEquipmentHostIfCapProviderEntry 3 }

cfprApEquipmentHostIfCapProviderDeleted OBJECT-TYPE
    SYNTAX       TruthValue
    MAX-ACCESS   read-only
    STATUS       current
    DESCRIPTION
        "Cisco Firepower equipment:HostIfCapProvider:deleted
        managed object property"
    ::= { cfprApEquipmentHostIfCapProviderEntry 4 }

cfprApEquipmentHostIfCapProviderDeprecated OBJECT-TYPE
    SYNTAX       TruthValue
    MAX-ACCESS   read-only
    STATUS       current
    DESCRIPTION
        "Cisco Firepower equipment:HostIfCapProvider:deprecated
        managed object property"
    ::= { cfprApEquipmentHostIfCapProviderEntry 5 }

cfprApEquipmentHostIfCapProviderElementLoadFailures OBJECT-TYPE
    SYNTAX       Gauge32
    MAX-ACCESS   read-only
    STATUS       current
    DESCRIPTION
        "Cisco Firepower equipment:HostIfCapProvider:elementLoadFailures
        managed object property"
    ::= { cfprApEquipmentHostIfCapProviderEntry 6 }

cfprApEquipmentHostIfCapProviderElementsLoaded OBJECT-TYPE
    SYNTAX       Gauge32
    MAX-ACCESS   read-only
    STATUS       current
    DESCRIPTION
        "Cisco Firepower equipment:HostIfCapProvider:elementsLoaded
        managed object property"
    ::= { cfprApEquipmentHostIfCapProviderEntry 7 }

cfprApEquipmentHostIfCapProviderGencount OBJECT-TYPE
    SYNTAX       Gauge32
    MAX-ACCESS   read-only
    STATUS       current
    DESCRIPTION
        "Cisco Firepower equipment:HostIfCapProvider:gencount
        managed object property"
    ::= { cfprApEquipmentHostIfCapProviderEntry 8 }

cfprApEquipmentHostIfCapProviderLoadErrors OBJECT-TYPE
    SYNTAX       Gauge32
    MAX-ACCESS   read-only
    STATUS       current
    DESCRIPTION
        "Cisco Firepower equipment:HostIfCapProvider:loadErrors
        managed object property"
    ::= { cfprApEquipmentHostIfCapProviderEntry 9 }

cfprApEquipmentHostIfCapProviderLoadWarnings OBJECT-TYPE
    SYNTAX       Gauge32
    MAX-ACCESS   read-only
    STATUS       current
    DESCRIPTION
        "Cisco Firepower equipment:HostIfCapProvider:loadWarnings
        managed object property"
    ::= { cfprApEquipmentHostIfCapProviderEntry 10 }

cfprApEquipmentHostIfCapProviderMgmtPlaneVer OBJECT-TYPE
    SYNTAX       SnmpAdminString
    MAX-ACCESS   read-only
    STATUS       current
    DESCRIPTION
        "Cisco Firepower equipment:HostIfCapProvider:mgmtPlaneVer
        managed object property"
    ::= { cfprApEquipmentHostIfCapProviderEntry 11 }

cfprApEquipmentHostIfCapProviderModel OBJECT-TYPE
    SYNTAX       SnmpAdminString
    MAX-ACCESS   read-only
    STATUS       current
    DESCRIPTION
        "Cisco Firepower equipment:HostIfCapProvider:model
        managed object property"
    ::= { cfprApEquipmentHostIfCapProviderEntry 12 }

cfprApEquipmentHostIfCapProviderPromCardType OBJECT-TYPE
    SYNTAX       Gauge32
    MAX-ACCESS   read-only
    STATUS       current
    DESCRIPTION
        "Cisco Firepower equipment:HostIfCapProvider:promCardType
        managed object property"
    ::= { cfprApEquipmentHostIfCapProviderEntry 13 }

cfprApEquipmentHostIfCapProviderRevision OBJECT-TYPE
    SYNTAX       SnmpAdminString
    MAX-ACCESS   read-only
    STATUS       current
    DESCRIPTION
        "Cisco Firepower equipment:HostIfCapProvider:revision
        managed object property"
    ::= { cfprApEquipmentHostIfCapProviderEntry 14 }

cfprApEquipmentHostIfCapProviderVendor OBJECT-TYPE
    SYNTAX       SnmpAdminString
    MAX-ACCESS   read-only
    STATUS       current
    DESCRIPTION
        "Cisco Firepower equipment:HostIfCapProvider:vendor
        managed object property"
    ::= { cfprApEquipmentHostIfCapProviderEntry 15 }

cfprApEquipmentIOCardTable OBJECT-TYPE
    SYNTAX           SEQUENCE OF CfprApEquipmentIOCardEntry
    MAX-ACCESS       not-accessible
    STATUS           current
    DESCRIPTION
        "Cisco Firepower equipment:IOCard managed object table"
    ::= { cfprApEquipmentObjects 64 }

cfprApEquipmentIOCardEntry OBJECT-TYPE
    SYNTAX           CfprApEquipmentIOCardEntry
    MAX-ACCESS       not-accessible
    STATUS           current
    DESCRIPTION
        "Entry for the cfprApEquipmentIOCardTable table."
    INDEX { cfprApEquipmentIOCardInstanceId }
    ::= { cfprApEquipmentIOCardTable 1 }

CfprApEquipmentIOCardEntry ::= SEQUENCE {
    cfprApEquipmentIOCardInstanceId                                  CfprApManagedObjectId,
    cfprApEquipmentIOCardDn                                          CfprApManagedObjectDn,
    cfprApEquipmentIOCardRn                                          SnmpAdminString,
    cfprApEquipmentIOCardAdminPowerState                             CfprApEquipmentAdminPowerState,
    cfprApEquipmentIOCardBaseAddr                                    InetAddressIPv4,
    cfprApEquipmentIOCardChassisId                                   Gauge32,
    cfprApEquipmentIOCardConfigState                                 CfprApEquipmentChassisConfigState,
    cfprApEquipmentIOCardDiscovery                                   CfprApEquipmentDiscoveryState,
    cfprApEquipmentIOCardFeOfflineTs                                 Unsigned64,
    cfprApEquipmentIOCardFeReadyTs                                   Unsigned64,
    cfprApEquipmentIOCardFltAggr                                     Unsigned64,
    cfprApEquipmentIOCardFsmDescr                                    SnmpAdminString,
    cfprApEquipmentIOCardFsmFlags                                    SnmpAdminString,
    cfprApEquipmentIOCardFsmPrev                                     SnmpAdminString,
    cfprApEquipmentIOCardFsmProgr                                    Gauge32,
    cfprApEquipmentIOCardFsmRmtInvErrCode                            Gauge32,
    cfprApEquipmentIOCardFsmRmtInvErrDescr                           SnmpAdminString,
    cfprApEquipmentIOCardFsmRmtInvRslt                               CfprApConditionRemoteInvRslt,
    cfprApEquipmentIOCardFsmStageDescr                               SnmpAdminString,
    cfprApEquipmentIOCardFsmStamp                                    DateAndTime,
    cfprApEquipmentIOCardFsmStatus                                   SnmpAdminString,
    cfprApEquipmentIOCardFsmTry                                      Gauge32,
    cfprApEquipmentIOCardId                                          CfprApEquipmentIOCardId,
    cfprApEquipmentIOCardLcName                                      SnmpAdminString,
    cfprApEquipmentIOCardLcTs                                        DateAndTime,
    cfprApEquipmentIOCardMfgTime                                     DateAndTime,
    cfprApEquipmentIOCardModel                                       SnmpAdminString,
    cfprApEquipmentIOCardOperQualifier                               CfprApEquipmentIOCardIssues,
    cfprApEquipmentIOCardOperQualifierReason                         SnmpAdminString,
    cfprApEquipmentIOCardOperState                                   CfprApEquipmentOperability,
    cfprApEquipmentIOCardOperability                                 CfprApEquipmentOperability,
    cfprApEquipmentIOCardPartNumber                                  SnmpAdminString,
    cfprApEquipmentIOCardPeerCommStatus                              CfprApEquipmentCommStatus,
    cfprApEquipmentIOCardPeerDn                                      SnmpAdminString,
    cfprApEquipmentIOCardPerf                                        CfprApEquipmentSensorThresholdStatus,
    cfprApEquipmentIOCardPower                                       CfprApEquipmentPowerState,
    cfprApEquipmentIOCardPresence                                    CfprApEquipmentPresence,
    cfprApEquipmentIOCardProcessorThermalState                       CfprApEquipmentSensorThresholdStatus,
    cfprApEquipmentIOCardRevision                                    SnmpAdminString,
    cfprApEquipmentIOCardSerial                                      SnmpAdminString,
    cfprApEquipmentIOCardSide                                        CfprApNetworkSide,
    cfprApEquipmentIOCardSwitchId                                    CfprApNetworkSwitchId,
    cfprApEquipmentIOCardThermal                                     CfprApEquipmentSensorThresholdStatus,
    cfprApEquipmentIOCardUpgradeStatus                               CfprApMgmtUpgradeStatus,
    cfprApEquipmentIOCardUsrLbl                                      SnmpAdminString,
    cfprApEquipmentIOCardVendor                                      SnmpAdminString,
    cfprApEquipmentIOCardVid                                         SnmpAdminString,
    cfprApEquipmentIOCardVoltage                                     CfprApEquipmentSensorThresholdStatus
}

cfprApEquipmentIOCardInstanceId OBJECT-TYPE
    SYNTAX       CfprApManagedObjectId
    MAX-ACCESS   not-accessible
    STATUS       current
    DESCRIPTION
        "Instance identifier of the managed object."
    ::= { cfprApEquipmentIOCardEntry 1 }

cfprApEquipmentIOCardDn OBJECT-TYPE
    SYNTAX       CfprApManagedObjectDn
    MAX-ACCESS   read-only
    STATUS       current
    DESCRIPTION
        "Cisco Firepower equipment:IOCard:dn managed object property"
    ::= { cfprApEquipmentIOCardEntry 2 }

cfprApEquipmentIOCardRn OBJECT-TYPE
    SYNTAX       SnmpAdminString
    MAX-ACCESS   read-only
    STATUS       current
    DESCRIPTION
        "Cisco Firepower equipment:IOCard:rn managed object property"
    ::= { cfprApEquipmentIOCardEntry 3 }

cfprApEquipmentIOCardAdminPowerState OBJECT-TYPE
    SYNTAX       CfprApEquipmentAdminPowerState
    MAX-ACCESS   read-only
    STATUS       current
    DESCRIPTION
        "Cisco Firepower equipment:IOCard:adminPowerState
        managed object property"
    ::= { cfprApEquipmentIOCardEntry 4 }

cfprApEquipmentIOCardBaseAddr OBJECT-TYPE
    SYNTAX       InetAddressIPv4
    MAX-ACCESS   read-only
    STATUS       current
    DESCRIPTION
        "Cisco Firepower equipment:IOCard:baseAddr managed
        object property"
    ::= { cfprApEquipmentIOCardEntry 5 }

cfprApEquipmentIOCardChassisId OBJECT-TYPE
    SYNTAX       Gauge32
    MAX-ACCESS   read-only
    STATUS       current
    DESCRIPTION
        "Cisco Firepower equipment:IOCard:chassisId managed
        object property"
    ::= { cfprApEquipmentIOCardEntry 6 }

cfprApEquipmentIOCardConfigState OBJECT-TYPE
    SYNTAX       CfprApEquipmentChassisConfigState
    MAX-ACCESS   read-only
    STATUS       current
    DESCRIPTION
        "Cisco Firepower equipment:IOCard:configState managed
        object property"
    ::= { cfprApEquipmentIOCardEntry 7 }

cfprApEquipmentIOCardDiscovery OBJECT-TYPE
    SYNTAX       CfprApEquipmentDiscoveryState
    MAX-ACCESS   read-only
    STATUS       current
    DESCRIPTION
        "Cisco Firepower equipment:IOCard:discovery managed
        object property"
    ::= { cfprApEquipmentIOCardEntry 8 }

cfprApEquipmentIOCardFeOfflineTs OBJECT-TYPE
    SYNTAX       Unsigned64
    MAX-ACCESS   read-only
    STATUS       current
    DESCRIPTION
        "Cisco Firepower equipment:IOCard:feOfflineTs managed
        object property"
    ::= { cfprApEquipmentIOCardEntry 9 }

cfprApEquipmentIOCardFeReadyTs OBJECT-TYPE
    SYNTAX       Unsigned64
    MAX-ACCESS   read-only
    STATUS       current
    DESCRIPTION
        "Cisco Firepower equipment:IOCard:feReadyTs managed
        object property"
    ::= { cfprApEquipmentIOCardEntry 10 }

cfprApEquipmentIOCardFltAggr OBJECT-TYPE
    SYNTAX       Unsigned64
    MAX-ACCESS   read-only
    STATUS       current
    DESCRIPTION
        "Cisco Firepower equipment:IOCard:fltAggr managed object property"
    ::= { cfprApEquipmentIOCardEntry 11 }

cfprApEquipmentIOCardFsmDescr OBJECT-TYPE
    SYNTAX       SnmpAdminString
    MAX-ACCESS   read-only
    STATUS       current
    DESCRIPTION
        "Cisco Firepower equipment:IOCard:fsmDescr managed
        object property"
    ::= { cfprApEquipmentIOCardEntry 12 }

cfprApEquipmentIOCardFsmFlags OBJECT-TYPE
    SYNTAX       SnmpAdminString
    MAX-ACCESS   read-only
    STATUS       current
    DESCRIPTION
        "Cisco Firepower equipment:IOCard:fsmFlags managed
        object property"
    ::= { cfprApEquipmentIOCardEntry 13 }

cfprApEquipmentIOCardFsmPrev OBJECT-TYPE
    SYNTAX       SnmpAdminString
    MAX-ACCESS   read-only
    STATUS       current
    DESCRIPTION
        "Cisco Firepower equipment:IOCard:fsmPrev managed object property"
    ::= { cfprApEquipmentIOCardEntry 14 }

cfprApEquipmentIOCardFsmProgr OBJECT-TYPE
    SYNTAX       Gauge32
    MAX-ACCESS   read-only
    STATUS       current
    DESCRIPTION
        "Cisco Firepower equipment:IOCard:fsmProgr managed
        object property"
    ::= { cfprApEquipmentIOCardEntry 15 }

cfprApEquipmentIOCardFsmRmtInvErrCode OBJECT-TYPE
    SYNTAX       Gauge32
    MAX-ACCESS   read-only
    STATUS       current
    DESCRIPTION
        "Cisco Firepower equipment:IOCard:fsmRmtInvErrCode
        managed object property"
    ::= { cfprApEquipmentIOCardEntry 16 }

cfprApEquipmentIOCardFsmRmtInvErrDescr OBJECT-TYPE
    SYNTAX       SnmpAdminString
    MAX-ACCESS   read-only
    STATUS       current
    DESCRIPTION
        "Cisco Firepower equipment:IOCard:fsmRmtInvErrDescr
        managed object property"
    ::= { cfprApEquipmentIOCardEntry 17 }

cfprApEquipmentIOCardFsmRmtInvRslt OBJECT-TYPE
    SYNTAX       CfprApConditionRemoteInvRslt
    MAX-ACCESS   read-only
    STATUS       current
    DESCRIPTION
        "Cisco Firepower equipment:IOCard:fsmRmtInvRslt
        managed object property"
    ::= { cfprApEquipmentIOCardEntry 18 }

cfprApEquipmentIOCardFsmStageDescr OBJECT-TYPE
    SYNTAX       SnmpAdminString
    MAX-ACCESS   read-only
    STATUS       current
    DESCRIPTION
        "Cisco Firepower equipment:IOCard:fsmStageDescr
        managed object property"
    ::= { cfprApEquipmentIOCardEntry 19 }

cfprApEquipmentIOCardFsmStamp OBJECT-TYPE
    SYNTAX       DateAndTime
    MAX-ACCESS   read-only
    STATUS       current
    DESCRIPTION
        "Cisco Firepower equipment:IOCard:fsmStamp managed
        object property"
    ::= { cfprApEquipmentIOCardEntry 20 }

cfprApEquipmentIOCardFsmStatus OBJECT-TYPE
    SYNTAX       SnmpAdminString
    MAX-ACCESS   read-only
    STATUS       current
    DESCRIPTION
        "Cisco Firepower equipment:IOCard:fsmStatus managed
        object property"
    ::= { cfprApEquipmentIOCardEntry 21 }

cfprApEquipmentIOCardFsmTry OBJECT-TYPE
    SYNTAX       Gauge32
    MAX-ACCESS   read-only
    STATUS       current
    DESCRIPTION
        "Cisco Firepower equipment:IOCard:fsmTry managed object property"
    ::= { cfprApEquipmentIOCardEntry 22 }

cfprApEquipmentIOCardId OBJECT-TYPE
    SYNTAX       CfprApEquipmentIOCardId
    MAX-ACCESS   read-only
    STATUS       current
    DESCRIPTION
        "Cisco Firepower equipment:IOCard:id managed object property"
    ::= { cfprApEquipmentIOCardEntry 23 }

cfprApEquipmentIOCardLcName OBJECT-TYPE
    SYNTAX       SnmpAdminString
    MAX-ACCESS   read-only
    STATUS       current
    DESCRIPTION
        "Cisco Firepower equipment:IOCard:lcName managed object property"
    ::= { cfprApEquipmentIOCardEntry 24 }

cfprApEquipmentIOCardLcTs OBJECT-TYPE
    SYNTAX       DateAndTime
    MAX-ACCESS   read-only
    STATUS       current
    DESCRIPTION
        "Cisco Firepower equipment:IOCard:lcTs managed object property"
    ::= { cfprApEquipmentIOCardEntry 25 }

cfprApEquipmentIOCardMfgTime OBJECT-TYPE
    SYNTAX       DateAndTime
    MAX-ACCESS   read-only
    STATUS       current
    DESCRIPTION
        "Cisco Firepower equipment:IOCard:mfgTime managed object property"
    ::= { cfprApEquipmentIOCardEntry 26 }

cfprApEquipmentIOCardModel OBJECT-TYPE
    SYNTAX       SnmpAdminString
    MAX-ACCESS   read-only
    STATUS       current
    DESCRIPTION
        "Cisco Firepower equipment:IOCard:model managed object property"
    ::= { cfprApEquipmentIOCardEntry 27 }

cfprApEquipmentIOCardOperQualifier OBJECT-TYPE
    SYNTAX       CfprApEquipmentIOCardIssues
    MAX-ACCESS   read-only
    STATUS       current
    DESCRIPTION
        "Cisco Firepower equipment:IOCard:operQualifier
        managed object property"
    ::= { cfprApEquipmentIOCardEntry 28 }

cfprApEquipmentIOCardOperQualifierReason OBJECT-TYPE
    SYNTAX       SnmpAdminString
    MAX-ACCESS   read-only
    STATUS       current
    DESCRIPTION
        "Cisco Firepower equipment:IOCard:operQualifierReason
        managed object property"
    ::= { cfprApEquipmentIOCardEntry 29 }

cfprApEquipmentIOCardOperState OBJECT-TYPE
    SYNTAX       CfprApEquipmentOperability
    MAX-ACCESS   read-only
    STATUS       current
    DESCRIPTION
        "Cisco Firepower equipment:IOCard:operState managed
        object property"
    ::= { cfprApEquipmentIOCardEntry 30 }

cfprApEquipmentIOCardOperability OBJECT-TYPE
    SYNTAX       CfprApEquipmentOperability
    MAX-ACCESS   read-only
    STATUS       current
    DESCRIPTION
        "Cisco Firepower equipment:IOCard:operability managed
        object property"
    ::= { cfprApEquipmentIOCardEntry 31 }

cfprApEquipmentIOCardPartNumber OBJECT-TYPE
    SYNTAX       SnmpAdminString
    MAX-ACCESS   read-only
    STATUS       current
    DESCRIPTION
        "Cisco Firepower equipment:IOCard:partNumber managed
        object property"
    ::= { cfprApEquipmentIOCardEntry 32 }

cfprApEquipmentIOCardPeerCommStatus OBJECT-TYPE
    SYNTAX       CfprApEquipmentCommStatus
    MAX-ACCESS   read-only
    STATUS       current
    DESCRIPTION
        "Cisco Firepower equipment:IOCard:peerCommStatus
        managed object property"
    ::= { cfprApEquipmentIOCardEntry 33 }

cfprApEquipmentIOCardPeerDn OBJECT-TYPE
    SYNTAX       SnmpAdminString
    MAX-ACCESS   read-only
    STATUS       current
    DESCRIPTION
        "Cisco Firepower equipment:IOCard:peerDn managed object property"
    ::= { cfprApEquipmentIOCardEntry 34 }

cfprApEquipmentIOCardPerf OBJECT-TYPE
    SYNTAX       CfprApEquipmentSensorThresholdStatus
    MAX-ACCESS   read-only
    STATUS       current
    DESCRIPTION
        "Cisco Firepower equipment:IOCard:perf managed object property"
    ::= { cfprApEquipmentIOCardEntry 35 }

cfprApEquipmentIOCardPower OBJECT-TYPE
    SYNTAX       CfprApEquipmentPowerState
    MAX-ACCESS   read-only
    STATUS       current
    DESCRIPTION
        "Cisco Firepower equipment:IOCard:power managed object property"
    ::= { cfprApEquipmentIOCardEntry 36 }

cfprApEquipmentIOCardPresence OBJECT-TYPE
    SYNTAX       CfprApEquipmentPresence
    MAX-ACCESS   read-only
    STATUS       current
    DESCRIPTION
        "Cisco Firepower equipment:IOCard:presence managed
        object property"
    ::= { cfprApEquipmentIOCardEntry 37 }

cfprApEquipmentIOCardProcessorThermalState OBJECT-TYPE
    SYNTAX       CfprApEquipmentSensorThresholdStatus
    MAX-ACCESS   read-only
    STATUS       current
    DESCRIPTION
        "Cisco Firepower equipment:IOCard:processorThermalState
        managed object property"
    ::= { cfprApEquipmentIOCardEntry 38 }

cfprApEquipmentIOCardRevision OBJECT-TYPE
    SYNTAX       SnmpAdminString
    MAX-ACCESS   read-only
    STATUS       current
    DESCRIPTION
        "Cisco Firepower equipment:IOCard:revision managed
        object property"
    ::= { cfprApEquipmentIOCardEntry 39 }

cfprApEquipmentIOCardSerial OBJECT-TYPE
    SYNTAX       SnmpAdminString
    MAX-ACCESS   read-only
    STATUS       current
    DESCRIPTION
        "Cisco Firepower equipment:IOCard:serial managed object property"
    ::= { cfprApEquipmentIOCardEntry 40 }

cfprApEquipmentIOCardSide OBJECT-TYPE
    SYNTAX       CfprApNetworkSide
    MAX-ACCESS   read-only
    STATUS       current
    DESCRIPTION
        "Cisco Firepower equipment:IOCard:side managed object property"
    ::= { cfprApEquipmentIOCardEntry 41 }

cfprApEquipmentIOCardSwitchId OBJECT-TYPE
    SYNTAX       CfprApNetworkSwitchId
    MAX-ACCESS   read-only
    STATUS       current
    DESCRIPTION
        "Cisco Firepower equipment:IOCard:switchId managed
        object property"
    ::= { cfprApEquipmentIOCardEntry 42 }

cfprApEquipmentIOCardThermal OBJECT-TYPE
    SYNTAX       CfprApEquipmentSensorThresholdStatus
    MAX-ACCESS   read-only
    STATUS       current
    DESCRIPTION
        "Cisco Firepower equipment:IOCard:thermal managed object property"
    ::= { cfprApEquipmentIOCardEntry 43 }

cfprApEquipmentIOCardUpgradeStatus OBJECT-TYPE
    SYNTAX       CfprApMgmtUpgradeStatus
    MAX-ACCESS   read-only
    STATUS       current
    DESCRIPTION
        "Cisco Firepower equipment:IOCard:upgradeStatus
        managed object property"
    ::= { cfprApEquipmentIOCardEntry 44 }

cfprApEquipmentIOCardUsrLbl OBJECT-TYPE
    SYNTAX       SnmpAdminString
    MAX-ACCESS   read-only
    STATUS       current
    DESCRIPTION
        "Cisco Firepower equipment:IOCard:usrLbl managed object property"
    ::= { cfprApEquipmentIOCardEntry 45 }

cfprApEquipmentIOCardVendor OBJECT-TYPE
    SYNTAX       SnmpAdminString
    MAX-ACCESS   read-only
    STATUS       current
    DESCRIPTION
        "Cisco Firepower equipment:IOCard:vendor managed object property"
    ::= { cfprApEquipmentIOCardEntry 46 }

cfprApEquipmentIOCardVid OBJECT-TYPE
    SYNTAX       SnmpAdminString
    MAX-ACCESS   read-only
    STATUS       current
    DESCRIPTION
        "Cisco Firepower equipment:IOCard:vid managed object property"
    ::= { cfprApEquipmentIOCardEntry 47 }

cfprApEquipmentIOCardVoltage OBJECT-TYPE
    SYNTAX       CfprApEquipmentSensorThresholdStatus
    MAX-ACCESS   read-only
    STATUS       current
    DESCRIPTION
        "Cisco Firepower equipment:IOCard:voltage managed object property"
    ::= { cfprApEquipmentIOCardEntry 48 }

cfprApEquipmentIOCardBaseFsmTable OBJECT-TYPE
    SYNTAX           SEQUENCE OF CfprApEquipmentIOCardBaseFsmEntry
    MAX-ACCESS       not-accessible
    STATUS           current
    DESCRIPTION
        "Cisco Firepower equipment:IOCardBaseFsm managed object table"
    ::= { cfprApEquipmentObjects 65 }

cfprApEquipmentIOCardBaseFsmEntry OBJECT-TYPE
    SYNTAX           CfprApEquipmentIOCardBaseFsmEntry
    MAX-ACCESS       not-accessible
    STATUS           current
    DESCRIPTION
        "Entry for the cfprApEquipmentIOCardBaseFsmTable table."
    INDEX { cfprApEquipmentIOCardBaseFsmInstanceId }
    ::= { cfprApEquipmentIOCardBaseFsmTable 1 }

CfprApEquipmentIOCardBaseFsmEntry ::= SEQUENCE {
    cfprApEquipmentIOCardBaseFsmInstanceId                           CfprApManagedObjectId,
    cfprApEquipmentIOCardBaseFsmDn                                   CfprApManagedObjectDn,
    cfprApEquipmentIOCardBaseFsmRn                                   SnmpAdminString,
    cfprApEquipmentIOCardBaseFsmCompletionTime                       DateAndTime,
    cfprApEquipmentIOCardBaseFsmCurrentFsm                           CfprApEquipmentIOCardBaseFsmCurrentFsm,
    cfprApEquipmentIOCardBaseFsmDescr                                SnmpAdminString,
    cfprApEquipmentIOCardBaseFsmFsmStatus                            CfprApFsmFsmStageStatus,
    cfprApEquipmentIOCardBaseFsmProgress                             Gauge32,
    cfprApEquipmentIOCardBaseFsmRmtErrCode                           Gauge32,
    cfprApEquipmentIOCardBaseFsmRmtErrDescr                          SnmpAdminString,
    cfprApEquipmentIOCardBaseFsmRmtRslt                              CfprApConditionRemoteInvRslt
}

cfprApEquipmentIOCardBaseFsmInstanceId OBJECT-TYPE
    SYNTAX       CfprApManagedObjectId
    MAX-ACCESS   not-accessible
    STATUS       current
    DESCRIPTION
        "Instance identifier of the managed object."
    ::= { cfprApEquipmentIOCardBaseFsmEntry 1 }

cfprApEquipmentIOCardBaseFsmDn OBJECT-TYPE
    SYNTAX       CfprApManagedObjectDn
    MAX-ACCESS   read-only
    STATUS       current
    DESCRIPTION
        "Cisco Firepower equipment:IOCardBaseFsm:dn managed
        object property"
    ::= { cfprApEquipmentIOCardBaseFsmEntry 2 }

cfprApEquipmentIOCardBaseFsmRn OBJECT-TYPE
    SYNTAX       SnmpAdminString
    MAX-ACCESS   read-only
    STATUS       current
    DESCRIPTION
        "Cisco Firepower equipment:IOCardBaseFsm:rn managed
        object property"
    ::= { cfprApEquipmentIOCardBaseFsmEntry 3 }

cfprApEquipmentIOCardBaseFsmCompletionTime OBJECT-TYPE
    SYNTAX       DateAndTime
    MAX-ACCESS   read-only
    STATUS       current
    DESCRIPTION
        "Cisco Firepower equipment:IOCardBaseFsm:completionTime
        managed object property"
    ::= { cfprApEquipmentIOCardBaseFsmEntry 4 }

cfprApEquipmentIOCardBaseFsmCurrentFsm OBJECT-TYPE
    SYNTAX       CfprApEquipmentIOCardBaseFsmCurrentFsm
    MAX-ACCESS   read-only
    STATUS       current
    DESCRIPTION
        "Cisco Firepower equipment:IOCardBaseFsm:currentFsm
        managed object property"
    ::= { cfprApEquipmentIOCardBaseFsmEntry 5 }

cfprApEquipmentIOCardBaseFsmDescr OBJECT-TYPE
    SYNTAX       SnmpAdminString
    MAX-ACCESS   read-only
    STATUS       current
    DESCRIPTION
        "Cisco Firepower equipment:IOCardBaseFsm:descr
        managed object property"
    ::= { cfprApEquipmentIOCardBaseFsmEntry 6 }

cfprApEquipmentIOCardBaseFsmFsmStatus OBJECT-TYPE
    SYNTAX       CfprApFsmFsmStageStatus
    MAX-ACCESS   read-only
    STATUS       current
    DESCRIPTION
        "Cisco Firepower equipment:IOCardBaseFsm:fsmStatus
        managed object property"
    ::= { cfprApEquipmentIOCardBaseFsmEntry 7 }

cfprApEquipmentIOCardBaseFsmProgress OBJECT-TYPE
    SYNTAX       Gauge32
    MAX-ACCESS   read-only
    STATUS       current
    DESCRIPTION
        "Cisco Firepower equipment:IOCardBaseFsm:progress
        managed object property"
    ::= { cfprApEquipmentIOCardBaseFsmEntry 8 }

cfprApEquipmentIOCardBaseFsmRmtErrCode OBJECT-TYPE
    SYNTAX       Gauge32
    MAX-ACCESS   read-only
    STATUS       current
    DESCRIPTION
        "Cisco Firepower equipment:IOCardBaseFsm:rmtErrCode
        managed object property"
    ::= { cfprApEquipmentIOCardBaseFsmEntry 9 }

cfprApEquipmentIOCardBaseFsmRmtErrDescr OBJECT-TYPE
    SYNTAX       SnmpAdminString
    MAX-ACCESS   read-only
    STATUS       current
    DESCRIPTION
        "Cisco Firepower equipment:IOCardBaseFsm:rmtErrDescr
        managed object property"
    ::= { cfprApEquipmentIOCardBaseFsmEntry 10 }

cfprApEquipmentIOCardBaseFsmRmtRslt OBJECT-TYPE
    SYNTAX       CfprApConditionRemoteInvRslt
    MAX-ACCESS   read-only
    STATUS       current
    DESCRIPTION
        "Cisco Firepower equipment:IOCardBaseFsm:rmtRslt
        managed object property"
    ::= { cfprApEquipmentIOCardBaseFsmEntry 11 }

cfprApEquipmentIOCardBaseFsmStageTable OBJECT-TYPE
    SYNTAX           SEQUENCE OF CfprApEquipmentIOCardBaseFsmStageEntry
    MAX-ACCESS       not-accessible
    STATUS           current
    DESCRIPTION
        "Cisco Firepower equipment:IOCardBaseFsmStage managed
        object table"
    ::= { cfprApEquipmentObjects 66 }

cfprApEquipmentIOCardBaseFsmStageEntry OBJECT-TYPE
    SYNTAX           CfprApEquipmentIOCardBaseFsmStageEntry
    MAX-ACCESS       not-accessible
    STATUS           current
    DESCRIPTION
        "Entry for the cfprApEquipmentIOCardBaseFsmStageTable table."
    INDEX { cfprApEquipmentIOCardBaseFsmStageInstanceId }
    ::= { cfprApEquipmentIOCardBaseFsmStageTable 1 }

CfprApEquipmentIOCardBaseFsmStageEntry ::= SEQUENCE {
    cfprApEquipmentIOCardBaseFsmStageInstanceId                      CfprApManagedObjectId,
    cfprApEquipmentIOCardBaseFsmStageDn                              CfprApManagedObjectDn,
    cfprApEquipmentIOCardBaseFsmStageRn                              SnmpAdminString,
    cfprApEquipmentIOCardBaseFsmStageDescr                           SnmpAdminString,
    cfprApEquipmentIOCardBaseFsmStageLastUpdateTime                  DateAndTime,
    cfprApEquipmentIOCardBaseFsmStageName                            CfprApEquipmentIOCardBaseFsmStageName,
    cfprApEquipmentIOCardBaseFsmStageOrder                           Gauge32,
    cfprApEquipmentIOCardBaseFsmStageRetry                           Gauge32,
    cfprApEquipmentIOCardBaseFsmStageStageStatus                     CfprApFsmFsmStageStatus
}

cfprApEquipmentIOCardBaseFsmStageInstanceId OBJECT-TYPE
    SYNTAX       CfprApManagedObjectId
    MAX-ACCESS   not-accessible
    STATUS       current
    DESCRIPTION
        "Instance identifier of the managed object."
    ::= { cfprApEquipmentIOCardBaseFsmStageEntry 1 }

cfprApEquipmentIOCardBaseFsmStageDn OBJECT-TYPE
    SYNTAX       CfprApManagedObjectDn
    MAX-ACCESS   read-only
    STATUS       current
    DESCRIPTION
        "Cisco Firepower equipment:IOCardBaseFsmStage:dn
        managed object property"
    ::= { cfprApEquipmentIOCardBaseFsmStageEntry 2 }

cfprApEquipmentIOCardBaseFsmStageRn OBJECT-TYPE
    SYNTAX       SnmpAdminString
    MAX-ACCESS   read-only
    STATUS       current
    DESCRIPTION
        "Cisco Firepower equipment:IOCardBaseFsmStage:rn
        managed object property"
    ::= { cfprApEquipmentIOCardBaseFsmStageEntry 3 }

cfprApEquipmentIOCardBaseFsmStageDescr OBJECT-TYPE
    SYNTAX       SnmpAdminString
    MAX-ACCESS   read-only
    STATUS       current
    DESCRIPTION
        "Cisco Firepower equipment:IOCardBaseFsmStage:descr
        managed object property"
    ::= { cfprApEquipmentIOCardBaseFsmStageEntry 4 }

cfprApEquipmentIOCardBaseFsmStageLastUpdateTime OBJECT-TYPE
    SYNTAX       DateAndTime
    MAX-ACCESS   read-only
    STATUS       current
    DESCRIPTION
        "Cisco Firepower equipment:IOCardBaseFsmStage:lastUpdateTime
        managed object property"
    ::= { cfprApEquipmentIOCardBaseFsmStageEntry 5 }

cfprApEquipmentIOCardBaseFsmStageName OBJECT-TYPE
    SYNTAX       CfprApEquipmentIOCardBaseFsmStageName
    MAX-ACCESS   read-only
    STATUS       current
    DESCRIPTION
        "Cisco Firepower equipment:IOCardBaseFsmStage:name
        managed object property"
    ::= { cfprApEquipmentIOCardBaseFsmStageEntry 6 }

cfprApEquipmentIOCardBaseFsmStageOrder OBJECT-TYPE
    SYNTAX       Gauge32
    MAX-ACCESS   read-only
    STATUS       current
    DESCRIPTION
        "Cisco Firepower equipment:IOCardBaseFsmStage:order
        managed object property"
    ::= { cfprApEquipmentIOCardBaseFsmStageEntry 7 }

cfprApEquipmentIOCardBaseFsmStageRetry OBJECT-TYPE
    SYNTAX       Gauge32
    MAX-ACCESS   read-only
    STATUS       current
    DESCRIPTION
        "Cisco Firepower equipment:IOCardBaseFsmStage:retry
        managed object property"
    ::= { cfprApEquipmentIOCardBaseFsmStageEntry 8 }

cfprApEquipmentIOCardBaseFsmStageStageStatus OBJECT-TYPE
    SYNTAX       CfprApFsmFsmStageStatus
    MAX-ACCESS   read-only
    STATUS       current
    DESCRIPTION
        "Cisco Firepower equipment:IOCardBaseFsmStage:stageStatus
        managed object property"
    ::= { cfprApEquipmentIOCardBaseFsmStageEntry 9 }

cfprApEquipmentIOCardBaseFsmTaskTable OBJECT-TYPE
    SYNTAX           SEQUENCE OF CfprApEquipmentIOCardBaseFsmTaskEntry
    MAX-ACCESS       not-accessible
    STATUS           current
    DESCRIPTION
        "Cisco Firepower equipment:IOCardBaseFsmTask managed object table"
    ::= { cfprApEquipmentObjects 67 }

cfprApEquipmentIOCardBaseFsmTaskEntry OBJECT-TYPE
    SYNTAX           CfprApEquipmentIOCardBaseFsmTaskEntry
    MAX-ACCESS       not-accessible
    STATUS           current
    DESCRIPTION
        "Entry for the cfprApEquipmentIOCardBaseFsmTaskTable table."
    INDEX { cfprApEquipmentIOCardBaseFsmTaskInstanceId }
    ::= { cfprApEquipmentIOCardBaseFsmTaskTable 1 }

CfprApEquipmentIOCardBaseFsmTaskEntry ::= SEQUENCE {
    cfprApEquipmentIOCardBaseFsmTaskInstanceId                       CfprApManagedObjectId,
    cfprApEquipmentIOCardBaseFsmTaskDn                               CfprApManagedObjectDn,
    cfprApEquipmentIOCardBaseFsmTaskRn                               SnmpAdminString,
    cfprApEquipmentIOCardBaseFsmTaskCompletion                       CfprApFsmCompletion,
    cfprApEquipmentIOCardBaseFsmTaskFlags                            CfprApEquipmentIOCardBaseFsmTaskFlags,
    cfprApEquipmentIOCardBaseFsmTaskItem                             CfprApEquipmentIOCardBaseFsmTaskItem,
    cfprApEquipmentIOCardBaseFsmTaskSeqId                            Gauge32
}

cfprApEquipmentIOCardBaseFsmTaskInstanceId OBJECT-TYPE
    SYNTAX       CfprApManagedObjectId
    MAX-ACCESS   not-accessible
    STATUS       current
    DESCRIPTION
        "Instance identifier of the managed object."
    ::= { cfprApEquipmentIOCardBaseFsmTaskEntry 1 }

cfprApEquipmentIOCardBaseFsmTaskDn OBJECT-TYPE
    SYNTAX       CfprApManagedObjectDn
    MAX-ACCESS   read-only
    STATUS       current
    DESCRIPTION
        "Cisco Firepower equipment:IOCardBaseFsmTask:dn
        managed object property"
    ::= { cfprApEquipmentIOCardBaseFsmTaskEntry 2 }

cfprApEquipmentIOCardBaseFsmTaskRn OBJECT-TYPE
    SYNTAX       SnmpAdminString
    MAX-ACCESS   read-only
    STATUS       current
    DESCRIPTION
        "Cisco Firepower equipment:IOCardBaseFsmTask:rn
        managed object property"
    ::= { cfprApEquipmentIOCardBaseFsmTaskEntry 3 }

cfprApEquipmentIOCardBaseFsmTaskCompletion OBJECT-TYPE
    SYNTAX       CfprApFsmCompletion
    MAX-ACCESS   read-only
    STATUS       current
    DESCRIPTION
        "Cisco Firepower equipment:IOCardBaseFsmTask:completion
        managed object property"
    ::= { cfprApEquipmentIOCardBaseFsmTaskEntry 4 }

cfprApEquipmentIOCardBaseFsmTaskFlags OBJECT-TYPE
    SYNTAX       CfprApEquipmentIOCardBaseFsmTaskFlags
    MAX-ACCESS   read-only
    STATUS       current
    DESCRIPTION
        "Cisco Firepower equipment:IOCardBaseFsmTask:flags
        managed object property"
    ::= { cfprApEquipmentIOCardBaseFsmTaskEntry 5 }

cfprApEquipmentIOCardBaseFsmTaskItem OBJECT-TYPE
    SYNTAX       CfprApEquipmentIOCardBaseFsmTaskItem
    MAX-ACCESS   read-only
    STATUS       current
    DESCRIPTION
        "Cisco Firepower equipment:IOCardBaseFsmTask:item
        managed object property"
    ::= { cfprApEquipmentIOCardBaseFsmTaskEntry 6 }

cfprApEquipmentIOCardBaseFsmTaskSeqId OBJECT-TYPE
    SYNTAX       Gauge32
    MAX-ACCESS   read-only
    STATUS       current
    DESCRIPTION
        "Cisco Firepower equipment:IOCardBaseFsmTask:seqId
        managed object property"
    ::= { cfprApEquipmentIOCardBaseFsmTaskEntry 7 }

cfprApEquipmentIOCardCapProviderTable OBJECT-TYPE
    SYNTAX           SEQUENCE OF CfprApEquipmentIOCardCapProviderEntry
    MAX-ACCESS       not-accessible
    STATUS           current
    DESCRIPTION
        "Cisco Firepower equipment:IOCardCapProvider managed object table"
    ::= { cfprApEquipmentObjects 68 }

cfprApEquipmentIOCardCapProviderEntry OBJECT-TYPE
    SYNTAX           CfprApEquipmentIOCardCapProviderEntry
    MAX-ACCESS       not-accessible
    STATUS           current
    DESCRIPTION
        "Entry for the cfprApEquipmentIOCardCapProviderTable table."
    INDEX { cfprApEquipmentIOCardCapProviderInstanceId }
    ::= { cfprApEquipmentIOCardCapProviderTable 1 }

CfprApEquipmentIOCardCapProviderEntry ::= SEQUENCE {
    cfprApEquipmentIOCardCapProviderInstanceId                       CfprApManagedObjectId,
    cfprApEquipmentIOCardCapProviderDn                               CfprApManagedObjectDn,
    cfprApEquipmentIOCardCapProviderRn                               SnmpAdminString,
    cfprApEquipmentIOCardCapProviderDeleted                          TruthValue,
    cfprApEquipmentIOCardCapProviderDeprecated                       TruthValue,
    cfprApEquipmentIOCardCapProviderElementLoadFailures              Gauge32,
    cfprApEquipmentIOCardCapProviderElementsLoaded                   Gauge32,
    cfprApEquipmentIOCardCapProviderGencount                         Gauge32,
    cfprApEquipmentIOCardCapProviderLoadErrors                       Gauge32,
    cfprApEquipmentIOCardCapProviderLoadWarnings                     Gauge32,
    cfprApEquipmentIOCardCapProviderMgmtPlaneVer                     SnmpAdminString,
    cfprApEquipmentIOCardCapProviderModel                            SnmpAdminString,
    cfprApEquipmentIOCardCapProviderPromCardType                     Gauge32,
    cfprApEquipmentIOCardCapProviderRevision                         SnmpAdminString,
    cfprApEquipmentIOCardCapProviderVendor                           SnmpAdminString
}

cfprApEquipmentIOCardCapProviderInstanceId OBJECT-TYPE
    SYNTAX       CfprApManagedObjectId
    MAX-ACCESS   not-accessible
    STATUS       current
    DESCRIPTION
        "Instance identifier of the managed object."
    ::= { cfprApEquipmentIOCardCapProviderEntry 1 }

cfprApEquipmentIOCardCapProviderDn OBJECT-TYPE
    SYNTAX       CfprApManagedObjectDn
    MAX-ACCESS   read-only
    STATUS       current
    DESCRIPTION
        "Cisco Firepower equipment:IOCardCapProvider:dn
        managed object property"
    ::= { cfprApEquipmentIOCardCapProviderEntry 2 }

cfprApEquipmentIOCardCapProviderRn OBJECT-TYPE
    SYNTAX       SnmpAdminString
    MAX-ACCESS   read-only
    STATUS       current
    DESCRIPTION
        "Cisco Firepower equipment:IOCardCapProvider:rn
        managed object property"
    ::= { cfprApEquipmentIOCardCapProviderEntry 3 }

cfprApEquipmentIOCardCapProviderDeleted OBJECT-TYPE
    SYNTAX       TruthValue
    MAX-ACCESS   read-only
    STATUS       current
    DESCRIPTION
        "Cisco Firepower equipment:IOCardCapProvider:deleted
        managed object property"
    ::= { cfprApEquipmentIOCardCapProviderEntry 4 }

cfprApEquipmentIOCardCapProviderDeprecated OBJECT-TYPE
    SYNTAX       TruthValue
    MAX-ACCESS   read-only
    STATUS       current
    DESCRIPTION
        "Cisco Firepower equipment:IOCardCapProvider:deprecated
        managed object property"
    ::= { cfprApEquipmentIOCardCapProviderEntry 5 }

cfprApEquipmentIOCardCapProviderElementLoadFailures OBJECT-TYPE
    SYNTAX       Gauge32
    MAX-ACCESS   read-only
    STATUS       current
    DESCRIPTION
        "Cisco Firepower equipment:IOCardCapProvider:elementLoadFailures
        managed object property"
    ::= { cfprApEquipmentIOCardCapProviderEntry 6 }

cfprApEquipmentIOCardCapProviderElementsLoaded OBJECT-TYPE
    SYNTAX       Gauge32
    MAX-ACCESS   read-only
    STATUS       current
    DESCRIPTION
        "Cisco Firepower equipment:IOCardCapProvider:elementsLoaded
        managed object property"
    ::= { cfprApEquipmentIOCardCapProviderEntry 7 }

cfprApEquipmentIOCardCapProviderGencount OBJECT-TYPE
    SYNTAX       Gauge32
    MAX-ACCESS   read-only
    STATUS       current
    DESCRIPTION
        "Cisco Firepower equipment:IOCardCapProvider:gencount
        managed object property"
    ::= { cfprApEquipmentIOCardCapProviderEntry 8 }

cfprApEquipmentIOCardCapProviderLoadErrors OBJECT-TYPE
    SYNTAX       Gauge32
    MAX-ACCESS   read-only
    STATUS       current
    DESCRIPTION
        "Cisco Firepower equipment:IOCardCapProvider:loadErrors
        managed object property"
    ::= { cfprApEquipmentIOCardCapProviderEntry 9 }

cfprApEquipmentIOCardCapProviderLoadWarnings OBJECT-TYPE
    SYNTAX       Gauge32
    MAX-ACCESS   read-only
    STATUS       current
    DESCRIPTION
        "Cisco Firepower equipment:IOCardCapProvider:loadWarnings
        managed object property"
    ::= { cfprApEquipmentIOCardCapProviderEntry 10 }

cfprApEquipmentIOCardCapProviderMgmtPlaneVer OBJECT-TYPE
    SYNTAX       SnmpAdminString
    MAX-ACCESS   read-only
    STATUS       current
    DESCRIPTION
        "Cisco Firepower equipment:IOCardCapProvider:mgmtPlaneVer
        managed object property"
    ::= { cfprApEquipmentIOCardCapProviderEntry 11 }

cfprApEquipmentIOCardCapProviderModel OBJECT-TYPE
    SYNTAX       SnmpAdminString
    MAX-ACCESS   read-only
    STATUS       current
    DESCRIPTION
        "Cisco Firepower equipment:IOCardCapProvider:model
        managed object property"
    ::= { cfprApEquipmentIOCardCapProviderEntry 12 }

cfprApEquipmentIOCardCapProviderPromCardType OBJECT-TYPE
    SYNTAX       Gauge32
    MAX-ACCESS   read-only
    STATUS       current
    DESCRIPTION
        "Cisco Firepower equipment:IOCardCapProvider:promCardType
        managed object property"
    ::= { cfprApEquipmentIOCardCapProviderEntry 13 }

cfprApEquipmentIOCardCapProviderRevision OBJECT-TYPE
    SYNTAX       SnmpAdminString
    MAX-ACCESS   read-only
    STATUS       current
    DESCRIPTION
        "Cisco Firepower equipment:IOCardCapProvider:revision
        managed object property"
    ::= { cfprApEquipmentIOCardCapProviderEntry 14 }

cfprApEquipmentIOCardCapProviderVendor OBJECT-TYPE
    SYNTAX       SnmpAdminString
    MAX-ACCESS   read-only
    STATUS       current
    DESCRIPTION
        "Cisco Firepower equipment:IOCardCapProvider:vendor
        managed object property"
    ::= { cfprApEquipmentIOCardCapProviderEntry 15 }

cfprApEquipmentIOCardFsmTable OBJECT-TYPE
    SYNTAX           SEQUENCE OF CfprApEquipmentIOCardFsmEntry
    MAX-ACCESS       not-accessible
    STATUS           current
    DESCRIPTION
        "Cisco Firepower equipment:IOCardFsm managed object table"
    ::= { cfprApEquipmentObjects 69 }

cfprApEquipmentIOCardFsmEntry OBJECT-TYPE
    SYNTAX           CfprApEquipmentIOCardFsmEntry
    MAX-ACCESS       not-accessible
    STATUS           current
    DESCRIPTION
        "Entry for the cfprApEquipmentIOCardFsmTable table."
    INDEX { cfprApEquipmentIOCardFsmInstanceId }
    ::= { cfprApEquipmentIOCardFsmTable 1 }

CfprApEquipmentIOCardFsmEntry ::= SEQUENCE {
    cfprApEquipmentIOCardFsmInstanceId                               CfprApManagedObjectId,
    cfprApEquipmentIOCardFsmDn                                       CfprApManagedObjectDn,
    cfprApEquipmentIOCardFsmRn                                       SnmpAdminString,
    cfprApEquipmentIOCardFsmCompletionTime                           DateAndTime,
    cfprApEquipmentIOCardFsmCurrentFsm                               CfprApEquipmentIOCardFsmCurrentFsm,
    cfprApEquipmentIOCardFsmDescrData                                SnmpAdminString,
    cfprApEquipmentIOCardFsmFsmStatus                                CfprApFsmFsmStageStatus,
    cfprApEquipmentIOCardFsmProgress                                 Gauge32,
    cfprApEquipmentIOCardFsmRmtErrCode                               Gauge32,
    cfprApEquipmentIOCardFsmRmtErrDescr                              SnmpAdminString,
    cfprApEquipmentIOCardFsmRmtRslt                                  CfprApConditionRemoteInvRslt
}

cfprApEquipmentIOCardFsmInstanceId OBJECT-TYPE
    SYNTAX       CfprApManagedObjectId
    MAX-ACCESS   not-accessible
    STATUS       current
    DESCRIPTION
        "Instance identifier of the managed object."
    ::= { cfprApEquipmentIOCardFsmEntry 1 }

cfprApEquipmentIOCardFsmDn OBJECT-TYPE
    SYNTAX       CfprApManagedObjectDn
    MAX-ACCESS   read-only
    STATUS       current
    DESCRIPTION
        "Cisco Firepower equipment:IOCardFsm:dn managed object property"
    ::= { cfprApEquipmentIOCardFsmEntry 2 }

cfprApEquipmentIOCardFsmRn OBJECT-TYPE
    SYNTAX       SnmpAdminString
    MAX-ACCESS   read-only
    STATUS       current
    DESCRIPTION
        "Cisco Firepower equipment:IOCardFsm:rn managed object property"
    ::= { cfprApEquipmentIOCardFsmEntry 3 }

cfprApEquipmentIOCardFsmCompletionTime OBJECT-TYPE
    SYNTAX       DateAndTime
    MAX-ACCESS   read-only
    STATUS       current
    DESCRIPTION
        "Cisco Firepower equipment:IOCardFsm:completionTime
        managed object property"
    ::= { cfprApEquipmentIOCardFsmEntry 4 }

cfprApEquipmentIOCardFsmCurrentFsm OBJECT-TYPE
    SYNTAX       CfprApEquipmentIOCardFsmCurrentFsm
    MAX-ACCESS   read-only
    STATUS       current
    DESCRIPTION
        "Cisco Firepower equipment:IOCardFsm:currentFsm
        managed object property"
    ::= { cfprApEquipmentIOCardFsmEntry 5 }

cfprApEquipmentIOCardFsmDescrData OBJECT-TYPE
    SYNTAX       SnmpAdminString
    MAX-ACCESS   read-only
    STATUS       current
    DESCRIPTION
        "Cisco Firepower equipment:IOCardFsm:descr managed
        object property"
    ::= { cfprApEquipmentIOCardFsmEntry 6 }

cfprApEquipmentIOCardFsmFsmStatus OBJECT-TYPE
    SYNTAX       CfprApFsmFsmStageStatus
    MAX-ACCESS   read-only
    STATUS       current
    DESCRIPTION
        "Cisco Firepower equipment:IOCardFsm:fsmStatus
        managed object property"
    ::= { cfprApEquipmentIOCardFsmEntry 7 }

cfprApEquipmentIOCardFsmProgress OBJECT-TYPE
    SYNTAX       Gauge32
    MAX-ACCESS   read-only
    STATUS       current
    DESCRIPTION
        "Cisco Firepower equipment:IOCardFsm:progress managed
        object property"
    ::= { cfprApEquipmentIOCardFsmEntry 8 }

cfprApEquipmentIOCardFsmRmtErrCode OBJECT-TYPE
    SYNTAX       Gauge32
    MAX-ACCESS   read-only
    STATUS       current
    DESCRIPTION
        "Cisco Firepower equipment:IOCardFsm:rmtErrCode
        managed object property"
    ::= { cfprApEquipmentIOCardFsmEntry 9 }

cfprApEquipmentIOCardFsmRmtErrDescr OBJECT-TYPE
    SYNTAX       SnmpAdminString
    MAX-ACCESS   read-only
    STATUS       current
    DESCRIPTION
        "Cisco Firepower equipment:IOCardFsm:rmtErrDescr
        managed object property"
    ::= { cfprApEquipmentIOCardFsmEntry 10 }

cfprApEquipmentIOCardFsmRmtRslt OBJECT-TYPE
    SYNTAX       CfprApConditionRemoteInvRslt
    MAX-ACCESS   read-only
    STATUS       current
    DESCRIPTION
        "Cisco Firepower equipment:IOCardFsm:rmtRslt managed
        object property"
    ::= { cfprApEquipmentIOCardFsmEntry 11 }

cfprApEquipmentIOCardFsmStageTable OBJECT-TYPE
    SYNTAX           SEQUENCE OF CfprApEquipmentIOCardFsmStageEntry
    MAX-ACCESS       not-accessible
    STATUS           current
    DESCRIPTION
        "Cisco Firepower equipment:IOCardFsmStage managed object table"
    ::= { cfprApEquipmentObjects 70 }

cfprApEquipmentIOCardFsmStageEntry OBJECT-TYPE
    SYNTAX           CfprApEquipmentIOCardFsmStageEntry
    MAX-ACCESS       not-accessible
    STATUS           current
    DESCRIPTION
        "Entry for the cfprApEquipmentIOCardFsmStageTable table."
    INDEX { cfprApEquipmentIOCardFsmStageInstanceId }
    ::= { cfprApEquipmentIOCardFsmStageTable 1 }

CfprApEquipmentIOCardFsmStageEntry ::= SEQUENCE {
    cfprApEquipmentIOCardFsmStageInstanceId                          CfprApManagedObjectId,
    cfprApEquipmentIOCardFsmStageDn                                  CfprApManagedObjectDn,
    cfprApEquipmentIOCardFsmStageRn                                  SnmpAdminString,
    cfprApEquipmentIOCardFsmStageDescrData                           SnmpAdminString,
    cfprApEquipmentIOCardFsmStageLastUpdateTime                      DateAndTime,
    cfprApEquipmentIOCardFsmStageName                                CfprApEquipmentIOCardFsmStageName,
    cfprApEquipmentIOCardFsmStageOrder                               Gauge32,
    cfprApEquipmentIOCardFsmStageRetry                               Gauge32,
    cfprApEquipmentIOCardFsmStageStageStatus                         CfprApFsmFsmStageStatus
}

cfprApEquipmentIOCardFsmStageInstanceId OBJECT-TYPE
    SYNTAX       CfprApManagedObjectId
    MAX-ACCESS   not-accessible
    STATUS       current
    DESCRIPTION
        "Instance identifier of the managed object."
    ::= { cfprApEquipmentIOCardFsmStageEntry 1 }

cfprApEquipmentIOCardFsmStageDn OBJECT-TYPE
    SYNTAX       CfprApManagedObjectDn
    MAX-ACCESS   read-only
    STATUS       current
    DESCRIPTION
        "Cisco Firepower equipment:IOCardFsmStage:dn managed
        object property"
    ::= { cfprApEquipmentIOCardFsmStageEntry 2 }

cfprApEquipmentIOCardFsmStageRn OBJECT-TYPE
    SYNTAX       SnmpAdminString
    MAX-ACCESS   read-only
    STATUS       current
    DESCRIPTION
        "Cisco Firepower equipment:IOCardFsmStage:rn managed
        object property"
    ::= { cfprApEquipmentIOCardFsmStageEntry 3 }

cfprApEquipmentIOCardFsmStageDescrData OBJECT-TYPE
    SYNTAX       SnmpAdminString
    MAX-ACCESS   read-only
    STATUS       current
    DESCRIPTION
        "Cisco Firepower equipment:IOCardFsmStage:descr
        managed object property"
    ::= { cfprApEquipmentIOCardFsmStageEntry 4 }

cfprApEquipmentIOCardFsmStageLastUpdateTime OBJECT-TYPE
    SYNTAX       DateAndTime
    MAX-ACCESS   read-only
    STATUS       current
    DESCRIPTION
        "Cisco Firepower equipment:IOCardFsmStage:lastUpdateTime
        managed object property"
    ::= { cfprApEquipmentIOCardFsmStageEntry 5 }

cfprApEquipmentIOCardFsmStageName OBJECT-TYPE
    SYNTAX       CfprApEquipmentIOCardFsmStageName
    MAX-ACCESS   read-only
    STATUS       current
    DESCRIPTION
        "Cisco Firepower equipment:IOCardFsmStage:name
        managed object property"
    ::= { cfprApEquipmentIOCardFsmStageEntry 6 }

cfprApEquipmentIOCardFsmStageOrder OBJECT-TYPE
    SYNTAX       Gauge32
    MAX-ACCESS   read-only
    STATUS       current
    DESCRIPTION
        "Cisco Firepower equipment:IOCardFsmStage:order
        managed object property"
    ::= { cfprApEquipmentIOCardFsmStageEntry 7 }

cfprApEquipmentIOCardFsmStageRetry OBJECT-TYPE
    SYNTAX       Gauge32
    MAX-ACCESS   read-only
    STATUS       current
    DESCRIPTION
        "Cisco Firepower equipment:IOCardFsmStage:retry
        managed object property"
    ::= { cfprApEquipmentIOCardFsmStageEntry 8 }

cfprApEquipmentIOCardFsmStageStageStatus OBJECT-TYPE
    SYNTAX       CfprApFsmFsmStageStatus
    MAX-ACCESS   read-only
    STATUS       current
    DESCRIPTION
        "Cisco Firepower equipment:IOCardFsmStage:stageStatus
        managed object property"
    ::= { cfprApEquipmentIOCardFsmStageEntry 9 }

cfprApEquipmentIOCardFsmTaskTable OBJECT-TYPE
    SYNTAX           SEQUENCE OF CfprApEquipmentIOCardFsmTaskEntry
    MAX-ACCESS       not-accessible
    STATUS           current
    DESCRIPTION
        "Cisco Firepower equipment:IOCardFsmTask managed object table"
    ::= { cfprApEquipmentObjects 71 }

cfprApEquipmentIOCardFsmTaskEntry OBJECT-TYPE
    SYNTAX           CfprApEquipmentIOCardFsmTaskEntry
    MAX-ACCESS       not-accessible
    STATUS           current
    DESCRIPTION
        "Entry for the cfprApEquipmentIOCardFsmTaskTable table."
    INDEX { cfprApEquipmentIOCardFsmTaskInstanceId }
    ::= { cfprApEquipmentIOCardFsmTaskTable 1 }

CfprApEquipmentIOCardFsmTaskEntry ::= SEQUENCE {
    cfprApEquipmentIOCardFsmTaskInstanceId                           CfprApManagedObjectId,
    cfprApEquipmentIOCardFsmTaskDn                                   CfprApManagedObjectDn,
    cfprApEquipmentIOCardFsmTaskRn                                   SnmpAdminString,
    cfprApEquipmentIOCardFsmTaskCompletion                           CfprApFsmCompletion,
    cfprApEquipmentIOCardFsmTaskFlags                                CfprApFsmFlags,
    cfprApEquipmentIOCardFsmTaskItem                                 CfprApEquipmentIOCardFsmTaskItem,
    cfprApEquipmentIOCardFsmTaskSeqId                                Gauge32
}

cfprApEquipmentIOCardFsmTaskInstanceId OBJECT-TYPE
    SYNTAX       CfprApManagedObjectId
    MAX-ACCESS   not-accessible
    STATUS       current
    DESCRIPTION
        "Instance identifier of the managed object."
    ::= { cfprApEquipmentIOCardFsmTaskEntry 1 }

cfprApEquipmentIOCardFsmTaskDn OBJECT-TYPE
    SYNTAX       CfprApManagedObjectDn
    MAX-ACCESS   read-only
    STATUS       current
    DESCRIPTION
        "Cisco Firepower equipment:IOCardFsmTask:dn managed
        object property"
    ::= { cfprApEquipmentIOCardFsmTaskEntry 2 }

cfprApEquipmentIOCardFsmTaskRn OBJECT-TYPE
    SYNTAX       SnmpAdminString
    MAX-ACCESS   read-only
    STATUS       current
    DESCRIPTION
        "Cisco Firepower equipment:IOCardFsmTask:rn managed
        object property"
    ::= { cfprApEquipmentIOCardFsmTaskEntry 3 }

cfprApEquipmentIOCardFsmTaskCompletion OBJECT-TYPE
    SYNTAX       CfprApFsmCompletion
    MAX-ACCESS   read-only
    STATUS       current
    DESCRIPTION
        "Cisco Firepower equipment:IOCardFsmTask:completion
        managed object property"
    ::= { cfprApEquipmentIOCardFsmTaskEntry 4 }

cfprApEquipmentIOCardFsmTaskFlags OBJECT-TYPE
    SYNTAX       CfprApFsmFlags
    MAX-ACCESS   read-only
    STATUS       current
    DESCRIPTION
        "Cisco Firepower equipment:IOCardFsmTask:flags
        managed object property"
    ::= { cfprApEquipmentIOCardFsmTaskEntry 5 }

cfprApEquipmentIOCardFsmTaskItem OBJECT-TYPE
    SYNTAX       CfprApEquipmentIOCardFsmTaskItem
    MAX-ACCESS   read-only
    STATUS       current
    DESCRIPTION
        "Cisco Firepower equipment:IOCardFsmTask:item managed
        object property"
    ::= { cfprApEquipmentIOCardFsmTaskEntry 6 }

cfprApEquipmentIOCardFsmTaskSeqId OBJECT-TYPE
    SYNTAX       Gauge32
    MAX-ACCESS   read-only
    STATUS       current
    DESCRIPTION
        "Cisco Firepower equipment:IOCardFsmTask:seqId
        managed object property"
    ::= { cfprApEquipmentIOCardFsmTaskEntry 7 }

cfprApEquipmentIOCardStatsTable OBJECT-TYPE
    SYNTAX           SEQUENCE OF CfprApEquipmentIOCardStatsEntry
    MAX-ACCESS       not-accessible
    STATUS           current
    DESCRIPTION
        "Cisco Firepower equipment:IOCardStats managed object table"
    ::= { cfprApEquipmentObjects 72 }

cfprApEquipmentIOCardStatsEntry OBJECT-TYPE
    SYNTAX           CfprApEquipmentIOCardStatsEntry
    MAX-ACCESS       not-accessible
    STATUS           current
    DESCRIPTION
        "Entry for the cfprApEquipmentIOCardStatsTable table."
    INDEX { cfprApEquipmentIOCardStatsInstanceId }
    ::= { cfprApEquipmentIOCardStatsTable 1 }

CfprApEquipmentIOCardStatsEntry ::= SEQUENCE {
    cfprApEquipmentIOCardStatsInstanceId                             CfprApManagedObjectId,
    cfprApEquipmentIOCardStatsDn                                     CfprApManagedObjectDn,
    cfprApEquipmentIOCardStatsRn                                     SnmpAdminString,
    cfprApEquipmentIOCardStatsAmbientTemp                            INTEGER,
    cfprApEquipmentIOCardStatsAmbientTempAvg                         INTEGER,
    cfprApEquipmentIOCardStatsAmbientTempMax                         INTEGER,
    cfprApEquipmentIOCardStatsAmbientTempMin                         INTEGER,
    cfprApEquipmentIOCardStatsDimmTemp                               INTEGER,
    cfprApEquipmentIOCardStatsDimmTempAvg                            INTEGER,
    cfprApEquipmentIOCardStatsDimmTempMax                            INTEGER,
    cfprApEquipmentIOCardStatsDimmTempMin                            INTEGER,
    cfprApEquipmentIOCardStatsIntervals                              Gauge32,
    cfprApEquipmentIOCardStatsProcTemp                               INTEGER,
    cfprApEquipmentIOCardStatsProcTempAvg                            INTEGER,
    cfprApEquipmentIOCardStatsProcTempMax                            INTEGER,
    cfprApEquipmentIOCardStatsProcTempMin                            INTEGER,
    cfprApEquipmentIOCardStatsSuspect                                TruthValue,
    cfprApEquipmentIOCardStatsTemp                                   INTEGER,
    cfprApEquipmentIOCardStatsTempAvg                                INTEGER,
    cfprApEquipmentIOCardStatsTempMax                                INTEGER,
    cfprApEquipmentIOCardStatsTempMin                                INTEGER,
    cfprApEquipmentIOCardStatsThresholded                            CfprApEquipmentIOCardStatsThresholded,
    cfprApEquipmentIOCardStatsTimeCollected                          DateAndTime,
    cfprApEquipmentIOCardStatsUpdate                                 Gauge32
}

cfprApEquipmentIOCardStatsInstanceId OBJECT-TYPE
    SYNTAX       CfprApManagedObjectId
    MAX-ACCESS   not-accessible
    STATUS       current
    DESCRIPTION
        "Instance identifier of the managed object."
    ::= { cfprApEquipmentIOCardStatsEntry 1 }

cfprApEquipmentIOCardStatsDn OBJECT-TYPE
    SYNTAX       CfprApManagedObjectDn
    MAX-ACCESS   read-only
    STATUS       current
    DESCRIPTION
        "Cisco Firepower equipment:IOCardStats:dn managed object property"
    ::= { cfprApEquipmentIOCardStatsEntry 2 }

cfprApEquipmentIOCardStatsRn OBJECT-TYPE
    SYNTAX       SnmpAdminString
    MAX-ACCESS   read-only
    STATUS       current
    DESCRIPTION
        "Cisco Firepower equipment:IOCardStats:rn managed object property"
    ::= { cfprApEquipmentIOCardStatsEntry 3 }

cfprApEquipmentIOCardStatsAmbientTemp OBJECT-TYPE
    SYNTAX       INTEGER
    MAX-ACCESS   read-only
    STATUS       current
    DESCRIPTION
        "Cisco Firepower equipment:IOCardStats:ambientTemp
        managed object property"
    ::= { cfprApEquipmentIOCardStatsEntry 4 }

cfprApEquipmentIOCardStatsAmbientTempAvg OBJECT-TYPE
    SYNTAX       INTEGER
    MAX-ACCESS   read-only
    STATUS       current
    DESCRIPTION
        "Cisco Firepower equipment:IOCardStats:ambientTempAvg
        managed object property"
    ::= { cfprApEquipmentIOCardStatsEntry 5 }

cfprApEquipmentIOCardStatsAmbientTempMax OBJECT-TYPE
    SYNTAX       INTEGER
    MAX-ACCESS   read-only
    STATUS       current
    DESCRIPTION
        "Cisco Firepower equipment:IOCardStats:ambientTempMax
        managed object property"
    ::= { cfprApEquipmentIOCardStatsEntry 6 }

cfprApEquipmentIOCardStatsAmbientTempMin OBJECT-TYPE
    SYNTAX       INTEGER
    MAX-ACCESS   read-only
    STATUS       current
    DESCRIPTION
        "Cisco Firepower equipment:IOCardStats:ambientTempMin
        managed object property"
    ::= { cfprApEquipmentIOCardStatsEntry 7 }

cfprApEquipmentIOCardStatsDimmTemp OBJECT-TYPE
    SYNTAX       INTEGER
    MAX-ACCESS   read-only
    STATUS       current
    DESCRIPTION
        "Cisco Firepower equipment:IOCardStats:dimmTemp
        managed object property"
    ::= { cfprApEquipmentIOCardStatsEntry 8 }

cfprApEquipmentIOCardStatsDimmTempAvg OBJECT-TYPE
    SYNTAX       INTEGER
    MAX-ACCESS   read-only
    STATUS       current
    DESCRIPTION
        "Cisco Firepower equipment:IOCardStats:dimmTempAvg
        managed object property"
    ::= { cfprApEquipmentIOCardStatsEntry 9 }

cfprApEquipmentIOCardStatsDimmTempMax OBJECT-TYPE
    SYNTAX       INTEGER
    MAX-ACCESS   read-only
    STATUS       current
    DESCRIPTION
        "Cisco Firepower equipment:IOCardStats:dimmTempMax
        managed object property"
    ::= { cfprApEquipmentIOCardStatsEntry 10 }

cfprApEquipmentIOCardStatsDimmTempMin OBJECT-TYPE
    SYNTAX       INTEGER
    MAX-ACCESS   read-only
    STATUS       current
    DESCRIPTION
        "Cisco Firepower equipment:IOCardStats:dimmTempMin
        managed object property"
    ::= { cfprApEquipmentIOCardStatsEntry 11 }

cfprApEquipmentIOCardStatsIntervals OBJECT-TYPE
    SYNTAX       Gauge32
    MAX-ACCESS   read-only
    STATUS       current
    DESCRIPTION
        "Cisco Firepower equipment:IOCardStats:intervals
        managed object property"
    ::= { cfprApEquipmentIOCardStatsEntry 12 }

cfprApEquipmentIOCardStatsProcTemp OBJECT-TYPE
    SYNTAX       INTEGER
    MAX-ACCESS   read-only
    STATUS       current
    DESCRIPTION
        "Cisco Firepower equipment:IOCardStats:procTemp
        managed object property"
    ::= { cfprApEquipmentIOCardStatsEntry 13 }

cfprApEquipmentIOCardStatsProcTempAvg OBJECT-TYPE
    SYNTAX       INTEGER
    MAX-ACCESS   read-only
    STATUS       current
    DESCRIPTION
        "Cisco Firepower equipment:IOCardStats:procTempAvg
        managed object property"
    ::= { cfprApEquipmentIOCardStatsEntry 14 }

cfprApEquipmentIOCardStatsProcTempMax OBJECT-TYPE
    SYNTAX       INTEGER
    MAX-ACCESS   read-only
    STATUS       current
    DESCRIPTION
        "Cisco Firepower equipment:IOCardStats:procTempMax
        managed object property"
    ::= { cfprApEquipmentIOCardStatsEntry 15 }

cfprApEquipmentIOCardStatsProcTempMin OBJECT-TYPE
    SYNTAX       INTEGER
    MAX-ACCESS   read-only
    STATUS       current
    DESCRIPTION
        "Cisco Firepower equipment:IOCardStats:procTempMin
        managed object property"
    ::= { cfprApEquipmentIOCardStatsEntry 16 }

cfprApEquipmentIOCardStatsSuspect OBJECT-TYPE
    SYNTAX       TruthValue
    MAX-ACCESS   read-only
    STATUS       current
    DESCRIPTION
        "Cisco Firepower equipment:IOCardStats:suspect
        managed object property"
    ::= { cfprApEquipmentIOCardStatsEntry 17 }

cfprApEquipmentIOCardStatsTemp OBJECT-TYPE
    SYNTAX       INTEGER
    MAX-ACCESS   read-only
    STATUS       current
    DESCRIPTION
        "Cisco Firepower equipment:IOCardStats:temp managed
        object property"
    ::= { cfprApEquipmentIOCardStatsEntry 18 }

cfprApEquipmentIOCardStatsTempAvg OBJECT-TYPE
    SYNTAX       INTEGER
    MAX-ACCESS   read-only
    STATUS       current
    DESCRIPTION
        "Cisco Firepower equipment:IOCardStats:tempAvg
        managed object property"
    ::= { cfprApEquipmentIOCardStatsEntry 19 }

cfprApEquipmentIOCardStatsTempMax OBJECT-TYPE
    SYNTAX       INTEGER
    MAX-ACCESS   read-only
    STATUS       current
    DESCRIPTION
        "Cisco Firepower equipment:IOCardStats:tempMax
        managed object property"
    ::= { cfprApEquipmentIOCardStatsEntry 20 }

cfprApEquipmentIOCardStatsTempMin OBJECT-TYPE
    SYNTAX       INTEGER
    MAX-ACCESS   read-only
    STATUS       current
    DESCRIPTION
        "Cisco Firepower equipment:IOCardStats:tempMin
        managed object property"
    ::= { cfprApEquipmentIOCardStatsEntry 21 }

cfprApEquipmentIOCardStatsThresholded OBJECT-TYPE
    SYNTAX       CfprApEquipmentIOCardStatsThresholded
    MAX-ACCESS   read-only
    STATUS       current
    DESCRIPTION
        "Cisco Firepower equipment:IOCardStats:thresholded
        managed object property"
    ::= { cfprApEquipmentIOCardStatsEntry 22 }

cfprApEquipmentIOCardStatsTimeCollected OBJECT-TYPE
    SYNTAX       DateAndTime
    MAX-ACCESS   read-only
    STATUS       current
    DESCRIPTION
        "Cisco Firepower equipment:IOCardStats:timeCollected
        managed object property"
    ::= { cfprApEquipmentIOCardStatsEntry 23 }

cfprApEquipmentIOCardStatsUpdate OBJECT-TYPE
    SYNTAX       Gauge32
    MAX-ACCESS   read-only
    STATUS       current
    DESCRIPTION
        "Cisco Firepower equipment:IOCardStats:update managed
        object property"
    ::= { cfprApEquipmentIOCardStatsEntry 24 }

cfprApEquipmentIOCardStatsHistTable OBJECT-TYPE
    SYNTAX           SEQUENCE OF CfprApEquipmentIOCardStatsHistEntry
    MAX-ACCESS       not-accessible
    STATUS           current
    DESCRIPTION
        "Cisco Firepower equipment:IOCardStatsHist managed object table"
    ::= { cfprApEquipmentObjects 73 }

cfprApEquipmentIOCardStatsHistEntry OBJECT-TYPE
    SYNTAX           CfprApEquipmentIOCardStatsHistEntry
    MAX-ACCESS       not-accessible
    STATUS           current
    DESCRIPTION
        "Entry for the cfprApEquipmentIOCardStatsHistTable table."
    INDEX { cfprApEquipmentIOCardStatsHistInstanceId }
    ::= { cfprApEquipmentIOCardStatsHistTable 1 }

CfprApEquipmentIOCardStatsHistEntry ::= SEQUENCE {
    cfprApEquipmentIOCardStatsHistInstanceId                         CfprApManagedObjectId,
    cfprApEquipmentIOCardStatsHistDn                                 CfprApManagedObjectDn,
    cfprApEquipmentIOCardStatsHistRn                                 SnmpAdminString,
    cfprApEquipmentIOCardStatsHistAmbientTemp                        INTEGER,
    cfprApEquipmentIOCardStatsHistAmbientTempAvg                     INTEGER,
    cfprApEquipmentIOCardStatsHistAmbientTempMax                     INTEGER,
    cfprApEquipmentIOCardStatsHistAmbientTempMin                     INTEGER,
    cfprApEquipmentIOCardStatsHistDimmTemp                           INTEGER,
    cfprApEquipmentIOCardStatsHistDimmTempAvg                        INTEGER,
    cfprApEquipmentIOCardStatsHistDimmTempMax                        INTEGER,
    cfprApEquipmentIOCardStatsHistDimmTempMin                        INTEGER,
    cfprApEquipmentIOCardStatsHistId                                 Unsigned64,
    cfprApEquipmentIOCardStatsHistMostRecent                         TruthValue,
    cfprApEquipmentIOCardStatsHistProcTemp                           INTEGER,
    cfprApEquipmentIOCardStatsHistProcTempAvg                        INTEGER,
    cfprApEquipmentIOCardStatsHistProcTempMax                        INTEGER,
    cfprApEquipmentIOCardStatsHistProcTempMin                        INTEGER,
    cfprApEquipmentIOCardStatsHistSuspect                            TruthValue,
    cfprApEquipmentIOCardStatsHistTemp                               INTEGER,
    cfprApEquipmentIOCardStatsHistTempAvg                            INTEGER,
    cfprApEquipmentIOCardStatsHistTempMax                            INTEGER,
    cfprApEquipmentIOCardStatsHistTempMin                            INTEGER,
    cfprApEquipmentIOCardStatsHistThresholded                        CfprApEquipmentIOCardStatsHistThresholded,
    cfprApEquipmentIOCardStatsHistTimeCollected                      DateAndTime
}

cfprApEquipmentIOCardStatsHistInstanceId OBJECT-TYPE
    SYNTAX       CfprApManagedObjectId
    MAX-ACCESS   not-accessible
    STATUS       current
    DESCRIPTION
        "Instance identifier of the managed object."
    ::= { cfprApEquipmentIOCardStatsHistEntry 1 }

cfprApEquipmentIOCardStatsHistDn OBJECT-TYPE
    SYNTAX       CfprApManagedObjectDn
    MAX-ACCESS   read-only
    STATUS       current
    DESCRIPTION
        "Cisco Firepower equipment:IOCardStatsHist:dn managed
        object property"
    ::= { cfprApEquipmentIOCardStatsHistEntry 2 }

cfprApEquipmentIOCardStatsHistRn OBJECT-TYPE
    SYNTAX       SnmpAdminString
    MAX-ACCESS   read-only
    STATUS       current
    DESCRIPTION
        "Cisco Firepower equipment:IOCardStatsHist:rn managed
        object property"
    ::= { cfprApEquipmentIOCardStatsHistEntry 3 }

cfprApEquipmentIOCardStatsHistAmbientTemp OBJECT-TYPE
    SYNTAX       INTEGER
    MAX-ACCESS   read-only
    STATUS       current
    DESCRIPTION
        "Cisco Firepower equipment:IOCardStatsHist:ambientTemp
        managed object property"
    ::= { cfprApEquipmentIOCardStatsHistEntry 4 }

cfprApEquipmentIOCardStatsHistAmbientTempAvg OBJECT-TYPE
    SYNTAX       INTEGER
    MAX-ACCESS   read-only
    STATUS       current
    DESCRIPTION
        "Cisco Firepower equipment:IOCardStatsHist:ambientTempAvg
        managed object property"
    ::= { cfprApEquipmentIOCardStatsHistEntry 5 }

cfprApEquipmentIOCardStatsHistAmbientTempMax OBJECT-TYPE
    SYNTAX       INTEGER
    MAX-ACCESS   read-only
    STATUS       current
    DESCRIPTION
        "Cisco Firepower equipment:IOCardStatsHist:ambientTempMax
        managed object property"
    ::= { cfprApEquipmentIOCardStatsHistEntry 6 }

cfprApEquipmentIOCardStatsHistAmbientTempMin OBJECT-TYPE
    SYNTAX       INTEGER
    MAX-ACCESS   read-only
    STATUS       current
    DESCRIPTION
        "Cisco Firepower equipment:IOCardStatsHist:ambientTempMin
        managed object property"
    ::= { cfprApEquipmentIOCardStatsHistEntry 7 }

cfprApEquipmentIOCardStatsHistDimmTemp OBJECT-TYPE
    SYNTAX       INTEGER
    MAX-ACCESS   read-only
    STATUS       current
    DESCRIPTION
        "Cisco Firepower equipment:IOCardStatsHist:dimmTemp
        managed object property"
    ::= { cfprApEquipmentIOCardStatsHistEntry 8 }

cfprApEquipmentIOCardStatsHistDimmTempAvg OBJECT-TYPE
    SYNTAX       INTEGER
    MAX-ACCESS   read-only
    STATUS       current
    DESCRIPTION
        "Cisco Firepower equipment:IOCardStatsHist:dimmTempAvg
        managed object property"
    ::= { cfprApEquipmentIOCardStatsHistEntry 9 }

cfprApEquipmentIOCardStatsHistDimmTempMax OBJECT-TYPE
    SYNTAX       INTEGER
    MAX-ACCESS   read-only
    STATUS       current
    DESCRIPTION
        "Cisco Firepower equipment:IOCardStatsHist:dimmTempMax
        managed object property"
    ::= { cfprApEquipmentIOCardStatsHistEntry 10 }

cfprApEquipmentIOCardStatsHistDimmTempMin OBJECT-TYPE
    SYNTAX       INTEGER
    MAX-ACCESS   read-only
    STATUS       current
    DESCRIPTION
        "Cisco Firepower equipment:IOCardStatsHist:dimmTempMin
        managed object property"
    ::= { cfprApEquipmentIOCardStatsHistEntry 11 }

cfprApEquipmentIOCardStatsHistId OBJECT-TYPE
    SYNTAX       Unsigned64
    MAX-ACCESS   read-only
    STATUS       current
    DESCRIPTION
        "Cisco Firepower equipment:IOCardStatsHist:id managed
        object property"
    ::= { cfprApEquipmentIOCardStatsHistEntry 12 }

cfprApEquipmentIOCardStatsHistMostRecent OBJECT-TYPE
    SYNTAX       TruthValue
    MAX-ACCESS   read-only
    STATUS       current
    DESCRIPTION
        "Cisco Firepower equipment:IOCardStatsHist:mostRecent
        managed object property"
    ::= { cfprApEquipmentIOCardStatsHistEntry 13 }

cfprApEquipmentIOCardStatsHistProcTemp OBJECT-TYPE
    SYNTAX       INTEGER
    MAX-ACCESS   read-only
    STATUS       current
    DESCRIPTION
        "Cisco Firepower equipment:IOCardStatsHist:procTemp
        managed object property"
    ::= { cfprApEquipmentIOCardStatsHistEntry 14 }

cfprApEquipmentIOCardStatsHistProcTempAvg OBJECT-TYPE
    SYNTAX       INTEGER
    MAX-ACCESS   read-only
    STATUS       current
    DESCRIPTION
        "Cisco Firepower equipment:IOCardStatsHist:procTempAvg
        managed object property"
    ::= { cfprApEquipmentIOCardStatsHistEntry 15 }

cfprApEquipmentIOCardStatsHistProcTempMax OBJECT-TYPE
    SYNTAX       INTEGER
    MAX-ACCESS   read-only
    STATUS       current
    DESCRIPTION
        "Cisco Firepower equipment:IOCardStatsHist:procTempMax
        managed object property"
    ::= { cfprApEquipmentIOCardStatsHistEntry 16 }

cfprApEquipmentIOCardStatsHistProcTempMin OBJECT-TYPE
    SYNTAX       INTEGER
    MAX-ACCESS   read-only
    STATUS       current
    DESCRIPTION
        "Cisco Firepower equipment:IOCardStatsHist:procTempMin
        managed object property"
    ::= { cfprApEquipmentIOCardStatsHistEntry 17 }

cfprApEquipmentIOCardStatsHistSuspect OBJECT-TYPE
    SYNTAX       TruthValue
    MAX-ACCESS   read-only
    STATUS       current
    DESCRIPTION
        "Cisco Firepower equipment:IOCardStatsHist:suspect
        managed object property"
    ::= { cfprApEquipmentIOCardStatsHistEntry 18 }

cfprApEquipmentIOCardStatsHistTemp OBJECT-TYPE
    SYNTAX       INTEGER
    MAX-ACCESS   read-only
    STATUS       current
    DESCRIPTION
        "Cisco Firepower equipment:IOCardStatsHist:temp
        managed object property"
    ::= { cfprApEquipmentIOCardStatsHistEntry 19 }

cfprApEquipmentIOCardStatsHistTempAvg OBJECT-TYPE
    SYNTAX       INTEGER
    MAX-ACCESS   read-only
    STATUS       current
    DESCRIPTION
        "Cisco Firepower equipment:IOCardStatsHist:tempAvg
        managed object property"
    ::= { cfprApEquipmentIOCardStatsHistEntry 20 }

cfprApEquipmentIOCardStatsHistTempMax OBJECT-TYPE
    SYNTAX       INTEGER
    MAX-ACCESS   read-only
    STATUS       current
    DESCRIPTION
        "Cisco Firepower equipment:IOCardStatsHist:tempMax
        managed object property"
    ::= { cfprApEquipmentIOCardStatsHistEntry 21 }

cfprApEquipmentIOCardStatsHistTempMin OBJECT-TYPE
    SYNTAX       INTEGER
    MAX-ACCESS   read-only
    STATUS       current
    DESCRIPTION
        "Cisco Firepower equipment:IOCardStatsHist:tempMin
        managed object property"
    ::= { cfprApEquipmentIOCardStatsHistEntry 22 }

cfprApEquipmentIOCardStatsHistThresholded OBJECT-TYPE
    SYNTAX       CfprApEquipmentIOCardStatsHistThresholded
    MAX-ACCESS   read-only
    STATUS       current
    DESCRIPTION
        "Cisco Firepower equipment:IOCardStatsHist:thresholded
        managed object property"
    ::= { cfprApEquipmentIOCardStatsHistEntry 23 }

cfprApEquipmentIOCardStatsHistTimeCollected OBJECT-TYPE
    SYNTAX       DateAndTime
    MAX-ACCESS   read-only
    STATUS       current
    DESCRIPTION
        "Cisco Firepower equipment:IOCardStatsHist:timeCollected
        managed object property"
    ::= { cfprApEquipmentIOCardStatsHistEntry 24 }

cfprApEquipmentIOCardTypeDefTable OBJECT-TYPE
    SYNTAX           SEQUENCE OF CfprApEquipmentIOCardTypeDefEntry
    MAX-ACCESS       not-accessible
    STATUS           current
    DESCRIPTION
        "Cisco Firepower equipment:IOCardTypeDef managed object table"
    ::= { cfprApEquipmentObjects 74 }

cfprApEquipmentIOCardTypeDefEntry OBJECT-TYPE
    SYNTAX           CfprApEquipmentIOCardTypeDefEntry
    MAX-ACCESS       not-accessible
    STATUS           current
    DESCRIPTION
        "Entry for the cfprApEquipmentIOCardTypeDefTable table."
    INDEX { cfprApEquipmentIOCardTypeDefInstanceId }
    ::= { cfprApEquipmentIOCardTypeDefTable 1 }

CfprApEquipmentIOCardTypeDefEntry ::= SEQUENCE {
    cfprApEquipmentIOCardTypeDefInstanceId                           CfprApManagedObjectId,
    cfprApEquipmentIOCardTypeDefDn                                   CfprApManagedObjectDn,
    cfprApEquipmentIOCardTypeDefRn                                   SnmpAdminString,
    cfprApEquipmentIOCardTypeDefDescr                                SnmpAdminString,
    cfprApEquipmentIOCardTypeDefIntId                                SnmpAdminString,
    cfprApEquipmentIOCardTypeDefName                                 SnmpAdminString,
    cfprApEquipmentIOCardTypeDefPolicyLevel                          Gauge32,
    cfprApEquipmentIOCardTypeDefPolicyOwner                          CfprApPolicyPolicyOwner,
    cfprApEquipmentIOCardTypeDefType                                 SnmpAdminString
}

cfprApEquipmentIOCardTypeDefInstanceId OBJECT-TYPE
    SYNTAX       CfprApManagedObjectId
    MAX-ACCESS   not-accessible
    STATUS       current
    DESCRIPTION
        "Instance identifier of the managed object."
    ::= { cfprApEquipmentIOCardTypeDefEntry 1 }

cfprApEquipmentIOCardTypeDefDn OBJECT-TYPE
    SYNTAX       CfprApManagedObjectDn
    MAX-ACCESS   read-only
    STATUS       current
    DESCRIPTION
        "Cisco Firepower equipment:IOCardTypeDef:dn managed
        object property"
    ::= { cfprApEquipmentIOCardTypeDefEntry 2 }

cfprApEquipmentIOCardTypeDefRn OBJECT-TYPE
    SYNTAX       SnmpAdminString
    MAX-ACCESS   read-only
    STATUS       current
    DESCRIPTION
        "Cisco Firepower equipment:IOCardTypeDef:rn managed
        object property"
    ::= { cfprApEquipmentIOCardTypeDefEntry 3 }

cfprApEquipmentIOCardTypeDefDescr OBJECT-TYPE
    SYNTAX       SnmpAdminString
    MAX-ACCESS   read-only
    STATUS       current
    DESCRIPTION
        "Cisco Firepower equipment:IOCardTypeDef:descr
        managed object property"
    ::= { cfprApEquipmentIOCardTypeDefEntry 4 }

cfprApEquipmentIOCardTypeDefIntId OBJECT-TYPE
    SYNTAX       SnmpAdminString
    MAX-ACCESS   read-only
    STATUS       current
    DESCRIPTION
        "Cisco Firepower equipment:IOCardTypeDef:intId
        managed object property"
    ::= { cfprApEquipmentIOCardTypeDefEntry 5 }

cfprApEquipmentIOCardTypeDefName OBJECT-TYPE
    SYNTAX       SnmpAdminString
    MAX-ACCESS   read-only
    STATUS       current
    DESCRIPTION
        "Cisco Firepower equipment:IOCardTypeDef:name managed
        object property"
    ::= { cfprApEquipmentIOCardTypeDefEntry 6 }

cfprApEquipmentIOCardTypeDefPolicyLevel OBJECT-TYPE
    SYNTAX       Gauge32
    MAX-ACCESS   read-only
    STATUS       current
    DESCRIPTION
        "Cisco Firepower equipment:IOCardTypeDef:policyLevel
        managed object property"
    ::= { cfprApEquipmentIOCardTypeDefEntry 7 }

cfprApEquipmentIOCardTypeDefPolicyOwner OBJECT-TYPE
    SYNTAX       CfprApPolicyPolicyOwner
    MAX-ACCESS   read-only
    STATUS       current
    DESCRIPTION
        "Cisco Firepower equipment:IOCardTypeDef:policyOwner
        managed object property"
    ::= { cfprApEquipmentIOCardTypeDefEntry 8 }

cfprApEquipmentIOCardTypeDefType OBJECT-TYPE
    SYNTAX       SnmpAdminString
    MAX-ACCESS   read-only
    STATUS       current
    DESCRIPTION
        "Cisco Firepower equipment:IOCardTypeDef:type managed
        object property"
    ::= { cfprApEquipmentIOCardTypeDefEntry 9 }

cfprApEquipmentInbandMgmtCapTable OBJECT-TYPE
    SYNTAX           SEQUENCE OF CfprApEquipmentInbandMgmtCapEntry
    MAX-ACCESS       not-accessible
    STATUS           current
    DESCRIPTION
        "Cisco Firepower equipment:InbandMgmtCap managed object table"
    ::= { cfprApEquipmentObjects 75 }

cfprApEquipmentInbandMgmtCapEntry OBJECT-TYPE
    SYNTAX           CfprApEquipmentInbandMgmtCapEntry
    MAX-ACCESS       not-accessible
    STATUS           current
    DESCRIPTION
        "Entry for the cfprApEquipmentInbandMgmtCapTable table."
    INDEX { cfprApEquipmentInbandMgmtCapInstanceId }
    ::= { cfprApEquipmentInbandMgmtCapTable 1 }

CfprApEquipmentInbandMgmtCapEntry ::= SEQUENCE {
    cfprApEquipmentInbandMgmtCapInstanceId                           CfprApManagedObjectId,
    cfprApEquipmentInbandMgmtCapDn                                   CfprApManagedObjectDn,
    cfprApEquipmentInbandMgmtCapRn                                   SnmpAdminString,
    cfprApEquipmentInbandMgmtCapIsSupported                          CfprApEquipmentIsSupported,
    cfprApEquipmentInbandMgmtCapMinCimcVersion                       SnmpAdminString,
    cfprApEquipmentInbandMgmtCapMinCmcVersion                        SnmpAdminString
}

cfprApEquipmentInbandMgmtCapInstanceId OBJECT-TYPE
    SYNTAX       CfprApManagedObjectId
    MAX-ACCESS   not-accessible
    STATUS       current
    DESCRIPTION
        "Instance identifier of the managed object."
    ::= { cfprApEquipmentInbandMgmtCapEntry 1 }

cfprApEquipmentInbandMgmtCapDn OBJECT-TYPE
    SYNTAX       CfprApManagedObjectDn
    MAX-ACCESS   read-only
    STATUS       current
    DESCRIPTION
        "Cisco Firepower equipment:InbandMgmtCap:dn managed
        object property"
    ::= { cfprApEquipmentInbandMgmtCapEntry 2 }

cfprApEquipmentInbandMgmtCapRn OBJECT-TYPE
    SYNTAX       SnmpAdminString
    MAX-ACCESS   read-only
    STATUS       current
    DESCRIPTION
        "Cisco Firepower equipment:InbandMgmtCap:rn managed
        object property"
    ::= { cfprApEquipmentInbandMgmtCapEntry 3 }

cfprApEquipmentInbandMgmtCapIsSupported OBJECT-TYPE
    SYNTAX       CfprApEquipmentIsSupported
    MAX-ACCESS   read-only
    STATUS       current
    DESCRIPTION
        "Cisco Firepower equipment:InbandMgmtCap:isSupported
        managed object property"
    ::= { cfprApEquipmentInbandMgmtCapEntry 4 }

cfprApEquipmentInbandMgmtCapMinCimcVersion OBJECT-TYPE
    SYNTAX       SnmpAdminString
    MAX-ACCESS   read-only
    STATUS       current
    DESCRIPTION
        "Cisco Firepower equipment:InbandMgmtCap:minCimcVersion
        managed object property"
    ::= { cfprApEquipmentInbandMgmtCapEntry 5 }

cfprApEquipmentInbandMgmtCapMinCmcVersion OBJECT-TYPE
    SYNTAX       SnmpAdminString
    MAX-ACCESS   read-only
    STATUS       current
    DESCRIPTION
        "Cisco Firepower equipment:InbandMgmtCap:minCmcVersion
        managed object property"
    ::= { cfprApEquipmentInbandMgmtCapEntry 6 }

cfprApEquipmentIndicatorLedTable OBJECT-TYPE
    SYNTAX           SEQUENCE OF CfprApEquipmentIndicatorLedEntry
    MAX-ACCESS       not-accessible
    STATUS           current
    DESCRIPTION
        "Cisco Firepower equipment:IndicatorLed managed object table"
    ::= { cfprApEquipmentObjects 76 }

cfprApEquipmentIndicatorLedEntry OBJECT-TYPE
    SYNTAX           CfprApEquipmentIndicatorLedEntry
    MAX-ACCESS       not-accessible
    STATUS           current
    DESCRIPTION
        "Entry for the cfprApEquipmentIndicatorLedTable table."
    INDEX { cfprApEquipmentIndicatorLedInstanceId }
    ::= { cfprApEquipmentIndicatorLedTable 1 }

CfprApEquipmentIndicatorLedEntry ::= SEQUENCE {
    cfprApEquipmentIndicatorLedInstanceId                            CfprApManagedObjectId,
    cfprApEquipmentIndicatorLedDn                                    CfprApManagedObjectDn,
    cfprApEquipmentIndicatorLedRn                                    SnmpAdminString,
    cfprApEquipmentIndicatorLedColor                                 CfprApEquipmentLedColor,
    cfprApEquipmentIndicatorLedId                                    Gauge32,
    cfprApEquipmentIndicatorLedName                                  SnmpAdminString,
    cfprApEquipmentIndicatorLedOperState                             CfprApEquipmentLedOperState
}

cfprApEquipmentIndicatorLedInstanceId OBJECT-TYPE
    SYNTAX       CfprApManagedObjectId
    MAX-ACCESS   not-accessible
    STATUS       current
    DESCRIPTION
        "Instance identifier of the managed object."
    ::= { cfprApEquipmentIndicatorLedEntry 1 }

cfprApEquipmentIndicatorLedDn OBJECT-TYPE
    SYNTAX       CfprApManagedObjectDn
    MAX-ACCESS   read-only
    STATUS       current
    DESCRIPTION
        "Cisco Firepower equipment:IndicatorLed:dn managed
        object property"
    ::= { cfprApEquipmentIndicatorLedEntry 2 }

cfprApEquipmentIndicatorLedRn OBJECT-TYPE
    SYNTAX       SnmpAdminString
    MAX-ACCESS   read-only
    STATUS       current
    DESCRIPTION
        "Cisco Firepower equipment:IndicatorLed:rn managed
        object property"
    ::= { cfprApEquipmentIndicatorLedEntry 3 }

cfprApEquipmentIndicatorLedColor OBJECT-TYPE
    SYNTAX       CfprApEquipmentLedColor
    MAX-ACCESS   read-only
    STATUS       current
    DESCRIPTION
        "Cisco Firepower equipment:IndicatorLed:color managed
        object property"
    ::= { cfprApEquipmentIndicatorLedEntry 4 }

cfprApEquipmentIndicatorLedId OBJECT-TYPE
    SYNTAX       Gauge32
    MAX-ACCESS   read-only
    STATUS       current
    DESCRIPTION
        "Cisco Firepower equipment:IndicatorLed:id managed
        object property"
    ::= { cfprApEquipmentIndicatorLedEntry 5 }

cfprApEquipmentIndicatorLedName OBJECT-TYPE
    SYNTAX       SnmpAdminString
    MAX-ACCESS   read-only
    STATUS       current
    DESCRIPTION
        "Cisco Firepower equipment:IndicatorLed:name managed
        object property"
    ::= { cfprApEquipmentIndicatorLedEntry 6 }

cfprApEquipmentIndicatorLedOperState OBJECT-TYPE
    SYNTAX       CfprApEquipmentLedOperState
    MAX-ACCESS   read-only
    STATUS       current
    DESCRIPTION
        "Cisco Firepower equipment:IndicatorLed:operState
        managed object property"
    ::= { cfprApEquipmentIndicatorLedEntry 7 }

cfprApEquipmentKvmMgmtCapTable OBJECT-TYPE
    SYNTAX           SEQUENCE OF CfprApEquipmentKvmMgmtCapEntry
    MAX-ACCESS       not-accessible
    STATUS           current
    DESCRIPTION
        "Cisco Firepower equipment:KvmMgmtCap managed object table"
    ::= { cfprApEquipmentObjects 77 }

cfprApEquipmentKvmMgmtCapEntry OBJECT-TYPE
    SYNTAX           CfprApEquipmentKvmMgmtCapEntry
    MAX-ACCESS       not-accessible
    STATUS           current
    DESCRIPTION
        "Entry for the cfprApEquipmentKvmMgmtCapTable table."
    INDEX { cfprApEquipmentKvmMgmtCapInstanceId }
    ::= { cfprApEquipmentKvmMgmtCapTable 1 }

CfprApEquipmentKvmMgmtCapEntry ::= SEQUENCE {
    cfprApEquipmentKvmMgmtCapInstanceId                              CfprApManagedObjectId,
    cfprApEquipmentKvmMgmtCapDn                                      CfprApManagedObjectDn,
    cfprApEquipmentKvmMgmtCapRn                                      SnmpAdminString,
    cfprApEquipmentKvmMgmtCapIsSupported                             CfprApEquipmentIsSupported,
    cfprApEquipmentKvmMgmtCapMinCimcVersion                          SnmpAdminString
}

cfprApEquipmentKvmMgmtCapInstanceId OBJECT-TYPE
    SYNTAX       CfprApManagedObjectId
    MAX-ACCESS   not-accessible
    STATUS       current
    DESCRIPTION
        "Instance identifier of the managed object."
    ::= { cfprApEquipmentKvmMgmtCapEntry 1 }

cfprApEquipmentKvmMgmtCapDn OBJECT-TYPE
    SYNTAX       CfprApManagedObjectDn
    MAX-ACCESS   read-only
    STATUS       current
    DESCRIPTION
        "Cisco Firepower equipment:KvmMgmtCap:dn managed object property"
    ::= { cfprApEquipmentKvmMgmtCapEntry 2 }

cfprApEquipmentKvmMgmtCapRn OBJECT-TYPE
    SYNTAX       SnmpAdminString
    MAX-ACCESS   read-only
    STATUS       current
    DESCRIPTION
        "Cisco Firepower equipment:KvmMgmtCap:rn managed object property"
    ::= { cfprApEquipmentKvmMgmtCapEntry 3 }

cfprApEquipmentKvmMgmtCapIsSupported OBJECT-TYPE
    SYNTAX       CfprApEquipmentIsSupported
    MAX-ACCESS   read-only
    STATUS       current
    DESCRIPTION
        "Cisco Firepower equipment:KvmMgmtCap:isSupported
        managed object property"
    ::= { cfprApEquipmentKvmMgmtCapEntry 4 }

cfprApEquipmentKvmMgmtCapMinCimcVersion OBJECT-TYPE
    SYNTAX       SnmpAdminString
    MAX-ACCESS   read-only
    STATUS       current
    DESCRIPTION
        "Cisco Firepower equipment:KvmMgmtCap:minCimcVersion
        managed object property"
    ::= { cfprApEquipmentKvmMgmtCapEntry 5 }

cfprApEquipmentLocalDiskCapProviderTable OBJECT-TYPE
    SYNTAX           SEQUENCE OF CfprApEquipmentLocalDiskCapProviderEntry
    MAX-ACCESS       not-accessible
    STATUS           current
    DESCRIPTION
        "Cisco Firepower equipment:LocalDiskCapProvider
        managed object table"
    ::= { cfprApEquipmentObjects 78 }

cfprApEquipmentLocalDiskCapProviderEntry OBJECT-TYPE
    SYNTAX           CfprApEquipmentLocalDiskCapProviderEntry
    MAX-ACCESS       not-accessible
    STATUS           current
    DESCRIPTION
        "Entry for the cfprApEquipmentLocalDiskCapProviderTable table."
    INDEX { cfprApEquipmentLocalDiskCapProviderInstanceId }
    ::= { cfprApEquipmentLocalDiskCapProviderTable 1 }

CfprApEquipmentLocalDiskCapProviderEntry ::= SEQUENCE {
    cfprApEquipmentLocalDiskCapProviderInstanceId                    CfprApManagedObjectId,
    cfprApEquipmentLocalDiskCapProviderDn                            CfprApManagedObjectDn,
    cfprApEquipmentLocalDiskCapProviderRn                            SnmpAdminString,
    cfprApEquipmentLocalDiskCapProviderDeleted                       TruthValue,
    cfprApEquipmentLocalDiskCapProviderDeprecated                    TruthValue,
    cfprApEquipmentLocalDiskCapProviderElementLoadFailures           Gauge32,
    cfprApEquipmentLocalDiskCapProviderElementsLoaded                Gauge32,
    cfprApEquipmentLocalDiskCapProviderGencount                      Gauge32,
    cfprApEquipmentLocalDiskCapProviderLoadErrors                    Gauge32,
    cfprApEquipmentLocalDiskCapProviderLoadWarnings                  Gauge32,
    cfprApEquipmentLocalDiskCapProviderMgmtPlaneVer                  SnmpAdminString,
    cfprApEquipmentLocalDiskCapProviderModel                         SnmpAdminString,
    cfprApEquipmentLocalDiskCapProviderPromCardType                  Gauge32,
    cfprApEquipmentLocalDiskCapProviderRevision                      SnmpAdminString,
    cfprApEquipmentLocalDiskCapProviderVendor                        SnmpAdminString
}

cfprApEquipmentLocalDiskCapProviderInstanceId OBJECT-TYPE
    SYNTAX       CfprApManagedObjectId
    MAX-ACCESS   not-accessible
    STATUS       current
    DESCRIPTION
        "Instance identifier of the managed object."
    ::= { cfprApEquipmentLocalDiskCapProviderEntry 1 }

cfprApEquipmentLocalDiskCapProviderDn OBJECT-TYPE
    SYNTAX       CfprApManagedObjectDn
    MAX-ACCESS   read-only
    STATUS       current
    DESCRIPTION
        "Cisco Firepower equipment:LocalDiskCapProvider:dn
        managed object property"
    ::= { cfprApEquipmentLocalDiskCapProviderEntry 2 }

cfprApEquipmentLocalDiskCapProviderRn OBJECT-TYPE
    SYNTAX       SnmpAdminString
    MAX-ACCESS   read-only
    STATUS       current
    DESCRIPTION
        "Cisco Firepower equipment:LocalDiskCapProvider:rn
        managed object property"
    ::= { cfprApEquipmentLocalDiskCapProviderEntry 3 }

cfprApEquipmentLocalDiskCapProviderDeleted OBJECT-TYPE
    SYNTAX       TruthValue
    MAX-ACCESS   read-only
    STATUS       current
    DESCRIPTION
        "Cisco Firepower equipment:LocalDiskCapProvider:deleted
        managed object property"
    ::= { cfprApEquipmentLocalDiskCapProviderEntry 4 }

cfprApEquipmentLocalDiskCapProviderDeprecated OBJECT-TYPE
    SYNTAX       TruthValue
    MAX-ACCESS   read-only
    STATUS       current
    DESCRIPTION
        "Cisco Firepower equipment:LocalDiskCapProvider:deprecated
        managed object property"
    ::= { cfprApEquipmentLocalDiskCapProviderEntry 5 }

cfprApEquipmentLocalDiskCapProviderElementLoadFailures OBJECT-TYPE
    SYNTAX       Gauge32
    MAX-ACCESS   read-only
    STATUS       current
    DESCRIPTION
        "Cisco Firepower equipment:LocalDiskCapProvider:elementLoadFailure
        s managed object property"
    ::= { cfprApEquipmentLocalDiskCapProviderEntry 6 }

cfprApEquipmentLocalDiskCapProviderElementsLoaded OBJECT-TYPE
    SYNTAX       Gauge32
    MAX-ACCESS   read-only
    STATUS       current
    DESCRIPTION
        "Cisco Firepower equipment:LocalDiskCapProvider:elementsLoaded
        managed object property"
    ::= { cfprApEquipmentLocalDiskCapProviderEntry 7 }

cfprApEquipmentLocalDiskCapProviderGencount OBJECT-TYPE
    SYNTAX       Gauge32
    MAX-ACCESS   read-only
    STATUS       current
    DESCRIPTION
        "Cisco Firepower equipment:LocalDiskCapProvider:gencount
        managed object property"
    ::= { cfprApEquipmentLocalDiskCapProviderEntry 8 }

cfprApEquipmentLocalDiskCapProviderLoadErrors OBJECT-TYPE
    SYNTAX       Gauge32
    MAX-ACCESS   read-only
    STATUS       current
    DESCRIPTION
        "Cisco Firepower equipment:LocalDiskCapProvider:loadErrors
        managed object property"
    ::= { cfprApEquipmentLocalDiskCapProviderEntry 9 }

cfprApEquipmentLocalDiskCapProviderLoadWarnings OBJECT-TYPE
    SYNTAX       Gauge32
    MAX-ACCESS   read-only
    STATUS       current
    DESCRIPTION
        "Cisco Firepower equipment:LocalDiskCapProvider:loadWarnings
        managed object property"
    ::= { cfprApEquipmentLocalDiskCapProviderEntry 10 }

cfprApEquipmentLocalDiskCapProviderMgmtPlaneVer OBJECT-TYPE
    SYNTAX       SnmpAdminString
    MAX-ACCESS   read-only
    STATUS       current
    DESCRIPTION
        "Cisco Firepower equipment:LocalDiskCapProvider:mgmtPlaneVer
        managed object property"
    ::= { cfprApEquipmentLocalDiskCapProviderEntry 11 }

cfprApEquipmentLocalDiskCapProviderModel OBJECT-TYPE
    SYNTAX       SnmpAdminString
    MAX-ACCESS   read-only
    STATUS       current
    DESCRIPTION
        "Cisco Firepower equipment:LocalDiskCapProvider:model
        managed object property"
    ::= { cfprApEquipmentLocalDiskCapProviderEntry 12 }

cfprApEquipmentLocalDiskCapProviderPromCardType OBJECT-TYPE
    SYNTAX       Gauge32
    MAX-ACCESS   read-only
    STATUS       current
    DESCRIPTION
        "Cisco Firepower equipment:LocalDiskCapProvider:promCardType
        managed object property"
    ::= { cfprApEquipmentLocalDiskCapProviderEntry 13 }

cfprApEquipmentLocalDiskCapProviderRevision OBJECT-TYPE
    SYNTAX       SnmpAdminString
    MAX-ACCESS   read-only
    STATUS       current
    DESCRIPTION
        "Cisco Firepower equipment:LocalDiskCapProvider:revision
        managed object property"
    ::= { cfprApEquipmentLocalDiskCapProviderEntry 14 }

cfprApEquipmentLocalDiskCapProviderVendor OBJECT-TYPE
    SYNTAX       SnmpAdminString
    MAX-ACCESS   read-only
    STATUS       current
    DESCRIPTION
        "Cisco Firepower equipment:LocalDiskCapProvider:vendor
        managed object property"
    ::= { cfprApEquipmentLocalDiskCapProviderEntry 15 }

cfprApEquipmentLocalDiskControllerCapProviderTable OBJECT-TYPE
    SYNTAX           SEQUENCE OF CfprApEquipmentLocalDiskControllerCapProviderEntry
    MAX-ACCESS       not-accessible
    STATUS           current
    DESCRIPTION
        "Cisco Firepower equipment:LocalDiskControllerCapProvider
        managed object table"
    ::= { cfprApEquipmentObjects 79 }

cfprApEquipmentLocalDiskControllerCapProviderEntry OBJECT-TYPE
    SYNTAX           CfprApEquipmentLocalDiskControllerCapProviderEntry
    MAX-ACCESS       not-accessible
    STATUS           current
    DESCRIPTION
        "Entry for the cfprApEquipmentLocalDiskControllerCapProviderTable table."
    INDEX { cfprApEquipmentLocalDiskControllerCapProviderInstanceId }
    ::= { cfprApEquipmentLocalDiskControllerCapProviderTable 1 }

CfprApEquipmentLocalDiskControllerCapProviderEntry ::= SEQUENCE {
    cfprApEquipmentLocalDiskControllerCapProviderInstanceId          CfprApManagedObjectId,
    cfprApEquipmentLocalDiskControllerCapProviderDn                  CfprApManagedObjectDn,
    cfprApEquipmentLocalDiskControllerCapProviderRn                  SnmpAdminString,
    cfprApEquipmentLocalDiskControllerCapProviderCardType            CfprApEquipmentCType,
    cfprApEquipmentLocalDiskControllerCapProviderDeleted             TruthValue,
    cfprApEquipmentLocalDiskControllerCapProviderDeprecated          TruthValue,
    cfprApEquipmentLocalDiskControllerCapProviderElementLoadFailures Gauge32,
    cfprApEquipmentLocalDiskControllerCapProviderElementsLoaded      Gauge32,
    cfprApEquipmentLocalDiskControllerCapProviderForm                CfprApStorageControllerForm,
    cfprApEquipmentLocalDiskControllerCapProviderGencount            Gauge32,
    cfprApEquipmentLocalDiskControllerCapProviderInternalports       Gauge32,
    cfprApEquipmentLocalDiskControllerCapProviderLoadErrors          Gauge32,
    cfprApEquipmentLocalDiskControllerCapProviderLoadWarnings        Gauge32,
    cfprApEquipmentLocalDiskControllerCapProviderMgmtPlaneVer        SnmpAdminString,
    cfprApEquipmentLocalDiskControllerCapProviderModel               SnmpAdminString,
    cfprApEquipmentLocalDiskControllerCapProviderPromCardType        Gauge32,
    cfprApEquipmentLocalDiskControllerCapProviderRevision            SnmpAdminString,
    cfprApEquipmentLocalDiskControllerCapProviderVendor              SnmpAdminString
}

cfprApEquipmentLocalDiskControllerCapProviderInstanceId OBJECT-TYPE
    SYNTAX       CfprApManagedObjectId
    MAX-ACCESS   not-accessible
    STATUS       current
    DESCRIPTION
        "Instance identifier of the managed object."
    ::= { cfprApEquipmentLocalDiskControllerCapProviderEntry 1 }

cfprApEquipmentLocalDiskControllerCapProviderDn OBJECT-TYPE
    SYNTAX       CfprApManagedObjectDn
    MAX-ACCESS   read-only
    STATUS       current
    DESCRIPTION
        "Cisco Firepower equipment:LocalDiskControllerCapProvider:dn
        managed object property"
    ::= { cfprApEquipmentLocalDiskControllerCapProviderEntry 2 }

cfprApEquipmentLocalDiskControllerCapProviderRn OBJECT-TYPE
    SYNTAX       SnmpAdminString
    MAX-ACCESS   read-only
    STATUS       current
    DESCRIPTION
        "Cisco Firepower equipment:LocalDiskControllerCapProvider:rn
        managed object property"
    ::= { cfprApEquipmentLocalDiskControllerCapProviderEntry 3 }

cfprApEquipmentLocalDiskControllerCapProviderCardType OBJECT-TYPE
    SYNTAX       CfprApEquipmentCType
    MAX-ACCESS   read-only
    STATUS       current
    DESCRIPTION
        "Cisco Firepower equipment:LocalDiskControllerCapProvider:cardType
         managed object property"
    ::= { cfprApEquipmentLocalDiskControllerCapProviderEntry 4 }

cfprApEquipmentLocalDiskControllerCapProviderDeleted OBJECT-TYPE
    SYNTAX       TruthValue
    MAX-ACCESS   read-only
    STATUS       current
    DESCRIPTION
        "Cisco Firepower equipment:LocalDiskControllerCapProvider:deleted
        managed object property"
    ::= { cfprApEquipmentLocalDiskControllerCapProviderEntry 5 }

cfprApEquipmentLocalDiskControllerCapProviderDeprecated OBJECT-TYPE
    SYNTAX       TruthValue
    MAX-ACCESS   read-only
    STATUS       current
    DESCRIPTION
        "Cisco Firepower equipment:LocalDiskControllerCapProvider:deprecat
        ed managed object property"
    ::= { cfprApEquipmentLocalDiskControllerCapProviderEntry 6 }

cfprApEquipmentLocalDiskControllerCapProviderElementLoadFailures OBJECT-TYPE
    SYNTAX       Gauge32
    MAX-ACCESS   read-only
    STATUS       current
    DESCRIPTION
        "Cisco Firepower equipment:LocalDiskControllerCapProvider:elementL
        oadFailures managed object property"
    ::= { cfprApEquipmentLocalDiskControllerCapProviderEntry 7 }

cfprApEquipmentLocalDiskControllerCapProviderElementsLoaded OBJECT-TYPE
    SYNTAX       Gauge32
    MAX-ACCESS   read-only
    STATUS       current
    DESCRIPTION
        "Cisco Firepower equipment:LocalDiskControllerCapProvider:elements
        Loaded managed object property"
    ::= { cfprApEquipmentLocalDiskControllerCapProviderEntry 8 }

cfprApEquipmentLocalDiskControllerCapProviderForm OBJECT-TYPE
    SYNTAX       CfprApStorageControllerForm
    MAX-ACCESS   read-only
    STATUS       current
    DESCRIPTION
        "Cisco Firepower equipment:LocalDiskControllerCapProvider:form
        managed object property"
    ::= { cfprApEquipmentLocalDiskControllerCapProviderEntry 9 }

cfprApEquipmentLocalDiskControllerCapProviderGencount OBJECT-TYPE
    SYNTAX       Gauge32
    MAX-ACCESS   read-only
    STATUS       current
    DESCRIPTION
        "Cisco Firepower equipment:LocalDiskControllerCapProvider:gencount
         managed object property"
    ::= { cfprApEquipmentLocalDiskControllerCapProviderEntry 10 }

cfprApEquipmentLocalDiskControllerCapProviderInternalports OBJECT-TYPE
    SYNTAX       Gauge32
    MAX-ACCESS   read-only
    STATUS       current
    DESCRIPTION
        "Cisco Firepower equipment:LocalDiskControllerCapProvider:internal
        ports managed object property"
    ::= { cfprApEquipmentLocalDiskControllerCapProviderEntry 11 }

cfprApEquipmentLocalDiskControllerCapProviderLoadErrors OBJECT-TYPE
    SYNTAX       Gauge32
    MAX-ACCESS   read-only
    STATUS       current
    DESCRIPTION
        "Cisco Firepower equipment:LocalDiskControllerCapProvider:loadErro
        rs managed object property"
    ::= { cfprApEquipmentLocalDiskControllerCapProviderEntry 12 }

cfprApEquipmentLocalDiskControllerCapProviderLoadWarnings OBJECT-TYPE
    SYNTAX       Gauge32
    MAX-ACCESS   read-only
    STATUS       current
    DESCRIPTION
        "Cisco Firepower equipment:LocalDiskControllerCapProvider:loadWarn
        ings managed object property"
    ::= { cfprApEquipmentLocalDiskControllerCapProviderEntry 13 }

cfprApEquipmentLocalDiskControllerCapProviderMgmtPlaneVer OBJECT-TYPE
    SYNTAX       SnmpAdminString
    MAX-ACCESS   read-only
    STATUS       current
    DESCRIPTION
        "Cisco Firepower equipment:LocalDiskControllerCapProvider:mgmtPlan
        eVer managed object property"
    ::= { cfprApEquipmentLocalDiskControllerCapProviderEntry 14 }

cfprApEquipmentLocalDiskControllerCapProviderModel OBJECT-TYPE
    SYNTAX       SnmpAdminString
    MAX-ACCESS   read-only
    STATUS       current
    DESCRIPTION
        "Cisco Firepower equipment:LocalDiskControllerCapProvider:model
        managed object property"
    ::= { cfprApEquipmentLocalDiskControllerCapProviderEntry 15 }

cfprApEquipmentLocalDiskControllerCapProviderPromCardType OBJECT-TYPE
    SYNTAX       Gauge32
    MAX-ACCESS   read-only
    STATUS       current
    DESCRIPTION
        "Cisco Firepower equipment:LocalDiskControllerCapProvider:promCard
        Type managed object property"
    ::= { cfprApEquipmentLocalDiskControllerCapProviderEntry 16 }

cfprApEquipmentLocalDiskControllerCapProviderRevision OBJECT-TYPE
    SYNTAX       SnmpAdminString
    MAX-ACCESS   read-only
    STATUS       current
    DESCRIPTION
        "Cisco Firepower equipment:LocalDiskControllerCapProvider:revision
         managed object property"
    ::= { cfprApEquipmentLocalDiskControllerCapProviderEntry 17 }

cfprApEquipmentLocalDiskControllerCapProviderVendor OBJECT-TYPE
    SYNTAX       SnmpAdminString
    MAX-ACCESS   read-only
    STATUS       current
    DESCRIPTION
        "Cisco Firepower equipment:LocalDiskControllerCapProvider:vendor
        managed object property"
    ::= { cfprApEquipmentLocalDiskControllerCapProviderEntry 18 }

cfprApEquipmentLocalDiskControllerCapRefTable OBJECT-TYPE
    SYNTAX           SEQUENCE OF CfprApEquipmentLocalDiskControllerCapRefEntry
    MAX-ACCESS       not-accessible
    STATUS           current
    DESCRIPTION
        "Cisco Firepower equipment:LocalDiskControllerCapRef
        managed object table"
    ::= { cfprApEquipmentObjects 80 }

cfprApEquipmentLocalDiskControllerCapRefEntry OBJECT-TYPE
    SYNTAX           CfprApEquipmentLocalDiskControllerCapRefEntry
    MAX-ACCESS       not-accessible
    STATUS           current
    DESCRIPTION
        "Entry for the cfprApEquipmentLocalDiskControllerCapRefTable table."
    INDEX { cfprApEquipmentLocalDiskControllerCapRefInstanceId }
    ::= { cfprApEquipmentLocalDiskControllerCapRefTable 1 }

CfprApEquipmentLocalDiskControllerCapRefEntry ::= SEQUENCE {
    cfprApEquipmentLocalDiskControllerCapRefInstanceId               CfprApManagedObjectId,
    cfprApEquipmentLocalDiskControllerCapRefDn                       CfprApManagedObjectDn,
    cfprApEquipmentLocalDiskControllerCapRefRn                       SnmpAdminString,
    cfprApEquipmentLocalDiskControllerCapRefIsSupported              CfprApEquipmentIsSupported,
    cfprApEquipmentLocalDiskControllerCapRefModel                    SnmpAdminString,
    cfprApEquipmentLocalDiskControllerCapRefRevision                 SnmpAdminString,
    cfprApEquipmentLocalDiskControllerCapRefVendor                   SnmpAdminString
}

cfprApEquipmentLocalDiskControllerCapRefInstanceId OBJECT-TYPE
    SYNTAX       CfprApManagedObjectId
    MAX-ACCESS   not-accessible
    STATUS       current
    DESCRIPTION
        "Instance identifier of the managed object."
    ::= { cfprApEquipmentLocalDiskControllerCapRefEntry 1 }

cfprApEquipmentLocalDiskControllerCapRefDn OBJECT-TYPE
    SYNTAX       CfprApManagedObjectDn
    MAX-ACCESS   read-only
    STATUS       current
    DESCRIPTION
        "Cisco Firepower equipment:LocalDiskControllerCapRef:dn
        managed object property"
    ::= { cfprApEquipmentLocalDiskControllerCapRefEntry 2 }

cfprApEquipmentLocalDiskControllerCapRefRn OBJECT-TYPE
    SYNTAX       SnmpAdminString
    MAX-ACCESS   read-only
    STATUS       current
    DESCRIPTION
        "Cisco Firepower equipment:LocalDiskControllerCapRef:rn
        managed object property"
    ::= { cfprApEquipmentLocalDiskControllerCapRefEntry 3 }

cfprApEquipmentLocalDiskControllerCapRefIsSupported OBJECT-TYPE
    SYNTAX       CfprApEquipmentIsSupported
    MAX-ACCESS   read-only
    STATUS       current
    DESCRIPTION
        "Cisco Firepower equipment:LocalDiskControllerCapRef:isSupported
        managed object property"
    ::= { cfprApEquipmentLocalDiskControllerCapRefEntry 4 }

cfprApEquipmentLocalDiskControllerCapRefModel OBJECT-TYPE
    SYNTAX       SnmpAdminString
    MAX-ACCESS   read-only
    STATUS       current
    DESCRIPTION
        "Cisco Firepower equipment:LocalDiskControllerCapRef:model
        managed object property"
    ::= { cfprApEquipmentLocalDiskControllerCapRefEntry 5 }

cfprApEquipmentLocalDiskControllerCapRefRevision OBJECT-TYPE
    SYNTAX       SnmpAdminString
    MAX-ACCESS   read-only
    STATUS       current
    DESCRIPTION
        "Cisco Firepower equipment:LocalDiskControllerCapRef:revision
        managed object property"
    ::= { cfprApEquipmentLocalDiskControllerCapRefEntry 6 }

cfprApEquipmentLocalDiskControllerCapRefVendor OBJECT-TYPE
    SYNTAX       SnmpAdminString
    MAX-ACCESS   read-only
    STATUS       current
    DESCRIPTION
        "Cisco Firepower equipment:LocalDiskControllerCapRef:vendor
        managed object property"
    ::= { cfprApEquipmentLocalDiskControllerCapRefEntry 7 }

cfprApEquipmentLocalDiskControllerDefTable OBJECT-TYPE
    SYNTAX           SEQUENCE OF CfprApEquipmentLocalDiskControllerDefEntry
    MAX-ACCESS       not-accessible
    STATUS           current
    DESCRIPTION
        "Cisco Firepower equipment:LocalDiskControllerDef
        managed object table"
    ::= { cfprApEquipmentObjects 81 }

cfprApEquipmentLocalDiskControllerDefEntry OBJECT-TYPE
    SYNTAX           CfprApEquipmentLocalDiskControllerDefEntry
    MAX-ACCESS       not-accessible
    STATUS           current
    DESCRIPTION
        "Entry for the cfprApEquipmentLocalDiskControllerDefTable table."
    INDEX { cfprApEquipmentLocalDiskControllerDefInstanceId }
    ::= { cfprApEquipmentLocalDiskControllerDefTable 1 }

CfprApEquipmentLocalDiskControllerDefEntry ::= SEQUENCE {
    cfprApEquipmentLocalDiskControllerDefInstanceId                  CfprApManagedObjectId,
    cfprApEquipmentLocalDiskControllerDefDn                          CfprApManagedObjectDn,
    cfprApEquipmentLocalDiskControllerDefRn                          SnmpAdminString,
    cfprApEquipmentLocalDiskControllerDefDescr                       SnmpAdminString,
    cfprApEquipmentLocalDiskControllerDefForceUpdateVersion          TruthValue,
    cfprApEquipmentLocalDiskControllerDefIntId                       SnmpAdminString,
    cfprApEquipmentLocalDiskControllerDefName                        SnmpAdminString,
    cfprApEquipmentLocalDiskControllerDefPolicyLevel                 Gauge32,
    cfprApEquipmentLocalDiskControllerDefPolicyOwner                 CfprApPolicyPolicyOwner
}

cfprApEquipmentLocalDiskControllerDefInstanceId OBJECT-TYPE
    SYNTAX       CfprApManagedObjectId
    MAX-ACCESS   not-accessible
    STATUS       current
    DESCRIPTION
        "Instance identifier of the managed object."
    ::= { cfprApEquipmentLocalDiskControllerDefEntry 1 }

cfprApEquipmentLocalDiskControllerDefDn OBJECT-TYPE
    SYNTAX       CfprApManagedObjectDn
    MAX-ACCESS   read-only
    STATUS       current
    DESCRIPTION
        "Cisco Firepower equipment:LocalDiskControllerDef:dn
        managed object property"
    ::= { cfprApEquipmentLocalDiskControllerDefEntry 2 }

cfprApEquipmentLocalDiskControllerDefRn OBJECT-TYPE
    SYNTAX       SnmpAdminString
    MAX-ACCESS   read-only
    STATUS       current
    DESCRIPTION
        "Cisco Firepower equipment:LocalDiskControllerDef:rn
        managed object property"
    ::= { cfprApEquipmentLocalDiskControllerDefEntry 3 }

cfprApEquipmentLocalDiskControllerDefDescr OBJECT-TYPE
    SYNTAX       SnmpAdminString
    MAX-ACCESS   read-only
    STATUS       current
    DESCRIPTION
        "Cisco Firepower equipment:LocalDiskControllerDef:descr
        managed object property"
    ::= { cfprApEquipmentLocalDiskControllerDefEntry 4 }

cfprApEquipmentLocalDiskControllerDefForceUpdateVersion OBJECT-TYPE
    SYNTAX       TruthValue
    MAX-ACCESS   read-only
    STATUS       current
    DESCRIPTION
        "Cisco Firepower equipment:LocalDiskControllerDef:forceUpdateVersi
        on managed object property"
    ::= { cfprApEquipmentLocalDiskControllerDefEntry 5 }

cfprApEquipmentLocalDiskControllerDefIntId OBJECT-TYPE
    SYNTAX       SnmpAdminString
    MAX-ACCESS   read-only
    STATUS       current
    DESCRIPTION
        "Cisco Firepower equipment:LocalDiskControllerDef:intId
        managed object property"
    ::= { cfprApEquipmentLocalDiskControllerDefEntry 6 }

cfprApEquipmentLocalDiskControllerDefName OBJECT-TYPE
    SYNTAX       SnmpAdminString
    MAX-ACCESS   read-only
    STATUS       current
    DESCRIPTION
        "Cisco Firepower equipment:LocalDiskControllerDef:name
        managed object property"
    ::= { cfprApEquipmentLocalDiskControllerDefEntry 7 }

cfprApEquipmentLocalDiskControllerDefPolicyLevel OBJECT-TYPE
    SYNTAX       Gauge32
    MAX-ACCESS   read-only
    STATUS       current
    DESCRIPTION
        "Cisco Firepower equipment:LocalDiskControllerDef:policyLevel
        managed object property"
    ::= { cfprApEquipmentLocalDiskControllerDefEntry 8 }

cfprApEquipmentLocalDiskControllerDefPolicyOwner OBJECT-TYPE
    SYNTAX       CfprApPolicyPolicyOwner
    MAX-ACCESS   read-only
    STATUS       current
    DESCRIPTION
        "Cisco Firepower equipment:LocalDiskControllerDef:policyOwner
        managed object property"
    ::= { cfprApEquipmentLocalDiskControllerDefEntry 9 }

cfprApEquipmentLocalDiskDefTable OBJECT-TYPE
    SYNTAX           SEQUENCE OF CfprApEquipmentLocalDiskDefEntry
    MAX-ACCESS       not-accessible
    STATUS           current
    DESCRIPTION
        "Cisco Firepower equipment:LocalDiskDef managed object table"
    ::= { cfprApEquipmentObjects 82 }

cfprApEquipmentLocalDiskDefEntry OBJECT-TYPE
    SYNTAX           CfprApEquipmentLocalDiskDefEntry
    MAX-ACCESS       not-accessible
    STATUS           current
    DESCRIPTION
        "Entry for the cfprApEquipmentLocalDiskDefTable table."
    INDEX { cfprApEquipmentLocalDiskDefInstanceId }
    ::= { cfprApEquipmentLocalDiskDefTable 1 }

CfprApEquipmentLocalDiskDefEntry ::= SEQUENCE {
    cfprApEquipmentLocalDiskDefInstanceId                            CfprApManagedObjectId,
    cfprApEquipmentLocalDiskDefDn                                    CfprApManagedObjectDn,
    cfprApEquipmentLocalDiskDefRn                                    SnmpAdminString,
    cfprApEquipmentLocalDiskDefBlockSize                             Gauge32,
    cfprApEquipmentLocalDiskDefCacheSize                             SnmpAdminString,
    cfprApEquipmentLocalDiskDefCapacity                              SnmpAdminString,
    cfprApEquipmentLocalDiskDefDescr                                 SnmpAdminString,
    cfprApEquipmentLocalDiskDefForceUpdateVersion                    TruthValue,
    cfprApEquipmentLocalDiskDefIntId                                 SnmpAdminString,
    cfprApEquipmentLocalDiskDefLinkSpeed                             SnmpAdminString,
    cfprApEquipmentLocalDiskDefName                                  SnmpAdminString,
    cfprApEquipmentLocalDiskDefNumberOfBlocks                        Unsigned64,
    cfprApEquipmentLocalDiskDefPolicyLevel                           Gauge32,
    cfprApEquipmentLocalDiskDefPolicyOwner                           CfprApPolicyPolicyOwner,
    cfprApEquipmentLocalDiskDefRotationalSpeed                       INTEGER,
    cfprApEquipmentLocalDiskDefSeekAverageReadWrite                  SnmpAdminString,
    cfprApEquipmentLocalDiskDefSeekTrackToTrackReadWrite             SnmpAdminString,
    cfprApEquipmentLocalDiskDefTechnology                            CfprApStorageTechnology
}

cfprApEquipmentLocalDiskDefInstanceId OBJECT-TYPE
    SYNTAX       CfprApManagedObjectId
    MAX-ACCESS   not-accessible
    STATUS       current
    DESCRIPTION
        "Instance identifier of the managed object."
    ::= { cfprApEquipmentLocalDiskDefEntry 1 }

cfprApEquipmentLocalDiskDefDn OBJECT-TYPE
    SYNTAX       CfprApManagedObjectDn
    MAX-ACCESS   read-only
    STATUS       current
    DESCRIPTION
        "Cisco Firepower equipment:LocalDiskDef:dn managed
        object property"
    ::= { cfprApEquipmentLocalDiskDefEntry 2 }

cfprApEquipmentLocalDiskDefRn OBJECT-TYPE
    SYNTAX       SnmpAdminString
    MAX-ACCESS   read-only
    STATUS       current
    DESCRIPTION
        "Cisco Firepower equipment:LocalDiskDef:rn managed
        object property"
    ::= { cfprApEquipmentLocalDiskDefEntry 3 }

cfprApEquipmentLocalDiskDefBlockSize OBJECT-TYPE
    SYNTAX       Gauge32
    MAX-ACCESS   read-only
    STATUS       current
    DESCRIPTION
        "Cisco Firepower equipment:LocalDiskDef:blockSize
        managed object property"
    ::= { cfprApEquipmentLocalDiskDefEntry 4 }

cfprApEquipmentLocalDiskDefCacheSize OBJECT-TYPE
    SYNTAX       SnmpAdminString
    MAX-ACCESS   read-only
    STATUS       current
    DESCRIPTION
        "Cisco Firepower equipment:LocalDiskDef:cacheSize
        managed object property"
    ::= { cfprApEquipmentLocalDiskDefEntry 5 }

cfprApEquipmentLocalDiskDefCapacity OBJECT-TYPE
    SYNTAX       SnmpAdminString
    MAX-ACCESS   read-only
    STATUS       current
    DESCRIPTION
        "Cisco Firepower equipment:LocalDiskDef:capacity
        managed object property"
    ::= { cfprApEquipmentLocalDiskDefEntry 6 }

cfprApEquipmentLocalDiskDefDescr OBJECT-TYPE
    SYNTAX       SnmpAdminString
    MAX-ACCESS   read-only
    STATUS       current
    DESCRIPTION
        "Cisco Firepower equipment:LocalDiskDef:descr managed
        object property"
    ::= { cfprApEquipmentLocalDiskDefEntry 7 }

cfprApEquipmentLocalDiskDefForceUpdateVersion OBJECT-TYPE
    SYNTAX       TruthValue
    MAX-ACCESS   read-only
    STATUS       current
    DESCRIPTION
        "Cisco Firepower equipment:LocalDiskDef:forceUpdateVersion
        managed object property"
    ::= { cfprApEquipmentLocalDiskDefEntry 8 }

cfprApEquipmentLocalDiskDefIntId OBJECT-TYPE
    SYNTAX       SnmpAdminString
    MAX-ACCESS   read-only
    STATUS       current
    DESCRIPTION
        "Cisco Firepower equipment:LocalDiskDef:intId managed
        object property"
    ::= { cfprApEquipmentLocalDiskDefEntry 9 }

cfprApEquipmentLocalDiskDefLinkSpeed OBJECT-TYPE
    SYNTAX       SnmpAdminString
    MAX-ACCESS   read-only
    STATUS       current
    DESCRIPTION
        "Cisco Firepower equipment:LocalDiskDef:linkSpeed
        managed object property"
    ::= { cfprApEquipmentLocalDiskDefEntry 10 }

cfprApEquipmentLocalDiskDefName OBJECT-TYPE
    SYNTAX       SnmpAdminString
    MAX-ACCESS   read-only
    STATUS       current
    DESCRIPTION
        "Cisco Firepower equipment:LocalDiskDef:name managed
        object property"
    ::= { cfprApEquipmentLocalDiskDefEntry 11 }

cfprApEquipmentLocalDiskDefNumberOfBlocks OBJECT-TYPE
    SYNTAX       Unsigned64
    MAX-ACCESS   read-only
    STATUS       current
    DESCRIPTION
        "Cisco Firepower equipment:LocalDiskDef:numberOfBlocks
        managed object property"
    ::= { cfprApEquipmentLocalDiskDefEntry 12 }

cfprApEquipmentLocalDiskDefPolicyLevel OBJECT-TYPE
    SYNTAX       Gauge32
    MAX-ACCESS   read-only
    STATUS       current
    DESCRIPTION
        "Cisco Firepower equipment:LocalDiskDef:policyLevel
        managed object property"
    ::= { cfprApEquipmentLocalDiskDefEntry 13 }

cfprApEquipmentLocalDiskDefPolicyOwner OBJECT-TYPE
    SYNTAX       CfprApPolicyPolicyOwner
    MAX-ACCESS   read-only
    STATUS       current
    DESCRIPTION
        "Cisco Firepower equipment:LocalDiskDef:policyOwner
        managed object property"
    ::= { cfprApEquipmentLocalDiskDefEntry 14 }

cfprApEquipmentLocalDiskDefRotationalSpeed OBJECT-TYPE
    SYNTAX       INTEGER
    MAX-ACCESS   read-only
    STATUS       current
    DESCRIPTION
        "Cisco Firepower equipment:LocalDiskDef:rotationalSpeed
        managed object property"
    ::= { cfprApEquipmentLocalDiskDefEntry 15 }

cfprApEquipmentLocalDiskDefSeekAverageReadWrite OBJECT-TYPE
    SYNTAX       SnmpAdminString
    MAX-ACCESS   read-only
    STATUS       current
    DESCRIPTION
        "Cisco Firepower equipment:LocalDiskDef:seekAverageReadWrite
        managed object property"
    ::= { cfprApEquipmentLocalDiskDefEntry 16 }

cfprApEquipmentLocalDiskDefSeekTrackToTrackReadWrite OBJECT-TYPE
    SYNTAX       SnmpAdminString
    MAX-ACCESS   read-only
    STATUS       current
    DESCRIPTION
        "Cisco Firepower equipment:LocalDiskDef:seekTrackToTrackReadWrite
        managed object property"
    ::= { cfprApEquipmentLocalDiskDefEntry 17 }

cfprApEquipmentLocalDiskDefTechnology OBJECT-TYPE
    SYNTAX       CfprApStorageTechnology
    MAX-ACCESS   read-only
    STATUS       current
    DESCRIPTION
        "Cisco Firepower equipment:LocalDiskDef:technology
        managed object property"
    ::= { cfprApEquipmentLocalDiskDefEntry 18 }

cfprApEquipmentLocatorLedTable OBJECT-TYPE
    SYNTAX           SEQUENCE OF CfprApEquipmentLocatorLedEntry
    MAX-ACCESS       not-accessible
    STATUS           current
    DESCRIPTION
        "Cisco Firepower equipment:LocatorLed managed object table"
    ::= { cfprApEquipmentObjects 83 }

cfprApEquipmentLocatorLedEntry OBJECT-TYPE
    SYNTAX           CfprApEquipmentLocatorLedEntry
    MAX-ACCESS       not-accessible
    STATUS           current
    DESCRIPTION
        "Entry for the cfprApEquipmentLocatorLedTable table."
    INDEX { cfprApEquipmentLocatorLedInstanceId }
    ::= { cfprApEquipmentLocatorLedTable 1 }

CfprApEquipmentLocatorLedEntry ::= SEQUENCE {
    cfprApEquipmentLocatorLedInstanceId                              CfprApManagedObjectId,
    cfprApEquipmentLocatorLedDn                                      CfprApManagedObjectDn,
    cfprApEquipmentLocatorLedRn                                      SnmpAdminString,
    cfprApEquipmentLocatorLedAdminState                              CfprApEquipmentLedLocatorState,
    cfprApEquipmentLocatorLedColor                                   CfprApEquipmentLedColor,
    cfprApEquipmentLocatorLedFsmDescr                                SnmpAdminString,
    cfprApEquipmentLocatorLedFsmPrev                                 SnmpAdminString,
    cfprApEquipmentLocatorLedFsmProgr                                Gauge32,
    cfprApEquipmentLocatorLedFsmRmtInvErrCode                        Gauge32,
    cfprApEquipmentLocatorLedFsmRmtInvErrDescr                       SnmpAdminString,
    cfprApEquipmentLocatorLedFsmRmtInvRslt                           CfprApConditionRemoteInvRslt,
    cfprApEquipmentLocatorLedFsmStageDescr                           SnmpAdminString,
    cfprApEquipmentLocatorLedFsmStamp                                DateAndTime,
    cfprApEquipmentLocatorLedFsmStatus                               SnmpAdminString,
    cfprApEquipmentLocatorLedFsmTry                                  Gauge32,
    cfprApEquipmentLocatorLedId                                      Gauge32,
    cfprApEquipmentLocatorLedName                                    SnmpAdminString,
    cfprApEquipmentLocatorLedOperState                               CfprApEquipmentLedOperState
}

cfprApEquipmentLocatorLedInstanceId OBJECT-TYPE
    SYNTAX       CfprApManagedObjectId
    MAX-ACCESS   not-accessible
    STATUS       current
    DESCRIPTION
        "Instance identifier of the managed object."
    ::= { cfprApEquipmentLocatorLedEntry 1 }

cfprApEquipmentLocatorLedDn OBJECT-TYPE
    SYNTAX       CfprApManagedObjectDn
    MAX-ACCESS   read-only
    STATUS       current
    DESCRIPTION
        "Cisco Firepower equipment:LocatorLed:dn managed object property"
    ::= { cfprApEquipmentLocatorLedEntry 2 }

cfprApEquipmentLocatorLedRn OBJECT-TYPE
    SYNTAX       SnmpAdminString
    MAX-ACCESS   read-only
    STATUS       current
    DESCRIPTION
        "Cisco Firepower equipment:LocatorLed:rn managed object property"
    ::= { cfprApEquipmentLocatorLedEntry 3 }

cfprApEquipmentLocatorLedAdminState OBJECT-TYPE
    SYNTAX       CfprApEquipmentLedLocatorState
    MAX-ACCESS   read-only
    STATUS       current
    DESCRIPTION
        "Cisco Firepower equipment:LocatorLed:adminState
        managed object property"
    ::= { cfprApEquipmentLocatorLedEntry 4 }

cfprApEquipmentLocatorLedColor OBJECT-TYPE
    SYNTAX       CfprApEquipmentLedColor
    MAX-ACCESS   read-only
    STATUS       current
    DESCRIPTION
        "Cisco Firepower equipment:LocatorLed:color managed
        object property"
    ::= { cfprApEquipmentLocatorLedEntry 6 }

cfprApEquipmentLocatorLedFsmDescr OBJECT-TYPE
    SYNTAX       SnmpAdminString
    MAX-ACCESS   read-only
    STATUS       current
    DESCRIPTION
        "Cisco Firepower equipment:LocatorLed:fsmDescr
        managed object property"
    ::= { cfprApEquipmentLocatorLedEntry 7 }

cfprApEquipmentLocatorLedFsmPrev OBJECT-TYPE
    SYNTAX       SnmpAdminString
    MAX-ACCESS   read-only
    STATUS       current
    DESCRIPTION
        "Cisco Firepower equipment:LocatorLed:fsmPrev managed
        object property"
    ::= { cfprApEquipmentLocatorLedEntry 8 }

cfprApEquipmentLocatorLedFsmProgr OBJECT-TYPE
    SYNTAX       Gauge32
    MAX-ACCESS   read-only
    STATUS       current
    DESCRIPTION
        "Cisco Firepower equipment:LocatorLed:fsmProgr
        managed object property"
    ::= { cfprApEquipmentLocatorLedEntry 9 }

cfprApEquipmentLocatorLedFsmRmtInvErrCode OBJECT-TYPE
    SYNTAX       Gauge32
    MAX-ACCESS   read-only
    STATUS       current
    DESCRIPTION
        "Cisco Firepower equipment:LocatorLed:fsmRmtInvErrCode
        managed object property"
    ::= { cfprApEquipmentLocatorLedEntry 10 }

cfprApEquipmentLocatorLedFsmRmtInvErrDescr OBJECT-TYPE
    SYNTAX       SnmpAdminString
    MAX-ACCESS   read-only
    STATUS       current
    DESCRIPTION
        "Cisco Firepower equipment:LocatorLed:fsmRmtInvErrDescr
        managed object property"
    ::= { cfprApEquipmentLocatorLedEntry 11 }

cfprApEquipmentLocatorLedFsmRmtInvRslt OBJECT-TYPE
    SYNTAX       CfprApConditionRemoteInvRslt
    MAX-ACCESS   read-only
    STATUS       current
    DESCRIPTION
        "Cisco Firepower equipment:LocatorLed:fsmRmtInvRslt
        managed object property"
    ::= { cfprApEquipmentLocatorLedEntry 12 }

cfprApEquipmentLocatorLedFsmStageDescr OBJECT-TYPE
    SYNTAX       SnmpAdminString
    MAX-ACCESS   read-only
    STATUS       current
    DESCRIPTION
        "Cisco Firepower equipment:LocatorLed:fsmStageDescr
        managed object property"
    ::= { cfprApEquipmentLocatorLedEntry 13 }

cfprApEquipmentLocatorLedFsmStamp OBJECT-TYPE
    SYNTAX       DateAndTime
    MAX-ACCESS   read-only
    STATUS       current
    DESCRIPTION
        "Cisco Firepower equipment:LocatorLed:fsmStamp
        managed object property"
    ::= { cfprApEquipmentLocatorLedEntry 14 }

cfprApEquipmentLocatorLedFsmStatus OBJECT-TYPE
    SYNTAX       SnmpAdminString
    MAX-ACCESS   read-only
    STATUS       current
    DESCRIPTION
        "Cisco Firepower equipment:LocatorLed:fsmStatus
        managed object property"
    ::= { cfprApEquipmentLocatorLedEntry 15 }

cfprApEquipmentLocatorLedFsmTry OBJECT-TYPE
    SYNTAX       Gauge32
    MAX-ACCESS   read-only
    STATUS       current
    DESCRIPTION
        "Cisco Firepower equipment:LocatorLed:fsmTry managed
        object property"
    ::= { cfprApEquipmentLocatorLedEntry 16 }

cfprApEquipmentLocatorLedId OBJECT-TYPE
    SYNTAX       Gauge32
    MAX-ACCESS   read-only
    STATUS       current
    DESCRIPTION
        "Cisco Firepower equipment:LocatorLed:id managed object property"
    ::= { cfprApEquipmentLocatorLedEntry 17 }

cfprApEquipmentLocatorLedName OBJECT-TYPE
    SYNTAX       SnmpAdminString
    MAX-ACCESS   read-only
    STATUS       current
    DESCRIPTION
        "Cisco Firepower equipment:LocatorLed:name managed
        object property"
    ::= { cfprApEquipmentLocatorLedEntry 18 }

cfprApEquipmentLocatorLedOperState OBJECT-TYPE
    SYNTAX       CfprApEquipmentLedOperState
    MAX-ACCESS   read-only
    STATUS       current
    DESCRIPTION
        "Cisco Firepower equipment:LocatorLed:operState
        managed object property"
    ::= { cfprApEquipmentLocatorLedEntry 19 }

cfprApEquipmentLocatorLedFsmTable OBJECT-TYPE
    SYNTAX           SEQUENCE OF CfprApEquipmentLocatorLedFsmEntry
    MAX-ACCESS       not-accessible
    STATUS           current
    DESCRIPTION
        "Cisco Firepower equipment:LocatorLedFsm managed object table"
    ::= { cfprApEquipmentObjects 84 }

cfprApEquipmentLocatorLedFsmEntry OBJECT-TYPE
    SYNTAX           CfprApEquipmentLocatorLedFsmEntry
    MAX-ACCESS       not-accessible
    STATUS           current
    DESCRIPTION
        "Entry for the cfprApEquipmentLocatorLedFsmTable table."
    INDEX { cfprApEquipmentLocatorLedFsmInstanceId }
    ::= { cfprApEquipmentLocatorLedFsmTable 1 }

CfprApEquipmentLocatorLedFsmEntry ::= SEQUENCE {
    cfprApEquipmentLocatorLedFsmInstanceId                           CfprApManagedObjectId,
    cfprApEquipmentLocatorLedFsmDn                                   CfprApManagedObjectDn,
    cfprApEquipmentLocatorLedFsmRn                                   SnmpAdminString,
    cfprApEquipmentLocatorLedFsmCompletionTime                       DateAndTime,
    cfprApEquipmentLocatorLedFsmCurrentFsm                           CfprApEquipmentLocatorLedFsmCurrentFsm,
    cfprApEquipmentLocatorLedFsmDescrData                            SnmpAdminString,
    cfprApEquipmentLocatorLedFsmFsmStatus                            CfprApFsmFsmStageStatus,
    cfprApEquipmentLocatorLedFsmProgress                             Gauge32,
    cfprApEquipmentLocatorLedFsmRmtErrCode                           Gauge32,
    cfprApEquipmentLocatorLedFsmRmtErrDescr                          SnmpAdminString,
    cfprApEquipmentLocatorLedFsmRmtRslt                              CfprApConditionRemoteInvRslt
}

cfprApEquipmentLocatorLedFsmInstanceId OBJECT-TYPE
    SYNTAX       CfprApManagedObjectId
    MAX-ACCESS   not-accessible
    STATUS       current
    DESCRIPTION
        "Instance identifier of the managed object."
    ::= { cfprApEquipmentLocatorLedFsmEntry 1 }

cfprApEquipmentLocatorLedFsmDn OBJECT-TYPE
    SYNTAX       CfprApManagedObjectDn
    MAX-ACCESS   read-only
    STATUS       current
    DESCRIPTION
        "Cisco Firepower equipment:LocatorLedFsm:dn managed
        object property"
    ::= { cfprApEquipmentLocatorLedFsmEntry 2 }

cfprApEquipmentLocatorLedFsmRn OBJECT-TYPE
    SYNTAX       SnmpAdminString
    MAX-ACCESS   read-only
    STATUS       current
    DESCRIPTION
        "Cisco Firepower equipment:LocatorLedFsm:rn managed
        object property"
    ::= { cfprApEquipmentLocatorLedFsmEntry 3 }

cfprApEquipmentLocatorLedFsmCompletionTime OBJECT-TYPE
    SYNTAX       DateAndTime
    MAX-ACCESS   read-only
    STATUS       current
    DESCRIPTION
        "Cisco Firepower equipment:LocatorLedFsm:completionTime
        managed object property"
    ::= { cfprApEquipmentLocatorLedFsmEntry 4 }

cfprApEquipmentLocatorLedFsmCurrentFsm OBJECT-TYPE
    SYNTAX       CfprApEquipmentLocatorLedFsmCurrentFsm
    MAX-ACCESS   read-only
    STATUS       current
    DESCRIPTION
        "Cisco Firepower equipment:LocatorLedFsm:currentFsm
        managed object property"
    ::= { cfprApEquipmentLocatorLedFsmEntry 5 }

cfprApEquipmentLocatorLedFsmDescrData OBJECT-TYPE
    SYNTAX       SnmpAdminString
    MAX-ACCESS   read-only
    STATUS       current
    DESCRIPTION
        "Cisco Firepower equipment:LocatorLedFsm:descr
        managed object property"
    ::= { cfprApEquipmentLocatorLedFsmEntry 6 }

cfprApEquipmentLocatorLedFsmFsmStatus OBJECT-TYPE
    SYNTAX       CfprApFsmFsmStageStatus
    MAX-ACCESS   read-only
    STATUS       current
    DESCRIPTION
        "Cisco Firepower equipment:LocatorLedFsm:fsmStatus
        managed object property"
    ::= { cfprApEquipmentLocatorLedFsmEntry 7 }

cfprApEquipmentLocatorLedFsmProgress OBJECT-TYPE
    SYNTAX       Gauge32
    MAX-ACCESS   read-only
    STATUS       current
    DESCRIPTION
        "Cisco Firepower equipment:LocatorLedFsm:progress
        managed object property"
    ::= { cfprApEquipmentLocatorLedFsmEntry 8 }

cfprApEquipmentLocatorLedFsmRmtErrCode OBJECT-TYPE
    SYNTAX       Gauge32
    MAX-ACCESS   read-only
    STATUS       current
    DESCRIPTION
        "Cisco Firepower equipment:LocatorLedFsm:rmtErrCode
        managed object property"
    ::= { cfprApEquipmentLocatorLedFsmEntry 9 }

cfprApEquipmentLocatorLedFsmRmtErrDescr OBJECT-TYPE
    SYNTAX       SnmpAdminString
    MAX-ACCESS   read-only
    STATUS       current
    DESCRIPTION
        "Cisco Firepower equipment:LocatorLedFsm:rmtErrDescr
        managed object property"
    ::= { cfprApEquipmentLocatorLedFsmEntry 10 }

cfprApEquipmentLocatorLedFsmRmtRslt OBJECT-TYPE
    SYNTAX       CfprApConditionRemoteInvRslt
    MAX-ACCESS   read-only
    STATUS       current
    DESCRIPTION
        "Cisco Firepower equipment:LocatorLedFsm:rmtRslt
        managed object property"
    ::= { cfprApEquipmentLocatorLedFsmEntry 11 }

cfprApEquipmentLocatorLedFsmStageTable OBJECT-TYPE
    SYNTAX           SEQUENCE OF CfprApEquipmentLocatorLedFsmStageEntry
    MAX-ACCESS       not-accessible
    STATUS           current
    DESCRIPTION
        "Cisco Firepower equipment:LocatorLedFsmStage managed
        object table"
    ::= { cfprApEquipmentObjects 85 }

cfprApEquipmentLocatorLedFsmStageEntry OBJECT-TYPE
    SYNTAX           CfprApEquipmentLocatorLedFsmStageEntry
    MAX-ACCESS       not-accessible
    STATUS           current
    DESCRIPTION
        "Entry for the cfprApEquipmentLocatorLedFsmStageTable table."
    INDEX { cfprApEquipmentLocatorLedFsmStageInstanceId }
    ::= { cfprApEquipmentLocatorLedFsmStageTable 1 }

CfprApEquipmentLocatorLedFsmStageEntry ::= SEQUENCE {
    cfprApEquipmentLocatorLedFsmStageInstanceId                      CfprApManagedObjectId,
    cfprApEquipmentLocatorLedFsmStageDn                              CfprApManagedObjectDn,
    cfprApEquipmentLocatorLedFsmStageRn                              SnmpAdminString,
    cfprApEquipmentLocatorLedFsmStageDescrData                       SnmpAdminString,
    cfprApEquipmentLocatorLedFsmStageLastUpdateTime                  DateAndTime,
    cfprApEquipmentLocatorLedFsmStageName                            CfprApEquipmentLocatorLedFsmStageName,
    cfprApEquipmentLocatorLedFsmStageOrder                           Gauge32,
    cfprApEquipmentLocatorLedFsmStageRetry                           Gauge32,
    cfprApEquipmentLocatorLedFsmStageStageStatus                     CfprApFsmFsmStageStatus
}

cfprApEquipmentLocatorLedFsmStageInstanceId OBJECT-TYPE
    SYNTAX       CfprApManagedObjectId
    MAX-ACCESS   not-accessible
    STATUS       current
    DESCRIPTION
        "Instance identifier of the managed object."
    ::= { cfprApEquipmentLocatorLedFsmStageEntry 1 }

cfprApEquipmentLocatorLedFsmStageDn OBJECT-TYPE
    SYNTAX       CfprApManagedObjectDn
    MAX-ACCESS   read-only
    STATUS       current
    DESCRIPTION
        "Cisco Firepower equipment:LocatorLedFsmStage:dn
        managed object property"
    ::= { cfprApEquipmentLocatorLedFsmStageEntry 2 }

cfprApEquipmentLocatorLedFsmStageRn OBJECT-TYPE
    SYNTAX       SnmpAdminString
    MAX-ACCESS   read-only
    STATUS       current
    DESCRIPTION
        "Cisco Firepower equipment:LocatorLedFsmStage:rn
        managed object property"
    ::= { cfprApEquipmentLocatorLedFsmStageEntry 3 }

cfprApEquipmentLocatorLedFsmStageDescrData OBJECT-TYPE
    SYNTAX       SnmpAdminString
    MAX-ACCESS   read-only
    STATUS       current
    DESCRIPTION
        "Cisco Firepower equipment:LocatorLedFsmStage:descr
        managed object property"
    ::= { cfprApEquipmentLocatorLedFsmStageEntry 4 }

cfprApEquipmentLocatorLedFsmStageLastUpdateTime OBJECT-TYPE
    SYNTAX       DateAndTime
    MAX-ACCESS   read-only
    STATUS       current
    DESCRIPTION
        "Cisco Firepower equipment:LocatorLedFsmStage:lastUpdateTime
        managed object property"
    ::= { cfprApEquipmentLocatorLedFsmStageEntry 5 }

cfprApEquipmentLocatorLedFsmStageName OBJECT-TYPE
    SYNTAX       CfprApEquipmentLocatorLedFsmStageName
    MAX-ACCESS   read-only
    STATUS       current
    DESCRIPTION
        "Cisco Firepower equipment:LocatorLedFsmStage:name
        managed object property"
    ::= { cfprApEquipmentLocatorLedFsmStageEntry 6 }

cfprApEquipmentLocatorLedFsmStageOrder OBJECT-TYPE
    SYNTAX       Gauge32
    MAX-ACCESS   read-only
    STATUS       current
    DESCRIPTION
        "Cisco Firepower equipment:LocatorLedFsmStage:order
        managed object property"
    ::= { cfprApEquipmentLocatorLedFsmStageEntry 7 }

cfprApEquipmentLocatorLedFsmStageRetry OBJECT-TYPE
    SYNTAX       Gauge32
    MAX-ACCESS   read-only
    STATUS       current
    DESCRIPTION
        "Cisco Firepower equipment:LocatorLedFsmStage:retry
        managed object property"
    ::= { cfprApEquipmentLocatorLedFsmStageEntry 8 }

cfprApEquipmentLocatorLedFsmStageStageStatus OBJECT-TYPE
    SYNTAX       CfprApFsmFsmStageStatus
    MAX-ACCESS   read-only
    STATUS       current
    DESCRIPTION
        "Cisco Firepower equipment:LocatorLedFsmStage:stageStatus
        managed object property"
    ::= { cfprApEquipmentLocatorLedFsmStageEntry 9 }

cfprApEquipmentLocatorLedFsmTaskTable OBJECT-TYPE
    SYNTAX           SEQUENCE OF CfprApEquipmentLocatorLedFsmTaskEntry
    MAX-ACCESS       not-accessible
    STATUS           current
    DESCRIPTION
        "Cisco Firepower equipment:LocatorLedFsmTask managed object table"
    ::= { cfprApEquipmentObjects 86 }

cfprApEquipmentLocatorLedFsmTaskEntry OBJECT-TYPE
    SYNTAX           CfprApEquipmentLocatorLedFsmTaskEntry
    MAX-ACCESS       not-accessible
    STATUS           current
    DESCRIPTION
        "Entry for the cfprApEquipmentLocatorLedFsmTaskTable table."
    INDEX { cfprApEquipmentLocatorLedFsmTaskInstanceId }
    ::= { cfprApEquipmentLocatorLedFsmTaskTable 1 }

CfprApEquipmentLocatorLedFsmTaskEntry ::= SEQUENCE {
    cfprApEquipmentLocatorLedFsmTaskInstanceId                       CfprApManagedObjectId,
    cfprApEquipmentLocatorLedFsmTaskDn                               CfprApManagedObjectDn,
    cfprApEquipmentLocatorLedFsmTaskRn                               SnmpAdminString,
    cfprApEquipmentLocatorLedFsmTaskCompletion                       CfprApFsmCompletion,
    cfprApEquipmentLocatorLedFsmTaskFlags                            CfprApFsmFlags,
    cfprApEquipmentLocatorLedFsmTaskItem                             CfprApEquipmentLocatorLedFsmTaskItem,
    cfprApEquipmentLocatorLedFsmTaskSeqId                            Gauge32
}

cfprApEquipmentLocatorLedFsmTaskInstanceId OBJECT-TYPE
    SYNTAX       CfprApManagedObjectId
    MAX-ACCESS   not-accessible
    STATUS       current
    DESCRIPTION
        "Instance identifier of the managed object."
    ::= { cfprApEquipmentLocatorLedFsmTaskEntry 1 }

cfprApEquipmentLocatorLedFsmTaskDn OBJECT-TYPE
    SYNTAX       CfprApManagedObjectDn
    MAX-ACCESS   read-only
    STATUS       current
    DESCRIPTION
        "Cisco Firepower equipment:LocatorLedFsmTask:dn
        managed object property"
    ::= { cfprApEquipmentLocatorLedFsmTaskEntry 2 }

cfprApEquipmentLocatorLedFsmTaskRn OBJECT-TYPE
    SYNTAX       SnmpAdminString
    MAX-ACCESS   read-only
    STATUS       current
    DESCRIPTION
        "Cisco Firepower equipment:LocatorLedFsmTask:rn
        managed object property"
    ::= { cfprApEquipmentLocatorLedFsmTaskEntry 3 }

cfprApEquipmentLocatorLedFsmTaskCompletion OBJECT-TYPE
    SYNTAX       CfprApFsmCompletion
    MAX-ACCESS   read-only
    STATUS       current
    DESCRIPTION
        "Cisco Firepower equipment:LocatorLedFsmTask:completion
        managed object property"
    ::= { cfprApEquipmentLocatorLedFsmTaskEntry 4 }

cfprApEquipmentLocatorLedFsmTaskFlags OBJECT-TYPE
    SYNTAX       CfprApFsmFlags
    MAX-ACCESS   read-only
    STATUS       current
    DESCRIPTION
        "Cisco Firepower equipment:LocatorLedFsmTask:flags
        managed object property"
    ::= { cfprApEquipmentLocatorLedFsmTaskEntry 5 }

cfprApEquipmentLocatorLedFsmTaskItem OBJECT-TYPE
    SYNTAX       CfprApEquipmentLocatorLedFsmTaskItem
    MAX-ACCESS   read-only
    STATUS       current
    DESCRIPTION
        "Cisco Firepower equipment:LocatorLedFsmTask:item
        managed object property"
    ::= { cfprApEquipmentLocatorLedFsmTaskEntry 6 }

cfprApEquipmentLocatorLedFsmTaskSeqId OBJECT-TYPE
    SYNTAX       Gauge32
    MAX-ACCESS   read-only
    STATUS       current
    DESCRIPTION
        "Cisco Firepower equipment:LocatorLedFsmTask:seqId
        managed object property"
    ::= { cfprApEquipmentLocatorLedFsmTaskEntry 7 }

cfprApEquipmentManufacturingDefTable OBJECT-TYPE
    SYNTAX           SEQUENCE OF CfprApEquipmentManufacturingDefEntry
    MAX-ACCESS       not-accessible
    STATUS           current
    DESCRIPTION
        "Cisco Firepower equipment:ManufacturingDef managed object table"
    ::= { cfprApEquipmentObjects 87 }

cfprApEquipmentManufacturingDefEntry OBJECT-TYPE
    SYNTAX           CfprApEquipmentManufacturingDefEntry
    MAX-ACCESS       not-accessible
    STATUS           current
    DESCRIPTION
        "Entry for the cfprApEquipmentManufacturingDefTable table."
    INDEX { cfprApEquipmentManufacturingDefInstanceId }
    ::= { cfprApEquipmentManufacturingDefTable 1 }

CfprApEquipmentManufacturingDefEntry ::= SEQUENCE {
    cfprApEquipmentManufacturingDefInstanceId                        CfprApManagedObjectId,
    cfprApEquipmentManufacturingDefDn                                CfprApManagedObjectDn,
    cfprApEquipmentManufacturingDefRn                                SnmpAdminString,
    cfprApEquipmentManufacturingDefCaption                           SnmpAdminString,
    cfprApEquipmentManufacturingDefClei                              SnmpAdminString,
    cfprApEquipmentManufacturingDefDescr                             SnmpAdminString,
    cfprApEquipmentManufacturingDefDescription                       SnmpAdminString,
    cfprApEquipmentManufacturingDefFruMajorType                      SnmpAdminString,
    cfprApEquipmentManufacturingDefFruMinorType                      SnmpAdminString,
    cfprApEquipmentManufacturingDefIntId                             SnmpAdminString,
    cfprApEquipmentManufacturingDefName                              SnmpAdminString,
    cfprApEquipmentManufacturingDefOemName                           SnmpAdminString,
    cfprApEquipmentManufacturingDefOemPartNumber                     SnmpAdminString,
    cfprApEquipmentManufacturingDefPartNumber                        SnmpAdminString,
    cfprApEquipmentManufacturingDefPid                               SnmpAdminString,
    cfprApEquipmentManufacturingDefPolicyLevel                       Gauge32,
    cfprApEquipmentManufacturingDefPolicyOwner                       CfprApPolicyPolicyOwner,
    cfprApEquipmentManufacturingDefSeries                            SnmpAdminString,
    cfprApEquipmentManufacturingDefSku                               SnmpAdminString,
    cfprApEquipmentManufacturingDefVendorEquipmentType               SnmpAdminString,
    cfprApEquipmentManufacturingDefVid                               SnmpAdminString
}

cfprApEquipmentManufacturingDefInstanceId OBJECT-TYPE
    SYNTAX       CfprApManagedObjectId
    MAX-ACCESS   not-accessible
    STATUS       current
    DESCRIPTION
        "Instance identifier of the managed object."
    ::= { cfprApEquipmentManufacturingDefEntry 1 }

cfprApEquipmentManufacturingDefDn OBJECT-TYPE
    SYNTAX       CfprApManagedObjectDn
    MAX-ACCESS   read-only
    STATUS       current
    DESCRIPTION
        "Cisco Firepower equipment:ManufacturingDef:dn
        managed object property"
    ::= { cfprApEquipmentManufacturingDefEntry 2 }

cfprApEquipmentManufacturingDefRn OBJECT-TYPE
    SYNTAX       SnmpAdminString
    MAX-ACCESS   read-only
    STATUS       current
    DESCRIPTION
        "Cisco Firepower equipment:ManufacturingDef:rn
        managed object property"
    ::= { cfprApEquipmentManufacturingDefEntry 3 }

cfprApEquipmentManufacturingDefCaption OBJECT-TYPE
    SYNTAX       SnmpAdminString
    MAX-ACCESS   read-only
    STATUS       current
    DESCRIPTION
        "Cisco Firepower equipment:ManufacturingDef:caption
        managed object property"
    ::= { cfprApEquipmentManufacturingDefEntry 4 }

cfprApEquipmentManufacturingDefClei OBJECT-TYPE
    SYNTAX       SnmpAdminString
    MAX-ACCESS   read-only
    STATUS       current
    DESCRIPTION
        "Cisco Firepower equipment:ManufacturingDef:clei
        managed object property"
    ::= { cfprApEquipmentManufacturingDefEntry 5 }

cfprApEquipmentManufacturingDefDescr OBJECT-TYPE
    SYNTAX       SnmpAdminString
    MAX-ACCESS   read-only
    STATUS       current
    DESCRIPTION
        "Cisco Firepower equipment:ManufacturingDef:descr
        managed object property"
    ::= { cfprApEquipmentManufacturingDefEntry 6 }

cfprApEquipmentManufacturingDefDescription OBJECT-TYPE
    SYNTAX       SnmpAdminString
    MAX-ACCESS   read-only
    STATUS       current
    DESCRIPTION
        "Cisco Firepower equipment:ManufacturingDef:description
        managed object property"
    ::= { cfprApEquipmentManufacturingDefEntry 7 }

cfprApEquipmentManufacturingDefFruMajorType OBJECT-TYPE
    SYNTAX       SnmpAdminString
    MAX-ACCESS   read-only
    STATUS       current
    DESCRIPTION
        "Cisco Firepower equipment:ManufacturingDef:fruMajorType
        managed object property"
    ::= { cfprApEquipmentManufacturingDefEntry 8 }

cfprApEquipmentManufacturingDefFruMinorType OBJECT-TYPE
    SYNTAX       SnmpAdminString
    MAX-ACCESS   read-only
    STATUS       current
    DESCRIPTION
        "Cisco Firepower equipment:ManufacturingDef:fruMinorType
        managed object property"
    ::= { cfprApEquipmentManufacturingDefEntry 9 }

cfprApEquipmentManufacturingDefIntId OBJECT-TYPE
    SYNTAX       SnmpAdminString
    MAX-ACCESS   read-only
    STATUS       current
    DESCRIPTION
        "Cisco Firepower equipment:ManufacturingDef:intId
        managed object property"
    ::= { cfprApEquipmentManufacturingDefEntry 10 }

cfprApEquipmentManufacturingDefName OBJECT-TYPE
    SYNTAX       SnmpAdminString
    MAX-ACCESS   read-only
    STATUS       current
    DESCRIPTION
        "Cisco Firepower equipment:ManufacturingDef:name
        managed object property"
    ::= { cfprApEquipmentManufacturingDefEntry 11 }

cfprApEquipmentManufacturingDefOemName OBJECT-TYPE
    SYNTAX       SnmpAdminString
    MAX-ACCESS   read-only
    STATUS       current
    DESCRIPTION
        "Cisco Firepower equipment:ManufacturingDef:oemName
        managed object property"
    ::= { cfprApEquipmentManufacturingDefEntry 12 }

cfprApEquipmentManufacturingDefOemPartNumber OBJECT-TYPE
    SYNTAX       SnmpAdminString
    MAX-ACCESS   read-only
    STATUS       current
    DESCRIPTION
        "Cisco Firepower equipment:ManufacturingDef:oemPartNumber
        managed object property"
    ::= { cfprApEquipmentManufacturingDefEntry 13 }

cfprApEquipmentManufacturingDefPartNumber OBJECT-TYPE
    SYNTAX       SnmpAdminString
    MAX-ACCESS   read-only
    STATUS       current
    DESCRIPTION
        "Cisco Firepower equipment:ManufacturingDef:partNumber
        managed object property"
    ::= { cfprApEquipmentManufacturingDefEntry 14 }

cfprApEquipmentManufacturingDefPid OBJECT-TYPE
    SYNTAX       SnmpAdminString
    MAX-ACCESS   read-only
    STATUS       current
    DESCRIPTION
        "Cisco Firepower equipment:ManufacturingDef:pid
        managed object property"
    ::= { cfprApEquipmentManufacturingDefEntry 15 }

cfprApEquipmentManufacturingDefPolicyLevel OBJECT-TYPE
    SYNTAX       Gauge32
    MAX-ACCESS   read-only
    STATUS       current
    DESCRIPTION
        "Cisco Firepower equipment:ManufacturingDef:policyLevel
        managed object property"
    ::= { cfprApEquipmentManufacturingDefEntry 16 }

cfprApEquipmentManufacturingDefPolicyOwner OBJECT-TYPE
    SYNTAX       CfprApPolicyPolicyOwner
    MAX-ACCESS   read-only
    STATUS       current
    DESCRIPTION
        "Cisco Firepower equipment:ManufacturingDef:policyOwner
        managed object property"
    ::= { cfprApEquipmentManufacturingDefEntry 17 }

cfprApEquipmentManufacturingDefSeries OBJECT-TYPE
    SYNTAX       SnmpAdminString
    MAX-ACCESS   read-only
    STATUS       current
    DESCRIPTION
        "Cisco Firepower equipment:ManufacturingDef:series
        managed object property"
    ::= { cfprApEquipmentManufacturingDefEntry 18 }

cfprApEquipmentManufacturingDefSku OBJECT-TYPE
    SYNTAX       SnmpAdminString
    MAX-ACCESS   read-only
    STATUS       current
    DESCRIPTION
        "Cisco Firepower equipment:ManufacturingDef:sku
        managed object property"
    ::= { cfprApEquipmentManufacturingDefEntry 19 }

cfprApEquipmentManufacturingDefVendorEquipmentType OBJECT-TYPE
    SYNTAX       SnmpAdminString
    MAX-ACCESS   read-only
    STATUS       current
    DESCRIPTION
        "Cisco Firepower equipment:ManufacturingDef:vendorEquipmentType
        managed object property"
    ::= { cfprApEquipmentManufacturingDefEntry 20 }

cfprApEquipmentManufacturingDefVid OBJECT-TYPE
    SYNTAX       SnmpAdminString
    MAX-ACCESS   read-only
    STATUS       current
    DESCRIPTION
        "Cisco Firepower equipment:ManufacturingDef:vid
        managed object property"
    ::= { cfprApEquipmentManufacturingDefEntry 21 }

cfprApEquipmentMaxPortSpeedCapProviderTable OBJECT-TYPE
    SYNTAX           SEQUENCE OF CfprApEquipmentMaxPortSpeedCapProviderEntry
    MAX-ACCESS       not-accessible
    STATUS           current
    DESCRIPTION
        "Cisco Firepower equipment:MaxPortSpeedCapProvider
        managed object table"
    ::= { cfprApEquipmentObjects 88 }

cfprApEquipmentMaxPortSpeedCapProviderEntry OBJECT-TYPE
    SYNTAX           CfprApEquipmentMaxPortSpeedCapProviderEntry
    MAX-ACCESS       not-accessible
    STATUS           current
    DESCRIPTION
        "Entry for the cfprApEquipmentMaxPortSpeedCapProviderTable table."
    INDEX { cfprApEquipmentMaxPortSpeedCapProviderInstanceId }
    ::= { cfprApEquipmentMaxPortSpeedCapProviderTable 1 }

CfprApEquipmentMaxPortSpeedCapProviderEntry ::= SEQUENCE {
    cfprApEquipmentMaxPortSpeedCapProviderInstanceId                 CfprApManagedObjectId,
    cfprApEquipmentMaxPortSpeedCapProviderDn                         CfprApManagedObjectDn,
    cfprApEquipmentMaxPortSpeedCapProviderRn                         SnmpAdminString,
    cfprApEquipmentMaxPortSpeedCapProviderDescr                      SnmpAdminString,
    cfprApEquipmentMaxPortSpeedCapProviderEndPortId                  Gauge32,
    cfprApEquipmentMaxPortSpeedCapProviderIntId                      SnmpAdminString,
    cfprApEquipmentMaxPortSpeedCapProviderName                       SnmpAdminString,
    cfprApEquipmentMaxPortSpeedCapProviderPolicyLevel                Gauge32,
    cfprApEquipmentMaxPortSpeedCapProviderPolicyOwner                CfprApPolicyPolicyOwner,
    cfprApEquipmentMaxPortSpeedCapProviderStartPortId                Gauge32,
    cfprApEquipmentMaxPortSpeedCapProviderSupportedSpeed             Unsigned64
}

cfprApEquipmentMaxPortSpeedCapProviderInstanceId OBJECT-TYPE
    SYNTAX       CfprApManagedObjectId
    MAX-ACCESS   not-accessible
    STATUS       current
    DESCRIPTION
        "Instance identifier of the managed object."
    ::= { cfprApEquipmentMaxPortSpeedCapProviderEntry 1 }

cfprApEquipmentMaxPortSpeedCapProviderDn OBJECT-TYPE
    SYNTAX       CfprApManagedObjectDn
    MAX-ACCESS   read-only
    STATUS       current
    DESCRIPTION
        "Cisco Firepower equipment:MaxPortSpeedCapProvider:dn
        managed object property"
    ::= { cfprApEquipmentMaxPortSpeedCapProviderEntry 2 }

cfprApEquipmentMaxPortSpeedCapProviderRn OBJECT-TYPE
    SYNTAX       SnmpAdminString
    MAX-ACCESS   read-only
    STATUS       current
    DESCRIPTION
        "Cisco Firepower equipment:MaxPortSpeedCapProvider:rn
        managed object property"
    ::= { cfprApEquipmentMaxPortSpeedCapProviderEntry 3 }

cfprApEquipmentMaxPortSpeedCapProviderDescr OBJECT-TYPE
    SYNTAX       SnmpAdminString
    MAX-ACCESS   read-only
    STATUS       current
    DESCRIPTION
        "Cisco Firepower equipment:MaxPortSpeedCapProvider:descr
        managed object property"
    ::= { cfprApEquipmentMaxPortSpeedCapProviderEntry 4 }

cfprApEquipmentMaxPortSpeedCapProviderEndPortId OBJECT-TYPE
    SYNTAX       Gauge32
    MAX-ACCESS   read-only
    STATUS       current
    DESCRIPTION
        "Cisco Firepower equipment:MaxPortSpeedCapProvider:endPortId
        managed object property"
    ::= { cfprApEquipmentMaxPortSpeedCapProviderEntry 5 }

cfprApEquipmentMaxPortSpeedCapProviderIntId OBJECT-TYPE
    SYNTAX       SnmpAdminString
    MAX-ACCESS   read-only
    STATUS       current
    DESCRIPTION
        "Cisco Firepower equipment:MaxPortSpeedCapProvider:intId
        managed object property"
    ::= { cfprApEquipmentMaxPortSpeedCapProviderEntry 6 }

cfprApEquipmentMaxPortSpeedCapProviderName OBJECT-TYPE
    SYNTAX       SnmpAdminString
    MAX-ACCESS   read-only
    STATUS       current
    DESCRIPTION
        "Cisco Firepower equipment:MaxPortSpeedCapProvider:name
        managed object property"
    ::= { cfprApEquipmentMaxPortSpeedCapProviderEntry 7 }

cfprApEquipmentMaxPortSpeedCapProviderPolicyLevel OBJECT-TYPE
    SYNTAX       Gauge32
    MAX-ACCESS   read-only
    STATUS       current
    DESCRIPTION
        "Cisco Firepower equipment:MaxPortSpeedCapProvider:policyLevel
        managed object property"
    ::= { cfprApEquipmentMaxPortSpeedCapProviderEntry 8 }

cfprApEquipmentMaxPortSpeedCapProviderPolicyOwner OBJECT-TYPE
    SYNTAX       CfprApPolicyPolicyOwner
    MAX-ACCESS   read-only
    STATUS       current
    DESCRIPTION
        "Cisco Firepower equipment:MaxPortSpeedCapProvider:policyOwner
        managed object property"
    ::= { cfprApEquipmentMaxPortSpeedCapProviderEntry 9 }

cfprApEquipmentMaxPortSpeedCapProviderStartPortId OBJECT-TYPE
    SYNTAX       Gauge32
    MAX-ACCESS   read-only
    STATUS       current
    DESCRIPTION
        "Cisco Firepower equipment:MaxPortSpeedCapProvider:startPortId
        managed object property"
    ::= { cfprApEquipmentMaxPortSpeedCapProviderEntry 10 }

cfprApEquipmentMaxPortSpeedCapProviderSupportedSpeed OBJECT-TYPE
    SYNTAX       Unsigned64
    MAX-ACCESS   read-only
    STATUS       current
    DESCRIPTION
        "Cisco Firepower equipment:MaxPortSpeedCapProvider:supportedSpeed
        managed object property"
    ::= { cfprApEquipmentMaxPortSpeedCapProviderEntry 11 }

cfprApEquipmentMemoryUnitCapProviderTable OBJECT-TYPE
    SYNTAX           SEQUENCE OF CfprApEquipmentMemoryUnitCapProviderEntry
    MAX-ACCESS       not-accessible
    STATUS           current
    DESCRIPTION
        "Cisco Firepower equipment:MemoryUnitCapProvider
        managed object table"
    ::= { cfprApEquipmentObjects 89 }

cfprApEquipmentMemoryUnitCapProviderEntry OBJECT-TYPE
    SYNTAX           CfprApEquipmentMemoryUnitCapProviderEntry
    MAX-ACCESS       not-accessible
    STATUS           current
    DESCRIPTION
        "Entry for the cfprApEquipmentMemoryUnitCapProviderTable table."
    INDEX { cfprApEquipmentMemoryUnitCapProviderInstanceId }
    ::= { cfprApEquipmentMemoryUnitCapProviderTable 1 }

CfprApEquipmentMemoryUnitCapProviderEntry ::= SEQUENCE {
    cfprApEquipmentMemoryUnitCapProviderInstanceId                   CfprApManagedObjectId,
    cfprApEquipmentMemoryUnitCapProviderDn                           CfprApManagedObjectDn,
    cfprApEquipmentMemoryUnitCapProviderRn                           SnmpAdminString,
    cfprApEquipmentMemoryUnitCapProviderDeleted                      TruthValue,
    cfprApEquipmentMemoryUnitCapProviderDeprecated                   TruthValue,
    cfprApEquipmentMemoryUnitCapProviderElementLoadFailures          Gauge32,
    cfprApEquipmentMemoryUnitCapProviderElementsLoaded               Gauge32,
    cfprApEquipmentMemoryUnitCapProviderGencount                     Gauge32,
    cfprApEquipmentMemoryUnitCapProviderLoadErrors                   Gauge32,
    cfprApEquipmentMemoryUnitCapProviderLoadWarnings                 Gauge32,
    cfprApEquipmentMemoryUnitCapProviderMgmtPlaneVer                 SnmpAdminString,
    cfprApEquipmentMemoryUnitCapProviderModel                        SnmpAdminString,
    cfprApEquipmentMemoryUnitCapProviderPromCardType                 Gauge32,
    cfprApEquipmentMemoryUnitCapProviderRevision                     SnmpAdminString,
    cfprApEquipmentMemoryUnitCapProviderVendor                       SnmpAdminString
}

cfprApEquipmentMemoryUnitCapProviderInstanceId OBJECT-TYPE
    SYNTAX       CfprApManagedObjectId
    MAX-ACCESS   not-accessible
    STATUS       current
    DESCRIPTION
        "Instance identifier of the managed object."
    ::= { cfprApEquipmentMemoryUnitCapProviderEntry 1 }

cfprApEquipmentMemoryUnitCapProviderDn OBJECT-TYPE
    SYNTAX       CfprApManagedObjectDn
    MAX-ACCESS   read-only
    STATUS       current
    DESCRIPTION
        "Cisco Firepower equipment:MemoryUnitCapProvider:dn
        managed object property"
    ::= { cfprApEquipmentMemoryUnitCapProviderEntry 2 }

cfprApEquipmentMemoryUnitCapProviderRn OBJECT-TYPE
    SYNTAX       SnmpAdminString
    MAX-ACCESS   read-only
    STATUS       current
    DESCRIPTION
        "Cisco Firepower equipment:MemoryUnitCapProvider:rn
        managed object property"
    ::= { cfprApEquipmentMemoryUnitCapProviderEntry 3 }

cfprApEquipmentMemoryUnitCapProviderDeleted OBJECT-TYPE
    SYNTAX       TruthValue
    MAX-ACCESS   read-only
    STATUS       current
    DESCRIPTION
        "Cisco Firepower equipment:MemoryUnitCapProvider:deleted
        managed object property"
    ::= { cfprApEquipmentMemoryUnitCapProviderEntry 4 }

cfprApEquipmentMemoryUnitCapProviderDeprecated OBJECT-TYPE
    SYNTAX       TruthValue
    MAX-ACCESS   read-only
    STATUS       current
    DESCRIPTION
        "Cisco Firepower equipment:MemoryUnitCapProvider:deprecated
        managed object property"
    ::= { cfprApEquipmentMemoryUnitCapProviderEntry 5 }

cfprApEquipmentMemoryUnitCapProviderElementLoadFailures OBJECT-TYPE
    SYNTAX       Gauge32
    MAX-ACCESS   read-only
    STATUS       current
    DESCRIPTION
        "Cisco Firepower equipment:MemoryUnitCapProvider:elementLoadFailur
        es managed object property"
    ::= { cfprApEquipmentMemoryUnitCapProviderEntry 6 }

cfprApEquipmentMemoryUnitCapProviderElementsLoaded OBJECT-TYPE
    SYNTAX       Gauge32
    MAX-ACCESS   read-only
    STATUS       current
    DESCRIPTION
        "Cisco Firepower equipment:MemoryUnitCapProvider:elementsLoaded
        managed object property"
    ::= { cfprApEquipmentMemoryUnitCapProviderEntry 7 }

cfprApEquipmentMemoryUnitCapProviderGencount OBJECT-TYPE
    SYNTAX       Gauge32
    MAX-ACCESS   read-only
    STATUS       current
    DESCRIPTION
        "Cisco Firepower equipment:MemoryUnitCapProvider:gencount
        managed object property"
    ::= { cfprApEquipmentMemoryUnitCapProviderEntry 8 }

cfprApEquipmentMemoryUnitCapProviderLoadErrors OBJECT-TYPE
    SYNTAX       Gauge32
    MAX-ACCESS   read-only
    STATUS       current
    DESCRIPTION
        "Cisco Firepower equipment:MemoryUnitCapProvider:loadErrors
        managed object property"
    ::= { cfprApEquipmentMemoryUnitCapProviderEntry 9 }

cfprApEquipmentMemoryUnitCapProviderLoadWarnings OBJECT-TYPE
    SYNTAX       Gauge32
    MAX-ACCESS   read-only
    STATUS       current
    DESCRIPTION
        "Cisco Firepower equipment:MemoryUnitCapProvider:loadWarnings
        managed object property"
    ::= { cfprApEquipmentMemoryUnitCapProviderEntry 10 }

cfprApEquipmentMemoryUnitCapProviderMgmtPlaneVer OBJECT-TYPE
    SYNTAX       SnmpAdminString
    MAX-ACCESS   read-only
    STATUS       current
    DESCRIPTION
        "Cisco Firepower equipment:MemoryUnitCapProvider:mgmtPlaneVer
        managed object property"
    ::= { cfprApEquipmentMemoryUnitCapProviderEntry 11 }

cfprApEquipmentMemoryUnitCapProviderModel OBJECT-TYPE
    SYNTAX       SnmpAdminString
    MAX-ACCESS   read-only
    STATUS       current
    DESCRIPTION
        "Cisco Firepower equipment:MemoryUnitCapProvider:model
        managed object property"
    ::= { cfprApEquipmentMemoryUnitCapProviderEntry 12 }

cfprApEquipmentMemoryUnitCapProviderPromCardType OBJECT-TYPE
    SYNTAX       Gauge32
    MAX-ACCESS   read-only
    STATUS       current
    DESCRIPTION
        "Cisco Firepower equipment:MemoryUnitCapProvider:promCardType
        managed object property"
    ::= { cfprApEquipmentMemoryUnitCapProviderEntry 13 }

cfprApEquipmentMemoryUnitCapProviderRevision OBJECT-TYPE
    SYNTAX       SnmpAdminString
    MAX-ACCESS   read-only
    STATUS       current
    DESCRIPTION
        "Cisco Firepower equipment:MemoryUnitCapProvider:revision
        managed object property"
    ::= { cfprApEquipmentMemoryUnitCapProviderEntry 14 }

cfprApEquipmentMemoryUnitCapProviderVendor OBJECT-TYPE
    SYNTAX       SnmpAdminString
    MAX-ACCESS   read-only
    STATUS       current
    DESCRIPTION
        "Cisco Firepower equipment:MemoryUnitCapProvider:vendor
        managed object property"
    ::= { cfprApEquipmentMemoryUnitCapProviderEntry 15 }

cfprApEquipmentMemoryUnitDiscoveryModifierDefTable OBJECT-TYPE
    SYNTAX           SEQUENCE OF CfprApEquipmentMemoryUnitDiscoveryModifierDefEntry
    MAX-ACCESS       not-accessible
    STATUS           current
    DESCRIPTION
        "Cisco Firepower equipment:MemoryUnitDiscoveryModifierDef
        managed object table"
    ::= { cfprApEquipmentObjects 90 }

cfprApEquipmentMemoryUnitDiscoveryModifierDefEntry OBJECT-TYPE
    SYNTAX           CfprApEquipmentMemoryUnitDiscoveryModifierDefEntry
    MAX-ACCESS       not-accessible
    STATUS           current
    DESCRIPTION
        "Entry for the cfprApEquipmentMemoryUnitDiscoveryModifierDefTable table."
    INDEX { cfprApEquipmentMemoryUnitDiscoveryModifierDefInstanceId }
    ::= { cfprApEquipmentMemoryUnitDiscoveryModifierDefTable 1 }

CfprApEquipmentMemoryUnitDiscoveryModifierDefEntry ::= SEQUENCE {
    cfprApEquipmentMemoryUnitDiscoveryModifierDefInstanceId          CfprApManagedObjectId,
    cfprApEquipmentMemoryUnitDiscoveryModifierDefDn                  CfprApManagedObjectDn,
    cfprApEquipmentMemoryUnitDiscoveryModifierDefRn                  SnmpAdminString,
    cfprApEquipmentMemoryUnitDiscoveryModifierDefAction              CfprApEquipmentMemoryUnitDiscoveryModifierAction,
    cfprApEquipmentMemoryUnitDiscoveryModifierDefConstraintType      CfprApComputeMemoryUnitConstraintType,
    cfprApEquipmentMemoryUnitDiscoveryModifierDefDescr               SnmpAdminString,
    cfprApEquipmentMemoryUnitDiscoveryModifierDefIntId               SnmpAdminString,
    cfprApEquipmentMemoryUnitDiscoveryModifierDefName                SnmpAdminString,
    cfprApEquipmentMemoryUnitDiscoveryModifierDefPolicyLevel         Gauge32,
    cfprApEquipmentMemoryUnitDiscoveryModifierDefPolicyOwner         CfprApPolicyPolicyOwner
}

cfprApEquipmentMemoryUnitDiscoveryModifierDefInstanceId OBJECT-TYPE
    SYNTAX       CfprApManagedObjectId
    MAX-ACCESS   not-accessible
    STATUS       current
    DESCRIPTION
        "Instance identifier of the managed object."
    ::= { cfprApEquipmentMemoryUnitDiscoveryModifierDefEntry 1 }

cfprApEquipmentMemoryUnitDiscoveryModifierDefDn OBJECT-TYPE
    SYNTAX       CfprApManagedObjectDn
    MAX-ACCESS   read-only
    STATUS       current
    DESCRIPTION
        "Cisco Firepower equipment:MemoryUnitDiscoveryModifierDef:dn
        managed object property"
    ::= { cfprApEquipmentMemoryUnitDiscoveryModifierDefEntry 2 }

cfprApEquipmentMemoryUnitDiscoveryModifierDefRn OBJECT-TYPE
    SYNTAX       SnmpAdminString
    MAX-ACCESS   read-only
    STATUS       current
    DESCRIPTION
        "Cisco Firepower equipment:MemoryUnitDiscoveryModifierDef:rn
        managed object property"
    ::= { cfprApEquipmentMemoryUnitDiscoveryModifierDefEntry 3 }

cfprApEquipmentMemoryUnitDiscoveryModifierDefAction OBJECT-TYPE
    SYNTAX       CfprApEquipmentMemoryUnitDiscoveryModifierAction
    MAX-ACCESS   read-only
    STATUS       current
    DESCRIPTION
        "Cisco Firepower equipment:MemoryUnitDiscoveryModifierDef:action
        managed object property"
    ::= { cfprApEquipmentMemoryUnitDiscoveryModifierDefEntry 4 }

cfprApEquipmentMemoryUnitDiscoveryModifierDefConstraintType OBJECT-TYPE
    SYNTAX       CfprApComputeMemoryUnitConstraintType
    MAX-ACCESS   read-only
    STATUS       current
    DESCRIPTION
        "Cisco Firepower equipment:MemoryUnitDiscoveryModifierDef:constrai
        ntType managed object property"
    ::= { cfprApEquipmentMemoryUnitDiscoveryModifierDefEntry 5 }

cfprApEquipmentMemoryUnitDiscoveryModifierDefDescr OBJECT-TYPE
    SYNTAX       SnmpAdminString
    MAX-ACCESS   read-only
    STATUS       current
    DESCRIPTION
        "Cisco Firepower equipment:MemoryUnitDiscoveryModifierDef:descr
        managed object property"
    ::= { cfprApEquipmentMemoryUnitDiscoveryModifierDefEntry 6 }

cfprApEquipmentMemoryUnitDiscoveryModifierDefIntId OBJECT-TYPE
    SYNTAX       SnmpAdminString
    MAX-ACCESS   read-only
    STATUS       current
    DESCRIPTION
        "Cisco Firepower equipment:MemoryUnitDiscoveryModifierDef:intId
        managed object property"
    ::= { cfprApEquipmentMemoryUnitDiscoveryModifierDefEntry 7 }

cfprApEquipmentMemoryUnitDiscoveryModifierDefName OBJECT-TYPE
    SYNTAX       SnmpAdminString
    MAX-ACCESS   read-only
    STATUS       current
    DESCRIPTION
        "Cisco Firepower equipment:MemoryUnitDiscoveryModifierDef:name
        managed object property"
    ::= { cfprApEquipmentMemoryUnitDiscoveryModifierDefEntry 8 }

cfprApEquipmentMemoryUnitDiscoveryModifierDefPolicyLevel OBJECT-TYPE
    SYNTAX       Gauge32
    MAX-ACCESS   read-only
    STATUS       current
    DESCRIPTION
        "Cisco Firepower equipment:MemoryUnitDiscoveryModifierDef:policyLe
        vel managed object property"
    ::= { cfprApEquipmentMemoryUnitDiscoveryModifierDefEntry 9 }

cfprApEquipmentMemoryUnitDiscoveryModifierDefPolicyOwner OBJECT-TYPE
    SYNTAX       CfprApPolicyPolicyOwner
    MAX-ACCESS   read-only
    STATUS       current
    DESCRIPTION
        "Cisco Firepower equipment:MemoryUnitDiscoveryModifierDef:policyOw
        ner managed object property"
    ::= { cfprApEquipmentMemoryUnitDiscoveryModifierDefEntry 10 }

cfprApEquipmentMgmtCapProviderTable OBJECT-TYPE
    SYNTAX           SEQUENCE OF CfprApEquipmentMgmtCapProviderEntry
    MAX-ACCESS       not-accessible
    STATUS           current
    DESCRIPTION
        "Cisco Firepower equipment:MgmtCapProvider managed object table"
    ::= { cfprApEquipmentObjects 91 }

cfprApEquipmentMgmtCapProviderEntry OBJECT-TYPE
    SYNTAX           CfprApEquipmentMgmtCapProviderEntry
    MAX-ACCESS       not-accessible
    STATUS           current
    DESCRIPTION
        "Entry for the cfprApEquipmentMgmtCapProviderTable table."
    INDEX { cfprApEquipmentMgmtCapProviderInstanceId }
    ::= { cfprApEquipmentMgmtCapProviderTable 1 }

CfprApEquipmentMgmtCapProviderEntry ::= SEQUENCE {
    cfprApEquipmentMgmtCapProviderInstanceId                         CfprApManagedObjectId,
    cfprApEquipmentMgmtCapProviderDn                                 CfprApManagedObjectDn,
    cfprApEquipmentMgmtCapProviderRn                                 SnmpAdminString,
    cfprApEquipmentMgmtCapProviderDeleted                            TruthValue,
    cfprApEquipmentMgmtCapProviderDeprecated                         TruthValue,
    cfprApEquipmentMgmtCapProviderElementLoadFailures                Gauge32,
    cfprApEquipmentMgmtCapProviderElementsLoaded                     Gauge32,
    cfprApEquipmentMgmtCapProviderGencount                           Gauge32,
    cfprApEquipmentMgmtCapProviderLoadErrors                         Gauge32,
    cfprApEquipmentMgmtCapProviderLoadWarnings                       Gauge32,
    cfprApEquipmentMgmtCapProviderMgmtPlaneVer                       SnmpAdminString,
    cfprApEquipmentMgmtCapProviderModel                              SnmpAdminString,
    cfprApEquipmentMgmtCapProviderPromCardType                       Gauge32,
    cfprApEquipmentMgmtCapProviderRevision                           SnmpAdminString,
    cfprApEquipmentMgmtCapProviderVendor                             SnmpAdminString
}

cfprApEquipmentMgmtCapProviderInstanceId OBJECT-TYPE
    SYNTAX       CfprApManagedObjectId
    MAX-ACCESS   not-accessible
    STATUS       current
    DESCRIPTION
        "Instance identifier of the managed object."
    ::= { cfprApEquipmentMgmtCapProviderEntry 1 }

cfprApEquipmentMgmtCapProviderDn OBJECT-TYPE
    SYNTAX       CfprApManagedObjectDn
    MAX-ACCESS   read-only
    STATUS       current
    DESCRIPTION
        "Cisco Firepower equipment:MgmtCapProvider:dn managed
        object property"
    ::= { cfprApEquipmentMgmtCapProviderEntry 2 }

cfprApEquipmentMgmtCapProviderRn OBJECT-TYPE
    SYNTAX       SnmpAdminString
    MAX-ACCESS   read-only
    STATUS       current
    DESCRIPTION
        "Cisco Firepower equipment:MgmtCapProvider:rn managed
        object property"
    ::= { cfprApEquipmentMgmtCapProviderEntry 3 }

cfprApEquipmentMgmtCapProviderDeleted OBJECT-TYPE
    SYNTAX       TruthValue
    MAX-ACCESS   read-only
    STATUS       current
    DESCRIPTION
        "Cisco Firepower equipment:MgmtCapProvider:deleted
        managed object property"
    ::= { cfprApEquipmentMgmtCapProviderEntry 4 }

cfprApEquipmentMgmtCapProviderDeprecated OBJECT-TYPE
    SYNTAX       TruthValue
    MAX-ACCESS   read-only
    STATUS       current
    DESCRIPTION
        "Cisco Firepower equipment:MgmtCapProvider:deprecated
        managed object property"
    ::= { cfprApEquipmentMgmtCapProviderEntry 5 }

cfprApEquipmentMgmtCapProviderElementLoadFailures OBJECT-TYPE
    SYNTAX       Gauge32
    MAX-ACCESS   read-only
    STATUS       current
    DESCRIPTION
        "Cisco Firepower equipment:MgmtCapProvider:elementLoadFailures
        managed object property"
    ::= { cfprApEquipmentMgmtCapProviderEntry 6 }

cfprApEquipmentMgmtCapProviderElementsLoaded OBJECT-TYPE
    SYNTAX       Gauge32
    MAX-ACCESS   read-only
    STATUS       current
    DESCRIPTION
        "Cisco Firepower equipment:MgmtCapProvider:elementsLoaded
        managed object property"
    ::= { cfprApEquipmentMgmtCapProviderEntry 7 }

cfprApEquipmentMgmtCapProviderGencount OBJECT-TYPE
    SYNTAX       Gauge32
    MAX-ACCESS   read-only
    STATUS       current
    DESCRIPTION
        "Cisco Firepower equipment:MgmtCapProvider:gencount
        managed object property"
    ::= { cfprApEquipmentMgmtCapProviderEntry 8 }

cfprApEquipmentMgmtCapProviderLoadErrors OBJECT-TYPE
    SYNTAX       Gauge32
    MAX-ACCESS   read-only
    STATUS       current
    DESCRIPTION
        "Cisco Firepower equipment:MgmtCapProvider:loadErrors
        managed object property"
    ::= { cfprApEquipmentMgmtCapProviderEntry 9 }

cfprApEquipmentMgmtCapProviderLoadWarnings OBJECT-TYPE
    SYNTAX       Gauge32
    MAX-ACCESS   read-only
    STATUS       current
    DESCRIPTION
        "Cisco Firepower equipment:MgmtCapProvider:loadWarnings
        managed object property"
    ::= { cfprApEquipmentMgmtCapProviderEntry 10 }

cfprApEquipmentMgmtCapProviderMgmtPlaneVer OBJECT-TYPE
    SYNTAX       SnmpAdminString
    MAX-ACCESS   read-only
    STATUS       current
    DESCRIPTION
        "Cisco Firepower equipment:MgmtCapProvider:mgmtPlaneVer
        managed object property"
    ::= { cfprApEquipmentMgmtCapProviderEntry 11 }

cfprApEquipmentMgmtCapProviderModel OBJECT-TYPE
    SYNTAX       SnmpAdminString
    MAX-ACCESS   read-only
    STATUS       current
    DESCRIPTION
        "Cisco Firepower equipment:MgmtCapProvider:model
        managed object property"
    ::= { cfprApEquipmentMgmtCapProviderEntry 12 }

cfprApEquipmentMgmtCapProviderPromCardType OBJECT-TYPE
    SYNTAX       Gauge32
    MAX-ACCESS   read-only
    STATUS       current
    DESCRIPTION
        "Cisco Firepower equipment:MgmtCapProvider:promCardType
        managed object property"
    ::= { cfprApEquipmentMgmtCapProviderEntry 13 }

cfprApEquipmentMgmtCapProviderRevision OBJECT-TYPE
    SYNTAX       SnmpAdminString
    MAX-ACCESS   read-only
    STATUS       current
    DESCRIPTION
        "Cisco Firepower equipment:MgmtCapProvider:revision
        managed object property"
    ::= { cfprApEquipmentMgmtCapProviderEntry 14 }

cfprApEquipmentMgmtCapProviderVendor OBJECT-TYPE
    SYNTAX       SnmpAdminString
    MAX-ACCESS   read-only
    STATUS       current
    DESCRIPTION
        "Cisco Firepower equipment:MgmtCapProvider:vendor
        managed object property"
    ::= { cfprApEquipmentMgmtCapProviderEntry 15 }

cfprApEquipmentMgmtExtCapProviderTable OBJECT-TYPE
    SYNTAX           SEQUENCE OF CfprApEquipmentMgmtExtCapProviderEntry
    MAX-ACCESS       not-accessible
    STATUS           current
    DESCRIPTION
        "Cisco Firepower equipment:MgmtExtCapProvider managed
        object table"
    ::= { cfprApEquipmentObjects 92 }

cfprApEquipmentMgmtExtCapProviderEntry OBJECT-TYPE
    SYNTAX           CfprApEquipmentMgmtExtCapProviderEntry
    MAX-ACCESS       not-accessible
    STATUS           current
    DESCRIPTION
        "Entry for the cfprApEquipmentMgmtExtCapProviderTable table."
    INDEX { cfprApEquipmentMgmtExtCapProviderInstanceId }
    ::= { cfprApEquipmentMgmtExtCapProviderTable 1 }

CfprApEquipmentMgmtExtCapProviderEntry ::= SEQUENCE {
    cfprApEquipmentMgmtExtCapProviderInstanceId                      CfprApManagedObjectId,
    cfprApEquipmentMgmtExtCapProviderDn                              CfprApManagedObjectDn,
    cfprApEquipmentMgmtExtCapProviderRn                              SnmpAdminString,
    cfprApEquipmentMgmtExtCapProviderDeleted                         TruthValue,
    cfprApEquipmentMgmtExtCapProviderDeprecated                      TruthValue,
    cfprApEquipmentMgmtExtCapProviderElementLoadFailures             Gauge32,
    cfprApEquipmentMgmtExtCapProviderElementsLoaded                  Gauge32,
    cfprApEquipmentMgmtExtCapProviderGencount                        Gauge32,
    cfprApEquipmentMgmtExtCapProviderLoadErrors                      Gauge32,
    cfprApEquipmentMgmtExtCapProviderLoadWarnings                    Gauge32,
    cfprApEquipmentMgmtExtCapProviderMgmtPlaneVer                    SnmpAdminString,
    cfprApEquipmentMgmtExtCapProviderModel                           SnmpAdminString,
    cfprApEquipmentMgmtExtCapProviderPromCardType                    Gauge32,
    cfprApEquipmentMgmtExtCapProviderRevision                        SnmpAdminString,
    cfprApEquipmentMgmtExtCapProviderVendor                          SnmpAdminString
}

cfprApEquipmentMgmtExtCapProviderInstanceId OBJECT-TYPE
    SYNTAX       CfprApManagedObjectId
    MAX-ACCESS   not-accessible
    STATUS       current
    DESCRIPTION
        "Instance identifier of the managed object."
    ::= { cfprApEquipmentMgmtExtCapProviderEntry 1 }

cfprApEquipmentMgmtExtCapProviderDn OBJECT-TYPE
    SYNTAX       CfprApManagedObjectDn
    MAX-ACCESS   read-only
    STATUS       current
    DESCRIPTION
        "Cisco Firepower equipment:MgmtExtCapProvider:dn
        managed object property"
    ::= { cfprApEquipmentMgmtExtCapProviderEntry 2 }

cfprApEquipmentMgmtExtCapProviderRn OBJECT-TYPE
    SYNTAX       SnmpAdminString
    MAX-ACCESS   read-only
    STATUS       current
    DESCRIPTION
        "Cisco Firepower equipment:MgmtExtCapProvider:rn
        managed object property"
    ::= { cfprApEquipmentMgmtExtCapProviderEntry 3 }

cfprApEquipmentMgmtExtCapProviderDeleted OBJECT-TYPE
    SYNTAX       TruthValue
    MAX-ACCESS   read-only
    STATUS       current
    DESCRIPTION
        "Cisco Firepower equipment:MgmtExtCapProvider:deleted
        managed object property"
    ::= { cfprApEquipmentMgmtExtCapProviderEntry 4 }

cfprApEquipmentMgmtExtCapProviderDeprecated OBJECT-TYPE
    SYNTAX       TruthValue
    MAX-ACCESS   read-only
    STATUS       current
    DESCRIPTION
        "Cisco Firepower equipment:MgmtExtCapProvider:deprecated
        managed object property"
    ::= { cfprApEquipmentMgmtExtCapProviderEntry 5 }

cfprApEquipmentMgmtExtCapProviderElementLoadFailures OBJECT-TYPE
    SYNTAX       Gauge32
    MAX-ACCESS   read-only
    STATUS       current
    DESCRIPTION
        "Cisco Firepower equipment:MgmtExtCapProvider:elementLoadFailures
        managed object property"
    ::= { cfprApEquipmentMgmtExtCapProviderEntry 6 }

cfprApEquipmentMgmtExtCapProviderElementsLoaded OBJECT-TYPE
    SYNTAX       Gauge32
    MAX-ACCESS   read-only
    STATUS       current
    DESCRIPTION
        "Cisco Firepower equipment:MgmtExtCapProvider:elementsLoaded
        managed object property"
    ::= { cfprApEquipmentMgmtExtCapProviderEntry 7 }

cfprApEquipmentMgmtExtCapProviderGencount OBJECT-TYPE
    SYNTAX       Gauge32
    MAX-ACCESS   read-only
    STATUS       current
    DESCRIPTION
        "Cisco Firepower equipment:MgmtExtCapProvider:gencount
        managed object property"
    ::= { cfprApEquipmentMgmtExtCapProviderEntry 8 }

cfprApEquipmentMgmtExtCapProviderLoadErrors OBJECT-TYPE
    SYNTAX       Gauge32
    MAX-ACCESS   read-only
    STATUS       current
    DESCRIPTION
        "Cisco Firepower equipment:MgmtExtCapProvider:loadErrors
        managed object property"
    ::= { cfprApEquipmentMgmtExtCapProviderEntry 9 }

cfprApEquipmentMgmtExtCapProviderLoadWarnings OBJECT-TYPE
    SYNTAX       Gauge32
    MAX-ACCESS   read-only
    STATUS       current
    DESCRIPTION
        "Cisco Firepower equipment:MgmtExtCapProvider:loadWarnings
        managed object property"
    ::= { cfprApEquipmentMgmtExtCapProviderEntry 10 }

cfprApEquipmentMgmtExtCapProviderMgmtPlaneVer OBJECT-TYPE
    SYNTAX       SnmpAdminString
    MAX-ACCESS   read-only
    STATUS       current
    DESCRIPTION
        "Cisco Firepower equipment:MgmtExtCapProvider:mgmtPlaneVer
        managed object property"
    ::= { cfprApEquipmentMgmtExtCapProviderEntry 11 }

cfprApEquipmentMgmtExtCapProviderModel OBJECT-TYPE
    SYNTAX       SnmpAdminString
    MAX-ACCESS   read-only
    STATUS       current
    DESCRIPTION
        "Cisco Firepower equipment:MgmtExtCapProvider:model
        managed object property"
    ::= { cfprApEquipmentMgmtExtCapProviderEntry 12 }

cfprApEquipmentMgmtExtCapProviderPromCardType OBJECT-TYPE
    SYNTAX       Gauge32
    MAX-ACCESS   read-only
    STATUS       current
    DESCRIPTION
        "Cisco Firepower equipment:MgmtExtCapProvider:promCardType
        managed object property"
    ::= { cfprApEquipmentMgmtExtCapProviderEntry 13 }

cfprApEquipmentMgmtExtCapProviderRevision OBJECT-TYPE
    SYNTAX       SnmpAdminString
    MAX-ACCESS   read-only
    STATUS       current
    DESCRIPTION
        "Cisco Firepower equipment:MgmtExtCapProvider:revision
        managed object property"
    ::= { cfprApEquipmentMgmtExtCapProviderEntry 14 }

cfprApEquipmentMgmtExtCapProviderVendor OBJECT-TYPE
    SYNTAX       SnmpAdminString
    MAX-ACCESS   read-only
    STATUS       current
    DESCRIPTION
        "Cisco Firepower equipment:MgmtExtCapProvider:vendor
        managed object property"
    ::= { cfprApEquipmentMgmtExtCapProviderEntry 15 }

cfprApEquipmentNetworkElementFanStatsTable OBJECT-TYPE
    SYNTAX           SEQUENCE OF CfprApEquipmentNetworkElementFanStatsEntry
    MAX-ACCESS       not-accessible
    STATUS           current
    DESCRIPTION
        "Cisco Firepower equipment:NetworkElementFanStats
        managed object table"
    ::= { cfprApEquipmentObjects 93 }

cfprApEquipmentNetworkElementFanStatsEntry OBJECT-TYPE
    SYNTAX           CfprApEquipmentNetworkElementFanStatsEntry
    MAX-ACCESS       not-accessible
    STATUS           current
    DESCRIPTION
        "Entry for the cfprApEquipmentNetworkElementFanStatsTable table."
    INDEX { cfprApEquipmentNetworkElementFanStatsInstanceId }
    ::= { cfprApEquipmentNetworkElementFanStatsTable 1 }

CfprApEquipmentNetworkElementFanStatsEntry ::= SEQUENCE {
    cfprApEquipmentNetworkElementFanStatsInstanceId                  CfprApManagedObjectId,
    cfprApEquipmentNetworkElementFanStatsDn                          CfprApManagedObjectDn,
    cfprApEquipmentNetworkElementFanStatsRn                          SnmpAdminString,
    cfprApEquipmentNetworkElementFanStatsAirflowDirection            CfprApEquipmentAirflowDirection,
    cfprApEquipmentNetworkElementFanStatsDrivePercentage             Gauge32,
    cfprApEquipmentNetworkElementFanStatsDrivePercentageAvg          Gauge32,
    cfprApEquipmentNetworkElementFanStatsDrivePercentageMax          Gauge32,
    cfprApEquipmentNetworkElementFanStatsDrivePercentageMin          Gauge32,
    cfprApEquipmentNetworkElementFanStatsIntervals                   Gauge32,
    cfprApEquipmentNetworkElementFanStatsSpeed                       Gauge32,
    cfprApEquipmentNetworkElementFanStatsSpeedAvg                    Gauge32,
    cfprApEquipmentNetworkElementFanStatsSpeedMax                    Gauge32,
    cfprApEquipmentNetworkElementFanStatsSpeedMin                    Gauge32,
    cfprApEquipmentNetworkElementFanStatsSuspect                     TruthValue,
    cfprApEquipmentNetworkElementFanStatsThresholded                 CfprApEquipmentNetworkElementFanStatsThresholded,
    cfprApEquipmentNetworkElementFanStatsTimeCollected               DateAndTime,
    cfprApEquipmentNetworkElementFanStatsUpdate                      Gauge32
}

cfprApEquipmentNetworkElementFanStatsInstanceId OBJECT-TYPE
    SYNTAX       CfprApManagedObjectId
    MAX-ACCESS   not-accessible
    STATUS       current
    DESCRIPTION
        "Instance identifier of the managed object."
    ::= { cfprApEquipmentNetworkElementFanStatsEntry 1 }

cfprApEquipmentNetworkElementFanStatsDn OBJECT-TYPE
    SYNTAX       CfprApManagedObjectDn
    MAX-ACCESS   read-only
    STATUS       current
    DESCRIPTION
        "Cisco Firepower equipment:NetworkElementFanStats:dn
        managed object property"
    ::= { cfprApEquipmentNetworkElementFanStatsEntry 2 }

cfprApEquipmentNetworkElementFanStatsRn OBJECT-TYPE
    SYNTAX       SnmpAdminString
    MAX-ACCESS   read-only
    STATUS       current
    DESCRIPTION
        "Cisco Firepower equipment:NetworkElementFanStats:rn
        managed object property"
    ::= { cfprApEquipmentNetworkElementFanStatsEntry 3 }

cfprApEquipmentNetworkElementFanStatsAirflowDirection OBJECT-TYPE
    SYNTAX       CfprApEquipmentAirflowDirection
    MAX-ACCESS   read-only
    STATUS       current
    DESCRIPTION
        "Cisco Firepower equipment:NetworkElementFanStats:airflowDirection
         managed object property"
    ::= { cfprApEquipmentNetworkElementFanStatsEntry 4 }

cfprApEquipmentNetworkElementFanStatsDrivePercentage OBJECT-TYPE
    SYNTAX       Gauge32
    MAX-ACCESS   read-only
    STATUS       current
    DESCRIPTION
        "Cisco Firepower equipment:NetworkElementFanStats:drivePercentage
        managed object property"
    ::= { cfprApEquipmentNetworkElementFanStatsEntry 5 }

cfprApEquipmentNetworkElementFanStatsDrivePercentageAvg OBJECT-TYPE
    SYNTAX       Gauge32
    MAX-ACCESS   read-only
    STATUS       current
    DESCRIPTION
        "Cisco Firepower equipment:NetworkElementFanStats:drivePercentageA
        vg managed object property"
    ::= { cfprApEquipmentNetworkElementFanStatsEntry 6 }

cfprApEquipmentNetworkElementFanStatsDrivePercentageMax OBJECT-TYPE
    SYNTAX       Gauge32
    MAX-ACCESS   read-only
    STATUS       current
    DESCRIPTION
        "Cisco Firepower equipment:NetworkElementFanStats:drivePercentageM
        ax managed object property"
    ::= { cfprApEquipmentNetworkElementFanStatsEntry 7 }

cfprApEquipmentNetworkElementFanStatsDrivePercentageMin OBJECT-TYPE
    SYNTAX       Gauge32
    MAX-ACCESS   read-only
    STATUS       current
    DESCRIPTION
        "Cisco Firepower equipment:NetworkElementFanStats:drivePercentageM
        in managed object property"
    ::= { cfprApEquipmentNetworkElementFanStatsEntry 8 }

cfprApEquipmentNetworkElementFanStatsIntervals OBJECT-TYPE
    SYNTAX       Gauge32
    MAX-ACCESS   read-only
    STATUS       current
    DESCRIPTION
        "Cisco Firepower equipment:NetworkElementFanStats:intervals
        managed object property"
    ::= { cfprApEquipmentNetworkElementFanStatsEntry 9 }

cfprApEquipmentNetworkElementFanStatsSpeed OBJECT-TYPE
    SYNTAX       Gauge32
    MAX-ACCESS   read-only
    STATUS       current
    DESCRIPTION
        "Cisco Firepower equipment:NetworkElementFanStats:speed
        managed object property"
    ::= { cfprApEquipmentNetworkElementFanStatsEntry 10 }

cfprApEquipmentNetworkElementFanStatsSpeedAvg OBJECT-TYPE
    SYNTAX       Gauge32
    MAX-ACCESS   read-only
    STATUS       current
    DESCRIPTION
        "Cisco Firepower equipment:NetworkElementFanStats:speedAvg
        managed object property"
    ::= { cfprApEquipmentNetworkElementFanStatsEntry 11 }

cfprApEquipmentNetworkElementFanStatsSpeedMax OBJECT-TYPE
    SYNTAX       Gauge32
    MAX-ACCESS   read-only
    STATUS       current
    DESCRIPTION
        "Cisco Firepower equipment:NetworkElementFanStats:speedMax
        managed object property"
    ::= { cfprApEquipmentNetworkElementFanStatsEntry 12 }

cfprApEquipmentNetworkElementFanStatsSpeedMin OBJECT-TYPE
    SYNTAX       Gauge32
    MAX-ACCESS   read-only
    STATUS       current
    DESCRIPTION
        "Cisco Firepower equipment:NetworkElementFanStats:speedMin
        managed object property"
    ::= { cfprApEquipmentNetworkElementFanStatsEntry 13 }

cfprApEquipmentNetworkElementFanStatsSuspect OBJECT-TYPE
    SYNTAX       TruthValue
    MAX-ACCESS   read-only
    STATUS       current
    DESCRIPTION
        "Cisco Firepower equipment:NetworkElementFanStats:suspect
        managed object property"
    ::= { cfprApEquipmentNetworkElementFanStatsEntry 14 }

cfprApEquipmentNetworkElementFanStatsThresholded OBJECT-TYPE
    SYNTAX       CfprApEquipmentNetworkElementFanStatsThresholded
    MAX-ACCESS   read-only
    STATUS       current
    DESCRIPTION
        "Cisco Firepower equipment:NetworkElementFanStats:thresholded
        managed object property"
    ::= { cfprApEquipmentNetworkElementFanStatsEntry 15 }

cfprApEquipmentNetworkElementFanStatsTimeCollected OBJECT-TYPE
    SYNTAX       DateAndTime
    MAX-ACCESS   read-only
    STATUS       current
    DESCRIPTION
        "Cisco Firepower equipment:NetworkElementFanStats:timeCollected
        managed object property"
    ::= { cfprApEquipmentNetworkElementFanStatsEntry 16 }

cfprApEquipmentNetworkElementFanStatsUpdate OBJECT-TYPE
    SYNTAX       Gauge32
    MAX-ACCESS   read-only
    STATUS       current
    DESCRIPTION
        "Cisco Firepower equipment:NetworkElementFanStats:update
        managed object property"
    ::= { cfprApEquipmentNetworkElementFanStatsEntry 17 }

cfprApEquipmentNetworkElementFanStatsHistTable OBJECT-TYPE
    SYNTAX           SEQUENCE OF CfprApEquipmentNetworkElementFanStatsHistEntry
    MAX-ACCESS       not-accessible
    STATUS           current
    DESCRIPTION
        "Cisco Firepower equipment:NetworkElementFanStatsHist
        managed object table"
    ::= { cfprApEquipmentObjects 94 }

cfprApEquipmentNetworkElementFanStatsHistEntry OBJECT-TYPE
    SYNTAX           CfprApEquipmentNetworkElementFanStatsHistEntry
    MAX-ACCESS       not-accessible
    STATUS           current
    DESCRIPTION
        "Entry for the cfprApEquipmentNetworkElementFanStatsHistTable table."
    INDEX { cfprApEquipmentNetworkElementFanStatsHistInstanceId }
    ::= { cfprApEquipmentNetworkElementFanStatsHistTable 1 }

CfprApEquipmentNetworkElementFanStatsHistEntry ::= SEQUENCE {
    cfprApEquipmentNetworkElementFanStatsHistInstanceId              CfprApManagedObjectId,
    cfprApEquipmentNetworkElementFanStatsHistDn                      CfprApManagedObjectDn,
    cfprApEquipmentNetworkElementFanStatsHistRn                      SnmpAdminString,
    cfprApEquipmentNetworkElementFanStatsHistDrivePercentage         Gauge32,
    cfprApEquipmentNetworkElementFanStatsHistDrivePercentageAvg      Gauge32,
    cfprApEquipmentNetworkElementFanStatsHistDrivePercentageMax      Gauge32,
    cfprApEquipmentNetworkElementFanStatsHistDrivePercentageMin      Gauge32,
    cfprApEquipmentNetworkElementFanStatsHistId                      Unsigned64,
    cfprApEquipmentNetworkElementFanStatsHistMostRecent              TruthValue,
    cfprApEquipmentNetworkElementFanStatsHistSpeed                   Gauge32,
    cfprApEquipmentNetworkElementFanStatsHistSpeedAvg                Gauge32,
    cfprApEquipmentNetworkElementFanStatsHistSpeedMax                Gauge32,
    cfprApEquipmentNetworkElementFanStatsHistSpeedMin                Gauge32,
    cfprApEquipmentNetworkElementFanStatsHistSuspect                 TruthValue,
    cfprApEquipmentNetworkElementFanStatsHistThresholded             CfprApEquipmentNetworkElementFanStatsHistThresholded,
    cfprApEquipmentNetworkElementFanStatsHistTimeCollected           DateAndTime
}

cfprApEquipmentNetworkElementFanStatsHistInstanceId OBJECT-TYPE
    SYNTAX       CfprApManagedObjectId
    MAX-ACCESS   not-accessible
    STATUS       current
    DESCRIPTION
        "Instance identifier of the managed object."
    ::= { cfprApEquipmentNetworkElementFanStatsHistEntry 1 }

cfprApEquipmentNetworkElementFanStatsHistDn OBJECT-TYPE
    SYNTAX       CfprApManagedObjectDn
    MAX-ACCESS   read-only
    STATUS       current
    DESCRIPTION
        "Cisco Firepower equipment:NetworkElementFanStatsHist:dn
        managed object property"
    ::= { cfprApEquipmentNetworkElementFanStatsHistEntry 2 }

cfprApEquipmentNetworkElementFanStatsHistRn OBJECT-TYPE
    SYNTAX       SnmpAdminString
    MAX-ACCESS   read-only
    STATUS       current
    DESCRIPTION
        "Cisco Firepower equipment:NetworkElementFanStatsHist:rn
        managed object property"
    ::= { cfprApEquipmentNetworkElementFanStatsHistEntry 3 }

cfprApEquipmentNetworkElementFanStatsHistDrivePercentage OBJECT-TYPE
    SYNTAX       Gauge32
    MAX-ACCESS   read-only
    STATUS       current
    DESCRIPTION
        "Cisco Firepower equipment:NetworkElementFanStatsHist:drivePercent
        age managed object property"
    ::= { cfprApEquipmentNetworkElementFanStatsHistEntry 4 }

cfprApEquipmentNetworkElementFanStatsHistDrivePercentageAvg OBJECT-TYPE
    SYNTAX       Gauge32
    MAX-ACCESS   read-only
    STATUS       current
    DESCRIPTION
        "Cisco Firepower equipment:NetworkElementFanStatsHist:drivePercent
        ageAvg managed object property"
    ::= { cfprApEquipmentNetworkElementFanStatsHistEntry 5 }

cfprApEquipmentNetworkElementFanStatsHistDrivePercentageMax OBJECT-TYPE
    SYNTAX       Gauge32
    MAX-ACCESS   read-only
    STATUS       current
    DESCRIPTION
        "Cisco Firepower equipment:NetworkElementFanStatsHist:drivePercent
        ageMax managed object property"
    ::= { cfprApEquipmentNetworkElementFanStatsHistEntry 6 }

cfprApEquipmentNetworkElementFanStatsHistDrivePercentageMin OBJECT-TYPE
    SYNTAX       Gauge32
    MAX-ACCESS   read-only
    STATUS       current
    DESCRIPTION
        "Cisco Firepower equipment:NetworkElementFanStatsHist:drivePercent
        ageMin managed object property"
    ::= { cfprApEquipmentNetworkElementFanStatsHistEntry 7 }

cfprApEquipmentNetworkElementFanStatsHistId OBJECT-TYPE
    SYNTAX       Unsigned64
    MAX-ACCESS   read-only
    STATUS       current
    DESCRIPTION
        "Cisco Firepower equipment:NetworkElementFanStatsHist:id
        managed object property"
    ::= { cfprApEquipmentNetworkElementFanStatsHistEntry 8 }

cfprApEquipmentNetworkElementFanStatsHistMostRecent OBJECT-TYPE
    SYNTAX       TruthValue
    MAX-ACCESS   read-only
    STATUS       current
    DESCRIPTION
        "Cisco Firepower equipment:NetworkElementFanStatsHist:mostRecent
        managed object property"
    ::= { cfprApEquipmentNetworkElementFanStatsHistEntry 9 }

cfprApEquipmentNetworkElementFanStatsHistSpeed OBJECT-TYPE
    SYNTAX       Gauge32
    MAX-ACCESS   read-only
    STATUS       current
    DESCRIPTION
        "Cisco Firepower equipment:NetworkElementFanStatsHist:speed
        managed object property"
    ::= { cfprApEquipmentNetworkElementFanStatsHistEntry 10 }

cfprApEquipmentNetworkElementFanStatsHistSpeedAvg OBJECT-TYPE
    SYNTAX       Gauge32
    MAX-ACCESS   read-only
    STATUS       current
    DESCRIPTION
        "Cisco Firepower equipment:NetworkElementFanStatsHist:speedAvg
        managed object property"
    ::= { cfprApEquipmentNetworkElementFanStatsHistEntry 11 }

cfprApEquipmentNetworkElementFanStatsHistSpeedMax OBJECT-TYPE
    SYNTAX       Gauge32
    MAX-ACCESS   read-only
    STATUS       current
    DESCRIPTION
        "Cisco Firepower equipment:NetworkElementFanStatsHist:speedMax
        managed object property"
    ::= { cfprApEquipmentNetworkElementFanStatsHistEntry 12 }

cfprApEquipmentNetworkElementFanStatsHistSpeedMin OBJECT-TYPE
    SYNTAX       Gauge32
    MAX-ACCESS   read-only
    STATUS       current
    DESCRIPTION
        "Cisco Firepower equipment:NetworkElementFanStatsHist:speedMin
        managed object property"
    ::= { cfprApEquipmentNetworkElementFanStatsHistEntry 13 }

cfprApEquipmentNetworkElementFanStatsHistSuspect OBJECT-TYPE
    SYNTAX       TruthValue
    MAX-ACCESS   read-only
    STATUS       current
    DESCRIPTION
        "Cisco Firepower equipment:NetworkElementFanStatsHist:suspect
        managed object property"
    ::= { cfprApEquipmentNetworkElementFanStatsHistEntry 14 }

cfprApEquipmentNetworkElementFanStatsHistThresholded OBJECT-TYPE
    SYNTAX       CfprApEquipmentNetworkElementFanStatsHistThresholded
    MAX-ACCESS   read-only
    STATUS       current
    DESCRIPTION
        "Cisco Firepower equipment:NetworkElementFanStatsHist:thresholded
        managed object property"
    ::= { cfprApEquipmentNetworkElementFanStatsHistEntry 15 }

cfprApEquipmentNetworkElementFanStatsHistTimeCollected OBJECT-TYPE
    SYNTAX       DateAndTime
    MAX-ACCESS   read-only
    STATUS       current
    DESCRIPTION
        "Cisco Firepower equipment:NetworkElementFanStatsHist:timeCollecte
        d managed object property"
    ::= { cfprApEquipmentNetworkElementFanStatsHistEntry 16 }

cfprApEquipmentPOSTTable OBJECT-TYPE
    SYNTAX           SEQUENCE OF CfprApEquipmentPOSTEntry
    MAX-ACCESS       not-accessible
    STATUS           current
    DESCRIPTION
        "Cisco Firepower equipment:POST managed object table"
    ::= { cfprApEquipmentObjects 95 }

cfprApEquipmentPOSTEntry OBJECT-TYPE
    SYNTAX           CfprApEquipmentPOSTEntry
    MAX-ACCESS       not-accessible
    STATUS           current
    DESCRIPTION
        "Entry for the cfprApEquipmentPOSTTable table."
    INDEX { cfprApEquipmentPOSTInstanceId }
    ::= { cfprApEquipmentPOSTTable 1 }

CfprApEquipmentPOSTEntry ::= SEQUENCE {
    cfprApEquipmentPOSTInstanceId                                    CfprApManagedObjectId,
    cfprApEquipmentPOSTDn                                            CfprApManagedObjectDn,
    cfprApEquipmentPOSTRn                                            SnmpAdminString,
    cfprApEquipmentPOSTCode                                          SnmpAdminString,
    cfprApEquipmentPOSTCreated                                       DateAndTime,
    cfprApEquipmentPOSTDescr                                         SnmpAdminString,
    cfprApEquipmentPOSTGlobalId                                      SnmpAdminString,
    cfprApEquipmentPOSTLocalId                                       SnmpAdminString,
    cfprApEquipmentPOSTMethod                                        CfprApEquipmentMethod,
    cfprApEquipmentPOSTName                                          SnmpAdminString,
    cfprApEquipmentPOSTRecoverable                                   CfprApEquipmentPOSTRecoverability,
    cfprApEquipmentPOSTRecoveryAction                                SnmpAdminString,
    cfprApEquipmentPOSTSeverity                                      CfprApConditionSeverity,
    cfprApEquipmentPOSTType                                          SnmpAdminString,
    cfprApEquipmentPOSTValue                                         Gauge32
}

cfprApEquipmentPOSTInstanceId OBJECT-TYPE
    SYNTAX       CfprApManagedObjectId
    MAX-ACCESS   not-accessible
    STATUS       current
    DESCRIPTION
        "Instance identifier of the managed object."
    ::= { cfprApEquipmentPOSTEntry 1 }

cfprApEquipmentPOSTDn OBJECT-TYPE
    SYNTAX       CfprApManagedObjectDn
    MAX-ACCESS   read-only
    STATUS       current
    DESCRIPTION
        "Cisco Firepower equipment:POST:dn managed object property"
    ::= { cfprApEquipmentPOSTEntry 2 }

cfprApEquipmentPOSTRn OBJECT-TYPE
    SYNTAX       SnmpAdminString
    MAX-ACCESS   read-only
    STATUS       current
    DESCRIPTION
        "Cisco Firepower equipment:POST:rn managed object property"
    ::= { cfprApEquipmentPOSTEntry 3 }

cfprApEquipmentPOSTCode OBJECT-TYPE
    SYNTAX       SnmpAdminString
    MAX-ACCESS   read-only
    STATUS       current
    DESCRIPTION
        "Cisco Firepower equipment:POST:code managed object property"
    ::= { cfprApEquipmentPOSTEntry 4 }

cfprApEquipmentPOSTCreated OBJECT-TYPE
    SYNTAX       DateAndTime
    MAX-ACCESS   read-only
    STATUS       current
    DESCRIPTION
        "Cisco Firepower equipment:POST:created managed object property"
    ::= { cfprApEquipmentPOSTEntry 5 }

cfprApEquipmentPOSTDescr OBJECT-TYPE
    SYNTAX       SnmpAdminString
    MAX-ACCESS   read-only
    STATUS       current
    DESCRIPTION
        "Cisco Firepower equipment:POST:descr managed object property"
    ::= { cfprApEquipmentPOSTEntry 6 }

cfprApEquipmentPOSTGlobalId OBJECT-TYPE
    SYNTAX       SnmpAdminString
    MAX-ACCESS   read-only
    STATUS       current
    DESCRIPTION
        "Cisco Firepower equipment:POST:globalId managed object property"
    ::= { cfprApEquipmentPOSTEntry 7 }

cfprApEquipmentPOSTLocalId OBJECT-TYPE
    SYNTAX       SnmpAdminString
    MAX-ACCESS   read-only
    STATUS       current
    DESCRIPTION
        "Cisco Firepower equipment:POST:localId managed object property"
    ::= { cfprApEquipmentPOSTEntry 8 }

cfprApEquipmentPOSTMethod OBJECT-TYPE
    SYNTAX       CfprApEquipmentMethod
    MAX-ACCESS   read-only
    STATUS       current
    DESCRIPTION
        "Cisco Firepower equipment:POST:method managed object property"
    ::= { cfprApEquipmentPOSTEntry 9 }

cfprApEquipmentPOSTName OBJECT-TYPE
    SYNTAX       SnmpAdminString
    MAX-ACCESS   read-only
    STATUS       current
    DESCRIPTION
        "Cisco Firepower equipment:POST:name managed object property"
    ::= { cfprApEquipmentPOSTEntry 10 }

cfprApEquipmentPOSTRecoverable OBJECT-TYPE
    SYNTAX       CfprApEquipmentPOSTRecoverability
    MAX-ACCESS   read-only
    STATUS       current
    DESCRIPTION
        "Cisco Firepower equipment:POST:recoverable managed
        object property"
    ::= { cfprApEquipmentPOSTEntry 11 }

cfprApEquipmentPOSTRecoveryAction OBJECT-TYPE
    SYNTAX       SnmpAdminString
    MAX-ACCESS   read-only
    STATUS       current
    DESCRIPTION
        "Cisco Firepower equipment:POST:recoveryAction
        managed object property"
    ::= { cfprApEquipmentPOSTEntry 12 }

cfprApEquipmentPOSTSeverity OBJECT-TYPE
    SYNTAX       CfprApConditionSeverity
    MAX-ACCESS   read-only
    STATUS       current
    DESCRIPTION
        "Cisco Firepower equipment:POST:severity managed object property"
    ::= { cfprApEquipmentPOSTEntry 13 }

cfprApEquipmentPOSTType OBJECT-TYPE
    SYNTAX       SnmpAdminString
    MAX-ACCESS   read-only
    STATUS       current
    DESCRIPTION
        "Cisco Firepower equipment:POST:type managed object property"
    ::= { cfprApEquipmentPOSTEntry 14 }

cfprApEquipmentPOSTValue OBJECT-TYPE
    SYNTAX       Gauge32
    MAX-ACCESS   read-only
    STATUS       current
    DESCRIPTION
        "Cisco Firepower equipment:POST:value managed object property"
    ::= { cfprApEquipmentPOSTEntry 15 }

cfprApEquipmentPOSTCodeTable OBJECT-TYPE
    SYNTAX           SEQUENCE OF CfprApEquipmentPOSTCodeEntry
    MAX-ACCESS       not-accessible
    STATUS           current
    DESCRIPTION
        "Cisco Firepower equipment:POSTCode managed object table"
    ::= { cfprApEquipmentObjects 96 }

cfprApEquipmentPOSTCodeEntry OBJECT-TYPE
    SYNTAX           CfprApEquipmentPOSTCodeEntry
    MAX-ACCESS       not-accessible
    STATUS           current
    DESCRIPTION
        "Entry for the cfprApEquipmentPOSTCodeTable table."
    INDEX { cfprApEquipmentPOSTCodeInstanceId }
    ::= { cfprApEquipmentPOSTCodeTable 1 }

CfprApEquipmentPOSTCodeEntry ::= SEQUENCE {
    cfprApEquipmentPOSTCodeInstanceId                                CfprApManagedObjectId,
    cfprApEquipmentPOSTCodeDn                                        CfprApManagedObjectDn,
    cfprApEquipmentPOSTCodeRn                                        SnmpAdminString,
    cfprApEquipmentPOSTCodeCode                                      SnmpAdminString,
    cfprApEquipmentPOSTCodeDescr                                     SnmpAdminString,
    cfprApEquipmentPOSTCodeGlobalId                                  SnmpAdminString,
    cfprApEquipmentPOSTCodeLocalId                                   SnmpAdminString,
    cfprApEquipmentPOSTCodeMethod                                    CfprApEquipmentMethod,
    cfprApEquipmentPOSTCodeName                                      SnmpAdminString,
    cfprApEquipmentPOSTCodeRecoverable                               CfprApEquipmentPOSTRecoverability,
    cfprApEquipmentPOSTCodeRecoveryAction                            SnmpAdminString,
    cfprApEquipmentPOSTCodeSeverity                                  CfprApConditionSeverity
}

cfprApEquipmentPOSTCodeInstanceId OBJECT-TYPE
    SYNTAX       CfprApManagedObjectId
    MAX-ACCESS   not-accessible
    STATUS       current
    DESCRIPTION
        "Instance identifier of the managed object."
    ::= { cfprApEquipmentPOSTCodeEntry 1 }

cfprApEquipmentPOSTCodeDn OBJECT-TYPE
    SYNTAX       CfprApManagedObjectDn
    MAX-ACCESS   read-only
    STATUS       current
    DESCRIPTION
        "Cisco Firepower equipment:POSTCode:dn managed object property"
    ::= { cfprApEquipmentPOSTCodeEntry 2 }

cfprApEquipmentPOSTCodeRn OBJECT-TYPE
    SYNTAX       SnmpAdminString
    MAX-ACCESS   read-only
    STATUS       current
    DESCRIPTION
        "Cisco Firepower equipment:POSTCode:rn managed object property"
    ::= { cfprApEquipmentPOSTCodeEntry 3 }

cfprApEquipmentPOSTCodeCode OBJECT-TYPE
    SYNTAX       SnmpAdminString
    MAX-ACCESS   read-only
    STATUS       current
    DESCRIPTION
        "Cisco Firepower equipment:POSTCode:code managed object property"
    ::= { cfprApEquipmentPOSTCodeEntry 4 }

cfprApEquipmentPOSTCodeDescr OBJECT-TYPE
    SYNTAX       SnmpAdminString
    MAX-ACCESS   read-only
    STATUS       current
    DESCRIPTION
        "Cisco Firepower equipment:POSTCode:descr managed object property"
    ::= { cfprApEquipmentPOSTCodeEntry 5 }

cfprApEquipmentPOSTCodeGlobalId OBJECT-TYPE
    SYNTAX       SnmpAdminString
    MAX-ACCESS   read-only
    STATUS       current
    DESCRIPTION
        "Cisco Firepower equipment:POSTCode:globalId managed
        object property"
    ::= { cfprApEquipmentPOSTCodeEntry 6 }

cfprApEquipmentPOSTCodeLocalId OBJECT-TYPE
    SYNTAX       SnmpAdminString
    MAX-ACCESS   read-only
    STATUS       current
    DESCRIPTION
        "Cisco Firepower equipment:POSTCode:localId managed
        object property"
    ::= { cfprApEquipmentPOSTCodeEntry 7 }

cfprApEquipmentPOSTCodeMethod OBJECT-TYPE
    SYNTAX       CfprApEquipmentMethod
    MAX-ACCESS   read-only
    STATUS       current
    DESCRIPTION
        "Cisco Firepower equipment:POSTCode:method managed
        object property"
    ::= { cfprApEquipmentPOSTCodeEntry 8 }

cfprApEquipmentPOSTCodeName OBJECT-TYPE
    SYNTAX       SnmpAdminString
    MAX-ACCESS   read-only
    STATUS       current
    DESCRIPTION
        "Cisco Firepower equipment:POSTCode:name managed object property"
    ::= { cfprApEquipmentPOSTCodeEntry 9 }

cfprApEquipmentPOSTCodeRecoverable OBJECT-TYPE
    SYNTAX       CfprApEquipmentPOSTRecoverability
    MAX-ACCESS   read-only
    STATUS       current
    DESCRIPTION
        "Cisco Firepower equipment:POSTCode:recoverable
        managed object property"
    ::= { cfprApEquipmentPOSTCodeEntry 10 }

cfprApEquipmentPOSTCodeRecoveryAction OBJECT-TYPE
    SYNTAX       SnmpAdminString
    MAX-ACCESS   read-only
    STATUS       current
    DESCRIPTION
        "Cisco Firepower equipment:POSTCode:recoveryAction
        managed object property"
    ::= { cfprApEquipmentPOSTCodeEntry 11 }

cfprApEquipmentPOSTCodeSeverity OBJECT-TYPE
    SYNTAX       CfprApConditionSeverity
    MAX-ACCESS   read-only
    STATUS       current
    DESCRIPTION
        "Cisco Firepower equipment:POSTCode:severity managed
        object property"
    ::= { cfprApEquipmentPOSTCodeEntry 12 }

cfprApEquipmentPOSTCodeReporterTable OBJECT-TYPE
    SYNTAX           SEQUENCE OF CfprApEquipmentPOSTCodeReporterEntry
    MAX-ACCESS       not-accessible
    STATUS           current
    DESCRIPTION
        "Cisco Firepower equipment:POSTCodeReporter managed object table"
    ::= { cfprApEquipmentObjects 97 }

cfprApEquipmentPOSTCodeReporterEntry OBJECT-TYPE
    SYNTAX           CfprApEquipmentPOSTCodeReporterEntry
    MAX-ACCESS       not-accessible
    STATUS           current
    DESCRIPTION
        "Entry for the cfprApEquipmentPOSTCodeReporterTable table."
    INDEX { cfprApEquipmentPOSTCodeReporterInstanceId }
    ::= { cfprApEquipmentPOSTCodeReporterTable 1 }

CfprApEquipmentPOSTCodeReporterEntry ::= SEQUENCE {
    cfprApEquipmentPOSTCodeReporterInstanceId                        CfprApManagedObjectId,
    cfprApEquipmentPOSTCodeReporterDn                                CfprApManagedObjectDn,
    cfprApEquipmentPOSTCodeReporterRn                                SnmpAdminString,
    cfprApEquipmentPOSTCodeReporterBaseContainer                     SnmpAdminString,
    cfprApEquipmentPOSTCodeReporterModel                             SnmpAdminString,
    cfprApEquipmentPOSTCodeReporterName                              SnmpAdminString,
    cfprApEquipmentPOSTCodeReporterRevision                          SnmpAdminString,
    cfprApEquipmentPOSTCodeReporterSerial                            SnmpAdminString,
    cfprApEquipmentPOSTCodeReporterType                              SnmpAdminString,
    cfprApEquipmentPOSTCodeReporterVendor                            SnmpAdminString
}

cfprApEquipmentPOSTCodeReporterInstanceId OBJECT-TYPE
    SYNTAX       CfprApManagedObjectId
    MAX-ACCESS   not-accessible
    STATUS       current
    DESCRIPTION
        "Instance identifier of the managed object."
    ::= { cfprApEquipmentPOSTCodeReporterEntry 1 }

cfprApEquipmentPOSTCodeReporterDn OBJECT-TYPE
    SYNTAX       CfprApManagedObjectDn
    MAX-ACCESS   read-only
    STATUS       current
    DESCRIPTION
        "Cisco Firepower equipment:POSTCodeReporter:dn
        managed object property"
    ::= { cfprApEquipmentPOSTCodeReporterEntry 2 }

cfprApEquipmentPOSTCodeReporterRn OBJECT-TYPE
    SYNTAX       SnmpAdminString
    MAX-ACCESS   read-only
    STATUS       current
    DESCRIPTION
        "Cisco Firepower equipment:POSTCodeReporter:rn
        managed object property"
    ::= { cfprApEquipmentPOSTCodeReporterEntry 3 }

cfprApEquipmentPOSTCodeReporterBaseContainer OBJECT-TYPE
    SYNTAX       SnmpAdminString
    MAX-ACCESS   read-only
    STATUS       current
    DESCRIPTION
        "Cisco Firepower equipment:POSTCodeReporter:baseContainer
        managed object property"
    ::= { cfprApEquipmentPOSTCodeReporterEntry 4 }

cfprApEquipmentPOSTCodeReporterModel OBJECT-TYPE
    SYNTAX       SnmpAdminString
    MAX-ACCESS   read-only
    STATUS       current
    DESCRIPTION
        "Cisco Firepower equipment:POSTCodeReporter:model
        managed object property"
    ::= { cfprApEquipmentPOSTCodeReporterEntry 5 }

cfprApEquipmentPOSTCodeReporterName OBJECT-TYPE
    SYNTAX       SnmpAdminString
    MAX-ACCESS   read-only
    STATUS       current
    DESCRIPTION
        "Cisco Firepower equipment:POSTCodeReporter:name
        managed object property"
    ::= { cfprApEquipmentPOSTCodeReporterEntry 6 }

cfprApEquipmentPOSTCodeReporterRevision OBJECT-TYPE
    SYNTAX       SnmpAdminString
    MAX-ACCESS   read-only
    STATUS       current
    DESCRIPTION
        "Cisco Firepower equipment:POSTCodeReporter:revision
        managed object property"
    ::= { cfprApEquipmentPOSTCodeReporterEntry 7 }

cfprApEquipmentPOSTCodeReporterSerial OBJECT-TYPE
    SYNTAX       SnmpAdminString
    MAX-ACCESS   read-only
    STATUS       current
    DESCRIPTION
        "Cisco Firepower equipment:POSTCodeReporter:serial
        managed object property"
    ::= { cfprApEquipmentPOSTCodeReporterEntry 8 }

cfprApEquipmentPOSTCodeReporterType OBJECT-TYPE
    SYNTAX       SnmpAdminString
    MAX-ACCESS   read-only
    STATUS       current
    DESCRIPTION
        "Cisco Firepower equipment:POSTCodeReporter:type
        managed object property"
    ::= { cfprApEquipmentPOSTCodeReporterEntry 9 }

cfprApEquipmentPOSTCodeReporterVendor OBJECT-TYPE
    SYNTAX       SnmpAdminString
    MAX-ACCESS   read-only
    STATUS       current
    DESCRIPTION
        "Cisco Firepower equipment:POSTCodeReporter:vendor
        managed object property"
    ::= { cfprApEquipmentPOSTCodeReporterEntry 10 }

cfprApEquipmentPOSTCodeTemplateTable OBJECT-TYPE
    SYNTAX           SEQUENCE OF CfprApEquipmentPOSTCodeTemplateEntry
    MAX-ACCESS       not-accessible
    STATUS           current
    DESCRIPTION
        "Cisco Firepower equipment:POSTCodeTemplate managed object table"
    ::= { cfprApEquipmentObjects 98 }

cfprApEquipmentPOSTCodeTemplateEntry OBJECT-TYPE
    SYNTAX           CfprApEquipmentPOSTCodeTemplateEntry
    MAX-ACCESS       not-accessible
    STATUS           current
    DESCRIPTION
        "Entry for the cfprApEquipmentPOSTCodeTemplateTable table."
    INDEX { cfprApEquipmentPOSTCodeTemplateInstanceId }
    ::= { cfprApEquipmentPOSTCodeTemplateTable 1 }

CfprApEquipmentPOSTCodeTemplateEntry ::= SEQUENCE {
    cfprApEquipmentPOSTCodeTemplateInstanceId                        CfprApManagedObjectId,
    cfprApEquipmentPOSTCodeTemplateDn                                CfprApManagedObjectDn,
    cfprApEquipmentPOSTCodeTemplateRn                                SnmpAdminString,
    cfprApEquipmentPOSTCodeTemplateBaseContainer                     SnmpAdminString,
    cfprApEquipmentPOSTCodeTemplateName                              SnmpAdminString
}

cfprApEquipmentPOSTCodeTemplateInstanceId OBJECT-TYPE
    SYNTAX       CfprApManagedObjectId
    MAX-ACCESS   not-accessible
    STATUS       current
    DESCRIPTION
        "Instance identifier of the managed object."
    ::= { cfprApEquipmentPOSTCodeTemplateEntry 1 }

cfprApEquipmentPOSTCodeTemplateDn OBJECT-TYPE
    SYNTAX       CfprApManagedObjectDn
    MAX-ACCESS   read-only
    STATUS       current
    DESCRIPTION
        "Cisco Firepower equipment:POSTCodeTemplate:dn
        managed object property"
    ::= { cfprApEquipmentPOSTCodeTemplateEntry 2 }

cfprApEquipmentPOSTCodeTemplateRn OBJECT-TYPE
    SYNTAX       SnmpAdminString
    MAX-ACCESS   read-only
    STATUS       current
    DESCRIPTION
        "Cisco Firepower equipment:POSTCodeTemplate:rn
        managed object property"
    ::= { cfprApEquipmentPOSTCodeTemplateEntry 3 }

cfprApEquipmentPOSTCodeTemplateBaseContainer OBJECT-TYPE
    SYNTAX       SnmpAdminString
    MAX-ACCESS   read-only
    STATUS       current
    DESCRIPTION
        "Cisco Firepower equipment:POSTCodeTemplate:baseContainer
        managed object property"
    ::= { cfprApEquipmentPOSTCodeTemplateEntry 4 }

cfprApEquipmentPOSTCodeTemplateName OBJECT-TYPE
    SYNTAX       SnmpAdminString
    MAX-ACCESS   read-only
    STATUS       current
    DESCRIPTION
        "Cisco Firepower equipment:POSTCodeTemplate:name
        managed object property"
    ::= { cfprApEquipmentPOSTCodeTemplateEntry 5 }

cfprApEquipmentPciDefTable OBJECT-TYPE
    SYNTAX           SEQUENCE OF CfprApEquipmentPciDefEntry
    MAX-ACCESS       not-accessible
    STATUS           current
    DESCRIPTION
        "Cisco Firepower equipment:PciDef managed object table"
    ::= { cfprApEquipmentObjects 99 }

cfprApEquipmentPciDefEntry OBJECT-TYPE
    SYNTAX           CfprApEquipmentPciDefEntry
    MAX-ACCESS       not-accessible
    STATUS           current
    DESCRIPTION
        "Entry for the cfprApEquipmentPciDefTable table."
    INDEX { cfprApEquipmentPciDefInstanceId }
    ::= { cfprApEquipmentPciDefTable 1 }

CfprApEquipmentPciDefEntry ::= SEQUENCE {
    cfprApEquipmentPciDefInstanceId                                  CfprApManagedObjectId,
    cfprApEquipmentPciDefDn                                          CfprApManagedObjectDn,
    cfprApEquipmentPciDefRn                                          SnmpAdminString,
    cfprApEquipmentPciDefDescr                                       SnmpAdminString,
    cfprApEquipmentPciDefDevice                                      Gauge32,
    cfprApEquipmentPciDefIntId                                       SnmpAdminString,
    cfprApEquipmentPciDefName                                        SnmpAdminString,
    cfprApEquipmentPciDefPolicyLevel                                 Gauge32,
    cfprApEquipmentPciDefPolicyOwner                                 CfprApPolicyPolicyOwner,
    cfprApEquipmentPciDefSubdevice                                   Gauge32,
    cfprApEquipmentPciDefSubvendor                                   Gauge32,
    cfprApEquipmentPciDefVendor                                      Gauge32
}

cfprApEquipmentPciDefInstanceId OBJECT-TYPE
    SYNTAX       CfprApManagedObjectId
    MAX-ACCESS   not-accessible
    STATUS       current
    DESCRIPTION
        "Instance identifier of the managed object."
    ::= { cfprApEquipmentPciDefEntry 1 }

cfprApEquipmentPciDefDn OBJECT-TYPE
    SYNTAX       CfprApManagedObjectDn
    MAX-ACCESS   read-only
    STATUS       current
    DESCRIPTION
        "Cisco Firepower equipment:PciDef:dn managed object property"
    ::= { cfprApEquipmentPciDefEntry 2 }

cfprApEquipmentPciDefRn OBJECT-TYPE
    SYNTAX       SnmpAdminString
    MAX-ACCESS   read-only
    STATUS       current
    DESCRIPTION
        "Cisco Firepower equipment:PciDef:rn managed object property"
    ::= { cfprApEquipmentPciDefEntry 3 }

cfprApEquipmentPciDefDescr OBJECT-TYPE
    SYNTAX       SnmpAdminString
    MAX-ACCESS   read-only
    STATUS       current
    DESCRIPTION
        "Cisco Firepower equipment:PciDef:descr managed object property"
    ::= { cfprApEquipmentPciDefEntry 4 }

cfprApEquipmentPciDefDevice OBJECT-TYPE
    SYNTAX       Gauge32
    MAX-ACCESS   read-only
    STATUS       current
    DESCRIPTION
        "Cisco Firepower equipment:PciDef:device managed object property"
    ::= { cfprApEquipmentPciDefEntry 5 }

cfprApEquipmentPciDefIntId OBJECT-TYPE
    SYNTAX       SnmpAdminString
    MAX-ACCESS   read-only
    STATUS       current
    DESCRIPTION
        "Cisco Firepower equipment:PciDef:intId managed object property"
    ::= { cfprApEquipmentPciDefEntry 6 }

cfprApEquipmentPciDefName OBJECT-TYPE
    SYNTAX       SnmpAdminString
    MAX-ACCESS   read-only
    STATUS       current
    DESCRIPTION
        "Cisco Firepower equipment:PciDef:name managed object property"
    ::= { cfprApEquipmentPciDefEntry 7 }

cfprApEquipmentPciDefPolicyLevel OBJECT-TYPE
    SYNTAX       Gauge32
    MAX-ACCESS   read-only
    STATUS       current
    DESCRIPTION
        "Cisco Firepower equipment:PciDef:policyLevel managed
        object property"
    ::= { cfprApEquipmentPciDefEntry 8 }

cfprApEquipmentPciDefPolicyOwner OBJECT-TYPE
    SYNTAX       CfprApPolicyPolicyOwner
    MAX-ACCESS   read-only
    STATUS       current
    DESCRIPTION
        "Cisco Firepower equipment:PciDef:policyOwner managed
        object property"
    ::= { cfprApEquipmentPciDefEntry 9 }

cfprApEquipmentPciDefSubdevice OBJECT-TYPE
    SYNTAX       Gauge32
    MAX-ACCESS   read-only
    STATUS       current
    DESCRIPTION
        "Cisco Firepower equipment:PciDef:subdevice managed
        object property"
    ::= { cfprApEquipmentPciDefEntry 10 }

cfprApEquipmentPciDefSubvendor OBJECT-TYPE
    SYNTAX       Gauge32
    MAX-ACCESS   read-only
    STATUS       current
    DESCRIPTION
        "Cisco Firepower equipment:PciDef:subvendor managed
        object property"
    ::= { cfprApEquipmentPciDefEntry 11 }

cfprApEquipmentPciDefVendor OBJECT-TYPE
    SYNTAX       Gauge32
    MAX-ACCESS   read-only
    STATUS       current
    DESCRIPTION
        "Cisco Firepower equipment:PciDef:vendor managed object property"
    ::= { cfprApEquipmentPciDefEntry 12 }

cfprApEquipmentPhysDevicesPerBoardTable OBJECT-TYPE
    SYNTAX           SEQUENCE OF CfprApEquipmentPhysDevicesPerBoardEntry
    MAX-ACCESS       not-accessible
    STATUS           current
    DESCRIPTION
        "Cisco Firepower equipment:PhysDevicesPerBoard
        managed object table"
    ::= { cfprApEquipmentObjects 100 }

cfprApEquipmentPhysDevicesPerBoardEntry OBJECT-TYPE
    SYNTAX           CfprApEquipmentPhysDevicesPerBoardEntry
    MAX-ACCESS       not-accessible
    STATUS           current
    DESCRIPTION
        "Entry for the cfprApEquipmentPhysDevicesPerBoardTable table."
    INDEX { cfprApEquipmentPhysDevicesPerBoardInstanceId }
    ::= { cfprApEquipmentPhysDevicesPerBoardTable 1 }

CfprApEquipmentPhysDevicesPerBoardEntry ::= SEQUENCE {
    cfprApEquipmentPhysDevicesPerBoardInstanceId                     CfprApManagedObjectId,
    cfprApEquipmentPhysDevicesPerBoardDn                             CfprApManagedObjectDn,
    cfprApEquipmentPhysDevicesPerBoardRn                             SnmpAdminString,
    cfprApEquipmentPhysDevicesPerBoardNumOfCpu                       Gauge32,
    cfprApEquipmentPhysDevicesPerBoardNumOfDimm                      Gauge32,
    cfprApEquipmentPhysDevicesPerBoardNumOfLocalDisk                 Gauge32,
    cfprApEquipmentPhysDevicesPerBoardNumOfStorageController         Gauge32,
    cfprApEquipmentPhysDevicesPerBoardNumOfadaptor                   Gauge32
}

cfprApEquipmentPhysDevicesPerBoardInstanceId OBJECT-TYPE
    SYNTAX       CfprApManagedObjectId
    MAX-ACCESS   not-accessible
    STATUS       current
    DESCRIPTION
        "Instance identifier of the managed object."
    ::= { cfprApEquipmentPhysDevicesPerBoardEntry 1 }

cfprApEquipmentPhysDevicesPerBoardDn OBJECT-TYPE
    SYNTAX       CfprApManagedObjectDn
    MAX-ACCESS   read-only
    STATUS       current
    DESCRIPTION
        "Cisco Firepower equipment:PhysDevicesPerBoard:dn
        managed object property"
    ::= { cfprApEquipmentPhysDevicesPerBoardEntry 2 }

cfprApEquipmentPhysDevicesPerBoardRn OBJECT-TYPE
    SYNTAX       SnmpAdminString
    MAX-ACCESS   read-only
    STATUS       current
    DESCRIPTION
        "Cisco Firepower equipment:PhysDevicesPerBoard:rn
        managed object property"
    ::= { cfprApEquipmentPhysDevicesPerBoardEntry 3 }

cfprApEquipmentPhysDevicesPerBoardNumOfCpu OBJECT-TYPE
    SYNTAX       Gauge32
    MAX-ACCESS   read-only
    STATUS       current
    DESCRIPTION
        "Cisco Firepower equipment:PhysDevicesPerBoard:numOfCpu
        managed object property"
    ::= { cfprApEquipmentPhysDevicesPerBoardEntry 4 }

cfprApEquipmentPhysDevicesPerBoardNumOfDimm OBJECT-TYPE
    SYNTAX       Gauge32
    MAX-ACCESS   read-only
    STATUS       current
    DESCRIPTION
        "Cisco Firepower equipment:PhysDevicesPerBoard:numOfDimm
        managed object property"
    ::= { cfprApEquipmentPhysDevicesPerBoardEntry 5 }

cfprApEquipmentPhysDevicesPerBoardNumOfLocalDisk OBJECT-TYPE
    SYNTAX       Gauge32
    MAX-ACCESS   read-only
    STATUS       current
    DESCRIPTION
        "Cisco Firepower equipment:PhysDevicesPerBoard:numOfLocalDisk
        managed object property"
    ::= { cfprApEquipmentPhysDevicesPerBoardEntry 6 }

cfprApEquipmentPhysDevicesPerBoardNumOfStorageController OBJECT-TYPE
    SYNTAX       Gauge32
    MAX-ACCESS   read-only
    STATUS       current
    DESCRIPTION
        "Cisco Firepower equipment:PhysDevicesPerBoard:numOfStorageControl
        ler managed object property"
    ::= { cfprApEquipmentPhysDevicesPerBoardEntry 7 }

cfprApEquipmentPhysDevicesPerBoardNumOfadaptor OBJECT-TYPE
    SYNTAX       Gauge32
    MAX-ACCESS   read-only
    STATUS       current
    DESCRIPTION
        "Cisco Firepower equipment:PhysDevicesPerBoard:numOfadaptor
        managed object property"
    ::= { cfprApEquipmentPhysDevicesPerBoardEntry 8 }

cfprApEquipmentPhysicalDefTable OBJECT-TYPE
    SYNTAX           SEQUENCE OF CfprApEquipmentPhysicalDefEntry
    MAX-ACCESS       not-accessible
    STATUS           current
    DESCRIPTION
        "Cisco Firepower equipment:PhysicalDef managed object table"
    ::= { cfprApEquipmentObjects 101 }

cfprApEquipmentPhysicalDefEntry OBJECT-TYPE
    SYNTAX           CfprApEquipmentPhysicalDefEntry
    MAX-ACCESS       not-accessible
    STATUS           current
    DESCRIPTION
        "Entry for the cfprApEquipmentPhysicalDefTable table."
    INDEX { cfprApEquipmentPhysicalDefInstanceId }
    ::= { cfprApEquipmentPhysicalDefTable 1 }

CfprApEquipmentPhysicalDefEntry ::= SEQUENCE {
    cfprApEquipmentPhysicalDefInstanceId                             CfprApManagedObjectId,
    cfprApEquipmentPhysicalDefDn                                     CfprApManagedObjectDn,
    cfprApEquipmentPhysicalDefRn                                     SnmpAdminString,
    cfprApEquipmentPhysicalDefDepth                                  INTEGER,
    cfprApEquipmentPhysicalDefDescr                                  SnmpAdminString,
    cfprApEquipmentPhysicalDefHeight                                 INTEGER,
    cfprApEquipmentPhysicalDefIntId                                  SnmpAdminString,
    cfprApEquipmentPhysicalDefMaximumPower                           INTEGER,
    cfprApEquipmentPhysicalDefMaximumTemperature                     INTEGER,
    cfprApEquipmentPhysicalDefMinimumPower                           INTEGER,
    cfprApEquipmentPhysicalDefMinimumTemperature                     INTEGER,
    cfprApEquipmentPhysicalDefName                                   SnmpAdminString,
    cfprApEquipmentPhysicalDefNominalPower                           INTEGER,
    cfprApEquipmentPhysicalDefNominalTemperature                     INTEGER,
    cfprApEquipmentPhysicalDefOperatingVoltages                      SnmpAdminString,
    cfprApEquipmentPhysicalDefPolicyLevel                            Gauge32,
    cfprApEquipmentPhysicalDefPolicyOwner                            CfprApPolicyPolicyOwner,
    cfprApEquipmentPhysicalDefWeight                                 INTEGER,
    cfprApEquipmentPhysicalDefWidth                                  INTEGER
}

cfprApEquipmentPhysicalDefInstanceId OBJECT-TYPE
    SYNTAX       CfprApManagedObjectId
    MAX-ACCESS   not-accessible
    STATUS       current
    DESCRIPTION
        "Instance identifier of the managed object."
    ::= { cfprApEquipmentPhysicalDefEntry 1 }

cfprApEquipmentPhysicalDefDn OBJECT-TYPE
    SYNTAX       CfprApManagedObjectDn
    MAX-ACCESS   read-only
    STATUS       current
    DESCRIPTION
        "Cisco Firepower equipment:PhysicalDef:dn managed object property"
    ::= { cfprApEquipmentPhysicalDefEntry 2 }

cfprApEquipmentPhysicalDefRn OBJECT-TYPE
    SYNTAX       SnmpAdminString
    MAX-ACCESS   read-only
    STATUS       current
    DESCRIPTION
        "Cisco Firepower equipment:PhysicalDef:rn managed object property"
    ::= { cfprApEquipmentPhysicalDefEntry 3 }

cfprApEquipmentPhysicalDefDepth OBJECT-TYPE
    SYNTAX       INTEGER
    MAX-ACCESS   read-only
    STATUS       current
    DESCRIPTION
        "Cisco Firepower equipment:PhysicalDef:depth managed
        object property"
    ::= { cfprApEquipmentPhysicalDefEntry 4 }

cfprApEquipmentPhysicalDefDescr OBJECT-TYPE
    SYNTAX       SnmpAdminString
    MAX-ACCESS   read-only
    STATUS       current
    DESCRIPTION
        "Cisco Firepower equipment:PhysicalDef:descr managed
        object property"
    ::= { cfprApEquipmentPhysicalDefEntry 5 }

cfprApEquipmentPhysicalDefHeight OBJECT-TYPE
    SYNTAX       INTEGER
    MAX-ACCESS   read-only
    STATUS       current
    DESCRIPTION
        "Cisco Firepower equipment:PhysicalDef:height managed
        object property"
    ::= { cfprApEquipmentPhysicalDefEntry 6 }

cfprApEquipmentPhysicalDefIntId OBJECT-TYPE
    SYNTAX       SnmpAdminString
    MAX-ACCESS   read-only
    STATUS       current
    DESCRIPTION
        "Cisco Firepower equipment:PhysicalDef:intId managed
        object property"
    ::= { cfprApEquipmentPhysicalDefEntry 7 }

cfprApEquipmentPhysicalDefMaximumPower OBJECT-TYPE
    SYNTAX       INTEGER
    MAX-ACCESS   read-only
    STATUS       current
    DESCRIPTION
        "Cisco Firepower equipment:PhysicalDef:maximumPower
        managed object property"
    ::= { cfprApEquipmentPhysicalDefEntry 8 }

cfprApEquipmentPhysicalDefMaximumTemperature OBJECT-TYPE
    SYNTAX       INTEGER
    MAX-ACCESS   read-only
    STATUS       current
    DESCRIPTION
        "Cisco Firepower equipment:PhysicalDef:maximumTemperature
        managed object property"
    ::= { cfprApEquipmentPhysicalDefEntry 9 }

cfprApEquipmentPhysicalDefMinimumPower OBJECT-TYPE
    SYNTAX       INTEGER
    MAX-ACCESS   read-only
    STATUS       current
    DESCRIPTION
        "Cisco Firepower equipment:PhysicalDef:minimumPower
        managed object property"
    ::= { cfprApEquipmentPhysicalDefEntry 10 }

cfprApEquipmentPhysicalDefMinimumTemperature OBJECT-TYPE
    SYNTAX       INTEGER
    MAX-ACCESS   read-only
    STATUS       current
    DESCRIPTION
        "Cisco Firepower equipment:PhysicalDef:minimumTemperature
        managed object property"
    ::= { cfprApEquipmentPhysicalDefEntry 11 }

cfprApEquipmentPhysicalDefName OBJECT-TYPE
    SYNTAX       SnmpAdminString
    MAX-ACCESS   read-only
    STATUS       current
    DESCRIPTION
        "Cisco Firepower equipment:PhysicalDef:name managed
        object property"
    ::= { cfprApEquipmentPhysicalDefEntry 12 }

cfprApEquipmentPhysicalDefNominalPower OBJECT-TYPE
    SYNTAX       INTEGER
    MAX-ACCESS   read-only
    STATUS       current
    DESCRIPTION
        "Cisco Firepower equipment:PhysicalDef:nominalPower
        managed object property"
    ::= { cfprApEquipmentPhysicalDefEntry 13 }

cfprApEquipmentPhysicalDefNominalTemperature OBJECT-TYPE
    SYNTAX       INTEGER
    MAX-ACCESS   read-only
    STATUS       current
    DESCRIPTION
        "Cisco Firepower equipment:PhysicalDef:nominalTemperature
        managed object property"
    ::= { cfprApEquipmentPhysicalDefEntry 14 }

cfprApEquipmentPhysicalDefOperatingVoltages OBJECT-TYPE
    SYNTAX       SnmpAdminString
    MAX-ACCESS   read-only
    STATUS       current
    DESCRIPTION
        "Cisco Firepower equipment:PhysicalDef:operatingVoltages
        managed object property"
    ::= { cfprApEquipmentPhysicalDefEntry 15 }

cfprApEquipmentPhysicalDefPolicyLevel OBJECT-TYPE
    SYNTAX       Gauge32
    MAX-ACCESS   read-only
    STATUS       current
    DESCRIPTION
        "Cisco Firepower equipment:PhysicalDef:policyLevel
        managed object property"
    ::= { cfprApEquipmentPhysicalDefEntry 16 }

cfprApEquipmentPhysicalDefPolicyOwner OBJECT-TYPE
    SYNTAX       CfprApPolicyPolicyOwner
    MAX-ACCESS   read-only
    STATUS       current
    DESCRIPTION
        "Cisco Firepower equipment:PhysicalDef:policyOwner
        managed object property"
    ::= { cfprApEquipmentPhysicalDefEntry 17 }

cfprApEquipmentPhysicalDefWeight OBJECT-TYPE
    SYNTAX       INTEGER
    MAX-ACCESS   read-only
    STATUS       current
    DESCRIPTION
        "Cisco Firepower equipment:PhysicalDef:weight managed
        object property"
    ::= { cfprApEquipmentPhysicalDefEntry 18 }

cfprApEquipmentPhysicalDefWidth OBJECT-TYPE
    SYNTAX       INTEGER
    MAX-ACCESS   read-only
    STATUS       current
    DESCRIPTION
        "Cisco Firepower equipment:PhysicalDef:width managed
        object property"
    ::= { cfprApEquipmentPhysicalDefEntry 19 }

cfprApEquipmentPictureTable OBJECT-TYPE
    SYNTAX           SEQUENCE OF CfprApEquipmentPictureEntry
    MAX-ACCESS       not-accessible
    STATUS           current
    DESCRIPTION
        "Cisco Firepower equipment:Picture managed object table"
    ::= { cfprApEquipmentObjects 102 }

cfprApEquipmentPictureEntry OBJECT-TYPE
    SYNTAX           CfprApEquipmentPictureEntry
    MAX-ACCESS       not-accessible
    STATUS           current
    DESCRIPTION
        "Entry for the cfprApEquipmentPictureTable table."
    INDEX { cfprApEquipmentPictureInstanceId }
    ::= { cfprApEquipmentPictureTable 1 }

CfprApEquipmentPictureEntry ::= SEQUENCE {
    cfprApEquipmentPictureInstanceId                                 CfprApManagedObjectId,
    cfprApEquipmentPictureDn                                         CfprApManagedObjectDn,
    cfprApEquipmentPictureRn                                         SnmpAdminString,
    cfprApEquipmentPictureFileName                                   SnmpAdminString,
    cfprApEquipmentPictureType                                       CfprApEquipmentPictureType
}

cfprApEquipmentPictureInstanceId OBJECT-TYPE
    SYNTAX       CfprApManagedObjectId
    MAX-ACCESS   not-accessible
    STATUS       current
    DESCRIPTION
        "Instance identifier of the managed object."
    ::= { cfprApEquipmentPictureEntry 1 }

cfprApEquipmentPictureDn OBJECT-TYPE
    SYNTAX       CfprApManagedObjectDn
    MAX-ACCESS   read-only
    STATUS       current
    DESCRIPTION
        "Cisco Firepower equipment:Picture:dn managed object property"
    ::= { cfprApEquipmentPictureEntry 2 }

cfprApEquipmentPictureRn OBJECT-TYPE
    SYNTAX       SnmpAdminString
    MAX-ACCESS   read-only
    STATUS       current
    DESCRIPTION
        "Cisco Firepower equipment:Picture:rn managed object property"
    ::= { cfprApEquipmentPictureEntry 3 }

cfprApEquipmentPictureFileName OBJECT-TYPE
    SYNTAX       SnmpAdminString
    MAX-ACCESS   read-only
    STATUS       current
    DESCRIPTION
        "Cisco Firepower equipment:Picture:fileName managed
        object property"
    ::= { cfprApEquipmentPictureEntry 4 }

cfprApEquipmentPictureType OBJECT-TYPE
    SYNTAX       CfprApEquipmentPictureType
    MAX-ACCESS   read-only
    STATUS       current
    DESCRIPTION
        "Cisco Firepower equipment:Picture:type managed object property"
    ::= { cfprApEquipmentPictureEntry 5 }

cfprApEquipmentPortCapTable OBJECT-TYPE
    SYNTAX           SEQUENCE OF CfprApEquipmentPortCapEntry
    MAX-ACCESS       not-accessible
    STATUS           current
    DESCRIPTION
        "Cisco Firepower equipment:PortCap managed object table"
    ::= { cfprApEquipmentObjects 103 }

cfprApEquipmentPortCapEntry OBJECT-TYPE
    SYNTAX           CfprApEquipmentPortCapEntry
    MAX-ACCESS       not-accessible
    STATUS           current
    DESCRIPTION
        "Entry for the cfprApEquipmentPortCapTable table."
    INDEX { cfprApEquipmentPortCapInstanceId }
    ::= { cfprApEquipmentPortCapTable 1 }

CfprApEquipmentPortCapEntry ::= SEQUENCE {
    cfprApEquipmentPortCapInstanceId                                 CfprApManagedObjectId,
    cfprApEquipmentPortCapDn                                         CfprApManagedObjectDn,
    cfprApEquipmentPortCapRn                                         SnmpAdminString,
    cfprApEquipmentPortCapBreakoutPortSpeedGb                        Gauge32,
    cfprApEquipmentPortCapCountBreakoutPorts                         Gauge32,
    cfprApEquipmentPortCapDescr                                      SnmpAdminString,
    cfprApEquipmentPortCapEndPortId                                  Gauge32,
    cfprApEquipmentPortCapIntId                                      SnmpAdminString,
    cfprApEquipmentPortCapName                                       SnmpAdminString,
    cfprApEquipmentPortCapPolicyLevel                                Gauge32,
    cfprApEquipmentPortCapPolicyOwner                                CfprApPolicyPolicyOwner,
    cfprApEquipmentPortCapPortAttribute                              CfprApEquipmentPortAttribute,
    cfprApEquipmentPortCapPortSpeedCap                               CfprApEquipmentEthPortSpeedCap,
    cfprApEquipmentPortCapPortSpeedGb                                Gauge32,
    cfprApEquipmentPortCapStartPortId                                Gauge32
}

cfprApEquipmentPortCapInstanceId OBJECT-TYPE
    SYNTAX       CfprApManagedObjectId
    MAX-ACCESS   not-accessible
    STATUS       current
    DESCRIPTION
        "Instance identifier of the managed object."
    ::= { cfprApEquipmentPortCapEntry 1 }

cfprApEquipmentPortCapDn OBJECT-TYPE
    SYNTAX       CfprApManagedObjectDn
    MAX-ACCESS   read-only
    STATUS       current
    DESCRIPTION
        "Cisco Firepower equipment:PortCap:dn managed object property"
    ::= { cfprApEquipmentPortCapEntry 2 }

cfprApEquipmentPortCapRn OBJECT-TYPE
    SYNTAX       SnmpAdminString
    MAX-ACCESS   read-only
    STATUS       current
    DESCRIPTION
        "Cisco Firepower equipment:PortCap:rn managed object property"
    ::= { cfprApEquipmentPortCapEntry 3 }

cfprApEquipmentPortCapBreakoutPortSpeedGb OBJECT-TYPE
    SYNTAX       Gauge32
    MAX-ACCESS   read-only
    STATUS       current
    DESCRIPTION
        "Cisco Firepower equipment:PortCap:breakoutPortSpeedGb
        managed object property"
    ::= { cfprApEquipmentPortCapEntry 4 }

cfprApEquipmentPortCapCountBreakoutPorts OBJECT-TYPE
    SYNTAX       Gauge32
    MAX-ACCESS   read-only
    STATUS       current
    DESCRIPTION
        "Cisco Firepower equipment:PortCap:countBreakoutPorts
        managed object property"
    ::= { cfprApEquipmentPortCapEntry 5 }

cfprApEquipmentPortCapDescr OBJECT-TYPE
    SYNTAX       SnmpAdminString
    MAX-ACCESS   read-only
    STATUS       current
    DESCRIPTION
        "Cisco Firepower equipment:PortCap:descr managed object property"
    ::= { cfprApEquipmentPortCapEntry 6 }

cfprApEquipmentPortCapEndPortId OBJECT-TYPE
    SYNTAX       Gauge32
    MAX-ACCESS   read-only
    STATUS       current
    DESCRIPTION
        "Cisco Firepower equipment:PortCap:endPortId managed
        object property"
    ::= { cfprApEquipmentPortCapEntry 7 }

cfprApEquipmentPortCapIntId OBJECT-TYPE
    SYNTAX       SnmpAdminString
    MAX-ACCESS   read-only
    STATUS       current
    DESCRIPTION
        "Cisco Firepower equipment:PortCap:intId managed object property"
    ::= { cfprApEquipmentPortCapEntry 8 }

cfprApEquipmentPortCapName OBJECT-TYPE
    SYNTAX       SnmpAdminString
    MAX-ACCESS   read-only
    STATUS       current
    DESCRIPTION
        "Cisco Firepower equipment:PortCap:name managed object property"
    ::= { cfprApEquipmentPortCapEntry 9 }

cfprApEquipmentPortCapPolicyLevel OBJECT-TYPE
    SYNTAX       Gauge32
    MAX-ACCESS   read-only
    STATUS       current
    DESCRIPTION
        "Cisco Firepower equipment:PortCap:policyLevel
        managed object property"
    ::= { cfprApEquipmentPortCapEntry 10 }

cfprApEquipmentPortCapPolicyOwner OBJECT-TYPE
    SYNTAX       CfprApPolicyPolicyOwner
    MAX-ACCESS   read-only
    STATUS       current
    DESCRIPTION
        "Cisco Firepower equipment:PortCap:policyOwner
        managed object property"
    ::= { cfprApEquipmentPortCapEntry 11 }

cfprApEquipmentPortCapPortAttribute OBJECT-TYPE
    SYNTAX       CfprApEquipmentPortAttribute
    MAX-ACCESS   read-only
    STATUS       current
    DESCRIPTION
        "Cisco Firepower equipment:PortCap:portAttribute
        managed object property"
    ::= { cfprApEquipmentPortCapEntry 12 }

cfprApEquipmentPortCapPortSpeedCap OBJECT-TYPE
    SYNTAX       CfprApEquipmentEthPortSpeedCap
    MAX-ACCESS   read-only
    STATUS       current
    DESCRIPTION
        "Cisco Firepower equipment:PortCap:portSpeedCap
        managed object property"
    ::= { cfprApEquipmentPortCapEntry 13 }

cfprApEquipmentPortCapPortSpeedGb OBJECT-TYPE
    SYNTAX       Gauge32
    MAX-ACCESS   read-only
    STATUS       current
    DESCRIPTION
        "Cisco Firepower equipment:PortCap:portSpeedGb
        managed object property"
    ::= { cfprApEquipmentPortCapEntry 14 }

cfprApEquipmentPortCapStartPortId OBJECT-TYPE
    SYNTAX       Gauge32
    MAX-ACCESS   read-only
    STATUS       current
    DESCRIPTION
        "Cisco Firepower equipment:PortCap:startPortId
        managed object property"
    ::= { cfprApEquipmentPortCapEntry 15 }

cfprApEquipmentPortGroupAggregationDefTable OBJECT-TYPE
    SYNTAX           SEQUENCE OF CfprApEquipmentPortGroupAggregationDefEntry
    MAX-ACCESS       not-accessible
    STATUS           current
    DESCRIPTION
        "Cisco Firepower equipment:PortGroupAggregationDef
        managed object table"
    ::= { cfprApEquipmentObjects 104 }

cfprApEquipmentPortGroupAggregationDefEntry OBJECT-TYPE
    SYNTAX           CfprApEquipmentPortGroupAggregationDefEntry
    MAX-ACCESS       not-accessible
    STATUS           current
    DESCRIPTION
        "Entry for the cfprApEquipmentPortGroupAggregationDefTable table."
    INDEX { cfprApEquipmentPortGroupAggregationDefInstanceId }
    ::= { cfprApEquipmentPortGroupAggregationDefTable 1 }

CfprApEquipmentPortGroupAggregationDefEntry ::= SEQUENCE {
    cfprApEquipmentPortGroupAggregationDefInstanceId                 CfprApManagedObjectId,
    cfprApEquipmentPortGroupAggregationDefDn                         CfprApManagedObjectDn,
    cfprApEquipmentPortGroupAggregationDefRn                         SnmpAdminString,
    cfprApEquipmentPortGroupAggregationDefAggregationCap             CfprApComputeLinkAggregationCap,
    cfprApEquipmentPortGroupAggregationDefDescr                      SnmpAdminString,
    cfprApEquipmentPortGroupAggregationDefIntId                      SnmpAdminString,
    cfprApEquipmentPortGroupAggregationDefName                       SnmpAdminString,
    cfprApEquipmentPortGroupAggregationDefPolicyLevel                Gauge32,
    cfprApEquipmentPortGroupAggregationDefPolicyOwner                CfprApPolicyPolicyOwner,
    cfprApEquipmentPortGroupAggregationDefType                       CfprApPortGroupType
}

cfprApEquipmentPortGroupAggregationDefInstanceId OBJECT-TYPE
    SYNTAX       CfprApManagedObjectId
    MAX-ACCESS   not-accessible
    STATUS       current
    DESCRIPTION
        "Instance identifier of the managed object."
    ::= { cfprApEquipmentPortGroupAggregationDefEntry 1 }

cfprApEquipmentPortGroupAggregationDefDn OBJECT-TYPE
    SYNTAX       CfprApManagedObjectDn
    MAX-ACCESS   read-only
    STATUS       current
    DESCRIPTION
        "Cisco Firepower equipment:PortGroupAggregationDef:dn
        managed object property"
    ::= { cfprApEquipmentPortGroupAggregationDefEntry 2 }

cfprApEquipmentPortGroupAggregationDefRn OBJECT-TYPE
    SYNTAX       SnmpAdminString
    MAX-ACCESS   read-only
    STATUS       current
    DESCRIPTION
        "Cisco Firepower equipment:PortGroupAggregationDef:rn
        managed object property"
    ::= { cfprApEquipmentPortGroupAggregationDefEntry 3 }

cfprApEquipmentPortGroupAggregationDefAggregationCap OBJECT-TYPE
    SYNTAX       CfprApComputeLinkAggregationCap
    MAX-ACCESS   read-only
    STATUS       current
    DESCRIPTION
        "Cisco Firepower equipment:PortGroupAggregationDef:aggregationCap
        managed object property"
    ::= { cfprApEquipmentPortGroupAggregationDefEntry 4 }

cfprApEquipmentPortGroupAggregationDefDescr OBJECT-TYPE
    SYNTAX       SnmpAdminString
    MAX-ACCESS   read-only
    STATUS       current
    DESCRIPTION
        "Cisco Firepower equipment:PortGroupAggregationDef:descr
        managed object property"
    ::= { cfprApEquipmentPortGroupAggregationDefEntry 5 }

cfprApEquipmentPortGroupAggregationDefIntId OBJECT-TYPE
    SYNTAX       SnmpAdminString
    MAX-ACCESS   read-only
    STATUS       current
    DESCRIPTION
        "Cisco Firepower equipment:PortGroupAggregationDef:intId
        managed object property"
    ::= { cfprApEquipmentPortGroupAggregationDefEntry 6 }

cfprApEquipmentPortGroupAggregationDefName OBJECT-TYPE
    SYNTAX       SnmpAdminString
    MAX-ACCESS   read-only
    STATUS       current
    DESCRIPTION
        "Cisco Firepower equipment:PortGroupAggregationDef:name
        managed object property"
    ::= { cfprApEquipmentPortGroupAggregationDefEntry 7 }

cfprApEquipmentPortGroupAggregationDefPolicyLevel OBJECT-TYPE
    SYNTAX       Gauge32
    MAX-ACCESS   read-only
    STATUS       current
    DESCRIPTION
        "Cisco Firepower equipment:PortGroupAggregationDef:policyLevel
        managed object property"
    ::= { cfprApEquipmentPortGroupAggregationDefEntry 8 }

cfprApEquipmentPortGroupAggregationDefPolicyOwner OBJECT-TYPE
    SYNTAX       CfprApPolicyPolicyOwner
    MAX-ACCESS   read-only
    STATUS       current
    DESCRIPTION
        "Cisco Firepower equipment:PortGroupAggregationDef:policyOwner
        managed object property"
    ::= { cfprApEquipmentPortGroupAggregationDefEntry 9 }

cfprApEquipmentPortGroupAggregationDefType OBJECT-TYPE
    SYNTAX       CfprApPortGroupType
    MAX-ACCESS   read-only
    STATUS       current
    DESCRIPTION
        "Cisco Firepower equipment:PortGroupAggregationDef:type
        managed object property"
    ::= { cfprApEquipmentPortGroupAggregationDefEntry 10 }

cfprApEquipmentPortGroupDefTable OBJECT-TYPE
    SYNTAX           SEQUENCE OF CfprApEquipmentPortGroupDefEntry
    MAX-ACCESS       not-accessible
    STATUS           current
    DESCRIPTION
        "Cisco Firepower equipment:PortGroupDef managed object table"
    ::= { cfprApEquipmentObjects 105 }

cfprApEquipmentPortGroupDefEntry OBJECT-TYPE
    SYNTAX           CfprApEquipmentPortGroupDefEntry
    MAX-ACCESS       not-accessible
    STATUS           current
    DESCRIPTION
        "Entry for the cfprApEquipmentPortGroupDefTable table."
    INDEX { cfprApEquipmentPortGroupDefInstanceId }
    ::= { cfprApEquipmentPortGroupDefTable 1 }

CfprApEquipmentPortGroupDefEntry ::= SEQUENCE {
    cfprApEquipmentPortGroupDefInstanceId                            CfprApManagedObjectId,
    cfprApEquipmentPortGroupDefDn                                    CfprApManagedObjectDn,
    cfprApEquipmentPortGroupDefRn                                    SnmpAdminString,
    cfprApEquipmentPortGroupDefDescr                                 SnmpAdminString,
    cfprApEquipmentPortGroupDefIntId                                 SnmpAdminString,
    cfprApEquipmentPortGroupDefName                                  SnmpAdminString,
    cfprApEquipmentPortGroupDefNumberOfPorts                         Gauge32,
    cfprApEquipmentPortGroupDefPolicyLevel                           Gauge32,
    cfprApEquipmentPortGroupDefPolicyOwner                           CfprApPolicyPolicyOwner,
    cfprApEquipmentPortGroupDefStartPortId                           Gauge32,
    cfprApEquipmentPortGroupDefType                                  CfprApPortGroupType
}

cfprApEquipmentPortGroupDefInstanceId OBJECT-TYPE
    SYNTAX       CfprApManagedObjectId
    MAX-ACCESS   not-accessible
    STATUS       current
    DESCRIPTION
        "Instance identifier of the managed object."
    ::= { cfprApEquipmentPortGroupDefEntry 1 }

cfprApEquipmentPortGroupDefDn OBJECT-TYPE
    SYNTAX       CfprApManagedObjectDn
    MAX-ACCESS   read-only
    STATUS       current
    DESCRIPTION
        "Cisco Firepower equipment:PortGroupDef:dn managed
        object property"
    ::= { cfprApEquipmentPortGroupDefEntry 2 }

cfprApEquipmentPortGroupDefRn OBJECT-TYPE
    SYNTAX       SnmpAdminString
    MAX-ACCESS   read-only
    STATUS       current
    DESCRIPTION
        "Cisco Firepower equipment:PortGroupDef:rn managed
        object property"
    ::= { cfprApEquipmentPortGroupDefEntry 3 }

cfprApEquipmentPortGroupDefDescr OBJECT-TYPE
    SYNTAX       SnmpAdminString
    MAX-ACCESS   read-only
    STATUS       current
    DESCRIPTION
        "Cisco Firepower equipment:PortGroupDef:descr managed
        object property"
    ::= { cfprApEquipmentPortGroupDefEntry 4 }

cfprApEquipmentPortGroupDefIntId OBJECT-TYPE
    SYNTAX       SnmpAdminString
    MAX-ACCESS   read-only
    STATUS       current
    DESCRIPTION
        "Cisco Firepower equipment:PortGroupDef:intId managed
        object property"
    ::= { cfprApEquipmentPortGroupDefEntry 5 }

cfprApEquipmentPortGroupDefName OBJECT-TYPE
    SYNTAX       SnmpAdminString
    MAX-ACCESS   read-only
    STATUS       current
    DESCRIPTION
        "Cisco Firepower equipment:PortGroupDef:name managed
        object property"
    ::= { cfprApEquipmentPortGroupDefEntry 6 }

cfprApEquipmentPortGroupDefNumberOfPorts OBJECT-TYPE
    SYNTAX       Gauge32
    MAX-ACCESS   read-only
    STATUS       current
    DESCRIPTION
        "Cisco Firepower equipment:PortGroupDef:numberOfPorts
        managed object property"
    ::= { cfprApEquipmentPortGroupDefEntry 7 }

cfprApEquipmentPortGroupDefPolicyLevel OBJECT-TYPE
    SYNTAX       Gauge32
    MAX-ACCESS   read-only
    STATUS       current
    DESCRIPTION
        "Cisco Firepower equipment:PortGroupDef:policyLevel
        managed object property"
    ::= { cfprApEquipmentPortGroupDefEntry 8 }

cfprApEquipmentPortGroupDefPolicyOwner OBJECT-TYPE
    SYNTAX       CfprApPolicyPolicyOwner
    MAX-ACCESS   read-only
    STATUS       current
    DESCRIPTION
        "Cisco Firepower equipment:PortGroupDef:policyOwner
        managed object property"
    ::= { cfprApEquipmentPortGroupDefEntry 9 }

cfprApEquipmentPortGroupDefStartPortId OBJECT-TYPE
    SYNTAX       Gauge32
    MAX-ACCESS   read-only
    STATUS       current
    DESCRIPTION
        "Cisco Firepower equipment:PortGroupDef:startPortId
        managed object property"
    ::= { cfprApEquipmentPortGroupDefEntry 10 }

cfprApEquipmentPortGroupDefType OBJECT-TYPE
    SYNTAX       CfprApPortGroupType
    MAX-ACCESS   read-only
    STATUS       current
    DESCRIPTION
        "Cisco Firepower equipment:PortGroupDef:type managed
        object property"
    ::= { cfprApEquipmentPortGroupDefEntry 11 }

cfprApEquipmentPortGroupSwComplexDefTable OBJECT-TYPE
    SYNTAX           SEQUENCE OF CfprApEquipmentPortGroupSwComplexDefEntry
    MAX-ACCESS       not-accessible
    STATUS           current
    DESCRIPTION
        "Cisco Firepower equipment:PortGroupSwComplexDef
        managed object table"
    ::= { cfprApEquipmentObjects 106 }

cfprApEquipmentPortGroupSwComplexDefEntry OBJECT-TYPE
    SYNTAX           CfprApEquipmentPortGroupSwComplexDefEntry
    MAX-ACCESS       not-accessible
    STATUS           current
    DESCRIPTION
        "Entry for the cfprApEquipmentPortGroupSwComplexDefTable table."
    INDEX { cfprApEquipmentPortGroupSwComplexDefInstanceId }
    ::= { cfprApEquipmentPortGroupSwComplexDefTable 1 }

CfprApEquipmentPortGroupSwComplexDefEntry ::= SEQUENCE {
    cfprApEquipmentPortGroupSwComplexDefInstanceId                   CfprApManagedObjectId,
    cfprApEquipmentPortGroupSwComplexDefDn                           CfprApManagedObjectDn,
    cfprApEquipmentPortGroupSwComplexDefRn                           SnmpAdminString,
    cfprApEquipmentPortGroupSwComplexDefAsic                         CfprApEquipmentAsicType,
    cfprApEquipmentPortGroupSwComplexDefDescr                        SnmpAdminString,
    cfprApEquipmentPortGroupSwComplexDefIntId                        SnmpAdminString,
    cfprApEquipmentPortGroupSwComplexDefName                         SnmpAdminString,
    cfprApEquipmentPortGroupSwComplexDefPolicyLevel                  Gauge32,
    cfprApEquipmentPortGroupSwComplexDefPolicyOwner                  CfprApPolicyPolicyOwner,
    cfprApEquipmentPortGroupSwComplexDefPortCapacity                 Gauge32,
    cfprApEquipmentPortGroupSwComplexDefSwComplexCapacity            Gauge32,
    cfprApEquipmentPortGroupSwComplexDefVifCapacity                  Gauge32
}

cfprApEquipmentPortGroupSwComplexDefInstanceId OBJECT-TYPE
    SYNTAX       CfprApManagedObjectId
    MAX-ACCESS   not-accessible
    STATUS       current
    DESCRIPTION
        "Instance identifier of the managed object."
    ::= { cfprApEquipmentPortGroupSwComplexDefEntry 1 }

cfprApEquipmentPortGroupSwComplexDefDn OBJECT-TYPE
    SYNTAX       CfprApManagedObjectDn
    MAX-ACCESS   read-only
    STATUS       current
    DESCRIPTION
        "Cisco Firepower equipment:PortGroupSwComplexDef:dn
        managed object property"
    ::= { cfprApEquipmentPortGroupSwComplexDefEntry 2 }

cfprApEquipmentPortGroupSwComplexDefRn OBJECT-TYPE
    SYNTAX       SnmpAdminString
    MAX-ACCESS   read-only
    STATUS       current
    DESCRIPTION
        "Cisco Firepower equipment:PortGroupSwComplexDef:rn
        managed object property"
    ::= { cfprApEquipmentPortGroupSwComplexDefEntry 3 }

cfprApEquipmentPortGroupSwComplexDefAsic OBJECT-TYPE
    SYNTAX       CfprApEquipmentAsicType
    MAX-ACCESS   read-only
    STATUS       current
    DESCRIPTION
        "Cisco Firepower equipment:PortGroupSwComplexDef:asic
        managed object property"
    ::= { cfprApEquipmentPortGroupSwComplexDefEntry 4 }

cfprApEquipmentPortGroupSwComplexDefDescr OBJECT-TYPE
    SYNTAX       SnmpAdminString
    MAX-ACCESS   read-only
    STATUS       current
    DESCRIPTION
        "Cisco Firepower equipment:PortGroupSwComplexDef:descr
        managed object property"
    ::= { cfprApEquipmentPortGroupSwComplexDefEntry 5 }

cfprApEquipmentPortGroupSwComplexDefIntId OBJECT-TYPE
    SYNTAX       SnmpAdminString
    MAX-ACCESS   read-only
    STATUS       current
    DESCRIPTION
        "Cisco Firepower equipment:PortGroupSwComplexDef:intId
        managed object property"
    ::= { cfprApEquipmentPortGroupSwComplexDefEntry 6 }

cfprApEquipmentPortGroupSwComplexDefName OBJECT-TYPE
    SYNTAX       SnmpAdminString
    MAX-ACCESS   read-only
    STATUS       current
    DESCRIPTION
        "Cisco Firepower equipment:PortGroupSwComplexDef:name
        managed object property"
    ::= { cfprApEquipmentPortGroupSwComplexDefEntry 7 }

cfprApEquipmentPortGroupSwComplexDefPolicyLevel OBJECT-TYPE
    SYNTAX       Gauge32
    MAX-ACCESS   read-only
    STATUS       current
    DESCRIPTION
        "Cisco Firepower equipment:PortGroupSwComplexDef:policyLevel
        managed object property"
    ::= { cfprApEquipmentPortGroupSwComplexDefEntry 8 }

cfprApEquipmentPortGroupSwComplexDefPolicyOwner OBJECT-TYPE
    SYNTAX       CfprApPolicyPolicyOwner
    MAX-ACCESS   read-only
    STATUS       current
    DESCRIPTION
        "Cisco Firepower equipment:PortGroupSwComplexDef:policyOwner
        managed object property"
    ::= { cfprApEquipmentPortGroupSwComplexDefEntry 9 }

cfprApEquipmentPortGroupSwComplexDefPortCapacity OBJECT-TYPE
    SYNTAX       Gauge32
    MAX-ACCESS   read-only
    STATUS       current
    DESCRIPTION
        "Cisco Firepower equipment:PortGroupSwComplexDef:portCapacity
        managed object property"
    ::= { cfprApEquipmentPortGroupSwComplexDefEntry 10 }

cfprApEquipmentPortGroupSwComplexDefSwComplexCapacity OBJECT-TYPE
    SYNTAX       Gauge32
    MAX-ACCESS   read-only
    STATUS       current
    DESCRIPTION
        "Cisco Firepower equipment:PortGroupSwComplexDef:swComplexCapacity
         managed object property"
    ::= { cfprApEquipmentPortGroupSwComplexDefEntry 11 }

cfprApEquipmentPortGroupSwComplexDefVifCapacity OBJECT-TYPE
    SYNTAX       Gauge32
    MAX-ACCESS   read-only
    STATUS       current
    DESCRIPTION
        "Cisco Firepower equipment:PortGroupSwComplexDef:vifCapacity
        managed object property"
    ::= { cfprApEquipmentPortGroupSwComplexDefEntry 12 }

cfprApEquipmentPortSwComplexRefTable OBJECT-TYPE
    SYNTAX           SEQUENCE OF CfprApEquipmentPortSwComplexRefEntry
    MAX-ACCESS       not-accessible
    STATUS           current
    DESCRIPTION
        "Cisco Firepower equipment:PortSwComplexRef managed object table"
    ::= { cfprApEquipmentObjects 107 }

cfprApEquipmentPortSwComplexRefEntry OBJECT-TYPE
    SYNTAX           CfprApEquipmentPortSwComplexRefEntry
    MAX-ACCESS       not-accessible
    STATUS           current
    DESCRIPTION
        "Entry for the cfprApEquipmentPortSwComplexRefTable table."
    INDEX { cfprApEquipmentPortSwComplexRefInstanceId }
    ::= { cfprApEquipmentPortSwComplexRefTable 1 }

CfprApEquipmentPortSwComplexRefEntry ::= SEQUENCE {
    cfprApEquipmentPortSwComplexRefInstanceId                        CfprApManagedObjectId,
    cfprApEquipmentPortSwComplexRefDn                                CfprApManagedObjectDn,
    cfprApEquipmentPortSwComplexRefRn                                SnmpAdminString,
    cfprApEquipmentPortSwComplexRefDescr                             SnmpAdminString,
    cfprApEquipmentPortSwComplexRefIntId                             SnmpAdminString,
    cfprApEquipmentPortSwComplexRefMaxPortId                         Gauge32,
    cfprApEquipmentPortSwComplexRefMinPortId                         Gauge32,
    cfprApEquipmentPortSwComplexRefName                              SnmpAdminString,
    cfprApEquipmentPortSwComplexRefPolicyLevel                       Gauge32,
    cfprApEquipmentPortSwComplexRefPolicyOwner                       CfprApPolicyPolicyOwner,
    cfprApEquipmentPortSwComplexRefSlotId                            Gauge32,
    cfprApEquipmentPortSwComplexRefSwComplexId                       Gauge32
}

cfprApEquipmentPortSwComplexRefInstanceId OBJECT-TYPE
    SYNTAX       CfprApManagedObjectId
    MAX-ACCESS   not-accessible
    STATUS       current
    DESCRIPTION
        "Instance identifier of the managed object."
    ::= { cfprApEquipmentPortSwComplexRefEntry 1 }

cfprApEquipmentPortSwComplexRefDn OBJECT-TYPE
    SYNTAX       CfprApManagedObjectDn
    MAX-ACCESS   read-only
    STATUS       current
    DESCRIPTION
        "Cisco Firepower equipment:PortSwComplexRef:dn
        managed object property"
    ::= { cfprApEquipmentPortSwComplexRefEntry 2 }

cfprApEquipmentPortSwComplexRefRn OBJECT-TYPE
    SYNTAX       SnmpAdminString
    MAX-ACCESS   read-only
    STATUS       current
    DESCRIPTION
        "Cisco Firepower equipment:PortSwComplexRef:rn
        managed object property"
    ::= { cfprApEquipmentPortSwComplexRefEntry 3 }

cfprApEquipmentPortSwComplexRefDescr OBJECT-TYPE
    SYNTAX       SnmpAdminString
    MAX-ACCESS   read-only
    STATUS       current
    DESCRIPTION
        "Cisco Firepower equipment:PortSwComplexRef:descr
        managed object property"
    ::= { cfprApEquipmentPortSwComplexRefEntry 4 }

cfprApEquipmentPortSwComplexRefIntId OBJECT-TYPE
    SYNTAX       SnmpAdminString
    MAX-ACCESS   read-only
    STATUS       current
    DESCRIPTION
        "Cisco Firepower equipment:PortSwComplexRef:intId
        managed object property"
    ::= { cfprApEquipmentPortSwComplexRefEntry 5 }

cfprApEquipmentPortSwComplexRefMaxPortId OBJECT-TYPE
    SYNTAX       Gauge32
    MAX-ACCESS   read-only
    STATUS       current
    DESCRIPTION
        "Cisco Firepower equipment:PortSwComplexRef:maxPortId
        managed object property"
    ::= { cfprApEquipmentPortSwComplexRefEntry 6 }

cfprApEquipmentPortSwComplexRefMinPortId OBJECT-TYPE
    SYNTAX       Gauge32
    MAX-ACCESS   read-only
    STATUS       current
    DESCRIPTION
        "Cisco Firepower equipment:PortSwComplexRef:minPortId
        managed object property"
    ::= { cfprApEquipmentPortSwComplexRefEntry 7 }

cfprApEquipmentPortSwComplexRefName OBJECT-TYPE
    SYNTAX       SnmpAdminString
    MAX-ACCESS   read-only
    STATUS       current
    DESCRIPTION
        "Cisco Firepower equipment:PortSwComplexRef:name
        managed object property"
    ::= { cfprApEquipmentPortSwComplexRefEntry 8 }

cfprApEquipmentPortSwComplexRefPolicyLevel OBJECT-TYPE
    SYNTAX       Gauge32
    MAX-ACCESS   read-only
    STATUS       current
    DESCRIPTION
        "Cisco Firepower equipment:PortSwComplexRef:policyLevel
        managed object property"
    ::= { cfprApEquipmentPortSwComplexRefEntry 9 }

cfprApEquipmentPortSwComplexRefPolicyOwner OBJECT-TYPE
    SYNTAX       CfprApPolicyPolicyOwner
    MAX-ACCESS   read-only
    STATUS       current
    DESCRIPTION
        "Cisco Firepower equipment:PortSwComplexRef:policyOwner
        managed object property"
    ::= { cfprApEquipmentPortSwComplexRefEntry 10 }

cfprApEquipmentPortSwComplexRefSlotId OBJECT-TYPE
    SYNTAX       Gauge32
    MAX-ACCESS   read-only
    STATUS       current
    DESCRIPTION
        "Cisco Firepower equipment:PortSwComplexRef:slotId
        managed object property"
    ::= { cfprApEquipmentPortSwComplexRefEntry 11 }

cfprApEquipmentPortSwComplexRefSwComplexId OBJECT-TYPE
    SYNTAX       Gauge32
    MAX-ACCESS   read-only
    STATUS       current
    DESCRIPTION
        "Cisco Firepower equipment:PortSwComplexRef:swComplexId
        managed object property"
    ::= { cfprApEquipmentPortSwComplexRefEntry 12 }

cfprApEquipmentPowerCapDefTable OBJECT-TYPE
    SYNTAX           SEQUENCE OF CfprApEquipmentPowerCapDefEntry
    MAX-ACCESS       not-accessible
    STATUS           current
    DESCRIPTION
        "Cisco Firepower equipment:PowerCapDef managed object table"
    ::= { cfprApEquipmentObjects 108 }

cfprApEquipmentPowerCapDefEntry OBJECT-TYPE
    SYNTAX           CfprApEquipmentPowerCapDefEntry
    MAX-ACCESS       not-accessible
    STATUS           current
    DESCRIPTION
        "Entry for the cfprApEquipmentPowerCapDefTable table."
    INDEX { cfprApEquipmentPowerCapDefInstanceId }
    ::= { cfprApEquipmentPowerCapDefTable 1 }

CfprApEquipmentPowerCapDefEntry ::= SEQUENCE {
    cfprApEquipmentPowerCapDefInstanceId                             CfprApManagedObjectId,
    cfprApEquipmentPowerCapDefDn                                     CfprApManagedObjectDn,
    cfprApEquipmentPowerCapDefRn                                     SnmpAdminString,
    cfprApEquipmentPowerCapDefMinBiosVersion                         SnmpAdminString,
    cfprApEquipmentPowerCapDefMinCimcVersion                         SnmpAdminString,
    cfprApEquipmentPowerCapDefMinCmcVersion                          SnmpAdminString,
    cfprApEquipmentPowerCapDefProfileMethod                          CfprApEquipmentPowerCapDefProfileMethod
}

cfprApEquipmentPowerCapDefInstanceId OBJECT-TYPE
    SYNTAX       CfprApManagedObjectId
    MAX-ACCESS   not-accessible
    STATUS       current
    DESCRIPTION
        "Instance identifier of the managed object."
    ::= { cfprApEquipmentPowerCapDefEntry 1 }

cfprApEquipmentPowerCapDefDn OBJECT-TYPE
    SYNTAX       CfprApManagedObjectDn
    MAX-ACCESS   read-only
    STATUS       current
    DESCRIPTION
        "Cisco Firepower equipment:PowerCapDef:dn managed object property"
    ::= { cfprApEquipmentPowerCapDefEntry 2 }

cfprApEquipmentPowerCapDefRn OBJECT-TYPE
    SYNTAX       SnmpAdminString
    MAX-ACCESS   read-only
    STATUS       current
    DESCRIPTION
        "Cisco Firepower equipment:PowerCapDef:rn managed object property"
    ::= { cfprApEquipmentPowerCapDefEntry 3 }

cfprApEquipmentPowerCapDefMinBiosVersion OBJECT-TYPE
    SYNTAX       SnmpAdminString
    MAX-ACCESS   read-only
    STATUS       current
    DESCRIPTION
        "Cisco Firepower equipment:PowerCapDef:minBiosVersion
        managed object property"
    ::= { cfprApEquipmentPowerCapDefEntry 4 }

cfprApEquipmentPowerCapDefMinCimcVersion OBJECT-TYPE
    SYNTAX       SnmpAdminString
    MAX-ACCESS   read-only
    STATUS       current
    DESCRIPTION
        "Cisco Firepower equipment:PowerCapDef:minCimcVersion
        managed object property"
    ::= { cfprApEquipmentPowerCapDefEntry 5 }

cfprApEquipmentPowerCapDefMinCmcVersion OBJECT-TYPE
    SYNTAX       SnmpAdminString
    MAX-ACCESS   read-only
    STATUS       current
    DESCRIPTION
        "Cisco Firepower equipment:PowerCapDef:minCmcVersion
        managed object property"
    ::= { cfprApEquipmentPowerCapDefEntry 6 }

cfprApEquipmentPowerCapDefProfileMethod OBJECT-TYPE
    SYNTAX       CfprApEquipmentPowerCapDefProfileMethod
    MAX-ACCESS   read-only
    STATUS       current
    DESCRIPTION
        "Cisco Firepower equipment:PowerCapDef:profileMethod
        managed object property"
    ::= { cfprApEquipmentPowerCapDefEntry 7 }

cfprApEquipmentProcessorUnitCapProviderTable OBJECT-TYPE
    SYNTAX           SEQUENCE OF CfprApEquipmentProcessorUnitCapProviderEntry
    MAX-ACCESS       not-accessible
    STATUS           current
    DESCRIPTION
        "Cisco Firepower equipment:ProcessorUnitCapProvider
        managed object table"
    ::= { cfprApEquipmentObjects 109 }

cfprApEquipmentProcessorUnitCapProviderEntry OBJECT-TYPE
    SYNTAX           CfprApEquipmentProcessorUnitCapProviderEntry
    MAX-ACCESS       not-accessible
    STATUS           current
    DESCRIPTION
        "Entry for the cfprApEquipmentProcessorUnitCapProviderTable table."
    INDEX { cfprApEquipmentProcessorUnitCapProviderInstanceId }
    ::= { cfprApEquipmentProcessorUnitCapProviderTable 1 }

CfprApEquipmentProcessorUnitCapProviderEntry ::= SEQUENCE {
    cfprApEquipmentProcessorUnitCapProviderInstanceId                CfprApManagedObjectId,
    cfprApEquipmentProcessorUnitCapProviderDn                        CfprApManagedObjectDn,
    cfprApEquipmentProcessorUnitCapProviderRn                        SnmpAdminString,
    cfprApEquipmentProcessorUnitCapProviderDeleted                   TruthValue,
    cfprApEquipmentProcessorUnitCapProviderDeprecated                TruthValue,
    cfprApEquipmentProcessorUnitCapProviderElementLoadFailures       Gauge32,
    cfprApEquipmentProcessorUnitCapProviderElementsLoaded            Gauge32,
    cfprApEquipmentProcessorUnitCapProviderGencount                  Gauge32,
    cfprApEquipmentProcessorUnitCapProviderLoadErrors                Gauge32,
    cfprApEquipmentProcessorUnitCapProviderLoadWarnings              Gauge32,
    cfprApEquipmentProcessorUnitCapProviderMgmtPlaneVer              SnmpAdminString,
    cfprApEquipmentProcessorUnitCapProviderModel                     SnmpAdminString,
    cfprApEquipmentProcessorUnitCapProviderPromCardType              Gauge32,
    cfprApEquipmentProcessorUnitCapProviderRevision                  SnmpAdminString,
    cfprApEquipmentProcessorUnitCapProviderVendor                    SnmpAdminString
}

cfprApEquipmentProcessorUnitCapProviderInstanceId OBJECT-TYPE
    SYNTAX       CfprApManagedObjectId
    MAX-ACCESS   not-accessible
    STATUS       current
    DESCRIPTION
        "Instance identifier of the managed object."
    ::= { cfprApEquipmentProcessorUnitCapProviderEntry 1 }

cfprApEquipmentProcessorUnitCapProviderDn OBJECT-TYPE
    SYNTAX       CfprApManagedObjectDn
    MAX-ACCESS   read-only
    STATUS       current
    DESCRIPTION
        "Cisco Firepower equipment:ProcessorUnitCapProvider:dn
        managed object property"
    ::= { cfprApEquipmentProcessorUnitCapProviderEntry 2 }

cfprApEquipmentProcessorUnitCapProviderRn OBJECT-TYPE
    SYNTAX       SnmpAdminString
    MAX-ACCESS   read-only
    STATUS       current
    DESCRIPTION
        "Cisco Firepower equipment:ProcessorUnitCapProvider:rn
        managed object property"
    ::= { cfprApEquipmentProcessorUnitCapProviderEntry 3 }

cfprApEquipmentProcessorUnitCapProviderDeleted OBJECT-TYPE
    SYNTAX       TruthValue
    MAX-ACCESS   read-only
    STATUS       current
    DESCRIPTION
        "Cisco Firepower equipment:ProcessorUnitCapProvider:deleted
        managed object property"
    ::= { cfprApEquipmentProcessorUnitCapProviderEntry 4 }

cfprApEquipmentProcessorUnitCapProviderDeprecated OBJECT-TYPE
    SYNTAX       TruthValue
    MAX-ACCESS   read-only
    STATUS       current
    DESCRIPTION
        "Cisco Firepower equipment:ProcessorUnitCapProvider:deprecated
        managed object property"
    ::= { cfprApEquipmentProcessorUnitCapProviderEntry 5 }

cfprApEquipmentProcessorUnitCapProviderElementLoadFailures OBJECT-TYPE
    SYNTAX       Gauge32
    MAX-ACCESS   read-only
    STATUS       current
    DESCRIPTION
        "Cisco Firepower equipment:ProcessorUnitCapProvider:elementLoadFai
        lures managed object property"
    ::= { cfprApEquipmentProcessorUnitCapProviderEntry 6 }

cfprApEquipmentProcessorUnitCapProviderElementsLoaded OBJECT-TYPE
    SYNTAX       Gauge32
    MAX-ACCESS   read-only
    STATUS       current
    DESCRIPTION
        "Cisco Firepower equipment:ProcessorUnitCapProvider:elementsLoaded
         managed object property"
    ::= { cfprApEquipmentProcessorUnitCapProviderEntry 7 }

cfprApEquipmentProcessorUnitCapProviderGencount OBJECT-TYPE
    SYNTAX       Gauge32
    MAX-ACCESS   read-only
    STATUS       current
    DESCRIPTION
        "Cisco Firepower equipment:ProcessorUnitCapProvider:gencount
        managed object property"
    ::= { cfprApEquipmentProcessorUnitCapProviderEntry 8 }

cfprApEquipmentProcessorUnitCapProviderLoadErrors OBJECT-TYPE
    SYNTAX       Gauge32
    MAX-ACCESS   read-only
    STATUS       current
    DESCRIPTION
        "Cisco Firepower equipment:ProcessorUnitCapProvider:loadErrors
        managed object property"
    ::= { cfprApEquipmentProcessorUnitCapProviderEntry 9 }

cfprApEquipmentProcessorUnitCapProviderLoadWarnings OBJECT-TYPE
    SYNTAX       Gauge32
    MAX-ACCESS   read-only
    STATUS       current
    DESCRIPTION
        "Cisco Firepower equipment:ProcessorUnitCapProvider:loadWarnings
        managed object property"
    ::= { cfprApEquipmentProcessorUnitCapProviderEntry 10 }

cfprApEquipmentProcessorUnitCapProviderMgmtPlaneVer OBJECT-TYPE
    SYNTAX       SnmpAdminString
    MAX-ACCESS   read-only
    STATUS       current
    DESCRIPTION
        "Cisco Firepower equipment:ProcessorUnitCapProvider:mgmtPlaneVer
        managed object property"
    ::= { cfprApEquipmentProcessorUnitCapProviderEntry 11 }

cfprApEquipmentProcessorUnitCapProviderModel OBJECT-TYPE
    SYNTAX       SnmpAdminString
    MAX-ACCESS   read-only
    STATUS       current
    DESCRIPTION
        "Cisco Firepower equipment:ProcessorUnitCapProvider:model
        managed object property"
    ::= { cfprApEquipmentProcessorUnitCapProviderEntry 12 }

cfprApEquipmentProcessorUnitCapProviderPromCardType OBJECT-TYPE
    SYNTAX       Gauge32
    MAX-ACCESS   read-only
    STATUS       current
    DESCRIPTION
        "Cisco Firepower equipment:ProcessorUnitCapProvider:promCardType
        managed object property"
    ::= { cfprApEquipmentProcessorUnitCapProviderEntry 13 }

cfprApEquipmentProcessorUnitCapProviderRevision OBJECT-TYPE
    SYNTAX       SnmpAdminString
    MAX-ACCESS   read-only
    STATUS       current
    DESCRIPTION
        "Cisco Firepower equipment:ProcessorUnitCapProvider:revision
        managed object property"
    ::= { cfprApEquipmentProcessorUnitCapProviderEntry 14 }

cfprApEquipmentProcessorUnitCapProviderVendor OBJECT-TYPE
    SYNTAX       SnmpAdminString
    MAX-ACCESS   read-only
    STATUS       current
    DESCRIPTION
        "Cisco Firepower equipment:ProcessorUnitCapProvider:vendor
        managed object property"
    ::= { cfprApEquipmentProcessorUnitCapProviderEntry 15 }

cfprApEquipmentProcessorUnitDefTable OBJECT-TYPE
    SYNTAX           SEQUENCE OF CfprApEquipmentProcessorUnitDefEntry
    MAX-ACCESS       not-accessible
    STATUS           current
    DESCRIPTION
        "Cisco Firepower equipment:ProcessorUnitDef managed object table"
    ::= { cfprApEquipmentObjects 110 }

cfprApEquipmentProcessorUnitDefEntry OBJECT-TYPE
    SYNTAX           CfprApEquipmentProcessorUnitDefEntry
    MAX-ACCESS       not-accessible
    STATUS           current
    DESCRIPTION
        "Entry for the cfprApEquipmentProcessorUnitDefTable table."
    INDEX { cfprApEquipmentProcessorUnitDefInstanceId }
    ::= { cfprApEquipmentProcessorUnitDefTable 1 }

CfprApEquipmentProcessorUnitDefEntry ::= SEQUENCE {
    cfprApEquipmentProcessorUnitDefInstanceId                        CfprApManagedObjectId,
    cfprApEquipmentProcessorUnitDefDn                                CfprApManagedObjectDn,
    cfprApEquipmentProcessorUnitDefRn                                SnmpAdminString,
    cfprApEquipmentProcessorUnitDefAddressWidth                      Gauge32,
    cfprApEquipmentProcessorUnitDefDataWidth                         Gauge32,
    cfprApEquipmentProcessorUnitDefDescr                             SnmpAdminString,
    cfprApEquipmentProcessorUnitDefIntId                             SnmpAdminString,
    cfprApEquipmentProcessorUnitDefMaxSpeed                          INTEGER,
    cfprApEquipmentProcessorUnitDefName                              SnmpAdminString,
    cfprApEquipmentProcessorUnitDefPolicyLevel                       Gauge32,
    cfprApEquipmentProcessorUnitDefPolicyOwner                       CfprApPolicyPolicyOwner
}

cfprApEquipmentProcessorUnitDefInstanceId OBJECT-TYPE
    SYNTAX       CfprApManagedObjectId
    MAX-ACCESS   not-accessible
    STATUS       current
    DESCRIPTION
        "Instance identifier of the managed object."
    ::= { cfprApEquipmentProcessorUnitDefEntry 1 }

cfprApEquipmentProcessorUnitDefDn OBJECT-TYPE
    SYNTAX       CfprApManagedObjectDn
    MAX-ACCESS   read-only
    STATUS       current
    DESCRIPTION
        "Cisco Firepower equipment:ProcessorUnitDef:dn
        managed object property"
    ::= { cfprApEquipmentProcessorUnitDefEntry 2 }

cfprApEquipmentProcessorUnitDefRn OBJECT-TYPE
    SYNTAX       SnmpAdminString
    MAX-ACCESS   read-only
    STATUS       current
    DESCRIPTION
        "Cisco Firepower equipment:ProcessorUnitDef:rn
        managed object property"
    ::= { cfprApEquipmentProcessorUnitDefEntry 3 }

cfprApEquipmentProcessorUnitDefAddressWidth OBJECT-TYPE
    SYNTAX       Gauge32
    MAX-ACCESS   read-only
    STATUS       current
    DESCRIPTION
        "Cisco Firepower equipment:ProcessorUnitDef:addressWidth
        managed object property"
    ::= { cfprApEquipmentProcessorUnitDefEntry 4 }

cfprApEquipmentProcessorUnitDefDataWidth OBJECT-TYPE
    SYNTAX       Gauge32
    MAX-ACCESS   read-only
    STATUS       current
    DESCRIPTION
        "Cisco Firepower equipment:ProcessorUnitDef:dataWidth
        managed object property"
    ::= { cfprApEquipmentProcessorUnitDefEntry 5 }

cfprApEquipmentProcessorUnitDefDescr OBJECT-TYPE
    SYNTAX       SnmpAdminString
    MAX-ACCESS   read-only
    STATUS       current
    DESCRIPTION
        "Cisco Firepower equipment:ProcessorUnitDef:descr
        managed object property"
    ::= { cfprApEquipmentProcessorUnitDefEntry 6 }

cfprApEquipmentProcessorUnitDefIntId OBJECT-TYPE
    SYNTAX       SnmpAdminString
    MAX-ACCESS   read-only
    STATUS       current
    DESCRIPTION
        "Cisco Firepower equipment:ProcessorUnitDef:intId
        managed object property"
    ::= { cfprApEquipmentProcessorUnitDefEntry 7 }

cfprApEquipmentProcessorUnitDefMaxSpeed OBJECT-TYPE
    SYNTAX       INTEGER
    MAX-ACCESS   read-only
    STATUS       current
    DESCRIPTION
        "Cisco Firepower equipment:ProcessorUnitDef:maxSpeed
        managed object property"
    ::= { cfprApEquipmentProcessorUnitDefEntry 8 }

cfprApEquipmentProcessorUnitDefName OBJECT-TYPE
    SYNTAX       SnmpAdminString
    MAX-ACCESS   read-only
    STATUS       current
    DESCRIPTION
        "Cisco Firepower equipment:ProcessorUnitDef:name
        managed object property"
    ::= { cfprApEquipmentProcessorUnitDefEntry 9 }

cfprApEquipmentProcessorUnitDefPolicyLevel OBJECT-TYPE
    SYNTAX       Gauge32
    MAX-ACCESS   read-only
    STATUS       current
    DESCRIPTION
        "Cisco Firepower equipment:ProcessorUnitDef:policyLevel
        managed object property"
    ::= { cfprApEquipmentProcessorUnitDefEntry 10 }

cfprApEquipmentProcessorUnitDefPolicyOwner OBJECT-TYPE
    SYNTAX       CfprApPolicyPolicyOwner
    MAX-ACCESS   read-only
    STATUS       current
    DESCRIPTION
        "Cisco Firepower equipment:ProcessorUnitDef:policyOwner
        managed object property"
    ::= { cfprApEquipmentProcessorUnitDefEntry 11 }

cfprApEquipmentPsuTable OBJECT-TYPE
    SYNTAX           SEQUENCE OF CfprApEquipmentPsuEntry
    MAX-ACCESS       not-accessible
    STATUS           current
    DESCRIPTION
        "Cisco Firepower equipment:Psu managed object table"
    ::= { cfprApEquipmentObjects 111 }

cfprApEquipmentPsuEntry OBJECT-TYPE
    SYNTAX           CfprApEquipmentPsuEntry
    MAX-ACCESS       not-accessible
    STATUS           current
    DESCRIPTION
        "Entry for the cfprApEquipmentPsuTable table."
    INDEX { cfprApEquipmentPsuInstanceId }
    ::= { cfprApEquipmentPsuTable 1 }

CfprApEquipmentPsuEntry ::= SEQUENCE {
    cfprApEquipmentPsuInstanceId                                     CfprApManagedObjectId,
    cfprApEquipmentPsuDn                                             CfprApManagedObjectDn,
    cfprApEquipmentPsuRn                                             SnmpAdminString,
    cfprApEquipmentPsuType                                           CfprApEquipmentPsuType,
    cfprApEquipmentPsuFltAggr                                        Unsigned64,
    cfprApEquipmentPsuId                                             CfprApEquipmentPsuId,
    cfprApEquipmentPsuModel                                          SnmpAdminString,
    cfprApEquipmentPsuOperQualifierReason                            SnmpAdminString,
    cfprApEquipmentPsuOperState                                      CfprApEquipmentOperability,
    cfprApEquipmentPsuOperability                                    CfprApEquipmentOperability,
    cfprApEquipmentPsuPartNumber                                     SnmpAdminString,
    cfprApEquipmentPsuPerf                                           CfprApEquipmentSensorThresholdStatus,
    cfprApEquipmentPsuPower                                          CfprApEquipmentPowerState,
    cfprApEquipmentPsuPowerStateQualifier                            CfprApEquipmentPsuStateQualifier,
    cfprApEquipmentPsuPresence                                       CfprApEquipmentPresence,
    cfprApEquipmentPsuPsuFanStatus                                   CfprApEquipmentPsuFanStatus,
    cfprApEquipmentPsuPsuFirmwareVersion                             SnmpAdminString,
    cfprApEquipmentPsuPsuInputSrc                                    CfprApEquipmentPsuInputSrc,
    cfprApEquipmentPsuPsuType                                        CfprApEquipmentPsuVoltageType,
    cfprApEquipmentPsuPsuWattage                                     Gauge32,
    cfprApEquipmentPsuRevision                                       SnmpAdminString,
    cfprApEquipmentPsuSerial                                         SnmpAdminString,
    cfprApEquipmentPsuThermal                                        CfprApEquipmentSensorThresholdStatus,
    cfprApEquipmentPsuVendor                                         SnmpAdminString,
    cfprApEquipmentPsuVid                                            SnmpAdminString,
    cfprApEquipmentPsuVoltage                                        CfprApEquipmentSensorThresholdStatus
}

cfprApEquipmentPsuInstanceId OBJECT-TYPE
    SYNTAX       CfprApManagedObjectId
    MAX-ACCESS   not-accessible
    STATUS       current
    DESCRIPTION
        "Instance identifier of the managed object."
    ::= { cfprApEquipmentPsuEntry 1 }

cfprApEquipmentPsuDn OBJECT-TYPE
    SYNTAX       CfprApManagedObjectDn
    MAX-ACCESS   read-only
    STATUS       current
    DESCRIPTION
        "Cisco Firepower equipment:Psu:dn managed object property"
    ::= { cfprApEquipmentPsuEntry 2 }

cfprApEquipmentPsuRn OBJECT-TYPE
    SYNTAX       SnmpAdminString
    MAX-ACCESS   read-only
    STATUS       current
    DESCRIPTION
        "Cisco Firepower equipment:Psu:rn managed object property"
    ::= { cfprApEquipmentPsuEntry 3 }

cfprApEquipmentPsuType OBJECT-TYPE
    SYNTAX       CfprApEquipmentPsuType
    MAX-ACCESS   read-only
    STATUS       current
    DESCRIPTION
        "Cisco Firepower equipment:Psu:Type managed object property"
    ::= { cfprApEquipmentPsuEntry 4 }

cfprApEquipmentPsuFltAggr OBJECT-TYPE
    SYNTAX       Unsigned64
    MAX-ACCESS   read-only
    STATUS       current
    DESCRIPTION
        "Cisco Firepower equipment:Psu:fltAggr managed object property"
    ::= { cfprApEquipmentPsuEntry 5 }

cfprApEquipmentPsuId OBJECT-TYPE
    SYNTAX       CfprApEquipmentPsuId
    MAX-ACCESS   read-only
    STATUS       current
    DESCRIPTION
        "Cisco Firepower equipment:Psu:id managed object property"
    ::= { cfprApEquipmentPsuEntry 6 }

cfprApEquipmentPsuModel OBJECT-TYPE
    SYNTAX       SnmpAdminString
    MAX-ACCESS   read-only
    STATUS       current
    DESCRIPTION
        "Cisco Firepower equipment:Psu:model managed object property"
    ::= { cfprApEquipmentPsuEntry 7 }

cfprApEquipmentPsuOperQualifierReason OBJECT-TYPE
    SYNTAX       SnmpAdminString
    MAX-ACCESS   read-only
    STATUS       current
    DESCRIPTION
        "Cisco Firepower equipment:Psu:operQualifierReason
        managed object property"
    ::= { cfprApEquipmentPsuEntry 8 }

cfprApEquipmentPsuOperState OBJECT-TYPE
    SYNTAX       CfprApEquipmentOperability
    MAX-ACCESS   read-only
    STATUS       current
    DESCRIPTION
        "Cisco Firepower equipment:Psu:operState managed object property"
    ::= { cfprApEquipmentPsuEntry 9 }

cfprApEquipmentPsuOperability OBJECT-TYPE
    SYNTAX       CfprApEquipmentOperability
    MAX-ACCESS   read-only
    STATUS       current
    DESCRIPTION
        "Cisco Firepower equipment:Psu:operability managed
        object property"
    ::= { cfprApEquipmentPsuEntry 10 }

cfprApEquipmentPsuPartNumber OBJECT-TYPE
    SYNTAX       SnmpAdminString
    MAX-ACCESS   read-only
    STATUS       current
    DESCRIPTION
        "Cisco Firepower equipment:Psu:partNumber managed object property"
    ::= { cfprApEquipmentPsuEntry 11 }

cfprApEquipmentPsuPerf OBJECT-TYPE
    SYNTAX       CfprApEquipmentSensorThresholdStatus
    MAX-ACCESS   read-only
    STATUS       current
    DESCRIPTION
        "Cisco Firepower equipment:Psu:perf managed object property"
    ::= { cfprApEquipmentPsuEntry 12 }

cfprApEquipmentPsuPower OBJECT-TYPE
    SYNTAX       CfprApEquipmentPowerState
    MAX-ACCESS   read-only
    STATUS       current
    DESCRIPTION
        "Cisco Firepower equipment:Psu:power managed object property"
    ::= { cfprApEquipmentPsuEntry 13 }

cfprApEquipmentPsuPowerStateQualifier OBJECT-TYPE
    SYNTAX       CfprApEquipmentPsuStateQualifier
    MAX-ACCESS   read-only
    STATUS       current
    DESCRIPTION
        "Cisco Firepower equipment:Psu:powerStateQualifier
        managed object property"
    ::= { cfprApEquipmentPsuEntry 14 }

cfprApEquipmentPsuPresence OBJECT-TYPE
    SYNTAX       CfprApEquipmentPresence
    MAX-ACCESS   read-only
    STATUS       current
    DESCRIPTION
        "Cisco Firepower equipment:Psu:presence managed object property"
    ::= { cfprApEquipmentPsuEntry 15 }

cfprApEquipmentPsuPsuFanStatus OBJECT-TYPE
    SYNTAX       CfprApEquipmentPsuFanStatus
    MAX-ACCESS   read-only
    STATUS       current
    DESCRIPTION
        "Cisco Firepower equipment:Psu:psuFanStatus managed
        object property"
    ::= { cfprApEquipmentPsuEntry 16 }

cfprApEquipmentPsuPsuFirmwareVersion OBJECT-TYPE
    SYNTAX       SnmpAdminString
    MAX-ACCESS   read-only
    STATUS       current
    DESCRIPTION
        "Cisco Firepower equipment:Psu:psuFirmwareVersion
        managed object property"
    ::= { cfprApEquipmentPsuEntry 17 }

cfprApEquipmentPsuPsuInputSrc OBJECT-TYPE
    SYNTAX       CfprApEquipmentPsuInputSrc
    MAX-ACCESS   read-only
    STATUS       current
    DESCRIPTION
        "Cisco Firepower equipment:Psu:psuInputSrc managed
        object property"
    ::= { cfprApEquipmentPsuEntry 18 }

cfprApEquipmentPsuPsuType OBJECT-TYPE
    SYNTAX       CfprApEquipmentPsuVoltageType
    MAX-ACCESS   read-only
    STATUS       current
    DESCRIPTION
        "Cisco Firepower equipment:Psu:psuType managed object property"
    ::= { cfprApEquipmentPsuEntry 19 }

cfprApEquipmentPsuPsuWattage OBJECT-TYPE
    SYNTAX       Gauge32
    MAX-ACCESS   read-only
    STATUS       current
    DESCRIPTION
        "Cisco Firepower equipment:Psu:psuWattage managed object property"
    ::= { cfprApEquipmentPsuEntry 20 }

cfprApEquipmentPsuRevision OBJECT-TYPE
    SYNTAX       SnmpAdminString
    MAX-ACCESS   read-only
    STATUS       current
    DESCRIPTION
        "Cisco Firepower equipment:Psu:revision managed object property"
    ::= { cfprApEquipmentPsuEntry 21 }

cfprApEquipmentPsuSerial OBJECT-TYPE
    SYNTAX       SnmpAdminString
    MAX-ACCESS   read-only
    STATUS       current
    DESCRIPTION
        "Cisco Firepower equipment:Psu:serial managed object property"
    ::= { cfprApEquipmentPsuEntry 22 }

cfprApEquipmentPsuThermal OBJECT-TYPE
    SYNTAX       CfprApEquipmentSensorThresholdStatus
    MAX-ACCESS   read-only
    STATUS       current
    DESCRIPTION
        "Cisco Firepower equipment:Psu:thermal managed object property"
    ::= { cfprApEquipmentPsuEntry 23 }

cfprApEquipmentPsuVendor OBJECT-TYPE
    SYNTAX       SnmpAdminString
    MAX-ACCESS   read-only
    STATUS       current
    DESCRIPTION
        "Cisco Firepower equipment:Psu:vendor managed object property"
    ::= { cfprApEquipmentPsuEntry 24 }

cfprApEquipmentPsuVid OBJECT-TYPE
    SYNTAX       SnmpAdminString
    MAX-ACCESS   read-only
    STATUS       current
    DESCRIPTION
        "Cisco Firepower equipment:Psu:vid managed object property"
    ::= { cfprApEquipmentPsuEntry 25 }

cfprApEquipmentPsuVoltage OBJECT-TYPE
    SYNTAX       CfprApEquipmentSensorThresholdStatus
    MAX-ACCESS   read-only
    STATUS       current
    DESCRIPTION
        "Cisco Firepower equipment:Psu:voltage managed object property"
    ::= { cfprApEquipmentPsuEntry 26 }

cfprApEquipmentPsuCapProviderTable OBJECT-TYPE
    SYNTAX           SEQUENCE OF CfprApEquipmentPsuCapProviderEntry
    MAX-ACCESS       not-accessible
    STATUS           current
    DESCRIPTION
        "Cisco Firepower equipment:PsuCapProvider managed object table"
    ::= { cfprApEquipmentObjects 112 }

cfprApEquipmentPsuCapProviderEntry OBJECT-TYPE
    SYNTAX           CfprApEquipmentPsuCapProviderEntry
    MAX-ACCESS       not-accessible
    STATUS           current
    DESCRIPTION
        "Entry for the cfprApEquipmentPsuCapProviderTable table."
    INDEX { cfprApEquipmentPsuCapProviderInstanceId }
    ::= { cfprApEquipmentPsuCapProviderTable 1 }

CfprApEquipmentPsuCapProviderEntry ::= SEQUENCE {
    cfprApEquipmentPsuCapProviderInstanceId                          CfprApManagedObjectId,
    cfprApEquipmentPsuCapProviderDn                                  CfprApManagedObjectDn,
    cfprApEquipmentPsuCapProviderRn                                  SnmpAdminString,
    cfprApEquipmentPsuCapProviderDeleted                             TruthValue,
    cfprApEquipmentPsuCapProviderDeprecated                          TruthValue,
    cfprApEquipmentPsuCapProviderElementLoadFailures                 Gauge32,
    cfprApEquipmentPsuCapProviderElementsLoaded                      Gauge32,
    cfprApEquipmentPsuCapProviderGencount                            Gauge32,
    cfprApEquipmentPsuCapProviderLoadErrors                          Gauge32,
    cfprApEquipmentPsuCapProviderLoadWarnings                        Gauge32,
    cfprApEquipmentPsuCapProviderMgmtPlaneVer                        SnmpAdminString,
    cfprApEquipmentPsuCapProviderModel                               SnmpAdminString,
    cfprApEquipmentPsuCapProviderPromCardType                        Gauge32,
    cfprApEquipmentPsuCapProviderRevision                            SnmpAdminString,
    cfprApEquipmentPsuCapProviderVendor                              SnmpAdminString
}

cfprApEquipmentPsuCapProviderInstanceId OBJECT-TYPE
    SYNTAX       CfprApManagedObjectId
    MAX-ACCESS   not-accessible
    STATUS       current
    DESCRIPTION
        "Instance identifier of the managed object."
    ::= { cfprApEquipmentPsuCapProviderEntry 1 }

cfprApEquipmentPsuCapProviderDn OBJECT-TYPE
    SYNTAX       CfprApManagedObjectDn
    MAX-ACCESS   read-only
    STATUS       current
    DESCRIPTION
        "Cisco Firepower equipment:PsuCapProvider:dn managed
        object property"
    ::= { cfprApEquipmentPsuCapProviderEntry 2 }

cfprApEquipmentPsuCapProviderRn OBJECT-TYPE
    SYNTAX       SnmpAdminString
    MAX-ACCESS   read-only
    STATUS       current
    DESCRIPTION
        "Cisco Firepower equipment:PsuCapProvider:rn managed
        object property"
    ::= { cfprApEquipmentPsuCapProviderEntry 3 }

cfprApEquipmentPsuCapProviderDeleted OBJECT-TYPE
    SYNTAX       TruthValue
    MAX-ACCESS   read-only
    STATUS       current
    DESCRIPTION
        "Cisco Firepower equipment:PsuCapProvider:deleted
        managed object property"
    ::= { cfprApEquipmentPsuCapProviderEntry 4 }

cfprApEquipmentPsuCapProviderDeprecated OBJECT-TYPE
    SYNTAX       TruthValue
    MAX-ACCESS   read-only
    STATUS       current
    DESCRIPTION
        "Cisco Firepower equipment:PsuCapProvider:deprecated
        managed object property"
    ::= { cfprApEquipmentPsuCapProviderEntry 5 }

cfprApEquipmentPsuCapProviderElementLoadFailures OBJECT-TYPE
    SYNTAX       Gauge32
    MAX-ACCESS   read-only
    STATUS       current
    DESCRIPTION
        "Cisco Firepower equipment:PsuCapProvider:elementLoadFailures
        managed object property"
    ::= { cfprApEquipmentPsuCapProviderEntry 6 }

cfprApEquipmentPsuCapProviderElementsLoaded OBJECT-TYPE
    SYNTAX       Gauge32
    MAX-ACCESS   read-only
    STATUS       current
    DESCRIPTION
        "Cisco Firepower equipment:PsuCapProvider:elementsLoaded
        managed object property"
    ::= { cfprApEquipmentPsuCapProviderEntry 7 }

cfprApEquipmentPsuCapProviderGencount OBJECT-TYPE
    SYNTAX       Gauge32
    MAX-ACCESS   read-only
    STATUS       current
    DESCRIPTION
        "Cisco Firepower equipment:PsuCapProvider:gencount
        managed object property"
    ::= { cfprApEquipmentPsuCapProviderEntry 8 }

cfprApEquipmentPsuCapProviderLoadErrors OBJECT-TYPE
    SYNTAX       Gauge32
    MAX-ACCESS   read-only
    STATUS       current
    DESCRIPTION
        "Cisco Firepower equipment:PsuCapProvider:loadErrors
        managed object property"
    ::= { cfprApEquipmentPsuCapProviderEntry 9 }

cfprApEquipmentPsuCapProviderLoadWarnings OBJECT-TYPE
    SYNTAX       Gauge32
    MAX-ACCESS   read-only
    STATUS       current
    DESCRIPTION
        "Cisco Firepower equipment:PsuCapProvider:loadWarnings
        managed object property"
    ::= { cfprApEquipmentPsuCapProviderEntry 10 }

cfprApEquipmentPsuCapProviderMgmtPlaneVer OBJECT-TYPE
    SYNTAX       SnmpAdminString
    MAX-ACCESS   read-only
    STATUS       current
    DESCRIPTION
        "Cisco Firepower equipment:PsuCapProvider:mgmtPlaneVer
        managed object property"
    ::= { cfprApEquipmentPsuCapProviderEntry 11 }

cfprApEquipmentPsuCapProviderModel OBJECT-TYPE
    SYNTAX       SnmpAdminString
    MAX-ACCESS   read-only
    STATUS       current
    DESCRIPTION
        "Cisco Firepower equipment:PsuCapProvider:model
        managed object property"
    ::= { cfprApEquipmentPsuCapProviderEntry 12 }

cfprApEquipmentPsuCapProviderPromCardType OBJECT-TYPE
    SYNTAX       Gauge32
    MAX-ACCESS   read-only
    STATUS       current
    DESCRIPTION
        "Cisco Firepower equipment:PsuCapProvider:promCardType
        managed object property"
    ::= { cfprApEquipmentPsuCapProviderEntry 13 }

cfprApEquipmentPsuCapProviderRevision OBJECT-TYPE
    SYNTAX       SnmpAdminString
    MAX-ACCESS   read-only
    STATUS       current
    DESCRIPTION
        "Cisco Firepower equipment:PsuCapProvider:revision
        managed object property"
    ::= { cfprApEquipmentPsuCapProviderEntry 14 }

cfprApEquipmentPsuCapProviderVendor OBJECT-TYPE
    SYNTAX       SnmpAdminString
    MAX-ACCESS   read-only
    STATUS       current
    DESCRIPTION
        "Cisco Firepower equipment:PsuCapProvider:vendor
        managed object property"
    ::= { cfprApEquipmentPsuCapProviderEntry 15 }

cfprApEquipmentPsuDefTable OBJECT-TYPE
    SYNTAX           SEQUENCE OF CfprApEquipmentPsuDefEntry
    MAX-ACCESS       not-accessible
    STATUS           current
    DESCRIPTION
        "Cisco Firepower equipment:PsuDef managed object table"
    ::= { cfprApEquipmentObjects 113 }

cfprApEquipmentPsuDefEntry OBJECT-TYPE
    SYNTAX           CfprApEquipmentPsuDefEntry
    MAX-ACCESS       not-accessible
    STATUS           current
    DESCRIPTION
        "Entry for the cfprApEquipmentPsuDefTable table."
    INDEX { cfprApEquipmentPsuDefInstanceId }
    ::= { cfprApEquipmentPsuDefTable 1 }

CfprApEquipmentPsuDefEntry ::= SEQUENCE {
    cfprApEquipmentPsuDefInstanceId                                  CfprApManagedObjectId,
    cfprApEquipmentPsuDefDn                                          CfprApManagedObjectDn,
    cfprApEquipmentPsuDefRn                                          SnmpAdminString,
    cfprApEquipmentPsuDefPsuType                                     SnmpAdminString,
    cfprApEquipmentPsuDefDescr                                       SnmpAdminString,
    cfprApEquipmentPsuDefIntId                                       SnmpAdminString,
    cfprApEquipmentPsuDefName                                        SnmpAdminString,
    cfprApEquipmentPsuDefPolicyLevel                                 Gauge32,
    cfprApEquipmentPsuDefPolicyOwner                                 CfprApPolicyPolicyOwner
}

cfprApEquipmentPsuDefInstanceId OBJECT-TYPE
    SYNTAX       CfprApManagedObjectId
    MAX-ACCESS   not-accessible
    STATUS       current
    DESCRIPTION
        "Instance identifier of the managed object."
    ::= { cfprApEquipmentPsuDefEntry 1 }

cfprApEquipmentPsuDefDn OBJECT-TYPE
    SYNTAX       CfprApManagedObjectDn
    MAX-ACCESS   read-only
    STATUS       current
    DESCRIPTION
        "Cisco Firepower equipment:PsuDef:dn managed object property"
    ::= { cfprApEquipmentPsuDefEntry 2 }

cfprApEquipmentPsuDefRn OBJECT-TYPE
    SYNTAX       SnmpAdminString
    MAX-ACCESS   read-only
    STATUS       current
    DESCRIPTION
        "Cisco Firepower equipment:PsuDef:rn managed object property"
    ::= { cfprApEquipmentPsuDefEntry 3 }

cfprApEquipmentPsuDefPsuType OBJECT-TYPE
    SYNTAX       SnmpAdminString
    MAX-ACCESS   read-only
    STATUS       current
    DESCRIPTION
        "Cisco Firepower equipment:PsuDef:PsuType managed object property"
    ::= { cfprApEquipmentPsuDefEntry 4 }

cfprApEquipmentPsuDefDescr OBJECT-TYPE
    SYNTAX       SnmpAdminString
    MAX-ACCESS   read-only
    STATUS       current
    DESCRIPTION
        "Cisco Firepower equipment:PsuDef:descr managed object property"
    ::= { cfprApEquipmentPsuDefEntry 5 }

cfprApEquipmentPsuDefIntId OBJECT-TYPE
    SYNTAX       SnmpAdminString
    MAX-ACCESS   read-only
    STATUS       current
    DESCRIPTION
        "Cisco Firepower equipment:PsuDef:intId managed object property"
    ::= { cfprApEquipmentPsuDefEntry 6 }

cfprApEquipmentPsuDefName OBJECT-TYPE
    SYNTAX       SnmpAdminString
    MAX-ACCESS   read-only
    STATUS       current
    DESCRIPTION
        "Cisco Firepower equipment:PsuDef:name managed object property"
    ::= { cfprApEquipmentPsuDefEntry 7 }

cfprApEquipmentPsuDefPolicyLevel OBJECT-TYPE
    SYNTAX       Gauge32
    MAX-ACCESS   read-only
    STATUS       current
    DESCRIPTION
        "Cisco Firepower equipment:PsuDef:policyLevel managed
        object property"
    ::= { cfprApEquipmentPsuDefEntry 8 }

cfprApEquipmentPsuDefPolicyOwner OBJECT-TYPE
    SYNTAX       CfprApPolicyPolicyOwner
    MAX-ACCESS   read-only
    STATUS       current
    DESCRIPTION
        "Cisco Firepower equipment:PsuDef:policyOwner managed
        object property"
    ::= { cfprApEquipmentPsuDefEntry 9 }

cfprApEquipmentPsuInputStatsTable OBJECT-TYPE
    SYNTAX           SEQUENCE OF CfprApEquipmentPsuInputStatsEntry
    MAX-ACCESS       not-accessible
    STATUS           current
    DESCRIPTION
        "Cisco Firepower equipment:PsuInputStats managed object table"
    ::= { cfprApEquipmentObjects 114 }

cfprApEquipmentPsuInputStatsEntry OBJECT-TYPE
    SYNTAX           CfprApEquipmentPsuInputStatsEntry
    MAX-ACCESS       not-accessible
    STATUS           current
    DESCRIPTION
        "Entry for the cfprApEquipmentPsuInputStatsTable table."
    INDEX { cfprApEquipmentPsuInputStatsInstanceId }
    ::= { cfprApEquipmentPsuInputStatsTable 1 }

CfprApEquipmentPsuInputStatsEntry ::= SEQUENCE {
    cfprApEquipmentPsuInputStatsInstanceId                           CfprApManagedObjectId,
    cfprApEquipmentPsuInputStatsDn                                   CfprApManagedObjectDn,
    cfprApEquipmentPsuInputStatsRn                                   SnmpAdminString,
    cfprApEquipmentPsuInputStatsCurrent                              INTEGER,
    cfprApEquipmentPsuInputStatsCurrentAvg                           INTEGER,
    cfprApEquipmentPsuInputStatsCurrentMax                           INTEGER,
    cfprApEquipmentPsuInputStatsCurrentMin                           INTEGER,
    cfprApEquipmentPsuInputStatsInputStatus                          SnmpAdminString,
    cfprApEquipmentPsuInputStatsIntervals                            Gauge32,
    cfprApEquipmentPsuInputStatsPower                                INTEGER,
    cfprApEquipmentPsuInputStatsPowerAvg                             INTEGER,
    cfprApEquipmentPsuInputStatsPowerMax                             INTEGER,
    cfprApEquipmentPsuInputStatsPowerMin                             INTEGER,
    cfprApEquipmentPsuInputStatsSuspect                              TruthValue,
    cfprApEquipmentPsuInputStatsThresholded                          CfprApEquipmentPsuInputStatsThresholded,
    cfprApEquipmentPsuInputStatsTimeCollected                        DateAndTime,
    cfprApEquipmentPsuInputStatsUpdate                               Gauge32,
    cfprApEquipmentPsuInputStatsVoltage                              INTEGER,
    cfprApEquipmentPsuInputStatsVoltageAvg                           INTEGER,
    cfprApEquipmentPsuInputStatsVoltageMax                           INTEGER,
    cfprApEquipmentPsuInputStatsVoltageMin                           INTEGER
}

cfprApEquipmentPsuInputStatsInstanceId OBJECT-TYPE
    SYNTAX       CfprApManagedObjectId
    MAX-ACCESS   not-accessible
    STATUS       current
    DESCRIPTION
        "Instance identifier of the managed object."
    ::= { cfprApEquipmentPsuInputStatsEntry 1 }

cfprApEquipmentPsuInputStatsDn OBJECT-TYPE
    SYNTAX       CfprApManagedObjectDn
    MAX-ACCESS   read-only
    STATUS       current
    DESCRIPTION
        "Cisco Firepower equipment:PsuInputStats:dn managed
        object property"
    ::= { cfprApEquipmentPsuInputStatsEntry 2 }

cfprApEquipmentPsuInputStatsRn OBJECT-TYPE
    SYNTAX       SnmpAdminString
    MAX-ACCESS   read-only
    STATUS       current
    DESCRIPTION
        "Cisco Firepower equipment:PsuInputStats:rn managed
        object property"
    ::= { cfprApEquipmentPsuInputStatsEntry 3 }

cfprApEquipmentPsuInputStatsCurrent OBJECT-TYPE
    SYNTAX       INTEGER
    MAX-ACCESS   read-only
    STATUS       current
    DESCRIPTION
        "Cisco Firepower equipment:PsuInputStats:current
        managed object property"
    ::= { cfprApEquipmentPsuInputStatsEntry 4 }

cfprApEquipmentPsuInputStatsCurrentAvg OBJECT-TYPE
    SYNTAX       INTEGER
    MAX-ACCESS   read-only
    STATUS       current
    DESCRIPTION
        "Cisco Firepower equipment:PsuInputStats:currentAvg
        managed object property"
    ::= { cfprApEquipmentPsuInputStatsEntry 5 }

cfprApEquipmentPsuInputStatsCurrentMax OBJECT-TYPE
    SYNTAX       INTEGER
    MAX-ACCESS   read-only
    STATUS       current
    DESCRIPTION
        "Cisco Firepower equipment:PsuInputStats:currentMax
        managed object property"
    ::= { cfprApEquipmentPsuInputStatsEntry 6 }

cfprApEquipmentPsuInputStatsCurrentMin OBJECT-TYPE
    SYNTAX       INTEGER
    MAX-ACCESS   read-only
    STATUS       current
    DESCRIPTION
        "Cisco Firepower equipment:PsuInputStats:currentMin
        managed object property"
    ::= { cfprApEquipmentPsuInputStatsEntry 7 }

cfprApEquipmentPsuInputStatsInputStatus OBJECT-TYPE
    SYNTAX       SnmpAdminString
    MAX-ACCESS   read-only
    STATUS       current
    DESCRIPTION
        "Cisco Firepower equipment:PsuInputStats:inputStatus
        managed object property"
    ::= { cfprApEquipmentPsuInputStatsEntry 8 }

cfprApEquipmentPsuInputStatsIntervals OBJECT-TYPE
    SYNTAX       Gauge32
    MAX-ACCESS   read-only
    STATUS       current
    DESCRIPTION
        "Cisco Firepower equipment:PsuInputStats:intervals
        managed object property"
    ::= { cfprApEquipmentPsuInputStatsEntry 9 }

cfprApEquipmentPsuInputStatsPower OBJECT-TYPE
    SYNTAX       INTEGER
    MAX-ACCESS   read-only
    STATUS       current
    DESCRIPTION
        "Cisco Firepower equipment:PsuInputStats:power
        managed object property"
    ::= { cfprApEquipmentPsuInputStatsEntry 10 }

cfprApEquipmentPsuInputStatsPowerAvg OBJECT-TYPE
    SYNTAX       INTEGER
    MAX-ACCESS   read-only
    STATUS       current
    DESCRIPTION
        "Cisco Firepower equipment:PsuInputStats:powerAvg
        managed object property"
    ::= { cfprApEquipmentPsuInputStatsEntry 11 }

cfprApEquipmentPsuInputStatsPowerMax OBJECT-TYPE
    SYNTAX       INTEGER
    MAX-ACCESS   read-only
    STATUS       current
    DESCRIPTION
        "Cisco Firepower equipment:PsuInputStats:powerMax
        managed object property"
    ::= { cfprApEquipmentPsuInputStatsEntry 12 }

cfprApEquipmentPsuInputStatsPowerMin OBJECT-TYPE
    SYNTAX       INTEGER
    MAX-ACCESS   read-only
    STATUS       current
    DESCRIPTION
        "Cisco Firepower equipment:PsuInputStats:powerMin
        managed object property"
    ::= { cfprApEquipmentPsuInputStatsEntry 13 }

cfprApEquipmentPsuInputStatsSuspect OBJECT-TYPE
    SYNTAX       TruthValue
    MAX-ACCESS   read-only
    STATUS       current
    DESCRIPTION
        "Cisco Firepower equipment:PsuInputStats:suspect
        managed object property"
    ::= { cfprApEquipmentPsuInputStatsEntry 14 }

cfprApEquipmentPsuInputStatsThresholded OBJECT-TYPE
    SYNTAX       CfprApEquipmentPsuInputStatsThresholded
    MAX-ACCESS   read-only
    STATUS       current
    DESCRIPTION
        "Cisco Firepower equipment:PsuInputStats:thresholded
        managed object property"
    ::= { cfprApEquipmentPsuInputStatsEntry 15 }

cfprApEquipmentPsuInputStatsTimeCollected OBJECT-TYPE
    SYNTAX       DateAndTime
    MAX-ACCESS   read-only
    STATUS       current
    DESCRIPTION
        "Cisco Firepower equipment:PsuInputStats:timeCollected
        managed object property"
    ::= { cfprApEquipmentPsuInputStatsEntry 16 }

cfprApEquipmentPsuInputStatsUpdate OBJECT-TYPE
    SYNTAX       Gauge32
    MAX-ACCESS   read-only
    STATUS       current
    DESCRIPTION
        "Cisco Firepower equipment:PsuInputStats:update
        managed object property"
    ::= { cfprApEquipmentPsuInputStatsEntry 17 }

cfprApEquipmentPsuInputStatsVoltage OBJECT-TYPE
    SYNTAX       INTEGER
    MAX-ACCESS   read-only
    STATUS       current
    DESCRIPTION
        "Cisco Firepower equipment:PsuInputStats:voltage
        managed object property"
    ::= { cfprApEquipmentPsuInputStatsEntry 18 }

cfprApEquipmentPsuInputStatsVoltageAvg OBJECT-TYPE
    SYNTAX       INTEGER
    MAX-ACCESS   read-only
    STATUS       current
    DESCRIPTION
        "Cisco Firepower equipment:PsuInputStats:voltageAvg
        managed object property"
    ::= { cfprApEquipmentPsuInputStatsEntry 19 }

cfprApEquipmentPsuInputStatsVoltageMax OBJECT-TYPE
    SYNTAX       INTEGER
    MAX-ACCESS   read-only
    STATUS       current
    DESCRIPTION
        "Cisco Firepower equipment:PsuInputStats:voltageMax
        managed object property"
    ::= { cfprApEquipmentPsuInputStatsEntry 20 }

cfprApEquipmentPsuInputStatsVoltageMin OBJECT-TYPE
    SYNTAX       INTEGER
    MAX-ACCESS   read-only
    STATUS       current
    DESCRIPTION
        "Cisco Firepower equipment:PsuInputStats:voltageMin
        managed object property"
    ::= { cfprApEquipmentPsuInputStatsEntry 21 }

cfprApEquipmentPsuInputStatsHistTable OBJECT-TYPE
    SYNTAX           SEQUENCE OF CfprApEquipmentPsuInputStatsHistEntry
    MAX-ACCESS       not-accessible
    STATUS           current
    DESCRIPTION
        "Cisco Firepower equipment:PsuInputStatsHist managed object table"
    ::= { cfprApEquipmentObjects 115 }

cfprApEquipmentPsuInputStatsHistEntry OBJECT-TYPE
    SYNTAX           CfprApEquipmentPsuInputStatsHistEntry
    MAX-ACCESS       not-accessible
    STATUS           current
    DESCRIPTION
        "Entry for the cfprApEquipmentPsuInputStatsHistTable table."
    INDEX { cfprApEquipmentPsuInputStatsHistInstanceId }
    ::= { cfprApEquipmentPsuInputStatsHistTable 1 }

CfprApEquipmentPsuInputStatsHistEntry ::= SEQUENCE {
    cfprApEquipmentPsuInputStatsHistInstanceId                       CfprApManagedObjectId,
    cfprApEquipmentPsuInputStatsHistDn                               CfprApManagedObjectDn,
    cfprApEquipmentPsuInputStatsHistRn                               SnmpAdminString,
    cfprApEquipmentPsuInputStatsHistCurrent                          INTEGER,
    cfprApEquipmentPsuInputStatsHistCurrentAvg                       INTEGER,
    cfprApEquipmentPsuInputStatsHistCurrentMax                       INTEGER,
    cfprApEquipmentPsuInputStatsHistCurrentMin                       INTEGER,
    cfprApEquipmentPsuInputStatsHistId                               Unsigned64,
    cfprApEquipmentPsuInputStatsHistMostRecent                       TruthValue,
    cfprApEquipmentPsuInputStatsHistPower                            INTEGER,
    cfprApEquipmentPsuInputStatsHistPowerAvg                         INTEGER,
    cfprApEquipmentPsuInputStatsHistPowerMax                         INTEGER,
    cfprApEquipmentPsuInputStatsHistPowerMin                         INTEGER,
    cfprApEquipmentPsuInputStatsHistSuspect                          TruthValue,
    cfprApEquipmentPsuInputStatsHistThresholded                      CfprApEquipmentPsuInputStatsHistThresholded,
    cfprApEquipmentPsuInputStatsHistTimeCollected                    DateAndTime,
    cfprApEquipmentPsuInputStatsHistVoltage                          INTEGER,
    cfprApEquipmentPsuInputStatsHistVoltageAvg                       INTEGER,
    cfprApEquipmentPsuInputStatsHistVoltageMax                       INTEGER,
    cfprApEquipmentPsuInputStatsHistVoltageMin                       INTEGER
}

cfprApEquipmentPsuInputStatsHistInstanceId OBJECT-TYPE
    SYNTAX       CfprApManagedObjectId
    MAX-ACCESS   not-accessible
    STATUS       current
    DESCRIPTION
        "Instance identifier of the managed object."
    ::= { cfprApEquipmentPsuInputStatsHistEntry 1 }

cfprApEquipmentPsuInputStatsHistDn OBJECT-TYPE
    SYNTAX       CfprApManagedObjectDn
    MAX-ACCESS   read-only
    STATUS       current
    DESCRIPTION
        "Cisco Firepower equipment:PsuInputStatsHist:dn
        managed object property"
    ::= { cfprApEquipmentPsuInputStatsHistEntry 2 }

cfprApEquipmentPsuInputStatsHistRn OBJECT-TYPE
    SYNTAX       SnmpAdminString
    MAX-ACCESS   read-only
    STATUS       current
    DESCRIPTION
        "Cisco Firepower equipment:PsuInputStatsHist:rn
        managed object property"
    ::= { cfprApEquipmentPsuInputStatsHistEntry 3 }

cfprApEquipmentPsuInputStatsHistCurrent OBJECT-TYPE
    SYNTAX       INTEGER
    MAX-ACCESS   read-only
    STATUS       current
    DESCRIPTION
        "Cisco Firepower equipment:PsuInputStatsHist:current
        managed object property"
    ::= { cfprApEquipmentPsuInputStatsHistEntry 4 }

cfprApEquipmentPsuInputStatsHistCurrentAvg OBJECT-TYPE
    SYNTAX       INTEGER
    MAX-ACCESS   read-only
    STATUS       current
    DESCRIPTION
        "Cisco Firepower equipment:PsuInputStatsHist:currentAvg
        managed object property"
    ::= { cfprApEquipmentPsuInputStatsHistEntry 5 }

cfprApEquipmentPsuInputStatsHistCurrentMax OBJECT-TYPE
    SYNTAX       INTEGER
    MAX-ACCESS   read-only
    STATUS       current
    DESCRIPTION
        "Cisco Firepower equipment:PsuInputStatsHist:currentMax
        managed object property"
    ::= { cfprApEquipmentPsuInputStatsHistEntry 6 }

cfprApEquipmentPsuInputStatsHistCurrentMin OBJECT-TYPE
    SYNTAX       INTEGER
    MAX-ACCESS   read-only
    STATUS       current
    DESCRIPTION
        "Cisco Firepower equipment:PsuInputStatsHist:currentMin
        managed object property"
    ::= { cfprApEquipmentPsuInputStatsHistEntry 7 }

cfprApEquipmentPsuInputStatsHistId OBJECT-TYPE
    SYNTAX       Unsigned64
    MAX-ACCESS   read-only
    STATUS       current
    DESCRIPTION
        "Cisco Firepower equipment:PsuInputStatsHist:id
        managed object property"
    ::= { cfprApEquipmentPsuInputStatsHistEntry 8 }

cfprApEquipmentPsuInputStatsHistMostRecent OBJECT-TYPE
    SYNTAX       TruthValue
    MAX-ACCESS   read-only
    STATUS       current
    DESCRIPTION
        "Cisco Firepower equipment:PsuInputStatsHist:mostRecent
        managed object property"
    ::= { cfprApEquipmentPsuInputStatsHistEntry 9 }

cfprApEquipmentPsuInputStatsHistPower OBJECT-TYPE
    SYNTAX       INTEGER
    MAX-ACCESS   read-only
    STATUS       current
    DESCRIPTION
        "Cisco Firepower equipment:PsuInputStatsHist:power
        managed object property"
    ::= { cfprApEquipmentPsuInputStatsHistEntry 10 }

cfprApEquipmentPsuInputStatsHistPowerAvg OBJECT-TYPE
    SYNTAX       INTEGER
    MAX-ACCESS   read-only
    STATUS       current
    DESCRIPTION
        "Cisco Firepower equipment:PsuInputStatsHist:powerAvg
        managed object property"
    ::= { cfprApEquipmentPsuInputStatsHistEntry 11 }

cfprApEquipmentPsuInputStatsHistPowerMax OBJECT-TYPE
    SYNTAX       INTEGER
    MAX-ACCESS   read-only
    STATUS       current
    DESCRIPTION
        "Cisco Firepower equipment:PsuInputStatsHist:powerMax
        managed object property"
    ::= { cfprApEquipmentPsuInputStatsHistEntry 12 }

cfprApEquipmentPsuInputStatsHistPowerMin OBJECT-TYPE
    SYNTAX       INTEGER
    MAX-ACCESS   read-only
    STATUS       current
    DESCRIPTION
        "Cisco Firepower equipment:PsuInputStatsHist:powerMin
        managed object property"
    ::= { cfprApEquipmentPsuInputStatsHistEntry 13 }

cfprApEquipmentPsuInputStatsHistSuspect OBJECT-TYPE
    SYNTAX       TruthValue
    MAX-ACCESS   read-only
    STATUS       current
    DESCRIPTION
        "Cisco Firepower equipment:PsuInputStatsHist:suspect
        managed object property"
    ::= { cfprApEquipmentPsuInputStatsHistEntry 14 }

cfprApEquipmentPsuInputStatsHistThresholded OBJECT-TYPE
    SYNTAX       CfprApEquipmentPsuInputStatsHistThresholded
    MAX-ACCESS   read-only
    STATUS       current
    DESCRIPTION
        "Cisco Firepower equipment:PsuInputStatsHist:thresholded
        managed object property"
    ::= { cfprApEquipmentPsuInputStatsHistEntry 15 }

cfprApEquipmentPsuInputStatsHistTimeCollected OBJECT-TYPE
    SYNTAX       DateAndTime
    MAX-ACCESS   read-only
    STATUS       current
    DESCRIPTION
        "Cisco Firepower equipment:PsuInputStatsHist:timeCollected
        managed object property"
    ::= { cfprApEquipmentPsuInputStatsHistEntry 16 }

cfprApEquipmentPsuInputStatsHistVoltage OBJECT-TYPE
    SYNTAX       INTEGER
    MAX-ACCESS   read-only
    STATUS       current
    DESCRIPTION
        "Cisco Firepower equipment:PsuInputStatsHist:voltage
        managed object property"
    ::= { cfprApEquipmentPsuInputStatsHistEntry 17 }

cfprApEquipmentPsuInputStatsHistVoltageAvg OBJECT-TYPE
    SYNTAX       INTEGER
    MAX-ACCESS   read-only
    STATUS       current
    DESCRIPTION
        "Cisco Firepower equipment:PsuInputStatsHist:voltageAvg
        managed object property"
    ::= { cfprApEquipmentPsuInputStatsHistEntry 18 }

cfprApEquipmentPsuInputStatsHistVoltageMax OBJECT-TYPE
    SYNTAX       INTEGER
    MAX-ACCESS   read-only
    STATUS       current
    DESCRIPTION
        "Cisco Firepower equipment:PsuInputStatsHist:voltageMax
        managed object property"
    ::= { cfprApEquipmentPsuInputStatsHistEntry 19 }

cfprApEquipmentPsuInputStatsHistVoltageMin OBJECT-TYPE
    SYNTAX       INTEGER
    MAX-ACCESS   read-only
    STATUS       current
    DESCRIPTION
        "Cisco Firepower equipment:PsuInputStatsHist:voltageMin
        managed object property"
    ::= { cfprApEquipmentPsuInputStatsHistEntry 20 }

cfprApEquipmentPsuOutputStatsTable OBJECT-TYPE
    SYNTAX           SEQUENCE OF CfprApEquipmentPsuOutputStatsEntry
    MAX-ACCESS       not-accessible
    STATUS           current
    DESCRIPTION
        "Cisco Firepower equipment:PsuOutputStats managed object table"
    ::= { cfprApEquipmentObjects 116 }

cfprApEquipmentPsuOutputStatsEntry OBJECT-TYPE
    SYNTAX           CfprApEquipmentPsuOutputStatsEntry
    MAX-ACCESS       not-accessible
    STATUS           current
    DESCRIPTION
        "Entry for the cfprApEquipmentPsuOutputStatsTable table."
    INDEX { cfprApEquipmentPsuOutputStatsInstanceId }
    ::= { cfprApEquipmentPsuOutputStatsTable 1 }

CfprApEquipmentPsuOutputStatsEntry ::= SEQUENCE {
    cfprApEquipmentPsuOutputStatsInstanceId                          CfprApManagedObjectId,
    cfprApEquipmentPsuOutputStatsDn                                  CfprApManagedObjectDn,
    cfprApEquipmentPsuOutputStatsRn                                  SnmpAdminString,
    cfprApEquipmentPsuOutputStatsCurrent                             INTEGER,
    cfprApEquipmentPsuOutputStatsCurrentAvg                          INTEGER,
    cfprApEquipmentPsuOutputStatsCurrentMax                          INTEGER,
    cfprApEquipmentPsuOutputStatsCurrentMin                          INTEGER,
    cfprApEquipmentPsuOutputStatsIntervals                           Gauge32,
    cfprApEquipmentPsuOutputStatsOutputStatus                        SnmpAdminString,
    cfprApEquipmentPsuOutputStatsPower                               INTEGER,
    cfprApEquipmentPsuOutputStatsPowerAvg                            INTEGER,
    cfprApEquipmentPsuOutputStatsPowerMax                            INTEGER,
    cfprApEquipmentPsuOutputStatsPowerMin                            INTEGER,
    cfprApEquipmentPsuOutputStatsSuspect                             TruthValue,
    cfprApEquipmentPsuOutputStatsThresholded                         CfprApEquipmentPsuOutputStatsThresholded,
    cfprApEquipmentPsuOutputStatsTimeCollected                       DateAndTime,
    cfprApEquipmentPsuOutputStatsUpdate                              Gauge32,
    cfprApEquipmentPsuOutputStatsVoltage                             INTEGER,
    cfprApEquipmentPsuOutputStatsVoltageAvg                          INTEGER,
    cfprApEquipmentPsuOutputStatsVoltageMax                          INTEGER,
    cfprApEquipmentPsuOutputStatsVoltageMin                          INTEGER
}

cfprApEquipmentPsuOutputStatsInstanceId OBJECT-TYPE
    SYNTAX       CfprApManagedObjectId
    MAX-ACCESS   not-accessible
    STATUS       current
    DESCRIPTION
        "Instance identifier of the managed object."
    ::= { cfprApEquipmentPsuOutputStatsEntry 1 }

cfprApEquipmentPsuOutputStatsDn OBJECT-TYPE
    SYNTAX       CfprApManagedObjectDn
    MAX-ACCESS   read-only
    STATUS       current
    DESCRIPTION
        "Cisco Firepower equipment:PsuOutputStats:dn managed
        object property"
    ::= { cfprApEquipmentPsuOutputStatsEntry 2 }

cfprApEquipmentPsuOutputStatsRn OBJECT-TYPE
    SYNTAX       SnmpAdminString
    MAX-ACCESS   read-only
    STATUS       current
    DESCRIPTION
        "Cisco Firepower equipment:PsuOutputStats:rn managed
        object property"
    ::= { cfprApEquipmentPsuOutputStatsEntry 3 }

cfprApEquipmentPsuOutputStatsCurrent OBJECT-TYPE
    SYNTAX       INTEGER
    MAX-ACCESS   read-only
    STATUS       current
    DESCRIPTION
        "Cisco Firepower equipment:PsuOutputStats:current
        managed object property"
    ::= { cfprApEquipmentPsuOutputStatsEntry 4 }

cfprApEquipmentPsuOutputStatsCurrentAvg OBJECT-TYPE
    SYNTAX       INTEGER
    MAX-ACCESS   read-only
    STATUS       current
    DESCRIPTION
        "Cisco Firepower equipment:PsuOutputStats:currentAvg
        managed object property"
    ::= { cfprApEquipmentPsuOutputStatsEntry 5 }

cfprApEquipmentPsuOutputStatsCurrentMax OBJECT-TYPE
    SYNTAX       INTEGER
    MAX-ACCESS   read-only
    STATUS       current
    DESCRIPTION
        "Cisco Firepower equipment:PsuOutputStats:currentMax
        managed object property"
    ::= { cfprApEquipmentPsuOutputStatsEntry 6 }

cfprApEquipmentPsuOutputStatsCurrentMin OBJECT-TYPE
    SYNTAX       INTEGER
    MAX-ACCESS   read-only
    STATUS       current
    DESCRIPTION
        "Cisco Firepower equipment:PsuOutputStats:currentMin
        managed object property"
    ::= { cfprApEquipmentPsuOutputStatsEntry 7 }

cfprApEquipmentPsuOutputStatsIntervals OBJECT-TYPE
    SYNTAX       Gauge32
    MAX-ACCESS   read-only
    STATUS       current
    DESCRIPTION
        "Cisco Firepower equipment:PsuOutputStats:intervals
        managed object property"
    ::= { cfprApEquipmentPsuOutputStatsEntry 8 }

cfprApEquipmentPsuOutputStatsOutputStatus OBJECT-TYPE
    SYNTAX       SnmpAdminString
    MAX-ACCESS   read-only
    STATUS       current
    DESCRIPTION
        "Cisco Firepower equipment:PsuOutputStats:outputStatus
        managed object property"
    ::= { cfprApEquipmentPsuOutputStatsEntry 9 }

cfprApEquipmentPsuOutputStatsPower OBJECT-TYPE
    SYNTAX       INTEGER
    MAX-ACCESS   read-only
    STATUS       current
    DESCRIPTION
        "Cisco Firepower equipment:PsuOutputStats:power
        managed object property"
    ::= { cfprApEquipmentPsuOutputStatsEntry 10 }

cfprApEquipmentPsuOutputStatsPowerAvg OBJECT-TYPE
    SYNTAX       INTEGER
    MAX-ACCESS   read-only
    STATUS       current
    DESCRIPTION
        "Cisco Firepower equipment:PsuOutputStats:powerAvg
        managed object property"
    ::= { cfprApEquipmentPsuOutputStatsEntry 11 }

cfprApEquipmentPsuOutputStatsPowerMax OBJECT-TYPE
    SYNTAX       INTEGER
    MAX-ACCESS   read-only
    STATUS       current
    DESCRIPTION
        "Cisco Firepower equipment:PsuOutputStats:powerMax
        managed object property"
    ::= { cfprApEquipmentPsuOutputStatsEntry 12 }

cfprApEquipmentPsuOutputStatsPowerMin OBJECT-TYPE
    SYNTAX       INTEGER
    MAX-ACCESS   read-only
    STATUS       current
    DESCRIPTION
        "Cisco Firepower equipment:PsuOutputStats:powerMin
        managed object property"
    ::= { cfprApEquipmentPsuOutputStatsEntry 13 }

cfprApEquipmentPsuOutputStatsSuspect OBJECT-TYPE
    SYNTAX       TruthValue
    MAX-ACCESS   read-only
    STATUS       current
    DESCRIPTION
        "Cisco Firepower equipment:PsuOutputStats:suspect
        managed object property"
    ::= { cfprApEquipmentPsuOutputStatsEntry 14 }

cfprApEquipmentPsuOutputStatsThresholded OBJECT-TYPE
    SYNTAX       CfprApEquipmentPsuOutputStatsThresholded
    MAX-ACCESS   read-only
    STATUS       current
    DESCRIPTION
        "Cisco Firepower equipment:PsuOutputStats:thresholded
        managed object property"
    ::= { cfprApEquipmentPsuOutputStatsEntry 15 }

cfprApEquipmentPsuOutputStatsTimeCollected OBJECT-TYPE
    SYNTAX       DateAndTime
    MAX-ACCESS   read-only
    STATUS       current
    DESCRIPTION
        "Cisco Firepower equipment:PsuOutputStats:timeCollected
        managed object property"
    ::= { cfprApEquipmentPsuOutputStatsEntry 16 }

cfprApEquipmentPsuOutputStatsUpdate OBJECT-TYPE
    SYNTAX       Gauge32
    MAX-ACCESS   read-only
    STATUS       current
    DESCRIPTION
        "Cisco Firepower equipment:PsuOutputStats:update
        managed object property"
    ::= { cfprApEquipmentPsuOutputStatsEntry 17 }

cfprApEquipmentPsuOutputStatsVoltage OBJECT-TYPE
    SYNTAX       INTEGER
    MAX-ACCESS   read-only
    STATUS       current
    DESCRIPTION
        "Cisco Firepower equipment:PsuOutputStats:voltage
        managed object property"
    ::= { cfprApEquipmentPsuOutputStatsEntry 18 }

cfprApEquipmentPsuOutputStatsVoltageAvg OBJECT-TYPE
    SYNTAX       INTEGER
    MAX-ACCESS   read-only
    STATUS       current
    DESCRIPTION
        "Cisco Firepower equipment:PsuOutputStats:voltageAvg
        managed object property"
    ::= { cfprApEquipmentPsuOutputStatsEntry 19 }

cfprApEquipmentPsuOutputStatsVoltageMax OBJECT-TYPE
    SYNTAX       INTEGER
    MAX-ACCESS   read-only
    STATUS       current
    DESCRIPTION
        "Cisco Firepower equipment:PsuOutputStats:voltageMax
        managed object property"
    ::= { cfprApEquipmentPsuOutputStatsEntry 20 }

cfprApEquipmentPsuOutputStatsVoltageMin OBJECT-TYPE
    SYNTAX       INTEGER
    MAX-ACCESS   read-only
    STATUS       current
    DESCRIPTION
        "Cisco Firepower equipment:PsuOutputStats:voltageMin
        managed object property"
    ::= { cfprApEquipmentPsuOutputStatsEntry 21 }

cfprApEquipmentPsuOutputStatsHistTable OBJECT-TYPE
    SYNTAX           SEQUENCE OF CfprApEquipmentPsuOutputStatsHistEntry
    MAX-ACCESS       not-accessible
    STATUS           current
    DESCRIPTION
        "Cisco Firepower equipment:PsuOutputStatsHist managed
        object table"
    ::= { cfprApEquipmentObjects 117 }

cfprApEquipmentPsuOutputStatsHistEntry OBJECT-TYPE
    SYNTAX           CfprApEquipmentPsuOutputStatsHistEntry
    MAX-ACCESS       not-accessible
    STATUS           current
    DESCRIPTION
        "Entry for the cfprApEquipmentPsuOutputStatsHistTable table."
    INDEX { cfprApEquipmentPsuOutputStatsHistInstanceId }
    ::= { cfprApEquipmentPsuOutputStatsHistTable 1 }

CfprApEquipmentPsuOutputStatsHistEntry ::= SEQUENCE {
    cfprApEquipmentPsuOutputStatsHistInstanceId                      CfprApManagedObjectId,
    cfprApEquipmentPsuOutputStatsHistDn                              CfprApManagedObjectDn,
    cfprApEquipmentPsuOutputStatsHistRn                              SnmpAdminString,
    cfprApEquipmentPsuOutputStatsHistCurrent                         INTEGER,
    cfprApEquipmentPsuOutputStatsHistCurrentAvg                      INTEGER,
    cfprApEquipmentPsuOutputStatsHistCurrentMax                      INTEGER,
    cfprApEquipmentPsuOutputStatsHistCurrentMin                      INTEGER,
    cfprApEquipmentPsuOutputStatsHistId                              Unsigned64,
    cfprApEquipmentPsuOutputStatsHistMostRecent                      TruthValue,
    cfprApEquipmentPsuOutputStatsHistPower                           INTEGER,
    cfprApEquipmentPsuOutputStatsHistPowerAvg                        INTEGER,
    cfprApEquipmentPsuOutputStatsHistPowerMax                        INTEGER,
    cfprApEquipmentPsuOutputStatsHistPowerMin                        INTEGER,
    cfprApEquipmentPsuOutputStatsHistSuspect                         TruthValue,
    cfprApEquipmentPsuOutputStatsHistThresholded                     CfprApEquipmentPsuOutputStatsHistThresholded,
    cfprApEquipmentPsuOutputStatsHistTimeCollected                   DateAndTime,
    cfprApEquipmentPsuOutputStatsHistVoltage                         INTEGER,
    cfprApEquipmentPsuOutputStatsHistVoltageAvg                      INTEGER,
    cfprApEquipmentPsuOutputStatsHistVoltageMax                      INTEGER,
    cfprApEquipmentPsuOutputStatsHistVoltageMin                      INTEGER
}

cfprApEquipmentPsuOutputStatsHistInstanceId OBJECT-TYPE
    SYNTAX       CfprApManagedObjectId
    MAX-ACCESS   not-accessible
    STATUS       current
    DESCRIPTION
        "Instance identifier of the managed object."
    ::= { cfprApEquipmentPsuOutputStatsHistEntry 1 }

cfprApEquipmentPsuOutputStatsHistDn OBJECT-TYPE
    SYNTAX       CfprApManagedObjectDn
    MAX-ACCESS   read-only
    STATUS       current
    DESCRIPTION
        "Cisco Firepower equipment:PsuOutputStatsHist:dn
        managed object property"
    ::= { cfprApEquipmentPsuOutputStatsHistEntry 2 }

cfprApEquipmentPsuOutputStatsHistRn OBJECT-TYPE
    SYNTAX       SnmpAdminString
    MAX-ACCESS   read-only
    STATUS       current
    DESCRIPTION
        "Cisco Firepower equipment:PsuOutputStatsHist:rn
        managed object property"
    ::= { cfprApEquipmentPsuOutputStatsHistEntry 3 }

cfprApEquipmentPsuOutputStatsHistCurrent OBJECT-TYPE
    SYNTAX       INTEGER
    MAX-ACCESS   read-only
    STATUS       current
    DESCRIPTION
        "Cisco Firepower equipment:PsuOutputStatsHist:current
        managed object property"
    ::= { cfprApEquipmentPsuOutputStatsHistEntry 4 }

cfprApEquipmentPsuOutputStatsHistCurrentAvg OBJECT-TYPE
    SYNTAX       INTEGER
    MAX-ACCESS   read-only
    STATUS       current
    DESCRIPTION
        "Cisco Firepower equipment:PsuOutputStatsHist:currentAvg
        managed object property"
    ::= { cfprApEquipmentPsuOutputStatsHistEntry 5 }

cfprApEquipmentPsuOutputStatsHistCurrentMax OBJECT-TYPE
    SYNTAX       INTEGER
    MAX-ACCESS   read-only
    STATUS       current
    DESCRIPTION
        "Cisco Firepower equipment:PsuOutputStatsHist:currentMax
        managed object property"
    ::= { cfprApEquipmentPsuOutputStatsHistEntry 6 }

cfprApEquipmentPsuOutputStatsHistCurrentMin OBJECT-TYPE
    SYNTAX       INTEGER
    MAX-ACCESS   read-only
    STATUS       current
    DESCRIPTION
        "Cisco Firepower equipment:PsuOutputStatsHist:currentMin
        managed object property"
    ::= { cfprApEquipmentPsuOutputStatsHistEntry 7 }

cfprApEquipmentPsuOutputStatsHistId OBJECT-TYPE
    SYNTAX       Unsigned64
    MAX-ACCESS   read-only
    STATUS       current
    DESCRIPTION
        "Cisco Firepower equipment:PsuOutputStatsHist:id
        managed object property"
    ::= { cfprApEquipmentPsuOutputStatsHistEntry 8 }

cfprApEquipmentPsuOutputStatsHistMostRecent OBJECT-TYPE
    SYNTAX       TruthValue
    MAX-ACCESS   read-only
    STATUS       current
    DESCRIPTION
        "Cisco Firepower equipment:PsuOutputStatsHist:mostRecent
        managed object property"
    ::= { cfprApEquipmentPsuOutputStatsHistEntry 9 }

cfprApEquipmentPsuOutputStatsHistPower OBJECT-TYPE
    SYNTAX       INTEGER
    MAX-ACCESS   read-only
    STATUS       current
    DESCRIPTION
        "Cisco Firepower equipment:PsuOutputStatsHist:power
        managed object property"
    ::= { cfprApEquipmentPsuOutputStatsHistEntry 10 }

cfprApEquipmentPsuOutputStatsHistPowerAvg OBJECT-TYPE
    SYNTAX       INTEGER
    MAX-ACCESS   read-only
    STATUS       current
    DESCRIPTION
        "Cisco Firepower equipment:PsuOutputStatsHist:powerAvg
        managed object property"
    ::= { cfprApEquipmentPsuOutputStatsHistEntry 11 }

cfprApEquipmentPsuOutputStatsHistPowerMax OBJECT-TYPE
    SYNTAX       INTEGER
    MAX-ACCESS   read-only
    STATUS       current
    DESCRIPTION
        "Cisco Firepower equipment:PsuOutputStatsHist:powerMax
        managed object property"
    ::= { cfprApEquipmentPsuOutputStatsHistEntry 12 }

cfprApEquipmentPsuOutputStatsHistPowerMin OBJECT-TYPE
    SYNTAX       INTEGER
    MAX-ACCESS   read-only
    STATUS       current
    DESCRIPTION
        "Cisco Firepower equipment:PsuOutputStatsHist:powerMin
        managed object property"
    ::= { cfprApEquipmentPsuOutputStatsHistEntry 13 }

cfprApEquipmentPsuOutputStatsHistSuspect OBJECT-TYPE
    SYNTAX       TruthValue
    MAX-ACCESS   read-only
    STATUS       current
    DESCRIPTION
        "Cisco Firepower equipment:PsuOutputStatsHist:suspect
        managed object property"
    ::= { cfprApEquipmentPsuOutputStatsHistEntry 14 }

cfprApEquipmentPsuOutputStatsHistThresholded OBJECT-TYPE
    SYNTAX       CfprApEquipmentPsuOutputStatsHistThresholded
    MAX-ACCESS   read-only
    STATUS       current
    DESCRIPTION
        "Cisco Firepower equipment:PsuOutputStatsHist:thresholded
        managed object property"
    ::= { cfprApEquipmentPsuOutputStatsHistEntry 15 }

cfprApEquipmentPsuOutputStatsHistTimeCollected OBJECT-TYPE
    SYNTAX       DateAndTime
    MAX-ACCESS   read-only
    STATUS       current
    DESCRIPTION
        "Cisco Firepower equipment:PsuOutputStatsHist:timeCollected
        managed object property"
    ::= { cfprApEquipmentPsuOutputStatsHistEntry 16 }

cfprApEquipmentPsuOutputStatsHistVoltage OBJECT-TYPE
    SYNTAX       INTEGER
    MAX-ACCESS   read-only
    STATUS       current
    DESCRIPTION
        "Cisco Firepower equipment:PsuOutputStatsHist:voltage
        managed object property"
    ::= { cfprApEquipmentPsuOutputStatsHistEntry 17 }

cfprApEquipmentPsuOutputStatsHistVoltageAvg OBJECT-TYPE
    SYNTAX       INTEGER
    MAX-ACCESS   read-only
    STATUS       current
    DESCRIPTION
        "Cisco Firepower equipment:PsuOutputStatsHist:voltageAvg
        managed object property"
    ::= { cfprApEquipmentPsuOutputStatsHistEntry 18 }

cfprApEquipmentPsuOutputStatsHistVoltageMax OBJECT-TYPE
    SYNTAX       INTEGER
    MAX-ACCESS   read-only
    STATUS       current
    DESCRIPTION
        "Cisco Firepower equipment:PsuOutputStatsHist:voltageMax
        managed object property"
    ::= { cfprApEquipmentPsuOutputStatsHistEntry 19 }

cfprApEquipmentPsuOutputStatsHistVoltageMin OBJECT-TYPE
    SYNTAX       INTEGER
    MAX-ACCESS   read-only
    STATUS       current
    DESCRIPTION
        "Cisco Firepower equipment:PsuOutputStatsHist:voltageMin
        managed object property"
    ::= { cfprApEquipmentPsuOutputStatsHistEntry 20 }

cfprApEquipmentPsuStatsTable OBJECT-TYPE
    SYNTAX           SEQUENCE OF CfprApEquipmentPsuStatsEntry
    MAX-ACCESS       not-accessible
    STATUS           current
    DESCRIPTION
        "Cisco Firepower equipment:PsuStats managed object table"
    ::= { cfprApEquipmentObjects 118 }

cfprApEquipmentPsuStatsEntry OBJECT-TYPE
    SYNTAX           CfprApEquipmentPsuStatsEntry
    MAX-ACCESS       not-accessible
    STATUS           current
    DESCRIPTION
        "Entry for the cfprApEquipmentPsuStatsTable table."
    INDEX { cfprApEquipmentPsuStatsInstanceId }
    ::= { cfprApEquipmentPsuStatsTable 1 }

CfprApEquipmentPsuStatsEntry ::= SEQUENCE {
    cfprApEquipmentPsuStatsInstanceId                                CfprApManagedObjectId,
    cfprApEquipmentPsuStatsDn                                        CfprApManagedObjectDn,
    cfprApEquipmentPsuStatsRn                                        SnmpAdminString,
    cfprApEquipmentPsuStatsFanSpeed                                  Gauge32,
    cfprApEquipmentPsuStatsFanSpeedAvg                               Gauge32,
    cfprApEquipmentPsuStatsFanSpeedMax                               Gauge32,
    cfprApEquipmentPsuStatsFanSpeedMin                               Gauge32,
    cfprApEquipmentPsuStatsInput210v                                 INTEGER,
    cfprApEquipmentPsuStatsInput210vAvg                              INTEGER,
    cfprApEquipmentPsuStatsInput210vMax                              INTEGER,
    cfprApEquipmentPsuStatsInput210vMin                              INTEGER,
    cfprApEquipmentPsuStatsInputCurrent                              INTEGER,
    cfprApEquipmentPsuStatsInputCurrentAvg                           INTEGER,
    cfprApEquipmentPsuStatsInputCurrentMax                           INTEGER,
    cfprApEquipmentPsuStatsInputCurrentMin                           INTEGER,
    cfprApEquipmentPsuStatsInputPower                                INTEGER,
    cfprApEquipmentPsuStatsInputPowerAvg                             INTEGER,
    cfprApEquipmentPsuStatsInputPowerMax                             INTEGER,
    cfprApEquipmentPsuStatsInputPowerMin                             INTEGER,
    cfprApEquipmentPsuStatsIntervals                                 Gauge32,
    cfprApEquipmentPsuStatsPsuTemp1                                  INTEGER,
    cfprApEquipmentPsuStatsPsuTemp2                                  INTEGER,
    cfprApEquipmentPsuStatsPsuTemp3                                  INTEGER,
    cfprApEquipmentPsuStatsSuspect                                   TruthValue,
    cfprApEquipmentPsuStatsThresholded                               CfprApEquipmentPsuStatsThresholded,
    cfprApEquipmentPsuStatsTimeCollected                             DateAndTime,
    cfprApEquipmentPsuStatsUpdate                                    Gauge32
}

cfprApEquipmentPsuStatsInstanceId OBJECT-TYPE
    SYNTAX       CfprApManagedObjectId
    MAX-ACCESS   not-accessible
    STATUS       current
    DESCRIPTION
        "Instance identifier of the managed object."
    ::= { cfprApEquipmentPsuStatsEntry 1 }

cfprApEquipmentPsuStatsDn OBJECT-TYPE
    SYNTAX       CfprApManagedObjectDn
    MAX-ACCESS   read-only
    STATUS       current
    DESCRIPTION
        "Cisco Firepower equipment:PsuStats:dn managed object property"
    ::= { cfprApEquipmentPsuStatsEntry 2 }

cfprApEquipmentPsuStatsRn OBJECT-TYPE
    SYNTAX       SnmpAdminString
    MAX-ACCESS   read-only
    STATUS       current
    DESCRIPTION
        "Cisco Firepower equipment:PsuStats:rn managed object property"
    ::= { cfprApEquipmentPsuStatsEntry 3 }

cfprApEquipmentPsuStatsFanSpeed OBJECT-TYPE
    SYNTAX       Gauge32
    MAX-ACCESS   read-only
    STATUS       current
    DESCRIPTION
        "Cisco Firepower equipment:PsuStats:fanSpeed managed
        object property"
    ::= { cfprApEquipmentPsuStatsEntry 8 }

cfprApEquipmentPsuStatsFanSpeedAvg OBJECT-TYPE
    SYNTAX       Gauge32
    MAX-ACCESS   read-only
    STATUS       current
    DESCRIPTION
        "Cisco Firepower equipment:PsuStats:fanSpeedAvg
        managed object property"
    ::= { cfprApEquipmentPsuStatsEntry 9 }

cfprApEquipmentPsuStatsFanSpeedMax OBJECT-TYPE
    SYNTAX       Gauge32
    MAX-ACCESS   read-only
    STATUS       current
    DESCRIPTION
        "Cisco Firepower equipment:PsuStats:fanSpeedMax
        managed object property"
    ::= { cfprApEquipmentPsuStatsEntry 10 }

cfprApEquipmentPsuStatsFanSpeedMin OBJECT-TYPE
    SYNTAX       Gauge32
    MAX-ACCESS   read-only
    STATUS       current
    DESCRIPTION
        "Cisco Firepower equipment:PsuStats:fanSpeedMin
        managed object property"
    ::= { cfprApEquipmentPsuStatsEntry 11 }

cfprApEquipmentPsuStatsInput210v OBJECT-TYPE
    SYNTAX       INTEGER
    MAX-ACCESS   read-only
    STATUS       current
    DESCRIPTION
        "Cisco Firepower equipment:PsuStats:input210v managed
        object property"
    ::= { cfprApEquipmentPsuStatsEntry 12 }

cfprApEquipmentPsuStatsInput210vAvg OBJECT-TYPE
    SYNTAX       INTEGER
    MAX-ACCESS   read-only
    STATUS       current
    DESCRIPTION
        "Cisco Firepower equipment:PsuStats:input210vAvg
        managed object property"
    ::= { cfprApEquipmentPsuStatsEntry 13 }

cfprApEquipmentPsuStatsInput210vMax OBJECT-TYPE
    SYNTAX       INTEGER
    MAX-ACCESS   read-only
    STATUS       current
    DESCRIPTION
        "Cisco Firepower equipment:PsuStats:input210vMax
        managed object property"
    ::= { cfprApEquipmentPsuStatsEntry 14 }

cfprApEquipmentPsuStatsInput210vMin OBJECT-TYPE
    SYNTAX       INTEGER
    MAX-ACCESS   read-only
    STATUS       current
    DESCRIPTION
        "Cisco Firepower equipment:PsuStats:input210vMin
        managed object property"
    ::= { cfprApEquipmentPsuStatsEntry 15 }

cfprApEquipmentPsuStatsInputCurrent OBJECT-TYPE
    SYNTAX       INTEGER
    MAX-ACCESS   read-only
    STATUS       current
    DESCRIPTION
        "Cisco Firepower equipment:PsuStats:inputCurrent
        managed object property"
    ::= { cfprApEquipmentPsuStatsEntry 16 }

cfprApEquipmentPsuStatsInputCurrentAvg OBJECT-TYPE
    SYNTAX       INTEGER
    MAX-ACCESS   read-only
    STATUS       current
    DESCRIPTION
        "Cisco Firepower equipment:PsuStats:inputCurrentAvg
        managed object property"
    ::= { cfprApEquipmentPsuStatsEntry 17 }

cfprApEquipmentPsuStatsInputCurrentMax OBJECT-TYPE
    SYNTAX       INTEGER
    MAX-ACCESS   read-only
    STATUS       current
    DESCRIPTION
        "Cisco Firepower equipment:PsuStats:inputCurrentMax
        managed object property"
    ::= { cfprApEquipmentPsuStatsEntry 18 }

cfprApEquipmentPsuStatsInputCurrentMin OBJECT-TYPE
    SYNTAX       INTEGER
    MAX-ACCESS   read-only
    STATUS       current
    DESCRIPTION
        "Cisco Firepower equipment:PsuStats:inputCurrentMin
        managed object property"
    ::= { cfprApEquipmentPsuStatsEntry 19 }

cfprApEquipmentPsuStatsInputPower OBJECT-TYPE
    SYNTAX       INTEGER
    MAX-ACCESS   read-only
    STATUS       current
    DESCRIPTION
        "Cisco Firepower equipment:PsuStats:inputPower
        managed object property"
    ::= { cfprApEquipmentPsuStatsEntry 20 }

cfprApEquipmentPsuStatsInputPowerAvg OBJECT-TYPE
    SYNTAX       INTEGER
    MAX-ACCESS   read-only
    STATUS       current
    DESCRIPTION
        "Cisco Firepower equipment:PsuStats:inputPowerAvg
        managed object property"
    ::= { cfprApEquipmentPsuStatsEntry 21 }

cfprApEquipmentPsuStatsInputPowerMax OBJECT-TYPE
    SYNTAX       INTEGER
    MAX-ACCESS   read-only
    STATUS       current
    DESCRIPTION
        "Cisco Firepower equipment:PsuStats:inputPowerMax
        managed object property"
    ::= { cfprApEquipmentPsuStatsEntry 22 }

cfprApEquipmentPsuStatsInputPowerMin OBJECT-TYPE
    SYNTAX       INTEGER
    MAX-ACCESS   read-only
    STATUS       current
    DESCRIPTION
        "Cisco Firepower equipment:PsuStats:inputPowerMin
        managed object property"
    ::= { cfprApEquipmentPsuStatsEntry 23 }

cfprApEquipmentPsuStatsIntervals OBJECT-TYPE
    SYNTAX       Gauge32
    MAX-ACCESS   read-only
    STATUS       current
    DESCRIPTION
        "Cisco Firepower equipment:PsuStats:intervals managed
        object property"
    ::= { cfprApEquipmentPsuStatsEntry 24 }

cfprApEquipmentPsuStatsPsuTemp1 OBJECT-TYPE
    SYNTAX       INTEGER
    MAX-ACCESS   read-only
    STATUS       current
    DESCRIPTION
        "Cisco Firepower equipment:PsuStats:psuTemp1 managed
        object property"
    ::= { cfprApEquipmentPsuStatsEntry 41 }

cfprApEquipmentPsuStatsPsuTemp2 OBJECT-TYPE
    SYNTAX       INTEGER
    MAX-ACCESS   read-only
    STATUS       current
    DESCRIPTION
        "Cisco Firepower equipment:PsuStats:psuTemp2 managed
        object property"
    ::= { cfprApEquipmentPsuStatsEntry 42 }

cfprApEquipmentPsuStatsPsuTemp3 OBJECT-TYPE
    SYNTAX       INTEGER
    MAX-ACCESS   read-only
    STATUS       current
    DESCRIPTION
        "Cisco Firepower equipment:PsuStats:psuTemp3 managed
        object property"
    ::= { cfprApEquipmentPsuStatsEntry 43 }

cfprApEquipmentPsuStatsSuspect OBJECT-TYPE
    SYNTAX       TruthValue
    MAX-ACCESS   read-only
    STATUS       current
    DESCRIPTION
        "Cisco Firepower equipment:PsuStats:suspect managed
        object property"
    ::= { cfprApEquipmentPsuStatsEntry 44 }

cfprApEquipmentPsuStatsThresholded OBJECT-TYPE
    SYNTAX       CfprApEquipmentPsuStatsThresholded
    MAX-ACCESS   read-only
    STATUS       current
    DESCRIPTION
        "Cisco Firepower equipment:PsuStats:thresholded
        managed object property"
    ::= { cfprApEquipmentPsuStatsEntry 45 }

cfprApEquipmentPsuStatsTimeCollected OBJECT-TYPE
    SYNTAX       DateAndTime
    MAX-ACCESS   read-only
    STATUS       current
    DESCRIPTION
        "Cisco Firepower equipment:PsuStats:timeCollected
        managed object property"
    ::= { cfprApEquipmentPsuStatsEntry 46 }

cfprApEquipmentPsuStatsUpdate OBJECT-TYPE
    SYNTAX       Gauge32
    MAX-ACCESS   read-only
    STATUS       current
    DESCRIPTION
        "Cisco Firepower equipment:PsuStats:update managed
        object property"
    ::= { cfprApEquipmentPsuStatsEntry 47 }

cfprApEquipmentPsuStatsHistTable OBJECT-TYPE
    SYNTAX           SEQUENCE OF CfprApEquipmentPsuStatsHistEntry
    MAX-ACCESS       not-accessible
    STATUS           current
    DESCRIPTION
        "Cisco Firepower equipment:PsuStatsHist managed object table"
    ::= { cfprApEquipmentObjects 119 }

cfprApEquipmentPsuStatsHistEntry OBJECT-TYPE
    SYNTAX           CfprApEquipmentPsuStatsHistEntry
    MAX-ACCESS       not-accessible
    STATUS           current
    DESCRIPTION
        "Entry for the cfprApEquipmentPsuStatsHistTable table."
    INDEX { cfprApEquipmentPsuStatsHistInstanceId }
    ::= { cfprApEquipmentPsuStatsHistTable 1 }

CfprApEquipmentPsuStatsHistEntry ::= SEQUENCE {
    cfprApEquipmentPsuStatsHistInstanceId                            CfprApManagedObjectId,
    cfprApEquipmentPsuStatsHistDn                                    CfprApManagedObjectDn,
    cfprApEquipmentPsuStatsHistRn                                    SnmpAdminString,
    cfprApEquipmentPsuStatsHistFanSpeed                              Gauge32,
    cfprApEquipmentPsuStatsHistFanSpeedAvg                           Gauge32,
    cfprApEquipmentPsuStatsHistFanSpeedMax                           Gauge32,
    cfprApEquipmentPsuStatsHistFanSpeedMin                           Gauge32,
    cfprApEquipmentPsuStatsHistId                                    Unsigned64,
    cfprApEquipmentPsuStatsHistInput210v                             INTEGER,
    cfprApEquipmentPsuStatsHistInput210vAvg                          INTEGER,
    cfprApEquipmentPsuStatsHistInput210vMax                          INTEGER,
    cfprApEquipmentPsuStatsHistInput210vMin                          INTEGER,
    cfprApEquipmentPsuStatsHistInputCurrent                          INTEGER,
    cfprApEquipmentPsuStatsHistInputCurrentAvg                       INTEGER,
    cfprApEquipmentPsuStatsHistInputCurrentMax                       INTEGER,
    cfprApEquipmentPsuStatsHistInputCurrentMin                       INTEGER,
    cfprApEquipmentPsuStatsHistInputPower                            INTEGER,
    cfprApEquipmentPsuStatsHistInputPowerAvg                         INTEGER,
    cfprApEquipmentPsuStatsHistInputPowerMax                         INTEGER,
    cfprApEquipmentPsuStatsHistInputPowerMin                         INTEGER,
    cfprApEquipmentPsuStatsHistMostRecent                            TruthValue,
    cfprApEquipmentPsuStatsHistSuspect                               TruthValue,
    cfprApEquipmentPsuStatsHistThresholded                           CfprApEquipmentPsuStatsHistThresholded,
    cfprApEquipmentPsuStatsHistTimeCollected                         DateAndTime
}

cfprApEquipmentPsuStatsHistInstanceId OBJECT-TYPE
    SYNTAX       CfprApManagedObjectId
    MAX-ACCESS   not-accessible
    STATUS       current
    DESCRIPTION
        "Instance identifier of the managed object."
    ::= { cfprApEquipmentPsuStatsHistEntry 1 }

cfprApEquipmentPsuStatsHistDn OBJECT-TYPE
    SYNTAX       CfprApManagedObjectDn
    MAX-ACCESS   read-only
    STATUS       current
    DESCRIPTION
        "Cisco Firepower equipment:PsuStatsHist:dn managed
        object property"
    ::= { cfprApEquipmentPsuStatsHistEntry 2 }

cfprApEquipmentPsuStatsHistRn OBJECT-TYPE
    SYNTAX       SnmpAdminString
    MAX-ACCESS   read-only
    STATUS       current
    DESCRIPTION
        "Cisco Firepower equipment:PsuStatsHist:rn managed
        object property"
    ::= { cfprApEquipmentPsuStatsHistEntry 3 }

cfprApEquipmentPsuStatsHistFanSpeed OBJECT-TYPE
    SYNTAX       Gauge32
    MAX-ACCESS   read-only
    STATUS       current
    DESCRIPTION
        "Cisco Firepower equipment:PsuStatsHist:fanSpeed
        managed object property"
    ::= { cfprApEquipmentPsuStatsHistEntry 8 }

cfprApEquipmentPsuStatsHistFanSpeedAvg OBJECT-TYPE
    SYNTAX       Gauge32
    MAX-ACCESS   read-only
    STATUS       current
    DESCRIPTION
        "Cisco Firepower equipment:PsuStatsHist:fanSpeedAvg
        managed object property"
    ::= { cfprApEquipmentPsuStatsHistEntry 9 }

cfprApEquipmentPsuStatsHistFanSpeedMax OBJECT-TYPE
    SYNTAX       Gauge32
    MAX-ACCESS   read-only
    STATUS       current
    DESCRIPTION
        "Cisco Firepower equipment:PsuStatsHist:fanSpeedMax
        managed object property"
    ::= { cfprApEquipmentPsuStatsHistEntry 10 }

cfprApEquipmentPsuStatsHistFanSpeedMin OBJECT-TYPE
    SYNTAX       Gauge32
    MAX-ACCESS   read-only
    STATUS       current
    DESCRIPTION
        "Cisco Firepower equipment:PsuStatsHist:fanSpeedMin
        managed object property"
    ::= { cfprApEquipmentPsuStatsHistEntry 11 }

cfprApEquipmentPsuStatsHistId OBJECT-TYPE
    SYNTAX       Unsigned64
    MAX-ACCESS   read-only
    STATUS       current
    DESCRIPTION
        "Cisco Firepower equipment:PsuStatsHist:id managed
        object property"
    ::= { cfprApEquipmentPsuStatsHistEntry 12 }

cfprApEquipmentPsuStatsHistInput210v OBJECT-TYPE
    SYNTAX       INTEGER
    MAX-ACCESS   read-only
    STATUS       current
    DESCRIPTION
        "Cisco Firepower equipment:PsuStatsHist:input210v
        managed object property"
    ::= { cfprApEquipmentPsuStatsHistEntry 13 }

cfprApEquipmentPsuStatsHistInput210vAvg OBJECT-TYPE
    SYNTAX       INTEGER
    MAX-ACCESS   read-only
    STATUS       current
    DESCRIPTION
        "Cisco Firepower equipment:PsuStatsHist:input210vAvg
        managed object property"
    ::= { cfprApEquipmentPsuStatsHistEntry 14 }

cfprApEquipmentPsuStatsHistInput210vMax OBJECT-TYPE
    SYNTAX       INTEGER
    MAX-ACCESS   read-only
    STATUS       current
    DESCRIPTION
        "Cisco Firepower equipment:PsuStatsHist:input210vMax
        managed object property"
    ::= { cfprApEquipmentPsuStatsHistEntry 15 }

cfprApEquipmentPsuStatsHistInput210vMin OBJECT-TYPE
    SYNTAX       INTEGER
    MAX-ACCESS   read-only
    STATUS       current
    DESCRIPTION
        "Cisco Firepower equipment:PsuStatsHist:input210vMin
        managed object property"
    ::= { cfprApEquipmentPsuStatsHistEntry 16 }

cfprApEquipmentPsuStatsHistInputCurrent OBJECT-TYPE
    SYNTAX       INTEGER
    MAX-ACCESS   read-only
    STATUS       current
    DESCRIPTION
        "Cisco Firepower equipment:PsuStatsHist:inputCurrent
        managed object property"
    ::= { cfprApEquipmentPsuStatsHistEntry 17 }

cfprApEquipmentPsuStatsHistInputCurrentAvg OBJECT-TYPE
    SYNTAX       INTEGER
    MAX-ACCESS   read-only
    STATUS       current
    DESCRIPTION
        "Cisco Firepower equipment:PsuStatsHist:inputCurrentAvg
        managed object property"
    ::= { cfprApEquipmentPsuStatsHistEntry 18 }

cfprApEquipmentPsuStatsHistInputCurrentMax OBJECT-TYPE
    SYNTAX       INTEGER
    MAX-ACCESS   read-only
    STATUS       current
    DESCRIPTION
        "Cisco Firepower equipment:PsuStatsHist:inputCurrentMax
        managed object property"
    ::= { cfprApEquipmentPsuStatsHistEntry 19 }

cfprApEquipmentPsuStatsHistInputCurrentMin OBJECT-TYPE
    SYNTAX       INTEGER
    MAX-ACCESS   read-only
    STATUS       current
    DESCRIPTION
        "Cisco Firepower equipment:PsuStatsHist:inputCurrentMin
        managed object property"
    ::= { cfprApEquipmentPsuStatsHistEntry 20 }

cfprApEquipmentPsuStatsHistInputPower OBJECT-TYPE
    SYNTAX       INTEGER
    MAX-ACCESS   read-only
    STATUS       current
    DESCRIPTION
        "Cisco Firepower equipment:PsuStatsHist:inputPower
        managed object property"
    ::= { cfprApEquipmentPsuStatsHistEntry 21 }

cfprApEquipmentPsuStatsHistInputPowerAvg OBJECT-TYPE
    SYNTAX       INTEGER
    MAX-ACCESS   read-only
    STATUS       current
    DESCRIPTION
        "Cisco Firepower equipment:PsuStatsHist:inputPowerAvg
        managed object property"
    ::= { cfprApEquipmentPsuStatsHistEntry 22 }

cfprApEquipmentPsuStatsHistInputPowerMax OBJECT-TYPE
    SYNTAX       INTEGER
    MAX-ACCESS   read-only
    STATUS       current
    DESCRIPTION
        "Cisco Firepower equipment:PsuStatsHist:inputPowerMax
        managed object property"
    ::= { cfprApEquipmentPsuStatsHistEntry 23 }

cfprApEquipmentPsuStatsHistInputPowerMin OBJECT-TYPE
    SYNTAX       INTEGER
    MAX-ACCESS   read-only
    STATUS       current
    DESCRIPTION
        "Cisco Firepower equipment:PsuStatsHist:inputPowerMin
        managed object property"
    ::= { cfprApEquipmentPsuStatsHistEntry 24 }

cfprApEquipmentPsuStatsHistMostRecent OBJECT-TYPE
    SYNTAX       TruthValue
    MAX-ACCESS   read-only
    STATUS       current
    DESCRIPTION
        "Cisco Firepower equipment:PsuStatsHist:mostRecent
        managed object property"
    ::= { cfprApEquipmentPsuStatsHistEntry 25 }

cfprApEquipmentPsuStatsHistSuspect OBJECT-TYPE
    SYNTAX       TruthValue
    MAX-ACCESS   read-only
    STATUS       current
    DESCRIPTION
        "Cisco Firepower equipment:PsuStatsHist:suspect
        managed object property"
    ::= { cfprApEquipmentPsuStatsHistEntry 42 }

cfprApEquipmentPsuStatsHistThresholded OBJECT-TYPE
    SYNTAX       CfprApEquipmentPsuStatsHistThresholded
    MAX-ACCESS   read-only
    STATUS       current
    DESCRIPTION
        "Cisco Firepower equipment:PsuStatsHist:thresholded
        managed object property"
    ::= { cfprApEquipmentPsuStatsHistEntry 43 }

cfprApEquipmentPsuStatsHistTimeCollected OBJECT-TYPE
    SYNTAX       DateAndTime
    MAX-ACCESS   read-only
    STATUS       current
    DESCRIPTION
        "Cisco Firepower equipment:PsuStatsHist:timeCollected
        managed object property"
    ::= { cfprApEquipmentPsuStatsHistEntry 44 }

cfprApEquipmentRackFanModuleDefTable OBJECT-TYPE
    SYNTAX           SEQUENCE OF CfprApEquipmentRackFanModuleDefEntry
    MAX-ACCESS       not-accessible
    STATUS           current
    DESCRIPTION
        "Cisco Firepower equipment:RackFanModuleDef managed object table"
    ::= { cfprApEquipmentObjects 120 }

cfprApEquipmentRackFanModuleDefEntry OBJECT-TYPE
    SYNTAX           CfprApEquipmentRackFanModuleDefEntry
    MAX-ACCESS       not-accessible
    STATUS           current
    DESCRIPTION
        "Entry for the cfprApEquipmentRackFanModuleDefTable table."
    INDEX { cfprApEquipmentRackFanModuleDefInstanceId }
    ::= { cfprApEquipmentRackFanModuleDefTable 1 }

CfprApEquipmentRackFanModuleDefEntry ::= SEQUENCE {
    cfprApEquipmentRackFanModuleDefInstanceId                        CfprApManagedObjectId,
    cfprApEquipmentRackFanModuleDefDn                                CfprApManagedObjectDn,
    cfprApEquipmentRackFanModuleDefRn                                SnmpAdminString,
    cfprApEquipmentRackFanModuleDefDescr                             SnmpAdminString,
    cfprApEquipmentRackFanModuleDefFanCapacity                       Gauge32,
    cfprApEquipmentRackFanModuleDefIntId                             SnmpAdminString,
    cfprApEquipmentRackFanModuleDefName                              SnmpAdminString,
    cfprApEquipmentRackFanModuleDefPolicyLevel                       Gauge32,
    cfprApEquipmentRackFanModuleDefPolicyOwner                       CfprApPolicyPolicyOwner
}

cfprApEquipmentRackFanModuleDefInstanceId OBJECT-TYPE
    SYNTAX       CfprApManagedObjectId
    MAX-ACCESS   not-accessible
    STATUS       current
    DESCRIPTION
        "Instance identifier of the managed object."
    ::= { cfprApEquipmentRackFanModuleDefEntry 1 }

cfprApEquipmentRackFanModuleDefDn OBJECT-TYPE
    SYNTAX       CfprApManagedObjectDn
    MAX-ACCESS   read-only
    STATUS       current
    DESCRIPTION
        "Cisco Firepower equipment:RackFanModuleDef:dn
        managed object property"
    ::= { cfprApEquipmentRackFanModuleDefEntry 2 }

cfprApEquipmentRackFanModuleDefRn OBJECT-TYPE
    SYNTAX       SnmpAdminString
    MAX-ACCESS   read-only
    STATUS       current
    DESCRIPTION
        "Cisco Firepower equipment:RackFanModuleDef:rn
        managed object property"
    ::= { cfprApEquipmentRackFanModuleDefEntry 3 }

cfprApEquipmentRackFanModuleDefDescr OBJECT-TYPE
    SYNTAX       SnmpAdminString
    MAX-ACCESS   read-only
    STATUS       current
    DESCRIPTION
        "Cisco Firepower equipment:RackFanModuleDef:descr
        managed object property"
    ::= { cfprApEquipmentRackFanModuleDefEntry 4 }

cfprApEquipmentRackFanModuleDefFanCapacity OBJECT-TYPE
    SYNTAX       Gauge32
    MAX-ACCESS   read-only
    STATUS       current
    DESCRIPTION
        "Cisco Firepower equipment:RackFanModuleDef:fanCapacity
        managed object property"
    ::= { cfprApEquipmentRackFanModuleDefEntry 5 }

cfprApEquipmentRackFanModuleDefIntId OBJECT-TYPE
    SYNTAX       SnmpAdminString
    MAX-ACCESS   read-only
    STATUS       current
    DESCRIPTION
        "Cisco Firepower equipment:RackFanModuleDef:intId
        managed object property"
    ::= { cfprApEquipmentRackFanModuleDefEntry 6 }

cfprApEquipmentRackFanModuleDefName OBJECT-TYPE
    SYNTAX       SnmpAdminString
    MAX-ACCESS   read-only
    STATUS       current
    DESCRIPTION
        "Cisco Firepower equipment:RackFanModuleDef:name
        managed object property"
    ::= { cfprApEquipmentRackFanModuleDefEntry 7 }

cfprApEquipmentRackFanModuleDefPolicyLevel OBJECT-TYPE
    SYNTAX       Gauge32
    MAX-ACCESS   read-only
    STATUS       current
    DESCRIPTION
        "Cisco Firepower equipment:RackFanModuleDef:policyLevel
        managed object property"
    ::= { cfprApEquipmentRackFanModuleDefEntry 8 }

cfprApEquipmentRackFanModuleDefPolicyOwner OBJECT-TYPE
    SYNTAX       CfprApPolicyPolicyOwner
    MAX-ACCESS   read-only
    STATUS       current
    DESCRIPTION
        "Cisco Firepower equipment:RackFanModuleDef:policyOwner
        managed object property"
    ::= { cfprApEquipmentRackFanModuleDefEntry 9 }

cfprApEquipmentRackUnitCapProviderTable OBJECT-TYPE
    SYNTAX           SEQUENCE OF CfprApEquipmentRackUnitCapProviderEntry
    MAX-ACCESS       not-accessible
    STATUS           current
    DESCRIPTION
        "Cisco Firepower equipment:RackUnitCapProvider
        managed object table"
    ::= { cfprApEquipmentObjects 121 }

cfprApEquipmentRackUnitCapProviderEntry OBJECT-TYPE
    SYNTAX           CfprApEquipmentRackUnitCapProviderEntry
    MAX-ACCESS       not-accessible
    STATUS           current
    DESCRIPTION
        "Entry for the cfprApEquipmentRackUnitCapProviderTable table."
    INDEX { cfprApEquipmentRackUnitCapProviderInstanceId }
    ::= { cfprApEquipmentRackUnitCapProviderTable 1 }

CfprApEquipmentRackUnitCapProviderEntry ::= SEQUENCE {
    cfprApEquipmentRackUnitCapProviderInstanceId                     CfprApManagedObjectId,
    cfprApEquipmentRackUnitCapProviderDn                             CfprApManagedObjectDn,
    cfprApEquipmentRackUnitCapProviderRn                             SnmpAdminString,
    cfprApEquipmentRackUnitCapProviderDeleted                        TruthValue,
    cfprApEquipmentRackUnitCapProviderDeprecated                     TruthValue,
    cfprApEquipmentRackUnitCapProviderElementLoadFailures            Gauge32,
    cfprApEquipmentRackUnitCapProviderElementsLoaded                 Gauge32,
    cfprApEquipmentRackUnitCapProviderGencount                       Gauge32,
    cfprApEquipmentRackUnitCapProviderLoadErrors                     Gauge32,
    cfprApEquipmentRackUnitCapProviderLoadWarnings                   Gauge32,
    cfprApEquipmentRackUnitCapProviderMaxLocalDisks                  Gauge32,
    cfprApEquipmentRackUnitCapProviderMgmtPlaneVer                   SnmpAdminString,
    cfprApEquipmentRackUnitCapProviderModel                          SnmpAdminString,
    cfprApEquipmentRackUnitCapProviderPromCardType                   Gauge32,
    cfprApEquipmentRackUnitCapProviderRevision                       SnmpAdminString,
    cfprApEquipmentRackUnitCapProviderVendor                         SnmpAdminString
}

cfprApEquipmentRackUnitCapProviderInstanceId OBJECT-TYPE
    SYNTAX       CfprApManagedObjectId
    MAX-ACCESS   not-accessible
    STATUS       current
    DESCRIPTION
        "Instance identifier of the managed object."
    ::= { cfprApEquipmentRackUnitCapProviderEntry 1 }

cfprApEquipmentRackUnitCapProviderDn OBJECT-TYPE
    SYNTAX       CfprApManagedObjectDn
    MAX-ACCESS   read-only
    STATUS       current
    DESCRIPTION
        "Cisco Firepower equipment:RackUnitCapProvider:dn
        managed object property"
    ::= { cfprApEquipmentRackUnitCapProviderEntry 2 }

cfprApEquipmentRackUnitCapProviderRn OBJECT-TYPE
    SYNTAX       SnmpAdminString
    MAX-ACCESS   read-only
    STATUS       current
    DESCRIPTION
        "Cisco Firepower equipment:RackUnitCapProvider:rn
        managed object property"
    ::= { cfprApEquipmentRackUnitCapProviderEntry 3 }

cfprApEquipmentRackUnitCapProviderDeleted OBJECT-TYPE
    SYNTAX       TruthValue
    MAX-ACCESS   read-only
    STATUS       current
    DESCRIPTION
        "Cisco Firepower equipment:RackUnitCapProvider:deleted
        managed object property"
    ::= { cfprApEquipmentRackUnitCapProviderEntry 4 }

cfprApEquipmentRackUnitCapProviderDeprecated OBJECT-TYPE
    SYNTAX       TruthValue
    MAX-ACCESS   read-only
    STATUS       current
    DESCRIPTION
        "Cisco Firepower equipment:RackUnitCapProvider:deprecated
        managed object property"
    ::= { cfprApEquipmentRackUnitCapProviderEntry 5 }

cfprApEquipmentRackUnitCapProviderElementLoadFailures OBJECT-TYPE
    SYNTAX       Gauge32
    MAX-ACCESS   read-only
    STATUS       current
    DESCRIPTION
        "Cisco Firepower equipment:RackUnitCapProvider:elementLoadFailures
         managed object property"
    ::= { cfprApEquipmentRackUnitCapProviderEntry 6 }

cfprApEquipmentRackUnitCapProviderElementsLoaded OBJECT-TYPE
    SYNTAX       Gauge32
    MAX-ACCESS   read-only
    STATUS       current
    DESCRIPTION
        "Cisco Firepower equipment:RackUnitCapProvider:elementsLoaded
        managed object property"
    ::= { cfprApEquipmentRackUnitCapProviderEntry 7 }

cfprApEquipmentRackUnitCapProviderGencount OBJECT-TYPE
    SYNTAX       Gauge32
    MAX-ACCESS   read-only
    STATUS       current
    DESCRIPTION
        "Cisco Firepower equipment:RackUnitCapProvider:gencount
        managed object property"
    ::= { cfprApEquipmentRackUnitCapProviderEntry 8 }

cfprApEquipmentRackUnitCapProviderLoadErrors OBJECT-TYPE
    SYNTAX       Gauge32
    MAX-ACCESS   read-only
    STATUS       current
    DESCRIPTION
        "Cisco Firepower equipment:RackUnitCapProvider:loadErrors
        managed object property"
    ::= { cfprApEquipmentRackUnitCapProviderEntry 9 }

cfprApEquipmentRackUnitCapProviderLoadWarnings OBJECT-TYPE
    SYNTAX       Gauge32
    MAX-ACCESS   read-only
    STATUS       current
    DESCRIPTION
        "Cisco Firepower equipment:RackUnitCapProvider:loadWarnings
        managed object property"
    ::= { cfprApEquipmentRackUnitCapProviderEntry 10 }

cfprApEquipmentRackUnitCapProviderMaxLocalDisks OBJECT-TYPE
    SYNTAX       Gauge32
    MAX-ACCESS   read-only
    STATUS       current
    DESCRIPTION
        "Cisco Firepower equipment:RackUnitCapProvider:maxLocalDisks
        managed object property"
    ::= { cfprApEquipmentRackUnitCapProviderEntry 11 }

cfprApEquipmentRackUnitCapProviderMgmtPlaneVer OBJECT-TYPE
    SYNTAX       SnmpAdminString
    MAX-ACCESS   read-only
    STATUS       current
    DESCRIPTION
        "Cisco Firepower equipment:RackUnitCapProvider:mgmtPlaneVer
        managed object property"
    ::= { cfprApEquipmentRackUnitCapProviderEntry 12 }

cfprApEquipmentRackUnitCapProviderModel OBJECT-TYPE
    SYNTAX       SnmpAdminString
    MAX-ACCESS   read-only
    STATUS       current
    DESCRIPTION
        "Cisco Firepower equipment:RackUnitCapProvider:model
        managed object property"
    ::= { cfprApEquipmentRackUnitCapProviderEntry 13 }

cfprApEquipmentRackUnitCapProviderPromCardType OBJECT-TYPE
    SYNTAX       Gauge32
    MAX-ACCESS   read-only
    STATUS       current
    DESCRIPTION
        "Cisco Firepower equipment:RackUnitCapProvider:promCardType
        managed object property"
    ::= { cfprApEquipmentRackUnitCapProviderEntry 14 }

cfprApEquipmentRackUnitCapProviderRevision OBJECT-TYPE
    SYNTAX       SnmpAdminString
    MAX-ACCESS   read-only
    STATUS       current
    DESCRIPTION
        "Cisco Firepower equipment:RackUnitCapProvider:revision
        managed object property"
    ::= { cfprApEquipmentRackUnitCapProviderEntry 15 }

cfprApEquipmentRackUnitCapProviderVendor OBJECT-TYPE
    SYNTAX       SnmpAdminString
    MAX-ACCESS   read-only
    STATUS       current
    DESCRIPTION
        "Cisco Firepower equipment:RackUnitCapProvider:vendor
        managed object property"
    ::= { cfprApEquipmentRackUnitCapProviderEntry 16 }

cfprApEquipmentRackUnitFanStatsTable OBJECT-TYPE
    SYNTAX           SEQUENCE OF CfprApEquipmentRackUnitFanStatsEntry
    MAX-ACCESS       not-accessible
    STATUS           current
    DESCRIPTION
        "Cisco Firepower equipment:RackUnitFanStats managed object table"
    ::= { cfprApEquipmentObjects 122 }

cfprApEquipmentRackUnitFanStatsEntry OBJECT-TYPE
    SYNTAX           CfprApEquipmentRackUnitFanStatsEntry
    MAX-ACCESS       not-accessible
    STATUS           current
    DESCRIPTION
        "Entry for the cfprApEquipmentRackUnitFanStatsTable table."
    INDEX { cfprApEquipmentRackUnitFanStatsInstanceId }
    ::= { cfprApEquipmentRackUnitFanStatsTable 1 }

CfprApEquipmentRackUnitFanStatsEntry ::= SEQUENCE {
    cfprApEquipmentRackUnitFanStatsInstanceId                        CfprApManagedObjectId,
    cfprApEquipmentRackUnitFanStatsDn                                CfprApManagedObjectDn,
    cfprApEquipmentRackUnitFanStatsRn                                SnmpAdminString,
    cfprApEquipmentRackUnitFanStatsIntervals                         Gauge32,
    cfprApEquipmentRackUnitFanStatsSpeed                             Gauge32,
    cfprApEquipmentRackUnitFanStatsSpeedAvg                          Gauge32,
    cfprApEquipmentRackUnitFanStatsSpeedMax                          Gauge32,
    cfprApEquipmentRackUnitFanStatsSpeedMin                          Gauge32,
    cfprApEquipmentRackUnitFanStatsSuspect                           TruthValue,
    cfprApEquipmentRackUnitFanStatsThresholded                       CfprApEquipmentRackUnitFanStatsThresholded,
    cfprApEquipmentRackUnitFanStatsTimeCollected                     DateAndTime,
    cfprApEquipmentRackUnitFanStatsUpdate                            Gauge32
}

cfprApEquipmentRackUnitFanStatsInstanceId OBJECT-TYPE
    SYNTAX       CfprApManagedObjectId
    MAX-ACCESS   not-accessible
    STATUS       current
    DESCRIPTION
        "Instance identifier of the managed object."
    ::= { cfprApEquipmentRackUnitFanStatsEntry 1 }

cfprApEquipmentRackUnitFanStatsDn OBJECT-TYPE
    SYNTAX       CfprApManagedObjectDn
    MAX-ACCESS   read-only
    STATUS       current
    DESCRIPTION
        "Cisco Firepower equipment:RackUnitFanStats:dn
        managed object property"
    ::= { cfprApEquipmentRackUnitFanStatsEntry 2 }

cfprApEquipmentRackUnitFanStatsRn OBJECT-TYPE
    SYNTAX       SnmpAdminString
    MAX-ACCESS   read-only
    STATUS       current
    DESCRIPTION
        "Cisco Firepower equipment:RackUnitFanStats:rn
        managed object property"
    ::= { cfprApEquipmentRackUnitFanStatsEntry 3 }

cfprApEquipmentRackUnitFanStatsIntervals OBJECT-TYPE
    SYNTAX       Gauge32
    MAX-ACCESS   read-only
    STATUS       current
    DESCRIPTION
        "Cisco Firepower equipment:RackUnitFanStats:intervals
        managed object property"
    ::= { cfprApEquipmentRackUnitFanStatsEntry 4 }

cfprApEquipmentRackUnitFanStatsSpeed OBJECT-TYPE
    SYNTAX       Gauge32
    MAX-ACCESS   read-only
    STATUS       current
    DESCRIPTION
        "Cisco Firepower equipment:RackUnitFanStats:speed
        managed object property"
    ::= { cfprApEquipmentRackUnitFanStatsEntry 5 }

cfprApEquipmentRackUnitFanStatsSpeedAvg OBJECT-TYPE
    SYNTAX       Gauge32
    MAX-ACCESS   read-only
    STATUS       current
    DESCRIPTION
        "Cisco Firepower equipment:RackUnitFanStats:speedAvg
        managed object property"
    ::= { cfprApEquipmentRackUnitFanStatsEntry 6 }

cfprApEquipmentRackUnitFanStatsSpeedMax OBJECT-TYPE
    SYNTAX       Gauge32
    MAX-ACCESS   read-only
    STATUS       current
    DESCRIPTION
        "Cisco Firepower equipment:RackUnitFanStats:speedMax
        managed object property"
    ::= { cfprApEquipmentRackUnitFanStatsEntry 7 }

cfprApEquipmentRackUnitFanStatsSpeedMin OBJECT-TYPE
    SYNTAX       Gauge32
    MAX-ACCESS   read-only
    STATUS       current
    DESCRIPTION
        "Cisco Firepower equipment:RackUnitFanStats:speedMin
        managed object property"
    ::= { cfprApEquipmentRackUnitFanStatsEntry 8 }

cfprApEquipmentRackUnitFanStatsSuspect OBJECT-TYPE
    SYNTAX       TruthValue
    MAX-ACCESS   read-only
    STATUS       current
    DESCRIPTION
        "Cisco Firepower equipment:RackUnitFanStats:suspect
        managed object property"
    ::= { cfprApEquipmentRackUnitFanStatsEntry 9 }

cfprApEquipmentRackUnitFanStatsThresholded OBJECT-TYPE
    SYNTAX       CfprApEquipmentRackUnitFanStatsThresholded
    MAX-ACCESS   read-only
    STATUS       current
    DESCRIPTION
        "Cisco Firepower equipment:RackUnitFanStats:thresholded
        managed object property"
    ::= { cfprApEquipmentRackUnitFanStatsEntry 10 }

cfprApEquipmentRackUnitFanStatsTimeCollected OBJECT-TYPE
    SYNTAX       DateAndTime
    MAX-ACCESS   read-only
    STATUS       current
    DESCRIPTION
        "Cisco Firepower equipment:RackUnitFanStats:timeCollected
        managed object property"
    ::= { cfprApEquipmentRackUnitFanStatsEntry 11 }

cfprApEquipmentRackUnitFanStatsUpdate OBJECT-TYPE
    SYNTAX       Gauge32
    MAX-ACCESS   read-only
    STATUS       current
    DESCRIPTION
        "Cisco Firepower equipment:RackUnitFanStats:update
        managed object property"
    ::= { cfprApEquipmentRackUnitFanStatsEntry 12 }

cfprApEquipmentRackUnitFanStatsHistTable OBJECT-TYPE
    SYNTAX           SEQUENCE OF CfprApEquipmentRackUnitFanStatsHistEntry
    MAX-ACCESS       not-accessible
    STATUS           current
    DESCRIPTION
        "Cisco Firepower equipment:RackUnitFanStatsHist
        managed object table"
    ::= { cfprApEquipmentObjects 123 }

cfprApEquipmentRackUnitFanStatsHistEntry OBJECT-TYPE
    SYNTAX           CfprApEquipmentRackUnitFanStatsHistEntry
    MAX-ACCESS       not-accessible
    STATUS           current
    DESCRIPTION
        "Entry for the cfprApEquipmentRackUnitFanStatsHistTable table."
    INDEX { cfprApEquipmentRackUnitFanStatsHistInstanceId }
    ::= { cfprApEquipmentRackUnitFanStatsHistTable 1 }

CfprApEquipmentRackUnitFanStatsHistEntry ::= SEQUENCE {
    cfprApEquipmentRackUnitFanStatsHistInstanceId                    CfprApManagedObjectId,
    cfprApEquipmentRackUnitFanStatsHistDn                            CfprApManagedObjectDn,
    cfprApEquipmentRackUnitFanStatsHistRn                            SnmpAdminString,
    cfprApEquipmentRackUnitFanStatsHistId                            Unsigned64,
    cfprApEquipmentRackUnitFanStatsHistMostRecent                    TruthValue,
    cfprApEquipmentRackUnitFanStatsHistSpeed                         Gauge32,
    cfprApEquipmentRackUnitFanStatsHistSpeedAvg                      Gauge32,
    cfprApEquipmentRackUnitFanStatsHistSpeedMax                      Gauge32,
    cfprApEquipmentRackUnitFanStatsHistSpeedMin                      Gauge32,
    cfprApEquipmentRackUnitFanStatsHistSuspect                       TruthValue,
    cfprApEquipmentRackUnitFanStatsHistThresholded                   CfprApEquipmentRackUnitFanStatsHistThresholded,
    cfprApEquipmentRackUnitFanStatsHistTimeCollected                 DateAndTime
}

cfprApEquipmentRackUnitFanStatsHistInstanceId OBJECT-TYPE
    SYNTAX       CfprApManagedObjectId
    MAX-ACCESS   not-accessible
    STATUS       current
    DESCRIPTION
        "Instance identifier of the managed object."
    ::= { cfprApEquipmentRackUnitFanStatsHistEntry 1 }

cfprApEquipmentRackUnitFanStatsHistDn OBJECT-TYPE
    SYNTAX       CfprApManagedObjectDn
    MAX-ACCESS   read-only
    STATUS       current
    DESCRIPTION
        "Cisco Firepower equipment:RackUnitFanStatsHist:dn
        managed object property"
    ::= { cfprApEquipmentRackUnitFanStatsHistEntry 2 }

cfprApEquipmentRackUnitFanStatsHistRn OBJECT-TYPE
    SYNTAX       SnmpAdminString
    MAX-ACCESS   read-only
    STATUS       current
    DESCRIPTION
        "Cisco Firepower equipment:RackUnitFanStatsHist:rn
        managed object property"
    ::= { cfprApEquipmentRackUnitFanStatsHistEntry 3 }

cfprApEquipmentRackUnitFanStatsHistId OBJECT-TYPE
    SYNTAX       Unsigned64
    MAX-ACCESS   read-only
    STATUS       current
    DESCRIPTION
        "Cisco Firepower equipment:RackUnitFanStatsHist:id
        managed object property"
    ::= { cfprApEquipmentRackUnitFanStatsHistEntry 4 }

cfprApEquipmentRackUnitFanStatsHistMostRecent OBJECT-TYPE
    SYNTAX       TruthValue
    MAX-ACCESS   read-only
    STATUS       current
    DESCRIPTION
        "Cisco Firepower equipment:RackUnitFanStatsHist:mostRecent
        managed object property"
    ::= { cfprApEquipmentRackUnitFanStatsHistEntry 5 }

cfprApEquipmentRackUnitFanStatsHistSpeed OBJECT-TYPE
    SYNTAX       Gauge32
    MAX-ACCESS   read-only
    STATUS       current
    DESCRIPTION
        "Cisco Firepower equipment:RackUnitFanStatsHist:speed
        managed object property"
    ::= { cfprApEquipmentRackUnitFanStatsHistEntry 6 }

cfprApEquipmentRackUnitFanStatsHistSpeedAvg OBJECT-TYPE
    SYNTAX       Gauge32
    MAX-ACCESS   read-only
    STATUS       current
    DESCRIPTION
        "Cisco Firepower equipment:RackUnitFanStatsHist:speedAvg
        managed object property"
    ::= { cfprApEquipmentRackUnitFanStatsHistEntry 7 }

cfprApEquipmentRackUnitFanStatsHistSpeedMax OBJECT-TYPE
    SYNTAX       Gauge32
    MAX-ACCESS   read-only
    STATUS       current
    DESCRIPTION
        "Cisco Firepower equipment:RackUnitFanStatsHist:speedMax
        managed object property"
    ::= { cfprApEquipmentRackUnitFanStatsHistEntry 8 }

cfprApEquipmentRackUnitFanStatsHistSpeedMin OBJECT-TYPE
    SYNTAX       Gauge32
    MAX-ACCESS   read-only
    STATUS       current
    DESCRIPTION
        "Cisco Firepower equipment:RackUnitFanStatsHist:speedMin
        managed object property"
    ::= { cfprApEquipmentRackUnitFanStatsHistEntry 9 }

cfprApEquipmentRackUnitFanStatsHistSuspect OBJECT-TYPE
    SYNTAX       TruthValue
    MAX-ACCESS   read-only
    STATUS       current
    DESCRIPTION
        "Cisco Firepower equipment:RackUnitFanStatsHist:suspect
        managed object property"
    ::= { cfprApEquipmentRackUnitFanStatsHistEntry 10 }

cfprApEquipmentRackUnitFanStatsHistThresholded OBJECT-TYPE
    SYNTAX       CfprApEquipmentRackUnitFanStatsHistThresholded
    MAX-ACCESS   read-only
    STATUS       current
    DESCRIPTION
        "Cisco Firepower equipment:RackUnitFanStatsHist:thresholded
        managed object property"
    ::= { cfprApEquipmentRackUnitFanStatsHistEntry 11 }

cfprApEquipmentRackUnitFanStatsHistTimeCollected OBJECT-TYPE
    SYNTAX       DateAndTime
    MAX-ACCESS   read-only
    STATUS       current
    DESCRIPTION
        "Cisco Firepower equipment:RackUnitFanStatsHist:timeCollected
        managed object property"
    ::= { cfprApEquipmentRackUnitFanStatsHistEntry 12 }

cfprApEquipmentRackUnitPsuStatsTable OBJECT-TYPE
    SYNTAX           SEQUENCE OF CfprApEquipmentRackUnitPsuStatsEntry
    MAX-ACCESS       not-accessible
    STATUS           current
    DESCRIPTION
        "Cisco Firepower equipment:RackUnitPsuStats managed object table"
    ::= { cfprApEquipmentObjects 124 }

cfprApEquipmentRackUnitPsuStatsEntry OBJECT-TYPE
    SYNTAX           CfprApEquipmentRackUnitPsuStatsEntry
    MAX-ACCESS       not-accessible
    STATUS           current
    DESCRIPTION
        "Entry for the cfprApEquipmentRackUnitPsuStatsTable table."
    INDEX { cfprApEquipmentRackUnitPsuStatsInstanceId }
    ::= { cfprApEquipmentRackUnitPsuStatsTable 1 }

CfprApEquipmentRackUnitPsuStatsEntry ::= SEQUENCE {
    cfprApEquipmentRackUnitPsuStatsInstanceId                        CfprApManagedObjectId,
    cfprApEquipmentRackUnitPsuStatsDn                                CfprApManagedObjectDn,
    cfprApEquipmentRackUnitPsuStatsRn                                SnmpAdminString,
    cfprApEquipmentRackUnitPsuStatsAmbientTemp                       INTEGER,
    cfprApEquipmentRackUnitPsuStatsAmbientTempAvg                    INTEGER,
    cfprApEquipmentRackUnitPsuStatsAmbientTempMax                    INTEGER,
    cfprApEquipmentRackUnitPsuStatsAmbientTempMin                    INTEGER,
    cfprApEquipmentRackUnitPsuStatsInputPower                        INTEGER,
    cfprApEquipmentRackUnitPsuStatsInputPowerAvg                     INTEGER,
    cfprApEquipmentRackUnitPsuStatsInputPowerMax                     INTEGER,
    cfprApEquipmentRackUnitPsuStatsInputPowerMin                     INTEGER,
    cfprApEquipmentRackUnitPsuStatsInputVoltage                      INTEGER,
    cfprApEquipmentRackUnitPsuStatsInputVoltageAvg                   INTEGER,
    cfprApEquipmentRackUnitPsuStatsInputVoltageMax                   INTEGER,
    cfprApEquipmentRackUnitPsuStatsInputVoltageMin                   INTEGER,
    cfprApEquipmentRackUnitPsuStatsIntervals                         Gauge32,
    cfprApEquipmentRackUnitPsuStatsOutputCurrent                     INTEGER,
    cfprApEquipmentRackUnitPsuStatsOutputCurrentAvg                  INTEGER,
    cfprApEquipmentRackUnitPsuStatsOutputCurrentMax                  INTEGER,
    cfprApEquipmentRackUnitPsuStatsOutputCurrentMin                  INTEGER,
    cfprApEquipmentRackUnitPsuStatsOutputPower                       INTEGER,
    cfprApEquipmentRackUnitPsuStatsOutputPowerAvg                    INTEGER,
    cfprApEquipmentRackUnitPsuStatsOutputPowerMax                    INTEGER,
    cfprApEquipmentRackUnitPsuStatsOutputPowerMin                    INTEGER,
    cfprApEquipmentRackUnitPsuStatsOutputVoltage                     INTEGER,
    cfprApEquipmentRackUnitPsuStatsOutputVoltageAvg                  INTEGER,
    cfprApEquipmentRackUnitPsuStatsOutputVoltageMax                  INTEGER,
    cfprApEquipmentRackUnitPsuStatsOutputVoltageMin                  INTEGER,
    cfprApEquipmentRackUnitPsuStatsSuspect                           TruthValue,
    cfprApEquipmentRackUnitPsuStatsThresholded                       CfprApEquipmentRackUnitPsuStatsThresholded,
    cfprApEquipmentRackUnitPsuStatsTimeCollected                     DateAndTime,
    cfprApEquipmentRackUnitPsuStatsUpdate                            Gauge32
}

cfprApEquipmentRackUnitPsuStatsInstanceId OBJECT-TYPE
    SYNTAX       CfprApManagedObjectId
    MAX-ACCESS   not-accessible
    STATUS       current
    DESCRIPTION
        "Instance identifier of the managed object."
    ::= { cfprApEquipmentRackUnitPsuStatsEntry 1 }

cfprApEquipmentRackUnitPsuStatsDn OBJECT-TYPE
    SYNTAX       CfprApManagedObjectDn
    MAX-ACCESS   read-only
    STATUS       current
    DESCRIPTION
        "Cisco Firepower equipment:RackUnitPsuStats:dn
        managed object property"
    ::= { cfprApEquipmentRackUnitPsuStatsEntry 2 }

cfprApEquipmentRackUnitPsuStatsRn OBJECT-TYPE
    SYNTAX       SnmpAdminString
    MAX-ACCESS   read-only
    STATUS       current
    DESCRIPTION
        "Cisco Firepower equipment:RackUnitPsuStats:rn
        managed object property"
    ::= { cfprApEquipmentRackUnitPsuStatsEntry 3 }

cfprApEquipmentRackUnitPsuStatsAmbientTemp OBJECT-TYPE
    SYNTAX       INTEGER
    MAX-ACCESS   read-only
    STATUS       current
    DESCRIPTION
        "Cisco Firepower equipment:RackUnitPsuStats:ambientTemp
        managed object property"
    ::= { cfprApEquipmentRackUnitPsuStatsEntry 4 }

cfprApEquipmentRackUnitPsuStatsAmbientTempAvg OBJECT-TYPE
    SYNTAX       INTEGER
    MAX-ACCESS   read-only
    STATUS       current
    DESCRIPTION
        "Cisco Firepower equipment:RackUnitPsuStats:ambientTempAvg
        managed object property"
    ::= { cfprApEquipmentRackUnitPsuStatsEntry 5 }

cfprApEquipmentRackUnitPsuStatsAmbientTempMax OBJECT-TYPE
    SYNTAX       INTEGER
    MAX-ACCESS   read-only
    STATUS       current
    DESCRIPTION
        "Cisco Firepower equipment:RackUnitPsuStats:ambientTempMax
        managed object property"
    ::= { cfprApEquipmentRackUnitPsuStatsEntry 6 }

cfprApEquipmentRackUnitPsuStatsAmbientTempMin OBJECT-TYPE
    SYNTAX       INTEGER
    MAX-ACCESS   read-only
    STATUS       current
    DESCRIPTION
        "Cisco Firepower equipment:RackUnitPsuStats:ambientTempMin
        managed object property"
    ::= { cfprApEquipmentRackUnitPsuStatsEntry 7 }

cfprApEquipmentRackUnitPsuStatsInputPower OBJECT-TYPE
    SYNTAX       INTEGER
    MAX-ACCESS   read-only
    STATUS       current
    DESCRIPTION
        "Cisco Firepower equipment:RackUnitPsuStats:inputPower
        managed object property"
    ::= { cfprApEquipmentRackUnitPsuStatsEntry 8 }

cfprApEquipmentRackUnitPsuStatsInputPowerAvg OBJECT-TYPE
    SYNTAX       INTEGER
    MAX-ACCESS   read-only
    STATUS       current
    DESCRIPTION
        "Cisco Firepower equipment:RackUnitPsuStats:inputPowerAvg
        managed object property"
    ::= { cfprApEquipmentRackUnitPsuStatsEntry 9 }

cfprApEquipmentRackUnitPsuStatsInputPowerMax OBJECT-TYPE
    SYNTAX       INTEGER
    MAX-ACCESS   read-only
    STATUS       current
    DESCRIPTION
        "Cisco Firepower equipment:RackUnitPsuStats:inputPowerMax
        managed object property"
    ::= { cfprApEquipmentRackUnitPsuStatsEntry 10 }

cfprApEquipmentRackUnitPsuStatsInputPowerMin OBJECT-TYPE
    SYNTAX       INTEGER
    MAX-ACCESS   read-only
    STATUS       current
    DESCRIPTION
        "Cisco Firepower equipment:RackUnitPsuStats:inputPowerMin
        managed object property"
    ::= { cfprApEquipmentRackUnitPsuStatsEntry 11 }

cfprApEquipmentRackUnitPsuStatsInputVoltage OBJECT-TYPE
    SYNTAX       INTEGER
    MAX-ACCESS   read-only
    STATUS       current
    DESCRIPTION
        "Cisco Firepower equipment:RackUnitPsuStats:inputVoltage
        managed object property"
    ::= { cfprApEquipmentRackUnitPsuStatsEntry 12 }

cfprApEquipmentRackUnitPsuStatsInputVoltageAvg OBJECT-TYPE
    SYNTAX       INTEGER
    MAX-ACCESS   read-only
    STATUS       current
    DESCRIPTION
        "Cisco Firepower equipment:RackUnitPsuStats:inputVoltageAvg
        managed object property"
    ::= { cfprApEquipmentRackUnitPsuStatsEntry 13 }

cfprApEquipmentRackUnitPsuStatsInputVoltageMax OBJECT-TYPE
    SYNTAX       INTEGER
    MAX-ACCESS   read-only
    STATUS       current
    DESCRIPTION
        "Cisco Firepower equipment:RackUnitPsuStats:inputVoltageMax
        managed object property"
    ::= { cfprApEquipmentRackUnitPsuStatsEntry 14 }

cfprApEquipmentRackUnitPsuStatsInputVoltageMin OBJECT-TYPE
    SYNTAX       INTEGER
    MAX-ACCESS   read-only
    STATUS       current
    DESCRIPTION
        "Cisco Firepower equipment:RackUnitPsuStats:inputVoltageMin
        managed object property"
    ::= { cfprApEquipmentRackUnitPsuStatsEntry 15 }

cfprApEquipmentRackUnitPsuStatsIntervals OBJECT-TYPE
    SYNTAX       Gauge32
    MAX-ACCESS   read-only
    STATUS       current
    DESCRIPTION
        "Cisco Firepower equipment:RackUnitPsuStats:intervals
        managed object property"
    ::= { cfprApEquipmentRackUnitPsuStatsEntry 16 }

cfprApEquipmentRackUnitPsuStatsOutputCurrent OBJECT-TYPE
    SYNTAX       INTEGER
    MAX-ACCESS   read-only
    STATUS       current
    DESCRIPTION
        "Cisco Firepower equipment:RackUnitPsuStats:outputCurrent
        managed object property"
    ::= { cfprApEquipmentRackUnitPsuStatsEntry 17 }

cfprApEquipmentRackUnitPsuStatsOutputCurrentAvg OBJECT-TYPE
    SYNTAX       INTEGER
    MAX-ACCESS   read-only
    STATUS       current
    DESCRIPTION
        "Cisco Firepower equipment:RackUnitPsuStats:outputCurrentAvg
        managed object property"
    ::= { cfprApEquipmentRackUnitPsuStatsEntry 18 }

cfprApEquipmentRackUnitPsuStatsOutputCurrentMax OBJECT-TYPE
    SYNTAX       INTEGER
    MAX-ACCESS   read-only
    STATUS       current
    DESCRIPTION
        "Cisco Firepower equipment:RackUnitPsuStats:outputCurrentMax
        managed object property"
    ::= { cfprApEquipmentRackUnitPsuStatsEntry 19 }

cfprApEquipmentRackUnitPsuStatsOutputCurrentMin OBJECT-TYPE
    SYNTAX       INTEGER
    MAX-ACCESS   read-only
    STATUS       current
    DESCRIPTION
        "Cisco Firepower equipment:RackUnitPsuStats:outputCurrentMin
        managed object property"
    ::= { cfprApEquipmentRackUnitPsuStatsEntry 20 }

cfprApEquipmentRackUnitPsuStatsOutputPower OBJECT-TYPE
    SYNTAX       INTEGER
    MAX-ACCESS   read-only
    STATUS       current
    DESCRIPTION
        "Cisco Firepower equipment:RackUnitPsuStats:outputPower
        managed object property"
    ::= { cfprApEquipmentRackUnitPsuStatsEntry 21 }

cfprApEquipmentRackUnitPsuStatsOutputPowerAvg OBJECT-TYPE
    SYNTAX       INTEGER
    MAX-ACCESS   read-only
    STATUS       current
    DESCRIPTION
        "Cisco Firepower equipment:RackUnitPsuStats:outputPowerAvg
        managed object property"
    ::= { cfprApEquipmentRackUnitPsuStatsEntry 22 }

cfprApEquipmentRackUnitPsuStatsOutputPowerMax OBJECT-TYPE
    SYNTAX       INTEGER
    MAX-ACCESS   read-only
    STATUS       current
    DESCRIPTION
        "Cisco Firepower equipment:RackUnitPsuStats:outputPowerMax
        managed object property"
    ::= { cfprApEquipmentRackUnitPsuStatsEntry 23 }

cfprApEquipmentRackUnitPsuStatsOutputPowerMin OBJECT-TYPE
    SYNTAX       INTEGER
    MAX-ACCESS   read-only
    STATUS       current
    DESCRIPTION
        "Cisco Firepower equipment:RackUnitPsuStats:outputPowerMin
        managed object property"
    ::= { cfprApEquipmentRackUnitPsuStatsEntry 24 }

cfprApEquipmentRackUnitPsuStatsOutputVoltage OBJECT-TYPE
    SYNTAX       INTEGER
    MAX-ACCESS   read-only
    STATUS       current
    DESCRIPTION
        "Cisco Firepower equipment:RackUnitPsuStats:outputVoltage
        managed object property"
    ::= { cfprApEquipmentRackUnitPsuStatsEntry 25 }

cfprApEquipmentRackUnitPsuStatsOutputVoltageAvg OBJECT-TYPE
    SYNTAX       INTEGER
    MAX-ACCESS   read-only
    STATUS       current
    DESCRIPTION
        "Cisco Firepower equipment:RackUnitPsuStats:outputVoltageAvg
        managed object property"
    ::= { cfprApEquipmentRackUnitPsuStatsEntry 26 }

cfprApEquipmentRackUnitPsuStatsOutputVoltageMax OBJECT-TYPE
    SYNTAX       INTEGER
    MAX-ACCESS   read-only
    STATUS       current
    DESCRIPTION
        "Cisco Firepower equipment:RackUnitPsuStats:outputVoltageMax
        managed object property"
    ::= { cfprApEquipmentRackUnitPsuStatsEntry 27 }

cfprApEquipmentRackUnitPsuStatsOutputVoltageMin OBJECT-TYPE
    SYNTAX       INTEGER
    MAX-ACCESS   read-only
    STATUS       current
    DESCRIPTION
        "Cisco Firepower equipment:RackUnitPsuStats:outputVoltageMin
        managed object property"
    ::= { cfprApEquipmentRackUnitPsuStatsEntry 28 }

cfprApEquipmentRackUnitPsuStatsSuspect OBJECT-TYPE
    SYNTAX       TruthValue
    MAX-ACCESS   read-only
    STATUS       current
    DESCRIPTION
        "Cisco Firepower equipment:RackUnitPsuStats:suspect
        managed object property"
    ::= { cfprApEquipmentRackUnitPsuStatsEntry 29 }

cfprApEquipmentRackUnitPsuStatsThresholded OBJECT-TYPE
    SYNTAX       CfprApEquipmentRackUnitPsuStatsThresholded
    MAX-ACCESS   read-only
    STATUS       current
    DESCRIPTION
        "Cisco Firepower equipment:RackUnitPsuStats:thresholded
        managed object property"
    ::= { cfprApEquipmentRackUnitPsuStatsEntry 30 }

cfprApEquipmentRackUnitPsuStatsTimeCollected OBJECT-TYPE
    SYNTAX       DateAndTime
    MAX-ACCESS   read-only
    STATUS       current
    DESCRIPTION
        "Cisco Firepower equipment:RackUnitPsuStats:timeCollected
        managed object property"
    ::= { cfprApEquipmentRackUnitPsuStatsEntry 31 }

cfprApEquipmentRackUnitPsuStatsUpdate OBJECT-TYPE
    SYNTAX       Gauge32
    MAX-ACCESS   read-only
    STATUS       current
    DESCRIPTION
        "Cisco Firepower equipment:RackUnitPsuStats:update
        managed object property"
    ::= { cfprApEquipmentRackUnitPsuStatsEntry 32 }

cfprApEquipmentRackUnitPsuStatsHistTable OBJECT-TYPE
    SYNTAX           SEQUENCE OF CfprApEquipmentRackUnitPsuStatsHistEntry
    MAX-ACCESS       not-accessible
    STATUS           current
    DESCRIPTION
        "Cisco Firepower equipment:RackUnitPsuStatsHist
        managed object table"
    ::= { cfprApEquipmentObjects 125 }

cfprApEquipmentRackUnitPsuStatsHistEntry OBJECT-TYPE
    SYNTAX           CfprApEquipmentRackUnitPsuStatsHistEntry
    MAX-ACCESS       not-accessible
    STATUS           current
    DESCRIPTION
        "Entry for the cfprApEquipmentRackUnitPsuStatsHistTable table."
    INDEX { cfprApEquipmentRackUnitPsuStatsHistInstanceId }
    ::= { cfprApEquipmentRackUnitPsuStatsHistTable 1 }

CfprApEquipmentRackUnitPsuStatsHistEntry ::= SEQUENCE {
    cfprApEquipmentRackUnitPsuStatsHistInstanceId                    CfprApManagedObjectId,
    cfprApEquipmentRackUnitPsuStatsHistDn                            CfprApManagedObjectDn,
    cfprApEquipmentRackUnitPsuStatsHistRn                            SnmpAdminString,
    cfprApEquipmentRackUnitPsuStatsHistAmbientTemp                   INTEGER,
    cfprApEquipmentRackUnitPsuStatsHistAmbientTempAvg                INTEGER,
    cfprApEquipmentRackUnitPsuStatsHistAmbientTempMax                INTEGER,
    cfprApEquipmentRackUnitPsuStatsHistAmbientTempMin                INTEGER,
    cfprApEquipmentRackUnitPsuStatsHistId                            Unsigned64,
    cfprApEquipmentRackUnitPsuStatsHistInputPower                    INTEGER,
    cfprApEquipmentRackUnitPsuStatsHistInputPowerAvg                 INTEGER,
    cfprApEquipmentRackUnitPsuStatsHistInputPowerMax                 INTEGER,
    cfprApEquipmentRackUnitPsuStatsHistInputPowerMin                 INTEGER,
    cfprApEquipmentRackUnitPsuStatsHistInputVoltage                  INTEGER,
    cfprApEquipmentRackUnitPsuStatsHistInputVoltageAvg               INTEGER,
    cfprApEquipmentRackUnitPsuStatsHistInputVoltageMax               INTEGER,
    cfprApEquipmentRackUnitPsuStatsHistInputVoltageMin               INTEGER,
    cfprApEquipmentRackUnitPsuStatsHistMostRecent                    TruthValue,
    cfprApEquipmentRackUnitPsuStatsHistOutputCurrent                 INTEGER,
    cfprApEquipmentRackUnitPsuStatsHistOutputCurrentAvg              INTEGER,
    cfprApEquipmentRackUnitPsuStatsHistOutputCurrentMax              INTEGER,
    cfprApEquipmentRackUnitPsuStatsHistOutputCurrentMin              INTEGER,
    cfprApEquipmentRackUnitPsuStatsHistOutputPower                   INTEGER,
    cfprApEquipmentRackUnitPsuStatsHistOutputPowerAvg                INTEGER,
    cfprApEquipmentRackUnitPsuStatsHistOutputPowerMax                INTEGER,
    cfprApEquipmentRackUnitPsuStatsHistOutputPowerMin                INTEGER,
    cfprApEquipmentRackUnitPsuStatsHistOutputVoltage                 INTEGER,
    cfprApEquipmentRackUnitPsuStatsHistOutputVoltageAvg              INTEGER,
    cfprApEquipmentRackUnitPsuStatsHistOutputVoltageMax              INTEGER,
    cfprApEquipmentRackUnitPsuStatsHistOutputVoltageMin              INTEGER,
    cfprApEquipmentRackUnitPsuStatsHistSuspect                       TruthValue,
    cfprApEquipmentRackUnitPsuStatsHistThresholded                   CfprApEquipmentRackUnitPsuStatsHistThresholded,
    cfprApEquipmentRackUnitPsuStatsHistTimeCollected                 DateAndTime
}

cfprApEquipmentRackUnitPsuStatsHistInstanceId OBJECT-TYPE
    SYNTAX       CfprApManagedObjectId
    MAX-ACCESS   not-accessible
    STATUS       current
    DESCRIPTION
        "Instance identifier of the managed object."
    ::= { cfprApEquipmentRackUnitPsuStatsHistEntry 1 }

cfprApEquipmentRackUnitPsuStatsHistDn OBJECT-TYPE
    SYNTAX       CfprApManagedObjectDn
    MAX-ACCESS   read-only
    STATUS       current
    DESCRIPTION
        "Cisco Firepower equipment:RackUnitPsuStatsHist:dn
        managed object property"
    ::= { cfprApEquipmentRackUnitPsuStatsHistEntry 2 }

cfprApEquipmentRackUnitPsuStatsHistRn OBJECT-TYPE
    SYNTAX       SnmpAdminString
    MAX-ACCESS   read-only
    STATUS       current
    DESCRIPTION
        "Cisco Firepower equipment:RackUnitPsuStatsHist:rn
        managed object property"
    ::= { cfprApEquipmentRackUnitPsuStatsHistEntry 3 }

cfprApEquipmentRackUnitPsuStatsHistAmbientTemp OBJECT-TYPE
    SYNTAX       INTEGER
    MAX-ACCESS   read-only
    STATUS       current
    DESCRIPTION
        "Cisco Firepower equipment:RackUnitPsuStatsHist:ambientTemp
        managed object property"
    ::= { cfprApEquipmentRackUnitPsuStatsHistEntry 4 }

cfprApEquipmentRackUnitPsuStatsHistAmbientTempAvg OBJECT-TYPE
    SYNTAX       INTEGER
    MAX-ACCESS   read-only
    STATUS       current
    DESCRIPTION
        "Cisco Firepower equipment:RackUnitPsuStatsHist:ambientTempAvg
        managed object property"
    ::= { cfprApEquipmentRackUnitPsuStatsHistEntry 5 }

cfprApEquipmentRackUnitPsuStatsHistAmbientTempMax OBJECT-TYPE
    SYNTAX       INTEGER
    MAX-ACCESS   read-only
    STATUS       current
    DESCRIPTION
        "Cisco Firepower equipment:RackUnitPsuStatsHist:ambientTempMax
        managed object property"
    ::= { cfprApEquipmentRackUnitPsuStatsHistEntry 6 }

cfprApEquipmentRackUnitPsuStatsHistAmbientTempMin OBJECT-TYPE
    SYNTAX       INTEGER
    MAX-ACCESS   read-only
    STATUS       current
    DESCRIPTION
        "Cisco Firepower equipment:RackUnitPsuStatsHist:ambientTempMin
        managed object property"
    ::= { cfprApEquipmentRackUnitPsuStatsHistEntry 7 }

cfprApEquipmentRackUnitPsuStatsHistId OBJECT-TYPE
    SYNTAX       Unsigned64
    MAX-ACCESS   read-only
    STATUS       current
    DESCRIPTION
        "Cisco Firepower equipment:RackUnitPsuStatsHist:id
        managed object property"
    ::= { cfprApEquipmentRackUnitPsuStatsHistEntry 8 }

cfprApEquipmentRackUnitPsuStatsHistInputPower OBJECT-TYPE
    SYNTAX       INTEGER
    MAX-ACCESS   read-only
    STATUS       current
    DESCRIPTION
        "Cisco Firepower equipment:RackUnitPsuStatsHist:inputPower
        managed object property"
    ::= { cfprApEquipmentRackUnitPsuStatsHistEntry 9 }

cfprApEquipmentRackUnitPsuStatsHistInputPowerAvg OBJECT-TYPE
    SYNTAX       INTEGER
    MAX-ACCESS   read-only
    STATUS       current
    DESCRIPTION
        "Cisco Firepower equipment:RackUnitPsuStatsHist:inputPowerAvg
        managed object property"
    ::= { cfprApEquipmentRackUnitPsuStatsHistEntry 10 }

cfprApEquipmentRackUnitPsuStatsHistInputPowerMax OBJECT-TYPE
    SYNTAX       INTEGER
    MAX-ACCESS   read-only
    STATUS       current
    DESCRIPTION
        "Cisco Firepower equipment:RackUnitPsuStatsHist:inputPowerMax
        managed object property"
    ::= { cfprApEquipmentRackUnitPsuStatsHistEntry 11 }

cfprApEquipmentRackUnitPsuStatsHistInputPowerMin OBJECT-TYPE
    SYNTAX       INTEGER
    MAX-ACCESS   read-only
    STATUS       current
    DESCRIPTION
        "Cisco Firepower equipment:RackUnitPsuStatsHist:inputPowerMin
        managed object property"
    ::= { cfprApEquipmentRackUnitPsuStatsHistEntry 12 }

cfprApEquipmentRackUnitPsuStatsHistInputVoltage OBJECT-TYPE
    SYNTAX       INTEGER
    MAX-ACCESS   read-only
    STATUS       current
    DESCRIPTION
        "Cisco Firepower equipment:RackUnitPsuStatsHist:inputVoltage
        managed object property"
    ::= { cfprApEquipmentRackUnitPsuStatsHistEntry 13 }

cfprApEquipmentRackUnitPsuStatsHistInputVoltageAvg OBJECT-TYPE
    SYNTAX       INTEGER
    MAX-ACCESS   read-only
    STATUS       current
    DESCRIPTION
        "Cisco Firepower equipment:RackUnitPsuStatsHist:inputVoltageAvg
        managed object property"
    ::= { cfprApEquipmentRackUnitPsuStatsHistEntry 14 }

cfprApEquipmentRackUnitPsuStatsHistInputVoltageMax OBJECT-TYPE
    SYNTAX       INTEGER
    MAX-ACCESS   read-only
    STATUS       current
    DESCRIPTION
        "Cisco Firepower equipment:RackUnitPsuStatsHist:inputVoltageMax
        managed object property"
    ::= { cfprApEquipmentRackUnitPsuStatsHistEntry 15 }

cfprApEquipmentRackUnitPsuStatsHistInputVoltageMin OBJECT-TYPE
    SYNTAX       INTEGER
    MAX-ACCESS   read-only
    STATUS       current
    DESCRIPTION
        "Cisco Firepower equipment:RackUnitPsuStatsHist:inputVoltageMin
        managed object property"
    ::= { cfprApEquipmentRackUnitPsuStatsHistEntry 16 }

cfprApEquipmentRackUnitPsuStatsHistMostRecent OBJECT-TYPE
    SYNTAX       TruthValue
    MAX-ACCESS   read-only
    STATUS       current
    DESCRIPTION
        "Cisco Firepower equipment:RackUnitPsuStatsHist:mostRecent
        managed object property"
    ::= { cfprApEquipmentRackUnitPsuStatsHistEntry 17 }

cfprApEquipmentRackUnitPsuStatsHistOutputCurrent OBJECT-TYPE
    SYNTAX       INTEGER
    MAX-ACCESS   read-only
    STATUS       current
    DESCRIPTION
        "Cisco Firepower equipment:RackUnitPsuStatsHist:outputCurrent
        managed object property"
    ::= { cfprApEquipmentRackUnitPsuStatsHistEntry 18 }

cfprApEquipmentRackUnitPsuStatsHistOutputCurrentAvg OBJECT-TYPE
    SYNTAX       INTEGER
    MAX-ACCESS   read-only
    STATUS       current
    DESCRIPTION
        "Cisco Firepower equipment:RackUnitPsuStatsHist:outputCurrentAvg
        managed object property"
    ::= { cfprApEquipmentRackUnitPsuStatsHistEntry 19 }

cfprApEquipmentRackUnitPsuStatsHistOutputCurrentMax OBJECT-TYPE
    SYNTAX       INTEGER
    MAX-ACCESS   read-only
    STATUS       current
    DESCRIPTION
        "Cisco Firepower equipment:RackUnitPsuStatsHist:outputCurrentMax
        managed object property"
    ::= { cfprApEquipmentRackUnitPsuStatsHistEntry 20 }

cfprApEquipmentRackUnitPsuStatsHistOutputCurrentMin OBJECT-TYPE
    SYNTAX       INTEGER
    MAX-ACCESS   read-only
    STATUS       current
    DESCRIPTION
        "Cisco Firepower equipment:RackUnitPsuStatsHist:outputCurrentMin
        managed object property"
    ::= { cfprApEquipmentRackUnitPsuStatsHistEntry 21 }

cfprApEquipmentRackUnitPsuStatsHistOutputPower OBJECT-TYPE
    SYNTAX       INTEGER
    MAX-ACCESS   read-only
    STATUS       current
    DESCRIPTION
        "Cisco Firepower equipment:RackUnitPsuStatsHist:outputPower
        managed object property"
    ::= { cfprApEquipmentRackUnitPsuStatsHistEntry 22 }

cfprApEquipmentRackUnitPsuStatsHistOutputPowerAvg OBJECT-TYPE
    SYNTAX       INTEGER
    MAX-ACCESS   read-only
    STATUS       current
    DESCRIPTION
        "Cisco Firepower equipment:RackUnitPsuStatsHist:outputPowerAvg
        managed object property"
    ::= { cfprApEquipmentRackUnitPsuStatsHistEntry 23 }

cfprApEquipmentRackUnitPsuStatsHistOutputPowerMax OBJECT-TYPE
    SYNTAX       INTEGER
    MAX-ACCESS   read-only
    STATUS       current
    DESCRIPTION
        "Cisco Firepower equipment:RackUnitPsuStatsHist:outputPowerMax
        managed object property"
    ::= { cfprApEquipmentRackUnitPsuStatsHistEntry 24 }

cfprApEquipmentRackUnitPsuStatsHistOutputPowerMin OBJECT-TYPE
    SYNTAX       INTEGER
    MAX-ACCESS   read-only
    STATUS       current
    DESCRIPTION
        "Cisco Firepower equipment:RackUnitPsuStatsHist:outputPowerMin
        managed object property"
    ::= { cfprApEquipmentRackUnitPsuStatsHistEntry 25 }

cfprApEquipmentRackUnitPsuStatsHistOutputVoltage OBJECT-TYPE
    SYNTAX       INTEGER
    MAX-ACCESS   read-only
    STATUS       current
    DESCRIPTION
        "Cisco Firepower equipment:RackUnitPsuStatsHist:outputVoltage
        managed object property"
    ::= { cfprApEquipmentRackUnitPsuStatsHistEntry 26 }

cfprApEquipmentRackUnitPsuStatsHistOutputVoltageAvg OBJECT-TYPE
    SYNTAX       INTEGER
    MAX-ACCESS   read-only
    STATUS       current
    DESCRIPTION
        "Cisco Firepower equipment:RackUnitPsuStatsHist:outputVoltageAvg
        managed object property"
    ::= { cfprApEquipmentRackUnitPsuStatsHistEntry 27 }

cfprApEquipmentRackUnitPsuStatsHistOutputVoltageMax OBJECT-TYPE
    SYNTAX       INTEGER
    MAX-ACCESS   read-only
    STATUS       current
    DESCRIPTION
        "Cisco Firepower equipment:RackUnitPsuStatsHist:outputVoltageMax
        managed object property"
    ::= { cfprApEquipmentRackUnitPsuStatsHistEntry 28 }

cfprApEquipmentRackUnitPsuStatsHistOutputVoltageMin OBJECT-TYPE
    SYNTAX       INTEGER
    MAX-ACCESS   read-only
    STATUS       current
    DESCRIPTION
        "Cisco Firepower equipment:RackUnitPsuStatsHist:outputVoltageMin
        managed object property"
    ::= { cfprApEquipmentRackUnitPsuStatsHistEntry 29 }

cfprApEquipmentRackUnitPsuStatsHistSuspect OBJECT-TYPE
    SYNTAX       TruthValue
    MAX-ACCESS   read-only
    STATUS       current
    DESCRIPTION
        "Cisco Firepower equipment:RackUnitPsuStatsHist:suspect
        managed object property"
    ::= { cfprApEquipmentRackUnitPsuStatsHistEntry 30 }

cfprApEquipmentRackUnitPsuStatsHistThresholded OBJECT-TYPE
    SYNTAX       CfprApEquipmentRackUnitPsuStatsHistThresholded
    MAX-ACCESS   read-only
    STATUS       current
    DESCRIPTION
        "Cisco Firepower equipment:RackUnitPsuStatsHist:thresholded
        managed object property"
    ::= { cfprApEquipmentRackUnitPsuStatsHistEntry 31 }

cfprApEquipmentRackUnitPsuStatsHistTimeCollected OBJECT-TYPE
    SYNTAX       DateAndTime
    MAX-ACCESS   read-only
    STATUS       current
    DESCRIPTION
        "Cisco Firepower equipment:RackUnitPsuStatsHist:timeCollected
        managed object property"
    ::= { cfprApEquipmentRackUnitPsuStatsHistEntry 32 }

cfprApEquipmentRaidDefTable OBJECT-TYPE
    SYNTAX           SEQUENCE OF CfprApEquipmentRaidDefEntry
    MAX-ACCESS       not-accessible
    STATUS           current
    DESCRIPTION
        "Cisco Firepower equipment:RaidDef managed object table"
    ::= { cfprApEquipmentObjects 126 }

cfprApEquipmentRaidDefEntry OBJECT-TYPE
    SYNTAX           CfprApEquipmentRaidDefEntry
    MAX-ACCESS       not-accessible
    STATUS           current
    DESCRIPTION
        "Entry for the cfprApEquipmentRaidDefTable table."
    INDEX { cfprApEquipmentRaidDefInstanceId }
    ::= { cfprApEquipmentRaidDefTable 1 }

CfprApEquipmentRaidDefEntry ::= SEQUENCE {
    cfprApEquipmentRaidDefInstanceId                                 CfprApManagedObjectId,
    cfprApEquipmentRaidDefDn                                         CfprApManagedObjectDn,
    cfprApEquipmentRaidDefRn                                         SnmpAdminString,
    cfprApEquipmentRaidDefDescr                                      SnmpAdminString,
    cfprApEquipmentRaidDefIntId                                      SnmpAdminString,
    cfprApEquipmentRaidDefLevel                                      CfprApStorageLocalDiskMode,
    cfprApEquipmentRaidDefName                                       SnmpAdminString,
    cfprApEquipmentRaidDefPolicyLevel                                Gauge32,
    cfprApEquipmentRaidDefPolicyOwner                                CfprApPolicyPolicyOwner
}

cfprApEquipmentRaidDefInstanceId OBJECT-TYPE
    SYNTAX       CfprApManagedObjectId
    MAX-ACCESS   not-accessible
    STATUS       current
    DESCRIPTION
        "Instance identifier of the managed object."
    ::= { cfprApEquipmentRaidDefEntry 1 }

cfprApEquipmentRaidDefDn OBJECT-TYPE
    SYNTAX       CfprApManagedObjectDn
    MAX-ACCESS   read-only
    STATUS       current
    DESCRIPTION
        "Cisco Firepower equipment:RaidDef:dn managed object property"
    ::= { cfprApEquipmentRaidDefEntry 2 }

cfprApEquipmentRaidDefRn OBJECT-TYPE
    SYNTAX       SnmpAdminString
    MAX-ACCESS   read-only
    STATUS       current
    DESCRIPTION
        "Cisco Firepower equipment:RaidDef:rn managed object property"
    ::= { cfprApEquipmentRaidDefEntry 3 }

cfprApEquipmentRaidDefDescr OBJECT-TYPE
    SYNTAX       SnmpAdminString
    MAX-ACCESS   read-only
    STATUS       current
    DESCRIPTION
        "Cisco Firepower equipment:RaidDef:descr managed object property"
    ::= { cfprApEquipmentRaidDefEntry 4 }

cfprApEquipmentRaidDefIntId OBJECT-TYPE
    SYNTAX       SnmpAdminString
    MAX-ACCESS   read-only
    STATUS       current
    DESCRIPTION
        "Cisco Firepower equipment:RaidDef:intId managed object property"
    ::= { cfprApEquipmentRaidDefEntry 5 }

cfprApEquipmentRaidDefLevel OBJECT-TYPE
    SYNTAX       CfprApStorageLocalDiskMode
    MAX-ACCESS   read-only
    STATUS       current
    DESCRIPTION
        "Cisco Firepower equipment:RaidDef:level managed object property"
    ::= { cfprApEquipmentRaidDefEntry 6 }

cfprApEquipmentRaidDefName OBJECT-TYPE
    SYNTAX       SnmpAdminString
    MAX-ACCESS   read-only
    STATUS       current
    DESCRIPTION
        "Cisco Firepower equipment:RaidDef:name managed object property"
    ::= { cfprApEquipmentRaidDefEntry 7 }

cfprApEquipmentRaidDefPolicyLevel OBJECT-TYPE
    SYNTAX       Gauge32
    MAX-ACCESS   read-only
    STATUS       current
    DESCRIPTION
        "Cisco Firepower equipment:RaidDef:policyLevel
        managed object property"
    ::= { cfprApEquipmentRaidDefEntry 8 }

cfprApEquipmentRaidDefPolicyOwner OBJECT-TYPE
    SYNTAX       CfprApPolicyPolicyOwner
    MAX-ACCESS   read-only
    STATUS       current
    DESCRIPTION
        "Cisco Firepower equipment:RaidDef:policyOwner
        managed object property"
    ::= { cfprApEquipmentRaidDefEntry 9 }

cfprApEquipmentRommonTable OBJECT-TYPE
    SYNTAX           SEQUENCE OF CfprApEquipmentRommonEntry
    MAX-ACCESS       not-accessible
    STATUS           current
    DESCRIPTION
        "Cisco Firepower equipment:Rommon managed object table"
    ::= { cfprApEquipmentObjects 127 }

cfprApEquipmentRommonEntry OBJECT-TYPE
    SYNTAX           CfprApEquipmentRommonEntry
    MAX-ACCESS       not-accessible
    STATUS           current
    DESCRIPTION
        "Entry for the cfprApEquipmentRommonTable table."
    INDEX { cfprApEquipmentRommonInstanceId }
    ::= { cfprApEquipmentRommonTable 1 }

CfprApEquipmentRommonEntry ::= SEQUENCE {
    cfprApEquipmentRommonInstanceId                                  CfprApManagedObjectId,
    cfprApEquipmentRommonDn                                          CfprApManagedObjectDn,
    cfprApEquipmentRommonRn                                          SnmpAdminString,
    cfprApEquipmentRommonBkupPackageVersion                          SnmpAdminString,
    cfprApEquipmentRommonBkupVersion                                 SnmpAdminString,
    cfprApEquipmentRommonFltAggr                                     Unsigned64,
    cfprApEquipmentRommonModel                                       SnmpAdminString,
    cfprApEquipmentRommonRevision                                    SnmpAdminString,
    cfprApEquipmentRommonSerial                                      SnmpAdminString,
    cfprApEquipmentRommonUpgradeStatus                               SnmpAdminString,
    cfprApEquipmentRommonVendor                                      SnmpAdminString
}

cfprApEquipmentRommonInstanceId OBJECT-TYPE
    SYNTAX       CfprApManagedObjectId
    MAX-ACCESS   not-accessible
    STATUS       current
    DESCRIPTION
        "Instance identifier of the managed object."
    ::= { cfprApEquipmentRommonEntry 1 }

cfprApEquipmentRommonDn OBJECT-TYPE
    SYNTAX       CfprApManagedObjectDn
    MAX-ACCESS   read-only
    STATUS       current
    DESCRIPTION
        "Cisco Firepower equipment:Rommon:dn managed object property"
    ::= { cfprApEquipmentRommonEntry 2 }

cfprApEquipmentRommonRn OBJECT-TYPE
    SYNTAX       SnmpAdminString
    MAX-ACCESS   read-only
    STATUS       current
    DESCRIPTION
        "Cisco Firepower equipment:Rommon:rn managed object property"
    ::= { cfprApEquipmentRommonEntry 3 }

cfprApEquipmentRommonBkupPackageVersion OBJECT-TYPE
    SYNTAX       SnmpAdminString
    MAX-ACCESS   read-only
    STATUS       current
    DESCRIPTION
        "Cisco Firepower equipment:Rommon:bkupPackageVersion
        managed object property"
    ::= { cfprApEquipmentRommonEntry 4 }

cfprApEquipmentRommonBkupVersion OBJECT-TYPE
    SYNTAX       SnmpAdminString
    MAX-ACCESS   read-only
    STATUS       current
    DESCRIPTION
        "Cisco Firepower equipment:Rommon:bkupVersion managed
        object property"
    ::= { cfprApEquipmentRommonEntry 5 }

cfprApEquipmentRommonFltAggr OBJECT-TYPE
    SYNTAX       Unsigned64
    MAX-ACCESS   read-only
    STATUS       current
    DESCRIPTION
        "Cisco Firepower equipment:Rommon:fltAggr managed object property"
    ::= { cfprApEquipmentRommonEntry 6 }

cfprApEquipmentRommonModel OBJECT-TYPE
    SYNTAX       SnmpAdminString
    MAX-ACCESS   read-only
    STATUS       current
    DESCRIPTION
        "Cisco Firepower equipment:Rommon:model managed object property"
    ::= { cfprApEquipmentRommonEntry 7 }

cfprApEquipmentRommonRevision OBJECT-TYPE
    SYNTAX       SnmpAdminString
    MAX-ACCESS   read-only
    STATUS       current
    DESCRIPTION
        "Cisco Firepower equipment:Rommon:revision managed
        object property"
    ::= { cfprApEquipmentRommonEntry 8 }

cfprApEquipmentRommonSerial OBJECT-TYPE
    SYNTAX       SnmpAdminString
    MAX-ACCESS   read-only
    STATUS       current
    DESCRIPTION
        "Cisco Firepower equipment:Rommon:serial managed object property"
    ::= { cfprApEquipmentRommonEntry 9 }

cfprApEquipmentRommonUpgradeStatus OBJECT-TYPE
    SYNTAX       SnmpAdminString
    MAX-ACCESS   read-only
    STATUS       current
    DESCRIPTION
        "Cisco Firepower equipment:Rommon:upgradeStatus
        managed object property"
    ::= { cfprApEquipmentRommonEntry 10 }

cfprApEquipmentRommonVendor OBJECT-TYPE
    SYNTAX       SnmpAdminString
    MAX-ACCESS   read-only
    STATUS       current
    DESCRIPTION
        "Cisco Firepower equipment:Rommon:vendor managed object property"
    ::= { cfprApEquipmentRommonEntry 11 }

cfprApEquipmentSecureBootTable OBJECT-TYPE
    SYNTAX           SEQUENCE OF CfprApEquipmentSecureBootEntry
    MAX-ACCESS       not-accessible
    STATUS           current
    DESCRIPTION
        "Cisco Firepower equipment:SecureBoot managed object table"
    ::= { cfprApEquipmentObjects 128 }

cfprApEquipmentSecureBootEntry OBJECT-TYPE
    SYNTAX           CfprApEquipmentSecureBootEntry
    MAX-ACCESS       not-accessible
    STATUS           current
    DESCRIPTION
        "Entry for the cfprApEquipmentSecureBootTable table."
    INDEX { cfprApEquipmentSecureBootInstanceId }
    ::= { cfprApEquipmentSecureBootTable 1 }

CfprApEquipmentSecureBootEntry ::= SEQUENCE {
    cfprApEquipmentSecureBootInstanceId                              CfprApManagedObjectId,
    cfprApEquipmentSecureBootDn                                      CfprApManagedObjectDn,
    cfprApEquipmentSecureBootRn                                      SnmpAdminString,
    cfprApEquipmentSecureBootDescr                                   SnmpAdminString,
    cfprApEquipmentSecureBootIntId                                   SnmpAdminString,
    cfprApEquipmentSecureBootMinBiosVersion                          SnmpAdminString,
    cfprApEquipmentSecureBootMinCimcVersion                          SnmpAdminString,
    cfprApEquipmentSecureBootName                                    SnmpAdminString,
    cfprApEquipmentSecureBootPolicyLevel                             Gauge32,
    cfprApEquipmentSecureBootPolicyOwner                             CfprApPolicyPolicyOwner
}

cfprApEquipmentSecureBootInstanceId OBJECT-TYPE
    SYNTAX       CfprApManagedObjectId
    MAX-ACCESS   not-accessible
    STATUS       current
    DESCRIPTION
        "Instance identifier of the managed object."
    ::= { cfprApEquipmentSecureBootEntry 1 }

cfprApEquipmentSecureBootDn OBJECT-TYPE
    SYNTAX       CfprApManagedObjectDn
    MAX-ACCESS   read-only
    STATUS       current
    DESCRIPTION
        "Cisco Firepower equipment:SecureBoot:dn managed object property"
    ::= { cfprApEquipmentSecureBootEntry 2 }

cfprApEquipmentSecureBootRn OBJECT-TYPE
    SYNTAX       SnmpAdminString
    MAX-ACCESS   read-only
    STATUS       current
    DESCRIPTION
        "Cisco Firepower equipment:SecureBoot:rn managed object property"
    ::= { cfprApEquipmentSecureBootEntry 3 }

cfprApEquipmentSecureBootDescr OBJECT-TYPE
    SYNTAX       SnmpAdminString
    MAX-ACCESS   read-only
    STATUS       current
    DESCRIPTION
        "Cisco Firepower equipment:SecureBoot:descr managed
        object property"
    ::= { cfprApEquipmentSecureBootEntry 4 }

cfprApEquipmentSecureBootIntId OBJECT-TYPE
    SYNTAX       SnmpAdminString
    MAX-ACCESS   read-only
    STATUS       current
    DESCRIPTION
        "Cisco Firepower equipment:SecureBoot:intId managed
        object property"
    ::= { cfprApEquipmentSecureBootEntry 5 }

cfprApEquipmentSecureBootMinBiosVersion OBJECT-TYPE
    SYNTAX       SnmpAdminString
    MAX-ACCESS   read-only
    STATUS       current
    DESCRIPTION
        "Cisco Firepower equipment:SecureBoot:minBiosVersion
        managed object property"
    ::= { cfprApEquipmentSecureBootEntry 6 }

cfprApEquipmentSecureBootMinCimcVersion OBJECT-TYPE
    SYNTAX       SnmpAdminString
    MAX-ACCESS   read-only
    STATUS       current
    DESCRIPTION
        "Cisco Firepower equipment:SecureBoot:minCimcVersion
        managed object property"
    ::= { cfprApEquipmentSecureBootEntry 7 }

cfprApEquipmentSecureBootName OBJECT-TYPE
    SYNTAX       SnmpAdminString
    MAX-ACCESS   read-only
    STATUS       current
    DESCRIPTION
        "Cisco Firepower equipment:SecureBoot:name managed
        object property"
    ::= { cfprApEquipmentSecureBootEntry 8 }

cfprApEquipmentSecureBootPolicyLevel OBJECT-TYPE
    SYNTAX       Gauge32
    MAX-ACCESS   read-only
    STATUS       current
    DESCRIPTION
        "Cisco Firepower equipment:SecureBoot:policyLevel
        managed object property"
    ::= { cfprApEquipmentSecureBootEntry 9 }

cfprApEquipmentSecureBootPolicyOwner OBJECT-TYPE
    SYNTAX       CfprApPolicyPolicyOwner
    MAX-ACCESS   read-only
    STATUS       current
    DESCRIPTION
        "Cisco Firepower equipment:SecureBoot:policyOwner
        managed object property"
    ::= { cfprApEquipmentSecureBootEntry 10 }

cfprApEquipmentServerFeatureCapTable OBJECT-TYPE
    SYNTAX           SEQUENCE OF CfprApEquipmentServerFeatureCapEntry
    MAX-ACCESS       not-accessible
    STATUS           current
    DESCRIPTION
        "Cisco Firepower equipment:ServerFeatureCap managed object table"
    ::= { cfprApEquipmentObjects 129 }

cfprApEquipmentServerFeatureCapEntry OBJECT-TYPE
    SYNTAX           CfprApEquipmentServerFeatureCapEntry
    MAX-ACCESS       not-accessible
    STATUS           current
    DESCRIPTION
        "Entry for the cfprApEquipmentServerFeatureCapTable table."
    INDEX { cfprApEquipmentServerFeatureCapInstanceId }
    ::= { cfprApEquipmentServerFeatureCapTable 1 }

CfprApEquipmentServerFeatureCapEntry ::= SEQUENCE {
    cfprApEquipmentServerFeatureCapInstanceId                        CfprApManagedObjectId,
    cfprApEquipmentServerFeatureCapDn                                CfprApManagedObjectDn,
    cfprApEquipmentServerFeatureCapRn                                SnmpAdminString,
    cfprApEquipmentServerFeatureCapCmosResetSupported                TruthValue
}

cfprApEquipmentServerFeatureCapInstanceId OBJECT-TYPE
    SYNTAX       CfprApManagedObjectId
    MAX-ACCESS   not-accessible
    STATUS       current
    DESCRIPTION
        "Instance identifier of the managed object."
    ::= { cfprApEquipmentServerFeatureCapEntry 1 }

cfprApEquipmentServerFeatureCapDn OBJECT-TYPE
    SYNTAX       CfprApManagedObjectDn
    MAX-ACCESS   read-only
    STATUS       current
    DESCRIPTION
        "Cisco Firepower equipment:ServerFeatureCap:dn
        managed object property"
    ::= { cfprApEquipmentServerFeatureCapEntry 2 }

cfprApEquipmentServerFeatureCapRn OBJECT-TYPE
    SYNTAX       SnmpAdminString
    MAX-ACCESS   read-only
    STATUS       current
    DESCRIPTION
        "Cisco Firepower equipment:ServerFeatureCap:rn
        managed object property"
    ::= { cfprApEquipmentServerFeatureCapEntry 3 }

cfprApEquipmentServerFeatureCapCmosResetSupported OBJECT-TYPE
    SYNTAX       TruthValue
    MAX-ACCESS   read-only
    STATUS       current
    DESCRIPTION
        "Cisco Firepower equipment:ServerFeatureCap:cmosResetSupported
        managed object property"
    ::= { cfprApEquipmentServerFeatureCapEntry 4 }

cfprApEquipmentServerPortCapProviderTable OBJECT-TYPE
    SYNTAX           SEQUENCE OF CfprApEquipmentServerPortCapProviderEntry
    MAX-ACCESS       not-accessible
    STATUS           current
    DESCRIPTION
        "Cisco Firepower equipment:ServerPortCapProvider
        managed object table"
    ::= { cfprApEquipmentObjects 130 }

cfprApEquipmentServerPortCapProviderEntry OBJECT-TYPE
    SYNTAX           CfprApEquipmentServerPortCapProviderEntry
    MAX-ACCESS       not-accessible
    STATUS           current
    DESCRIPTION
        "Entry for the cfprApEquipmentServerPortCapProviderTable table."
    INDEX { cfprApEquipmentServerPortCapProviderInstanceId }
    ::= { cfprApEquipmentServerPortCapProviderTable 1 }

CfprApEquipmentServerPortCapProviderEntry ::= SEQUENCE {
    cfprApEquipmentServerPortCapProviderInstanceId                   CfprApManagedObjectId,
    cfprApEquipmentServerPortCapProviderDn                           CfprApManagedObjectDn,
    cfprApEquipmentServerPortCapProviderRn                           SnmpAdminString,
    cfprApEquipmentServerPortCapProviderDescr                        SnmpAdminString,
    cfprApEquipmentServerPortCapProviderEndPortId                    Gauge32,
    cfprApEquipmentServerPortCapProviderIntId                        SnmpAdminString,
    cfprApEquipmentServerPortCapProviderName                         SnmpAdminString,
    cfprApEquipmentServerPortCapProviderPolicyLevel                  Gauge32,
    cfprApEquipmentServerPortCapProviderPolicyOwner                  CfprApPolicyPolicyOwner,
    cfprApEquipmentServerPortCapProviderStartPortId                  Gauge32
}

cfprApEquipmentServerPortCapProviderInstanceId OBJECT-TYPE
    SYNTAX       CfprApManagedObjectId
    MAX-ACCESS   not-accessible
    STATUS       current
    DESCRIPTION
        "Instance identifier of the managed object."
    ::= { cfprApEquipmentServerPortCapProviderEntry 1 }

cfprApEquipmentServerPortCapProviderDn OBJECT-TYPE
    SYNTAX       CfprApManagedObjectDn
    MAX-ACCESS   read-only
    STATUS       current
    DESCRIPTION
        "Cisco Firepower equipment:ServerPortCapProvider:dn
        managed object property"
    ::= { cfprApEquipmentServerPortCapProviderEntry 2 }

cfprApEquipmentServerPortCapProviderRn OBJECT-TYPE
    SYNTAX       SnmpAdminString
    MAX-ACCESS   read-only
    STATUS       current
    DESCRIPTION
        "Cisco Firepower equipment:ServerPortCapProvider:rn
        managed object property"
    ::= { cfprApEquipmentServerPortCapProviderEntry 3 }

cfprApEquipmentServerPortCapProviderDescr OBJECT-TYPE
    SYNTAX       SnmpAdminString
    MAX-ACCESS   read-only
    STATUS       current
    DESCRIPTION
        "Cisco Firepower equipment:ServerPortCapProvider:descr
        managed object property"
    ::= { cfprApEquipmentServerPortCapProviderEntry 4 }

cfprApEquipmentServerPortCapProviderEndPortId OBJECT-TYPE
    SYNTAX       Gauge32
    MAX-ACCESS   read-only
    STATUS       current
    DESCRIPTION
        "Cisco Firepower equipment:ServerPortCapProvider:endPortId
        managed object property"
    ::= { cfprApEquipmentServerPortCapProviderEntry 5 }

cfprApEquipmentServerPortCapProviderIntId OBJECT-TYPE
    SYNTAX       SnmpAdminString
    MAX-ACCESS   read-only
    STATUS       current
    DESCRIPTION
        "Cisco Firepower equipment:ServerPortCapProvider:intId
        managed object property"
    ::= { cfprApEquipmentServerPortCapProviderEntry 6 }

cfprApEquipmentServerPortCapProviderName OBJECT-TYPE
    SYNTAX       SnmpAdminString
    MAX-ACCESS   read-only
    STATUS       current
    DESCRIPTION
        "Cisco Firepower equipment:ServerPortCapProvider:name
        managed object property"
    ::= { cfprApEquipmentServerPortCapProviderEntry 7 }

cfprApEquipmentServerPortCapProviderPolicyLevel OBJECT-TYPE
    SYNTAX       Gauge32
    MAX-ACCESS   read-only
    STATUS       current
    DESCRIPTION
        "Cisco Firepower equipment:ServerPortCapProvider:policyLevel
        managed object property"
    ::= { cfprApEquipmentServerPortCapProviderEntry 8 }

cfprApEquipmentServerPortCapProviderPolicyOwner OBJECT-TYPE
    SYNTAX       CfprApPolicyPolicyOwner
    MAX-ACCESS   read-only
    STATUS       current
    DESCRIPTION
        "Cisco Firepower equipment:ServerPortCapProvider:policyOwner
        managed object property"
    ::= { cfprApEquipmentServerPortCapProviderEntry 9 }

cfprApEquipmentServerPortCapProviderStartPortId OBJECT-TYPE
    SYNTAX       Gauge32
    MAX-ACCESS   read-only
    STATUS       current
    DESCRIPTION
        "Cisco Firepower equipment:ServerPortCapProvider:startPortId
        managed object property"
    ::= { cfprApEquipmentServerPortCapProviderEntry 10 }

cfprApEquipmentServiceDefTable OBJECT-TYPE
    SYNTAX           SEQUENCE OF CfprApEquipmentServiceDefEntry
    MAX-ACCESS       not-accessible
    STATUS           current
    DESCRIPTION
        "Cisco Firepower equipment:ServiceDef managed object table"
    ::= { cfprApEquipmentObjects 131 }

cfprApEquipmentServiceDefEntry OBJECT-TYPE
    SYNTAX           CfprApEquipmentServiceDefEntry
    MAX-ACCESS       not-accessible
    STATUS           current
    DESCRIPTION
        "Entry for the cfprApEquipmentServiceDefTable table."
    INDEX { cfprApEquipmentServiceDefInstanceId }
    ::= { cfprApEquipmentServiceDefTable 1 }

CfprApEquipmentServiceDefEntry ::= SEQUENCE {
    cfprApEquipmentServiceDefInstanceId                              CfprApManagedObjectId,
    cfprApEquipmentServiceDefDn                                      CfprApManagedObjectDn,
    cfprApEquipmentServiceDefRn                                      SnmpAdminString,
    cfprApEquipmentServiceDefCanBeFRUed                              TruthValue,
    cfprApEquipmentServiceDefDescr                                   SnmpAdminString,
    cfprApEquipmentServiceDefIntId                                   SnmpAdminString,
    cfprApEquipmentServiceDefName                                    SnmpAdminString,
    cfprApEquipmentServiceDefPolicyLevel                             Gauge32,
    cfprApEquipmentServiceDefPolicyOwner                             CfprApPolicyPolicyOwner,
    cfprApEquipmentServiceDefRemovalConditions                       CfprApEquipmentRemovalConditions,
    cfprApEquipmentServiceDefServicePhilosophy                       SnmpAdminString
}

cfprApEquipmentServiceDefInstanceId OBJECT-TYPE
    SYNTAX       CfprApManagedObjectId
    MAX-ACCESS   not-accessible
    STATUS       current
    DESCRIPTION
        "Instance identifier of the managed object."
    ::= { cfprApEquipmentServiceDefEntry 1 }

cfprApEquipmentServiceDefDn OBJECT-TYPE
    SYNTAX       CfprApManagedObjectDn
    MAX-ACCESS   read-only
    STATUS       current
    DESCRIPTION
        "Cisco Firepower equipment:ServiceDef:dn managed object property"
    ::= { cfprApEquipmentServiceDefEntry 2 }

cfprApEquipmentServiceDefRn OBJECT-TYPE
    SYNTAX       SnmpAdminString
    MAX-ACCESS   read-only
    STATUS       current
    DESCRIPTION
        "Cisco Firepower equipment:ServiceDef:rn managed object property"
    ::= { cfprApEquipmentServiceDefEntry 3 }

cfprApEquipmentServiceDefCanBeFRUed OBJECT-TYPE
    SYNTAX       TruthValue
    MAX-ACCESS   read-only
    STATUS       current
    DESCRIPTION
        "Cisco Firepower equipment:ServiceDef:canBeFRUed
        managed object property"
    ::= { cfprApEquipmentServiceDefEntry 4 }

cfprApEquipmentServiceDefDescr OBJECT-TYPE
    SYNTAX       SnmpAdminString
    MAX-ACCESS   read-only
    STATUS       current
    DESCRIPTION
        "Cisco Firepower equipment:ServiceDef:descr managed
        object property"
    ::= { cfprApEquipmentServiceDefEntry 5 }

cfprApEquipmentServiceDefIntId OBJECT-TYPE
    SYNTAX       SnmpAdminString
    MAX-ACCESS   read-only
    STATUS       current
    DESCRIPTION
        "Cisco Firepower equipment:ServiceDef:intId managed
        object property"
    ::= { cfprApEquipmentServiceDefEntry 6 }

cfprApEquipmentServiceDefName OBJECT-TYPE
    SYNTAX       SnmpAdminString
    MAX-ACCESS   read-only
    STATUS       current
    DESCRIPTION
        "Cisco Firepower equipment:ServiceDef:name managed
        object property"
    ::= { cfprApEquipmentServiceDefEntry 7 }

cfprApEquipmentServiceDefPolicyLevel OBJECT-TYPE
    SYNTAX       Gauge32
    MAX-ACCESS   read-only
    STATUS       current
    DESCRIPTION
        "Cisco Firepower equipment:ServiceDef:policyLevel
        managed object property"
    ::= { cfprApEquipmentServiceDefEntry 8 }

cfprApEquipmentServiceDefPolicyOwner OBJECT-TYPE
    SYNTAX       CfprApPolicyPolicyOwner
    MAX-ACCESS   read-only
    STATUS       current
    DESCRIPTION
        "Cisco Firepower equipment:ServiceDef:policyOwner
        managed object property"
    ::= { cfprApEquipmentServiceDefEntry 9 }

cfprApEquipmentServiceDefRemovalConditions OBJECT-TYPE
    SYNTAX       CfprApEquipmentRemovalConditions
    MAX-ACCESS   read-only
    STATUS       current
    DESCRIPTION
        "Cisco Firepower equipment:ServiceDef:removalConditions
        managed object property"
    ::= { cfprApEquipmentServiceDefEntry 10 }

cfprApEquipmentServiceDefServicePhilosophy OBJECT-TYPE
    SYNTAX       SnmpAdminString
    MAX-ACCESS   read-only
    STATUS       current
    DESCRIPTION
        "Cisco Firepower equipment:ServiceDef:servicePhilosophy
        managed object property"
    ::= { cfprApEquipmentServiceDefEntry 11 }

cfprApEquipmentSlotArrayTable OBJECT-TYPE
    SYNTAX           SEQUENCE OF CfprApEquipmentSlotArrayEntry
    MAX-ACCESS       not-accessible
    STATUS           current
    DESCRIPTION
        "Cisco Firepower equipment:SlotArray managed object table"
    ::= { cfprApEquipmentObjects 132 }

cfprApEquipmentSlotArrayEntry OBJECT-TYPE
    SYNTAX           CfprApEquipmentSlotArrayEntry
    MAX-ACCESS       not-accessible
    STATUS           current
    DESCRIPTION
        "Entry for the cfprApEquipmentSlotArrayTable table."
    INDEX { cfprApEquipmentSlotArrayInstanceId }
    ::= { cfprApEquipmentSlotArrayTable 1 }

CfprApEquipmentSlotArrayEntry ::= SEQUENCE {
    cfprApEquipmentSlotArrayInstanceId                               CfprApManagedObjectId,
    cfprApEquipmentSlotArrayDn                                       CfprApManagedObjectDn,
    cfprApEquipmentSlotArrayRn                                       SnmpAdminString,
    cfprApEquipmentSlotArrayDescr                                    SnmpAdminString,
    cfprApEquipmentSlotArrayFirstIndex                               Gauge32,
    cfprApEquipmentSlotArrayHeight                                   INTEGER,
    cfprApEquipmentSlotArrayHorizontalStartOffset                    INTEGER,
    cfprApEquipmentSlotArrayInlineGroupSeparation                    INTEGER,
    cfprApEquipmentSlotArrayInlineGroupSize                          Gauge32,
    cfprApEquipmentSlotArrayInlineOffset                             INTEGER,
    cfprApEquipmentSlotArrayIntId                                    SnmpAdminString,
    cfprApEquipmentSlotArrayLocation                                 CfprApEquipmentSlotArrayLocation,
    cfprApEquipmentSlotArrayName                                     SnmpAdminString,
    cfprApEquipmentSlotArrayNumberOfSlots                            Gauge32,
    cfprApEquipmentSlotArrayOrientation                              CfprApEquipmentSlotArrayOrientation,
    cfprApEquipmentSlotArrayPolicyLevel                              Gauge32,
    cfprApEquipmentSlotArrayPolicyOwner                              CfprApPolicyPolicyOwner,
    cfprApEquipmentSlotArraySelector                                 CfprApEquipmentSlotArraySelector,
    cfprApEquipmentSlotArraySlotsPerLine                             Gauge32,
    cfprApEquipmentSlotArrayTransverseGroupSeparation                INTEGER,
    cfprApEquipmentSlotArrayTransverseGroupSize                      Gauge32,
    cfprApEquipmentSlotArrayTransverseOffset                         INTEGER,
    cfprApEquipmentSlotArrayVerticalStartOffset                      INTEGER,
    cfprApEquipmentSlotArrayWidth                                    INTEGER
}

cfprApEquipmentSlotArrayInstanceId OBJECT-TYPE
    SYNTAX       CfprApManagedObjectId
    MAX-ACCESS   not-accessible
    STATUS       current
    DESCRIPTION
        "Instance identifier of the managed object."
    ::= { cfprApEquipmentSlotArrayEntry 1 }

cfprApEquipmentSlotArrayDn OBJECT-TYPE
    SYNTAX       CfprApManagedObjectDn
    MAX-ACCESS   read-only
    STATUS       current
    DESCRIPTION
        "Cisco Firepower equipment:SlotArray:dn managed object property"
    ::= { cfprApEquipmentSlotArrayEntry 2 }

cfprApEquipmentSlotArrayRn OBJECT-TYPE
    SYNTAX       SnmpAdminString
    MAX-ACCESS   read-only
    STATUS       current
    DESCRIPTION
        "Cisco Firepower equipment:SlotArray:rn managed object property"
    ::= { cfprApEquipmentSlotArrayEntry 3 }

cfprApEquipmentSlotArrayDescr OBJECT-TYPE
    SYNTAX       SnmpAdminString
    MAX-ACCESS   read-only
    STATUS       current
    DESCRIPTION
        "Cisco Firepower equipment:SlotArray:descr managed
        object property"
    ::= { cfprApEquipmentSlotArrayEntry 4 }

cfprApEquipmentSlotArrayFirstIndex OBJECT-TYPE
    SYNTAX       Gauge32
    MAX-ACCESS   read-only
    STATUS       current
    DESCRIPTION
        "Cisco Firepower equipment:SlotArray:firstIndex
        managed object property"
    ::= { cfprApEquipmentSlotArrayEntry 5 }

cfprApEquipmentSlotArrayHeight OBJECT-TYPE
    SYNTAX       INTEGER
    MAX-ACCESS   read-only
    STATUS       current
    DESCRIPTION
        "Cisco Firepower equipment:SlotArray:height managed
        object property"
    ::= { cfprApEquipmentSlotArrayEntry 6 }

cfprApEquipmentSlotArrayHorizontalStartOffset OBJECT-TYPE
    SYNTAX       INTEGER
    MAX-ACCESS   read-only
    STATUS       current
    DESCRIPTION
        "Cisco Firepower equipment:SlotArray:horizontalStartOffset
        managed object property"
    ::= { cfprApEquipmentSlotArrayEntry 7 }

cfprApEquipmentSlotArrayInlineGroupSeparation OBJECT-TYPE
    SYNTAX       INTEGER
    MAX-ACCESS   read-only
    STATUS       current
    DESCRIPTION
        "Cisco Firepower equipment:SlotArray:inlineGroupSeparation
        managed object property"
    ::= { cfprApEquipmentSlotArrayEntry 8 }

cfprApEquipmentSlotArrayInlineGroupSize OBJECT-TYPE
    SYNTAX       Gauge32
    MAX-ACCESS   read-only
    STATUS       current
    DESCRIPTION
        "Cisco Firepower equipment:SlotArray:inlineGroupSize
        managed object property"
    ::= { cfprApEquipmentSlotArrayEntry 9 }

cfprApEquipmentSlotArrayInlineOffset OBJECT-TYPE
    SYNTAX       INTEGER
    MAX-ACCESS   read-only
    STATUS       current
    DESCRIPTION
        "Cisco Firepower equipment:SlotArray:inlineOffset
        managed object property"
    ::= { cfprApEquipmentSlotArrayEntry 10 }

cfprApEquipmentSlotArrayIntId OBJECT-TYPE
    SYNTAX       SnmpAdminString
    MAX-ACCESS   read-only
    STATUS       current
    DESCRIPTION
        "Cisco Firepower equipment:SlotArray:intId managed
        object property"
    ::= { cfprApEquipmentSlotArrayEntry 11 }

cfprApEquipmentSlotArrayLocation OBJECT-TYPE
    SYNTAX       CfprApEquipmentSlotArrayLocation
    MAX-ACCESS   read-only
    STATUS       current
    DESCRIPTION
        "Cisco Firepower equipment:SlotArray:location managed
        object property"
    ::= { cfprApEquipmentSlotArrayEntry 12 }

cfprApEquipmentSlotArrayName OBJECT-TYPE
    SYNTAX       SnmpAdminString
    MAX-ACCESS   read-only
    STATUS       current
    DESCRIPTION
        "Cisco Firepower equipment:SlotArray:name managed object property"
    ::= { cfprApEquipmentSlotArrayEntry 13 }

cfprApEquipmentSlotArrayNumberOfSlots OBJECT-TYPE
    SYNTAX       Gauge32
    MAX-ACCESS   read-only
    STATUS       current
    DESCRIPTION
        "Cisco Firepower equipment:SlotArray:numberOfSlots
        managed object property"
    ::= { cfprApEquipmentSlotArrayEntry 14 }

cfprApEquipmentSlotArrayOrientation OBJECT-TYPE
    SYNTAX       CfprApEquipmentSlotArrayOrientation
    MAX-ACCESS   read-only
    STATUS       current
    DESCRIPTION
        "Cisco Firepower equipment:SlotArray:orientation
        managed object property"
    ::= { cfprApEquipmentSlotArrayEntry 15 }

cfprApEquipmentSlotArrayPolicyLevel OBJECT-TYPE
    SYNTAX       Gauge32
    MAX-ACCESS   read-only
    STATUS       current
    DESCRIPTION
        "Cisco Firepower equipment:SlotArray:policyLevel
        managed object property"
    ::= { cfprApEquipmentSlotArrayEntry 16 }

cfprApEquipmentSlotArrayPolicyOwner OBJECT-TYPE
    SYNTAX       CfprApPolicyPolicyOwner
    MAX-ACCESS   read-only
    STATUS       current
    DESCRIPTION
        "Cisco Firepower equipment:SlotArray:policyOwner
        managed object property"
    ::= { cfprApEquipmentSlotArrayEntry 17 }

cfprApEquipmentSlotArraySelector OBJECT-TYPE
    SYNTAX       CfprApEquipmentSlotArraySelector
    MAX-ACCESS   read-only
    STATUS       current
    DESCRIPTION
        "Cisco Firepower equipment:SlotArray:selector managed
        object property"
    ::= { cfprApEquipmentSlotArrayEntry 18 }

cfprApEquipmentSlotArraySlotsPerLine OBJECT-TYPE
    SYNTAX       Gauge32
    MAX-ACCESS   read-only
    STATUS       current
    DESCRIPTION
        "Cisco Firepower equipment:SlotArray:slotsPerLine
        managed object property"
    ::= { cfprApEquipmentSlotArrayEntry 19 }

cfprApEquipmentSlotArrayTransverseGroupSeparation OBJECT-TYPE
    SYNTAX       INTEGER
    MAX-ACCESS   read-only
    STATUS       current
    DESCRIPTION
        "Cisco Firepower equipment:SlotArray:transverseGroupSeparation
        managed object property"
    ::= { cfprApEquipmentSlotArrayEntry 20 }

cfprApEquipmentSlotArrayTransverseGroupSize OBJECT-TYPE
    SYNTAX       Gauge32
    MAX-ACCESS   read-only
    STATUS       current
    DESCRIPTION
        "Cisco Firepower equipment:SlotArray:transverseGroupSize
        managed object property"
    ::= { cfprApEquipmentSlotArrayEntry 21 }

cfprApEquipmentSlotArrayTransverseOffset OBJECT-TYPE
    SYNTAX       INTEGER
    MAX-ACCESS   read-only
    STATUS       current
    DESCRIPTION
        "Cisco Firepower equipment:SlotArray:transverseOffset
        managed object property"
    ::= { cfprApEquipmentSlotArrayEntry 22 }

cfprApEquipmentSlotArrayVerticalStartOffset OBJECT-TYPE
    SYNTAX       INTEGER
    MAX-ACCESS   read-only
    STATUS       current
    DESCRIPTION
        "Cisco Firepower equipment:SlotArray:verticalStartOffset
        managed object property"
    ::= { cfprApEquipmentSlotArrayEntry 23 }

cfprApEquipmentSlotArrayWidth OBJECT-TYPE
    SYNTAX       INTEGER
    MAX-ACCESS   read-only
    STATUS       current
    DESCRIPTION
        "Cisco Firepower equipment:SlotArray:width managed
        object property"
    ::= { cfprApEquipmentSlotArrayEntry 24 }

cfprApEquipmentSlotArrayRefTable OBJECT-TYPE
    SYNTAX           SEQUENCE OF CfprApEquipmentSlotArrayRefEntry
    MAX-ACCESS       not-accessible
    STATUS           current
    DESCRIPTION
        "Cisco Firepower equipment:SlotArrayRef managed object table"
    ::= { cfprApEquipmentObjects 133 }

cfprApEquipmentSlotArrayRefEntry OBJECT-TYPE
    SYNTAX           CfprApEquipmentSlotArrayRefEntry
    MAX-ACCESS       not-accessible
    STATUS           current
    DESCRIPTION
        "Entry for the cfprApEquipmentSlotArrayRefTable table."
    INDEX { cfprApEquipmentSlotArrayRefInstanceId }
    ::= { cfprApEquipmentSlotArrayRefTable 1 }

CfprApEquipmentSlotArrayRefEntry ::= SEQUENCE {
    cfprApEquipmentSlotArrayRefInstanceId                            CfprApManagedObjectId,
    cfprApEquipmentSlotArrayRefDn                                    CfprApManagedObjectDn,
    cfprApEquipmentSlotArrayRefRn                                    SnmpAdminString,
    cfprApEquipmentSlotArrayRefDescr                                 SnmpAdminString,
    cfprApEquipmentSlotArrayRefIntId                                 SnmpAdminString,
    cfprApEquipmentSlotArrayRefName                                  SnmpAdminString,
    cfprApEquipmentSlotArrayRefNumberOfSlotsSpanned                  Gauge32,
    cfprApEquipmentSlotArrayRefPolicyLevel                           Gauge32,
    cfprApEquipmentSlotArrayRefPolicyOwner                           CfprApPolicyPolicyOwner,
    cfprApEquipmentSlotArrayRefSlotSpanOrientation                   CfprApEquipmentSlotSpanOrientation,
    cfprApEquipmentSlotArrayRefTargetDn                              SnmpAdminString
}

cfprApEquipmentSlotArrayRefInstanceId OBJECT-TYPE
    SYNTAX       CfprApManagedObjectId
    MAX-ACCESS   not-accessible
    STATUS       current
    DESCRIPTION
        "Instance identifier of the managed object."
    ::= { cfprApEquipmentSlotArrayRefEntry 1 }

cfprApEquipmentSlotArrayRefDn OBJECT-TYPE
    SYNTAX       CfprApManagedObjectDn
    MAX-ACCESS   read-only
    STATUS       current
    DESCRIPTION
        "Cisco Firepower equipment:SlotArrayRef:dn managed
        object property"
    ::= { cfprApEquipmentSlotArrayRefEntry 2 }

cfprApEquipmentSlotArrayRefRn OBJECT-TYPE
    SYNTAX       SnmpAdminString
    MAX-ACCESS   read-only
    STATUS       current
    DESCRIPTION
        "Cisco Firepower equipment:SlotArrayRef:rn managed
        object property"
    ::= { cfprApEquipmentSlotArrayRefEntry 3 }

cfprApEquipmentSlotArrayRefDescr OBJECT-TYPE
    SYNTAX       SnmpAdminString
    MAX-ACCESS   read-only
    STATUS       current
    DESCRIPTION
        "Cisco Firepower equipment:SlotArrayRef:descr managed
        object property"
    ::= { cfprApEquipmentSlotArrayRefEntry 4 }

cfprApEquipmentSlotArrayRefIntId OBJECT-TYPE
    SYNTAX       SnmpAdminString
    MAX-ACCESS   read-only
    STATUS       current
    DESCRIPTION
        "Cisco Firepower equipment:SlotArrayRef:intId managed
        object property"
    ::= { cfprApEquipmentSlotArrayRefEntry 5 }

cfprApEquipmentSlotArrayRefName OBJECT-TYPE
    SYNTAX       SnmpAdminString
    MAX-ACCESS   read-only
    STATUS       current
    DESCRIPTION
        "Cisco Firepower equipment:SlotArrayRef:name managed
        object property"
    ::= { cfprApEquipmentSlotArrayRefEntry 6 }

cfprApEquipmentSlotArrayRefNumberOfSlotsSpanned OBJECT-TYPE
    SYNTAX       Gauge32
    MAX-ACCESS   read-only
    STATUS       current
    DESCRIPTION
        "Cisco Firepower equipment:SlotArrayRef:numberOfSlotsSpanned
        managed object property"
    ::= { cfprApEquipmentSlotArrayRefEntry 7 }

cfprApEquipmentSlotArrayRefPolicyLevel OBJECT-TYPE
    SYNTAX       Gauge32
    MAX-ACCESS   read-only
    STATUS       current
    DESCRIPTION
        "Cisco Firepower equipment:SlotArrayRef:policyLevel
        managed object property"
    ::= { cfprApEquipmentSlotArrayRefEntry 8 }

cfprApEquipmentSlotArrayRefPolicyOwner OBJECT-TYPE
    SYNTAX       CfprApPolicyPolicyOwner
    MAX-ACCESS   read-only
    STATUS       current
    DESCRIPTION
        "Cisco Firepower equipment:SlotArrayRef:policyOwner
        managed object property"
    ::= { cfprApEquipmentSlotArrayRefEntry 9 }

cfprApEquipmentSlotArrayRefSlotSpanOrientation OBJECT-TYPE
    SYNTAX       CfprApEquipmentSlotSpanOrientation
    MAX-ACCESS   read-only
    STATUS       current
    DESCRIPTION
        "Cisco Firepower equipment:SlotArrayRef:slotSpanOrientation
        managed object property"
    ::= { cfprApEquipmentSlotArrayRefEntry 10 }

cfprApEquipmentSlotArrayRefTargetDn OBJECT-TYPE
    SYNTAX       SnmpAdminString
    MAX-ACCESS   read-only
    STATUS       current
    DESCRIPTION
        "Cisco Firepower equipment:SlotArrayRef:targetDn
        managed object property"
    ::= { cfprApEquipmentSlotArrayRefEntry 11 }

cfprApEquipmentSwitchCapTable OBJECT-TYPE
    SYNTAX           SEQUENCE OF CfprApEquipmentSwitchCapEntry
    MAX-ACCESS       not-accessible
    STATUS           current
    DESCRIPTION
        "Cisco Firepower equipment:SwitchCap managed object table"
    ::= { cfprApEquipmentObjects 134 }

cfprApEquipmentSwitchCapEntry OBJECT-TYPE
    SYNTAX           CfprApEquipmentSwitchCapEntry
    MAX-ACCESS       not-accessible
    STATUS           current
    DESCRIPTION
        "Entry for the cfprApEquipmentSwitchCapTable table."
    INDEX { cfprApEquipmentSwitchCapInstanceId }
    ::= { cfprApEquipmentSwitchCapTable 1 }

CfprApEquipmentSwitchCapEntry ::= SEQUENCE {
    cfprApEquipmentSwitchCapInstanceId                               CfprApManagedObjectId,
    cfprApEquipmentSwitchCapDn                                       CfprApManagedObjectDn,
    cfprApEquipmentSwitchCapRn                                       SnmpAdminString,
    cfprApEquipmentSwitchCapBreakoutIfSupported                      TruthValue,
    cfprApEquipmentSwitchCapDescr                                    SnmpAdminString,
    cfprApEquipmentSwitchCapFanModulesSupported                      TruthValue,
    cfprApEquipmentSwitchCapIntId                                    SnmpAdminString,
    cfprApEquipmentSwitchCapLocatorBeaconSupported                   TruthValue,
    cfprApEquipmentSwitchCapMaxActiveSpanSessionCount                Gauge32,
    cfprApEquipmentSwitchCapMaxEth1gPort                             Gauge32,
    cfprApEquipmentSwitchCapMaxEth1gSlot                             Gauge32,
    cfprApEquipmentSwitchCapMaxEthPcMembers                          Gauge32,
    cfprApEquipmentSwitchCapMaxEthPcs                                Gauge32,
    cfprApEquipmentSwitchCapMaxFcoePcMembers                         Gauge32,
    cfprApEquipmentSwitchCapMaxUplinkPorts                           Gauge32,
    cfprApEquipmentSwitchCapMgmtDaughterCardSlotId                   Gauge32,
    cfprApEquipmentSwitchCapName                                     SnmpAdminString,
    cfprApEquipmentSwitchCapPolicyLevel                              Gauge32,
    cfprApEquipmentSwitchCapPolicyOwner                              CfprApPolicyPolicyOwner,
    cfprApEquipmentSwitchCapSerenoNetflowSupported                   TruthValue
}

cfprApEquipmentSwitchCapInstanceId OBJECT-TYPE
    SYNTAX       CfprApManagedObjectId
    MAX-ACCESS   not-accessible
    STATUS       current
    DESCRIPTION
        "Instance identifier of the managed object."
    ::= { cfprApEquipmentSwitchCapEntry 1 }

cfprApEquipmentSwitchCapDn OBJECT-TYPE
    SYNTAX       CfprApManagedObjectDn
    MAX-ACCESS   read-only
    STATUS       current
    DESCRIPTION
        "Cisco Firepower equipment:SwitchCap:dn managed object property"
    ::= { cfprApEquipmentSwitchCapEntry 2 }

cfprApEquipmentSwitchCapRn OBJECT-TYPE
    SYNTAX       SnmpAdminString
    MAX-ACCESS   read-only
    STATUS       current
    DESCRIPTION
        "Cisco Firepower equipment:SwitchCap:rn managed object property"
    ::= { cfprApEquipmentSwitchCapEntry 3 }

cfprApEquipmentSwitchCapBreakoutIfSupported OBJECT-TYPE
    SYNTAX       TruthValue
    MAX-ACCESS   read-only
    STATUS       current
    DESCRIPTION
        "Cisco Firepower equipment:SwitchCap:breakoutIfSupported
        managed object property"
    ::= { cfprApEquipmentSwitchCapEntry 4 }

cfprApEquipmentSwitchCapDescr OBJECT-TYPE
    SYNTAX       SnmpAdminString
    MAX-ACCESS   read-only
    STATUS       current
    DESCRIPTION
        "Cisco Firepower equipment:SwitchCap:descr managed
        object property"
    ::= { cfprApEquipmentSwitchCapEntry 5 }

cfprApEquipmentSwitchCapFanModulesSupported OBJECT-TYPE
    SYNTAX       TruthValue
    MAX-ACCESS   read-only
    STATUS       current
    DESCRIPTION
        "Cisco Firepower equipment:SwitchCap:fanModulesSupported
        managed object property"
    ::= { cfprApEquipmentSwitchCapEntry 6 }

cfprApEquipmentSwitchCapIntId OBJECT-TYPE
    SYNTAX       SnmpAdminString
    MAX-ACCESS   read-only
    STATUS       current
    DESCRIPTION
        "Cisco Firepower equipment:SwitchCap:intId managed
        object property"
    ::= { cfprApEquipmentSwitchCapEntry 7 }

cfprApEquipmentSwitchCapLocatorBeaconSupported OBJECT-TYPE
    SYNTAX       TruthValue
    MAX-ACCESS   read-only
    STATUS       current
    DESCRIPTION
        "Cisco Firepower equipment:SwitchCap:locatorBeaconSupported
        managed object property"
    ::= { cfprApEquipmentSwitchCapEntry 8 }

cfprApEquipmentSwitchCapMaxActiveSpanSessionCount OBJECT-TYPE
    SYNTAX       Gauge32
    MAX-ACCESS   read-only
    STATUS       current
    DESCRIPTION
        "Cisco Firepower equipment:SwitchCap:maxActiveSpanSessionCount
        managed object property"
    ::= { cfprApEquipmentSwitchCapEntry 9 }

cfprApEquipmentSwitchCapMaxEth1gPort OBJECT-TYPE
    SYNTAX       Gauge32
    MAX-ACCESS   read-only
    STATUS       current
    DESCRIPTION
        "Cisco Firepower equipment:SwitchCap:maxEth1gPort
        managed object property"
    ::= { cfprApEquipmentSwitchCapEntry 10 }

cfprApEquipmentSwitchCapMaxEth1gSlot OBJECT-TYPE
    SYNTAX       Gauge32
    MAX-ACCESS   read-only
    STATUS       current
    DESCRIPTION
        "Cisco Firepower equipment:SwitchCap:maxEth1gSlot
        managed object property"
    ::= { cfprApEquipmentSwitchCapEntry 11 }

cfprApEquipmentSwitchCapMaxEthPcMembers OBJECT-TYPE
    SYNTAX       Gauge32
    MAX-ACCESS   read-only
    STATUS       current
    DESCRIPTION
        "Cisco Firepower equipment:SwitchCap:maxEthPcMembers
        managed object property"
    ::= { cfprApEquipmentSwitchCapEntry 12 }

cfprApEquipmentSwitchCapMaxEthPcs OBJECT-TYPE
    SYNTAX       Gauge32
    MAX-ACCESS   read-only
    STATUS       current
    DESCRIPTION
        "Cisco Firepower equipment:SwitchCap:maxEthPcs
        managed object property"
    ::= { cfprApEquipmentSwitchCapEntry 13 }

cfprApEquipmentSwitchCapMaxFcoePcMembers OBJECT-TYPE
    SYNTAX       Gauge32
    MAX-ACCESS   read-only
    STATUS       current
    DESCRIPTION
        "Cisco Firepower equipment:SwitchCap:maxFcoePcMembers
        managed object property"
    ::= { cfprApEquipmentSwitchCapEntry 14 }

cfprApEquipmentSwitchCapMaxUplinkPorts OBJECT-TYPE
    SYNTAX       Gauge32
    MAX-ACCESS   read-only
    STATUS       current
    DESCRIPTION
        "Cisco Firepower equipment:SwitchCap:maxUplinkPorts
        managed object property"
    ::= { cfprApEquipmentSwitchCapEntry 15 }

cfprApEquipmentSwitchCapMgmtDaughterCardSlotId OBJECT-TYPE
    SYNTAX       Gauge32
    MAX-ACCESS   read-only
    STATUS       current
    DESCRIPTION
        "Cisco Firepower equipment:SwitchCap:mgmtDaughterCardSlotId
        managed object property"
    ::= { cfprApEquipmentSwitchCapEntry 16 }

cfprApEquipmentSwitchCapName OBJECT-TYPE
    SYNTAX       SnmpAdminString
    MAX-ACCESS   read-only
    STATUS       current
    DESCRIPTION
        "Cisco Firepower equipment:SwitchCap:name managed object property"
    ::= { cfprApEquipmentSwitchCapEntry 17 }

cfprApEquipmentSwitchCapPolicyLevel OBJECT-TYPE
    SYNTAX       Gauge32
    MAX-ACCESS   read-only
    STATUS       current
    DESCRIPTION
        "Cisco Firepower equipment:SwitchCap:policyLevel
        managed object property"
    ::= { cfprApEquipmentSwitchCapEntry 18 }

cfprApEquipmentSwitchCapPolicyOwner OBJECT-TYPE
    SYNTAX       CfprApPolicyPolicyOwner
    MAX-ACCESS   read-only
    STATUS       current
    DESCRIPTION
        "Cisco Firepower equipment:SwitchCap:policyOwner
        managed object property"
    ::= { cfprApEquipmentSwitchCapEntry 19 }

cfprApEquipmentSwitchCapSerenoNetflowSupported OBJECT-TYPE
    SYNTAX       TruthValue
    MAX-ACCESS   read-only
    STATUS       current
    DESCRIPTION
        "Cisco Firepower equipment:SwitchCap:serenoNetflowSupported
        managed object property"
    ::= { cfprApEquipmentSwitchCapEntry 20 }

cfprApEquipmentSwitchCapProviderTable OBJECT-TYPE
    SYNTAX           SEQUENCE OF CfprApEquipmentSwitchCapProviderEntry
    MAX-ACCESS       not-accessible
    STATUS           current
    DESCRIPTION
        "Cisco Firepower equipment:SwitchCapProvider managed object table"
    ::= { cfprApEquipmentObjects 135 }

cfprApEquipmentSwitchCapProviderEntry OBJECT-TYPE
    SYNTAX           CfprApEquipmentSwitchCapProviderEntry
    MAX-ACCESS       not-accessible
    STATUS           current
    DESCRIPTION
        "Entry for the cfprApEquipmentSwitchCapProviderTable table."
    INDEX { cfprApEquipmentSwitchCapProviderInstanceId }
    ::= { cfprApEquipmentSwitchCapProviderTable 1 }

CfprApEquipmentSwitchCapProviderEntry ::= SEQUENCE {
    cfprApEquipmentSwitchCapProviderInstanceId                       CfprApManagedObjectId,
    cfprApEquipmentSwitchCapProviderDn                               CfprApManagedObjectDn,
    cfprApEquipmentSwitchCapProviderRn                               SnmpAdminString,
    cfprApEquipmentSwitchCapProviderDeleted                          TruthValue,
    cfprApEquipmentSwitchCapProviderDeprecated                       TruthValue,
    cfprApEquipmentSwitchCapProviderElementLoadFailures              Gauge32,
    cfprApEquipmentSwitchCapProviderElementsLoaded                   Gauge32,
    cfprApEquipmentSwitchCapProviderExpectedMemory                   Gauge32,
    cfprApEquipmentSwitchCapProviderGencount                         Gauge32,
    cfprApEquipmentSwitchCapProviderLoadErrors                       Gauge32,
    cfprApEquipmentSwitchCapProviderLoadWarnings                     Gauge32,
    cfprApEquipmentSwitchCapProviderMgmtPlaneVer                     SnmpAdminString,
    cfprApEquipmentSwitchCapProviderModel                            SnmpAdminString,
    cfprApEquipmentSwitchCapProviderPromCardType                     Gauge32,
    cfprApEquipmentSwitchCapProviderRevision                         SnmpAdminString,
    cfprApEquipmentSwitchCapProviderVendor                           SnmpAdminString
}

cfprApEquipmentSwitchCapProviderInstanceId OBJECT-TYPE
    SYNTAX       CfprApManagedObjectId
    MAX-ACCESS   not-accessible
    STATUS       current
    DESCRIPTION
        "Instance identifier of the managed object."
    ::= { cfprApEquipmentSwitchCapProviderEntry 1 }

cfprApEquipmentSwitchCapProviderDn OBJECT-TYPE
    SYNTAX       CfprApManagedObjectDn
    MAX-ACCESS   read-only
    STATUS       current
    DESCRIPTION
        "Cisco Firepower equipment:SwitchCapProvider:dn
        managed object property"
    ::= { cfprApEquipmentSwitchCapProviderEntry 2 }

cfprApEquipmentSwitchCapProviderRn OBJECT-TYPE
    SYNTAX       SnmpAdminString
    MAX-ACCESS   read-only
    STATUS       current
    DESCRIPTION
        "Cisco Firepower equipment:SwitchCapProvider:rn
        managed object property"
    ::= { cfprApEquipmentSwitchCapProviderEntry 3 }

cfprApEquipmentSwitchCapProviderDeleted OBJECT-TYPE
    SYNTAX       TruthValue
    MAX-ACCESS   read-only
    STATUS       current
    DESCRIPTION
        "Cisco Firepower equipment:SwitchCapProvider:deleted
        managed object property"
    ::= { cfprApEquipmentSwitchCapProviderEntry 4 }

cfprApEquipmentSwitchCapProviderDeprecated OBJECT-TYPE
    SYNTAX       TruthValue
    MAX-ACCESS   read-only
    STATUS       current
    DESCRIPTION
        "Cisco Firepower equipment:SwitchCapProvider:deprecated
        managed object property"
    ::= { cfprApEquipmentSwitchCapProviderEntry 5 }

cfprApEquipmentSwitchCapProviderElementLoadFailures OBJECT-TYPE
    SYNTAX       Gauge32
    MAX-ACCESS   read-only
    STATUS       current
    DESCRIPTION
        "Cisco Firepower equipment:SwitchCapProvider:elementLoadFailures
        managed object property"
    ::= { cfprApEquipmentSwitchCapProviderEntry 6 }

cfprApEquipmentSwitchCapProviderElementsLoaded OBJECT-TYPE
    SYNTAX       Gauge32
    MAX-ACCESS   read-only
    STATUS       current
    DESCRIPTION
        "Cisco Firepower equipment:SwitchCapProvider:elementsLoaded
        managed object property"
    ::= { cfprApEquipmentSwitchCapProviderEntry 7 }

cfprApEquipmentSwitchCapProviderExpectedMemory OBJECT-TYPE
    SYNTAX       Gauge32
    MAX-ACCESS   read-only
    STATUS       current
    DESCRIPTION
        "Cisco Firepower equipment:SwitchCapProvider:expectedMemory
        managed object property"
    ::= { cfprApEquipmentSwitchCapProviderEntry 8 }

cfprApEquipmentSwitchCapProviderGencount OBJECT-TYPE
    SYNTAX       Gauge32
    MAX-ACCESS   read-only
    STATUS       current
    DESCRIPTION
        "Cisco Firepower equipment:SwitchCapProvider:gencount
        managed object property"
    ::= { cfprApEquipmentSwitchCapProviderEntry 9 }

cfprApEquipmentSwitchCapProviderLoadErrors OBJECT-TYPE
    SYNTAX       Gauge32
    MAX-ACCESS   read-only
    STATUS       current
    DESCRIPTION
        "Cisco Firepower equipment:SwitchCapProvider:loadErrors
        managed object property"
    ::= { cfprApEquipmentSwitchCapProviderEntry 10 }

cfprApEquipmentSwitchCapProviderLoadWarnings OBJECT-TYPE
    SYNTAX       Gauge32
    MAX-ACCESS   read-only
    STATUS       current
    DESCRIPTION
        "Cisco Firepower equipment:SwitchCapProvider:loadWarnings
        managed object property"
    ::= { cfprApEquipmentSwitchCapProviderEntry 11 }

cfprApEquipmentSwitchCapProviderMgmtPlaneVer OBJECT-TYPE
    SYNTAX       SnmpAdminString
    MAX-ACCESS   read-only
    STATUS       current
    DESCRIPTION
        "Cisco Firepower equipment:SwitchCapProvider:mgmtPlaneVer
        managed object property"
    ::= { cfprApEquipmentSwitchCapProviderEntry 12 }

cfprApEquipmentSwitchCapProviderModel OBJECT-TYPE
    SYNTAX       SnmpAdminString
    MAX-ACCESS   read-only
    STATUS       current
    DESCRIPTION
        "Cisco Firepower equipment:SwitchCapProvider:model
        managed object property"
    ::= { cfprApEquipmentSwitchCapProviderEntry 13 }

cfprApEquipmentSwitchCapProviderPromCardType OBJECT-TYPE
    SYNTAX       Gauge32
    MAX-ACCESS   read-only
    STATUS       current
    DESCRIPTION
        "Cisco Firepower equipment:SwitchCapProvider:promCardType
        managed object property"
    ::= { cfprApEquipmentSwitchCapProviderEntry 14 }

cfprApEquipmentSwitchCapProviderRevision OBJECT-TYPE
    SYNTAX       SnmpAdminString
    MAX-ACCESS   read-only
    STATUS       current
    DESCRIPTION
        "Cisco Firepower equipment:SwitchCapProvider:revision
        managed object property"
    ::= { cfprApEquipmentSwitchCapProviderEntry 15 }

cfprApEquipmentSwitchCapProviderVendor OBJECT-TYPE
    SYNTAX       SnmpAdminString
    MAX-ACCESS   read-only
    STATUS       current
    DESCRIPTION
        "Cisco Firepower equipment:SwitchCapProvider:vendor
        managed object property"
    ::= { cfprApEquipmentSwitchCapProviderEntry 16 }

cfprApEquipmentSwitchCardTable OBJECT-TYPE
    SYNTAX           SEQUENCE OF CfprApEquipmentSwitchCardEntry
    MAX-ACCESS       not-accessible
    STATUS           current
    DESCRIPTION
        "Cisco Firepower equipment:SwitchCard managed object table"
    ::= { cfprApEquipmentObjects 136 }

cfprApEquipmentSwitchCardEntry OBJECT-TYPE
    SYNTAX           CfprApEquipmentSwitchCardEntry
    MAX-ACCESS       not-accessible
    STATUS           current
    DESCRIPTION
        "Entry for the cfprApEquipmentSwitchCardTable table."
    INDEX { cfprApEquipmentSwitchCardInstanceId }
    ::= { cfprApEquipmentSwitchCardTable 1 }

CfprApEquipmentSwitchCardEntry ::= SEQUENCE {
    cfprApEquipmentSwitchCardInstanceId                              CfprApManagedObjectId,
    cfprApEquipmentSwitchCardDn                                      CfprApManagedObjectDn,
    cfprApEquipmentSwitchCardRn                                      SnmpAdminString,
    cfprApEquipmentSwitchCardAct2FailState                           TruthValue,
    cfprApEquipmentSwitchCardDescr                                   SnmpAdminString,
    cfprApEquipmentSwitchCardFltAggr                                 Unsigned64,
    cfprApEquipmentSwitchCardId                                      Gauge32,
    cfprApEquipmentSwitchCardModel                                   SnmpAdminString,
    cfprApEquipmentSwitchCardNumPorts                                Gauge32,
    cfprApEquipmentSwitchCardOperQualifierReason                     SnmpAdminString,
    cfprApEquipmentSwitchCardOperState                               CfprApEquipmentOperability,
    cfprApEquipmentSwitchCardOperability                             CfprApEquipmentOperability,
    cfprApEquipmentSwitchCardPerf                                    CfprApEquipmentSensorThresholdStatus,
    cfprApEquipmentSwitchCardPower                                   CfprApEquipmentPowerState,
    cfprApEquipmentSwitchCardPresence                                CfprApEquipmentPresence,
    cfprApEquipmentSwitchCardRevision                                SnmpAdminString,
    cfprApEquipmentSwitchCardSerial                                  SnmpAdminString,
    cfprApEquipmentSwitchCardState                                   CfprApEquipmentPowerState,
    cfprApEquipmentSwitchCardThermal                                 CfprApEquipmentSensorThresholdStatus,
    cfprApEquipmentSwitchCardTs                                      DateAndTime,
    cfprApEquipmentSwitchCardVendor                                  SnmpAdminString,
    cfprApEquipmentSwitchCardVoltage                                 CfprApEquipmentSensorThresholdStatus
}

cfprApEquipmentSwitchCardInstanceId OBJECT-TYPE
    SYNTAX       CfprApManagedObjectId
    MAX-ACCESS   not-accessible
    STATUS       current
    DESCRIPTION
        "Instance identifier of the managed object."
    ::= { cfprApEquipmentSwitchCardEntry 1 }

cfprApEquipmentSwitchCardDn OBJECT-TYPE
    SYNTAX       CfprApManagedObjectDn
    MAX-ACCESS   read-only
    STATUS       current
    DESCRIPTION
        "Cisco Firepower equipment:SwitchCard:dn managed object property"
    ::= { cfprApEquipmentSwitchCardEntry 2 }

cfprApEquipmentSwitchCardRn OBJECT-TYPE
    SYNTAX       SnmpAdminString
    MAX-ACCESS   read-only
    STATUS       current
    DESCRIPTION
        "Cisco Firepower equipment:SwitchCard:rn managed object property"
    ::= { cfprApEquipmentSwitchCardEntry 3 }

cfprApEquipmentSwitchCardAct2FailState OBJECT-TYPE
    SYNTAX       TruthValue
    MAX-ACCESS   read-only
    STATUS       current
    DESCRIPTION
        "Cisco Firepower equipment:SwitchCard:act2FailState
        managed object property"
    ::= { cfprApEquipmentSwitchCardEntry 4 }

cfprApEquipmentSwitchCardDescr OBJECT-TYPE
    SYNTAX       SnmpAdminString
    MAX-ACCESS   read-only
    STATUS       current
    DESCRIPTION
        "Cisco Firepower equipment:SwitchCard:descr managed
        object property"
    ::= { cfprApEquipmentSwitchCardEntry 5 }

cfprApEquipmentSwitchCardFltAggr OBJECT-TYPE
    SYNTAX       Unsigned64
    MAX-ACCESS   read-only
    STATUS       current
    DESCRIPTION
        "Cisco Firepower equipment:SwitchCard:fltAggr managed
        object property"
    ::= { cfprApEquipmentSwitchCardEntry 6 }

cfprApEquipmentSwitchCardId OBJECT-TYPE
    SYNTAX       Gauge32
    MAX-ACCESS   read-only
    STATUS       current
    DESCRIPTION
        "Cisco Firepower equipment:SwitchCard:id managed object property"
    ::= { cfprApEquipmentSwitchCardEntry 7 }

cfprApEquipmentSwitchCardModel OBJECT-TYPE
    SYNTAX       SnmpAdminString
    MAX-ACCESS   read-only
    STATUS       current
    DESCRIPTION
        "Cisco Firepower equipment:SwitchCard:model managed
        object property"
    ::= { cfprApEquipmentSwitchCardEntry 8 }

cfprApEquipmentSwitchCardNumPorts OBJECT-TYPE
    SYNTAX       Gauge32
    MAX-ACCESS   read-only
    STATUS       current
    DESCRIPTION
        "Cisco Firepower equipment:SwitchCard:numPorts
        managed object property"
    ::= { cfprApEquipmentSwitchCardEntry 9 }

cfprApEquipmentSwitchCardOperQualifierReason OBJECT-TYPE
    SYNTAX       SnmpAdminString
    MAX-ACCESS   read-only
    STATUS       current
    DESCRIPTION
        "Cisco Firepower equipment:SwitchCard:operQualifierReason
        managed object property"
    ::= { cfprApEquipmentSwitchCardEntry 10 }

cfprApEquipmentSwitchCardOperState OBJECT-TYPE
    SYNTAX       CfprApEquipmentOperability
    MAX-ACCESS   read-only
    STATUS       current
    DESCRIPTION
        "Cisco Firepower equipment:SwitchCard:operState
        managed object property"
    ::= { cfprApEquipmentSwitchCardEntry 11 }

cfprApEquipmentSwitchCardOperability OBJECT-TYPE
    SYNTAX       CfprApEquipmentOperability
    MAX-ACCESS   read-only
    STATUS       current
    DESCRIPTION
        "Cisco Firepower equipment:SwitchCard:operability
        managed object property"
    ::= { cfprApEquipmentSwitchCardEntry 12 }

cfprApEquipmentSwitchCardPerf OBJECT-TYPE
    SYNTAX       CfprApEquipmentSensorThresholdStatus
    MAX-ACCESS   read-only
    STATUS       current
    DESCRIPTION
        "Cisco Firepower equipment:SwitchCard:perf managed
        object property"
    ::= { cfprApEquipmentSwitchCardEntry 13 }

cfprApEquipmentSwitchCardPower OBJECT-TYPE
    SYNTAX       CfprApEquipmentPowerState
    MAX-ACCESS   read-only
    STATUS       current
    DESCRIPTION
        "Cisco Firepower equipment:SwitchCard:power managed
        object property"
    ::= { cfprApEquipmentSwitchCardEntry 14 }

cfprApEquipmentSwitchCardPresence OBJECT-TYPE
    SYNTAX       CfprApEquipmentPresence
    MAX-ACCESS   read-only
    STATUS       current
    DESCRIPTION
        "Cisco Firepower equipment:SwitchCard:presence
        managed object property"
    ::= { cfprApEquipmentSwitchCardEntry 15 }

cfprApEquipmentSwitchCardRevision OBJECT-TYPE
    SYNTAX       SnmpAdminString
    MAX-ACCESS   read-only
    STATUS       current
    DESCRIPTION
        "Cisco Firepower equipment:SwitchCard:revision
        managed object property"
    ::= { cfprApEquipmentSwitchCardEntry 16 }

cfprApEquipmentSwitchCardSerial OBJECT-TYPE
    SYNTAX       SnmpAdminString
    MAX-ACCESS   read-only
    STATUS       current
    DESCRIPTION
        "Cisco Firepower equipment:SwitchCard:serial managed
        object property"
    ::= { cfprApEquipmentSwitchCardEntry 17 }

cfprApEquipmentSwitchCardState OBJECT-TYPE
    SYNTAX       CfprApEquipmentPowerState
    MAX-ACCESS   read-only
    STATUS       current
    DESCRIPTION
        "Cisco Firepower equipment:SwitchCard:state managed
        object property"
    ::= { cfprApEquipmentSwitchCardEntry 18 }

cfprApEquipmentSwitchCardThermal OBJECT-TYPE
    SYNTAX       CfprApEquipmentSensorThresholdStatus
    MAX-ACCESS   read-only
    STATUS       current
    DESCRIPTION
        "Cisco Firepower equipment:SwitchCard:thermal managed
        object property"
    ::= { cfprApEquipmentSwitchCardEntry 19 }

cfprApEquipmentSwitchCardTs OBJECT-TYPE
    SYNTAX       DateAndTime
    MAX-ACCESS   read-only
    STATUS       current
    DESCRIPTION
        "Cisco Firepower equipment:SwitchCard:ts managed object property"
    ::= { cfprApEquipmentSwitchCardEntry 20 }

cfprApEquipmentSwitchCardVendor OBJECT-TYPE
    SYNTAX       SnmpAdminString
    MAX-ACCESS   read-only
    STATUS       current
    DESCRIPTION
        "Cisco Firepower equipment:SwitchCard:vendor managed
        object property"
    ::= { cfprApEquipmentSwitchCardEntry 21 }

cfprApEquipmentSwitchCardVoltage OBJECT-TYPE
    SYNTAX       CfprApEquipmentSensorThresholdStatus
    MAX-ACCESS   read-only
    STATUS       current
    DESCRIPTION
        "Cisco Firepower equipment:SwitchCard:voltage managed
        object property"
    ::= { cfprApEquipmentSwitchCardEntry 22 }

cfprApEquipmentSwitchIOCardTable OBJECT-TYPE
    SYNTAX           SEQUENCE OF CfprApEquipmentSwitchIOCardEntry
    MAX-ACCESS       not-accessible
    STATUS           current
    DESCRIPTION
        "Cisco Firepower equipment:SwitchIOCard managed object table"
    ::= { cfprApEquipmentObjects 137 }

cfprApEquipmentSwitchIOCardEntry OBJECT-TYPE
    SYNTAX           CfprApEquipmentSwitchIOCardEntry
    MAX-ACCESS       not-accessible
    STATUS           current
    DESCRIPTION
        "Entry for the cfprApEquipmentSwitchIOCardTable table."
    INDEX { cfprApEquipmentSwitchIOCardInstanceId }
    ::= { cfprApEquipmentSwitchIOCardTable 1 }

CfprApEquipmentSwitchIOCardEntry ::= SEQUENCE {
    cfprApEquipmentSwitchIOCardInstanceId                            CfprApManagedObjectId,
    cfprApEquipmentSwitchIOCardDn                                    CfprApManagedObjectDn,
    cfprApEquipmentSwitchIOCardRn                                    SnmpAdminString,
    cfprApEquipmentSwitchIOCardAdminPowerState                       CfprApEquipmentAdminPowerState,
    cfprApEquipmentSwitchIOCardBaseAddr                              InetAddressIPv4,
    cfprApEquipmentSwitchIOCardChassisId                             Gauge32,
    cfprApEquipmentSwitchIOCardConfigState                           CfprApEquipmentChassisConfigState,
    cfprApEquipmentSwitchIOCardDiscovery                             CfprApEquipmentDiscoveryState,
    cfprApEquipmentSwitchIOCardFeOfflineTs                           Unsigned64,
    cfprApEquipmentSwitchIOCardFeReadyTs                             Unsigned64,
    cfprApEquipmentSwitchIOCardFltAggr                               Unsigned64,
    cfprApEquipmentSwitchIOCardFsmDescr                              SnmpAdminString,
    cfprApEquipmentSwitchIOCardFsmFlags                              SnmpAdminString,
    cfprApEquipmentSwitchIOCardFsmPrev                               SnmpAdminString,
    cfprApEquipmentSwitchIOCardFsmProgr                              Gauge32,
    cfprApEquipmentSwitchIOCardFsmRmtInvErrCode                      Gauge32,
    cfprApEquipmentSwitchIOCardFsmRmtInvErrDescr                     SnmpAdminString,
    cfprApEquipmentSwitchIOCardFsmRmtInvRslt                         CfprApConditionRemoteInvRslt,
    cfprApEquipmentSwitchIOCardFsmStageDescr                         SnmpAdminString,
    cfprApEquipmentSwitchIOCardFsmStamp                              DateAndTime,
    cfprApEquipmentSwitchIOCardFsmStatus                             SnmpAdminString,
    cfprApEquipmentSwitchIOCardFsmTry                                Gauge32,
    cfprApEquipmentSwitchIOCardId                                    CfprApEquipmentSwitchIOCardId,
    cfprApEquipmentSwitchIOCardLcName                                SnmpAdminString,
    cfprApEquipmentSwitchIOCardLcTs                                  DateAndTime,
    cfprApEquipmentSwitchIOCardMfgTime                               DateAndTime,
    cfprApEquipmentSwitchIOCardModel                                 SnmpAdminString,
    cfprApEquipmentSwitchIOCardOperQualifier                         CfprApEquipmentIOCardIssues,
    cfprApEquipmentSwitchIOCardOperQualifierReason                   SnmpAdminString,
    cfprApEquipmentSwitchIOCardOperState                             CfprApEquipmentOperability,
    cfprApEquipmentSwitchIOCardOperability                           CfprApEquipmentOperability,
    cfprApEquipmentSwitchIOCardPeerCommStatus                        CfprApEquipmentCommStatus,
    cfprApEquipmentSwitchIOCardPeerDn                                SnmpAdminString,
    cfprApEquipmentSwitchIOCardPerf                                  CfprApEquipmentSensorThresholdStatus,
    cfprApEquipmentSwitchIOCardPower                                 CfprApEquipmentPowerState,
    cfprApEquipmentSwitchIOCardPresence                              CfprApEquipmentPresence,
    cfprApEquipmentSwitchIOCardProcessorThermalState                 CfprApEquipmentSensorThresholdStatus,
    cfprApEquipmentSwitchIOCardRevision                              SnmpAdminString,
    cfprApEquipmentSwitchIOCardSerial                                SnmpAdminString,
    cfprApEquipmentSwitchIOCardSide                                  CfprApNetworkSide,
    cfprApEquipmentSwitchIOCardSwitchId                              CfprApNetworkSwitchId,
    cfprApEquipmentSwitchIOCardThermal                               CfprApEquipmentSensorThresholdStatus,
    cfprApEquipmentSwitchIOCardUpgradeStatus                         CfprApMgmtUpgradeStatus,
    cfprApEquipmentSwitchIOCardUsrLbl                                SnmpAdminString,
    cfprApEquipmentSwitchIOCardVendor                                SnmpAdminString,
    cfprApEquipmentSwitchIOCardVoltage                               CfprApEquipmentSensorThresholdStatus
}

cfprApEquipmentSwitchIOCardInstanceId OBJECT-TYPE
    SYNTAX       CfprApManagedObjectId
    MAX-ACCESS   not-accessible
    STATUS       current
    DESCRIPTION
        "Instance identifier of the managed object."
    ::= { cfprApEquipmentSwitchIOCardEntry 1 }

cfprApEquipmentSwitchIOCardDn OBJECT-TYPE
    SYNTAX       CfprApManagedObjectDn
    MAX-ACCESS   read-only
    STATUS       current
    DESCRIPTION
        "Cisco Firepower equipment:SwitchIOCard:dn managed
        object property"
    ::= { cfprApEquipmentSwitchIOCardEntry 2 }

cfprApEquipmentSwitchIOCardRn OBJECT-TYPE
    SYNTAX       SnmpAdminString
    MAX-ACCESS   read-only
    STATUS       current
    DESCRIPTION
        "Cisco Firepower equipment:SwitchIOCard:rn managed
        object property"
    ::= { cfprApEquipmentSwitchIOCardEntry 3 }

cfprApEquipmentSwitchIOCardAdminPowerState OBJECT-TYPE
    SYNTAX       CfprApEquipmentAdminPowerState
    MAX-ACCESS   read-only
    STATUS       current
    DESCRIPTION
        "Cisco Firepower equipment:SwitchIOCard:adminPowerState
        managed object property"
    ::= { cfprApEquipmentSwitchIOCardEntry 4 }

cfprApEquipmentSwitchIOCardBaseAddr OBJECT-TYPE
    SYNTAX       InetAddressIPv4
    MAX-ACCESS   read-only
    STATUS       current
    DESCRIPTION
        "Cisco Firepower equipment:SwitchIOCard:baseAddr
        managed object property"
    ::= { cfprApEquipmentSwitchIOCardEntry 5 }

cfprApEquipmentSwitchIOCardChassisId OBJECT-TYPE
    SYNTAX       Gauge32
    MAX-ACCESS   read-only
    STATUS       current
    DESCRIPTION
        "Cisco Firepower equipment:SwitchIOCard:chassisId
        managed object property"
    ::= { cfprApEquipmentSwitchIOCardEntry 6 }

cfprApEquipmentSwitchIOCardConfigState OBJECT-TYPE
    SYNTAX       CfprApEquipmentChassisConfigState
    MAX-ACCESS   read-only
    STATUS       current
    DESCRIPTION
        "Cisco Firepower equipment:SwitchIOCard:configState
        managed object property"
    ::= { cfprApEquipmentSwitchIOCardEntry 7 }

cfprApEquipmentSwitchIOCardDiscovery OBJECT-TYPE
    SYNTAX       CfprApEquipmentDiscoveryState
    MAX-ACCESS   read-only
    STATUS       current
    DESCRIPTION
        "Cisco Firepower equipment:SwitchIOCard:discovery
        managed object property"
    ::= { cfprApEquipmentSwitchIOCardEntry 8 }

cfprApEquipmentSwitchIOCardFeOfflineTs OBJECT-TYPE
    SYNTAX       Unsigned64
    MAX-ACCESS   read-only
    STATUS       current
    DESCRIPTION
        "Cisco Firepower equipment:SwitchIOCard:feOfflineTs
        managed object property"
    ::= { cfprApEquipmentSwitchIOCardEntry 9 }

cfprApEquipmentSwitchIOCardFeReadyTs OBJECT-TYPE
    SYNTAX       Unsigned64
    MAX-ACCESS   read-only
    STATUS       current
    DESCRIPTION
        "Cisco Firepower equipment:SwitchIOCard:feReadyTs
        managed object property"
    ::= { cfprApEquipmentSwitchIOCardEntry 10 }

cfprApEquipmentSwitchIOCardFltAggr OBJECT-TYPE
    SYNTAX       Unsigned64
    MAX-ACCESS   read-only
    STATUS       current
    DESCRIPTION
        "Cisco Firepower equipment:SwitchIOCard:fltAggr
        managed object property"
    ::= { cfprApEquipmentSwitchIOCardEntry 11 }

cfprApEquipmentSwitchIOCardFsmDescr OBJECT-TYPE
    SYNTAX       SnmpAdminString
    MAX-ACCESS   read-only
    STATUS       current
    DESCRIPTION
        "Cisco Firepower equipment:SwitchIOCard:fsmDescr
        managed object property"
    ::= { cfprApEquipmentSwitchIOCardEntry 12 }

cfprApEquipmentSwitchIOCardFsmFlags OBJECT-TYPE
    SYNTAX       SnmpAdminString
    MAX-ACCESS   read-only
    STATUS       current
    DESCRIPTION
        "Cisco Firepower equipment:SwitchIOCard:fsmFlags
        managed object property"
    ::= { cfprApEquipmentSwitchIOCardEntry 13 }

cfprApEquipmentSwitchIOCardFsmPrev OBJECT-TYPE
    SYNTAX       SnmpAdminString
    MAX-ACCESS   read-only
    STATUS       current
    DESCRIPTION
        "Cisco Firepower equipment:SwitchIOCard:fsmPrev
        managed object property"
    ::= { cfprApEquipmentSwitchIOCardEntry 14 }

cfprApEquipmentSwitchIOCardFsmProgr OBJECT-TYPE
    SYNTAX       Gauge32
    MAX-ACCESS   read-only
    STATUS       current
    DESCRIPTION
        "Cisco Firepower equipment:SwitchIOCard:fsmProgr
        managed object property"
    ::= { cfprApEquipmentSwitchIOCardEntry 15 }

cfprApEquipmentSwitchIOCardFsmRmtInvErrCode OBJECT-TYPE
    SYNTAX       Gauge32
    MAX-ACCESS   read-only
    STATUS       current
    DESCRIPTION
        "Cisco Firepower equipment:SwitchIOCard:fsmRmtInvErrCode
        managed object property"
    ::= { cfprApEquipmentSwitchIOCardEntry 16 }

cfprApEquipmentSwitchIOCardFsmRmtInvErrDescr OBJECT-TYPE
    SYNTAX       SnmpAdminString
    MAX-ACCESS   read-only
    STATUS       current
    DESCRIPTION
        "Cisco Firepower equipment:SwitchIOCard:fsmRmtInvErrDescr
        managed object property"
    ::= { cfprApEquipmentSwitchIOCardEntry 17 }

cfprApEquipmentSwitchIOCardFsmRmtInvRslt OBJECT-TYPE
    SYNTAX       CfprApConditionRemoteInvRslt
    MAX-ACCESS   read-only
    STATUS       current
    DESCRIPTION
        "Cisco Firepower equipment:SwitchIOCard:fsmRmtInvRslt
        managed object property"
    ::= { cfprApEquipmentSwitchIOCardEntry 18 }

cfprApEquipmentSwitchIOCardFsmStageDescr OBJECT-TYPE
    SYNTAX       SnmpAdminString
    MAX-ACCESS   read-only
    STATUS       current
    DESCRIPTION
        "Cisco Firepower equipment:SwitchIOCard:fsmStageDescr
        managed object property"
    ::= { cfprApEquipmentSwitchIOCardEntry 19 }

cfprApEquipmentSwitchIOCardFsmStamp OBJECT-TYPE
    SYNTAX       DateAndTime
    MAX-ACCESS   read-only
    STATUS       current
    DESCRIPTION
        "Cisco Firepower equipment:SwitchIOCard:fsmStamp
        managed object property"
    ::= { cfprApEquipmentSwitchIOCardEntry 20 }

cfprApEquipmentSwitchIOCardFsmStatus OBJECT-TYPE
    SYNTAX       SnmpAdminString
    MAX-ACCESS   read-only
    STATUS       current
    DESCRIPTION
        "Cisco Firepower equipment:SwitchIOCard:fsmStatus
        managed object property"
    ::= { cfprApEquipmentSwitchIOCardEntry 21 }

cfprApEquipmentSwitchIOCardFsmTry OBJECT-TYPE
    SYNTAX       Gauge32
    MAX-ACCESS   read-only
    STATUS       current
    DESCRIPTION
        "Cisco Firepower equipment:SwitchIOCard:fsmTry
        managed object property"
    ::= { cfprApEquipmentSwitchIOCardEntry 22 }

cfprApEquipmentSwitchIOCardId OBJECT-TYPE
    SYNTAX       CfprApEquipmentSwitchIOCardId
    MAX-ACCESS   read-only
    STATUS       current
    DESCRIPTION
        "Cisco Firepower equipment:SwitchIOCard:id managed
        object property"
    ::= { cfprApEquipmentSwitchIOCardEntry 23 }

cfprApEquipmentSwitchIOCardLcName OBJECT-TYPE
    SYNTAX       SnmpAdminString
    MAX-ACCESS   read-only
    STATUS       current
    DESCRIPTION
        "Cisco Firepower equipment:SwitchIOCard:lcName
        managed object property"
    ::= { cfprApEquipmentSwitchIOCardEntry 24 }

cfprApEquipmentSwitchIOCardLcTs OBJECT-TYPE
    SYNTAX       DateAndTime
    MAX-ACCESS   read-only
    STATUS       current
    DESCRIPTION
        "Cisco Firepower equipment:SwitchIOCard:lcTs managed
        object property"
    ::= { cfprApEquipmentSwitchIOCardEntry 25 }

cfprApEquipmentSwitchIOCardMfgTime OBJECT-TYPE
    SYNTAX       DateAndTime
    MAX-ACCESS   read-only
    STATUS       current
    DESCRIPTION
        "Cisco Firepower equipment:SwitchIOCard:mfgTime
        managed object property"
    ::= { cfprApEquipmentSwitchIOCardEntry 26 }

cfprApEquipmentSwitchIOCardModel OBJECT-TYPE
    SYNTAX       SnmpAdminString
    MAX-ACCESS   read-only
    STATUS       current
    DESCRIPTION
        "Cisco Firepower equipment:SwitchIOCard:model managed
        object property"
    ::= { cfprApEquipmentSwitchIOCardEntry 27 }

cfprApEquipmentSwitchIOCardOperQualifier OBJECT-TYPE
    SYNTAX       CfprApEquipmentIOCardIssues
    MAX-ACCESS   read-only
    STATUS       current
    DESCRIPTION
        "Cisco Firepower equipment:SwitchIOCard:operQualifier
        managed object property"
    ::= { cfprApEquipmentSwitchIOCardEntry 28 }

cfprApEquipmentSwitchIOCardOperQualifierReason OBJECT-TYPE
    SYNTAX       SnmpAdminString
    MAX-ACCESS   read-only
    STATUS       current
    DESCRIPTION
        "Cisco Firepower equipment:SwitchIOCard:operQualifierReason
        managed object property"
    ::= { cfprApEquipmentSwitchIOCardEntry 29 }

cfprApEquipmentSwitchIOCardOperState OBJECT-TYPE
    SYNTAX       CfprApEquipmentOperability
    MAX-ACCESS   read-only
    STATUS       current
    DESCRIPTION
        "Cisco Firepower equipment:SwitchIOCard:operState
        managed object property"
    ::= { cfprApEquipmentSwitchIOCardEntry 30 }

cfprApEquipmentSwitchIOCardOperability OBJECT-TYPE
    SYNTAX       CfprApEquipmentOperability
    MAX-ACCESS   read-only
    STATUS       current
    DESCRIPTION
        "Cisco Firepower equipment:SwitchIOCard:operability
        managed object property"
    ::= { cfprApEquipmentSwitchIOCardEntry 31 }

cfprApEquipmentSwitchIOCardPeerCommStatus OBJECT-TYPE
    SYNTAX       CfprApEquipmentCommStatus
    MAX-ACCESS   read-only
    STATUS       current
    DESCRIPTION
        "Cisco Firepower equipment:SwitchIOCard:peerCommStatus
        managed object property"
    ::= { cfprApEquipmentSwitchIOCardEntry 32 }

cfprApEquipmentSwitchIOCardPeerDn OBJECT-TYPE
    SYNTAX       SnmpAdminString
    MAX-ACCESS   read-only
    STATUS       current
    DESCRIPTION
        "Cisco Firepower equipment:SwitchIOCard:peerDn
        managed object property"
    ::= { cfprApEquipmentSwitchIOCardEntry 33 }

cfprApEquipmentSwitchIOCardPerf OBJECT-TYPE
    SYNTAX       CfprApEquipmentSensorThresholdStatus
    MAX-ACCESS   read-only
    STATUS       current
    DESCRIPTION
        "Cisco Firepower equipment:SwitchIOCard:perf managed
        object property"
    ::= { cfprApEquipmentSwitchIOCardEntry 34 }

cfprApEquipmentSwitchIOCardPower OBJECT-TYPE
    SYNTAX       CfprApEquipmentPowerState
    MAX-ACCESS   read-only
    STATUS       current
    DESCRIPTION
        "Cisco Firepower equipment:SwitchIOCard:power managed
        object property"
    ::= { cfprApEquipmentSwitchIOCardEntry 35 }

cfprApEquipmentSwitchIOCardPresence OBJECT-TYPE
    SYNTAX       CfprApEquipmentPresence
    MAX-ACCESS   read-only
    STATUS       current
    DESCRIPTION
        "Cisco Firepower equipment:SwitchIOCard:presence
        managed object property"
    ::= { cfprApEquipmentSwitchIOCardEntry 36 }

cfprApEquipmentSwitchIOCardProcessorThermalState OBJECT-TYPE
    SYNTAX       CfprApEquipmentSensorThresholdStatus
    MAX-ACCESS   read-only
    STATUS       current
    DESCRIPTION
        "Cisco Firepower equipment:SwitchIOCard:processorThermalState
        managed object property"
    ::= { cfprApEquipmentSwitchIOCardEntry 37 }

cfprApEquipmentSwitchIOCardRevision OBJECT-TYPE
    SYNTAX       SnmpAdminString
    MAX-ACCESS   read-only
    STATUS       current
    DESCRIPTION
        "Cisco Firepower equipment:SwitchIOCard:revision
        managed object property"
    ::= { cfprApEquipmentSwitchIOCardEntry 38 }

cfprApEquipmentSwitchIOCardSerial OBJECT-TYPE
    SYNTAX       SnmpAdminString
    MAX-ACCESS   read-only
    STATUS       current
    DESCRIPTION
        "Cisco Firepower equipment:SwitchIOCard:serial
        managed object property"
    ::= { cfprApEquipmentSwitchIOCardEntry 39 }

cfprApEquipmentSwitchIOCardSide OBJECT-TYPE
    SYNTAX       CfprApNetworkSide
    MAX-ACCESS   read-only
    STATUS       current
    DESCRIPTION
        "Cisco Firepower equipment:SwitchIOCard:side managed
        object property"
    ::= { cfprApEquipmentSwitchIOCardEntry 40 }

cfprApEquipmentSwitchIOCardSwitchId OBJECT-TYPE
    SYNTAX       CfprApNetworkSwitchId
    MAX-ACCESS   read-only
    STATUS       current
    DESCRIPTION
        "Cisco Firepower equipment:SwitchIOCard:switchId
        managed object property"
    ::= { cfprApEquipmentSwitchIOCardEntry 41 }

cfprApEquipmentSwitchIOCardThermal OBJECT-TYPE
    SYNTAX       CfprApEquipmentSensorThresholdStatus
    MAX-ACCESS   read-only
    STATUS       current
    DESCRIPTION
        "Cisco Firepower equipment:SwitchIOCard:thermal
        managed object property"
    ::= { cfprApEquipmentSwitchIOCardEntry 42 }

cfprApEquipmentSwitchIOCardUpgradeStatus OBJECT-TYPE
    SYNTAX       CfprApMgmtUpgradeStatus
    MAX-ACCESS   read-only
    STATUS       current
    DESCRIPTION
        "Cisco Firepower equipment:SwitchIOCard:upgradeStatus
        managed object property"
    ::= { cfprApEquipmentSwitchIOCardEntry 43 }

cfprApEquipmentSwitchIOCardUsrLbl OBJECT-TYPE
    SYNTAX       SnmpAdminString
    MAX-ACCESS   read-only
    STATUS       current
    DESCRIPTION
        "Cisco Firepower equipment:SwitchIOCard:usrLbl
        managed object property"
    ::= { cfprApEquipmentSwitchIOCardEntry 44 }

cfprApEquipmentSwitchIOCardVendor OBJECT-TYPE
    SYNTAX       SnmpAdminString
    MAX-ACCESS   read-only
    STATUS       current
    DESCRIPTION
        "Cisco Firepower equipment:SwitchIOCard:vendor
        managed object property"
    ::= { cfprApEquipmentSwitchIOCardEntry 45 }

cfprApEquipmentSwitchIOCardVoltage OBJECT-TYPE
    SYNTAX       CfprApEquipmentSensorThresholdStatus
    MAX-ACCESS   read-only
    STATUS       current
    DESCRIPTION
        "Cisco Firepower equipment:SwitchIOCard:voltage
        managed object property"
    ::= { cfprApEquipmentSwitchIOCardEntry 46 }

cfprApEquipmentSwitchIOCardCapProviderTable OBJECT-TYPE
    SYNTAX           SEQUENCE OF CfprApEquipmentSwitchIOCardCapProviderEntry
    MAX-ACCESS       not-accessible
    STATUS           current
    DESCRIPTION
        "Cisco Firepower equipment:SwitchIOCardCapProvider
        managed object table"
    ::= { cfprApEquipmentObjects 138 }

cfprApEquipmentSwitchIOCardCapProviderEntry OBJECT-TYPE
    SYNTAX           CfprApEquipmentSwitchIOCardCapProviderEntry
    MAX-ACCESS       not-accessible
    STATUS           current
    DESCRIPTION
        "Entry for the cfprApEquipmentSwitchIOCardCapProviderTable table."
    INDEX { cfprApEquipmentSwitchIOCardCapProviderInstanceId }
    ::= { cfprApEquipmentSwitchIOCardCapProviderTable 1 }

CfprApEquipmentSwitchIOCardCapProviderEntry ::= SEQUENCE {
    cfprApEquipmentSwitchIOCardCapProviderInstanceId                 CfprApManagedObjectId,
    cfprApEquipmentSwitchIOCardCapProviderDn                         CfprApManagedObjectDn,
    cfprApEquipmentSwitchIOCardCapProviderRn                         SnmpAdminString,
    cfprApEquipmentSwitchIOCardCapProviderDeleted                    TruthValue,
    cfprApEquipmentSwitchIOCardCapProviderDeprecated                 TruthValue,
    cfprApEquipmentSwitchIOCardCapProviderElementLoadFailures        Gauge32,
    cfprApEquipmentSwitchIOCardCapProviderElementsLoaded             Gauge32,
    cfprApEquipmentSwitchIOCardCapProviderGencount                   Gauge32,
    cfprApEquipmentSwitchIOCardCapProviderLoadErrors                 Gauge32,
    cfprApEquipmentSwitchIOCardCapProviderLoadWarnings               Gauge32,
    cfprApEquipmentSwitchIOCardCapProviderMgmtPlaneVer               SnmpAdminString,
    cfprApEquipmentSwitchIOCardCapProviderModel                      SnmpAdminString,
    cfprApEquipmentSwitchIOCardCapProviderPromCardType               Gauge32,
    cfprApEquipmentSwitchIOCardCapProviderRevision                   SnmpAdminString,
    cfprApEquipmentSwitchIOCardCapProviderVendor                     SnmpAdminString
}

cfprApEquipmentSwitchIOCardCapProviderInstanceId OBJECT-TYPE
    SYNTAX       CfprApManagedObjectId
    MAX-ACCESS   not-accessible
    STATUS       current
    DESCRIPTION
        "Instance identifier of the managed object."
    ::= { cfprApEquipmentSwitchIOCardCapProviderEntry 1 }

cfprApEquipmentSwitchIOCardCapProviderDn OBJECT-TYPE
    SYNTAX       CfprApManagedObjectDn
    MAX-ACCESS   read-only
    STATUS       current
    DESCRIPTION
        "Cisco Firepower equipment:SwitchIOCardCapProvider:dn
        managed object property"
    ::= { cfprApEquipmentSwitchIOCardCapProviderEntry 2 }

cfprApEquipmentSwitchIOCardCapProviderRn OBJECT-TYPE
    SYNTAX       SnmpAdminString
    MAX-ACCESS   read-only
    STATUS       current
    DESCRIPTION
        "Cisco Firepower equipment:SwitchIOCardCapProvider:rn
        managed object property"
    ::= { cfprApEquipmentSwitchIOCardCapProviderEntry 3 }

cfprApEquipmentSwitchIOCardCapProviderDeleted OBJECT-TYPE
    SYNTAX       TruthValue
    MAX-ACCESS   read-only
    STATUS       current
    DESCRIPTION
        "Cisco Firepower equipment:SwitchIOCardCapProvider:deleted
        managed object property"
    ::= { cfprApEquipmentSwitchIOCardCapProviderEntry 4 }

cfprApEquipmentSwitchIOCardCapProviderDeprecated OBJECT-TYPE
    SYNTAX       TruthValue
    MAX-ACCESS   read-only
    STATUS       current
    DESCRIPTION
        "Cisco Firepower equipment:SwitchIOCardCapProvider:deprecated
        managed object property"
    ::= { cfprApEquipmentSwitchIOCardCapProviderEntry 5 }

cfprApEquipmentSwitchIOCardCapProviderElementLoadFailures OBJECT-TYPE
    SYNTAX       Gauge32
    MAX-ACCESS   read-only
    STATUS       current
    DESCRIPTION
        "Cisco Firepower equipment:SwitchIOCardCapProvider:elementLoadFail
        ures managed object property"
    ::= { cfprApEquipmentSwitchIOCardCapProviderEntry 6 }

cfprApEquipmentSwitchIOCardCapProviderElementsLoaded OBJECT-TYPE
    SYNTAX       Gauge32
    MAX-ACCESS   read-only
    STATUS       current
    DESCRIPTION
        "Cisco Firepower equipment:SwitchIOCardCapProvider:elementsLoaded
        managed object property"
    ::= { cfprApEquipmentSwitchIOCardCapProviderEntry 7 }

cfprApEquipmentSwitchIOCardCapProviderGencount OBJECT-TYPE
    SYNTAX       Gauge32
    MAX-ACCESS   read-only
    STATUS       current
    DESCRIPTION
        "Cisco Firepower equipment:SwitchIOCardCapProvider:gencount
        managed object property"
    ::= { cfprApEquipmentSwitchIOCardCapProviderEntry 8 }

cfprApEquipmentSwitchIOCardCapProviderLoadErrors OBJECT-TYPE
    SYNTAX       Gauge32
    MAX-ACCESS   read-only
    STATUS       current
    DESCRIPTION
        "Cisco Firepower equipment:SwitchIOCardCapProvider:loadErrors
        managed object property"
    ::= { cfprApEquipmentSwitchIOCardCapProviderEntry 9 }

cfprApEquipmentSwitchIOCardCapProviderLoadWarnings OBJECT-TYPE
    SYNTAX       Gauge32
    MAX-ACCESS   read-only
    STATUS       current
    DESCRIPTION
        "Cisco Firepower equipment:SwitchIOCardCapProvider:loadWarnings
        managed object property"
    ::= { cfprApEquipmentSwitchIOCardCapProviderEntry 10 }

cfprApEquipmentSwitchIOCardCapProviderMgmtPlaneVer OBJECT-TYPE
    SYNTAX       SnmpAdminString
    MAX-ACCESS   read-only
    STATUS       current
    DESCRIPTION
        "Cisco Firepower equipment:SwitchIOCardCapProvider:mgmtPlaneVer
        managed object property"
    ::= { cfprApEquipmentSwitchIOCardCapProviderEntry 11 }

cfprApEquipmentSwitchIOCardCapProviderModel OBJECT-TYPE
    SYNTAX       SnmpAdminString
    MAX-ACCESS   read-only
    STATUS       current
    DESCRIPTION
        "Cisco Firepower equipment:SwitchIOCardCapProvider:model
        managed object property"
    ::= { cfprApEquipmentSwitchIOCardCapProviderEntry 12 }

cfprApEquipmentSwitchIOCardCapProviderPromCardType OBJECT-TYPE
    SYNTAX       Gauge32
    MAX-ACCESS   read-only
    STATUS       current
    DESCRIPTION
        "Cisco Firepower equipment:SwitchIOCardCapProvider:promCardType
        managed object property"
    ::= { cfprApEquipmentSwitchIOCardCapProviderEntry 13 }

cfprApEquipmentSwitchIOCardCapProviderRevision OBJECT-TYPE
    SYNTAX       SnmpAdminString
    MAX-ACCESS   read-only
    STATUS       current
    DESCRIPTION
        "Cisco Firepower equipment:SwitchIOCardCapProvider:revision
        managed object property"
    ::= { cfprApEquipmentSwitchIOCardCapProviderEntry 14 }

cfprApEquipmentSwitchIOCardCapProviderVendor OBJECT-TYPE
    SYNTAX       SnmpAdminString
    MAX-ACCESS   read-only
    STATUS       current
    DESCRIPTION
        "Cisco Firepower equipment:SwitchIOCardCapProvider:vendor
        managed object property"
    ::= { cfprApEquipmentSwitchIOCardCapProviderEntry 15 }

cfprApEquipmentSwitchIOCardFsmTable OBJECT-TYPE
    SYNTAX           SEQUENCE OF CfprApEquipmentSwitchIOCardFsmEntry
    MAX-ACCESS       not-accessible
    STATUS           current
    DESCRIPTION
        "Cisco Firepower equipment:SwitchIOCardFsm managed object table"
    ::= { cfprApEquipmentObjects 139 }

cfprApEquipmentSwitchIOCardFsmEntry OBJECT-TYPE
    SYNTAX           CfprApEquipmentSwitchIOCardFsmEntry
    MAX-ACCESS       not-accessible
    STATUS           current
    DESCRIPTION
        "Entry for the cfprApEquipmentSwitchIOCardFsmTable table."
    INDEX { cfprApEquipmentSwitchIOCardFsmInstanceId }
    ::= { cfprApEquipmentSwitchIOCardFsmTable 1 }

CfprApEquipmentSwitchIOCardFsmEntry ::= SEQUENCE {
    cfprApEquipmentSwitchIOCardFsmInstanceId                         CfprApManagedObjectId,
    cfprApEquipmentSwitchIOCardFsmDn                                 CfprApManagedObjectDn,
    cfprApEquipmentSwitchIOCardFsmRn                                 SnmpAdminString,
    cfprApEquipmentSwitchIOCardFsmCompletionTime                     DateAndTime,
    cfprApEquipmentSwitchIOCardFsmCurrentFsm                         CfprApEquipmentSwitchIOCardFsmCurrentFsm,
    cfprApEquipmentSwitchIOCardFsmDescrData                          SnmpAdminString,
    cfprApEquipmentSwitchIOCardFsmFsmStatus                          CfprApFsmFsmStageStatus,
    cfprApEquipmentSwitchIOCardFsmProgress                           Gauge32,
    cfprApEquipmentSwitchIOCardFsmRmtErrCode                         Gauge32,
    cfprApEquipmentSwitchIOCardFsmRmtErrDescr                        SnmpAdminString,
    cfprApEquipmentSwitchIOCardFsmRmtRslt                            CfprApConditionRemoteInvRslt
}

cfprApEquipmentSwitchIOCardFsmInstanceId OBJECT-TYPE
    SYNTAX       CfprApManagedObjectId
    MAX-ACCESS   not-accessible
    STATUS       current
    DESCRIPTION
        "Instance identifier of the managed object."
    ::= { cfprApEquipmentSwitchIOCardFsmEntry 1 }

cfprApEquipmentSwitchIOCardFsmDn OBJECT-TYPE
    SYNTAX       CfprApManagedObjectDn
    MAX-ACCESS   read-only
    STATUS       current
    DESCRIPTION
        "Cisco Firepower equipment:SwitchIOCardFsm:dn managed
        object property"
    ::= { cfprApEquipmentSwitchIOCardFsmEntry 2 }

cfprApEquipmentSwitchIOCardFsmRn OBJECT-TYPE
    SYNTAX       SnmpAdminString
    MAX-ACCESS   read-only
    STATUS       current
    DESCRIPTION
        "Cisco Firepower equipment:SwitchIOCardFsm:rn managed
        object property"
    ::= { cfprApEquipmentSwitchIOCardFsmEntry 3 }

cfprApEquipmentSwitchIOCardFsmCompletionTime OBJECT-TYPE
    SYNTAX       DateAndTime
    MAX-ACCESS   read-only
    STATUS       current
    DESCRIPTION
        "Cisco Firepower equipment:SwitchIOCardFsm:completionTime
        managed object property"
    ::= { cfprApEquipmentSwitchIOCardFsmEntry 4 }

cfprApEquipmentSwitchIOCardFsmCurrentFsm OBJECT-TYPE
    SYNTAX       CfprApEquipmentSwitchIOCardFsmCurrentFsm
    MAX-ACCESS   read-only
    STATUS       current
    DESCRIPTION
        "Cisco Firepower equipment:SwitchIOCardFsm:currentFsm
        managed object property"
    ::= { cfprApEquipmentSwitchIOCardFsmEntry 5 }

cfprApEquipmentSwitchIOCardFsmDescrData OBJECT-TYPE
    SYNTAX       SnmpAdminString
    MAX-ACCESS   read-only
    STATUS       current
    DESCRIPTION
        "Cisco Firepower equipment:SwitchIOCardFsm:descr
        managed object property"
    ::= { cfprApEquipmentSwitchIOCardFsmEntry 6 }

cfprApEquipmentSwitchIOCardFsmFsmStatus OBJECT-TYPE
    SYNTAX       CfprApFsmFsmStageStatus
    MAX-ACCESS   read-only
    STATUS       current
    DESCRIPTION
        "Cisco Firepower equipment:SwitchIOCardFsm:fsmStatus
        managed object property"
    ::= { cfprApEquipmentSwitchIOCardFsmEntry 7 }

cfprApEquipmentSwitchIOCardFsmProgress OBJECT-TYPE
    SYNTAX       Gauge32
    MAX-ACCESS   read-only
    STATUS       current
    DESCRIPTION
        "Cisco Firepower equipment:SwitchIOCardFsm:progress
        managed object property"
    ::= { cfprApEquipmentSwitchIOCardFsmEntry 8 }

cfprApEquipmentSwitchIOCardFsmRmtErrCode OBJECT-TYPE
    SYNTAX       Gauge32
    MAX-ACCESS   read-only
    STATUS       current
    DESCRIPTION
        "Cisco Firepower equipment:SwitchIOCardFsm:rmtErrCode
        managed object property"
    ::= { cfprApEquipmentSwitchIOCardFsmEntry 9 }

cfprApEquipmentSwitchIOCardFsmRmtErrDescr OBJECT-TYPE
    SYNTAX       SnmpAdminString
    MAX-ACCESS   read-only
    STATUS       current
    DESCRIPTION
        "Cisco Firepower equipment:SwitchIOCardFsm:rmtErrDescr
        managed object property"
    ::= { cfprApEquipmentSwitchIOCardFsmEntry 10 }

cfprApEquipmentSwitchIOCardFsmRmtRslt OBJECT-TYPE
    SYNTAX       CfprApConditionRemoteInvRslt
    MAX-ACCESS   read-only
    STATUS       current
    DESCRIPTION
        "Cisco Firepower equipment:SwitchIOCardFsm:rmtRslt
        managed object property"
    ::= { cfprApEquipmentSwitchIOCardFsmEntry 11 }

cfprApEquipmentSwitchIOCardFsmStageTable OBJECT-TYPE
    SYNTAX           SEQUENCE OF CfprApEquipmentSwitchIOCardFsmStageEntry
    MAX-ACCESS       not-accessible
    STATUS           current
    DESCRIPTION
        "Cisco Firepower equipment:SwitchIOCardFsmStage
        managed object table"
    ::= { cfprApEquipmentObjects 140 }

cfprApEquipmentSwitchIOCardFsmStageEntry OBJECT-TYPE
    SYNTAX           CfprApEquipmentSwitchIOCardFsmStageEntry
    MAX-ACCESS       not-accessible
    STATUS           current
    DESCRIPTION
        "Entry for the cfprApEquipmentSwitchIOCardFsmStageTable table."
    INDEX { cfprApEquipmentSwitchIOCardFsmStageInstanceId }
    ::= { cfprApEquipmentSwitchIOCardFsmStageTable 1 }

CfprApEquipmentSwitchIOCardFsmStageEntry ::= SEQUENCE {
    cfprApEquipmentSwitchIOCardFsmStageInstanceId                    CfprApManagedObjectId,
    cfprApEquipmentSwitchIOCardFsmStageDn                            CfprApManagedObjectDn,
    cfprApEquipmentSwitchIOCardFsmStageRn                            SnmpAdminString,
    cfprApEquipmentSwitchIOCardFsmStageDescrData                     SnmpAdminString,
    cfprApEquipmentSwitchIOCardFsmStageLastUpdateTime                DateAndTime,
    cfprApEquipmentSwitchIOCardFsmStageName                          CfprApEquipmentSwitchIOCardFsmStageName,
    cfprApEquipmentSwitchIOCardFsmStageOrder                         Gauge32,
    cfprApEquipmentSwitchIOCardFsmStageRetry                         Gauge32,
    cfprApEquipmentSwitchIOCardFsmStageStageStatus                   CfprApFsmFsmStageStatus
}

cfprApEquipmentSwitchIOCardFsmStageInstanceId OBJECT-TYPE
    SYNTAX       CfprApManagedObjectId
    MAX-ACCESS   not-accessible
    STATUS       current
    DESCRIPTION
        "Instance identifier of the managed object."
    ::= { cfprApEquipmentSwitchIOCardFsmStageEntry 1 }

cfprApEquipmentSwitchIOCardFsmStageDn OBJECT-TYPE
    SYNTAX       CfprApManagedObjectDn
    MAX-ACCESS   read-only
    STATUS       current
    DESCRIPTION
        "Cisco Firepower equipment:SwitchIOCardFsmStage:dn
        managed object property"
    ::= { cfprApEquipmentSwitchIOCardFsmStageEntry 2 }

cfprApEquipmentSwitchIOCardFsmStageRn OBJECT-TYPE
    SYNTAX       SnmpAdminString
    MAX-ACCESS   read-only
    STATUS       current
    DESCRIPTION
        "Cisco Firepower equipment:SwitchIOCardFsmStage:rn
        managed object property"
    ::= { cfprApEquipmentSwitchIOCardFsmStageEntry 3 }

cfprApEquipmentSwitchIOCardFsmStageDescrData OBJECT-TYPE
    SYNTAX       SnmpAdminString
    MAX-ACCESS   read-only
    STATUS       current
    DESCRIPTION
        "Cisco Firepower equipment:SwitchIOCardFsmStage:descr
        managed object property"
    ::= { cfprApEquipmentSwitchIOCardFsmStageEntry 4 }

cfprApEquipmentSwitchIOCardFsmStageLastUpdateTime OBJECT-TYPE
    SYNTAX       DateAndTime
    MAX-ACCESS   read-only
    STATUS       current
    DESCRIPTION
        "Cisco Firepower equipment:SwitchIOCardFsmStage:lastUpdateTime
        managed object property"
    ::= { cfprApEquipmentSwitchIOCardFsmStageEntry 5 }

cfprApEquipmentSwitchIOCardFsmStageName OBJECT-TYPE
    SYNTAX       CfprApEquipmentSwitchIOCardFsmStageName
    MAX-ACCESS   read-only
    STATUS       current
    DESCRIPTION
        "Cisco Firepower equipment:SwitchIOCardFsmStage:name
        managed object property"
    ::= { cfprApEquipmentSwitchIOCardFsmStageEntry 6 }

cfprApEquipmentSwitchIOCardFsmStageOrder OBJECT-TYPE
    SYNTAX       Gauge32
    MAX-ACCESS   read-only
    STATUS       current
    DESCRIPTION
        "Cisco Firepower equipment:SwitchIOCardFsmStage:order
        managed object property"
    ::= { cfprApEquipmentSwitchIOCardFsmStageEntry 7 }

cfprApEquipmentSwitchIOCardFsmStageRetry OBJECT-TYPE
    SYNTAX       Gauge32
    MAX-ACCESS   read-only
    STATUS       current
    DESCRIPTION
        "Cisco Firepower equipment:SwitchIOCardFsmStage:retry
        managed object property"
    ::= { cfprApEquipmentSwitchIOCardFsmStageEntry 8 }

cfprApEquipmentSwitchIOCardFsmStageStageStatus OBJECT-TYPE
    SYNTAX       CfprApFsmFsmStageStatus
    MAX-ACCESS   read-only
    STATUS       current
    DESCRIPTION
        "Cisco Firepower equipment:SwitchIOCardFsmStage:stageStatus
        managed object property"
    ::= { cfprApEquipmentSwitchIOCardFsmStageEntry 9 }

cfprApEquipmentSwitchTypeDefTable OBJECT-TYPE
    SYNTAX           SEQUENCE OF CfprApEquipmentSwitchTypeDefEntry
    MAX-ACCESS       not-accessible
    STATUS           current
    DESCRIPTION
        "Cisco Firepower equipment:SwitchTypeDef managed object table"
    ::= { cfprApEquipmentObjects 141 }

cfprApEquipmentSwitchTypeDefEntry OBJECT-TYPE
    SYNTAX           CfprApEquipmentSwitchTypeDefEntry
    MAX-ACCESS       not-accessible
    STATUS           current
    DESCRIPTION
        "Entry for the cfprApEquipmentSwitchTypeDefTable table."
    INDEX { cfprApEquipmentSwitchTypeDefInstanceId }
    ::= { cfprApEquipmentSwitchTypeDefTable 1 }

CfprApEquipmentSwitchTypeDefEntry ::= SEQUENCE {
    cfprApEquipmentSwitchTypeDefInstanceId                           CfprApManagedObjectId,
    cfprApEquipmentSwitchTypeDefDn                                   CfprApManagedObjectDn,
    cfprApEquipmentSwitchTypeDefRn                                   SnmpAdminString,
    cfprApEquipmentSwitchTypeDefDescr                                SnmpAdminString,
    cfprApEquipmentSwitchTypeDefIntId                                SnmpAdminString,
    cfprApEquipmentSwitchTypeDefName                                 SnmpAdminString,
    cfprApEquipmentSwitchTypeDefPolicyLevel                          Gauge32,
    cfprApEquipmentSwitchTypeDefPolicyOwner                          CfprApPolicyPolicyOwner,
    cfprApEquipmentSwitchTypeDefType                                 SnmpAdminString
}

cfprApEquipmentSwitchTypeDefInstanceId OBJECT-TYPE
    SYNTAX       CfprApManagedObjectId
    MAX-ACCESS   not-accessible
    STATUS       current
    DESCRIPTION
        "Instance identifier of the managed object."
    ::= { cfprApEquipmentSwitchTypeDefEntry 1 }

cfprApEquipmentSwitchTypeDefDn OBJECT-TYPE
    SYNTAX       CfprApManagedObjectDn
    MAX-ACCESS   read-only
    STATUS       current
    DESCRIPTION
        "Cisco Firepower equipment:SwitchTypeDef:dn managed
        object property"
    ::= { cfprApEquipmentSwitchTypeDefEntry 2 }

cfprApEquipmentSwitchTypeDefRn OBJECT-TYPE
    SYNTAX       SnmpAdminString
    MAX-ACCESS   read-only
    STATUS       current
    DESCRIPTION
        "Cisco Firepower equipment:SwitchTypeDef:rn managed
        object property"
    ::= { cfprApEquipmentSwitchTypeDefEntry 3 }

cfprApEquipmentSwitchTypeDefDescr OBJECT-TYPE
    SYNTAX       SnmpAdminString
    MAX-ACCESS   read-only
    STATUS       current
    DESCRIPTION
        "Cisco Firepower equipment:SwitchTypeDef:descr
        managed object property"
    ::= { cfprApEquipmentSwitchTypeDefEntry 4 }

cfprApEquipmentSwitchTypeDefIntId OBJECT-TYPE
    SYNTAX       SnmpAdminString
    MAX-ACCESS   read-only
    STATUS       current
    DESCRIPTION
        "Cisco Firepower equipment:SwitchTypeDef:intId
        managed object property"
    ::= { cfprApEquipmentSwitchTypeDefEntry 5 }

cfprApEquipmentSwitchTypeDefName OBJECT-TYPE
    SYNTAX       SnmpAdminString
    MAX-ACCESS   read-only
    STATUS       current
    DESCRIPTION
        "Cisco Firepower equipment:SwitchTypeDef:name managed
        object property"
    ::= { cfprApEquipmentSwitchTypeDefEntry 6 }

cfprApEquipmentSwitchTypeDefPolicyLevel OBJECT-TYPE
    SYNTAX       Gauge32
    MAX-ACCESS   read-only
    STATUS       current
    DESCRIPTION
        "Cisco Firepower equipment:SwitchTypeDef:policyLevel
        managed object property"
    ::= { cfprApEquipmentSwitchTypeDefEntry 7 }

cfprApEquipmentSwitchTypeDefPolicyOwner OBJECT-TYPE
    SYNTAX       CfprApPolicyPolicyOwner
    MAX-ACCESS   read-only
    STATUS       current
    DESCRIPTION
        "Cisco Firepower equipment:SwitchTypeDef:policyOwner
        managed object property"
    ::= { cfprApEquipmentSwitchTypeDefEntry 8 }

cfprApEquipmentSwitchTypeDefType OBJECT-TYPE
    SYNTAX       SnmpAdminString
    MAX-ACCESS   read-only
    STATUS       current
    DESCRIPTION
        "Cisco Firepower equipment:SwitchTypeDef:type managed
        object property"
    ::= { cfprApEquipmentSwitchTypeDefEntry 9 }

cfprApEquipmentTpmTable OBJECT-TYPE
    SYNTAX           SEQUENCE OF CfprApEquipmentTpmEntry
    MAX-ACCESS       not-accessible
    STATUS           current
    DESCRIPTION
        "Cisco Firepower equipment:Tpm managed object table"
    ::= { cfprApEquipmentObjects 142 }

cfprApEquipmentTpmEntry OBJECT-TYPE
    SYNTAX           CfprApEquipmentTpmEntry
    MAX-ACCESS       not-accessible
    STATUS           current
    DESCRIPTION
        "Entry for the cfprApEquipmentTpmTable table."
    INDEX { cfprApEquipmentTpmInstanceId }
    ::= { cfprApEquipmentTpmTable 1 }

CfprApEquipmentTpmEntry ::= SEQUENCE {
    cfprApEquipmentTpmInstanceId                                     CfprApManagedObjectId,
    cfprApEquipmentTpmDn                                             CfprApManagedObjectDn,
    cfprApEquipmentTpmRn                                             SnmpAdminString,
    cfprApEquipmentTpmActiveStatus                                   CfprApEquipmentActiveStatus,
    cfprApEquipmentTpmEnabledStatus                                  CfprApEquipmentEnabledStatus,
    cfprApEquipmentTpmId                                             Gauge32,
    cfprApEquipmentTpmModel                                          SnmpAdminString,
    cfprApEquipmentTpmOwnership                                      CfprApEquipmentOwnership,
    cfprApEquipmentTpmPasswordState                                  CfprApEquipmentPasswordState,
    cfprApEquipmentTpmPresence                                       CfprApEquipmentPresence,
    cfprApEquipmentTpmRevision                                       SnmpAdminString,
    cfprApEquipmentTpmSerial                                         SnmpAdminString,
    cfprApEquipmentTpmTpmRevision                                    Gauge32,
    cfprApEquipmentTpmType                                           CfprApEquipmentTpmType,
    cfprApEquipmentTpmVendor                                         SnmpAdminString
}

cfprApEquipmentTpmInstanceId OBJECT-TYPE
    SYNTAX       CfprApManagedObjectId
    MAX-ACCESS   not-accessible
    STATUS       current
    DESCRIPTION
        "Instance identifier of the managed object."
    ::= { cfprApEquipmentTpmEntry 1 }

cfprApEquipmentTpmDn OBJECT-TYPE
    SYNTAX       CfprApManagedObjectDn
    MAX-ACCESS   read-only
    STATUS       current
    DESCRIPTION
        "Cisco Firepower equipment:Tpm:dn managed object property"
    ::= { cfprApEquipmentTpmEntry 2 }

cfprApEquipmentTpmRn OBJECT-TYPE
    SYNTAX       SnmpAdminString
    MAX-ACCESS   read-only
    STATUS       current
    DESCRIPTION
        "Cisco Firepower equipment:Tpm:rn managed object property"
    ::= { cfprApEquipmentTpmEntry 3 }

cfprApEquipmentTpmActiveStatus OBJECT-TYPE
    SYNTAX       CfprApEquipmentActiveStatus
    MAX-ACCESS   read-only
    STATUS       current
    DESCRIPTION
        "Cisco Firepower equipment:Tpm:activeStatus managed
        object property"
    ::= { cfprApEquipmentTpmEntry 4 }

cfprApEquipmentTpmEnabledStatus OBJECT-TYPE
    SYNTAX       CfprApEquipmentEnabledStatus
    MAX-ACCESS   read-only
    STATUS       current
    DESCRIPTION
        "Cisco Firepower equipment:Tpm:enabledStatus managed
        object property"
    ::= { cfprApEquipmentTpmEntry 5 }

cfprApEquipmentTpmId OBJECT-TYPE
    SYNTAX       Gauge32
    MAX-ACCESS   read-only
    STATUS       current
    DESCRIPTION
        "Cisco Firepower equipment:Tpm:id managed object property"
    ::= { cfprApEquipmentTpmEntry 6 }

cfprApEquipmentTpmModel OBJECT-TYPE
    SYNTAX       SnmpAdminString
    MAX-ACCESS   read-only
    STATUS       current
    DESCRIPTION
        "Cisco Firepower equipment:Tpm:model managed object property"
    ::= { cfprApEquipmentTpmEntry 7 }

cfprApEquipmentTpmOwnership OBJECT-TYPE
    SYNTAX       CfprApEquipmentOwnership
    MAX-ACCESS   read-only
    STATUS       current
    DESCRIPTION
        "Cisco Firepower equipment:Tpm:ownership managed object property"
    ::= { cfprApEquipmentTpmEntry 8 }

cfprApEquipmentTpmPasswordState OBJECT-TYPE
    SYNTAX       CfprApEquipmentPasswordState
    MAX-ACCESS   read-only
    STATUS       current
    DESCRIPTION
        "Cisco Firepower equipment:Tpm:passwordState managed
        object property"
    ::= { cfprApEquipmentTpmEntry 9 }

cfprApEquipmentTpmPresence OBJECT-TYPE
    SYNTAX       CfprApEquipmentPresence
    MAX-ACCESS   read-only
    STATUS       current
    DESCRIPTION
        "Cisco Firepower equipment:Tpm:presence managed object property"
    ::= { cfprApEquipmentTpmEntry 10 }

cfprApEquipmentTpmRevision OBJECT-TYPE
    SYNTAX       SnmpAdminString
    MAX-ACCESS   read-only
    STATUS       current
    DESCRIPTION
        "Cisco Firepower equipment:Tpm:revision managed object property"
    ::= { cfprApEquipmentTpmEntry 11 }

cfprApEquipmentTpmSerial OBJECT-TYPE
    SYNTAX       SnmpAdminString
    MAX-ACCESS   read-only
    STATUS       current
    DESCRIPTION
        "Cisco Firepower equipment:Tpm:serial managed object property"
    ::= { cfprApEquipmentTpmEntry 12 }

cfprApEquipmentTpmTpmRevision OBJECT-TYPE
    SYNTAX       Gauge32
    MAX-ACCESS   read-only
    STATUS       current
    DESCRIPTION
        "Cisco Firepower equipment:Tpm:tpmRevision managed
        object property"
    ::= { cfprApEquipmentTpmEntry 13 }

cfprApEquipmentTpmType OBJECT-TYPE
    SYNTAX       CfprApEquipmentTpmType
    MAX-ACCESS   read-only
    STATUS       current
    DESCRIPTION
        "Cisco Firepower equipment:Tpm:type managed object property"
    ::= { cfprApEquipmentTpmEntry 14 }

cfprApEquipmentTpmVendor OBJECT-TYPE
    SYNTAX       SnmpAdminString
    MAX-ACCESS   read-only
    STATUS       current
    DESCRIPTION
        "Cisco Firepower equipment:Tpm:vendor managed object property"
    ::= { cfprApEquipmentTpmEntry 15 }

cfprApEquipmentTpmCapProviderTable OBJECT-TYPE
    SYNTAX           SEQUENCE OF CfprApEquipmentTpmCapProviderEntry
    MAX-ACCESS       not-accessible
    STATUS           current
    DESCRIPTION
        "Cisco Firepower equipment:TpmCapProvider managed object table"
    ::= { cfprApEquipmentObjects 143 }

cfprApEquipmentTpmCapProviderEntry OBJECT-TYPE
    SYNTAX           CfprApEquipmentTpmCapProviderEntry
    MAX-ACCESS       not-accessible
    STATUS           current
    DESCRIPTION
        "Entry for the cfprApEquipmentTpmCapProviderTable table."
    INDEX { cfprApEquipmentTpmCapProviderInstanceId }
    ::= { cfprApEquipmentTpmCapProviderTable 1 }

CfprApEquipmentTpmCapProviderEntry ::= SEQUENCE {
    cfprApEquipmentTpmCapProviderInstanceId                          CfprApManagedObjectId,
    cfprApEquipmentTpmCapProviderDn                                  CfprApManagedObjectDn,
    cfprApEquipmentTpmCapProviderRn                                  SnmpAdminString,
    cfprApEquipmentTpmCapProviderDeleted                             TruthValue,
    cfprApEquipmentTpmCapProviderDeprecated                          TruthValue,
    cfprApEquipmentTpmCapProviderElementLoadFailures                 Gauge32,
    cfprApEquipmentTpmCapProviderElementsLoaded                      Gauge32,
    cfprApEquipmentTpmCapProviderGencount                            Gauge32,
    cfprApEquipmentTpmCapProviderLoadErrors                          Gauge32,
    cfprApEquipmentTpmCapProviderLoadWarnings                        Gauge32,
    cfprApEquipmentTpmCapProviderMgmtPlaneVer                        SnmpAdminString,
    cfprApEquipmentTpmCapProviderModel                               SnmpAdminString,
    cfprApEquipmentTpmCapProviderPromCardType                        Gauge32,
    cfprApEquipmentTpmCapProviderRevision                            SnmpAdminString,
    cfprApEquipmentTpmCapProviderVendor                              SnmpAdminString
}

cfprApEquipmentTpmCapProviderInstanceId OBJECT-TYPE
    SYNTAX       CfprApManagedObjectId
    MAX-ACCESS   not-accessible
    STATUS       current
    DESCRIPTION
        "Instance identifier of the managed object."
    ::= { cfprApEquipmentTpmCapProviderEntry 1 }

cfprApEquipmentTpmCapProviderDn OBJECT-TYPE
    SYNTAX       CfprApManagedObjectDn
    MAX-ACCESS   read-only
    STATUS       current
    DESCRIPTION
        "Cisco Firepower equipment:TpmCapProvider:dn managed
        object property"
    ::= { cfprApEquipmentTpmCapProviderEntry 2 }

cfprApEquipmentTpmCapProviderRn OBJECT-TYPE
    SYNTAX       SnmpAdminString
    MAX-ACCESS   read-only
    STATUS       current
    DESCRIPTION
        "Cisco Firepower equipment:TpmCapProvider:rn managed
        object property"
    ::= { cfprApEquipmentTpmCapProviderEntry 3 }

cfprApEquipmentTpmCapProviderDeleted OBJECT-TYPE
    SYNTAX       TruthValue
    MAX-ACCESS   read-only
    STATUS       current
    DESCRIPTION
        "Cisco Firepower equipment:TpmCapProvider:deleted
        managed object property"
    ::= { cfprApEquipmentTpmCapProviderEntry 4 }

cfprApEquipmentTpmCapProviderDeprecated OBJECT-TYPE
    SYNTAX       TruthValue
    MAX-ACCESS   read-only
    STATUS       current
    DESCRIPTION
        "Cisco Firepower equipment:TpmCapProvider:deprecated
        managed object property"
    ::= { cfprApEquipmentTpmCapProviderEntry 5 }

cfprApEquipmentTpmCapProviderElementLoadFailures OBJECT-TYPE
    SYNTAX       Gauge32
    MAX-ACCESS   read-only
    STATUS       current
    DESCRIPTION
        "Cisco Firepower equipment:TpmCapProvider:elementLoadFailures
        managed object property"
    ::= { cfprApEquipmentTpmCapProviderEntry 6 }

cfprApEquipmentTpmCapProviderElementsLoaded OBJECT-TYPE
    SYNTAX       Gauge32
    MAX-ACCESS   read-only
    STATUS       current
    DESCRIPTION
        "Cisco Firepower equipment:TpmCapProvider:elementsLoaded
        managed object property"
    ::= { cfprApEquipmentTpmCapProviderEntry 7 }

cfprApEquipmentTpmCapProviderGencount OBJECT-TYPE
    SYNTAX       Gauge32
    MAX-ACCESS   read-only
    STATUS       current
    DESCRIPTION
        "Cisco Firepower equipment:TpmCapProvider:gencount
        managed object property"
    ::= { cfprApEquipmentTpmCapProviderEntry 8 }

cfprApEquipmentTpmCapProviderLoadErrors OBJECT-TYPE
    SYNTAX       Gauge32
    MAX-ACCESS   read-only
    STATUS       current
    DESCRIPTION
        "Cisco Firepower equipment:TpmCapProvider:loadErrors
        managed object property"
    ::= { cfprApEquipmentTpmCapProviderEntry 9 }

cfprApEquipmentTpmCapProviderLoadWarnings OBJECT-TYPE
    SYNTAX       Gauge32
    MAX-ACCESS   read-only
    STATUS       current
    DESCRIPTION
        "Cisco Firepower equipment:TpmCapProvider:loadWarnings
        managed object property"
    ::= { cfprApEquipmentTpmCapProviderEntry 10 }

cfprApEquipmentTpmCapProviderMgmtPlaneVer OBJECT-TYPE
    SYNTAX       SnmpAdminString
    MAX-ACCESS   read-only
    STATUS       current
    DESCRIPTION
        "Cisco Firepower equipment:TpmCapProvider:mgmtPlaneVer
        managed object property"
    ::= { cfprApEquipmentTpmCapProviderEntry 11 }

cfprApEquipmentTpmCapProviderModel OBJECT-TYPE
    SYNTAX       SnmpAdminString
    MAX-ACCESS   read-only
    STATUS       current
    DESCRIPTION
        "Cisco Firepower equipment:TpmCapProvider:model
        managed object property"
    ::= { cfprApEquipmentTpmCapProviderEntry 12 }

cfprApEquipmentTpmCapProviderPromCardType OBJECT-TYPE
    SYNTAX       Gauge32
    MAX-ACCESS   read-only
    STATUS       current
    DESCRIPTION
        "Cisco Firepower equipment:TpmCapProvider:promCardType
        managed object property"
    ::= { cfprApEquipmentTpmCapProviderEntry 13 }

cfprApEquipmentTpmCapProviderRevision OBJECT-TYPE
    SYNTAX       SnmpAdminString
    MAX-ACCESS   read-only
    STATUS       current
    DESCRIPTION
        "Cisco Firepower equipment:TpmCapProvider:revision
        managed object property"
    ::= { cfprApEquipmentTpmCapProviderEntry 14 }

cfprApEquipmentTpmCapProviderVendor OBJECT-TYPE
    SYNTAX       SnmpAdminString
    MAX-ACCESS   read-only
    STATUS       current
    DESCRIPTION
        "Cisco Firepower equipment:TpmCapProvider:vendor
        managed object property"
    ::= { cfprApEquipmentTpmCapProviderEntry 15 }

cfprApEquipmentUnifiedPortCapProviderTable OBJECT-TYPE
    SYNTAX           SEQUENCE OF CfprApEquipmentUnifiedPortCapProviderEntry
    MAX-ACCESS       not-accessible
    STATUS           current
    DESCRIPTION
        "Cisco Firepower equipment:UnifiedPortCapProvider
        managed object table"
    ::= { cfprApEquipmentObjects 144 }

cfprApEquipmentUnifiedPortCapProviderEntry OBJECT-TYPE
    SYNTAX           CfprApEquipmentUnifiedPortCapProviderEntry
    MAX-ACCESS       not-accessible
    STATUS           current
    DESCRIPTION
        "Entry for the cfprApEquipmentUnifiedPortCapProviderTable table."
    INDEX { cfprApEquipmentUnifiedPortCapProviderInstanceId }
    ::= { cfprApEquipmentUnifiedPortCapProviderTable 1 }

CfprApEquipmentUnifiedPortCapProviderEntry ::= SEQUENCE {
    cfprApEquipmentUnifiedPortCapProviderInstanceId                  CfprApManagedObjectId,
    cfprApEquipmentUnifiedPortCapProviderDn                          CfprApManagedObjectDn,
    cfprApEquipmentUnifiedPortCapProviderRn                          SnmpAdminString,
    cfprApEquipmentUnifiedPortCapProviderDescr                       SnmpAdminString,
    cfprApEquipmentUnifiedPortCapProviderEndPortId                   Gauge32,
    cfprApEquipmentUnifiedPortCapProviderIntId                       SnmpAdminString,
    cfprApEquipmentUnifiedPortCapProviderName                        SnmpAdminString,
    cfprApEquipmentUnifiedPortCapProviderPolicyLevel                 Gauge32,
    cfprApEquipmentUnifiedPortCapProviderPolicyOwner                 CfprApPolicyPolicyOwner,
    cfprApEquipmentUnifiedPortCapProviderStartPortId                 Gauge32,
    cfprApEquipmentUnifiedPortCapProviderSupportedAlgorithm          CfprApEquipmentUnifiedPortAlgorithm
}

cfprApEquipmentUnifiedPortCapProviderInstanceId OBJECT-TYPE
    SYNTAX       CfprApManagedObjectId
    MAX-ACCESS   not-accessible
    STATUS       current
    DESCRIPTION
        "Instance identifier of the managed object."
    ::= { cfprApEquipmentUnifiedPortCapProviderEntry 1 }

cfprApEquipmentUnifiedPortCapProviderDn OBJECT-TYPE
    SYNTAX       CfprApManagedObjectDn
    MAX-ACCESS   read-only
    STATUS       current
    DESCRIPTION
        "Cisco Firepower equipment:UnifiedPortCapProvider:dn
        managed object property"
    ::= { cfprApEquipmentUnifiedPortCapProviderEntry 2 }

cfprApEquipmentUnifiedPortCapProviderRn OBJECT-TYPE
    SYNTAX       SnmpAdminString
    MAX-ACCESS   read-only
    STATUS       current
    DESCRIPTION
        "Cisco Firepower equipment:UnifiedPortCapProvider:rn
        managed object property"
    ::= { cfprApEquipmentUnifiedPortCapProviderEntry 3 }

cfprApEquipmentUnifiedPortCapProviderDescr OBJECT-TYPE
    SYNTAX       SnmpAdminString
    MAX-ACCESS   read-only
    STATUS       current
    DESCRIPTION
        "Cisco Firepower equipment:UnifiedPortCapProvider:descr
        managed object property"
    ::= { cfprApEquipmentUnifiedPortCapProviderEntry 4 }

cfprApEquipmentUnifiedPortCapProviderEndPortId OBJECT-TYPE
    SYNTAX       Gauge32
    MAX-ACCESS   read-only
    STATUS       current
    DESCRIPTION
        "Cisco Firepower equipment:UnifiedPortCapProvider:endPortId
        managed object property"
    ::= { cfprApEquipmentUnifiedPortCapProviderEntry 5 }

cfprApEquipmentUnifiedPortCapProviderIntId OBJECT-TYPE
    SYNTAX       SnmpAdminString
    MAX-ACCESS   read-only
    STATUS       current
    DESCRIPTION
        "Cisco Firepower equipment:UnifiedPortCapProvider:intId
        managed object property"
    ::= { cfprApEquipmentUnifiedPortCapProviderEntry 6 }

cfprApEquipmentUnifiedPortCapProviderName OBJECT-TYPE
    SYNTAX       SnmpAdminString
    MAX-ACCESS   read-only
    STATUS       current
    DESCRIPTION
        "Cisco Firepower equipment:UnifiedPortCapProvider:name
        managed object property"
    ::= { cfprApEquipmentUnifiedPortCapProviderEntry 7 }

cfprApEquipmentUnifiedPortCapProviderPolicyLevel OBJECT-TYPE
    SYNTAX       Gauge32
    MAX-ACCESS   read-only
    STATUS       current
    DESCRIPTION
        "Cisco Firepower equipment:UnifiedPortCapProvider:policyLevel
        managed object property"
    ::= { cfprApEquipmentUnifiedPortCapProviderEntry 8 }

cfprApEquipmentUnifiedPortCapProviderPolicyOwner OBJECT-TYPE
    SYNTAX       CfprApPolicyPolicyOwner
    MAX-ACCESS   read-only
    STATUS       current
    DESCRIPTION
        "Cisco Firepower equipment:UnifiedPortCapProvider:policyOwner
        managed object property"
    ::= { cfprApEquipmentUnifiedPortCapProviderEntry 9 }

cfprApEquipmentUnifiedPortCapProviderStartPortId OBJECT-TYPE
    SYNTAX       Gauge32
    MAX-ACCESS   read-only
    STATUS       current
    DESCRIPTION
        "Cisco Firepower equipment:UnifiedPortCapProvider:startPortId
        managed object property"
    ::= { cfprApEquipmentUnifiedPortCapProviderEntry 10 }

cfprApEquipmentUnifiedPortCapProviderSupportedAlgorithm OBJECT-TYPE
    SYNTAX       CfprApEquipmentUnifiedPortAlgorithm
    MAX-ACCESS   read-only
    STATUS       current
    DESCRIPTION
        "Cisco Firepower equipment:UnifiedPortCapProvider:supportedAlgorit
        hm managed object property"
    ::= { cfprApEquipmentUnifiedPortCapProviderEntry 11 }

cfprApEquipmentUuidFeatureCapTable OBJECT-TYPE
    SYNTAX           SEQUENCE OF CfprApEquipmentUuidFeatureCapEntry
    MAX-ACCESS       not-accessible
    STATUS           current
    DESCRIPTION
        "Cisco Firepower equipment:UuidFeatureCap managed object table"
    ::= { cfprApEquipmentObjects 145 }

cfprApEquipmentUuidFeatureCapEntry OBJECT-TYPE
    SYNTAX           CfprApEquipmentUuidFeatureCapEntry
    MAX-ACCESS       not-accessible
    STATUS           current
    DESCRIPTION
        "Entry for the cfprApEquipmentUuidFeatureCapTable table."
    INDEX { cfprApEquipmentUuidFeatureCapInstanceId }
    ::= { cfprApEquipmentUuidFeatureCapTable 1 }

CfprApEquipmentUuidFeatureCapEntry ::= SEQUENCE {
    cfprApEquipmentUuidFeatureCapInstanceId                          CfprApManagedObjectId,
    cfprApEquipmentUuidFeatureCapDn                                  CfprApManagedObjectDn,
    cfprApEquipmentUuidFeatureCapRn                                  SnmpAdminString,
    cfprApEquipmentUuidFeatureCapUuidSupportMode                     CfprApEquipmentUuidFeatureCapUuidSupportMode
}

cfprApEquipmentUuidFeatureCapInstanceId OBJECT-TYPE
    SYNTAX       CfprApManagedObjectId
    MAX-ACCESS   not-accessible
    STATUS       current
    DESCRIPTION
        "Instance identifier of the managed object."
    ::= { cfprApEquipmentUuidFeatureCapEntry 1 }

cfprApEquipmentUuidFeatureCapDn OBJECT-TYPE
    SYNTAX       CfprApManagedObjectDn
    MAX-ACCESS   read-only
    STATUS       current
    DESCRIPTION
        "Cisco Firepower equipment:UuidFeatureCap:dn managed
        object property"
    ::= { cfprApEquipmentUuidFeatureCapEntry 2 }

cfprApEquipmentUuidFeatureCapRn OBJECT-TYPE
    SYNTAX       SnmpAdminString
    MAX-ACCESS   read-only
    STATUS       current
    DESCRIPTION
        "Cisco Firepower equipment:UuidFeatureCap:rn managed
        object property"
    ::= { cfprApEquipmentUuidFeatureCapEntry 3 }

cfprApEquipmentUuidFeatureCapUuidSupportMode OBJECT-TYPE
    SYNTAX       CfprApEquipmentUuidFeatureCapUuidSupportMode
    MAX-ACCESS   read-only
    STATUS       current
    DESCRIPTION
        "Cisco Firepower equipment:UuidFeatureCap:uuidSupportMode
        managed object property"
    ::= { cfprApEquipmentUuidFeatureCapEntry 4 }

cfprApEquipmentVersionConstraintTable OBJECT-TYPE
    SYNTAX           SEQUENCE OF CfprApEquipmentVersionConstraintEntry
    MAX-ACCESS       not-accessible
    STATUS           current
    DESCRIPTION
        "Cisco Firepower equipment:VersionConstraint managed object table"
    ::= { cfprApEquipmentObjects 146 }

cfprApEquipmentVersionConstraintEntry OBJECT-TYPE
    SYNTAX           CfprApEquipmentVersionConstraintEntry
    MAX-ACCESS       not-accessible
    STATUS           current
    DESCRIPTION
        "Entry for the cfprApEquipmentVersionConstraintTable table."
    INDEX { cfprApEquipmentVersionConstraintInstanceId }
    ::= { cfprApEquipmentVersionConstraintTable 1 }

CfprApEquipmentVersionConstraintEntry ::= SEQUENCE {
    cfprApEquipmentVersionConstraintInstanceId                       CfprApManagedObjectId,
    cfprApEquipmentVersionConstraintDn                               CfprApManagedObjectDn,
    cfprApEquipmentVersionConstraintRn                               SnmpAdminString,
    cfprApEquipmentVersionConstraintMinVer1                          SnmpAdminString
}

cfprApEquipmentVersionConstraintInstanceId OBJECT-TYPE
    SYNTAX       CfprApManagedObjectId
    MAX-ACCESS   not-accessible
    STATUS       current
    DESCRIPTION
        "Instance identifier of the managed object."
    ::= { cfprApEquipmentVersionConstraintEntry 1 }

cfprApEquipmentVersionConstraintDn OBJECT-TYPE
    SYNTAX       CfprApManagedObjectDn
    MAX-ACCESS   read-only
    STATUS       current
    DESCRIPTION
        "Cisco Firepower equipment:VersionConstraint:dn
        managed object property"
    ::= { cfprApEquipmentVersionConstraintEntry 2 }

cfprApEquipmentVersionConstraintRn OBJECT-TYPE
    SYNTAX       SnmpAdminString
    MAX-ACCESS   read-only
    STATUS       current
    DESCRIPTION
        "Cisco Firepower equipment:VersionConstraint:rn
        managed object property"
    ::= { cfprApEquipmentVersionConstraintEntry 3 }

cfprApEquipmentVersionConstraintMinVer1 OBJECT-TYPE
    SYNTAX       SnmpAdminString
    MAX-ACCESS   read-only
    STATUS       current
    DESCRIPTION
        "Cisco Firepower equipment:VersionConstraint:minVer1
        managed object property"
    ::= { cfprApEquipmentVersionConstraintEntry 4 }

cfprApEquipmentXcvrTable OBJECT-TYPE
    SYNTAX           SEQUENCE OF CfprApEquipmentXcvrEntry
    MAX-ACCESS       not-accessible
    STATUS           current
    DESCRIPTION
        "Cisco Firepower equipment:Xcvr managed object table"
    ::= { cfprApEquipmentObjects 147 }

cfprApEquipmentXcvrEntry OBJECT-TYPE
    SYNTAX           CfprApEquipmentXcvrEntry
    MAX-ACCESS       not-accessible
    STATUS           current
    DESCRIPTION
        "Entry for the cfprApEquipmentXcvrTable table."
    INDEX { cfprApEquipmentXcvrInstanceId }
    ::= { cfprApEquipmentXcvrTable 1 }

CfprApEquipmentXcvrEntry ::= SEQUENCE {
    cfprApEquipmentXcvrInstanceId                                    CfprApManagedObjectId,
    cfprApEquipmentXcvrDn                                            CfprApManagedObjectDn,
    cfprApEquipmentXcvrRn                                            SnmpAdminString,
    cfprApEquipmentXcvrId                                            CfprApEquipmentXcvrId,
    cfprApEquipmentXcvrModel                                         SnmpAdminString,
    cfprApEquipmentXcvrRevision                                      SnmpAdminString,
    cfprApEquipmentXcvrSerial                                        SnmpAdminString,
    cfprApEquipmentXcvrTs                                            DateAndTime,
    cfprApEquipmentXcvrType                                          CfprApEquipmentXcvrType,
    cfprApEquipmentXcvrVendor                                        SnmpAdminString
}

cfprApEquipmentXcvrInstanceId OBJECT-TYPE
    SYNTAX       CfprApManagedObjectId
    MAX-ACCESS   not-accessible
    STATUS       current
    DESCRIPTION
        "Instance identifier of the managed object."
    ::= { cfprApEquipmentXcvrEntry 1 }

cfprApEquipmentXcvrDn OBJECT-TYPE
    SYNTAX       CfprApManagedObjectDn
    MAX-ACCESS   read-only
    STATUS       current
    DESCRIPTION
        "Cisco Firepower equipment:Xcvr:dn managed object property"
    ::= { cfprApEquipmentXcvrEntry 2 }

cfprApEquipmentXcvrRn OBJECT-TYPE
    SYNTAX       SnmpAdminString
    MAX-ACCESS   read-only
    STATUS       current
    DESCRIPTION
        "Cisco Firepower equipment:Xcvr:rn managed object property"
    ::= { cfprApEquipmentXcvrEntry 3 }

cfprApEquipmentXcvrId OBJECT-TYPE
    SYNTAX       CfprApEquipmentXcvrId
    MAX-ACCESS   read-only
    STATUS       current
    DESCRIPTION
        "Cisco Firepower equipment:Xcvr:id managed object property"
    ::= { cfprApEquipmentXcvrEntry 4 }

cfprApEquipmentXcvrModel OBJECT-TYPE
    SYNTAX       SnmpAdminString
    MAX-ACCESS   read-only
    STATUS       current
    DESCRIPTION
        "Cisco Firepower equipment:Xcvr:model managed object property"
    ::= { cfprApEquipmentXcvrEntry 5 }

cfprApEquipmentXcvrRevision OBJECT-TYPE
    SYNTAX       SnmpAdminString
    MAX-ACCESS   read-only
    STATUS       current
    DESCRIPTION
        "Cisco Firepower equipment:Xcvr:revision managed object property"
    ::= { cfprApEquipmentXcvrEntry 6 }

cfprApEquipmentXcvrSerial OBJECT-TYPE
    SYNTAX       SnmpAdminString
    MAX-ACCESS   read-only
    STATUS       current
    DESCRIPTION
        "Cisco Firepower equipment:Xcvr:serial managed object property"
    ::= { cfprApEquipmentXcvrEntry 7 }

cfprApEquipmentXcvrTs OBJECT-TYPE
    SYNTAX       DateAndTime
    MAX-ACCESS   read-only
    STATUS       current
    DESCRIPTION
        "Cisco Firepower equipment:Xcvr:ts managed object property"
    ::= { cfprApEquipmentXcvrEntry 8 }

cfprApEquipmentXcvrType OBJECT-TYPE
    SYNTAX       CfprApEquipmentXcvrType
    MAX-ACCESS   read-only
    STATUS       current
    DESCRIPTION
        "Cisco Firepower equipment:Xcvr:type managed object property"
    ::= { cfprApEquipmentXcvrEntry 9 }

cfprApEquipmentXcvrVendor OBJECT-TYPE
    SYNTAX       SnmpAdminString
    MAX-ACCESS   read-only
    STATUS       current
    DESCRIPTION
        "Cisco Firepower equipment:Xcvr:vendor managed object property"
    ::= { cfprApEquipmentXcvrEntry 10 }

END
