-- *****************************************************************
-- APPN DLUR MIB
--
-- Jan 1996, Barry Chan
--
-- Copyright (c) 1996 by cisco Systems, Inc.
-- All rights reserved.
-- *****************************************************************
--
-- This mib was extracted from RFC xxxx


  APPN-DLUR-MIB DEFINITIONS ::= BEGIN

  -- ***********************************************************************
  --         MIB for APPN Dependent LU Requester
  --
  -- This MIB contains information that is useful for the management of an 
  -- APPN product that implements DLUR (Dependent Logical Unit Requester).
  -- This DLUR product has a client/server relationship with an APPN product
  -- that implements DLUR (Dependent Logical Unit Server).
  --
  -- This MIB has three groups:
  --
  --
  -- dlurNodeCapabilities	* information about the DLUR implementation
  --
  -- dlurPuInfo			* information about the PUs supported by DLUR
  --
  -- 				  (this MIB assumes the presence of the IETF
  --  				   NAU MIB, which provides a standard model
  --				   for representing PU configurations)
  --
  -- dlurDlurInfo		* information about the DLUS nodes that this
  --				  DLUR node has sessions with
  -- ***********************************************************************

  IMPORTS
	enterprises
		FROM RFC1155-SMI

	DisplayString
		FROM RFC1213-MIB

	OBJECT-TYPE
		FROM RFC-1212;

  -- *************** The appnDlur registration point  ********************

  ibm		OBJECT IDENTIFIER ::= { enterprises 2 }
  ibmArchitecture	OBJECT IDENTIFIER ::= { ibm 5 }
  appnDlur	OBJECT IDENTIFIER ::= { ibmArchitecture 12 }

  -- ********************************************************************
  --        DLUR Capabilities of the node
  -- 
  -- This group represents the capabilities and options of the DLUR
  -- implementation.
  -- ********************************************************************
  dlurNodeCapabilities	OBJECT IDENTIFIER ::= { appnDlur 1 }

  dlurReleaseLevel	OBJECT-TYPE
	SYNTAX DisplayString (SIZE (2))
	ACCESS read-only
	STATUS mandatory
	DESCRIPTION	
		"The DLUR release level of this implementation.  This is the
		value that is encoded in the DLUR/DLUS Capabilities (CV51).
		To insure consistent display, this one-byte value is encoded
		here as two displayable characters that are equivalent to a 
		hexidecimal display.  For example, if the one-byte value as 
		encoded in CV51 is X' 1', this object will contain the 
		displayable string ' 1'."

	::=  { dlurNodeCapabilities 1 }

  dlurANSsupport 	OBJECT-TYPE
	SYNTAX INTEGER {
			continueOrStop(1),
			stopOnly(2)
			}
	ACCESS read-only
	STATUS mandatory
	DESCRIPTION
		"Automatic Network Shutdown capability of this node.
     
		'continueOrStop' indicates that the DLUR implementation
		supports either ANS value (continue or stop) as specified by the 
		SLU on ACTPU value of stop.
		
		'stopOnly' indicates that the DLUR implementation only
		supports the AND value of stop.
	
		ANS = continue means that the DLUR node will keep LU-LU sessions
		active even is the SSCP-PU and SSCP-LU control sessions are interrupted.

		ANS = stop means that LU-LU sessions will be interrupted when the 
 		SSCP-PU and SSCP-LU sessions are interrupted."

	::=  { dlurNodeCapabilities 2 }
  
  dlurMultiSubnetSupport 	OBJECT-TYPE
	SYNTAX INTEGER {
			yes(1),
			no(2)
			}
	ACCESS read-only
	STATUS mandatory 
	DESCRIPTION
		"Capability of this implementation to support CP-SVR sessions 
		that cross NETID boundaries.
	
		'yes' means that these sessions can cross NETID boundaries.

		'no' means that these sessions cannot cross NETID boundaries."

	::=  { dlurNodeCapabilities 3 }

  -- **************************************************************************
  --             DLUR-unique Information about the PUs
  -- 
  -- The following talbe carries DLUR-unique information about the PUs
  -- that this APPN node is supporting via DLUR.  Notice that this table
  -- is intended to supplement the snaNodeAdminTable and snaNodeOperTable
  -- in the IETF NAU MIB.  Those tables provide a general purpose method
  -- for representing information about a set of PU resources.
  -- **************************************************************************
  dlurPuInfo	OBJECT IDENTIFIER ::= { appnDlur 2 }

  dlurPuTable	OBJECT-TYPE
	SYNTAX SEQUENCE OF DlurPuEntry
	ACCESS not-accessible
	STATUS mandatory
	DESCRIPTION
		"DLUr-unique information about supported PUs."
	
	::=  { dlurPuInfo 1 }

  dlurPuEntry	OBJECT-TYPE
	SYNTAX DlurPuEntry
	ACCESS not-accessible
	STATUS mandatory
	DESCRIPTION
		"Entry in table of DLUR-unique information about PUs."

	INDEX 
		{ dlurPuIndex }
	
	::=  { dlurPuTable 1 }

  DlurPuEntry ::= SEQUENCE {
			dlurPuIndex
				INTEGER,
			dlurPuName
				DisplayString,
			dlurPuStatus
				INTEGER,
			dlurPuANSsupport
				INTEGER,
			dlurPuLocation
				INTEGER,
			dlurPuDlusSessnStatus
				INTEGER,
			dlurPuActiveDlusName	
				DisplayString,
			dlurPuDefPrimDlusName
				DisplayString,
			dlurPuDefBackDlusName
				DisplayString
			}

  dlurPuIndex	OBJECT-TYPE
	SYNTAX INTEGER
	ACCESS read-only
	STATUS mandatory
	DESCRIPTION
		"This object has the same value as snaNodeAdminIndex
		in the snaNodeAdminEntry and snaNodeOperEntry entries of the 
		IETF SNA NAU MIB that provide information about the same PU."

	::=  { dlurPuEntry 1 }
 
  dlurPuName	OBJECT-TYPE
	SYNTAX DisplayString (SIZE (1..17))
	ACCESS read-only
	STATUS mandatory
	DESCRIPTION
		"The SNA name of the PU.  This value is expressed as
		NETID.PUNAME, including the perios (.).  If the NETID is
		not known, the PU name alone is provided.  A null string
		indicates that the value is unavailable."
	
	::=  { dlurPuEntry 2 }

  dlurPuStatus	OBJECT-TYPE
	SYNTAX INTEGER {
		reset(1),
		pendReqActRsp(2),
		pendActpu(3),
		pendActpuRsp(4),
		active(5),
		pendLinkact(6),
		pendDactpuRsp(7),
		pendInop(8),
		pendInopActpu(9)
		}
	ACCESS read-only
	STATUS mandatory
	DESCRIPTION
		"Status of the DLUR-supported PU.
		This is a more detailed enumeration os the state of the PU
		than is found in the ANU MB."

	::=  { dlurPuEntry 3 }

  dlurPuANSsupport	OBJECT-TYPE
	SYNTAX INTEGER {
		continue(1),
		stop(2) 
		}
	ACCESS read-only
	STATUS mandatory
	DESCRIPTION
		"The Automatic Network Shutdown (AND) support configured for this
		PU.  This value (as configured by the network administrator) is
		sent by the DLUS with ACTPU for each PU.

		'continue' means that the DLUR node will attempt to keep LU-LU
		sessions active even is the SSCP-PU and SSCP-LU control sessions
		are interrupted.
		
		'stop' means that LU-LU sessions will be interrupted when the
		SSCP-PU and SSCP-LU sessions are interrupted."

	::=  { dlurPuEntry 4 }

  dlurPuLocation	OBJECT-TYPE
	SYNTAX INTEGER {
		internal(1),
		downstream(2)
		}
	ACCESS read-only
	STATUS mandatory
	DESCRIPTION
		"Location of the DLUR-supported PU.  Either internal to the APPN
		node itself (no link)_ or downstream of the APPN node
		(connected via a link)."

	::=  { dlurPuEntry 5 }

  dlurPuDlusSessnStatus	OBJECT-TYPE
	SYNTAX INTEGER {	
		reset(1),
		pendingActive(2),
		active(3),
		pendingInactive(4)
		}
	ACCESS read-only
	STATUS mandatory
	DESCRIPTION
		"Status of the control session to the DLUS identified in
		dlurPuActiveDlusName.  This is a combination os 
		the separate states for the conwinner and conloser sessions."
	
	::=  { dlurPuEntry 6 }


  dlurPuActiveDlusName	OBJECT-TYPE	
	SYNTAX DisplayString (SIZE (0..17))
	ACCESS read-only
	STATUS mandatory
	DESCRIPTION
		"The SNA name of the active DLUS.  This value is expressed as
		NETID.CPNAME, including the periois (.).  A null string
		indicates that the value is unavailable."
	
	::=  { dlurPuEntry 7 }

  dlurPuDefPrimDlusName OBJECT-TYPE
	SYNTAX DisplayString (SIZE (0..17))
	ACCESS read-only
	STATUS mandatory
	DESCRIPTION
		"The SNA name os the defined primary DLUS for this PU.
		Expressed as NETID.CPNAME, including the period (.).
		A null string indicates that he value is unavailable."
	
	::=  { dlurPuEntry 8 }

  dlurPuDefBackDlusName 	OBJECT-TYPE
	SYNTAX DisplayString (SIZE (0..17))
	ACCESS read-only
	STATUS mandatory
	DESCRIPTION
		"The SNA name of the defined backup DLUR for this PU.
		Expressed as NETID.CPNAME, including the period (.).
		A null string indicates that the value is unavailable."
	
	::=  { dlurPuEntry 9 }

  -- ***********************************************************************
  --           DLUS Control Sessions (CP-SVR Pipes)
  -- 
  -- This table contains information about DLUS control sessions (also known
  -- as CP-SVR pipes).  Although DLUR uses a pair of CP-SVR sessions for
  -- communication, for purposes of status, information about those two
  -- sessions is combined to yield a single status for the request/server
  -- connection.
  -- ***********************************************************************
  dlurDlusInfo	OBJECT IDENTIFIER ::= { appnDlur 3 }
	
  dlurDlusTable	OBJECT-TYPE
	SYNTAX SEQUENCE OF DlurDlusEntry
	ACCESS not-accessible
	STATUS mandatory
	DESCRIPTION
		"Information about DLUS control sessions."

	::=  { dlurDlusInfo 1 }

  dlurDlusEntry	OBJECT-TYPE
	SYNTAX DlurDlusEntry
	ACCESS not-accessible
	STATUS mandatory
	DESCRIPTION
		"Entry in table of information about DLUS control sessions."

	INDEX
		{ dlurDlusIndex }

	::=  { dlurDlusTable 1 }

  DlurDlusEntry ::= SEQUENCE {
			dlurDlusIndex
				INTEGER,
			dlurDlusName
				DisplayString,
			dlurDlusSessnStatus
				INTEGER
			}

  dlurDlusIndex	OBJECT-TYPE
	SYNTAX INTEGER
	ACCESS read-only
	STATUS mandatory
	DESCRIPTION
		"Index to the table."

	::=  { dlurDlusEntry 1 }

  dlurDlusName 	OBJECT-TYPE
	SYNTAX DisplayString (SIZE(0..17))
	ACCESS read-only
	STATUS mandatory
	DESCRIPTION
		"The SNA name of the DLUS.  This value is expressed as
		NETID.CPNAME, including the period (.).  A null string
		indicates that the value is unavailable."

	::=  { dlurDlusEntry 2 }

  dlurDlusSessnStatus	OBJECT-TYPE
	SYNTAX INTEGER {
		reset(1),
		pendingActive(2),
		active(3),
		pendingInactive(4)
		}
	ACCESS read-only
	STATUS mandatory
	DESCRIPTION
		"Status of the session with the DLUS.  This is the combination os
		the separate states for the conwinner and conloser sessions."

	::=  { dlurDlusEntry 3 }

END
