-- *******************************************************************
-- CISCO-LWAPP-MESH MIB CAPABILITY
--   
-- November 18, 2020
--   
-- Copyright (c) 2020, 2022 by Cisco Systems, Inc.
-- All rights reserved.
-- *******************************************************************

CISCO-LWAPP-MESH-CAPABILITY DEFINITIONS ::= BEGIN

IMPORTS
    MODULE-IDENTITY
        FROM SNMPv2-SMI
    AGENT-CAPABILITIES
        FROM SNMPv2-CONF
    ciscoAgentCapability
        FROM CISCO-SMI;


ciscoLwappMeshCapability MODULE-IDENTITY
    LAST-UPDATED    "202011180000Z"
    ORGANIZATION    "Cisco Systems, Inc."
    CONTACT-INFO
            "Cisco Systems
            Customer Service

            Postal: 170 W Tasman Drive
            San Jose, CA  95134
            USA

            Tel: +1 800 553-NETS

            E-mail: cs-wnbu-snmp@cisco.com"
    DESCRIPTION
        "Agent capabilities for
        CISCO-LWAPP-MESH-MIB"
    REVISION        "202011180000Z"
    DESCRIPTION
        "Initial version of this MIB module."
    ::= { ciscoAgentCapability 1150 }



ciscoLwappMeshCapabilityCEV1R0 AGENT-CAPABILITIES
    PRODUCT-RELEASE "Cisco EWLC 1.0"
    STATUS          current
    DESCRIPTION
        "CISCO-LWAPP-MESH--MIB capabilities."

    SUPPORTS        CISCO-LWAPP-MESH-MIB
    INCLUDES        {
                        clMeshGpsInfoTable,
                        clMeshAtfStatsTable,
                        clMeshNodeTable,
                        clMeshNeighborTable
                    }

    VARIATION       clMeshGpsInfoEntry
    ACCESS          not-implemented
    DESCRIPTION
        "Not supported"

    VARIATION       clMeshGpsLocationPresent
    ACCESS          not-implemented
    DESCRIPTION
        "Not supported"

    VARIATION       clMeshGpsLocationValid
    ACCESS          not-implemented
    DESCRIPTION
        "Not supported"

    VARIATION       clMeshGpsLatitude
    ACCESS          not-implemented
    DESCRIPTION
        "Not supported"

    VARIATION       clMeshGpsLongitude
    ACCESS          not-implemented
    DESCRIPTION
        "Not supported"

    VARIATION       clMeshGpsAltitude
    ACCESS          not-implemented
    DESCRIPTION
        "Not supported"

    VARIATION       clMeshGpsCollectionTime
    ACCESS          not-implemented
    DESCRIPTION
        "Not supported"

    VARIATION       clMeshAuthFailureNotifEnabled
    ACCESS          not-implemented
    DESCRIPTION
        "Not supported"

    VARIATION       clMeshChildExcludedParentNotifEnabled
    ACCESS          not-implemented
    DESCRIPTION
        "Not supported"

    VARIATION       clMeshParentChangeNotifEnabled
    ACCESS          not-implemented
    DESCRIPTION
        "Not supported"

    VARIATION       clMeshChildMovedNotifEnabled
    ACCESS          not-implemented
    DESCRIPTION
        "Not supported"

    VARIATION       clMeshExcessiveParentChangeNotifEnabled
    ACCESS          not-implemented
    DESCRIPTION
        "Not supported"

    VARIATION       clMeshPoorSNRNotifEnabled
    ACCESS          not-implemented
    DESCRIPTION
        "Not supported"

    VARIATION       clMeshConsoleLoginNotifEnabled
    ACCESS          not-implemented
    DESCRIPTION
        "Not supported"

    VARIATION       clMeshDefaultBridgeGroupNameNotifEnabled
    ACCESS          not-implemented
    DESCRIPTION
        "Not supported"

    VARIATION       clMeshExcessiveHopCountNotifEnabled
    ACCESS          not-implemented
    DESCRIPTION
        "Not supported"

    VARIATION       clMeshExcessiveChildrenNotifEnabled
    ACCESS          not-implemented
    DESCRIPTION
        "Not supported"

    VARIATION       clMeshHighSNRNotifEnabled
    ACCESS          not-implemented
    DESCRIPTION
        "Not supported"

    VARIATION       clMeshNodePrevTemperatureState
    ACCESS          not-implemented
    DESCRIPTION
        "Not supported"

    VARIATION       clMeshNodeNewTemperatureState
    ACCESS          not-implemented
    DESCRIPTION
        "Not supported"

    VARIATION       clMeshAtfStatsEntry
    ACCESS          not-implemented
    DESCRIPTION
        "Not supported"

    VARIATION       clMeshAtfAirtimeUsedInstantaneous
    ACCESS          not-implemented
    DESCRIPTION
        "Not supported"

    VARIATION       clMeshAtfAirtimeUsedCumulative
    ACCESS          not-implemented
    DESCRIPTION
        "Not supported"

    VARIATION       clMeshAtfFramesSentInstantaneous
    ACCESS          not-implemented
    DESCRIPTION
        "Not supported"

    VARIATION       clMeshAtfFramesSentCumulative
    ACCESS          not-implemented
    DESCRIPTION
        "Not supported"

    VARIATION       clMeshAtfFramesDroppedInstantaneous
    ACCESS          not-implemented
    DESCRIPTION
        "Not supported"

    VARIATION       clMeshAtfFramesDroppedCumulative
    ACCESS          not-implemented
    DESCRIPTION
        "Not supported"

    VARIATION       clMeshNodeGroupName
    ACCESS          not-implemented
    DESCRIPTION
        "Not supported"

    VARIATION       clMeshNodeBackhaulDataRate
    ACCESS          not-implemented
    DESCRIPTION
        "Not supported"

    VARIATION       clMeshNodeEthernetBridge
    ACCESS          not-implemented
    DESCRIPTION
        "Not supported"

    VARIATION       clMeshNodeEthernetLinkStatus
    ACCESS          not-implemented
    DESCRIPTION
        "Not supported"

    VARIATION       clMeshNodePublicSafetyBackhaul
    ACCESS          not-implemented
    DESCRIPTION
        "Not supported"

    VARIATION       clMeshNodeHeaterStatus
    ACCESS          not-implemented
    DESCRIPTION
        "Not supported"

    VARIATION       clMeshNodeInternalTemp
    ACCESS          not-implemented
    DESCRIPTION
        "Not supported"

    VARIATION       clMeshNodeType
    ACCESS          not-implemented
    DESCRIPTION
        "Not supported"

    VARIATION       clMeshNodeBHDataRate
    ACCESS          not-implemented
    DESCRIPTION
        "Not supported"

    VARIATION       clMeshNodeBGNStrictMatch
    ACCESS          not-implemented
    DESCRIPTION
        "Not supported"

    VARIATION       clMeshNodeRAPDownlinkBackhaul
    ACCESS          not-implemented
    DESCRIPTION
        "Not supported"

    VARIATION       clMeshNodeRange
    ACCESS          not-implemented
    DESCRIPTION
        "Not supported"

    VARIATION       clMeshBackhaulClientAccess
    ACCESS          not-implemented
    DESCRIPTION
        "Not supported"

    VARIATION       clMeshBackgroundScan
    ACCESS          not-implemented
    DESCRIPTION
        "Not supported"

    VARIATION       clMeshAuthenticationMode
    ACCESS          not-implemented
    DESCRIPTION
        "Not supported"

    VARIATION       clMeshisAMSDUEnable
    ACCESS          not-implemented
    DESCRIPTION
        "Not supported"

    VARIATION       clMeshIsIdsEnable
    ACCESS          not-implemented
    DESCRIPTION
        "Not supported"

    VARIATION       clMeshIsDCAChannelsEnable
    ACCESS          not-implemented
    DESCRIPTION
        "Not supported"

    VARIATION       clMeshIsExtendedUAEnable
    ACCESS          not-implemented
    DESCRIPTION
        "Not supported"

    VARIATION       clMeshEthenetBridgingVlanTransparent
    ACCESS          not-implemented
    DESCRIPTION
        "Not supported"

    VARIATION       clMeshRAPDownlinkBackhaul
    ACCESS          not-implemented
    DESCRIPTION
        "Not supported"

    VARIATION       clMeshNeighborEntry
    ACCESS          not-implemented
    DESCRIPTION
        "Not supported"

    VARIATION       clMeshNeighborChannel
    ACCESS          not-implemented
    DESCRIPTION
        "Not supported"

    VARIATION       clMeshNeighborUpdate
    ACCESS          not-implemented
    DESCRIPTION
        "Not supported"

    ::= { ciscoLwappMeshCapability 1 }

END
