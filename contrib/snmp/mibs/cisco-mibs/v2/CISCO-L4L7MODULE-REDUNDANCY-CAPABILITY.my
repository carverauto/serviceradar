-- *****************************************************************
-- CISCO-L4L7MODULE-REDUNDANCY-CAPABILITY.my
-- CISCO-L4L7MODULE-REDUNDANCY-MIB.my AGENT-CAPABILITIES
--   
-- July 2008, Umayal Ramanathan.
--   
-- Copyright (c) 2008 by cisco Systems, Inc.
-- All rights reserved.
--   
-- *****************************************************************

CISCO-L4L7MODULE-REDUNDANCY-CAPABILITY DEFINITIONS ::= BEGIN

IMPORTS
    MODULE-IDENTITY
        FROM SNMPv2-SMI
    AGENT-CAPABILITIES
        FROM SNMPv2-CONF
    ciscoAgentCapability
        FROM CISCO-SMI;


ciscoL4l7moduleRedundancyCapability MODULE-IDENTITY
    LAST-UPDATED    "200807230000Z"
    ORGANIZATION    "Cisco Systems, Inc."
    CONTACT-INFO
            "Cisco Systems
            Customer Service
            Postal: 170 W Tasman Drive
            San Jose, CA  95134
            USA

            Tel: +1 800 553-NETS

            E-mail: cs-l4l7security@cisco.com"
    DESCRIPTION
        "The capabilities description for
        CISCO-L4L7MODULE-REDUNDANCY-MIB."
    REVISION        "200807230000Z"
    DESCRIPTION
        "Added capability statement cl4l7ModRedCapc4701aceVA3R100"
    ::= { ciscoAgentCapability 566 }



cl4l7ModRedCapc4710aceVA3R100 AGENT-CAPABILITIES
    PRODUCT-RELEASE "ACSW (Application Control Software) A3(1) for
                     ACE 4710 Application Control Engine Appliance"
    STATUS          current
    DESCRIPTION
        "CISCO-L4L7-MODULE-REDUNDANCY-MIB capabilities"

    SUPPORTS        CISCO-L4L7MODULE-REDUNDANCY-MIB
    INCLUDES        {
                        clrPeerConfigGroup,
                        clrRedInfoGroup,
                        clrRedundancyStatsGroup
                    }
    VARIATION       clrPeerInterface
    ACCESS          not-implemented
    DESCRIPTION
        "Object not implemented."

    VARIATION       clrPeerBackupInterface
    ACCESS          not-implemented
    DESCRIPTION
        "Object not implemented."

    VARIATION       clrPeerHeartBeatTime
    ACCESS          not-implemented
    DESCRIPTION
        "Object not implemented."

    VARIATION       clrPeerHeartBeatCount
    ACCESS          not-implemented
    DESCRIPTION
        "Object not implemented."

    VARIATION       clrPeerStorageType
    ACCESS          not-implemented
    DESCRIPTION
        "Object not implemented."

    VARIATION       clrPeerRowStatus
    ACCESS          not-implemented
    DESCRIPTION
        "Object not implemented."

    VARIATION       clrRedundancyPriority
    ACCESS          not-implemented
    DESCRIPTION
        "Object not implemented."

    VARIATION       clrRedundancyStateChangeTime
    ACCESS          not-implemented
    DESCRIPTION
        "Object not implemented."

    VARIATION       clrHAStatsMissedHeartBeatMsgs
    ACCESS          not-implemented
    DESCRIPTION
        "Object not implemented."

    VARIATION       clrHAStatsRxUniDirectionalHeartBeatMsgs
    ACCESS          not-implemented
    DESCRIPTION
        "Object not implemented."

    VARIATION       clrHAStatsHeartBeatTimeoutMismatches
    ACCESS          not-implemented
    DESCRIPTION
        "Object not implemented."

    VARIATION       clrHAStatsPeerUpEvents
    ACCESS          not-implemented
    DESCRIPTION
        "Object not implemented."

    VARIATION       clrHAStatsPeerDownEvents
    ACCESS          not-implemented
    DESCRIPTION
        "Object not implemented."

    VARIATION       clrLBStatsSharedStickyEntries
    ACCESS          not-implemented
    DESCRIPTION
        "Object not implemented."

    VARIATION       clrLBStatsSentPackets
    ACCESS          not-implemented
    DESCRIPTION
        "Object not implemented."

    VARIATION       clrLBStatsSendFailures
    ACCESS          not-implemented
    DESCRIPTION
        "Object not implemented."

    VARIATION       clrLBStatsDroppedEntries
    ACCESS          not-implemented
    DESCRIPTION
        "Object not implemented."

    VARIATION       clrLBStatsReceivedPackets
    ACCESS          not-implemented
    DESCRIPTION
        "Object not implemented."

    VARIATION       clrLBStatsReceiveFailures
    ACCESS          not-implemented
    DESCRIPTION
        "Object not implemented."

    ::= { ciscoL4l7moduleRedundancyCapability 1 }

END
