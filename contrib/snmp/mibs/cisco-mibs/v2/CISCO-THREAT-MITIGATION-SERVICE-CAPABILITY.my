-- *****************************************************************
-- CISCO-THREAT-MITIGATION-SERVICE-CAPABILITY.my:
-- Cisco Threat Mitigation Service MIB AGENT-CAPABILITIES.
--   
-- January 2007, Alok K Sinha
--   
-- Copyright (c) 2007 by Cisco Systems, Inc.
-- All rights reserved.
-- *****************************************************************

CISCO-THREAT-MITIGATION-SERVICE-CAPABILITY DEFINITIONS ::= BEGIN

IMPORTS
    MODULE-IDENTITY,
    Unsigned32
        FROM SNMPv2-SMI
    AGENT-CAPABILITIES
        FROM SNMPv2-CONF
    ciscoAgentCapability
        FROM CISCO-SMI;


ciscoThreatMitigationServiceCapability MODULE-IDENTITY
    LAST-UPDATED    "200705170000Z"
    ORGANIZATION    "Cisco Systems, Inc."
    CONTACT-INFO
            "Cisco Systems
            Customer Service

            Postal: 170 West Tasman Drive
            San Jose, CA  95134
            USA

            Tel: +1 800 553-NETS

            E-mail: cs-tms@cisco.com"
    DESCRIPTION
        "Agent capabilities for
        CISCO-THREAT-MITIGATION-SERVICE-MIB."
    REVISION        "200705170000Z"
    DESCRIPTION
        "Added the agent capabilities statement for
        ciscoTmsCapIOSV12R05T."
    REVISION        "200701290000Z"
    DESCRIPTION
        "Initial version of this MIB module."
          ::= { ciscoAgentCapability 532 }



ciscoTmsCapIOSV12R02S AGENT-CAPABILITIES
    PRODUCT-RELEASE "Cisco IOS 12.2S "
    STATUS          current
    DESCRIPTION     "CISCO-THREAT-MITIGATION-SERVICE-MIB capabilities."

    SUPPORTS        CISCO-THREAT-MITIGATION-SERVICE-MIB
    INCLUDES        {
                        ciscoTmsConsumerGroup,
                        ciscoTmsThreatGroup,
                        ciscoTmsThreatActionGroup,
                        ciscoTmsThreatInterfaceGroup,
                        ciscoTmsNotificationGroup
                    }
    VARIATION       ciTmsActiveThreats
    ACCESS          not-implemented
    DESCRIPTION     "Not implemented"

    VARIATION       ciTmsInActiveThreats
    ACCESS          not-implemented
    DESCRIPTION     "Not implemented"

    VARIATION       ciTmsConsumerDeviceId
    ACCESS          not-implemented
    DESCRIPTION     "Not implemented"

    VARIATION       ciTmsGroupsMaxEntries
    ACCESS          not-implemented
    DESCRIPTION     "Not implemented"

    VARIATION       ciTmsThreatsMaxEntries
    ACCESS          not-implemented
    DESCRIPTION     "Not implemented"

    VARIATION       ciTmsThreatActionMaxEntries
    ACCESS          not-implemented
    DESCRIPTION     "Not implemented"

    VARIATION       ciTmsInterfaceMaxEntries
    ACCESS          not-implemented
    DESCRIPTION     "Not implemented"

    VARIATION       ciTmsConsumerState
    ACCESS          accessible-for-notify
    DESCRIPTION
        "Accessible only by consumer state change
        notification"

    VARIATION       ciTmsGroupConsumerRegStatus
    ACCESS          not-implemented
    DESCRIPTION     "Not implemented"

    VARIATION       ciTmsGroupNotifEnable
    ACCESS          not-implemented
    DESCRIPTION     "Not implemented"

    VARIATION       ciTmsGroupStorageType
    ACCESS          not-implemented
    DESCRIPTION     "Not implemented"

    VARIATION       ciTmsGroupRowStatus
    ACCESS          not-implemented
    DESCRIPTION     "Not implemented"

    VARIATION       ciTmsThreatVer
    ACCESS          accessible-for-notify
    DESCRIPTION
        "Accessible only through ciscoTmsThreatStatusChange
        notification."

    VARIATION       ciTmsThreatStatus
    ACCESS          accessible-for-notify
    DESCRIPTION
        "Accessible only through ciscoTmsThreatStatusChange
        notification."

    VARIATION       ciTmsThreatClass
    ACCESS          not-implemented
    DESCRIPTION     "Not implemented"

    VARIATION       ciTmsThreatName
    ACCESS          not-implemented
    DESCRIPTION     "Not implemented"

    VARIATION       ciTmsThreatActiveTimeDuration
    ACCESS          not-implemented
    DESCRIPTION     "Not implemented"

    VARIATION       ciTmsThreatPriority
    ACCESS          accessible-for-notify
    DESCRIPTION
        "Accessible only through ciscoTmsThreatStatusChange
        notification."

    VARIATION       ciTmsThreatTcdf
    ACCESS          not-implemented
    DESCRIPTION     "Not implemented"

    VARIATION       ciTmsThreatActionParamType
    ACCESS          accessible-for-notify
    DESCRIPTION
        "Accessible only through ciscoTmsMitigationActionFailed
        notification."

    VARIATION       ciTmsThreatActionParamLength
    ACCESS          accessible-for-notify
    DESCRIPTION
        "Accessible only through ciscoTmsMitigationActionFailed
        notification."

    VARIATION       ciTmsThreatActionParamValue
    ACCESS          accessible-for-notify
    DESCRIPTION
        "Accessible only through ciscoTmsMitigationActionFailed
        notification."

    VARIATION       ciTmsThreatActionFailReason
    ACCESS          accessible-for-notify
    DESCRIPTION
        "Accessible only through ciscoTmsMitigationActionFailed
        notification."

    VARIATION       ciThreatInterfaceMitigationApplied
    ACCESS          not-implemented
    DESCRIPTION     "Not implemented"

    ::= { ciscoThreatMitigationServiceCapability 1 }

ciscoTmsCapIOSV12R05T AGENT-CAPABILITIES
    PRODUCT-RELEASE "Cisco IOS 12.5T"
    STATUS          current
    DESCRIPTION     "CISCO-THREAT-MITIGATION-SERVICE-MIB capabilities."

    SUPPORTS        CISCO-THREAT-MITIGATION-SERVICE-MIB
    INCLUDES        {
                        ciscoTmsConsumerGroup,
                        ciscoTmsThreatGroup,
                        ciscoTmsThreatActionGroup,
                        ciscoTmsThreatInterfaceGroup,
                        ciscoTmsNotificationGroup
                    }
    VARIATION       ciTmsActiveThreats
    ACCESS          not-implemented
    DESCRIPTION     "Not implemented"

    VARIATION       ciTmsInActiveThreats
    ACCESS          not-implemented
    DESCRIPTION     "Not implemented"

    VARIATION       ciTmsConsumerDeviceId
    ACCESS          not-implemented
    DESCRIPTION     "Not implemented"

    VARIATION       ciTmsGroupsMaxEntries
    ACCESS          not-implemented
    DESCRIPTION     "Not implemented"

    VARIATION       ciTmsThreatsMaxEntries
    ACCESS          not-implemented
    DESCRIPTION     "Not implemented"

    VARIATION       ciTmsThreatActionMaxEntries
    ACCESS          not-implemented
    DESCRIPTION     "Not implemented"

    VARIATION       ciTmsInterfaceMaxEntries
    ACCESS          not-implemented
    DESCRIPTION     "Not implemented"

    VARIATION       ciTmsConsumerState
    ACCESS          accessible-for-notify
    DESCRIPTION
        "Accessible only by consumer state change
        notification"

    VARIATION       ciTmsGroupConsumerRegStatus
    ACCESS          not-implemented
    DESCRIPTION     "Not implemented"

    VARIATION       ciTmsGroupNotifEnable
    ACCESS          not-implemented
    DESCRIPTION     "Not implemented"

    VARIATION       ciTmsGroupStorageType
    ACCESS          not-implemented
    DESCRIPTION     "Not implemented"

    VARIATION       ciTmsGroupRowStatus
    ACCESS          not-implemented
    DESCRIPTION     "Not implemented"

    VARIATION       ciTmsThreatVer
    ACCESS          accessible-for-notify
    DESCRIPTION
        "Accessible only through ciscoTmsThreatStatusChange
        notification."

    VARIATION       ciTmsThreatStatus
    ACCESS          accessible-for-notify
    DESCRIPTION
        "Accessible only through ciscoTmsThreatStatusChange
        notification."

    VARIATION       ciTmsThreatClass
    ACCESS          not-implemented
    DESCRIPTION     "Not implemented"

    VARIATION       ciTmsThreatName
    ACCESS          not-implemented
    DESCRIPTION     "Not implemented"

    VARIATION       ciTmsThreatActiveTimeDuration
    ACCESS          not-implemented
    DESCRIPTION     "Not implemented"

    VARIATION       ciTmsThreatPriority
    ACCESS          accessible-for-notify
    DESCRIPTION
        "Accessible only through ciscoTmsThreatStatusChange
        notification."

    VARIATION       ciTmsThreatTcdf
    ACCESS          not-implemented
    DESCRIPTION     "Not implemented"

    VARIATION       ciTmsThreatActionParamType
    ACCESS          accessible-for-notify
    DESCRIPTION
        "Accessible only through ciscoTmsMitigationActionFailed
        notification."

    VARIATION       ciTmsThreatActionParamLength
    ACCESS          accessible-for-notify
    DESCRIPTION
        "Accessible only through ciscoTmsMitigationActionFailed
        notification."

    VARIATION       ciTmsThreatActionParamValue
    ACCESS          accessible-for-notify
    DESCRIPTION
        "Accessible only through ciscoTmsMitigationActionFailed
        notification."

    VARIATION       ciTmsThreatActionFailReason
    ACCESS          accessible-for-notify
    DESCRIPTION
        "Accessible only through ciscoTmsMitigationActionFailed
        notification."

    VARIATION       ciThreatInterfaceMitigationApplied
    ACCESS          not-implemented
    DESCRIPTION     "Not implemented"

    ::= { ciscoThreatMitigationServiceCapability 2 }

END
