-- *******************************************************************
-- CISCO-LWAPP-MFP MIB CAPABILITY
--
-- November 18, 2020
--
-- Copyright (c) 2020, 2022 by Cisco Systems, Inc.
-- All rights reserved.
-- *******************************************************************

CISCO-LWAPP-MFP-CAPABILITY DEFINITIONS ::= BEGIN


IMPORTS
       MODULE-IDENTITY
           FROM SNMPv2-SMI
       AGENT-CAPABILITIES
           FROM SNMPv2-CONF
       ciscoAgentCapability
           FROM CISCO-SMI;


ciscoLwappMfpCapability  MODULE-IDENTITY

       LAST-UPDATED         "202011180000Z"
       ORGANIZATION         "Cisco Systems, Inc."
       CONTACT-INFO
               "Cisco Systems
               Customer Service

               Postal: 170 W Tasman Drive
               San Jose, CA  95134
               USA

               Tel: +1 800 553-NETS

               E-mail: cs-wnbu-snmp@cisco.com"

       DESCRIPTION
               "Agent capabilities for
               CISCO-LWAPP-MFP-MIB "
       REVISION      "202011180000Z"
       DESCRIPTION
               "Initial version of this MIB module. "

   ::= { ciscoAgentCapability 1173 }

ciscoLwappMfpCapabilityCEV1R0 AGENT-CAPABILITIES

       PRODUCT-RELEASE "Cisco EWLC 1.0"
       STATUS          current
       DESCRIPTION     "CISCO-LWAPP-MFP--MIB capabilities."

       SUPPORTS        CISCO-LWAPP-MFP-MIB
       INCLUDES        {
                           cLMfpClientTable,
                           cLMfpWlanConfigTable,
                           cLMfpApIfSmtCapTable,
                           cLMfpApParamTable
                       }

       VARIATION       cLMfpClientEntry
       ACCESS          not-implemented
       DESCRIPTION     "Not supported"

       VARIATION       cLMfpClientMfpEnabled
       ACCESS          not-implemented
       DESCRIPTION     "Not supported"

       VARIATION       cLMfpCtrlTimeBaseStatus
       ACCESS          not-implemented
       DESCRIPTION     "Not supported"

       VARIATION       cLMfpWlanConfigEntry
       ACCESS          not-implemented
       DESCRIPTION     "Not supported"

       VARIATION       cLMfpProtectionEnable
       ACCESS          not-implemented
       DESCRIPTION     "Not supported"

       VARIATION       cLMfpApIfSmtCapEntry
       ACCESS          not-implemented
       DESCRIPTION     "Not supported"

       VARIATION       cLMfpApIfMfpVersionSupported
       ACCESS          not-implemented
       DESCRIPTION     "Not supported"

       VARIATION       cLMfpApIfMfpProtectionCapability
       ACCESS          not-implemented
       DESCRIPTION     "Not supported"

       VARIATION       cLMfpApIfMfpValidationCapability
       ACCESS          not-implemented
       DESCRIPTION     "Not supported"

       VARIATION       cLMfpCtrlNotifEnable
       ACCESS          not-implemented
       DESCRIPTION     "Not supported"

       VARIATION       cLWlanIdx
       ACCESS          not-implemented
       DESCRIPTION     "Not supported"

       VARIATION       cLMfpApIfMfpProtectionActual
       ACCESS          not-implemented
       DESCRIPTION     "Not supported"

       VARIATION       cLMfpApParamEntry
       ACCESS          not-implemented
       DESCRIPTION     "Not supported"

   ::= { ciscoLwappMfpCapability 1 }

END
