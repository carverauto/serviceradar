-- $Id: CISCO-RF-SUPPLEMENTAL-MIB.my,v 1.1.2.1 2010/10/15 11:24:32 gavelayu Exp $
-- $Source: /auto/wnbu-cvsroot-acq/cvsroot/gate/lvl7dev/src/mgmt/snmp/snmp_sr/src/snmpd/unix/mibs/Attic/CISCO-RF-SUPPLEMENTAL-MIB.my,v $
-- *****************************************************************
-- CISCO-RF-SUPPLEMENTAL-MIB.my
--   
-- Created January 2001, Fred Frazer
--   
-- Copyright (c) 2001, 2004, 2014-2017, 2019 by Cisco Systems Inc.
-- All rights reserved.
-- *****************************************************************
-- $Log: CISCO-RF-SUPPLEMENTAL-MIB.my,v $
-- Revision 1.1.2.1  2010/10/15 11:24:32  gavelayu
-- bug: CSCtj49032
-- comment:Phase 1 of HA for SNMP/WEBUI. CISCO-RF-MIB implementation
-- and monitor screens.
-- *****************************************************************
-- $Endlog$

CISCO-RF-SUPPLEMENTAL-MIB DEFINITIONS ::= BEGIN

IMPORTS
    MODULE-IDENTITY,
    OBJECT-TYPE,
    NOTIFICATION-TYPE,
    Counter32
        FROM SNMPv2-SMI
    MODULE-COMPLIANCE,
    NOTIFICATION-GROUP,
    OBJECT-GROUP
        FROM SNMPv2-CONF
    TEXTUAL-CONVENTION,
    TruthValue,
    DateAndTime
        FROM SNMPv2-TC
    SnmpAdminString
        FROM SNMP-FRAMEWORK-MIB
    PhysicalIndex
        FROM ENTITY-MIB
    ifIndex,
    ifAdminStatus,
    ifOperStatus
        FROM IF-MIB
    ConfigCopyState
        FROM CISCO-CONFIG-COPY-MIB
    ciscoMgmt
        FROM CISCO-SMI;


ciscoRfSupMIB MODULE-IDENTITY
    LAST-UPDATED    "201902220000Z"
    ORGANIZATION    "Cisco Systems, Inc."
    CONTACT-INFO
            "Cisco Systems Customer Service
            Postal: 170 West Tasman Drive
                    San Jose, CA 95134
                    USA
            Tel: +1 800 553-NETS

            E-mail: cs-rf-mib@cisco.com"
    DESCRIPTION
        "This MIB was designed to complement the CISCO-RF-MIB by
        providing additional optional status and configuration control 
        for redundant CPU platforms.

        However, the MIB should also be applicable to redundant 
        platforms which don't use the RF Redundancy Framework software 
        since it makes no direct references to any CISCO-RF-MIB objects 
        or textual conventions and no direct reference to any RF 
        states, RF events or internal information.

        Glossary of terms used in this document:

            Active -   A redundant CPU which is actively controlling 
                       the system.

            Running configuration - The runtime configuration of a
                       system which reflects current configured 
                       hardware or software settings. Runtime 
                       configuration which is not stored in 
                       non-volatile memory may be lost if the system
                       loses power.

            Standby -  A redundant CPU which is not currently 
                       controlling the system, but which can take 
                       over control if the Active CPU fails.

            Startup configuration - A copy of system configuration
                       stored in non-volatile memory which can be
                       applied following a system powerup.

                       For platforms where all runtime configuration
                       is automatically stored in a non-volatile
                       manner, the running and startup configurations
                       are always identical.

            Switchover - The transfer of control from one CPU to a 
                       redundant CPU.

            Sync -     The mirroring (or synchronizing) of system 
                       state, configuration, statistics or other 
                       information from the Active CPU to a Standby 
                       CPU to allow it to maintain full system 
                       control following a switchover."
    REVISION        "201902220000Z"
    DESCRIPTION
        "Added the following notify object
        ciscoRfSupHAFailureEvent,
        and ciscoRfSupPeerLinkStateChangeEvent.
        Added ciscoRfSupNotifGroupRev1 and
        replaced by ciscoRfSupNotifGroup.
        Added ciscoRfSupMibComplianceRev3 and 
        replaced by ciscoRfSupMibComplianceRev2."
    REVISION        "200405270000Z"
    DESCRIPTION
        "Added the following scalar object to the cRfSupSystem
        subgroup:
        cRfSupSysIfCounterSync"
    REVISION        "200403040000Z"
    DESCRIPTION
        "Two notifications ciscoRfSupTimeChangeEvent and
        ciscoRfSupTimeZoneChangeEvent have been added.
        cRfSupNotificationsEnabled has been added to control 
        the above objects."
    REVISION        "200103160000Z"
    DESCRIPTION
        "The initial release of this MIB."
    ::= { ciscoMgmt 198 }



-- Textual conventions

RfSupSyncAdminState ::= TEXTUAL-CONVENTION
    STATUS          current
    DESCRIPTION
        "An enumerated value which indicates the administrative
        state to allow user control of the syncing of database 
        information from an Active unit to the Standby unit(s)."
    SYNTAX          INTEGER  {
                        enableAutoSync(1),
                        disableAutoSync(2)
                    }

RfSupSyncOperState ::= TEXTUAL-CONVENTION
    STATUS          current
    DESCRIPTION
        "An enumerated value which indicates the operational state
        for the syncing of database information from an Active unit 
        to the Standby unit(s)."
    SYNTAX          INTEGER  {
                        inSync(1),
                        lastUpdateFailed(2), -- last sync failed, reason
                                             -- unknown or unspecified.
                        commDown(3),
                                 -- All communication down to Standby
                        syncDisabled(4),
                                     -- Disabled by user configuration
                        noStandbyPresent(5)
                    }
-- OBJECT IDENTIFIER assignments for various groups

ciscoRfSupMIBNotifs  OBJECT IDENTIFIER
    ::= { ciscoRfSupMIB 0 }

ciscoRfSupMIBObjects  OBJECT IDENTIFIER
    ::= { ciscoRfSupMIB 1 }

-- sub-groups

cRfSupSystem  OBJECT IDENTIFIER
    ::= { ciscoRfSupMIBObjects 1 }

cRfSupCpu  OBJECT IDENTIFIER
    ::= { ciscoRfSupMIBObjects 2 }

cRfSupAction  OBJECT IDENTIFIER
    ::= { ciscoRfSupMIBObjects 3 }


-- The following "System" sub-group definitions are made up of
-- objects that monitor or control aspects of the combined redundant
-- system.

cRfSupSysAvailableStartTime OBJECT-TYPE
    SYNTAX          DateAndTime
    MAX-ACCESS      read-only
    STATUS          current
    DESCRIPTION
        "The date and time when this system began providing
        uninterrupted operation. This includes the time while either 
        redundant unit was Active, but may also include brief intervals 
        during switchover where the new Active unit was operational, 
        but not yet reachable for network management purposes. It may 
        also include intervals where no Standby unit was offering 
        protection, as long as the Active unit was still operational.  

        It normally changes only if an unprotected system restart
        occurs or if a Standby unit was forced to take over before 
        the initial database sync was completed.

        However, it may also change if the system's Time of Day clock 
        is changed or adjusted.  This object will be inaccurate if the
        system's Time of Day clock has not been set accurately. However,
        it should be implemented in such a way that when the system's 
        Time of Day clock is adjusted to an accurate setting, 
        cRfSupSysAvailableStartTime will also adjust to show the 
        accurate available start time." 
    ::= { cRfSupSystem 1 }

cRfSupSysSwitchoverTime OBJECT-TYPE
    SYNTAX          DateAndTime
    MAX-ACCESS      read-only
    STATUS          current
    DESCRIPTION
        "The date and time when the last CPU switchover took place.
        This object will remain uninstantiated if no switchovers have 
        taken place since the current Active CPU was initialized." 
    ::= { cRfSupSystem 2 }

cRfSupSysSwitchovers OBJECT-TYPE
    SYNTAX          Counter32
    MAX-ACCESS      read-only
    STATUS          current
    DESCRIPTION
        "The number of times that switchovers have occurred since
        cRfSupSysAvailableStartTime.

        This object will remain uninstantiated if no switchovers have 
        taken place since the current Active CPU was initialized
        or if a Standby unit was forced to take over before the 
        initial database sync was completed." 
    ::= { cRfSupSystem 3 }

cRfSupSysRunningConfigSyncTime OBJECT-TYPE
    SYNTAX          DateAndTime
    MAX-ACCESS      read-only
    STATUS          current
    DESCRIPTION
        "The date and time when the running configuration was last
        successfully synced from the current Active unit to the 
        Standby unit. 

        This object will remain uninstantiated if no sync has yet
        taken place since the current Active CPU was initialized
        or if a Standby unit was forced to take over before the 
        initial database sync was completed.

        Since automatic running configuration syncs are event driven 
        and can be disabled by configuration, this time doesn't
        directly indicate whether Standby software reflects the
        running configuration of the Active unit.

        Instead, see the cRfSupSysRunningConfigOper object to 
        determine whether Standby running configuration is in 
        sync with the Active CPU." 
    ::= { cRfSupSystem 4 }

cRfSupSysRunningConfigAdmin OBJECT-TYPE
    SYNTAX          RfSupSyncAdminState
    MAX-ACCESS      read-write
    STATUS          current
    DESCRIPTION
        "Enables/Disables automatic running configuration syncs only.
        Doesn't affect other types of sync activity. If set to the 
        default value enableAutoSync, the Active unit will send the 
        full current running configuration following any operation
        that changes the running configuration.

        Setting disableAutoSync may be useful for some maintenance 
        and debugging operations." 
    ::= { cRfSupSystem 5 }

cRfSupSysRunningConfigOper OBJECT-TYPE
    SYNTAX          RfSupSyncOperState
    MAX-ACCESS      read-only
    STATUS          current
    DESCRIPTION
        "The current operational state of running configuration syncs.
        When the value inSync is returned, it indicates that the 
        Standby running configuration is being kept actively in sync 
        with the Active unit." 
    ::= { cRfSupSystem 6 }

cRfSupSysStartupConfigSyncTime OBJECT-TYPE
    SYNTAX          DateAndTime
    MAX-ACCESS      read-only
    STATUS          current
    DESCRIPTION
        "The date and time when the startup configuration was last
        successfully synced from the current Active unit to the 
        Standby unit(s). 

        This object will remain uninstantiated if no sync has yet
        taken place since the current Active CPU was initialized
        or if a Standby unit was forced to take over before the 
        initial database sync was completed.

        For platforms where running configuration is always stored 
        in a non-volatile manner, this object should be identical
        to cRfSupSysRunningConfigSyncTime.

        Since automatic startup configuration syncs are event driven 
        and may be disabled by configuration, this time doesn't
        directly reflect whether Standby startup configuration is 
        in sync with the Active unit.

        Instead, see the cRfSupSysStartupConfigOper object to 
        determine whether Standby startup configuration is in sync 
        with the Active unit." 
    ::= { cRfSupSystem 7 }

cRfSupSysStartupConfigAdmin OBJECT-TYPE
    SYNTAX          RfSupSyncAdminState
    MAX-ACCESS      read-write
    STATUS          current
    DESCRIPTION
        "Enables/Disables automatic startup configuration syncs only.
        Doesn't affect other types of sync activity. If set to the 
        default value enableAutoSync, the Active unit will send the 
        full current startup configuration to the Standby unit(s) 
        after any operation that changes the startup configuration 
        in non-volatile memory.

        This object is not applicable to systems where running
        configuration is always stored in non-volatile memory.

        Setting disableAutoSync may be useful for some maintenance 
        and debugging operations." 
    ::= { cRfSupSystem 8 }

cRfSupSysStartupConfigOper OBJECT-TYPE
    SYNTAX          RfSupSyncOperState
    MAX-ACCESS      read-only
    STATUS          current
    DESCRIPTION
        "The current operational state of startup configuration syncs.
        When the value inSync is returned, it indicates that the 
        Standby startup configuration is being kept actively in sync 
        with the Active unit." 
    ::= { cRfSupSystem 9 }

cRfSupSysBootImageSyncTime OBJECT-TYPE
    SYNTAX          DateAndTime
    MAX-ACCESS      read-only
    STATUS          current
    DESCRIPTION
        "The date and time when the boot image memory was last
        successfully synced from the current Active unit to the 
        Standby unit(s). 

        This object will remain uninstantiated if no sync has yet
        taken place since the current Active CPU was initialized
        or if a Standby unit was forced to take over before the 
        initial database sync was completed.

        Since automatic boot image memory syncs are event driven 
        and may be disabled by configuration, this time doesn't
        directly reflect whether Standby boot image memory is 
        in sync with the Active unit.

        Instead, see the cRfSupSysBootImageOper object to determine 
        whether Standby boot image memory is in sync with the Active 
        unit." 
    ::= { cRfSupSystem 10 }

cRfSupSysBootImageAdmin OBJECT-TYPE
    SYNTAX          RfSupSyncAdminState
    MAX-ACCESS      read-write
    STATUS          current
    DESCRIPTION
        "Enables/Disables automatic boot image memory syncs only.
        Doesn't affect other types of sync activity. If set to the 
        default value enableAutoSync, the Active unit will send the 
        full current boot image memory to the Standby unit(s) after 
        any operation that affects the boot image.

        This object is not applicable for systems that don't
        support automatic boot image memory mirroring.

        Setting disableAutoSync is necessary during software upgrades 
        for the case where the boot image memory space is too small to 
        simultaneously hold both the old and new images." 
    ::= { cRfSupSystem 11 }

cRfSupSysBootImageOper OBJECT-TYPE
    SYNTAX          RfSupSyncOperState
    MAX-ACCESS      read-only
    STATUS          current
    DESCRIPTION
        "The current operational state of boot image memory syncs.
        When the value inSync is returned, it indicates that 
        Standby boot image memory is being actively mirrored from
        the Active unit." 
    ::= { cRfSupSystem 12 }

cRfSupSysStandbyBootFile OBJECT-TYPE
    SYNTAX          SnmpAdminString (SIZE  (0..255))
    MAX-ACCESS      read-write
    STATUS          current
    DESCRIPTION
        "Allow Standby unit(s) to automatically load a boot image
        which differs from the image specified for the Active unit. 
        The string should be of the form <device>:<filename>.  
        Specifying a null value indicates that Standby unit(s) should 
        not use a different image than the Active unit.

        This is used during software upgrade/downgrade procedures,
        for platforms that support automatic syncs for boot image 
        memory." 
    ::= { cRfSupSystem 13 }

cRfSupNotificationsEnabled OBJECT-TYPE
    SYNTAX          TruthValue
    MAX-ACCESS      read-write
    STATUS          current
    DESCRIPTION
        "This specifies whether ciscoRfSupTimeChangeEvent,
        ciscoRfSupTimeZoneChangeEvent notifications shall be sent 
        when the system's clock or time zone is changed causing
        a change in the values of cRfSupSysAvailableStartTime or 
        cRfSupSysSwitchoverTime objects.

        Notifications will be sent only if this object is 
        set to 'true'."
    DEFVAL          { false } 
    ::= { cRfSupSystem 14 }

cRfSupSysIfCounterSync OBJECT-TYPE
    SYNTAX          TruthValue
    MAX-ACCESS      read-write
    STATUS          current
    DESCRIPTION
        "This object configures the synchronization of Interface
        Statistics information from Active CPU to the
        Standby CPU.
        When this object is set to 'true', synchronization is
        enabled. When this object is set to 'false',
        synchronization is disabled." 
    ::= { cRfSupSystem 15 }

cRfSupSysFailureReason OBJECT-TYPE
    SYNTAX          OCTET STRING
    MAX-ACCESS      read-only
    STATUS          current
    DESCRIPTION
        "This object represents the reason code for a generic
        failure between Active and redundant unit. The generic failure
        can be a sync failure, upload and download issue.
        Failure reason is a texual description of the failure." 
    ::= { cRfSupSystem 16 }

cRfSupSysSeverity OBJECT-TYPE
    SYNTAX          INTEGER  {
                        critical(1),
                        major(2),
                        minor(3),
                        informational(4),
                        clear(5)
                    }
    MAX-ACCESS      read-only
    STATUS          current
    DESCRIPTION
        "This object represents the severity for a generic
        failure between Active and redundant unit. The generic 
        failure can be a sync failure, upload and download issue.
        critical - Critical severity alarm has to be raised for 
                   cRfSupSysErrorType
        major - Major failure that occured during sync/upload/download.
        minor - Minor failure that occured during sync/upload/download.
        Informational - warning during sync/upload/download.
        clear - Critical severity alarm to be cleared for the 
                cRfSupSysErrorType." 
    ::= { cRfSupSystem 17 }

cRfSupSysErrorType OBJECT-TYPE
    SYNTAX          INTEGER  {
                        download-config(1),
                        download-code(2),
                        download-icon(3),
                        download-image(4),
                        download-signature(5),
                        download-webadmincert(6),
                        download-webauthcert(7),
                        download-webauthbundle(8),
                        download-eapdevcert(9),
                        download-eapcacert(10),
                        download-login-banner(11),
                        upload-config(12),
                        upload-debug-file(13),
                        upload-crashfile(14),
                        upload-watchdog-crash-file(15),
                        upload-panic-crash-file(16),
                        upload-coredump(17),
                        upload-errorlog(18),
                        upload-invalid-config(19),
                        upload-pac(20),
                        upload-radio-core-dump(21),
                        upload-ap-crash-data(22),
                        upload-signature(23),
                        upload-systemtrace(24),
                        upload-packet-capture(25),
                        upload-traplog(26),
                        route-add(27),
                        route-del(28),
                        interface-service-port(29),
                        reset(30),
                        other(31),
                        config-sync-fail(32),
                        peer-maintenance(33),
                        peer-loss(34),
                        rfTrapClearTemplist(35)
                    }
    MAX-ACCESS      read-only
    STATUS          current
    DESCRIPTION
        "This object represents the error type for a generic
        failure between Active and redundant unit. The generic 
        failure can be a sync failure, upload and download issue.
        Notification will be sent if the object has a valid 
        error type. 
        A value of download-config indicates that, config download 
        is failed.
        A value of download-code indicates that, code download is 
        failed.
        A value of download-icon indicates that, icon download is 
        failed. 
        A value of download-image indicates that, image download is 
        failed.
        A value of download-signature indicates that, signature download 
        is failed.
        A value of download-webadmincert indicates that, webadmincert 
        download is failed.
        A value of download-webauthcert indicates that, webauthcert 
        download is failed.
        A value of download-webauthbundle indicates that, webauthbundle 
        download is failed.
        A value of download-eapdevcert indicates that, eapdevcert 
        download is failed.
        A value of download-eapcacert indicates that,  eapcacert 
        download is failed.
        A value of download-login-banner indicates that, login 
        banner download is failed.
        A value of upload-config indicates that, config upload 
        is failed.
        A value of upload-debug-file indicates that, debug file 
        upload is failed.
        A value of upload-crashfile indicates that, crash file 
        upload is failed.
        A value of upload-watchdog-crash-file indicates that, watchdog 
        crash file upload is failed.
        A value of upload-panic-crash-file indicates that, panic crash 
        file upload is failed.
        A value of upload-coredump indicates that, coredump upload 
        is failed.
        A value of upload-errorlog indicates that, errorlog upload 
        is failed.
        A value of upload-invalid-config indicates that, invalid 
        config upload is failed.
        A value of upload-pac indicates that, pac upload is failed.
        A value of upload-radio-core-dump that, radio core dump 
        upload is failed.
        A value of upload-ap-crash-data indicates that, ap crash data 
        upload is failed.
        A value of upload-signature indicates that, signature upload is 
        failed.
        A value of upload-systemtrace indicates that, system trace upload 
        is failed.
        A value of upload-packet-capture indicates that, packet capture 
        upload is failed.
        A value of upload-traplog indicates that, trap log upload 
        is failed. 
        A value of route-add indicates that, addition of route is failed. 
        A value of route-del indicates that, deletion of route is failed.
        A value of interface-service-port indicates that, service port 
        interface is failed.
        A value of reset indicates that, reset is failed.
        A value of other indicates that, other reason for failed.
        A value of config-sync-fail indicates that, config sync 
        is failed.
        A value of peer-maintenance indicates that, maintenance of peer 
        is failed.
        A value of peer-loss indicates that, peer connection losed.
        A value of rfTrapClearTemplist indicates that, rf trap clear temp 
        list is failed." 
    ::= { cRfSupSystem 18 }
-- The following "Cpu" sub-group definitions are made up of
-- objects that monitor or control aspects of the individual
-- redundant units.

cRfSupCpuTable OBJECT-TYPE
    SYNTAX          SEQUENCE OF CRfSupCpuEntry 
    MAX-ACCESS      not-accessible
    STATUS          current
    DESCRIPTION
        "A table containing redundancy-related information for
        individual CPU cards."
    ::= { cRfSupCpu 1 }

cRfSupCpuEntry OBJECT-TYPE
    SYNTAX          CRfSupCpuEntry
    MAX-ACCESS      not-accessible
    STATUS          current
    DESCRIPTION
        "Information which can differ for each of the redundant
        CPU units in the system."
    INDEX           { cRfSupCpuUniqueIndex } 
    ::= { cRfSupCpuTable 1 }

CRfSupCpuEntry ::= SEQUENCE {
        cRfSupCpuUniqueIndex    PhysicalIndex,
        cRfSupCpuActiveSeverity INTEGER,
        cRfSupCpuInitTime       DateAndTime
}

cRfSupCpuUniqueIndex OBJECT-TYPE
    SYNTAX          PhysicalIndex
    MAX-ACCESS      not-accessible
    STATUS          current
    DESCRIPTION
        "A table index which always has a unique platform-assigned
        value for each physical redundant unit within a particular 
        system. 

        This index should refer to a particular physical unit 
        rather than a logically Active or Standby unit." 
    ::= { cRfSupCpuEntry 1 }

cRfSupCpuActiveSeverity OBJECT-TYPE
    SYNTAX          INTEGER  {
                        nonFaulty(0),
                        nonTrafficAffectingFault(1),
                        partialTrafficAffectingFault(2),
                        fullyTrafficAffectingFault(3),
                        unknown(4)
                    }
    MAX-ACCESS      read-only
    STATUS          current
    DESCRIPTION
        "The fault severity of a redundant unit, as calculated by
        software. The value zero represents a good unit with no 
        detected faults. Higher values represent progressively more 
        serious faults.  If it's not possible to determine any current 
        or prior severity information about a unit, the value unknown 
        should be returned.

        Unlike some severity definitions, cRfSupCpuActiveSeverity 
        should not be downgraded when it switches from being Active. 
        The severity for a faulty Standby unit should correspond to 
        the system impact it would have if it were made to be the 
        Active unit, assuming the severity can be determined while 
        Standby.

        The severity can be affected by either hardware or software 
        faults with the CPU itself. It can also be affected by faults
        which prevent this CPU from interacting with one or more other
        system components (such as linecards), even when the actual 
        faulty Field Replaceable Unit (FRU) is not the CPU itself.

        As a minimum, the nonFaulty and fullyTrafficAffectingFault
        values should be supported on any platform supporting this 
        object. Support of the other severity values is preferred, 
        but optional." 
    ::= { cRfSupCpuEntry 2 }

cRfSupCpuInitTime OBJECT-TYPE
    SYNTAX          DateAndTime
    MAX-ACCESS      read-only
    STATUS          current
    DESCRIPTION
        "The date and time when this redundant unit was last
        initialized. 

        If the unit started out in the Standby state, this will also 
        include the time while running as Standby." 
    ::= { cRfSupCpuEntry 3 }
 


-- The following "Action" sub-group definitions are made up of objects
-- that are associated with the execution of system actions.

cRfSupActionManualSync OBJECT-TYPE
    SYNTAX          INTEGER  {
                        noAction(1),
                        runningConfig(2),
                        startupConfig(3),
                        bootImage(4)
                    }
    MAX-ACCESS      read-write
    STATUS          current
    DESCRIPTION
        "This variable is set to invoke a one-time manual copy of the
        specified information type from the Active to one or more 
        Standby units.

        When read, this object returns the last command written
        or noAction if no action has been written to the Active unit
        since it was initialized. The value noAction can not be used
        in a write request. 

        The result of the last requested action can be determined 
        by reading the value of cRfSupActionLastSyncResult. The value 
        of the cRfSupActionManualSync object can not be changed until 
        the cRfSupActionLastSyncResult transitions to the successful
        or failed state." 
    ::= { cRfSupAction 1 }

cRfSupActionLastSyncResult OBJECT-TYPE
    SYNTAX          ConfigCopyState
    MAX-ACCESS      read-only
    STATUS          current
    DESCRIPTION
        "Contains the result of the last Manual Sync action request.
        This object is instantiated only after the 
        cRfSupActionManualSync object has been set to a value other 
        than noAction." 
    ::= { cRfSupAction 2 }

-- Notifications

ciscoRfSupTimeChangeEvent NOTIFICATION-TYPE
    OBJECTS         {
                        cRfSupSysAvailableStartTime,
                        cRfSupSysSwitchoverTime
                    }
    STATUS          current
    DESCRIPTION
        "This notification is sent on the event of system clock
        modification causing a change in the values of 
        cRfSupSysAvailableStartTime or cRfSupSysSwitchoverTime objects,
        if cRfSupNotificationsEnabled object has value 'true'.

        If the system clock change is a result of a time zone change
        event,this notification will not be sent."
   ::= { ciscoRfSupMIBNotifs 1 }

ciscoRfSupTimeZoneChangeEvent NOTIFICATION-TYPE
    OBJECTS         {
                        cRfSupSysAvailableStartTime,
                        cRfSupSysSwitchoverTime
                    }
    STATUS          current
    DESCRIPTION
        "This notification is sent on the event of system time zone
        modification causing a change in the values of 
        cRfSupSysAvailableStartTime or cRfSupSysSwitchoverTime objects,
        if cRfSupNotificationsEnabled object has value 'true'."
   ::= { ciscoRfSupMIBNotifs 2 }

ciscoRfSupHAFailureEvent NOTIFICATION-TYPE
    OBJECTS         {
                        cRfSupSysStartupConfigSyncTime,
                        cRfSupSysRunningConfigSyncTime,
                        cRfSupActionManualSync,
                        cRfSupActionLastSyncResult,
                        cRfSupSysFailureReason,
                        cRfSupSysSeverity,
                        cRfSupSysErrorType
                    }
    STATUS          current
    DESCRIPTION
        "This notification is sent on the event of a generic failure
        between the active and standby unit"
   ::= { ciscoRfSupMIBNotifs 3 }

ciscoRfSupPeerLinkStateChangeEvent NOTIFICATION-TYPE
    OBJECTS         {
                        ifIndex,
                        ifAdminStatus,
                        ifOperStatus
                    }
    STATUS          current
    DESCRIPTION
        "This notification is sent on the event of a Standby
        Port state change"
   ::= { ciscoRfSupMIBNotifs 4 }
-- Conformance

ciscoRfSupMibConformance  OBJECT IDENTIFIER
    ::= { ciscoRfSupMIB 2 }

ciscoRfSupMibCompliances  OBJECT IDENTIFIER
    ::= { ciscoRfSupMibConformance 1 }

ciscoRfSupMibGroups  OBJECT IDENTIFIER
    ::= { ciscoRfSupMibConformance 2 }


-- compliance statements

ciscoRfSupMibCompliance MODULE-COMPLIANCE
    STATUS          deprecated
    DESCRIPTION
        "The compliance statement for entities which implement the
        Cisco RF SUPPLEMENTAL MIB. 

        Note: Platforms which implement the Cisco RF MIB are 
        not required to support the RF SUPPLEMENTAL MIB."
    MODULE          -- this module
    MANDATORY-GROUPS {
                        ciscoRfSupSysGroup,
                        ciscoRfSupActionGroup
                    }

    GROUP           ciscoRfSupCpuGroup
    DESCRIPTION
        "The ciscoRfSupCpuGroup is mandatory only for platforms
        supporting the ENTITY-MIB."
    ::= { ciscoRfSupMibCompliances 1 }

ciscoRfSupMibComplianceRev1 MODULE-COMPLIANCE
    STATUS          deprecated
    DESCRIPTION
        "The compliance statement for entities which implement the
        Cisco RF SUPPLEMENTAL MIB.

        Note: Platforms which implement the Cisco RF MIB are
        not required to support the RF SUPPLEMENTAL MIB."
    MODULE          -- this module
    MANDATORY-GROUPS {
                        ciscoRfSupSysGroup,
                        ciscoRfSupActionGroup
                    }

    GROUP           ciscoRfSupCpuGroup
    DESCRIPTION
        "The ciscoRfSupCpuGroup is mandatory only for platforms
        supporting the ENTITY-MIB."

    GROUP           ciscoRfSupSysOptionalGroup
    DESCRIPTION
        "The ciscoRfSupSysOptionalGroup is mandatory only for
        systems supporting ciscoRfSupNotifGroup."
    ::= { ciscoRfSupMibCompliances 2 }

ciscoRfSupMibComplianceRev2 MODULE-COMPLIANCE
    STATUS          deprecated
    DESCRIPTION
        "The compliance statement for entities which implement the
        Cisco RF SUPPLEMENTAL MIB.

        Note: Platforms which implement the Cisco RF MIB are
        not required to support the RF SUPPLEMENTAL MIB."
    MODULE          -- this module
    MANDATORY-GROUPS {
                        ciscoRfSupSysGroup,
                        ciscoRfSupActionGroup
                    }

    GROUP           ciscoRfSupCpuGroup
    DESCRIPTION
        "The ciscoRfSupCpuGroup is mandatory only for platforms
        supporting the ENTITY-MIB."

    GROUP           ciscoRfSupSysOptionalGroup
    DESCRIPTION
        "The ciscoRfSupSysOptionalGroup is mandatory only for
        systems supporting ciscoRfSupNotifGroup."

    GROUP           ciscoRfSupNotifGroup
    DESCRIPTION
        "This group is optional on platforms supporting the
        CISCO-RF-SUPPLEMENTAL-MIB."

    GROUP           ciscoRfSupSysOptionalSyncGroup
    DESCRIPTION
        "This group is optional on platforms supporting the
        the CISCO-RF-SUPPLEMENTAL-MIB."
    ::= { ciscoRfSupMibCompliances 3 }

ciscoRfSupMibComplianceRev3 MODULE-COMPLIANCE
    STATUS          current
    DESCRIPTION
        "The compliance statement for entities which implement the
        Cisco RF SUPPLEMENTAL MIB.

        Note: Platforms which implement the Cisco RF MIB are
        not required to support the RF SUPPLEMENTAL MIB."
    MODULE          -- this module
    MANDATORY-GROUPS {
                        ciscoRfSupSysGroup,
                        ciscoRfSupActionGroup
                    }

    GROUP           ciscoRfSupCpuGroup
    DESCRIPTION
        "The ciscoRfSupCpuGroup is mandatory only for platforms
        supporting the ENTITY-MIB."

    GROUP           ciscoRfSupSysOptionalGroup
    DESCRIPTION
        "The ciscoRfSupSysOptionalGroup is mandatory only for
        systems supporting ciscoRfSupNotifGroup."

    GROUP           ciscoRfSupNotifGroupRev1
    DESCRIPTION
        "This group is optional on platforms supporting the
        CISCO-RF-SUPPLEMENTAL-MIB."

    GROUP           ciscoRfSupSysOptionalSyncGroup
    DESCRIPTION
        "This group is optional on platforms supporting the
        the CISCO-RF-SUPPLEMENTAL-MIB."
    ::= { ciscoRfSupMibCompliances 4 }

-- Units of conformance

ciscoRfSupSysGroup OBJECT-GROUP
    OBJECTS         {
                        cRfSupSysAvailableStartTime,
                        cRfSupSysSwitchoverTime,
                        cRfSupSysSwitchovers,
                        cRfSupSysRunningConfigSyncTime,
                        cRfSupSysRunningConfigAdmin,
                        cRfSupSysRunningConfigOper,
                        cRfSupSysStartupConfigSyncTime,
                        cRfSupSysStartupConfigAdmin,
                        cRfSupSysStartupConfigOper,
                        cRfSupSysBootImageSyncTime,
                        cRfSupSysBootImageAdmin,
                        cRfSupSysBootImageOper,
                        cRfSupSysStandbyBootFile
                    }
    STATUS          current
    DESCRIPTION
        "The collection of RF SUPPLEMENTAL system-wide objects."
    ::= { ciscoRfSupMibGroups 1 }

ciscoRfSupCpuGroup OBJECT-GROUP
    OBJECTS         {
                        cRfSupCpuActiveSeverity,
                        cRfSupCpuInitTime
                    }
    STATUS          current
    DESCRIPTION
        "The collection of RF SUPPLEMENTAL per-CPU objects."
    ::= { ciscoRfSupMibGroups 2 }

ciscoRfSupActionGroup OBJECT-GROUP
    OBJECTS         {
                        cRfSupActionManualSync,
                        cRfSupActionLastSyncResult
                    }
    STATUS          current
    DESCRIPTION
        "The collection of RF SUPPLEMENTAL execution actions."
    ::= { ciscoRfSupMibGroups 3 }

ciscoRfSupSysOptionalGroup OBJECT-GROUP
    OBJECTS         { cRfSupNotificationsEnabled }
    STATUS          current
    DESCRIPTION
        "The collection of optional RF SUPPLEMENTAL system-wide
        objects."
    ::= { ciscoRfSupMibGroups 4 }

ciscoRfSupNotifGroup NOTIFICATION-GROUP
   NOTIFICATIONS    { ciscoRfSupTimeChangeEvent }
    STATUS          deprecated
    DESCRIPTION
        "The collection of optional notifications issued on
        system time/time zone modifications.
        ciscoRfSupNotifGroup object is superseded by ciscoRfSupNotifGroupRev1."
    ::= { ciscoRfSupMibGroups 5 }

ciscoRfSupSysOptionalSyncGroup OBJECT-GROUP
    OBJECTS         { cRfSupSysIfCounterSync }
    STATUS          current
    DESCRIPTION
        "The collection of optional RF SUPPLEMENTAL system wide
        objects that control and monitor the synchronization of
        information between the redundant system units."
    ::= { ciscoRfSupMibGroups 6 }

ciscoRfSupNotifGroupRev1 NOTIFICATION-GROUP
   NOTIFICATIONS    {
                        ciscoRfSupTimeChangeEvent,
                        ciscoRfSupTimeZoneChangeEvent,
                        ciscoRfSupHAFailureEvent,
                        ciscoRfSupPeerLinkStateChangeEvent
                    }
    STATUS          current
    DESCRIPTION
        "The collection of optional notifications issued on
        system time/time zone modifications."
    ::= { ciscoRfSupMibGroups 7 }

END
