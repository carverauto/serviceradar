-- *******************************************************************
-- CISCO-LWAPP-REAP MIB CAPABILITY
--
-- November 18, 2020
--
-- Copyright (c) 2020, 2022 by Cisco Systems, Inc.
-- All rights reserved.
-- *******************************************************************

CISCO-LWAPP-REAP-CAPABILITY DEFINITIONS ::= BEGIN


IMPORTS
       MODULE-IDENTITY
           FROM SNMPv2-SMI
       AGENT-CAPABILITIES
           FROM SNMPv2-CONF
       ciscoAgentCapability
           FROM CISCO-SMI;


ciscoLwappReapCapability  MODULE-IDENTITY

       LAST-UPDATED         "202011180000Z"
       ORGANIZATION         "Cisco Systems, Inc."
       CONTACT-INFO
               "Cisco Systems
               Customer Service

               Postal: 170 W Tasman Drive
               San Jose, CA  95134
               USA

               Tel: +1 800 553-NETS

               E-mail: cs-wnbu-snmp@cisco.com"

       DESCRIPTION
               "Agent capabilities for
               CISCO-LWAPP-REAP-MIB "
       REVISION      "202011180000Z"
       DESCRIPTION
               "Initial version of this MIB module. "

   ::= { ciscoAgentCapability 1172 }

ciscoLwappReapCapabilityCEV1R0 AGENT-CAPABILITIES

       PRODUCT-RELEASE "Cisco EWLC 1.0"
       STATUS          current
       DESCRIPTION     "CISCO-LWAPP-REAP--MIB capabilities."

       SUPPORTS        CISCO-LWAPP-REAP-MIB
       INCLUDES        {
                           cLReapIpv6AclTable,
                           cLReapAclTable,
                           cLReapGroupLocalSplitAclTable,
                           cLReapApL2AclTable,
                           cLReapGroupVlanAclTable,
                           cLReapGroupConfigTable,
                           cLReapMasterApConfigTable,
                           cLReapApCentralDhcpTable,
                           cLReapIpv6AclRuleTable,
                           cLReapWebPolicyAclTable,
                           cLReapGroupWebPolicyAclTable,
                           cLReapApVlanIdAclTable,
                           cLReapApWlanAclTable,
                           cLReapAclUrlDomainRuleTable,
                           cLReapGroupUserConfigTable,
                           cLReapGroupAclTable,
                           cLReapApVlanIdTable,
                           cLReapGroupApConfigTable,
                           cLReapVlanIdNameMapTable,
                           cLReapIpv6AclUrlDomainRuleTable,
                           cLReapApLocalSplitACLTable,
                           cLReapL2AclRuleTable,
                           cLReapGroupVlanIdTable,
                           cLReapWlanConfigTable,
                           cLReapAclRuleTable,
                           cLReapGroupAVCFlexTable,
                           cLReapApConfigTable,
                           cLReapGroupCentralDhcpTable,
                           cLReapL2AclTable
                       }

       VARIATION       cLReapIpv6AclEntry
       ACCESS          not-implemented
       DESCRIPTION     "Not supported"

       VARIATION       cLReapIpv6AclName
       ACCESS          not-implemented
       DESCRIPTION     "Not supported"

       VARIATION       cLReapIpv6AclApplyMode
       ACCESS          not-implemented
       DESCRIPTION     "Not supported"

       VARIATION       cLReapIpv6AclRowStatus
       ACCESS          not-implemented
       DESCRIPTION     "Not supported"

       VARIATION       cLReapAclEntry
       ACCESS          not-implemented
       DESCRIPTION     "Not supported"

       VARIATION       cLReapAclName
       ACCESS          not-implemented
       DESCRIPTION     "Not supported"

       VARIATION       cLReapAclApplyMode
       ACCESS          not-implemented
       DESCRIPTION     "Not supported"

       VARIATION       cLReapAclRowStatus
       ACCESS          not-implemented
       DESCRIPTION     "Not supported"

       VARIATION       cLReapAclUrlDomainListType
       ACCESS          not-implemented
       DESCRIPTION     "Not supported"

       VARIATION       cLReapGroupLocalSplitAclEntry
       ACCESS          not-implemented
       DESCRIPTION     "Not supported"

       VARIATION       cLReapGroupLocalSplitAcl
       ACCESS          not-implemented
       DESCRIPTION     "Not supported"

       VARIATION       cLReapGroupLocalSplitAclRowStatus
       ACCESS          not-implemented
       DESCRIPTION     "Not supported"

       VARIATION       cLReapApL2AclEntry
       ACCESS          not-implemented
       DESCRIPTION     "Not supported"

       VARIATION       cLReapApL2Acl
       ACCESS          not-implemented
       DESCRIPTION     "Not supported"

       VARIATION       cLReapApL2AclRowStatus
       ACCESS          not-implemented
       DESCRIPTION     "Not supported"

       VARIATION       cLReapGroupIngressAcl
       ACCESS          not-implemented
       DESCRIPTION     "Not supported"

       VARIATION       cLReapGroupEgressAcl
       ACCESS          not-implemented
       DESCRIPTION     "Not supported"

       VARIATION       cLReapGroupVlanOrder
       ACCESS          not-implemented
       DESCRIPTION     "Not supported"

       VARIATION       cLReapGroupPrimaryRadiusIndex
       ACCESS          not-implemented
       DESCRIPTION     "Not supported"

       VARIATION       cLReapGroupSecondaryRadiusIndex
       ACCESS          not-implemented
       DESCRIPTION     "Not supported"

       VARIATION       cLReapGroupStorageType
       ACCESS          not-implemented
       DESCRIPTION     "Not supported"

       VARIATION       cLReapGroupRowStatus
       ACCESS          not-implemented
       DESCRIPTION     "Not supported"

       VARIATION       cLReapGroupRadiusPacTimeout
       ACCESS          not-implemented
       DESCRIPTION     "Not supported"

       VARIATION       cLReapGroupRadiusAuthorityId
       ACCESS          not-implemented
       DESCRIPTION     "Not supported"

       VARIATION       cLReapGroupRadiusAuthorityInfo
       ACCESS          not-implemented
       DESCRIPTION     "Not supported"

       VARIATION       cLReapGroupRadiusServerKey
       ACCESS          not-implemented
       DESCRIPTION     "Not supported"

       VARIATION       cLReapGroupRadiusIgnoreKey
       ACCESS          not-implemented
       DESCRIPTION     "Not supported"

       VARIATION       cLReapGroupRadiusPacTimeoutCtrl
       ACCESS          not-implemented
       DESCRIPTION     "Not supported"

       VARIATION       cLReapGroupApUpgradeStart
       ACCESS          not-implemented
       DESCRIPTION     "Not supported"

       VARIATION       cLReapGroupPrimaryRadiusServerType
       ACCESS          not-implemented
       DESCRIPTION     "Not supported"

       VARIATION       cLReapGroupPrimaryRadiusServerAddress
       ACCESS          not-implemented
       DESCRIPTION     "Not supported"

       VARIATION       cLReapGroupPrimaryRadiusServerPort
       ACCESS          not-implemented
       DESCRIPTION     "Not supported"

       VARIATION       cLReapGroupPrimaryServerSecret
       ACCESS          not-implemented
       DESCRIPTION     "Not supported"

       VARIATION       cLReapGroupSecRadiusServerType
       ACCESS          not-implemented
       DESCRIPTION     "Not supported"

       VARIATION       cLReapGroupSecRadiusServerAddress
       ACCESS          not-implemented
       DESCRIPTION     "Not supported"

       VARIATION       cLReapGroupSecRadiusServerPort
       ACCESS          not-implemented
       DESCRIPTION     "Not supported"

       VARIATION       cLReapGroupSecServerSecret
       ACCESS          not-implemented
       DESCRIPTION     "Not supported"

       VARIATION       cLReapGroupCertificateEapTlsEnable
       ACCESS          not-implemented
       DESCRIPTION     "Not supported"

       VARIATION       cLReapGroupOverrideVlanEnable
       ACCESS          not-implemented
       DESCRIPTION     "Not supported"

       VARIATION       cLReapGroupVlanTemplateName
       ACCESS          not-implemented
       DESCRIPTION     "Not supported"

       VARIATION       cLReapGroupEfficientApJoinEnable
       ACCESS          not-implemented
       DESCRIPTION     "Not supported"

       VARIATION       cLReapMasterApConfigEntry
       ACCESS          not-implemented
       DESCRIPTION     "Not supported"

       VARIATION       cLReapMasterApModel
       ACCESS          not-implemented
       DESCRIPTION     "Not supported"

       VARIATION       cLReapMasterApManual
       ACCESS          not-implemented
       DESCRIPTION     "Not supported"

       VARIATION       cLReapMasterApRowStatus
       ACCESS          not-implemented
       DESCRIPTION     "Not supported"

       VARIATION       cLReapApCentralDhcpEntry
       ACCESS          not-implemented
       DESCRIPTION     "Not supported"

       VARIATION       cLReapApDhcpCentral
       ACCESS          not-implemented
       DESCRIPTION     "Not supported"

       VARIATION       cLReapApDhcpOverrideDNS
       ACCESS          not-implemented
       DESCRIPTION     "Not supported"

       VARIATION       cLReapApNatPatEnabled
       ACCESS          not-implemented
       DESCRIPTION     "Not supported"

       VARIATION       cLReapApDhcpRowStatus
       ACCESS          not-implemented
       DESCRIPTION     "Not supported"

       VARIATION       cLReapApInheritance
       ACCESS          not-implemented
       DESCRIPTION     "Not supported"

       VARIATION       cLReapIpv6AclRuleEntry
       ACCESS          not-implemented
       DESCRIPTION     "Not supported"

       VARIATION       cLReapIpv6AclRuleIndex
       ACCESS          not-implemented
       DESCRIPTION     "Not supported"

       VARIATION       cLReapIpv6AclRuleAction
       ACCESS          not-implemented
       DESCRIPTION     "Not supported"

       VARIATION       cLReapIpv6AclRuleSourceAddressType
       ACCESS          not-implemented
       DESCRIPTION     "Not supported"

       VARIATION       cLReapIpv6AclRuleSourceAddress
       ACCESS          not-implemented
       DESCRIPTION     "Not supported"

       VARIATION       cLReapIpv6AclRuleSourcePrefixLength
       ACCESS          not-implemented
       DESCRIPTION     "Not supported"

       VARIATION       cLReapIpv6AclRuleDestinationAddressType
       ACCESS          not-implemented
       DESCRIPTION     "Not supported"

       VARIATION       cLReapIpv6AclRuleDestinationAddress
       ACCESS          not-implemented
       DESCRIPTION     "Not supported"

       VARIATION       cLReapIpv6AclRuleDestinationPrefixLength
       ACCESS          not-implemented
       DESCRIPTION     "Not supported"

       VARIATION       cLReapIpv6AclRuleProtocol
       ACCESS          not-implemented
       DESCRIPTION     "Not supported"

       VARIATION       cLReapIpv6AclRuleStartSourcePort
       ACCESS          not-implemented
       DESCRIPTION     "Not supported"

       VARIATION       cLReapIpv6AclRuleEndSourcePort
       ACCESS          not-implemented
       DESCRIPTION     "Not supported"

       VARIATION       cLReapIpv6AclRuleStartDestinationPort
       ACCESS          not-implemented
       DESCRIPTION     "Not supported"

       VARIATION       cLReapIpv6AclRuleEndDestinationPort
       ACCESS          not-implemented
       DESCRIPTION     "Not supported"

       VARIATION       cLReapIpv6AclRuleDscp
       ACCESS          not-implemented
       DESCRIPTION     "Not supported"

       VARIATION       cLReapIpv6AclNewRuleIndex
       ACCESS          not-implemented
       DESCRIPTION     "Not supported"

       VARIATION       cLReapIpv6AclRuleRowStatus
       ACCESS          not-implemented
       DESCRIPTION     "Not supported"

       VARIATION       cLReapWebPolicyAclEntry
       ACCESS          not-implemented
       DESCRIPTION     "Not supported"

       VARIATION       cLReapWebPolicyAcl
       ACCESS          not-implemented
       DESCRIPTION     "Not supported"

       VARIATION       cLReapWebPolicyAclRowStatus
       ACCESS          not-implemented
       DESCRIPTION     "Not supported"

       VARIATION       cLReapGroupWebPolicyAclType
       ACCESS          not-implemented
       DESCRIPTION     "Not supported"

       VARIATION       cLReapApVlanIdAclEntry
       ACCESS          not-implemented
       DESCRIPTION     "Not supported"

       VARIATION       cLReapVlanId
       ACCESS          not-implemented
       DESCRIPTION     "Not supported"

       VARIATION       cLReapIngressAcl
       ACCESS          not-implemented
       DESCRIPTION     "Not supported"

       VARIATION       cLReapEgressAcl
       ACCESS          not-implemented
       DESCRIPTION     "Not supported"

       VARIATION       cLReapApVlanIdAclRowStatus
       ACCESS          not-implemented
       DESCRIPTION     "Not supported"

       VARIATION       cLReapVlanIdAclType
       ACCESS          not-implemented
       DESCRIPTION     "Not supported"

       VARIATION       cLReapApWlanAclEntry
       ACCESS          not-implemented
       DESCRIPTION     "Not supported"

       VARIATION       cLReapApWebAuthAcl
       ACCESS          not-implemented
       DESCRIPTION     "Not supported"

       VARIATION       cLReapApWebAuthAclRowStatus
       ACCESS          not-implemented
       DESCRIPTION     "Not supported"

       VARIATION       cLReapAclUrlDomainRuleEntry
       ACCESS          not-implemented
       DESCRIPTION     "Not supported"

       VARIATION       cLReapAclUrlDomainRuleIndex
       ACCESS          not-implemented
       DESCRIPTION     "Not supported"

       VARIATION       cLReapAclUrlDomainRuleUrl
       ACCESS          not-implemented
       DESCRIPTION     "Not supported"

       VARIATION       cLReapAclUrlDomainRuleAction
       ACCESS          not-implemented
       DESCRIPTION     "Not supported"

       VARIATION       cLReapAclUrlDomainRuleRowStatus
       ACCESS          not-implemented
       DESCRIPTION     "Not supported"

       VARIATION       cLReapGroupUserStorageType
       ACCESS          not-implemented
       DESCRIPTION     "Not supported"

       VARIATION       cLReapGroupAclEntry
       ACCESS          not-implemented
       DESCRIPTION     "Not supported"

       VARIATION       cLReapGroupWebAuthAcl
       ACCESS          not-implemented
       DESCRIPTION     "Not supported"

       VARIATION       cLReapGroupAclRowStatus
       ACCESS          not-implemented
       DESCRIPTION     "Not supported"

       VARIATION       cLReapGroupWebAuthIpv6Acl
       ACCESS          not-implemented
       DESCRIPTION     "Not supported"

       VARIATION       cLReapApVlanIdEntry
       ACCESS          not-implemented
       DESCRIPTION     "Not supported"

       VARIATION       cLReapApVlanId
       ACCESS          not-implemented
       DESCRIPTION     "Not supported"

       VARIATION       cLReapApVlanInheritance
       ACCESS          not-implemented
       DESCRIPTION     "Not supported"

       VARIATION       cLReapApVlanRowStatus
       ACCESS          not-implemented
       DESCRIPTION     "Not supported"

       VARIATION       cLReapApVlanUsedBySecEthInterface
       ACCESS          not-implemented
       DESCRIPTION     "Not supported"

       VARIATION       cLReapGroupApConfigEntry
       ACCESS          not-implemented
       DESCRIPTION     "Not supported"

       VARIATION       cLReapGroupApStorageType
       ACCESS          not-implemented
       DESCRIPTION     "Not supported"

       VARIATION       cLReapGroupApRowStatus
       ACCESS          not-implemented
       DESCRIPTION     "Not supported"

       VARIATION       cLReapGroupApEntryType
       ACCESS          not-implemented
       DESCRIPTION     "Not supported"

       VARIATION       cLReapGroupApPnPConflict
       ACCESS          not-implemented
       DESCRIPTION     "Not supported"

       VARIATION       cLReapVlanIdNameMapEntry
       ACCESS          not-implemented
       DESCRIPTION     "Not supported"

       VARIATION       cLReapVlanName
       ACCESS          not-implemented
       DESCRIPTION     "Not supported"

       VARIATION       cLReapVlanMapId
       ACCESS          not-implemented
       DESCRIPTION     "Not supported"

       VARIATION       cLReapVlanIdNameMapRowStatus
       ACCESS          not-implemented
       DESCRIPTION     "Not supported"

       VARIATION       cLReapIpv6AclUrlDomainRuleEntry
       ACCESS          not-implemented
       DESCRIPTION     "Not supported"

       VARIATION       cLReapIpv6AclUrlDomainRuleIndex
       ACCESS          not-implemented
       DESCRIPTION     "Not supported"

       VARIATION       cLReapIpv6AclUrlDomainRuleUrl
       ACCESS          not-implemented
       DESCRIPTION     "Not supported"

       VARIATION       cLReapIpv6AclUrlDomainRuleAction
       ACCESS          not-implemented
       DESCRIPTION     "Not supported"

       VARIATION       cLReapIpv6AclUrlDomainRuleRowStatus
       ACCESS          not-implemented
       DESCRIPTION     "Not supported"

       VARIATION       cLReapArpCaheEnabled
       ACCESS          not-implemented
       DESCRIPTION     "Not supported"

       VARIATION       cLReapApLocalSplitACLEntry
       ACCESS          not-implemented
       DESCRIPTION     "Not supported"

       VARIATION       cLReapApLocalSplitAcl
       ACCESS          not-implemented
       DESCRIPTION     "Not supported"

       VARIATION       cLReapApLocalSplitAclRowStatus
       ACCESS          not-implemented
       DESCRIPTION     "Not supported"

       VARIATION       cLReapL2AclRuleEntry
       ACCESS          not-implemented
       DESCRIPTION     "Not supported"

       VARIATION       cLReapL2AclRuleIndex
       ACCESS          not-implemented
       DESCRIPTION     "Not supported"

       VARIATION       cLReapL2AclRuleAction
       ACCESS          not-implemented
       DESCRIPTION     "Not supported"

       VARIATION       cLReapL2AclRuleEthertype
       ACCESS          not-implemented
       DESCRIPTION     "Not supported"

       VARIATION       cLReapL2AclRuleEthertypeMask
       ACCESS          not-implemented
       DESCRIPTION     "Not supported"

       VARIATION       cLReapL2AclRuleDirection
       ACCESS          not-implemented
       DESCRIPTION     "Not supported"

       VARIATION       cLReapL2AclNewRuleIndex
       ACCESS          not-implemented
       DESCRIPTION     "Not supported"

       VARIATION       cLReapL2AclRuleRowStatus
       ACCESS          not-implemented
       DESCRIPTION     "Not supported"

       VARIATION       cLReapGroupVlanIdEntry
       ACCESS          not-implemented
       DESCRIPTION     "Not supported"

       VARIATION       cLReapGroupWlanVlanId
       ACCESS          not-implemented
       DESCRIPTION     "Not supported"

       VARIATION       cLReapGroupVlanRowStatus
       ACCESS          not-implemented
       DESCRIPTION     "Not supported"

       VARIATION       cLReapWlanConfigEntry
       ACCESS          not-implemented
       DESCRIPTION     "Not supported"

       VARIATION       cLReapWlanEnLocalSwitching
       ACCESS          not-implemented
       DESCRIPTION     "Not supported"

       VARIATION       cLReapWlanClientIpLearnEnable
       ACCESS          not-implemented
       DESCRIPTION     "Not supported"

       VARIATION       cLReapWlanApAuth
       ACCESS          not-implemented
       DESCRIPTION     "Not supported"

       VARIATION       cLReapWlanVlanCentralSwitching
       ACCESS          not-implemented
       DESCRIPTION     "Not supported"

       VARIATION       cLReapWlanDhcpCentral
       ACCESS          not-implemented
       DESCRIPTION     "Not supported"

       VARIATION       cLReapWlanDhcpOverrideDNS
       ACCESS          not-implemented
       DESCRIPTION     "Not supported"

       VARIATION       cLReapWlanNatPatEnabled
       ACCESS          not-implemented
       DESCRIPTION     "Not supported"

       VARIATION       cLReapWlanAssocCentral
       ACCESS          not-implemented
       DESCRIPTION     "Not supported"

       VARIATION       cLReapAclRuleEntry
       ACCESS          not-implemented
       DESCRIPTION     "Not supported"

       VARIATION       cLReapAclRuleIndex
       ACCESS          not-implemented
       DESCRIPTION     "Not supported"

       VARIATION       cLReapAclRuleAction
       ACCESS          not-implemented
       DESCRIPTION     "Not supported"

       VARIATION       cLReapAclRuleSourceIpAddressType
       ACCESS          not-implemented
       DESCRIPTION     "Not supported"

       VARIATION       cLReapAclRuleSourceIpAddress
       ACCESS          not-implemented
       DESCRIPTION     "Not supported"

       VARIATION       cLReapAclRuleSourceIpNetmaskType
       ACCESS          not-implemented
       DESCRIPTION     "Not supported"

       VARIATION       cLReapAclRuleSourceIpNetmask
       ACCESS          not-implemented
       DESCRIPTION     "Not supported"

       VARIATION       cLReapAclRuleDestinationIpAddressType
       ACCESS          not-implemented
       DESCRIPTION     "Not supported"

       VARIATION       cLReapAclRuleDestinationIpAddress
       ACCESS          not-implemented
       DESCRIPTION     "Not supported"

       VARIATION       cLReapAclRuleDestinationIpNetmaskType
       ACCESS          not-implemented
       DESCRIPTION     "Not supported"

       VARIATION       cLReapAclRuleDestinationIpNetmask
       ACCESS          not-implemented
       DESCRIPTION     "Not supported"

       VARIATION       cLReapAclRuleProtocol
       ACCESS          not-implemented
       DESCRIPTION     "Not supported"

       VARIATION       cLReapAclRuleStartSourcePort
       ACCESS          not-implemented
       DESCRIPTION     "Not supported"

       VARIATION       cLReapAclRuleEndSourcePort
       ACCESS          not-implemented
       DESCRIPTION     "Not supported"

       VARIATION       cLReapAclRuleStartDestinationPort
       ACCESS          not-implemented
       DESCRIPTION     "Not supported"

       VARIATION       cLReapAclRuleEndDestinationPort
       ACCESS          not-implemented
       DESCRIPTION     "Not supported"

       VARIATION       cLReapAclRuleDscp
       ACCESS          not-implemented
       DESCRIPTION     "Not supported"

       VARIATION       cLReapAclNewRuleIndex
       ACCESS          not-implemented
       DESCRIPTION     "Not supported"

       VARIATION       cLReapAclRuleRowStatus
       ACCESS          not-implemented
       DESCRIPTION     "Not supported"

       VARIATION       cLReapGroupAVCFlexEntry
       ACCESS          not-implemented
       DESCRIPTION     "Not supported"

       VARIATION       cLReapGroupAVCFlexProfileName
       ACCESS          not-implemented
       DESCRIPTION     "Not supported"

       VARIATION       cLReapGroupNbarStatsVisibilityEnable
       ACCESS          not-implemented
       DESCRIPTION     "Not supported"

       VARIATION       cLReapGroupAVCFlexRowStatus
       ACCESS          not-implemented
       DESCRIPTION     "Not supported"

       VARIATION       cLReapApNativeVlanId
       ACCESS          not-implemented
       DESCRIPTION     "Not supported"

       VARIATION       cLReapApVlanEnable
       ACCESS          not-implemented
       DESCRIPTION     "Not supported"

       VARIATION       cLReapHomeApEnable
       ACCESS          not-implemented
       DESCRIPTION     "Not supported"

       VARIATION       cLReapApLeastLatencyJoinEnable
       ACCESS          not-implemented
       DESCRIPTION     "Not supported"

       VARIATION       cLReapInstallMappingRadioBackhaul
       ACCESS          not-implemented
       DESCRIPTION     "Not supported"

       VARIATION       cLReapApResilientMode
       ACCESS          not-implemented
       DESCRIPTION     "Not supported"

       VARIATION       cLReapApNativeVlanLevel
       ACCESS          not-implemented
       DESCRIPTION     "Not supported"

       VARIATION       cLReapGroupCentralDhcpEntry
       ACCESS          not-implemented
       DESCRIPTION     "Not supported"

       VARIATION       cLReapGroupDhcpCentral
       ACCESS          not-implemented
       DESCRIPTION     "Not supported"

       VARIATION       cLReapGroupDhcpOverrideDNS
       ACCESS          not-implemented
       DESCRIPTION     "Not supported"

       VARIATION       cLReapGroupNatPatEnabled
       ACCESS          not-implemented
       DESCRIPTION     "Not supported"

       VARIATION       cLReapGroupDhcpRowStatus
       ACCESS          not-implemented
       DESCRIPTION     "Not supported"

       VARIATION       cLReapL2AclEntry
       ACCESS          not-implemented
       DESCRIPTION     "Not supported"

       VARIATION       cLReapL2AclName
       ACCESS          not-implemented
       DESCRIPTION     "Not supported"

       VARIATION       cLReapL2AclApplyMode
       ACCESS          not-implemented
       DESCRIPTION     "Not supported"

       VARIATION       cLReapL2AclRowStatus
       ACCESS          not-implemented
       DESCRIPTION     "Not supported"

   ::= { ciscoLwappReapCapability 1 }

END
