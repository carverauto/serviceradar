-- *******************************************************************
-- CISCO-LWAPP-CDP MIB CAPABILITY
--
-- November 18, 2020
--
-- Copyright (c) 2020, 2022 by Cisco Systems, Inc.
-- All rights reserved.
-- *******************************************************************

CISCO-LWAPP-CDP-CAPABILITY DEFINITIONS ::= BEGIN


IMPORTS
       MODULE-IDENTITY
           FROM SNMPv2-SMI
       AGENT-CAPABILITIES
           FROM SNMPv2-CONF
       ciscoAgentCapability
           FROM CISCO-SMI;


ciscoLwappCdpCapability  MODULE-IDENTITY

       LAST-UPDATED         "202011180000Z"
       ORGANIZATION         "Cisco Systems, Inc."
       CONTACT-INFO
               "Cisco Systems
               Customer Service

               Postal: 170 W Tasman Drive
               San Jose, CA  95134
               USA

               Tel: +1 800 553-NETS

               E-mail: cs-wnbu-snmp@cisco.com"

       DESCRIPTION
               "Agent capabilities for
               CISCO-LWAPP-CDP-MIB "
       REVISION      "202011180000Z"
       DESCRIPTION
               "Initial version of this MIB module. "

   ::= { ciscoAgentCapability 1161 }

ciscoLwappCdpCapabilityCEV1R0 AGENT-CAPABILITIES

       PRODUCT-RELEASE "Cisco EWLC 1.0"
       STATUS          current
       DESCRIPTION     "CISCO-LWAPP-CDP--MIB capabilities."

       SUPPORTS        CISCO-LWAPP-CDP-MIB
       INCLUDES        {
                           clcCdpApTable
                       }

       VARIATION       clcCdpApEntry
       ACCESS          not-implemented
       DESCRIPTION     "Not supported"

       VARIATION       clcCdpApCdpEnable
       ACCESS          not-implemented
       DESCRIPTION     "Not supported"

       VARIATION       clcCdpInPackets
       ACCESS          not-implemented
       DESCRIPTION     "Not supported"

       VARIATION       clcCdpOutPackets
       ACCESS          not-implemented
       DESCRIPTION     "Not supported"

       VARIATION       clcCdpChecksumErrorPackets
       ACCESS          not-implemented
       DESCRIPTION     "Not supported"

       VARIATION       clcCdpNoMemoryPackets
       ACCESS          not-implemented
       DESCRIPTION     "Not supported"

       VARIATION       clcCdpInvalidPackets
       ACCESS          not-implemented
       DESCRIPTION     "Not supported"

       VARIATION       clcCdpAdvtVersion
       ACCESS          not-implemented
       DESCRIPTION     "Not supported"

       VARIATION       clcCdpMessageInterval
       ACCESS          not-implemented
       DESCRIPTION     "Not supported"

       VARIATION       clcCdpGlobalEnable
       ACCESS          not-implemented
       DESCRIPTION     "Not supported"

   ::= { ciscoLwappCdpCapability 1 }

END
